-- *********************************************************************
-- CISCO-FIREPOWER-ADAPTOR-MIB.my
--
-- MIB representation of the Cisco Firepower
-- ADAPTOR management information model package
--
-- Created March 2020 by Charles Bullis
--
-- Copyright (c) 2005-2020 Cisco Systems, Inc. All rights reserved.
--
-- *********************************************************************

CISCO-FIREPOWER-ADAPTOR-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIBObjects,
    CfprManagedObjectId,
    CfprManagedObjectDn
        FROM CISCO-FIREPOWER-MIB
    CfprAdaptorAdapterStatsTrafficDir,
    CfprAdaptorAdminPowerState,
    CfprAdaptorCIoEpIfType,
    CfprAdaptorCapDefFwVersionOpr,
    CfprAdaptorCapDefType,
    CfprAdaptorCapSpecType,
    CfprAdaptorDefaultAction,
    CfprAdaptorEthArfsProfileAccelaratedRFS,
    CfprAdaptorEthInterruptProfileCoalescingType,
    CfprAdaptorEthNVGREProfileAdminState,
    CfprAdaptorEthOffloadProfileLargeReceive,
    CfprAdaptorEthOffloadProfileTcpRxChecksum,
    CfprAdaptorEthOffloadProfileTcpSegment,
    CfprAdaptorEthOffloadProfileTcpTxChecksum,
    CfprAdaptorEthPortBySizeLargeStatsHistThresholded,
    CfprAdaptorEthPortBySizeLargeStatsThresholded,
    CfprAdaptorEthPortBySizeSmallStatsHistThresholded,
    CfprAdaptorEthPortBySizeSmallStatsThresholded,
    CfprAdaptorEthPortErrStatsHistThresholded,
    CfprAdaptorEthPortErrStatsThresholded,
    CfprAdaptorEthPortMcastStatsHistThresholded,
    CfprAdaptorEthPortMcastStatsThresholded,
    CfprAdaptorEthPortOutsizedStatsHistThresholded,
    CfprAdaptorEthPortOutsizedStatsThresholded,
    CfprAdaptorEthPortStatsHistThresholded,
    CfprAdaptorEthPortStatsThresholded,
    CfprAdaptorEthRoCEProfileAdminState,
    CfprAdaptorEthVxLANProfileAdminState,
    CfprAdaptorEtherIfStatsHistThresholded,
    CfprAdaptorEtherIfStatsThresholded,
    CfprAdaptorExtEthIfFsmCurrentFsm,
    CfprAdaptorExtEthIfFsmStageName,
    CfprAdaptorExtEthIfFsmTaskItem,
    CfprAdaptorExtEthIfPcEpPortId,
    CfprAdaptorExtEthIfPcEpSlotId,
    CfprAdaptorExtEthIfPcPortId,
    CfprAdaptorExtEthIfPcTransport,
    CfprAdaptorExtIfAdminState,
    CfprAdaptorExtIfEpIfRole,
    CfprAdaptorExtIfEpType,
    CfprAdaptorExtIfPcIfRole,
    CfprAdaptorExtIfPcType,
    CfprAdaptorExtIpV6RssHashProfileIpHash,
    CfprAdaptorExtIpV6RssHashProfileTcpHash,
    CfprAdaptorExternalEpLocale,
    CfprAdaptorExternalPcLocale,
    CfprAdaptorFcErrorRecoveryProfileFcpErrorRecovery,
    CfprAdaptorFcIfEventStatsHistThresholded,
    CfprAdaptorFcIfEventStatsThresholded,
    CfprAdaptorFcIfFC4StatsHistThresholded,
    CfprAdaptorFcIfFC4StatsThresholded,
    CfprAdaptorFcIfFrameStatsHistThresholded,
    CfprAdaptorFcIfFrameStatsThresholded,
    CfprAdaptorFcPortStatsHistThresholded,
    CfprAdaptorFcPortStatsThresholded,
    CfprAdaptorHostEthIfFsmCurrentFsm,
    CfprAdaptorHostEthIfFsmStageName,
    CfprAdaptorHostEthIfFsmTaskItem,
    CfprAdaptorHostEthIfHostPort,
    CfprAdaptorHostFcIfAdminState,
    CfprAdaptorHostFcIfFsmCurrentFsm,
    CfprAdaptorHostFcIfFsmStageName,
    CfprAdaptorHostFcIfFsmTaskItem,
    CfprAdaptorHostFcIfHostPort,
    CfprAdaptorHostFcIfPersBind,
    CfprAdaptorHostIfAdminState,
    CfprAdaptorHostIfBootDev,
    CfprAdaptorHostMgmtCapPreboot,
    CfprAdaptorHostMgmtCapPresence,
    CfprAdaptorHostPortId,
    CfprAdaptorHostServiceEthIfIfRole,
    CfprAdaptorHostVisibility,
    CfprAdaptorIScsiCapBootOrderType,
    CfprAdaptorInterruptMode,
    CfprAdaptorIpV4RssHashProfileIpHash,
    CfprAdaptorIpV4RssHashProfileTcpHash,
    CfprAdaptorIpV6RssHashProfileIpHash,
    CfprAdaptorIpV6RssHashProfileTcpHash,
    CfprAdaptorIscsiProtConnectionTimeOut,
    CfprAdaptorIscsiProtDhcpTimeOut,
    CfprAdaptorIscsiProtLunBusyRetryCount,
    CfprAdaptorLanCapDefaultVlan,
    CfprAdaptorLinkState,
    CfprAdaptorLldpCapSupport,
    CfprAdaptorMenloBaseErrorStatsHistThresholded,
    CfprAdaptorMenloBaseErrorStatsThresholded,
    CfprAdaptorMenloDcePortStatsHistThresholded,
    CfprAdaptorMenloDcePortStatsThresholded,
    CfprAdaptorMenloEthErrorStatsHistThresholded,
    CfprAdaptorMenloEthErrorStatsThresholded,
    CfprAdaptorMenloEthStatsHistThresholded,
    CfprAdaptorMenloEthStatsThresholded,
    CfprAdaptorMenloFcErrorStatsHistThresholded,
    CfprAdaptorMenloFcErrorStatsThresholded,
    CfprAdaptorMenloFcStatsHistThresholded,
    CfprAdaptorMenloFcStatsThresholded,
    CfprAdaptorMenloHostPortStatsHistThresholded,
    CfprAdaptorMenloHostPortStatsThresholded,
    CfprAdaptorMenloMcpuErrorStatsHistThresholded,
    CfprAdaptorMenloMcpuErrorStatsThresholded,
    CfprAdaptorMenloMcpuStatsHistThresholded,
    CfprAdaptorMenloMcpuStatsThresholded,
    CfprAdaptorMenloNetEgStatsHistThresholded,
    CfprAdaptorMenloNetEgStatsThresholded,
    CfprAdaptorMenloNetInStatsHistThresholded,
    CfprAdaptorMenloNetInStatsThresholded,
    CfprAdaptorMenloQErrorStatsHistThresholded,
    CfprAdaptorMenloQErrorStatsThresholded,
    CfprAdaptorMenloQStatsHistThresholded,
    CfprAdaptorMenloQStatsThresholded,
    CfprAdaptorMenloQueueStatsComponent,
    CfprAdaptorMenloStatsIndex,
    CfprAdaptorMgmtCapMode,
    CfprAdaptorMgmtCapOperPowerRequirement,
    CfprAdaptorMgmtCapRebootActionOnDestructive,
    CfprAdaptorNwMgmtCapApi,
    CfprAdaptorNwMgmtCapMgmtTransport,
    CfprAdaptorOffloadMethod,
    CfprAdaptorPIoEpIfType,
    CfprAdaptorProtocolProfileConnectionTimeOut,
    CfprAdaptorProtocolProfileLunBusyRetryCount,
    CfprAdaptorPurpose,
    CfprAdaptorReachability,
    CfprAdaptorRssProfileReceiveSideScaling,
    CfprAdaptorSanCapHostNvram,
    CfprAdaptorServiceState,
    CfprAdaptorUnitExtnId,
    CfprAdaptorUnitId,
    CfprAdaptorVnicStatsHistThresholded,
    CfprAdaptorVnicStatsThresholded,
    CfprAddressType,
    CfprConditionRemoteInvRslt,
    CfprDcxAdminState,
    CfprEquipmentConnectionStatus,
    CfprEquipmentOperability,
    CfprEquipmentPowerState,
    CfprEquipmentPresence,
    CfprEquipmentSensorThresholdStatus,
    CfprEtherSatelliteConnectionDisc,
    CfprFabricAVlanAssocPrimaryVlanSwitchId,
    CfprFabricAVlanSharing,
    CfprFabricAVlanTransport,
    CfprFabricAVlanType,
    CfprFabricAVsanTransport,
    CfprFabricAVsanType,
    CfprFabricEpVlanVlanType,
    CfprFabricMembershipStatus,
    CfprFabricVlanAssocPrimaryVlanState,
    CfprFabricVlanOperState,
    CfprFabricVlanOverlapState,
    CfprFabricVnetEpIfRole,
    CfprFabricVnetEpLocale,
    CfprFabricVnetEpPolicyOwner,
    CfprFabricVsanOperState,
    CfprFabricZoningState,
    CfprFsmCompletion,
    CfprFsmFlags,
    CfprFsmFsmStageStatus,
    CfprFsmLifecycle,
    CfprNetworkConnectionType,
    CfprNetworkLocale,
    CfprNetworkPhysEpIfType,
    CfprNetworkPortOperState,
    CfprNetworkPortRole,
    CfprNetworkSide,
    CfprNetworkSwitchId,
    CfprNetworkTransport,
    CfprNetworkVnetEpIfType,
    CfprPolicyPolicyOwner,
    CfprPortEthSpeed,
    CfprVnicVirtualizationPreferenceType
        FROM CISCO-FIREPOWER-TC-MIB;

cfprAdaptorObjects MODULE-IDENTITY
    LAST-UPDATED    "202003100000Z"
    ORGANIZATION    "Cisco Systems Inc."
    CONTACT-INFO
        "Cisco Systems
        Customer Service

        Postal: 170 W Tasman Drive
        San Jose, CA  95134
        USA

        Tel: +1 800 553-NETS

        E-mail: firepower-mibs@cisco.com"
    DESCRIPTION
        "MIB representation of the Cisco Firepower
        ADAPTOR management information model package"
    ::= { ciscoFirepowerMIBObjects 3 }

cfprAdaptorCapQualTable OBJECT-TYPE
    SYNTAX           SEQUENCE OF CfprAdaptorCapQualEntry
    MAX-ACCESS       not-accessible
    STATUS           current
    DESCRIPTION
        "Cisco Firepower adaptor:CapQual managed object table"
    ::= { cfprAdaptorObjects 1 }

cfprAdaptorCapQualEntry OBJECT-TYPE
    SYNTAX           CfprAdaptorCapQualEntry
    MAX-ACCESS       not-accessible
    STATUS           current
    DESCRIPTION
        "Entry for the cfprAdaptorCapQualTable table."
    INDEX { cfprAdaptorCapQualInstanceId }
    ::= { cfprAdaptorCapQualTable 1 }

CfprAdaptorCapQualEntry ::= SEQUENCE {
    cfprAdaptorCapQualInstanceId                                     CfprManagedObjectId,
    cfprAdaptorCapQualDn                                             CfprManagedObjectDn,
    cfprAdaptorCapQualRn                                             SnmpAdminString,
    cfprAdaptorCapQualFwVersionHi                                    SnmpAdminString,
    cfprAdaptorCapQualFwVersionLo                                    SnmpAdminString,
    cfprAdaptorCapQualFwVersionOpr                                   CfprAdaptorCapDefFwVersionOpr,
    cfprAdaptorCapQualMaximum                                        Gauge32,
    cfprAdaptorCapQualModel                                          SnmpAdminString,
    cfprAdaptorCapQualNfVersionLo                                    SnmpAdminString,
    cfprAdaptorCapQualType                                           CfprAdaptorCapDefType
}

cfprAdaptorCapQualInstanceId OBJECT-TYPE
    SYNTAX       CfprManagedObjectId
    MAX-ACCESS   not-accessible
    STATUS       current
    DESCRIPTION
        "Instance identifier of the managed object."
    ::= { cfprAdaptorCapQualEntry 1 }

cfprAdaptorCapQualDn OBJECT-TYPE
    SYNTAX       CfprManagedObjectDn
    MAX-ACCESS   read-only
    STATUS       current
    DESCRIPTION
        "Cisco Firepower adaptor:CapQual:dn managed object property"
    ::= { cfprAdaptorCapQualEntry 2 }

cfprAdaptorCapQualRn OBJECT-TYPE
    SYNTAX       SnmpAdminString
    MAX-ACCESS   read-only
    STATUS       current
    DESCRIPTION
        "Cisco Firepower adaptor:CapQual:rn managed object property"
    ::= { cfprAdaptorCapQualEntry 3 }

cfprAdaptorCapQualFwVersionHi OBJECT-TYPE
    SYNTAX       SnmpAdminString
    MAX-ACCESS   read-only
    STATUS       current
    DESCRIPTION
        "Cisco Firepower adaptor:CapQual:fwVersionHi managed
        object property"
    ::= { cfprAdaptorCapQualEntry 4 }

cfprAdaptorCapQualFwVersionLo OBJECT-TYPE
    SYNTAX       SnmpAdminString
    MAX-ACCESS   read-only
    STATUS       current
    DESCRIPTION
        "Cisco Firepower adaptor:CapQual:fwVersionLo managed
        object property"
    ::= { cfprAdaptorCapQualEntry 5 }

cfprAdaptorCapQualFwVersionOpr OBJECT-TYPE
    SYNTAX       CfprAdaptorCapDefFwVersionOpr
    MAX-ACCESS   read-only
    STATUS       current
    DESCRIPTION
        "Cisco Firepower adaptor:CapQual:fwVersionOpr managed
        object property"
    ::= { cfprAdaptorCapQualEntry 6 }

cfprAdaptorCapQualMaximum OBJECT-TYPE
    SYNTAX       Gauge32
    MAX-ACCESS   read-only
    STATUS       current
    DESCRIPTION
        "Cisco Firepower adaptor:CapQual:maximum managed object property"
    ::= { cfprAdaptorCapQualEntry 7 }

cfprAdaptorCapQualModel OBJECT-TYPE
    SYNTAX       SnmpAdminString
    MAX-ACCESS   read-only
    STATUS       current
    DESCRIPTION
        "Cisco Firepower adaptor:CapQual:model managed object property"
    ::= { cfprAdaptorCapQualEntry 8 }

cfprAdaptorCapQualNfVersionLo OBJECT-TYPE
    SYNTAX       SnmpAdminString
    MAX-ACCESS   read-only
    STATUS       current
    DESCRIPTION
        "Cisco Firepower adaptor:CapQual:nfVersionLo managed
        object property"
    ::= { cfprAdaptorCapQualEntry 9 }

cfprAdaptorCapQualType OBJECT-TYPE
    SYNTAX       CfprAdaptorCapDefType
    MAX-ACCESS   read-only
    STATUS       current
    DESCRIPTION
        "Cisco Firepower adaptor:CapQual:type managed object property"
    ::= { cfprAdaptorCapQualEntry 10 }

cfprAdaptorCapSpecTable OBJECT-TYPE
    SYNTAX           SEQUENCE OF CfprAdaptorCapSpecEntry
    MAX-ACCESS       not-accessible
    STATUS           current
    DESCRIPTION
        "Cisco Firepower adaptor:CapSpec managed object table"
    ::= { cfprAdaptorObjects 2 }

cfprAdaptorCapSpecEntry OBJECT-TYPE
    SYNTAX           CfprAdaptorCapSpecEntry
    MAX-ACCESS       not-accessible
    STATUS           current
    DESCRIPTION
        "Entry for the cfprAdaptorCapSpecTable table."
    INDEX { cfprAdaptorCapSpecInstanceId }
    ::= { cfprAdaptorCapSpecTable 1 }

CfprAdaptorCapSpecEntry ::= SEQUENCE {
    cfprAdaptorCapSpecInstanceId                                     CfprManagedObjectId,
    cfprAdaptorCapSpecDn                                             CfprManagedObjectDn,
    cfprAdaptorCapSpecRn                                             SnmpAdminString,
    cfprAdaptorCapSpecFwVersionHi                                    SnmpAdminString,
    cfprAdaptorCapSpecFwVersionLo                                    SnmpAdminString,
    cfprAdaptorCapSpecFwVersionOpr                                   CfprAdaptorCapDefFwVersionOpr,
    cfprAdaptorCapSpecMaximum                                        Gauge32,
    cfprAdaptorCapSpecNfVersionLo                                    SnmpAdminString,
    cfprAdaptorCapSpecType                                           CfprAdaptorCapSpecType
}

cfprAdaptorCapSpecInstanceId OBJECT-TYPE
    SYNTAX       CfprManagedObjectId
    MAX-ACCESS   not-accessible
    STATUS       current
    DESCRIPTION
        "Instance identifier of the managed object."
    ::= { cfprAdaptorCapSpecEntry 1 }

cfprAdaptorCapSpecDn OBJECT-TYPE
    SYNTAX       CfprManagedObjectDn
    MAX-ACCESS   read-only
    STATUS       current
    DESCRIPTION
        "Cisco Firepower adaptor:CapSpec:dn managed object property"
    ::= { cfprAdaptorCapSpecEntry 2 }

cfprAdaptorCapSpecRn OBJECT-TYPE
    SYNTAX       SnmpAdminString
    MAX-ACCESS   read-only
    STATUS       current
    DESCRIPTION
        "Cisco Firepower adaptor:CapSpec:rn managed object property"
    ::= { cfprAdaptorCapSpecEntry 3 }

cfprAdaptorCapSpecFwVersionHi OBJECT-TYPE
    SYNTAX       SnmpAdminString
    MAX-ACCESS   read-only
    STATUS       current
    DESCRIPTION
        "Cisco Firepower adaptor:CapSpec:fwVersionHi managed
        object property"
    ::= { cfprAdaptorCapSpecEntry 4 }

cfprAdaptorCapSpecFwVersionLo OBJECT-TYPE
    SYNTAX       SnmpAdminString
    MAX-ACCESS   read-only
    STATUS       current
    DESCRIPTION
        "Cisco Firepower adaptor:CapSpec:fwVersionLo managed
        object property"
    ::= { cfprAdaptorCapSpecEntry 5 }

cfprAdaptorCapSpecFwVersionOpr OBJECT-TYPE
    SYNTAX       CfprAdaptorCapDefFwVersionOpr
    MAX-ACCESS   read-only
    STATUS       current
    DESCRIPTION
        "Cisco Firepower adaptor:CapSpec:fwVersionOpr managed
        object property"
    ::= { cfprAdaptorCapSpecEntry 6 }

cfprAdaptorCapSpecMaximum OBJECT-TYPE
    SYNTAX       Gauge32
    MAX-ACCESS   read-only
    STATUS       current
    DESCRIPTION
        "Cisco Firepower adaptor:CapSpec:maximum managed object property"
    ::= { cfprAdaptorCapSpecEntry 7 }

cfprAdaptorCapSpecNfVersionLo OBJECT-TYPE
    SYNTAX       SnmpAdminString
    MAX-ACCESS   read-only
    STATUS       current
    DESCRIPTION
        "Cisco Firepower adaptor:CapSpec:nfVersionLo managed
        object property"
    ::= { cfprAdaptorCapSpecEntry 8 }

cfprAdaptorCapSpecType OBJECT-TYPE
    SYNTAX       CfprAdaptorCapSpecType
    MAX-ACCESS   read-only
    STATUS       current
    DESCRIPTION
        "Cisco Firepower adaptor:CapSpec:type managed object property"
    ::= { cfprAdaptorCapSpecEntry 9 }

cfprAdaptorDiagCapTable OBJECT-TYPE
    SYNTAX           SEQUENCE OF CfprAdaptorDiagCapEntry
    MAX-ACCESS       not-accessible
    STATUS           current
    DESCRIPTION
        "Cisco Firepower adaptor:DiagCap managed object table"
    ::= { cfprAdaptorObjects 3 }

cfprAdaptorDiagCapEntry OBJECT-TYPE
    SYNTAX           CfprAdaptorDiagCapEntry
    MAX-ACCESS       not-accessible
    STATUS           current
    DESCRIPTION
        "Entry for the cfprAdaptorDiagCapTable table."
    INDEX { cfprAdaptorDiagCapInstanceId }
    ::= { cfprAdaptorDiagCapTable 1 }

CfprAdaptorDiagCapEntry ::= SEQUENCE {
    cfprAdaptorDiagCapInstanceId                                     CfprManagedObjectId,
    cfprAdaptorDiagCapDn                                             CfprManagedObjectDn,
    cfprAdaptorDiagCapRn                                             SnmpAdminString,
    cfprAdaptorDiagCapEnableLldpTransmit                             TruthValue
}

cfprAdaptorDiagCapInstanceId OBJECT-TYPE
    SYNTAX       CfprManagedObjectId
    MAX-ACCESS   not-accessible
    STATUS       current
    DESCRIPTION
        "Instance identifier of the managed object."
    ::= { cfprAdaptorDiagCapEntry 1 }

cfprAdaptorDiagCapDn OBJECT-TYPE
    SYNTAX       CfprManagedObjectDn
    MAX-ACCESS   read-only
    STATUS       current
    DESCRIPTION
        "Cisco Firepower adaptor:DiagCap:dn managed object property"
    ::= { cfprAdaptorDiagCapEntry 2 }

cfprAdaptorDiagCapRn OBJECT-TYPE
    SYNTAX       SnmpAdminString
    MAX-ACCESS   read-only
    STATUS       current
    DESCRIPTION
        "Cisco Firepower adaptor:DiagCap:rn managed object property"
    ::= { cfprAdaptorDiagCapEntry 3 }

cfprAdaptorDiagCapEnableLldpTransmit OBJECT-TYPE
    SYNTAX       TruthValue
    MAX-ACCESS   read-only
    STATUS       current
    DESCRIPTION
        "Cisco Firepower adaptor:DiagCap:enableLldpTransmit
        managed object property"
    ::= { cfprAdaptorDiagCapEntry 4 }

cfprAdaptorEthArfsProfileTable OBJECT-TYPE
    SYNTAX           SEQUENCE OF CfprAdaptorEthArfsProfileEntry
    MAX-ACCESS       not-accessible
    STATUS           current
    DESCRIPTION
        "Cisco Firepower adaptor:EthArfsProfile managed object table"
    ::= { cfprAdaptorObjects 4 }

cfprAdaptorEthArfsProfileEntry OBJECT-TYPE
    SYNTAX           CfprAdaptorEthArfsProfileEntry
    MAX-ACCESS       not-accessible
    STATUS           current
    DESCRIPTION
        "Entry for the cfprAdaptorEthArfsProfileTable table."
    INDEX { cfprAdaptorEthArfsProfileInstanceId }
    ::= { cfprAdaptorEthArfsProfileTable 1 }

CfprAdaptorEthArfsProfileEntry ::= SEQUENCE {
    cfprAdaptorEthArfsProfileInstanceId                              CfprManagedObjectId,
    cfprAdaptorEthArfsProfileDn                                      CfprManagedObjectDn,
    cfprAdaptorEthArfsProfileRn                                      SnmpAdminString,
    cfprAdaptorEthArfsProfileAccelaratedRFS                          CfprAdaptorEthArfsProfileAccelaratedRFS
}

cfprAdaptorEthArfsProfileInstanceId OBJECT-TYPE
    SYNTAX       CfprManagedObjectId
    MAX-ACCESS   not-accessible
    STATUS       current
    DESCRIPTION
        "Instance identifier of the managed object."
    ::= { cfprAdaptorEthArfsProfileEntry 1 }

cfprAdaptorEthArfsProfileDn OBJECT-TYPE
    SYNTAX       CfprManagedObjectDn
    MAX-ACCESS   read-only
    STATUS       current
    DESCRIPTION
        "Cisco Firepower adaptor:EthArfsProfile:dn managed
        object property"
    ::= { cfprAdaptorEthArfsProfileEntry 2 }

cfprAdaptorEthArfsProfileRn OBJECT-TYPE
    SYNTAX       SnmpAdminString
    MAX-ACCESS   read-only
    STATUS       current
    DESCRIPTION
        "Cisco Firepower adaptor:EthArfsProfile:rn managed
        object property"
    ::= { cfprAdaptorEthArfsProfileEntry 3 }

cfprAdaptorEthArfsProfileAccelaratedRFS OBJECT-TYPE
    SYNTAX       CfprAdaptorEthArfsProfileAccelaratedRFS
    MAX-ACCESS   read-only
    STATUS       current
    DESCRIPTION
        "Cisco Firepower adaptor:EthArfsProfile:accelaratedRFS
        managed object property"
    ::= { cfprAdaptorEthArfsProfileEntry 4 }

cfprAdaptorEthCompQueueProfileTable OBJECT-TYPE
    SYNTAX           SEQUENCE OF CfprAdaptorEthCompQueueProfileEntry
    MAX-ACCESS       not-accessible
    STATUS           current
    DESCRIPTION
        "Cisco Firepower adaptor:EthCompQueueProfile managed object table"
    ::= { cfprAdaptorObjects 5 }

cfprAdaptorEthCompQueueProfileEntry OBJECT-TYPE
    SYNTAX           CfprAdaptorEthCompQueueProfileEntry
    MAX-ACCESS       not-accessible
    STATUS           current
    DESCRIPTION
        "Entry for the cfprAdaptorEthCompQueueProfileTable table."
    INDEX { cfprAdaptorEthCompQueueProfileInstanceId }
    ::= { cfprAdaptorEthCompQueueProfileTable 1 }

CfprAdaptorEthCompQueueProfileEntry ::= SEQUENCE {
    cfprAdaptorEthCompQueueProfileInstanceId                         CfprManagedObjectId,
    cfprAdaptorEthCompQueueProfileDn                                 CfprManagedObjectDn,
    cfprAdaptorEthCompQueueProfileRn                                 SnmpAdminString,
    cfprAdaptorEthCompQueueProfileCount                              Gauge32,
    cfprAdaptorEthCompQueueProfileRingSize                           Gauge32
}

cfprAdaptorEthCompQueueProfileInstanceId OBJECT-TYPE
    SYNTAX       CfprManagedObjectId
    MAX-ACCESS   not-accessible
    STATUS       current
    DESCRIPTION
        "Instance identifier of the managed object."
    ::= { cfprAdaptorEthCompQueueProfileEntry 1 }

cfprAdaptorEthCompQueueProfileDn OBJECT-TYPE
    SYNTAX       CfprManagedObjectDn
    MAX-ACCESS   read-only
    STATUS       current
    DESCRIPTION
        "Cisco Firepower adaptor:EthCompQueueProfile:dn
        managed object property"
    ::= { cfprAdaptorEthCompQueueProfileEntry 2 }

cfprAdaptorEthCompQueueProfileRn OBJECT-TYPE
    SYNTAX       SnmpAdminString
    MAX-ACCESS   read-only
    STATUS       current
    DESCRIPTION
        "Cisco Firepower adaptor:EthCompQueueProfile:rn
        managed object property"
    ::= { cfprAdaptorEthCompQueueProfileEntry 3 }

cfprAdaptorEthCompQueueProfileCount OBJECT-TYPE
    SYNTAX       Gauge32
    MAX-ACCESS   read-only
    STATUS       current
    DESCRIPTION
        "Cisco Firepower adaptor:EthCompQueueProfile:count
        managed object property"
    ::= { cfprAdaptorEthCompQueueProfileEntry 4 }

cfprAdaptorEthCompQueueProfileRingSize OBJECT-TYPE
    SYNTAX       Gauge32
    MAX-ACCESS   read-only
    STATUS       current
    DESCRIPTION
        "Cisco Firepower adaptor:EthCompQueueProfile:ringSize
        managed object property"
    ::= { cfprAdaptorEthCompQueueProfileEntry 5 }

cfprAdaptorEthFailoverProfileTable OBJECT-TYPE
    SYNTAX           SEQUENCE OF CfprAdaptorEthFailoverProfileEntry
    MAX-ACCESS       not-accessible
    STATUS           current
    DESCRIPTION
        "Cisco Firepower adaptor:EthFailoverProfile managed object table"
    ::= { cfprAdaptorObjects 6 }

cfprAdaptorEthFailoverProfileEntry OBJECT-TYPE
    SYNTAX           CfprAdaptorEthFailoverProfileEntry
    MAX-ACCESS       not-accessible
    STATUS           current
    DESCRIPTION
        "Entry for the cfprAdaptorEthFailoverProfileTable table."
    INDEX { cfprAdaptorEthFailoverProfileInstanceId }
    ::= { cfprAdaptorEthFailoverProfileTable 1 }

CfprAdaptorEthFailoverProfileEntry ::= SEQUENCE {
    cfprAdaptorEthFailoverProfileInstanceId                          CfprManagedObjectId,
    cfprAdaptorEthFailoverProfileDn                                  CfprManagedObjectDn,
    cfprAdaptorEthFailoverProfileRn                                  SnmpAdminString,
    cfprAdaptorEthFailoverProfileTimeout                             Gauge32
}

cfprAdaptorEthFailoverProfileInstanceId OBJECT-TYPE
    SYNTAX       CfprManagedObjectId
    MAX-ACCESS   not-accessible
    STATUS       current
    DESCRIPTION
        "Instance identifier of the managed object."
    ::= { cfprAdaptorEthFailoverProfileEntry 1 }

cfprAdaptorEthFailoverProfileDn OBJECT-TYPE
    SYNTAX       CfprManagedObjectDn
    MAX-ACCESS   read-only
    STATUS       current
    DESCRIPTION
        "Cisco Firepower adaptor:EthFailoverProfile:dn
        managed object property"
    ::= { cfprAdaptorEthFailoverProfileEntry 2 }

cfprAdaptorEthFailoverProfileRn OBJECT-TYPE
    SYNTAX       SnmpAdminString
    MAX-ACCESS   read-only
    STATUS       current
    DESCRIPTION
        "Cisco Firepower adaptor:EthFailoverProfile:rn
        managed object property"
    ::= { cfprAdaptorEthFailoverProfileEntry 3 }

cfprAdaptorEthFailoverProfileTimeout OBJECT-TYPE
    SYNTAX       Gauge32
    MAX-ACCESS   read-only
    STATUS       current
    DESCRIPTION
        "Cisco Firepower adaptor:EthFailoverProfile:timeout
        managed object property"
    ::= { cfprAdaptorEthFailoverProfileEntry 4 }

cfprAdaptorEthInterruptProfileTable OBJECT-TYPE
    SYNTAX           SEQUENCE OF CfprAdaptorEthInterruptProfileEntry
    MAX-ACCESS       not-accessible
    STATUS           current
    DESCRIPTION
        "Cisco Firepower adaptor:EthInterruptProfile managed object table"
    ::= { cfprAdaptorObjects 7 }

cfprAdaptorEthInterruptProfileEntry OBJECT-TYPE
    SYNTAX           CfprAdaptorEthInterruptProfileEntry
    MAX-ACCESS       not-accessible
    STATUS           current
    DESCRIPTION
        "Entry for the cfprAdaptorEthInterruptProfileTable table."
    INDEX { cfprAdaptorEthInterruptProfileInstanceId }
    ::= { cfprAdaptorEthInterruptProfileTable 1 }

CfprAdaptorEthInterruptProfileEntry ::= SEQUENCE {
    cfprAdaptorEthInterruptProfileInstanceId                         CfprManagedObjectId,
    cfprAdaptorEthInterruptProfileDn                                 CfprManagedObjectDn,
    cfprAdaptorEthInterruptProfileRn                                 SnmpAdminString,
    cfprAdaptorEthInterruptProfileCoalescingTime                     Gauge32,
    cfprAdaptorEthInterruptProfileCoalescingType                     CfprAdaptorEthInterruptProfileCoalescingType,
    cfprAdaptorEthInterruptProfileCount                              Gauge32,
    cfprAdaptorEthInterruptProfileMode                               CfprAdaptorInterruptMode
}

cfprAdaptorEthInterruptProfileInstanceId OBJECT-TYPE
    SYNTAX       CfprManagedObjectId
    MAX-ACCESS   not-accessible
    STATUS       current
    DESCRIPTION
        "Instance identifier of the managed object."
    ::= { cfprAdaptorEthInterruptProfileEntry 1 }

cfprAdaptorEthInterruptProfileDn OBJECT-TYPE
    SYNTAX       CfprManagedObjectDn
    MAX-ACCESS   read-only
    STATUS       current
    DESCRIPTION
        "Cisco Firepower adaptor:EthInterruptProfile:dn
        managed object property"
    ::= { cfprAdaptorEthInterruptProfileEntry 2 }

cfprAdaptorEthInterruptProfileRn OBJECT-TYPE
    SYNTAX       SnmpAdminString
    MAX-ACCESS   read-only
    STATUS       current
    DESCRIPTION
        "Cisco Firepower adaptor:EthInterruptProfile:rn
        managed object property"
    ::= { cfprAdaptorEthInterruptProfileEntry 3 }

cfprAdaptorEthInterruptProfileCoalescingTime OBJECT-TYPE
    SYNTAX       Gauge32
    MAX-ACCESS   read-only
    STATUS       current
    DESCRIPTION
        "Cisco Firepower adaptor:EthInterruptProfile:coalescingTime
        managed object property"
    ::= { cfprAdaptorEthInterruptProfileEntry 4 }

cfprAdaptorEthInterruptProfileCoalescingType OBJECT-TYPE
    SYNTAX       CfprAdaptorEthInterruptProfileCoalescingType
    MAX-ACCESS   read-only
    STATUS       current
    DESCRIPTION
        "Cisco Firepower adaptor:EthInterruptProfile:coalescingType
        managed object property"
    ::= { cfprAdaptorEthInterruptProfileEntry 5 }

cfprAdaptorEthInterruptProfileCount OBJECT-TYPE
    SYNTAX       Gauge32
    MAX-ACCESS   read-only
    STATUS       current
    DESCRIPTION
        "Cisco Firepower adaptor:EthInterruptProfile:count
        managed object property"
    ::= { cfprAdaptorEthInterruptProfileEntry 6 }

cfprAdaptorEthInterruptProfileMode OBJECT-TYPE
    SYNTAX       CfprAdaptorInterruptMode
    MAX-ACCESS   read-only
    STATUS       current
    DESCRIPTION
        "Cisco Firepower adaptor:EthInterruptProfile:mode
        managed object property"
    ::= { cfprAdaptorEthInterruptProfileEntry 7 }

cfprAdaptorEthNVGREProfileTable OBJECT-TYPE
    SYNTAX           SEQUENCE OF CfprAdaptorEthNVGREProfileEntry
    MAX-ACCESS       not-accessible
    STATUS           current
    DESCRIPTION
        "Cisco Firepower adaptor:EthNVGREProfile managed object table"
    ::= { cfprAdaptorObjects 8 }

cfprAdaptorEthNVGREProfileEntry OBJECT-TYPE
    SYNTAX           CfprAdaptorEthNVGREProfileEntry
    MAX-ACCESS       not-accessible
    STATUS           current
    DESCRIPTION
        "Entry for the cfprAdaptorEthNVGREProfileTable table."
    INDEX { cfprAdaptorEthNVGREProfileInstanceId }
    ::= { cfprAdaptorEthNVGREProfileTable 1 }

CfprAdaptorEthNVGREProfileEntry ::= SEQUENCE {
    cfprAdaptorEthNVGREProfileInstanceId                             CfprManagedObjectId,
    cfprAdaptorEthNVGREProfileDn                                     CfprManagedObjectDn,
    cfprAdaptorEthNVGREProfileRn                                     SnmpAdminString,
    cfprAdaptorEthNVGREProfileAdminState                             CfprAdaptorEthNVGREProfileAdminState
}

cfprAdaptorEthNVGREProfileInstanceId OBJECT-TYPE
    SYNTAX       CfprManagedObjectId
    MAX-ACCESS   not-accessible
    STATUS       current
    DESCRIPTION
        "Instance identifier of the managed object."
    ::= { cfprAdaptorEthNVGREProfileEntry 1 }

cfprAdaptorEthNVGREProfileDn OBJECT-TYPE
    SYNTAX       CfprManagedObjectDn
    MAX-ACCESS   read-only
    STATUS       current
    DESCRIPTION
        "Cisco Firepower adaptor:EthNVGREProfile:dn managed
        object property"
    ::= { cfprAdaptorEthNVGREProfileEntry 2 }

cfprAdaptorEthNVGREProfileRn OBJECT-TYPE
    SYNTAX       SnmpAdminString
    MAX-ACCESS   read-only
    STATUS       current
    DESCRIPTION
        "Cisco Firepower adaptor:EthNVGREProfile:rn managed
        object property"
    ::= { cfprAdaptorEthNVGREProfileEntry 3 }

cfprAdaptorEthNVGREProfileAdminState OBJECT-TYPE
    SYNTAX       CfprAdaptorEthNVGREProfileAdminState
    MAX-ACCESS   read-only
    STATUS       current
    DESCRIPTION
        "Cisco Firepower adaptor:EthNVGREProfile:adminState
        managed object property"
    ::= { cfprAdaptorEthNVGREProfileEntry 4 }

cfprAdaptorEthOffloadProfileTable OBJECT-TYPE
    SYNTAX           SEQUENCE OF CfprAdaptorEthOffloadProfileEntry
    MAX-ACCESS       not-accessible
    STATUS           current
    DESCRIPTION
        "Cisco Firepower adaptor:EthOffloadProfile managed object table"
    ::= { cfprAdaptorObjects 9 }

cfprAdaptorEthOffloadProfileEntry OBJECT-TYPE
    SYNTAX           CfprAdaptorEthOffloadProfileEntry
    MAX-ACCESS       not-accessible
    STATUS           current
    DESCRIPTION
        "Entry for the cfprAdaptorEthOffloadProfileTable table."
    INDEX { cfprAdaptorEthOffloadProfileInstanceId }
    ::= { cfprAdaptorEthOffloadProfileTable 1 }

CfprAdaptorEthOffloadProfileEntry ::= SEQUENCE {
    cfprAdaptorEthOffloadProfileInstanceId                           CfprManagedObjectId,
    cfprAdaptorEthOffloadProfileDn                                   CfprManagedObjectDn,
    cfprAdaptorEthOffloadProfileRn                                   SnmpAdminString,
    cfprAdaptorEthOffloadProfileLargeReceive                         CfprAdaptorEthOffloadProfileLargeReceive,
    cfprAdaptorEthOffloadProfileTcpRxChecksum                        CfprAdaptorEthOffloadProfileTcpRxChecksum,
    cfprAdaptorEthOffloadProfileTcpSegment                           CfprAdaptorEthOffloadProfileTcpSegment,
    cfprAdaptorEthOffloadProfileTcpTxChecksum                        CfprAdaptorEthOffloadProfileTcpTxChecksum
}

cfprAdaptorEthOffloadProfileInstanceId OBJECT-TYPE
    SYNTAX       CfprManagedObjectId
    MAX-ACCESS   not-accessible
    STATUS       current
    DESCRIPTION
        "Instance identifier of the managed object."
    ::= { cfprAdaptorEthOffloadProfileEntry 1 }

cfprAdaptorEthOffloadProfileDn OBJECT-TYPE
    SYNTAX       CfprManagedObjectDn
    MAX-ACCESS   read-only
    STATUS       current
    DESCRIPTION
        "Cisco Firepower adaptor:EthOffloadProfile:dn managed
        object property"
    ::= { cfprAdaptorEthOffloadProfileEntry 2 }

cfprAdaptorEthOffloadProfileRn OBJECT-TYPE
    SYNTAX       SnmpAdminString
    MAX-ACCESS   read-only
    STATUS       current
    DESCRIPTION
        "Cisco Firepower adaptor:EthOffloadProfile:rn managed
        object property"
    ::= { cfprAdaptorEthOffloadProfileEntry 3 }

cfprAdaptorEthOffloadProfileLargeReceive OBJECT-TYPE
    SYNTAX       CfprAdaptorEthOffloadProfileLargeReceive
    MAX-ACCESS   read-only
    STATUS       current
    DESCRIPTION
        "Cisco Firepower adaptor:EthOffloadProfile:largeReceive
        managed object property"
    ::= { cfprAdaptorEthOffloadProfileEntry 4 }

cfprAdaptorEthOffloadProfileTcpRxChecksum OBJECT-TYPE
    SYNTAX       CfprAdaptorEthOffloadProfileTcpRxChecksum
    MAX-ACCESS   read-only
    STATUS       current
    DESCRIPTION
        "Cisco Firepower adaptor:EthOffloadProfile:tcpRxChecksum
        managed object property"
    ::= { cfprAdaptorEthOffloadProfileEntry 5 }

cfprAdaptorEthOffloadProfileTcpSegment OBJECT-TYPE
    SYNTAX       CfprAdaptorEthOffloadProfileTcpSegment
    MAX-ACCESS   read-only
    STATUS       current
    DESCRIPTION
        "Cisco Firepower adaptor:EthOffloadProfile:tcpSegment
        managed object property"
    ::= { cfprAdaptorEthOffloadProfileEntry 6 }

cfprAdaptorEthOffloadProfileTcpTxChecksum OBJECT-TYPE
    SYNTAX       CfprAdaptorEthOffloadProfileTcpTxChecksum
    MAX-ACCESS   read-only
    STATUS       current
    DESCRIPTION
        "Cisco Firepower adaptor:EthOffloadProfile:tcpTxChecksum
        managed object property"
    ::= { cfprAdaptorEthOffloadProfileEntry 7 }

cfprAdaptorEthPortBySizeLargeStatsTable OBJECT-TYPE
    SYNTAX           SEQUENCE OF CfprAdaptorEthPortBySizeLargeStatsEntry
    MAX-ACCESS       not-accessible
    STATUS           current
    DESCRIPTION
        "Cisco Firepower adaptor:EthPortBySizeLargeStats
        managed object table"
    ::= { cfprAdaptorObjects 10 }

cfprAdaptorEthPortBySizeLargeStatsEntry OBJECT-TYPE
    SYNTAX           CfprAdaptorEthPortBySizeLargeStatsEntry
    MAX-ACCESS       not-accessible
    STATUS           current
    DESCRIPTION
        "Entry for the cfprAdaptorEthPortBySizeLargeStatsTable table."
    INDEX { cfprAdaptorEthPortBySizeLargeStatsInstanceId }
    ::= { cfprAdaptorEthPortBySizeLargeStatsTable 1 }

CfprAdaptorEthPortBySizeLargeStatsEntry ::= SEQUENCE {
    cfprAdaptorEthPortBySizeLargeStatsInstanceId                     CfprManagedObjectId,
    cfprAdaptorEthPortBySizeLargeStatsDn                             CfprManagedObjectDn,
    cfprAdaptorEthPortBySizeLargeStatsRn                             SnmpAdminString,
    cfprAdaptorEthPortBySizeLargeStatsGreaterThanOrEqualTo9216       Unsigned64,
    cfprAdaptorEthPortBySizeLargeStatsGreaterThanOrEqualTo9216Delta  Counter64,
    cfprAdaptorEthPortBySizeLargeStatsGreaterThanOrEqualTo9216DeltaAvg Unsigned64,
    cfprAdaptorEthPortBySizeLargeStatsGreaterThanOrEqualTo9216DeltaMax Unsigned64,
    cfprAdaptorEthPortBySizeLargeStatsGreaterThanOrEqualTo9216DeltaMin Unsigned64,
    cfprAdaptorEthPortBySizeLargeStatsIntervals                      Gauge32,
    cfprAdaptorEthPortBySizeLargeStatsLessThan2048                   Unsigned64,
    cfprAdaptorEthPortBySizeLargeStatsLessThan2048Delta              Counter64,
    cfprAdaptorEthPortBySizeLargeStatsLessThan2048DeltaAvg           Unsigned64,
    cfprAdaptorEthPortBySizeLargeStatsLessThan2048DeltaMax           Unsigned64,
    cfprAdaptorEthPortBySizeLargeStatsLessThan2048DeltaMin           Unsigned64,
    cfprAdaptorEthPortBySizeLargeStatsLessThan4096                   Unsigned64,
    cfprAdaptorEthPortBySizeLargeStatsLessThan4096Delta              Counter64,
    cfprAdaptorEthPortBySizeLargeStatsLessThan4096DeltaAvg           Unsigned64,
    cfprAdaptorEthPortBySizeLargeStatsLessThan4096DeltaMax           Unsigned64,
    cfprAdaptorEthPortBySizeLargeStatsLessThan4096DeltaMin           Unsigned64,
    cfprAdaptorEthPortBySizeLargeStatsLessThan8192                   Unsigned64,
    cfprAdaptorEthPortBySizeLargeStatsLessThan8192Delta              Counter64,
    cfprAdaptorEthPortBySizeLargeStatsLessThan8192DeltaAvg           Unsigned64,
    cfprAdaptorEthPortBySizeLargeStatsLessThan8192DeltaMax           Unsigned64,
    cfprAdaptorEthPortBySizeLargeStatsLessThan8192DeltaMin           Unsigned64,
    cfprAdaptorEthPortBySizeLargeStatsLessThan9216                   Unsigned64,
    cfprAdaptorEthPortBySizeLargeStatsLessThan9216Delta              Counter64,
    cfprAdaptorEthPortBySizeLargeStatsLessThan9216DeltaAvg           Unsigned64,
    cfprAdaptorEthPortBySizeLargeStatsLessThan9216DeltaMax           Unsigned64,
    cfprAdaptorEthPortBySizeLargeStatsLessThan9216DeltaMin           Unsigned64,
    cfprAdaptorEthPortBySizeLargeStatsLessThanOrEqualTo1518          Unsigned64,
    cfprAdaptorEthPortBySizeLargeStatsLessThanOrEqualTo1518Delta     Counter64,
    cfprAdaptorEthPortBySizeLargeStatsLessThanOrEqualTo1518DeltaAvg  Unsigned64,
    cfprAdaptorEthPortBySizeLargeStatsLessThanOrEqualTo1518DeltaMax  Unsigned64,
    cfprAdaptorEthPortBySizeLargeStatsLessThanOrEqualTo1518DeltaMin  Unsigned64,
    cfprAdaptorEthPortBySizeLargeStatsNoBreakdownGreaterThan1518     Unsigned64,
    cfprAdaptorEthPortBySizeLargeStatsNoBreakdownGreaterThan1518Delta Counter64,
    cfprAdaptorEthPortBySizeLargeStatsNoBreakdownGreaterThan1518DeltaAvg Unsigned64,
    cfprAdaptorEthPortBySizeLargeStatsNoBreakdownGreaterThan1518DeltaMax Unsigned64,
    cfprAdaptorEthPortBySizeLargeStatsNoBreakdownGreaterThan1518DeltaMin Unsigned64,
    cfprAdaptorEthPortBySizeLargeStatsSuspect                        TruthValue,
    cfprAdaptorEthPortBySizeLargeStatsThresholded                    CfprAdaptorEthPortBySizeLargeStatsThresholded,
    cfprAdaptorEthPortBySizeLargeStatsTimeCollected                  DateAndTime,
    cfprAdaptorEthPortBySizeLargeStatsTrafficDirection               CfprAdaptorAdapterStatsTrafficDir,
    cfprAdaptorEthPortBySizeLargeStatsUpdate                         Gauge32
}

cfprAdaptorEthPortBySizeLargeStatsInstanceId OBJECT-TYPE
    SYNTAX       CfprManagedObjectId
    MAX-ACCESS   not-accessible
    STATUS       current
    DESCRIPTION
        "Instance identifier of the managed object."
    ::= { cfprAdaptorEthPortBySizeLargeStatsEntry 1 }

cfprAdaptorEthPortBySizeLargeStatsDn OBJECT-TYPE
    SYNTAX       CfprManagedObjectDn
    MAX-ACCESS   read-only
    STATUS       current
    DESCRIPTION
        "Cisco Firepower adaptor:EthPortBySizeLargeStats:dn
        managed object property"
    ::= { cfprAdaptorEthPortBySizeLargeStatsEntry 2 }

cfprAdaptorEthPortBySizeLargeStatsRn OBJECT-TYPE
    SYNTAX       SnmpAdminString
    MAX-ACCESS   read-only
    STATUS       current
    DESCRIPTION
        "Cisco Firepower adaptor:EthPortBySizeLargeStats:rn
        managed object property"
    ::= { cfprAdaptorEthPortBySizeLargeStatsEntry 3 }

cfprAdaptorEthPortBySizeLargeStatsGreaterThanOrEqualTo9216 OBJECT-TYPE
    SYNTAX       Unsigned64
    MAX-ACCESS   read-only
    STATUS       current
    DESCRIPTION
        "Cisco Firepower adaptor:EthPortBySizeLargeStats:greaterThanOrEqua
        lTo9216 managed object property"
    ::= { cfprAdaptorEthPortBySizeLargeStatsEntry 4 }

cfprAdaptorEthPortBySizeLargeStatsGreaterThanOrEqualTo9216Delta OBJECT-TYPE
    SYNTAX       Counter64
    MAX-ACCESS   read-only
    STATUS       current
    DESCRIPTION
        "Cisco Firepower adaptor:EthPortBySizeLargeStats:greaterThanOrEqua
        lTo9216Delta managed object property"
    ::= { cfprAdaptorEthPortBySizeLargeStatsEntry 5 }

cfprAdaptorEthPortBySizeLargeStatsGreaterThanOrEqualTo9216DeltaAvg OBJECT-TYPE
    SYNTAX       Unsigned64
    MAX-ACCESS   read-only
    STATUS       current
    DESCRIPTION
        "Cisco Firepower adaptor:EthPortBySizeLargeStats:greaterThanOrEqua
        lTo9216DeltaAvg managed object property"
    ::= { cfprAdaptorEthPortBySizeLargeStatsEntry 6 }

cfprAdaptorEthPortBySizeLargeStatsGreaterThanOrEqualTo9216DeltaMax OBJECT-TYPE
    SYNTAX       Unsigned64
    MAX-ACCESS   read-only
    STATUS       current
    DESCRIPTION
        "Cisco Firepower adaptor:EthPortBySizeLargeStats:greaterThanOrEqua
        lTo9216DeltaMax managed object property"
    ::= { cfprAdaptorEthPortBySizeLargeStatsEntry 7 }

cfprAdaptorEthPortBySizeLargeStatsGreaterThanOrEqualTo9216DeltaMin OBJECT-TYPE
    SYNTAX       Unsigned64
    MAX-ACCESS   read-only
    STATUS       current
    DESCRIPTION
        "Cisco Firepower adaptor:EthPortBySizeLargeStats:greaterThanOrEqua
        lTo9216DeltaMin managed object property"
    ::= { cfprAdaptorEthPortBySizeLargeStatsEntry 8 }

cfprAdaptorEthPortBySizeLargeStatsIntervals OBJECT-TYPE
    SYNTAX       Gauge32
    MAX-ACCESS   read-only
    STATUS       current
    DESCRIPTION
        "Cisco Firepower adaptor:EthPortBySizeLargeStats:intervals
        managed object property"
    ::= { cfprAdaptorEthPortBySizeLargeStatsEntry 9 }

cfprAdaptorEthPortBySizeLargeStatsLessThan2048 OBJECT-TYPE
    SYNTAX       Unsigned64
    MAX-ACCESS   read-only
    STATUS       current
    DESCRIPTION
        "Cisco Firepower adaptor:EthPortBySizeLargeStats:lessThan2048
        managed object property"
    ::= { cfprAdaptorEthPortBySizeLargeStatsEntry 10 }

cfprAdaptorEthPortBySizeLargeStatsLessThan2048Delta OBJECT-TYPE
    SYNTAX       Counter64
    MAX-ACCESS   read-only
    STATUS       current
    DESCRIPTION
        "Cisco Firepower adaptor:EthPortBySizeLargeStats:lessThan2048Delta
         managed object property"
    ::= { cfprAdaptorEthPortBySizeLargeStatsEntry 11 }

cfprAdaptorEthPortBySizeLargeStatsLessThan2048DeltaAvg OBJECT-TYPE
    SYNTAX       Unsigned64
    MAX-ACCESS   read-only
    STATUS       current
    DESCRIPTION
        "Cisco Firepower adaptor:EthPortBySizeLargeStats:lessThan2048Delta
        Avg managed object property"
    ::= { cfprAdaptorEthPortBySizeLargeStatsEntry 12 }

cfprAdaptorEthPortBySizeLargeStatsLessThan2048DeltaMax OBJECT-TYPE
    SYNTAX       Unsigned64
    MAX-ACCESS   read-only
    STATUS       current
    DESCRIPTION
        "Cisco Firepower adaptor:EthPortBySizeLargeStats:lessThan2048Delta
        Max managed object property"
    ::= { cfprAdaptorEthPortBySizeLargeStatsEntry 13 }

cfprAdaptorEthPortBySizeLargeStatsLessThan2048DeltaMin OBJECT-TYPE
    SYNTAX       Unsigned64
    MAX-ACCESS   read-only
    STATUS       current
    DESCRIPTION
        "Cisco Firepower adaptor:EthPortBySizeLargeStats:lessThan2048Delta
        Min managed object property"
    ::= { cfprAdaptorEthPortBySizeLargeStatsEntry 14 }

cfprAdaptorEthPortBySizeLargeStatsLessThan4096 OBJECT-TYPE
    SYNTAX       Unsigned64
    MAX-ACCESS   read-only
    STATUS       current
    DESCRIPTION
        "Cisco Firepower adaptor:EthPortBySizeLargeStats:lessThan4096
        managed object property"
    ::= { cfprAdaptorEthPortBySizeLargeStatsEntry 15 }

cfprAdaptorEthPortBySizeLargeStatsLessThan4096Delta OBJECT-TYPE
    SYNTAX       Counter64
    MAX-ACCESS   read-only
    STATUS       current
    DESCRIPTION
        "Cisco Firepower adaptor:EthPortBySizeLargeStats:lessThan4096Delta
         managed object property"
    ::= { cfprAdaptorEthPortBySizeLargeStatsEntry 16 }

cfprAdaptorEthPortBySizeLargeStatsLessThan4096DeltaAvg OBJECT-TYPE
    SYNTAX       Unsigned64
    MAX-ACCESS   read-only
    STATUS       current
    DESCRIPTION
        "Cisco Firepower adaptor:EthPortBySizeLargeStats:lessThan4096Delta
        Avg managed object property"
    ::= { cfprAdaptorEthPortBySizeLargeStatsEntry 17 }

cfprAdaptorEthPortBySizeLargeStatsLessThan4096DeltaMax OBJECT-TYPE
    SYNTAX       Unsigned64
    MAX-ACCESS   read-only
    STATUS       current
    DESCRIPTION
        "Cisco Firepower adaptor:EthPortBySizeLargeStats:lessThan4096Delta
        Max managed object property"
    ::= { cfprAdaptorEthPortBySizeLargeStatsEntry 18 }

cfprAdaptorEthPortBySizeLargeStatsLessThan4096DeltaMin OBJECT-TYPE
    SYNTAX       Unsigned64
    MAX-ACCESS   read-only
    STATUS       current
    DESCRIPTION
        "Cisco Firepower adaptor:EthPortBySizeLargeStats:lessThan4096Delta
        Min managed object property"
    ::= { cfprAdaptorEthPortBySizeLargeStatsEntry 19 }

cfprAdaptorEthPortBySizeLargeStatsLessThan8192 OBJECT-TYPE
    SYNTAX       Unsigned64
    MAX-ACCESS   read-only
    STATUS       current
    DESCRIPTION
        "Cisco Firepower adaptor:EthPortBySizeLargeStats:lessThan8192
        managed object property"
    ::= { cfprAdaptorEthPortBySizeLargeStatsEntry 20 }

cfprAdaptorEthPortBySizeLargeStatsLessThan8192Delta OBJECT-TYPE
    SYNTAX       Counter64
    MAX-ACCESS   read-only
    STATUS       current
    DESCRIPTION
        "Cisco Firepower adaptor:EthPortBySizeLargeStats:lessThan8192Delta
         managed object property"
    ::= { cfprAdaptorEthPortBySizeLargeStatsEntry 21 }

cfprAdaptorEthPortBySizeLargeStatsLessThan8192DeltaAvg OBJECT-TYPE
    SYNTAX       Unsigned64
    MAX-ACCESS   read-only
    STATUS       current
    DESCRIPTION
        "Cisco Firepower adaptor:EthPortBySizeLargeStats:lessThan8192Delta
        Avg managed object property"
    ::= { cfprAdaptorEthPortBySizeLargeStatsEntry 22 }

cfprAdaptorEthPortBySizeLargeStatsLessThan8192DeltaMax OBJECT-TYPE
    SYNTAX       Unsigned64
    MAX-ACCESS   read-only
    STATUS       current
    DESCRIPTION
        "Cisco Firepower adaptor:EthPortBySizeLargeStats:lessThan8192Delta
        Max managed object property"
    ::= { cfprAdaptorEthPortBySizeLargeStatsEntry 23 }

cfprAdaptorEthPortBySizeLargeStatsLessThan8192DeltaMin OBJECT-TYPE
    SYNTAX       Unsigned64
    MAX-ACCESS   read-only
    STATUS       current
    DESCRIPTION
        "Cisco Firepower adaptor:EthPortBySizeLargeStats:lessThan8192Delta
        Min managed object property"
    ::= { cfprAdaptorEthPortBySizeLargeStatsEntry 24 }

cfprAdaptorEthPortBySizeLargeStatsLessThan9216 OBJECT-TYPE
    SYNTAX       Unsigned64
    MAX-ACCESS   read-only
    STATUS       current
    DESCRIPTION
        "Cisco Firepower adaptor:EthPortBySizeLargeStats:lessThan9216
        managed object property"
    ::= { cfprAdaptorEthPortBySizeLargeStatsEntry 25 }

cfprAdaptorEthPortBySizeLargeStatsLessThan9216Delta OBJECT-TYPE
    SYNTAX       Counter64
    MAX-ACCESS   read-only
    STATUS       current
    DESCRIPTION
        "Cisco Firepower adaptor:EthPortBySizeLargeStats:lessThan9216Delta
         managed object property"
    ::= { cfprAdaptorEthPortBySizeLargeStatsEntry 26 }

cfprAdaptorEthPortBySizeLargeStatsLessThan9216DeltaAvg OBJECT-TYPE
    SYNTAX       Unsigned64
    MAX-ACCESS   read-only
    STATUS       current
    DESCRIPTION
        "Cisco Firepower adaptor:EthPortBySizeLargeStats:lessThan9216Delta
        Avg managed object property"
    ::= { cfprAdaptorEthPortBySizeLargeStatsEntry 27 }

cfprAdaptorEthPortBySizeLargeStatsLessThan9216DeltaMax OBJECT-TYPE
    SYNTAX       Unsigned64
    MAX-ACCESS   read-only
    STATUS       current
    DESCRIPTION
        "Cisco Firepower adaptor:EthPortBySizeLargeStats:lessThan9216Delta
        Max managed object property"
    ::= { cfprAdaptorEthPortBySizeLargeStatsEntry 28 }

cfprAdaptorEthPortBySizeLargeStatsLessThan9216DeltaMin OBJECT-TYPE
    SYNTAX       Unsigned64
    MAX-ACCESS   read-only
    STATUS       current
    DESCRIPTION
        "Cisco Firepower adaptor:EthPortBySizeLargeStats:lessThan9216Delta
        Min managed object property"
    ::= { cfprAdaptorEthPortBySizeLargeStatsEntry 29 }

cfprAdaptorEthPortBySizeLargeStatsLessThanOrEqualTo1518 OBJECT-TYPE
    SYNTAX       Unsigned64
    MAX-ACCESS   read-only
    STATUS       current
    DESCRIPTION
        "Cisco Firepower adaptor:EthPortBySizeLargeStats:lessThanOrEqualTo
        1518 managed object property"
    ::= { cfprAdaptorEthPortBySizeLargeStatsEntry 30 }

cfprAdaptorEthPortBySizeLargeStatsLessThanOrEqualTo1518Delta OBJECT-TYPE
    SYNTAX       Counter64
    MAX-ACCESS   read-only
    STATUS       current
    DESCRIPTION
        "Cisco Firepower adaptor:EthPortBySizeLargeStats:lessThanOrEqualTo
        1518Delta managed object property"
    ::= { cfprAdaptorEthPortBySizeLargeStatsEntry 31 }

cfprAdaptorEthPortBySizeLargeStatsLessThanOrEqualTo1518DeltaAvg OBJECT-TYPE
    SYNTAX       Unsigned64
    MAX-ACCESS   read-only
    STATUS       current
    DESCRIPTION
        "Cisco Firepower adaptor:EthPortBySizeLargeStats:lessThanOrEqualTo
        1518DeltaAvg managed object property"
    ::= { cfprAdaptorEthPortBySizeLargeStatsEntry 32 }

cfprAdaptorEthPortBySizeLargeStatsLessThanOrEqualTo1518DeltaMax OBJECT-TYPE
    SYNTAX       Unsigned64
    MAX-ACCESS   read-only
    STATUS       current
    DESCRIPTION
        "Cisco Firepower adaptor:EthPortBySizeLargeStats:lessThanOrEqualTo
        1518DeltaMax managed object property"
    ::= { cfprAdaptorEthPortBySizeLargeStatsEntry 33 }

cfprAdaptorEthPortBySizeLargeStatsLessThanOrEqualTo1518DeltaMin OBJECT-TYPE
    SYNTAX       Unsigned64
    MAX-ACCESS   read-only
    STATUS       current
    DESCRIPTION
        "Cisco Firepower adaptor:EthPortBySizeLargeStats:lessThanOrEqualTo
        1518DeltaMin managed object property"
    ::= { cfprAdaptorEthPortBySizeLargeStatsEntry 34 }

cfprAdaptorEthPortBySizeLargeStatsNoBreakdownGreaterThan1518 OBJECT-TYPE
    SYNTAX       Unsigned64
    MAX-ACCESS   read-only
    STATUS       current
    DESCRIPTION
        "Cisco Firepower adaptor:EthPortBySizeLargeStats:noBreakdownGreate
        rThan1518 managed object property"
    ::= { cfprAdaptorEthPortBySizeLargeStatsEntry 35 }

cfprAdaptorEthPortBySizeLargeStatsNoBreakdownGreaterThan1518Delta OBJECT-TYPE
    SYNTAX       Counter64
    MAX-ACCESS   read-only
    STATUS       current
    DESCRIPTION
        "Cisco Firepower adaptor:EthPortBySizeLargeStats:noBreakdownGreate
        rThan1518Delta managed object property"
    ::= { cfprAdaptorEthPortBySizeLargeStatsEntry 36 }

cfprAdaptorEthPortBySizeLargeStatsNoBreakdownGreaterThan1518DeltaAvg OBJECT-TYPE
    SYNTAX       Unsigned64
    MAX-ACCESS   read-only
    STATUS       current
    DESCRIPTION
        "Cisco Firepower adaptor:EthPortBySizeLargeStats:noBreakdownGreate
        rThan1518DeltaAvg managed object property"
    ::= { cfprAdaptorEthPortBySizeLargeStatsEntry 37 }

cfprAdaptorEthPortBySizeLargeStatsNoBreakdownGreaterThan1518DeltaMax OBJECT-TYPE
    SYNTAX       Unsigned64
    MAX-ACCESS   read-only
    STATUS       current
    DESCRIPTION
        "Cisco Firepower adaptor:EthPortBySizeLargeStats:noBreakdownGreate
        rThan1518DeltaMax managed object property"
    ::= { cfprAdaptorEthPortBySizeLargeStatsEntry 38 }

cfprAdaptorEthPortBySizeLargeStatsNoBreakdownGreaterThan1518DeltaMin OBJECT-TYPE
    SYNTAX       Unsigned64
    MAX-ACCESS   read-only
    STATUS       current
    DESCRIPTION
        "Cisco Firepower adaptor:EthPortBySizeLargeStats:noBreakdownGreate
        rThan1518DeltaMin managed object property"
    ::= { cfprAdaptorEthPortBySizeLargeStatsEntry 39 }

cfprAdaptorEthPortBySizeLargeStatsSuspect OBJECT-TYPE
    SYNTAX       TruthValue
    MAX-ACCESS   read-only
    STATUS       current
    DESCRIPTION
        "Cisco Firepower adaptor:EthPortBySizeLargeStats:suspect
        managed object property"
    ::= { cfprAdaptorEthPortBySizeLargeStatsEntry 40 }

cfprAdaptorEthPortBySizeLargeStatsThresholded OBJECT-TYPE
    SYNTAX       CfprAdaptorEthPortBySizeLargeStatsThresholded
    MAX-ACCESS   read-only
    STATUS       current
    DESCRIPTION
        "Cisco Firepower adaptor:EthPortBySizeLargeStats:thresholded
        managed object property"
    ::= { cfprAdaptorEthPortBySizeLargeStatsEntry 41 }

cfprAdaptorEthPortBySizeLargeStatsTimeCollected OBJECT-TYPE
    SYNTAX       DateAndTime
    MAX-ACCESS   read-only
    STATUS       current
    DESCRIPTION
        "Cisco Firepower adaptor:EthPortBySizeLargeStats:timeCollected
        managed object property"
    ::= { cfprAdaptorEthPortBySizeLargeStatsEntry 42 }

cfprAdaptorEthPortBySizeLargeStatsTrafficDirection OBJECT-TYPE
    SYNTAX       CfprAdaptorAdapterStatsTrafficDir
    MAX-ACCESS   read-only
    STATUS       current
    DESCRIPTION
        "Cisco Firepower adaptor:EthPortBySizeLargeStats:trafficDirection
        managed object property"
    ::= { cfprAdaptorEthPortBySizeLargeStatsEntry 43 }

cfprAdaptorEthPortBySizeLargeStatsUpdate OBJECT-TYPE
    SYNTAX       Gauge32
    MAX-ACCESS   read-only
    STATUS       current
    DESCRIPTION
        "Cisco Firepower adaptor:EthPortBySizeLargeStats:update
        managed object property"
    ::= { cfprAdaptorEthPortBySizeLargeStatsEntry 44 }

cfprAdaptorEthPortBySizeLargeStatsHistTable OBJECT-TYPE
    SYNTAX           SEQUENCE OF CfprAdaptorEthPortBySizeLargeStatsHistEntry
    MAX-ACCESS       not-accessible
    STATUS           current
    DESCRIPTION
        "Cisco Firepower adaptor:EthPortBySizeLargeStatsHist
        managed object table"
    ::= { cfprAdaptorObjects 11 }

cfprAdaptorEthPortBySizeLargeStatsHistEntry OBJECT-TYPE
    SYNTAX           CfprAdaptorEthPortBySizeLargeStatsHistEntry
    MAX-ACCESS       not-accessible
    STATUS           current
    DESCRIPTION
        "Entry for the cfprAdaptorEthPortBySizeLargeStatsHistTable table."
    INDEX { cfprAdaptorEthPortBySizeLargeStatsHistInstanceId }
    ::= { cfprAdaptorEthPortBySizeLargeStatsHistTable 1 }

CfprAdaptorEthPortBySizeLargeStatsHistEntry ::= SEQUENCE {
    cfprAdaptorEthPortBySizeLargeStatsHistInstanceId                 CfprManagedObjectId,
    cfprAdaptorEthPortBySizeLargeStatsHistDn                         CfprManagedObjectDn,
    cfprAdaptorEthPortBySizeLargeStatsHistRn                         SnmpAdminString,
    cfprAdaptorEthPortBySizeLargeStatsHistGreaterThanOrEqualTo9216   Unsigned64,
    cfprAdaptorEthPortBySizeLargeStatsHistGreaterThanOrEqualTo9216Delta Unsigned64,
    cfprAdaptorEthPortBySizeLargeStatsHistGreaterThanOrEqualTo9216DeltaAvg Unsigned64,
    cfprAdaptorEthPortBySizeLargeStatsHistGreaterThanOrEqualTo9216DeltaMax Unsigned64,
    cfprAdaptorEthPortBySizeLargeStatsHistGreaterThanOrEqualTo9216DeltaMin Unsigned64,
    cfprAdaptorEthPortBySizeLargeStatsHistId                         Unsigned64,
    cfprAdaptorEthPortBySizeLargeStatsHistLessThan2048               Unsigned64,
    cfprAdaptorEthPortBySizeLargeStatsHistLessThan2048Delta          Unsigned64,
    cfprAdaptorEthPortBySizeLargeStatsHistLessThan2048DeltaAvg       Unsigned64,
    cfprAdaptorEthPortBySizeLargeStatsHistLessThan2048DeltaMax       Unsigned64,
    cfprAdaptorEthPortBySizeLargeStatsHistLessThan2048DeltaMin       Unsigned64,
    cfprAdaptorEthPortBySizeLargeStatsHistLessThan4096               Unsigned64,
    cfprAdaptorEthPortBySizeLargeStatsHistLessThan4096Delta          Unsigned64,
    cfprAdaptorEthPortBySizeLargeStatsHistLessThan4096DeltaAvg       Unsigned64,
    cfprAdaptorEthPortBySizeLargeStatsHistLessThan4096DeltaMax       Unsigned64,
    cfprAdaptorEthPortBySizeLargeStatsHistLessThan4096DeltaMin       Unsigned64,
    cfprAdaptorEthPortBySizeLargeStatsHistLessThan8192               Unsigned64,
    cfprAdaptorEthPortBySizeLargeStatsHistLessThan8192Delta          Unsigned64,
    cfprAdaptorEthPortBySizeLargeStatsHistLessThan8192DeltaAvg       Unsigned64,
    cfprAdaptorEthPortBySizeLargeStatsHistLessThan8192DeltaMax       Unsigned64,
    cfprAdaptorEthPortBySizeLargeStatsHistLessThan8192DeltaMin       Unsigned64,
    cfprAdaptorEthPortBySizeLargeStatsHistLessThan9216               Unsigned64,
    cfprAdaptorEthPortBySizeLargeStatsHistLessThan9216Delta          Unsigned64,
    cfprAdaptorEthPortBySizeLargeStatsHistLessThan9216DeltaAvg       Unsigned64,
    cfprAdaptorEthPortBySizeLargeStatsHistLessThan9216DeltaMax       Unsigned64,
    cfprAdaptorEthPortBySizeLargeStatsHistLessThan9216DeltaMin       Unsigned64,
    cfprAdaptorEthPortBySizeLargeStatsHistLessThanOrEqualTo1518      Unsigned64,
    cfprAdaptorEthPortBySizeLargeStatsHistLessThanOrEqualTo1518Delta Unsigned64,
    cfprAdaptorEthPortBySizeLargeStatsHistLessThanOrEqualTo1518DeltaAvg Unsigned64,
    cfprAdaptorEthPortBySizeLargeStatsHistLessThanOrEqualTo1518DeltaMax Unsigned64,
    cfprAdaptorEthPortBySizeLargeStatsHistLessThanOrEqualTo1518DeltaMin Unsigned64,
    cfprAdaptorEthPortBySizeLargeStatsHistMostRecent                 TruthValue,
    cfprAdaptorEthPortBySizeLargeStatsHistNoBreakdownGreaterThan1518 Unsigned64,
    cfprAdaptorEthPortBySizeLargeStatsHistNoBreakdownGreaterThan1518Delta Unsigned64,
    cfprAdaptorEthPortBySizeLargeStatsHistNoBreakdownGreaterThan1518DeltaAvg Unsigned64,
    cfprAdaptorEthPortBySizeLargeStatsHistNoBreakdownGreaterThan1518DeltaMax Unsigned64,
    cfprAdaptorEthPortBySizeLargeStatsHistNoBreakdownGreaterThan1518DeltaMin Unsigned64,
    cfprAdaptorEthPortBySizeLargeStatsHistSuspect                    TruthValue,
    cfprAdaptorEthPortBySizeLargeStatsHistThresholded                CfprAdaptorEthPortBySizeLargeStatsHistThresholded,
    cfprAdaptorEthPortBySizeLargeStatsHistTimeCollected              DateAndTime
}

cfprAdaptorEthPortBySizeLargeStatsHistInstanceId OBJECT-TYPE
    SYNTAX       CfprManagedObjectId
    MAX-ACCESS   not-accessible
    STATUS       current
    DESCRIPTION
        "Instance identifier of the managed object."
    ::= { cfprAdaptorEthPortBySizeLargeStatsHistEntry 1 }

cfprAdaptorEthPortBySizeLargeStatsHistDn OBJECT-TYPE
    SYNTAX       CfprManagedObjectDn
    MAX-ACCESS   read-only
    STATUS       current
    DESCRIPTION
        "Cisco Firepower adaptor:EthPortBySizeLargeStatsHist:dn
        managed object property"
    ::= { cfprAdaptorEthPortBySizeLargeStatsHistEntry 2 }

cfprAdaptorEthPortBySizeLargeStatsHistRn OBJECT-TYPE
    SYNTAX       SnmpAdminString
    MAX-ACCESS   read-only
    STATUS       current
    DESCRIPTION
        "Cisco Firepower adaptor:EthPortBySizeLargeStatsHist:rn
        managed object property"
    ::= { cfprAdaptorEthPortBySizeLargeStatsHistEntry 3 }

cfprAdaptorEthPortBySizeLargeStatsHistGreaterThanOrEqualTo9216 OBJECT-TYPE
    SYNTAX       Unsigned64
    MAX-ACCESS   read-only
    STATUS       current
    DESCRIPTION
        "Cisco Firepower adaptor:EthPortBySizeLargeStatsHist:greaterThanOr
        EqualTo9216 managed object property"
    ::= { cfprAdaptorEthPortBySizeLargeStatsHistEntry 4 }

cfprAdaptorEthPortBySizeLargeStatsHistGreaterThanOrEqualTo9216Delta OBJECT-TYPE
    SYNTAX       Unsigned64
    MAX-ACCESS   read-only
    STATUS       current
    DESCRIPTION
        "Cisco Firepower adaptor:EthPortBySizeLargeStatsHist:greaterThanOr
        EqualTo9216Delta managed object property"
    ::= { cfprAdaptorEthPortBySizeLargeStatsHistEntry 5 }

cfprAdaptorEthPortBySizeLargeStatsHistGreaterThanOrEqualTo9216DeltaAvg OBJECT-TYPE
    SYNTAX       Unsigned64
    MAX-ACCESS   read-only
    STATUS       current
    DESCRIPTION
        "Cisco Firepower adaptor:EthPortBySizeLargeStatsHist:greaterThanOr
        EqualTo9216DeltaAvg managed object property"
    ::= { cfprAdaptorEthPortBySizeLargeStatsHistEntry 6 }

cfprAdaptorEthPortBySizeLargeStatsHistGreaterThanOrEqualTo9216DeltaMax OBJECT-TYPE
    SYNTAX       Unsigned64
    MAX-ACCESS   read-only
    STATUS       current
    DESCRIPTION
        "Cisco Firepower adaptor:EthPortBySizeLargeStatsHist:greaterThanOr
        EqualTo9216DeltaMax managed object property"
    ::= { cfprAdaptorEthPortBySizeLargeStatsHistEntry 7 }

cfprAdaptorEthPortBySizeLargeStatsHistGreaterThanOrEqualTo9216DeltaMin OBJECT-TYPE
    SYNTAX       Unsigned64
    MAX-ACCESS   read-only
    STATUS       current
    DESCRIPTION
        "Cisco Firepower adaptor:EthPortBySizeLargeStatsHist:greaterThanOr
        EqualTo9216DeltaMin managed object property"
    ::= { cfprAdaptorEthPortBySizeLargeStatsHistEntry 8 }

cfprAdaptorEthPortBySizeLargeStatsHistId OBJECT-TYPE
    SYNTAX       Unsigned64
    MAX-ACCESS   read-only
    STATUS       current
    DESCRIPTION
        "Cisco Firepower adaptor:EthPortBySizeLargeStatsHist:id
        managed object property"
    ::= { cfprAdaptorEthPortBySizeLargeStatsHistEntry 9 }

cfprAdaptorEthPortBySizeLargeStatsHistLessThan2048 OBJECT-TYPE
    SYNTAX       Unsigned64
    MAX-ACCESS   read-only
    STATUS       current
    DESCRIPTION
        "Cisco Firepower adaptor:EthPortBySizeLargeStatsHist:lessThan2048
        managed object property"
    ::= { cfprAdaptorEthPortBySizeLargeStatsHistEntry 10 }

cfprAdaptorEthPortBySizeLargeStatsHistLessThan2048Delta OBJECT-TYPE
    SYNTAX       Unsigned64
    MAX-ACCESS   read-only
    STATUS       current
    DESCRIPTION
        "Cisco Firepower adaptor:EthPortBySizeLargeStatsHist:lessThan2048D
        elta managed object property"
    ::= { cfprAdaptorEthPortBySizeLargeStatsHistEntry 11 }

cfprAdaptorEthPortBySizeLargeStatsHistLessThan2048DeltaAvg OBJECT-TYPE
    SYNTAX       Unsigned64
    MAX-ACCESS   read-only
    STATUS       current
    DESCRIPTION
        "Cisco Firepower adaptor:EthPortBySizeLargeStatsHist:lessThan2048D
        eltaAvg managed object property"
    ::= { cfprAdaptorEthPortBySizeLargeStatsHistEntry 12 }

cfprAdaptorEthPortBySizeLargeStatsHistLessThan2048DeltaMax OBJECT-TYPE
    SYNTAX       Unsigned64
    MAX-ACCESS   read-only
    STATUS       current
    DESCRIPTION
        "Cisco Firepower adaptor:EthPortBySizeLargeStatsHist:lessThan2048D
        eltaMax managed object property"
    ::= { cfprAdaptorEthPortBySizeLargeStatsHistEntry 13 }

cfprAdaptorEthPortBySizeLargeStatsHistLessThan2048DeltaMin OBJECT-TYPE
    SYNTAX       Unsigned64
    MAX-ACCESS   read-only
    STATUS       current
    DESCRIPTION
        "Cisco Firepower adaptor:EthPortBySizeLargeStatsHist:lessThan2048D
        eltaMin managed object property"
    ::= { cfprAdaptorEthPortBySizeLargeStatsHistEntry 14 }

cfprAdaptorEthPortBySizeLargeStatsHistLessThan4096 OBJECT-TYPE
    SYNTAX       Unsigned64
    MAX-ACCESS   read-only
    STATUS       current
    DESCRIPTION
        "Cisco Firepower adaptor:EthPortBySizeLargeStatsHist:lessThan4096
        managed object property"
    ::= { cfprAdaptorEthPortBySizeLargeStatsHistEntry 15 }

cfprAdaptorEthPortBySizeLargeStatsHistLessThan4096Delta OBJECT-TYPE
    SYNTAX       Unsigned64
    MAX-ACCESS   read-only
    STATUS       current
    DESCRIPTION
        "Cisco Firepower adaptor:EthPortBySizeLargeStatsHist:lessThan4096D
        elta managed object property"
    ::= { cfprAdaptorEthPortBySizeLargeStatsHistEntry 16 }

cfprAdaptorEthPortBySizeLargeStatsHistLessThan4096DeltaAvg OBJECT-TYPE
    SYNTAX       Unsigned64
    MAX-ACCESS   read-only
    STATUS       current
    DESCRIPTION
        "Cisco Firepower adaptor:EthPortBySizeLargeStatsHist:lessThan4096D
        eltaAvg managed object property"
    ::= { cfprAdaptorEthPortBySizeLargeStatsHistEntry 17 }

cfprAdaptorEthPortBySizeLargeStatsHistLessThan4096DeltaMax OBJECT-TYPE
    SYNTAX       Unsigned64
    MAX-ACCESS   read-only
    STATUS       current
    DESCRIPTION
        "Cisco Firepower adaptor:EthPortBySizeLargeStatsHist:lessThan4096D
        eltaMax managed object property"
    ::= { cfprAdaptorEthPortBySizeLargeStatsHistEntry 18 }

cfprAdaptorEthPortBySizeLargeStatsHistLessThan4096DeltaMin OBJECT-TYPE
    SYNTAX       Unsigned64
    MAX-ACCESS   read-only
    STATUS       current
    DESCRIPTION
        "Cisco Firepower adaptor:EthPortBySizeLargeStatsHist:lessThan4096D
        eltaMin managed object property"
    ::= { cfprAdaptorEthPortBySizeLargeStatsHistEntry 19 }

cfprAdaptorEthPortBySizeLargeStatsHistLessThan8192 OBJECT-TYPE
    SYNTAX       Unsigned64
    MAX-ACCESS   read-only
    STATUS       current
    DESCRIPTION
        "Cisco Firepower adaptor:EthPortBySizeLargeStatsHist:lessThan8192
        managed object property"
    ::= { cfprAdaptorEthPortBySizeLargeStatsHistEntry 20 }

cfprAdaptorEthPortBySizeLargeStatsHistLessThan8192Delta OBJECT-TYPE
    SYNTAX       Unsigned64
    MAX-ACCESS   read-only
    STATUS       current
    DESCRIPTION
        "Cisco Firepower adaptor:EthPortBySizeLargeStatsHist:lessThan8192D
        elta managed object property"
    ::= { cfprAdaptorEthPortBySizeLargeStatsHistEntry 21 }

cfprAdaptorEthPortBySizeLargeStatsHistLessThan8192DeltaAvg OBJECT-TYPE
    SYNTAX       Unsigned64
    MAX-ACCESS   read-only
    STATUS       current
    DESCRIPTION
        "Cisco Firepower adaptor:EthPortBySizeLargeStatsHist:lessThan8192D
        eltaAvg managed object property"
    ::= { cfprAdaptorEthPortBySizeLargeStatsHistEntry 22 }

cfprAdaptorEthPortBySizeLargeStatsHistLessThan8192DeltaMax OBJECT-TYPE
    SYNTAX       Unsigned64
    MAX-ACCESS   read-only
    STATUS       current
    DESCRIPTION
        "Cisco Firepower adaptor:EthPortBySizeLargeStatsHist:lessThan8192D
        eltaMax managed object property"
    ::= { cfprAdaptorEthPortBySizeLargeStatsHistEntry 23 }

cfprAdaptorEthPortBySizeLargeStatsHistLessThan8192DeltaMin OBJECT-TYPE
    SYNTAX       Unsigned64
    MAX-ACCESS   read-only
    STATUS       current
    DESCRIPTION
        "Cisco Firepower adaptor:EthPortBySizeLargeStatsHist:lessThan8192D
        eltaMin managed object property"
    ::= { cfprAdaptorEthPortBySizeLargeStatsHistEntry 24 }

cfprAdaptorEthPortBySizeLargeStatsHistLessThan9216 OBJECT-TYPE
    SYNTAX       Unsigned64
    MAX-ACCESS   read-only
    STATUS       current
    DESCRIPTION
        "Cisco Firepower adaptor:EthPortBySizeLargeStatsHist:lessThan9216
        managed object property"
    ::= { cfprAdaptorEthPortBySizeLargeStatsHistEntry 25 }

cfprAdaptorEthPortBySizeLargeStatsHistLessThan9216Delta OBJECT-TYPE
    SYNTAX       Unsigned64
    MAX-ACCESS   read-only
    STATUS       current
    DESCRIPTION
        "Cisco Firepower adaptor:EthPortBySizeLargeStatsHist:lessThan9216D
        elta managed object property"
    ::= { cfprAdaptorEthPortBySizeLargeStatsHistEntry 26 }

cfprAdaptorEthPortBySizeLargeStatsHistLessThan9216DeltaAvg OBJECT-TYPE
    SYNTAX       Unsigned64
    MAX-ACCESS   read-only
    STATUS       current
    DESCRIPTION
        "Cisco Firepower adaptor:EthPortBySizeLargeStatsHist:lessThan9216D
        eltaAvg managed object property"
    ::= { cfprAdaptorEthPortBySizeLargeStatsHistEntry 27 }

cfprAdaptorEthPortBySizeLargeStatsHistLessThan9216DeltaMax OBJECT-TYPE
    SYNTAX       Unsigned64
    MAX-ACCESS   read-only
    STATUS       current
    DESCRIPTION
        "Cisco Firepower adaptor:EthPortBySizeLargeStatsHist:lessThan9216D
        eltaMax managed object property"
    ::= { cfprAdaptorEthPortBySizeLargeStatsHistEntry 28 }

cfprAdaptorEthPortBySizeLargeStatsHistLessThan9216DeltaMin OBJECT-TYPE
    SYNTAX       Unsigned64
    MAX-ACCESS   read-only
    STATUS       current
    DESCRIPTION
        "Cisco Firepower adaptor:EthPortBySizeLargeStatsHist:lessThan9216D
        eltaMin managed object property"
    ::= { cfprAdaptorEthPortBySizeLargeStatsHistEntry 29 }

cfprAdaptorEthPortBySizeLargeStatsHistLessThanOrEqualTo1518 OBJECT-TYPE
    SYNTAX       Unsigned64
    MAX-ACCESS   read-only
    STATUS       current
    DESCRIPTION
        "Cisco Firepower adaptor:EthPortBySizeLargeStatsHist:lessThanOrEqu
        alTo1518 managed object property"
    ::= { cfprAdaptorEthPortBySizeLargeStatsHistEntry 30 }

cfprAdaptorEthPortBySizeLargeStatsHistLessThanOrEqualTo1518Delta OBJECT-TYPE
    SYNTAX       Unsigned64
    MAX-ACCESS   read-only
    STATUS       current
    DESCRIPTION
        "Cisco Firepower adaptor:EthPortBySizeLargeStatsHist:lessThanOrEqu
        alTo1518Delta managed object property"
    ::= { cfprAdaptorEthPortBySizeLargeStatsHistEntry 31 }

cfprAdaptorEthPortBySizeLargeStatsHistLessThanOrEqualTo1518DeltaAvg OBJECT-TYPE
    SYNTAX       Unsigned64
    MAX-ACCESS   read-only
    STATUS       current
    DESCRIPTION
        "Cisco Firepower adaptor:EthPortBySizeLargeStatsHist:lessThanOrEqu
        alTo1518DeltaAvg managed object property"
    ::= { cfprAdaptorEthPortBySizeLargeStatsHistEntry 32 }

cfprAdaptorEthPortBySizeLargeStatsHistLessThanOrEqualTo1518DeltaMax OBJECT-TYPE
    SYNTAX       Unsigned64
    MAX-ACCESS   read-only
    STATUS       current
    DESCRIPTION
        "Cisco Firepower adaptor:EthPortBySizeLargeStatsHist:lessThanOrEqu
        alTo1518DeltaMax managed object property"
    ::= { cfprAdaptorEthPortBySizeLargeStatsHistEntry 33 }

cfprAdaptorEthPortBySizeLargeStatsHistLessThanOrEqualTo1518DeltaMin OBJECT-TYPE
    SYNTAX       Unsigned64
    MAX-ACCESS   read-only
    STATUS       current
    DESCRIPTION
        "Cisco Firepower adaptor:EthPortBySizeLargeStatsHist:lessThanOrEqu
        alTo1518DeltaMin managed object property"
    ::= { cfprAdaptorEthPortBySizeLargeStatsHistEntry 34 }

cfprAdaptorEthPortBySizeLargeStatsHistMostRecent OBJECT-TYPE
    SYNTAX       TruthValue
    MAX-ACCESS   read-only
    STATUS       current
    DESCRIPTION
        "Cisco Firepower adaptor:EthPortBySizeLargeStatsHist:mostRecent
        managed object property"
    ::= { cfprAdaptorEthPortBySizeLargeStatsHistEntry 35 }

cfprAdaptorEthPortBySizeLargeStatsHistNoBreakdownGreaterThan1518 OBJECT-TYPE
    SYNTAX       Unsigned64
    MAX-ACCESS   read-only
    STATUS       current
    DESCRIPTION
        "Cisco Firepower adaptor:EthPortBySizeLargeStatsHist:noBreakdownGr
        eaterThan1518 managed object property"
    ::= { cfprAdaptorEthPortBySizeLargeStatsHistEntry 36 }

cfprAdaptorEthPortBySizeLargeStatsHistNoBreakdownGreaterThan1518Delta OBJECT-TYPE
    SYNTAX       Unsigned64
    MAX-ACCESS   read-only
    STATUS       current
    DESCRIPTION
        "Cisco Firepower adaptor:EthPortBySizeLargeStatsHist:noBreakdownGr
        eaterThan1518Delta managed object property"
    ::= { cfprAdaptorEthPortBySizeLargeStatsHistEntry 37 }

cfprAdaptorEthPortBySizeLargeStatsHistNoBreakdownGreaterThan1518DeltaAvg OBJECT-TYPE
    SYNTAX       Unsigned64
    MAX-ACCESS   read-only
    STATUS       current
    DESCRIPTION
        "Cisco Firepower adaptor:EthPortBySizeLargeStatsHist:noBreakdownGr
        eaterThan1518DeltaAvg managed object property"
    ::= { cfprAdaptorEthPortBySizeLargeStatsHistEntry 38 }

cfprAdaptorEthPortBySizeLargeStatsHistNoBreakdownGreaterThan1518DeltaMax OBJECT-TYPE
    SYNTAX       Unsigned64
    MAX-ACCESS   read-only
    STATUS       current
    DESCRIPTION
        "Cisco Firepower adaptor:EthPortBySizeLargeStatsHist:noBreakdownGr
        eaterThan1518DeltaMax managed object property"
    ::= { cfprAdaptorEthPortBySizeLargeStatsHistEntry 39 }

cfprAdaptorEthPortBySizeLargeStatsHistNoBreakdownGreaterThan1518DeltaMin OBJECT-TYPE
    SYNTAX       Unsigned64
    MAX-ACCESS   read-only
    STATUS       current
    DESCRIPTION
        "Cisco Firepower adaptor:EthPortBySizeLargeStatsHist:noBreakdownGr
        eaterThan1518DeltaMin managed object property"
    ::= { cfprAdaptorEthPortBySizeLargeStatsHistEntry 40 }

cfprAdaptorEthPortBySizeLargeStatsHistSuspect OBJECT-TYPE
    SYNTAX       TruthValue
    MAX-ACCESS   read-only
    STATUS       current
    DESCRIPTION
        "Cisco Firepower adaptor:EthPortBySizeLargeStatsHist:suspect
        managed object property"
    ::= { cfprAdaptorEthPortBySizeLargeStatsHistEntry 41 }

cfprAdaptorEthPortBySizeLargeStatsHistThresholded OBJECT-TYPE
    SYNTAX       CfprAdaptorEthPortBySizeLargeStatsHistThresholded
    MAX-ACCESS   read-only
    STATUS       current
    DESCRIPTION
        "Cisco Firepower adaptor:EthPortBySizeLargeStatsHist:thresholded
        managed object property"
    ::= { cfprAdaptorEthPortBySizeLargeStatsHistEntry 42 }

cfprAdaptorEthPortBySizeLargeStatsHistTimeCollected OBJECT-TYPE
    SYNTAX       DateAndTime
    MAX-ACCESS   read-only
    STATUS       current
    DESCRIPTION
        "Cisco Firepower adaptor:EthPortBySizeLargeStatsHist:timeCollected
         managed object property"
    ::= { cfprAdaptorEthPortBySizeLargeStatsHistEntry 43 }

cfprAdaptorEthPortBySizeSmallStatsTable OBJECT-TYPE
    SYNTAX           SEQUENCE OF CfprAdaptorEthPortBySizeSmallStatsEntry
    MAX-ACCESS       not-accessible
    STATUS           current
    DESCRIPTION
        "Cisco Firepower adaptor:EthPortBySizeSmallStats
        managed object table"
    ::= { cfprAdaptorObjects 12 }

cfprAdaptorEthPortBySizeSmallStatsEntry OBJECT-TYPE
    SYNTAX           CfprAdaptorEthPortBySizeSmallStatsEntry
    MAX-ACCESS       not-accessible
    STATUS           current
    DESCRIPTION
        "Entry for the cfprAdaptorEthPortBySizeSmallStatsTable table."
    INDEX { cfprAdaptorEthPortBySizeSmallStatsInstanceId }
    ::= { cfprAdaptorEthPortBySizeSmallStatsTable 1 }

CfprAdaptorEthPortBySizeSmallStatsEntry ::= SEQUENCE {
    cfprAdaptorEthPortBySizeSmallStatsInstanceId                     CfprManagedObjectId,
    cfprAdaptorEthPortBySizeSmallStatsDn                             CfprManagedObjectDn,
    cfprAdaptorEthPortBySizeSmallStatsRn                             SnmpAdminString,
    cfprAdaptorEthPortBySizeSmallStatsEquals64                       Unsigned64,
    cfprAdaptorEthPortBySizeSmallStatsEquals64Delta                  Counter64,
    cfprAdaptorEthPortBySizeSmallStatsEquals64DeltaAvg               Unsigned64,
    cfprAdaptorEthPortBySizeSmallStatsEquals64DeltaMax               Unsigned64,
    cfprAdaptorEthPortBySizeSmallStatsEquals64DeltaMin               Unsigned64,
    cfprAdaptorEthPortBySizeSmallStatsIntervals                      Gauge32,
    cfprAdaptorEthPortBySizeSmallStatsLessThan1024                   Unsigned64,
    cfprAdaptorEthPortBySizeSmallStatsLessThan1024Delta              Counter64,
    cfprAdaptorEthPortBySizeSmallStatsLessThan1024DeltaAvg           Unsigned64,
    cfprAdaptorEthPortBySizeSmallStatsLessThan1024DeltaMax           Unsigned64,
    cfprAdaptorEthPortBySizeSmallStatsLessThan1024DeltaMin           Unsigned64,
    cfprAdaptorEthPortBySizeSmallStatsLessThan128                    Unsigned64,
    cfprAdaptorEthPortBySizeSmallStatsLessThan128Delta               Counter64,
    cfprAdaptorEthPortBySizeSmallStatsLessThan128DeltaAvg            Unsigned64,
    cfprAdaptorEthPortBySizeSmallStatsLessThan128DeltaMax            Unsigned64,
    cfprAdaptorEthPortBySizeSmallStatsLessThan128DeltaMin            Unsigned64,
    cfprAdaptorEthPortBySizeSmallStatsLessThan256                    Unsigned64,
    cfprAdaptorEthPortBySizeSmallStatsLessThan256Delta               Counter64,
    cfprAdaptorEthPortBySizeSmallStatsLessThan256DeltaAvg            Unsigned64,
    cfprAdaptorEthPortBySizeSmallStatsLessThan256DeltaMax            Unsigned64,
    cfprAdaptorEthPortBySizeSmallStatsLessThan256DeltaMin            Unsigned64,
    cfprAdaptorEthPortBySizeSmallStatsLessThan512                    Unsigned64,
    cfprAdaptorEthPortBySizeSmallStatsLessThan512Delta               Counter64,
    cfprAdaptorEthPortBySizeSmallStatsLessThan512DeltaAvg            Unsigned64,
    cfprAdaptorEthPortBySizeSmallStatsLessThan512DeltaMax            Unsigned64,
    cfprAdaptorEthPortBySizeSmallStatsLessThan512DeltaMin            Unsigned64,
    cfprAdaptorEthPortBySizeSmallStatsLessThan64                     Unsigned64,
    cfprAdaptorEthPortBySizeSmallStatsLessThan64Delta                Counter64,
    cfprAdaptorEthPortBySizeSmallStatsLessThan64DeltaAvg             Unsigned64,
    cfprAdaptorEthPortBySizeSmallStatsLessThan64DeltaMax             Unsigned64,
    cfprAdaptorEthPortBySizeSmallStatsLessThan64DeltaMin             Unsigned64,
    cfprAdaptorEthPortBySizeSmallStatsSuspect                        TruthValue,
    cfprAdaptorEthPortBySizeSmallStatsThresholded                    CfprAdaptorEthPortBySizeSmallStatsThresholded,
    cfprAdaptorEthPortBySizeSmallStatsTimeCollected                  DateAndTime,
    cfprAdaptorEthPortBySizeSmallStatsTrafficDirection               CfprAdaptorAdapterStatsTrafficDir,
    cfprAdaptorEthPortBySizeSmallStatsUpdate                         Gauge32
}

cfprAdaptorEthPortBySizeSmallStatsInstanceId OBJECT-TYPE
    SYNTAX       CfprManagedObjectId
    MAX-ACCESS   not-accessible
    STATUS       current
    DESCRIPTION
        "Instance identifier of the managed object."
    ::= { cfprAdaptorEthPortBySizeSmallStatsEntry 1 }

cfprAdaptorEthPortBySizeSmallStatsDn OBJECT-TYPE
    SYNTAX       CfprManagedObjectDn
    MAX-ACCESS   read-only
    STATUS       current
    DESCRIPTION
        "Cisco Firepower adaptor:EthPortBySizeSmallStats:dn
        managed object property"
    ::= { cfprAdaptorEthPortBySizeSmallStatsEntry 2 }

cfprAdaptorEthPortBySizeSmallStatsRn OBJECT-TYPE
    SYNTAX       SnmpAdminString
    MAX-ACCESS   read-only
    STATUS       current
    DESCRIPTION
        "Cisco Firepower adaptor:EthPortBySizeSmallStats:rn
        managed object property"
    ::= { cfprAdaptorEthPortBySizeSmallStatsEntry 3 }

cfprAdaptorEthPortBySizeSmallStatsEquals64 OBJECT-TYPE
    SYNTAX       Unsigned64
    MAX-ACCESS   read-only
    STATUS       current
    DESCRIPTION
        "Cisco Firepower adaptor:EthPortBySizeSmallStats:equals64
        managed object property"
    ::= { cfprAdaptorEthPortBySizeSmallStatsEntry 4 }

cfprAdaptorEthPortBySizeSmallStatsEquals64Delta OBJECT-TYPE
    SYNTAX       Counter64
    MAX-ACCESS   read-only
    STATUS       current
    DESCRIPTION
        "Cisco Firepower adaptor:EthPortBySizeSmallStats:equals64Delta
        managed object property"
    ::= { cfprAdaptorEthPortBySizeSmallStatsEntry 5 }

cfprAdaptorEthPortBySizeSmallStatsEquals64DeltaAvg OBJECT-TYPE
    SYNTAX       Unsigned64
    MAX-ACCESS   read-only
    STATUS       current
    DESCRIPTION
        "Cisco Firepower adaptor:EthPortBySizeSmallStats:equals64DeltaAvg
        managed object property"
    ::= { cfprAdaptorEthPortBySizeSmallStatsEntry 6 }

cfprAdaptorEthPortBySizeSmallStatsEquals64DeltaMax OBJECT-TYPE
    SYNTAX       Unsigned64
    MAX-ACCESS   read-only
    STATUS       current
    DESCRIPTION
        "Cisco Firepower adaptor:EthPortBySizeSmallStats:equals64DeltaMax
        managed object property"
    ::= { cfprAdaptorEthPortBySizeSmallStatsEntry 7 }

cfprAdaptorEthPortBySizeSmallStatsEquals64DeltaMin OBJECT-TYPE
    SYNTAX       Unsigned64
    MAX-ACCESS   read-only
    STATUS       current
    DESCRIPTION
        "Cisco Firepower adaptor:EthPortBySizeSmallStats:equals64DeltaMin
        managed object property"
    ::= { cfprAdaptorEthPortBySizeSmallStatsEntry 8 }

cfprAdaptorEthPortBySizeSmallStatsIntervals OBJECT-TYPE
    SYNTAX       Gauge32
    MAX-ACCESS   read-only
    STATUS       current
    DESCRIPTION
        "Cisco Firepower adaptor:EthPortBySizeSmallStats:intervals
        managed object property"
    ::= { cfprAdaptorEthPortBySizeSmallStatsEntry 9 }

cfprAdaptorEthPortBySizeSmallStatsLessThan1024 OBJECT-TYPE
    SYNTAX       Unsigned64
    MAX-ACCESS   read-only
    STATUS       current
    DESCRIPTION
        "Cisco Firepower adaptor:EthPortBySizeSmallStats:lessThan1024
        managed object property"
    ::= { cfprAdaptorEthPortBySizeSmallStatsEntry 10 }

cfprAdaptorEthPortBySizeSmallStatsLessThan1024Delta OBJECT-TYPE
    SYNTAX       Counter64
    MAX-ACCESS   read-only
    STATUS       current
    DESCRIPTION
        "Cisco Firepower adaptor:EthPortBySizeSmallStats:lessThan1024Delta
         managed object property"
    ::= { cfprAdaptorEthPortBySizeSmallStatsEntry 11 }

cfprAdaptorEthPortBySizeSmallStatsLessThan1024DeltaAvg OBJECT-TYPE
    SYNTAX       Unsigned64
    MAX-ACCESS   read-only
    STATUS       current
    DESCRIPTION
        "Cisco Firepower adaptor:EthPortBySizeSmallStats:lessThan1024Delta
        Avg managed object property"
    ::= { cfprAdaptorEthPortBySizeSmallStatsEntry 12 }

cfprAdaptorEthPortBySizeSmallStatsLessThan1024DeltaMax OBJECT-TYPE
    SYNTAX       Unsigned64
    MAX-ACCESS   read-only
    STATUS       current
    DESCRIPTION
        "Cisco Firepower adaptor:EthPortBySizeSmallStats:lessThan1024Delta
        Max managed object property"
    ::= { cfprAdaptorEthPortBySizeSmallStatsEntry 13 }

cfprAdaptorEthPortBySizeSmallStatsLessThan1024DeltaMin OBJECT-TYPE
    SYNTAX       Unsigned64
    MAX-ACCESS   read-only
    STATUS       current
    DESCRIPTION
        "Cisco Firepower adaptor:EthPortBySizeSmallStats:lessThan1024Delta
        Min managed object property"
    ::= { cfprAdaptorEthPortBySizeSmallStatsEntry 14 }

cfprAdaptorEthPortBySizeSmallStatsLessThan128 OBJECT-TYPE
    SYNTAX       Unsigned64
    MAX-ACCESS   read-only
    STATUS       current
    DESCRIPTION
        "Cisco Firepower adaptor:EthPortBySizeSmallStats:lessThan128
        managed object property"
    ::= { cfprAdaptorEthPortBySizeSmallStatsEntry 15 }

cfprAdaptorEthPortBySizeSmallStatsLessThan128Delta OBJECT-TYPE
    SYNTAX       Counter64
    MAX-ACCESS   read-only
    STATUS       current
    DESCRIPTION
        "Cisco Firepower adaptor:EthPortBySizeSmallStats:lessThan128Delta
        managed object property"
    ::= { cfprAdaptorEthPortBySizeSmallStatsEntry 16 }

cfprAdaptorEthPortBySizeSmallStatsLessThan128DeltaAvg OBJECT-TYPE
    SYNTAX       Unsigned64
    MAX-ACCESS   read-only
    STATUS       current
    DESCRIPTION
        "Cisco Firepower adaptor:EthPortBySizeSmallStats:lessThan128DeltaA
        vg managed object property"
    ::= { cfprAdaptorEthPortBySizeSmallStatsEntry 17 }

cfprAdaptorEthPortBySizeSmallStatsLessThan128DeltaMax OBJECT-TYPE
    SYNTAX       Unsigned64
    MAX-ACCESS   read-only
    STATUS       current
    DESCRIPTION
        "Cisco Firepower adaptor:EthPortBySizeSmallStats:lessThan128DeltaM
        ax managed object property"
    ::= { cfprAdaptorEthPortBySizeSmallStatsEntry 18 }

cfprAdaptorEthPortBySizeSmallStatsLessThan128DeltaMin OBJECT-TYPE
    SYNTAX       Unsigned64
    MAX-ACCESS   read-only
    STATUS       current
    DESCRIPTION
        "Cisco Firepower adaptor:EthPortBySizeSmallStats:lessThan128DeltaM
        in managed object property"
    ::= { cfprAdaptorEthPortBySizeSmallStatsEntry 19 }

cfprAdaptorEthPortBySizeSmallStatsLessThan256 OBJECT-TYPE
    SYNTAX       Unsigned64
    MAX-ACCESS   read-only
    STATUS       current
    DESCRIPTION
        "Cisco Firepower adaptor:EthPortBySizeSmallStats:lessThan256
        managed object property"
    ::= { cfprAdaptorEthPortBySizeSmallStatsEntry 20 }

cfprAdaptorEthPortBySizeSmallStatsLessThan256Delta OBJECT-TYPE
    SYNTAX       Counter64
    MAX-ACCESS   read-only
    STATUS       current
    DESCRIPTION
        "Cisco Firepower adaptor:EthPortBySizeSmallStats:lessThan256Delta
        managed object property"
    ::= { cfprAdaptorEthPortBySizeSmallStatsEntry 21 }

cfprAdaptorEthPortBySizeSmallStatsLessThan256DeltaAvg OBJECT-TYPE
    SYNTAX       Unsigned64
    MAX-ACCESS   read-only
    STATUS       current
    DESCRIPTION
        "Cisco Firepower adaptor:EthPortBySizeSmallStats:lessThan256DeltaA
        vg managed object property"
    ::= { cfprAdaptorEthPortBySizeSmallStatsEntry 22 }

cfprAdaptorEthPortBySizeSmallStatsLessThan256DeltaMax OBJECT-TYPE
    SYNTAX       Unsigned64
    MAX-ACCESS   read-only
    STATUS       current
    DESCRIPTION
        "Cisco Firepower adaptor:EthPortBySizeSmallStats:lessThan256DeltaM
        ax managed object property"
    ::= { cfprAdaptorEthPortBySizeSmallStatsEntry 23 }

cfprAdaptorEthPortBySizeSmallStatsLessThan256DeltaMin OBJECT-TYPE
    SYNTAX       Unsigned64
    MAX-ACCESS   read-only
    STATUS       current
    DESCRIPTION
        "Cisco Firepower adaptor:EthPortBySizeSmallStats:lessThan256DeltaM
        in managed object property"
    ::= { cfprAdaptorEthPortBySizeSmallStatsEntry 24 }

cfprAdaptorEthPortBySizeSmallStatsLessThan512 OBJECT-TYPE
    SYNTAX       Unsigned64
    MAX-ACCESS   read-only
    STATUS       current
    DESCRIPTION
        "Cisco Firepower adaptor:EthPortBySizeSmallStats:lessThan512
        managed object property"
    ::= { cfprAdaptorEthPortBySizeSmallStatsEntry 25 }

cfprAdaptorEthPortBySizeSmallStatsLessThan512Delta OBJECT-TYPE
    SYNTAX       Counter64
    MAX-ACCESS   read-only
    STATUS       current
    DESCRIPTION
        "Cisco Firepower adaptor:EthPortBySizeSmallStats:lessThan512Delta
        managed object property"
    ::= { cfprAdaptorEthPortBySizeSmallStatsEntry 26 }

cfprAdaptorEthPortBySizeSmallStatsLessThan512DeltaAvg OBJECT-TYPE
    SYNTAX       Unsigned64
    MAX-ACCESS   read-only
    STATUS       current
    DESCRIPTION
        "Cisco Firepower adaptor:EthPortBySizeSmallStats:lessThan512DeltaA
        vg managed object property"
    ::= { cfprAdaptorEthPortBySizeSmallStatsEntry 27 }

cfprAdaptorEthPortBySizeSmallStatsLessThan512DeltaMax OBJECT-TYPE
    SYNTAX       Unsigned64
    MAX-ACCESS   read-only
    STATUS       current
    DESCRIPTION
        "Cisco Firepower adaptor:EthPortBySizeSmallStats:lessThan512DeltaM
        ax managed object property"
    ::= { cfprAdaptorEthPortBySizeSmallStatsEntry 28 }

cfprAdaptorEthPortBySizeSmallStatsLessThan512DeltaMin OBJECT-TYPE
    SYNTAX       Unsigned64
    MAX-ACCESS   read-only
    STATUS       current
    DESCRIPTION
        "Cisco Firepower adaptor:EthPortBySizeSmallStats:lessThan512DeltaM
        in managed object property"
    ::= { cfprAdaptorEthPortBySizeSmallStatsEntry 29 }

cfprAdaptorEthPortBySizeSmallStatsLessThan64 OBJECT-TYPE
    SYNTAX       Unsigned64
    MAX-ACCESS   read-only
    STATUS       current
    DESCRIPTION
        "Cisco Firepower adaptor:EthPortBySizeSmallStats:lessThan64
        managed object property"
    ::= { cfprAdaptorEthPortBySizeSmallStatsEntry 30 }

cfprAdaptorEthPortBySizeSmallStatsLessThan64Delta OBJECT-TYPE
    SYNTAX       Counter64
    MAX-ACCESS   read-only
    STATUS       current
    DESCRIPTION
        "Cisco Firepower adaptor:EthPortBySizeSmallStats:lessThan64Delta
        managed object property"
    ::= { cfprAdaptorEthPortBySizeSmallStatsEntry 31 }

cfprAdaptorEthPortBySizeSmallStatsLessThan64DeltaAvg OBJECT-TYPE
    SYNTAX       Unsigned64
    MAX-ACCESS   read-only
    STATUS       current
    DESCRIPTION
        "Cisco Firepower adaptor:EthPortBySizeSmallStats:lessThan64DeltaAv
        g managed object property"
    ::= { cfprAdaptorEthPortBySizeSmallStatsEntry 32 }

cfprAdaptorEthPortBySizeSmallStatsLessThan64DeltaMax OBJECT-TYPE
    SYNTAX       Unsigned64
    MAX-ACCESS   read-only
    STATUS       current
    DESCRIPTION
        "Cisco Firepower adaptor:EthPortBySizeSmallStats:lessThan64DeltaMa
        x managed object property"
    ::= { cfprAdaptorEthPortBySizeSmallStatsEntry 33 }

cfprAdaptorEthPortBySizeSmallStatsLessThan64DeltaMin OBJECT-TYPE
    SYNTAX       Unsigned64
    MAX-ACCESS   read-only
    STATUS       current
    DESCRIPTION
        "Cisco Firepower adaptor:EthPortBySizeSmallStats:lessThan64DeltaMi
        n managed object property"
    ::= { cfprAdaptorEthPortBySizeSmallStatsEntry 34 }

cfprAdaptorEthPortBySizeSmallStatsSuspect OBJECT-TYPE
    SYNTAX       TruthValue
    MAX-ACCESS   read-only
    STATUS       current
    DESCRIPTION
        "Cisco Firepower adaptor:EthPortBySizeSmallStats:suspect
        managed object property"
    ::= { cfprAdaptorEthPortBySizeSmallStatsEntry 35 }

cfprAdaptorEthPortBySizeSmallStatsThresholded OBJECT-TYPE
    SYNTAX       CfprAdaptorEthPortBySizeSmallStatsThresholded
    MAX-ACCESS   read-only
    STATUS       current
    DESCRIPTION
        "Cisco Firepower adaptor:EthPortBySizeSmallStats:thresholded
        managed object property"
    ::= { cfprAdaptorEthPortBySizeSmallStatsEntry 36 }

cfprAdaptorEthPortBySizeSmallStatsTimeCollected OBJECT-TYPE
    SYNTAX       DateAndTime
    MAX-ACCESS   read-only
    STATUS       current
    DESCRIPTION
        "Cisco Firepower adaptor:EthPortBySizeSmallStats:timeCollected
        managed object property"
    ::= { cfprAdaptorEthPortBySizeSmallStatsEntry 37 }

cfprAdaptorEthPortBySizeSmallStatsTrafficDirection OBJECT-TYPE
    SYNTAX       CfprAdaptorAdapterStatsTrafficDir
    MAX-ACCESS   read-only
    STATUS       current
    DESCRIPTION
        "Cisco Firepower adaptor:EthPortBySizeSmallStats:trafficDirection
        managed object property"
    ::= { cfprAdaptorEthPortBySizeSmallStatsEntry 38 }

cfprAdaptorEthPortBySizeSmallStatsUpdate OBJECT-TYPE
    SYNTAX       Gauge32
    MAX-ACCESS   read-only
    STATUS       current
    DESCRIPTION
        "Cisco Firepower adaptor:EthPortBySizeSmallStats:update
        managed object property"
    ::= { cfprAdaptorEthPortBySizeSmallStatsEntry 39 }

cfprAdaptorEthPortBySizeSmallStatsHistTable OBJECT-TYPE
    SYNTAX           SEQUENCE OF CfprAdaptorEthPortBySizeSmallStatsHistEntry
    MAX-ACCESS       not-accessible
    STATUS           current
    DESCRIPTION
        "Cisco Firepower adaptor:EthPortBySizeSmallStatsHist
        managed object table"
    ::= { cfprAdaptorObjects 13 }

cfprAdaptorEthPortBySizeSmallStatsHistEntry OBJECT-TYPE
    SYNTAX           CfprAdaptorEthPortBySizeSmallStatsHistEntry
    MAX-ACCESS       not-accessible
    STATUS           current
    DESCRIPTION
        "Entry for the cfprAdaptorEthPortBySizeSmallStatsHistTable table."
    INDEX { cfprAdaptorEthPortBySizeSmallStatsHistInstanceId }
    ::= { cfprAdaptorEthPortBySizeSmallStatsHistTable 1 }

CfprAdaptorEthPortBySizeSmallStatsHistEntry ::= SEQUENCE {
    cfprAdaptorEthPortBySizeSmallStatsHistInstanceId                 CfprManagedObjectId,
    cfprAdaptorEthPortBySizeSmallStatsHistDn                         CfprManagedObjectDn,
    cfprAdaptorEthPortBySizeSmallStatsHistRn                         SnmpAdminString,
    cfprAdaptorEthPortBySizeSmallStatsHistEquals64                   Unsigned64,
    cfprAdaptorEthPortBySizeSmallStatsHistEquals64Delta              Unsigned64,
    cfprAdaptorEthPortBySizeSmallStatsHistEquals64DeltaAvg           Unsigned64,
    cfprAdaptorEthPortBySizeSmallStatsHistEquals64DeltaMax           Unsigned64,
    cfprAdaptorEthPortBySizeSmallStatsHistEquals64DeltaMin           Unsigned64,
    cfprAdaptorEthPortBySizeSmallStatsHistId                         Unsigned64,
    cfprAdaptorEthPortBySizeSmallStatsHistLessThan1024               Unsigned64,
    cfprAdaptorEthPortBySizeSmallStatsHistLessThan1024Delta          Unsigned64,
    cfprAdaptorEthPortBySizeSmallStatsHistLessThan1024DeltaAvg       Unsigned64,
    cfprAdaptorEthPortBySizeSmallStatsHistLessThan1024DeltaMax       Unsigned64,
    cfprAdaptorEthPortBySizeSmallStatsHistLessThan1024DeltaMin       Unsigned64,
    cfprAdaptorEthPortBySizeSmallStatsHistLessThan128                Unsigned64,
    cfprAdaptorEthPortBySizeSmallStatsHistLessThan128Delta           Unsigned64,
    cfprAdaptorEthPortBySizeSmallStatsHistLessThan128DeltaAvg        Unsigned64,
    cfprAdaptorEthPortBySizeSmallStatsHistLessThan128DeltaMax        Unsigned64,
    cfprAdaptorEthPortBySizeSmallStatsHistLessThan128DeltaMin        Unsigned64,
    cfprAdaptorEthPortBySizeSmallStatsHistLessThan256                Unsigned64,
    cfprAdaptorEthPortBySizeSmallStatsHistLessThan256Delta           Unsigned64,
    cfprAdaptorEthPortBySizeSmallStatsHistLessThan256DeltaAvg        Unsigned64,
    cfprAdaptorEthPortBySizeSmallStatsHistLessThan256DeltaMax        Unsigned64,
    cfprAdaptorEthPortBySizeSmallStatsHistLessThan256DeltaMin        Unsigned64,
    cfprAdaptorEthPortBySizeSmallStatsHistLessThan512                Unsigned64,
    cfprAdaptorEthPortBySizeSmallStatsHistLessThan512Delta           Unsigned64,
    cfprAdaptorEthPortBySizeSmallStatsHistLessThan512DeltaAvg        Unsigned64,
    cfprAdaptorEthPortBySizeSmallStatsHistLessThan512DeltaMax        Unsigned64,
    cfprAdaptorEthPortBySizeSmallStatsHistLessThan512DeltaMin        Unsigned64,
    cfprAdaptorEthPortBySizeSmallStatsHistLessThan64                 Unsigned64,
    cfprAdaptorEthPortBySizeSmallStatsHistLessThan64Delta            Unsigned64,
    cfprAdaptorEthPortBySizeSmallStatsHistLessThan64DeltaAvg         Unsigned64,
    cfprAdaptorEthPortBySizeSmallStatsHistLessThan64DeltaMax         Unsigned64,
    cfprAdaptorEthPortBySizeSmallStatsHistLessThan64DeltaMin         Unsigned64,
    cfprAdaptorEthPortBySizeSmallStatsHistMostRecent                 TruthValue,
    cfprAdaptorEthPortBySizeSmallStatsHistSuspect                    TruthValue,
    cfprAdaptorEthPortBySizeSmallStatsHistThresholded                CfprAdaptorEthPortBySizeSmallStatsHistThresholded,
    cfprAdaptorEthPortBySizeSmallStatsHistTimeCollected              DateAndTime
}

cfprAdaptorEthPortBySizeSmallStatsHistInstanceId OBJECT-TYPE
    SYNTAX       CfprManagedObjectId
    MAX-ACCESS   not-accessible
    STATUS       current
    DESCRIPTION
        "Instance identifier of the managed object."
    ::= { cfprAdaptorEthPortBySizeSmallStatsHistEntry 1 }

cfprAdaptorEthPortBySizeSmallStatsHistDn OBJECT-TYPE
    SYNTAX       CfprManagedObjectDn
    MAX-ACCESS   read-only
    STATUS       current
    DESCRIPTION
        "Cisco Firepower adaptor:EthPortBySizeSmallStatsHist:dn
        managed object property"
    ::= { cfprAdaptorEthPortBySizeSmallStatsHistEntry 2 }

cfprAdaptorEthPortBySizeSmallStatsHistRn OBJECT-TYPE
    SYNTAX       SnmpAdminString
    MAX-ACCESS   read-only
    STATUS       current
    DESCRIPTION
        "Cisco Firepower adaptor:EthPortBySizeSmallStatsHist:rn
        managed object property"
    ::= { cfprAdaptorEthPortBySizeSmallStatsHistEntry 3 }

cfprAdaptorEthPortBySizeSmallStatsHistEquals64 OBJECT-TYPE
    SYNTAX       Unsigned64
    MAX-ACCESS   read-only
    STATUS       current
    DESCRIPTION
        "Cisco Firepower adaptor:EthPortBySizeSmallStatsHist:equals64
        managed object property"
    ::= { cfprAdaptorEthPortBySizeSmallStatsHistEntry 4 }

cfprAdaptorEthPortBySizeSmallStatsHistEquals64Delta OBJECT-TYPE
    SYNTAX       Unsigned64
    MAX-ACCESS   read-only
    STATUS       current
    DESCRIPTION
        "Cisco Firepower adaptor:EthPortBySizeSmallStatsHist:equals64Delta
         managed object property"
    ::= { cfprAdaptorEthPortBySizeSmallStatsHistEntry 5 }

cfprAdaptorEthPortBySizeSmallStatsHistEquals64DeltaAvg OBJECT-TYPE
    SYNTAX       Unsigned64
    MAX-ACCESS   read-only
    STATUS       current
    DESCRIPTION
        "Cisco Firepower adaptor:EthPortBySizeSmallStatsHist:equals64Delta
        Avg managed object property"
    ::= { cfprAdaptorEthPortBySizeSmallStatsHistEntry 6 }

cfprAdaptorEthPortBySizeSmallStatsHistEquals64DeltaMax OBJECT-TYPE
    SYNTAX       Unsigned64
    MAX-ACCESS   read-only
    STATUS       current
    DESCRIPTION
        "Cisco Firepower adaptor:EthPortBySizeSmallStatsHist:equals64Delta
        Max managed object property"
    ::= { cfprAdaptorEthPortBySizeSmallStatsHistEntry 7 }

cfprAdaptorEthPortBySizeSmallStatsHistEquals64DeltaMin OBJECT-TYPE
    SYNTAX       Unsigned64
    MAX-ACCESS   read-only
    STATUS       current
    DESCRIPTION
        "Cisco Firepower adaptor:EthPortBySizeSmallStatsHist:equals64Delta
        Min managed object property"
    ::= { cfprAdaptorEthPortBySizeSmallStatsHistEntry 8 }

cfprAdaptorEthPortBySizeSmallStatsHistId OBJECT-TYPE
    SYNTAX       Unsigned64
    MAX-ACCESS   read-only
    STATUS       current
    DESCRIPTION
        "Cisco Firepower adaptor:EthPortBySizeSmallStatsHist:id
        managed object property"
    ::= { cfprAdaptorEthPortBySizeSmallStatsHistEntry 9 }

cfprAdaptorEthPortBySizeSmallStatsHistLessThan1024 OBJECT-TYPE
    SYNTAX       Unsigned64
    MAX-ACCESS   read-only
    STATUS       current
    DESCRIPTION
        "Cisco Firepower adaptor:EthPortBySizeSmallStatsHist:lessThan1024
        managed object property"
    ::= { cfprAdaptorEthPortBySizeSmallStatsHistEntry 10 }

cfprAdaptorEthPortBySizeSmallStatsHistLessThan1024Delta OBJECT-TYPE
    SYNTAX       Unsigned64
    MAX-ACCESS   read-only
    STATUS       current
    DESCRIPTION
        "Cisco Firepower adaptor:EthPortBySizeSmallStatsHist:lessThan1024D
        elta managed object property"
    ::= { cfprAdaptorEthPortBySizeSmallStatsHistEntry 11 }

cfprAdaptorEthPortBySizeSmallStatsHistLessThan1024DeltaAvg OBJECT-TYPE
    SYNTAX       Unsigned64
    MAX-ACCESS   read-only
    STATUS       current
    DESCRIPTION
        "Cisco Firepower adaptor:EthPortBySizeSmallStatsHist:lessThan1024D
        eltaAvg managed object property"
    ::= { cfprAdaptorEthPortBySizeSmallStatsHistEntry 12 }

cfprAdaptorEthPortBySizeSmallStatsHistLessThan1024DeltaMax OBJECT-TYPE
    SYNTAX       Unsigned64
    MAX-ACCESS   read-only
    STATUS       current
    DESCRIPTION
        "Cisco Firepower adaptor:EthPortBySizeSmallStatsHist:lessThan1024D
        eltaMax managed object property"
    ::= { cfprAdaptorEthPortBySizeSmallStatsHistEntry 13 }

cfprAdaptorEthPortBySizeSmallStatsHistLessThan1024DeltaMin OBJECT-TYPE
    SYNTAX       Unsigned64
    MAX-ACCESS   read-only
    STATUS       current
    DESCRIPTION
        "Cisco Firepower adaptor:EthPortBySizeSmallStatsHist:lessThan1024D
        eltaMin managed object property"
    ::= { cfprAdaptorEthPortBySizeSmallStatsHistEntry 14 }

cfprAdaptorEthPortBySizeSmallStatsHistLessThan128 OBJECT-TYPE
    SYNTAX       Unsigned64
    MAX-ACCESS   read-only
    STATUS       current
    DESCRIPTION
        "Cisco Firepower adaptor:EthPortBySizeSmallStatsHist:lessThan128
        managed object property"
    ::= { cfprAdaptorEthPortBySizeSmallStatsHistEntry 15 }

cfprAdaptorEthPortBySizeSmallStatsHistLessThan128Delta OBJECT-TYPE
    SYNTAX       Unsigned64
    MAX-ACCESS   read-only
    STATUS       current
    DESCRIPTION
        "Cisco Firepower adaptor:EthPortBySizeSmallStatsHist:lessThan128De
        lta managed object property"
    ::= { cfprAdaptorEthPortBySizeSmallStatsHistEntry 16 }

cfprAdaptorEthPortBySizeSmallStatsHistLessThan128DeltaAvg OBJECT-TYPE
    SYNTAX       Unsigned64
    MAX-ACCESS   read-only
    STATUS       current
    DESCRIPTION
        "Cisco Firepower adaptor:EthPortBySizeSmallStatsHist:lessThan128De
        ltaAvg managed object property"
    ::= { cfprAdaptorEthPortBySizeSmallStatsHistEntry 17 }

cfprAdaptorEthPortBySizeSmallStatsHistLessThan128DeltaMax OBJECT-TYPE
    SYNTAX       Unsigned64
    MAX-ACCESS   read-only
    STATUS       current
    DESCRIPTION
        "Cisco Firepower adaptor:EthPortBySizeSmallStatsHist:lessThan128De
        ltaMax managed object property"
    ::= { cfprAdaptorEthPortBySizeSmallStatsHistEntry 18 }

cfprAdaptorEthPortBySizeSmallStatsHistLessThan128DeltaMin OBJECT-TYPE
    SYNTAX       Unsigned64
    MAX-ACCESS   read-only
    STATUS       current
    DESCRIPTION
        "Cisco Firepower adaptor:EthPortBySizeSmallStatsHist:lessThan128De
        ltaMin managed object property"
    ::= { cfprAdaptorEthPortBySizeSmallStatsHistEntry 19 }

cfprAdaptorEthPortBySizeSmallStatsHistLessThan256 OBJECT-TYPE
    SYNTAX       Unsigned64
    MAX-ACCESS   read-only
    STATUS       current
    DESCRIPTION
        "Cisco Firepower adaptor:EthPortBySizeSmallStatsHist:lessThan256
        managed object property"
    ::= { cfprAdaptorEthPortBySizeSmallStatsHistEntry 20 }

cfprAdaptorEthPortBySizeSmallStatsHistLessThan256Delta OBJECT-TYPE
    SYNTAX       Unsigned64
    MAX-ACCESS   read-only
    STATUS       current
    DESCRIPTION
        "Cisco Firepower adaptor:EthPortBySizeSmallStatsHist:lessThan256De
        lta managed object property"
    ::= { cfprAdaptorEthPortBySizeSmallStatsHistEntry 21 }

cfprAdaptorEthPortBySizeSmallStatsHistLessThan256DeltaAvg OBJECT-TYPE
    SYNTAX       Unsigned64
    MAX-ACCESS   read-only
    STATUS       current
    DESCRIPTION
        "Cisco Firepower adaptor:EthPortBySizeSmallStatsHist:lessThan256De
        ltaAvg managed object property"
    ::= { cfprAdaptorEthPortBySizeSmallStatsHistEntry 22 }

cfprAdaptorEthPortBySizeSmallStatsHistLessThan256DeltaMax OBJECT-TYPE
    SYNTAX       Unsigned64
    MAX-ACCESS   read-only
    STATUS       current
    DESCRIPTION
        "Cisco Firepower adaptor:EthPortBySizeSmallStatsHist:lessThan256De
        ltaMax managed object property"
    ::= { cfprAdaptorEthPortBySizeSmallStatsHistEntry 23 }

cfprAdaptorEthPortBySizeSmallStatsHistLessThan256DeltaMin OBJECT-TYPE
    SYNTAX       Unsigned64
    MAX-ACCESS   read-only
    STATUS       current
    DESCRIPTION
        "Cisco Firepower adaptor:EthPortBySizeSmallStatsHist:lessThan256De
        ltaMin managed object property"
    ::= { cfprAdaptorEthPortBySizeSmallStatsHistEntry 24 }

cfprAdaptorEthPortBySizeSmallStatsHistLessThan512 OBJECT-TYPE
    SYNTAX       Unsigned64
    MAX-ACCESS   read-only
    STATUS       current
    DESCRIPTION
        "Cisco Firepower adaptor:EthPortBySizeSmallStatsHist:lessThan512
        managed object property"
    ::= { cfprAdaptorEthPortBySizeSmallStatsHistEntry 25 }

cfprAdaptorEthPortBySizeSmallStatsHistLessThan512Delta OBJECT-TYPE
    SYNTAX       Unsigned64
    MAX-ACCESS   read-only
    STATUS       current
    DESCRIPTION
        "Cisco Firepower adaptor:EthPortBySizeSmallStatsHist:lessThan512De
        lta managed object property"
    ::= { cfprAdaptorEthPortBySizeSmallStatsHistEntry 26 }

cfprAdaptorEthPortBySizeSmallStatsHistLessThan512DeltaAvg OBJECT-TYPE
    SYNTAX       Unsigned64
    MAX-ACCESS   read-only
    STATUS       current
    DESCRIPTION
        "Cisco Firepower adaptor:EthPortBySizeSmallStatsHist:lessThan512De
        ltaAvg managed object property"
    ::= { cfprAdaptorEthPortBySizeSmallStatsHistEntry 27 }

cfprAdaptorEthPortBySizeSmallStatsHistLessThan512DeltaMax OBJECT-TYPE
    SYNTAX       Unsigned64
    MAX-ACCESS   read-only
    STATUS       current
    DESCRIPTION
        "Cisco Firepower adaptor:EthPortBySizeSmallStatsHist:lessThan512De
        ltaMax managed object property"
    ::= { cfprAdaptorEthPortBySizeSmallStatsHistEntry 28 }

cfprAdaptorEthPortBySizeSmallStatsHistLessThan512DeltaMin OBJECT-TYPE
    SYNTAX       Unsigned64
    MAX-ACCESS   read-only
    STATUS       current
    DESCRIPTION
        "Cisco Firepower adaptor:EthPortBySizeSmallStatsHist:lessThan512De
        ltaMin managed object property"
    ::= { cfprAdaptorEthPortBySizeSmallStatsHistEntry 29 }

cfprAdaptorEthPortBySizeSmallStatsHistLessThan64 OBJECT-TYPE
    SYNTAX       Unsigned64
    MAX-ACCESS   read-only
    STATUS       current
    DESCRIPTION
        "Cisco Firepower adaptor:EthPortBySizeSmallStatsHist:lessThan64
        managed object property"
    ::= { cfprAdaptorEthPortBySizeSmallStatsHistEntry 30 }

cfprAdaptorEthPortBySizeSmallStatsHistLessThan64Delta OBJECT-TYPE
    SYNTAX       Unsigned64
    MAX-ACCESS   read-only
    STATUS       current
    DESCRIPTION
        "Cisco Firepower adaptor:EthPortBySizeSmallStatsHist:lessThan64Del
        ta managed object property"
    ::= { cfprAdaptorEthPortBySizeSmallStatsHistEntry 31 }

cfprAdaptorEthPortBySizeSmallStatsHistLessThan64DeltaAvg OBJECT-TYPE
    SYNTAX       Unsigned64
    MAX-ACCESS   read-only
    STATUS       current
    DESCRIPTION
        "Cisco Firepower adaptor:EthPortBySizeSmallStatsHist:lessThan64Del
        taAvg managed object property"
    ::= { cfprAdaptorEthPortBySizeSmallStatsHistEntry 32 }

cfprAdaptorEthPortBySizeSmallStatsHistLessThan64DeltaMax OBJECT-TYPE
    SYNTAX       Unsigned64
    MAX-ACCESS   read-only
    STATUS       current
    DESCRIPTION
        "Cisco Firepower adaptor:EthPortBySizeSmallStatsHist:lessThan64Del
        taMax managed object property"
    ::= { cfprAdaptorEthPortBySizeSmallStatsHistEntry 33 }

cfprAdaptorEthPortBySizeSmallStatsHistLessThan64DeltaMin OBJECT-TYPE
    SYNTAX       Unsigned64
    MAX-ACCESS   read-only
    STATUS       current
    DESCRIPTION
        "Cisco Firepower adaptor:EthPortBySizeSmallStatsHist:lessThan64Del
        taMin managed object property"
    ::= { cfprAdaptorEthPortBySizeSmallStatsHistEntry 34 }

cfprAdaptorEthPortBySizeSmallStatsHistMostRecent OBJECT-TYPE
    SYNTAX       TruthValue
    MAX-ACCESS   read-only
    STATUS       current
    DESCRIPTION
        "Cisco Firepower adaptor:EthPortBySizeSmallStatsHist:mostRecent
        managed object property"
    ::= { cfprAdaptorEthPortBySizeSmallStatsHistEntry 35 }

cfprAdaptorEthPortBySizeSmallStatsHistSuspect OBJECT-TYPE
    SYNTAX       TruthValue
    MAX-ACCESS   read-only
    STATUS       current
    DESCRIPTION
        "Cisco Firepower adaptor:EthPortBySizeSmallStatsHist:suspect
        managed object property"
    ::= { cfprAdaptorEthPortBySizeSmallStatsHistEntry 36 }

cfprAdaptorEthPortBySizeSmallStatsHistThresholded OBJECT-TYPE
    SYNTAX       CfprAdaptorEthPortBySizeSmallStatsHistThresholded
    MAX-ACCESS   read-only
    STATUS       current
    DESCRIPTION
        "Cisco Firepower adaptor:EthPortBySizeSmallStatsHist:thresholded
        managed object property"
    ::= { cfprAdaptorEthPortBySizeSmallStatsHistEntry 37 }

cfprAdaptorEthPortBySizeSmallStatsHistTimeCollected OBJECT-TYPE
    SYNTAX       DateAndTime
    MAX-ACCESS   read-only
    STATUS       current
    DESCRIPTION
        "Cisco Firepower adaptor:EthPortBySizeSmallStatsHist:timeCollected
         managed object property"
    ::= { cfprAdaptorEthPortBySizeSmallStatsHistEntry 38 }

cfprAdaptorEthPortErrStatsTable OBJECT-TYPE
    SYNTAX           SEQUENCE OF CfprAdaptorEthPortErrStatsEntry
    MAX-ACCESS       not-accessible
    STATUS           current
    DESCRIPTION
        "Cisco Firepower adaptor:EthPortErrStats managed object table"
    ::= { cfprAdaptorObjects 14 }

cfprAdaptorEthPortErrStatsEntry OBJECT-TYPE
    SYNTAX           CfprAdaptorEthPortErrStatsEntry
    MAX-ACCESS       not-accessible
    STATUS           current
    DESCRIPTION
        "Entry for the cfprAdaptorEthPortErrStatsTable table."
    INDEX { cfprAdaptorEthPortErrStatsInstanceId }
    ::= { cfprAdaptorEthPortErrStatsTable 1 }

CfprAdaptorEthPortErrStatsEntry ::= SEQUENCE {
    cfprAdaptorEthPortErrStatsInstanceId                             CfprManagedObjectId,
    cfprAdaptorEthPortErrStatsDn                                     CfprManagedObjectDn,
    cfprAdaptorEthPortErrStatsRn                                     SnmpAdminString,
    cfprAdaptorEthPortErrStatsBadCrcPackets                          Unsigned64,
    cfprAdaptorEthPortErrStatsBadCrcPacketsDelta                     Counter64,
    cfprAdaptorEthPortErrStatsBadCrcPacketsDeltaAvg                  Unsigned64,
    cfprAdaptorEthPortErrStatsBadCrcPacketsDeltaMax                  Unsigned64,
    cfprAdaptorEthPortErrStatsBadCrcPacketsDeltaMin                  Unsigned64,
    cfprAdaptorEthPortErrStatsBadLengthPackets                       Unsigned64,
    cfprAdaptorEthPortErrStatsBadLengthPacketsDelta                  Counter64,
    cfprAdaptorEthPortErrStatsBadLengthPacketsDeltaAvg               Unsigned64,
    cfprAdaptorEthPortErrStatsBadLengthPacketsDeltaMax               Unsigned64,
    cfprAdaptorEthPortErrStatsBadLengthPacketsDeltaMin               Unsigned64,
    cfprAdaptorEthPortErrStatsIntervals                              Gauge32,
    cfprAdaptorEthPortErrStatsMacDiscardedPackets                    Unsigned64,
    cfprAdaptorEthPortErrStatsMacDiscardedPacketsDelta               Counter64,
    cfprAdaptorEthPortErrStatsMacDiscardedPacketsDeltaAvg            Unsigned64,
    cfprAdaptorEthPortErrStatsMacDiscardedPacketsDeltaMax            Unsigned64,
    cfprAdaptorEthPortErrStatsMacDiscardedPacketsDeltaMin            Unsigned64,
    cfprAdaptorEthPortErrStatsSuspect                                TruthValue,
    cfprAdaptorEthPortErrStatsThresholded                            CfprAdaptorEthPortErrStatsThresholded,
    cfprAdaptorEthPortErrStatsTimeCollected                          DateAndTime,
    cfprAdaptorEthPortErrStatsTrafficDirection                       CfprAdaptorAdapterStatsTrafficDir,
    cfprAdaptorEthPortErrStatsUpdate                                 Gauge32
}

cfprAdaptorEthPortErrStatsInstanceId OBJECT-TYPE
    SYNTAX       CfprManagedObjectId
    MAX-ACCESS   not-accessible
    STATUS       current
    DESCRIPTION
        "Instance identifier of the managed object."
    ::= { cfprAdaptorEthPortErrStatsEntry 1 }

cfprAdaptorEthPortErrStatsDn OBJECT-TYPE
    SYNTAX       CfprManagedObjectDn
    MAX-ACCESS   read-only
    STATUS       current
    DESCRIPTION
        "Cisco Firepower adaptor:EthPortErrStats:dn managed
        object property"
    ::= { cfprAdaptorEthPortErrStatsEntry 2 }

cfprAdaptorEthPortErrStatsRn OBJECT-TYPE
    SYNTAX       SnmpAdminString
    MAX-ACCESS   read-only
    STATUS       current
    DESCRIPTION
        "Cisco Firepower adaptor:EthPortErrStats:rn managed
        object property"
    ::= { cfprAdaptorEthPortErrStatsEntry 3 }

cfprAdaptorEthPortErrStatsBadCrcPackets OBJECT-TYPE
    SYNTAX       Unsigned64
    MAX-ACCESS   read-only
    STATUS       current
    DESCRIPTION
        "Cisco Firepower adaptor:EthPortErrStats:badCrcPackets
        managed object property"
    ::= { cfprAdaptorEthPortErrStatsEntry 4 }

cfprAdaptorEthPortErrStatsBadCrcPacketsDelta OBJECT-TYPE
    SYNTAX       Counter64
    MAX-ACCESS   read-only
    STATUS       current
    DESCRIPTION
        "Cisco Firepower adaptor:EthPortErrStats:badCrcPacketsDelta
        managed object property"
    ::= { cfprAdaptorEthPortErrStatsEntry 5 }

cfprAdaptorEthPortErrStatsBadCrcPacketsDeltaAvg OBJECT-TYPE
    SYNTAX       Unsigned64
    MAX-ACCESS   read-only
    STATUS       current
    DESCRIPTION
        "Cisco Firepower adaptor:EthPortErrStats:badCrcPacketsDeltaAvg
        managed object property"
    ::= { cfprAdaptorEthPortErrStatsEntry 6 }

cfprAdaptorEthPortErrStatsBadCrcPacketsDeltaMax OBJECT-TYPE
    SYNTAX       Unsigned64
    MAX-ACCESS   read-only
    STATUS       current
    DESCRIPTION
        "Cisco Firepower adaptor:EthPortErrStats:badCrcPacketsDeltaMax
        managed object property"
    ::= { cfprAdaptorEthPortErrStatsEntry 7 }

cfprAdaptorEthPortErrStatsBadCrcPacketsDeltaMin OBJECT-TYPE
    SYNTAX       Unsigned64
    MAX-ACCESS   read-only
    STATUS       current
    DESCRIPTION
        "Cisco Firepower adaptor:EthPortErrStats:badCrcPacketsDeltaMin
        managed object property"
    ::= { cfprAdaptorEthPortErrStatsEntry 8 }

cfprAdaptorEthPortErrStatsBadLengthPackets OBJECT-TYPE
    SYNTAX       Unsigned64
    MAX-ACCESS   read-only
    STATUS       current
    DESCRIPTION
        "Cisco Firepower adaptor:EthPortErrStats:badLengthPackets
        managed object property"
    ::= { cfprAdaptorEthPortErrStatsEntry 9 }

cfprAdaptorEthPortErrStatsBadLengthPacketsDelta OBJECT-TYPE
    SYNTAX       Counter64
    MAX-ACCESS   read-only
    STATUS       current
    DESCRIPTION
        "Cisco Firepower adaptor:EthPortErrStats:badLengthPacketsDelta
        managed object property"
    ::= { cfprAdaptorEthPortErrStatsEntry 10 }

cfprAdaptorEthPortErrStatsBadLengthPacketsDeltaAvg OBJECT-TYPE
    SYNTAX       Unsigned64
    MAX-ACCESS   read-only
    STATUS       current
    DESCRIPTION
        "Cisco Firepower adaptor:EthPortErrStats:badLengthPacketsDeltaAvg
        managed object property"
    ::= { cfprAdaptorEthPortErrStatsEntry 11 }

cfprAdaptorEthPortErrStatsBadLengthPacketsDeltaMax OBJECT-TYPE
    SYNTAX       Unsigned64
    MAX-ACCESS   read-only
    STATUS       current
    DESCRIPTION
        "Cisco Firepower adaptor:EthPortErrStats:badLengthPacketsDeltaMax
        managed object property"
    ::= { cfprAdaptorEthPortErrStatsEntry 12 }

cfprAdaptorEthPortErrStatsBadLengthPacketsDeltaMin OBJECT-TYPE
    SYNTAX       Unsigned64
    MAX-ACCESS   read-only
    STATUS       current
    DESCRIPTION
        "Cisco Firepower adaptor:EthPortErrStats:badLengthPacketsDeltaMin
        managed object property"
    ::= { cfprAdaptorEthPortErrStatsEntry 13 }

cfprAdaptorEthPortErrStatsIntervals OBJECT-TYPE
    SYNTAX       Gauge32
    MAX-ACCESS   read-only
    STATUS       current
    DESCRIPTION
        "Cisco Firepower adaptor:EthPortErrStats:intervals
        managed object property"
    ::= { cfprAdaptorEthPortErrStatsEntry 14 }

cfprAdaptorEthPortErrStatsMacDiscardedPackets OBJECT-TYPE
    SYNTAX       Unsigned64
    MAX-ACCESS   read-only
    STATUS       current
    DESCRIPTION
        "Cisco Firepower adaptor:EthPortErrStats:macDiscardedPackets
        managed object property"
    ::= { cfprAdaptorEthPortErrStatsEntry 15 }

cfprAdaptorEthPortErrStatsMacDiscardedPacketsDelta OBJECT-TYPE
    SYNTAX       Counter64
    MAX-ACCESS   read-only
    STATUS       current
    DESCRIPTION
        "Cisco Firepower adaptor:EthPortErrStats:macDiscardedPacketsDelta
        managed object property"
    ::= { cfprAdaptorEthPortErrStatsEntry 16 }

cfprAdaptorEthPortErrStatsMacDiscardedPacketsDeltaAvg OBJECT-TYPE
    SYNTAX       Unsigned64
    MAX-ACCESS   read-only
    STATUS       current
    DESCRIPTION
        "Cisco Firepower adaptor:EthPortErrStats:macDiscardedPacketsDeltaA
        vg managed object property"
    ::= { cfprAdaptorEthPortErrStatsEntry 17 }

cfprAdaptorEthPortErrStatsMacDiscardedPacketsDeltaMax OBJECT-TYPE
    SYNTAX       Unsigned64
    MAX-ACCESS   read-only
    STATUS       current
    DESCRIPTION
        "Cisco Firepower adaptor:EthPortErrStats:macDiscardedPacketsDeltaM
        ax managed object property"
    ::= { cfprAdaptorEthPortErrStatsEntry 18 }

cfprAdaptorEthPortErrStatsMacDiscardedPacketsDeltaMin OBJECT-TYPE
    SYNTAX       Unsigned64
    MAX-ACCESS   read-only
    STATUS       current
    DESCRIPTION
        "Cisco Firepower adaptor:EthPortErrStats:macDiscardedPacketsDeltaM
        in managed object property"
    ::= { cfprAdaptorEthPortErrStatsEntry 19 }

cfprAdaptorEthPortErrStatsSuspect OBJECT-TYPE
    SYNTAX       TruthValue
    MAX-ACCESS   read-only
    STATUS       current
    DESCRIPTION
        "Cisco Firepower adaptor:EthPortErrStats:suspect
        managed object property"
    ::= { cfprAdaptorEthPortErrStatsEntry 20 }

cfprAdaptorEthPortErrStatsThresholded OBJECT-TYPE
    SYNTAX       CfprAdaptorEthPortErrStatsThresholded
    MAX-ACCESS   read-only
    STATUS       current
    DESCRIPTION
        "Cisco Firepower adaptor:EthPortErrStats:thresholded
        managed object property"
    ::= { cfprAdaptorEthPortErrStatsEntry 21 }

cfprAdaptorEthPortErrStatsTimeCollected OBJECT-TYPE
    SYNTAX       DateAndTime
    MAX-ACCESS   read-only
    STATUS       current
    DESCRIPTION
        "Cisco Firepower adaptor:EthPortErrStats:timeCollected
        managed object property"
    ::= { cfprAdaptorEthPortErrStatsEntry 22 }

cfprAdaptorEthPortErrStatsTrafficDirection OBJECT-TYPE
    SYNTAX       CfprAdaptorAdapterStatsTrafficDir
    MAX-ACCESS   read-only
    STATUS       current
    DESCRIPTION
        "Cisco Firepower adaptor:EthPortErrStats:trafficDirection
        managed object property"
    ::= { cfprAdaptorEthPortErrStatsEntry 23 }

cfprAdaptorEthPortErrStatsUpdate OBJECT-TYPE
    SYNTAX       Gauge32
    MAX-ACCESS   read-only
    STATUS       current
    DESCRIPTION
        "Cisco Firepower adaptor:EthPortErrStats:update
        managed object property"
    ::= { cfprAdaptorEthPortErrStatsEntry 24 }

cfprAdaptorEthPortErrStatsHistTable OBJECT-TYPE
    SYNTAX           SEQUENCE OF CfprAdaptorEthPortErrStatsHistEntry
    MAX-ACCESS       not-accessible
    STATUS           current
    DESCRIPTION
        "Cisco Firepower adaptor:EthPortErrStatsHist managed object table"
    ::= { cfprAdaptorObjects 15 }

cfprAdaptorEthPortErrStatsHistEntry OBJECT-TYPE
    SYNTAX           CfprAdaptorEthPortErrStatsHistEntry
    MAX-ACCESS       not-accessible
    STATUS           current
    DESCRIPTION
        "Entry for the cfprAdaptorEthPortErrStatsHistTable table."
    INDEX { cfprAdaptorEthPortErrStatsHistInstanceId }
    ::= { cfprAdaptorEthPortErrStatsHistTable 1 }

CfprAdaptorEthPortErrStatsHistEntry ::= SEQUENCE {
    cfprAdaptorEthPortErrStatsHistInstanceId                         CfprManagedObjectId,
    cfprAdaptorEthPortErrStatsHistDn                                 CfprManagedObjectDn,
    cfprAdaptorEthPortErrStatsHistRn                                 SnmpAdminString,
    cfprAdaptorEthPortErrStatsHistBadCrcPackets                      Unsigned64,
    cfprAdaptorEthPortErrStatsHistBadCrcPacketsDelta                 Unsigned64,
    cfprAdaptorEthPortErrStatsHistBadCrcPacketsDeltaAvg              Unsigned64,
    cfprAdaptorEthPortErrStatsHistBadCrcPacketsDeltaMax              Unsigned64,
    cfprAdaptorEthPortErrStatsHistBadCrcPacketsDeltaMin              Unsigned64,
    cfprAdaptorEthPortErrStatsHistBadLengthPackets                   Unsigned64,
    cfprAdaptorEthPortErrStatsHistBadLengthPacketsDelta              Unsigned64,
    cfprAdaptorEthPortErrStatsHistBadLengthPacketsDeltaAvg           Unsigned64,
    cfprAdaptorEthPortErrStatsHistBadLengthPacketsDeltaMax           Unsigned64,
    cfprAdaptorEthPortErrStatsHistBadLengthPacketsDeltaMin           Unsigned64,
    cfprAdaptorEthPortErrStatsHistId                                 Unsigned64,
    cfprAdaptorEthPortErrStatsHistMacDiscardedPackets                Unsigned64,
    cfprAdaptorEthPortErrStatsHistMacDiscardedPacketsDelta           Unsigned64,
    cfprAdaptorEthPortErrStatsHistMacDiscardedPacketsDeltaAvg        Unsigned64,
    cfprAdaptorEthPortErrStatsHistMacDiscardedPacketsDeltaMax        Unsigned64,
    cfprAdaptorEthPortErrStatsHistMacDiscardedPacketsDeltaMin        Unsigned64,
    cfprAdaptorEthPortErrStatsHistMostRecent                         TruthValue,
    cfprAdaptorEthPortErrStatsHistSuspect                            TruthValue,
    cfprAdaptorEthPortErrStatsHistThresholded                        CfprAdaptorEthPortErrStatsHistThresholded,
    cfprAdaptorEthPortErrStatsHistTimeCollected                      DateAndTime
}

cfprAdaptorEthPortErrStatsHistInstanceId OBJECT-TYPE
    SYNTAX       CfprManagedObjectId
    MAX-ACCESS   not-accessible
    STATUS       current
    DESCRIPTION
        "Instance identifier of the managed object."
    ::= { cfprAdaptorEthPortErrStatsHistEntry 1 }

cfprAdaptorEthPortErrStatsHistDn OBJECT-TYPE
    SYNTAX       CfprManagedObjectDn
    MAX-ACCESS   read-only
    STATUS       current
    DESCRIPTION
        "Cisco Firepower adaptor:EthPortErrStatsHist:dn
        managed object property"
    ::= { cfprAdaptorEthPortErrStatsHistEntry 2 }

cfprAdaptorEthPortErrStatsHistRn OBJECT-TYPE
    SYNTAX       SnmpAdminString
    MAX-ACCESS   read-only
    STATUS       current
    DESCRIPTION
        "Cisco Firepower adaptor:EthPortErrStatsHist:rn
        managed object property"
    ::= { cfprAdaptorEthPortErrStatsHistEntry 3 }

cfprAdaptorEthPortErrStatsHistBadCrcPackets OBJECT-TYPE
    SYNTAX       Unsigned64
    MAX-ACCESS   read-only
    STATUS       current
    DESCRIPTION
        "Cisco Firepower adaptor:EthPortErrStatsHist:badCrcPackets
        managed object property"
    ::= { cfprAdaptorEthPortErrStatsHistEntry 4 }

cfprAdaptorEthPortErrStatsHistBadCrcPacketsDelta OBJECT-TYPE
    SYNTAX       Unsigned64
    MAX-ACCESS   read-only
    STATUS       current
    DESCRIPTION
        "Cisco Firepower adaptor:EthPortErrStatsHist:badCrcPacketsDelta
        managed object property"
    ::= { cfprAdaptorEthPortErrStatsHistEntry 5 }

cfprAdaptorEthPortErrStatsHistBadCrcPacketsDeltaAvg OBJECT-TYPE
    SYNTAX       Unsigned64
    MAX-ACCESS   read-only
    STATUS       current
    DESCRIPTION
        "Cisco Firepower adaptor:EthPortErrStatsHist:badCrcPacketsDeltaAvg
         managed object property"
    ::= { cfprAdaptorEthPortErrStatsHistEntry 6 }

cfprAdaptorEthPortErrStatsHistBadCrcPacketsDeltaMax OBJECT-TYPE
    SYNTAX       Unsigned64
    MAX-ACCESS   read-only
    STATUS       current
    DESCRIPTION
        "Cisco Firepower adaptor:EthPortErrStatsHist:badCrcPacketsDeltaMax
         managed object property"
    ::= { cfprAdaptorEthPortErrStatsHistEntry 7 }

cfprAdaptorEthPortErrStatsHistBadCrcPacketsDeltaMin OBJECT-TYPE
    SYNTAX       Unsigned64
    MAX-ACCESS   read-only
    STATUS       current
    DESCRIPTION
        "Cisco Firepower adaptor:EthPortErrStatsHist:badCrcPacketsDeltaMin
         managed object property"
    ::= { cfprAdaptorEthPortErrStatsHistEntry 8 }

cfprAdaptorEthPortErrStatsHistBadLengthPackets OBJECT-TYPE
    SYNTAX       Unsigned64
    MAX-ACCESS   read-only
    STATUS       current
    DESCRIPTION
        "Cisco Firepower adaptor:EthPortErrStatsHist:badLengthPackets
        managed object property"
    ::= { cfprAdaptorEthPortErrStatsHistEntry 9 }

cfprAdaptorEthPortErrStatsHistBadLengthPacketsDelta OBJECT-TYPE
    SYNTAX       Unsigned64
    MAX-ACCESS   read-only
    STATUS       current
    DESCRIPTION
        "Cisco Firepower adaptor:EthPortErrStatsHist:badLengthPacketsDelta
         managed object property"
    ::= { cfprAdaptorEthPortErrStatsHistEntry 10 }

cfprAdaptorEthPortErrStatsHistBadLengthPacketsDeltaAvg OBJECT-TYPE
    SYNTAX       Unsigned64
    MAX-ACCESS   read-only
    STATUS       current
    DESCRIPTION
        "Cisco Firepower adaptor:EthPortErrStatsHist:badLengthPacketsDelta
        Avg managed object property"
    ::= { cfprAdaptorEthPortErrStatsHistEntry 11 }

cfprAdaptorEthPortErrStatsHistBadLengthPacketsDeltaMax OBJECT-TYPE
    SYNTAX       Unsigned64
    MAX-ACCESS   read-only
    STATUS       current
    DESCRIPTION
        "Cisco Firepower adaptor:EthPortErrStatsHist:badLengthPacketsDelta
        Max managed object property"
    ::= { cfprAdaptorEthPortErrStatsHistEntry 12 }

cfprAdaptorEthPortErrStatsHistBadLengthPacketsDeltaMin OBJECT-TYPE
    SYNTAX       Unsigned64
    MAX-ACCESS   read-only
    STATUS       current
    DESCRIPTION
        "Cisco Firepower adaptor:EthPortErrStatsHist:badLengthPacketsDelta
        Min managed object property"
    ::= { cfprAdaptorEthPortErrStatsHistEntry 13 }

cfprAdaptorEthPortErrStatsHistId OBJECT-TYPE
    SYNTAX       Unsigned64
    MAX-ACCESS   read-only
    STATUS       current
    DESCRIPTION
        "Cisco Firepower adaptor:EthPortErrStatsHist:id
        managed object property"
    ::= { cfprAdaptorEthPortErrStatsHistEntry 14 }

cfprAdaptorEthPortErrStatsHistMacDiscardedPackets OBJECT-TYPE
    SYNTAX       Unsigned64
    MAX-ACCESS   read-only
    STATUS       current
    DESCRIPTION
        "Cisco Firepower adaptor:EthPortErrStatsHist:macDiscardedPackets
        managed object property"
    ::= { cfprAdaptorEthPortErrStatsHistEntry 15 }

cfprAdaptorEthPortErrStatsHistMacDiscardedPacketsDelta OBJECT-TYPE
    SYNTAX       Unsigned64
    MAX-ACCESS   read-only
    STATUS       current
    DESCRIPTION
        "Cisco Firepower adaptor:EthPortErrStatsHist:macDiscardedPacketsDe
        lta managed object property"
    ::= { cfprAdaptorEthPortErrStatsHistEntry 16 }

cfprAdaptorEthPortErrStatsHistMacDiscardedPacketsDeltaAvg OBJECT-TYPE
    SYNTAX       Unsigned64
    MAX-ACCESS   read-only
    STATUS       current
    DESCRIPTION
        "Cisco Firepower adaptor:EthPortErrStatsHist:macDiscardedPacketsDe
        ltaAvg managed object property"
    ::= { cfprAdaptorEthPortErrStatsHistEntry 17 }

cfprAdaptorEthPortErrStatsHistMacDiscardedPacketsDeltaMax OBJECT-TYPE
    SYNTAX       Unsigned64
    MAX-ACCESS   read-only
    STATUS       current
    DESCRIPTION
        "Cisco Firepower adaptor:EthPortErrStatsHist:macDiscardedPacketsDe
        ltaMax managed object property"
    ::= { cfprAdaptorEthPortErrStatsHistEntry 18 }

cfprAdaptorEthPortErrStatsHistMacDiscardedPacketsDeltaMin OBJECT-TYPE
    SYNTAX       Unsigned64
    MAX-ACCESS   read-only
    STATUS       current
    DESCRIPTION
        "Cisco Firepower adaptor:EthPortErrStatsHist:macDiscardedPacketsDe
        ltaMin managed object property"
    ::= { cfprAdaptorEthPortErrStatsHistEntry 19 }

cfprAdaptorEthPortErrStatsHistMostRecent OBJECT-TYPE
    SYNTAX       TruthValue
    MAX-ACCESS   read-only
    STATUS       current
    DESCRIPTION
        "Cisco Firepower adaptor:EthPortErrStatsHist:mostRecent
        managed object property"
    ::= { cfprAdaptorEthPortErrStatsHistEntry 20 }

cfprAdaptorEthPortErrStatsHistSuspect OBJECT-TYPE
    SYNTAX       TruthValue
    MAX-ACCESS   read-only
    STATUS       current
    DESCRIPTION
        "Cisco Firepower adaptor:EthPortErrStatsHist:suspect
        managed object property"
    ::= { cfprAdaptorEthPortErrStatsHistEntry 21 }

cfprAdaptorEthPortErrStatsHistThresholded OBJECT-TYPE
    SYNTAX       CfprAdaptorEthPortErrStatsHistThresholded
    MAX-ACCESS   read-only
    STATUS       current
    DESCRIPTION
        "Cisco Firepower adaptor:EthPortErrStatsHist:thresholded
        managed object property"
    ::= { cfprAdaptorEthPortErrStatsHistEntry 22 }

cfprAdaptorEthPortErrStatsHistTimeCollected OBJECT-TYPE
    SYNTAX       DateAndTime
    MAX-ACCESS   read-only
    STATUS       current
    DESCRIPTION
        "Cisco Firepower adaptor:EthPortErrStatsHist:timeCollected
        managed object property"
    ::= { cfprAdaptorEthPortErrStatsHistEntry 23 }

cfprAdaptorEthPortMcastStatsTable OBJECT-TYPE
    SYNTAX           SEQUENCE OF CfprAdaptorEthPortMcastStatsEntry
    MAX-ACCESS       not-accessible
    STATUS           current
    DESCRIPTION
        "Cisco Firepower adaptor:EthPortMcastStats managed object table"
    ::= { cfprAdaptorObjects 16 }

cfprAdaptorEthPortMcastStatsEntry OBJECT-TYPE
    SYNTAX           CfprAdaptorEthPortMcastStatsEntry
    MAX-ACCESS       not-accessible
    STATUS           current
    DESCRIPTION
        "Entry for the cfprAdaptorEthPortMcastStatsTable table."
    INDEX { cfprAdaptorEthPortMcastStatsInstanceId }
    ::= { cfprAdaptorEthPortMcastStatsTable 1 }

CfprAdaptorEthPortMcastStatsEntry ::= SEQUENCE {
    cfprAdaptorEthPortMcastStatsInstanceId                           CfprManagedObjectId,
    cfprAdaptorEthPortMcastStatsDn                                   CfprManagedObjectDn,
    cfprAdaptorEthPortMcastStatsRn                                   SnmpAdminString,
    cfprAdaptorEthPortMcastStatsBroadcastPackets                     Unsigned64,
    cfprAdaptorEthPortMcastStatsBroadcastPacketsDelta                Counter64,
    cfprAdaptorEthPortMcastStatsBroadcastPacketsDeltaAvg             Unsigned64,
    cfprAdaptorEthPortMcastStatsBroadcastPacketsDeltaMax             Unsigned64,
    cfprAdaptorEthPortMcastStatsBroadcastPacketsDeltaMin             Unsigned64,
    cfprAdaptorEthPortMcastStatsIntervals                            Gauge32,
    cfprAdaptorEthPortMcastStatsMulticastPackets                     Unsigned64,
    cfprAdaptorEthPortMcastStatsMulticastPacketsDelta                Counter64,
    cfprAdaptorEthPortMcastStatsMulticastPacketsDeltaAvg             Unsigned64,
    cfprAdaptorEthPortMcastStatsMulticastPacketsDeltaMax             Unsigned64,
    cfprAdaptorEthPortMcastStatsMulticastPacketsDeltaMin             Unsigned64,
    cfprAdaptorEthPortMcastStatsSuspect                              TruthValue,
    cfprAdaptorEthPortMcastStatsThresholded                          CfprAdaptorEthPortMcastStatsThresholded,
    cfprAdaptorEthPortMcastStatsTimeCollected                        DateAndTime,
    cfprAdaptorEthPortMcastStatsTrafficDirection                     CfprAdaptorAdapterStatsTrafficDir,
    cfprAdaptorEthPortMcastStatsUnicastPackets                       Unsigned64,
    cfprAdaptorEthPortMcastStatsUnicastPacketsDelta                  Counter64,
    cfprAdaptorEthPortMcastStatsUnicastPacketsDeltaAvg               Unsigned64,
    cfprAdaptorEthPortMcastStatsUnicastPacketsDeltaMax               Unsigned64,
    cfprAdaptorEthPortMcastStatsUnicastPacketsDeltaMin               Unsigned64,
    cfprAdaptorEthPortMcastStatsUpdate                               Gauge32
}

cfprAdaptorEthPortMcastStatsInstanceId OBJECT-TYPE
    SYNTAX       CfprManagedObjectId
    MAX-ACCESS   not-accessible
    STATUS       current
    DESCRIPTION
        "Instance identifier of the managed object."
    ::= { cfprAdaptorEthPortMcastStatsEntry 1 }

cfprAdaptorEthPortMcastStatsDn OBJECT-TYPE
    SYNTAX       CfprManagedObjectDn
    MAX-ACCESS   read-only
    STATUS       current
    DESCRIPTION
        "Cisco Firepower adaptor:EthPortMcastStats:dn managed
        object property"
    ::= { cfprAdaptorEthPortMcastStatsEntry 2 }

cfprAdaptorEthPortMcastStatsRn OBJECT-TYPE
    SYNTAX       SnmpAdminString
    MAX-ACCESS   read-only
    STATUS       current
    DESCRIPTION
        "Cisco Firepower adaptor:EthPortMcastStats:rn managed
        object property"
    ::= { cfprAdaptorEthPortMcastStatsEntry 3 }

cfprAdaptorEthPortMcastStatsBroadcastPackets OBJECT-TYPE
    SYNTAX       Unsigned64
    MAX-ACCESS   read-only
    STATUS       current
    DESCRIPTION
        "Cisco Firepower adaptor:EthPortMcastStats:broadcastPackets
        managed object property"
    ::= { cfprAdaptorEthPortMcastStatsEntry 4 }

cfprAdaptorEthPortMcastStatsBroadcastPacketsDelta OBJECT-TYPE
    SYNTAX       Counter64
    MAX-ACCESS   read-only
    STATUS       current
    DESCRIPTION
        "Cisco Firepower adaptor:EthPortMcastStats:broadcastPacketsDelta
        managed object property"
    ::= { cfprAdaptorEthPortMcastStatsEntry 5 }

cfprAdaptorEthPortMcastStatsBroadcastPacketsDeltaAvg OBJECT-TYPE
    SYNTAX       Unsigned64
    MAX-ACCESS   read-only
    STATUS       current
    DESCRIPTION
        "Cisco Firepower adaptor:EthPortMcastStats:broadcastPacketsDeltaAv
        g managed object property"
    ::= { cfprAdaptorEthPortMcastStatsEntry 6 }

cfprAdaptorEthPortMcastStatsBroadcastPacketsDeltaMax OBJECT-TYPE
    SYNTAX       Unsigned64
    MAX-ACCESS   read-only
    STATUS       current
    DESCRIPTION
        "Cisco Firepower adaptor:EthPortMcastStats:broadcastPacketsDeltaMa
        x managed object property"
    ::= { cfprAdaptorEthPortMcastStatsEntry 7 }

cfprAdaptorEthPortMcastStatsBroadcastPacketsDeltaMin OBJECT-TYPE
    SYNTAX       Unsigned64
    MAX-ACCESS   read-only
    STATUS       current
    DESCRIPTION
        "Cisco Firepower adaptor:EthPortMcastStats:broadcastPacketsDeltaMi
        n managed object property"
    ::= { cfprAdaptorEthPortMcastStatsEntry 8 }

cfprAdaptorEthPortMcastStatsIntervals OBJECT-TYPE
    SYNTAX       Gauge32
    MAX-ACCESS   read-only
    STATUS       current
    DESCRIPTION
        "Cisco Firepower adaptor:EthPortMcastStats:intervals
        managed object property"
    ::= { cfprAdaptorEthPortMcastStatsEntry 9 }

cfprAdaptorEthPortMcastStatsMulticastPackets OBJECT-TYPE
    SYNTAX       Unsigned64
    MAX-ACCESS   read-only
    STATUS       current
    DESCRIPTION
        "Cisco Firepower adaptor:EthPortMcastStats:multicastPackets
        managed object property"
    ::= { cfprAdaptorEthPortMcastStatsEntry 10 }

cfprAdaptorEthPortMcastStatsMulticastPacketsDelta OBJECT-TYPE
    SYNTAX       Counter64
    MAX-ACCESS   read-only
    STATUS       current
    DESCRIPTION
        "Cisco Firepower adaptor:EthPortMcastStats:multicastPacketsDelta
        managed object property"
    ::= { cfprAdaptorEthPortMcastStatsEntry 11 }

cfprAdaptorEthPortMcastStatsMulticastPacketsDeltaAvg OBJECT-TYPE
    SYNTAX       Unsigned64
    MAX-ACCESS   read-only
    STATUS       current
    DESCRIPTION
        "Cisco Firepower adaptor:EthPortMcastStats:multicastPacketsDeltaAv
        g managed object property"
    ::= { cfprAdaptorEthPortMcastStatsEntry 12 }

cfprAdaptorEthPortMcastStatsMulticastPacketsDeltaMax OBJECT-TYPE
    SYNTAX       Unsigned64
    MAX-ACCESS   read-only
    STATUS       current
    DESCRIPTION
        "Cisco Firepower adaptor:EthPortMcastStats:multicastPacketsDeltaMa
        x managed object property"
    ::= { cfprAdaptorEthPortMcastStatsEntry 13 }

cfprAdaptorEthPortMcastStatsMulticastPacketsDeltaMin OBJECT-TYPE
    SYNTAX       Unsigned64
    MAX-ACCESS   read-only
    STATUS       current
    DESCRIPTION
        "Cisco Firepower adaptor:EthPortMcastStats:multicastPacketsDeltaMi
        n managed object property"
    ::= { cfprAdaptorEthPortMcastStatsEntry 14 }

cfprAdaptorEthPortMcastStatsSuspect OBJECT-TYPE
    SYNTAX       TruthValue
    MAX-ACCESS   read-only
    STATUS       current
    DESCRIPTION
        "Cisco Firepower adaptor:EthPortMcastStats:suspect
        managed object property"
    ::= { cfprAdaptorEthPortMcastStatsEntry 15 }

cfprAdaptorEthPortMcastStatsThresholded OBJECT-TYPE
    SYNTAX       CfprAdaptorEthPortMcastStatsThresholded
    MAX-ACCESS   read-only
    STATUS       current
    DESCRIPTION
        "Cisco Firepower adaptor:EthPortMcastStats:thresholded
        managed object property"
    ::= { cfprAdaptorEthPortMcastStatsEntry 16 }

cfprAdaptorEthPortMcastStatsTimeCollected OBJECT-TYPE
    SYNTAX       DateAndTime
    MAX-ACCESS   read-only
    STATUS       current
    DESCRIPTION
        "Cisco Firepower adaptor:EthPortMcastStats:timeCollected
        managed object property"
    ::= { cfprAdaptorEthPortMcastStatsEntry 17 }

cfprAdaptorEthPortMcastStatsTrafficDirection OBJECT-TYPE
    SYNTAX       CfprAdaptorAdapterStatsTrafficDir
    MAX-ACCESS   read-only
    STATUS       current
    DESCRIPTION
        "Cisco Firepower adaptor:EthPortMcastStats:trafficDirection
        managed object property"
    ::= { cfprAdaptorEthPortMcastStatsEntry 18 }

cfprAdaptorEthPortMcastStatsUnicastPackets OBJECT-TYPE
    SYNTAX       Unsigned64
    MAX-ACCESS   read-only
    STATUS       current
    DESCRIPTION
        "Cisco Firepower adaptor:EthPortMcastStats:unicastPackets
        managed object property"
    ::= { cfprAdaptorEthPortMcastStatsEntry 19 }

cfprAdaptorEthPortMcastStatsUnicastPacketsDelta OBJECT-TYPE
    SYNTAX       Counter64
    MAX-ACCESS   read-only
    STATUS       current
    DESCRIPTION
        "Cisco Firepower adaptor:EthPortMcastStats:unicastPacketsDelta
        managed object property"
    ::= { cfprAdaptorEthPortMcastStatsEntry 20 }

cfprAdaptorEthPortMcastStatsUnicastPacketsDeltaAvg OBJECT-TYPE
    SYNTAX       Unsigned64
    MAX-ACCESS   read-only
    STATUS       current
    DESCRIPTION
        "Cisco Firepower adaptor:EthPortMcastStats:unicastPacketsDeltaAvg
        managed object property"
    ::= { cfprAdaptorEthPortMcastStatsEntry 21 }

cfprAdaptorEthPortMcastStatsUnicastPacketsDeltaMax OBJECT-TYPE
    SYNTAX       Unsigned64
    MAX-ACCESS   read-only
    STATUS       current
    DESCRIPTION
        "Cisco Firepower adaptor:EthPortMcastStats:unicastPacketsDeltaMax
        managed object property"
    ::= { cfprAdaptorEthPortMcastStatsEntry 22 }

cfprAdaptorEthPortMcastStatsUnicastPacketsDeltaMin OBJECT-TYPE
    SYNTAX       Unsigned64
    MAX-ACCESS   read-only
    STATUS       current
    DESCRIPTION
        "Cisco Firepower adaptor:EthPortMcastStats:unicastPacketsDeltaMin
        managed object property"
    ::= { cfprAdaptorEthPortMcastStatsEntry 23 }

cfprAdaptorEthPortMcastStatsUpdate OBJECT-TYPE
    SYNTAX       Gauge32
    MAX-ACCESS   read-only
    STATUS       current
    DESCRIPTION
        "Cisco Firepower adaptor:EthPortMcastStats:update
        managed object property"
    ::= { cfprAdaptorEthPortMcastStatsEntry 24 }

cfprAdaptorEthPortMcastStatsHistTable OBJECT-TYPE
    SYNTAX           SEQUENCE OF CfprAdaptorEthPortMcastStatsHistEntry
    MAX-ACCESS       not-accessible
    STATUS           current
    DESCRIPTION
        "Cisco Firepower adaptor:EthPortMcastStatsHist
        managed object table"
    ::= { cfprAdaptorObjects 17 }

cfprAdaptorEthPortMcastStatsHistEntry OBJECT-TYPE
    SYNTAX           CfprAdaptorEthPortMcastStatsHistEntry
    MAX-ACCESS       not-accessible
    STATUS           current
    DESCRIPTION
        "Entry for the cfprAdaptorEthPortMcastStatsHistTable table."
    INDEX { cfprAdaptorEthPortMcastStatsHistInstanceId }
    ::= { cfprAdaptorEthPortMcastStatsHistTable 1 }

CfprAdaptorEthPortMcastStatsHistEntry ::= SEQUENCE {
    cfprAdaptorEthPortMcastStatsHistInstanceId                       CfprManagedObjectId,
    cfprAdaptorEthPortMcastStatsHistDn                               CfprManagedObjectDn,
    cfprAdaptorEthPortMcastStatsHistRn                               SnmpAdminString,
    cfprAdaptorEthPortMcastStatsHistBroadcastPackets                 Unsigned64,
    cfprAdaptorEthPortMcastStatsHistBroadcastPacketsDelta            Unsigned64,
    cfprAdaptorEthPortMcastStatsHistBroadcastPacketsDeltaAvg         Unsigned64,
    cfprAdaptorEthPortMcastStatsHistBroadcastPacketsDeltaMax         Unsigned64,
    cfprAdaptorEthPortMcastStatsHistBroadcastPacketsDeltaMin         Unsigned64,
    cfprAdaptorEthPortMcastStatsHistId                               Unsigned64,
    cfprAdaptorEthPortMcastStatsHistMostRecent                       TruthValue,
    cfprAdaptorEthPortMcastStatsHistMulticastPackets                 Unsigned64,
    cfprAdaptorEthPortMcastStatsHistMulticastPacketsDelta            Unsigned64,
    cfprAdaptorEthPortMcastStatsHistMulticastPacketsDeltaAvg         Unsigned64,
    cfprAdaptorEthPortMcastStatsHistMulticastPacketsDeltaMax         Unsigned64,
    cfprAdaptorEthPortMcastStatsHistMulticastPacketsDeltaMin         Unsigned64,
    cfprAdaptorEthPortMcastStatsHistSuspect                          TruthValue,
    cfprAdaptorEthPortMcastStatsHistThresholded                      CfprAdaptorEthPortMcastStatsHistThresholded,
    cfprAdaptorEthPortMcastStatsHistTimeCollected                    DateAndTime,
    cfprAdaptorEthPortMcastStatsHistUnicastPackets                   Unsigned64,
    cfprAdaptorEthPortMcastStatsHistUnicastPacketsDelta              Unsigned64,
    cfprAdaptorEthPortMcastStatsHistUnicastPacketsDeltaAvg           Unsigned64,
    cfprAdaptorEthPortMcastStatsHistUnicastPacketsDeltaMax           Unsigned64,
    cfprAdaptorEthPortMcastStatsHistUnicastPacketsDeltaMin           Unsigned64
}

cfprAdaptorEthPortMcastStatsHistInstanceId OBJECT-TYPE
    SYNTAX       CfprManagedObjectId
    MAX-ACCESS   not-accessible
    STATUS       current
    DESCRIPTION
        "Instance identifier of the managed object."
    ::= { cfprAdaptorEthPortMcastStatsHistEntry 1 }

cfprAdaptorEthPortMcastStatsHistDn OBJECT-TYPE
    SYNTAX       CfprManagedObjectDn
    MAX-ACCESS   read-only
    STATUS       current
    DESCRIPTION
        "Cisco Firepower adaptor:EthPortMcastStatsHist:dn
        managed object property"
    ::= { cfprAdaptorEthPortMcastStatsHistEntry 2 }

cfprAdaptorEthPortMcastStatsHistRn OBJECT-TYPE
    SYNTAX       SnmpAdminString
    MAX-ACCESS   read-only
    STATUS       current
    DESCRIPTION
        "Cisco Firepower adaptor:EthPortMcastStatsHist:rn
        managed object property"
    ::= { cfprAdaptorEthPortMcastStatsHistEntry 3 }

cfprAdaptorEthPortMcastStatsHistBroadcastPackets OBJECT-TYPE
    SYNTAX       Unsigned64
    MAX-ACCESS   read-only
    STATUS       current
    DESCRIPTION
        "Cisco Firepower adaptor:EthPortMcastStatsHist:broadcastPackets
        managed object property"
    ::= { cfprAdaptorEthPortMcastStatsHistEntry 4 }

cfprAdaptorEthPortMcastStatsHistBroadcastPacketsDelta OBJECT-TYPE
    SYNTAX       Unsigned64
    MAX-ACCESS   read-only
    STATUS       current
    DESCRIPTION
        "Cisco Firepower adaptor:EthPortMcastStatsHist:broadcastPacketsDel
        ta managed object property"
    ::= { cfprAdaptorEthPortMcastStatsHistEntry 5 }

cfprAdaptorEthPortMcastStatsHistBroadcastPacketsDeltaAvg OBJECT-TYPE
    SYNTAX       Unsigned64
    MAX-ACCESS   read-only
    STATUS       current
    DESCRIPTION
        "Cisco Firepower adaptor:EthPortMcastStatsHist:broadcastPacketsDel
        taAvg managed object property"
    ::= { cfprAdaptorEthPortMcastStatsHistEntry 6 }

cfprAdaptorEthPortMcastStatsHistBroadcastPacketsDeltaMax OBJECT-TYPE
    SYNTAX       Unsigned64
    MAX-ACCESS   read-only
    STATUS       current
    DESCRIPTION
        "Cisco Firepower adaptor:EthPortMcastStatsHist:broadcastPacketsDel
        taMax managed object property"
    ::= { cfprAdaptorEthPortMcastStatsHistEntry 7 }

cfprAdaptorEthPortMcastStatsHistBroadcastPacketsDeltaMin OBJECT-TYPE
    SYNTAX       Unsigned64
    MAX-ACCESS   read-only
    STATUS       current
    DESCRIPTION
        "Cisco Firepower adaptor:EthPortMcastStatsHist:broadcastPacketsDel
        taMin managed object property"
    ::= { cfprAdaptorEthPortMcastStatsHistEntry 8 }

cfprAdaptorEthPortMcastStatsHistId OBJECT-TYPE
    SYNTAX       Unsigned64
    MAX-ACCESS   read-only
    STATUS       current
    DESCRIPTION
        "Cisco Firepower adaptor:EthPortMcastStatsHist:id
        managed object property"
    ::= { cfprAdaptorEthPortMcastStatsHistEntry 9 }

cfprAdaptorEthPortMcastStatsHistMostRecent OBJECT-TYPE
    SYNTAX       TruthValue
    MAX-ACCESS   read-only
    STATUS       current
    DESCRIPTION
        "Cisco Firepower adaptor:EthPortMcastStatsHist:mostRecent
        managed object property"
    ::= { cfprAdaptorEthPortMcastStatsHistEntry 10 }

cfprAdaptorEthPortMcastStatsHistMulticastPackets OBJECT-TYPE
    SYNTAX       Unsigned64
    MAX-ACCESS   read-only
    STATUS       current
    DESCRIPTION
        "Cisco Firepower adaptor:EthPortMcastStatsHist:multicastPackets
        managed object property"
    ::= { cfprAdaptorEthPortMcastStatsHistEntry 11 }

cfprAdaptorEthPortMcastStatsHistMulticastPacketsDelta OBJECT-TYPE
    SYNTAX       Unsigned64
    MAX-ACCESS   read-only
    STATUS       current
    DESCRIPTION
        "Cisco Firepower adaptor:EthPortMcastStatsHist:multicastPacketsDel
        ta managed object property"
    ::= { cfprAdaptorEthPortMcastStatsHistEntry 12 }

cfprAdaptorEthPortMcastStatsHistMulticastPacketsDeltaAvg OBJECT-TYPE
    SYNTAX       Unsigned64
    MAX-ACCESS   read-only
    STATUS       current
    DESCRIPTION
        "Cisco Firepower adaptor:EthPortMcastStatsHist:multicastPacketsDel
        taAvg managed object property"
    ::= { cfprAdaptorEthPortMcastStatsHistEntry 13 }

cfprAdaptorEthPortMcastStatsHistMulticastPacketsDeltaMax OBJECT-TYPE
    SYNTAX       Unsigned64
    MAX-ACCESS   read-only
    STATUS       current
    DESCRIPTION
        "Cisco Firepower adaptor:EthPortMcastStatsHist:multicastPacketsDel
        taMax managed object property"
    ::= { cfprAdaptorEthPortMcastStatsHistEntry 14 }

cfprAdaptorEthPortMcastStatsHistMulticastPacketsDeltaMin OBJECT-TYPE
    SYNTAX       Unsigned64
    MAX-ACCESS   read-only
    STATUS       current
    DESCRIPTION
        "Cisco Firepower adaptor:EthPortMcastStatsHist:multicastPacketsDel
        taMin managed object property"
    ::= { cfprAdaptorEthPortMcastStatsHistEntry 15 }

cfprAdaptorEthPortMcastStatsHistSuspect OBJECT-TYPE
    SYNTAX       TruthValue
    MAX-ACCESS   read-only
    STATUS       current
    DESCRIPTION
        "Cisco Firepower adaptor:EthPortMcastStatsHist:suspect
        managed object property"
    ::= { cfprAdaptorEthPortMcastStatsHistEntry 16 }

cfprAdaptorEthPortMcastStatsHistThresholded OBJECT-TYPE
    SYNTAX       CfprAdaptorEthPortMcastStatsHistThresholded
    MAX-ACCESS   read-only
    STATUS       current
    DESCRIPTION
        "Cisco Firepower adaptor:EthPortMcastStatsHist:thresholded
        managed object property"
    ::= { cfprAdaptorEthPortMcastStatsHistEntry 17 }

cfprAdaptorEthPortMcastStatsHistTimeCollected OBJECT-TYPE
    SYNTAX       DateAndTime
    MAX-ACCESS   read-only
    STATUS       current
    DESCRIPTION
        "Cisco Firepower adaptor:EthPortMcastStatsHist:timeCollected
        managed object property"
    ::= { cfprAdaptorEthPortMcastStatsHistEntry 18 }

cfprAdaptorEthPortMcastStatsHistUnicastPackets OBJECT-TYPE
    SYNTAX       Unsigned64
    MAX-ACCESS   read-only
    STATUS       current
    DESCRIPTION
        "Cisco Firepower adaptor:EthPortMcastStatsHist:unicastPackets
        managed object property"
    ::= { cfprAdaptorEthPortMcastStatsHistEntry 19 }

cfprAdaptorEthPortMcastStatsHistUnicastPacketsDelta OBJECT-TYPE
    SYNTAX       Unsigned64
    MAX-ACCESS   read-only
    STATUS       current
    DESCRIPTION
        "Cisco Firepower adaptor:EthPortMcastStatsHist:unicastPacketsDelta
         managed object property"
    ::= { cfprAdaptorEthPortMcastStatsHistEntry 20 }

cfprAdaptorEthPortMcastStatsHistUnicastPacketsDeltaAvg OBJECT-TYPE
    SYNTAX       Unsigned64
    MAX-ACCESS   read-only
    STATUS       current
    DESCRIPTION
        "Cisco Firepower adaptor:EthPortMcastStatsHist:unicastPacketsDelta
        Avg managed object property"
    ::= { cfprAdaptorEthPortMcastStatsHistEntry 21 }

cfprAdaptorEthPortMcastStatsHistUnicastPacketsDeltaMax OBJECT-TYPE
    SYNTAX       Unsigned64
    MAX-ACCESS   read-only
    STATUS       current
    DESCRIPTION
        "Cisco Firepower adaptor:EthPortMcastStatsHist:unicastPacketsDelta
        Max managed object property"
    ::= { cfprAdaptorEthPortMcastStatsHistEntry 22 }

cfprAdaptorEthPortMcastStatsHistUnicastPacketsDeltaMin OBJECT-TYPE
    SYNTAX       Unsigned64
    MAX-ACCESS   read-only
    STATUS       current
    DESCRIPTION
        "Cisco Firepower adaptor:EthPortMcastStatsHist:unicastPacketsDelta
        Min managed object property"
    ::= { cfprAdaptorEthPortMcastStatsHistEntry 23 }

cfprAdaptorEthPortOutsizedStatsTable OBJECT-TYPE
    SYNTAX           SEQUENCE OF CfprAdaptorEthPortOutsizedStatsEntry
    MAX-ACCESS       not-accessible
    STATUS           current
    DESCRIPTION
        "Cisco Firepower adaptor:EthPortOutsizedStats managed
        object table"
    ::= { cfprAdaptorObjects 18 }

cfprAdaptorEthPortOutsizedStatsEntry OBJECT-TYPE
    SYNTAX           CfprAdaptorEthPortOutsizedStatsEntry
    MAX-ACCESS       not-accessible
    STATUS           current
    DESCRIPTION
        "Entry for the cfprAdaptorEthPortOutsizedStatsTable table."
    INDEX { cfprAdaptorEthPortOutsizedStatsInstanceId }
    ::= { cfprAdaptorEthPortOutsizedStatsTable 1 }

CfprAdaptorEthPortOutsizedStatsEntry ::= SEQUENCE {
    cfprAdaptorEthPortOutsizedStatsInstanceId                        CfprManagedObjectId,
    cfprAdaptorEthPortOutsizedStatsDn                                CfprManagedObjectDn,
    cfprAdaptorEthPortOutsizedStatsRn                                SnmpAdminString,
    cfprAdaptorEthPortOutsizedStatsIntervals                         Gauge32,
    cfprAdaptorEthPortOutsizedStatsOversizedBadCrcPackets            Unsigned64,
    cfprAdaptorEthPortOutsizedStatsOversizedBadCrcPacketsDelta       Counter64,
    cfprAdaptorEthPortOutsizedStatsOversizedBadCrcPacketsDeltaAvg    Unsigned64,
    cfprAdaptorEthPortOutsizedStatsOversizedBadCrcPacketsDeltaMax    Unsigned64,
    cfprAdaptorEthPortOutsizedStatsOversizedBadCrcPacketsDeltaMin    Unsigned64,
    cfprAdaptorEthPortOutsizedStatsOversizedGoodCrcPackets           Unsigned64,
    cfprAdaptorEthPortOutsizedStatsOversizedGoodCrcPacketsDelta      Counter64,
    cfprAdaptorEthPortOutsizedStatsOversizedGoodCrcPacketsDeltaAvg   Unsigned64,
    cfprAdaptorEthPortOutsizedStatsOversizedGoodCrcPacketsDeltaMax   Unsigned64,
    cfprAdaptorEthPortOutsizedStatsOversizedGoodCrcPacketsDeltaMin   Unsigned64,
    cfprAdaptorEthPortOutsizedStatsOversizedPackets                  Unsigned64,
    cfprAdaptorEthPortOutsizedStatsOversizedPacketsDelta             Counter64,
    cfprAdaptorEthPortOutsizedStatsOversizedPacketsDeltaAvg          Unsigned64,
    cfprAdaptorEthPortOutsizedStatsOversizedPacketsDeltaMax          Unsigned64,
    cfprAdaptorEthPortOutsizedStatsOversizedPacketsDeltaMin          Unsigned64,
    cfprAdaptorEthPortOutsizedStatsSuspect                           TruthValue,
    cfprAdaptorEthPortOutsizedStatsThresholded                       CfprAdaptorEthPortOutsizedStatsThresholded,
    cfprAdaptorEthPortOutsizedStatsTimeCollected                     DateAndTime,
    cfprAdaptorEthPortOutsizedStatsTrafficDirection                  CfprAdaptorAdapterStatsTrafficDir,
    cfprAdaptorEthPortOutsizedStatsUndersizedBadCrcPackets           Unsigned64,
    cfprAdaptorEthPortOutsizedStatsUndersizedBadCrcPacketsDelta      Counter64,
    cfprAdaptorEthPortOutsizedStatsUndersizedBadCrcPacketsDeltaAvg   Unsigned64,
    cfprAdaptorEthPortOutsizedStatsUndersizedBadCrcPacketsDeltaMax   Unsigned64,
    cfprAdaptorEthPortOutsizedStatsUndersizedBadCrcPacketsDeltaMin   Unsigned64,
    cfprAdaptorEthPortOutsizedStatsUndersizedGoodCrcPackets          Unsigned64,
    cfprAdaptorEthPortOutsizedStatsUndersizedGoodCrcPacketsDelta     Counter64,
    cfprAdaptorEthPortOutsizedStatsUndersizedGoodCrcPacketsDeltaAvg  Unsigned64,
    cfprAdaptorEthPortOutsizedStatsUndersizedGoodCrcPacketsDeltaMax  Unsigned64,
    cfprAdaptorEthPortOutsizedStatsUndersizedGoodCrcPacketsDeltaMin  Unsigned64,
    cfprAdaptorEthPortOutsizedStatsUpdate                            Gauge32
}

cfprAdaptorEthPortOutsizedStatsInstanceId OBJECT-TYPE
    SYNTAX       CfprManagedObjectId
    MAX-ACCESS   not-accessible
    STATUS       current
    DESCRIPTION
        "Instance identifier of the managed object."
    ::= { cfprAdaptorEthPortOutsizedStatsEntry 1 }

cfprAdaptorEthPortOutsizedStatsDn OBJECT-TYPE
    SYNTAX       CfprManagedObjectDn
    MAX-ACCESS   read-only
    STATUS       current
    DESCRIPTION
        "Cisco Firepower adaptor:EthPortOutsizedStats:dn
        managed object property"
    ::= { cfprAdaptorEthPortOutsizedStatsEntry 2 }

cfprAdaptorEthPortOutsizedStatsRn OBJECT-TYPE
    SYNTAX       SnmpAdminString
    MAX-ACCESS   read-only
    STATUS       current
    DESCRIPTION
        "Cisco Firepower adaptor:EthPortOutsizedStats:rn
        managed object property"
    ::= { cfprAdaptorEthPortOutsizedStatsEntry 3 }

cfprAdaptorEthPortOutsizedStatsIntervals OBJECT-TYPE
    SYNTAX       Gauge32
    MAX-ACCESS   read-only
    STATUS       current
    DESCRIPTION
        "Cisco Firepower adaptor:EthPortOutsizedStats:intervals
        managed object property"
    ::= { cfprAdaptorEthPortOutsizedStatsEntry 4 }

cfprAdaptorEthPortOutsizedStatsOversizedBadCrcPackets OBJECT-TYPE
    SYNTAX       Unsigned64
    MAX-ACCESS   read-only
    STATUS       current
    DESCRIPTION
        "Cisco Firepower adaptor:EthPortOutsizedStats:oversizedBadCrcPacke
        ts managed object property"
    ::= { cfprAdaptorEthPortOutsizedStatsEntry 5 }

cfprAdaptorEthPortOutsizedStatsOversizedBadCrcPacketsDelta OBJECT-TYPE
    SYNTAX       Counter64
    MAX-ACCESS   read-only
    STATUS       current
    DESCRIPTION
        "Cisco Firepower adaptor:EthPortOutsizedStats:oversizedBadCrcPacke
        tsDelta managed object property"
    ::= { cfprAdaptorEthPortOutsizedStatsEntry 6 }

cfprAdaptorEthPortOutsizedStatsOversizedBadCrcPacketsDeltaAvg OBJECT-TYPE
    SYNTAX       Unsigned64
    MAX-ACCESS   read-only
    STATUS       current
    DESCRIPTION
        "Cisco Firepower adaptor:EthPortOutsizedStats:oversizedBadCrcPacke
        tsDeltaAvg managed object property"
    ::= { cfprAdaptorEthPortOutsizedStatsEntry 7 }

cfprAdaptorEthPortOutsizedStatsOversizedBadCrcPacketsDeltaMax OBJECT-TYPE
    SYNTAX       Unsigned64
    MAX-ACCESS   read-only
    STATUS       current
    DESCRIPTION
        "Cisco Firepower adaptor:EthPortOutsizedStats:oversizedBadCrcPacke
        tsDeltaMax managed object property"
    ::= { cfprAdaptorEthPortOutsizedStatsEntry 8 }

cfprAdaptorEthPortOutsizedStatsOversizedBadCrcPacketsDeltaMin OBJECT-TYPE
    SYNTAX       Unsigned64
    MAX-ACCESS   read-only
    STATUS       current
    DESCRIPTION
        "Cisco Firepower adaptor:EthPortOutsizedStats:oversizedBadCrcPacke
        tsDeltaMin managed object property"
    ::= { cfprAdaptorEthPortOutsizedStatsEntry 9 }

cfprAdaptorEthPortOutsizedStatsOversizedGoodCrcPackets OBJECT-TYPE
    SYNTAX       Unsigned64
    MAX-ACCESS   read-only
    STATUS       current
    DESCRIPTION
        "Cisco Firepower adaptor:EthPortOutsizedStats:oversizedGoodCrcPack
        ets managed object property"
    ::= { cfprAdaptorEthPortOutsizedStatsEntry 10 }

cfprAdaptorEthPortOutsizedStatsOversizedGoodCrcPacketsDelta OBJECT-TYPE
    SYNTAX       Counter64
    MAX-ACCESS   read-only
    STATUS       current
    DESCRIPTION
        "Cisco Firepower adaptor:EthPortOutsizedStats:oversizedGoodCrcPack
        etsDelta managed object property"
    ::= { cfprAdaptorEthPortOutsizedStatsEntry 11 }

cfprAdaptorEthPortOutsizedStatsOversizedGoodCrcPacketsDeltaAvg OBJECT-TYPE
    SYNTAX       Unsigned64
    MAX-ACCESS   read-only
    STATUS       current
    DESCRIPTION
        "Cisco Firepower adaptor:EthPortOutsizedStats:oversizedGoodCrcPack
        etsDeltaAvg managed object property"
    ::= { cfprAdaptorEthPortOutsizedStatsEntry 12 }

cfprAdaptorEthPortOutsizedStatsOversizedGoodCrcPacketsDeltaMax OBJECT-TYPE
    SYNTAX       Unsigned64
    MAX-ACCESS   read-only
    STATUS       current
    DESCRIPTION
        "Cisco Firepower adaptor:EthPortOutsizedStats:oversizedGoodCrcPack
        etsDeltaMax managed object property"
    ::= { cfprAdaptorEthPortOutsizedStatsEntry 13 }

cfprAdaptorEthPortOutsizedStatsOversizedGoodCrcPacketsDeltaMin OBJECT-TYPE
    SYNTAX       Unsigned64
    MAX-ACCESS   read-only
    STATUS       current
    DESCRIPTION
        "Cisco Firepower adaptor:EthPortOutsizedStats:oversizedGoodCrcPack
        etsDeltaMin managed object property"
    ::= { cfprAdaptorEthPortOutsizedStatsEntry 14 }

cfprAdaptorEthPortOutsizedStatsOversizedPackets OBJECT-TYPE
    SYNTAX       Unsigned64
    MAX-ACCESS   read-only
    STATUS       current
    DESCRIPTION
        "Cisco Firepower adaptor:EthPortOutsizedStats:oversizedPackets
        managed object property"
    ::= { cfprAdaptorEthPortOutsizedStatsEntry 15 }

cfprAdaptorEthPortOutsizedStatsOversizedPacketsDelta OBJECT-TYPE
    SYNTAX       Counter64
    MAX-ACCESS   read-only
    STATUS       current
    DESCRIPTION
        "Cisco Firepower adaptor:EthPortOutsizedStats:oversizedPacketsDelt
        a managed object property"
    ::= { cfprAdaptorEthPortOutsizedStatsEntry 16 }

cfprAdaptorEthPortOutsizedStatsOversizedPacketsDeltaAvg OBJECT-TYPE
    SYNTAX       Unsigned64
    MAX-ACCESS   read-only
    STATUS       current
    DESCRIPTION
        "Cisco Firepower adaptor:EthPortOutsizedStats:oversizedPacketsDelt
        aAvg managed object property"
    ::= { cfprAdaptorEthPortOutsizedStatsEntry 17 }

cfprAdaptorEthPortOutsizedStatsOversizedPacketsDeltaMax OBJECT-TYPE
    SYNTAX       Unsigned64
    MAX-ACCESS   read-only
    STATUS       current
    DESCRIPTION
        "Cisco Firepower adaptor:EthPortOutsizedStats:oversizedPacketsDelt
        aMax managed object property"
    ::= { cfprAdaptorEthPortOutsizedStatsEntry 18 }

cfprAdaptorEthPortOutsizedStatsOversizedPacketsDeltaMin OBJECT-TYPE
    SYNTAX       Unsigned64
    MAX-ACCESS   read-only
    STATUS       current
    DESCRIPTION
        "Cisco Firepower adaptor:EthPortOutsizedStats:oversizedPacketsDelt
        aMin managed object property"
    ::= { cfprAdaptorEthPortOutsizedStatsEntry 19 }

cfprAdaptorEthPortOutsizedStatsSuspect OBJECT-TYPE
    SYNTAX       TruthValue
    MAX-ACCESS   read-only
    STATUS       current
    DESCRIPTION
        "Cisco Firepower adaptor:EthPortOutsizedStats:suspect
        managed object property"
    ::= { cfprAdaptorEthPortOutsizedStatsEntry 20 }

cfprAdaptorEthPortOutsizedStatsThresholded OBJECT-TYPE
    SYNTAX       CfprAdaptorEthPortOutsizedStatsThresholded
    MAX-ACCESS   read-only
    STATUS       current
    DESCRIPTION
        "Cisco Firepower adaptor:EthPortOutsizedStats:thresholded
        managed object property"
    ::= { cfprAdaptorEthPortOutsizedStatsEntry 21 }

cfprAdaptorEthPortOutsizedStatsTimeCollected OBJECT-TYPE
    SYNTAX       DateAndTime
    MAX-ACCESS   read-only
    STATUS       current
    DESCRIPTION
        "Cisco Firepower adaptor:EthPortOutsizedStats:timeCollected
        managed object property"
    ::= { cfprAdaptorEthPortOutsizedStatsEntry 22 }

cfprAdaptorEthPortOutsizedStatsTrafficDirection OBJECT-TYPE
    SYNTAX       CfprAdaptorAdapterStatsTrafficDir
    MAX-ACCESS   read-only
    STATUS       current
    DESCRIPTION
        "Cisco Firepower adaptor:EthPortOutsizedStats:trafficDirection
        managed object property"
    ::= { cfprAdaptorEthPortOutsizedStatsEntry 23 }

cfprAdaptorEthPortOutsizedStatsUndersizedBadCrcPackets OBJECT-TYPE
    SYNTAX       Unsigned64
    MAX-ACCESS   read-only
    STATUS       current
    DESCRIPTION
        "Cisco Firepower adaptor:EthPortOutsizedStats:undersizedBadCrcPack
        ets managed object property"
    ::= { cfprAdaptorEthPortOutsizedStatsEntry 24 }

cfprAdaptorEthPortOutsizedStatsUndersizedBadCrcPacketsDelta OBJECT-TYPE
    SYNTAX       Counter64
    MAX-ACCESS   read-only
    STATUS       current
    DESCRIPTION
        "Cisco Firepower adaptor:EthPortOutsizedStats:undersizedBadCrcPack
        etsDelta managed object property"
    ::= { cfprAdaptorEthPortOutsizedStatsEntry 25 }

cfprAdaptorEthPortOutsizedStatsUndersizedBadCrcPacketsDeltaAvg OBJECT-TYPE
    SYNTAX       Unsigned64
    MAX-ACCESS   read-only
    STATUS       current
    DESCRIPTION
        "Cisco Firepower adaptor:EthPortOutsizedStats:undersizedBadCrcPack
        etsDeltaAvg managed object property"
    ::= { cfprAdaptorEthPortOutsizedStatsEntry 26 }

cfprAdaptorEthPortOutsizedStatsUndersizedBadCrcPacketsDeltaMax OBJECT-TYPE
    SYNTAX       Unsigned64
    MAX-ACCESS   read-only
    STATUS       current
    DESCRIPTION
        "Cisco Firepower adaptor:EthPortOutsizedStats:undersizedBadCrcPack
        etsDeltaMax managed object property"
    ::= { cfprAdaptorEthPortOutsizedStatsEntry 27 }

cfprAdaptorEthPortOutsizedStatsUndersizedBadCrcPacketsDeltaMin OBJECT-TYPE
    SYNTAX       Unsigned64
    MAX-ACCESS   read-only
    STATUS       current
    DESCRIPTION
        "Cisco Firepower adaptor:EthPortOutsizedStats:undersizedBadCrcPack
        etsDeltaMin managed object property"
    ::= { cfprAdaptorEthPortOutsizedStatsEntry 28 }

cfprAdaptorEthPortOutsizedStatsUndersizedGoodCrcPackets OBJECT-TYPE
    SYNTAX       Unsigned64
    MAX-ACCESS   read-only
    STATUS       current
    DESCRIPTION
        "Cisco Firepower adaptor:EthPortOutsizedStats:undersizedGoodCrcPac
        kets managed object property"
    ::= { cfprAdaptorEthPortOutsizedStatsEntry 29 }

cfprAdaptorEthPortOutsizedStatsUndersizedGoodCrcPacketsDelta OBJECT-TYPE
    SYNTAX       Counter64
    MAX-ACCESS   read-only
    STATUS       current
    DESCRIPTION
        "Cisco Firepower adaptor:EthPortOutsizedStats:undersizedGoodCrcPac
        ketsDelta managed object property"
    ::= { cfprAdaptorEthPortOutsizedStatsEntry 30 }

cfprAdaptorEthPortOutsizedStatsUndersizedGoodCrcPacketsDeltaAvg OBJECT-TYPE
    SYNTAX       Unsigned64
    MAX-ACCESS   read-only
    STATUS       current
    DESCRIPTION
        "Cisco Firepower adaptor:EthPortOutsizedStats:undersizedGoodCrcPac
        ketsDeltaAvg managed object property"
    ::= { cfprAdaptorEthPortOutsizedStatsEntry 31 }

cfprAdaptorEthPortOutsizedStatsUndersizedGoodCrcPacketsDeltaMax OBJECT-TYPE
    SYNTAX       Unsigned64
    MAX-ACCESS   read-only
    STATUS       current
    DESCRIPTION
        "Cisco Firepower adaptor:EthPortOutsizedStats:undersizedGoodCrcPac
        ketsDeltaMax managed object property"
    ::= { cfprAdaptorEthPortOutsizedStatsEntry 32 }

cfprAdaptorEthPortOutsizedStatsUndersizedGoodCrcPacketsDeltaMin OBJECT-TYPE
    SYNTAX       Unsigned64
    MAX-ACCESS   read-only
    STATUS       current
    DESCRIPTION
        "Cisco Firepower adaptor:EthPortOutsizedStats:undersizedGoodCrcPac
        ketsDeltaMin managed object property"
    ::= { cfprAdaptorEthPortOutsizedStatsEntry 33 }

cfprAdaptorEthPortOutsizedStatsUpdate OBJECT-TYPE
    SYNTAX       Gauge32
    MAX-ACCESS   read-only
    STATUS       current
    DESCRIPTION
        "Cisco Firepower adaptor:EthPortOutsizedStats:update
        managed object property"
    ::= { cfprAdaptorEthPortOutsizedStatsEntry 34 }

cfprAdaptorEthPortOutsizedStatsHistTable OBJECT-TYPE
    SYNTAX           SEQUENCE OF CfprAdaptorEthPortOutsizedStatsHistEntry
    MAX-ACCESS       not-accessible
    STATUS           current
    DESCRIPTION
        "Cisco Firepower adaptor:EthPortOutsizedStatsHist
        managed object table"
    ::= { cfprAdaptorObjects 19 }

cfprAdaptorEthPortOutsizedStatsHistEntry OBJECT-TYPE
    SYNTAX           CfprAdaptorEthPortOutsizedStatsHistEntry
    MAX-ACCESS       not-accessible
    STATUS           current
    DESCRIPTION
        "Entry for the cfprAdaptorEthPortOutsizedStatsHistTable table."
    INDEX { cfprAdaptorEthPortOutsizedStatsHistInstanceId }
    ::= { cfprAdaptorEthPortOutsizedStatsHistTable 1 }

CfprAdaptorEthPortOutsizedStatsHistEntry ::= SEQUENCE {
    cfprAdaptorEthPortOutsizedStatsHistInstanceId                    CfprManagedObjectId,
    cfprAdaptorEthPortOutsizedStatsHistDn                            CfprManagedObjectDn,
    cfprAdaptorEthPortOutsizedStatsHistRn                            SnmpAdminString,
    cfprAdaptorEthPortOutsizedStatsHistId                            Unsigned64,
    cfprAdaptorEthPortOutsizedStatsHistMostRecent                    TruthValue,
    cfprAdaptorEthPortOutsizedStatsHistOversizedBadCrcPackets        Unsigned64,
    cfprAdaptorEthPortOutsizedStatsHistOversizedBadCrcPacketsDelta   Unsigned64,
    cfprAdaptorEthPortOutsizedStatsHistOversizedBadCrcPacketsDeltaAvg Unsigned64,
    cfprAdaptorEthPortOutsizedStatsHistOversizedBadCrcPacketsDeltaMax Unsigned64,
    cfprAdaptorEthPortOutsizedStatsHistOversizedBadCrcPacketsDeltaMin Unsigned64,
    cfprAdaptorEthPortOutsizedStatsHistOversizedGoodCrcPackets       Unsigned64,
    cfprAdaptorEthPortOutsizedStatsHistOversizedGoodCrcPacketsDelta  Unsigned64,
    cfprAdaptorEthPortOutsizedStatsHistOversizedGoodCrcPacketsDeltaAvg Unsigned64,
    cfprAdaptorEthPortOutsizedStatsHistOversizedGoodCrcPacketsDeltaMax Unsigned64,
    cfprAdaptorEthPortOutsizedStatsHistOversizedGoodCrcPacketsDeltaMin Unsigned64,
    cfprAdaptorEthPortOutsizedStatsHistOversizedPackets              Unsigned64,
    cfprAdaptorEthPortOutsizedStatsHistOversizedPacketsDelta         Unsigned64,
    cfprAdaptorEthPortOutsizedStatsHistOversizedPacketsDeltaAvg      Unsigned64,
    cfprAdaptorEthPortOutsizedStatsHistOversizedPacketsDeltaMax      Unsigned64,
    cfprAdaptorEthPortOutsizedStatsHistOversizedPacketsDeltaMin      Unsigned64,
    cfprAdaptorEthPortOutsizedStatsHistSuspect                       TruthValue,
    cfprAdaptorEthPortOutsizedStatsHistThresholded                   CfprAdaptorEthPortOutsizedStatsHistThresholded,
    cfprAdaptorEthPortOutsizedStatsHistTimeCollected                 DateAndTime,
    cfprAdaptorEthPortOutsizedStatsHistUndersizedBadCrcPackets       Unsigned64,
    cfprAdaptorEthPortOutsizedStatsHistUndersizedBadCrcPacketsDelta  Unsigned64,
    cfprAdaptorEthPortOutsizedStatsHistUndersizedBadCrcPacketsDeltaAvg Unsigned64,
    cfprAdaptorEthPortOutsizedStatsHistUndersizedBadCrcPacketsDeltaMax Unsigned64,
    cfprAdaptorEthPortOutsizedStatsHistUndersizedBadCrcPacketsDeltaMin Unsigned64,
    cfprAdaptorEthPortOutsizedStatsHistUndersizedGoodCrcPackets      Unsigned64,
    cfprAdaptorEthPortOutsizedStatsHistUndersizedGoodCrcPacketsDelta Unsigned64,
    cfprAdaptorEthPortOutsizedStatsHistUndersizedGoodCrcPacketsDeltaAvg Unsigned64,
    cfprAdaptorEthPortOutsizedStatsHistUndersizedGoodCrcPacketsDeltaMax Unsigned64,
    cfprAdaptorEthPortOutsizedStatsHistUndersizedGoodCrcPacketsDeltaMin Unsigned64
}

cfprAdaptorEthPortOutsizedStatsHistInstanceId OBJECT-TYPE
    SYNTAX       CfprManagedObjectId
    MAX-ACCESS   not-accessible
    STATUS       current
    DESCRIPTION
        "Instance identifier of the managed object."
    ::= { cfprAdaptorEthPortOutsizedStatsHistEntry 1 }

cfprAdaptorEthPortOutsizedStatsHistDn OBJECT-TYPE
    SYNTAX       CfprManagedObjectDn
    MAX-ACCESS   read-only
    STATUS       current
    DESCRIPTION
        "Cisco Firepower adaptor:EthPortOutsizedStatsHist:dn
        managed object property"
    ::= { cfprAdaptorEthPortOutsizedStatsHistEntry 2 }

cfprAdaptorEthPortOutsizedStatsHistRn OBJECT-TYPE
    SYNTAX       SnmpAdminString
    MAX-ACCESS   read-only
    STATUS       current
    DESCRIPTION
        "Cisco Firepower adaptor:EthPortOutsizedStatsHist:rn
        managed object property"
    ::= { cfprAdaptorEthPortOutsizedStatsHistEntry 3 }

cfprAdaptorEthPortOutsizedStatsHistId OBJECT-TYPE
    SYNTAX       Unsigned64
    MAX-ACCESS   read-only
    STATUS       current
    DESCRIPTION
        "Cisco Firepower adaptor:EthPortOutsizedStatsHist:id
        managed object property"
    ::= { cfprAdaptorEthPortOutsizedStatsHistEntry 4 }

cfprAdaptorEthPortOutsizedStatsHistMostRecent OBJECT-TYPE
    SYNTAX       TruthValue
    MAX-ACCESS   read-only
    STATUS       current
    DESCRIPTION
        "Cisco Firepower adaptor:EthPortOutsizedStatsHist:mostRecent
        managed object property"
    ::= { cfprAdaptorEthPortOutsizedStatsHistEntry 5 }

cfprAdaptorEthPortOutsizedStatsHistOversizedBadCrcPackets OBJECT-TYPE
    SYNTAX       Unsigned64
    MAX-ACCESS   read-only
    STATUS       current
    DESCRIPTION
        "Cisco Firepower adaptor:EthPortOutsizedStatsHist:oversizedBadCrcP
        ackets managed object property"
    ::= { cfprAdaptorEthPortOutsizedStatsHistEntry 6 }

cfprAdaptorEthPortOutsizedStatsHistOversizedBadCrcPacketsDelta OBJECT-TYPE
    SYNTAX       Unsigned64
    MAX-ACCESS   read-only
    STATUS       current
    DESCRIPTION
        "Cisco Firepower adaptor:EthPortOutsizedStatsHist:oversizedBadCrcP
        acketsDelta managed object property"
    ::= { cfprAdaptorEthPortOutsizedStatsHistEntry 7 }

cfprAdaptorEthPortOutsizedStatsHistOversizedBadCrcPacketsDeltaAvg OBJECT-TYPE
    SYNTAX       Unsigned64
    MAX-ACCESS   read-only
    STATUS       current
    DESCRIPTION
        "Cisco Firepower adaptor:EthPortOutsizedStatsHist:oversizedBadCrcP
        acketsDeltaAvg managed object property"
    ::= { cfprAdaptorEthPortOutsizedStatsHistEntry 8 }

cfprAdaptorEthPortOutsizedStatsHistOversizedBadCrcPacketsDeltaMax OBJECT-TYPE
    SYNTAX       Unsigned64
    MAX-ACCESS   read-only
    STATUS       current
    DESCRIPTION
        "Cisco Firepower adaptor:EthPortOutsizedStatsHist:oversizedBadCrcP
        acketsDeltaMax managed object property"
    ::= { cfprAdaptorEthPortOutsizedStatsHistEntry 9 }

cfprAdaptorEthPortOutsizedStatsHistOversizedBadCrcPacketsDeltaMin OBJECT-TYPE
    SYNTAX       Unsigned64
    MAX-ACCESS   read-only
    STATUS       current
    DESCRIPTION
        "Cisco Firepower adaptor:EthPortOutsizedStatsHist:oversizedBadCrcP
        acketsDeltaMin managed object property"
    ::= { cfprAdaptorEthPortOutsizedStatsHistEntry 10 }

cfprAdaptorEthPortOutsizedStatsHistOversizedGoodCrcPackets OBJECT-TYPE
    SYNTAX       Unsigned64
    MAX-ACCESS   read-only
    STATUS       current
    DESCRIPTION
        "Cisco Firepower adaptor:EthPortOutsizedStatsHist:oversizedGoodCrc
        Packets managed object property"
    ::= { cfprAdaptorEthPortOutsizedStatsHistEntry 11 }

cfprAdaptorEthPortOutsizedStatsHistOversizedGoodCrcPacketsDelta OBJECT-TYPE
    SYNTAX       Unsigned64
    MAX-ACCESS   read-only
    STATUS       current
    DESCRIPTION
        "Cisco Firepower adaptor:EthPortOutsizedStatsHist:oversizedGoodCrc
        PacketsDelta managed object property"
    ::= { cfprAdaptorEthPortOutsizedStatsHistEntry 12 }

cfprAdaptorEthPortOutsizedStatsHistOversizedGoodCrcPacketsDeltaAvg OBJECT-TYPE
    SYNTAX       Unsigned64
    MAX-ACCESS   read-only
    STATUS       current
    DESCRIPTION
        "Cisco Firepower adaptor:EthPortOutsizedStatsHist:oversizedGoodCrc
        PacketsDeltaAvg managed object property"
    ::= { cfprAdaptorEthPortOutsizedStatsHistEntry 13 }

cfprAdaptorEthPortOutsizedStatsHistOversizedGoodCrcPacketsDeltaMax OBJECT-TYPE
    SYNTAX       Unsigned64
    MAX-ACCESS   read-only
    STATUS       current
    DESCRIPTION
        "Cisco Firepower adaptor:EthPortOutsizedStatsHist:oversizedGoodCrc
        PacketsDeltaMax managed object property"
    ::= { cfprAdaptorEthPortOutsizedStatsHistEntry 14 }

cfprAdaptorEthPortOutsizedStatsHistOversizedGoodCrcPacketsDeltaMin OBJECT-TYPE
    SYNTAX       Unsigned64
    MAX-ACCESS   read-only
    STATUS       current
    DESCRIPTION
        "Cisco Firepower adaptor:EthPortOutsizedStatsHist:oversizedGoodCrc
        PacketsDeltaMin managed object property"
    ::= { cfprAdaptorEthPortOutsizedStatsHistEntry 15 }

cfprAdaptorEthPortOutsizedStatsHistOversizedPackets OBJECT-TYPE
    SYNTAX       Unsigned64
    MAX-ACCESS   read-only
    STATUS       current
    DESCRIPTION
        "Cisco Firepower adaptor:EthPortOutsizedStatsHist:oversizedPackets
         managed object property"
    ::= { cfprAdaptorEthPortOutsizedStatsHistEntry 16 }

cfprAdaptorEthPortOutsizedStatsHistOversizedPacketsDelta OBJECT-TYPE
    SYNTAX       Unsigned64
    MAX-ACCESS   read-only
    STATUS       current
    DESCRIPTION
        "Cisco Firepower adaptor:EthPortOutsizedStatsHist:oversizedPackets
        Delta managed object property"
    ::= { cfprAdaptorEthPortOutsizedStatsHistEntry 17 }

cfprAdaptorEthPortOutsizedStatsHistOversizedPacketsDeltaAvg OBJECT-TYPE
    SYNTAX       Unsigned64
    MAX-ACCESS   read-only
    STATUS       current
    DESCRIPTION
        "Cisco Firepower adaptor:EthPortOutsizedStatsHist:oversizedPackets
        DeltaAvg managed object property"
    ::= { cfprAdaptorEthPortOutsizedStatsHistEntry 18 }

cfprAdaptorEthPortOutsizedStatsHistOversizedPacketsDeltaMax OBJECT-TYPE
    SYNTAX       Unsigned64
    MAX-ACCESS   read-only
    STATUS       current
    DESCRIPTION
        "Cisco Firepower adaptor:EthPortOutsizedStatsHist:oversizedPackets
        DeltaMax managed object property"
    ::= { cfprAdaptorEthPortOutsizedStatsHistEntry 19 }

cfprAdaptorEthPortOutsizedStatsHistOversizedPacketsDeltaMin OBJECT-TYPE
    SYNTAX       Unsigned64
    MAX-ACCESS   read-only
    STATUS       current
    DESCRIPTION
        "Cisco Firepower adaptor:EthPortOutsizedStatsHist:oversizedPackets
        DeltaMin managed object property"
    ::= { cfprAdaptorEthPortOutsizedStatsHistEntry 20 }

cfprAdaptorEthPortOutsizedStatsHistSuspect OBJECT-TYPE
    SYNTAX       TruthValue
    MAX-ACCESS   read-only
    STATUS       current
    DESCRIPTION
        "Cisco Firepower adaptor:EthPortOutsizedStatsHist:suspect
        managed object property"
    ::= { cfprAdaptorEthPortOutsizedStatsHistEntry 21 }

cfprAdaptorEthPortOutsizedStatsHistThresholded OBJECT-TYPE
    SYNTAX       CfprAdaptorEthPortOutsizedStatsHistThresholded
    MAX-ACCESS   read-only
    STATUS       current
    DESCRIPTION
        "Cisco Firepower adaptor:EthPortOutsizedStatsHist:thresholded
        managed object property"
    ::= { cfprAdaptorEthPortOutsizedStatsHistEntry 22 }

cfprAdaptorEthPortOutsizedStatsHistTimeCollected OBJECT-TYPE
    SYNTAX       DateAndTime
    MAX-ACCESS   read-only
    STATUS       current
    DESCRIPTION
        "Cisco Firepower adaptor:EthPortOutsizedStatsHist:timeCollected
        managed object property"
    ::= { cfprAdaptorEthPortOutsizedStatsHistEntry 23 }

cfprAdaptorEthPortOutsizedStatsHistUndersizedBadCrcPackets OBJECT-TYPE
    SYNTAX       Unsigned64
    MAX-ACCESS   read-only
    STATUS       current
    DESCRIPTION
        "Cisco Firepower adaptor:EthPortOutsizedStatsHist:undersizedBadCrc
        Packets managed object property"
    ::= { cfprAdaptorEthPortOutsizedStatsHistEntry 24 }

cfprAdaptorEthPortOutsizedStatsHistUndersizedBadCrcPacketsDelta OBJECT-TYPE
    SYNTAX       Unsigned64
    MAX-ACCESS   read-only
    STATUS       current
    DESCRIPTION
        "Cisco Firepower adaptor:EthPortOutsizedStatsHist:undersizedBadCrc
        PacketsDelta managed object property"
    ::= { cfprAdaptorEthPortOutsizedStatsHistEntry 25 }

cfprAdaptorEthPortOutsizedStatsHistUndersizedBadCrcPacketsDeltaAvg OBJECT-TYPE
    SYNTAX       Unsigned64
    MAX-ACCESS   read-only
    STATUS       current
    DESCRIPTION
        "Cisco Firepower adaptor:EthPortOutsizedStatsHist:undersizedBadCrc
        PacketsDeltaAvg managed object property"
    ::= { cfprAdaptorEthPortOutsizedStatsHistEntry 26 }

cfprAdaptorEthPortOutsizedStatsHistUndersizedBadCrcPacketsDeltaMax OBJECT-TYPE
    SYNTAX       Unsigned64
    MAX-ACCESS   read-only
    STATUS       current
    DESCRIPTION
        "Cisco Firepower adaptor:EthPortOutsizedStatsHist:undersizedBadCrc
        PacketsDeltaMax managed object property"
    ::= { cfprAdaptorEthPortOutsizedStatsHistEntry 27 }

cfprAdaptorEthPortOutsizedStatsHistUndersizedBadCrcPacketsDeltaMin OBJECT-TYPE
    SYNTAX       Unsigned64
    MAX-ACCESS   read-only
    STATUS       current
    DESCRIPTION
        "Cisco Firepower adaptor:EthPortOutsizedStatsHist:undersizedBadCrc
        PacketsDeltaMin managed object property"
    ::= { cfprAdaptorEthPortOutsizedStatsHistEntry 28 }

cfprAdaptorEthPortOutsizedStatsHistUndersizedGoodCrcPackets OBJECT-TYPE
    SYNTAX       Unsigned64
    MAX-ACCESS   read-only
    STATUS       current
    DESCRIPTION
        "Cisco Firepower adaptor:EthPortOutsizedStatsHist:undersizedGoodCr
        cPackets managed object property"
    ::= { cfprAdaptorEthPortOutsizedStatsHistEntry 29 }

cfprAdaptorEthPortOutsizedStatsHistUndersizedGoodCrcPacketsDelta OBJECT-TYPE
    SYNTAX       Unsigned64
    MAX-ACCESS   read-only
    STATUS       current
    DESCRIPTION
        "Cisco Firepower adaptor:EthPortOutsizedStatsHist:undersizedGoodCr
        cPacketsDelta managed object property"
    ::= { cfprAdaptorEthPortOutsizedStatsHistEntry 30 }

cfprAdaptorEthPortOutsizedStatsHistUndersizedGoodCrcPacketsDeltaAvg OBJECT-TYPE
    SYNTAX       Unsigned64
    MAX-ACCESS   read-only
    STATUS       current
    DESCRIPTION
        "Cisco Firepower adaptor:EthPortOutsizedStatsHist:undersizedGoodCr
        cPacketsDeltaAvg managed object property"
    ::= { cfprAdaptorEthPortOutsizedStatsHistEntry 31 }

cfprAdaptorEthPortOutsizedStatsHistUndersizedGoodCrcPacketsDeltaMax OBJECT-TYPE
    SYNTAX       Unsigned64
    MAX-ACCESS   read-only
    STATUS       current
    DESCRIPTION
        "Cisco Firepower adaptor:EthPortOutsizedStatsHist:undersizedGoodCr
        cPacketsDeltaMax managed object property"
    ::= { cfprAdaptorEthPortOutsizedStatsHistEntry 32 }

cfprAdaptorEthPortOutsizedStatsHistUndersizedGoodCrcPacketsDeltaMin OBJECT-TYPE
    SYNTAX       Unsigned64
    MAX-ACCESS   read-only
    STATUS       current
    DESCRIPTION
        "Cisco Firepower adaptor:EthPortOutsizedStatsHist:undersizedGoodCr
        cPacketsDeltaMin managed object property"
    ::= { cfprAdaptorEthPortOutsizedStatsHistEntry 33 }

cfprAdaptorEthPortStatsTable OBJECT-TYPE
    SYNTAX           SEQUENCE OF CfprAdaptorEthPortStatsEntry
    MAX-ACCESS       not-accessible
    STATUS           current
    DESCRIPTION
        "Cisco Firepower adaptor:EthPortStats managed object table"
    ::= { cfprAdaptorObjects 20 }

cfprAdaptorEthPortStatsEntry OBJECT-TYPE
    SYNTAX           CfprAdaptorEthPortStatsEntry
    MAX-ACCESS       not-accessible
    STATUS           current
    DESCRIPTION
        "Entry for the cfprAdaptorEthPortStatsTable table."
    INDEX { cfprAdaptorEthPortStatsInstanceId }
    ::= { cfprAdaptorEthPortStatsTable 1 }

CfprAdaptorEthPortStatsEntry ::= SEQUENCE {
    cfprAdaptorEthPortStatsInstanceId                                CfprManagedObjectId,
    cfprAdaptorEthPortStatsDn                                        CfprManagedObjectDn,
    cfprAdaptorEthPortStatsRn                                        SnmpAdminString,
    cfprAdaptorEthPortStatsGoodPackets                               Unsigned64,
    cfprAdaptorEthPortStatsGoodPacketsDelta                          Counter64,
    cfprAdaptorEthPortStatsGoodPacketsDeltaAvg                       Unsigned64,
    cfprAdaptorEthPortStatsGoodPacketsDeltaMax                       Unsigned64,
    cfprAdaptorEthPortStatsGoodPacketsDeltaMin                       Unsigned64,
    cfprAdaptorEthPortStatsIntervals                                 Gauge32,
    cfprAdaptorEthPortStatsPausePackets                              Unsigned64,
    cfprAdaptorEthPortStatsPausePacketsDelta                         Counter64,
    cfprAdaptorEthPortStatsPausePacketsDeltaAvg                      Unsigned64,
    cfprAdaptorEthPortStatsPausePacketsDeltaMax                      Unsigned64,
    cfprAdaptorEthPortStatsPausePacketsDeltaMin                      Unsigned64,
    cfprAdaptorEthPortStatsPerPriorityPausePackets                   Unsigned64,
    cfprAdaptorEthPortStatsPerPriorityPausePacketsDelta              Counter64,
    cfprAdaptorEthPortStatsPerPriorityPausePacketsDeltaAvg           Unsigned64,
    cfprAdaptorEthPortStatsPerPriorityPausePacketsDeltaMax           Unsigned64,
    cfprAdaptorEthPortStatsPerPriorityPausePacketsDeltaMin           Unsigned64,
    cfprAdaptorEthPortStatsPppPackets                                Unsigned64,
    cfprAdaptorEthPortStatsPppPacketsDelta                           Counter64,
    cfprAdaptorEthPortStatsPppPacketsDeltaAvg                        Unsigned64,
    cfprAdaptorEthPortStatsPppPacketsDeltaMax                        Unsigned64,
    cfprAdaptorEthPortStatsPppPacketsDeltaMin                        Unsigned64,
    cfprAdaptorEthPortStatsSuspect                                   TruthValue,
    cfprAdaptorEthPortStatsThresholded                               CfprAdaptorEthPortStatsThresholded,
    cfprAdaptorEthPortStatsTimeCollected                             DateAndTime,
    cfprAdaptorEthPortStatsTotalPackets                              Unsigned64,
    cfprAdaptorEthPortStatsTotalPacketsDelta                         Counter64,
    cfprAdaptorEthPortStatsTotalPacketsDeltaAvg                      Unsigned64,
    cfprAdaptorEthPortStatsTotalPacketsDeltaMax                      Unsigned64,
    cfprAdaptorEthPortStatsTotalPacketsDeltaMin                      Unsigned64,
    cfprAdaptorEthPortStatsTrafficDirection                          CfprAdaptorAdapterStatsTrafficDir,
    cfprAdaptorEthPortStatsUpdate                                    Gauge32,
    cfprAdaptorEthPortStatsVlanPackets                               Unsigned64,
    cfprAdaptorEthPortStatsVlanPacketsDelta                          Counter64,
    cfprAdaptorEthPortStatsVlanPacketsDeltaAvg                       Unsigned64,
    cfprAdaptorEthPortStatsVlanPacketsDeltaMax                       Unsigned64,
    cfprAdaptorEthPortStatsVlanPacketsDeltaMin                       Unsigned64
}

cfprAdaptorEthPortStatsInstanceId OBJECT-TYPE
    SYNTAX       CfprManagedObjectId
    MAX-ACCESS   not-accessible
    STATUS       current
    DESCRIPTION
        "Instance identifier of the managed object."
    ::= { cfprAdaptorEthPortStatsEntry 1 }

cfprAdaptorEthPortStatsDn OBJECT-TYPE
    SYNTAX       CfprManagedObjectDn
    MAX-ACCESS   read-only
    STATUS       current
    DESCRIPTION
        "Cisco Firepower adaptor:EthPortStats:dn managed object property"
    ::= { cfprAdaptorEthPortStatsEntry 2 }

cfprAdaptorEthPortStatsRn OBJECT-TYPE
    SYNTAX       SnmpAdminString
    MAX-ACCESS   read-only
    STATUS       current
    DESCRIPTION
        "Cisco Firepower adaptor:EthPortStats:rn managed object property"
    ::= { cfprAdaptorEthPortStatsEntry 3 }

cfprAdaptorEthPortStatsGoodPackets OBJECT-TYPE
    SYNTAX       Unsigned64
    MAX-ACCESS   read-only
    STATUS       current
    DESCRIPTION
        "Cisco Firepower adaptor:EthPortStats:goodPackets
        managed object property"
    ::= { cfprAdaptorEthPortStatsEntry 4 }

cfprAdaptorEthPortStatsGoodPacketsDelta OBJECT-TYPE
    SYNTAX       Counter64
    MAX-ACCESS   read-only
    STATUS       current
    DESCRIPTION
        "Cisco Firepower adaptor:EthPortStats:goodPacketsDelta
        managed object property"
    ::= { cfprAdaptorEthPortStatsEntry 5 }

cfprAdaptorEthPortStatsGoodPacketsDeltaAvg OBJECT-TYPE
    SYNTAX       Unsigned64
    MAX-ACCESS   read-only
    STATUS       current
    DESCRIPTION
        "Cisco Firepower adaptor:EthPortStats:goodPacketsDeltaAvg
        managed object property"
    ::= { cfprAdaptorEthPortStatsEntry 6 }

cfprAdaptorEthPortStatsGoodPacketsDeltaMax OBJECT-TYPE
    SYNTAX       Unsigned64
    MAX-ACCESS   read-only
    STATUS       current
    DESCRIPTION
        "Cisco Firepower adaptor:EthPortStats:goodPacketsDeltaMax
        managed object property"
    ::= { cfprAdaptorEthPortStatsEntry 7 }

cfprAdaptorEthPortStatsGoodPacketsDeltaMin OBJECT-TYPE
    SYNTAX       Unsigned64
    MAX-ACCESS   read-only
    STATUS       current
    DESCRIPTION
        "Cisco Firepower adaptor:EthPortStats:goodPacketsDeltaMin
        managed object property"
    ::= { cfprAdaptorEthPortStatsEntry 8 }

cfprAdaptorEthPortStatsIntervals OBJECT-TYPE
    SYNTAX       Gauge32
    MAX-ACCESS   read-only
    STATUS       current
    DESCRIPTION
        "Cisco Firepower adaptor:EthPortStats:intervals
        managed object property"
    ::= { cfprAdaptorEthPortStatsEntry 9 }

cfprAdaptorEthPortStatsPausePackets OBJECT-TYPE
    SYNTAX       Unsigned64
    MAX-ACCESS   read-only
    STATUS       current
    DESCRIPTION
        "Cisco Firepower adaptor:EthPortStats:pausePackets
        managed object property"
    ::= { cfprAdaptorEthPortStatsEntry 10 }

cfprAdaptorEthPortStatsPausePacketsDelta OBJECT-TYPE
    SYNTAX       Counter64
    MAX-ACCESS   read-only
    STATUS       current
    DESCRIPTION
        "Cisco Firepower adaptor:EthPortStats:pausePacketsDelta
        managed object property"
    ::= { cfprAdaptorEthPortStatsEntry 11 }

cfprAdaptorEthPortStatsPausePacketsDeltaAvg OBJECT-TYPE
    SYNTAX       Unsigned64
    MAX-ACCESS   read-only
    STATUS       current
    DESCRIPTION
        "Cisco Firepower adaptor:EthPortStats:pausePacketsDeltaAvg
        managed object property"
    ::= { cfprAdaptorEthPortStatsEntry 12 }

cfprAdaptorEthPortStatsPausePacketsDeltaMax OBJECT-TYPE
    SYNTAX       Unsigned64
    MAX-ACCESS   read-only
    STATUS       current
    DESCRIPTION
        "Cisco Firepower adaptor:EthPortStats:pausePacketsDeltaMax
        managed object property"
    ::= { cfprAdaptorEthPortStatsEntry 13 }

cfprAdaptorEthPortStatsPausePacketsDeltaMin OBJECT-TYPE
    SYNTAX       Unsigned64
    MAX-ACCESS   read-only
    STATUS       current
    DESCRIPTION
        "Cisco Firepower adaptor:EthPortStats:pausePacketsDeltaMin
        managed object property"
    ::= { cfprAdaptorEthPortStatsEntry 14 }

cfprAdaptorEthPortStatsPerPriorityPausePackets OBJECT-TYPE
    SYNTAX       Unsigned64
    MAX-ACCESS   read-only
    STATUS       current
    DESCRIPTION
        "Cisco Firepower adaptor:EthPortStats:perPriorityPausePackets
        managed object property"
    ::= { cfprAdaptorEthPortStatsEntry 15 }

cfprAdaptorEthPortStatsPerPriorityPausePacketsDelta OBJECT-TYPE
    SYNTAX       Counter64
    MAX-ACCESS   read-only
    STATUS       current
    DESCRIPTION
        "Cisco Firepower adaptor:EthPortStats:perPriorityPausePacketsDelta
         managed object property"
    ::= { cfprAdaptorEthPortStatsEntry 16 }

cfprAdaptorEthPortStatsPerPriorityPausePacketsDeltaAvg OBJECT-TYPE
    SYNTAX       Unsigned64
    MAX-ACCESS   read-only
    STATUS       current
    DESCRIPTION
        "Cisco Firepower adaptor:EthPortStats:perPriorityPausePacketsDelta
        Avg managed object property"
    ::= { cfprAdaptorEthPortStatsEntry 17 }

cfprAdaptorEthPortStatsPerPriorityPausePacketsDeltaMax OBJECT-TYPE
    SYNTAX       Unsigned64
    MAX-ACCESS   read-only
    STATUS       current
    DESCRIPTION
        "Cisco Firepower adaptor:EthPortStats:perPriorityPausePacketsDelta
        Max managed object property"
    ::= { cfprAdaptorEthPortStatsEntry 18 }

cfprAdaptorEthPortStatsPerPriorityPausePacketsDeltaMin OBJECT-TYPE
    SYNTAX       Unsigned64
    MAX-ACCESS   read-only
    STATUS       current
    DESCRIPTION
        "Cisco Firepower adaptor:EthPortStats:perPriorityPausePacketsDelta
        Min managed object property"
    ::= { cfprAdaptorEthPortStatsEntry 19 }

cfprAdaptorEthPortStatsPppPackets OBJECT-TYPE
    SYNTAX       Unsigned64
    MAX-ACCESS   read-only
    STATUS       current
    DESCRIPTION
        "Cisco Firepower adaptor:EthPortStats:pppPackets
        managed object property"
    ::= { cfprAdaptorEthPortStatsEntry 20 }

cfprAdaptorEthPortStatsPppPacketsDelta OBJECT-TYPE
    SYNTAX       Counter64
    MAX-ACCESS   read-only
    STATUS       current
    DESCRIPTION
        "Cisco Firepower adaptor:EthPortStats:pppPacketsDelta
        managed object property"
    ::= { cfprAdaptorEthPortStatsEntry 21 }

cfprAdaptorEthPortStatsPppPacketsDeltaAvg OBJECT-TYPE
    SYNTAX       Unsigned64
    MAX-ACCESS   read-only
    STATUS       current
    DESCRIPTION
        "Cisco Firepower adaptor:EthPortStats:pppPacketsDeltaAvg
        managed object property"
    ::= { cfprAdaptorEthPortStatsEntry 22 }

cfprAdaptorEthPortStatsPppPacketsDeltaMax OBJECT-TYPE
    SYNTAX       Unsigned64
    MAX-ACCESS   read-only
    STATUS       current
    DESCRIPTION
        "Cisco Firepower adaptor:EthPortStats:pppPacketsDeltaMax
        managed object property"
    ::= { cfprAdaptorEthPortStatsEntry 23 }

cfprAdaptorEthPortStatsPppPacketsDeltaMin OBJECT-TYPE
    SYNTAX       Unsigned64
    MAX-ACCESS   read-only
    STATUS       current
    DESCRIPTION
        "Cisco Firepower adaptor:EthPortStats:pppPacketsDeltaMin
        managed object property"
    ::= { cfprAdaptorEthPortStatsEntry 24 }

cfprAdaptorEthPortStatsSuspect OBJECT-TYPE
    SYNTAX       TruthValue
    MAX-ACCESS   read-only
    STATUS       current
    DESCRIPTION
        "Cisco Firepower adaptor:EthPortStats:suspect managed
        object property"
    ::= { cfprAdaptorEthPortStatsEntry 25 }

cfprAdaptorEthPortStatsThresholded OBJECT-TYPE
    SYNTAX       CfprAdaptorEthPortStatsThresholded
    MAX-ACCESS   read-only
    STATUS       current
    DESCRIPTION
        "Cisco Firepower adaptor:EthPortStats:thresholded
        managed object property"
    ::= { cfprAdaptorEthPortStatsEntry 26 }

cfprAdaptorEthPortStatsTimeCollected OBJECT-TYPE
    SYNTAX       DateAndTime
    MAX-ACCESS   read-only
    STATUS       current
    DESCRIPTION
        "Cisco Firepower adaptor:EthPortStats:timeCollected
        managed object property"
    ::= { cfprAdaptorEthPortStatsEntry 27 }

cfprAdaptorEthPortStatsTotalPackets OBJECT-TYPE
    SYNTAX       Unsigned64
    MAX-ACCESS   read-only
    STATUS       current
    DESCRIPTION
        "Cisco Firepower adaptor:EthPortStats:totalPackets
        managed object property"
    ::= { cfprAdaptorEthPortStatsEntry 28 }

cfprAdaptorEthPortStatsTotalPacketsDelta OBJECT-TYPE
    SYNTAX       Counter64
    MAX-ACCESS   read-only
    STATUS       current
    DESCRIPTION
        "Cisco Firepower adaptor:EthPortStats:totalPacketsDelta
        managed object property"
    ::= { cfprAdaptorEthPortStatsEntry 29 }

cfprAdaptorEthPortStatsTotalPacketsDeltaAvg OBJECT-TYPE
    SYNTAX       Unsigned64
    MAX-ACCESS   read-only
    STATUS       current
    DESCRIPTION
        "Cisco Firepower adaptor:EthPortStats:totalPacketsDeltaAvg
        managed object property"
    ::= { cfprAdaptorEthPortStatsEntry 30 }

cfprAdaptorEthPortStatsTotalPacketsDeltaMax OBJECT-TYPE
    SYNTAX       Unsigned64
    MAX-ACCESS   read-only
    STATUS       current
    DESCRIPTION
        "Cisco Firepower adaptor:EthPortStats:totalPacketsDeltaMax
        managed object property"
    ::= { cfprAdaptorEthPortStatsEntry 31 }

cfprAdaptorEthPortStatsTotalPacketsDeltaMin OBJECT-TYPE
    SYNTAX       Unsigned64
    MAX-ACCESS   read-only
    STATUS       current
    DESCRIPTION
        "Cisco Firepower adaptor:EthPortStats:totalPacketsDeltaMin
        managed object property"
    ::= { cfprAdaptorEthPortStatsEntry 32 }

cfprAdaptorEthPortStatsTrafficDirection OBJECT-TYPE
    SYNTAX       CfprAdaptorAdapterStatsTrafficDir
    MAX-ACCESS   read-only
    STATUS       current
    DESCRIPTION
        "Cisco Firepower adaptor:EthPortStats:trafficDirection
        managed object property"
    ::= { cfprAdaptorEthPortStatsEntry 33 }

cfprAdaptorEthPortStatsUpdate OBJECT-TYPE
    SYNTAX       Gauge32
    MAX-ACCESS   read-only
    STATUS       current
    DESCRIPTION
        "Cisco Firepower adaptor:EthPortStats:update managed
        object property"
    ::= { cfprAdaptorEthPortStatsEntry 34 }

cfprAdaptorEthPortStatsVlanPackets OBJECT-TYPE
    SYNTAX       Unsigned64
    MAX-ACCESS   read-only
    STATUS       current
    DESCRIPTION
        "Cisco Firepower adaptor:EthPortStats:vlanPackets
        managed object property"
    ::= { cfprAdaptorEthPortStatsEntry 35 }

cfprAdaptorEthPortStatsVlanPacketsDelta OBJECT-TYPE
    SYNTAX       Counter64
    MAX-ACCESS   read-only
    STATUS       current
    DESCRIPTION
        "Cisco Firepower adaptor:EthPortStats:vlanPacketsDelta
        managed object property"
    ::= { cfprAdaptorEthPortStatsEntry 36 }

cfprAdaptorEthPortStatsVlanPacketsDeltaAvg OBJECT-TYPE
    SYNTAX       Unsigned64
    MAX-ACCESS   read-only
    STATUS       current
    DESCRIPTION
        "Cisco Firepower adaptor:EthPortStats:vlanPacketsDeltaAvg
        managed object property"
    ::= { cfprAdaptorEthPortStatsEntry 37 }

cfprAdaptorEthPortStatsVlanPacketsDeltaMax OBJECT-TYPE
    SYNTAX       Unsigned64
    MAX-ACCESS   read-only
    STATUS       current
    DESCRIPTION
        "Cisco Firepower adaptor:EthPortStats:vlanPacketsDeltaMax
        managed object property"
    ::= { cfprAdaptorEthPortStatsEntry 38 }

cfprAdaptorEthPortStatsVlanPacketsDeltaMin OBJECT-TYPE
    SYNTAX       Unsigned64
    MAX-ACCESS   read-only
    STATUS       current
    DESCRIPTION
        "Cisco Firepower adaptor:EthPortStats:vlanPacketsDeltaMin
        managed object property"
    ::= { cfprAdaptorEthPortStatsEntry 39 }

cfprAdaptorEthPortStatsHistTable OBJECT-TYPE
    SYNTAX           SEQUENCE OF CfprAdaptorEthPortStatsHistEntry
    MAX-ACCESS       not-accessible
    STATUS           current
    DESCRIPTION
        "Cisco Firepower adaptor:EthPortStatsHist managed object table"
    ::= { cfprAdaptorObjects 21 }

cfprAdaptorEthPortStatsHistEntry OBJECT-TYPE
    SYNTAX           CfprAdaptorEthPortStatsHistEntry
    MAX-ACCESS       not-accessible
    STATUS           current
    DESCRIPTION
        "Entry for the cfprAdaptorEthPortStatsHistTable table."
    INDEX { cfprAdaptorEthPortStatsHistInstanceId }
    ::= { cfprAdaptorEthPortStatsHistTable 1 }

CfprAdaptorEthPortStatsHistEntry ::= SEQUENCE {
    cfprAdaptorEthPortStatsHistInstanceId                            CfprManagedObjectId,
    cfprAdaptorEthPortStatsHistDn                                    CfprManagedObjectDn,
    cfprAdaptorEthPortStatsHistRn                                    SnmpAdminString,
    cfprAdaptorEthPortStatsHistGoodPackets                           Unsigned64,
    cfprAdaptorEthPortStatsHistGoodPacketsDelta                      Unsigned64,
    cfprAdaptorEthPortStatsHistGoodPacketsDeltaAvg                   Unsigned64,
    cfprAdaptorEthPortStatsHistGoodPacketsDeltaMax                   Unsigned64,
    cfprAdaptorEthPortStatsHistGoodPacketsDeltaMin                   Unsigned64,
    cfprAdaptorEthPortStatsHistId                                    Unsigned64,
    cfprAdaptorEthPortStatsHistMostRecent                            TruthValue,
    cfprAdaptorEthPortStatsHistPausePackets                          Unsigned64,
    cfprAdaptorEthPortStatsHistPausePacketsDelta                     Unsigned64,
    cfprAdaptorEthPortStatsHistPausePacketsDeltaAvg                  Unsigned64,
    cfprAdaptorEthPortStatsHistPausePacketsDeltaMax                  Unsigned64,
    cfprAdaptorEthPortStatsHistPausePacketsDeltaMin                  Unsigned64,
    cfprAdaptorEthPortStatsHistPerPriorityPausePackets               Unsigned64,
    cfprAdaptorEthPortStatsHistPerPriorityPausePacketsDelta          Unsigned64,
    cfprAdaptorEthPortStatsHistPerPriorityPausePacketsDeltaAvg       Unsigned64,
    cfprAdaptorEthPortStatsHistPerPriorityPausePacketsDeltaMax       Unsigned64,
    cfprAdaptorEthPortStatsHistPerPriorityPausePacketsDeltaMin       Unsigned64,
    cfprAdaptorEthPortStatsHistPppPackets                            Unsigned64,
    cfprAdaptorEthPortStatsHistPppPacketsDelta                       Unsigned64,
    cfprAdaptorEthPortStatsHistPppPacketsDeltaAvg                    Unsigned64,
    cfprAdaptorEthPortStatsHistPppPacketsDeltaMax                    Unsigned64,
    cfprAdaptorEthPortStatsHistPppPacketsDeltaMin                    Unsigned64,
    cfprAdaptorEthPortStatsHistSuspect                               TruthValue,
    cfprAdaptorEthPortStatsHistThresholded                           CfprAdaptorEthPortStatsHistThresholded,
    cfprAdaptorEthPortStatsHistTimeCollected                         DateAndTime,
    cfprAdaptorEthPortStatsHistTotalPackets                          Unsigned64,
    cfprAdaptorEthPortStatsHistTotalPacketsDelta                     Unsigned64,
    cfprAdaptorEthPortStatsHistTotalPacketsDeltaAvg                  Unsigned64,
    cfprAdaptorEthPortStatsHistTotalPacketsDeltaMax                  Unsigned64,
    cfprAdaptorEthPortStatsHistTotalPacketsDeltaMin                  Unsigned64,
    cfprAdaptorEthPortStatsHistVlanPackets                           Unsigned64,
    cfprAdaptorEthPortStatsHistVlanPacketsDelta                      Unsigned64,
    cfprAdaptorEthPortStatsHistVlanPacketsDeltaAvg                   Unsigned64,
    cfprAdaptorEthPortStatsHistVlanPacketsDeltaMax                   Unsigned64,
    cfprAdaptorEthPortStatsHistVlanPacketsDeltaMin                   Unsigned64
}

cfprAdaptorEthPortStatsHistInstanceId OBJECT-TYPE
    SYNTAX       CfprManagedObjectId
    MAX-ACCESS   not-accessible
    STATUS       current
    DESCRIPTION
        "Instance identifier of the managed object."
    ::= { cfprAdaptorEthPortStatsHistEntry 1 }

cfprAdaptorEthPortStatsHistDn OBJECT-TYPE
    SYNTAX       CfprManagedObjectDn
    MAX-ACCESS   read-only
    STATUS       current
    DESCRIPTION
        "Cisco Firepower adaptor:EthPortStatsHist:dn managed
        object property"
    ::= { cfprAdaptorEthPortStatsHistEntry 2 }

cfprAdaptorEthPortStatsHistRn OBJECT-TYPE
    SYNTAX       SnmpAdminString
    MAX-ACCESS   read-only
    STATUS       current
    DESCRIPTION
        "Cisco Firepower adaptor:EthPortStatsHist:rn managed
        object property"
    ::= { cfprAdaptorEthPortStatsHistEntry 3 }

cfprAdaptorEthPortStatsHistGoodPackets OBJECT-TYPE
    SYNTAX       Unsigned64
    MAX-ACCESS   read-only
    STATUS       current
    DESCRIPTION
        "Cisco Firepower adaptor:EthPortStatsHist:goodPackets
        managed object property"
    ::= { cfprAdaptorEthPortStatsHistEntry 4 }

cfprAdaptorEthPortStatsHistGoodPacketsDelta OBJECT-TYPE
    SYNTAX       Unsigned64
    MAX-ACCESS   read-only
    STATUS       current
    DESCRIPTION
        "Cisco Firepower adaptor:EthPortStatsHist:goodPacketsDelta
        managed object property"
    ::= { cfprAdaptorEthPortStatsHistEntry 5 }

cfprAdaptorEthPortStatsHistGoodPacketsDeltaAvg OBJECT-TYPE
    SYNTAX       Unsigned64
    MAX-ACCESS   read-only
    STATUS       current
    DESCRIPTION
        "Cisco Firepower adaptor:EthPortStatsHist:goodPacketsDeltaAvg
        managed object property"
    ::= { cfprAdaptorEthPortStatsHistEntry 6 }

cfprAdaptorEthPortStatsHistGoodPacketsDeltaMax OBJECT-TYPE
    SYNTAX       Unsigned64
    MAX-ACCESS   read-only
    STATUS       current
    DESCRIPTION
        "Cisco Firepower adaptor:EthPortStatsHist:goodPacketsDeltaMax
        managed object property"
    ::= { cfprAdaptorEthPortStatsHistEntry 7 }

cfprAdaptorEthPortStatsHistGoodPacketsDeltaMin OBJECT-TYPE
    SYNTAX       Unsigned64
    MAX-ACCESS   read-only
    STATUS       current
    DESCRIPTION
        "Cisco Firepower adaptor:EthPortStatsHist:goodPacketsDeltaMin
        managed object property"
    ::= { cfprAdaptorEthPortStatsHistEntry 8 }

cfprAdaptorEthPortStatsHistId OBJECT-TYPE
    SYNTAX       Unsigned64
    MAX-ACCESS   read-only
    STATUS       current
    DESCRIPTION
        "Cisco Firepower adaptor:EthPortStatsHist:id managed
        object property"
    ::= { cfprAdaptorEthPortStatsHistEntry 9 }

cfprAdaptorEthPortStatsHistMostRecent OBJECT-TYPE
    SYNTAX       TruthValue
    MAX-ACCESS   read-only
    STATUS       current
    DESCRIPTION
        "Cisco Firepower adaptor:EthPortStatsHist:mostRecent
        managed object property"
    ::= { cfprAdaptorEthPortStatsHistEntry 10 }

cfprAdaptorEthPortStatsHistPausePackets OBJECT-TYPE
    SYNTAX       Unsigned64
    MAX-ACCESS   read-only
    STATUS       current
    DESCRIPTION
        "Cisco Firepower adaptor:EthPortStatsHist:pausePackets
        managed object property"
    ::= { cfprAdaptorEthPortStatsHistEntry 11 }

cfprAdaptorEthPortStatsHistPausePacketsDelta OBJECT-TYPE
    SYNTAX       Unsigned64
    MAX-ACCESS   read-only
    STATUS       current
    DESCRIPTION
        "Cisco Firepower adaptor:EthPortStatsHist:pausePacketsDelta
        managed object property"
    ::= { cfprAdaptorEthPortStatsHistEntry 12 }

cfprAdaptorEthPortStatsHistPausePacketsDeltaAvg OBJECT-TYPE
    SYNTAX       Unsigned64
    MAX-ACCESS   read-only
    STATUS       current
    DESCRIPTION
        "Cisco Firepower adaptor:EthPortStatsHist:pausePacketsDeltaAvg
        managed object property"
    ::= { cfprAdaptorEthPortStatsHistEntry 13 }

cfprAdaptorEthPortStatsHistPausePacketsDeltaMax OBJECT-TYPE
    SYNTAX       Unsigned64
    MAX-ACCESS   read-only
    STATUS       current
    DESCRIPTION
        "Cisco Firepower adaptor:EthPortStatsHist:pausePacketsDeltaMax
        managed object property"
    ::= { cfprAdaptorEthPortStatsHistEntry 14 }

cfprAdaptorEthPortStatsHistPausePacketsDeltaMin OBJECT-TYPE
    SYNTAX       Unsigned64
    MAX-ACCESS   read-only
    STATUS       current
    DESCRIPTION
        "Cisco Firepower adaptor:EthPortStatsHist:pausePacketsDeltaMin
        managed object property"
    ::= { cfprAdaptorEthPortStatsHistEntry 15 }

cfprAdaptorEthPortStatsHistPerPriorityPausePackets OBJECT-TYPE
    SYNTAX       Unsigned64
    MAX-ACCESS   read-only
    STATUS       current
    DESCRIPTION
        "Cisco Firepower adaptor:EthPortStatsHist:perPriorityPausePackets
        managed object property"
    ::= { cfprAdaptorEthPortStatsHistEntry 16 }

cfprAdaptorEthPortStatsHistPerPriorityPausePacketsDelta OBJECT-TYPE
    SYNTAX       Unsigned64
    MAX-ACCESS   read-only
    STATUS       current
    DESCRIPTION
        "Cisco Firepower adaptor:EthPortStatsHist:perPriorityPausePacketsD
        elta managed object property"
    ::= { cfprAdaptorEthPortStatsHistEntry 17 }

cfprAdaptorEthPortStatsHistPerPriorityPausePacketsDeltaAvg OBJECT-TYPE
    SYNTAX       Unsigned64
    MAX-ACCESS   read-only
    STATUS       current
    DESCRIPTION
        "Cisco Firepower adaptor:EthPortStatsHist:perPriorityPausePacketsD
        eltaAvg managed object property"
    ::= { cfprAdaptorEthPortStatsHistEntry 18 }

cfprAdaptorEthPortStatsHistPerPriorityPausePacketsDeltaMax OBJECT-TYPE
    SYNTAX       Unsigned64
    MAX-ACCESS   read-only
    STATUS       current
    DESCRIPTION
        "Cisco Firepower adaptor:EthPortStatsHist:perPriorityPausePacketsD
        eltaMax managed object property"
    ::= { cfprAdaptorEthPortStatsHistEntry 19 }

cfprAdaptorEthPortStatsHistPerPriorityPausePacketsDeltaMin OBJECT-TYPE
    SYNTAX       Unsigned64
    MAX-ACCESS   read-only
    STATUS       current
    DESCRIPTION
        "Cisco Firepower adaptor:EthPortStatsHist:perPriorityPausePacketsD
        eltaMin managed object property"
    ::= { cfprAdaptorEthPortStatsHistEntry 20 }

cfprAdaptorEthPortStatsHistPppPackets OBJECT-TYPE
    SYNTAX       Unsigned64
    MAX-ACCESS   read-only
    STATUS       current
    DESCRIPTION
        "Cisco Firepower adaptor:EthPortStatsHist:pppPackets
        managed object property"
    ::= { cfprAdaptorEthPortStatsHistEntry 21 }

cfprAdaptorEthPortStatsHistPppPacketsDelta OBJECT-TYPE
    SYNTAX       Unsigned64
    MAX-ACCESS   read-only
    STATUS       current
    DESCRIPTION
        "Cisco Firepower adaptor:EthPortStatsHist:pppPacketsDelta
        managed object property"
    ::= { cfprAdaptorEthPortStatsHistEntry 22 }

cfprAdaptorEthPortStatsHistPppPacketsDeltaAvg OBJECT-TYPE
    SYNTAX       Unsigned64
    MAX-ACCESS   read-only
    STATUS       current
    DESCRIPTION
        "Cisco Firepower adaptor:EthPortStatsHist:pppPacketsDeltaAvg
        managed object property"
    ::= { cfprAdaptorEthPortStatsHistEntry 23 }

cfprAdaptorEthPortStatsHistPppPacketsDeltaMax OBJECT-TYPE
    SYNTAX       Unsigned64
    MAX-ACCESS   read-only
    STATUS       current
    DESCRIPTION
        "Cisco Firepower adaptor:EthPortStatsHist:pppPacketsDeltaMax
        managed object property"
    ::= { cfprAdaptorEthPortStatsHistEntry 24 }

cfprAdaptorEthPortStatsHistPppPacketsDeltaMin OBJECT-TYPE
    SYNTAX       Unsigned64
    MAX-ACCESS   read-only
    STATUS       current
    DESCRIPTION
        "Cisco Firepower adaptor:EthPortStatsHist:pppPacketsDeltaMin
        managed object property"
    ::= { cfprAdaptorEthPortStatsHistEntry 25 }

cfprAdaptorEthPortStatsHistSuspect OBJECT-TYPE
    SYNTAX       TruthValue
    MAX-ACCESS   read-only
    STATUS       current
    DESCRIPTION
        "Cisco Firepower adaptor:EthPortStatsHist:suspect
        managed object property"
    ::= { cfprAdaptorEthPortStatsHistEntry 26 }

cfprAdaptorEthPortStatsHistThresholded OBJECT-TYPE
    SYNTAX       CfprAdaptorEthPortStatsHistThresholded
    MAX-ACCESS   read-only
    STATUS       current
    DESCRIPTION
        "Cisco Firepower adaptor:EthPortStatsHist:thresholded
        managed object property"
    ::= { cfprAdaptorEthPortStatsHistEntry 27 }

cfprAdaptorEthPortStatsHistTimeCollected OBJECT-TYPE
    SYNTAX       DateAndTime
    MAX-ACCESS   read-only
    STATUS       current
    DESCRIPTION
        "Cisco Firepower adaptor:EthPortStatsHist:timeCollected
        managed object property"
    ::= { cfprAdaptorEthPortStatsHistEntry 28 }

cfprAdaptorEthPortStatsHistTotalPackets OBJECT-TYPE
    SYNTAX       Unsigned64
    MAX-ACCESS   read-only
    STATUS       current
    DESCRIPTION
        "Cisco Firepower adaptor:EthPortStatsHist:totalPackets
        managed object property"
    ::= { cfprAdaptorEthPortStatsHistEntry 29 }

cfprAdaptorEthPortStatsHistTotalPacketsDelta OBJECT-TYPE
    SYNTAX       Unsigned64
    MAX-ACCESS   read-only
    STATUS       current
    DESCRIPTION
        "Cisco Firepower adaptor:EthPortStatsHist:totalPacketsDelta
        managed object property"
    ::= { cfprAdaptorEthPortStatsHistEntry 30 }

cfprAdaptorEthPortStatsHistTotalPacketsDeltaAvg OBJECT-TYPE
    SYNTAX       Unsigned64
    MAX-ACCESS   read-only
    STATUS       current
    DESCRIPTION
        "Cisco Firepower adaptor:EthPortStatsHist:totalPacketsDeltaAvg
        managed object property"
    ::= { cfprAdaptorEthPortStatsHistEntry 31 }

cfprAdaptorEthPortStatsHistTotalPacketsDeltaMax OBJECT-TYPE
    SYNTAX       Unsigned64
    MAX-ACCESS   read-only
    STATUS       current
    DESCRIPTION
        "Cisco Firepower adaptor:EthPortStatsHist:totalPacketsDeltaMax
        managed object property"
    ::= { cfprAdaptorEthPortStatsHistEntry 32 }

cfprAdaptorEthPortStatsHistTotalPacketsDeltaMin OBJECT-TYPE
    SYNTAX       Unsigned64
    MAX-ACCESS   read-only
    STATUS       current
    DESCRIPTION
        "Cisco Firepower adaptor:EthPortStatsHist:totalPacketsDeltaMin
        managed object property"
    ::= { cfprAdaptorEthPortStatsHistEntry 33 }

cfprAdaptorEthPortStatsHistVlanPackets OBJECT-TYPE
    SYNTAX       Unsigned64
    MAX-ACCESS   read-only
    STATUS       current
    DESCRIPTION
        "Cisco Firepower adaptor:EthPortStatsHist:vlanPackets
        managed object property"
    ::= { cfprAdaptorEthPortStatsHistEntry 34 }

cfprAdaptorEthPortStatsHistVlanPacketsDelta OBJECT-TYPE
    SYNTAX       Unsigned64
    MAX-ACCESS   read-only
    STATUS       current
    DESCRIPTION
        "Cisco Firepower adaptor:EthPortStatsHist:vlanPacketsDelta
        managed object property"
    ::= { cfprAdaptorEthPortStatsHistEntry 35 }

cfprAdaptorEthPortStatsHistVlanPacketsDeltaAvg OBJECT-TYPE
    SYNTAX       Unsigned64
    MAX-ACCESS   read-only
    STATUS       current
    DESCRIPTION
        "Cisco Firepower adaptor:EthPortStatsHist:vlanPacketsDeltaAvg
        managed object property"
    ::= { cfprAdaptorEthPortStatsHistEntry 36 }

cfprAdaptorEthPortStatsHistVlanPacketsDeltaMax OBJECT-TYPE
    SYNTAX       Unsigned64
    MAX-ACCESS   read-only
    STATUS       current
    DESCRIPTION
        "Cisco Firepower adaptor:EthPortStatsHist:vlanPacketsDeltaMax
        managed object property"
    ::= { cfprAdaptorEthPortStatsHistEntry 37 }

cfprAdaptorEthPortStatsHistVlanPacketsDeltaMin OBJECT-TYPE
    SYNTAX       Unsigned64
    MAX-ACCESS   read-only
    STATUS       current
    DESCRIPTION
        "Cisco Firepower adaptor:EthPortStatsHist:vlanPacketsDeltaMin
        managed object property"
    ::= { cfprAdaptorEthPortStatsHistEntry 38 }

cfprAdaptorEthRecvQueueProfileTable OBJECT-TYPE
    SYNTAX           SEQUENCE OF CfprAdaptorEthRecvQueueProfileEntry
    MAX-ACCESS       not-accessible
    STATUS           current
    DESCRIPTION
        "Cisco Firepower adaptor:EthRecvQueueProfile managed object table"
    ::= { cfprAdaptorObjects 22 }

cfprAdaptorEthRecvQueueProfileEntry OBJECT-TYPE
    SYNTAX           CfprAdaptorEthRecvQueueProfileEntry
    MAX-ACCESS       not-accessible
    STATUS           current
    DESCRIPTION
        "Entry for the cfprAdaptorEthRecvQueueProfileTable table."
    INDEX { cfprAdaptorEthRecvQueueProfileInstanceId }
    ::= { cfprAdaptorEthRecvQueueProfileTable 1 }

CfprAdaptorEthRecvQueueProfileEntry ::= SEQUENCE {
    cfprAdaptorEthRecvQueueProfileInstanceId                         CfprManagedObjectId,
    cfprAdaptorEthRecvQueueProfileDn                                 CfprManagedObjectDn,
    cfprAdaptorEthRecvQueueProfileRn                                 SnmpAdminString,
    cfprAdaptorEthRecvQueueProfileCount                              Gauge32,
    cfprAdaptorEthRecvQueueProfileRingSize                           Gauge32
}

cfprAdaptorEthRecvQueueProfileInstanceId OBJECT-TYPE
    SYNTAX       CfprManagedObjectId
    MAX-ACCESS   not-accessible
    STATUS       current
    DESCRIPTION
        "Instance identifier of the managed object."
    ::= { cfprAdaptorEthRecvQueueProfileEntry 1 }

cfprAdaptorEthRecvQueueProfileDn OBJECT-TYPE
    SYNTAX       CfprManagedObjectDn
    MAX-ACCESS   read-only
    STATUS       current
    DESCRIPTION
        "Cisco Firepower adaptor:EthRecvQueueProfile:dn
        managed object property"
    ::= { cfprAdaptorEthRecvQueueProfileEntry 2 }

cfprAdaptorEthRecvQueueProfileRn OBJECT-TYPE
    SYNTAX       SnmpAdminString
    MAX-ACCESS   read-only
    STATUS       current
    DESCRIPTION
        "Cisco Firepower adaptor:EthRecvQueueProfile:rn
        managed object property"
    ::= { cfprAdaptorEthRecvQueueProfileEntry 3 }

cfprAdaptorEthRecvQueueProfileCount OBJECT-TYPE
    SYNTAX       Gauge32
    MAX-ACCESS   read-only
    STATUS       current
    DESCRIPTION
        "Cisco Firepower adaptor:EthRecvQueueProfile:count
        managed object property"
    ::= { cfprAdaptorEthRecvQueueProfileEntry 4 }

cfprAdaptorEthRecvQueueProfileRingSize OBJECT-TYPE
    SYNTAX       Gauge32
    MAX-ACCESS   read-only
    STATUS       current
    DESCRIPTION
        "Cisco Firepower adaptor:EthRecvQueueProfile:ringSize
        managed object property"
    ::= { cfprAdaptorEthRecvQueueProfileEntry 5 }

cfprAdaptorEthRoCEProfileTable OBJECT-TYPE
    SYNTAX           SEQUENCE OF CfprAdaptorEthRoCEProfileEntry
    MAX-ACCESS       not-accessible
    STATUS           current
    DESCRIPTION
        "Cisco Firepower adaptor:EthRoCEProfile managed object table"
    ::= { cfprAdaptorObjects 23 }

cfprAdaptorEthRoCEProfileEntry OBJECT-TYPE
    SYNTAX           CfprAdaptorEthRoCEProfileEntry
    MAX-ACCESS       not-accessible
    STATUS           current
    DESCRIPTION
        "Entry for the cfprAdaptorEthRoCEProfileTable table."
    INDEX { cfprAdaptorEthRoCEProfileInstanceId }
    ::= { cfprAdaptorEthRoCEProfileTable 1 }

CfprAdaptorEthRoCEProfileEntry ::= SEQUENCE {
    cfprAdaptorEthRoCEProfileInstanceId                              CfprManagedObjectId,
    cfprAdaptorEthRoCEProfileDn                                      CfprManagedObjectDn,
    cfprAdaptorEthRoCEProfileRn                                      SnmpAdminString,
    cfprAdaptorEthRoCEProfileAdminState                              CfprAdaptorEthRoCEProfileAdminState,
    cfprAdaptorEthRoCEProfileMemoryRegions                           Gauge32,
    cfprAdaptorEthRoCEProfileQueuePairs                              Gauge32,
    cfprAdaptorEthRoCEProfileResourceGroups                          Gauge32
}

cfprAdaptorEthRoCEProfileInstanceId OBJECT-TYPE
    SYNTAX       CfprManagedObjectId
    MAX-ACCESS   not-accessible
    STATUS       current
    DESCRIPTION
        "Instance identifier of the managed object."
    ::= { cfprAdaptorEthRoCEProfileEntry 1 }

cfprAdaptorEthRoCEProfileDn OBJECT-TYPE
    SYNTAX       CfprManagedObjectDn
    MAX-ACCESS   read-only
    STATUS       current
    DESCRIPTION
        "Cisco Firepower adaptor:EthRoCEProfile:dn managed
        object property"
    ::= { cfprAdaptorEthRoCEProfileEntry 2 }

cfprAdaptorEthRoCEProfileRn OBJECT-TYPE
    SYNTAX       SnmpAdminString
    MAX-ACCESS   read-only
    STATUS       current
    DESCRIPTION
        "Cisco Firepower adaptor:EthRoCEProfile:rn managed
        object property"
    ::= { cfprAdaptorEthRoCEProfileEntry 3 }

cfprAdaptorEthRoCEProfileAdminState OBJECT-TYPE
    SYNTAX       CfprAdaptorEthRoCEProfileAdminState
    MAX-ACCESS   read-only
    STATUS       current
    DESCRIPTION
        "Cisco Firepower adaptor:EthRoCEProfile:adminState
        managed object property"
    ::= { cfprAdaptorEthRoCEProfileEntry 4 }

cfprAdaptorEthRoCEProfileMemoryRegions OBJECT-TYPE
    SYNTAX       Gauge32
    MAX-ACCESS   read-only
    STATUS       current
    DESCRIPTION
        "Cisco Firepower adaptor:EthRoCEProfile:memoryRegions
        managed object property"
    ::= { cfprAdaptorEthRoCEProfileEntry 5 }

cfprAdaptorEthRoCEProfileQueuePairs OBJECT-TYPE
    SYNTAX       Gauge32
    MAX-ACCESS   read-only
    STATUS       current
    DESCRIPTION
        "Cisco Firepower adaptor:EthRoCEProfile:queuePairs
        managed object property"
    ::= { cfprAdaptorEthRoCEProfileEntry 6 }

cfprAdaptorEthRoCEProfileResourceGroups OBJECT-TYPE
    SYNTAX       Gauge32
    MAX-ACCESS   read-only
    STATUS       current
    DESCRIPTION
        "Cisco Firepower adaptor:EthRoCEProfile:resourceGroups
        managed object property"
    ::= { cfprAdaptorEthRoCEProfileEntry 7 }

cfprAdaptorEthVxLANProfileTable OBJECT-TYPE
    SYNTAX           SEQUENCE OF CfprAdaptorEthVxLANProfileEntry
    MAX-ACCESS       not-accessible
    STATUS           current
    DESCRIPTION
        "Cisco Firepower adaptor:EthVxLANProfile managed object table"
    ::= { cfprAdaptorObjects 24 }

cfprAdaptorEthVxLANProfileEntry OBJECT-TYPE
    SYNTAX           CfprAdaptorEthVxLANProfileEntry
    MAX-ACCESS       not-accessible
    STATUS           current
    DESCRIPTION
        "Entry for the cfprAdaptorEthVxLANProfileTable table."
    INDEX { cfprAdaptorEthVxLANProfileInstanceId }
    ::= { cfprAdaptorEthVxLANProfileTable 1 }

CfprAdaptorEthVxLANProfileEntry ::= SEQUENCE {
    cfprAdaptorEthVxLANProfileInstanceId                             CfprManagedObjectId,
    cfprAdaptorEthVxLANProfileDn                                     CfprManagedObjectDn,
    cfprAdaptorEthVxLANProfileRn                                     SnmpAdminString,
    cfprAdaptorEthVxLANProfileAdminState                             CfprAdaptorEthVxLANProfileAdminState
}

cfprAdaptorEthVxLANProfileInstanceId OBJECT-TYPE
    SYNTAX       CfprManagedObjectId
    MAX-ACCESS   not-accessible
    STATUS       current
    DESCRIPTION
        "Instance identifier of the managed object."
    ::= { cfprAdaptorEthVxLANProfileEntry 1 }

cfprAdaptorEthVxLANProfileDn OBJECT-TYPE
    SYNTAX       CfprManagedObjectDn
    MAX-ACCESS   read-only
    STATUS       current
    DESCRIPTION
        "Cisco Firepower adaptor:EthVxLANProfile:dn managed
        object property"
    ::= { cfprAdaptorEthVxLANProfileEntry 2 }

cfprAdaptorEthVxLANProfileRn OBJECT-TYPE
    SYNTAX       SnmpAdminString
    MAX-ACCESS   read-only
    STATUS       current
    DESCRIPTION
        "Cisco Firepower adaptor:EthVxLANProfile:rn managed
        object property"
    ::= { cfprAdaptorEthVxLANProfileEntry 3 }

cfprAdaptorEthVxLANProfileAdminState OBJECT-TYPE
    SYNTAX       CfprAdaptorEthVxLANProfileAdminState
    MAX-ACCESS   read-only
    STATUS       current
    DESCRIPTION
        "Cisco Firepower adaptor:EthVxLANProfile:adminState
        managed object property"
    ::= { cfprAdaptorEthVxLANProfileEntry 4 }

cfprAdaptorEthWorkQueueProfileTable OBJECT-TYPE
    SYNTAX           SEQUENCE OF CfprAdaptorEthWorkQueueProfileEntry
    MAX-ACCESS       not-accessible
    STATUS           current
    DESCRIPTION
        "Cisco Firepower adaptor:EthWorkQueueProfile managed object table"
    ::= { cfprAdaptorObjects 25 }

cfprAdaptorEthWorkQueueProfileEntry OBJECT-TYPE
    SYNTAX           CfprAdaptorEthWorkQueueProfileEntry
    MAX-ACCESS       not-accessible
    STATUS           current
    DESCRIPTION
        "Entry for the cfprAdaptorEthWorkQueueProfileTable table."
    INDEX { cfprAdaptorEthWorkQueueProfileInstanceId }
    ::= { cfprAdaptorEthWorkQueueProfileTable 1 }

CfprAdaptorEthWorkQueueProfileEntry ::= SEQUENCE {
    cfprAdaptorEthWorkQueueProfileInstanceId                         CfprManagedObjectId,
    cfprAdaptorEthWorkQueueProfileDn                                 CfprManagedObjectDn,
    cfprAdaptorEthWorkQueueProfileRn                                 SnmpAdminString,
    cfprAdaptorEthWorkQueueProfileCount                              Gauge32,
    cfprAdaptorEthWorkQueueProfileRingSize                           Gauge32
}

cfprAdaptorEthWorkQueueProfileInstanceId OBJECT-TYPE
    SYNTAX       CfprManagedObjectId
    MAX-ACCESS   not-accessible
    STATUS       current
    DESCRIPTION
        "Instance identifier of the managed object."
    ::= { cfprAdaptorEthWorkQueueProfileEntry 1 }

cfprAdaptorEthWorkQueueProfileDn OBJECT-TYPE
    SYNTAX       CfprManagedObjectDn
    MAX-ACCESS   read-only
    STATUS       current
    DESCRIPTION
        "Cisco Firepower adaptor:EthWorkQueueProfile:dn
        managed object property"
    ::= { cfprAdaptorEthWorkQueueProfileEntry 2 }

cfprAdaptorEthWorkQueueProfileRn OBJECT-TYPE
    SYNTAX       SnmpAdminString
    MAX-ACCESS   read-only
    STATUS       current
    DESCRIPTION
        "Cisco Firepower adaptor:EthWorkQueueProfile:rn
        managed object property"
    ::= { cfprAdaptorEthWorkQueueProfileEntry 3 }

cfprAdaptorEthWorkQueueProfileCount OBJECT-TYPE
    SYNTAX       Gauge32
    MAX-ACCESS   read-only
    STATUS       current
    DESCRIPTION
        "Cisco Firepower adaptor:EthWorkQueueProfile:count
        managed object property"
    ::= { cfprAdaptorEthWorkQueueProfileEntry 4 }

cfprAdaptorEthWorkQueueProfileRingSize OBJECT-TYPE
    SYNTAX       Gauge32
    MAX-ACCESS   read-only
    STATUS       current
    DESCRIPTION
        "Cisco Firepower adaptor:EthWorkQueueProfile:ringSize
        managed object property"
    ::= { cfprAdaptorEthWorkQueueProfileEntry 5 }

cfprAdaptorEtherIfStatsTable OBJECT-TYPE
    SYNTAX           SEQUENCE OF CfprAdaptorEtherIfStatsEntry
    MAX-ACCESS       not-accessible
    STATUS           current
    DESCRIPTION
        "Cisco Firepower adaptor:EtherIfStats managed object table"
    ::= { cfprAdaptorObjects 26 }

cfprAdaptorEtherIfStatsEntry OBJECT-TYPE
    SYNTAX           CfprAdaptorEtherIfStatsEntry
    MAX-ACCESS       not-accessible
    STATUS           current
    DESCRIPTION
        "Entry for the cfprAdaptorEtherIfStatsTable table."
    INDEX { cfprAdaptorEtherIfStatsInstanceId }
    ::= { cfprAdaptorEtherIfStatsTable 1 }

CfprAdaptorEtherIfStatsEntry ::= SEQUENCE {
    cfprAdaptorEtherIfStatsInstanceId                                CfprManagedObjectId,
    cfprAdaptorEtherIfStatsDn                                        CfprManagedObjectDn,
    cfprAdaptorEtherIfStatsRn                                        SnmpAdminString,
    cfprAdaptorEtherIfStatsIntervals                                 Gauge32,
    cfprAdaptorEtherIfStatsRxBytes                                   Gauge32,
    cfprAdaptorEtherIfStatsRxBytesDelta                              Counter32,
    cfprAdaptorEtherIfStatsRxBytesDeltaAvg                           Gauge32,
    cfprAdaptorEtherIfStatsRxBytesDeltaMax                           Gauge32,
    cfprAdaptorEtherIfStatsRxBytesDeltaMin                           Gauge32,
    cfprAdaptorEtherIfStatsRxDropped                                 Gauge32,
    cfprAdaptorEtherIfStatsRxDroppedDelta                            Counter32,
    cfprAdaptorEtherIfStatsRxDroppedDeltaAvg                         Gauge32,
    cfprAdaptorEtherIfStatsRxDroppedDeltaMax                         Gauge32,
    cfprAdaptorEtherIfStatsRxDroppedDeltaMin                         Gauge32,
    cfprAdaptorEtherIfStatsRxErrors                                  Gauge32,
    cfprAdaptorEtherIfStatsRxErrorsDelta                             Counter32,
    cfprAdaptorEtherIfStatsRxErrorsDeltaAvg                          Gauge32,
    cfprAdaptorEtherIfStatsRxErrorsDeltaMax                          Gauge32,
    cfprAdaptorEtherIfStatsRxErrorsDeltaMin                          Gauge32,
    cfprAdaptorEtherIfStatsRxPackets                                 Gauge32,
    cfprAdaptorEtherIfStatsRxPacketsDelta                            Counter32,
    cfprAdaptorEtherIfStatsRxPacketsDeltaAvg                         Gauge32,
    cfprAdaptorEtherIfStatsRxPacketsDeltaMax                         Gauge32,
    cfprAdaptorEtherIfStatsRxPacketsDeltaMin                         Gauge32,
    cfprAdaptorEtherIfStatsSuspect                                   TruthValue,
    cfprAdaptorEtherIfStatsThresholded                               CfprAdaptorEtherIfStatsThresholded,
    cfprAdaptorEtherIfStatsTimeCollected                             DateAndTime,
    cfprAdaptorEtherIfStatsTxBytes                                   Gauge32,
    cfprAdaptorEtherIfStatsTxBytesDelta                              Counter32,
    cfprAdaptorEtherIfStatsTxBytesDeltaAvg                           Gauge32,
    cfprAdaptorEtherIfStatsTxBytesDeltaMax                           Gauge32,
    cfprAdaptorEtherIfStatsTxBytesDeltaMin                           Gauge32,
    cfprAdaptorEtherIfStatsTxDropped                                 Gauge32,
    cfprAdaptorEtherIfStatsTxDroppedDelta                            Counter32,
    cfprAdaptorEtherIfStatsTxDroppedDeltaAvg                         Gauge32,
    cfprAdaptorEtherIfStatsTxDroppedDeltaMax                         Gauge32,
    cfprAdaptorEtherIfStatsTxDroppedDeltaMin                         Gauge32,
    cfprAdaptorEtherIfStatsTxErrors                                  Gauge32,
    cfprAdaptorEtherIfStatsTxErrorsDelta                             Counter32,
    cfprAdaptorEtherIfStatsTxErrorsDeltaAvg                          Gauge32,
    cfprAdaptorEtherIfStatsTxErrorsDeltaMax                          Gauge32,
    cfprAdaptorEtherIfStatsTxErrorsDeltaMin                          Gauge32,
    cfprAdaptorEtherIfStatsTxPackets                                 Gauge32,
    cfprAdaptorEtherIfStatsTxPacketsDelta                            Counter32,
    cfprAdaptorEtherIfStatsTxPacketsDeltaAvg                         Gauge32,
    cfprAdaptorEtherIfStatsTxPacketsDeltaMax                         Gauge32,
    cfprAdaptorEtherIfStatsTxPacketsDeltaMin                         Gauge32,
    cfprAdaptorEtherIfStatsUpdate                                    Gauge32
}

cfprAdaptorEtherIfStatsInstanceId OBJECT-TYPE
    SYNTAX       CfprManagedObjectId
    MAX-ACCESS   not-accessible
    STATUS       current
    DESCRIPTION
        "Instance identifier of the managed object."
    ::= { cfprAdaptorEtherIfStatsEntry 1 }

cfprAdaptorEtherIfStatsDn OBJECT-TYPE
    SYNTAX       CfprManagedObjectDn
    MAX-ACCESS   read-only
    STATUS       current
    DESCRIPTION
        "Cisco Firepower adaptor:EtherIfStats:dn managed object property"
    ::= { cfprAdaptorEtherIfStatsEntry 2 }

cfprAdaptorEtherIfStatsRn OBJECT-TYPE
    SYNTAX       SnmpAdminString
    MAX-ACCESS   read-only
    STATUS       current
    DESCRIPTION
        "Cisco Firepower adaptor:EtherIfStats:rn managed object property"
    ::= { cfprAdaptorEtherIfStatsEntry 3 }

cfprAdaptorEtherIfStatsIntervals OBJECT-TYPE
    SYNTAX       Gauge32
    MAX-ACCESS   read-only
    STATUS       current
    DESCRIPTION
        "Cisco Firepower adaptor:EtherIfStats:intervals
        managed object property"
    ::= { cfprAdaptorEtherIfStatsEntry 4 }

cfprAdaptorEtherIfStatsRxBytes OBJECT-TYPE
    SYNTAX       Gauge32
    MAX-ACCESS   read-only
    STATUS       current
    DESCRIPTION
        "Cisco Firepower adaptor:EtherIfStats:rxBytes managed
        object property"
    ::= { cfprAdaptorEtherIfStatsEntry 5 }

cfprAdaptorEtherIfStatsRxBytesDelta OBJECT-TYPE
    SYNTAX       Counter32
    MAX-ACCESS   read-only
    STATUS       current
    DESCRIPTION
        "Cisco Firepower adaptor:EtherIfStats:rxBytesDelta
        managed object property"
    ::= { cfprAdaptorEtherIfStatsEntry 6 }

cfprAdaptorEtherIfStatsRxBytesDeltaAvg OBJECT-TYPE
    SYNTAX       Gauge32
    MAX-ACCESS   read-only
    STATUS       current
    DESCRIPTION
        "Cisco Firepower adaptor:EtherIfStats:rxBytesDeltaAvg
        managed object property"
    ::= { cfprAdaptorEtherIfStatsEntry 7 }

cfprAdaptorEtherIfStatsRxBytesDeltaMax OBJECT-TYPE
    SYNTAX       Gauge32
    MAX-ACCESS   read-only
    STATUS       current
    DESCRIPTION
        "Cisco Firepower adaptor:EtherIfStats:rxBytesDeltaMax
        managed object property"
    ::= { cfprAdaptorEtherIfStatsEntry 8 }

cfprAdaptorEtherIfStatsRxBytesDeltaMin OBJECT-TYPE
    SYNTAX       Gauge32
    MAX-ACCESS   read-only
    STATUS       current
    DESCRIPTION
        "Cisco Firepower adaptor:EtherIfStats:rxBytesDeltaMin
        managed object property"
    ::= { cfprAdaptorEtherIfStatsEntry 9 }

cfprAdaptorEtherIfStatsRxDropped OBJECT-TYPE
    SYNTAX       Gauge32
    MAX-ACCESS   read-only
    STATUS       current
    DESCRIPTION
        "Cisco Firepower adaptor:EtherIfStats:rxDropped
        managed object property"
    ::= { cfprAdaptorEtherIfStatsEntry 10 }

cfprAdaptorEtherIfStatsRxDroppedDelta OBJECT-TYPE
    SYNTAX       Counter32
    MAX-ACCESS   read-only
    STATUS       current
    DESCRIPTION
        "Cisco Firepower adaptor:EtherIfStats:rxDroppedDelta
        managed object property"
    ::= { cfprAdaptorEtherIfStatsEntry 11 }

cfprAdaptorEtherIfStatsRxDroppedDeltaAvg OBJECT-TYPE
    SYNTAX       Gauge32
    MAX-ACCESS   read-only
    STATUS       current
    DESCRIPTION
        "Cisco Firepower adaptor:EtherIfStats:rxDroppedDeltaAvg
        managed object property"
    ::= { cfprAdaptorEtherIfStatsEntry 12 }

cfprAdaptorEtherIfStatsRxDroppedDeltaMax OBJECT-TYPE
    SYNTAX       Gauge32
    MAX-ACCESS   read-only
    STATUS       current
    DESCRIPTION
        "Cisco Firepower adaptor:EtherIfStats:rxDroppedDeltaMax
        managed object property"
    ::= { cfprAdaptorEtherIfStatsEntry 13 }

cfprAdaptorEtherIfStatsRxDroppedDeltaMin OBJECT-TYPE
    SYNTAX       Gauge32
    MAX-ACCESS   read-only
    STATUS       current
    DESCRIPTION
        "Cisco Firepower adaptor:EtherIfStats:rxDroppedDeltaMin
        managed object property"
    ::= { cfprAdaptorEtherIfStatsEntry 14 }

cfprAdaptorEtherIfStatsRxErrors OBJECT-TYPE
    SYNTAX       Gauge32
    MAX-ACCESS   read-only
    STATUS       current
    DESCRIPTION
        "Cisco Firepower adaptor:EtherIfStats:rxErrors
        managed object property"
    ::= { cfprAdaptorEtherIfStatsEntry 15 }

cfprAdaptorEtherIfStatsRxErrorsDelta OBJECT-TYPE
    SYNTAX       Counter32
    MAX-ACCESS   read-only
    STATUS       current
    DESCRIPTION
        "Cisco Firepower adaptor:EtherIfStats:rxErrorsDelta
        managed object property"
    ::= { cfprAdaptorEtherIfStatsEntry 16 }

cfprAdaptorEtherIfStatsRxErrorsDeltaAvg OBJECT-TYPE
    SYNTAX       Gauge32
    MAX-ACCESS   read-only
    STATUS       current
    DESCRIPTION
        "Cisco Firepower adaptor:EtherIfStats:rxErrorsDeltaAvg
        managed object property"
    ::= { cfprAdaptorEtherIfStatsEntry 17 }

cfprAdaptorEtherIfStatsRxErrorsDeltaMax OBJECT-TYPE
    SYNTAX       Gauge32
    MAX-ACCESS   read-only
    STATUS       current
    DESCRIPTION
        "Cisco Firepower adaptor:EtherIfStats:rxErrorsDeltaMax
        managed object property"
    ::= { cfprAdaptorEtherIfStatsEntry 18 }

cfprAdaptorEtherIfStatsRxErrorsDeltaMin OBJECT-TYPE
    SYNTAX       Gauge32
    MAX-ACCESS   read-only
    STATUS       current
    DESCRIPTION
        "Cisco Firepower adaptor:EtherIfStats:rxErrorsDeltaMin
        managed object property"
    ::= { cfprAdaptorEtherIfStatsEntry 19 }

cfprAdaptorEtherIfStatsRxPackets OBJECT-TYPE
    SYNTAX       Gauge32
    MAX-ACCESS   read-only
    STATUS       current
    DESCRIPTION
        "Cisco Firepower adaptor:EtherIfStats:rxPackets
        managed object property"
    ::= { cfprAdaptorEtherIfStatsEntry 20 }

cfprAdaptorEtherIfStatsRxPacketsDelta OBJECT-TYPE
    SYNTAX       Counter32
    MAX-ACCESS   read-only
    STATUS       current
    DESCRIPTION
        "Cisco Firepower adaptor:EtherIfStats:rxPacketsDelta
        managed object property"
    ::= { cfprAdaptorEtherIfStatsEntry 21 }

cfprAdaptorEtherIfStatsRxPacketsDeltaAvg OBJECT-TYPE
    SYNTAX       Gauge32
    MAX-ACCESS   read-only
    STATUS       current
    DESCRIPTION
        "Cisco Firepower adaptor:EtherIfStats:rxPacketsDeltaAvg
        managed object property"
    ::= { cfprAdaptorEtherIfStatsEntry 22 }

cfprAdaptorEtherIfStatsRxPacketsDeltaMax OBJECT-TYPE
    SYNTAX       Gauge32
    MAX-ACCESS   read-only
    STATUS       current
    DESCRIPTION
        "Cisco Firepower adaptor:EtherIfStats:rxPacketsDeltaMax
        managed object property"
    ::= { cfprAdaptorEtherIfStatsEntry 23 }

cfprAdaptorEtherIfStatsRxPacketsDeltaMin OBJECT-TYPE
    SYNTAX       Gauge32
    MAX-ACCESS   read-only
    STATUS       current
    DESCRIPTION
        "Cisco Firepower adaptor:EtherIfStats:rxPacketsDeltaMin
        managed object property"
    ::= { cfprAdaptorEtherIfStatsEntry 24 }

cfprAdaptorEtherIfStatsSuspect OBJECT-TYPE
    SYNTAX       TruthValue
    MAX-ACCESS   read-only
    STATUS       current
    DESCRIPTION
        "Cisco Firepower adaptor:EtherIfStats:suspect managed
        object property"
    ::= { cfprAdaptorEtherIfStatsEntry 25 }

cfprAdaptorEtherIfStatsThresholded OBJECT-TYPE
    SYNTAX       CfprAdaptorEtherIfStatsThresholded
    MAX-ACCESS   read-only
    STATUS       current
    DESCRIPTION
        "Cisco Firepower adaptor:EtherIfStats:thresholded
        managed object property"
    ::= { cfprAdaptorEtherIfStatsEntry 26 }

cfprAdaptorEtherIfStatsTimeCollected OBJECT-TYPE
    SYNTAX       DateAndTime
    MAX-ACCESS   read-only
    STATUS       current
    DESCRIPTION
        "Cisco Firepower adaptor:EtherIfStats:timeCollected
        managed object property"
    ::= { cfprAdaptorEtherIfStatsEntry 27 }

cfprAdaptorEtherIfStatsTxBytes OBJECT-TYPE
    SYNTAX       Gauge32
    MAX-ACCESS   read-only
    STATUS       current
    DESCRIPTION
        "Cisco Firepower adaptor:EtherIfStats:txBytes managed
        object property"
    ::= { cfprAdaptorEtherIfStatsEntry 28 }

cfprAdaptorEtherIfStatsTxBytesDelta OBJECT-TYPE
    SYNTAX       Counter32
    MAX-ACCESS   read-only
    STATUS       current
    DESCRIPTION
        "Cisco Firepower adaptor:EtherIfStats:txBytesDelta
        managed object property"
    ::= { cfprAdaptorEtherIfStatsEntry 29 }

cfprAdaptorEtherIfStatsTxBytesDeltaAvg OBJECT-TYPE
    SYNTAX       Gauge32
    MAX-ACCESS   read-only
    STATUS       current
    DESCRIPTION
        "Cisco Firepower adaptor:EtherIfStats:txBytesDeltaAvg
        managed object property"
    ::= { cfprAdaptorEtherIfStatsEntry 30 }

cfprAdaptorEtherIfStatsTxBytesDeltaMax OBJECT-TYPE
    SYNTAX       Gauge32
    MAX-ACCESS   read-only
    STATUS       current
    DESCRIPTION
        "Cisco Firepower adaptor:EtherIfStats:txBytesDeltaMax
        managed object property"
    ::= { cfprAdaptorEtherIfStatsEntry 31 }

cfprAdaptorEtherIfStatsTxBytesDeltaMin OBJECT-TYPE
    SYNTAX       Gauge32
    MAX-ACCESS   read-only
    STATUS       current
    DESCRIPTION
        "Cisco Firepower adaptor:EtherIfStats:txBytesDeltaMin
        managed object property"
    ::= { cfprAdaptorEtherIfStatsEntry 32 }

cfprAdaptorEtherIfStatsTxDropped OBJECT-TYPE
    SYNTAX       Gauge32
    MAX-ACCESS   read-only
    STATUS       current
    DESCRIPTION
        "Cisco Firepower adaptor:EtherIfStats:txDropped
        managed object property"
    ::= { cfprAdaptorEtherIfStatsEntry 33 }

cfprAdaptorEtherIfStatsTxDroppedDelta OBJECT-TYPE
    SYNTAX       Counter32
    MAX-ACCESS   read-only
    STATUS       current
    DESCRIPTION
        "Cisco Firepower adaptor:EtherIfStats:txDroppedDelta
        managed object property"
    ::= { cfprAdaptorEtherIfStatsEntry 34 }

cfprAdaptorEtherIfStatsTxDroppedDeltaAvg OBJECT-TYPE
    SYNTAX       Gauge32
    MAX-ACCESS   read-only
    STATUS       current
    DESCRIPTION
        "Cisco Firepower adaptor:EtherIfStats:txDroppedDeltaAvg
        managed object property"
    ::= { cfprAdaptorEtherIfStatsEntry 35 }

cfprAdaptorEtherIfStatsTxDroppedDeltaMax OBJECT-TYPE
    SYNTAX       Gauge32
    MAX-ACCESS   read-only
    STATUS       current
    DESCRIPTION
        "Cisco Firepower adaptor:EtherIfStats:txDroppedDeltaMax
        managed object property"
    ::= { cfprAdaptorEtherIfStatsEntry 36 }

cfprAdaptorEtherIfStatsTxDroppedDeltaMin OBJECT-TYPE
    SYNTAX       Gauge32
    MAX-ACCESS   read-only
    STATUS       current
    DESCRIPTION
        "Cisco Firepower adaptor:EtherIfStats:txDroppedDeltaMin
        managed object property"
    ::= { cfprAdaptorEtherIfStatsEntry 37 }

cfprAdaptorEtherIfStatsTxErrors OBJECT-TYPE
    SYNTAX       Gauge32
    MAX-ACCESS   read-only
    STATUS       current
    DESCRIPTION
        "Cisco Firepower adaptor:EtherIfStats:txErrors
        managed object property"
    ::= { cfprAdaptorEtherIfStatsEntry 38 }

cfprAdaptorEtherIfStatsTxErrorsDelta OBJECT-TYPE
    SYNTAX       Counter32
    MAX-ACCESS   read-only
    STATUS       current
    DESCRIPTION
        "Cisco Firepower adaptor:EtherIfStats:txErrorsDelta
        managed object property"
    ::= { cfprAdaptorEtherIfStatsEntry 39 }

cfprAdaptorEtherIfStatsTxErrorsDeltaAvg OBJECT-TYPE
    SYNTAX       Gauge32
    MAX-ACCESS   read-only
    STATUS       current
    DESCRIPTION
        "Cisco Firepower adaptor:EtherIfStats:txErrorsDeltaAvg
        managed object property"
    ::= { cfprAdaptorEtherIfStatsEntry 40 }

cfprAdaptorEtherIfStatsTxErrorsDeltaMax OBJECT-TYPE
    SYNTAX       Gauge32
    MAX-ACCESS   read-only
    STATUS       current
    DESCRIPTION
        "Cisco Firepower adaptor:EtherIfStats:txErrorsDeltaMax
        managed object property"
    ::= { cfprAdaptorEtherIfStatsEntry 41 }

cfprAdaptorEtherIfStatsTxErrorsDeltaMin OBJECT-TYPE
    SYNTAX       Gauge32
    MAX-ACCESS   read-only
    STATUS       current
    DESCRIPTION
        "Cisco Firepower adaptor:EtherIfStats:txErrorsDeltaMin
        managed object property"
    ::= { cfprAdaptorEtherIfStatsEntry 42 }

cfprAdaptorEtherIfStatsTxPackets OBJECT-TYPE
    SYNTAX       Gauge32
    MAX-ACCESS   read-only
    STATUS       current
    DESCRIPTION
        "Cisco Firepower adaptor:EtherIfStats:txPackets
        managed object property"
    ::= { cfprAdaptorEtherIfStatsEntry 43 }

cfprAdaptorEtherIfStatsTxPacketsDelta OBJECT-TYPE
    SYNTAX       Counter32
    MAX-ACCESS   read-only
    STATUS       current
    DESCRIPTION
        "Cisco Firepower adaptor:EtherIfStats:txPacketsDelta
        managed object property"
    ::= { cfprAdaptorEtherIfStatsEntry 44 }

cfprAdaptorEtherIfStatsTxPacketsDeltaAvg OBJECT-TYPE
    SYNTAX       Gauge32
    MAX-ACCESS   read-only
    STATUS       current
    DESCRIPTION
        "Cisco Firepower adaptor:EtherIfStats:txPacketsDeltaAvg
        managed object property"
    ::= { cfprAdaptorEtherIfStatsEntry 45 }

cfprAdaptorEtherIfStatsTxPacketsDeltaMax OBJECT-TYPE
    SYNTAX       Gauge32
    MAX-ACCESS   read-only
    STATUS       current
    DESCRIPTION
        "Cisco Firepower adaptor:EtherIfStats:txPacketsDeltaMax
        managed object property"
    ::= { cfprAdaptorEtherIfStatsEntry 46 }

cfprAdaptorEtherIfStatsTxPacketsDeltaMin OBJECT-TYPE
    SYNTAX       Gauge32
    MAX-ACCESS   read-only
    STATUS       current
    DESCRIPTION
        "Cisco Firepower adaptor:EtherIfStats:txPacketsDeltaMin
        managed object property"
    ::= { cfprAdaptorEtherIfStatsEntry 47 }

cfprAdaptorEtherIfStatsUpdate OBJECT-TYPE
    SYNTAX       Gauge32
    MAX-ACCESS   read-only
    STATUS       current
    DESCRIPTION
        "Cisco Firepower adaptor:EtherIfStats:update managed
        object property"
    ::= { cfprAdaptorEtherIfStatsEntry 48 }

cfprAdaptorEtherIfStatsHistTable OBJECT-TYPE
    SYNTAX           SEQUENCE OF CfprAdaptorEtherIfStatsHistEntry
    MAX-ACCESS       not-accessible
    STATUS           current
    DESCRIPTION
        "Cisco Firepower adaptor:EtherIfStatsHist managed object table"
    ::= { cfprAdaptorObjects 27 }

cfprAdaptorEtherIfStatsHistEntry OBJECT-TYPE
    SYNTAX           CfprAdaptorEtherIfStatsHistEntry
    MAX-ACCESS       not-accessible
    STATUS           current
    DESCRIPTION
        "Entry for the cfprAdaptorEtherIfStatsHistTable table."
    INDEX { cfprAdaptorEtherIfStatsHistInstanceId }
    ::= { cfprAdaptorEtherIfStatsHistTable 1 }

CfprAdaptorEtherIfStatsHistEntry ::= SEQUENCE {
    cfprAdaptorEtherIfStatsHistInstanceId                            CfprManagedObjectId,
    cfprAdaptorEtherIfStatsHistDn                                    CfprManagedObjectDn,
    cfprAdaptorEtherIfStatsHistRn                                    SnmpAdminString,
    cfprAdaptorEtherIfStatsHistId                                    Unsigned64,
    cfprAdaptorEtherIfStatsHistMostRecent                            TruthValue,
    cfprAdaptorEtherIfStatsHistRxBytes                               Gauge32,
    cfprAdaptorEtherIfStatsHistRxBytesDelta                          Gauge32,
    cfprAdaptorEtherIfStatsHistRxBytesDeltaAvg                       Gauge32,
    cfprAdaptorEtherIfStatsHistRxBytesDeltaMax                       Gauge32,
    cfprAdaptorEtherIfStatsHistRxBytesDeltaMin                       Gauge32,
    cfprAdaptorEtherIfStatsHistRxDropped                             Gauge32,
    cfprAdaptorEtherIfStatsHistRxDroppedDelta                        Gauge32,
    cfprAdaptorEtherIfStatsHistRxDroppedDeltaAvg                     Gauge32,
    cfprAdaptorEtherIfStatsHistRxDroppedDeltaMax                     Gauge32,
    cfprAdaptorEtherIfStatsHistRxDroppedDeltaMin                     Gauge32,
    cfprAdaptorEtherIfStatsHistRxErrors                              Gauge32,
    cfprAdaptorEtherIfStatsHistRxErrorsDelta                         Gauge32,
    cfprAdaptorEtherIfStatsHistRxErrorsDeltaAvg                      Gauge32,
    cfprAdaptorEtherIfStatsHistRxErrorsDeltaMax                      Gauge32,
    cfprAdaptorEtherIfStatsHistRxErrorsDeltaMin                      Gauge32,
    cfprAdaptorEtherIfStatsHistRxPackets                             Gauge32,
    cfprAdaptorEtherIfStatsHistRxPacketsDelta                        Gauge32,
    cfprAdaptorEtherIfStatsHistRxPacketsDeltaAvg                     Gauge32,
    cfprAdaptorEtherIfStatsHistRxPacketsDeltaMax                     Gauge32,
    cfprAdaptorEtherIfStatsHistRxPacketsDeltaMin                     Gauge32,
    cfprAdaptorEtherIfStatsHistSuspect                               TruthValue,
    cfprAdaptorEtherIfStatsHistThresholded                           CfprAdaptorEtherIfStatsHistThresholded,
    cfprAdaptorEtherIfStatsHistTimeCollected                         DateAndTime,
    cfprAdaptorEtherIfStatsHistTxBytes                               Gauge32,
    cfprAdaptorEtherIfStatsHistTxBytesDelta                          Gauge32,
    cfprAdaptorEtherIfStatsHistTxBytesDeltaAvg                       Gauge32,
    cfprAdaptorEtherIfStatsHistTxBytesDeltaMax                       Gauge32,
    cfprAdaptorEtherIfStatsHistTxBytesDeltaMin                       Gauge32,
    cfprAdaptorEtherIfStatsHistTxDropped                             Gauge32,
    cfprAdaptorEtherIfStatsHistTxDroppedDelta                        Gauge32,
    cfprAdaptorEtherIfStatsHistTxDroppedDeltaAvg                     Gauge32,
    cfprAdaptorEtherIfStatsHistTxDroppedDeltaMax                     Gauge32,
    cfprAdaptorEtherIfStatsHistTxDroppedDeltaMin                     Gauge32,
    cfprAdaptorEtherIfStatsHistTxErrors                              Gauge32,
    cfprAdaptorEtherIfStatsHistTxErrorsDelta                         Gauge32,
    cfprAdaptorEtherIfStatsHistTxErrorsDeltaAvg                      Gauge32,
    cfprAdaptorEtherIfStatsHistTxErrorsDeltaMax                      Gauge32,
    cfprAdaptorEtherIfStatsHistTxErrorsDeltaMin                      Gauge32,
    cfprAdaptorEtherIfStatsHistTxPackets                             Gauge32,
    cfprAdaptorEtherIfStatsHistTxPacketsDelta                        Gauge32,
    cfprAdaptorEtherIfStatsHistTxPacketsDeltaAvg                     Gauge32,
    cfprAdaptorEtherIfStatsHistTxPacketsDeltaMax                     Gauge32,
    cfprAdaptorEtherIfStatsHistTxPacketsDeltaMin                     Gauge32
}

cfprAdaptorEtherIfStatsHistInstanceId OBJECT-TYPE
    SYNTAX       CfprManagedObjectId
    MAX-ACCESS   not-accessible
    STATUS       current
    DESCRIPTION
        "Instance identifier of the managed object."
    ::= { cfprAdaptorEtherIfStatsHistEntry 1 }

cfprAdaptorEtherIfStatsHistDn OBJECT-TYPE
    SYNTAX       CfprManagedObjectDn
    MAX-ACCESS   read-only
    STATUS       current
    DESCRIPTION
        "Cisco Firepower adaptor:EtherIfStatsHist:dn managed
        object property"
    ::= { cfprAdaptorEtherIfStatsHistEntry 2 }

cfprAdaptorEtherIfStatsHistRn OBJECT-TYPE
    SYNTAX       SnmpAdminString
    MAX-ACCESS   read-only
    STATUS       current
    DESCRIPTION
        "Cisco Firepower adaptor:EtherIfStatsHist:rn managed
        object property"
    ::= { cfprAdaptorEtherIfStatsHistEntry 3 }

cfprAdaptorEtherIfStatsHistId OBJECT-TYPE
    SYNTAX       Unsigned64
    MAX-ACCESS   read-only
    STATUS       current
    DESCRIPTION
        "Cisco Firepower adaptor:EtherIfStatsHist:id managed
        object property"
    ::= { cfprAdaptorEtherIfStatsHistEntry 4 }

cfprAdaptorEtherIfStatsHistMostRecent OBJECT-TYPE
    SYNTAX       TruthValue
    MAX-ACCESS   read-only
    STATUS       current
    DESCRIPTION
        "Cisco Firepower adaptor:EtherIfStatsHist:mostRecent
        managed object property"
    ::= { cfprAdaptorEtherIfStatsHistEntry 5 }

cfprAdaptorEtherIfStatsHistRxBytes OBJECT-TYPE
    SYNTAX       Gauge32
    MAX-ACCESS   read-only
    STATUS       current
    DESCRIPTION
        "Cisco Firepower adaptor:EtherIfStatsHist:rxBytes
        managed object property"
    ::= { cfprAdaptorEtherIfStatsHistEntry 6 }

cfprAdaptorEtherIfStatsHistRxBytesDelta OBJECT-TYPE
    SYNTAX       Gauge32
    MAX-ACCESS   read-only
    STATUS       current
    DESCRIPTION
        "Cisco Firepower adaptor:EtherIfStatsHist:rxBytesDelta
        managed object property"
    ::= { cfprAdaptorEtherIfStatsHistEntry 7 }

cfprAdaptorEtherIfStatsHistRxBytesDeltaAvg OBJECT-TYPE
    SYNTAX       Gauge32
    MAX-ACCESS   read-only
    STATUS       current
    DESCRIPTION
        "Cisco Firepower adaptor:EtherIfStatsHist:rxBytesDeltaAvg
        managed object property"
    ::= { cfprAdaptorEtherIfStatsHistEntry 8 }

cfprAdaptorEtherIfStatsHistRxBytesDeltaMax OBJECT-TYPE
    SYNTAX       Gauge32
    MAX-ACCESS   read-only
    STATUS       current
    DESCRIPTION
        "Cisco Firepower adaptor:EtherIfStatsHist:rxBytesDeltaMax
        managed object property"
    ::= { cfprAdaptorEtherIfStatsHistEntry 9 }

cfprAdaptorEtherIfStatsHistRxBytesDeltaMin OBJECT-TYPE
    SYNTAX       Gauge32
    MAX-ACCESS   read-only
    STATUS       current
    DESCRIPTION
        "Cisco Firepower adaptor:EtherIfStatsHist:rxBytesDeltaMin
        managed object property"
    ::= { cfprAdaptorEtherIfStatsHistEntry 10 }

cfprAdaptorEtherIfStatsHistRxDropped OBJECT-TYPE
    SYNTAX       Gauge32
    MAX-ACCESS   read-only
    STATUS       current
    DESCRIPTION
        "Cisco Firepower adaptor:EtherIfStatsHist:rxDropped
        managed object property"
    ::= { cfprAdaptorEtherIfStatsHistEntry 11 }

cfprAdaptorEtherIfStatsHistRxDroppedDelta OBJECT-TYPE
    SYNTAX       Gauge32
    MAX-ACCESS   read-only
    STATUS       current
    DESCRIPTION
        "Cisco Firepower adaptor:EtherIfStatsHist:rxDroppedDelta
        managed object property"
    ::= { cfprAdaptorEtherIfStatsHistEntry 12 }

cfprAdaptorEtherIfStatsHistRxDroppedDeltaAvg OBJECT-TYPE
    SYNTAX       Gauge32
    MAX-ACCESS   read-only
    STATUS       current
    DESCRIPTION
        "Cisco Firepower adaptor:EtherIfStatsHist:rxDroppedDeltaAvg
        managed object property"
    ::= { cfprAdaptorEtherIfStatsHistEntry 13 }

cfprAdaptorEtherIfStatsHistRxDroppedDeltaMax OBJECT-TYPE
    SYNTAX       Gauge32
    MAX-ACCESS   read-only
    STATUS       current
    DESCRIPTION
        "Cisco Firepower adaptor:EtherIfStatsHist:rxDroppedDeltaMax
        managed object property"
    ::= { cfprAdaptorEtherIfStatsHistEntry 14 }

cfprAdaptorEtherIfStatsHistRxDroppedDeltaMin OBJECT-TYPE
    SYNTAX       Gauge32
    MAX-ACCESS   read-only
    STATUS       current
    DESCRIPTION
        "Cisco Firepower adaptor:EtherIfStatsHist:rxDroppedDeltaMin
        managed object property"
    ::= { cfprAdaptorEtherIfStatsHistEntry 15 }

cfprAdaptorEtherIfStatsHistRxErrors OBJECT-TYPE
    SYNTAX       Gauge32
    MAX-ACCESS   read-only
    STATUS       current
    DESCRIPTION
        "Cisco Firepower adaptor:EtherIfStatsHist:rxErrors
        managed object property"
    ::= { cfprAdaptorEtherIfStatsHistEntry 16 }

cfprAdaptorEtherIfStatsHistRxErrorsDelta OBJECT-TYPE
    SYNTAX       Gauge32
    MAX-ACCESS   read-only
    STATUS       current
    DESCRIPTION
        "Cisco Firepower adaptor:EtherIfStatsHist:rxErrorsDelta
        managed object property"
    ::= { cfprAdaptorEtherIfStatsHistEntry 17 }

cfprAdaptorEtherIfStatsHistRxErrorsDeltaAvg OBJECT-TYPE
    SYNTAX       Gauge32
    MAX-ACCESS   read-only
    STATUS       current
    DESCRIPTION
        "Cisco Firepower adaptor:EtherIfStatsHist:rxErrorsDeltaAvg
        managed object property"
    ::= { cfprAdaptorEtherIfStatsHistEntry 18 }

cfprAdaptorEtherIfStatsHistRxErrorsDeltaMax OBJECT-TYPE
    SYNTAX       Gauge32
    MAX-ACCESS   read-only
    STATUS       current
    DESCRIPTION
        "Cisco Firepower adaptor:EtherIfStatsHist:rxErrorsDeltaMax
        managed object property"
    ::= { cfprAdaptorEtherIfStatsHistEntry 19 }

cfprAdaptorEtherIfStatsHistRxErrorsDeltaMin OBJECT-TYPE
    SYNTAX       Gauge32
    MAX-ACCESS   read-only
    STATUS       current
    DESCRIPTION
        "Cisco Firepower adaptor:EtherIfStatsHist:rxErrorsDeltaMin
        managed object property"
    ::= { cfprAdaptorEtherIfStatsHistEntry 20 }

cfprAdaptorEtherIfStatsHistRxPackets OBJECT-TYPE
    SYNTAX       Gauge32
    MAX-ACCESS   read-only
    STATUS       current
    DESCRIPTION
        "Cisco Firepower adaptor:EtherIfStatsHist:rxPackets
        managed object property"
    ::= { cfprAdaptorEtherIfStatsHistEntry 21 }

cfprAdaptorEtherIfStatsHistRxPacketsDelta OBJECT-TYPE
    SYNTAX       Gauge32
    MAX-ACCESS   read-only
    STATUS       current
    DESCRIPTION
        "Cisco Firepower adaptor:EtherIfStatsHist:rxPacketsDelta
        managed object property"
    ::= { cfprAdaptorEtherIfStatsHistEntry 22 }

cfprAdaptorEtherIfStatsHistRxPacketsDeltaAvg OBJECT-TYPE
    SYNTAX       Gauge32
    MAX-ACCESS   read-only
    STATUS       current
    DESCRIPTION
        "Cisco Firepower adaptor:EtherIfStatsHist:rxPacketsDeltaAvg
        managed object property"
    ::= { cfprAdaptorEtherIfStatsHistEntry 23 }

cfprAdaptorEtherIfStatsHistRxPacketsDeltaMax OBJECT-TYPE
    SYNTAX       Gauge32
    MAX-ACCESS   read-only
    STATUS       current
    DESCRIPTION
        "Cisco Firepower adaptor:EtherIfStatsHist:rxPacketsDeltaMax
        managed object property"
    ::= { cfprAdaptorEtherIfStatsHistEntry 24 }

cfprAdaptorEtherIfStatsHistRxPacketsDeltaMin OBJECT-TYPE
    SYNTAX       Gauge32
    MAX-ACCESS   read-only
    STATUS       current
    DESCRIPTION
        "Cisco Firepower adaptor:EtherIfStatsHist:rxPacketsDeltaMin
        managed object property"
    ::= { cfprAdaptorEtherIfStatsHistEntry 25 }

cfprAdaptorEtherIfStatsHistSuspect OBJECT-TYPE
    SYNTAX       TruthValue
    MAX-ACCESS   read-only
    STATUS       current
    DESCRIPTION
        "Cisco Firepower adaptor:EtherIfStatsHist:suspect
        managed object property"
    ::= { cfprAdaptorEtherIfStatsHistEntry 26 }

cfprAdaptorEtherIfStatsHistThresholded OBJECT-TYPE
    SYNTAX       CfprAdaptorEtherIfStatsHistThresholded
    MAX-ACCESS   read-only
    STATUS       current
    DESCRIPTION
        "Cisco Firepower adaptor:EtherIfStatsHist:thresholded
        managed object property"
    ::= { cfprAdaptorEtherIfStatsHistEntry 27 }

cfprAdaptorEtherIfStatsHistTimeCollected OBJECT-TYPE
    SYNTAX       DateAndTime
    MAX-ACCESS   read-only
    STATUS       current
    DESCRIPTION
        "Cisco Firepower adaptor:EtherIfStatsHist:timeCollected
        managed object property"
    ::= { cfprAdaptorEtherIfStatsHistEntry 28 }

cfprAdaptorEtherIfStatsHistTxBytes OBJECT-TYPE
    SYNTAX       Gauge32
    MAX-ACCESS   read-only
    STATUS       current
    DESCRIPTION
        "Cisco Firepower adaptor:EtherIfStatsHist:txBytes
        managed object property"
    ::= { cfprAdaptorEtherIfStatsHistEntry 29 }

cfprAdaptorEtherIfStatsHistTxBytesDelta OBJECT-TYPE
    SYNTAX       Gauge32
    MAX-ACCESS   read-only
    STATUS       current
    DESCRIPTION
        "Cisco Firepower adaptor:EtherIfStatsHist:txBytesDelta
        managed object property"
    ::= { cfprAdaptorEtherIfStatsHistEntry 30 }

cfprAdaptorEtherIfStatsHistTxBytesDeltaAvg OBJECT-TYPE
    SYNTAX       Gauge32
    MAX-ACCESS   read-only
    STATUS       current
    DESCRIPTION
        "Cisco Firepower adaptor:EtherIfStatsHist:txBytesDeltaAvg
        managed object property"
    ::= { cfprAdaptorEtherIfStatsHistEntry 31 }

cfprAdaptorEtherIfStatsHistTxBytesDeltaMax OBJECT-TYPE
    SYNTAX       Gauge32
    MAX-ACCESS   read-only
    STATUS       current
    DESCRIPTION
        "Cisco Firepower adaptor:EtherIfStatsHist:txBytesDeltaMax
        managed object property"
    ::= { cfprAdaptorEtherIfStatsHistEntry 32 }

cfprAdaptorEtherIfStatsHistTxBytesDeltaMin OBJECT-TYPE
    SYNTAX       Gauge32
    MAX-ACCESS   read-only
    STATUS       current
    DESCRIPTION
        "Cisco Firepower adaptor:EtherIfStatsHist:txBytesDeltaMin
        managed object property"
    ::= { cfprAdaptorEtherIfStatsHistEntry 33 }

cfprAdaptorEtherIfStatsHistTxDropped OBJECT-TYPE
    SYNTAX       Gauge32
    MAX-ACCESS   read-only
    STATUS       current
    DESCRIPTION
        "Cisco Firepower adaptor:EtherIfStatsHist:txDropped
        managed object property"
    ::= { cfprAdaptorEtherIfStatsHistEntry 34 }

cfprAdaptorEtherIfStatsHistTxDroppedDelta OBJECT-TYPE
    SYNTAX       Gauge32
    MAX-ACCESS   read-only
    STATUS       current
    DESCRIPTION
        "Cisco Firepower adaptor:EtherIfStatsHist:txDroppedDelta
        managed object property"
    ::= { cfprAdaptorEtherIfStatsHistEntry 35 }

cfprAdaptorEtherIfStatsHistTxDroppedDeltaAvg OBJECT-TYPE
    SYNTAX       Gauge32
    MAX-ACCESS   read-only
    STATUS       current
    DESCRIPTION
        "Cisco Firepower adaptor:EtherIfStatsHist:txDroppedDeltaAvg
        managed object property"
    ::= { cfprAdaptorEtherIfStatsHistEntry 36 }

cfprAdaptorEtherIfStatsHistTxDroppedDeltaMax OBJECT-TYPE
    SYNTAX       Gauge32
    MAX-ACCESS   read-only
    STATUS       current
    DESCRIPTION
        "Cisco Firepower adaptor:EtherIfStatsHist:txDroppedDeltaMax
        managed object property"
    ::= { cfprAdaptorEtherIfStatsHistEntry 37 }

cfprAdaptorEtherIfStatsHistTxDroppedDeltaMin OBJECT-TYPE
    SYNTAX       Gauge32
    MAX-ACCESS   read-only
    STATUS       current
    DESCRIPTION
        "Cisco Firepower adaptor:EtherIfStatsHist:txDroppedDeltaMin
        managed object property"
    ::= { cfprAdaptorEtherIfStatsHistEntry 38 }

cfprAdaptorEtherIfStatsHistTxErrors OBJECT-TYPE
    SYNTAX       Gauge32
    MAX-ACCESS   read-only
    STATUS       current
    DESCRIPTION
        "Cisco Firepower adaptor:EtherIfStatsHist:txErrors
        managed object property"
    ::= { cfprAdaptorEtherIfStatsHistEntry 39 }

cfprAdaptorEtherIfStatsHistTxErrorsDelta OBJECT-TYPE
    SYNTAX       Gauge32
    MAX-ACCESS   read-only
    STATUS       current
    DESCRIPTION
        "Cisco Firepower adaptor:EtherIfStatsHist:txErrorsDelta
        managed object property"
    ::= { cfprAdaptorEtherIfStatsHistEntry 40 }

cfprAdaptorEtherIfStatsHistTxErrorsDeltaAvg OBJECT-TYPE
    SYNTAX       Gauge32
    MAX-ACCESS   read-only
    STATUS       current
    DESCRIPTION
        "Cisco Firepower adaptor:EtherIfStatsHist:txErrorsDeltaAvg
        managed object property"
    ::= { cfprAdaptorEtherIfStatsHistEntry 41 }

cfprAdaptorEtherIfStatsHistTxErrorsDeltaMax OBJECT-TYPE
    SYNTAX       Gauge32
    MAX-ACCESS   read-only
    STATUS       current
    DESCRIPTION
        "Cisco Firepower adaptor:EtherIfStatsHist:txErrorsDeltaMax
        managed object property"
    ::= { cfprAdaptorEtherIfStatsHistEntry 42 }

cfprAdaptorEtherIfStatsHistTxErrorsDeltaMin OBJECT-TYPE
    SYNTAX       Gauge32
    MAX-ACCESS   read-only
    STATUS       current
    DESCRIPTION
        "Cisco Firepower adaptor:EtherIfStatsHist:txErrorsDeltaMin
        managed object property"
    ::= { cfprAdaptorEtherIfStatsHistEntry 43 }

cfprAdaptorEtherIfStatsHistTxPackets OBJECT-TYPE
    SYNTAX       Gauge32
    MAX-ACCESS   read-only
    STATUS       current
    DESCRIPTION
        "Cisco Firepower adaptor:EtherIfStatsHist:txPackets
        managed object property"
    ::= { cfprAdaptorEtherIfStatsHistEntry 44 }

cfprAdaptorEtherIfStatsHistTxPacketsDelta OBJECT-TYPE
    SYNTAX       Gauge32
    MAX-ACCESS   read-only
    STATUS       current
    DESCRIPTION
        "Cisco Firepower adaptor:EtherIfStatsHist:txPacketsDelta
        managed object property"
    ::= { cfprAdaptorEtherIfStatsHistEntry 45 }

cfprAdaptorEtherIfStatsHistTxPacketsDeltaAvg OBJECT-TYPE
    SYNTAX       Gauge32
    MAX-ACCESS   read-only
    STATUS       current
    DESCRIPTION
        "Cisco Firepower adaptor:EtherIfStatsHist:txPacketsDeltaAvg
        managed object property"
    ::= { cfprAdaptorEtherIfStatsHistEntry 46 }

cfprAdaptorEtherIfStatsHistTxPacketsDeltaMax OBJECT-TYPE
    SYNTAX       Gauge32
    MAX-ACCESS   read-only
    STATUS       current
    DESCRIPTION
        "Cisco Firepower adaptor:EtherIfStatsHist:txPacketsDeltaMax
        managed object property"
    ::= { cfprAdaptorEtherIfStatsHistEntry 47 }

cfprAdaptorEtherIfStatsHistTxPacketsDeltaMin OBJECT-TYPE
    SYNTAX       Gauge32
    MAX-ACCESS   read-only
    STATUS       current
    DESCRIPTION
        "Cisco Firepower adaptor:EtherIfStatsHist:txPacketsDeltaMin
        managed object property"
    ::= { cfprAdaptorEtherIfStatsHistEntry 48 }

cfprAdaptorExtEthIfTable OBJECT-TYPE
    SYNTAX           SEQUENCE OF CfprAdaptorExtEthIfEntry
    MAX-ACCESS       not-accessible
    STATUS           current
    DESCRIPTION
        "Cisco Firepower adaptor:ExtEthIf managed object table"
    ::= { cfprAdaptorObjects 28 }

cfprAdaptorExtEthIfEntry OBJECT-TYPE
    SYNTAX           CfprAdaptorExtEthIfEntry
    MAX-ACCESS       not-accessible
    STATUS           current
    DESCRIPTION
        "Entry for the cfprAdaptorExtEthIfTable table."
    INDEX { cfprAdaptorExtEthIfInstanceId }
    ::= { cfprAdaptorExtEthIfTable 1 }

CfprAdaptorExtEthIfEntry ::= SEQUENCE {
    cfprAdaptorExtEthIfInstanceId                                    CfprManagedObjectId,
    cfprAdaptorExtEthIfDn                                            CfprManagedObjectDn,
    cfprAdaptorExtEthIfRn                                            SnmpAdminString,
    cfprAdaptorExtEthIfAdapterId                                     Gauge32,
    cfprAdaptorExtEthIfAdminState                                    CfprAdaptorExtIfAdminState,
    cfprAdaptorExtEthIfAggrPortId                                    Gauge32,
    cfprAdaptorExtEthIfChassisId                                     Gauge32,
    cfprAdaptorExtEthIfDiscovery                                     CfprEtherSatelliteConnectionDisc,
    cfprAdaptorExtEthIfEpDn                                          SnmpAdminString,
    cfprAdaptorExtEthIfFsmDescr                                      SnmpAdminString,
    cfprAdaptorExtEthIfFsmPrev                                       SnmpAdminString,
    cfprAdaptorExtEthIfFsmProgr                                      Gauge32,
    cfprAdaptorExtEthIfFsmRmtInvErrCode                              Gauge32,
    cfprAdaptorExtEthIfFsmRmtInvErrDescr                             SnmpAdminString,
    cfprAdaptorExtEthIfFsmRmtInvRslt                                 CfprConditionRemoteInvRslt,
    cfprAdaptorExtEthIfFsmStageDescr                                 SnmpAdminString,
    cfprAdaptorExtEthIfFsmStamp                                      DateAndTime,
    cfprAdaptorExtEthIfFsmStatus                                     SnmpAdminString,
    cfprAdaptorExtEthIfFsmTry                                        Gauge32,
    cfprAdaptorExtEthIfId                                            Gauge32,
    cfprAdaptorExtEthIfIfRole                                        CfprNetworkPortRole,
    cfprAdaptorExtEthIfIfType                                        CfprNetworkPhysEpIfType,
    cfprAdaptorExtEthIfLinkState                                     CfprAdaptorLinkState,
    cfprAdaptorExtEthIfLldpMac                                       MacAddress,
    cfprAdaptorExtEthIfLocale                                        CfprNetworkLocale,
    cfprAdaptorExtEthIfMac                                           MacAddress,
    cfprAdaptorExtEthIfMacAddrType                                   CfprAddressType,
    cfprAdaptorExtEthIfName                                          SnmpAdminString,
    cfprAdaptorExtEthIfOperState                                     CfprNetworkPortOperState,
    cfprAdaptorExtEthIfOperStateDesc                                 SnmpAdminString,
    cfprAdaptorExtEthIfPeerAggrPortId                                Gauge32,
    cfprAdaptorExtEthIfPeerChassisId                                 Gauge32,
    cfprAdaptorExtEthIfPeerDn                                        SnmpAdminString,
    cfprAdaptorExtEthIfPeerPortId                                    Gauge32,
    cfprAdaptorExtEthIfPeerSlotId                                    Gauge32,
    cfprAdaptorExtEthIfPhysEpDn                                      SnmpAdminString,
    cfprAdaptorExtEthIfPortId                                        Gauge32,
    cfprAdaptorExtEthIfPurpose                                       CfprAdaptorPurpose,
    cfprAdaptorExtEthIfSide                                          CfprNetworkSide,
    cfprAdaptorExtEthIfSlotId                                        Gauge32,
    cfprAdaptorExtEthIfSwitchId                                      CfprNetworkSwitchId,
    cfprAdaptorExtEthIfTransport                                     CfprNetworkTransport,
    cfprAdaptorExtEthIfType                                          CfprNetworkConnectionType,
    cfprAdaptorExtEthIfServiceState                                  CfprAdaptorServiceState
}

cfprAdaptorExtEthIfInstanceId OBJECT-TYPE
    SYNTAX       CfprManagedObjectId
    MAX-ACCESS   not-accessible
    STATUS       current
    DESCRIPTION
        "Instance identifier of the managed object."
    ::= { cfprAdaptorExtEthIfEntry 1 }

cfprAdaptorExtEthIfDn OBJECT-TYPE
    SYNTAX       CfprManagedObjectDn
    MAX-ACCESS   read-only
    STATUS       current
    DESCRIPTION
        "Cisco Firepower adaptor:ExtEthIf:dn managed object property"
    ::= { cfprAdaptorExtEthIfEntry 2 }

cfprAdaptorExtEthIfRn OBJECT-TYPE
    SYNTAX       SnmpAdminString
    MAX-ACCESS   read-only
    STATUS       current
    DESCRIPTION
        "Cisco Firepower adaptor:ExtEthIf:rn managed object property"
    ::= { cfprAdaptorExtEthIfEntry 3 }

cfprAdaptorExtEthIfAdapterId OBJECT-TYPE
    SYNTAX       Gauge32
    MAX-ACCESS   read-only
    STATUS       current
    DESCRIPTION
        "Cisco Firepower adaptor:ExtEthIf:adapterId managed
        object property"
    ::= { cfprAdaptorExtEthIfEntry 4 }

cfprAdaptorExtEthIfAdminState OBJECT-TYPE
    SYNTAX       CfprAdaptorExtIfAdminState
    MAX-ACCESS   read-only
    STATUS       current
    DESCRIPTION
        "Cisco Firepower adaptor:ExtEthIf:adminState managed
        object property"
    ::= { cfprAdaptorExtEthIfEntry 5 }

cfprAdaptorExtEthIfAggrPortId OBJECT-TYPE
    SYNTAX       Gauge32
    MAX-ACCESS   read-only
    STATUS       current
    DESCRIPTION
        "Cisco Firepower adaptor:ExtEthIf:aggrPortId managed
        object property"
    ::= { cfprAdaptorExtEthIfEntry 6 }

cfprAdaptorExtEthIfChassisId OBJECT-TYPE
    SYNTAX       Gauge32
    MAX-ACCESS   read-only
    STATUS       current
    DESCRIPTION
        "Cisco Firepower adaptor:ExtEthIf:chassisId managed
        object property"
    ::= { cfprAdaptorExtEthIfEntry 7 }

cfprAdaptorExtEthIfDiscovery OBJECT-TYPE
    SYNTAX       CfprEtherSatelliteConnectionDisc
    MAX-ACCESS   read-only
    STATUS       current
    DESCRIPTION
        "Cisco Firepower adaptor:ExtEthIf:discovery managed
        object property"
    ::= { cfprAdaptorExtEthIfEntry 8 }

cfprAdaptorExtEthIfEpDn OBJECT-TYPE
    SYNTAX       SnmpAdminString
    MAX-ACCESS   read-only
    STATUS       current
    DESCRIPTION
        "Cisco Firepower adaptor:ExtEthIf:epDn managed object property"
    ::= { cfprAdaptorExtEthIfEntry 9 }

cfprAdaptorExtEthIfFsmDescr OBJECT-TYPE
    SYNTAX       SnmpAdminString
    MAX-ACCESS   read-only
    STATUS       current
    DESCRIPTION
        "Cisco Firepower adaptor:ExtEthIf:fsmDescr managed
        object property"
    ::= { cfprAdaptorExtEthIfEntry 10 }

cfprAdaptorExtEthIfFsmPrev OBJECT-TYPE
    SYNTAX       SnmpAdminString
    MAX-ACCESS   read-only
    STATUS       current
    DESCRIPTION
        "Cisco Firepower adaptor:ExtEthIf:fsmPrev managed object property"
    ::= { cfprAdaptorExtEthIfEntry 11 }

cfprAdaptorExtEthIfFsmProgr OBJECT-TYPE
    SYNTAX       Gauge32
    MAX-ACCESS   read-only
    STATUS       current
    DESCRIPTION
        "Cisco Firepower adaptor:ExtEthIf:fsmProgr managed
        object property"
    ::= { cfprAdaptorExtEthIfEntry 12 }

cfprAdaptorExtEthIfFsmRmtInvErrCode OBJECT-TYPE
    SYNTAX       Gauge32
    MAX-ACCESS   read-only
    STATUS       current
    DESCRIPTION
        "Cisco Firepower adaptor:ExtEthIf:fsmRmtInvErrCode
        managed object property"
    ::= { cfprAdaptorExtEthIfEntry 13 }

cfprAdaptorExtEthIfFsmRmtInvErrDescr OBJECT-TYPE
    SYNTAX       SnmpAdminString
    MAX-ACCESS   read-only
    STATUS       current
    DESCRIPTION
        "Cisco Firepower adaptor:ExtEthIf:fsmRmtInvErrDescr
        managed object property"
    ::= { cfprAdaptorExtEthIfEntry 14 }

cfprAdaptorExtEthIfFsmRmtInvRslt OBJECT-TYPE
    SYNTAX       CfprConditionRemoteInvRslt
    MAX-ACCESS   read-only
    STATUS       current
    DESCRIPTION
        "Cisco Firepower adaptor:ExtEthIf:fsmRmtInvRslt
        managed object property"
    ::= { cfprAdaptorExtEthIfEntry 15 }

cfprAdaptorExtEthIfFsmStageDescr OBJECT-TYPE
    SYNTAX       SnmpAdminString
    MAX-ACCESS   read-only
    STATUS       current
    DESCRIPTION
        "Cisco Firepower adaptor:ExtEthIf:fsmStageDescr
        managed object property"
    ::= { cfprAdaptorExtEthIfEntry 16 }

cfprAdaptorExtEthIfFsmStamp OBJECT-TYPE
    SYNTAX       DateAndTime
    MAX-ACCESS   read-only
    STATUS       current
    DESCRIPTION
        "Cisco Firepower adaptor:ExtEthIf:fsmStamp managed
        object property"
    ::= { cfprAdaptorExtEthIfEntry 17 }

cfprAdaptorExtEthIfFsmStatus OBJECT-TYPE
    SYNTAX       SnmpAdminString
    MAX-ACCESS   read-only
    STATUS       current
    DESCRIPTION
        "Cisco Firepower adaptor:ExtEthIf:fsmStatus managed
        object property"
    ::= { cfprAdaptorExtEthIfEntry 18 }

cfprAdaptorExtEthIfFsmTry OBJECT-TYPE
    SYNTAX       Gauge32
    MAX-ACCESS   read-only
    STATUS       current
    DESCRIPTION
        "Cisco Firepower adaptor:ExtEthIf:fsmTry managed object property"
    ::= { cfprAdaptorExtEthIfEntry 19 }

cfprAdaptorExtEthIfId OBJECT-TYPE
    SYNTAX       Gauge32
    MAX-ACCESS   read-only
    STATUS       current
    DESCRIPTION
        "Cisco Firepower adaptor:ExtEthIf:id managed object property"
    ::= { cfprAdaptorExtEthIfEntry 20 }

cfprAdaptorExtEthIfIfRole OBJECT-TYPE
    SYNTAX       CfprNetworkPortRole
    MAX-ACCESS   read-only
    STATUS       current
    DESCRIPTION
        "Cisco Firepower adaptor:ExtEthIf:ifRole managed object property"
    ::= { cfprAdaptorExtEthIfEntry 21 }

cfprAdaptorExtEthIfIfType OBJECT-TYPE
    SYNTAX       CfprNetworkPhysEpIfType
    MAX-ACCESS   read-only
    STATUS       current
    DESCRIPTION
        "Cisco Firepower adaptor:ExtEthIf:ifType managed object property"
    ::= { cfprAdaptorExtEthIfEntry 22 }

cfprAdaptorExtEthIfLinkState OBJECT-TYPE
    SYNTAX       CfprAdaptorLinkState
    MAX-ACCESS   read-only
    STATUS       current
    DESCRIPTION
        "Cisco Firepower adaptor:ExtEthIf:linkState managed
        object property"
    ::= { cfprAdaptorExtEthIfEntry 23 }

cfprAdaptorExtEthIfLldpMac OBJECT-TYPE
    SYNTAX       MacAddress
    MAX-ACCESS   read-only
    STATUS       current
    DESCRIPTION
        "Cisco Firepower adaptor:ExtEthIf:lldpMac managed object property"
    ::= { cfprAdaptorExtEthIfEntry 24 }

cfprAdaptorExtEthIfLocale OBJECT-TYPE
    SYNTAX       CfprNetworkLocale
    MAX-ACCESS   read-only
    STATUS       current
    DESCRIPTION
        "Cisco Firepower adaptor:ExtEthIf:locale managed object property"
    ::= { cfprAdaptorExtEthIfEntry 25 }

cfprAdaptorExtEthIfMac OBJECT-TYPE
    SYNTAX       MacAddress
    MAX-ACCESS   read-only
    STATUS       current
    DESCRIPTION
        "Cisco Firepower adaptor:ExtEthIf:mac managed object property"
    ::= { cfprAdaptorExtEthIfEntry 26 }

cfprAdaptorExtEthIfMacAddrType OBJECT-TYPE
    SYNTAX       CfprAddressType
    MAX-ACCESS   read-only
    STATUS       current
    DESCRIPTION
        "Cisco Firepower adaptor:ExtEthIf:macAddrType managed
        object property"
    ::= { cfprAdaptorExtEthIfEntry 27 }

cfprAdaptorExtEthIfName OBJECT-TYPE
    SYNTAX       SnmpAdminString
    MAX-ACCESS   read-only
    STATUS       current
    DESCRIPTION
        "Cisco Firepower adaptor:ExtEthIf:name managed object property"
    ::= { cfprAdaptorExtEthIfEntry 28 }

cfprAdaptorExtEthIfOperState OBJECT-TYPE
    SYNTAX       CfprNetworkPortOperState
    MAX-ACCESS   read-only
    STATUS       current
    DESCRIPTION
        "Cisco Firepower adaptor:ExtEthIf:operState managed
        object property"
    ::= { cfprAdaptorExtEthIfEntry 29 }

cfprAdaptorExtEthIfOperStateDesc OBJECT-TYPE
    SYNTAX       SnmpAdminString
    MAX-ACCESS   read-only
    STATUS       current
    DESCRIPTION
        "Cisco Firepower adaptor:ExtEthIf:operStateDesc
        managed object property"
    ::= { cfprAdaptorExtEthIfEntry 30 }

cfprAdaptorExtEthIfPeerAggrPortId OBJECT-TYPE
    SYNTAX       Gauge32
    MAX-ACCESS   read-only
    STATUS       current
    DESCRIPTION
        "Cisco Firepower adaptor:ExtEthIf:peerAggrPortId
        managed object property"
    ::= { cfprAdaptorExtEthIfEntry 31 }

cfprAdaptorExtEthIfPeerChassisId OBJECT-TYPE
    SYNTAX       Gauge32
    MAX-ACCESS   read-only
    STATUS       current
    DESCRIPTION
        "Cisco Firepower adaptor:ExtEthIf:peerChassisId
        managed object property"
    ::= { cfprAdaptorExtEthIfEntry 32 }

cfprAdaptorExtEthIfPeerDn OBJECT-TYPE
    SYNTAX       SnmpAdminString
    MAX-ACCESS   read-only
    STATUS       current
    DESCRIPTION
        "Cisco Firepower adaptor:ExtEthIf:peerDn managed object property"
    ::= { cfprAdaptorExtEthIfEntry 33 }

cfprAdaptorExtEthIfPeerPortId OBJECT-TYPE
    SYNTAX       Gauge32
    MAX-ACCESS   read-only
    STATUS       current
    DESCRIPTION
        "Cisco Firepower adaptor:ExtEthIf:peerPortId managed
        object property"
    ::= { cfprAdaptorExtEthIfEntry 34 }

cfprAdaptorExtEthIfPeerSlotId OBJECT-TYPE
    SYNTAX       Gauge32
    MAX-ACCESS   read-only
    STATUS       current
    DESCRIPTION
        "Cisco Firepower adaptor:ExtEthIf:peerSlotId managed
        object property"
    ::= { cfprAdaptorExtEthIfEntry 35 }

cfprAdaptorExtEthIfPhysEpDn OBJECT-TYPE
    SYNTAX       SnmpAdminString
    MAX-ACCESS   read-only
    STATUS       current
    DESCRIPTION
        "Cisco Firepower adaptor:ExtEthIf:physEpDn managed
        object property"
    ::= { cfprAdaptorExtEthIfEntry 36 }

cfprAdaptorExtEthIfPortId OBJECT-TYPE
    SYNTAX       Gauge32
    MAX-ACCESS   read-only
    STATUS       current
    DESCRIPTION
        "Cisco Firepower adaptor:ExtEthIf:portId managed object property"
    ::= { cfprAdaptorExtEthIfEntry 37 }

cfprAdaptorExtEthIfPurpose OBJECT-TYPE
    SYNTAX       CfprAdaptorPurpose
    MAX-ACCESS   read-only
    STATUS       current
    DESCRIPTION
        "Cisco Firepower adaptor:ExtEthIf:purpose managed object property"
    ::= { cfprAdaptorExtEthIfEntry 38 }

cfprAdaptorExtEthIfSide OBJECT-TYPE
    SYNTAX       CfprNetworkSide
    MAX-ACCESS   read-only
    STATUS       current
    DESCRIPTION
        "Cisco Firepower adaptor:ExtEthIf:side managed object property"
    ::= { cfprAdaptorExtEthIfEntry 39 }

cfprAdaptorExtEthIfSlotId OBJECT-TYPE
    SYNTAX       Gauge32
    MAX-ACCESS   read-only
    STATUS       current
    DESCRIPTION
        "Cisco Firepower adaptor:ExtEthIf:slotId managed object property"
    ::= { cfprAdaptorExtEthIfEntry 40 }

cfprAdaptorExtEthIfSwitchId OBJECT-TYPE
    SYNTAX       CfprNetworkSwitchId
    MAX-ACCESS   read-only
    STATUS       current
    DESCRIPTION
        "Cisco Firepower adaptor:ExtEthIf:switchId managed
        object property"
    ::= { cfprAdaptorExtEthIfEntry 41 }

cfprAdaptorExtEthIfTransport OBJECT-TYPE
    SYNTAX       CfprNetworkTransport
    MAX-ACCESS   read-only
    STATUS       current
    DESCRIPTION
        "Cisco Firepower adaptor:ExtEthIf:transport managed
        object property"
    ::= { cfprAdaptorExtEthIfEntry 42 }

cfprAdaptorExtEthIfType OBJECT-TYPE
    SYNTAX       CfprNetworkConnectionType
    MAX-ACCESS   read-only
    STATUS       current
    DESCRIPTION
        "Cisco Firepower adaptor:ExtEthIf:type managed object property"
    ::= { cfprAdaptorExtEthIfEntry 43 }

cfprAdaptorExtEthIfServiceState OBJECT-TYPE
    SYNTAX       CfprAdaptorServiceState
    MAX-ACCESS   read-only
    STATUS       current
    DESCRIPTION
        "Cisco Firepower adaptor:ExtEthIf:serviceState
        managed object property"
    ::= { cfprAdaptorExtEthIfEntry 44 }

cfprAdaptorExtEthIfFsmTable OBJECT-TYPE
    SYNTAX           SEQUENCE OF CfprAdaptorExtEthIfFsmEntry
    MAX-ACCESS       not-accessible
    STATUS           current
    DESCRIPTION
        "Cisco Firepower adaptor:ExtEthIfFsm managed object table"
    ::= { cfprAdaptorObjects 29 }

cfprAdaptorExtEthIfFsmEntry OBJECT-TYPE
    SYNTAX           CfprAdaptorExtEthIfFsmEntry
    MAX-ACCESS       not-accessible
    STATUS           current
    DESCRIPTION
        "Entry for the cfprAdaptorExtEthIfFsmTable table."
    INDEX { cfprAdaptorExtEthIfFsmInstanceId }
    ::= { cfprAdaptorExtEthIfFsmTable 1 }

CfprAdaptorExtEthIfFsmEntry ::= SEQUENCE {
    cfprAdaptorExtEthIfFsmInstanceId                                 CfprManagedObjectId,
    cfprAdaptorExtEthIfFsmDn                                         CfprManagedObjectDn,
    cfprAdaptorExtEthIfFsmRn                                         SnmpAdminString,
    cfprAdaptorExtEthIfFsmCompletionTime                             DateAndTime,
    cfprAdaptorExtEthIfFsmCurrentFsm                                 CfprAdaptorExtEthIfFsmCurrentFsm,
    cfprAdaptorExtEthIfFsmDescrData                                  SnmpAdminString,
    cfprAdaptorExtEthIfFsmFsmStatus                                  CfprFsmFsmStageStatus,
    cfprAdaptorExtEthIfFsmProgress                                   Gauge32,
    cfprAdaptorExtEthIfFsmRmtErrCode                                 Gauge32,
    cfprAdaptorExtEthIfFsmRmtErrDescr                                SnmpAdminString,
    cfprAdaptorExtEthIfFsmRmtRslt                                    CfprConditionRemoteInvRslt
}

cfprAdaptorExtEthIfFsmInstanceId OBJECT-TYPE
    SYNTAX       CfprManagedObjectId
    MAX-ACCESS   not-accessible
    STATUS       current
    DESCRIPTION
        "Instance identifier of the managed object."
    ::= { cfprAdaptorExtEthIfFsmEntry 1 }

cfprAdaptorExtEthIfFsmDn OBJECT-TYPE
    SYNTAX       CfprManagedObjectDn
    MAX-ACCESS   read-only
    STATUS       current
    DESCRIPTION
        "Cisco Firepower adaptor:ExtEthIfFsm:dn managed object property"
    ::= { cfprAdaptorExtEthIfFsmEntry 2 }

cfprAdaptorExtEthIfFsmRn OBJECT-TYPE
    SYNTAX       SnmpAdminString
    MAX-ACCESS   read-only
    STATUS       current
    DESCRIPTION
        "Cisco Firepower adaptor:ExtEthIfFsm:rn managed object property"
    ::= { cfprAdaptorExtEthIfFsmEntry 3 }

cfprAdaptorExtEthIfFsmCompletionTime OBJECT-TYPE
    SYNTAX       DateAndTime
    MAX-ACCESS   read-only
    STATUS       current
    DESCRIPTION
        "Cisco Firepower adaptor:ExtEthIfFsm:completionTime
        managed object property"
    ::= { cfprAdaptorExtEthIfFsmEntry 4 }

cfprAdaptorExtEthIfFsmCurrentFsm OBJECT-TYPE
    SYNTAX       CfprAdaptorExtEthIfFsmCurrentFsm
    MAX-ACCESS   read-only
    STATUS       current
    DESCRIPTION
        "Cisco Firepower adaptor:ExtEthIfFsm:currentFsm
        managed object property"
    ::= { cfprAdaptorExtEthIfFsmEntry 5 }

cfprAdaptorExtEthIfFsmDescrData OBJECT-TYPE
    SYNTAX       SnmpAdminString
    MAX-ACCESS   read-only
    STATUS       current
    DESCRIPTION
        "Cisco Firepower adaptor:ExtEthIfFsm:descr managed
        object property"
    ::= { cfprAdaptorExtEthIfFsmEntry 6 }

cfprAdaptorExtEthIfFsmFsmStatus OBJECT-TYPE
    SYNTAX       CfprFsmFsmStageStatus
    MAX-ACCESS   read-only
    STATUS       current
    DESCRIPTION
        "Cisco Firepower adaptor:ExtEthIfFsm:fsmStatus
        managed object property"
    ::= { cfprAdaptorExtEthIfFsmEntry 7 }

cfprAdaptorExtEthIfFsmProgress OBJECT-TYPE
    SYNTAX       Gauge32
    MAX-ACCESS   read-only
    STATUS       current
    DESCRIPTION
        "Cisco Firepower adaptor:ExtEthIfFsm:progress managed
        object property"
    ::= { cfprAdaptorExtEthIfFsmEntry 8 }

cfprAdaptorExtEthIfFsmRmtErrCode OBJECT-TYPE
    SYNTAX       Gauge32
    MAX-ACCESS   read-only
    STATUS       current
    DESCRIPTION
        "Cisco Firepower adaptor:ExtEthIfFsm:rmtErrCode
        managed object property"
    ::= { cfprAdaptorExtEthIfFsmEntry 9 }

cfprAdaptorExtEthIfFsmRmtErrDescr OBJECT-TYPE
    SYNTAX       SnmpAdminString
    MAX-ACCESS   read-only
    STATUS       current
    DESCRIPTION
        "Cisco Firepower adaptor:ExtEthIfFsm:rmtErrDescr
        managed object property"
    ::= { cfprAdaptorExtEthIfFsmEntry 10 }

cfprAdaptorExtEthIfFsmRmtRslt OBJECT-TYPE
    SYNTAX       CfprConditionRemoteInvRslt
    MAX-ACCESS   read-only
    STATUS       current
    DESCRIPTION
        "Cisco Firepower adaptor:ExtEthIfFsm:rmtRslt managed
        object property"
    ::= { cfprAdaptorExtEthIfFsmEntry 11 }

cfprAdaptorExtEthIfFsmStageTable OBJECT-TYPE
    SYNTAX           SEQUENCE OF CfprAdaptorExtEthIfFsmStageEntry
    MAX-ACCESS       not-accessible
    STATUS           current
    DESCRIPTION
        "Cisco Firepower adaptor:ExtEthIfFsmStage managed object table"
    ::= { cfprAdaptorObjects 30 }

cfprAdaptorExtEthIfFsmStageEntry OBJECT-TYPE
    SYNTAX           CfprAdaptorExtEthIfFsmStageEntry
    MAX-ACCESS       not-accessible
    STATUS           current
    DESCRIPTION
        "Entry for the cfprAdaptorExtEthIfFsmStageTable table."
    INDEX { cfprAdaptorExtEthIfFsmStageInstanceId }
    ::= { cfprAdaptorExtEthIfFsmStageTable 1 }

CfprAdaptorExtEthIfFsmStageEntry ::= SEQUENCE {
    cfprAdaptorExtEthIfFsmStageInstanceId                            CfprManagedObjectId,
    cfprAdaptorExtEthIfFsmStageDn                                    CfprManagedObjectDn,
    cfprAdaptorExtEthIfFsmStageRn                                    SnmpAdminString,
    cfprAdaptorExtEthIfFsmStageDescrData                             SnmpAdminString,
    cfprAdaptorExtEthIfFsmStageLastUpdateTime                        DateAndTime,
    cfprAdaptorExtEthIfFsmStageName                                  CfprAdaptorExtEthIfFsmStageName,
    cfprAdaptorExtEthIfFsmStageOrder                                 Gauge32,
    cfprAdaptorExtEthIfFsmStageRetry                                 Gauge32,
    cfprAdaptorExtEthIfFsmStageStageStatus                           CfprFsmFsmStageStatus
}

cfprAdaptorExtEthIfFsmStageInstanceId OBJECT-TYPE
    SYNTAX       CfprManagedObjectId
    MAX-ACCESS   not-accessible
    STATUS       current
    DESCRIPTION
        "Instance identifier of the managed object."
    ::= { cfprAdaptorExtEthIfFsmStageEntry 1 }

cfprAdaptorExtEthIfFsmStageDn OBJECT-TYPE
    SYNTAX       CfprManagedObjectDn
    MAX-ACCESS   read-only
    STATUS       current
    DESCRIPTION
        "Cisco Firepower adaptor:ExtEthIfFsmStage:dn managed
        object property"
    ::= { cfprAdaptorExtEthIfFsmStageEntry 2 }

cfprAdaptorExtEthIfFsmStageRn OBJECT-TYPE
    SYNTAX       SnmpAdminString
    MAX-ACCESS   read-only
    STATUS       current
    DESCRIPTION
        "Cisco Firepower adaptor:ExtEthIfFsmStage:rn managed
        object property"
    ::= { cfprAdaptorExtEthIfFsmStageEntry 3 }

cfprAdaptorExtEthIfFsmStageDescrData OBJECT-TYPE
    SYNTAX       SnmpAdminString
    MAX-ACCESS   read-only
    STATUS       current
    DESCRIPTION
        "Cisco Firepower adaptor:ExtEthIfFsmStage:descr
        managed object property"
    ::= { cfprAdaptorExtEthIfFsmStageEntry 4 }

cfprAdaptorExtEthIfFsmStageLastUpdateTime OBJECT-TYPE
    SYNTAX       DateAndTime
    MAX-ACCESS   read-only
    STATUS       current
    DESCRIPTION
        "Cisco Firepower adaptor:ExtEthIfFsmStage:lastUpdateTime
        managed object property"
    ::= { cfprAdaptorExtEthIfFsmStageEntry 5 }

cfprAdaptorExtEthIfFsmStageName OBJECT-TYPE
    SYNTAX       CfprAdaptorExtEthIfFsmStageName
    MAX-ACCESS   read-only
    STATUS       current
    DESCRIPTION
        "Cisco Firepower adaptor:ExtEthIfFsmStage:name
        managed object property"
    ::= { cfprAdaptorExtEthIfFsmStageEntry 6 }

cfprAdaptorExtEthIfFsmStageOrder OBJECT-TYPE
    SYNTAX       Gauge32
    MAX-ACCESS   read-only
    STATUS       current
    DESCRIPTION
        "Cisco Firepower adaptor:ExtEthIfFsmStage:order
        managed object property"
    ::= { cfprAdaptorExtEthIfFsmStageEntry 7 }

cfprAdaptorExtEthIfFsmStageRetry OBJECT-TYPE
    SYNTAX       Gauge32
    MAX-ACCESS   read-only
    STATUS       current
    DESCRIPTION
        "Cisco Firepower adaptor:ExtEthIfFsmStage:retry
        managed object property"
    ::= { cfprAdaptorExtEthIfFsmStageEntry 8 }

cfprAdaptorExtEthIfFsmStageStageStatus OBJECT-TYPE
    SYNTAX       CfprFsmFsmStageStatus
    MAX-ACCESS   read-only
    STATUS       current
    DESCRIPTION
        "Cisco Firepower adaptor:ExtEthIfFsmStage:stageStatus
        managed object property"
    ::= { cfprAdaptorExtEthIfFsmStageEntry 9 }

cfprAdaptorExtEthIfFsmTaskTable OBJECT-TYPE
    SYNTAX           SEQUENCE OF CfprAdaptorExtEthIfFsmTaskEntry
    MAX-ACCESS       not-accessible
    STATUS           current
    DESCRIPTION
        "Cisco Firepower adaptor:ExtEthIfFsmTask managed object table"
    ::= { cfprAdaptorObjects 31 }

cfprAdaptorExtEthIfFsmTaskEntry OBJECT-TYPE
    SYNTAX           CfprAdaptorExtEthIfFsmTaskEntry
    MAX-ACCESS       not-accessible
    STATUS           current
    DESCRIPTION
        "Entry for the cfprAdaptorExtEthIfFsmTaskTable table."
    INDEX { cfprAdaptorExtEthIfFsmTaskInstanceId }
    ::= { cfprAdaptorExtEthIfFsmTaskTable 1 }

CfprAdaptorExtEthIfFsmTaskEntry ::= SEQUENCE {
    cfprAdaptorExtEthIfFsmTaskInstanceId                             CfprManagedObjectId,
    cfprAdaptorExtEthIfFsmTaskDn                                     CfprManagedObjectDn,
    cfprAdaptorExtEthIfFsmTaskRn                                     SnmpAdminString,
    cfprAdaptorExtEthIfFsmTaskCompletion                             CfprFsmCompletion,
    cfprAdaptorExtEthIfFsmTaskFlags                                  CfprFsmFlags,
    cfprAdaptorExtEthIfFsmTaskItem                                   CfprAdaptorExtEthIfFsmTaskItem,
    cfprAdaptorExtEthIfFsmTaskSeqId                                  Gauge32
}

cfprAdaptorExtEthIfFsmTaskInstanceId OBJECT-TYPE
    SYNTAX       CfprManagedObjectId
    MAX-ACCESS   not-accessible
    STATUS       current
    DESCRIPTION
        "Instance identifier of the managed object."
    ::= { cfprAdaptorExtEthIfFsmTaskEntry 1 }

cfprAdaptorExtEthIfFsmTaskDn OBJECT-TYPE
    SYNTAX       CfprManagedObjectDn
    MAX-ACCESS   read-only
    STATUS       current
    DESCRIPTION
        "Cisco Firepower adaptor:ExtEthIfFsmTask:dn managed
        object property"
    ::= { cfprAdaptorExtEthIfFsmTaskEntry 2 }

cfprAdaptorExtEthIfFsmTaskRn OBJECT-TYPE
    SYNTAX       SnmpAdminString
    MAX-ACCESS   read-only
    STATUS       current
    DESCRIPTION
        "Cisco Firepower adaptor:ExtEthIfFsmTask:rn managed
        object property"
    ::= { cfprAdaptorExtEthIfFsmTaskEntry 3 }

cfprAdaptorExtEthIfFsmTaskCompletion OBJECT-TYPE
    SYNTAX       CfprFsmCompletion
    MAX-ACCESS   read-only
    STATUS       current
    DESCRIPTION
        "Cisco Firepower adaptor:ExtEthIfFsmTask:completion
        managed object property"
    ::= { cfprAdaptorExtEthIfFsmTaskEntry 4 }

cfprAdaptorExtEthIfFsmTaskFlags OBJECT-TYPE
    SYNTAX       CfprFsmFlags
    MAX-ACCESS   read-only
    STATUS       current
    DESCRIPTION
        "Cisco Firepower adaptor:ExtEthIfFsmTask:flags
        managed object property"
    ::= { cfprAdaptorExtEthIfFsmTaskEntry 5 }

cfprAdaptorExtEthIfFsmTaskItem OBJECT-TYPE
    SYNTAX       CfprAdaptorExtEthIfFsmTaskItem
    MAX-ACCESS   read-only
    STATUS       current
    DESCRIPTION
        "Cisco Firepower adaptor:ExtEthIfFsmTask:item managed
        object property"
    ::= { cfprAdaptorExtEthIfFsmTaskEntry 6 }

cfprAdaptorExtEthIfFsmTaskSeqId OBJECT-TYPE
    SYNTAX       Gauge32
    MAX-ACCESS   read-only
    STATUS       current
    DESCRIPTION
        "Cisco Firepower adaptor:ExtEthIfFsmTask:seqId
        managed object property"
    ::= { cfprAdaptorExtEthIfFsmTaskEntry 7 }

cfprAdaptorExtEthIfPcTable OBJECT-TYPE
    SYNTAX           SEQUENCE OF CfprAdaptorExtEthIfPcEntry
    MAX-ACCESS       not-accessible
    STATUS           current
    DESCRIPTION
        "Cisco Firepower adaptor:ExtEthIfPc managed object table"
    ::= { cfprAdaptorObjects 32 }

cfprAdaptorExtEthIfPcEntry OBJECT-TYPE
    SYNTAX           CfprAdaptorExtEthIfPcEntry
    MAX-ACCESS       not-accessible
    STATUS           current
    DESCRIPTION
        "Entry for the cfprAdaptorExtEthIfPcTable table."
    INDEX { cfprAdaptorExtEthIfPcInstanceId }
    ::= { cfprAdaptorExtEthIfPcTable 1 }

CfprAdaptorExtEthIfPcEntry ::= SEQUENCE {
    cfprAdaptorExtEthIfPcInstanceId                                  CfprManagedObjectId,
    cfprAdaptorExtEthIfPcDn                                          CfprManagedObjectDn,
    cfprAdaptorExtEthIfPcRn                                          SnmpAdminString,
    cfprAdaptorExtEthIfPcEpDn                                        SnmpAdminString,
    cfprAdaptorExtEthIfPcFltAggr                                     Unsigned64,
    cfprAdaptorExtEthIfPcIfRole                                      CfprAdaptorExtIfPcIfRole,
    cfprAdaptorExtEthIfPcIfType                                      CfprAdaptorCIoEpIfType,
    cfprAdaptorExtEthIfPcLocale                                      CfprAdaptorExternalPcLocale,
    cfprAdaptorExtEthIfPcMac                                         MacAddress,
    cfprAdaptorExtEthIfPcName                                        SnmpAdminString,
    cfprAdaptorExtEthIfPcOperSpeed                                   CfprPortEthSpeed,
    cfprAdaptorExtEthIfPcOperState                                   CfprNetworkPortOperState,
    cfprAdaptorExtEthIfPcPeerDn                                      SnmpAdminString,
    cfprAdaptorExtEthIfPcPortId                                      CfprAdaptorExtEthIfPcPortId,
    cfprAdaptorExtEthIfPcStateQual                                   SnmpAdminString,
    cfprAdaptorExtEthIfPcSwitchId                                    CfprNetworkSwitchId,
    cfprAdaptorExtEthIfPcTransport                                   CfprAdaptorExtEthIfPcTransport,
    cfprAdaptorExtEthIfPcType                                        CfprAdaptorExtIfPcType
}

cfprAdaptorExtEthIfPcInstanceId OBJECT-TYPE
    SYNTAX       CfprManagedObjectId
    MAX-ACCESS   not-accessible
    STATUS       current
    DESCRIPTION
        "Instance identifier of the managed object."
    ::= { cfprAdaptorExtEthIfPcEntry 1 }

cfprAdaptorExtEthIfPcDn OBJECT-TYPE
    SYNTAX       CfprManagedObjectDn
    MAX-ACCESS   read-only
    STATUS       current
    DESCRIPTION
        "Cisco Firepower adaptor:ExtEthIfPc:dn managed object property"
    ::= { cfprAdaptorExtEthIfPcEntry 2 }

cfprAdaptorExtEthIfPcRn OBJECT-TYPE
    SYNTAX       SnmpAdminString
    MAX-ACCESS   read-only
    STATUS       current
    DESCRIPTION
        "Cisco Firepower adaptor:ExtEthIfPc:rn managed object property"
    ::= { cfprAdaptorExtEthIfPcEntry 3 }

cfprAdaptorExtEthIfPcEpDn OBJECT-TYPE
    SYNTAX       SnmpAdminString
    MAX-ACCESS   read-only
    STATUS       current
    DESCRIPTION
        "Cisco Firepower adaptor:ExtEthIfPc:epDn managed object property"
    ::= { cfprAdaptorExtEthIfPcEntry 4 }

cfprAdaptorExtEthIfPcFltAggr OBJECT-TYPE
    SYNTAX       Unsigned64
    MAX-ACCESS   read-only
    STATUS       current
    DESCRIPTION
        "Cisco Firepower adaptor:ExtEthIfPc:fltAggr managed
        object property"
    ::= { cfprAdaptorExtEthIfPcEntry 5 }

cfprAdaptorExtEthIfPcIfRole OBJECT-TYPE
    SYNTAX       CfprAdaptorExtIfPcIfRole
    MAX-ACCESS   read-only
    STATUS       current
    DESCRIPTION
        "Cisco Firepower adaptor:ExtEthIfPc:ifRole managed
        object property"
    ::= { cfprAdaptorExtEthIfPcEntry 6 }

cfprAdaptorExtEthIfPcIfType OBJECT-TYPE
    SYNTAX       CfprAdaptorCIoEpIfType
    MAX-ACCESS   read-only
    STATUS       current
    DESCRIPTION
        "Cisco Firepower adaptor:ExtEthIfPc:ifType managed
        object property"
    ::= { cfprAdaptorExtEthIfPcEntry 7 }

cfprAdaptorExtEthIfPcLocale OBJECT-TYPE
    SYNTAX       CfprAdaptorExternalPcLocale
    MAX-ACCESS   read-only
    STATUS       current
    DESCRIPTION
        "Cisco Firepower adaptor:ExtEthIfPc:locale managed
        object property"
    ::= { cfprAdaptorExtEthIfPcEntry 8 }

cfprAdaptorExtEthIfPcMac OBJECT-TYPE
    SYNTAX       MacAddress
    MAX-ACCESS   read-only
    STATUS       current
    DESCRIPTION
        "Cisco Firepower adaptor:ExtEthIfPc:mac managed object property"
    ::= { cfprAdaptorExtEthIfPcEntry 9 }

cfprAdaptorExtEthIfPcName OBJECT-TYPE
    SYNTAX       SnmpAdminString
    MAX-ACCESS   read-only
    STATUS       current
    DESCRIPTION
        "Cisco Firepower adaptor:ExtEthIfPc:name managed object property"
    ::= { cfprAdaptorExtEthIfPcEntry 10 }

cfprAdaptorExtEthIfPcOperSpeed OBJECT-TYPE
    SYNTAX       CfprPortEthSpeed
    MAX-ACCESS   read-only
    STATUS       current
    DESCRIPTION
        "Cisco Firepower adaptor:ExtEthIfPc:operSpeed managed
        object property"
    ::= { cfprAdaptorExtEthIfPcEntry 11 }

cfprAdaptorExtEthIfPcOperState OBJECT-TYPE
    SYNTAX       CfprNetworkPortOperState
    MAX-ACCESS   read-only
    STATUS       current
    DESCRIPTION
        "Cisco Firepower adaptor:ExtEthIfPc:operState managed
        object property"
    ::= { cfprAdaptorExtEthIfPcEntry 12 }

cfprAdaptorExtEthIfPcPeerDn OBJECT-TYPE
    SYNTAX       SnmpAdminString
    MAX-ACCESS   read-only
    STATUS       current
    DESCRIPTION
        "Cisco Firepower adaptor:ExtEthIfPc:peerDn managed
        object property"
    ::= { cfprAdaptorExtEthIfPcEntry 13 }

cfprAdaptorExtEthIfPcPortId OBJECT-TYPE
    SYNTAX       CfprAdaptorExtEthIfPcPortId
    MAX-ACCESS   read-only
    STATUS       current
    DESCRIPTION
        "Cisco Firepower adaptor:ExtEthIfPc:portId managed
        object property"
    ::= { cfprAdaptorExtEthIfPcEntry 14 }

cfprAdaptorExtEthIfPcStateQual OBJECT-TYPE
    SYNTAX       SnmpAdminString
    MAX-ACCESS   read-only
    STATUS       current
    DESCRIPTION
        "Cisco Firepower adaptor:ExtEthIfPc:stateQual managed
        object property"
    ::= { cfprAdaptorExtEthIfPcEntry 15 }

cfprAdaptorExtEthIfPcSwitchId OBJECT-TYPE
    SYNTAX       CfprNetworkSwitchId
    MAX-ACCESS   read-only
    STATUS       current
    DESCRIPTION
        "Cisco Firepower adaptor:ExtEthIfPc:switchId managed
        object property"
    ::= { cfprAdaptorExtEthIfPcEntry 16 }

cfprAdaptorExtEthIfPcTransport OBJECT-TYPE
    SYNTAX       CfprAdaptorExtEthIfPcTransport
    MAX-ACCESS   read-only
    STATUS       current
    DESCRIPTION
        "Cisco Firepower adaptor:ExtEthIfPc:transport managed
        object property"
    ::= { cfprAdaptorExtEthIfPcEntry 17 }

cfprAdaptorExtEthIfPcType OBJECT-TYPE
    SYNTAX       CfprAdaptorExtIfPcType
    MAX-ACCESS   read-only
    STATUS       current
    DESCRIPTION
        "Cisco Firepower adaptor:ExtEthIfPc:type managed object property"
    ::= { cfprAdaptorExtEthIfPcEntry 18 }

cfprAdaptorExtEthIfPcEpTable OBJECT-TYPE
    SYNTAX           SEQUENCE OF CfprAdaptorExtEthIfPcEpEntry
    MAX-ACCESS       not-accessible
    STATUS           current
    DESCRIPTION
        "Cisco Firepower adaptor:ExtEthIfPcEp managed object table"
    ::= { cfprAdaptorObjects 33 }

cfprAdaptorExtEthIfPcEpEntry OBJECT-TYPE
    SYNTAX           CfprAdaptorExtEthIfPcEpEntry
    MAX-ACCESS       not-accessible
    STATUS           current
    DESCRIPTION
        "Entry for the cfprAdaptorExtEthIfPcEpTable table."
    INDEX { cfprAdaptorExtEthIfPcEpInstanceId }
    ::= { cfprAdaptorExtEthIfPcEpTable 1 }

CfprAdaptorExtEthIfPcEpEntry ::= SEQUENCE {
    cfprAdaptorExtEthIfPcEpInstanceId                                CfprManagedObjectId,
    cfprAdaptorExtEthIfPcEpDnData                                    CfprManagedObjectDn,
    cfprAdaptorExtEthIfPcEpRn                                        SnmpAdminString,
    cfprAdaptorExtEthIfPcEpAggrPortId                                Gauge32,
    cfprAdaptorExtEthIfPcEpChassisId                                 Gauge32,
    cfprAdaptorExtEthIfPcEpEpDn                                      SnmpAdminString,
    cfprAdaptorExtEthIfPcEpIfRole                                    CfprAdaptorExtIfEpIfRole,
    cfprAdaptorExtEthIfPcEpIfType                                    CfprAdaptorPIoEpIfType,
    cfprAdaptorExtEthIfPcEpLocale                                    CfprAdaptorExternalEpLocale,
    cfprAdaptorExtEthIfPcEpMembership                                CfprFabricMembershipStatus,
    cfprAdaptorExtEthIfPcEpName                                      SnmpAdminString,
    cfprAdaptorExtEthIfPcEpPeerAggrPortId                            Gauge32,
    cfprAdaptorExtEthIfPcEpPeerChassisId                             Gauge32,
    cfprAdaptorExtEthIfPcEpPeerDn                                    SnmpAdminString,
    cfprAdaptorExtEthIfPcEpPeerPortId                                Gauge32,
    cfprAdaptorExtEthIfPcEpPeerSlotId                                Gauge32,
    cfprAdaptorExtEthIfPcEpPortId                                    CfprAdaptorExtEthIfPcEpPortId,
    cfprAdaptorExtEthIfPcEpSlotId                                    CfprAdaptorExtEthIfPcEpSlotId,
    cfprAdaptorExtEthIfPcEpSwitchId                                  CfprNetworkSwitchId,
    cfprAdaptorExtEthIfPcEpTransport                                 CfprNetworkTransport,
    cfprAdaptorExtEthIfPcEpType                                      CfprAdaptorExtIfEpType
}

cfprAdaptorExtEthIfPcEpInstanceId OBJECT-TYPE
    SYNTAX       CfprManagedObjectId
    MAX-ACCESS   not-accessible
    STATUS       current
    DESCRIPTION
        "Instance identifier of the managed object."
    ::= { cfprAdaptorExtEthIfPcEpEntry 1 }

cfprAdaptorExtEthIfPcEpDnData OBJECT-TYPE
    SYNTAX       CfprManagedObjectDn
    MAX-ACCESS   read-only
    STATUS       current
    DESCRIPTION
        "Cisco Firepower adaptor:ExtEthIfPcEp:dn managed object property"
    ::= { cfprAdaptorExtEthIfPcEpEntry 2 }

cfprAdaptorExtEthIfPcEpRn OBJECT-TYPE
    SYNTAX       SnmpAdminString
    MAX-ACCESS   read-only
    STATUS       current
    DESCRIPTION
        "Cisco Firepower adaptor:ExtEthIfPcEp:rn managed object property"
    ::= { cfprAdaptorExtEthIfPcEpEntry 3 }

cfprAdaptorExtEthIfPcEpAggrPortId OBJECT-TYPE
    SYNTAX       Gauge32
    MAX-ACCESS   read-only
    STATUS       current
    DESCRIPTION
        "Cisco Firepower adaptor:ExtEthIfPcEp:aggrPortId
        managed object property"
    ::= { cfprAdaptorExtEthIfPcEpEntry 4 }

cfprAdaptorExtEthIfPcEpChassisId OBJECT-TYPE
    SYNTAX       Gauge32
    MAX-ACCESS   read-only
    STATUS       current
    DESCRIPTION
        "Cisco Firepower adaptor:ExtEthIfPcEp:chassisId
        managed object property"
    ::= { cfprAdaptorExtEthIfPcEpEntry 5 }

cfprAdaptorExtEthIfPcEpEpDn OBJECT-TYPE
    SYNTAX       SnmpAdminString
    MAX-ACCESS   read-only
    STATUS       current
    DESCRIPTION
        "Cisco Firepower adaptor:ExtEthIfPcEp:epDn managed
        object property"
    ::= { cfprAdaptorExtEthIfPcEpEntry 6 }

cfprAdaptorExtEthIfPcEpIfRole OBJECT-TYPE
    SYNTAX       CfprAdaptorExtIfEpIfRole
    MAX-ACCESS   read-only
    STATUS       current
    DESCRIPTION
        "Cisco Firepower adaptor:ExtEthIfPcEp:ifRole managed
        object property"
    ::= { cfprAdaptorExtEthIfPcEpEntry 7 }

cfprAdaptorExtEthIfPcEpIfType OBJECT-TYPE
    SYNTAX       CfprAdaptorPIoEpIfType
    MAX-ACCESS   read-only
    STATUS       current
    DESCRIPTION
        "Cisco Firepower adaptor:ExtEthIfPcEp:ifType managed
        object property"
    ::= { cfprAdaptorExtEthIfPcEpEntry 8 }

cfprAdaptorExtEthIfPcEpLocale OBJECT-TYPE
    SYNTAX       CfprAdaptorExternalEpLocale
    MAX-ACCESS   read-only
    STATUS       current
    DESCRIPTION
        "Cisco Firepower adaptor:ExtEthIfPcEp:locale managed
        object property"
    ::= { cfprAdaptorExtEthIfPcEpEntry 9 }

cfprAdaptorExtEthIfPcEpMembership OBJECT-TYPE
    SYNTAX       CfprFabricMembershipStatus
    MAX-ACCESS   read-only
    STATUS       current
    DESCRIPTION
        "Cisco Firepower adaptor:ExtEthIfPcEp:membership
        managed object property"
    ::= { cfprAdaptorExtEthIfPcEpEntry 10 }

cfprAdaptorExtEthIfPcEpName OBJECT-TYPE
    SYNTAX       SnmpAdminString
    MAX-ACCESS   read-only
    STATUS       current
    DESCRIPTION
        "Cisco Firepower adaptor:ExtEthIfPcEp:name managed
        object property"
    ::= { cfprAdaptorExtEthIfPcEpEntry 11 }

cfprAdaptorExtEthIfPcEpPeerAggrPortId OBJECT-TYPE
    SYNTAX       Gauge32
    MAX-ACCESS   read-only
    STATUS       current
    DESCRIPTION
        "Cisco Firepower adaptor:ExtEthIfPcEp:peerAggrPortId
        managed object property"
    ::= { cfprAdaptorExtEthIfPcEpEntry 12 }

cfprAdaptorExtEthIfPcEpPeerChassisId OBJECT-TYPE
    SYNTAX       Gauge32
    MAX-ACCESS   read-only
    STATUS       current
    DESCRIPTION
        "Cisco Firepower adaptor:ExtEthIfPcEp:peerChassisId
        managed object property"
    ::= { cfprAdaptorExtEthIfPcEpEntry 13 }

cfprAdaptorExtEthIfPcEpPeerDn OBJECT-TYPE
    SYNTAX       SnmpAdminString
    MAX-ACCESS   read-only
    STATUS       current
    DESCRIPTION
        "Cisco Firepower adaptor:ExtEthIfPcEp:peerDn managed
        object property"
    ::= { cfprAdaptorExtEthIfPcEpEntry 14 }

cfprAdaptorExtEthIfPcEpPeerPortId OBJECT-TYPE
    SYNTAX       Gauge32
    MAX-ACCESS   read-only
    STATUS       current
    DESCRIPTION
        "Cisco Firepower adaptor:ExtEthIfPcEp:peerPortId
        managed object property"
    ::= { cfprAdaptorExtEthIfPcEpEntry 15 }

cfprAdaptorExtEthIfPcEpPeerSlotId OBJECT-TYPE
    SYNTAX       Gauge32
    MAX-ACCESS   read-only
    STATUS       current
    DESCRIPTION
        "Cisco Firepower adaptor:ExtEthIfPcEp:peerSlotId
        managed object property"
    ::= { cfprAdaptorExtEthIfPcEpEntry 16 }

cfprAdaptorExtEthIfPcEpPortId OBJECT-TYPE
    SYNTAX       CfprAdaptorExtEthIfPcEpPortId
    MAX-ACCESS   read-only
    STATUS       current
    DESCRIPTION
        "Cisco Firepower adaptor:ExtEthIfPcEp:portId managed
        object property"
    ::= { cfprAdaptorExtEthIfPcEpEntry 17 }

cfprAdaptorExtEthIfPcEpSlotId OBJECT-TYPE
    SYNTAX       CfprAdaptorExtEthIfPcEpSlotId
    MAX-ACCESS   read-only
    STATUS       current
    DESCRIPTION
        "Cisco Firepower adaptor:ExtEthIfPcEp:slotId managed
        object property"
    ::= { cfprAdaptorExtEthIfPcEpEntry 18 }

cfprAdaptorExtEthIfPcEpSwitchId OBJECT-TYPE
    SYNTAX       CfprNetworkSwitchId
    MAX-ACCESS   read-only
    STATUS       current
    DESCRIPTION
        "Cisco Firepower adaptor:ExtEthIfPcEp:switchId
        managed object property"
    ::= { cfprAdaptorExtEthIfPcEpEntry 19 }

cfprAdaptorExtEthIfPcEpTransport OBJECT-TYPE
    SYNTAX       CfprNetworkTransport
    MAX-ACCESS   read-only
    STATUS       current
    DESCRIPTION
        "Cisco Firepower adaptor:ExtEthIfPcEp:transport
        managed object property"
    ::= { cfprAdaptorExtEthIfPcEpEntry 20 }

cfprAdaptorExtEthIfPcEpType OBJECT-TYPE
    SYNTAX       CfprAdaptorExtIfEpType
    MAX-ACCESS   read-only
    STATUS       current
    DESCRIPTION
        "Cisco Firepower adaptor:ExtEthIfPcEp:type managed
        object property"
    ::= { cfprAdaptorExtEthIfPcEpEntry 21 }

cfprAdaptorExtIpV6RssHashProfileTable OBJECT-TYPE
    SYNTAX           SEQUENCE OF CfprAdaptorExtIpV6RssHashProfileEntry
    MAX-ACCESS       not-accessible
    STATUS           current
    DESCRIPTION
        "Cisco Firepower adaptor:ExtIpV6RssHashProfile
        managed object table"
    ::= { cfprAdaptorObjects 34 }

cfprAdaptorExtIpV6RssHashProfileEntry OBJECT-TYPE
    SYNTAX           CfprAdaptorExtIpV6RssHashProfileEntry
    MAX-ACCESS       not-accessible
    STATUS           current
    DESCRIPTION
        "Entry for the cfprAdaptorExtIpV6RssHashProfileTable table."
    INDEX { cfprAdaptorExtIpV6RssHashProfileInstanceId }
    ::= { cfprAdaptorExtIpV6RssHashProfileTable 1 }

CfprAdaptorExtIpV6RssHashProfileEntry ::= SEQUENCE {
    cfprAdaptorExtIpV6RssHashProfileInstanceId                       CfprManagedObjectId,
    cfprAdaptorExtIpV6RssHashProfileDn                               CfprManagedObjectDn,
    cfprAdaptorExtIpV6RssHashProfileRn                               SnmpAdminString,
    cfprAdaptorExtIpV6RssHashProfileIpHash                           CfprAdaptorExtIpV6RssHashProfileIpHash,
    cfprAdaptorExtIpV6RssHashProfileTcpHash                          CfprAdaptorExtIpV6RssHashProfileTcpHash
}

cfprAdaptorExtIpV6RssHashProfileInstanceId OBJECT-TYPE
    SYNTAX       CfprManagedObjectId
    MAX-ACCESS   not-accessible
    STATUS       current
    DESCRIPTION
        "Instance identifier of the managed object."
    ::= { cfprAdaptorExtIpV6RssHashProfileEntry 1 }

cfprAdaptorExtIpV6RssHashProfileDn OBJECT-TYPE
    SYNTAX       CfprManagedObjectDn
    MAX-ACCESS   read-only
    STATUS       current
    DESCRIPTION
        "Cisco Firepower adaptor:ExtIpV6RssHashProfile:dn
        managed object property"
    ::= { cfprAdaptorExtIpV6RssHashProfileEntry 2 }

cfprAdaptorExtIpV6RssHashProfileRn OBJECT-TYPE
    SYNTAX       SnmpAdminString
    MAX-ACCESS   read-only
    STATUS       current
    DESCRIPTION
        "Cisco Firepower adaptor:ExtIpV6RssHashProfile:rn
        managed object property"
    ::= { cfprAdaptorExtIpV6RssHashProfileEntry 3 }

cfprAdaptorExtIpV6RssHashProfileIpHash OBJECT-TYPE
    SYNTAX       CfprAdaptorExtIpV6RssHashProfileIpHash
    MAX-ACCESS   read-only
    STATUS       current
    DESCRIPTION
        "Cisco Firepower adaptor:ExtIpV6RssHashProfile:ipHash
        managed object property"
    ::= { cfprAdaptorExtIpV6RssHashProfileEntry 4 }

cfprAdaptorExtIpV6RssHashProfileTcpHash OBJECT-TYPE
    SYNTAX       CfprAdaptorExtIpV6RssHashProfileTcpHash
    MAX-ACCESS   read-only
    STATUS       current
    DESCRIPTION
        "Cisco Firepower adaptor:ExtIpV6RssHashProfile:tcpHash
        managed object property"
    ::= { cfprAdaptorExtIpV6RssHashProfileEntry 5 }

cfprAdaptorFamilyTypeDefTable OBJECT-TYPE
    SYNTAX           SEQUENCE OF CfprAdaptorFamilyTypeDefEntry
    MAX-ACCESS       not-accessible
    STATUS           current
    DESCRIPTION
        "Cisco Firepower adaptor:FamilyTypeDef managed object table"
    ::= { cfprAdaptorObjects 35 }

cfprAdaptorFamilyTypeDefEntry OBJECT-TYPE
    SYNTAX           CfprAdaptorFamilyTypeDefEntry
    MAX-ACCESS       not-accessible
    STATUS           current
    DESCRIPTION
        "Entry for the cfprAdaptorFamilyTypeDefTable table."
    INDEX { cfprAdaptorFamilyTypeDefInstanceId }
    ::= { cfprAdaptorFamilyTypeDefTable 1 }

CfprAdaptorFamilyTypeDefEntry ::= SEQUENCE {
    cfprAdaptorFamilyTypeDefInstanceId                               CfprManagedObjectId,
    cfprAdaptorFamilyTypeDefDn                                       CfprManagedObjectDn,
    cfprAdaptorFamilyTypeDefRn                                       SnmpAdminString,
    cfprAdaptorFamilyTypeDefIsPassthrough                            TruthValue,
    cfprAdaptorFamilyTypeDefNumDcePorts                              Gauge32,
    cfprAdaptorFamilyTypeDefPortFamily                               SnmpAdminString,
    cfprAdaptorFamilyTypeDefType                                     SnmpAdminString
}

cfprAdaptorFamilyTypeDefInstanceId OBJECT-TYPE
    SYNTAX       CfprManagedObjectId
    MAX-ACCESS   not-accessible
    STATUS       current
    DESCRIPTION
        "Instance identifier of the managed object."
    ::= { cfprAdaptorFamilyTypeDefEntry 1 }

cfprAdaptorFamilyTypeDefDn OBJECT-TYPE
    SYNTAX       CfprManagedObjectDn
    MAX-ACCESS   read-only
    STATUS       current
    DESCRIPTION
        "Cisco Firepower adaptor:FamilyTypeDef:dn managed object property"
    ::= { cfprAdaptorFamilyTypeDefEntry 2 }

cfprAdaptorFamilyTypeDefRn OBJECT-TYPE
    SYNTAX       SnmpAdminString
    MAX-ACCESS   read-only
    STATUS       current
    DESCRIPTION
        "Cisco Firepower adaptor:FamilyTypeDef:rn managed object property"
    ::= { cfprAdaptorFamilyTypeDefEntry 3 }

cfprAdaptorFamilyTypeDefIsPassthrough OBJECT-TYPE
    SYNTAX       TruthValue
    MAX-ACCESS   read-only
    STATUS       current
    DESCRIPTION
        "Cisco Firepower adaptor:FamilyTypeDef:isPassthrough
        managed object property"
    ::= { cfprAdaptorFamilyTypeDefEntry 4 }

cfprAdaptorFamilyTypeDefNumDcePorts OBJECT-TYPE
    SYNTAX       Gauge32
    MAX-ACCESS   read-only
    STATUS       current
    DESCRIPTION
        "Cisco Firepower adaptor:FamilyTypeDef:numDcePorts
        managed object property"
    ::= { cfprAdaptorFamilyTypeDefEntry 5 }

cfprAdaptorFamilyTypeDefPortFamily OBJECT-TYPE
    SYNTAX       SnmpAdminString
    MAX-ACCESS   read-only
    STATUS       current
    DESCRIPTION
        "Cisco Firepower adaptor:FamilyTypeDef:portFamily
        managed object property"
    ::= { cfprAdaptorFamilyTypeDefEntry 6 }

cfprAdaptorFamilyTypeDefType OBJECT-TYPE
    SYNTAX       SnmpAdminString
    MAX-ACCESS   read-only
    STATUS       current
    DESCRIPTION
        "Cisco Firepower adaptor:FamilyTypeDef:type managed
        object property"
    ::= { cfprAdaptorFamilyTypeDefEntry 7 }

cfprAdaptorFcCdbWorkQueueProfileTable OBJECT-TYPE
    SYNTAX           SEQUENCE OF CfprAdaptorFcCdbWorkQueueProfileEntry
    MAX-ACCESS       not-accessible
    STATUS           current
    DESCRIPTION
        "Cisco Firepower adaptor:FcCdbWorkQueueProfile
        managed object table"
    ::= { cfprAdaptorObjects 36 }

cfprAdaptorFcCdbWorkQueueProfileEntry OBJECT-TYPE
    SYNTAX           CfprAdaptorFcCdbWorkQueueProfileEntry
    MAX-ACCESS       not-accessible
    STATUS           current
    DESCRIPTION
        "Entry for the cfprAdaptorFcCdbWorkQueueProfileTable table."
    INDEX { cfprAdaptorFcCdbWorkQueueProfileInstanceId }
    ::= { cfprAdaptorFcCdbWorkQueueProfileTable 1 }

CfprAdaptorFcCdbWorkQueueProfileEntry ::= SEQUENCE {
    cfprAdaptorFcCdbWorkQueueProfileInstanceId                       CfprManagedObjectId,
    cfprAdaptorFcCdbWorkQueueProfileDn                               CfprManagedObjectDn,
    cfprAdaptorFcCdbWorkQueueProfileRn                               SnmpAdminString,
    cfprAdaptorFcCdbWorkQueueProfileCount                            Gauge32,
    cfprAdaptorFcCdbWorkQueueProfileRingSize                         Gauge32
}

cfprAdaptorFcCdbWorkQueueProfileInstanceId OBJECT-TYPE
    SYNTAX       CfprManagedObjectId
    MAX-ACCESS   not-accessible
    STATUS       current
    DESCRIPTION
        "Instance identifier of the managed object."
    ::= { cfprAdaptorFcCdbWorkQueueProfileEntry 1 }

cfprAdaptorFcCdbWorkQueueProfileDn OBJECT-TYPE
    SYNTAX       CfprManagedObjectDn
    MAX-ACCESS   read-only
    STATUS       current
    DESCRIPTION
        "Cisco Firepower adaptor:FcCdbWorkQueueProfile:dn
        managed object property"
    ::= { cfprAdaptorFcCdbWorkQueueProfileEntry 2 }

cfprAdaptorFcCdbWorkQueueProfileRn OBJECT-TYPE
    SYNTAX       SnmpAdminString
    MAX-ACCESS   read-only
    STATUS       current
    DESCRIPTION
        "Cisco Firepower adaptor:FcCdbWorkQueueProfile:rn
        managed object property"
    ::= { cfprAdaptorFcCdbWorkQueueProfileEntry 3 }

cfprAdaptorFcCdbWorkQueueProfileCount OBJECT-TYPE
    SYNTAX       Gauge32
    MAX-ACCESS   read-only
    STATUS       current
    DESCRIPTION
        "Cisco Firepower adaptor:FcCdbWorkQueueProfile:count
        managed object property"
    ::= { cfprAdaptorFcCdbWorkQueueProfileEntry 4 }

cfprAdaptorFcCdbWorkQueueProfileRingSize OBJECT-TYPE
    SYNTAX       Gauge32
    MAX-ACCESS   read-only
    STATUS       current
    DESCRIPTION
        "Cisco Firepower adaptor:FcCdbWorkQueueProfile:ringSize
        managed object property"
    ::= { cfprAdaptorFcCdbWorkQueueProfileEntry 5 }

cfprAdaptorFcErrorRecoveryProfileTable OBJECT-TYPE
    SYNTAX           SEQUENCE OF CfprAdaptorFcErrorRecoveryProfileEntry
    MAX-ACCESS       not-accessible
    STATUS           current
    DESCRIPTION
        "Cisco Firepower adaptor:FcErrorRecoveryProfile
        managed object table"
    ::= { cfprAdaptorObjects 37 }

cfprAdaptorFcErrorRecoveryProfileEntry OBJECT-TYPE
    SYNTAX           CfprAdaptorFcErrorRecoveryProfileEntry
    MAX-ACCESS       not-accessible
    STATUS           current
    DESCRIPTION
        "Entry for the cfprAdaptorFcErrorRecoveryProfileTable table."
    INDEX { cfprAdaptorFcErrorRecoveryProfileInstanceId }
    ::= { cfprAdaptorFcErrorRecoveryProfileTable 1 }

CfprAdaptorFcErrorRecoveryProfileEntry ::= SEQUENCE {
    cfprAdaptorFcErrorRecoveryProfileInstanceId                      CfprManagedObjectId,
    cfprAdaptorFcErrorRecoveryProfileDn                              CfprManagedObjectDn,
    cfprAdaptorFcErrorRecoveryProfileRn                              SnmpAdminString,
    cfprAdaptorFcErrorRecoveryProfileErrorDetectTimeout              Gauge32,
    cfprAdaptorFcErrorRecoveryProfileFcpErrorRecovery                CfprAdaptorFcErrorRecoveryProfileFcpErrorRecovery,
    cfprAdaptorFcErrorRecoveryProfileLinkDownTimeout                 Gauge32,
    cfprAdaptorFcErrorRecoveryProfilePortDownIoRetryCount            Gauge32,
    cfprAdaptorFcErrorRecoveryProfilePortDownTimeout                 Gauge32,
    cfprAdaptorFcErrorRecoveryProfileResourceAllocationTimeout       Gauge32
}

cfprAdaptorFcErrorRecoveryProfileInstanceId OBJECT-TYPE
    SYNTAX       CfprManagedObjectId
    MAX-ACCESS   not-accessible
    STATUS       current
    DESCRIPTION
        "Instance identifier of the managed object."
    ::= { cfprAdaptorFcErrorRecoveryProfileEntry 1 }

cfprAdaptorFcErrorRecoveryProfileDn OBJECT-TYPE
    SYNTAX       CfprManagedObjectDn
    MAX-ACCESS   read-only
    STATUS       current
    DESCRIPTION
        "Cisco Firepower adaptor:FcErrorRecoveryProfile:dn
        managed object property"
    ::= { cfprAdaptorFcErrorRecoveryProfileEntry 2 }

cfprAdaptorFcErrorRecoveryProfileRn OBJECT-TYPE
    SYNTAX       SnmpAdminString
    MAX-ACCESS   read-only
    STATUS       current
    DESCRIPTION
        "Cisco Firepower adaptor:FcErrorRecoveryProfile:rn
        managed object property"
    ::= { cfprAdaptorFcErrorRecoveryProfileEntry 3 }

cfprAdaptorFcErrorRecoveryProfileErrorDetectTimeout OBJECT-TYPE
    SYNTAX       Gauge32
    MAX-ACCESS   read-only
    STATUS       current
    DESCRIPTION
        "Cisco Firepower adaptor:FcErrorRecoveryProfile:errorDetectTimeout
         managed object property"
    ::= { cfprAdaptorFcErrorRecoveryProfileEntry 4 }

cfprAdaptorFcErrorRecoveryProfileFcpErrorRecovery OBJECT-TYPE
    SYNTAX       CfprAdaptorFcErrorRecoveryProfileFcpErrorRecovery
    MAX-ACCESS   read-only
    STATUS       current
    DESCRIPTION
        "Cisco Firepower adaptor:FcErrorRecoveryProfile:fcpErrorRecovery
        managed object property"
    ::= { cfprAdaptorFcErrorRecoveryProfileEntry 5 }

cfprAdaptorFcErrorRecoveryProfileLinkDownTimeout OBJECT-TYPE
    SYNTAX       Gauge32
    MAX-ACCESS   read-only
    STATUS       current
    DESCRIPTION
        "Cisco Firepower adaptor:FcErrorRecoveryProfile:linkDownTimeout
        managed object property"
    ::= { cfprAdaptorFcErrorRecoveryProfileEntry 6 }

cfprAdaptorFcErrorRecoveryProfilePortDownIoRetryCount OBJECT-TYPE
    SYNTAX       Gauge32
    MAX-ACCESS   read-only
    STATUS       current
    DESCRIPTION
        "Cisco Firepower adaptor:FcErrorRecoveryProfile:portDownIoRetryCou
        nt managed object property"
    ::= { cfprAdaptorFcErrorRecoveryProfileEntry 7 }

cfprAdaptorFcErrorRecoveryProfilePortDownTimeout OBJECT-TYPE
    SYNTAX       Gauge32
    MAX-ACCESS   read-only
    STATUS       current
    DESCRIPTION
        "Cisco Firepower adaptor:FcErrorRecoveryProfile:portDownTimeout
        managed object property"
    ::= { cfprAdaptorFcErrorRecoveryProfileEntry 8 }

cfprAdaptorFcErrorRecoveryProfileResourceAllocationTimeout OBJECT-TYPE
    SYNTAX       Gauge32
    MAX-ACCESS   read-only
    STATUS       current
    DESCRIPTION
        "Cisco Firepower adaptor:FcErrorRecoveryProfile:resourceAllocation
        Timeout managed object property"
    ::= { cfprAdaptorFcErrorRecoveryProfileEntry 9 }

cfprAdaptorFcIfEventStatsTable OBJECT-TYPE
    SYNTAX           SEQUENCE OF CfprAdaptorFcIfEventStatsEntry
    MAX-ACCESS       not-accessible
    STATUS           current
    DESCRIPTION
        "Cisco Firepower adaptor:FcIfEventStats managed object table"
    ::= { cfprAdaptorObjects 38 }

cfprAdaptorFcIfEventStatsEntry OBJECT-TYPE
    SYNTAX           CfprAdaptorFcIfEventStatsEntry
    MAX-ACCESS       not-accessible
    STATUS           current
    DESCRIPTION
        "Entry for the cfprAdaptorFcIfEventStatsTable table."
    INDEX { cfprAdaptorFcIfEventStatsInstanceId }
    ::= { cfprAdaptorFcIfEventStatsTable 1 }

CfprAdaptorFcIfEventStatsEntry ::= SEQUENCE {
    cfprAdaptorFcIfEventStatsInstanceId                              CfprManagedObjectId,
    cfprAdaptorFcIfEventStatsDn                                      CfprManagedObjectDn,
    cfprAdaptorFcIfEventStatsRn                                      SnmpAdminString,
    cfprAdaptorFcIfEventStatsIntervals                               Gauge32,
    cfprAdaptorFcIfEventStatsInvalidCRCCount                         Unsigned64,
    cfprAdaptorFcIfEventStatsInvalidCRCCountDelta                    Counter64,
    cfprAdaptorFcIfEventStatsInvalidCRCCountDeltaAvg                 Unsigned64,
    cfprAdaptorFcIfEventStatsInvalidCRCCountDeltaMax                 Unsigned64,
    cfprAdaptorFcIfEventStatsInvalidCRCCountDeltaMin                 Unsigned64,
    cfprAdaptorFcIfEventStatsLinkFailureCount                        Unsigned64,
    cfprAdaptorFcIfEventStatsLinkFailureCountDelta                   Counter64,
    cfprAdaptorFcIfEventStatsLinkFailureCountDeltaAvg                Unsigned64,
    cfprAdaptorFcIfEventStatsLinkFailureCountDeltaMax                Unsigned64,
    cfprAdaptorFcIfEventStatsLinkFailureCountDeltaMin                Unsigned64,
    cfprAdaptorFcIfEventStatsLipCount                                Unsigned64,
    cfprAdaptorFcIfEventStatsLipCountDelta                           Counter64,
    cfprAdaptorFcIfEventStatsLipCountDeltaAvg                        Unsigned64,
    cfprAdaptorFcIfEventStatsLipCountDeltaMax                        Unsigned64,
    cfprAdaptorFcIfEventStatsLipCountDeltaMin                        Unsigned64,
    cfprAdaptorFcIfEventStatsLossOfSignalCount                       Unsigned64,
    cfprAdaptorFcIfEventStatsLossOfSignalCountDelta                  Counter64,
    cfprAdaptorFcIfEventStatsLossOfSignalCountDeltaAvg               Unsigned64,
    cfprAdaptorFcIfEventStatsLossOfSignalCountDeltaMax               Unsigned64,
    cfprAdaptorFcIfEventStatsLossOfSignalCountDeltaMin               Unsigned64,
    cfprAdaptorFcIfEventStatsLossOfSyncCount                         Unsigned64,
    cfprAdaptorFcIfEventStatsLossOfSyncCountDelta                    Counter64,
    cfprAdaptorFcIfEventStatsLossOfSyncCountDeltaAvg                 Unsigned64,
    cfprAdaptorFcIfEventStatsLossOfSyncCountDeltaMax                 Unsigned64,
    cfprAdaptorFcIfEventStatsLossOfSyncCountDeltaMin                 Unsigned64,
    cfprAdaptorFcIfEventStatsNOSCount                                Unsigned64,
    cfprAdaptorFcIfEventStatsNOSCountDelta                           Counter64,
    cfprAdaptorFcIfEventStatsNOSCountDeltaAvg                        Unsigned64,
    cfprAdaptorFcIfEventStatsNOSCountDeltaMax                        Unsigned64,
    cfprAdaptorFcIfEventStatsNOSCountDeltaMin                        Unsigned64,
    cfprAdaptorFcIfEventStatsSecondsSinceLastReset                   Unsigned64,
    cfprAdaptorFcIfEventStatsSecondsSinceLastResetDelta              Counter64,
    cfprAdaptorFcIfEventStatsSecondsSinceLastResetDeltaAvg           Unsigned64,
    cfprAdaptorFcIfEventStatsSecondsSinceLastResetDeltaMax           Unsigned64,
    cfprAdaptorFcIfEventStatsSecondsSinceLastResetDeltaMin           Unsigned64,
    cfprAdaptorFcIfEventStatsSeqProtocolErrCount                     Unsigned64,
    cfprAdaptorFcIfEventStatsSeqProtocolErrCountDelta                Counter64,
    cfprAdaptorFcIfEventStatsSeqProtocolErrCountDeltaAvg             Unsigned64,
    cfprAdaptorFcIfEventStatsSeqProtocolErrCountDeltaMax             Unsigned64,
    cfprAdaptorFcIfEventStatsSeqProtocolErrCountDeltaMin             Unsigned64,
    cfprAdaptorFcIfEventStatsSuspect                                 TruthValue,
    cfprAdaptorFcIfEventStatsThresholded                             CfprAdaptorFcIfEventStatsThresholded,
    cfprAdaptorFcIfEventStatsTimeCollected                           DateAndTime,
    cfprAdaptorFcIfEventStatsUpdate                                  Gauge32
}

cfprAdaptorFcIfEventStatsInstanceId OBJECT-TYPE
    SYNTAX       CfprManagedObjectId
    MAX-ACCESS   not-accessible
    STATUS       current
    DESCRIPTION
        "Instance identifier of the managed object."
    ::= { cfprAdaptorFcIfEventStatsEntry 1 }

cfprAdaptorFcIfEventStatsDn OBJECT-TYPE
    SYNTAX       CfprManagedObjectDn
    MAX-ACCESS   read-only
    STATUS       current
    DESCRIPTION
        "Cisco Firepower adaptor:FcIfEventStats:dn managed
        object property"
    ::= { cfprAdaptorFcIfEventStatsEntry 2 }

cfprAdaptorFcIfEventStatsRn OBJECT-TYPE
    SYNTAX       SnmpAdminString
    MAX-ACCESS   read-only
    STATUS       current
    DESCRIPTION
        "Cisco Firepower adaptor:FcIfEventStats:rn managed
        object property"
    ::= { cfprAdaptorFcIfEventStatsEntry 3 }

cfprAdaptorFcIfEventStatsIntervals OBJECT-TYPE
    SYNTAX       Gauge32
    MAX-ACCESS   read-only
    STATUS       current
    DESCRIPTION
        "Cisco Firepower adaptor:FcIfEventStats:intervals
        managed object property"
    ::= { cfprAdaptorFcIfEventStatsEntry 4 }

cfprAdaptorFcIfEventStatsInvalidCRCCount OBJECT-TYPE
    SYNTAX       Unsigned64
    MAX-ACCESS   read-only
    STATUS       current
    DESCRIPTION
        "Cisco Firepower adaptor:FcIfEventStats:invalidCRCCount
        managed object property"
    ::= { cfprAdaptorFcIfEventStatsEntry 5 }

cfprAdaptorFcIfEventStatsInvalidCRCCountDelta OBJECT-TYPE
    SYNTAX       Counter64
    MAX-ACCESS   read-only
    STATUS       current
    DESCRIPTION
        "Cisco Firepower adaptor:FcIfEventStats:invalidCRCCountDelta
        managed object property"
    ::= { cfprAdaptorFcIfEventStatsEntry 6 }

cfprAdaptorFcIfEventStatsInvalidCRCCountDeltaAvg OBJECT-TYPE
    SYNTAX       Unsigned64
    MAX-ACCESS   read-only
    STATUS       current
    DESCRIPTION
        "Cisco Firepower adaptor:FcIfEventStats:invalidCRCCountDeltaAvg
        managed object property"
    ::= { cfprAdaptorFcIfEventStatsEntry 7 }

cfprAdaptorFcIfEventStatsInvalidCRCCountDeltaMax OBJECT-TYPE
    SYNTAX       Unsigned64
    MAX-ACCESS   read-only
    STATUS       current
    DESCRIPTION
        "Cisco Firepower adaptor:FcIfEventStats:invalidCRCCountDeltaMax
        managed object property"
    ::= { cfprAdaptorFcIfEventStatsEntry 8 }

cfprAdaptorFcIfEventStatsInvalidCRCCountDeltaMin OBJECT-TYPE
    SYNTAX       Unsigned64
    MAX-ACCESS   read-only
    STATUS       current
    DESCRIPTION
        "Cisco Firepower adaptor:FcIfEventStats:invalidCRCCountDeltaMin
        managed object property"
    ::= { cfprAdaptorFcIfEventStatsEntry 9 }

cfprAdaptorFcIfEventStatsLinkFailureCount OBJECT-TYPE
    SYNTAX       Unsigned64
    MAX-ACCESS   read-only
    STATUS       current
    DESCRIPTION
        "Cisco Firepower adaptor:FcIfEventStats:linkFailureCount
        managed object property"
    ::= { cfprAdaptorFcIfEventStatsEntry 10 }

cfprAdaptorFcIfEventStatsLinkFailureCountDelta OBJECT-TYPE
    SYNTAX       Counter64
    MAX-ACCESS   read-only
    STATUS       current
    DESCRIPTION
        "Cisco Firepower adaptor:FcIfEventStats:linkFailureCountDelta
        managed object property"
    ::= { cfprAdaptorFcIfEventStatsEntry 11 }

cfprAdaptorFcIfEventStatsLinkFailureCountDeltaAvg OBJECT-TYPE
    SYNTAX       Unsigned64
    MAX-ACCESS   read-only
    STATUS       current
    DESCRIPTION
        "Cisco Firepower adaptor:FcIfEventStats:linkFailureCountDeltaAvg
        managed object property"
    ::= { cfprAdaptorFcIfEventStatsEntry 12 }

cfprAdaptorFcIfEventStatsLinkFailureCountDeltaMax OBJECT-TYPE
    SYNTAX       Unsigned64
    MAX-ACCESS   read-only
    STATUS       current
    DESCRIPTION
        "Cisco Firepower adaptor:FcIfEventStats:linkFailureCountDeltaMax
        managed object property"
    ::= { cfprAdaptorFcIfEventStatsEntry 13 }

cfprAdaptorFcIfEventStatsLinkFailureCountDeltaMin OBJECT-TYPE
    SYNTAX       Unsigned64
    MAX-ACCESS   read-only
    STATUS       current
    DESCRIPTION
        "Cisco Firepower adaptor:FcIfEventStats:linkFailureCountDeltaMin
        managed object property"
    ::= { cfprAdaptorFcIfEventStatsEntry 14 }

cfprAdaptorFcIfEventStatsLipCount OBJECT-TYPE
    SYNTAX       Unsigned64
    MAX-ACCESS   read-only
    STATUS       current
    DESCRIPTION
        "Cisco Firepower adaptor:FcIfEventStats:lipCount
        managed object property"
    ::= { cfprAdaptorFcIfEventStatsEntry 15 }

cfprAdaptorFcIfEventStatsLipCountDelta OBJECT-TYPE
    SYNTAX       Counter64
    MAX-ACCESS   read-only
    STATUS       current
    DESCRIPTION
        "Cisco Firepower adaptor:FcIfEventStats:lipCountDelta
        managed object property"
    ::= { cfprAdaptorFcIfEventStatsEntry 16 }

cfprAdaptorFcIfEventStatsLipCountDeltaAvg OBJECT-TYPE
    SYNTAX       Unsigned64
    MAX-ACCESS   read-only
    STATUS       current
    DESCRIPTION
        "Cisco Firepower adaptor:FcIfEventStats:lipCountDeltaAvg
        managed object property"
    ::= { cfprAdaptorFcIfEventStatsEntry 17 }

cfprAdaptorFcIfEventStatsLipCountDeltaMax OBJECT-TYPE
    SYNTAX       Unsigned64
    MAX-ACCESS   read-only
    STATUS       current
    DESCRIPTION
        "Cisco Firepower adaptor:FcIfEventStats:lipCountDeltaMax
        managed object property"
    ::= { cfprAdaptorFcIfEventStatsEntry 18 }

cfprAdaptorFcIfEventStatsLipCountDeltaMin OBJECT-TYPE
    SYNTAX       Unsigned64
    MAX-ACCESS   read-only
    STATUS       current
    DESCRIPTION
        "Cisco Firepower adaptor:FcIfEventStats:lipCountDeltaMin
        managed object property"
    ::= { cfprAdaptorFcIfEventStatsEntry 19 }

cfprAdaptorFcIfEventStatsLossOfSignalCount OBJECT-TYPE
    SYNTAX       Unsigned64
    MAX-ACCESS   read-only
    STATUS       current
    DESCRIPTION
        "Cisco Firepower adaptor:FcIfEventStats:lossOfSignalCount
        managed object property"
    ::= { cfprAdaptorFcIfEventStatsEntry 20 }

cfprAdaptorFcIfEventStatsLossOfSignalCountDelta OBJECT-TYPE
    SYNTAX       Counter64
    MAX-ACCESS   read-only
    STATUS       current
    DESCRIPTION
        "Cisco Firepower adaptor:FcIfEventStats:lossOfSignalCountDelta
        managed object property"
    ::= { cfprAdaptorFcIfEventStatsEntry 21 }

cfprAdaptorFcIfEventStatsLossOfSignalCountDeltaAvg OBJECT-TYPE
    SYNTAX       Unsigned64
    MAX-ACCESS   read-only
    STATUS       current
    DESCRIPTION
        "Cisco Firepower adaptor:FcIfEventStats:lossOfSignalCountDeltaAvg
        managed object property"
    ::= { cfprAdaptorFcIfEventStatsEntry 22 }

cfprAdaptorFcIfEventStatsLossOfSignalCountDeltaMax OBJECT-TYPE
    SYNTAX       Unsigned64
    MAX-ACCESS   read-only
    STATUS       current
    DESCRIPTION
        "Cisco Firepower adaptor:FcIfEventStats:lossOfSignalCountDeltaMax
        managed object property"
    ::= { cfprAdaptorFcIfEventStatsEntry 23 }

cfprAdaptorFcIfEventStatsLossOfSignalCountDeltaMin OBJECT-TYPE
    SYNTAX       Unsigned64
    MAX-ACCESS   read-only
    STATUS       current
    DESCRIPTION
        "Cisco Firepower adaptor:FcIfEventStats:lossOfSignalCountDeltaMin
        managed object property"
    ::= { cfprAdaptorFcIfEventStatsEntry 24 }

cfprAdaptorFcIfEventStatsLossOfSyncCount OBJECT-TYPE
    SYNTAX       Unsigned64
    MAX-ACCESS   read-only
    STATUS       current
    DESCRIPTION
        "Cisco Firepower adaptor:FcIfEventStats:lossOfSyncCount
        managed object property"
    ::= { cfprAdaptorFcIfEventStatsEntry 25 }

cfprAdaptorFcIfEventStatsLossOfSyncCountDelta OBJECT-TYPE
    SYNTAX       Counter64
    MAX-ACCESS   read-only
    STATUS       current
    DESCRIPTION
        "Cisco Firepower adaptor:FcIfEventStats:lossOfSyncCountDelta
        managed object property"
    ::= { cfprAdaptorFcIfEventStatsEntry 26 }

cfprAdaptorFcIfEventStatsLossOfSyncCountDeltaAvg OBJECT-TYPE
    SYNTAX       Unsigned64
    MAX-ACCESS   read-only
    STATUS       current
    DESCRIPTION
        "Cisco Firepower adaptor:FcIfEventStats:lossOfSyncCountDeltaAvg
        managed object property"
    ::= { cfprAdaptorFcIfEventStatsEntry 27 }

cfprAdaptorFcIfEventStatsLossOfSyncCountDeltaMax OBJECT-TYPE
    SYNTAX       Unsigned64
    MAX-ACCESS   read-only
    STATUS       current
    DESCRIPTION
        "Cisco Firepower adaptor:FcIfEventStats:lossOfSyncCountDeltaMax
        managed object property"
    ::= { cfprAdaptorFcIfEventStatsEntry 28 }

cfprAdaptorFcIfEventStatsLossOfSyncCountDeltaMin OBJECT-TYPE
    SYNTAX       Unsigned64
    MAX-ACCESS   read-only
    STATUS       current
    DESCRIPTION
        "Cisco Firepower adaptor:FcIfEventStats:lossOfSyncCountDeltaMin
        managed object property"
    ::= { cfprAdaptorFcIfEventStatsEntry 29 }

cfprAdaptorFcIfEventStatsNOSCount OBJECT-TYPE
    SYNTAX       Unsigned64
    MAX-ACCESS   read-only
    STATUS       current
    DESCRIPTION
        "Cisco Firepower adaptor:FcIfEventStats:nOSCount
        managed object property"
    ::= { cfprAdaptorFcIfEventStatsEntry 30 }

cfprAdaptorFcIfEventStatsNOSCountDelta OBJECT-TYPE
    SYNTAX       Counter64
    MAX-ACCESS   read-only
    STATUS       current
    DESCRIPTION
        "Cisco Firepower adaptor:FcIfEventStats:nOSCountDelta
        managed object property"
    ::= { cfprAdaptorFcIfEventStatsEntry 31 }

cfprAdaptorFcIfEventStatsNOSCountDeltaAvg OBJECT-TYPE
    SYNTAX       Unsigned64
    MAX-ACCESS   read-only
    STATUS       current
    DESCRIPTION
        "Cisco Firepower adaptor:FcIfEventStats:nOSCountDeltaAvg
        managed object property"
    ::= { cfprAdaptorFcIfEventStatsEntry 32 }

cfprAdaptorFcIfEventStatsNOSCountDeltaMax OBJECT-TYPE
    SYNTAX       Unsigned64
    MAX-ACCESS   read-only
    STATUS       current
    DESCRIPTION
        "Cisco Firepower adaptor:FcIfEventStats:nOSCountDeltaMax
        managed object property"
    ::= { cfprAdaptorFcIfEventStatsEntry 33 }

cfprAdaptorFcIfEventStatsNOSCountDeltaMin OBJECT-TYPE
    SYNTAX       Unsigned64
    MAX-ACCESS   read-only
    STATUS       current
    DESCRIPTION
        "Cisco Firepower adaptor:FcIfEventStats:nOSCountDeltaMin
        managed object property"
    ::= { cfprAdaptorFcIfEventStatsEntry 34 }

cfprAdaptorFcIfEventStatsSecondsSinceLastReset OBJECT-TYPE
    SYNTAX       Unsigned64
    MAX-ACCESS   read-only
    STATUS       current
    DESCRIPTION
        "Cisco Firepower adaptor:FcIfEventStats:secondsSinceLastReset
        managed object property"
    ::= { cfprAdaptorFcIfEventStatsEntry 35 }

cfprAdaptorFcIfEventStatsSecondsSinceLastResetDelta OBJECT-TYPE
    SYNTAX       Counter64
    MAX-ACCESS   read-only
    STATUS       current
    DESCRIPTION
        "Cisco Firepower adaptor:FcIfEventStats:secondsSinceLastResetDelta
         managed object property"
    ::= { cfprAdaptorFcIfEventStatsEntry 36 }

cfprAdaptorFcIfEventStatsSecondsSinceLastResetDeltaAvg OBJECT-TYPE
    SYNTAX       Unsigned64
    MAX-ACCESS   read-only
    STATUS       current
    DESCRIPTION
        "Cisco Firepower adaptor:FcIfEventStats:secondsSinceLastResetDelta
        Avg managed object property"
    ::= { cfprAdaptorFcIfEventStatsEntry 37 }

cfprAdaptorFcIfEventStatsSecondsSinceLastResetDeltaMax OBJECT-TYPE
    SYNTAX       Unsigned64
    MAX-ACCESS   read-only
    STATUS       current
    DESCRIPTION
        "Cisco Firepower adaptor:FcIfEventStats:secondsSinceLastResetDelta
        Max managed object property"
    ::= { cfprAdaptorFcIfEventStatsEntry 38 }

cfprAdaptorFcIfEventStatsSecondsSinceLastResetDeltaMin OBJECT-TYPE
    SYNTAX       Unsigned64
    MAX-ACCESS   read-only
    STATUS       current
    DESCRIPTION
        "Cisco Firepower adaptor:FcIfEventStats:secondsSinceLastResetDelta
        Min managed object property"
    ::= { cfprAdaptorFcIfEventStatsEntry 39 }

cfprAdaptorFcIfEventStatsSeqProtocolErrCount OBJECT-TYPE
    SYNTAX       Unsigned64
    MAX-ACCESS   read-only
    STATUS       current
    DESCRIPTION
        "Cisco Firepower adaptor:FcIfEventStats:seqProtocolErrCount
        managed object property"
    ::= { cfprAdaptorFcIfEventStatsEntry 40 }

cfprAdaptorFcIfEventStatsSeqProtocolErrCountDelta OBJECT-TYPE
    SYNTAX       Counter64
    MAX-ACCESS   read-only
    STATUS       current
    DESCRIPTION
        "Cisco Firepower adaptor:FcIfEventStats:seqProtocolErrCountDelta
        managed object property"
    ::= { cfprAdaptorFcIfEventStatsEntry 41 }

cfprAdaptorFcIfEventStatsSeqProtocolErrCountDeltaAvg OBJECT-TYPE
    SYNTAX       Unsigned64
    MAX-ACCESS   read-only
    STATUS       current
    DESCRIPTION
        "Cisco Firepower adaptor:FcIfEventStats:seqProtocolErrCountDeltaAv
        g managed object property"
    ::= { cfprAdaptorFcIfEventStatsEntry 42 }

cfprAdaptorFcIfEventStatsSeqProtocolErrCountDeltaMax OBJECT-TYPE
    SYNTAX       Unsigned64
    MAX-ACCESS   read-only
    STATUS       current
    DESCRIPTION
        "Cisco Firepower adaptor:FcIfEventStats:seqProtocolErrCountDeltaMa
        x managed object property"
    ::= { cfprAdaptorFcIfEventStatsEntry 43 }

cfprAdaptorFcIfEventStatsSeqProtocolErrCountDeltaMin OBJECT-TYPE
    SYNTAX       Unsigned64
    MAX-ACCESS   read-only
    STATUS       current
    DESCRIPTION
        "Cisco Firepower adaptor:FcIfEventStats:seqProtocolErrCountDeltaMi
        n managed object property"
    ::= { cfprAdaptorFcIfEventStatsEntry 44 }

cfprAdaptorFcIfEventStatsSuspect OBJECT-TYPE
    SYNTAX       TruthValue
    MAX-ACCESS   read-only
    STATUS       current
    DESCRIPTION
        "Cisco Firepower adaptor:FcIfEventStats:suspect
        managed object property"
    ::= { cfprAdaptorFcIfEventStatsEntry 45 }

cfprAdaptorFcIfEventStatsThresholded OBJECT-TYPE
    SYNTAX       CfprAdaptorFcIfEventStatsThresholded
    MAX-ACCESS   read-only
    STATUS       current
    DESCRIPTION
        "Cisco Firepower adaptor:FcIfEventStats:thresholded
        managed object property"
    ::= { cfprAdaptorFcIfEventStatsEntry 46 }

cfprAdaptorFcIfEventStatsTimeCollected OBJECT-TYPE
    SYNTAX       DateAndTime
    MAX-ACCESS   read-only
    STATUS       current
    DESCRIPTION
        "Cisco Firepower adaptor:FcIfEventStats:timeCollected
        managed object property"
    ::= { cfprAdaptorFcIfEventStatsEntry 47 }

cfprAdaptorFcIfEventStatsUpdate OBJECT-TYPE
    SYNTAX       Gauge32
    MAX-ACCESS   read-only
    STATUS       current
    DESCRIPTION
        "Cisco Firepower adaptor:FcIfEventStats:update
        managed object property"
    ::= { cfprAdaptorFcIfEventStatsEntry 48 }

cfprAdaptorFcIfEventStatsHistTable OBJECT-TYPE
    SYNTAX           SEQUENCE OF CfprAdaptorFcIfEventStatsHistEntry
    MAX-ACCESS       not-accessible
    STATUS           current
    DESCRIPTION
        "Cisco Firepower adaptor:FcIfEventStatsHist managed object table"
    ::= { cfprAdaptorObjects 39 }

cfprAdaptorFcIfEventStatsHistEntry OBJECT-TYPE
    SYNTAX           CfprAdaptorFcIfEventStatsHistEntry
    MAX-ACCESS       not-accessible
    STATUS           current
    DESCRIPTION
        "Entry for the cfprAdaptorFcIfEventStatsHistTable table."
    INDEX { cfprAdaptorFcIfEventStatsHistInstanceId }
    ::= { cfprAdaptorFcIfEventStatsHistTable 1 }

CfprAdaptorFcIfEventStatsHistEntry ::= SEQUENCE {
    cfprAdaptorFcIfEventStatsHistInstanceId                          CfprManagedObjectId,
    cfprAdaptorFcIfEventStatsHistDn                                  CfprManagedObjectDn,
    cfprAdaptorFcIfEventStatsHistRn                                  SnmpAdminString,
    cfprAdaptorFcIfEventStatsHistId                                  Unsigned64,
    cfprAdaptorFcIfEventStatsHistInvalidCRCCount                     Unsigned64,
    cfprAdaptorFcIfEventStatsHistInvalidCRCCountDelta                Unsigned64,
    cfprAdaptorFcIfEventStatsHistInvalidCRCCountDeltaAvg             Unsigned64,
    cfprAdaptorFcIfEventStatsHistInvalidCRCCountDeltaMax             Unsigned64,
    cfprAdaptorFcIfEventStatsHistInvalidCRCCountDeltaMin             Unsigned64,
    cfprAdaptorFcIfEventStatsHistLinkFailureCount                    Unsigned64,
    cfprAdaptorFcIfEventStatsHistLinkFailureCountDelta               Unsigned64,
    cfprAdaptorFcIfEventStatsHistLinkFailureCountDeltaAvg            Unsigned64,
    cfprAdaptorFcIfEventStatsHistLinkFailureCountDeltaMax            Unsigned64,
    cfprAdaptorFcIfEventStatsHistLinkFailureCountDeltaMin            Unsigned64,
    cfprAdaptorFcIfEventStatsHistLipCount                            Unsigned64,
    cfprAdaptorFcIfEventStatsHistLipCountDelta                       Unsigned64,
    cfprAdaptorFcIfEventStatsHistLipCountDeltaAvg                    Unsigned64,
    cfprAdaptorFcIfEventStatsHistLipCountDeltaMax                    Unsigned64,
    cfprAdaptorFcIfEventStatsHistLipCountDeltaMin                    Unsigned64,
    cfprAdaptorFcIfEventStatsHistLossOfSignalCount                   Unsigned64,
    cfprAdaptorFcIfEventStatsHistLossOfSignalCountDelta              Unsigned64,
    cfprAdaptorFcIfEventStatsHistLossOfSignalCountDeltaAvg           Unsigned64,
    cfprAdaptorFcIfEventStatsHistLossOfSignalCountDeltaMax           Unsigned64,
    cfprAdaptorFcIfEventStatsHistLossOfSignalCountDeltaMin           Unsigned64,
    cfprAdaptorFcIfEventStatsHistLossOfSyncCount                     Unsigned64,
    cfprAdaptorFcIfEventStatsHistLossOfSyncCountDelta                Unsigned64,
    cfprAdaptorFcIfEventStatsHistLossOfSyncCountDeltaAvg             Unsigned64,
    cfprAdaptorFcIfEventStatsHistLossOfSyncCountDeltaMax             Unsigned64,
    cfprAdaptorFcIfEventStatsHistLossOfSyncCountDeltaMin             Unsigned64,
    cfprAdaptorFcIfEventStatsHistMostRecent                          TruthValue,
    cfprAdaptorFcIfEventStatsHistNOSCount                            Unsigned64,
    cfprAdaptorFcIfEventStatsHistNOSCountDelta                       Unsigned64,
    cfprAdaptorFcIfEventStatsHistNOSCountDeltaAvg                    Unsigned64,
    cfprAdaptorFcIfEventStatsHistNOSCountDeltaMax                    Unsigned64,
    cfprAdaptorFcIfEventStatsHistNOSCountDeltaMin                    Unsigned64,
    cfprAdaptorFcIfEventStatsHistSecondsSinceLastReset               Unsigned64,
    cfprAdaptorFcIfEventStatsHistSecondsSinceLastResetDelta          Unsigned64,
    cfprAdaptorFcIfEventStatsHistSecondsSinceLastResetDeltaAvg       Unsigned64,
    cfprAdaptorFcIfEventStatsHistSecondsSinceLastResetDeltaMax       Unsigned64,
    cfprAdaptorFcIfEventStatsHistSecondsSinceLastResetDeltaMin       Unsigned64,
    cfprAdaptorFcIfEventStatsHistSeqProtocolErrCount                 Unsigned64,
    cfprAdaptorFcIfEventStatsHistSeqProtocolErrCountDelta            Unsigned64,
    cfprAdaptorFcIfEventStatsHistSeqProtocolErrCountDeltaAvg         Unsigned64,
    cfprAdaptorFcIfEventStatsHistSeqProtocolErrCountDeltaMax         Unsigned64,
    cfprAdaptorFcIfEventStatsHistSeqProtocolErrCountDeltaMin         Unsigned64,
    cfprAdaptorFcIfEventStatsHistSuspect                             TruthValue,
    cfprAdaptorFcIfEventStatsHistThresholded                         CfprAdaptorFcIfEventStatsHistThresholded,
    cfprAdaptorFcIfEventStatsHistTimeCollected                       DateAndTime
}

cfprAdaptorFcIfEventStatsHistInstanceId OBJECT-TYPE
    SYNTAX       CfprManagedObjectId
    MAX-ACCESS   not-accessible
    STATUS       current
    DESCRIPTION
        "Instance identifier of the managed object."
    ::= { cfprAdaptorFcIfEventStatsHistEntry 1 }

cfprAdaptorFcIfEventStatsHistDn OBJECT-TYPE
    SYNTAX       CfprManagedObjectDn
    MAX-ACCESS   read-only
    STATUS       current
    DESCRIPTION
        "Cisco Firepower adaptor:FcIfEventStatsHist:dn
        managed object property"
    ::= { cfprAdaptorFcIfEventStatsHistEntry 2 }

cfprAdaptorFcIfEventStatsHistRn OBJECT-TYPE
    SYNTAX       SnmpAdminString
    MAX-ACCESS   read-only
    STATUS       current
    DESCRIPTION
        "Cisco Firepower adaptor:FcIfEventStatsHist:rn
        managed object property"
    ::= { cfprAdaptorFcIfEventStatsHistEntry 3 }

cfprAdaptorFcIfEventStatsHistId OBJECT-TYPE
    SYNTAX       Unsigned64
    MAX-ACCESS   read-only
    STATUS       current
    DESCRIPTION
        "Cisco Firepower adaptor:FcIfEventStatsHist:id
        managed object property"
    ::= { cfprAdaptorFcIfEventStatsHistEntry 4 }

cfprAdaptorFcIfEventStatsHistInvalidCRCCount OBJECT-TYPE
    SYNTAX       Unsigned64
    MAX-ACCESS   read-only
    STATUS       current
    DESCRIPTION
        "Cisco Firepower adaptor:FcIfEventStatsHist:invalidCRCCount
        managed object property"
    ::= { cfprAdaptorFcIfEventStatsHistEntry 5 }

cfprAdaptorFcIfEventStatsHistInvalidCRCCountDelta OBJECT-TYPE
    SYNTAX       Unsigned64
    MAX-ACCESS   read-only
    STATUS       current
    DESCRIPTION
        "Cisco Firepower adaptor:FcIfEventStatsHist:invalidCRCCountDelta
        managed object property"
    ::= { cfprAdaptorFcIfEventStatsHistEntry 6 }

cfprAdaptorFcIfEventStatsHistInvalidCRCCountDeltaAvg OBJECT-TYPE
    SYNTAX       Unsigned64
    MAX-ACCESS   read-only
    STATUS       current
    DESCRIPTION
        "Cisco Firepower adaptor:FcIfEventStatsHist:invalidCRCCountDeltaAv
        g managed object property"
    ::= { cfprAdaptorFcIfEventStatsHistEntry 7 }

cfprAdaptorFcIfEventStatsHistInvalidCRCCountDeltaMax OBJECT-TYPE
    SYNTAX       Unsigned64
    MAX-ACCESS   read-only
    STATUS       current
    DESCRIPTION
        "Cisco Firepower adaptor:FcIfEventStatsHist:invalidCRCCountDeltaMa
        x managed object property"
    ::= { cfprAdaptorFcIfEventStatsHistEntry 8 }

cfprAdaptorFcIfEventStatsHistInvalidCRCCountDeltaMin OBJECT-TYPE
    SYNTAX       Unsigned64
    MAX-ACCESS   read-only
    STATUS       current
    DESCRIPTION
        "Cisco Firepower adaptor:FcIfEventStatsHist:invalidCRCCountDeltaMi
        n managed object property"
    ::= { cfprAdaptorFcIfEventStatsHistEntry 9 }

cfprAdaptorFcIfEventStatsHistLinkFailureCount OBJECT-TYPE
    SYNTAX       Unsigned64
    MAX-ACCESS   read-only
    STATUS       current
    DESCRIPTION
        "Cisco Firepower adaptor:FcIfEventStatsHist:linkFailureCount
        managed object property"
    ::= { cfprAdaptorFcIfEventStatsHistEntry 10 }

cfprAdaptorFcIfEventStatsHistLinkFailureCountDelta OBJECT-TYPE
    SYNTAX       Unsigned64
    MAX-ACCESS   read-only
    STATUS       current
    DESCRIPTION
        "Cisco Firepower adaptor:FcIfEventStatsHist:linkFailureCountDelta
        managed object property"
    ::= { cfprAdaptorFcIfEventStatsHistEntry 11 }

cfprAdaptorFcIfEventStatsHistLinkFailureCountDeltaAvg OBJECT-TYPE
    SYNTAX       Unsigned64
    MAX-ACCESS   read-only
    STATUS       current
    DESCRIPTION
        "Cisco Firepower adaptor:FcIfEventStatsHist:linkFailureCountDeltaA
        vg managed object property"
    ::= { cfprAdaptorFcIfEventStatsHistEntry 12 }

cfprAdaptorFcIfEventStatsHistLinkFailureCountDeltaMax OBJECT-TYPE
    SYNTAX       Unsigned64
    MAX-ACCESS   read-only
    STATUS       current
    DESCRIPTION
        "Cisco Firepower adaptor:FcIfEventStatsHist:linkFailureCountDeltaM
        ax managed object property"
    ::= { cfprAdaptorFcIfEventStatsHistEntry 13 }

cfprAdaptorFcIfEventStatsHistLinkFailureCountDeltaMin OBJECT-TYPE
    SYNTAX       Unsigned64
    MAX-ACCESS   read-only
    STATUS       current
    DESCRIPTION
        "Cisco Firepower adaptor:FcIfEventStatsHist:linkFailureCountDeltaM
        in managed object property"
    ::= { cfprAdaptorFcIfEventStatsHistEntry 14 }

cfprAdaptorFcIfEventStatsHistLipCount OBJECT-TYPE
    SYNTAX       Unsigned64
    MAX-ACCESS   read-only
    STATUS       current
    DESCRIPTION
        "Cisco Firepower adaptor:FcIfEventStatsHist:lipCount
        managed object property"
    ::= { cfprAdaptorFcIfEventStatsHistEntry 15 }

cfprAdaptorFcIfEventStatsHistLipCountDelta OBJECT-TYPE
    SYNTAX       Unsigned64
    MAX-ACCESS   read-only
    STATUS       current
    DESCRIPTION
        "Cisco Firepower adaptor:FcIfEventStatsHist:lipCountDelta
        managed object property"
    ::= { cfprAdaptorFcIfEventStatsHistEntry 16 }

cfprAdaptorFcIfEventStatsHistLipCountDeltaAvg OBJECT-TYPE
    SYNTAX       Unsigned64
    MAX-ACCESS   read-only
    STATUS       current
    DESCRIPTION
        "Cisco Firepower adaptor:FcIfEventStatsHist:lipCountDeltaAvg
        managed object property"
    ::= { cfprAdaptorFcIfEventStatsHistEntry 17 }

cfprAdaptorFcIfEventStatsHistLipCountDeltaMax OBJECT-TYPE
    SYNTAX       Unsigned64
    MAX-ACCESS   read-only
    STATUS       current
    DESCRIPTION
        "Cisco Firepower adaptor:FcIfEventStatsHist:lipCountDeltaMax
        managed object property"
    ::= { cfprAdaptorFcIfEventStatsHistEntry 18 }

cfprAdaptorFcIfEventStatsHistLipCountDeltaMin OBJECT-TYPE
    SYNTAX       Unsigned64
    MAX-ACCESS   read-only
    STATUS       current
    DESCRIPTION
        "Cisco Firepower adaptor:FcIfEventStatsHist:lipCountDeltaMin
        managed object property"
    ::= { cfprAdaptorFcIfEventStatsHistEntry 19 }

cfprAdaptorFcIfEventStatsHistLossOfSignalCount OBJECT-TYPE
    SYNTAX       Unsigned64
    MAX-ACCESS   read-only
    STATUS       current
    DESCRIPTION
        "Cisco Firepower adaptor:FcIfEventStatsHist:lossOfSignalCount
        managed object property"
    ::= { cfprAdaptorFcIfEventStatsHistEntry 20 }

cfprAdaptorFcIfEventStatsHistLossOfSignalCountDelta OBJECT-TYPE
    SYNTAX       Unsigned64
    MAX-ACCESS   read-only
    STATUS       current
    DESCRIPTION
        "Cisco Firepower adaptor:FcIfEventStatsHist:lossOfSignalCountDelta
         managed object property"
    ::= { cfprAdaptorFcIfEventStatsHistEntry 21 }

cfprAdaptorFcIfEventStatsHistLossOfSignalCountDeltaAvg OBJECT-TYPE
    SYNTAX       Unsigned64
    MAX-ACCESS   read-only
    STATUS       current
    DESCRIPTION
        "Cisco Firepower adaptor:FcIfEventStatsHist:lossOfSignalCountDelta
        Avg managed object property"
    ::= { cfprAdaptorFcIfEventStatsHistEntry 22 }

cfprAdaptorFcIfEventStatsHistLossOfSignalCountDeltaMax OBJECT-TYPE
    SYNTAX       Unsigned64
    MAX-ACCESS   read-only
    STATUS       current
    DESCRIPTION
        "Cisco Firepower adaptor:FcIfEventStatsHist:lossOfSignalCountDelta
        Max managed object property"
    ::= { cfprAdaptorFcIfEventStatsHistEntry 23 }

cfprAdaptorFcIfEventStatsHistLossOfSignalCountDeltaMin OBJECT-TYPE
    SYNTAX       Unsigned64
    MAX-ACCESS   read-only
    STATUS       current
    DESCRIPTION
        "Cisco Firepower adaptor:FcIfEventStatsHist:lossOfSignalCountDelta
        Min managed object property"
    ::= { cfprAdaptorFcIfEventStatsHistEntry 24 }

cfprAdaptorFcIfEventStatsHistLossOfSyncCount OBJECT-TYPE
    SYNTAX       Unsigned64
    MAX-ACCESS   read-only
    STATUS       current
    DESCRIPTION
        "Cisco Firepower adaptor:FcIfEventStatsHist:lossOfSyncCount
        managed object property"
    ::= { cfprAdaptorFcIfEventStatsHistEntry 25 }

cfprAdaptorFcIfEventStatsHistLossOfSyncCountDelta OBJECT-TYPE
    SYNTAX       Unsigned64
    MAX-ACCESS   read-only
    STATUS       current
    DESCRIPTION
        "Cisco Firepower adaptor:FcIfEventStatsHist:lossOfSyncCountDelta
        managed object property"
    ::= { cfprAdaptorFcIfEventStatsHistEntry 26 }

cfprAdaptorFcIfEventStatsHistLossOfSyncCountDeltaAvg OBJECT-TYPE
    SYNTAX       Unsigned64
    MAX-ACCESS   read-only
    STATUS       current
    DESCRIPTION
        "Cisco Firepower adaptor:FcIfEventStatsHist:lossOfSyncCountDeltaAv
        g managed object property"
    ::= { cfprAdaptorFcIfEventStatsHistEntry 27 }

cfprAdaptorFcIfEventStatsHistLossOfSyncCountDeltaMax OBJECT-TYPE
    SYNTAX       Unsigned64
    MAX-ACCESS   read-only
    STATUS       current
    DESCRIPTION
        "Cisco Firepower adaptor:FcIfEventStatsHist:lossOfSyncCountDeltaMa
        x managed object property"
    ::= { cfprAdaptorFcIfEventStatsHistEntry 28 }

cfprAdaptorFcIfEventStatsHistLossOfSyncCountDeltaMin OBJECT-TYPE
    SYNTAX       Unsigned64
    MAX-ACCESS   read-only
    STATUS       current
    DESCRIPTION
        "Cisco Firepower adaptor:FcIfEventStatsHist:lossOfSyncCountDeltaMi
        n managed object property"
    ::= { cfprAdaptorFcIfEventStatsHistEntry 29 }

cfprAdaptorFcIfEventStatsHistMostRecent OBJECT-TYPE
    SYNTAX       TruthValue
    MAX-ACCESS   read-only
    STATUS       current
    DESCRIPTION
        "Cisco Firepower adaptor:FcIfEventStatsHist:mostRecent
        managed object property"
    ::= { cfprAdaptorFcIfEventStatsHistEntry 30 }

cfprAdaptorFcIfEventStatsHistNOSCount OBJECT-TYPE
    SYNTAX       Unsigned64
    MAX-ACCESS   read-only
    STATUS       current
    DESCRIPTION
        "Cisco Firepower adaptor:FcIfEventStatsHist:nOSCount
        managed object property"
    ::= { cfprAdaptorFcIfEventStatsHistEntry 31 }

cfprAdaptorFcIfEventStatsHistNOSCountDelta OBJECT-TYPE
    SYNTAX       Unsigned64
    MAX-ACCESS   read-only
    STATUS       current
    DESCRIPTION
        "Cisco Firepower adaptor:FcIfEventStatsHist:nOSCountDelta
        managed object property"
    ::= { cfprAdaptorFcIfEventStatsHistEntry 32 }

cfprAdaptorFcIfEventStatsHistNOSCountDeltaAvg OBJECT-TYPE
    SYNTAX       Unsigned64
    MAX-ACCESS   read-only
    STATUS       current
    DESCRIPTION
        "Cisco Firepower adaptor:FcIfEventStatsHist:nOSCountDeltaAvg
        managed object property"
    ::= { cfprAdaptorFcIfEventStatsHistEntry 33 }

cfprAdaptorFcIfEventStatsHistNOSCountDeltaMax OBJECT-TYPE
    SYNTAX       Unsigned64
    MAX-ACCESS   read-only
    STATUS       current
    DESCRIPTION
        "Cisco Firepower adaptor:FcIfEventStatsHist:nOSCountDeltaMax
        managed object property"
    ::= { cfprAdaptorFcIfEventStatsHistEntry 34 }

cfprAdaptorFcIfEventStatsHistNOSCountDeltaMin OBJECT-TYPE
    SYNTAX       Unsigned64
    MAX-ACCESS   read-only
    STATUS       current
    DESCRIPTION
        "Cisco Firepower adaptor:FcIfEventStatsHist:nOSCountDeltaMin
        managed object property"
    ::= { cfprAdaptorFcIfEventStatsHistEntry 35 }

cfprAdaptorFcIfEventStatsHistSecondsSinceLastReset OBJECT-TYPE
    SYNTAX       Unsigned64
    MAX-ACCESS   read-only
    STATUS       current
    DESCRIPTION
        "Cisco Firepower adaptor:FcIfEventStatsHist:secondsSinceLastReset
        managed object property"
    ::= { cfprAdaptorFcIfEventStatsHistEntry 36 }

cfprAdaptorFcIfEventStatsHistSecondsSinceLastResetDelta OBJECT-TYPE
    SYNTAX       Unsigned64
    MAX-ACCESS   read-only
    STATUS       current
    DESCRIPTION
        "Cisco Firepower adaptor:FcIfEventStatsHist:secondsSinceLastResetD
        elta managed object property"
    ::= { cfprAdaptorFcIfEventStatsHistEntry 37 }

cfprAdaptorFcIfEventStatsHistSecondsSinceLastResetDeltaAvg OBJECT-TYPE
    SYNTAX       Unsigned64
    MAX-ACCESS   read-only
    STATUS       current
    DESCRIPTION
        "Cisco Firepower adaptor:FcIfEventStatsHist:secondsSinceLastResetD
        eltaAvg managed object property"
    ::= { cfprAdaptorFcIfEventStatsHistEntry 38 }

cfprAdaptorFcIfEventStatsHistSecondsSinceLastResetDeltaMax OBJECT-TYPE
    SYNTAX       Unsigned64
    MAX-ACCESS   read-only
    STATUS       current
    DESCRIPTION
        "Cisco Firepower adaptor:FcIfEventStatsHist:secondsSinceLastResetD
        eltaMax managed object property"
    ::= { cfprAdaptorFcIfEventStatsHistEntry 39 }

cfprAdaptorFcIfEventStatsHistSecondsSinceLastResetDeltaMin OBJECT-TYPE
    SYNTAX       Unsigned64
    MAX-ACCESS   read-only
    STATUS       current
    DESCRIPTION
        "Cisco Firepower adaptor:FcIfEventStatsHist:secondsSinceLastResetD
        eltaMin managed object property"
    ::= { cfprAdaptorFcIfEventStatsHistEntry 40 }

cfprAdaptorFcIfEventStatsHistSeqProtocolErrCount OBJECT-TYPE
    SYNTAX       Unsigned64
    MAX-ACCESS   read-only
    STATUS       current
    DESCRIPTION
        "Cisco Firepower adaptor:FcIfEventStatsHist:seqProtocolErrCount
        managed object property"
    ::= { cfprAdaptorFcIfEventStatsHistEntry 41 }

cfprAdaptorFcIfEventStatsHistSeqProtocolErrCountDelta OBJECT-TYPE
    SYNTAX       Unsigned64
    MAX-ACCESS   read-only
    STATUS       current
    DESCRIPTION
        "Cisco Firepower adaptor:FcIfEventStatsHist:seqProtocolErrCountDel
        ta managed object property"
    ::= { cfprAdaptorFcIfEventStatsHistEntry 42 }

cfprAdaptorFcIfEventStatsHistSeqProtocolErrCountDeltaAvg OBJECT-TYPE
    SYNTAX       Unsigned64
    MAX-ACCESS   read-only
    STATUS       current
    DESCRIPTION
        "Cisco Firepower adaptor:FcIfEventStatsHist:seqProtocolErrCountDel
        taAvg managed object property"
    ::= { cfprAdaptorFcIfEventStatsHistEntry 43 }

cfprAdaptorFcIfEventStatsHistSeqProtocolErrCountDeltaMax OBJECT-TYPE
    SYNTAX       Unsigned64
    MAX-ACCESS   read-only
    STATUS       current
    DESCRIPTION
        "Cisco Firepower adaptor:FcIfEventStatsHist:seqProtocolErrCountDel
        taMax managed object property"
    ::= { cfprAdaptorFcIfEventStatsHistEntry 44 }

cfprAdaptorFcIfEventStatsHistSeqProtocolErrCountDeltaMin OBJECT-TYPE
    SYNTAX       Unsigned64
    MAX-ACCESS   read-only
    STATUS       current
    DESCRIPTION
        "Cisco Firepower adaptor:FcIfEventStatsHist:seqProtocolErrCountDel
        taMin managed object property"
    ::= { cfprAdaptorFcIfEventStatsHistEntry 45 }

cfprAdaptorFcIfEventStatsHistSuspect OBJECT-TYPE
    SYNTAX       TruthValue
    MAX-ACCESS   read-only
    STATUS       current
    DESCRIPTION
        "Cisco Firepower adaptor:FcIfEventStatsHist:suspect
        managed object property"
    ::= { cfprAdaptorFcIfEventStatsHistEntry 46 }

cfprAdaptorFcIfEventStatsHistThresholded OBJECT-TYPE
    SYNTAX       CfprAdaptorFcIfEventStatsHistThresholded
    MAX-ACCESS   read-only
    STATUS       current
    DESCRIPTION
        "Cisco Firepower adaptor:FcIfEventStatsHist:thresholded
        managed object property"
    ::= { cfprAdaptorFcIfEventStatsHistEntry 47 }

cfprAdaptorFcIfEventStatsHistTimeCollected OBJECT-TYPE
    SYNTAX       DateAndTime
    MAX-ACCESS   read-only
    STATUS       current
    DESCRIPTION
        "Cisco Firepower adaptor:FcIfEventStatsHist:timeCollected
        managed object property"
    ::= { cfprAdaptorFcIfEventStatsHistEntry 48 }

cfprAdaptorFcIfFC4StatsTable OBJECT-TYPE
    SYNTAX           SEQUENCE OF CfprAdaptorFcIfFC4StatsEntry
    MAX-ACCESS       not-accessible
    STATUS           current
    DESCRIPTION
        "Cisco Firepower adaptor:FcIfFC4Stats managed object table"
    ::= { cfprAdaptorObjects 40 }

cfprAdaptorFcIfFC4StatsEntry OBJECT-TYPE
    SYNTAX           CfprAdaptorFcIfFC4StatsEntry
    MAX-ACCESS       not-accessible
    STATUS           current
    DESCRIPTION
        "Entry for the cfprAdaptorFcIfFC4StatsTable table."
    INDEX { cfprAdaptorFcIfFC4StatsInstanceId }
    ::= { cfprAdaptorFcIfFC4StatsTable 1 }

CfprAdaptorFcIfFC4StatsEntry ::= SEQUENCE {
    cfprAdaptorFcIfFC4StatsInstanceId                                CfprManagedObjectId,
    cfprAdaptorFcIfFC4StatsDn                                        CfprManagedObjectDn,
    cfprAdaptorFcIfFC4StatsRn                                        SnmpAdminString,
    cfprAdaptorFcIfFC4StatsControlRequests                           Unsigned64,
    cfprAdaptorFcIfFC4StatsControlRequestsDelta                      Counter64,
    cfprAdaptorFcIfFC4StatsControlRequestsDeltaAvg                   Unsigned64,
    cfprAdaptorFcIfFC4StatsControlRequestsDeltaMax                   Unsigned64,
    cfprAdaptorFcIfFC4StatsControlRequestsDeltaMin                   Unsigned64,
    cfprAdaptorFcIfFC4StatsInputMegabytes                            Unsigned64,
    cfprAdaptorFcIfFC4StatsInputMegabytesDelta                       Counter64,
    cfprAdaptorFcIfFC4StatsInputMegabytesDeltaAvg                    Unsigned64,
    cfprAdaptorFcIfFC4StatsInputMegabytesDeltaMax                    Unsigned64,
    cfprAdaptorFcIfFC4StatsInputMegabytesDeltaMin                    Unsigned64,
    cfprAdaptorFcIfFC4StatsInputRequests                             Unsigned64,
    cfprAdaptorFcIfFC4StatsInputRequestsDelta                        Counter64,
    cfprAdaptorFcIfFC4StatsInputRequestsDeltaAvg                     Unsigned64,
    cfprAdaptorFcIfFC4StatsInputRequestsDeltaMax                     Unsigned64,
    cfprAdaptorFcIfFC4StatsInputRequestsDeltaMin                     Unsigned64,
    cfprAdaptorFcIfFC4StatsIntervals                                 Gauge32,
    cfprAdaptorFcIfFC4StatsOutputMegabytes                           Unsigned64,
    cfprAdaptorFcIfFC4StatsOutputMegabytesDelta                      Counter64,
    cfprAdaptorFcIfFC4StatsOutputMegabytesDeltaAvg                   Unsigned64,
    cfprAdaptorFcIfFC4StatsOutputMegabytesDeltaMax                   Unsigned64,
    cfprAdaptorFcIfFC4StatsOutputMegabytesDeltaMin                   Unsigned64,
    cfprAdaptorFcIfFC4StatsOutputRequests                            Unsigned64,
    cfprAdaptorFcIfFC4StatsOutputRequestsDelta                       Counter64,
    cfprAdaptorFcIfFC4StatsOutputRequestsDeltaAvg                    Unsigned64,
    cfprAdaptorFcIfFC4StatsOutputRequestsDeltaMax                    Unsigned64,
    cfprAdaptorFcIfFC4StatsOutputRequestsDeltaMin                    Unsigned64,
    cfprAdaptorFcIfFC4StatsSuspect                                   TruthValue,
    cfprAdaptorFcIfFC4StatsThresholded                               CfprAdaptorFcIfFC4StatsThresholded,
    cfprAdaptorFcIfFC4StatsTimeCollected                             DateAndTime,
    cfprAdaptorFcIfFC4StatsUpdate                                    Gauge32
}

cfprAdaptorFcIfFC4StatsInstanceId OBJECT-TYPE
    SYNTAX       CfprManagedObjectId
    MAX-ACCESS   not-accessible
    STATUS       current
    DESCRIPTION
        "Instance identifier of the managed object."
    ::= { cfprAdaptorFcIfFC4StatsEntry 1 }

cfprAdaptorFcIfFC4StatsDn OBJECT-TYPE
    SYNTAX       CfprManagedObjectDn
    MAX-ACCESS   read-only
    STATUS       current
    DESCRIPTION
        "Cisco Firepower adaptor:FcIfFC4Stats:dn managed object property"
    ::= { cfprAdaptorFcIfFC4StatsEntry 2 }

cfprAdaptorFcIfFC4StatsRn OBJECT-TYPE
    SYNTAX       SnmpAdminString
    MAX-ACCESS   read-only
    STATUS       current
    DESCRIPTION
        "Cisco Firepower adaptor:FcIfFC4Stats:rn managed object property"
    ::= { cfprAdaptorFcIfFC4StatsEntry 3 }

cfprAdaptorFcIfFC4StatsControlRequests OBJECT-TYPE
    SYNTAX       Unsigned64
    MAX-ACCESS   read-only
    STATUS       current
    DESCRIPTION
        "Cisco Firepower adaptor:FcIfFC4Stats:controlRequests
        managed object property"
    ::= { cfprAdaptorFcIfFC4StatsEntry 4 }

cfprAdaptorFcIfFC4StatsControlRequestsDelta OBJECT-TYPE
    SYNTAX       Counter64
    MAX-ACCESS   read-only
    STATUS       current
    DESCRIPTION
        "Cisco Firepower adaptor:FcIfFC4Stats:controlRequestsDelta
        managed object property"
    ::= { cfprAdaptorFcIfFC4StatsEntry 5 }

cfprAdaptorFcIfFC4StatsControlRequestsDeltaAvg OBJECT-TYPE
    SYNTAX       Unsigned64
    MAX-ACCESS   read-only
    STATUS       current
    DESCRIPTION
        "Cisco Firepower adaptor:FcIfFC4Stats:controlRequestsDeltaAvg
        managed object property"
    ::= { cfprAdaptorFcIfFC4StatsEntry 6 }

cfprAdaptorFcIfFC4StatsControlRequestsDeltaMax OBJECT-TYPE
    SYNTAX       Unsigned64
    MAX-ACCESS   read-only
    STATUS       current
    DESCRIPTION
        "Cisco Firepower adaptor:FcIfFC4Stats:controlRequestsDeltaMax
        managed object property"
    ::= { cfprAdaptorFcIfFC4StatsEntry 7 }

cfprAdaptorFcIfFC4StatsControlRequestsDeltaMin OBJECT-TYPE
    SYNTAX       Unsigned64
    MAX-ACCESS   read-only
    STATUS       current
    DESCRIPTION
        "Cisco Firepower adaptor:FcIfFC4Stats:controlRequestsDeltaMin
        managed object property"
    ::= { cfprAdaptorFcIfFC4StatsEntry 8 }

cfprAdaptorFcIfFC4StatsInputMegabytes OBJECT-TYPE
    SYNTAX       Unsigned64
    MAX-ACCESS   read-only
    STATUS       current
    DESCRIPTION
        "Cisco Firepower adaptor:FcIfFC4Stats:inputMegabytes
        managed object property"
    ::= { cfprAdaptorFcIfFC4StatsEntry 9 }

cfprAdaptorFcIfFC4StatsInputMegabytesDelta OBJECT-TYPE
    SYNTAX       Counter64
    MAX-ACCESS   read-only
    STATUS       current
    DESCRIPTION
        "Cisco Firepower adaptor:FcIfFC4Stats:inputMegabytesDelta
        managed object property"
    ::= { cfprAdaptorFcIfFC4StatsEntry 10 }

cfprAdaptorFcIfFC4StatsInputMegabytesDeltaAvg OBJECT-TYPE
    SYNTAX       Unsigned64
    MAX-ACCESS   read-only
    STATUS       current
    DESCRIPTION
        "Cisco Firepower adaptor:FcIfFC4Stats:inputMegabytesDeltaAvg
        managed object property"
    ::= { cfprAdaptorFcIfFC4StatsEntry 11 }

cfprAdaptorFcIfFC4StatsInputMegabytesDeltaMax OBJECT-TYPE
    SYNTAX       Unsigned64
    MAX-ACCESS   read-only
    STATUS       current
    DESCRIPTION
        "Cisco Firepower adaptor:FcIfFC4Stats:inputMegabytesDeltaMax
        managed object property"
    ::= { cfprAdaptorFcIfFC4StatsEntry 12 }

cfprAdaptorFcIfFC4StatsInputMegabytesDeltaMin OBJECT-TYPE
    SYNTAX       Unsigned64
    MAX-ACCESS   read-only
    STATUS       current
    DESCRIPTION
        "Cisco Firepower adaptor:FcIfFC4Stats:inputMegabytesDeltaMin
        managed object property"
    ::= { cfprAdaptorFcIfFC4StatsEntry 13 }

cfprAdaptorFcIfFC4StatsInputRequests OBJECT-TYPE
    SYNTAX       Unsigned64
    MAX-ACCESS   read-only
    STATUS       current
    DESCRIPTION
        "Cisco Firepower adaptor:FcIfFC4Stats:inputRequests
        managed object property"
    ::= { cfprAdaptorFcIfFC4StatsEntry 14 }

cfprAdaptorFcIfFC4StatsInputRequestsDelta OBJECT-TYPE
    SYNTAX       Counter64
    MAX-ACCESS   read-only
    STATUS       current
    DESCRIPTION
        "Cisco Firepower adaptor:FcIfFC4Stats:inputRequestsDelta
        managed object property"
    ::= { cfprAdaptorFcIfFC4StatsEntry 15 }

cfprAdaptorFcIfFC4StatsInputRequestsDeltaAvg OBJECT-TYPE
    SYNTAX       Unsigned64
    MAX-ACCESS   read-only
    STATUS       current
    DESCRIPTION
        "Cisco Firepower adaptor:FcIfFC4Stats:inputRequestsDeltaAvg
        managed object property"
    ::= { cfprAdaptorFcIfFC4StatsEntry 16 }

cfprAdaptorFcIfFC4StatsInputRequestsDeltaMax OBJECT-TYPE
    SYNTAX       Unsigned64
    MAX-ACCESS   read-only
    STATUS       current
    DESCRIPTION
        "Cisco Firepower adaptor:FcIfFC4Stats:inputRequestsDeltaMax
        managed object property"
    ::= { cfprAdaptorFcIfFC4StatsEntry 17 }

cfprAdaptorFcIfFC4StatsInputRequestsDeltaMin OBJECT-TYPE
    SYNTAX       Unsigned64
    MAX-ACCESS   read-only
    STATUS       current
    DESCRIPTION
        "Cisco Firepower adaptor:FcIfFC4Stats:inputRequestsDeltaMin
        managed object property"
    ::= { cfprAdaptorFcIfFC4StatsEntry 18 }

cfprAdaptorFcIfFC4StatsIntervals OBJECT-TYPE
    SYNTAX       Gauge32
    MAX-ACCESS   read-only
    STATUS       current
    DESCRIPTION
        "Cisco Firepower adaptor:FcIfFC4Stats:intervals
        managed object property"
    ::= { cfprAdaptorFcIfFC4StatsEntry 19 }

cfprAdaptorFcIfFC4StatsOutputMegabytes OBJECT-TYPE
    SYNTAX       Unsigned64
    MAX-ACCESS   read-only
    STATUS       current
    DESCRIPTION
        "Cisco Firepower adaptor:FcIfFC4Stats:outputMegabytes
        managed object property"
    ::= { cfprAdaptorFcIfFC4StatsEntry 20 }

cfprAdaptorFcIfFC4StatsOutputMegabytesDelta OBJECT-TYPE
    SYNTAX       Counter64
    MAX-ACCESS   read-only
    STATUS       current
    DESCRIPTION
        "Cisco Firepower adaptor:FcIfFC4Stats:outputMegabytesDelta
        managed object property"
    ::= { cfprAdaptorFcIfFC4StatsEntry 21 }

cfprAdaptorFcIfFC4StatsOutputMegabytesDeltaAvg OBJECT-TYPE
    SYNTAX       Unsigned64
    MAX-ACCESS   read-only
    STATUS       current
    DESCRIPTION
        "Cisco Firepower adaptor:FcIfFC4Stats:outputMegabytesDeltaAvg
        managed object property"
    ::= { cfprAdaptorFcIfFC4StatsEntry 22 }

cfprAdaptorFcIfFC4StatsOutputMegabytesDeltaMax OBJECT-TYPE
    SYNTAX       Unsigned64
    MAX-ACCESS   read-only
    STATUS       current
    DESCRIPTION
        "Cisco Firepower adaptor:FcIfFC4Stats:outputMegabytesDeltaMax
        managed object property"
    ::= { cfprAdaptorFcIfFC4StatsEntry 23 }

cfprAdaptorFcIfFC4StatsOutputMegabytesDeltaMin OBJECT-TYPE
    SYNTAX       Unsigned64
    MAX-ACCESS   read-only
    STATUS       current
    DESCRIPTION
        "Cisco Firepower adaptor:FcIfFC4Stats:outputMegabytesDeltaMin
        managed object property"
    ::= { cfprAdaptorFcIfFC4StatsEntry 24 }

cfprAdaptorFcIfFC4StatsOutputRequests OBJECT-TYPE
    SYNTAX       Unsigned64
    MAX-ACCESS   read-only
    STATUS       current
    DESCRIPTION
        "Cisco Firepower adaptor:FcIfFC4Stats:outputRequests
        managed object property"
    ::= { cfprAdaptorFcIfFC4StatsEntry 25 }

cfprAdaptorFcIfFC4StatsOutputRequestsDelta OBJECT-TYPE
    SYNTAX       Counter64
    MAX-ACCESS   read-only
    STATUS       current
    DESCRIPTION
        "Cisco Firepower adaptor:FcIfFC4Stats:outputRequestsDelta
        managed object property"
    ::= { cfprAdaptorFcIfFC4StatsEntry 26 }

cfprAdaptorFcIfFC4StatsOutputRequestsDeltaAvg OBJECT-TYPE
    SYNTAX       Unsigned64
    MAX-ACCESS   read-only
    STATUS       current
    DESCRIPTION
        "Cisco Firepower adaptor:FcIfFC4Stats:outputRequestsDeltaAvg
        managed object property"
    ::= { cfprAdaptorFcIfFC4StatsEntry 27 }

cfprAdaptorFcIfFC4StatsOutputRequestsDeltaMax OBJECT-TYPE
    SYNTAX       Unsigned64
    MAX-ACCESS   read-only
    STATUS       current
    DESCRIPTION
        "Cisco Firepower adaptor:FcIfFC4Stats:outputRequestsDeltaMax
        managed object property"
    ::= { cfprAdaptorFcIfFC4StatsEntry 28 }

cfprAdaptorFcIfFC4StatsOutputRequestsDeltaMin OBJECT-TYPE
    SYNTAX       Unsigned64
    MAX-ACCESS   read-only
    STATUS       current
    DESCRIPTION
        "Cisco Firepower adaptor:FcIfFC4Stats:outputRequestsDeltaMin
        managed object property"
    ::= { cfprAdaptorFcIfFC4StatsEntry 29 }

cfprAdaptorFcIfFC4StatsSuspect OBJECT-TYPE
    SYNTAX       TruthValue
    MAX-ACCESS   read-only
    STATUS       current
    DESCRIPTION
        "Cisco Firepower adaptor:FcIfFC4Stats:suspect managed
        object property"
    ::= { cfprAdaptorFcIfFC4StatsEntry 30 }

cfprAdaptorFcIfFC4StatsThresholded OBJECT-TYPE
    SYNTAX       CfprAdaptorFcIfFC4StatsThresholded
    MAX-ACCESS   read-only
    STATUS       current
    DESCRIPTION
        "Cisco Firepower adaptor:FcIfFC4Stats:thresholded
        managed object property"
    ::= { cfprAdaptorFcIfFC4StatsEntry 31 }

cfprAdaptorFcIfFC4StatsTimeCollected OBJECT-TYPE
    SYNTAX       DateAndTime
    MAX-ACCESS   read-only
    STATUS       current
    DESCRIPTION
        "Cisco Firepower adaptor:FcIfFC4Stats:timeCollected
        managed object property"
    ::= { cfprAdaptorFcIfFC4StatsEntry 32 }

cfprAdaptorFcIfFC4StatsUpdate OBJECT-TYPE
    SYNTAX       Gauge32
    MAX-ACCESS   read-only
    STATUS       current
    DESCRIPTION
        "Cisco Firepower adaptor:FcIfFC4Stats:update managed
        object property"
    ::= { cfprAdaptorFcIfFC4StatsEntry 33 }

cfprAdaptorFcIfFC4StatsHistTable OBJECT-TYPE
    SYNTAX           SEQUENCE OF CfprAdaptorFcIfFC4StatsHistEntry
    MAX-ACCESS       not-accessible
    STATUS           current
    DESCRIPTION
        "Cisco Firepower adaptor:FcIfFC4StatsHist managed object table"
    ::= { cfprAdaptorObjects 41 }

cfprAdaptorFcIfFC4StatsHistEntry OBJECT-TYPE
    SYNTAX           CfprAdaptorFcIfFC4StatsHistEntry
    MAX-ACCESS       not-accessible
    STATUS           current
    DESCRIPTION
        "Entry for the cfprAdaptorFcIfFC4StatsHistTable table."
    INDEX { cfprAdaptorFcIfFC4StatsHistInstanceId }
    ::= { cfprAdaptorFcIfFC4StatsHistTable 1 }

CfprAdaptorFcIfFC4StatsHistEntry ::= SEQUENCE {
    cfprAdaptorFcIfFC4StatsHistInstanceId                            CfprManagedObjectId,
    cfprAdaptorFcIfFC4StatsHistDn                                    CfprManagedObjectDn,
    cfprAdaptorFcIfFC4StatsHistRn                                    SnmpAdminString,
    cfprAdaptorFcIfFC4StatsHistControlRequests                       Unsigned64,
    cfprAdaptorFcIfFC4StatsHistControlRequestsDelta                  Unsigned64,
    cfprAdaptorFcIfFC4StatsHistControlRequestsDeltaAvg               Unsigned64,
    cfprAdaptorFcIfFC4StatsHistControlRequestsDeltaMax               Unsigned64,
    cfprAdaptorFcIfFC4StatsHistControlRequestsDeltaMin               Unsigned64,
    cfprAdaptorFcIfFC4StatsHistId                                    Unsigned64,
    cfprAdaptorFcIfFC4StatsHistInputMegabytes                        Unsigned64,
    cfprAdaptorFcIfFC4StatsHistInputMegabytesDelta                   Unsigned64,
    cfprAdaptorFcIfFC4StatsHistInputMegabytesDeltaAvg                Unsigned64,
    cfprAdaptorFcIfFC4StatsHistInputMegabytesDeltaMax                Unsigned64,
    cfprAdaptorFcIfFC4StatsHistInputMegabytesDeltaMin                Unsigned64,
    cfprAdaptorFcIfFC4StatsHistInputRequests                         Unsigned64,
    cfprAdaptorFcIfFC4StatsHistInputRequestsDelta                    Unsigned64,
    cfprAdaptorFcIfFC4StatsHistInputRequestsDeltaAvg                 Unsigned64,
    cfprAdaptorFcIfFC4StatsHistInputRequestsDeltaMax                 Unsigned64,
    cfprAdaptorFcIfFC4StatsHistInputRequestsDeltaMin                 Unsigned64,
    cfprAdaptorFcIfFC4StatsHistMostRecent                            TruthValue,
    cfprAdaptorFcIfFC4StatsHistOutputMegabytes                       Unsigned64,
    cfprAdaptorFcIfFC4StatsHistOutputMegabytesDelta                  Unsigned64,
    cfprAdaptorFcIfFC4StatsHistOutputMegabytesDeltaAvg               Unsigned64,
    cfprAdaptorFcIfFC4StatsHistOutputMegabytesDeltaMax               Unsigned64,
    cfprAdaptorFcIfFC4StatsHistOutputMegabytesDeltaMin               Unsigned64,
    cfprAdaptorFcIfFC4StatsHistOutputRequests                        Unsigned64,
    cfprAdaptorFcIfFC4StatsHistOutputRequestsDelta                   Unsigned64,
    cfprAdaptorFcIfFC4StatsHistOutputRequestsDeltaAvg                Unsigned64,
    cfprAdaptorFcIfFC4StatsHistOutputRequestsDeltaMax                Unsigned64,
    cfprAdaptorFcIfFC4StatsHistOutputRequestsDeltaMin                Unsigned64,
    cfprAdaptorFcIfFC4StatsHistSuspect                               TruthValue,
    cfprAdaptorFcIfFC4StatsHistThresholded                           CfprAdaptorFcIfFC4StatsHistThresholded,
    cfprAdaptorFcIfFC4StatsHistTimeCollected                         DateAndTime
}

cfprAdaptorFcIfFC4StatsHistInstanceId OBJECT-TYPE
    SYNTAX       CfprManagedObjectId
    MAX-ACCESS   not-accessible
    STATUS       current
    DESCRIPTION
        "Instance identifier of the managed object."
    ::= { cfprAdaptorFcIfFC4StatsHistEntry 1 }

cfprAdaptorFcIfFC4StatsHistDn OBJECT-TYPE
    SYNTAX       CfprManagedObjectDn
    MAX-ACCESS   read-only
    STATUS       current
    DESCRIPTION
        "Cisco Firepower adaptor:FcIfFC4StatsHist:dn managed
        object property"
    ::= { cfprAdaptorFcIfFC4StatsHistEntry 2 }

cfprAdaptorFcIfFC4StatsHistRn OBJECT-TYPE
    SYNTAX       SnmpAdminString
    MAX-ACCESS   read-only
    STATUS       current
    DESCRIPTION
        "Cisco Firepower adaptor:FcIfFC4StatsHist:rn managed
        object property"
    ::= { cfprAdaptorFcIfFC4StatsHistEntry 3 }

cfprAdaptorFcIfFC4StatsHistControlRequests OBJECT-TYPE
    SYNTAX       Unsigned64
    MAX-ACCESS   read-only
    STATUS       current
    DESCRIPTION
        "Cisco Firepower adaptor:FcIfFC4StatsHist:controlRequests
        managed object property"
    ::= { cfprAdaptorFcIfFC4StatsHistEntry 4 }

cfprAdaptorFcIfFC4StatsHistControlRequestsDelta OBJECT-TYPE
    SYNTAX       Unsigned64
    MAX-ACCESS   read-only
    STATUS       current
    DESCRIPTION
        "Cisco Firepower adaptor:FcIfFC4StatsHist:controlRequestsDelta
        managed object property"
    ::= { cfprAdaptorFcIfFC4StatsHistEntry 5 }

cfprAdaptorFcIfFC4StatsHistControlRequestsDeltaAvg OBJECT-TYPE
    SYNTAX       Unsigned64
    MAX-ACCESS   read-only
    STATUS       current
    DESCRIPTION
        "Cisco Firepower adaptor:FcIfFC4StatsHist:controlRequestsDeltaAvg
        managed object property"
    ::= { cfprAdaptorFcIfFC4StatsHistEntry 6 }

cfprAdaptorFcIfFC4StatsHistControlRequestsDeltaMax OBJECT-TYPE
    SYNTAX       Unsigned64
    MAX-ACCESS   read-only
    STATUS       current
    DESCRIPTION
        "Cisco Firepower adaptor:FcIfFC4StatsHist:controlRequestsDeltaMax
        managed object property"
    ::= { cfprAdaptorFcIfFC4StatsHistEntry 7 }

cfprAdaptorFcIfFC4StatsHistControlRequestsDeltaMin OBJECT-TYPE
    SYNTAX       Unsigned64
    MAX-ACCESS   read-only
    STATUS       current
    DESCRIPTION
        "Cisco Firepower adaptor:FcIfFC4StatsHist:controlRequestsDeltaMin
        managed object property"
    ::= { cfprAdaptorFcIfFC4StatsHistEntry 8 }

cfprAdaptorFcIfFC4StatsHistId OBJECT-TYPE
    SYNTAX       Unsigned64
    MAX-ACCESS   read-only
    STATUS       current
    DESCRIPTION
        "Cisco Firepower adaptor:FcIfFC4StatsHist:id managed
        object property"
    ::= { cfprAdaptorFcIfFC4StatsHistEntry 9 }

cfprAdaptorFcIfFC4StatsHistInputMegabytes OBJECT-TYPE
    SYNTAX       Unsigned64
    MAX-ACCESS   read-only
    STATUS       current
    DESCRIPTION
        "Cisco Firepower adaptor:FcIfFC4StatsHist:inputMegabytes
        managed object property"
    ::= { cfprAdaptorFcIfFC4StatsHistEntry 10 }

cfprAdaptorFcIfFC4StatsHistInputMegabytesDelta OBJECT-TYPE
    SYNTAX       Unsigned64
    MAX-ACCESS   read-only
    STATUS       current
    DESCRIPTION
        "Cisco Firepower adaptor:FcIfFC4StatsHist:inputMegabytesDelta
        managed object property"
    ::= { cfprAdaptorFcIfFC4StatsHistEntry 11 }

cfprAdaptorFcIfFC4StatsHistInputMegabytesDeltaAvg OBJECT-TYPE
    SYNTAX       Unsigned64
    MAX-ACCESS   read-only
    STATUS       current
    DESCRIPTION
        "Cisco Firepower adaptor:FcIfFC4StatsHist:inputMegabytesDeltaAvg
        managed object property"
    ::= { cfprAdaptorFcIfFC4StatsHistEntry 12 }

cfprAdaptorFcIfFC4StatsHistInputMegabytesDeltaMax OBJECT-TYPE
    SYNTAX       Unsigned64
    MAX-ACCESS   read-only
    STATUS       current
    DESCRIPTION
        "Cisco Firepower adaptor:FcIfFC4StatsHist:inputMegabytesDeltaMax
        managed object property"
    ::= { cfprAdaptorFcIfFC4StatsHistEntry 13 }

cfprAdaptorFcIfFC4StatsHistInputMegabytesDeltaMin OBJECT-TYPE
    SYNTAX       Unsigned64
    MAX-ACCESS   read-only
    STATUS       current
    DESCRIPTION
        "Cisco Firepower adaptor:FcIfFC4StatsHist:inputMegabytesDeltaMin
        managed object property"
    ::= { cfprAdaptorFcIfFC4StatsHistEntry 14 }

cfprAdaptorFcIfFC4StatsHistInputRequests OBJECT-TYPE
    SYNTAX       Unsigned64
    MAX-ACCESS   read-only
    STATUS       current
    DESCRIPTION
        "Cisco Firepower adaptor:FcIfFC4StatsHist:inputRequests
        managed object property"
    ::= { cfprAdaptorFcIfFC4StatsHistEntry 15 }

cfprAdaptorFcIfFC4StatsHistInputRequestsDelta OBJECT-TYPE
    SYNTAX       Unsigned64
    MAX-ACCESS   read-only
    STATUS       current
    DESCRIPTION
        "Cisco Firepower adaptor:FcIfFC4StatsHist:inputRequestsDelta
        managed object property"
    ::= { cfprAdaptorFcIfFC4StatsHistEntry 16 }

cfprAdaptorFcIfFC4StatsHistInputRequestsDeltaAvg OBJECT-TYPE
    SYNTAX       Unsigned64
    MAX-ACCESS   read-only
    STATUS       current
    DESCRIPTION
        "Cisco Firepower adaptor:FcIfFC4StatsHist:inputRequestsDeltaAvg
        managed object property"
    ::= { cfprAdaptorFcIfFC4StatsHistEntry 17 }

cfprAdaptorFcIfFC4StatsHistInputRequestsDeltaMax OBJECT-TYPE
    SYNTAX       Unsigned64
    MAX-ACCESS   read-only
    STATUS       current
    DESCRIPTION
        "Cisco Firepower adaptor:FcIfFC4StatsHist:inputRequestsDeltaMax
        managed object property"
    ::= { cfprAdaptorFcIfFC4StatsHistEntry 18 }

cfprAdaptorFcIfFC4StatsHistInputRequestsDeltaMin OBJECT-TYPE
    SYNTAX       Unsigned64
    MAX-ACCESS   read-only
    STATUS       current
    DESCRIPTION
        "Cisco Firepower adaptor:FcIfFC4StatsHist:inputRequestsDeltaMin
        managed object property"
    ::= { cfprAdaptorFcIfFC4StatsHistEntry 19 }

cfprAdaptorFcIfFC4StatsHistMostRecent OBJECT-TYPE
    SYNTAX       TruthValue
    MAX-ACCESS   read-only
    STATUS       current
    DESCRIPTION
        "Cisco Firepower adaptor:FcIfFC4StatsHist:mostRecent
        managed object property"
    ::= { cfprAdaptorFcIfFC4StatsHistEntry 20 }

cfprAdaptorFcIfFC4StatsHistOutputMegabytes OBJECT-TYPE
    SYNTAX       Unsigned64
    MAX-ACCESS   read-only
    STATUS       current
    DESCRIPTION
        "Cisco Firepower adaptor:FcIfFC4StatsHist:outputMegabytes
        managed object property"
    ::= { cfprAdaptorFcIfFC4StatsHistEntry 21 }

cfprAdaptorFcIfFC4StatsHistOutputMegabytesDelta OBJECT-TYPE
    SYNTAX       Unsigned64
    MAX-ACCESS   read-only
    STATUS       current
    DESCRIPTION
        "Cisco Firepower adaptor:FcIfFC4StatsHist:outputMegabytesDelta
        managed object property"
    ::= { cfprAdaptorFcIfFC4StatsHistEntry 22 }

cfprAdaptorFcIfFC4StatsHistOutputMegabytesDeltaAvg OBJECT-TYPE
    SYNTAX       Unsigned64
    MAX-ACCESS   read-only
    STATUS       current
    DESCRIPTION
        "Cisco Firepower adaptor:FcIfFC4StatsHist:outputMegabytesDeltaAvg
        managed object property"
    ::= { cfprAdaptorFcIfFC4StatsHistEntry 23 }

cfprAdaptorFcIfFC4StatsHistOutputMegabytesDeltaMax OBJECT-TYPE
    SYNTAX       Unsigned64
    MAX-ACCESS   read-only
    STATUS       current
    DESCRIPTION
        "Cisco Firepower adaptor:FcIfFC4StatsHist:outputMegabytesDeltaMax
        managed object property"
    ::= { cfprAdaptorFcIfFC4StatsHistEntry 24 }

cfprAdaptorFcIfFC4StatsHistOutputMegabytesDeltaMin OBJECT-TYPE
    SYNTAX       Unsigned64
    MAX-ACCESS   read-only
    STATUS       current
    DESCRIPTION
        "Cisco Firepower adaptor:FcIfFC4StatsHist:outputMegabytesDeltaMin
        managed object property"
    ::= { cfprAdaptorFcIfFC4StatsHistEntry 25 }

cfprAdaptorFcIfFC4StatsHistOutputRequests OBJECT-TYPE
    SYNTAX       Unsigned64
    MAX-ACCESS   read-only
    STATUS       current
    DESCRIPTION
        "Cisco Firepower adaptor:FcIfFC4StatsHist:outputRequests
        managed object property"
    ::= { cfprAdaptorFcIfFC4StatsHistEntry 26 }

cfprAdaptorFcIfFC4StatsHistOutputRequestsDelta OBJECT-TYPE
    SYNTAX       Unsigned64
    MAX-ACCESS   read-only
    STATUS       current
    DESCRIPTION
        "Cisco Firepower adaptor:FcIfFC4StatsHist:outputRequestsDelta
        managed object property"
    ::= { cfprAdaptorFcIfFC4StatsHistEntry 27 }

cfprAdaptorFcIfFC4StatsHistOutputRequestsDeltaAvg OBJECT-TYPE
    SYNTAX       Unsigned64
    MAX-ACCESS   read-only
    STATUS       current
    DESCRIPTION
        "Cisco Firepower adaptor:FcIfFC4StatsHist:outputRequestsDeltaAvg
        managed object property"
    ::= { cfprAdaptorFcIfFC4StatsHistEntry 28 }

cfprAdaptorFcIfFC4StatsHistOutputRequestsDeltaMax OBJECT-TYPE
    SYNTAX       Unsigned64
    MAX-ACCESS   read-only
    STATUS       current
    DESCRIPTION
        "Cisco Firepower adaptor:FcIfFC4StatsHist:outputRequestsDeltaMax
        managed object property"
    ::= { cfprAdaptorFcIfFC4StatsHistEntry 29 }

cfprAdaptorFcIfFC4StatsHistOutputRequestsDeltaMin OBJECT-TYPE
    SYNTAX       Unsigned64
    MAX-ACCESS   read-only
    STATUS       current
    DESCRIPTION
        "Cisco Firepower adaptor:FcIfFC4StatsHist:outputRequestsDeltaMin
        managed object property"
    ::= { cfprAdaptorFcIfFC4StatsHistEntry 30 }

cfprAdaptorFcIfFC4StatsHistSuspect OBJECT-TYPE
    SYNTAX       TruthValue
    MAX-ACCESS   read-only
    STATUS       current
    DESCRIPTION
        "Cisco Firepower adaptor:FcIfFC4StatsHist:suspect
        managed object property"
    ::= { cfprAdaptorFcIfFC4StatsHistEntry 31 }

cfprAdaptorFcIfFC4StatsHistThresholded OBJECT-TYPE
    SYNTAX       CfprAdaptorFcIfFC4StatsHistThresholded
    MAX-ACCESS   read-only
    STATUS       current
    DESCRIPTION
        "Cisco Firepower adaptor:FcIfFC4StatsHist:thresholded
        managed object property"
    ::= { cfprAdaptorFcIfFC4StatsHistEntry 32 }

cfprAdaptorFcIfFC4StatsHistTimeCollected OBJECT-TYPE
    SYNTAX       DateAndTime
    MAX-ACCESS   read-only
    STATUS       current
    DESCRIPTION
        "Cisco Firepower adaptor:FcIfFC4StatsHist:timeCollected
        managed object property"
    ::= { cfprAdaptorFcIfFC4StatsHistEntry 33 }

cfprAdaptorFcIfFrameStatsTable OBJECT-TYPE
    SYNTAX           SEQUENCE OF CfprAdaptorFcIfFrameStatsEntry
    MAX-ACCESS       not-accessible
    STATUS           current
    DESCRIPTION
        "Cisco Firepower adaptor:FcIfFrameStats managed object table"
    ::= { cfprAdaptorObjects 42 }

cfprAdaptorFcIfFrameStatsEntry OBJECT-TYPE
    SYNTAX           CfprAdaptorFcIfFrameStatsEntry
    MAX-ACCESS       not-accessible
    STATUS           current
    DESCRIPTION
        "Entry for the cfprAdaptorFcIfFrameStatsTable table."
    INDEX { cfprAdaptorFcIfFrameStatsInstanceId }
    ::= { cfprAdaptorFcIfFrameStatsTable 1 }

CfprAdaptorFcIfFrameStatsEntry ::= SEQUENCE {
    cfprAdaptorFcIfFrameStatsInstanceId                              CfprManagedObjectId,
    cfprAdaptorFcIfFrameStatsDn                                      CfprManagedObjectDn,
    cfprAdaptorFcIfFrameStatsRn                                      SnmpAdminString,
    cfprAdaptorFcIfFrameStatsDumpedFrames                            Unsigned64,
    cfprAdaptorFcIfFrameStatsDumpedFramesDelta                       Counter64,
    cfprAdaptorFcIfFrameStatsDumpedFramesDeltaAvg                    Unsigned64,
    cfprAdaptorFcIfFrameStatsDumpedFramesDeltaMax                    Unsigned64,
    cfprAdaptorFcIfFrameStatsDumpedFramesDeltaMin                    Unsigned64,
    cfprAdaptorFcIfFrameStatsErrorFrames                             Unsigned64,
    cfprAdaptorFcIfFrameStatsErrorFramesDelta                        Counter64,
    cfprAdaptorFcIfFrameStatsErrorFramesDeltaAvg                     Unsigned64,
    cfprAdaptorFcIfFrameStatsErrorFramesDeltaMax                     Unsigned64,
    cfprAdaptorFcIfFrameStatsErrorFramesDeltaMin                     Unsigned64,
    cfprAdaptorFcIfFrameStatsIntervals                               Gauge32,
    cfprAdaptorFcIfFrameStatsRxFrames                                Unsigned64,
    cfprAdaptorFcIfFrameStatsRxFramesDelta                           Counter64,
    cfprAdaptorFcIfFrameStatsRxFramesDeltaAvg                        Unsigned64,
    cfprAdaptorFcIfFrameStatsRxFramesDeltaMax                        Unsigned64,
    cfprAdaptorFcIfFrameStatsRxFramesDeltaMin                        Unsigned64,
    cfprAdaptorFcIfFrameStatsSuspect                                 TruthValue,
    cfprAdaptorFcIfFrameStatsThresholded                             CfprAdaptorFcIfFrameStatsThresholded,
    cfprAdaptorFcIfFrameStatsTimeCollected                           DateAndTime,
    cfprAdaptorFcIfFrameStatsTxFrames                                Unsigned64,
    cfprAdaptorFcIfFrameStatsTxFramesDelta                           Counter64,
    cfprAdaptorFcIfFrameStatsTxFramesDeltaAvg                        Unsigned64,
    cfprAdaptorFcIfFrameStatsTxFramesDeltaMax                        Unsigned64,
    cfprAdaptorFcIfFrameStatsTxFramesDeltaMin                        Unsigned64,
    cfprAdaptorFcIfFrameStatsUpdate                                  Gauge32
}

cfprAdaptorFcIfFrameStatsInstanceId OBJECT-TYPE
    SYNTAX       CfprManagedObjectId
    MAX-ACCESS   not-accessible
    STATUS       current
    DESCRIPTION
        "Instance identifier of the managed object."
    ::= { cfprAdaptorFcIfFrameStatsEntry 1 }

cfprAdaptorFcIfFrameStatsDn OBJECT-TYPE
    SYNTAX       CfprManagedObjectDn
    MAX-ACCESS   read-only
    STATUS       current
    DESCRIPTION
        "Cisco Firepower adaptor:FcIfFrameStats:dn managed
        object property"
    ::= { cfprAdaptorFcIfFrameStatsEntry 2 }

cfprAdaptorFcIfFrameStatsRn OBJECT-TYPE
    SYNTAX       SnmpAdminString
    MAX-ACCESS   read-only
    STATUS       current
    DESCRIPTION
        "Cisco Firepower adaptor:FcIfFrameStats:rn managed
        object property"
    ::= { cfprAdaptorFcIfFrameStatsEntry 3 }

cfprAdaptorFcIfFrameStatsDumpedFrames OBJECT-TYPE
    SYNTAX       Unsigned64
    MAX-ACCESS   read-only
    STATUS       current
    DESCRIPTION
        "Cisco Firepower adaptor:FcIfFrameStats:dumpedFrames
        managed object property"
    ::= { cfprAdaptorFcIfFrameStatsEntry 4 }

cfprAdaptorFcIfFrameStatsDumpedFramesDelta OBJECT-TYPE
    SYNTAX       Counter64
    MAX-ACCESS   read-only
    STATUS       current
    DESCRIPTION
        "Cisco Firepower adaptor:FcIfFrameStats:dumpedFramesDelta
        managed object property"
    ::= { cfprAdaptorFcIfFrameStatsEntry 5 }

cfprAdaptorFcIfFrameStatsDumpedFramesDeltaAvg OBJECT-TYPE
    SYNTAX       Unsigned64
    MAX-ACCESS   read-only
    STATUS       current
    DESCRIPTION
        "Cisco Firepower adaptor:FcIfFrameStats:dumpedFramesDeltaAvg
        managed object property"
    ::= { cfprAdaptorFcIfFrameStatsEntry 6 }

cfprAdaptorFcIfFrameStatsDumpedFramesDeltaMax OBJECT-TYPE
    SYNTAX       Unsigned64
    MAX-ACCESS   read-only
    STATUS       current
    DESCRIPTION
        "Cisco Firepower adaptor:FcIfFrameStats:dumpedFramesDeltaMax
        managed object property"
    ::= { cfprAdaptorFcIfFrameStatsEntry 7 }

cfprAdaptorFcIfFrameStatsDumpedFramesDeltaMin OBJECT-TYPE
    SYNTAX       Unsigned64
    MAX-ACCESS   read-only
    STATUS       current
    DESCRIPTION
        "Cisco Firepower adaptor:FcIfFrameStats:dumpedFramesDeltaMin
        managed object property"
    ::= { cfprAdaptorFcIfFrameStatsEntry 8 }

cfprAdaptorFcIfFrameStatsErrorFrames OBJECT-TYPE
    SYNTAX       Unsigned64
    MAX-ACCESS   read-only
    STATUS       current
    DESCRIPTION
        "Cisco Firepower adaptor:FcIfFrameStats:errorFrames
        managed object property"
    ::= { cfprAdaptorFcIfFrameStatsEntry 9 }

cfprAdaptorFcIfFrameStatsErrorFramesDelta OBJECT-TYPE
    SYNTAX       Counter64
    MAX-ACCESS   read-only
    STATUS       current
    DESCRIPTION
        "Cisco Firepower adaptor:FcIfFrameStats:errorFramesDelta
        managed object property"
    ::= { cfprAdaptorFcIfFrameStatsEntry 10 }

cfprAdaptorFcIfFrameStatsErrorFramesDeltaAvg OBJECT-TYPE
    SYNTAX       Unsigned64
    MAX-ACCESS   read-only
    STATUS       current
    DESCRIPTION
        "Cisco Firepower adaptor:FcIfFrameStats:errorFramesDeltaAvg
        managed object property"
    ::= { cfprAdaptorFcIfFrameStatsEntry 11 }

cfprAdaptorFcIfFrameStatsErrorFramesDeltaMax OBJECT-TYPE
    SYNTAX       Unsigned64
    MAX-ACCESS   read-only
    STATUS       current
    DESCRIPTION
        "Cisco Firepower adaptor:FcIfFrameStats:errorFramesDeltaMax
        managed object property"
    ::= { cfprAdaptorFcIfFrameStatsEntry 12 }

cfprAdaptorFcIfFrameStatsErrorFramesDeltaMin OBJECT-TYPE
    SYNTAX       Unsigned64
    MAX-ACCESS   read-only
    STATUS       current
    DESCRIPTION
        "Cisco Firepower adaptor:FcIfFrameStats:errorFramesDeltaMin
        managed object property"
    ::= { cfprAdaptorFcIfFrameStatsEntry 13 }

cfprAdaptorFcIfFrameStatsIntervals OBJECT-TYPE
    SYNTAX       Gauge32
    MAX-ACCESS   read-only
    STATUS       current
    DESCRIPTION
        "Cisco Firepower adaptor:FcIfFrameStats:intervals
        managed object property"
    ::= { cfprAdaptorFcIfFrameStatsEntry 14 }

cfprAdaptorFcIfFrameStatsRxFrames OBJECT-TYPE
    SYNTAX       Unsigned64
    MAX-ACCESS   read-only
    STATUS       current
    DESCRIPTION
        "Cisco Firepower adaptor:FcIfFrameStats:rxFrames
        managed object property"
    ::= { cfprAdaptorFcIfFrameStatsEntry 15 }

cfprAdaptorFcIfFrameStatsRxFramesDelta OBJECT-TYPE
    SYNTAX       Counter64
    MAX-ACCESS   read-only
    STATUS       current
    DESCRIPTION
        "Cisco Firepower adaptor:FcIfFrameStats:rxFramesDelta
        managed object property"
    ::= { cfprAdaptorFcIfFrameStatsEntry 16 }

cfprAdaptorFcIfFrameStatsRxFramesDeltaAvg OBJECT-TYPE
    SYNTAX       Unsigned64
    MAX-ACCESS   read-only
    STATUS       current
    DESCRIPTION
        "Cisco Firepower adaptor:FcIfFrameStats:rxFramesDeltaAvg
        managed object property"
    ::= { cfprAdaptorFcIfFrameStatsEntry 17 }

cfprAdaptorFcIfFrameStatsRxFramesDeltaMax OBJECT-TYPE
    SYNTAX       Unsigned64
    MAX-ACCESS   read-only
    STATUS       current
    DESCRIPTION
        "Cisco Firepower adaptor:FcIfFrameStats:rxFramesDeltaMax
        managed object property"
    ::= { cfprAdaptorFcIfFrameStatsEntry 18 }

cfprAdaptorFcIfFrameStatsRxFramesDeltaMin OBJECT-TYPE
    SYNTAX       Unsigned64
    MAX-ACCESS   read-only
    STATUS       current
    DESCRIPTION
        "Cisco Firepower adaptor:FcIfFrameStats:rxFramesDeltaMin
        managed object property"
    ::= { cfprAdaptorFcIfFrameStatsEntry 19 }

cfprAdaptorFcIfFrameStatsSuspect OBJECT-TYPE
    SYNTAX       TruthValue
    MAX-ACCESS   read-only
    STATUS       current
    DESCRIPTION
        "Cisco Firepower adaptor:FcIfFrameStats:suspect
        managed object property"
    ::= { cfprAdaptorFcIfFrameStatsEntry 20 }

cfprAdaptorFcIfFrameStatsThresholded OBJECT-TYPE
    SYNTAX       CfprAdaptorFcIfFrameStatsThresholded
    MAX-ACCESS   read-only
    STATUS       current
    DESCRIPTION
        "Cisco Firepower adaptor:FcIfFrameStats:thresholded
        managed object property"
    ::= { cfprAdaptorFcIfFrameStatsEntry 21 }

cfprAdaptorFcIfFrameStatsTimeCollected OBJECT-TYPE
    SYNTAX       DateAndTime
    MAX-ACCESS   read-only
    STATUS       current
    DESCRIPTION
        "Cisco Firepower adaptor:FcIfFrameStats:timeCollected
        managed object property"
    ::= { cfprAdaptorFcIfFrameStatsEntry 22 }

cfprAdaptorFcIfFrameStatsTxFrames OBJECT-TYPE
    SYNTAX       Unsigned64
    MAX-ACCESS   read-only
    STATUS       current
    DESCRIPTION
        "Cisco Firepower adaptor:FcIfFrameStats:txFrames
        managed object property"
    ::= { cfprAdaptorFcIfFrameStatsEntry 23 }

cfprAdaptorFcIfFrameStatsTxFramesDelta OBJECT-TYPE
    SYNTAX       Counter64
    MAX-ACCESS   read-only
    STATUS       current
    DESCRIPTION
        "Cisco Firepower adaptor:FcIfFrameStats:txFramesDelta
        managed object property"
    ::= { cfprAdaptorFcIfFrameStatsEntry 24 }

cfprAdaptorFcIfFrameStatsTxFramesDeltaAvg OBJECT-TYPE
    SYNTAX       Unsigned64
    MAX-ACCESS   read-only
    STATUS       current
    DESCRIPTION
        "Cisco Firepower adaptor:FcIfFrameStats:txFramesDeltaAvg
        managed object property"
    ::= { cfprAdaptorFcIfFrameStatsEntry 25 }

cfprAdaptorFcIfFrameStatsTxFramesDeltaMax OBJECT-TYPE
    SYNTAX       Unsigned64
    MAX-ACCESS   read-only
    STATUS       current
    DESCRIPTION
        "Cisco Firepower adaptor:FcIfFrameStats:txFramesDeltaMax
        managed object property"
    ::= { cfprAdaptorFcIfFrameStatsEntry 26 }

cfprAdaptorFcIfFrameStatsTxFramesDeltaMin OBJECT-TYPE
    SYNTAX       Unsigned64
    MAX-ACCESS   read-only
    STATUS       current
    DESCRIPTION
        "Cisco Firepower adaptor:FcIfFrameStats:txFramesDeltaMin
        managed object property"
    ::= { cfprAdaptorFcIfFrameStatsEntry 27 }

cfprAdaptorFcIfFrameStatsUpdate OBJECT-TYPE
    SYNTAX       Gauge32
    MAX-ACCESS   read-only
    STATUS       current
    DESCRIPTION
        "Cisco Firepower adaptor:FcIfFrameStats:update
        managed object property"
    ::= { cfprAdaptorFcIfFrameStatsEntry 28 }

cfprAdaptorFcIfFrameStatsHistTable OBJECT-TYPE
    SYNTAX           SEQUENCE OF CfprAdaptorFcIfFrameStatsHistEntry
    MAX-ACCESS       not-accessible
    STATUS           current
    DESCRIPTION
        "Cisco Firepower adaptor:FcIfFrameStatsHist managed object table"
    ::= { cfprAdaptorObjects 43 }

cfprAdaptorFcIfFrameStatsHistEntry OBJECT-TYPE
    SYNTAX           CfprAdaptorFcIfFrameStatsHistEntry
    MAX-ACCESS       not-accessible
    STATUS           current
    DESCRIPTION
        "Entry for the cfprAdaptorFcIfFrameStatsHistTable table."
    INDEX { cfprAdaptorFcIfFrameStatsHistInstanceId }
    ::= { cfprAdaptorFcIfFrameStatsHistTable 1 }

CfprAdaptorFcIfFrameStatsHistEntry ::= SEQUENCE {
    cfprAdaptorFcIfFrameStatsHistInstanceId                          CfprManagedObjectId,
    cfprAdaptorFcIfFrameStatsHistDn                                  CfprManagedObjectDn,
    cfprAdaptorFcIfFrameStatsHistRn                                  SnmpAdminString,
    cfprAdaptorFcIfFrameStatsHistDumpedFrames                        Unsigned64,
    cfprAdaptorFcIfFrameStatsHistDumpedFramesDelta                   Unsigned64,
    cfprAdaptorFcIfFrameStatsHistDumpedFramesDeltaAvg                Unsigned64,
    cfprAdaptorFcIfFrameStatsHistDumpedFramesDeltaMax                Unsigned64,
    cfprAdaptorFcIfFrameStatsHistDumpedFramesDeltaMin                Unsigned64,
    cfprAdaptorFcIfFrameStatsHistErrorFrames                         Unsigned64,
    cfprAdaptorFcIfFrameStatsHistErrorFramesDelta                    Unsigned64,
    cfprAdaptorFcIfFrameStatsHistErrorFramesDeltaAvg                 Unsigned64,
    cfprAdaptorFcIfFrameStatsHistErrorFramesDeltaMax                 Unsigned64,
    cfprAdaptorFcIfFrameStatsHistErrorFramesDeltaMin                 Unsigned64,
    cfprAdaptorFcIfFrameStatsHistId                                  Unsigned64,
    cfprAdaptorFcIfFrameStatsHistMostRecent                          TruthValue,
    cfprAdaptorFcIfFrameStatsHistRxFrames                            Unsigned64,
    cfprAdaptorFcIfFrameStatsHistRxFramesDelta                       Unsigned64,
    cfprAdaptorFcIfFrameStatsHistRxFramesDeltaAvg                    Unsigned64,
    cfprAdaptorFcIfFrameStatsHistRxFramesDeltaMax                    Unsigned64,
    cfprAdaptorFcIfFrameStatsHistRxFramesDeltaMin                    Unsigned64,
    cfprAdaptorFcIfFrameStatsHistSuspect                             TruthValue,
    cfprAdaptorFcIfFrameStatsHistThresholded                         CfprAdaptorFcIfFrameStatsHistThresholded,
    cfprAdaptorFcIfFrameStatsHistTimeCollected                       DateAndTime,
    cfprAdaptorFcIfFrameStatsHistTxFrames                            Unsigned64,
    cfprAdaptorFcIfFrameStatsHistTxFramesDelta                       Unsigned64,
    cfprAdaptorFcIfFrameStatsHistTxFramesDeltaAvg                    Unsigned64,
    cfprAdaptorFcIfFrameStatsHistTxFramesDeltaMax                    Unsigned64,
    cfprAdaptorFcIfFrameStatsHistTxFramesDeltaMin                    Unsigned64
}

cfprAdaptorFcIfFrameStatsHistInstanceId OBJECT-TYPE
    SYNTAX       CfprManagedObjectId
    MAX-ACCESS   not-accessible
    STATUS       current
    DESCRIPTION
        "Instance identifier of the managed object."
    ::= { cfprAdaptorFcIfFrameStatsHistEntry 1 }

cfprAdaptorFcIfFrameStatsHistDn OBJECT-TYPE
    SYNTAX       CfprManagedObjectDn
    MAX-ACCESS   read-only
    STATUS       current
    DESCRIPTION
        "Cisco Firepower adaptor:FcIfFrameStatsHist:dn
        managed object property"
    ::= { cfprAdaptorFcIfFrameStatsHistEntry 2 }

cfprAdaptorFcIfFrameStatsHistRn OBJECT-TYPE
    SYNTAX       SnmpAdminString
    MAX-ACCESS   read-only
    STATUS       current
    DESCRIPTION
        "Cisco Firepower adaptor:FcIfFrameStatsHist:rn
        managed object property"
    ::= { cfprAdaptorFcIfFrameStatsHistEntry 3 }

cfprAdaptorFcIfFrameStatsHistDumpedFrames OBJECT-TYPE
    SYNTAX       Unsigned64
    MAX-ACCESS   read-only
    STATUS       current
    DESCRIPTION
        "Cisco Firepower adaptor:FcIfFrameStatsHist:dumpedFrames
        managed object property"
    ::= { cfprAdaptorFcIfFrameStatsHistEntry 4 }

cfprAdaptorFcIfFrameStatsHistDumpedFramesDelta OBJECT-TYPE
    SYNTAX       Unsigned64
    MAX-ACCESS   read-only
    STATUS       current
    DESCRIPTION
        "Cisco Firepower adaptor:FcIfFrameStatsHist:dumpedFramesDelta
        managed object property"
    ::= { cfprAdaptorFcIfFrameStatsHistEntry 5 }

cfprAdaptorFcIfFrameStatsHistDumpedFramesDeltaAvg OBJECT-TYPE
    SYNTAX       Unsigned64
    MAX-ACCESS   read-only
    STATUS       current
    DESCRIPTION
        "Cisco Firepower adaptor:FcIfFrameStatsHist:dumpedFramesDeltaAvg
        managed object property"
    ::= { cfprAdaptorFcIfFrameStatsHistEntry 6 }

cfprAdaptorFcIfFrameStatsHistDumpedFramesDeltaMax OBJECT-TYPE
    SYNTAX       Unsigned64
    MAX-ACCESS   read-only
    STATUS       current
    DESCRIPTION
        "Cisco Firepower adaptor:FcIfFrameStatsHist:dumpedFramesDeltaMax
        managed object property"
    ::= { cfprAdaptorFcIfFrameStatsHistEntry 7 }

cfprAdaptorFcIfFrameStatsHistDumpedFramesDeltaMin OBJECT-TYPE
    SYNTAX       Unsigned64
    MAX-ACCESS   read-only
    STATUS       current
    DESCRIPTION
        "Cisco Firepower adaptor:FcIfFrameStatsHist:dumpedFramesDeltaMin
        managed object property"
    ::= { cfprAdaptorFcIfFrameStatsHistEntry 8 }

cfprAdaptorFcIfFrameStatsHistErrorFrames OBJECT-TYPE
    SYNTAX       Unsigned64
    MAX-ACCESS   read-only
    STATUS       current
    DESCRIPTION
        "Cisco Firepower adaptor:FcIfFrameStatsHist:errorFrames
        managed object property"
    ::= { cfprAdaptorFcIfFrameStatsHistEntry 9 }

cfprAdaptorFcIfFrameStatsHistErrorFramesDelta OBJECT-TYPE
    SYNTAX       Unsigned64
    MAX-ACCESS   read-only
    STATUS       current
    DESCRIPTION
        "Cisco Firepower adaptor:FcIfFrameStatsHist:errorFramesDelta
        managed object property"
    ::= { cfprAdaptorFcIfFrameStatsHistEntry 10 }

cfprAdaptorFcIfFrameStatsHistErrorFramesDeltaAvg OBJECT-TYPE
    SYNTAX       Unsigned64
    MAX-ACCESS   read-only
    STATUS       current
    DESCRIPTION
        "Cisco Firepower adaptor:FcIfFrameStatsHist:errorFramesDeltaAvg
        managed object property"
    ::= { cfprAdaptorFcIfFrameStatsHistEntry 11 }

cfprAdaptorFcIfFrameStatsHistErrorFramesDeltaMax OBJECT-TYPE
    SYNTAX       Unsigned64
    MAX-ACCESS   read-only
    STATUS       current
    DESCRIPTION
        "Cisco Firepower adaptor:FcIfFrameStatsHist:errorFramesDeltaMax
        managed object property"
    ::= { cfprAdaptorFcIfFrameStatsHistEntry 12 }

cfprAdaptorFcIfFrameStatsHistErrorFramesDeltaMin OBJECT-TYPE
    SYNTAX       Unsigned64
    MAX-ACCESS   read-only
    STATUS       current
    DESCRIPTION
        "Cisco Firepower adaptor:FcIfFrameStatsHist:errorFramesDeltaMin
        managed object property"
    ::= { cfprAdaptorFcIfFrameStatsHistEntry 13 }

cfprAdaptorFcIfFrameStatsHistId OBJECT-TYPE
    SYNTAX       Unsigned64
    MAX-ACCESS   read-only
    STATUS       current
    DESCRIPTION
        "Cisco Firepower adaptor:FcIfFrameStatsHist:id
        managed object property"
    ::= { cfprAdaptorFcIfFrameStatsHistEntry 14 }

cfprAdaptorFcIfFrameStatsHistMostRecent OBJECT-TYPE
    SYNTAX       TruthValue
    MAX-ACCESS   read-only
    STATUS       current
    DESCRIPTION
        "Cisco Firepower adaptor:FcIfFrameStatsHist:mostRecent
        managed object property"
    ::= { cfprAdaptorFcIfFrameStatsHistEntry 15 }

cfprAdaptorFcIfFrameStatsHistRxFrames OBJECT-TYPE
    SYNTAX       Unsigned64
    MAX-ACCESS   read-only
    STATUS       current
    DESCRIPTION
        "Cisco Firepower adaptor:FcIfFrameStatsHist:rxFrames
        managed object property"
    ::= { cfprAdaptorFcIfFrameStatsHistEntry 16 }

cfprAdaptorFcIfFrameStatsHistRxFramesDelta OBJECT-TYPE
    SYNTAX       Unsigned64
    MAX-ACCESS   read-only
    STATUS       current
    DESCRIPTION
        "Cisco Firepower adaptor:FcIfFrameStatsHist:rxFramesDelta
        managed object property"
    ::= { cfprAdaptorFcIfFrameStatsHistEntry 17 }

cfprAdaptorFcIfFrameStatsHistRxFramesDeltaAvg OBJECT-TYPE
    SYNTAX       Unsigned64
    MAX-ACCESS   read-only
    STATUS       current
    DESCRIPTION
        "Cisco Firepower adaptor:FcIfFrameStatsHist:rxFramesDeltaAvg
        managed object property"
    ::= { cfprAdaptorFcIfFrameStatsHistEntry 18 }

cfprAdaptorFcIfFrameStatsHistRxFramesDeltaMax OBJECT-TYPE
    SYNTAX       Unsigned64
    MAX-ACCESS   read-only
    STATUS       current
    DESCRIPTION
        "Cisco Firepower adaptor:FcIfFrameStatsHist:rxFramesDeltaMax
        managed object property"
    ::= { cfprAdaptorFcIfFrameStatsHistEntry 19 }

cfprAdaptorFcIfFrameStatsHistRxFramesDeltaMin OBJECT-TYPE
    SYNTAX       Unsigned64
    MAX-ACCESS   read-only
    STATUS       current
    DESCRIPTION
        "Cisco Firepower adaptor:FcIfFrameStatsHist:rxFramesDeltaMin
        managed object property"
    ::= { cfprAdaptorFcIfFrameStatsHistEntry 20 }

cfprAdaptorFcIfFrameStatsHistSuspect OBJECT-TYPE
    SYNTAX       TruthValue
    MAX-ACCESS   read-only
    STATUS       current
    DESCRIPTION
        "Cisco Firepower adaptor:FcIfFrameStatsHist:suspect
        managed object property"
    ::= { cfprAdaptorFcIfFrameStatsHistEntry 21 }

cfprAdaptorFcIfFrameStatsHistThresholded OBJECT-TYPE
    SYNTAX       CfprAdaptorFcIfFrameStatsHistThresholded
    MAX-ACCESS   read-only
    STATUS       current
    DESCRIPTION
        "Cisco Firepower adaptor:FcIfFrameStatsHist:thresholded
        managed object property"
    ::= { cfprAdaptorFcIfFrameStatsHistEntry 22 }

cfprAdaptorFcIfFrameStatsHistTimeCollected OBJECT-TYPE
    SYNTAX       DateAndTime
    MAX-ACCESS   read-only
    STATUS       current
    DESCRIPTION
        "Cisco Firepower adaptor:FcIfFrameStatsHist:timeCollected
        managed object property"
    ::= { cfprAdaptorFcIfFrameStatsHistEntry 23 }

cfprAdaptorFcIfFrameStatsHistTxFrames OBJECT-TYPE
    SYNTAX       Unsigned64
    MAX-ACCESS   read-only
    STATUS       current
    DESCRIPTION
        "Cisco Firepower adaptor:FcIfFrameStatsHist:txFrames
        managed object property"
    ::= { cfprAdaptorFcIfFrameStatsHistEntry 24 }

cfprAdaptorFcIfFrameStatsHistTxFramesDelta OBJECT-TYPE
    SYNTAX       Unsigned64
    MAX-ACCESS   read-only
    STATUS       current
    DESCRIPTION
        "Cisco Firepower adaptor:FcIfFrameStatsHist:txFramesDelta
        managed object property"
    ::= { cfprAdaptorFcIfFrameStatsHistEntry 25 }

cfprAdaptorFcIfFrameStatsHistTxFramesDeltaAvg OBJECT-TYPE
    SYNTAX       Unsigned64
    MAX-ACCESS   read-only
    STATUS       current
    DESCRIPTION
        "Cisco Firepower adaptor:FcIfFrameStatsHist:txFramesDeltaAvg
        managed object property"
    ::= { cfprAdaptorFcIfFrameStatsHistEntry 26 }

cfprAdaptorFcIfFrameStatsHistTxFramesDeltaMax OBJECT-TYPE
    SYNTAX       Unsigned64
    MAX-ACCESS   read-only
    STATUS       current
    DESCRIPTION
        "Cisco Firepower adaptor:FcIfFrameStatsHist:txFramesDeltaMax
        managed object property"
    ::= { cfprAdaptorFcIfFrameStatsHistEntry 27 }

cfprAdaptorFcIfFrameStatsHistTxFramesDeltaMin OBJECT-TYPE
    SYNTAX       Unsigned64
    MAX-ACCESS   read-only
    STATUS       current
    DESCRIPTION
        "Cisco Firepower adaptor:FcIfFrameStatsHist:txFramesDeltaMin
        managed object property"
    ::= { cfprAdaptorFcIfFrameStatsHistEntry 28 }

cfprAdaptorFcInterruptProfileTable OBJECT-TYPE
    SYNTAX           SEQUENCE OF CfprAdaptorFcInterruptProfileEntry
    MAX-ACCESS       not-accessible
    STATUS           current
    DESCRIPTION
        "Cisco Firepower adaptor:FcInterruptProfile managed object table"
    ::= { cfprAdaptorObjects 44 }

cfprAdaptorFcInterruptProfileEntry OBJECT-TYPE
    SYNTAX           CfprAdaptorFcInterruptProfileEntry
    MAX-ACCESS       not-accessible
    STATUS           current
    DESCRIPTION
        "Entry for the cfprAdaptorFcInterruptProfileTable table."
    INDEX { cfprAdaptorFcInterruptProfileInstanceId }
    ::= { cfprAdaptorFcInterruptProfileTable 1 }

CfprAdaptorFcInterruptProfileEntry ::= SEQUENCE {
    cfprAdaptorFcInterruptProfileInstanceId                          CfprManagedObjectId,
    cfprAdaptorFcInterruptProfileDn                                  CfprManagedObjectDn,
    cfprAdaptorFcInterruptProfileRn                                  SnmpAdminString,
    cfprAdaptorFcInterruptProfileMode                                CfprAdaptorInterruptMode
}

cfprAdaptorFcInterruptProfileInstanceId OBJECT-TYPE
    SYNTAX       CfprManagedObjectId
    MAX-ACCESS   not-accessible
    STATUS       current
    DESCRIPTION
        "Instance identifier of the managed object."
    ::= { cfprAdaptorFcInterruptProfileEntry 1 }

cfprAdaptorFcInterruptProfileDn OBJECT-TYPE
    SYNTAX       CfprManagedObjectDn
    MAX-ACCESS   read-only
    STATUS       current
    DESCRIPTION
        "Cisco Firepower adaptor:FcInterruptProfile:dn
        managed object property"
    ::= { cfprAdaptorFcInterruptProfileEntry 2 }

cfprAdaptorFcInterruptProfileRn OBJECT-TYPE
    SYNTAX       SnmpAdminString
    MAX-ACCESS   read-only
    STATUS       current
    DESCRIPTION
        "Cisco Firepower adaptor:FcInterruptProfile:rn
        managed object property"
    ::= { cfprAdaptorFcInterruptProfileEntry 3 }

cfprAdaptorFcInterruptProfileMode OBJECT-TYPE
    SYNTAX       CfprAdaptorInterruptMode
    MAX-ACCESS   read-only
    STATUS       current
    DESCRIPTION
        "Cisco Firepower adaptor:FcInterruptProfile:mode
        managed object property"
    ::= { cfprAdaptorFcInterruptProfileEntry 4 }

cfprAdaptorFcOEIfTable OBJECT-TYPE
    SYNTAX           SEQUENCE OF CfprAdaptorFcOEIfEntry
    MAX-ACCESS       not-accessible
    STATUS           current
    DESCRIPTION
        "Cisco Firepower adaptor:FcOEIf managed object table"
    ::= { cfprAdaptorObjects 45 }

cfprAdaptorFcOEIfEntry OBJECT-TYPE
    SYNTAX           CfprAdaptorFcOEIfEntry
    MAX-ACCESS       not-accessible
    STATUS           current
    DESCRIPTION
        "Entry for the cfprAdaptorFcOEIfTable table."
    INDEX { cfprAdaptorFcOEIfInstanceId }
    ::= { cfprAdaptorFcOEIfTable 1 }

CfprAdaptorFcOEIfEntry ::= SEQUENCE {
    cfprAdaptorFcOEIfInstanceId                                      CfprManagedObjectId,
    cfprAdaptorFcOEIfDn                                              CfprManagedObjectDn,
    cfprAdaptorFcOEIfRn                                              SnmpAdminString,
    cfprAdaptorFcOEIfEpDn                                            SnmpAdminString,
    cfprAdaptorFcOEIfFcoeVlan                                        Gauge32,
    cfprAdaptorFcOEIfId                                              Gauge32,
    cfprAdaptorFcOEIfIfRole                                          CfprFabricVnetEpIfRole,
    cfprAdaptorFcOEIfIfType                                          CfprNetworkVnetEpIfType,
    cfprAdaptorFcOEIfLc                                              CfprFsmLifecycle,
    cfprAdaptorFcOEIfLocale                                          CfprFabricVnetEpLocale,
    cfprAdaptorFcOEIfMac                                             MacAddress,
    cfprAdaptorFcOEIfName                                            SnmpAdminString,
    cfprAdaptorFcOEIfOperState                                       CfprFabricVsanOperState,
    cfprAdaptorFcOEIfPeerDn                                          SnmpAdminString,
    cfprAdaptorFcOEIfPolicyOwner                                     CfprFabricVnetEpPolicyOwner,
    cfprAdaptorFcOEIfSwitchId                                        CfprNetworkSwitchId,
    cfprAdaptorFcOEIfTransport                                       CfprFabricAVsanTransport,
    cfprAdaptorFcOEIfType                                            CfprFabricAVsanType,
    cfprAdaptorFcOEIfZoningState                                     CfprFabricZoningState
}

cfprAdaptorFcOEIfInstanceId OBJECT-TYPE
    SYNTAX       CfprManagedObjectId
    MAX-ACCESS   not-accessible
    STATUS       current
    DESCRIPTION
        "Instance identifier of the managed object."
    ::= { cfprAdaptorFcOEIfEntry 1 }

cfprAdaptorFcOEIfDn OBJECT-TYPE
    SYNTAX       CfprManagedObjectDn
    MAX-ACCESS   read-only
    STATUS       current
    DESCRIPTION
        "Cisco Firepower adaptor:FcOEIf:dn managed object property"
    ::= { cfprAdaptorFcOEIfEntry 2 }

cfprAdaptorFcOEIfRn OBJECT-TYPE
    SYNTAX       SnmpAdminString
    MAX-ACCESS   read-only
    STATUS       current
    DESCRIPTION
        "Cisco Firepower adaptor:FcOEIf:rn managed object property"
    ::= { cfprAdaptorFcOEIfEntry 3 }

cfprAdaptorFcOEIfEpDn OBJECT-TYPE
    SYNTAX       SnmpAdminString
    MAX-ACCESS   read-only
    STATUS       current
    DESCRIPTION
        "Cisco Firepower adaptor:FcOEIf:epDn managed object property"
    ::= { cfprAdaptorFcOEIfEntry 4 }

cfprAdaptorFcOEIfFcoeVlan OBJECT-TYPE
    SYNTAX       Gauge32
    MAX-ACCESS   read-only
    STATUS       current
    DESCRIPTION
        "Cisco Firepower adaptor:FcOEIf:fcoeVlan managed object property"
    ::= { cfprAdaptorFcOEIfEntry 5 }

cfprAdaptorFcOEIfId OBJECT-TYPE
    SYNTAX       Gauge32
    MAX-ACCESS   read-only
    STATUS       current
    DESCRIPTION
        "Cisco Firepower adaptor:FcOEIf:id managed object property"
    ::= { cfprAdaptorFcOEIfEntry 6 }

cfprAdaptorFcOEIfIfRole OBJECT-TYPE
    SYNTAX       CfprFabricVnetEpIfRole
    MAX-ACCESS   read-only
    STATUS       current
    DESCRIPTION
        "Cisco Firepower adaptor:FcOEIf:ifRole managed object property"
    ::= { cfprAdaptorFcOEIfEntry 7 }

cfprAdaptorFcOEIfIfType OBJECT-TYPE
    SYNTAX       CfprNetworkVnetEpIfType
    MAX-ACCESS   read-only
    STATUS       current
    DESCRIPTION
        "Cisco Firepower adaptor:FcOEIf:ifType managed object property"
    ::= { cfprAdaptorFcOEIfEntry 8 }

cfprAdaptorFcOEIfLc OBJECT-TYPE
    SYNTAX       CfprFsmLifecycle
    MAX-ACCESS   read-only
    STATUS       current
    DESCRIPTION
        "Cisco Firepower adaptor:FcOEIf:lc managed object property"
    ::= { cfprAdaptorFcOEIfEntry 9 }

cfprAdaptorFcOEIfLocale OBJECT-TYPE
    SYNTAX       CfprFabricVnetEpLocale
    MAX-ACCESS   read-only
    STATUS       current
    DESCRIPTION
        "Cisco Firepower adaptor:FcOEIf:locale managed object property"
    ::= { cfprAdaptorFcOEIfEntry 10 }

cfprAdaptorFcOEIfMac OBJECT-TYPE
    SYNTAX       MacAddress
    MAX-ACCESS   read-only
    STATUS       current
    DESCRIPTION
        "Cisco Firepower adaptor:FcOEIf:mac managed object property"
    ::= { cfprAdaptorFcOEIfEntry 11 }

cfprAdaptorFcOEIfName OBJECT-TYPE
    SYNTAX       SnmpAdminString
    MAX-ACCESS   read-only
    STATUS       current
    DESCRIPTION
        "Cisco Firepower adaptor:FcOEIf:name managed object property"
    ::= { cfprAdaptorFcOEIfEntry 12 }

cfprAdaptorFcOEIfOperState OBJECT-TYPE
    SYNTAX       CfprFabricVsanOperState
    MAX-ACCESS   read-only
    STATUS       current
    DESCRIPTION
        "Cisco Firepower adaptor:FcOEIf:operState managed object property"
    ::= { cfprAdaptorFcOEIfEntry 13 }

cfprAdaptorFcOEIfPeerDn OBJECT-TYPE
    SYNTAX       SnmpAdminString
    MAX-ACCESS   read-only
    STATUS       current
    DESCRIPTION
        "Cisco Firepower adaptor:FcOEIf:peerDn managed object property"
    ::= { cfprAdaptorFcOEIfEntry 14 }

cfprAdaptorFcOEIfPolicyOwner OBJECT-TYPE
    SYNTAX       CfprFabricVnetEpPolicyOwner
    MAX-ACCESS   read-only
    STATUS       current
    DESCRIPTION
        "Cisco Firepower adaptor:FcOEIf:policyOwner managed
        object property"
    ::= { cfprAdaptorFcOEIfEntry 15 }

cfprAdaptorFcOEIfSwitchId OBJECT-TYPE
    SYNTAX       CfprNetworkSwitchId
    MAX-ACCESS   read-only
    STATUS       current
    DESCRIPTION
        "Cisco Firepower adaptor:FcOEIf:switchId managed object property"
    ::= { cfprAdaptorFcOEIfEntry 16 }

cfprAdaptorFcOEIfTransport OBJECT-TYPE
    SYNTAX       CfprFabricAVsanTransport
    MAX-ACCESS   read-only
    STATUS       current
    DESCRIPTION
        "Cisco Firepower adaptor:FcOEIf:transport managed object property"
    ::= { cfprAdaptorFcOEIfEntry 17 }

cfprAdaptorFcOEIfType OBJECT-TYPE
    SYNTAX       CfprFabricAVsanType
    MAX-ACCESS   read-only
    STATUS       current
    DESCRIPTION
        "Cisco Firepower adaptor:FcOEIf:type managed object property"
    ::= { cfprAdaptorFcOEIfEntry 18 }

cfprAdaptorFcOEIfZoningState OBJECT-TYPE
    SYNTAX       CfprFabricZoningState
    MAX-ACCESS   read-only
    STATUS       current
    DESCRIPTION
        "Cisco Firepower adaptor:FcOEIf:zoningState managed
        object property"
    ::= { cfprAdaptorFcOEIfEntry 19 }

cfprAdaptorFcPortFLogiProfileTable OBJECT-TYPE
    SYNTAX           SEQUENCE OF CfprAdaptorFcPortFLogiProfileEntry
    MAX-ACCESS       not-accessible
    STATUS           current
    DESCRIPTION
        "Cisco Firepower adaptor:FcPortFLogiProfile managed object table"
    ::= { cfprAdaptorObjects 46 }

cfprAdaptorFcPortFLogiProfileEntry OBJECT-TYPE
    SYNTAX           CfprAdaptorFcPortFLogiProfileEntry
    MAX-ACCESS       not-accessible
    STATUS           current
    DESCRIPTION
        "Entry for the cfprAdaptorFcPortFLogiProfileTable table."
    INDEX { cfprAdaptorFcPortFLogiProfileInstanceId }
    ::= { cfprAdaptorFcPortFLogiProfileTable 1 }

CfprAdaptorFcPortFLogiProfileEntry ::= SEQUENCE {
    cfprAdaptorFcPortFLogiProfileInstanceId                          CfprManagedObjectId,
    cfprAdaptorFcPortFLogiProfileDn                                  CfprManagedObjectDn,
    cfprAdaptorFcPortFLogiProfileRn                                  SnmpAdminString,
    cfprAdaptorFcPortFLogiProfileRetries                             Gauge32,
    cfprAdaptorFcPortFLogiProfileTimeout                             Gauge32
}

cfprAdaptorFcPortFLogiProfileInstanceId OBJECT-TYPE
    SYNTAX       CfprManagedObjectId
    MAX-ACCESS   not-accessible
    STATUS       current
    DESCRIPTION
        "Instance identifier of the managed object."
    ::= { cfprAdaptorFcPortFLogiProfileEntry 1 }

cfprAdaptorFcPortFLogiProfileDn OBJECT-TYPE
    SYNTAX       CfprManagedObjectDn
    MAX-ACCESS   read-only
    STATUS       current
    DESCRIPTION
        "Cisco Firepower adaptor:FcPortFLogiProfile:dn
        managed object property"
    ::= { cfprAdaptorFcPortFLogiProfileEntry 2 }

cfprAdaptorFcPortFLogiProfileRn OBJECT-TYPE
    SYNTAX       SnmpAdminString
    MAX-ACCESS   read-only
    STATUS       current
    DESCRIPTION
        "Cisco Firepower adaptor:FcPortFLogiProfile:rn
        managed object property"
    ::= { cfprAdaptorFcPortFLogiProfileEntry 3 }

cfprAdaptorFcPortFLogiProfileRetries OBJECT-TYPE
    SYNTAX       Gauge32
    MAX-ACCESS   read-only
    STATUS       current
    DESCRIPTION
        "Cisco Firepower adaptor:FcPortFLogiProfile:retries
        managed object property"
    ::= { cfprAdaptorFcPortFLogiProfileEntry 4 }

cfprAdaptorFcPortFLogiProfileTimeout OBJECT-TYPE
    SYNTAX       Gauge32
    MAX-ACCESS   read-only
    STATUS       current
    DESCRIPTION
        "Cisco Firepower adaptor:FcPortFLogiProfile:timeout
        managed object property"
    ::= { cfprAdaptorFcPortFLogiProfileEntry 5 }

cfprAdaptorFcPortPLogiProfileTable OBJECT-TYPE
    SYNTAX           SEQUENCE OF CfprAdaptorFcPortPLogiProfileEntry
    MAX-ACCESS       not-accessible
    STATUS           current
    DESCRIPTION
        "Cisco Firepower adaptor:FcPortPLogiProfile managed object table"
    ::= { cfprAdaptorObjects 47 }

cfprAdaptorFcPortPLogiProfileEntry OBJECT-TYPE
    SYNTAX           CfprAdaptorFcPortPLogiProfileEntry
    MAX-ACCESS       not-accessible
    STATUS           current
    DESCRIPTION
        "Entry for the cfprAdaptorFcPortPLogiProfileTable table."
    INDEX { cfprAdaptorFcPortPLogiProfileInstanceId }
    ::= { cfprAdaptorFcPortPLogiProfileTable 1 }

CfprAdaptorFcPortPLogiProfileEntry ::= SEQUENCE {
    cfprAdaptorFcPortPLogiProfileInstanceId                          CfprManagedObjectId,
    cfprAdaptorFcPortPLogiProfileDn                                  CfprManagedObjectDn,
    cfprAdaptorFcPortPLogiProfileRn                                  SnmpAdminString,
    cfprAdaptorFcPortPLogiProfileRetries                             Gauge32,
    cfprAdaptorFcPortPLogiProfileTimeout                             Gauge32
}

cfprAdaptorFcPortPLogiProfileInstanceId OBJECT-TYPE
    SYNTAX       CfprManagedObjectId
    MAX-ACCESS   not-accessible
    STATUS       current
    DESCRIPTION
        "Instance identifier of the managed object."
    ::= { cfprAdaptorFcPortPLogiProfileEntry 1 }

cfprAdaptorFcPortPLogiProfileDn OBJECT-TYPE
    SYNTAX       CfprManagedObjectDn
    MAX-ACCESS   read-only
    STATUS       current
    DESCRIPTION
        "Cisco Firepower adaptor:FcPortPLogiProfile:dn
        managed object property"
    ::= { cfprAdaptorFcPortPLogiProfileEntry 2 }

cfprAdaptorFcPortPLogiProfileRn OBJECT-TYPE
    SYNTAX       SnmpAdminString
    MAX-ACCESS   read-only
    STATUS       current
    DESCRIPTION
        "Cisco Firepower adaptor:FcPortPLogiProfile:rn
        managed object property"
    ::= { cfprAdaptorFcPortPLogiProfileEntry 3 }

cfprAdaptorFcPortPLogiProfileRetries OBJECT-TYPE
    SYNTAX       Gauge32
    MAX-ACCESS   read-only
    STATUS       current
    DESCRIPTION
        "Cisco Firepower adaptor:FcPortPLogiProfile:retries
        managed object property"
    ::= { cfprAdaptorFcPortPLogiProfileEntry 4 }

cfprAdaptorFcPortPLogiProfileTimeout OBJECT-TYPE
    SYNTAX       Gauge32
    MAX-ACCESS   read-only
    STATUS       current
    DESCRIPTION
        "Cisco Firepower adaptor:FcPortPLogiProfile:timeout
        managed object property"
    ::= { cfprAdaptorFcPortPLogiProfileEntry 5 }

cfprAdaptorFcPortProfileTable OBJECT-TYPE
    SYNTAX           SEQUENCE OF CfprAdaptorFcPortProfileEntry
    MAX-ACCESS       not-accessible
    STATUS           current
    DESCRIPTION
        "Cisco Firepower adaptor:FcPortProfile managed object table"
    ::= { cfprAdaptorObjects 48 }

cfprAdaptorFcPortProfileEntry OBJECT-TYPE
    SYNTAX           CfprAdaptorFcPortProfileEntry
    MAX-ACCESS       not-accessible
    STATUS           current
    DESCRIPTION
        "Entry for the cfprAdaptorFcPortProfileTable table."
    INDEX { cfprAdaptorFcPortProfileInstanceId }
    ::= { cfprAdaptorFcPortProfileTable 1 }

CfprAdaptorFcPortProfileEntry ::= SEQUENCE {
    cfprAdaptorFcPortProfileInstanceId                               CfprManagedObjectId,
    cfprAdaptorFcPortProfileDn                                       CfprManagedObjectDn,
    cfprAdaptorFcPortProfileRn                                       SnmpAdminString,
    cfprAdaptorFcPortProfileIoThrottleCount                          Gauge32,
    cfprAdaptorFcPortProfileLunsPerTarget                            Gauge32
}

cfprAdaptorFcPortProfileInstanceId OBJECT-TYPE
    SYNTAX       CfprManagedObjectId
    MAX-ACCESS   not-accessible
    STATUS       current
    DESCRIPTION
        "Instance identifier of the managed object."
    ::= { cfprAdaptorFcPortProfileEntry 1 }

cfprAdaptorFcPortProfileDn OBJECT-TYPE
    SYNTAX       CfprManagedObjectDn
    MAX-ACCESS   read-only
    STATUS       current
    DESCRIPTION
        "Cisco Firepower adaptor:FcPortProfile:dn managed object property"
    ::= { cfprAdaptorFcPortProfileEntry 2 }

cfprAdaptorFcPortProfileRn OBJECT-TYPE
    SYNTAX       SnmpAdminString
    MAX-ACCESS   read-only
    STATUS       current
    DESCRIPTION
        "Cisco Firepower adaptor:FcPortProfile:rn managed object property"
    ::= { cfprAdaptorFcPortProfileEntry 3 }

cfprAdaptorFcPortProfileIoThrottleCount OBJECT-TYPE
    SYNTAX       Gauge32
    MAX-ACCESS   read-only
    STATUS       current
    DESCRIPTION
        "Cisco Firepower adaptor:FcPortProfile:ioThrottleCount
        managed object property"
    ::= { cfprAdaptorFcPortProfileEntry 4 }

cfprAdaptorFcPortProfileLunsPerTarget OBJECT-TYPE
    SYNTAX       Gauge32
    MAX-ACCESS   read-only
    STATUS       current
    DESCRIPTION
        "Cisco Firepower adaptor:FcPortProfile:lunsPerTarget
        managed object property"
    ::= { cfprAdaptorFcPortProfileEntry 5 }

cfprAdaptorFcPortStatsTable OBJECT-TYPE
    SYNTAX           SEQUENCE OF CfprAdaptorFcPortStatsEntry
    MAX-ACCESS       not-accessible
    STATUS           current
    DESCRIPTION
        "Cisco Firepower adaptor:FcPortStats managed object table"
    ::= { cfprAdaptorObjects 49 }

cfprAdaptorFcPortStatsEntry OBJECT-TYPE
    SYNTAX           CfprAdaptorFcPortStatsEntry
    MAX-ACCESS       not-accessible
    STATUS           current
    DESCRIPTION
        "Entry for the cfprAdaptorFcPortStatsTable table."
    INDEX { cfprAdaptorFcPortStatsInstanceId }
    ::= { cfprAdaptorFcPortStatsTable 1 }

CfprAdaptorFcPortStatsEntry ::= SEQUENCE {
    cfprAdaptorFcPortStatsInstanceId                                 CfprManagedObjectId,
    cfprAdaptorFcPortStatsDn                                         CfprManagedObjectDn,
    cfprAdaptorFcPortStatsRn                                         SnmpAdminString,
    cfprAdaptorFcPortStatsIntervals                                  Gauge32,
    cfprAdaptorFcPortStatsRxBadFrames                                Unsigned64,
    cfprAdaptorFcPortStatsRxBadFramesDelta                           Counter64,
    cfprAdaptorFcPortStatsRxBadFramesDeltaAvg                        Unsigned64,
    cfprAdaptorFcPortStatsRxBadFramesDeltaMax                        Unsigned64,
    cfprAdaptorFcPortStatsRxBadFramesDeltaMin                        Unsigned64,
    cfprAdaptorFcPortStatsRxFrames                                   Unsigned64,
    cfprAdaptorFcPortStatsRxFramesDelta                              Counter64,
    cfprAdaptorFcPortStatsRxFramesDeltaAvg                           Unsigned64,
    cfprAdaptorFcPortStatsRxFramesDeltaMax                           Unsigned64,
    cfprAdaptorFcPortStatsRxFramesDeltaMin                           Unsigned64,
    cfprAdaptorFcPortStatsSuspect                                    TruthValue,
    cfprAdaptorFcPortStatsThresholded                                CfprAdaptorFcPortStatsThresholded,
    cfprAdaptorFcPortStatsTimeCollected                              DateAndTime,
    cfprAdaptorFcPortStatsTxBadFrames                                Unsigned64,
    cfprAdaptorFcPortStatsTxBadFramesDelta                           Counter64,
    cfprAdaptorFcPortStatsTxBadFramesDeltaAvg                        Unsigned64,
    cfprAdaptorFcPortStatsTxBadFramesDeltaMax                        Unsigned64,
    cfprAdaptorFcPortStatsTxBadFramesDeltaMin                        Unsigned64,
    cfprAdaptorFcPortStatsTxFrames                                   Unsigned64,
    cfprAdaptorFcPortStatsTxFramesDelta                              Counter64,
    cfprAdaptorFcPortStatsTxFramesDeltaAvg                           Unsigned64,
    cfprAdaptorFcPortStatsTxFramesDeltaMax                           Unsigned64,
    cfprAdaptorFcPortStatsTxFramesDeltaMin                           Unsigned64,
    cfprAdaptorFcPortStatsUpdate                                     Gauge32
}

cfprAdaptorFcPortStatsInstanceId OBJECT-TYPE
    SYNTAX       CfprManagedObjectId
    MAX-ACCESS   not-accessible
    STATUS       current
    DESCRIPTION
        "Instance identifier of the managed object."
    ::= { cfprAdaptorFcPortStatsEntry 1 }

cfprAdaptorFcPortStatsDn OBJECT-TYPE
    SYNTAX       CfprManagedObjectDn
    MAX-ACCESS   read-only
    STATUS       current
    DESCRIPTION
        "Cisco Firepower adaptor:FcPortStats:dn managed object property"
    ::= { cfprAdaptorFcPortStatsEntry 2 }

cfprAdaptorFcPortStatsRn OBJECT-TYPE
    SYNTAX       SnmpAdminString
    MAX-ACCESS   read-only
    STATUS       current
    DESCRIPTION
        "Cisco Firepower adaptor:FcPortStats:rn managed object property"
    ::= { cfprAdaptorFcPortStatsEntry 3 }

cfprAdaptorFcPortStatsIntervals OBJECT-TYPE
    SYNTAX       Gauge32
    MAX-ACCESS   read-only
    STATUS       current
    DESCRIPTION
        "Cisco Firepower adaptor:FcPortStats:intervals
        managed object property"
    ::= { cfprAdaptorFcPortStatsEntry 4 }

cfprAdaptorFcPortStatsRxBadFrames OBJECT-TYPE
    SYNTAX       Unsigned64
    MAX-ACCESS   read-only
    STATUS       current
    DESCRIPTION
        "Cisco Firepower adaptor:FcPortStats:rxBadFrames
        managed object property"
    ::= { cfprAdaptorFcPortStatsEntry 5 }

cfprAdaptorFcPortStatsRxBadFramesDelta OBJECT-TYPE
    SYNTAX       Counter64
    MAX-ACCESS   read-only
    STATUS       current
    DESCRIPTION
        "Cisco Firepower adaptor:FcPortStats:rxBadFramesDelta
        managed object property"
    ::= { cfprAdaptorFcPortStatsEntry 6 }

cfprAdaptorFcPortStatsRxBadFramesDeltaAvg OBJECT-TYPE
    SYNTAX       Unsigned64
    MAX-ACCESS   read-only
    STATUS       current
    DESCRIPTION
        "Cisco Firepower adaptor:FcPortStats:rxBadFramesDeltaAvg
        managed object property"
    ::= { cfprAdaptorFcPortStatsEntry 7 }

cfprAdaptorFcPortStatsRxBadFramesDeltaMax OBJECT-TYPE
    SYNTAX       Unsigned64
    MAX-ACCESS   read-only
    STATUS       current
    DESCRIPTION
        "Cisco Firepower adaptor:FcPortStats:rxBadFramesDeltaMax
        managed object property"
    ::= { cfprAdaptorFcPortStatsEntry 8 }

cfprAdaptorFcPortStatsRxBadFramesDeltaMin OBJECT-TYPE
    SYNTAX       Unsigned64
    MAX-ACCESS   read-only
    STATUS       current
    DESCRIPTION
        "Cisco Firepower adaptor:FcPortStats:rxBadFramesDeltaMin
        managed object property"
    ::= { cfprAdaptorFcPortStatsEntry 9 }

cfprAdaptorFcPortStatsRxFrames OBJECT-TYPE
    SYNTAX       Unsigned64
    MAX-ACCESS   read-only
    STATUS       current
    DESCRIPTION
        "Cisco Firepower adaptor:FcPortStats:rxFrames managed
        object property"
    ::= { cfprAdaptorFcPortStatsEntry 10 }

cfprAdaptorFcPortStatsRxFramesDelta OBJECT-TYPE
    SYNTAX       Counter64
    MAX-ACCESS   read-only
    STATUS       current
    DESCRIPTION
        "Cisco Firepower adaptor:FcPortStats:rxFramesDelta
        managed object property"
    ::= { cfprAdaptorFcPortStatsEntry 11 }

cfprAdaptorFcPortStatsRxFramesDeltaAvg OBJECT-TYPE
    SYNTAX       Unsigned64
    MAX-ACCESS   read-only
    STATUS       current
    DESCRIPTION
        "Cisco Firepower adaptor:FcPortStats:rxFramesDeltaAvg
        managed object property"
    ::= { cfprAdaptorFcPortStatsEntry 12 }

cfprAdaptorFcPortStatsRxFramesDeltaMax OBJECT-TYPE
    SYNTAX       Unsigned64
    MAX-ACCESS   read-only
    STATUS       current
    DESCRIPTION
        "Cisco Firepower adaptor:FcPortStats:rxFramesDeltaMax
        managed object property"
    ::= { cfprAdaptorFcPortStatsEntry 13 }

cfprAdaptorFcPortStatsRxFramesDeltaMin OBJECT-TYPE
    SYNTAX       Unsigned64
    MAX-ACCESS   read-only
    STATUS       current
    DESCRIPTION
        "Cisco Firepower adaptor:FcPortStats:rxFramesDeltaMin
        managed object property"
    ::= { cfprAdaptorFcPortStatsEntry 14 }

cfprAdaptorFcPortStatsSuspect OBJECT-TYPE
    SYNTAX       TruthValue
    MAX-ACCESS   read-only
    STATUS       current
    DESCRIPTION
        "Cisco Firepower adaptor:FcPortStats:suspect managed
        object property"
    ::= { cfprAdaptorFcPortStatsEntry 15 }

cfprAdaptorFcPortStatsThresholded OBJECT-TYPE
    SYNTAX       CfprAdaptorFcPortStatsThresholded
    MAX-ACCESS   read-only
    STATUS       current
    DESCRIPTION
        "Cisco Firepower adaptor:FcPortStats:thresholded
        managed object property"
    ::= { cfprAdaptorFcPortStatsEntry 16 }

cfprAdaptorFcPortStatsTimeCollected OBJECT-TYPE
    SYNTAX       DateAndTime
    MAX-ACCESS   read-only
    STATUS       current
    DESCRIPTION
        "Cisco Firepower adaptor:FcPortStats:timeCollected
        managed object property"
    ::= { cfprAdaptorFcPortStatsEntry 17 }

cfprAdaptorFcPortStatsTxBadFrames OBJECT-TYPE
    SYNTAX       Unsigned64
    MAX-ACCESS   read-only
    STATUS       current
    DESCRIPTION
        "Cisco Firepower adaptor:FcPortStats:txBadFrames
        managed object property"
    ::= { cfprAdaptorFcPortStatsEntry 18 }

cfprAdaptorFcPortStatsTxBadFramesDelta OBJECT-TYPE
    SYNTAX       Counter64
    MAX-ACCESS   read-only
    STATUS       current
    DESCRIPTION
        "Cisco Firepower adaptor:FcPortStats:txBadFramesDelta
        managed object property"
    ::= { cfprAdaptorFcPortStatsEntry 19 }

cfprAdaptorFcPortStatsTxBadFramesDeltaAvg OBJECT-TYPE
    SYNTAX       Unsigned64
    MAX-ACCESS   read-only
    STATUS       current
    DESCRIPTION
        "Cisco Firepower adaptor:FcPortStats:txBadFramesDeltaAvg
        managed object property"
    ::= { cfprAdaptorFcPortStatsEntry 20 }

cfprAdaptorFcPortStatsTxBadFramesDeltaMax OBJECT-TYPE
    SYNTAX       Unsigned64
    MAX-ACCESS   read-only
    STATUS       current
    DESCRIPTION
        "Cisco Firepower adaptor:FcPortStats:txBadFramesDeltaMax
        managed object property"
    ::= { cfprAdaptorFcPortStatsEntry 21 }

cfprAdaptorFcPortStatsTxBadFramesDeltaMin OBJECT-TYPE
    SYNTAX       Unsigned64
    MAX-ACCESS   read-only
    STATUS       current
    DESCRIPTION
        "Cisco Firepower adaptor:FcPortStats:txBadFramesDeltaMin
        managed object property"
    ::= { cfprAdaptorFcPortStatsEntry 22 }

cfprAdaptorFcPortStatsTxFrames OBJECT-TYPE
    SYNTAX       Unsigned64
    MAX-ACCESS   read-only
    STATUS       current
    DESCRIPTION
        "Cisco Firepower adaptor:FcPortStats:txFrames managed
        object property"
    ::= { cfprAdaptorFcPortStatsEntry 23 }

cfprAdaptorFcPortStatsTxFramesDelta OBJECT-TYPE
    SYNTAX       Counter64
    MAX-ACCESS   read-only
    STATUS       current
    DESCRIPTION
        "Cisco Firepower adaptor:FcPortStats:txFramesDelta
        managed object property"
    ::= { cfprAdaptorFcPortStatsEntry 24 }

cfprAdaptorFcPortStatsTxFramesDeltaAvg OBJECT-TYPE
    SYNTAX       Unsigned64
    MAX-ACCESS   read-only
    STATUS       current
    DESCRIPTION
        "Cisco Firepower adaptor:FcPortStats:txFramesDeltaAvg
        managed object property"
    ::= { cfprAdaptorFcPortStatsEntry 25 }

cfprAdaptorFcPortStatsTxFramesDeltaMax OBJECT-TYPE
    SYNTAX       Unsigned64
    MAX-ACCESS   read-only
    STATUS       current
    DESCRIPTION
        "Cisco Firepower adaptor:FcPortStats:txFramesDeltaMax
        managed object property"
    ::= { cfprAdaptorFcPortStatsEntry 26 }

cfprAdaptorFcPortStatsTxFramesDeltaMin OBJECT-TYPE
    SYNTAX       Unsigned64
    MAX-ACCESS   read-only
    STATUS       current
    DESCRIPTION
        "Cisco Firepower adaptor:FcPortStats:txFramesDeltaMin
        managed object property"
    ::= { cfprAdaptorFcPortStatsEntry 27 }

cfprAdaptorFcPortStatsUpdate OBJECT-TYPE
    SYNTAX       Gauge32
    MAX-ACCESS   read-only
    STATUS       current
    DESCRIPTION
        "Cisco Firepower adaptor:FcPortStats:update managed
        object property"
    ::= { cfprAdaptorFcPortStatsEntry 28 }

cfprAdaptorFcPortStatsHistTable OBJECT-TYPE
    SYNTAX           SEQUENCE OF CfprAdaptorFcPortStatsHistEntry
    MAX-ACCESS       not-accessible
    STATUS           current
    DESCRIPTION
        "Cisco Firepower adaptor:FcPortStatsHist managed object table"
    ::= { cfprAdaptorObjects 50 }

cfprAdaptorFcPortStatsHistEntry OBJECT-TYPE
    SYNTAX           CfprAdaptorFcPortStatsHistEntry
    MAX-ACCESS       not-accessible
    STATUS           current
    DESCRIPTION
        "Entry for the cfprAdaptorFcPortStatsHistTable table."
    INDEX { cfprAdaptorFcPortStatsHistInstanceId }
    ::= { cfprAdaptorFcPortStatsHistTable 1 }

CfprAdaptorFcPortStatsHistEntry ::= SEQUENCE {
    cfprAdaptorFcPortStatsHistInstanceId                             CfprManagedObjectId,
    cfprAdaptorFcPortStatsHistDn                                     CfprManagedObjectDn,
    cfprAdaptorFcPortStatsHistRn                                     SnmpAdminString,
    cfprAdaptorFcPortStatsHistId                                     Unsigned64,
    cfprAdaptorFcPortStatsHistMostRecent                             TruthValue,
    cfprAdaptorFcPortStatsHistRxBadFrames                            Unsigned64,
    cfprAdaptorFcPortStatsHistRxBadFramesDelta                       Unsigned64,
    cfprAdaptorFcPortStatsHistRxBadFramesDeltaAvg                    Unsigned64,
    cfprAdaptorFcPortStatsHistRxBadFramesDeltaMax                    Unsigned64,
    cfprAdaptorFcPortStatsHistRxBadFramesDeltaMin                    Unsigned64,
    cfprAdaptorFcPortStatsHistRxFrames                               Unsigned64,
    cfprAdaptorFcPortStatsHistRxFramesDelta                          Unsigned64,
    cfprAdaptorFcPortStatsHistRxFramesDeltaAvg                       Unsigned64,
    cfprAdaptorFcPortStatsHistRxFramesDeltaMax                       Unsigned64,
    cfprAdaptorFcPortStatsHistRxFramesDeltaMin                       Unsigned64,
    cfprAdaptorFcPortStatsHistSuspect                                TruthValue,
    cfprAdaptorFcPortStatsHistThresholded                            CfprAdaptorFcPortStatsHistThresholded,
    cfprAdaptorFcPortStatsHistTimeCollected                          DateAndTime,
    cfprAdaptorFcPortStatsHistTxBadFrames                            Unsigned64,
    cfprAdaptorFcPortStatsHistTxBadFramesDelta                       Unsigned64,
    cfprAdaptorFcPortStatsHistTxBadFramesDeltaAvg                    Unsigned64,
    cfprAdaptorFcPortStatsHistTxBadFramesDeltaMax                    Unsigned64,
    cfprAdaptorFcPortStatsHistTxBadFramesDeltaMin                    Unsigned64,
    cfprAdaptorFcPortStatsHistTxFrames                               Unsigned64,
    cfprAdaptorFcPortStatsHistTxFramesDelta                          Unsigned64,
    cfprAdaptorFcPortStatsHistTxFramesDeltaAvg                       Unsigned64,
    cfprAdaptorFcPortStatsHistTxFramesDeltaMax                       Unsigned64,
    cfprAdaptorFcPortStatsHistTxFramesDeltaMin                       Unsigned64
}

cfprAdaptorFcPortStatsHistInstanceId OBJECT-TYPE
    SYNTAX       CfprManagedObjectId
    MAX-ACCESS   not-accessible
    STATUS       current
    DESCRIPTION
        "Instance identifier of the managed object."
    ::= { cfprAdaptorFcPortStatsHistEntry 1 }

cfprAdaptorFcPortStatsHistDn OBJECT-TYPE
    SYNTAX       CfprManagedObjectDn
    MAX-ACCESS   read-only
    STATUS       current
    DESCRIPTION
        "Cisco Firepower adaptor:FcPortStatsHist:dn managed
        object property"
    ::= { cfprAdaptorFcPortStatsHistEntry 2 }

cfprAdaptorFcPortStatsHistRn OBJECT-TYPE
    SYNTAX       SnmpAdminString
    MAX-ACCESS   read-only
    STATUS       current
    DESCRIPTION
        "Cisco Firepower adaptor:FcPortStatsHist:rn managed
        object property"
    ::= { cfprAdaptorFcPortStatsHistEntry 3 }

cfprAdaptorFcPortStatsHistId OBJECT-TYPE
    SYNTAX       Unsigned64
    MAX-ACCESS   read-only
    STATUS       current
    DESCRIPTION
        "Cisco Firepower adaptor:FcPortStatsHist:id managed
        object property"
    ::= { cfprAdaptorFcPortStatsHistEntry 4 }

cfprAdaptorFcPortStatsHistMostRecent OBJECT-TYPE
    SYNTAX       TruthValue
    MAX-ACCESS   read-only
    STATUS       current
    DESCRIPTION
        "Cisco Firepower adaptor:FcPortStatsHist:mostRecent
        managed object property"
    ::= { cfprAdaptorFcPortStatsHistEntry 5 }

cfprAdaptorFcPortStatsHistRxBadFrames OBJECT-TYPE
    SYNTAX       Unsigned64
    MAX-ACCESS   read-only
    STATUS       current
    DESCRIPTION
        "Cisco Firepower adaptor:FcPortStatsHist:rxBadFrames
        managed object property"
    ::= { cfprAdaptorFcPortStatsHistEntry 6 }

cfprAdaptorFcPortStatsHistRxBadFramesDelta OBJECT-TYPE
    SYNTAX       Unsigned64
    MAX-ACCESS   read-only
    STATUS       current
    DESCRIPTION
        "Cisco Firepower adaptor:FcPortStatsHist:rxBadFramesDelta
        managed object property"
    ::= { cfprAdaptorFcPortStatsHistEntry 7 }

cfprAdaptorFcPortStatsHistRxBadFramesDeltaAvg OBJECT-TYPE
    SYNTAX       Unsigned64
    MAX-ACCESS   read-only
    STATUS       current
    DESCRIPTION
        "Cisco Firepower adaptor:FcPortStatsHist:rxBadFramesDeltaAvg
        managed object property"
    ::= { cfprAdaptorFcPortStatsHistEntry 8 }

cfprAdaptorFcPortStatsHistRxBadFramesDeltaMax OBJECT-TYPE
    SYNTAX       Unsigned64
    MAX-ACCESS   read-only
    STATUS       current
    DESCRIPTION
        "Cisco Firepower adaptor:FcPortStatsHist:rxBadFramesDeltaMax
        managed object property"
    ::= { cfprAdaptorFcPortStatsHistEntry 9 }

cfprAdaptorFcPortStatsHistRxBadFramesDeltaMin OBJECT-TYPE
    SYNTAX       Unsigned64
    MAX-ACCESS   read-only
    STATUS       current
    DESCRIPTION
        "Cisco Firepower adaptor:FcPortStatsHist:rxBadFramesDeltaMin
        managed object property"
    ::= { cfprAdaptorFcPortStatsHistEntry 10 }

cfprAdaptorFcPortStatsHistRxFrames OBJECT-TYPE
    SYNTAX       Unsigned64
    MAX-ACCESS   read-only
    STATUS       current
    DESCRIPTION
        "Cisco Firepower adaptor:FcPortStatsHist:rxFrames
        managed object property"
    ::= { cfprAdaptorFcPortStatsHistEntry 11 }

cfprAdaptorFcPortStatsHistRxFramesDelta OBJECT-TYPE
    SYNTAX       Unsigned64
    MAX-ACCESS   read-only
    STATUS       current
    DESCRIPTION
        "Cisco Firepower adaptor:FcPortStatsHist:rxFramesDelta
        managed object property"
    ::= { cfprAdaptorFcPortStatsHistEntry 12 }

cfprAdaptorFcPortStatsHistRxFramesDeltaAvg OBJECT-TYPE
    SYNTAX       Unsigned64
    MAX-ACCESS   read-only
    STATUS       current
    DESCRIPTION
        "Cisco Firepower adaptor:FcPortStatsHist:rxFramesDeltaAvg
        managed object property"
    ::= { cfprAdaptorFcPortStatsHistEntry 13 }

cfprAdaptorFcPortStatsHistRxFramesDeltaMax OBJECT-TYPE
    SYNTAX       Unsigned64
    MAX-ACCESS   read-only
    STATUS       current
    DESCRIPTION
        "Cisco Firepower adaptor:FcPortStatsHist:rxFramesDeltaMax
        managed object property"
    ::= { cfprAdaptorFcPortStatsHistEntry 14 }

cfprAdaptorFcPortStatsHistRxFramesDeltaMin OBJECT-TYPE
    SYNTAX       Unsigned64
    MAX-ACCESS   read-only
    STATUS       current
    DESCRIPTION
        "Cisco Firepower adaptor:FcPortStatsHist:rxFramesDeltaMin
        managed object property"
    ::= { cfprAdaptorFcPortStatsHistEntry 15 }

cfprAdaptorFcPortStatsHistSuspect OBJECT-TYPE
    SYNTAX       TruthValue
    MAX-ACCESS   read-only
    STATUS       current
    DESCRIPTION
        "Cisco Firepower adaptor:FcPortStatsHist:suspect
        managed object property"
    ::= { cfprAdaptorFcPortStatsHistEntry 16 }

cfprAdaptorFcPortStatsHistThresholded OBJECT-TYPE
    SYNTAX       CfprAdaptorFcPortStatsHistThresholded
    MAX-ACCESS   read-only
    STATUS       current
    DESCRIPTION
        "Cisco Firepower adaptor:FcPortStatsHist:thresholded
        managed object property"
    ::= { cfprAdaptorFcPortStatsHistEntry 17 }

cfprAdaptorFcPortStatsHistTimeCollected OBJECT-TYPE
    SYNTAX       DateAndTime
    MAX-ACCESS   read-only
    STATUS       current
    DESCRIPTION
        "Cisco Firepower adaptor:FcPortStatsHist:timeCollected
        managed object property"
    ::= { cfprAdaptorFcPortStatsHistEntry 18 }

cfprAdaptorFcPortStatsHistTxBadFrames OBJECT-TYPE
    SYNTAX       Unsigned64
    MAX-ACCESS   read-only
    STATUS       current
    DESCRIPTION
        "Cisco Firepower adaptor:FcPortStatsHist:txBadFrames
        managed object property"
    ::= { cfprAdaptorFcPortStatsHistEntry 19 }

cfprAdaptorFcPortStatsHistTxBadFramesDelta OBJECT-TYPE
    SYNTAX       Unsigned64
    MAX-ACCESS   read-only
    STATUS       current
    DESCRIPTION
        "Cisco Firepower adaptor:FcPortStatsHist:txBadFramesDelta
        managed object property"
    ::= { cfprAdaptorFcPortStatsHistEntry 20 }

cfprAdaptorFcPortStatsHistTxBadFramesDeltaAvg OBJECT-TYPE
    SYNTAX       Unsigned64
    MAX-ACCESS   read-only
    STATUS       current
    DESCRIPTION
        "Cisco Firepower adaptor:FcPortStatsHist:txBadFramesDeltaAvg
        managed object property"
    ::= { cfprAdaptorFcPortStatsHistEntry 21 }

cfprAdaptorFcPortStatsHistTxBadFramesDeltaMax OBJECT-TYPE
    SYNTAX       Unsigned64
    MAX-ACCESS   read-only
    STATUS       current
    DESCRIPTION
        "Cisco Firepower adaptor:FcPortStatsHist:txBadFramesDeltaMax
        managed object property"
    ::= { cfprAdaptorFcPortStatsHistEntry 22 }

cfprAdaptorFcPortStatsHistTxBadFramesDeltaMin OBJECT-TYPE
    SYNTAX       Unsigned64
    MAX-ACCESS   read-only
    STATUS       current
    DESCRIPTION
        "Cisco Firepower adaptor:FcPortStatsHist:txBadFramesDeltaMin
        managed object property"
    ::= { cfprAdaptorFcPortStatsHistEntry 23 }

cfprAdaptorFcPortStatsHistTxFrames OBJECT-TYPE
    SYNTAX       Unsigned64
    MAX-ACCESS   read-only
    STATUS       current
    DESCRIPTION
        "Cisco Firepower adaptor:FcPortStatsHist:txFrames
        managed object property"
    ::= { cfprAdaptorFcPortStatsHistEntry 24 }

cfprAdaptorFcPortStatsHistTxFramesDelta OBJECT-TYPE
    SYNTAX       Unsigned64
    MAX-ACCESS   read-only
    STATUS       current
    DESCRIPTION
        "Cisco Firepower adaptor:FcPortStatsHist:txFramesDelta
        managed object property"
    ::= { cfprAdaptorFcPortStatsHistEntry 25 }

cfprAdaptorFcPortStatsHistTxFramesDeltaAvg OBJECT-TYPE
    SYNTAX       Unsigned64
    MAX-ACCESS   read-only
    STATUS       current
    DESCRIPTION
        "Cisco Firepower adaptor:FcPortStatsHist:txFramesDeltaAvg
        managed object property"
    ::= { cfprAdaptorFcPortStatsHistEntry 26 }

cfprAdaptorFcPortStatsHistTxFramesDeltaMax OBJECT-TYPE
    SYNTAX       Unsigned64
    MAX-ACCESS   read-only
    STATUS       current
    DESCRIPTION
        "Cisco Firepower adaptor:FcPortStatsHist:txFramesDeltaMax
        managed object property"
    ::= { cfprAdaptorFcPortStatsHistEntry 27 }

cfprAdaptorFcPortStatsHistTxFramesDeltaMin OBJECT-TYPE
    SYNTAX       Unsigned64
    MAX-ACCESS   read-only
    STATUS       current
    DESCRIPTION
        "Cisco Firepower adaptor:FcPortStatsHist:txFramesDeltaMin
        managed object property"
    ::= { cfprAdaptorFcPortStatsHistEntry 28 }

cfprAdaptorFcRecvQueueProfileTable OBJECT-TYPE
    SYNTAX           SEQUENCE OF CfprAdaptorFcRecvQueueProfileEntry
    MAX-ACCESS       not-accessible
    STATUS           current
    DESCRIPTION
        "Cisco Firepower adaptor:FcRecvQueueProfile managed object table"
    ::= { cfprAdaptorObjects 51 }

cfprAdaptorFcRecvQueueProfileEntry OBJECT-TYPE
    SYNTAX           CfprAdaptorFcRecvQueueProfileEntry
    MAX-ACCESS       not-accessible
    STATUS           current
    DESCRIPTION
        "Entry for the cfprAdaptorFcRecvQueueProfileTable table."
    INDEX { cfprAdaptorFcRecvQueueProfileInstanceId }
    ::= { cfprAdaptorFcRecvQueueProfileTable 1 }

CfprAdaptorFcRecvQueueProfileEntry ::= SEQUENCE {
    cfprAdaptorFcRecvQueueProfileInstanceId                          CfprManagedObjectId,
    cfprAdaptorFcRecvQueueProfileDn                                  CfprManagedObjectDn,
    cfprAdaptorFcRecvQueueProfileRn                                  SnmpAdminString,
    cfprAdaptorFcRecvQueueProfileCount                               Gauge32,
    cfprAdaptorFcRecvQueueProfileRingSize                            Gauge32
}

cfprAdaptorFcRecvQueueProfileInstanceId OBJECT-TYPE
    SYNTAX       CfprManagedObjectId
    MAX-ACCESS   not-accessible
    STATUS       current
    DESCRIPTION
        "Instance identifier of the managed object."
    ::= { cfprAdaptorFcRecvQueueProfileEntry 1 }

cfprAdaptorFcRecvQueueProfileDn OBJECT-TYPE
    SYNTAX       CfprManagedObjectDn
    MAX-ACCESS   read-only
    STATUS       current
    DESCRIPTION
        "Cisco Firepower adaptor:FcRecvQueueProfile:dn
        managed object property"
    ::= { cfprAdaptorFcRecvQueueProfileEntry 2 }

cfprAdaptorFcRecvQueueProfileRn OBJECT-TYPE
    SYNTAX       SnmpAdminString
    MAX-ACCESS   read-only
    STATUS       current
    DESCRIPTION
        "Cisco Firepower adaptor:FcRecvQueueProfile:rn
        managed object property"
    ::= { cfprAdaptorFcRecvQueueProfileEntry 3 }

cfprAdaptorFcRecvQueueProfileCount OBJECT-TYPE
    SYNTAX       Gauge32
    MAX-ACCESS   read-only
    STATUS       current
    DESCRIPTION
        "Cisco Firepower adaptor:FcRecvQueueProfile:count
        managed object property"
    ::= { cfprAdaptorFcRecvQueueProfileEntry 4 }

cfprAdaptorFcRecvQueueProfileRingSize OBJECT-TYPE
    SYNTAX       Gauge32
    MAX-ACCESS   read-only
    STATUS       current
    DESCRIPTION
        "Cisco Firepower adaptor:FcRecvQueueProfile:ringSize
        managed object property"
    ::= { cfprAdaptorFcRecvQueueProfileEntry 5 }

cfprAdaptorFcWorkQueueProfileTable OBJECT-TYPE
    SYNTAX           SEQUENCE OF CfprAdaptorFcWorkQueueProfileEntry
    MAX-ACCESS       not-accessible
    STATUS           current
    DESCRIPTION
        "Cisco Firepower adaptor:FcWorkQueueProfile managed object table"
    ::= { cfprAdaptorObjects 52 }

cfprAdaptorFcWorkQueueProfileEntry OBJECT-TYPE
    SYNTAX           CfprAdaptorFcWorkQueueProfileEntry
    MAX-ACCESS       not-accessible
    STATUS           current
    DESCRIPTION
        "Entry for the cfprAdaptorFcWorkQueueProfileTable table."
    INDEX { cfprAdaptorFcWorkQueueProfileInstanceId }
    ::= { cfprAdaptorFcWorkQueueProfileTable 1 }

CfprAdaptorFcWorkQueueProfileEntry ::= SEQUENCE {
    cfprAdaptorFcWorkQueueProfileInstanceId                          CfprManagedObjectId,
    cfprAdaptorFcWorkQueueProfileDn                                  CfprManagedObjectDn,
    cfprAdaptorFcWorkQueueProfileRn                                  SnmpAdminString,
    cfprAdaptorFcWorkQueueProfileCount                               Gauge32,
    cfprAdaptorFcWorkQueueProfileRingSize                            Gauge32
}

cfprAdaptorFcWorkQueueProfileInstanceId OBJECT-TYPE
    SYNTAX       CfprManagedObjectId
    MAX-ACCESS   not-accessible
    STATUS       current
    DESCRIPTION
        "Instance identifier of the managed object."
    ::= { cfprAdaptorFcWorkQueueProfileEntry 1 }

cfprAdaptorFcWorkQueueProfileDn OBJECT-TYPE
    SYNTAX       CfprManagedObjectDn
    MAX-ACCESS   read-only
    STATUS       current
    DESCRIPTION
        "Cisco Firepower adaptor:FcWorkQueueProfile:dn
        managed object property"
    ::= { cfprAdaptorFcWorkQueueProfileEntry 2 }

cfprAdaptorFcWorkQueueProfileRn OBJECT-TYPE
    SYNTAX       SnmpAdminString
    MAX-ACCESS   read-only
    STATUS       current
    DESCRIPTION
        "Cisco Firepower adaptor:FcWorkQueueProfile:rn
        managed object property"
    ::= { cfprAdaptorFcWorkQueueProfileEntry 3 }

cfprAdaptorFcWorkQueueProfileCount OBJECT-TYPE
    SYNTAX       Gauge32
    MAX-ACCESS   read-only
    STATUS       current
    DESCRIPTION
        "Cisco Firepower adaptor:FcWorkQueueProfile:count
        managed object property"
    ::= { cfprAdaptorFcWorkQueueProfileEntry 4 }

cfprAdaptorFcWorkQueueProfileRingSize OBJECT-TYPE
    SYNTAX       Gauge32
    MAX-ACCESS   read-only
    STATUS       current
    DESCRIPTION
        "Cisco Firepower adaptor:FcWorkQueueProfile:ringSize
        managed object property"
    ::= { cfprAdaptorFcWorkQueueProfileEntry 5 }

cfprAdaptorFruCapProviderTable OBJECT-TYPE
    SYNTAX           SEQUENCE OF CfprAdaptorFruCapProviderEntry
    MAX-ACCESS       not-accessible
    STATUS           current
    DESCRIPTION
        "Cisco Firepower adaptor:FruCapProvider managed object table"
    ::= { cfprAdaptorObjects 53 }

cfprAdaptorFruCapProviderEntry OBJECT-TYPE
    SYNTAX           CfprAdaptorFruCapProviderEntry
    MAX-ACCESS       not-accessible
    STATUS           current
    DESCRIPTION
        "Entry for the cfprAdaptorFruCapProviderTable table."
    INDEX { cfprAdaptorFruCapProviderInstanceId }
    ::= { cfprAdaptorFruCapProviderTable 1 }

CfprAdaptorFruCapProviderEntry ::= SEQUENCE {
    cfprAdaptorFruCapProviderInstanceId                              CfprManagedObjectId,
    cfprAdaptorFruCapProviderDn                                      CfprManagedObjectDn,
    cfprAdaptorFruCapProviderRn                                      SnmpAdminString,
    cfprAdaptorFruCapProviderDeleted                                 TruthValue,
    cfprAdaptorFruCapProviderDeprecated                              TruthValue,
    cfprAdaptorFruCapProviderElementLoadFailures                     Gauge32,
    cfprAdaptorFruCapProviderElementsLoaded                          Gauge32,
    cfprAdaptorFruCapProviderGencount                                Gauge32,
    cfprAdaptorFruCapProviderLoadErrors                              Gauge32,
    cfprAdaptorFruCapProviderLoadWarnings                            Gauge32,
    cfprAdaptorFruCapProviderMgmtPlaneVer                            SnmpAdminString,
    cfprAdaptorFruCapProviderModel                                   SnmpAdminString,
    cfprAdaptorFruCapProviderPromCardType                            Gauge32,
    cfprAdaptorFruCapProviderRevision                                SnmpAdminString,
    cfprAdaptorFruCapProviderVendor                                  SnmpAdminString
}

cfprAdaptorFruCapProviderInstanceId OBJECT-TYPE
    SYNTAX       CfprManagedObjectId
    MAX-ACCESS   not-accessible
    STATUS       current
    DESCRIPTION
        "Instance identifier of the managed object."
    ::= { cfprAdaptorFruCapProviderEntry 1 }

cfprAdaptorFruCapProviderDn OBJECT-TYPE
    SYNTAX       CfprManagedObjectDn
    MAX-ACCESS   read-only
    STATUS       current
    DESCRIPTION
        "Cisco Firepower adaptor:FruCapProvider:dn managed
        object property"
    ::= { cfprAdaptorFruCapProviderEntry 2 }

cfprAdaptorFruCapProviderRn OBJECT-TYPE
    SYNTAX       SnmpAdminString
    MAX-ACCESS   read-only
    STATUS       current
    DESCRIPTION
        "Cisco Firepower adaptor:FruCapProvider:rn managed
        object property"
    ::= { cfprAdaptorFruCapProviderEntry 3 }

cfprAdaptorFruCapProviderDeleted OBJECT-TYPE
    SYNTAX       TruthValue
    MAX-ACCESS   read-only
    STATUS       current
    DESCRIPTION
        "Cisco Firepower adaptor:FruCapProvider:deleted
        managed object property"
    ::= { cfprAdaptorFruCapProviderEntry 4 }

cfprAdaptorFruCapProviderDeprecated OBJECT-TYPE
    SYNTAX       TruthValue
    MAX-ACCESS   read-only
    STATUS       current
    DESCRIPTION
        "Cisco Firepower adaptor:FruCapProvider:deprecated
        managed object property"
    ::= { cfprAdaptorFruCapProviderEntry 5 }

cfprAdaptorFruCapProviderElementLoadFailures OBJECT-TYPE
    SYNTAX       Gauge32
    MAX-ACCESS   read-only
    STATUS       current
    DESCRIPTION
        "Cisco Firepower adaptor:FruCapProvider:elementLoadFailures
        managed object property"
    ::= { cfprAdaptorFruCapProviderEntry 6 }

cfprAdaptorFruCapProviderElementsLoaded OBJECT-TYPE
    SYNTAX       Gauge32
    MAX-ACCESS   read-only
    STATUS       current
    DESCRIPTION
        "Cisco Firepower adaptor:FruCapProvider:elementsLoaded
        managed object property"
    ::= { cfprAdaptorFruCapProviderEntry 7 }

cfprAdaptorFruCapProviderGencount OBJECT-TYPE
    SYNTAX       Gauge32
    MAX-ACCESS   read-only
    STATUS       current
    DESCRIPTION
        "Cisco Firepower adaptor:FruCapProvider:gencount
        managed object property"
    ::= { cfprAdaptorFruCapProviderEntry 8 }

cfprAdaptorFruCapProviderLoadErrors OBJECT-TYPE
    SYNTAX       Gauge32
    MAX-ACCESS   read-only
    STATUS       current
    DESCRIPTION
        "Cisco Firepower adaptor:FruCapProvider:loadErrors
        managed object property"
    ::= { cfprAdaptorFruCapProviderEntry 9 }

cfprAdaptorFruCapProviderLoadWarnings OBJECT-TYPE
    SYNTAX       Gauge32
    MAX-ACCESS   read-only
    STATUS       current
    DESCRIPTION
        "Cisco Firepower adaptor:FruCapProvider:loadWarnings
        managed object property"
    ::= { cfprAdaptorFruCapProviderEntry 10 }

cfprAdaptorFruCapProviderMgmtPlaneVer OBJECT-TYPE
    SYNTAX       SnmpAdminString
    MAX-ACCESS   read-only
    STATUS       current
    DESCRIPTION
        "Cisco Firepower adaptor:FruCapProvider:mgmtPlaneVer
        managed object property"
    ::= { cfprAdaptorFruCapProviderEntry 11 }

cfprAdaptorFruCapProviderModel OBJECT-TYPE
    SYNTAX       SnmpAdminString
    MAX-ACCESS   read-only
    STATUS       current
    DESCRIPTION
        "Cisco Firepower adaptor:FruCapProvider:model managed
        object property"
    ::= { cfprAdaptorFruCapProviderEntry 12 }

cfprAdaptorFruCapProviderPromCardType OBJECT-TYPE
    SYNTAX       Gauge32
    MAX-ACCESS   read-only
    STATUS       current
    DESCRIPTION
        "Cisco Firepower adaptor:FruCapProvider:promCardType
        managed object property"
    ::= { cfprAdaptorFruCapProviderEntry 13 }

cfprAdaptorFruCapProviderRevision OBJECT-TYPE
    SYNTAX       SnmpAdminString
    MAX-ACCESS   read-only
    STATUS       current
    DESCRIPTION
        "Cisco Firepower adaptor:FruCapProvider:revision
        managed object property"
    ::= { cfprAdaptorFruCapProviderEntry 14 }

cfprAdaptorFruCapProviderVendor OBJECT-TYPE
    SYNTAX       SnmpAdminString
    MAX-ACCESS   read-only
    STATUS       current
    DESCRIPTION
        "Cisco Firepower adaptor:FruCapProvider:vendor
        managed object property"
    ::= { cfprAdaptorFruCapProviderEntry 15 }

cfprAdaptorFruCapRefTable OBJECT-TYPE
    SYNTAX           SEQUENCE OF CfprAdaptorFruCapRefEntry
    MAX-ACCESS       not-accessible
    STATUS           current
    DESCRIPTION
        "Cisco Firepower adaptor:FruCapRef managed object table"
    ::= { cfprAdaptorObjects 54 }

cfprAdaptorFruCapRefEntry OBJECT-TYPE
    SYNTAX           CfprAdaptorFruCapRefEntry
    MAX-ACCESS       not-accessible
    STATUS           current
    DESCRIPTION
        "Entry for the cfprAdaptorFruCapRefTable table."
    INDEX { cfprAdaptorFruCapRefInstanceId }
    ::= { cfprAdaptorFruCapRefTable 1 }

CfprAdaptorFruCapRefEntry ::= SEQUENCE {
    cfprAdaptorFruCapRefInstanceId                                   CfprManagedObjectId,
    cfprAdaptorFruCapRefDn                                           CfprManagedObjectDn,
    cfprAdaptorFruCapRefRn                                           SnmpAdminString,
    cfprAdaptorFruCapRefIsSupported                                  CfprAdaptorDefaultAction,
    cfprAdaptorFruCapRefModel                                        SnmpAdminString,
    cfprAdaptorFruCapRefRevision                                     SnmpAdminString,
    cfprAdaptorFruCapRefVendor                                       SnmpAdminString
}

cfprAdaptorFruCapRefInstanceId OBJECT-TYPE
    SYNTAX       CfprManagedObjectId
    MAX-ACCESS   not-accessible
    STATUS       current
    DESCRIPTION
        "Instance identifier of the managed object."
    ::= { cfprAdaptorFruCapRefEntry 1 }

cfprAdaptorFruCapRefDn OBJECT-TYPE
    SYNTAX       CfprManagedObjectDn
    MAX-ACCESS   read-only
    STATUS       current
    DESCRIPTION
        "Cisco Firepower adaptor:FruCapRef:dn managed object property"
    ::= { cfprAdaptorFruCapRefEntry 2 }

cfprAdaptorFruCapRefRn OBJECT-TYPE
    SYNTAX       SnmpAdminString
    MAX-ACCESS   read-only
    STATUS       current
    DESCRIPTION
        "Cisco Firepower adaptor:FruCapRef:rn managed object property"
    ::= { cfprAdaptorFruCapRefEntry 3 }

cfprAdaptorFruCapRefIsSupported OBJECT-TYPE
    SYNTAX       CfprAdaptorDefaultAction
    MAX-ACCESS   read-only
    STATUS       current
    DESCRIPTION
        "Cisco Firepower adaptor:FruCapRef:isSupported
        managed object property"
    ::= { cfprAdaptorFruCapRefEntry 4 }

cfprAdaptorFruCapRefModel OBJECT-TYPE
    SYNTAX       SnmpAdminString
    MAX-ACCESS   read-only
    STATUS       current
    DESCRIPTION
        "Cisco Firepower adaptor:FruCapRef:model managed object property"
    ::= { cfprAdaptorFruCapRefEntry 5 }

cfprAdaptorFruCapRefRevision OBJECT-TYPE
    SYNTAX       SnmpAdminString
    MAX-ACCESS   read-only
    STATUS       current
    DESCRIPTION
        "Cisco Firepower adaptor:FruCapRef:revision managed
        object property"
    ::= { cfprAdaptorFruCapRefEntry 6 }

cfprAdaptorFruCapRefVendor OBJECT-TYPE
    SYNTAX       SnmpAdminString
    MAX-ACCESS   read-only
    STATUS       current
    DESCRIPTION
        "Cisco Firepower adaptor:FruCapRef:vendor managed object property"
    ::= { cfprAdaptorFruCapRefEntry 7 }

cfprAdaptorFwCapProviderTable OBJECT-TYPE
    SYNTAX           SEQUENCE OF CfprAdaptorFwCapProviderEntry
    MAX-ACCESS       not-accessible
    STATUS           current
    DESCRIPTION
        "Cisco Firepower adaptor:FwCapProvider managed object table"
    ::= { cfprAdaptorObjects 55 }

cfprAdaptorFwCapProviderEntry OBJECT-TYPE
    SYNTAX           CfprAdaptorFwCapProviderEntry
    MAX-ACCESS       not-accessible
    STATUS           current
    DESCRIPTION
        "Entry for the cfprAdaptorFwCapProviderTable table."
    INDEX { cfprAdaptorFwCapProviderInstanceId }
    ::= { cfprAdaptorFwCapProviderTable 1 }

CfprAdaptorFwCapProviderEntry ::= SEQUENCE {
    cfprAdaptorFwCapProviderInstanceId                               CfprManagedObjectId,
    cfprAdaptorFwCapProviderDn                                       CfprManagedObjectDn,
    cfprAdaptorFwCapProviderRn                                       SnmpAdminString,
    cfprAdaptorFwCapProviderDeleted                                  TruthValue,
    cfprAdaptorFwCapProviderDeprecated                               TruthValue,
    cfprAdaptorFwCapProviderElementLoadFailures                      Gauge32,
    cfprAdaptorFwCapProviderElementsLoaded                           Gauge32,
    cfprAdaptorFwCapProviderGencount                                 Gauge32,
    cfprAdaptorFwCapProviderLoadErrors                               Gauge32,
    cfprAdaptorFwCapProviderLoadWarnings                             Gauge32,
    cfprAdaptorFwCapProviderMgmtPlaneVer                             SnmpAdminString,
    cfprAdaptorFwCapProviderModel                                    SnmpAdminString,
    cfprAdaptorFwCapProviderVendor                                   SnmpAdminString,
    cfprAdaptorFwCapProviderVersion                                  SnmpAdminString
}

cfprAdaptorFwCapProviderInstanceId OBJECT-TYPE
    SYNTAX       CfprManagedObjectId
    MAX-ACCESS   not-accessible
    STATUS       current
    DESCRIPTION
        "Instance identifier of the managed object."
    ::= { cfprAdaptorFwCapProviderEntry 1 }

cfprAdaptorFwCapProviderDn OBJECT-TYPE
    SYNTAX       CfprManagedObjectDn
    MAX-ACCESS   read-only
    STATUS       current
    DESCRIPTION
        "Cisco Firepower adaptor:FwCapProvider:dn managed object property"
    ::= { cfprAdaptorFwCapProviderEntry 2 }

cfprAdaptorFwCapProviderRn OBJECT-TYPE
    SYNTAX       SnmpAdminString
    MAX-ACCESS   read-only
    STATUS       current
    DESCRIPTION
        "Cisco Firepower adaptor:FwCapProvider:rn managed object property"
    ::= { cfprAdaptorFwCapProviderEntry 3 }

cfprAdaptorFwCapProviderDeleted OBJECT-TYPE
    SYNTAX       TruthValue
    MAX-ACCESS   read-only
    STATUS       current
    DESCRIPTION
        "Cisco Firepower adaptor:FwCapProvider:deleted
        managed object property"
    ::= { cfprAdaptorFwCapProviderEntry 4 }

cfprAdaptorFwCapProviderDeprecated OBJECT-TYPE
    SYNTAX       TruthValue
    MAX-ACCESS   read-only
    STATUS       current
    DESCRIPTION
        "Cisco Firepower adaptor:FwCapProvider:deprecated
        managed object property"
    ::= { cfprAdaptorFwCapProviderEntry 5 }

cfprAdaptorFwCapProviderElementLoadFailures OBJECT-TYPE
    SYNTAX       Gauge32
    MAX-ACCESS   read-only
    STATUS       current
    DESCRIPTION
        "Cisco Firepower adaptor:FwCapProvider:elementLoadFailures
        managed object property"
    ::= { cfprAdaptorFwCapProviderEntry 6 }

cfprAdaptorFwCapProviderElementsLoaded OBJECT-TYPE
    SYNTAX       Gauge32
    MAX-ACCESS   read-only
    STATUS       current
    DESCRIPTION
        "Cisco Firepower adaptor:FwCapProvider:elementsLoaded
        managed object property"
    ::= { cfprAdaptorFwCapProviderEntry 7 }

cfprAdaptorFwCapProviderGencount OBJECT-TYPE
    SYNTAX       Gauge32
    MAX-ACCESS   read-only
    STATUS       current
    DESCRIPTION
        "Cisco Firepower adaptor:FwCapProvider:gencount
        managed object property"
    ::= { cfprAdaptorFwCapProviderEntry 8 }

cfprAdaptorFwCapProviderLoadErrors OBJECT-TYPE
    SYNTAX       Gauge32
    MAX-ACCESS   read-only
    STATUS       current
    DESCRIPTION
        "Cisco Firepower adaptor:FwCapProvider:loadErrors
        managed object property"
    ::= { cfprAdaptorFwCapProviderEntry 9 }

cfprAdaptorFwCapProviderLoadWarnings OBJECT-TYPE
    SYNTAX       Gauge32
    MAX-ACCESS   read-only
    STATUS       current
    DESCRIPTION
        "Cisco Firepower adaptor:FwCapProvider:loadWarnings
        managed object property"
    ::= { cfprAdaptorFwCapProviderEntry 10 }

cfprAdaptorFwCapProviderMgmtPlaneVer OBJECT-TYPE
    SYNTAX       SnmpAdminString
    MAX-ACCESS   read-only
    STATUS       current
    DESCRIPTION
        "Cisco Firepower adaptor:FwCapProvider:mgmtPlaneVer
        managed object property"
    ::= { cfprAdaptorFwCapProviderEntry 11 }

cfprAdaptorFwCapProviderModel OBJECT-TYPE
    SYNTAX       SnmpAdminString
    MAX-ACCESS   read-only
    STATUS       current
    DESCRIPTION
        "Cisco Firepower adaptor:FwCapProvider:model managed
        object property"
    ::= { cfprAdaptorFwCapProviderEntry 12 }

cfprAdaptorFwCapProviderVendor OBJECT-TYPE
    SYNTAX       SnmpAdminString
    MAX-ACCESS   read-only
    STATUS       current
    DESCRIPTION
        "Cisco Firepower adaptor:FwCapProvider:vendor managed
        object property"
    ::= { cfprAdaptorFwCapProviderEntry 13 }

cfprAdaptorFwCapProviderVersion OBJECT-TYPE
    SYNTAX       SnmpAdminString
    MAX-ACCESS   read-only
    STATUS       current
    DESCRIPTION
        "Cisco Firepower adaptor:FwCapProvider:version
        managed object property"
    ::= { cfprAdaptorFwCapProviderEntry 14 }

cfprAdaptorHostEthIfTable OBJECT-TYPE
    SYNTAX           SEQUENCE OF CfprAdaptorHostEthIfEntry
    MAX-ACCESS       not-accessible
    STATUS           current
    DESCRIPTION
        "Cisco Firepower adaptor:HostEthIf managed object table"
    ::= { cfprAdaptorObjects 56 }

cfprAdaptorHostEthIfEntry OBJECT-TYPE
    SYNTAX           CfprAdaptorHostEthIfEntry
    MAX-ACCESS       not-accessible
    STATUS           current
    DESCRIPTION
        "Entry for the cfprAdaptorHostEthIfTable table."
    INDEX { cfprAdaptorHostEthIfInstanceId }
    ::= { cfprAdaptorHostEthIfTable 1 }

CfprAdaptorHostEthIfEntry ::= SEQUENCE {
    cfprAdaptorHostEthIfInstanceId                                   CfprManagedObjectId,
    cfprAdaptorHostEthIfDn                                           CfprManagedObjectDn,
    cfprAdaptorHostEthIfRn                                           SnmpAdminString,
    cfprAdaptorHostEthIfAdminState                                   CfprAdaptorHostIfAdminState,
    cfprAdaptorHostEthIfBootDev                                      CfprAdaptorHostIfBootDev,
    cfprAdaptorHostEthIfChassisId                                    Gauge32,
    cfprAdaptorHostEthIfDiscovery                                    CfprEtherSatelliteConnectionDisc,
    cfprAdaptorHostEthIfEpDn                                         SnmpAdminString,
    cfprAdaptorHostEthIfFltAggr                                      Unsigned64,
    cfprAdaptorHostEthIfFsmDescr                                     SnmpAdminString,
    cfprAdaptorHostEthIfFsmPrev                                      SnmpAdminString,
    cfprAdaptorHostEthIfFsmProgr                                     Gauge32,
    cfprAdaptorHostEthIfFsmRmtInvErrCode                             Gauge32,
    cfprAdaptorHostEthIfFsmRmtInvErrDescr                            SnmpAdminString,
    cfprAdaptorHostEthIfFsmRmtInvRslt                                CfprConditionRemoteInvRslt,
    cfprAdaptorHostEthIfFsmStageDescr                                SnmpAdminString,
    cfprAdaptorHostEthIfFsmStamp                                     DateAndTime,
    cfprAdaptorHostEthIfFsmStatus                                    SnmpAdminString,
    cfprAdaptorHostEthIfFsmTry                                       Gauge32,
    cfprAdaptorHostEthIfHostPort                                     CfprAdaptorHostEthIfHostPort,
    cfprAdaptorHostEthIfId                                           Gauge32,
    cfprAdaptorHostEthIfIfRole                                       CfprNetworkPortRole,
    cfprAdaptorHostEthIfIfType                                       CfprNetworkPhysEpIfType,
    cfprAdaptorHostEthIfLc                                           CfprFsmLifecycle,
    cfprAdaptorHostEthIfLinkState                                    CfprAdaptorLinkState,
    cfprAdaptorHostEthIfLocale                                       CfprNetworkLocale,
    cfprAdaptorHostEthIfMac                                          MacAddress,
    cfprAdaptorHostEthIfModel                                        SnmpAdminString,
    cfprAdaptorHostEthIfMtu                                          Gauge32,
    cfprAdaptorHostEthIfName                                         SnmpAdminString,
    cfprAdaptorHostEthIfOperQualifierReason                          SnmpAdminString,
    cfprAdaptorHostEthIfOperState                                    CfprEquipmentOperability,
    cfprAdaptorHostEthIfOperability                                  CfprEquipmentOperability,
    cfprAdaptorHostEthIfOrder                                        Gauge32,
    cfprAdaptorHostEthIfOriginalMac                                  MacAddress,
    cfprAdaptorHostEthIfPciAddr                                      SnmpAdminString,
    cfprAdaptorHostEthIfPciFunc                                      Gauge32,
    cfprAdaptorHostEthIfPciSlot                                      Gauge32,
    cfprAdaptorHostEthIfPeerChassisId                                Gauge32,
    cfprAdaptorHostEthIfPeerDn                                       SnmpAdminString,
    cfprAdaptorHostEthIfPeerPortId                                   Gauge32,
    cfprAdaptorHostEthIfPeerSlotId                                   Gauge32,
    cfprAdaptorHostEthIfPerf                                         CfprEquipmentSensorThresholdStatus,
    cfprAdaptorHostEthIfPfDn                                         SnmpAdminString,
    cfprAdaptorHostEthIfPortId                                       Gauge32,
    cfprAdaptorHostEthIfPower                                        CfprEquipmentPowerState,
    cfprAdaptorHostEthIfPresence                                     CfprEquipmentPresence,
    cfprAdaptorHostEthIfPurpose                                      CfprAdaptorPurpose,
    cfprAdaptorHostEthIfRevision                                     SnmpAdminString,
    cfprAdaptorHostEthIfSerial                                       SnmpAdminString,
    cfprAdaptorHostEthIfSide                                         CfprNetworkSide,
    cfprAdaptorHostEthIfSlotId                                       Gauge32,
    cfprAdaptorHostEthIfSwitchId                                     CfprNetworkSwitchId,
    cfprAdaptorHostEthIfThermal                                      CfprEquipmentSensorThresholdStatus,
    cfprAdaptorHostEthIfTransport                                    CfprNetworkTransport,
    cfprAdaptorHostEthIfType                                         CfprNetworkConnectionType,
    cfprAdaptorHostEthIfVendor                                       SnmpAdminString,
    cfprAdaptorHostEthIfVirtualizationPreference                     CfprVnicVirtualizationPreferenceType,
    cfprAdaptorHostEthIfVnicDn                                       SnmpAdminString,
    cfprAdaptorHostEthIfVoltage                                      CfprEquipmentSensorThresholdStatus,
    cfprAdaptorHostEthIfServiceState                                 CfprAdaptorServiceState,
    cfprAdaptorHostEthIfVcAdminState                                 CfprDcxAdminState
}

cfprAdaptorHostEthIfInstanceId OBJECT-TYPE
    SYNTAX       CfprManagedObjectId
    MAX-ACCESS   not-accessible
    STATUS       current
    DESCRIPTION
        "Instance identifier of the managed object."
    ::= { cfprAdaptorHostEthIfEntry 1 }

cfprAdaptorHostEthIfDn OBJECT-TYPE
    SYNTAX       CfprManagedObjectDn
    MAX-ACCESS   read-only
    STATUS       current
    DESCRIPTION
        "Cisco Firepower adaptor:HostEthIf:dn managed object property"
    ::= { cfprAdaptorHostEthIfEntry 2 }

cfprAdaptorHostEthIfRn OBJECT-TYPE
    SYNTAX       SnmpAdminString
    MAX-ACCESS   read-only
    STATUS       current
    DESCRIPTION
        "Cisco Firepower adaptor:HostEthIf:rn managed object property"
    ::= { cfprAdaptorHostEthIfEntry 3 }

cfprAdaptorHostEthIfAdminState OBJECT-TYPE
    SYNTAX       CfprAdaptorHostIfAdminState
    MAX-ACCESS   read-only
    STATUS       current
    DESCRIPTION
        "Cisco Firepower adaptor:HostEthIf:adminState managed
        object property"
    ::= { cfprAdaptorHostEthIfEntry 4 }

cfprAdaptorHostEthIfBootDev OBJECT-TYPE
    SYNTAX       CfprAdaptorHostIfBootDev
    MAX-ACCESS   read-only
    STATUS       current
    DESCRIPTION
        "Cisco Firepower adaptor:HostEthIf:bootDev managed
        object property"
    ::= { cfprAdaptorHostEthIfEntry 5 }

cfprAdaptorHostEthIfChassisId OBJECT-TYPE
    SYNTAX       Gauge32
    MAX-ACCESS   read-only
    STATUS       current
    DESCRIPTION
        "Cisco Firepower adaptor:HostEthIf:chassisId managed
        object property"
    ::= { cfprAdaptorHostEthIfEntry 6 }

cfprAdaptorHostEthIfDiscovery OBJECT-TYPE
    SYNTAX       CfprEtherSatelliteConnectionDisc
    MAX-ACCESS   read-only
    STATUS       current
    DESCRIPTION
        "Cisco Firepower adaptor:HostEthIf:discovery managed
        object property"
    ::= { cfprAdaptorHostEthIfEntry 7 }

cfprAdaptorHostEthIfEpDn OBJECT-TYPE
    SYNTAX       SnmpAdminString
    MAX-ACCESS   read-only
    STATUS       current
    DESCRIPTION
        "Cisco Firepower adaptor:HostEthIf:epDn managed object property"
    ::= { cfprAdaptorHostEthIfEntry 8 }

cfprAdaptorHostEthIfFltAggr OBJECT-TYPE
    SYNTAX       Unsigned64
    MAX-ACCESS   read-only
    STATUS       current
    DESCRIPTION
        "Cisco Firepower adaptor:HostEthIf:fltAggr managed
        object property"
    ::= { cfprAdaptorHostEthIfEntry 9 }

cfprAdaptorHostEthIfFsmDescr OBJECT-TYPE
    SYNTAX       SnmpAdminString
    MAX-ACCESS   read-only
    STATUS       current
    DESCRIPTION
        "Cisco Firepower adaptor:HostEthIf:fsmDescr managed
        object property"
    ::= { cfprAdaptorHostEthIfEntry 10 }

cfprAdaptorHostEthIfFsmPrev OBJECT-TYPE
    SYNTAX       SnmpAdminString
    MAX-ACCESS   read-only
    STATUS       current
    DESCRIPTION
        "Cisco Firepower adaptor:HostEthIf:fsmPrev managed
        object property"
    ::= { cfprAdaptorHostEthIfEntry 11 }

cfprAdaptorHostEthIfFsmProgr OBJECT-TYPE
    SYNTAX       Gauge32
    MAX-ACCESS   read-only
    STATUS       current
    DESCRIPTION
        "Cisco Firepower adaptor:HostEthIf:fsmProgr managed
        object property"
    ::= { cfprAdaptorHostEthIfEntry 12 }

cfprAdaptorHostEthIfFsmRmtInvErrCode OBJECT-TYPE
    SYNTAX       Gauge32
    MAX-ACCESS   read-only
    STATUS       current
    DESCRIPTION
        "Cisco Firepower adaptor:HostEthIf:fsmRmtInvErrCode
        managed object property"
    ::= { cfprAdaptorHostEthIfEntry 13 }

cfprAdaptorHostEthIfFsmRmtInvErrDescr OBJECT-TYPE
    SYNTAX       SnmpAdminString
    MAX-ACCESS   read-only
    STATUS       current
    DESCRIPTION
        "Cisco Firepower adaptor:HostEthIf:fsmRmtInvErrDescr
        managed object property"
    ::= { cfprAdaptorHostEthIfEntry 14 }

cfprAdaptorHostEthIfFsmRmtInvRslt OBJECT-TYPE
    SYNTAX       CfprConditionRemoteInvRslt
    MAX-ACCESS   read-only
    STATUS       current
    DESCRIPTION
        "Cisco Firepower adaptor:HostEthIf:fsmRmtInvRslt
        managed object property"
    ::= { cfprAdaptorHostEthIfEntry 15 }

cfprAdaptorHostEthIfFsmStageDescr OBJECT-TYPE
    SYNTAX       SnmpAdminString
    MAX-ACCESS   read-only
    STATUS       current
    DESCRIPTION
        "Cisco Firepower adaptor:HostEthIf:fsmStageDescr
        managed object property"
    ::= { cfprAdaptorHostEthIfEntry 16 }

cfprAdaptorHostEthIfFsmStamp OBJECT-TYPE
    SYNTAX       DateAndTime
    MAX-ACCESS   read-only
    STATUS       current
    DESCRIPTION
        "Cisco Firepower adaptor:HostEthIf:fsmStamp managed
        object property"
    ::= { cfprAdaptorHostEthIfEntry 17 }

cfprAdaptorHostEthIfFsmStatus OBJECT-TYPE
    SYNTAX       SnmpAdminString
    MAX-ACCESS   read-only
    STATUS       current
    DESCRIPTION
        "Cisco Firepower adaptor:HostEthIf:fsmStatus managed
        object property"
    ::= { cfprAdaptorHostEthIfEntry 18 }

cfprAdaptorHostEthIfFsmTry OBJECT-TYPE
    SYNTAX       Gauge32
    MAX-ACCESS   read-only
    STATUS       current
    DESCRIPTION
        "Cisco Firepower adaptor:HostEthIf:fsmTry managed object property"
    ::= { cfprAdaptorHostEthIfEntry 19 }

cfprAdaptorHostEthIfHostPort OBJECT-TYPE
    SYNTAX       CfprAdaptorHostEthIfHostPort
    MAX-ACCESS   read-only
    STATUS       current
    DESCRIPTION
        "Cisco Firepower adaptor:HostEthIf:hostPort managed
        object property"
    ::= { cfprAdaptorHostEthIfEntry 20 }

cfprAdaptorHostEthIfId OBJECT-TYPE
    SYNTAX       Gauge32
    MAX-ACCESS   read-only
    STATUS       current
    DESCRIPTION
        "Cisco Firepower adaptor:HostEthIf:id managed object property"
    ::= { cfprAdaptorHostEthIfEntry 21 }

cfprAdaptorHostEthIfIfRole OBJECT-TYPE
    SYNTAX       CfprNetworkPortRole
    MAX-ACCESS   read-only
    STATUS       current
    DESCRIPTION
        "Cisco Firepower adaptor:HostEthIf:ifRole managed object property"
    ::= { cfprAdaptorHostEthIfEntry 22 }

cfprAdaptorHostEthIfIfType OBJECT-TYPE
    SYNTAX       CfprNetworkPhysEpIfType
    MAX-ACCESS   read-only
    STATUS       current
    DESCRIPTION
        "Cisco Firepower adaptor:HostEthIf:ifType managed object property"
    ::= { cfprAdaptorHostEthIfEntry 23 }

cfprAdaptorHostEthIfLc OBJECT-TYPE
    SYNTAX       CfprFsmLifecycle
    MAX-ACCESS   read-only
    STATUS       current
    DESCRIPTION
        "Cisco Firepower adaptor:HostEthIf:lc managed object property"
    ::= { cfprAdaptorHostEthIfEntry 24 }

cfprAdaptorHostEthIfLinkState OBJECT-TYPE
    SYNTAX       CfprAdaptorLinkState
    MAX-ACCESS   read-only
    STATUS       current
    DESCRIPTION
        "Cisco Firepower adaptor:HostEthIf:linkState managed
        object property"
    ::= { cfprAdaptorHostEthIfEntry 25 }

cfprAdaptorHostEthIfLocale OBJECT-TYPE
    SYNTAX       CfprNetworkLocale
    MAX-ACCESS   read-only
    STATUS       current
    DESCRIPTION
        "Cisco Firepower adaptor:HostEthIf:locale managed object property"
    ::= { cfprAdaptorHostEthIfEntry 26 }

cfprAdaptorHostEthIfMac OBJECT-TYPE
    SYNTAX       MacAddress
    MAX-ACCESS   read-only
    STATUS       current
    DESCRIPTION
        "Cisco Firepower adaptor:HostEthIf:mac managed object property"
    ::= { cfprAdaptorHostEthIfEntry 27 }

cfprAdaptorHostEthIfModel OBJECT-TYPE
    SYNTAX       SnmpAdminString
    MAX-ACCESS   read-only
    STATUS       current
    DESCRIPTION
        "Cisco Firepower adaptor:HostEthIf:model managed object property"
    ::= { cfprAdaptorHostEthIfEntry 28 }

cfprAdaptorHostEthIfMtu OBJECT-TYPE
    SYNTAX       Gauge32
    MAX-ACCESS   read-only
    STATUS       current
    DESCRIPTION
        "Cisco Firepower adaptor:HostEthIf:mtu managed object property"
    ::= { cfprAdaptorHostEthIfEntry 29 }

cfprAdaptorHostEthIfName OBJECT-TYPE
    SYNTAX       SnmpAdminString
    MAX-ACCESS   read-only
    STATUS       current
    DESCRIPTION
        "Cisco Firepower adaptor:HostEthIf:name managed object property"
    ::= { cfprAdaptorHostEthIfEntry 30 }

cfprAdaptorHostEthIfOperQualifierReason OBJECT-TYPE
    SYNTAX       SnmpAdminString
    MAX-ACCESS   read-only
    STATUS       current
    DESCRIPTION
        "Cisco Firepower adaptor:HostEthIf:operQualifierReason
        managed object property"
    ::= { cfprAdaptorHostEthIfEntry 31 }

cfprAdaptorHostEthIfOperState OBJECT-TYPE
    SYNTAX       CfprEquipmentOperability
    MAX-ACCESS   read-only
    STATUS       current
    DESCRIPTION
        "Cisco Firepower adaptor:HostEthIf:operState managed
        object property"
    ::= { cfprAdaptorHostEthIfEntry 32 }

cfprAdaptorHostEthIfOperability OBJECT-TYPE
    SYNTAX       CfprEquipmentOperability
    MAX-ACCESS   read-only
    STATUS       current
    DESCRIPTION
        "Cisco Firepower adaptor:HostEthIf:operability
        managed object property"
    ::= { cfprAdaptorHostEthIfEntry 33 }

cfprAdaptorHostEthIfOrder OBJECT-TYPE
    SYNTAX       Gauge32
    MAX-ACCESS   read-only
    STATUS       current
    DESCRIPTION
        "Cisco Firepower adaptor:HostEthIf:order managed object property"
    ::= { cfprAdaptorHostEthIfEntry 34 }

cfprAdaptorHostEthIfOriginalMac OBJECT-TYPE
    SYNTAX       MacAddress
    MAX-ACCESS   read-only
    STATUS       current
    DESCRIPTION
        "Cisco Firepower adaptor:HostEthIf:originalMac
        managed object property"
    ::= { cfprAdaptorHostEthIfEntry 35 }

cfprAdaptorHostEthIfPciAddr OBJECT-TYPE
    SYNTAX       SnmpAdminString
    MAX-ACCESS   read-only
    STATUS       current
    DESCRIPTION
        "Cisco Firepower adaptor:HostEthIf:pciAddr managed
        object property"
    ::= { cfprAdaptorHostEthIfEntry 36 }

cfprAdaptorHostEthIfPciFunc OBJECT-TYPE
    SYNTAX       Gauge32
    MAX-ACCESS   read-only
    STATUS       current
    DESCRIPTION
        "Cisco Firepower adaptor:HostEthIf:pciFunc managed
        object property"
    ::= { cfprAdaptorHostEthIfEntry 37 }

cfprAdaptorHostEthIfPciSlot OBJECT-TYPE
    SYNTAX       Gauge32
    MAX-ACCESS   read-only
    STATUS       current
    DESCRIPTION
        "Cisco Firepower adaptor:HostEthIf:pciSlot managed
        object property"
    ::= { cfprAdaptorHostEthIfEntry 38 }

cfprAdaptorHostEthIfPeerChassisId OBJECT-TYPE
    SYNTAX       Gauge32
    MAX-ACCESS   read-only
    STATUS       current
    DESCRIPTION
        "Cisco Firepower adaptor:HostEthIf:peerChassisId
        managed object property"
    ::= { cfprAdaptorHostEthIfEntry 39 }

cfprAdaptorHostEthIfPeerDn OBJECT-TYPE
    SYNTAX       SnmpAdminString
    MAX-ACCESS   read-only
    STATUS       current
    DESCRIPTION
        "Cisco Firepower adaptor:HostEthIf:peerDn managed object property"
    ::= { cfprAdaptorHostEthIfEntry 40 }

cfprAdaptorHostEthIfPeerPortId OBJECT-TYPE
    SYNTAX       Gauge32
    MAX-ACCESS   read-only
    STATUS       current
    DESCRIPTION
        "Cisco Firepower adaptor:HostEthIf:peerPortId managed
        object property"
    ::= { cfprAdaptorHostEthIfEntry 41 }

cfprAdaptorHostEthIfPeerSlotId OBJECT-TYPE
    SYNTAX       Gauge32
    MAX-ACCESS   read-only
    STATUS       current
    DESCRIPTION
        "Cisco Firepower adaptor:HostEthIf:peerSlotId managed
        object property"
    ::= { cfprAdaptorHostEthIfEntry 42 }

cfprAdaptorHostEthIfPerf OBJECT-TYPE
    SYNTAX       CfprEquipmentSensorThresholdStatus
    MAX-ACCESS   read-only
    STATUS       current
    DESCRIPTION
        "Cisco Firepower adaptor:HostEthIf:perf managed object property"
    ::= { cfprAdaptorHostEthIfEntry 43 }

cfprAdaptorHostEthIfPfDn OBJECT-TYPE
    SYNTAX       SnmpAdminString
    MAX-ACCESS   read-only
    STATUS       current
    DESCRIPTION
        "Cisco Firepower adaptor:HostEthIf:pfDn managed object property"
    ::= { cfprAdaptorHostEthIfEntry 44 }

cfprAdaptorHostEthIfPortId OBJECT-TYPE
    SYNTAX       Gauge32
    MAX-ACCESS   read-only
    STATUS       current
    DESCRIPTION
        "Cisco Firepower adaptor:HostEthIf:portId managed object property"
    ::= { cfprAdaptorHostEthIfEntry 45 }

cfprAdaptorHostEthIfPower OBJECT-TYPE
    SYNTAX       CfprEquipmentPowerState
    MAX-ACCESS   read-only
    STATUS       current
    DESCRIPTION
        "Cisco Firepower adaptor:HostEthIf:power managed object property"
    ::= { cfprAdaptorHostEthIfEntry 46 }

cfprAdaptorHostEthIfPresence OBJECT-TYPE
    SYNTAX       CfprEquipmentPresence
    MAX-ACCESS   read-only
    STATUS       current
    DESCRIPTION
        "Cisco Firepower adaptor:HostEthIf:presence managed
        object property"
    ::= { cfprAdaptorHostEthIfEntry 47 }

cfprAdaptorHostEthIfPurpose OBJECT-TYPE
    SYNTAX       CfprAdaptorPurpose
    MAX-ACCESS   read-only
    STATUS       current
    DESCRIPTION
        "Cisco Firepower adaptor:HostEthIf:purpose managed
        object property"
    ::= { cfprAdaptorHostEthIfEntry 48 }

cfprAdaptorHostEthIfRevision OBJECT-TYPE
    SYNTAX       SnmpAdminString
    MAX-ACCESS   read-only
    STATUS       current
    DESCRIPTION
        "Cisco Firepower adaptor:HostEthIf:revision managed
        object property"
    ::= { cfprAdaptorHostEthIfEntry 49 }

cfprAdaptorHostEthIfSerial OBJECT-TYPE
    SYNTAX       SnmpAdminString
    MAX-ACCESS   read-only
    STATUS       current
    DESCRIPTION
        "Cisco Firepower adaptor:HostEthIf:serial managed object property"
    ::= { cfprAdaptorHostEthIfEntry 50 }

cfprAdaptorHostEthIfSide OBJECT-TYPE
    SYNTAX       CfprNetworkSide
    MAX-ACCESS   read-only
    STATUS       current
    DESCRIPTION
        "Cisco Firepower adaptor:HostEthIf:side managed object property"
    ::= { cfprAdaptorHostEthIfEntry 51 }

cfprAdaptorHostEthIfSlotId OBJECT-TYPE
    SYNTAX       Gauge32
    MAX-ACCESS   read-only
    STATUS       current
    DESCRIPTION
        "Cisco Firepower adaptor:HostEthIf:slotId managed object property"
    ::= { cfprAdaptorHostEthIfEntry 52 }

cfprAdaptorHostEthIfSwitchId OBJECT-TYPE
    SYNTAX       CfprNetworkSwitchId
    MAX-ACCESS   read-only
    STATUS       current
    DESCRIPTION
        "Cisco Firepower adaptor:HostEthIf:switchId managed
        object property"
    ::= { cfprAdaptorHostEthIfEntry 53 }

cfprAdaptorHostEthIfThermal OBJECT-TYPE
    SYNTAX       CfprEquipmentSensorThresholdStatus
    MAX-ACCESS   read-only
    STATUS       current
    DESCRIPTION
        "Cisco Firepower adaptor:HostEthIf:thermal managed
        object property"
    ::= { cfprAdaptorHostEthIfEntry 54 }

cfprAdaptorHostEthIfTransport OBJECT-TYPE
    SYNTAX       CfprNetworkTransport
    MAX-ACCESS   read-only
    STATUS       current
    DESCRIPTION
        "Cisco Firepower adaptor:HostEthIf:transport managed
        object property"
    ::= { cfprAdaptorHostEthIfEntry 55 }

cfprAdaptorHostEthIfType OBJECT-TYPE
    SYNTAX       CfprNetworkConnectionType
    MAX-ACCESS   read-only
    STATUS       current
    DESCRIPTION
        "Cisco Firepower adaptor:HostEthIf:type managed object property"
    ::= { cfprAdaptorHostEthIfEntry 56 }

cfprAdaptorHostEthIfVendor OBJECT-TYPE
    SYNTAX       SnmpAdminString
    MAX-ACCESS   read-only
    STATUS       current
    DESCRIPTION
        "Cisco Firepower adaptor:HostEthIf:vendor managed object property"
    ::= { cfprAdaptorHostEthIfEntry 57 }

cfprAdaptorHostEthIfVirtualizationPreference OBJECT-TYPE
    SYNTAX       CfprVnicVirtualizationPreferenceType
    MAX-ACCESS   read-only
    STATUS       current
    DESCRIPTION
        "Cisco Firepower adaptor:HostEthIf:virtualizationPreference
        managed object property"
    ::= { cfprAdaptorHostEthIfEntry 58 }

cfprAdaptorHostEthIfVnicDn OBJECT-TYPE
    SYNTAX       SnmpAdminString
    MAX-ACCESS   read-only
    STATUS       current
    DESCRIPTION
        "Cisco Firepower adaptor:HostEthIf:vnicDn managed object property"
    ::= { cfprAdaptorHostEthIfEntry 59 }

cfprAdaptorHostEthIfVoltage OBJECT-TYPE
    SYNTAX       CfprEquipmentSensorThresholdStatus
    MAX-ACCESS   read-only
    STATUS       current
    DESCRIPTION
        "Cisco Firepower adaptor:HostEthIf:voltage managed
        object property"
    ::= { cfprAdaptorHostEthIfEntry 60 }

cfprAdaptorHostEthIfServiceState OBJECT-TYPE
    SYNTAX       CfprAdaptorServiceState
    MAX-ACCESS   read-only
    STATUS       current
    DESCRIPTION
        "Cisco Firepower adaptor:HostEthIf:serviceState
        managed object property"
    ::= { cfprAdaptorHostEthIfEntry 61 }

cfprAdaptorHostEthIfVcAdminState OBJECT-TYPE
    SYNTAX       CfprDcxAdminState
    MAX-ACCESS   read-only
    STATUS       current
    DESCRIPTION
        "Cisco Firepower adaptor:HostEthIf:vcAdminState
        managed object property"
    ::= { cfprAdaptorHostEthIfEntry 62 }

cfprAdaptorHostEthIfFsmTable OBJECT-TYPE
    SYNTAX           SEQUENCE OF CfprAdaptorHostEthIfFsmEntry
    MAX-ACCESS       not-accessible
    STATUS           current
    DESCRIPTION
        "Cisco Firepower adaptor:HostEthIfFsm managed object table"
    ::= { cfprAdaptorObjects 57 }

cfprAdaptorHostEthIfFsmEntry OBJECT-TYPE
    SYNTAX           CfprAdaptorHostEthIfFsmEntry
    MAX-ACCESS       not-accessible
    STATUS           current
    DESCRIPTION
        "Entry for the cfprAdaptorHostEthIfFsmTable table."
    INDEX { cfprAdaptorHostEthIfFsmInstanceId }
    ::= { cfprAdaptorHostEthIfFsmTable 1 }

CfprAdaptorHostEthIfFsmEntry ::= SEQUENCE {
    cfprAdaptorHostEthIfFsmInstanceId                                CfprManagedObjectId,
    cfprAdaptorHostEthIfFsmDn                                        CfprManagedObjectDn,
    cfprAdaptorHostEthIfFsmRn                                        SnmpAdminString,
    cfprAdaptorHostEthIfFsmCompletionTime                            DateAndTime,
    cfprAdaptorHostEthIfFsmCurrentFsm                                CfprAdaptorHostEthIfFsmCurrentFsm,
    cfprAdaptorHostEthIfFsmDescrData                                 SnmpAdminString,
    cfprAdaptorHostEthIfFsmFsmStatus                                 CfprFsmFsmStageStatus,
    cfprAdaptorHostEthIfFsmProgress                                  Gauge32,
    cfprAdaptorHostEthIfFsmRmtErrCode                                Gauge32,
    cfprAdaptorHostEthIfFsmRmtErrDescr                               SnmpAdminString,
    cfprAdaptorHostEthIfFsmRmtRslt                                   CfprConditionRemoteInvRslt
}

cfprAdaptorHostEthIfFsmInstanceId OBJECT-TYPE
    SYNTAX       CfprManagedObjectId
    MAX-ACCESS   not-accessible
    STATUS       current
    DESCRIPTION
        "Instance identifier of the managed object."
    ::= { cfprAdaptorHostEthIfFsmEntry 1 }

cfprAdaptorHostEthIfFsmDn OBJECT-TYPE
    SYNTAX       CfprManagedObjectDn
    MAX-ACCESS   read-only
    STATUS       current
    DESCRIPTION
        "Cisco Firepower adaptor:HostEthIfFsm:dn managed object property"
    ::= { cfprAdaptorHostEthIfFsmEntry 2 }

cfprAdaptorHostEthIfFsmRn OBJECT-TYPE
    SYNTAX       SnmpAdminString
    MAX-ACCESS   read-only
    STATUS       current
    DESCRIPTION
        "Cisco Firepower adaptor:HostEthIfFsm:rn managed object property"
    ::= { cfprAdaptorHostEthIfFsmEntry 3 }

cfprAdaptorHostEthIfFsmCompletionTime OBJECT-TYPE
    SYNTAX       DateAndTime
    MAX-ACCESS   read-only
    STATUS       current
    DESCRIPTION
        "Cisco Firepower adaptor:HostEthIfFsm:completionTime
        managed object property"
    ::= { cfprAdaptorHostEthIfFsmEntry 4 }

cfprAdaptorHostEthIfFsmCurrentFsm OBJECT-TYPE
    SYNTAX       CfprAdaptorHostEthIfFsmCurrentFsm
    MAX-ACCESS   read-only
    STATUS       current
    DESCRIPTION
        "Cisco Firepower adaptor:HostEthIfFsm:currentFsm
        managed object property"
    ::= { cfprAdaptorHostEthIfFsmEntry 5 }

cfprAdaptorHostEthIfFsmDescrData OBJECT-TYPE
    SYNTAX       SnmpAdminString
    MAX-ACCESS   read-only
    STATUS       current
    DESCRIPTION
        "Cisco Firepower adaptor:HostEthIfFsm:descr managed
        object property"
    ::= { cfprAdaptorHostEthIfFsmEntry 6 }

cfprAdaptorHostEthIfFsmFsmStatus OBJECT-TYPE
    SYNTAX       CfprFsmFsmStageStatus
    MAX-ACCESS   read-only
    STATUS       current
    DESCRIPTION
        "Cisco Firepower adaptor:HostEthIfFsm:fsmStatus
        managed object property"
    ::= { cfprAdaptorHostEthIfFsmEntry 7 }

cfprAdaptorHostEthIfFsmProgress OBJECT-TYPE
    SYNTAX       Gauge32
    MAX-ACCESS   read-only
    STATUS       current
    DESCRIPTION
        "Cisco Firepower adaptor:HostEthIfFsm:progress
        managed object property"
    ::= { cfprAdaptorHostEthIfFsmEntry 8 }

cfprAdaptorHostEthIfFsmRmtErrCode OBJECT-TYPE
    SYNTAX       Gauge32
    MAX-ACCESS   read-only
    STATUS       current
    DESCRIPTION
        "Cisco Firepower adaptor:HostEthIfFsm:rmtErrCode
        managed object property"
    ::= { cfprAdaptorHostEthIfFsmEntry 9 }

cfprAdaptorHostEthIfFsmRmtErrDescr OBJECT-TYPE
    SYNTAX       SnmpAdminString
    MAX-ACCESS   read-only
    STATUS       current
    DESCRIPTION
        "Cisco Firepower adaptor:HostEthIfFsm:rmtErrDescr
        managed object property"
    ::= { cfprAdaptorHostEthIfFsmEntry 10 }

cfprAdaptorHostEthIfFsmRmtRslt OBJECT-TYPE
    SYNTAX       CfprConditionRemoteInvRslt
    MAX-ACCESS   read-only
    STATUS       current
    DESCRIPTION
        "Cisco Firepower adaptor:HostEthIfFsm:rmtRslt managed
        object property"
    ::= { cfprAdaptorHostEthIfFsmEntry 11 }

cfprAdaptorHostEthIfFsmStageTable OBJECT-TYPE
    SYNTAX           SEQUENCE OF CfprAdaptorHostEthIfFsmStageEntry
    MAX-ACCESS       not-accessible
    STATUS           current
    DESCRIPTION
        "Cisco Firepower adaptor:HostEthIfFsmStage managed object table"
    ::= { cfprAdaptorObjects 58 }

cfprAdaptorHostEthIfFsmStageEntry OBJECT-TYPE
    SYNTAX           CfprAdaptorHostEthIfFsmStageEntry
    MAX-ACCESS       not-accessible
    STATUS           current
    DESCRIPTION
        "Entry for the cfprAdaptorHostEthIfFsmStageTable table."
    INDEX { cfprAdaptorHostEthIfFsmStageInstanceId }
    ::= { cfprAdaptorHostEthIfFsmStageTable 1 }

CfprAdaptorHostEthIfFsmStageEntry ::= SEQUENCE {
    cfprAdaptorHostEthIfFsmStageInstanceId                           CfprManagedObjectId,
    cfprAdaptorHostEthIfFsmStageDn                                   CfprManagedObjectDn,
    cfprAdaptorHostEthIfFsmStageRn                                   SnmpAdminString,
    cfprAdaptorHostEthIfFsmStageDescrData                            SnmpAdminString,
    cfprAdaptorHostEthIfFsmStageLastUpdateTime                       DateAndTime,
    cfprAdaptorHostEthIfFsmStageName                                 CfprAdaptorHostEthIfFsmStageName,
    cfprAdaptorHostEthIfFsmStageOrder                                Gauge32,
    cfprAdaptorHostEthIfFsmStageRetry                                Gauge32,
    cfprAdaptorHostEthIfFsmStageStageStatus                          CfprFsmFsmStageStatus
}

cfprAdaptorHostEthIfFsmStageInstanceId OBJECT-TYPE
    SYNTAX       CfprManagedObjectId
    MAX-ACCESS   not-accessible
    STATUS       current
    DESCRIPTION
        "Instance identifier of the managed object."
    ::= { cfprAdaptorHostEthIfFsmStageEntry 1 }

cfprAdaptorHostEthIfFsmStageDn OBJECT-TYPE
    SYNTAX       CfprManagedObjectDn
    MAX-ACCESS   read-only
    STATUS       current
    DESCRIPTION
        "Cisco Firepower adaptor:HostEthIfFsmStage:dn managed
        object property"
    ::= { cfprAdaptorHostEthIfFsmStageEntry 2 }

cfprAdaptorHostEthIfFsmStageRn OBJECT-TYPE
    SYNTAX       SnmpAdminString
    MAX-ACCESS   read-only
    STATUS       current
    DESCRIPTION
        "Cisco Firepower adaptor:HostEthIfFsmStage:rn managed
        object property"
    ::= { cfprAdaptorHostEthIfFsmStageEntry 3 }

cfprAdaptorHostEthIfFsmStageDescrData OBJECT-TYPE
    SYNTAX       SnmpAdminString
    MAX-ACCESS   read-only
    STATUS       current
    DESCRIPTION
        "Cisco Firepower adaptor:HostEthIfFsmStage:descr
        managed object property"
    ::= { cfprAdaptorHostEthIfFsmStageEntry 4 }

cfprAdaptorHostEthIfFsmStageLastUpdateTime OBJECT-TYPE
    SYNTAX       DateAndTime
    MAX-ACCESS   read-only
    STATUS       current
    DESCRIPTION
        "Cisco Firepower adaptor:HostEthIfFsmStage:lastUpdateTime
        managed object property"
    ::= { cfprAdaptorHostEthIfFsmStageEntry 5 }

cfprAdaptorHostEthIfFsmStageName OBJECT-TYPE
    SYNTAX       CfprAdaptorHostEthIfFsmStageName
    MAX-ACCESS   read-only
    STATUS       current
    DESCRIPTION
        "Cisco Firepower adaptor:HostEthIfFsmStage:name
        managed object property"
    ::= { cfprAdaptorHostEthIfFsmStageEntry 6 }

cfprAdaptorHostEthIfFsmStageOrder OBJECT-TYPE
    SYNTAX       Gauge32
    MAX-ACCESS   read-only
    STATUS       current
    DESCRIPTION
        "Cisco Firepower adaptor:HostEthIfFsmStage:order
        managed object property"
    ::= { cfprAdaptorHostEthIfFsmStageEntry 7 }

cfprAdaptorHostEthIfFsmStageRetry OBJECT-TYPE
    SYNTAX       Gauge32
    MAX-ACCESS   read-only
    STATUS       current
    DESCRIPTION
        "Cisco Firepower adaptor:HostEthIfFsmStage:retry
        managed object property"
    ::= { cfprAdaptorHostEthIfFsmStageEntry 8 }

cfprAdaptorHostEthIfFsmStageStageStatus OBJECT-TYPE
    SYNTAX       CfprFsmFsmStageStatus
    MAX-ACCESS   read-only
    STATUS       current
    DESCRIPTION
        "Cisco Firepower adaptor:HostEthIfFsmStage:stageStatus
        managed object property"
    ::= { cfprAdaptorHostEthIfFsmStageEntry 9 }

cfprAdaptorHostEthIfFsmTaskTable OBJECT-TYPE
    SYNTAX           SEQUENCE OF CfprAdaptorHostEthIfFsmTaskEntry
    MAX-ACCESS       not-accessible
    STATUS           current
    DESCRIPTION
        "Cisco Firepower adaptor:HostEthIfFsmTask managed object table"
    ::= { cfprAdaptorObjects 59 }

cfprAdaptorHostEthIfFsmTaskEntry OBJECT-TYPE
    SYNTAX           CfprAdaptorHostEthIfFsmTaskEntry
    MAX-ACCESS       not-accessible
    STATUS           current
    DESCRIPTION
        "Entry for the cfprAdaptorHostEthIfFsmTaskTable table."
    INDEX { cfprAdaptorHostEthIfFsmTaskInstanceId }
    ::= { cfprAdaptorHostEthIfFsmTaskTable 1 }

CfprAdaptorHostEthIfFsmTaskEntry ::= SEQUENCE {
    cfprAdaptorHostEthIfFsmTaskInstanceId                            CfprManagedObjectId,
    cfprAdaptorHostEthIfFsmTaskDn                                    CfprManagedObjectDn,
    cfprAdaptorHostEthIfFsmTaskRn                                    SnmpAdminString,
    cfprAdaptorHostEthIfFsmTaskCompletion                            CfprFsmCompletion,
    cfprAdaptorHostEthIfFsmTaskFlags                                 CfprFsmFlags,
    cfprAdaptorHostEthIfFsmTaskItem                                  CfprAdaptorHostEthIfFsmTaskItem,
    cfprAdaptorHostEthIfFsmTaskSeqId                                 Gauge32
}

cfprAdaptorHostEthIfFsmTaskInstanceId OBJECT-TYPE
    SYNTAX       CfprManagedObjectId
    MAX-ACCESS   not-accessible
    STATUS       current
    DESCRIPTION
        "Instance identifier of the managed object."
    ::= { cfprAdaptorHostEthIfFsmTaskEntry 1 }

cfprAdaptorHostEthIfFsmTaskDn OBJECT-TYPE
    SYNTAX       CfprManagedObjectDn
    MAX-ACCESS   read-only
    STATUS       current
    DESCRIPTION
        "Cisco Firepower adaptor:HostEthIfFsmTask:dn managed
        object property"
    ::= { cfprAdaptorHostEthIfFsmTaskEntry 2 }

cfprAdaptorHostEthIfFsmTaskRn OBJECT-TYPE
    SYNTAX       SnmpAdminString
    MAX-ACCESS   read-only
    STATUS       current
    DESCRIPTION
        "Cisco Firepower adaptor:HostEthIfFsmTask:rn managed
        object property"
    ::= { cfprAdaptorHostEthIfFsmTaskEntry 3 }

cfprAdaptorHostEthIfFsmTaskCompletion OBJECT-TYPE
    SYNTAX       CfprFsmCompletion
    MAX-ACCESS   read-only
    STATUS       current
    DESCRIPTION
        "Cisco Firepower adaptor:HostEthIfFsmTask:completion
        managed object property"
    ::= { cfprAdaptorHostEthIfFsmTaskEntry 4 }

cfprAdaptorHostEthIfFsmTaskFlags OBJECT-TYPE
    SYNTAX       CfprFsmFlags
    MAX-ACCESS   read-only
    STATUS       current
    DESCRIPTION
        "Cisco Firepower adaptor:HostEthIfFsmTask:flags
        managed object property"
    ::= { cfprAdaptorHostEthIfFsmTaskEntry 5 }

cfprAdaptorHostEthIfFsmTaskItem OBJECT-TYPE
    SYNTAX       CfprAdaptorHostEthIfFsmTaskItem
    MAX-ACCESS   read-only
    STATUS       current
    DESCRIPTION
        "Cisco Firepower adaptor:HostEthIfFsmTask:item
        managed object property"
    ::= { cfprAdaptorHostEthIfFsmTaskEntry 6 }

cfprAdaptorHostEthIfFsmTaskSeqId OBJECT-TYPE
    SYNTAX       Gauge32
    MAX-ACCESS   read-only
    STATUS       current
    DESCRIPTION
        "Cisco Firepower adaptor:HostEthIfFsmTask:seqId
        managed object property"
    ::= { cfprAdaptorHostEthIfFsmTaskEntry 7 }

cfprAdaptorHostEthIfProfileTable OBJECT-TYPE
    SYNTAX           SEQUENCE OF CfprAdaptorHostEthIfProfileEntry
    MAX-ACCESS       not-accessible
    STATUS           current
    DESCRIPTION
        "Cisco Firepower adaptor:HostEthIfProfile managed object table"
    ::= { cfprAdaptorObjects 60 }

cfprAdaptorHostEthIfProfileEntry OBJECT-TYPE
    SYNTAX           CfprAdaptorHostEthIfProfileEntry
    MAX-ACCESS       not-accessible
    STATUS           current
    DESCRIPTION
        "Entry for the cfprAdaptorHostEthIfProfileTable table."
    INDEX { cfprAdaptorHostEthIfProfileInstanceId }
    ::= { cfprAdaptorHostEthIfProfileTable 1 }

CfprAdaptorHostEthIfProfileEntry ::= SEQUENCE {
    cfprAdaptorHostEthIfProfileInstanceId                            CfprManagedObjectId,
    cfprAdaptorHostEthIfProfileDn                                    CfprManagedObjectDn,
    cfprAdaptorHostEthIfProfileRn                                    SnmpAdminString,
    cfprAdaptorHostEthIfProfileDescr                                 SnmpAdminString,
    cfprAdaptorHostEthIfProfileIntId                                 SnmpAdminString,
    cfprAdaptorHostEthIfProfileName                                  SnmpAdminString,
    cfprAdaptorHostEthIfProfilePolicyLevel                           Gauge32,
    cfprAdaptorHostEthIfProfilePolicyOwner                           CfprPolicyPolicyOwner
}

cfprAdaptorHostEthIfProfileInstanceId OBJECT-TYPE
    SYNTAX       CfprManagedObjectId
    MAX-ACCESS   not-accessible
    STATUS       current
    DESCRIPTION
        "Instance identifier of the managed object."
    ::= { cfprAdaptorHostEthIfProfileEntry 1 }

cfprAdaptorHostEthIfProfileDn OBJECT-TYPE
    SYNTAX       CfprManagedObjectDn
    MAX-ACCESS   read-only
    STATUS       current
    DESCRIPTION
        "Cisco Firepower adaptor:HostEthIfProfile:dn managed
        object property"
    ::= { cfprAdaptorHostEthIfProfileEntry 2 }

cfprAdaptorHostEthIfProfileRn OBJECT-TYPE
    SYNTAX       SnmpAdminString
    MAX-ACCESS   read-only
    STATUS       current
    DESCRIPTION
        "Cisco Firepower adaptor:HostEthIfProfile:rn managed
        object property"
    ::= { cfprAdaptorHostEthIfProfileEntry 3 }

cfprAdaptorHostEthIfProfileDescr OBJECT-TYPE
    SYNTAX       SnmpAdminString
    MAX-ACCESS   read-only
    STATUS       current
    DESCRIPTION
        "Cisco Firepower adaptor:HostEthIfProfile:descr
        managed object property"
    ::= { cfprAdaptorHostEthIfProfileEntry 4 }

cfprAdaptorHostEthIfProfileIntId OBJECT-TYPE
    SYNTAX       SnmpAdminString
    MAX-ACCESS   read-only
    STATUS       current
    DESCRIPTION
        "Cisco Firepower adaptor:HostEthIfProfile:intId
        managed object property"
    ::= { cfprAdaptorHostEthIfProfileEntry 5 }

cfprAdaptorHostEthIfProfileName OBJECT-TYPE
    SYNTAX       SnmpAdminString
    MAX-ACCESS   read-only
    STATUS       current
    DESCRIPTION
        "Cisco Firepower adaptor:HostEthIfProfile:name
        managed object property"
    ::= { cfprAdaptorHostEthIfProfileEntry 6 }

cfprAdaptorHostEthIfProfilePolicyLevel OBJECT-TYPE
    SYNTAX       Gauge32
    MAX-ACCESS   read-only
    STATUS       current
    DESCRIPTION
        "Cisco Firepower adaptor:HostEthIfProfile:policyLevel
        managed object property"
    ::= { cfprAdaptorHostEthIfProfileEntry 7 }

cfprAdaptorHostEthIfProfilePolicyOwner OBJECT-TYPE
    SYNTAX       CfprPolicyPolicyOwner
    MAX-ACCESS   read-only
    STATUS       current
    DESCRIPTION
        "Cisco Firepower adaptor:HostEthIfProfile:policyOwner
        managed object property"
    ::= { cfprAdaptorHostEthIfProfileEntry 8 }

cfprAdaptorHostFcIfTable OBJECT-TYPE
    SYNTAX           SEQUENCE OF CfprAdaptorHostFcIfEntry
    MAX-ACCESS       not-accessible
    STATUS           current
    DESCRIPTION
        "Cisco Firepower adaptor:HostFcIf managed object table"
    ::= { cfprAdaptorObjects 61 }

cfprAdaptorHostFcIfEntry OBJECT-TYPE
    SYNTAX           CfprAdaptorHostFcIfEntry
    MAX-ACCESS       not-accessible
    STATUS           current
    DESCRIPTION
        "Entry for the cfprAdaptorHostFcIfTable table."
    INDEX { cfprAdaptorHostFcIfInstanceId }
    ::= { cfprAdaptorHostFcIfTable 1 }

CfprAdaptorHostFcIfEntry ::= SEQUENCE {
    cfprAdaptorHostFcIfInstanceId                                    CfprManagedObjectId,
    cfprAdaptorHostFcIfDn                                            CfprManagedObjectDn,
    cfprAdaptorHostFcIfRn                                            SnmpAdminString,
    cfprAdaptorHostFcIfAdminState                                    CfprAdaptorHostFcIfAdminState,
    cfprAdaptorHostFcIfBootDev                                       CfprAdaptorHostIfBootDev,
    cfprAdaptorHostFcIfChassisId                                     Gauge32,
    cfprAdaptorHostFcIfDiscovery                                     CfprEtherSatelliteConnectionDisc,
    cfprAdaptorHostFcIfEpDn                                          SnmpAdminString,
    cfprAdaptorHostFcIfFltAggr                                       Unsigned64,
    cfprAdaptorHostFcIfFsmDescr                                      SnmpAdminString,
    cfprAdaptorHostFcIfFsmPrev                                       SnmpAdminString,
    cfprAdaptorHostFcIfFsmProgr                                      Gauge32,
    cfprAdaptorHostFcIfFsmRmtInvErrCode                              Gauge32,
    cfprAdaptorHostFcIfFsmRmtInvErrDescr                             SnmpAdminString,
    cfprAdaptorHostFcIfFsmRmtInvRslt                                 CfprConditionRemoteInvRslt,
    cfprAdaptorHostFcIfFsmStageDescr                                 SnmpAdminString,
    cfprAdaptorHostFcIfFsmStamp                                      DateAndTime,
    cfprAdaptorHostFcIfFsmStatus                                     SnmpAdminString,
    cfprAdaptorHostFcIfFsmTry                                        Gauge32,
    cfprAdaptorHostFcIfHostPort                                      CfprAdaptorHostFcIfHostPort,
    cfprAdaptorHostFcIfId                                            Gauge32,
    cfprAdaptorHostFcIfIfRole                                        CfprNetworkPortRole,
    cfprAdaptorHostFcIfIfType                                        CfprNetworkPhysEpIfType,
    cfprAdaptorHostFcIfLc                                            CfprFsmLifecycle,
    cfprAdaptorHostFcIfLinkState                                     CfprAdaptorLinkState,
    cfprAdaptorHostFcIfLocale                                        CfprNetworkLocale,
    cfprAdaptorHostFcIfMaxDataFieldSize                              Gauge32,
    cfprAdaptorHostFcIfModel                                         SnmpAdminString,
    cfprAdaptorHostFcIfName                                          SnmpAdminString,
    cfprAdaptorHostFcIfNodeWwn                                       Unsigned64,
    cfprAdaptorHostFcIfOperQualifierReason                           SnmpAdminString,
    cfprAdaptorHostFcIfOperState                                     CfprEquipmentOperability,
    cfprAdaptorHostFcIfOperability                                   CfprEquipmentOperability,
    cfprAdaptorHostFcIfOrder                                         Gauge32,
    cfprAdaptorHostFcIfOriginalNodeWwn                               Unsigned64,
    cfprAdaptorHostFcIfOriginalWwn                                   Unsigned64,
    cfprAdaptorHostFcIfPciAddr                                       SnmpAdminString,
    cfprAdaptorHostFcIfPciFunc                                       Gauge32,
    cfprAdaptorHostFcIfPciSlot                                       Gauge32,
    cfprAdaptorHostFcIfPeerChassisId                                 Gauge32,
    cfprAdaptorHostFcIfPeerDn                                        SnmpAdminString,
    cfprAdaptorHostFcIfPeerPortId                                    Gauge32,
    cfprAdaptorHostFcIfPeerSlotId                                    Gauge32,
    cfprAdaptorHostFcIfPerf                                          CfprEquipmentSensorThresholdStatus,
    cfprAdaptorHostFcIfPersBind                                      CfprAdaptorHostFcIfPersBind,
    cfprAdaptorHostFcIfPortId                                        Gauge32,
    cfprAdaptorHostFcIfPower                                         CfprEquipmentPowerState,
    cfprAdaptorHostFcIfPresence                                      CfprEquipmentPresence,
    cfprAdaptorHostFcIfPurpose                                       CfprAdaptorPurpose,
    cfprAdaptorHostFcIfRevision                                      SnmpAdminString,
    cfprAdaptorHostFcIfSerial                                        SnmpAdminString,
    cfprAdaptorHostFcIfSide                                          CfprNetworkSide,
    cfprAdaptorHostFcIfSlotId                                        Gauge32,
    cfprAdaptorHostFcIfSwitchId                                      CfprNetworkSwitchId,
    cfprAdaptorHostFcIfThermal                                       CfprEquipmentSensorThresholdStatus,
    cfprAdaptorHostFcIfTransport                                     CfprNetworkTransport,
    cfprAdaptorHostFcIfType                                          CfprNetworkConnectionType,
    cfprAdaptorHostFcIfVendor                                        SnmpAdminString,
    cfprAdaptorHostFcIfVnicDn                                        SnmpAdminString,
    cfprAdaptorHostFcIfVoltage                                       CfprEquipmentSensorThresholdStatus,
    cfprAdaptorHostFcIfWwn                                           Unsigned64,
    cfprAdaptorHostFcIfServiceState                                  CfprAdaptorServiceState,
    cfprAdaptorHostFcIfVcAdminState                                  CfprDcxAdminState
}

cfprAdaptorHostFcIfInstanceId OBJECT-TYPE
    SYNTAX       CfprManagedObjectId
    MAX-ACCESS   not-accessible
    STATUS       current
    DESCRIPTION
        "Instance identifier of the managed object."
    ::= { cfprAdaptorHostFcIfEntry 1 }

cfprAdaptorHostFcIfDn OBJECT-TYPE
    SYNTAX       CfprManagedObjectDn
    MAX-ACCESS   read-only
    STATUS       current
    DESCRIPTION
        "Cisco Firepower adaptor:HostFcIf:dn managed object property"
    ::= { cfprAdaptorHostFcIfEntry 2 }

cfprAdaptorHostFcIfRn OBJECT-TYPE
    SYNTAX       SnmpAdminString
    MAX-ACCESS   read-only
    STATUS       current
    DESCRIPTION
        "Cisco Firepower adaptor:HostFcIf:rn managed object property"
    ::= { cfprAdaptorHostFcIfEntry 3 }

cfprAdaptorHostFcIfAdminState OBJECT-TYPE
    SYNTAX       CfprAdaptorHostFcIfAdminState
    MAX-ACCESS   read-only
    STATUS       current
    DESCRIPTION
        "Cisco Firepower adaptor:HostFcIf:adminState managed
        object property"
    ::= { cfprAdaptorHostFcIfEntry 4 }

cfprAdaptorHostFcIfBootDev OBJECT-TYPE
    SYNTAX       CfprAdaptorHostIfBootDev
    MAX-ACCESS   read-only
    STATUS       current
    DESCRIPTION
        "Cisco Firepower adaptor:HostFcIf:bootDev managed object property"
    ::= { cfprAdaptorHostFcIfEntry 5 }

cfprAdaptorHostFcIfChassisId OBJECT-TYPE
    SYNTAX       Gauge32
    MAX-ACCESS   read-only
    STATUS       current
    DESCRIPTION
        "Cisco Firepower adaptor:HostFcIf:chassisId managed
        object property"
    ::= { cfprAdaptorHostFcIfEntry 6 }

cfprAdaptorHostFcIfDiscovery OBJECT-TYPE
    SYNTAX       CfprEtherSatelliteConnectionDisc
    MAX-ACCESS   read-only
    STATUS       current
    DESCRIPTION
        "Cisco Firepower adaptor:HostFcIf:discovery managed
        object property"
    ::= { cfprAdaptorHostFcIfEntry 7 }

cfprAdaptorHostFcIfEpDn OBJECT-TYPE
    SYNTAX       SnmpAdminString
    MAX-ACCESS   read-only
    STATUS       current
    DESCRIPTION
        "Cisco Firepower adaptor:HostFcIf:epDn managed object property"
    ::= { cfprAdaptorHostFcIfEntry 8 }

cfprAdaptorHostFcIfFltAggr OBJECT-TYPE
    SYNTAX       Unsigned64
    MAX-ACCESS   read-only
    STATUS       current
    DESCRIPTION
        "Cisco Firepower adaptor:HostFcIf:fltAggr managed object property"
    ::= { cfprAdaptorHostFcIfEntry 9 }

cfprAdaptorHostFcIfFsmDescr OBJECT-TYPE
    SYNTAX       SnmpAdminString
    MAX-ACCESS   read-only
    STATUS       current
    DESCRIPTION
        "Cisco Firepower adaptor:HostFcIf:fsmDescr managed
        object property"
    ::= { cfprAdaptorHostFcIfEntry 10 }

cfprAdaptorHostFcIfFsmPrev OBJECT-TYPE
    SYNTAX       SnmpAdminString
    MAX-ACCESS   read-only
    STATUS       current
    DESCRIPTION
        "Cisco Firepower adaptor:HostFcIf:fsmPrev managed object property"
    ::= { cfprAdaptorHostFcIfEntry 11 }

cfprAdaptorHostFcIfFsmProgr OBJECT-TYPE
    SYNTAX       Gauge32
    MAX-ACCESS   read-only
    STATUS       current
    DESCRIPTION
        "Cisco Firepower adaptor:HostFcIf:fsmProgr managed
        object property"
    ::= { cfprAdaptorHostFcIfEntry 12 }

cfprAdaptorHostFcIfFsmRmtInvErrCode OBJECT-TYPE
    SYNTAX       Gauge32
    MAX-ACCESS   read-only
    STATUS       current
    DESCRIPTION
        "Cisco Firepower adaptor:HostFcIf:fsmRmtInvErrCode
        managed object property"
    ::= { cfprAdaptorHostFcIfEntry 13 }

cfprAdaptorHostFcIfFsmRmtInvErrDescr OBJECT-TYPE
    SYNTAX       SnmpAdminString
    MAX-ACCESS   read-only
    STATUS       current
    DESCRIPTION
        "Cisco Firepower adaptor:HostFcIf:fsmRmtInvErrDescr
        managed object property"
    ::= { cfprAdaptorHostFcIfEntry 14 }

cfprAdaptorHostFcIfFsmRmtInvRslt OBJECT-TYPE
    SYNTAX       CfprConditionRemoteInvRslt
    MAX-ACCESS   read-only
    STATUS       current
    DESCRIPTION
        "Cisco Firepower adaptor:HostFcIf:fsmRmtInvRslt
        managed object property"
    ::= { cfprAdaptorHostFcIfEntry 15 }

cfprAdaptorHostFcIfFsmStageDescr OBJECT-TYPE
    SYNTAX       SnmpAdminString
    MAX-ACCESS   read-only
    STATUS       current
    DESCRIPTION
        "Cisco Firepower adaptor:HostFcIf:fsmStageDescr
        managed object property"
    ::= { cfprAdaptorHostFcIfEntry 16 }

cfprAdaptorHostFcIfFsmStamp OBJECT-TYPE
    SYNTAX       DateAndTime
    MAX-ACCESS   read-only
    STATUS       current
    DESCRIPTION
        "Cisco Firepower adaptor:HostFcIf:fsmStamp managed
        object property"
    ::= { cfprAdaptorHostFcIfEntry 17 }

cfprAdaptorHostFcIfFsmStatus OBJECT-TYPE
    SYNTAX       SnmpAdminString
    MAX-ACCESS   read-only
    STATUS       current
    DESCRIPTION
        "Cisco Firepower adaptor:HostFcIf:fsmStatus managed
        object property"
    ::= { cfprAdaptorHostFcIfEntry 18 }

cfprAdaptorHostFcIfFsmTry OBJECT-TYPE
    SYNTAX       Gauge32
    MAX-ACCESS   read-only
    STATUS       current
    DESCRIPTION
        "Cisco Firepower adaptor:HostFcIf:fsmTry managed object property"
    ::= { cfprAdaptorHostFcIfEntry 19 }

cfprAdaptorHostFcIfHostPort OBJECT-TYPE
    SYNTAX       CfprAdaptorHostFcIfHostPort
    MAX-ACCESS   read-only
    STATUS       current
    DESCRIPTION
        "Cisco Firepower adaptor:HostFcIf:hostPort managed
        object property"
    ::= { cfprAdaptorHostFcIfEntry 20 }

cfprAdaptorHostFcIfId OBJECT-TYPE
    SYNTAX       Gauge32
    MAX-ACCESS   read-only
    STATUS       current
    DESCRIPTION
        "Cisco Firepower adaptor:HostFcIf:id managed object property"
    ::= { cfprAdaptorHostFcIfEntry 21 }

cfprAdaptorHostFcIfIfRole OBJECT-TYPE
    SYNTAX       CfprNetworkPortRole
    MAX-ACCESS   read-only
    STATUS       current
    DESCRIPTION
        "Cisco Firepower adaptor:HostFcIf:ifRole managed object property"
    ::= { cfprAdaptorHostFcIfEntry 22 }

cfprAdaptorHostFcIfIfType OBJECT-TYPE
    SYNTAX       CfprNetworkPhysEpIfType
    MAX-ACCESS   read-only
    STATUS       current
    DESCRIPTION
        "Cisco Firepower adaptor:HostFcIf:ifType managed object property"
    ::= { cfprAdaptorHostFcIfEntry 23 }

cfprAdaptorHostFcIfLc OBJECT-TYPE
    SYNTAX       CfprFsmLifecycle
    MAX-ACCESS   read-only
    STATUS       current
    DESCRIPTION
        "Cisco Firepower adaptor:HostFcIf:lc managed object property"
    ::= { cfprAdaptorHostFcIfEntry 24 }

cfprAdaptorHostFcIfLinkState OBJECT-TYPE
    SYNTAX       CfprAdaptorLinkState
    MAX-ACCESS   read-only
    STATUS       current
    DESCRIPTION
        "Cisco Firepower adaptor:HostFcIf:linkState managed
        object property"
    ::= { cfprAdaptorHostFcIfEntry 25 }

cfprAdaptorHostFcIfLocale OBJECT-TYPE
    SYNTAX       CfprNetworkLocale
    MAX-ACCESS   read-only
    STATUS       current
    DESCRIPTION
        "Cisco Firepower adaptor:HostFcIf:locale managed object property"
    ::= { cfprAdaptorHostFcIfEntry 26 }

cfprAdaptorHostFcIfMaxDataFieldSize OBJECT-TYPE
    SYNTAX       Gauge32
    MAX-ACCESS   read-only
    STATUS       current
    DESCRIPTION
        "Cisco Firepower adaptor:HostFcIf:maxDataFieldSize
        managed object property"
    ::= { cfprAdaptorHostFcIfEntry 27 }

cfprAdaptorHostFcIfModel OBJECT-TYPE
    SYNTAX       SnmpAdminString
    MAX-ACCESS   read-only
    STATUS       current
    DESCRIPTION
        "Cisco Firepower adaptor:HostFcIf:model managed object property"
    ::= { cfprAdaptorHostFcIfEntry 28 }

cfprAdaptorHostFcIfName OBJECT-TYPE
    SYNTAX       SnmpAdminString
    MAX-ACCESS   read-only
    STATUS       current
    DESCRIPTION
        "Cisco Firepower adaptor:HostFcIf:name managed object property"
    ::= { cfprAdaptorHostFcIfEntry 29 }

cfprAdaptorHostFcIfNodeWwn OBJECT-TYPE
    SYNTAX       Unsigned64
    MAX-ACCESS   read-only
    STATUS       current
    DESCRIPTION
        "Cisco Firepower adaptor:HostFcIf:nodeWwn managed object property"
    ::= { cfprAdaptorHostFcIfEntry 30 }

cfprAdaptorHostFcIfOperQualifierReason OBJECT-TYPE
    SYNTAX       SnmpAdminString
    MAX-ACCESS   read-only
    STATUS       current
    DESCRIPTION
        "Cisco Firepower adaptor:HostFcIf:operQualifierReason
        managed object property"
    ::= { cfprAdaptorHostFcIfEntry 31 }

cfprAdaptorHostFcIfOperState OBJECT-TYPE
    SYNTAX       CfprEquipmentOperability
    MAX-ACCESS   read-only
    STATUS       current
    DESCRIPTION
        "Cisco Firepower adaptor:HostFcIf:operState managed
        object property"
    ::= { cfprAdaptorHostFcIfEntry 32 }

cfprAdaptorHostFcIfOperability OBJECT-TYPE
    SYNTAX       CfprEquipmentOperability
    MAX-ACCESS   read-only
    STATUS       current
    DESCRIPTION
        "Cisco Firepower adaptor:HostFcIf:operability managed
        object property"
    ::= { cfprAdaptorHostFcIfEntry 33 }

cfprAdaptorHostFcIfOrder OBJECT-TYPE
    SYNTAX       Gauge32
    MAX-ACCESS   read-only
    STATUS       current
    DESCRIPTION
        "Cisco Firepower adaptor:HostFcIf:order managed object property"
    ::= { cfprAdaptorHostFcIfEntry 34 }

cfprAdaptorHostFcIfOriginalNodeWwn OBJECT-TYPE
    SYNTAX       Unsigned64
    MAX-ACCESS   read-only
    STATUS       current
    DESCRIPTION
        "Cisco Firepower adaptor:HostFcIf:originalNodeWwn
        managed object property"
    ::= { cfprAdaptorHostFcIfEntry 35 }

cfprAdaptorHostFcIfOriginalWwn OBJECT-TYPE
    SYNTAX       Unsigned64
    MAX-ACCESS   read-only
    STATUS       current
    DESCRIPTION
        "Cisco Firepower adaptor:HostFcIf:originalWwn managed
        object property"
    ::= { cfprAdaptorHostFcIfEntry 36 }

cfprAdaptorHostFcIfPciAddr OBJECT-TYPE
    SYNTAX       SnmpAdminString
    MAX-ACCESS   read-only
    STATUS       current
    DESCRIPTION
        "Cisco Firepower adaptor:HostFcIf:pciAddr managed object property"
    ::= { cfprAdaptorHostFcIfEntry 37 }

cfprAdaptorHostFcIfPciFunc OBJECT-TYPE
    SYNTAX       Gauge32
    MAX-ACCESS   read-only
    STATUS       current
    DESCRIPTION
        "Cisco Firepower adaptor:HostFcIf:pciFunc managed object property"
    ::= { cfprAdaptorHostFcIfEntry 38 }

cfprAdaptorHostFcIfPciSlot OBJECT-TYPE
    SYNTAX       Gauge32
    MAX-ACCESS   read-only
    STATUS       current
    DESCRIPTION
        "Cisco Firepower adaptor:HostFcIf:pciSlot managed object property"
    ::= { cfprAdaptorHostFcIfEntry 39 }

cfprAdaptorHostFcIfPeerChassisId OBJECT-TYPE
    SYNTAX       Gauge32
    MAX-ACCESS   read-only
    STATUS       current
    DESCRIPTION
        "Cisco Firepower adaptor:HostFcIf:peerChassisId
        managed object property"
    ::= { cfprAdaptorHostFcIfEntry 40 }

cfprAdaptorHostFcIfPeerDn OBJECT-TYPE
    SYNTAX       SnmpAdminString
    MAX-ACCESS   read-only
    STATUS       current
    DESCRIPTION
        "Cisco Firepower adaptor:HostFcIf:peerDn managed object property"
    ::= { cfprAdaptorHostFcIfEntry 41 }

cfprAdaptorHostFcIfPeerPortId OBJECT-TYPE
    SYNTAX       Gauge32
    MAX-ACCESS   read-only
    STATUS       current
    DESCRIPTION
        "Cisco Firepower adaptor:HostFcIf:peerPortId managed
        object property"
    ::= { cfprAdaptorHostFcIfEntry 42 }

cfprAdaptorHostFcIfPeerSlotId OBJECT-TYPE
    SYNTAX       Gauge32
    MAX-ACCESS   read-only
    STATUS       current
    DESCRIPTION
        "Cisco Firepower adaptor:HostFcIf:peerSlotId managed
        object property"
    ::= { cfprAdaptorHostFcIfEntry 43 }

cfprAdaptorHostFcIfPerf OBJECT-TYPE
    SYNTAX       CfprEquipmentSensorThresholdStatus
    MAX-ACCESS   read-only
    STATUS       current
    DESCRIPTION
        "Cisco Firepower adaptor:HostFcIf:perf managed object property"
    ::= { cfprAdaptorHostFcIfEntry 44 }

cfprAdaptorHostFcIfPersBind OBJECT-TYPE
    SYNTAX       CfprAdaptorHostFcIfPersBind
    MAX-ACCESS   read-only
    STATUS       current
    DESCRIPTION
        "Cisco Firepower adaptor:HostFcIf:persBind managed
        object property"
    ::= { cfprAdaptorHostFcIfEntry 45 }

cfprAdaptorHostFcIfPortId OBJECT-TYPE
    SYNTAX       Gauge32
    MAX-ACCESS   read-only
    STATUS       current
    DESCRIPTION
        "Cisco Firepower adaptor:HostFcIf:portId managed object property"
    ::= { cfprAdaptorHostFcIfEntry 46 }

cfprAdaptorHostFcIfPower OBJECT-TYPE
    SYNTAX       CfprEquipmentPowerState
    MAX-ACCESS   read-only
    STATUS       current
    DESCRIPTION
        "Cisco Firepower adaptor:HostFcIf:power managed object property"
    ::= { cfprAdaptorHostFcIfEntry 47 }

cfprAdaptorHostFcIfPresence OBJECT-TYPE
    SYNTAX       CfprEquipmentPresence
    MAX-ACCESS   read-only
    STATUS       current
    DESCRIPTION
        "Cisco Firepower adaptor:HostFcIf:presence managed
        object property"
    ::= { cfprAdaptorHostFcIfEntry 48 }

cfprAdaptorHostFcIfPurpose OBJECT-TYPE
    SYNTAX       CfprAdaptorPurpose
    MAX-ACCESS   read-only
    STATUS       current
    DESCRIPTION
        "Cisco Firepower adaptor:HostFcIf:purpose managed object property"
    ::= { cfprAdaptorHostFcIfEntry 49 }

cfprAdaptorHostFcIfRevision OBJECT-TYPE
    SYNTAX       SnmpAdminString
    MAX-ACCESS   read-only
    STATUS       current
    DESCRIPTION
        "Cisco Firepower adaptor:HostFcIf:revision managed
        object property"
    ::= { cfprAdaptorHostFcIfEntry 50 }

cfprAdaptorHostFcIfSerial OBJECT-TYPE
    SYNTAX       SnmpAdminString
    MAX-ACCESS   read-only
    STATUS       current
    DESCRIPTION
        "Cisco Firepower adaptor:HostFcIf:serial managed object property"
    ::= { cfprAdaptorHostFcIfEntry 51 }

cfprAdaptorHostFcIfSide OBJECT-TYPE
    SYNTAX       CfprNetworkSide
    MAX-ACCESS   read-only
    STATUS       current
    DESCRIPTION
        "Cisco Firepower adaptor:HostFcIf:side managed object property"
    ::= { cfprAdaptorHostFcIfEntry 52 }

cfprAdaptorHostFcIfSlotId OBJECT-TYPE
    SYNTAX       Gauge32
    MAX-ACCESS   read-only
    STATUS       current
    DESCRIPTION
        "Cisco Firepower adaptor:HostFcIf:slotId managed object property"
    ::= { cfprAdaptorHostFcIfEntry 53 }

cfprAdaptorHostFcIfSwitchId OBJECT-TYPE
    SYNTAX       CfprNetworkSwitchId
    MAX-ACCESS   read-only
    STATUS       current
    DESCRIPTION
        "Cisco Firepower adaptor:HostFcIf:switchId managed
        object property"
    ::= { cfprAdaptorHostFcIfEntry 54 }

cfprAdaptorHostFcIfThermal OBJECT-TYPE
    SYNTAX       CfprEquipmentSensorThresholdStatus
    MAX-ACCESS   read-only
    STATUS       current
    DESCRIPTION
        "Cisco Firepower adaptor:HostFcIf:thermal managed object property"
    ::= { cfprAdaptorHostFcIfEntry 55 }

cfprAdaptorHostFcIfTransport OBJECT-TYPE
    SYNTAX       CfprNetworkTransport
    MAX-ACCESS   read-only
    STATUS       current
    DESCRIPTION
        "Cisco Firepower adaptor:HostFcIf:transport managed
        object property"
    ::= { cfprAdaptorHostFcIfEntry 56 }

cfprAdaptorHostFcIfType OBJECT-TYPE
    SYNTAX       CfprNetworkConnectionType
    MAX-ACCESS   read-only
    STATUS       current
    DESCRIPTION
        "Cisco Firepower adaptor:HostFcIf:type managed object property"
    ::= { cfprAdaptorHostFcIfEntry 57 }

cfprAdaptorHostFcIfVendor OBJECT-TYPE
    SYNTAX       SnmpAdminString
    MAX-ACCESS   read-only
    STATUS       current
    DESCRIPTION
        "Cisco Firepower adaptor:HostFcIf:vendor managed object property"
    ::= { cfprAdaptorHostFcIfEntry 58 }

cfprAdaptorHostFcIfVnicDn OBJECT-TYPE
    SYNTAX       SnmpAdminString
    MAX-ACCESS   read-only
    STATUS       current
    DESCRIPTION
        "Cisco Firepower adaptor:HostFcIf:vnicDn managed object property"
    ::= { cfprAdaptorHostFcIfEntry 59 }

cfprAdaptorHostFcIfVoltage OBJECT-TYPE
    SYNTAX       CfprEquipmentSensorThresholdStatus
    MAX-ACCESS   read-only
    STATUS       current
    DESCRIPTION
        "Cisco Firepower adaptor:HostFcIf:voltage managed object property"
    ::= { cfprAdaptorHostFcIfEntry 60 }

cfprAdaptorHostFcIfWwn OBJECT-TYPE
    SYNTAX       Unsigned64
    MAX-ACCESS   read-only
    STATUS       current
    DESCRIPTION
        "Cisco Firepower adaptor:HostFcIf:wwn managed object property"
    ::= { cfprAdaptorHostFcIfEntry 61 }

cfprAdaptorHostFcIfServiceState OBJECT-TYPE
    SYNTAX       CfprAdaptorServiceState
    MAX-ACCESS   read-only
    STATUS       current
    DESCRIPTION
        "Cisco Firepower adaptor:HostFcIf:serviceState
        managed object property"
    ::= { cfprAdaptorHostFcIfEntry 62 }

cfprAdaptorHostFcIfVcAdminState OBJECT-TYPE
    SYNTAX       CfprDcxAdminState
    MAX-ACCESS   read-only
    STATUS       current
    DESCRIPTION
        "Cisco Firepower adaptor:HostFcIf:vcAdminState
        managed object property"
    ::= { cfprAdaptorHostFcIfEntry 63 }

cfprAdaptorHostFcIfFsmTable OBJECT-TYPE
    SYNTAX           SEQUENCE OF CfprAdaptorHostFcIfFsmEntry
    MAX-ACCESS       not-accessible
    STATUS           current
    DESCRIPTION
        "Cisco Firepower adaptor:HostFcIfFsm managed object table"
    ::= { cfprAdaptorObjects 62 }

cfprAdaptorHostFcIfFsmEntry OBJECT-TYPE
    SYNTAX           CfprAdaptorHostFcIfFsmEntry
    MAX-ACCESS       not-accessible
    STATUS           current
    DESCRIPTION
        "Entry for the cfprAdaptorHostFcIfFsmTable table."
    INDEX { cfprAdaptorHostFcIfFsmInstanceId }
    ::= { cfprAdaptorHostFcIfFsmTable 1 }

CfprAdaptorHostFcIfFsmEntry ::= SEQUENCE {
    cfprAdaptorHostFcIfFsmInstanceId                                 CfprManagedObjectId,
    cfprAdaptorHostFcIfFsmDn                                         CfprManagedObjectDn,
    cfprAdaptorHostFcIfFsmRn                                         SnmpAdminString,
    cfprAdaptorHostFcIfFsmCompletionTime                             DateAndTime,
    cfprAdaptorHostFcIfFsmCurrentFsm                                 CfprAdaptorHostFcIfFsmCurrentFsm,
    cfprAdaptorHostFcIfFsmDescrData                                  SnmpAdminString,
    cfprAdaptorHostFcIfFsmFsmStatus                                  CfprFsmFsmStageStatus,
    cfprAdaptorHostFcIfFsmProgress                                   Gauge32,
    cfprAdaptorHostFcIfFsmRmtErrCode                                 Gauge32,
    cfprAdaptorHostFcIfFsmRmtErrDescr                                SnmpAdminString,
    cfprAdaptorHostFcIfFsmRmtRslt                                    CfprConditionRemoteInvRslt
}

cfprAdaptorHostFcIfFsmInstanceId OBJECT-TYPE
    SYNTAX       CfprManagedObjectId
    MAX-ACCESS   not-accessible
    STATUS       current
    DESCRIPTION
        "Instance identifier of the managed object."
    ::= { cfprAdaptorHostFcIfFsmEntry 1 }

cfprAdaptorHostFcIfFsmDn OBJECT-TYPE
    SYNTAX       CfprManagedObjectDn
    MAX-ACCESS   read-only
    STATUS       current
    DESCRIPTION
        "Cisco Firepower adaptor:HostFcIfFsm:dn managed object property"
    ::= { cfprAdaptorHostFcIfFsmEntry 2 }

cfprAdaptorHostFcIfFsmRn OBJECT-TYPE
    SYNTAX       SnmpAdminString
    MAX-ACCESS   read-only
    STATUS       current
    DESCRIPTION
        "Cisco Firepower adaptor:HostFcIfFsm:rn managed object property"
    ::= { cfprAdaptorHostFcIfFsmEntry 3 }

cfprAdaptorHostFcIfFsmCompletionTime OBJECT-TYPE
    SYNTAX       DateAndTime
    MAX-ACCESS   read-only
    STATUS       current
    DESCRIPTION
        "Cisco Firepower adaptor:HostFcIfFsm:completionTime
        managed object property"
    ::= { cfprAdaptorHostFcIfFsmEntry 4 }

cfprAdaptorHostFcIfFsmCurrentFsm OBJECT-TYPE
    SYNTAX       CfprAdaptorHostFcIfFsmCurrentFsm
    MAX-ACCESS   read-only
    STATUS       current
    DESCRIPTION
        "Cisco Firepower adaptor:HostFcIfFsm:currentFsm
        managed object property"
    ::= { cfprAdaptorHostFcIfFsmEntry 5 }

cfprAdaptorHostFcIfFsmDescrData OBJECT-TYPE
    SYNTAX       SnmpAdminString
    MAX-ACCESS   read-only
    STATUS       current
    DESCRIPTION
        "Cisco Firepower adaptor:HostFcIfFsm:descr managed
        object property"
    ::= { cfprAdaptorHostFcIfFsmEntry 6 }

cfprAdaptorHostFcIfFsmFsmStatus OBJECT-TYPE
    SYNTAX       CfprFsmFsmStageStatus
    MAX-ACCESS   read-only
    STATUS       current
    DESCRIPTION
        "Cisco Firepower adaptor:HostFcIfFsm:fsmStatus
        managed object property"
    ::= { cfprAdaptorHostFcIfFsmEntry 7 }

cfprAdaptorHostFcIfFsmProgress OBJECT-TYPE
    SYNTAX       Gauge32
    MAX-ACCESS   read-only
    STATUS       current
    DESCRIPTION
        "Cisco Firepower adaptor:HostFcIfFsm:progress managed
        object property"
    ::= { cfprAdaptorHostFcIfFsmEntry 8 }

cfprAdaptorHostFcIfFsmRmtErrCode OBJECT-TYPE
    SYNTAX       Gauge32
    MAX-ACCESS   read-only
    STATUS       current
    DESCRIPTION
        "Cisco Firepower adaptor:HostFcIfFsm:rmtErrCode
        managed object property"
    ::= { cfprAdaptorHostFcIfFsmEntry 9 }

cfprAdaptorHostFcIfFsmRmtErrDescr OBJECT-TYPE
    SYNTAX       SnmpAdminString
    MAX-ACCESS   read-only
    STATUS       current
    DESCRIPTION
        "Cisco Firepower adaptor:HostFcIfFsm:rmtErrDescr
        managed object property"
    ::= { cfprAdaptorHostFcIfFsmEntry 10 }

cfprAdaptorHostFcIfFsmRmtRslt OBJECT-TYPE
    SYNTAX       CfprConditionRemoteInvRslt
    MAX-ACCESS   read-only
    STATUS       current
    DESCRIPTION
        "Cisco Firepower adaptor:HostFcIfFsm:rmtRslt managed
        object property"
    ::= { cfprAdaptorHostFcIfFsmEntry 11 }

cfprAdaptorHostFcIfFsmStageTable OBJECT-TYPE
    SYNTAX           SEQUENCE OF CfprAdaptorHostFcIfFsmStageEntry
    MAX-ACCESS       not-accessible
    STATUS           current
    DESCRIPTION
        "Cisco Firepower adaptor:HostFcIfFsmStage managed object table"
    ::= { cfprAdaptorObjects 63 }

cfprAdaptorHostFcIfFsmStageEntry OBJECT-TYPE
    SYNTAX           CfprAdaptorHostFcIfFsmStageEntry
    MAX-ACCESS       not-accessible
    STATUS           current
    DESCRIPTION
        "Entry for the cfprAdaptorHostFcIfFsmStageTable table."
    INDEX { cfprAdaptorHostFcIfFsmStageInstanceId }
    ::= { cfprAdaptorHostFcIfFsmStageTable 1 }

CfprAdaptorHostFcIfFsmStageEntry ::= SEQUENCE {
    cfprAdaptorHostFcIfFsmStageInstanceId                            CfprManagedObjectId,
    cfprAdaptorHostFcIfFsmStageDn                                    CfprManagedObjectDn,
    cfprAdaptorHostFcIfFsmStageRn                                    SnmpAdminString,
    cfprAdaptorHostFcIfFsmStageDescrData                             SnmpAdminString,
    cfprAdaptorHostFcIfFsmStageLastUpdateTime                        DateAndTime,
    cfprAdaptorHostFcIfFsmStageName                                  CfprAdaptorHostFcIfFsmStageName,
    cfprAdaptorHostFcIfFsmStageOrder                                 Gauge32,
    cfprAdaptorHostFcIfFsmStageRetry                                 Gauge32,
    cfprAdaptorHostFcIfFsmStageStageStatus                           CfprFsmFsmStageStatus
}

cfprAdaptorHostFcIfFsmStageInstanceId OBJECT-TYPE
    SYNTAX       CfprManagedObjectId
    MAX-ACCESS   not-accessible
    STATUS       current
    DESCRIPTION
        "Instance identifier of the managed object."
    ::= { cfprAdaptorHostFcIfFsmStageEntry 1 }

cfprAdaptorHostFcIfFsmStageDn OBJECT-TYPE
    SYNTAX       CfprManagedObjectDn
    MAX-ACCESS   read-only
    STATUS       current
    DESCRIPTION
        "Cisco Firepower adaptor:HostFcIfFsmStage:dn managed
        object property"
    ::= { cfprAdaptorHostFcIfFsmStageEntry 2 }

cfprAdaptorHostFcIfFsmStageRn OBJECT-TYPE
    SYNTAX       SnmpAdminString
    MAX-ACCESS   read-only
    STATUS       current
    DESCRIPTION
        "Cisco Firepower adaptor:HostFcIfFsmStage:rn managed
        object property"
    ::= { cfprAdaptorHostFcIfFsmStageEntry 3 }

cfprAdaptorHostFcIfFsmStageDescrData OBJECT-TYPE
    SYNTAX       SnmpAdminString
    MAX-ACCESS   read-only
    STATUS       current
    DESCRIPTION
        "Cisco Firepower adaptor:HostFcIfFsmStage:descr
        managed object property"
    ::= { cfprAdaptorHostFcIfFsmStageEntry 4 }

cfprAdaptorHostFcIfFsmStageLastUpdateTime OBJECT-TYPE
    SYNTAX       DateAndTime
    MAX-ACCESS   read-only
    STATUS       current
    DESCRIPTION
        "Cisco Firepower adaptor:HostFcIfFsmStage:lastUpdateTime
        managed object property"
    ::= { cfprAdaptorHostFcIfFsmStageEntry 5 }

cfprAdaptorHostFcIfFsmStageName OBJECT-TYPE
    SYNTAX       CfprAdaptorHostFcIfFsmStageName
    MAX-ACCESS   read-only
    STATUS       current
    DESCRIPTION
        "Cisco Firepower adaptor:HostFcIfFsmStage:name
        managed object property"
    ::= { cfprAdaptorHostFcIfFsmStageEntry 6 }

cfprAdaptorHostFcIfFsmStageOrder OBJECT-TYPE
    SYNTAX       Gauge32
    MAX-ACCESS   read-only
    STATUS       current
    DESCRIPTION
        "Cisco Firepower adaptor:HostFcIfFsmStage:order
        managed object property"
    ::= { cfprAdaptorHostFcIfFsmStageEntry 7 }

cfprAdaptorHostFcIfFsmStageRetry OBJECT-TYPE
    SYNTAX       Gauge32
    MAX-ACCESS   read-only
    STATUS       current
    DESCRIPTION
        "Cisco Firepower adaptor:HostFcIfFsmStage:retry
        managed object property"
    ::= { cfprAdaptorHostFcIfFsmStageEntry 8 }

cfprAdaptorHostFcIfFsmStageStageStatus OBJECT-TYPE
    SYNTAX       CfprFsmFsmStageStatus
    MAX-ACCESS   read-only
    STATUS       current
    DESCRIPTION
        "Cisco Firepower adaptor:HostFcIfFsmStage:stageStatus
        managed object property"
    ::= { cfprAdaptorHostFcIfFsmStageEntry 9 }

cfprAdaptorHostFcIfFsmTaskTable OBJECT-TYPE
    SYNTAX           SEQUENCE OF CfprAdaptorHostFcIfFsmTaskEntry
    MAX-ACCESS       not-accessible
    STATUS           current
    DESCRIPTION
        "Cisco Firepower adaptor:HostFcIfFsmTask managed object table"
    ::= { cfprAdaptorObjects 64 }

cfprAdaptorHostFcIfFsmTaskEntry OBJECT-TYPE
    SYNTAX           CfprAdaptorHostFcIfFsmTaskEntry
    MAX-ACCESS       not-accessible
    STATUS           current
    DESCRIPTION
        "Entry for the cfprAdaptorHostFcIfFsmTaskTable table."
    INDEX { cfprAdaptorHostFcIfFsmTaskInstanceId }
    ::= { cfprAdaptorHostFcIfFsmTaskTable 1 }

CfprAdaptorHostFcIfFsmTaskEntry ::= SEQUENCE {
    cfprAdaptorHostFcIfFsmTaskInstanceId                             CfprManagedObjectId,
    cfprAdaptorHostFcIfFsmTaskDn                                     CfprManagedObjectDn,
    cfprAdaptorHostFcIfFsmTaskRn                                     SnmpAdminString,
    cfprAdaptorHostFcIfFsmTaskCompletion                             CfprFsmCompletion,
    cfprAdaptorHostFcIfFsmTaskFlags                                  CfprFsmFlags,
    cfprAdaptorHostFcIfFsmTaskItem                                   CfprAdaptorHostFcIfFsmTaskItem,
    cfprAdaptorHostFcIfFsmTaskSeqId                                  Gauge32
}

cfprAdaptorHostFcIfFsmTaskInstanceId OBJECT-TYPE
    SYNTAX       CfprManagedObjectId
    MAX-ACCESS   not-accessible
    STATUS       current
    DESCRIPTION
        "Instance identifier of the managed object."
    ::= { cfprAdaptorHostFcIfFsmTaskEntry 1 }

cfprAdaptorHostFcIfFsmTaskDn OBJECT-TYPE
    SYNTAX       CfprManagedObjectDn
    MAX-ACCESS   read-only
    STATUS       current
    DESCRIPTION
        "Cisco Firepower adaptor:HostFcIfFsmTask:dn managed
        object property"
    ::= { cfprAdaptorHostFcIfFsmTaskEntry 2 }

cfprAdaptorHostFcIfFsmTaskRn OBJECT-TYPE
    SYNTAX       SnmpAdminString
    MAX-ACCESS   read-only
    STATUS       current
    DESCRIPTION
        "Cisco Firepower adaptor:HostFcIfFsmTask:rn managed
        object property"
    ::= { cfprAdaptorHostFcIfFsmTaskEntry 3 }

cfprAdaptorHostFcIfFsmTaskCompletion OBJECT-TYPE
    SYNTAX       CfprFsmCompletion
    MAX-ACCESS   read-only
    STATUS       current
    DESCRIPTION
        "Cisco Firepower adaptor:HostFcIfFsmTask:completion
        managed object property"
    ::= { cfprAdaptorHostFcIfFsmTaskEntry 4 }

cfprAdaptorHostFcIfFsmTaskFlags OBJECT-TYPE
    SYNTAX       CfprFsmFlags
    MAX-ACCESS   read-only
    STATUS       current
    DESCRIPTION
        "Cisco Firepower adaptor:HostFcIfFsmTask:flags
        managed object property"
    ::= { cfprAdaptorHostFcIfFsmTaskEntry 5 }

cfprAdaptorHostFcIfFsmTaskItem OBJECT-TYPE
    SYNTAX       CfprAdaptorHostFcIfFsmTaskItem
    MAX-ACCESS   read-only
    STATUS       current
    DESCRIPTION
        "Cisco Firepower adaptor:HostFcIfFsmTask:item managed
        object property"
    ::= { cfprAdaptorHostFcIfFsmTaskEntry 6 }

cfprAdaptorHostFcIfFsmTaskSeqId OBJECT-TYPE
    SYNTAX       Gauge32
    MAX-ACCESS   read-only
    STATUS       current
    DESCRIPTION
        "Cisco Firepower adaptor:HostFcIfFsmTask:seqId
        managed object property"
    ::= { cfprAdaptorHostFcIfFsmTaskEntry 7 }

cfprAdaptorHostFcIfProfileTable OBJECT-TYPE
    SYNTAX           SEQUENCE OF CfprAdaptorHostFcIfProfileEntry
    MAX-ACCESS       not-accessible
    STATUS           current
    DESCRIPTION
        "Cisco Firepower adaptor:HostFcIfProfile managed object table"
    ::= { cfprAdaptorObjects 65 }

cfprAdaptorHostFcIfProfileEntry OBJECT-TYPE
    SYNTAX           CfprAdaptorHostFcIfProfileEntry
    MAX-ACCESS       not-accessible
    STATUS           current
    DESCRIPTION
        "Entry for the cfprAdaptorHostFcIfProfileTable table."
    INDEX { cfprAdaptorHostFcIfProfileInstanceId }
    ::= { cfprAdaptorHostFcIfProfileTable 1 }

CfprAdaptorHostFcIfProfileEntry ::= SEQUENCE {
    cfprAdaptorHostFcIfProfileInstanceId                             CfprManagedObjectId,
    cfprAdaptorHostFcIfProfileDn                                     CfprManagedObjectDn,
    cfprAdaptorHostFcIfProfileRn                                     SnmpAdminString,
    cfprAdaptorHostFcIfProfileDescr                                  SnmpAdminString,
    cfprAdaptorHostFcIfProfileIntId                                  SnmpAdminString,
    cfprAdaptorHostFcIfProfileName                                   SnmpAdminString,
    cfprAdaptorHostFcIfProfilePolicyLevel                            Gauge32,
    cfprAdaptorHostFcIfProfilePolicyOwner                            CfprPolicyPolicyOwner
}

cfprAdaptorHostFcIfProfileInstanceId OBJECT-TYPE
    SYNTAX       CfprManagedObjectId
    MAX-ACCESS   not-accessible
    STATUS       current
    DESCRIPTION
        "Instance identifier of the managed object."
    ::= { cfprAdaptorHostFcIfProfileEntry 1 }

cfprAdaptorHostFcIfProfileDn OBJECT-TYPE
    SYNTAX       CfprManagedObjectDn
    MAX-ACCESS   read-only
    STATUS       current
    DESCRIPTION
        "Cisco Firepower adaptor:HostFcIfProfile:dn managed
        object property"
    ::= { cfprAdaptorHostFcIfProfileEntry 2 }

cfprAdaptorHostFcIfProfileRn OBJECT-TYPE
    SYNTAX       SnmpAdminString
    MAX-ACCESS   read-only
    STATUS       current
    DESCRIPTION
        "Cisco Firepower adaptor:HostFcIfProfile:rn managed
        object property"
    ::= { cfprAdaptorHostFcIfProfileEntry 3 }

cfprAdaptorHostFcIfProfileDescr OBJECT-TYPE
    SYNTAX       SnmpAdminString
    MAX-ACCESS   read-only
    STATUS       current
    DESCRIPTION
        "Cisco Firepower adaptor:HostFcIfProfile:descr
        managed object property"
    ::= { cfprAdaptorHostFcIfProfileEntry 4 }

cfprAdaptorHostFcIfProfileIntId OBJECT-TYPE
    SYNTAX       SnmpAdminString
    MAX-ACCESS   read-only
    STATUS       current
    DESCRIPTION
        "Cisco Firepower adaptor:HostFcIfProfile:intId
        managed object property"
    ::= { cfprAdaptorHostFcIfProfileEntry 5 }

cfprAdaptorHostFcIfProfileName OBJECT-TYPE
    SYNTAX       SnmpAdminString
    MAX-ACCESS   read-only
    STATUS       current
    DESCRIPTION
        "Cisco Firepower adaptor:HostFcIfProfile:name managed
        object property"
    ::= { cfprAdaptorHostFcIfProfileEntry 6 }

cfprAdaptorHostFcIfProfilePolicyLevel OBJECT-TYPE
    SYNTAX       Gauge32
    MAX-ACCESS   read-only
    STATUS       current
    DESCRIPTION
        "Cisco Firepower adaptor:HostFcIfProfile:policyLevel
        managed object property"
    ::= { cfprAdaptorHostFcIfProfileEntry 7 }

cfprAdaptorHostFcIfProfilePolicyOwner OBJECT-TYPE
    SYNTAX       CfprPolicyPolicyOwner
    MAX-ACCESS   read-only
    STATUS       current
    DESCRIPTION
        "Cisco Firepower adaptor:HostFcIfProfile:policyOwner
        managed object property"
    ::= { cfprAdaptorHostFcIfProfileEntry 8 }

cfprAdaptorHostIscsiIfTable OBJECT-TYPE
    SYNTAX           SEQUENCE OF CfprAdaptorHostIscsiIfEntry
    MAX-ACCESS       not-accessible
    STATUS           current
    DESCRIPTION
        "Cisco Firepower adaptor:HostIscsiIf managed object table"
    ::= { cfprAdaptorObjects 66 }

cfprAdaptorHostIscsiIfEntry OBJECT-TYPE
    SYNTAX           CfprAdaptorHostIscsiIfEntry
    MAX-ACCESS       not-accessible
    STATUS           current
    DESCRIPTION
        "Entry for the cfprAdaptorHostIscsiIfTable table."
    INDEX { cfprAdaptorHostIscsiIfInstanceId }
    ::= { cfprAdaptorHostIscsiIfTable 1 }

CfprAdaptorHostIscsiIfEntry ::= SEQUENCE {
    cfprAdaptorHostIscsiIfInstanceId                                 CfprManagedObjectId,
    cfprAdaptorHostIscsiIfDn                                         CfprManagedObjectDn,
    cfprAdaptorHostIscsiIfRn                                         SnmpAdminString,
    cfprAdaptorHostIscsiIfAdminState                                 CfprAdaptorHostIfAdminState,
    cfprAdaptorHostIscsiIfBootDev                                    CfprAdaptorHostIfBootDev,
    cfprAdaptorHostIscsiIfChassisId                                  Gauge32,
    cfprAdaptorHostIscsiIfDiscovery                                  CfprEtherSatelliteConnectionDisc,
    cfprAdaptorHostIscsiIfEpDn                                       SnmpAdminString,
    cfprAdaptorHostIscsiIfEthEpDn                                    SnmpAdminString,
    cfprAdaptorHostIscsiIfFltAggr                                    Unsigned64,
    cfprAdaptorHostIscsiIfHostVisible                                CfprAdaptorHostVisibility,
    cfprAdaptorHostIscsiIfId                                         Gauge32,
    cfprAdaptorHostIscsiIfIfRole                                     CfprNetworkPortRole,
    cfprAdaptorHostIscsiIfIfType                                     CfprNetworkPhysEpIfType,
    cfprAdaptorHostIscsiIfInitiatorName                              SnmpAdminString,
    cfprAdaptorHostIscsiIfLc                                         CfprFsmLifecycle,
    cfprAdaptorHostIscsiIfLinkState                                  CfprAdaptorLinkState,
    cfprAdaptorHostIscsiIfLocale                                     CfprNetworkLocale,
    cfprAdaptorHostIscsiIfMac                                        MacAddress,
    cfprAdaptorHostIscsiIfModel                                      SnmpAdminString,
    cfprAdaptorHostIscsiIfName                                       SnmpAdminString,
    cfprAdaptorHostIscsiIfOperQualifierReason                        SnmpAdminString,
    cfprAdaptorHostIscsiIfOperState                                  CfprEquipmentOperability,
    cfprAdaptorHostIscsiIfOperability                                CfprEquipmentOperability,
    cfprAdaptorHostIscsiIfOrder                                      Gauge32,
    cfprAdaptorHostIscsiIfOriginalMac                                MacAddress,
    cfprAdaptorHostIscsiIfPciAddr                                    SnmpAdminString,
    cfprAdaptorHostIscsiIfPciFunc                                    Gauge32,
    cfprAdaptorHostIscsiIfPciSlot                                    Gauge32,
    cfprAdaptorHostIscsiIfPeerChassisId                              Gauge32,
    cfprAdaptorHostIscsiIfPeerDn                                     SnmpAdminString,
    cfprAdaptorHostIscsiIfPeerPortId                                 Gauge32,
    cfprAdaptorHostIscsiIfPeerSlotId                                 Gauge32,
    cfprAdaptorHostIscsiIfPerf                                       CfprEquipmentSensorThresholdStatus,
    cfprAdaptorHostIscsiIfPortId                                     Gauge32,
    cfprAdaptorHostIscsiIfPower                                      CfprEquipmentPowerState,
    cfprAdaptorHostIscsiIfPresence                                   CfprEquipmentPresence,
    cfprAdaptorHostIscsiIfPurpose                                    CfprAdaptorPurpose,
    cfprAdaptorHostIscsiIfRevision                                   SnmpAdminString,
    cfprAdaptorHostIscsiIfSerial                                     SnmpAdminString,
    cfprAdaptorHostIscsiIfSide                                       CfprNetworkSide,
    cfprAdaptorHostIscsiIfSlotId                                     Gauge32,
    cfprAdaptorHostIscsiIfSwitchId                                   CfprNetworkSwitchId,
    cfprAdaptorHostIscsiIfThermal                                    CfprEquipmentSensorThresholdStatus,
    cfprAdaptorHostIscsiIfTransport                                  CfprNetworkTransport,
    cfprAdaptorHostIscsiIfType                                       CfprNetworkConnectionType,
    cfprAdaptorHostIscsiIfVendor                                     SnmpAdminString,
    cfprAdaptorHostIscsiIfVnicDn                                     SnmpAdminString,
    cfprAdaptorHostIscsiIfVnicName                                   SnmpAdminString,
    cfprAdaptorHostIscsiIfVoltage                                    CfprEquipmentSensorThresholdStatus,
    cfprAdaptorHostIscsiIfServiceState                               CfprAdaptorServiceState,
    cfprAdaptorHostIscsiIfVcAdminState                               CfprDcxAdminState
}

cfprAdaptorHostIscsiIfInstanceId OBJECT-TYPE
    SYNTAX       CfprManagedObjectId
    MAX-ACCESS   not-accessible
    STATUS       current
    DESCRIPTION
        "Instance identifier of the managed object."
    ::= { cfprAdaptorHostIscsiIfEntry 1 }

cfprAdaptorHostIscsiIfDn OBJECT-TYPE
    SYNTAX       CfprManagedObjectDn
    MAX-ACCESS   read-only
    STATUS       current
    DESCRIPTION
        "Cisco Firepower adaptor:HostIscsiIf:dn managed object property"
    ::= { cfprAdaptorHostIscsiIfEntry 2 }

cfprAdaptorHostIscsiIfRn OBJECT-TYPE
    SYNTAX       SnmpAdminString
    MAX-ACCESS   read-only
    STATUS       current
    DESCRIPTION
        "Cisco Firepower adaptor:HostIscsiIf:rn managed object property"
    ::= { cfprAdaptorHostIscsiIfEntry 3 }

cfprAdaptorHostIscsiIfAdminState OBJECT-TYPE
    SYNTAX       CfprAdaptorHostIfAdminState
    MAX-ACCESS   read-only
    STATUS       current
    DESCRIPTION
        "Cisco Firepower adaptor:HostIscsiIf:adminState
        managed object property"
    ::= { cfprAdaptorHostIscsiIfEntry 4 }

cfprAdaptorHostIscsiIfBootDev OBJECT-TYPE
    SYNTAX       CfprAdaptorHostIfBootDev
    MAX-ACCESS   read-only
    STATUS       current
    DESCRIPTION
        "Cisco Firepower adaptor:HostIscsiIf:bootDev managed
        object property"
    ::= { cfprAdaptorHostIscsiIfEntry 5 }

cfprAdaptorHostIscsiIfChassisId OBJECT-TYPE
    SYNTAX       Gauge32
    MAX-ACCESS   read-only
    STATUS       current
    DESCRIPTION
        "Cisco Firepower adaptor:HostIscsiIf:chassisId
        managed object property"
    ::= { cfprAdaptorHostIscsiIfEntry 6 }

cfprAdaptorHostIscsiIfDiscovery OBJECT-TYPE
    SYNTAX       CfprEtherSatelliteConnectionDisc
    MAX-ACCESS   read-only
    STATUS       current
    DESCRIPTION
        "Cisco Firepower adaptor:HostIscsiIf:discovery
        managed object property"
    ::= { cfprAdaptorHostIscsiIfEntry 7 }

cfprAdaptorHostIscsiIfEpDn OBJECT-TYPE
    SYNTAX       SnmpAdminString
    MAX-ACCESS   read-only
    STATUS       current
    DESCRIPTION
        "Cisco Firepower adaptor:HostIscsiIf:epDn managed object property"
    ::= { cfprAdaptorHostIscsiIfEntry 8 }

cfprAdaptorHostIscsiIfEthEpDn OBJECT-TYPE
    SYNTAX       SnmpAdminString
    MAX-ACCESS   read-only
    STATUS       current
    DESCRIPTION
        "Cisco Firepower adaptor:HostIscsiIf:ethEpDn managed
        object property"
    ::= { cfprAdaptorHostIscsiIfEntry 9 }

cfprAdaptorHostIscsiIfFltAggr OBJECT-TYPE
    SYNTAX       Unsigned64
    MAX-ACCESS   read-only
    STATUS       current
    DESCRIPTION
        "Cisco Firepower adaptor:HostIscsiIf:fltAggr managed
        object property"
    ::= { cfprAdaptorHostIscsiIfEntry 10 }

cfprAdaptorHostIscsiIfHostVisible OBJECT-TYPE
    SYNTAX       CfprAdaptorHostVisibility
    MAX-ACCESS   read-only
    STATUS       current
    DESCRIPTION
        "Cisco Firepower adaptor:HostIscsiIf:hostVisible
        managed object property"
    ::= { cfprAdaptorHostIscsiIfEntry 11 }

cfprAdaptorHostIscsiIfId OBJECT-TYPE
    SYNTAX       Gauge32
    MAX-ACCESS   read-only
    STATUS       current
    DESCRIPTION
        "Cisco Firepower adaptor:HostIscsiIf:id managed object property"
    ::= { cfprAdaptorHostIscsiIfEntry 12 }

cfprAdaptorHostIscsiIfIfRole OBJECT-TYPE
    SYNTAX       CfprNetworkPortRole
    MAX-ACCESS   read-only
    STATUS       current
    DESCRIPTION
        "Cisco Firepower adaptor:HostIscsiIf:ifRole managed
        object property"
    ::= { cfprAdaptorHostIscsiIfEntry 13 }

cfprAdaptorHostIscsiIfIfType OBJECT-TYPE
    SYNTAX       CfprNetworkPhysEpIfType
    MAX-ACCESS   read-only
    STATUS       current
    DESCRIPTION
        "Cisco Firepower adaptor:HostIscsiIf:ifType managed
        object property"
    ::= { cfprAdaptorHostIscsiIfEntry 14 }

cfprAdaptorHostIscsiIfInitiatorName OBJECT-TYPE
    SYNTAX       SnmpAdminString
    MAX-ACCESS   read-only
    STATUS       current
    DESCRIPTION
        "Cisco Firepower adaptor:HostIscsiIf:initiatorName
        managed object property"
    ::= { cfprAdaptorHostIscsiIfEntry 15 }

cfprAdaptorHostIscsiIfLc OBJECT-TYPE
    SYNTAX       CfprFsmLifecycle
    MAX-ACCESS   read-only
    STATUS       current
    DESCRIPTION
        "Cisco Firepower adaptor:HostIscsiIf:lc managed object property"
    ::= { cfprAdaptorHostIscsiIfEntry 16 }

cfprAdaptorHostIscsiIfLinkState OBJECT-TYPE
    SYNTAX       CfprAdaptorLinkState
    MAX-ACCESS   read-only
    STATUS       current
    DESCRIPTION
        "Cisco Firepower adaptor:HostIscsiIf:linkState
        managed object property"
    ::= { cfprAdaptorHostIscsiIfEntry 17 }

cfprAdaptorHostIscsiIfLocale OBJECT-TYPE
    SYNTAX       CfprNetworkLocale
    MAX-ACCESS   read-only
    STATUS       current
    DESCRIPTION
        "Cisco Firepower adaptor:HostIscsiIf:locale managed
        object property"
    ::= { cfprAdaptorHostIscsiIfEntry 18 }

cfprAdaptorHostIscsiIfMac OBJECT-TYPE
    SYNTAX       MacAddress
    MAX-ACCESS   read-only
    STATUS       current
    DESCRIPTION
        "Cisco Firepower adaptor:HostIscsiIf:mac managed object property"
    ::= { cfprAdaptorHostIscsiIfEntry 19 }

cfprAdaptorHostIscsiIfModel OBJECT-TYPE
    SYNTAX       SnmpAdminString
    MAX-ACCESS   read-only
    STATUS       current
    DESCRIPTION
        "Cisco Firepower adaptor:HostIscsiIf:model managed
        object property"
    ::= { cfprAdaptorHostIscsiIfEntry 20 }

cfprAdaptorHostIscsiIfName OBJECT-TYPE
    SYNTAX       SnmpAdminString
    MAX-ACCESS   read-only
    STATUS       current
    DESCRIPTION
        "Cisco Firepower adaptor:HostIscsiIf:name managed object property"
    ::= { cfprAdaptorHostIscsiIfEntry 21 }

cfprAdaptorHostIscsiIfOperQualifierReason OBJECT-TYPE
    SYNTAX       SnmpAdminString
    MAX-ACCESS   read-only
    STATUS       current
    DESCRIPTION
        "Cisco Firepower adaptor:HostIscsiIf:operQualifierReason
        managed object property"
    ::= { cfprAdaptorHostIscsiIfEntry 22 }

cfprAdaptorHostIscsiIfOperState OBJECT-TYPE
    SYNTAX       CfprEquipmentOperability
    MAX-ACCESS   read-only
    STATUS       current
    DESCRIPTION
        "Cisco Firepower adaptor:HostIscsiIf:operState
        managed object property"
    ::= { cfprAdaptorHostIscsiIfEntry 23 }

cfprAdaptorHostIscsiIfOperability OBJECT-TYPE
    SYNTAX       CfprEquipmentOperability
    MAX-ACCESS   read-only
    STATUS       current
    DESCRIPTION
        "Cisco Firepower adaptor:HostIscsiIf:operability
        managed object property"
    ::= { cfprAdaptorHostIscsiIfEntry 24 }

cfprAdaptorHostIscsiIfOrder OBJECT-TYPE
    SYNTAX       Gauge32
    MAX-ACCESS   read-only
    STATUS       current
    DESCRIPTION
        "Cisco Firepower adaptor:HostIscsiIf:order managed
        object property"
    ::= { cfprAdaptorHostIscsiIfEntry 25 }

cfprAdaptorHostIscsiIfOriginalMac OBJECT-TYPE
    SYNTAX       MacAddress
    MAX-ACCESS   read-only
    STATUS       current
    DESCRIPTION
        "Cisco Firepower adaptor:HostIscsiIf:originalMac
        managed object property"
    ::= { cfprAdaptorHostIscsiIfEntry 26 }

cfprAdaptorHostIscsiIfPciAddr OBJECT-TYPE
    SYNTAX       SnmpAdminString
    MAX-ACCESS   read-only
    STATUS       current
    DESCRIPTION
        "Cisco Firepower adaptor:HostIscsiIf:pciAddr managed
        object property"
    ::= { cfprAdaptorHostIscsiIfEntry 27 }

cfprAdaptorHostIscsiIfPciFunc OBJECT-TYPE
    SYNTAX       Gauge32
    MAX-ACCESS   read-only
    STATUS       current
    DESCRIPTION
        "Cisco Firepower adaptor:HostIscsiIf:pciFunc managed
        object property"
    ::= { cfprAdaptorHostIscsiIfEntry 28 }

cfprAdaptorHostIscsiIfPciSlot OBJECT-TYPE
    SYNTAX       Gauge32
    MAX-ACCESS   read-only
    STATUS       current
    DESCRIPTION
        "Cisco Firepower adaptor:HostIscsiIf:pciSlot managed
        object property"
    ::= { cfprAdaptorHostIscsiIfEntry 29 }

cfprAdaptorHostIscsiIfPeerChassisId OBJECT-TYPE
    SYNTAX       Gauge32
    MAX-ACCESS   read-only
    STATUS       current
    DESCRIPTION
        "Cisco Firepower adaptor:HostIscsiIf:peerChassisId
        managed object property"
    ::= { cfprAdaptorHostIscsiIfEntry 30 }

cfprAdaptorHostIscsiIfPeerDn OBJECT-TYPE
    SYNTAX       SnmpAdminString
    MAX-ACCESS   read-only
    STATUS       current
    DESCRIPTION
        "Cisco Firepower adaptor:HostIscsiIf:peerDn managed
        object property"
    ::= { cfprAdaptorHostIscsiIfEntry 31 }

cfprAdaptorHostIscsiIfPeerPortId OBJECT-TYPE
    SYNTAX       Gauge32
    MAX-ACCESS   read-only
    STATUS       current
    DESCRIPTION
        "Cisco Firepower adaptor:HostIscsiIf:peerPortId
        managed object property"
    ::= { cfprAdaptorHostIscsiIfEntry 32 }

cfprAdaptorHostIscsiIfPeerSlotId OBJECT-TYPE
    SYNTAX       Gauge32
    MAX-ACCESS   read-only
    STATUS       current
    DESCRIPTION
        "Cisco Firepower adaptor:HostIscsiIf:peerSlotId
        managed object property"
    ::= { cfprAdaptorHostIscsiIfEntry 33 }

cfprAdaptorHostIscsiIfPerf OBJECT-TYPE
    SYNTAX       CfprEquipmentSensorThresholdStatus
    MAX-ACCESS   read-only
    STATUS       current
    DESCRIPTION
        "Cisco Firepower adaptor:HostIscsiIf:perf managed object property"
    ::= { cfprAdaptorHostIscsiIfEntry 34 }

cfprAdaptorHostIscsiIfPortId OBJECT-TYPE
    SYNTAX       Gauge32
    MAX-ACCESS   read-only
    STATUS       current
    DESCRIPTION
        "Cisco Firepower adaptor:HostIscsiIf:portId managed
        object property"
    ::= { cfprAdaptorHostIscsiIfEntry 35 }

cfprAdaptorHostIscsiIfPower OBJECT-TYPE
    SYNTAX       CfprEquipmentPowerState
    MAX-ACCESS   read-only
    STATUS       current
    DESCRIPTION
        "Cisco Firepower adaptor:HostIscsiIf:power managed
        object property"
    ::= { cfprAdaptorHostIscsiIfEntry 36 }

cfprAdaptorHostIscsiIfPresence OBJECT-TYPE
    SYNTAX       CfprEquipmentPresence
    MAX-ACCESS   read-only
    STATUS       current
    DESCRIPTION
        "Cisco Firepower adaptor:HostIscsiIf:presence managed
        object property"
    ::= { cfprAdaptorHostIscsiIfEntry 37 }

cfprAdaptorHostIscsiIfPurpose OBJECT-TYPE
    SYNTAX       CfprAdaptorPurpose
    MAX-ACCESS   read-only
    STATUS       current
    DESCRIPTION
        "Cisco Firepower adaptor:HostIscsiIf:purpose managed
        object property"
    ::= { cfprAdaptorHostIscsiIfEntry 38 }

cfprAdaptorHostIscsiIfRevision OBJECT-TYPE
    SYNTAX       SnmpAdminString
    MAX-ACCESS   read-only
    STATUS       current
    DESCRIPTION
        "Cisco Firepower adaptor:HostIscsiIf:revision managed
        object property"
    ::= { cfprAdaptorHostIscsiIfEntry 39 }

cfprAdaptorHostIscsiIfSerial OBJECT-TYPE
    SYNTAX       SnmpAdminString
    MAX-ACCESS   read-only
    STATUS       current
    DESCRIPTION
        "Cisco Firepower adaptor:HostIscsiIf:serial managed
        object property"
    ::= { cfprAdaptorHostIscsiIfEntry 40 }

cfprAdaptorHostIscsiIfSide OBJECT-TYPE
    SYNTAX       CfprNetworkSide
    MAX-ACCESS   read-only
    STATUS       current
    DESCRIPTION
        "Cisco Firepower adaptor:HostIscsiIf:side managed object property"
    ::= { cfprAdaptorHostIscsiIfEntry 41 }

cfprAdaptorHostIscsiIfSlotId OBJECT-TYPE
    SYNTAX       Gauge32
    MAX-ACCESS   read-only
    STATUS       current
    DESCRIPTION
        "Cisco Firepower adaptor:HostIscsiIf:slotId managed
        object property"
    ::= { cfprAdaptorHostIscsiIfEntry 42 }

cfprAdaptorHostIscsiIfSwitchId OBJECT-TYPE
    SYNTAX       CfprNetworkSwitchId
    MAX-ACCESS   read-only
    STATUS       current
    DESCRIPTION
        "Cisco Firepower adaptor:HostIscsiIf:switchId managed
        object property"
    ::= { cfprAdaptorHostIscsiIfEntry 43 }

cfprAdaptorHostIscsiIfThermal OBJECT-TYPE
    SYNTAX       CfprEquipmentSensorThresholdStatus
    MAX-ACCESS   read-only
    STATUS       current
    DESCRIPTION
        "Cisco Firepower adaptor:HostIscsiIf:thermal managed
        object property"
    ::= { cfprAdaptorHostIscsiIfEntry 44 }

cfprAdaptorHostIscsiIfTransport OBJECT-TYPE
    SYNTAX       CfprNetworkTransport
    MAX-ACCESS   read-only
    STATUS       current
    DESCRIPTION
        "Cisco Firepower adaptor:HostIscsiIf:transport
        managed object property"
    ::= { cfprAdaptorHostIscsiIfEntry 45 }

cfprAdaptorHostIscsiIfType OBJECT-TYPE
    SYNTAX       CfprNetworkConnectionType
    MAX-ACCESS   read-only
    STATUS       current
    DESCRIPTION
        "Cisco Firepower adaptor:HostIscsiIf:type managed object property"
    ::= { cfprAdaptorHostIscsiIfEntry 46 }

cfprAdaptorHostIscsiIfVendor OBJECT-TYPE
    SYNTAX       SnmpAdminString
    MAX-ACCESS   read-only
    STATUS       current
    DESCRIPTION
        "Cisco Firepower adaptor:HostIscsiIf:vendor managed
        object property"
    ::= { cfprAdaptorHostIscsiIfEntry 47 }

cfprAdaptorHostIscsiIfVnicDn OBJECT-TYPE
    SYNTAX       SnmpAdminString
    MAX-ACCESS   read-only
    STATUS       current
    DESCRIPTION
        "Cisco Firepower adaptor:HostIscsiIf:vnicDn managed
        object property"
    ::= { cfprAdaptorHostIscsiIfEntry 48 }

cfprAdaptorHostIscsiIfVnicName OBJECT-TYPE
    SYNTAX       SnmpAdminString
    MAX-ACCESS   read-only
    STATUS       current
    DESCRIPTION
        "Cisco Firepower adaptor:HostIscsiIf:vnicName managed
        object property"
    ::= { cfprAdaptorHostIscsiIfEntry 49 }

cfprAdaptorHostIscsiIfVoltage OBJECT-TYPE
    SYNTAX       CfprEquipmentSensorThresholdStatus
    MAX-ACCESS   read-only
    STATUS       current
    DESCRIPTION
        "Cisco Firepower adaptor:HostIscsiIf:voltage managed
        object property"
    ::= { cfprAdaptorHostIscsiIfEntry 50 }

cfprAdaptorHostIscsiIfServiceState OBJECT-TYPE
    SYNTAX       CfprAdaptorServiceState
    MAX-ACCESS   read-only
    STATUS       current
    DESCRIPTION
        "Cisco Firepower adaptor:HostIscsiIf:serviceState
        managed object property"
    ::= { cfprAdaptorHostIscsiIfEntry 51 }

cfprAdaptorHostIscsiIfVcAdminState OBJECT-TYPE
    SYNTAX       CfprDcxAdminState
    MAX-ACCESS   read-only
    STATUS       current
    DESCRIPTION
        "Cisco Firepower adaptor:HostIscsiIf:vcAdminState
        managed object property"
    ::= { cfprAdaptorHostIscsiIfEntry 52 }

cfprAdaptorHostIscsiIfProfileTable OBJECT-TYPE
    SYNTAX           SEQUENCE OF CfprAdaptorHostIscsiIfProfileEntry
    MAX-ACCESS       not-accessible
    STATUS           current
    DESCRIPTION
        "Cisco Firepower adaptor:HostIscsiIfProfile managed object table"
    ::= { cfprAdaptorObjects 67 }

cfprAdaptorHostIscsiIfProfileEntry OBJECT-TYPE
    SYNTAX           CfprAdaptorHostIscsiIfProfileEntry
    MAX-ACCESS       not-accessible
    STATUS           current
    DESCRIPTION
        "Entry for the cfprAdaptorHostIscsiIfProfileTable table."
    INDEX { cfprAdaptorHostIscsiIfProfileInstanceId }
    ::= { cfprAdaptorHostIscsiIfProfileTable 1 }

CfprAdaptorHostIscsiIfProfileEntry ::= SEQUENCE {
    cfprAdaptorHostIscsiIfProfileInstanceId                          CfprManagedObjectId,
    cfprAdaptorHostIscsiIfProfileDn                                  CfprManagedObjectDn,
    cfprAdaptorHostIscsiIfProfileRn                                  SnmpAdminString,
    cfprAdaptorHostIscsiIfProfileDescr                               SnmpAdminString,
    cfprAdaptorHostIscsiIfProfileIntId                               SnmpAdminString,
    cfprAdaptorHostIscsiIfProfileName                                SnmpAdminString,
    cfprAdaptorHostIscsiIfProfilePolicyLevel                         Gauge32,
    cfprAdaptorHostIscsiIfProfilePolicyOwner                         CfprPolicyPolicyOwner
}

cfprAdaptorHostIscsiIfProfileInstanceId OBJECT-TYPE
    SYNTAX       CfprManagedObjectId
    MAX-ACCESS   not-accessible
    STATUS       current
    DESCRIPTION
        "Instance identifier of the managed object."
    ::= { cfprAdaptorHostIscsiIfProfileEntry 1 }

cfprAdaptorHostIscsiIfProfileDn OBJECT-TYPE
    SYNTAX       CfprManagedObjectDn
    MAX-ACCESS   read-only
    STATUS       current
    DESCRIPTION
        "Cisco Firepower adaptor:HostIscsiIfProfile:dn
        managed object property"
    ::= { cfprAdaptorHostIscsiIfProfileEntry 2 }

cfprAdaptorHostIscsiIfProfileRn OBJECT-TYPE
    SYNTAX       SnmpAdminString
    MAX-ACCESS   read-only
    STATUS       current
    DESCRIPTION
        "Cisco Firepower adaptor:HostIscsiIfProfile:rn
        managed object property"
    ::= { cfprAdaptorHostIscsiIfProfileEntry 3 }

cfprAdaptorHostIscsiIfProfileDescr OBJECT-TYPE
    SYNTAX       SnmpAdminString
    MAX-ACCESS   read-only
    STATUS       current
    DESCRIPTION
        "Cisco Firepower adaptor:HostIscsiIfProfile:descr
        managed object property"
    ::= { cfprAdaptorHostIscsiIfProfileEntry 4 }

cfprAdaptorHostIscsiIfProfileIntId OBJECT-TYPE
    SYNTAX       SnmpAdminString
    MAX-ACCESS   read-only
    STATUS       current
    DESCRIPTION
        "Cisco Firepower adaptor:HostIscsiIfProfile:intId
        managed object property"
    ::= { cfprAdaptorHostIscsiIfProfileEntry 5 }

cfprAdaptorHostIscsiIfProfileName OBJECT-TYPE
    SYNTAX       SnmpAdminString
    MAX-ACCESS   read-only
    STATUS       current
    DESCRIPTION
        "Cisco Firepower adaptor:HostIscsiIfProfile:name
        managed object property"
    ::= { cfprAdaptorHostIscsiIfProfileEntry 6 }

cfprAdaptorHostIscsiIfProfilePolicyLevel OBJECT-TYPE
    SYNTAX       Gauge32
    MAX-ACCESS   read-only
    STATUS       current
    DESCRIPTION
        "Cisco Firepower adaptor:HostIscsiIfProfile:policyLevel
        managed object property"
    ::= { cfprAdaptorHostIscsiIfProfileEntry 7 }

cfprAdaptorHostIscsiIfProfilePolicyOwner OBJECT-TYPE
    SYNTAX       CfprPolicyPolicyOwner
    MAX-ACCESS   read-only
    STATUS       current
    DESCRIPTION
        "Cisco Firepower adaptor:HostIscsiIfProfile:policyOwner
        managed object property"
    ::= { cfprAdaptorHostIscsiIfProfileEntry 8 }

cfprAdaptorHostMgmtCapTable OBJECT-TYPE
    SYNTAX           SEQUENCE OF CfprAdaptorHostMgmtCapEntry
    MAX-ACCESS       not-accessible
    STATUS           current
    DESCRIPTION
        "Cisco Firepower adaptor:HostMgmtCap managed object table"
    ::= { cfprAdaptorObjects 68 }

cfprAdaptorHostMgmtCapEntry OBJECT-TYPE
    SYNTAX           CfprAdaptorHostMgmtCapEntry
    MAX-ACCESS       not-accessible
    STATUS           current
    DESCRIPTION
        "Entry for the cfprAdaptorHostMgmtCapTable table."
    INDEX { cfprAdaptorHostMgmtCapInstanceId }
    ::= { cfprAdaptorHostMgmtCapTable 1 }

CfprAdaptorHostMgmtCapEntry ::= SEQUENCE {
    cfprAdaptorHostMgmtCapInstanceId                                 CfprManagedObjectId,
    cfprAdaptorHostMgmtCapDn                                         CfprManagedObjectDn,
    cfprAdaptorHostMgmtCapRn                                         SnmpAdminString,
    cfprAdaptorHostMgmtCapMode                                       CfprAdaptorMgmtCapMode,
    cfprAdaptorHostMgmtCapOperPowerRequirement                       CfprAdaptorMgmtCapOperPowerRequirement,
    cfprAdaptorHostMgmtCapPreboot                                    CfprAdaptorHostMgmtCapPreboot,
    cfprAdaptorHostMgmtCapPresence                                   CfprAdaptorHostMgmtCapPresence,
    cfprAdaptorHostMgmtCapRebootActionOnDestructive                  CfprAdaptorMgmtCapRebootActionOnDestructive
}

cfprAdaptorHostMgmtCapInstanceId OBJECT-TYPE
    SYNTAX       CfprManagedObjectId
    MAX-ACCESS   not-accessible
    STATUS       current
    DESCRIPTION
        "Instance identifier of the managed object."
    ::= { cfprAdaptorHostMgmtCapEntry 1 }

cfprAdaptorHostMgmtCapDn OBJECT-TYPE
    SYNTAX       CfprManagedObjectDn
    MAX-ACCESS   read-only
    STATUS       current
    DESCRIPTION
        "Cisco Firepower adaptor:HostMgmtCap:dn managed object property"
    ::= { cfprAdaptorHostMgmtCapEntry 2 }

cfprAdaptorHostMgmtCapRn OBJECT-TYPE
    SYNTAX       SnmpAdminString
    MAX-ACCESS   read-only
    STATUS       current
    DESCRIPTION
        "Cisco Firepower adaptor:HostMgmtCap:rn managed object property"
    ::= { cfprAdaptorHostMgmtCapEntry 3 }

cfprAdaptorHostMgmtCapMode OBJECT-TYPE
    SYNTAX       CfprAdaptorMgmtCapMode
    MAX-ACCESS   read-only
    STATUS       current
    DESCRIPTION
        "Cisco Firepower adaptor:HostMgmtCap:mode managed object property"
    ::= { cfprAdaptorHostMgmtCapEntry 4 }

cfprAdaptorHostMgmtCapOperPowerRequirement OBJECT-TYPE
    SYNTAX       CfprAdaptorMgmtCapOperPowerRequirement
    MAX-ACCESS   read-only
    STATUS       current
    DESCRIPTION
        "Cisco Firepower adaptor:HostMgmtCap:operPowerRequirement
        managed object property"
    ::= { cfprAdaptorHostMgmtCapEntry 5 }

cfprAdaptorHostMgmtCapPreboot OBJECT-TYPE
    SYNTAX       CfprAdaptorHostMgmtCapPreboot
    MAX-ACCESS   read-only
    STATUS       current
    DESCRIPTION
        "Cisco Firepower adaptor:HostMgmtCap:preboot managed
        object property"
    ::= { cfprAdaptorHostMgmtCapEntry 6 }

cfprAdaptorHostMgmtCapPresence OBJECT-TYPE
    SYNTAX       CfprAdaptorHostMgmtCapPresence
    MAX-ACCESS   read-only
    STATUS       current
    DESCRIPTION
        "Cisco Firepower adaptor:HostMgmtCap:presence managed
        object property"
    ::= { cfprAdaptorHostMgmtCapEntry 7 }

cfprAdaptorHostMgmtCapRebootActionOnDestructive OBJECT-TYPE
    SYNTAX       CfprAdaptorMgmtCapRebootActionOnDestructive
    MAX-ACCESS   read-only
    STATUS       current
    DESCRIPTION
        "Cisco Firepower adaptor:HostMgmtCap:rebootActionOnDestructive
        managed object property"
    ::= { cfprAdaptorHostMgmtCapEntry 8 }

cfprAdaptorHostPortTable OBJECT-TYPE
    SYNTAX           SEQUENCE OF CfprAdaptorHostPortEntry
    MAX-ACCESS       not-accessible
    STATUS           current
    DESCRIPTION
        "Cisco Firepower adaptor:HostPort managed object table"
    ::= { cfprAdaptorObjects 69 }

cfprAdaptorHostPortEntry OBJECT-TYPE
    SYNTAX           CfprAdaptorHostPortEntry
    MAX-ACCESS       not-accessible
    STATUS           current
    DESCRIPTION
        "Entry for the cfprAdaptorHostPortTable table."
    INDEX { cfprAdaptorHostPortInstanceId }
    ::= { cfprAdaptorHostPortTable 1 }

CfprAdaptorHostPortEntry ::= SEQUENCE {
    cfprAdaptorHostPortInstanceId                                    CfprManagedObjectId,
    cfprAdaptorHostPortDn                                            CfprManagedObjectDn,
    cfprAdaptorHostPortRn                                            SnmpAdminString,
    cfprAdaptorHostPortFltAggr                                       Unsigned64,
    cfprAdaptorHostPortId                                            CfprAdaptorHostPortId,
    cfprAdaptorHostPortLocationDn                                    SnmpAdminString,
    cfprAdaptorHostPortModel                                         SnmpAdminString,
    cfprAdaptorHostPortOperQualifierReason                           SnmpAdminString,
    cfprAdaptorHostPortOperState                                     CfprEquipmentOperability,
    cfprAdaptorHostPortOperability                                   CfprEquipmentOperability,
    cfprAdaptorHostPortPerf                                          CfprEquipmentSensorThresholdStatus,
    cfprAdaptorHostPortPower                                         CfprEquipmentPowerState,
    cfprAdaptorHostPortPresence                                      CfprEquipmentPresence,
    cfprAdaptorHostPortRevision                                      SnmpAdminString,
    cfprAdaptorHostPortSerial                                        SnmpAdminString,
    cfprAdaptorHostPortThermal                                       CfprEquipmentSensorThresholdStatus,
    cfprAdaptorHostPortVendor                                        SnmpAdminString,
    cfprAdaptorHostPortVoltage                                       CfprEquipmentSensorThresholdStatus
}

cfprAdaptorHostPortInstanceId OBJECT-TYPE
    SYNTAX       CfprManagedObjectId
    MAX-ACCESS   not-accessible
    STATUS       current
    DESCRIPTION
        "Instance identifier of the managed object."
    ::= { cfprAdaptorHostPortEntry 1 }

cfprAdaptorHostPortDn OBJECT-TYPE
    SYNTAX       CfprManagedObjectDn
    MAX-ACCESS   read-only
    STATUS       current
    DESCRIPTION
        "Cisco Firepower adaptor:HostPort:dn managed object property"
    ::= { cfprAdaptorHostPortEntry 2 }

cfprAdaptorHostPortRn OBJECT-TYPE
    SYNTAX       SnmpAdminString
    MAX-ACCESS   read-only
    STATUS       current
    DESCRIPTION
        "Cisco Firepower adaptor:HostPort:rn managed object property"
    ::= { cfprAdaptorHostPortEntry 3 }

cfprAdaptorHostPortFltAggr OBJECT-TYPE
    SYNTAX       Unsigned64
    MAX-ACCESS   read-only
    STATUS       current
    DESCRIPTION
        "Cisco Firepower adaptor:HostPort:fltAggr managed object property"
    ::= { cfprAdaptorHostPortEntry 4 }

cfprAdaptorHostPortId OBJECT-TYPE
    SYNTAX       CfprAdaptorHostPortId
    MAX-ACCESS   read-only
    STATUS       current
    DESCRIPTION
        "Cisco Firepower adaptor:HostPort:id managed object property"
    ::= { cfprAdaptorHostPortEntry 5 }

cfprAdaptorHostPortLocationDn OBJECT-TYPE
    SYNTAX       SnmpAdminString
    MAX-ACCESS   read-only
    STATUS       current
    DESCRIPTION
        "Cisco Firepower adaptor:HostPort:locationDn managed
        object property"
    ::= { cfprAdaptorHostPortEntry 6 }

cfprAdaptorHostPortModel OBJECT-TYPE
    SYNTAX       SnmpAdminString
    MAX-ACCESS   read-only
    STATUS       current
    DESCRIPTION
        "Cisco Firepower adaptor:HostPort:model managed object property"
    ::= { cfprAdaptorHostPortEntry 7 }

cfprAdaptorHostPortOperQualifierReason OBJECT-TYPE
    SYNTAX       SnmpAdminString
    MAX-ACCESS   read-only
    STATUS       current
    DESCRIPTION
        "Cisco Firepower adaptor:HostPort:operQualifierReason
        managed object property"
    ::= { cfprAdaptorHostPortEntry 8 }

cfprAdaptorHostPortOperState OBJECT-TYPE
    SYNTAX       CfprEquipmentOperability
    MAX-ACCESS   read-only
    STATUS       current
    DESCRIPTION
        "Cisco Firepower adaptor:HostPort:operState managed
        object property"
    ::= { cfprAdaptorHostPortEntry 9 }

cfprAdaptorHostPortOperability OBJECT-TYPE
    SYNTAX       CfprEquipmentOperability
    MAX-ACCESS   read-only
    STATUS       current
    DESCRIPTION
        "Cisco Firepower adaptor:HostPort:operability managed
        object property"
    ::= { cfprAdaptorHostPortEntry 10 }

cfprAdaptorHostPortPerf OBJECT-TYPE
    SYNTAX       CfprEquipmentSensorThresholdStatus
    MAX-ACCESS   read-only
    STATUS       current
    DESCRIPTION
        "Cisco Firepower adaptor:HostPort:perf managed object property"
    ::= { cfprAdaptorHostPortEntry 11 }

cfprAdaptorHostPortPower OBJECT-TYPE
    SYNTAX       CfprEquipmentPowerState
    MAX-ACCESS   read-only
    STATUS       current
    DESCRIPTION
        "Cisco Firepower adaptor:HostPort:power managed object property"
    ::= { cfprAdaptorHostPortEntry 12 }

cfprAdaptorHostPortPresence OBJECT-TYPE
    SYNTAX       CfprEquipmentPresence
    MAX-ACCESS   read-only
    STATUS       current
    DESCRIPTION
        "Cisco Firepower adaptor:HostPort:presence managed
        object property"
    ::= { cfprAdaptorHostPortEntry 13 }

cfprAdaptorHostPortRevision OBJECT-TYPE
    SYNTAX       SnmpAdminString
    MAX-ACCESS   read-only
    STATUS       current
    DESCRIPTION
        "Cisco Firepower adaptor:HostPort:revision managed
        object property"
    ::= { cfprAdaptorHostPortEntry 14 }

cfprAdaptorHostPortSerial OBJECT-TYPE
    SYNTAX       SnmpAdminString
    MAX-ACCESS   read-only
    STATUS       current
    DESCRIPTION
        "Cisco Firepower adaptor:HostPort:serial managed object property"
    ::= { cfprAdaptorHostPortEntry 15 }

cfprAdaptorHostPortThermal OBJECT-TYPE
    SYNTAX       CfprEquipmentSensorThresholdStatus
    MAX-ACCESS   read-only
    STATUS       current
    DESCRIPTION
        "Cisco Firepower adaptor:HostPort:thermal managed object property"
    ::= { cfprAdaptorHostPortEntry 16 }

cfprAdaptorHostPortVendor OBJECT-TYPE
    SYNTAX       SnmpAdminString
    MAX-ACCESS   read-only
    STATUS       current
    DESCRIPTION
        "Cisco Firepower adaptor:HostPort:vendor managed object property"
    ::= { cfprAdaptorHostPortEntry 17 }

cfprAdaptorHostPortVoltage OBJECT-TYPE
    SYNTAX       CfprEquipmentSensorThresholdStatus
    MAX-ACCESS   read-only
    STATUS       current
    DESCRIPTION
        "Cisco Firepower adaptor:HostPort:voltage managed object property"
    ::= { cfprAdaptorHostPortEntry 18 }

cfprAdaptorHostPortCapTable OBJECT-TYPE
    SYNTAX           SEQUENCE OF CfprAdaptorHostPortCapEntry
    MAX-ACCESS       not-accessible
    STATUS           current
    DESCRIPTION
        "Cisco Firepower adaptor:HostPortCap managed object table"
    ::= { cfprAdaptorObjects 70 }

cfprAdaptorHostPortCapEntry OBJECT-TYPE
    SYNTAX           CfprAdaptorHostPortCapEntry
    MAX-ACCESS       not-accessible
    STATUS           current
    DESCRIPTION
        "Entry for the cfprAdaptorHostPortCapTable table."
    INDEX { cfprAdaptorHostPortCapInstanceId }
    ::= { cfprAdaptorHostPortCapTable 1 }

CfprAdaptorHostPortCapEntry ::= SEQUENCE {
    cfprAdaptorHostPortCapInstanceId                                 CfprManagedObjectId,
    cfprAdaptorHostPortCapDn                                         CfprManagedObjectDn,
    cfprAdaptorHostPortCapRn                                         SnmpAdminString,
    cfprAdaptorHostPortCapMaxPorts                                   Gauge32
}

cfprAdaptorHostPortCapInstanceId OBJECT-TYPE
    SYNTAX       CfprManagedObjectId
    MAX-ACCESS   not-accessible
    STATUS       current
    DESCRIPTION
        "Instance identifier of the managed object."
    ::= { cfprAdaptorHostPortCapEntry 1 }

cfprAdaptorHostPortCapDn OBJECT-TYPE
    SYNTAX       CfprManagedObjectDn
    MAX-ACCESS   read-only
    STATUS       current
    DESCRIPTION
        "Cisco Firepower adaptor:HostPortCap:dn managed object property"
    ::= { cfprAdaptorHostPortCapEntry 2 }

cfprAdaptorHostPortCapRn OBJECT-TYPE
    SYNTAX       SnmpAdminString
    MAX-ACCESS   read-only
    STATUS       current
    DESCRIPTION
        "Cisco Firepower adaptor:HostPortCap:rn managed object property"
    ::= { cfprAdaptorHostPortCapEntry 3 }

cfprAdaptorHostPortCapMaxPorts OBJECT-TYPE
    SYNTAX       Gauge32
    MAX-ACCESS   read-only
    STATUS       current
    DESCRIPTION
        "Cisco Firepower adaptor:HostPortCap:maxPorts managed
        object property"
    ::= { cfprAdaptorHostPortCapEntry 4 }

cfprAdaptorHostServiceEthIfTable OBJECT-TYPE
    SYNTAX           SEQUENCE OF CfprAdaptorHostServiceEthIfEntry
    MAX-ACCESS       not-accessible
    STATUS           current
    DESCRIPTION
        "Cisco Firepower adaptor:HostServiceEthIf managed object table"
    ::= { cfprAdaptorObjects 71 }

cfprAdaptorHostServiceEthIfEntry OBJECT-TYPE
    SYNTAX           CfprAdaptorHostServiceEthIfEntry
    MAX-ACCESS       not-accessible
    STATUS           current
    DESCRIPTION
        "Entry for the cfprAdaptorHostServiceEthIfTable table."
    INDEX { cfprAdaptorHostServiceEthIfInstanceId }
    ::= { cfprAdaptorHostServiceEthIfTable 1 }

CfprAdaptorHostServiceEthIfEntry ::= SEQUENCE {
    cfprAdaptorHostServiceEthIfInstanceId                            CfprManagedObjectId,
    cfprAdaptorHostServiceEthIfDn                                    CfprManagedObjectDn,
    cfprAdaptorHostServiceEthIfRn                                    SnmpAdminString,
    cfprAdaptorHostServiceEthIfAdminState                            CfprAdaptorHostIfAdminState,
    cfprAdaptorHostServiceEthIfBootDev                               CfprAdaptorHostIfBootDev,
    cfprAdaptorHostServiceEthIfChassisId                             Gauge32,
    cfprAdaptorHostServiceEthIfDiscovery                             CfprEtherSatelliteConnectionDisc,
    cfprAdaptorHostServiceEthIfEpDn                                  SnmpAdminString,
    cfprAdaptorHostServiceEthIfFltAggr                               Unsigned64,
    cfprAdaptorHostServiceEthIfId                                    Gauge32,
    cfprAdaptorHostServiceEthIfIfRole                                CfprAdaptorHostServiceEthIfIfRole,
    cfprAdaptorHostServiceEthIfIfType                                CfprNetworkPhysEpIfType,
    cfprAdaptorHostServiceEthIfLc                                    CfprFsmLifecycle,
    cfprAdaptorHostServiceEthIfLinkState                             CfprAdaptorLinkState,
    cfprAdaptorHostServiceEthIfLocale                                CfprNetworkLocale,
    cfprAdaptorHostServiceEthIfMac                                   MacAddress,
    cfprAdaptorHostServiceEthIfModel                                 SnmpAdminString,
    cfprAdaptorHostServiceEthIfMtu                                   Gauge32,
    cfprAdaptorHostServiceEthIfName                                  SnmpAdminString,
    cfprAdaptorHostServiceEthIfOperQualifierReason                   SnmpAdminString,
    cfprAdaptorHostServiceEthIfOperState                             CfprEquipmentOperability,
    cfprAdaptorHostServiceEthIfOperability                           CfprEquipmentOperability,
    cfprAdaptorHostServiceEthIfOrder                                 Gauge32,
    cfprAdaptorHostServiceEthIfOriginalMac                           MacAddress,
    cfprAdaptorHostServiceEthIfPciAddr                               SnmpAdminString,
    cfprAdaptorHostServiceEthIfPciFunc                               Gauge32,
    cfprAdaptorHostServiceEthIfPciSlot                               Gauge32,
    cfprAdaptorHostServiceEthIfPeerChassisId                         Gauge32,
    cfprAdaptorHostServiceEthIfPeerDn                                SnmpAdminString,
    cfprAdaptorHostServiceEthIfPeerPortId                            Gauge32,
    cfprAdaptorHostServiceEthIfPeerSlotId                            Gauge32,
    cfprAdaptorHostServiceEthIfPerf                                  CfprEquipmentSensorThresholdStatus,
    cfprAdaptorHostServiceEthIfPortId                                Gauge32,
    cfprAdaptorHostServiceEthIfPower                                 CfprEquipmentPowerState,
    cfprAdaptorHostServiceEthIfPresence                              CfprEquipmentPresence,
    cfprAdaptorHostServiceEthIfPurpose                               CfprAdaptorPurpose,
    cfprAdaptorHostServiceEthIfRevision                              SnmpAdminString,
    cfprAdaptorHostServiceEthIfSerial                                SnmpAdminString,
    cfprAdaptorHostServiceEthIfSide                                  CfprNetworkSide,
    cfprAdaptorHostServiceEthIfSlotId                                Gauge32,
    cfprAdaptorHostServiceEthIfSwitchId                              CfprNetworkSwitchId,
    cfprAdaptorHostServiceEthIfThermal                               CfprEquipmentSensorThresholdStatus,
    cfprAdaptorHostServiceEthIfTransport                             CfprNetworkTransport,
    cfprAdaptorHostServiceEthIfType                                  CfprNetworkConnectionType,
    cfprAdaptorHostServiceEthIfVendor                                SnmpAdminString,
    cfprAdaptorHostServiceEthIfVnicDn                                SnmpAdminString,
    cfprAdaptorHostServiceEthIfVoltage                               CfprEquipmentSensorThresholdStatus,
    cfprAdaptorHostServiceEthIfServiceState                          CfprAdaptorServiceState,
    cfprAdaptorHostServiceEthIfVcAdminState                          CfprDcxAdminState
}

cfprAdaptorHostServiceEthIfInstanceId OBJECT-TYPE
    SYNTAX       CfprManagedObjectId
    MAX-ACCESS   not-accessible
    STATUS       current
    DESCRIPTION
        "Instance identifier of the managed object."
    ::= { cfprAdaptorHostServiceEthIfEntry 1 }

cfprAdaptorHostServiceEthIfDn OBJECT-TYPE
    SYNTAX       CfprManagedObjectDn
    MAX-ACCESS   read-only
    STATUS       current
    DESCRIPTION
        "Cisco Firepower adaptor:HostServiceEthIf:dn managed
        object property"
    ::= { cfprAdaptorHostServiceEthIfEntry 2 }

cfprAdaptorHostServiceEthIfRn OBJECT-TYPE
    SYNTAX       SnmpAdminString
    MAX-ACCESS   read-only
    STATUS       current
    DESCRIPTION
        "Cisco Firepower adaptor:HostServiceEthIf:rn managed
        object property"
    ::= { cfprAdaptorHostServiceEthIfEntry 3 }

cfprAdaptorHostServiceEthIfAdminState OBJECT-TYPE
    SYNTAX       CfprAdaptorHostIfAdminState
    MAX-ACCESS   read-only
    STATUS       current
    DESCRIPTION
        "Cisco Firepower adaptor:HostServiceEthIf:adminState
        managed object property"
    ::= { cfprAdaptorHostServiceEthIfEntry 4 }

cfprAdaptorHostServiceEthIfBootDev OBJECT-TYPE
    SYNTAX       CfprAdaptorHostIfBootDev
    MAX-ACCESS   read-only
    STATUS       current
    DESCRIPTION
        "Cisco Firepower adaptor:HostServiceEthIf:bootDev
        managed object property"
    ::= { cfprAdaptorHostServiceEthIfEntry 5 }

cfprAdaptorHostServiceEthIfChassisId OBJECT-TYPE
    SYNTAX       Gauge32
    MAX-ACCESS   read-only
    STATUS       current
    DESCRIPTION
        "Cisco Firepower adaptor:HostServiceEthIf:chassisId
        managed object property"
    ::= { cfprAdaptorHostServiceEthIfEntry 6 }

cfprAdaptorHostServiceEthIfDiscovery OBJECT-TYPE
    SYNTAX       CfprEtherSatelliteConnectionDisc
    MAX-ACCESS   read-only
    STATUS       current
    DESCRIPTION
        "Cisco Firepower adaptor:HostServiceEthIf:discovery
        managed object property"
    ::= { cfprAdaptorHostServiceEthIfEntry 7 }

cfprAdaptorHostServiceEthIfEpDn OBJECT-TYPE
    SYNTAX       SnmpAdminString
    MAX-ACCESS   read-only
    STATUS       current
    DESCRIPTION
        "Cisco Firepower adaptor:HostServiceEthIf:epDn
        managed object property"
    ::= { cfprAdaptorHostServiceEthIfEntry 8 }

cfprAdaptorHostServiceEthIfFltAggr OBJECT-TYPE
    SYNTAX       Unsigned64
    MAX-ACCESS   read-only
    STATUS       current
    DESCRIPTION
        "Cisco Firepower adaptor:HostServiceEthIf:fltAggr
        managed object property"
    ::= { cfprAdaptorHostServiceEthIfEntry 9 }

cfprAdaptorHostServiceEthIfId OBJECT-TYPE
    SYNTAX       Gauge32
    MAX-ACCESS   read-only
    STATUS       current
    DESCRIPTION
        "Cisco Firepower adaptor:HostServiceEthIf:id managed
        object property"
    ::= { cfprAdaptorHostServiceEthIfEntry 10 }

cfprAdaptorHostServiceEthIfIfRole OBJECT-TYPE
    SYNTAX       CfprAdaptorHostServiceEthIfIfRole
    MAX-ACCESS   read-only
    STATUS       current
    DESCRIPTION
        "Cisco Firepower adaptor:HostServiceEthIf:ifRole
        managed object property"
    ::= { cfprAdaptorHostServiceEthIfEntry 11 }

cfprAdaptorHostServiceEthIfIfType OBJECT-TYPE
    SYNTAX       CfprNetworkPhysEpIfType
    MAX-ACCESS   read-only
    STATUS       current
    DESCRIPTION
        "Cisco Firepower adaptor:HostServiceEthIf:ifType
        managed object property"
    ::= { cfprAdaptorHostServiceEthIfEntry 12 }

cfprAdaptorHostServiceEthIfLc OBJECT-TYPE
    SYNTAX       CfprFsmLifecycle
    MAX-ACCESS   read-only
    STATUS       current
    DESCRIPTION
        "Cisco Firepower adaptor:HostServiceEthIf:lc managed
        object property"
    ::= { cfprAdaptorHostServiceEthIfEntry 13 }

cfprAdaptorHostServiceEthIfLinkState OBJECT-TYPE
    SYNTAX       CfprAdaptorLinkState
    MAX-ACCESS   read-only
    STATUS       current
    DESCRIPTION
        "Cisco Firepower adaptor:HostServiceEthIf:linkState
        managed object property"
    ::= { cfprAdaptorHostServiceEthIfEntry 14 }

cfprAdaptorHostServiceEthIfLocale OBJECT-TYPE
    SYNTAX       CfprNetworkLocale
    MAX-ACCESS   read-only
    STATUS       current
    DESCRIPTION
        "Cisco Firepower adaptor:HostServiceEthIf:locale
        managed object property"
    ::= { cfprAdaptorHostServiceEthIfEntry 15 }

cfprAdaptorHostServiceEthIfMac OBJECT-TYPE
    SYNTAX       MacAddress
    MAX-ACCESS   read-only
    STATUS       current
    DESCRIPTION
        "Cisco Firepower adaptor:HostServiceEthIf:mac managed
        object property"
    ::= { cfprAdaptorHostServiceEthIfEntry 16 }

cfprAdaptorHostServiceEthIfModel OBJECT-TYPE
    SYNTAX       SnmpAdminString
    MAX-ACCESS   read-only
    STATUS       current
    DESCRIPTION
        "Cisco Firepower adaptor:HostServiceEthIf:model
        managed object property"
    ::= { cfprAdaptorHostServiceEthIfEntry 17 }

cfprAdaptorHostServiceEthIfMtu OBJECT-TYPE
    SYNTAX       Gauge32
    MAX-ACCESS   read-only
    STATUS       current
    DESCRIPTION
        "Cisco Firepower adaptor:HostServiceEthIf:mtu managed
        object property"
    ::= { cfprAdaptorHostServiceEthIfEntry 18 }

cfprAdaptorHostServiceEthIfName OBJECT-TYPE
    SYNTAX       SnmpAdminString
    MAX-ACCESS   read-only
    STATUS       current
    DESCRIPTION
        "Cisco Firepower adaptor:HostServiceEthIf:name
        managed object property"
    ::= { cfprAdaptorHostServiceEthIfEntry 19 }

cfprAdaptorHostServiceEthIfOperQualifierReason OBJECT-TYPE
    SYNTAX       SnmpAdminString
    MAX-ACCESS   read-only
    STATUS       current
    DESCRIPTION
        "Cisco Firepower adaptor:HostServiceEthIf:operQualifierReason
        managed object property"
    ::= { cfprAdaptorHostServiceEthIfEntry 20 }

cfprAdaptorHostServiceEthIfOperState OBJECT-TYPE
    SYNTAX       CfprEquipmentOperability
    MAX-ACCESS   read-only
    STATUS       current
    DESCRIPTION
        "Cisco Firepower adaptor:HostServiceEthIf:operState
        managed object property"
    ::= { cfprAdaptorHostServiceEthIfEntry 21 }

cfprAdaptorHostServiceEthIfOperability OBJECT-TYPE
    SYNTAX       CfprEquipmentOperability
    MAX-ACCESS   read-only
    STATUS       current
    DESCRIPTION
        "Cisco Firepower adaptor:HostServiceEthIf:operability
        managed object property"
    ::= { cfprAdaptorHostServiceEthIfEntry 22 }

cfprAdaptorHostServiceEthIfOrder OBJECT-TYPE
    SYNTAX       Gauge32
    MAX-ACCESS   read-only
    STATUS       current
    DESCRIPTION
        "Cisco Firepower adaptor:HostServiceEthIf:order
        managed object property"
    ::= { cfprAdaptorHostServiceEthIfEntry 23 }

cfprAdaptorHostServiceEthIfOriginalMac OBJECT-TYPE
    SYNTAX       MacAddress
    MAX-ACCESS   read-only
    STATUS       current
    DESCRIPTION
        "Cisco Firepower adaptor:HostServiceEthIf:originalMac
        managed object property"
    ::= { cfprAdaptorHostServiceEthIfEntry 24 }

cfprAdaptorHostServiceEthIfPciAddr OBJECT-TYPE
    SYNTAX       SnmpAdminString
    MAX-ACCESS   read-only
    STATUS       current
    DESCRIPTION
        "Cisco Firepower adaptor:HostServiceEthIf:pciAddr
        managed object property"
    ::= { cfprAdaptorHostServiceEthIfEntry 25 }

cfprAdaptorHostServiceEthIfPciFunc OBJECT-TYPE
    SYNTAX       Gauge32
    MAX-ACCESS   read-only
    STATUS       current
    DESCRIPTION
        "Cisco Firepower adaptor:HostServiceEthIf:pciFunc
        managed object property"
    ::= { cfprAdaptorHostServiceEthIfEntry 26 }

cfprAdaptorHostServiceEthIfPciSlot OBJECT-TYPE
    SYNTAX       Gauge32
    MAX-ACCESS   read-only
    STATUS       current
    DESCRIPTION
        "Cisco Firepower adaptor:HostServiceEthIf:pciSlot
        managed object property"
    ::= { cfprAdaptorHostServiceEthIfEntry 27 }

cfprAdaptorHostServiceEthIfPeerChassisId OBJECT-TYPE
    SYNTAX       Gauge32
    MAX-ACCESS   read-only
    STATUS       current
    DESCRIPTION
        "Cisco Firepower adaptor:HostServiceEthIf:peerChassisId
        managed object property"
    ::= { cfprAdaptorHostServiceEthIfEntry 28 }

cfprAdaptorHostServiceEthIfPeerDn OBJECT-TYPE
    SYNTAX       SnmpAdminString
    MAX-ACCESS   read-only
    STATUS       current
    DESCRIPTION
        "Cisco Firepower adaptor:HostServiceEthIf:peerDn
        managed object property"
    ::= { cfprAdaptorHostServiceEthIfEntry 29 }

cfprAdaptorHostServiceEthIfPeerPortId OBJECT-TYPE
    SYNTAX       Gauge32
    MAX-ACCESS   read-only
    STATUS       current
    DESCRIPTION
        "Cisco Firepower adaptor:HostServiceEthIf:peerPortId
        managed object property"
    ::= { cfprAdaptorHostServiceEthIfEntry 30 }

cfprAdaptorHostServiceEthIfPeerSlotId OBJECT-TYPE
    SYNTAX       Gauge32
    MAX-ACCESS   read-only
    STATUS       current
    DESCRIPTION
        "Cisco Firepower adaptor:HostServiceEthIf:peerSlotId
        managed object property"
    ::= { cfprAdaptorHostServiceEthIfEntry 31 }

cfprAdaptorHostServiceEthIfPerf OBJECT-TYPE
    SYNTAX       CfprEquipmentSensorThresholdStatus
    MAX-ACCESS   read-only
    STATUS       current
    DESCRIPTION
        "Cisco Firepower adaptor:HostServiceEthIf:perf
        managed object property"
    ::= { cfprAdaptorHostServiceEthIfEntry 32 }

cfprAdaptorHostServiceEthIfPortId OBJECT-TYPE
    SYNTAX       Gauge32
    MAX-ACCESS   read-only
    STATUS       current
    DESCRIPTION
        "Cisco Firepower adaptor:HostServiceEthIf:portId
        managed object property"
    ::= { cfprAdaptorHostServiceEthIfEntry 33 }

cfprAdaptorHostServiceEthIfPower OBJECT-TYPE
    SYNTAX       CfprEquipmentPowerState
    MAX-ACCESS   read-only
    STATUS       current
    DESCRIPTION
        "Cisco Firepower adaptor:HostServiceEthIf:power
        managed object property"
    ::= { cfprAdaptorHostServiceEthIfEntry 34 }

cfprAdaptorHostServiceEthIfPresence OBJECT-TYPE
    SYNTAX       CfprEquipmentPresence
    MAX-ACCESS   read-only
    STATUS       current
    DESCRIPTION
        "Cisco Firepower adaptor:HostServiceEthIf:presence
        managed object property"
    ::= { cfprAdaptorHostServiceEthIfEntry 35 }

cfprAdaptorHostServiceEthIfPurpose OBJECT-TYPE
    SYNTAX       CfprAdaptorPurpose
    MAX-ACCESS   read-only
    STATUS       current
    DESCRIPTION
        "Cisco Firepower adaptor:HostServiceEthIf:purpose
        managed object property"
    ::= { cfprAdaptorHostServiceEthIfEntry 36 }

cfprAdaptorHostServiceEthIfRevision OBJECT-TYPE
    SYNTAX       SnmpAdminString
    MAX-ACCESS   read-only
    STATUS       current
    DESCRIPTION
        "Cisco Firepower adaptor:HostServiceEthIf:revision
        managed object property"
    ::= { cfprAdaptorHostServiceEthIfEntry 37 }

cfprAdaptorHostServiceEthIfSerial OBJECT-TYPE
    SYNTAX       SnmpAdminString
    MAX-ACCESS   read-only
    STATUS       current
    DESCRIPTION
        "Cisco Firepower adaptor:HostServiceEthIf:serial
        managed object property"
    ::= { cfprAdaptorHostServiceEthIfEntry 38 }

cfprAdaptorHostServiceEthIfSide OBJECT-TYPE
    SYNTAX       CfprNetworkSide
    MAX-ACCESS   read-only
    STATUS       current
    DESCRIPTION
        "Cisco Firepower adaptor:HostServiceEthIf:side
        managed object property"
    ::= { cfprAdaptorHostServiceEthIfEntry 39 }

cfprAdaptorHostServiceEthIfSlotId OBJECT-TYPE
    SYNTAX       Gauge32
    MAX-ACCESS   read-only
    STATUS       current
    DESCRIPTION
        "Cisco Firepower adaptor:HostServiceEthIf:slotId
        managed object property"
    ::= { cfprAdaptorHostServiceEthIfEntry 40 }

cfprAdaptorHostServiceEthIfSwitchId OBJECT-TYPE
    SYNTAX       CfprNetworkSwitchId
    MAX-ACCESS   read-only
    STATUS       current
    DESCRIPTION
        "Cisco Firepower adaptor:HostServiceEthIf:switchId
        managed object property"
    ::= { cfprAdaptorHostServiceEthIfEntry 41 }

cfprAdaptorHostServiceEthIfThermal OBJECT-TYPE
    SYNTAX       CfprEquipmentSensorThresholdStatus
    MAX-ACCESS   read-only
    STATUS       current
    DESCRIPTION
        "Cisco Firepower adaptor:HostServiceEthIf:thermal
        managed object property"
    ::= { cfprAdaptorHostServiceEthIfEntry 42 }

cfprAdaptorHostServiceEthIfTransport OBJECT-TYPE
    SYNTAX       CfprNetworkTransport
    MAX-ACCESS   read-only
    STATUS       current
    DESCRIPTION
        "Cisco Firepower adaptor:HostServiceEthIf:transport
        managed object property"
    ::= { cfprAdaptorHostServiceEthIfEntry 43 }

cfprAdaptorHostServiceEthIfType OBJECT-TYPE
    SYNTAX       CfprNetworkConnectionType
    MAX-ACCESS   read-only
    STATUS       current
    DESCRIPTION
        "Cisco Firepower adaptor:HostServiceEthIf:type
        managed object property"
    ::= { cfprAdaptorHostServiceEthIfEntry 44 }

cfprAdaptorHostServiceEthIfVendor OBJECT-TYPE
    SYNTAX       SnmpAdminString
    MAX-ACCESS   read-only
    STATUS       current
    DESCRIPTION
        "Cisco Firepower adaptor:HostServiceEthIf:vendor
        managed object property"
    ::= { cfprAdaptorHostServiceEthIfEntry 45 }

cfprAdaptorHostServiceEthIfVnicDn OBJECT-TYPE
    SYNTAX       SnmpAdminString
    MAX-ACCESS   read-only
    STATUS       current
    DESCRIPTION
        "Cisco Firepower adaptor:HostServiceEthIf:vnicDn
        managed object property"
    ::= { cfprAdaptorHostServiceEthIfEntry 46 }

cfprAdaptorHostServiceEthIfVoltage OBJECT-TYPE
    SYNTAX       CfprEquipmentSensorThresholdStatus
    MAX-ACCESS   read-only
    STATUS       current
    DESCRIPTION
        "Cisco Firepower adaptor:HostServiceEthIf:voltage
        managed object property"
    ::= { cfprAdaptorHostServiceEthIfEntry 47 }

cfprAdaptorHostServiceEthIfServiceState OBJECT-TYPE
    SYNTAX       CfprAdaptorServiceState
    MAX-ACCESS   read-only
    STATUS       current
    DESCRIPTION
        "Cisco Firepower adaptor:HostServiceEthIf:serviceState
        managed object property"
    ::= { cfprAdaptorHostServiceEthIfEntry 48 }

cfprAdaptorHostServiceEthIfVcAdminState OBJECT-TYPE
    SYNTAX       CfprDcxAdminState
    MAX-ACCESS   read-only
    STATUS       current
    DESCRIPTION
        "Cisco Firepower adaptor:HostServiceEthIf:vcAdminState
        managed object property"
    ::= { cfprAdaptorHostServiceEthIfEntry 49 }

cfprAdaptorHostethHwAddrCapTable OBJECT-TYPE
    SYNTAX           SEQUENCE OF CfprAdaptorHostethHwAddrCapEntry
    MAX-ACCESS       not-accessible
    STATUS           current
    DESCRIPTION
        "Cisco Firepower adaptor:HostethHwAddrCap managed object table"
    ::= { cfprAdaptorObjects 72 }

cfprAdaptorHostethHwAddrCapEntry OBJECT-TYPE
    SYNTAX           CfprAdaptorHostethHwAddrCapEntry
    MAX-ACCESS       not-accessible
    STATUS           current
    DESCRIPTION
        "Entry for the cfprAdaptorHostethHwAddrCapTable table."
    INDEX { cfprAdaptorHostethHwAddrCapInstanceId }
    ::= { cfprAdaptorHostethHwAddrCapTable 1 }

CfprAdaptorHostethHwAddrCapEntry ::= SEQUENCE {
    cfprAdaptorHostethHwAddrCapInstanceId                            CfprManagedObjectId,
    cfprAdaptorHostethHwAddrCapDn                                    CfprManagedObjectDn,
    cfprAdaptorHostethHwAddrCapRn                                    SnmpAdminString,
    cfprAdaptorHostethHwAddrCapMacOffset1                            Gauge32,
    cfprAdaptorHostethHwAddrCapMacOffset2                            Gauge32
}

cfprAdaptorHostethHwAddrCapInstanceId OBJECT-TYPE
    SYNTAX       CfprManagedObjectId
    MAX-ACCESS   not-accessible
    STATUS       current
    DESCRIPTION
        "Instance identifier of the managed object."
    ::= { cfprAdaptorHostethHwAddrCapEntry 1 }

cfprAdaptorHostethHwAddrCapDn OBJECT-TYPE
    SYNTAX       CfprManagedObjectDn
    MAX-ACCESS   read-only
    STATUS       current
    DESCRIPTION
        "Cisco Firepower adaptor:HostethHwAddrCap:dn managed
        object property"
    ::= { cfprAdaptorHostethHwAddrCapEntry 2 }

cfprAdaptorHostethHwAddrCapRn OBJECT-TYPE
    SYNTAX       SnmpAdminString
    MAX-ACCESS   read-only
    STATUS       current
    DESCRIPTION
        "Cisco Firepower adaptor:HostethHwAddrCap:rn managed
        object property"
    ::= { cfprAdaptorHostethHwAddrCapEntry 3 }

cfprAdaptorHostethHwAddrCapMacOffset1 OBJECT-TYPE
    SYNTAX       Gauge32
    MAX-ACCESS   read-only
    STATUS       current
    DESCRIPTION
        "Cisco Firepower adaptor:HostethHwAddrCap:macOffset1
        managed object property"
    ::= { cfprAdaptorHostethHwAddrCapEntry 4 }

cfprAdaptorHostethHwAddrCapMacOffset2 OBJECT-TYPE
    SYNTAX       Gauge32
    MAX-ACCESS   read-only
    STATUS       current
    DESCRIPTION
        "Cisco Firepower adaptor:HostethHwAddrCap:macOffset2
        managed object property"
    ::= { cfprAdaptorHostethHwAddrCapEntry 5 }

cfprAdaptorHostfcHwAddrCapTable OBJECT-TYPE
    SYNTAX           SEQUENCE OF CfprAdaptorHostfcHwAddrCapEntry
    MAX-ACCESS       not-accessible
    STATUS           current
    DESCRIPTION
        "Cisco Firepower adaptor:HostfcHwAddrCap managed object table"
    ::= { cfprAdaptorObjects 73 }

cfprAdaptorHostfcHwAddrCapEntry OBJECT-TYPE
    SYNTAX           CfprAdaptorHostfcHwAddrCapEntry
    MAX-ACCESS       not-accessible
    STATUS           current
    DESCRIPTION
        "Entry for the cfprAdaptorHostfcHwAddrCapTable table."
    INDEX { cfprAdaptorHostfcHwAddrCapInstanceId }
    ::= { cfprAdaptorHostfcHwAddrCapTable 1 }

CfprAdaptorHostfcHwAddrCapEntry ::= SEQUENCE {
    cfprAdaptorHostfcHwAddrCapInstanceId                             CfprManagedObjectId,
    cfprAdaptorHostfcHwAddrCapDn                                     CfprManagedObjectDn,
    cfprAdaptorHostfcHwAddrCapRn                                     SnmpAdminString,
    cfprAdaptorHostfcHwAddrCapMacOffset1                             Gauge32,
    cfprAdaptorHostfcHwAddrCapMacOffset2                             Gauge32,
    cfprAdaptorHostfcHwAddrCapWwnReverseMaskA                        Unsigned64,
    cfprAdaptorHostfcHwAddrCapWwnReverseMaskB                        Unsigned64,
    cfprAdaptorHostfcHwAddrCapWwnnReverseMaskA                       Unsigned64,
    cfprAdaptorHostfcHwAddrCapWwnnReverseMaskB                       Unsigned64
}

cfprAdaptorHostfcHwAddrCapInstanceId OBJECT-TYPE
    SYNTAX       CfprManagedObjectId
    MAX-ACCESS   not-accessible
    STATUS       current
    DESCRIPTION
        "Instance identifier of the managed object."
    ::= { cfprAdaptorHostfcHwAddrCapEntry 1 }

cfprAdaptorHostfcHwAddrCapDn OBJECT-TYPE
    SYNTAX       CfprManagedObjectDn
    MAX-ACCESS   read-only
    STATUS       current
    DESCRIPTION
        "Cisco Firepower adaptor:HostfcHwAddrCap:dn managed
        object property"
    ::= { cfprAdaptorHostfcHwAddrCapEntry 2 }

cfprAdaptorHostfcHwAddrCapRn OBJECT-TYPE
    SYNTAX       SnmpAdminString
    MAX-ACCESS   read-only
    STATUS       current
    DESCRIPTION
        "Cisco Firepower adaptor:HostfcHwAddrCap:rn managed
        object property"
    ::= { cfprAdaptorHostfcHwAddrCapEntry 3 }

cfprAdaptorHostfcHwAddrCapMacOffset1 OBJECT-TYPE
    SYNTAX       Gauge32
    MAX-ACCESS   read-only
    STATUS       current
    DESCRIPTION
        "Cisco Firepower adaptor:HostfcHwAddrCap:macOffset1
        managed object property"
    ::= { cfprAdaptorHostfcHwAddrCapEntry 4 }

cfprAdaptorHostfcHwAddrCapMacOffset2 OBJECT-TYPE
    SYNTAX       Gauge32
    MAX-ACCESS   read-only
    STATUS       current
    DESCRIPTION
        "Cisco Firepower adaptor:HostfcHwAddrCap:macOffset2
        managed object property"
    ::= { cfprAdaptorHostfcHwAddrCapEntry 5 }

cfprAdaptorHostfcHwAddrCapWwnReverseMaskA OBJECT-TYPE
    SYNTAX       Unsigned64
    MAX-ACCESS   read-only
    STATUS       current
    DESCRIPTION
        "Cisco Firepower adaptor:HostfcHwAddrCap:wwnReverseMaskA
        managed object property"
    ::= { cfprAdaptorHostfcHwAddrCapEntry 6 }

cfprAdaptorHostfcHwAddrCapWwnReverseMaskB OBJECT-TYPE
    SYNTAX       Unsigned64
    MAX-ACCESS   read-only
    STATUS       current
    DESCRIPTION
        "Cisco Firepower adaptor:HostfcHwAddrCap:wwnReverseMaskB
        managed object property"
    ::= { cfprAdaptorHostfcHwAddrCapEntry 7 }

cfprAdaptorHostfcHwAddrCapWwnnReverseMaskA OBJECT-TYPE
    SYNTAX       Unsigned64
    MAX-ACCESS   read-only
    STATUS       current
    DESCRIPTION
        "Cisco Firepower adaptor:HostfcHwAddrCap:wwnnReverseMaskA
        managed object property"
    ::= { cfprAdaptorHostfcHwAddrCapEntry 8 }

cfprAdaptorHostfcHwAddrCapWwnnReverseMaskB OBJECT-TYPE
    SYNTAX       Unsigned64
    MAX-ACCESS   read-only
    STATUS       current
    DESCRIPTION
        "Cisco Firepower adaptor:HostfcHwAddrCap:wwnnReverseMaskB
        managed object property"
    ::= { cfprAdaptorHostfcHwAddrCapEntry 9 }

cfprAdaptorIScsiCapTable OBJECT-TYPE
    SYNTAX           SEQUENCE OF CfprAdaptorIScsiCapEntry
    MAX-ACCESS       not-accessible
    STATUS           current
    DESCRIPTION
        "Cisco Firepower adaptor:IScsiCap managed object table"
    ::= { cfprAdaptorObjects 74 }

cfprAdaptorIScsiCapEntry OBJECT-TYPE
    SYNTAX           CfprAdaptorIScsiCapEntry
    MAX-ACCESS       not-accessible
    STATUS           current
    DESCRIPTION
        "Entry for the cfprAdaptorIScsiCapTable table."
    INDEX { cfprAdaptorIScsiCapInstanceId }
    ::= { cfprAdaptorIScsiCapTable 1 }

CfprAdaptorIScsiCapEntry ::= SEQUENCE {
    cfprAdaptorIScsiCapInstanceId                                    CfprManagedObjectId,
    cfprAdaptorIScsiCapDn                                            CfprManagedObjectDn,
    cfprAdaptorIScsiCapRn                                            SnmpAdminString,
    cfprAdaptorIScsiCapBootOrderType                                 CfprAdaptorIScsiCapBootOrderType,
    cfprAdaptorIScsiCapMacOffset1                                    Gauge32,
    cfprAdaptorIScsiCapMacOffset2                                    Gauge32,
    cfprAdaptorIScsiCapOffloadSupport                                TruthValue,
    cfprAdaptorIScsiCapOffloadType                                   CfprAdaptorOffloadMethod,
    cfprAdaptorIScsiCapVlanForBoot                                   TruthValue
}

cfprAdaptorIScsiCapInstanceId OBJECT-TYPE
    SYNTAX       CfprManagedObjectId
    MAX-ACCESS   not-accessible
    STATUS       current
    DESCRIPTION
        "Instance identifier of the managed object."
    ::= { cfprAdaptorIScsiCapEntry 1 }

cfprAdaptorIScsiCapDn OBJECT-TYPE
    SYNTAX       CfprManagedObjectDn
    MAX-ACCESS   read-only
    STATUS       current
    DESCRIPTION
        "Cisco Firepower adaptor:IScsiCap:dn managed object property"
    ::= { cfprAdaptorIScsiCapEntry 2 }

cfprAdaptorIScsiCapRn OBJECT-TYPE
    SYNTAX       SnmpAdminString
    MAX-ACCESS   read-only
    STATUS       current
    DESCRIPTION
        "Cisco Firepower adaptor:IScsiCap:rn managed object property"
    ::= { cfprAdaptorIScsiCapEntry 3 }

cfprAdaptorIScsiCapBootOrderType OBJECT-TYPE
    SYNTAX       CfprAdaptorIScsiCapBootOrderType
    MAX-ACCESS   read-only
    STATUS       current
    DESCRIPTION
        "Cisco Firepower adaptor:IScsiCap:bootOrderType
        managed object property"
    ::= { cfprAdaptorIScsiCapEntry 4 }

cfprAdaptorIScsiCapMacOffset1 OBJECT-TYPE
    SYNTAX       Gauge32
    MAX-ACCESS   read-only
    STATUS       current
    DESCRIPTION
        "Cisco Firepower adaptor:IScsiCap:macOffset1 managed
        object property"
    ::= { cfprAdaptorIScsiCapEntry 5 }

cfprAdaptorIScsiCapMacOffset2 OBJECT-TYPE
    SYNTAX       Gauge32
    MAX-ACCESS   read-only
    STATUS       current
    DESCRIPTION
        "Cisco Firepower adaptor:IScsiCap:macOffset2 managed
        object property"
    ::= { cfprAdaptorIScsiCapEntry 6 }

cfprAdaptorIScsiCapOffloadSupport OBJECT-TYPE
    SYNTAX       TruthValue
    MAX-ACCESS   read-only
    STATUS       current
    DESCRIPTION
        "Cisco Firepower adaptor:IScsiCap:offloadSupport
        managed object property"
    ::= { cfprAdaptorIScsiCapEntry 7 }

cfprAdaptorIScsiCapOffloadType OBJECT-TYPE
    SYNTAX       CfprAdaptorOffloadMethod
    MAX-ACCESS   read-only
    STATUS       current
    DESCRIPTION
        "Cisco Firepower adaptor:IScsiCap:offloadType managed
        object property"
    ::= { cfprAdaptorIScsiCapEntry 8 }

cfprAdaptorIScsiCapVlanForBoot OBJECT-TYPE
    SYNTAX       TruthValue
    MAX-ACCESS   read-only
    STATUS       current
    DESCRIPTION
        "Cisco Firepower adaptor:IScsiCap:vlanForBoot managed
        object property"
    ::= { cfprAdaptorIScsiCapEntry 9 }

cfprAdaptorIpV4RssHashProfileTable OBJECT-TYPE
    SYNTAX           SEQUENCE OF CfprAdaptorIpV4RssHashProfileEntry
    MAX-ACCESS       not-accessible
    STATUS           current
    DESCRIPTION
        "Cisco Firepower adaptor:IpV4RssHashProfile managed object table"
    ::= { cfprAdaptorObjects 75 }

cfprAdaptorIpV4RssHashProfileEntry OBJECT-TYPE
    SYNTAX           CfprAdaptorIpV4RssHashProfileEntry
    MAX-ACCESS       not-accessible
    STATUS           current
    DESCRIPTION
        "Entry for the cfprAdaptorIpV4RssHashProfileTable table."
    INDEX { cfprAdaptorIpV4RssHashProfileInstanceId }
    ::= { cfprAdaptorIpV4RssHashProfileTable 1 }

CfprAdaptorIpV4RssHashProfileEntry ::= SEQUENCE {
    cfprAdaptorIpV4RssHashProfileInstanceId                          CfprManagedObjectId,
    cfprAdaptorIpV4RssHashProfileDn                                  CfprManagedObjectDn,
    cfprAdaptorIpV4RssHashProfileRn                                  SnmpAdminString,
    cfprAdaptorIpV4RssHashProfileIpHash                              CfprAdaptorIpV4RssHashProfileIpHash,
    cfprAdaptorIpV4RssHashProfileTcpHash                             CfprAdaptorIpV4RssHashProfileTcpHash
}

cfprAdaptorIpV4RssHashProfileInstanceId OBJECT-TYPE
    SYNTAX       CfprManagedObjectId
    MAX-ACCESS   not-accessible
    STATUS       current
    DESCRIPTION
        "Instance identifier of the managed object."
    ::= { cfprAdaptorIpV4RssHashProfileEntry 1 }

cfprAdaptorIpV4RssHashProfileDn OBJECT-TYPE
    SYNTAX       CfprManagedObjectDn
    MAX-ACCESS   read-only
    STATUS       current
    DESCRIPTION
        "Cisco Firepower adaptor:IpV4RssHashProfile:dn
        managed object property"
    ::= { cfprAdaptorIpV4RssHashProfileEntry 2 }

cfprAdaptorIpV4RssHashProfileRn OBJECT-TYPE
    SYNTAX       SnmpAdminString
    MAX-ACCESS   read-only
    STATUS       current
    DESCRIPTION
        "Cisco Firepower adaptor:IpV4RssHashProfile:rn
        managed object property"
    ::= { cfprAdaptorIpV4RssHashProfileEntry 3 }

cfprAdaptorIpV4RssHashProfileIpHash OBJECT-TYPE
    SYNTAX       CfprAdaptorIpV4RssHashProfileIpHash
    MAX-ACCESS   read-only
    STATUS       current
    DESCRIPTION
        "Cisco Firepower adaptor:IpV4RssHashProfile:ipHash
        managed object property"
    ::= { cfprAdaptorIpV4RssHashProfileEntry 4 }

cfprAdaptorIpV4RssHashProfileTcpHash OBJECT-TYPE
    SYNTAX       CfprAdaptorIpV4RssHashProfileTcpHash
    MAX-ACCESS   read-only
    STATUS       current
    DESCRIPTION
        "Cisco Firepower adaptor:IpV4RssHashProfile:tcpHash
        managed object property"
    ::= { cfprAdaptorIpV4RssHashProfileEntry 5 }

cfprAdaptorIpV6RssHashProfileTable OBJECT-TYPE
    SYNTAX           SEQUENCE OF CfprAdaptorIpV6RssHashProfileEntry
    MAX-ACCESS       not-accessible
    STATUS           current
    DESCRIPTION
        "Cisco Firepower adaptor:IpV6RssHashProfile managed object table"
    ::= { cfprAdaptorObjects 76 }

cfprAdaptorIpV6RssHashProfileEntry OBJECT-TYPE
    SYNTAX           CfprAdaptorIpV6RssHashProfileEntry
    MAX-ACCESS       not-accessible
    STATUS           current
    DESCRIPTION
        "Entry for the cfprAdaptorIpV6RssHashProfileTable table."
    INDEX { cfprAdaptorIpV6RssHashProfileInstanceId }
    ::= { cfprAdaptorIpV6RssHashProfileTable 1 }

CfprAdaptorIpV6RssHashProfileEntry ::= SEQUENCE {
    cfprAdaptorIpV6RssHashProfileInstanceId                          CfprManagedObjectId,
    cfprAdaptorIpV6RssHashProfileDn                                  CfprManagedObjectDn,
    cfprAdaptorIpV6RssHashProfileRn                                  SnmpAdminString,
    cfprAdaptorIpV6RssHashProfileIpHash                              CfprAdaptorIpV6RssHashProfileIpHash,
    cfprAdaptorIpV6RssHashProfileTcpHash                             CfprAdaptorIpV6RssHashProfileTcpHash
}

cfprAdaptorIpV6RssHashProfileInstanceId OBJECT-TYPE
    SYNTAX       CfprManagedObjectId
    MAX-ACCESS   not-accessible
    STATUS       current
    DESCRIPTION
        "Instance identifier of the managed object."
    ::= { cfprAdaptorIpV6RssHashProfileEntry 1 }

cfprAdaptorIpV6RssHashProfileDn OBJECT-TYPE
    SYNTAX       CfprManagedObjectDn
    MAX-ACCESS   read-only
    STATUS       current
    DESCRIPTION
        "Cisco Firepower adaptor:IpV6RssHashProfile:dn
        managed object property"
    ::= { cfprAdaptorIpV6RssHashProfileEntry 2 }

cfprAdaptorIpV6RssHashProfileRn OBJECT-TYPE
    SYNTAX       SnmpAdminString
    MAX-ACCESS   read-only
    STATUS       current
    DESCRIPTION
        "Cisco Firepower adaptor:IpV6RssHashProfile:rn
        managed object property"
    ::= { cfprAdaptorIpV6RssHashProfileEntry 3 }

cfprAdaptorIpV6RssHashProfileIpHash OBJECT-TYPE
    SYNTAX       CfprAdaptorIpV6RssHashProfileIpHash
    MAX-ACCESS   read-only
    STATUS       current
    DESCRIPTION
        "Cisco Firepower adaptor:IpV6RssHashProfile:ipHash
        managed object property"
    ::= { cfprAdaptorIpV6RssHashProfileEntry 4 }

cfprAdaptorIpV6RssHashProfileTcpHash OBJECT-TYPE
    SYNTAX       CfprAdaptorIpV6RssHashProfileTcpHash
    MAX-ACCESS   read-only
    STATUS       current
    DESCRIPTION
        "Cisco Firepower adaptor:IpV6RssHashProfile:tcpHash
        managed object property"
    ::= { cfprAdaptorIpV6RssHashProfileEntry 5 }

cfprAdaptorIscsiAuthTable OBJECT-TYPE
    SYNTAX           SEQUENCE OF CfprAdaptorIscsiAuthEntry
    MAX-ACCESS       not-accessible
    STATUS           current
    DESCRIPTION
        "Cisco Firepower adaptor:IscsiAuth managed object table"
    ::= { cfprAdaptorObjects 77 }

cfprAdaptorIscsiAuthEntry OBJECT-TYPE
    SYNTAX           CfprAdaptorIscsiAuthEntry
    MAX-ACCESS       not-accessible
    STATUS           current
    DESCRIPTION
        "Entry for the cfprAdaptorIscsiAuthTable table."
    INDEX { cfprAdaptorIscsiAuthInstanceId }
    ::= { cfprAdaptorIscsiAuthTable 1 }

CfprAdaptorIscsiAuthEntry ::= SEQUENCE {
    cfprAdaptorIscsiAuthInstanceId                                   CfprManagedObjectId,
    cfprAdaptorIscsiAuthDn                                           CfprManagedObjectDn,
    cfprAdaptorIscsiAuthRn                                           SnmpAdminString,
    cfprAdaptorIscsiAuthPassword                                     SnmpAdminString,
    cfprAdaptorIscsiAuthUserId                                       SnmpAdminString
}

cfprAdaptorIscsiAuthInstanceId OBJECT-TYPE
    SYNTAX       CfprManagedObjectId
    MAX-ACCESS   not-accessible
    STATUS       current
    DESCRIPTION
        "Instance identifier of the managed object."
    ::= { cfprAdaptorIscsiAuthEntry 1 }

cfprAdaptorIscsiAuthDn OBJECT-TYPE
    SYNTAX       CfprManagedObjectDn
    MAX-ACCESS   read-only
    STATUS       current
    DESCRIPTION
        "Cisco Firepower adaptor:IscsiAuth:dn managed object property"
    ::= { cfprAdaptorIscsiAuthEntry 2 }

cfprAdaptorIscsiAuthRn OBJECT-TYPE
    SYNTAX       SnmpAdminString
    MAX-ACCESS   read-only
    STATUS       current
    DESCRIPTION
        "Cisco Firepower adaptor:IscsiAuth:rn managed object property"
    ::= { cfprAdaptorIscsiAuthEntry 3 }

cfprAdaptorIscsiAuthPassword OBJECT-TYPE
    SYNTAX       SnmpAdminString
    MAX-ACCESS   read-only
    STATUS       current
    DESCRIPTION
        "Cisco Firepower adaptor:IscsiAuth:password managed
        object property"
    ::= { cfprAdaptorIscsiAuthEntry 4 }

cfprAdaptorIscsiAuthUserId OBJECT-TYPE
    SYNTAX       SnmpAdminString
    MAX-ACCESS   read-only
    STATUS       current
    DESCRIPTION
        "Cisco Firepower adaptor:IscsiAuth:userId managed object property"
    ::= { cfprAdaptorIscsiAuthEntry 5 }

cfprAdaptorIscsiProtTable OBJECT-TYPE
    SYNTAX           SEQUENCE OF CfprAdaptorIscsiProtEntry
    MAX-ACCESS       not-accessible
    STATUS           current
    DESCRIPTION
        "Cisco Firepower adaptor:IscsiProt managed object table"
    ::= { cfprAdaptorObjects 78 }

cfprAdaptorIscsiProtEntry OBJECT-TYPE
    SYNTAX           CfprAdaptorIscsiProtEntry
    MAX-ACCESS       not-accessible
    STATUS           current
    DESCRIPTION
        "Entry for the cfprAdaptorIscsiProtTable table."
    INDEX { cfprAdaptorIscsiProtInstanceId }
    ::= { cfprAdaptorIscsiProtTable 1 }

CfprAdaptorIscsiProtEntry ::= SEQUENCE {
    cfprAdaptorIscsiProtInstanceId                                   CfprManagedObjectId,
    cfprAdaptorIscsiProtDn                                           CfprManagedObjectDn,
    cfprAdaptorIscsiProtRn                                           SnmpAdminString,
    cfprAdaptorIscsiProtConnectionTimeOut                            CfprAdaptorIscsiProtConnectionTimeOut,
    cfprAdaptorIscsiProtDhcpTimeOut                                  CfprAdaptorIscsiProtDhcpTimeOut,
    cfprAdaptorIscsiProtFltAggr                                      Unsigned64,
    cfprAdaptorIscsiProtInitiatorName                                SnmpAdminString,
    cfprAdaptorIscsiProtLunBusyRetryCount                            CfprAdaptorIscsiProtLunBusyRetryCount,
    cfprAdaptorIscsiProtTcpTimeStamp                                 TruthValue
}

cfprAdaptorIscsiProtInstanceId OBJECT-TYPE
    SYNTAX       CfprManagedObjectId
    MAX-ACCESS   not-accessible
    STATUS       current
    DESCRIPTION
        "Instance identifier of the managed object."
    ::= { cfprAdaptorIscsiProtEntry 1 }

cfprAdaptorIscsiProtDn OBJECT-TYPE
    SYNTAX       CfprManagedObjectDn
    MAX-ACCESS   read-only
    STATUS       current
    DESCRIPTION
        "Cisco Firepower adaptor:IscsiProt:dn managed object property"
    ::= { cfprAdaptorIscsiProtEntry 2 }

cfprAdaptorIscsiProtRn OBJECT-TYPE
    SYNTAX       SnmpAdminString
    MAX-ACCESS   read-only
    STATUS       current
    DESCRIPTION
        "Cisco Firepower adaptor:IscsiProt:rn managed object property"
    ::= { cfprAdaptorIscsiProtEntry 3 }

cfprAdaptorIscsiProtConnectionTimeOut OBJECT-TYPE
    SYNTAX       CfprAdaptorIscsiProtConnectionTimeOut
    MAX-ACCESS   read-only
    STATUS       current
    DESCRIPTION
        "Cisco Firepower adaptor:IscsiProt:connectionTimeOut
        managed object property"
    ::= { cfprAdaptorIscsiProtEntry 4 }

cfprAdaptorIscsiProtDhcpTimeOut OBJECT-TYPE
    SYNTAX       CfprAdaptorIscsiProtDhcpTimeOut
    MAX-ACCESS   read-only
    STATUS       current
    DESCRIPTION
        "Cisco Firepower adaptor:IscsiProt:dhcpTimeOut
        managed object property"
    ::= { cfprAdaptorIscsiProtEntry 5 }

cfprAdaptorIscsiProtFltAggr OBJECT-TYPE
    SYNTAX       Unsigned64
    MAX-ACCESS   read-only
    STATUS       current
    DESCRIPTION
        "Cisco Firepower adaptor:IscsiProt:fltAggr managed
        object property"
    ::= { cfprAdaptorIscsiProtEntry 6 }

cfprAdaptorIscsiProtInitiatorName OBJECT-TYPE
    SYNTAX       SnmpAdminString
    MAX-ACCESS   read-only
    STATUS       current
    DESCRIPTION
        "Cisco Firepower adaptor:IscsiProt:initiatorName
        managed object property"
    ::= { cfprAdaptorIscsiProtEntry 7 }

cfprAdaptorIscsiProtLunBusyRetryCount OBJECT-TYPE
    SYNTAX       CfprAdaptorIscsiProtLunBusyRetryCount
    MAX-ACCESS   read-only
    STATUS       current
    DESCRIPTION
        "Cisco Firepower adaptor:IscsiProt:lunBusyRetryCount
        managed object property"
    ::= { cfprAdaptorIscsiProtEntry 8 }

cfprAdaptorIscsiProtTcpTimeStamp OBJECT-TYPE
    SYNTAX       TruthValue
    MAX-ACCESS   read-only
    STATUS       current
    DESCRIPTION
        "Cisco Firepower adaptor:IscsiProt:tcpTimeStamp
        managed object property"
    ::= { cfprAdaptorIscsiProtEntry 9 }

cfprAdaptorIscsiTargetIfTable OBJECT-TYPE
    SYNTAX           SEQUENCE OF CfprAdaptorIscsiTargetIfEntry
    MAX-ACCESS       not-accessible
    STATUS           current
    DESCRIPTION
        "Cisco Firepower adaptor:IscsiTargetIf managed object table"
    ::= { cfprAdaptorObjects 79 }

cfprAdaptorIscsiTargetIfEntry OBJECT-TYPE
    SYNTAX           CfprAdaptorIscsiTargetIfEntry
    MAX-ACCESS       not-accessible
    STATUS           current
    DESCRIPTION
        "Entry for the cfprAdaptorIscsiTargetIfTable table."
    INDEX { cfprAdaptorIscsiTargetIfInstanceId }
    ::= { cfprAdaptorIscsiTargetIfTable 1 }

CfprAdaptorIscsiTargetIfEntry ::= SEQUENCE {
    cfprAdaptorIscsiTargetIfInstanceId                               CfprManagedObjectId,
    cfprAdaptorIscsiTargetIfDn                                       CfprManagedObjectDn,
    cfprAdaptorIscsiTargetIfRn                                       SnmpAdminString,
    cfprAdaptorIscsiTargetIfDhcpVendorId                             SnmpAdminString,
    cfprAdaptorIscsiTargetIfFltAggr                                  Unsigned64,
    cfprAdaptorIscsiTargetIfIpAddress                                InetAddressIPv4,
    cfprAdaptorIscsiTargetIfLun                                      Gauge32,
    cfprAdaptorIscsiTargetIfName                                     SnmpAdminString,
    cfprAdaptorIscsiTargetIfPortNumber                               Gauge32,
    cfprAdaptorIscsiTargetIfPriority                                 Gauge32
}

cfprAdaptorIscsiTargetIfInstanceId OBJECT-TYPE
    SYNTAX       CfprManagedObjectId
    MAX-ACCESS   not-accessible
    STATUS       current
    DESCRIPTION
        "Instance identifier of the managed object."
    ::= { cfprAdaptorIscsiTargetIfEntry 1 }

cfprAdaptorIscsiTargetIfDn OBJECT-TYPE
    SYNTAX       CfprManagedObjectDn
    MAX-ACCESS   read-only
    STATUS       current
    DESCRIPTION
        "Cisco Firepower adaptor:IscsiTargetIf:dn managed object property"
    ::= { cfprAdaptorIscsiTargetIfEntry 2 }

cfprAdaptorIscsiTargetIfRn OBJECT-TYPE
    SYNTAX       SnmpAdminString
    MAX-ACCESS   read-only
    STATUS       current
    DESCRIPTION
        "Cisco Firepower adaptor:IscsiTargetIf:rn managed object property"
    ::= { cfprAdaptorIscsiTargetIfEntry 3 }

cfprAdaptorIscsiTargetIfDhcpVendorId OBJECT-TYPE
    SYNTAX       SnmpAdminString
    MAX-ACCESS   read-only
    STATUS       current
    DESCRIPTION
        "Cisco Firepower adaptor:IscsiTargetIf:dhcpVendorId
        managed object property"
    ::= { cfprAdaptorIscsiTargetIfEntry 4 }

cfprAdaptorIscsiTargetIfFltAggr OBJECT-TYPE
    SYNTAX       Unsigned64
    MAX-ACCESS   read-only
    STATUS       current
    DESCRIPTION
        "Cisco Firepower adaptor:IscsiTargetIf:fltAggr
        managed object property"
    ::= { cfprAdaptorIscsiTargetIfEntry 5 }

cfprAdaptorIscsiTargetIfIpAddress OBJECT-TYPE
    SYNTAX       InetAddressIPv4
    MAX-ACCESS   read-only
    STATUS       current
    DESCRIPTION
        "Cisco Firepower adaptor:IscsiTargetIf:ipAddress
        managed object property"
    ::= { cfprAdaptorIscsiTargetIfEntry 6 }

cfprAdaptorIscsiTargetIfLun OBJECT-TYPE
    SYNTAX       Gauge32
    MAX-ACCESS   read-only
    STATUS       current
    DESCRIPTION
        "Cisco Firepower adaptor:IscsiTargetIf:lun managed
        object property"
    ::= { cfprAdaptorIscsiTargetIfEntry 7 }

cfprAdaptorIscsiTargetIfName OBJECT-TYPE
    SYNTAX       SnmpAdminString
    MAX-ACCESS   read-only
    STATUS       current
    DESCRIPTION
        "Cisco Firepower adaptor:IscsiTargetIf:name managed
        object property"
    ::= { cfprAdaptorIscsiTargetIfEntry 8 }

cfprAdaptorIscsiTargetIfPortNumber OBJECT-TYPE
    SYNTAX       Gauge32
    MAX-ACCESS   read-only
    STATUS       current
    DESCRIPTION
        "Cisco Firepower adaptor:IscsiTargetIf:portNumber
        managed object property"
    ::= { cfprAdaptorIscsiTargetIfEntry 9 }

cfprAdaptorIscsiTargetIfPriority OBJECT-TYPE
    SYNTAX       Gauge32
    MAX-ACCESS   read-only
    STATUS       current
    DESCRIPTION
        "Cisco Firepower adaptor:IscsiTargetIf:priority
        managed object property"
    ::= { cfprAdaptorIscsiTargetIfEntry 10 }

cfprAdaptorLanCapTable OBJECT-TYPE
    SYNTAX           SEQUENCE OF CfprAdaptorLanCapEntry
    MAX-ACCESS       not-accessible
    STATUS           current
    DESCRIPTION
        "Cisco Firepower adaptor:LanCap managed object table"
    ::= { cfprAdaptorObjects 80 }

cfprAdaptorLanCapEntry OBJECT-TYPE
    SYNTAX           CfprAdaptorLanCapEntry
    MAX-ACCESS       not-accessible
    STATUS           current
    DESCRIPTION
        "Entry for the cfprAdaptorLanCapTable table."
    INDEX { cfprAdaptorLanCapInstanceId }
    ::= { cfprAdaptorLanCapTable 1 }

CfprAdaptorLanCapEntry ::= SEQUENCE {
    cfprAdaptorLanCapInstanceId                                      CfprManagedObjectId,
    cfprAdaptorLanCapDn                                              CfprManagedObjectDn,
    cfprAdaptorLanCapRn                                              SnmpAdminString,
    cfprAdaptorLanCapDefaultVlan                                     CfprAdaptorLanCapDefaultVlan
}

cfprAdaptorLanCapInstanceId OBJECT-TYPE
    SYNTAX       CfprManagedObjectId
    MAX-ACCESS   not-accessible
    STATUS       current
    DESCRIPTION
        "Instance identifier of the managed object."
    ::= { cfprAdaptorLanCapEntry 1 }

cfprAdaptorLanCapDn OBJECT-TYPE
    SYNTAX       CfprManagedObjectDn
    MAX-ACCESS   read-only
    STATUS       current
    DESCRIPTION
        "Cisco Firepower adaptor:LanCap:dn managed object property"
    ::= { cfprAdaptorLanCapEntry 2 }

cfprAdaptorLanCapRn OBJECT-TYPE
    SYNTAX       SnmpAdminString
    MAX-ACCESS   read-only
    STATUS       current
    DESCRIPTION
        "Cisco Firepower adaptor:LanCap:rn managed object property"
    ::= { cfprAdaptorLanCapEntry 3 }

cfprAdaptorLanCapDefaultVlan OBJECT-TYPE
    SYNTAX       CfprAdaptorLanCapDefaultVlan
    MAX-ACCESS   read-only
    STATUS       current
    DESCRIPTION
        "Cisco Firepower adaptor:LanCap:defaultVlan managed
        object property"
    ::= { cfprAdaptorLanCapEntry 4 }

cfprAdaptorLldpCapTable OBJECT-TYPE
    SYNTAX           SEQUENCE OF CfprAdaptorLldpCapEntry
    MAX-ACCESS       not-accessible
    STATUS           current
    DESCRIPTION
        "Cisco Firepower adaptor:LldpCap managed object table"
    ::= { cfprAdaptorObjects 81 }

cfprAdaptorLldpCapEntry OBJECT-TYPE
    SYNTAX           CfprAdaptorLldpCapEntry
    MAX-ACCESS       not-accessible
    STATUS           current
    DESCRIPTION
        "Entry for the cfprAdaptorLldpCapTable table."
    INDEX { cfprAdaptorLldpCapInstanceId }
    ::= { cfprAdaptorLldpCapTable 1 }

CfprAdaptorLldpCapEntry ::= SEQUENCE {
    cfprAdaptorLldpCapInstanceId                                     CfprManagedObjectId,
    cfprAdaptorLldpCapDn                                             CfprManagedObjectDn,
    cfprAdaptorLldpCapRn                                             SnmpAdminString,
    cfprAdaptorLldpCapSupport                                        CfprAdaptorLldpCapSupport
}

cfprAdaptorLldpCapInstanceId OBJECT-TYPE
    SYNTAX       CfprManagedObjectId
    MAX-ACCESS   not-accessible
    STATUS       current
    DESCRIPTION
        "Instance identifier of the managed object."
    ::= { cfprAdaptorLldpCapEntry 1 }

cfprAdaptorLldpCapDn OBJECT-TYPE
    SYNTAX       CfprManagedObjectDn
    MAX-ACCESS   read-only
    STATUS       current
    DESCRIPTION
        "Cisco Firepower adaptor:LldpCap:dn managed object property"
    ::= { cfprAdaptorLldpCapEntry 2 }

cfprAdaptorLldpCapRn OBJECT-TYPE
    SYNTAX       SnmpAdminString
    MAX-ACCESS   read-only
    STATUS       current
    DESCRIPTION
        "Cisco Firepower adaptor:LldpCap:rn managed object property"
    ::= { cfprAdaptorLldpCapEntry 3 }

cfprAdaptorLldpCapSupport OBJECT-TYPE
    SYNTAX       CfprAdaptorLldpCapSupport
    MAX-ACCESS   read-only
    STATUS       current
    DESCRIPTION
        "Cisco Firepower adaptor:LldpCap:support managed object property"
    ::= { cfprAdaptorLldpCapEntry 4 }

cfprAdaptorMenloBaseErrorStatsTable OBJECT-TYPE
    SYNTAX           SEQUENCE OF CfprAdaptorMenloBaseErrorStatsEntry
    MAX-ACCESS       not-accessible
    STATUS           current
    DESCRIPTION
        "Cisco Firepower adaptor:MenloBaseErrorStats managed object table"
    ::= { cfprAdaptorObjects 82 }

cfprAdaptorMenloBaseErrorStatsEntry OBJECT-TYPE
    SYNTAX           CfprAdaptorMenloBaseErrorStatsEntry
    MAX-ACCESS       not-accessible
    STATUS           current
    DESCRIPTION
        "Entry for the cfprAdaptorMenloBaseErrorStatsTable table."
    INDEX { cfprAdaptorMenloBaseErrorStatsInstanceId }
    ::= { cfprAdaptorMenloBaseErrorStatsTable 1 }

CfprAdaptorMenloBaseErrorStatsEntry ::= SEQUENCE {
    cfprAdaptorMenloBaseErrorStatsInstanceId                         CfprManagedObjectId,
    cfprAdaptorMenloBaseErrorStatsDn                                 CfprManagedObjectDn,
    cfprAdaptorMenloBaseErrorStatsRn                                 SnmpAdminString,
    cfprAdaptorMenloBaseErrorStatsCorrectableErrors                  Unsigned64,
    cfprAdaptorMenloBaseErrorStatsCorrectableErrorsDelta             Counter64,
    cfprAdaptorMenloBaseErrorStatsCorrectableErrorsDeltaAvg          Unsigned64,
    cfprAdaptorMenloBaseErrorStatsCorrectableErrorsDeltaMax          Unsigned64,
    cfprAdaptorMenloBaseErrorStatsCorrectableErrorsDeltaMin          Unsigned64,
    cfprAdaptorMenloBaseErrorStatsIntervals                          Gauge32,
    cfprAdaptorMenloBaseErrorStatsSuspect                            TruthValue,
    cfprAdaptorMenloBaseErrorStatsThresholded                        CfprAdaptorMenloBaseErrorStatsThresholded,
    cfprAdaptorMenloBaseErrorStatsTimeCollected                      DateAndTime,
    cfprAdaptorMenloBaseErrorStatsUncorrectableErrors                Unsigned64,
    cfprAdaptorMenloBaseErrorStatsUncorrectableErrorsDelta           Counter64,
    cfprAdaptorMenloBaseErrorStatsUncorrectableErrorsDeltaAvg        Unsigned64,
    cfprAdaptorMenloBaseErrorStatsUncorrectableErrorsDeltaMax        Unsigned64,
    cfprAdaptorMenloBaseErrorStatsUncorrectableErrorsDeltaMin        Unsigned64,
    cfprAdaptorMenloBaseErrorStatsUpdate                             Gauge32
}

cfprAdaptorMenloBaseErrorStatsInstanceId OBJECT-TYPE
    SYNTAX       CfprManagedObjectId
    MAX-ACCESS   not-accessible
    STATUS       current
    DESCRIPTION
        "Instance identifier of the managed object."
    ::= { cfprAdaptorMenloBaseErrorStatsEntry 1 }

cfprAdaptorMenloBaseErrorStatsDn OBJECT-TYPE
    SYNTAX       CfprManagedObjectDn
    MAX-ACCESS   read-only
    STATUS       current
    DESCRIPTION
        "Cisco Firepower adaptor:MenloBaseErrorStats:dn
        managed object property"
    ::= { cfprAdaptorMenloBaseErrorStatsEntry 2 }

cfprAdaptorMenloBaseErrorStatsRn OBJECT-TYPE
    SYNTAX       SnmpAdminString
    MAX-ACCESS   read-only
    STATUS       current
    DESCRIPTION
        "Cisco Firepower adaptor:MenloBaseErrorStats:rn
        managed object property"
    ::= { cfprAdaptorMenloBaseErrorStatsEntry 3 }

cfprAdaptorMenloBaseErrorStatsCorrectableErrors OBJECT-TYPE
    SYNTAX       Unsigned64
    MAX-ACCESS   read-only
    STATUS       current
    DESCRIPTION
        "Cisco Firepower adaptor:MenloBaseErrorStats:correctableErrors
        managed object property"
    ::= { cfprAdaptorMenloBaseErrorStatsEntry 4 }

cfprAdaptorMenloBaseErrorStatsCorrectableErrorsDelta OBJECT-TYPE
    SYNTAX       Counter64
    MAX-ACCESS   read-only
    STATUS       current
    DESCRIPTION
        "Cisco Firepower adaptor:MenloBaseErrorStats:correctableErrorsDelt
        a managed object property"
    ::= { cfprAdaptorMenloBaseErrorStatsEntry 5 }

cfprAdaptorMenloBaseErrorStatsCorrectableErrorsDeltaAvg OBJECT-TYPE
    SYNTAX       Unsigned64
    MAX-ACCESS   read-only
    STATUS       current
    DESCRIPTION
        "Cisco Firepower adaptor:MenloBaseErrorStats:correctableErrorsDelt
        aAvg managed object property"
    ::= { cfprAdaptorMenloBaseErrorStatsEntry 6 }

cfprAdaptorMenloBaseErrorStatsCorrectableErrorsDeltaMax OBJECT-TYPE
    SYNTAX       Unsigned64
    MAX-ACCESS   read-only
    STATUS       current
    DESCRIPTION
        "Cisco Firepower adaptor:MenloBaseErrorStats:correctableErrorsDelt
        aMax managed object property"
    ::= { cfprAdaptorMenloBaseErrorStatsEntry 7 }

cfprAdaptorMenloBaseErrorStatsCorrectableErrorsDeltaMin OBJECT-TYPE
    SYNTAX       Unsigned64
    MAX-ACCESS   read-only
    STATUS       current
    DESCRIPTION
        "Cisco Firepower adaptor:MenloBaseErrorStats:correctableErrorsDelt
        aMin managed object property"
    ::= { cfprAdaptorMenloBaseErrorStatsEntry 8 }

cfprAdaptorMenloBaseErrorStatsIntervals OBJECT-TYPE
    SYNTAX       Gauge32
    MAX-ACCESS   read-only
    STATUS       current
    DESCRIPTION
        "Cisco Firepower adaptor:MenloBaseErrorStats:intervals
        managed object property"
    ::= { cfprAdaptorMenloBaseErrorStatsEntry 9 }

cfprAdaptorMenloBaseErrorStatsSuspect OBJECT-TYPE
    SYNTAX       TruthValue
    MAX-ACCESS   read-only
    STATUS       current
    DESCRIPTION
        "Cisco Firepower adaptor:MenloBaseErrorStats:suspect
        managed object property"
    ::= { cfprAdaptorMenloBaseErrorStatsEntry 10 }

cfprAdaptorMenloBaseErrorStatsThresholded OBJECT-TYPE
    SYNTAX       CfprAdaptorMenloBaseErrorStatsThresholded
    MAX-ACCESS   read-only
    STATUS       current
    DESCRIPTION
        "Cisco Firepower adaptor:MenloBaseErrorStats:thresholded
        managed object property"
    ::= { cfprAdaptorMenloBaseErrorStatsEntry 11 }

cfprAdaptorMenloBaseErrorStatsTimeCollected OBJECT-TYPE
    SYNTAX       DateAndTime
    MAX-ACCESS   read-only
    STATUS       current
    DESCRIPTION
        "Cisco Firepower adaptor:MenloBaseErrorStats:timeCollected
        managed object property"
    ::= { cfprAdaptorMenloBaseErrorStatsEntry 12 }

cfprAdaptorMenloBaseErrorStatsUncorrectableErrors OBJECT-TYPE
    SYNTAX       Unsigned64
    MAX-ACCESS   read-only
    STATUS       current
    DESCRIPTION
        "Cisco Firepower adaptor:MenloBaseErrorStats:uncorrectableErrors
        managed object property"
    ::= { cfprAdaptorMenloBaseErrorStatsEntry 13 }

cfprAdaptorMenloBaseErrorStatsUncorrectableErrorsDelta OBJECT-TYPE
    SYNTAX       Counter64
    MAX-ACCESS   read-only
    STATUS       current
    DESCRIPTION
        "Cisco Firepower adaptor:MenloBaseErrorStats:uncorrectableErrorsDe
        lta managed object property"
    ::= { cfprAdaptorMenloBaseErrorStatsEntry 14 }

cfprAdaptorMenloBaseErrorStatsUncorrectableErrorsDeltaAvg OBJECT-TYPE
    SYNTAX       Unsigned64
    MAX-ACCESS   read-only
    STATUS       current
    DESCRIPTION
        "Cisco Firepower adaptor:MenloBaseErrorStats:uncorrectableErrorsDe
        ltaAvg managed object property"
    ::= { cfprAdaptorMenloBaseErrorStatsEntry 15 }

cfprAdaptorMenloBaseErrorStatsUncorrectableErrorsDeltaMax OBJECT-TYPE
    SYNTAX       Unsigned64
    MAX-ACCESS   read-only
    STATUS       current
    DESCRIPTION
        "Cisco Firepower adaptor:MenloBaseErrorStats:uncorrectableErrorsDe
        ltaMax managed object property"
    ::= { cfprAdaptorMenloBaseErrorStatsEntry 16 }

cfprAdaptorMenloBaseErrorStatsUncorrectableErrorsDeltaMin OBJECT-TYPE
    SYNTAX       Unsigned64
    MAX-ACCESS   read-only
    STATUS       current
    DESCRIPTION
        "Cisco Firepower adaptor:MenloBaseErrorStats:uncorrectableErrorsDe
        ltaMin managed object property"
    ::= { cfprAdaptorMenloBaseErrorStatsEntry 17 }

cfprAdaptorMenloBaseErrorStatsUpdate OBJECT-TYPE
    SYNTAX       Gauge32
    MAX-ACCESS   read-only
    STATUS       current
    DESCRIPTION
        "Cisco Firepower adaptor:MenloBaseErrorStats:update
        managed object property"
    ::= { cfprAdaptorMenloBaseErrorStatsEntry 18 }

cfprAdaptorMenloBaseErrorStatsHistTable OBJECT-TYPE
    SYNTAX           SEQUENCE OF CfprAdaptorMenloBaseErrorStatsHistEntry
    MAX-ACCESS       not-accessible
    STATUS           current
    DESCRIPTION
        "Cisco Firepower adaptor:MenloBaseErrorStatsHist
        managed object table"
    ::= { cfprAdaptorObjects 83 }

cfprAdaptorMenloBaseErrorStatsHistEntry OBJECT-TYPE
    SYNTAX           CfprAdaptorMenloBaseErrorStatsHistEntry
    MAX-ACCESS       not-accessible
    STATUS           current
    DESCRIPTION
        "Entry for the cfprAdaptorMenloBaseErrorStatsHistTable table."
    INDEX { cfprAdaptorMenloBaseErrorStatsHistInstanceId }
    ::= { cfprAdaptorMenloBaseErrorStatsHistTable 1 }

CfprAdaptorMenloBaseErrorStatsHistEntry ::= SEQUENCE {
    cfprAdaptorMenloBaseErrorStatsHistInstanceId                     CfprManagedObjectId,
    cfprAdaptorMenloBaseErrorStatsHistDn                             CfprManagedObjectDn,
    cfprAdaptorMenloBaseErrorStatsHistRn                             SnmpAdminString,
    cfprAdaptorMenloBaseErrorStatsHistCorrectableErrors              Unsigned64,
    cfprAdaptorMenloBaseErrorStatsHistCorrectableErrorsDelta         Unsigned64,
    cfprAdaptorMenloBaseErrorStatsHistCorrectableErrorsDeltaAvg      Unsigned64,
    cfprAdaptorMenloBaseErrorStatsHistCorrectableErrorsDeltaMax      Unsigned64,
    cfprAdaptorMenloBaseErrorStatsHistCorrectableErrorsDeltaMin      Unsigned64,
    cfprAdaptorMenloBaseErrorStatsHistId                             Unsigned64,
    cfprAdaptorMenloBaseErrorStatsHistMostRecent                     TruthValue,
    cfprAdaptorMenloBaseErrorStatsHistSuspect                        TruthValue,
    cfprAdaptorMenloBaseErrorStatsHistThresholded                    CfprAdaptorMenloBaseErrorStatsHistThresholded,
    cfprAdaptorMenloBaseErrorStatsHistTimeCollected                  DateAndTime,
    cfprAdaptorMenloBaseErrorStatsHistUncorrectableErrors            Unsigned64,
    cfprAdaptorMenloBaseErrorStatsHistUncorrectableErrorsDelta       Unsigned64,
    cfprAdaptorMenloBaseErrorStatsHistUncorrectableErrorsDeltaAvg    Unsigned64,
    cfprAdaptorMenloBaseErrorStatsHistUncorrectableErrorsDeltaMax    Unsigned64,
    cfprAdaptorMenloBaseErrorStatsHistUncorrectableErrorsDeltaMin    Unsigned64
}

cfprAdaptorMenloBaseErrorStatsHistInstanceId OBJECT-TYPE
    SYNTAX       CfprManagedObjectId
    MAX-ACCESS   not-accessible
    STATUS       current
    DESCRIPTION
        "Instance identifier of the managed object."
    ::= { cfprAdaptorMenloBaseErrorStatsHistEntry 1 }

cfprAdaptorMenloBaseErrorStatsHistDn OBJECT-TYPE
    SYNTAX       CfprManagedObjectDn
    MAX-ACCESS   read-only
    STATUS       current
    DESCRIPTION
        "Cisco Firepower adaptor:MenloBaseErrorStatsHist:dn
        managed object property"
    ::= { cfprAdaptorMenloBaseErrorStatsHistEntry 2 }

cfprAdaptorMenloBaseErrorStatsHistRn OBJECT-TYPE
    SYNTAX       SnmpAdminString
    MAX-ACCESS   read-only
    STATUS       current
    DESCRIPTION
        "Cisco Firepower adaptor:MenloBaseErrorStatsHist:rn
        managed object property"
    ::= { cfprAdaptorMenloBaseErrorStatsHistEntry 3 }

cfprAdaptorMenloBaseErrorStatsHistCorrectableErrors OBJECT-TYPE
    SYNTAX       Unsigned64
    MAX-ACCESS   read-only
    STATUS       current
    DESCRIPTION
        "Cisco Firepower adaptor:MenloBaseErrorStatsHist:correctableErrors
         managed object property"
    ::= { cfprAdaptorMenloBaseErrorStatsHistEntry 4 }

cfprAdaptorMenloBaseErrorStatsHistCorrectableErrorsDelta OBJECT-TYPE
    SYNTAX       Unsigned64
    MAX-ACCESS   read-only
    STATUS       current
    DESCRIPTION
        "Cisco Firepower adaptor:MenloBaseErrorStatsHist:correctableErrors
        Delta managed object property"
    ::= { cfprAdaptorMenloBaseErrorStatsHistEntry 5 }

cfprAdaptorMenloBaseErrorStatsHistCorrectableErrorsDeltaAvg OBJECT-TYPE
    SYNTAX       Unsigned64
    MAX-ACCESS   read-only
    STATUS       current
    DESCRIPTION
        "Cisco Firepower adaptor:MenloBaseErrorStatsHist:correctableErrors
        DeltaAvg managed object property"
    ::= { cfprAdaptorMenloBaseErrorStatsHistEntry 6 }

cfprAdaptorMenloBaseErrorStatsHistCorrectableErrorsDeltaMax OBJECT-TYPE
    SYNTAX       Unsigned64
    MAX-ACCESS   read-only
    STATUS       current
    DESCRIPTION
        "Cisco Firepower adaptor:MenloBaseErrorStatsHist:correctableErrors
        DeltaMax managed object property"
    ::= { cfprAdaptorMenloBaseErrorStatsHistEntry 7 }

cfprAdaptorMenloBaseErrorStatsHistCorrectableErrorsDeltaMin OBJECT-TYPE
    SYNTAX       Unsigned64
    MAX-ACCESS   read-only
    STATUS       current
    DESCRIPTION
        "Cisco Firepower adaptor:MenloBaseErrorStatsHist:correctableErrors
        DeltaMin managed object property"
    ::= { cfprAdaptorMenloBaseErrorStatsHistEntry 8 }

cfprAdaptorMenloBaseErrorStatsHistId OBJECT-TYPE
    SYNTAX       Unsigned64
    MAX-ACCESS   read-only
    STATUS       current
    DESCRIPTION
        "Cisco Firepower adaptor:MenloBaseErrorStatsHist:id
        managed object property"
    ::= { cfprAdaptorMenloBaseErrorStatsHistEntry 9 }

cfprAdaptorMenloBaseErrorStatsHistMostRecent OBJECT-TYPE
    SYNTAX       TruthValue
    MAX-ACCESS   read-only
    STATUS       current
    DESCRIPTION
        "Cisco Firepower adaptor:MenloBaseErrorStatsHist:mostRecent
        managed object property"
    ::= { cfprAdaptorMenloBaseErrorStatsHistEntry 10 }

cfprAdaptorMenloBaseErrorStatsHistSuspect OBJECT-TYPE
    SYNTAX       TruthValue
    MAX-ACCESS   read-only
    STATUS       current
    DESCRIPTION
        "Cisco Firepower adaptor:MenloBaseErrorStatsHist:suspect
        managed object property"
    ::= { cfprAdaptorMenloBaseErrorStatsHistEntry 11 }

cfprAdaptorMenloBaseErrorStatsHistThresholded OBJECT-TYPE
    SYNTAX       CfprAdaptorMenloBaseErrorStatsHistThresholded
    MAX-ACCESS   read-only
    STATUS       current
    DESCRIPTION
        "Cisco Firepower adaptor:MenloBaseErrorStatsHist:thresholded
        managed object property"
    ::= { cfprAdaptorMenloBaseErrorStatsHistEntry 12 }

cfprAdaptorMenloBaseErrorStatsHistTimeCollected OBJECT-TYPE
    SYNTAX       DateAndTime
    MAX-ACCESS   read-only
    STATUS       current
    DESCRIPTION
        "Cisco Firepower adaptor:MenloBaseErrorStatsHist:timeCollected
        managed object property"
    ::= { cfprAdaptorMenloBaseErrorStatsHistEntry 13 }

cfprAdaptorMenloBaseErrorStatsHistUncorrectableErrors OBJECT-TYPE
    SYNTAX       Unsigned64
    MAX-ACCESS   read-only
    STATUS       current
    DESCRIPTION
        "Cisco Firepower adaptor:MenloBaseErrorStatsHist:uncorrectableErro
        rs managed object property"
    ::= { cfprAdaptorMenloBaseErrorStatsHistEntry 14 }

cfprAdaptorMenloBaseErrorStatsHistUncorrectableErrorsDelta OBJECT-TYPE
    SYNTAX       Unsigned64
    MAX-ACCESS   read-only
    STATUS       current
    DESCRIPTION
        "Cisco Firepower adaptor:MenloBaseErrorStatsHist:uncorrectableErro
        rsDelta managed object property"
    ::= { cfprAdaptorMenloBaseErrorStatsHistEntry 15 }

cfprAdaptorMenloBaseErrorStatsHistUncorrectableErrorsDeltaAvg OBJECT-TYPE
    SYNTAX       Unsigned64
    MAX-ACCESS   read-only
    STATUS       current
    DESCRIPTION
        "Cisco Firepower adaptor:MenloBaseErrorStatsHist:uncorrectableErro
        rsDeltaAvg managed object property"
    ::= { cfprAdaptorMenloBaseErrorStatsHistEntry 16 }

cfprAdaptorMenloBaseErrorStatsHistUncorrectableErrorsDeltaMax OBJECT-TYPE
    SYNTAX       Unsigned64
    MAX-ACCESS   read-only
    STATUS       current
    DESCRIPTION
        "Cisco Firepower adaptor:MenloBaseErrorStatsHist:uncorrectableErro
        rsDeltaMax managed object property"
    ::= { cfprAdaptorMenloBaseErrorStatsHistEntry 17 }

cfprAdaptorMenloBaseErrorStatsHistUncorrectableErrorsDeltaMin OBJECT-TYPE
    SYNTAX       Unsigned64
    MAX-ACCESS   read-only
    STATUS       current
    DESCRIPTION
        "Cisco Firepower adaptor:MenloBaseErrorStatsHist:uncorrectableErro
        rsDeltaMin managed object property"
    ::= { cfprAdaptorMenloBaseErrorStatsHistEntry 18 }

cfprAdaptorMenloDcePortStatsTable OBJECT-TYPE
    SYNTAX           SEQUENCE OF CfprAdaptorMenloDcePortStatsEntry
    MAX-ACCESS       not-accessible
    STATUS           current
    DESCRIPTION
        "Cisco Firepower adaptor:MenloDcePortStats managed object table"
    ::= { cfprAdaptorObjects 84 }

cfprAdaptorMenloDcePortStatsEntry OBJECT-TYPE
    SYNTAX           CfprAdaptorMenloDcePortStatsEntry
    MAX-ACCESS       not-accessible
    STATUS           current
    DESCRIPTION
        "Entry for the cfprAdaptorMenloDcePortStatsTable table."
    INDEX { cfprAdaptorMenloDcePortStatsInstanceId }
    ::= { cfprAdaptorMenloDcePortStatsTable 1 }

CfprAdaptorMenloDcePortStatsEntry ::= SEQUENCE {
    cfprAdaptorMenloDcePortStatsInstanceId                           CfprManagedObjectId,
    cfprAdaptorMenloDcePortStatsDn                                   CfprManagedObjectDn,
    cfprAdaptorMenloDcePortStatsRn                                   SnmpAdminString,
    cfprAdaptorMenloDcePortStatsIntervals                            Gauge32,
    cfprAdaptorMenloDcePortStatsMenloPortIndex                       CfprAdaptorMenloStatsIndex,
    cfprAdaptorMenloDcePortStatsRxPauseCFC                           Unsigned64,
    cfprAdaptorMenloDcePortStatsRxPauseCFCDelta                      Counter64,
    cfprAdaptorMenloDcePortStatsRxPauseCFCDeltaAvg                   Unsigned64,
    cfprAdaptorMenloDcePortStatsRxPauseCFCDeltaMax                   Unsigned64,
    cfprAdaptorMenloDcePortStatsRxPauseCFCDeltaMin                   Unsigned64,
    cfprAdaptorMenloDcePortStatsRxPausePFC                           Unsigned64,
    cfprAdaptorMenloDcePortStatsRxPausePFCDelta                      Counter64,
    cfprAdaptorMenloDcePortStatsRxPausePFCDeltaAvg                   Unsigned64,
    cfprAdaptorMenloDcePortStatsRxPausePFCDeltaMax                   Unsigned64,
    cfprAdaptorMenloDcePortStatsRxPausePFCDeltaMin                   Unsigned64,
    cfprAdaptorMenloDcePortStatsSuspect                              TruthValue,
    cfprAdaptorMenloDcePortStatsThresholded                          CfprAdaptorMenloDcePortStatsThresholded,
    cfprAdaptorMenloDcePortStatsTimeCollected                        DateAndTime,
    cfprAdaptorMenloDcePortStatsTxPauseCFC                           Unsigned64,
    cfprAdaptorMenloDcePortStatsTxPauseCFCDelta                      Counter64,
    cfprAdaptorMenloDcePortStatsTxPauseCFCDeltaAvg                   Unsigned64,
    cfprAdaptorMenloDcePortStatsTxPauseCFCDeltaMax                   Unsigned64,
    cfprAdaptorMenloDcePortStatsTxPauseCFCDeltaMin                   Unsigned64,
    cfprAdaptorMenloDcePortStatsTxPausePFC                           Unsigned64,
    cfprAdaptorMenloDcePortStatsTxPausePFCDelta                      Counter64,
    cfprAdaptorMenloDcePortStatsTxPausePFCDeltaAvg                   Unsigned64,
    cfprAdaptorMenloDcePortStatsTxPausePFCDeltaMax                   Unsigned64,
    cfprAdaptorMenloDcePortStatsTxPausePFCDeltaMin                   Unsigned64,
    cfprAdaptorMenloDcePortStatsUpdate                               Gauge32
}

cfprAdaptorMenloDcePortStatsInstanceId OBJECT-TYPE
    SYNTAX       CfprManagedObjectId
    MAX-ACCESS   not-accessible
    STATUS       current
    DESCRIPTION
        "Instance identifier of the managed object."
    ::= { cfprAdaptorMenloDcePortStatsEntry 1 }

cfprAdaptorMenloDcePortStatsDn OBJECT-TYPE
    SYNTAX       CfprManagedObjectDn
    MAX-ACCESS   read-only
    STATUS       current
    DESCRIPTION
        "Cisco Firepower adaptor:MenloDcePortStats:dn managed
        object property"
    ::= { cfprAdaptorMenloDcePortStatsEntry 2 }

cfprAdaptorMenloDcePortStatsRn OBJECT-TYPE
    SYNTAX       SnmpAdminString
    MAX-ACCESS   read-only
    STATUS       current
    DESCRIPTION
        "Cisco Firepower adaptor:MenloDcePortStats:rn managed
        object property"
    ::= { cfprAdaptorMenloDcePortStatsEntry 3 }

cfprAdaptorMenloDcePortStatsIntervals OBJECT-TYPE
    SYNTAX       Gauge32
    MAX-ACCESS   read-only
    STATUS       current
    DESCRIPTION
        "Cisco Firepower adaptor:MenloDcePortStats:intervals
        managed object property"
    ::= { cfprAdaptorMenloDcePortStatsEntry 4 }

cfprAdaptorMenloDcePortStatsMenloPortIndex OBJECT-TYPE
    SYNTAX       CfprAdaptorMenloStatsIndex
    MAX-ACCESS   read-only
    STATUS       current
    DESCRIPTION
        "Cisco Firepower adaptor:MenloDcePortStats:menloPortIndex
        managed object property"
    ::= { cfprAdaptorMenloDcePortStatsEntry 5 }

cfprAdaptorMenloDcePortStatsRxPauseCFC OBJECT-TYPE
    SYNTAX       Unsigned64
    MAX-ACCESS   read-only
    STATUS       current
    DESCRIPTION
        "Cisco Firepower adaptor:MenloDcePortStats:rxPauseCFC
        managed object property"
    ::= { cfprAdaptorMenloDcePortStatsEntry 6 }

cfprAdaptorMenloDcePortStatsRxPauseCFCDelta OBJECT-TYPE
    SYNTAX       Counter64
    MAX-ACCESS   read-only
    STATUS       current
    DESCRIPTION
        "Cisco Firepower adaptor:MenloDcePortStats:rxPauseCFCDelta
        managed object property"
    ::= { cfprAdaptorMenloDcePortStatsEntry 7 }

cfprAdaptorMenloDcePortStatsRxPauseCFCDeltaAvg OBJECT-TYPE
    SYNTAX       Unsigned64
    MAX-ACCESS   read-only
    STATUS       current
    DESCRIPTION
        "Cisco Firepower adaptor:MenloDcePortStats:rxPauseCFCDeltaAvg
        managed object property"
    ::= { cfprAdaptorMenloDcePortStatsEntry 8 }

cfprAdaptorMenloDcePortStatsRxPauseCFCDeltaMax OBJECT-TYPE
    SYNTAX       Unsigned64
    MAX-ACCESS   read-only
    STATUS       current
    DESCRIPTION
        "Cisco Firepower adaptor:MenloDcePortStats:rxPauseCFCDeltaMax
        managed object property"
    ::= { cfprAdaptorMenloDcePortStatsEntry 9 }

cfprAdaptorMenloDcePortStatsRxPauseCFCDeltaMin OBJECT-TYPE
    SYNTAX       Unsigned64
    MAX-ACCESS   read-only
    STATUS       current
    DESCRIPTION
        "Cisco Firepower adaptor:MenloDcePortStats:rxPauseCFCDeltaMin
        managed object property"
    ::= { cfprAdaptorMenloDcePortStatsEntry 10 }

cfprAdaptorMenloDcePortStatsRxPausePFC OBJECT-TYPE
    SYNTAX       Unsigned64
    MAX-ACCESS   read-only
    STATUS       current
    DESCRIPTION
        "Cisco Firepower adaptor:MenloDcePortStats:rxPausePFC
        managed object property"
    ::= { cfprAdaptorMenloDcePortStatsEntry 11 }

cfprAdaptorMenloDcePortStatsRxPausePFCDelta OBJECT-TYPE
    SYNTAX       Counter64
    MAX-ACCESS   read-only
    STATUS       current
    DESCRIPTION
        "Cisco Firepower adaptor:MenloDcePortStats:rxPausePFCDelta
        managed object property"
    ::= { cfprAdaptorMenloDcePortStatsEntry 12 }

cfprAdaptorMenloDcePortStatsRxPausePFCDeltaAvg OBJECT-TYPE
    SYNTAX       Unsigned64
    MAX-ACCESS   read-only
    STATUS       current
    DESCRIPTION
        "Cisco Firepower adaptor:MenloDcePortStats:rxPausePFCDeltaAvg
        managed object property"
    ::= { cfprAdaptorMenloDcePortStatsEntry 13 }

cfprAdaptorMenloDcePortStatsRxPausePFCDeltaMax OBJECT-TYPE
    SYNTAX       Unsigned64
    MAX-ACCESS   read-only
    STATUS       current
    DESCRIPTION
        "Cisco Firepower adaptor:MenloDcePortStats:rxPausePFCDeltaMax
        managed object property"
    ::= { cfprAdaptorMenloDcePortStatsEntry 14 }

cfprAdaptorMenloDcePortStatsRxPausePFCDeltaMin OBJECT-TYPE
    SYNTAX       Unsigned64
    MAX-ACCESS   read-only
    STATUS       current
    DESCRIPTION
        "Cisco Firepower adaptor:MenloDcePortStats:rxPausePFCDeltaMin
        managed object property"
    ::= { cfprAdaptorMenloDcePortStatsEntry 15 }

cfprAdaptorMenloDcePortStatsSuspect OBJECT-TYPE
    SYNTAX       TruthValue
    MAX-ACCESS   read-only
    STATUS       current
    DESCRIPTION
        "Cisco Firepower adaptor:MenloDcePortStats:suspect
        managed object property"
    ::= { cfprAdaptorMenloDcePortStatsEntry 16 }

cfprAdaptorMenloDcePortStatsThresholded OBJECT-TYPE
    SYNTAX       CfprAdaptorMenloDcePortStatsThresholded
    MAX-ACCESS   read-only
    STATUS       current
    DESCRIPTION
        "Cisco Firepower adaptor:MenloDcePortStats:thresholded
        managed object property"
    ::= { cfprAdaptorMenloDcePortStatsEntry 17 }

cfprAdaptorMenloDcePortStatsTimeCollected OBJECT-TYPE
    SYNTAX       DateAndTime
    MAX-ACCESS   read-only
    STATUS       current
    DESCRIPTION
        "Cisco Firepower adaptor:MenloDcePortStats:timeCollected
        managed object property"
    ::= { cfprAdaptorMenloDcePortStatsEntry 18 }

cfprAdaptorMenloDcePortStatsTxPauseCFC OBJECT-TYPE
    SYNTAX       Unsigned64
    MAX-ACCESS   read-only
    STATUS       current
    DESCRIPTION
        "Cisco Firepower adaptor:MenloDcePortStats:txPauseCFC
        managed object property"
    ::= { cfprAdaptorMenloDcePortStatsEntry 19 }

cfprAdaptorMenloDcePortStatsTxPauseCFCDelta OBJECT-TYPE
    SYNTAX       Counter64
    MAX-ACCESS   read-only
    STATUS       current
    DESCRIPTION
        "Cisco Firepower adaptor:MenloDcePortStats:txPauseCFCDelta
        managed object property"
    ::= { cfprAdaptorMenloDcePortStatsEntry 20 }

cfprAdaptorMenloDcePortStatsTxPauseCFCDeltaAvg OBJECT-TYPE
    SYNTAX       Unsigned64
    MAX-ACCESS   read-only
    STATUS       current
    DESCRIPTION
        "Cisco Firepower adaptor:MenloDcePortStats:txPauseCFCDeltaAvg
        managed object property"
    ::= { cfprAdaptorMenloDcePortStatsEntry 21 }

cfprAdaptorMenloDcePortStatsTxPauseCFCDeltaMax OBJECT-TYPE
    SYNTAX       Unsigned64
    MAX-ACCESS   read-only
    STATUS       current
    DESCRIPTION
        "Cisco Firepower adaptor:MenloDcePortStats:txPauseCFCDeltaMax
        managed object property"
    ::= { cfprAdaptorMenloDcePortStatsEntry 22 }

cfprAdaptorMenloDcePortStatsTxPauseCFCDeltaMin OBJECT-TYPE
    SYNTAX       Unsigned64
    MAX-ACCESS   read-only
    STATUS       current
    DESCRIPTION
        "Cisco Firepower adaptor:MenloDcePortStats:txPauseCFCDeltaMin
        managed object property"
    ::= { cfprAdaptorMenloDcePortStatsEntry 23 }

cfprAdaptorMenloDcePortStatsTxPausePFC OBJECT-TYPE
    SYNTAX       Unsigned64
    MAX-ACCESS   read-only
    STATUS       current
    DESCRIPTION
        "Cisco Firepower adaptor:MenloDcePortStats:txPausePFC
        managed object property"
    ::= { cfprAdaptorMenloDcePortStatsEntry 24 }

cfprAdaptorMenloDcePortStatsTxPausePFCDelta OBJECT-TYPE
    SYNTAX       Counter64
    MAX-ACCESS   read-only
    STATUS       current
    DESCRIPTION
        "Cisco Firepower adaptor:MenloDcePortStats:txPausePFCDelta
        managed object property"
    ::= { cfprAdaptorMenloDcePortStatsEntry 25 }

cfprAdaptorMenloDcePortStatsTxPausePFCDeltaAvg OBJECT-TYPE
    SYNTAX       Unsigned64
    MAX-ACCESS   read-only
    STATUS       current
    DESCRIPTION
        "Cisco Firepower adaptor:MenloDcePortStats:txPausePFCDeltaAvg
        managed object property"
    ::= { cfprAdaptorMenloDcePortStatsEntry 26 }

cfprAdaptorMenloDcePortStatsTxPausePFCDeltaMax OBJECT-TYPE
    SYNTAX       Unsigned64
    MAX-ACCESS   read-only
    STATUS       current
    DESCRIPTION
        "Cisco Firepower adaptor:MenloDcePortStats:txPausePFCDeltaMax
        managed object property"
    ::= { cfprAdaptorMenloDcePortStatsEntry 27 }

cfprAdaptorMenloDcePortStatsTxPausePFCDeltaMin OBJECT-TYPE
    SYNTAX       Unsigned64
    MAX-ACCESS   read-only
    STATUS       current
    DESCRIPTION
        "Cisco Firepower adaptor:MenloDcePortStats:txPausePFCDeltaMin
        managed object property"
    ::= { cfprAdaptorMenloDcePortStatsEntry 28 }

cfprAdaptorMenloDcePortStatsUpdate OBJECT-TYPE
    SYNTAX       Gauge32
    MAX-ACCESS   read-only
    STATUS       current
    DESCRIPTION
        "Cisco Firepower adaptor:MenloDcePortStats:update
        managed object property"
    ::= { cfprAdaptorMenloDcePortStatsEntry 29 }

cfprAdaptorMenloDcePortStatsHistTable OBJECT-TYPE
    SYNTAX           SEQUENCE OF CfprAdaptorMenloDcePortStatsHistEntry
    MAX-ACCESS       not-accessible
    STATUS           current
    DESCRIPTION
        "Cisco Firepower adaptor:MenloDcePortStatsHist
        managed object table"
    ::= { cfprAdaptorObjects 85 }

cfprAdaptorMenloDcePortStatsHistEntry OBJECT-TYPE
    SYNTAX           CfprAdaptorMenloDcePortStatsHistEntry
    MAX-ACCESS       not-accessible
    STATUS           current
    DESCRIPTION
        "Entry for the cfprAdaptorMenloDcePortStatsHistTable table."
    INDEX { cfprAdaptorMenloDcePortStatsHistInstanceId }
    ::= { cfprAdaptorMenloDcePortStatsHistTable 1 }

CfprAdaptorMenloDcePortStatsHistEntry ::= SEQUENCE {
    cfprAdaptorMenloDcePortStatsHistInstanceId                       CfprManagedObjectId,
    cfprAdaptorMenloDcePortStatsHistDn                               CfprManagedObjectDn,
    cfprAdaptorMenloDcePortStatsHistRn                               SnmpAdminString,
    cfprAdaptorMenloDcePortStatsHistId                               Unsigned64,
    cfprAdaptorMenloDcePortStatsHistMostRecent                       TruthValue,
    cfprAdaptorMenloDcePortStatsHistRxPauseCFC                       Unsigned64,
    cfprAdaptorMenloDcePortStatsHistRxPauseCFCDelta                  Unsigned64,
    cfprAdaptorMenloDcePortStatsHistRxPauseCFCDeltaAvg               Unsigned64,
    cfprAdaptorMenloDcePortStatsHistRxPauseCFCDeltaMax               Unsigned64,
    cfprAdaptorMenloDcePortStatsHistRxPauseCFCDeltaMin               Unsigned64,
    cfprAdaptorMenloDcePortStatsHistRxPausePFC                       Unsigned64,
    cfprAdaptorMenloDcePortStatsHistRxPausePFCDelta                  Unsigned64,
    cfprAdaptorMenloDcePortStatsHistRxPausePFCDeltaAvg               Unsigned64,
    cfprAdaptorMenloDcePortStatsHistRxPausePFCDeltaMax               Unsigned64,
    cfprAdaptorMenloDcePortStatsHistRxPausePFCDeltaMin               Unsigned64,
    cfprAdaptorMenloDcePortStatsHistSuspect                          TruthValue,
    cfprAdaptorMenloDcePortStatsHistThresholded                      CfprAdaptorMenloDcePortStatsHistThresholded,
    cfprAdaptorMenloDcePortStatsHistTimeCollected                    DateAndTime,
    cfprAdaptorMenloDcePortStatsHistTxPauseCFC                       Unsigned64,
    cfprAdaptorMenloDcePortStatsHistTxPauseCFCDelta                  Unsigned64,
    cfprAdaptorMenloDcePortStatsHistTxPauseCFCDeltaAvg               Unsigned64,
    cfprAdaptorMenloDcePortStatsHistTxPauseCFCDeltaMax               Unsigned64,
    cfprAdaptorMenloDcePortStatsHistTxPauseCFCDeltaMin               Unsigned64,
    cfprAdaptorMenloDcePortStatsHistTxPausePFC                       Unsigned64,
    cfprAdaptorMenloDcePortStatsHistTxPausePFCDelta                  Unsigned64,
    cfprAdaptorMenloDcePortStatsHistTxPausePFCDeltaAvg               Unsigned64,
    cfprAdaptorMenloDcePortStatsHistTxPausePFCDeltaMax               Unsigned64,
    cfprAdaptorMenloDcePortStatsHistTxPausePFCDeltaMin               Unsigned64
}

cfprAdaptorMenloDcePortStatsHistInstanceId OBJECT-TYPE
    SYNTAX       CfprManagedObjectId
    MAX-ACCESS   not-accessible
    STATUS       current
    DESCRIPTION
        "Instance identifier of the managed object."
    ::= { cfprAdaptorMenloDcePortStatsHistEntry 1 }

cfprAdaptorMenloDcePortStatsHistDn OBJECT-TYPE
    SYNTAX       CfprManagedObjectDn
    MAX-ACCESS   read-only
    STATUS       current
    DESCRIPTION
        "Cisco Firepower adaptor:MenloDcePortStatsHist:dn
        managed object property"
    ::= { cfprAdaptorMenloDcePortStatsHistEntry 2 }

cfprAdaptorMenloDcePortStatsHistRn OBJECT-TYPE
    SYNTAX       SnmpAdminString
    MAX-ACCESS   read-only
    STATUS       current
    DESCRIPTION
        "Cisco Firepower adaptor:MenloDcePortStatsHist:rn
        managed object property"
    ::= { cfprAdaptorMenloDcePortStatsHistEntry 3 }

cfprAdaptorMenloDcePortStatsHistId OBJECT-TYPE
    SYNTAX       Unsigned64
    MAX-ACCESS   read-only
    STATUS       current
    DESCRIPTION
        "Cisco Firepower adaptor:MenloDcePortStatsHist:id
        managed object property"
    ::= { cfprAdaptorMenloDcePortStatsHistEntry 4 }

cfprAdaptorMenloDcePortStatsHistMostRecent OBJECT-TYPE
    SYNTAX       TruthValue
    MAX-ACCESS   read-only
    STATUS       current
    DESCRIPTION
        "Cisco Firepower adaptor:MenloDcePortStatsHist:mostRecent
        managed object property"
    ::= { cfprAdaptorMenloDcePortStatsHistEntry 5 }

cfprAdaptorMenloDcePortStatsHistRxPauseCFC OBJECT-TYPE
    SYNTAX       Unsigned64
    MAX-ACCESS   read-only
    STATUS       current
    DESCRIPTION
        "Cisco Firepower adaptor:MenloDcePortStatsHist:rxPauseCFC
        managed object property"
    ::= { cfprAdaptorMenloDcePortStatsHistEntry 6 }

cfprAdaptorMenloDcePortStatsHistRxPauseCFCDelta OBJECT-TYPE
    SYNTAX       Unsigned64
    MAX-ACCESS   read-only
    STATUS       current
    DESCRIPTION
        "Cisco Firepower adaptor:MenloDcePortStatsHist:rxPauseCFCDelta
        managed object property"
    ::= { cfprAdaptorMenloDcePortStatsHistEntry 7 }

cfprAdaptorMenloDcePortStatsHistRxPauseCFCDeltaAvg OBJECT-TYPE
    SYNTAX       Unsigned64
    MAX-ACCESS   read-only
    STATUS       current
    DESCRIPTION
        "Cisco Firepower adaptor:MenloDcePortStatsHist:rxPauseCFCDeltaAvg
        managed object property"
    ::= { cfprAdaptorMenloDcePortStatsHistEntry 8 }

cfprAdaptorMenloDcePortStatsHistRxPauseCFCDeltaMax OBJECT-TYPE
    SYNTAX       Unsigned64
    MAX-ACCESS   read-only
    STATUS       current
    DESCRIPTION
        "Cisco Firepower adaptor:MenloDcePortStatsHist:rxPauseCFCDeltaMax
        managed object property"
    ::= { cfprAdaptorMenloDcePortStatsHistEntry 9 }

cfprAdaptorMenloDcePortStatsHistRxPauseCFCDeltaMin OBJECT-TYPE
    SYNTAX       Unsigned64
    MAX-ACCESS   read-only
    STATUS       current
    DESCRIPTION
        "Cisco Firepower adaptor:MenloDcePortStatsHist:rxPauseCFCDeltaMin
        managed object property"
    ::= { cfprAdaptorMenloDcePortStatsHistEntry 10 }

cfprAdaptorMenloDcePortStatsHistRxPausePFC OBJECT-TYPE
    SYNTAX       Unsigned64
    MAX-ACCESS   read-only
    STATUS       current
    DESCRIPTION
        "Cisco Firepower adaptor:MenloDcePortStatsHist:rxPausePFC
        managed object property"
    ::= { cfprAdaptorMenloDcePortStatsHistEntry 11 }

cfprAdaptorMenloDcePortStatsHistRxPausePFCDelta OBJECT-TYPE
    SYNTAX       Unsigned64
    MAX-ACCESS   read-only
    STATUS       current
    DESCRIPTION
        "Cisco Firepower adaptor:MenloDcePortStatsHist:rxPausePFCDelta
        managed object property"
    ::= { cfprAdaptorMenloDcePortStatsHistEntry 12 }

cfprAdaptorMenloDcePortStatsHistRxPausePFCDeltaAvg OBJECT-TYPE
    SYNTAX       Unsigned64
    MAX-ACCESS   read-only
    STATUS       current
    DESCRIPTION
        "Cisco Firepower adaptor:MenloDcePortStatsHist:rxPausePFCDeltaAvg
        managed object property"
    ::= { cfprAdaptorMenloDcePortStatsHistEntry 13 }

cfprAdaptorMenloDcePortStatsHistRxPausePFCDeltaMax OBJECT-TYPE
    SYNTAX       Unsigned64
    MAX-ACCESS   read-only
    STATUS       current
    DESCRIPTION
        "Cisco Firepower adaptor:MenloDcePortStatsHist:rxPausePFCDeltaMax
        managed object property"
    ::= { cfprAdaptorMenloDcePortStatsHistEntry 14 }

cfprAdaptorMenloDcePortStatsHistRxPausePFCDeltaMin OBJECT-TYPE
    SYNTAX       Unsigned64
    MAX-ACCESS   read-only
    STATUS       current
    DESCRIPTION
        "Cisco Firepower adaptor:MenloDcePortStatsHist:rxPausePFCDeltaMin
        managed object property"
    ::= { cfprAdaptorMenloDcePortStatsHistEntry 15 }

cfprAdaptorMenloDcePortStatsHistSuspect OBJECT-TYPE
    SYNTAX       TruthValue
    MAX-ACCESS   read-only
    STATUS       current
    DESCRIPTION
        "Cisco Firepower adaptor:MenloDcePortStatsHist:suspect
        managed object property"
    ::= { cfprAdaptorMenloDcePortStatsHistEntry 16 }

cfprAdaptorMenloDcePortStatsHistThresholded OBJECT-TYPE
    SYNTAX       CfprAdaptorMenloDcePortStatsHistThresholded
    MAX-ACCESS   read-only
    STATUS       current
    DESCRIPTION
        "Cisco Firepower adaptor:MenloDcePortStatsHist:thresholded
        managed object property"
    ::= { cfprAdaptorMenloDcePortStatsHistEntry 17 }

cfprAdaptorMenloDcePortStatsHistTimeCollected OBJECT-TYPE
    SYNTAX       DateAndTime
    MAX-ACCESS   read-only
    STATUS       current
    DESCRIPTION
        "Cisco Firepower adaptor:MenloDcePortStatsHist:timeCollected
        managed object property"
    ::= { cfprAdaptorMenloDcePortStatsHistEntry 18 }

cfprAdaptorMenloDcePortStatsHistTxPauseCFC OBJECT-TYPE
    SYNTAX       Unsigned64
    MAX-ACCESS   read-only
    STATUS       current
    DESCRIPTION
        "Cisco Firepower adaptor:MenloDcePortStatsHist:txPauseCFC
        managed object property"
    ::= { cfprAdaptorMenloDcePortStatsHistEntry 19 }

cfprAdaptorMenloDcePortStatsHistTxPauseCFCDelta OBJECT-TYPE
    SYNTAX       Unsigned64
    MAX-ACCESS   read-only
    STATUS       current
    DESCRIPTION
        "Cisco Firepower adaptor:MenloDcePortStatsHist:txPauseCFCDelta
        managed object property"
    ::= { cfprAdaptorMenloDcePortStatsHistEntry 20 }

cfprAdaptorMenloDcePortStatsHistTxPauseCFCDeltaAvg OBJECT-TYPE
    SYNTAX       Unsigned64
    MAX-ACCESS   read-only
    STATUS       current
    DESCRIPTION
        "Cisco Firepower adaptor:MenloDcePortStatsHist:txPauseCFCDeltaAvg
        managed object property"
    ::= { cfprAdaptorMenloDcePortStatsHistEntry 21 }

cfprAdaptorMenloDcePortStatsHistTxPauseCFCDeltaMax OBJECT-TYPE
    SYNTAX       Unsigned64
    MAX-ACCESS   read-only
    STATUS       current
    DESCRIPTION
        "Cisco Firepower adaptor:MenloDcePortStatsHist:txPauseCFCDeltaMax
        managed object property"
    ::= { cfprAdaptorMenloDcePortStatsHistEntry 22 }

cfprAdaptorMenloDcePortStatsHistTxPauseCFCDeltaMin OBJECT-TYPE
    SYNTAX       Unsigned64
    MAX-ACCESS   read-only
    STATUS       current
    DESCRIPTION
        "Cisco Firepower adaptor:MenloDcePortStatsHist:txPauseCFCDeltaMin
        managed object property"
    ::= { cfprAdaptorMenloDcePortStatsHistEntry 23 }

cfprAdaptorMenloDcePortStatsHistTxPausePFC OBJECT-TYPE
    SYNTAX       Unsigned64
    MAX-ACCESS   read-only
    STATUS       current
    DESCRIPTION
        "Cisco Firepower adaptor:MenloDcePortStatsHist:txPausePFC
        managed object property"
    ::= { cfprAdaptorMenloDcePortStatsHistEntry 24 }

cfprAdaptorMenloDcePortStatsHistTxPausePFCDelta OBJECT-TYPE
    SYNTAX       Unsigned64
    MAX-ACCESS   read-only
    STATUS       current
    DESCRIPTION
        "Cisco Firepower adaptor:MenloDcePortStatsHist:txPausePFCDelta
        managed object property"
    ::= { cfprAdaptorMenloDcePortStatsHistEntry 25 }

cfprAdaptorMenloDcePortStatsHistTxPausePFCDeltaAvg OBJECT-TYPE
    SYNTAX       Unsigned64
    MAX-ACCESS   read-only
    STATUS       current
    DESCRIPTION
        "Cisco Firepower adaptor:MenloDcePortStatsHist:txPausePFCDeltaAvg
        managed object property"
    ::= { cfprAdaptorMenloDcePortStatsHistEntry 26 }

cfprAdaptorMenloDcePortStatsHistTxPausePFCDeltaMax OBJECT-TYPE
    SYNTAX       Unsigned64
    MAX-ACCESS   read-only
    STATUS       current
    DESCRIPTION
        "Cisco Firepower adaptor:MenloDcePortStatsHist:txPausePFCDeltaMax
        managed object property"
    ::= { cfprAdaptorMenloDcePortStatsHistEntry 27 }

cfprAdaptorMenloDcePortStatsHistTxPausePFCDeltaMin OBJECT-TYPE
    SYNTAX       Unsigned64
    MAX-ACCESS   read-only
    STATUS       current
    DESCRIPTION
        "Cisco Firepower adaptor:MenloDcePortStatsHist:txPausePFCDeltaMin
        managed object property"
    ::= { cfprAdaptorMenloDcePortStatsHistEntry 28 }

cfprAdaptorMenloEthErrorStatsTable OBJECT-TYPE
    SYNTAX           SEQUENCE OF CfprAdaptorMenloEthErrorStatsEntry
    MAX-ACCESS       not-accessible
    STATUS           current
    DESCRIPTION
        "Cisco Firepower adaptor:MenloEthErrorStats managed object table"
    ::= { cfprAdaptorObjects 86 }

cfprAdaptorMenloEthErrorStatsEntry OBJECT-TYPE
    SYNTAX           CfprAdaptorMenloEthErrorStatsEntry
    MAX-ACCESS       not-accessible
    STATUS           current
    DESCRIPTION
        "Entry for the cfprAdaptorMenloEthErrorStatsTable table."
    INDEX { cfprAdaptorMenloEthErrorStatsInstanceId }
    ::= { cfprAdaptorMenloEthErrorStatsTable 1 }

CfprAdaptorMenloEthErrorStatsEntry ::= SEQUENCE {
    cfprAdaptorMenloEthErrorStatsInstanceId                          CfprManagedObjectId,
    cfprAdaptorMenloEthErrorStatsDn                                  CfprManagedObjectDn,
    cfprAdaptorMenloEthErrorStatsRn                                  SnmpAdminString,
    cfprAdaptorMenloEthErrorStatsCorrectableErrors                   Unsigned64,
    cfprAdaptorMenloEthErrorStatsCorrectableErrorsDelta              Counter64,
    cfprAdaptorMenloEthErrorStatsCorrectableErrorsDeltaAvg           Unsigned64,
    cfprAdaptorMenloEthErrorStatsCorrectableErrorsDeltaMax           Unsigned64,
    cfprAdaptorMenloEthErrorStatsCorrectableErrorsDeltaMin           Unsigned64,
    cfprAdaptorMenloEthErrorStatsDropAcl                             Unsigned64,
    cfprAdaptorMenloEthErrorStatsDropAclDelta                        Counter64,
    cfprAdaptorMenloEthErrorStatsDropAclDeltaAvg                     Unsigned64,
    cfprAdaptorMenloEthErrorStatsDropAclDeltaMax                     Unsigned64,
    cfprAdaptorMenloEthErrorStatsDropAclDeltaMin                     Unsigned64,
    cfprAdaptorMenloEthErrorStatsIntervals                           Gauge32,
    cfprAdaptorMenloEthErrorStatsMenloEthIndex                       CfprAdaptorMenloStatsIndex,
    cfprAdaptorMenloEthErrorStatsPopErrors                           Unsigned64,
    cfprAdaptorMenloEthErrorStatsPopErrorsDelta                      Counter64,
    cfprAdaptorMenloEthErrorStatsPopErrorsDeltaAvg                   Unsigned64,
    cfprAdaptorMenloEthErrorStatsPopErrorsDeltaMax                   Unsigned64,
    cfprAdaptorMenloEthErrorStatsPopErrorsDeltaMin                   Unsigned64,
    cfprAdaptorMenloEthErrorStatsPushErrors                          Unsigned64,
    cfprAdaptorMenloEthErrorStatsPushErrorsDelta                     Counter64,
    cfprAdaptorMenloEthErrorStatsPushErrorsDeltaAvg                  Unsigned64,
    cfprAdaptorMenloEthErrorStatsPushErrorsDeltaMax                  Unsigned64,
    cfprAdaptorMenloEthErrorStatsPushErrorsDeltaMin                  Unsigned64,
    cfprAdaptorMenloEthErrorStatsSuspect                             TruthValue,
    cfprAdaptorMenloEthErrorStatsThresholded                         CfprAdaptorMenloEthErrorStatsThresholded,
    cfprAdaptorMenloEthErrorStatsTimeCollected                       DateAndTime,
    cfprAdaptorMenloEthErrorStatsUncorrectableErrors                 Unsigned64,
    cfprAdaptorMenloEthErrorStatsUncorrectableErrorsDelta            Counter64,
    cfprAdaptorMenloEthErrorStatsUncorrectableErrorsDeltaAvg         Unsigned64,
    cfprAdaptorMenloEthErrorStatsUncorrectableErrorsDeltaMax         Unsigned64,
    cfprAdaptorMenloEthErrorStatsUncorrectableErrorsDeltaMin         Unsigned64,
    cfprAdaptorMenloEthErrorStatsUpdate                              Gauge32
}

cfprAdaptorMenloEthErrorStatsInstanceId OBJECT-TYPE
    SYNTAX       CfprManagedObjectId
    MAX-ACCESS   not-accessible
    STATUS       current
    DESCRIPTION
        "Instance identifier of the managed object."
    ::= { cfprAdaptorMenloEthErrorStatsEntry 1 }

cfprAdaptorMenloEthErrorStatsDn OBJECT-TYPE
    SYNTAX       CfprManagedObjectDn
    MAX-ACCESS   read-only
    STATUS       current
    DESCRIPTION
        "Cisco Firepower adaptor:MenloEthErrorStats:dn
        managed object property"
    ::= { cfprAdaptorMenloEthErrorStatsEntry 2 }

cfprAdaptorMenloEthErrorStatsRn OBJECT-TYPE
    SYNTAX       SnmpAdminString
    MAX-ACCESS   read-only
    STATUS       current
    DESCRIPTION
        "Cisco Firepower adaptor:MenloEthErrorStats:rn
        managed object property"
    ::= { cfprAdaptorMenloEthErrorStatsEntry 3 }

cfprAdaptorMenloEthErrorStatsCorrectableErrors OBJECT-TYPE
    SYNTAX       Unsigned64
    MAX-ACCESS   read-only
    STATUS       current
    DESCRIPTION
        "Cisco Firepower adaptor:MenloEthErrorStats:correctableErrors
        managed object property"
    ::= { cfprAdaptorMenloEthErrorStatsEntry 4 }

cfprAdaptorMenloEthErrorStatsCorrectableErrorsDelta OBJECT-TYPE
    SYNTAX       Counter64
    MAX-ACCESS   read-only
    STATUS       current
    DESCRIPTION
        "Cisco Firepower adaptor:MenloEthErrorStats:correctableErrorsDelta
         managed object property"
    ::= { cfprAdaptorMenloEthErrorStatsEntry 5 }

cfprAdaptorMenloEthErrorStatsCorrectableErrorsDeltaAvg OBJECT-TYPE
    SYNTAX       Unsigned64
    MAX-ACCESS   read-only
    STATUS       current
    DESCRIPTION
        "Cisco Firepower adaptor:MenloEthErrorStats:correctableErrorsDelta
        Avg managed object property"
    ::= { cfprAdaptorMenloEthErrorStatsEntry 6 }

cfprAdaptorMenloEthErrorStatsCorrectableErrorsDeltaMax OBJECT-TYPE
    SYNTAX       Unsigned64
    MAX-ACCESS   read-only
    STATUS       current
    DESCRIPTION
        "Cisco Firepower adaptor:MenloEthErrorStats:correctableErrorsDelta
        Max managed object property"
    ::= { cfprAdaptorMenloEthErrorStatsEntry 7 }

cfprAdaptorMenloEthErrorStatsCorrectableErrorsDeltaMin OBJECT-TYPE
    SYNTAX       Unsigned64
    MAX-ACCESS   read-only
    STATUS       current
    DESCRIPTION
        "Cisco Firepower adaptor:MenloEthErrorStats:correctableErrorsDelta
        Min managed object property"
    ::= { cfprAdaptorMenloEthErrorStatsEntry 8 }

cfprAdaptorMenloEthErrorStatsDropAcl OBJECT-TYPE
    SYNTAX       Unsigned64
    MAX-ACCESS   read-only
    STATUS       current
    DESCRIPTION
        "Cisco Firepower adaptor:MenloEthErrorStats:dropAcl
        managed object property"
    ::= { cfprAdaptorMenloEthErrorStatsEntry 9 }

cfprAdaptorMenloEthErrorStatsDropAclDelta OBJECT-TYPE
    SYNTAX       Counter64
    MAX-ACCESS   read-only
    STATUS       current
    DESCRIPTION
        "Cisco Firepower adaptor:MenloEthErrorStats:dropAclDelta
        managed object property"
    ::= { cfprAdaptorMenloEthErrorStatsEntry 10 }

cfprAdaptorMenloEthErrorStatsDropAclDeltaAvg OBJECT-TYPE
    SYNTAX       Unsigned64
    MAX-ACCESS   read-only
    STATUS       current
    DESCRIPTION
        "Cisco Firepower adaptor:MenloEthErrorStats:dropAclDeltaAvg
        managed object property"
    ::= { cfprAdaptorMenloEthErrorStatsEntry 11 }

cfprAdaptorMenloEthErrorStatsDropAclDeltaMax OBJECT-TYPE
    SYNTAX       Unsigned64
    MAX-ACCESS   read-only
    STATUS       current
    DESCRIPTION
        "Cisco Firepower adaptor:MenloEthErrorStats:dropAclDeltaMax
        managed object property"
    ::= { cfprAdaptorMenloEthErrorStatsEntry 12 }

cfprAdaptorMenloEthErrorStatsDropAclDeltaMin OBJECT-TYPE
    SYNTAX       Unsigned64
    MAX-ACCESS   read-only
    STATUS       current
    DESCRIPTION
        "Cisco Firepower adaptor:MenloEthErrorStats:dropAclDeltaMin
        managed object property"
    ::= { cfprAdaptorMenloEthErrorStatsEntry 13 }

cfprAdaptorMenloEthErrorStatsIntervals OBJECT-TYPE
    SYNTAX       Gauge32
    MAX-ACCESS   read-only
    STATUS       current
    DESCRIPTION
        "Cisco Firepower adaptor:MenloEthErrorStats:intervals
        managed object property"
    ::= { cfprAdaptorMenloEthErrorStatsEntry 14 }

cfprAdaptorMenloEthErrorStatsMenloEthIndex OBJECT-TYPE
    SYNTAX       CfprAdaptorMenloStatsIndex
    MAX-ACCESS   read-only
    STATUS       current
    DESCRIPTION
        "Cisco Firepower adaptor:MenloEthErrorStats:menloEthIndex
        managed object property"
    ::= { cfprAdaptorMenloEthErrorStatsEntry 15 }

cfprAdaptorMenloEthErrorStatsPopErrors OBJECT-TYPE
    SYNTAX       Unsigned64
    MAX-ACCESS   read-only
    STATUS       current
    DESCRIPTION
        "Cisco Firepower adaptor:MenloEthErrorStats:popErrors
        managed object property"
    ::= { cfprAdaptorMenloEthErrorStatsEntry 16 }

cfprAdaptorMenloEthErrorStatsPopErrorsDelta OBJECT-TYPE
    SYNTAX       Counter64
    MAX-ACCESS   read-only
    STATUS       current
    DESCRIPTION
        "Cisco Firepower adaptor:MenloEthErrorStats:popErrorsDelta
        managed object property"
    ::= { cfprAdaptorMenloEthErrorStatsEntry 17 }

cfprAdaptorMenloEthErrorStatsPopErrorsDeltaAvg OBJECT-TYPE
    SYNTAX       Unsigned64
    MAX-ACCESS   read-only
    STATUS       current
    DESCRIPTION
        "Cisco Firepower adaptor:MenloEthErrorStats:popErrorsDeltaAvg
        managed object property"
    ::= { cfprAdaptorMenloEthErrorStatsEntry 18 }

cfprAdaptorMenloEthErrorStatsPopErrorsDeltaMax OBJECT-TYPE
    SYNTAX       Unsigned64
    MAX-ACCESS   read-only
    STATUS       current
    DESCRIPTION
        "Cisco Firepower adaptor:MenloEthErrorStats:popErrorsDeltaMax
        managed object property"
    ::= { cfprAdaptorMenloEthErrorStatsEntry 19 }

cfprAdaptorMenloEthErrorStatsPopErrorsDeltaMin OBJECT-TYPE
    SYNTAX       Unsigned64
    MAX-ACCESS   read-only
    STATUS       current
    DESCRIPTION
        "Cisco Firepower adaptor:MenloEthErrorStats:popErrorsDeltaMin
        managed object property"
    ::= { cfprAdaptorMenloEthErrorStatsEntry 20 }

cfprAdaptorMenloEthErrorStatsPushErrors OBJECT-TYPE
    SYNTAX       Unsigned64
    MAX-ACCESS   read-only
    STATUS       current
    DESCRIPTION
        "Cisco Firepower adaptor:MenloEthErrorStats:pushErrors
        managed object property"
    ::= { cfprAdaptorMenloEthErrorStatsEntry 21 }

cfprAdaptorMenloEthErrorStatsPushErrorsDelta OBJECT-TYPE
    SYNTAX       Counter64
    MAX-ACCESS   read-only
    STATUS       current
    DESCRIPTION
        "Cisco Firepower adaptor:MenloEthErrorStats:pushErrorsDelta
        managed object property"
    ::= { cfprAdaptorMenloEthErrorStatsEntry 22 }

cfprAdaptorMenloEthErrorStatsPushErrorsDeltaAvg OBJECT-TYPE
    SYNTAX       Unsigned64
    MAX-ACCESS   read-only
    STATUS       current
    DESCRIPTION
        "Cisco Firepower adaptor:MenloEthErrorStats:pushErrorsDeltaAvg
        managed object property"
    ::= { cfprAdaptorMenloEthErrorStatsEntry 23 }

cfprAdaptorMenloEthErrorStatsPushErrorsDeltaMax OBJECT-TYPE
    SYNTAX       Unsigned64
    MAX-ACCESS   read-only
    STATUS       current
    DESCRIPTION
        "Cisco Firepower adaptor:MenloEthErrorStats:pushErrorsDeltaMax
        managed object property"
    ::= { cfprAdaptorMenloEthErrorStatsEntry 24 }

cfprAdaptorMenloEthErrorStatsPushErrorsDeltaMin OBJECT-TYPE
    SYNTAX       Unsigned64
    MAX-ACCESS   read-only
    STATUS       current
    DESCRIPTION
        "Cisco Firepower adaptor:MenloEthErrorStats:pushErrorsDeltaMin
        managed object property"
    ::= { cfprAdaptorMenloEthErrorStatsEntry 25 }

cfprAdaptorMenloEthErrorStatsSuspect OBJECT-TYPE
    SYNTAX       TruthValue
    MAX-ACCESS   read-only
    STATUS       current
    DESCRIPTION
        "Cisco Firepower adaptor:MenloEthErrorStats:suspect
        managed object property"
    ::= { cfprAdaptorMenloEthErrorStatsEntry 26 }

cfprAdaptorMenloEthErrorStatsThresholded OBJECT-TYPE
    SYNTAX       CfprAdaptorMenloEthErrorStatsThresholded
    MAX-ACCESS   read-only
    STATUS       current
    DESCRIPTION
        "Cisco Firepower adaptor:MenloEthErrorStats:thresholded
        managed object property"
    ::= { cfprAdaptorMenloEthErrorStatsEntry 27 }

cfprAdaptorMenloEthErrorStatsTimeCollected OBJECT-TYPE
    SYNTAX       DateAndTime
    MAX-ACCESS   read-only
    STATUS       current
    DESCRIPTION
        "Cisco Firepower adaptor:MenloEthErrorStats:timeCollected
        managed object property"
    ::= { cfprAdaptorMenloEthErrorStatsEntry 28 }

cfprAdaptorMenloEthErrorStatsUncorrectableErrors OBJECT-TYPE
    SYNTAX       Unsigned64
    MAX-ACCESS   read-only
    STATUS       current
    DESCRIPTION
        "Cisco Firepower adaptor:MenloEthErrorStats:uncorrectableErrors
        managed object property"
    ::= { cfprAdaptorMenloEthErrorStatsEntry 29 }

cfprAdaptorMenloEthErrorStatsUncorrectableErrorsDelta OBJECT-TYPE
    SYNTAX       Counter64
    MAX-ACCESS   read-only
    STATUS       current
    DESCRIPTION
        "Cisco Firepower adaptor:MenloEthErrorStats:uncorrectableErrorsDel
        ta managed object property"
    ::= { cfprAdaptorMenloEthErrorStatsEntry 30 }

cfprAdaptorMenloEthErrorStatsUncorrectableErrorsDeltaAvg OBJECT-TYPE
    SYNTAX       Unsigned64
    MAX-ACCESS   read-only
    STATUS       current
    DESCRIPTION
        "Cisco Firepower adaptor:MenloEthErrorStats:uncorrectableErrorsDel
        taAvg managed object property"
    ::= { cfprAdaptorMenloEthErrorStatsEntry 31 }

cfprAdaptorMenloEthErrorStatsUncorrectableErrorsDeltaMax OBJECT-TYPE
    SYNTAX       Unsigned64
    MAX-ACCESS   read-only
    STATUS       current
    DESCRIPTION
        "Cisco Firepower adaptor:MenloEthErrorStats:uncorrectableErrorsDel
        taMax managed object property"
    ::= { cfprAdaptorMenloEthErrorStatsEntry 32 }

cfprAdaptorMenloEthErrorStatsUncorrectableErrorsDeltaMin OBJECT-TYPE
    SYNTAX       Unsigned64
    MAX-ACCESS   read-only
    STATUS       current
    DESCRIPTION
        "Cisco Firepower adaptor:MenloEthErrorStats:uncorrectableErrorsDel
        taMin managed object property"
    ::= { cfprAdaptorMenloEthErrorStatsEntry 33 }

cfprAdaptorMenloEthErrorStatsUpdate OBJECT-TYPE
    SYNTAX       Gauge32
    MAX-ACCESS   read-only
    STATUS       current
    DESCRIPTION
        "Cisco Firepower adaptor:MenloEthErrorStats:update
        managed object property"
    ::= { cfprAdaptorMenloEthErrorStatsEntry 34 }

cfprAdaptorMenloEthErrorStatsHistTable OBJECT-TYPE
    SYNTAX           SEQUENCE OF CfprAdaptorMenloEthErrorStatsHistEntry
    MAX-ACCESS       not-accessible
    STATUS           current
    DESCRIPTION
        "Cisco Firepower adaptor:MenloEthErrorStatsHist
        managed object table"
    ::= { cfprAdaptorObjects 87 }

cfprAdaptorMenloEthErrorStatsHistEntry OBJECT-TYPE
    SYNTAX           CfprAdaptorMenloEthErrorStatsHistEntry
    MAX-ACCESS       not-accessible
    STATUS           current
    DESCRIPTION
        "Entry for the cfprAdaptorMenloEthErrorStatsHistTable table."
    INDEX { cfprAdaptorMenloEthErrorStatsHistInstanceId }
    ::= { cfprAdaptorMenloEthErrorStatsHistTable 1 }

CfprAdaptorMenloEthErrorStatsHistEntry ::= SEQUENCE {
    cfprAdaptorMenloEthErrorStatsHistInstanceId                      CfprManagedObjectId,
    cfprAdaptorMenloEthErrorStatsHistDn                              CfprManagedObjectDn,
    cfprAdaptorMenloEthErrorStatsHistRn                              SnmpAdminString,
    cfprAdaptorMenloEthErrorStatsHistCorrectableErrors               Unsigned64,
    cfprAdaptorMenloEthErrorStatsHistCorrectableErrorsDelta          Unsigned64,
    cfprAdaptorMenloEthErrorStatsHistCorrectableErrorsDeltaAvg       Unsigned64,
    cfprAdaptorMenloEthErrorStatsHistCorrectableErrorsDeltaMax       Unsigned64,
    cfprAdaptorMenloEthErrorStatsHistCorrectableErrorsDeltaMin       Unsigned64,
    cfprAdaptorMenloEthErrorStatsHistDropAcl                         Unsigned64,
    cfprAdaptorMenloEthErrorStatsHistDropAclDelta                    Unsigned64,
    cfprAdaptorMenloEthErrorStatsHistDropAclDeltaAvg                 Unsigned64,
    cfprAdaptorMenloEthErrorStatsHistDropAclDeltaMax                 Unsigned64,
    cfprAdaptorMenloEthErrorStatsHistDropAclDeltaMin                 Unsigned64,
    cfprAdaptorMenloEthErrorStatsHistId                              Unsigned64,
    cfprAdaptorMenloEthErrorStatsHistMostRecent                      TruthValue,
    cfprAdaptorMenloEthErrorStatsHistPopErrors                       Unsigned64,
    cfprAdaptorMenloEthErrorStatsHistPopErrorsDelta                  Unsigned64,
    cfprAdaptorMenloEthErrorStatsHistPopErrorsDeltaAvg               Unsigned64,
    cfprAdaptorMenloEthErrorStatsHistPopErrorsDeltaMax               Unsigned64,
    cfprAdaptorMenloEthErrorStatsHistPopErrorsDeltaMin               Unsigned64,
    cfprAdaptorMenloEthErrorStatsHistPushErrors                      Unsigned64,
    cfprAdaptorMenloEthErrorStatsHistPushErrorsDelta                 Unsigned64,
    cfprAdaptorMenloEthErrorStatsHistPushErrorsDeltaAvg              Unsigned64,
    cfprAdaptorMenloEthErrorStatsHistPushErrorsDeltaMax              Unsigned64,
    cfprAdaptorMenloEthErrorStatsHistPushErrorsDeltaMin              Unsigned64,
    cfprAdaptorMenloEthErrorStatsHistSuspect                         TruthValue,
    cfprAdaptorMenloEthErrorStatsHistThresholded                     CfprAdaptorMenloEthErrorStatsHistThresholded,
    cfprAdaptorMenloEthErrorStatsHistTimeCollected                   DateAndTime,
    cfprAdaptorMenloEthErrorStatsHistUncorrectableErrors             Unsigned64,
    cfprAdaptorMenloEthErrorStatsHistUncorrectableErrorsDelta        Unsigned64,
    cfprAdaptorMenloEthErrorStatsHistUncorrectableErrorsDeltaAvg     Unsigned64,
    cfprAdaptorMenloEthErrorStatsHistUncorrectableErrorsDeltaMax     Unsigned64,
    cfprAdaptorMenloEthErrorStatsHistUncorrectableErrorsDeltaMin     Unsigned64
}

cfprAdaptorMenloEthErrorStatsHistInstanceId OBJECT-TYPE
    SYNTAX       CfprManagedObjectId
    MAX-ACCESS   not-accessible
    STATUS       current
    DESCRIPTION
        "Instance identifier of the managed object."
    ::= { cfprAdaptorMenloEthErrorStatsHistEntry 1 }

cfprAdaptorMenloEthErrorStatsHistDn OBJECT-TYPE
    SYNTAX       CfprManagedObjectDn
    MAX-ACCESS   read-only
    STATUS       current
    DESCRIPTION
        "Cisco Firepower adaptor:MenloEthErrorStatsHist:dn
        managed object property"
    ::= { cfprAdaptorMenloEthErrorStatsHistEntry 2 }

cfprAdaptorMenloEthErrorStatsHistRn OBJECT-TYPE
    SYNTAX       SnmpAdminString
    MAX-ACCESS   read-only
    STATUS       current
    DESCRIPTION
        "Cisco Firepower adaptor:MenloEthErrorStatsHist:rn
        managed object property"
    ::= { cfprAdaptorMenloEthErrorStatsHistEntry 3 }

cfprAdaptorMenloEthErrorStatsHistCorrectableErrors OBJECT-TYPE
    SYNTAX       Unsigned64
    MAX-ACCESS   read-only
    STATUS       current
    DESCRIPTION
        "Cisco Firepower adaptor:MenloEthErrorStatsHist:correctableErrors
        managed object property"
    ::= { cfprAdaptorMenloEthErrorStatsHistEntry 4 }

cfprAdaptorMenloEthErrorStatsHistCorrectableErrorsDelta OBJECT-TYPE
    SYNTAX       Unsigned64
    MAX-ACCESS   read-only
    STATUS       current
    DESCRIPTION
        "Cisco Firepower adaptor:MenloEthErrorStatsHist:correctableErrorsD
        elta managed object property"
    ::= { cfprAdaptorMenloEthErrorStatsHistEntry 5 }

cfprAdaptorMenloEthErrorStatsHistCorrectableErrorsDeltaAvg OBJECT-TYPE
    SYNTAX       Unsigned64
    MAX-ACCESS   read-only
    STATUS       current
    DESCRIPTION
        "Cisco Firepower adaptor:MenloEthErrorStatsHist:correctableErrorsD
        eltaAvg managed object property"
    ::= { cfprAdaptorMenloEthErrorStatsHistEntry 6 }

cfprAdaptorMenloEthErrorStatsHistCorrectableErrorsDeltaMax OBJECT-TYPE
    SYNTAX       Unsigned64
    MAX-ACCESS   read-only
    STATUS       current
    DESCRIPTION
        "Cisco Firepower adaptor:MenloEthErrorStatsHist:correctableErrorsD
        eltaMax managed object property"
    ::= { cfprAdaptorMenloEthErrorStatsHistEntry 7 }

cfprAdaptorMenloEthErrorStatsHistCorrectableErrorsDeltaMin OBJECT-TYPE
    SYNTAX       Unsigned64
    MAX-ACCESS   read-only
    STATUS       current
    DESCRIPTION
        "Cisco Firepower adaptor:MenloEthErrorStatsHist:correctableErrorsD
        eltaMin managed object property"
    ::= { cfprAdaptorMenloEthErrorStatsHistEntry 8 }

cfprAdaptorMenloEthErrorStatsHistDropAcl OBJECT-TYPE
    SYNTAX       Unsigned64
    MAX-ACCESS   read-only
    STATUS       current
    DESCRIPTION
        "Cisco Firepower adaptor:MenloEthErrorStatsHist:dropAcl
        managed object property"
    ::= { cfprAdaptorMenloEthErrorStatsHistEntry 9 }

cfprAdaptorMenloEthErrorStatsHistDropAclDelta OBJECT-TYPE
    SYNTAX       Unsigned64
    MAX-ACCESS   read-only
    STATUS       current
    DESCRIPTION
        "Cisco Firepower adaptor:MenloEthErrorStatsHist:dropAclDelta
        managed object property"
    ::= { cfprAdaptorMenloEthErrorStatsHistEntry 10 }

cfprAdaptorMenloEthErrorStatsHistDropAclDeltaAvg OBJECT-TYPE
    SYNTAX       Unsigned64
    MAX-ACCESS   read-only
    STATUS       current
    DESCRIPTION
        "Cisco Firepower adaptor:MenloEthErrorStatsHist:dropAclDeltaAvg
        managed object property"
    ::= { cfprAdaptorMenloEthErrorStatsHistEntry 11 }

cfprAdaptorMenloEthErrorStatsHistDropAclDeltaMax OBJECT-TYPE
    SYNTAX       Unsigned64
    MAX-ACCESS   read-only
    STATUS       current
    DESCRIPTION
        "Cisco Firepower adaptor:MenloEthErrorStatsHist:dropAclDeltaMax
        managed object property"
    ::= { cfprAdaptorMenloEthErrorStatsHistEntry 12 }

cfprAdaptorMenloEthErrorStatsHistDropAclDeltaMin OBJECT-TYPE
    SYNTAX       Unsigned64
    MAX-ACCESS   read-only
    STATUS       current
    DESCRIPTION
        "Cisco Firepower adaptor:MenloEthErrorStatsHist:dropAclDeltaMin
        managed object property"
    ::= { cfprAdaptorMenloEthErrorStatsHistEntry 13 }

cfprAdaptorMenloEthErrorStatsHistId OBJECT-TYPE
    SYNTAX       Unsigned64
    MAX-ACCESS   read-only
    STATUS       current
    DESCRIPTION
        "Cisco Firepower adaptor:MenloEthErrorStatsHist:id
        managed object property"
    ::= { cfprAdaptorMenloEthErrorStatsHistEntry 14 }

cfprAdaptorMenloEthErrorStatsHistMostRecent OBJECT-TYPE
    SYNTAX       TruthValue
    MAX-ACCESS   read-only
    STATUS       current
    DESCRIPTION
        "Cisco Firepower adaptor:MenloEthErrorStatsHist:mostRecent
        managed object property"
    ::= { cfprAdaptorMenloEthErrorStatsHistEntry 15 }

cfprAdaptorMenloEthErrorStatsHistPopErrors OBJECT-TYPE
    SYNTAX       Unsigned64
    MAX-ACCESS   read-only
    STATUS       current
    DESCRIPTION
        "Cisco Firepower adaptor:MenloEthErrorStatsHist:popErrors
        managed object property"
    ::= { cfprAdaptorMenloEthErrorStatsHistEntry 16 }

cfprAdaptorMenloEthErrorStatsHistPopErrorsDelta OBJECT-TYPE
    SYNTAX       Unsigned64
    MAX-ACCESS   read-only
    STATUS       current
    DESCRIPTION
        "Cisco Firepower adaptor:MenloEthErrorStatsHist:popErrorsDelta
        managed object property"
    ::= { cfprAdaptorMenloEthErrorStatsHistEntry 17 }

cfprAdaptorMenloEthErrorStatsHistPopErrorsDeltaAvg OBJECT-TYPE
    SYNTAX       Unsigned64
    MAX-ACCESS   read-only
    STATUS       current
    DESCRIPTION
        "Cisco Firepower adaptor:MenloEthErrorStatsHist:popErrorsDeltaAvg
        managed object property"
    ::= { cfprAdaptorMenloEthErrorStatsHistEntry 18 }

cfprAdaptorMenloEthErrorStatsHistPopErrorsDeltaMax OBJECT-TYPE
    SYNTAX       Unsigned64
    MAX-ACCESS   read-only
    STATUS       current
    DESCRIPTION
        "Cisco Firepower adaptor:MenloEthErrorStatsHist:popErrorsDeltaMax
        managed object property"
    ::= { cfprAdaptorMenloEthErrorStatsHistEntry 19 }

cfprAdaptorMenloEthErrorStatsHistPopErrorsDeltaMin OBJECT-TYPE
    SYNTAX       Unsigned64
    MAX-ACCESS   read-only
    STATUS       current
    DESCRIPTION
        "Cisco Firepower adaptor:MenloEthErrorStatsHist:popErrorsDeltaMin
        managed object property"
    ::= { cfprAdaptorMenloEthErrorStatsHistEntry 20 }

cfprAdaptorMenloEthErrorStatsHistPushErrors OBJECT-TYPE
    SYNTAX       Unsigned64
    MAX-ACCESS   read-only
    STATUS       current
    DESCRIPTION
        "Cisco Firepower adaptor:MenloEthErrorStatsHist:pushErrors
        managed object property"
    ::= { cfprAdaptorMenloEthErrorStatsHistEntry 21 }

cfprAdaptorMenloEthErrorStatsHistPushErrorsDelta OBJECT-TYPE
    SYNTAX       Unsigned64
    MAX-ACCESS   read-only
    STATUS       current
    DESCRIPTION
        "Cisco Firepower adaptor:MenloEthErrorStatsHist:pushErrorsDelta
        managed object property"
    ::= { cfprAdaptorMenloEthErrorStatsHistEntry 22 }

cfprAdaptorMenloEthErrorStatsHistPushErrorsDeltaAvg OBJECT-TYPE
    SYNTAX       Unsigned64
    MAX-ACCESS   read-only
    STATUS       current
    DESCRIPTION
        "Cisco Firepower adaptor:MenloEthErrorStatsHist:pushErrorsDeltaAvg
         managed object property"
    ::= { cfprAdaptorMenloEthErrorStatsHistEntry 23 }

cfprAdaptorMenloEthErrorStatsHistPushErrorsDeltaMax OBJECT-TYPE
    SYNTAX       Unsigned64
    MAX-ACCESS   read-only
    STATUS       current
    DESCRIPTION
        "Cisco Firepower adaptor:MenloEthErrorStatsHist:pushErrorsDeltaMax
         managed object property"
    ::= { cfprAdaptorMenloEthErrorStatsHistEntry 24 }

cfprAdaptorMenloEthErrorStatsHistPushErrorsDeltaMin OBJECT-TYPE
    SYNTAX       Unsigned64
    MAX-ACCESS   read-only
    STATUS       current
    DESCRIPTION
        "Cisco Firepower adaptor:MenloEthErrorStatsHist:pushErrorsDeltaMin
         managed object property"
    ::= { cfprAdaptorMenloEthErrorStatsHistEntry 25 }

cfprAdaptorMenloEthErrorStatsHistSuspect OBJECT-TYPE
    SYNTAX       TruthValue
    MAX-ACCESS   read-only
    STATUS       current
    DESCRIPTION
        "Cisco Firepower adaptor:MenloEthErrorStatsHist:suspect
        managed object property"
    ::= { cfprAdaptorMenloEthErrorStatsHistEntry 26 }

cfprAdaptorMenloEthErrorStatsHistThresholded OBJECT-TYPE
    SYNTAX       CfprAdaptorMenloEthErrorStatsHistThresholded
    MAX-ACCESS   read-only
    STATUS       current
    DESCRIPTION
        "Cisco Firepower adaptor:MenloEthErrorStatsHist:thresholded
        managed object property"
    ::= { cfprAdaptorMenloEthErrorStatsHistEntry 27 }

cfprAdaptorMenloEthErrorStatsHistTimeCollected OBJECT-TYPE
    SYNTAX       DateAndTime
    MAX-ACCESS   read-only
    STATUS       current
    DESCRIPTION
        "Cisco Firepower adaptor:MenloEthErrorStatsHist:timeCollected
        managed object property"
    ::= { cfprAdaptorMenloEthErrorStatsHistEntry 28 }

cfprAdaptorMenloEthErrorStatsHistUncorrectableErrors OBJECT-TYPE
    SYNTAX       Unsigned64
    MAX-ACCESS   read-only
    STATUS       current
    DESCRIPTION
        "Cisco Firepower adaptor:MenloEthErrorStatsHist:uncorrectableError
        s managed object property"
    ::= { cfprAdaptorMenloEthErrorStatsHistEntry 29 }

cfprAdaptorMenloEthErrorStatsHistUncorrectableErrorsDelta OBJECT-TYPE
    SYNTAX       Unsigned64
    MAX-ACCESS   read-only
    STATUS       current
    DESCRIPTION
        "Cisco Firepower adaptor:MenloEthErrorStatsHist:uncorrectableError
        sDelta managed object property"
    ::= { cfprAdaptorMenloEthErrorStatsHistEntry 30 }

cfprAdaptorMenloEthErrorStatsHistUncorrectableErrorsDeltaAvg OBJECT-TYPE
    SYNTAX       Unsigned64
    MAX-ACCESS   read-only
    STATUS       current
    DESCRIPTION
        "Cisco Firepower adaptor:MenloEthErrorStatsHist:uncorrectableError
        sDeltaAvg managed object property"
    ::= { cfprAdaptorMenloEthErrorStatsHistEntry 31 }

cfprAdaptorMenloEthErrorStatsHistUncorrectableErrorsDeltaMax OBJECT-TYPE
    SYNTAX       Unsigned64
    MAX-ACCESS   read-only
    STATUS       current
    DESCRIPTION
        "Cisco Firepower adaptor:MenloEthErrorStatsHist:uncorrectableError
        sDeltaMax managed object property"
    ::= { cfprAdaptorMenloEthErrorStatsHistEntry 32 }

cfprAdaptorMenloEthErrorStatsHistUncorrectableErrorsDeltaMin OBJECT-TYPE
    SYNTAX       Unsigned64
    MAX-ACCESS   read-only
    STATUS       current
    DESCRIPTION
        "Cisco Firepower adaptor:MenloEthErrorStatsHist:uncorrectableError
        sDeltaMin managed object property"
    ::= { cfprAdaptorMenloEthErrorStatsHistEntry 33 }

cfprAdaptorMenloEthStatsTable OBJECT-TYPE
    SYNTAX           SEQUENCE OF CfprAdaptorMenloEthStatsEntry
    MAX-ACCESS       not-accessible
    STATUS           current
    DESCRIPTION
        "Cisco Firepower adaptor:MenloEthStats managed object table"
    ::= { cfprAdaptorObjects 88 }

cfprAdaptorMenloEthStatsEntry OBJECT-TYPE
    SYNTAX           CfprAdaptorMenloEthStatsEntry
    MAX-ACCESS       not-accessible
    STATUS           current
    DESCRIPTION
        "Entry for the cfprAdaptorMenloEthStatsTable table."
    INDEX { cfprAdaptorMenloEthStatsInstanceId }
    ::= { cfprAdaptorMenloEthStatsTable 1 }

CfprAdaptorMenloEthStatsEntry ::= SEQUENCE {
    cfprAdaptorMenloEthStatsInstanceId                               CfprManagedObjectId,
    cfprAdaptorMenloEthStatsDn                                       CfprManagedObjectDn,
    cfprAdaptorMenloEthStatsRn                                       SnmpAdminString,
    cfprAdaptorMenloEthStatsDropOverrun                              Unsigned64,
    cfprAdaptorMenloEthStatsDropOverrunDelta                         Counter64,
    cfprAdaptorMenloEthStatsDropOverrunDeltaAvg                      Unsigned64,
    cfprAdaptorMenloEthStatsDropOverrunDeltaMax                      Unsigned64,
    cfprAdaptorMenloEthStatsDropOverrunDeltaMin                      Unsigned64,
    cfprAdaptorMenloEthStatsDropRunt                                 Unsigned64,
    cfprAdaptorMenloEthStatsDropRuntDelta                            Counter64,
    cfprAdaptorMenloEthStatsDropRuntDeltaAvg                         Unsigned64,
    cfprAdaptorMenloEthStatsDropRuntDeltaMax                         Unsigned64,
    cfprAdaptorMenloEthStatsDropRuntDeltaMin                         Unsigned64,
    cfprAdaptorMenloEthStatsIntervals                                Gauge32,
    cfprAdaptorMenloEthStatsMenloEthIndex                            CfprAdaptorMenloStatsIndex,
    cfprAdaptorMenloEthStatsSuspect                                  TruthValue,
    cfprAdaptorMenloEthStatsThresholded                              CfprAdaptorMenloEthStatsThresholded,
    cfprAdaptorMenloEthStatsTimeCollected                            DateAndTime,
    cfprAdaptorMenloEthStatsTruncateOverrun                          Unsigned64,
    cfprAdaptorMenloEthStatsTruncateOverrunDelta                     Counter64,
    cfprAdaptorMenloEthStatsTruncateOverrunDeltaAvg                  Unsigned64,
    cfprAdaptorMenloEthStatsTruncateOverrunDeltaMax                  Unsigned64,
    cfprAdaptorMenloEthStatsTruncateOverrunDeltaMin                  Unsigned64,
    cfprAdaptorMenloEthStatsUpdate                                   Gauge32
}

cfprAdaptorMenloEthStatsInstanceId OBJECT-TYPE
    SYNTAX       CfprManagedObjectId
    MAX-ACCESS   not-accessible
    STATUS       current
    DESCRIPTION
        "Instance identifier of the managed object."
    ::= { cfprAdaptorMenloEthStatsEntry 1 }

cfprAdaptorMenloEthStatsDn OBJECT-TYPE
    SYNTAX       CfprManagedObjectDn
    MAX-ACCESS   read-only
    STATUS       current
    DESCRIPTION
        "Cisco Firepower adaptor:MenloEthStats:dn managed object property"
    ::= { cfprAdaptorMenloEthStatsEntry 2 }

cfprAdaptorMenloEthStatsRn OBJECT-TYPE
    SYNTAX       SnmpAdminString
    MAX-ACCESS   read-only
    STATUS       current
    DESCRIPTION
        "Cisco Firepower adaptor:MenloEthStats:rn managed object property"
    ::= { cfprAdaptorMenloEthStatsEntry 3 }

cfprAdaptorMenloEthStatsDropOverrun OBJECT-TYPE
    SYNTAX       Unsigned64
    MAX-ACCESS   read-only
    STATUS       current
    DESCRIPTION
        "Cisco Firepower adaptor:MenloEthStats:dropOverrun
        managed object property"
    ::= { cfprAdaptorMenloEthStatsEntry 4 }

cfprAdaptorMenloEthStatsDropOverrunDelta OBJECT-TYPE
    SYNTAX       Counter64
    MAX-ACCESS   read-only
    STATUS       current
    DESCRIPTION
        "Cisco Firepower adaptor:MenloEthStats:dropOverrunDelta
        managed object property"
    ::= { cfprAdaptorMenloEthStatsEntry 5 }

cfprAdaptorMenloEthStatsDropOverrunDeltaAvg OBJECT-TYPE
    SYNTAX       Unsigned64
    MAX-ACCESS   read-only
    STATUS       current
    DESCRIPTION
        "Cisco Firepower adaptor:MenloEthStats:dropOverrunDeltaAvg
        managed object property"
    ::= { cfprAdaptorMenloEthStatsEntry 6 }

cfprAdaptorMenloEthStatsDropOverrunDeltaMax OBJECT-TYPE
    SYNTAX       Unsigned64
    MAX-ACCESS   read-only
    STATUS       current
    DESCRIPTION
        "Cisco Firepower adaptor:MenloEthStats:dropOverrunDeltaMax
        managed object property"
    ::= { cfprAdaptorMenloEthStatsEntry 7 }

cfprAdaptorMenloEthStatsDropOverrunDeltaMin OBJECT-TYPE
    SYNTAX       Unsigned64
    MAX-ACCESS   read-only
    STATUS       current
    DESCRIPTION
        "Cisco Firepower adaptor:MenloEthStats:dropOverrunDeltaMin
        managed object property"
    ::= { cfprAdaptorMenloEthStatsEntry 8 }

cfprAdaptorMenloEthStatsDropRunt OBJECT-TYPE
    SYNTAX       Unsigned64
    MAX-ACCESS   read-only
    STATUS       current
    DESCRIPTION
        "Cisco Firepower adaptor:MenloEthStats:dropRunt
        managed object property"
    ::= { cfprAdaptorMenloEthStatsEntry 9 }

cfprAdaptorMenloEthStatsDropRuntDelta OBJECT-TYPE
    SYNTAX       Counter64
    MAX-ACCESS   read-only
    STATUS       current
    DESCRIPTION
        "Cisco Firepower adaptor:MenloEthStats:dropRuntDelta
        managed object property"
    ::= { cfprAdaptorMenloEthStatsEntry 10 }

cfprAdaptorMenloEthStatsDropRuntDeltaAvg OBJECT-TYPE
    SYNTAX       Unsigned64
    MAX-ACCESS   read-only
    STATUS       current
    DESCRIPTION
        "Cisco Firepower adaptor:MenloEthStats:dropRuntDeltaAvg
        managed object property"
    ::= { cfprAdaptorMenloEthStatsEntry 11 }

cfprAdaptorMenloEthStatsDropRuntDeltaMax OBJECT-TYPE
    SYNTAX       Unsigned64
    MAX-ACCESS   read-only
    STATUS       current
    DESCRIPTION
        "Cisco Firepower adaptor:MenloEthStats:dropRuntDeltaMax
        managed object property"
    ::= { cfprAdaptorMenloEthStatsEntry 12 }

cfprAdaptorMenloEthStatsDropRuntDeltaMin OBJECT-TYPE
    SYNTAX       Unsigned64
    MAX-ACCESS   read-only
    STATUS       current
    DESCRIPTION
        "Cisco Firepower adaptor:MenloEthStats:dropRuntDeltaMin
        managed object property"
    ::= { cfprAdaptorMenloEthStatsEntry 13 }

cfprAdaptorMenloEthStatsIntervals OBJECT-TYPE
    SYNTAX       Gauge32
    MAX-ACCESS   read-only
    STATUS       current
    DESCRIPTION
        "Cisco Firepower adaptor:MenloEthStats:intervals
        managed object property"
    ::= { cfprAdaptorMenloEthStatsEntry 14 }

cfprAdaptorMenloEthStatsMenloEthIndex OBJECT-TYPE
    SYNTAX       CfprAdaptorMenloStatsIndex
    MAX-ACCESS   read-only
    STATUS       current
    DESCRIPTION
        "Cisco Firepower adaptor:MenloEthStats:menloEthIndex
        managed object property"
    ::= { cfprAdaptorMenloEthStatsEntry 15 }

cfprAdaptorMenloEthStatsSuspect OBJECT-TYPE
    SYNTAX       TruthValue
    MAX-ACCESS   read-only
    STATUS       current
    DESCRIPTION
        "Cisco Firepower adaptor:MenloEthStats:suspect
        managed object property"
    ::= { cfprAdaptorMenloEthStatsEntry 16 }

cfprAdaptorMenloEthStatsThresholded OBJECT-TYPE
    SYNTAX       CfprAdaptorMenloEthStatsThresholded
    MAX-ACCESS   read-only
    STATUS       current
    DESCRIPTION
        "Cisco Firepower adaptor:MenloEthStats:thresholded
        managed object property"
    ::= { cfprAdaptorMenloEthStatsEntry 17 }

cfprAdaptorMenloEthStatsTimeCollected OBJECT-TYPE
    SYNTAX       DateAndTime
    MAX-ACCESS   read-only
    STATUS       current
    DESCRIPTION
        "Cisco Firepower adaptor:MenloEthStats:timeCollected
        managed object property"
    ::= { cfprAdaptorMenloEthStatsEntry 18 }

cfprAdaptorMenloEthStatsTruncateOverrun OBJECT-TYPE
    SYNTAX       Unsigned64
    MAX-ACCESS   read-only
    STATUS       current
    DESCRIPTION
        "Cisco Firepower adaptor:MenloEthStats:truncateOverrun
        managed object property"
    ::= { cfprAdaptorMenloEthStatsEntry 19 }

cfprAdaptorMenloEthStatsTruncateOverrunDelta OBJECT-TYPE
    SYNTAX       Counter64
    MAX-ACCESS   read-only
    STATUS       current
    DESCRIPTION
        "Cisco Firepower adaptor:MenloEthStats:truncateOverrunDelta
        managed object property"
    ::= { cfprAdaptorMenloEthStatsEntry 20 }

cfprAdaptorMenloEthStatsTruncateOverrunDeltaAvg OBJECT-TYPE
    SYNTAX       Unsigned64
    MAX-ACCESS   read-only
    STATUS       current
    DESCRIPTION
        "Cisco Firepower adaptor:MenloEthStats:truncateOverrunDeltaAvg
        managed object property"
    ::= { cfprAdaptorMenloEthStatsEntry 21 }

cfprAdaptorMenloEthStatsTruncateOverrunDeltaMax OBJECT-TYPE
    SYNTAX       Unsigned64
    MAX-ACCESS   read-only
    STATUS       current
    DESCRIPTION
        "Cisco Firepower adaptor:MenloEthStats:truncateOverrunDeltaMax
        managed object property"
    ::= { cfprAdaptorMenloEthStatsEntry 22 }

cfprAdaptorMenloEthStatsTruncateOverrunDeltaMin OBJECT-TYPE
    SYNTAX       Unsigned64
    MAX-ACCESS   read-only
    STATUS       current
    DESCRIPTION
        "Cisco Firepower adaptor:MenloEthStats:truncateOverrunDeltaMin
        managed object property"
    ::= { cfprAdaptorMenloEthStatsEntry 23 }

cfprAdaptorMenloEthStatsUpdate OBJECT-TYPE
    SYNTAX       Gauge32
    MAX-ACCESS   read-only
    STATUS       current
    DESCRIPTION
        "Cisco Firepower adaptor:MenloEthStats:update managed
        object property"
    ::= { cfprAdaptorMenloEthStatsEntry 24 }

cfprAdaptorMenloEthStatsHistTable OBJECT-TYPE
    SYNTAX           SEQUENCE OF CfprAdaptorMenloEthStatsHistEntry
    MAX-ACCESS       not-accessible
    STATUS           current
    DESCRIPTION
        "Cisco Firepower adaptor:MenloEthStatsHist managed object table"
    ::= { cfprAdaptorObjects 89 }

cfprAdaptorMenloEthStatsHistEntry OBJECT-TYPE
    SYNTAX           CfprAdaptorMenloEthStatsHistEntry
    MAX-ACCESS       not-accessible
    STATUS           current
    DESCRIPTION
        "Entry for the cfprAdaptorMenloEthStatsHistTable table."
    INDEX { cfprAdaptorMenloEthStatsHistInstanceId }
    ::= { cfprAdaptorMenloEthStatsHistTable 1 }

CfprAdaptorMenloEthStatsHistEntry ::= SEQUENCE {
    cfprAdaptorMenloEthStatsHistInstanceId                           CfprManagedObjectId,
    cfprAdaptorMenloEthStatsHistDn                                   CfprManagedObjectDn,
    cfprAdaptorMenloEthStatsHistRn                                   SnmpAdminString,
    cfprAdaptorMenloEthStatsHistDropOverrun                          Unsigned64,
    cfprAdaptorMenloEthStatsHistDropOverrunDelta                     Unsigned64,
    cfprAdaptorMenloEthStatsHistDropOverrunDeltaAvg                  Unsigned64,
    cfprAdaptorMenloEthStatsHistDropOverrunDeltaMax                  Unsigned64,
    cfprAdaptorMenloEthStatsHistDropOverrunDeltaMin                  Unsigned64,
    cfprAdaptorMenloEthStatsHistDropRunt                             Unsigned64,
    cfprAdaptorMenloEthStatsHistDropRuntDelta                        Unsigned64,
    cfprAdaptorMenloEthStatsHistDropRuntDeltaAvg                     Unsigned64,
    cfprAdaptorMenloEthStatsHistDropRuntDeltaMax                     Unsigned64,
    cfprAdaptorMenloEthStatsHistDropRuntDeltaMin                     Unsigned64,
    cfprAdaptorMenloEthStatsHistId                                   Unsigned64,
    cfprAdaptorMenloEthStatsHistMostRecent                           TruthValue,
    cfprAdaptorMenloEthStatsHistSuspect                              TruthValue,
    cfprAdaptorMenloEthStatsHistThresholded                          CfprAdaptorMenloEthStatsHistThresholded,
    cfprAdaptorMenloEthStatsHistTimeCollected                        DateAndTime,
    cfprAdaptorMenloEthStatsHistTruncateOverrun                      Unsigned64,
    cfprAdaptorMenloEthStatsHistTruncateOverrunDelta                 Unsigned64,
    cfprAdaptorMenloEthStatsHistTruncateOverrunDeltaAvg              Unsigned64,
    cfprAdaptorMenloEthStatsHistTruncateOverrunDeltaMax              Unsigned64,
    cfprAdaptorMenloEthStatsHistTruncateOverrunDeltaMin              Unsigned64
}

cfprAdaptorMenloEthStatsHistInstanceId OBJECT-TYPE
    SYNTAX       CfprManagedObjectId
    MAX-ACCESS   not-accessible
    STATUS       current
    DESCRIPTION
        "Instance identifier of the managed object."
    ::= { cfprAdaptorMenloEthStatsHistEntry 1 }

cfprAdaptorMenloEthStatsHistDn OBJECT-TYPE
    SYNTAX       CfprManagedObjectDn
    MAX-ACCESS   read-only
    STATUS       current
    DESCRIPTION
        "Cisco Firepower adaptor:MenloEthStatsHist:dn managed
        object property"
    ::= { cfprAdaptorMenloEthStatsHistEntry 2 }

cfprAdaptorMenloEthStatsHistRn OBJECT-TYPE
    SYNTAX       SnmpAdminString
    MAX-ACCESS   read-only
    STATUS       current
    DESCRIPTION
        "Cisco Firepower adaptor:MenloEthStatsHist:rn managed
        object property"
    ::= { cfprAdaptorMenloEthStatsHistEntry 3 }

cfprAdaptorMenloEthStatsHistDropOverrun OBJECT-TYPE
    SYNTAX       Unsigned64
    MAX-ACCESS   read-only
    STATUS       current
    DESCRIPTION
        "Cisco Firepower adaptor:MenloEthStatsHist:dropOverrun
        managed object property"
    ::= { cfprAdaptorMenloEthStatsHistEntry 4 }

cfprAdaptorMenloEthStatsHistDropOverrunDelta OBJECT-TYPE
    SYNTAX       Unsigned64
    MAX-ACCESS   read-only
    STATUS       current
    DESCRIPTION
        "Cisco Firepower adaptor:MenloEthStatsHist:dropOverrunDelta
        managed object property"
    ::= { cfprAdaptorMenloEthStatsHistEntry 5 }

cfprAdaptorMenloEthStatsHistDropOverrunDeltaAvg OBJECT-TYPE
    SYNTAX       Unsigned64
    MAX-ACCESS   read-only
    STATUS       current
    DESCRIPTION
        "Cisco Firepower adaptor:MenloEthStatsHist:dropOverrunDeltaAvg
        managed object property"
    ::= { cfprAdaptorMenloEthStatsHistEntry 6 }

cfprAdaptorMenloEthStatsHistDropOverrunDeltaMax OBJECT-TYPE
    SYNTAX       Unsigned64
    MAX-ACCESS   read-only
    STATUS       current
    DESCRIPTION
        "Cisco Firepower adaptor:MenloEthStatsHist:dropOverrunDeltaMax
        managed object property"
    ::= { cfprAdaptorMenloEthStatsHistEntry 7 }

cfprAdaptorMenloEthStatsHistDropOverrunDeltaMin OBJECT-TYPE
    SYNTAX       Unsigned64
    MAX-ACCESS   read-only
    STATUS       current
    DESCRIPTION
        "Cisco Firepower adaptor:MenloEthStatsHist:dropOverrunDeltaMin
        managed object property"
    ::= { cfprAdaptorMenloEthStatsHistEntry 8 }

cfprAdaptorMenloEthStatsHistDropRunt OBJECT-TYPE
    SYNTAX       Unsigned64
    MAX-ACCESS   read-only
    STATUS       current
    DESCRIPTION
        "Cisco Firepower adaptor:MenloEthStatsHist:dropRunt
        managed object property"
    ::= { cfprAdaptorMenloEthStatsHistEntry 9 }

cfprAdaptorMenloEthStatsHistDropRuntDelta OBJECT-TYPE
    SYNTAX       Unsigned64
    MAX-ACCESS   read-only
    STATUS       current
    DESCRIPTION
        "Cisco Firepower adaptor:MenloEthStatsHist:dropRuntDelta
        managed object property"
    ::= { cfprAdaptorMenloEthStatsHistEntry 10 }

cfprAdaptorMenloEthStatsHistDropRuntDeltaAvg OBJECT-TYPE
    SYNTAX       Unsigned64
    MAX-ACCESS   read-only
    STATUS       current
    DESCRIPTION
        "Cisco Firepower adaptor:MenloEthStatsHist:dropRuntDeltaAvg
        managed object property"
    ::= { cfprAdaptorMenloEthStatsHistEntry 11 }

cfprAdaptorMenloEthStatsHistDropRuntDeltaMax OBJECT-TYPE
    SYNTAX       Unsigned64
    MAX-ACCESS   read-only
    STATUS       current
    DESCRIPTION
        "Cisco Firepower adaptor:MenloEthStatsHist:dropRuntDeltaMax
        managed object property"
    ::= { cfprAdaptorMenloEthStatsHistEntry 12 }

cfprAdaptorMenloEthStatsHistDropRuntDeltaMin OBJECT-TYPE
    SYNTAX       Unsigned64
    MAX-ACCESS   read-only
    STATUS       current
    DESCRIPTION
        "Cisco Firepower adaptor:MenloEthStatsHist:dropRuntDeltaMin
        managed object property"
    ::= { cfprAdaptorMenloEthStatsHistEntry 13 }

cfprAdaptorMenloEthStatsHistId OBJECT-TYPE
    SYNTAX       Unsigned64
    MAX-ACCESS   read-only
    STATUS       current
    DESCRIPTION
        "Cisco Firepower adaptor:MenloEthStatsHist:id managed
        object property"
    ::= { cfprAdaptorMenloEthStatsHistEntry 14 }

cfprAdaptorMenloEthStatsHistMostRecent OBJECT-TYPE
    SYNTAX       TruthValue
    MAX-ACCESS   read-only
    STATUS       current
    DESCRIPTION
        "Cisco Firepower adaptor:MenloEthStatsHist:mostRecent
        managed object property"
    ::= { cfprAdaptorMenloEthStatsHistEntry 15 }

cfprAdaptorMenloEthStatsHistSuspect OBJECT-TYPE
    SYNTAX       TruthValue
    MAX-ACCESS   read-only
    STATUS       current
    DESCRIPTION
        "Cisco Firepower adaptor:MenloEthStatsHist:suspect
        managed object property"
    ::= { cfprAdaptorMenloEthStatsHistEntry 16 }

cfprAdaptorMenloEthStatsHistThresholded OBJECT-TYPE
    SYNTAX       CfprAdaptorMenloEthStatsHistThresholded
    MAX-ACCESS   read-only
    STATUS       current
    DESCRIPTION
        "Cisco Firepower adaptor:MenloEthStatsHist:thresholded
        managed object property"
    ::= { cfprAdaptorMenloEthStatsHistEntry 17 }

cfprAdaptorMenloEthStatsHistTimeCollected OBJECT-TYPE
    SYNTAX       DateAndTime
    MAX-ACCESS   read-only
    STATUS       current
    DESCRIPTION
        "Cisco Firepower adaptor:MenloEthStatsHist:timeCollected
        managed object property"
    ::= { cfprAdaptorMenloEthStatsHistEntry 18 }

cfprAdaptorMenloEthStatsHistTruncateOverrun OBJECT-TYPE
    SYNTAX       Unsigned64
    MAX-ACCESS   read-only
    STATUS       current
    DESCRIPTION
        "Cisco Firepower adaptor:MenloEthStatsHist:truncateOverrun
        managed object property"
    ::= { cfprAdaptorMenloEthStatsHistEntry 19 }

cfprAdaptorMenloEthStatsHistTruncateOverrunDelta OBJECT-TYPE
    SYNTAX       Unsigned64
    MAX-ACCESS   read-only
    STATUS       current
    DESCRIPTION
        "Cisco Firepower adaptor:MenloEthStatsHist:truncateOverrunDelta
        managed object property"
    ::= { cfprAdaptorMenloEthStatsHistEntry 20 }

cfprAdaptorMenloEthStatsHistTruncateOverrunDeltaAvg OBJECT-TYPE
    SYNTAX       Unsigned64
    MAX-ACCESS   read-only
    STATUS       current
    DESCRIPTION
        "Cisco Firepower adaptor:MenloEthStatsHist:truncateOverrunDeltaAvg
         managed object property"
    ::= { cfprAdaptorMenloEthStatsHistEntry 21 }

cfprAdaptorMenloEthStatsHistTruncateOverrunDeltaMax OBJECT-TYPE
    SYNTAX       Unsigned64
    MAX-ACCESS   read-only
    STATUS       current
    DESCRIPTION
        "Cisco Firepower adaptor:MenloEthStatsHist:truncateOverrunDeltaMax
         managed object property"
    ::= { cfprAdaptorMenloEthStatsHistEntry 22 }

cfprAdaptorMenloEthStatsHistTruncateOverrunDeltaMin OBJECT-TYPE
    SYNTAX       Unsigned64
    MAX-ACCESS   read-only
    STATUS       current
    DESCRIPTION
        "Cisco Firepower adaptor:MenloEthStatsHist:truncateOverrunDeltaMin
         managed object property"
    ::= { cfprAdaptorMenloEthStatsHistEntry 23 }

cfprAdaptorMenloFcErrorStatsTable OBJECT-TYPE
    SYNTAX           SEQUENCE OF CfprAdaptorMenloFcErrorStatsEntry
    MAX-ACCESS       not-accessible
    STATUS           current
    DESCRIPTION
        "Cisco Firepower adaptor:MenloFcErrorStats managed object table"
    ::= { cfprAdaptorObjects 90 }

cfprAdaptorMenloFcErrorStatsEntry OBJECT-TYPE
    SYNTAX           CfprAdaptorMenloFcErrorStatsEntry
    MAX-ACCESS       not-accessible
    STATUS           current
    DESCRIPTION
        "Entry for the cfprAdaptorMenloFcErrorStatsTable table."
    INDEX { cfprAdaptorMenloFcErrorStatsInstanceId }
    ::= { cfprAdaptorMenloFcErrorStatsTable 1 }

CfprAdaptorMenloFcErrorStatsEntry ::= SEQUENCE {
    cfprAdaptorMenloFcErrorStatsInstanceId                           CfprManagedObjectId,
    cfprAdaptorMenloFcErrorStatsDn                                   CfprManagedObjectDn,
    cfprAdaptorMenloFcErrorStatsRn                                   SnmpAdminString,
    cfprAdaptorMenloFcErrorStatsCorrectableErrors                    Unsigned64,
    cfprAdaptorMenloFcErrorStatsCorrectableErrorsDelta               Counter64,
    cfprAdaptorMenloFcErrorStatsCorrectableErrorsDeltaAvg            Unsigned64,
    cfprAdaptorMenloFcErrorStatsCorrectableErrorsDeltaMax            Unsigned64,
    cfprAdaptorMenloFcErrorStatsCorrectableErrorsDeltaMin            Unsigned64,
    cfprAdaptorMenloFcErrorStatsIntervals                            Gauge32,
    cfprAdaptorMenloFcErrorStatsMenloFcIndex                         CfprAdaptorMenloStatsIndex,
    cfprAdaptorMenloFcErrorStatsPopErrors                            Unsigned64,
    cfprAdaptorMenloFcErrorStatsPopErrorsDelta                       Counter64,
    cfprAdaptorMenloFcErrorStatsPopErrorsDeltaAvg                    Unsigned64,
    cfprAdaptorMenloFcErrorStatsPopErrorsDeltaMax                    Unsigned64,
    cfprAdaptorMenloFcErrorStatsPopErrorsDeltaMin                    Unsigned64,
    cfprAdaptorMenloFcErrorStatsPushErrors                           Unsigned64,
    cfprAdaptorMenloFcErrorStatsPushErrorsDelta                      Counter64,
    cfprAdaptorMenloFcErrorStatsPushErrorsDeltaAvg                   Unsigned64,
    cfprAdaptorMenloFcErrorStatsPushErrorsDeltaMax                   Unsigned64,
    cfprAdaptorMenloFcErrorStatsPushErrorsDeltaMin                   Unsigned64,
    cfprAdaptorMenloFcErrorStatsSuspect                              TruthValue,
    cfprAdaptorMenloFcErrorStatsThresholded                          CfprAdaptorMenloFcErrorStatsThresholded,
    cfprAdaptorMenloFcErrorStatsTimeCollected                        DateAndTime,
    cfprAdaptorMenloFcErrorStatsUncorrectableErrors                  Unsigned64,
    cfprAdaptorMenloFcErrorStatsUncorrectableErrorsDelta             Counter64,
    cfprAdaptorMenloFcErrorStatsUncorrectableErrorsDeltaAvg          Unsigned64,
    cfprAdaptorMenloFcErrorStatsUncorrectableErrorsDeltaMax          Unsigned64,
    cfprAdaptorMenloFcErrorStatsUncorrectableErrorsDeltaMin          Unsigned64,
    cfprAdaptorMenloFcErrorStatsUpdate                               Gauge32
}

cfprAdaptorMenloFcErrorStatsInstanceId OBJECT-TYPE
    SYNTAX       CfprManagedObjectId
    MAX-ACCESS   not-accessible
    STATUS       current
    DESCRIPTION
        "Instance identifier of the managed object."
    ::= { cfprAdaptorMenloFcErrorStatsEntry 1 }

cfprAdaptorMenloFcErrorStatsDn OBJECT-TYPE
    SYNTAX       CfprManagedObjectDn
    MAX-ACCESS   read-only
    STATUS       current
    DESCRIPTION
        "Cisco Firepower adaptor:MenloFcErrorStats:dn managed
        object property"
    ::= { cfprAdaptorMenloFcErrorStatsEntry 2 }

cfprAdaptorMenloFcErrorStatsRn OBJECT-TYPE
    SYNTAX       SnmpAdminString
    MAX-ACCESS   read-only
    STATUS       current
    DESCRIPTION
        "Cisco Firepower adaptor:MenloFcErrorStats:rn managed
        object property"
    ::= { cfprAdaptorMenloFcErrorStatsEntry 3 }

cfprAdaptorMenloFcErrorStatsCorrectableErrors OBJECT-TYPE
    SYNTAX       Unsigned64
    MAX-ACCESS   read-only
    STATUS       current
    DESCRIPTION
        "Cisco Firepower adaptor:MenloFcErrorStats:correctableErrors
        managed object property"
    ::= { cfprAdaptorMenloFcErrorStatsEntry 4 }

cfprAdaptorMenloFcErrorStatsCorrectableErrorsDelta OBJECT-TYPE
    SYNTAX       Counter64
    MAX-ACCESS   read-only
    STATUS       current
    DESCRIPTION
        "Cisco Firepower adaptor:MenloFcErrorStats:correctableErrorsDelta
        managed object property"
    ::= { cfprAdaptorMenloFcErrorStatsEntry 5 }

cfprAdaptorMenloFcErrorStatsCorrectableErrorsDeltaAvg OBJECT-TYPE
    SYNTAX       Unsigned64
    MAX-ACCESS   read-only
    STATUS       current
    DESCRIPTION
        "Cisco Firepower adaptor:MenloFcErrorStats:correctableErrorsDeltaA
        vg managed object property"
    ::= { cfprAdaptorMenloFcErrorStatsEntry 6 }

cfprAdaptorMenloFcErrorStatsCorrectableErrorsDeltaMax OBJECT-TYPE
    SYNTAX       Unsigned64
    MAX-ACCESS   read-only
    STATUS       current
    DESCRIPTION
        "Cisco Firepower adaptor:MenloFcErrorStats:correctableErrorsDeltaM
        ax managed object property"
    ::= { cfprAdaptorMenloFcErrorStatsEntry 7 }

cfprAdaptorMenloFcErrorStatsCorrectableErrorsDeltaMin OBJECT-TYPE
    SYNTAX       Unsigned64
    MAX-ACCESS   read-only
    STATUS       current
    DESCRIPTION
        "Cisco Firepower adaptor:MenloFcErrorStats:correctableErrorsDeltaM
        in managed object property"
    ::= { cfprAdaptorMenloFcErrorStatsEntry 8 }

cfprAdaptorMenloFcErrorStatsIntervals OBJECT-TYPE
    SYNTAX       Gauge32
    MAX-ACCESS   read-only
    STATUS       current
    DESCRIPTION
        "Cisco Firepower adaptor:MenloFcErrorStats:intervals
        managed object property"
    ::= { cfprAdaptorMenloFcErrorStatsEntry 9 }

cfprAdaptorMenloFcErrorStatsMenloFcIndex OBJECT-TYPE
    SYNTAX       CfprAdaptorMenloStatsIndex
    MAX-ACCESS   read-only
    STATUS       current
    DESCRIPTION
        "Cisco Firepower adaptor:MenloFcErrorStats:menloFcIndex
        managed object property"
    ::= { cfprAdaptorMenloFcErrorStatsEntry 10 }

cfprAdaptorMenloFcErrorStatsPopErrors OBJECT-TYPE
    SYNTAX       Unsigned64
    MAX-ACCESS   read-only
    STATUS       current
    DESCRIPTION
        "Cisco Firepower adaptor:MenloFcErrorStats:popErrors
        managed object property"
    ::= { cfprAdaptorMenloFcErrorStatsEntry 11 }

cfprAdaptorMenloFcErrorStatsPopErrorsDelta OBJECT-TYPE
    SYNTAX       Counter64
    MAX-ACCESS   read-only
    STATUS       current
    DESCRIPTION
        "Cisco Firepower adaptor:MenloFcErrorStats:popErrorsDelta
        managed object property"
    ::= { cfprAdaptorMenloFcErrorStatsEntry 12 }

cfprAdaptorMenloFcErrorStatsPopErrorsDeltaAvg OBJECT-TYPE
    SYNTAX       Unsigned64
    MAX-ACCESS   read-only
    STATUS       current
    DESCRIPTION
        "Cisco Firepower adaptor:MenloFcErrorStats:popErrorsDeltaAvg
        managed object property"
    ::= { cfprAdaptorMenloFcErrorStatsEntry 13 }

cfprAdaptorMenloFcErrorStatsPopErrorsDeltaMax OBJECT-TYPE
    SYNTAX       Unsigned64
    MAX-ACCESS   read-only
    STATUS       current
    DESCRIPTION
        "Cisco Firepower adaptor:MenloFcErrorStats:popErrorsDeltaMax
        managed object property"
    ::= { cfprAdaptorMenloFcErrorStatsEntry 14 }

cfprAdaptorMenloFcErrorStatsPopErrorsDeltaMin OBJECT-TYPE
    SYNTAX       Unsigned64
    MAX-ACCESS   read-only
    STATUS       current
    DESCRIPTION
        "Cisco Firepower adaptor:MenloFcErrorStats:popErrorsDeltaMin
        managed object property"
    ::= { cfprAdaptorMenloFcErrorStatsEntry 15 }

cfprAdaptorMenloFcErrorStatsPushErrors OBJECT-TYPE
    SYNTAX       Unsigned64
    MAX-ACCESS   read-only
    STATUS       current
    DESCRIPTION
        "Cisco Firepower adaptor:MenloFcErrorStats:pushErrors
        managed object property"
    ::= { cfprAdaptorMenloFcErrorStatsEntry 16 }

cfprAdaptorMenloFcErrorStatsPushErrorsDelta OBJECT-TYPE
    SYNTAX       Counter64
    MAX-ACCESS   read-only
    STATUS       current
    DESCRIPTION
        "Cisco Firepower adaptor:MenloFcErrorStats:pushErrorsDelta
        managed object property"
    ::= { cfprAdaptorMenloFcErrorStatsEntry 17 }

cfprAdaptorMenloFcErrorStatsPushErrorsDeltaAvg OBJECT-TYPE
    SYNTAX       Unsigned64
    MAX-ACCESS   read-only
    STATUS       current
    DESCRIPTION
        "Cisco Firepower adaptor:MenloFcErrorStats:pushErrorsDeltaAvg
        managed object property"
    ::= { cfprAdaptorMenloFcErrorStatsEntry 18 }

cfprAdaptorMenloFcErrorStatsPushErrorsDeltaMax OBJECT-TYPE
    SYNTAX       Unsigned64
    MAX-ACCESS   read-only
    STATUS       current
    DESCRIPTION
        "Cisco Firepower adaptor:MenloFcErrorStats:pushErrorsDeltaMax
        managed object property"
    ::= { cfprAdaptorMenloFcErrorStatsEntry 19 }

cfprAdaptorMenloFcErrorStatsPushErrorsDeltaMin OBJECT-TYPE
    SYNTAX       Unsigned64
    MAX-ACCESS   read-only
    STATUS       current
    DESCRIPTION
        "Cisco Firepower adaptor:MenloFcErrorStats:pushErrorsDeltaMin
        managed object property"
    ::= { cfprAdaptorMenloFcErrorStatsEntry 20 }

cfprAdaptorMenloFcErrorStatsSuspect OBJECT-TYPE
    SYNTAX       TruthValue
    MAX-ACCESS   read-only
    STATUS       current
    DESCRIPTION
        "Cisco Firepower adaptor:MenloFcErrorStats:suspect
        managed object property"
    ::= { cfprAdaptorMenloFcErrorStatsEntry 21 }

cfprAdaptorMenloFcErrorStatsThresholded OBJECT-TYPE
    SYNTAX       CfprAdaptorMenloFcErrorStatsThresholded
    MAX-ACCESS   read-only
    STATUS       current
    DESCRIPTION
        "Cisco Firepower adaptor:MenloFcErrorStats:thresholded
        managed object property"
    ::= { cfprAdaptorMenloFcErrorStatsEntry 22 }

cfprAdaptorMenloFcErrorStatsTimeCollected OBJECT-TYPE
    SYNTAX       DateAndTime
    MAX-ACCESS   read-only
    STATUS       current
    DESCRIPTION
        "Cisco Firepower adaptor:MenloFcErrorStats:timeCollected
        managed object property"
    ::= { cfprAdaptorMenloFcErrorStatsEntry 23 }

cfprAdaptorMenloFcErrorStatsUncorrectableErrors OBJECT-TYPE
    SYNTAX       Unsigned64
    MAX-ACCESS   read-only
    STATUS       current
    DESCRIPTION
        "Cisco Firepower adaptor:MenloFcErrorStats:uncorrectableErrors
        managed object property"
    ::= { cfprAdaptorMenloFcErrorStatsEntry 24 }

cfprAdaptorMenloFcErrorStatsUncorrectableErrorsDelta OBJECT-TYPE
    SYNTAX       Counter64
    MAX-ACCESS   read-only
    STATUS       current
    DESCRIPTION
        "Cisco Firepower adaptor:MenloFcErrorStats:uncorrectableErrorsDelt
        a managed object property"
    ::= { cfprAdaptorMenloFcErrorStatsEntry 25 }

cfprAdaptorMenloFcErrorStatsUncorrectableErrorsDeltaAvg OBJECT-TYPE
    SYNTAX       Unsigned64
    MAX-ACCESS   read-only
    STATUS       current
    DESCRIPTION
        "Cisco Firepower adaptor:MenloFcErrorStats:uncorrectableErrorsDelt
        aAvg managed object property"
    ::= { cfprAdaptorMenloFcErrorStatsEntry 26 }

cfprAdaptorMenloFcErrorStatsUncorrectableErrorsDeltaMax OBJECT-TYPE
    SYNTAX       Unsigned64
    MAX-ACCESS   read-only
    STATUS       current
    DESCRIPTION
        "Cisco Firepower adaptor:MenloFcErrorStats:uncorrectableErrorsDelt
        aMax managed object property"
    ::= { cfprAdaptorMenloFcErrorStatsEntry 27 }

cfprAdaptorMenloFcErrorStatsUncorrectableErrorsDeltaMin OBJECT-TYPE
    SYNTAX       Unsigned64
    MAX-ACCESS   read-only
    STATUS       current
    DESCRIPTION
        "Cisco Firepower adaptor:MenloFcErrorStats:uncorrectableErrorsDelt
        aMin managed object property"
    ::= { cfprAdaptorMenloFcErrorStatsEntry 28 }

cfprAdaptorMenloFcErrorStatsUpdate OBJECT-TYPE
    SYNTAX       Gauge32
    MAX-ACCESS   read-only
    STATUS       current
    DESCRIPTION
        "Cisco Firepower adaptor:MenloFcErrorStats:update
        managed object property"
    ::= { cfprAdaptorMenloFcErrorStatsEntry 29 }

cfprAdaptorMenloFcErrorStatsHistTable OBJECT-TYPE
    SYNTAX           SEQUENCE OF CfprAdaptorMenloFcErrorStatsHistEntry
    MAX-ACCESS       not-accessible
    STATUS           current
    DESCRIPTION
        "Cisco Firepower adaptor:MenloFcErrorStatsHist
        managed object table"
    ::= { cfprAdaptorObjects 91 }

cfprAdaptorMenloFcErrorStatsHistEntry OBJECT-TYPE
    SYNTAX           CfprAdaptorMenloFcErrorStatsHistEntry
    MAX-ACCESS       not-accessible
    STATUS           current
    DESCRIPTION
        "Entry for the cfprAdaptorMenloFcErrorStatsHistTable table."
    INDEX { cfprAdaptorMenloFcErrorStatsHistInstanceId }
    ::= { cfprAdaptorMenloFcErrorStatsHistTable 1 }

CfprAdaptorMenloFcErrorStatsHistEntry ::= SEQUENCE {
    cfprAdaptorMenloFcErrorStatsHistInstanceId                       CfprManagedObjectId,
    cfprAdaptorMenloFcErrorStatsHistDn                               CfprManagedObjectDn,
    cfprAdaptorMenloFcErrorStatsHistRn                               SnmpAdminString,
    cfprAdaptorMenloFcErrorStatsHistCorrectableErrors                Unsigned64,
    cfprAdaptorMenloFcErrorStatsHistCorrectableErrorsDelta           Unsigned64,
    cfprAdaptorMenloFcErrorStatsHistCorrectableErrorsDeltaAvg        Unsigned64,
    cfprAdaptorMenloFcErrorStatsHistCorrectableErrorsDeltaMax        Unsigned64,
    cfprAdaptorMenloFcErrorStatsHistCorrectableErrorsDeltaMin        Unsigned64,
    cfprAdaptorMenloFcErrorStatsHistId                               Unsigned64,
    cfprAdaptorMenloFcErrorStatsHistMostRecent                       TruthValue,
    cfprAdaptorMenloFcErrorStatsHistPopErrors                        Unsigned64,
    cfprAdaptorMenloFcErrorStatsHistPopErrorsDelta                   Unsigned64,
    cfprAdaptorMenloFcErrorStatsHistPopErrorsDeltaAvg                Unsigned64,
    cfprAdaptorMenloFcErrorStatsHistPopErrorsDeltaMax                Unsigned64,
    cfprAdaptorMenloFcErrorStatsHistPopErrorsDeltaMin                Unsigned64,
    cfprAdaptorMenloFcErrorStatsHistPushErrors                       Unsigned64,
    cfprAdaptorMenloFcErrorStatsHistPushErrorsDelta                  Unsigned64,
    cfprAdaptorMenloFcErrorStatsHistPushErrorsDeltaAvg               Unsigned64,
    cfprAdaptorMenloFcErrorStatsHistPushErrorsDeltaMax               Unsigned64,
    cfprAdaptorMenloFcErrorStatsHistPushErrorsDeltaMin               Unsigned64,
    cfprAdaptorMenloFcErrorStatsHistSuspect                          TruthValue,
    cfprAdaptorMenloFcErrorStatsHistThresholded                      CfprAdaptorMenloFcErrorStatsHistThresholded,
    cfprAdaptorMenloFcErrorStatsHistTimeCollected                    DateAndTime,
    cfprAdaptorMenloFcErrorStatsHistUncorrectableErrors              Unsigned64,
    cfprAdaptorMenloFcErrorStatsHistUncorrectableErrorsDelta         Unsigned64,
    cfprAdaptorMenloFcErrorStatsHistUncorrectableErrorsDeltaAvg      Unsigned64,
    cfprAdaptorMenloFcErrorStatsHistUncorrectableErrorsDeltaMax      Unsigned64,
    cfprAdaptorMenloFcErrorStatsHistUncorrectableErrorsDeltaMin      Unsigned64
}

cfprAdaptorMenloFcErrorStatsHistInstanceId OBJECT-TYPE
    SYNTAX       CfprManagedObjectId
    MAX-ACCESS   not-accessible
    STATUS       current
    DESCRIPTION
        "Instance identifier of the managed object."
    ::= { cfprAdaptorMenloFcErrorStatsHistEntry 1 }

cfprAdaptorMenloFcErrorStatsHistDn OBJECT-TYPE
    SYNTAX       CfprManagedObjectDn
    MAX-ACCESS   read-only
    STATUS       current
    DESCRIPTION
        "Cisco Firepower adaptor:MenloFcErrorStatsHist:dn
        managed object property"
    ::= { cfprAdaptorMenloFcErrorStatsHistEntry 2 }

cfprAdaptorMenloFcErrorStatsHistRn OBJECT-TYPE
    SYNTAX       SnmpAdminString
    MAX-ACCESS   read-only
    STATUS       current
    DESCRIPTION
        "Cisco Firepower adaptor:MenloFcErrorStatsHist:rn
        managed object property"
    ::= { cfprAdaptorMenloFcErrorStatsHistEntry 3 }

cfprAdaptorMenloFcErrorStatsHistCorrectableErrors OBJECT-TYPE
    SYNTAX       Unsigned64
    MAX-ACCESS   read-only
    STATUS       current
    DESCRIPTION
        "Cisco Firepower adaptor:MenloFcErrorStatsHist:correctableErrors
        managed object property"
    ::= { cfprAdaptorMenloFcErrorStatsHistEntry 4 }

cfprAdaptorMenloFcErrorStatsHistCorrectableErrorsDelta OBJECT-TYPE
    SYNTAX       Unsigned64
    MAX-ACCESS   read-only
    STATUS       current
    DESCRIPTION
        "Cisco Firepower adaptor:MenloFcErrorStatsHist:correctableErrorsDe
        lta managed object property"
    ::= { cfprAdaptorMenloFcErrorStatsHistEntry 5 }

cfprAdaptorMenloFcErrorStatsHistCorrectableErrorsDeltaAvg OBJECT-TYPE
    SYNTAX       Unsigned64
    MAX-ACCESS   read-only
    STATUS       current
    DESCRIPTION
        "Cisco Firepower adaptor:MenloFcErrorStatsHist:correctableErrorsDe
        ltaAvg managed object property"
    ::= { cfprAdaptorMenloFcErrorStatsHistEntry 6 }

cfprAdaptorMenloFcErrorStatsHistCorrectableErrorsDeltaMax OBJECT-TYPE
    SYNTAX       Unsigned64
    MAX-ACCESS   read-only
    STATUS       current
    DESCRIPTION
        "Cisco Firepower adaptor:MenloFcErrorStatsHist:correctableErrorsDe
        ltaMax managed object property"
    ::= { cfprAdaptorMenloFcErrorStatsHistEntry 7 }

cfprAdaptorMenloFcErrorStatsHistCorrectableErrorsDeltaMin OBJECT-TYPE
    SYNTAX       Unsigned64
    MAX-ACCESS   read-only
    STATUS       current
    DESCRIPTION
        "Cisco Firepower adaptor:MenloFcErrorStatsHist:correctableErrorsDe
        ltaMin managed object property"
    ::= { cfprAdaptorMenloFcErrorStatsHistEntry 8 }

cfprAdaptorMenloFcErrorStatsHistId OBJECT-TYPE
    SYNTAX       Unsigned64
    MAX-ACCESS   read-only
    STATUS       current
    DESCRIPTION
        "Cisco Firepower adaptor:MenloFcErrorStatsHist:id
        managed object property"
    ::= { cfprAdaptorMenloFcErrorStatsHistEntry 9 }

cfprAdaptorMenloFcErrorStatsHistMostRecent OBJECT-TYPE
    SYNTAX       TruthValue
    MAX-ACCESS   read-only
    STATUS       current
    DESCRIPTION
        "Cisco Firepower adaptor:MenloFcErrorStatsHist:mostRecent
        managed object property"
    ::= { cfprAdaptorMenloFcErrorStatsHistEntry 10 }

cfprAdaptorMenloFcErrorStatsHistPopErrors OBJECT-TYPE
    SYNTAX       Unsigned64
    MAX-ACCESS   read-only
    STATUS       current
    DESCRIPTION
        "Cisco Firepower adaptor:MenloFcErrorStatsHist:popErrors
        managed object property"
    ::= { cfprAdaptorMenloFcErrorStatsHistEntry 11 }

cfprAdaptorMenloFcErrorStatsHistPopErrorsDelta OBJECT-TYPE
    SYNTAX       Unsigned64
    MAX-ACCESS   read-only
    STATUS       current
    DESCRIPTION
        "Cisco Firepower adaptor:MenloFcErrorStatsHist:popErrorsDelta
        managed object property"
    ::= { cfprAdaptorMenloFcErrorStatsHistEntry 12 }

cfprAdaptorMenloFcErrorStatsHistPopErrorsDeltaAvg OBJECT-TYPE
    SYNTAX       Unsigned64
    MAX-ACCESS   read-only
    STATUS       current
    DESCRIPTION
        "Cisco Firepower adaptor:MenloFcErrorStatsHist:popErrorsDeltaAvg
        managed object property"
    ::= { cfprAdaptorMenloFcErrorStatsHistEntry 13 }

cfprAdaptorMenloFcErrorStatsHistPopErrorsDeltaMax OBJECT-TYPE
    SYNTAX       Unsigned64
    MAX-ACCESS   read-only
    STATUS       current
    DESCRIPTION
        "Cisco Firepower adaptor:MenloFcErrorStatsHist:popErrorsDeltaMax
        managed object property"
    ::= { cfprAdaptorMenloFcErrorStatsHistEntry 14 }

cfprAdaptorMenloFcErrorStatsHistPopErrorsDeltaMin OBJECT-TYPE
    SYNTAX       Unsigned64
    MAX-ACCESS   read-only
    STATUS       current
    DESCRIPTION
        "Cisco Firepower adaptor:MenloFcErrorStatsHist:popErrorsDeltaMin
        managed object property"
    ::= { cfprAdaptorMenloFcErrorStatsHistEntry 15 }

cfprAdaptorMenloFcErrorStatsHistPushErrors OBJECT-TYPE
    SYNTAX       Unsigned64
    MAX-ACCESS   read-only
    STATUS       current
    DESCRIPTION
        "Cisco Firepower adaptor:MenloFcErrorStatsHist:pushErrors
        managed object property"
    ::= { cfprAdaptorMenloFcErrorStatsHistEntry 16 }

cfprAdaptorMenloFcErrorStatsHistPushErrorsDelta OBJECT-TYPE
    SYNTAX       Unsigned64
    MAX-ACCESS   read-only
    STATUS       current
    DESCRIPTION
        "Cisco Firepower adaptor:MenloFcErrorStatsHist:pushErrorsDelta
        managed object property"
    ::= { cfprAdaptorMenloFcErrorStatsHistEntry 17 }

cfprAdaptorMenloFcErrorStatsHistPushErrorsDeltaAvg OBJECT-TYPE
    SYNTAX       Unsigned64
    MAX-ACCESS   read-only
    STATUS       current
    DESCRIPTION
        "Cisco Firepower adaptor:MenloFcErrorStatsHist:pushErrorsDeltaAvg
        managed object property"
    ::= { cfprAdaptorMenloFcErrorStatsHistEntry 18 }

cfprAdaptorMenloFcErrorStatsHistPushErrorsDeltaMax OBJECT-TYPE
    SYNTAX       Unsigned64
    MAX-ACCESS   read-only
    STATUS       current
    DESCRIPTION
        "Cisco Firepower adaptor:MenloFcErrorStatsHist:pushErrorsDeltaMax
        managed object property"
    ::= { cfprAdaptorMenloFcErrorStatsHistEntry 19 }

cfprAdaptorMenloFcErrorStatsHistPushErrorsDeltaMin OBJECT-TYPE
    SYNTAX       Unsigned64
    MAX-ACCESS   read-only
    STATUS       current
    DESCRIPTION
        "Cisco Firepower adaptor:MenloFcErrorStatsHist:pushErrorsDeltaMin
        managed object property"
    ::= { cfprAdaptorMenloFcErrorStatsHistEntry 20 }

cfprAdaptorMenloFcErrorStatsHistSuspect OBJECT-TYPE
    SYNTAX       TruthValue
    MAX-ACCESS   read-only
    STATUS       current
    DESCRIPTION
        "Cisco Firepower adaptor:MenloFcErrorStatsHist:suspect
        managed object property"
    ::= { cfprAdaptorMenloFcErrorStatsHistEntry 21 }

cfprAdaptorMenloFcErrorStatsHistThresholded OBJECT-TYPE
    SYNTAX       CfprAdaptorMenloFcErrorStatsHistThresholded
    MAX-ACCESS   read-only
    STATUS       current
    DESCRIPTION
        "Cisco Firepower adaptor:MenloFcErrorStatsHist:thresholded
        managed object property"
    ::= { cfprAdaptorMenloFcErrorStatsHistEntry 22 }

cfprAdaptorMenloFcErrorStatsHistTimeCollected OBJECT-TYPE
    SYNTAX       DateAndTime
    MAX-ACCESS   read-only
    STATUS       current
    DESCRIPTION
        "Cisco Firepower adaptor:MenloFcErrorStatsHist:timeCollected
        managed object property"
    ::= { cfprAdaptorMenloFcErrorStatsHistEntry 23 }

cfprAdaptorMenloFcErrorStatsHistUncorrectableErrors OBJECT-TYPE
    SYNTAX       Unsigned64
    MAX-ACCESS   read-only
    STATUS       current
    DESCRIPTION
        "Cisco Firepower adaptor:MenloFcErrorStatsHist:uncorrectableErrors
         managed object property"
    ::= { cfprAdaptorMenloFcErrorStatsHistEntry 24 }

cfprAdaptorMenloFcErrorStatsHistUncorrectableErrorsDelta OBJECT-TYPE
    SYNTAX       Unsigned64
    MAX-ACCESS   read-only
    STATUS       current
    DESCRIPTION
        "Cisco Firepower adaptor:MenloFcErrorStatsHist:uncorrectableErrors
        Delta managed object property"
    ::= { cfprAdaptorMenloFcErrorStatsHistEntry 25 }

cfprAdaptorMenloFcErrorStatsHistUncorrectableErrorsDeltaAvg OBJECT-TYPE
    SYNTAX       Unsigned64
    MAX-ACCESS   read-only
    STATUS       current
    DESCRIPTION
        "Cisco Firepower adaptor:MenloFcErrorStatsHist:uncorrectableErrors
        DeltaAvg managed object property"
    ::= { cfprAdaptorMenloFcErrorStatsHistEntry 26 }

cfprAdaptorMenloFcErrorStatsHistUncorrectableErrorsDeltaMax OBJECT-TYPE
    SYNTAX       Unsigned64
    MAX-ACCESS   read-only
    STATUS       current
    DESCRIPTION
        "Cisco Firepower adaptor:MenloFcErrorStatsHist:uncorrectableErrors
        DeltaMax managed object property"
    ::= { cfprAdaptorMenloFcErrorStatsHistEntry 27 }

cfprAdaptorMenloFcErrorStatsHistUncorrectableErrorsDeltaMin OBJECT-TYPE
    SYNTAX       Unsigned64
    MAX-ACCESS   read-only
    STATUS       current
    DESCRIPTION
        "Cisco Firepower adaptor:MenloFcErrorStatsHist:uncorrectableErrors
        DeltaMin managed object property"
    ::= { cfprAdaptorMenloFcErrorStatsHistEntry 28 }

cfprAdaptorMenloFcStatsTable OBJECT-TYPE
    SYNTAX           SEQUENCE OF CfprAdaptorMenloFcStatsEntry
    MAX-ACCESS       not-accessible
    STATUS           current
    DESCRIPTION
        "Cisco Firepower adaptor:MenloFcStats managed object table"
    ::= { cfprAdaptorObjects 92 }

cfprAdaptorMenloFcStatsEntry OBJECT-TYPE
    SYNTAX           CfprAdaptorMenloFcStatsEntry
    MAX-ACCESS       not-accessible
    STATUS           current
    DESCRIPTION
        "Entry for the cfprAdaptorMenloFcStatsTable table."
    INDEX { cfprAdaptorMenloFcStatsInstanceId }
    ::= { cfprAdaptorMenloFcStatsTable 1 }

CfprAdaptorMenloFcStatsEntry ::= SEQUENCE {
    cfprAdaptorMenloFcStatsInstanceId                                CfprManagedObjectId,
    cfprAdaptorMenloFcStatsDn                                        CfprManagedObjectDn,
    cfprAdaptorMenloFcStatsRn                                        SnmpAdminString,
    cfprAdaptorMenloFcStatsDropAcl                                   Unsigned64,
    cfprAdaptorMenloFcStatsDropAclDelta                              Counter64,
    cfprAdaptorMenloFcStatsDropAclDeltaAvg                           Unsigned64,
    cfprAdaptorMenloFcStatsDropAclDeltaMax                           Unsigned64,
    cfprAdaptorMenloFcStatsDropAclDeltaMin                           Unsigned64,
    cfprAdaptorMenloFcStatsDropOverrun                               Unsigned64,
    cfprAdaptorMenloFcStatsDropOverrunDelta                          Counter64,
    cfprAdaptorMenloFcStatsDropOverrunDeltaAvg                       Unsigned64,
    cfprAdaptorMenloFcStatsDropOverrunDeltaMax                       Unsigned64,
    cfprAdaptorMenloFcStatsDropOverrunDeltaMin                       Unsigned64,
    cfprAdaptorMenloFcStatsDropRunt                                  Unsigned64,
    cfprAdaptorMenloFcStatsDropRuntDelta                             Counter64,
    cfprAdaptorMenloFcStatsDropRuntDeltaAvg                          Unsigned64,
    cfprAdaptorMenloFcStatsDropRuntDeltaMax                          Unsigned64,
    cfprAdaptorMenloFcStatsDropRuntDeltaMin                          Unsigned64,
    cfprAdaptorMenloFcStatsIntervals                                 Gauge32,
    cfprAdaptorMenloFcStatsMenloFcIndex                              CfprAdaptorMenloStatsIndex,
    cfprAdaptorMenloFcStatsSuspect                                   TruthValue,
    cfprAdaptorMenloFcStatsThresholded                               CfprAdaptorMenloFcStatsThresholded,
    cfprAdaptorMenloFcStatsTimeCollected                             DateAndTime,
    cfprAdaptorMenloFcStatsTruncateOverrun                           Unsigned64,
    cfprAdaptorMenloFcStatsTruncateOverrunDelta                      Counter64,
    cfprAdaptorMenloFcStatsTruncateOverrunDeltaAvg                   Unsigned64,
    cfprAdaptorMenloFcStatsTruncateOverrunDeltaMax                   Unsigned64,
    cfprAdaptorMenloFcStatsTruncateOverrunDeltaMin                   Unsigned64,
    cfprAdaptorMenloFcStatsUpdate                                    Gauge32
}

cfprAdaptorMenloFcStatsInstanceId OBJECT-TYPE
    SYNTAX       CfprManagedObjectId
    MAX-ACCESS   not-accessible
    STATUS       current
    DESCRIPTION
        "Instance identifier of the managed object."
    ::= { cfprAdaptorMenloFcStatsEntry 1 }

cfprAdaptorMenloFcStatsDn OBJECT-TYPE
    SYNTAX       CfprManagedObjectDn
    MAX-ACCESS   read-only
    STATUS       current
    DESCRIPTION
        "Cisco Firepower adaptor:MenloFcStats:dn managed object property"
    ::= { cfprAdaptorMenloFcStatsEntry 2 }

cfprAdaptorMenloFcStatsRn OBJECT-TYPE
    SYNTAX       SnmpAdminString
    MAX-ACCESS   read-only
    STATUS       current
    DESCRIPTION
        "Cisco Firepower adaptor:MenloFcStats:rn managed object property"
    ::= { cfprAdaptorMenloFcStatsEntry 3 }

cfprAdaptorMenloFcStatsDropAcl OBJECT-TYPE
    SYNTAX       Unsigned64
    MAX-ACCESS   read-only
    STATUS       current
    DESCRIPTION
        "Cisco Firepower adaptor:MenloFcStats:dropAcl managed
        object property"
    ::= { cfprAdaptorMenloFcStatsEntry 4 }

cfprAdaptorMenloFcStatsDropAclDelta OBJECT-TYPE
    SYNTAX       Counter64
    MAX-ACCESS   read-only
    STATUS       current
    DESCRIPTION
        "Cisco Firepower adaptor:MenloFcStats:dropAclDelta
        managed object property"
    ::= { cfprAdaptorMenloFcStatsEntry 5 }

cfprAdaptorMenloFcStatsDropAclDeltaAvg OBJECT-TYPE
    SYNTAX       Unsigned64
    MAX-ACCESS   read-only
    STATUS       current
    DESCRIPTION
        "Cisco Firepower adaptor:MenloFcStats:dropAclDeltaAvg
        managed object property"
    ::= { cfprAdaptorMenloFcStatsEntry 6 }

cfprAdaptorMenloFcStatsDropAclDeltaMax OBJECT-TYPE
    SYNTAX       Unsigned64
    MAX-ACCESS   read-only
    STATUS       current
    DESCRIPTION
        "Cisco Firepower adaptor:MenloFcStats:dropAclDeltaMax
        managed object property"
    ::= { cfprAdaptorMenloFcStatsEntry 7 }

cfprAdaptorMenloFcStatsDropAclDeltaMin OBJECT-TYPE
    SYNTAX       Unsigned64
    MAX-ACCESS   read-only
    STATUS       current
    DESCRIPTION
        "Cisco Firepower adaptor:MenloFcStats:dropAclDeltaMin
        managed object property"
    ::= { cfprAdaptorMenloFcStatsEntry 8 }

cfprAdaptorMenloFcStatsDropOverrun OBJECT-TYPE
    SYNTAX       Unsigned64
    MAX-ACCESS   read-only
    STATUS       current
    DESCRIPTION
        "Cisco Firepower adaptor:MenloFcStats:dropOverrun
        managed object property"
    ::= { cfprAdaptorMenloFcStatsEntry 9 }

cfprAdaptorMenloFcStatsDropOverrunDelta OBJECT-TYPE
    SYNTAX       Counter64
    MAX-ACCESS   read-only
    STATUS       current
    DESCRIPTION
        "Cisco Firepower adaptor:MenloFcStats:dropOverrunDelta
        managed object property"
    ::= { cfprAdaptorMenloFcStatsEntry 10 }

cfprAdaptorMenloFcStatsDropOverrunDeltaAvg OBJECT-TYPE
    SYNTAX       Unsigned64
    MAX-ACCESS   read-only
    STATUS       current
    DESCRIPTION
        "Cisco Firepower adaptor:MenloFcStats:dropOverrunDeltaAvg
        managed object property"
    ::= { cfprAdaptorMenloFcStatsEntry 11 }

cfprAdaptorMenloFcStatsDropOverrunDeltaMax OBJECT-TYPE
    SYNTAX       Unsigned64
    MAX-ACCESS   read-only
    STATUS       current
    DESCRIPTION
        "Cisco Firepower adaptor:MenloFcStats:dropOverrunDeltaMax
        managed object property"
    ::= { cfprAdaptorMenloFcStatsEntry 12 }

cfprAdaptorMenloFcStatsDropOverrunDeltaMin OBJECT-TYPE
    SYNTAX       Unsigned64
    MAX-ACCESS   read-only
    STATUS       current
    DESCRIPTION
        "Cisco Firepower adaptor:MenloFcStats:dropOverrunDeltaMin
        managed object property"
    ::= { cfprAdaptorMenloFcStatsEntry 13 }

cfprAdaptorMenloFcStatsDropRunt OBJECT-TYPE
    SYNTAX       Unsigned64
    MAX-ACCESS   read-only
    STATUS       current
    DESCRIPTION
        "Cisco Firepower adaptor:MenloFcStats:dropRunt
        managed object property"
    ::= { cfprAdaptorMenloFcStatsEntry 14 }

cfprAdaptorMenloFcStatsDropRuntDelta OBJECT-TYPE
    SYNTAX       Counter64
    MAX-ACCESS   read-only
    STATUS       current
    DESCRIPTION
        "Cisco Firepower adaptor:MenloFcStats:dropRuntDelta
        managed object property"
    ::= { cfprAdaptorMenloFcStatsEntry 15 }

cfprAdaptorMenloFcStatsDropRuntDeltaAvg OBJECT-TYPE
    SYNTAX       Unsigned64
    MAX-ACCESS   read-only
    STATUS       current
    DESCRIPTION
        "Cisco Firepower adaptor:MenloFcStats:dropRuntDeltaAvg
        managed object property"
    ::= { cfprAdaptorMenloFcStatsEntry 16 }

cfprAdaptorMenloFcStatsDropRuntDeltaMax OBJECT-TYPE
    SYNTAX       Unsigned64
    MAX-ACCESS   read-only
    STATUS       current
    DESCRIPTION
        "Cisco Firepower adaptor:MenloFcStats:dropRuntDeltaMax
        managed object property"
    ::= { cfprAdaptorMenloFcStatsEntry 17 }

cfprAdaptorMenloFcStatsDropRuntDeltaMin OBJECT-TYPE
    SYNTAX       Unsigned64
    MAX-ACCESS   read-only
    STATUS       current
    DESCRIPTION
        "Cisco Firepower adaptor:MenloFcStats:dropRuntDeltaMin
        managed object property"
    ::= { cfprAdaptorMenloFcStatsEntry 18 }

cfprAdaptorMenloFcStatsIntervals OBJECT-TYPE
    SYNTAX       Gauge32
    MAX-ACCESS   read-only
    STATUS       current
    DESCRIPTION
        "Cisco Firepower adaptor:MenloFcStats:intervals
        managed object property"
    ::= { cfprAdaptorMenloFcStatsEntry 19 }

cfprAdaptorMenloFcStatsMenloFcIndex OBJECT-TYPE
    SYNTAX       CfprAdaptorMenloStatsIndex
    MAX-ACCESS   read-only
    STATUS       current
    DESCRIPTION
        "Cisco Firepower adaptor:MenloFcStats:menloFcIndex
        managed object property"
    ::= { cfprAdaptorMenloFcStatsEntry 20 }

cfprAdaptorMenloFcStatsSuspect OBJECT-TYPE
    SYNTAX       TruthValue
    MAX-ACCESS   read-only
    STATUS       current
    DESCRIPTION
        "Cisco Firepower adaptor:MenloFcStats:suspect managed
        object property"
    ::= { cfprAdaptorMenloFcStatsEntry 21 }

cfprAdaptorMenloFcStatsThresholded OBJECT-TYPE
    SYNTAX       CfprAdaptorMenloFcStatsThresholded
    MAX-ACCESS   read-only
    STATUS       current
    DESCRIPTION
        "Cisco Firepower adaptor:MenloFcStats:thresholded
        managed object property"
    ::= { cfprAdaptorMenloFcStatsEntry 22 }

cfprAdaptorMenloFcStatsTimeCollected OBJECT-TYPE
    SYNTAX       DateAndTime
    MAX-ACCESS   read-only
    STATUS       current
    DESCRIPTION
        "Cisco Firepower adaptor:MenloFcStats:timeCollected
        managed object property"
    ::= { cfprAdaptorMenloFcStatsEntry 23 }

cfprAdaptorMenloFcStatsTruncateOverrun OBJECT-TYPE
    SYNTAX       Unsigned64
    MAX-ACCESS   read-only
    STATUS       current
    DESCRIPTION
        "Cisco Firepower adaptor:MenloFcStats:truncateOverrun
        managed object property"
    ::= { cfprAdaptorMenloFcStatsEntry 24 }

cfprAdaptorMenloFcStatsTruncateOverrunDelta OBJECT-TYPE
    SYNTAX       Counter64
    MAX-ACCESS   read-only
    STATUS       current
    DESCRIPTION
        "Cisco Firepower adaptor:MenloFcStats:truncateOverrunDelta
        managed object property"
    ::= { cfprAdaptorMenloFcStatsEntry 25 }

cfprAdaptorMenloFcStatsTruncateOverrunDeltaAvg OBJECT-TYPE
    SYNTAX       Unsigned64
    MAX-ACCESS   read-only
    STATUS       current
    DESCRIPTION
        "Cisco Firepower adaptor:MenloFcStats:truncateOverrunDeltaAvg
        managed object property"
    ::= { cfprAdaptorMenloFcStatsEntry 26 }

cfprAdaptorMenloFcStatsTruncateOverrunDeltaMax OBJECT-TYPE
    SYNTAX       Unsigned64
    MAX-ACCESS   read-only
    STATUS       current
    DESCRIPTION
        "Cisco Firepower adaptor:MenloFcStats:truncateOverrunDeltaMax
        managed object property"
    ::= { cfprAdaptorMenloFcStatsEntry 27 }

cfprAdaptorMenloFcStatsTruncateOverrunDeltaMin OBJECT-TYPE
    SYNTAX       Unsigned64
    MAX-ACCESS   read-only
    STATUS       current
    DESCRIPTION
        "Cisco Firepower adaptor:MenloFcStats:truncateOverrunDeltaMin
        managed object property"
    ::= { cfprAdaptorMenloFcStatsEntry 28 }

cfprAdaptorMenloFcStatsUpdate OBJECT-TYPE
    SYNTAX       Gauge32
    MAX-ACCESS   read-only
    STATUS       current
    DESCRIPTION
        "Cisco Firepower adaptor:MenloFcStats:update managed
        object property"
    ::= { cfprAdaptorMenloFcStatsEntry 29 }

cfprAdaptorMenloFcStatsHistTable OBJECT-TYPE
    SYNTAX           SEQUENCE OF CfprAdaptorMenloFcStatsHistEntry
    MAX-ACCESS       not-accessible
    STATUS           current
    DESCRIPTION
        "Cisco Firepower adaptor:MenloFcStatsHist managed object table"
    ::= { cfprAdaptorObjects 93 }

cfprAdaptorMenloFcStatsHistEntry OBJECT-TYPE
    SYNTAX           CfprAdaptorMenloFcStatsHistEntry
    MAX-ACCESS       not-accessible
    STATUS           current
    DESCRIPTION
        "Entry for the cfprAdaptorMenloFcStatsHistTable table."
    INDEX { cfprAdaptorMenloFcStatsHistInstanceId }
    ::= { cfprAdaptorMenloFcStatsHistTable 1 }

CfprAdaptorMenloFcStatsHistEntry ::= SEQUENCE {
    cfprAdaptorMenloFcStatsHistInstanceId                            CfprManagedObjectId,
    cfprAdaptorMenloFcStatsHistDn                                    CfprManagedObjectDn,
    cfprAdaptorMenloFcStatsHistRn                                    SnmpAdminString,
    cfprAdaptorMenloFcStatsHistDropAcl                               Unsigned64,
    cfprAdaptorMenloFcStatsHistDropAclDelta                          Unsigned64,
    cfprAdaptorMenloFcStatsHistDropAclDeltaAvg                       Unsigned64,
    cfprAdaptorMenloFcStatsHistDropAclDeltaMax                       Unsigned64,
    cfprAdaptorMenloFcStatsHistDropAclDeltaMin                       Unsigned64,
    cfprAdaptorMenloFcStatsHistDropOverrun                           Unsigned64,
    cfprAdaptorMenloFcStatsHistDropOverrunDelta                      Unsigned64,
    cfprAdaptorMenloFcStatsHistDropOverrunDeltaAvg                   Unsigned64,
    cfprAdaptorMenloFcStatsHistDropOverrunDeltaMax                   Unsigned64,
    cfprAdaptorMenloFcStatsHistDropOverrunDeltaMin                   Unsigned64,
    cfprAdaptorMenloFcStatsHistDropRunt                              Unsigned64,
    cfprAdaptorMenloFcStatsHistDropRuntDelta                         Unsigned64,
    cfprAdaptorMenloFcStatsHistDropRuntDeltaAvg                      Unsigned64,
    cfprAdaptorMenloFcStatsHistDropRuntDeltaMax                      Unsigned64,
    cfprAdaptorMenloFcStatsHistDropRuntDeltaMin                      Unsigned64,
    cfprAdaptorMenloFcStatsHistId                                    Unsigned64,
    cfprAdaptorMenloFcStatsHistMostRecent                            TruthValue,
    cfprAdaptorMenloFcStatsHistSuspect                               TruthValue,
    cfprAdaptorMenloFcStatsHistThresholded                           CfprAdaptorMenloFcStatsHistThresholded,
    cfprAdaptorMenloFcStatsHistTimeCollected                         DateAndTime,
    cfprAdaptorMenloFcStatsHistTruncateOverrun                       Unsigned64,
    cfprAdaptorMenloFcStatsHistTruncateOverrunDelta                  Unsigned64,
    cfprAdaptorMenloFcStatsHistTruncateOverrunDeltaAvg               Unsigned64,
    cfprAdaptorMenloFcStatsHistTruncateOverrunDeltaMax               Unsigned64,
    cfprAdaptorMenloFcStatsHistTruncateOverrunDeltaMin               Unsigned64
}

cfprAdaptorMenloFcStatsHistInstanceId OBJECT-TYPE
    SYNTAX       CfprManagedObjectId
    MAX-ACCESS   not-accessible
    STATUS       current
    DESCRIPTION
        "Instance identifier of the managed object."
    ::= { cfprAdaptorMenloFcStatsHistEntry 1 }

cfprAdaptorMenloFcStatsHistDn OBJECT-TYPE
    SYNTAX       CfprManagedObjectDn
    MAX-ACCESS   read-only
    STATUS       current
    DESCRIPTION
        "Cisco Firepower adaptor:MenloFcStatsHist:dn managed
        object property"
    ::= { cfprAdaptorMenloFcStatsHistEntry 2 }

cfprAdaptorMenloFcStatsHistRn OBJECT-TYPE
    SYNTAX       SnmpAdminString
    MAX-ACCESS   read-only
    STATUS       current
    DESCRIPTION
        "Cisco Firepower adaptor:MenloFcStatsHist:rn managed
        object property"
    ::= { cfprAdaptorMenloFcStatsHistEntry 3 }

cfprAdaptorMenloFcStatsHistDropAcl OBJECT-TYPE
    SYNTAX       Unsigned64
    MAX-ACCESS   read-only
    STATUS       current
    DESCRIPTION
        "Cisco Firepower adaptor:MenloFcStatsHist:dropAcl
        managed object property"
    ::= { cfprAdaptorMenloFcStatsHistEntry 4 }

cfprAdaptorMenloFcStatsHistDropAclDelta OBJECT-TYPE
    SYNTAX       Unsigned64
    MAX-ACCESS   read-only
    STATUS       current
    DESCRIPTION
        "Cisco Firepower adaptor:MenloFcStatsHist:dropAclDelta
        managed object property"
    ::= { cfprAdaptorMenloFcStatsHistEntry 5 }

cfprAdaptorMenloFcStatsHistDropAclDeltaAvg OBJECT-TYPE
    SYNTAX       Unsigned64
    MAX-ACCESS   read-only
    STATUS       current
    DESCRIPTION
        "Cisco Firepower adaptor:MenloFcStatsHist:dropAclDeltaAvg
        managed object property"
    ::= { cfprAdaptorMenloFcStatsHistEntry 6 }

cfprAdaptorMenloFcStatsHistDropAclDeltaMax OBJECT-TYPE
    SYNTAX       Unsigned64
    MAX-ACCESS   read-only
    STATUS       current
    DESCRIPTION
        "Cisco Firepower adaptor:MenloFcStatsHist:dropAclDeltaMax
        managed object property"
    ::= { cfprAdaptorMenloFcStatsHistEntry 7 }

cfprAdaptorMenloFcStatsHistDropAclDeltaMin OBJECT-TYPE
    SYNTAX       Unsigned64
    MAX-ACCESS   read-only
    STATUS       current
    DESCRIPTION
        "Cisco Firepower adaptor:MenloFcStatsHist:dropAclDeltaMin
        managed object property"
    ::= { cfprAdaptorMenloFcStatsHistEntry 8 }

cfprAdaptorMenloFcStatsHistDropOverrun OBJECT-TYPE
    SYNTAX       Unsigned64
    MAX-ACCESS   read-only
    STATUS       current
    DESCRIPTION
        "Cisco Firepower adaptor:MenloFcStatsHist:dropOverrun
        managed object property"
    ::= { cfprAdaptorMenloFcStatsHistEntry 9 }

cfprAdaptorMenloFcStatsHistDropOverrunDelta OBJECT-TYPE
    SYNTAX       Unsigned64
    MAX-ACCESS   read-only
    STATUS       current
    DESCRIPTION
        "Cisco Firepower adaptor:MenloFcStatsHist:dropOverrunDelta
        managed object property"
    ::= { cfprAdaptorMenloFcStatsHistEntry 10 }

cfprAdaptorMenloFcStatsHistDropOverrunDeltaAvg OBJECT-TYPE
    SYNTAX       Unsigned64
    MAX-ACCESS   read-only
    STATUS       current
    DESCRIPTION
        "Cisco Firepower adaptor:MenloFcStatsHist:dropOverrunDeltaAvg
        managed object property"
    ::= { cfprAdaptorMenloFcStatsHistEntry 11 }

cfprAdaptorMenloFcStatsHistDropOverrunDeltaMax OBJECT-TYPE
    SYNTAX       Unsigned64
    MAX-ACCESS   read-only
    STATUS       current
    DESCRIPTION
        "Cisco Firepower adaptor:MenloFcStatsHist:dropOverrunDeltaMax
        managed object property"
    ::= { cfprAdaptorMenloFcStatsHistEntry 12 }

cfprAdaptorMenloFcStatsHistDropOverrunDeltaMin OBJECT-TYPE
    SYNTAX       Unsigned64
    MAX-ACCESS   read-only
    STATUS       current
    DESCRIPTION
        "Cisco Firepower adaptor:MenloFcStatsHist:dropOverrunDeltaMin
        managed object property"
    ::= { cfprAdaptorMenloFcStatsHistEntry 13 }

cfprAdaptorMenloFcStatsHistDropRunt OBJECT-TYPE
    SYNTAX       Unsigned64
    MAX-ACCESS   read-only
    STATUS       current
    DESCRIPTION
        "Cisco Firepower adaptor:MenloFcStatsHist:dropRunt
        managed object property"
    ::= { cfprAdaptorMenloFcStatsHistEntry 14 }

cfprAdaptorMenloFcStatsHistDropRuntDelta OBJECT-TYPE
    SYNTAX       Unsigned64
    MAX-ACCESS   read-only
    STATUS       current
    DESCRIPTION
        "Cisco Firepower adaptor:MenloFcStatsHist:dropRuntDelta
        managed object property"
    ::= { cfprAdaptorMenloFcStatsHistEntry 15 }

cfprAdaptorMenloFcStatsHistDropRuntDeltaAvg OBJECT-TYPE
    SYNTAX       Unsigned64
    MAX-ACCESS   read-only
    STATUS       current
    DESCRIPTION
        "Cisco Firepower adaptor:MenloFcStatsHist:dropRuntDeltaAvg
        managed object property"
    ::= { cfprAdaptorMenloFcStatsHistEntry 16 }

cfprAdaptorMenloFcStatsHistDropRuntDeltaMax OBJECT-TYPE
    SYNTAX       Unsigned64
    MAX-ACCESS   read-only
    STATUS       current
    DESCRIPTION
        "Cisco Firepower adaptor:MenloFcStatsHist:dropRuntDeltaMax
        managed object property"
    ::= { cfprAdaptorMenloFcStatsHistEntry 17 }

cfprAdaptorMenloFcStatsHistDropRuntDeltaMin OBJECT-TYPE
    SYNTAX       Unsigned64
    MAX-ACCESS   read-only
    STATUS       current
    DESCRIPTION
        "Cisco Firepower adaptor:MenloFcStatsHist:dropRuntDeltaMin
        managed object property"
    ::= { cfprAdaptorMenloFcStatsHistEntry 18 }

cfprAdaptorMenloFcStatsHistId OBJECT-TYPE
    SYNTAX       Unsigned64
    MAX-ACCESS   read-only
    STATUS       current
    DESCRIPTION
        "Cisco Firepower adaptor:MenloFcStatsHist:id managed
        object property"
    ::= { cfprAdaptorMenloFcStatsHistEntry 19 }

cfprAdaptorMenloFcStatsHistMostRecent OBJECT-TYPE
    SYNTAX       TruthValue
    MAX-ACCESS   read-only
    STATUS       current
    DESCRIPTION
        "Cisco Firepower adaptor:MenloFcStatsHist:mostRecent
        managed object property"
    ::= { cfprAdaptorMenloFcStatsHistEntry 20 }

cfprAdaptorMenloFcStatsHistSuspect OBJECT-TYPE
    SYNTAX       TruthValue
    MAX-ACCESS   read-only
    STATUS       current
    DESCRIPTION
        "Cisco Firepower adaptor:MenloFcStatsHist:suspect
        managed object property"
    ::= { cfprAdaptorMenloFcStatsHistEntry 21 }

cfprAdaptorMenloFcStatsHistThresholded OBJECT-TYPE
    SYNTAX       CfprAdaptorMenloFcStatsHistThresholded
    MAX-ACCESS   read-only
    STATUS       current
    DESCRIPTION
        "Cisco Firepower adaptor:MenloFcStatsHist:thresholded
        managed object property"
    ::= { cfprAdaptorMenloFcStatsHistEntry 22 }

cfprAdaptorMenloFcStatsHistTimeCollected OBJECT-TYPE
    SYNTAX       DateAndTime
    MAX-ACCESS   read-only
    STATUS       current
    DESCRIPTION
        "Cisco Firepower adaptor:MenloFcStatsHist:timeCollected
        managed object property"
    ::= { cfprAdaptorMenloFcStatsHistEntry 23 }

cfprAdaptorMenloFcStatsHistTruncateOverrun OBJECT-TYPE
    SYNTAX       Unsigned64
    MAX-ACCESS   read-only
    STATUS       current
    DESCRIPTION
        "Cisco Firepower adaptor:MenloFcStatsHist:truncateOverrun
        managed object property"
    ::= { cfprAdaptorMenloFcStatsHistEntry 24 }

cfprAdaptorMenloFcStatsHistTruncateOverrunDelta OBJECT-TYPE
    SYNTAX       Unsigned64
    MAX-ACCESS   read-only
    STATUS       current
    DESCRIPTION
        "Cisco Firepower adaptor:MenloFcStatsHist:truncateOverrunDelta
        managed object property"
    ::= { cfprAdaptorMenloFcStatsHistEntry 25 }

cfprAdaptorMenloFcStatsHistTruncateOverrunDeltaAvg OBJECT-TYPE
    SYNTAX       Unsigned64
    MAX-ACCESS   read-only
    STATUS       current
    DESCRIPTION
        "Cisco Firepower adaptor:MenloFcStatsHist:truncateOverrunDeltaAvg
        managed object property"
    ::= { cfprAdaptorMenloFcStatsHistEntry 26 }

cfprAdaptorMenloFcStatsHistTruncateOverrunDeltaMax OBJECT-TYPE
    SYNTAX       Unsigned64
    MAX-ACCESS   read-only
    STATUS       current
    DESCRIPTION
        "Cisco Firepower adaptor:MenloFcStatsHist:truncateOverrunDeltaMax
        managed object property"
    ::= { cfprAdaptorMenloFcStatsHistEntry 27 }

cfprAdaptorMenloFcStatsHistTruncateOverrunDeltaMin OBJECT-TYPE
    SYNTAX       Unsigned64
    MAX-ACCESS   read-only
    STATUS       current
    DESCRIPTION
        "Cisco Firepower adaptor:MenloFcStatsHist:truncateOverrunDeltaMin
        managed object property"
    ::= { cfprAdaptorMenloFcStatsHistEntry 28 }

cfprAdaptorMenloHostPortStatsTable OBJECT-TYPE
    SYNTAX           SEQUENCE OF CfprAdaptorMenloHostPortStatsEntry
    MAX-ACCESS       not-accessible
    STATUS           current
    DESCRIPTION
        "Cisco Firepower adaptor:MenloHostPortStats managed object table"
    ::= { cfprAdaptorObjects 94 }

cfprAdaptorMenloHostPortStatsEntry OBJECT-TYPE
    SYNTAX           CfprAdaptorMenloHostPortStatsEntry
    MAX-ACCESS       not-accessible
    STATUS           current
    DESCRIPTION
        "Entry for the cfprAdaptorMenloHostPortStatsTable table."
    INDEX { cfprAdaptorMenloHostPortStatsInstanceId }
    ::= { cfprAdaptorMenloHostPortStatsTable 1 }

CfprAdaptorMenloHostPortStatsEntry ::= SEQUENCE {
    cfprAdaptorMenloHostPortStatsInstanceId                          CfprManagedObjectId,
    cfprAdaptorMenloHostPortStatsDn                                  CfprManagedObjectDn,
    cfprAdaptorMenloHostPortStatsRn                                  SnmpAdminString,
    cfprAdaptorMenloHostPortStatsIntervals                           Gauge32,
    cfprAdaptorMenloHostPortStatsMenloPortIndex                      CfprAdaptorMenloStatsIndex,
    cfprAdaptorMenloHostPortStatsRxPauseCFC                          Unsigned64,
    cfprAdaptorMenloHostPortStatsRxPauseCFCDelta                     Counter64,
    cfprAdaptorMenloHostPortStatsRxPauseCFCDeltaAvg                  Unsigned64,
    cfprAdaptorMenloHostPortStatsRxPauseCFCDeltaMax                  Unsigned64,
    cfprAdaptorMenloHostPortStatsRxPauseCFCDeltaMin                  Unsigned64,
    cfprAdaptorMenloHostPortStatsRxPausePFC                          Unsigned64,
    cfprAdaptorMenloHostPortStatsRxPausePFCDelta                     Counter64,
    cfprAdaptorMenloHostPortStatsRxPausePFCDeltaAvg                  Unsigned64,
    cfprAdaptorMenloHostPortStatsRxPausePFCDeltaMax                  Unsigned64,
    cfprAdaptorMenloHostPortStatsRxPausePFCDeltaMin                  Unsigned64,
    cfprAdaptorMenloHostPortStatsSuspect                             TruthValue,
    cfprAdaptorMenloHostPortStatsThresholded                         CfprAdaptorMenloHostPortStatsThresholded,
    cfprAdaptorMenloHostPortStatsTimeCollected                       DateAndTime,
    cfprAdaptorMenloHostPortStatsTxPauseCFC                          Unsigned64,
    cfprAdaptorMenloHostPortStatsTxPauseCFCDelta                     Counter64,
    cfprAdaptorMenloHostPortStatsTxPauseCFCDeltaAvg                  Unsigned64,
    cfprAdaptorMenloHostPortStatsTxPauseCFCDeltaMax                  Unsigned64,
    cfprAdaptorMenloHostPortStatsTxPauseCFCDeltaMin                  Unsigned64,
    cfprAdaptorMenloHostPortStatsTxPausePFC                          Unsigned64,
    cfprAdaptorMenloHostPortStatsTxPausePFCDelta                     Counter64,
    cfprAdaptorMenloHostPortStatsTxPausePFCDeltaAvg                  Unsigned64,
    cfprAdaptorMenloHostPortStatsTxPausePFCDeltaMax                  Unsigned64,
    cfprAdaptorMenloHostPortStatsTxPausePFCDeltaMin                  Unsigned64,
    cfprAdaptorMenloHostPortStatsUpdate                              Gauge32
}

cfprAdaptorMenloHostPortStatsInstanceId OBJECT-TYPE
    SYNTAX       CfprManagedObjectId
    MAX-ACCESS   not-accessible
    STATUS       current
    DESCRIPTION
        "Instance identifier of the managed object."
    ::= { cfprAdaptorMenloHostPortStatsEntry 1 }

cfprAdaptorMenloHostPortStatsDn OBJECT-TYPE
    SYNTAX       CfprManagedObjectDn
    MAX-ACCESS   read-only
    STATUS       current
    DESCRIPTION
        "Cisco Firepower adaptor:MenloHostPortStats:dn
        managed object property"
    ::= { cfprAdaptorMenloHostPortStatsEntry 2 }

cfprAdaptorMenloHostPortStatsRn OBJECT-TYPE
    SYNTAX       SnmpAdminString
    MAX-ACCESS   read-only
    STATUS       current
    DESCRIPTION
        "Cisco Firepower adaptor:MenloHostPortStats:rn
        managed object property"
    ::= { cfprAdaptorMenloHostPortStatsEntry 3 }

cfprAdaptorMenloHostPortStatsIntervals OBJECT-TYPE
    SYNTAX       Gauge32
    MAX-ACCESS   read-only
    STATUS       current
    DESCRIPTION
        "Cisco Firepower adaptor:MenloHostPortStats:intervals
        managed object property"
    ::= { cfprAdaptorMenloHostPortStatsEntry 4 }

cfprAdaptorMenloHostPortStatsMenloPortIndex OBJECT-TYPE
    SYNTAX       CfprAdaptorMenloStatsIndex
    MAX-ACCESS   read-only
    STATUS       current
    DESCRIPTION
        "Cisco Firepower adaptor:MenloHostPortStats:menloPortIndex
        managed object property"
    ::= { cfprAdaptorMenloHostPortStatsEntry 5 }

cfprAdaptorMenloHostPortStatsRxPauseCFC OBJECT-TYPE
    SYNTAX       Unsigned64
    MAX-ACCESS   read-only
    STATUS       current
    DESCRIPTION
        "Cisco Firepower adaptor:MenloHostPortStats:rxPauseCFC
        managed object property"
    ::= { cfprAdaptorMenloHostPortStatsEntry 6 }

cfprAdaptorMenloHostPortStatsRxPauseCFCDelta OBJECT-TYPE
    SYNTAX       Counter64
    MAX-ACCESS   read-only
    STATUS       current
    DESCRIPTION
        "Cisco Firepower adaptor:MenloHostPortStats:rxPauseCFCDelta
        managed object property"
    ::= { cfprAdaptorMenloHostPortStatsEntry 7 }

cfprAdaptorMenloHostPortStatsRxPauseCFCDeltaAvg OBJECT-TYPE
    SYNTAX       Unsigned64
    MAX-ACCESS   read-only
    STATUS       current
    DESCRIPTION
        "Cisco Firepower adaptor:MenloHostPortStats:rxPauseCFCDeltaAvg
        managed object property"
    ::= { cfprAdaptorMenloHostPortStatsEntry 8 }

cfprAdaptorMenloHostPortStatsRxPauseCFCDeltaMax OBJECT-TYPE
    SYNTAX       Unsigned64
    MAX-ACCESS   read-only
    STATUS       current
    DESCRIPTION
        "Cisco Firepower adaptor:MenloHostPortStats:rxPauseCFCDeltaMax
        managed object property"
    ::= { cfprAdaptorMenloHostPortStatsEntry 9 }

cfprAdaptorMenloHostPortStatsRxPauseCFCDeltaMin OBJECT-TYPE
    SYNTAX       Unsigned64
    MAX-ACCESS   read-only
    STATUS       current
    DESCRIPTION
        "Cisco Firepower adaptor:MenloHostPortStats:rxPauseCFCDeltaMin
        managed object property"
    ::= { cfprAdaptorMenloHostPortStatsEntry 10 }

cfprAdaptorMenloHostPortStatsRxPausePFC OBJECT-TYPE
    SYNTAX       Unsigned64
    MAX-ACCESS   read-only
    STATUS       current
    DESCRIPTION
        "Cisco Firepower adaptor:MenloHostPortStats:rxPausePFC
        managed object property"
    ::= { cfprAdaptorMenloHostPortStatsEntry 11 }

cfprAdaptorMenloHostPortStatsRxPausePFCDelta OBJECT-TYPE
    SYNTAX       Counter64
    MAX-ACCESS   read-only
    STATUS       current
    DESCRIPTION
        "Cisco Firepower adaptor:MenloHostPortStats:rxPausePFCDelta
        managed object property"
    ::= { cfprAdaptorMenloHostPortStatsEntry 12 }

cfprAdaptorMenloHostPortStatsRxPausePFCDeltaAvg OBJECT-TYPE
    SYNTAX       Unsigned64
    MAX-ACCESS   read-only
    STATUS       current
    DESCRIPTION
        "Cisco Firepower adaptor:MenloHostPortStats:rxPausePFCDeltaAvg
        managed object property"
    ::= { cfprAdaptorMenloHostPortStatsEntry 13 }

cfprAdaptorMenloHostPortStatsRxPausePFCDeltaMax OBJECT-TYPE
    SYNTAX       Unsigned64
    MAX-ACCESS   read-only
    STATUS       current
    DESCRIPTION
        "Cisco Firepower adaptor:MenloHostPortStats:rxPausePFCDeltaMax
        managed object property"
    ::= { cfprAdaptorMenloHostPortStatsEntry 14 }

cfprAdaptorMenloHostPortStatsRxPausePFCDeltaMin OBJECT-TYPE
    SYNTAX       Unsigned64
    MAX-ACCESS   read-only
    STATUS       current
    DESCRIPTION
        "Cisco Firepower adaptor:MenloHostPortStats:rxPausePFCDeltaMin
        managed object property"
    ::= { cfprAdaptorMenloHostPortStatsEntry 15 }

cfprAdaptorMenloHostPortStatsSuspect OBJECT-TYPE
    SYNTAX       TruthValue
    MAX-ACCESS   read-only
    STATUS       current
    DESCRIPTION
        "Cisco Firepower adaptor:MenloHostPortStats:suspect
        managed object property"
    ::= { cfprAdaptorMenloHostPortStatsEntry 16 }

cfprAdaptorMenloHostPortStatsThresholded OBJECT-TYPE
    SYNTAX       CfprAdaptorMenloHostPortStatsThresholded
    MAX-ACCESS   read-only
    STATUS       current
    DESCRIPTION
        "Cisco Firepower adaptor:MenloHostPortStats:thresholded
        managed object property"
    ::= { cfprAdaptorMenloHostPortStatsEntry 17 }

cfprAdaptorMenloHostPortStatsTimeCollected OBJECT-TYPE
    SYNTAX       DateAndTime
    MAX-ACCESS   read-only
    STATUS       current
    DESCRIPTION
        "Cisco Firepower adaptor:MenloHostPortStats:timeCollected
        managed object property"
    ::= { cfprAdaptorMenloHostPortStatsEntry 18 }

cfprAdaptorMenloHostPortStatsTxPauseCFC OBJECT-TYPE
    SYNTAX       Unsigned64
    MAX-ACCESS   read-only
    STATUS       current
    DESCRIPTION
        "Cisco Firepower adaptor:MenloHostPortStats:txPauseCFC
        managed object property"
    ::= { cfprAdaptorMenloHostPortStatsEntry 19 }

cfprAdaptorMenloHostPortStatsTxPauseCFCDelta OBJECT-TYPE
    SYNTAX       Counter64
    MAX-ACCESS   read-only
    STATUS       current
    DESCRIPTION
        "Cisco Firepower adaptor:MenloHostPortStats:txPauseCFCDelta
        managed object property"
    ::= { cfprAdaptorMenloHostPortStatsEntry 20 }

cfprAdaptorMenloHostPortStatsTxPauseCFCDeltaAvg OBJECT-TYPE
    SYNTAX       Unsigned64
    MAX-ACCESS   read-only
    STATUS       current
    DESCRIPTION
        "Cisco Firepower adaptor:MenloHostPortStats:txPauseCFCDeltaAvg
        managed object property"
    ::= { cfprAdaptorMenloHostPortStatsEntry 21 }

cfprAdaptorMenloHostPortStatsTxPauseCFCDeltaMax OBJECT-TYPE
    SYNTAX       Unsigned64
    MAX-ACCESS   read-only
    STATUS       current
    DESCRIPTION
        "Cisco Firepower adaptor:MenloHostPortStats:txPauseCFCDeltaMax
        managed object property"
    ::= { cfprAdaptorMenloHostPortStatsEntry 22 }

cfprAdaptorMenloHostPortStatsTxPauseCFCDeltaMin OBJECT-TYPE
    SYNTAX       Unsigned64
    MAX-ACCESS   read-only
    STATUS       current
    DESCRIPTION
        "Cisco Firepower adaptor:MenloHostPortStats:txPauseCFCDeltaMin
        managed object property"
    ::= { cfprAdaptorMenloHostPortStatsEntry 23 }

cfprAdaptorMenloHostPortStatsTxPausePFC OBJECT-TYPE
    SYNTAX       Unsigned64
    MAX-ACCESS   read-only
    STATUS       current
    DESCRIPTION
        "Cisco Firepower adaptor:MenloHostPortStats:txPausePFC
        managed object property"
    ::= { cfprAdaptorMenloHostPortStatsEntry 24 }

cfprAdaptorMenloHostPortStatsTxPausePFCDelta OBJECT-TYPE
    SYNTAX       Counter64
    MAX-ACCESS   read-only
    STATUS       current
    DESCRIPTION
        "Cisco Firepower adaptor:MenloHostPortStats:txPausePFCDelta
        managed object property"
    ::= { cfprAdaptorMenloHostPortStatsEntry 25 }

cfprAdaptorMenloHostPortStatsTxPausePFCDeltaAvg OBJECT-TYPE
    SYNTAX       Unsigned64
    MAX-ACCESS   read-only
    STATUS       current
    DESCRIPTION
        "Cisco Firepower adaptor:MenloHostPortStats:txPausePFCDeltaAvg
        managed object property"
    ::= { cfprAdaptorMenloHostPortStatsEntry 26 }

cfprAdaptorMenloHostPortStatsTxPausePFCDeltaMax OBJECT-TYPE
    SYNTAX       Unsigned64
    MAX-ACCESS   read-only
    STATUS       current
    DESCRIPTION
        "Cisco Firepower adaptor:MenloHostPortStats:txPausePFCDeltaMax
        managed object property"
    ::= { cfprAdaptorMenloHostPortStatsEntry 27 }

cfprAdaptorMenloHostPortStatsTxPausePFCDeltaMin OBJECT-TYPE
    SYNTAX       Unsigned64
    MAX-ACCESS   read-only
    STATUS       current
    DESCRIPTION
        "Cisco Firepower adaptor:MenloHostPortStats:txPausePFCDeltaMin
        managed object property"
    ::= { cfprAdaptorMenloHostPortStatsEntry 28 }

cfprAdaptorMenloHostPortStatsUpdate OBJECT-TYPE
    SYNTAX       Gauge32
    MAX-ACCESS   read-only
    STATUS       current
    DESCRIPTION
        "Cisco Firepower adaptor:MenloHostPortStats:update
        managed object property"
    ::= { cfprAdaptorMenloHostPortStatsEntry 29 }

cfprAdaptorMenloHostPortStatsHistTable OBJECT-TYPE
    SYNTAX           SEQUENCE OF CfprAdaptorMenloHostPortStatsHistEntry
    MAX-ACCESS       not-accessible
    STATUS           current
    DESCRIPTION
        "Cisco Firepower adaptor:MenloHostPortStatsHist
        managed object table"
    ::= { cfprAdaptorObjects 95 }

cfprAdaptorMenloHostPortStatsHistEntry OBJECT-TYPE
    SYNTAX           CfprAdaptorMenloHostPortStatsHistEntry
    MAX-ACCESS       not-accessible
    STATUS           current
    DESCRIPTION
        "Entry for the cfprAdaptorMenloHostPortStatsHistTable table."
    INDEX { cfprAdaptorMenloHostPortStatsHistInstanceId }
    ::= { cfprAdaptorMenloHostPortStatsHistTable 1 }

CfprAdaptorMenloHostPortStatsHistEntry ::= SEQUENCE {
    cfprAdaptorMenloHostPortStatsHistInstanceId                      CfprManagedObjectId,
    cfprAdaptorMenloHostPortStatsHistDn                              CfprManagedObjectDn,
    cfprAdaptorMenloHostPortStatsHistRn                              SnmpAdminString,
    cfprAdaptorMenloHostPortStatsHistId                              Unsigned64,
    cfprAdaptorMenloHostPortStatsHistMostRecent                      TruthValue,
    cfprAdaptorMenloHostPortStatsHistRxPauseCFC                      Unsigned64,
    cfprAdaptorMenloHostPortStatsHistRxPauseCFCDelta                 Unsigned64,
    cfprAdaptorMenloHostPortStatsHistRxPauseCFCDeltaAvg              Unsigned64,
    cfprAdaptorMenloHostPortStatsHistRxPauseCFCDeltaMax              Unsigned64,
    cfprAdaptorMenloHostPortStatsHistRxPauseCFCDeltaMin              Unsigned64,
    cfprAdaptorMenloHostPortStatsHistRxPausePFC                      Unsigned64,
    cfprAdaptorMenloHostPortStatsHistRxPausePFCDelta                 Unsigned64,
    cfprAdaptorMenloHostPortStatsHistRxPausePFCDeltaAvg              Unsigned64,
    cfprAdaptorMenloHostPortStatsHistRxPausePFCDeltaMax              Unsigned64,
    cfprAdaptorMenloHostPortStatsHistRxPausePFCDeltaMin              Unsigned64,
    cfprAdaptorMenloHostPortStatsHistSuspect                         TruthValue,
    cfprAdaptorMenloHostPortStatsHistThresholded                     CfprAdaptorMenloHostPortStatsHistThresholded,
    cfprAdaptorMenloHostPortStatsHistTimeCollected                   DateAndTime,
    cfprAdaptorMenloHostPortStatsHistTxPauseCFC                      Unsigned64,
    cfprAdaptorMenloHostPortStatsHistTxPauseCFCDelta                 Unsigned64,
    cfprAdaptorMenloHostPortStatsHistTxPauseCFCDeltaAvg              Unsigned64,
    cfprAdaptorMenloHostPortStatsHistTxPauseCFCDeltaMax              Unsigned64,
    cfprAdaptorMenloHostPortStatsHistTxPauseCFCDeltaMin              Unsigned64,
    cfprAdaptorMenloHostPortStatsHistTxPausePFC                      Unsigned64,
    cfprAdaptorMenloHostPortStatsHistTxPausePFCDelta                 Unsigned64,
    cfprAdaptorMenloHostPortStatsHistTxPausePFCDeltaAvg              Unsigned64,
    cfprAdaptorMenloHostPortStatsHistTxPausePFCDeltaMax              Unsigned64,
    cfprAdaptorMenloHostPortStatsHistTxPausePFCDeltaMin              Unsigned64
}

cfprAdaptorMenloHostPortStatsHistInstanceId OBJECT-TYPE
    SYNTAX       CfprManagedObjectId
    MAX-ACCESS   not-accessible
    STATUS       current
    DESCRIPTION
        "Instance identifier of the managed object."
    ::= { cfprAdaptorMenloHostPortStatsHistEntry 1 }

cfprAdaptorMenloHostPortStatsHistDn OBJECT-TYPE
    SYNTAX       CfprManagedObjectDn
    MAX-ACCESS   read-only
    STATUS       current
    DESCRIPTION
        "Cisco Firepower adaptor:MenloHostPortStatsHist:dn
        managed object property"
    ::= { cfprAdaptorMenloHostPortStatsHistEntry 2 }

cfprAdaptorMenloHostPortStatsHistRn OBJECT-TYPE
    SYNTAX       SnmpAdminString
    MAX-ACCESS   read-only
    STATUS       current
    DESCRIPTION
        "Cisco Firepower adaptor:MenloHostPortStatsHist:rn
        managed object property"
    ::= { cfprAdaptorMenloHostPortStatsHistEntry 3 }

cfprAdaptorMenloHostPortStatsHistId OBJECT-TYPE
    SYNTAX       Unsigned64
    MAX-ACCESS   read-only
    STATUS       current
    DESCRIPTION
        "Cisco Firepower adaptor:MenloHostPortStatsHist:id
        managed object property"
    ::= { cfprAdaptorMenloHostPortStatsHistEntry 4 }

cfprAdaptorMenloHostPortStatsHistMostRecent OBJECT-TYPE
    SYNTAX       TruthValue
    MAX-ACCESS   read-only
    STATUS       current
    DESCRIPTION
        "Cisco Firepower adaptor:MenloHostPortStatsHist:mostRecent
        managed object property"
    ::= { cfprAdaptorMenloHostPortStatsHistEntry 5 }

cfprAdaptorMenloHostPortStatsHistRxPauseCFC OBJECT-TYPE
    SYNTAX       Unsigned64
    MAX-ACCESS   read-only
    STATUS       current
    DESCRIPTION
        "Cisco Firepower adaptor:MenloHostPortStatsHist:rxPauseCFC
        managed object property"
    ::= { cfprAdaptorMenloHostPortStatsHistEntry 6 }

cfprAdaptorMenloHostPortStatsHistRxPauseCFCDelta OBJECT-TYPE
    SYNTAX       Unsigned64
    MAX-ACCESS   read-only
    STATUS       current
    DESCRIPTION
        "Cisco Firepower adaptor:MenloHostPortStatsHist:rxPauseCFCDelta
        managed object property"
    ::= { cfprAdaptorMenloHostPortStatsHistEntry 7 }

cfprAdaptorMenloHostPortStatsHistRxPauseCFCDeltaAvg OBJECT-TYPE
    SYNTAX       Unsigned64
    MAX-ACCESS   read-only
    STATUS       current
    DESCRIPTION
        "Cisco Firepower adaptor:MenloHostPortStatsHist:rxPauseCFCDeltaAvg
         managed object property"
    ::= { cfprAdaptorMenloHostPortStatsHistEntry 8 }

cfprAdaptorMenloHostPortStatsHistRxPauseCFCDeltaMax OBJECT-TYPE
    SYNTAX       Unsigned64
    MAX-ACCESS   read-only
    STATUS       current
    DESCRIPTION
        "Cisco Firepower adaptor:MenloHostPortStatsHist:rxPauseCFCDeltaMax
         managed object property"
    ::= { cfprAdaptorMenloHostPortStatsHistEntry 9 }

cfprAdaptorMenloHostPortStatsHistRxPauseCFCDeltaMin OBJECT-TYPE
    SYNTAX       Unsigned64
    MAX-ACCESS   read-only
    STATUS       current
    DESCRIPTION
        "Cisco Firepower adaptor:MenloHostPortStatsHist:rxPauseCFCDeltaMin
         managed object property"
    ::= { cfprAdaptorMenloHostPortStatsHistEntry 10 }

cfprAdaptorMenloHostPortStatsHistRxPausePFC OBJECT-TYPE
    SYNTAX       Unsigned64
    MAX-ACCESS   read-only
    STATUS       current
    DESCRIPTION
        "Cisco Firepower adaptor:MenloHostPortStatsHist:rxPausePFC
        managed object property"
    ::= { cfprAdaptorMenloHostPortStatsHistEntry 11 }

cfprAdaptorMenloHostPortStatsHistRxPausePFCDelta OBJECT-TYPE
    SYNTAX       Unsigned64
    MAX-ACCESS   read-only
    STATUS       current
    DESCRIPTION
        "Cisco Firepower adaptor:MenloHostPortStatsHist:rxPausePFCDelta
        managed object property"
    ::= { cfprAdaptorMenloHostPortStatsHistEntry 12 }

cfprAdaptorMenloHostPortStatsHistRxPausePFCDeltaAvg OBJECT-TYPE
    SYNTAX       Unsigned64
    MAX-ACCESS   read-only
    STATUS       current
    DESCRIPTION
        "Cisco Firepower adaptor:MenloHostPortStatsHist:rxPausePFCDeltaAvg
         managed object property"
    ::= { cfprAdaptorMenloHostPortStatsHistEntry 13 }

cfprAdaptorMenloHostPortStatsHistRxPausePFCDeltaMax OBJECT-TYPE
    SYNTAX       Unsigned64
    MAX-ACCESS   read-only
    STATUS       current
    DESCRIPTION
        "Cisco Firepower adaptor:MenloHostPortStatsHist:rxPausePFCDeltaMax
         managed object property"
    ::= { cfprAdaptorMenloHostPortStatsHistEntry 14 }

cfprAdaptorMenloHostPortStatsHistRxPausePFCDeltaMin OBJECT-TYPE
    SYNTAX       Unsigned64
    MAX-ACCESS   read-only
    STATUS       current
    DESCRIPTION
        "Cisco Firepower adaptor:MenloHostPortStatsHist:rxPausePFCDeltaMin
         managed object property"
    ::= { cfprAdaptorMenloHostPortStatsHistEntry 15 }

cfprAdaptorMenloHostPortStatsHistSuspect OBJECT-TYPE
    SYNTAX       TruthValue
    MAX-ACCESS   read-only
    STATUS       current
    DESCRIPTION
        "Cisco Firepower adaptor:MenloHostPortStatsHist:suspect
        managed object property"
    ::= { cfprAdaptorMenloHostPortStatsHistEntry 16 }

cfprAdaptorMenloHostPortStatsHistThresholded OBJECT-TYPE
    SYNTAX       CfprAdaptorMenloHostPortStatsHistThresholded
    MAX-ACCESS   read-only
    STATUS       current
    DESCRIPTION
        "Cisco Firepower adaptor:MenloHostPortStatsHist:thresholded
        managed object property"
    ::= { cfprAdaptorMenloHostPortStatsHistEntry 17 }

cfprAdaptorMenloHostPortStatsHistTimeCollected OBJECT-TYPE
    SYNTAX       DateAndTime
    MAX-ACCESS   read-only
    STATUS       current
    DESCRIPTION
        "Cisco Firepower adaptor:MenloHostPortStatsHist:timeCollected
        managed object property"
    ::= { cfprAdaptorMenloHostPortStatsHistEntry 18 }

cfprAdaptorMenloHostPortStatsHistTxPauseCFC OBJECT-TYPE
    SYNTAX       Unsigned64
    MAX-ACCESS   read-only
    STATUS       current
    DESCRIPTION
        "Cisco Firepower adaptor:MenloHostPortStatsHist:txPauseCFC
        managed object property"
    ::= { cfprAdaptorMenloHostPortStatsHistEntry 19 }

cfprAdaptorMenloHostPortStatsHistTxPauseCFCDelta OBJECT-TYPE
    SYNTAX       Unsigned64
    MAX-ACCESS   read-only
    STATUS       current
    DESCRIPTION
        "Cisco Firepower adaptor:MenloHostPortStatsHist:txPauseCFCDelta
        managed object property"
    ::= { cfprAdaptorMenloHostPortStatsHistEntry 20 }

cfprAdaptorMenloHostPortStatsHistTxPauseCFCDeltaAvg OBJECT-TYPE
    SYNTAX       Unsigned64
    MAX-ACCESS   read-only
    STATUS       current
    DESCRIPTION
        "Cisco Firepower adaptor:MenloHostPortStatsHist:txPauseCFCDeltaAvg
         managed object property"
    ::= { cfprAdaptorMenloHostPortStatsHistEntry 21 }

cfprAdaptorMenloHostPortStatsHistTxPauseCFCDeltaMax OBJECT-TYPE
    SYNTAX       Unsigned64
    MAX-ACCESS   read-only
    STATUS       current
    DESCRIPTION
        "Cisco Firepower adaptor:MenloHostPortStatsHist:txPauseCFCDeltaMax
         managed object property"
    ::= { cfprAdaptorMenloHostPortStatsHistEntry 22 }

cfprAdaptorMenloHostPortStatsHistTxPauseCFCDeltaMin OBJECT-TYPE
    SYNTAX       Unsigned64
    MAX-ACCESS   read-only
    STATUS       current
    DESCRIPTION
        "Cisco Firepower adaptor:MenloHostPortStatsHist:txPauseCFCDeltaMin
         managed object property"
    ::= { cfprAdaptorMenloHostPortStatsHistEntry 23 }

cfprAdaptorMenloHostPortStatsHistTxPausePFC OBJECT-TYPE
    SYNTAX       Unsigned64
    MAX-ACCESS   read-only
    STATUS       current
    DESCRIPTION
        "Cisco Firepower adaptor:MenloHostPortStatsHist:txPausePFC
        managed object property"
    ::= { cfprAdaptorMenloHostPortStatsHistEntry 24 }

cfprAdaptorMenloHostPortStatsHistTxPausePFCDelta OBJECT-TYPE
    SYNTAX       Unsigned64
    MAX-ACCESS   read-only
    STATUS       current
    DESCRIPTION
        "Cisco Firepower adaptor:MenloHostPortStatsHist:txPausePFCDelta
        managed object property"
    ::= { cfprAdaptorMenloHostPortStatsHistEntry 25 }

cfprAdaptorMenloHostPortStatsHistTxPausePFCDeltaAvg OBJECT-TYPE
    SYNTAX       Unsigned64
    MAX-ACCESS   read-only
    STATUS       current
    DESCRIPTION
        "Cisco Firepower adaptor:MenloHostPortStatsHist:txPausePFCDeltaAvg
         managed object property"
    ::= { cfprAdaptorMenloHostPortStatsHistEntry 26 }

cfprAdaptorMenloHostPortStatsHistTxPausePFCDeltaMax OBJECT-TYPE
    SYNTAX       Unsigned64
    MAX-ACCESS   read-only
    STATUS       current
    DESCRIPTION
        "Cisco Firepower adaptor:MenloHostPortStatsHist:txPausePFCDeltaMax
         managed object property"
    ::= { cfprAdaptorMenloHostPortStatsHistEntry 27 }

cfprAdaptorMenloHostPortStatsHistTxPausePFCDeltaMin OBJECT-TYPE
    SYNTAX       Unsigned64
    MAX-ACCESS   read-only
    STATUS       current
    DESCRIPTION
        "Cisco Firepower adaptor:MenloHostPortStatsHist:txPausePFCDeltaMin
         managed object property"
    ::= { cfprAdaptorMenloHostPortStatsHistEntry 28 }

cfprAdaptorMenloMcpuErrorStatsTable OBJECT-TYPE
    SYNTAX           SEQUENCE OF CfprAdaptorMenloMcpuErrorStatsEntry
    MAX-ACCESS       not-accessible
    STATUS           current
    DESCRIPTION
        "Cisco Firepower adaptor:MenloMcpuErrorStats managed object table"
    ::= { cfprAdaptorObjects 96 }

cfprAdaptorMenloMcpuErrorStatsEntry OBJECT-TYPE
    SYNTAX           CfprAdaptorMenloMcpuErrorStatsEntry
    MAX-ACCESS       not-accessible
    STATUS           current
    DESCRIPTION
        "Entry for the cfprAdaptorMenloMcpuErrorStatsTable table."
    INDEX { cfprAdaptorMenloMcpuErrorStatsInstanceId }
    ::= { cfprAdaptorMenloMcpuErrorStatsTable 1 }

CfprAdaptorMenloMcpuErrorStatsEntry ::= SEQUENCE {
    cfprAdaptorMenloMcpuErrorStatsInstanceId                         CfprManagedObjectId,
    cfprAdaptorMenloMcpuErrorStatsDn                                 CfprManagedObjectDn,
    cfprAdaptorMenloMcpuErrorStatsRn                                 SnmpAdminString,
    cfprAdaptorMenloMcpuErrorStatsCorrectableErrors                  Unsigned64,
    cfprAdaptorMenloMcpuErrorStatsCorrectableErrorsDelta             Counter64,
    cfprAdaptorMenloMcpuErrorStatsCorrectableErrorsDeltaAvg          Unsigned64,
    cfprAdaptorMenloMcpuErrorStatsCorrectableErrorsDeltaMax          Unsigned64,
    cfprAdaptorMenloMcpuErrorStatsCorrectableErrorsDeltaMin          Unsigned64,
    cfprAdaptorMenloMcpuErrorStatsIntervals                          Gauge32,
    cfprAdaptorMenloMcpuErrorStatsMenloMcpuIndex                     CfprAdaptorMenloStatsIndex,
    cfprAdaptorMenloMcpuErrorStatsPopErrors                          Unsigned64,
    cfprAdaptorMenloMcpuErrorStatsPopErrorsDelta                     Counter64,
    cfprAdaptorMenloMcpuErrorStatsPopErrorsDeltaAvg                  Unsigned64,
    cfprAdaptorMenloMcpuErrorStatsPopErrorsDeltaMax                  Unsigned64,
    cfprAdaptorMenloMcpuErrorStatsPopErrorsDeltaMin                  Unsigned64,
    cfprAdaptorMenloMcpuErrorStatsPushErrors                         Unsigned64,
    cfprAdaptorMenloMcpuErrorStatsPushErrorsDelta                    Counter64,
    cfprAdaptorMenloMcpuErrorStatsPushErrorsDeltaAvg                 Unsigned64,
    cfprAdaptorMenloMcpuErrorStatsPushErrorsDeltaMax                 Unsigned64,
    cfprAdaptorMenloMcpuErrorStatsPushErrorsDeltaMin                 Unsigned64,
    cfprAdaptorMenloMcpuErrorStatsSuspect                            TruthValue,
    cfprAdaptorMenloMcpuErrorStatsThresholded                        CfprAdaptorMenloMcpuErrorStatsThresholded,
    cfprAdaptorMenloMcpuErrorStatsTimeCollected                      DateAndTime,
    cfprAdaptorMenloMcpuErrorStatsUncorrectableErrors                Unsigned64,
    cfprAdaptorMenloMcpuErrorStatsUncorrectableErrorsDelta           Counter64,
    cfprAdaptorMenloMcpuErrorStatsUncorrectableErrorsDeltaAvg        Unsigned64,
    cfprAdaptorMenloMcpuErrorStatsUncorrectableErrorsDeltaMax        Unsigned64,
    cfprAdaptorMenloMcpuErrorStatsUncorrectableErrorsDeltaMin        Unsigned64,
    cfprAdaptorMenloMcpuErrorStatsUpdate                             Gauge32
}

cfprAdaptorMenloMcpuErrorStatsInstanceId OBJECT-TYPE
    SYNTAX       CfprManagedObjectId
    MAX-ACCESS   not-accessible
    STATUS       current
    DESCRIPTION
        "Instance identifier of the managed object."
    ::= { cfprAdaptorMenloMcpuErrorStatsEntry 1 }

cfprAdaptorMenloMcpuErrorStatsDn OBJECT-TYPE
    SYNTAX       CfprManagedObjectDn
    MAX-ACCESS   read-only
    STATUS       current
    DESCRIPTION
        "Cisco Firepower adaptor:MenloMcpuErrorStats:dn
        managed object property"
    ::= { cfprAdaptorMenloMcpuErrorStatsEntry 2 }

cfprAdaptorMenloMcpuErrorStatsRn OBJECT-TYPE
    SYNTAX       SnmpAdminString
    MAX-ACCESS   read-only
    STATUS       current
    DESCRIPTION
        "Cisco Firepower adaptor:MenloMcpuErrorStats:rn
        managed object property"
    ::= { cfprAdaptorMenloMcpuErrorStatsEntry 3 }

cfprAdaptorMenloMcpuErrorStatsCorrectableErrors OBJECT-TYPE
    SYNTAX       Unsigned64
    MAX-ACCESS   read-only
    STATUS       current
    DESCRIPTION
        "Cisco Firepower adaptor:MenloMcpuErrorStats:correctableErrors
        managed object property"
    ::= { cfprAdaptorMenloMcpuErrorStatsEntry 4 }

cfprAdaptorMenloMcpuErrorStatsCorrectableErrorsDelta OBJECT-TYPE
    SYNTAX       Counter64
    MAX-ACCESS   read-only
    STATUS       current
    DESCRIPTION
        "Cisco Firepower adaptor:MenloMcpuErrorStats:correctableErrorsDelt
        a managed object property"
    ::= { cfprAdaptorMenloMcpuErrorStatsEntry 5 }

cfprAdaptorMenloMcpuErrorStatsCorrectableErrorsDeltaAvg OBJECT-TYPE
    SYNTAX       Unsigned64
    MAX-ACCESS   read-only
    STATUS       current
    DESCRIPTION
        "Cisco Firepower adaptor:MenloMcpuErrorStats:correctableErrorsDelt
        aAvg managed object property"
    ::= { cfprAdaptorMenloMcpuErrorStatsEntry 6 }

cfprAdaptorMenloMcpuErrorStatsCorrectableErrorsDeltaMax OBJECT-TYPE
    SYNTAX       Unsigned64
    MAX-ACCESS   read-only
    STATUS       current
    DESCRIPTION
        "Cisco Firepower adaptor:MenloMcpuErrorStats:correctableErrorsDelt
        aMax managed object property"
    ::= { cfprAdaptorMenloMcpuErrorStatsEntry 7 }

cfprAdaptorMenloMcpuErrorStatsCorrectableErrorsDeltaMin OBJECT-TYPE
    SYNTAX       Unsigned64
    MAX-ACCESS   read-only
    STATUS       current
    DESCRIPTION
        "Cisco Firepower adaptor:MenloMcpuErrorStats:correctableErrorsDelt
        aMin managed object property"
    ::= { cfprAdaptorMenloMcpuErrorStatsEntry 8 }

cfprAdaptorMenloMcpuErrorStatsIntervals OBJECT-TYPE
    SYNTAX       Gauge32
    MAX-ACCESS   read-only
    STATUS       current
    DESCRIPTION
        "Cisco Firepower adaptor:MenloMcpuErrorStats:intervals
        managed object property"
    ::= { cfprAdaptorMenloMcpuErrorStatsEntry 9 }

cfprAdaptorMenloMcpuErrorStatsMenloMcpuIndex OBJECT-TYPE
    SYNTAX       CfprAdaptorMenloStatsIndex
    MAX-ACCESS   read-only
    STATUS       current
    DESCRIPTION
        "Cisco Firepower adaptor:MenloMcpuErrorStats:menloMcpuIndex
        managed object property"
    ::= { cfprAdaptorMenloMcpuErrorStatsEntry 10 }

cfprAdaptorMenloMcpuErrorStatsPopErrors OBJECT-TYPE
    SYNTAX       Unsigned64
    MAX-ACCESS   read-only
    STATUS       current
    DESCRIPTION
        "Cisco Firepower adaptor:MenloMcpuErrorStats:popErrors
        managed object property"
    ::= { cfprAdaptorMenloMcpuErrorStatsEntry 11 }

cfprAdaptorMenloMcpuErrorStatsPopErrorsDelta OBJECT-TYPE
    SYNTAX       Counter64
    MAX-ACCESS   read-only
    STATUS       current
    DESCRIPTION
        "Cisco Firepower adaptor:MenloMcpuErrorStats:popErrorsDelta
        managed object property"
    ::= { cfprAdaptorMenloMcpuErrorStatsEntry 12 }

cfprAdaptorMenloMcpuErrorStatsPopErrorsDeltaAvg OBJECT-TYPE
    SYNTAX       Unsigned64
    MAX-ACCESS   read-only
    STATUS       current
    DESCRIPTION
        "Cisco Firepower adaptor:MenloMcpuErrorStats:popErrorsDeltaAvg
        managed object property"
    ::= { cfprAdaptorMenloMcpuErrorStatsEntry 13 }

cfprAdaptorMenloMcpuErrorStatsPopErrorsDeltaMax OBJECT-TYPE
    SYNTAX       Unsigned64
    MAX-ACCESS   read-only
    STATUS       current
    DESCRIPTION
        "Cisco Firepower adaptor:MenloMcpuErrorStats:popErrorsDeltaMax
        managed object property"
    ::= { cfprAdaptorMenloMcpuErrorStatsEntry 14 }

cfprAdaptorMenloMcpuErrorStatsPopErrorsDeltaMin OBJECT-TYPE
    SYNTAX       Unsigned64
    MAX-ACCESS   read-only
    STATUS       current
    DESCRIPTION
        "Cisco Firepower adaptor:MenloMcpuErrorStats:popErrorsDeltaMin
        managed object property"
    ::= { cfprAdaptorMenloMcpuErrorStatsEntry 15 }

cfprAdaptorMenloMcpuErrorStatsPushErrors OBJECT-TYPE
    SYNTAX       Unsigned64
    MAX-ACCESS   read-only
    STATUS       current
    DESCRIPTION
        "Cisco Firepower adaptor:MenloMcpuErrorStats:pushErrors
        managed object property"
    ::= { cfprAdaptorMenloMcpuErrorStatsEntry 16 }

cfprAdaptorMenloMcpuErrorStatsPushErrorsDelta OBJECT-TYPE
    SYNTAX       Counter64
    MAX-ACCESS   read-only
    STATUS       current
    DESCRIPTION
        "Cisco Firepower adaptor:MenloMcpuErrorStats:pushErrorsDelta
        managed object property"
    ::= { cfprAdaptorMenloMcpuErrorStatsEntry 17 }

cfprAdaptorMenloMcpuErrorStatsPushErrorsDeltaAvg OBJECT-TYPE
    SYNTAX       Unsigned64
    MAX-ACCESS   read-only
    STATUS       current
    DESCRIPTION
        "Cisco Firepower adaptor:MenloMcpuErrorStats:pushErrorsDeltaAvg
        managed object property"
    ::= { cfprAdaptorMenloMcpuErrorStatsEntry 18 }

cfprAdaptorMenloMcpuErrorStatsPushErrorsDeltaMax OBJECT-TYPE
    SYNTAX       Unsigned64
    MAX-ACCESS   read-only
    STATUS       current
    DESCRIPTION
        "Cisco Firepower adaptor:MenloMcpuErrorStats:pushErrorsDeltaMax
        managed object property"
    ::= { cfprAdaptorMenloMcpuErrorStatsEntry 19 }

cfprAdaptorMenloMcpuErrorStatsPushErrorsDeltaMin OBJECT-TYPE
    SYNTAX       Unsigned64
    MAX-ACCESS   read-only
    STATUS       current
    DESCRIPTION
        "Cisco Firepower adaptor:MenloMcpuErrorStats:pushErrorsDeltaMin
        managed object property"
    ::= { cfprAdaptorMenloMcpuErrorStatsEntry 20 }

cfprAdaptorMenloMcpuErrorStatsSuspect OBJECT-TYPE
    SYNTAX       TruthValue
    MAX-ACCESS   read-only
    STATUS       current
    DESCRIPTION
        "Cisco Firepower adaptor:MenloMcpuErrorStats:suspect
        managed object property"
    ::= { cfprAdaptorMenloMcpuErrorStatsEntry 21 }

cfprAdaptorMenloMcpuErrorStatsThresholded OBJECT-TYPE
    SYNTAX       CfprAdaptorMenloMcpuErrorStatsThresholded
    MAX-ACCESS   read-only
    STATUS       current
    DESCRIPTION
        "Cisco Firepower adaptor:MenloMcpuErrorStats:thresholded
        managed object property"
    ::= { cfprAdaptorMenloMcpuErrorStatsEntry 22 }

cfprAdaptorMenloMcpuErrorStatsTimeCollected OBJECT-TYPE
    SYNTAX       DateAndTime
    MAX-ACCESS   read-only
    STATUS       current
    DESCRIPTION
        "Cisco Firepower adaptor:MenloMcpuErrorStats:timeCollected
        managed object property"
    ::= { cfprAdaptorMenloMcpuErrorStatsEntry 23 }

cfprAdaptorMenloMcpuErrorStatsUncorrectableErrors OBJECT-TYPE
    SYNTAX       Unsigned64
    MAX-ACCESS   read-only
    STATUS       current
    DESCRIPTION
        "Cisco Firepower adaptor:MenloMcpuErrorStats:uncorrectableErrors
        managed object property"
    ::= { cfprAdaptorMenloMcpuErrorStatsEntry 24 }

cfprAdaptorMenloMcpuErrorStatsUncorrectableErrorsDelta OBJECT-TYPE
    SYNTAX       Counter64
    MAX-ACCESS   read-only
    STATUS       current
    DESCRIPTION
        "Cisco Firepower adaptor:MenloMcpuErrorStats:uncorrectableErrorsDe
        lta managed object property"
    ::= { cfprAdaptorMenloMcpuErrorStatsEntry 25 }

cfprAdaptorMenloMcpuErrorStatsUncorrectableErrorsDeltaAvg OBJECT-TYPE
    SYNTAX       Unsigned64
    MAX-ACCESS   read-only
    STATUS       current
    DESCRIPTION
        "Cisco Firepower adaptor:MenloMcpuErrorStats:uncorrectableErrorsDe
        ltaAvg managed object property"
    ::= { cfprAdaptorMenloMcpuErrorStatsEntry 26 }

cfprAdaptorMenloMcpuErrorStatsUncorrectableErrorsDeltaMax OBJECT-TYPE
    SYNTAX       Unsigned64
    MAX-ACCESS   read-only
    STATUS       current
    DESCRIPTION
        "Cisco Firepower adaptor:MenloMcpuErrorStats:uncorrectableErrorsDe
        ltaMax managed object property"
    ::= { cfprAdaptorMenloMcpuErrorStatsEntry 27 }

cfprAdaptorMenloMcpuErrorStatsUncorrectableErrorsDeltaMin OBJECT-TYPE
    SYNTAX       Unsigned64
    MAX-ACCESS   read-only
    STATUS       current
    DESCRIPTION
        "Cisco Firepower adaptor:MenloMcpuErrorStats:uncorrectableErrorsDe
        ltaMin managed object property"
    ::= { cfprAdaptorMenloMcpuErrorStatsEntry 28 }

cfprAdaptorMenloMcpuErrorStatsUpdate OBJECT-TYPE
    SYNTAX       Gauge32
    MAX-ACCESS   read-only
    STATUS       current
    DESCRIPTION
        "Cisco Firepower adaptor:MenloMcpuErrorStats:update
        managed object property"
    ::= { cfprAdaptorMenloMcpuErrorStatsEntry 29 }

cfprAdaptorMenloMcpuErrorStatsHistTable OBJECT-TYPE
    SYNTAX           SEQUENCE OF CfprAdaptorMenloMcpuErrorStatsHistEntry
    MAX-ACCESS       not-accessible
    STATUS           current
    DESCRIPTION
        "Cisco Firepower adaptor:MenloMcpuErrorStatsHist
        managed object table"
    ::= { cfprAdaptorObjects 97 }

cfprAdaptorMenloMcpuErrorStatsHistEntry OBJECT-TYPE
    SYNTAX           CfprAdaptorMenloMcpuErrorStatsHistEntry
    MAX-ACCESS       not-accessible
    STATUS           current
    DESCRIPTION
        "Entry for the cfprAdaptorMenloMcpuErrorStatsHistTable table."
    INDEX { cfprAdaptorMenloMcpuErrorStatsHistInstanceId }
    ::= { cfprAdaptorMenloMcpuErrorStatsHistTable 1 }

CfprAdaptorMenloMcpuErrorStatsHistEntry ::= SEQUENCE {
    cfprAdaptorMenloMcpuErrorStatsHistInstanceId                     CfprManagedObjectId,
    cfprAdaptorMenloMcpuErrorStatsHistDn                             CfprManagedObjectDn,
    cfprAdaptorMenloMcpuErrorStatsHistRn                             SnmpAdminString,
    cfprAdaptorMenloMcpuErrorStatsHistCorrectableErrors              Unsigned64,
    cfprAdaptorMenloMcpuErrorStatsHistCorrectableErrorsDelta         Unsigned64,
    cfprAdaptorMenloMcpuErrorStatsHistCorrectableErrorsDeltaAvg      Unsigned64,
    cfprAdaptorMenloMcpuErrorStatsHistCorrectableErrorsDeltaMax      Unsigned64,
    cfprAdaptorMenloMcpuErrorStatsHistCorrectableErrorsDeltaMin      Unsigned64,
    cfprAdaptorMenloMcpuErrorStatsHistId                             Unsigned64,
    cfprAdaptorMenloMcpuErrorStatsHistMostRecent                     TruthValue,
    cfprAdaptorMenloMcpuErrorStatsHistPopErrors                      Unsigned64,
    cfprAdaptorMenloMcpuErrorStatsHistPopErrorsDelta                 Unsigned64,
    cfprAdaptorMenloMcpuErrorStatsHistPopErrorsDeltaAvg              Unsigned64,
    cfprAdaptorMenloMcpuErrorStatsHistPopErrorsDeltaMax              Unsigned64,
    cfprAdaptorMenloMcpuErrorStatsHistPopErrorsDeltaMin              Unsigned64,
    cfprAdaptorMenloMcpuErrorStatsHistPushErrors                     Unsigned64,
    cfprAdaptorMenloMcpuErrorStatsHistPushErrorsDelta                Unsigned64,
    cfprAdaptorMenloMcpuErrorStatsHistPushErrorsDeltaAvg             Unsigned64,
    cfprAdaptorMenloMcpuErrorStatsHistPushErrorsDeltaMax             Unsigned64,
    cfprAdaptorMenloMcpuErrorStatsHistPushErrorsDeltaMin             Unsigned64,
    cfprAdaptorMenloMcpuErrorStatsHistSuspect                        TruthValue,
    cfprAdaptorMenloMcpuErrorStatsHistThresholded                    CfprAdaptorMenloMcpuErrorStatsHistThresholded,
    cfprAdaptorMenloMcpuErrorStatsHistTimeCollected                  DateAndTime,
    cfprAdaptorMenloMcpuErrorStatsHistUncorrectableErrors            Unsigned64,
    cfprAdaptorMenloMcpuErrorStatsHistUncorrectableErrorsDelta       Unsigned64,
    cfprAdaptorMenloMcpuErrorStatsHistUncorrectableErrorsDeltaAvg    Unsigned64,
    cfprAdaptorMenloMcpuErrorStatsHistUncorrectableErrorsDeltaMax    Unsigned64,
    cfprAdaptorMenloMcpuErrorStatsHistUncorrectableErrorsDeltaMin    Unsigned64
}

cfprAdaptorMenloMcpuErrorStatsHistInstanceId OBJECT-TYPE
    SYNTAX       CfprManagedObjectId
    MAX-ACCESS   not-accessible
    STATUS       current
    DESCRIPTION
        "Instance identifier of the managed object."
    ::= { cfprAdaptorMenloMcpuErrorStatsHistEntry 1 }

cfprAdaptorMenloMcpuErrorStatsHistDn OBJECT-TYPE
    SYNTAX       CfprManagedObjectDn
    MAX-ACCESS   read-only
    STATUS       current
    DESCRIPTION
        "Cisco Firepower adaptor:MenloMcpuErrorStatsHist:dn
        managed object property"
    ::= { cfprAdaptorMenloMcpuErrorStatsHistEntry 2 }

cfprAdaptorMenloMcpuErrorStatsHistRn OBJECT-TYPE
    SYNTAX       SnmpAdminString
    MAX-ACCESS   read-only
    STATUS       current
    DESCRIPTION
        "Cisco Firepower adaptor:MenloMcpuErrorStatsHist:rn
        managed object property"
    ::= { cfprAdaptorMenloMcpuErrorStatsHistEntry 3 }

cfprAdaptorMenloMcpuErrorStatsHistCorrectableErrors OBJECT-TYPE
    SYNTAX       Unsigned64
    MAX-ACCESS   read-only
    STATUS       current
    DESCRIPTION
        "Cisco Firepower adaptor:MenloMcpuErrorStatsHist:correctableErrors
         managed object property"
    ::= { cfprAdaptorMenloMcpuErrorStatsHistEntry 4 }

cfprAdaptorMenloMcpuErrorStatsHistCorrectableErrorsDelta OBJECT-TYPE
    SYNTAX       Unsigned64
    MAX-ACCESS   read-only
    STATUS       current
    DESCRIPTION
        "Cisco Firepower adaptor:MenloMcpuErrorStatsHist:correctableErrors
        Delta managed object property"
    ::= { cfprAdaptorMenloMcpuErrorStatsHistEntry 5 }

cfprAdaptorMenloMcpuErrorStatsHistCorrectableErrorsDeltaAvg OBJECT-TYPE
    SYNTAX       Unsigned64
    MAX-ACCESS   read-only
    STATUS       current
    DESCRIPTION
        "Cisco Firepower adaptor:MenloMcpuErrorStatsHist:correctableErrors
        DeltaAvg managed object property"
    ::= { cfprAdaptorMenloMcpuErrorStatsHistEntry 6 }

cfprAdaptorMenloMcpuErrorStatsHistCorrectableErrorsDeltaMax OBJECT-TYPE
    SYNTAX       Unsigned64
    MAX-ACCESS   read-only
    STATUS       current
    DESCRIPTION
        "Cisco Firepower adaptor:MenloMcpuErrorStatsHist:correctableErrors
        DeltaMax managed object property"
    ::= { cfprAdaptorMenloMcpuErrorStatsHistEntry 7 }

cfprAdaptorMenloMcpuErrorStatsHistCorrectableErrorsDeltaMin OBJECT-TYPE
    SYNTAX       Unsigned64
    MAX-ACCESS   read-only
    STATUS       current
    DESCRIPTION
        "Cisco Firepower adaptor:MenloMcpuErrorStatsHist:correctableErrors
        DeltaMin managed object property"
    ::= { cfprAdaptorMenloMcpuErrorStatsHistEntry 8 }

cfprAdaptorMenloMcpuErrorStatsHistId OBJECT-TYPE
    SYNTAX       Unsigned64
    MAX-ACCESS   read-only
    STATUS       current
    DESCRIPTION
        "Cisco Firepower adaptor:MenloMcpuErrorStatsHist:id
        managed object property"
    ::= { cfprAdaptorMenloMcpuErrorStatsHistEntry 9 }

cfprAdaptorMenloMcpuErrorStatsHistMostRecent OBJECT-TYPE
    SYNTAX       TruthValue
    MAX-ACCESS   read-only
    STATUS       current
    DESCRIPTION
        "Cisco Firepower adaptor:MenloMcpuErrorStatsHist:mostRecent
        managed object property"
    ::= { cfprAdaptorMenloMcpuErrorStatsHistEntry 10 }

cfprAdaptorMenloMcpuErrorStatsHistPopErrors OBJECT-TYPE
    SYNTAX       Unsigned64
    MAX-ACCESS   read-only
    STATUS       current
    DESCRIPTION
        "Cisco Firepower adaptor:MenloMcpuErrorStatsHist:popErrors
        managed object property"
    ::= { cfprAdaptorMenloMcpuErrorStatsHistEntry 11 }

cfprAdaptorMenloMcpuErrorStatsHistPopErrorsDelta OBJECT-TYPE
    SYNTAX       Unsigned64
    MAX-ACCESS   read-only
    STATUS       current
    DESCRIPTION
        "Cisco Firepower adaptor:MenloMcpuErrorStatsHist:popErrorsDelta
        managed object property"
    ::= { cfprAdaptorMenloMcpuErrorStatsHistEntry 12 }

cfprAdaptorMenloMcpuErrorStatsHistPopErrorsDeltaAvg OBJECT-TYPE
    SYNTAX       Unsigned64
    MAX-ACCESS   read-only
    STATUS       current
    DESCRIPTION
        "Cisco Firepower adaptor:MenloMcpuErrorStatsHist:popErrorsDeltaAvg
         managed object property"
    ::= { cfprAdaptorMenloMcpuErrorStatsHistEntry 13 }

cfprAdaptorMenloMcpuErrorStatsHistPopErrorsDeltaMax OBJECT-TYPE
    SYNTAX       Unsigned64
    MAX-ACCESS   read-only
    STATUS       current
    DESCRIPTION
        "Cisco Firepower adaptor:MenloMcpuErrorStatsHist:popErrorsDeltaMax
         managed object property"
    ::= { cfprAdaptorMenloMcpuErrorStatsHistEntry 14 }

cfprAdaptorMenloMcpuErrorStatsHistPopErrorsDeltaMin OBJECT-TYPE
    SYNTAX       Unsigned64
    MAX-ACCESS   read-only
    STATUS       current
    DESCRIPTION
        "Cisco Firepower adaptor:MenloMcpuErrorStatsHist:popErrorsDeltaMin
         managed object property"
    ::= { cfprAdaptorMenloMcpuErrorStatsHistEntry 15 }

cfprAdaptorMenloMcpuErrorStatsHistPushErrors OBJECT-TYPE
    SYNTAX       Unsigned64
    MAX-ACCESS   read-only
    STATUS       current
    DESCRIPTION
        "Cisco Firepower adaptor:MenloMcpuErrorStatsHist:pushErrors
        managed object property"
    ::= { cfprAdaptorMenloMcpuErrorStatsHistEntry 16 }

cfprAdaptorMenloMcpuErrorStatsHistPushErrorsDelta OBJECT-TYPE
    SYNTAX       Unsigned64
    MAX-ACCESS   read-only
    STATUS       current
    DESCRIPTION
        "Cisco Firepower adaptor:MenloMcpuErrorStatsHist:pushErrorsDelta
        managed object property"
    ::= { cfprAdaptorMenloMcpuErrorStatsHistEntry 17 }

cfprAdaptorMenloMcpuErrorStatsHistPushErrorsDeltaAvg OBJECT-TYPE
    SYNTAX       Unsigned64
    MAX-ACCESS   read-only
    STATUS       current
    DESCRIPTION
        "Cisco Firepower adaptor:MenloMcpuErrorStatsHist:pushErrorsDeltaAv
        g managed object property"
    ::= { cfprAdaptorMenloMcpuErrorStatsHistEntry 18 }

cfprAdaptorMenloMcpuErrorStatsHistPushErrorsDeltaMax OBJECT-TYPE
    SYNTAX       Unsigned64
    MAX-ACCESS   read-only
    STATUS       current
    DESCRIPTION
        "Cisco Firepower adaptor:MenloMcpuErrorStatsHist:pushErrorsDeltaMa
        x managed object property"
    ::= { cfprAdaptorMenloMcpuErrorStatsHistEntry 19 }

cfprAdaptorMenloMcpuErrorStatsHistPushErrorsDeltaMin OBJECT-TYPE
    SYNTAX       Unsigned64
    MAX-ACCESS   read-only
    STATUS       current
    DESCRIPTION
        "Cisco Firepower adaptor:MenloMcpuErrorStatsHist:pushErrorsDeltaMi
        n managed object property"
    ::= { cfprAdaptorMenloMcpuErrorStatsHistEntry 20 }

cfprAdaptorMenloMcpuErrorStatsHistSuspect OBJECT-TYPE
    SYNTAX       TruthValue
    MAX-ACCESS   read-only
    STATUS       current
    DESCRIPTION
        "Cisco Firepower adaptor:MenloMcpuErrorStatsHist:suspect
        managed object property"
    ::= { cfprAdaptorMenloMcpuErrorStatsHistEntry 21 }

cfprAdaptorMenloMcpuErrorStatsHistThresholded OBJECT-TYPE
    SYNTAX       CfprAdaptorMenloMcpuErrorStatsHistThresholded
    MAX-ACCESS   read-only
    STATUS       current
    DESCRIPTION
        "Cisco Firepower adaptor:MenloMcpuErrorStatsHist:thresholded
        managed object property"
    ::= { cfprAdaptorMenloMcpuErrorStatsHistEntry 22 }

cfprAdaptorMenloMcpuErrorStatsHistTimeCollected OBJECT-TYPE
    SYNTAX       DateAndTime
    MAX-ACCESS   read-only
    STATUS       current
    DESCRIPTION
        "Cisco Firepower adaptor:MenloMcpuErrorStatsHist:timeCollected
        managed object property"
    ::= { cfprAdaptorMenloMcpuErrorStatsHistEntry 23 }

cfprAdaptorMenloMcpuErrorStatsHistUncorrectableErrors OBJECT-TYPE
    SYNTAX       Unsigned64
    MAX-ACCESS   read-only
    STATUS       current
    DESCRIPTION
        "Cisco Firepower adaptor:MenloMcpuErrorStatsHist:uncorrectableErro
        rs managed object property"
    ::= { cfprAdaptorMenloMcpuErrorStatsHistEntry 24 }

cfprAdaptorMenloMcpuErrorStatsHistUncorrectableErrorsDelta OBJECT-TYPE
    SYNTAX       Unsigned64
    MAX-ACCESS   read-only
    STATUS       current
    DESCRIPTION
        "Cisco Firepower adaptor:MenloMcpuErrorStatsHist:uncorrectableErro
        rsDelta managed object property"
    ::= { cfprAdaptorMenloMcpuErrorStatsHistEntry 25 }

cfprAdaptorMenloMcpuErrorStatsHistUncorrectableErrorsDeltaAvg OBJECT-TYPE
    SYNTAX       Unsigned64
    MAX-ACCESS   read-only
    STATUS       current
    DESCRIPTION
        "Cisco Firepower adaptor:MenloMcpuErrorStatsHist:uncorrectableErro
        rsDeltaAvg managed object property"
    ::= { cfprAdaptorMenloMcpuErrorStatsHistEntry 26 }

cfprAdaptorMenloMcpuErrorStatsHistUncorrectableErrorsDeltaMax OBJECT-TYPE
    SYNTAX       Unsigned64
    MAX-ACCESS   read-only
    STATUS       current
    DESCRIPTION
        "Cisco Firepower adaptor:MenloMcpuErrorStatsHist:uncorrectableErro
        rsDeltaMax managed object property"
    ::= { cfprAdaptorMenloMcpuErrorStatsHistEntry 27 }

cfprAdaptorMenloMcpuErrorStatsHistUncorrectableErrorsDeltaMin OBJECT-TYPE
    SYNTAX       Unsigned64
    MAX-ACCESS   read-only
    STATUS       current
    DESCRIPTION
        "Cisco Firepower adaptor:MenloMcpuErrorStatsHist:uncorrectableErro
        rsDeltaMin managed object property"
    ::= { cfprAdaptorMenloMcpuErrorStatsHistEntry 28 }

cfprAdaptorMenloMcpuStatsTable OBJECT-TYPE
    SYNTAX           SEQUENCE OF CfprAdaptorMenloMcpuStatsEntry
    MAX-ACCESS       not-accessible
    STATUS           current
    DESCRIPTION
        "Cisco Firepower adaptor:MenloMcpuStats managed object table"
    ::= { cfprAdaptorObjects 98 }

cfprAdaptorMenloMcpuStatsEntry OBJECT-TYPE
    SYNTAX           CfprAdaptorMenloMcpuStatsEntry
    MAX-ACCESS       not-accessible
    STATUS           current
    DESCRIPTION
        "Entry for the cfprAdaptorMenloMcpuStatsTable table."
    INDEX { cfprAdaptorMenloMcpuStatsInstanceId }
    ::= { cfprAdaptorMenloMcpuStatsTable 1 }

CfprAdaptorMenloMcpuStatsEntry ::= SEQUENCE {
    cfprAdaptorMenloMcpuStatsInstanceId                              CfprManagedObjectId,
    cfprAdaptorMenloMcpuStatsDn                                      CfprManagedObjectDn,
    cfprAdaptorMenloMcpuStatsRn                                      SnmpAdminString,
    cfprAdaptorMenloMcpuStatsDropAcl                                 Unsigned64,
    cfprAdaptorMenloMcpuStatsDropAclDelta                            Counter64,
    cfprAdaptorMenloMcpuStatsDropAclDeltaAvg                         Unsigned64,
    cfprAdaptorMenloMcpuStatsDropAclDeltaMax                         Unsigned64,
    cfprAdaptorMenloMcpuStatsDropAclDeltaMin                         Unsigned64,
    cfprAdaptorMenloMcpuStatsDropOverrun                             Unsigned64,
    cfprAdaptorMenloMcpuStatsDropOverrunDelta                        Counter64,
    cfprAdaptorMenloMcpuStatsDropOverrunDeltaAvg                     Unsigned64,
    cfprAdaptorMenloMcpuStatsDropOverrunDeltaMax                     Unsigned64,
    cfprAdaptorMenloMcpuStatsDropOverrunDeltaMin                     Unsigned64,
    cfprAdaptorMenloMcpuStatsDropRunt                                Unsigned64,
    cfprAdaptorMenloMcpuStatsDropRuntDelta                           Counter64,
    cfprAdaptorMenloMcpuStatsDropRuntDeltaAvg                        Unsigned64,
    cfprAdaptorMenloMcpuStatsDropRuntDeltaMax                        Unsigned64,
    cfprAdaptorMenloMcpuStatsDropRuntDeltaMin                        Unsigned64,
    cfprAdaptorMenloMcpuStatsIntervals                               Gauge32,
    cfprAdaptorMenloMcpuStatsMenloMcpuIndex                          CfprAdaptorMenloStatsIndex,
    cfprAdaptorMenloMcpuStatsSuspect                                 TruthValue,
    cfprAdaptorMenloMcpuStatsThresholded                             CfprAdaptorMenloMcpuStatsThresholded,
    cfprAdaptorMenloMcpuStatsTimeCollected                           DateAndTime,
    cfprAdaptorMenloMcpuStatsTruncateOverrun                         Unsigned64,
    cfprAdaptorMenloMcpuStatsTruncateOverrunDelta                    Counter64,
    cfprAdaptorMenloMcpuStatsTruncateOverrunDeltaAvg                 Unsigned64,
    cfprAdaptorMenloMcpuStatsTruncateOverrunDeltaMax                 Unsigned64,
    cfprAdaptorMenloMcpuStatsTruncateOverrunDeltaMin                 Unsigned64,
    cfprAdaptorMenloMcpuStatsUpdate                                  Gauge32
}

cfprAdaptorMenloMcpuStatsInstanceId OBJECT-TYPE
    SYNTAX       CfprManagedObjectId
    MAX-ACCESS   not-accessible
    STATUS       current
    DESCRIPTION
        "Instance identifier of the managed object."
    ::= { cfprAdaptorMenloMcpuStatsEntry 1 }

cfprAdaptorMenloMcpuStatsDn OBJECT-TYPE
    SYNTAX       CfprManagedObjectDn
    MAX-ACCESS   read-only
    STATUS       current
    DESCRIPTION
        "Cisco Firepower adaptor:MenloMcpuStats:dn managed
        object property"
    ::= { cfprAdaptorMenloMcpuStatsEntry 2 }

cfprAdaptorMenloMcpuStatsRn OBJECT-TYPE
    SYNTAX       SnmpAdminString
    MAX-ACCESS   read-only
    STATUS       current
    DESCRIPTION
        "Cisco Firepower adaptor:MenloMcpuStats:rn managed
        object property"
    ::= { cfprAdaptorMenloMcpuStatsEntry 3 }

cfprAdaptorMenloMcpuStatsDropAcl OBJECT-TYPE
    SYNTAX       Unsigned64
    MAX-ACCESS   read-only
    STATUS       current
    DESCRIPTION
        "Cisco Firepower adaptor:MenloMcpuStats:dropAcl
        managed object property"
    ::= { cfprAdaptorMenloMcpuStatsEntry 4 }

cfprAdaptorMenloMcpuStatsDropAclDelta OBJECT-TYPE
    SYNTAX       Counter64
    MAX-ACCESS   read-only
    STATUS       current
    DESCRIPTION
        "Cisco Firepower adaptor:MenloMcpuStats:dropAclDelta
        managed object property"
    ::= { cfprAdaptorMenloMcpuStatsEntry 5 }

cfprAdaptorMenloMcpuStatsDropAclDeltaAvg OBJECT-TYPE
    SYNTAX       Unsigned64
    MAX-ACCESS   read-only
    STATUS       current
    DESCRIPTION
        "Cisco Firepower adaptor:MenloMcpuStats:dropAclDeltaAvg
        managed object property"
    ::= { cfprAdaptorMenloMcpuStatsEntry 6 }

cfprAdaptorMenloMcpuStatsDropAclDeltaMax OBJECT-TYPE
    SYNTAX       Unsigned64
    MAX-ACCESS   read-only
    STATUS       current
    DESCRIPTION
        "Cisco Firepower adaptor:MenloMcpuStats:dropAclDeltaMax
        managed object property"
    ::= { cfprAdaptorMenloMcpuStatsEntry 7 }

cfprAdaptorMenloMcpuStatsDropAclDeltaMin OBJECT-TYPE
    SYNTAX       Unsigned64
    MAX-ACCESS   read-only
    STATUS       current
    DESCRIPTION
        "Cisco Firepower adaptor:MenloMcpuStats:dropAclDeltaMin
        managed object property"
    ::= { cfprAdaptorMenloMcpuStatsEntry 8 }

cfprAdaptorMenloMcpuStatsDropOverrun OBJECT-TYPE
    SYNTAX       Unsigned64
    MAX-ACCESS   read-only
    STATUS       current
    DESCRIPTION
        "Cisco Firepower adaptor:MenloMcpuStats:dropOverrun
        managed object property"
    ::= { cfprAdaptorMenloMcpuStatsEntry 9 }

cfprAdaptorMenloMcpuStatsDropOverrunDelta OBJECT-TYPE
    SYNTAX       Counter64
    MAX-ACCESS   read-only
    STATUS       current
    DESCRIPTION
        "Cisco Firepower adaptor:MenloMcpuStats:dropOverrunDelta
        managed object property"
    ::= { cfprAdaptorMenloMcpuStatsEntry 10 }

cfprAdaptorMenloMcpuStatsDropOverrunDeltaAvg OBJECT-TYPE
    SYNTAX       Unsigned64
    MAX-ACCESS   read-only
    STATUS       current
    DESCRIPTION
        "Cisco Firepower adaptor:MenloMcpuStats:dropOverrunDeltaAvg
        managed object property"
    ::= { cfprAdaptorMenloMcpuStatsEntry 11 }

cfprAdaptorMenloMcpuStatsDropOverrunDeltaMax OBJECT-TYPE
    SYNTAX       Unsigned64
    MAX-ACCESS   read-only
    STATUS       current
    DESCRIPTION
        "Cisco Firepower adaptor:MenloMcpuStats:dropOverrunDeltaMax
        managed object property"
    ::= { cfprAdaptorMenloMcpuStatsEntry 12 }

cfprAdaptorMenloMcpuStatsDropOverrunDeltaMin OBJECT-TYPE
    SYNTAX       Unsigned64
    MAX-ACCESS   read-only
    STATUS       current
    DESCRIPTION
        "Cisco Firepower adaptor:MenloMcpuStats:dropOverrunDeltaMin
        managed object property"
    ::= { cfprAdaptorMenloMcpuStatsEntry 13 }

cfprAdaptorMenloMcpuStatsDropRunt OBJECT-TYPE
    SYNTAX       Unsigned64
    MAX-ACCESS   read-only
    STATUS       current
    DESCRIPTION
        "Cisco Firepower adaptor:MenloMcpuStats:dropRunt
        managed object property"
    ::= { cfprAdaptorMenloMcpuStatsEntry 14 }

cfprAdaptorMenloMcpuStatsDropRuntDelta OBJECT-TYPE
    SYNTAX       Counter64
    MAX-ACCESS   read-only
    STATUS       current
    DESCRIPTION
        "Cisco Firepower adaptor:MenloMcpuStats:dropRuntDelta
        managed object property"
    ::= { cfprAdaptorMenloMcpuStatsEntry 15 }

cfprAdaptorMenloMcpuStatsDropRuntDeltaAvg OBJECT-TYPE
    SYNTAX       Unsigned64
    MAX-ACCESS   read-only
    STATUS       current
    DESCRIPTION
        "Cisco Firepower adaptor:MenloMcpuStats:dropRuntDeltaAvg
        managed object property"
    ::= { cfprAdaptorMenloMcpuStatsEntry 16 }

cfprAdaptorMenloMcpuStatsDropRuntDeltaMax OBJECT-TYPE
    SYNTAX       Unsigned64
    MAX-ACCESS   read-only
    STATUS       current
    DESCRIPTION
        "Cisco Firepower adaptor:MenloMcpuStats:dropRuntDeltaMax
        managed object property"
    ::= { cfprAdaptorMenloMcpuStatsEntry 17 }

cfprAdaptorMenloMcpuStatsDropRuntDeltaMin OBJECT-TYPE
    SYNTAX       Unsigned64
    MAX-ACCESS   read-only
    STATUS       current
    DESCRIPTION
        "Cisco Firepower adaptor:MenloMcpuStats:dropRuntDeltaMin
        managed object property"
    ::= { cfprAdaptorMenloMcpuStatsEntry 18 }

cfprAdaptorMenloMcpuStatsIntervals OBJECT-TYPE
    SYNTAX       Gauge32
    MAX-ACCESS   read-only
    STATUS       current
    DESCRIPTION
        "Cisco Firepower adaptor:MenloMcpuStats:intervals
        managed object property"
    ::= { cfprAdaptorMenloMcpuStatsEntry 19 }

cfprAdaptorMenloMcpuStatsMenloMcpuIndex OBJECT-TYPE
    SYNTAX       CfprAdaptorMenloStatsIndex
    MAX-ACCESS   read-only
    STATUS       current
    DESCRIPTION
        "Cisco Firepower adaptor:MenloMcpuStats:menloMcpuIndex
        managed object property"
    ::= { cfprAdaptorMenloMcpuStatsEntry 20 }

cfprAdaptorMenloMcpuStatsSuspect OBJECT-TYPE
    SYNTAX       TruthValue
    MAX-ACCESS   read-only
    STATUS       current
    DESCRIPTION
        "Cisco Firepower adaptor:MenloMcpuStats:suspect
        managed object property"
    ::= { cfprAdaptorMenloMcpuStatsEntry 21 }

cfprAdaptorMenloMcpuStatsThresholded OBJECT-TYPE
    SYNTAX       CfprAdaptorMenloMcpuStatsThresholded
    MAX-ACCESS   read-only
    STATUS       current
    DESCRIPTION
        "Cisco Firepower adaptor:MenloMcpuStats:thresholded
        managed object property"
    ::= { cfprAdaptorMenloMcpuStatsEntry 22 }

cfprAdaptorMenloMcpuStatsTimeCollected OBJECT-TYPE
    SYNTAX       DateAndTime
    MAX-ACCESS   read-only
    STATUS       current
    DESCRIPTION
        "Cisco Firepower adaptor:MenloMcpuStats:timeCollected
        managed object property"
    ::= { cfprAdaptorMenloMcpuStatsEntry 23 }

cfprAdaptorMenloMcpuStatsTruncateOverrun OBJECT-TYPE
    SYNTAX       Unsigned64
    MAX-ACCESS   read-only
    STATUS       current
    DESCRIPTION
        "Cisco Firepower adaptor:MenloMcpuStats:truncateOverrun
        managed object property"
    ::= { cfprAdaptorMenloMcpuStatsEntry 24 }

cfprAdaptorMenloMcpuStatsTruncateOverrunDelta OBJECT-TYPE
    SYNTAX       Counter64
    MAX-ACCESS   read-only
    STATUS       current
    DESCRIPTION
        "Cisco Firepower adaptor:MenloMcpuStats:truncateOverrunDelta
        managed object property"
    ::= { cfprAdaptorMenloMcpuStatsEntry 25 }

cfprAdaptorMenloMcpuStatsTruncateOverrunDeltaAvg OBJECT-TYPE
    SYNTAX       Unsigned64
    MAX-ACCESS   read-only
    STATUS       current
    DESCRIPTION
        "Cisco Firepower adaptor:MenloMcpuStats:truncateOverrunDeltaAvg
        managed object property"
    ::= { cfprAdaptorMenloMcpuStatsEntry 26 }

cfprAdaptorMenloMcpuStatsTruncateOverrunDeltaMax OBJECT-TYPE
    SYNTAX       Unsigned64
    MAX-ACCESS   read-only
    STATUS       current
    DESCRIPTION
        "Cisco Firepower adaptor:MenloMcpuStats:truncateOverrunDeltaMax
        managed object property"
    ::= { cfprAdaptorMenloMcpuStatsEntry 27 }

cfprAdaptorMenloMcpuStatsTruncateOverrunDeltaMin OBJECT-TYPE
    SYNTAX       Unsigned64
    MAX-ACCESS   read-only
    STATUS       current
    DESCRIPTION
        "Cisco Firepower adaptor:MenloMcpuStats:truncateOverrunDeltaMin
        managed object property"
    ::= { cfprAdaptorMenloMcpuStatsEntry 28 }

cfprAdaptorMenloMcpuStatsUpdate OBJECT-TYPE
    SYNTAX       Gauge32
    MAX-ACCESS   read-only
    STATUS       current
    DESCRIPTION
        "Cisco Firepower adaptor:MenloMcpuStats:update
        managed object property"
    ::= { cfprAdaptorMenloMcpuStatsEntry 29 }

cfprAdaptorMenloMcpuStatsHistTable OBJECT-TYPE
    SYNTAX           SEQUENCE OF CfprAdaptorMenloMcpuStatsHistEntry
    MAX-ACCESS       not-accessible
    STATUS           current
    DESCRIPTION
        "Cisco Firepower adaptor:MenloMcpuStatsHist managed object table"
    ::= { cfprAdaptorObjects 99 }

cfprAdaptorMenloMcpuStatsHistEntry OBJECT-TYPE
    SYNTAX           CfprAdaptorMenloMcpuStatsHistEntry
    MAX-ACCESS       not-accessible
    STATUS           current
    DESCRIPTION
        "Entry for the cfprAdaptorMenloMcpuStatsHistTable table."
    INDEX { cfprAdaptorMenloMcpuStatsHistInstanceId }
    ::= { cfprAdaptorMenloMcpuStatsHistTable 1 }

CfprAdaptorMenloMcpuStatsHistEntry ::= SEQUENCE {
    cfprAdaptorMenloMcpuStatsHistInstanceId                          CfprManagedObjectId,
    cfprAdaptorMenloMcpuStatsHistDn                                  CfprManagedObjectDn,
    cfprAdaptorMenloMcpuStatsHistRn                                  SnmpAdminString,
    cfprAdaptorMenloMcpuStatsHistDropAcl                             Unsigned64,
    cfprAdaptorMenloMcpuStatsHistDropAclDelta                        Unsigned64,
    cfprAdaptorMenloMcpuStatsHistDropAclDeltaAvg                     Unsigned64,
    cfprAdaptorMenloMcpuStatsHistDropAclDeltaMax                     Unsigned64,
    cfprAdaptorMenloMcpuStatsHistDropAclDeltaMin                     Unsigned64,
    cfprAdaptorMenloMcpuStatsHistDropOverrun                         Unsigned64,
    cfprAdaptorMenloMcpuStatsHistDropOverrunDelta                    Unsigned64,
    cfprAdaptorMenloMcpuStatsHistDropOverrunDeltaAvg                 Unsigned64,
    cfprAdaptorMenloMcpuStatsHistDropOverrunDeltaMax                 Unsigned64,
    cfprAdaptorMenloMcpuStatsHistDropOverrunDeltaMin                 Unsigned64,
    cfprAdaptorMenloMcpuStatsHistDropRunt                            Unsigned64,
    cfprAdaptorMenloMcpuStatsHistDropRuntDelta                       Unsigned64,
    cfprAdaptorMenloMcpuStatsHistDropRuntDeltaAvg                    Unsigned64,
    cfprAdaptorMenloMcpuStatsHistDropRuntDeltaMax                    Unsigned64,
    cfprAdaptorMenloMcpuStatsHistDropRuntDeltaMin                    Unsigned64,
    cfprAdaptorMenloMcpuStatsHistId                                  Unsigned64,
    cfprAdaptorMenloMcpuStatsHistMostRecent                          TruthValue,
    cfprAdaptorMenloMcpuStatsHistSuspect                             TruthValue,
    cfprAdaptorMenloMcpuStatsHistThresholded                         CfprAdaptorMenloMcpuStatsHistThresholded,
    cfprAdaptorMenloMcpuStatsHistTimeCollected                       DateAndTime,
    cfprAdaptorMenloMcpuStatsHistTruncateOverrun                     Unsigned64,
    cfprAdaptorMenloMcpuStatsHistTruncateOverrunDelta                Unsigned64,
    cfprAdaptorMenloMcpuStatsHistTruncateOverrunDeltaAvg             Unsigned64,
    cfprAdaptorMenloMcpuStatsHistTruncateOverrunDeltaMax             Unsigned64,
    cfprAdaptorMenloMcpuStatsHistTruncateOverrunDeltaMin             Unsigned64
}

cfprAdaptorMenloMcpuStatsHistInstanceId OBJECT-TYPE
    SYNTAX       CfprManagedObjectId
    MAX-ACCESS   not-accessible
    STATUS       current
    DESCRIPTION
        "Instance identifier of the managed object."
    ::= { cfprAdaptorMenloMcpuStatsHistEntry 1 }

cfprAdaptorMenloMcpuStatsHistDn OBJECT-TYPE
    SYNTAX       CfprManagedObjectDn
    MAX-ACCESS   read-only
    STATUS       current
    DESCRIPTION
        "Cisco Firepower adaptor:MenloMcpuStatsHist:dn
        managed object property"
    ::= { cfprAdaptorMenloMcpuStatsHistEntry 2 }

cfprAdaptorMenloMcpuStatsHistRn OBJECT-TYPE
    SYNTAX       SnmpAdminString
    MAX-ACCESS   read-only
    STATUS       current
    DESCRIPTION
        "Cisco Firepower adaptor:MenloMcpuStatsHist:rn
        managed object property"
    ::= { cfprAdaptorMenloMcpuStatsHistEntry 3 }

cfprAdaptorMenloMcpuStatsHistDropAcl OBJECT-TYPE
    SYNTAX       Unsigned64
    MAX-ACCESS   read-only
    STATUS       current
    DESCRIPTION
        "Cisco Firepower adaptor:MenloMcpuStatsHist:dropAcl
        managed object property"
    ::= { cfprAdaptorMenloMcpuStatsHistEntry 4 }

cfprAdaptorMenloMcpuStatsHistDropAclDelta OBJECT-TYPE
    SYNTAX       Unsigned64
    MAX-ACCESS   read-only
    STATUS       current
    DESCRIPTION
        "Cisco Firepower adaptor:MenloMcpuStatsHist:dropAclDelta
        managed object property"
    ::= { cfprAdaptorMenloMcpuStatsHistEntry 5 }

cfprAdaptorMenloMcpuStatsHistDropAclDeltaAvg OBJECT-TYPE
    SYNTAX       Unsigned64
    MAX-ACCESS   read-only
    STATUS       current
    DESCRIPTION
        "Cisco Firepower adaptor:MenloMcpuStatsHist:dropAclDeltaAvg
        managed object property"
    ::= { cfprAdaptorMenloMcpuStatsHistEntry 6 }

cfprAdaptorMenloMcpuStatsHistDropAclDeltaMax OBJECT-TYPE
    SYNTAX       Unsigned64
    MAX-ACCESS   read-only
    STATUS       current
    DESCRIPTION
        "Cisco Firepower adaptor:MenloMcpuStatsHist:dropAclDeltaMax
        managed object property"
    ::= { cfprAdaptorMenloMcpuStatsHistEntry 7 }

cfprAdaptorMenloMcpuStatsHistDropAclDeltaMin OBJECT-TYPE
    SYNTAX       Unsigned64
    MAX-ACCESS   read-only
    STATUS       current
    DESCRIPTION
        "Cisco Firepower adaptor:MenloMcpuStatsHist:dropAclDeltaMin
        managed object property"
    ::= { cfprAdaptorMenloMcpuStatsHistEntry 8 }

cfprAdaptorMenloMcpuStatsHistDropOverrun OBJECT-TYPE
    SYNTAX       Unsigned64
    MAX-ACCESS   read-only
    STATUS       current
    DESCRIPTION
        "Cisco Firepower adaptor:MenloMcpuStatsHist:dropOverrun
        managed object property"
    ::= { cfprAdaptorMenloMcpuStatsHistEntry 9 }

cfprAdaptorMenloMcpuStatsHistDropOverrunDelta OBJECT-TYPE
    SYNTAX       Unsigned64
    MAX-ACCESS   read-only
    STATUS       current
    DESCRIPTION
        "Cisco Firepower adaptor:MenloMcpuStatsHist:dropOverrunDelta
        managed object property"
    ::= { cfprAdaptorMenloMcpuStatsHistEntry 10 }

cfprAdaptorMenloMcpuStatsHistDropOverrunDeltaAvg OBJECT-TYPE
    SYNTAX       Unsigned64
    MAX-ACCESS   read-only
    STATUS       current
    DESCRIPTION
        "Cisco Firepower adaptor:MenloMcpuStatsHist:dropOverrunDeltaAvg
        managed object property"
    ::= { cfprAdaptorMenloMcpuStatsHistEntry 11 }

cfprAdaptorMenloMcpuStatsHistDropOverrunDeltaMax OBJECT-TYPE
    SYNTAX       Unsigned64
    MAX-ACCESS   read-only
    STATUS       current
    DESCRIPTION
        "Cisco Firepower adaptor:MenloMcpuStatsHist:dropOverrunDeltaMax
        managed object property"
    ::= { cfprAdaptorMenloMcpuStatsHistEntry 12 }

cfprAdaptorMenloMcpuStatsHistDropOverrunDeltaMin OBJECT-TYPE
    SYNTAX       Unsigned64
    MAX-ACCESS   read-only
    STATUS       current
    DESCRIPTION
        "Cisco Firepower adaptor:MenloMcpuStatsHist:dropOverrunDeltaMin
        managed object property"
    ::= { cfprAdaptorMenloMcpuStatsHistEntry 13 }

cfprAdaptorMenloMcpuStatsHistDropRunt OBJECT-TYPE
    SYNTAX       Unsigned64
    MAX-ACCESS   read-only
    STATUS       current
    DESCRIPTION
        "Cisco Firepower adaptor:MenloMcpuStatsHist:dropRunt
        managed object property"
    ::= { cfprAdaptorMenloMcpuStatsHistEntry 14 }

cfprAdaptorMenloMcpuStatsHistDropRuntDelta OBJECT-TYPE
    SYNTAX       Unsigned64
    MAX-ACCESS   read-only
    STATUS       current
    DESCRIPTION
        "Cisco Firepower adaptor:MenloMcpuStatsHist:dropRuntDelta
        managed object property"
    ::= { cfprAdaptorMenloMcpuStatsHistEntry 15 }

cfprAdaptorMenloMcpuStatsHistDropRuntDeltaAvg OBJECT-TYPE
    SYNTAX       Unsigned64
    MAX-ACCESS   read-only
    STATUS       current
    DESCRIPTION
        "Cisco Firepower adaptor:MenloMcpuStatsHist:dropRuntDeltaAvg
        managed object property"
    ::= { cfprAdaptorMenloMcpuStatsHistEntry 16 }

cfprAdaptorMenloMcpuStatsHistDropRuntDeltaMax OBJECT-TYPE
    SYNTAX       Unsigned64
    MAX-ACCESS   read-only
    STATUS       current
    DESCRIPTION
        "Cisco Firepower adaptor:MenloMcpuStatsHist:dropRuntDeltaMax
        managed object property"
    ::= { cfprAdaptorMenloMcpuStatsHistEntry 17 }

cfprAdaptorMenloMcpuStatsHistDropRuntDeltaMin OBJECT-TYPE
    SYNTAX       Unsigned64
    MAX-ACCESS   read-only
    STATUS       current
    DESCRIPTION
        "Cisco Firepower adaptor:MenloMcpuStatsHist:dropRuntDeltaMin
        managed object property"
    ::= { cfprAdaptorMenloMcpuStatsHistEntry 18 }

cfprAdaptorMenloMcpuStatsHistId OBJECT-TYPE
    SYNTAX       Unsigned64
    MAX-ACCESS   read-only
    STATUS       current
    DESCRIPTION
        "Cisco Firepower adaptor:MenloMcpuStatsHist:id
        managed object property"
    ::= { cfprAdaptorMenloMcpuStatsHistEntry 19 }

cfprAdaptorMenloMcpuStatsHistMostRecent OBJECT-TYPE
    SYNTAX       TruthValue
    MAX-ACCESS   read-only
    STATUS       current
    DESCRIPTION
        "Cisco Firepower adaptor:MenloMcpuStatsHist:mostRecent
        managed object property"
    ::= { cfprAdaptorMenloMcpuStatsHistEntry 20 }

cfprAdaptorMenloMcpuStatsHistSuspect OBJECT-TYPE
    SYNTAX       TruthValue
    MAX-ACCESS   read-only
    STATUS       current
    DESCRIPTION
        "Cisco Firepower adaptor:MenloMcpuStatsHist:suspect
        managed object property"
    ::= { cfprAdaptorMenloMcpuStatsHistEntry 21 }

cfprAdaptorMenloMcpuStatsHistThresholded OBJECT-TYPE
    SYNTAX       CfprAdaptorMenloMcpuStatsHistThresholded
    MAX-ACCESS   read-only
    STATUS       current
    DESCRIPTION
        "Cisco Firepower adaptor:MenloMcpuStatsHist:thresholded
        managed object property"
    ::= { cfprAdaptorMenloMcpuStatsHistEntry 22 }

cfprAdaptorMenloMcpuStatsHistTimeCollected OBJECT-TYPE
    SYNTAX       DateAndTime
    MAX-ACCESS   read-only
    STATUS       current
    DESCRIPTION
        "Cisco Firepower adaptor:MenloMcpuStatsHist:timeCollected
        managed object property"
    ::= { cfprAdaptorMenloMcpuStatsHistEntry 23 }

cfprAdaptorMenloMcpuStatsHistTruncateOverrun OBJECT-TYPE
    SYNTAX       Unsigned64
    MAX-ACCESS   read-only
    STATUS       current
    DESCRIPTION
        "Cisco Firepower adaptor:MenloMcpuStatsHist:truncateOverrun
        managed object property"
    ::= { cfprAdaptorMenloMcpuStatsHistEntry 24 }

cfprAdaptorMenloMcpuStatsHistTruncateOverrunDelta OBJECT-TYPE
    SYNTAX       Unsigned64
    MAX-ACCESS   read-only
    STATUS       current
    DESCRIPTION
        "Cisco Firepower adaptor:MenloMcpuStatsHist:truncateOverrunDelta
        managed object property"
    ::= { cfprAdaptorMenloMcpuStatsHistEntry 25 }

cfprAdaptorMenloMcpuStatsHistTruncateOverrunDeltaAvg OBJECT-TYPE
    SYNTAX       Unsigned64
    MAX-ACCESS   read-only
    STATUS       current
    DESCRIPTION
        "Cisco Firepower adaptor:MenloMcpuStatsHist:truncateOverrunDeltaAv
        g managed object property"
    ::= { cfprAdaptorMenloMcpuStatsHistEntry 26 }

cfprAdaptorMenloMcpuStatsHistTruncateOverrunDeltaMax OBJECT-TYPE
    SYNTAX       Unsigned64
    MAX-ACCESS   read-only
    STATUS       current
    DESCRIPTION
        "Cisco Firepower adaptor:MenloMcpuStatsHist:truncateOverrunDeltaMa
        x managed object property"
    ::= { cfprAdaptorMenloMcpuStatsHistEntry 27 }

cfprAdaptorMenloMcpuStatsHistTruncateOverrunDeltaMin OBJECT-TYPE
    SYNTAX       Unsigned64
    MAX-ACCESS   read-only
    STATUS       current
    DESCRIPTION
        "Cisco Firepower adaptor:MenloMcpuStatsHist:truncateOverrunDeltaMi
        n managed object property"
    ::= { cfprAdaptorMenloMcpuStatsHistEntry 28 }

cfprAdaptorMenloNetEgStatsTable OBJECT-TYPE
    SYNTAX           SEQUENCE OF CfprAdaptorMenloNetEgStatsEntry
    MAX-ACCESS       not-accessible
    STATUS           current
    DESCRIPTION
        "Cisco Firepower adaptor:MenloNetEgStats managed object table"
    ::= { cfprAdaptorObjects 100 }

cfprAdaptorMenloNetEgStatsEntry OBJECT-TYPE
    SYNTAX           CfprAdaptorMenloNetEgStatsEntry
    MAX-ACCESS       not-accessible
    STATUS           current
    DESCRIPTION
        "Entry for the cfprAdaptorMenloNetEgStatsTable table."
    INDEX { cfprAdaptorMenloNetEgStatsInstanceId }
    ::= { cfprAdaptorMenloNetEgStatsTable 1 }

CfprAdaptorMenloNetEgStatsEntry ::= SEQUENCE {
    cfprAdaptorMenloNetEgStatsInstanceId                             CfprManagedObjectId,
    cfprAdaptorMenloNetEgStatsDn                                     CfprManagedObjectDn,
    cfprAdaptorMenloNetEgStatsRn                                     SnmpAdminString,
    cfprAdaptorMenloNetEgStatsDropCmd                                Unsigned64,
    cfprAdaptorMenloNetEgStatsDropCmdDelta                           Counter64,
    cfprAdaptorMenloNetEgStatsDropCmdDeltaAvg                        Unsigned64,
    cfprAdaptorMenloNetEgStatsDropCmdDeltaMax                        Unsigned64,
    cfprAdaptorMenloNetEgStatsDropCmdDeltaMin                        Unsigned64,
    cfprAdaptorMenloNetEgStatsDropLifCfgInvalid                      Unsigned64,
    cfprAdaptorMenloNetEgStatsDropLifCfgInvalidDelta                 Counter64,
    cfprAdaptorMenloNetEgStatsDropLifCfgInvalidDeltaAvg              Unsigned64,
    cfprAdaptorMenloNetEgStatsDropLifCfgInvalidDeltaMax              Unsigned64,
    cfprAdaptorMenloNetEgStatsDropLifCfgInvalidDeltaMin              Unsigned64,
    cfprAdaptorMenloNetEgStatsDropLifMapNoHit                        Unsigned64,
    cfprAdaptorMenloNetEgStatsDropLifMapNoHitDelta                   Counter64,
    cfprAdaptorMenloNetEgStatsDropLifMapNoHitDeltaAvg                Unsigned64,
    cfprAdaptorMenloNetEgStatsDropLifMapNoHitDeltaMax                Unsigned64,
    cfprAdaptorMenloNetEgStatsDropLifMapNoHitDeltaMin                Unsigned64,
    cfprAdaptorMenloNetEgStatsDropSrcBind                            Unsigned64,
    cfprAdaptorMenloNetEgStatsDropSrcBindDelta                       Counter64,
    cfprAdaptorMenloNetEgStatsDropSrcBindDeltaAvg                    Unsigned64,
    cfprAdaptorMenloNetEgStatsDropSrcBindDeltaMax                    Unsigned64,
    cfprAdaptorMenloNetEgStatsDropSrcBindDeltaMin                    Unsigned64,
    cfprAdaptorMenloNetEgStatsIntervals                              Gauge32,
    cfprAdaptorMenloNetEgStatsLearnReqDrop                           Unsigned64,
    cfprAdaptorMenloNetEgStatsLearnReqDropDelta                      Counter64,
    cfprAdaptorMenloNetEgStatsLearnReqDropDeltaAvg                   Unsigned64,
    cfprAdaptorMenloNetEgStatsLearnReqDropDeltaMax                   Unsigned64,
    cfprAdaptorMenloNetEgStatsLearnReqDropDeltaMin                   Unsigned64,
    cfprAdaptorMenloNetEgStatsMenloNetIndex                          CfprAdaptorMenloStatsIndex,
    cfprAdaptorMenloNetEgStatsSuspect                                TruthValue,
    cfprAdaptorMenloNetEgStatsThresholded                            CfprAdaptorMenloNetEgStatsThresholded,
    cfprAdaptorMenloNetEgStatsTimeCollected                          DateAndTime,
    cfprAdaptorMenloNetEgStatsUpdate                                 Gauge32
}

cfprAdaptorMenloNetEgStatsInstanceId OBJECT-TYPE
    SYNTAX       CfprManagedObjectId
    MAX-ACCESS   not-accessible
    STATUS       current
    DESCRIPTION
        "Instance identifier of the managed object."
    ::= { cfprAdaptorMenloNetEgStatsEntry 1 }

cfprAdaptorMenloNetEgStatsDn OBJECT-TYPE
    SYNTAX       CfprManagedObjectDn
    MAX-ACCESS   read-only
    STATUS       current
    DESCRIPTION
        "Cisco Firepower adaptor:MenloNetEgStats:dn managed
        object property"
    ::= { cfprAdaptorMenloNetEgStatsEntry 2 }

cfprAdaptorMenloNetEgStatsRn OBJECT-TYPE
    SYNTAX       SnmpAdminString
    MAX-ACCESS   read-only
    STATUS       current
    DESCRIPTION
        "Cisco Firepower adaptor:MenloNetEgStats:rn managed
        object property"
    ::= { cfprAdaptorMenloNetEgStatsEntry 3 }

cfprAdaptorMenloNetEgStatsDropCmd OBJECT-TYPE
    SYNTAX       Unsigned64
    MAX-ACCESS   read-only
    STATUS       current
    DESCRIPTION
        "Cisco Firepower adaptor:MenloNetEgStats:dropCmd
        managed object property"
    ::= { cfprAdaptorMenloNetEgStatsEntry 4 }

cfprAdaptorMenloNetEgStatsDropCmdDelta OBJECT-TYPE
    SYNTAX       Counter64
    MAX-ACCESS   read-only
    STATUS       current
    DESCRIPTION
        "Cisco Firepower adaptor:MenloNetEgStats:dropCmdDelta
        managed object property"
    ::= { cfprAdaptorMenloNetEgStatsEntry 5 }

cfprAdaptorMenloNetEgStatsDropCmdDeltaAvg OBJECT-TYPE
    SYNTAX       Unsigned64
    MAX-ACCESS   read-only
    STATUS       current
    DESCRIPTION
        "Cisco Firepower adaptor:MenloNetEgStats:dropCmdDeltaAvg
        managed object property"
    ::= { cfprAdaptorMenloNetEgStatsEntry 6 }

cfprAdaptorMenloNetEgStatsDropCmdDeltaMax OBJECT-TYPE
    SYNTAX       Unsigned64
    MAX-ACCESS   read-only
    STATUS       current
    DESCRIPTION
        "Cisco Firepower adaptor:MenloNetEgStats:dropCmdDeltaMax
        managed object property"
    ::= { cfprAdaptorMenloNetEgStatsEntry 7 }

cfprAdaptorMenloNetEgStatsDropCmdDeltaMin OBJECT-TYPE
    SYNTAX       Unsigned64
    MAX-ACCESS   read-only
    STATUS       current
    DESCRIPTION
        "Cisco Firepower adaptor:MenloNetEgStats:dropCmdDeltaMin
        managed object property"
    ::= { cfprAdaptorMenloNetEgStatsEntry 8 }

cfprAdaptorMenloNetEgStatsDropLifCfgInvalid OBJECT-TYPE
    SYNTAX       Unsigned64
    MAX-ACCESS   read-only
    STATUS       current
    DESCRIPTION
        "Cisco Firepower adaptor:MenloNetEgStats:dropLifCfgInvalid
        managed object property"
    ::= { cfprAdaptorMenloNetEgStatsEntry 9 }

cfprAdaptorMenloNetEgStatsDropLifCfgInvalidDelta OBJECT-TYPE
    SYNTAX       Counter64
    MAX-ACCESS   read-only
    STATUS       current
    DESCRIPTION
        "Cisco Firepower adaptor:MenloNetEgStats:dropLifCfgInvalidDelta
        managed object property"
    ::= { cfprAdaptorMenloNetEgStatsEntry 10 }

cfprAdaptorMenloNetEgStatsDropLifCfgInvalidDeltaAvg OBJECT-TYPE
    SYNTAX       Unsigned64
    MAX-ACCESS   read-only
    STATUS       current
    DESCRIPTION
        "Cisco Firepower adaptor:MenloNetEgStats:dropLifCfgInvalidDeltaAvg
         managed object property"
    ::= { cfprAdaptorMenloNetEgStatsEntry 11 }

cfprAdaptorMenloNetEgStatsDropLifCfgInvalidDeltaMax OBJECT-TYPE
    SYNTAX       Unsigned64
    MAX-ACCESS   read-only
    STATUS       current
    DESCRIPTION
        "Cisco Firepower adaptor:MenloNetEgStats:dropLifCfgInvalidDeltaMax
         managed object property"
    ::= { cfprAdaptorMenloNetEgStatsEntry 12 }

cfprAdaptorMenloNetEgStatsDropLifCfgInvalidDeltaMin OBJECT-TYPE
    SYNTAX       Unsigned64
    MAX-ACCESS   read-only
    STATUS       current
    DESCRIPTION
        "Cisco Firepower adaptor:MenloNetEgStats:dropLifCfgInvalidDeltaMin
         managed object property"
    ::= { cfprAdaptorMenloNetEgStatsEntry 13 }

cfprAdaptorMenloNetEgStatsDropLifMapNoHit OBJECT-TYPE
    SYNTAX       Unsigned64
    MAX-ACCESS   read-only
    STATUS       current
    DESCRIPTION
        "Cisco Firepower adaptor:MenloNetEgStats:dropLifMapNoHit
        managed object property"
    ::= { cfprAdaptorMenloNetEgStatsEntry 14 }

cfprAdaptorMenloNetEgStatsDropLifMapNoHitDelta OBJECT-TYPE
    SYNTAX       Counter64
    MAX-ACCESS   read-only
    STATUS       current
    DESCRIPTION
        "Cisco Firepower adaptor:MenloNetEgStats:dropLifMapNoHitDelta
        managed object property"
    ::= { cfprAdaptorMenloNetEgStatsEntry 15 }

cfprAdaptorMenloNetEgStatsDropLifMapNoHitDeltaAvg OBJECT-TYPE
    SYNTAX       Unsigned64
    MAX-ACCESS   read-only
    STATUS       current
    DESCRIPTION
        "Cisco Firepower adaptor:MenloNetEgStats:dropLifMapNoHitDeltaAvg
        managed object property"
    ::= { cfprAdaptorMenloNetEgStatsEntry 16 }

cfprAdaptorMenloNetEgStatsDropLifMapNoHitDeltaMax OBJECT-TYPE
    SYNTAX       Unsigned64
    MAX-ACCESS   read-only
    STATUS       current
    DESCRIPTION
        "Cisco Firepower adaptor:MenloNetEgStats:dropLifMapNoHitDeltaMax
        managed object property"
    ::= { cfprAdaptorMenloNetEgStatsEntry 17 }

cfprAdaptorMenloNetEgStatsDropLifMapNoHitDeltaMin OBJECT-TYPE
    SYNTAX       Unsigned64
    MAX-ACCESS   read-only
    STATUS       current
    DESCRIPTION
        "Cisco Firepower adaptor:MenloNetEgStats:dropLifMapNoHitDeltaMin
        managed object property"
    ::= { cfprAdaptorMenloNetEgStatsEntry 18 }

cfprAdaptorMenloNetEgStatsDropSrcBind OBJECT-TYPE
    SYNTAX       Unsigned64
    MAX-ACCESS   read-only
    STATUS       current
    DESCRIPTION
        "Cisco Firepower adaptor:MenloNetEgStats:dropSrcBind
        managed object property"
    ::= { cfprAdaptorMenloNetEgStatsEntry 19 }

cfprAdaptorMenloNetEgStatsDropSrcBindDelta OBJECT-TYPE
    SYNTAX       Counter64
    MAX-ACCESS   read-only
    STATUS       current
    DESCRIPTION
        "Cisco Firepower adaptor:MenloNetEgStats:dropSrcBindDelta
        managed object property"
    ::= { cfprAdaptorMenloNetEgStatsEntry 20 }

cfprAdaptorMenloNetEgStatsDropSrcBindDeltaAvg OBJECT-TYPE
    SYNTAX       Unsigned64
    MAX-ACCESS   read-only
    STATUS       current
    DESCRIPTION
        "Cisco Firepower adaptor:MenloNetEgStats:dropSrcBindDeltaAvg
        managed object property"
    ::= { cfprAdaptorMenloNetEgStatsEntry 21 }

cfprAdaptorMenloNetEgStatsDropSrcBindDeltaMax OBJECT-TYPE
    SYNTAX       Unsigned64
    MAX-ACCESS   read-only
    STATUS       current
    DESCRIPTION
        "Cisco Firepower adaptor:MenloNetEgStats:dropSrcBindDeltaMax
        managed object property"
    ::= { cfprAdaptorMenloNetEgStatsEntry 22 }

cfprAdaptorMenloNetEgStatsDropSrcBindDeltaMin OBJECT-TYPE
    SYNTAX       Unsigned64
    MAX-ACCESS   read-only
    STATUS       current
    DESCRIPTION
        "Cisco Firepower adaptor:MenloNetEgStats:dropSrcBindDeltaMin
        managed object property"
    ::= { cfprAdaptorMenloNetEgStatsEntry 23 }

cfprAdaptorMenloNetEgStatsIntervals OBJECT-TYPE
    SYNTAX       Gauge32
    MAX-ACCESS   read-only
    STATUS       current
    DESCRIPTION
        "Cisco Firepower adaptor:MenloNetEgStats:intervals
        managed object property"
    ::= { cfprAdaptorMenloNetEgStatsEntry 24 }

cfprAdaptorMenloNetEgStatsLearnReqDrop OBJECT-TYPE
    SYNTAX       Unsigned64
    MAX-ACCESS   read-only
    STATUS       current
    DESCRIPTION
        "Cisco Firepower adaptor:MenloNetEgStats:learnReqDrop
        managed object property"
    ::= { cfprAdaptorMenloNetEgStatsEntry 25 }

cfprAdaptorMenloNetEgStatsLearnReqDropDelta OBJECT-TYPE
    SYNTAX       Counter64
    MAX-ACCESS   read-only
    STATUS       current
    DESCRIPTION
        "Cisco Firepower adaptor:MenloNetEgStats:learnReqDropDelta
        managed object property"
    ::= { cfprAdaptorMenloNetEgStatsEntry 26 }

cfprAdaptorMenloNetEgStatsLearnReqDropDeltaAvg OBJECT-TYPE
    SYNTAX       Unsigned64
    MAX-ACCESS   read-only
    STATUS       current
    DESCRIPTION
        "Cisco Firepower adaptor:MenloNetEgStats:learnReqDropDeltaAvg
        managed object property"
    ::= { cfprAdaptorMenloNetEgStatsEntry 27 }

cfprAdaptorMenloNetEgStatsLearnReqDropDeltaMax OBJECT-TYPE
    SYNTAX       Unsigned64
    MAX-ACCESS   read-only
    STATUS       current
    DESCRIPTION
        "Cisco Firepower adaptor:MenloNetEgStats:learnReqDropDeltaMax
        managed object property"
    ::= { cfprAdaptorMenloNetEgStatsEntry 28 }

cfprAdaptorMenloNetEgStatsLearnReqDropDeltaMin OBJECT-TYPE
    SYNTAX       Unsigned64
    MAX-ACCESS   read-only
    STATUS       current
    DESCRIPTION
        "Cisco Firepower adaptor:MenloNetEgStats:learnReqDropDeltaMin
        managed object property"
    ::= { cfprAdaptorMenloNetEgStatsEntry 29 }

cfprAdaptorMenloNetEgStatsMenloNetIndex OBJECT-TYPE
    SYNTAX       CfprAdaptorMenloStatsIndex
    MAX-ACCESS   read-only
    STATUS       current
    DESCRIPTION
        "Cisco Firepower adaptor:MenloNetEgStats:menloNetIndex
        managed object property"
    ::= { cfprAdaptorMenloNetEgStatsEntry 30 }

cfprAdaptorMenloNetEgStatsSuspect OBJECT-TYPE
    SYNTAX       TruthValue
    MAX-ACCESS   read-only
    STATUS       current
    DESCRIPTION
        "Cisco Firepower adaptor:MenloNetEgStats:suspect
        managed object property"
    ::= { cfprAdaptorMenloNetEgStatsEntry 31 }

cfprAdaptorMenloNetEgStatsThresholded OBJECT-TYPE
    SYNTAX       CfprAdaptorMenloNetEgStatsThresholded
    MAX-ACCESS   read-only
    STATUS       current
    DESCRIPTION
        "Cisco Firepower adaptor:MenloNetEgStats:thresholded
        managed object property"
    ::= { cfprAdaptorMenloNetEgStatsEntry 32 }

cfprAdaptorMenloNetEgStatsTimeCollected OBJECT-TYPE
    SYNTAX       DateAndTime
    MAX-ACCESS   read-only
    STATUS       current
    DESCRIPTION
        "Cisco Firepower adaptor:MenloNetEgStats:timeCollected
        managed object property"
    ::= { cfprAdaptorMenloNetEgStatsEntry 33 }

cfprAdaptorMenloNetEgStatsUpdate OBJECT-TYPE
    SYNTAX       Gauge32
    MAX-ACCESS   read-only
    STATUS       current
    DESCRIPTION
        "Cisco Firepower adaptor:MenloNetEgStats:update
        managed object property"
    ::= { cfprAdaptorMenloNetEgStatsEntry 34 }

cfprAdaptorMenloNetEgStatsHistTable OBJECT-TYPE
    SYNTAX           SEQUENCE OF CfprAdaptorMenloNetEgStatsHistEntry
    MAX-ACCESS       not-accessible
    STATUS           current
    DESCRIPTION
        "Cisco Firepower adaptor:MenloNetEgStatsHist managed object table"
    ::= { cfprAdaptorObjects 101 }

cfprAdaptorMenloNetEgStatsHistEntry OBJECT-TYPE
    SYNTAX           CfprAdaptorMenloNetEgStatsHistEntry
    MAX-ACCESS       not-accessible
    STATUS           current
    DESCRIPTION
        "Entry for the cfprAdaptorMenloNetEgStatsHistTable table."
    INDEX { cfprAdaptorMenloNetEgStatsHistInstanceId }
    ::= { cfprAdaptorMenloNetEgStatsHistTable 1 }

CfprAdaptorMenloNetEgStatsHistEntry ::= SEQUENCE {
    cfprAdaptorMenloNetEgStatsHistInstanceId                         CfprManagedObjectId,
    cfprAdaptorMenloNetEgStatsHistDn                                 CfprManagedObjectDn,
    cfprAdaptorMenloNetEgStatsHistRn                                 SnmpAdminString,
    cfprAdaptorMenloNetEgStatsHistDropCmd                            Unsigned64,
    cfprAdaptorMenloNetEgStatsHistDropCmdDelta                       Unsigned64,
    cfprAdaptorMenloNetEgStatsHistDropCmdDeltaAvg                    Unsigned64,
    cfprAdaptorMenloNetEgStatsHistDropCmdDeltaMax                    Unsigned64,
    cfprAdaptorMenloNetEgStatsHistDropCmdDeltaMin                    Unsigned64,
    cfprAdaptorMenloNetEgStatsHistDropLifCfgInvalid                  Unsigned64,
    cfprAdaptorMenloNetEgStatsHistDropLifCfgInvalidDelta             Unsigned64,
    cfprAdaptorMenloNetEgStatsHistDropLifCfgInvalidDeltaAvg          Unsigned64,
    cfprAdaptorMenloNetEgStatsHistDropLifCfgInvalidDeltaMax          Unsigned64,
    cfprAdaptorMenloNetEgStatsHistDropLifCfgInvalidDeltaMin          Unsigned64,
    cfprAdaptorMenloNetEgStatsHistDropLifMapNoHit                    Unsigned64,
    cfprAdaptorMenloNetEgStatsHistDropLifMapNoHitDelta               Unsigned64,
    cfprAdaptorMenloNetEgStatsHistDropLifMapNoHitDeltaAvg            Unsigned64,
    cfprAdaptorMenloNetEgStatsHistDropLifMapNoHitDeltaMax            Unsigned64,
    cfprAdaptorMenloNetEgStatsHistDropLifMapNoHitDeltaMin            Unsigned64,
    cfprAdaptorMenloNetEgStatsHistDropSrcBind                        Unsigned64,
    cfprAdaptorMenloNetEgStatsHistDropSrcBindDelta                   Unsigned64,
    cfprAdaptorMenloNetEgStatsHistDropSrcBindDeltaAvg                Unsigned64,
    cfprAdaptorMenloNetEgStatsHistDropSrcBindDeltaMax                Unsigned64,
    cfprAdaptorMenloNetEgStatsHistDropSrcBindDeltaMin                Unsigned64,
    cfprAdaptorMenloNetEgStatsHistId                                 Unsigned64,
    cfprAdaptorMenloNetEgStatsHistLearnReqDrop                       Unsigned64,
    cfprAdaptorMenloNetEgStatsHistLearnReqDropDelta                  Unsigned64,
    cfprAdaptorMenloNetEgStatsHistLearnReqDropDeltaAvg               Unsigned64,
    cfprAdaptorMenloNetEgStatsHistLearnReqDropDeltaMax               Unsigned64,
    cfprAdaptorMenloNetEgStatsHistLearnReqDropDeltaMin               Unsigned64,
    cfprAdaptorMenloNetEgStatsHistMostRecent                         TruthValue,
    cfprAdaptorMenloNetEgStatsHistSuspect                            TruthValue,
    cfprAdaptorMenloNetEgStatsHistThresholded                        CfprAdaptorMenloNetEgStatsHistThresholded,
    cfprAdaptorMenloNetEgStatsHistTimeCollected                      DateAndTime
}

cfprAdaptorMenloNetEgStatsHistInstanceId OBJECT-TYPE
    SYNTAX       CfprManagedObjectId
    MAX-ACCESS   not-accessible
    STATUS       current
    DESCRIPTION
        "Instance identifier of the managed object."
    ::= { cfprAdaptorMenloNetEgStatsHistEntry 1 }

cfprAdaptorMenloNetEgStatsHistDn OBJECT-TYPE
    SYNTAX       CfprManagedObjectDn
    MAX-ACCESS   read-only
    STATUS       current
    DESCRIPTION
        "Cisco Firepower adaptor:MenloNetEgStatsHist:dn
        managed object property"
    ::= { cfprAdaptorMenloNetEgStatsHistEntry 2 }

cfprAdaptorMenloNetEgStatsHistRn OBJECT-TYPE
    SYNTAX       SnmpAdminString
    MAX-ACCESS   read-only
    STATUS       current
    DESCRIPTION
        "Cisco Firepower adaptor:MenloNetEgStatsHist:rn
        managed object property"
    ::= { cfprAdaptorMenloNetEgStatsHistEntry 3 }

cfprAdaptorMenloNetEgStatsHistDropCmd OBJECT-TYPE
    SYNTAX       Unsigned64
    MAX-ACCESS   read-only
    STATUS       current
    DESCRIPTION
        "Cisco Firepower adaptor:MenloNetEgStatsHist:dropCmd
        managed object property"
    ::= { cfprAdaptorMenloNetEgStatsHistEntry 4 }

cfprAdaptorMenloNetEgStatsHistDropCmdDelta OBJECT-TYPE
    SYNTAX       Unsigned64
    MAX-ACCESS   read-only
    STATUS       current
    DESCRIPTION
        "Cisco Firepower adaptor:MenloNetEgStatsHist:dropCmdDelta
        managed object property"
    ::= { cfprAdaptorMenloNetEgStatsHistEntry 5 }

cfprAdaptorMenloNetEgStatsHistDropCmdDeltaAvg OBJECT-TYPE
    SYNTAX       Unsigned64
    MAX-ACCESS   read-only
    STATUS       current
    DESCRIPTION
        "Cisco Firepower adaptor:MenloNetEgStatsHist:dropCmdDeltaAvg
        managed object property"
    ::= { cfprAdaptorMenloNetEgStatsHistEntry 6 }

cfprAdaptorMenloNetEgStatsHistDropCmdDeltaMax OBJECT-TYPE
    SYNTAX       Unsigned64
    MAX-ACCESS   read-only
    STATUS       current
    DESCRIPTION
        "Cisco Firepower adaptor:MenloNetEgStatsHist:dropCmdDeltaMax
        managed object property"
    ::= { cfprAdaptorMenloNetEgStatsHistEntry 7 }

cfprAdaptorMenloNetEgStatsHistDropCmdDeltaMin OBJECT-TYPE
    SYNTAX       Unsigned64
    MAX-ACCESS   read-only
    STATUS       current
    DESCRIPTION
        "Cisco Firepower adaptor:MenloNetEgStatsHist:dropCmdDeltaMin
        managed object property"
    ::= { cfprAdaptorMenloNetEgStatsHistEntry 8 }

cfprAdaptorMenloNetEgStatsHistDropLifCfgInvalid OBJECT-TYPE
    SYNTAX       Unsigned64
    MAX-ACCESS   read-only
    STATUS       current
    DESCRIPTION
        "Cisco Firepower adaptor:MenloNetEgStatsHist:dropLifCfgInvalid
        managed object property"
    ::= { cfprAdaptorMenloNetEgStatsHistEntry 9 }

cfprAdaptorMenloNetEgStatsHistDropLifCfgInvalidDelta OBJECT-TYPE
    SYNTAX       Unsigned64
    MAX-ACCESS   read-only
    STATUS       current
    DESCRIPTION
        "Cisco Firepower adaptor:MenloNetEgStatsHist:dropLifCfgInvalidDelt
        a managed object property"
    ::= { cfprAdaptorMenloNetEgStatsHistEntry 10 }

cfprAdaptorMenloNetEgStatsHistDropLifCfgInvalidDeltaAvg OBJECT-TYPE
    SYNTAX       Unsigned64
    MAX-ACCESS   read-only
    STATUS       current
    DESCRIPTION
        "Cisco Firepower adaptor:MenloNetEgStatsHist:dropLifCfgInvalidDelt
        aAvg managed object property"
    ::= { cfprAdaptorMenloNetEgStatsHistEntry 11 }

cfprAdaptorMenloNetEgStatsHistDropLifCfgInvalidDeltaMax OBJECT-TYPE
    SYNTAX       Unsigned64
    MAX-ACCESS   read-only
    STATUS       current
    DESCRIPTION
        "Cisco Firepower adaptor:MenloNetEgStatsHist:dropLifCfgInvalidDelt
        aMax managed object property"
    ::= { cfprAdaptorMenloNetEgStatsHistEntry 12 }

cfprAdaptorMenloNetEgStatsHistDropLifCfgInvalidDeltaMin OBJECT-TYPE
    SYNTAX       Unsigned64
    MAX-ACCESS   read-only
    STATUS       current
    DESCRIPTION
        "Cisco Firepower adaptor:MenloNetEgStatsHist:dropLifCfgInvalidDelt
        aMin managed object property"
    ::= { cfprAdaptorMenloNetEgStatsHistEntry 13 }

cfprAdaptorMenloNetEgStatsHistDropLifMapNoHit OBJECT-TYPE
    SYNTAX       Unsigned64
    MAX-ACCESS   read-only
    STATUS       current
    DESCRIPTION
        "Cisco Firepower adaptor:MenloNetEgStatsHist:dropLifMapNoHit
        managed object property"
    ::= { cfprAdaptorMenloNetEgStatsHistEntry 14 }

cfprAdaptorMenloNetEgStatsHistDropLifMapNoHitDelta OBJECT-TYPE
    SYNTAX       Unsigned64
    MAX-ACCESS   read-only
    STATUS       current
    DESCRIPTION
        "Cisco Firepower adaptor:MenloNetEgStatsHist:dropLifMapNoHitDelta
        managed object property"
    ::= { cfprAdaptorMenloNetEgStatsHistEntry 15 }

cfprAdaptorMenloNetEgStatsHistDropLifMapNoHitDeltaAvg OBJECT-TYPE
    SYNTAX       Unsigned64
    MAX-ACCESS   read-only
    STATUS       current
    DESCRIPTION
        "Cisco Firepower adaptor:MenloNetEgStatsHist:dropLifMapNoHitDeltaA
        vg managed object property"
    ::= { cfprAdaptorMenloNetEgStatsHistEntry 16 }

cfprAdaptorMenloNetEgStatsHistDropLifMapNoHitDeltaMax OBJECT-TYPE
    SYNTAX       Unsigned64
    MAX-ACCESS   read-only
    STATUS       current
    DESCRIPTION
        "Cisco Firepower adaptor:MenloNetEgStatsHist:dropLifMapNoHitDeltaM
        ax managed object property"
    ::= { cfprAdaptorMenloNetEgStatsHistEntry 17 }

cfprAdaptorMenloNetEgStatsHistDropLifMapNoHitDeltaMin OBJECT-TYPE
    SYNTAX       Unsigned64
    MAX-ACCESS   read-only
    STATUS       current
    DESCRIPTION
        "Cisco Firepower adaptor:MenloNetEgStatsHist:dropLifMapNoHitDeltaM
        in managed object property"
    ::= { cfprAdaptorMenloNetEgStatsHistEntry 18 }

cfprAdaptorMenloNetEgStatsHistDropSrcBind OBJECT-TYPE
    SYNTAX       Unsigned64
    MAX-ACCESS   read-only
    STATUS       current
    DESCRIPTION
        "Cisco Firepower adaptor:MenloNetEgStatsHist:dropSrcBind
        managed object property"
    ::= { cfprAdaptorMenloNetEgStatsHistEntry 19 }

cfprAdaptorMenloNetEgStatsHistDropSrcBindDelta OBJECT-TYPE
    SYNTAX       Unsigned64
    MAX-ACCESS   read-only
    STATUS       current
    DESCRIPTION
        "Cisco Firepower adaptor:MenloNetEgStatsHist:dropSrcBindDelta
        managed object property"
    ::= { cfprAdaptorMenloNetEgStatsHistEntry 20 }

cfprAdaptorMenloNetEgStatsHistDropSrcBindDeltaAvg OBJECT-TYPE
    SYNTAX       Unsigned64
    MAX-ACCESS   read-only
    STATUS       current
    DESCRIPTION
        "Cisco Firepower adaptor:MenloNetEgStatsHist:dropSrcBindDeltaAvg
        managed object property"
    ::= { cfprAdaptorMenloNetEgStatsHistEntry 21 }

cfprAdaptorMenloNetEgStatsHistDropSrcBindDeltaMax OBJECT-TYPE
    SYNTAX       Unsigned64
    MAX-ACCESS   read-only
    STATUS       current
    DESCRIPTION
        "Cisco Firepower adaptor:MenloNetEgStatsHist:dropSrcBindDeltaMax
        managed object property"
    ::= { cfprAdaptorMenloNetEgStatsHistEntry 22 }

cfprAdaptorMenloNetEgStatsHistDropSrcBindDeltaMin OBJECT-TYPE
    SYNTAX       Unsigned64
    MAX-ACCESS   read-only
    STATUS       current
    DESCRIPTION
        "Cisco Firepower adaptor:MenloNetEgStatsHist:dropSrcBindDeltaMin
        managed object property"
    ::= { cfprAdaptorMenloNetEgStatsHistEntry 23 }

cfprAdaptorMenloNetEgStatsHistId OBJECT-TYPE
    SYNTAX       Unsigned64
    MAX-ACCESS   read-only
    STATUS       current
    DESCRIPTION
        "Cisco Firepower adaptor:MenloNetEgStatsHist:id
        managed object property"
    ::= { cfprAdaptorMenloNetEgStatsHistEntry 24 }

cfprAdaptorMenloNetEgStatsHistLearnReqDrop OBJECT-TYPE
    SYNTAX       Unsigned64
    MAX-ACCESS   read-only
    STATUS       current
    DESCRIPTION
        "Cisco Firepower adaptor:MenloNetEgStatsHist:learnReqDrop
        managed object property"
    ::= { cfprAdaptorMenloNetEgStatsHistEntry 25 }

cfprAdaptorMenloNetEgStatsHistLearnReqDropDelta OBJECT-TYPE
    SYNTAX       Unsigned64
    MAX-ACCESS   read-only
    STATUS       current
    DESCRIPTION
        "Cisco Firepower adaptor:MenloNetEgStatsHist:learnReqDropDelta
        managed object property"
    ::= { cfprAdaptorMenloNetEgStatsHistEntry 26 }

cfprAdaptorMenloNetEgStatsHistLearnReqDropDeltaAvg OBJECT-TYPE
    SYNTAX       Unsigned64
    MAX-ACCESS   read-only
    STATUS       current
    DESCRIPTION
        "Cisco Firepower adaptor:MenloNetEgStatsHist:learnReqDropDeltaAvg
        managed object property"
    ::= { cfprAdaptorMenloNetEgStatsHistEntry 27 }

cfprAdaptorMenloNetEgStatsHistLearnReqDropDeltaMax OBJECT-TYPE
    SYNTAX       Unsigned64
    MAX-ACCESS   read-only
    STATUS       current
    DESCRIPTION
        "Cisco Firepower adaptor:MenloNetEgStatsHist:learnReqDropDeltaMax
        managed object property"
    ::= { cfprAdaptorMenloNetEgStatsHistEntry 28 }

cfprAdaptorMenloNetEgStatsHistLearnReqDropDeltaMin OBJECT-TYPE
    SYNTAX       Unsigned64
    MAX-ACCESS   read-only
    STATUS       current
    DESCRIPTION
        "Cisco Firepower adaptor:MenloNetEgStatsHist:learnReqDropDeltaMin
        managed object property"
    ::= { cfprAdaptorMenloNetEgStatsHistEntry 29 }

cfprAdaptorMenloNetEgStatsHistMostRecent OBJECT-TYPE
    SYNTAX       TruthValue
    MAX-ACCESS   read-only
    STATUS       current
    DESCRIPTION
        "Cisco Firepower adaptor:MenloNetEgStatsHist:mostRecent
        managed object property"
    ::= { cfprAdaptorMenloNetEgStatsHistEntry 30 }

cfprAdaptorMenloNetEgStatsHistSuspect OBJECT-TYPE
    SYNTAX       TruthValue
    MAX-ACCESS   read-only
    STATUS       current
    DESCRIPTION
        "Cisco Firepower adaptor:MenloNetEgStatsHist:suspect
        managed object property"
    ::= { cfprAdaptorMenloNetEgStatsHistEntry 31 }

cfprAdaptorMenloNetEgStatsHistThresholded OBJECT-TYPE
    SYNTAX       CfprAdaptorMenloNetEgStatsHistThresholded
    MAX-ACCESS   read-only
    STATUS       current
    DESCRIPTION
        "Cisco Firepower adaptor:MenloNetEgStatsHist:thresholded
        managed object property"
    ::= { cfprAdaptorMenloNetEgStatsHistEntry 32 }

cfprAdaptorMenloNetEgStatsHistTimeCollected OBJECT-TYPE
    SYNTAX       DateAndTime
    MAX-ACCESS   read-only
    STATUS       current
    DESCRIPTION
        "Cisco Firepower adaptor:MenloNetEgStatsHist:timeCollected
        managed object property"
    ::= { cfprAdaptorMenloNetEgStatsHistEntry 33 }

cfprAdaptorMenloNetInStatsTable OBJECT-TYPE
    SYNTAX           SEQUENCE OF CfprAdaptorMenloNetInStatsEntry
    MAX-ACCESS       not-accessible
    STATUS           current
    DESCRIPTION
        "Cisco Firepower adaptor:MenloNetInStats managed object table"
    ::= { cfprAdaptorObjects 102 }

cfprAdaptorMenloNetInStatsEntry OBJECT-TYPE
    SYNTAX           CfprAdaptorMenloNetInStatsEntry
    MAX-ACCESS       not-accessible
    STATUS           current
    DESCRIPTION
        "Entry for the cfprAdaptorMenloNetInStatsTable table."
    INDEX { cfprAdaptorMenloNetInStatsInstanceId }
    ::= { cfprAdaptorMenloNetInStatsTable 1 }

CfprAdaptorMenloNetInStatsEntry ::= SEQUENCE {
    cfprAdaptorMenloNetInStatsInstanceId                             CfprManagedObjectId,
    cfprAdaptorMenloNetInStatsDn                                     CfprManagedObjectDn,
    cfprAdaptorMenloNetInStatsRn                                     SnmpAdminString,
    cfprAdaptorMenloNetInStatsDropFcLifInvalid                       Unsigned64,
    cfprAdaptorMenloNetInStatsDropFcLifInvalidDelta                  Counter64,
    cfprAdaptorMenloNetInStatsDropFcLifInvalidDeltaAvg               Unsigned64,
    cfprAdaptorMenloNetInStatsDropFcLifInvalidDeltaMax               Unsigned64,
    cfprAdaptorMenloNetInStatsDropFcLifInvalidDeltaMin               Unsigned64,
    cfprAdaptorMenloNetInStatsDropFcMulticast                        Unsigned64,
    cfprAdaptorMenloNetInStatsDropFcMulticastDelta                   Counter64,
    cfprAdaptorMenloNetInStatsDropFcMulticastDeltaAvg                Unsigned64,
    cfprAdaptorMenloNetInStatsDropFcMulticastDeltaMax                Unsigned64,
    cfprAdaptorMenloNetInStatsDropFcMulticastDeltaMin                Unsigned64,
    cfprAdaptorMenloNetInStatsDropNullPif                            Unsigned64,
    cfprAdaptorMenloNetInStatsDropNullPifDelta                       Counter64,
    cfprAdaptorMenloNetInStatsDropNullPifDeltaAvg                    Unsigned64,
    cfprAdaptorMenloNetInStatsDropNullPifDeltaMax                    Unsigned64,
    cfprAdaptorMenloNetInStatsDropNullPifDeltaMin                    Unsigned64,
    cfprAdaptorMenloNetInStatsFwdLookupNoHit                         Unsigned64,
    cfprAdaptorMenloNetInStatsFwdLookupNoHitDelta                    Counter64,
    cfprAdaptorMenloNetInStatsFwdLookupNoHitDeltaAvg                 Unsigned64,
    cfprAdaptorMenloNetInStatsFwdLookupNoHitDeltaMax                 Unsigned64,
    cfprAdaptorMenloNetInStatsFwdLookupNoHitDeltaMin                 Unsigned64,
    cfprAdaptorMenloNetInStatsIntervals                              Gauge32,
    cfprAdaptorMenloNetInStatsMenloNetIndex                          CfprAdaptorMenloStatsIndex,
    cfprAdaptorMenloNetInStatsSuspect                                TruthValue,
    cfprAdaptorMenloNetInStatsThresholded                            CfprAdaptorMenloNetInStatsThresholded,
    cfprAdaptorMenloNetInStatsTimeCollected                          DateAndTime,
    cfprAdaptorMenloNetInStatsUpdate                                 Gauge32
}

cfprAdaptorMenloNetInStatsInstanceId OBJECT-TYPE
    SYNTAX       CfprManagedObjectId
    MAX-ACCESS   not-accessible
    STATUS       current
    DESCRIPTION
        "Instance identifier of the managed object."
    ::= { cfprAdaptorMenloNetInStatsEntry 1 }

cfprAdaptorMenloNetInStatsDn OBJECT-TYPE
    SYNTAX       CfprManagedObjectDn
    MAX-ACCESS   read-only
    STATUS       current
    DESCRIPTION
        "Cisco Firepower adaptor:MenloNetInStats:dn managed
        object property"
    ::= { cfprAdaptorMenloNetInStatsEntry 2 }

cfprAdaptorMenloNetInStatsRn OBJECT-TYPE
    SYNTAX       SnmpAdminString
    MAX-ACCESS   read-only
    STATUS       current
    DESCRIPTION
        "Cisco Firepower adaptor:MenloNetInStats:rn managed
        object property"
    ::= { cfprAdaptorMenloNetInStatsEntry 3 }

cfprAdaptorMenloNetInStatsDropFcLifInvalid OBJECT-TYPE
    SYNTAX       Unsigned64
    MAX-ACCESS   read-only
    STATUS       current
    DESCRIPTION
        "Cisco Firepower adaptor:MenloNetInStats:dropFcLifInvalid
        managed object property"
    ::= { cfprAdaptorMenloNetInStatsEntry 4 }

cfprAdaptorMenloNetInStatsDropFcLifInvalidDelta OBJECT-TYPE
    SYNTAX       Counter64
    MAX-ACCESS   read-only
    STATUS       current
    DESCRIPTION
        "Cisco Firepower adaptor:MenloNetInStats:dropFcLifInvalidDelta
        managed object property"
    ::= { cfprAdaptorMenloNetInStatsEntry 5 }

cfprAdaptorMenloNetInStatsDropFcLifInvalidDeltaAvg OBJECT-TYPE
    SYNTAX       Unsigned64
    MAX-ACCESS   read-only
    STATUS       current
    DESCRIPTION
        "Cisco Firepower adaptor:MenloNetInStats:dropFcLifInvalidDeltaAvg
        managed object property"
    ::= { cfprAdaptorMenloNetInStatsEntry 6 }

cfprAdaptorMenloNetInStatsDropFcLifInvalidDeltaMax OBJECT-TYPE
    SYNTAX       Unsigned64
    MAX-ACCESS   read-only
    STATUS       current
    DESCRIPTION
        "Cisco Firepower adaptor:MenloNetInStats:dropFcLifInvalidDeltaMax
        managed object property"
    ::= { cfprAdaptorMenloNetInStatsEntry 7 }

cfprAdaptorMenloNetInStatsDropFcLifInvalidDeltaMin OBJECT-TYPE
    SYNTAX       Unsigned64
    MAX-ACCESS   read-only
    STATUS       current
    DESCRIPTION
        "Cisco Firepower adaptor:MenloNetInStats:dropFcLifInvalidDeltaMin
        managed object property"
    ::= { cfprAdaptorMenloNetInStatsEntry 8 }

cfprAdaptorMenloNetInStatsDropFcMulticast OBJECT-TYPE
    SYNTAX       Unsigned64
    MAX-ACCESS   read-only
    STATUS       current
    DESCRIPTION
        "Cisco Firepower adaptor:MenloNetInStats:dropFcMulticast
        managed object property"
    ::= { cfprAdaptorMenloNetInStatsEntry 9 }

cfprAdaptorMenloNetInStatsDropFcMulticastDelta OBJECT-TYPE
    SYNTAX       Counter64
    MAX-ACCESS   read-only
    STATUS       current
    DESCRIPTION
        "Cisco Firepower adaptor:MenloNetInStats:dropFcMulticastDelta
        managed object property"
    ::= { cfprAdaptorMenloNetInStatsEntry 10 }

cfprAdaptorMenloNetInStatsDropFcMulticastDeltaAvg OBJECT-TYPE
    SYNTAX       Unsigned64
    MAX-ACCESS   read-only
    STATUS       current
    DESCRIPTION
        "Cisco Firepower adaptor:MenloNetInStats:dropFcMulticastDeltaAvg
        managed object property"
    ::= { cfprAdaptorMenloNetInStatsEntry 11 }

cfprAdaptorMenloNetInStatsDropFcMulticastDeltaMax OBJECT-TYPE
    SYNTAX       Unsigned64
    MAX-ACCESS   read-only
    STATUS       current
    DESCRIPTION
        "Cisco Firepower adaptor:MenloNetInStats:dropFcMulticastDeltaMax
        managed object property"
    ::= { cfprAdaptorMenloNetInStatsEntry 12 }

cfprAdaptorMenloNetInStatsDropFcMulticastDeltaMin OBJECT-TYPE
    SYNTAX       Unsigned64
    MAX-ACCESS   read-only
    STATUS       current
    DESCRIPTION
        "Cisco Firepower adaptor:MenloNetInStats:dropFcMulticastDeltaMin
        managed object property"
    ::= { cfprAdaptorMenloNetInStatsEntry 13 }

cfprAdaptorMenloNetInStatsDropNullPif OBJECT-TYPE
    SYNTAX       Unsigned64
    MAX-ACCESS   read-only
    STATUS       current
    DESCRIPTION
        "Cisco Firepower adaptor:MenloNetInStats:dropNullPif
        managed object property"
    ::= { cfprAdaptorMenloNetInStatsEntry 14 }

cfprAdaptorMenloNetInStatsDropNullPifDelta OBJECT-TYPE
    SYNTAX       Counter64
    MAX-ACCESS   read-only
    STATUS       current
    DESCRIPTION
        "Cisco Firepower adaptor:MenloNetInStats:dropNullPifDelta
        managed object property"
    ::= { cfprAdaptorMenloNetInStatsEntry 15 }

cfprAdaptorMenloNetInStatsDropNullPifDeltaAvg OBJECT-TYPE
    SYNTAX       Unsigned64
    MAX-ACCESS   read-only
    STATUS       current
    DESCRIPTION
        "Cisco Firepower adaptor:MenloNetInStats:dropNullPifDeltaAvg
        managed object property"
    ::= { cfprAdaptorMenloNetInStatsEntry 16 }

cfprAdaptorMenloNetInStatsDropNullPifDeltaMax OBJECT-TYPE
    SYNTAX       Unsigned64
    MAX-ACCESS   read-only
    STATUS       current
    DESCRIPTION
        "Cisco Firepower adaptor:MenloNetInStats:dropNullPifDeltaMax
        managed object property"
    ::= { cfprAdaptorMenloNetInStatsEntry 17 }

cfprAdaptorMenloNetInStatsDropNullPifDeltaMin OBJECT-TYPE
    SYNTAX       Unsigned64
    MAX-ACCESS   read-only
    STATUS       current
    DESCRIPTION
        "Cisco Firepower adaptor:MenloNetInStats:dropNullPifDeltaMin
        managed object property"
    ::= { cfprAdaptorMenloNetInStatsEntry 18 }

cfprAdaptorMenloNetInStatsFwdLookupNoHit OBJECT-TYPE
    SYNTAX       Unsigned64
    MAX-ACCESS   read-only
    STATUS       current
    DESCRIPTION
        "Cisco Firepower adaptor:MenloNetInStats:fwdLookupNoHit
        managed object property"
    ::= { cfprAdaptorMenloNetInStatsEntry 19 }

cfprAdaptorMenloNetInStatsFwdLookupNoHitDelta OBJECT-TYPE
    SYNTAX       Counter64
    MAX-ACCESS   read-only
    STATUS       current
    DESCRIPTION
        "Cisco Firepower adaptor:MenloNetInStats:fwdLookupNoHitDelta
        managed object property"
    ::= { cfprAdaptorMenloNetInStatsEntry 20 }

cfprAdaptorMenloNetInStatsFwdLookupNoHitDeltaAvg OBJECT-TYPE
    SYNTAX       Unsigned64
    MAX-ACCESS   read-only
    STATUS       current
    DESCRIPTION
        "Cisco Firepower adaptor:MenloNetInStats:fwdLookupNoHitDeltaAvg
        managed object property"
    ::= { cfprAdaptorMenloNetInStatsEntry 21 }

cfprAdaptorMenloNetInStatsFwdLookupNoHitDeltaMax OBJECT-TYPE
    SYNTAX       Unsigned64
    MAX-ACCESS   read-only
    STATUS       current
    DESCRIPTION
        "Cisco Firepower adaptor:MenloNetInStats:fwdLookupNoHitDeltaMax
        managed object property"
    ::= { cfprAdaptorMenloNetInStatsEntry 22 }

cfprAdaptorMenloNetInStatsFwdLookupNoHitDeltaMin OBJECT-TYPE
    SYNTAX       Unsigned64
    MAX-ACCESS   read-only
    STATUS       current
    DESCRIPTION
        "Cisco Firepower adaptor:MenloNetInStats:fwdLookupNoHitDeltaMin
        managed object property"
    ::= { cfprAdaptorMenloNetInStatsEntry 23 }

cfprAdaptorMenloNetInStatsIntervals OBJECT-TYPE
    SYNTAX       Gauge32
    MAX-ACCESS   read-only
    STATUS       current
    DESCRIPTION
        "Cisco Firepower adaptor:MenloNetInStats:intervals
        managed object property"
    ::= { cfprAdaptorMenloNetInStatsEntry 24 }

cfprAdaptorMenloNetInStatsMenloNetIndex OBJECT-TYPE
    SYNTAX       CfprAdaptorMenloStatsIndex
    MAX-ACCESS   read-only
    STATUS       current
    DESCRIPTION
        "Cisco Firepower adaptor:MenloNetInStats:menloNetIndex
        managed object property"
    ::= { cfprAdaptorMenloNetInStatsEntry 25 }

cfprAdaptorMenloNetInStatsSuspect OBJECT-TYPE
    SYNTAX       TruthValue
    MAX-ACCESS   read-only
    STATUS       current
    DESCRIPTION
        "Cisco Firepower adaptor:MenloNetInStats:suspect
        managed object property"
    ::= { cfprAdaptorMenloNetInStatsEntry 26 }

cfprAdaptorMenloNetInStatsThresholded OBJECT-TYPE
    SYNTAX       CfprAdaptorMenloNetInStatsThresholded
    MAX-ACCESS   read-only
    STATUS       current
    DESCRIPTION
        "Cisco Firepower adaptor:MenloNetInStats:thresholded
        managed object property"
    ::= { cfprAdaptorMenloNetInStatsEntry 27 }

cfprAdaptorMenloNetInStatsTimeCollected OBJECT-TYPE
    SYNTAX       DateAndTime
    MAX-ACCESS   read-only
    STATUS       current
    DESCRIPTION
        "Cisco Firepower adaptor:MenloNetInStats:timeCollected
        managed object property"
    ::= { cfprAdaptorMenloNetInStatsEntry 28 }

cfprAdaptorMenloNetInStatsUpdate OBJECT-TYPE
    SYNTAX       Gauge32
    MAX-ACCESS   read-only
    STATUS       current
    DESCRIPTION
        "Cisco Firepower adaptor:MenloNetInStats:update
        managed object property"
    ::= { cfprAdaptorMenloNetInStatsEntry 29 }

cfprAdaptorMenloNetInStatsHistTable OBJECT-TYPE
    SYNTAX           SEQUENCE OF CfprAdaptorMenloNetInStatsHistEntry
    MAX-ACCESS       not-accessible
    STATUS           current
    DESCRIPTION
        "Cisco Firepower adaptor:MenloNetInStatsHist managed object table"
    ::= { cfprAdaptorObjects 103 }

cfprAdaptorMenloNetInStatsHistEntry OBJECT-TYPE
    SYNTAX           CfprAdaptorMenloNetInStatsHistEntry
    MAX-ACCESS       not-accessible
    STATUS           current
    DESCRIPTION
        "Entry for the cfprAdaptorMenloNetInStatsHistTable table."
    INDEX { cfprAdaptorMenloNetInStatsHistInstanceId }
    ::= { cfprAdaptorMenloNetInStatsHistTable 1 }

CfprAdaptorMenloNetInStatsHistEntry ::= SEQUENCE {
    cfprAdaptorMenloNetInStatsHistInstanceId                         CfprManagedObjectId,
    cfprAdaptorMenloNetInStatsHistDn                                 CfprManagedObjectDn,
    cfprAdaptorMenloNetInStatsHistRn                                 SnmpAdminString,
    cfprAdaptorMenloNetInStatsHistDropFcLifInvalid                   Unsigned64,
    cfprAdaptorMenloNetInStatsHistDropFcLifInvalidDelta              Unsigned64,
    cfprAdaptorMenloNetInStatsHistDropFcLifInvalidDeltaAvg           Unsigned64,
    cfprAdaptorMenloNetInStatsHistDropFcLifInvalidDeltaMax           Unsigned64,
    cfprAdaptorMenloNetInStatsHistDropFcLifInvalidDeltaMin           Unsigned64,
    cfprAdaptorMenloNetInStatsHistDropFcMulticast                    Unsigned64,
    cfprAdaptorMenloNetInStatsHistDropFcMulticastDelta               Unsigned64,
    cfprAdaptorMenloNetInStatsHistDropFcMulticastDeltaAvg            Unsigned64,
    cfprAdaptorMenloNetInStatsHistDropFcMulticastDeltaMax            Unsigned64,
    cfprAdaptorMenloNetInStatsHistDropFcMulticastDeltaMin            Unsigned64,
    cfprAdaptorMenloNetInStatsHistDropNullPif                        Unsigned64,
    cfprAdaptorMenloNetInStatsHistDropNullPifDelta                   Unsigned64,
    cfprAdaptorMenloNetInStatsHistDropNullPifDeltaAvg                Unsigned64,
    cfprAdaptorMenloNetInStatsHistDropNullPifDeltaMax                Unsigned64,
    cfprAdaptorMenloNetInStatsHistDropNullPifDeltaMin                Unsigned64,
    cfprAdaptorMenloNetInStatsHistFwdLookupNoHit                     Unsigned64,
    cfprAdaptorMenloNetInStatsHistFwdLookupNoHitDelta                Unsigned64,
    cfprAdaptorMenloNetInStatsHistFwdLookupNoHitDeltaAvg             Unsigned64,
    cfprAdaptorMenloNetInStatsHistFwdLookupNoHitDeltaMax             Unsigned64,
    cfprAdaptorMenloNetInStatsHistFwdLookupNoHitDeltaMin             Unsigned64,
    cfprAdaptorMenloNetInStatsHistId                                 Unsigned64,
    cfprAdaptorMenloNetInStatsHistMostRecent                         TruthValue,
    cfprAdaptorMenloNetInStatsHistSuspect                            TruthValue,
    cfprAdaptorMenloNetInStatsHistThresholded                        CfprAdaptorMenloNetInStatsHistThresholded,
    cfprAdaptorMenloNetInStatsHistTimeCollected                      DateAndTime
}

cfprAdaptorMenloNetInStatsHistInstanceId OBJECT-TYPE
    SYNTAX       CfprManagedObjectId
    MAX-ACCESS   not-accessible
    STATUS       current
    DESCRIPTION
        "Instance identifier of the managed object."
    ::= { cfprAdaptorMenloNetInStatsHistEntry 1 }

cfprAdaptorMenloNetInStatsHistDn OBJECT-TYPE
    SYNTAX       CfprManagedObjectDn
    MAX-ACCESS   read-only
    STATUS       current
    DESCRIPTION
        "Cisco Firepower adaptor:MenloNetInStatsHist:dn
        managed object property"
    ::= { cfprAdaptorMenloNetInStatsHistEntry 2 }

cfprAdaptorMenloNetInStatsHistRn OBJECT-TYPE
    SYNTAX       SnmpAdminString
    MAX-ACCESS   read-only
    STATUS       current
    DESCRIPTION
        "Cisco Firepower adaptor:MenloNetInStatsHist:rn
        managed object property"
    ::= { cfprAdaptorMenloNetInStatsHistEntry 3 }

cfprAdaptorMenloNetInStatsHistDropFcLifInvalid OBJECT-TYPE
    SYNTAX       Unsigned64
    MAX-ACCESS   read-only
    STATUS       current
    DESCRIPTION
        "Cisco Firepower adaptor:MenloNetInStatsHist:dropFcLifInvalid
        managed object property"
    ::= { cfprAdaptorMenloNetInStatsHistEntry 4 }

cfprAdaptorMenloNetInStatsHistDropFcLifInvalidDelta OBJECT-TYPE
    SYNTAX       Unsigned64
    MAX-ACCESS   read-only
    STATUS       current
    DESCRIPTION
        "Cisco Firepower adaptor:MenloNetInStatsHist:dropFcLifInvalidDelta
         managed object property"
    ::= { cfprAdaptorMenloNetInStatsHistEntry 5 }

cfprAdaptorMenloNetInStatsHistDropFcLifInvalidDeltaAvg OBJECT-TYPE
    SYNTAX       Unsigned64
    MAX-ACCESS   read-only
    STATUS       current
    DESCRIPTION
        "Cisco Firepower adaptor:MenloNetInStatsHist:dropFcLifInvalidDelta
        Avg managed object property"
    ::= { cfprAdaptorMenloNetInStatsHistEntry 6 }

cfprAdaptorMenloNetInStatsHistDropFcLifInvalidDeltaMax OBJECT-TYPE
    SYNTAX       Unsigned64
    MAX-ACCESS   read-only
    STATUS       current
    DESCRIPTION
        "Cisco Firepower adaptor:MenloNetInStatsHist:dropFcLifInvalidDelta
        Max managed object property"
    ::= { cfprAdaptorMenloNetInStatsHistEntry 7 }

cfprAdaptorMenloNetInStatsHistDropFcLifInvalidDeltaMin OBJECT-TYPE
    SYNTAX       Unsigned64
    MAX-ACCESS   read-only
    STATUS       current
    DESCRIPTION
        "Cisco Firepower adaptor:MenloNetInStatsHist:dropFcLifInvalidDelta
        Min managed object property"
    ::= { cfprAdaptorMenloNetInStatsHistEntry 8 }

cfprAdaptorMenloNetInStatsHistDropFcMulticast OBJECT-TYPE
    SYNTAX       Unsigned64
    MAX-ACCESS   read-only
    STATUS       current
    DESCRIPTION
        "Cisco Firepower adaptor:MenloNetInStatsHist:dropFcMulticast
        managed object property"
    ::= { cfprAdaptorMenloNetInStatsHistEntry 9 }

cfprAdaptorMenloNetInStatsHistDropFcMulticastDelta OBJECT-TYPE
    SYNTAX       Unsigned64
    MAX-ACCESS   read-only
    STATUS       current
    DESCRIPTION
        "Cisco Firepower adaptor:MenloNetInStatsHist:dropFcMulticastDelta
        managed object property"
    ::= { cfprAdaptorMenloNetInStatsHistEntry 10 }

cfprAdaptorMenloNetInStatsHistDropFcMulticastDeltaAvg OBJECT-TYPE
    SYNTAX       Unsigned64
    MAX-ACCESS   read-only
    STATUS       current
    DESCRIPTION
        "Cisco Firepower adaptor:MenloNetInStatsHist:dropFcMulticastDeltaA
        vg managed object property"
    ::= { cfprAdaptorMenloNetInStatsHistEntry 11 }

cfprAdaptorMenloNetInStatsHistDropFcMulticastDeltaMax OBJECT-TYPE
    SYNTAX       Unsigned64
    MAX-ACCESS   read-only
    STATUS       current
    DESCRIPTION
        "Cisco Firepower adaptor:MenloNetInStatsHist:dropFcMulticastDeltaM
        ax managed object property"
    ::= { cfprAdaptorMenloNetInStatsHistEntry 12 }

cfprAdaptorMenloNetInStatsHistDropFcMulticastDeltaMin OBJECT-TYPE
    SYNTAX       Unsigned64
    MAX-ACCESS   read-only
    STATUS       current
    DESCRIPTION
        "Cisco Firepower adaptor:MenloNetInStatsHist:dropFcMulticastDeltaM
        in managed object property"
    ::= { cfprAdaptorMenloNetInStatsHistEntry 13 }

cfprAdaptorMenloNetInStatsHistDropNullPif OBJECT-TYPE
    SYNTAX       Unsigned64
    MAX-ACCESS   read-only
    STATUS       current
    DESCRIPTION
        "Cisco Firepower adaptor:MenloNetInStatsHist:dropNullPif
        managed object property"
    ::= { cfprAdaptorMenloNetInStatsHistEntry 14 }

cfprAdaptorMenloNetInStatsHistDropNullPifDelta OBJECT-TYPE
    SYNTAX       Unsigned64
    MAX-ACCESS   read-only
    STATUS       current
    DESCRIPTION
        "Cisco Firepower adaptor:MenloNetInStatsHist:dropNullPifDelta
        managed object property"
    ::= { cfprAdaptorMenloNetInStatsHistEntry 15 }

cfprAdaptorMenloNetInStatsHistDropNullPifDeltaAvg OBJECT-TYPE
    SYNTAX       Unsigned64
    MAX-ACCESS   read-only
    STATUS       current
    DESCRIPTION
        "Cisco Firepower adaptor:MenloNetInStatsHist:dropNullPifDeltaAvg
        managed object property"
    ::= { cfprAdaptorMenloNetInStatsHistEntry 16 }

cfprAdaptorMenloNetInStatsHistDropNullPifDeltaMax OBJECT-TYPE
    SYNTAX       Unsigned64
    MAX-ACCESS   read-only
    STATUS       current
    DESCRIPTION
        "Cisco Firepower adaptor:MenloNetInStatsHist:dropNullPifDeltaMax
        managed object property"
    ::= { cfprAdaptorMenloNetInStatsHistEntry 17 }

cfprAdaptorMenloNetInStatsHistDropNullPifDeltaMin OBJECT-TYPE
    SYNTAX       Unsigned64
    MAX-ACCESS   read-only
    STATUS       current
    DESCRIPTION
        "Cisco Firepower adaptor:MenloNetInStatsHist:dropNullPifDeltaMin
        managed object property"
    ::= { cfprAdaptorMenloNetInStatsHistEntry 18 }

cfprAdaptorMenloNetInStatsHistFwdLookupNoHit OBJECT-TYPE
    SYNTAX       Unsigned64
    MAX-ACCESS   read-only
    STATUS       current
    DESCRIPTION
        "Cisco Firepower adaptor:MenloNetInStatsHist:fwdLookupNoHit
        managed object property"
    ::= { cfprAdaptorMenloNetInStatsHistEntry 19 }

cfprAdaptorMenloNetInStatsHistFwdLookupNoHitDelta OBJECT-TYPE
    SYNTAX       Unsigned64
    MAX-ACCESS   read-only
    STATUS       current
    DESCRIPTION
        "Cisco Firepower adaptor:MenloNetInStatsHist:fwdLookupNoHitDelta
        managed object property"
    ::= { cfprAdaptorMenloNetInStatsHistEntry 20 }

cfprAdaptorMenloNetInStatsHistFwdLookupNoHitDeltaAvg OBJECT-TYPE
    SYNTAX       Unsigned64
    MAX-ACCESS   read-only
    STATUS       current
    DESCRIPTION
        "Cisco Firepower adaptor:MenloNetInStatsHist:fwdLookupNoHitDeltaAv
        g managed object property"
    ::= { cfprAdaptorMenloNetInStatsHistEntry 21 }

cfprAdaptorMenloNetInStatsHistFwdLookupNoHitDeltaMax OBJECT-TYPE
    SYNTAX       Unsigned64
    MAX-ACCESS   read-only
    STATUS       current
    DESCRIPTION
        "Cisco Firepower adaptor:MenloNetInStatsHist:fwdLookupNoHitDeltaMa
        x managed object property"
    ::= { cfprAdaptorMenloNetInStatsHistEntry 22 }

cfprAdaptorMenloNetInStatsHistFwdLookupNoHitDeltaMin OBJECT-TYPE
    SYNTAX       Unsigned64
    MAX-ACCESS   read-only
    STATUS       current
    DESCRIPTION
        "Cisco Firepower adaptor:MenloNetInStatsHist:fwdLookupNoHitDeltaMi
        n managed object property"
    ::= { cfprAdaptorMenloNetInStatsHistEntry 23 }

cfprAdaptorMenloNetInStatsHistId OBJECT-TYPE
    SYNTAX       Unsigned64
    MAX-ACCESS   read-only
    STATUS       current
    DESCRIPTION
        "Cisco Firepower adaptor:MenloNetInStatsHist:id
        managed object property"
    ::= { cfprAdaptorMenloNetInStatsHistEntry 24 }

cfprAdaptorMenloNetInStatsHistMostRecent OBJECT-TYPE
    SYNTAX       TruthValue
    MAX-ACCESS   read-only
    STATUS       current
    DESCRIPTION
        "Cisco Firepower adaptor:MenloNetInStatsHist:mostRecent
        managed object property"
    ::= { cfprAdaptorMenloNetInStatsHistEntry 25 }

cfprAdaptorMenloNetInStatsHistSuspect OBJECT-TYPE
    SYNTAX       TruthValue
    MAX-ACCESS   read-only
    STATUS       current
    DESCRIPTION
        "Cisco Firepower adaptor:MenloNetInStatsHist:suspect
        managed object property"
    ::= { cfprAdaptorMenloNetInStatsHistEntry 26 }

cfprAdaptorMenloNetInStatsHistThresholded OBJECT-TYPE
    SYNTAX       CfprAdaptorMenloNetInStatsHistThresholded
    MAX-ACCESS   read-only
    STATUS       current
    DESCRIPTION
        "Cisco Firepower adaptor:MenloNetInStatsHist:thresholded
        managed object property"
    ::= { cfprAdaptorMenloNetInStatsHistEntry 27 }

cfprAdaptorMenloNetInStatsHistTimeCollected OBJECT-TYPE
    SYNTAX       DateAndTime
    MAX-ACCESS   read-only
    STATUS       current
    DESCRIPTION
        "Cisco Firepower adaptor:MenloNetInStatsHist:timeCollected
        managed object property"
    ::= { cfprAdaptorMenloNetInStatsHistEntry 28 }

cfprAdaptorMenloQErrorStatsTable OBJECT-TYPE
    SYNTAX           SEQUENCE OF CfprAdaptorMenloQErrorStatsEntry
    MAX-ACCESS       not-accessible
    STATUS           current
    DESCRIPTION
        "Cisco Firepower adaptor:MenloQErrorStats managed object table"
    ::= { cfprAdaptorObjects 104 }

cfprAdaptorMenloQErrorStatsEntry OBJECT-TYPE
    SYNTAX           CfprAdaptorMenloQErrorStatsEntry
    MAX-ACCESS       not-accessible
    STATUS           current
    DESCRIPTION
        "Entry for the cfprAdaptorMenloQErrorStatsTable table."
    INDEX { cfprAdaptorMenloQErrorStatsInstanceId }
    ::= { cfprAdaptorMenloQErrorStatsTable 1 }

CfprAdaptorMenloQErrorStatsEntry ::= SEQUENCE {
    cfprAdaptorMenloQErrorStatsInstanceId                            CfprManagedObjectId,
    cfprAdaptorMenloQErrorStatsDn                                    CfprManagedObjectDn,
    cfprAdaptorMenloQErrorStatsRn                                    SnmpAdminString,
    cfprAdaptorMenloQErrorStatsCorrectableErrors                     Unsigned64,
    cfprAdaptorMenloQErrorStatsCorrectableErrorsDelta                Counter64,
    cfprAdaptorMenloQErrorStatsCorrectableErrorsDeltaAvg             Unsigned64,
    cfprAdaptorMenloQErrorStatsCorrectableErrorsDeltaMax             Unsigned64,
    cfprAdaptorMenloQErrorStatsCorrectableErrorsDeltaMin             Unsigned64,
    cfprAdaptorMenloQErrorStatsIntervals                             Gauge32,
    cfprAdaptorMenloQErrorStatsMenloQueueComponent                   CfprAdaptorMenloQueueStatsComponent,
    cfprAdaptorMenloQErrorStatsMenloQueueIndex                       CfprAdaptorMenloStatsIndex,
    cfprAdaptorMenloQErrorStatsPopErrors                             Unsigned64,
    cfprAdaptorMenloQErrorStatsPopErrorsDelta                        Counter64,
    cfprAdaptorMenloQErrorStatsPopErrorsDeltaAvg                     Unsigned64,
    cfprAdaptorMenloQErrorStatsPopErrorsDeltaMax                     Unsigned64,
    cfprAdaptorMenloQErrorStatsPopErrorsDeltaMin                     Unsigned64,
    cfprAdaptorMenloQErrorStatsPushErrors                            Unsigned64,
    cfprAdaptorMenloQErrorStatsPushErrorsDelta                       Counter64,
    cfprAdaptorMenloQErrorStatsPushErrorsDeltaAvg                    Unsigned64,
    cfprAdaptorMenloQErrorStatsPushErrorsDeltaMax                    Unsigned64,
    cfprAdaptorMenloQErrorStatsPushErrorsDeltaMin                    Unsigned64,
    cfprAdaptorMenloQErrorStatsSuspect                               TruthValue,
    cfprAdaptorMenloQErrorStatsThresholded                           CfprAdaptorMenloQErrorStatsThresholded,
    cfprAdaptorMenloQErrorStatsTimeCollected                         DateAndTime,
    cfprAdaptorMenloQErrorStatsUncorrectableErrors                   Unsigned64,
    cfprAdaptorMenloQErrorStatsUncorrectableErrorsDelta              Counter64,
    cfprAdaptorMenloQErrorStatsUncorrectableErrorsDeltaAvg           Unsigned64,
    cfprAdaptorMenloQErrorStatsUncorrectableErrorsDeltaMax           Unsigned64,
    cfprAdaptorMenloQErrorStatsUncorrectableErrorsDeltaMin           Unsigned64,
    cfprAdaptorMenloQErrorStatsUpdate                                Gauge32
}

cfprAdaptorMenloQErrorStatsInstanceId OBJECT-TYPE
    SYNTAX       CfprManagedObjectId
    MAX-ACCESS   not-accessible
    STATUS       current
    DESCRIPTION
        "Instance identifier of the managed object."
    ::= { cfprAdaptorMenloQErrorStatsEntry 1 }

cfprAdaptorMenloQErrorStatsDn OBJECT-TYPE
    SYNTAX       CfprManagedObjectDn
    MAX-ACCESS   read-only
    STATUS       current
    DESCRIPTION
        "Cisco Firepower adaptor:MenloQErrorStats:dn managed
        object property"
    ::= { cfprAdaptorMenloQErrorStatsEntry 2 }

cfprAdaptorMenloQErrorStatsRn OBJECT-TYPE
    SYNTAX       SnmpAdminString
    MAX-ACCESS   read-only
    STATUS       current
    DESCRIPTION
        "Cisco Firepower adaptor:MenloQErrorStats:rn managed
        object property"
    ::= { cfprAdaptorMenloQErrorStatsEntry 3 }

cfprAdaptorMenloQErrorStatsCorrectableErrors OBJECT-TYPE
    SYNTAX       Unsigned64
    MAX-ACCESS   read-only
    STATUS       current
    DESCRIPTION
        "Cisco Firepower adaptor:MenloQErrorStats:correctableErrors
        managed object property"
    ::= { cfprAdaptorMenloQErrorStatsEntry 4 }

cfprAdaptorMenloQErrorStatsCorrectableErrorsDelta OBJECT-TYPE
    SYNTAX       Counter64
    MAX-ACCESS   read-only
    STATUS       current
    DESCRIPTION
        "Cisco Firepower adaptor:MenloQErrorStats:correctableErrorsDelta
        managed object property"
    ::= { cfprAdaptorMenloQErrorStatsEntry 5 }

cfprAdaptorMenloQErrorStatsCorrectableErrorsDeltaAvg OBJECT-TYPE
    SYNTAX       Unsigned64
    MAX-ACCESS   read-only
    STATUS       current
    DESCRIPTION
        "Cisco Firepower adaptor:MenloQErrorStats:correctableErrorsDeltaAv
        g managed object property"
    ::= { cfprAdaptorMenloQErrorStatsEntry 6 }

cfprAdaptorMenloQErrorStatsCorrectableErrorsDeltaMax OBJECT-TYPE
    SYNTAX       Unsigned64
    MAX-ACCESS   read-only
    STATUS       current
    DESCRIPTION
        "Cisco Firepower adaptor:MenloQErrorStats:correctableErrorsDeltaMa
        x managed object property"
    ::= { cfprAdaptorMenloQErrorStatsEntry 7 }

cfprAdaptorMenloQErrorStatsCorrectableErrorsDeltaMin OBJECT-TYPE
    SYNTAX       Unsigned64
    MAX-ACCESS   read-only
    STATUS       current
    DESCRIPTION
        "Cisco Firepower adaptor:MenloQErrorStats:correctableErrorsDeltaMi
        n managed object property"
    ::= { cfprAdaptorMenloQErrorStatsEntry 8 }

cfprAdaptorMenloQErrorStatsIntervals OBJECT-TYPE
    SYNTAX       Gauge32
    MAX-ACCESS   read-only
    STATUS       current
    DESCRIPTION
        "Cisco Firepower adaptor:MenloQErrorStats:intervals
        managed object property"
    ::= { cfprAdaptorMenloQErrorStatsEntry 9 }

cfprAdaptorMenloQErrorStatsMenloQueueComponent OBJECT-TYPE
    SYNTAX       CfprAdaptorMenloQueueStatsComponent
    MAX-ACCESS   read-only
    STATUS       current
    DESCRIPTION
        "Cisco Firepower adaptor:MenloQErrorStats:menloQueueComponent
        managed object property"
    ::= { cfprAdaptorMenloQErrorStatsEntry 10 }

cfprAdaptorMenloQErrorStatsMenloQueueIndex OBJECT-TYPE
    SYNTAX       CfprAdaptorMenloStatsIndex
    MAX-ACCESS   read-only
    STATUS       current
    DESCRIPTION
        "Cisco Firepower adaptor:MenloQErrorStats:menloQueueIndex
        managed object property"
    ::= { cfprAdaptorMenloQErrorStatsEntry 11 }

cfprAdaptorMenloQErrorStatsPopErrors OBJECT-TYPE
    SYNTAX       Unsigned64
    MAX-ACCESS   read-only
    STATUS       current
    DESCRIPTION
        "Cisco Firepower adaptor:MenloQErrorStats:popErrors
        managed object property"
    ::= { cfprAdaptorMenloQErrorStatsEntry 12 }

cfprAdaptorMenloQErrorStatsPopErrorsDelta OBJECT-TYPE
    SYNTAX       Counter64
    MAX-ACCESS   read-only
    STATUS       current
    DESCRIPTION
        "Cisco Firepower adaptor:MenloQErrorStats:popErrorsDelta
        managed object property"
    ::= { cfprAdaptorMenloQErrorStatsEntry 13 }

cfprAdaptorMenloQErrorStatsPopErrorsDeltaAvg OBJECT-TYPE
    SYNTAX       Unsigned64
    MAX-ACCESS   read-only
    STATUS       current
    DESCRIPTION
        "Cisco Firepower adaptor:MenloQErrorStats:popErrorsDeltaAvg
        managed object property"
    ::= { cfprAdaptorMenloQErrorStatsEntry 14 }

cfprAdaptorMenloQErrorStatsPopErrorsDeltaMax OBJECT-TYPE
    SYNTAX       Unsigned64
    MAX-ACCESS   read-only
    STATUS       current
    DESCRIPTION
        "Cisco Firepower adaptor:MenloQErrorStats:popErrorsDeltaMax
        managed object property"
    ::= { cfprAdaptorMenloQErrorStatsEntry 15 }

cfprAdaptorMenloQErrorStatsPopErrorsDeltaMin OBJECT-TYPE
    SYNTAX       Unsigned64
    MAX-ACCESS   read-only
    STATUS       current
    DESCRIPTION
        "Cisco Firepower adaptor:MenloQErrorStats:popErrorsDeltaMin
        managed object property"
    ::= { cfprAdaptorMenloQErrorStatsEntry 16 }

cfprAdaptorMenloQErrorStatsPushErrors OBJECT-TYPE
    SYNTAX       Unsigned64
    MAX-ACCESS   read-only
    STATUS       current
    DESCRIPTION
        "Cisco Firepower adaptor:MenloQErrorStats:pushErrors
        managed object property"
    ::= { cfprAdaptorMenloQErrorStatsEntry 17 }

cfprAdaptorMenloQErrorStatsPushErrorsDelta OBJECT-TYPE
    SYNTAX       Counter64
    MAX-ACCESS   read-only
    STATUS       current
    DESCRIPTION
        "Cisco Firepower adaptor:MenloQErrorStats:pushErrorsDelta
        managed object property"
    ::= { cfprAdaptorMenloQErrorStatsEntry 18 }

cfprAdaptorMenloQErrorStatsPushErrorsDeltaAvg OBJECT-TYPE
    SYNTAX       Unsigned64
    MAX-ACCESS   read-only
    STATUS       current
    DESCRIPTION
        "Cisco Firepower adaptor:MenloQErrorStats:pushErrorsDeltaAvg
        managed object property"
    ::= { cfprAdaptorMenloQErrorStatsEntry 19 }

cfprAdaptorMenloQErrorStatsPushErrorsDeltaMax OBJECT-TYPE
    SYNTAX       Unsigned64
    MAX-ACCESS   read-only
    STATUS       current
    DESCRIPTION
        "Cisco Firepower adaptor:MenloQErrorStats:pushErrorsDeltaMax
        managed object property"
    ::= { cfprAdaptorMenloQErrorStatsEntry 20 }

cfprAdaptorMenloQErrorStatsPushErrorsDeltaMin OBJECT-TYPE
    SYNTAX       Unsigned64
    MAX-ACCESS   read-only
    STATUS       current
    DESCRIPTION
        "Cisco Firepower adaptor:MenloQErrorStats:pushErrorsDeltaMin
        managed object property"
    ::= { cfprAdaptorMenloQErrorStatsEntry 21 }

cfprAdaptorMenloQErrorStatsSuspect OBJECT-TYPE
    SYNTAX       TruthValue
    MAX-ACCESS   read-only
    STATUS       current
    DESCRIPTION
        "Cisco Firepower adaptor:MenloQErrorStats:suspect
        managed object property"
    ::= { cfprAdaptorMenloQErrorStatsEntry 22 }

cfprAdaptorMenloQErrorStatsThresholded OBJECT-TYPE
    SYNTAX       CfprAdaptorMenloQErrorStatsThresholded
    MAX-ACCESS   read-only
    STATUS       current
    DESCRIPTION
        "Cisco Firepower adaptor:MenloQErrorStats:thresholded
        managed object property"
    ::= { cfprAdaptorMenloQErrorStatsEntry 23 }

cfprAdaptorMenloQErrorStatsTimeCollected OBJECT-TYPE
    SYNTAX       DateAndTime
    MAX-ACCESS   read-only
    STATUS       current
    DESCRIPTION
        "Cisco Firepower adaptor:MenloQErrorStats:timeCollected
        managed object property"
    ::= { cfprAdaptorMenloQErrorStatsEntry 24 }

cfprAdaptorMenloQErrorStatsUncorrectableErrors OBJECT-TYPE
    SYNTAX       Unsigned64
    MAX-ACCESS   read-only
    STATUS       current
    DESCRIPTION
        "Cisco Firepower adaptor:MenloQErrorStats:uncorrectableErrors
        managed object property"
    ::= { cfprAdaptorMenloQErrorStatsEntry 25 }

cfprAdaptorMenloQErrorStatsUncorrectableErrorsDelta OBJECT-TYPE
    SYNTAX       Counter64
    MAX-ACCESS   read-only
    STATUS       current
    DESCRIPTION
        "Cisco Firepower adaptor:MenloQErrorStats:uncorrectableErrorsDelta
         managed object property"
    ::= { cfprAdaptorMenloQErrorStatsEntry 26 }

cfprAdaptorMenloQErrorStatsUncorrectableErrorsDeltaAvg OBJECT-TYPE
    SYNTAX       Unsigned64
    MAX-ACCESS   read-only
    STATUS       current
    DESCRIPTION
        "Cisco Firepower adaptor:MenloQErrorStats:uncorrectableErrorsDelta
        Avg managed object property"
    ::= { cfprAdaptorMenloQErrorStatsEntry 27 }

cfprAdaptorMenloQErrorStatsUncorrectableErrorsDeltaMax OBJECT-TYPE
    SYNTAX       Unsigned64
    MAX-ACCESS   read-only
    STATUS       current
    DESCRIPTION
        "Cisco Firepower adaptor:MenloQErrorStats:uncorrectableErrorsDelta
        Max managed object property"
    ::= { cfprAdaptorMenloQErrorStatsEntry 28 }

cfprAdaptorMenloQErrorStatsUncorrectableErrorsDeltaMin OBJECT-TYPE
    SYNTAX       Unsigned64
    MAX-ACCESS   read-only
    STATUS       current
    DESCRIPTION
        "Cisco Firepower adaptor:MenloQErrorStats:uncorrectableErrorsDelta
        Min managed object property"
    ::= { cfprAdaptorMenloQErrorStatsEntry 29 }

cfprAdaptorMenloQErrorStatsUpdate OBJECT-TYPE
    SYNTAX       Gauge32
    MAX-ACCESS   read-only
    STATUS       current
    DESCRIPTION
        "Cisco Firepower adaptor:MenloQErrorStats:update
        managed object property"
    ::= { cfprAdaptorMenloQErrorStatsEntry 30 }

cfprAdaptorMenloQErrorStatsHistTable OBJECT-TYPE
    SYNTAX           SEQUENCE OF CfprAdaptorMenloQErrorStatsHistEntry
    MAX-ACCESS       not-accessible
    STATUS           current
    DESCRIPTION
        "Cisco Firepower adaptor:MenloQErrorStatsHist managed
        object table"
    ::= { cfprAdaptorObjects 105 }

cfprAdaptorMenloQErrorStatsHistEntry OBJECT-TYPE
    SYNTAX           CfprAdaptorMenloQErrorStatsHistEntry
    MAX-ACCESS       not-accessible
    STATUS           current
    DESCRIPTION
        "Entry for the cfprAdaptorMenloQErrorStatsHistTable table."
    INDEX { cfprAdaptorMenloQErrorStatsHistInstanceId }
    ::= { cfprAdaptorMenloQErrorStatsHistTable 1 }

CfprAdaptorMenloQErrorStatsHistEntry ::= SEQUENCE {
    cfprAdaptorMenloQErrorStatsHistInstanceId                        CfprManagedObjectId,
    cfprAdaptorMenloQErrorStatsHistDn                                CfprManagedObjectDn,
    cfprAdaptorMenloQErrorStatsHistRn                                SnmpAdminString,
    cfprAdaptorMenloQErrorStatsHistCorrectableErrors                 Unsigned64,
    cfprAdaptorMenloQErrorStatsHistCorrectableErrorsDelta            Unsigned64,
    cfprAdaptorMenloQErrorStatsHistCorrectableErrorsDeltaAvg         Unsigned64,
    cfprAdaptorMenloQErrorStatsHistCorrectableErrorsDeltaMax         Unsigned64,
    cfprAdaptorMenloQErrorStatsHistCorrectableErrorsDeltaMin         Unsigned64,
    cfprAdaptorMenloQErrorStatsHistId                                Unsigned64,
    cfprAdaptorMenloQErrorStatsHistMostRecent                        TruthValue,
    cfprAdaptorMenloQErrorStatsHistPopErrors                         Unsigned64,
    cfprAdaptorMenloQErrorStatsHistPopErrorsDelta                    Unsigned64,
    cfprAdaptorMenloQErrorStatsHistPopErrorsDeltaAvg                 Unsigned64,
    cfprAdaptorMenloQErrorStatsHistPopErrorsDeltaMax                 Unsigned64,
    cfprAdaptorMenloQErrorStatsHistPopErrorsDeltaMin                 Unsigned64,
    cfprAdaptorMenloQErrorStatsHistPushErrors                        Unsigned64,
    cfprAdaptorMenloQErrorStatsHistPushErrorsDelta                   Unsigned64,
    cfprAdaptorMenloQErrorStatsHistPushErrorsDeltaAvg                Unsigned64,
    cfprAdaptorMenloQErrorStatsHistPushErrorsDeltaMax                Unsigned64,
    cfprAdaptorMenloQErrorStatsHistPushErrorsDeltaMin                Unsigned64,
    cfprAdaptorMenloQErrorStatsHistSuspect                           TruthValue,
    cfprAdaptorMenloQErrorStatsHistThresholded                       CfprAdaptorMenloQErrorStatsHistThresholded,
    cfprAdaptorMenloQErrorStatsHistTimeCollected                     DateAndTime,
    cfprAdaptorMenloQErrorStatsHistUncorrectableErrors               Unsigned64,
    cfprAdaptorMenloQErrorStatsHistUncorrectableErrorsDelta          Unsigned64,
    cfprAdaptorMenloQErrorStatsHistUncorrectableErrorsDeltaAvg       Unsigned64,
    cfprAdaptorMenloQErrorStatsHistUncorrectableErrorsDeltaMax       Unsigned64,
    cfprAdaptorMenloQErrorStatsHistUncorrectableErrorsDeltaMin       Unsigned64
}

cfprAdaptorMenloQErrorStatsHistInstanceId OBJECT-TYPE
    SYNTAX       CfprManagedObjectId
    MAX-ACCESS   not-accessible
    STATUS       current
    DESCRIPTION
        "Instance identifier of the managed object."
    ::= { cfprAdaptorMenloQErrorStatsHistEntry 1 }

cfprAdaptorMenloQErrorStatsHistDn OBJECT-TYPE
    SYNTAX       CfprManagedObjectDn
    MAX-ACCESS   read-only
    STATUS       current
    DESCRIPTION
        "Cisco Firepower adaptor:MenloQErrorStatsHist:dn
        managed object property"
    ::= { cfprAdaptorMenloQErrorStatsHistEntry 2 }

cfprAdaptorMenloQErrorStatsHistRn OBJECT-TYPE
    SYNTAX       SnmpAdminString
    MAX-ACCESS   read-only
    STATUS       current
    DESCRIPTION
        "Cisco Firepower adaptor:MenloQErrorStatsHist:rn
        managed object property"
    ::= { cfprAdaptorMenloQErrorStatsHistEntry 3 }

cfprAdaptorMenloQErrorStatsHistCorrectableErrors OBJECT-TYPE
    SYNTAX       Unsigned64
    MAX-ACCESS   read-only
    STATUS       current
    DESCRIPTION
        "Cisco Firepower adaptor:MenloQErrorStatsHist:correctableErrors
        managed object property"
    ::= { cfprAdaptorMenloQErrorStatsHistEntry 4 }

cfprAdaptorMenloQErrorStatsHistCorrectableErrorsDelta OBJECT-TYPE
    SYNTAX       Unsigned64
    MAX-ACCESS   read-only
    STATUS       current
    DESCRIPTION
        "Cisco Firepower adaptor:MenloQErrorStatsHist:correctableErrorsDel
        ta managed object property"
    ::= { cfprAdaptorMenloQErrorStatsHistEntry 5 }

cfprAdaptorMenloQErrorStatsHistCorrectableErrorsDeltaAvg OBJECT-TYPE
    SYNTAX       Unsigned64
    MAX-ACCESS   read-only
    STATUS       current
    DESCRIPTION
        "Cisco Firepower adaptor:MenloQErrorStatsHist:correctableErrorsDel
        taAvg managed object property"
    ::= { cfprAdaptorMenloQErrorStatsHistEntry 6 }

cfprAdaptorMenloQErrorStatsHistCorrectableErrorsDeltaMax OBJECT-TYPE
    SYNTAX       Unsigned64
    MAX-ACCESS   read-only
    STATUS       current
    DESCRIPTION
        "Cisco Firepower adaptor:MenloQErrorStatsHist:correctableErrorsDel
        taMax managed object property"
    ::= { cfprAdaptorMenloQErrorStatsHistEntry 7 }

cfprAdaptorMenloQErrorStatsHistCorrectableErrorsDeltaMin OBJECT-TYPE
    SYNTAX       Unsigned64
    MAX-ACCESS   read-only
    STATUS       current
    DESCRIPTION
        "Cisco Firepower adaptor:MenloQErrorStatsHist:correctableErrorsDel
        taMin managed object property"
    ::= { cfprAdaptorMenloQErrorStatsHistEntry 8 }

cfprAdaptorMenloQErrorStatsHistId OBJECT-TYPE
    SYNTAX       Unsigned64
    MAX-ACCESS   read-only
    STATUS       current
    DESCRIPTION
        "Cisco Firepower adaptor:MenloQErrorStatsHist:id
        managed object property"
    ::= { cfprAdaptorMenloQErrorStatsHistEntry 9 }

cfprAdaptorMenloQErrorStatsHistMostRecent OBJECT-TYPE
    SYNTAX       TruthValue
    MAX-ACCESS   read-only
    STATUS       current
    DESCRIPTION
        "Cisco Firepower adaptor:MenloQErrorStatsHist:mostRecent
        managed object property"
    ::= { cfprAdaptorMenloQErrorStatsHistEntry 10 }

cfprAdaptorMenloQErrorStatsHistPopErrors OBJECT-TYPE
    SYNTAX       Unsigned64
    MAX-ACCESS   read-only
    STATUS       current
    DESCRIPTION
        "Cisco Firepower adaptor:MenloQErrorStatsHist:popErrors
        managed object property"
    ::= { cfprAdaptorMenloQErrorStatsHistEntry 11 }

cfprAdaptorMenloQErrorStatsHistPopErrorsDelta OBJECT-TYPE
    SYNTAX       Unsigned64
    MAX-ACCESS   read-only
    STATUS       current
    DESCRIPTION
        "Cisco Firepower adaptor:MenloQErrorStatsHist:popErrorsDelta
        managed object property"
    ::= { cfprAdaptorMenloQErrorStatsHistEntry 12 }

cfprAdaptorMenloQErrorStatsHistPopErrorsDeltaAvg OBJECT-TYPE
    SYNTAX       Unsigned64
    MAX-ACCESS   read-only
    STATUS       current
    DESCRIPTION
        "Cisco Firepower adaptor:MenloQErrorStatsHist:popErrorsDeltaAvg
        managed object property"
    ::= { cfprAdaptorMenloQErrorStatsHistEntry 13 }

cfprAdaptorMenloQErrorStatsHistPopErrorsDeltaMax OBJECT-TYPE
    SYNTAX       Unsigned64
    MAX-ACCESS   read-only
    STATUS       current
    DESCRIPTION
        "Cisco Firepower adaptor:MenloQErrorStatsHist:popErrorsDeltaMax
        managed object property"
    ::= { cfprAdaptorMenloQErrorStatsHistEntry 14 }

cfprAdaptorMenloQErrorStatsHistPopErrorsDeltaMin OBJECT-TYPE
    SYNTAX       Unsigned64
    MAX-ACCESS   read-only
    STATUS       current
    DESCRIPTION
        "Cisco Firepower adaptor:MenloQErrorStatsHist:popErrorsDeltaMin
        managed object property"
    ::= { cfprAdaptorMenloQErrorStatsHistEntry 15 }

cfprAdaptorMenloQErrorStatsHistPushErrors OBJECT-TYPE
    SYNTAX       Unsigned64
    MAX-ACCESS   read-only
    STATUS       current
    DESCRIPTION
        "Cisco Firepower adaptor:MenloQErrorStatsHist:pushErrors
        managed object property"
    ::= { cfprAdaptorMenloQErrorStatsHistEntry 16 }

cfprAdaptorMenloQErrorStatsHistPushErrorsDelta OBJECT-TYPE
    SYNTAX       Unsigned64
    MAX-ACCESS   read-only
    STATUS       current
    DESCRIPTION
        "Cisco Firepower adaptor:MenloQErrorStatsHist:pushErrorsDelta
        managed object property"
    ::= { cfprAdaptorMenloQErrorStatsHistEntry 17 }

cfprAdaptorMenloQErrorStatsHistPushErrorsDeltaAvg OBJECT-TYPE
    SYNTAX       Unsigned64
    MAX-ACCESS   read-only
    STATUS       current
    DESCRIPTION
        "Cisco Firepower adaptor:MenloQErrorStatsHist:pushErrorsDeltaAvg
        managed object property"
    ::= { cfprAdaptorMenloQErrorStatsHistEntry 18 }

cfprAdaptorMenloQErrorStatsHistPushErrorsDeltaMax OBJECT-TYPE
    SYNTAX       Unsigned64
    MAX-ACCESS   read-only
    STATUS       current
    DESCRIPTION
        "Cisco Firepower adaptor:MenloQErrorStatsHist:pushErrorsDeltaMax
        managed object property"
    ::= { cfprAdaptorMenloQErrorStatsHistEntry 19 }

cfprAdaptorMenloQErrorStatsHistPushErrorsDeltaMin OBJECT-TYPE
    SYNTAX       Unsigned64
    MAX-ACCESS   read-only
    STATUS       current
    DESCRIPTION
        "Cisco Firepower adaptor:MenloQErrorStatsHist:pushErrorsDeltaMin
        managed object property"
    ::= { cfprAdaptorMenloQErrorStatsHistEntry 20 }

cfprAdaptorMenloQErrorStatsHistSuspect OBJECT-TYPE
    SYNTAX       TruthValue
    MAX-ACCESS   read-only
    STATUS       current
    DESCRIPTION
        "Cisco Firepower adaptor:MenloQErrorStatsHist:suspect
        managed object property"
    ::= { cfprAdaptorMenloQErrorStatsHistEntry 21 }

cfprAdaptorMenloQErrorStatsHistThresholded OBJECT-TYPE
    SYNTAX       CfprAdaptorMenloQErrorStatsHistThresholded
    MAX-ACCESS   read-only
    STATUS       current
    DESCRIPTION
        "Cisco Firepower adaptor:MenloQErrorStatsHist:thresholded
        managed object property"
    ::= { cfprAdaptorMenloQErrorStatsHistEntry 22 }

cfprAdaptorMenloQErrorStatsHistTimeCollected OBJECT-TYPE
    SYNTAX       DateAndTime
    MAX-ACCESS   read-only
    STATUS       current
    DESCRIPTION
        "Cisco Firepower adaptor:MenloQErrorStatsHist:timeCollected
        managed object property"
    ::= { cfprAdaptorMenloQErrorStatsHistEntry 23 }

cfprAdaptorMenloQErrorStatsHistUncorrectableErrors OBJECT-TYPE
    SYNTAX       Unsigned64
    MAX-ACCESS   read-only
    STATUS       current
    DESCRIPTION
        "Cisco Firepower adaptor:MenloQErrorStatsHist:uncorrectableErrors
        managed object property"
    ::= { cfprAdaptorMenloQErrorStatsHistEntry 24 }

cfprAdaptorMenloQErrorStatsHistUncorrectableErrorsDelta OBJECT-TYPE
    SYNTAX       Unsigned64
    MAX-ACCESS   read-only
    STATUS       current
    DESCRIPTION
        "Cisco Firepower adaptor:MenloQErrorStatsHist:uncorrectableErrorsD
        elta managed object property"
    ::= { cfprAdaptorMenloQErrorStatsHistEntry 25 }

cfprAdaptorMenloQErrorStatsHistUncorrectableErrorsDeltaAvg OBJECT-TYPE
    SYNTAX       Unsigned64
    MAX-ACCESS   read-only
    STATUS       current
    DESCRIPTION
        "Cisco Firepower adaptor:MenloQErrorStatsHist:uncorrectableErrorsD
        eltaAvg managed object property"
    ::= { cfprAdaptorMenloQErrorStatsHistEntry 26 }

cfprAdaptorMenloQErrorStatsHistUncorrectableErrorsDeltaMax OBJECT-TYPE
    SYNTAX       Unsigned64
    MAX-ACCESS   read-only
    STATUS       current
    DESCRIPTION
        "Cisco Firepower adaptor:MenloQErrorStatsHist:uncorrectableErrorsD
        eltaMax managed object property"
    ::= { cfprAdaptorMenloQErrorStatsHistEntry 27 }

cfprAdaptorMenloQErrorStatsHistUncorrectableErrorsDeltaMin OBJECT-TYPE
    SYNTAX       Unsigned64
    MAX-ACCESS   read-only
    STATUS       current
    DESCRIPTION
        "Cisco Firepower adaptor:MenloQErrorStatsHist:uncorrectableErrorsD
        eltaMin managed object property"
    ::= { cfprAdaptorMenloQErrorStatsHistEntry 28 }

cfprAdaptorMenloQStatsTable OBJECT-TYPE
    SYNTAX           SEQUENCE OF CfprAdaptorMenloQStatsEntry
    MAX-ACCESS       not-accessible
    STATUS           current
    DESCRIPTION
        "Cisco Firepower adaptor:MenloQStats managed object table"
    ::= { cfprAdaptorObjects 106 }

cfprAdaptorMenloQStatsEntry OBJECT-TYPE
    SYNTAX           CfprAdaptorMenloQStatsEntry
    MAX-ACCESS       not-accessible
    STATUS           current
    DESCRIPTION
        "Entry for the cfprAdaptorMenloQStatsTable table."
    INDEX { cfprAdaptorMenloQStatsInstanceId }
    ::= { cfprAdaptorMenloQStatsTable 1 }

CfprAdaptorMenloQStatsEntry ::= SEQUENCE {
    cfprAdaptorMenloQStatsInstanceId                                 CfprManagedObjectId,
    cfprAdaptorMenloQStatsDn                                         CfprManagedObjectDn,
    cfprAdaptorMenloQStatsRn                                         SnmpAdminString,
    cfprAdaptorMenloQStatsDropOverrunN0                              Unsigned64,
    cfprAdaptorMenloQStatsDropOverrunN0Delta                         Counter64,
    cfprAdaptorMenloQStatsDropOverrunN0DeltaAvg                      Unsigned64,
    cfprAdaptorMenloQStatsDropOverrunN0DeltaMax                      Unsigned64,
    cfprAdaptorMenloQStatsDropOverrunN0DeltaMin                      Unsigned64,
    cfprAdaptorMenloQStatsDropOverrunN1                              Unsigned64,
    cfprAdaptorMenloQStatsDropOverrunN1Delta                         Counter64,
    cfprAdaptorMenloQStatsDropOverrunN1DeltaAvg                      Unsigned64,
    cfprAdaptorMenloQStatsDropOverrunN1DeltaMax                      Unsigned64,
    cfprAdaptorMenloQStatsDropOverrunN1DeltaMin                      Unsigned64,
    cfprAdaptorMenloQStatsIntervals                                  Gauge32,
    cfprAdaptorMenloQStatsMenloQueueComponent                        CfprAdaptorMenloQueueStatsComponent,
    cfprAdaptorMenloQStatsMenloQueueIndex                            CfprAdaptorMenloStatsIndex,
    cfprAdaptorMenloQStatsSuspect                                    TruthValue,
    cfprAdaptorMenloQStatsThresholded                                CfprAdaptorMenloQStatsThresholded,
    cfprAdaptorMenloQStatsTimeCollected                              DateAndTime,
    cfprAdaptorMenloQStatsTruncateOverrunN0                          Unsigned64,
    cfprAdaptorMenloQStatsTruncateOverrunN0Delta                     Counter64,
    cfprAdaptorMenloQStatsTruncateOverrunN0DeltaAvg                  Unsigned64,
    cfprAdaptorMenloQStatsTruncateOverrunN0DeltaMax                  Unsigned64,
    cfprAdaptorMenloQStatsTruncateOverrunN0DeltaMin                  Unsigned64,
    cfprAdaptorMenloQStatsTruncateOverrunN1                          Unsigned64,
    cfprAdaptorMenloQStatsTruncateOverrunN1Delta                     Counter64,
    cfprAdaptorMenloQStatsTruncateOverrunN1DeltaAvg                  Unsigned64,
    cfprAdaptorMenloQStatsTruncateOverrunN1DeltaMax                  Unsigned64,
    cfprAdaptorMenloQStatsTruncateOverrunN1DeltaMin                  Unsigned64,
    cfprAdaptorMenloQStatsUpdate                                     Gauge32
}

cfprAdaptorMenloQStatsInstanceId OBJECT-TYPE
    SYNTAX       CfprManagedObjectId
    MAX-ACCESS   not-accessible
    STATUS       current
    DESCRIPTION
        "Instance identifier of the managed object."
    ::= { cfprAdaptorMenloQStatsEntry 1 }

cfprAdaptorMenloQStatsDn OBJECT-TYPE
    SYNTAX       CfprManagedObjectDn
    MAX-ACCESS   read-only
    STATUS       current
    DESCRIPTION
        "Cisco Firepower adaptor:MenloQStats:dn managed object property"
    ::= { cfprAdaptorMenloQStatsEntry 2 }

cfprAdaptorMenloQStatsRn OBJECT-TYPE
    SYNTAX       SnmpAdminString
    MAX-ACCESS   read-only
    STATUS       current
    DESCRIPTION
        "Cisco Firepower adaptor:MenloQStats:rn managed object property"
    ::= { cfprAdaptorMenloQStatsEntry 3 }

cfprAdaptorMenloQStatsDropOverrunN0 OBJECT-TYPE
    SYNTAX       Unsigned64
    MAX-ACCESS   read-only
    STATUS       current
    DESCRIPTION
        "Cisco Firepower adaptor:MenloQStats:dropOverrunN0
        managed object property"
    ::= { cfprAdaptorMenloQStatsEntry 4 }

cfprAdaptorMenloQStatsDropOverrunN0Delta OBJECT-TYPE
    SYNTAX       Counter64
    MAX-ACCESS   read-only
    STATUS       current
    DESCRIPTION
        "Cisco Firepower adaptor:MenloQStats:dropOverrunN0Delta
        managed object property"
    ::= { cfprAdaptorMenloQStatsEntry 5 }

cfprAdaptorMenloQStatsDropOverrunN0DeltaAvg OBJECT-TYPE
    SYNTAX       Unsigned64
    MAX-ACCESS   read-only
    STATUS       current
    DESCRIPTION
        "Cisco Firepower adaptor:MenloQStats:dropOverrunN0DeltaAvg
        managed object property"
    ::= { cfprAdaptorMenloQStatsEntry 6 }

cfprAdaptorMenloQStatsDropOverrunN0DeltaMax OBJECT-TYPE
    SYNTAX       Unsigned64
    MAX-ACCESS   read-only
    STATUS       current
    DESCRIPTION
        "Cisco Firepower adaptor:MenloQStats:dropOverrunN0DeltaMax
        managed object property"
    ::= { cfprAdaptorMenloQStatsEntry 7 }

cfprAdaptorMenloQStatsDropOverrunN0DeltaMin OBJECT-TYPE
    SYNTAX       Unsigned64
    MAX-ACCESS   read-only
    STATUS       current
    DESCRIPTION
        "Cisco Firepower adaptor:MenloQStats:dropOverrunN0DeltaMin
        managed object property"
    ::= { cfprAdaptorMenloQStatsEntry 8 }

cfprAdaptorMenloQStatsDropOverrunN1 OBJECT-TYPE
    SYNTAX       Unsigned64
    MAX-ACCESS   read-only
    STATUS       current
    DESCRIPTION
        "Cisco Firepower adaptor:MenloQStats:dropOverrunN1
        managed object property"
    ::= { cfprAdaptorMenloQStatsEntry 9 }

cfprAdaptorMenloQStatsDropOverrunN1Delta OBJECT-TYPE
    SYNTAX       Counter64
    MAX-ACCESS   read-only
    STATUS       current
    DESCRIPTION
        "Cisco Firepower adaptor:MenloQStats:dropOverrunN1Delta
        managed object property"
    ::= { cfprAdaptorMenloQStatsEntry 10 }

cfprAdaptorMenloQStatsDropOverrunN1DeltaAvg OBJECT-TYPE
    SYNTAX       Unsigned64
    MAX-ACCESS   read-only
    STATUS       current
    DESCRIPTION
        "Cisco Firepower adaptor:MenloQStats:dropOverrunN1DeltaAvg
        managed object property"
    ::= { cfprAdaptorMenloQStatsEntry 11 }

cfprAdaptorMenloQStatsDropOverrunN1DeltaMax OBJECT-TYPE
    SYNTAX       Unsigned64
    MAX-ACCESS   read-only
    STATUS       current
    DESCRIPTION
        "Cisco Firepower adaptor:MenloQStats:dropOverrunN1DeltaMax
        managed object property"
    ::= { cfprAdaptorMenloQStatsEntry 12 }

cfprAdaptorMenloQStatsDropOverrunN1DeltaMin OBJECT-TYPE
    SYNTAX       Unsigned64
    MAX-ACCESS   read-only
    STATUS       current
    DESCRIPTION
        "Cisco Firepower adaptor:MenloQStats:dropOverrunN1DeltaMin
        managed object property"
    ::= { cfprAdaptorMenloQStatsEntry 13 }

cfprAdaptorMenloQStatsIntervals OBJECT-TYPE
    SYNTAX       Gauge32
    MAX-ACCESS   read-only
    STATUS       current
    DESCRIPTION
        "Cisco Firepower adaptor:MenloQStats:intervals
        managed object property"
    ::= { cfprAdaptorMenloQStatsEntry 14 }

cfprAdaptorMenloQStatsMenloQueueComponent OBJECT-TYPE
    SYNTAX       CfprAdaptorMenloQueueStatsComponent
    MAX-ACCESS   read-only
    STATUS       current
    DESCRIPTION
        "Cisco Firepower adaptor:MenloQStats:menloQueueComponent
        managed object property"
    ::= { cfprAdaptorMenloQStatsEntry 15 }

cfprAdaptorMenloQStatsMenloQueueIndex OBJECT-TYPE
    SYNTAX       CfprAdaptorMenloStatsIndex
    MAX-ACCESS   read-only
    STATUS       current
    DESCRIPTION
        "Cisco Firepower adaptor:MenloQStats:menloQueueIndex
        managed object property"
    ::= { cfprAdaptorMenloQStatsEntry 16 }

cfprAdaptorMenloQStatsSuspect OBJECT-TYPE
    SYNTAX       TruthValue
    MAX-ACCESS   read-only
    STATUS       current
    DESCRIPTION
        "Cisco Firepower adaptor:MenloQStats:suspect managed
        object property"
    ::= { cfprAdaptorMenloQStatsEntry 17 }

cfprAdaptorMenloQStatsThresholded OBJECT-TYPE
    SYNTAX       CfprAdaptorMenloQStatsThresholded
    MAX-ACCESS   read-only
    STATUS       current
    DESCRIPTION
        "Cisco Firepower adaptor:MenloQStats:thresholded
        managed object property"
    ::= { cfprAdaptorMenloQStatsEntry 18 }

cfprAdaptorMenloQStatsTimeCollected OBJECT-TYPE
    SYNTAX       DateAndTime
    MAX-ACCESS   read-only
    STATUS       current
    DESCRIPTION
        "Cisco Firepower adaptor:MenloQStats:timeCollected
        managed object property"
    ::= { cfprAdaptorMenloQStatsEntry 19 }

cfprAdaptorMenloQStatsTruncateOverrunN0 OBJECT-TYPE
    SYNTAX       Unsigned64
    MAX-ACCESS   read-only
    STATUS       current
    DESCRIPTION
        "Cisco Firepower adaptor:MenloQStats:truncateOverrunN0
        managed object property"
    ::= { cfprAdaptorMenloQStatsEntry 20 }

cfprAdaptorMenloQStatsTruncateOverrunN0Delta OBJECT-TYPE
    SYNTAX       Counter64
    MAX-ACCESS   read-only
    STATUS       current
    DESCRIPTION
        "Cisco Firepower adaptor:MenloQStats:truncateOverrunN0Delta
        managed object property"
    ::= { cfprAdaptorMenloQStatsEntry 21 }

cfprAdaptorMenloQStatsTruncateOverrunN0DeltaAvg OBJECT-TYPE
    SYNTAX       Unsigned64
    MAX-ACCESS   read-only
    STATUS       current
    DESCRIPTION
        "Cisco Firepower adaptor:MenloQStats:truncateOverrunN0DeltaAvg
        managed object property"
    ::= { cfprAdaptorMenloQStatsEntry 22 }

cfprAdaptorMenloQStatsTruncateOverrunN0DeltaMax OBJECT-TYPE
    SYNTAX       Unsigned64
    MAX-ACCESS   read-only
    STATUS       current
    DESCRIPTION
        "Cisco Firepower adaptor:MenloQStats:truncateOverrunN0DeltaMax
        managed object property"
    ::= { cfprAdaptorMenloQStatsEntry 23 }

cfprAdaptorMenloQStatsTruncateOverrunN0DeltaMin OBJECT-TYPE
    SYNTAX       Unsigned64
    MAX-ACCESS   read-only
    STATUS       current
    DESCRIPTION
        "Cisco Firepower adaptor:MenloQStats:truncateOverrunN0DeltaMin
        managed object property"
    ::= { cfprAdaptorMenloQStatsEntry 24 }

cfprAdaptorMenloQStatsTruncateOverrunN1 OBJECT-TYPE
    SYNTAX       Unsigned64
    MAX-ACCESS   read-only
    STATUS       current
    DESCRIPTION
        "Cisco Firepower adaptor:MenloQStats:truncateOverrunN1
        managed object property"
    ::= { cfprAdaptorMenloQStatsEntry 25 }

cfprAdaptorMenloQStatsTruncateOverrunN1Delta OBJECT-TYPE
    SYNTAX       Counter64
    MAX-ACCESS   read-only
    STATUS       current
    DESCRIPTION
        "Cisco Firepower adaptor:MenloQStats:truncateOverrunN1Delta
        managed object property"
    ::= { cfprAdaptorMenloQStatsEntry 26 }

cfprAdaptorMenloQStatsTruncateOverrunN1DeltaAvg OBJECT-TYPE
    SYNTAX       Unsigned64
    MAX-ACCESS   read-only
    STATUS       current
    DESCRIPTION
        "Cisco Firepower adaptor:MenloQStats:truncateOverrunN1DeltaAvg
        managed object property"
    ::= { cfprAdaptorMenloQStatsEntry 27 }

cfprAdaptorMenloQStatsTruncateOverrunN1DeltaMax OBJECT-TYPE
    SYNTAX       Unsigned64
    MAX-ACCESS   read-only
    STATUS       current
    DESCRIPTION
        "Cisco Firepower adaptor:MenloQStats:truncateOverrunN1DeltaMax
        managed object property"
    ::= { cfprAdaptorMenloQStatsEntry 28 }

cfprAdaptorMenloQStatsTruncateOverrunN1DeltaMin OBJECT-TYPE
    SYNTAX       Unsigned64
    MAX-ACCESS   read-only
    STATUS       current
    DESCRIPTION
        "Cisco Firepower adaptor:MenloQStats:truncateOverrunN1DeltaMin
        managed object property"
    ::= { cfprAdaptorMenloQStatsEntry 29 }

cfprAdaptorMenloQStatsUpdate OBJECT-TYPE
    SYNTAX       Gauge32
    MAX-ACCESS   read-only
    STATUS       current
    DESCRIPTION
        "Cisco Firepower adaptor:MenloQStats:update managed
        object property"
    ::= { cfprAdaptorMenloQStatsEntry 30 }

cfprAdaptorMenloQStatsHistTable OBJECT-TYPE
    SYNTAX           SEQUENCE OF CfprAdaptorMenloQStatsHistEntry
    MAX-ACCESS       not-accessible
    STATUS           current
    DESCRIPTION
        "Cisco Firepower adaptor:MenloQStatsHist managed object table"
    ::= { cfprAdaptorObjects 107 }

cfprAdaptorMenloQStatsHistEntry OBJECT-TYPE
    SYNTAX           CfprAdaptorMenloQStatsHistEntry
    MAX-ACCESS       not-accessible
    STATUS           current
    DESCRIPTION
        "Entry for the cfprAdaptorMenloQStatsHistTable table."
    INDEX { cfprAdaptorMenloQStatsHistInstanceId }
    ::= { cfprAdaptorMenloQStatsHistTable 1 }

CfprAdaptorMenloQStatsHistEntry ::= SEQUENCE {
    cfprAdaptorMenloQStatsHistInstanceId                             CfprManagedObjectId,
    cfprAdaptorMenloQStatsHistDn                                     CfprManagedObjectDn,
    cfprAdaptorMenloQStatsHistRn                                     SnmpAdminString,
    cfprAdaptorMenloQStatsHistDropOverrunN0                          Unsigned64,
    cfprAdaptorMenloQStatsHistDropOverrunN0Delta                     Unsigned64,
    cfprAdaptorMenloQStatsHistDropOverrunN0DeltaAvg                  Unsigned64,
    cfprAdaptorMenloQStatsHistDropOverrunN0DeltaMax                  Unsigned64,
    cfprAdaptorMenloQStatsHistDropOverrunN0DeltaMin                  Unsigned64,
    cfprAdaptorMenloQStatsHistDropOverrunN1                          Unsigned64,
    cfprAdaptorMenloQStatsHistDropOverrunN1Delta                     Unsigned64,
    cfprAdaptorMenloQStatsHistDropOverrunN1DeltaAvg                  Unsigned64,
    cfprAdaptorMenloQStatsHistDropOverrunN1DeltaMax                  Unsigned64,
    cfprAdaptorMenloQStatsHistDropOverrunN1DeltaMin                  Unsigned64,
    cfprAdaptorMenloQStatsHistId                                     Unsigned64,
    cfprAdaptorMenloQStatsHistMostRecent                             TruthValue,
    cfprAdaptorMenloQStatsHistSuspect                                TruthValue,
    cfprAdaptorMenloQStatsHistThresholded                            CfprAdaptorMenloQStatsHistThresholded,
    cfprAdaptorMenloQStatsHistTimeCollected                          DateAndTime,
    cfprAdaptorMenloQStatsHistTruncateOverrunN0                      Unsigned64,
    cfprAdaptorMenloQStatsHistTruncateOverrunN0Delta                 Unsigned64,
    cfprAdaptorMenloQStatsHistTruncateOverrunN0DeltaAvg              Unsigned64,
    cfprAdaptorMenloQStatsHistTruncateOverrunN0DeltaMax              Unsigned64,
    cfprAdaptorMenloQStatsHistTruncateOverrunN0DeltaMin              Unsigned64,
    cfprAdaptorMenloQStatsHistTruncateOverrunN1                      Unsigned64,
    cfprAdaptorMenloQStatsHistTruncateOverrunN1Delta                 Unsigned64,
    cfprAdaptorMenloQStatsHistTruncateOverrunN1DeltaAvg              Unsigned64,
    cfprAdaptorMenloQStatsHistTruncateOverrunN1DeltaMax              Unsigned64,
    cfprAdaptorMenloQStatsHistTruncateOverrunN1DeltaMin              Unsigned64
}

cfprAdaptorMenloQStatsHistInstanceId OBJECT-TYPE
    SYNTAX       CfprManagedObjectId
    MAX-ACCESS   not-accessible
    STATUS       current
    DESCRIPTION
        "Instance identifier of the managed object."
    ::= { cfprAdaptorMenloQStatsHistEntry 1 }

cfprAdaptorMenloQStatsHistDn OBJECT-TYPE
    SYNTAX       CfprManagedObjectDn
    MAX-ACCESS   read-only
    STATUS       current
    DESCRIPTION
        "Cisco Firepower adaptor:MenloQStatsHist:dn managed
        object property"
    ::= { cfprAdaptorMenloQStatsHistEntry 2 }

cfprAdaptorMenloQStatsHistRn OBJECT-TYPE
    SYNTAX       SnmpAdminString
    MAX-ACCESS   read-only
    STATUS       current
    DESCRIPTION
        "Cisco Firepower adaptor:MenloQStatsHist:rn managed
        object property"
    ::= { cfprAdaptorMenloQStatsHistEntry 3 }

cfprAdaptorMenloQStatsHistDropOverrunN0 OBJECT-TYPE
    SYNTAX       Unsigned64
    MAX-ACCESS   read-only
    STATUS       current
    DESCRIPTION
        "Cisco Firepower adaptor:MenloQStatsHist:dropOverrunN0
        managed object property"
    ::= { cfprAdaptorMenloQStatsHistEntry 4 }

cfprAdaptorMenloQStatsHistDropOverrunN0Delta OBJECT-TYPE
    SYNTAX       Unsigned64
    MAX-ACCESS   read-only
    STATUS       current
    DESCRIPTION
        "Cisco Firepower adaptor:MenloQStatsHist:dropOverrunN0Delta
        managed object property"
    ::= { cfprAdaptorMenloQStatsHistEntry 5 }

cfprAdaptorMenloQStatsHistDropOverrunN0DeltaAvg OBJECT-TYPE
    SYNTAX       Unsigned64
    MAX-ACCESS   read-only
    STATUS       current
    DESCRIPTION
        "Cisco Firepower adaptor:MenloQStatsHist:dropOverrunN0DeltaAvg
        managed object property"
    ::= { cfprAdaptorMenloQStatsHistEntry 6 }

cfprAdaptorMenloQStatsHistDropOverrunN0DeltaMax OBJECT-TYPE
    SYNTAX       Unsigned64
    MAX-ACCESS   read-only
    STATUS       current
    DESCRIPTION
        "Cisco Firepower adaptor:MenloQStatsHist:dropOverrunN0DeltaMax
        managed object property"
    ::= { cfprAdaptorMenloQStatsHistEntry 7 }

cfprAdaptorMenloQStatsHistDropOverrunN0DeltaMin OBJECT-TYPE
    SYNTAX       Unsigned64
    MAX-ACCESS   read-only
    STATUS       current
    DESCRIPTION
        "Cisco Firepower adaptor:MenloQStatsHist:dropOverrunN0DeltaMin
        managed object property"
    ::= { cfprAdaptorMenloQStatsHistEntry 8 }

cfprAdaptorMenloQStatsHistDropOverrunN1 OBJECT-TYPE
    SYNTAX       Unsigned64
    MAX-ACCESS   read-only
    STATUS       current
    DESCRIPTION
        "Cisco Firepower adaptor:MenloQStatsHist:dropOverrunN1
        managed object property"
    ::= { cfprAdaptorMenloQStatsHistEntry 9 }

cfprAdaptorMenloQStatsHistDropOverrunN1Delta OBJECT-TYPE
    SYNTAX       Unsigned64
    MAX-ACCESS   read-only
    STATUS       current
    DESCRIPTION
        "Cisco Firepower adaptor:MenloQStatsHist:dropOverrunN1Delta
        managed object property"
    ::= { cfprAdaptorMenloQStatsHistEntry 10 }

cfprAdaptorMenloQStatsHistDropOverrunN1DeltaAvg OBJECT-TYPE
    SYNTAX       Unsigned64
    MAX-ACCESS   read-only
    STATUS       current
    DESCRIPTION
        "Cisco Firepower adaptor:MenloQStatsHist:dropOverrunN1DeltaAvg
        managed object property"
    ::= { cfprAdaptorMenloQStatsHistEntry 11 }

cfprAdaptorMenloQStatsHistDropOverrunN1DeltaMax OBJECT-TYPE
    SYNTAX       Unsigned64
    MAX-ACCESS   read-only
    STATUS       current
    DESCRIPTION
        "Cisco Firepower adaptor:MenloQStatsHist:dropOverrunN1DeltaMax
        managed object property"
    ::= { cfprAdaptorMenloQStatsHistEntry 12 }

cfprAdaptorMenloQStatsHistDropOverrunN1DeltaMin OBJECT-TYPE
    SYNTAX       Unsigned64
    MAX-ACCESS   read-only
    STATUS       current
    DESCRIPTION
        "Cisco Firepower adaptor:MenloQStatsHist:dropOverrunN1DeltaMin
        managed object property"
    ::= { cfprAdaptorMenloQStatsHistEntry 13 }

cfprAdaptorMenloQStatsHistId OBJECT-TYPE
    SYNTAX       Unsigned64
    MAX-ACCESS   read-only
    STATUS       current
    DESCRIPTION
        "Cisco Firepower adaptor:MenloQStatsHist:id managed
        object property"
    ::= { cfprAdaptorMenloQStatsHistEntry 14 }

cfprAdaptorMenloQStatsHistMostRecent OBJECT-TYPE
    SYNTAX       TruthValue
    MAX-ACCESS   read-only
    STATUS       current
    DESCRIPTION
        "Cisco Firepower adaptor:MenloQStatsHist:mostRecent
        managed object property"
    ::= { cfprAdaptorMenloQStatsHistEntry 15 }

cfprAdaptorMenloQStatsHistSuspect OBJECT-TYPE
    SYNTAX       TruthValue
    MAX-ACCESS   read-only
    STATUS       current
    DESCRIPTION
        "Cisco Firepower adaptor:MenloQStatsHist:suspect
        managed object property"
    ::= { cfprAdaptorMenloQStatsHistEntry 16 }

cfprAdaptorMenloQStatsHistThresholded OBJECT-TYPE
    SYNTAX       CfprAdaptorMenloQStatsHistThresholded
    MAX-ACCESS   read-only
    STATUS       current
    DESCRIPTION
        "Cisco Firepower adaptor:MenloQStatsHist:thresholded
        managed object property"
    ::= { cfprAdaptorMenloQStatsHistEntry 17 }

cfprAdaptorMenloQStatsHistTimeCollected OBJECT-TYPE
    SYNTAX       DateAndTime
    MAX-ACCESS   read-only
    STATUS       current
    DESCRIPTION
        "Cisco Firepower adaptor:MenloQStatsHist:timeCollected
        managed object property"
    ::= { cfprAdaptorMenloQStatsHistEntry 18 }

cfprAdaptorMenloQStatsHistTruncateOverrunN0 OBJECT-TYPE
    SYNTAX       Unsigned64
    MAX-ACCESS   read-only
    STATUS       current
    DESCRIPTION
        "Cisco Firepower adaptor:MenloQStatsHist:truncateOverrunN0
        managed object property"
    ::= { cfprAdaptorMenloQStatsHistEntry 19 }

cfprAdaptorMenloQStatsHistTruncateOverrunN0Delta OBJECT-TYPE
    SYNTAX       Unsigned64
    MAX-ACCESS   read-only
    STATUS       current
    DESCRIPTION
        "Cisco Firepower adaptor:MenloQStatsHist:truncateOverrunN0Delta
        managed object property"
    ::= { cfprAdaptorMenloQStatsHistEntry 20 }

cfprAdaptorMenloQStatsHistTruncateOverrunN0DeltaAvg OBJECT-TYPE
    SYNTAX       Unsigned64
    MAX-ACCESS   read-only
    STATUS       current
    DESCRIPTION
        "Cisco Firepower adaptor:MenloQStatsHist:truncateOverrunN0DeltaAvg
         managed object property"
    ::= { cfprAdaptorMenloQStatsHistEntry 21 }

cfprAdaptorMenloQStatsHistTruncateOverrunN0DeltaMax OBJECT-TYPE
    SYNTAX       Unsigned64
    MAX-ACCESS   read-only
    STATUS       current
    DESCRIPTION
        "Cisco Firepower adaptor:MenloQStatsHist:truncateOverrunN0DeltaMax
         managed object property"
    ::= { cfprAdaptorMenloQStatsHistEntry 22 }

cfprAdaptorMenloQStatsHistTruncateOverrunN0DeltaMin OBJECT-TYPE
    SYNTAX       Unsigned64
    MAX-ACCESS   read-only
    STATUS       current
    DESCRIPTION
        "Cisco Firepower adaptor:MenloQStatsHist:truncateOverrunN0DeltaMin
         managed object property"
    ::= { cfprAdaptorMenloQStatsHistEntry 23 }

cfprAdaptorMenloQStatsHistTruncateOverrunN1 OBJECT-TYPE
    SYNTAX       Unsigned64
    MAX-ACCESS   read-only
    STATUS       current
    DESCRIPTION
        "Cisco Firepower adaptor:MenloQStatsHist:truncateOverrunN1
        managed object property"
    ::= { cfprAdaptorMenloQStatsHistEntry 24 }

cfprAdaptorMenloQStatsHistTruncateOverrunN1Delta OBJECT-TYPE
    SYNTAX       Unsigned64
    MAX-ACCESS   read-only
    STATUS       current
    DESCRIPTION
        "Cisco Firepower adaptor:MenloQStatsHist:truncateOverrunN1Delta
        managed object property"
    ::= { cfprAdaptorMenloQStatsHistEntry 25 }

cfprAdaptorMenloQStatsHistTruncateOverrunN1DeltaAvg OBJECT-TYPE
    SYNTAX       Unsigned64
    MAX-ACCESS   read-only
    STATUS       current
    DESCRIPTION
        "Cisco Firepower adaptor:MenloQStatsHist:truncateOverrunN1DeltaAvg
         managed object property"
    ::= { cfprAdaptorMenloQStatsHistEntry 26 }

cfprAdaptorMenloQStatsHistTruncateOverrunN1DeltaMax OBJECT-TYPE
    SYNTAX       Unsigned64
    MAX-ACCESS   read-only
    STATUS       current
    DESCRIPTION
        "Cisco Firepower adaptor:MenloQStatsHist:truncateOverrunN1DeltaMax
         managed object property"
    ::= { cfprAdaptorMenloQStatsHistEntry 27 }

cfprAdaptorMenloQStatsHistTruncateOverrunN1DeltaMin OBJECT-TYPE
    SYNTAX       Unsigned64
    MAX-ACCESS   read-only
    STATUS       current
    DESCRIPTION
        "Cisco Firepower adaptor:MenloQStatsHist:truncateOverrunN1DeltaMin
         managed object property"
    ::= { cfprAdaptorMenloQStatsHistEntry 28 }

cfprAdaptorNwMgmtCapTable OBJECT-TYPE
    SYNTAX           SEQUENCE OF CfprAdaptorNwMgmtCapEntry
    MAX-ACCESS       not-accessible
    STATUS           current
    DESCRIPTION
        "Cisco Firepower adaptor:NwMgmtCap managed object table"
    ::= { cfprAdaptorObjects 108 }

cfprAdaptorNwMgmtCapEntry OBJECT-TYPE
    SYNTAX           CfprAdaptorNwMgmtCapEntry
    MAX-ACCESS       not-accessible
    STATUS           current
    DESCRIPTION
        "Entry for the cfprAdaptorNwMgmtCapTable table."
    INDEX { cfprAdaptorNwMgmtCapInstanceId }
    ::= { cfprAdaptorNwMgmtCapTable 1 }

CfprAdaptorNwMgmtCapEntry ::= SEQUENCE {
    cfprAdaptorNwMgmtCapInstanceId                                   CfprManagedObjectId,
    cfprAdaptorNwMgmtCapDn                                           CfprManagedObjectDn,
    cfprAdaptorNwMgmtCapRn                                           SnmpAdminString,
    cfprAdaptorNwMgmtCapApi                                          CfprAdaptorNwMgmtCapApi,
    cfprAdaptorNwMgmtCapMgmtTransport                                CfprAdaptorNwMgmtCapMgmtTransport,
    cfprAdaptorNwMgmtCapMode                                         CfprAdaptorMgmtCapMode,
    cfprAdaptorNwMgmtCapOperPowerRequirement                         CfprAdaptorMgmtCapOperPowerRequirement,
    cfprAdaptorNwMgmtCapRebootActionOnDestructive                    CfprAdaptorMgmtCapRebootActionOnDestructive
}

cfprAdaptorNwMgmtCapInstanceId OBJECT-TYPE
    SYNTAX       CfprManagedObjectId
    MAX-ACCESS   not-accessible
    STATUS       current
    DESCRIPTION
        "Instance identifier of the managed object."
    ::= { cfprAdaptorNwMgmtCapEntry 1 }

cfprAdaptorNwMgmtCapDn OBJECT-TYPE
    SYNTAX       CfprManagedObjectDn
    MAX-ACCESS   read-only
    STATUS       current
    DESCRIPTION
        "Cisco Firepower adaptor:NwMgmtCap:dn managed object property"
    ::= { cfprAdaptorNwMgmtCapEntry 2 }

cfprAdaptorNwMgmtCapRn OBJECT-TYPE
    SYNTAX       SnmpAdminString
    MAX-ACCESS   read-only
    STATUS       current
    DESCRIPTION
        "Cisco Firepower adaptor:NwMgmtCap:rn managed object property"
    ::= { cfprAdaptorNwMgmtCapEntry 3 }

cfprAdaptorNwMgmtCapApi OBJECT-TYPE
    SYNTAX       CfprAdaptorNwMgmtCapApi
    MAX-ACCESS   read-only
    STATUS       current
    DESCRIPTION
        "Cisco Firepower adaptor:NwMgmtCap:api managed object property"
    ::= { cfprAdaptorNwMgmtCapEntry 4 }

cfprAdaptorNwMgmtCapMgmtTransport OBJECT-TYPE
    SYNTAX       CfprAdaptorNwMgmtCapMgmtTransport
    MAX-ACCESS   read-only
    STATUS       current
    DESCRIPTION
        "Cisco Firepower adaptor:NwMgmtCap:mgmtTransport
        managed object property"
    ::= { cfprAdaptorNwMgmtCapEntry 5 }

cfprAdaptorNwMgmtCapMode OBJECT-TYPE
    SYNTAX       CfprAdaptorMgmtCapMode
    MAX-ACCESS   read-only
    STATUS       current
    DESCRIPTION
        "Cisco Firepower adaptor:NwMgmtCap:mode managed object property"
    ::= { cfprAdaptorNwMgmtCapEntry 6 }

cfprAdaptorNwMgmtCapOperPowerRequirement OBJECT-TYPE
    SYNTAX       CfprAdaptorMgmtCapOperPowerRequirement
    MAX-ACCESS   read-only
    STATUS       current
    DESCRIPTION
        "Cisco Firepower adaptor:NwMgmtCap:operPowerRequirement
        managed object property"
    ::= { cfprAdaptorNwMgmtCapEntry 7 }

cfprAdaptorNwMgmtCapRebootActionOnDestructive OBJECT-TYPE
    SYNTAX       CfprAdaptorMgmtCapRebootActionOnDestructive
    MAX-ACCESS   read-only
    STATUS       current
    DESCRIPTION
        "Cisco Firepower adaptor:NwMgmtCap:rebootActionOnDestructive
        managed object property"
    ::= { cfprAdaptorNwMgmtCapEntry 8 }

cfprAdaptorProtocolProfileTable OBJECT-TYPE
    SYNTAX           SEQUENCE OF CfprAdaptorProtocolProfileEntry
    MAX-ACCESS       not-accessible
    STATUS           current
    DESCRIPTION
        "Cisco Firepower adaptor:ProtocolProfile managed object table"
    ::= { cfprAdaptorObjects 109 }

cfprAdaptorProtocolProfileEntry OBJECT-TYPE
    SYNTAX           CfprAdaptorProtocolProfileEntry
    MAX-ACCESS       not-accessible
    STATUS           current
    DESCRIPTION
        "Entry for the cfprAdaptorProtocolProfileTable table."
    INDEX { cfprAdaptorProtocolProfileInstanceId }
    ::= { cfprAdaptorProtocolProfileTable 1 }

CfprAdaptorProtocolProfileEntry ::= SEQUENCE {
    cfprAdaptorProtocolProfileInstanceId                             CfprManagedObjectId,
    cfprAdaptorProtocolProfileDn                                     CfprManagedObjectDn,
    cfprAdaptorProtocolProfileRn                                     SnmpAdminString,
    cfprAdaptorProtocolProfileBootToTarget                           TruthValue,
    cfprAdaptorProtocolProfileConnectionTimeOut                      CfprAdaptorProtocolProfileConnectionTimeOut,
    cfprAdaptorProtocolProfileDhcpTimeOut                            Gauge32,
    cfprAdaptorProtocolProfileHbaMode                                TruthValue,
    cfprAdaptorProtocolProfileLunBusyRetryCount                      CfprAdaptorProtocolProfileLunBusyRetryCount,
    cfprAdaptorProtocolProfileTcpTimeStamp                           TruthValue
}

cfprAdaptorProtocolProfileInstanceId OBJECT-TYPE
    SYNTAX       CfprManagedObjectId
    MAX-ACCESS   not-accessible
    STATUS       current
    DESCRIPTION
        "Instance identifier of the managed object."
    ::= { cfprAdaptorProtocolProfileEntry 1 }

cfprAdaptorProtocolProfileDn OBJECT-TYPE
    SYNTAX       CfprManagedObjectDn
    MAX-ACCESS   read-only
    STATUS       current
    DESCRIPTION
        "Cisco Firepower adaptor:ProtocolProfile:dn managed
        object property"
    ::= { cfprAdaptorProtocolProfileEntry 2 }

cfprAdaptorProtocolProfileRn OBJECT-TYPE
    SYNTAX       SnmpAdminString
    MAX-ACCESS   read-only
    STATUS       current
    DESCRIPTION
        "Cisco Firepower adaptor:ProtocolProfile:rn managed
        object property"
    ::= { cfprAdaptorProtocolProfileEntry 3 }

cfprAdaptorProtocolProfileBootToTarget OBJECT-TYPE
    SYNTAX       TruthValue
    MAX-ACCESS   read-only
    STATUS       current
    DESCRIPTION
        "Cisco Firepower adaptor:ProtocolProfile:bootToTarget
        managed object property"
    ::= { cfprAdaptorProtocolProfileEntry 4 }

cfprAdaptorProtocolProfileConnectionTimeOut OBJECT-TYPE
    SYNTAX       CfprAdaptorProtocolProfileConnectionTimeOut
    MAX-ACCESS   read-only
    STATUS       current
    DESCRIPTION
        "Cisco Firepower adaptor:ProtocolProfile:connectionTimeOut
        managed object property"
    ::= { cfprAdaptorProtocolProfileEntry 5 }

cfprAdaptorProtocolProfileDhcpTimeOut OBJECT-TYPE
    SYNTAX       Gauge32
    MAX-ACCESS   read-only
    STATUS       current
    DESCRIPTION
        "Cisco Firepower adaptor:ProtocolProfile:dhcpTimeOut
        managed object property"
    ::= { cfprAdaptorProtocolProfileEntry 6 }

cfprAdaptorProtocolProfileHbaMode OBJECT-TYPE
    SYNTAX       TruthValue
    MAX-ACCESS   read-only
    STATUS       current
    DESCRIPTION
        "Cisco Firepower adaptor:ProtocolProfile:hbaMode
        managed object property"
    ::= { cfprAdaptorProtocolProfileEntry 7 }

cfprAdaptorProtocolProfileLunBusyRetryCount OBJECT-TYPE
    SYNTAX       CfprAdaptorProtocolProfileLunBusyRetryCount
    MAX-ACCESS   read-only
    STATUS       current
    DESCRIPTION
        "Cisco Firepower adaptor:ProtocolProfile:lunBusyRetryCount
        managed object property"
    ::= { cfprAdaptorProtocolProfileEntry 8 }

cfprAdaptorProtocolProfileTcpTimeStamp OBJECT-TYPE
    SYNTAX       TruthValue
    MAX-ACCESS   read-only
    STATUS       current
    DESCRIPTION
        "Cisco Firepower adaptor:ProtocolProfile:tcpTimeStamp
        managed object property"
    ::= { cfprAdaptorProtocolProfileEntry 9 }

cfprAdaptorQualTable OBJECT-TYPE
    SYNTAX           SEQUENCE OF CfprAdaptorQualEntry
    MAX-ACCESS       not-accessible
    STATUS           current
    DESCRIPTION
        "Cisco Firepower adaptor:Qual managed object table"
    ::= { cfprAdaptorObjects 110 }

cfprAdaptorQualEntry OBJECT-TYPE
    SYNTAX           CfprAdaptorQualEntry
    MAX-ACCESS       not-accessible
    STATUS           current
    DESCRIPTION
        "Entry for the cfprAdaptorQualTable table."
    INDEX { cfprAdaptorQualInstanceId }
    ::= { cfprAdaptorQualTable 1 }

CfprAdaptorQualEntry ::= SEQUENCE {
    cfprAdaptorQualInstanceId                                        CfprManagedObjectId,
    cfprAdaptorQualDn                                                CfprManagedObjectDn,
    cfprAdaptorQualRn                                                SnmpAdminString
}

cfprAdaptorQualInstanceId OBJECT-TYPE
    SYNTAX       CfprManagedObjectId
    MAX-ACCESS   not-accessible
    STATUS       current
    DESCRIPTION
        "Instance identifier of the managed object."
    ::= { cfprAdaptorQualEntry 1 }

cfprAdaptorQualDn OBJECT-TYPE
    SYNTAX       CfprManagedObjectDn
    MAX-ACCESS   read-only
    STATUS       current
    DESCRIPTION
        "Cisco Firepower adaptor:Qual:dn managed object property"
    ::= { cfprAdaptorQualEntry 2 }

cfprAdaptorQualRn OBJECT-TYPE
    SYNTAX       SnmpAdminString
    MAX-ACCESS   read-only
    STATUS       current
    DESCRIPTION
        "Cisco Firepower adaptor:Qual:rn managed object property"
    ::= { cfprAdaptorQualEntry 3 }

cfprAdaptorRssProfileTable OBJECT-TYPE
    SYNTAX           SEQUENCE OF CfprAdaptorRssProfileEntry
    MAX-ACCESS       not-accessible
    STATUS           current
    DESCRIPTION
        "Cisco Firepower adaptor:RssProfile managed object table"
    ::= { cfprAdaptorObjects 111 }

cfprAdaptorRssProfileEntry OBJECT-TYPE
    SYNTAX           CfprAdaptorRssProfileEntry
    MAX-ACCESS       not-accessible
    STATUS           current
    DESCRIPTION
        "Entry for the cfprAdaptorRssProfileTable table."
    INDEX { cfprAdaptorRssProfileInstanceId }
    ::= { cfprAdaptorRssProfileTable 1 }

CfprAdaptorRssProfileEntry ::= SEQUENCE {
    cfprAdaptorRssProfileInstanceId                                  CfprManagedObjectId,
    cfprAdaptorRssProfileDn                                          CfprManagedObjectDn,
    cfprAdaptorRssProfileRn                                          SnmpAdminString,
    cfprAdaptorRssProfileReceiveSideScaling                          CfprAdaptorRssProfileReceiveSideScaling
}

cfprAdaptorRssProfileInstanceId OBJECT-TYPE
    SYNTAX       CfprManagedObjectId
    MAX-ACCESS   not-accessible
    STATUS       current
    DESCRIPTION
        "Instance identifier of the managed object."
    ::= { cfprAdaptorRssProfileEntry 1 }

cfprAdaptorRssProfileDn OBJECT-TYPE
    SYNTAX       CfprManagedObjectDn
    MAX-ACCESS   read-only
    STATUS       current
    DESCRIPTION
        "Cisco Firepower adaptor:RssProfile:dn managed object property"
    ::= { cfprAdaptorRssProfileEntry 2 }

cfprAdaptorRssProfileRn OBJECT-TYPE
    SYNTAX       SnmpAdminString
    MAX-ACCESS   read-only
    STATUS       current
    DESCRIPTION
        "Cisco Firepower adaptor:RssProfile:rn managed object property"
    ::= { cfprAdaptorRssProfileEntry 3 }

cfprAdaptorRssProfileReceiveSideScaling OBJECT-TYPE
    SYNTAX       CfprAdaptorRssProfileReceiveSideScaling
    MAX-ACCESS   read-only
    STATUS       current
    DESCRIPTION
        "Cisco Firepower adaptor:RssProfile:receiveSideScaling
        managed object property"
    ::= { cfprAdaptorRssProfileEntry 4 }

cfprAdaptorSanCapTable OBJECT-TYPE
    SYNTAX           SEQUENCE OF CfprAdaptorSanCapEntry
    MAX-ACCESS       not-accessible
    STATUS           current
    DESCRIPTION
        "Cisco Firepower adaptor:SanCap managed object table"
    ::= { cfprAdaptorObjects 112 }

cfprAdaptorSanCapEntry OBJECT-TYPE
    SYNTAX           CfprAdaptorSanCapEntry
    MAX-ACCESS       not-accessible
    STATUS           current
    DESCRIPTION
        "Entry for the cfprAdaptorSanCapTable table."
    INDEX { cfprAdaptorSanCapInstanceId }
    ::= { cfprAdaptorSanCapTable 1 }

CfprAdaptorSanCapEntry ::= SEQUENCE {
    cfprAdaptorSanCapInstanceId                                      CfprManagedObjectId,
    cfprAdaptorSanCapDn                                              CfprManagedObjectDn,
    cfprAdaptorSanCapRn                                              SnmpAdminString,
    cfprAdaptorSanCapHostNvram                                       CfprAdaptorSanCapHostNvram
}

cfprAdaptorSanCapInstanceId OBJECT-TYPE
    SYNTAX       CfprManagedObjectId
    MAX-ACCESS   not-accessible
    STATUS       current
    DESCRIPTION
        "Instance identifier of the managed object."
    ::= { cfprAdaptorSanCapEntry 1 }

cfprAdaptorSanCapDn OBJECT-TYPE
    SYNTAX       CfprManagedObjectDn
    MAX-ACCESS   read-only
    STATUS       current
    DESCRIPTION
        "Cisco Firepower adaptor:SanCap:dn managed object property"
    ::= { cfprAdaptorSanCapEntry 2 }

cfprAdaptorSanCapRn OBJECT-TYPE
    SYNTAX       SnmpAdminString
    MAX-ACCESS   read-only
    STATUS       current
    DESCRIPTION
        "Cisco Firepower adaptor:SanCap:rn managed object property"
    ::= { cfprAdaptorSanCapEntry 3 }

cfprAdaptorSanCapHostNvram OBJECT-TYPE
    SYNTAX       CfprAdaptorSanCapHostNvram
    MAX-ACCESS   read-only
    STATUS       current
    DESCRIPTION
        "Cisco Firepower adaptor:SanCap:hostNvram managed object property"
    ::= { cfprAdaptorSanCapEntry 4 }

cfprAdaptorUnitTable OBJECT-TYPE
    SYNTAX           SEQUENCE OF CfprAdaptorUnitEntry
    MAX-ACCESS       not-accessible
    STATUS           current
    DESCRIPTION
        "Cisco Firepower adaptor:Unit managed object table"
    ::= { cfprAdaptorObjects 113 }

cfprAdaptorUnitEntry OBJECT-TYPE
    SYNTAX           CfprAdaptorUnitEntry
    MAX-ACCESS       not-accessible
    STATUS           current
    DESCRIPTION
        "Entry for the cfprAdaptorUnitTable table."
    INDEX { cfprAdaptorUnitInstanceId }
    ::= { cfprAdaptorUnitTable 1 }

CfprAdaptorUnitEntry ::= SEQUENCE {
    cfprAdaptorUnitInstanceId                                        CfprManagedObjectId,
    cfprAdaptorUnitDn                                                CfprManagedObjectDn,
    cfprAdaptorUnitRn                                                SnmpAdminString,
    cfprAdaptorUnitAdminPowerState                                   CfprAdaptorAdminPowerState,
    cfprAdaptorUnitBaseMac                                           MacAddress,
    cfprAdaptorUnitBladeId                                           Gauge32,
    cfprAdaptorUnitChassisId                                         Gauge32,
    cfprAdaptorUnitConnPath                                          CfprEquipmentConnectionStatus,
    cfprAdaptorUnitConnStatus                                        CfprEquipmentConnectionStatus,
    cfprAdaptorUnitFltAggr                                           Unsigned64,
    cfprAdaptorUnitId                                                CfprAdaptorUnitId,
    cfprAdaptorUnitIntegrated                                        TruthValue,
    cfprAdaptorUnitLocationDn                                        SnmpAdminString,
    cfprAdaptorUnitManagingInst                                      CfprNetworkSwitchId,
    cfprAdaptorUnitMfgTime                                           DateAndTime,
    cfprAdaptorUnitModel                                             SnmpAdminString,
    cfprAdaptorUnitOperQualifierReason                               SnmpAdminString,
    cfprAdaptorUnitOperState                                         CfprEquipmentOperability,
    cfprAdaptorUnitOperability                                       CfprEquipmentOperability,
    cfprAdaptorUnitPartNumber                                        SnmpAdminString,
    cfprAdaptorUnitPciAddr                                           SnmpAdminString,
    cfprAdaptorUnitPciSlot                                           SnmpAdminString,
    cfprAdaptorUnitPerf                                              CfprEquipmentSensorThresholdStatus,
    cfprAdaptorUnitPower                                             CfprEquipmentPowerState,
    cfprAdaptorUnitPresence                                          CfprEquipmentPresence,
    cfprAdaptorUnitReachability                                      CfprAdaptorReachability,
    cfprAdaptorUnitRevision                                          SnmpAdminString,
    cfprAdaptorUnitSerial                                            SnmpAdminString,
    cfprAdaptorUnitThermal                                           CfprEquipmentSensorThresholdStatus,
    cfprAdaptorUnitVendor                                            SnmpAdminString,
    cfprAdaptorUnitVoltage                                           CfprEquipmentSensorThresholdStatus
}

cfprAdaptorUnitInstanceId OBJECT-TYPE
    SYNTAX       CfprManagedObjectId
    MAX-ACCESS   not-accessible
    STATUS       current
    DESCRIPTION
        "Instance identifier of the managed object."
    ::= { cfprAdaptorUnitEntry 1 }

cfprAdaptorUnitDn OBJECT-TYPE
    SYNTAX       CfprManagedObjectDn
    MAX-ACCESS   read-only
    STATUS       current
    DESCRIPTION
        "Cisco Firepower adaptor:Unit:dn managed object property"
    ::= { cfprAdaptorUnitEntry 2 }

cfprAdaptorUnitRn OBJECT-TYPE
    SYNTAX       SnmpAdminString
    MAX-ACCESS   read-only
    STATUS       current
    DESCRIPTION
        "Cisco Firepower adaptor:Unit:rn managed object property"
    ::= { cfprAdaptorUnitEntry 3 }

cfprAdaptorUnitAdminPowerState OBJECT-TYPE
    SYNTAX       CfprAdaptorAdminPowerState
    MAX-ACCESS   read-only
    STATUS       current
    DESCRIPTION
        "Cisco Firepower adaptor:Unit:adminPowerState managed
        object property"
    ::= { cfprAdaptorUnitEntry 4 }

cfprAdaptorUnitBaseMac OBJECT-TYPE
    SYNTAX       MacAddress
    MAX-ACCESS   read-only
    STATUS       current
    DESCRIPTION
        "Cisco Firepower adaptor:Unit:baseMac managed object property"
    ::= { cfprAdaptorUnitEntry 5 }

cfprAdaptorUnitBladeId OBJECT-TYPE
    SYNTAX       Gauge32
    MAX-ACCESS   read-only
    STATUS       current
    DESCRIPTION
        "Cisco Firepower adaptor:Unit:bladeId managed object property"
    ::= { cfprAdaptorUnitEntry 6 }

cfprAdaptorUnitChassisId OBJECT-TYPE
    SYNTAX       Gauge32
    MAX-ACCESS   read-only
    STATUS       current
    DESCRIPTION
        "Cisco Firepower adaptor:Unit:chassisId managed object property"
    ::= { cfprAdaptorUnitEntry 7 }

cfprAdaptorUnitConnPath OBJECT-TYPE
    SYNTAX       CfprEquipmentConnectionStatus
    MAX-ACCESS   read-only
    STATUS       current
    DESCRIPTION
        "Cisco Firepower adaptor:Unit:connPath managed object property"
    ::= { cfprAdaptorUnitEntry 8 }

cfprAdaptorUnitConnStatus OBJECT-TYPE
    SYNTAX       CfprEquipmentConnectionStatus
    MAX-ACCESS   read-only
    STATUS       current
    DESCRIPTION
        "Cisco Firepower adaptor:Unit:connStatus managed object property"
    ::= { cfprAdaptorUnitEntry 9 }

cfprAdaptorUnitFltAggr OBJECT-TYPE
    SYNTAX       Unsigned64
    MAX-ACCESS   read-only
    STATUS       current
    DESCRIPTION
        "Cisco Firepower adaptor:Unit:fltAggr managed object property"
    ::= { cfprAdaptorUnitEntry 10 }

cfprAdaptorUnitId OBJECT-TYPE
    SYNTAX       CfprAdaptorUnitId
    MAX-ACCESS   read-only
    STATUS       current
    DESCRIPTION
        "Cisco Firepower adaptor:Unit:id managed object property"
    ::= { cfprAdaptorUnitEntry 11 }

cfprAdaptorUnitIntegrated OBJECT-TYPE
    SYNTAX       TruthValue
    MAX-ACCESS   read-only
    STATUS       current
    DESCRIPTION
        "Cisco Firepower adaptor:Unit:integrated managed object property"
    ::= { cfprAdaptorUnitEntry 12 }

cfprAdaptorUnitLocationDn OBJECT-TYPE
    SYNTAX       SnmpAdminString
    MAX-ACCESS   read-only
    STATUS       current
    DESCRIPTION
        "Cisco Firepower adaptor:Unit:locationDn managed object property"
    ::= { cfprAdaptorUnitEntry 13 }

cfprAdaptorUnitManagingInst OBJECT-TYPE
    SYNTAX       CfprNetworkSwitchId
    MAX-ACCESS   read-only
    STATUS       current
    DESCRIPTION
        "Cisco Firepower adaptor:Unit:managingInst managed
        object property"
    ::= { cfprAdaptorUnitEntry 14 }

cfprAdaptorUnitMfgTime OBJECT-TYPE
    SYNTAX       DateAndTime
    MAX-ACCESS   read-only
    STATUS       current
    DESCRIPTION
        "Cisco Firepower adaptor:Unit:mfgTime managed object property"
    ::= { cfprAdaptorUnitEntry 15 }

cfprAdaptorUnitModel OBJECT-TYPE
    SYNTAX       SnmpAdminString
    MAX-ACCESS   read-only
    STATUS       current
    DESCRIPTION
        "Cisco Firepower adaptor:Unit:model managed object property"
    ::= { cfprAdaptorUnitEntry 16 }

cfprAdaptorUnitOperQualifierReason OBJECT-TYPE
    SYNTAX       SnmpAdminString
    MAX-ACCESS   read-only
    STATUS       current
    DESCRIPTION
        "Cisco Firepower adaptor:Unit:operQualifierReason
        managed object property"
    ::= { cfprAdaptorUnitEntry 17 }

cfprAdaptorUnitOperState OBJECT-TYPE
    SYNTAX       CfprEquipmentOperability
    MAX-ACCESS   read-only
    STATUS       current
    DESCRIPTION
        "Cisco Firepower adaptor:Unit:operState managed object property"
    ::= { cfprAdaptorUnitEntry 18 }

cfprAdaptorUnitOperability OBJECT-TYPE
    SYNTAX       CfprEquipmentOperability
    MAX-ACCESS   read-only
    STATUS       current
    DESCRIPTION
        "Cisco Firepower adaptor:Unit:operability managed object property"
    ::= { cfprAdaptorUnitEntry 19 }

cfprAdaptorUnitPartNumber OBJECT-TYPE
    SYNTAX       SnmpAdminString
    MAX-ACCESS   read-only
    STATUS       current
    DESCRIPTION
        "Cisco Firepower adaptor:Unit:partNumber managed object property"
    ::= { cfprAdaptorUnitEntry 20 }

cfprAdaptorUnitPciAddr OBJECT-TYPE
    SYNTAX       SnmpAdminString
    MAX-ACCESS   read-only
    STATUS       current
    DESCRIPTION
        "Cisco Firepower adaptor:Unit:pciAddr managed object property"
    ::= { cfprAdaptorUnitEntry 21 }

cfprAdaptorUnitPciSlot OBJECT-TYPE
    SYNTAX       SnmpAdminString
    MAX-ACCESS   read-only
    STATUS       current
    DESCRIPTION
        "Cisco Firepower adaptor:Unit:pciSlot managed object property"
    ::= { cfprAdaptorUnitEntry 22 }

cfprAdaptorUnitPerf OBJECT-TYPE
    SYNTAX       CfprEquipmentSensorThresholdStatus
    MAX-ACCESS   read-only
    STATUS       current
    DESCRIPTION
        "Cisco Firepower adaptor:Unit:perf managed object property"
    ::= { cfprAdaptorUnitEntry 23 }

cfprAdaptorUnitPower OBJECT-TYPE
    SYNTAX       CfprEquipmentPowerState
    MAX-ACCESS   read-only
    STATUS       current
    DESCRIPTION
        "Cisco Firepower adaptor:Unit:power managed object property"
    ::= { cfprAdaptorUnitEntry 24 }

cfprAdaptorUnitPresence OBJECT-TYPE
    SYNTAX       CfprEquipmentPresence
    MAX-ACCESS   read-only
    STATUS       current
    DESCRIPTION
        "Cisco Firepower adaptor:Unit:presence managed object property"
    ::= { cfprAdaptorUnitEntry 25 }

cfprAdaptorUnitReachability OBJECT-TYPE
    SYNTAX       CfprAdaptorReachability
    MAX-ACCESS   read-only
    STATUS       current
    DESCRIPTION
        "Cisco Firepower adaptor:Unit:reachability managed
        object property"
    ::= { cfprAdaptorUnitEntry 26 }

cfprAdaptorUnitRevision OBJECT-TYPE
    SYNTAX       SnmpAdminString
    MAX-ACCESS   read-only
    STATUS       current
    DESCRIPTION
        "Cisco Firepower adaptor:Unit:revision managed object property"
    ::= { cfprAdaptorUnitEntry 27 }

cfprAdaptorUnitSerial OBJECT-TYPE
    SYNTAX       SnmpAdminString
    MAX-ACCESS   read-only
    STATUS       current
    DESCRIPTION
        "Cisco Firepower adaptor:Unit:serial managed object property"
    ::= { cfprAdaptorUnitEntry 28 }

cfprAdaptorUnitThermal OBJECT-TYPE
    SYNTAX       CfprEquipmentSensorThresholdStatus
    MAX-ACCESS   read-only
    STATUS       current
    DESCRIPTION
        "Cisco Firepower adaptor:Unit:thermal managed object property"
    ::= { cfprAdaptorUnitEntry 29 }

cfprAdaptorUnitVendor OBJECT-TYPE
    SYNTAX       SnmpAdminString
    MAX-ACCESS   read-only
    STATUS       current
    DESCRIPTION
        "Cisco Firepower adaptor:Unit:vendor managed object property"
    ::= { cfprAdaptorUnitEntry 30 }

cfprAdaptorUnitVoltage OBJECT-TYPE
    SYNTAX       CfprEquipmentSensorThresholdStatus
    MAX-ACCESS   read-only
    STATUS       current
    DESCRIPTION
        "Cisco Firepower adaptor:Unit:voltage managed object property"
    ::= { cfprAdaptorUnitEntry 31 }

cfprAdaptorUnitAssocCtxTable OBJECT-TYPE
    SYNTAX           SEQUENCE OF CfprAdaptorUnitAssocCtxEntry
    MAX-ACCESS       not-accessible
    STATUS           current
    DESCRIPTION
        "Cisco Firepower adaptor:UnitAssocCtx managed object table"
    ::= { cfprAdaptorObjects 114 }

cfprAdaptorUnitAssocCtxEntry OBJECT-TYPE
    SYNTAX           CfprAdaptorUnitAssocCtxEntry
    MAX-ACCESS       not-accessible
    STATUS           current
    DESCRIPTION
        "Entry for the cfprAdaptorUnitAssocCtxTable table."
    INDEX { cfprAdaptorUnitAssocCtxInstanceId }
    ::= { cfprAdaptorUnitAssocCtxTable 1 }

CfprAdaptorUnitAssocCtxEntry ::= SEQUENCE {
    cfprAdaptorUnitAssocCtxInstanceId                                CfprManagedObjectId,
    cfprAdaptorUnitAssocCtxDn                                        CfprManagedObjectDn,
    cfprAdaptorUnitAssocCtxRn                                        SnmpAdminString,
    cfprAdaptorUnitAssocCtxFruCapDn                                  SnmpAdminString,
    cfprAdaptorUnitAssocCtxId                                        Gauge32,
    cfprAdaptorUnitAssocCtxPciAddr                                   SnmpAdminString
}

cfprAdaptorUnitAssocCtxInstanceId OBJECT-TYPE
    SYNTAX       CfprManagedObjectId
    MAX-ACCESS   not-accessible
    STATUS       current
    DESCRIPTION
        "Instance identifier of the managed object."
    ::= { cfprAdaptorUnitAssocCtxEntry 1 }

cfprAdaptorUnitAssocCtxDn OBJECT-TYPE
    SYNTAX       CfprManagedObjectDn
    MAX-ACCESS   read-only
    STATUS       current
    DESCRIPTION
        "Cisco Firepower adaptor:UnitAssocCtx:dn managed object property"
    ::= { cfprAdaptorUnitAssocCtxEntry 2 }

cfprAdaptorUnitAssocCtxRn OBJECT-TYPE
    SYNTAX       SnmpAdminString
    MAX-ACCESS   read-only
    STATUS       current
    DESCRIPTION
        "Cisco Firepower adaptor:UnitAssocCtx:rn managed object property"
    ::= { cfprAdaptorUnitAssocCtxEntry 3 }

cfprAdaptorUnitAssocCtxFruCapDn OBJECT-TYPE
    SYNTAX       SnmpAdminString
    MAX-ACCESS   read-only
    STATUS       current
    DESCRIPTION
        "Cisco Firepower adaptor:UnitAssocCtx:fruCapDn
        managed object property"
    ::= { cfprAdaptorUnitAssocCtxEntry 4 }

cfprAdaptorUnitAssocCtxId OBJECT-TYPE
    SYNTAX       Gauge32
    MAX-ACCESS   read-only
    STATUS       current
    DESCRIPTION
        "Cisco Firepower adaptor:UnitAssocCtx:id managed object property"
    ::= { cfprAdaptorUnitAssocCtxEntry 5 }

cfprAdaptorUnitAssocCtxPciAddr OBJECT-TYPE
    SYNTAX       SnmpAdminString
    MAX-ACCESS   read-only
    STATUS       current
    DESCRIPTION
        "Cisco Firepower adaptor:UnitAssocCtx:pciAddr managed
        object property"
    ::= { cfprAdaptorUnitAssocCtxEntry 6 }

cfprAdaptorUnitExtnTable OBJECT-TYPE
    SYNTAX           SEQUENCE OF CfprAdaptorUnitExtnEntry
    MAX-ACCESS       not-accessible
    STATUS           current
    DESCRIPTION
        "Cisco Firepower adaptor:UnitExtn managed object table"
    ::= { cfprAdaptorObjects 115 }

cfprAdaptorUnitExtnEntry OBJECT-TYPE
    SYNTAX           CfprAdaptorUnitExtnEntry
    MAX-ACCESS       not-accessible
    STATUS           current
    DESCRIPTION
        "Entry for the cfprAdaptorUnitExtnTable table."
    INDEX { cfprAdaptorUnitExtnInstanceId }
    ::= { cfprAdaptorUnitExtnTable 1 }

CfprAdaptorUnitExtnEntry ::= SEQUENCE {
    cfprAdaptorUnitExtnInstanceId                                    CfprManagedObjectId,
    cfprAdaptorUnitExtnDn                                            CfprManagedObjectDn,
    cfprAdaptorUnitExtnRn                                            SnmpAdminString,
    cfprAdaptorUnitExtnAdaptorId                                     Gauge32,
    cfprAdaptorUnitExtnBladeId                                       Gauge32,
    cfprAdaptorUnitExtnChassisId                                     Gauge32,
    cfprAdaptorUnitExtnFltAggr                                       Unsigned64,
    cfprAdaptorUnitExtnId                                            CfprAdaptorUnitExtnId,
    cfprAdaptorUnitExtnLocationDn                                    SnmpAdminString,
    cfprAdaptorUnitExtnModel                                         SnmpAdminString,
    cfprAdaptorUnitExtnOperQualifierReason                           SnmpAdminString,
    cfprAdaptorUnitExtnOperState                                     CfprEquipmentOperability,
    cfprAdaptorUnitExtnOperability                                   CfprEquipmentOperability,
    cfprAdaptorUnitExtnPartNumber                                    SnmpAdminString,
    cfprAdaptorUnitExtnPerf                                          CfprEquipmentSensorThresholdStatus,
    cfprAdaptorUnitExtnPower                                         CfprEquipmentPowerState,
    cfprAdaptorUnitExtnPresence                                      CfprEquipmentPresence,
    cfprAdaptorUnitExtnRevision                                      SnmpAdminString,
    cfprAdaptorUnitExtnSerial                                        SnmpAdminString,
    cfprAdaptorUnitExtnThermal                                       CfprEquipmentSensorThresholdStatus,
    cfprAdaptorUnitExtnVendor                                        SnmpAdminString,
    cfprAdaptorUnitExtnVoltage                                       CfprEquipmentSensorThresholdStatus
}

cfprAdaptorUnitExtnInstanceId OBJECT-TYPE
    SYNTAX       CfprManagedObjectId
    MAX-ACCESS   not-accessible
    STATUS       current
    DESCRIPTION
        "Instance identifier of the managed object."
    ::= { cfprAdaptorUnitExtnEntry 1 }

cfprAdaptorUnitExtnDn OBJECT-TYPE
    SYNTAX       CfprManagedObjectDn
    MAX-ACCESS   read-only
    STATUS       current
    DESCRIPTION
        "Cisco Firepower adaptor:UnitExtn:dn managed object property"
    ::= { cfprAdaptorUnitExtnEntry 2 }

cfprAdaptorUnitExtnRn OBJECT-TYPE
    SYNTAX       SnmpAdminString
    MAX-ACCESS   read-only
    STATUS       current
    DESCRIPTION
        "Cisco Firepower adaptor:UnitExtn:rn managed object property"
    ::= { cfprAdaptorUnitExtnEntry 3 }

cfprAdaptorUnitExtnAdaptorId OBJECT-TYPE
    SYNTAX       Gauge32
    MAX-ACCESS   read-only
    STATUS       current
    DESCRIPTION
        "Cisco Firepower adaptor:UnitExtn:adaptorId managed
        object property"
    ::= { cfprAdaptorUnitExtnEntry 4 }

cfprAdaptorUnitExtnBladeId OBJECT-TYPE
    SYNTAX       Gauge32
    MAX-ACCESS   read-only
    STATUS       current
    DESCRIPTION
        "Cisco Firepower adaptor:UnitExtn:bladeId managed object property"
    ::= { cfprAdaptorUnitExtnEntry 5 }

cfprAdaptorUnitExtnChassisId OBJECT-TYPE
    SYNTAX       Gauge32
    MAX-ACCESS   read-only
    STATUS       current
    DESCRIPTION
        "Cisco Firepower adaptor:UnitExtn:chassisId managed
        object property"
    ::= { cfprAdaptorUnitExtnEntry 6 }

cfprAdaptorUnitExtnFltAggr OBJECT-TYPE
    SYNTAX       Unsigned64
    MAX-ACCESS   read-only
    STATUS       current
    DESCRIPTION
        "Cisco Firepower adaptor:UnitExtn:fltAggr managed object property"
    ::= { cfprAdaptorUnitExtnEntry 7 }

cfprAdaptorUnitExtnId OBJECT-TYPE
    SYNTAX       CfprAdaptorUnitExtnId
    MAX-ACCESS   read-only
    STATUS       current
    DESCRIPTION
        "Cisco Firepower adaptor:UnitExtn:id managed object property"
    ::= { cfprAdaptorUnitExtnEntry 8 }

cfprAdaptorUnitExtnLocationDn OBJECT-TYPE
    SYNTAX       SnmpAdminString
    MAX-ACCESS   read-only
    STATUS       current
    DESCRIPTION
        "Cisco Firepower adaptor:UnitExtn:locationDn managed
        object property"
    ::= { cfprAdaptorUnitExtnEntry 9 }

cfprAdaptorUnitExtnModel OBJECT-TYPE
    SYNTAX       SnmpAdminString
    MAX-ACCESS   read-only
    STATUS       current
    DESCRIPTION
        "Cisco Firepower adaptor:UnitExtn:model managed object property"
    ::= { cfprAdaptorUnitExtnEntry 10 }

cfprAdaptorUnitExtnOperQualifierReason OBJECT-TYPE
    SYNTAX       SnmpAdminString
    MAX-ACCESS   read-only
    STATUS       current
    DESCRIPTION
        "Cisco Firepower adaptor:UnitExtn:operQualifierReason
        managed object property"
    ::= { cfprAdaptorUnitExtnEntry 11 }

cfprAdaptorUnitExtnOperState OBJECT-TYPE
    SYNTAX       CfprEquipmentOperability
    MAX-ACCESS   read-only
    STATUS       current
    DESCRIPTION
        "Cisco Firepower adaptor:UnitExtn:operState managed
        object property"
    ::= { cfprAdaptorUnitExtnEntry 12 }

cfprAdaptorUnitExtnOperability OBJECT-TYPE
    SYNTAX       CfprEquipmentOperability
    MAX-ACCESS   read-only
    STATUS       current
    DESCRIPTION
        "Cisco Firepower adaptor:UnitExtn:operability managed
        object property"
    ::= { cfprAdaptorUnitExtnEntry 13 }

cfprAdaptorUnitExtnPartNumber OBJECT-TYPE
    SYNTAX       SnmpAdminString
    MAX-ACCESS   read-only
    STATUS       current
    DESCRIPTION
        "Cisco Firepower adaptor:UnitExtn:partNumber managed
        object property"
    ::= { cfprAdaptorUnitExtnEntry 14 }

cfprAdaptorUnitExtnPerf OBJECT-TYPE
    SYNTAX       CfprEquipmentSensorThresholdStatus
    MAX-ACCESS   read-only
    STATUS       current
    DESCRIPTION
        "Cisco Firepower adaptor:UnitExtn:perf managed object property"
    ::= { cfprAdaptorUnitExtnEntry 15 }

cfprAdaptorUnitExtnPower OBJECT-TYPE
    SYNTAX       CfprEquipmentPowerState
    MAX-ACCESS   read-only
    STATUS       current
    DESCRIPTION
        "Cisco Firepower adaptor:UnitExtn:power managed object property"
    ::= { cfprAdaptorUnitExtnEntry 16 }

cfprAdaptorUnitExtnPresence OBJECT-TYPE
    SYNTAX       CfprEquipmentPresence
    MAX-ACCESS   read-only
    STATUS       current
    DESCRIPTION
        "Cisco Firepower adaptor:UnitExtn:presence managed
        object property"
    ::= { cfprAdaptorUnitExtnEntry 17 }

cfprAdaptorUnitExtnRevision OBJECT-TYPE
    SYNTAX       SnmpAdminString
    MAX-ACCESS   read-only
    STATUS       current
    DESCRIPTION
        "Cisco Firepower adaptor:UnitExtn:revision managed
        object property"
    ::= { cfprAdaptorUnitExtnEntry 18 }

cfprAdaptorUnitExtnSerial OBJECT-TYPE
    SYNTAX       SnmpAdminString
    MAX-ACCESS   read-only
    STATUS       current
    DESCRIPTION
        "Cisco Firepower adaptor:UnitExtn:serial managed object property"
    ::= { cfprAdaptorUnitExtnEntry 19 }

cfprAdaptorUnitExtnThermal OBJECT-TYPE
    SYNTAX       CfprEquipmentSensorThresholdStatus
    MAX-ACCESS   read-only
    STATUS       current
    DESCRIPTION
        "Cisco Firepower adaptor:UnitExtn:thermal managed object property"
    ::= { cfprAdaptorUnitExtnEntry 20 }

cfprAdaptorUnitExtnVendor OBJECT-TYPE
    SYNTAX       SnmpAdminString
    MAX-ACCESS   read-only
    STATUS       current
    DESCRIPTION
        "Cisco Firepower adaptor:UnitExtn:vendor managed object property"
    ::= { cfprAdaptorUnitExtnEntry 21 }

cfprAdaptorUnitExtnVoltage OBJECT-TYPE
    SYNTAX       CfprEquipmentSensorThresholdStatus
    MAX-ACCESS   read-only
    STATUS       current
    DESCRIPTION
        "Cisco Firepower adaptor:UnitExtn:voltage managed object property"
    ::= { cfprAdaptorUnitExtnEntry 22 }

cfprAdaptorUplinkHwAddrCapTable OBJECT-TYPE
    SYNTAX           SEQUENCE OF CfprAdaptorUplinkHwAddrCapEntry
    MAX-ACCESS       not-accessible
    STATUS           current
    DESCRIPTION
        "Cisco Firepower adaptor:UplinkHwAddrCap managed object table"
    ::= { cfprAdaptorObjects 116 }

cfprAdaptorUplinkHwAddrCapEntry OBJECT-TYPE
    SYNTAX           CfprAdaptorUplinkHwAddrCapEntry
    MAX-ACCESS       not-accessible
    STATUS           current
    DESCRIPTION
        "Entry for the cfprAdaptorUplinkHwAddrCapTable table."
    INDEX { cfprAdaptorUplinkHwAddrCapInstanceId }
    ::= { cfprAdaptorUplinkHwAddrCapTable 1 }

CfprAdaptorUplinkHwAddrCapEntry ::= SEQUENCE {
    cfprAdaptorUplinkHwAddrCapInstanceId                             CfprManagedObjectId,
    cfprAdaptorUplinkHwAddrCapDn                                     CfprManagedObjectDn,
    cfprAdaptorUplinkHwAddrCapRn                                     SnmpAdminString,
    cfprAdaptorUplinkHwAddrCapLldpMacOffset1                         Gauge32,
    cfprAdaptorUplinkHwAddrCapLldpMacOffset2                         Gauge32,
    cfprAdaptorUplinkHwAddrCapMacOffset1                             Gauge32,
    cfprAdaptorUplinkHwAddrCapMacOffset2                             Gauge32,
    cfprAdaptorUplinkHwAddrCapMacOffsetSub00                         Gauge32,
    cfprAdaptorUplinkHwAddrCapMacOffsetSub01                         Gauge32,
    cfprAdaptorUplinkHwAddrCapMacOffsetSub02                         Gauge32,
    cfprAdaptorUplinkHwAddrCapMacOffsetSub03                         Gauge32,
    cfprAdaptorUplinkHwAddrCapMacOffsetSub10                         Gauge32,
    cfprAdaptorUplinkHwAddrCapMacOffsetSub11                         Gauge32,
    cfprAdaptorUplinkHwAddrCapMacOffsetSub12                         Gauge32,
    cfprAdaptorUplinkHwAddrCapMacOffsetSub13                         Gauge32
}

cfprAdaptorUplinkHwAddrCapInstanceId OBJECT-TYPE
    SYNTAX       CfprManagedObjectId
    MAX-ACCESS   not-accessible
    STATUS       current
    DESCRIPTION
        "Instance identifier of the managed object."
    ::= { cfprAdaptorUplinkHwAddrCapEntry 1 }

cfprAdaptorUplinkHwAddrCapDn OBJECT-TYPE
    SYNTAX       CfprManagedObjectDn
    MAX-ACCESS   read-only
    STATUS       current
    DESCRIPTION
        "Cisco Firepower adaptor:UplinkHwAddrCap:dn managed
        object property"
    ::= { cfprAdaptorUplinkHwAddrCapEntry 2 }

cfprAdaptorUplinkHwAddrCapRn OBJECT-TYPE
    SYNTAX       SnmpAdminString
    MAX-ACCESS   read-only
    STATUS       current
    DESCRIPTION
        "Cisco Firepower adaptor:UplinkHwAddrCap:rn managed
        object property"
    ::= { cfprAdaptorUplinkHwAddrCapEntry 3 }

cfprAdaptorUplinkHwAddrCapLldpMacOffset1 OBJECT-TYPE
    SYNTAX       Gauge32
    MAX-ACCESS   read-only
    STATUS       current
    DESCRIPTION
        "Cisco Firepower adaptor:UplinkHwAddrCap:lldpMacOffset1
        managed object property"
    ::= { cfprAdaptorUplinkHwAddrCapEntry 4 }

cfprAdaptorUplinkHwAddrCapLldpMacOffset2 OBJECT-TYPE
    SYNTAX       Gauge32
    MAX-ACCESS   read-only
    STATUS       current
    DESCRIPTION
        "Cisco Firepower adaptor:UplinkHwAddrCap:lldpMacOffset2
        managed object property"
    ::= { cfprAdaptorUplinkHwAddrCapEntry 5 }

cfprAdaptorUplinkHwAddrCapMacOffset1 OBJECT-TYPE
    SYNTAX       Gauge32
    MAX-ACCESS   read-only
    STATUS       current
    DESCRIPTION
        "Cisco Firepower adaptor:UplinkHwAddrCap:macOffset1
        managed object property"
    ::= { cfprAdaptorUplinkHwAddrCapEntry 6 }

cfprAdaptorUplinkHwAddrCapMacOffset2 OBJECT-TYPE
    SYNTAX       Gauge32
    MAX-ACCESS   read-only
    STATUS       current
    DESCRIPTION
        "Cisco Firepower adaptor:UplinkHwAddrCap:macOffset2
        managed object property"
    ::= { cfprAdaptorUplinkHwAddrCapEntry 7 }

cfprAdaptorUplinkHwAddrCapMacOffsetSub00 OBJECT-TYPE
    SYNTAX       Gauge32
    MAX-ACCESS   read-only
    STATUS       current
    DESCRIPTION
        "Cisco Firepower adaptor:UplinkHwAddrCap:macOffsetSub00
        managed object property"
    ::= { cfprAdaptorUplinkHwAddrCapEntry 8 }

cfprAdaptorUplinkHwAddrCapMacOffsetSub01 OBJECT-TYPE
    SYNTAX       Gauge32
    MAX-ACCESS   read-only
    STATUS       current
    DESCRIPTION
        "Cisco Firepower adaptor:UplinkHwAddrCap:macOffsetSub01
        managed object property"
    ::= { cfprAdaptorUplinkHwAddrCapEntry 9 }

cfprAdaptorUplinkHwAddrCapMacOffsetSub02 OBJECT-TYPE
    SYNTAX       Gauge32
    MAX-ACCESS   read-only
    STATUS       current
    DESCRIPTION
        "Cisco Firepower adaptor:UplinkHwAddrCap:macOffsetSub02
        managed object property"
    ::= { cfprAdaptorUplinkHwAddrCapEntry 10 }

cfprAdaptorUplinkHwAddrCapMacOffsetSub03 OBJECT-TYPE
    SYNTAX       Gauge32
    MAX-ACCESS   read-only
    STATUS       current
    DESCRIPTION
        "Cisco Firepower adaptor:UplinkHwAddrCap:macOffsetSub03
        managed object property"
    ::= { cfprAdaptorUplinkHwAddrCapEntry 11 }

cfprAdaptorUplinkHwAddrCapMacOffsetSub10 OBJECT-TYPE
    SYNTAX       Gauge32
    MAX-ACCESS   read-only
    STATUS       current
    DESCRIPTION
        "Cisco Firepower adaptor:UplinkHwAddrCap:macOffsetSub10
        managed object property"
    ::= { cfprAdaptorUplinkHwAddrCapEntry 12 }

cfprAdaptorUplinkHwAddrCapMacOffsetSub11 OBJECT-TYPE
    SYNTAX       Gauge32
    MAX-ACCESS   read-only
    STATUS       current
    DESCRIPTION
        "Cisco Firepower adaptor:UplinkHwAddrCap:macOffsetSub11
        managed object property"
    ::= { cfprAdaptorUplinkHwAddrCapEntry 13 }

cfprAdaptorUplinkHwAddrCapMacOffsetSub12 OBJECT-TYPE
    SYNTAX       Gauge32
    MAX-ACCESS   read-only
    STATUS       current
    DESCRIPTION
        "Cisco Firepower adaptor:UplinkHwAddrCap:macOffsetSub12
        managed object property"
    ::= { cfprAdaptorUplinkHwAddrCapEntry 14 }

cfprAdaptorUplinkHwAddrCapMacOffsetSub13 OBJECT-TYPE
    SYNTAX       Gauge32
    MAX-ACCESS   read-only
    STATUS       current
    DESCRIPTION
        "Cisco Firepower adaptor:UplinkHwAddrCap:macOffsetSub13
        managed object property"
    ::= { cfprAdaptorUplinkHwAddrCapEntry 15 }

cfprAdaptorUsnicConnDefTable OBJECT-TYPE
    SYNTAX           SEQUENCE OF CfprAdaptorUsnicConnDefEntry
    MAX-ACCESS       not-accessible
    STATUS           current
    DESCRIPTION
        "Cisco Firepower adaptor:UsnicConnDef managed object table"
    ::= { cfprAdaptorObjects 117 }

cfprAdaptorUsnicConnDefEntry OBJECT-TYPE
    SYNTAX           CfprAdaptorUsnicConnDefEntry
    MAX-ACCESS       not-accessible
    STATUS           current
    DESCRIPTION
        "Entry for the cfprAdaptorUsnicConnDefTable table."
    INDEX { cfprAdaptorUsnicConnDefInstanceId }
    ::= { cfprAdaptorUsnicConnDefTable 1 }

CfprAdaptorUsnicConnDefEntry ::= SEQUENCE {
    cfprAdaptorUsnicConnDefInstanceId                                CfprManagedObjectId,
    cfprAdaptorUsnicConnDefDn                                        CfprManagedObjectDn,
    cfprAdaptorUsnicConnDefRn                                        SnmpAdminString,
    cfprAdaptorUsnicConnDefConPolicyName                             SnmpAdminString,
    cfprAdaptorUsnicConnDefUsnicCount                                Gauge32
}

cfprAdaptorUsnicConnDefInstanceId OBJECT-TYPE
    SYNTAX       CfprManagedObjectId
    MAX-ACCESS   not-accessible
    STATUS       current
    DESCRIPTION
        "Instance identifier of the managed object."
    ::= { cfprAdaptorUsnicConnDefEntry 1 }

cfprAdaptorUsnicConnDefDn OBJECT-TYPE
    SYNTAX       CfprManagedObjectDn
    MAX-ACCESS   read-only
    STATUS       current
    DESCRIPTION
        "Cisco Firepower adaptor:UsnicConnDef:dn managed object property"
    ::= { cfprAdaptorUsnicConnDefEntry 2 }

cfprAdaptorUsnicConnDefRn OBJECT-TYPE
    SYNTAX       SnmpAdminString
    MAX-ACCESS   read-only
    STATUS       current
    DESCRIPTION
        "Cisco Firepower adaptor:UsnicConnDef:rn managed object property"
    ::= { cfprAdaptorUsnicConnDefEntry 3 }

cfprAdaptorUsnicConnDefConPolicyName OBJECT-TYPE
    SYNTAX       SnmpAdminString
    MAX-ACCESS   read-only
    STATUS       current
    DESCRIPTION
        "Cisco Firepower adaptor:UsnicConnDef:conPolicyName
        managed object property"
    ::= { cfprAdaptorUsnicConnDefEntry 4 }

cfprAdaptorUsnicConnDefUsnicCount OBJECT-TYPE
    SYNTAX       Gauge32
    MAX-ACCESS   read-only
    STATUS       current
    DESCRIPTION
        "Cisco Firepower adaptor:UsnicConnDef:usnicCount
        managed object property"
    ::= { cfprAdaptorUsnicConnDefEntry 5 }

cfprAdaptorVlanTable OBJECT-TYPE
    SYNTAX           SEQUENCE OF CfprAdaptorVlanEntry
    MAX-ACCESS       not-accessible
    STATUS           current
    DESCRIPTION
        "Cisco Firepower adaptor:Vlan managed object table"
    ::= { cfprAdaptorObjects 118 }

cfprAdaptorVlanEntry OBJECT-TYPE
    SYNTAX           CfprAdaptorVlanEntry
    MAX-ACCESS       not-accessible
    STATUS           current
    DESCRIPTION
        "Entry for the cfprAdaptorVlanTable table."
    INDEX { cfprAdaptorVlanInstanceId }
    ::= { cfprAdaptorVlanTable 1 }

CfprAdaptorVlanEntry ::= SEQUENCE {
    cfprAdaptorVlanInstanceId                                        CfprManagedObjectId,
    cfprAdaptorVlanDn                                                CfprManagedObjectDn,
    cfprAdaptorVlanRn                                                SnmpAdminString,
    cfprAdaptorVlanAssocPrimaryVlanState                             CfprFabricVlanAssocPrimaryVlanState,
    cfprAdaptorVlanAssocPrimaryVlanSwitchId                          CfprFabricAVlanAssocPrimaryVlanSwitchId,
    cfprAdaptorVlanEpDn                                              SnmpAdminString,
    cfprAdaptorVlanId                                                Gauge32,
    cfprAdaptorVlanIfRole                                            CfprFabricVnetEpIfRole,
    cfprAdaptorVlanIfType                                            CfprNetworkVnetEpIfType,
    cfprAdaptorVlanLc                                                CfprFsmLifecycle,
    cfprAdaptorVlanLocale                                            CfprFabricVnetEpLocale,
    cfprAdaptorVlanName                                              SnmpAdminString,
    cfprAdaptorVlanOperState                                         CfprFabricVlanOperState,
    cfprAdaptorVlanOverlapStateForA                                  CfprFabricVlanOverlapState,
    cfprAdaptorVlanOverlapStateForB                                  CfprFabricVlanOverlapState,
    cfprAdaptorVlanPeerDn                                            SnmpAdminString,
    cfprAdaptorVlanPolicyOwner                                       CfprFabricVnetEpPolicyOwner,
    cfprAdaptorVlanPubNwDn                                           SnmpAdminString,
    cfprAdaptorVlanPubNwId                                           Gauge32,
    cfprAdaptorVlanPubNwName                                         SnmpAdminString,
    cfprAdaptorVlanSharing                                           CfprFabricAVlanSharing,
    cfprAdaptorVlanSwitchId                                          CfprNetworkSwitchId,
    cfprAdaptorVlanTransport                                         CfprFabricAVlanTransport,
    cfprAdaptorVlanType                                              CfprFabricAVlanType,
    cfprAdaptorVlanVlanType                                          CfprFabricEpVlanVlanType
}

cfprAdaptorVlanInstanceId OBJECT-TYPE
    SYNTAX       CfprManagedObjectId
    MAX-ACCESS   not-accessible
    STATUS       current
    DESCRIPTION
        "Instance identifier of the managed object."
    ::= { cfprAdaptorVlanEntry 1 }

cfprAdaptorVlanDn OBJECT-TYPE
    SYNTAX       CfprManagedObjectDn
    MAX-ACCESS   read-only
    STATUS       current
    DESCRIPTION
        "Cisco Firepower adaptor:Vlan:dn managed object property"
    ::= { cfprAdaptorVlanEntry 2 }

cfprAdaptorVlanRn OBJECT-TYPE
    SYNTAX       SnmpAdminString
    MAX-ACCESS   read-only
    STATUS       current
    DESCRIPTION
        "Cisco Firepower adaptor:Vlan:rn managed object property"
    ::= { cfprAdaptorVlanEntry 3 }

cfprAdaptorVlanAssocPrimaryVlanState OBJECT-TYPE
    SYNTAX       CfprFabricVlanAssocPrimaryVlanState
    MAX-ACCESS   read-only
    STATUS       current
    DESCRIPTION
        "Cisco Firepower adaptor:Vlan:assocPrimaryVlanState
        managed object property"
    ::= { cfprAdaptorVlanEntry 4 }

cfprAdaptorVlanAssocPrimaryVlanSwitchId OBJECT-TYPE
    SYNTAX       CfprFabricAVlanAssocPrimaryVlanSwitchId
    MAX-ACCESS   read-only
    STATUS       current
    DESCRIPTION
        "Cisco Firepower adaptor:Vlan:assocPrimaryVlanSwitchId
        managed object property"
    ::= { cfprAdaptorVlanEntry 5 }

cfprAdaptorVlanEpDn OBJECT-TYPE
    SYNTAX       SnmpAdminString
    MAX-ACCESS   read-only
    STATUS       current
    DESCRIPTION
        "Cisco Firepower adaptor:Vlan:epDn managed object property"
    ::= { cfprAdaptorVlanEntry 6 }

cfprAdaptorVlanId OBJECT-TYPE
    SYNTAX       Gauge32
    MAX-ACCESS   read-only
    STATUS       current
    DESCRIPTION
        "Cisco Firepower adaptor:Vlan:id managed object property"
    ::= { cfprAdaptorVlanEntry 7 }

cfprAdaptorVlanIfRole OBJECT-TYPE
    SYNTAX       CfprFabricVnetEpIfRole
    MAX-ACCESS   read-only
    STATUS       current
    DESCRIPTION
        "Cisco Firepower adaptor:Vlan:ifRole managed object property"
    ::= { cfprAdaptorVlanEntry 8 }

cfprAdaptorVlanIfType OBJECT-TYPE
    SYNTAX       CfprNetworkVnetEpIfType
    MAX-ACCESS   read-only
    STATUS       current
    DESCRIPTION
        "Cisco Firepower adaptor:Vlan:ifType managed object property"
    ::= { cfprAdaptorVlanEntry 9 }

cfprAdaptorVlanLc OBJECT-TYPE
    SYNTAX       CfprFsmLifecycle
    MAX-ACCESS   read-only
    STATUS       current
    DESCRIPTION
        "Cisco Firepower adaptor:Vlan:lc managed object property"
    ::= { cfprAdaptorVlanEntry 10 }

cfprAdaptorVlanLocale OBJECT-TYPE
    SYNTAX       CfprFabricVnetEpLocale
    MAX-ACCESS   read-only
    STATUS       current
    DESCRIPTION
        "Cisco Firepower adaptor:Vlan:locale managed object property"
    ::= { cfprAdaptorVlanEntry 11 }

cfprAdaptorVlanName OBJECT-TYPE
    SYNTAX       SnmpAdminString
    MAX-ACCESS   read-only
    STATUS       current
    DESCRIPTION
        "Cisco Firepower adaptor:Vlan:name managed object property"
    ::= { cfprAdaptorVlanEntry 12 }

cfprAdaptorVlanOperState OBJECT-TYPE
    SYNTAX       CfprFabricVlanOperState
    MAX-ACCESS   read-only
    STATUS       current
    DESCRIPTION
        "Cisco Firepower adaptor:Vlan:operState managed object property"
    ::= { cfprAdaptorVlanEntry 13 }

cfprAdaptorVlanOverlapStateForA OBJECT-TYPE
    SYNTAX       CfprFabricVlanOverlapState
    MAX-ACCESS   read-only
    STATUS       current
    DESCRIPTION
        "Cisco Firepower adaptor:Vlan:overlapStateForA
        managed object property"
    ::= { cfprAdaptorVlanEntry 14 }

cfprAdaptorVlanOverlapStateForB OBJECT-TYPE
    SYNTAX       CfprFabricVlanOverlapState
    MAX-ACCESS   read-only
    STATUS       current
    DESCRIPTION
        "Cisco Firepower adaptor:Vlan:overlapStateForB
        managed object property"
    ::= { cfprAdaptorVlanEntry 15 }

cfprAdaptorVlanPeerDn OBJECT-TYPE
    SYNTAX       SnmpAdminString
    MAX-ACCESS   read-only
    STATUS       current
    DESCRIPTION
        "Cisco Firepower adaptor:Vlan:peerDn managed object property"
    ::= { cfprAdaptorVlanEntry 16 }

cfprAdaptorVlanPolicyOwner OBJECT-TYPE
    SYNTAX       CfprFabricVnetEpPolicyOwner
    MAX-ACCESS   read-only
    STATUS       current
    DESCRIPTION
        "Cisco Firepower adaptor:Vlan:policyOwner managed object property"
    ::= { cfprAdaptorVlanEntry 17 }

cfprAdaptorVlanPubNwDn OBJECT-TYPE
    SYNTAX       SnmpAdminString
    MAX-ACCESS   read-only
    STATUS       current
    DESCRIPTION
        "Cisco Firepower adaptor:Vlan:pubNwDn managed object property"
    ::= { cfprAdaptorVlanEntry 18 }

cfprAdaptorVlanPubNwId OBJECT-TYPE
    SYNTAX       Gauge32
    MAX-ACCESS   read-only
    STATUS       current
    DESCRIPTION
        "Cisco Firepower adaptor:Vlan:pubNwId managed object property"
    ::= { cfprAdaptorVlanEntry 19 }

cfprAdaptorVlanPubNwName OBJECT-TYPE
    SYNTAX       SnmpAdminString
    MAX-ACCESS   read-only
    STATUS       current
    DESCRIPTION
        "Cisco Firepower adaptor:Vlan:pubNwName managed object property"
    ::= { cfprAdaptorVlanEntry 20 }

cfprAdaptorVlanSharing OBJECT-TYPE
    SYNTAX       CfprFabricAVlanSharing
    MAX-ACCESS   read-only
    STATUS       current
    DESCRIPTION
        "Cisco Firepower adaptor:Vlan:sharing managed object property"
    ::= { cfprAdaptorVlanEntry 21 }

cfprAdaptorVlanSwitchId OBJECT-TYPE
    SYNTAX       CfprNetworkSwitchId
    MAX-ACCESS   read-only
    STATUS       current
    DESCRIPTION
        "Cisco Firepower adaptor:Vlan:switchId managed object property"
    ::= { cfprAdaptorVlanEntry 22 }

cfprAdaptorVlanTransport OBJECT-TYPE
    SYNTAX       CfprFabricAVlanTransport
    MAX-ACCESS   read-only
    STATUS       current
    DESCRIPTION
        "Cisco Firepower adaptor:Vlan:transport managed object property"
    ::= { cfprAdaptorVlanEntry 23 }

cfprAdaptorVlanType OBJECT-TYPE
    SYNTAX       CfprFabricAVlanType
    MAX-ACCESS   read-only
    STATUS       current
    DESCRIPTION
        "Cisco Firepower adaptor:Vlan:type managed object property"
    ::= { cfprAdaptorVlanEntry 24 }

cfprAdaptorVlanVlanType OBJECT-TYPE
    SYNTAX       CfprFabricEpVlanVlanType
    MAX-ACCESS   read-only
    STATUS       current
    DESCRIPTION
        "Cisco Firepower adaptor:Vlan:vlanType managed object property"
    ::= { cfprAdaptorVlanEntry 25 }

cfprAdaptorVnicStatsTable OBJECT-TYPE
    SYNTAX           SEQUENCE OF CfprAdaptorVnicStatsEntry
    MAX-ACCESS       not-accessible
    STATUS           current
    DESCRIPTION
        "Cisco Firepower adaptor:VnicStats managed object table"
    ::= { cfprAdaptorObjects 119 }

cfprAdaptorVnicStatsEntry OBJECT-TYPE
    SYNTAX           CfprAdaptorVnicStatsEntry
    MAX-ACCESS       not-accessible
    STATUS           current
    DESCRIPTION
        "Entry for the cfprAdaptorVnicStatsTable table."
    INDEX { cfprAdaptorVnicStatsInstanceId }
    ::= { cfprAdaptorVnicStatsTable 1 }

CfprAdaptorVnicStatsEntry ::= SEQUENCE {
    cfprAdaptorVnicStatsInstanceId                                   CfprManagedObjectId,
    cfprAdaptorVnicStatsDn                                           CfprManagedObjectDn,
    cfprAdaptorVnicStatsRn                                           SnmpAdminString,
    cfprAdaptorVnicStatsBytesRx                                      Unsigned64,
    cfprAdaptorVnicStatsBytesRxDelta                                 Counter64,
    cfprAdaptorVnicStatsBytesRxDeltaAvg                              Unsigned64,
    cfprAdaptorVnicStatsBytesRxDeltaMax                              Unsigned64,
    cfprAdaptorVnicStatsBytesRxDeltaMin                              Unsigned64,
    cfprAdaptorVnicStatsBytesTx                                      Unsigned64,
    cfprAdaptorVnicStatsBytesTxDelta                                 Counter64,
    cfprAdaptorVnicStatsBytesTxDeltaAvg                              Unsigned64,
    cfprAdaptorVnicStatsBytesTxDeltaMax                              Unsigned64,
    cfprAdaptorVnicStatsBytesTxDeltaMin                              Unsigned64,
    cfprAdaptorVnicStatsDroppedRx                                    Unsigned64,
    cfprAdaptorVnicStatsDroppedRxDelta                               Counter64,
    cfprAdaptorVnicStatsDroppedRxDeltaAvg                            Unsigned64,
    cfprAdaptorVnicStatsDroppedRxDeltaMax                            Unsigned64,
    cfprAdaptorVnicStatsDroppedRxDeltaMin                            Unsigned64,
    cfprAdaptorVnicStatsDroppedTx                                    Unsigned64,
    cfprAdaptorVnicStatsDroppedTxDelta                               Counter64,
    cfprAdaptorVnicStatsDroppedTxDeltaAvg                            Unsigned64,
    cfprAdaptorVnicStatsDroppedTxDeltaMax                            Unsigned64,
    cfprAdaptorVnicStatsDroppedTxDeltaMin                            Unsigned64,
    cfprAdaptorVnicStatsErrorsRx                                     Unsigned64,
    cfprAdaptorVnicStatsErrorsRxDelta                                Counter64,
    cfprAdaptorVnicStatsErrorsRxDeltaAvg                             Unsigned64,
    cfprAdaptorVnicStatsErrorsRxDeltaMax                             Unsigned64,
    cfprAdaptorVnicStatsErrorsRxDeltaMin                             Unsigned64,
    cfprAdaptorVnicStatsErrorsTx                                     Unsigned64,
    cfprAdaptorVnicStatsErrorsTxDelta                                Counter64,
    cfprAdaptorVnicStatsErrorsTxDeltaAvg                             Unsigned64,
    cfprAdaptorVnicStatsErrorsTxDeltaMax                             Unsigned64,
    cfprAdaptorVnicStatsErrorsTxDeltaMin                             Unsigned64,
    cfprAdaptorVnicStatsIntervals                                    Gauge32,
    cfprAdaptorVnicStatsPacketsRx                                    Unsigned64,
    cfprAdaptorVnicStatsPacketsRxDelta                               Counter64,
    cfprAdaptorVnicStatsPacketsRxDeltaAvg                            Unsigned64,
    cfprAdaptorVnicStatsPacketsRxDeltaMax                            Unsigned64,
    cfprAdaptorVnicStatsPacketsRxDeltaMin                            Unsigned64,
    cfprAdaptorVnicStatsPacketsTx                                    Unsigned64,
    cfprAdaptorVnicStatsPacketsTxDelta                               Counter64,
    cfprAdaptorVnicStatsPacketsTxDeltaAvg                            Unsigned64,
    cfprAdaptorVnicStatsPacketsTxDeltaMax                            Unsigned64,
    cfprAdaptorVnicStatsPacketsTxDeltaMin                            Unsigned64,
    cfprAdaptorVnicStatsSuspect                                      TruthValue,
    cfprAdaptorVnicStatsThresholded                                  CfprAdaptorVnicStatsThresholded,
    cfprAdaptorVnicStatsTimeCollected                                DateAndTime,
    cfprAdaptorVnicStatsUpdate                                       Gauge32
}

cfprAdaptorVnicStatsInstanceId OBJECT-TYPE
    SYNTAX       CfprManagedObjectId
    MAX-ACCESS   not-accessible
    STATUS       current
    DESCRIPTION
        "Instance identifier of the managed object."
    ::= { cfprAdaptorVnicStatsEntry 1 }

cfprAdaptorVnicStatsDn OBJECT-TYPE
    SYNTAX       CfprManagedObjectDn
    MAX-ACCESS   read-only
    STATUS       current
    DESCRIPTION
        "Cisco Firepower adaptor:VnicStats:dn managed object property"
    ::= { cfprAdaptorVnicStatsEntry 2 }

cfprAdaptorVnicStatsRn OBJECT-TYPE
    SYNTAX       SnmpAdminString
    MAX-ACCESS   read-only
    STATUS       current
    DESCRIPTION
        "Cisco Firepower adaptor:VnicStats:rn managed object property"
    ::= { cfprAdaptorVnicStatsEntry 3 }

cfprAdaptorVnicStatsBytesRx OBJECT-TYPE
    SYNTAX       Unsigned64
    MAX-ACCESS   read-only
    STATUS       current
    DESCRIPTION
        "Cisco Firepower adaptor:VnicStats:bytesRx managed
        object property"
    ::= { cfprAdaptorVnicStatsEntry 4 }

cfprAdaptorVnicStatsBytesRxDelta OBJECT-TYPE
    SYNTAX       Counter64
    MAX-ACCESS   read-only
    STATUS       current
    DESCRIPTION
        "Cisco Firepower adaptor:VnicStats:bytesRxDelta
        managed object property"
    ::= { cfprAdaptorVnicStatsEntry 5 }

cfprAdaptorVnicStatsBytesRxDeltaAvg OBJECT-TYPE
    SYNTAX       Unsigned64
    MAX-ACCESS   read-only
    STATUS       current
    DESCRIPTION
        "Cisco Firepower adaptor:VnicStats:bytesRxDeltaAvg
        managed object property"
    ::= { cfprAdaptorVnicStatsEntry 6 }

cfprAdaptorVnicStatsBytesRxDeltaMax OBJECT-TYPE
    SYNTAX       Unsigned64
    MAX-ACCESS   read-only
    STATUS       current
    DESCRIPTION
        "Cisco Firepower adaptor:VnicStats:bytesRxDeltaMax
        managed object property"
    ::= { cfprAdaptorVnicStatsEntry 7 }

cfprAdaptorVnicStatsBytesRxDeltaMin OBJECT-TYPE
    SYNTAX       Unsigned64
    MAX-ACCESS   read-only
    STATUS       current
    DESCRIPTION
        "Cisco Firepower adaptor:VnicStats:bytesRxDeltaMin
        managed object property"
    ::= { cfprAdaptorVnicStatsEntry 8 }

cfprAdaptorVnicStatsBytesTx OBJECT-TYPE
    SYNTAX       Unsigned64
    MAX-ACCESS   read-only
    STATUS       current
    DESCRIPTION
        "Cisco Firepower adaptor:VnicStats:bytesTx managed
        object property"
    ::= { cfprAdaptorVnicStatsEntry 9 }

cfprAdaptorVnicStatsBytesTxDelta OBJECT-TYPE
    SYNTAX       Counter64
    MAX-ACCESS   read-only
    STATUS       current
    DESCRIPTION
        "Cisco Firepower adaptor:VnicStats:bytesTxDelta
        managed object property"
    ::= { cfprAdaptorVnicStatsEntry 10 }

cfprAdaptorVnicStatsBytesTxDeltaAvg OBJECT-TYPE
    SYNTAX       Unsigned64
    MAX-ACCESS   read-only
    STATUS       current
    DESCRIPTION
        "Cisco Firepower adaptor:VnicStats:bytesTxDeltaAvg
        managed object property"
    ::= { cfprAdaptorVnicStatsEntry 11 }

cfprAdaptorVnicStatsBytesTxDeltaMax OBJECT-TYPE
    SYNTAX       Unsigned64
    MAX-ACCESS   read-only
    STATUS       current
    DESCRIPTION
        "Cisco Firepower adaptor:VnicStats:bytesTxDeltaMax
        managed object property"
    ::= { cfprAdaptorVnicStatsEntry 12 }

cfprAdaptorVnicStatsBytesTxDeltaMin OBJECT-TYPE
    SYNTAX       Unsigned64
    MAX-ACCESS   read-only
    STATUS       current
    DESCRIPTION
        "Cisco Firepower adaptor:VnicStats:bytesTxDeltaMin
        managed object property"
    ::= { cfprAdaptorVnicStatsEntry 13 }

cfprAdaptorVnicStatsDroppedRx OBJECT-TYPE
    SYNTAX       Unsigned64
    MAX-ACCESS   read-only
    STATUS       current
    DESCRIPTION
        "Cisco Firepower adaptor:VnicStats:droppedRx managed
        object property"
    ::= { cfprAdaptorVnicStatsEntry 14 }

cfprAdaptorVnicStatsDroppedRxDelta OBJECT-TYPE
    SYNTAX       Counter64
    MAX-ACCESS   read-only
    STATUS       current
    DESCRIPTION
        "Cisco Firepower adaptor:VnicStats:droppedRxDelta
        managed object property"
    ::= { cfprAdaptorVnicStatsEntry 15 }

cfprAdaptorVnicStatsDroppedRxDeltaAvg OBJECT-TYPE
    SYNTAX       Unsigned64
    MAX-ACCESS   read-only
    STATUS       current
    DESCRIPTION
        "Cisco Firepower adaptor:VnicStats:droppedRxDeltaAvg
        managed object property"
    ::= { cfprAdaptorVnicStatsEntry 16 }

cfprAdaptorVnicStatsDroppedRxDeltaMax OBJECT-TYPE
    SYNTAX       Unsigned64
    MAX-ACCESS   read-only
    STATUS       current
    DESCRIPTION
        "Cisco Firepower adaptor:VnicStats:droppedRxDeltaMax
        managed object property"
    ::= { cfprAdaptorVnicStatsEntry 17 }

cfprAdaptorVnicStatsDroppedRxDeltaMin OBJECT-TYPE
    SYNTAX       Unsigned64
    MAX-ACCESS   read-only
    STATUS       current
    DESCRIPTION
        "Cisco Firepower adaptor:VnicStats:droppedRxDeltaMin
        managed object property"
    ::= { cfprAdaptorVnicStatsEntry 18 }

cfprAdaptorVnicStatsDroppedTx OBJECT-TYPE
    SYNTAX       Unsigned64
    MAX-ACCESS   read-only
    STATUS       current
    DESCRIPTION
        "Cisco Firepower adaptor:VnicStats:droppedTx managed
        object property"
    ::= { cfprAdaptorVnicStatsEntry 19 }

cfprAdaptorVnicStatsDroppedTxDelta OBJECT-TYPE
    SYNTAX       Counter64
    MAX-ACCESS   read-only
    STATUS       current
    DESCRIPTION
        "Cisco Firepower adaptor:VnicStats:droppedTxDelta
        managed object property"
    ::= { cfprAdaptorVnicStatsEntry 20 }

cfprAdaptorVnicStatsDroppedTxDeltaAvg OBJECT-TYPE
    SYNTAX       Unsigned64
    MAX-ACCESS   read-only
    STATUS       current
    DESCRIPTION
        "Cisco Firepower adaptor:VnicStats:droppedTxDeltaAvg
        managed object property"
    ::= { cfprAdaptorVnicStatsEntry 21 }

cfprAdaptorVnicStatsDroppedTxDeltaMax OBJECT-TYPE
    SYNTAX       Unsigned64
    MAX-ACCESS   read-only
    STATUS       current
    DESCRIPTION
        "Cisco Firepower adaptor:VnicStats:droppedTxDeltaMax
        managed object property"
    ::= { cfprAdaptorVnicStatsEntry 22 }

cfprAdaptorVnicStatsDroppedTxDeltaMin OBJECT-TYPE
    SYNTAX       Unsigned64
    MAX-ACCESS   read-only
    STATUS       current
    DESCRIPTION
        "Cisco Firepower adaptor:VnicStats:droppedTxDeltaMin
        managed object property"
    ::= { cfprAdaptorVnicStatsEntry 23 }

cfprAdaptorVnicStatsErrorsRx OBJECT-TYPE
    SYNTAX       Unsigned64
    MAX-ACCESS   read-only
    STATUS       current
    DESCRIPTION
        "Cisco Firepower adaptor:VnicStats:errorsRx managed
        object property"
    ::= { cfprAdaptorVnicStatsEntry 24 }

cfprAdaptorVnicStatsErrorsRxDelta OBJECT-TYPE
    SYNTAX       Counter64
    MAX-ACCESS   read-only
    STATUS       current
    DESCRIPTION
        "Cisco Firepower adaptor:VnicStats:errorsRxDelta
        managed object property"
    ::= { cfprAdaptorVnicStatsEntry 25 }

cfprAdaptorVnicStatsErrorsRxDeltaAvg OBJECT-TYPE
    SYNTAX       Unsigned64
    MAX-ACCESS   read-only
    STATUS       current
    DESCRIPTION
        "Cisco Firepower adaptor:VnicStats:errorsRxDeltaAvg
        managed object property"
    ::= { cfprAdaptorVnicStatsEntry 26 }

cfprAdaptorVnicStatsErrorsRxDeltaMax OBJECT-TYPE
    SYNTAX       Unsigned64
    MAX-ACCESS   read-only
    STATUS       current
    DESCRIPTION
        "Cisco Firepower adaptor:VnicStats:errorsRxDeltaMax
        managed object property"
    ::= { cfprAdaptorVnicStatsEntry 27 }

cfprAdaptorVnicStatsErrorsRxDeltaMin OBJECT-TYPE
    SYNTAX       Unsigned64
    MAX-ACCESS   read-only
    STATUS       current
    DESCRIPTION
        "Cisco Firepower adaptor:VnicStats:errorsRxDeltaMin
        managed object property"
    ::= { cfprAdaptorVnicStatsEntry 28 }

cfprAdaptorVnicStatsErrorsTx OBJECT-TYPE
    SYNTAX       Unsigned64
    MAX-ACCESS   read-only
    STATUS       current
    DESCRIPTION
        "Cisco Firepower adaptor:VnicStats:errorsTx managed
        object property"
    ::= { cfprAdaptorVnicStatsEntry 29 }

cfprAdaptorVnicStatsErrorsTxDelta OBJECT-TYPE
    SYNTAX       Counter64
    MAX-ACCESS   read-only
    STATUS       current
    DESCRIPTION
        "Cisco Firepower adaptor:VnicStats:errorsTxDelta
        managed object property"
    ::= { cfprAdaptorVnicStatsEntry 30 }

cfprAdaptorVnicStatsErrorsTxDeltaAvg OBJECT-TYPE
    SYNTAX       Unsigned64
    MAX-ACCESS   read-only
    STATUS       current
    DESCRIPTION
        "Cisco Firepower adaptor:VnicStats:errorsTxDeltaAvg
        managed object property"
    ::= { cfprAdaptorVnicStatsEntry 31 }

cfprAdaptorVnicStatsErrorsTxDeltaMax OBJECT-TYPE
    SYNTAX       Unsigned64
    MAX-ACCESS   read-only
    STATUS       current
    DESCRIPTION
        "Cisco Firepower adaptor:VnicStats:errorsTxDeltaMax
        managed object property"
    ::= { cfprAdaptorVnicStatsEntry 32 }

cfprAdaptorVnicStatsErrorsTxDeltaMin OBJECT-TYPE
    SYNTAX       Unsigned64
    MAX-ACCESS   read-only
    STATUS       current
    DESCRIPTION
        "Cisco Firepower adaptor:VnicStats:errorsTxDeltaMin
        managed object property"
    ::= { cfprAdaptorVnicStatsEntry 33 }

cfprAdaptorVnicStatsIntervals OBJECT-TYPE
    SYNTAX       Gauge32
    MAX-ACCESS   read-only
    STATUS       current
    DESCRIPTION
        "Cisco Firepower adaptor:VnicStats:intervals managed
        object property"
    ::= { cfprAdaptorVnicStatsEntry 34 }

cfprAdaptorVnicStatsPacketsRx OBJECT-TYPE
    SYNTAX       Unsigned64
    MAX-ACCESS   read-only
    STATUS       current
    DESCRIPTION
        "Cisco Firepower adaptor:VnicStats:packetsRx managed
        object property"
    ::= { cfprAdaptorVnicStatsEntry 35 }

cfprAdaptorVnicStatsPacketsRxDelta OBJECT-TYPE
    SYNTAX       Counter64
    MAX-ACCESS   read-only
    STATUS       current
    DESCRIPTION
        "Cisco Firepower adaptor:VnicStats:packetsRxDelta
        managed object property"
    ::= { cfprAdaptorVnicStatsEntry 36 }

cfprAdaptorVnicStatsPacketsRxDeltaAvg OBJECT-TYPE
    SYNTAX       Unsigned64
    MAX-ACCESS   read-only
    STATUS       current
    DESCRIPTION
        "Cisco Firepower adaptor:VnicStats:packetsRxDeltaAvg
        managed object property"
    ::= { cfprAdaptorVnicStatsEntry 37 }

cfprAdaptorVnicStatsPacketsRxDeltaMax OBJECT-TYPE
    SYNTAX       Unsigned64
    MAX-ACCESS   read-only
    STATUS       current
    DESCRIPTION
        "Cisco Firepower adaptor:VnicStats:packetsRxDeltaMax
        managed object property"
    ::= { cfprAdaptorVnicStatsEntry 38 }

cfprAdaptorVnicStatsPacketsRxDeltaMin OBJECT-TYPE
    SYNTAX       Unsigned64
    MAX-ACCESS   read-only
    STATUS       current
    DESCRIPTION
        "Cisco Firepower adaptor:VnicStats:packetsRxDeltaMin
        managed object property"
    ::= { cfprAdaptorVnicStatsEntry 39 }

cfprAdaptorVnicStatsPacketsTx OBJECT-TYPE
    SYNTAX       Unsigned64
    MAX-ACCESS   read-only
    STATUS       current
    DESCRIPTION
        "Cisco Firepower adaptor:VnicStats:packetsTx managed
        object property"
    ::= { cfprAdaptorVnicStatsEntry 40 }

cfprAdaptorVnicStatsPacketsTxDelta OBJECT-TYPE
    SYNTAX       Counter64
    MAX-ACCESS   read-only
    STATUS       current
    DESCRIPTION
        "Cisco Firepower adaptor:VnicStats:packetsTxDelta
        managed object property"
    ::= { cfprAdaptorVnicStatsEntry 41 }

cfprAdaptorVnicStatsPacketsTxDeltaAvg OBJECT-TYPE
    SYNTAX       Unsigned64
    MAX-ACCESS   read-only
    STATUS       current
    DESCRIPTION
        "Cisco Firepower adaptor:VnicStats:packetsTxDeltaAvg
        managed object property"
    ::= { cfprAdaptorVnicStatsEntry 42 }

cfprAdaptorVnicStatsPacketsTxDeltaMax OBJECT-TYPE
    SYNTAX       Unsigned64
    MAX-ACCESS   read-only
    STATUS       current
    DESCRIPTION
        "Cisco Firepower adaptor:VnicStats:packetsTxDeltaMax
        managed object property"
    ::= { cfprAdaptorVnicStatsEntry 43 }

cfprAdaptorVnicStatsPacketsTxDeltaMin OBJECT-TYPE
    SYNTAX       Unsigned64
    MAX-ACCESS   read-only
    STATUS       current
    DESCRIPTION
        "Cisco Firepower adaptor:VnicStats:packetsTxDeltaMin
        managed object property"
    ::= { cfprAdaptorVnicStatsEntry 44 }

cfprAdaptorVnicStatsSuspect OBJECT-TYPE
    SYNTAX       TruthValue
    MAX-ACCESS   read-only
    STATUS       current
    DESCRIPTION
        "Cisco Firepower adaptor:VnicStats:suspect managed
        object property"
    ::= { cfprAdaptorVnicStatsEntry 45 }

cfprAdaptorVnicStatsThresholded OBJECT-TYPE
    SYNTAX       CfprAdaptorVnicStatsThresholded
    MAX-ACCESS   read-only
    STATUS       current
    DESCRIPTION
        "Cisco Firepower adaptor:VnicStats:thresholded
        managed object property"
    ::= { cfprAdaptorVnicStatsEntry 46 }

cfprAdaptorVnicStatsTimeCollected OBJECT-TYPE
    SYNTAX       DateAndTime
    MAX-ACCESS   read-only
    STATUS       current
    DESCRIPTION
        "Cisco Firepower adaptor:VnicStats:timeCollected
        managed object property"
    ::= { cfprAdaptorVnicStatsEntry 47 }

cfprAdaptorVnicStatsUpdate OBJECT-TYPE
    SYNTAX       Gauge32
    MAX-ACCESS   read-only
    STATUS       current
    DESCRIPTION
        "Cisco Firepower adaptor:VnicStats:update managed object property"
    ::= { cfprAdaptorVnicStatsEntry 48 }

cfprAdaptorVnicStatsHistTable OBJECT-TYPE
    SYNTAX           SEQUENCE OF CfprAdaptorVnicStatsHistEntry
    MAX-ACCESS       not-accessible
    STATUS           current
    DESCRIPTION
        "Cisco Firepower adaptor:VnicStatsHist managed object table"
    ::= { cfprAdaptorObjects 120 }

cfprAdaptorVnicStatsHistEntry OBJECT-TYPE
    SYNTAX           CfprAdaptorVnicStatsHistEntry
    MAX-ACCESS       not-accessible
    STATUS           current
    DESCRIPTION
        "Entry for the cfprAdaptorVnicStatsHistTable table."
    INDEX { cfprAdaptorVnicStatsHistInstanceId }
    ::= { cfprAdaptorVnicStatsHistTable 1 }

CfprAdaptorVnicStatsHistEntry ::= SEQUENCE {
    cfprAdaptorVnicStatsHistInstanceId                               CfprManagedObjectId,
    cfprAdaptorVnicStatsHistDn                                       CfprManagedObjectDn,
    cfprAdaptorVnicStatsHistRn                                       SnmpAdminString,
    cfprAdaptorVnicStatsHistBytesRx                                  Unsigned64,
    cfprAdaptorVnicStatsHistBytesRxDelta                             Unsigned64,
    cfprAdaptorVnicStatsHistBytesRxDeltaAvg                          Unsigned64,
    cfprAdaptorVnicStatsHistBytesRxDeltaMax                          Unsigned64,
    cfprAdaptorVnicStatsHistBytesRxDeltaMin                          Unsigned64,
    cfprAdaptorVnicStatsHistBytesTx                                  Unsigned64,
    cfprAdaptorVnicStatsHistBytesTxDelta                             Unsigned64,
    cfprAdaptorVnicStatsHistBytesTxDeltaAvg                          Unsigned64,
    cfprAdaptorVnicStatsHistBytesTxDeltaMax                          Unsigned64,
    cfprAdaptorVnicStatsHistBytesTxDeltaMin                          Unsigned64,
    cfprAdaptorVnicStatsHistDroppedRx                                Unsigned64,
    cfprAdaptorVnicStatsHistDroppedRxDelta                           Unsigned64,
    cfprAdaptorVnicStatsHistDroppedRxDeltaAvg                        Unsigned64,
    cfprAdaptorVnicStatsHistDroppedRxDeltaMax                        Unsigned64,
    cfprAdaptorVnicStatsHistDroppedRxDeltaMin                        Unsigned64,
    cfprAdaptorVnicStatsHistDroppedTx                                Unsigned64,
    cfprAdaptorVnicStatsHistDroppedTxDelta                           Unsigned64,
    cfprAdaptorVnicStatsHistDroppedTxDeltaAvg                        Unsigned64,
    cfprAdaptorVnicStatsHistDroppedTxDeltaMax                        Unsigned64,
    cfprAdaptorVnicStatsHistDroppedTxDeltaMin                        Unsigned64,
    cfprAdaptorVnicStatsHistErrorsRx                                 Unsigned64,
    cfprAdaptorVnicStatsHistErrorsRxDelta                            Unsigned64,
    cfprAdaptorVnicStatsHistErrorsRxDeltaAvg                         Unsigned64,
    cfprAdaptorVnicStatsHistErrorsRxDeltaMax                         Unsigned64,
    cfprAdaptorVnicStatsHistErrorsRxDeltaMin                         Unsigned64,
    cfprAdaptorVnicStatsHistErrorsTx                                 Unsigned64,
    cfprAdaptorVnicStatsHistErrorsTxDelta                            Unsigned64,
    cfprAdaptorVnicStatsHistErrorsTxDeltaAvg                         Unsigned64,
    cfprAdaptorVnicStatsHistErrorsTxDeltaMax                         Unsigned64,
    cfprAdaptorVnicStatsHistErrorsTxDeltaMin                         Unsigned64,
    cfprAdaptorVnicStatsHistId                                       Unsigned64,
    cfprAdaptorVnicStatsHistMostRecent                               TruthValue,
    cfprAdaptorVnicStatsHistPacketsRx                                Unsigned64,
    cfprAdaptorVnicStatsHistPacketsRxDelta                           Unsigned64,
    cfprAdaptorVnicStatsHistPacketsRxDeltaAvg                        Unsigned64,
    cfprAdaptorVnicStatsHistPacketsRxDeltaMax                        Unsigned64,
    cfprAdaptorVnicStatsHistPacketsRxDeltaMin                        Unsigned64,
    cfprAdaptorVnicStatsHistPacketsTx                                Unsigned64,
    cfprAdaptorVnicStatsHistPacketsTxDelta                           Unsigned64,
    cfprAdaptorVnicStatsHistPacketsTxDeltaAvg                        Unsigned64,
    cfprAdaptorVnicStatsHistPacketsTxDeltaMax                        Unsigned64,
    cfprAdaptorVnicStatsHistPacketsTxDeltaMin                        Unsigned64,
    cfprAdaptorVnicStatsHistSuspect                                  TruthValue,
    cfprAdaptorVnicStatsHistThresholded                              CfprAdaptorVnicStatsHistThresholded,
    cfprAdaptorVnicStatsHistTimeCollected                            DateAndTime
}

cfprAdaptorVnicStatsHistInstanceId OBJECT-TYPE
    SYNTAX       CfprManagedObjectId
    MAX-ACCESS   not-accessible
    STATUS       current
    DESCRIPTION
        "Instance identifier of the managed object."
    ::= { cfprAdaptorVnicStatsHistEntry 1 }

cfprAdaptorVnicStatsHistDn OBJECT-TYPE
    SYNTAX       CfprManagedObjectDn
    MAX-ACCESS   read-only
    STATUS       current
    DESCRIPTION
        "Cisco Firepower adaptor:VnicStatsHist:dn managed object property"
    ::= { cfprAdaptorVnicStatsHistEntry 2 }

cfprAdaptorVnicStatsHistRn OBJECT-TYPE
    SYNTAX       SnmpAdminString
    MAX-ACCESS   read-only
    STATUS       current
    DESCRIPTION
        "Cisco Firepower adaptor:VnicStatsHist:rn managed object property"
    ::= { cfprAdaptorVnicStatsHistEntry 3 }

cfprAdaptorVnicStatsHistBytesRx OBJECT-TYPE
    SYNTAX       Unsigned64
    MAX-ACCESS   read-only
    STATUS       current
    DESCRIPTION
        "Cisco Firepower adaptor:VnicStatsHist:bytesRx
        managed object property"
    ::= { cfprAdaptorVnicStatsHistEntry 4 }

cfprAdaptorVnicStatsHistBytesRxDelta OBJECT-TYPE
    SYNTAX       Unsigned64
    MAX-ACCESS   read-only
    STATUS       current
    DESCRIPTION
        "Cisco Firepower adaptor:VnicStatsHist:bytesRxDelta
        managed object property"
    ::= { cfprAdaptorVnicStatsHistEntry 5 }

cfprAdaptorVnicStatsHistBytesRxDeltaAvg OBJECT-TYPE
    SYNTAX       Unsigned64
    MAX-ACCESS   read-only
    STATUS       current
    DESCRIPTION
        "Cisco Firepower adaptor:VnicStatsHist:bytesRxDeltaAvg
        managed object property"
    ::= { cfprAdaptorVnicStatsHistEntry 6 }

cfprAdaptorVnicStatsHistBytesRxDeltaMax OBJECT-TYPE
    SYNTAX       Unsigned64
    MAX-ACCESS   read-only
    STATUS       current
    DESCRIPTION
        "Cisco Firepower adaptor:VnicStatsHist:bytesRxDeltaMax
        managed object property"
    ::= { cfprAdaptorVnicStatsHistEntry 7 }

cfprAdaptorVnicStatsHistBytesRxDeltaMin OBJECT-TYPE
    SYNTAX       Unsigned64
    MAX-ACCESS   read-only
    STATUS       current
    DESCRIPTION
        "Cisco Firepower adaptor:VnicStatsHist:bytesRxDeltaMin
        managed object property"
    ::= { cfprAdaptorVnicStatsHistEntry 8 }

cfprAdaptorVnicStatsHistBytesTx OBJECT-TYPE
    SYNTAX       Unsigned64
    MAX-ACCESS   read-only
    STATUS       current
    DESCRIPTION
        "Cisco Firepower adaptor:VnicStatsHist:bytesTx
        managed object property"
    ::= { cfprAdaptorVnicStatsHistEntry 9 }

cfprAdaptorVnicStatsHistBytesTxDelta OBJECT-TYPE
    SYNTAX       Unsigned64
    MAX-ACCESS   read-only
    STATUS       current
    DESCRIPTION
        "Cisco Firepower adaptor:VnicStatsHist:bytesTxDelta
        managed object property"
    ::= { cfprAdaptorVnicStatsHistEntry 10 }

cfprAdaptorVnicStatsHistBytesTxDeltaAvg OBJECT-TYPE
    SYNTAX       Unsigned64
    MAX-ACCESS   read-only
    STATUS       current
    DESCRIPTION
        "Cisco Firepower adaptor:VnicStatsHist:bytesTxDeltaAvg
        managed object property"
    ::= { cfprAdaptorVnicStatsHistEntry 11 }

cfprAdaptorVnicStatsHistBytesTxDeltaMax OBJECT-TYPE
    SYNTAX       Unsigned64
    MAX-ACCESS   read-only
    STATUS       current
    DESCRIPTION
        "Cisco Firepower adaptor:VnicStatsHist:bytesTxDeltaMax
        managed object property"
    ::= { cfprAdaptorVnicStatsHistEntry 12 }

cfprAdaptorVnicStatsHistBytesTxDeltaMin OBJECT-TYPE
    SYNTAX       Unsigned64
    MAX-ACCESS   read-only
    STATUS       current
    DESCRIPTION
        "Cisco Firepower adaptor:VnicStatsHist:bytesTxDeltaMin
        managed object property"
    ::= { cfprAdaptorVnicStatsHistEntry 13 }

cfprAdaptorVnicStatsHistDroppedRx OBJECT-TYPE
    SYNTAX       Unsigned64
    MAX-ACCESS   read-only
    STATUS       current
    DESCRIPTION
        "Cisco Firepower adaptor:VnicStatsHist:droppedRx
        managed object property"
    ::= { cfprAdaptorVnicStatsHistEntry 14 }

cfprAdaptorVnicStatsHistDroppedRxDelta OBJECT-TYPE
    SYNTAX       Unsigned64
    MAX-ACCESS   read-only
    STATUS       current
    DESCRIPTION
        "Cisco Firepower adaptor:VnicStatsHist:droppedRxDelta
        managed object property"
    ::= { cfprAdaptorVnicStatsHistEntry 15 }

cfprAdaptorVnicStatsHistDroppedRxDeltaAvg OBJECT-TYPE
    SYNTAX       Unsigned64
    MAX-ACCESS   read-only
    STATUS       current
    DESCRIPTION
        "Cisco Firepower adaptor:VnicStatsHist:droppedRxDeltaAvg
        managed object property"
    ::= { cfprAdaptorVnicStatsHistEntry 16 }

cfprAdaptorVnicStatsHistDroppedRxDeltaMax OBJECT-TYPE
    SYNTAX       Unsigned64
    MAX-ACCESS   read-only
    STATUS       current
    DESCRIPTION
        "Cisco Firepower adaptor:VnicStatsHist:droppedRxDeltaMax
        managed object property"
    ::= { cfprAdaptorVnicStatsHistEntry 17 }

cfprAdaptorVnicStatsHistDroppedRxDeltaMin OBJECT-TYPE
    SYNTAX       Unsigned64
    MAX-ACCESS   read-only
    STATUS       current
    DESCRIPTION
        "Cisco Firepower adaptor:VnicStatsHist:droppedRxDeltaMin
        managed object property"
    ::= { cfprAdaptorVnicStatsHistEntry 18 }

cfprAdaptorVnicStatsHistDroppedTx OBJECT-TYPE
    SYNTAX       Unsigned64
    MAX-ACCESS   read-only
    STATUS       current
    DESCRIPTION
        "Cisco Firepower adaptor:VnicStatsHist:droppedTx
        managed object property"
    ::= { cfprAdaptorVnicStatsHistEntry 19 }

cfprAdaptorVnicStatsHistDroppedTxDelta OBJECT-TYPE
    SYNTAX       Unsigned64
    MAX-ACCESS   read-only
    STATUS       current
    DESCRIPTION
        "Cisco Firepower adaptor:VnicStatsHist:droppedTxDelta
        managed object property"
    ::= { cfprAdaptorVnicStatsHistEntry 20 }

cfprAdaptorVnicStatsHistDroppedTxDeltaAvg OBJECT-TYPE
    SYNTAX       Unsigned64
    MAX-ACCESS   read-only
    STATUS       current
    DESCRIPTION
        "Cisco Firepower adaptor:VnicStatsHist:droppedTxDeltaAvg
        managed object property"
    ::= { cfprAdaptorVnicStatsHistEntry 21 }

cfprAdaptorVnicStatsHistDroppedTxDeltaMax OBJECT-TYPE
    SYNTAX       Unsigned64
    MAX-ACCESS   read-only
    STATUS       current
    DESCRIPTION
        "Cisco Firepower adaptor:VnicStatsHist:droppedTxDeltaMax
        managed object property"
    ::= { cfprAdaptorVnicStatsHistEntry 22 }

cfprAdaptorVnicStatsHistDroppedTxDeltaMin OBJECT-TYPE
    SYNTAX       Unsigned64
    MAX-ACCESS   read-only
    STATUS       current
    DESCRIPTION
        "Cisco Firepower adaptor:VnicStatsHist:droppedTxDeltaMin
        managed object property"
    ::= { cfprAdaptorVnicStatsHistEntry 23 }

cfprAdaptorVnicStatsHistErrorsRx OBJECT-TYPE
    SYNTAX       Unsigned64
    MAX-ACCESS   read-only
    STATUS       current
    DESCRIPTION
        "Cisco Firepower adaptor:VnicStatsHist:errorsRx
        managed object property"
    ::= { cfprAdaptorVnicStatsHistEntry 24 }

cfprAdaptorVnicStatsHistErrorsRxDelta OBJECT-TYPE
    SYNTAX       Unsigned64
    MAX-ACCESS   read-only
    STATUS       current
    DESCRIPTION
        "Cisco Firepower adaptor:VnicStatsHist:errorsRxDelta
        managed object property"
    ::= { cfprAdaptorVnicStatsHistEntry 25 }

cfprAdaptorVnicStatsHistErrorsRxDeltaAvg OBJECT-TYPE
    SYNTAX       Unsigned64
    MAX-ACCESS   read-only
    STATUS       current
    DESCRIPTION
        "Cisco Firepower adaptor:VnicStatsHist:errorsRxDeltaAvg
        managed object property"
    ::= { cfprAdaptorVnicStatsHistEntry 26 }

cfprAdaptorVnicStatsHistErrorsRxDeltaMax OBJECT-TYPE
    SYNTAX       Unsigned64
    MAX-ACCESS   read-only
    STATUS       current
    DESCRIPTION
        "Cisco Firepower adaptor:VnicStatsHist:errorsRxDeltaMax
        managed object property"
    ::= { cfprAdaptorVnicStatsHistEntry 27 }

cfprAdaptorVnicStatsHistErrorsRxDeltaMin OBJECT-TYPE
    SYNTAX       Unsigned64
    MAX-ACCESS   read-only
    STATUS       current
    DESCRIPTION
        "Cisco Firepower adaptor:VnicStatsHist:errorsRxDeltaMin
        managed object property"
    ::= { cfprAdaptorVnicStatsHistEntry 28 }

cfprAdaptorVnicStatsHistErrorsTx OBJECT-TYPE
    SYNTAX       Unsigned64
    MAX-ACCESS   read-only
    STATUS       current
    DESCRIPTION
        "Cisco Firepower adaptor:VnicStatsHist:errorsTx
        managed object property"
    ::= { cfprAdaptorVnicStatsHistEntry 29 }

cfprAdaptorVnicStatsHistErrorsTxDelta OBJECT-TYPE
    SYNTAX       Unsigned64
    MAX-ACCESS   read-only
    STATUS       current
    DESCRIPTION
        "Cisco Firepower adaptor:VnicStatsHist:errorsTxDelta
        managed object property"
    ::= { cfprAdaptorVnicStatsHistEntry 30 }

cfprAdaptorVnicStatsHistErrorsTxDeltaAvg OBJECT-TYPE
    SYNTAX       Unsigned64
    MAX-ACCESS   read-only
    STATUS       current
    DESCRIPTION
        "Cisco Firepower adaptor:VnicStatsHist:errorsTxDeltaAvg
        managed object property"
    ::= { cfprAdaptorVnicStatsHistEntry 31 }

cfprAdaptorVnicStatsHistErrorsTxDeltaMax OBJECT-TYPE
    SYNTAX       Unsigned64
    MAX-ACCESS   read-only
    STATUS       current
    DESCRIPTION
        "Cisco Firepower adaptor:VnicStatsHist:errorsTxDeltaMax
        managed object property"
    ::= { cfprAdaptorVnicStatsHistEntry 32 }

cfprAdaptorVnicStatsHistErrorsTxDeltaMin OBJECT-TYPE
    SYNTAX       Unsigned64
    MAX-ACCESS   read-only
    STATUS       current
    DESCRIPTION
        "Cisco Firepower adaptor:VnicStatsHist:errorsTxDeltaMin
        managed object property"
    ::= { cfprAdaptorVnicStatsHistEntry 33 }

cfprAdaptorVnicStatsHistId OBJECT-TYPE
    SYNTAX       Unsigned64
    MAX-ACCESS   read-only
    STATUS       current
    DESCRIPTION
        "Cisco Firepower adaptor:VnicStatsHist:id managed object property"
    ::= { cfprAdaptorVnicStatsHistEntry 34 }

cfprAdaptorVnicStatsHistMostRecent OBJECT-TYPE
    SYNTAX       TruthValue
    MAX-ACCESS   read-only
    STATUS       current
    DESCRIPTION
        "Cisco Firepower adaptor:VnicStatsHist:mostRecent
        managed object property"
    ::= { cfprAdaptorVnicStatsHistEntry 35 }

cfprAdaptorVnicStatsHistPacketsRx OBJECT-TYPE
    SYNTAX       Unsigned64
    MAX-ACCESS   read-only
    STATUS       current
    DESCRIPTION
        "Cisco Firepower adaptor:VnicStatsHist:packetsRx
        managed object property"
    ::= { cfprAdaptorVnicStatsHistEntry 36 }

cfprAdaptorVnicStatsHistPacketsRxDelta OBJECT-TYPE
    SYNTAX       Unsigned64
    MAX-ACCESS   read-only
    STATUS       current
    DESCRIPTION
        "Cisco Firepower adaptor:VnicStatsHist:packetsRxDelta
        managed object property"
    ::= { cfprAdaptorVnicStatsHistEntry 37 }

cfprAdaptorVnicStatsHistPacketsRxDeltaAvg OBJECT-TYPE
    SYNTAX       Unsigned64
    MAX-ACCESS   read-only
    STATUS       current
    DESCRIPTION
        "Cisco Firepower adaptor:VnicStatsHist:packetsRxDeltaAvg
        managed object property"
    ::= { cfprAdaptorVnicStatsHistEntry 38 }

cfprAdaptorVnicStatsHistPacketsRxDeltaMax OBJECT-TYPE
    SYNTAX       Unsigned64
    MAX-ACCESS   read-only
    STATUS       current
    DESCRIPTION
        "Cisco Firepower adaptor:VnicStatsHist:packetsRxDeltaMax
        managed object property"
    ::= { cfprAdaptorVnicStatsHistEntry 39 }

cfprAdaptorVnicStatsHistPacketsRxDeltaMin OBJECT-TYPE
    SYNTAX       Unsigned64
    MAX-ACCESS   read-only
    STATUS       current
    DESCRIPTION
        "Cisco Firepower adaptor:VnicStatsHist:packetsRxDeltaMin
        managed object property"
    ::= { cfprAdaptorVnicStatsHistEntry 40 }

cfprAdaptorVnicStatsHistPacketsTx OBJECT-TYPE
    SYNTAX       Unsigned64
    MAX-ACCESS   read-only
    STATUS       current
    DESCRIPTION
        "Cisco Firepower adaptor:VnicStatsHist:packetsTx
        managed object property"
    ::= { cfprAdaptorVnicStatsHistEntry 41 }

cfprAdaptorVnicStatsHistPacketsTxDelta OBJECT-TYPE
    SYNTAX       Unsigned64
    MAX-ACCESS   read-only
    STATUS       current
    DESCRIPTION
        "Cisco Firepower adaptor:VnicStatsHist:packetsTxDelta
        managed object property"
    ::= { cfprAdaptorVnicStatsHistEntry 42 }

cfprAdaptorVnicStatsHistPacketsTxDeltaAvg OBJECT-TYPE
    SYNTAX       Unsigned64
    MAX-ACCESS   read-only
    STATUS       current
    DESCRIPTION
        "Cisco Firepower adaptor:VnicStatsHist:packetsTxDeltaAvg
        managed object property"
    ::= { cfprAdaptorVnicStatsHistEntry 43 }

cfprAdaptorVnicStatsHistPacketsTxDeltaMax OBJECT-TYPE
    SYNTAX       Unsigned64
    MAX-ACCESS   read-only
    STATUS       current
    DESCRIPTION
        "Cisco Firepower adaptor:VnicStatsHist:packetsTxDeltaMax
        managed object property"
    ::= { cfprAdaptorVnicStatsHistEntry 44 }

cfprAdaptorVnicStatsHistPacketsTxDeltaMin OBJECT-TYPE
    SYNTAX       Unsigned64
    MAX-ACCESS   read-only
    STATUS       current
    DESCRIPTION
        "Cisco Firepower adaptor:VnicStatsHist:packetsTxDeltaMin
        managed object property"
    ::= { cfprAdaptorVnicStatsHistEntry 45 }

cfprAdaptorVnicStatsHistSuspect OBJECT-TYPE
    SYNTAX       TruthValue
    MAX-ACCESS   read-only
    STATUS       current
    DESCRIPTION
        "Cisco Firepower adaptor:VnicStatsHist:suspect
        managed object property"
    ::= { cfprAdaptorVnicStatsHistEntry 46 }

cfprAdaptorVnicStatsHistThresholded OBJECT-TYPE
    SYNTAX       CfprAdaptorVnicStatsHistThresholded
    MAX-ACCESS   read-only
    STATUS       current
    DESCRIPTION
        "Cisco Firepower adaptor:VnicStatsHist:thresholded
        managed object property"
    ::= { cfprAdaptorVnicStatsHistEntry 47 }

cfprAdaptorVnicStatsHistTimeCollected OBJECT-TYPE
    SYNTAX       DateAndTime
    MAX-ACCESS   read-only
    STATUS       current
    DESCRIPTION
        "Cisco Firepower adaptor:VnicStatsHist:timeCollected
        managed object property"
    ::= { cfprAdaptorVnicStatsHistEntry 48 }

cfprAdaptorVsanTable OBJECT-TYPE
    SYNTAX           SEQUENCE OF CfprAdaptorVsanEntry
    MAX-ACCESS       not-accessible
    STATUS           current
    DESCRIPTION
        "Cisco Firepower adaptor:Vsan managed object table"
    ::= { cfprAdaptorObjects 121 }

cfprAdaptorVsanEntry OBJECT-TYPE
    SYNTAX           CfprAdaptorVsanEntry
    MAX-ACCESS       not-accessible
    STATUS           current
    DESCRIPTION
        "Entry for the cfprAdaptorVsanTable table."
    INDEX { cfprAdaptorVsanInstanceId }
    ::= { cfprAdaptorVsanTable 1 }

CfprAdaptorVsanEntry ::= SEQUENCE {
    cfprAdaptorVsanInstanceId                                        CfprManagedObjectId,
    cfprAdaptorVsanDn                                                CfprManagedObjectDn,
    cfprAdaptorVsanRn                                                SnmpAdminString,
    cfprAdaptorVsanEpDn                                              SnmpAdminString,
    cfprAdaptorVsanFcoeVlan                                          Gauge32,
    cfprAdaptorVsanId                                                Gauge32,
    cfprAdaptorVsanIfRole                                            CfprFabricVnetEpIfRole,
    cfprAdaptorVsanIfType                                            CfprNetworkVnetEpIfType,
    cfprAdaptorVsanLc                                                CfprFsmLifecycle,
    cfprAdaptorVsanLocale                                            CfprFabricVnetEpLocale,
    cfprAdaptorVsanName                                              SnmpAdminString,
    cfprAdaptorVsanOperState                                         CfprFabricVsanOperState,
    cfprAdaptorVsanPeerDn                                            SnmpAdminString,
    cfprAdaptorVsanPolicyOwner                                       CfprFabricVnetEpPolicyOwner,
    cfprAdaptorVsanSwitchId                                          CfprNetworkSwitchId,
    cfprAdaptorVsanTransport                                         CfprFabricAVsanTransport,
    cfprAdaptorVsanType                                              CfprFabricAVsanType,
    cfprAdaptorVsanZoningState                                       CfprFabricZoningState
}

cfprAdaptorVsanInstanceId OBJECT-TYPE
    SYNTAX       CfprManagedObjectId
    MAX-ACCESS   not-accessible
    STATUS       current
    DESCRIPTION
        "Instance identifier of the managed object."
    ::= { cfprAdaptorVsanEntry 1 }

cfprAdaptorVsanDn OBJECT-TYPE
    SYNTAX       CfprManagedObjectDn
    MAX-ACCESS   read-only
    STATUS       current
    DESCRIPTION
        "Cisco Firepower adaptor:Vsan:dn managed object property"
    ::= { cfprAdaptorVsanEntry 2 }

cfprAdaptorVsanRn OBJECT-TYPE
    SYNTAX       SnmpAdminString
    MAX-ACCESS   read-only
    STATUS       current
    DESCRIPTION
        "Cisco Firepower adaptor:Vsan:rn managed object property"
    ::= { cfprAdaptorVsanEntry 3 }

cfprAdaptorVsanEpDn OBJECT-TYPE
    SYNTAX       SnmpAdminString
    MAX-ACCESS   read-only
    STATUS       current
    DESCRIPTION
        "Cisco Firepower adaptor:Vsan:epDn managed object property"
    ::= { cfprAdaptorVsanEntry 4 }

cfprAdaptorVsanFcoeVlan OBJECT-TYPE
    SYNTAX       Gauge32
    MAX-ACCESS   read-only
    STATUS       current
    DESCRIPTION
        "Cisco Firepower adaptor:Vsan:fcoeVlan managed object property"
    ::= { cfprAdaptorVsanEntry 5 }

cfprAdaptorVsanId OBJECT-TYPE
    SYNTAX       Gauge32
    MAX-ACCESS   read-only
    STATUS       current
    DESCRIPTION
        "Cisco Firepower adaptor:Vsan:id managed object property"
    ::= { cfprAdaptorVsanEntry 6 }

cfprAdaptorVsanIfRole OBJECT-TYPE
    SYNTAX       CfprFabricVnetEpIfRole
    MAX-ACCESS   read-only
    STATUS       current
    DESCRIPTION
        "Cisco Firepower adaptor:Vsan:ifRole managed object property"
    ::= { cfprAdaptorVsanEntry 7 }

cfprAdaptorVsanIfType OBJECT-TYPE
    SYNTAX       CfprNetworkVnetEpIfType
    MAX-ACCESS   read-only
    STATUS       current
    DESCRIPTION
        "Cisco Firepower adaptor:Vsan:ifType managed object property"
    ::= { cfprAdaptorVsanEntry 8 }

cfprAdaptorVsanLc OBJECT-TYPE
    SYNTAX       CfprFsmLifecycle
    MAX-ACCESS   read-only
    STATUS       current
    DESCRIPTION
        "Cisco Firepower adaptor:Vsan:lc managed object property"
    ::= { cfprAdaptorVsanEntry 9 }

cfprAdaptorVsanLocale OBJECT-TYPE
    SYNTAX       CfprFabricVnetEpLocale
    MAX-ACCESS   read-only
    STATUS       current
    DESCRIPTION
        "Cisco Firepower adaptor:Vsan:locale managed object property"
    ::= { cfprAdaptorVsanEntry 10 }

cfprAdaptorVsanName OBJECT-TYPE
    SYNTAX       SnmpAdminString
    MAX-ACCESS   read-only
    STATUS       current
    DESCRIPTION
        "Cisco Firepower adaptor:Vsan:name managed object property"
    ::= { cfprAdaptorVsanEntry 11 }

cfprAdaptorVsanOperState OBJECT-TYPE
    SYNTAX       CfprFabricVsanOperState
    MAX-ACCESS   read-only
    STATUS       current
    DESCRIPTION
        "Cisco Firepower adaptor:Vsan:operState managed object property"
    ::= { cfprAdaptorVsanEntry 12 }

cfprAdaptorVsanPeerDn OBJECT-TYPE
    SYNTAX       SnmpAdminString
    MAX-ACCESS   read-only
    STATUS       current
    DESCRIPTION
        "Cisco Firepower adaptor:Vsan:peerDn managed object property"
    ::= { cfprAdaptorVsanEntry 13 }

cfprAdaptorVsanPolicyOwner OBJECT-TYPE
    SYNTAX       CfprFabricVnetEpPolicyOwner
    MAX-ACCESS   read-only
    STATUS       current
    DESCRIPTION
        "Cisco Firepower adaptor:Vsan:policyOwner managed object property"
    ::= { cfprAdaptorVsanEntry 14 }

cfprAdaptorVsanSwitchId OBJECT-TYPE
    SYNTAX       CfprNetworkSwitchId
    MAX-ACCESS   read-only
    STATUS       current
    DESCRIPTION
        "Cisco Firepower adaptor:Vsan:switchId managed object property"
    ::= { cfprAdaptorVsanEntry 15 }

cfprAdaptorVsanTransport OBJECT-TYPE
    SYNTAX       CfprFabricAVsanTransport
    MAX-ACCESS   read-only
    STATUS       current
    DESCRIPTION
        "Cisco Firepower adaptor:Vsan:transport managed object property"
    ::= { cfprAdaptorVsanEntry 16 }

cfprAdaptorVsanType OBJECT-TYPE
    SYNTAX       CfprFabricAVsanType
    MAX-ACCESS   read-only
    STATUS       current
    DESCRIPTION
        "Cisco Firepower adaptor:Vsan:type managed object property"
    ::= { cfprAdaptorVsanEntry 17 }

cfprAdaptorVsanZoningState OBJECT-TYPE
    SYNTAX       CfprFabricZoningState
    MAX-ACCESS   read-only
    STATUS       current
    DESCRIPTION
        "Cisco Firepower adaptor:Vsan:zoningState managed object property"
    ::= { cfprAdaptorVsanEntry 18 }

END
