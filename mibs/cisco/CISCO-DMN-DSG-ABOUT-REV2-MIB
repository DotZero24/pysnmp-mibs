--*****************************************************************
-- CISCO_DMN_DSG_About_Rev2.mib: MIB file for board information.
--
-- May 15 2013, Ming Yao
--
-- Copyright (c) 2013 by Cisco Systems, Inc.
-- All rights reserved.
--*****************************************************************

CISCO-DMN-DSG-ABOUT-REV2-MIB

DEFINITIONS ::= BEGIN

IMPORTS
    OBJECT-TYPE,
    MODULE-IDENTITY, Integer32
        FROM SNMPv2-SMI
    DisplayString
        FROM SNMPv2-TC
    OBJECT-GROUP, MODULE-COMPLIANCE
        FROM SNMPv2-CONF
    ciscoDSGUtilities
        FROM CISCO-DMN-DSG-ROOT-MIB;


ciscoDSGAboutRev2 MODULE-IDENTITY
    LAST-UPDATED    "201305150600Z"
    ORGANIZATION    "Cisco Systems, Inc."
    CONTACT-INFO
        "Cisco Systems, Inc.
        Customer Service
        Postal: 170 W Tasman Drive
        San Jose, CA 95134
        USA
        Tel: +1 800 553 NETS

        E-mail: cs-ipsla@cisco.com"
    DESCRIPTION     "Cisco About MIB Rev 2."

    REVISION        "201305150600Z"
    DESCRIPTION     "V01.00.00 2013-05-15
                    Initial Version."

    ::= { ciscoDSGUtilities 42 }

aboutRev2Table            OBJECT IDENTIFIER ::= { ciscoDSGAboutRev2 2 }

--*****************************
-- Pcb Version Table Branch
--*****************************

pcbVersionTable OBJECT-TYPE
    SYNTAX  SEQUENCE OF PcbVersionEntry
    MAX-ACCESS  not-accessible
    STATUS  current
    DESCRIPTION
        "Pcb Version Table."
    ::={ aboutRev2Table 1 }

pcbVersionEntry  OBJECT-TYPE
    SYNTAX  PcbVersionEntry
    MAX-ACCESS  not-accessible
    STATUS  current
    DESCRIPTION
        "Entry for Pcb Version Table."
    INDEX { pcbVersionIdx }
    ::={ pcbVersionTable 1 }

PcbVersionEntry  ::= SEQUENCE
{
    pcbVersionIdx          Integer32,
    pcbVersionPosition     Integer32,
    pcbVersionID           DisplayString,
    pcbVersionRev          DisplayString,
    pcbVersionOptions      DisplayString,
    pcbVersionSerialNum    DisplayString
}

pcbVersionIdx  OBJECT-TYPE
    SYNTAX  Integer32(1..2147483647)
    MAX-ACCESS read-only
    STATUS  current
    DESCRIPTION
        "Index of PCB version Table."
    ::= { pcbVersionEntry 1 }

pcbVersionPosition  OBJECT-TYPE
    SYNTAX  Integer32(1..2147483647)
    MAX-ACCESS  read-only
    STATUS current
    DESCRIPTION
        "PCB Position."
    ::= { pcbVersionEntry 2 }

pcbVersionID OBJECT-TYPE
    SYNTAX  DisplayString(SIZE(0..32))
    MAX-ACCESS  read-only
    STATUS current
    DESCRIPTION
        "PCB identification."
    ::= { pcbVersionEntry 3 }

pcbVersionRev  OBJECT-TYPE
    SYNTAX  DisplayString(SIZE(0..32))
    MAX-ACCESS  read-only
    STATUS current
    DESCRIPTION
        "PCB Revision."
    ::= { pcbVersionEntry 4 }

pcbVersionOptions OBJECT-TYPE
    SYNTAX  DisplayString(SIZE(0..32))
    MAX-ACCESS  read-only
    STATUS current
    DESCRIPTION
        "Installation Options."
    ::= { pcbVersionEntry 5 }

pcbVersionSerialNum OBJECT-TYPE
    SYNTAX  DisplayString(SIZE(0..32))
    MAX-ACCESS  read-only
    STATUS current
    DESCRIPTION
        "PCB Serial Number."
    ::= { pcbVersionEntry 6 }


--***********************************
-- Firmware Version Table Branch
--***********************************

firmwareVersionTable OBJECT-TYPE
    SYNTAX  SEQUENCE OF FirmwareVersionEntry
    MAX-ACCESS  not-accessible
    STATUS current
    DESCRIPTION
        "Firmware Version Table."
    ::={ aboutRev2Table 2 }

firmwareVersionEntry  OBJECT-TYPE
    SYNTAX  FirmwareVersionEntry
    MAX-ACCESS  not-accessible
    STATUS current
    DESCRIPTION
        "Entry for Firmware Version Table."
    INDEX { firmwareVersionBoard, firmwareVersionrow }
    ::= { firmwareVersionTable 1 }

FirmwareVersionEntry ::= SEQUENCE
{
    firmwareVersionBoard           Integer32,
    firmwareVersionrow             Integer32,
    firmwareVersionID              DisplayString,
    firmwareVersionVersion         DisplayString,
    firmwareVersionValidationCode  Integer32
}

firmwareVersionBoard  OBJECT-TYPE
    SYNTAX  Integer32( 1..2147483647 )
    MAX-ACCESS  read-only
    STATUS current
    DESCRIPTION
        "Board index of Firmware Version Table."
    ::= { firmwareVersionEntry 1 }

firmwareVersionrow  OBJECT-TYPE
    SYNTAX  Integer32( 1..2147483647 )
    MAX-ACCESS  read-only
    STATUS current
    DESCRIPTION
        "Row index of Firmware Version on each board."
    ::= { firmwareVersionEntry 2 }

firmwareVersionID  OBJECT-TYPE
    SYNTAX  DisplayString(SIZE(0..32))
    MAX-ACCESS  read-only
    STATUS current
    DESCRIPTION
        "Firware Version Identification."
    ::= { firmwareVersionEntry 3 }

firmwareVersionVersion  OBJECT-TYPE
    SYNTAX  DisplayString(SIZE(0..32))
    MAX-ACCESS  read-only
    STATUS current
    DESCRIPTION
        "Firware Version Numbers."
    ::= { firmwareVersionEntry 4 }

firmwareVersionValidationCode  OBJECT-TYPE
    SYNTAX  Integer32( 1..2147483647 )
    MAX-ACCESS  read-only
    STATUS current
    DESCRIPTION
        "Firware Validation Code."
    ::= { firmwareVersionEntry 5 }

--***********************************
-- Current App Table Branch
--***********************************

currentAppTable OBJECT-TYPE
    SYNTAX  SEQUENCE OF CurrenAppEntry
    MAX-ACCESS  not-accessible
    STATUS current
    DESCRIPTION
        "Current App Table."
    ::={ aboutRev2Table 3 }

currentAppEntry  OBJECT-TYPE
    SYNTAX  CurrenAppEntry
    MAX-ACCESS  not-accessible
    STATUS current
    DESCRIPTION
        "Entry for Current App Table."
    INDEX { currentAppBoard, currentApprow }
    ::= { currentAppTable 1 }

CurrenAppEntry ::= SEQUENCE
{
    currentAppBoard           Integer32,
    currentApprow             Integer32,
    currentAppID              DisplayString,
    currentAppVersion         DisplayString,
    currentAppValidationCode  Integer32
}

currentAppBoard  OBJECT-TYPE
    SYNTAX  Integer32( 1..2147483647 )
    MAX-ACCESS  read-only
    STATUS current
    DESCRIPTION
        "Board index of Current App Table."
    ::= { currentAppEntry 1 }

currentApprow  OBJECT-TYPE
    SYNTAX  Integer32( 1..2147483647 )
    MAX-ACCESS  read-only
    STATUS current
    DESCRIPTION
        "Row index of Current App on each board."
    ::= { currentAppEntry 2 }

currentAppID  OBJECT-TYPE
    SYNTAX  DisplayString(SIZE(0..32))
    MAX-ACCESS  read-only
    STATUS current
    DESCRIPTION
        "Current App Identification."
    ::= { currentAppEntry 3 }

currentAppVersion  OBJECT-TYPE
    SYNTAX  DisplayString(SIZE(0..32))
    MAX-ACCESS  read-only
    STATUS current
    DESCRIPTION
        "Current App Version Numbers."
    ::= { currentAppEntry 4 }

currentAppValidationCode  OBJECT-TYPE
    SYNTAX  Integer32( 1..2147483647 )
    MAX-ACCESS  read-only
    STATUS current
    DESCRIPTION
        "Current App Validation Code."
    ::= { currentAppEntry 5 }

--***********************************
-- Current Fpga Table Branch
--***********************************

currentFpgaTable OBJECT-TYPE
    SYNTAX  SEQUENCE OF CurrenFpgaEntry
    MAX-ACCESS  not-accessible
    STATUS current
    DESCRIPTION
        "Current Fpga Table."
    ::={ aboutRev2Table 4 }

currentFpgaEntry  OBJECT-TYPE
    SYNTAX  CurrenFpgaEntry
    MAX-ACCESS  not-accessible
    STATUS current
    DESCRIPTION
        "Entry for Current Fpga Table."
    INDEX { currentFpgaBoard, currentFpgarow }
    ::= { currentFpgaTable 1 }

CurrenFpgaEntry ::= SEQUENCE
{
    currentFpgaBoard           Integer32,
    currentFpgarow             Integer32,
    currentFpgaID              DisplayString,
    currentFpgaVersion         DisplayString,
    currentFpgaValidationCode  Integer32
}

currentFpgaBoard  OBJECT-TYPE
    SYNTAX  Integer32( 1..2147483647 )
    MAX-ACCESS  read-only
    STATUS current
    DESCRIPTION
        "Board index of Current Fpga Table."
    ::= { currentFpgaEntry 1 }

currentFpgarow  OBJECT-TYPE
    SYNTAX  Integer32( 1..2147483647 )
    MAX-ACCESS  read-only
    STATUS current
    DESCRIPTION
        "Row index of Current Fpga on each board."
    ::= { currentFpgaEntry 2 }

currentFpgaID  OBJECT-TYPE
    SYNTAX  DisplayString(SIZE(0..32))
    MAX-ACCESS  read-only
    STATUS current
    DESCRIPTION
        "Current Fpga Identification."
    ::= { currentFpgaEntry 3 }

currentFpgaVersion  OBJECT-TYPE
    SYNTAX  DisplayString(SIZE(0..32))
    MAX-ACCESS  read-only
    STATUS current
    DESCRIPTION
        "Current Fpga Version Numbers."
    ::= { currentFpgaEntry 4 }

currentFpgaValidationCode  OBJECT-TYPE
    SYNTAX  Integer32( 1..2147483647 )
    MAX-ACCESS  read-only
    STATUS current
    DESCRIPTION
        "Current Fpga Validation Code."
    ::= { currentFpgaEntry 5 }


--***********************************
-- Runnable App Table Branch
--***********************************

runnableAppTable OBJECT-TYPE
    SYNTAX  SEQUENCE OF RunnableAppEntry
    MAX-ACCESS  not-accessible
    STATUS current
    DESCRIPTION
        "Runnable App Table."
    ::= { aboutRev2Table 5 }

runnableAppEntry  OBJECT-TYPE
    SYNTAX  RunnableAppEntry
    MAX-ACCESS  not-accessible
    STATUS current
    DESCRIPTION
        "Entry for Runnable App Table."
    INDEX { runnableAppIdx }
    ::= { runnableAppTable 1 }

RunnableAppEntry ::= SEQUENCE
{
    runnableAppIdx             Integer32,
    runnableAppFileIdx         Integer32,
    runnableAppVersion         DisplayString,
    runnableAppSelect          INTEGER,
    runnableAppErase           INTEGER
}

runnableAppIdx  OBJECT-TYPE
    SYNTAX  Integer32(1..2147483647)
    MAX-ACCESS  read-only
    STATUS  current
    DESCRIPTION
        "Runnable App Table Index."
    ::= { runnableAppEntry 1 }

runnableAppFileIdx  OBJECT-TYPE
    SYNTAX  Integer32(1..2147483647)
    MAX-ACCESS  read-only
    STATUS  current
    DESCRIPTION
        "File Index in Nonvolatile File System."
    ::= { runnableAppEntry 2 }

runnableAppVersion  OBJECT-TYPE
    SYNTAX  DisplayString(SIZE(0..32))
    MAX-ACCESS  read-only
    STATUS  current
    DESCRIPTION
        "Runnable App Version."
    ::= { runnableAppEntry 3 }

runnableAppSelect OBJECT-TYPE
    SYNTAX  INTEGER {
            no(1),
            yes(2)
        }
    MAX-ACCESS  read-write
    STATUS  current
    DESCRIPTION
        "Select yes to change Runnable App."
    ::= { runnableAppEntry 4 }

runnableAppErase  OBJECT-TYPE
    SYNTAX  INTEGER {
            no(1),
            yes(2)
        }
    MAX-ACCESS  read-write
    STATUS  current
    DESCRIPTION
        "Select yes to erase Runnable App."
    ::= { runnableAppEntry 5 }

--***********************************
-- Runnable Fpga Table Branch
--***********************************

runnableFpgaTable OBJECT-TYPE
    SYNTAX  SEQUENCE OF RunnableFpgaEntry
    MAX-ACCESS  not-accessible
    STATUS current
    DESCRIPTION
        "Runnable Fpga Table."
    ::= { aboutRev2Table 6 }

runnableFpgaEntry  OBJECT-TYPE
    SYNTAX  RunnableFpgaEntry
    MAX-ACCESS  not-accessible
    STATUS current
    DESCRIPTION
        "Entry for Runnable Fpga Table."
    INDEX { runnableFpgaIdx }
    ::= { runnableFpgaTable 1 }

RunnableFpgaEntry ::= SEQUENCE
{
    runnableFpgaIdx             Integer32,
    runnableFpgaFileIdx         Integer32,
    runnableFpgaVersion         DisplayString,
    runnableFpgaSelect          INTEGER,
    runnableFpgaErase           INTEGER
}

runnableFpgaIdx  OBJECT-TYPE
    SYNTAX  Integer32(1..2147483647)
    MAX-ACCESS  read-only
    STATUS  current
    DESCRIPTION
        "Runnable Fpga Table Index."
    ::= { runnableFpgaEntry 1 }

runnableFpgaFileIdx  OBJECT-TYPE
    SYNTAX  Integer32(1..2147483647)
    MAX-ACCESS  read-only
    STATUS  current
    DESCRIPTION
        "File Index in Nonvolatile File System."
    ::= { runnableFpgaEntry 2 }

runnableFpgaVersion  OBJECT-TYPE
    SYNTAX  DisplayString(SIZE(0..32))
    MAX-ACCESS  read-only
    STATUS  current
    DESCRIPTION
        "Runnable Fpga Version."
    ::= { runnableFpgaEntry 3 }

runnableFpgaSelect OBJECT-TYPE
    SYNTAX  INTEGER {
            no(1),
            yes(2)
        }
    MAX-ACCESS  read-write
    STATUS  current
    DESCRIPTION
        "Select yes to change Runnable Fpga."
    ::= { runnableFpgaEntry 4 }

runnableFpgaErase  OBJECT-TYPE
    SYNTAX  INTEGER {
            no(1),
            yes(2)
        }
    MAX-ACCESS  read-write
    STATUS  current
    DESCRIPTION
        "Select yes to erase Runnable Fpga."
    ::= { runnableFpgaEntry 5 }

--***********************************
-- Runnable FecFpga Table Branch
--***********************************

runnableFecFpgaTable OBJECT-TYPE
    SYNTAX  SEQUENCE OF RunnableFecFpgaEntry
    MAX-ACCESS  not-accessible
    STATUS current
    DESCRIPTION
        "Runnable FecFpga Table."
    ::= { aboutRev2Table 7 }

runnableFecFpgaEntry  OBJECT-TYPE
    SYNTAX  RunnableFecFpgaEntry
    MAX-ACCESS  not-accessible
    STATUS current
    DESCRIPTION
        "Entry for Runnable FecFpga Table."
    INDEX { runnableFecFpgaIdx }
    ::= { runnableFecFpgaTable 1 }

RunnableFecFpgaEntry ::= SEQUENCE
{
    runnableFecFpgaIdx             Integer32,
    runnableFecFpgaFileIdx         Integer32,
    runnableFecFpgaVersion         DisplayString,
    runnableFecFpgaSelect          INTEGER,
    runnableFecFpgaErase           INTEGER
}

runnableFecFpgaIdx  OBJECT-TYPE
    SYNTAX  Integer32(1..2147483647)
    MAX-ACCESS  read-only
    STATUS  current
    DESCRIPTION
        "Runnable FecFpga Table Index."
    ::= { runnableFecFpgaEntry 1 }

runnableFecFpgaFileIdx  OBJECT-TYPE
    SYNTAX  Integer32(1..2147483647)
    MAX-ACCESS  read-only
    STATUS  current
    DESCRIPTION
        "File Index in Nonvolatile File System."
    ::= { runnableFecFpgaEntry 2 }

runnableFecFpgaVersion  OBJECT-TYPE
    SYNTAX  DisplayString(SIZE(0..32))
    MAX-ACCESS  read-only
    STATUS  current
    DESCRIPTION
        "Runnable FecFpga Version."
    ::= { runnableFecFpgaEntry 3 }

runnableFecFpgaSelect OBJECT-TYPE
    SYNTAX  INTEGER {
            no(1),
            yes(2)
        }
    MAX-ACCESS  read-write
    STATUS  current
    DESCRIPTION
        "Select yes to change Runnable FecFpga."
    ::= { runnableFecFpgaEntry 4 }

runnableFecFpgaErase  OBJECT-TYPE
    SYNTAX  INTEGER {
            no(1),
            yes(2)
        }
    MAX-ACCESS  read-write
    STATUS  current
    DESCRIPTION
        "Select yes to erase Runnable FecFpga."
    ::= { runnableFecFpgaEntry 5 }
END
