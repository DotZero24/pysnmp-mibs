-- *********************************************************************
-- CISCO-FIREPOWER-TC-MIB.my
--
-- MIB representation of the Cisco Firepower
-- TEXTUALCONVENTIONS management information model package
--
-- Created March 2020 by Charles Bullis
--
-- Copyright (c) 2005-2020 Cisco Systems, Inc. All rights reserved.
--
-- *********************************************************************

CISCO-FIREPOWER-TC-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIB,
    CfprManagedObjectId,
    CfprManagedObjectDn
        FROM CISCO-FIREPOWER-MIB;

cfprTextualConventionsObjects MODULE-IDENTITY
    LAST-UPDATED    "202003100000Z"
    ORGANIZATION    "Cisco Systems Inc."
    CONTACT-INFO
        "Cisco Systems
        Customer Service

        Postal: 170 W Tasman Drive
        San Jose, CA  95134
        USA

        Tel: +1 800 553-NETS

        E-mail: firepower-mibs@cisco.com"
    DESCRIPTION
        "MIB representation of the Cisco Firepower
        TEXTUALCONVENTIONS management information model package"
    ::= { ciscoFirepowerMIB 4 }

CfprAaaAccess ::= TEXTUAL-CONVENTION
    STATUS        current
    DESCRIPTION
        ""
    SYNTAX        BITS
    {
        readOnly(0),
        admin(1),
        operations(2),
        fault(3),
        aaa(4),
        podConfig(5),
        podPolicy(6),
        podSecurity(7),
        podQos(8),
        extLanConfig(9),
        extLanPolicy(10),
        extLanSecurity(11),
        extLanQos(12),
        extSanConfig(13),
        extSanPolicy(14),
        extSanSecurity(15),
        extSanQos(16),
        pnEquipment(17),
        pnPolicy(18),
        pnSecurity(19),
        pnMaintenance(20),
        lsConfig(21),
        lsStorage(22),
        lsNetwork(23),
        lsSecurity(24),
        lsServer(25),
        lsQos(26),
        lsConfigPolicy(27),
        lsStoragePolicy(28),
        lsNetworkPolicy(29),
        lsSecurityPolicy(30),
        lsServerPolicy(31),
        lsQosPolicy(32),
        lsExtAccess(33),
        powerMgmt(34),
        lsServerOper(36),
        lsCompute(37),
        orgManagement(38)
    }

CfprAaaAccountStatus ::= TEXTUAL-CONVENTION
    STATUS        current
    DESCRIPTION
        ""
    SYNTAX        INTEGER
    {
        active(0),
        inactive(1)
    }

CfprAaaAuthRealmFsmCurrentFsm ::= TEXTUAL-CONVENTION
    STATUS        current
    DESCRIPTION
        ""
    SYNTAX        INTEGER
    {
        nop(0),
        updateRealm(200)
    }

CfprAaaAuthRealmFsmStageName ::= TEXTUAL-CONVENTION
    STATUS        current
    DESCRIPTION
        ""
    SYNTAX        INTEGER
    {
        nop(0),
        updateRealmBegin(200),
        updateRealmSetRealmLocal(201),
        updateRealmSetRealmPeer(202),
        updateRealmFail(324),
        updateRealmSuccess(325)
    }

CfprAaaCimcSessionType ::= TEXTUAL-CONVENTION
    STATUS        current
    DESCRIPTION
        ""
    SYNTAX        INTEGER
    {
        all(0),
        kvm(1),
        vmedia(2),
        sol(3)
    }

CfprAaaCipherMode ::= TEXTUAL-CONVENTION
    STATUS        current
    DESCRIPTION
        ""
    SYNTAX        INTEGER
    {
        custom(0),
        highStrength(1),
        lowStrength(2),
        mediumStrength(3)
    }

CfprAaaClear ::= TEXTUAL-CONVENTION
    STATUS        current
    DESCRIPTION
        ""
    SYNTAX        INTEGER
    {
        no(0),
        yes(1)
    }

CfprAaaConfigState ::= TEXTUAL-CONVENTION
    STATUS        current
    DESCRIPTION
        ""
    SYNTAX        INTEGER
    {
        ok(0),
        notApplied(1)
    }

CfprAaaDomainAuthRealm ::= TEXTUAL-CONVENTION
    STATUS        current
    DESCRIPTION
        ""
    SYNTAX        INTEGER
    {
        local(0),
        radius(1),
        tacacs(2),
        ldap(3),
        none(4)
    }

CfprAaaEpAccess ::= TEXTUAL-CONVENTION
    STATUS        current
    DESCRIPTION
        ""
    SYNTAX        INTEGER
    {
        readonly(1),
        admin(2)
    }

CfprAaaEpFsmCurrentFsm ::= TEXTUAL-CONVENTION
    STATUS        current
    DESCRIPTION
        ""
    SYNTAX        INTEGER
    {
        nop(0),
        updateEp(197)
    }

CfprAaaEpFsmStageName ::= TEXTUAL-CONVENTION
    STATUS        current
    DESCRIPTION
        ""
    SYNTAX        INTEGER
    {
        nop(0),
        updateEpBegin(197),
        updateEpSetEpLocal(198),
        updateEpSetEpPeer(199),
        updateEpFail(322),
        updateEpSuccess(323)
    }

CfprAaaEpFsmTaskItem ::= TEXTUAL-CONVENTION
    STATUS        current
    DESCRIPTION
        ""
    SYNTAX        INTEGER
    {
        nop(0),
        updateEp(197)
    }

CfprAaaExtMgmtAccess ::= TEXTUAL-CONVENTION
    STATUS        current
    DESCRIPTION
        ""
    SYNTAX        INTEGER
    {
        kvm(1)
    }

CfprAaaIpmiOverLan ::= TEXTUAL-CONVENTION
    STATUS        current
    DESCRIPTION
        ""
    SYNTAX        INTEGER
    {
        disable(0),
        enable(1)
    }

CfprAaaLdapEpFsmCurrentFsm ::= TEXTUAL-CONVENTION
    STATUS        current
    DESCRIPTION
        ""
    SYNTAX        INTEGER
    {
        nop(0),
        updateEp(197)
    }

CfprAaaLdapEpFsmStageName ::= TEXTUAL-CONVENTION
    STATUS        current
    DESCRIPTION
        ""
    SYNTAX        INTEGER
    {
        nop(0),
        updateEpBegin(197),
        updateEpSetEpLocal(198),
        updateEpSetEpPeer(199),
        updateEpFail(322),
        updateEpSuccess(323)
    }

CfprAaaLdapGroupRuleAuthorization ::= TEXTUAL-CONVENTION
    STATUS        current
    DESCRIPTION
        ""
    SYNTAX        INTEGER
    {
        disable(0),
        enable(1)
    }

CfprAaaLdapGroupRuleTraversal ::= TEXTUAL-CONVENTION
    STATUS        current
    DESCRIPTION
        ""
    SYNTAX        INTEGER
    {
        nonRecursive(0),
        recursive(1)
    }

CfprAaaLdapVendor ::= TEXTUAL-CONVENTION
    STATUS        current
    DESCRIPTION
        ""
    SYNTAX        INTEGER
    {
        openLdap(0),
        msAd(1)
    }

CfprAaaNoRolePolicy ::= TEXTUAL-CONVENTION
    STATUS        current
    DESCRIPTION
        ""
    SYNTAX        INTEGER
    {
        noLogin(0),
        assignDefaultRole(1)
    }

CfprAaaPwdPolicy ::= TEXTUAL-CONVENTION
    STATUS        current
    DESCRIPTION
        ""
    SYNTAX        INTEGER
    {
        enable(0),
        disable(1)
    }

CfprAaaRadiusEpFsmCurrentFsm ::= TEXTUAL-CONVENTION
    STATUS        current
    DESCRIPTION
        ""
    SYNTAX        INTEGER
    {
        nop(0),
        updateEp(197)
    }

CfprAaaRadiusEpFsmStageName ::= TEXTUAL-CONVENTION
    STATUS        current
    DESCRIPTION
        ""
    SYNTAX        INTEGER
    {
        nop(0),
        updateEpBegin(197),
        updateEpSetEpLocal(198),
        updateEpSetEpPeer(199),
        updateEpFail(322),
        updateEpSuccess(323)
    }

CfprAaaRadiusService ::= TEXTUAL-CONVENTION
    STATUS        current
    DESCRIPTION
        ""
    SYNTAX        INTEGER
    {
        all(0),
        authorization(1),
        accounting(2)
    }

CfprAaaRealm ::= TEXTUAL-CONVENTION
    STATUS        current
    DESCRIPTION
        ""
    SYNTAX        INTEGER
    {
        local(0),
        radius(1),
        tacacs(2),
        ldap(3),
        none(4)
    }

CfprAaaRealmFsmCurrentFsm ::= TEXTUAL-CONVENTION
    STATUS        current
    DESCRIPTION
        ""
    SYNTAX        INTEGER
    {
        nop(0),
        updateRealm(200)
    }

CfprAaaRealmFsmStageName ::= TEXTUAL-CONVENTION
    STATUS        current
    DESCRIPTION
        ""
    SYNTAX        INTEGER
    {
        nop(0),
        updateRealmBegin(200),
        updateRealmSetRealmLocal(201),
        updateRealmSetRealmPeer(202),
        updateRealmFail(324),
        updateRealmSuccess(325)
    }

CfprAaaRealmFsmTaskItem ::= TEXTUAL-CONVENTION
    STATUS        current
    DESCRIPTION
        ""
    SYNTAX        INTEGER
    {
        nop(0),
        updateRealm(200)
    }

CfprAaaRevokePolicy ::= TEXTUAL-CONVENTION
    STATUS        current
    DESCRIPTION
        ""
    SYNTAX        INTEGER
    {
        relaxed(0),
        strict(1)
    }

CfprAaaSession ::= TEXTUAL-CONVENTION
    STATUS        current
    DESCRIPTION
        ""
    SYNTAX        INTEGER
    {
        local(0),
        remote(1),
        ipmi(2)
    }

CfprAaaSessionState ::= TEXTUAL-CONVENTION
    STATUS        current
    DESCRIPTION
        ""
    SYNTAX        INTEGER
    {
        active(0),
        inactive(1)
    }

CfprAaaSshStr ::= TEXTUAL-CONVENTION
    STATUS        current
    DESCRIPTION
        ""
    SYNTAX        INTEGER
    {
        none(0),
        key(1)
    }

CfprAaaTacacsPlusEpFsmCurrentFsm ::= TEXTUAL-CONVENTION
    STATUS        current
    DESCRIPTION
        ""
    SYNTAX        INTEGER
    {
        nop(0),
        updateEp(197)
    }

CfprAaaTacacsPlusEpFsmStageName ::= TEXTUAL-CONVENTION
    STATUS        current
    DESCRIPTION
        ""
    SYNTAX        INTEGER
    {
        nop(0),
        updateEpBegin(197),
        updateEpSetEpLocal(198),
        updateEpSetEpPeer(199),
        updateEpFail(322),
        updateEpSuccess(323)
    }

CfprAaaUserEpFsmCurrentFsm ::= TEXTUAL-CONVENTION
    STATUS        current
    DESCRIPTION
        ""
    SYNTAX        INTEGER
    {
        nop(0),
        updateUserEp(203)
    }

CfprAaaUserEpFsmStageName ::= TEXTUAL-CONVENTION
    STATUS        current
    DESCRIPTION
        ""
    SYNTAX        INTEGER
    {
        nop(0),
        updateUserEpBegin(203),
        updateUserEpSetUserLocal(204),
        updateUserEpSetUserPeer(205),
        updateUserEpFail(326),
        updateUserEpSuccess(327)
    }

CfprAaaUserEpFsmTaskItem ::= TEXTUAL-CONVENTION
    STATUS        current
    DESCRIPTION
        ""
    SYNTAX        INTEGER
    {
        nop(0),
        updateUserEp(203)
    }

CfprAaaUserInterface ::= TEXTUAL-CONVENTION
    STATUS        current
    DESCRIPTION
        ""
    SYNTAX        INTEGER
    {
        none(0),
        shell(1),
        web(2),
        ep(3),
        kvm(4),
        vmedia(5),
        sol(6)
    }

CfprAdaptorAdapterStatsTrafficDir ::= TEXTUAL-CONVENTION
    STATUS        current
    DESCRIPTION
        ""
    SYNTAX        INTEGER
    {
        unknown(0),
        tx(1),
        rx(2)
    }

CfprAdaptorAdminPowerState ::= TEXTUAL-CONVENTION
    STATUS        current
    DESCRIPTION
        ""
    SYNTAX        INTEGER
    {
        none(0),
        resetPower(1)
    }

CfprAdaptorCIoEpIfType ::= TEXTUAL-CONVENTION
    STATUS        current
    DESCRIPTION
        ""
    SYNTAX        INTEGER
    {
        unknown(0),
        physical(1),
        aggregation(2),
        virtual(3)
    }

CfprAdaptorCapDefFwVersionOpr ::= TEXTUAL-CONVENTION
    STATUS        current
    DESCRIPTION
        ""
    SYNTAX        INTEGER
    {
        none(0),
        gt(1),
        lt(2),
        range(3)
    }

CfprAdaptorCapDefType ::= TEXTUAL-CONVENTION
    STATUS        current
    DESCRIPTION
        ""
    SYNTAX        INTEGER
    {
        virtualizedEthIf(1),
        virtualizedFcIf(2),
        virtualizedScsiIf(3),
        nonVirtualizedEthIf(4),
        nonVirtualizedFcIf(5),
        fcoe(6),
        protectedEthIf(7),
        protectedFcIf(8),
        protectedFcoe(9),
        pathEncapVirtual(10),
        pathEncapConsolidated(11),
        uplinkAggregation(12),
        virtualizedEthSriov(13),
        virtualizedFcSriov(14),
        virtualizedEthSriovUsnic(15),
        virtualizedEthVmq(16),
        ethFlowMonitoringNetflow(17),
        ethRoce(18),
        ethVxlan(19),
        ethNvgre(20)
    }

CfprAdaptorCapSpecType ::= TEXTUAL-CONVENTION
    STATUS        current
    DESCRIPTION
        ""
    SYNTAX        INTEGER
    {
        virtualizedEthIf(1),
        virtualizedFcIf(2),
        virtualizedScsiIf(3),
        nonVirtualizedEthIf(4),
        nonVirtualizedFcIf(5),
        fcoe(6),
        protectedEthIf(7),
        protectedFcIf(8),
        protectedFcoe(9),
        pathEncapVirtual(10),
        pathEncapConsolidated(11),
        uplinkAggregation(12),
        virtualizedEthSriov(13),
        virtualizedFcSriov(14),
        virtualizedEthSriovUsnic(15),
        virtualizedEthVmq(16),
        ethFlowMonitoringNetflow(17),
        ethRoce(18),
        ethVxlan(19),
        ethNvgre(20)
    }

CfprAdaptorDefaultAction ::= TEXTUAL-CONVENTION
    STATUS        current
    DESCRIPTION
        ""
    SYNTAX        INTEGER
    {
        no(0),
        yes(1)
    }

CfprAdaptorEthArfsProfileAccelaratedRFS ::= TEXTUAL-CONVENTION
    STATUS        current
    DESCRIPTION
        ""
    SYNTAX        INTEGER
    {
        disabled(0),
        enabled(1)
    }

CfprAdaptorEthInterruptProfileCoalescingType ::= TEXTUAL-CONVENTION
    STATUS        current
    DESCRIPTION
        ""
    SYNTAX        INTEGER
    {
        min(0),
        idle(1)
    }

CfprAdaptorEthNVGREProfileAdminState ::= TEXTUAL-CONVENTION
    STATUS        current
    DESCRIPTION
        ""
    SYNTAX        INTEGER
    {
        disabled(0),
        enabled(1)
    }

CfprAdaptorEthOffloadProfileLargeReceive ::= TEXTUAL-CONVENTION
    STATUS        current
    DESCRIPTION
        ""
    SYNTAX        INTEGER
    {
        disabled(0),
        enabled(1)
    }

CfprAdaptorEthOffloadProfileTcpRxChecksum ::= TEXTUAL-CONVENTION
    STATUS        current
    DESCRIPTION
        ""
    SYNTAX        INTEGER
    {
        disabled(0),
        enabled(1)
    }

CfprAdaptorEthOffloadProfileTcpSegment ::= TEXTUAL-CONVENTION
    STATUS        current
    DESCRIPTION
        ""
    SYNTAX        INTEGER
    {
        disabled(0),
        enabled(1)
    }

CfprAdaptorEthOffloadProfileTcpTxChecksum ::= TEXTUAL-CONVENTION
    STATUS        current
    DESCRIPTION
        ""
    SYNTAX        INTEGER
    {
        disabled(0),
        enabled(1)
    }

CfprAdaptorEthPortBySizeLargeStatsThresholded ::= TEXTUAL-CONVENTION
    STATUS        current
    DESCRIPTION
        ""
    SYNTAX        BITS
    {
        greaterThanOrEqualTo9216Delta(0),
        greaterThanOrEqualTo9216DeltaAvg(1),
        greaterThanOrEqualTo9216DeltaMax(2),
        greaterThanOrEqualTo9216DeltaMin(3),
        lessThan2048Delta(4),
        lessThan2048DeltaAvg(5),
        lessThan2048DeltaMax(6),
        lessThan2048DeltaMin(7),
        lessThan4096Delta(8),
        lessThan4096DeltaAvg(9),
        lessThan4096DeltaMax(10),
        lessThan4096DeltaMin(11),
        lessThan8192Delta(12),
        lessThan8192DeltaAvg(13),
        lessThan8192DeltaMax(14),
        lessThan8192DeltaMin(15),
        lessThan9216Delta(16),
        lessThan9216DeltaAvg(17),
        lessThan9216DeltaMax(18),
        lessThan9216DeltaMin(19),
        lessThanOrEqualTo1518Delta(20),
        lessThanOrEqualTo1518DeltaAvg(21),
        lessThanOrEqualTo1518DeltaMax(22),
        lessThanOrEqualTo1518DeltaMin(23),
        noBreakdownGreaterThan1518Delta(24),
        noBreakdownGreaterThan1518DeltaAvg(25),
        noBreakdownGreaterThan1518DeltaMax(26),
        noBreakdownGreaterThan1518DeltaMin(27)
    }

CfprAdaptorEthPortBySizeLargeStatsHistThresholded ::= TEXTUAL-CONVENTION
    STATUS        current
    DESCRIPTION
        ""
    SYNTAX        BITS
    {
        greaterThanOrEqualTo9216Delta(0),
        greaterThanOrEqualTo9216DeltaAvg(1),
        greaterThanOrEqualTo9216DeltaMax(2),
        greaterThanOrEqualTo9216DeltaMin(3),
        lessThan2048Delta(4),
        lessThan2048DeltaAvg(5),
        lessThan2048DeltaMax(6),
        lessThan2048DeltaMin(7),
        lessThan4096Delta(8),
        lessThan4096DeltaAvg(9),
        lessThan4096DeltaMax(10),
        lessThan4096DeltaMin(11),
        lessThan8192Delta(12),
        lessThan8192DeltaAvg(13),
        lessThan8192DeltaMax(14),
        lessThan8192DeltaMin(15),
        lessThan9216Delta(16),
        lessThan9216DeltaAvg(17),
        lessThan9216DeltaMax(18),
        lessThan9216DeltaMin(19),
        lessThanOrEqualTo1518Delta(20),
        lessThanOrEqualTo1518DeltaAvg(21),
        lessThanOrEqualTo1518DeltaMax(22),
        lessThanOrEqualTo1518DeltaMin(23),
        noBreakdownGreaterThan1518Delta(24),
        noBreakdownGreaterThan1518DeltaAvg(25),
        noBreakdownGreaterThan1518DeltaMax(26),
        noBreakdownGreaterThan1518DeltaMin(27)
    }

CfprAdaptorEthPortBySizeSmallStatsThresholded ::= TEXTUAL-CONVENTION
    STATUS        current
    DESCRIPTION
        ""
    SYNTAX        BITS
    {
        equals64Delta(0),
        equals64DeltaAvg(1),
        equals64DeltaMax(2),
        equals64DeltaMin(3),
        lessThan1024Delta(4),
        lessThan1024DeltaAvg(5),
        lessThan1024DeltaMax(6),
        lessThan1024DeltaMin(7),
        lessThan128Delta(8),
        lessThan128DeltaAvg(9),
        lessThan128DeltaMax(10),
        lessThan128DeltaMin(11),
        lessThan256Delta(12),
        lessThan256DeltaAvg(13),
        lessThan256DeltaMax(14),
        lessThan256DeltaMin(15),
        lessThan512Delta(16),
        lessThan512DeltaAvg(17),
        lessThan512DeltaMax(18),
        lessThan512DeltaMin(19),
        lessThan64Delta(20),
        lessThan64DeltaAvg(21),
        lessThan64DeltaMax(22),
        lessThan64DeltaMin(23)
    }

CfprAdaptorEthPortBySizeSmallStatsHistThresholded ::= TEXTUAL-CONVENTION
    STATUS        current
    DESCRIPTION
        ""
    SYNTAX        BITS
    {
        equals64Delta(0),
        equals64DeltaAvg(1),
        equals64DeltaMax(2),
        equals64DeltaMin(3),
        lessThan1024Delta(4),
        lessThan1024DeltaAvg(5),
        lessThan1024DeltaMax(6),
        lessThan1024DeltaMin(7),
        lessThan128Delta(8),
        lessThan128DeltaAvg(9),
        lessThan128DeltaMax(10),
        lessThan128DeltaMin(11),
        lessThan256Delta(12),
        lessThan256DeltaAvg(13),
        lessThan256DeltaMax(14),
        lessThan256DeltaMin(15),
        lessThan512Delta(16),
        lessThan512DeltaAvg(17),
        lessThan512DeltaMax(18),
        lessThan512DeltaMin(19),
        lessThan64Delta(20),
        lessThan64DeltaAvg(21),
        lessThan64DeltaMax(22),
        lessThan64DeltaMin(23)
    }

CfprAdaptorEthPortErrStatsThresholded ::= TEXTUAL-CONVENTION
    STATUS        current
    DESCRIPTION
        ""
    SYNTAX        BITS
    {
        badCrcPacketsDelta(0),
        badCrcPacketsDeltaAvg(1),
        badCrcPacketsDeltaMax(2),
        badCrcPacketsDeltaMin(3),
        badLengthPacketsDelta(4),
        badLengthPacketsDeltaAvg(5),
        badLengthPacketsDeltaMax(6),
        badLengthPacketsDeltaMin(7),
        macDiscardedPacketsDelta(8),
        macDiscardedPacketsDeltaAvg(9),
        macDiscardedPacketsDeltaMax(10),
        macDiscardedPacketsDeltaMin(11)
    }

CfprAdaptorEthPortErrStatsHistThresholded ::= TEXTUAL-CONVENTION
    STATUS        current
    DESCRIPTION
        ""
    SYNTAX        BITS
    {
        badCrcPacketsDelta(0),
        badCrcPacketsDeltaAvg(1),
        badCrcPacketsDeltaMax(2),
        badCrcPacketsDeltaMin(3),
        badLengthPacketsDelta(4),
        badLengthPacketsDeltaAvg(5),
        badLengthPacketsDeltaMax(6),
        badLengthPacketsDeltaMin(7),
        macDiscardedPacketsDelta(8),
        macDiscardedPacketsDeltaAvg(9),
        macDiscardedPacketsDeltaMax(10),
        macDiscardedPacketsDeltaMin(11)
    }

CfprAdaptorEthPortMcastStatsThresholded ::= TEXTUAL-CONVENTION
    STATUS        current
    DESCRIPTION
        ""
    SYNTAX        BITS
    {
        broadcastPacketsDelta(0),
        broadcastPacketsDeltaAvg(1),
        broadcastPacketsDeltaMax(2),
        broadcastPacketsDeltaMin(3),
        multicastPacketsDelta(4),
        multicastPacketsDeltaAvg(5),
        multicastPacketsDeltaMax(6),
        multicastPacketsDeltaMin(7),
        unicastPacketsDelta(8),
        unicastPacketsDeltaAvg(9),
        unicastPacketsDeltaMax(10),
        unicastPacketsDeltaMin(11)
    }

CfprAdaptorEthPortMcastStatsHistThresholded ::= TEXTUAL-CONVENTION
    STATUS        current
    DESCRIPTION
        ""
    SYNTAX        BITS
    {
        broadcastPacketsDelta(0),
        broadcastPacketsDeltaAvg(1),
        broadcastPacketsDeltaMax(2),
        broadcastPacketsDeltaMin(3),
        multicastPacketsDelta(4),
        multicastPacketsDeltaAvg(5),
        multicastPacketsDeltaMax(6),
        multicastPacketsDeltaMin(7),
        unicastPacketsDelta(8),
        unicastPacketsDeltaAvg(9),
        unicastPacketsDeltaMax(10),
        unicastPacketsDeltaMin(11)
    }

CfprAdaptorEthPortOutsizedStatsThresholded ::= TEXTUAL-CONVENTION
    STATUS        current
    DESCRIPTION
        ""
    SYNTAX        BITS
    {
        oversizedBadCrcPacketsDelta(0),
        oversizedBadCrcPacketsDeltaAvg(1),
        oversizedBadCrcPacketsDeltaMax(2),
        oversizedBadCrcPacketsDeltaMin(3),
        oversizedGoodCrcPacketsDelta(4),
        oversizedGoodCrcPacketsDeltaAvg(5),
        oversizedGoodCrcPacketsDeltaMax(6),
        oversizedGoodCrcPacketsDeltaMin(7),
        oversizedPacketsDelta(8),
        oversizedPacketsDeltaAvg(9),
        oversizedPacketsDeltaMax(10),
        oversizedPacketsDeltaMin(11),
        undersizedBadCrcPacketsDelta(12),
        undersizedBadCrcPacketsDeltaAvg(13),
        undersizedBadCrcPacketsDeltaMax(14),
        undersizedBadCrcPacketsDeltaMin(15),
        undersizedGoodCrcPacketsDelta(16),
        undersizedGoodCrcPacketsDeltaAvg(17),
        undersizedGoodCrcPacketsDeltaMax(18),
        undersizedGoodCrcPacketsDeltaMin(19)
    }

CfprAdaptorEthPortOutsizedStatsHistThresholded ::= TEXTUAL-CONVENTION
    STATUS        current
    DESCRIPTION
        ""
    SYNTAX        BITS
    {
        oversizedBadCrcPacketsDelta(0),
        oversizedBadCrcPacketsDeltaAvg(1),
        oversizedBadCrcPacketsDeltaMax(2),
        oversizedBadCrcPacketsDeltaMin(3),
        oversizedGoodCrcPacketsDelta(4),
        oversizedGoodCrcPacketsDeltaAvg(5),
        oversizedGoodCrcPacketsDeltaMax(6),
        oversizedGoodCrcPacketsDeltaMin(7),
        oversizedPacketsDelta(8),
        oversizedPacketsDeltaAvg(9),
        oversizedPacketsDeltaMax(10),
        oversizedPacketsDeltaMin(11),
        undersizedBadCrcPacketsDelta(12),
        undersizedBadCrcPacketsDeltaAvg(13),
        undersizedBadCrcPacketsDeltaMax(14),
        undersizedBadCrcPacketsDeltaMin(15),
        undersizedGoodCrcPacketsDelta(16),
        undersizedGoodCrcPacketsDeltaAvg(17),
        undersizedGoodCrcPacketsDeltaMax(18),
        undersizedGoodCrcPacketsDeltaMin(19)
    }

CfprAdaptorEthPortStatsThresholded ::= TEXTUAL-CONVENTION
    STATUS        current
    DESCRIPTION
        ""
    SYNTAX        BITS
    {
        goodPacketsDelta(0),
        goodPacketsDeltaAvg(1),
        goodPacketsDeltaMax(2),
        goodPacketsDeltaMin(3),
        pausePacketsDelta(4),
        pausePacketsDeltaAvg(5),
        pausePacketsDeltaMax(6),
        pausePacketsDeltaMin(7),
        perPriorityPausePacketsDelta(8),
        perPriorityPausePacketsDeltaAvg(9),
        perPriorityPausePacketsDeltaMax(10),
        perPriorityPausePacketsDeltaMin(11),
        pppPacketsDelta(12),
        pppPacketsDeltaAvg(13),
        pppPacketsDeltaMax(14),
        pppPacketsDeltaMin(15),
        totalPacketsDelta(16),
        totalPacketsDeltaAvg(17),
        totalPacketsDeltaMax(18),
        totalPacketsDeltaMin(19),
        vlanPacketsDelta(20),
        vlanPacketsDeltaAvg(21),
        vlanPacketsDeltaMax(22),
        vlanPacketsDeltaMin(23)
    }

CfprAdaptorEthPortStatsHistThresholded ::= TEXTUAL-CONVENTION
    STATUS        current
    DESCRIPTION
        ""
    SYNTAX        BITS
    {
        goodPacketsDelta(0),
        goodPacketsDeltaAvg(1),
        goodPacketsDeltaMax(2),
        goodPacketsDeltaMin(3),
        pausePacketsDelta(4),
        pausePacketsDeltaAvg(5),
        pausePacketsDeltaMax(6),
        pausePacketsDeltaMin(7),
        perPriorityPausePacketsDelta(8),
        perPriorityPausePacketsDeltaAvg(9),
        perPriorityPausePacketsDeltaMax(10),
        perPriorityPausePacketsDeltaMin(11),
        pppPacketsDelta(12),
        pppPacketsDeltaAvg(13),
        pppPacketsDeltaMax(14),
        pppPacketsDeltaMin(15),
        totalPacketsDelta(16),
        totalPacketsDeltaAvg(17),
        totalPacketsDeltaMax(18),
        totalPacketsDeltaMin(19),
        vlanPacketsDelta(20),
        vlanPacketsDeltaAvg(21),
        vlanPacketsDeltaMax(22),
        vlanPacketsDeltaMin(23)
    }

CfprAdaptorEthRoCEProfileAdminState ::= TEXTUAL-CONVENTION
    STATUS        current
    DESCRIPTION
        ""
    SYNTAX        INTEGER
    {
        disabled(0),
        enabled(1)
    }

CfprAdaptorEthVxLANProfileAdminState ::= TEXTUAL-CONVENTION
    STATUS        current
    DESCRIPTION
        ""
    SYNTAX        INTEGER
    {
        disabled(0),
        enabled(1)
    }

CfprAdaptorEtherIfStatsThresholded ::= TEXTUAL-CONVENTION
    STATUS        current
    DESCRIPTION
        ""
    SYNTAX        BITS
    {
        rxBytesDelta(0),
        rxBytesDeltaAvg(1),
        rxBytesDeltaMax(2),
        rxBytesDeltaMin(3),
        rxDroppedDelta(4),
        rxDroppedDeltaAvg(5),
        rxDroppedDeltaMax(6),
        rxDroppedDeltaMin(7),
        rxErrorsDelta(8),
        rxErrorsDeltaAvg(9),
        rxErrorsDeltaMax(10),
        rxErrorsDeltaMin(11),
        rxPacketsDelta(12),
        rxPacketsDeltaAvg(13),
        rxPacketsDeltaMax(14),
        rxPacketsDeltaMin(15),
        txBytesDelta(16),
        txBytesDeltaAvg(17),
        txBytesDeltaMax(18),
        txBytesDeltaMin(19),
        txDroppedDelta(20),
        txDroppedDeltaAvg(21),
        txDroppedDeltaMax(22),
        txDroppedDeltaMin(23),
        txErrorsDelta(24),
        txErrorsDeltaAvg(25),
        txErrorsDeltaMax(26),
        txErrorsDeltaMin(27),
        txPacketsDelta(28),
        txPacketsDeltaAvg(29),
        txPacketsDeltaMax(30),
        txPacketsDeltaMin(31)
    }

CfprAdaptorEtherIfStatsHistThresholded ::= TEXTUAL-CONVENTION
    STATUS        current
    DESCRIPTION
        ""
    SYNTAX        BITS
    {
        rxBytesDelta(0),
        rxBytesDeltaAvg(1),
        rxBytesDeltaMax(2),
        rxBytesDeltaMin(3),
        rxDroppedDelta(4),
        rxDroppedDeltaAvg(5),
        rxDroppedDeltaMax(6),
        rxDroppedDeltaMin(7),
        rxErrorsDelta(8),
        rxErrorsDeltaAvg(9),
        rxErrorsDeltaMax(10),
        rxErrorsDeltaMin(11),
        rxPacketsDelta(12),
        rxPacketsDeltaAvg(13),
        rxPacketsDeltaMax(14),
        rxPacketsDeltaMin(15),
        txBytesDelta(16),
        txBytesDeltaAvg(17),
        txBytesDeltaMax(18),
        txBytesDeltaMin(19),
        txDroppedDelta(20),
        txDroppedDeltaAvg(21),
        txDroppedDeltaMax(22),
        txDroppedDeltaMin(23),
        txErrorsDelta(24),
        txErrorsDeltaAvg(25),
        txErrorsDeltaMax(26),
        txErrorsDeltaMin(27),
        txPacketsDelta(28),
        txPacketsDeltaAvg(29),
        txPacketsDeltaMax(30),
        txPacketsDeltaMin(31)
    }

CfprAdaptorExtEthIfFsmCurrentFsm ::= TEXTUAL-CONVENTION
    STATUS        current
    DESCRIPTION
        ""
    SYNTAX        INTEGER
    {
        nop(0),
        pathReset(499)
    }

CfprAdaptorExtEthIfFsmStageName ::= TEXTUAL-CONVENTION
    STATUS        current
    DESCRIPTION
        ""
    SYNTAX        INTEGER
    {
        nop(0),
        pathResetBegin(499),
        pathResetDisable(500),
        pathResetEnable(501),
        pathResetFail(502),
        pathResetSuccess(503)
    }

CfprAdaptorExtEthIfFsmTaskItem ::= TEXTUAL-CONVENTION
    STATUS        current
    DESCRIPTION
        ""
    SYNTAX        INTEGER
    {
        nop(0),
        pathReset(499)
    }

CfprAdaptorExtEthIfPcPortId ::= TEXTUAL-CONVENTION
    STATUS        current
    DESCRIPTION
        ""
    SYNTAX        Gauge32 (1024..4096)

CfprAdaptorExtEthIfPcTransport ::= TEXTUAL-CONVENTION
    STATUS        current
    DESCRIPTION
        ""
    SYNTAX        BITS
    {
        ether(0),
        dce(1),
        fc(2)
    }

CfprAdaptorExtEthIfPcEpPortId ::= TEXTUAL-CONVENTION
    STATUS        current
    DESCRIPTION
        ""
    SYNTAX        Gauge32 (1..8)

CfprAdaptorExtEthIfPcEpSlotId ::= TEXTUAL-CONVENTION
    STATUS        current
    DESCRIPTION
        ""
    SYNTAX        Gauge32 (1..8)

CfprAdaptorExtIfAdminState ::= TEXTUAL-CONVENTION
    STATUS        current
    DESCRIPTION
        ""
    SYNTAX        INTEGER
    {
        enabled(0),
        resetConnectivity(44)
    }

CfprAdaptorExtIfEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprAdaptorExtIfEpType ::= TEXTUAL-CONVENTION
    STATUS        current
    DESCRIPTION
        ""
    SYNTAX        BITS
    {
        lan(0),
        san(1),
        ipc(2)
    }

CfprAdaptorExtIfPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprAdaptorExtIfPcType ::= TEXTUAL-CONVENTION
    STATUS        current
    DESCRIPTION
        ""
    SYNTAX        BITS
    {
        lan(0),
        san(1),
        ipc(2)
    }

CfprAdaptorExtIpV6RssHashProfileIpHash ::= TEXTUAL-CONVENTION
    STATUS        current
    DESCRIPTION
        ""
    SYNTAX        INTEGER
    {
        disabled(0),
        enabled(1)
    }

CfprAdaptorExtIpV6RssHashProfileTcpHash ::= TEXTUAL-CONVENTION
    STATUS        current
    DESCRIPTION
        ""
    SYNTAX        INTEGER
    {
        disabled(0),
        enabled(1)
    }

CfprAdaptorExternalEpLocale ::= TEXTUAL-CONVENTION
    STATUS        current
    DESCRIPTION
        ""
    SYNTAX        BITS
    {
        server(0),
        chassis(1),
        internal(2),
        external(3)
    }

CfprAdaptorExternalPcLocale ::= TEXTUAL-CONVENTION
    STATUS        current
    DESCRIPTION
        ""
    SYNTAX        BITS
    {
        server(0),
        chassis(1),
        internal(2),
        external(3)
    }

CfprAdaptorFcErrorRecoveryProfileFcpErrorRecovery ::= TEXTUAL-CONVENTION
    STATUS        current
    DESCRIPTION
        ""
    SYNTAX        INTEGER
    {
        disabled(0),
        enabled(1)
    }

CfprAdaptorFcIfEventStatsThresholded ::= TEXTUAL-CONVENTION
    STATUS        current
    DESCRIPTION
        ""
    SYNTAX        BITS
    {
        invalidCRCCountDelta(0),
        invalidCRCCountDeltaAvg(1),
        invalidCRCCountDeltaMax(2),
        invalidCRCCountDeltaMin(3),
        linkFailureCountDelta(4),
        linkFailureCountDeltaAvg(5),
        linkFailureCountDeltaMax(6),
        linkFailureCountDeltaMin(7),
        lipCountDelta(8),
        lipCountDeltaAvg(9),
        lipCountDeltaMax(10),
        lipCountDeltaMin(11),
        lossOfSignalCountDelta(12),
        lossOfSignalCountDeltaAvg(13),
        lossOfSignalCountDeltaMax(14),
        lossOfSignalCountDeltaMin(15),
        lossOfSyncCountDelta(16),
        lossOfSyncCountDeltaAvg(17),
        lossOfSyncCountDeltaMax(18),
        lossOfSyncCountDeltaMin(19),
        nOSCountDelta(20),
        nOSCountDeltaAvg(21),
        nOSCountDeltaMax(22),
        nOSCountDeltaMin(23),
        secondsSinceLastResetDelta(24),
        secondsSinceLastResetDeltaAvg(25),
        secondsSinceLastResetDeltaMax(26),
        secondsSinceLastResetDeltaMin(27),
        seqProtocolErrCountDelta(28),
        seqProtocolErrCountDeltaAvg(29),
        seqProtocolErrCountDeltaMax(30),
        seqProtocolErrCountDeltaMin(31)
    }

CfprAdaptorFcIfEventStatsHistThresholded ::= TEXTUAL-CONVENTION
    STATUS        current
    DESCRIPTION
        ""
    SYNTAX        BITS
    {
        invalidCRCCountDelta(0),
        invalidCRCCountDeltaAvg(1),
        invalidCRCCountDeltaMax(2),
        invalidCRCCountDeltaMin(3),
        linkFailureCountDelta(4),
        linkFailureCountDeltaAvg(5),
        linkFailureCountDeltaMax(6),
        linkFailureCountDeltaMin(7),
        lipCountDelta(8),
        lipCountDeltaAvg(9),
        lipCountDeltaMax(10),
        lipCountDeltaMin(11),
        lossOfSignalCountDelta(12),
        lossOfSignalCountDeltaAvg(13),
        lossOfSignalCountDeltaMax(14),
        lossOfSignalCountDeltaMin(15),
        lossOfSyncCountDelta(16),
        lossOfSyncCountDeltaAvg(17),
        lossOfSyncCountDeltaMax(18),
        lossOfSyncCountDeltaMin(19),
        nOSCountDelta(20),
        nOSCountDeltaAvg(21),
        nOSCountDeltaMax(22),
        nOSCountDeltaMin(23),
        secondsSinceLastResetDelta(24),
        secondsSinceLastResetDeltaAvg(25),
        secondsSinceLastResetDeltaMax(26),
        secondsSinceLastResetDeltaMin(27),
        seqProtocolErrCountDelta(28),
        seqProtocolErrCountDeltaAvg(29),
        seqProtocolErrCountDeltaMax(30),
        seqProtocolErrCountDeltaMin(31)
    }

CfprAdaptorFcIfFC4StatsThresholded ::= TEXTUAL-CONVENTION
    STATUS        current
    DESCRIPTION
        ""
    SYNTAX        BITS
    {
        controlRequestsDelta(0),
        controlRequestsDeltaAvg(1),
        controlRequestsDeltaMax(2),
        controlRequestsDeltaMin(3),
        inputMegabytesDelta(4),
        inputMegabytesDeltaAvg(5),
        inputMegabytesDeltaMax(6),
        inputMegabytesDeltaMin(7),
        inputRequestsDelta(8),
        inputRequestsDeltaAvg(9),
        inputRequestsDeltaMax(10),
        inputRequestsDeltaMin(11),
        outputMegabytesDelta(12),
        outputMegabytesDeltaAvg(13),
        outputMegabytesDeltaMax(14),
        outputMegabytesDeltaMin(15),
        outputRequestsDelta(16),
        outputRequestsDeltaAvg(17),
        outputRequestsDeltaMax(18),
        outputRequestsDeltaMin(19)
    }

CfprAdaptorFcIfFC4StatsHistThresholded ::= TEXTUAL-CONVENTION
    STATUS        current
    DESCRIPTION
        ""
    SYNTAX        BITS
    {
        controlRequestsDelta(0),
        controlRequestsDeltaAvg(1),
        controlRequestsDeltaMax(2),
        controlRequestsDeltaMin(3),
        inputMegabytesDelta(4),
        inputMegabytesDeltaAvg(5),
        inputMegabytesDeltaMax(6),
        inputMegabytesDeltaMin(7),
        inputRequestsDelta(8),
        inputRequestsDeltaAvg(9),
        inputRequestsDeltaMax(10),
        inputRequestsDeltaMin(11),
        outputMegabytesDelta(12),
        outputMegabytesDeltaAvg(13),
        outputMegabytesDeltaMax(14),
        outputMegabytesDeltaMin(15),
        outputRequestsDelta(16),
        outputRequestsDeltaAvg(17),
        outputRequestsDeltaMax(18),
        outputRequestsDeltaMin(19)
    }

CfprAdaptorFcIfFrameStatsThresholded ::= TEXTUAL-CONVENTION
    STATUS        current
    DESCRIPTION
        ""
    SYNTAX        BITS
    {
        dumpedFramesDelta(0),
        dumpedFramesDeltaAvg(1),
        dumpedFramesDeltaMax(2),
        dumpedFramesDeltaMin(3),
        errorFramesDelta(4),
        errorFramesDeltaAvg(5),
        errorFramesDeltaMax(6),
        errorFramesDeltaMin(7),
        rxFramesDelta(8),
        rxFramesDeltaAvg(9),
        rxFramesDeltaMax(10),
        rxFramesDeltaMin(11),
        txFramesDelta(12),
        txFramesDeltaAvg(13),
        txFramesDeltaMax(14),
        txFramesDeltaMin(15)
    }

CfprAdaptorFcIfFrameStatsHistThresholded ::= TEXTUAL-CONVENTION
    STATUS        current
    DESCRIPTION
        ""
    SYNTAX        BITS
    {
        dumpedFramesDelta(0),
        dumpedFramesDeltaAvg(1),
        dumpedFramesDeltaMax(2),
        dumpedFramesDeltaMin(3),
        errorFramesDelta(4),
        errorFramesDeltaAvg(5),
        errorFramesDeltaMax(6),
        errorFramesDeltaMin(7),
        rxFramesDelta(8),
        rxFramesDeltaAvg(9),
        rxFramesDeltaMax(10),
        rxFramesDeltaMin(11),
        txFramesDelta(12),
        txFramesDeltaAvg(13),
        txFramesDeltaMax(14),
        txFramesDeltaMin(15)
    }

CfprAdaptorFcPortStatsThresholded ::= TEXTUAL-CONVENTION
    STATUS        current
    DESCRIPTION
        ""
    SYNTAX        BITS
    {
        rxBadFramesDelta(0),
        rxBadFramesDeltaAvg(1),
        rxBadFramesDeltaMax(2),
        rxBadFramesDeltaMin(3),
        rxFramesDelta(4),
        rxFramesDeltaAvg(5),
        rxFramesDeltaMax(6),
        rxFramesDeltaMin(7),
        txBadFramesDelta(8),
        txBadFramesDeltaAvg(9),
        txBadFramesDeltaMax(10),
        txBadFramesDeltaMin(11),
        txFramesDelta(12),
        txFramesDeltaAvg(13),
        txFramesDeltaMax(14),
        txFramesDeltaMin(15)
    }

CfprAdaptorFcPortStatsHistThresholded ::= TEXTUAL-CONVENTION
    STATUS        current
    DESCRIPTION
        ""
    SYNTAX        BITS
    {
        rxBadFramesDelta(0),
        rxBadFramesDeltaAvg(1),
        rxBadFramesDeltaMax(2),
        rxBadFramesDeltaMin(3),
        rxFramesDelta(4),
        rxFramesDeltaAvg(5),
        rxFramesDeltaMax(6),
        rxFramesDeltaMin(7),
        txBadFramesDelta(8),
        txBadFramesDeltaAvg(9),
        txBadFramesDeltaMax(10),
        txBadFramesDeltaMin(11),
        txFramesDelta(12),
        txFramesDeltaAvg(13),
        txFramesDeltaMax(14),
        txFramesDeltaMin(15)
    }

CfprAdaptorHostEthIfHostPort ::= TEXTUAL-CONVENTION
    STATUS        current
    DESCRIPTION
        ""
    SYNTAX        INTEGER
    {
        any(0),
        n1(1),
        n2(2),
        none(10)
    }

CfprAdaptorHostEthIfFsmCurrentFsm ::= TEXTUAL-CONVENTION
    STATUS        current
    DESCRIPTION
        ""
    SYNTAX        INTEGER
    {
        nop(0),
        circuitReset(505)
    }

CfprAdaptorHostEthIfFsmStageName ::= TEXTUAL-CONVENTION
    STATUS        current
    DESCRIPTION
        ""
    SYNTAX        INTEGER
    {
        nop(0),
        circuitResetBegin(505),
        circuitResetDisableA(506),
        circuitResetEnableA(507),
        circuitResetDisableB(508),
        circuitResetEnableB(509),
        circuitResetFail(515),
        circuitResetSuccess(516)
    }

CfprAdaptorHostEthIfFsmTaskItem ::= TEXTUAL-CONVENTION
    STATUS        current
    DESCRIPTION
        ""
    SYNTAX        INTEGER
    {
        nop(0),
        circuitReset(505)
    }

CfprAdaptorHostFcIfAdminState ::= TEXTUAL-CONVENTION
    STATUS        current
    DESCRIPTION
        ""
    SYNTAX        INTEGER
    {
        enabled(0),
        resetConnectivityActive(44),
        resetConnectivityPassive(45),
        resetConnectivity(46),
        disabled(47),
        disabledPassive(48),
        disabledActive(49),
        enabledPassive(50),
        enabledActive(51)
    }

CfprAdaptorHostFcIfHostPort ::= TEXTUAL-CONVENTION
    STATUS        current
    DESCRIPTION
        ""
    SYNTAX        INTEGER
    {
        any(0),
        n1(1),
        n2(2),
        none(10)
    }

CfprAdaptorHostFcIfPersBind ::= TEXTUAL-CONVENTION
    STATUS        current
    DESCRIPTION
        ""
    SYNTAX        INTEGER
    {
        disabled(0),
        enabled(4)
    }

CfprAdaptorHostFcIfFsmCurrentFsm ::= TEXTUAL-CONVENTION
    STATUS        current
    DESCRIPTION
        ""
    SYNTAX        INTEGER
    {
        nop(0),
        resetFcPersBinding(142),
        circuitReset(510)
    }

CfprAdaptorHostFcIfFsmStageName ::= TEXTUAL-CONVENTION
    STATUS        current
    DESCRIPTION
        ""
    SYNTAX        INTEGER
    {
        nop(0),
        resetFcPersBindingBegin(142),
        resetFcPersBindingFail(328),
        resetFcPersBindingSuccess(329),
        circuitResetBegin(510),
        circuitResetDisableA(511),
        circuitResetEnableA(512),
        circuitResetDisableB(513),
        circuitResetEnableB(514),
        circuitResetFail(517),
        circuitResetSuccess(518),
        resetFcPersBindingExecuteLocal(813),
        resetFcPersBindingExecutePeer(814)
    }

CfprAdaptorHostFcIfFsmTaskItem ::= TEXTUAL-CONVENTION
    STATUS        current
    DESCRIPTION
        ""
    SYNTAX        INTEGER
    {
        nop(0),
        resetFcPersBinding(142),
        circuitReset(510)
    }

CfprAdaptorHostIfAdminState ::= TEXTUAL-CONVENTION
    STATUS        current
    DESCRIPTION
        ""
    SYNTAX        INTEGER
    {
        enabled(0),
        resetConnectivityActive(44),
        resetConnectivityPassive(45),
        resetConnectivity(46),
        disabled(47),
        disabledPassive(48),
        disabledActive(49),
        enabledPassive(50),
        enabledActive(51)
    }

CfprAdaptorHostIfBootDev ::= TEXTUAL-CONVENTION
    STATUS        current
    DESCRIPTION
        ""
    SYNTAX        INTEGER
    {
        disabled(0),
        enabled(1)
    }

CfprAdaptorHostMgmtCapPreboot ::= TEXTUAL-CONVENTION
    STATUS        current
    DESCRIPTION
        ""
    SYNTAX        INTEGER
    {
        none(0),
        pnuOS(1),
        efi(2)
    }

CfprAdaptorHostMgmtCapPresence ::= TEXTUAL-CONVENTION
    STATUS        current
    DESCRIPTION
        ""
    SYNTAX        INTEGER
    {
        unspecified(0),
        host(1),
        cimc(2)
    }

CfprAdaptorHostPortId ::= TEXTUAL-CONVENTION
    STATUS        current
    DESCRIPTION
        ""
    SYNTAX        Gauge32 (1..5000)

CfprAdaptorHostServiceEthIfIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprAdaptorHostVisibility ::= TEXTUAL-CONVENTION
    STATUS        current
    DESCRIPTION
        ""
    SYNTAX        INTEGER
    {
        no(0),
        yes(1),
        osDependent(2)
    }

CfprAdaptorIScsiCapBootOrderType ::= TEXTUAL-CONVENTION
    STATUS        current
    DESCRIPTION
        ""
    SYNTAX        INTEGER
    {
        systemBootOrder(0),
        fddOrder(1),
        hddOrder(2),
        cdOrder(3),
        networkDeviceOrder(6),
        internalEfiShell(16),
        unknownDeviceOrder(99),
        localStorageAnyDeviceOrder(100),
        sanDeviceOrder(101),
        sanAnyDeviceOrder(102),
        internalUsbDeviceOrder(103),
        externalUsbDeviceOrder(104),
        sdcardDeviceOrder(105),
        lanAnyDeviceOrder(106),
        uefiTargetDeviceOrder(107),
        iscsiDeviceOrder(108),
        iscsiAnyDeviceOrder(109),
        cimcVmediaCddDeviceOrder(110),
        cimcVmediaHddDeviceOrder(111),
        cimcVmediaFddDeviceOrder(112),
        kvmVmediaCddDeviceOrder(113),
        kvmVmediaHddDeviceOrder(114),
        kvmVmediaFddDeviceOrder(115),
        bevOrder(128)
    }

CfprAdaptorInterruptMode ::= TEXTUAL-CONVENTION
    STATUS        current
    DESCRIPTION
        ""
    SYNTAX        INTEGER
    {
        msiX(1),
        msi(2),
        intx(3)
    }

CfprAdaptorIpV4RssHashProfileIpHash ::= TEXTUAL-CONVENTION
    STATUS        current
    DESCRIPTION
        ""
    SYNTAX        INTEGER
    {
        disabled(0),
        enabled(1)
    }

CfprAdaptorIpV4RssHashProfileTcpHash ::= TEXTUAL-CONVENTION
    STATUS        current
    DESCRIPTION
        ""
    SYNTAX        INTEGER
    {
        disabled(0),
        enabled(1)
    }

CfprAdaptorIpV6RssHashProfileIpHash ::= TEXTUAL-CONVENTION
    STATUS        current
    DESCRIPTION
        ""
    SYNTAX        INTEGER
    {
        disabled(0),
        enabled(1)
    }

CfprAdaptorIpV6RssHashProfileTcpHash ::= TEXTUAL-CONVENTION
    STATUS        current
    DESCRIPTION
        ""
    SYNTAX        INTEGER
    {
        disabled(0),
        enabled(1)
    }

CfprAdaptorIscsiProtConnectionTimeOut ::= TEXTUAL-CONVENTION
    STATUS        current
    DESCRIPTION
        ""
    SYNTAX        Gauge32 (0..255)

CfprAdaptorIscsiProtDhcpTimeOut ::= TEXTUAL-CONVENTION
    STATUS        current
    DESCRIPTION
        ""
    SYNTAX        Gauge32 (60..300)

CfprAdaptorIscsiProtLunBusyRetryCount ::= TEXTUAL-CONVENTION
    STATUS        current
    DESCRIPTION
        ""
    SYNTAX        Gauge32 (0..60)

CfprAdaptorLanCapDefaultVlan ::= TEXTUAL-CONVENTION
    STATUS        current
    DESCRIPTION
        ""
    SYNTAX        INTEGER
    {
        nativeVlan(1),
        defaultVlan(2)
    }

CfprAdaptorLinkState ::= TEXTUAL-CONVENTION
    STATUS        current
    DESCRIPTION
        ""
    SYNTAX        INTEGER
    {
        unknown(0),
        adminDown(1),
        down(2),
        error(3),
        up(4),
        unallocated(5),
        unavailable(6)
    }

CfprAdaptorLldpCapSupport ::= TEXTUAL-CONVENTION
    STATUS        current
    DESCRIPTION
        ""
    SYNTAX        INTEGER
    {
        none(1),
        full(2)
    }

CfprAdaptorMenloBaseErrorStatsThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        uncorrectableErrorsDelta(4),
        uncorrectableErrorsDeltaAvg(5),
        uncorrectableErrorsDeltaMax(6),
        uncorrectableErrorsDeltaMin(7)
    }

CfprAdaptorMenloBaseErrorStatsHistThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        uncorrectableErrorsDelta(4),
        uncorrectableErrorsDeltaAvg(5),
        uncorrectableErrorsDeltaMax(6),
        uncorrectableErrorsDeltaMin(7)
    }

CfprAdaptorMenloDcePortStatsThresholded ::= TEXTUAL-CONVENTION
    STATUS        current
    DESCRIPTION
        ""
    SYNTAX        BITS
    {
        rxPauseCFCDelta(0),
        rxPauseCFCDeltaAvg(1),
        rxPauseCFCDeltaMax(2),
        rxPauseCFCDeltaMin(3),
        rxPausePFCDelta(4),
        rxPausePFCDeltaAvg(5),
        rxPausePFCDeltaMax(6),
        rxPausePFCDeltaMin(7),
        txPauseCFCDelta(8),
        txPauseCFCDeltaAvg(9),
        txPauseCFCDeltaMax(10),
        txPauseCFCDeltaMin(11),
        txPausePFCDelta(12),
        txPausePFCDeltaAvg(13),
        txPausePFCDeltaMax(14),
        txPausePFCDeltaMin(15)
    }

CfprAdaptorMenloDcePortStatsHistThresholded ::= TEXTUAL-CONVENTION
    STATUS        current
    DESCRIPTION
        ""
    SYNTAX        BITS
    {
        rxPauseCFCDelta(0),
        rxPauseCFCDeltaAvg(1),
        rxPauseCFCDeltaMax(2),
        rxPauseCFCDeltaMin(3),
        rxPausePFCDelta(4),
        rxPausePFCDeltaAvg(5),
        rxPausePFCDeltaMax(6),
        rxPausePFCDeltaMin(7),
        txPauseCFCDelta(8),
        txPauseCFCDeltaAvg(9),
        txPauseCFCDeltaMax(10),
        txPauseCFCDeltaMin(11),
        txPausePFCDelta(12),
        txPausePFCDeltaAvg(13),
        txPausePFCDeltaMax(14),
        txPausePFCDeltaMin(15)
    }

CfprAdaptorMenloEthErrorStatsThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        dropAclDelta(4),
        dropAclDeltaAvg(5),
        dropAclDeltaMax(6),
        dropAclDeltaMin(7),
        popErrorsDelta(8),
        popErrorsDeltaAvg(9),
        popErrorsDeltaMax(10),
        popErrorsDeltaMin(11),
        pushErrorsDelta(12),
        pushErrorsDeltaAvg(13),
        pushErrorsDeltaMax(14),
        pushErrorsDeltaMin(15),
        uncorrectableErrorsDelta(16),
        uncorrectableErrorsDeltaAvg(17),
        uncorrectableErrorsDeltaMax(18),
        uncorrectableErrorsDeltaMin(19)
    }

CfprAdaptorMenloEthErrorStatsHistThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        dropAclDelta(4),
        dropAclDeltaAvg(5),
        dropAclDeltaMax(6),
        dropAclDeltaMin(7),
        popErrorsDelta(8),
        popErrorsDeltaAvg(9),
        popErrorsDeltaMax(10),
        popErrorsDeltaMin(11),
        pushErrorsDelta(12),
        pushErrorsDeltaAvg(13),
        pushErrorsDeltaMax(14),
        pushErrorsDeltaMin(15),
        uncorrectableErrorsDelta(16),
        uncorrectableErrorsDeltaAvg(17),
        uncorrectableErrorsDeltaMax(18),
        uncorrectableErrorsDeltaMin(19)
    }

CfprAdaptorMenloEthStatsThresholded ::= TEXTUAL-CONVENTION
    STATUS        current
    DESCRIPTION
        ""
    SYNTAX        BITS
    {
        dropOverrunDelta(0),
        dropOverrunDeltaAvg(1),
        dropOverrunDeltaMax(2),
        dropOverrunDeltaMin(3),
        dropRuntDelta(4),
        dropRuntDeltaAvg(5),
        dropRuntDeltaMax(6),
        dropRuntDeltaMin(7),
        truncateOverrunDelta(8),
        truncateOverrunDeltaAvg(9),
        truncateOverrunDeltaMax(10),
        truncateOverrunDeltaMin(11)
    }

CfprAdaptorMenloEthStatsHistThresholded ::= TEXTUAL-CONVENTION
    STATUS        current
    DESCRIPTION
        ""
    SYNTAX        BITS
    {
        dropOverrunDelta(0),
        dropOverrunDeltaAvg(1),
        dropOverrunDeltaMax(2),
        dropOverrunDeltaMin(3),
        dropRuntDelta(4),
        dropRuntDeltaAvg(5),
        dropRuntDeltaMax(6),
        dropRuntDeltaMin(7),
        truncateOverrunDelta(8),
        truncateOverrunDeltaAvg(9),
        truncateOverrunDeltaMax(10),
        truncateOverrunDeltaMin(11)
    }

CfprAdaptorMenloFcErrorStatsThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CfprAdaptorMenloFcErrorStatsHistThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CfprAdaptorMenloFcStatsThresholded ::= TEXTUAL-CONVENTION
    STATUS        current
    DESCRIPTION
        ""
    SYNTAX        BITS
    {
        dropAclDelta(0),
        dropAclDeltaAvg(1),
        dropAclDeltaMax(2),
        dropAclDeltaMin(3),
        dropOverrunDelta(4),
        dropOverrunDeltaAvg(5),
        dropOverrunDeltaMax(6),
        dropOverrunDeltaMin(7),
        dropRuntDelta(8),
        dropRuntDeltaAvg(9),
        dropRuntDeltaMax(10),
        dropRuntDeltaMin(11),
        truncateOverrunDelta(12),
        truncateOverrunDeltaAvg(13),
        truncateOverrunDeltaMax(14),
        truncateOverrunDeltaMin(15)
    }

CfprAdaptorMenloFcStatsHistThresholded ::= TEXTUAL-CONVENTION
    STATUS        current
    DESCRIPTION
        ""
    SYNTAX        BITS
    {
        dropAclDelta(0),
        dropAclDeltaAvg(1),
        dropAclDeltaMax(2),
        dropAclDeltaMin(3),
        dropOverrunDelta(4),
        dropOverrunDeltaAvg(5),
        dropOverrunDeltaMax(6),
        dropOverrunDeltaMin(7),
        dropRuntDelta(8),
        dropRuntDeltaAvg(9),
        dropRuntDeltaMax(10),
        dropRuntDeltaMin(11),
        truncateOverrunDelta(12),
        truncateOverrunDeltaAvg(13),
        truncateOverrunDeltaMax(14),
        truncateOverrunDeltaMin(15)
    }

CfprAdaptorMenloHostPortStatsThresholded ::= TEXTUAL-CONVENTION
    STATUS        current
    DESCRIPTION
        ""
    SYNTAX        BITS
    {
        rxPauseCFCDelta(0),
        rxPauseCFCDeltaAvg(1),
        rxPauseCFCDeltaMax(2),
        rxPauseCFCDeltaMin(3),
        rxPausePFCDelta(4),
        rxPausePFCDeltaAvg(5),
        rxPausePFCDeltaMax(6),
        rxPausePFCDeltaMin(7),
        txPauseCFCDelta(8),
        txPauseCFCDeltaAvg(9),
        txPauseCFCDeltaMax(10),
        txPauseCFCDeltaMin(11),
        txPausePFCDelta(12),
        txPausePFCDeltaAvg(13),
        txPausePFCDeltaMax(14),
        txPausePFCDeltaMin(15)
    }

CfprAdaptorMenloHostPortStatsHistThresholded ::= TEXTUAL-CONVENTION
    STATUS        current
    DESCRIPTION
        ""
    SYNTAX        BITS
    {
        rxPauseCFCDelta(0),
        rxPauseCFCDeltaAvg(1),
        rxPauseCFCDeltaMax(2),
        rxPauseCFCDeltaMin(3),
        rxPausePFCDelta(4),
        rxPausePFCDeltaAvg(5),
        rxPausePFCDeltaMax(6),
        rxPausePFCDeltaMin(7),
        txPauseCFCDelta(8),
        txPauseCFCDeltaAvg(9),
        txPauseCFCDeltaMax(10),
        txPauseCFCDeltaMin(11),
        txPausePFCDelta(12),
        txPausePFCDeltaAvg(13),
        txPausePFCDeltaMax(14),
        txPausePFCDeltaMin(15)
    }

CfprAdaptorMenloMcpuErrorStatsThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CfprAdaptorMenloMcpuErrorStatsHistThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CfprAdaptorMenloMcpuStatsThresholded ::= TEXTUAL-CONVENTION
    STATUS        current
    DESCRIPTION
        ""
    SYNTAX        BITS
    {
        dropAclDelta(0),
        dropAclDeltaAvg(1),
        dropAclDeltaMax(2),
        dropAclDeltaMin(3),
        dropOverrunDelta(4),
        dropOverrunDeltaAvg(5),
        dropOverrunDeltaMax(6),
        dropOverrunDeltaMin(7),
        dropRuntDelta(8),
        dropRuntDeltaAvg(9),
        dropRuntDeltaMax(10),
        dropRuntDeltaMin(11),
        truncateOverrunDelta(12),
        truncateOverrunDeltaAvg(13),
        truncateOverrunDeltaMax(14),
        truncateOverrunDeltaMin(15)
    }

CfprAdaptorMenloMcpuStatsHistThresholded ::= TEXTUAL-CONVENTION
    STATUS        current
    DESCRIPTION
        ""
    SYNTAX        BITS
    {
        dropAclDelta(0),
        dropAclDeltaAvg(1),
        dropAclDeltaMax(2),
        dropAclDeltaMin(3),
        dropOverrunDelta(4),
        dropOverrunDeltaAvg(5),
        dropOverrunDeltaMax(6),
        dropOverrunDeltaMin(7),
        dropRuntDelta(8),
        dropRuntDeltaAvg(9),
        dropRuntDeltaMax(10),
        dropRuntDeltaMin(11),
        truncateOverrunDelta(12),
        truncateOverrunDeltaAvg(13),
        truncateOverrunDeltaMax(14),
        truncateOverrunDeltaMin(15)
    }

CfprAdaptorMenloNetEgStatsThresholded ::= TEXTUAL-CONVENTION
    STATUS        current
    DESCRIPTION
        ""
    SYNTAX        BITS
    {
        dropCmdDelta(0),
        dropCmdDeltaAvg(1),
        dropCmdDeltaMax(2),
        dropCmdDeltaMin(3),
        dropLifCfgInvalidDelta(4),
        dropLifCfgInvalidDeltaAvg(5),
        dropLifCfgInvalidDeltaMax(6),
        dropLifCfgInvalidDeltaMin(7),
        dropLifMapNoHitDelta(8),
        dropLifMapNoHitDeltaAvg(9),
        dropLifMapNoHitDeltaMax(10),
        dropLifMapNoHitDeltaMin(11),
        dropSrcBindDelta(12),
        dropSrcBindDeltaAvg(13),
        dropSrcBindDeltaMax(14),
        dropSrcBindDeltaMin(15),
        learnReqDropDelta(16),
        learnReqDropDeltaAvg(17),
        learnReqDropDeltaMax(18),
        learnReqDropDeltaMin(19)
    }

CfprAdaptorMenloNetEgStatsHistThresholded ::= TEXTUAL-CONVENTION
    STATUS        current
    DESCRIPTION
        ""
    SYNTAX        BITS
    {
        dropCmdDelta(0),
        dropCmdDeltaAvg(1),
        dropCmdDeltaMax(2),
        dropCmdDeltaMin(3),
        dropLifCfgInvalidDelta(4),
        dropLifCfgInvalidDeltaAvg(5),
        dropLifCfgInvalidDeltaMax(6),
        dropLifCfgInvalidDeltaMin(7),
        dropLifMapNoHitDelta(8),
        dropLifMapNoHitDeltaAvg(9),
        dropLifMapNoHitDeltaMax(10),
        dropLifMapNoHitDeltaMin(11),
        dropSrcBindDelta(12),
        dropSrcBindDeltaAvg(13),
        dropSrcBindDeltaMax(14),
        dropSrcBindDeltaMin(15),
        learnReqDropDelta(16),
        learnReqDropDeltaAvg(17),
        learnReqDropDeltaMax(18),
        learnReqDropDeltaMin(19)
    }

CfprAdaptorMenloNetInStatsThresholded ::= TEXTUAL-CONVENTION
    STATUS        current
    DESCRIPTION
        ""
    SYNTAX        BITS
    {
        dropFcLifInvalidDelta(0),
        dropFcLifInvalidDeltaAvg(1),
        dropFcLifInvalidDeltaMax(2),
        dropFcLifInvalidDeltaMin(3),
        dropFcMulticastDelta(4),
        dropFcMulticastDeltaAvg(5),
        dropFcMulticastDeltaMax(6),
        dropFcMulticastDeltaMin(7),
        dropNullPifDelta(8),
        dropNullPifDeltaAvg(9),
        dropNullPifDeltaMax(10),
        dropNullPifDeltaMin(11),
        fwdLookupNoHitDelta(12),
        fwdLookupNoHitDeltaAvg(13),
        fwdLookupNoHitDeltaMax(14),
        fwdLookupNoHitDeltaMin(15)
    }

CfprAdaptorMenloNetInStatsHistThresholded ::= TEXTUAL-CONVENTION
    STATUS        current
    DESCRIPTION
        ""
    SYNTAX        BITS
    {
        dropFcLifInvalidDelta(0),
        dropFcLifInvalidDeltaAvg(1),
        dropFcLifInvalidDeltaMax(2),
        dropFcLifInvalidDeltaMin(3),
        dropFcMulticastDelta(4),
        dropFcMulticastDeltaAvg(5),
        dropFcMulticastDeltaMax(6),
        dropFcMulticastDeltaMin(7),
        dropNullPifDelta(8),
        dropNullPifDeltaAvg(9),
        dropNullPifDeltaMax(10),
        dropNullPifDeltaMin(11),
        fwdLookupNoHitDelta(12),
        fwdLookupNoHitDeltaAvg(13),
        fwdLookupNoHitDeltaMax(14),
        fwdLookupNoHitDeltaMin(15)
    }

CfprAdaptorMenloQErrorStatsThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CfprAdaptorMenloQErrorStatsHistThresholded ::= TEXTUAL-CONVENTION
    STATUS        current
    DESCRIPTION
        ""
    SYNTAX        BITS
    {
        correctableErrorsDelta(0),
        correctableErrorsDeltaAvg(1),
        correctableErrorsDeltaMax(2),
        correctableErrorsDeltaMin(3),
        popErrorsDelta(4),
        popErrorsDeltaAvg(5),
        popErrorsDeltaMax(6),
        popErrorsDeltaMin(7),
        pushErrorsDelta(8),
        pushErrorsDeltaAvg(9),
        pushErrorsDeltaMax(10),
        pushErrorsDeltaMin(11),
        uncorrectableErrorsDelta(12),
        uncorrectableErrorsDeltaAvg(13),
        uncorrectableErrorsDeltaMax(14),
        uncorrectableErrorsDeltaMin(15)
    }

CfprAdaptorMenloQStatsThresholded ::= TEXTUAL-CONVENTION
    STATUS        current
    DESCRIPTION
        ""
    SYNTAX        BITS
    {
        dropOverrunN0Delta(0),
        dropOverrunN0DeltaAvg(1),
        dropOverrunN0DeltaMax(2),
        dropOverrunN0DeltaMin(3),
        dropOverrunN1Delta(4),
        dropOverrunN1DeltaAvg(5),
        dropOverrunN1DeltaMax(6),
        dropOverrunN1DeltaMin(7),
        truncateOverrunN0Delta(8),
        truncateOverrunN0DeltaAvg(9),
        truncateOverrunN0DeltaMax(10),
        truncateOverrunN0DeltaMin(11),
        truncateOverrunN1Delta(12),
        truncateOverrunN1DeltaAvg(13),
        truncateOverrunN1DeltaMax(14),
        truncateOverrunN1DeltaMin(15)
    }

CfprAdaptorMenloQStatsHistThresholded ::= TEXTUAL-CONVENTION
    STATUS        current
    DESCRIPTION
        ""
    SYNTAX        BITS
    {
        dropOverrunN0Delta(0),
        dropOverrunN0DeltaAvg(1),
        dropOverrunN0DeltaMax(2),
        dropOverrunN0DeltaMin(3),
        dropOverrunN1Delta(4),
        dropOverrunN1DeltaAvg(5),
        dropOverrunN1DeltaMax(6),
        dropOverrunN1DeltaMin(7),
        truncateOverrunN0Delta(8),
        truncateOverrunN0DeltaAvg(9),
        truncateOverrunN0DeltaMax(10),
        truncateOverrunN0DeltaMin(11),
        truncateOverrunN1Delta(12),
        truncateOverrunN1DeltaAvg(13),
        truncateOverrunN1DeltaMax(14),
        truncateOverrunN1DeltaMin(15)
    }

CfprAdaptorMenloQueueStatsComponent ::= TEXTUAL-CONVENTION
    STATUS        current
    DESCRIPTION
        ""
    SYNTAX        INTEGER
    {
        unknown(0),
        cpu(1),
        eth(2),
        fc(3),
        n(4)
    }

CfprAdaptorMenloStatsIndex ::= TEXTUAL-CONVENTION
    STATUS        current
    DESCRIPTION
        ""
    SYNTAX        INTEGER
    {
        unknown(0),
        n0(1),
        n1(2),
        n0A(3),
        n0B(4),
        n1A(5),
        n1B(6)
    }

CfprAdaptorMgmtCapMode ::= TEXTUAL-CONVENTION
    STATUS        current
    DESCRIPTION
        ""
    SYNTAX        INTEGER
    {
        full(1),
        partial(2)
    }

CfprAdaptorMgmtCapOperPowerRequirement ::= TEXTUAL-CONVENTION
    STATUS        current
    DESCRIPTION
        ""
    SYNTAX        INTEGER
    {
        none(0),
        standby(1),
        full(2)
    }

CfprAdaptorMgmtCapRebootActionOnDestructive ::= TEXTUAL-CONVENTION
    STATUS        current
    DESCRIPTION
        ""
    SYNTAX        INTEGER
    {
        none(0),
        host(1),
        adaptor(2)
    }

CfprAdaptorNwMgmtCapApi ::= TEXTUAL-CONVENTION
    STATUS        current
    DESCRIPTION
        ""
    SYNTAX        INTEGER
    {
        none(0),
        menlo(1),
        palo(2)
    }

CfprAdaptorNwMgmtCapMgmtTransport ::= TEXTUAL-CONVENTION
    STATUS        current
    DESCRIPTION
        ""
    SYNTAX        INTEGER
    {
        l2(0),
        l3(1)
    }

CfprAdaptorOffloadMethod ::= TEXTUAL-CONVENTION
    STATUS        current
    DESCRIPTION
        ""
    SYNTAX        INTEGER
    {
        virtual(0),
        physical(1),
        none(2)
    }

CfprAdaptorPIoEpIfType ::= TEXTUAL-CONVENTION
    STATUS        current
    DESCRIPTION
        ""
    SYNTAX        INTEGER
    {
        unknown(0),
        physical(1),
        aggregation(2),
        virtual(3)
    }

CfprAdaptorProtocolProfileConnectionTimeOut ::= TEXTUAL-CONVENTION
    STATUS        current
    DESCRIPTION
        ""
    SYNTAX        Gauge32 (0..255)

CfprAdaptorProtocolProfileLunBusyRetryCount ::= TEXTUAL-CONVENTION
    STATUS        current
    DESCRIPTION
        ""
    SYNTAX        Gauge32 (0..60)

CfprAdaptorPurpose ::= TEXTUAL-CONVENTION
    STATUS        current
    DESCRIPTION
        ""
    SYNTAX        INTEGER
    {
        unused(0),
        general(1),
        management(2),
        utility(3)
    }

CfprAdaptorReachability ::= TEXTUAL-CONVENTION
    STATUS        current
    DESCRIPTION
        ""
    SYNTAX        BITS
    {
        a(0),
        b(1),
        unmanaged(7)
    }

CfprAdaptorRssProfileReceiveSideScaling ::= TEXTUAL-CONVENTION
    STATUS        current
    DESCRIPTION
        ""
    SYNTAX        INTEGER
    {
        disabled(0),
        enabled(1)
    }

CfprAdaptorSanCapHostNvram ::= TEXTUAL-CONVENTION
    STATUS        current
    DESCRIPTION
        ""
    SYNTAX        INTEGER
    {
        none(1),
        full(2)
    }

CfprAdaptorServiceState ::= TEXTUAL-CONVENTION
    STATUS        current
    DESCRIPTION
        ""
    SYNTAX        INTEGER
    {
        outOfService(0),
        inService(1)
    }

CfprAdaptorUnitId ::= TEXTUAL-CONVENTION
    STATUS        current
    DESCRIPTION
        ""
    SYNTAX        Gauge32 (1..5000)

CfprAdaptorUnitExtnId ::= TEXTUAL-CONVENTION
    STATUS        current
    DESCRIPTION
        ""
    SYNTAX        Gauge32 (1..5000)

CfprAdaptorVnicStatsThresholded ::= TEXTUAL-CONVENTION
    STATUS        current
    DESCRIPTION
        ""
    SYNTAX        BITS
    {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        droppedRxDelta(8),
        droppedRxDeltaAvg(9),
        droppedRxDeltaMax(10),
        droppedRxDeltaMin(11),
        droppedTxDelta(12),
        droppedTxDeltaAvg(13),
        droppedTxDeltaMax(14),
        droppedTxDeltaMin(15),
        errorsRxDelta(16),
        errorsRxDeltaAvg(17),
        errorsRxDeltaMax(18),
        errorsRxDeltaMin(19),
        errorsTxDelta(20),
        errorsTxDeltaAvg(21),
        errorsTxDeltaMax(22),
        errorsTxDeltaMin(23),
        packetsRxDelta(24),
        packetsRxDeltaAvg(25),
        packetsRxDeltaMax(26),
        packetsRxDeltaMin(27),
        packetsTxDelta(28),
        packetsTxDeltaAvg(29),
        packetsTxDeltaMax(30),
        packetsTxDeltaMin(31)
    }

CfprAdaptorVnicStatsHistThresholded ::= TEXTUAL-CONVENTION
    STATUS        current
    DESCRIPTION
        ""
    SYNTAX        BITS
    {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        droppedRxDelta(8),
        droppedRxDeltaAvg(9),
        droppedRxDeltaMax(10),
        droppedRxDeltaMin(11),
        droppedTxDelta(12),
        droppedTxDeltaAvg(13),
        droppedTxDeltaMax(14),
        droppedTxDeltaMin(15),
        errorsRxDelta(16),
        errorsRxDeltaAvg(17),
        errorsRxDeltaMax(18),
        errorsRxDeltaMin(19),
        errorsTxDelta(20),
        errorsTxDeltaAvg(21),
        errorsTxDeltaMax(22),
        errorsTxDeltaMin(23),
        packetsRxDelta(24),
        packetsRxDeltaAvg(25),
        packetsRxDeltaMax(26),
        packetsRxDeltaMin(27),
        packetsTxDelta(28),
        packetsTxDeltaAvg(29),
        packetsTxDeltaMax(30),
        packetsTxDeltaMin(31)
    }

CfprAddressMACMask ::= TEXTUAL-CONVENTION
    STATUS        current
    DESCRIPTION
        ""
    SYNTAX        Counter64

CfprAddressType ::= TEXTUAL-CONVENTION
    STATUS        current
    DESCRIPTION
        ""
    SYNTAX        INTEGER
    {
        unknown(0),
        operational(1),
        floating(2)
    }

CfprAddressUIDSuffxMask ::= TEXTUAL-CONVENTION
    STATUS        current
    DESCRIPTION
        ""
    SYNTAX        Counter64

CfprAddressWWNMask ::= TEXTUAL-CONVENTION
    STATUS        current
    DESCRIPTION
        ""
    SYNTAX        Counter64

CfprApplicationDownloaderFsmCurrentFsm ::= TEXTUAL-CONVENTION
    STATUS        current
    DESCRIPTION
        ""
    SYNTAX        INTEGER
    {
        nop(0),
        download(1714)
    }

CfprApplicationDownloaderFsmStageName ::= TEXTUAL-CONVENTION
    STATUS        current
    DESCRIPTION
        ""
    SYNTAX        INTEGER
    {
        nop(0),
        downloadBegin(1714),
        downloadLocal(1715),
        downloadUnpackLocal(1716),
        downloadFail(1784),
        downloadSuccess(1785),
        downloadVerify(1925)
    }

CfprApplicationDownloaderFsmTaskItem ::= TEXTUAL-CONVENTION
    STATUS        current
    DESCRIPTION
        ""
    SYNTAX        INTEGER
    {
        nop(0),
        download(1714)
    }

CfprBiosBootDevErrorCode ::= TEXTUAL-CONVENTION
    STATUS        current
    DESCRIPTION
        ""
    SYNTAX        INTEGER
    {
        success(0),
        failure(1)
    }

CfprBiosBootDevGrpType ::= TEXTUAL-CONVENTION
    STATUS        current
    DESCRIPTION
        ""
    SYNTAX        INTEGER
    {
        systemBootOrder(0),
        fddOrder(1),
        hddOrder(2),
        cdOrder(3),
        networkDeviceOrder(6),
        internalEfiShell(16),
        unknownDeviceOrder(99),
        localStorageAnyDeviceOrder(100),
        sanDeviceOrder(101),
        sanAnyDeviceOrder(102),
        internalUsbDeviceOrder(103),
        externalUsbDeviceOrder(104),
        sdcardDeviceOrder(105),
        lanAnyDeviceOrder(106),
        uefiTargetDeviceOrder(107),
        iscsiDeviceOrder(108),
        iscsiAnyDeviceOrder(109),
        cimcVmediaCddDeviceOrder(110),
        cimcVmediaHddDeviceOrder(111),
        cimcVmediaFddDeviceOrder(112),
        kvmVmediaCddDeviceOrder(113),
        kvmVmediaHddDeviceOrder(114),
        kvmVmediaFddDeviceOrder(115),
        bevOrder(128)
    }

CfprBiosBootDevOrder ::= TEXTUAL-CONVENTION
    STATUS        current
    DESCRIPTION
        ""
    SYNTAX        INTEGER
    {
        n1(1),
        n2(2),
        n3(3),
        n4(4),
        n5(5),
        n6(6),
        n7(7)
    }

CfprBiosDefaultAction ::= TEXTUAL-CONVENTION
    STATUS        current
    DESCRIPTION
        ""
    SYNTAX        INTEGER
    {
        no(0),
        yes(1)
    }

CfprBiosSupportedAction ::= TEXTUAL-CONVENTION
    STATUS        current
    DESCRIPTION
        ""
    SYNTAX        INTEGER
    {
        no(0),
        yes(1)
    }

CfprBiosVfACPI10SupportVpACPI10Support ::= TEXTUAL-CONVENTION
    STATUS        current
    DESCRIPTION
        ""
    SYNTAX        INTEGER
    {
        platformRecommended(0),
        disabled(122),
        enabled(123)
    }

CfprBiosVfAllUSBDevicesVpAllUSBDevices ::= TEXTUAL-CONVENTION
    STATUS        current
    DESCRIPTION
        ""
    SYNTAX        INTEGER
    {
        platformRecommended(0),
        disabled(386),
        enabled(387)
    }

CfprBiosVfAltitudeVpAltitude ::= TEXTUAL-CONVENTION
    STATUS        current
    DESCRIPTION
        ""
    SYNTAX        INTEGER
    {
        platformRecommended(0),
        auto(482),
        n300M(483),
        n900M(484),
        n1500M(485),
        n3000M(486)
    }

CfprBiosVfAssertNMIOnPERRVpAssertNMIOnPERR ::= TEXTUAL-CONVENTION
    STATUS        current
    DESCRIPTION
        ""
    SYNTAX        INTEGER
    {
        platformRecommended(0),
        disabled(68),
        enabled(69)
    }

CfprBiosVfAssertNMIOnSERRVpAssertNMIOnSERR ::= TEXTUAL-CONVENTION
    STATUS        current
    DESCRIPTION
        ""
    SYNTAX        INTEGER
    {
        platformRecommended(0),
        disabled(66),
        enabled(67)
    }

CfprBiosVfBootOptionRetryVpBootOptionRetry ::= TEXTUAL-CONVENTION
    STATUS        current
    DESCRIPTION
        ""
    SYNTAX        INTEGER
    {
        platformRecommended(0),
        disabled(96),
        enabled(97)
    }

CfprBiosVfCPUPerformanceVpCPUPerformance ::= TEXTUAL-CONVENTION
    STATUS        current
    DESCRIPTION
        ""
    SYNTAX        INTEGER
    {
        platformRecommended(0),
        enterprise(175),
        highThroughput(176),
        hpc(177)
    }

CfprBiosVfConsoleRedirectionVpBaudRate ::= TEXTUAL-CONVENTION
    STATUS        current
    DESCRIPTION
        ""
    SYNTAX        INTEGER
    {
        platformRecommended(0),
        n9600(131),
        n19200(132),
        n38400(133),
        n57600(134),
        n115200(135)
    }

CfprBiosVfConsoleRedirectionVpConsoleRedirection ::= TEXTUAL-CONVENTION
    STATUS        current
    DESCRIPTION
        ""
    SYNTAX        INTEGER
    {
        platformRecommended(0),
        disabled(77),
        serialPortA(78),
        serialPortB(130),
        enabled(260),
        com0(261)
    }

CfprBiosVfConsoleRedirectionVpFlowControl ::= TEXTUAL-CONVENTION
    STATUS        current
    DESCRIPTION
        ""
    SYNTAX        INTEGER
    {
        platformRecommended(0),
        none(79),
        rtsCts(80)
    }

CfprBiosVfConsoleRedirectionVpLegacyOSRedirection ::= TEXTUAL-CONVENTION
    STATUS        current
    DESCRIPTION
        ""
    SYNTAX        INTEGER
    {
        platformRecommended(0),
        disabled(90),
        enabled(91)
    }

CfprBiosVfConsoleRedirectionVpPuttyKeyPad ::= TEXTUAL-CONVENTION
    STATUS        current
    DESCRIPTION
        ""
    SYNTAX        INTEGER
    {
        platformRecommended(0),
        vt100(295),
        linux(296),
        xtermr6(297),
        sco(298),
        escn(299),
        vt400(300)
    }

CfprBiosVfConsoleRedirectionVpTerminalType ::= TEXTUAL-CONVENTION
    STATUS        current
    DESCRIPTION
        ""
    SYNTAX        INTEGER
    {
        platformRecommended(0),
        pcAnsi(86),
        vt100(87),
        vt100Plus(88),
        vtUtf8(89)
    }

CfprBiosVfCoreMultiProcessingVpCoreMultiProcessing ::= TEXTUAL-CONVENTION
    STATUS        current
    DESCRIPTION
        ""
    SYNTAX        INTEGER
    {
        platformRecommended(0),
        all(170),
        n1(178),
        n2(179),
        n3(180),
        n4(181),
        n5(182),
        n6(183),
        n7(184),
        n8(185),
        n9(189),
        n10(190),
        n11(274),
        n12(275),
        n13(292),
        n14(293),
        n15(294),
        n16(440),
        n17(441),
        n18(442)
    }

CfprBiosVfDRAMClockThrottlingVpDRAMClockThrottling ::= TEXTUAL-CONVENTION
    STATUS        current
    DESCRIPTION
        ""
    SYNTAX        INTEGER
    {
        platformRecommended(0),
        auto(432),
        balanced(433),
        performance(434),
        energyEfficient(435)
    }

CfprBiosVfDirectCacheAccessVpDirectCacheAccess ::= TEXTUAL-CONVENTION
    STATUS        current
    DESCRIPTION
        ""
    SYNTAX        INTEGER
    {
        platformRecommended(0),
        disabled(28),
        enabled(29)
    }

CfprBiosVfDramRefreshRateVpDramRefreshRate ::= TEXTUAL-CONVENTION
    STATUS        current
    DESCRIPTION
        ""
    SYNTAX        INTEGER
    {
        platformRecommended(0),
        n1x(262),
        n2x(263),
        n3x(264),
        n4x(265),
        auto(270)
    }

CfprBiosVfEnhancedIntelSpeedStepTechVpEnhancedIntelSpeedStepTech ::= TEXTUAL-CONVENTION
    STATUS        current
    DESCRIPTION
        ""
    SYNTAX        INTEGER
    {
        platformRecommended(0),
        disabled(3),
        enabled(4)
    }

CfprBiosVfExecuteDisableBitVpExecuteDisableBit ::= TEXTUAL-CONVENTION
    STATUS        current
    DESCRIPTION
        ""
    SYNTAX        INTEGER
    {
        platformRecommended(0),
        disabled(10),
        enabled(11)
    }

CfprBiosVfFRB2TimerVpFRB2Timer ::= TEXTUAL-CONVENTION
    STATUS        current
    DESCRIPTION
        ""
    SYNTAX        INTEGER
    {
        platformRecommended(0),
        disabled(417),
        enabled(418)
    }

CfprBiosVfFrequencyFloorOverrideVpFrequencyFloorOverride ::= TEXTUAL-CONVENTION
    STATUS        current
    DESCRIPTION
        ""
    SYNTAX        INTEGER
    {
        platformRecommended(0),
        disabled(427),
        enabled(428)
    }

CfprBiosVfFrontPanelLockoutVpFrontPanelLockout ::= TEXTUAL-CONVENTION
    STATUS        current
    DESCRIPTION
        ""
    SYNTAX        INTEGER
    {
        platformRecommended(0),
        disabled(60),
        enabled(61)
    }

CfprBiosVfIntelEntrySASRAIDModuleVpSASRAID ::= TEXTUAL-CONVENTION
    STATUS        current
    DESCRIPTION
        ""
    SYNTAX        INTEGER
    {
        platformRecommended(0),
        disabled(154),
        enabled(155)
    }

CfprBiosVfIntelEntrySASRAIDModuleVpSASRAIDModule ::= TEXTUAL-CONVENTION
    STATUS        current
    DESCRIPTION
        ""
    SYNTAX        INTEGER
    {
        platformRecommended(0),
        itIrRaid(156),
        intelEsrtii(157)
    }

CfprBiosVfIntelHyperThreadingTechVpIntelHyperThreadingTech ::= TEXTUAL-CONVENTION
    STATUS        current
    DESCRIPTION
        ""
    SYNTAX        INTEGER
    {
        platformRecommended(0),
        disabled(5),
        enabled(6)
    }

CfprBiosVfIntelTurboBoostTechVpIntelTurboBoostTech ::= TEXTUAL-CONVENTION
    STATUS        current
    DESCRIPTION
        ""
    SYNTAX        INTEGER
    {
        platformRecommended(0),
        disabled(1),
        enabled(2)
    }

CfprBiosVfIntelVTForDirectedIOVpIntelVTDATSSupport ::= TEXTUAL-CONVENTION
    STATUS        current
    DESCRIPTION
        ""
    SYNTAX        INTEGER
    {
        platformRecommended(0),
        disabled(20),
        enabled(21)
    }

CfprBiosVfIntelVTForDirectedIOVpIntelVTDCoherencySupport ::= TEXTUAL-CONVENTION
    STATUS        current
    DESCRIPTION
        ""
    SYNTAX        INTEGER
    {
        platformRecommended(0),
        disabled(18),
        enabled(19)
    }

CfprBiosVfIntelVTForDirectedIOVpIntelVTDInterruptRemapping ::= TEXTUAL-CONVENTION
    STATUS        current
    DESCRIPTION
        ""
    SYNTAX        INTEGER
    {
        platformRecommended(0),
        disabled(16),
        enabled(17)
    }

CfprBiosVfIntelVTForDirectedIOVpIntelVTDPassThroughDMASupport ::= TEXTUAL-CONVENTION
    STATUS        current
    DESCRIPTION
        ""
    SYNTAX        INTEGER
    {
        platformRecommended(0),
        disabled(22),
        enabled(23)
    }

CfprBiosVfIntelVTForDirectedIOVpIntelVTForDirectedIO ::= TEXTUAL-CONVENTION
    STATUS        current
    DESCRIPTION
        ""
    SYNTAX        INTEGER
    {
        platformRecommended(0),
        disabled(14),
        enabled(15)
    }

CfprBiosVfIntelVirtualizationTechnologyVpIntelVirtTechnology ::= TEXTUAL-CONVENTION
    STATUS        current
    DESCRIPTION
        ""
    SYNTAX        INTEGER
    {
        platformRecommended(0),
        disabled(12),
        enabled(13)
    }

CfprBiosVfInterleaveConfigurationVpChannelInterleaving ::= TEXTUAL-CONVENTION
    STATUS        current
    DESCRIPTION
        ""
    SYNTAX        INTEGER
    {
        platformRecommended(0),
        auto(282),
        n1Way(283),
        n2Way(284),
        n3Way(285),
        n4Way(286)
    }

CfprBiosVfInterleaveConfigurationVpMemoryInterleaving ::= TEXTUAL-CONVENTION
    STATUS        current
    DESCRIPTION
        ""
    SYNTAX        INTEGER
    {
        platformRecommended(0),
        numa1WayNodeInterleave(278),
        n2WayNodeInterleave(279),
        n4WayNodeInterleave(280),
        n8WayInterleavingInterSocket(281)
    }

CfprBiosVfInterleaveConfigurationVpRankInterleaving ::= TEXTUAL-CONVENTION
    STATUS        current
    DESCRIPTION
        ""
    SYNTAX        INTEGER
    {
        platformRecommended(0),
        auto(287),
        n1Way(288),
        n2Way(289),
        n4Way(290),
        n8Way(291)
    }

CfprBiosVfLocalX2ApicVpLocalX2Apic ::= TEXTUAL-CONVENTION
    STATUS        current
    DESCRIPTION
        ""
    SYNTAX        INTEGER
    {
        platformRecommended(0),
        xapic(271),
        x2apic(272),
        auto(273)
    }

CfprBiosVfLvDIMMSupportVpLvDDRMode ::= TEXTUAL-CONVENTION
    STATUS        current
    DESCRIPTION
        ""
    SYNTAX        INTEGER
    {
        platformRecommended(0),
        powerSavingMode(138),
        performanceMode(139),
        auto(301)
    }

CfprBiosVfMaxVariableMTRRSettingVpProcessorMtrr ::= TEXTUAL-CONVENTION
    STATUS        current
    DESCRIPTION
        ""
    SYNTAX        INTEGER
    {
        platformRecommended(0),
        autoMax(191),
        n8(192)
    }

CfprBiosVfMaximumMemoryBelow4GBVpMaximumMemoryBelow4GB ::= TEXTUAL-CONVENTION
    STATUS        current
    DESCRIPTION
        ""
    SYNTAX        INTEGER
    {
        platformRecommended(0),
        disabled(54),
        enabled(55)
    }

CfprBiosVfMemoryMappedIOAbove4GBVpMemoryMappedIOAbove4GB ::= TEXTUAL-CONVENTION
    STATUS        current
    DESCRIPTION
        ""
    SYNTAX        INTEGER
    {
        platformRecommended(0),
        disabled(56),
        enabled(57)
    }

CfprBiosVfMirroringModeVpMirroringMode ::= TEXTUAL-CONVENTION
    STATUS        current
    DESCRIPTION
        ""
    SYNTAX        INTEGER
    {
        platformRecommended(0),
        interSocket(142),
        intraSocket(143)
    }

CfprBiosVfNUMAOptimizedVpNUMAOptimized ::= TEXTUAL-CONVENTION
    STATUS        current
    DESCRIPTION
        ""
    SYNTAX        INTEGER
    {
        platformRecommended(0),
        disabled(32),
        enabled(33)
    }

CfprBiosVfOSBootWatchdogTimerVpOSBootWatchdogTimer ::= TEXTUAL-CONVENTION
    STATUS        current
    DESCRIPTION
        ""
    SYNTAX        INTEGER
    {
        platformRecommended(0),
        disabled(114),
        enabled(115)
    }

CfprBiosVfOSBootWatchdogTimerPolicyVpOSBootWatchdogTimerPolicy ::= TEXTUAL-CONVENTION
    STATUS        current
    DESCRIPTION
        ""
    SYNTAX        INTEGER
    {
        platformRecommended(0),
        powerOff(116),
        reset(162)
    }

CfprBiosVfOSBootWatchdogTimerTimeoutVpOSBootWatchdogTimerTimeout ::= TEXTUAL-CONVENTION
    STATUS        current
    DESCRIPTION
        ""
    SYNTAX        INTEGER
    {
        platformRecommended(0),
        n5Minutes(254),
        n10Minutes(255),
        n15Minutes(256),
        n20Minutes(257)
    }

CfprBiosVfOnboardSATAControllerVpOnboardSATAController ::= TEXTUAL-CONVENTION
    STATUS        current
    DESCRIPTION
        ""
    SYNTAX        INTEGER
    {
        platformRecommended(0),
        disabled(38),
        enabled(39)
    }

CfprBiosVfOnboardSATAControllerVpSATAMode ::= TEXTUAL-CONVENTION
    STATUS        current
    DESCRIPTION
        ""
    SYNTAX        INTEGER
    {
        platformRecommended(0),
        enhanced(40),
        compatibility(41),
        ahci(42),
        swRaid(186)
    }

CfprBiosVfOnboardStorageVpOnboardSCUStorageSupport ::= TEXTUAL-CONVENTION
    STATUS        current
    DESCRIPTION
        ""
    SYNTAX        INTEGER
    {
        platformRecommended(0),
        disabled(252),
        enabled(253)
    }

CfprBiosVfOptionROMEnableVpState ::= TEXTUAL-CONVENTION
    STATUS        current
    DESCRIPTION
        ""
    SYNTAX        INTEGER
    {
        platformRecommended(0),
        disabled(208),
        enabled(209),
        uefiOnly(443),
        legacyOnly(444)
    }

CfprBiosVfOptionROMLoadVpLoad ::= TEXTUAL-CONVENTION
    STATUS        current
    DESCRIPTION
        ""
    SYNTAX        INTEGER
    {
        platformRecommended(0),
        enabled(187),
        disabled(188)
    }

CfprBiosVfPCISlotLinkSpeedVpPCIeSlot10LinkSpeed ::= TEXTUAL-CONVENTION
    STATUS        current
    DESCRIPTION
        ""
    SYNTAX        INTEGER
    {
        platformRecommended(0),
        gen1(363),
        gen2(364),
        gen3(365),
        auto(366),
        disabled(367)
    }

CfprBiosVfPCISlotLinkSpeedVpPCIeSlot1LinkSpeed ::= TEXTUAL-CONVENTION
    STATUS        current
    DESCRIPTION
        ""
    SYNTAX        INTEGER
    {
        platformRecommended(0),
        gen1(318),
        gen2(319),
        gen3(320),
        auto(321),
        disabled(322)
    }

CfprBiosVfPCISlotLinkSpeedVpPCIeSlot2LinkSpeed ::= TEXTUAL-CONVENTION
    STATUS        current
    DESCRIPTION
        ""
    SYNTAX        INTEGER
    {
        platformRecommended(0),
        gen1(323),
        gen2(324),
        gen3(325),
        auto(326),
        disabled(327)
    }

CfprBiosVfPCISlotLinkSpeedVpPCIeSlot3LinkSpeed ::= TEXTUAL-CONVENTION
    STATUS        current
    DESCRIPTION
        ""
    SYNTAX        INTEGER
    {
        platformRecommended(0),
        gen1(328),
        gen2(329),
        gen3(330),
        auto(331),
        disabled(332)
    }

CfprBiosVfPCISlotLinkSpeedVpPCIeSlot4LinkSpeed ::= TEXTUAL-CONVENTION
    STATUS        current
    DESCRIPTION
        ""
    SYNTAX        INTEGER
    {
        platformRecommended(0),
        gen1(333),
        gen2(334),
        gen3(335),
        auto(336),
        disabled(337)
    }

CfprBiosVfPCISlotLinkSpeedVpPCIeSlot5LinkSpeed ::= TEXTUAL-CONVENTION
    STATUS        current
    DESCRIPTION
        ""
    SYNTAX        INTEGER
    {
        platformRecommended(0),
        gen1(338),
        gen2(339),
        gen3(340),
        auto(341),
        disabled(342)
    }

CfprBiosVfPCISlotLinkSpeedVpPCIeSlot6LinkSpeed ::= TEXTUAL-CONVENTION
    STATUS        current
    DESCRIPTION
        ""
    SYNTAX        INTEGER
    {
        platformRecommended(0),
        gen1(343),
        gen2(344),
        gen3(345),
        auto(346),
        disabled(347)
    }

CfprBiosVfPCISlotLinkSpeedVpPCIeSlot7LinkSpeed ::= TEXTUAL-CONVENTION
    STATUS        current
    DESCRIPTION
        ""
    SYNTAX        INTEGER
    {
        platformRecommended(0),
        gen1(348),
        gen2(349),
        gen3(350),
        auto(351),
        disabled(352)
    }

CfprBiosVfPCISlotLinkSpeedVpPCIeSlot8LinkSpeed ::= TEXTUAL-CONVENTION
    STATUS        current
    DESCRIPTION
        ""
    SYNTAX        INTEGER
    {
        platformRecommended(0),
        gen1(353),
        gen2(354),
        gen3(355),
        auto(356),
        disabled(357)
    }

CfprBiosVfPCISlotLinkSpeedVpPCIeSlot9LinkSpeed ::= TEXTUAL-CONVENTION
    STATUS        current
    DESCRIPTION
        ""
    SYNTAX        INTEGER
    {
        platformRecommended(0),
        gen1(358),
        gen2(359),
        gen3(360),
        auto(361),
        disabled(362)
    }

CfprBiosVfPCISlotOptionROMEnableVpPCIeSlotHBAOptionROM ::= TEXTUAL-CONVENTION
    STATUS        current
    DESCRIPTION
        ""
    SYNTAX        INTEGER
    {
        platformRecommended(0),
        disabled(463),
        enabled(464),
        uefiOnly(465),
        legacyOnly(466)
    }

CfprBiosVfPCISlotOptionROMEnableVpPCIeSlotMLOMOptionROM ::= TEXTUAL-CONVENTION
    STATUS        current
    DESCRIPTION
        ""
    SYNTAX        INTEGER
    {
        platformRecommended(0),
        disabled(459),
        enabled(460),
        uefiOnly(461),
        legacyOnly(462)
    }

CfprBiosVfPCISlotOptionROMEnableVpPCIeSlotN1OptionROM ::= TEXTUAL-CONVENTION
    STATUS        current
    DESCRIPTION
        ""
    SYNTAX        INTEGER
    {
        platformRecommended(0),
        disabled(467),
        enabled(468),
        uefiOnly(469),
        legacyOnly(470)
    }

CfprBiosVfPCISlotOptionROMEnableVpPCIeSlotN2OptionROM ::= TEXTUAL-CONVENTION
    STATUS        current
    DESCRIPTION
        ""
    SYNTAX        INTEGER
    {
        platformRecommended(0),
        disabled(471),
        enabled(472),
        uefiOnly(473),
        legacyOnly(474)
    }

CfprBiosVfPCISlotOptionROMEnableVpPCIeSlotSASOptionROM ::= TEXTUAL-CONVENTION
    STATUS        current
    DESCRIPTION
        ""
    SYNTAX        INTEGER
    {
        platformRecommended(0),
        disabled(302),
        enabled(303),
        uefiOnly(304),
        legacyOnly(305)
    }

CfprBiosVfPCISlotOptionROMEnableVpSlot10State ::= TEXTUAL-CONVENTION
    STATUS        current
    DESCRIPTION
        ""
    SYNTAX        INTEGER
    {
        platformRecommended(0),
        disabled(314),
        enabled(315),
        uefiOnly(316),
        legacyOnly(317)
    }

CfprBiosVfPCISlotOptionROMEnableVpSlot1State ::= TEXTUAL-CONVENTION
    STATUS        current
    DESCRIPTION
        ""
    SYNTAX        INTEGER
    {
        platformRecommended(0),
        disabled(210),
        enabled(211),
        uefiOnly(445),
        legacyOnly(446)
    }

CfprBiosVfPCISlotOptionROMEnableVpSlot2State ::= TEXTUAL-CONVENTION
    STATUS        current
    DESCRIPTION
        ""
    SYNTAX        INTEGER
    {
        platformRecommended(0),
        disabled(212),
        enabled(213),
        uefiOnly(447),
        legacyOnly(448)
    }

CfprBiosVfPCISlotOptionROMEnableVpSlot3State ::= TEXTUAL-CONVENTION
    STATUS        current
    DESCRIPTION
        ""
    SYNTAX        INTEGER
    {
        platformRecommended(0),
        disabled(214),
        enabled(215),
        uefiOnly(449),
        legacyOnly(450)
    }

CfprBiosVfPCISlotOptionROMEnableVpSlot4State ::= TEXTUAL-CONVENTION
    STATUS        current
    DESCRIPTION
        ""
    SYNTAX        INTEGER
    {
        platformRecommended(0),
        disabled(216),
        enabled(217),
        uefiOnly(451),
        legacyOnly(452)
    }

CfprBiosVfPCISlotOptionROMEnableVpSlot5State ::= TEXTUAL-CONVENTION
    STATUS        current
    DESCRIPTION
        ""
    SYNTAX        INTEGER
    {
        platformRecommended(0),
        disabled(218),
        enabled(219),
        uefiOnly(453),
        legacyOnly(454)
    }

CfprBiosVfPCISlotOptionROMEnableVpSlot6State ::= TEXTUAL-CONVENTION
    STATUS        current
    DESCRIPTION
        ""
    SYNTAX        INTEGER
    {
        platformRecommended(0),
        disabled(266),
        enabled(267),
        uefiOnly(455),
        legacyOnly(456)
    }

CfprBiosVfPCISlotOptionROMEnableVpSlot7State ::= TEXTUAL-CONVENTION
    STATUS        current
    DESCRIPTION
        ""
    SYNTAX        INTEGER
    {
        platformRecommended(0),
        disabled(268),
        enabled(269),
        uefiOnly(457),
        legacyOnly(458)
    }

CfprBiosVfPCISlotOptionROMEnableVpSlot8State ::= TEXTUAL-CONVENTION
    STATUS        current
    DESCRIPTION
        ""
    SYNTAX        INTEGER
    {
        platformRecommended(0),
        disabled(306),
        enabled(307),
        uefiOnly(308),
        legacyOnly(309)
    }

CfprBiosVfPCISlotOptionROMEnableVpSlot9State ::= TEXTUAL-CONVENTION
    STATUS        current
    DESCRIPTION
        ""
    SYNTAX        INTEGER
    {
        platformRecommended(0),
        disabled(310),
        enabled(311),
        uefiOnly(312),
        legacyOnly(313)
    }

CfprBiosVfPCISlotOptionROMEnableVpSlotMezzState ::= TEXTUAL-CONVENTION
    STATUS        current
    DESCRIPTION
        ""
    SYNTAX        INTEGER
    {
        platformRecommended(0),
        disabled(220),
        enabled(221)
    }

CfprBiosVfPOSTErrorPauseVpPOSTErrorPause ::= TEXTUAL-CONVENTION
    STATUS        current
    DESCRIPTION
        ""
    SYNTAX        INTEGER
    {
        platformRecommended(0),
        disabled(102),
        enabled(103)
    }

CfprBiosVfPSTATECoordinationVpPSTATECoordination ::= TEXTUAL-CONVENTION
    STATUS        current
    DESCRIPTION
        ""
    SYNTAX        INTEGER
    {
        platformRecommended(0),
        hwAll(429),
        swAll(430),
        swAny(431)
    }

CfprBiosVfPackageCStateLimitVpPackageCStateLimit ::= TEXTUAL-CONVENTION
    STATUS        current
    DESCRIPTION
        ""
    SYNTAX        INTEGER
    {
        platformRecommended(0),
        noLimit(222),
        c0(223),
        c1(224),
        c3(225),
        c6(226)
    }

CfprBiosVfProcessorC1EVpProcessorC1E ::= TEXTUAL-CONVENTION
    STATUS        current
    DESCRIPTION
        ""
    SYNTAX        INTEGER
    {
        platformRecommended(0),
        disabled(201),
        enabled(202)
    }

CfprBiosVfProcessorC3ReportVpProcessorC3Report ::= TEXTUAL-CONVENTION
    STATUS        current
    DESCRIPTION
        ""
    SYNTAX        INTEGER
    {
        platformRecommended(0),
        disabled(108),
        acpiC2(136),
        acpiC3(137)
    }

CfprBiosVfProcessorC6ReportVpProcessorC6Report ::= TEXTUAL-CONVENTION
    STATUS        current
    DESCRIPTION
        ""
    SYNTAX        INTEGER
    {
        platformRecommended(0),
        disabled(110),
        enabled(111)
    }

CfprBiosVfProcessorC7ReportVpProcessorC7Report ::= TEXTUAL-CONVENTION
    STATUS        current
    DESCRIPTION
        ""
    SYNTAX        INTEGER
    {
        platformRecommended(0),
        disabled(206),
        enabled(207)
    }

CfprBiosVfProcessorCStateVpProcessorCState ::= TEXTUAL-CONVENTION
    STATUS        current
    DESCRIPTION
        ""
    SYNTAX        INTEGER
    {
        platformRecommended(0),
        disabled(199),
        enabled(200)
    }

CfprBiosVfProcessorEnergyConfigurationVpEnergyPerformance ::= TEXTUAL-CONVENTION
    STATUS        current
    DESCRIPTION
        ""
    SYNTAX        INTEGER
    {
        platformRecommended(0),
        performance(423),
        balancedPerformance(424),
        balancedEnergy(425),
        energyEfficient(426)
    }

CfprBiosVfProcessorEnergyConfigurationVpPowerTechnology ::= TEXTUAL-CONVENTION
    STATUS        current
    DESCRIPTION
        ""
    SYNTAX        INTEGER
    {
        platformRecommended(0),
        disabled(419),
        energyEfficient(420),
        performance(421),
        custom(422)
    }

CfprBiosVfProcessorPrefetchConfigVpAdjacentCacheLinePrefetcher ::= TEXTUAL-CONVENTION
    STATUS        current
    DESCRIPTION
        ""
    SYNTAX        INTEGER
    {
        platformRecommended(0),
        disabled(404),
        enabled(405)
    }

CfprBiosVfProcessorPrefetchConfigVpDCUIPPrefetcher ::= TEXTUAL-CONVENTION
    STATUS        current
    DESCRIPTION
        ""
    SYNTAX        INTEGER
    {
        platformRecommended(0),
        disabled(408),
        enabled(409)
    }

CfprBiosVfProcessorPrefetchConfigVpDCUStreamerPrefetch ::= TEXTUAL-CONVENTION
    STATUS        current
    DESCRIPTION
        ""
    SYNTAX        INTEGER
    {
        platformRecommended(0),
        disabled(406),
        enabled(407)
    }

CfprBiosVfProcessorPrefetchConfigVpHardwarePrefetcher ::= TEXTUAL-CONVENTION
    STATUS        current
    DESCRIPTION
        ""
    SYNTAX        INTEGER
    {
        platformRecommended(0),
        disabled(402),
        enabled(403)
    }

CfprBiosVfQPILinkFrequencySelectVpQPILinkFrequencySelect ::= TEXTUAL-CONVENTION
    STATUS        current
    DESCRIPTION
        ""
    SYNTAX        INTEGER
    {
        platformRecommended(0),
        n6400(436),
        n7200(437),
        n8000(438),
        auto(439)
    }

CfprBiosVfQuietBootVpQuietBoot ::= TEXTUAL-CONVENTION
    STATUS        current
    DESCRIPTION
        ""
    SYNTAX        INTEGER
    {
        platformRecommended(0),
        disabled(100),
        enabled(101)
    }

CfprBiosVfResumeOnACPowerLossVpResumeOnACPowerLoss ::= TEXTUAL-CONVENTION
    STATUS        current
    DESCRIPTION
        ""
    SYNTAX        INTEGER
    {
        platformRecommended(0),
        stayOff(70),
        lastState(71),
        reset(72)
    }

CfprBiosVfScrubPoliciesVpDemandScrub ::= TEXTUAL-CONVENTION
    STATUS        current
    DESCRIPTION
        ""
    SYNTAX        INTEGER
    {
        platformRecommended(0),
        disabled(412),
        enabled(413)
    }

CfprBiosVfScrubPoliciesVpPatrolScrub ::= TEXTUAL-CONVENTION
    STATUS        current
    DESCRIPTION
        ""
    SYNTAX        INTEGER
    {
        platformRecommended(0),
        disabled(410),
        enabled(411)
    }

CfprBiosVfSelectMemoryRASConfigurationVpSelectMemoryRASConf ::= TEXTUAL-CONVENTION
    STATUS        current
    DESCRIPTION
        ""
    SYNTAX        INTEGER
    {
        platformRecommended(0),
        maximumPerformance(30),
        mirroring(31),
        lockstep(124),
        sparing(125)
    }

CfprBiosVfSerialPortAEnableVpSerialPortAEnable ::= TEXTUAL-CONVENTION
    STATUS        current
    DESCRIPTION
        ""
    SYNTAX        INTEGER
    {
        platformRecommended(0),
        disabled(44),
        enabled(45)
    }

CfprBiosVfSparingModeVpSparingMode ::= TEXTUAL-CONVENTION
    STATUS        current
    DESCRIPTION
        ""
    SYNTAX        INTEGER
    {
        platformRecommended(0),
        dimmSparing(126),
        rankSparing(127)
    }

CfprBiosVfSriovConfigVpSriov ::= TEXTUAL-CONVENTION
    STATUS        current
    DESCRIPTION
        ""
    SYNTAX        INTEGER
    {
        platformRecommended(0),
        disabled(258),
        enabled(259)
    }

CfprBiosVfTPMSupportVpTPMSupport ::= TEXTUAL-CONVENTION
    STATUS        current
    DESCRIPTION
        ""
    SYNTAX        INTEGER
    {
        platformRecommended(0),
        disabled(475),
        enabled(476)
    }

CfprBiosVfFPRMBootModeControlVpUEFIBootMode ::= TEXTUAL-CONVENTION
    STATUS        current
    DESCRIPTION
        ""
    SYNTAX        INTEGER
    {
        platformRecommended(0),
        disabled(276),
        enabled(277)
    }

CfprBiosVfFPRMBootOrderRuleControlVpFPRMBootOrderRule ::= TEXTUAL-CONVENTION
    STATUS        current
    DESCRIPTION
        ""
    SYNTAX        INTEGER
    {
        platformRecommended(0),
        strict(197),
        loose(198)
    }

CfprBiosVfUEFIOSUseLegacyVideoVpUEFIOSUseLegacyVideo ::= TEXTUAL-CONVENTION
    STATUS        current
    DESCRIPTION
        ""
    SYNTAX        INTEGER
    {
        platformRecommended(0),
        disabled(160),
        enabled(161)
    }

CfprBiosVfUSBBootConfigVpLegacyUSBSupport ::= TEXTUAL-CONVENTION
    STATUS        current
    DESCRIPTION
        ""
    SYNTAX        INTEGER
    {
        platformRecommended(0),
        disabled(249),
        enabled(250),
        auto(251)
    }

CfprBiosVfUSBBootConfigVpMakeDeviceNonBootable ::= TEXTUAL-CONVENTION
    STATUS        current
    DESCRIPTION
        ""
    SYNTAX        INTEGER
    {
        platformRecommended(0),
        disabled(106),
        enabled(107)
    }

CfprBiosVfUSBConfigurationVpLegacyUSBSupport ::= TEXTUAL-CONVENTION
    STATUS        current
    DESCRIPTION
        ""
    SYNTAX        INTEGER
    {
        platformRecommended(0),
        disabled(479),
        enabled(480),
        auto(481)
    }

CfprBiosVfUSBConfigurationVpXHCIMode ::= TEXTUAL-CONVENTION
    STATUS        current
    DESCRIPTION
        ""
    SYNTAX        INTEGER
    {
        platformRecommended(0),
        disabled(477),
        enabled(478)
    }

CfprBiosVfUSBFrontPanelAccessLockVpUSBFrontPanelLock ::= TEXTUAL-CONVENTION
    STATUS        current
    DESCRIPTION
        ""
    SYNTAX        INTEGER
    {
        platformRecommended(0),
        disabled(195),
        enabled(203)
    }

CfprBiosVfUSBPortConfigurationVpPort6064Emulation ::= TEXTUAL-CONVENTION
    STATUS        current
    DESCRIPTION
        ""
    SYNTAX        INTEGER
    {
        platformRecommended(0),
        disabled(388),
        enabled(389)
    }

CfprBiosVfUSBPortConfigurationVpUSBPortFront ::= TEXTUAL-CONVENTION
    STATUS        current
    DESCRIPTION
        ""
    SYNTAX        INTEGER
    {
        platformRecommended(0),
        disabled(392),
        enabled(393)
    }

CfprBiosVfUSBPortConfigurationVpUSBPortInternal ::= TEXTUAL-CONVENTION
    STATUS        current
    DESCRIPTION
        ""
    SYNTAX        INTEGER
    {
        platformRecommended(0),
        disabled(394),
        enabled(395)
    }

CfprBiosVfUSBPortConfigurationVpUSBPortKVM ::= TEXTUAL-CONVENTION
    STATUS        current
    DESCRIPTION
        ""
    SYNTAX        INTEGER
    {
        platformRecommended(0),
        disabled(396),
        enabled(397)
    }

CfprBiosVfUSBPortConfigurationVpUSBPortRear ::= TEXTUAL-CONVENTION
    STATUS        current
    DESCRIPTION
        ""
    SYNTAX        INTEGER
    {
        platformRecommended(0),
        disabled(390),
        enabled(391)
    }

CfprBiosVfUSBPortConfigurationVpUSBPortSDCard ::= TEXTUAL-CONVENTION
    STATUS        current
    DESCRIPTION
        ""
    SYNTAX        INTEGER
    {
        platformRecommended(0),
        disabled(400),
        enabled(401)
    }

CfprBiosVfUSBPortConfigurationVpUSBPortVMedia ::= TEXTUAL-CONVENTION
    STATUS        current
    DESCRIPTION
        ""
    SYNTAX        INTEGER
    {
        platformRecommended(0),
        disabled(398),
        enabled(399)
    }

CfprBiosVfUSBSysIdlePowerOptimizingSettingVpUSBIdlePowerOptimize ::= TEXTUAL-CONVENTION
    STATUS        current
    DESCRIPTION
        ""
    SYNTAX        INTEGER
    {
        platformRecommended(0),
        highPerformance(193),
        lowerIdlePower(194)
    }

CfprBiosVfVGAPriorityVpVGAPriority ::= TEXTUAL-CONVENTION
    STATUS        current
    DESCRIPTION
        ""
    SYNTAX        INTEGER
    {
        platformRecommended(0),
        onboard(414),
        offboard(415),
        onboardVgaDisabled(416)
    }

CfprBmcSELCntEqptClassId ::= TEXTUAL-CONVENTION
    STATUS        current
    DESCRIPTION
        ""
    SYNTAX        INTEGER
    {
        unspecified(0),
        processorUnit(142),
        memoryUnit(247),
        computeBoard(605)
    }

CfprBmcSELCntEqptInstIdPropId ::= TEXTUAL-CONVENTION
    STATUS        current
    DESCRIPTION
        ""
    SYNTAX        INTEGER
    {
        unspecified(0),
        processorUnitId(360),
        memoryUnitId(698)
    }

CfprBmcSELCntStatsClassId ::= TEXTUAL-CONVENTION
    STATUS        current
    DESCRIPTION
        ""
    SYNTAX        INTEGER
    {
        unspecified(0),
        computePCIeFatalProtocolStats(882),
        computePCIeFatalReceiveStats(884),
        computePCIeFatalCompletionStats(886),
        computePCIeFatalStats(888),
        processorErrorStats(935),
        memoryErrorStats(940)
    }

CfprCallhomeAdminState ::= TEXTUAL-CONVENTION
    STATUS        current
    DESCRIPTION
        ""
    SYNTAX        INTEGER
    {
        off(0),
        on(1)
    }

CfprCallhomeAlertGroup ::= TEXTUAL-CONVENTION
    STATUS        current
    DESCRIPTION
        ""
    SYNTAX        INTEGER
    {
        diagnostic(0),
        environmental(1),
        unknown(100)
    }

CfprCallhomeAlertGroups ::= TEXTUAL-CONVENTION
    STATUS        current
    DESCRIPTION
        ""
    SYNTAX        BITS
    {
        system(0),
        environmental(1),
        linecard(2),
        supervisor(3),
        inventory(4),
        test(5),
        ciscoTac(6),
        syslogPort(7),
        license(8),
        lifeCycle(9),
        diagnostic(10),
        smartLicense(11)
    }

CfprCallhomeAlertLevel ::= TEXTUAL-CONVENTION
    STATUS        current
    DESCRIPTION
        ""
    SYNTAX        INTEGER
    {
        debug(0),
        normal(1),
        notify(2),
        warning(3),
        minor(4),
        major(5),
        critical(6),
        fatal(7),
        unknown(100)
    }

CfprCallhomeAlertMessageSubtype ::= TEXTUAL-CONVENTION
    STATUS        current
    DESCRIPTION
        ""
    SYNTAX        INTEGER
    {
        nosubtype(0),
        test(1),
        full(2),
        delta(3),
        minor(4),
        major(5),
        goldnormal(6),
        goldminor(7),
        goldmajor(8),
        unknown(100)
    }

CfprCallhomeAlertMessageType ::= TEXTUAL-CONVENTION
    STATUS        current
    DESCRIPTION
        ""
    SYNTAX        INTEGER
    {
        inventory(0),
        syslog(1),
        test(2),
        diag(3),
        env(4),
        conf(5),
        telemetry(6),
        unknown(100)
    }

CfprCallhomeAlertThrottlingAdminState ::= TEXTUAL-CONVENTION
    STATUS        current
    DESCRIPTION
        ""
    SYNTAX        INTEGER
    {
        off(0),
        on(1)
    }

CfprCallhomeAnonymousReportingAdminState ::= TEXTUAL-CONVENTION
    STATUS        current
    DESCRIPTION
        ""
    SYNTAX        INTEGER
    {
        off(0),
        on(1)
    }

CfprCallhomeCallhomeProtocol ::= TEXTUAL-CONVENTION
    STATUS        current
    DESCRIPTION
        ""
    SYNTAX        INTEGER
    {
        email(0),
        https(1),
        http(2)
    }

CfprCallhomeEpConfigState ::= TEXTUAL-CONVENTION
    STATUS        current
    DESCRIPTION
        ""
    SYNTAX        INTEGER
    {
        ok(0),
        notApplied(1)
    }

CfprCallhomeEpFsmCurrentFsm ::= TEXTUAL-CONVENTION
    STATUS        current
    DESCRIPTION
        ""
    SYNTAX        INTEGER
    {
        nop(0),
        configCallhome(274)
    }

CfprCallhomeEpFsmStageName ::= TEXTUAL-CONVENTION
    STATUS        current
    DESCRIPTION
        ""
    SYNTAX        INTEGER
    {
        nop(0),
        configCallhomeBegin(274),
        configCallhomeSetLocal(275),
        configCallhomeSetPeer(276),
        configCallhomeFail(330),
        configCallhomeSuccess(331)
    }

CfprCallhomeEpFsmTaskItem ::= TEXTUAL-CONVENTION
    STATUS        current
    DESCRIPTION
        ""
    SYNTAX        INTEGER
    {
        nop(0),
        configCallhome(274)
    }

CfprCallhomeFormat ::= TEXTUAL-CONVENTION
    STATUS        current
    DESCRIPTION
        ""
    SYNTAX        INTEGER
    {
        xml(1),
        fullTxt(2),
        shortTxt(4)
    }

CfprCallhomeHttpProxyEnable ::= TEXTUAL-CONVENTION
    STATUS        current
    DESCRIPTION
        ""
    SYNTAX        INTEGER
    {
        off(0),
        on(1)
    }

CfprCallhomeLevel ::= TEXTUAL-CONVENTION
    STATUS        current
    DESCRIPTION
        ""
    SYNTAX        INTEGER
    {
        debug(0),
        normal(1),
        notification(2),
        warning(3),
        minor(4),
        major(5),
        critical(6),
        fatal(7),
        disaster(8)
    }

CfprCallhomePolicyAdminState ::= TEXTUAL-CONVENTION
    STATUS        current
    DESCRIPTION
        ""
    SYNTAX        INTEGER
    {
        enabled(1),
        disabled(2)
    }

CfprCallhomeUrgency ::= TEXTUAL-CONVENTION
    STATUS        current
    DESCRIPTION
        ""
    SYNTAX        INTEGER
    {
        emergency(0),
        alert(1),
        critical(2),
        error(3),
        warning(4),
        notice(5),
        info(6),
        debug(7)
    }

CfprCallhomeReportingType ::= TEXTUAL-CONVENTION
    STATUS        current
    DESCRIPTION
        ""
    SYNTAX        INTEGER
    {
        smartLicenseData(0),
        smartCallHomeData(1)
    }

CfprCapabilityAdminState ::= TEXTUAL-CONVENTION
    STATUS        current
    DESCRIPTION
        ""
    SYNTAX        INTEGER
    {
        restart(0),
        idle(1)
    }

CfprCapabilityCatalogueFsmCurrentFsm ::= TEXTUAL-CONVENTION
    STATUS        current
    DESCRIPTION
        ""
    SYNTAX        INTEGER
    {
        nop(0),
        deployCatalogue(609),
        activateCatalog(904)
    }

CfprCapabilityCatalogueFsmStageName ::= TEXTUAL-CONVENTION
    STATUS        current
    DESCRIPTION
        ""
    SYNTAX        INTEGER
    {
        nop(0),
        deployCatalogueBegin(609),
        deployCatalogueSyncBladeAGLocal(610),
        deployCatalogueSyncBladeAGRemote(611),
        deployCatalogueSyncNicAGLocal(612),
        deployCatalogueSyncNicAGRemote(613),
        deployCatalogueSyncPortAGLocal(614),
        deployCatalogueSyncPortAGRemote(615),
        deployCatalogueSyncHostagentAGLocal(616),
        deployCatalogueSyncHostagentAGRemote(617),
        deployCatalogueFinalize(618),
        deployCatalogueFail(619),
        deployCatalogueSuccess(620),
        activateCatalogBegin(904),
        activateCatalogUnpackLocal(905),
        activateCatalogCopyRemote(906),
        activateCatalogApplyCatalog(907),
        activateCatalogRescanImages(908),
        activateCatalogEvaluateStatus(909),
        activateCatalogFail(936),
        activateCatalogSuccess(937),
        activateCatalogCopyCatFromRep(1565),
        activateCatalogCopyExternalRepToRemote(1566)
    }

CfprCapabilityCatalogueFsmTaskItem ::= TEXTUAL-CONVENTION
    STATUS        current
    DESCRIPTION
        ""
    SYNTAX        INTEGER
    {
        nop(0),
        deployCatalogue(609),
        activateCatalog(904)
    }

CfprCapabilityFeatureStatus ::= TEXTUAL-CONVENTION
    STATUS        current
    DESCRIPTION
        ""
    SYNTAX        INTEGER
    {
        supported(0),
        unsupported(1)
    }

CfprCapabilityMgmtExtensionFsmCurrentFsm ::= TEXTUAL-CONVENTION
    STATUS        current
    DESCRIPTION
        ""
    SYNTAX        INTEGER
    {
        nop(0),
        activateMgmtExt(910)
    }

CfprCapabilityMgmtExtensionFsmStageName ::= TEXTUAL-CONVENTION
    STATUS        current
    DESCRIPTION
        ""
    SYNTAX        INTEGER
    {
        nop(0),
        activateMgmtExtBegin(910),
        activateMgmtExtUnpackLocal(911),
        activateMgmtExtCopyRemote(912),
        activateMgmtExtApplyCatalog(913),
        activateMgmtExtRescanImages(914),
        activateMgmtExtEvaluateStatus(915),
        activateMgmtExtFail(938),
        activateMgmtExtSuccess(939)
    }

CfprCapabilityMgmtExtensionFsmTaskItem ::= TEXTUAL-CONVENTION
    STATUS        current
    DESCRIPTION
        ""
    SYNTAX        INTEGER
    {
        nop(0),
        activateMgmtExt(910)
    }

CfprCapabilityOperStatus ::= TEXTUAL-CONVENTION
    STATUS        current
    DESCRIPTION
        ""
    SYNTAX        INTEGER
    {
        init(0),
        downloading(1),
        downloaded(2),
        applied(3),
        failed(4)
    }

CfprCapabilityPlatform ::= TEXTUAL-CONVENTION
    STATUS        current
    DESCRIPTION
        ""
    SYNTAX        INTEGER
    {
        ucs6100(0),
        ucs6200(1),
        ucs6324(2)
    }

CfprCapabilityUpdaterFsmCurrentFsm ::= TEXTUAL-CONVENTION
    STATUS        current
    DESCRIPTION
        ""
    SYNTAX        INTEGER
    {
        nop(0),
        updater(582)
    }

CfprCapabilityUpdaterFsmStageName ::= TEXTUAL-CONVENTION
    STATUS        current
    DESCRIPTION
        ""
    SYNTAX        INTEGER
    {
        nop(0),
        updaterBegin(582),
        updaterLocal(583),
        updaterUnpackLocal(584),
        updaterDeleteLocal(585),
        updaterCopyRemote(586),
        updaterApply(587),
        updaterRescanImages(588),
        updaterFail(589),
        updaterSuccess(590),
        updaterEvaluateStatus(903)
    }

CfprCapabilityUpdaterFsmTaskItem ::= TEXTUAL-CONVENTION
    STATUS        current
    DESCRIPTION
        ""
    SYNTAX        INTEGER
    {
        nop(0),
        updater(582)
    }

CfprChangeStatus ::= TEXTUAL-CONVENTION
    STATUS        current
    DESCRIPTION
        ""
    SYNTAX        INTEGER
    {
        modified(0),
        created(1),
        deleted(2),
        intentDeletion(3)
    }

CfprCimcvmediaDeviceType ::= TEXTUAL-CONVENTION
    STATUS        current
    DESCRIPTION
        ""
    SYNTAX        INTEGER
    {
        unknown(0),
        cdd(1),
        hdd(2)
    }

CfprCimcvmediaErrorType ::= TEXTUAL-CONVENTION
    STATUS        current
    DESCRIPTION
        ""
    SYNTAX        INTEGER
    {
        unknown(0),
        none(1),
        genericFailure(2),
        connectionTimeout(3),
        connectionRejected(4),
        authenticationFailed(5),
        badPath(6),
        badParam(7),
        invalidVdiskUsage(8),
        invalidVdiskType(9),
        alreadyMapped(10),
        imageStoreFull(11),
        fileNotFound(12),
        openRoFailed(13),
        openRwFailed(14),
        diskEjected(15),
        diskIoFailure(16),
        writeToReadonlyFile(17),
        mountInUse(18),
        invalidArgument(19),
        imgageDeleted(20),
        postmapError(21)
    }

CfprCimcvmediaMountConfigRetryOnMountFail ::= TEXTUAL-CONVENTION
    STATUS        current
    DESCRIPTION
        ""
    SYNTAX        INTEGER
    {
        no(0),
        yes(1)
    }

CfprCimcvmediaMountStatus ::= TEXTUAL-CONVENTION
    STATUS        current
    DESCRIPTION
        ""
    SYNTAX        INTEGER
    {
        unknown(0),
        mounting(1),
        mounted(2),
        unmounting(3),
        notMounted(4),
        mountFailed(5),
        unmountFailed(6)
    }

CfprCimcvmediaTransport ::= TEXTUAL-CONVENTION
    STATUS        current
    DESCRIPTION
        ""
    SYNTAX        INTEGER
    {
        unknown(0),
        nfs(1),
        cifs(2),
        http(3),
        https(4)
    }

CfprCommAdminState ::= TEXTUAL-CONVENTION
    STATUS        current
    DESCRIPTION
        ""
    SYNTAX        INTEGER
    {
        enabled(1),
        disabled(2)
    }

CfprCommAuth ::= TEXTUAL-CONVENTION
    STATUS        current
    DESCRIPTION
        ""
    SYNTAX        INTEGER
    {
        rsa(1),
        ecdsa(2),
        rsaEcdsa(3)
    }

CfprCommChannel ::= TEXTUAL-CONVENTION
    STATUS        current
    DESCRIPTION
        ""
    SYNTAX        INTEGER
    {
        fullssl(0),
        noencssl(1),
        plain(2)
    }

CfprCommCipherSuiteMode ::= TEXTUAL-CONVENTION
    STATUS        current
    DESCRIPTION
        ""
    SYNTAX        INTEGER
    {
        highStrength(1),
        mediumStrength(2),
        lowStrength(3),
        custom(4)
    }

CfprCommClientAdminState ::= TEXTUAL-CONVENTION
    STATUS        current
    DESCRIPTION
        ""
    SYNTAX        INTEGER
    {
        enabled(1),
        disabled(2)
    }

CfprCommClientItemAdminState ::= TEXTUAL-CONVENTION
    STATUS        current
    DESCRIPTION
        ""
    SYNTAX        INTEGER
    {
        enabled(1),
        disabled(2)
    }

CfprCommCrlModeType ::= TEXTUAL-CONVENTION
    STATUS        current
    DESCRIPTION
        ""
    SYNTAX        INTEGER
    {
        relaxed(1),
        strict(2)
    }

CfprCommDnsProviderAdminState ::= TEXTUAL-CONVENTION
    STATUS        current
    DESCRIPTION
        ""
    SYNTAX        INTEGER
    {
        enabled(1),
        disabled(2)
    }

CfprCommFilePathProtocol ::= TEXTUAL-CONVENTION
    STATUS        current
    DESCRIPTION
        ""
    SYNTAX        INTEGER
    {
        none(0),
        workspace(1),
        volatile(2),
        ftp(3),
        tftp(4),
        scp(5),
        sftp(6),
        usbdrive(7),
        usbA(8),
        usbB(9),
        https(11),
        http(12)
    }

CfprCommHostKeyEcdsa ::= TEXTUAL-CONVENTION
    STATUS        current
    DESCRIPTION
        ""
    SYNTAX        INTEGER
    {
        secp256r1(256),
        secp384r1(384),
        secp521r1(521)
    }

CfprCommHttpRedirectState ::= TEXTUAL-CONVENTION
    STATUS        current
    DESCRIPTION
        ""
    SYNTAX        INTEGER
    {
        enabled(1),
        disabled(2)
    }

CfprCommHttpsAuthType ::= TEXTUAL-CONVENTION
    STATUS        current
    DESCRIPTION
        ""
    SYNTAX        INTEGER
    {
        credAuth(1),
        certAuth(2)
    }

CfprCommIpv4Prefix ::= TEXTUAL-CONVENTION
    STATUS        current
    DESCRIPTION
        ""
    SYNTAX        Gauge32 (0..32)

CfprCommIpv6Prefix ::= TEXTUAL-CONVENTION
    STATUS        current
    DESCRIPTION
        ""
    SYNTAX        Gauge32 (0..128)

CfprCommModeAdminState ::= TEXTUAL-CONVENTION
    STATUS        current
    DESCRIPTION
        ""
    SYNTAX        INTEGER
    {
        disabled(0),
        enabled(1)
    }

CfprCommModeFlag ::= TEXTUAL-CONVENTION
    STATUS        current
    DESCRIPTION
        ""
    SYNTAX        INTEGER
    {
        noChange(0),
        fipsModeChange(1),
        ccModeChange(2),
        ccAndFipsModeChange(3)
    }

CfprCommNtpAuthState ::= TEXTUAL-CONVENTION
    STATUS        current
    DESCRIPTION
        ""
    SYNTAX        INTEGER
    {
        disabled(0),
        enabled(1)
    }

CfprCommNtpProviderAdminState ::= TEXTUAL-CONVENTION
    STATUS        current
    DESCRIPTION
        ""
    SYNTAX        INTEGER
    {
        enabled(1),
        disabled(2)
    }

CfprCommNtpSha1Id ::= TEXTUAL-CONVENTION
    STATUS        current
    DESCRIPTION
        ""
    SYNTAX        Gauge32 (0..65535)

CfprCommProtocol ::= TEXTUAL-CONVENTION
    STATUS        current
    DESCRIPTION
        ""
    SYNTAX        INTEGER
    {
        none(0),
        tcp(1),
        udp(2),
        all(3)
    }

CfprCommRebootState ::= TEXTUAL-CONVENTION
    STATUS        current
    DESCRIPTION
        ""
    SYNTAX        INTEGER
    {
        none(0),
        pendingReboot(1)
    }

CfprCommServiceProtocol ::= TEXTUAL-CONVENTION
    STATUS        current
    DESCRIPTION
        ""
    SYNTAX        INTEGER
    {
        ssh(0),
        https(1),
        snmp(2)
    }

CfprCommShellProto ::= TEXTUAL-CONVENTION
    STATUS        current
    DESCRIPTION
        ""
    SYNTAX        INTEGER
    {
        none(0),
        tcp(1),
        udp(2),
        all(3)
    }

CfprCommSmashCLPProto ::= TEXTUAL-CONVENTION
    STATUS        current
    DESCRIPTION
        ""
    SYNTAX        INTEGER
    {
        none(0),
        tcp(1),
        udp(2),
        all(3)
    }

CfprCommSnmpConfigState ::= TEXTUAL-CONVENTION
    STATUS        current
    DESCRIPTION
        ""
    SYNTAX        INTEGER
    {
        ok(0),
        notApplied(1)
    }

CfprCommSnmpProto ::= TEXTUAL-CONVENTION
    STATUS        current
    DESCRIPTION
        ""
    SYNTAX        INTEGER
    {
        none(0),
        tcp(1),
        udp(2),
        all(3)
    }

CfprCommSnmpAuth ::= TEXTUAL-CONVENTION
    STATUS        current
    DESCRIPTION
        ""
    SYNTAX        INTEGER
    {
        sha(2)
    }

CfprCommSnmpNotificationType ::= TEXTUAL-CONVENTION
    STATUS        current
    DESCRIPTION
        ""
    SYNTAX        INTEGER
    {
        traps(1),
        informs(2)
    }

CfprCommSnmpV3Privilege ::= TEXTUAL-CONVENTION
    STATUS        current
    DESCRIPTION
        ""
    SYNTAX        INTEGER
    {
        auth(1),
        noauth(2),
        priv(3)
    }

CfprCommSnmpVersion ::= TEXTUAL-CONVENTION
    STATUS        current
    DESCRIPTION
        ""
    SYNTAX        INTEGER
    {
        v1(1),
        v2c(2),
        v3(3)
    }

CfprCommSshAdminState ::= TEXTUAL-CONVENTION
    STATUS        current
    DESCRIPTION
        ""
    SYNTAX        INTEGER
    {
        enabled(1),
        disabled(2)
    }

CfprCommSshAuthAlgo ::= TEXTUAL-CONVENTION
    STATUS        current
    DESCRIPTION
        ""
    SYNTAX        INTEGER
    {
        rsa(1),
        norsa(2)
    }

CfprCommSshEncryptAlgo ::= TEXTUAL-CONVENTION
    STATUS        current
    DESCRIPTION
        ""
    SYNTAX        BITS
    {
        aes128Ctr(0),
        aes192Ctr(1),
        aes256Ctr(2),
        n3desCbc(3),
        aes128Cbc(4),
        aes192Cbc(5),
        aes256Cbc(6),
        aes128GcmOpensshCom(7),
        aes256GcmOpensshCom(8),
        chacha20Poly1305OpensshCom(9)
    }

CfprCommSshKexAlgo ::= TEXTUAL-CONVENTION
    STATUS        current
    DESCRIPTION
        ""
    SYNTAX        BITS
    {
        diffieHellmanGroup14Sha1(0),
        curve25519Sha256(1),
        curve25519Sha256LibsshOrg(2),
        ecdhSha2Nistp256(3),
        ecdhSha2Nistp384(4),
        ecdhSha2Nistp521(5),
        diffieHellmanGroup14Sha256(6)
    }

CfprCommSshMacAlgo ::= TEXTUAL-CONVENTION
    STATUS        current
    DESCRIPTION
        ""
    SYNTAX        BITS
    {
        hmacSha1(0),
        hmacSha2256(2),
        hmacSha2512(3)
    }

CfprCommSshcCliEncryptAlgo ::= TEXTUAL-CONVENTION
    STATUS        current
    DESCRIPTION
        ""
    SYNTAX        BITS
    {
        aes128Ctr(0),
        aes192Ctr(1),
        aes256Ctr(2),
        n3desCbc(3),
        aes128Cbc(4),
        aes192Cbc(5),
        aes256Cbc(6),
        aes128GcmOpensshCom(7),
        aes256GcmOpensshCom(8),
        chacha20Poly1305OpensshCom(9)
    }

CfprCommSshcCliKexAlgo ::= TEXTUAL-CONVENTION
    STATUS        current
    DESCRIPTION
        ""
    SYNTAX        BITS
    {
        diffieHellmanGroup14Sha1(0),
        curve25519Sha256(1),
        curve25519Sha256LibsshOrg(2),
        ecdhSha2Nistp256(3),
        ecdhSha2Nistp384(4),
        ecdhSha2Nistp521(5),
        diffieHellmanGroup14Sha256(6)
    }

CfprCommSshcCliMacAlgo ::= TEXTUAL-CONVENTION
    STATUS        current
    DESCRIPTION
        ""
    SYNTAX        BITS
    {
        hmacSha1(0),
        hmacSha2256(2),
        hmacSha2512(3)
    }

CfprCommSshcStrictKeyCheck ::= TEXTUAL-CONVENTION
    STATUS        current
    DESCRIPTION
        ""
    SYNTAX        INTEGER
    {
        disable(0),
        enable(1),
        prompt(2)
    }

CfprCommSvcEpFsmCurrentFsm ::= TEXTUAL-CONVENTION
    STATUS        current
    DESCRIPTION
        ""
    SYNTAX        INTEGER
    {
        nop(0),
        updateSvcEp(190),
        restartWebSvc(193)
    }

CfprCommSvcEpFsmStageName ::= TEXTUAL-CONVENTION
    STATUS        current
    DESCRIPTION
        ""
    SYNTAX        INTEGER
    {
        nop(0),
        updateSvcEpBegin(190),
        updateSvcEpSetEpLocal(191),
        updateSvcEpSetEpPeer(192),
        restartWebSvcBegin(193),
        restartWebSvcFail(332),
        restartWebSvcSuccess(333),
        updateSvcEpFail(334),
        updateSvcEpSuccess(335),
        updateSvcEpPropogateEpSettings(532),
        updateSvcEpPropogateEpTimeZoneSettingsLocal(592),
        updateSvcEpPropogateEpTimeZoneSettingsPeer(593),
        updateSvcEpPropogateEpTimeZoneSettingsToAdaptorsLocal(877),
        updateSvcEpPropogateEpTimeZoneSettingsToAdaptorsPeer(878),
        updateSvcEpPropogateEpTimeZoneSettingsToFexIomLocal(1046),
        updateSvcEpPropogateEpTimeZoneSettingsToFexIomPeer(1047),
        restartWebSvcLocal(1165),
        restartWebSvcPeer(1166),
        updateSvcEpInitIptablesLocal(2034),
        updateSvcEpInitIptablesPeer(2035)
    }

CfprCommSvcEpFsmTaskFlags ::= TEXTUAL-CONVENTION
    STATUS        current
    DESCRIPTION
        ""
    SYNTAX        BITS
    {
        samDmeCommSvcEpUpdateSvcEpEpChange(21),
        samDmeCommSvcEpUpdateSvcEpPropogateSettings(22)
    }

CfprCommSvcEpFsmTaskItem ::= TEXTUAL-CONVENTION
    STATUS        current
    DESCRIPTION
        ""
    SYNTAX        INTEGER
    {
        nop(0),
        updateSvcEp(190),
        restartWebSvc(193)
    }

CfprCommSysTimeSyncStatus ::= TEXTUAL-CONVENTION
    STATUS        current
    DESCRIPTION
        ""
    SYNTAX        INTEGER
    {
        ntpNotConfigured(0),
        ntpConfigFailed(1),
        timeSyncInProgress(2),
        timeSynchronized(3)
    }

CfprCommSyslogProto ::= TEXTUAL-CONVENTION
    STATUS        current
    DESCRIPTION
        ""
    SYNTAX        INTEGER
    {
        none(0),
        tcp(1),
        udp(2),
        all(3)
    }

CfprCommSyslogAdminState ::= TEXTUAL-CONVENTION
    STATUS        current
    DESCRIPTION
        ""
    SYNTAX        INTEGER
    {
        enabled(1),
        disabled(2)
    }

CfprCommSyslogClientEnum ::= TEXTUAL-CONVENTION
    STATUS        current
    DESCRIPTION
        ""
    SYNTAX        INTEGER
    {
        primary(1),
        secondary(2),
        tertiary(3)
    }

CfprCommSyslogFileSize ::= TEXTUAL-CONVENTION
    STATUS        current
    DESCRIPTION
        ""
    SYNTAX        Gauge32 (4096..4194304)

CfprCommSyslogForwardingFacility ::= TEXTUAL-CONVENTION
    STATUS        current
    DESCRIPTION
        ""
    SYNTAX        INTEGER
    {
        local0(0),
        local1(1),
        local2(2),
        local3(3),
        local4(4),
        local5(5),
        local6(6),
        local7(7)
    }

CfprCommSyslogPlatformAdminState ::= TEXTUAL-CONVENTION
    STATUS        current
    DESCRIPTION
        ""
    SYNTAX        INTEGER
    {
        enabled(1),
        disabled(2)
    }

CfprCommSyslogRestrictedSeverity ::= TEXTUAL-CONVENTION
    STATUS        current
    DESCRIPTION
        ""
    SYNTAX        INTEGER
    {
        emergencies(0),
        alerts(1),
        critical(2)
    }

CfprCommSyslogSeverity ::= TEXTUAL-CONVENTION
    STATUS        current
    DESCRIPTION
        ""
    SYNTAX        INTEGER
    {
        emergencies(0),
        alerts(1),
        critical(2),
        errors(3),
        warnings(4),
        notifications(5),
        information(6),
        debugging(7)
    }

CfprCommSyslogSourceAudits ::= TEXTUAL-CONVENTION
    STATUS        current
    DESCRIPTION
        ""
    SYNTAX        INTEGER
    {
        enabled(1),
        disabled(2)
    }

CfprCommSyslogSourceEvents ::= TEXTUAL-CONVENTION
    STATUS        current
    DESCRIPTION
        ""
    SYNTAX        INTEGER
    {
        enabled(1),
        disabled(2)
    }

CfprCommSyslogSourceFaults ::= TEXTUAL-CONVENTION
    STATUS        current
    DESCRIPTION
        ""
    SYNTAX        INTEGER
    {
        enabled(1),
        disabled(2)
    }

CfprCommTelemetryAdminState ::= TEXTUAL-CONVENTION
    STATUS        current
    DESCRIPTION
        ""
    SYNTAX        INTEGER
    {
        disabled(0),
        enabled(1)
    }

CfprCommTelemetryFsmCurrentFsm ::= TEXTUAL-CONVENTION
    STATUS        current
    DESCRIPTION
        ""
    SYNTAX        INTEGER
    {
        nop(0),
        dataExchSeq(2036),
        enableDisableTelemetry(2040)
    }

CfprCommTelemetryFsmStageName ::= TEXTUAL-CONVENTION
    STATUS        current
    DESCRIPTION
        ""
    SYNTAX        INTEGER
    {
        nop(0),
        dataExchSeqBegin(2036),
        dataExchSeqRegisterforTelemetry(2037),
        dataExchSeqGetTelemetryData(2038),
        dataExchSeqSendTelemetryData(2039),
        enableDisableTelemetryBegin(2040),
        enableDisableTelemetrySendChassisConfig(2041),
        enableDisableTelemetryUnRegister(2042),
        dataExchSeqFail(2057),
        dataExchSeqSuccess(2058),
        enableDisableTelemetryFail(2059),
        enableDisableTelemetrySuccess(2060)
    }

CfprCommTelemetryFsmTaskItem ::= TEXTUAL-CONVENTION
    STATUS        current
    DESCRIPTION
        ""
    SYNTAX        INTEGER
    {
        nop(0),
        dataExchSeq(2036),
        enableDisableTelemetry(2040)
    }

CfprCommTelemetryOperState ::= TEXTUAL-CONVENTION
    STATUS        current
    DESCRIPTION
        ""
    SYNTAX        INTEGER
    {
        unregistering(0),
        unregisterFailure(1),
        registering(2),
        registerFailure(3),
        starting(4),
        getData(5),
        getDataFailure(6),
        sendData(7),
        sendDataFailure(8),
        ok(9),
        unknown(10)
    }

CfprCommTimeSyncStatus ::= TEXTUAL-CONVENTION
    STATUS        current
    DESCRIPTION
        ""
    SYNTAX        INTEGER
    {
        notAvailable(0),
        unreachableOrInvalidNtpServer(1),
        timeSyncInProgress(2),
        timeSynchronized(3),
        candidate(4),
        falsetick(5),
        outlier(6)
    }

CfprCommTimeZoneConfigState ::= TEXTUAL-CONVENTION
    STATUS        current
    DESCRIPTION
        ""
    SYNTAX        INTEGER
    {
        success(0),
        failure(1)
    }

CfprCommTlsVerType ::= TEXTUAL-CONVENTION
    STATUS        current
    DESCRIPTION
        ""
    SYNTAX        INTEGER
    {
        v10(0),
        v11(1),
        v12(2)
    }

CfprCommWebProto ::= TEXTUAL-CONVENTION
    STATUS        current
    DESCRIPTION
        ""
    SYNTAX        INTEGER
    {
        none(0),
        tcp(1),
        udp(2),
        all(3)
    }

CfprCommXmlClConnPolicyClientType ::= TEXTUAL-CONVENTION
    STATUS        current
    DESCRIPTION
        ""
    SYNTAX        INTEGER
    {
        javaUi(0),
        flexUi(1),
        extrenalApiClient(2)
    }

CfprComputeABoardPower ::= TEXTUAL-CONVENTION
    STATUS        current
    DESCRIPTION
        ""
    SYNTAX        INTEGER
    {
        unknown(0),
        on(1),
        test(2),
        off(3),
        online(4),
        offline(5),
        offduty(6),
        degraded(7),
        powerSave(8),
        error(9),
        ok(10),
        failed(11),
        oirFailed(12),
        oirInvalid(13),
        notSupported(100)
    }

CfprComputeAdminLinkAggregation ::= TEXTUAL-CONVENTION
    STATUS        current
    DESCRIPTION
        ""
    SYNTAX        INTEGER
    {
        none(0),
        portChannel(1),
        global(2)
    }

CfprComputeAdminMemoryState ::= TEXTUAL-CONVENTION
    STATUS        current
    DESCRIPTION
        ""
    SYNTAX        INTEGER
    {
        policy(1),
        resetMemoryErrors(2),
        resetInProgress(3)
    }

CfprComputeAdminPowerState ::= TEXTUAL-CONVENTION
    STATUS        current
    DESCRIPTION
        ""
    SYNTAX        INTEGER
    {
        cycleImmediate(2),
        cycleWait(3),
        hardResetImmediate(4),
        hardResetWait(5),
        cmosResetImmediate(12),
        bmcResetImmediate(13),
        bmcResetWait(14),
        diagnosticInterrupt(15),
        kvmReset(16),
        policy(30),
        adminUp(31),
        adminDown(32),
        ipmiReset(33)
    }

CfprComputeAdminState ::= TEXTUAL-CONVENTION
    STATUS        current
    DESCRIPTION
        ""
    SYNTAX        INTEGER
    {
        inService(1),
        outOfService(2)
    }

CfprComputeAdminTrigger ::= TEXTUAL-CONVENTION
    STATUS        current
    DESCRIPTION
        ""
    SYNTAX        INTEGER
    {
        undiscovered(0),
        rediscover(1),
        resetToFactory(2),
        discovered(3),
        remove(4),
        migrate(5),
        decommission(6),
        upgradeFirmware(7),
        decommissionSecure(8)
    }

CfprComputeAlarmSeverity ::= TEXTUAL-CONVENTION
    STATUS        current
    DESCRIPTION
        ""
    SYNTAX        INTEGER
    {
        minor(1),
        severe(2)
    }

CfprComputeAssociation ::= TEXTUAL-CONVENTION
    STATUS        current
    DESCRIPTION
        ""
    SYNTAX        INTEGER
    {
        none(0),
        establishing(1),
        associated(2),
        removing(3),
        failed(4),
        throttled(5)
    }

CfprComputeAvailability ::= TEXTUAL-CONVENTION
    STATUS        current
    DESCRIPTION
        ""
    SYNTAX        INTEGER
    {
        unavailable(0),
        available(1)
    }

CfprComputeBlackListing ::= TEXTUAL-CONVENTION
    STATUS        current
    DESCRIPTION
        ""
    SYNTAX        INTEGER
    {
        disabled(0),
        enabled(1)
    }

CfprComputeBladeSlotId ::= TEXTUAL-CONVENTION
    STATUS        current
    DESCRIPTION
        ""
    SYNTAX        Gauge32 (1..8)

CfprComputeBladeFsmCurrentFsm ::= TEXTUAL-CONVENTION
    STATUS        current
    DESCRIPTION
        ""
    SYNTAX        INTEGER
    {
        nop(0),
        discover(23),
        diag(144),
        associate(665),
        disassociate(727),
        powerCap(767),
        decommission(769),
        softShutdown(771),
        hardShutdown(773),
        turnup(775),
        powercycle(777),
        hardreset(781),
        softreset(785),
        swConnUpd(789),
        biosRecovery(792),
        cmosReset(806),
        resetBmc(815),
        updateExtUsers(879),
        updateAdaptor(891),
        activateAdaptor(898),
        configSoL(932),
        unconfigSoL(934),
        diagnosticInterrupt(1036),
        resetKvm(1055),
        updateBIOS(1152),
        activateBIOS(1157),
        resetIpmi(1200),
        fwUpgrade(1202),
        cimcSessionDelete(1477),
        updateBoardController(1497),
        configBoard(1506),
        resetMemoryErrors(1508),
        serviceInfraDeploy(1531),
        serviceInfraWithdraw(1536),
        flashController(1638),
        enableCimcSecureBoot(1669),
        updateAdaptorBoot(1991),
        hardPowercycle(2055)
    }

CfprComputeBladeFsmStageName ::= TEXTUAL-CONVENTION
    STATUS        current
    DESCRIPTION
        ""
    SYNTAX        INTEGER
    {
        nop(0),
        discoverBegin(23),
        discoverBmcPresence(24),
        discoverBmcInventory(25),
        discoverConfigFeLocal(26),
        discoverConfigFePeer(27),
        discoverConfigUserAccess(28),
        discoverBladePowerOn(29),
        discoverSwConfigPnuOSLocal(33),
        discoverSwConfigPnuOSPeer(34),
        discoverBladeBootPnuos(35),
        discoverBladeReadSmbios(36),
        discoverHagConnect(37),
        discoverPnuOSIdent(38),
        discoverPnuOSPolicy(39),
        discoverPnuOSInventory(40),
        discoverPnuOSSelfTest(41),
        discoverSwUnconfigPnuOSLocal(43),
        discoverSwUnconfigPnuOSPeer(44),
        discoverHagDisconnect(45),
        discoverBmcShutdownDiscovered(46),
        discoverHandlePooling(47),
        discoverSuccess(48),
        discoverFail(49),
        diagBegin(144),
        diagBmcPresence(145),
        diagBmcInventory(146),
        diagConfigFeLocal(147),
        diagConfigFePeer(148),
        diagBladePowerOn(149),
        diagDeriveConfig(152),
        diagConfigUserAccess(153),
        diagSwConfigLocal(155),
        diagSwConfigPeer(156),
        diagSetupVMediaLocal(158),
        diagSetupVMediaPeer(159),
        diagBladeBoot(160),
        diagBladeReadSmbios(161),
        diagHostConnect(162),
        diagHostIdent(165),
        diagHostPolicy(166),
        diagSetDiagUser(167),
        diagHostInventory(168),
        diagGenerateReport(171),
        diagRemoveConfig(172),
        diagRemoveVMediaLocal(173),
        diagRemoveVMediaPeer(174),
        diagSwUnconfigLocal(176),
        diagSwUnconfigPeer(177),
        diagUnconfigUserAccess(178),
        diagHostDisconnect(180),
        diagBmcShutdownDiagCompleted(181),
        diagSuccess(182),
        diagFail(183),
        discoverPnuOSScrub(458),
        diagHostServerDiag(479),
        diagHostServerDiagStatus(480),
        diagDisableServerConnSwB(481),
        diagStartFabricATrafficTest(482),
        diagFabricATrafficTestStatus(483),
        diagEnableServerConnSwB(484),
        diagDisableServerConnSwA(485),
        diagStartFabricBTrafficTest(486),
        diagFabricBTrafficTestStatus(487),
        diagEnableServerConnSwA(488),
        discoverBladeBootWait(504),
        diagBladeBootWait(519),
        diagBiosPostCompletion(520),
        discoverBiosPostCompletion(521),
        diagRestoreConfigFeLocal(526),
        diagRestoreConfigFePeer(527),
        discoverSetupVmediaLocal(528),
        discoverSetupVmediaPeer(529),
        discoverTeardownVmediaLocal(530),
        discoverTeardownVmediaPeer(531),
        diagGenerateLogWait(533),
        diagStopVMediaLocal(534),
        diagStopVMediaPeer(535),
        discoverSanitize(545),
        discoverPreSanitize(567),
        diagDebugWait(591),
        diagEvaluateStatus(599),
        diagNicPresenceLocal(647),
        diagNicPresencePeer(648),
        diagNicInventoryLocal(649),
        diagNicInventoryPeer(650),
        diagNicConfigLocal(651),
        diagNicConfigPeer(652),
        diagNicUnconfigLocal(653),
        diagNicUnconfigPeer(654),
        discoverNicPresenceLocal(657),
        discoverNicPresencePeer(658),
        discoverNicConfigPnuOSLocal(659),
        discoverNicConfigPnuOSPeer(660),
        discoverNicUnconfigPnuOSLocal(663),
        discoverNicUnconfigPnuOSPeer(664),
        associateBegin(665),
        associateUpdateIBMCFw(668),
        associateWaitForIBMCFwUpdate(669),
        associateActivateIBMCFw(670),
        associateResetIBMC(671),
        associatePreSanitize(672),
        associateSanitize(673),
        associateConfigUserAccess(674),
        associateBladePowerOff(675),
        associateUpdateBoardCtrlRequest(676),
        associatePollBoardCtrlUpdateStatus(677),
        associatePowerOn(678),
        associateBmcPreconfigPnuOSLocal(679),
        associateBmcPreconfigPnuOSPeer(680),
        associateBmcConfigPnuOS(681),
        associateSwConfigPnuOSLocal(682),
        associateSwConfigPnuOSPeer(683),
        associateUpdateAdaptorNwFwLocal(684),
        associateUpdateAdaptorNwFwPeer(685),
        associateWaitForAdaptorNwFwUpdateLocal(686),
        associateWaitForAdaptorNwFwUpdatePeer(687),
        associateActivateAdaptorNwFwLocal(688),
        associateActivateAdaptorNwFwPeer(689),
        associateNicConfigPnuOSLocal(690),
        associateNicConfigPnuOSPeer(691),
        associateBootPnuos(692),
        associateBootWait(693),
        associateBiosPostCompletion(694),
        associateHagPnuOSConnect(695),
        associatePnuOSIdent(696),
        associatePnuOSPolicy(697),
        associatePnuOSValidate(698),
        associatePnuOSSelfTest(699),
        associateBiosImgUpdate(700),
        associateStorageCtlrImgUpdate(701),
        associateHbaImgUpdate(702),
        associateNicImgUpdate(703),
        associatePnuOSInventory(704),
        associatePnuOSConfig(705),
        associatePnuOSLocalDiskConfig(706),
        associatePnuOSUnloadDrivers(707),
        associateBmcUnconfigPnuOS(708),
        associateNicUnconfigPnuOSLocal(709),
        associateNicUnconfigPnuOSPeer(710),
        associateSwUnconfigPnuOSLocal(711),
        associateSwUnconfigPnuOSPeer(712),
        associateSwConfigHostOSLocal(713),
        associateSwConfigHostOSPeer(714),
        associateNicConfigHostOSLocal(715),
        associateNicConfigHostOSPeer(716),
        associateHagPnuOSDisconnect(717),
        associateConfigSoL(718),
        associatePrepareForBoot(719),
        associateConfigUuid(720),
        associateBootHost(721),
        associateHagHostOSConnect(722),
        associateHostOSIdent(723),
        associateHostOSPolicy(724),
        associateHostOSValidate(725),
        associateHostOSConfig(726),
        disassociateBegin(727),
        disassociateConfigUserAccess(730),
        disassociatePowerOn(731),
        disassociatePreSanitize(732),
        disassociateSanitize(733),
        disassociateNicUnconfigHostOSLocal(734),
        disassociateNicUnconfigHostOSPeer(735),
        disassociateSwUnconfigHostOSLocal(736),
        disassociateSwUnconfigHostOSPeer(737),
        disassociateBmcPreconfigPnuOSLocal(738),
        disassociateBmcPreconfigPnuOSPeer(739),
        disassociateBmcConfigPnuOS(740),
        disassociateSwConfigPnuOSLocal(741),
        disassociateSwConfigPnuOSPeer(742),
        disassociateNicConfigPnuOSLocal(743),
        disassociateNicConfigPnuOSPeer(744),
        disassociateConfigBios(745),
        disassociateBootPnuos(746),
        disassociateBootWait(747),
        disassociateBiosPostCompletion(748),
        disassociateHagPnuOSConnect(749),
        disassociatePnuOSIdent(750),
        disassociatePnuOSPolicy(751),
        disassociatePnuOSValidate(752),
        disassociatePnuOSUnconfig(753),
        disassociatePnuOSScrub(754),
        disassociatePnuOSSelfTest(755),
        disassociateBmcUnconfigPnuOS(756),
        disassociateNicUnconfigPnuOSLocal(757),
        disassociateNicUnconfigPnuOSPeer(758),
        disassociateHagPnuOSDisconnect(759),
        disassociateUnconfigUuid(760),
        disassociateShutdown(761),
        disassociateUnconfigBios(762),
        disassociateSwUnconfigPnuOSLocal(763),
        disassociateSwUnconfigPnuOSPeer(764),
        disassociateUnconfigSoL(765),
        disassociateHandlePooling(766),
        powerCapBegin(767),
        powerCapConfig(768),
        decommissionBegin(769),
        decommissionExecute(770),
        softShutdownBegin(771),
        softShutdownExecute(772),
        hardShutdownBegin(773),
        hardShutdownExecute(774),
        turnupBegin(775),
        turnupExecute(776),
        powercycleBegin(777),
        powercyclePreSanitize(778),
        powercycleSanitize(779),
        powercycleExecute(780),
        hardresetBegin(781),
        hardresetPreSanitize(782),
        hardresetSanitize(783),
        hardresetExecute(784),
        softresetBegin(785),
        softresetPreSanitize(786),
        softresetSanitize(787),
        softresetExecute(788),
        swConnUpdBegin(789),
        swConnUpdA(790),
        swConnUpdB(791),
        biosRecoveryBegin(792),
        biosRecoveryShutdown(793),
        biosRecoveryPreSanitize(794),
        biosRecoverySanitize(795),
        biosRecoverySetupVmediaLocal(796),
        biosRecoverySetupVmediaPeer(797),
        biosRecoveryStart(798),
        biosRecoveryWait(799),
        biosRecoveryCleanup(800),
        biosRecoveryReset(801),
        biosRecoveryTeardownVmediaLocal(802),
        biosRecoveryTeardownVmediaPeer(803),
        cmosResetBegin(806),
        cmosResetPreSanitize(807),
        cmosResetSanitize(808),
        cmosResetExecute(809),
        cmosResetReconfigBios(810),
        cmosResetReconfigUuid(811),
        cmosResetBladePowerOn(812),
        resetBmcBegin(815),
        resetBmcExecute(816),
        updateExtUsersBegin(879),
        updateExtUsersDeploy(880),
        updateAdaptorBegin(891),
        updateAdaptorPowerOn(892),
        updateAdaptorUpdateRequestLocal(893),
        updateAdaptorUpdateRequestPeer(894),
        updateAdaptorPollUpdateStatusLocal(895),
        updateAdaptorPollUpdateStatusPeer(896),
        updateAdaptorPowerOff(897),
        activateAdaptorBegin(898),
        activateAdaptorPowerOn(899),
        activateAdaptorActivateLocal(900),
        activateAdaptorActivatePeer(901),
        activateAdaptorReset(902),
        configSoLBegin(932),
        configSoLExecute(933),
        unconfigSoLBegin(934),
        unconfigSoLExecute(935),
        activateAdaptorFail(940),
        activateAdaptorSuccess(941),
        associateFail(942),
        associateSuccess(943),
        biosRecoveryFail(946),
        biosRecoverySuccess(947),
        cmosResetFail(948),
        cmosResetSuccess(949),
        configSoLFail(950),
        configSoLSuccess(951),
        decommissionFail(952),
        decommissionSuccess(953),
        disassociateFail(954),
        disassociateSuccess(955),
        hardShutdownFail(956),
        hardShutdownSuccess(957),
        hardresetFail(958),
        hardresetSuccess(959),
        powerCapFail(960),
        powerCapSuccess(961),
        powercycleFail(962),
        powercycleSuccess(963),
        resetBmcFail(964),
        resetBmcSuccess(965),
        softShutdownFail(966),
        softShutdownSuccess(967),
        softresetFail(968),
        softresetSuccess(969),
        swConnUpdFail(970),
        swConnUpdSuccess(971),
        turnupFail(972),
        turnupSuccess(973),
        unconfigSoLFail(974),
        unconfigSoLSuccess(975),
        updateAdaptorFail(976),
        updateAdaptorSuccess(977),
        updateExtUsersFail(978),
        updateExtUsersSuccess(979),
        decommissionStopVMediaLocal(1019),
        decommissionStopVMediaPeer(1020),
        biosRecoveryStopVMediaLocal(1021),
        biosRecoveryStopVMediaPeer(1022),
        diagCleanupServerConnSwA(1032),
        diagCleanupServerConnSwB(1033),
        diagnosticInterruptBegin(1036),
        diagnosticInterruptExecute(1037),
        diagnosticInterruptFail(1038),
        diagnosticInterruptSuccess(1039),
        associateLocalDiskFwUpdate(1040),
        resetKvmBegin(1055),
        resetKvmExecute(1056),
        resetKvmFail(1057),
        resetKvmSuccess(1058),
        associateSwConfigPortNivLocal(1069),
        associateSwConfigPortNivPeer(1070),
        disassociateSwConfigPortNivLocal(1071),
        disassociateSwConfigPortNivPeer(1072),
        discoverBmcPreConfigPnuOSLocal(1078),
        discoverBmcPreConfigPnuOSPeer(1079),
        discoverBmcConfigPnuOS(1080),
        diagBmcConfigPnuOS(1089),
        diagSolRedirectEnable(1096),
        diagSerialDebugConnect(1097),
        diagSerialDebugDisconnect(1098),
        diagSolRedirectDisable(1099),
        discoverSolRedirectEnable(1100),
        discoverSerialDebugConnect(1101),
        discoverSerialDebugDisconnect(1102),
        discoverSolRedirectDisable(1103),
        associateSolRedirectEnable(1104),
        associateSerialDebugPnuOSConnect(1105),
        associateSerialDebugPnuOSDisconnect(1106),
        associateSolRedirectDisable(1107),
        disassociateSolRedirectEnable(1108),
        disassociateSerialDebugPnuOSConnect(1109),
        disassociateSerialDebugPnuOSDisconnect(1110),
        disassociateSolRedirectDisable(1111),
        decommissionCleanupCIMC(1112),
        updateBIOSBegin(1152),
        updateBIOSClear(1153),
        updateBIOSPollClearStatus(1154),
        updateBIOSUpdateRequest(1155),
        updateBIOSPollUpdateStatus(1156),
        activateBIOSBegin(1157),
        activateBIOSPowerOff(1158),
        activateBIOSClear(1159),
        activateBIOSPollClearStatus(1160),
        activateBIOSActivate(1161),
        activateBIOSPollActivateStatus(1162),
        activateBIOSUpdateTokens(1163),
        activateBIOSPowerOn(1164),
        diagHostCatalog(1167),
        discoverPnuOSCatalog(1168),
        associateClearBiosUpdate(1169),
        associatePollClearBiosUpdateStatus(1170),
        associateUpdateBiosRequest(1171),
        associatePollBiosUpdateStatus(1172),
        associateActivateBios(1173),
        associatePollBiosActivateStatus(1174),
        associatePnuOSCatalog(1175),
        disassociatePnuOSCatalog(1176),
        activateBIOSFail(1178),
        activateBIOSSuccess(1179),
        updateBIOSFail(1180),
        updateBIOSSuccess(1181),
        associateMarkAdapterForReboot(1193),
        associateDeassertResetBypass(1194),
        associateVerifyFcZoneConfig(1195),
        disassociateDeassertResetBypass(1196),
        disassociateVerifyFcZoneConfig(1197),
        decommissionCleanupPortConfigLocal(1198),
        decommissionCleanupPortConfigPeer(1199),
        resetIpmiBegin(1200),
        resetIpmiExecute(1201),
        fwUpgradeBegin(1202),
        fwUpgradeUpdateIBMCFw(1203),
        fwUpgradeWaitForIBMCFwUpdate(1204),
        fwUpgradeActivateIBMCFw(1205),
        fwUpgradeResetIBMC(1206),
        fwUpgradePreSanitize(1207),
        fwUpgradeSanitize(1208),
        fwUpgradeBladePowerOff(1209),
        fwUpgradeUpdateBoardCtrlRequest(1210),
        fwUpgradePollBoardCtrlUpdateStatus(1211),
        fwUpgradeClearBiosUpdate(1212),
        fwUpgradePollClearBiosUpdateStatus(1213),
        fwUpgradeUpdateBiosRequest(1214),
        fwUpgradePollBiosUpdateStatus(1215),
        fwUpgradeActivateBios(1216),
        fwUpgradePollBiosActivateStatus(1217),
        fwUpgradePowerOn(1218),
        fwUpgradeBmcPreconfigPnuOSLocal(1219),
        fwUpgradeBmcPreconfigPnuOSPeer(1220),
        fwUpgradeSwConfigPortNivLocal(1221),
        fwUpgradeSwConfigPortNivPeer(1222),
        fwUpgradeSwConfigPnuOSLocal(1223),
        fwUpgradeSwConfigPnuOSPeer(1224),
        fwUpgradeUpdateAdaptorNwFwLocal(1225),
        fwUpgradeUpdateAdaptorNwFwPeer(1226),
        fwUpgradeWaitForAdaptorNwFwUpdateLocal(1227),
        fwUpgradeWaitForAdaptorNwFwUpdatePeer(1228),
        fwUpgradeActivateAdaptorNwFwLocal(1229),
        fwUpgradeActivateAdaptorNwFwPeer(1230),
        fwUpgradeNicConfigPnuOSLocal(1231),
        fwUpgradeNicConfigPnuOSPeer(1232),
        fwUpgradeBmcConfigPnuOS(1233),
        fwUpgradeSolRedirectEnable(1234),
        fwUpgradeSerialDebugPnuOSConnect(1235),
        fwUpgradeBootPnuos(1236),
        fwUpgradeBootWait(1237),
        fwUpgradeBiosPostCompletion(1238),
        fwUpgradeHagPnuOSConnect(1239),
        fwUpgradePnuOSIdent(1240),
        fwUpgradePnuOSPolicy(1241),
        fwUpgradePnuOSCatalog(1242),
        fwUpgradePnuOSValidate(1243),
        fwUpgradePnuOSSelfTest(1244),
        fwUpgradeStorageCtlrImgUpdate(1245),
        fwUpgradeHbaImgUpdate(1246),
        fwUpgradeNicImgUpdate(1247),
        fwUpgradeLocalDiskFwUpdate(1248),
        fwUpgradePnuOSConfig(1249),
        fwUpgradePnuOSInventory(1250),
        fwUpgradeBiosImgUpdate(1251),
        fwUpgradePnuOSUnloadDrivers(1252),
        fwUpgradeBmcUnconfigPnuOS(1253),
        fwUpgradeNicUnconfigPnuOSLocal(1254),
        fwUpgradeNicUnconfigPnuOSPeer(1255),
        fwUpgradeSwUnconfigPnuOSLocal(1256),
        fwUpgradeSwUnconfigPnuOSPeer(1257),
        fwUpgradeDeassertResetBypass(1258),
        fwUpgradeHagPnuOSDisconnect(1259),
        fwUpgradeSerialDebugPnuOSDisconnect(1260),
        fwUpgradeSolRedirectDisable(1261),
        fwUpgradeShutdown(1262),
        activateAdaptorDeassertResetBypass(1307),
        fwUpgradeFail(1386),
        fwUpgradeSuccess(1387),
        resetIpmiFail(1388),
        resetIpmiSuccess(1389),
        associateConfigFlexFlash(1468),
        associateSyncPowerState(1469),
        disassociateUnconfigFlexFlash(1470),
        cimcSessionDeleteBegin(1477),
        cimcSessionDeleteExecute(1478),
        cimcSessionDeleteFail(1483),
        cimcSessionDeleteSuccess(1484),
        updateBoardControllerBegin(1497),
        updateBoardControllerPrepareForUpdate(1498),
        updateBoardControllerServerPowerOff(1499),
        updateBoardControllerUpdateRequest(1500),
        updateBoardControllerPollUpdateStatus(1501),
        updateBoardControllerServerPowerOn(1502),
        configBoardBegin(1506),
        configBoardConfigMemoryPolicy(1507),
        resetMemoryErrorsBegin(1508),
        resetMemoryErrorsExecute(1509),
        discoverOobStorageInventory(1518),
        discoverConfigFlexFlashScrub(1519),
        associateOobStorageInventory(1520),
        associateSwConfigServiceInfraLocal(1521),
        associateSwConfigServiceInfraPeer(1522),
        associateNicConfigServiceInfraLocal(1523),
        associateNicConfigServiceInfraPeer(1524),
        disassociateNicUnconfigServiceInfraLocal(1525),
        disassociateNicUnconfigServiceInfraPeer(1526),
        disassociateConfigFlexFlashScrub(1527),
        serviceInfraDeployBegin(1531),
        serviceInfraDeploySwConfigLocal(1532),
        serviceInfraDeploySwConfigPeer(1533),
        serviceInfraDeployNicConfigLocal(1534),
        serviceInfraDeployNicConfigPeer(1535),
        serviceInfraWithdrawBegin(1536),
        serviceInfraWithdrawSwUnConfigLocal(1537),
        serviceInfraWithdrawSwUnConfigPeer(1538),
        serviceInfraWithdrawNicUnConfigLocal(1539),
        serviceInfraWithdrawNicUnConfigPeer(1540),
        configBoardFail(1541),
        configBoardSuccess(1542),
        resetMemoryErrorsFail(1543),
        resetMemoryErrorsSuccess(1544),
        serviceInfraDeployFail(1545),
        serviceInfraDeploySuccess(1546),
        serviceInfraWithdrawFail(1547),
        serviceInfraWithdrawSuccess(1548),
        updateBoardControllerFail(1549),
        updateBoardControllerSuccess(1550),
        associatePowerOnPreConfig(1561),
        disassociateResetSecureBootConfig(1562),
        discoverConfigBMCPowerParams(1567),
        discoverCheckPowerAvailability(1568),
        discoverSendBmcProfilingInit(1569),
        discoverPnuOSPowerProfiling(1570),
        discoverSendBmcProfilingDone(1571),
        associateDownloadImages(1572),
        associateCopyRemote(1573),
        associateCheckPowerAvailability(1574),
        associateDeleteCurlDownloadedImages(1575),
        fwUpgradeDownloadImages(1576),
        fwUpgradeCopyRemote(1577),
        fwUpgradeDeleteCurlDownloadedImages(1578),
        updateAdaptorCheckPowerAvailability(1597),
        updateAdaptorPowerDeployWait(1598),
        activateAdaptorCheckPowerAvailability(1599),
        activateAdaptorPowerDeployWait(1600),
        discoverPowerDeployWait(1601),
        associatePowerDeployWait(1602),
        disassociateCheckPowerAvailability(1603),
        disassociatePowerDeployWait(1604),
        fwUpgradeCheckPowerAvailability(1605),
        fwUpgradePowerDeployWait(1606),
        discoverUnconfigExtMgmtRules(1617),
        discoverUnconfigExtMgmtGw(1618),
        discoverUnconfigCimcVMedia(1619),
        associateUnconfigExtMgmtRules(1620),
        associateUnconfigExtMgmtGw(1621),
        associateUnconfigCimcVMedia(1622),
        associateGraphicsImageUpdate(1623),
        associateConfigExtMgmtRules(1624),
        associateConfigExtMgmtGw(1625),
        associateConfigCimcVMedia(1626),
        associateSspUpdateHostPreBoot(1627),
        disassociateConfigKvmMgmtDefaultSetting(1628),
        disassociateUnconfigExtMgmtRules(1629),
        disassociateUnconfigExtMgmtGw(1630),
        disassociateUnconfigCimcVMedia(1631),
        decommissionUnconfigExtMgmtRules(1632),
        decommissionUnconfigExtMgmtGw(1633),
        fwUpgradeUnconfigExtMgmtRules(1634),
        fwUpgradeUnconfigExtMgmtGw(1635),
        fwUpgradeUnconfigCimcVMedia(1636),
        fwUpgradeGraphicsImageUpdate(1637),
        flashControllerBegin(1638),
        flashControllerUpdateFlashLife(1639),
        flashControllerFail(1653),
        flashControllerSuccess(1654),
        enableCimcSecureBootBegin(1669),
        enableCimcSecureBootUpdateRequest(1670),
        enableCimcSecureBootPollUpdateStatus(1671),
        enableCimcSecureBootActivate(1672),
        enableCimcSecureBootReset(1673),
        enableCimcSecureBootFail(1676),
        enableCimcSecureBootSuccess(1677),
        discoverPrepareKeyFile(1710),
        associateUpdateSspOsSoftware(1711),
        associateWaitForSspOsUpdateComplete(1712),
        associatePrepareKeyFile(1713),
        updateAdaptorBootBegin(1991),
        updateAdaptorBootCheckPowerAvailability(1992),
        updateAdaptorBootPowerDeployWait(1993),
        updateAdaptorBootPowerOn(1994),
        updateAdaptorBootUpdateRequestLocal(1995),
        updateAdaptorBootUpdateRequestPeer(1996),
        updateAdaptorBootPollUpdateStatusLocal(1997),
        updateAdaptorBootPollUpdateStatusPeer(1998),
        updateAdaptorBootPowerOff(1999),
        updateAdaptorBootFail(2000),
        updateAdaptorBootSuccess(2001),
        hardPowercycleBegin(2055),
        hardPowercycleExecute(2056),
        hardPowercycleFail(2061),
        hardPowercycleSuccess(2062)
    }

CfprComputeBladeFsmTaskFlags ::= TEXTUAL-CONVENTION
    STATUS        current
    DESCRIPTION
        ""
    SYNTAX        BITS
    {
        samDmeComputeBladeDiscoverCheckPoint(0),
        samDmeComputeBladeDiagEfiDiag(18),
        samDmeComputeBladeDiagDetailDiag(20),
        samDmeComputeBladeDiagCancelDiag(23)
    }

CfprComputeBladeFsmTaskItem ::= TEXTUAL-CONVENTION
    STATUS        current
    DESCRIPTION
        ""
    SYNTAX        INTEGER
    {
        nop(0),
        discover(23),
        diag(144)
    }

CfprComputeChassisConnPolicyChassisId ::= TEXTUAL-CONVENTION
    STATUS        current
    DESCRIPTION
        ""
    SYNTAX        Gauge32 (1..255)

CfprComputeChassisDiscAction ::= TEXTUAL-CONVENTION
    STATUS        current
    DESCRIPTION
        ""
    SYNTAX        INTEGER
    {
        immediate(0),
        userAcknowledged(1),
        n1Link(2),
        n2Link(3),
        n4Link(4),
        n8Link(5),
        platformMax(6)
    }

CfprComputeChassisQualMaxId ::= TEXTUAL-CONVENTION
    STATUS        current
    DESCRIPTION
        ""
    SYNTAX        Gauge32 (1..255)

CfprComputeChassisQualMinId ::= TEXTUAL-CONVENTION
    STATUS        current
    DESCRIPTION
        ""
    SYNTAX        Gauge32 (1..255)

CfprComputeCheckPoint ::= TEXTUAL-CONVENTION
    STATUS        current
    DESCRIPTION
        ""
    SYNTAX        INTEGER
    {
        unknown(0),
        removing(1),
        shallowCheckpoint(2),
        deepCheckpoint(3),
        discovered(4)
    }

CfprComputeConnectivityRebalancing ::= TEXTUAL-CONVENTION
    STATUS        current
    DESCRIPTION
        ""
    SYNTAX        INTEGER
    {
        immediate(0),
        userAcknowledged(1)
    }

CfprComputeDecommissionState ::= TEXTUAL-CONVENTION
    STATUS        current
    DESCRIPTION
        ""
    SYNTAX        INTEGER
    {
        none(0),
        succeeded(1),
        failed(2),
        inProgress(3)
    }

CfprComputeDiscovery ::= TEXTUAL-CONVENTION
    STATUS        current
    DESCRIPTION
        ""
    SYNTAX        INTEGER
    {
        undiscovered(0),
        inProgress(1),
        malformedFruInfo(2),
        fruNotReady(3),
        insufficientlyEquipped(4),
        invalidAdaptorIocard(5),
        failed(8),
        complete(16),
        retry(32),
        throttled(64),
        illegalFru(128),
        fruIdentityIndeterminate(129),
        fruStateIndeterminate(130),
        diagnosticsInProgress(131),
        efidiagnosticsInProgress(132),
        diagnosticsFailed(133),
        diagnosticsComplete(134),
        waitingForUserAck(135),
        userAcknowledged(136),
        waitingForMgmtAck(137),
        illegalPartNumber(138)
    }

CfprComputeIOHubEnvStatsThresholded ::= TEXTUAL-CONVENTION
    STATUS        current
    DESCRIPTION
        ""
    SYNTAX        BITS
    {
        temperature(0),
        temperatureAvg(1),
        temperatureMax(2),
        temperatureMin(3)
    }

CfprComputeIOHubEnvStatsHistThresholded ::= TEXTUAL-CONVENTION
    STATUS        current
    DESCRIPTION
        ""
    SYNTAX        BITS
    {
        temperature(0),
        temperatureAvg(1),
        temperatureMax(2),
        temperatureMin(3)
    }

CfprComputeIssues ::= TEXTUAL-CONVENTION
    STATUS        current
    DESCRIPTION
        ""
    SYNTAX        BITS
    {
        computeThermal(0),
        computeInoperable(1),
        computeVoltage(2),
        computePerf(3),
        computePower(4),
        removed(5),
        config(6),
        computePostFailure(7),
        cpuThermal(8),
        cpuInoperable(9),
        cpuVoltage(10),
        cpuPerf(11),
        cpuPower(12),
        memoryThermal(13),
        memoryInoperable(14),
        memoryVoltage(15),
        memoryPerf(16),
        memoryPower(17),
        adaptorThermal(18),
        adaptorInoperable(19),
        adaptorVoltage(20),
        adaptorPerf(21),
        adaptorPower(22),
        nicThermal(23),
        nicInoperable(24),
        nicVoltage(25),
        nicPerf(26),
        nicPower(27),
        hbaThermal(28),
        hbaInoperable(29),
        hbaVoltage(30),
        hbaPerf(31),
        hbaPower(32),
        mismatch(33),
        powerInoperable(34),
        networkMisconfig(35),
        adaptorMismatch(36)
    }

CfprComputeKvmMgmtPolicyVmediaEncryption ::= TEXTUAL-CONVENTION
    STATUS        current
    DESCRIPTION
        ""
    SYNTAX        INTEGER
    {
        disable(0),
        enable(1)
    }

CfprComputeLinkAggregation ::= TEXTUAL-CONVENTION
    STATUS        current
    DESCRIPTION
        ""
    SYNTAX        INTEGER
    {
        none(0),
        portChannel(1)
    }

CfprComputeLinkAggregationCap ::= TEXTUAL-CONVENTION
    STATUS        current
    DESCRIPTION
        ""
    SYNTAX        BITS
    {
        portChannel(0)
    }

CfprComputeMbPowerStatsThresholded ::= TEXTUAL-CONVENTION
    STATUS        current
    DESCRIPTION
        ""
    SYNTAX        BITS
    {
        consumedPower(0),
        consumedPowerAvg(1),
        consumedPowerMax(2),
        consumedPowerMin(3),
        inputCurrent(4),
        inputCurrentAvg(5),
        inputCurrentMax(6),
        inputCurrentMin(7),
        inputVoltage(8),
        inputVoltageAvg(9),
        inputVoltageMax(10),
        inputVoltageMin(11)
    }

CfprComputeMbPowerStatsHistThresholded ::= TEXTUAL-CONVENTION
    STATUS        current
    DESCRIPTION
        ""
    SYNTAX        BITS
    {
        consumedPower(0),
        consumedPowerAvg(1),
        consumedPowerMax(2),
        consumedPowerMin(3),
        inputCurrent(4),
        inputCurrentAvg(5),
        inputCurrentMax(6),
        inputCurrentMin(7),
        inputVoltage(8),
        inputVoltageAvg(9),
        inputVoltageMax(10),
        inputVoltageMin(11)
    }

CfprComputeMbTempStatsThresholded ::= TEXTUAL-CONVENTION
    STATUS        current
    DESCRIPTION
        ""
    SYNTAX        BITS
    {
        fmTempSenIo(0),
        fmTempSenIoAvg(1),
        fmTempSenIoMax(2),
        fmTempSenIoMin(3),
        fmTempSenRear(4),
        fmTempSenRearAvg(5),
        fmTempSenRearL(6),
        fmTempSenRearLAvg(7),
        fmTempSenRearLMax(8),
        fmTempSenRearLMin(9),
        fmTempSenRearMax(10),
        fmTempSenRearMin(11),
        fmTempSenRearR(12),
        fmTempSenRearRAvg(13),
        fmTempSenRearRMax(14),
        fmTempSenRearRMin(15)
    }

CfprComputeMbTempStatsHistThresholded ::= TEXTUAL-CONVENTION
    STATUS        current
    DESCRIPTION
        ""
    SYNTAX        BITS
    {
        fmTempSenIo(0),
        fmTempSenIoAvg(1),
        fmTempSenIoMax(2),
        fmTempSenIoMin(3),
        fmTempSenRear(4),
        fmTempSenRearAvg(5),
        fmTempSenRearL(6),
        fmTempSenRearLAvg(7),
        fmTempSenRearLMax(8),
        fmTempSenRearLMin(9),
        fmTempSenRearMax(10),
        fmTempSenRearMin(11),
        fmTempSenRearR(12),
        fmTempSenRearRAvg(13),
        fmTempSenRearRMax(14),
        fmTempSenRearRMin(15)
    }

CfprComputeMemoryUnitConstraintType ::= TEXTUAL-CONVENTION
    STATUS        current
    DESCRIPTION
        ""
    SYNTAX        INTEGER
    {
        unknown(0),
        kit(1)
    }

CfprComputeMode ::= TEXTUAL-CONVENTION
    STATUS        current
    DESCRIPTION
        ""
    SYNTAX        INTEGER
    {
        none(0),
        single(1),
        scaled(2)
    }

CfprComputeOwner ::= TEXTUAL-CONVENTION
    STATUS        current
    DESCRIPTION
        ""
    SYNTAX        INTEGER
    {
        policy(1),
        management(2)
    }

CfprComputePCIeFatalCompletionStatsThresholded ::= TEXTUAL-CONVENTION
    STATUS        current
    DESCRIPTION
        ""
    SYNTAX        BITS
    {
        abortErrors(0),
        timeoutErrors(1),
        unexpectedErrors(2)
    }

CfprComputePCIeFatalProtocolStatsThresholded ::= TEXTUAL-CONVENTION
    STATUS        current
    DESCRIPTION
        ""
    SYNTAX        BITS
    {
        dllpErrors(0),
        flowControlErrors(1)
    }

CfprComputePCIeFatalReceiveStatsThresholded ::= TEXTUAL-CONVENTION
    STATUS        current
    DESCRIPTION
        ""
    SYNTAX        BITS
    {
        bufferOverflowErrors(0),
        errFatalErrors(1),
        errNonFatalErrors(2),
        unsupportedRequestErrors(3)
    }

CfprComputePCIeFatalStatsThresholded ::= TEXTUAL-CONVENTION
    STATUS        current
    DESCRIPTION
        ""
    SYNTAX        BITS
    {
        acsViolationErrors(0),
        malformedTLPErrors(1),
        poisonedTLPErrors(2),
        surpriseLinkDownErrors(3)
    }

CfprComputePciCapOrder ::= TEXTUAL-CONVENTION
    STATUS        current
    DESCRIPTION
        ""
    SYNTAX        INTEGER
    {
        ascending(0),
        descending(1),
        ascendingDual(2),
        ascendingSeq(3),
        ascendingExtended(4)
    }

CfprComputePhysicalLowVoltageMemory ::= TEXTUAL-CONVENTION
    STATUS        current
    DESCRIPTION
        ""
    SYNTAX        INTEGER
    {
        notApplicable(0),
        lowVoltage(1),
        regularVoltage(2)
    }

CfprComputePhysicalFsmCurrentFsm ::= TEXTUAL-CONVENTION
    STATUS        current
    DESCRIPTION
        ""
    SYNTAX        INTEGER
    {
        nop(0),
        associate(665),
        disassociate(727),
        powerCap(767),
        decommission(769),
        softShutdown(771),
        hardShutdown(773),
        turnup(775),
        powercycle(777),
        hardreset(781),
        softreset(785),
        swConnUpd(789),
        biosRecovery(792),
        cmosReset(806),
        resetBmc(815),
        updateExtUsers(879),
        updateAdaptor(891),
        activateAdaptor(898),
        configSoL(932),
        unconfigSoL(934),
        diagnosticInterrupt(1036),
        resetKvm(1055),
        updateBIOS(1152),
        activateBIOS(1157),
        resetIpmi(1200),
        fwUpgrade(1202),
        cimcSessionDelete(1477),
        updateBoardController(1497),
        configBoard(1506),
        resetMemoryErrors(1508),
        serviceInfraDeploy(1531),
        serviceInfraWithdraw(1536),
        flashController(1638),
        enableCimcSecureBoot(1669),
        updateAdaptorBoot(1991),
        hardPowercycle(2055)
    }

CfprComputePhysicalFsmStageName ::= TEXTUAL-CONVENTION
    STATUS        current
    DESCRIPTION
        ""
    SYNTAX        INTEGER
    {
        nop(0),
        associateBegin(665),
        associateUpdateIBMCFw(668),
        associateWaitForIBMCFwUpdate(669),
        associateActivateIBMCFw(670),
        associateResetIBMC(671),
        associatePreSanitize(672),
        associateSanitize(673),
        associateConfigUserAccess(674),
        associateBladePowerOff(675),
        associateUpdateBoardCtrlRequest(676),
        associatePollBoardCtrlUpdateStatus(677),
        associatePowerOn(678),
        associateBmcPreconfigPnuOSLocal(679),
        associateBmcPreconfigPnuOSPeer(680),
        associateBmcConfigPnuOS(681),
        associateSwConfigPnuOSLocal(682),
        associateSwConfigPnuOSPeer(683),
        associateUpdateAdaptorNwFwLocal(684),
        associateUpdateAdaptorNwFwPeer(685),
        associateWaitForAdaptorNwFwUpdateLocal(686),
        associateWaitForAdaptorNwFwUpdatePeer(687),
        associateActivateAdaptorNwFwLocal(688),
        associateActivateAdaptorNwFwPeer(689),
        associateNicConfigPnuOSLocal(690),
        associateNicConfigPnuOSPeer(691),
        associateBootPnuos(692),
        associateBootWait(693),
        associateBiosPostCompletion(694),
        associateHagPnuOSConnect(695),
        associatePnuOSIdent(696),
        associatePnuOSPolicy(697),
        associatePnuOSValidate(698),
        associatePnuOSSelfTest(699),
        associateBiosImgUpdate(700),
        associateStorageCtlrImgUpdate(701),
        associateHbaImgUpdate(702),
        associateNicImgUpdate(703),
        associatePnuOSInventory(704),
        associatePnuOSConfig(705),
        associatePnuOSLocalDiskConfig(706),
        associatePnuOSUnloadDrivers(707),
        associateBmcUnconfigPnuOS(708),
        associateNicUnconfigPnuOSLocal(709),
        associateNicUnconfigPnuOSPeer(710),
        associateSwUnconfigPnuOSLocal(711),
        associateSwUnconfigPnuOSPeer(712),
        associateSwConfigHostOSLocal(713),
        associateSwConfigHostOSPeer(714),
        associateNicConfigHostOSLocal(715),
        associateNicConfigHostOSPeer(716),
        associateHagPnuOSDisconnect(717),
        associateConfigSoL(718),
        associatePrepareForBoot(719),
        associateConfigUuid(720),
        associateBootHost(721),
        associateHagHostOSConnect(722),
        associateHostOSIdent(723),
        associateHostOSPolicy(724),
        associateHostOSValidate(725),
        associateHostOSConfig(726),
        disassociateBegin(727),
        disassociateConfigUserAccess(730),
        disassociatePowerOn(731),
        disassociatePreSanitize(732),
        disassociateSanitize(733),
        disassociateNicUnconfigHostOSLocal(734),
        disassociateNicUnconfigHostOSPeer(735),
        disassociateSwUnconfigHostOSLocal(736),
        disassociateSwUnconfigHostOSPeer(737),
        disassociateBmcPreconfigPnuOSLocal(738),
        disassociateBmcPreconfigPnuOSPeer(739),
        disassociateBmcConfigPnuOS(740),
        disassociateSwConfigPnuOSLocal(741),
        disassociateSwConfigPnuOSPeer(742),
        disassociateNicConfigPnuOSLocal(743),
        disassociateNicConfigPnuOSPeer(744),
        disassociateConfigBios(745),
        disassociateBootPnuos(746),
        disassociateBootWait(747),
        disassociateBiosPostCompletion(748),
        disassociateHagPnuOSConnect(749),
        disassociatePnuOSIdent(750),
        disassociatePnuOSPolicy(751),
        disassociatePnuOSValidate(752),
        disassociatePnuOSUnconfig(753),
        disassociatePnuOSScrub(754),
        disassociatePnuOSSelfTest(755),
        disassociateBmcUnconfigPnuOS(756),
        disassociateNicUnconfigPnuOSLocal(757),
        disassociateNicUnconfigPnuOSPeer(758),
        disassociateHagPnuOSDisconnect(759),
        disassociateUnconfigUuid(760),
        disassociateShutdown(761),
        disassociateUnconfigBios(762),
        disassociateSwUnconfigPnuOSLocal(763),
        disassociateSwUnconfigPnuOSPeer(764),
        disassociateUnconfigSoL(765),
        disassociateHandlePooling(766),
        powerCapBegin(767),
        powerCapConfig(768),
        decommissionBegin(769),
        decommissionExecute(770),
        softShutdownBegin(771),
        softShutdownExecute(772),
        hardShutdownBegin(773),
        hardShutdownExecute(774),
        turnupBegin(775),
        turnupExecute(776),
        powercycleBegin(777),
        powercyclePreSanitize(778),
        powercycleSanitize(779),
        powercycleExecute(780),
        hardresetBegin(781),
        hardresetPreSanitize(782),
        hardresetSanitize(783),
        hardresetExecute(784),
        softresetBegin(785),
        softresetPreSanitize(786),
        softresetSanitize(787),
        softresetExecute(788),
        swConnUpdBegin(789),
        swConnUpdA(790),
        swConnUpdB(791),
        biosRecoveryBegin(792),
        biosRecoveryShutdown(793),
        biosRecoveryPreSanitize(794),
        biosRecoverySanitize(795),
        biosRecoverySetupVmediaLocal(796),
        biosRecoverySetupVmediaPeer(797),
        biosRecoveryStart(798),
        biosRecoveryWait(799),
        biosRecoveryCleanup(800),
        biosRecoveryReset(801),
        biosRecoveryTeardownVmediaLocal(802),
        biosRecoveryTeardownVmediaPeer(803),
        cmosResetBegin(806),
        cmosResetPreSanitize(807),
        cmosResetSanitize(808),
        cmosResetExecute(809),
        cmosResetReconfigBios(810),
        cmosResetReconfigUuid(811),
        cmosResetBladePowerOn(812),
        resetBmcBegin(815),
        resetBmcExecute(816),
        updateExtUsersBegin(879),
        updateExtUsersDeploy(880),
        updateAdaptorBegin(891),
        updateAdaptorPowerOn(892),
        updateAdaptorUpdateRequestLocal(893),
        updateAdaptorUpdateRequestPeer(894),
        updateAdaptorPollUpdateStatusLocal(895),
        updateAdaptorPollUpdateStatusPeer(896),
        updateAdaptorPowerOff(897),
        activateAdaptorBegin(898),
        activateAdaptorPowerOn(899),
        activateAdaptorActivateLocal(900),
        activateAdaptorActivatePeer(901),
        activateAdaptorReset(902),
        configSoLBegin(932),
        configSoLExecute(933),
        unconfigSoLBegin(934),
        unconfigSoLExecute(935),
        activateAdaptorFail(940),
        activateAdaptorSuccess(941),
        associateFail(942),
        associateSuccess(943),
        biosRecoveryFail(946),
        biosRecoverySuccess(947),
        cmosResetFail(948),
        cmosResetSuccess(949),
        configSoLFail(950),
        configSoLSuccess(951),
        decommissionFail(952),
        decommissionSuccess(953),
        disassociateFail(954),
        disassociateSuccess(955),
        hardShutdownFail(956),
        hardShutdownSuccess(957),
        hardresetFail(958),
        hardresetSuccess(959),
        powerCapFail(960),
        powerCapSuccess(961),
        powercycleFail(962),
        powercycleSuccess(963),
        resetBmcFail(964),
        resetBmcSuccess(965),
        softShutdownFail(966),
        softShutdownSuccess(967),
        softresetFail(968),
        softresetSuccess(969),
        swConnUpdFail(970),
        swConnUpdSuccess(971),
        turnupFail(972),
        turnupSuccess(973),
        unconfigSoLFail(974),
        unconfigSoLSuccess(975),
        updateAdaptorFail(976),
        updateAdaptorSuccess(977),
        updateExtUsersFail(978),
        updateExtUsersSuccess(979),
        decommissionStopVMediaLocal(1019),
        decommissionStopVMediaPeer(1020),
        biosRecoveryStopVMediaLocal(1021),
        biosRecoveryStopVMediaPeer(1022),
        diagnosticInterruptBegin(1036),
        diagnosticInterruptExecute(1037),
        diagnosticInterruptFail(1038),
        diagnosticInterruptSuccess(1039),
        associateLocalDiskFwUpdate(1040),
        resetKvmBegin(1055),
        resetKvmExecute(1056),
        resetKvmFail(1057),
        resetKvmSuccess(1058),
        associateSwConfigPortNivLocal(1069),
        associateSwConfigPortNivPeer(1070),
        disassociateSwConfigPortNivLocal(1071),
        disassociateSwConfigPortNivPeer(1072),
        associateSolRedirectEnable(1104),
        associateSerialDebugPnuOSConnect(1105),
        associateSerialDebugPnuOSDisconnect(1106),
        associateSolRedirectDisable(1107),
        disassociateSolRedirectEnable(1108),
        disassociateSerialDebugPnuOSConnect(1109),
        disassociateSerialDebugPnuOSDisconnect(1110),
        disassociateSolRedirectDisable(1111),
        decommissionCleanupCIMC(1112),
        updateBIOSBegin(1152),
        updateBIOSClear(1153),
        updateBIOSPollClearStatus(1154),
        updateBIOSUpdateRequest(1155),
        updateBIOSPollUpdateStatus(1156),
        activateBIOSBegin(1157),
        activateBIOSPowerOff(1158),
        activateBIOSClear(1159),
        activateBIOSPollClearStatus(1160),
        activateBIOSActivate(1161),
        activateBIOSPollActivateStatus(1162),
        activateBIOSUpdateTokens(1163),
        activateBIOSPowerOn(1164),
        associateClearBiosUpdate(1169),
        associatePollClearBiosUpdateStatus(1170),
        associateUpdateBiosRequest(1171),
        associatePollBiosUpdateStatus(1172),
        associateActivateBios(1173),
        associatePollBiosActivateStatus(1174),
        associatePnuOSCatalog(1175),
        disassociatePnuOSCatalog(1176),
        activateBIOSFail(1178),
        activateBIOSSuccess(1179),
        updateBIOSFail(1180),
        updateBIOSSuccess(1181),
        associateMarkAdapterForReboot(1193),
        associateDeassertResetBypass(1194),
        associateVerifyFcZoneConfig(1195),
        disassociateDeassertResetBypass(1196),
        disassociateVerifyFcZoneConfig(1197),
        decommissionCleanupPortConfigLocal(1198),
        decommissionCleanupPortConfigPeer(1199),
        resetIpmiBegin(1200),
        resetIpmiExecute(1201),
        fwUpgradeBegin(1202),
        fwUpgradeUpdateIBMCFw(1203),
        fwUpgradeWaitForIBMCFwUpdate(1204),
        fwUpgradeActivateIBMCFw(1205),
        fwUpgradeResetIBMC(1206),
        fwUpgradePreSanitize(1207),
        fwUpgradeSanitize(1208),
        fwUpgradeBladePowerOff(1209),
        fwUpgradeUpdateBoardCtrlRequest(1210),
        fwUpgradePollBoardCtrlUpdateStatus(1211),
        fwUpgradeClearBiosUpdate(1212),
        fwUpgradePollClearBiosUpdateStatus(1213),
        fwUpgradeUpdateBiosRequest(1214),
        fwUpgradePollBiosUpdateStatus(1215),
        fwUpgradeActivateBios(1216),
        fwUpgradePollBiosActivateStatus(1217),
        fwUpgradePowerOn(1218),
        fwUpgradeBmcPreconfigPnuOSLocal(1219),
        fwUpgradeBmcPreconfigPnuOSPeer(1220),
        fwUpgradeSwConfigPortNivLocal(1221),
        fwUpgradeSwConfigPortNivPeer(1222),
        fwUpgradeSwConfigPnuOSLocal(1223),
        fwUpgradeSwConfigPnuOSPeer(1224),
        fwUpgradeUpdateAdaptorNwFwLocal(1225),
        fwUpgradeUpdateAdaptorNwFwPeer(1226),
        fwUpgradeWaitForAdaptorNwFwUpdateLocal(1227),
        fwUpgradeWaitForAdaptorNwFwUpdatePeer(1228),
        fwUpgradeActivateAdaptorNwFwLocal(1229),
        fwUpgradeActivateAdaptorNwFwPeer(1230),
        fwUpgradeNicConfigPnuOSLocal(1231),
        fwUpgradeNicConfigPnuOSPeer(1232),
        fwUpgradeBmcConfigPnuOS(1233),
        fwUpgradeSolRedirectEnable(1234),
        fwUpgradeSerialDebugPnuOSConnect(1235),
        fwUpgradeBootPnuos(1236),
        fwUpgradeBootWait(1237),
        fwUpgradeBiosPostCompletion(1238),
        fwUpgradeHagPnuOSConnect(1239),
        fwUpgradePnuOSIdent(1240),
        fwUpgradePnuOSPolicy(1241),
        fwUpgradePnuOSCatalog(1242),
        fwUpgradePnuOSValidate(1243),
        fwUpgradePnuOSSelfTest(1244),
        fwUpgradeStorageCtlrImgUpdate(1245),
        fwUpgradeHbaImgUpdate(1246),
        fwUpgradeNicImgUpdate(1247),
        fwUpgradeLocalDiskFwUpdate(1248),
        fwUpgradePnuOSConfig(1249),
        fwUpgradePnuOSInventory(1250),
        fwUpgradeBiosImgUpdate(1251),
        fwUpgradePnuOSUnloadDrivers(1252),
        fwUpgradeBmcUnconfigPnuOS(1253),
        fwUpgradeNicUnconfigPnuOSLocal(1254),
        fwUpgradeNicUnconfigPnuOSPeer(1255),
        fwUpgradeSwUnconfigPnuOSLocal(1256),
        fwUpgradeSwUnconfigPnuOSPeer(1257),
        fwUpgradeDeassertResetBypass(1258),
        fwUpgradeHagPnuOSDisconnect(1259),
        fwUpgradeSerialDebugPnuOSDisconnect(1260),
        fwUpgradeSolRedirectDisable(1261),
        fwUpgradeShutdown(1262),
        activateAdaptorDeassertResetBypass(1307),
        fwUpgradeFail(1386),
        fwUpgradeSuccess(1387),
        resetIpmiFail(1388),
        resetIpmiSuccess(1389),
        associateConfigFlexFlash(1468),
        associateSyncPowerState(1469),
        disassociateUnconfigFlexFlash(1470),
        cimcSessionDeleteBegin(1477),
        cimcSessionDeleteExecute(1478),
        cimcSessionDeleteFail(1483),
        cimcSessionDeleteSuccess(1484),
        updateBoardControllerBegin(1497),
        updateBoardControllerPrepareForUpdate(1498),
        updateBoardControllerServerPowerOff(1499),
        updateBoardControllerUpdateRequest(1500),
        updateBoardControllerPollUpdateStatus(1501),
        updateBoardControllerServerPowerOn(1502),
        configBoardBegin(1506),
        configBoardConfigMemoryPolicy(1507),
        resetMemoryErrorsBegin(1508),
        resetMemoryErrorsExecute(1509),
        associateOobStorageInventory(1520),
        associateSwConfigServiceInfraLocal(1521),
        associateSwConfigServiceInfraPeer(1522),
        associateNicConfigServiceInfraLocal(1523),
        associateNicConfigServiceInfraPeer(1524),
        disassociateNicUnconfigServiceInfraLocal(1525),
        disassociateNicUnconfigServiceInfraPeer(1526),
        disassociateConfigFlexFlashScrub(1527),
        serviceInfraDeployBegin(1531),
        serviceInfraDeploySwConfigLocal(1532),
        serviceInfraDeploySwConfigPeer(1533),
        serviceInfraDeployNicConfigLocal(1534),
        serviceInfraDeployNicConfigPeer(1535),
        serviceInfraWithdrawBegin(1536),
        serviceInfraWithdrawSwUnConfigLocal(1537),
        serviceInfraWithdrawSwUnConfigPeer(1538),
        serviceInfraWithdrawNicUnConfigLocal(1539),
        serviceInfraWithdrawNicUnConfigPeer(1540),
        configBoardFail(1541),
        configBoardSuccess(1542),
        resetMemoryErrorsFail(1543),
        resetMemoryErrorsSuccess(1544),
        serviceInfraDeployFail(1545),
        serviceInfraDeploySuccess(1546),
        serviceInfraWithdrawFail(1547),
        serviceInfraWithdrawSuccess(1548),
        updateBoardControllerFail(1549),
        updateBoardControllerSuccess(1550),
        associatePowerOnPreConfig(1561),
        disassociateResetSecureBootConfig(1562),
        associateDownloadImages(1572),
        associateCopyRemote(1573),
        associateCheckPowerAvailability(1574),
        associateDeleteCurlDownloadedImages(1575),
        fwUpgradeDownloadImages(1576),
        fwUpgradeCopyRemote(1577),
        fwUpgradeDeleteCurlDownloadedImages(1578),
        updateAdaptorCheckPowerAvailability(1597),
        updateAdaptorPowerDeployWait(1598),
        activateAdaptorCheckPowerAvailability(1599),
        activateAdaptorPowerDeployWait(1600),
        associatePowerDeployWait(1602),
        disassociateCheckPowerAvailability(1603),
        disassociatePowerDeployWait(1604),
        fwUpgradeCheckPowerAvailability(1605),
        fwUpgradePowerDeployWait(1606),
        associateUnconfigExtMgmtRules(1620),
        associateUnconfigExtMgmtGw(1621),
        associateUnconfigCimcVMedia(1622),
        associateGraphicsImageUpdate(1623),
        associateConfigExtMgmtRules(1624),
        associateConfigExtMgmtGw(1625),
        associateConfigCimcVMedia(1626),
        associateSspUpdateHostPreBoot(1627),
        disassociateConfigKvmMgmtDefaultSetting(1628),
        disassociateUnconfigExtMgmtRules(1629),
        disassociateUnconfigExtMgmtGw(1630),
        disassociateUnconfigCimcVMedia(1631),
        decommissionUnconfigExtMgmtRules(1632),
        decommissionUnconfigExtMgmtGw(1633),
        fwUpgradeUnconfigExtMgmtRules(1634),
        fwUpgradeUnconfigExtMgmtGw(1635),
        fwUpgradeUnconfigCimcVMedia(1636),
        fwUpgradeGraphicsImageUpdate(1637),
        flashControllerBegin(1638),
        flashControllerUpdateFlashLife(1639),
        flashControllerFail(1653),
        flashControllerSuccess(1654),
        enableCimcSecureBootBegin(1669),
        enableCimcSecureBootUpdateRequest(1670),
        enableCimcSecureBootPollUpdateStatus(1671),
        enableCimcSecureBootActivate(1672),
        enableCimcSecureBootReset(1673),
        enableCimcSecureBootFail(1676),
        enableCimcSecureBootSuccess(1677),
        associateUpdateSspOsSoftware(1711),
        associateWaitForSspOsUpdateComplete(1712),
        associatePrepareKeyFile(1713),
        updateAdaptorBootBegin(1991),
        updateAdaptorBootCheckPowerAvailability(1992),
        updateAdaptorBootPowerDeployWait(1993),
        updateAdaptorBootPowerOn(1994),
        updateAdaptorBootUpdateRequestLocal(1995),
        updateAdaptorBootUpdateRequestPeer(1996),
        updateAdaptorBootPollUpdateStatusLocal(1997),
        updateAdaptorBootPollUpdateStatusPeer(1998),
        updateAdaptorBootPowerOff(1999),
        updateAdaptorBootFail(2000),
        updateAdaptorBootSuccess(2001),
        hardPowercycleBegin(2055),
        hardPowercycleExecute(2056),
        hardPowercycleFail(2061),
        hardPowercycleSuccess(2062)
    }

CfprComputePhysicalFsmTaskFlags ::= TEXTUAL-CONVENTION
    STATUS        current
    DESCRIPTION
        ""
    SYNTAX        BITS
    {
        samDmeComputePhysicalFwUpgradeConfigBoardCtrlFw(0),
        samDmeComputePhysicalFwUpgradeConfigBmcBiosUpdate(1),
        samDmeComputePhysicalAssociateFlexflashConfig(9),
        samDmeComputePhysicalAssociatePowerForceConfig(10),
        samDmeComputePhysicalDisassociateMaskPnuos(11),
        samDmeComputePhysicalAssociatePowercapConfig(13),
        samDmeComputePhysicalAssociateVmediaConfig(16),
        samDmeComputePhysicalAssociateSsposUpdate(19),
        samDmeComputePhysicalAssociatePnuosConfig(28),
        samDmeComputePhysicalAssociateSwitchConfig(29),
        samDmeComputePhysicalAssociateHostConfig(30),
        samDmeComputePhysicalAssociateHostReboot(31),
        samDmeComputePhysicalAssociateIfConfig(32),
        samDmeComputePhysicalAssociateNicConfig(33),
        samDmeComputePhysicalAssociateAdaptorNwFwConfig(34),
        samDmeComputePhysicalAssociateMgmtFwConfig(35),
        samDmeComputePhysicalAssociateBootConfig(36),
        samDmeComputePhysicalAssociateBiosUpdate(37),
        samDmeComputePhysicalDisassociateSolConfig(38),
        samDmeComputePhysicalAssociateEpAuthConfig(39),
        samDmeComputePhysicalAssociateDiskConfig(40),
        samDmeComputePhysicalAssociateBoardCtrlFwConfig(41),
        samDmeComputePhysicalDisassociateSwitchUnconfig(42),
        samDmeComputePhysicalCmosResetAlways(43),
        samDmeComputePhysicalCmosResetSetUuidBiosBoot(44),
        samDmeComputePhysicalCmosResetPowerOn(45),
        samDmeComputePhysicalActivateAdaptorActivate(47),
        samDmeComputePhysicalActivateAdaptorReset(48),
        samDmeComputePhysicalAssociateBmcBiosUpdate(58),
        samDmeComputePhysicalAssociateLsRename(59),
        samDmeComputePhysicalAssociateStorageConfig(60),
        samDmeComputePhysicalFwUpgradeConfigPnuos(61),
        samDmeComputePhysicalFwUpgradeConfigAdaptorNwFw(62)
    }

CfprComputePhysicalFsmTaskItem ::= TEXTUAL-CONVENTION
    STATUS        current
    DESCRIPTION
        ""
    SYNTAX        INTEGER
    {
        nop(0),
        associate(665),
        disassociate(727),
        powerCap(767),
        decommission(769),
        softShutdown(771),
        hardShutdown(773),
        turnup(775),
        powercycle(777),
        hardreset(781),
        softreset(785),
        swConnUpd(789),
        biosRecovery(792),
        cmosReset(806),
        resetBmc(815),
        updateExtUsers(879),
        updateAdaptor(891),
        activateAdaptor(898),
        configSoL(932),
        unconfigSoL(934),
        diagnosticInterrupt(1036),
        resetKvm(1055),
        updateBIOS(1152),
        activateBIOS(1157),
        resetIpmi(1200),
        fwUpgrade(1202),
        cimcSessionDelete(1477),
        updateBoardController(1497),
        configBoard(1506),
        resetMemoryErrors(1508),
        serviceInfraDeploy(1531),
        serviceInfraWithdraw(1536),
        flashController(1638),
        enableCimcSecureBoot(1669),
        updateAdaptorBoot(1991),
        hardPowercycle(2055)
    }

CfprComputePooledRackUnitId ::= TEXTUAL-CONVENTION
    STATUS        current
    DESCRIPTION
        ""
    SYNTAX        Gauge32 (1..255)

CfprComputePooledSlotSlotId ::= TEXTUAL-CONVENTION
    STATUS        current
    DESCRIPTION
        ""
    SYNTAX        Gauge32 (1..8)

CfprComputePsuClusterState ::= TEXTUAL-CONVENTION
    STATUS        current
    DESCRIPTION
        ""
    SYNTAX        INTEGER
    {
        unknown(0),
        slot1Master(1),
        slot2Master(2),
        notClustered(3)
    }

CfprComputePsuControlRedundancy ::= TEXTUAL-CONVENTION
    STATUS        current
    DESCRIPTION
        ""
    SYNTAX        INTEGER
    {
        unknown(0),
        nonRedundant(1),
        nPlus1(2),
        grid(3)
    }

CfprComputePsuRedundancy ::= TEXTUAL-CONVENTION
    STATUS        current
    DESCRIPTION
        ""
    SYNTAX        INTEGER
    {
        nonRedundant(1),
        nPlus1(2),
        grid(3)
    }

CfprComputePsuRedundancyOperQualifier ::= TEXTUAL-CONVENTION
    STATUS        current
    DESCRIPTION
        ""
    SYNTAX        BITS
    {
        redundancyLost(0),
        redundancyDegraded(1),
        nonRedundantSufficientResources(2),
        nonRedundantInsufficientResources(3)
    }

CfprComputePsuRedundancyOperState ::= TEXTUAL-CONVENTION
    STATUS        current
    DESCRIPTION
        ""
    SYNTAX        INTEGER
    {
        unknown(0),
        ok(1),
        failed(2),
        degraded(3)
    }

CfprComputeRackQualMaxId ::= TEXTUAL-CONVENTION
    STATUS        current
    DESCRIPTION
        ""
    SYNTAX        Gauge32 (1..255)

CfprComputeRackQualMinId ::= TEXTUAL-CONVENTION
    STATUS        current
    DESCRIPTION
        ""
    SYNTAX        Gauge32 (1..255)

CfprComputeRackUnitId ::= TEXTUAL-CONVENTION
    STATUS        current
    DESCRIPTION
        ""
    SYNTAX        Gauge32 (1..255)

CfprComputeRackUnitFsmCurrentFsm ::= TEXTUAL-CONVENTION
    STATUS        current
    DESCRIPTION
        ""
    SYNTAX        INTEGER
    {
        nop(0),
        associate(665),
        disassociate(727),
        powerCap(767),
        decommission(769),
        softShutdown(771),
        hardShutdown(773),
        turnup(775),
        powercycle(777),
        hardreset(781),
        softreset(785),
        swConnUpd(789),
        biosRecovery(792),
        cmosReset(806),
        resetBmc(815),
        discover(819),
        updateExtUsers(879),
        updateAdaptor(891),
        activateAdaptor(898),
        configSoL(932),
        unconfigSoL(934),
        diagnosticInterrupt(1036),
        resetKvm(1055),
        offline(1064),
        updateBIOS(1152),
        activateBIOS(1157),
        resetIpmi(1200),
        fwUpgrade(1202),
        adapterReset(1263),
        cimcSessionDelete(1477),
        updateBoardController(1497),
        configBoard(1506),
        resetMemoryErrors(1508),
        createDhcpEntry(1528),
        serviceInfraDeploy(1531),
        serviceInfraWithdraw(1536),
        flashController(1638),
        enableCimcSecureBoot(1669),
        updateAdaptorBoot(1991),
        hardPowercycle(2055)
    }

CfprComputeRackUnitFsmStageName ::= TEXTUAL-CONVENTION
    STATUS        current
    DESCRIPTION
        ""
    SYNTAX        INTEGER
    {
        nop(0),
        associateBegin(665),
        associateUpdateIBMCFw(668),
        associateWaitForIBMCFwUpdate(669),
        associateActivateIBMCFw(670),
        associateResetIBMC(671),
        associatePreSanitize(672),
        associateSanitize(673),
        associateConfigUserAccess(674),
        associateBladePowerOff(675),
        associateUpdateBoardCtrlRequest(676),
        associatePollBoardCtrlUpdateStatus(677),
        associatePowerOn(678),
        associateBmcPreconfigPnuOSLocal(679),
        associateBmcPreconfigPnuOSPeer(680),
        associateBmcConfigPnuOS(681),
        associateSwConfigPnuOSLocal(682),
        associateSwConfigPnuOSPeer(683),
        associateUpdateAdaptorNwFwLocal(684),
        associateUpdateAdaptorNwFwPeer(685),
        associateWaitForAdaptorNwFwUpdateLocal(686),
        associateWaitForAdaptorNwFwUpdatePeer(687),
        associateActivateAdaptorNwFwLocal(688),
        associateActivateAdaptorNwFwPeer(689),
        associateNicConfigPnuOSLocal(690),
        associateNicConfigPnuOSPeer(691),
        associateBootPnuos(692),
        associateBootWait(693),
        associateBiosPostCompletion(694),
        associateHagPnuOSConnect(695),
        associatePnuOSIdent(696),
        associatePnuOSPolicy(697),
        associatePnuOSValidate(698),
        associatePnuOSSelfTest(699),
        associateBiosImgUpdate(700),
        associateStorageCtlrImgUpdate(701),
        associateHbaImgUpdate(702),
        associateNicImgUpdate(703),
        associatePnuOSInventory(704),
        associatePnuOSConfig(705),
        associatePnuOSLocalDiskConfig(706),
        associatePnuOSUnloadDrivers(707),
        associateBmcUnconfigPnuOS(708),
        associateNicUnconfigPnuOSLocal(709),
        associateNicUnconfigPnuOSPeer(710),
        associateSwUnconfigPnuOSLocal(711),
        associateSwUnconfigPnuOSPeer(712),
        associateSwConfigHostOSLocal(713),
        associateSwConfigHostOSPeer(714),
        associateNicConfigHostOSLocal(715),
        associateNicConfigHostOSPeer(716),
        associateHagPnuOSDisconnect(717),
        associateConfigSoL(718),
        associatePrepareForBoot(719),
        associateConfigUuid(720),
        associateBootHost(721),
        associateHagHostOSConnect(722),
        associateHostOSIdent(723),
        associateHostOSPolicy(724),
        associateHostOSValidate(725),
        associateHostOSConfig(726),
        disassociateBegin(727),
        disassociateConfigUserAccess(730),
        disassociatePowerOn(731),
        disassociatePreSanitize(732),
        disassociateSanitize(733),
        disassociateNicUnconfigHostOSLocal(734),
        disassociateNicUnconfigHostOSPeer(735),
        disassociateSwUnconfigHostOSLocal(736),
        disassociateSwUnconfigHostOSPeer(737),
        disassociateBmcPreconfigPnuOSLocal(738),
        disassociateBmcPreconfigPnuOSPeer(739),
        disassociateBmcConfigPnuOS(740),
        disassociateSwConfigPnuOSLocal(741),
        disassociateSwConfigPnuOSPeer(742),
        disassociateNicConfigPnuOSLocal(743),
        disassociateNicConfigPnuOSPeer(744),
        disassociateConfigBios(745),
        disassociateBootPnuos(746),
        disassociateBootWait(747),
        disassociateBiosPostCompletion(748),
        disassociateHagPnuOSConnect(749),
        disassociatePnuOSIdent(750),
        disassociatePnuOSPolicy(751),
        disassociatePnuOSValidate(752),
        disassociatePnuOSUnconfig(753),
        disassociatePnuOSScrub(754),
        disassociatePnuOSSelfTest(755),
        disassociateBmcUnconfigPnuOS(756),
        disassociateNicUnconfigPnuOSLocal(757),
        disassociateNicUnconfigPnuOSPeer(758),
        disassociateHagPnuOSDisconnect(759),
        disassociateUnconfigUuid(760),
        disassociateShutdown(761),
        disassociateUnconfigBios(762),
        disassociateSwUnconfigPnuOSLocal(763),
        disassociateSwUnconfigPnuOSPeer(764),
        disassociateUnconfigSoL(765),
        disassociateHandlePooling(766),
        powerCapBegin(767),
        powerCapConfig(768),
        decommissionBegin(769),
        decommissionExecute(770),
        softShutdownBegin(771),
        softShutdownExecute(772),
        hardShutdownBegin(773),
        hardShutdownExecute(774),
        turnupBegin(775),
        turnupExecute(776),
        powercycleBegin(777),
        powercyclePreSanitize(778),
        powercycleSanitize(779),
        powercycleExecute(780),
        hardresetBegin(781),
        hardresetPreSanitize(782),
        hardresetSanitize(783),
        hardresetExecute(784),
        softresetBegin(785),
        softresetPreSanitize(786),
        softresetSanitize(787),
        softresetExecute(788),
        swConnUpdBegin(789),
        swConnUpdA(790),
        swConnUpdB(791),
        biosRecoveryBegin(792),
        biosRecoveryShutdown(793),
        biosRecoveryPreSanitize(794),
        biosRecoverySanitize(795),
        biosRecoverySetupVmediaLocal(796),
        biosRecoverySetupVmediaPeer(797),
        biosRecoveryStart(798),
        biosRecoveryWait(799),
        biosRecoveryCleanup(800),
        biosRecoveryReset(801),
        biosRecoveryTeardownVmediaLocal(802),
        biosRecoveryTeardownVmediaPeer(803),
        cmosResetBegin(806),
        cmosResetPreSanitize(807),
        cmosResetSanitize(808),
        cmosResetExecute(809),
        cmosResetReconfigBios(810),
        cmosResetReconfigUuid(811),
        cmosResetBladePowerOn(812),
        resetBmcBegin(815),
        resetBmcExecute(816),
        discoverBegin(819),
        discoverBmcConfigureConnLocal(820),
        discoverSwConfigureConnLocal(821),
        discoverBmcConfigureConnPeer(822),
        discoverSwConfigureConnPeer(823),
        discoverBmcPresence(826),
        discoverBmcInventory(827),
        discoverPreSanitize(828),
        discoverSanitize(829),
        discoverConfigUserAccess(830),
        discoverSwConfigPnuOSLocal(831),
        discoverSwConfigPnuOSPeer(832),
        discoverBmcPreconfigPnuOSLocal(833),
        discoverBmcPreconfigPnuOSPeer(834),
        discoverBmcConfigPnuOS(835),
        discoverBootPnuos(836),
        discoverBootWait(837),
        discoverBiosPostCompletion(838),
        discoverReadSmbios(839),
        discoverHagConnect(841),
        discoverPnuOSIdent(842),
        discoverPnuOSPolicy(843),
        discoverPnuOSInventory(844),
        discoverPnuOSScrub(845),
        discoverPnuOSConnectivity(846),
        discoverPnuOSConnStatus(847),
        discoverSwPnuOSConnectivityLocal(848),
        discoverSwPnuOSConnectivityPeer(849),
        discoverPnuOSSelfTest(850),
        discoverBmcUnconfigPnuOS(851),
        discoverHagDisconnect(852),
        discoverBmcShutdownDiscovered(853),
        discoverHandlePooling(854),
        discoverSuccess(855),
        discoverFail(856),
        updateExtUsersBegin(879),
        updateExtUsersDeploy(880),
        updateAdaptorBegin(891),
        updateAdaptorPowerOn(892),
        updateAdaptorUpdateRequestLocal(893),
        updateAdaptorUpdateRequestPeer(894),
        updateAdaptorPollUpdateStatusLocal(895),
        updateAdaptorPollUpdateStatusPeer(896),
        updateAdaptorPowerOff(897),
        activateAdaptorBegin(898),
        activateAdaptorPowerOn(899),
        activateAdaptorActivateLocal(900),
        activateAdaptorActivatePeer(901),
        activateAdaptorReset(902),
        configSoLBegin(932),
        configSoLExecute(933),
        unconfigSoLBegin(934),
        unconfigSoLExecute(935),
        activateAdaptorFail(940),
        activateAdaptorSuccess(941),
        associateFail(942),
        associateSuccess(943),
        biosRecoveryFail(946),
        biosRecoverySuccess(947),
        cmosResetFail(948),
        cmosResetSuccess(949),
        configSoLFail(950),
        configSoLSuccess(951),
        decommissionFail(952),
        decommissionSuccess(953),
        disassociateFail(954),
        disassociateSuccess(955),
        hardShutdownFail(956),
        hardShutdownSuccess(957),
        hardresetFail(958),
        hardresetSuccess(959),
        powerCapFail(960),
        powerCapSuccess(961),
        powercycleFail(962),
        powercycleSuccess(963),
        resetBmcFail(964),
        resetBmcSuccess(965),
        softShutdownFail(966),
        softShutdownSuccess(967),
        softresetFail(968),
        softresetSuccess(969),
        swConnUpdFail(970),
        swConnUpdSuccess(971),
        turnupFail(972),
        turnupSuccess(973),
        unconfigSoLFail(974),
        unconfigSoLSuccess(975),
        updateAdaptorFail(976),
        updateAdaptorSuccess(977),
        updateExtUsersFail(978),
        updateExtUsersSuccess(979),
        decommissionStopVMediaLocal(1019),
        decommissionStopVMediaPeer(1020),
        biosRecoveryStopVMediaLocal(1021),
        biosRecoveryStopVMediaPeer(1022),
        discoverConfigDiscoveryMode(1023),
        discoverSwUnconfigPortNivLocal(1024),
        discoverSwUnconfigPortNivPeer(1025),
        discoverSwConfigPortNivLocal(1027),
        discoverSwConfigPortNivPeer(1028),
        discoverNicInventoryLocal(1029),
        discoverNicInventoryPeer(1030),
        discoverConfigNivMode(1031),
        diagnosticInterruptBegin(1036),
        diagnosticInterruptExecute(1037),
        diagnosticInterruptFail(1038),
        diagnosticInterruptSuccess(1039),
        associateLocalDiskFwUpdate(1040),
        discoverWaitForConnReady(1050),
        resetKvmBegin(1055),
        resetKvmExecute(1056),
        resetKvmFail(1057),
        resetKvmSuccess(1058),
        offlineBegin(1064),
        offlineCleanupLocal(1065),
        offlineCleanupPeer(1066),
        offlineSwUnconfigureLocal(1067),
        offlineSwUnconfigurePeer(1068),
        associateSwConfigPortNivLocal(1069),
        associateSwConfigPortNivPeer(1070),
        disassociateSwConfigPortNivLocal(1071),
        disassociateSwConfigPortNivPeer(1072),
        offlineFail(1073),
        offlineSuccess(1074),
        discoverSolRedirectEnable(1092),
        discoverSerialDebugConnect(1093),
        discoverSerialDebugDisconnect(1094),
        discoverSolRedirectDisable(1095),
        associateSolRedirectEnable(1104),
        associateSerialDebugPnuOSConnect(1105),
        associateSerialDebugPnuOSDisconnect(1106),
        associateSolRedirectDisable(1107),
        disassociateSolRedirectEnable(1108),
        disassociateSerialDebugPnuOSConnect(1109),
        disassociateSerialDebugPnuOSDisconnect(1110),
        disassociateSolRedirectDisable(1111),
        decommissionCleanupCIMC(1112),
        updateBIOSBegin(1152),
        updateBIOSClear(1153),
        updateBIOSPollClearStatus(1154),
        updateBIOSUpdateRequest(1155),
        updateBIOSPollUpdateStatus(1156),
        activateBIOSBegin(1157),
        activateBIOSPowerOff(1158),
        activateBIOSClear(1159),
        activateBIOSPollClearStatus(1160),
        activateBIOSActivate(1161),
        activateBIOSPollActivateStatus(1162),
        activateBIOSUpdateTokens(1163),
        activateBIOSPowerOn(1164),
        associateClearBiosUpdate(1169),
        associatePollClearBiosUpdateStatus(1170),
        associateUpdateBiosRequest(1171),
        associatePollBiosUpdateStatus(1172),
        associateActivateBios(1173),
        associatePollBiosActivateStatus(1174),
        associatePnuOSCatalog(1175),
        disassociatePnuOSCatalog(1176),
        discoverPnuOSCatalog(1177),
        activateBIOSFail(1178),
        activateBIOSSuccess(1179),
        updateBIOSFail(1180),
        updateBIOSSuccess(1181),
        discoverBladePowerOff(1189),
        discoverNicConfigPnuOSLocal(1190),
        discoverNicConfigPnuOSPeer(1191),
        associateMarkAdapterForReboot(1193),
        associateDeassertResetBypass(1194),
        associateVerifyFcZoneConfig(1195),
        disassociateDeassertResetBypass(1196),
        disassociateVerifyFcZoneConfig(1197),
        decommissionCleanupPortConfigLocal(1198),
        decommissionCleanupPortConfigPeer(1199),
        resetIpmiBegin(1200),
        resetIpmiExecute(1201),
        fwUpgradeBegin(1202),
        fwUpgradeUpdateIBMCFw(1203),
        fwUpgradeWaitForIBMCFwUpdate(1204),
        fwUpgradeActivateIBMCFw(1205),
        fwUpgradeResetIBMC(1206),
        fwUpgradePreSanitize(1207),
        fwUpgradeSanitize(1208),
        fwUpgradeBladePowerOff(1209),
        fwUpgradeUpdateBoardCtrlRequest(1210),
        fwUpgradePollBoardCtrlUpdateStatus(1211),
        fwUpgradeClearBiosUpdate(1212),
        fwUpgradePollClearBiosUpdateStatus(1213),
        fwUpgradeUpdateBiosRequest(1214),
        fwUpgradePollBiosUpdateStatus(1215),
        fwUpgradeActivateBios(1216),
        fwUpgradePollBiosActivateStatus(1217),
        fwUpgradePowerOn(1218),
        fwUpgradeBmcPreconfigPnuOSLocal(1219),
        fwUpgradeBmcPreconfigPnuOSPeer(1220),
        fwUpgradeSwConfigPortNivLocal(1221),
        fwUpgradeSwConfigPortNivPeer(1222),
        fwUpgradeSwConfigPnuOSLocal(1223),
        fwUpgradeSwConfigPnuOSPeer(1224),
        fwUpgradeUpdateAdaptorNwFwLocal(1225),
        fwUpgradeUpdateAdaptorNwFwPeer(1226),
        fwUpgradeWaitForAdaptorNwFwUpdateLocal(1227),
        fwUpgradeWaitForAdaptorNwFwUpdatePeer(1228),
        fwUpgradeActivateAdaptorNwFwLocal(1229),
        fwUpgradeActivateAdaptorNwFwPeer(1230),
        fwUpgradeNicConfigPnuOSLocal(1231),
        fwUpgradeNicConfigPnuOSPeer(1232),
        fwUpgradeBmcConfigPnuOS(1233),
        fwUpgradeSolRedirectEnable(1234),
        fwUpgradeSerialDebugPnuOSConnect(1235),
        fwUpgradeBootPnuos(1236),
        fwUpgradeBootWait(1237),
        fwUpgradeBiosPostCompletion(1238),
        fwUpgradeHagPnuOSConnect(1239),
        fwUpgradePnuOSIdent(1240),
        fwUpgradePnuOSPolicy(1241),
        fwUpgradePnuOSCatalog(1242),
        fwUpgradePnuOSValidate(1243),
        fwUpgradePnuOSSelfTest(1244),
        fwUpgradeStorageCtlrImgUpdate(1245),
        fwUpgradeHbaImgUpdate(1246),
        fwUpgradeNicImgUpdate(1247),
        fwUpgradeLocalDiskFwUpdate(1248),
        fwUpgradePnuOSConfig(1249),
        fwUpgradePnuOSInventory(1250),
        fwUpgradeBiosImgUpdate(1251),
        fwUpgradePnuOSUnloadDrivers(1252),
        fwUpgradeBmcUnconfigPnuOS(1253),
        fwUpgradeNicUnconfigPnuOSLocal(1254),
        fwUpgradeNicUnconfigPnuOSPeer(1255),
        fwUpgradeSwUnconfigPnuOSLocal(1256),
        fwUpgradeSwUnconfigPnuOSPeer(1257),
        fwUpgradeDeassertResetBypass(1258),
        fwUpgradeHagPnuOSDisconnect(1259),
        fwUpgradeSerialDebugPnuOSDisconnect(1260),
        fwUpgradeSolRedirectDisable(1261),
        fwUpgradeShutdown(1262),
        adapterResetBegin(1263),
        adapterResetPreSanitize(1264),
        adapterResetSanitize(1265),
        adapterResetDeassertResetBypass(1266),
        adapterResetPowerCycle(1267),
        activateAdaptorDeassertResetBypass(1307),
        fwUpgradeFail(1386),
        fwUpgradeSuccess(1387),
        resetIpmiFail(1388),
        resetIpmiSuccess(1389),
        adapterResetFail(1390),
        adapterResetSuccess(1391),
        associateConfigFlexFlash(1468),
        associateSyncPowerState(1469),
        disassociateUnconfigFlexFlash(1470),
        cimcSessionDeleteBegin(1477),
        cimcSessionDeleteExecute(1478),
        cimcSessionDeleteFail(1483),
        cimcSessionDeleteSuccess(1484),
        updateBoardControllerBegin(1497),
        updateBoardControllerPrepareForUpdate(1498),
        updateBoardControllerServerPowerOff(1499),
        updateBoardControllerUpdateRequest(1500),
        updateBoardControllerPollUpdateStatus(1501),
        updateBoardControllerServerPowerOn(1502),
        configBoardBegin(1506),
        configBoardConfigMemoryPolicy(1507),
        resetMemoryErrorsBegin(1508),
        resetMemoryErrorsExecute(1509),
        discoverOobStorageInventory(1510),
        discoverConfigFlexFlashScrub(1511),
        associateOobStorageInventory(1520),
        associateSwConfigServiceInfraLocal(1521),
        associateSwConfigServiceInfraPeer(1522),
        associateNicConfigServiceInfraLocal(1523),
        associateNicConfigServiceInfraPeer(1524),
        disassociateNicUnconfigServiceInfraLocal(1525),
        disassociateNicUnconfigServiceInfraPeer(1526),
        disassociateConfigFlexFlashScrub(1527),
        createDhcpEntryBegin(1528),
        createDhcpEntryExecuteLocal(1529),
        createDhcpEntryExecutePeer(1530),
        serviceInfraDeployBegin(1531),
        serviceInfraDeploySwConfigLocal(1532),
        serviceInfraDeploySwConfigPeer(1533),
        serviceInfraDeployNicConfigLocal(1534),
        serviceInfraDeployNicConfigPeer(1535),
        serviceInfraWithdrawBegin(1536),
        serviceInfraWithdrawSwUnConfigLocal(1537),
        serviceInfraWithdrawSwUnConfigPeer(1538),
        serviceInfraWithdrawNicUnConfigLocal(1539),
        serviceInfraWithdrawNicUnConfigPeer(1540),
        configBoardFail(1541),
        configBoardSuccess(1542),
        resetMemoryErrorsFail(1543),
        resetMemoryErrorsSuccess(1544),
        serviceInfraDeployFail(1545),
        serviceInfraDeploySuccess(1546),
        serviceInfraWithdrawFail(1547),
        serviceInfraWithdrawSuccess(1548),
        updateBoardControllerFail(1549),
        updateBoardControllerSuccess(1550),
        createDhcpEntryFail(1551),
        createDhcpEntrySuccess(1552),
        associatePowerOnPreConfig(1561),
        disassociateResetSecureBootConfig(1562),
        associateDownloadImages(1572),
        associateCopyRemote(1573),
        associateCheckPowerAvailability(1574),
        associateDeleteCurlDownloadedImages(1575),
        fwUpgradeDownloadImages(1576),
        fwUpgradeCopyRemote(1577),
        fwUpgradeDeleteCurlDownloadedImages(1578),
        updateAdaptorCheckPowerAvailability(1597),
        updateAdaptorPowerDeployWait(1598),
        activateAdaptorCheckPowerAvailability(1599),
        activateAdaptorPowerDeployWait(1600),
        associatePowerDeployWait(1602),
        disassociateCheckPowerAvailability(1603),
        disassociatePowerDeployWait(1604),
        fwUpgradeCheckPowerAvailability(1605),
        fwUpgradePowerDeployWait(1606),
        discoverUnconfigExtMgmtRules(1614),
        discoverUnconfigExtMgmtGw(1615),
        discoverUnconfigCimcVMedia(1616),
        associateUnconfigExtMgmtRules(1620),
        associateUnconfigExtMgmtGw(1621),
        associateUnconfigCimcVMedia(1622),
        associateGraphicsImageUpdate(1623),
        associateConfigExtMgmtRules(1624),
        associateConfigExtMgmtGw(1625),
        associateConfigCimcVMedia(1626),
        associateSspUpdateHostPreBoot(1627),
        disassociateConfigKvmMgmtDefaultSetting(1628),
        disassociateUnconfigExtMgmtRules(1629),
        disassociateUnconfigExtMgmtGw(1630),
        disassociateUnconfigCimcVMedia(1631),
        decommissionUnconfigExtMgmtRules(1632),
        decommissionUnconfigExtMgmtGw(1633),
        fwUpgradeUnconfigExtMgmtRules(1634),
        fwUpgradeUnconfigExtMgmtGw(1635),
        fwUpgradeUnconfigCimcVMedia(1636),
        fwUpgradeGraphicsImageUpdate(1637),
        flashControllerBegin(1638),
        flashControllerUpdateFlashLife(1639),
        flashControllerFail(1653),
        flashControllerSuccess(1654),
        enableCimcSecureBootBegin(1669),
        enableCimcSecureBootUpdateRequest(1670),
        enableCimcSecureBootPollUpdateStatus(1671),
        enableCimcSecureBootActivate(1672),
        enableCimcSecureBootReset(1673),
        enableCimcSecureBootFail(1676),
        enableCimcSecureBootSuccess(1677),
        associateUpdateSspOsSoftware(1711),
        associateWaitForSspOsUpdateComplete(1712),
        associatePrepareKeyFile(1713),
        updateAdaptorBootBegin(1991),
        updateAdaptorBootCheckPowerAvailability(1992),
        updateAdaptorBootPowerDeployWait(1993),
        updateAdaptorBootPowerOn(1994),
        updateAdaptorBootUpdateRequestLocal(1995),
        updateAdaptorBootUpdateRequestPeer(1996),
        updateAdaptorBootPollUpdateStatusLocal(1997),
        updateAdaptorBootPollUpdateStatusPeer(1998),
        updateAdaptorBootPowerOff(1999),
        updateAdaptorBootFail(2000),
        updateAdaptorBootSuccess(2001),
        hardPowercycleBegin(2055),
        hardPowercycleExecute(2056),
        hardPowercycleFail(2061),
        hardPowercycleSuccess(2062)
    }

CfprComputeRackUnitFsmTaskFlags ::= TEXTUAL-CONVENTION
    STATUS        current
    DESCRIPTION
        ""
    SYNTAX        BITS
    {
        samDmeComputeRackUnitAdapterResetAlways(2),
        samDmeComputeRackUnitAdapterResetPowerOn(3),
        samDmeComputeRackUnitDiscoverCheckPoint(46)
    }

CfprComputeRackUnitFsmTaskItem ::= TEXTUAL-CONVENTION
    STATUS        current
    DESCRIPTION
        ""
    SYNTAX        INTEGER
    {
        nop(0),
        discover(819),
        offline(1064),
        adapterReset(1263),
        createDhcpEntry(1528)
    }

CfprComputeRackUnitMbTempStatsThresholded ::= TEXTUAL-CONVENTION
    STATUS        current
    DESCRIPTION
        ""
    SYNTAX        BITS
    {
        ambientTemp(0),
        ambientTempAvg(1),
        ambientTempMax(2),
        ambientTempMin(3),
        frontTemp(4),
        frontTempAvg(5),
        frontTempMax(6),
        frontTempMin(7),
        ioh1Temp(8),
        ioh1TempAvg(9),
        ioh1TempMax(10),
        ioh1TempMin(11),
        ioh2Temp(12),
        ioh2TempAvg(13),
        ioh2TempMax(14),
        ioh2TempMin(15),
        rearTemp(16),
        rearTempAvg(17),
        rearTempMax(18),
        rearTempMin(19)
    }

CfprComputeRackUnitMbTempStatsHistThresholded ::= TEXTUAL-CONVENTION
    STATUS        current
    DESCRIPTION
        ""
    SYNTAX        BITS
    {
        ambientTemp(0),
        ambientTempAvg(1),
        ambientTempMax(2),
        ambientTempMin(3),
        frontTemp(4),
        frontTempAvg(5),
        frontTempMax(6),
        frontTempMin(7),
        ioh1Temp(8),
        ioh1TempAvg(9),
        ioh1TempMax(10),
        ioh1TempMin(11),
        ioh2Temp(12),
        ioh2TempAvg(13),
        ioh2TempMax(14),
        ioh2TempMin(15),
        rearTemp(16),
        rearTempAvg(17),
        rearTempMax(18),
        rearTempMin(19)
    }

CfprComputeScrubAction ::= TEXTUAL-CONVENTION
    STATUS        current
    DESCRIPTION
        ""
    SYNTAX        INTEGER
    {
        no(0),
        yes(1)
    }

CfprComputeServerDiscPolicyFsmCurrentFsm ::= TEXTUAL-CONVENTION
    STATUS        current
    DESCRIPTION
        ""
    SYNTAX        INTEGER
    {
        nop(0),
        resolveScrubPolicy(1329)
    }

CfprComputeServerDiscPolicyFsmStageName ::= TEXTUAL-CONVENTION
    STATUS        current
    DESCRIPTION
        ""
    SYNTAX        INTEGER
    {
        nop(0),
        resolveScrubPolicyBegin(1329),
        resolveScrubPolicyResolve(1330),
        resolveScrubPolicyFail(1392),
        resolveScrubPolicySuccess(1393)
    }

CfprComputeServerDiscPolicyFsmTaskItem ::= TEXTUAL-CONVENTION
    STATUS        current
    DESCRIPTION
        ""
    SYNTAX        INTEGER
    {
        nop(0),
        resolveScrubPolicy(1329)
    }

CfprComputeServerMgmtDiscAction ::= TEXTUAL-CONVENTION
    STATUS        current
    DESCRIPTION
        ""
    SYNTAX        INTEGER
    {
        autoAcknowledged(0),
        userAcknowledged(1)
    }

CfprComputeSlotQualMaxId ::= TEXTUAL-CONVENTION
    STATUS        current
    DESCRIPTION
        ""
    SYNTAX        Gauge32 (1..8)

CfprComputeSlotQualMinId ::= TEXTUAL-CONVENTION
    STATUS        current
    DESCRIPTION
        ""
    SYNTAX        Gauge32 (1..8)

CfprComputeUpgradeStatus ::= TEXTUAL-CONVENTION
    STATUS        current
    DESCRIPTION
        ""
    SYNTAX        INTEGER
    {
        notUpgraded(0),
        upgraded(1),
        notApplicable(2)
    }

CfprConditionAckAction ::= TEXTUAL-CONVENTION
    STATUS        current
    DESCRIPTION
        ""
    SYNTAX        INTEGER
    {
        deleteOnClear(1),
        initialSeverity(2)
    }

CfprConditionActionIndicator ::= TEXTUAL-CONVENTION
    STATUS        current
    DESCRIPTION
        ""
    SYNTAX        INTEGER
    {
        creation(0),
        modification(1),
        deletion(2),
        stateTransition(3),
        special(4),
        failure(5)
    }

CfprConditionCallHomeCause ::= TEXTUAL-CONVENTION
    STATUS        current
    DESCRIPTION
        ""
    SYNTAX        INTEGER
    {
        unspecified(0),
        equipmentInoperable(1),
        thermalProblem(2),
        connectivityProblem(3),
        licenseGraceperiodExpired(4),
        mgmtifDown(5),
        linkDown(6),
        electionFailure(7),
        managementServicesFailure(8),
        managementServicesUnresponsive(9),
        versionIncompatible(10),
        identityUnestablishable(11),
        equipmentInaccessible(12),
        configurationFailure(13),
        associationFailed(14),
        powerProblem(15),
        equipmentProblem(16),
        voltageProblem(17),
        fruProblem(18),
        equipmentDisabled(19),
        limitReached(20),
        equipmentOffline(21),
        inventoryFailed(22),
        portFailed(23),
        vifIdsMismatch(24),
        equipmentDegraded(25),
        arpTargetsConfigError(26),
        ndiscTargetsConfigError(27),
        psuInsufficient(28),
        psuMixedMode(29),
        equipmentRemoved(30),
        adaptorMismatch(31),
        healthLedAmberBlinking(32),
        healthLedAmber(33),
        nearMaxLimit(34),
        memoryError(35),
        fileMissing(36)
    }

CfprConditionCause ::= TEXTUAL-CONVENTION
    STATUS        current
    DESCRIPTION
        ""
    SYNTAX        INTEGER
    {
        unknown(0),
        transition(1),
        beginFailed(2),
        fsmFailed(3),
        shutdownFailed(4),
        checkLicenseFailed(5),
        identifyFailed(6),
        configureSwMgmtEndPointFailed(7),
        configureVifNsFailed(8),
        configureEndPointFailed(9),
        discoverChassisFailed(10),
        enableChassisFailed(11),
        decomissionFailed(12),
        unIdentifyLocalFailed(13),
        cleanupEntriesFailed(14),
        waitFailed(15),
        disableEndPointFailed(16),
        unIdentifyPeerFailed(17),
        executeFailed(18),
        configFailed(19),
        bmcConfigureConnLocalFailed(20),
        swConfigureConnLocalFailed(21),
        bmcConfigureConnPeerFailed(22),
        swConfigureConnPeerFailed(23),
        bmcPresenceFailed(24),
        bmcInventoryFailed(25),
        preSanitizeFailed(26),
        sanitizeFailed(27),
        configUserAccessFailed(28),
        configDiscoveryModeFailed(29),
        swUnconfigPortNivLocalFailed(30),
        swUnconfigPortNivPeerFailed(31),
        swConfigPnuoslocalFailed(32),
        swConfigPnuospeerFailed(33),
        bmcPreconfigPnuoslocalFailed(34),
        bmcPreconfigPnuospeerFailed(35),
        bmcConfigPnuosFailed(36),
        bootPnuosFailed(37),
        bootWaitFailed(38),
        biosPostCompletionFailed(39),
        readSmbiosFailed(40),
        hagConnectFailed(41),
        pnuosidentFailed(42),
        pnuospolicyFailed(43),
        pnuosinventoryFailed(44),
        pnuosscrubFailed(45),
        pnuosconnectivityFailed(46),
        waitForConnReadyFailed(47),
        pnuosconnStatusFailed(48),
        swPnuosconnectivityLocalFailed(49),
        swPnuosconnectivityPeerFailed(50),
        pnuosselfTestFailed(51),
        bmcUnconfigPnuosFailed(52),
        hagDisconnectFailed(53),
        swConfigPortNivLocalFailed(54),
        swConfigPortNivPeerFailed(55),
        nicInventoryLocalFailed(56),
        nicInventoryPeerFailed(57),
        configNivModeFailed(58),
        bmcShutdownDiscoveredFailed(59),
        handlePoolingFailed(60),
        cleanupLocalFailed(63),
        cleanupPeerFailed(64),
        swUnconfigureLocalFailed(65),
        swUnconfigurePeerFailed(66),
        configFeLocalFailed(67),
        configFePeerFailed(68),
        bladePowerOnFailed(69),
        nicPresenceLocalFailed(70),
        nicPresencePeerFailed(71),
        deriveConfigFailed(72),
        swConfigLocalFailed(74),
        swConfigPeerFailed(75),
        nicConfigLocalFailed(76),
        nicConfigPeerFailed(77),
        stopvmediaLocalFailed(78),
        stopvmediaPeerFailed(79),
        setupvmediaLocalFailed(80),
        setupvmediaPeerFailed(81),
        bladeBootFailed(82),
        bladeBootWaitFailed(83),
        bladeReadSmbiosFailed(84),
        hostConnectFailed(85),
        hostIdentFailed(88),
        hostPolicyFailed(89),
        setDiagUserFailed(90),
        hostInventoryFailed(91),
        hostServerDiagFailed(92),
        hostServerDiagStatusFailed(93),
        disableServerConnSwBfailed(94),
        enableServerConnSwAfailed(95),
        startFabricatrafficTestFailed(96),
        fabricatrafficTestStatusFailed(97),
        disableServerConnSwAfailed(98),
        enableServerConnSwBfailed(99),
        startFabricbtrafficTestFailed(100),
        fabricbtrafficTestStatusFailed(101),
        cleanupServerConnSwAfailed(102),
        cleanupServerConnSwBfailed(103),
        generateReportFailed(104),
        generateLogWaitFailed(105),
        debugWaitFailed(106),
        removevmediaLocalFailed(107),
        removevmediaPeerFailed(108),
        nicUnconfigLocalFailed(109),
        nicUnconfigPeerFailed(110),
        swUnconfigLocalFailed(111),
        swUnconfigPeerFailed(112),
        removeConfigFailed(113),
        restoreConfigFeLocalFailed(114),
        restoreConfigFePeerFailed(115),
        unconfigUserAccessFailed(116),
        hostDisconnectFailed(118),
        bmcShutdownDiagCompletedFailed(119),
        evaluateStatusFailed(120),
        primaryFailed(121),
        secondaryFailed(122),
        executeLocalFailed(123),
        executePeerFailed(124),
        nicConfigPnuoslocalFailed(125),
        nicConfigPnuospeerFailed(126),
        setupVmediaLocalFailed(127),
        setupVmediaPeerFailed(128),
        bladeBootPnuosFailed(129),
        nicUnconfigPnuoslocalFailed(130),
        nicUnconfigPnuospeerFailed(131),
        swUnconfigPnuoslocalFailed(132),
        swUnconfigPnuospeerFailed(133),
        teardownVmediaLocalFailed(134),
        teardownVmediaPeerFailed(135),
        updateibmcfwFailed(136),
        waitForibmcfwUpdateFailed(137),
        activateibmcfwFailed(138),
        resetibmcFailed(139),
        bladePowerOffFailed(140),
        updateBoardCtrlRequestFailed(141),
        pollBoardCtrlUpdateStatusFailed(142),
        powerOnFailed(143),
        updateAdaptorNwFwLocalFailed(144),
        updateAdaptorNwFwPeerFailed(145),
        waitForAdaptorNwFwUpdateLocalFailed(146),
        waitForAdaptorNwFwUpdatePeerFailed(147),
        activateAdaptorNwFwLocalFailed(148),
        activateAdaptorNwFwPeerFailed(149),
        hagPnuosconnectFailed(150),
        pnuosvalidateFailed(151),
        biosImgUpdateFailed(152),
        storageCtlrImgUpdateFailed(153),
        hbaImgUpdateFailed(154),
        nicImgUpdateFailed(155),
        localDiskFwUpdateFailed(156),
        pnuosconfigFailed(157),
        pnuoslocalDiskConfigFailed(158),
        pnuosunloadDriversFailed(159),
        swConfigHostoslocalFailed(160),
        swConfigHostospeerFailed(161),
        nicConfigHostoslocalFailed(162),
        nicConfigHostospeerFailed(163),
        hagPnuosdisconnectFailed(164),
        configSoLfailed(165),
        prepareForBootFailed(166),
        configUuidFailed(167),
        bootHostFailed(168),
        hagHostosconnectFailed(169),
        hostosidentFailed(170),
        hostospolicyFailed(171),
        hostosvalidateFailed(172),
        hostosconfigFailed(173),
        nicUnconfigHostoslocalFailed(174),
        nicUnconfigHostospeerFailed(175),
        swUnconfigHostoslocalFailed(176),
        swUnconfigHostospeerFailed(177),
        configBiosFailed(178),
        pnuosunconfigFailed(179),
        unconfigUuidFailed(180),
        unconfigBiosFailed(181),
        unconfigSoLfailed(182),
        aFailed(183),
        bFailed(184),
        startFailed(185),
        cleanupFailed(186),
        resetFailed(187),
        reconfigBiosFailed(188),
        reconfigUuidFailed(189),
        applyTemplateFailed(190),
        applyIdentifiersFailed(191),
        applyPoliciesFailed(192),
        resolveBootConfigFailed(193),
        evaluateAssociationFailed(194),
        analyzeImpactFailed(195),
        waitForMaintPermissionFailed(196),
        waitForMaintWindowFailed(197),
        applyConfigFailed(198),
        mgmtifDown(199),
        updateEthMonFailed(200),
        updateFcMonFailed(201),
        serverMoved(202),
        serverIdentificationProblem(203),
        emptyPinGroup(205),
        membershipDown(206),
        configError(209),
        localFailed(211),
        peerFailed(212),
        configurationFailed(213),
        equipmentInoperable(214),
        thermalProblem(215),
        voltageProblem(216),
        capacityExceeded(217),
        equipmentDegraded(218),
        identityUnestablishable(219),
        setEpLocalFailed(220),
        setEpPeerFailed(221),
        propogateEpSettingsFailed(222),
        propogateEpTimeZoneSettingsLocalFailed(223),
        propogateEpTimeZoneSettingsPeerFailed(224),
        propogateEpTimeZoneSettingsToAdaptorsLocalFailed(225),
        propogateEpTimeZoneSettingsToAdaptorsPeerFailed(226),
        propogateEpTimeZoneSettingsToFexIomLocalFailed(227),
        propogateEpTimeZoneSettingsToFexIomPeerFailed(228),
        deployFailed(230),
        setRealmLocalFailed(231),
        setRealmPeerFailed(232),
        setUserLocalFailed(233),
        setUserPeerFailed(234),
        setKeyRingLocalFailed(235),
        setKeyRingPeerFailed(236),
        unidentifiableFru(237),
        equipmentMissing(238),
        connectivityProblem(239),
        linkDown(240),
        linkMisconnected(241),
        linkMissing(242),
        disableFailed(243),
        enableFailed(244),
        disableAfailed(245),
        enableAfailed(246),
        disableBfailed(247),
        enableBfailed(248),
        vifDown(249),
        tftpServerError(250),
        copySubFailed(251),
        copyPrimaryFailed(252),
        deleteSubFailed(253),
        deletePrimaryFailed(254),
        groupCapInsufficient(255),
        oldChassisComponentFirmware(256),
        oldFirmware(257),
        psuInsufficient(258),
        psuRedundancyFail(260),
        powerCapFail(261),
        powerConsumptionHitLimit(262),
        noAckFromBios(263),
        noCapFail(264),
        updateConnectivityFailed(265),
        createLocalFailed(266),
        createRemoteFailed(267),
        unpackLocalFailed(268),
        deleteLocalFailed(269),
        copyRemoteFailed(270),
        remoteFailed(271),
        updateLocalFailed(272),
        verifyLocalFailed(273),
        resetLocalFailed(274),
        updateRemoteFailed(275),
        verifyRemoteFailed(276),
        resetRemoteFailed(277),
        updateRequestFailed(278),
        pollUpdateStatusFailed(279),
        activateFailed(280),
        updateRequestLocalFailed(281),
        updateRequestPeerFailed(282),
        pollUpdateStatusLocalFailed(283),
        pollUpdateStatusPeerFailed(284),
        powerOffFailed(285),
        activateLocalFailed(286),
        activatePeerFailed(287),
        prepareForUpdateFailed(288),
        imageDeleted(289),
        imageUnusable(290),
        imageCannotBoot(291),
        applyFailed(292),
        rescanImagesFailed(293),
        applyCatalogFailed(294),
        syncBladeaglocalFailed(295),
        syncBladeagremoteFailed(296),
        syncNicaglocalFailed(297),
        syncNicagremoteFailed(298),
        syncPortaglocalFailed(299),
        syncPortagremoteFailed(300),
        syncHostagentaglocalFailed(301),
        syncHostagentagremoteFailed(302),
        finalizeFailed(303),
        validateLocalFailed(304),
        validateRemoteFailed(305),
        poweredOff(306),
        licenseGraceperiodEntered(307),
        licenseGraceperiod10days(308),
        licenseGraceperiod30days(309),
        serverAssociating(310),
        licenseGraceperiod90days(311),
        licenseGraceperiod119days(312),
        licenseGraceperiodExpired(313),
        serverAssigned(314),
        licenseFileNotDeleted(315),
        portFailed(316),
        unsupportedTransceiver(317),
        interfaceFailed(318),
        operationalStateDown(319),
        cmcVifDown(320),
        setLocalFailed(321),
        setPeerFailed(322),
        switchFailed(323),
        limitReached(324),
        emptyPool(325),
        backupLocalFailed(328),
        uploadFailed(329),
        downloadLocalFailed(330),
        reportResultsFailed(331),
        electionFailure(332),
        managementServicesFailure(333),
        managementServicesUnresponsive(334),
        haNotReady(335),
        versionIncompatible(336),
        logCapacity(338),
        fileTransferFailed(339),
        thresholdCrossed(340),
        insufficientResources(342),
        insufficientlyEquipped(343),
        powerProblem(344),
        discoveryFailed(345),
        associationFailed(346),
        equipmentInaccessible(347),
        equipmentProblem(348),
        solRedirectEnableFailed(364),
        serialDebugConnectFailed(365),
        maintenanceFailed(366),
        serialDebugDisconnectFailed(367),
        solRedirectDisableFailed(368),
        assignmentFailed(369),
        unassociated(370),
        nonExistentScheduler(371),
        getVersionFailed(372),
        removeLocalFailed(373),
        setEpAfailed(374),
        setEpBfailed(375),
        satelliteConnectionAbsent(376),
        bmcPreConfigPnuospeerFailed(377),
        satelliteMisConnected(378),
        unexpectedNumberOfLinks(379),
        equipmentOffline(380),
        serialDebugPnuosconnectFailed(381),
        firmwareUpgradeProblem(382),
        unsupportedConnectivityConfiguration(383),
        equipmentUnacknowledged(384),
        autoFirmwareUpgrade(385),
        equipmentDisconnected(386),
        fruProblem(387),
        validateConfigurationFailed(393),
        applyPhysicalFailed(394),
        waitOnPhysFailed(395),
        interfaceMisconfigured(402),
        missingPrimaryVlan(403),
        pinningMismatch(404),
        pinningMisconfig(405),
        equipmentDisabled(406),
        portInventorySwAfailed(419),
        portInventorySwBfailed(420),
        configSwAfailed(421),
        configSwBfailed(422),
        verifyPhysConfigFailed(423),
        activationFailed(427),
        deviceSharedStorageError(438),
        haSshKeysMismatched(439),
        executeAfailed(443),
        executeBfailed(444),
        powerDown(445),
        leadershipChange(446),
        deviceSharedStorageIOError(447),
        serverAssociated(448),
        configurationApplied(449),
        underTest(450),
        serverUnassociated(451),
        serverDeassociating(452),
        serverUnassigned(453),
        inventoryFailed(454),
        configureFailed(455),
        clearFailed(456),
        pollClearStatusFailed(457),
        pollActivateStatusFailed(458),
        updateTokensFailed(459),
        hostCatalogFailed(460),
        pnuoscatalogFailed(461),
        clearBiosUpdateFailed(462),
        pollClearBiosUpdateStatusFailed(463),
        updateBiosRequestFailed(464),
        pollBiosUpdateStatusFailed(465),
        activateBiosFailed(466),
        pollBiosActivateStatusFailed(467),
        fexUnsupported(468),
        invalidKeyringCertificate(469),
        invalidTrustpointCertChain(470),
        disassociationFailed(471),
        vifIdsMismatch(472),
        profileConfigIncorrect(473),
        pingFailed(474),
        suppressStatusChange(475),
        inaccessibleVlanReferenced(476),
        referencedVlanUnresolvable(477),
        invalidVlanInTheAllowedVlanList(478),
        vlanConflictPermit(479),
        vlanPermitUnresolved(480),
        groupPermitUnresolved(481),
        checkPowerAvailabilityFailed(482),
        markAdapterForRebootFailed(483),
        deassertResetBypassFailed(484),
        verifyFcZoneConfigFailed(485),
        cleanupPortConfigLocalFailed(486),
        cleanupPortConfigPeerFailed(487),
        powerCycleFailed(488),
        enablePortFailed(489),
        resolveIdentifiersFailed(490),
        applyDefaultIdentifiersFailed(491),
        resolveDefaultIdentifiersFailed(492),
        resolvePoliciesFailed(493),
        resolveDistributableNamesFailed(494),
        resolveDistributableFailed(495),
        resolveImagesFailed(496),
        resolveScheduleFailed(497),
        provisionStorageFailed(498),
        waitForStorageProvisionFailed(499),
        commitStorageFailed(500),
        waitForCommitStorageFailed(501),
        waitForAssocCompletionFailed(502),
        clientLostConnectivity(503),
        registerClientFailed(504),
        verifyRegistrationFailed(505),
        mountLocalFailed(506),
        mountPeerFailed(507),
        unmountLocalFailed(508),
        unmountPeerFailed(509),
        reportFailed(510),
        configurationError(511),
        operationFailed(513),
        copyExtToLocalFailed(514),
        copyExtToPeerFailed(515),
        copyToLocalFailed(516),
        copyToPeerFailed(517),
        waitForDeployFailed(518),
        activatefprmFailed(519),
        pollActivateOffprmFailed(520),
        updateiomFailed(521),
        pollUpdateOfiomFailed(522),
        activateiomFailed(523),
        pollActivateOfiomFailed(524),
        activateRemotefiFailed(525),
        pollActivateOfRemotefiFailed(526),
        waitForUserAckFailed(527),
        activateLocalfiFailed(528),
        pollActivateOfLocalfiFailed(529),
        activateCatalogFailed(530),
        providerGroupAlreadyExists(531),
        invalidServerGroup(532),
        roleConfigError(533),
        localeConfigError(534),
        userRoleConfigError(535),
        userLocaleConfigError(536),
        keyringConfigError(537),
        snmpConfigError(538),
        timezoneFileNotExists(539),
        userConfigError(540),
        snmpUserConfigError(541),
        commSvcConfigError(542),
        resolveFailed(543),
        updateVlanGroupsFailed(544),
        updateZonesFailed(545),
        noVlanOptimization(546),
        suspendModeEntered(547),
        verifyGuidFailed(548),
        unregisterFailed(549),
        cleanOldDataFailed(550),
        requestFailed(551),
        verifyFailed(552),
        releaseFailed(553),
        resolveManyFailed(554),
        releaseManyFailed(555),
        resolveAllFailed(556),
        releaseAllFailed(557),
        invalidTarget(560),
        vlanMcastPolicyMisconfigured(565),
        anotherConnectionAlreadyEnabled(566),
        connectionUnused(567),
        unsupportedConnectivity(568),
        callhomeConfigError(569),
        loadCatalogFailed(570),
        newVnicVconSchemeApplied(571),
        arpTargetsConfigError(572),
        removeFailed(573),
        configFlexFlashFailed(574),
        syncPowerStateFailed(575),
        unconfigFlexFlashFailed(576),
        resolveNetworkPoliciesFailed(577),
        resolveNetworkTemplatesFailed(578),
        validatePolicyOwnershipFailed(579),
        licenseInsufficient(580),
        invalidKeyringModulus(581),
        localeOrgConfigError(582),
        checkInventoryStatusFailed(583),
        reportFullInventoryFailed(584),
        extraPrimaryVlans(585),
        syncFailed(586),
        healthLedAmberBlinking(587),
        healthLedAmber(588),
        referencedRemoteVlanUnresolvable(589),
        multipleConnectionPolicies(591),
        updateEthFlowMonFailed(592),
        equipmentUnhealthy(593),
        postSetKeyRingLocalFailed(594),
        postSetKeyRingPeerFailed(595),
        providerGroupSizeEmpty(596),
        serverPowerOffFailed(597),
        serverPowerOnFailed(598),
        defaultHostpackMissing(599),
        defaultHostpackMissingVersions(600),
        namedVlanUnresolved(601),
        vmNetworkReferenceIncorrect(602),
        ndiscTargetsConfigError(603),
        configMemoryPolicyFailed(604),
        boardCtrlUpgraded(605),
        incompatibleServerFirmware(606),
        oobStorageInventoryFailed(608),
        configFlexFlashScrubFailed(609),
        cimcvlanCfgLocalFailed(610),
        cimcvlanCfgPeerFailed(611),
        cmcvlanCfgFailed(612),
        cmcvlanCfgPeerFailed(613),
        activeFailed(614),
        swConfigServiceInfraLocalFailed(615),
        swConfigServiceInfraPeerFailed(616),
        nicConfigServiceInfraLocalFailed(617),
        nicConfigServiceInfraPeerFailed(618),
        nicUnconfigServiceInfraLocalFailed(619),
        nicUnconfigServiceInfraPeerFailed(620),
        swUnConfigLocalFailed(621),
        swUnConfigPeerFailed(622),
        nicUnConfigLocalFailed(623),
        nicUnConfigPeerFailed(624),
        powerOnPreConfigFailed(625),
        resetSecureBootConfigFailed(626),
        udldLinkDown(627),
        copyImgFromRepFailed(630),
        copyiomimgToSubFailed(631),
        copyCatFromRepFailed(632),
        copyExternalRepToRemoteFailed(633),
        psuMixedMode(634),
        configbmcpowerParamsFailed(635),
        sendBmcProfilingInitFailed(636),
        pnuospowerProfilingFailed(637),
        sendBmcProfilingDoneFailed(638),
        downloadImagesFailed(639),
        deleteCurlDownloadedImagesFailed(640),
        configChassisIdFailed(641),
        powerButtonLockConfigFailed(642),
        powerDeployWaitFailed(643),
        extraSecondaryVlans(644),
        extraSecondaryVlansPerPrimary(645),
        sendCommandFailed(646),
        waitStageFailed(647),
        updateAppInstanceFailed(648),
        configBackupOutdated(649),
        cimcFirmwareMismatch(650),
        pldFirmwareMismatch(651),
        serverError(652),
        unconfigExtMgmtRulesFailed(653),
        unconfigExtMgmtGwFailed(654),
        unconfigCimcvmediaFailed(655),
        graphicsImageUpdateFailed(656),
        configExtMgmtRulesFailed(657),
        configExtMgmtGwFailed(658),
        configCimcvmediaFailed(659),
        sspUpdateHostPreBootFailed(660),
        configKvmMgmtDefaultSettingFailed(661),
        updateFlashLifeFailed(662),
        svnicNotPresent(663),
        unsupportedCimcFirmware(664),
        vmediaMountInaccessible(665),
        primaryVlanMissingForIsolated(666),
        primaryVlanMissingForCommunity(667),
        vlanMismatch(668),
        vlanErrorAssocPrimary(669),
        hostPrepareBootFailed(670),
        hostWaitForRommonReadyFailed(671),
        hostCheckRommonReadyFailed(672),
        hostCheckUpgradeImageStatusFailed(673),
        verifyLinkConfigFailed(677),
        formatFailed(678),
        pairFailed(679),
        namedInbandVlanUnresolved(680),
        inbandUnsupportedServer(681),
        adaptorMismatch(682),
        act2Fail(683),
        tpmOnSlaveBoard(684),
        duplicatedAssigned(685),
        checkAssignedIdentifiersForDupFailed(686),
        checkAssignedDefaultIdentifiersForDupFailed(687),
        nearMaxLimit(688),
        memoryError(689),
        waitForAppsInstallationFailed(690),
        waitForLinkConfigurationFailed(691),
        startAppsFailed(692),
        verifyBreakoutConfigFailed(693),
        slotNotResponding(694),
        bladeNotWorking(695),
        diskFormatFailed(696),
        bladeSwap(697),
        appinstanceNotResponding(698),
        appinstanceInstallFailed(699),
        appinstanceStartFailed(700),
        appinstanceUpdateFailed(701),
        appinstanceStopFailed(702),
        restoreFailed(703),
        prepareKeyFileFailed(704),
        updateSspOsSoftwareFailed(705),
        waitForSspOsUpdateCompleteFailed(706),
        configInterfaceFailed(707),
        fprmProcessFailure(708),
        waitForReadyFailed(709),
        defaultPlaformVersionMissing(710),
        bootupFailure(711),
        hostPrepareKeyFileFailed(712),
        hostWaitForRommonValidateImageFailed(713),
        hostCheckImageValidationStatusFailed(714),
        hostWaitForSspOsRunningFailed(715),
        requestToUpgradeFailed(716),
        hostWaitForUpgradeCompleteFailed(717),
        rebootHostAfterUpgradeFailed(718),
        checkBladeReadinessFailed(719),
        releaseAppLicenseFailed(720),
        configureLinksFailed(721),
        waitForConfigurationFailed(722),
        sendBundleStatusFailed(723),
        sendInterfacesFailed(724),
        unconfigureLinksFailed(725),
        configureSwitchFailed(726),
        waitForSwitchConfigFailed(727),
        sendStatusFailed(728),
        sendConfigFailed(729),
        startDiskFormatFailed(730),
        resetBladePowerFailed(731),
        waitForDiskFormatCompleteFailed(732),
        updateTimeZoneFailed(733),
        getAttributesFailed(734),
        sendUpdateFailed(735),
        updateSspEthMonFailed(736),
        switchConfigFailed(737),
        waitForConfigCompletionFailed(738),
        updateBundleStatusFailed(739),
        resetBladesFailed(740),
        licenseAgreementNotAccepted(741),
        stopDecoratorAppsFailed(742),
        wairForStopDecoratorsFailed(743),
        stopMainAppFailed(744),
        waitForBladeRebootFailed(745),
        waitForStopMainAppFailed(746),
        startMainAppFailed(747),
        waitForStartMainAppFailed(748),
        startDecoratorAppsFailed(749),
        appinstanceUnsupported(751),
        softwareVersionIncompatible(753),
        bypass(754),
        unconfigureLogicalDeviceFailed(755),
        stopAppFailed(756),
        waitForStopAppFailed(757),
        upgradeAppFailed(758),
        waitForUpgradeAppFailed(759),
        startAppFailed(760),
        cleanUpFailed(761),
        configBreakoutFailed(762),
        waitForSwitchFailed(763),
        deletePcapFileFailed(764),
        debundlePortFailed(765),
        pollDebundlePortFailed(766),
        activateMgmtExtFailed(767),
        pollActivateOfMgmtExtFailed(768),
        validateFirmwarePackFailed(769),
        activateFirmwarePackFailed(770),
        pollActivateOfFirmwarePackFailed(771),
        updateImageVersionFailed(772),
        waitForFirmwareVersionUpdateFailed(773),
        updatePackageVersionFailed(774),
        completeFirmwareUpgradeFailed(775),
        waitForBladeShutdownFailed(776),
        applyShutdownFailed(777),
        ntpConfigFailed(778),
        registerFailed(779),
        unRegisterFailed(780),
        checkReadinessFailed(781),
        logicalDeviceConfigError(784),
        resolvePolicyFailed(785),
        validateldconfigFailed(786),
        checkConfigIssuesFailed(787),
        autoConfigFailed(788),
        appImgCorrupted(789),
        installFailed(790),
        upgradeFailed(791),
        stopFailed(792),
        uninstallFailed(793),
        applyRebootFailed(794),
        platformPackFailed(795),
        completeFailed(796),
        checkUpgradeStatusFailed(797),
        ipsecConfigError(798),
        hotfixInstallFailed(799),
        hotfixError(800),
        genericError(801),
        cloudRegistrationFailed(802),
        cloudUnregistrationFailed(803),
        updateHotfixFailed(804),
        debundlePortsFailed(805),
        shutdownBladeFailed(806),
        validatePlatformPackFailed(807),
        requestToUninstallLicenseFailed(808),
        requestToInstallLicenseFailed(809),
        waitForLicInstalledCompleteFailed(810),
        hostWaitForLicInstalledCompleteFailed(811),
        onChassisFailed(812),
        rebootSystemFailed(813),
        onBladesFailed(814),
        waitForCompletionFailed(815),
        appInstallFailed(816),
        appInstalling(817),
        appNotInstalled(818),
        appNotResponding(819),
        appOffline(820),
        appOnline(821),
        appStarted(822),
        appStartFailed(823),
        appStarting(824),
        appStopFailed(825),
        appStopping(826),
        appUnsupported(827),
        appUpdateFailed(828),
        appUpdateSucceeded(829),
        appUpdating(830),
        appInCluster(831),
        appNotInCluster(832),
        appNotApplicable(833),
        appDebundle(834),
        appLeavingCluster(835),
        appJoiningCluster(836),
        slotFaultState(837),
        licenseInstalled(838),
        vnicConfigFailed(839),
        moduleOffline(840),
        moduleFailed(841),
        moduleError(842),
        moduleOirFailed(843),
        moduleOirInvalid(844),
        moduleRemoval(845),
        moduleMismatch(846),
        moduleSupriseRemoval(847),
        updateManagerFailed(848),
        adapterBootUpgradeRequired(849),
        cclSubnetNotSupported(852),
        appinstanceNotInstalled(853),
        conversionFailed(854),
        deregisterFailed(855),
        fileMissing(856),
        externalPortLinkConflictConfiguration(857),
        sendInterfaceDeletingFailed(858),
        updateSettingsFailed(859),
        appinstanceFaultState(862),
        passwordEncryptionKeyNotSet(864),
        hardwareCryptoVersionUnsupportedOrFailure(865),
        internalMgmtVnicConfigFail(867),
        invalidTpAutoImport(868),
        tpAutoImport(869),
        invalidKeyringEc(870),
        verifyKeyFailed(871),
        telemetryUnregistrationFailed(872),
        telemetryGetDataFailed(873),
        telemetrySendDataFailed(874),
        initIptablesLocalFailed(876),
        initIptablesPeerFailed(877),
        registerforTelemetryFailed(878),
        getTelemetryDataFailed(879),
        sendTelemetryDataFailed(880),
        sendChassisConfigFailed(881),
        gracefulStopAppFailed(882),
        waitForDiskFormatSecureCompleteFailed(883),
        decommissionBladeFailed(884),
        waitforDecommissionCompleteFailed(885),
        retrieveFailed(886),
        vnicPreAllocationFail(891),
        differentResourcesInProfile(892),
        resetChassisFailed(893),
        imageVersionMismatch(894),
        reenableSspEthMonFailed(895),
        decommissionFail(896),
        any(-1)
    }

CfprConditionCode ::= TEXTUAL-CONVENTION
    STATUS        current
    DESCRIPTION
        ""
    SYNTAX        INTEGER
    {
        generic(0),
        f0156(156),
        f0157(157),
        f0169(169),
        f0174(174),
        f0175(175),
        f0176(176),
        f0177(177),
        f0178(178),
        f0179(179),
        f0180(180),
        f0181(181),
        f0182(182),
        f0183(183),
        f0184(184),
        f0185(185),
        f0186(186),
        f0187(187),
        f0188(188),
        f0189(189),
        f0190(190),
        f0191(191),
        f0200(200),
        f0203(203),
        f0206(206),
        f0207(207),
        f0209(209),
        f0276(276),
        f0277(277),
        f0278(278),
        f0279(279),
        f0282(282),
        f0283(283),
        f0291(291),
        f0293(293),
        f0294(294),
        f0304(304),
        f0305(305),
        f0306(306),
        f0310(310),
        f0311(311),
        f0312(312),
        f0313(313),
        f0314(314),
        f0315(315),
        f0317(317),
        f0318(318),
        f0319(319),
        f0320(320),
        f0321(321),
        f0322(322),
        f0324(324),
        f0326(326),
        f0327(327),
        f0329(329),
        f0330(330),
        f0331(331),
        f0332(332),
        f0334(334),
        f0337(337),
        f0367(367),
        f0368(368),
        f0369(369),
        f0371(371),
        f0373(373),
        f0374(374),
        f0376(376),
        f0377(377),
        f0378(378),
        f0379(379),
        f0380(380),
        f0381(381),
        f0382(382),
        f0383(383),
        f0384(384),
        f0385(385),
        f0387(387),
        f0389(389),
        f0391(391),
        f0392(392),
        f0393(393),
        f0394(394),
        f0395(395),
        f0396(396),
        f0397(397),
        f0398(398),
        f0399(399),
        f0400(400),
        f0401(401),
        f0402(402),
        f0403(403),
        f0404(404),
        f0405(405),
        f0406(406),
        f0407(407),
        f0408(408),
        f0409(409),
        f0410(410),
        f0411(411),
        f0424(424),
        f0425(425),
        f0428(428),
        f0429(429),
        f0430(430),
        f0434(434),
        f0435(435),
        f0436(436),
        f0440(440),
        f0451(451),
        f0452(452),
        f0456(456),
        f0458(458),
        f0459(459),
        f0460(460),
        f0461(461),
        f0462(462),
        f0463(463),
        f0464(464),
        f0465(465),
        f0466(466),
        f0470(470),
        f0471(471),
        f0476(476),
        f0478(478),
        f0479(479),
        f0480(480),
        f0481(481),
        f0484(484),
        f0502(502),
        f0517(517),
        f0528(528),
        f0531(531),
        f0532(532),
        f0533(533),
        f0535(535),
        f0536(536),
        f0537(537),
        f0538(538),
        f0539(539),
        f0540(540),
        f0543(543),
        f0549(549),
        f0621(621),
        f0625(625),
        f0626(626),
        f0635(635),
        f0637(637),
        f0640(640),
        f0642(642),
        f0643(643),
        f0670(670),
        f0671(671),
        f0672(672),
        f0673(673),
        f0674(674),
        f0675(675),
        f0676(676),
        f0677(677),
        f0678(678),
        f0688(688),
        f0689(689),
        f0702(702),
        f0703(703),
        f0708(708),
        f0713(713),
        f0717(717),
        f0727(727),
        f0729(729),
        f0730(730),
        f0731(731),
        f0733(733),
        f0736(736),
        f0740(740),
        f0741(741),
        f0742(742),
        f0743(743),
        f0744(744),
        f0747(747),
        f0757(757),
        f0764(764),
        f0765(765),
        f0766(766),
        f0772(772),
        f0775(775),
        f0776(776),
        f0777(777),
        f0778(778),
        f0794(794),
        f0795(795),
        f0798(798),
        f0801(801),
        f0821(821),
        f0831(831),
        f0832(832),
        f0834(834),
        f0835(835),
        f0836(836),
        f0840(840),
        f0841(841),
        f0842(842),
        f0844(844),
        f0856(856),
        f0858(858),
        f0863(863),
        f0864(864),
        f0865(865),
        f0866(866),
        f0868(868),
        f0876(876),
        f0881(881),
        f0882(882),
        f0883(883),
        f0884(884),
        f0885(885),
        f0900(900),
        f0901(901),
        f0902(902),
        f0903(903),
        f0909(909),
        f0910(910),
        f0915(915),
        f0916(916),
        f0917(917),
        f0932(932),
        f0933(933),
        f0934(934),
        f0935(935),
        f0936(936),
        f0937(937),
        f0988(988),
        f0996(996),
        f0997(997),
        f0998(998),
        f0999(999),
        f1001(1001),
        f1003(1003),
        f1004(1004),
        f1005(1005),
        f1006(1006),
        f1007(1007),
        f1008(1008),
        f1009(1009),
        f1010(1010),
        f1026(1026),
        f1027(1027),
        f1028(1028),
        f1029(1029),
        f1030(1030),
        f1031(1031),
        f1032(1032),
        f1033(1033),
        f1034(1034),
        f1035(1035),
        f1036(1036),
        f1037(1037),
        f1056(1056),
        f1057(1057),
        f1080(1080),
        f1088(1088),
        f1090(1090),
        f1091(1091),
        f1095(1095),
        f1097(1097),
        f1098(1098),
        f1099(1099),
        f1102(1102),
        f1103(1103),
        f1114(1114),
        f1211(1211),
        f1212(1212),
        f1213(1213),
        f1214(1214),
        f1215(1215),
        f1216(1216),
        f1217(1217),
        f1218(1218),
        f1219(1219),
        f1222(1222),
        f1223(1223),
        f1229(1229),
        f1236(1236),
        f1237(1237),
        f1249(1249),
        f1251(1251),
        f1252(1252),
        f1256(1256),
        f1257(1257),
        f1258(1258),
        f1259(1259),
        f1260(1260),
        f1261(1261),
        f1262(1262),
        f1279(1279),
        f1284(1284),
        f1285(1285),
        f1304(1304),
        f1305(1305),
        f1306(1306),
        f1320(1320),
        f1321(1321),
        f1325(1325),
        f1328(1328),
        f1358(1358),
        f1359(1359),
        f1407(1407),
        f1408(1408),
        f1409(1409),
        f1410(1410),
        f1411(1411),
        f1412(1412),
        f1413(1413),
        f1414(1414),
        f1415(1415),
        f1421(1421),
        f1426(1426),
        f1432(1432),
        f1433(1433),
        f1437(1437),
        f1441(1441),
        f1442(1442),
        f1443(1443),
        f1444(1444),
        f1459(1459),
        f1460(1460),
        f1461(1461),
        f1462(1462),
        f1463(1463),
        f1464(1464),
        f1465(1465),
        f1466(1466),
        f1467(1467),
        f1468(1468),
        f1469(1469),
        f1470(1470),
        f1471(1471),
        f1472(1472),
        f1494(1494),
        f1495(1495),
        f1496(1496),
        f1497(1497),
        f1498(1498),
        f1506(1506),
        f1507(1507),
        f1508(1508),
        f1509(1509),
        f1510(1510),
        f1511(1511),
        f1512(1512),
        f1519(1519),
        f1520(1520),
        f1536(1536),
        f1537(1537),
        f1538(1538),
        f1539(1539),
        f1540(1540),
        f1541(1541),
        f1542(1542),
        f1543(1543),
        f1544(1544),
        f1545(1545),
        f1546(1546),
        f1547(1547),
        f1548(1548),
        f1549(1549),
        f1550(1550),
        f1551(1551),
        f1552(1552),
        f1553(1553),
        f1565(1565),
        f1568(1568),
        f1569(1569),
        f1571(1571),
        f1574(1574),
        f1575(1575),
        f1595(1595),
        f1622(1622),
        f1623(1623),
        f1626(1626),
        f1628(1628),
        f1629(1629),
        f1630(1630),
        f1638(1638),
        f1661(1661),
        f1671(1671),
        f1673(1673),
        f1677(1677),
        f1679(1679),
        f1681(1681),
        f1682(1682),
        f1683(1683),
        f1691(1691),
        f1692(1692),
        f1693(1693),
        f1694(1694),
        f1695(1695),
        f1716(1716),
        f1717(1717),
        f1718(1718),
        f1719(1719),
        f1720(1720),
        f1721(1721),
        f1722(1722),
        f1723(1723),
        f1724(1724),
        f1725(1725),
        f1729(1729),
        f1732(1732),
        f1735(1735),
        f1736(1736),
        f1737(1737),
        f1738(1738),
        f1739(1739),
        f1740(1740),
        f1741(1741),
        f1742(1742),
        f1743(1743),
        f1744(1744),
        f1750(1750),
        f1753(1753),
        f1757(1757),
        f1758(1758),
        f1760(1760),
        f1761(1761),
        f1762(1762),
        f1763(1763),
        f1764(1764),
        f1765(1765),
        f1766(1766),
        f1767(1767),
        f1768(1768),
        f1769(1769),
        f1774(1774),
        f1775(1775),
        f1776(1776),
        f1777(1777),
        f1778(1778),
        f1779(1779),
        f1780(1780),
        f1781(1781),
        f1782(1782),
        f1783(1783),
        f1784(1784),
        f16407(16407),
        f16408(16408),
        f16518(16518),
        f16519(16519),
        f16520(16520),
        f16533(16533),
        f16534(16534),
        f16535(16535),
        f16539(16539),
        f16550(16550),
        f16576(16576),
        f16577(16577),
        f16579(16579),
        f16580(16580),
        f16581(16581),
        f16582(16582),
        f16600(16600),
        f16601(16601),
        f16604(16604),
        f16605(16605),
        f16606(16606),
        f16634(16634),
        f16635(16635),
        f16636(16636),
        f16637(16637),
        f16641(16641),
        f16650(16650),
        f16651(16651),
        f16653(16653),
        f16654(16654),
        f16655(16655),
        f16656(16656),
        f16657(16657),
        f16670(16670),
        f16673(16673),
        f16674(16674),
        f16679(16679),
        f16680(16680),
        f16681(16681),
        f16682(16682),
        f16683(16683),
        f16684(16684),
        f16742(16742),
        f16745(16745),
        f16749(16749),
        f16750(16750),
        f16803(16803),
        f16815(16815),
        f16823(16823),
        f16852(16852),
        f16857(16857),
        f16858(16858),
        f16879(16879),
        f16880(16880),
        f16881(16881),
        f16898(16898),
        f16904(16904),
        f16906(16906),
        f16931(16931),
        f16942(16942),
        f16943(16943),
        f16944(16944),
        f16945(16945),
        f16973(16973),
        f16974(16974),
        f16975(16975),
        f16976(16976),
        f16977(16977),
        f16978(16978),
        f16979(16979),
        f16980(16980),
        f16981(16981),
        f16982(16982),
        f16983(16983),
        f16984(16984),
        f16986(16986),
        f16987(16987),
        f16988(16988),
        f16994(16994),
        f16995(16995),
        f17000(17000),
        f17001(17001),
        f17002(17002),
        f17008(17008),
        f17012(17012),
        f17013(17013),
        f17014(17014),
        f17043(17043),
        f17044(17044),
        f17045(17045),
        f17046(17046),
        f17050(17050),
        f17051(17051),
        f17052(17052),
        f17053(17053),
        f17083(17083),
        f17084(17084),
        f17089(17089),
        f17116(17116),
        f17133(17133),
        f17134(17134),
        f17163(17163),
        f17169(17169),
        f17170(17170),
        f17187(17187),
        f17214(17214),
        f17223(17223),
        f17239(17239),
        f17254(17254),
        f17259(17259),
        f17262(17262),
        f17271(17271),
        f17281(17281),
        f17282(17282),
        f17312(17312),
        f17313(17313),
        f17326(17326),
        f17327(17327),
        f17328(17328),
        f17358(17358),
        f17359(17359),
        f17360(17360),
        f17361(17361),
        f17377(17377),
        f17378(17378),
        f17379(17379),
        f17395(17395),
        f17408(17408),
        f17409(17409),
        f17426(17426),
        f17439(17439),
        f17446(17446),
        f17447(17447),
        f17448(17448),
        f17449(17449),
        f17450(17450),
        f17451(17451),
        f17452(17452),
        f17453(17453),
        f17454(17454),
        f17455(17455),
        f17456(17456),
        f17457(17457),
        f17458(17458),
        f17459(17459),
        f17460(17460),
        f17461(17461),
        f17462(17462),
        f17484(17484),
        f17485(17485),
        f17491(17491),
        f17492(17492),
        f17493(17493),
        f17494(17494),
        f17499(17499),
        f17608(17608),
        f17609(17609),
        f17612(17612),
        f17619(17619),
        f17639(17639),
        f17665(17665),
        f17667(17667),
        f17703(17703),
        f17707(17707),
        f17708(17708),
        f17714(17714),
        f17715(17715),
        f17716(17716),
        f17717(17717),
        f17808(17808),
        f17809(17809),
        f17813(17813),
        f17819(17819),
        f17830(17830),
        f17839(17839),
        f17863(17863),
        f17866(17866),
        f17872(17872),
        f17873(17873),
        f17874(17874),
        f17877(17877),
        f17897(17897),
        f17911(17911),
        f17912(17912),
        f17917(17917),
        f17920(17920),
        f17922(17922),
        f17928(17928),
        f17929(17929),
        f17930(17930),
        f17945(17945),
        f17948(17948),
        f17949(17949),
        f17954(17954),
        f17957(17957),
        f17964(17964),
        f17965(17965),
        f17966(17966),
        f17967(17967),
        f17968(17968),
        f17969(17969),
        f17970(17970),
        f17971(17971),
        f17972(17972),
        f17973(17973),
        f17974(17974),
        f17975(17975),
        f17976(17976),
        f17977(17977),
        f17978(17978),
        f17979(17979),
        f17980(17980),
        f17981(17981),
        f17982(17982),
        f17983(17983),
        f17984(17984),
        f18000(18000),
        f18003(18003),
        f18008(18008),
        f18020(18020),
        f18023(18023),
        f18024(18024),
        f18025(18025),
        f18034(18034),
        f18035(18035),
        f18043(18043),
        f18051(18051),
        f18052(18052),
        f18053(18053),
        f18056(18056),
        f18058(18058),
        f18059(18059),
        f18060(18060),
        f18064(18064),
        f18081(18081),
        f18082(18082),
        f18083(18083),
        f18092(18092),
        f18098(18098),
        f18099(18099),
        f18112(18112),
        f18129(18129),
        f18135(18135),
        f18136(18136),
        f18138(18138),
        f18154(18154),
        f18155(18155),
        f18156(18156),
        f18157(18157),
        f18169(18169),
        f33142(33142),
        f33144(33144),
        f33145(33145),
        f33146(33146),
        f33167(33167),
        f33168(33168),
        f33169(33169),
        f33170(33170),
        f33177(33177),
        f33178(33178),
        f33179(33179),
        f33180(33180),
        f33187(33187),
        f33188(33188),
        f33189(33189),
        f33190(33190),
        f33197(33197),
        f33198(33198),
        f33199(33199),
        f33200(33200),
        f33211(33211),
        f33212(33212),
        f33213(33213),
        f33214(33214),
        f33221(33221),
        f33222(33222),
        f33223(33223),
        f33224(33224),
        f33231(33231),
        f33232(33232),
        f33233(33233),
        f33234(33234),
        f33241(33241),
        f33242(33242),
        f33243(33243),
        f33244(33244),
        f33251(33251),
        f33252(33252),
        f33253(33253),
        f33254(33254),
        f33261(33261),
        f33262(33262),
        f33263(33263),
        f33264(33264),
        f33271(33271),
        f33272(33272),
        f33273(33273),
        f33274(33274),
        f33281(33281),
        f33282(33282),
        f33283(33283),
        f33284(33284),
        f33291(33291),
        f33292(33292),
        f33293(33293),
        f33294(33294),
        f33301(33301),
        f33302(33302),
        f33303(33303),
        f33304(33304),
        f33483(33483),
        f33485(33485),
        f33486(33486),
        f33487(33487),
        f33491(33491),
        f33493(33493),
        f33494(33494),
        f33495(33495),
        f33499(33499),
        f33501(33501),
        f33502(33502),
        f33503(33503),
        f33720(33720),
        f33721(33721),
        f33722(33722),
        f33723(33723),
        f33730(33730),
        f33731(33731),
        f33732(33732),
        f33733(33733),
        f33740(33740),
        f33741(33741),
        f33742(33742),
        f33743(33743),
        f33750(33750),
        f33751(33751),
        f33752(33752),
        f33753(33753),
        f33760(33760),
        f33761(33761),
        f33762(33762),
        f33763(33763),
        f33770(33770),
        f33771(33771),
        f33772(33772),
        f33773(33773),
        f33810(33810),
        f33811(33811),
        f33812(33812),
        f33813(33813),
        f33820(33820),
        f33821(33821),
        f33822(33822),
        f33823(33823),
        f33830(33830),
        f33831(33831),
        f33832(33832),
        f33833(33833),
        f33840(33840),
        f33841(33841),
        f33842(33842),
        f33843(33843),
        f33850(33850),
        f33851(33851),
        f33852(33852),
        f33853(33853),
        f33860(33860),
        f33861(33861),
        f33862(33862),
        f33863(33863),
        f33875(33875),
        f33876(33876),
        f33877(33877),
        f33878(33878),
        f33885(33885),
        f33886(33886),
        f33887(33887),
        f33888(33888),
        f33895(33895),
        f33896(33896),
        f33897(33897),
        f33898(33898),
        f33905(33905),
        f33906(33906),
        f33907(33907),
        f33908(33908),
        f33915(33915),
        f33916(33916),
        f33917(33917),
        f33918(33918),
        f33925(33925),
        f33926(33926),
        f33927(33927),
        f33928(33928),
        f33940(33940),
        f33941(33941),
        f33942(33942),
        f33943(33943),
        f33950(33950),
        f33951(33951),
        f33952(33952),
        f33953(33953),
        f33960(33960),
        f33961(33961),
        f33962(33962),
        f33963(33963),
        f33970(33970),
        f33971(33971),
        f33972(33972),
        f33973(33973),
        f33980(33980),
        f33981(33981),
        f33982(33982),
        f33983(33983),
        f33995(33995),
        f33996(33996),
        f33997(33997),
        f33998(33998),
        f34005(34005),
        f34006(34006),
        f34007(34007),
        f34008(34008),
        f34015(34015),
        f34016(34016),
        f34017(34017),
        f34018(34018),
        f34030(34030),
        f34031(34031),
        f34032(34032),
        f34033(34033),
        f34040(34040),
        f34041(34041),
        f34042(34042),
        f34043(34043),
        f34050(34050),
        f34051(34051),
        f34052(34052),
        f34053(34053),
        f34064(34064),
        f34065(34065),
        f34066(34066),
        f34067(34067),
        f34074(34074),
        f34075(34075),
        f34076(34076),
        f34077(34077),
        f34084(34084),
        f34085(34085),
        f34086(34086),
        f34087(34087),
        f34094(34094),
        f34095(34095),
        f34096(34096),
        f34097(34097),
        f34108(34108),
        f34109(34109),
        f34110(34110),
        f34111(34111),
        f34118(34118),
        f34119(34119),
        f34120(34120),
        f34121(34121),
        f34128(34128),
        f34129(34129),
        f34130(34130),
        f34131(34131),
        f34138(34138),
        f34139(34139),
        f34140(34140),
        f34141(34141),
        f34148(34148),
        f34149(34149),
        f34150(34150),
        f34151(34151),
        f34158(34158),
        f34159(34159),
        f34160(34160),
        f34161(34161),
        f34168(34168),
        f34169(34169),
        f34170(34170),
        f34171(34171),
        f34178(34178),
        f34179(34179),
        f34180(34180),
        f34181(34181),
        f34192(34192),
        f34193(34193),
        f34194(34194),
        f34195(34195),
        f34202(34202),
        f34203(34203),
        f34204(34204),
        f34205(34205),
        f34212(34212),
        f34213(34213),
        f34214(34214),
        f34215(34215),
        f34222(34222),
        f34223(34223),
        f34224(34224),
        f34225(34225),
        f34232(34232),
        f34233(34233),
        f34234(34234),
        f34235(34235),
        f34246(34246),
        f34247(34247),
        f34248(34248),
        f34249(34249),
        f34256(34256),
        f34257(34257),
        f34258(34258),
        f34259(34259),
        f34271(34271),
        f34272(34272),
        f34273(34273),
        f34274(34274),
        f34281(34281),
        f34282(34282),
        f34283(34283),
        f34284(34284),
        f34291(34291),
        f34292(34292),
        f34293(34293),
        f34294(34294),
        f34301(34301),
        f34302(34302),
        f34303(34303),
        f34304(34304),
        f34316(34316),
        f34317(34317),
        f34318(34318),
        f34319(34319),
        f34326(34326),
        f34327(34327),
        f34328(34328),
        f34329(34329),
        f34336(34336),
        f34337(34337),
        f34338(34338),
        f34339(34339),
        f34346(34346),
        f34347(34347),
        f34348(34348),
        f34349(34349),
        f34361(34361),
        f34362(34362),
        f34363(34363),
        f34364(34364),
        f34371(34371),
        f34372(34372),
        f34373(34373),
        f34374(34374),
        f34381(34381),
        f34382(34382),
        f34383(34383),
        f34384(34384),
        f34396(34396),
        f34397(34397),
        f34398(34398),
        f34399(34399),
        f34406(34406),
        f34407(34407),
        f34408(34408),
        f34409(34409),
        f34416(34416),
        f34417(34417),
        f34418(34418),
        f34419(34419),
        f34426(34426),
        f34427(34427),
        f34428(34428),
        f34429(34429),
        f34436(34436),
        f34437(34437),
        f34438(34438),
        f34439(34439),
        f34451(34451),
        f34452(34452),
        f34453(34453),
        f34454(34454),
        f34461(34461),
        f34462(34462),
        f34463(34463),
        f34464(34464),
        f34471(34471),
        f34472(34472),
        f34473(34473),
        f34474(34474),
        f34481(34481),
        f34482(34482),
        f34483(34483),
        f34484(34484),
        f34496(34496),
        f34497(34497),
        f34498(34498),
        f34499(34499),
        f34506(34506),
        f34507(34507),
        f34508(34508),
        f34509(34509),
        f34516(34516),
        f34517(34517),
        f34518(34518),
        f34519(34519),
        f34526(34526),
        f34527(34527),
        f34528(34528),
        f34529(34529),
        f34542(34542),
        f34543(34543),
        f34544(34544),
        f34545(34545),
        f34552(34552),
        f34553(34553),
        f34554(34554),
        f34555(34555),
        f34562(34562),
        f34563(34563),
        f34564(34564),
        f34565(34565),
        f34572(34572),
        f34573(34573),
        f34574(34574),
        f34575(34575),
        f34588(34588),
        f34589(34589),
        f34590(34590),
        f34591(34591),
        f34598(34598),
        f34599(34599),
        f34600(34600),
        f34601(34601),
        f34608(34608),
        f34609(34609),
        f34610(34610),
        f34611(34611),
        f34618(34618),
        f34619(34619),
        f34620(34620),
        f34621(34621),
        f34633(34633),
        f34634(34634),
        f34635(34635),
        f34636(34636),
        f34643(34643),
        f34644(34644),
        f34645(34645),
        f34646(34646),
        f34653(34653),
        f34654(34654),
        f34655(34655),
        f34656(34656),
        f34663(34663),
        f34664(34664),
        f34665(34665),
        f34666(34666),
        f34673(34673),
        f34674(34674),
        f34675(34675),
        f34676(34676),
        f34688(34688),
        f34689(34689),
        f34690(34690),
        f34691(34691),
        f34698(34698),
        f34699(34699),
        f34700(34700),
        f34701(34701),
        f34708(34708),
        f34709(34709),
        f34710(34710),
        f34711(34711),
        f34718(34718),
        f34719(34719),
        f34720(34720),
        f34721(34721),
        f34733(34733),
        f34734(34734),
        f34735(34735),
        f34736(34736),
        f34743(34743),
        f34744(34744),
        f34745(34745),
        f34746(34746),
        f34753(34753),
        f34754(34754),
        f34755(34755),
        f34756(34756),
        f34763(34763),
        f34764(34764),
        f34765(34765),
        f34766(34766),
        f34778(34778),
        f34779(34779),
        f34780(34780),
        f34781(34781),
        f34788(34788),
        f34789(34789),
        f34790(34790),
        f34791(34791),
        f34798(34798),
        f34799(34799),
        f34800(34800),
        f34801(34801),
        f34808(34808),
        f34809(34809),
        f34810(34810),
        f34811(34811),
        f34822(34822),
        f34823(34823),
        f34824(34824),
        f34825(34825),
        f34832(34832),
        f34833(34833),
        f34834(34834),
        f34835(34835),
        f34842(34842),
        f34843(34843),
        f34844(34844),
        f34845(34845),
        f34852(34852),
        f34853(34853),
        f34854(34854),
        f34855(34855),
        f34862(34862),
        f34863(34863),
        f34864(34864),
        f34865(34865),
        f34872(34872),
        f34873(34873),
        f34874(34874),
        f34875(34875),
        f34882(34882),
        f34883(34883),
        f34884(34884),
        f34885(34885),
        f34892(34892),
        f34893(34893),
        f34894(34894),
        f34895(34895),
        f34906(34906),
        f34907(34907),
        f34908(34908),
        f34909(34909),
        f34916(34916),
        f34917(34917),
        f34918(34918),
        f34919(34919),
        f34926(34926),
        f34927(34927),
        f34928(34928),
        f34929(34929),
        f34936(34936),
        f34937(34937),
        f34938(34938),
        f34939(34939),
        f34950(34950),
        f34951(34951),
        f34952(34952),
        f34953(34953),
        f34960(34960),
        f34961(34961),
        f34962(34962),
        f34963(34963),
        f34970(34970),
        f34971(34971),
        f34972(34972),
        f34973(34973),
        f34980(34980),
        f34981(34981),
        f34982(34982),
        f34983(34983),
        f34990(34990),
        f34991(34991),
        f34992(34992),
        f34993(34993),
        f35000(35000),
        f35001(35001),
        f35002(35002),
        f35003(35003),
        f35010(35010),
        f35011(35011),
        f35012(35012),
        f35013(35013),
        f35020(35020),
        f35021(35021),
        f35022(35022),
        f35023(35023),
        f35166(35166),
        f35168(35168),
        f35169(35169),
        f35170(35170),
        f35174(35174),
        f35176(35176),
        f35177(35177),
        f35178(35178),
        f35198(35198),
        f35200(35200),
        f35201(35201),
        f35202(35202),
        f35206(35206),
        f35208(35208),
        f35209(35209),
        f35210(35210),
        f35214(35214),
        f35216(35216),
        f35217(35217),
        f35218(35218),
        f35222(35222),
        f35224(35224),
        f35225(35225),
        f35226(35226),
        f35234(35234),
        f35236(35236),
        f35237(35237),
        f35238(35238),
        f35242(35242),
        f35244(35244),
        f35245(35245),
        f35246(35246),
        f35250(35250),
        f35252(35252),
        f35253(35253),
        f35254(35254),
        f35275(35275),
        f35276(35276),
        f35277(35277),
        f35278(35278),
        f35285(35285),
        f35286(35286),
        f35287(35287),
        f35288(35288),
        f35295(35295),
        f35296(35296),
        f35297(35297),
        f35298(35298),
        f35305(35305),
        f35306(35306),
        f35307(35307),
        f35308(35308),
        f35315(35315),
        f35316(35316),
        f35317(35317),
        f35318(35318),
        f35329(35329),
        f35330(35330),
        f35331(35331),
        f35332(35332),
        f35339(35339),
        f35340(35340),
        f35341(35341),
        f35342(35342),
        f35349(35349),
        f35350(35350),
        f35351(35351),
        f35352(35352),
        f35359(35359),
        f35360(35360),
        f35361(35361),
        f35362(35362),
        f35369(35369),
        f35370(35370),
        f35371(35371),
        f35372(35372),
        f35379(35379),
        f35380(35380),
        f35381(35381),
        f35382(35382),
        f35962(35962),
        f35964(35964),
        f35965(35965),
        f35966(35966),
        f35974(35974),
        f35976(35976),
        f35977(35977),
        f35978(35978),
        f36234(36234),
        f36236(36236),
        f36237(36237),
        f36238(36238),
        f36242(36242),
        f36244(36244),
        f36245(36245),
        f36246(36246),
        f36266(36266),
        f36268(36268),
        f36269(36269),
        f36270(36270),
        f36274(36274),
        f36276(36276),
        f36277(36277),
        f36278(36278),
        f36282(36282),
        f36284(36284),
        f36285(36285),
        f36286(36286),
        f36294(36294),
        f36296(36296),
        f36297(36297),
        f36298(36298),
        f36302(36302),
        f36304(36304),
        f36305(36305),
        f36306(36306),
        f36310(36310),
        f36312(36312),
        f36313(36313),
        f36314(36314),
        f36323(36323),
        f36325(36325),
        f36326(36326),
        f36327(36327),
        f36335(36335),
        f36337(36337),
        f36338(36338),
        f36339(36339),
        f37154(37154),
        f37156(37156),
        f37157(37157),
        f37158(37158),
        f37162(37162),
        f37164(37164),
        f37165(37165),
        f37166(37166),
        f37170(37170),
        f37172(37172),
        f37173(37173),
        f37174(37174),
        f37269(37269),
        f37271(37271),
        f37272(37272),
        f37273(37273),
        f37313(37313),
        f37314(37314),
        f37315(37315),
        f37316(37316),
        f37323(37323),
        f37324(37324),
        f37325(37325),
        f37326(37326),
        f37333(37333),
        f37334(37334),
        f37335(37335),
        f37336(37336),
        f37343(37343),
        f37344(37344),
        f37345(37345),
        f37346(37346),
        f37353(37353),
        f37354(37354),
        f37355(37355),
        f37356(37356),
        f37363(37363),
        f37364(37364),
        f37365(37365),
        f37366(37366),
        f37383(37383),
        f37384(37384),
        f37385(37385),
        f37386(37386),
        f37393(37393),
        f37394(37394),
        f37395(37395),
        f37396(37396),
        f37403(37403),
        f37404(37404),
        f37405(37405),
        f37406(37406),
        f37413(37413),
        f37414(37414),
        f37415(37415),
        f37416(37416),
        f37423(37423),
        f37424(37424),
        f37425(37425),
        f37426(37426),
        f37443(37443),
        f37444(37444),
        f37445(37445),
        f37446(37446),
        f37453(37453),
        f37454(37454),
        f37455(37455),
        f37456(37456),
        f37463(37463),
        f37464(37464),
        f37465(37465),
        f37466(37466),
        f37473(37473),
        f37474(37474),
        f37475(37475),
        f37476(37476),
        f37485(37485),
        f37486(37486),
        f37487(37487),
        f37488(37488),
        f37495(37495),
        f37496(37496),
        f37497(37497),
        f37498(37498),
        f37505(37505),
        f37506(37506),
        f37507(37507),
        f37508(37508),
        f37532(37532),
        f37533(37533),
        f37534(37534),
        f37535(37535),
        f37543(37543),
        f37544(37544),
        f37545(37545),
        f37546(37546),
        f37553(37553),
        f37554(37554),
        f37555(37555),
        f37556(37556),
        f37564(37564),
        f37566(37566),
        f37567(37567),
        f37568(37568),
        f37572(37572),
        f37574(37574),
        f37575(37575),
        f37576(37576),
        f37580(37580),
        f37582(37582),
        f37583(37583),
        f37584(37584),
        f37600(37600),
        f37602(37602),
        f37603(37603),
        f37604(37604),
        f37610(37610),
        f37612(37612),
        f37613(37613),
        f37614(37614),
        f37771(37771),
        f37773(37773),
        f37774(37774),
        f37775(37775),
        f37779(37779),
        f37781(37781),
        f37782(37782),
        f37783(37783),
        f38022(38022),
        f38032(38032),
        f38044(38044),
        f38054(38054),
        f38064(38064),
        f38086(38086),
        f38096(38096),
        f38106(38106),
        f38128(38128),
        f38138(38138),
        f38148(38148),
        f38158(38158),
        f38311(38311),
        f38313(38313),
        f38314(38314),
        f38315(38315),
        f38349(38349),
        f38351(38351),
        f38352(38352),
        f38353(38353),
        f38357(38357),
        f38359(38359),
        f38360(38360),
        f38361(38361),
        f38408(38408),
        f38409(38409),
        f38410(38410),
        f38411(38411),
        f38438(38438),
        f38440(38440),
        f38441(38441),
        f38442(38442),
        f38451(38451),
        f38453(38453),
        f38454(38454),
        f38455(38455),
        f38779(38779),
        f38788(38788),
        f38797(38797),
        f38806(38806),
        f38815(38815),
        f38829(38829),
        f38838(38838),
        f38847(38847),
        f38856(38856),
        f38909(38909),
        f39032(39032),
        f39034(39034),
        f39035(39035),
        f39036(39036),
        f39040(39040),
        f39042(39042),
        f39043(39043),
        f39044(39044),
        f39240(39240),
        f39242(39242),
        f39243(39243),
        f39244(39244),
        f39421(39421),
        f39423(39423),
        f39424(39424),
        f39425(39425),
        f39429(39429),
        f39431(39431),
        f39432(39432),
        f39433(39433),
        f39437(39437),
        f39439(39439),
        f39440(39440),
        f39441(39441),
        f39445(39445),
        f39447(39447),
        f39448(39448),
        f39449(39449),
        f39453(39453),
        f39455(39455),
        f39456(39456),
        f39457(39457),
        f39464(39464),
        f39466(39466),
        f39467(39467),
        f39468(39468),
        f39472(39472),
        f39474(39474),
        f39475(39475),
        f39476(39476),
        f39480(39480),
        f39482(39482),
        f39483(39483),
        f39484(39484),
        f39488(39488),
        f39490(39490),
        f39491(39491),
        f39492(39492),
        f39498(39498),
        f39500(39500),
        f39501(39501),
        f39502(39502),
        f39506(39506),
        f39508(39508),
        f39509(39509),
        f39510(39510),
        f39514(39514),
        f39516(39516),
        f39517(39517),
        f39518(39518),
        f39525(39525),
        f39527(39527),
        f39528(39528),
        f39529(39529),
        f39533(39533),
        f39535(39535),
        f39536(39536),
        f39537(39537),
        f39541(39541),
        f39543(39543),
        f39544(39544),
        f39545(39545),
        f39549(39549),
        f39551(39551),
        f39552(39552),
        f39553(39553),
        f39557(39557),
        f39559(39559),
        f39560(39560),
        f39561(39561),
        f39565(39565),
        f39567(39567),
        f39568(39568),
        f39569(39569),
        f39575(39575),
        f39577(39577),
        f39578(39578),
        f39579(39579),
        f40092(40092),
        f40094(40094),
        f40095(40095),
        f40096(40096),
        f40100(40100),
        f40102(40102),
        f40103(40103),
        f40104(40104),
        f40108(40108),
        f40110(40110),
        f40111(40111),
        f40112(40112),
        f40116(40116),
        f40118(40118),
        f40119(40119),
        f40120(40120),
        f40124(40124),
        f40126(40126),
        f40127(40127),
        f40128(40128),
        f40547(40547),
        f40549(40549),
        f40550(40550),
        f40551(40551),
        f40555(40555),
        f40557(40557),
        f40558(40558),
        f40559(40559),
        f40563(40563),
        f40565(40565),
        f40566(40566),
        f40567(40567),
        f40574(40574),
        f40576(40576),
        f40577(40577),
        f40578(40578),
        f40582(40582),
        f40584(40584),
        f40585(40585),
        f40586(40586),
        f41199(41199),
        f41201(41201),
        f41202(41202),
        f41203(41203),
        f41207(41207),
        f41209(41209),
        f41210(41210),
        f41211(41211),
        f41215(41215),
        f41217(41217),
        f41218(41218),
        f41219(41219),
        f41289(41289),
        f41290(41290),
        f41291(41291),
        f41292(41292),
        f41299(41299),
        f41300(41300),
        f41301(41301),
        f41302(41302),
        f41309(41309),
        f41310(41310),
        f41311(41311),
        f41312(41312),
        f41319(41319),
        f41320(41320),
        f41321(41321),
        f41322(41322),
        f41329(41329),
        f41330(41330),
        f41331(41331),
        f41332(41332),
        f41339(41339),
        f41340(41340),
        f41341(41341),
        f41342(41342),
        f41349(41349),
        f41350(41350),
        f41351(41351),
        f41352(41352),
        f41359(41359),
        f41360(41360),
        f41361(41361),
        f41362(41362),
        f43101(43101),
        f43103(43103),
        f43104(43104),
        f43105(43105),
        f43109(43109),
        f43111(43111),
        f43112(43112),
        f43113(43113),
        f43787(43787),
        f43788(43788),
        f43789(43789),
        f43790(43790),
        f43797(43797),
        f43798(43798),
        f43799(43799),
        f43800(43800),
        f43807(43807),
        f43808(43808),
        f43809(43809),
        f43810(43810),
        f43817(43817),
        f43818(43818),
        f43819(43819),
        f43820(43820),
        f43827(43827),
        f43828(43828),
        f43829(43829),
        f43830(43830),
        f77847(77847),
        f77848(77848),
        f77958(77958),
        f77959(77959),
        f77960(77960),
        f77973(77973),
        f77974(77974),
        f77975(77975),
        f77979(77979),
        f77990(77990),
        f78016(78016),
        f78017(78017),
        f78019(78019),
        f78020(78020),
        f78021(78021),
        f78022(78022),
        f78040(78040),
        f78041(78041),
        f78044(78044),
        f78045(78045),
        f78046(78046),
        f78074(78074),
        f78075(78075),
        f78076(78076),
        f78077(78077),
        f78081(78081),
        f78090(78090),
        f78091(78091),
        f78093(78093),
        f78094(78094),
        f78095(78095),
        f78096(78096),
        f78097(78097),
        f78110(78110),
        f78113(78113),
        f78114(78114),
        f78119(78119),
        f78120(78120),
        f78121(78121),
        f78122(78122),
        f78123(78123),
        f78124(78124),
        f78182(78182),
        f78185(78185),
        f78189(78189),
        f78190(78190),
        f78243(78243),
        f78255(78255),
        f78263(78263),
        f78292(78292),
        f78297(78297),
        f78298(78298),
        f78319(78319),
        f78320(78320),
        f78321(78321),
        f78338(78338),
        f78344(78344),
        f78346(78346),
        f78371(78371),
        f78382(78382),
        f78383(78383),
        f78384(78384),
        f78385(78385),
        f78413(78413),
        f78414(78414),
        f78415(78415),
        f78416(78416),
        f78417(78417),
        f78418(78418),
        f78419(78419),
        f78420(78420),
        f78421(78421),
        f78422(78422),
        f78423(78423),
        f78424(78424),
        f78426(78426),
        f78427(78427),
        f78428(78428),
        f78434(78434),
        f78435(78435),
        f78440(78440),
        f78441(78441),
        f78442(78442),
        f78448(78448),
        f78452(78452),
        f78453(78453),
        f78454(78454),
        f78483(78483),
        f78484(78484),
        f78485(78485),
        f78486(78486),
        f78490(78490),
        f78491(78491),
        f78492(78492),
        f78493(78493),
        f78523(78523),
        f78524(78524),
        f78529(78529),
        f78556(78556),
        f78573(78573),
        f78574(78574),
        f78603(78603),
        f78609(78609),
        f78610(78610),
        f78627(78627),
        f78654(78654),
        f78663(78663),
        f78679(78679),
        f78694(78694),
        f78699(78699),
        f78702(78702),
        f78711(78711),
        f78721(78721),
        f78722(78722),
        f78752(78752),
        f78753(78753),
        f78766(78766),
        f78767(78767),
        f78768(78768),
        f78798(78798),
        f78799(78799),
        f78800(78800),
        f78801(78801),
        f78817(78817),
        f78818(78818),
        f78819(78819),
        f78835(78835),
        f78848(78848),
        f78849(78849),
        f78866(78866),
        f78879(78879),
        f78886(78886),
        f78887(78887),
        f78888(78888),
        f78889(78889),
        f78890(78890),
        f78891(78891),
        f78892(78892),
        f78893(78893),
        f78894(78894),
        f78895(78895),
        f78896(78896),
        f78897(78897),
        f78898(78898),
        f78899(78899),
        f78900(78900),
        f78901(78901),
        f78902(78902),
        f78924(78924),
        f78925(78925),
        f78931(78931),
        f78932(78932),
        f78933(78933),
        f78934(78934),
        f78939(78939),
        f79048(79048),
        f79049(79049),
        f79052(79052),
        f79059(79059),
        f79079(79079),
        f79105(79105),
        f79107(79107),
        f79143(79143),
        f79147(79147),
        f79148(79148),
        f79154(79154),
        f79155(79155),
        f79156(79156),
        f79157(79157),
        f79248(79248),
        f79249(79249),
        f79253(79253),
        f79259(79259),
        f79270(79270),
        f79279(79279),
        f79303(79303),
        f79306(79306),
        f79312(79312),
        f79313(79313),
        f79314(79314),
        f79317(79317),
        f79337(79337),
        f79351(79351),
        f79352(79352),
        f79357(79357),
        f79360(79360),
        f79362(79362),
        f79368(79368),
        f79369(79369),
        f79370(79370),
        f79385(79385),
        f79388(79388),
        f79389(79389),
        f79394(79394),
        f79397(79397),
        f79404(79404),
        f79405(79405),
        f79406(79406),
        f79407(79407),
        f79408(79408),
        f79409(79409),
        f79410(79410),
        f79411(79411),
        f79412(79412),
        f79413(79413),
        f79414(79414),
        f79415(79415),
        f79416(79416),
        f79417(79417),
        f79418(79418),
        f79419(79419),
        f79420(79420),
        f79421(79421),
        f79422(79422),
        f79423(79423),
        f79424(79424),
        f79440(79440),
        f79443(79443),
        f79448(79448),
        f79460(79460),
        f79463(79463),
        f79464(79464),
        f79465(79465),
        f79474(79474),
        f79475(79475),
        f79483(79483),
        f79491(79491),
        f79492(79492),
        f79493(79493),
        f79496(79496),
        f79498(79498),
        f79499(79499),
        f79500(79500),
        f79504(79504),
        f79521(79521),
        f79522(79522),
        f79523(79523),
        f79532(79532),
        f79538(79538),
        f79539(79539),
        f79552(79552),
        f79569(79569),
        f79575(79575),
        f79576(79576),
        f79578(79578),
        f79594(79594),
        f79595(79595),
        f79596(79596),
        f79597(79597),
        f79609(79609),
        f999447(999447),
        f999448(999448),
        f999558(999558),
        f999559(999559),
        f999560(999560),
        f999573(999573),
        f999574(999574),
        f999575(999575),
        f999579(999579),
        f999590(999590),
        f999616(999616),
        f999617(999617),
        f999619(999619),
        f999620(999620),
        f999621(999621),
        f999622(999622),
        f999640(999640),
        f999641(999641),
        f999644(999644),
        f999645(999645),
        f999646(999646),
        f999674(999674),
        f999675(999675),
        f999676(999676),
        f999677(999677),
        f999681(999681),
        f999690(999690),
        f999691(999691),
        f999693(999693),
        f999694(999694),
        f999695(999695),
        f999696(999696),
        f999697(999697),
        f999710(999710),
        f999713(999713),
        f999714(999714),
        f999719(999719),
        f999720(999720),
        f999721(999721),
        f999722(999722),
        f999723(999723),
        f999724(999724),
        f999782(999782),
        f999785(999785),
        f999789(999789),
        f999790(999790),
        f999843(999843),
        f999855(999855),
        f999863(999863),
        f999892(999892),
        f999897(999897),
        f999898(999898),
        f999919(999919),
        f999920(999920),
        f999921(999921),
        f999938(999938),
        f999944(999944),
        f999946(999946),
        f999971(999971),
        f999982(999982),
        f999983(999983),
        f999984(999984),
        f999985(999985),
        f1000013(1000013),
        f1000014(1000014),
        f1000015(1000015),
        f1000016(1000016),
        f1000017(1000017),
        f1000018(1000018),
        f1000019(1000019),
        f1000020(1000020),
        f1000021(1000021),
        f1000022(1000022),
        f1000023(1000023),
        f1000024(1000024),
        f1000026(1000026),
        f1000027(1000027),
        f1000028(1000028),
        f1000034(1000034),
        f1000035(1000035),
        f1000040(1000040),
        f1000041(1000041),
        f1000042(1000042),
        f1000048(1000048),
        f1000052(1000052),
        f1000053(1000053),
        f1000054(1000054),
        f1000083(1000083),
        f1000084(1000084),
        f1000085(1000085),
        f1000086(1000086),
        f1000090(1000090),
        f1000091(1000091),
        f1000092(1000092),
        f1000093(1000093),
        f1000123(1000123),
        f1000124(1000124),
        f1000129(1000129),
        f1000156(1000156),
        f1000173(1000173),
        f1000174(1000174),
        f1000203(1000203),
        f1000209(1000209),
        f1000210(1000210),
        f1000227(1000227),
        f1000254(1000254),
        f1000263(1000263),
        f1000279(1000279),
        f1000294(1000294),
        f1000299(1000299),
        f1000302(1000302),
        f1000311(1000311),
        f1000321(1000321),
        f1000322(1000322),
        f1000352(1000352),
        f1000353(1000353),
        f1000366(1000366),
        f1000367(1000367),
        f1000368(1000368),
        f1000398(1000398),
        f1000399(1000399),
        f1000400(1000400),
        f1000401(1000401),
        f1000417(1000417),
        f1000418(1000418),
        f1000419(1000419),
        f1000435(1000435),
        f1000448(1000448),
        f1000449(1000449),
        f1000466(1000466),
        f1000479(1000479),
        f1000486(1000486),
        f1000487(1000487),
        f1000488(1000488),
        f1000489(1000489),
        f1000490(1000490),
        f1000491(1000491),
        f1000492(1000492),
        f1000493(1000493),
        f1000494(1000494),
        f1000495(1000495),
        f1000496(1000496),
        f1000497(1000497),
        f1000498(1000498),
        f1000499(1000499),
        f1000500(1000500),
        f1000501(1000501),
        f1000502(1000502),
        f1000524(1000524),
        f1000525(1000525),
        f1000531(1000531),
        f1000532(1000532),
        f1000533(1000533),
        f1000534(1000534),
        f1000539(1000539),
        f1000648(1000648),
        f1000649(1000649),
        f1000652(1000652),
        f1000659(1000659),
        f1000679(1000679),
        f1000705(1000705),
        f1000707(1000707),
        f1000743(1000743),
        f1000747(1000747),
        f1000748(1000748),
        f1000754(1000754),
        f1000755(1000755),
        f1000756(1000756),
        f1000757(1000757),
        f1000848(1000848),
        f1000849(1000849),
        f1000853(1000853),
        f1000859(1000859),
        f1000870(1000870),
        f1000879(1000879),
        f1000903(1000903),
        f1000906(1000906),
        f1000912(1000912),
        f1000913(1000913),
        f1000914(1000914),
        f1000917(1000917),
        f1000937(1000937),
        f1000951(1000951),
        f1000952(1000952),
        f1000957(1000957),
        f1000960(1000960),
        f1000962(1000962),
        f1000968(1000968),
        f1000969(1000969),
        f1000970(1000970),
        f1000985(1000985),
        f1000988(1000988),
        f1000989(1000989),
        f1000994(1000994),
        f1000997(1000997),
        f1001004(1001004),
        f1001005(1001005),
        f1001006(1001006),
        f1001007(1001007),
        f1001008(1001008),
        f1001009(1001009),
        f1001010(1001010),
        f1001011(1001011),
        f1001012(1001012),
        f1001013(1001013),
        f1001014(1001014),
        f1001015(1001015),
        f1001016(1001016),
        f1001017(1001017),
        f1001018(1001018),
        f1001019(1001019),
        f1001020(1001020),
        f1001021(1001021),
        f1001022(1001022),
        f1001023(1001023),
        f1001024(1001024),
        f1001040(1001040),
        f1001043(1001043),
        f1001048(1001048),
        f1001060(1001060),
        f1001063(1001063),
        f1001064(1001064),
        f1001065(1001065),
        f1001074(1001074),
        f1001075(1001075),
        f1001083(1001083),
        f1001091(1001091),
        f1001092(1001092),
        f1001093(1001093),
        f1001096(1001096),
        f1001098(1001098),
        f1001099(1001099),
        f1001100(1001100),
        f1001104(1001104),
        f1001121(1001121),
        f1001122(1001122),
        f1001123(1001123),
        f1001132(1001132),
        f1001138(1001138),
        f1001139(1001139),
        f1001152(1001152),
        f1001169(1001169),
        f1001175(1001175),
        f1001176(1001176),
        f1001178(1001178),
        f1001194(1001194),
        f1001195(1001195),
        f1001196(1001196),
        f1001197(1001197),
        f1001209(1001209),
        e4194528(4194528),
        e4194529(4194529),
        e4194530(4194530),
        e4194531(4194531),
        e4194532(4194532),
        e4194533(4194533),
        e4194534(4194534),
        e4194535(4194535),
        e4194536(4194536),
        e4194537(4194537),
        e4194538(4194538),
        e4194539(4194539),
        e4194540(4194540),
        e4194541(4194541),
        e4194542(4194542),
        e4194543(4194543),
        e4194544(4194544),
        e4194545(4194545),
        e4194546(4194546),
        e4194547(4194547),
        e4194548(4194548),
        e4194549(4194549),
        e4194550(4194550),
        e4194551(4194551),
        e4194552(4194552),
        e4194553(4194553),
        e4194554(4194554),
        e4194555(4194555),
        e4194556(4194556),
        e4194557(4194557),
        e4194558(4194558),
        e4194559(4194559),
        e4194560(4194560),
        e4194561(4194561),
        e4194562(4194562),
        e4194563(4194563),
        e4194564(4194564),
        e4194565(4194565),
        e4194566(4194566),
        e4194567(4194567),
        e4194568(4194568),
        e4194569(4194569),
        e4194570(4194570),
        e4194571(4194571),
        e4194572(4194572),
        e4194573(4194573),
        e4194574(4194574),
        e4194575(4194575),
        e4194576(4194576),
        e4194577(4194577),
        e4194578(4194578),
        e4194579(4194579),
        e4194580(4194580),
        e4194581(4194581),
        e4194582(4194582),
        e4194583(4194583),
        e4194584(4194584),
        e4194585(4194585),
        e4194586(4194586),
        e4194587(4194587),
        e4194591(4194591),
        e4194592(4194592),
        e4194593(4194593),
        e4194594(4194594),
        e4194595(4194595),
        e4194596(4194596),
        e4194597(4194597),
        e4194598(4194598),
        e4194599(4194599),
        e4194600(4194600),
        e4194601(4194601),
        e4194602(4194602),
        e4194603(4194603),
        e4194604(4194604),
        e4194605(4194605),
        e4194607(4194607),
        e4194608(4194608),
        e4194609(4194609),
        e4194610(4194610),
        e4194611(4194611),
        e4194612(4194612),
        e4194613(4194613),
        e4194614(4194614),
        e4194615(4194615),
        e4194616(4194616),
        e4194617(4194617),
        e4194620(4194620),
        e4194621(4194621),
        e4194622(4194622),
        e4194623(4194623),
        e4194624(4194624),
        e4194626(4194626),
        e4194627(4194627),
        e4194628(4194628),
        e4194629(4194629),
        e4194630(4194630),
        e4194631(4194631),
        e4194632(4194632),
        e4194652(4194652),
        e4194654(4194654),
        e4194655(4194655),
        e4194656(4194656),
        e4194657(4194657),
        e4194658(4194658),
        e4194659(4194659),
        e4194660(4194660),
        e4194661(4194661),
        e4194662(4194662),
        e4194663(4194663),
        e4194664(4194664),
        e4194665(4194665),
        e4194671(4194671),
        e4194672(4194672),
        e4194673(4194673),
        e4194674(4194674),
        e4194675(4194675),
        e4194676(4194676),
        e4194683(4194683),
        e4194684(4194684),
        e4194685(4194685),
        e4194686(4194686),
        e4194687(4194687),
        e4194688(4194688),
        e4194689(4194689),
        e4194693(4194693),
        e4194694(4194694),
        e4194695(4194695),
        e4194697(4194697),
        e4194698(4194698),
        e4194699(4194699),
        e4194700(4194700),
        e4194701(4194701),
        e4194702(4194702),
        e4194703(4194703),
        e4194704(4194704),
        e4194705(4194705),
        e4194706(4194706),
        e4194714(4194714),
        e4194715(4194715),
        e4194717(4194717),
        e4194718(4194718),
        e4194720(4194720),
        e4194721(4194721),
        e4194722(4194722),
        e4194723(4194723),
        e4194724(4194724),
        e4194725(4194725),
        e4194726(4194726),
        e4194727(4194727),
        e4194728(4194728),
        e4194729(4194729),
        e4194730(4194730),
        e4194734(4194734),
        e4194736(4194736),
        e4194737(4194737),
        e4194738(4194738),
        e4194739(4194739),
        e4194740(4194740),
        e4194741(4194741),
        e4194744(4194744),
        e4194745(4194745),
        e4194746(4194746),
        e4194747(4194747),
        e4194748(4194748),
        e4194749(4194749),
        e4194750(4194750),
        e4194751(4194751),
        e4194752(4194752),
        e4194753(4194753),
        e4194754(4194754),
        e4194755(4194755),
        e4194763(4194763),
        e4194764(4194764),
        e4194765(4194765),
        e4194766(4194766),
        e4194767(4194767),
        e4194768(4194768),
        e4194769(4194769),
        e4194770(4194770),
        e4194771(4194771),
        e4194773(4194773),
        e4194774(4194774),
        e4194775(4194775),
        e4194776(4194776),
        e4194777(4194777),
        e4194778(4194778),
        e4194787(4194787),
        e4194788(4194788),
        e4194789(4194789),
        e4194790(4194790),
        e4194791(4194791),
        e4194792(4194792),
        e4194793(4194793),
        e4194794(4194794),
        e4194795(4194795),
        e4194796(4194796),
        e4194797(4194797),
        e4194798(4194798),
        e4194799(4194799),
        e4194800(4194800),
        e4194801(4194801),
        e4194802(4194802),
        e4194803(4194803),
        e4194804(4194804),
        e4194805(4194805),
        e4194806(4194806),
        e4194807(4194807),
        e4194812(4194812),
        e4194828(4194828),
        e4194830(4194830),
        e4194831(4194831),
        e4194832(4194832),
        e4194833(4194833),
        e4194834(4194834),
        e4194835(4194835),
        e4194836(4194836),
        e4194847(4194847),
        e4194848(4194848),
        e4194849(4194849),
        e4194856(4194856),
        e4194859(4194859),
        e4194860(4194860),
        e4194861(4194861),
        e4194862(4194862),
        e4194863(4194863),
        e4194864(4194864),
        e4194865(4194865),
        e4194866(4194866),
        e4194867(4194867),
        e4194868(4194868),
        e4194869(4194869),
        e4194871(4194871),
        e4194876(4194876),
        e4194878(4194878),
        e4194879(4194879),
        e4194880(4194880),
        e4194881(4194881),
        e4194883(4194883),
        e4194884(4194884),
        e4194885(4194885),
        e4194886(4194886),
        e4194887(4194887),
        e4194888(4194888),
        e4194889(4194889),
        e4194890(4194890),
        e4194891(4194891),
        e4194892(4194892),
        e4194894(4194894),
        e4194895(4194895),
        e4194896(4194896),
        e4194897(4194897),
        e4194899(4194899),
        e4194900(4194900),
        e4194901(4194901),
        e4194902(4194902),
        e4194903(4194903),
        e4194904(4194904),
        e4194905(4194905),
        e4194906(4194906),
        e4194907(4194907),
        e4194908(4194908),
        e4194909(4194909),
        e4194910(4194910),
        e4194911(4194911),
        e4194918(4194918),
        e4194919(4194919),
        e4194920(4194920),
        e4194921(4194921),
        e4194924(4194924),
        e4194925(4194925),
        e4194926(4194926),
        e4194927(4194927),
        e4194928(4194928),
        e4194929(4194929),
        e4194930(4194930),
        e4194931(4194931),
        e4194932(4194932),
        e4194933(4194933),
        e4194934(4194934),
        e4194935(4194935),
        e4194936(4194936),
        e4194937(4194937),
        e4194938(4194938),
        e4194939(4194939),
        e4194940(4194940),
        e4194941(4194941),
        e4194942(4194942),
        e4194943(4194943),
        e4194944(4194944),
        e4194945(4194945),
        e4194946(4194946),
        e4194947(4194947),
        e4194948(4194948),
        e4194949(4194949),
        e4194950(4194950),
        e4194951(4194951),
        e4194952(4194952),
        e4194953(4194953),
        e4194954(4194954),
        e4194955(4194955),
        e4194956(4194956),
        e4194969(4194969),
        e4194970(4194970),
        e4194971(4194971),
        e4194984(4194984),
        e4194985(4194985),
        e4194986(4194986),
        e4194987(4194987),
        e4194988(4194988),
        e4194989(4194989),
        e4194990(4194990),
        e4194991(4194991),
        e4194992(4194992),
        e4194993(4194993),
        e4194994(4194994),
        e4194995(4194995),
        e4194996(4194996),
        e4194997(4194997),
        e4195000(4195000),
        e4195001(4195001),
        e4195003(4195003),
        e4195004(4195004),
        e4195006(4195006),
        e4195007(4195007),
        e4195008(4195008),
        e4195009(4195009),
        e4195010(4195010),
        e4195011(4195011),
        e4195012(4195012),
        e4195013(4195013),
        e4195014(4195014),
        e4195017(4195017),
        e4195018(4195018),
        e4195019(4195019),
        e4195020(4195020),
        e4195021(4195021),
        e4195022(4195022),
        e4195023(4195023),
        e4195024(4195024),
        e4195025(4195025),
        e4195026(4195026),
        e4195027(4195027),
        e4195028(4195028),
        e4195029(4195029),
        e4195030(4195030),
        e4195031(4195031),
        e4195032(4195032),
        e4195033(4195033),
        e4195034(4195034),
        e4195036(4195036),
        e4195037(4195037),
        e4195038(4195038),
        e4195039(4195039),
        e4195040(4195040),
        e4195041(4195041),
        e4195043(4195043),
        e4195044(4195044),
        e4195045(4195045),
        e4195046(4195046),
        e4195047(4195047),
        e4195048(4195048),
        e4195049(4195049),
        e4195050(4195050),
        e4195051(4195051),
        e4195052(4195052),
        e4195053(4195053),
        e4195054(4195054),
        e4195055(4195055),
        e4195056(4195056),
        e4195057(4195057),
        e4195058(4195058),
        e4195059(4195059),
        e4195060(4195060),
        e4195061(4195061),
        e4195064(4195064),
        e4195065(4195065),
        e4195066(4195066),
        e4195067(4195067),
        e4195068(4195068),
        e4195069(4195069),
        e4195071(4195071),
        e4195072(4195072),
        e4195073(4195073),
        e4195074(4195074),
        e4195075(4195075),
        e4195076(4195076),
        e4195077(4195077),
        e4195078(4195078),
        e4195080(4195080),
        e4195081(4195081),
        e4195082(4195082),
        e4195083(4195083),
        e4195084(4195084),
        e4195085(4195085),
        e4195086(4195086),
        e4195087(4195087),
        e4195088(4195088),
        e4195207(4195207),
        e4195208(4195208),
        e4195209(4195209),
        e4195213(4195213),
        e4195214(4195214),
        e4195220(4195220),
        e4195221(4195221),
        e4195222(4195222),
        e4195223(4195223),
        e4195224(4195224),
        e4195225(4195225),
        e4195226(4195226),
        e4195227(4195227),
        e4195228(4195228),
        e4195229(4195229),
        e4195230(4195230),
        e4195231(4195231),
        e4195232(4195232),
        e4195234(4195234),
        e4195235(4195235),
        e4195236(4195236),
        e4195237(4195237),
        e4195238(4195238),
        e4195239(4195239),
        e4195242(4195242),
        e4195243(4195243),
        e4195244(4195244),
        e4195245(4195245),
        e4195246(4195246),
        e4195247(4195247),
        e4195248(4195248),
        e4195249(4195249),
        e4195250(4195250),
        e4195251(4195251),
        e4195252(4195252),
        e4195253(4195253),
        e4195254(4195254),
        e4195255(4195255),
        e4195256(4195256),
        e4195257(4195257),
        e4195258(4195258),
        e4195259(4195259),
        e4195260(4195260),
        e4195261(4195261),
        e4195262(4195262),
        e4195263(4195263),
        e4195264(4195264),
        e4195265(4195265),
        e4195266(4195266),
        e4195267(4195267),
        e4195268(4195268),
        e4195269(4195269),
        e4195270(4195270),
        e4195271(4195271),
        e4195272(4195272),
        e4195273(4195273),
        e4195274(4195274),
        e4195275(4195275),
        e4195276(4195276),
        e4195277(4195277),
        e4195278(4195278),
        e4195279(4195279),
        e4195281(4195281),
        e4195282(4195282),
        e4195283(4195283),
        e4195284(4195284),
        e4195285(4195285),
        e4195286(4195286),
        e4195287(4195287),
        e4195288(4195288),
        e4195289(4195289),
        e4195290(4195290),
        e4195291(4195291),
        e4195292(4195292),
        e4195293(4195293),
        e4195294(4195294),
        e4195295(4195295),
        e4195296(4195296),
        e4195297(4195297),
        e4195298(4195298),
        e4195299(4195299),
        e4195300(4195300),
        e4195301(4195301),
        e4195302(4195302),
        e4195303(4195303),
        e4195304(4195304),
        e4195305(4195305),
        e4195306(4195306),
        e4195307(4195307),
        e4195308(4195308),
        e4195309(4195309),
        e4195310(4195310),
        e4195311(4195311),
        e4195312(4195312),
        e4195313(4195313),
        e4195314(4195314),
        e4195315(4195315),
        e4195316(4195316),
        e4195317(4195317),
        e4195318(4195318),
        e4195319(4195319),
        e4195320(4195320),
        e4195321(4195321),
        e4195331(4195331),
        e4195332(4195332),
        e4195333(4195333),
        e4195334(4195334),
        e4195335(4195335),
        e4195336(4195336),
        e4195337(4195337),
        e4195338(4195338),
        e4195339(4195339),
        e4195340(4195340),
        e4195341(4195341),
        e4195342(4195342),
        e4195343(4195343),
        e4195344(4195344),
        e4195345(4195345),
        e4195346(4195346),
        e4195347(4195347),
        e4195348(4195348),
        e4195349(4195349),
        e4195350(4195350),
        e4195351(4195351),
        e4195352(4195352),
        e4195353(4195353),
        e4195354(4195354),
        e4195355(4195355),
        e4195356(4195356),
        e4195357(4195357),
        e4195358(4195358),
        e4195359(4195359),
        e4195360(4195360),
        e4195361(4195361),
        e4195362(4195362),
        e4195363(4195363),
        e4195364(4195364),
        e4195365(4195365),
        e4195366(4195366),
        e4195367(4195367),
        e4195368(4195368),
        e4195369(4195369),
        e4195370(4195370),
        e4195371(4195371),
        e4195372(4195372),
        e4195373(4195373),
        e4195374(4195374),
        e4195375(4195375),
        e4195376(4195376),
        e4195377(4195377),
        e4195378(4195378),
        e4195379(4195379),
        e4195380(4195380),
        e4195381(4195381),
        e4195382(4195382),
        e4195387(4195387),
        e4195388(4195388),
        e4195389(4195389),
        e4195390(4195390),
        e4195391(4195391),
        e4195392(4195392),
        e4195393(4195393),
        e4195394(4195394),
        e4195395(4195395),
        e4195396(4195396),
        e4195397(4195397),
        e4195398(4195398),
        e4195400(4195400),
        e4195401(4195401),
        e4195402(4195402),
        e4195403(4195403),
        e4195404(4195404),
        e4195405(4195405),
        e4195406(4195406),
        e4195407(4195407),
        e4195408(4195408),
        e4195409(4195409),
        e4195410(4195410),
        e4195411(4195411),
        e4195412(4195412),
        e4195413(4195413),
        e4195414(4195414),
        e4195415(4195415),
        e4195416(4195416),
        e4195417(4195417),
        e4195418(4195418),
        e4195419(4195419),
        e4195460(4195460),
        e4195461(4195461),
        e4195462(4195462),
        e4195463(4195463),
        e4195464(4195464),
        e4195465(4195465),
        e4195466(4195466),
        e4195467(4195467),
        e4195472(4195472),
        e4195473(4195473),
        e4195474(4195474),
        e4195475(4195475),
        e4195476(4195476),
        e4195477(4195477),
        e4195478(4195478),
        e4195479(4195479),
        e4195480(4195480),
        e4195481(4195481),
        e4195482(4195482),
        e4195483(4195483),
        e4195484(4195484),
        e4195485(4195485),
        e4195486(4195486),
        e4195487(4195487),
        e4195488(4195488),
        e4195489(4195489),
        e4195490(4195490),
        e4195491(4195491),
        e4195492(4195492),
        e4195493(4195493),
        e4195494(4195494),
        e4195495(4195495),
        e4195496(4195496),
        e4195497(4195497),
        e4195498(4195498),
        e4195499(4195499),
        e4195500(4195500),
        e4195501(4195501),
        e4195502(4195502),
        e4195503(4195503),
        e4195504(4195504),
        e4195505(4195505),
        e4195506(4195506),
        e4195507(4195507),
        e4195508(4195508),
        e4195509(4195509),
        e4195510(4195510),
        e4195511(4195511),
        e4195512(4195512),
        e4195513(4195513),
        e4195514(4195514),
        e4195515(4195515),
        e4195516(4195516),
        e4195517(4195517),
        e4195518(4195518),
        e4195519(4195519),
        e4195520(4195520),
        e4195521(4195521),
        e4195522(4195522),
        e4195523(4195523),
        e4195524(4195524),
        e4195525(4195525),
        e4195526(4195526),
        e4195527(4195527),
        e4195528(4195528),
        e4195529(4195529),
        e4195530(4195530),
        e4195531(4195531),
        e4195532(4195532),
        e4195533(4195533),
        e4195534(4195534),
        e4195535(4195535),
        e4195536(4195536),
        e4195537(4195537),
        e4195538(4195538),
        e4195539(4195539),
        e4195540(4195540),
        e4195541(4195541),
        e4195542(4195542),
        e4195543(4195543),
        e4195544(4195544),
        e4195545(4195545),
        e4195546(4195546),
        e4195547(4195547),
        e4195548(4195548),
        e4195549(4195549),
        e4195550(4195550),
        e4195551(4195551),
        e4195552(4195552),
        e4195553(4195553),
        e4195560(4195560),
        e4195561(4195561),
        e4195562(4195562),
        e4195563(4195563),
        e4195564(4195564),
        e4195565(4195565),
        e4195566(4195566),
        e4195567(4195567),
        e4195568(4195568),
        e4195571(4195571),
        e4195572(4195572),
        e4195573(4195573),
        e4195574(4195574),
        e4195575(4195575),
        e4195576(4195576),
        e4195577(4195577),
        e4195578(4195578),
        e4195579(4195579),
        e4195580(4195580),
        e4195581(4195581),
        e4195582(4195582),
        e4195583(4195583),
        e4195584(4195584),
        e4195585(4195585),
        e4195586(4195586),
        e4195587(4195587),
        e4195588(4195588),
        e4195592(4195592),
        e4195593(4195593),
        e4195594(4195594),
        e4195595(4195595),
        e4195596(4195596),
        e4195597(4195597),
        e4195598(4195598),
        e4195599(4195599),
        e4195601(4195601),
        e4195602(4195602),
        e4195603(4195603),
        e4195604(4195604),
        e4195605(4195605),
        e4195606(4195606),
        e4195607(4195607),
        e4195615(4195615),
        e4195616(4195616),
        e4195617(4195617),
        e4195655(4195655),
        e4195656(4195656),
        e4195660(4195660),
        e4195661(4195661),
        e4195662(4195662),
        e4195663(4195663),
        e4195664(4195664),
        e4195665(4195665),
        e4195666(4195666),
        e4195667(4195667),
        e4195669(4195669),
        e4195670(4195670),
        e4195671(4195671),
        e4195672(4195672),
        e4195673(4195673),
        e4195674(4195674),
        e4195698(4195698),
        e4195699(4195699),
        e4195700(4195700),
        e4195701(4195701),
        e4195702(4195702),
        e4195703(4195703),
        e4195704(4195704),
        e4195705(4195705),
        e4195706(4195706),
        e4195707(4195707),
        e4195708(4195708),
        e4195709(4195709),
        e4195710(4195710),
        e4195711(4195711),
        e4195712(4195712),
        e4195713(4195713),
        e4195714(4195714),
        e4195715(4195715),
        e4195716(4195716),
        e4195718(4195718),
        e4195721(4195721),
        e4195730(4195730),
        e4195731(4195731),
        e4195732(4195732),
        e4195739(4195739),
        e4195740(4195740),
        e4195741(4195741),
        e4195742(4195742),
        e4195743(4195743),
        e4195744(4195744),
        e4195745(4195745),
        e4195746(4195746),
        e4195747(4195747),
        e4195748(4195748),
        e4195749(4195749),
        e4195750(4195750),
        e4195751(4195751),
        e4195752(4195752),
        e4195753(4195753),
        e4195754(4195754),
        e4195755(4195755),
        e4195756(4195756),
        e4195757(4195757),
        e4195758(4195758),
        e4195759(4195759),
        e4195760(4195760),
        e4195761(4195761),
        e4195762(4195762),
        e4195763(4195763),
        e4195764(4195764),
        e4195765(4195765),
        e4195766(4195766),
        e4195767(4195767),
        e4195768(4195768),
        e4195769(4195769),
        e4195770(4195770),
        e4195771(4195771),
        e4195772(4195772),
        e4195775(4195775),
        e4195776(4195776),
        e4195777(4195777),
        e4195778(4195778),
        e4195779(4195779),
        e4195786(4195786),
        e4195787(4195787),
        e4195788(4195788),
        e4195789(4195789),
        e4195790(4195790),
        e4195791(4195791),
        e4195792(4195792),
        e4195793(4195793),
        e4195794(4195794),
        e4195795(4195795),
        e4195796(4195796),
        e4195797(4195797),
        e4195798(4195798),
        e4195799(4195799),
        e4195800(4195800),
        e4195801(4195801),
        e4195802(4195802),
        e4195803(4195803),
        e4195804(4195804),
        e4195807(4195807),
        e4195808(4195808),
        e4195809(4195809),
        e4195810(4195810),
        e4195813(4195813),
        e4195814(4195814),
        e4195815(4195815),
        e4195818(4195818),
        e4195819(4195819),
        e4195820(4195820),
        e4195821(4195821),
        e4195822(4195822),
        e4195823(4195823),
        e4195824(4195824),
        e4195825(4195825),
        e4195826(4195826),
        e4195827(4195827),
        e4195828(4195828),
        e4195829(4195829),
        e4195830(4195830),
        e4195831(4195831),
        e4195832(4195832),
        e4195833(4195833),
        e4195834(4195834),
        e4195835(4195835),
        e4195836(4195836),
        e4195837(4195837),
        e4195838(4195838),
        e4195839(4195839),
        e4195840(4195840),
        e4195841(4195841),
        e4195842(4195842),
        e4195843(4195843),
        e4195844(4195844),
        e4195845(4195845),
        e4195846(4195846),
        e4195847(4195847),
        e4195848(4195848),
        e4195849(4195849),
        e4195850(4195850),
        e4195851(4195851),
        e4195852(4195852),
        e4195853(4195853),
        e4195854(4195854),
        e4195855(4195855),
        e4195856(4195856),
        e4195857(4195857),
        e4195858(4195858),
        e4195859(4195859),
        e4195860(4195860),
        e4195861(4195861),
        e4195862(4195862),
        e4195863(4195863),
        e4195864(4195864),
        e4195865(4195865),
        e4195866(4195866),
        e4195867(4195867),
        e4195868(4195868),
        e4195869(4195869),
        e4195870(4195870),
        e4195871(4195871),
        e4195872(4195872),
        e4195873(4195873),
        e4195874(4195874),
        e4195875(4195875),
        e4195876(4195876),
        e4195877(4195877),
        e4195880(4195880),
        e4195881(4195881),
        e4195882(4195882),
        e4195883(4195883),
        e4195884(4195884),
        e4195885(4195885),
        e4195886(4195886),
        e4195887(4195887),
        e4195888(4195888),
        e4195889(4195889),
        e4195890(4195890),
        e4195891(4195891),
        e4195892(4195892),
        e4195893(4195893),
        e4195894(4195894),
        e4195895(4195895),
        e4195896(4195896),
        e4195897(4195897),
        e4195898(4195898),
        e4195899(4195899),
        e4195900(4195900),
        e4195901(4195901),
        e4195902(4195902),
        e4195903(4195903),
        e4195904(4195904),
        e4195905(4195905),
        e4195906(4195906),
        e4195907(4195907),
        e4195908(4195908),
        e4195909(4195909),
        e4195910(4195910),
        e4195911(4195911),
        e4195912(4195912),
        e4195913(4195913),
        e4195914(4195914),
        e4195915(4195915),
        e4195916(4195916),
        e4195917(4195917),
        e4195918(4195918),
        e4195919(4195919),
        e4195920(4195920),
        e4195921(4195921),
        e4195922(4195922),
        e4195923(4195923),
        e4195924(4195924),
        e4195925(4195925),
        e4195926(4195926),
        e4195927(4195927),
        e4195928(4195928),
        e4195929(4195929),
        e4195930(4195930),
        e4195931(4195931),
        e4195932(4195932),
        e4195933(4195933),
        e4195934(4195934),
        e4195935(4195935),
        e4195936(4195936),
        e4195937(4195937),
        e4195938(4195938),
        e4195939(4195939),
        e4195940(4195940),
        e4195941(4195941),
        e4195942(4195942),
        e4195943(4195943),
        e4195944(4195944),
        e4195945(4195945),
        e4195946(4195946),
        e4195947(4195947),
        e4195948(4195948),
        e4195949(4195949),
        e4195950(4195950),
        e4195951(4195951),
        e4195952(4195952),
        e4195953(4195953),
        e4195956(4195956),
        e4195957(4195957),
        e4195958(4195958),
        e4195959(4195959),
        e4195960(4195960),
        e4195961(4195961),
        e4195962(4195962),
        e4195963(4195963),
        e4195964(4195964),
        e4195965(4195965),
        e4195966(4195966),
        e4195967(4195967),
        e4195968(4195968),
        e4195969(4195969),
        e4195970(4195970),
        e4195971(4195971),
        e4195972(4195972),
        e4195973(4195973),
        e4195976(4195976),
        e4195977(4195977),
        e4195978(4195978),
        e4195979(4195979),
        e4195980(4195980),
        e4195981(4195981),
        e4195982(4195982),
        e4195983(4195983),
        e4195984(4195984),
        e4195985(4195985),
        e4195986(4195986),
        e4195987(4195987),
        e4195988(4195988),
        e4195989(4195989),
        e4195991(4195991),
        e4195992(4195992),
        e4195993(4195993),
        e4195994(4195994),
        e4195995(4195995),
        e4195996(4195996),
        e4195997(4195997),
        e4195998(4195998),
        e4195999(4195999),
        e4196000(4196000),
        e4196001(4196001),
        e4196002(4196002),
        e4196003(4196003),
        e4196004(4196004),
        e4196005(4196005),
        e4196006(4196006),
        e4196007(4196007),
        e4196008(4196008),
        e4196009(4196009),
        e4196010(4196010),
        e4196011(4196011),
        e4196012(4196012),
        e4196013(4196013),
        e4196014(4196014),
        e4196015(4196015),
        e4196016(4196016),
        e4196017(4196017),
        e4196018(4196018),
        e4196019(4196019),
        e4196020(4196020),
        e4196023(4196023),
        e4196024(4196024),
        e4196025(4196025),
        e4196026(4196026),
        e4196027(4196027),
        e4196034(4196034),
        e4196035(4196035),
        e4196036(4196036),
        e4196041(4196041),
        e4196042(4196042),
        e4196045(4196045),
        e4196047(4196047),
        e4196048(4196048),
        e4196049(4196049),
        e4196051(4196051),
        e4196052(4196052),
        e4196055(4196055),
        e4196056(4196056),
        e4196060(4196060),
        e4196061(4196061),
        e4196062(4196062),
        e4196063(4196063),
        e4196065(4196065),
        e4196066(4196066),
        e4196068(4196068),
        e4196069(4196069),
        e4196070(4196070),
        e4196071(4196071),
        e4196072(4196072),
        e4196073(4196073),
        e4196074(4196074),
        e4196075(4196075),
        e4196076(4196076),
        e4196077(4196077),
        e4196078(4196078),
        e4196079(4196079),
        e4196080(4196080),
        e4196081(4196081),
        e4196082(4196082),
        e4196083(4196083),
        e4196084(4196084),
        e4196085(4196085),
        e4196086(4196086),
        e4196087(4196087),
        e4196088(4196088),
        e4196089(4196089),
        e4196090(4196090),
        e4196091(4196091),
        e4196092(4196092),
        e4196093(4196093),
        e4196094(4196094),
        e4196095(4196095),
        e4196096(4196096),
        e4196097(4196097),
        e4196098(4196098),
        e4196099(4196099),
        e4196100(4196100),
        e4196101(4196101),
        e4196102(4196102),
        e4196103(4196103),
        e4196104(4196104),
        e4196105(4196105),
        e4196106(4196106),
        e4196107(4196107),
        e4196108(4196108),
        e4196109(4196109),
        e4196110(4196110),
        e4196111(4196111),
        e4196112(4196112),
        e4196113(4196113),
        e4196114(4196114),
        e4196115(4196115),
        e4196116(4196116),
        e4196117(4196117),
        e4196118(4196118),
        e4196119(4196119),
        e4196120(4196120),
        e4196121(4196121),
        e4196122(4196122),
        e4196123(4196123),
        e4196124(4196124),
        e4196125(4196125),
        e4196126(4196126),
        e4196127(4196127),
        e4196128(4196128),
        e4196129(4196129),
        e4196130(4196130),
        e4196131(4196131),
        e4196132(4196132),
        e4196133(4196133),
        e4196134(4196134),
        e4196135(4196135),
        e4196136(4196136),
        e4196137(4196137),
        e4196138(4196138),
        e4196139(4196139),
        e4196140(4196140),
        e4196141(4196141),
        e4196142(4196142),
        e4196143(4196143),
        e4196144(4196144),
        e4196145(4196145),
        e4196146(4196146),
        e4196147(4196147),
        e4196149(4196149),
        e4196151(4196151),
        e4196152(4196152),
        e4196153(4196153),
        e4196154(4196154),
        e4196155(4196155),
        e4196156(4196156),
        e4196157(4196157),
        e4196158(4196158),
        e4196159(4196159),
        e4196160(4196160),
        e4196161(4196161),
        e4196162(4196162),
        e4196163(4196163),
        e4196164(4196164),
        e4196165(4196165),
        e4196168(4196168),
        e4196169(4196169),
        e4196170(4196170),
        e4196171(4196171),
        e4196172(4196172),
        e4196173(4196173),
        e4196174(4196174),
        e4196175(4196175),
        e4196176(4196176),
        e4196177(4196177),
        e4196178(4196178),
        e4196179(4196179),
        e4196180(4196180),
        e4196181(4196181),
        e4196182(4196182),
        e4196183(4196183),
        e4196184(4196184),
        e4196185(4196185),
        e4196186(4196186),
        e4196187(4196187),
        e4196188(4196188),
        e4196189(4196189),
        e4196190(4196190),
        e4196191(4196191),
        e4196192(4196192),
        e4196193(4196193),
        e4196194(4196194),
        e4196195(4196195),
        e4196196(4196196),
        e4196197(4196197),
        e4196198(4196198),
        e4196199(4196199),
        e4196200(4196200),
        e4196201(4196201),
        e4196202(4196202),
        e4196203(4196203),
        e4196204(4196204),
        e4196205(4196205),
        e4196206(4196206),
        e4196207(4196207),
        e4196208(4196208),
        e4196209(4196209),
        e4196210(4196210),
        e4196211(4196211),
        e4196214(4196214),
        e4196215(4196215),
        e4196216(4196216),
        e4196217(4196217),
        e4196218(4196218),
        e4196219(4196219),
        e4196220(4196220),
        e4196221(4196221),
        e4196222(4196222),
        e4196223(4196223),
        e4196224(4196224),
        e4196225(4196225),
        e4196226(4196226),
        e4196227(4196227),
        e4196228(4196228),
        e4196229(4196229),
        e4196230(4196230),
        e4196231(4196231),
        e4196232(4196232),
        e4196233(4196233),
        e4196234(4196234),
        e4196235(4196235),
        e4196236(4196236),
        e4196237(4196237),
        e4196241(4196241),
        e4196242(4196242),
        e4196243(4196243),
        e4196244(4196244),
        e4196245(4196245),
        e4196246(4196246),
        e4196247(4196247),
        e4196249(4196249),
        e4196250(4196250),
        e4196251(4196251),
        e4196252(4196252),
        e4196253(4196253),
        e4196254(4196254),
        e4196255(4196255),
        e4196259(4196259),
        e4196261(4196261),
        e4196262(4196262),
        e4196263(4196263),
        e4196264(4196264),
        e4196265(4196265),
        e4196268(4196268),
        e4196269(4196269),
        e4196270(4196270),
        e4196271(4196271),
        e4196272(4196272),
        e4196273(4196273),
        e4196274(4196274),
        e4196275(4196275),
        e4196276(4196276),
        e4196277(4196277),
        e4196278(4196278),
        e4196279(4196279),
        e4196280(4196280),
        e4196281(4196281),
        e4196282(4196282),
        e4196283(4196283),
        e4196284(4196284),
        e4196285(4196285),
        e4196286(4196286),
        e4196287(4196287),
        e4196288(4196288),
        e4196289(4196289),
        e4196290(4196290),
        e4196291(4196291),
        e4196292(4196292),
        e4196293(4196293),
        e4196294(4196294),
        e4196295(4196295),
        e4196296(4196296),
        e4196297(4196297),
        e4196298(4196298),
        e4196299(4196299),
        e4196300(4196300),
        e4196301(4196301),
        e4196302(4196302),
        e4196303(4196303),
        e4196304(4196304),
        e4196305(4196305),
        e4196306(4196306),
        e4196307(4196307),
        e4196308(4196308),
        e4196309(4196309),
        e4196310(4196310),
        e4196317(4196317),
        e4196318(4196318),
        e4196319(4196319),
        e4196320(4196320),
        e4196321(4196321),
        e4196322(4196322),
        e4196323(4196323),
        e4196324(4196324),
        e4196325(4196325),
        e4196326(4196326),
        e4196327(4196327),
        e4196328(4196328),
        e4196334(4196334),
        e4196338(4196338),
        e4196342(4196342),
        e4196343(4196343),
        e4196344(4196344),
        e4196345(4196345),
        e4196346(4196346),
        e4196347(4196347),
        e4196348(4196348),
        e4196349(4196349),
        e4196350(4196350),
        e4196354(4196354),
        e4196355(4196355),
        e4196356(4196356),
        e4196357(4196357),
        e4196358(4196358),
        e4196359(4196359),
        e4196360(4196360),
        e4196361(4196361),
        e4196362(4196362),
        e4196363(4196363),
        e4196364(4196364),
        e4196365(4196365),
        e4196366(4196366),
        e4196367(4196367),
        e4196368(4196368),
        e4196369(4196369),
        e4196370(4196370),
        e4196371(4196371),
        e4196372(4196372),
        e4196373(4196373),
        e4196374(4196374),
        e4196375(4196375),
        e4196376(4196376),
        e4196377(4196377),
        e4196378(4196378),
        e4196379(4196379),
        e4196380(4196380),
        e4196382(4196382),
        e4196383(4196383),
        e4196384(4196384),
        e4196385(4196385),
        e4196386(4196386),
        e4196387(4196387),
        e4196391(4196391),
        e4196392(4196392),
        e4196393(4196393),
        e4196394(4196394),
        e4196395(4196395),
        e4196396(4196396),
        e4196397(4196397),
        e4196398(4196398),
        e4196399(4196399),
        e4196403(4196403),
        e4196407(4196407),
        e4196408(4196408),
        e4196409(4196409),
        e4196422(4196422),
        e4196423(4196423),
        e4196424(4196424),
        e4196425(4196425),
        e4196426(4196426),
        e4196427(4196427),
        e4196428(4196428),
        e4196430(4196430),
        e4196431(4196431),
        e4196432(4196432),
        e4196433(4196433),
        e4196434(4196434),
        e4196435(4196435),
        e4196436(4196436),
        e4196437(4196437),
        e4196438(4196438),
        e4196439(4196439),
        e4196440(4196440),
        e4196441(4196441),
        e4196442(4196442),
        e4196443(4196443),
        e4196444(4196444),
        e4196445(4196445),
        e4196446(4196446),
        e4196447(4196447),
        e4196448(4196448),
        e4196450(4196450),
        e4196451(4196451),
        e4196452(4196452),
        e4196453(4196453),
        e4196454(4196454),
        e4196455(4196455),
        e4196458(4196458),
        e4196459(4196459),
        e4196460(4196460),
        e4196461(4196461),
        e4196462(4196462),
        e4196464(4196464),
        e4196465(4196465),
        e4196466(4196466),
        e4196467(4196467),
        e4196468(4196468),
        e4196469(4196469),
        e4196470(4196470),
        e4196471(4196471),
        e4196472(4196472),
        e4196474(4196474),
        e4196475(4196475),
        e4196477(4196477),
        e4196478(4196478),
        e4196480(4196480),
        e4196481(4196481),
        e4196483(4196483),
        e4196484(4196484),
        e4196485(4196485),
        e4196486(4196486),
        e4196487(4196487),
        e4196488(4196488),
        e4196489(4196489),
        e4196490(4196490),
        e4196491(4196491),
        e4196492(4196492),
        e4196493(4196493),
        e4196494(4196494),
        e4196495(4196495),
        e4196496(4196496),
        e4196497(4196497),
        e4196498(4196498),
        e4196499(4196499),
        e4196500(4196500),
        e4196501(4196501),
        e4196502(4196502),
        e4196512(4196512),
        e4196513(4196513),
        e4196514(4196514),
        e4196515(4196515),
        e4196516(4196516),
        e4196520(4196520),
        e4196521(4196521),
        e4196522(4196522),
        e4196523(4196523),
        e4196524(4196524),
        e4196525(4196525),
        e4196526(4196526),
        e4196527(4196527),
        e4196528(4196528),
        e4196529(4196529),
        e4196531(4196531),
        e4196532(4196532),
        e4196533(4196533),
        e4196534(4196534),
        e4196535(4196535),
        e4196536(4196536),
        e4196537(4196537),
        e4196538(4196538),
        e4196539(4196539),
        e4196540(4196540),
        e4196541(4196541),
        e4196542(4196542),
        e4196543(4196543),
        e4196544(4196544),
        e4196545(4196545),
        e4196546(4196546),
        e4196555(4196555),
        e4196556(4196556),
        e4196557(4196557),
        e4196558(4196558),
        e4196559(4196559),
        e4196560(4196560),
        e4196561(4196561),
        e4196562(4196562),
        e4196563(4196563),
        e4196564(4196564),
        e4196565(4196565),
        e4196566(4196566),
        e4196567(4196567),
        e4196568(4196568),
        e4196569(4196569),
        e4196570(4196570),
        e4196571(4196571),
        e4196572(4196572),
        e4196573(4196573),
        e4196574(4196574),
        e4196575(4196575),
        e4196578(4196578),
        e4196579(4196579),
        e4196580(4196580),
        e4196581(4196581),
        e4196582(4196582),
        e4196583(4196583),
        e4196584(4196584),
        e4196585(4196585),
        e4196586(4196586),
        e4196587(4196587),
        e4196588(4196588),
        e4196589(4196589),
        e4196593(4196593),
        e4196594(4196594),
        e4196595(4196595),
        e4196596(4196596),
        e4196597(4196597),
        e4196598(4196598),
        e4196599(4196599),
        e4196600(4196600),
        e4196601(4196601),
        e4196602(4196602),
        e4196603(4196603),
        e4196604(4196604),
        e4196605(4196605),
        e4196606(4196606),
        e4196607(4196607),
        e4196608(4196608),
        e4196609(4196609),
        e4196610(4196610),
        e4196611(4196611),
        e4196612(4196612),
        e4196613(4196613),
        e4196614(4196614),
        e4196619(4196619),
        e4196620(4196620),
        e4196621(4196621),
        e4196622(4196622),
        e4196623(4196623),
        e4196624(4196624),
        e4196625(4196625),
        e4196626(4196626),
        e4196627(4196627),
        e4196628(4196628),
        e4196629(4196629),
        e4196630(4196630),
        e4196631(4196631),
        e4196632(4196632),
        e4196633(4196633),
        e4196634(4196634),
        e4196635(4196635),
        e4196636(4196636),
        e4196637(4196637),
        e4196638(4196638),
        e4196639(4196639),
        e4196640(4196640),
        e4196641(4196641),
        e4196642(4196642),
        e4196643(4196643),
        e4196644(4196644),
        e4196645(4196645),
        e4196646(4196646),
        e4196647(4196647),
        e4196648(4196648),
        e4196649(4196649),
        e4196650(4196650),
        e4196651(4196651),
        e4196652(4196652),
        e4196653(4196653),
        e4196654(4196654),
        e4196655(4196655),
        e4196656(4196656),
        e4196657(4196657),
        e4196658(4196658),
        e4196659(4196659),
        e4196660(4196660),
        e4196661(4196661),
        e4196662(4196662),
        e4196663(4196663),
        e4196664(4196664),
        e4196665(4196665),
        e4196666(4196666),
        e4196667(4196667),
        e4196668(4196668),
        e4196669(4196669),
        e4196670(4196670),
        e4196671(4196671),
        e4196672(4196672),
        e4196673(4196673),
        e4196674(4196674),
        e4196675(4196675),
        e4196676(4196676),
        e4196677(4196677),
        e4196678(4196678),
        e4196679(4196679),
        e4196680(4196680),
        e4196681(4196681),
        e4196682(4196682),
        e4196683(4196683),
        e4196684(4196684),
        e4196685(4196685),
        e4196686(4196686),
        e4196687(4196687),
        e4196688(4196688),
        e4196689(4196689),
        e4196690(4196690),
        e4196691(4196691),
        e4196692(4196692),
        e4196693(4196693),
        e4196694(4196694),
        e4196695(4196695),
        e4196696(4196696),
        e4196697(4196697),
        e4196698(4196698),
        e4196701(4196701),
        e4196702(4196702),
        e4196703(4196703),
        e4196704(4196704),
        e4196705(4196705),
        e4196706(4196706),
        e4196707(4196707),
        e4196708(4196708),
        e4196709(4196709),
        e4196710(4196710),
        e4196711(4196711),
        e4196712(4196712),
        e4196713(4196713),
        e4196714(4196714),
        e4196715(4196715),
        e4196716(4196716),
        e4196717(4196717),
        e4196718(4196718),
        e4196719(4196719),
        e4196720(4196720),
        e4196721(4196721),
        e4196722(4196722),
        e4196723(4196723),
        e4196724(4196724),
        e4196725(4196725),
        e4196726(4196726),
        e4196727(4196727),
        e4196728(4196728),
        e4196729(4196729),
        e4196730(4196730),
        e4196731(4196731),
        e4196732(4196732),
        e4196733(4196733),
        e4196734(4196734),
        e4196735(4196735),
        e4196736(4196736),
        e4196737(4196737),
        e4196738(4196738),
        e4196739(4196739),
        e4196740(4196740),
        e4196741(4196741),
        e4196742(4196742),
        e4196743(4196743),
        e4196744(4196744),
        e4196745(4196745),
        e4196746(4196746),
        e4196747(4196747),
        e4196748(4196748),
        e4196749(4196749),
        e4196750(4196750),
        e4196751(4196751),
        e4196752(4196752),
        e4196753(4196753),
        e4196754(4196754),
        e4196755(4196755),
        e4196756(4196756),
        e4196757(4196757),
        e4196758(4196758),
        e4196759(4196759),
        e4196760(4196760),
        e4196761(4196761),
        e4196762(4196762),
        e4196763(4196763),
        e4196764(4196764),
        e4196765(4196765),
        e4196766(4196766),
        e4196767(4196767),
        e4196768(4196768),
        e4196769(4196769),
        e4196770(4196770),
        e4196771(4196771),
        e4196772(4196772),
        e4196773(4196773),
        e4196774(4196774),
        e4196775(4196775),
        e4196776(4196776),
        e4196777(4196777),
        e4196778(4196778),
        e4196779(4196779),
        e4196780(4196780),
        e4196781(4196781),
        e4196785(4196785),
        e4196787(4196787),
        e4196788(4196788),
        e4196789(4196789),
        e4196790(4196790),
        e4196791(4196791),
        e4196792(4196792),
        e4196793(4196793),
        e4196794(4196794),
        e4196795(4196795),
        e4196796(4196796),
        e4196797(4196797),
        e4196798(4196798),
        e4196799(4196799),
        e4196800(4196800),
        e4196801(4196801),
        e4196802(4196802),
        e4196803(4196803),
        e4196804(4196804),
        e4196811(4196811),
        e4196812(4196812),
        e4196813(4196813),
        e4196814(4196814),
        e4196815(4196815),
        e4196816(4196816),
        e4196817(4196817),
        e4196820(4196820),
        e4196821(4196821),
        e4196822(4196822),
        e4196823(4196823),
        e4196824(4196824),
        e4196827(4196827),
        e4196828(4196828),
        e4196829(4196829),
        e4196830(4196830),
        e4196831(4196831),
        e4196832(4196832),
        e4196833(4196833),
        e4196834(4196834),
        e4196838(4196838),
        e4196839(4196839),
        e4196840(4196840),
        e4196841(4196841),
        e4196842(4196842),
        e4196843(4196843),
        e4196844(4196844),
        e4196845(4196845),
        e4196846(4196846),
        e4196847(4196847),
        e4196848(4196848),
        e4196849(4196849),
        e4196850(4196850),
        e4196851(4196851),
        e4196852(4196852),
        e4196853(4196853),
        e4196854(4196854),
        e4196855(4196855),
        e4196856(4196856),
        e4196857(4196857),
        e4196858(4196858),
        e4196859(4196859),
        e4196860(4196860),
        e4196861(4196861),
        e4196863(4196863),
        e4196864(4196864),
        e4196865(4196865),
        e4196866(4196866),
        e4196867(4196867),
        e4196868(4196868),
        e4196869(4196869),
        e4196870(4196870),
        e4196871(4196871),
        e4196872(4196872),
        e4196873(4196873),
        e4196874(4196874),
        e4196875(4196875),
        e4196876(4196876),
        e4196877(4196877),
        e4196878(4196878),
        e4196879(4196879),
        e4196880(4196880),
        e4196881(4196881),
        e4196882(4196882),
        e4196883(4196883),
        e4196884(4196884),
        e4196885(4196885),
        e4196886(4196886),
        e4196887(4196887),
        e4196888(4196888),
        e4196889(4196889),
        e4196890(4196890),
        e4196891(4196891),
        e4196892(4196892),
        e4196893(4196893),
        e4196894(4196894),
        e4196895(4196895),
        e4196896(4196896),
        e4196897(4196897),
        e4196898(4196898),
        e4196899(4196899),
        e4196900(4196900),
        e4196901(4196901),
        e4196902(4196902),
        e4196903(4196903),
        e4196904(4196904),
        e4196905(4196905),
        e4196906(4196906),
        e4196907(4196907),
        e4196908(4196908),
        e4196909(4196909),
        e4196910(4196910),
        e4196911(4196911),
        e4196912(4196912),
        e4196913(4196913),
        e4196914(4196914),
        e4196915(4196915),
        e4196916(4196916),
        e4196917(4196917),
        e4196918(4196918),
        e4196919(4196919),
        e4196920(4196920),
        e4196921(4196921),
        e4196922(4196922),
        e4196923(4196923),
        e4196924(4196924),
        e4196925(4196925),
        e4196926(4196926),
        e4196927(4196927),
        e4196928(4196928),
        e4196929(4196929),
        e4196930(4196930),
        e4196931(4196931),
        e4196932(4196932),
        e4196933(4196933),
        e4196934(4196934),
        e4196935(4196935),
        e4196936(4196936),
        e4196937(4196937),
        e4196938(4196938),
        e4196939(4196939),
        e4196940(4196940),
        e4196941(4196941),
        e4196942(4196942),
        e4196943(4196943),
        e4196944(4196944),
        e4196945(4196945),
        e4196946(4196946),
        e4196947(4196947),
        e4196948(4196948),
        e4196949(4196949),
        e4196950(4196950),
        e4196951(4196951),
        e4196952(4196952),
        e4196953(4196953),
        e4196954(4196954),
        e4196955(4196955),
        e4196956(4196956),
        e4196957(4196957),
        e4196958(4196958),
        e4196959(4196959),
        e4196960(4196960),
        e4196961(4196961),
        e4196962(4196962),
        e4196963(4196963),
        e4196964(4196964),
        e4196965(4196965),
        e4196966(4196966),
        e4196967(4196967),
        e4196968(4196968),
        e4196969(4196969),
        e4196970(4196970),
        e4196971(4196971),
        e4196972(4196972),
        e4196973(4196973),
        e4196974(4196974),
        e4196975(4196975),
        e4196976(4196976),
        e4196977(4196977),
        e4196978(4196978),
        e4196979(4196979),
        e4196980(4196980),
        e4196981(4196981),
        e4196982(4196982),
        e4196983(4196983),
        e4196984(4196984),
        e4196985(4196985),
        e4196986(4196986),
        e4196987(4196987),
        e4196988(4196988),
        e4196989(4196989),
        e4196990(4196990),
        e4196991(4196991),
        e4196992(4196992),
        e4196993(4196993),
        e4196994(4196994),
        e4196995(4196995),
        e4196996(4196996),
        e4196997(4196997),
        e4196998(4196998),
        e4197001(4197001),
        e4197002(4197002),
        e4197003(4197003),
        e4197004(4197004),
        e4197005(4197005),
        e4197006(4197006),
        e4197007(4197007),
        e4197008(4197008),
        e4197009(4197009),
        e4197010(4197010),
        e4197011(4197011),
        e4197012(4197012),
        e4197013(4197013),
        e4197014(4197014),
        e4197015(4197015),
        e4197016(4197016),
        e4197017(4197017),
        e4197018(4197018),
        e4197019(4197019),
        e4197020(4197020),
        e4197021(4197021),
        e4197022(4197022),
        e4197023(4197023),
        e4197024(4197024),
        e4197025(4197025),
        e4197026(4197026),
        e4197027(4197027),
        e4197028(4197028),
        e4197029(4197029),
        e4197030(4197030),
        e4197031(4197031),
        e4197032(4197032),
        e4197033(4197033),
        e4197034(4197034),
        e4197035(4197035),
        e4197036(4197036),
        e4197037(4197037),
        e4197038(4197038),
        e4197039(4197039),
        e4197040(4197040),
        e4197041(4197041),
        e4197042(4197042),
        e4197043(4197043),
        e4197044(4197044),
        e4197045(4197045),
        e4197046(4197046),
        e4197047(4197047),
        e4197048(4197048),
        e4197049(4197049),
        e4197050(4197050),
        e4197051(4197051),
        e4197052(4197052),
        e4197053(4197053),
        e4197054(4197054),
        e4197055(4197055),
        e4197056(4197056),
        e4197057(4197057),
        e4197058(4197058),
        e4197059(4197059),
        e4197060(4197060),
        e4197061(4197061),
        e4197062(4197062),
        e4197063(4197063),
        e4197064(4197064),
        e4197065(4197065),
        e4197066(4197066),
        e4197067(4197067),
        e4197068(4197068),
        e4197069(4197069),
        e4197070(4197070),
        e4197071(4197071),
        e4197072(4197072),
        e4197073(4197073),
        e4197074(4197074),
        e4197075(4197075),
        e4197076(4197076),
        e4197077(4197077),
        e4197078(4197078),
        e4197079(4197079),
        e4197080(4197080),
        e4197081(4197081),
        e4197082(4197082),
        e4197083(4197083),
        e4197084(4197084),
        e4197085(4197085),
        e4197086(4197086),
        e4197087(4197087),
        e4197088(4197088),
        e4197089(4197089),
        e4197090(4197090),
        e4197091(4197091),
        e4197092(4197092),
        e4197093(4197093),
        e4197094(4197094),
        e4197095(4197095),
        e4197096(4197096),
        e4197097(4197097),
        e4197098(4197098),
        e4197099(4197099),
        e4197100(4197100),
        e4197101(4197101),
        e4197102(4197102),
        e4197103(4197103),
        e4197104(4197104),
        e4197105(4197105),
        e4197106(4197106),
        e4197107(4197107),
        e4197108(4197108),
        e4197109(4197109),
        e4197110(4197110),
        e4197111(4197111),
        e4197112(4197112),
        e4197113(4197113),
        e4197114(4197114),
        e4197115(4197115),
        e4197116(4197116),
        e4197117(4197117),
        e4197118(4197118),
        e4197119(4197119),
        e4197120(4197120),
        e4197121(4197121),
        e4197122(4197122),
        e4197123(4197123),
        e4197124(4197124),
        e4197125(4197125),
        e4197126(4197126),
        e4197127(4197127),
        e4197128(4197128),
        e4197129(4197129),
        e4197130(4197130),
        e4197131(4197131),
        e4197132(4197132),
        e4197133(4197133),
        e4197134(4197134),
        e4197135(4197135),
        e4197136(4197136),
        e4197137(4197137),
        e4197138(4197138),
        e4197139(4197139),
        e4197140(4197140),
        e4197141(4197141),
        e4197142(4197142),
        e4197146(4197146),
        e4197147(4197147),
        e4197148(4197148),
        e4197149(4197149),
        e4197150(4197150),
        e4197151(4197151),
        e4197152(4197152),
        e4197153(4197153),
        e4197154(4197154),
        e4197155(4197155),
        e4197156(4197156),
        e4197157(4197157),
        e4197158(4197158),
        e4197159(4197159),
        e4197160(4197160),
        e4197161(4197161),
        e4197162(4197162),
        e4197163(4197163),
        e4197164(4197164),
        e4197165(4197165),
        e4197166(4197166),
        e4197167(4197167),
        e4197168(4197168),
        e4197169(4197169),
        e4197170(4197170),
        e4197171(4197171),
        e4197172(4197172),
        e4197173(4197173),
        e4197174(4197174),
        e4197175(4197175),
        e4197176(4197176),
        e4197177(4197177),
        e4197178(4197178),
        e4197179(4197179),
        e4197180(4197180),
        e4197181(4197181),
        e4197182(4197182),
        e4197183(4197183),
        e4197184(4197184),
        e4197185(4197185),
        e4197186(4197186),
        e4197187(4197187),
        e4197188(4197188),
        e4197189(4197189),
        e4197190(4197190),
        e4197191(4197191),
        e4197192(4197192),
        e4197193(4197193),
        e4197194(4197194),
        e4197195(4197195),
        e4197196(4197196),
        e4197197(4197197),
        e4197198(4197198),
        e4197199(4197199),
        e4197200(4197200),
        e4197201(4197201),
        e4197202(4197202),
        e4197203(4197203),
        e4197204(4197204),
        e4197205(4197205),
        e4197206(4197206),
        e4197207(4197207),
        e4197208(4197208),
        e4197209(4197209),
        e4197210(4197210),
        e4197211(4197211),
        e4197212(4197212),
        e4197213(4197213),
        e4197214(4197214),
        e4197215(4197215),
        e4197216(4197216),
        e4197217(4197217),
        e4197218(4197218),
        e4197219(4197219),
        e4197220(4197220),
        e4197221(4197221),
        e4197222(4197222),
        e4197223(4197223),
        e4197224(4197224),
        e4197225(4197225),
        e4197226(4197226),
        e4197227(4197227),
        e4197228(4197228),
        e4197229(4197229),
        e4197230(4197230),
        e4197231(4197231),
        e4197232(4197232),
        e4197233(4197233),
        e4197234(4197234),
        e4197235(4197235),
        e4197236(4197236),
        e4197237(4197237),
        e4197238(4197238),
        e4197239(4197239),
        e4197240(4197240),
        e4197241(4197241),
        e4197242(4197242),
        e4197243(4197243),
        e4197244(4197244),
        e4197245(4197245),
        e4197246(4197246),
        e4197247(4197247),
        e4197248(4197248),
        e4197249(4197249),
        e4197250(4197250),
        e4197251(4197251),
        e4197252(4197252),
        e4197253(4197253),
        e4197254(4197254),
        e4197255(4197255),
        e4197256(4197256),
        e4197257(4197257),
        e4197258(4197258),
        e4197259(4197259),
        e4197260(4197260),
        e4197261(4197261),
        e4197262(4197262),
        e4197263(4197263),
        e4197264(4197264),
        e4197265(4197265),
        e4197266(4197266),
        e4197267(4197267),
        e4197268(4197268),
        e4197269(4197269),
        e4197270(4197270),
        e4197271(4197271),
        e4197272(4197272),
        e4197273(4197273),
        e4197274(4197274),
        e4197275(4197275),
        e4197276(4197276),
        e4197277(4197277),
        e4197278(4197278),
        e4197279(4197279),
        e4197280(4197280),
        e4197343(4197343),
        e4197344(4197344),
        e4197345(4197345),
        e4197346(4197346),
        e4197347(4197347),
        e4197348(4197348),
        e4197349(4197349),
        e4197350(4197350),
        e4197351(4197351),
        e4197352(4197352),
        e4197353(4197353),
        e4197354(4197354),
        e4197355(4197355),
        e4197356(4197356),
        e4197357(4197357),
        e4197358(4197358),
        e4197359(4197359),
        e4197360(4197360),
        e4197361(4197361),
        e4197362(4197362),
        e4197363(4197363),
        e4197364(4197364),
        e4197365(4197365),
        e4197366(4197366),
        e4197367(4197367),
        e4197368(4197368),
        e4197369(4197369),
        e4197370(4197370),
        e4197371(4197371),
        e4197372(4197372),
        e4197373(4197373),
        e4197374(4197374),
        e4197375(4197375),
        e4197376(4197376),
        e4197377(4197377),
        e4197378(4197378),
        e4197379(4197379),
        e4197380(4197380),
        e4197381(4197381),
        e4197382(4197382),
        e4197383(4197383),
        e4197384(4197384),
        e4197385(4197385),
        e4197386(4197386),
        e4197387(4197387),
        e4197388(4197388),
        e4197389(4197389),
        e4197390(4197390),
        e4197391(4197391),
        e4197392(4197392),
        e4197393(4197393),
        e4197394(4197394),
        e4197395(4197395),
        e4197396(4197396),
        e4197397(4197397),
        e4197398(4197398),
        e4197399(4197399),
        e4197400(4197400),
        e4197401(4197401),
        e4197402(4197402),
        e4197403(4197403),
        e4197404(4197404),
        e4197405(4197405),
        e4197406(4197406),
        e4197407(4197407),
        e4197408(4197408),
        e4197409(4197409),
        e4197410(4197410),
        e4197411(4197411),
        e4197412(4197412),
        e4197413(4197413),
        e4197414(4197414),
        e4197415(4197415),
        e4197416(4197416),
        e4197417(4197417),
        e4197418(4197418),
        e4197419(4197419),
        e4197420(4197420),
        e4197421(4197421),
        e4197422(4197422),
        e4197424(4197424),
        e4197425(4197425),
        e4197426(4197426),
        e4197427(4197427),
        e4197428(4197428),
        e4197429(4197429),
        e4197430(4197430),
        e4197431(4197431),
        e4197432(4197432),
        e4197433(4197433),
        e4197434(4197434),
        e4197435(4197435),
        e4197436(4197436),
        e4197437(4197437),
        e4197438(4197438),
        e4197439(4197439),
        e4197440(4197440),
        e4197441(4197441),
        e4197442(4197442),
        e4197443(4197443),
        e4197444(4197444),
        e4197445(4197445),
        e4197446(4197446),
        e4197447(4197447),
        e4197448(4197448),
        e4197449(4197449),
        e4197450(4197450),
        e4197451(4197451),
        e4197452(4197452),
        e4197453(4197453),
        e4197454(4197454),
        e4197455(4197455),
        e4197456(4197456),
        e4197457(4197457),
        e4197458(4197458),
        e4197459(4197459),
        e4197460(4197460),
        e4197461(4197461),
        e4197462(4197462),
        e4197463(4197463),
        e4197464(4197464),
        e4197465(4197465),
        e4197466(4197466),
        e4197467(4197467),
        e4197468(4197468),
        e4197469(4197469),
        e4197470(4197470),
        e4197471(4197471),
        e4197472(4197472),
        e4197473(4197473),
        e4197474(4197474),
        e4197475(4197475),
        e4197476(4197476),
        e4197477(4197477),
        e4197481(4197481),
        e4197482(4197482),
        e4197483(4197483),
        e4197484(4197484),
        e4197485(4197485),
        e4197486(4197486),
        e4197487(4197487),
        e4197488(4197488),
        e4197489(4197489),
        e4197490(4197490),
        e4197491(4197491),
        e4197492(4197492),
        e4197493(4197493),
        e4197494(4197494),
        e4197495(4197495),
        e4197496(4197496),
        e4197497(4197497),
        e4197498(4197498),
        e4197499(4197499),
        e4197500(4197500),
        e4197501(4197501),
        e4197502(4197502),
        e4197503(4197503),
        e4197504(4197504),
        e4197505(4197505),
        e4197506(4197506),
        e4197507(4197507),
        e4197508(4197508),
        e4197509(4197509),
        e4197510(4197510),
        e4197511(4197511),
        e4197512(4197512),
        e4197513(4197513),
        e4197514(4197514),
        e4197515(4197515),
        e4197516(4197516),
        e4197517(4197517),
        e4197518(4197518),
        e4197519(4197519),
        e4197520(4197520),
        e4197521(4197521),
        e4197522(4197522),
        e4197523(4197523),
        e4197524(4197524),
        e4197525(4197525),
        e4197526(4197526),
        e4197527(4197527),
        e4197528(4197528),
        e4197529(4197529),
        e4197530(4197530),
        e4197531(4197531),
        e4197532(4197532),
        e4197533(4197533),
        e4197534(4197534),
        e4197535(4197535),
        e4197536(4197536),
        e4197537(4197537),
        e4197538(4197538),
        e4197539(4197539),
        e4197540(4197540),
        e4197541(4197541),
        e4197542(4197542),
        e4197543(4197543),
        e4197544(4197544),
        e4197545(4197545),
        e4197546(4197546),
        e4197547(4197547),
        e4197548(4197548),
        e4197549(4197549),
        e4197550(4197550),
        e4197551(4197551),
        e4197552(4197552),
        e4197553(4197553),
        e4197554(4197554),
        e4197555(4197555),
        e4197556(4197556),
        e4197557(4197557),
        e4197558(4197558),
        e4197559(4197559),
        e4197560(4197560),
        e4197561(4197561),
        e4197562(4197562),
        e4197563(4197563),
        e4197564(4197564),
        e4197565(4197565),
        e4197566(4197566),
        e4197567(4197567),
        e4197568(4197568),
        e4197569(4197569),
        e4197570(4197570),
        e4197571(4197571),
        e4197572(4197572),
        e4197573(4197573),
        e4197574(4197574),
        e4197575(4197575),
        e4197576(4197576),
        e4197577(4197577),
        e4197578(4197578),
        e4197579(4197579),
        e4197580(4197580),
        e4197581(4197581),
        e4197582(4197582),
        e4197583(4197583),
        e4197584(4197584),
        e4197585(4197585),
        e4197586(4197586),
        e4197587(4197587),
        e4197588(4197588),
        e4197589(4197589),
        e4197590(4197590),
        e4197591(4197591),
        e4197592(4197592),
        e4197593(4197593),
        e4197594(4197594),
        e4197595(4197595),
        e4197596(4197596),
        e4197597(4197597),
        e4197598(4197598),
        e4197599(4197599),
        e4197600(4197600),
        e4197601(4197601),
        e4197602(4197602),
        e4197603(4197603),
        e4197604(4197604),
        e4197605(4197605),
        e4197606(4197606),
        e4197607(4197607),
        e4197608(4197608),
        e4197609(4197609),
        e4197610(4197610),
        e4197611(4197611),
        e4197612(4197612),
        e4197613(4197613),
        e4197614(4197614),
        e4197615(4197615),
        e4197616(4197616),
        e4197617(4197617),
        e4197618(4197618),
        e4197619(4197619),
        e4197620(4197620),
        e4197621(4197621),
        e4197622(4197622),
        e4197623(4197623),
        e4197624(4197624),
        e4197625(4197625),
        e4197626(4197626),
        e4197627(4197627),
        e4197628(4197628),
        e4197629(4197629),
        e4197630(4197630),
        e4197631(4197631),
        e4197632(4197632),
        e4197633(4197633),
        e4197634(4197634),
        e4197635(4197635),
        e4197636(4197636),
        e4197637(4197637),
        e4197638(4197638),
        e4197639(4197639),
        e4197640(4197640),
        e4197641(4197641),
        e4197642(4197642),
        e4197643(4197643),
        e4197644(4197644),
        e4197645(4197645),
        e4197646(4197646),
        e4197647(4197647),
        e4197648(4197648),
        e4197649(4197649),
        e4197650(4197650),
        e4197651(4197651),
        e4197652(4197652),
        e4197653(4197653),
        e4197654(4197654),
        e4197655(4197655),
        e4197656(4197656),
        e4197657(4197657),
        e4197658(4197658),
        e4197659(4197659),
        e4197660(4197660),
        e4197661(4197661),
        e4197662(4197662),
        e4197663(4197663),
        e4197664(4197664),
        e4197665(4197665),
        e4197666(4197666),
        e4197667(4197667),
        e4197668(4197668),
        e4197669(4197669),
        e4197670(4197670),
        e4197671(4197671),
        e4197672(4197672),
        e4197673(4197673),
        e4197674(4197674),
        e4197675(4197675),
        e4197676(4197676),
        e4197677(4197677),
        e4197678(4197678),
        e4197679(4197679),
        e4197680(4197680),
        e4197681(4197681),
        e4197682(4197682),
        e4197683(4197683),
        e4197684(4197684),
        e4197685(4197685),
        e4197686(4197686),
        e4197687(4197687),
        e4197688(4197688),
        e4197689(4197689),
        e4197690(4197690),
        e4197691(4197691),
        e4197692(4197692),
        e4197693(4197693),
        e4197694(4197694),
        e4197695(4197695),
        e4197696(4197696),
        e4197697(4197697),
        e4197698(4197698),
        e4197699(4197699),
        e4197700(4197700),
        e4197701(4197701),
        e4197702(4197702),
        e4197703(4197703),
        e4197704(4197704),
        e4197705(4197705),
        e4197706(4197706),
        e4197707(4197707),
        e4197708(4197708),
        e4197709(4197709),
        e4197710(4197710),
        e4197711(4197711),
        e4197712(4197712),
        e4197713(4197713),
        e4197714(4197714),
        e4197715(4197715),
        e4197716(4197716),
        e4197717(4197717),
        e4197718(4197718),
        e4197719(4197719),
        e4197720(4197720),
        e4197721(4197721),
        e4197722(4197722),
        e4197723(4197723),
        e4197724(4197724),
        e4197725(4197725),
        e4197726(4197726),
        e4197727(4197727),
        e4197728(4197728),
        e4197729(4197729),
        e4197730(4197730),
        e4197731(4197731),
        e4197732(4197732),
        e4197733(4197733),
        e4197734(4197734),
        e4197735(4197735),
        e4197736(4197736),
        e4197737(4197737),
        e4197738(4197738),
        e4197739(4197739),
        e4197740(4197740),
        e4197741(4197741),
        e4197742(4197742),
        e4197743(4197743),
        e4197744(4197744),
        e4197745(4197745),
        e4197746(4197746),
        e4197747(4197747),
        e4197748(4197748),
        e4197749(4197749),
        e4197750(4197750),
        e4197751(4197751),
        e4197752(4197752),
        e4197753(4197753),
        e4197754(4197754),
        e4197755(4197755),
        e4197756(4197756),
        e4197757(4197757),
        e4197758(4197758),
        e4197759(4197759),
        e4197760(4197760),
        e4197761(4197761),
        e4197762(4197762),
        e4197763(4197763),
        e4197764(4197764),
        e4197765(4197765),
        e4197766(4197766),
        e4197767(4197767),
        e4197768(4197768),
        e4197769(4197769),
        e4197770(4197770),
        e4197771(4197771),
        e4197772(4197772),
        e4197773(4197773),
        e4197774(4197774),
        e4197775(4197775),
        e4197776(4197776),
        e4197777(4197777),
        e4197782(4197782),
        e4197783(4197783),
        e4197784(4197784),
        e4197785(4197785),
        e4197786(4197786),
        e4197787(4197787),
        e4197788(4197788),
        e4197789(4197789),
        e4197790(4197790),
        e4197791(4197791),
        e4197792(4197792),
        e4197793(4197793),
        e4197794(4197794),
        e4197795(4197795),
        e4197796(4197796),
        e4197797(4197797),
        e4197798(4197798),
        e4197799(4197799),
        e4197800(4197800),
        e4197801(4197801),
        e4197804(4197804),
        e4197805(4197805),
        e4197806(4197806),
        e4197807(4197807),
        e4197808(4197808),
        e4197809(4197809),
        e4197816(4197816),
        e4197817(4197817),
        e4197818(4197818),
        e4197819(4197819),
        e4197820(4197820),
        e4197821(4197821),
        e4197822(4197822),
        e4197823(4197823),
        e4197824(4197824),
        e4197825(4197825),
        e4197826(4197826),
        e4197827(4197827),
        e4197828(4197828),
        e4197829(4197829),
        e4197830(4197830),
        e4197831(4197831),
        e4197832(4197832),
        e4197833(4197833),
        e4197834(4197834),
        e4197835(4197835),
        e4197836(4197836),
        e4197837(4197837),
        e4197838(4197838),
        e4197839(4197839),
        e4197840(4197840),
        e4197841(4197841),
        e4197842(4197842),
        e4197843(4197843),
        e4197844(4197844),
        e4197845(4197845),
        e4197846(4197846),
        e4197847(4197847),
        e4197848(4197848),
        e4197849(4197849),
        e4197850(4197850),
        e4197851(4197851),
        e4197852(4197852),
        e4197853(4197853),
        e4197854(4197854),
        e4197855(4197855),
        e4197856(4197856),
        e4197857(4197857),
        e4197858(4197858),
        e4197859(4197859),
        e4197860(4197860),
        e4197861(4197861),
        e4197862(4197862),
        e4197863(4197863),
        e4197864(4197864),
        e4197865(4197865),
        e4197866(4197866),
        e4197867(4197867),
        e4197868(4197868),
        e4197872(4197872),
        e4197873(4197873),
        e4197874(4197874),
        e4197875(4197875),
        e4197876(4197876),
        e4197877(4197877),
        e4197878(4197878),
        e4197879(4197879),
        e4197880(4197880),
        e4197881(4197881),
        e4197882(4197882),
        e4197883(4197883),
        e4197884(4197884),
        e4197885(4197885),
        e4197886(4197886),
        e4197887(4197887),
        e4197888(4197888),
        e4197889(4197889),
        e4197890(4197890),
        e4197891(4197891),
        e4197892(4197892),
        e4197893(4197893),
        e4197894(4197894),
        e4197895(4197895),
        e4197896(4197896),
        e4197897(4197897),
        e4197898(4197898),
        e4197899(4197899),
        e4197900(4197900),
        e4197901(4197901),
        e4197902(4197902),
        e4197903(4197903),
        e4197904(4197904),
        e4197905(4197905),
        e4197906(4197906),
        e4197907(4197907),
        e4197908(4197908),
        e4197909(4197909),
        e4197910(4197910),
        e4197911(4197911),
        e4197912(4197912),
        e4197913(4197913),
        e4197914(4197914),
        e4197915(4197915),
        e4197916(4197916),
        e4197917(4197917),
        e4197918(4197918),
        e4197940(4197940),
        e4197941(4197941),
        e4197942(4197942),
        e4197943(4197943),
        e4197944(4197944),
        e4197945(4197945),
        e4197946(4197946),
        e4197947(4197947),
        e4197948(4197948),
        e4197949(4197949),
        e4197950(4197950),
        e4197951(4197951),
        e4197952(4197952),
        e4197953(4197953),
        e4197954(4197954),
        e4197955(4197955),
        e4197956(4197956),
        e4197957(4197957),
        e4197958(4197958),
        e4197961(4197961),
        e4197970(4197970),
        e4197971(4197971),
        e4197972(4197972),
        e4197973(4197973),
        e4197974(4197974),
        e4197975(4197975),
        e4197976(4197976),
        e4197977(4197977),
        e4197978(4197978),
        e4197979(4197979),
        e4197980(4197980),
        e4197981(4197981),
        e4197982(4197982),
        e4197983(4197983),
        e4197984(4197984),
        e4197985(4197985),
        e4197986(4197986),
        e4197987(4197987),
        e4197988(4197988),
        e4197989(4197989),
        e4197990(4197990),
        e4197991(4197991),
        e4197992(4197992),
        e4197993(4197993),
        e4197994(4197994),
        e4197995(4197995),
        e4197996(4197996),
        e4197997(4197997),
        e4197998(4197998),
        e4197999(4197999),
        e4198000(4198000),
        e4198001(4198001),
        e4198002(4198002),
        e4198003(4198003),
        e4198004(4198004),
        e4198005(4198005),
        e4198006(4198006),
        e4198007(4198007),
        e4198008(4198008),
        e4198009(4198009),
        e4198010(4198010),
        e4198011(4198011),
        e4198012(4198012),
        e4198013(4198013),
        e4198014(4198014),
        e4198015(4198015),
        e4198016(4198016),
        e4198017(4198017),
        e4198018(4198018),
        e4198019(4198019),
        e4198020(4198020),
        e4198021(4198021),
        e4198022(4198022),
        e4198023(4198023),
        e4198024(4198024),
        e4198025(4198025),
        e4198026(4198026),
        e4198027(4198027),
        e4198028(4198028),
        e4198029(4198029),
        e4198030(4198030),
        e4198031(4198031),
        e4198032(4198032),
        e4198033(4198033),
        e4198034(4198034),
        e4198035(4198035),
        e4198036(4198036),
        e4198037(4198037),
        e4198038(4198038),
        e4198039(4198039),
        e4198040(4198040),
        e4198041(4198041),
        e4198042(4198042),
        e4198043(4198043),
        e4198044(4198044),
        e4198045(4198045),
        e4198046(4198046),
        e4198047(4198047),
        e4198048(4198048),
        e4198049(4198049),
        e4198050(4198050),
        e4198051(4198051),
        e4198052(4198052),
        e4198053(4198053),
        e4198054(4198054),
        e4198055(4198055),
        e4198056(4198056),
        e4198057(4198057),
        f4522530(4522530),
        f4522532(4522532),
        f4522544(4522544),
        f4522561(4522561),
        f4522588(4522588),
        f4522603(4522603),
        f4525234(4525234),
        f4525239(4525239),
        f4525240(4525240),
        f4525241(4525241),
        f4525247(4525247),
        f4525248(4525248),
        f4525250(4525250),
        f4525251(4525251),
        f4525252(4525252),
        f4525253(4525253),
        f4525254(4525254),
        f4526517(4526517),
        f4526850(4526850),
        f4526851(4526851),
        f4526901(4526901),
        f4526902(4526902),
        f4527601(4527601),
        f4528207(4528207),
        f4528209(4528209),
        f4528211(4528211),
        f4528216(4528216),
        f4528218(4528218),
        f4528220(4528220),
        f4528223(4528223),
        f4528225(4528225),
        f4528227(4528227),
        f4528268(4528268),
        f4528270(4528270),
        f4528591(4528591),
        f4528596(4528596),
        f4528842(4528842),
        f4529444(4529444),
        f4529447(4529447),
        f4529495(4529495),
        f4529514(4529514),
        f4529520(4529520),
        f4529533(4529533),
        f4529971(4529971),
        f4529973(4529973),
        f4530046(4530046),
        f4530080(4530080),
        f4530082(4530082),
        f4530097(4530097),
        f4530100(4530100),
        f4530113(4530113),
        f4530122(4530122),
        f4530125(4530125),
        f4530127(4530127),
        f4530143(4530143),
        f4530204(4530204),
        f4530206(4530206),
        f4530727(4530727),
        f4531222(4531222),
        f4531400(4531400),
        f4531404(4531404),
        f4531414(4531414),
        f4531419(4531419),
        f4531518(4531518),
        f4531578(4531578),
        f4531580(4531580),
        f4531707(4531707),
        f4531711(4531711),
        f4531714(4531714),
        f4531768(4531768),
        f4531770(4531770),
        f4531775(4531775),
        f4531796(4531796),
        f4531810(4531810),
        f4531828(4531828),
        f4531835(4531835),
        f4531839(4531839),
        f4531844(4531844),
        f4532617(4532617),
        f4532627(4532627),
        f4532629(4532629),
        f4532693(4532693),
        f4532695(4532695),
        f4534499(4534499),
        f4534828(4534828),
        f4534836(4534836),
        f4534849(4534849),
        f4534923(4534923)
    }

CfprConditionLifecycle ::= TEXTUAL-CONVENTION
    STATUS        current
    DESCRIPTION
        ""
    SYNTAX        BITS
    {
        flapping(0),
        soakingClear(1),
        soakingRaise(2),
        suppressed(3)
    }

CfprConditionRemoteInvRslt ::= TEXTUAL-CONVENTION
    STATUS        current
    DESCRIPTION
        ""
    SYNTAX        BITS
    {
        failure(0),
        unidentifiedFail(1),
        internalError(2),
        timeout(3),
        endPointUnavailable(4),
        endPointFailed(5),
        endPointProtocolError(6),
        swDefect(7),
        fwDefect(8),
        hwDefect(9),
        resourceUnavailable(10),
        resourceCapacityExceeded(11),
        resourceDependency(12),
        capabilityNotImplementedIgnore(13),
        capabilityNotImplementedFailure(14),
        capabilityNotSupported(15),
        capabilityUnavailable(16),
        serviceNotImplementedIgnore(17),
        serviceNotImplementedFail(18),
        serviceNotSupported(19),
        serviceUnavailable(20),
        serviceProtocolError(21),
        fruIdentityIndeterminate(22),
        fruInfoMalformed(23),
        illegalFru(24),
        fruStateIndeterminate(25),
        fruNotReady(26),
        extendTimeout(27),
        taskReset(28),
        fruNotSupported(29),
        intermittentError(30)
    }

CfprConditionRule ::= TEXTUAL-CONVENTION
    STATUS        current
    DESCRIPTION
        ""
    SYNTAX        INTEGER
    {
        generic(0),
        fabricComputeSlotEpMisplacedInChassisSlot(156),
        fabricComputeSlotEpServerIdentificationProblem(157),
        vnicEtherConfigFailed(169),
        processorUnitInoperable(174),
        processorUnitThermalNonCritical(175),
        processorUnitThermalThresholdCritical(176),
        processorUnitThermalThresholdNonRecoverable(177),
        processorUnitVoltageThresholdNonCritical(178),
        processorUnitVoltageThresholdCritical(179),
        processorUnitVoltageThresholdNonRecoverable(180),
        storageLocalDiskInoperable(181),
        storageItemCapacityExceeded(182),
        storageItemCapacityWarning(183),
        memoryUnitDegraded(184),
        memoryUnitInoperable(185),
        memoryUnitThermalThresholdNonCritical(186),
        memoryUnitThermalThresholdCritical(187),
        memoryUnitThermalThresholdNonRecoverable(188),
        memoryArrayVoltageThresholdNonCritical(189),
        memoryArrayVoltageThresholdCritical(190),
        memoryArrayVoltageThresholdNonRecoverable(191),
        adaptorUnitUnidentifiableFru(200),
        adaptorUnitMissing(203),
        adaptorUnitAdaptorReachability(206),
        adaptorHostIfLinkDown(207),
        adaptorExtIfLinkDown(209),
        portPioLinkDown(276),
        portPioFailed(277),
        portPioHardwareFailure(278),
        portPioSfpNotPresent(279),
        fabricExternalPcDown(282),
        dcxVcDown(283),
        networkElementInoperable(291),
        mgmtEntityDegraded(293),
        mgmtEntityDown(294),
        dcxNsFailed(304),
        computePhysicalInsufficientlyEquipped(305),
        computePhysicalIdentityUnestablishable(306),
        computeBoardPowerError(310),
        computePhysicalPowerProblem(311),
        computePhysicalThermalProblem(312),
        computePhysicalBiosPostTimeout(313),
        computePhysicalDiscoveryFailed(314),
        computePhysicalAssociationFailed(315),
        computePhysicalInoperable(317),
        computePhysicalUnassignedMissing(318),
        computePhysicalAssignedMissing(319),
        computePhysicalUnidentified(320),
        computePhysicalUnassignedInaccessible(321),
        computePhysicalAssignedInaccessible(322),
        lsServerFailed(324),
        lsServerDiscoveryFailed(326),
        lsServerConfigFailure(327),
        lsServerMaintenanceFailed(329),
        lsServerRemoved(330),
        lsServerInaccessible(331),
        lsServerAssociationFailed(332),
        lsServerUnassociated(334),
        lsServerServerUnfulfilled(337),
        etherSwitchIntfioSatelliteConnectionAbsent(367),
        etherSwitchIntfioSatelliteWiringProblem(368),
        equipmentPsuPowerSupplyProblem(369),
        equipmentFanDegraded(371),
        equipmentFanInoperable(373),
        equipmentPsuInoperable(374),
        equipmentIocardRemoved(376),
        equipmentFanModuleMissing(377),
        equipmentPsuMissing(378),
        equipmentIocardThermalProblem(379),
        equipmentFanModuleThermalThresholdNonCritical(380),
        equipmentPsuThermalThresholdNonCritical(381),
        equipmentFanModuleThermalThresholdCritical(382),
        equipmentPsuThermalThresholdCritical(383),
        equipmentFanModuleThermalThresholdNonRecoverable(384),
        equipmentPsuThermalThresholdNonRecoverable(385),
        equipmentPsuVoltageThresholdNonCritical(387),
        equipmentPsuVoltageThresholdCritical(389),
        equipmentPsuVoltageThresholdNonRecoverable(391),
        equipmentPsuPerfThresholdNonCritical(392),
        equipmentPsuPerfThresholdCritical(393),
        equipmentPsuPerfThresholdNonRecoverable(394),
        equipmentFanPerfThresholdNonCritical(395),
        equipmentFanPerfThresholdCritical(396),
        equipmentFanPerfThresholdNonRecoverable(397),
        equipmentIocardFirmwareUpgrade(398),
        equipmentChassisUnsupportedConnectivity(399),
        equipmentChassisUnacknowledged(400),
        equipmentIocardUnsupportedConnectivity(401),
        equipmentIocardUnacknowledged(402),
        equipmentIocardPeerDisconnected(403),
        equipmentChassisIdentity(404),
        equipmentIocardIdentity(405),
        equipmentFanModuleIdentity(406),
        equipmentPsuIdentity(407),
        equipmentChassisPowerProblem(408),
        equipmentChassisThermalThresholdCritical(409),
        equipmentChassisThermalThresholdNonCritical(410),
        equipmentChassisThermalThresholdNonRecoverable(411),
        computeBoardCmosVoltageThresholdCritical(424),
        computeBoardCmosVoltageThresholdNonRecoverable(425),
        mgmtEntityElectionFailure(428),
        mgmtEntityHaNotReady(429),
        mgmtEntityVersionIncompatible(430),
        equipmentFanMissing(434),
        equipmentIocardAutoUpgradingFirmware(435),
        firmwarePackItemImageMissing(436),
        etherSwitchIntfioSatelliteWiringNumbersUnexpected(440),
        mgmtEntityManagementServicesFailure(451),
        mgmtEntityManagementServicesUnresponsive(452),
        equipmentChassisInoperable(456),
        etherServerIntfioHardwareFailure(458),
        dcxVcMgmtVifDown(459),
        sysdebugMepLogMEpLogLog(460),
        sysdebugMepLogMEpLogVeryLow(461),
        sysdebugMepLogMEpLogFull(462),
        computePoolEmpty(463),
        uuidpoolPoolEmpty(464),
        ippoolPoolEmpty(465),
        macpoolPoolEmpty(466),
        firmwareUpdatableImageUnusable(470),
        firmwareBootUnitCantBoot(471),
        fcpoolInitiatorsEmpty(476),
        equipmentIocardInaccessible(478),
        dcxVifLinkState(479),
        equipmentFanModuleDegraded(480),
        equipmentIocardPostFailure(481),
        equipmentFanPerfThresholdLowerNonRecoverable(484),
        memoryUnitIdentityUnestablishable(502),
        computePhysicalPostFailure(517),
        equipmentPsuOffline(528),
        storageRaidBatteryInoperable(531),
        sysdebugMepLogTransferError(532),
        computeRtcBatteryInoperable(533),
        memoryBufferUnitThermalThresholdNonCritical(535),
        memoryBufferUnitThermalThresholdCritical(536),
        memoryBufferUnitThermalThresholdNonRecoverable(537),
        computeIohubThermalNonCritical(538),
        computeIohubThermalThresholdCritical(539),
        computeIohubThermalThresholdNonRecoverable(540),
        equipmentChassisIdentityUnestablishable(543),
        swVlanPortNsResourceStatus(549),
        fabricLanPinGroupEmpty(621),
        adaptorExtEthIfMisConnect(625),
        adaptorHostEthIfMisConnect(626),
        powerBudgetPowerBudgetCmcProblem(635),
        powerBudgetPowerBudgetBmcProblem(637),
        powerBudgetPowerBudgetDiscFail(640),
        powerGroupPowerGroupInsufficientBudget(642),
        powerGroupPowerGroupBudgetIncorrect(643),
        licenseInstanceGracePeriodWarning1(670),
        licenseInstanceGracePeriodWarning2(671),
        licenseInstanceGracePeriodWarning3(672),
        licenseInstanceGracePeriodWarning4(673),
        licenseInstanceGracePeriodWarning5(674),
        licenseInstanceGracePeriodWarning6(675),
        licenseInstanceGracePeriodWarning7(676),
        licenseFileBadLicenseFile(677),
        licenseFileFileNotDeleted(678),
        mgmtIfMisConnect(688),
        lsComputeBindingAssignmentRequirementsNotMet(689),
        equipmentFexPostFailure(702),
        equipmentFexIdentity(703),
        adaptorHostEthIfMissing(708),
        portPioInvalidSfp(713),
        mgmtIfMissing(717),
        fabricEthLanPcEpDown(727),
        equipmentIocardThermalThresholdNonCritical(729),
        equipmentIocardThermalThresholdCritical(730),
        equipmentIocardThermalThresholdNonRecoverable(731),
        equipmentChassisSeepromInoperable(733),
        extmgmtIfMgmtifdown(736),
        powerChassisMemberPowerGroupCapInsufficient(740),
        powerChassisMemberChassisFirmwareProblem(741),
        powerChassisMemberChassisPsuInsufficient(742),
        powerChassisMemberChassisPsuRedundanceFailure(743),
        powerBudgetPowerCapReachedCommit(744),
        sysdebugAutoCoreFileExportTargetAutoCoreTransferFailure(747),
        fabricMonSpanConfigFail(757),
        powerBudgetChassisPsuInsufficient(764),
        powerBudgetTstateTransition(765),
        powerPolicyPowerPolicyApplicationFail(766),
        mgmtIfNew(772),
        adaptorExtEthIfMissing(775),
        storageLocalDiskSlotEpUnusable(776),
        fabricEthEstcPcEpDown(777),
        equipmentFexIdentityUnestablishable(778),
        equipmentFanModuleInoperable(794),
        lsmaintMaintPolicyUnresolvableScheduler(795),
        powerBudgetFirmwareMismatch(798),
        processorUnitIdentityUnestablishable(801),
        iqnpoolPoolEmpty(821),
        fabricDceSwSrvPcEpDown(831),
        fabricEpMgrEpTransModeFail(832),
        fabricPioEpErrorMisconfigured(834),
        fabricEthLanEpMissingPrimaryVlan(835),
        fabricEthLanPcMissingPrimaryVlan(836),
        vnicEtherPinningMismatch(840),
        vnicEtherPinningMisconfig(841),
        processorUnitDisabled(842),
        memoryUnitDisabled(844),
        firmwareBootUnitActivateStatusFailed(856),
        fabricInternalPcDown(858),
        mgmtEntityDevice1SharedStorageError(863),
        mgmtEntityDevice2SharedStorageError(864),
        mgmtEntityDevice3SharedStorageError(865),
        mgmtEntityHaSshKeysMismatched(866),
        computeBoardPowerFail(868),
        vmVifLinkState(876),
        equipmentPsuPowerSupplyShutdown(881),
        equipmentPsuPowerThreshold(882),
        equipmentPsuInputError(883),
        equipmentSwitchCardPowerOff(884),
        networkElementInventoryFailed(885),
        adaptorUnitExtnUnidentifiableFru(900),
        adaptorUnitExtnMissing(901),
        equipmentFexFexUnsupported(902),
        vnicIscsiConfigFailed(903),
        pkiKeyRingStatus(909),
        pkiTpStatus(910),
        computePhysicalDisassociationFailed(915),
        computePhysicalNetworkMisconfigured(916),
        vnicProfileProfileConfigIncorrect(917),
        vnicEtherIfVlanAccessFault(932),
        vnicEtherIfVlanUnresolvable(933),
        vnicEtherIfInvalidVlan(934),
        fabricVlanVlanConflictPermit(935),
        fabricVlanReqVlanPermitUnresolved(936),
        fabricVlanGroupReqVlanGroupPermitUnresolved(937),
        extpolClientClientLostConnectivity(988),
        storageLocalDiskDegraded(996),
        storageRaidBatteryDegraded(997),
        storageRaidBatteryRelearnAborted(998),
        storageRaidBatteryRelearnFailed(999),
        storageInitiatorConfigurationError(1001),
        storageControllerPatrolReadFailed(1003),
        storageControllerInoperable(1004),
        storageLocalDiskRebuildFailed(1005),
        storageLocalDiskCopybackFailed(1006),
        storageVirtualDriveInoperable(1007),
        storageVirtualDriveDegraded(1008),
        storageVirtualDriveReconstructionFailed(1009),
        storageVirtualDriveConsistencyCheckFailed(1010),
        aaaProviderGroupProvidergroup(1026),
        aaaConfigServergroup(1027),
        aaaRoleRoleNotDeployed(1028),
        aaaLocaleLocaleNotDeployed(1029),
        aaaUserRoleUserRoleNotDeployed(1030),
        aaaUserLocaleUserLocaleNotDeployed(1031),
        pkiKeyRingKeyRingNotDeployed(1032),
        commSnmpSyscontactEmpty(1033),
        commDateTimeCommTimeZoneInvalid(1034),
        aaaUserLocalUserNotDeployed(1035),
        commSnmpUserSnmpUserNotDeployed(1036),
        commSvcEpCommSvcNotDeployed(1037),
        swVlanPortNsVlancompNotSupport(1056),
        policyControlEpSuspendModeActive(1057),
        networkElementThermalThresholdCritical(1080),
        fabricPinTargetDown(1088),
        fabricEthLanEpOverlappingVlan(1090),
        fabricEthLanPcOverlappingVlan(1091),
        fabricVlanMisconfiguredMcastPolicy(1095),
        mgmtConnectionDisabled(1097),
        mgmtConnectionUnused(1098),
        mgmtConnectionUnsupportedConnectivity(1099),
        callhomeEpNoSnmpPolicyForCallhome(1102),
        capabilityCatalogueLoadErrors(1103),
        extmgmtArpTargetsArpTargetsNotValid(1114),
        extpolClientGracePeriodWarning(1211),
        extpolClientGracePeriodWarning2(1212),
        extpolClientGracePeriodWarning3(1213),
        extpolClientGracePeriodWarning4(1214),
        extpolClientGracePeriodWarning5(1215),
        extpolClientGracePeriodWarning6(1216),
        extpolClientGracePeriodWarning7(1217),
        extpolClientGracePeriodWarning1(1218),
        storageItemFilesystemIssues(1219),
        pkiKeyRingModulus(1222),
        aaaOrgLocaleOrgNotPresent(1223),
        networkOperLevelExtraprimaryvlans(1229),
        equipmentHealthLedCriticalError(1236),
        equipmentHealthLedMinorError(1237),
        vnicEtherIfRemoteVlanUnresolvable(1249),
        vnicEtherVirtualizationConflict(1251),
        lsIssuesIscsiConfigFailed(1252),
        storageLocalDiskMissing(1256),
        storageFlexFlashControllerInoperable(1257),
        storageFlexFlashCardInoperable(1258),
        storageFlexFlashCardMissing(1259),
        storageFlexFlashVirtualDriveDegraded(1260),
        storageFlexFlashVirtualDriveInoperable(1261),
        storageFlexFlashControllerUnhealthy(1262),
        aaaProviderGroupProvidergroupsize(1279),
        firmwareAutoSyncPolicyDefaultHostPackageMissing(1284),
        firmwareAutoSyncPolicyDefaultHostPackageMissingVersions(1285),
        fabricNetflowMonSessionFlowMonConfigFail(1304),
        fabricNetflowMonSessionNetflowSessionConfigFail(1305),
        fabricPooledVlanNamedVlanUnresolved(1306),
        extvmmVmndrefVmNetworkReferenceIncorrect(1320),
        extmgmtNdiscTargetsNdiscTargetsNotValid(1321),
        firmwareBootUnitPowerCycleRequired(1325),
        mgmtControllerUnsupportedDimmBlacklisting(1328),
        fabricEthLanEpUdldLinkDown(1358),
        fabricEthLanPcEpUdldLinkDown(1359),
        equipmentChassisInvalidFru(1407),
        equipmentSwitchiocardRemoved(1408),
        equipmentSwitchiocardThermalProblem(1409),
        equipmentSwitchiocardThermalThresholdNonCritical(1410),
        equipmentSwitchiocardThermalThresholdCritical(1411),
        equipmentSwitchiocardThermalThresholdNonRecoverable(1412),
        equipmentSwitchiocardPeerDisconnected(1413),
        equipmentSwitchiocardIdentity(1414),
        equipmentSwitchiocardCpuThermalThresholdCritical(1415),
        powerBudgetChassisPsuMixedMode(1421),
        networkElementRemoved(1426),
        networkOperLevelExtrasecondaryvlans(1432),
        swVlanExtrasecondaryvlansperprimary(1433),
        mgmtBackupPolicyConfigConfigurationBackupOutdated(1437),
        firmwareStatusCimcFirmwareMismatch(1441),
        firmwareStatusPldFirmwareMismatch(1442),
        vnicEtherVirtualizationNetflowConflict(1443),
        sysdebugLogExportStatusLogExportFailure(1444),
        lsServerSvnicNotPresent(1459),
        lsIssuesKvmPolicyUnsupported(1460),
        computeAboardThermalProblem(1461),
        computeAboardPowerUsageProblem(1462),
        computeAboardMotherBoardVoltageThresholdUpperNonRecoverable(1463),
        computeAboardMotherBoardVoltageThresholdLowerNonRecoverable(1464),
        computeAboardMotherBoardVoltageUpperThresholdCritical(1465),
        computeAboardMotherBoardVoltageLowerThresholdCritical(1466),
        cimcvmediaActualMountEntryVmediaMountFailed(1467),
        fabricVlanPrimaryVlanMissingForIsolated(1468),
        fabricVlanPrimaryVlanMissingForCommunity(1469),
        fabricVlanMismatchA(1470),
        fabricVlanMismatchB(1471),
        fabricVlanErrorAssocPrimary(1472),
        storageMezzFlashLifeConfigurationError(1494),
        storageMezzFlashLifeDegraded(1495),
        storageFlexFlashControllerMismatch(1496),
        storageFlexFlashDriveUnhealthy(1497),
        storageFlexFlashCardUnhealthy(1498),
        mgmtInterfaceNamedInbandVlanUnresolved(1506),
        mgmtInterfaceInbandUnsupportedServer(1507),
        mgmtInterfaceInbandUnsupportedFirmware(1508),
        computePhysicalAdapterMismatch(1509),
        equipmentSwitchCardAct2LiteFail(1510),
        equipmentTpmSlaveTpm(1511),
        poolElementDuplicatedAssigned(1512),
        swVlanPortNsResourceStatusWarning(1519),
        networkElementMemoryerror(1520),
        smSlotSmaHeartbeat(1536),
        smSlotBladeNotWorking(1537),
        smSlotDiskFormatFailed(1538),
        smSlotBladeSwap(1539),
        smAppInstanceAppNotResponding(1540),
        smAppInstanceAppInstallFailed(1541),
        smAppInstanceAppStartFailed(1542),
        smAppInstanceAppUpdateFailed(1543),
        smAppInstanceAppStopFailed(1544),
        mgmtPmonEntryFprmProcessFailure(1565),
        firmwarePlatformPackBundleVersionMissing(1571),
        osControllerFailedBladeBootup(1574),
        osControllerFailedBootupRecovery(1575),
        smSecSvcSwitchConfigFail(1622),
        smAppLicenseAgreementNotAccepted(1623),
        smLogicalDeviceIncompleteConfig(1628),
        smLogicalDeviceLogicalDeviceError(1629),
        etherFtwPortPairBypass(1638),
        commDateTimeCommNtpConfigurationFailed(1661),
        smConfigIssueLogicalDeviceConfigError(1671),
        smAppAppImageCorrupted(1673),
        equipmentXcvrNonSupportedXcvr(1677),
        fabricSspEthMonDelAllSessEnabled(1679),
        ipsecConnectionIpsecConnInvalidKey(1681),
        ipsecConnectionIpsecConnInvalidCert(1682),
        ipsecAuthorityIpsecAuthorInvalidTp(1683),
        smHotfixHotfixInstallFailed(1691),
        smHotfixHotfixError(1692),
        smErrorError(1693),
        smCloudConnectorCloudRegistrationFailed(1694),
        smCloudConnectorCloudUnregistrationFailed(1695),
        smUnsignedCspLicenseUnsignedcsplicenseInstalled(1716),
        sdLinkVnicConfigFail(1717),
        nwctrlCardConfigOffline(1718),
        nwctrlCardConfigFailed(1719),
        nwctrlCardConfigError(1720),
        nwctrlCardConfigOirFailed(1721),
        nwctrlCardConfigOirInvalid(1722),
        nwctrlCardConfigRemoval(1723),
        nwctrlCardConfigMismatch(1724),
        nwctrlCardConfigSupriseRemoval(1725),
        firmwareRunnableAdapterUpgradeRequired(1729),
        smClusterBootstrapCclSubnetNotSupported(1732),
        smAppInstanceFailedConversion(1735),
        smAppInstance2AppNotResponding(1736),
        smAppInstance2AppInstallFailed(1737),
        smAppInstance2AppStartFailed(1738),
        smAppInstance2AppUpdateFailed(1739),
        smAppInstance2AppStopFailed(1740),
        smAppInstance2AppNotInstalled(1741),
        smAppInstance2AppInstanceError(1742),
        smAppInstance2AppInstanceUnsupported(1743),
        smAppInstance2SoftwareIncompatible(1744),
        networkElementSamconfig(1750),
        smExternalPortLinkConflictConfig(1753),
        smAppInstance2AppFaultState(1757),
        smSlotAdapter2NotResponding(1760),
        smHwCryptoHwCryptoNotOperable(1761),
        sdExternalLduLinkExternalLduLinkVnicConfigFail(1762),
        sdAppLduLinkAppLduLinkEndpoint1VnicConfigFail(1763),
        sdAppLduLinkAppLduLinkEndpoint2VnicConfigFail(1764),
        mgmtImporterConfigurationImportFailed(1765),
        commTelemetryTelemetryUnregistrationFailed(1766),
        commTelemetryTelemetryGetDataFailed(1767),
        commTelemetryTelemetrySendDataFailed(1768),
        sdPreAllocatedVnicVnicPreAllocationFail(1778),
        sdLogicalDeviceDifferentResourcesInProfile(1779),
        firmwareVersionIssueImageVersionMismatch(1780),
        fabricComputeSlotEpBladeDecommissionFail(1781),
        etherFtwPortPairPhyBypass(1782),
        etherFtwPortPairPhyBypassErr(1783),
        fsmSamDmeEquipmentChassisRemoveChassis(16407),
        fsmSamDmeEquipmentLocatorLedSetLocatorLed(16408),
        fsmSamDmeMgmtControllerExtMgmtIfConfig(16518),
        fsmSamDmeFabricComputeSlotEpIdentify(16519),
        fsmSamDmeComputeBladeDiscover(16520),
        fsmSamDmeEquipmentChassisPsuPolicyConfig(16533),
        fsmSamDmeAdaptorHostFcIfResetFcPersBinding(16534),
        fsmSamDmeComputeBladeDiag(16535),
        fsmSamDmeFabricLanCloudSwitchMode(16539),
        fsmSamDmeVnicProfileSetDeploy(16550),
        fsmSamDmeCommSvcEpUpdateSvcEp(16576),
        fsmSamDmeCommSvcEpRestartWebSvc(16577),
        fsmSamDmeAaaEpUpdateEp(16579),
        fsmSamDmeAaaRealmUpdateRealm(16580),
        fsmSamDmeAaaUserEpUpdateUserEp(16581),
        fsmSamDmePkiEpUpdateEp(16582),
        fsmSamDmeSysfileMutationSingle(16600),
        fsmSamDmeSysfileMutationGlobal(16601),
        fsmSamDmeSysdebugManualCoreFileExportTargetExport(16604),
        fsmSamDmeSysdebugAutoCoreFileExportTargetConfigure(16605),
        fsmSamDmeSysdebugLogControlEpLogControlPersist(16606),
        fsmSamDmeSwAccessDomainDeploy(16634),
        fsmSamDmeSwEthLanBorderDeploy(16635),
        fsmSamDmeSwFcSanBorderDeploy(16636),
        fsmSamDmeSwUtilityDomainDeploy(16637),
        fsmSamDmeSyntheticFsObjCreate(16641),
        fsmSamDmeFirmwareDownloaderDownload(16650),
        fsmSamDmeFirmwareImageDelete(16651),
        fsmSamDmeMgmtControllerUpdateSwitch(16653),
        fsmSamDmeMgmtControllerUpdateiom(16654),
        fsmSamDmeMgmtControllerActivateiom(16655),
        fsmSamDmeMgmtControllerUpdatebmc(16656),
        fsmSamDmeMgmtControllerActivatebmc(16657),
        fsmSamDmeCallhomeEpConfigCallhome(16670),
        fsmSamDmeMgmtIfSwMgmtOobIfConfig(16673),
        fsmSamDmeMgmtIfSwMgmtInbandIfConfig(16674),
        fsmSamDmeMgmtIfVirtualIfConfig(16679),
        fsmSamDmeMgmtIfEnableVip(16680),
        fsmSamDmeMgmtIfDisableVip(16681),
        fsmSamDmeMgmtIfEnableha(16682),
        fsmSamDmeMgmtBackupBackup(16683),
        fsmSamDmeMgmtImporterImport(16684),
        fsmSamDmeStatsCollectionPolicyUpdateEp(16742),
        fsmSamDmeQosclassDefinitionConfigGlobalQos(16745),
        fsmSamDmeEpqosDefinitionDeploy(16749),
        fsmSamDmeEpqosDefinitionDelTaskRemove(16750),
        fsmSamDmeEquipmentiocardResetCmc(16803),
        fsmSamDmeMgmtControllerUpdatefprmanager(16815),
        fsmSamDmeMgmtControllerSysConfig(16823),
        fsmSamDmeAdaptorExtEthIfPathReset(16852),
        fsmSamDmeAdaptorHostEthIfCircuitReset(16857),
        fsmSamDmeAdaptorHostFcIfCircuitReset(16858),
        fsmSamDmeExtvmmProviderConfig(16879),
        fsmSamDmeExtvmmKeyStoreCertInstall(16880),
        fsmSamDmeExtvmmSwitchDelTaskRemoveProvider(16881),
        fsmSamDmeExtvmmMasterExtKeyConfig(16898),
        fsmSamDmeCapabilityUpdaterUpdater(16904),
        fsmSamDmeFirmwareDistributableDelete(16906),
        fsmSamDmeCapabilityCatalogueDeployCatalogue(16931),
        fsmSamDmeEquipmentFexRemoveFex(16942),
        fsmSamDmeEquipmentLocatorLedSetFeLocatorLed(16943),
        fsmSamDmeEquipmentChassisPowerCap(16944),
        fsmSamDmeEquipmentiocardMuxOffline(16945),
        fsmSamDmeComputePhysicalAssociate(16973),
        fsmSamDmeComputePhysicalDisassociate(16974),
        fsmSamDmeComputePhysicalPowerCap(16975),
        fsmSamDmeComputePhysicalDecommission(16976),
        fsmSamDmeComputePhysicalSoftShutdown(16977),
        fsmSamDmeComputePhysicalHardShutdown(16978),
        fsmSamDmeComputePhysicalTurnup(16979),
        fsmSamDmeComputePhysicalPowercycle(16980),
        fsmSamDmeComputePhysicalHardreset(16981),
        fsmSamDmeComputePhysicalSoftreset(16982),
        fsmSamDmeComputePhysicalSwConnUpd(16983),
        fsmSamDmeComputePhysicalBiosRecovery(16984),
        fsmSamDmeComputePhysicalCmosReset(16986),
        fsmSamDmeComputePhysicalResetBmc(16987),
        fsmSamDmeEquipmentiocardResetIom(16988),
        fsmSamDmeComputeRackUnitDiscover(16994),
        fsmSamDmeLsServerConfigure(16995),
        fsmSamDmeSwEthMonDeploy(17000),
        fsmSamDmeSwFcMonDeploy(17001),
        fsmSamDmeFabricSanCloudSwitchMode(17002),
        fsmSamDmeComputePhysicalUpdateExtUsers(17008),
        fsmSamDmeSysdebugTechSupportInitiate(17012),
        fsmSamDmeSysdebugTechSupportDeleteTechSupFile(17013),
        fsmSamDmeSysdebugTechSupportDownload(17014),
        fsmSamDmeComputePhysicalUpdateAdaptor(17043),
        fsmSamDmeComputePhysicalActivateAdaptor(17044),
        fsmSamDmeCapabilityCatalogueActivateCatalog(17045),
        fsmSamDmeCapabilityMgmtExtensionActivateMgmtExt(17046),
        fsmSamDmeLicenseDownloaderDownload(17050),
        fsmSamDmeLicenseFileInstall(17051),
        fsmSamDmeLicenseFileClear(17052),
        fsmSamDmeLicenseInstanceUpdateFlexlm(17053),
        fsmSamDmeComputePhysicalConfigSol(17083),
        fsmSamDmeComputePhysicalUnconfigSol(17084),
        fsmSamDmePortpioInCompatSfpPresence(17089),
        fsmSamDmeComputePhysicalDiagnosticInterrupt(17116),
        fsmSamDmeSysdebugCoreDownload(17133),
        fsmSamDmeEquipmentChassisDynamicReallocation(17134),
        fsmSamDmeComputePhysicalResetKvm(17163),
        fsmSamDmeMgmtControllerOnline(17169),
        fsmSamDmeComputeRackUnitOffline(17170),
        fsmSamDmeEquipmentLocatorLedSetFiLocatorLed(17187),
        fsmSamDmeFabricEpMgrConfigure(17214),
        fsmSamDmeVnicProfileSetDeployAlias(17223),
        fsmSamDmeSwPhysConfPhysical(17239),
        fsmSamDmeExtvmmEpClusterRole(17254),
        fsmSamDmeVmLifeCyclePolicyConfig(17259),
        fsmSamDmeEquipmentBeaconLedIlluminate(17262),
        fsmSamDmeEtherServerIntfioConfigSpeed(17271),
        fsmSamDmeComputePhysicalUpdatebios(17281),
        fsmSamDmeComputePhysicalActivatebios(17282),
        fsmSamDmeIdentIdentRequestUpdateIdent(17312),
        fsmSamDmeIdentMetaSystemSync(17313),
        fsmSamDmeComputePhysicalResetIpmi(17326),
        fsmSamDmeComputePhysicalFwUpgrade(17327),
        fsmSamDmeComputeRackUnitAdapterReset(17328),
        fsmSamDmePortpioInCompatSfpReplaced(17358),
        fsmSamDmeExtpolEpRegisterFsm(17359),
        fsmSamDmeExtpolRegistryCrossDomainConfig(17360),
        fsmSamDmeExtpolRegistryCrossDomainDelete(17361),
        fsmSamDmeNfsMountInstMount(17377),
        fsmSamDmeNfsMountInstUnmount(17378),
        fsmSamDmeNfsMountDefReportNfsMountSuspend(17379),
        fsmSamDmeStorageSystemSync(17395),
        fsmSamDmeFirmwareSystemDeploy(17408),
        fsmSamDmeFirmwareSystemApplyCatalogPack(17409),
        fsmSamDmeComputeServerDiscPolicyResolveScrubPolicy(17426),
        fsmSamDmeSwFcSanBorderActivateZoneSet(17439),
        fsmSamDmeExtpolEpRepairCert(17446),
        fsmSamDmePolicyControlEpOperate(17447),
        fsmSamDmePolicyPolicyScopeReleasePolicyFsm(17448),
        fsmSamDmePolicyPolicyScopeReleaseOperationFsm(17449),
        fsmSamDmePolicyPolicyScopeReleaseStorageFsm(17450),
        fsmSamDmePolicyPolicyScopeResolveManyPolicyFsm(17451),
        fsmSamDmePolicyPolicyScopeResolveManyOperationFsm(17452),
        fsmSamDmePolicyPolicyScopeResolveManyStorageFsm(17453),
        fsmSamDmePolicyPolicyScopeReleaseManyPolicyFsm(17454),
        fsmSamDmePolicyPolicyScopeReleaseManyOperationFsm(17455),
        fsmSamDmePolicyPolicyScopeReleaseManyStorageFsm(17456),
        fsmSamDmePolicyPolicyScopeResolveAllPolicyFsm(17457),
        fsmSamDmePolicyPolicyScopeResolveAllOperationFsm(17458),
        fsmSamDmePolicyPolicyScopeResolveAllStorageFsm(17459),
        fsmSamDmePolicyPolicyScopeReleaseAllPolicyFsm(17460),
        fsmSamDmePolicyPolicyScopeReleaseAllOperationFsm(17461),
        fsmSamDmePolicyPolicyScopeReleaseAllStorageFsm(17462),
        fsmSamDmeMgmtExportPolicyReportConfigCopy(17484),
        fsmSamDmeExtpolProviderReportConfigImport(17485),
        fsmSamDmeObserveObservedResolvePolicyFsm(17491),
        fsmSamDmeObserveObservedResolveResourceFsm(17492),
        fsmSamDmeObserveObservedResolvevmfsm(17493),
        fsmSamDmeObserveObservedResolveControllerFsm(17494),
        fsmSamDmeMgmtControllerRegistryConfig(17499),
        fsmSamDmeGmetaHolderInventory(17608),
        fsmSamDmeComputePhysicalCimcSessionDelete(17609),
        fsmSamDmePolicyControlledTypeOperate(17612),
        fsmSamDmeFabricVnetEpSyncEpPushVnetEpDeletion(17619),
        fsmSamDmeSwEthLanFlowMonDeploy(17639),
        fsmSamDmeMgmtipv6IfAddrSwMgmtOobIpv6IfConfig(17665),
        fsmSamDmeComputePhysicalUpdateBoardController(17667),
        fsmSamDmeExtvmmNetworkSetsDeploy(17703),
        fsmSamDmeComputePhysicalConfigBoard(17707),
        fsmSamDmeComputePhysicalResetMemoryErrors(17708),
        fsmSamDmeMgmtControllerExtMgmtInterfaceConfig(17714),
        fsmSamDmeComputeRackUnitCreateDhcpEntry(17715),
        fsmSamDmeComputePhysicalServiceInfraDeploy(17716),
        fsmSamDmeComputePhysicalServiceInfraWithdraw(17717),
        fsmSamDmeEquipmentiocardBaseFePresence(17808),
        fsmSamDmeEquipmentiocardBaseFeConn(17809),
        fsmSamDmeMgmtControllerLockConfig(17813),
        fsmSamDmeSdAppInstanceInstallApplication(17819),
        fsmSamDmeSysdebugLogExportPolicyConfigure(17830),
        fsmSamDmeComputePhysicalFlashController(17839),
        fsmSamDmeOsControllerDeployos(17863),
        fsmSamDmeNhTableHolderConfigureLinks(17866),
        fsmSamDmeStorageFlexFlashControllermopsReset(17872),
        fsmSamDmeStorageFlexFlashControllermopsFormat(17873),
        fsmSamDmeStorageFlexFlashControllermopsPair(17874),
        fsmSamDmeIdentMetaSystemFprcUnivSync(17877),
        fsmSamDmeComputePhysicalEnableCimcSecureBoot(17897),
        fsmSamDmeSdAppInstanceStartApplication(17911),
        fsmSamDmeSdLduProvisionldu(17912),
        fsmSamDmeSwExtUtilityConfPortBreakout(17917),
        fsmSamDmeSmAppDelete(17929),
        fsmSamDmeSmSecSvcRestoreApplication(17930),
        fsmSamDmeApplicationDownloaderDownload(17945),
        fsmSamDmeNhTableHolderBootstrapLinks(17948),
        fsmSamDmeFirmwarePlatformPackPlatformVersion(17954),
        fsmSamDmeLicenseSmartConfigSetConfig(17957),
        fsmSamDmeOsControllerUpgradeos(17970),
        fsmSamDmeOsControllerInitos(17971),
        fsmSamDmeSdAppInstanceUpgradeApplication(17972),
        fsmSamDmeSdAppInstanceStopApplication(17973),
        fsmSamDmeSdAppInstanceUninstallApplication(17974),
        fsmSamDmeSdSlotChangePlatformLogLevel(17975),
        fsmSamDmeSdAppInstanceBundleDataPorts(17976),
        fsmSamDmeSdLogicalDeviceConfigureLinks(17977),
        fsmSamDmeSdExternalLduLinkUpdateInterfaceStatus(17978),
        fsmSamDmeSdAppInstanceUpdateClusterConfiguration(17979),
        fsmSamDmeSdSlotFormatDisk(17980),
        fsmSamDmeSdSlotSynchTimeZone(17981),
        fsmSamDmeSdAppAttributeCtrlGetAppAttributes(17982),
        fsmSamDmeSdMgmtInfoUpdateMgmtInfo(17983),
        fsmSamDmeSdNetMgmtBootstrapUpdateNetMgmtBootstrap(17984),
        fsmSamDmeSwSspEthMonDeploy(18000),
        fsmSamDmeSdClusterBootstrapUpdateClusterConfiguration(18003),
        fsmSamDmeSmAppInstanceResetApplication(18008),
        fsmSamDmeIpsecEpUpdateEp(18020),
        fsmSamDmeEtherFtwPortPairConfigFtw(18023),
        fsmSamDmeSdLinkUpdateInterfaceStatus(18024),
        fsmSamDmeSdUpgradeTaskStopUpgradeStartApp(18025),
        fsmSamDmeSwSspEthMonSrcPhyEpDelete(18034),
        fsmSamDmeFirmwareSupFirmwareDeploy(18035),
        fsmSamDmeEquipmentChassisShutdownChassis(18043),
        fsmSamDmeSmCloudConnectorRegisterCloudConnector(18051),
        fsmSamDmeSmCloudConnectorUnRegisterCloudConnector(18052),
        fsmSamDmeSmAppVerifyApplication(18053),
        fsmSamDmeSmLogicalDeviceConfigure(18056),
        fsmSamDmeSdLduUpdateInterfaceStatus(18058),
        fsmSamDmeSdLogicalDeviceConfigureUserMacs(18059),
        fsmSamDmeEquipmentChassisRebootChassis(18060),
        fsmSamDmeFirmwareValidationStatusValidate(18064),
        fsmSamDmeSdPortsBundleBundleDataPorts(18081),
        fsmSamDmeSdHotfixInstallHotfix(18082),
        fsmSamDmeSdHotfixUninstallHotfix(18083),
        fsmSamDmeOsControllerInstallLicense(18092),
        fsmSamDmeSmUnsignedCspLicenseDeploy(18098),
        fsmSamDmeSmLicenseFileDelete(18099),
        fsmSamDmeComputePhysicalUpdateAdaptorBoot(18112),
        fsmSamDmeSmAppInstance2ResetApplication(18129),
        fsmSamDmeSdAppInstSettingsTaskSendAppInstSettings(18136),
        fsmSamDmeSdLogicalDeviceConfigureMacs(18138),
        fsmSamDmeCommTelemetryDataExchSeq(18154),
        fsmSamDmeCommTelemetryEnableDisableTelemetry(18155),
        fsmSamDmeSdCspMetaCtrlRetrievecspmeta(18156),
        fsmSamDmeSdAppInstanceGracefulStopApp(18157),
        fsmSamDmeComputePhysicalHardPowercycle(18169),
        tcaProcessorRuntimeLoad(33142),
        tcaProcessorRuntimeLoadMin(33144),
        tcaProcessorRuntimeLoadMax(33145),
        tcaProcessorRuntimeLoadAvg(33146),
        tcaFcStatsBytesRxDelta(33167),
        tcaFcStatsBytesRxDeltaMin(33168),
        tcaFcStatsBytesRxDeltaMax(33169),
        tcaFcStatsBytesRxDeltaAvg(33170),
        tcaFcStatsPacketsRxDelta(33177),
        tcaFcStatsPacketsRxDeltaMin(33178),
        tcaFcStatsPacketsRxDeltaMax(33179),
        tcaFcStatsPacketsRxDeltaAvg(33180),
        tcaFcStatsBytesTxDelta(33187),
        tcaFcStatsBytesTxDeltaMin(33188),
        tcaFcStatsBytesTxDeltaMax(33189),
        tcaFcStatsBytesTxDeltaAvg(33190),
        tcaFcStatsPacketsTxDelta(33197),
        tcaFcStatsPacketsTxDeltaMin(33198),
        tcaFcStatsPacketsTxDeltaMax(33199),
        tcaFcStatsPacketsTxDeltaAvg(33200),
        tcaFcErrStatsCrcRxDelta(33211),
        tcaFcErrStatsCrcRxDeltaMin(33212),
        tcaFcErrStatsCrcRxDeltaMax(33213),
        tcaFcErrStatsCrcRxDeltaAvg(33214),
        tcaFcErrStatsDiscardRxDelta(33221),
        tcaFcErrStatsDiscardRxDeltaMin(33222),
        tcaFcErrStatsDiscardRxDeltaMax(33223),
        tcaFcErrStatsDiscardRxDeltaAvg(33224),
        tcaFcErrStatsTooLongRxDelta(33231),
        tcaFcErrStatsTooLongRxDeltaMin(33232),
        tcaFcErrStatsTooLongRxDeltaMax(33233),
        tcaFcErrStatsTooLongRxDeltaAvg(33234),
        tcaFcErrStatsTooShortRxDelta(33241),
        tcaFcErrStatsTooShortRxDeltaMin(33242),
        tcaFcErrStatsTooShortRxDeltaMax(33243),
        tcaFcErrStatsTooShortRxDeltaAvg(33244),
        tcaFcErrStatsRxDelta(33251),
        tcaFcErrStatsRxDeltaMin(33252),
        tcaFcErrStatsRxDeltaMax(33253),
        tcaFcErrStatsRxDeltaAvg(33254),
        tcaFcErrStatsDiscardTxDelta(33261),
        tcaFcErrStatsDiscardTxDeltaMin(33262),
        tcaFcErrStatsDiscardTxDeltaMax(33263),
        tcaFcErrStatsDiscardTxDeltaAvg(33264),
        tcaFcErrStatsTxDelta(33271),
        tcaFcErrStatsTxDeltaMin(33272),
        tcaFcErrStatsTxDeltaMax(33273),
        tcaFcErrStatsTxDeltaAvg(33274),
        tcaFcErrStatsLinkFailuresDelta(33281),
        tcaFcErrStatsLinkFailuresDeltaMin(33282),
        tcaFcErrStatsLinkFailuresDeltaMax(33283),
        tcaFcErrStatsLinkFailuresDeltaAvg(33284),
        tcaFcErrStatsSyncLossesDelta(33291),
        tcaFcErrStatsSyncLossesDeltaMin(33292),
        tcaFcErrStatsSyncLossesDeltaMax(33293),
        tcaFcErrStatsSyncLossesDeltaAvg(33294),
        tcaFcErrStatsSignalLossesDelta(33301),
        tcaFcErrStatsSignalLossesDeltaMin(33302),
        tcaFcErrStatsSignalLossesDeltaMax(33303),
        tcaFcErrStatsSignalLossesDeltaAvg(33304),
        tcaMemoryRuntimeTotal(33483),
        tcaMemoryRuntimeTotalMin(33485),
        tcaMemoryRuntimeTotalMax(33486),
        tcaMemoryRuntimeTotalAvg(33487),
        tcaMemoryRuntimeAvailable(33491),
        tcaMemoryRuntimeAvailableMin(33493),
        tcaMemoryRuntimeAvailableMax(33494),
        tcaMemoryRuntimeAvailableAvg(33495),
        tcaMemoryRuntimeCached(33499),
        tcaMemoryRuntimeCachedMin(33501),
        tcaMemoryRuntimeCachedMax(33502),
        tcaMemoryRuntimeCachedAvg(33503),
        tcaAdaptorEthPortStatsTotalPacketsDelta(33720),
        tcaAdaptorEthPortStatsTotalPacketsDeltaMin(33721),
        tcaAdaptorEthPortStatsTotalPacketsDeltaMax(33722),
        tcaAdaptorEthPortStatsTotalPacketsDeltaAvg(33723),
        tcaAdaptorEthPortStatsGoodPacketsDelta(33730),
        tcaAdaptorEthPortStatsGoodPacketsDeltaMin(33731),
        tcaAdaptorEthPortStatsGoodPacketsDeltaMax(33732),
        tcaAdaptorEthPortStatsGoodPacketsDeltaAvg(33733),
        tcaAdaptorEthPortStatsVlanPacketsDelta(33740),
        tcaAdaptorEthPortStatsVlanPacketsDeltaMin(33741),
        tcaAdaptorEthPortStatsVlanPacketsDeltaMax(33742),
        tcaAdaptorEthPortStatsVlanPacketsDeltaAvg(33743),
        tcaAdaptorEthPortStatsPausePacketsDelta(33750),
        tcaAdaptorEthPortStatsPausePacketsDeltaMin(33751),
        tcaAdaptorEthPortStatsPausePacketsDeltaMax(33752),
        tcaAdaptorEthPortStatsPausePacketsDeltaAvg(33753),
        tcaAdaptorEthPortStatsPerPriorityPausePacketsDelta(33760),
        tcaAdaptorEthPortStatsPerPriorityPausePacketsDeltaMin(33761),
        tcaAdaptorEthPortStatsPerPriorityPausePacketsDeltaMax(33762),
        tcaAdaptorEthPortStatsPerPriorityPausePacketsDeltaAvg(33763),
        tcaAdaptorEthPortStatsPppPacketsDelta(33770),
        tcaAdaptorEthPortStatsPppPacketsDeltaMin(33771),
        tcaAdaptorEthPortStatsPppPacketsDeltaMax(33772),
        tcaAdaptorEthPortStatsPppPacketsDeltaAvg(33773),
        tcaAdaptorEthPortBySizeSmallStatsLessThan64Delta(33810),
        tcaAdaptorEthPortBySizeSmallStatsLessThan64DeltaMin(33811),
        tcaAdaptorEthPortBySizeSmallStatsLessThan64DeltaMax(33812),
        tcaAdaptorEthPortBySizeSmallStatsLessThan64DeltaAvg(33813),
        tcaAdaptorEthPortBySizeSmallStatsEquals64Delta(33820),
        tcaAdaptorEthPortBySizeSmallStatsEquals64DeltaMin(33821),
        tcaAdaptorEthPortBySizeSmallStatsEquals64DeltaMax(33822),
        tcaAdaptorEthPortBySizeSmallStatsEquals64DeltaAvg(33823),
        tcaAdaptorEthPortBySizeSmallStatsLessThan128Delta(33830),
        tcaAdaptorEthPortBySizeSmallStatsLessThan128DeltaMin(33831),
        tcaAdaptorEthPortBySizeSmallStatsLessThan128DeltaMax(33832),
        tcaAdaptorEthPortBySizeSmallStatsLessThan128DeltaAvg(33833),
        tcaAdaptorEthPortBySizeSmallStatsLessThan256Delta(33840),
        tcaAdaptorEthPortBySizeSmallStatsLessThan256DeltaMin(33841),
        tcaAdaptorEthPortBySizeSmallStatsLessThan256DeltaMax(33842),
        tcaAdaptorEthPortBySizeSmallStatsLessThan256DeltaAvg(33843),
        tcaAdaptorEthPortBySizeSmallStatsLessThan512Delta(33850),
        tcaAdaptorEthPortBySizeSmallStatsLessThan512DeltaMin(33851),
        tcaAdaptorEthPortBySizeSmallStatsLessThan512DeltaMax(33852),
        tcaAdaptorEthPortBySizeSmallStatsLessThan512DeltaAvg(33853),
        tcaAdaptorEthPortBySizeSmallStatsLessThan1024Delta(33860),
        tcaAdaptorEthPortBySizeSmallStatsLessThan1024DeltaMin(33861),
        tcaAdaptorEthPortBySizeSmallStatsLessThan1024DeltaMax(33862),
        tcaAdaptorEthPortBySizeSmallStatsLessThan1024DeltaAvg(33863),
        tcaAdaptorEthPortBySizeLargeStatsLessThanOrEqualTo1518Delta(33875),
        tcaAdaptorEthPortBySizeLargeStatsLessThanOrEqualTo1518DeltaMin(33876),
        tcaAdaptorEthPortBySizeLargeStatsLessThanOrEqualTo1518DeltaMax(33877),
        tcaAdaptorEthPortBySizeLargeStatsLessThanOrEqualTo1518DeltaAvg(33878),
        tcaAdaptorEthPortBySizeLargeStatsLessThan2048Delta(33885),
        tcaAdaptorEthPortBySizeLargeStatsLessThan2048DeltaMin(33886),
        tcaAdaptorEthPortBySizeLargeStatsLessThan2048DeltaMax(33887),
        tcaAdaptorEthPortBySizeLargeStatsLessThan2048DeltaAvg(33888),
        tcaAdaptorEthPortBySizeLargeStatsLessThan4096Delta(33895),
        tcaAdaptorEthPortBySizeLargeStatsLessThan4096DeltaMin(33896),
        tcaAdaptorEthPortBySizeLargeStatsLessThan4096DeltaMax(33897),
        tcaAdaptorEthPortBySizeLargeStatsLessThan4096DeltaAvg(33898),
        tcaAdaptorEthPortBySizeLargeStatsLessThan8192Delta(33905),
        tcaAdaptorEthPortBySizeLargeStatsLessThan8192DeltaMin(33906),
        tcaAdaptorEthPortBySizeLargeStatsLessThan8192DeltaMax(33907),
        tcaAdaptorEthPortBySizeLargeStatsLessThan8192DeltaAvg(33908),
        tcaAdaptorEthPortBySizeLargeStatsLessThan9216Delta(33915),
        tcaAdaptorEthPortBySizeLargeStatsLessThan9216DeltaMin(33916),
        tcaAdaptorEthPortBySizeLargeStatsLessThan9216DeltaMax(33917),
        tcaAdaptorEthPortBySizeLargeStatsLessThan9216DeltaAvg(33918),
        tcaAdaptorEthPortBySizeLargeStatsGreaterThanOrEqualTo9216Delta(33925),
        tcaAdaptorEthPrtBySizeLargeStatsGreaterThanOrEqualTo9216DeltaMin(33926),
        tcaAdaptorEthPrtBySizeLargeStatsGreaterThanOrEqualTo9216DeltaMax(33927),
        tcaAdaptorEthPrtBySizeLargeStatsGreaterThanOrEqualTo9216DeltaAvg(33928),
        tcaAdaptorEthPortOutsizedStatsOversizedPacketsDelta(33940),
        tcaAdaptorEthPortOutsizedStatsOversizedPacketsDeltaMin(33941),
        tcaAdaptorEthPortOutsizedStatsOversizedPacketsDeltaMax(33942),
        tcaAdaptorEthPortOutsizedStatsOversizedPacketsDeltaAvg(33943),
        tcaAdaptorEthPortOutsizedStatsOversizedGoodCrcPacketsDelta(33950),
        tcaAdaptorEthPortOutsizedStatsOversizedGoodCrcPacketsDeltaMin(33951),
        tcaAdaptorEthPortOutsizedStatsOversizedGoodCrcPacketsDeltaMax(33952),
        tcaAdaptorEthPortOutsizedStatsOversizedGoodCrcPacketsDeltaAvg(33953),
        tcaAdaptorEthPortOutsizedStatsOversizedBadCrcPacketsDelta(33960),
        tcaAdaptorEthPortOutsizedStatsOversizedBadCrcPacketsDeltaMin(33961),
        tcaAdaptorEthPortOutsizedStatsOversizedBadCrcPacketsDeltaMax(33962),
        tcaAdaptorEthPortOutsizedStatsOversizedBadCrcPacketsDeltaAvg(33963),
        tcaAdaptorEthPortOutsizedStatsUndersizedGoodCrcPacketsDelta(33970),
        tcaAdaptorEthPortOutsizedStatsUndersizedGoodCrcPacketsDeltaMin(33971),
        tcaAdaptorEthPortOutsizedStatsUndersizedGoodCrcPacketsDeltaMax(33972),
        tcaAdaptorEthPortOutsizedStatsUndersizedGoodCrcPacketsDeltaAvg(33973),
        tcaAdaptorEthPortOutsizedStatsUndersizedBadCrcPacketsDelta(33980),
        tcaAdaptorEthPortOutsizedStatsUndersizedBadCrcPacketsDeltaMin(33981),
        tcaAdaptorEthPortOutsizedStatsUndersizedBadCrcPacketsDeltaMax(33982),
        tcaAdaptorEthPortOutsizedStatsUndersizedBadCrcPacketsDeltaAvg(33983),
        tcaAdaptorEthPortMcastStatsUnicastPacketsDelta(33995),
        tcaAdaptorEthPortMcastStatsUnicastPacketsDeltaMin(33996),
        tcaAdaptorEthPortMcastStatsUnicastPacketsDeltaMax(33997),
        tcaAdaptorEthPortMcastStatsUnicastPacketsDeltaAvg(33998),
        tcaAdaptorEthPortMcastStatsMulticastPacketsDelta(34005),
        tcaAdaptorEthPortMcastStatsMulticastPacketsDeltaMin(34006),
        tcaAdaptorEthPortMcastStatsMulticastPacketsDeltaMax(34007),
        tcaAdaptorEthPortMcastStatsMulticastPacketsDeltaAvg(34008),
        tcaAdaptorEthPortMcastStatsBroadcastPacketsDelta(34015),
        tcaAdaptorEthPortMcastStatsBroadcastPacketsDeltaMin(34016),
        tcaAdaptorEthPortMcastStatsBroadcastPacketsDeltaMax(34017),
        tcaAdaptorEthPortMcastStatsBroadcastPacketsDeltaAvg(34018),
        tcaAdaptorEthPortErrStatsMacDiscardedPacketsDelta(34030),
        tcaAdaptorEthPortErrStatsMacDiscardedPacketsDeltaMin(34031),
        tcaAdaptorEthPortErrStatsMacDiscardedPacketsDeltaMax(34032),
        tcaAdaptorEthPortErrStatsMacDiscardedPacketsDeltaAvg(34033),
        tcaAdaptorEthPortErrStatsBadCrcPacketsDelta(34040),
        tcaAdaptorEthPortErrStatsBadCrcPacketsDeltaMin(34041),
        tcaAdaptorEthPortErrStatsBadCrcPacketsDeltaMax(34042),
        tcaAdaptorEthPortErrStatsBadCrcPacketsDeltaAvg(34043),
        tcaAdaptorEthPortErrStatsBadLengthPacketsDelta(34050),
        tcaAdaptorEthPortErrStatsBadLengthPacketsDeltaMin(34051),
        tcaAdaptorEthPortErrStatsBadLengthPacketsDeltaMax(34052),
        tcaAdaptorEthPortErrStatsBadLengthPacketsDeltaAvg(34053),
        tcaAdaptorFcPortStatsRxFramesDelta(34064),
        tcaAdaptorFcPortStatsRxFramesDeltaMin(34065),
        tcaAdaptorFcPortStatsRxFramesDeltaMax(34066),
        tcaAdaptorFcPortStatsRxFramesDeltaAvg(34067),
        tcaAdaptorFcPortStatsTxFramesDelta(34074),
        tcaAdaptorFcPortStatsTxFramesDeltaMin(34075),
        tcaAdaptorFcPortStatsTxFramesDeltaMax(34076),
        tcaAdaptorFcPortStatsTxFramesDeltaAvg(34077),
        tcaAdaptorFcPortStatsRxBadFramesDelta(34084),
        tcaAdaptorFcPortStatsRxBadFramesDeltaMin(34085),
        tcaAdaptorFcPortStatsRxBadFramesDeltaMax(34086),
        tcaAdaptorFcPortStatsRxBadFramesDeltaAvg(34087),
        tcaAdaptorFcPortStatsTxBadFramesDelta(34094),
        tcaAdaptorFcPortStatsTxBadFramesDeltaMin(34095),
        tcaAdaptorFcPortStatsTxBadFramesDeltaMax(34096),
        tcaAdaptorFcPortStatsTxBadFramesDeltaAvg(34097),
        tcaAdaptorVnicStatsPacketsTxDelta(34108),
        tcaAdaptorVnicStatsPacketsTxDeltaMin(34109),
        tcaAdaptorVnicStatsPacketsTxDeltaMax(34110),
        tcaAdaptorVnicStatsPacketsTxDeltaAvg(34111),
        tcaAdaptorVnicStatsPacketsRxDelta(34118),
        tcaAdaptorVnicStatsPacketsRxDeltaMin(34119),
        tcaAdaptorVnicStatsPacketsRxDeltaMax(34120),
        tcaAdaptorVnicStatsPacketsRxDeltaAvg(34121),
        tcaAdaptorVnicStatsBytesTxDelta(34128),
        tcaAdaptorVnicStatsBytesTxDeltaMin(34129),
        tcaAdaptorVnicStatsBytesTxDeltaMax(34130),
        tcaAdaptorVnicStatsBytesTxDeltaAvg(34131),
        tcaAdaptorVnicStatsBytesRxDelta(34138),
        tcaAdaptorVnicStatsBytesRxDeltaMin(34139),
        tcaAdaptorVnicStatsBytesRxDeltaMax(34140),
        tcaAdaptorVnicStatsBytesRxDeltaAvg(34141),
        tcaAdaptorVnicStatsErrorsTxDelta(34148),
        tcaAdaptorVnicStatsErrorsTxDeltaMin(34149),
        tcaAdaptorVnicStatsErrorsTxDeltaMax(34150),
        tcaAdaptorVnicStatsErrorsTxDeltaAvg(34151),
        tcaAdaptorVnicStatsErrorsRxDelta(34158),
        tcaAdaptorVnicStatsErrorsRxDeltaMin(34159),
        tcaAdaptorVnicStatsErrorsRxDeltaMax(34160),
        tcaAdaptorVnicStatsErrorsRxDeltaAvg(34161),
        tcaAdaptorVnicStatsDroppedTxDelta(34168),
        tcaAdaptorVnicStatsDroppedTxDeltaMin(34169),
        tcaAdaptorVnicStatsDroppedTxDeltaMax(34170),
        tcaAdaptorVnicStatsDroppedTxDeltaAvg(34171),
        tcaAdaptorVnicStatsDroppedRxDelta(34178),
        tcaAdaptorVnicStatsDroppedRxDeltaMin(34179),
        tcaAdaptorVnicStatsDroppedRxDeltaMax(34180),
        tcaAdaptorVnicStatsDroppedRxDeltaAvg(34181),
        tcaAdaptorFcIffc4StatsInputRequestsDelta(34192),
        tcaAdaptorFcIffc4StatsInputRequestsDeltaMin(34193),
        tcaAdaptorFcIffc4StatsInputRequestsDeltaMax(34194),
        tcaAdaptorFcIffc4StatsInputRequestsDeltaAvg(34195),
        tcaAdaptorFcIffc4StatsOutputRequestsDelta(34202),
        tcaAdaptorFcIffc4StatsOutputRequestsDeltaMin(34203),
        tcaAdaptorFcIffc4StatsOutputRequestsDeltaMax(34204),
        tcaAdaptorFcIffc4StatsOutputRequestsDeltaAvg(34205),
        tcaAdaptorFcIffc4StatsControlRequestsDelta(34212),
        tcaAdaptorFcIffc4StatsControlRequestsDeltaMin(34213),
        tcaAdaptorFcIffc4StatsControlRequestsDeltaMax(34214),
        tcaAdaptorFcIffc4StatsControlRequestsDeltaAvg(34215),
        tcaAdaptorFcIffc4StatsInputMegabytesDelta(34222),
        tcaAdaptorFcIffc4StatsInputMegabytesDeltaMin(34223),
        tcaAdaptorFcIffc4StatsInputMegabytesDeltaMax(34224),
        tcaAdaptorFcIffc4StatsInputMegabytesDeltaAvg(34225),
        tcaAdaptorFcIffc4StatsOutputMegabytesDelta(34232),
        tcaAdaptorFcIffc4StatsOutputMegabytesDeltaMin(34233),
        tcaAdaptorFcIffc4StatsOutputMegabytesDeltaMax(34234),
        tcaAdaptorFcIffc4StatsOutputMegabytesDeltaAvg(34235),
        tcaAdaptorMenloBaseErrorStatsCorrectableErrorsDelta(34246),
        tcaAdaptorMenloBaseErrorStatsCorrectableErrorsDeltaMin(34247),
        tcaAdaptorMenloBaseErrorStatsCorrectableErrorsDeltaMax(34248),
        tcaAdaptorMenloBaseErrorStatsCorrectableErrorsDeltaAvg(34249),
        tcaAdaptorMenloBaseErrorStatsUncorrectableErrorsDelta(34256),
        tcaAdaptorMenloBaseErrorStatsUncorrectableErrorsDeltaMin(34257),
        tcaAdaptorMenloBaseErrorStatsUncorrectableErrorsDeltaMax(34258),
        tcaAdaptorMenloBaseErrorStatsUncorrectableErrorsDeltaAvg(34259),
        tcaAdaptorMenloMcpuStatsDropAclDelta(34271),
        tcaAdaptorMenloMcpuStatsDropAclDeltaMin(34272),
        tcaAdaptorMenloMcpuStatsDropAclDeltaMax(34273),
        tcaAdaptorMenloMcpuStatsDropAclDeltaAvg(34274),
        tcaAdaptorMenloMcpuStatsDropOverrunDelta(34281),
        tcaAdaptorMenloMcpuStatsDropOverrunDeltaMin(34282),
        tcaAdaptorMenloMcpuStatsDropOverrunDeltaMax(34283),
        tcaAdaptorMenloMcpuStatsDropOverrunDeltaAvg(34284),
        tcaAdaptorMenloMcpuStatsDropRuntDelta(34291),
        tcaAdaptorMenloMcpuStatsDropRuntDeltaMin(34292),
        tcaAdaptorMenloMcpuStatsDropRuntDeltaMax(34293),
        tcaAdaptorMenloMcpuStatsDropRuntDeltaAvg(34294),
        tcaAdaptorMenloMcpuStatsTruncateOverrunDelta(34301),
        tcaAdaptorMenloMcpuStatsTruncateOverrunDeltaMin(34302),
        tcaAdaptorMenloMcpuStatsTruncateOverrunDeltaMax(34303),
        tcaAdaptorMenloMcpuStatsTruncateOverrunDeltaAvg(34304),
        tcaAdaptorMenloMcpuErrorStatsCorrectableErrorsDelta(34316),
        tcaAdaptorMenloMcpuErrorStatsCorrectableErrorsDeltaMin(34317),
        tcaAdaptorMenloMcpuErrorStatsCorrectableErrorsDeltaMax(34318),
        tcaAdaptorMenloMcpuErrorStatsCorrectableErrorsDeltaAvg(34319),
        tcaAdaptorMenloMcpuErrorStatsPopErrorsDelta(34326),
        tcaAdaptorMenloMcpuErrorStatsPopErrorsDeltaMin(34327),
        tcaAdaptorMenloMcpuErrorStatsPopErrorsDeltaMax(34328),
        tcaAdaptorMenloMcpuErrorStatsPopErrorsDeltaAvg(34329),
        tcaAdaptorMenloMcpuErrorStatsPushErrorsDelta(34336),
        tcaAdaptorMenloMcpuErrorStatsPushErrorsDeltaMin(34337),
        tcaAdaptorMenloMcpuErrorStatsPushErrorsDeltaMax(34338),
        tcaAdaptorMenloMcpuErrorStatsPushErrorsDeltaAvg(34339),
        tcaAdaptorMenloMcpuErrorStatsUncorrectableErrorsDelta(34346),
        tcaAdaptorMenloMcpuErrorStatsUncorrectableErrorsDeltaMin(34347),
        tcaAdaptorMenloMcpuErrorStatsUncorrectableErrorsDeltaMax(34348),
        tcaAdaptorMenloMcpuErrorStatsUncorrectableErrorsDeltaAvg(34349),
        tcaAdaptorMenloEthStatsDropOverrunDelta(34361),
        tcaAdaptorMenloEthStatsDropOverrunDeltaMin(34362),
        tcaAdaptorMenloEthStatsDropOverrunDeltaMax(34363),
        tcaAdaptorMenloEthStatsDropOverrunDeltaAvg(34364),
        tcaAdaptorMenloEthStatsDropRuntDelta(34371),
        tcaAdaptorMenloEthStatsDropRuntDeltaMin(34372),
        tcaAdaptorMenloEthStatsDropRuntDeltaMax(34373),
        tcaAdaptorMenloEthStatsDropRuntDeltaAvg(34374),
        tcaAdaptorMenloEthStatsTruncateOverrunDelta(34381),
        tcaAdaptorMenloEthStatsTruncateOverrunDeltaMin(34382),
        tcaAdaptorMenloEthStatsTruncateOverrunDeltaMax(34383),
        tcaAdaptorMenloEthStatsTruncateOverrunDeltaAvg(34384),
        tcaAdaptorMenloEthErrorStatsCorrectableErrorsDelta(34396),
        tcaAdaptorMenloEthErrorStatsCorrectableErrorsDeltaMin(34397),
        tcaAdaptorMenloEthErrorStatsCorrectableErrorsDeltaMax(34398),
        tcaAdaptorMenloEthErrorStatsCorrectableErrorsDeltaAvg(34399),
        tcaAdaptorMenloEthErrorStatsDropAclDelta(34406),
        tcaAdaptorMenloEthErrorStatsDropAclDeltaMin(34407),
        tcaAdaptorMenloEthErrorStatsDropAclDeltaMax(34408),
        tcaAdaptorMenloEthErrorStatsDropAclDeltaAvg(34409),
        tcaAdaptorMenloEthErrorStatsPopErrorsDelta(34416),
        tcaAdaptorMenloEthErrorStatsPopErrorsDeltaMin(34417),
        tcaAdaptorMenloEthErrorStatsPopErrorsDeltaMax(34418),
        tcaAdaptorMenloEthErrorStatsPopErrorsDeltaAvg(34419),
        tcaAdaptorMenloEthErrorStatsPushErrorsDelta(34426),
        tcaAdaptorMenloEthErrorStatsPushErrorsDeltaMin(34427),
        tcaAdaptorMenloEthErrorStatsPushErrorsDeltaMax(34428),
        tcaAdaptorMenloEthErrorStatsPushErrorsDeltaAvg(34429),
        tcaAdaptorMenloEthErrorStatsUncorrectableErrorsDelta(34436),
        tcaAdaptorMenloEthErrorStatsUncorrectableErrorsDeltaMin(34437),
        tcaAdaptorMenloEthErrorStatsUncorrectableErrorsDeltaMax(34438),
        tcaAdaptorMenloEthErrorStatsUncorrectableErrorsDeltaAvg(34439),
        tcaAdaptorMenloFcStatsDropAclDelta(34451),
        tcaAdaptorMenloFcStatsDropAclDeltaMin(34452),
        tcaAdaptorMenloFcStatsDropAclDeltaMax(34453),
        tcaAdaptorMenloFcStatsDropAclDeltaAvg(34454),
        tcaAdaptorMenloFcStatsDropOverrunDelta(34461),
        tcaAdaptorMenloFcStatsDropOverrunDeltaMin(34462),
        tcaAdaptorMenloFcStatsDropOverrunDeltaMax(34463),
        tcaAdaptorMenloFcStatsDropOverrunDeltaAvg(34464),
        tcaAdaptorMenloFcStatsDropRuntDelta(34471),
        tcaAdaptorMenloFcStatsDropRuntDeltaMin(34472),
        tcaAdaptorMenloFcStatsDropRuntDeltaMax(34473),
        tcaAdaptorMenloFcStatsDropRuntDeltaAvg(34474),
        tcaAdaptorMenloFcStatsTruncateOverrunDelta(34481),
        tcaAdaptorMenloFcStatsTruncateOverrunDeltaMin(34482),
        tcaAdaptorMenloFcStatsTruncateOverrunDeltaMax(34483),
        tcaAdaptorMenloFcStatsTruncateOverrunDeltaAvg(34484),
        tcaAdaptorMenloFcErrorStatsCorrectableErrorsDelta(34496),
        tcaAdaptorMenloFcErrorStatsCorrectableErrorsDeltaMin(34497),
        tcaAdaptorMenloFcErrorStatsCorrectableErrorsDeltaMax(34498),
        tcaAdaptorMenloFcErrorStatsCorrectableErrorsDeltaAvg(34499),
        tcaAdaptorMenloFcErrorStatsPopErrorsDelta(34506),
        tcaAdaptorMenloFcErrorStatsPopErrorsDeltaMin(34507),
        tcaAdaptorMenloFcErrorStatsPopErrorsDeltaMax(34508),
        tcaAdaptorMenloFcErrorStatsPopErrorsDeltaAvg(34509),
        tcaAdaptorMenloFcErrorStatsPushErrorsDelta(34516),
        tcaAdaptorMenloFcErrorStatsPushErrorsDeltaMin(34517),
        tcaAdaptorMenloFcErrorStatsPushErrorsDeltaMax(34518),
        tcaAdaptorMenloFcErrorStatsPushErrorsDeltaAvg(34519),
        tcaAdaptorMenloFcErrorStatsUncorrectableErrorsDelta(34526),
        tcaAdaptorMenloFcErrorStatsUncorrectableErrorsDeltaMin(34527),
        tcaAdaptorMenloFcErrorStatsUncorrectableErrorsDeltaMax(34528),
        tcaAdaptorMenloFcErrorStatsUncorrectableErrorsDeltaAvg(34529),
        tcaAdaptorMenloqstatsDropOverrunN0Delta(34542),
        tcaAdaptorMenloqstatsDropOverrunN0DeltaMin(34543),
        tcaAdaptorMenloqstatsDropOverrunN0DeltaMax(34544),
        tcaAdaptorMenloqstatsDropOverrunN0DeltaAvg(34545),
        tcaAdaptorMenloqstatsDropOverrunN1Delta(34552),
        tcaAdaptorMenloqstatsDropOverrunN1DeltaMin(34553),
        tcaAdaptorMenloqstatsDropOverrunN1DeltaMax(34554),
        tcaAdaptorMenloqstatsDropOverrunN1DeltaAvg(34555),
        tcaAdaptorMenloqstatsTruncateOverrunN0Delta(34562),
        tcaAdaptorMenloqstatsTruncateOverrunN0DeltaMin(34563),
        tcaAdaptorMenloqstatsTruncateOverrunN0DeltaMax(34564),
        tcaAdaptorMenloqstatsTruncateOverrunN0DeltaAvg(34565),
        tcaAdaptorMenloqstatsTruncateOverrunN1Delta(34572),
        tcaAdaptorMenloqstatsTruncateOverrunN1DeltaMin(34573),
        tcaAdaptorMenloqstatsTruncateOverrunN1DeltaMax(34574),
        tcaAdaptorMenloqstatsTruncateOverrunN1DeltaAvg(34575),
        tcaAdaptorMenloqerrorStatsCorrectableErrorsDelta(34588),
        tcaAdaptorMenloqerrorStatsCorrectableErrorsDeltaMin(34589),
        tcaAdaptorMenloqerrorStatsCorrectableErrorsDeltaMax(34590),
        tcaAdaptorMenloqerrorStatsCorrectableErrorsDeltaAvg(34591),
        tcaAdaptorMenloqerrorStatsPopErrorsDelta(34598),
        tcaAdaptorMenloqerrorStatsPopErrorsDeltaMin(34599),
        tcaAdaptorMenloqerrorStatsPopErrorsDeltaMax(34600),
        tcaAdaptorMenloqerrorStatsPopErrorsDeltaAvg(34601),
        tcaAdaptorMenloqerrorStatsPushErrorsDelta(34608),
        tcaAdaptorMenloqerrorStatsPushErrorsDeltaMin(34609),
        tcaAdaptorMenloqerrorStatsPushErrorsDeltaMax(34610),
        tcaAdaptorMenloqerrorStatsPushErrorsDeltaAvg(34611),
        tcaAdaptorMenloqerrorStatsUncorrectableErrorsDelta(34618),
        tcaAdaptorMenloqerrorStatsUncorrectableErrorsDeltaMin(34619),
        tcaAdaptorMenloqerrorStatsUncorrectableErrorsDeltaMax(34620),
        tcaAdaptorMenloqerrorStatsUncorrectableErrorsDeltaAvg(34621),
        tcaAdaptorMenloNetEgStatsLearnReqDropDelta(34633),
        tcaAdaptorMenloNetEgStatsLearnReqDropDeltaMin(34634),
        tcaAdaptorMenloNetEgStatsLearnReqDropDeltaMax(34635),
        tcaAdaptorMenloNetEgStatsLearnReqDropDeltaAvg(34636),
        tcaAdaptorMenloNetEgStatsDropCmdDelta(34643),
        tcaAdaptorMenloNetEgStatsDropCmdDeltaMin(34644),
        tcaAdaptorMenloNetEgStatsDropCmdDeltaMax(34645),
        tcaAdaptorMenloNetEgStatsDropCmdDeltaAvg(34646),
        tcaAdaptorMenloNetEgStatsDropLifCfgInvalidDelta(34653),
        tcaAdaptorMenloNetEgStatsDropLifCfgInvalidDeltaMin(34654),
        tcaAdaptorMenloNetEgStatsDropLifCfgInvalidDeltaMax(34655),
        tcaAdaptorMenloNetEgStatsDropLifCfgInvalidDeltaAvg(34656),
        tcaAdaptorMenloNetEgStatsDropLifMapNoHitDelta(34663),
        tcaAdaptorMenloNetEgStatsDropLifMapNoHitDeltaMin(34664),
        tcaAdaptorMenloNetEgStatsDropLifMapNoHitDeltaMax(34665),
        tcaAdaptorMenloNetEgStatsDropLifMapNoHitDeltaAvg(34666),
        tcaAdaptorMenloNetEgStatsDropSrcBindDelta(34673),
        tcaAdaptorMenloNetEgStatsDropSrcBindDeltaMin(34674),
        tcaAdaptorMenloNetEgStatsDropSrcBindDeltaMax(34675),
        tcaAdaptorMenloNetEgStatsDropSrcBindDeltaAvg(34676),
        tcaAdaptorMenloNetInStatsFwdLookupNoHitDelta(34688),
        tcaAdaptorMenloNetInStatsFwdLookupNoHitDeltaMin(34689),
        tcaAdaptorMenloNetInStatsFwdLookupNoHitDeltaMax(34690),
        tcaAdaptorMenloNetInStatsFwdLookupNoHitDeltaAvg(34691),
        tcaAdaptorMenloNetInStatsDropFcMulticastDelta(34698),
        tcaAdaptorMenloNetInStatsDropFcMulticastDeltaMin(34699),
        tcaAdaptorMenloNetInStatsDropFcMulticastDeltaMax(34700),
        tcaAdaptorMenloNetInStatsDropFcMulticastDeltaAvg(34701),
        tcaAdaptorMenloNetInStatsDropFcLifInvalidDelta(34708),
        tcaAdaptorMenloNetInStatsDropFcLifInvalidDeltaMin(34709),
        tcaAdaptorMenloNetInStatsDropFcLifInvalidDeltaMax(34710),
        tcaAdaptorMenloNetInStatsDropFcLifInvalidDeltaAvg(34711),
        tcaAdaptorMenloNetInStatsDropNullPifDelta(34718),
        tcaAdaptorMenloNetInStatsDropNullPifDeltaMin(34719),
        tcaAdaptorMenloNetInStatsDropNullPifDeltaMax(34720),
        tcaAdaptorMenloNetInStatsDropNullPifDeltaAvg(34721),
        tcaAdaptorMenloHostPortStatsRxPausecfcdelta(34733),
        tcaAdaptorMenloHostPortStatsRxPausecfcdeltaMin(34734),
        tcaAdaptorMenloHostPortStatsRxPausecfcdeltaMax(34735),
        tcaAdaptorMenloHostPortStatsRxPausecfcdeltaAvg(34736),
        tcaAdaptorMenloHostPortStatsRxPausepfcdelta(34743),
        tcaAdaptorMenloHostPortStatsRxPausepfcdeltaMin(34744),
        tcaAdaptorMenloHostPortStatsRxPausepfcdeltaMax(34745),
        tcaAdaptorMenloHostPortStatsRxPausepfcdeltaAvg(34746),
        tcaAdaptorMenloHostPortStatsTxPausecfcdelta(34753),
        tcaAdaptorMenloHostPortStatsTxPausecfcdeltaMin(34754),
        tcaAdaptorMenloHostPortStatsTxPausecfcdeltaMax(34755),
        tcaAdaptorMenloHostPortStatsTxPausecfcdeltaAvg(34756),
        tcaAdaptorMenloHostPortStatsTxPausepfcdelta(34763),
        tcaAdaptorMenloHostPortStatsTxPausepfcdeltaMin(34764),
        tcaAdaptorMenloHostPortStatsTxPausepfcdeltaMax(34765),
        tcaAdaptorMenloHostPortStatsTxPausepfcdeltaAvg(34766),
        tcaAdaptorMenloDcePortStatsRxPausecfcdelta(34778),
        tcaAdaptorMenloDcePortStatsRxPausecfcdeltaMin(34779),
        tcaAdaptorMenloDcePortStatsRxPausecfcdeltaMax(34780),
        tcaAdaptorMenloDcePortStatsRxPausecfcdeltaAvg(34781),
        tcaAdaptorMenloDcePortStatsRxPausepfcdelta(34788),
        tcaAdaptorMenloDcePortStatsRxPausepfcdeltaMin(34789),
        tcaAdaptorMenloDcePortStatsRxPausepfcdeltaMax(34790),
        tcaAdaptorMenloDcePortStatsRxPausepfcdeltaAvg(34791),
        tcaAdaptorMenloDcePortStatsTxPausecfcdelta(34798),
        tcaAdaptorMenloDcePortStatsTxPausecfcdeltaMin(34799),
        tcaAdaptorMenloDcePortStatsTxPausecfcdeltaMax(34800),
        tcaAdaptorMenloDcePortStatsTxPausecfcdeltaAvg(34801),
        tcaAdaptorMenloDcePortStatsTxPausepfcdelta(34808),
        tcaAdaptorMenloDcePortStatsTxPausepfcdeltaMin(34809),
        tcaAdaptorMenloDcePortStatsTxPausepfcdeltaMax(34810),
        tcaAdaptorMenloDcePortStatsTxPausepfcdeltaAvg(34811),
        tcaAdaptorEtherIfStatsTxBytesDelta(34822),
        tcaAdaptorEtherIfStatsTxBytesDeltaMin(34823),
        tcaAdaptorEtherIfStatsTxBytesDeltaMax(34824),
        tcaAdaptorEtherIfStatsTxBytesDeltaAvg(34825),
        tcaAdaptorEtherIfStatsTxPacketsDelta(34832),
        tcaAdaptorEtherIfStatsTxPacketsDeltaMin(34833),
        tcaAdaptorEtherIfStatsTxPacketsDeltaMax(34834),
        tcaAdaptorEtherIfStatsTxPacketsDeltaAvg(34835),
        tcaAdaptorEtherIfStatsTxErrorsDelta(34842),
        tcaAdaptorEtherIfStatsTxErrorsDeltaMin(34843),
        tcaAdaptorEtherIfStatsTxErrorsDeltaMax(34844),
        tcaAdaptorEtherIfStatsTxErrorsDeltaAvg(34845),
        tcaAdaptorEtherIfStatsTxDroppedDelta(34852),
        tcaAdaptorEtherIfStatsTxDroppedDeltaMin(34853),
        tcaAdaptorEtherIfStatsTxDroppedDeltaMax(34854),
        tcaAdaptorEtherIfStatsTxDroppedDeltaAvg(34855),
        tcaAdaptorEtherIfStatsRxBytesDelta(34862),
        tcaAdaptorEtherIfStatsRxBytesDeltaMin(34863),
        tcaAdaptorEtherIfStatsRxBytesDeltaMax(34864),
        tcaAdaptorEtherIfStatsRxBytesDeltaAvg(34865),
        tcaAdaptorEtherIfStatsRxPacketsDelta(34872),
        tcaAdaptorEtherIfStatsRxPacketsDeltaMin(34873),
        tcaAdaptorEtherIfStatsRxPacketsDeltaMax(34874),
        tcaAdaptorEtherIfStatsRxPacketsDeltaAvg(34875),
        tcaAdaptorEtherIfStatsRxErrorsDelta(34882),
        tcaAdaptorEtherIfStatsRxErrorsDeltaMin(34883),
        tcaAdaptorEtherIfStatsRxErrorsDeltaMax(34884),
        tcaAdaptorEtherIfStatsRxErrorsDeltaAvg(34885),
        tcaAdaptorEtherIfStatsRxDroppedDelta(34892),
        tcaAdaptorEtherIfStatsRxDroppedDeltaMin(34893),
        tcaAdaptorEtherIfStatsRxDroppedDeltaMax(34894),
        tcaAdaptorEtherIfStatsRxDroppedDeltaAvg(34895),
        tcaAdaptorFcIfFrameStatsTxFramesDelta(34906),
        tcaAdaptorFcIfFrameStatsTxFramesDeltaMin(34907),
        tcaAdaptorFcIfFrameStatsTxFramesDeltaMax(34908),
        tcaAdaptorFcIfFrameStatsTxFramesDeltaAvg(34909),
        tcaAdaptorFcIfFrameStatsRxFramesDelta(34916),
        tcaAdaptorFcIfFrameStatsRxFramesDeltaMin(34917),
        tcaAdaptorFcIfFrameStatsRxFramesDeltaMax(34918),
        tcaAdaptorFcIfFrameStatsRxFramesDeltaAvg(34919),
        tcaAdaptorFcIfFrameStatsErrorFramesDelta(34926),
        tcaAdaptorFcIfFrameStatsErrorFramesDeltaMin(34927),
        tcaAdaptorFcIfFrameStatsErrorFramesDeltaMax(34928),
        tcaAdaptorFcIfFrameStatsErrorFramesDeltaAvg(34929),
        tcaAdaptorFcIfFrameStatsDumpedFramesDelta(34936),
        tcaAdaptorFcIfFrameStatsDumpedFramesDeltaMin(34937),
        tcaAdaptorFcIfFrameStatsDumpedFramesDeltaMax(34938),
        tcaAdaptorFcIfFrameStatsDumpedFramesDeltaAvg(34939),
        tcaAdaptorFcIfEventStatsLipCountDelta(34950),
        tcaAdaptorFcIfEventStatsLipCountDeltaMin(34951),
        tcaAdaptorFcIfEventStatsLipCountDeltaMax(34952),
        tcaAdaptorFcIfEventStatsLipCountDeltaAvg(34953),
        tcaAdaptorFcIfEventStatsInvalidcrccountDelta(34960),
        tcaAdaptorFcIfEventStatsInvalidcrccountDeltaMin(34961),
        tcaAdaptorFcIfEventStatsInvalidcrccountDeltaMax(34962),
        tcaAdaptorFcIfEventStatsInvalidcrccountDeltaAvg(34963),
        tcaAdaptorFcIfEventStatsNoscountDelta(34970),
        tcaAdaptorFcIfEventStatsNoscountDeltaMin(34971),
        tcaAdaptorFcIfEventStatsNoscountDeltaMax(34972),
        tcaAdaptorFcIfEventStatsNoscountDeltaAvg(34973),
        tcaAdaptorFcIfEventStatsLinkFailureCountDelta(34980),
        tcaAdaptorFcIfEventStatsLinkFailureCountDeltaMin(34981),
        tcaAdaptorFcIfEventStatsLinkFailureCountDeltaMax(34982),
        tcaAdaptorFcIfEventStatsLinkFailureCountDeltaAvg(34983),
        tcaAdaptorFcIfEventStatsLossOfSyncCountDelta(34990),
        tcaAdaptorFcIfEventStatsLossOfSyncCountDeltaMin(34991),
        tcaAdaptorFcIfEventStatsLossOfSyncCountDeltaMax(34992),
        tcaAdaptorFcIfEventStatsLossOfSyncCountDeltaAvg(34993),
        tcaAdaptorFcIfEventStatsLossOfSignalCountDelta(35000),
        tcaAdaptorFcIfEventStatsLossOfSignalCountDeltaMin(35001),
        tcaAdaptorFcIfEventStatsLossOfSignalCountDeltaMax(35002),
        tcaAdaptorFcIfEventStatsLossOfSignalCountDeltaAvg(35003),
        tcaAdaptorFcIfEventStatsSeqProtocolErrCountDelta(35010),
        tcaAdaptorFcIfEventStatsSeqProtocolErrCountDeltaMin(35011),
        tcaAdaptorFcIfEventStatsSeqProtocolErrCountDeltaMax(35012),
        tcaAdaptorFcIfEventStatsSeqProtocolErrCountDeltaAvg(35013),
        tcaAdaptorFcIfEventStatsSecondsSinceLastResetDelta(35020),
        tcaAdaptorFcIfEventStatsSecondsSinceLastResetDeltaMin(35021),
        tcaAdaptorFcIfEventStatsSecondsSinceLastResetDeltaMax(35022),
        tcaAdaptorFcIfEventStatsSecondsSinceLastResetDeltaAvg(35023),
        tcaSwEnvStatsMainBoardOutlet1(35166),
        tcaSwEnvStatsMainBoardOutlet1Min(35168),
        tcaSwEnvStatsMainBoardOutlet1Max(35169),
        tcaSwEnvStatsMainBoardOutlet1Avg(35170),
        tcaSwEnvStatsMainBoardOutlet2(35174),
        tcaSwEnvStatsMainBoardOutlet2Min(35176),
        tcaSwEnvStatsMainBoardOutlet2Max(35177),
        tcaSwEnvStatsMainBoardOutlet2Avg(35178),
        tcaSwEnvStatsFanCtrlrInlet1(35198),
        tcaSwEnvStatsFanCtrlrInlet1Min(35200),
        tcaSwEnvStatsFanCtrlrInlet1Max(35201),
        tcaSwEnvStatsFanCtrlrInlet1Avg(35202),
        tcaSwEnvStatsFanCtrlrInlet2(35206),
        tcaSwEnvStatsFanCtrlrInlet2Min(35208),
        tcaSwEnvStatsFanCtrlrInlet2Max(35209),
        tcaSwEnvStatsFanCtrlrInlet2Avg(35210),
        tcaSwEnvStatsFanCtrlrInlet3(35214),
        tcaSwEnvStatsFanCtrlrInlet3Min(35216),
        tcaSwEnvStatsFanCtrlrInlet3Max(35217),
        tcaSwEnvStatsFanCtrlrInlet3Avg(35218),
        tcaSwEnvStatsFanCtrlrInlet4(35222),
        tcaSwEnvStatsFanCtrlrInlet4Min(35224),
        tcaSwEnvStatsFanCtrlrInlet4Max(35225),
        tcaSwEnvStatsFanCtrlrInlet4Avg(35226),
        tcaSwSystemStatsMemAvailable(35234),
        tcaSwSystemStatsMemAvailableMin(35236),
        tcaSwSystemStatsMemAvailableMax(35237),
        tcaSwSystemStatsMemAvailableAvg(35238),
        tcaSwSystemStatsMemCached(35242),
        tcaSwSystemStatsMemCachedMin(35244),
        tcaSwSystemStatsMemCachedMax(35245),
        tcaSwSystemStatsMemCachedAvg(35246),
        tcaSwSystemStatsLoad(35250),
        tcaSwSystemStatsLoadMin(35252),
        tcaSwSystemStatsLoadMax(35253),
        tcaSwSystemStatsLoadAvg(35254),
        tcaEtherTxStatsTotalBytesDelta(35275),
        tcaEtherTxStatsTotalBytesDeltaMin(35276),
        tcaEtherTxStatsTotalBytesDeltaMax(35277),
        tcaEtherTxStatsTotalBytesDeltaAvg(35278),
        tcaEtherTxStatsTotalPacketsDelta(35285),
        tcaEtherTxStatsTotalPacketsDeltaMin(35286),
        tcaEtherTxStatsTotalPacketsDeltaMax(35287),
        tcaEtherTxStatsTotalPacketsDeltaAvg(35288),
        tcaEtherTxStatsMulticastPacketsDelta(35295),
        tcaEtherTxStatsMulticastPacketsDeltaMin(35296),
        tcaEtherTxStatsMulticastPacketsDeltaMax(35297),
        tcaEtherTxStatsMulticastPacketsDeltaAvg(35298),
        tcaEtherTxStatsBroadcastPacketsDelta(35305),
        tcaEtherTxStatsBroadcastPacketsDeltaMin(35306),
        tcaEtherTxStatsBroadcastPacketsDeltaMax(35307),
        tcaEtherTxStatsBroadcastPacketsDeltaAvg(35308),
        tcaEtherTxStatsJumboPacketsDelta(35315),
        tcaEtherTxStatsJumboPacketsDeltaMin(35316),
        tcaEtherTxStatsJumboPacketsDeltaMax(35317),
        tcaEtherTxStatsJumboPacketsDeltaAvg(35318),
        tcaEtherRxStatsTotalBytesDelta(35329),
        tcaEtherRxStatsTotalBytesDeltaMin(35330),
        tcaEtherRxStatsTotalBytesDeltaMax(35331),
        tcaEtherRxStatsTotalBytesDeltaAvg(35332),
        tcaEtherRxStatsTotalPacketsDelta(35339),
        tcaEtherRxStatsTotalPacketsDeltaMin(35340),
        tcaEtherRxStatsTotalPacketsDeltaMax(35341),
        tcaEtherRxStatsTotalPacketsDeltaAvg(35342),
        tcaEtherRxStatsUnicastPacketsDelta(35349),
        tcaEtherRxStatsUnicastPacketsDeltaMin(35350),
        tcaEtherRxStatsUnicastPacketsDeltaMax(35351),
        tcaEtherRxStatsUnicastPacketsDeltaAvg(35352),
        tcaEtherRxStatsMulticastPacketsDelta(35359),
        tcaEtherRxStatsMulticastPacketsDeltaMin(35360),
        tcaEtherRxStatsMulticastPacketsDeltaMax(35361),
        tcaEtherRxStatsMulticastPacketsDeltaAvg(35362),
        tcaEtherRxStatsBroadcastPacketsDelta(35369),
        tcaEtherRxStatsBroadcastPacketsDeltaMin(35370),
        tcaEtherRxStatsBroadcastPacketsDeltaMax(35371),
        tcaEtherRxStatsBroadcastPacketsDeltaAvg(35372),
        tcaEtherRxStatsJumboPacketsDelta(35379),
        tcaEtherRxStatsJumboPacketsDeltaMin(35380),
        tcaEtherRxStatsJumboPacketsDeltaMax(35381),
        tcaEtherRxStatsJumboPacketsDeltaAvg(35382),
        tcaComputeMbPowerStatsConsumedPower(35962),
        tcaComputeMbPowerStatsConsumedPowerMin(35964),
        tcaComputeMbPowerStatsConsumedPowerMax(35965),
        tcaComputeMbPowerStatsConsumedPowerAvg(35966),
        tcaComputeMbTempStatsFmTempSenIo(35974),
        tcaComputeMbTempStatsFmTempSenIoMin(35976),
        tcaComputeMbTempStatsFmTempSenIoMax(35977),
        tcaComputeMbTempStatsFmTempSenIoAvg(35978),
        tcaEquipmentChassisStatsInputPower(36234),
        tcaEquipmentChassisStatsInputPowerMin(36236),
        tcaEquipmentChassisStatsInputPowerMax(36237),
        tcaEquipmentChassisStatsInputPowerAvg(36238),
        tcaEquipmentChassisStatsOutputPower(36242),
        tcaEquipmentChassisStatsOutputPowerMin(36244),
        tcaEquipmentChassisStatsOutputPowerMax(36245),
        tcaEquipmentChassisStatsOutputPowerAvg(36246),
        tcaEquipmentPsuStatsAmbientTemp(36266),
        tcaEquipmentPsuStatsAmbientTempMin(36268),
        tcaEquipmentPsuStatsAmbientTempMax(36269),
        tcaEquipmentPsuStatsAmbientTempAvg(36270),
        tcaEquipmentPsuStatsOutputCurrent(36274),
        tcaEquipmentPsuStatsOutputCurrentMin(36276),
        tcaEquipmentPsuStatsOutputCurrentMax(36277),
        tcaEquipmentPsuStatsOutputCurrentAvg(36278),
        tcaEquipmentPsuStatsOutputPower(36282),
        tcaEquipmentPsuStatsOutputPowerMin(36284),
        tcaEquipmentPsuStatsOutputPowerMax(36285),
        tcaEquipmentPsuStatsOutputPowerAvg(36286),
        tcaEquipmentPsuInputStatsCurrent(36294),
        tcaEquipmentPsuInputStatsCurrentMin(36296),
        tcaEquipmentPsuInputStatsCurrentMax(36297),
        tcaEquipmentPsuInputStatsCurrentAvg(36298),
        tcaEquipmentPsuInputStatsVoltage(36302),
        tcaEquipmentPsuInputStatsVoltageMin(36304),
        tcaEquipmentPsuInputStatsVoltageMax(36305),
        tcaEquipmentPsuInputStatsVoltageAvg(36306),
        tcaEquipmentPsuInputStatsPower(36310),
        tcaEquipmentPsuInputStatsPowerMin(36312),
        tcaEquipmentPsuInputStatsPowerMax(36313),
        tcaEquipmentPsuInputStatsPowerAvg(36314),
        tcaEquipmentFanModuleStatsAmbientTemp(36323),
        tcaEquipmentFanModuleStatsAmbientTempMin(36325),
        tcaEquipmentFanModuleStatsAmbientTempMax(36326),
        tcaEquipmentFanModuleStatsAmbientTempAvg(36327),
        tcaEquipmentFanStatsSpeed(36335),
        tcaEquipmentFanStatsSpeedMin(36337),
        tcaEquipmentFanStatsSpeedMax(36338),
        tcaEquipmentFanStatsSpeedAvg(36339),
        tcaEquipmentPsuStatsOutput12v(37154),
        tcaEquipmentPsuStatsOutput12vMin(37156),
        tcaEquipmentPsuStatsOutput12vMax(37157),
        tcaEquipmentPsuStatsOutput12vAvg(37158),
        tcaEquipmentPsuStatsOutput3v3(37162),
        tcaEquipmentPsuStatsOutput3v3Min(37164),
        tcaEquipmentPsuStatsOutput3v3Max(37165),
        tcaEquipmentPsuStatsOutput3v3Avg(37166),
        tcaEquipmentPsuStatsInput210v(37170),
        tcaEquipmentPsuStatsInput210vMin(37172),
        tcaEquipmentPsuStatsInput210vMax(37173),
        tcaEquipmentPsuStatsInput210vAvg(37174),
        tcaEquipmentIocardStatsAmbientTemp(37269),
        tcaEquipmentIocardStatsAmbientTempMin(37271),
        tcaEquipmentIocardStatsAmbientTempMax(37272),
        tcaEquipmentIocardStatsAmbientTempAvg(37273),
        tcaEtherErrStatsAlignDelta(37313),
        tcaEtherErrStatsAlignDeltaMin(37314),
        tcaEtherErrStatsAlignDeltaMax(37315),
        tcaEtherErrStatsAlignDeltaAvg(37316),
        tcaEtherErrStatsFcsDelta(37323),
        tcaEtherErrStatsFcsDeltaMin(37324),
        tcaEtherErrStatsFcsDeltaMax(37325),
        tcaEtherErrStatsFcsDeltaAvg(37326),
        tcaEtherErrStatsXmitDelta(37333),
        tcaEtherErrStatsXmitDeltaMin(37334),
        tcaEtherErrStatsXmitDeltaMax(37335),
        tcaEtherErrStatsXmitDeltaAvg(37336),
        tcaEtherErrStatsRcvDelta(37343),
        tcaEtherErrStatsRcvDeltaMin(37344),
        tcaEtherErrStatsRcvDeltaMax(37345),
        tcaEtherErrStatsRcvDeltaAvg(37346),
        tcaEtherErrStatsUnderSizeDelta(37353),
        tcaEtherErrStatsUnderSizeDeltaMin(37354),
        tcaEtherErrStatsUnderSizeDeltaMax(37355),
        tcaEtherErrStatsUnderSizeDeltaAvg(37356),
        tcaEtherErrStatsOutDiscardDelta(37363),
        tcaEtherErrStatsOutDiscardDeltaMin(37364),
        tcaEtherErrStatsOutDiscardDeltaMax(37365),
        tcaEtherErrStatsOutDiscardDeltaAvg(37366),
        tcaEtherErrStatsIntMacTxDelta(37383),
        tcaEtherErrStatsIntMacTxDeltaMin(37384),
        tcaEtherErrStatsIntMacTxDeltaMax(37385),
        tcaEtherErrStatsIntMacTxDeltaAvg(37386),
        tcaEtherErrStatsIntMacRxDelta(37393),
        tcaEtherErrStatsIntMacRxDeltaMin(37394),
        tcaEtherErrStatsIntMacRxDeltaMax(37395),
        tcaEtherErrStatsIntMacRxDeltaAvg(37396),
        tcaEtherLossStatsSingleCollisionDelta(37403),
        tcaEtherLossStatsSingleCollisionDeltaMin(37404),
        tcaEtherLossStatsSingleCollisionDeltaMax(37405),
        tcaEtherLossStatsSingleCollisionDeltaAvg(37406),
        tcaEtherLossStatsMultiCollisionDelta(37413),
        tcaEtherLossStatsMultiCollisionDeltaMin(37414),
        tcaEtherLossStatsMultiCollisionDeltaMax(37415),
        tcaEtherLossStatsMultiCollisionDeltaAvg(37416),
        tcaEtherLossStatsLateCollisionDelta(37423),
        tcaEtherLossStatsLateCollisionDeltaMin(37424),
        tcaEtherLossStatsLateCollisionDeltaMax(37425),
        tcaEtherLossStatsLateCollisionDeltaAvg(37426),
        tcaEtherLossStatsCarrierSenseDelta(37443),
        tcaEtherLossStatsCarrierSenseDeltaMin(37444),
        tcaEtherLossStatsCarrierSenseDeltaMax(37445),
        tcaEtherLossStatsCarrierSenseDeltaAvg(37446),
        tcaEtherLossStatsGiantsDelta(37453),
        tcaEtherLossStatsGiantsDeltaMin(37454),
        tcaEtherLossStatsGiantsDeltaMax(37455),
        tcaEtherLossStatsGiantsDeltaAvg(37456),
        tcaEtherLossStatsSymbolDelta(37463),
        tcaEtherLossStatsSymbolDeltaMin(37464),
        tcaEtherLossStatsSymbolDeltaMax(37465),
        tcaEtherLossStatsSymbolDeltaAvg(37466),
        tcaEtherLossStatsSqetestDelta(37473),
        tcaEtherLossStatsSqetestDeltaMin(37474),
        tcaEtherLossStatsSqetestDeltaMax(37475),
        tcaEtherLossStatsSqetestDeltaAvg(37476),
        tcaEtherPauseStatsRecvPauseDelta(37485),
        tcaEtherPauseStatsRecvPauseDeltaMin(37486),
        tcaEtherPauseStatsRecvPauseDeltaMax(37487),
        tcaEtherPauseStatsRecvPauseDeltaAvg(37488),
        tcaEtherPauseStatsXmitPauseDelta(37495),
        tcaEtherPauseStatsXmitPauseDeltaMin(37496),
        tcaEtherPauseStatsXmitPauseDeltaMax(37497),
        tcaEtherPauseStatsXmitPauseDeltaAvg(37498),
        tcaEtherPauseStatsResetsDelta(37505),
        tcaEtherPauseStatsResetsDeltaMin(37506),
        tcaEtherPauseStatsResetsDeltaMax(37507),
        tcaEtherPauseStatsResetsDeltaAvg(37508),
        tcaEtherLossStatsExcessCollisionDelta(37532),
        tcaEtherLossStatsExcessCollisionDeltaMin(37533),
        tcaEtherLossStatsExcessCollisionDeltaMax(37534),
        tcaEtherLossStatsExcessCollisionDeltaAvg(37535),
        tcaEtherTxStatsUnicastPacketsDelta(37543),
        tcaEtherTxStatsUnicastPacketsDeltaMin(37544),
        tcaEtherTxStatsUnicastPacketsDeltaMax(37545),
        tcaEtherTxStatsUnicastPacketsDeltaAvg(37546),
        tcaEtherErrStatsDeferredTxDelta(37553),
        tcaEtherErrStatsDeferredTxDeltaMin(37554),
        tcaEtherErrStatsDeferredTxDeltaMax(37555),
        tcaEtherErrStatsDeferredTxDeltaAvg(37556),
        tcaComputeMbPowerStatsInputVoltage(37564),
        tcaComputeMbPowerStatsInputVoltageMin(37566),
        tcaComputeMbPowerStatsInputVoltageMax(37567),
        tcaComputeMbPowerStatsInputVoltageAvg(37568),
        tcaComputeMbPowerStatsInputCurrent(37572),
        tcaComputeMbPowerStatsInputCurrentMin(37574),
        tcaComputeMbPowerStatsInputCurrentMax(37575),
        tcaComputeMbPowerStatsInputCurrentAvg(37576),
        tcaComputeMbTempStatsFmTempSenRear(37580),
        tcaComputeMbTempStatsFmTempSenRearMin(37582),
        tcaComputeMbTempStatsFmTempSenRearMax(37583),
        tcaComputeMbTempStatsFmTempSenRearAvg(37584),
        tcaMemoryUnitEnvStatsTemperature(37600),
        tcaMemoryUnitEnvStatsTemperatureMin(37602),
        tcaMemoryUnitEnvStatsTemperatureMax(37603),
        tcaMemoryUnitEnvStatsTemperatureAvg(37604),
        tcaProcessorEnvStatsTemperature(37610),
        tcaProcessorEnvStatsTemperatureMin(37612),
        tcaProcessorEnvStatsTemperatureMax(37613),
        tcaProcessorEnvStatsTemperatureAvg(37614),
        tcaSwEnvStatsPsuCtrlrInlet1(37771),
        tcaSwEnvStatsPsuCtrlrInlet1Min(37773),
        tcaSwEnvStatsPsuCtrlrInlet1Max(37774),
        tcaSwEnvStatsPsuCtrlrInlet1Avg(37775),
        tcaSwEnvStatsPsuCtrlrInlet2(37779),
        tcaSwEnvStatsPsuCtrlrInlet2Min(37781),
        tcaSwEnvStatsPsuCtrlrInlet2Max(37782),
        tcaSwEnvStatsPsuCtrlrInlet2Avg(37783),
        tcaComputePcieFatalProtocolStatsDllpErrors(38022),
        tcaComputePcieFatalProtocolStatsFlowControlErrors(38032),
        tcaComputePcieFatalReceiveStatsUnsupportedRequestErrors(38044),
        tcaComputePcieFatalReceiveStatsErrFatalErrors(38054),
        tcaComputePcieFatalReceiveStatsErrNonFatalErrors(38064),
        tcaComputePcieFatalCompletionStatsUnexpectedErrors(38086),
        tcaComputePcieFatalCompletionStatsTimeoutErrors(38096),
        tcaComputePcieFatalCompletionStatsAbortErrors(38106),
        tcaComputePcieFatalStatsSurpriseLinkDownErrors(38128),
        tcaComputePcieFatalStatsPoisonedtlperrors(38138),
        tcaComputePcieFatalStatsAcsViolationErrors(38148),
        tcaComputePcieFatalStatsMalformedtlperrors(38158),
        tcaEquipmentIocardStatsTemp(38311),
        tcaEquipmentIocardStatsTempMin(38313),
        tcaEquipmentIocardStatsTempMax(38314),
        tcaEquipmentIocardStatsTempAvg(38315),
        tcaProcessorEnvStatsInputCurrent(38349),
        tcaProcessorEnvStatsInputCurrentMin(38351),
        tcaProcessorEnvStatsInputCurrentMax(38352),
        tcaProcessorEnvStatsInputCurrentAvg(38353),
        tcaMemoryArrayEnvStatsInputCurrent(38357),
        tcaMemoryArrayEnvStatsInputCurrentMin(38359),
        tcaMemoryArrayEnvStatsInputCurrentMax(38360),
        tcaMemoryArrayEnvStatsInputCurrentAvg(38361),
        tcaAdaptorEthPortBySizeLargeStatsNoBreakdownGreaterThan1518Delta(38408),
        tcaAdaptorEthPortBySizeLargeStatsNoBrkdnGreaterThan1518DeltaMin(38409),
        tcaAdaptorEthPortBySizeLargeStatsNoBrkdnGreaterThan1518DeltaMax(38410),
        tcaAdaptorEthPortBySizeLargeStatsNoBrkdnGreaterThan1518DeltaAvg(38411),
        tcaMemoryBufferUnitEnvStatsTemperature(38438),
        tcaMemoryBufferUnitEnvStatsTemperatureMin(38440),
        tcaMemoryBufferUnitEnvStatsTemperatureMax(38441),
        tcaMemoryBufferUnitEnvStatsTemperatureAvg(38442),
        tcaComputeIohubEnvStatsTemperature(38451),
        tcaComputeIohubEnvStatsTemperatureMin(38453),
        tcaComputeIohubEnvStatsTemperatureMax(38454),
        tcaComputeIohubEnvStatsTemperatureAvg(38455),
        tcaProcessorErrorStatsMirroringIntraSockErrors(38779),
        tcaProcessorErrorStatsMirroringInterSockErrors(38788),
        tcaProcessorErrorStatsSparingErrors(38797),
        tcaProcessorErrorStatsSmiLinkCorrErrors(38806),
        tcaProcessorErrorStatsSmiLinkUncorrErrors(38815),
        tcaMemoryErrorStatsEccMultibitErrors(38829),
        tcaMemoryErrorStatsEccSinglebitErrors(38838),
        tcaMemoryErrorStatsAddressParityErrors(38847),
        tcaMemoryErrorStatsMismatchErrors(38856),
        tcaComputePcieFatalReceiveStatsBufferOverflowErrors(38909),
        tcaComputeMbTempStatsFmTempSenRearl(39032),
        tcaComputeMbTempStatsFmTempSenRearlmin(39034),
        tcaComputeMbTempStatsFmTempSenRearlmax(39035),
        tcaComputeMbTempStatsFmTempSenRearlavg(39036),
        tcaComputeMbTempStatsFmTempSenRearr(39040),
        tcaComputeMbTempStatsFmTempSenRearrmin(39042),
        tcaComputeMbTempStatsFmTempSenRearrmax(39043),
        tcaComputeMbTempStatsFmTempSenRearravg(39044),
        tcaPowerGroupStatsPower(39240),
        tcaPowerGroupStatsPowerMin(39242),
        tcaPowerGroupStatsPowerMax(39243),
        tcaPowerGroupStatsPowerAvg(39244),
        tcaEquipmentFexEnvStatsOutlet1(39421),
        tcaEquipmentFexEnvStatsOutlet1Min(39423),
        tcaEquipmentFexEnvStatsOutlet1Max(39424),
        tcaEquipmentFexEnvStatsOutlet1Avg(39425),
        tcaEquipmentFexEnvStatsOutlet2(39429),
        tcaEquipmentFexEnvStatsOutlet2Min(39431),
        tcaEquipmentFexEnvStatsOutlet2Max(39432),
        tcaEquipmentFexEnvStatsOutlet2Avg(39433),
        tcaEquipmentFexEnvStatsInlet(39437),
        tcaEquipmentFexEnvStatsInletMin(39439),
        tcaEquipmentFexEnvStatsInletMax(39440),
        tcaEquipmentFexEnvStatsInletAvg(39441),
        tcaEquipmentFexEnvStatsInlet1(39445),
        tcaEquipmentFexEnvStatsInlet1Min(39447),
        tcaEquipmentFexEnvStatsInlet1Max(39448),
        tcaEquipmentFexEnvStatsInlet1Avg(39449),
        tcaEquipmentFexEnvStatsDie1(39453),
        tcaEquipmentFexEnvStatsDie1Min(39455),
        tcaEquipmentFexEnvStatsDie1Max(39456),
        tcaEquipmentFexEnvStatsDie1Avg(39457),
        tcaEquipmentFexPowerSummaryTotalPower(39464),
        tcaEquipmentFexPowerSummaryTotalPowerMin(39466),
        tcaEquipmentFexPowerSummaryTotalPowerMax(39467),
        tcaEquipmentFexPowerSummaryTotalPowerAvg(39468),
        tcaEquipmentFexPowerSummaryReservedPower(39472),
        tcaEquipmentFexPowerSummaryReservedPowerMin(39474),
        tcaEquipmentFexPowerSummaryReservedPowerMax(39475),
        tcaEquipmentFexPowerSummaryReservedPowerAvg(39476),
        tcaEquipmentFexPowerSummaryModulePower(39480),
        tcaEquipmentFexPowerSummaryModulePowerMin(39482),
        tcaEquipmentFexPowerSummaryModulePowerMax(39483),
        tcaEquipmentFexPowerSummaryModulePowerAvg(39484),
        tcaEquipmentFexPowerSummaryAvailablePower(39488),
        tcaEquipmentFexPowerSummaryAvailablePowerMin(39490),
        tcaEquipmentFexPowerSummaryAvailablePowerMax(39491),
        tcaEquipmentFexPowerSummaryAvailablePowerAvg(39492),
        tcaEquipmentFexPsuInputStatsCurrent(39498),
        tcaEquipmentFexPsuInputStatsCurrentMin(39500),
        tcaEquipmentFexPsuInputStatsCurrentMax(39501),
        tcaEquipmentFexPsuInputStatsCurrentAvg(39502),
        tcaEquipmentFexPsuInputStatsVoltage(39506),
        tcaEquipmentFexPsuInputStatsVoltageMin(39508),
        tcaEquipmentFexPsuInputStatsVoltageMax(39509),
        tcaEquipmentFexPsuInputStatsVoltageAvg(39510),
        tcaEquipmentFexPsuInputStatsPower(39514),
        tcaEquipmentFexPsuInputStatsPowerMin(39516),
        tcaEquipmentFexPsuInputStatsPowerMax(39517),
        tcaEquipmentFexPsuInputStatsPowerAvg(39518),
        tcaEquipmentRackUnitPsuStatsAmbientTemp(39525),
        tcaEquipmentRackUnitPsuStatsAmbientTempMin(39527),
        tcaEquipmentRackUnitPsuStatsAmbientTempMax(39528),
        tcaEquipmentRackUnitPsuStatsAmbientTempAvg(39529),
        tcaEquipmentRackUnitPsuStatsOutputCurrent(39533),
        tcaEquipmentRackUnitPsuStatsOutputCurrentMin(39535),
        tcaEquipmentRackUnitPsuStatsOutputCurrentMax(39536),
        tcaEquipmentRackUnitPsuStatsOutputCurrentAvg(39537),
        tcaEquipmentRackUnitPsuStatsOutputPower(39541),
        tcaEquipmentRackUnitPsuStatsOutputPowerMin(39543),
        tcaEquipmentRackUnitPsuStatsOutputPowerMax(39544),
        tcaEquipmentRackUnitPsuStatsOutputPowerAvg(39545),
        tcaEquipmentRackUnitPsuStatsInputPower(39549),
        tcaEquipmentRackUnitPsuStatsInputPowerMin(39551),
        tcaEquipmentRackUnitPsuStatsInputPowerMax(39552),
        tcaEquipmentRackUnitPsuStatsInputPowerAvg(39553),
        tcaEquipmentRackUnitPsuStatsOutputVoltage(39557),
        tcaEquipmentRackUnitPsuStatsOutputVoltageMin(39559),
        tcaEquipmentRackUnitPsuStatsOutputVoltageMax(39560),
        tcaEquipmentRackUnitPsuStatsOutputVoltageAvg(39561),
        tcaEquipmentRackUnitPsuStatsInputVoltage(39565),
        tcaEquipmentRackUnitPsuStatsInputVoltageMin(39567),
        tcaEquipmentRackUnitPsuStatsInputVoltageMax(39568),
        tcaEquipmentRackUnitPsuStatsInputVoltageAvg(39569),
        tcaEquipmentRackUnitFanStatsSpeed(39575),
        tcaEquipmentRackUnitFanStatsSpeedMin(39577),
        tcaEquipmentRackUnitFanStatsSpeedMax(39578),
        tcaEquipmentRackUnitFanStatsSpeedAvg(39579),
        tcaComputeRackUnitMbTempStatsFrontTemp(40092),
        tcaComputeRackUnitMbTempStatsFrontTempMin(40094),
        tcaComputeRackUnitMbTempStatsFrontTempMax(40095),
        tcaComputeRackUnitMbTempStatsFrontTempAvg(40096),
        tcaComputeRackUnitMbTempStatsRearTemp(40100),
        tcaComputeRackUnitMbTempStatsRearTempMin(40102),
        tcaComputeRackUnitMbTempStatsRearTempMax(40103),
        tcaComputeRackUnitMbTempStatsRearTempAvg(40104),
        tcaComputeRackUnitMbTempStatsAmbientTemp(40108),
        tcaComputeRackUnitMbTempStatsAmbientTempMin(40110),
        tcaComputeRackUnitMbTempStatsAmbientTempMax(40111),
        tcaComputeRackUnitMbTempStatsAmbientTempAvg(40112),
        tcaComputeRackUnitMbTempStatsIoh1Temp(40116),
        tcaComputeRackUnitMbTempStatsIoh1TempMin(40118),
        tcaComputeRackUnitMbTempStatsIoh1TempMax(40119),
        tcaComputeRackUnitMbTempStatsIoh1TempAvg(40120),
        tcaComputeRackUnitMbTempStatsIoh2Temp(40124),
        tcaComputeRackUnitMbTempStatsIoh2TempMin(40126),
        tcaComputeRackUnitMbTempStatsIoh2TempMax(40127),
        tcaComputeRackUnitMbTempStatsIoh2TempAvg(40128),
        tcaEquipmentPsuOutputStatsCurrent(40547),
        tcaEquipmentPsuOutputStatsCurrentMin(40549),
        tcaEquipmentPsuOutputStatsCurrentMax(40550),
        tcaEquipmentPsuOutputStatsCurrentAvg(40551),
        tcaEquipmentPsuOutputStatsVoltage(40555),
        tcaEquipmentPsuOutputStatsVoltageMin(40557),
        tcaEquipmentPsuOutputStatsVoltageMax(40558),
        tcaEquipmentPsuOutputStatsVoltageAvg(40559),
        tcaEquipmentPsuOutputStatsPower(40563),
        tcaEquipmentPsuOutputStatsPowerMin(40565),
        tcaEquipmentPsuOutputStatsPowerMax(40566),
        tcaEquipmentPsuOutputStatsPowerAvg(40567),
        tcaEquipmentNetworkElementFanStatsSpeed(40574),
        tcaEquipmentNetworkElementFanStatsSpeedMin(40576),
        tcaEquipmentNetworkElementFanStatsSpeedMax(40577),
        tcaEquipmentNetworkElementFanStatsSpeedAvg(40578),
        tcaEquipmentNetworkElementFanStatsDrivePercentage(40582),
        tcaEquipmentNetworkElementFanStatsDrivePercentageMin(40584),
        tcaEquipmentNetworkElementFanStatsDrivePercentageMax(40585),
        tcaEquipmentNetworkElementFanStatsDrivePercentageAvg(40586),
        tcaSwCardEnvStatsSlotOutlet1(41199),
        tcaSwCardEnvStatsSlotOutlet1Min(41201),
        tcaSwCardEnvStatsSlotOutlet1Max(41202),
        tcaSwCardEnvStatsSlotOutlet1Avg(41203),
        tcaSwCardEnvStatsSlotOutlet2(41207),
        tcaSwCardEnvStatsSlotOutlet2Min(41209),
        tcaSwCardEnvStatsSlotOutlet2Max(41210),
        tcaSwCardEnvStatsSlotOutlet2Avg(41211),
        tcaSwCardEnvStatsSlotOutlet3(41215),
        tcaSwCardEnvStatsSlotOutlet3Min(41217),
        tcaSwCardEnvStatsSlotOutlet3Max(41218),
        tcaSwCardEnvStatsSlotOutlet3Avg(41219),
        tcaEtherFcoeInterfaceStatsPacketsTxDelta(41289),
        tcaEtherFcoeInterfaceStatsPacketsTxDeltaMin(41290),
        tcaEtherFcoeInterfaceStatsPacketsTxDeltaMax(41291),
        tcaEtherFcoeInterfaceStatsPacketsTxDeltaAvg(41292),
        tcaEtherFcoeInterfaceStatsPacketsRxDelta(41299),
        tcaEtherFcoeInterfaceStatsPacketsRxDeltaMin(41300),
        tcaEtherFcoeInterfaceStatsPacketsRxDeltaMax(41301),
        tcaEtherFcoeInterfaceStatsPacketsRxDeltaAvg(41302),
        tcaEtherFcoeInterfaceStatsBytesTxDelta(41309),
        tcaEtherFcoeInterfaceStatsBytesTxDeltaMin(41310),
        tcaEtherFcoeInterfaceStatsBytesTxDeltaMax(41311),
        tcaEtherFcoeInterfaceStatsBytesTxDeltaAvg(41312),
        tcaEtherFcoeInterfaceStatsBytesRxDelta(41319),
        tcaEtherFcoeInterfaceStatsBytesRxDeltaMin(41320),
        tcaEtherFcoeInterfaceStatsBytesRxDeltaMax(41321),
        tcaEtherFcoeInterfaceStatsBytesRxDeltaAvg(41322),
        tcaEtherFcoeInterfaceStatsErrorsTxDelta(41329),
        tcaEtherFcoeInterfaceStatsErrorsTxDeltaMin(41330),
        tcaEtherFcoeInterfaceStatsErrorsTxDeltaMax(41331),
        tcaEtherFcoeInterfaceStatsErrorsTxDeltaAvg(41332),
        tcaEtherFcoeInterfaceStatsErrorsRxDelta(41339),
        tcaEtherFcoeInterfaceStatsErrorsRxDeltaMin(41340),
        tcaEtherFcoeInterfaceStatsErrorsRxDeltaMax(41341),
        tcaEtherFcoeInterfaceStatsErrorsRxDeltaAvg(41342),
        tcaEtherFcoeInterfaceStatsDroppedTxDelta(41349),
        tcaEtherFcoeInterfaceStatsDroppedTxDeltaMin(41350),
        tcaEtherFcoeInterfaceStatsDroppedTxDeltaMax(41351),
        tcaEtherFcoeInterfaceStatsDroppedTxDeltaAvg(41352),
        tcaEtherFcoeInterfaceStatsDroppedRxDelta(41359),
        tcaEtherFcoeInterfaceStatsDroppedRxDeltaMin(41360),
        tcaEtherFcoeInterfaceStatsDroppedRxDeltaMax(41361),
        tcaEtherFcoeInterfaceStatsDroppedRxDeltaAvg(41362),
        tcaEquipmentIocardStatsProcTemp(43101),
        tcaEquipmentIocardStatsProcTempMin(43103),
        tcaEquipmentIocardStatsProcTempMax(43104),
        tcaEquipmentIocardStatsProcTempAvg(43105),
        tcaEquipmentIocardStatsDimmTemp(43109),
        tcaEquipmentIocardStatsDimmTempMin(43111),
        tcaEquipmentIocardStatsDimmTempMax(43112),
        tcaEquipmentIocardStatsDimmTempAvg(43113),
        tcaEtherNiErrStatsFrameTxDelta(43787),
        tcaEtherNiErrStatsFrameTxDeltaMin(43788),
        tcaEtherNiErrStatsFrameTxDeltaMax(43789),
        tcaEtherNiErrStatsFrameTxDeltaAvg(43790),
        tcaEtherNiErrStatsTooLongDelta(43797),
        tcaEtherNiErrStatsTooLongDeltaMin(43798),
        tcaEtherNiErrStatsTooLongDeltaMax(43799),
        tcaEtherNiErrStatsTooLongDeltaAvg(43800),
        tcaEtherNiErrStatsTooShortDelta(43807),
        tcaEtherNiErrStatsTooShortDeltaMin(43808),
        tcaEtherNiErrStatsTooShortDeltaMax(43809),
        tcaEtherNiErrStatsTooShortDeltaAvg(43810),
        tcaEtherNiErrStatsCrcDelta(43817),
        tcaEtherNiErrStatsCrcDeltaMin(43818),
        tcaEtherNiErrStatsCrcDeltaMax(43819),
        tcaEtherNiErrStatsCrcDeltaAvg(43820),
        tcaEtherNiErrStatsInRangeDelta(43827),
        tcaEtherNiErrStatsInRangeDeltaMin(43828),
        tcaEtherNiErrStatsInRangeDeltaMax(43829),
        tcaEtherNiErrStatsInRangeDeltaAvg(43830),
        fsmSamDmeEquipmentChassisRemoveChassisRemoteInv(77847),
        fsmSamDmeEquipmentLocatorLedSetLocatorLedRemoteInv(77848),
        fsmSamDmeMgmtControllerExtMgmtIfConfigRemoteInv(77958),
        fsmSamDmeFabricComputeSlotEpIdentifyRemoteInv(77959),
        fsmSamDmeComputeBladeDiscoverRemoteInv(77960),
        fsmSamDmeEquipmentChassisPsuPolicyConfigRemoteInv(77973),
        fsmSamDmeAdaptorHostFcIfResetFcPersBindingRemoteInv(77974),
        fsmSamDmeComputeBladeDiagRemoteInv(77975),
        fsmSamDmeFabricLanCloudSwitchModeRemoteInv(77979),
        fsmSamDmeVnicProfileSetDeployRemoteInv(77990),
        fsmSamDmeCommSvcEpUpdateSvcEpRemoteInv(78016),
        fsmSamDmeCommSvcEpRestartWebSvcRemoteInv(78017),
        fsmSamDmeAaaEpUpdateEpRemoteInv(78019),
        fsmSamDmeAaaRealmUpdateRealmRemoteInv(78020),
        fsmSamDmeAaaUserEpUpdateUserEpRemoteInv(78021),
        fsmSamDmePkiEpUpdateEpRemoteInv(78022),
        fsmSamDmeSysfileMutationSingleRemoteInv(78040),
        fsmSamDmeSysfileMutationGlobalRemoteInv(78041),
        fsmSamDmeSysdebugManualCoreFileExportTargetExportRemoteInv(78044),
        fsmSamDmeSysdebugAutoCoreFileExportTargetConfigureRemoteInv(78045),
        fsmSamDmeSysdebugLogControlEpLogControlPersistRemoteInv(78046),
        fsmSamDmeSwAccessDomainDeployRemoteInv(78074),
        fsmSamDmeSwEthLanBorderDeployRemoteInv(78075),
        fsmSamDmeSwFcSanBorderDeployRemoteInv(78076),
        fsmSamDmeSwUtilityDomainDeployRemoteInv(78077),
        fsmSamDmeSyntheticFsObjCreateRemoteInv(78081),
        fsmSamDmeFirmwareDownloaderDownloadRemoteInv(78090),
        fsmSamDmeFirmwareImageDeleteRemoteInv(78091),
        fsmSamDmeMgmtControllerUpdateSwitchRemoteInv(78093),
        fsmSamDmeMgmtControllerUpdateiomRemoteInv(78094),
        fsmSamDmeMgmtControllerActivateiomRemoteInv(78095),
        fsmSamDmeMgmtControllerUpdatebmcRemoteInv(78096),
        fsmSamDmeMgmtControllerActivatebmcRemoteInv(78097),
        fsmSamDmeCallhomeEpConfigCallhomeRemoteInv(78110),
        fsmSamDmeMgmtIfSwMgmtOobIfConfigRemoteInv(78113),
        fsmSamDmeMgmtIfSwMgmtInbandIfConfigRemoteInv(78114),
        fsmSamDmeMgmtIfVirtualIfConfigRemoteInv(78119),
        fsmSamDmeMgmtIfEnableVipRemoteInv(78120),
        fsmSamDmeMgmtIfDisableVipRemoteInv(78121),
        fsmSamDmeMgmtIfEnablehaRemoteInv(78122),
        fsmSamDmeMgmtBackupBackupRemoteInv(78123),
        fsmSamDmeMgmtImporterImportRemoteInv(78124),
        fsmSamDmeStatsCollectionPolicyUpdateEpRemoteInv(78182),
        fsmSamDmeQosclassDefinitionConfigGlobalQoSremoteInv(78185),
        fsmSamDmeEpqosDefinitionDeployRemoteInv(78189),
        fsmSamDmeEpqosDefinitionDelTaskRemoveRemoteInv(78190),
        fsmSamDmeEquipmentiocardResetCmcRemoteInv(78243),
        fsmSamDmeMgmtControllerUpdatefprmanagerRemoteInv(78255),
        fsmSamDmeMgmtControllerSysConfigRemoteInv(78263),
        fsmSamDmeAdaptorExtEthIfPathResetRemoteInv(78292),
        fsmSamDmeAdaptorHostEthIfCircuitResetRemoteInv(78297),
        fsmSamDmeAdaptorHostFcIfCircuitResetRemoteInv(78298),
        fsmSamDmeExtvmmProviderConfigRemoteInv(78319),
        fsmSamDmeExtvmmKeyStoreCertInstallRemoteInv(78320),
        fsmSamDmeExtvmmSwitchDelTaskRemoveProviderRemoteInv(78321),
        fsmSamDmeExtvmmMasterExtKeyConfigRemoteInv(78338),
        fsmSamDmeCapabilityUpdaterUpdaterRemoteInv(78344),
        fsmSamDmeFirmwareDistributableDeleteRemoteInv(78346),
        fsmSamDmeCapabilityCatalogueDeployCatalogueRemoteInv(78371),
        fsmSamDmeEquipmentFexRemoveFexRemoteInv(78382),
        fsmSamDmeEquipmentLocatorLedSetFeLocatorLedRemoteInv(78383),
        fsmSamDmeEquipmentChassisPowerCapRemoteInv(78384),
        fsmSamDmeEquipmentiocardMuxOfflineRemoteInv(78385),
        fsmSamDmeComputePhysicalAssociateRemoteInv(78413),
        fsmSamDmeComputePhysicalDisassociateRemoteInv(78414),
        fsmSamDmeComputePhysicalPowerCapRemoteInv(78415),
        fsmSamDmeComputePhysicalDecommissionRemoteInv(78416),
        fsmSamDmeComputePhysicalSoftShutdownRemoteInv(78417),
        fsmSamDmeComputePhysicalHardShutdownRemoteInv(78418),
        fsmSamDmeComputePhysicalTurnupRemoteInv(78419),
        fsmSamDmeComputePhysicalPowercycleRemoteInv(78420),
        fsmSamDmeComputePhysicalHardresetRemoteInv(78421),
        fsmSamDmeComputePhysicalSoftresetRemoteInv(78422),
        fsmSamDmeComputePhysicalSwConnUpdRemoteInv(78423),
        fsmSamDmeComputePhysicalBiosRecoveryRemoteInv(78424),
        fsmSamDmeComputePhysicalCmosResetRemoteInv(78426),
        fsmSamDmeComputePhysicalResetBmcRemoteInv(78427),
        fsmSamDmeEquipmentiocardResetIomRemoteInv(78428),
        fsmSamDmeComputeRackUnitDiscoverRemoteInv(78434),
        fsmSamDmeLsServerConfigureRemoteInv(78435),
        fsmSamDmeSwEthMonDeployRemoteInv(78440),
        fsmSamDmeSwFcMonDeployRemoteInv(78441),
        fsmSamDmeFabricSanCloudSwitchModeRemoteInv(78442),
        fsmSamDmeComputePhysicalUpdateExtUsersRemoteInv(78448),
        fsmSamDmeSysdebugTechSupportInitiateRemoteInv(78452),
        fsmSamDmeSysdebugTechSupportDeleteTechSupFileRemoteInv(78453),
        fsmSamDmeSysdebugTechSupportDownloadRemoteInv(78454),
        fsmSamDmeComputePhysicalUpdateAdaptorRemoteInv(78483),
        fsmSamDmeComputePhysicalActivateAdaptorRemoteInv(78484),
        fsmSamDmeCapabilityCatalogueActivateCatalogRemoteInv(78485),
        fsmSamDmeCapabilityMgmtExtensionActivateMgmtExtRemoteInv(78486),
        fsmSamDmeLicenseDownloaderDownloadRemoteInv(78490),
        fsmSamDmeLicenseFileInstallRemoteInv(78491),
        fsmSamDmeLicenseFileClearRemoteInv(78492),
        fsmSamDmeLicenseInstanceUpdateFlexlmRemoteInv(78493),
        fsmSamDmeComputePhysicalConfigSoLremoteInv(78523),
        fsmSamDmeComputePhysicalUnconfigSoLremoteInv(78524),
        fsmSamDmePortpioInCompatSfpPresenceRemoteInv(78529),
        fsmSamDmeComputePhysicalDiagnosticInterruptRemoteInv(78556),
        fsmSamDmeSysdebugCoreDownloadRemoteInv(78573),
        fsmSamDmeEquipmentChassisDynamicReallocationRemoteInv(78574),
        fsmSamDmeComputePhysicalResetKvmRemoteInv(78603),
        fsmSamDmeMgmtControllerOnlineRemoteInv(78609),
        fsmSamDmeComputeRackUnitOfflineRemoteInv(78610),
        fsmSamDmeEquipmentLocatorLedSetFiLocatorLedRemoteInv(78627),
        fsmSamDmeFabricEpMgrConfigureRemoteInv(78654),
        fsmSamDmeVnicProfileSetDeployAliasRemoteInv(78663),
        fsmSamDmeSwPhysConfPhysicalRemoteInv(78679),
        fsmSamDmeExtvmmEpClusterRoleRemoteInv(78694),
        fsmSamDmeVmLifeCyclePolicyConfigRemoteInv(78699),
        fsmSamDmeEquipmentBeaconLedIlluminateRemoteInv(78702),
        fsmSamDmeEtherServerIntfioConfigSpeedRemoteInv(78711),
        fsmSamDmeComputePhysicalUpdatebiosRemoteInv(78721),
        fsmSamDmeComputePhysicalActivatebiosRemoteInv(78722),
        fsmSamDmeIdentIdentRequestUpdateIdentRemoteInv(78752),
        fsmSamDmeIdentMetaSystemSyncRemoteInv(78753),
        fsmSamDmeComputePhysicalResetIpmiRemoteInv(78766),
        fsmSamDmeComputePhysicalFwUpgradeRemoteInv(78767),
        fsmSamDmeComputeRackUnitAdapterResetRemoteInv(78768),
        fsmSamDmePortpioInCompatSfpReplacedRemoteInv(78798),
        fsmSamDmeExtpolEpRegisterFsmRemoteInv(78799),
        fsmSamDmeExtpolRegistryCrossDomainConfigRemoteInv(78800),
        fsmSamDmeExtpolRegistryCrossDomainDeleteRemoteInv(78801),
        fsmSamDmeNfsMountInstMountRemoteInv(78817),
        fsmSamDmeNfsMountInstUnmountRemoteInv(78818),
        fsmSamDmeNfsMountDefReportNfsMountSuspendRemoteInv(78819),
        fsmSamDmeStorageSystemSyncRemoteInv(78835),
        fsmSamDmeFirmwareSystemDeployRemoteInv(78848),
        fsmSamDmeFirmwareSystemApplyCatalogPackRemoteInv(78849),
        fsmSamDmeComputeServerDiscPolicyResolveScrubPolicyRemoteInv(78866),
        fsmSamDmeSwFcSanBorderActivateZoneSetRemoteInv(78879),
        fsmSamDmeExtpolEpRepairCertRemoteInv(78886),
        fsmSamDmePolicyControlEpOperateRemoteInv(78887),
        fsmSamDmePolicyPolicyScopeReleasePolicyFsmRemoteInv(78888),
        fsmSamDmePolicyPolicyScopeReleaseOperationFsmRemoteInv(78889),
        fsmSamDmePolicyPolicyScopeReleaseStorageFsmRemoteInv(78890),
        fsmSamDmePolicyPolicyScopeResolveManyPolicyFsmRemoteInv(78891),
        fsmSamDmePolicyPolicyScopeResolveManyOperationFsmRemoteInv(78892),
        fsmSamDmePolicyPolicyScopeResolveManyStorageFsmRemoteInv(78893),
        fsmSamDmePolicyPolicyScopeReleaseManyPolicyFsmRemoteInv(78894),
        fsmSamDmePolicyPolicyScopeReleaseManyOperationFsmRemoteInv(78895),
        fsmSamDmePolicyPolicyScopeReleaseManyStorageFsmRemoteInv(78896),
        fsmSamDmePolicyPolicyScopeResolveAllPolicyFsmRemoteInv(78897),
        fsmSamDmePolicyPolicyScopeResolveAllOperationFsmRemoteInv(78898),
        fsmSamDmePolicyPolicyScopeResolveAllStorageFsmRemoteInv(78899),
        fsmSamDmePolicyPolicyScopeReleaseAllPolicyFsmRemoteInv(78900),
        fsmSamDmePolicyPolicyScopeReleaseAllOperationFsmRemoteInv(78901),
        fsmSamDmePolicyPolicyScopeReleaseAllStorageFsmRemoteInv(78902),
        fsmSamDmeMgmtExportPolicyReportConfigCopyRemoteInv(78924),
        fsmSamDmeExtpolProviderReportConfigImportRemoteInv(78925),
        fsmSamDmeObserveObservedResolvePolicyFsmRemoteInv(78931),
        fsmSamDmeObserveObservedResolveResourceFsmRemoteInv(78932),
        fsmSamDmeObserveObservedResolvevmfsmRemoteInv(78933),
        fsmSamDmeObserveObservedResolveControllerFsmRemoteInv(78934),
        fsmSamDmeMgmtControllerRegistryConfigRemoteInv(78939),
        fsmSamDmeGmetaHolderInventoryRemoteInv(79048),
        fsmSamDmeComputePhysicalCimcSessionDeleteRemoteInv(79049),
        fsmSamDmePolicyControlledTypeOperateRemoteInv(79052),
        fsmSamDmeFabricVnetEpSyncEpPushVnetEpDeletionRemoteInv(79059),
        fsmSamDmeSwEthLanFlowMonDeployRemoteInv(79079),
        fsmSamDmeMgmtipv6IfAddrSwMgmtOobIpv6IfConfigRemoteInv(79105),
        fsmSamDmeComputePhysicalUpdateBoardControllerRemoteInv(79107),
        fsmSamDmeExtvmmNetworkSetsDeployRemoteInv(79143),
        fsmSamDmeComputePhysicalConfigBoardRemoteInv(79147),
        fsmSamDmeComputePhysicalResetMemoryErrorsRemoteInv(79148),
        fsmSamDmeMgmtControllerExtMgmtInterfaceConfigRemoteInv(79154),
        fsmSamDmeComputeRackUnitCreateDhcpEntryRemoteInv(79155),
        fsmSamDmeComputePhysicalServiceInfraDeployRemoteInv(79156),
        fsmSamDmeComputePhysicalServiceInfraWithdrawRemoteInv(79157),
        fsmSamDmeEquipmentiocardBaseFePresenceRemoteInv(79248),
        fsmSamDmeEquipmentiocardBaseFeConnRemoteInv(79249),
        fsmSamDmeMgmtControllerLockConfigRemoteInv(79253),
        fsmSamDmeSdAppInstanceInstallApplicationRemoteInv(79259),
        fsmSamDmeSysdebugLogExportPolicyConfigureRemoteInv(79270),
        fsmSamDmeComputePhysicalFlashControllerRemoteInv(79279),
        fsmSamDmeOsControllerDeployosRemoteInv(79303),
        fsmSamDmeNhTableHolderConfigureLinksRemoteInv(79306),
        fsmSamDmeStorageFlexFlashControllermopsResetRemoteInv(79312),
        fsmSamDmeStorageFlexFlashControllermopsFormatRemoteInv(79313),
        fsmSamDmeStorageFlexFlashControllermopsPairRemoteInv(79314),
        fsmSamDmeIdentMetaSystemFprcUnivSyncRemoteInv(79317),
        fsmSamDmeComputePhysicalEnableCimcSecureBootRemoteInv(79337),
        fsmSamDmeSdAppInstanceStartApplicationRemoteInv(79351),
        fsmSamDmeSdLduProvisionlduRemoteInv(79352),
        fsmSamDmeSwExtUtilityConfPortBreakoutRemoteInv(79357),
        fsmSamDmeSmAppDeleteRemoteInv(79369),
        fsmSamDmeSmSecSvcRestoreApplicationRemoteInv(79370),
        fsmSamDmeApplicationDownloaderDownloadRemoteInv(79385),
        fsmSamDmeNhTableHolderBootstrapLinksRemoteInv(79388),
        fsmSamDmeFirmwarePlatformPackPlatformVersionRemoteInv(79394),
        fsmSamDmeLicenseSmartConfigSetConfigRemoteInv(79397),
        fsmSamDmeOsControllerUpgradeosRemoteInv(79410),
        fsmSamDmeOsControllerInitosRemoteInv(79411),
        fsmSamDmeSdAppInstanceUpgradeApplicationRemoteInv(79412),
        fsmSamDmeSdAppInstanceStopApplicationRemoteInv(79413),
        fsmSamDmeSdAppInstanceUninstallApplicationRemoteInv(79414),
        fsmSamDmeSdSlotChangePlatformLogLevelRemoteInv(79415),
        fsmSamDmeSdAppInstanceBundleDataPortsRemoteInv(79416),
        fsmSamDmeSdLogicalDeviceConfigureLinksRemoteInv(79417),
        fsmSamDmeSdExternalLduLinkUpdateInterfaceStatusRemoteInv(79418),
        fsmSamDmeSdAppInstanceUpdateClusterConfigurationRemoteInv(79419),
        fsmSamDmeSdSlotFormatDiskRemoteInv(79420),
        fsmSamDmeSdSlotSynchTimeZoneRemoteInv(79421),
        fsmSamDmeSdAppAttributeCtrlGetAppAttributesRemoteInv(79422),
        fsmSamDmeSdMgmtInfoUpdateMgmtInfoRemoteInv(79423),
        fsmSamDmeSdNetMgmtBootstrapUpdateNetMgmtBootstrapRemoteInv(79424),
        fsmSamDmeSwSspEthMonDeployRemoteInv(79440),
        fsmSamDmeSdClusterBootstrapUpdateClusterConfigurationRemoteInv(79443),
        fsmSamDmeSmAppInstanceResetApplicationRemoteInv(79448),
        fsmSamDmeIpsecEpUpdateEpRemoteInv(79460),
        fsmSamDmeEtherFtwPortPairConfigFtwRemoteInv(79463),
        fsmSamDmeSdLinkUpdateInterfaceStatusRemoteInv(79464),
        fsmSamDmeSdUpgradeTaskStopUpgradeStartAppRemoteInv(79465),
        fsmSamDmeSwSspEthMonSrcPhyEpDeleteRemoteInv(79474),
        fsmSamDmeFirmwareSupFirmwareDeployRemoteInv(79475),
        fsmSamDmeEquipmentChassisShutdownChassisRemoteInv(79483),
        fsmSamDmeSmCloudConnectorRegisterCloudConnectorRemoteInv(79491),
        fsmSamDmeSmCloudConnectorUnRegisterCloudConnectorRemoteInv(79492),
        fsmSamDmeSmAppVerifyApplicationRemoteInv(79493),
        fsmSamDmeSmLogicalDeviceConfigureRemoteInv(79496),
        fsmSamDmeSdLduUpdateInterfaceStatusRemoteInv(79498),
        fsmSamDmeSdLogicalDeviceConfigureUserMacsRemoteInv(79499),
        fsmSamDmeEquipmentChassisRebootChassisRemoteInv(79500),
        fsmSamDmeFirmwareValidationStatusValidateRemoteInv(79504),
        fsmSamDmeSdPortsBundleBundleDataPortsRemoteInv(79521),
        fsmSamDmeSdHotfixInstallHotfixRemoteInv(79522),
        fsmSamDmeSdHotfixUninstallHotfixRemoteInv(79523),
        fsmSamDmeOsControllerInstallLicenseRemoteInv(79532),
        fsmSamDmeSmUnsignedCspLicenseDeployRemoteInv(79538),
        fsmSamDmeSmLicenseFileDeleteRemoteInv(79539),
        fsmSamDmeComputePhysicalUpdateAdaptorBootRemoteInv(79552),
        fsmSamDmeSmAppInstance2ResetApplicationRemoteInv(79569),
        fsmSamDmeSdAppInstSettingsTaskSendAppInstSettingsRemoteInv(79576),
        fsmSamDmeSdLogicalDeviceConfigureMacsRemoteInv(79578),
        fsmSamDmeCommTelemetryDataExchSeqRemoteInv(79594),
        fsmSamDmeCommTelemetryEnableDisableTelemetryRemoteInv(79595),
        fsmSamDmeSdCspMetaCtrlRetrievecspmetaRemoteInv(79596),
        fsmSamDmeSdAppInstanceGracefulStopAppRemoteInv(79597),
        fsmSamDmeComputePhysicalHardPowercycleRemoteInv(79609),
        fsmSamDmeEquipmentChassisRemoveChassisFsmFail(999447),
        fsmSamDmeEquipmentLocatorLedSetLocatorLedFsmFail(999448),
        fsmSamDmeMgmtControllerExtMgmtIfConfigFsmFail(999558),
        fsmSamDmeFabricComputeSlotEpIdentifyFsmFail(999559),
        fsmSamDmeComputeBladeDiscoverFsmFail(999560),
        fsmSamDmeEquipmentChassisPsuPolicyConfigFsmFail(999573),
        fsmSamDmeAdaptorHostFcIfResetFcPersBindingFsmFail(999574),
        fsmSamDmeComputeBladeDiagFsmFail(999575),
        fsmSamDmeFabricLanCloudSwitchModeFsmFail(999579),
        fsmSamDmeVnicProfileSetDeployFsmFail(999590),
        fsmSamDmeCommSvcEpUpdateSvcEpFsmFail(999616),
        fsmSamDmeCommSvcEpRestartWebSvcFsmFail(999617),
        fsmSamDmeAaaEpUpdateEpFsmFail(999619),
        fsmSamDmeAaaRealmUpdateRealmFsmFail(999620),
        fsmSamDmeAaaUserEpUpdateUserEpFsmFail(999621),
        fsmSamDmePkiEpUpdateEpFsmFail(999622),
        fsmSamDmeSysfileMutationSingleFsmFail(999640),
        fsmSamDmeSysfileMutationGlobalFsmFail(999641),
        fsmSamDmeSysdebugManualCoreFileExportTargetExportFsmFail(999644),
        fsmSamDmeSysdebugAutoCoreFileExportTargetConfigureFsmFail(999645),
        fsmSamDmeSysdebugLogControlEpLogControlPersistFsmFail(999646),
        fsmSamDmeSwAccessDomainDeployFsmFail(999674),
        fsmSamDmeSwEthLanBorderDeployFsmFail(999675),
        fsmSamDmeSwFcSanBorderDeployFsmFail(999676),
        fsmSamDmeSwUtilityDomainDeployFsmFail(999677),
        fsmSamDmeSyntheticFsObjCreateFsmFail(999681),
        fsmSamDmeFirmwareDownloaderDownloadFsmFail(999690),
        fsmSamDmeFirmwareImageDeleteFsmFail(999691),
        fsmSamDmeMgmtControllerUpdateSwitchFsmFail(999693),
        fsmSamDmeMgmtControllerUpdateiomFsmFail(999694),
        fsmSamDmeMgmtControllerActivateiomFsmFail(999695),
        fsmSamDmeMgmtControllerUpdatebmcFsmFail(999696),
        fsmSamDmeMgmtControllerActivatebmcFsmFail(999697),
        fsmSamDmeCallhomeEpConfigCallhomeFsmFail(999710),
        fsmSamDmeMgmtIfSwMgmtOobIfConfigFsmFail(999713),
        fsmSamDmeMgmtIfSwMgmtInbandIfConfigFsmFail(999714),
        fsmSamDmeMgmtIfVirtualIfConfigFsmFail(999719),
        fsmSamDmeMgmtIfEnableVipFsmFail(999720),
        fsmSamDmeMgmtIfDisableVipFsmFail(999721),
        fsmSamDmeMgmtIfEnablehaFsmFail(999722),
        fsmSamDmeMgmtBackupBackupFsmFail(999723),
        fsmSamDmeMgmtImporterImportFsmFail(999724),
        fsmSamDmeStatsCollectionPolicyUpdateEpFsmFail(999782),
        fsmSamDmeQosclassDefinitionConfigGlobalQoSfsmFail(999785),
        fsmSamDmeEpqosDefinitionDeployFsmFail(999789),
        fsmSamDmeEpqosDefinitionDelTaskRemoveFsmFail(999790),
        fsmSamDmeEquipmentiocardResetCmcFsmFail(999843),
        fsmSamDmeMgmtControllerUpdatefprmanagerFsmFail(999855),
        fsmSamDmeMgmtControllerSysConfigFsmFail(999863),
        fsmSamDmeAdaptorExtEthIfPathResetFsmFail(999892),
        fsmSamDmeAdaptorHostEthIfCircuitResetFsmFail(999897),
        fsmSamDmeAdaptorHostFcIfCircuitResetFsmFail(999898),
        fsmSamDmeExtvmmProviderConfigFsmFail(999919),
        fsmSamDmeExtvmmKeyStoreCertInstallFsmFail(999920),
        fsmSamDmeExtvmmSwitchDelTaskRemoveProviderFsmFail(999921),
        fsmSamDmeExtvmmMasterExtKeyConfigFsmFail(999938),
        fsmSamDmeCapabilityUpdaterUpdaterFsmFail(999944),
        fsmSamDmeFirmwareDistributableDeleteFsmFail(999946),
        fsmSamDmeCapabilityCatalogueDeployCatalogueFsmFail(999971),
        fsmSamDmeEquipmentFexRemoveFexFsmFail(999982),
        fsmSamDmeEquipmentLocatorLedSetFeLocatorLedFsmFail(999983),
        fsmSamDmeEquipmentChassisPowerCapFsmFail(999984),
        fsmSamDmeEquipmentiocardMuxOfflineFsmFail(999985),
        fsmSamDmeComputePhysicalAssociateFsmFail(1000013),
        fsmSamDmeComputePhysicalDisassociateFsmFail(1000014),
        fsmSamDmeComputePhysicalPowerCapFsmFail(1000015),
        fsmSamDmeComputePhysicalDecommissionFsmFail(1000016),
        fsmSamDmeComputePhysicalSoftShutdownFsmFail(1000017),
        fsmSamDmeComputePhysicalHardShutdownFsmFail(1000018),
        fsmSamDmeComputePhysicalTurnupFsmFail(1000019),
        fsmSamDmeComputePhysicalPowercycleFsmFail(1000020),
        fsmSamDmeComputePhysicalHardresetFsmFail(1000021),
        fsmSamDmeComputePhysicalSoftresetFsmFail(1000022),
        fsmSamDmeComputePhysicalSwConnUpdFsmFail(1000023),
        fsmSamDmeComputePhysicalBiosRecoveryFsmFail(1000024),
        fsmSamDmeComputePhysicalCmosResetFsmFail(1000026),
        fsmSamDmeComputePhysicalResetBmcFsmFail(1000027),
        fsmSamDmeEquipmentiocardResetIomFsmFail(1000028),
        fsmSamDmeComputeRackUnitDiscoverFsmFail(1000034),
        fsmSamDmeLsServerConfigureFsmFail(1000035),
        fsmSamDmeSwEthMonDeployFsmFail(1000040),
        fsmSamDmeSwFcMonDeployFsmFail(1000041),
        fsmSamDmeFabricSanCloudSwitchModeFsmFail(1000042),
        fsmSamDmeComputePhysicalUpdateExtUsersFsmFail(1000048),
        fsmSamDmeSysdebugTechSupportInitiateFsmFail(1000052),
        fsmSamDmeSysdebugTechSupportDeleteTechSupFileFsmFail(1000053),
        fsmSamDmeSysdebugTechSupportDownloadFsmFail(1000054),
        fsmSamDmeComputePhysicalUpdateAdaptorFsmFail(1000083),
        fsmSamDmeComputePhysicalActivateAdaptorFsmFail(1000084),
        fsmSamDmeCapabilityCatalogueActivateCatalogFsmFail(1000085),
        fsmSamDmeCapabilityMgmtExtensionActivateMgmtExtFsmFail(1000086),
        fsmSamDmeLicenseDownloaderDownloadFsmFail(1000090),
        fsmSamDmeLicenseFileInstallFsmFail(1000091),
        fsmSamDmeLicenseFileClearFsmFail(1000092),
        fsmSamDmeLicenseInstanceUpdateFlexlmFsmFail(1000093),
        fsmSamDmeComputePhysicalConfigSoLfsmFail(1000123),
        fsmSamDmeComputePhysicalUnconfigSoLfsmFail(1000124),
        fsmSamDmePortpioInCompatSfpPresenceFsmFail(1000129),
        fsmSamDmeComputePhysicalDiagnosticInterruptFsmFail(1000156),
        fsmSamDmeSysdebugCoreDownloadFsmFail(1000173),
        fsmSamDmeEquipmentChassisDynamicReallocationFsmFail(1000174),
        fsmSamDmeComputePhysicalResetKvmFsmFail(1000203),
        fsmSamDmeMgmtControllerOnlineFsmFail(1000209),
        fsmSamDmeComputeRackUnitOfflineFsmFail(1000210),
        fsmSamDmeEquipmentLocatorLedSetFiLocatorLedFsmFail(1000227),
        fsmSamDmeFabricEpMgrConfigureFsmFail(1000254),
        fsmSamDmeVnicProfileSetDeployAliasFsmFail(1000263),
        fsmSamDmeSwPhysConfPhysicalFsmFail(1000279),
        fsmSamDmeExtvmmEpClusterRoleFsmFail(1000294),
        fsmSamDmeVmLifeCyclePolicyConfigFsmFail(1000299),
        fsmSamDmeEquipmentBeaconLedIlluminateFsmFail(1000302),
        fsmSamDmeEtherServerIntfioConfigSpeedFsmFail(1000311),
        fsmSamDmeComputePhysicalUpdatebiosFsmFail(1000321),
        fsmSamDmeComputePhysicalActivatebiosFsmFail(1000322),
        fsmSamDmeIdentIdentRequestUpdateIdentFsmFail(1000352),
        fsmSamDmeIdentMetaSystemSyncFsmFail(1000353),
        fsmSamDmeComputePhysicalResetIpmiFsmFail(1000366),
        fsmSamDmeComputePhysicalFwUpgradeFsmFail(1000367),
        fsmSamDmeComputeRackUnitAdapterResetFsmFail(1000368),
        fsmSamDmePortpioInCompatSfpReplacedFsmFail(1000398),
        fsmSamDmeExtpolEpRegisterFsmFsmFail(1000399),
        fsmSamDmeExtpolRegistryCrossDomainConfigFsmFail(1000400),
        fsmSamDmeExtpolRegistryCrossDomainDeleteFsmFail(1000401),
        fsmSamDmeNfsMountInstMountFsmFail(1000417),
        fsmSamDmeNfsMountInstUnmountFsmFail(1000418),
        fsmSamDmeNfsMountDefReportNfsMountSuspendFsmFail(1000419),
        fsmSamDmeStorageSystemSyncFsmFail(1000435),
        fsmSamDmeFirmwareSystemDeployFsmFail(1000448),
        fsmSamDmeFirmwareSystemApplyCatalogPackFsmFail(1000449),
        fsmSamDmeComputeServerDiscPolicyResolveScrubPolicyFsmFail(1000466),
        fsmSamDmeSwFcSanBorderActivateZoneSetFsmFail(1000479),
        fsmSamDmeExtpolEpRepairCertFsmFail(1000486),
        fsmSamDmePolicyControlEpOperateFsmFail(1000487),
        fsmSamDmePolicyPolicyScopeReleasePolicyFsmFsmFail(1000488),
        fsmSamDmePolicyPolicyScopeReleaseOperationFsmFsmFail(1000489),
        fsmSamDmePolicyPolicyScopeReleaseStorageFsmFsmFail(1000490),
        fsmSamDmePolicyPolicyScopeResolveManyPolicyFsmFsmFail(1000491),
        fsmSamDmePolicyPolicyScopeResolveManyOperationFsmFsmFail(1000492),
        fsmSamDmePolicyPolicyScopeResolveManyStorageFsmFsmFail(1000493),
        fsmSamDmePolicyPolicyScopeReleaseManyPolicyFsmFsmFail(1000494),
        fsmSamDmePolicyPolicyScopeReleaseManyOperationFsmFsmFail(1000495),
        fsmSamDmePolicyPolicyScopeReleaseManyStorageFsmFsmFail(1000496),
        fsmSamDmePolicyPolicyScopeResolveAllPolicyFsmFsmFail(1000497),
        fsmSamDmePolicyPolicyScopeResolveAllOperationFsmFsmFail(1000498),
        fsmSamDmePolicyPolicyScopeResolveAllStorageFsmFsmFail(1000499),
        fsmSamDmePolicyPolicyScopeReleaseAllPolicyFsmFsmFail(1000500),
        fsmSamDmePolicyPolicyScopeReleaseAllOperationFsmFsmFail(1000501),
        fsmSamDmePolicyPolicyScopeReleaseAllStorageFsmFsmFail(1000502),
        fsmSamDmeMgmtExportPolicyReportConfigCopyFsmFail(1000524),
        fsmSamDmeExtpolProviderReportConfigImportFsmFail(1000525),
        fsmSamDmeObserveObservedResolvePolicyFsmFsmFail(1000531),
        fsmSamDmeObserveObservedResolveResourceFsmFsmFail(1000532),
        fsmSamDmeObserveObservedResolvevmfsmFsmFail(1000533),
        fsmSamDmeObserveObservedResolveControllerFsmFsmFail(1000534),
        fsmSamDmeMgmtControllerRegistryConfigFsmFail(1000539),
        fsmSamDmeGmetaHolderInventoryFsmFail(1000648),
        fsmSamDmeComputePhysicalCimcSessionDeleteFsmFail(1000649),
        fsmSamDmePolicyControlledTypeOperateFsmFail(1000652),
        fsmSamDmeFabricVnetEpSyncEpPushVnetEpDeletionFsmFail(1000659),
        fsmSamDmeSwEthLanFlowMonDeployFsmFail(1000679),
        fsmSamDmeMgmtipv6IfAddrSwMgmtOobIpv6IfConfigFsmFail(1000705),
        fsmSamDmeComputePhysicalUpdateBoardControllerFsmFail(1000707),
        fsmSamDmeExtvmmNetworkSetsDeployFsmFail(1000743),
        fsmSamDmeComputePhysicalConfigBoardFsmFail(1000747),
        fsmSamDmeComputePhysicalResetMemoryErrorsFsmFail(1000748),
        fsmSamDmeMgmtControllerExtMgmtInterfaceConfigFsmFail(1000754),
        fsmSamDmeComputeRackUnitCreateDhcpEntryFsmFail(1000755),
        fsmSamDmeComputePhysicalServiceInfraDeployFsmFail(1000756),
        fsmSamDmeComputePhysicalServiceInfraWithdrawFsmFail(1000757),
        fsmSamDmeEquipmentiocardBaseFePresenceFsmFail(1000848),
        fsmSamDmeEquipmentiocardBaseFeConnFsmFail(1000849),
        fsmSamDmeMgmtControllerLockConfigFsmFail(1000853),
        fsmSamDmeSdAppInstanceInstallApplicationFsmFail(1000859),
        fsmSamDmeSysdebugLogExportPolicyConfigureFsmFail(1000870),
        fsmSamDmeComputePhysicalFlashControllerFsmFail(1000879),
        fsmSamDmeOsControllerDeployosFsmFail(1000903),
        fsmSamDmeNhTableHolderConfigureLinksFsmFail(1000906),
        fsmSamDmeStorageFlexFlashControllermopsResetFsmFail(1000912),
        fsmSamDmeStorageFlexFlashControllermopsFormatFsmFail(1000913),
        fsmSamDmeStorageFlexFlashControllermopsPairFsmFail(1000914),
        fsmSamDmeIdentMetaSystemFprcUnivSyncFsmFail(1000917),
        fsmSamDmeComputePhysicalEnableCimcSecureBootFsmFail(1000937),
        fsmSamDmeSdAppInstanceStartApplicationFsmFail(1000951),
        fsmSamDmeSdLduProvisionlduFsmFail(1000952),
        fsmSamDmeSwExtUtilityConfPortBreakoutFsmFail(1000957),
        fsmSamDmeSmAppDeleteFsmFail(1000969),
        fsmSamDmeSmSecSvcRestoreApplicationFsmFail(1000970),
        fsmSamDmeApplicationDownloaderDownloadFsmFail(1000985),
        fsmSamDmeNhTableHolderBootstrapLinksFsmFail(1000988),
        fsmSamDmeFirmwarePlatformPackPlatformVersionFsmFail(1000994),
        fsmSamDmeLicenseSmartConfigSetConfigFsmFail(1000997),
        fsmSamDmeOsControllerUpgradeosFsmFail(1001010),
        fsmSamDmeOsControllerInitosFsmFail(1001011),
        fsmSamDmeSdAppInstanceUpgradeApplicationFsmFail(1001012),
        fsmSamDmeSdAppInstanceStopApplicationFsmFail(1001013),
        fsmSamDmeSdAppInstanceUninstallApplicationFsmFail(1001014),
        fsmSamDmeSdSlotChangePlatformLogLevelFsmFail(1001015),
        fsmSamDmeSdAppInstanceBundleDataPortsFsmFail(1001016),
        fsmSamDmeSdLogicalDeviceConfigureLinksFsmFail(1001017),
        fsmSamDmeSdExternalLduLinkUpdateInterfaceStatusFsmFail(1001018),
        fsmSamDmeSdAppInstanceUpdateClusterConfigurationFsmFail(1001019),
        fsmSamDmeSdSlotFormatDiskFsmFail(1001020),
        fsmSamDmeSdSlotSynchTimeZoneFsmFail(1001021),
        fsmSamDmeSdAppAttributeCtrlGetAppAttributesFsmFail(1001022),
        fsmSamDmeSdMgmtInfoUpdateMgmtInfoFsmFail(1001023),
        fsmSamDmeSdNetMgmtBootstrapUpdateNetMgmtBootstrapFsmFail(1001024),
        fsmSamDmeSwSspEthMonDeployFsmFail(1001040),
        fsmSamDmeSdClusterBootstrapUpdateClusterConfigurationFsmFail(1001043),
        fsmSamDmeSmAppInstanceResetApplicationFsmFail(1001048),
        fsmSamDmeIpsecEpUpdateEpFsmFail(1001060),
        fsmSamDmeEtherFtwPortPairConfigFtwFsmFail(1001063),
        fsmSamDmeSdLinkUpdateInterfaceStatusFsmFail(1001064),
        fsmSamDmeSdUpgradeTaskStopUpgradeStartAppFsmFail(1001065),
        fsmSamDmeSwSspEthMonSrcPhyEpDeleteFsmFail(1001074),
        fsmSamDmeFirmwareSupFirmwareDeployFsmFail(1001075),
        fsmSamDmeEquipmentChassisShutdownChassisFsmFail(1001083),
        fsmSamDmeSmCloudConnectorRegisterCloudConnectorFsmFail(1001091),
        fsmSamDmeSmCloudConnectorUnRegisterCloudConnectorFsmFail(1001092),
        fsmSamDmeSmAppVerifyApplicationFsmFail(1001093),
        fsmSamDmeSmLogicalDeviceConfigureFsmFail(1001096),
        fsmSamDmeSdLduUpdateInterfaceStatusFsmFail(1001098),
        fsmSamDmeSdLogicalDeviceConfigureUserMacsFsmFail(1001099),
        fsmSamDmeEquipmentChassisRebootChassisFsmFail(1001100),
        fsmSamDmeFirmwareValidationStatusValidateFsmFail(1001104),
        fsmSamDmeSdPortsBundleBundleDataPortsFsmFail(1001121),
        fsmSamDmeSdHotfixInstallHotfixFsmFail(1001122),
        fsmSamDmeSdHotfixUninstallHotfixFsmFail(1001123),
        fsmSamDmeOsControllerInstallLicenseFsmFail(1001132),
        fsmSamDmeSmUnsignedCspLicenseDeployFsmFail(1001138),
        fsmSamDmeSmLicenseFileDeleteFsmFail(1001139),
        fsmSamDmeComputePhysicalUpdateAdaptorBootFsmFail(1001152),
        fsmSamDmeSmAppInstance2ResetApplicationFsmFail(1001169),
        fsmSamDmeSdAppInstSettingsTaskSendAppInstSettingsFsmFail(1001176),
        fsmSamDmeSdLogicalDeviceConfigureMacsFsmFail(1001178),
        fsmSamDmeCommTelemetryDataExchSeqFsmFail(1001194),
        fsmSamDmeCommTelemetryEnableDisableTelemetryFsmFail(1001195),
        fsmSamDmeSdCspMetaCtrlRetrievecspmetaFsmFail(1001196),
        fsmSamDmeSdAppInstanceGracefulStopAppFsmFail(1001197),
        fsmSamDmeComputePhysicalHardPowercycleFsmFail(1001209),
        unrVnicTemplStatsPolicyName(4522530),
        unrVnicSanConnTemplQosPolicyName(4522532),
        unrVnicIpV4PooledAddrName(4522544),
        unrVnicVnicStatsPolicyName(4522561),
        unrVnicProfileQosPolicyName(4522588),
        unrVnicFcNodeIdentPoolName(4522603),
        unrLsServerSrcTemplName(4525234),
        unrLsServerIdentPoolName(4525239),
        unrLsServerBootPolicyName(4525240),
        unrLsServerLocalDiskPolicyName(4525241),
        unrLsServerScrubPolicyName(4525247),
        unrLsServerDynamicConPolicyName(4525248),
        unrLsServerHostFwPolicyName(4525250),
        unrLsServerMgmtFwPolicyName(4525251),
        unrLsServerMgmtAccessPolicyName(4525252),
        unrLsServerSolPolicyName(4525253),
        unrLsServerStatsPolicyName(4525254),
        unrVnicEtherBaseQosPolicyName(4526517),
        unrVnicEtherBaseNwCtrlPolicyName(4526850),
        unrVnicProfileNwCtrlPolicyName(4526851),
        unrLsServerVconProfileName(4526901),
        unrLsServerBiosProfileName(4526902),
        unrLsRequirementName(4527601),
        unrVnicSanConnTemplIdentPoolName(4528207),
        unrVnicLanConnTemplNwCtrlPolicyName(4528209),
        unrVnicLanConnTemplIdentPoolName(4528211),
        unrVnicFcBaseAdaptorProfileName(4528216),
        unrVnicFcBaseIdentPoolName(4528218),
        unrVnicFcBaseNwTemplName(4528220),
        unrVnicEtherBaseAdaptorProfileName(4528223),
        unrVnicEtherBaseIdentPoolName(4528225),
        unrVnicEtherBaseNwTemplName(4528227),
        unrVnicLanConnTemplQosPolicyName(4528268),
        unrVnicFcBaseQosPolicyName(4528270),
        unrLsServerPowerPolicyName(4528591),
        unrLsServerMaintPolicyName(4528596),
        unrTrigTriggerableScheduler(4528842),
        unrFabricEthEstcEpNwCtrlPolicyName(4529444),
        unrFabricEthEstcPcNwCtrlPolicyName(4529447),
        unrVnicIpv4PooledIscsiAddrIdentPoolName(4529495),
        unrVnicIscsiIqnIdentPoolName(4529514),
        unrVnicIscsiAuthProfileName(4529520),
        unrVnicIscsiStaticTargetIfAuthProfileName(4529533),
        unrVnicFcBasePinToGroupName(4529971),
        unrVnicEtherBasePinToGroupName(4529973),
        unrFaultSuppressTaskSuppressPolicyName(4530046),
        unrVnicConnDefLanConnPolicyName(4530080),
        unrVnicConnDefSanConnPolicyName(4530082),
        unrVnicFcGroupTemplStorageConnPolicyName(4530097),
        unrVnicDynamicConPolicyRefConPolicyName(4530100),
        unrVnicAgroupStatsPolicyName(4530113),
        unrVnicFcGroupDefStorageConnPolicyName(4530122),
        unrVnicIscsiBaseIdentPoolName(4530125),
        unrVnicIscsiBaseAdaptorProfileName(4530127),
        unrFabricVlanMcastPolicyName(4530143),
        unrVnicIscsiBootVnicIqnIdentPoolName(4530204),
        unrVnicIscsiBootVnicAuthProfileName(4530206),
        unrLsServerExtippoolName(4530727),
        unrVnicIscsiNodeIqnIdentPoolName(4531222),
        unrVnicVmqConPolicyRefConPolicyName(4531400),
        unrVnicUsnicConPolicyRefConPolicyName(4531404),
        unrVnicIpV4MgmtPooledAddrName(4531414),
        unrVnicIpV6MgmtPooledAddrName(4531419),
        unrFabricFcoeSanEpEthLinkProfileName(4531518),
        unrFabricEthLinkProfileUdldLinkPolicyName(4531578),
        unrFabricEthLinkProfileCdpLinkPolicyName(4531580),
        unrFabricFcoeSanPcEpEthLinkProfileName(4531707),
        unrFabricEthLanEpEthLinkProfileName(4531711),
        unrFabricEthLanPcEpEthLinkProfileName(4531714),
        unrFabricFlowMonitorFlowMonRecordDef(4531768),
        unrFabricFlowMonitorFlowTimeoutPolicy(4531770),
        unrFabricNetflowMonitorRefNfMonitorName(4531775),
        unrFabricFlowMonExporterFlowExpProfile(4531796),
        unrFabricNetflowMonExporterRefNfMonExporterName(4531810),
        unrExtvmmVmnetworkDefinitionExtIpPoolName(4531828),
        unrExtvmmVmnetworkFabricNetworkName(4531835),
        unrExtvmmVmndrefVmNetworkDefName(4531839),
        unrExtvmmFndreferenceFnDefName(4531844),
        unrFabricEthLanPcLacpPolicyName(4532617),
        unrFabricFcoeSanPcLacpPolicyName(4532627),
        unrFabricEthEstcPcLacpPolicyName(4532629),
        unrLsServerVmediaPolicyName(4532693),
        unrLsServerKvmMgmtPolicyName(4532695),
        unrSdAppInstanceResourceProfileName(4534499),
        unrFabricEthLanPcNwCtrlPolicyName(4534828),
        unrFabricEthLanEpNwCtrlPolicyName(4534849)
    }

CfprConditionSeverity ::= TEXTUAL-CONVENTION
    STATUS        current
    DESCRIPTION
        ""
    SYNTAX        INTEGER
    {
        cleared(0),
        info(1),
        condition(2),
        warning(3),
        minor(4),
        major(5),
        critical(6)
    }

CfprConditionTag ::= TEXTUAL-CONVENTION
    STATUS        current
    DESCRIPTION
        ""
    SYNTAX        BITS
    {
        server(0),
        network(1),
        storage(2),
        pod(3),
        security(4),
        operations(5),
        fsmstagefail(6),
        fsmstageretry(7),
        fsmstageremoteinv(8)
    }

CfprConditionType ::= TEXTUAL-CONVENTION
    STATUS        current
    DESCRIPTION
        ""
    SYNTAX        INTEGER
    {
        generic(0),
        configuration(1),
        fsm(2),
        network(3),
        server(4),
        management(5),
        equipment(6),
        environmental(7),
        operational(8),
        connectivity(9),
        security(10),
        sysdebug(11),
        any(65535)
    }

CfprConfigImpactResponseState ::= TEXTUAL-CONVENTION
    STATUS        current
    DESCRIPTION
        ""
    SYNTAX        INTEGER
    {
        notStarted(0),
        waiting(1),
        complete(2)
    }

CfprConfigSorterDirection ::= TEXTUAL-CONVENTION
    STATUS        current
    DESCRIPTION
        ""
    SYNTAX        INTEGER
    {
        ascending(0),
        descending(1)
    }

CfprDcxAdminState ::= TEXTUAL-CONVENTION
    STATUS        current
    DESCRIPTION
        ""
    SYNTAX        INTEGER
    {
        enabled(0),
        disabled(1)
    }

CfprDcxNsAllocStatus ::= TEXTUAL-CONVENTION
    STATUS        current
    DESCRIPTION
        ""
    SYNTAX        INTEGER
    {
        available(0),
        full(1),
        exceeded(2)
    }

CfprDcxOperState ::= TEXTUAL-CONVENTION
    STATUS        current
    DESCRIPTION
        ""
    SYNTAX        INTEGER
    {
        unknown(0),
        adminDown(1),
        linkDown(2),
        error(3),
        active(4),
        passive(5)
    }

CfprDcxProtState ::= TEXTUAL-CONVENTION
    STATUS        current
    DESCRIPTION
        ""
    SYNTAX        INTEGER
    {
        noProtection(0),
        active(1),
        passive(2)
    }

CfprDcxState ::= TEXTUAL-CONVENTION
    STATUS        current
    DESCRIPTION
        ""
    SYNTAX        INTEGER
    {
        unknown(0),
        present(1),
        creating(2),
        modifying(3),
        destroying(4),
        createPend(5),
        modifyPend(6),
        destroyPend(7)
    }

CfprDcxVIfProtRole ::= TEXTUAL-CONVENTION
    STATUS        current
    DESCRIPTION
        ""
    SYNTAX        INTEGER
    {
        unprotected(0),
        primary(1),
        backup(2)
    }

CfprDiagAdminState ::= TEXTUAL-CONVENTION
    STATUS        current
    DESCRIPTION
        ""
    SYNTAX        INTEGER
    {
        ready(0),
        trigger(1),
        cancel(2)
    }

CfprDiagBladeTestType ::= TEXTUAL-CONVENTION
    STATUS        current
    DESCRIPTION
        ""
    SYNTAX        INTEGER
    {
        disk(0),
        processor(1),
        memory(2),
        memtest(3),
        stress(4),
        pci(5)
    }

CfprDiagFailureAction ::= TEXTUAL-CONVENTION
    STATUS        current
    DESCRIPTION
        ""
    SYNTAX        BITS
    {
        techSupport(0),
        waitDebug(1),
        skipRemaining(2)
    }

CfprDiagNetworkTestType ::= TEXTUAL-CONVENTION
    STATUS        current
    DESCRIPTION
        ""
    SYNTAX        INTEGER
    {
        eth(0),
        fc(1)
    }

CfprDiagSrvCtrlType ::= TEXTUAL-CONVENTION
    STATUS        current
    DESCRIPTION
        ""
    SYNTAX        INTEGER
    {
        full(1),
        efi(33)
    }

CfprDiagStatus ::= TEXTUAL-CONVENTION
    STATUS        current
    DESCRIPTION
        ""
    SYNTAX        INTEGER
    {
        complete(0),
        inProgress(1),
        failed(2),
        notRun(3),
        cancelled(4),
        scheduled(5)
    }

CfprDiagStatusIssues ::= TEXTUAL-CONVENTION
    STATUS        current
    DESCRIPTION
        ""
    SYNTAX        BITS
    {
        testFailure(0),
        runCancelled(1),
        componentError(2),
        stagesCompleted(3),
        stageFailed(4)
    }

CfprDiagSuccessAction ::= TEXTUAL-CONVENTION
    STATUS        current
    DESCRIPTION
        ""
    SYNTAX        BITS
    {
        techSupport(0),
        waitDebug(1)
    }

CfprDiagTestOrder ::= TEXTUAL-CONVENTION
    STATUS        current
    DESCRIPTION
        ""
    SYNTAX        Gauge32 (1..64)

CfprDomainFeatureType ::= TEXTUAL-CONVENTION
    STATUS        current
    DESCRIPTION
        ""
    SYNTAX        INTEGER
    {
        major(0),
        minor(1)
    }

CfprDomainFunctionalState ::= TEXTUAL-CONVENTION
    STATUS        current
    DESCRIPTION
        ""
    SYNTAX        INTEGER
    {
        enabled(0),
        disabled(1)
    }

CfprDpsecForgedTransmit ::= TEXTUAL-CONVENTION
    STATUS        current
    DESCRIPTION
        ""
    SYNTAX        INTEGER
    {
        allow(0),
        deny(1)
    }

CfprEpqosDefinitionDelTaskFsmCurrentFsm ::= TEXTUAL-CONVENTION
    STATUS        current
    DESCRIPTION
        ""
    SYNTAX        INTEGER
    {
        nop(0),
        remove(319)
    }

CfprEpqosDefinitionDelTaskFsmStageName ::= TEXTUAL-CONVENTION
    STATUS        current
    DESCRIPTION
        ""
    SYNTAX        INTEGER
    {
        nop(0),
        removeBegin(319),
        removeLocal(320),
        removePeer(321),
        removeFail(370),
        removeSuccess(371)
    }

CfprEpqosDefinitionDelTaskFsmTaskItem ::= TEXTUAL-CONVENTION
    STATUS        current
    DESCRIPTION
        ""
    SYNTAX        INTEGER
    {
        nop(0),
        remove(319)
    }

CfprEpqosDefinitionFsmCurrentFsm ::= TEXTUAL-CONVENTION
    STATUS        current
    DESCRIPTION
        ""
    SYNTAX        INTEGER
    {
        nop(0),
        deploy(316)
    }

CfprEpqosDefinitionFsmStageName ::= TEXTUAL-CONVENTION
    STATUS        current
    DESCRIPTION
        ""
    SYNTAX        INTEGER
    {
        nop(0),
        deployBegin(316),
        deployLocal(317),
        deployPeer(318),
        deployFail(372),
        deploySuccess(373)
    }

CfprEpqosDefinitionFsmTaskItem ::= TEXTUAL-CONVENTION
    STATUS        current
    DESCRIPTION
        ""
    SYNTAX        INTEGER
    {
        nop(0),
        deploy(316)
    }

CfprEquipmentActiveStatus ::= TEXTUAL-CONVENTION
    STATUS        current
    DESCRIPTION
        ""
    SYNTAX        INTEGER
    {
        unknown(0),
        activated(1),
        deactivated(2)
    }

CfprEquipmentAdminPowerState ::= TEXTUAL-CONVENTION
    STATUS        current
    DESCRIPTION
        ""
    SYNTAX        INTEGER
    {
        policy(1),
        cycleImmediate(2),
        cycleWait(3)
    }

CfprEquipmentAirflowDirection ::= TEXTUAL-CONVENTION
    STATUS        current
    DESCRIPTION
        ""
    SYNTAX        INTEGER
    {
        unknown(0),
        frontToBack(1),
        backToFront(2)
    }

CfprEquipmentAppType ::= TEXTUAL-CONVENTION
    STATUS        current
    DESCRIPTION
        ""
    SYNTAX        INTEGER
    {
        native(0),
        container(1)
    }

CfprEquipmentAsicType ::= TEXTUAL-CONVENTION
    STATUS        current
    DESCRIPTION
        ""
    SYNTAX        INTEGER
    {
        unknown(0),
        gatos(1),
        carmel(2)
    }

CfprEquipmentBeaconLedFsmCurrentFsm ::= TEXTUAL-CONVENTION
    STATUS        current
    DESCRIPTION
        ""
    SYNTAX        INTEGER
    {
        nop(0),
        illuminate(1135)
    }

CfprEquipmentBeaconLedFsmStageName ::= TEXTUAL-CONVENTION
    STATUS        current
    DESCRIPTION
        ""
    SYNTAX        INTEGER
    {
        nop(0),
        illuminateBegin(1135),
        illuminateExecuteA(1136),
        illuminateExecuteB(1137),
        illuminateFail(1138),
        illuminateSuccess(1139)
    }

CfprEquipmentBeaconLedFsmTaskItem ::= TEXTUAL-CONVENTION
    STATUS        current
    DESCRIPTION
        ""
    SYNTAX        INTEGER
    {
        nop(0),
        illuminate(1135)
    }

CfprEquipmentBeaconLedState ::= TEXTUAL-CONVENTION
    STATUS        current
    DESCRIPTION
        ""
    SYNTAX        INTEGER
    {
        on(1),
        off(2),
        blinking(3),
        eth(4),
        fc(5)
    }

CfprEquipmentBiosPostState ::= TEXTUAL-CONVENTION
    STATUS        current
    DESCRIPTION
        ""
    SYNTAX        INTEGER
    {
        unknown(0),
        complete(1),
        notComplete(2),
        timeout(3)
    }

CfprEquipmentBiosUpdateMethod ::= TEXTUAL-CONVENTION
    STATUS        current
    DESCRIPTION
        ""
    SYNTAX        INTEGER
    {
        unknown(0),
        managementController(1),
        pnuos(2)
    }

CfprEquipmentBoardAggregationRole ::= TEXTUAL-CONVENTION
    STATUS        current
    DESCRIPTION
        ""
    SYNTAX        INTEGER
    {
        none(0),
        single(1),
        multiMaster(2),
        multiSlave(3)
    }

CfprEquipmentBoardConnectorType ::= TEXTUAL-CONVENTION
    STATUS        current
    DESCRIPTION
        ""
    SYNTAX        INTEGER
    {
        connUnlinked(1),
        connLinked(2)
    }

CfprEquipmentCardAdminState ::= TEXTUAL-CONVENTION
    STATUS        current
    DESCRIPTION
        ""
    SYNTAX        INTEGER
    {
        online(0),
        offline(1)
    }

CfprEquipmentChassisId ::= TEXTUAL-CONVENTION
    STATUS        current
    DESCRIPTION
        ""
    SYNTAX        Gauge32 (1..255)

CfprEquipmentChassisAdminState ::= TEXTUAL-CONVENTION
    STATUS        current
    DESCRIPTION
        ""
    SYNTAX        INTEGER
    {
        acknowledged(1),
        reAcknowledge(2),
        decommission(3),
        remove(4),
        enablePortChannel(5),
        disablePortChannel(6),
        autoAcknowledge(7)
    }

CfprEquipmentChassisConfigProgressIndicator ::= TEXTUAL-CONVENTION
    STATUS        current
    DESCRIPTION
        ""
    SYNTAX        INTEGER
    {
        ackNotInProgress(0),
        ackInProgress(1)
    }

CfprEquipmentChassisConfigState ::= TEXTUAL-CONVENTION
    STATUS        current
    DESCRIPTION
        ""
    SYNTAX        INTEGER
    {
        unInitialized(0),
        unAcknowledged(1),
        unsupportedConnectivity(2),
        ok(3),
        removing(4),
        ackInProgress(6),
        evaluation(7),
        acknowledged(8),
        autoAck(9)
    }

CfprEquipmentChassisFsmCurrentFsm ::= TEXTUAL-CONVENTION
    STATUS        current
    DESCRIPTION
        ""
    SYNTAX        INTEGER
    {
        nop(0),
        removeChassis(9),
        psuPolicyConfig(140),
        powerCap(643),
        dynamicReallocation(1048),
        shutdownChassis(1892),
        rebootChassis(1922)
    }

CfprEquipmentChassisFsmStageName ::= TEXTUAL-CONVENTION
    STATUS        current
    DESCRIPTION
        ""
    SYNTAX        INTEGER
    {
        nop(0),
        removeChassisBegin(9),
        removeChassisDecomission(10),
        removeChassisDisableEndPoint(11),
        removeChassisUnIdentifyLocal(12),
        removeChassisUnIdentifyPeer(13),
        removeChassisWait(14),
        psuPolicyConfigBegin(140),
        psuPolicyConfigExecute(141),
        psuPolicyConfigFail(374),
        psuPolicyConfigSuccess(375),
        removeChassisFail(376),
        removeChassisSuccess(377),
        powerCapBegin(643),
        powerCapConfig(644),
        powerCapFail(980),
        powerCapSuccess(981),
        dynamicReallocationBegin(1048),
        dynamicReallocationConfig(1049),
        dynamicReallocationFail(1051),
        dynamicReallocationSuccess(1052),
        shutdownChassisBegin(1892),
        shutdownChassisWaitForBladeShutdown(1893),
        shutdownChassisApplyShutdown(1894),
        shutdownChassisFail(1895),
        shutdownChassisSuccess(1896),
        rebootChassisBegin(1922),
        rebootChassisWaitForBladeShutdown(1923),
        rebootChassisApplyReboot(1924),
        rebootChassisFail(1931),
        rebootChassisSuccess(1932),
        shutdownChassisDebundlePort(1967),
        shutdownChassisPollDebundlePort(1968),
        shutdownChassisShutdownBlade(1969),
        rebootChassisDebundlePort(1970),
        rebootChassisPollDebundlePort(1971),
        rebootChassisShutdownBlade(1972)
    }

CfprEquipmentChassisFsmTaskFlags ::= TEXTUAL-CONVENTION
    STATUS        current
    DESCRIPTION
        ""
    SYNTAX        BITS
    {
        samDmeEquipmentChassisRebootChassisDebundle(35),
        samDmeEquipmentChassisRebootChassisReset(36)
    }

CfprEquipmentChassisFsmTaskItem ::= TEXTUAL-CONVENTION
    STATUS        current
    DESCRIPTION
        ""
    SYNTAX        INTEGER
    {
        nop(0),
        removeChassis(9),
        psuPolicyConfig(140),
        powerCap(643),
        dynamicReallocation(1048),
        shutdownChassis(1892),
        rebootChassis(1922)
    }

CfprEquipmentChassisIssues ::= TEXTUAL-CONVENTION
    STATUS        current
    DESCRIPTION
        ""
    SYNTAX        BITS
    {
        chassisThermal(0),
        chassisInoperable(1),
        chassisVoltage(2),
        chassisPerf(3),
        chassisPower(4),
        removed(5),
        config(6),
        chassisPostFailure(7),
        psuThermal(8),
        psuInoperable(9),
        psuVoltage(10),
        psuPerf(11),
        psuPower(12),
        fanThermal(13),
        fanInoperable(14),
        fanVoltage(15),
        fanPerf(16),
        fanPower(17),
        iocardThermal(18),
        iocardInoperable(19),
        iocardVoltage(20),
        iocardPerf(21),
        iocardPower(22),
        computeThermal(23),
        computeInoperable(24),
        computeVoltage(25),
        computePerf(26),
        computePower(27),
        iocardInaccessible(28),
        fabricConnProblem(29),
        fabricUnsupportedConn(30),
        chassisLimitExceeded(31),
        chassisVifCapacityReduced(32),
        chassisPortChannelEnabled(33),
        chassisUnsupported(34)
    }

CfprEquipmentChassisPowerOperState ::= TEXTUAL-CONVENTION
    STATUS        current
    DESCRIPTION
        ""
    SYNTAX        INTEGER
    {
        unknown(0),
        ok(1),
        failed(2),
        inputFailed(3),
        inputDegraded(4),
        outputFailed(5),
        outputDegraded(6),
        redundancyFailed(7),
        redundancyDegraded(8)
    }

CfprEquipmentChassisStatsThresholded ::= TEXTUAL-CONVENTION
    STATUS        current
    DESCRIPTION
        ""
    SYNTAX        BITS
    {
        inputPower(0),
        inputPowerAvg(1),
        inputPowerMax(2),
        inputPowerMin(3),
        outputPower(4),
        outputPowerAvg(5),
        outputPowerMax(6),
        outputPowerMin(7)
    }

CfprEquipmentChassisStatsHistThresholded ::= TEXTUAL-CONVENTION
    STATUS        current
    DESCRIPTION
        ""
    SYNTAX        BITS
    {
        inputPower(0),
        inputPowerAvg(1),
        inputPowerMax(2),
        inputPowerMin(3),
        outputPower(4),
        outputPowerAvg(5),
        outputPowerMax(6),
        outputPowerMin(7)
    }

CfprEquipmentCommStatus ::= TEXTUAL-CONVENTION
    STATUS        current
    DESCRIPTION
        ""
    SYNTAX        INTEGER
    {
        unknown(0),
        connected(1),
        disconnected(2)
    }

CfprEquipmentConnectionStatus ::= TEXTUAL-CONVENTION
    STATUS        current
    DESCRIPTION
        ""
    SYNTAX        BITS
    {
        a(0),
        b(1)
    }

CfprEquipmentCpuType ::= TEXTUAL-CONVENTION
    STATUS        current
    DESCRIPTION
        ""
    SYNTAX        INTEGER
    {
        other(0),
        ivyBridge(1),
        sandyBridge(2)
    }

CfprEquipmentDiscoveryCapOperPowerRequirement ::= TEXTUAL-CONVENTION
    STATUS        current
    DESCRIPTION
        ""
    SYNTAX        INTEGER
    {
        none(0),
        standby(1),
        full(2)
    }

CfprEquipmentDiscoveryState ::= TEXTUAL-CONVENTION
    STATUS        current
    DESCRIPTION
        ""
    SYNTAX        INTEGER
    {
        unknown(0),
        online(1),
        offline(2),
        discovered(3),
        unsupportedConnectivity(4),
        autoUpgrading(5)
    }

CfprEquipmentEnabledStatus ::= TEXTUAL-CONVENTION
    STATUS        current
    DESCRIPTION
        ""
    SYNTAX        INTEGER
    {
        unknown(0),
        enabled(1),
        disabled(2)
    }

CfprEquipmentEthPortSpeedCap ::= TEXTUAL-CONVENTION
    STATUS        current
    DESCRIPTION
        ""
    SYNTAX        BITS
    {
        auto(0),
        n1gbps(1),
        n10gbps(2),
        n20gbps(3),
        n40gbps(4),
        n100gbps(5),
        n10mbps(6),
        n100mbps(7)
    }

CfprEquipmentFanId ::= TEXTUAL-CONVENTION
    STATUS        current
    DESCRIPTION
        ""
    SYNTAX        Gauge32 (1..8)

CfprEquipmentFanModule ::= TEXTUAL-CONVENTION
    STATUS        current
    DESCRIPTION
        ""
    SYNTAX        Gauge32 (1..8)

CfprEquipmentFanTray ::= TEXTUAL-CONVENTION
    STATUS        current
    DESCRIPTION
        ""
    SYNTAX        Gauge32 (1..8)

CfprEquipmentFanModuleId ::= TEXTUAL-CONVENTION
    STATUS        current
    DESCRIPTION
        ""
    SYNTAX        Gauge32 (1..8)

CfprEquipmentFanModuleTray ::= TEXTUAL-CONVENTION
    STATUS        current
    DESCRIPTION
        ""
    SYNTAX        Gauge32 (1..1)

CfprEquipmentFanModuleStatsThresholded ::= TEXTUAL-CONVENTION
    STATUS        current
    DESCRIPTION
        ""
    SYNTAX        BITS
    {
        ambientTemp(0),
        ambientTempAvg(1),
        ambientTempMax(2),
        ambientTempMin(3)
    }

CfprEquipmentFanModuleStatsHistThresholded ::= TEXTUAL-CONVENTION
    STATUS        current
    DESCRIPTION
        ""
    SYNTAX        BITS
    {
        ambientTemp(0),
        ambientTempAvg(1),
        ambientTempMax(2),
        ambientTempMin(3)
    }

CfprEquipmentFanStatsThresholded ::= TEXTUAL-CONVENTION
    STATUS        current
    DESCRIPTION
        ""
    SYNTAX        BITS
    {
        speed(0),
        speedAvg(1),
        speedMax(2),
        speedMin(3)
    }

CfprEquipmentFanStatsHistThresholded ::= TEXTUAL-CONVENTION
    STATUS        current
    DESCRIPTION
        ""
    SYNTAX        BITS
    {
        speed(0),
        speedAvg(1),
        speedMax(2),
        speedMin(3)
    }

CfprEquipmentFexId ::= TEXTUAL-CONVENTION
    STATUS        current
    DESCRIPTION
        ""
    SYNTAX        Gauge32 (1..255)

CfprEquipmentFexCapProviderRole ::= TEXTUAL-CONVENTION
    STATUS        current
    DESCRIPTION
        ""
    SYNTAX        INTEGER
    {
        mgmt(1),
        data(2),
        full(3)
    }

CfprEquipmentFexEnvStatsThresholded ::= TEXTUAL-CONVENTION
    STATUS        current
    DESCRIPTION
        ""
    SYNTAX        BITS
    {
        die1(0),
        die1Avg(1),
        die1Max(2),
        die1Min(3),
        inlet(4),
        inlet1(5),
        inlet1Avg(6),
        inlet1Max(7),
        inlet1Min(8),
        inletAvg(9),
        inletMax(10),
        inletMin(11),
        outlet1(12),
        outlet1Avg(13),
        outlet1Max(14),
        outlet1Min(15),
        outlet2(16),
        outlet2Avg(17),
        outlet2Max(18),
        outlet2Min(19)
    }

CfprEquipmentFexEnvStatsHistThresholded ::= TEXTUAL-CONVENTION
    STATUS        current
    DESCRIPTION
        ""
    SYNTAX        BITS
    {
        die1(0),
        die1Avg(1),
        die1Max(2),
        die1Min(3),
        inlet(4),
        inlet1(5),
        inlet1Avg(6),
        inlet1Max(7),
        inlet1Min(8),
        inletAvg(9),
        inletMax(10),
        inletMin(11),
        outlet1(12),
        outlet1Avg(13),
        outlet1Max(14),
        outlet1Min(15),
        outlet2(16),
        outlet2Avg(17),
        outlet2Max(18),
        outlet2Min(19)
    }

CfprEquipmentFexFsmCurrentFsm ::= TEXTUAL-CONVENTION
    STATUS        current
    DESCRIPTION
        ""
    SYNTAX        INTEGER
    {
        nop(0),
        removeFex(636)
    }

CfprEquipmentFexFsmStageName ::= TEXTUAL-CONVENTION
    STATUS        current
    DESCRIPTION
        ""
    SYNTAX        INTEGER
    {
        nop(0),
        removeFexBegin(636),
        removeFexDecomission(637),
        removeFexUnIdentifyLocal(638),
        removeFexCleanupEntries(639),
        removeFexWait(640),
        removeFexFail(982),
        removeFexSuccess(983)
    }

CfprEquipmentFexFsmTaskItem ::= TEXTUAL-CONVENTION
    STATUS        current
    DESCRIPTION
        ""
    SYNTAX        INTEGER
    {
        nop(0),
        removeFex(636)
    }

CfprEquipmentFexPowerSummaryThresholded ::= TEXTUAL-CONVENTION
    STATUS        current
    DESCRIPTION
        ""
    SYNTAX        BITS
    {
        modulePower(0),
        modulePowerAvg(1),
        modulePowerMax(2),
        modulePowerMin(3),
        availablePower(4),
        availablePowerAvg(5),
        availablePowerMax(6),
        availablePowerMin(7),
        reservedPower(8),
        reservedPowerAvg(9),
        reservedPowerMax(10),
        reservedPowerMin(11),
        totalPower(12),
        totalPowerAvg(13),
        totalPowerMax(14),
        totalPowerMin(15)
    }

CfprEquipmentFexPowerSummaryHistThresholded ::= TEXTUAL-CONVENTION
    STATUS        current
    DESCRIPTION
        ""
    SYNTAX        BITS
    {
        modulePower(0),
        modulePowerAvg(1),
        modulePowerMax(2),
        modulePowerMin(3),
        availablePower(4),
        availablePowerAvg(5),
        availablePowerMax(6),
        availablePowerMin(7),
        reservedPower(8),
        reservedPowerAvg(9),
        reservedPowerMax(10),
        reservedPowerMin(11),
        totalPower(12),
        totalPowerAvg(13),
        totalPowerMax(14),
        totalPowerMin(15)
    }

CfprEquipmentFexPsuInputStatsThresholded ::= TEXTUAL-CONVENTION
    STATUS        current
    DESCRIPTION
        ""
    SYNTAX        BITS
    {
        current(0),
        currentAvg(1),
        currentMax(2),
        currentMin(3),
        power(4),
        powerAvg(5),
        powerMax(6),
        powerMin(7),
        voltage(8),
        voltageAvg(9),
        voltageMax(10),
        voltageMin(11)
    }

CfprEquipmentFexPsuInputStatsHistThresholded ::= TEXTUAL-CONVENTION
    STATUS        current
    DESCRIPTION
        ""
    SYNTAX        BITS
    {
        current(0),
        currentAvg(1),
        currentMax(2),
        currentMin(3),
        power(4),
        powerAvg(5),
        powerMax(6),
        powerMin(7),
        voltage(8),
        voltageAvg(9),
        voltageMax(10),
        voltageMin(11)
    }

CfprEquipmentHealthLedState ::= TEXTUAL-CONVENTION
    STATUS        current
    DESCRIPTION
        ""
    SYNTAX        INTEGER
    {
        normal(0),
        minor(1),
        critical(2)
    }

CfprEquipmentIOCardId ::= TEXTUAL-CONVENTION
    STATUS        current
    DESCRIPTION
        ""
    SYNTAX        Gauge32 (1..2)

CfprEquipmentIOCardBaseFsmCurrentFsm ::= TEXTUAL-CONVENTION
    STATUS        current
    DESCRIPTION
        ""
    SYNTAX        INTEGER
    {
        nop(0),
        fePresence(1579),
        feConn(1583)
    }

CfprEquipmentIOCardBaseFsmStageName ::= TEXTUAL-CONVENTION
    STATUS        current
    DESCRIPTION
        ""
    SYNTAX        INTEGER
    {
        nop(0),
        fePresenceBegin(1579),
        fePresenceCheckLicense(1580),
        fePresenceIdentify(1581),
        fePresenceConfigChassisId(1582),
        feConnBegin(1583),
        feConnConfigureSwMgmtEndPoint(1584),
        feConnConfigureVifNs(1585),
        feConnConfigureEndPoint(1586),
        feConnDiscoverChassis(1587),
        feConnEnableChassis(1588),
        feConnFail(1591),
        feConnSuccess(1592),
        fePresenceFail(1593),
        fePresenceSuccess(1594),
        feConnResetBlades(1830)
    }

CfprEquipmentIOCardBaseFsmTaskFlags ::= TEXTUAL-CONVENTION
    STATUS        current
    DESCRIPTION
        ""
    SYNTAX        BITS
    {
        samDmeEquipmentIOCardBaseFePresenceFprConfig(14),
        samDmeEquipmentIOCardBaseFePresenceMiniFprConfig(15)
    }

CfprEquipmentIOCardBaseFsmTaskItem ::= TEXTUAL-CONVENTION
    STATUS        current
    DESCRIPTION
        ""
    SYNTAX        INTEGER
    {
        nop(0),
        fePresence(1579),
        feConn(1583)
    }

CfprEquipmentIOCardFsmCurrentFsm ::= TEXTUAL-CONVENTION
    STATUS        current
    DESCRIPTION
        ""
    SYNTAX        INTEGER
    {
        nop(0),
        resetCmc(461),
        muxOffline(645),
        resetIom(817),
        fePresence(1579),
        feConn(1583)
    }

CfprEquipmentIOCardFsmStageName ::= TEXTUAL-CONVENTION
    STATUS        current
    DESCRIPTION
        ""
    SYNTAX        INTEGER
    {
        nop(0),
        resetCmcBegin(461),
        resetCmcExecute(462),
        resetCmcFail(465),
        resetCmcSuccess(466),
        muxOfflineBegin(645),
        muxOfflineCleanupEntries(646),
        resetIomBegin(817),
        resetIomExecute(818),
        muxOfflineFail(984),
        muxOfflineSuccess(985),
        resetIomFail(986),
        resetIomSuccess(987),
        fePresenceBegin(1579),
        fePresenceCheckLicense(1580),
        fePresenceIdentify(1581),
        fePresenceConfigChassisId(1582),
        feConnBegin(1583),
        feConnConfigureSwMgmtEndPoint(1584),
        feConnConfigureVifNs(1585),
        feConnConfigureEndPoint(1586),
        feConnDiscoverChassis(1587),
        feConnEnableChassis(1588),
        feConnFail(1591),
        feConnSuccess(1592),
        fePresenceFail(1593),
        fePresenceSuccess(1594),
        feConnResetBlades(1830)
    }

CfprEquipmentIOCardFsmTaskItem ::= TEXTUAL-CONVENTION
    STATUS        current
    DESCRIPTION
        ""
    SYNTAX        INTEGER
    {
        nop(0),
        resetCmc(461),
        muxOffline(645),
        resetIom(817)
    }

CfprEquipmentIOCardIssues ::= TEXTUAL-CONVENTION
    STATUS        current
    DESCRIPTION
        ""
    SYNTAX        BITS
    {
        thermal(0),
        inoperable(1),
        voltage(2),
        perf(3),
        power(4),
        removed(5),
        fabricPortProblem(6),
        postFailure(7),
        serverPortProblem(8),
        fabricpcLinkAutoAckBlocked(9)
    }

CfprEquipmentIOCardStatsThresholded ::= TEXTUAL-CONVENTION
    STATUS        current
    DESCRIPTION
        ""
    SYNTAX        BITS
    {
        ambientTemp(0),
        ambientTempAvg(1),
        ambientTempMax(2),
        ambientTempMin(3),
        dimmTemp(4),
        dimmTempAvg(5),
        dimmTempMax(6),
        dimmTempMin(7),
        procTemp(8),
        procTempAvg(9),
        procTempMax(10),
        procTempMin(11),
        temp(12),
        tempAvg(13),
        tempMax(14),
        tempMin(15)
    }

CfprEquipmentIOCardStatsHistThresholded ::= TEXTUAL-CONVENTION
    STATUS        current
    DESCRIPTION
        ""
    SYNTAX        BITS
    {
        ambientTemp(0),
        ambientTempAvg(1),
        ambientTempMax(2),
        ambientTempMin(3),
        dimmTemp(4),
        dimmTempAvg(5),
        dimmTempMax(6),
        dimmTempMin(7),
        procTemp(8),
        procTempAvg(9),
        procTempMax(10),
        procTempMin(11),
        temp(12),
        tempAvg(13),
        tempMax(14),
        tempMin(15)
    }

CfprEquipmentInternalFanType ::= TEXTUAL-CONVENTION
    STATUS        current
    DESCRIPTION
        ""
    SYNTAX        INTEGER
    {
        chassis(0),
        switch(1),
        fex(2)
    }

CfprEquipmentIsSupported ::= TEXTUAL-CONVENTION
    STATUS        current
    DESCRIPTION
        ""
    SYNTAX        INTEGER
    {
        no(0),
        yes(1)
    }

CfprEquipmentLedColor ::= TEXTUAL-CONVENTION
    STATUS        current
    DESCRIPTION
        ""
    SYNTAX        INTEGER
    {
        unknown(0),
        green(1),
        amber(2),
        red(3),
        blue(4)
    }

CfprEquipmentLedLocatorState ::= TEXTUAL-CONVENTION
    STATUS        current
    DESCRIPTION
        ""
    SYNTAX        INTEGER
    {
        inactive(0),
        off(1),
        on(2)
    }

CfprEquipmentLedOperState ::= TEXTUAL-CONVENTION
    STATUS        current
    DESCRIPTION
        ""
    SYNTAX        INTEGER
    {
        unknown(0),
        on(1),
        off(2),
        blinking(3),
        eth(4),
        fc(5)
    }

CfprEquipmentLocatorLedFsmCurrentFsm ::= TEXTUAL-CONVENTION
    STATUS        current
    DESCRIPTION
        ""
    SYNTAX        INTEGER
    {
        nop(0),
        setLocatorLed(15),
        setFeLocatorLed(641),
        setFiLocatorLed(1090)
    }

CfprEquipmentLocatorLedFsmStageName ::= TEXTUAL-CONVENTION
    STATUS        current
    DESCRIPTION
        ""
    SYNTAX        INTEGER
    {
        nop(0),
        setLocatorLedBegin(15),
        setLocatorLedExecute(16),
        setLocatorLedFail(382),
        setLocatorLedSuccess(383),
        setFeLocatorLedBegin(641),
        setFeLocatorLedExecute(642),
        setFeLocatorLedFail(988),
        setFeLocatorLedSuccess(989),
        setFiLocatorLedBegin(1090),
        setFiLocatorLedExecute(1091),
        setFiLocatorLedFail(1140),
        setFiLocatorLedSuccess(1141)
    }

CfprEquipmentLocatorLedFsmTaskItem ::= TEXTUAL-CONVENTION
    STATUS        current
    DESCRIPTION
        ""
    SYNTAX        INTEGER
    {
        nop(0),
        setLocatorLed(15),
        setFeLocatorLed(641),
        setFiLocatorLed(1090)
    }

CfprEquipmentMediaType ::= TEXTUAL-CONVENTION
    STATUS        current
    DESCRIPTION
        ""
    SYNTAX        INTEGER
    {
        none(0),
        rj45(1),
        sfp(2)
    }

CfprEquipmentMemoryUnitDiscoveryModifierAction ::= TEXTUAL-CONVENTION
    STATUS        current
    DESCRIPTION
        ""
    SYNTAX        INTEGER
    {
        unknown(0),
        setRevToOne(1),
        setRev(2),
        setRevStrict(3)
    }

CfprEquipmentMethod ::= TEXTUAL-CONVENTION
    STATUS        current
    DESCRIPTION
        ""
    SYNTAX        BITS
    {
        post(0),
        configCheck(1),
        diagCheck(2),
        selCheck(3)
    }

CfprEquipmentNetworkElementFanStatsThresholded ::= TEXTUAL-CONVENTION
    STATUS        current
    DESCRIPTION
        ""
    SYNTAX        BITS
    {
        drivePercentage(0),
        drivePercentageAvg(1),
        drivePercentageMax(2),
        drivePercentageMin(3),
        speed(4),
        speedAvg(5),
        speedMax(6),
        speedMin(7)
    }

CfprEquipmentNetworkElementFanStatsHistThresholded ::= TEXTUAL-CONVENTION
    STATUS        current
    DESCRIPTION
        ""
    SYNTAX        BITS
    {
        drivePercentage(0),
        drivePercentageAvg(1),
        drivePercentageMax(2),
        drivePercentageMin(3),
        speed(4),
        speedAvg(5),
        speedMax(6),
        speedMin(7)
    }

CfprEquipmentOperability ::= TEXTUAL-CONVENTION
    STATUS        current
    DESCRIPTION
        ""
    SYNTAX        INTEGER
    {
        unknown(0),
        operable(1),
        inoperable(2),
        degraded(3),
        poweredOff(4),
        powerProblem(5),
        removed(6),
        voltageProblem(7),
        thermalProblem(8),
        performanceProblem(9),
        accessibilityProblem(10),
        identityUnestablishable(11),
        biosPostTimeout(12),
        disabled(13),
        malformedFru(14),
        fabricConnProblem(51),
        fabricUnsupportedConn(52),
        config(81),
        equipmentProblem(82),
        decomissioning(83),
        chassisLimitExceeded(84),
        notSupported(100),
        discovery(101),
        discoveryFailed(102),
        identify(103),
        postFailure(104),
        upgradeProblem(105),
        peerCommProblem(106),
        autoUpgrade(107),
        linkActivateBlocked(108)
    }

CfprEquipmentOwnership ::= TEXTUAL-CONVENTION
    STATUS        current
    DESCRIPTION
        ""
    SYNTAX        INTEGER
    {
        unknown(0),
        owned(1),
        unowned(2)
    }

CfprEquipmentPOSTRecoverability ::= TEXTUAL-CONVENTION
    STATUS        current
    DESCRIPTION
        ""
    SYNTAX        INTEGER
    {
        unknown(0),
        recoverable(1),
        nonRecoverable(2)
    }

CfprEquipmentPasswordState ::= TEXTUAL-CONVENTION
    STATUS        current
    DESCRIPTION
        ""
    SYNTAX        INTEGER
    {
        unknown(0),
        set(1),
        notSet(2)
    }

CfprEquipmentPictureType ::= TEXTUAL-CONVENTION
    STATUS        current
    DESCRIPTION
        ""
    SYNTAX        INTEGER
    {
        unknown(0),
        front(1),
        back(2),
        top(3),
        bottom(4),
        left(5),
        right(6)
    }

CfprEquipmentPortAttribute ::= TEXTUAL-CONVENTION
    STATUS        current
    DESCRIPTION
        ""
    SYNTAX        INTEGER
    {
        none(0),
        scalability(1)
    }

CfprEquipmentPowerCapDefProfileMethod ::= TEXTUAL-CONVENTION
    STATUS        current
    DESCRIPTION
        ""
    SYNTAX        INTEGER
    {
        unknown(0),
        default(1),
        static(2),
        pnuos(3),
        nodemgr(4)
    }

CfprEquipmentPowerState ::= TEXTUAL-CONVENTION
    STATUS        current
    DESCRIPTION
        ""
    SYNTAX        INTEGER
    {
        unknown(0),
        on(1),
        test(2),
        off(3),
        online(4),
        offline(5),
        offduty(6),
        degraded(7),
        powerSave(8),
        error(9),
        ok(10),
        failed(11),
        oirFailed(12),
        oirInvalid(13),
        notSupported(100)
    }

CfprEquipmentPresence ::= TEXTUAL-CONVENTION
    STATUS        current
    DESCRIPTION
        ""
    SYNTAX        INTEGER
    {
        unknown(0),
        empty(1),
        equipped(10),
        missing(11),
        mismatch(12),
        equippedNotPrimary(13),
        equippedSlave(14),
        mismatchSlave(15),
        missingSlave(16),
        equippedIdentityUnestablishable(20),
        mismatchIdentityUnestablishable(21),
        equippedWithMalformedFru(22),
        inaccessible(30),
        unauthorized(40),
        notSupported(100)
    }

CfprEquipmentPsuType ::= TEXTUAL-CONVENTION
    STATUS        current
    DESCRIPTION
        ""
    SYNTAX        INTEGER
    {
        ac(1),
        dc(2)
    }

CfprEquipmentPsuId ::= TEXTUAL-CONVENTION
    STATUS        current
    DESCRIPTION
        ""
    SYNTAX        Gauge32 (1..4)

CfprEquipmentPsuEnvPsuType ::= TEXTUAL-CONVENTION
    STATUS        current
    DESCRIPTION
        ""
    SYNTAX        INTEGER
    {
        ac(1),
        dc(2)
    }

CfprEquipmentPsuInputSrc ::= TEXTUAL-CONVENTION
    STATUS        current
    DESCRIPTION
        ""
    SYNTAX        INTEGER
    {
        unknown(0),
        n210AC50380DC(1),
        n110AC(2),
        undetermined(3),
        n115AC230AC(4),
        n40DC62DC(5)
    }

CfprEquipmentPsuInputStatsThresholded ::= TEXTUAL-CONVENTION
    STATUS        current
    DESCRIPTION
        ""
    SYNTAX        BITS
    {
        current(0),
        currentAvg(1),
        currentMax(2),
        currentMin(3),
        power(4),
        powerAvg(5),
        powerMax(6),
        powerMin(7),
        voltage(8),
        voltageAvg(9),
        voltageMax(10),
        voltageMin(11)
    }

CfprEquipmentPsuInputStatsHistThresholded ::= TEXTUAL-CONVENTION
    STATUS        current
    DESCRIPTION
        ""
    SYNTAX        BITS
    {
        current(0),
        currentAvg(1),
        currentMax(2),
        currentMin(3),
        power(4),
        powerAvg(5),
        powerMax(6),
        powerMin(7),
        voltage(8),
        voltageAvg(9),
        voltageMax(10),
        voltageMin(11)
    }

CfprEquipmentPsuOutputStatsThresholded ::= TEXTUAL-CONVENTION
    STATUS        current
    DESCRIPTION
        ""
    SYNTAX        BITS
    {
        current(0),
        currentAvg(1),
        currentMax(2),
        currentMin(3),
        power(4),
        powerAvg(5),
        powerMax(6),
        powerMin(7),
        voltage(8),
        voltageAvg(9),
        voltageMax(10),
        voltageMin(11)
    }

CfprEquipmentPsuOutputStatsHistThresholded ::= TEXTUAL-CONVENTION
    STATUS        current
    DESCRIPTION
        ""
    SYNTAX        BITS
    {
        current(0),
        currentAvg(1),
        currentMax(2),
        currentMin(3),
        power(4),
        powerAvg(5),
        powerMax(6),
        powerMin(7),
        voltage(8),
        voltageAvg(9),
        voltageMax(10),
        voltageMin(11)
    }

CfprEquipmentPsuStateQualifier ::= TEXTUAL-CONVENTION
    STATUS        current
    DESCRIPTION
        ""
    SYNTAX        INTEGER
    {
        unknown(0),
        failure(1),
        overCurrent(2),
        overTemperature(3),
        inputLoss(4),
        fanFailure(5),
        inputCurrentWarning(6),
        inputVoltageWarning(7),
        ambientTemperatureWarning(8),
        outputCurrentWarning(9)
    }

CfprEquipmentPsuStatsThresholded ::= TEXTUAL-CONVENTION
    STATUS        current
    DESCRIPTION
        ""
    SYNTAX        BITS
    {
        ambientTemp(0),
        ambientTempAvg(1),
        ambientTempMax(2),
        ambientTempMin(3),
        input210v(4),
        input210vAvg(5),
        input210vMax(6),
        input210vMin(7),
        output12v(8),
        output12vAvg(9),
        output12vMax(10),
        output12vMin(11),
        output3v3(12),
        output3v3Avg(13),
        output3v3Max(14),
        output3v3Min(15),
        outputCurrent(16),
        outputCurrentAvg(17),
        outputCurrentMax(18),
        outputCurrentMin(19),
        outputPower(20),
        outputPowerAvg(21),
        outputPowerMax(22),
        outputPowerMin(23)
    }

CfprEquipmentPsuStatsHistThresholded ::= TEXTUAL-CONVENTION
    STATUS        current
    DESCRIPTION
        ""
    SYNTAX        BITS
    {
        ambientTemp(0),
        ambientTempAvg(1),
        ambientTempMax(2),
        ambientTempMin(3),
        input210v(4),
        input210vAvg(5),
        input210vMax(6),
        input210vMin(7),
        output12v(8),
        output12vAvg(9),
        output12vMax(10),
        output12vMin(11),
        output3v3(12),
        output3v3Avg(13),
        output3v3Max(14),
        output3v3Min(15),
        outputCurrent(16),
        outputCurrentAvg(17),
        outputCurrentMax(18),
        outputCurrentMin(19),
        outputPower(20),
        outputPowerAvg(21),
        outputPowerMax(22),
        outputPowerMin(23)
    }

CfprEquipmentPsuVoltageType ::= TEXTUAL-CONVENTION
    STATUS        current
    DESCRIPTION
        ""
    SYNTAX        INTEGER
    {
        unknown(0),
        ac(1),
        dc(2),
        dv(3),
        hvdc(4)
    }

CfprEquipmentRackUnitFanStatsThresholded ::= TEXTUAL-CONVENTION
    STATUS        current
    DESCRIPTION
        ""
    SYNTAX        BITS
    {
        speed(0),
        speedAvg(1),
        speedMax(2),
        speedMin(3)
    }

CfprEquipmentRackUnitFanStatsHistThresholded ::= TEXTUAL-CONVENTION
    STATUS        current
    DESCRIPTION
        ""
    SYNTAX        BITS
    {
        speed(0),
        speedAvg(1),
        speedMax(2),
        speedMin(3)
    }

CfprEquipmentRackUnitPsuStatsThresholded ::= TEXTUAL-CONVENTION
    STATUS        current
    DESCRIPTION
        ""
    SYNTAX        BITS
    {
        ambientTemp(0),
        ambientTempAvg(1),
        ambientTempMax(2),
        ambientTempMin(3),
        inputPower(4),
        inputPowerAvg(5),
        inputPowerMax(6),
        inputPowerMin(7),
        inputVoltage(8),
        inputVoltageAvg(9),
        inputVoltageMax(10),
        inputVoltageMin(11),
        outputCurrent(12),
        outputCurrentAvg(13),
        outputCurrentMax(14),
        outputCurrentMin(15),
        outputPower(16),
        outputPowerAvg(17),
        outputPowerMax(18),
        outputPowerMin(19),
        outputVoltage(20),
        outputVoltageAvg(21),
        outputVoltageMax(22),
        outputVoltageMin(23)
    }

CfprEquipmentRackUnitPsuStatsHistThresholded ::= TEXTUAL-CONVENTION
    STATUS        current
    DESCRIPTION
        ""
    SYNTAX        BITS
    {
        ambientTemp(0),
        ambientTempAvg(1),
        ambientTempMax(2),
        ambientTempMin(3),
        inputPower(4),
        inputPowerAvg(5),
        inputPowerMax(6),
        inputPowerMin(7),
        inputVoltage(8),
        inputVoltageAvg(9),
        inputVoltageMax(10),
        inputVoltageMin(11),
        outputCurrent(12),
        outputCurrentAvg(13),
        outputCurrentMax(14),
        outputCurrentMin(15),
        outputPower(16),
        outputPowerAvg(17),
        outputPowerMax(18),
        outputPowerMin(19),
        outputVoltage(20),
        outputVoltageAvg(21),
        outputVoltageMax(22),
        outputVoltageMin(23)
    }

CfprEquipmentRemovalConditions ::= TEXTUAL-CONVENTION
    STATUS        current
    DESCRIPTION
        ""
    SYNTAX        INTEGER
    {
        unknown(0),
        notApplicable(2),
        removableWhenOff(3),
        removableWhenOnOrOff(4)
    }

CfprEquipmentResetOn ::= TEXTUAL-CONVENTION
    STATUS        current
    DESCRIPTION
        ""
    SYNTAX        INTEGER
    {
        unknown(0),
        update(1),
        activate(2)
    }

CfprEquipmentSecureBios ::= TEXTUAL-CONVENTION
    STATUS        current
    DESCRIPTION
        ""
    SYNTAX        INTEGER
    {
        unknown(0),
        notSupported(1),
        supported(2)
    }

CfprEquipmentSensorThresholdStatus ::= TEXTUAL-CONVENTION
    STATUS        current
    DESCRIPTION
        ""
    SYNTAX        INTEGER
    {
        unknown(0),
        ok(1),
        upperNonRecoverable(2),
        upperCritical(3),
        upperNonCritical(4),
        lowerNonCritical(5),
        lowerCritical(6),
        lowerNonRecoverable(7),
        notSupported(100)
    }

CfprEquipmentShutdownAction ::= TEXTUAL-CONVENTION
    STATUS        current
    DESCRIPTION
        ""
    SYNTAX        INTEGER
    {
        none(0),
        shutdown(1),
        reboot(2)
    }

CfprEquipmentSlotArrayLocation ::= TEXTUAL-CONVENTION
    STATUS        current
    DESCRIPTION
        ""
    SYNTAX        INTEGER
    {
        unknown(0),
        front(1),
        back(2),
        top(3),
        bottom(4),
        left(5),
        right(6)
    }

CfprEquipmentSlotArrayOrientation ::= TEXTUAL-CONVENTION
    STATUS        current
    DESCRIPTION
        ""
    SYNTAX        INTEGER
    {
        unknown(0),
        vertical(1),
        horizontal(2)
    }

CfprEquipmentSlotArraySelector ::= TEXTUAL-CONVENTION
    STATUS        current
    DESCRIPTION
        ""
    SYNTAX        INTEGER
    {
        unknown(0),
        psu(1),
        fan(2),
        iocard(3),
        diskSlot(5),
        driveSlot(6),
        usbPort(7),
        ethernetPort(8),
        comPort(9),
        parPort(10),
        vgaPort(11),
        dviPort(12),
        keyboardPort(13),
        mousePort(14),
        gem(15),
        blade(16)
    }

CfprEquipmentSlotSpanOrientation ::= TEXTUAL-CONVENTION
    STATUS        current
    DESCRIPTION
        ""
    SYNTAX        INTEGER
    {
        unknown(0),
        inline(1),
        transverse(2)
    }

CfprEquipmentSlotStatus ::= TEXTUAL-CONVENTION
    STATUS        current
    DESCRIPTION
        ""
    SYNTAX        INTEGER
    {
        unknown(0),
        empty(1),
        equipped(10),
        missing(11),
        mismatch(12),
        equippedNotPrimary(13),
        equippedSlave(14),
        mismatchSlave(15),
        missingSlave(16),
        equippedIdentityUnestablishable(20),
        mismatchIdentityUnestablishable(21),
        equippedWithMalformedFru(22),
        inaccessible(30),
        unauthorized(40)
    }

CfprEquipmentStorageMethod ::= TEXTUAL-CONVENTION
    STATUS        current
    DESCRIPTION
        ""
    SYNTAX        INTEGER
    {
        unknown(0),
        singleFlash(1),
        dualFlash(2)
    }

CfprEquipmentSwitchIOCardId ::= TEXTUAL-CONVENTION
    STATUS        current
    DESCRIPTION
        ""
    SYNTAX        Gauge32 (1..2)

CfprEquipmentSwitchIOCardFsmCurrentFsm ::= TEXTUAL-CONVENTION
    STATUS        current
    DESCRIPTION
        ""
    SYNTAX        INTEGER
    {
        nop(0),
        fePresence(1579),
        feConn(1583)
    }

CfprEquipmentSwitchIOCardFsmStageName ::= TEXTUAL-CONVENTION
    STATUS        current
    DESCRIPTION
        ""
    SYNTAX        INTEGER
    {
        nop(0),
        fePresenceBegin(1579),
        fePresenceCheckLicense(1580),
        fePresenceIdentify(1581),
        fePresenceConfigChassisId(1582),
        feConnBegin(1583),
        feConnConfigureSwMgmtEndPoint(1584),
        feConnConfigureVifNs(1585),
        feConnConfigureEndPoint(1586),
        feConnDiscoverChassis(1587),
        feConnEnableChassis(1588),
        feConnFail(1591),
        feConnSuccess(1592),
        fePresenceFail(1593),
        fePresenceSuccess(1594),
        feConnResetBlades(1830)
    }

CfprEquipmentTpmConfigSupport ::= TEXTUAL-CONVENTION
    STATUS        current
    DESCRIPTION
        ""
    SYNTAX        INTEGER
    {
        unsupported(0),
        supported(1)
    }

CfprEquipmentTpmType ::= TEXTUAL-CONVENTION
    STATUS        current
    DESCRIPTION
        ""
    SYNTAX        INTEGER
    {
        unknown(0),
        physical(1),
        virtual(2)
    }

CfprEquipmentUnifiedPortAlgorithm ::= TEXTUAL-CONVENTION
    STATUS        current
    DESCRIPTION
        ""
    SYNTAX        INTEGER
    {
        none(0),
        slideRuleEthFirstDoubleRow(1),
        unrestricted(2),
        slideRuleEthFirstSingleRow(3),
        slideRuleFcFirstDoubleRow(4),
        slideRuleFcFirstSingleRow(5)
    }

CfprEquipmentUuidFeatureCapUuidSupportMode ::= TEXTUAL-CONVENTION
    STATUS        current
    DESCRIPTION
        ""
    SYNTAX        INTEGER
    {
        none(0),
        loose(1),
        strict(2)
    }

CfprEquipmentXcvrId ::= TEXTUAL-CONVENTION
    STATUS        current
    DESCRIPTION
        ""
    SYNTAX        Gauge32 (1..128)

CfprEquipmentXcvrStatus ::= TEXTUAL-CONVENTION
    STATUS        current
    DESCRIPTION
        ""
    SYNTAX        INTEGER
    {
        ok(0),
        nonSupport(1)
    }

CfprEquipmentXcvrType ::= TEXTUAL-CONVENTION
    STATUS        current
    DESCRIPTION
        ""
    SYNTAX        INTEGER
    {
        unknown(0),
        h10gcu1m(1),
        h10gcu3m(2),
        h10gcu5m(3),
        h10gcu7m(4),
        h10gusr(5),
        h10glrmsm(6),
        cwdm1471(7),
        cwdm1531(8),
        cwdm1551(9),
        fet(10),
        sfp(11),
        x2(12),
        n10gbasesr(13),
        n10gbaselr(14),
        n10gbaselrm(15),
        n10gbaseer(16),
        h10gacu1m(17),
        h10gacu3m(18),
        h10gacu5m(19),
        h10gacu7m(20),
        h10gacu10m(21),
        h10gacu15m(22),
        qsfp40gsr4(23),
        qsfph40gcu1m(24),
        qsfph40gcu2m(25),
        qsfph40gcu3m(26),
        qsfph40gcu5m(27),
        qsfp40gcr4(28),
        qsfp40glr4(29),
        qsfp4sfp10gcu1m(30),
        qsfp4sfp10gcu3m(31),
        qsfp4sfp10gcu5m(32),
        qsfp4x10gac1m(33),
        qsfp4x10gac3m(34),
        qsfp4x10gac5m(35),
        qsfp4x10gac7m(36),
        qsfp4x10gac10m(37),
        qsfploop(38),
        qsfph40gacu1m(39),
        qsfph40gacu3m(40),
        qsfph40gacu5m(41),
        qsfph40gacu7m(42),
        qsfph40gacu10m(43),
        qsfp4x10glr(44),
        qsfp40gcsr4(45),
        qsfpqsa(46),
        qsfp4sfp10gcu2m(47),
        qsfp40gfet(48),
        qsfp40gsrbd(49),
        qsfph40gaoc1m(50),
        qsfph40gaoc2m(51),
        qsfph40gaoc3m(52),
        qsfph40gaoc5m(53),
        qsfph40gaoc7m(54),
        qsfph40gaoc10m(55),
        qsfph40gaocunknown(56),
        qsfp4x10ga0c1m(57),
        qsfp4x10ga0c2m(58),
        qsfp4x10ga0c3m(59),
        qsfp4x10ga0c5m(60),
        qsfp4x10ga0c7m(61),
        qsfp4x10ga0c10m(62),
        qsfp4x10ga0cunknown(63),
        qsfpunknown(64),
        qsfp100gaoc(65),
        qsfp100gsr4(66),
        qsfp100glr4(67),
        qsfp100gcwdm4(68),
        qsfp100gpsm4(69),
        qsfp100gcr4(70),
        qsfp100gunknown(71),
        n1000baset(72),
        n1000basesx(73),
        n1000baselx(74),
        n1000baselh(75),
        n1000basezx(76),
        n1000basevx(77),
        n1000basex(78),
        n1000basecx(79),
        n1000baseunknown(80),
        glcexsmd(81),
        qsfph40gcu4m(82)
    }

CfprEquipmentCType ::= TEXTUAL-CONVENTION
    STATUS        current
    DESCRIPTION
        ""
    SYNTAX        INTEGER
    {
        sas(0),
        flash(1)
    }

CfprEquipmentFabricEpType ::= TEXTUAL-CONVENTION
    STATUS        current
    DESCRIPTION
        ""
    SYNTAX        INTEGER
    {
        unknown(0),
        chassis(1),
        fex(2),
        blade(3),
        rackUnit(4)
    }

CfprEtherCIoEpIfType ::= TEXTUAL-CONVENTION
    STATUS        current
    DESCRIPTION
        ""
    SYNTAX        INTEGER
    {
        unknown(0),
        physical(1),
        aggregation(2),
        virtual(3)
    }

CfprEtherCloudType ::= TEXTUAL-CONVENTION
    STATUS        current
    DESCRIPTION
        ""
    SYNTAX        INTEGER
    {
        unclassified(1),
        lan(2),
        san(3)
    }

CfprEtherErrStatsThresholded ::= TEXTUAL-CONVENTION
    STATUS        current
    DESCRIPTION
        ""
    SYNTAX        BITS
    {
        alignDelta(0),
        alignDeltaAvg(1),
        alignDeltaMax(2),
        alignDeltaMin(3),
        deferredTxDelta(4),
        deferredTxDeltaAvg(5),
        deferredTxDeltaMax(6),
        deferredTxDeltaMin(7),
        fcsDelta(8),
        fcsDeltaAvg(9),
        fcsDeltaMax(10),
        fcsDeltaMin(11),
        intMacRxDelta(12),
        intMacRxDeltaAvg(13),
        intMacRxDeltaMax(14),
        intMacRxDeltaMin(15),
        intMacTxDelta(16),
        intMacTxDeltaAvg(17),
        intMacTxDeltaMax(18),
        intMacTxDeltaMin(19),
        outDiscardDelta(20),
        outDiscardDeltaAvg(21),
        outDiscardDeltaMax(22),
        outDiscardDeltaMin(23),
        rcvDelta(24),
        rcvDeltaAvg(25),
        rcvDeltaMax(26),
        rcvDeltaMin(27),
        underSizeDelta(28),
        underSizeDeltaAvg(29),
        underSizeDeltaMax(30),
        underSizeDeltaMin(31),
        xmitDelta(32),
        xmitDeltaAvg(33),
        xmitDeltaMax(34),
        xmitDeltaMin(35)
    }

CfprEtherErrStatsHistThresholded ::= TEXTUAL-CONVENTION
    STATUS        current
    DESCRIPTION
        ""
    SYNTAX        BITS
    {
        alignDelta(0),
        alignDeltaAvg(1),
        alignDeltaMax(2),
        alignDeltaMin(3),
        deferredTxDelta(4),
        deferredTxDeltaAvg(5),
        deferredTxDeltaMax(6),
        deferredTxDeltaMin(7),
        fcsDelta(8),
        fcsDeltaAvg(9),
        fcsDeltaMax(10),
        fcsDeltaMin(11),
        intMacRxDelta(12),
        intMacRxDeltaAvg(13),
        intMacRxDeltaMax(14),
        intMacRxDeltaMin(15),
        intMacTxDelta(16),
        intMacTxDeltaAvg(17),
        intMacTxDeltaMax(18),
        intMacTxDeltaMin(19),
        outDiscardDelta(20),
        outDiscardDeltaAvg(21),
        outDiscardDeltaMax(22),
        outDiscardDeltaMin(23),
        rcvDelta(24),
        rcvDeltaAvg(25),
        rcvDeltaMax(26),
        rcvDeltaMin(27),
        underSizeDelta(28),
        underSizeDeltaAvg(29),
        underSizeDeltaMax(30),
        underSizeDeltaMin(31),
        xmitDelta(32),
        xmitDeltaAvg(33),
        xmitDeltaMax(34),
        xmitDeltaMin(35)
    }

CfprEtherExternalEpAdminState ::= TEXTUAL-CONVENTION
    STATUS        current
    DESCRIPTION
        ""
    SYNTAX        INTEGER
    {
        enabled(1),
        disabled(2)
    }

CfprEtherExternalEpLocale ::= TEXTUAL-CONVENTION
    STATUS        current
    DESCRIPTION
        ""
    SYNTAX        BITS
    {
        server(0),
        chassis(1),
        internal(2),
        external(3)
    }

CfprEtherExternalPcAdminState ::= TEXTUAL-CONVENTION
    STATUS        current
    DESCRIPTION
        ""
    SYNTAX        INTEGER
    {
        enabled(1),
        disabled(2)
    }

CfprEtherExternalPcLocale ::= TEXTUAL-CONVENTION
    STATUS        current
    DESCRIPTION
        ""
    SYNTAX        BITS
    {
        server(0),
        chassis(1),
        internal(2),
        external(3)
    }

CfprEtherFcoeInterfaceStatsThresholded ::= TEXTUAL-CONVENTION
    STATUS        current
    DESCRIPTION
        ""
    SYNTAX        BITS
    {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        droppedRxDelta(8),
        droppedRxDeltaAvg(9),
        droppedRxDeltaMax(10),
        droppedRxDeltaMin(11),
        droppedTxDelta(12),
        droppedTxDeltaAvg(13),
        droppedTxDeltaMax(14),
        droppedTxDeltaMin(15),
        errorsRxDelta(16),
        errorsRxDeltaAvg(17),
        errorsRxDeltaMax(18),
        errorsRxDeltaMin(19),
        errorsTxDelta(20),
        errorsTxDeltaAvg(21),
        errorsTxDeltaMax(22),
        errorsTxDeltaMin(23),
        packetsRxDelta(24),
        packetsRxDeltaAvg(25),
        packetsRxDeltaMax(26),
        packetsRxDeltaMin(27),
        packetsTxDelta(28),
        packetsTxDeltaAvg(29),
        packetsTxDeltaMax(30),
        packetsTxDeltaMin(31)
    }

CfprEtherFcoeInterfaceStatsHistThresholded ::= TEXTUAL-CONVENTION
    STATUS        current
    DESCRIPTION
        ""
    SYNTAX        BITS
    {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        droppedRxDelta(8),
        droppedRxDeltaAvg(9),
        droppedRxDeltaMax(10),
        droppedRxDeltaMin(11),
        droppedTxDelta(12),
        droppedTxDeltaAvg(13),
        droppedTxDeltaMax(14),
        droppedTxDeltaMin(15),
        errorsRxDelta(16),
        errorsRxDeltaAvg(17),
        errorsRxDeltaMax(18),
        errorsRxDeltaMin(19),
        errorsTxDelta(20),
        errorsTxDeltaAvg(21),
        errorsTxDeltaMax(22),
        errorsTxDeltaMin(23),
        packetsRxDelta(24),
        packetsRxDeltaAvg(25),
        packetsRxDeltaMax(26),
        packetsRxDeltaMin(27),
        packetsTxDelta(28),
        packetsTxDeltaAvg(29),
        packetsTxDeltaMax(30),
        packetsTxDeltaMin(31)
    }

CfprEtherFtwOperMode ::= TEXTUAL-CONVENTION
    STATUS        current
    DESCRIPTION
        ""
    SYNTAX        INTEGER
    {
        disabled(0),
        standby(1),
        switchBypass(2),
        phyBypass(3)
    }

CfprEtherFtwPortPairMode ::= TEXTUAL-CONVENTION
    STATUS        current
    DESCRIPTION
        ""
    SYNTAX        INTEGER
    {
        disabled(0),
        standby(1),
        switchBypass(2),
        phyBypass(3),
        unmanaged(4)
    }

CfprEtherFtwPortPairWdtState ::= TEXTUAL-CONVENTION
    STATUS        current
    DESCRIPTION
        ""
    SYNTAX        INTEGER
    {
        enabled(1),
        disabled(2)
    }

CfprEtherFtwPortPairFsmCurrentFsm ::= TEXTUAL-CONVENTION
    STATUS        current
    DESCRIPTION
        ""
    SYNTAX        INTEGER
    {
        nop(0),
        configFtw(1844)
    }

CfprEtherFtwPortPairFsmStageName ::= TEXTUAL-CONVENTION
    STATUS        current
    DESCRIPTION
        ""
    SYNTAX        INTEGER
    {
        nop(0),
        configFtwBegin(1844),
        configFtwConfigure(1845),
        configFtwFail(1876),
        configFtwSuccess(1877)
    }

CfprEtherFtwPortPairFsmTaskItem ::= TEXTUAL-CONVENTION
    STATUS        current
    DESCRIPTION
        ""
    SYNTAX        INTEGER
    {
        nop(0),
        configFtw(1844)
    }

CfprEtherIntFIoEpType ::= TEXTUAL-CONVENTION
    STATUS        current
    DESCRIPTION
        ""
    SYNTAX        BITS
    {
        lan(0),
        san(1),
        ipc(2)
    }

CfprEtherInternalPcLocale ::= TEXTUAL-CONVENTION
    STATUS        current
    DESCRIPTION
        ""
    SYNTAX        BITS
    {
        server(0),
        chassis(1),
        internal(2),
        external(3)
    }

CfprEtherLossStatsThresholded ::= TEXTUAL-CONVENTION
    STATUS        current
    DESCRIPTION
        ""
    SYNTAX        BITS
    {
        sqetestDelta(0),
        sqetestDeltaAvg(1),
        sqetestDeltaMax(2),
        sqetestDeltaMin(3),
        carrierSenseDelta(4),
        carrierSenseDeltaAvg(5),
        carrierSenseDeltaMax(6),
        carrierSenseDeltaMin(7),
        excessCollisionDelta(8),
        excessCollisionDeltaAvg(9),
        excessCollisionDeltaMax(10),
        excessCollisionDeltaMin(11),
        giantsDelta(12),
        giantsDeltaAvg(13),
        giantsDeltaMax(14),
        giantsDeltaMin(15),
        lateCollisionDelta(16),
        lateCollisionDeltaAvg(17),
        lateCollisionDeltaMax(18),
        lateCollisionDeltaMin(19),
        multiCollisionDelta(20),
        multiCollisionDeltaAvg(21),
        multiCollisionDeltaMax(22),
        multiCollisionDeltaMin(23),
        singleCollisionDelta(24),
        singleCollisionDeltaAvg(25),
        singleCollisionDeltaMax(26),
        singleCollisionDeltaMin(27),
        symbolDelta(28),
        symbolDeltaAvg(29),
        symbolDeltaMax(30),
        symbolDeltaMin(31)
    }

CfprEtherLossStatsHistThresholded ::= TEXTUAL-CONVENTION
    STATUS        current
    DESCRIPTION
        ""
    SYNTAX        BITS
    {
        sqetestDelta(0),
        sqetestDeltaAvg(1),
        sqetestDeltaMax(2),
        sqetestDeltaMin(3),
        carrierSenseDelta(4),
        carrierSenseDeltaAvg(5),
        carrierSenseDeltaMax(6),
        carrierSenseDeltaMin(7),
        excessCollisionDelta(8),
        excessCollisionDeltaAvg(9),
        excessCollisionDeltaMax(10),
        excessCollisionDeltaMin(11),
        giantsDelta(12),
        giantsDeltaAvg(13),
        giantsDeltaMax(14),
        giantsDeltaMin(15),
        lateCollisionDelta(16),
        lateCollisionDeltaAvg(17),
        lateCollisionDeltaMax(18),
        lateCollisionDeltaMin(19),
        multiCollisionDelta(20),
        multiCollisionDeltaAvg(21),
        multiCollisionDeltaMax(22),
        multiCollisionDeltaMin(23),
        singleCollisionDelta(24),
        singleCollisionDeltaAvg(25),
        singleCollisionDeltaMax(26),
        singleCollisionDeltaMin(27),
        symbolDelta(28),
        symbolDeltaAvg(29),
        symbolDeltaMax(30),
        symbolDeltaMin(31)
    }

CfprEtherNiErrStatsThresholded ::= TEXTUAL-CONVENTION
    STATUS        current
    DESCRIPTION
        ""
    SYNTAX        BITS
    {
        crcDelta(0),
        crcDeltaAvg(1),
        crcDeltaMax(2),
        crcDeltaMin(3),
        frameTxDelta(4),
        frameTxDeltaAvg(5),
        frameTxDeltaMax(6),
        frameTxDeltaMin(7),
        inRangeDelta(8),
        inRangeDeltaAvg(9),
        inRangeDeltaMax(10),
        inRangeDeltaMin(11),
        tooLongDelta(12),
        tooLongDeltaAvg(13),
        tooLongDeltaMax(14),
        tooLongDeltaMin(15),
        tooShortDelta(16),
        tooShortDeltaAvg(17),
        tooShortDeltaMax(18),
        tooShortDeltaMin(19)
    }

CfprEtherNiErrStatsHistThresholded ::= TEXTUAL-CONVENTION
    STATUS        current
    DESCRIPTION
        ""
    SYNTAX        BITS
    {
        crcDelta(0),
        crcDeltaAvg(1),
        crcDeltaMax(2),
        crcDeltaMin(3),
        frameTxDelta(4),
        frameTxDeltaAvg(5),
        frameTxDeltaMax(6),
        frameTxDeltaMin(7),
        inRangeDelta(8),
        inRangeDeltaAvg(9),
        inRangeDeltaMax(10),
        inRangeDeltaMin(11),
        tooLongDelta(12),
        tooLongDeltaAvg(13),
        tooLongDeltaMax(14),
        tooLongDeltaMin(15),
        tooShortDelta(16),
        tooShortDeltaAvg(17),
        tooShortDeltaMax(18),
        tooShortDeltaMin(19)
    }

CfprEtherPIoEpIfType ::= TEXTUAL-CONVENTION
    STATUS        current
    DESCRIPTION
        ""
    SYNTAX        INTEGER
    {
        unknown(0),
        physical(1),
        aggregation(2),
        virtual(3)
    }

CfprEtherPIoFsmCurrentFsm ::= TEXTUAL-CONVENTION
    STATUS        current
    DESCRIPTION
        ""
    SYNTAX        INTEGER
    {
        nop(0),
        inCompatSfpPresence(1014),
        inCompatSfpReplaced(1268)
    }

CfprEtherPIoFsmStageName ::= TEXTUAL-CONVENTION
    STATUS        current
    DESCRIPTION
        ""
    SYNTAX        INTEGER
    {
        nop(0),
        inCompatSfpPresenceBegin(1014),
        inCompatSfpPresenceShutdown(1015),
        inCompatSfpPresenceFail(1034),
        inCompatSfpPresenceSuccess(1035),
        inCompatSfpReplacedBegin(1268),
        inCompatSfpReplacedEnablePort(1269),
        inCompatSfpReplacedFail(1462),
        inCompatSfpReplacedSuccess(1463)
    }

CfprEtherPauseStatsThresholded ::= TEXTUAL-CONVENTION
    STATUS        current
    DESCRIPTION
        ""
    SYNTAX        BITS
    {
        recvPauseDelta(0),
        recvPauseDeltaAvg(1),
        recvPauseDeltaMax(2),
        recvPauseDeltaMin(3),
        resetsDelta(4),
        resetsDeltaAvg(5),
        resetsDeltaMax(6),
        resetsDeltaMin(7),
        xmitPauseDelta(8),
        xmitPauseDeltaAvg(9),
        xmitPauseDeltaMax(10),
        xmitPauseDeltaMin(11)
    }

CfprEtherPauseStatsHistThresholded ::= TEXTUAL-CONVENTION
    STATUS        current
    DESCRIPTION
        ""
    SYNTAX        BITS
    {
        recvPauseDelta(0),
        recvPauseDeltaAvg(1),
        recvPauseDeltaMax(2),
        recvPauseDeltaMin(3),
        resetsDelta(4),
        resetsDeltaAvg(5),
        resetsDeltaMax(6),
        resetsDeltaMin(7),
        xmitPauseDelta(8),
        xmitPauseDeltaAvg(9),
        xmitPauseDeltaMax(10),
        xmitPauseDeltaMin(11)
    }

CfprEtherRxStatsThresholded ::= TEXTUAL-CONVENTION
    STATUS        current
    DESCRIPTION
        ""
    SYNTAX        BITS
    {
        broadcastPacketsDelta(0),
        broadcastPacketsDeltaAvg(1),
        broadcastPacketsDeltaMax(2),
        broadcastPacketsDeltaMin(3),
        jumboPacketsDelta(4),
        jumboPacketsDeltaAvg(5),
        jumboPacketsDeltaMax(6),
        jumboPacketsDeltaMin(7),
        multicastPacketsDelta(8),
        multicastPacketsDeltaAvg(9),
        multicastPacketsDeltaMax(10),
        multicastPacketsDeltaMin(11),
        totalBytesDelta(12),
        totalBytesDeltaAvg(13),
        totalBytesDeltaMax(14),
        totalBytesDeltaMin(15),
        totalPacketsDelta(16),
        totalPacketsDeltaAvg(17),
        totalPacketsDeltaMax(18),
        totalPacketsDeltaMin(19),
        unicastPacketsDelta(20),
        unicastPacketsDeltaAvg(21),
        unicastPacketsDeltaMax(22),
        unicastPacketsDeltaMin(23)
    }

CfprEtherRxStatsHistThresholded ::= TEXTUAL-CONVENTION
    STATUS        current
    DESCRIPTION
        ""
    SYNTAX        BITS
    {
        broadcastPacketsDelta(0),
        broadcastPacketsDeltaAvg(1),
        broadcastPacketsDeltaMax(2),
        broadcastPacketsDeltaMin(3),
        jumboPacketsDelta(4),
        jumboPacketsDeltaAvg(5),
        jumboPacketsDeltaMax(6),
        jumboPacketsDeltaMin(7),
        multicastPacketsDelta(8),
        multicastPacketsDeltaAvg(9),
        multicastPacketsDeltaMax(10),
        multicastPacketsDeltaMin(11),
        totalBytesDelta(12),
        totalBytesDeltaAvg(13),
        totalBytesDeltaMax(14),
        totalBytesDeltaMin(15),
        totalPacketsDelta(16),
        totalPacketsDeltaAvg(17),
        totalPacketsDeltaMax(18),
        totalPacketsDeltaMin(19),
        unicastPacketsDelta(20),
        unicastPacketsDeltaAvg(21),
        unicastPacketsDeltaMax(22),
        unicastPacketsDeltaMin(23)
    }

CfprEtherSatelliteConnectionDisc ::= TEXTUAL-CONVENTION
    STATUS        current
    DESCRIPTION
        ""
    SYNTAX        INTEGER
    {
        absent(0),
        present(1),
        misConnect(2),
        missing(3),
        new(4)
    }

CfprEtherServerIntFIoAdminState ::= TEXTUAL-CONVENTION
    STATUS        current
    DESCRIPTION
        ""
    SYNTAX        INTEGER
    {
        enabled(1),
        disabled(2)
    }

CfprEtherServerIntFIoIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprEtherServerIntFIoLocale ::= TEXTUAL-CONVENTION
    STATUS        current
    DESCRIPTION
        ""
    SYNTAX        BITS
    {
        server(0),
        chassis(1),
        internal(2),
        external(3)
    }

CfprEtherServerIntFIoTransport ::= TEXTUAL-CONVENTION
    STATUS        current
    DESCRIPTION
        ""
    SYNTAX        BITS
    {
        ether(0),
        dce(1),
        fc(2)
    }

CfprEtherServerIntFIoType ::= TEXTUAL-CONVENTION
    STATUS        current
    DESCRIPTION
        ""
    SYNTAX        BITS
    {
        lan(0),
        san(1),
        ipc(2)
    }

CfprEtherServerIntFIoFsmCurrentFsm ::= TEXTUAL-CONVENTION
    STATUS        current
    DESCRIPTION
        ""
    SYNTAX        INTEGER
    {
        nop(0),
        configSpeed(1150)
    }

CfprEtherServerIntFIoFsmStageName ::= TEXTUAL-CONVENTION
    STATUS        current
    DESCRIPTION
        ""
    SYNTAX        INTEGER
    {
        nop(0),
        configSpeedBegin(1150),
        configSpeedConfigure(1151),
        configSpeedFail(1182),
        configSpeedSuccess(1183)
    }

CfprEtherServerIntFIoFsmTaskItem ::= TEXTUAL-CONVENTION
    STATUS        current
    DESCRIPTION
        ""
    SYNTAX        INTEGER
    {
        nop(0),
        configSpeed(1150)
    }

CfprEtherServerIntFIoPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprEtherServerIntFIoPcPortId ::= TEXTUAL-CONVENTION
    STATUS        current
    DESCRIPTION
        ""
    SYNTAX        Gauge32 (1024..4096)

CfprEtherServerIntFIoPcTransport ::= TEXTUAL-CONVENTION
    STATUS        current
    DESCRIPTION
        ""
    SYNTAX        BITS
    {
        ether(0),
        dce(1),
        fc(2)
    }

CfprEtherServerIntFIoPcType ::= TEXTUAL-CONVENTION
    STATUS        current
    DESCRIPTION
        ""
    SYNTAX        BITS
    {
        lan(0),
        san(1),
        ipc(2)
    }

CfprEtherServerIntFIoPcEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprEtherServerIntFIoPcEpPortId ::= TEXTUAL-CONVENTION
    STATUS        current
    DESCRIPTION
        ""
    SYNTAX        Gauge32 (1..33)

CfprEtherSwitchIntFIoAck ::= TEXTUAL-CONVENTION
    STATUS        current
    DESCRIPTION
        ""
    SYNTAX        INTEGER
    {
        unInitialized(0),
        unAcknowledged(1),
        unsupportedConnectivity(2),
        ok(3),
        removing(4),
        ackInProgress(6),
        evaluation(7),
        acknowledged(8),
        autoAck(9)
    }

CfprEtherSwitchIntFIoIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprEtherSwitchIntFIoLocale ::= TEXTUAL-CONVENTION
    STATUS        current
    DESCRIPTION
        ""
    SYNTAX        BITS
    {
        server(0),
        chassis(1),
        internal(2),
        external(3)
    }

CfprEtherSwitchIntFIoTransport ::= TEXTUAL-CONVENTION
    STATUS        current
    DESCRIPTION
        ""
    SYNTAX        BITS
    {
        ether(0),
        dce(1),
        fc(2)
    }

CfprEtherSwitchIntFIoType ::= TEXTUAL-CONVENTION
    STATUS        current
    DESCRIPTION
        ""
    SYNTAX        BITS
    {
        lan(0),
        san(1),
        ipc(2)
    }

CfprEtherSwitchIntFIoPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprEtherSwitchIntFIoPcPortId ::= TEXTUAL-CONVENTION
    STATUS        current
    DESCRIPTION
        ""
    SYNTAX        Gauge32 (1024..4096)

CfprEtherSwitchIntFIoPcTransport ::= TEXTUAL-CONVENTION
    STATUS        current
    DESCRIPTION
        ""
    SYNTAX        BITS
    {
        ether(0),
        dce(1),
        fc(2)
    }

CfprEtherSwitchIntFIoPcType ::= TEXTUAL-CONVENTION
    STATUS        current
    DESCRIPTION
        ""
    SYNTAX        BITS
    {
        lan(0),
        san(1),
        ipc(2)
    }

CfprEtherSwitchIntFIoPcEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprEtherSwitchIntFIoPcEpPortId ::= TEXTUAL-CONVENTION
    STATUS        current
    DESCRIPTION
        ""
    SYNTAX        Gauge32 (1..8)

CfprEtherTxStatsThresholded ::= TEXTUAL-CONVENTION
    STATUS        current
    DESCRIPTION
        ""
    SYNTAX        BITS
    {
        broadcastPacketsDelta(0),
        broadcastPacketsDeltaAvg(1),
        broadcastPacketsDeltaMax(2),
        broadcastPacketsDeltaMin(3),
        jumboPacketsDelta(4),
        jumboPacketsDeltaAvg(5),
        jumboPacketsDeltaMax(6),
        jumboPacketsDeltaMin(7),
        multicastPacketsDelta(8),
        multicastPacketsDeltaAvg(9),
        multicastPacketsDeltaMax(10),
        multicastPacketsDeltaMin(11),
        totalBytesDelta(12),
        totalBytesDeltaAvg(13),
        totalBytesDeltaMax(14),
        totalBytesDeltaMin(15),
        totalPacketsDelta(16),
        totalPacketsDeltaAvg(17),
        totalPacketsDeltaMax(18),
        totalPacketsDeltaMin(19),
        unicastPacketsDelta(20),
        unicastPacketsDeltaAvg(21),
        unicastPacketsDeltaMax(22),
        unicastPacketsDeltaMin(23)
    }

CfprEtherTxStatsHistThresholded ::= TEXTUAL-CONVENTION
    STATUS        current
    DESCRIPTION
        ""
    SYNTAX        BITS
    {
        broadcastPacketsDelta(0),
        broadcastPacketsDeltaAvg(1),
        broadcastPacketsDeltaMax(2),
        broadcastPacketsDeltaMin(3),
        jumboPacketsDelta(4),
        jumboPacketsDeltaAvg(5),
        jumboPacketsDeltaMax(6),
        jumboPacketsDeltaMin(7),
        multicastPacketsDelta(8),
        multicastPacketsDeltaAvg(9),
        multicastPacketsDeltaMax(10),
        multicastPacketsDeltaMin(11),
        totalBytesDelta(12),
        totalBytesDeltaAvg(13),
        totalBytesDeltaMax(14),
        totalBytesDeltaMin(15),
        totalPacketsDelta(16),
        totalPacketsDeltaAvg(17),
        totalPacketsDeltaMax(18),
        totalPacketsDeltaMin(19),
        unicastPacketsDelta(20),
        unicastPacketsDeltaAvg(21),
        unicastPacketsDeltaMax(22),
        unicastPacketsDeltaMin(23)
    }

CfprEventEpCtrlLevel ::= TEXTUAL-CONVENTION
    STATUS        current
    DESCRIPTION
        ""
    SYNTAX        INTEGER
    {
        cleared(0),
        info(1),
        condition(2),
        warning(3),
        minor(4),
        major(5),
        critical(6)
    }

CfprExtmgmtArpTargetsMaxDeadlineTimeout ::= TEXTUAL-CONVENTION
    STATUS        current
    DESCRIPTION
        ""
    SYNTAX        Gauge32 (5..15)

CfprExtmgmtArpTargetsNumberOfArpRequests ::= TEXTUAL-CONVENTION
    STATUS        current
    DESCRIPTION
        ""
    SYNTAX        Gauge32 (1..5)

CfprExtmgmtGatewayPingMaxDeadlineTimeout ::= TEXTUAL-CONVENTION
    STATUS        current
    DESCRIPTION
        ""
    SYNTAX        Gauge32 (5..15)

CfprExtmgmtGatewayPingNumberOfPingRequests ::= TEXTUAL-CONVENTION
    STATUS        current
    DESCRIPTION
        ""
    SYNTAX        Gauge32 (1..5)

CfprExtmgmtIfType ::= TEXTUAL-CONVENTION
    STATUS        current
    DESCRIPTION
        ""
    SYNTAX        BITS
    {
        lan(0),
        san(1),
        ipc(2)
    }

CfprExtmgmtIfMonPolicyAdminState ::= TEXTUAL-CONVENTION
    STATUS        current
    DESCRIPTION
        ""
    SYNTAX        INTEGER
    {
        enabled(1),
        disabled(2)
    }

CfprExtmgmtIfMonPolicyMonitorMechanism ::= TEXTUAL-CONVENTION
    STATUS        current
    DESCRIPTION
        ""
    SYNTAX        INTEGER
    {
        miiStatus(0),
        arpTargetPing(1),
        gatewayPing(2)
    }

CfprExtmgmtMiiStatusMaxRetryCount ::= TEXTUAL-CONVENTION
    STATUS        current
    DESCRIPTION
        ""
    SYNTAX        Gauge32 (1..3)

CfprExtmgmtMiiStatusRetryInterval ::= TEXTUAL-CONVENTION
    STATUS        current
    DESCRIPTION
        ""
    SYNTAX        Gauge32 (3..10)

CfprExtmgmtNdiscTargetsMaxDeadlineTimeout ::= TEXTUAL-CONVENTION
    STATUS        current
    DESCRIPTION
        ""
    SYNTAX        Gauge32 (5..15)

CfprExtmgmtNdiscTargetsNumberOfNdiscRequests ::= TEXTUAL-CONVENTION
    STATUS        current
    DESCRIPTION
        ""
    SYNTAX        Gauge32 (1..5)

CfprExtpolAppCapability ::= TEXTUAL-CONVENTION
    STATUS        current
    DESCRIPTION
        ""
    SYNTAX        BITS
    {
        serviceReg(0),
        identifierMgr(1),
        operationMgr(2),
        resourceMgr(3),
        virtualSwitchingMgr(4),
        policyMgr(5),
        bootMgr(6),
        vmMgr(7),
        vmAdmin(8),
        infraCryptoOffloa(9),
        vmm(10),
        vmVasw(11),
        vmFw(12),
        vmSlb(13),
        infraFw(14),
        infraSlb(15),
        ipam(16),
        pcm(17),
        infraAggr(18),
        infraWas(19),
        infraWaf(20),
        infraPasw(21),
        infraPdsw(22),
        storageBroker(23),
        orgMgr(24),
        statsMgr(25),
        centralMgr(26)
    }

CfprExtpolConnProtocol ::= TEXTUAL-CONVENTION
    STATUS        current
    DESCRIPTION
        ""
    SYNTAX        INTEGER
    {
        ipv4(0),
        ipv6(1),
        unknown(2)
    }

CfprExtpolConnType ::= TEXTUAL-CONVENTION
    STATUS        current
    DESCRIPTION
        ""
    SYNTAX        INTEGER
    {
        ape(5),
        serviceReg(27),
        identifierMgr(28),
        operationMgr(29),
        resourceMgr(30),
        virtualSwitchingMgr(31),
        policyMgr(32),
        bootMgr(33),
        vmMgr(34),
        managedEndpoint(35),
        mgmtController(36),
        storageBroker(37),
        resourceAggr(38),
        statsMgr(39),
        centralMgr(40)
    }

CfprExtpolConnectorOperState ::= TEXTUAL-CONVENTION
    STATUS        current
    DESCRIPTION
        ""
    SYNTAX        INTEGER
    {
        unregistered(0),
        lostVisibility(1),
        registering(2),
        synchronizing(3),
        registered(4),
        versionMismatch(5),
        registryNotReachable(6)
    }

CfprExtpolEpFsmCurrentFsm ::= TEXTUAL-CONVENTION
    STATUS        current
    DESCRIPTION
        ""
    SYNTAX        INTEGER
    {
        nop(0),
        registerFsm(1283),
        repairCert(1334)
    }

CfprExtpolEpFsmStageName ::= TEXTUAL-CONVENTION
    STATUS        current
    DESCRIPTION
        ""
    SYNTAX        INTEGER
    {
        nop(0),
        registerFsmBegin(1283),
        registerFsmExecute(1284),
        repairCertBegin(1334),
        repairCertVerifyGuid(1335),
        repairCertUnregister(1336),
        repairCertCleanOldData(1337),
        repairCertRequest(1338),
        repairCertVerify(1339),
        registerFsmFail(1394),
        registerFsmSuccess(1395),
        repairCertFail(1396),
        repairCertSuccess(1397)
    }

CfprExtpolEpFsmTaskItem ::= TEXTUAL-CONVENTION
    STATUS        current
    DESCRIPTION
        ""
    SYNTAX        INTEGER
    {
        nop(0),
        registerFsm(1283),
        repairCert(1334)
    }

CfprExtpolProviderFsmCurrentFsm ::= TEXTUAL-CONVENTION
    STATUS        current
    DESCRIPTION
        ""
    SYNTAX        INTEGER
    {
        nop(0),
        reportConfigImport(1374)
    }

CfprExtpolProviderFsmStageName ::= TEXTUAL-CONVENTION
    STATUS        current
    DESCRIPTION
        ""
    SYNTAX        INTEGER
    {
        nop(0),
        reportConfigImportBegin(1374),
        reportConfigImportReport(1375),
        reportConfigImportFail(1398),
        reportConfigImportSuccess(1399)
    }

CfprExtpolProviderFsmTaskItem ::= TEXTUAL-CONVENTION
    STATUS        current
    DESCRIPTION
        ""
    SYNTAX        INTEGER
    {
        nop(0),
        reportConfigImport(1374)
    }

CfprExtpolRegistryFsmCurrentFsm ::= TEXTUAL-CONVENTION
    STATUS        current
    DESCRIPTION
        ""
    SYNTAX        INTEGER
    {
        nop(0),
        crossDomainConfig(1285),
        crossDomainDelete(1288)
    }

CfprExtpolRegistryFsmStageName ::= TEXTUAL-CONVENTION
    STATUS        current
    DESCRIPTION
        ""
    SYNTAX        INTEGER
    {
        nop(0),
        crossDomainConfigBegin(1285),
        crossDomainConfigSetLocal(1286),
        crossDomainConfigSetPeer(1287),
        crossDomainDeleteBegin(1288),
        crossDomainDeleteSetLocal(1289),
        crossDomainDeleteSetPeer(1290),
        crossDomainConfigFail(1400),
        crossDomainConfigSuccess(1401),
        crossDomainDeleteFail(1402),
        crossDomainDeleteSuccess(1403)
    }

CfprExtpolRegistryFsmTaskItem ::= TEXTUAL-CONVENTION
    STATUS        current
    DESCRIPTION
        ""
    SYNTAX        INTEGER
    {
        nop(0),
        crossDomainConfig(1285),
        crossDomainDelete(1288)
    }

CfprExtpolState ::= TEXTUAL-CONVENTION
    STATUS        current
    DESCRIPTION
        ""
    SYNTAX        INTEGER
    {
        unknown(0),
        licenseOk(1),
        licenseInsufficient(2),
        licenseGraceperiod(3),
        licenseExpired(4),
        notApplicable(5)
    }

CfprExtpolSuspendState ::= TEXTUAL-CONVENTION
    STATUS        current
    DESCRIPTION
        ""
    SYNTAX        INTEGER
    {
        off(0),
        on(1)
    }

CfprExtvmmEpFsmCurrentFsm ::= TEXTUAL-CONVENTION
    STATUS        current
    DESCRIPTION
        ""
    SYNTAX        INTEGER
    {
        nop(0),
        clusterRole(1129)
    }

CfprExtvmmEpFsmStageName ::= TEXTUAL-CONVENTION
    STATUS        current
    DESCRIPTION
        ""
    SYNTAX        INTEGER
    {
        nop(0),
        clusterRoleBegin(1129),
        clusterRoleSetPeer(1130),
        clusterRoleSetLocal(1131),
        clusterRoleFail(1142),
        clusterRoleSuccess(1143)
    }

CfprExtvmmEpFsmTaskItem ::= TEXTUAL-CONVENTION
    STATUS        current
    DESCRIPTION
        ""
    SYNTAX        INTEGER
    {
        nop(0),
        clusterRole(1129)
    }

CfprExtvmmFabricNetworkType ::= TEXTUAL-CONVENTION
    STATUS        current
    DESCRIPTION
        ""
    SYNTAX        INTEGER
    {
        notConnected(0),
        notConnectedPvlans(1),
        connected(2)
    }

CfprExtvmmKeyStoreFsmCurrentFsm ::= TEXTUAL-CONVENTION
    STATUS        current
    DESCRIPTION
        ""
    SYNTAX        INTEGER
    {
        nop(0),
        certInstall(539)
    }

CfprExtvmmKeyStoreFsmStageName ::= TEXTUAL-CONVENTION
    STATUS        current
    DESCRIPTION
        ""
    SYNTAX        INTEGER
    {
        nop(0),
        certInstallBegin(539),
        certInstallSetLocal(540),
        certInstallSetPeer(541),
        certInstallFail(561),
        certInstallSuccess(562)
    }

CfprExtvmmKeyStoreFsmTaskItem ::= TEXTUAL-CONVENTION
    STATUS        current
    DESCRIPTION
        ""
    SYNTAX        INTEGER
    {
        nop(0),
        certInstall(539)
    }

CfprExtvmmMasterExtKeyFsmCurrentFsm ::= TEXTUAL-CONVENTION
    STATUS        current
    DESCRIPTION
        ""
    SYNTAX        INTEGER
    {
        nop(0),
        config(575)
    }

CfprExtvmmMasterExtKeyFsmStageName ::= TEXTUAL-CONVENTION
    STATUS        current
    DESCRIPTION
        ""
    SYNTAX        INTEGER
    {
        nop(0),
        configBegin(575),
        configSetLocal(576),
        configSetPeer(577),
        configFail(578),
        configSuccess(579)
    }

CfprExtvmmMasterExtKeyFsmTaskItem ::= TEXTUAL-CONVENTION
    STATUS        current
    DESCRIPTION
        ""
    SYNTAX        INTEGER
    {
        nop(0),
        config(575)
    }

CfprExtvmmNetworkSetConfigQualifier ::= TEXTUAL-CONVENTION
    STATUS        current
    DESCRIPTION
        ""
    SYNTAX        INTEGER
    {
        normal(0),
        duplicateVmndReference(1)
    }

CfprExtvmmNetworkSetsFsmCurrentFsm ::= TEXTUAL-CONVENTION
    STATUS        current
    DESCRIPTION
        ""
    SYNTAX        INTEGER
    {
        nop(0),
        deploy(1503)
    }

CfprExtvmmNetworkSetsFsmStageName ::= TEXTUAL-CONVENTION
    STATUS        current
    DESCRIPTION
        ""
    SYNTAX        INTEGER
    {
        nop(0),
        deployBegin(1503),
        deployLocal(1504),
        deployPeer(1505),
        deployFail(1553),
        deploySuccess(1554)
    }

CfprExtvmmNetworkSetsFsmTaskItem ::= TEXTUAL-CONVENTION
    STATUS        current
    DESCRIPTION
        ""
    SYNTAX        INTEGER
    {
        nop(0),
        deploy(1503)
    }

CfprExtvmmOwnership ::= TEXTUAL-CONVENTION
    STATUS        current
    DESCRIPTION
        ""
    SYNTAX        INTEGER
    {
        discovered(1),
        managed(2)
    }

CfprExtvmmProviderFsmCurrentFsm ::= TEXTUAL-CONVENTION
    STATUS        current
    DESCRIPTION
        ""
    SYNTAX        INTEGER
    {
        nop(0),
        config(536)
    }

CfprExtvmmProviderFsmStageName ::= TEXTUAL-CONVENTION
    STATUS        current
    DESCRIPTION
        ""
    SYNTAX        INTEGER
    {
        nop(0),
        configBegin(536),
        configSetPeer(537),
        configSetLocal(538),
        configFail(563),
        configSuccess(564),
        configGetVersion(581)
    }

CfprExtvmmProviderFsmTaskItem ::= TEXTUAL-CONVENTION
    STATUS        current
    DESCRIPTION
        ""
    SYNTAX        INTEGER
    {
        nop(0),
        config(536)
    }

CfprExtvmmRefOperState ::= TEXTUAL-CONVENTION
    STATUS        current
    DESCRIPTION
        ""
    SYNTAX        INTEGER
    {
        up(0),
        invalidReference(1)
    }

CfprExtvmmSwitchDelTaskFsmCurrentFsm ::= TEXTUAL-CONVENTION
    STATUS        current
    DESCRIPTION
        ""
    SYNTAX        INTEGER
    {
        nop(0),
        removeProvider(542)
    }

CfprExtvmmSwitchDelTaskFsmStageName ::= TEXTUAL-CONVENTION
    STATUS        current
    DESCRIPTION
        ""
    SYNTAX        INTEGER
    {
        nop(0),
        removeProviderBegin(542),
        removeProviderRemoveLocal(543),
        removeProviderFail(565),
        removeProviderSuccess(566)
    }

CfprExtvmmSwitchDelTaskFsmTaskItem ::= TEXTUAL-CONVENTION
    STATUS        current
    DESCRIPTION
        ""
    SYNTAX        INTEGER
    {
        nop(0),
        removeProvider(542)
    }

CfprExtvmmVcVersion ::= TEXTUAL-CONVENTION
    STATUS        current
    DESCRIPTION
        ""
    SYNTAX        INTEGER
    {
        unknown(0),
        kl(1),
        klU1(2)
    }

CfprExtvmmVnicType ::= TEXTUAL-CONVENTION
    STATUS        current
    DESCRIPTION
        ""
    SYNTAX        INTEGER
    {
        unknown(0),
        ether(1),
        fc(4),
        scsi(8),
        ipc(16)
    }

CfprExtvmmProviderVendorType ::= TEXTUAL-CONVENTION
    STATUS        current
    DESCRIPTION
        ""
    SYNTAX        INTEGER
    {
        unknown(0),
        vmware(1),
        microsoft(2)
    }

CfprFabricADceSwSrvEpTransport ::= TEXTUAL-CONVENTION
    STATUS        current
    DESCRIPTION
        ""
    SYNTAX        BITS
    {
        ether(0),
        dce(1),
        fc(2)
    }

CfprFabricAEthEstcEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprFabricAEthEstcEpTransport ::= TEXTUAL-CONVENTION
    STATUS        current
    DESCRIPTION
        ""
    SYNTAX        BITS
    {
        ether(0),
        dce(1),
        fc(2)
    }

CfprFabricAEthEstcEpType ::= TEXTUAL-CONVENTION
    STATUS        current
    DESCRIPTION
        ""
    SYNTAX        BITS
    {
        lan(0),
        san(1),
        ipc(2)
    }

CfprFabricAEthLanEpTransport ::= TEXTUAL-CONVENTION
    STATUS        current
    DESCRIPTION
        ""
    SYNTAX        BITS
    {
        ether(0),
        dce(1),
        fc(2)
    }

CfprFabricAFcEstcEpTransport ::= TEXTUAL-CONVENTION
    STATUS        current
    DESCRIPTION
        ""
    SYNTAX        BITS
    {
        ether(0),
        dce(1),
        fc(2)
    }

CfprFabricAFcEstcEpType ::= TEXTUAL-CONVENTION
    STATUS        current
    DESCRIPTION
        ""
    SYNTAX        BITS
    {
        lan(0),
        san(1),
        ipc(2)
    }

CfprFabricAFcSanEpTransport ::= TEXTUAL-CONVENTION
    STATUS        current
    DESCRIPTION
        ""
    SYNTAX        BITS
    {
        ether(0),
        dce(1),
        fc(2)
    }

CfprFabricAFcoeEstcEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprFabricAFcoeEstcEpTransport ::= TEXTUAL-CONVENTION
    STATUS        current
    DESCRIPTION
        ""
    SYNTAX        BITS
    {
        ether(0),
        dce(1),
        fc(2)
    }

CfprFabricAFcoeEstcEpType ::= TEXTUAL-CONVENTION
    STATUS        current
    DESCRIPTION
        ""
    SYNTAX        BITS
    {
        lan(0),
        san(1),
        ipc(2)
    }

CfprFabricAFcoeSanEpTransport ::= TEXTUAL-CONVENTION
    STATUS        current
    DESCRIPTION
        ""
    SYNTAX        BITS
    {
        ether(0),
        dce(1),
        fc(2)
    }

CfprFabricAVlanAssocPrimaryVlanSwitchId ::= TEXTUAL-CONVENTION
    STATUS        current
    DESCRIPTION
        ""
    SYNTAX        INTEGER
    {
        none(0),
        a(1),
        b(2)
    }

CfprFabricAVlanSharing ::= TEXTUAL-CONVENTION
    STATUS        current
    DESCRIPTION
        ""
    SYNTAX        INTEGER
    {
        none(0),
        primary(1),
        isolated(2),
        community(3)
    }

CfprFabricAVlanTransport ::= TEXTUAL-CONVENTION
    STATUS        current
    DESCRIPTION
        ""
    SYNTAX        BITS
    {
        ether(0),
        dce(1),
        fc(2)
    }

CfprFabricAVlanType ::= TEXTUAL-CONVENTION
    STATUS        current
    DESCRIPTION
        ""
    SYNTAX        BITS
    {
        lan(0),
        san(1),
        ipc(2)
    }

CfprFabricAVsanTransport ::= TEXTUAL-CONVENTION
    STATUS        current
    DESCRIPTION
        ""
    SYNTAX        BITS
    {
        ether(0),
        dce(1),
        fc(2)
    }

CfprFabricAVsanType ::= TEXTUAL-CONVENTION
    STATUS        current
    DESCRIPTION
        ""
    SYNTAX        BITS
    {
        lan(0),
        san(1),
        ipc(2)
    }

CfprFabricAccessType ::= TEXTUAL-CONVENTION
    STATUS        current
    DESCRIPTION
        ""
    SYNTAX        INTEGER
    {
        lan(0),
        san(1)
    }

CfprFabricAdminState ::= TEXTUAL-CONVENTION
    STATUS        current
    DESCRIPTION
        ""
    SYNTAX        INTEGER
    {
        enabled(1),
        disabled(2)
    }

CfprFabricAllowedVlanType ::= TEXTUAL-CONVENTION
    STATUS        current
    DESCRIPTION
        ""
    SYNTAX        INTEGER
    {
        all(0),
        untagged(1)
    }

CfprFabricBHVlanSwitchId ::= TEXTUAL-CONVENTION
    STATUS        current
    DESCRIPTION
        ""
    SYNTAX        INTEGER
    {
        none(0),
        a(1),
        b(2),
        dual(3)
    }

CfprFabricBladeLifeCycle ::= TEXTUAL-CONVENTION
    STATUS        current
    DESCRIPTION
        ""
    SYNTAX        INTEGER
    {
        inService(1),
        outOfService(2),
        outOfServiceSlave(3)
    }

CfprFabricBreakoutPortId ::= TEXTUAL-CONVENTION
    STATUS        current
    DESCRIPTION
        ""
    SYNTAX        Gauge32 (1..4)

CfprFabricBreakoutSlotId ::= TEXTUAL-CONVENTION
    STATUS        current
    DESCRIPTION
        ""
    SYNTAX        Gauge32 (2..3)

CfprFabricBreakoutType ::= TEXTUAL-CONVENTION
    STATUS        current
    DESCRIPTION
        ""
    SYNTAX        INTEGER
    {
        unknown(0),
        n10g4x(1)
    }

CfprFabricCIoEpAdminState ::= TEXTUAL-CONVENTION
    STATUS        current
    DESCRIPTION
        ""
    SYNTAX        INTEGER
    {
        enabled(1),
        disabled(2)
    }

CfprFabricCIoEpIfType ::= TEXTUAL-CONVENTION
    STATUS        current
    DESCRIPTION
        ""
    SYNTAX        INTEGER
    {
        unknown(0),
        physical(1),
        aggregation(2),
        virtual(3)
    }

CfprFabricCdpLinkPolicyAdminState ::= TEXTUAL-CONVENTION
    STATUS        current
    DESCRIPTION
        ""
    SYNTAX        INTEGER
    {
        enabled(1),
        disabled(2)
    }

CfprFabricCloudType ::= TEXTUAL-CONVENTION
    STATUS        current
    DESCRIPTION
        ""
    SYNTAX        BITS
    {
        ethlan(0),
        ethestclan(1),
        ethlanmon(2),
        fcsan(3),
        fcsanmon(4),
        fcestc(5)
    }

CfprFabricComputeEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprFabricComputeEpType ::= TEXTUAL-CONVENTION
    STATUS        current
    DESCRIPTION
        ""
    SYNTAX        BITS
    {
        lan(0),
        san(1),
        ipc(2)
    }

CfprFabricComputePhEpAdminState ::= TEXTUAL-CONVENTION
    STATUS        current
    DESCRIPTION
        ""
    SYNTAX        INTEGER
    {
        enabled(1),
        disabled(2),
        remove(3)
    }

CfprFabricComputeSlotEpSlotId ::= TEXTUAL-CONVENTION
    STATUS        current
    DESCRIPTION
        ""
    SYNTAX        Gauge32 (1..8)

CfprFabricComputeSlotEpFsmCurrentFsm ::= TEXTUAL-CONVENTION
    STATUS        current
    DESCRIPTION
        ""
    SYNTAX        INTEGER
    {
        nop(0),
        identify(20)
    }

CfprFabricComputeSlotEpFsmStageName ::= TEXTUAL-CONVENTION
    STATUS        current
    DESCRIPTION
        ""
    SYNTAX        INTEGER
    {
        nop(0),
        identifyBegin(20),
        identifyExecuteLocal(21),
        identifyExecutePeer(22),
        identifyFail(390),
        identifySuccess(391)
    }

CfprFabricComputeSlotEpFsmTaskItem ::= TEXTUAL-CONVENTION
    STATUS        current
    DESCRIPTION
        ""
    SYNTAX        INTEGER
    {
        nop(0),
        identify(20)
    }

CfprFabricConfMode ::= TEXTUAL-CONVENTION
    STATUS        current
    DESCRIPTION
        ""
    SYNTAX        INTEGER
    {
        none(0),
        logicalConfigInvalid(1),
        validatingConf(2),
        applyPhysTrans(3),
        confSwitch(4)
    }

CfprFabricConfState ::= TEXTUAL-CONVENTION
    STATUS        current
    DESCRIPTION
        ""
    SYNTAX        INTEGER
    {
        ok(0),
        logicalConfigInvalid(1)
    }

CfprFabricConfigState ::= TEXTUAL-CONVENTION
    STATUS        current
    DESCRIPTION
        ""
    SYNTAX        INTEGER
    {
        applied(1),
        inconsistent(2)
    }

CfprFabricDceSwSrvEpPortId ::= TEXTUAL-CONVENTION
    STATUS        current
    DESCRIPTION
        ""
    SYNTAX        Gauge32 (1..48)

CfprFabricDceSwSrvEpSlotId ::= TEXTUAL-CONVENTION
    STATUS        current
    DESCRIPTION
        ""
    SYNTAX        Gauge32 (1..4)

CfprFabricDceSwSrvPcAdminState ::= TEXTUAL-CONVENTION
    STATUS        current
    DESCRIPTION
        ""
    SYNTAX        INTEGER
    {
        enabled(1),
        disabled(2)
    }

CfprFabricDceSwSrvPcPortId ::= TEXTUAL-CONVENTION
    STATUS        current
    DESCRIPTION
        ""
    SYNTAX        Gauge32 (1024..4096)

CfprFabricDceSwSrvPcTransport ::= TEXTUAL-CONVENTION
    STATUS        current
    DESCRIPTION
        ""
    SYNTAX        BITS
    {
        ether(0),
        dce(1),
        fc(2)
    }

CfprFabricDceSwSrvPcEpPortId ::= TEXTUAL-CONVENTION
    STATUS        current
    DESCRIPTION
        ""
    SYNTAX        Gauge32 (1..48)

CfprFabricDceSwSrvPcEpSlotId ::= TEXTUAL-CONVENTION
    STATUS        current
    DESCRIPTION
        ""
    SYNTAX        Gauge32 (1..4)

CfprFabricDefaultZoningState ::= TEXTUAL-CONVENTION
    STATUS        current
    DESCRIPTION
        ""
    SYNTAX        INTEGER
    {
        disabled(0),
        enabled(1)
    }

CfprFabricDirection ::= TEXTUAL-CONVENTION
    STATUS        current
    DESCRIPTION
        ""
    SYNTAX        INTEGER
    {
        receive(1),
        transmit(2)
    }

CfprFabricEpMgrFsmCurrentFsm ::= TEXTUAL-CONVENTION
    STATUS        current
    DESCRIPTION
        ""
    SYNTAX        INTEGER
    {
        nop(0),
        configure(1113)
    }

CfprFabricEpMgrFsmStageName ::= TEXTUAL-CONVENTION
    STATUS        current
    DESCRIPTION
        ""
    SYNTAX        INTEGER
    {
        nop(0),
        configureBegin(1113),
        configureValidateConfiguration(1114),
        configureApplyPhysical(1115),
        configureWaitOnPhys(1116),
        configureApplyConfig(1117),
        configureFail(1144),
        configureSuccess(1145)
    }

CfprFabricEpMgrFsmTaskFlags ::= TEXTUAL-CONVENTION
    STATUS        current
    DESCRIPTION
        ""
    SYNTAX        BITS
    {
        samDmeFabricEpMgrConfigurePhysChange(51),
        samDmeFabricEpMgrConfigureModification(52),
        samDmeFabricEpMgrConfigureEthServerConfig(53),
        samDmeFabricEpMgrConfigureEthUplinkConfig(54),
        samDmeFabricEpMgrConfigureFcUplinkConfig(55),
        samDmeFabricEpMgrConfigureEthStorageConfig(56),
        samDmeFabricEpMgrConfigureFcStorageConfig(57)
    }

CfprFabricEpMgrFsmTaskItem ::= TEXTUAL-CONVENTION
    STATUS        current
    DESCRIPTION
        ""
    SYNTAX        INTEGER
    {
        nop(0),
        configure(1113)
    }

CfprFabricEpVlanVlanType ::= TEXTUAL-CONVENTION
    STATUS        current
    DESCRIPTION
        ""
    SYNTAX        INTEGER
    {
        regular(0),
        default(1),
        native(2),
        fcoeuplinknative(3)
    }

CfprFabricEstcEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprFabricEstcPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprFabricEstcPcType ::= TEXTUAL-CONVENTION
    STATUS        current
    DESCRIPTION
        ""
    SYNTAX        BITS
    {
        lan(0),
        san(1),
        ipc(2)
    }

CfprFabricEthCdpPolicyProtocol ::= TEXTUAL-CONVENTION
    STATUS        current
    DESCRIPTION
        ""
    SYNTAX        INTEGER
    {
        unknown(0),
        udld(1),
        cdp(2)
    }

CfprFabricEthEstcTransport ::= TEXTUAL-CONVENTION
    STATUS        current
    DESCRIPTION
        ""
    SYNTAX        BITS
    {
        ether(0),
        dce(1),
        fc(2)
    }

CfprFabricEthEstcType ::= TEXTUAL-CONVENTION
    STATUS        current
    DESCRIPTION
        ""
    SYNTAX        BITS
    {
        lan(0),
        san(1),
        ipc(2)
    }

CfprFabricEthEstcEpPortId ::= TEXTUAL-CONVENTION
    STATUS        current
    DESCRIPTION
        ""
    SYNTAX        Gauge32 (1..48)

CfprFabricEthEstcEpPrio ::= TEXTUAL-CONVENTION
    STATUS        current
    DESCRIPTION
        ""
    SYNTAX        INTEGER
    {
        fc(1),
        platinum(2),
        gold(3),
        silver(4),
        bronze(5),
        bestEffort(6)
    }

CfprFabricEthEstcEpSlotId ::= TEXTUAL-CONVENTION
    STATUS        current
    DESCRIPTION
        ""
    SYNTAX        Gauge32 (1..4)

CfprFabricEthEstcEpTransport ::= TEXTUAL-CONVENTION
    STATUS        current
    DESCRIPTION
        ""
    SYNTAX        BITS
    {
        ether(0),
        dce(1),
        fc(2)
    }

CfprFabricEthEstcEpType ::= TEXTUAL-CONVENTION
    STATUS        current
    DESCRIPTION
        ""
    SYNTAX        BITS
    {
        lan(0),
        san(1),
        ipc(2)
    }

CfprFabricEthEstcOperPortMode ::= TEXTUAL-CONVENTION
    STATUS        current
    DESCRIPTION
        ""
    SYNTAX        INTEGER
    {
        regularTrunk(1),
        regularAccess(2),
        promiscuousTrunk(3),
        promiscuousAccess(4)
    }

CfprFabricEthEstcPcTransport ::= TEXTUAL-CONVENTION
    STATUS        current
    DESCRIPTION
        ""
    SYNTAX        BITS
    {
        ether(0),
        dce(1),
        fc(2)
    }

CfprFabricEthEstcPcEpPortId ::= TEXTUAL-CONVENTION
    STATUS        current
    DESCRIPTION
        ""
    SYNTAX        Gauge32 (1..48)

CfprFabricEthEstcPcEpSlotId ::= TEXTUAL-CONVENTION
    STATUS        current
    DESCRIPTION
        ""
    SYNTAX        Gauge32 (1..4)

CfprFabricEthEstcPortMode ::= TEXTUAL-CONVENTION
    STATUS        current
    DESCRIPTION
        ""
    SYNTAX        INTEGER
    {
        trunk(1),
        access(2)
    }

CfprFabricEthFlowMonLanTransport ::= TEXTUAL-CONVENTION
    STATUS        current
    DESCRIPTION
        ""
    SYNTAX        BITS
    {
        ether(0),
        dce(1),
        fc(2)
    }

CfprFabricEthFlowMonLanType ::= TEXTUAL-CONVENTION
    STATUS        current
    DESCRIPTION
        ""
    SYNTAX        BITS
    {
        lan(0),
        san(1),
        ipc(2)
    }

CfprFabricEthFlowMonSourceType ::= TEXTUAL-CONVENTION
    STATUS        current
    DESCRIPTION
        ""
    SYNTAX        INTEGER
    {
        vnic(1),
        portProfile(2)
    }

CfprFabricEthFlowMonSrcRefType ::= TEXTUAL-CONVENTION
    STATUS        current
    DESCRIPTION
        ""
    SYNTAX        BITS
    {
        lan(0),
        san(1),
        ipc(2)
    }

CfprFabricEthLanTransport ::= TEXTUAL-CONVENTION
    STATUS        current
    DESCRIPTION
        ""
    SYNTAX        BITS
    {
        ether(0),
        dce(1),
        fc(2)
    }

CfprFabricEthLanEpAdminState ::= TEXTUAL-CONVENTION
    STATUS        current
    DESCRIPTION
        ""
    SYNTAX        INTEGER
    {
        enabled(1),
        disabled(2)
    }

CfprFabricEthLanEpInlineState ::= TEXTUAL-CONVENTION
    STATUS        current
    DESCRIPTION
        ""
    SYNTAX        INTEGER
    {
        enabled(1),
        disabled(2)
    }

CfprFabricEthLanEpVlanStatus ::= TEXTUAL-CONVENTION
    STATUS        current
    DESCRIPTION
        ""
    SYNTAX        INTEGER
    {
        ok(0),
        missingPrimary(1)
    }

CfprFabricEthLanFlowMonTransport ::= TEXTUAL-CONVENTION
    STATUS        current
    DESCRIPTION
        ""
    SYNTAX        BITS
    {
        ether(0),
        dce(1),
        fc(2)
    }

CfprFabricEthLanFlowMonCollectorTransport ::= TEXTUAL-CONVENTION
    STATUS        current
    DESCRIPTION
        ""
    SYNTAX        BITS
    {
        ether(0),
        dce(1),
        fc(2)
    }

CfprFabricEthLanFlowMonExporterTransport ::= TEXTUAL-CONVENTION
    STATUS        current
    DESCRIPTION
        ""
    SYNTAX        BITS
    {
        ether(0),
        dce(1),
        fc(2)
    }

CfprFabricEthLanFlowMonSrcEpTransport ::= TEXTUAL-CONVENTION
    STATUS        current
    DESCRIPTION
        ""
    SYNTAX        BITS
    {
        ether(0),
        dce(1),
        fc(2)
    }

CfprFabricEthLanFlowMonitorTransport ::= TEXTUAL-CONVENTION
    STATUS        current
    DESCRIPTION
        ""
    SYNTAX        BITS
    {
        ether(0),
        dce(1),
        fc(2)
    }

CfprFabricEthLanFlowMonitoringType ::= TEXTUAL-CONVENTION
    STATUS        current
    DESCRIPTION
        ""
    SYNTAX        INTEGER
    {
        unknown(0),
        ethFlowMonitoring(1),
        span(2)
    }

CfprFabricEthLanPcAdminState ::= TEXTUAL-CONVENTION
    STATUS        current
    DESCRIPTION
        ""
    SYNTAX        INTEGER
    {
        enabled(1),
        disabled(2)
    }

CfprFabricEthLanPcInlineState ::= TEXTUAL-CONVENTION
    STATUS        current
    DESCRIPTION
        ""
    SYNTAX        INTEGER
    {
        enabled(1),
        disabled(2)
    }

CfprFabricEthLanPcLacpDetach ::= TEXTUAL-CONVENTION
    STATUS        current
    DESCRIPTION
        ""
    SYNTAX        INTEGER
    {
        enabled(1),
        disabled(2)
    }

CfprFabricEthLanPcTransport ::= TEXTUAL-CONVENTION
    STATUS        current
    DESCRIPTION
        ""
    SYNTAX        BITS
    {
        ether(0),
        dce(1),
        fc(2)
    }

CfprFabricEthLanPcVlanStatus ::= TEXTUAL-CONVENTION
    STATUS        current
    DESCRIPTION
        ""
    SYNTAX        INTEGER
    {
        ok(0),
        missingPrimary(1)
    }

CfprFabricEthLinkPolicyType ::= TEXTUAL-CONVENTION
    STATUS        current
    DESCRIPTION
        ""
    SYNTAX        BITS
    {
        lan(0),
        san(1),
        ipc(2)
    }

CfprFabricEthMonTransport ::= TEXTUAL-CONVENTION
    STATUS        current
    DESCRIPTION
        ""
    SYNTAX        BITS
    {
        ether(0),
        dce(1),
        fc(2)
    }

CfprFabricEthMonType ::= TEXTUAL-CONVENTION
    STATUS        current
    DESCRIPTION
        ""
    SYNTAX        BITS
    {
        lan(0),
        san(1),
        ipc(2)
    }

CfprFabricEthMonDestEpAdminSpeed ::= TEXTUAL-CONVENTION
    STATUS        current
    DESCRIPTION
        ""
    SYNTAX        INTEGER
    {
        indeterminate(0),
        n1gbps(1),
        n10gbps(2),
        n20gbps(3),
        n40gbps(4)
    }

CfprFabricEthMonDestEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprFabricEthMonDestEpPortId ::= TEXTUAL-CONVENTION
    STATUS        current
    DESCRIPTION
        ""
    SYNTAX        Gauge32 (1..48)

CfprFabricEthMonDestEpSlotId ::= TEXTUAL-CONVENTION
    STATUS        current
    DESCRIPTION
        ""
    SYNTAX        Gauge32 (1..4)

CfprFabricEthMonDestEpType ::= TEXTUAL-CONVENTION
    STATUS        current
    DESCRIPTION
        ""
    SYNTAX        BITS
    {
        lan(0),
        san(1),
        ipc(2)
    }

CfprFabricEthMonFiltEpType ::= TEXTUAL-CONVENTION
    STATUS        current
    DESCRIPTION
        ""
    SYNTAX        BITS
    {
        lan(0),
        san(1),
        ipc(2)
    }

CfprFabricEthMonFiltRefType ::= TEXTUAL-CONVENTION
    STATUS        current
    DESCRIPTION
        ""
    SYNTAX        BITS
    {
        lan(0),
        san(1),
        ipc(2)
    }

CfprFabricEthMonLanTransport ::= TEXTUAL-CONVENTION
    STATUS        current
    DESCRIPTION
        ""
    SYNTAX        BITS
    {
        ether(0),
        dce(1),
        fc(2)
    }

CfprFabricEthMonLanType ::= TEXTUAL-CONVENTION
    STATUS        current
    DESCRIPTION
        ""
    SYNTAX        BITS
    {
        lan(0),
        san(1),
        ipc(2)
    }

CfprFabricEthMonSrcEpType ::= TEXTUAL-CONVENTION
    STATUS        current
    DESCRIPTION
        ""
    SYNTAX        BITS
    {
        lan(0),
        san(1),
        ipc(2)
    }

CfprFabricEthMonSrcRefType ::= TEXTUAL-CONVENTION
    STATUS        current
    DESCRIPTION
        ""
    SYNTAX        BITS
    {
        lan(0),
        san(1),
        ipc(2)
    }

CfprFabricEthPcProtocol ::= TEXTUAL-CONVENTION
    STATUS        current
    DESCRIPTION
        ""
    SYNTAX        INTEGER
    {
        static(1),
        lacp(2)
    }

CfprFabricEthSourceType ::= TEXTUAL-CONVENTION
    STATUS        current
    DESCRIPTION
        ""
    SYNTAX        INTEGER
    {
        vnic(1),
        uplinkPort(2),
        vlan(3),
        serverPort(4),
        portChannel(5),
        hostPort(6),
        storage(7),
        nasPort(8),
        nasPortChannel(9),
        fcoeuplinkPort(10),
        fcoeuplinkPortchannel(11),
        vmNic(12),
        vhba(20)
    }

CfprFabricEthTargetEpTransport ::= TEXTUAL-CONVENTION
    STATUS        current
    DESCRIPTION
        ""
    SYNTAX        BITS
    {
        ether(0),
        dce(1),
        fc(2)
    }

CfprFabricEthUdldPolicyProtocol ::= TEXTUAL-CONVENTION
    STATUS        current
    DESCRIPTION
        ""
    SYNTAX        INTEGER
    {
        unknown(0),
        udld(1),
        cdp(2)
    }

CfprFabricEthVlanPcTransport ::= TEXTUAL-CONVENTION
    STATUS        current
    DESCRIPTION
        ""
    SYNTAX        BITS
    {
        ether(0),
        dce(1),
        fc(2)
    }

CfprFabricExternalLocale ::= TEXTUAL-CONVENTION
    STATUS        current
    DESCRIPTION
        ""
    SYNTAX        BITS
    {
        server(0),
        chassis(1),
        internal(2),
        external(3)
    }

CfprFabricExternalEpAdminState ::= TEXTUAL-CONVENTION
    STATUS        current
    DESCRIPTION
        ""
    SYNTAX        INTEGER
    {
        enabled(1),
        disabled(2)
    }

CfprFabricExternalEpLocale ::= TEXTUAL-CONVENTION
    STATUS        current
    DESCRIPTION
        ""
    SYNTAX        BITS
    {
        server(0),
        chassis(1),
        internal(2),
        external(3)
    }

CfprFabricExternalPcLocale ::= TEXTUAL-CONVENTION
    STATUS        current
    DESCRIPTION
        ""
    SYNTAX        BITS
    {
        server(0),
        chassis(1),
        internal(2),
        external(3)
    }

CfprFabricFcEstcTransport ::= TEXTUAL-CONVENTION
    STATUS        current
    DESCRIPTION
        ""
    SYNTAX        BITS
    {
        ether(0),
        dce(1),
        fc(2)
    }

CfprFabricFcEstcType ::= TEXTUAL-CONVENTION
    STATUS        current
    DESCRIPTION
        ""
    SYNTAX        BITS
    {
        lan(0),
        san(1),
        ipc(2)
    }

CfprFabricFcEstcEpPortId ::= TEXTUAL-CONVENTION
    STATUS        current
    DESCRIPTION
        ""
    SYNTAX        Gauge32 (1..48)

CfprFabricFcEstcEpSlotId ::= TEXTUAL-CONVENTION
    STATUS        current
    DESCRIPTION
        ""
    SYNTAX        Gauge32 (1..5)

CfprFabricFcMonTransport ::= TEXTUAL-CONVENTION
    STATUS        current
    DESCRIPTION
        ""
    SYNTAX        BITS
    {
        ether(0),
        dce(1),
        fc(2)
    }

CfprFabricFcMonType ::= TEXTUAL-CONVENTION
    STATUS        current
    DESCRIPTION
        ""
    SYNTAX        BITS
    {
        lan(0),
        san(1),
        ipc(2)
    }

CfprFabricFcMonDestEpAdminSpeed ::= TEXTUAL-CONVENTION
    STATUS        current
    DESCRIPTION
        ""
    SYNTAX        INTEGER
    {
        indeterminate(0),
        n1gbps(1),
        n2gbps(2),
        n4gbps(3),
        n8gbps(4),
        auto(5)
    }

CfprFabricFcMonDestEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprFabricFcMonDestEpPortId ::= TEXTUAL-CONVENTION
    STATUS        current
    DESCRIPTION
        ""
    SYNTAX        Gauge32 (1..48)

CfprFabricFcMonDestEpSlotId ::= TEXTUAL-CONVENTION
    STATUS        current
    DESCRIPTION
        ""
    SYNTAX        Gauge32 (1..5)

CfprFabricFcMonDestEpType ::= TEXTUAL-CONVENTION
    STATUS        current
    DESCRIPTION
        ""
    SYNTAX        BITS
    {
        lan(0),
        san(1),
        ipc(2)
    }

CfprFabricFcMonFiltEpType ::= TEXTUAL-CONVENTION
    STATUS        current
    DESCRIPTION
        ""
    SYNTAX        BITS
    {
        lan(0),
        san(1),
        ipc(2)
    }

CfprFabricFcMonFiltRefType ::= TEXTUAL-CONVENTION
    STATUS        current
    DESCRIPTION
        ""
    SYNTAX        BITS
    {
        lan(0),
        san(1),
        ipc(2)
    }

CfprFabricFcMonSanTransport ::= TEXTUAL-CONVENTION
    STATUS        current
    DESCRIPTION
        ""
    SYNTAX        BITS
    {
        ether(0),
        dce(1),
        fc(2)
    }

CfprFabricFcMonSanType ::= TEXTUAL-CONVENTION
    STATUS        current
    DESCRIPTION
        ""
    SYNTAX        BITS
    {
        lan(0),
        san(1),
        ipc(2)
    }

CfprFabricFcMonSrcEpType ::= TEXTUAL-CONVENTION
    STATUS        current
    DESCRIPTION
        ""
    SYNTAX        BITS
    {
        lan(0),
        san(1),
        ipc(2)
    }

CfprFabricFcMonSrcRefType ::= TEXTUAL-CONVENTION
    STATUS        current
    DESCRIPTION
        ""
    SYNTAX        BITS
    {
        lan(0),
        san(1),
        ipc(2)
    }

CfprFabricFcSanTransport ::= TEXTUAL-CONVENTION
    STATUS        current
    DESCRIPTION
        ""
    SYNTAX        BITS
    {
        ether(0),
        dce(1),
        fc(2)
    }

CfprFabricFcSanUplinkTrunking ::= TEXTUAL-CONVENTION
    STATUS        current
    DESCRIPTION
        ""
    SYNTAX        INTEGER
    {
        disabled(0),
        enabled(1)
    }

CfprFabricFcSanEpPortId ::= TEXTUAL-CONVENTION
    STATUS        current
    DESCRIPTION
        ""
    SYNTAX        Gauge32 (1..48)

CfprFabricFcSanEpSlotId ::= TEXTUAL-CONVENTION
    STATUS        current
    DESCRIPTION
        ""
    SYNTAX        Gauge32 (1..5)

CfprFabricFcSanPcTransport ::= TEXTUAL-CONVENTION
    STATUS        current
    DESCRIPTION
        ""
    SYNTAX        BITS
    {
        ether(0),
        dce(1),
        fc(2)
    }

CfprFabricFcSanPcEpPortId ::= TEXTUAL-CONVENTION
    STATUS        current
    DESCRIPTION
        ""
    SYNTAX        Gauge32 (1..48)

CfprFabricFcSanPcEpSlotId ::= TEXTUAL-CONVENTION
    STATUS        current
    DESCRIPTION
        ""
    SYNTAX        Gauge32 (1..5)

CfprFabricFcSourceType ::= TEXTUAL-CONVENTION
    STATUS        current
    DESCRIPTION
        ""
    SYNTAX        INTEGER
    {
        uplinkPort(2),
        vsan(3),
        storage(4),
        portChannel(5),
        vhba(20)
    }

CfprFabricFcVsanPcTransport ::= TEXTUAL-CONVENTION
    STATUS        current
    DESCRIPTION
        ""
    SYNTAX        BITS
    {
        ether(0),
        dce(1),
        fc(2)
    }

CfprFabricFcVsanPortEpPortId ::= TEXTUAL-CONVENTION
    STATUS        current
    DESCRIPTION
        ""
    SYNTAX        Gauge32 (1..256)

CfprFabricFcVsanPortEpSlotId ::= TEXTUAL-CONVENTION
    STATUS        current
    DESCRIPTION
        ""
    SYNTAX        Gauge32 (1..5)

CfprFabricFcZoneSharingMode ::= TEXTUAL-CONVENTION
    STATUS        current
    DESCRIPTION
        ""
    SYNTAX        INTEGER
    {
        coalesce(0),
        clearUnmanagedZoneAll(1)
    }

CfprFabricFcoeEstcEpPortId ::= TEXTUAL-CONVENTION
    STATUS        current
    DESCRIPTION
        ""
    SYNTAX        Gauge32 (1..48)

CfprFabricFcoeEstcEpSlotId ::= TEXTUAL-CONVENTION
    STATUS        current
    DESCRIPTION
        ""
    SYNTAX        Gauge32 (1..4)

CfprFabricFcoeSanEpPortId ::= TEXTUAL-CONVENTION
    STATUS        current
    DESCRIPTION
        ""
    SYNTAX        Gauge32 (1..48)

CfprFabricFcoeSanEpSlotId ::= TEXTUAL-CONVENTION
    STATUS        current
    DESCRIPTION
        ""
    SYNTAX        Gauge32 (1..5)

CfprFabricFcoeSanPcTransport ::= TEXTUAL-CONVENTION
    STATUS        current
    DESCRIPTION
        ""
    SYNTAX        BITS
    {
        ether(0),
        dce(1),
        fc(2)
    }

CfprFabricFcoeSanPcEpPortId ::= TEXTUAL-CONVENTION
    STATUS        current
    DESCRIPTION
        ""
    SYNTAX        Gauge32 (1..48)

CfprFabricFcoeSanPcEpSlotId ::= TEXTUAL-CONVENTION
    STATUS        current
    DESCRIPTION
        ""
    SYNTAX        Gauge32 (1..5)

CfprFabricFcoeVsanPcTransport ::= TEXTUAL-CONVENTION
    STATUS        current
    DESCRIPTION
        ""
    SYNTAX        BITS
    {
        ether(0),
        dce(1),
        fc(2)
    }

CfprFabricFcoeVsanPortEpPortId ::= TEXTUAL-CONVENTION
    STATUS        current
    DESCRIPTION
        ""
    SYNTAX        Gauge32 (1..256)

CfprFabricFcoeVsanPortEpSlotId ::= TEXTUAL-CONVENTION
    STATUS        current
    DESCRIPTION
        ""
    SYNTAX        Gauge32 (1..5)

CfprFabricFillPattern ::= TEXTUAL-CONVENTION
    STATUS        current
    DESCRIPTION
        ""
    SYNTAX        INTEGER
    {
        idle(0),
        arbff(1)
    }

CfprFabricFlowMonCollectorLocale ::= TEXTUAL-CONVENTION
    STATUS        current
    DESCRIPTION
        ""
    SYNTAX        BITS
    {
        server(0),
        chassis(1),
        internal(2),
        external(3)
    }

CfprFabricFlowMonDefType ::= TEXTUAL-CONVENTION
    STATUS        current
    DESCRIPTION
        ""
    SYNTAX        INTEGER
    {
        systemDefined(1),
        userDefined(2)
    }

CfprFabricFlowMonIpv4Keys ::= TEXTUAL-CONVENTION
    STATUS        current
    DESCRIPTION
        ""
    SYNTAX        BITS
    {
        ipv4SrcAddress(0),
        ipv4DestAddress(1),
        ipProtocol(2),
        ipTos(3),
        srcPort(4),
        destPort(5)
    }

CfprFabricFlowMonIpv6Keys ::= TEXTUAL-CONVENTION
    STATUS        current
    DESCRIPTION
        ""
    SYNTAX        BITS
    {
        ipv6SrcAddress(0),
        ipv6DestAddress(1),
        ipProtocol(2),
        srcPort(4),
        destPort(5)
    }

CfprFabricFlowMonKeyType ::= TEXTUAL-CONVENTION
    STATUS        current
    DESCRIPTION
        ""
    SYNTAX        INTEGER
    {
        l2keys(0),
        ipv4keys(1),
        ipv6keys(2)
    }

CfprFabricFlowMonL2Keys ::= TEXTUAL-CONVENTION
    STATUS        current
    DESCRIPTION
        ""
    SYNTAX        BITS
    {
        ethertype(0),
        destMacAddress(1),
        srcMacAddress(2)
    }

CfprFabricFlowMonNonKeys ::= TEXTUAL-CONVENTION
    STATUS        current
    DESCRIPTION
        ""
    SYNTAX        BITS
    {
        counterPacketsLong(0),
        counterBytesLong(1),
        sysUptimeFirst(2),
        sysUptimeLast(3)
    }

CfprFabricFlowMonitoringCategoryAdminState ::= TEXTUAL-CONVENTION
    STATUS        current
    DESCRIPTION
        ""
    SYNTAX        INTEGER
    {
        enabled(1),
        disabled(2)
    }

CfprFabricHostPortId ::= TEXTUAL-CONVENTION
    STATUS        current
    DESCRIPTION
        ""
    SYNTAX        INTEGER
    {
        any(0),
        n1(1),
        n2(2),
        none(10)
    }

CfprFabricInternalLocale ::= TEXTUAL-CONVENTION
    STATUS        current
    DESCRIPTION
        ""
    SYNTAX        BITS
    {
        server(0),
        chassis(1),
        internal(2),
        external(3)
    }

CfprFabricInternalDceSrvTransport ::= TEXTUAL-CONVENTION
    STATUS        current
    DESCRIPTION
        ""
    SYNTAX        BITS
    {
        ether(0),
        dce(1),
        fc(2)
    }

CfprFabricInternalDceSrvType ::= TEXTUAL-CONVENTION
    STATUS        current
    DESCRIPTION
        ""
    SYNTAX        BITS
    {
        lan(0),
        san(1),
        ipc(2)
    }

CfprFabricInternalEpAdminState ::= TEXTUAL-CONVENTION
    STATUS        current
    DESCRIPTION
        ""
    SYNTAX        INTEGER
    {
        enabled(1),
        disabled(2)
    }

CfprFabricInternalEpLocale ::= TEXTUAL-CONVENTION
    STATUS        current
    DESCRIPTION
        ""
    SYNTAX        BITS
    {
        server(0),
        chassis(1),
        internal(2),
        external(3)
    }

CfprFabricInternalPcLocale ::= TEXTUAL-CONVENTION
    STATUS        current
    DESCRIPTION
        ""
    SYNTAX        BITS
    {
        server(0),
        chassis(1),
        internal(2),
        external(3)
    }

CfprFabricLacpMode ::= TEXTUAL-CONVENTION
    STATUS        current
    DESCRIPTION
        ""
    SYNTAX        INTEGER
    {
        active(0),
        on(1)
    }

CfprFabricLacpRate ::= TEXTUAL-CONVENTION
    STATUS        current
    DESCRIPTION
        ""
    SYNTAX        INTEGER
    {
        normal(0),
        fast(1)
    }

CfprFabricLacpSuspend ::= TEXTUAL-CONVENTION
    STATUS        current
    DESCRIPTION
        ""
    SYNTAX        INTEGER
    {
        false(0),
        true(1)
    }

CfprFabricLanType ::= TEXTUAL-CONVENTION
    STATUS        current
    DESCRIPTION
        ""
    SYNTAX        BITS
    {
        lan(0),
        san(1),
        ipc(2)
    }

CfprFabricLanCloudVlanCompression ::= TEXTUAL-CONVENTION
    STATUS        current
    DESCRIPTION
        ""
    SYNTAX        INTEGER
    {
        enabled(1),
        disabled(2)
    }

CfprFabricLanCloudFsmCurrentFsm ::= TEXTUAL-CONVENTION
    STATUS        current
    DESCRIPTION
        ""
    SYNTAX        INTEGER
    {
        nop(0),
        switchMode(184)
    }

CfprFabricLanCloudFsmStageName ::= TEXTUAL-CONVENTION
    STATUS        current
    DESCRIPTION
        ""
    SYNTAX        INTEGER
    {
        nop(0),
        switchModeBegin(184),
        switchModeSwConfigPeer(185),
        switchModeSwConfigLocal(186),
        switchModeFail(392),
        switchModeSuccess(393)
    }

CfprFabricLanCloudFsmTaskItem ::= TEXTUAL-CONVENTION
    STATUS        current
    DESCRIPTION
        ""
    SYNTAX        INTEGER
    {
        nop(0),
        switchMode(184)
    }

CfprFabricLanEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprFabricLanEpType ::= TEXTUAL-CONVENTION
    STATUS        current
    DESCRIPTION
        ""
    SYNTAX        BITS
    {
        lan(0),
        san(1),
        ipc(2)
    }

CfprFabricLanFlowMonType ::= TEXTUAL-CONVENTION
    STATUS        current
    DESCRIPTION
        ""
    SYNTAX        BITS
    {
        lan(0),
        san(1),
        ipc(2)
    }

CfprFabricLanFlowMonCollectorType ::= TEXTUAL-CONVENTION
    STATUS        current
    DESCRIPTION
        ""
    SYNTAX        BITS
    {
        lan(0),
        san(1),
        ipc(2)
    }

CfprFabricLanFlowMonExporterType ::= TEXTUAL-CONVENTION
    STATUS        current
    DESCRIPTION
        ""
    SYNTAX        BITS
    {
        lan(0),
        san(1),
        ipc(2)
    }

CfprFabricLanFlowMonSrcEpType ::= TEXTUAL-CONVENTION
    STATUS        current
    DESCRIPTION
        ""
    SYNTAX        BITS
    {
        lan(0),
        san(1),
        ipc(2)
    }

CfprFabricLanFlowMonitorType ::= TEXTUAL-CONVENTION
    STATUS        current
    DESCRIPTION
        ""
    SYNTAX        BITS
    {
        lan(0),
        san(1),
        ipc(2)
    }

CfprFabricLanPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprFabricLanPcType ::= TEXTUAL-CONVENTION
    STATUS        current
    DESCRIPTION
        ""
    SYNTAX        BITS
    {
        lan(0),
        san(1),
        ipc(2)
    }

CfprFabricLifeCycle ::= TEXTUAL-CONVENTION
    STATUS        current
    DESCRIPTION
        ""
    SYNTAX        INTEGER
    {
        inService(1),
        outOfService(2),
        outOfServiceSlave(3)
    }

CfprFabricMemberStatus ::= TEXTUAL-CONVENTION
    STATUS        current
    DESCRIPTION
        ""
    SYNTAX        INTEGER
    {
        up(0),
        down(1)
    }

CfprFabricMembershipStatus ::= TEXTUAL-CONVENTION
    STATUS        current
    DESCRIPTION
        ""
    SYNTAX        INTEGER
    {
        down(1),
        up(2),
        hotStandby(3),
        suspended(4),
        individual(5),
        moduleRemoved(6),
        incompatibleSpeed(7),
        unknown(8)
    }

CfprFabricMonAdminState ::= TEXTUAL-CONVENTION
    STATUS        current
    DESCRIPTION
        ""
    SYNTAX        INTEGER
    {
        enabled(1),
        disabled(2)
    }

CfprFabricMonOperState ::= TEXTUAL-CONVENTION
    STATUS        current
    DESCRIPTION
        ""
    SYNTAX        INTEGER
    {
        unknown(0),
        up(1),
        down(2),
        error(3)
    }

CfprFabricMonOperStateReason ::= TEXTUAL-CONVENTION
    STATUS        current
    DESCRIPTION
        ""
    SYNTAX        INTEGER
    {
        active(0),
        noHardwareResource(1),
        noOperationalSrcDst(2),
        genericError(3),
        noSourcesConfigured(4),
        noDestinationConfigured(5),
        noSourceDestinationConfigured(6),
        sessionAdminShut(7),
        wrongDestinationMode(8),
        wrongSourceMode(9),
        tunnelMisconfDown(10),
        noFlowIdSpecified(11),
        unknown(12)
    }

CfprFabricNFExporterVersion ::= TEXTUAL-CONVENTION
    STATUS        current
    DESCRIPTION
        ""
    SYNTAX        INTEGER
    {
        v9(1),
        ipfix(2)
    }

CfprFabricNFTransport ::= TEXTUAL-CONVENTION
    STATUS        current
    DESCRIPTION
        ""
    SYNTAX        INTEGER
    {
        udp(1),
        sctp(2)
    }

CfprFabricNetGroupSwitchId ::= TEXTUAL-CONVENTION
    STATUS        current
    DESCRIPTION
        ""
    SYNTAX        INTEGER
    {
        none(0),
        a(1),
        b(2),
        dual(3)
    }

CfprFabricNetGroupType ::= TEXTUAL-CONVENTION
    STATUS        current
    DESCRIPTION
        ""
    SYNTAX        BITS
    {
        mgmt(0),
        vlanCompression(1),
        vlanUncompressed(2)
    }

CfprFabricNetflowCollectorFlowProtocol ::= TEXTUAL-CONVENTION
    STATUS        current
    DESCRIPTION
        ""
    SYNTAX        INTEGER
    {
        netflow(1)
    }

CfprFabricNetflowConfigIssues ::= TEXTUAL-CONVENTION
    STATUS        current
    DESCRIPTION
        ""
    SYNTAX        BITS
    {
        monitorUnresolved(0),
        exporterUnresolved(1),
        exporterProfileUnresolved(2),
        collectorUnresolved(3),
        sourceVlanUnresolved(4)
    }

CfprFabricNetflowMonExporterProtocol ::= TEXTUAL-CONVENTION
    STATUS        current
    DESCRIPTION
        ""
    SYNTAX        INTEGER
    {
        netflow(1)
    }

CfprFabricNetflowMonSessionAdminState ::= TEXTUAL-CONVENTION
    STATUS        current
    DESCRIPTION
        ""
    SYNTAX        INTEGER
    {
        enabled(1),
        disabled(2)
    }

CfprFabricNetflowMonSessionProtocol ::= TEXTUAL-CONVENTION
    STATUS        current
    DESCRIPTION
        ""
    SYNTAX        INTEGER
    {
        netflow(1)
    }

CfprFabricNetflowMonSrcEpProtocol ::= TEXTUAL-CONVENTION
    STATUS        current
    DESCRIPTION
        ""
    SYNTAX        INTEGER
    {
        netflow(1)
    }

CfprFabricNetflowMonSrcRefProtocol ::= TEXTUAL-CONVENTION
    STATUS        current
    DESCRIPTION
        ""
    SYNTAX        INTEGER
    {
        netflow(1)
    }

CfprFabricNetflowMonitorFlowMonProtocol ::= TEXTUAL-CONVENTION
    STATUS        current
    DESCRIPTION
        ""
    SYNTAX        INTEGER
    {
        netflow(1)
    }

CfprFabricOperState ::= TEXTUAL-CONVENTION
    STATUS        current
    DESCRIPTION
        ""
    SYNTAX        INTEGER
    {
        unknown(0),
        up(1),
        down(2),
        errorMisconfigured(3)
    }

CfprFabricOwner ::= TEXTUAL-CONVENTION
    STATUS        current
    DESCRIPTION
        ""
    SYNTAX        INTEGER
    {
        policy(1),
        management(2)
    }

CfprFabricPIoEpIfType ::= TEXTUAL-CONVENTION
    STATUS        current
    DESCRIPTION
        ""
    SYNTAX        INTEGER
    {
        unknown(0),
        physical(1),
        aggregation(2),
        virtual(3)
    }

CfprFabricPIoEpOperState ::= TEXTUAL-CONVENTION
    STATUS        current
    DESCRIPTION
        ""
    SYNTAX        INTEGER
    {
        unknown(0),
        up(1),
        down(2),
        errorMisconfigured(3)
    }

CfprFabricPIoEpPortId ::= TEXTUAL-CONVENTION
    STATUS        current
    DESCRIPTION
        ""
    SYNTAX        Gauge32 (1..48)

CfprFabricPIoEpSlotId ::= TEXTUAL-CONVENTION
    STATUS        current
    DESCRIPTION
        ""
    SYNTAX        Gauge32 (1..4)

CfprFabricPathEpIfType ::= TEXTUAL-CONVENTION
    STATUS        current
    DESCRIPTION
        ""
    SYNTAX        INTEGER
    {
        unknown(0),
        physical(1),
        aggregation(2),
        virtual(3)
    }

CfprFabricPathEpLocale ::= TEXTUAL-CONVENTION
    STATUS        current
    DESCRIPTION
        ""
    SYNTAX        BITS
    {
        server(0),
        chassis(1),
        internal(2),
        external(3)
    }

CfprFabricPcConfigStatus ::= TEXTUAL-CONVENTION
    STATUS        current
    DESCRIPTION
        ""
    SYNTAX        INTEGER
    {
        applied(1),
        incompatibleSpeed(2)
    }

CfprFabricPcMode ::= TEXTUAL-CONVENTION
    STATUS        current
    DESCRIPTION
        ""
    SYNTAX        INTEGER
    {
        active(0),
        on(1)
    }

CfprFabricPcModeState ::= TEXTUAL-CONVENTION
    STATUS        current
    DESCRIPTION
        ""
    SYNTAX        INTEGER
    {
        disabled(0),
        enabled(1)
    }

CfprFabricPktCaptureAppSlotId ::= TEXTUAL-CONVENTION
    STATUS        current
    DESCRIPTION
        ""
    SYNTAX        Gauge32 (1..3)

CfprFabricPktCaptureAppendFlag ::= TEXTUAL-CONVENTION
    STATUS        current
    DESCRIPTION
        ""
    SYNTAX        INTEGER
    {
        append(1),
        overwrite(2)
    }

CfprFabricPoolMemberConfigIssues ::= TEXTUAL-CONVENTION
    STATUS        current
    DESCRIPTION
        ""
    SYNTAX        BITS
    {
        namedVlanUnresolved(0)
    }

CfprFabricPort ::= TEXTUAL-CONVENTION
    STATUS        current
    DESCRIPTION
        ""
    SYNTAX        Gauge32 (0..65535)

CfprFabricQosPrio ::= TEXTUAL-CONVENTION
    STATUS        current
    DESCRIPTION
        ""
    SYNTAX        INTEGER
    {
        low(0),
        high(1)
    }

CfprFabricQuerierType ::= TEXTUAL-CONVENTION
    STATUS        current
    DESCRIPTION
        ""
    SYNTAX        INTEGER
    {
        enabled(0),
        disabled(1)
    }

CfprFabricReqIssues ::= TEXTUAL-CONVENTION
    STATUS        current
    DESCRIPTION
        ""
    SYNTAX        BITS
    {
        permitUnresolved(0)
    }

CfprFabricSSAPortType ::= TEXTUAL-CONVENTION
    STATUS        current
    DESCRIPTION
        ""
    SYNTAX        INTEGER
    {
        data(0),
        mgmt(1),
        cluster(2),
        firepowerEventing(3),
        virtualData(4),
        dataSharing(5)
    }

CfprFabricSSASubPortType ::= TEXTUAL-CONVENTION
    STATUS        current
    DESCRIPTION
        ""
    SYNTAX        INTEGER
    {
        data(0),
        cluster(2),
        dataSharing(5)
    }

CfprFabricSanType ::= TEXTUAL-CONVENTION
    STATUS        current
    DESCRIPTION
        ""
    SYNTAX        BITS
    {
        lan(0),
        san(1),
        ipc(2)
    }

CfprFabricSanCloudFsmCurrentFsm ::= TEXTUAL-CONVENTION
    STATUS        current
    DESCRIPTION
        ""
    SYNTAX        INTEGER
    {
        nop(0),
        switchMode(871)
    }

CfprFabricSanCloudFsmStageName ::= TEXTUAL-CONVENTION
    STATUS        current
    DESCRIPTION
        ""
    SYNTAX        INTEGER
    {
        nop(0),
        switchModeBegin(871),
        switchModeSwConfigPeer(872),
        switchModeSwConfigLocal(873),
        switchModeFail(992),
        switchModeSuccess(993)
    }

CfprFabricSanCloudFsmTaskItem ::= TEXTUAL-CONVENTION
    STATUS        current
    DESCRIPTION
        ""
    SYNTAX        INTEGER
    {
        nop(0),
        switchMode(871)
    }

CfprFabricSanEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprFabricSanEpType ::= TEXTUAL-CONVENTION
    STATUS        current
    DESCRIPTION
        ""
    SYNTAX        BITS
    {
        lan(0),
        san(1),
        ipc(2)
    }

CfprFabricSanPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprFabricSanPcType ::= TEXTUAL-CONVENTION
    STATUS        current
    DESCRIPTION
        ""
    SYNTAX        BITS
    {
        lan(0),
        san(1),
        ipc(2)
    }

CfprFabricSlotAdminState ::= TEXTUAL-CONVENTION
    STATUS        current
    DESCRIPTION
        ""
    SYNTAX        INTEGER
    {
        acknowledged(1),
        reacknowledge(3)
    }

CfprFabricSnoopingType ::= TEXTUAL-CONVENTION
    STATUS        current
    DESCRIPTION
        ""
    SYNTAX        INTEGER
    {
        enabled(0),
        disabled(1)
    }

CfprFabricSpannedCluster ::= TEXTUAL-CONVENTION
    STATUS        current
    DESCRIPTION
        ""
    SYNTAX        INTEGER
    {
        enabled(1),
        disabled(2)
    }

CfprFabricSspEthMonAppendFlag ::= TEXTUAL-CONVENTION
    STATUS        current
    DESCRIPTION
        ""
    SYNTAX        INTEGER
    {
        append(1),
        overwrite(2)
    }

CfprFabricSspEthMonDelAllSessEnabledState ::= TEXTUAL-CONVENTION
    STATUS        current
    DESCRIPTION
        ""
    SYNTAX        INTEGER
    {
        valid(1),
        invalid(2)
    }

CfprFabricSspLanMonCloudDelAllSess ::= TEXTUAL-CONVENTION
    STATUS        current
    DESCRIPTION
        ""
    SYNTAX        INTEGER
    {
        enabled(1),
        disabled(2)
    }

CfprFabricSspMonAdminState ::= TEXTUAL-CONVENTION
    STATUS        current
    DESCRIPTION
        ""
    SYNTAX        INTEGER
    {
        enabled(1),
        disabled(2)
    }

CfprFabricSspMonDelPcap ::= TEXTUAL-CONVENTION
    STATUS        current
    DESCRIPTION
        ""
    SYNTAX        INTEGER
    {
        enabled(1),
        disabled(2)
    }

CfprFabricSspMonOperState ::= TEXTUAL-CONVENTION
    STATUS        current
    DESCRIPTION
        ""
    SYNTAX        INTEGER
    {
        unknown(0),
        up(1),
        down(2),
        error(3)
    }

CfprFabricSspMonOperStateReason ::= TEXTUAL-CONVENTION
    STATUS        current
    DESCRIPTION
        ""
    SYNTAX        INTEGER
    {
        active(0),
        noHardwareResource(1),
        noOperationalSrcDst(2),
        genericError(3),
        noSourcesConfigured(4),
        sessionAdminShut(5),
        directoryError(8),
        unknown(12),
        fileError(16),
        memoryOvershoot(32),
        pipeError(64),
        linkError(128),
        filterError(256),
        filterErrorAppId(768)
    }

CfprFabricStatus ::= TEXTUAL-CONVENTION
    STATUS        current
    DESCRIPTION
        ""
    SYNTAX        INTEGER
    {
        modified(0),
        created(1),
        deleted(2),
        intentDeletion(3)
    }

CfprFabricSubGroupAggrPortId ::= TEXTUAL-CONVENTION
    STATUS        current
    DESCRIPTION
        ""
    SYNTAX        Gauge32 (1..48)

CfprFabricSubGroupConfigState ::= TEXTUAL-CONVENTION
    STATUS        current
    DESCRIPTION
        ""
    SYNTAX        INTEGER
    {
        enabled(1),
        disabled(2)
    }

CfprFabricSubGroupSlotId ::= TEXTUAL-CONVENTION
    STATUS        current
    DESCRIPTION
        ""
    SYNTAX        Gauge32 (1..4)

CfprFabricSwChEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprFabricSwChEpType ::= TEXTUAL-CONVENTION
    STATUS        current
    DESCRIPTION
        ""
    SYNTAX        BITS
    {
        lan(0),
        san(1),
        ipc(2)
    }

CfprFabricSwChPhEpAdminState ::= TEXTUAL-CONVENTION
    STATUS        current
    DESCRIPTION
        ""
    SYNTAX        INTEGER
    {
        enabled(1),
        disabled(2),
        remove(3)
    }

CfprFabricSwSrvEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprFabricSwSrvEpType ::= TEXTUAL-CONVENTION
    STATUS        current
    DESCRIPTION
        ""
    SYNTAX        BITS
    {
        lan(0),
        san(1),
        ipc(2)
    }

CfprFabricSwSrvPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprFabricSwSrvPcType ::= TEXTUAL-CONVENTION
    STATUS        current
    DESCRIPTION
        ""
    SYNTAX        BITS
    {
        lan(0),
        san(1),
        ipc(2)
    }

CfprFabricSwSubGroupAggrPortId ::= TEXTUAL-CONVENTION
    STATUS        current
    DESCRIPTION
        ""
    SYNTAX        Gauge32 (1..48)

CfprFabricSwSubGroupConfigState ::= TEXTUAL-CONVENTION
    STATUS        current
    DESCRIPTION
        ""
    SYNTAX        INTEGER
    {
        enabled(1),
        disabled(2)
    }

CfprFabricSwSubGroupSlotId ::= TEXTUAL-CONVENTION
    STATUS        current
    DESCRIPTION
        ""
    SYNTAX        Gauge32 (1..4)

CfprFabricSwitchingMode ::= TEXTUAL-CONVENTION
    STATUS        current
    DESCRIPTION
        ""
    SYNTAX        INTEGER
    {
        endHost(0),
        switch(1),
        securityNode(2)
    }

CfprFabricTargetEpType ::= TEXTUAL-CONVENTION
    STATUS        current
    DESCRIPTION
        ""
    SYNTAX        BITS
    {
        lan(0),
        san(1),
        ipc(2)
    }

CfprFabricTargetStatus ::= TEXTUAL-CONVENTION
    STATUS        current
    DESCRIPTION
        ""
    SYNTAX        INTEGER
    {
        valid(0),
        invalid(1)
    }

CfprFabricTrafficDirection ::= TEXTUAL-CONVENTION
    STATUS        current
    DESCRIPTION
        ""
    SYNTAX        INTEGER
    {
        rx(1),
        tx(2),
        both(3)
    }

CfprFabricUdldLinkPolicyAdminState ::= TEXTUAL-CONVENTION
    STATUS        current
    DESCRIPTION
        ""
    SYNTAX        INTEGER
    {
        enabled(1),
        disabled(2)
    }

CfprFabricUdldLinkPolicyMode ::= TEXTUAL-CONVENTION
    STATUS        current
    DESCRIPTION
        ""
    SYNTAX        INTEGER
    {
        normal(0),
        aggressive(1)
    }

CfprFabricUdldOperState ::= TEXTUAL-CONVENTION
    STATUS        current
    DESCRIPTION
        ""
    SYNTAX        INTEGER
    {
        unknown(0),
        unidirectional(1),
        bidirectional(2),
        txRxLoop(3),
        mismatch(4),
        echoEmpty(5),
        adminDisabled(6)
    }

CfprFabricVConInstType ::= TEXTUAL-CONVENTION
    STATUS        current
    DESCRIPTION
        ""
    SYNTAX        INTEGER
    {
        auto(1),
        manual(2),
        policy(3)
    }

CfprFabricVConMappingScheme ::= TEXTUAL-CONVENTION
    STATUS        current
    DESCRIPTION
        ""
    SYNTAX        INTEGER
    {
        roundRobin(2),
        linearOrdered(3),
        roundRobinToLinearOrdered(4),
        linearOrderedToRoundRobin(5)
    }

CfprFabricVConPlacementPref ::= TEXTUAL-CONVENTION
    STATUS        current
    DESCRIPTION
        ""
    SYNTAX        INTEGER
    {
        physical(1),
        auto(2)
    }

CfprFabricVConSelectPref ::= TEXTUAL-CONVENTION
    STATUS        current
    DESCRIPTION
        ""
    SYNTAX        INTEGER
    {
        assignedOnly(1),
        unassignedOnly(2),
        dynamicOnly(4),
        excludeUsnic(7),
        usnicOnly(8),
        excludeDynamic(11),
        excludeUnassigned(13),
        all(15)
    }

CfprFabricVConSharePref ::= TEXTUAL-CONVENTION
    STATUS        current
    DESCRIPTION
        ""
    SYNTAX        INTEGER
    {
        exclusiveOnly(1),
        exclusivePreferred(2),
        sameTransport(3),
        differentTransport(4),
        shared(5)
    }

CfprFabricVConTransportPref ::= TEXTUAL-CONVENTION
    STATUS        current
    DESCRIPTION
        ""
    SYNTAX        BITS
    {
        fc(0),
        ethernet(1)
    }

CfprFabricVlanSwitchId ::= TEXTUAL-CONVENTION
    STATUS        current
    DESCRIPTION
        ""
    SYNTAX        INTEGER
    {
        none(0),
        a(1),
        b(2),
        dual(3)
    }

CfprFabricVlanAssocPrimaryVlanState ::= TEXTUAL-CONVENTION
    STATUS        current
    DESCRIPTION
        ""
    SYNTAX        INTEGER
    {
        ok(1),
        isEmpty(2),
        doesNotExists(3),
        isNotPrimaryType(4),
        isInErrorState(5)
    }

CfprFabricVlanCompType ::= TEXTUAL-CONVENTION
    STATUS        current
    DESCRIPTION
        ""
    SYNTAX        INTEGER
    {
        included(1),
        excluded(2)
    }

CfprFabricVlanConfigIssues ::= TEXTUAL-CONVENTION
    STATUS        current
    DESCRIPTION
        ""
    SYNTAX        BITS
    {
        conflictingVlanAccess(0),
        unsupportedMulticastPolicy(1)
    }

CfprFabricVlanOperState ::= TEXTUAL-CONVENTION
    STATUS        current
    DESCRIPTION
        ""
    SYNTAX        INTEGER
    {
        ok(1),
        errorMisconfigured(2)
    }

CfprFabricVlanOverlapState ::= TEXTUAL-CONVENTION
    STATUS        current
    DESCRIPTION
        ""
    SYNTAX        INTEGER
    {
        notActive(0),
        ok(1),
        sharingTypeMismatch(2),
        primaryIdMismatch(3)
    }

CfprFabricVlanSharingType ::= TEXTUAL-CONVENTION
    STATUS        current
    DESCRIPTION
        ""
    SYNTAX        INTEGER
    {
        none(0),
        primary(1),
        isolated(2),
        community(3)
    }

CfprFabricVnetEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprFabricVnetEpLocale ::= TEXTUAL-CONVENTION
    STATUS        current
    DESCRIPTION
        ""
    SYNTAX        BITS
    {
        server(0),
        chassis(1),
        internal(2),
        external(3)
    }

CfprFabricVnetEpPolicyOwner ::= TEXTUAL-CONVENTION
    STATUS        current
    DESCRIPTION
        ""
    SYNTAX        INTEGER
    {
        local(0),
        policy(1),
        pendingPolicy(2)
    }

CfprFabricVnetEpSyncEpFsmCurrentFsm ::= TEXTUAL-CONVENTION
    STATUS        current
    DESCRIPTION
        ""
    SYNTAX        INTEGER
    {
        nop(0),
        pushVnetEpDeletion(1481)
    }

CfprFabricVnetEpSyncEpFsmStageName ::= TEXTUAL-CONVENTION
    STATUS        current
    DESCRIPTION
        ""
    SYNTAX        INTEGER
    {
        nop(0),
        pushVnetEpDeletionBegin(1481),
        pushVnetEpDeletionSync(1482),
        pushVnetEpDeletionFail(1485),
        pushVnetEpDeletionSuccess(1486)
    }

CfprFabricVnetEpSyncEpFsmTaskItem ::= TEXTUAL-CONVENTION
    STATUS        current
    DESCRIPTION
        ""
    SYNTAX        INTEGER
    {
        nop(0),
        pushVnetEpDeletion(1481)
    }

CfprFabricVsanSwitchId ::= TEXTUAL-CONVENTION
    STATUS        current
    DESCRIPTION
        ""
    SYNTAX        INTEGER
    {
        none(0),
        a(1),
        b(2),
        dual(3)
    }

CfprFabricVsanOperState ::= TEXTUAL-CONVENTION
    STATUS        current
    DESCRIPTION
        ""
    SYNTAX        INTEGER
    {
        ok(1),
        errorMisconfigured(2),
        errorReserved(3)
    }

CfprFabricWarnings ::= TEXTUAL-CONVENTION
    STATUS        current
    DESCRIPTION
        ""
    SYNTAX        BITS
    {
        fcZoningEnabled(0),
        configurationError(1)
    }

CfprFabricZoningState ::= TEXTUAL-CONVENTION
    STATUS        current
    DESCRIPTION
        ""
    SYNTAX        INTEGER
    {
        disabled(0),
        enabled(1)
    }

CfprFabricRecoveryAction ::= TEXTUAL-CONVENTION
    STATUS        current
    DESCRIPTION
        ""
    SYNTAX        INTEGER
    {
        none(0),
        reset(1)
    }

CfprFaultBasePolicyClearAction ::= TEXTUAL-CONVENTION
    STATUS        current
    DESCRIPTION
        ""
    SYNTAX        INTEGER
    {
        retain(0),
        delete(1)
    }

CfprFaultBasePolicySoakingSeverity ::= TEXTUAL-CONVENTION
    STATUS        current
    DESCRIPTION
        ""
    SYNTAX        INTEGER
    {
        info(1),
        condition(2),
        warning(3)
    }

CfprFcErrStatsThresholded ::= TEXTUAL-CONVENTION
    STATUS        current
    DESCRIPTION
        ""
    SYNTAX        BITS
    {
        crcRxDelta(0),
        crcRxDeltaAvg(1),
        crcRxDeltaMax(2),
        crcRxDeltaMin(3),
        discardRxDelta(4),
        discardRxDeltaAvg(5),
        discardRxDeltaMax(6),
        discardRxDeltaMin(7),
        discardTxDelta(8),
        discardTxDeltaAvg(9),
        discardTxDeltaMax(10),
        discardTxDeltaMin(11),
        linkFailuresDelta(12),
        linkFailuresDeltaAvg(13),
        linkFailuresDeltaMax(14),
        linkFailuresDeltaMin(15),
        rxDelta(16),
        rxDeltaAvg(17),
        rxDeltaMax(18),
        rxDeltaMin(19),
        signalLossesDelta(20),
        signalLossesDeltaAvg(21),
        signalLossesDeltaMax(22),
        signalLossesDeltaMin(23),
        syncLossesDelta(24),
        syncLossesDeltaAvg(25),
        syncLossesDeltaMax(26),
        syncLossesDeltaMin(27),
        tooLongRxDelta(28),
        tooLongRxDeltaAvg(29),
        tooLongRxDeltaMax(30),
        tooLongRxDeltaMin(31),
        tooShortRxDelta(32),
        tooShortRxDeltaAvg(33),
        tooShortRxDeltaMax(34),
        tooShortRxDeltaMin(35),
        txDelta(36),
        txDeltaAvg(37),
        txDeltaMax(38),
        txDeltaMin(39)
    }

CfprFcErrStatsHistThresholded ::= TEXTUAL-CONVENTION
    STATUS        current
    DESCRIPTION
        ""
    SYNTAX        BITS
    {
        crcRxDelta(0),
        crcRxDeltaAvg(1),
        crcRxDeltaMax(2),
        crcRxDeltaMin(3),
        discardRxDelta(4),
        discardRxDeltaAvg(5),
        discardRxDeltaMax(6),
        discardRxDeltaMin(7),
        discardTxDelta(8),
        discardTxDeltaAvg(9),
        discardTxDeltaMax(10),
        discardTxDeltaMin(11),
        linkFailuresDelta(12),
        linkFailuresDeltaAvg(13),
        linkFailuresDeltaMax(14),
        linkFailuresDeltaMin(15),
        rxDelta(16),
        rxDeltaAvg(17),
        rxDeltaMax(18),
        rxDeltaMin(19),
        signalLossesDelta(20),
        signalLossesDeltaAvg(21),
        signalLossesDeltaMax(22),
        signalLossesDeltaMin(23),
        syncLossesDelta(24),
        syncLossesDeltaAvg(25),
        syncLossesDeltaMax(26),
        syncLossesDeltaMin(27),
        tooLongRxDelta(28),
        tooLongRxDeltaAvg(29),
        tooLongRxDeltaMax(30),
        tooLongRxDeltaMin(31),
        tooShortRxDelta(32),
        tooShortRxDeltaAvg(33),
        tooShortRxDeltaMax(34),
        tooShortRxDeltaMin(35),
        txDelta(36),
        txDeltaAvg(37),
        txDeltaMax(38),
        txDeltaMin(39)
    }

CfprFcPIoFsmCurrentFsm ::= TEXTUAL-CONVENTION
    STATUS        current
    DESCRIPTION
        ""
    SYNTAX        INTEGER
    {
        nop(0),
        inCompatSfpPresence(1014),
        inCompatSfpReplaced(1268)
    }

CfprFcPIoFsmStageName ::= TEXTUAL-CONVENTION
    STATUS        current
    DESCRIPTION
        ""
    SYNTAX        INTEGER
    {
        nop(0),
        inCompatSfpPresenceBegin(1014),
        inCompatSfpPresenceShutdown(1015),
        inCompatSfpPresenceFail(1034),
        inCompatSfpPresenceSuccess(1035),
        inCompatSfpReplacedBegin(1268),
        inCompatSfpReplacedEnablePort(1269),
        inCompatSfpReplacedFail(1462),
        inCompatSfpReplacedSuccess(1463)
    }

CfprFcStatsThresholded ::= TEXTUAL-CONVENTION
    STATUS        current
    DESCRIPTION
        ""
    SYNTAX        BITS
    {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        packetsRxDelta(8),
        packetsRxDeltaAvg(9),
        packetsRxDeltaMax(10),
        packetsRxDeltaMin(11),
        packetsTxDelta(12),
        packetsTxDeltaAvg(13),
        packetsTxDeltaMax(14),
        packetsTxDeltaMin(15)
    }

CfprFcStatsHistThresholded ::= TEXTUAL-CONVENTION
    STATUS        current
    DESCRIPTION
        ""
    SYNTAX        BITS
    {
        bytesRxDelta(0),
        bytesRxDeltaAvg(1),
        bytesRxDeltaMax(2),
        bytesRxDeltaMin(3),
        bytesTxDelta(4),
        bytesTxDeltaAvg(5),
        bytesTxDeltaMax(6),
        bytesTxDeltaMin(7),
        packetsRxDelta(8),
        packetsRxDeltaAvg(9),
        packetsRxDeltaMax(10),
        packetsRxDeltaMin(11),
        packetsTxDelta(12),
        packetsTxDeltaAvg(13),
        packetsTxDeltaMax(14),
        packetsTxDeltaMin(15)
    }

CfprFcpoolBootTargetType ::= TEXTUAL-CONVENTION
    STATUS        current
    DESCRIPTION
        ""
    SYNTAX        INTEGER
    {
        primary(0),
        secondary(1)
    }

CfprFcpoolInitiatorPurpose ::= TEXTUAL-CONVENTION
    STATUS        current
    DESCRIPTION
        ""
    SYNTAX        INTEGER
    {
        portWwn(0),
        nodeWwn(1),
        derived(2)
    }

CfprFcpoolInitiatorEpPurpose ::= TEXTUAL-CONVENTION
    STATUS        current
    DESCRIPTION
        ""
    SYNTAX        INTEGER
    {
        portWwn(0),
        nodeWwn(1)
    }

CfprFcpoolInitiatorsAssignmentOrder ::= TEXTUAL-CONVENTION
    STATUS        current
    DESCRIPTION
        ""
    SYNTAX        INTEGER
    {
        default(0),
        sequential(1)
    }

CfprFcpoolInitiatorsMaxPortsPerNode ::= TEXTUAL-CONVENTION
    STATUS        current
    DESCRIPTION
        ""
    SYNTAX        INTEGER
    {
        upto3(3),
        upto7(7),
        upto15(15),
        upto31(31),
        upto63(63)
    }

CfprFcpoolInitiatorsPurpose ::= TEXTUAL-CONVENTION
    STATUS        current
    DESCRIPTION
        ""
    SYNTAX        INTEGER
    {
        nodeAndPortWwnAssignment(0),
        portWwnAssignment(1),
        nodeWwnAssignment(2)
    }

CfprFeatureSupportabilityType ::= TEXTUAL-CONVENTION
    STATUS        current
    DESCRIPTION
        ""
    SYNTAX        INTEGER
    {
        supported(0),
        notSupported(1),
        deprecated(2)
    }

CfprFirmwareAdminState ::= TEXTUAL-CONVENTION
    STATUS        current
    DESCRIPTION
        ""
    SYNTAX        INTEGER
    {
        active(0),
        deleted(1)
    }

CfprFirmwareAutoSyncConfigIssue ::= TEXTUAL-CONVENTION
    STATUS        current
    DESCRIPTION
        ""
    SYNTAX        INTEGER
    {
        noIssues(0),
        defaultPackageMissing(1),
        versionsEmptyInDefaultPackage(2)
    }

CfprFirmwareAutoSyncState ::= TEXTUAL-CONVENTION
    STATUS        current
    DESCRIPTION
        ""
    SYNTAX        INTEGER
    {
        autoAcknowledge(0),
        userAcknowledge(1),
        noActions(2)
    }

CfprFirmwareBootUnitImage ::= TEXTUAL-CONVENTION
    STATUS        current
    DESCRIPTION
        ""
    SYNTAX        INTEGER
    {
        running(0),
        backup(1)
    }

CfprFirmwareBootUnitMode ::= TEXTUAL-CONVENTION
    STATUS        current
    DESCRIPTION
        ""
    SYNTAX        INTEGER
    {
        install(0),
        upgrade(1)
    }

CfprFirmwareCatalogPackConfigState ::= TEXTUAL-CONVENTION
    STATUS        current
    DESCRIPTION
        ""
    SYNTAX        INTEGER
    {
        ok(0),
        notApplied(1),
        failed(2)
    }

CfprFirmwareCompleteness ::= TEXTUAL-CONVENTION
    STATUS        current
    DESCRIPTION
        ""
    SYNTAX        INTEGER
    {
        partial(0),
        complete(1)
    }

CfprFirmwareComponentType ::= TEXTUAL-CONVENTION
    STATUS        current
    DESCRIPTION
        ""
    SYNTAX        BITS
    {
        kernel(0),
        system(1),
        combined(2),
        bootLoader(3)
    }

CfprFirmwareDependencyRelationship ::= TEXTUAL-CONVENTION
    STATUS        current
    DESCRIPTION
        ""
    SYNTAX        INTEGER
    {
        special(0),
        ancestor(1),
        descendent(2)
    }

CfprFirmwareDependencyScope ::= TEXTUAL-CONVENTION
    STATUS        current
    DESCRIPTION
        ""
    SYNTAX        INTEGER
    {
        unknown(0),
        blade(1),
        chassis(2),
        system(4),
        switch(8),
        global(16)
    }

CfprFirmwareDependencySensitivity ::= TEXTUAL-CONVENTION
    STATUS        current
    DESCRIPTION
        ""
    SYNTAX        INTEGER
    {
        global(0),
        fabric(1),
        path(2)
    }

CfprFirmwareDeployment ::= TEXTUAL-CONVENTION
    STATUS        current
    DESCRIPTION
        ""
    SYNTAX        INTEGER
    {
        unspecified(0)
    }

CfprFirmwareDistributableFsmCurrentFsm ::= TEXTUAL-CONVENTION
    STATUS        current
    DESCRIPTION
        ""
    SYNTAX        INTEGER
    {
        nop(0),
        delete(594)
    }

CfprFirmwareDistributableFsmStageName ::= TEXTUAL-CONVENTION
    STATUS        current
    DESCRIPTION
        ""
    SYNTAX        INTEGER
    {
        nop(0),
        deleteBegin(594),
        deleteLocal(595),
        deleteRemote(596),
        deleteFail(597),
        deleteSuccess(598)
    }

CfprFirmwareDistributableFsmTaskItem ::= TEXTUAL-CONVENTION
    STATUS        current
    DESCRIPTION
        ""
    SYNTAX        INTEGER
    {
        nop(0),
        delete(594)
    }

CfprFirmwareDistributableType ::= TEXTUAL-CONVENTION
    STATUS        current
    DESCRIPTION
        ""
    SYNTAX        INTEGER
    {
        unknown(0),
        image(1),
        fullBundle(2),
        infrastructureBundle(3),
        bSeriesBundle(4),
        cSeriesBundle(5),
        catalog(6),
        platformBundle(7),
        firmwareFpr9kBundle(8),
        firmwareFpr4kBundle(9)
    }

CfprFirmwareDownloadActivity ::= TEXTUAL-CONVENTION
    STATUS        current
    DESCRIPTION
        ""
    SYNTAX        INTEGER
    {
        restart(0),
        idle(1)
    }

CfprFirmwareDownloaderFsmCurrentFsm ::= TEXTUAL-CONVENTION
    STATUS        current
    DESCRIPTION
        ""
    SYNTAX        INTEGER
    {
        nop(0),
        download(233)
    }

CfprFirmwareDownloaderFsmStageName ::= TEXTUAL-CONVENTION
    STATUS        current
    DESCRIPTION
        ""
    SYNTAX        INTEGER
    {
        nop(0),
        downloadBegin(233),
        downloadLocal(234),
        downloadUnpackLocal(235),
        downloadCopyRemote(236),
        downloadDeleteLocal(239),
        downloadFail(394),
        downloadSuccess(395)
    }

CfprFirmwareDownloaderFsmTaskItem ::= TEXTUAL-CONVENTION
    STATUS        current
    DESCRIPTION
        ""
    SYNTAX        INTEGER
    {
        nop(0),
        download(233)
    }

CfprFirmwareEquipmentType ::= TEXTUAL-CONVENTION
    STATUS        current
    DESCRIPTION
        ""
    SYNTAX        INTEGER
    {
        unknown(0),
        system(1),
        switch(2),
        iocard(3),
        server(4),
        cimc(5),
        adaptor(6),
        storageController(7),
        boardController(8),
        bios(9),
        serviceProfile(10),
        graphicsCard(11)
    }

CfprFirmwareFirmwareState ::= TEXTUAL-CONVENTION
    STATUS        current
    DESCRIPTION
        ""
    SYNTAX        BITS
    {
        cimcFirmwareMismatch(0),
        pldFirmwareMismatch(1)
    }

CfprFirmwareFwState ::= TEXTUAL-CONVENTION
    STATUS        current
    DESCRIPTION
        ""
    SYNTAX        INTEGER
    {
        unknown(0),
        sameRelease(1),
        compatible(2),
        incompatible(3),
        multipleReleases(4)
    }

CfprFirmwareFwUpgradeState ::= TEXTUAL-CONVENTION
    STATUS        current
    DESCRIPTION
        ""
    SYNTAX        INTEGER
    {
        ready(0),
        inProgress(1),
        upgrading(2),
        updatingImageVersion(3),
        updatingPackageVersion(4),
        failed(5),
        failedUpgrade(6)
    }

CfprFirmwareHostPackConfigQualifier ::= TEXTUAL-CONVENTION
    STATUS        current
    DESCRIPTION
        ""
    SYNTAX        BITS
    {
        biosImageNotSelected(0)
    }

CfprFirmwareImageDeleted ::= TEXTUAL-CONVENTION
    STATUS        current
    DESCRIPTION
        ""
    SYNTAX        BITS
    {
        a(0),
        b(1)
    }

CfprFirmwareImageError ::= TEXTUAL-CONVENTION
    STATUS        current
    DESCRIPTION
        ""
    SYNTAX        INTEGER
    {
        none(0),
        checksumFailure(1),
        filesystemError(2),
        mgmtConnectError(3),
        bootConfMissing(4),
        crcFailure(5),
        unknownError(6),
        rebuilding(7)
    }

CfprFirmwareImageFsmCurrentFsm ::= TEXTUAL-CONVENTION
    STATUS        current
    DESCRIPTION
        ""
    SYNTAX        INTEGER
    {
        nop(0),
        delete(240)
    }

CfprFirmwareImageFsmStageName ::= TEXTUAL-CONVENTION
    STATUS        current
    DESCRIPTION
        ""
    SYNTAX        INTEGER
    {
        nop(0),
        deleteBegin(240),
        deleteLocal(241),
        deleteRemote(242),
        deleteFail(396),
        deleteSuccess(397)
    }

CfprFirmwareImageFsmTaskItem ::= TEXTUAL-CONVENTION
    STATUS        current
    DESCRIPTION
        ""
    SYNTAX        INTEGER
    {
        nop(0),
        delete(240)
    }

CfprFirmwareImagePresence ::= TEXTUAL-CONVENTION
    STATUS        current
    DESCRIPTION
        ""
    SYNTAX        BITS
    {
        a(0),
        b(1)
    }

CfprFirmwareImageState ::= TEXTUAL-CONVENTION
    STATUS        current
    DESCRIPTION
        ""
    SYNTAX        INTEGER
    {
        ready(0),
        scheduled(1),
        updating(2),
        activating(3),
        failed(4),
        setStartup(5),
        rebooting(6),
        pendingNextBoot(7),
        throttled(8),
        upgrading(9),
        autoUpdating(10),
        autoActivating(11),
        pendingPowerCycle(12),
        badImage(13),
        rebuilding(14)
    }

CfprFirmwareImageValidationStateType ::= TEXTUAL-CONVENTION
    STATUS        current
    DESCRIPTION
        ""
    SYNTAX        INTEGER
    {
        none(0),
        inProgress(1),
        completed(2),
        failed(3),
        queued(4)
    }

CfprFirmwareImageValidationType ::= TEXTUAL-CONVENTION
    STATUS        current
    DESCRIPTION
        ""
    SYNTAX        INTEGER
    {
        none(0),
        ok(1),
        okNotAvailable(2),
        failedSignatureCheck(3),
        failedIntegrityCheck(4),
        failedPresenceCheck(5),
        failedChecksumCheck(6),
        failedDiskSpaceIssue(7),
        failed(8)
    }

CfprFirmwareImpactType ::= TEXTUAL-CONVENTION
    STATUS        current
    DESCRIPTION
        ""
    SYNTAX        INTEGER
    {
        activate(0),
        noimpact(1),
        reset(2),
        update(3)
    }

CfprFirmwareInstallState ::= TEXTUAL-CONVENTION
    STATUS        current
    DESCRIPTION
        ""
    SYNTAX        INTEGER
    {
        ready(0),
        scheduled(1),
        inProgress(2),
        failed(3),
        pendingUserAck(4),
        startPendingExtPermission(5)
    }

CfprFirmwareItemType ::= TEXTUAL-CONVENTION
    STATUS        current
    DESCRIPTION
        ""
    SYNTAX        INTEGER
    {
        unspecified(0),
        switchKernel(1),
        switchSoftware(2),
        system(3),
        bladeController(4),
        iocard(5),
        bladeBios(6),
        adaptor(7),
        storageController(8),
        hostNic(9),
        hostHba(10),
        hostHbaOptionrom(11),
        hostNicOptionrom(12),
        boardController(13),
        localDisk(14),
        flexflashController(20),
        bladeSspOsController(22),
        graphicsCard(25),
        adaptorBoot(29)
    }

CfprFirmwarePackMode ::= TEXTUAL-CONVENTION
    STATUS        current
    DESCRIPTION
        ""
    SYNTAX        INTEGER
    {
        staged(0),
        oneShot(1)
    }

CfprFirmwarePackItemPresence ::= TEXTUAL-CONVENTION
    STATUS        current
    DESCRIPTION
        ""
    SYNTAX        INTEGER
    {
        unknown(0),
        missing(1),
        present(2)
    }

CfprFirmwarePlatformPackFsmCurrentFsm ::= TEXTUAL-CONVENTION
    STATUS        current
    DESCRIPTION
        ""
    SYNTAX        INTEGER
    {
        nop(0),
        platformVersion(1720)
    }

CfprFirmwarePlatformPackFsmStageName ::= TEXTUAL-CONVENTION
    STATUS        current
    DESCRIPTION
        ""
    SYNTAX        INTEGER
    {
        nop(0),
        platformVersionBegin(1720),
        platformVersionWaitForReady(1721),
        platformVersionRestore(1722),
        platformVersionFail(1786),
        platformVersionSuccess(1787)
    }

CfprFirmwarePlatformPackFsmTaskFlags ::= TEXTUAL-CONVENTION
    STATUS        current
    DESCRIPTION
        ""
    SYNTAX        BITS
    {
        samDmeFirmwarePlatformPackPlatformVersionInitRestore(20)
    }

CfprFirmwarePlatformPackFsmTaskItem ::= TEXTUAL-CONVENTION
    STATUS        current
    DESCRIPTION
        ""
    SYNTAX        INTEGER
    {
        nop(0),
        platformVersion(1720)
    }

CfprFirmwarePlatformType ::= TEXTUAL-CONVENTION
    STATUS        current
    DESCRIPTION
        ""
    SYNTAX        INTEGER
    {
        fpr(0),
        fprMini(1),
        sspBakerstreet(2)
    }

CfprFirmwareRunningDeployment ::= TEXTUAL-CONVENTION
    STATUS        current
    DESCRIPTION
        ""
    SYNTAX        INTEGER
    {
        unspecified(0),
        kernel(1),
        bootLoader(2),
        system(3)
    }

CfprFirmwareSupFirmwareFsmCurrentFsm ::= TEXTUAL-CONVENTION
    STATUS        current
    DESCRIPTION
        ""
    SYNTAX        INTEGER
    {
        nop(0),
        deploy(1865)
    }

CfprFirmwareSupFirmwareFsmStageName ::= TEXTUAL-CONVENTION
    STATUS        current
    DESCRIPTION
        ""
    SYNTAX        INTEGER
    {
        nop(0),
        deployBegin(1865),
        deployWaitForDeploy(1866),
        deployValidateFirmwarePack(1867),
        deployDebundlePort(1868),
        deployPollDebundlePort(1869),
        deployActivateFirmwarePack(1870),
        deployPollActivateOfFirmwarePack(1871),
        deployUpdateImageVersion(1872),
        deployWaitForFirmwareVersionUpdate(1873),
        deployUpdatePackageVersion(1874),
        deployCompleteFirmwareUpgrade(1875),
        deployFail(1878),
        deploySuccess(1879),
        deployCheckUpgradeStatus(1930),
        deployResetChassis(2052)
    }

CfprFirmwareSupFirmwareFsmTaskFlags ::= TEXTUAL-CONVENTION
    STATUS        current
    DESCRIPTION
        ""
    SYNTAX        BITS
    {
        samDmeFirmwareSupFirmwareDeployApplySupfw(24)
    }

CfprFirmwareSupFirmwareFsmTaskItem ::= TEXTUAL-CONVENTION
    STATUS        current
    DESCRIPTION
        ""
    SYNTAX        INTEGER
    {
        nop(0),
        deploy(1865)
    }

CfprFirmwareSupportedModeType ::= TEXTUAL-CONVENTION
    STATUS        current
    DESCRIPTION
        ""
    SYNTAX        INTEGER
    {
        restricted(0),
        limited(1),
        all(2)
    }

CfprFirmwareSystemFsmCurrentFsm ::= TEXTUAL-CONVENTION
    STATUS        current
    DESCRIPTION
        ""
    SYNTAX        INTEGER
    {
        nop(0),
        deploy(1308),
        applyCatalogPack(1324)
    }

CfprFirmwareSystemFsmStageName ::= TEXTUAL-CONVENTION
    STATUS        current
    DESCRIPTION
        ""
    SYNTAX        INTEGER
    {
        nop(0),
        deployBegin(1308),
        deployWaitForDeploy(1309),
        deployResolveDistributableNames(1310),
        deployResolveDistributable(1311),
        deployResolveImages(1312),
        deployActivateFPRM(1313),
        deployPollActivateOfFPRM(1314),
        deployUpdateIOM(1315),
        deployPollUpdateOfIOM(1316),
        deployActivateIOM(1317),
        deployPollActivateOfIOM(1318),
        deployActivateRemoteFI(1319),
        deployPollActivateOfRemoteFI(1320),
        deployWaitForUserAck(1321),
        deployActivateLocalFI(1322),
        deployPollActivateOfLocalFI(1323),
        applyCatalogPackBegin(1324),
        applyCatalogPackResolveDistributableNames(1325),
        applyCatalogPackResolveDistributable(1326),
        applyCatalogPackResolveImages(1327),
        applyCatalogPackActivateCatalog(1328),
        applyCatalogPackFail(1404),
        applyCatalogPackSuccess(1405),
        deployFail(1406),
        deploySuccess(1407),
        deployDebundlePort(1861),
        deployPollDebundlePort(1862),
        deployActivateMgmtExt(1863),
        deployPollActivateOfMgmtExt(1864),
        deployValidatePlatformPack(1973)
    }

CfprFirmwareSystemFsmTaskFlags ::= TEXTUAL-CONVENTION
    STATUS        current
    DESCRIPTION
        ""
    SYNTAX        BITS
    {
        samDmeFirmwareSystemDeployApplyInfra(5)
    }

CfprFirmwareSystemFsmTaskItem ::= TEXTUAL-CONVENTION
    STATUS        current
    DESCRIPTION
        ""
    SYNTAX        INTEGER
    {
        nop(0),
        deploy(1308),
        applyCatalogPack(1324)
    }

CfprFirmwareTransferState ::= TEXTUAL-CONVENTION
    STATUS        current
    DESCRIPTION
        ""
    SYNTAX        INTEGER
    {
        init(0),
        downloading(1),
        downloaded(2),
        failed(3)
    }

CfprFirmwareTransport ::= TEXTUAL-CONVENTION
    STATUS        current
    DESCRIPTION
        ""
    SYNTAX        INTEGER
    {
        ftp(0),
        tftp(1),
        scp(2),
        sftp(3),
        local(4),
        usbA(5),
        usbB(6),
        https(11),
        http(12)
    }

CfprFirmwareTriggerState ::= TEXTUAL-CONVENTION
    STATUS        current
    DESCRIPTION
        ""
    SYNTAX        INTEGER
    {
        triggered(0),
        trigger(1)
    }

CfprFirmwareType ::= TEXTUAL-CONVENTION
    STATUS        current
    DESCRIPTION
        ""
    SYNTAX        INTEGER
    {
        unspecified(0),
        switchKernel(1),
        switchSoftware(2),
        system(3),
        bladeController(4),
        iocard(5),
        fex(6),
        adaptor(7),
        storageController(8),
        hostNic(9),
        hostHba(10),
        hostHbaOptionrom(11),
        hostNicOptionrom(12),
        boardController(13),
        localDisk(14),
        diag(15),
        catalog(16),
        mgmtExt(17),
        debugPlugIn(18),
        switch(19),
        flexflashController(20),
        bladeSspOsController(22),
        fxosCspCompatibility(23),
        fprRommon(24),
        graphicsCard(25),
        fprNmFpga(26),
        adaptorBoot(29)
    }

CfprFirmwareUpdatableDeployment ::= TEXTUAL-CONVENTION
    STATUS        current
    DESCRIPTION
        ""
    SYNTAX        INTEGER
    {
        unspecified(0),
        backup(4)
    }

CfprFirmwareUpgradeCategory ::= TEXTUAL-CONVENTION
    STATUS        current
    DESCRIPTION
        ""
    SYNTAX        INTEGER
    {
        other(0),
        dataLoad(1),
        catalog(2),
        config(3),
        serverReboot(4),
        faults(5)
    }

CfprFirmwareUpgradeSeverity ::= TEXTUAL-CONVENTION
    STATUS        current
    DESCRIPTION
        ""
    SYNTAX        INTEGER
    {
        unknown(0),
        fatal(1),
        error(2),
        warn(3),
        info(4)
    }

CfprFirmwareUpgradeStatus ::= TEXTUAL-CONVENTION
    STATUS        current
    DESCRIPTION
        ""
    SYNTAX        INTEGER
    {
        unknown(0),
        inProgress(1),
        failed(2),
        success(3),
        warnings(4),
        skipped(5)
    }

CfprFirmwareValidationStatusFsmCurrentFsm ::= TEXTUAL-CONVENTION
    STATUS        current
    DESCRIPTION
        ""
    SYNTAX        INTEGER
    {
        nop(0),
        validate(1926)
    }

CfprFirmwareValidationStatusFsmStageName ::= TEXTUAL-CONVENTION
    STATUS        current
    DESCRIPTION
        ""
    SYNTAX        INTEGER
    {
        nop(0),
        validateBegin(1926),
        validateCheckReadiness(1927),
        validatePlatformPack(1928),
        validateComplete(1929),
        validateFail(1933),
        validateSuccess(1934)
    }

CfprFirmwareValidationStatusFsmTaskFlags ::= TEXTUAL-CONVENTION
    STATUS        current
    DESCRIPTION
        ""
    SYNTAX        BITS
    {
        samDmeFirmwareValidationStatusValidateApplyInfra(28)
    }

CfprFirmwareValidationStatusFsmTaskItem ::= TEXTUAL-CONVENTION
    STATUS        current
    DESCRIPTION
        ""
    SYNTAX        INTEGER
    {
        nop(0),
        validate(1926)
    }

CfprFirmwareVerifyPackStatus ::= TEXTUAL-CONVENTION
    STATUS        current
    DESCRIPTION
        ""
    SYNTAX        INTEGER
    {
        none(0),
        preparing(1),
        inProgress(2),
        failed(3),
        success(4),
        warnings(5),
        skipped(6)
    }

CfprFlowctrlFlowControl ::= TEXTUAL-CONVENTION
    STATUS        current
    DESCRIPTION
        ""
    SYNTAX        INTEGER
    {
        off(0),
        on(1)
    }

CfprFlowctrlFlowControlRx ::= TEXTUAL-CONVENTION
    STATUS        current
    DESCRIPTION
        ""
    SYNTAX        INTEGER
    {
        off(0)
    }

CfprFlowctrlFlowControlTx ::= TEXTUAL-CONVENTION
    STATUS        current
    DESCRIPTION
        ""
    SYNTAX        INTEGER
    {
        off(0),
        on(1)
    }

CfprFlowctrlPriorityPause ::= TEXTUAL-CONVENTION
    STATUS        current
    DESCRIPTION
        ""
    SYNTAX        INTEGER
    {
        auto(0),
        on(1)
    }

CfprFsmCompletion ::= TEXTUAL-CONVENTION
    STATUS        current
    DESCRIPTION
        ""
    SYNTAX        INTEGER
    {
        scheduled(0),
        processing(1),
        completed(2),
        cancelled(3)
    }

CfprFsmFlags ::= TEXTUAL-CONVENTION
    STATUS        current
    DESCRIPTION
        ""
    SYNTAX        BITS
    {
        unused(1)
    }

CfprFsmFsmStageStatus ::= TEXTUAL-CONVENTION
    STATUS        current
    DESCRIPTION
        ""
    SYNTAX        INTEGER
    {
        fail(0),
        success(1),
        skip(2),
        pending(3),
        inProgress(4),
        throttled(5),
        nop(255)
    }

CfprFsmLifecycle ::= TEXTUAL-CONVENTION
    STATUS        current
    DESCRIPTION
        ""
    SYNTAX        INTEGER
    {
        available(0),
        allocated(1),
        deallocated(2),
        repurposed(3)
    }

CfprGmetaCategory ::= TEXTUAL-CONVENTION
    STATUS        current
    DESCRIPTION
        ""
    SYNTAX        INTEGER
    {
        unknown(0),
        inventory(1)
    }

CfprGmetaHolderFsmCurrentFsm ::= TEXTUAL-CONVENTION
    STATUS        current
    DESCRIPTION
        ""
    SYNTAX        INTEGER
    {
        nop(0),
        inventory(1474)
    }

CfprGmetaHolderFsmStageName ::= TEXTUAL-CONVENTION
    STATUS        current
    DESCRIPTION
        ""
    SYNTAX        INTEGER
    {
        nop(0),
        inventoryBegin(1474),
        inventoryCheckInventoryStatus(1475),
        inventoryReportFullInventory(1476),
        inventoryFail(1487),
        inventorySuccess(1488)
    }

CfprGmetaHolderFsmTaskFlags ::= TEXTUAL-CONVENTION
    STATUS        current
    DESCRIPTION
        ""
    SYNTAX        BITS
    {
        samDmeGmetaHolderInventoryRegister(12)
    }

CfprGmetaHolderFsmTaskItem ::= TEXTUAL-CONVENTION
    STATUS        current
    DESCRIPTION
        ""
    SYNTAX        INTEGER
    {
        nop(0),
        inventory(1474)
    }

CfprGmetaInventoryStatus ::= TEXTUAL-CONVENTION
    STATUS        current
    DESCRIPTION
        ""
    SYNTAX        INTEGER
    {
        invDisable(0),
        invEnable(1),
        invStop(2),
        invThrottled(3)
    }

CfprGmetaPollInterval ::= TEXTUAL-CONVENTION
    STATUS        current
    DESCRIPTION
        ""
    SYNTAX        INTEGER
    {
        never(0),
        n1min(1),
        n2min(2),
        n5min(5),
        n10min(10),
        n15min(15),
        n30min(30)
    }

CfprHostagAction ::= TEXTUAL-CONVENTION
    STATUS        current
    DESCRIPTION
        ""
    SYNTAX        INTEGER
    {
        none(0)
    }

CfprHostagAgentType ::= TEXTUAL-CONVENTION
    STATUS        current
    DESCRIPTION
        ""
    SYNTAX        INTEGER
    {
        indeterminate(0),
        pnuosAgent(1),
        hostAgent(2)
    }

CfprHostagEvent ::= TEXTUAL-CONVENTION
    STATUS        current
    DESCRIPTION
        ""
    SYNTAX        INTEGER
    {
        none(0)
    }

CfprHostimgComposition ::= TEXTUAL-CONVENTION
    STATUS        current
    DESCRIPTION
        ""
    SYNTAX        INTEGER
    {
        complete(0),
        componentized(1)
    }

CfprHostimgDistribution ::= TEXTUAL-CONVENTION
    STATUS        current
    DESCRIPTION
        ""
    SYNTAX        INTEGER
    {
        unknown(0),
        fedora(1)
    }

CfprHostimgImgType ::= TEXTUAL-CONVENTION
    STATUS        current
    DESCRIPTION
        ""
    SYNTAX        INTEGER
    {
        unknown(0),
        esxi(1),
        kvm(2),
        xen(3),
        linux(4),
        windows(5),
        gpxeScript(6)
    }

CfprHostimgType ::= TEXTUAL-CONVENTION
    STATUS        current
    DESCRIPTION
        ""
    SYNTAX        INTEGER
    {
        complete(0),
        kernel(1),
        fileSystem(2),
        module(3),
        gpxeScript(4)
    }

CfprIdentConsType ::= TEXTUAL-CONVENTION
    STATUS        current
    DESCRIPTION
        ""
    SYNTAX        INTEGER
    {
        vnic(1),
        vhba(2),
        server(3),
        chassis(4),
        vm(5),
        vmnic(6)
    }

CfprIdentIdDefinedInIdm ::= TEXTUAL-CONVENTION
    STATUS        current
    DESCRIPTION
        ""
    SYNTAX        INTEGER
    {
        no(0),
        yes(1)
    }

CfprIdentIdentReqIntent ::= TEXTUAL-CONVENTION
    STATUS        current
    DESCRIPTION
        ""
    SYNTAX        INTEGER
    {
        requisition(1),
        assign(2),
        unassign(3),
        addPooled(4),
        deletePooled(5),
        checkDuplicateId(6)
    }

CfprIdentIdentRequestFsmCurrentFsm ::= TEXTUAL-CONVENTION
    STATUS        current
    DESCRIPTION
        ""
    SYNTAX        INTEGER
    {
        nop(0),
        updateIdent(1184)
    }

CfprIdentIdentRequestFsmStageName ::= TEXTUAL-CONVENTION
    STATUS        current
    DESCRIPTION
        ""
    SYNTAX        INTEGER
    {
        nop(0),
        updateIdentBegin(1184),
        updateIdentExecute(1185),
        updateIdentFail(1408),
        updateIdentSuccess(1409)
    }

CfprIdentIdentRequestFsmTaskItem ::= TEXTUAL-CONVENTION
    STATUS        current
    DESCRIPTION
        ""
    SYNTAX        INTEGER
    {
        nop(0),
        updateIdent(1184)
    }

CfprIdentIdentType ::= TEXTUAL-CONVENTION
    STATUS        current
    DESCRIPTION
        ""
    SYNTAX        INTEGER
    {
        mac(1),
        wwnn(2),
        wwpn(3),
        uuid(4),
        vlan(5),
        ipV4(6),
        ipV6(7),
        iqn(8)
    }

CfprIdentMetaSystemFsmCurrentFsm ::= TEXTUAL-CONVENTION
    STATUS        current
    DESCRIPTION
        ""
    SYNTAX        INTEGER
    {
        nop(0),
        sync(1186),
        fprcUnivSync(1667)
    }

CfprIdentMetaSystemFsmStageName ::= TEXTUAL-CONVENTION
    STATUS        current
    DESCRIPTION
        ""
    SYNTAX        INTEGER
    {
        nop(0),
        syncBegin(1186),
        syncPing(1187),
        syncExecute(1188),
        syncFail(1410),
        syncSuccess(1411),
        fprcUnivSyncBegin(1667),
        fprcUnivSyncExecute(1668),
        fprcUnivSyncFail(1678),
        fprcUnivSyncSuccess(1679)
    }

CfprIdentMetaSystemFsmTaskItem ::= TEXTUAL-CONVENTION
    STATUS        current
    DESCRIPTION
        ""
    SYNTAX        INTEGER
    {
        nop(0),
        sync(1186),
        fprcUnivSync(1667)
    }

CfprIdentRetStatus ::= TEXTUAL-CONVENTION
    STATUS        current
    DESCRIPTION
        ""
    SYNTAX        INTEGER
    {
        succeeded(1),
        assignedByOther(2),
        outOfSync(3),
        failed(4),
        synced(5)
    }

CfprImgsecKeyType ::= TEXTUAL-CONVENTION
    STATUS        current
    DESCRIPTION
        ""
    SYNTAX        INTEGER
    {
        public(0),
        private(1),
        shared(2)
    }

CfprInitiatorFcInitiatorEpProt ::= TEXTUAL-CONVENTION
    STATUS        current
    DESCRIPTION
        ""
    SYNTAX        INTEGER
    {
        derived(0),
        fc(1),
        iscsi(2)
    }

CfprInitiatorGroupType ::= TEXTUAL-CONVENTION
    STATUS        current
    DESCRIPTION
        ""
    SYNTAX        INTEGER
    {
        dedicated(1),
        shared(2),
        policy(3)
    }

CfprInitiatorIScsiInitiatorEpProt ::= TEXTUAL-CONVENTION
    STATUS        current
    DESCRIPTION
        ""
    SYNTAX        INTEGER
    {
        derived(0),
        fc(1),
        iscsi(2)
    }

CfprInitiatorInitiatorEpPref ::= TEXTUAL-CONVENTION
    STATUS        current
    DESCRIPTION
        ""
    SYNTAX        INTEGER
    {
        preferred(0),
        alternate(1)
    }

CfprIpIPv4DnsPref ::= TEXTUAL-CONVENTION
    STATUS        current
    DESCRIPTION
        ""
    SYNTAX        INTEGER
    {
        preferred(0),
        alternate(1)
    }

CfprIpIpV4StaticAddrPref ::= TEXTUAL-CONVENTION
    STATUS        current
    DESCRIPTION
        ""
    SYNTAX        INTEGER
    {
        preferred(0),
        alternate(1)
    }

CfprIpProtocol ::= TEXTUAL-CONVENTION
    STATUS        current
    DESCRIPTION
        ""
    SYNTAX        INTEGER
    {
        tcp(1),
        udp(2)
    }

CfprIpServiceIfPref ::= TEXTUAL-CONVENTION
    STATUS        current
    DESCRIPTION
        ""
    SYNTAX        INTEGER
    {
        preferred(0),
        alternate(1)
    }

CfprIppoolDHCPMode ::= TEXTUAL-CONVENTION
    STATUS        current
    DESCRIPTION
        ""
    SYNTAX        INTEGER
    {
        disabled(0),
        enabled(1)
    }

CfprIppoolManagementMode ::= TEXTUAL-CONVENTION
    STATUS        current
    DESCRIPTION
        ""
    SYNTAX        INTEGER
    {
        internal(0),
        external(1)
    }

CfprIppoolNetBIOSMode ::= TEXTUAL-CONVENTION
    STATUS        current
    DESCRIPTION
        ""
    SYNTAX        INTEGER
    {
        disabled(0),
        enabled(1)
    }

CfprIppoolPoolAssignmentOrder ::= TEXTUAL-CONVENTION
    STATUS        current
    DESCRIPTION
        ""
    SYNTAX        INTEGER
    {
        default(0),
        sequential(1)
    }

CfprIpsecAuthType ::= TEXTUAL-CONVENTION
    STATUS        current
    DESCRIPTION
        ""
    SYNTAX        INTEGER
    {
        pubkey(0)
    }

CfprIpsecCommand ::= TEXTUAL-CONVENTION
    STATUS        current
    DESCRIPTION
        ""
    SYNTAX        INTEGER
    {
        ready(0),
        reload(1),
        updateStats(2),
        clearLog(3)
    }

CfprIpsecConfigState ::= TEXTUAL-CONVENTION
    STATUS        current
    DESCRIPTION
        ""
    SYNTAX        INTEGER
    {
        ok(0),
        disabled(1),
        invalidKeyr(2),
        invalidTp(3),
        invalidCert(4)
    }

CfprIpsecConnState ::= TEXTUAL-CONVENTION
    STATUS        current
    DESCRIPTION
        ""
    SYNTAX        INTEGER
    {
        disabled(0),
        enabled(1)
    }

CfprIpsecEpFsmCurrentFsm ::= TEXTUAL-CONVENTION
    STATUS        current
    DESCRIPTION
        ""
    SYNTAX        INTEGER
    {
        nop(0),
        updateEp(1842)
    }

CfprIpsecEpFsmStageName ::= TEXTUAL-CONVENTION
    STATUS        current
    DESCRIPTION
        ""
    SYNTAX        INTEGER
    {
        nop(0),
        updateEpBegin(1842),
        updateEpApplyConfig(1843),
        updateEpFail(1880),
        updateEpSuccess(1881)
    }

CfprIpsecEpFsmTaskItem ::= TEXTUAL-CONVENTION
    STATUS        current
    DESCRIPTION
        ""
    SYNTAX        INTEGER
    {
        nop(0),
        updateEp(1842)
    }

CfprIpsecEspMode ::= TEXTUAL-CONVENTION
    STATUS        current
    DESCRIPTION
        ""
    SYNTAX        INTEGER
    {
        transport(0),
        tunnel(1)
    }

CfprIpsecFqdnEnforceType ::= TEXTUAL-CONVENTION
    STATUS        current
    DESCRIPTION
        ""
    SYNTAX        INTEGER
    {
        notSet(0),
        none(1),
        remoteIkeId(2)
    }

CfprIpsecRevokePolicy ::= TEXTUAL-CONVENTION
    STATUS        current
    DESCRIPTION
        ""
    SYNTAX        INTEGER
    {
        relaxed(0),
        strict(1)
    }

CfprIpsecStatsType ::= TEXTUAL-CONVENTION
    STATUS        current
    DESCRIPTION
        ""
    SYNTAX        INTEGER
    {
        status(1),
        listconn(2),
        listsa(3),
        listauthor(4),
        listcert(5)
    }

CfprIqnpoolBlockFrom ::= TEXTUAL-CONVENTION
    STATUS        current
    DESCRIPTION
        ""
    SYNTAX        Gauge32 (0..65535)

CfprIqnpoolBlockTo ::= TEXTUAL-CONVENTION
    STATUS        current
    DESCRIPTION
        ""
    SYNTAX        Gauge32 (0..65535)

CfprIqnpoolPoolAssignmentOrder ::= TEXTUAL-CONVENTION
    STATUS        current
    DESCRIPTION
        ""
    SYNTAX        INTEGER
    {
        default(0),
        sequential(1)
    }

CfprIqnpoolTransportBlockFrom ::= TEXTUAL-CONVENTION
    STATUS        current
    DESCRIPTION
        ""
    SYNTAX        Gauge32 (0..65535)

CfprIqnpoolTransportBlockTo ::= TEXTUAL-CONVENTION
    STATUS        current
    DESCRIPTION
        ""
    SYNTAX        Gauge32 (0..65535)

CfprLicenseConfigOperation ::= TEXTUAL-CONVENTION
    STATUS        current
    DESCRIPTION
        ""
    SYNTAX        INTEGER
    {
        register(0),
        unregister(1),
        setdebug(2),
        cleardebug(3),
        renew(4),
        expireauth(5),
        expireeval(6),
        cadev(7),
        caprod(8),
        enableResv(9),
        disableResv(10),
        request(11),
        install(12),
        return(13),
        cancel(14),
        expireResv(15),
        expireidcert(16),
        enableHostInfoTx(17),
        disableHostInfoTx(18),
        sseGetKey(19),
        changehostname(20)
    }

CfprLicenseDebugFlag ::= TEXTUAL-CONVENTION
    STATUS        current
    DESCRIPTION
        ""
    SYNTAX        INTEGER
    {
        error(0),
        debug(1),
        trace(2),
        all(3)
    }

CfprLicenseDownloadActivity ::= TEXTUAL-CONVENTION
    STATUS        current
    DESCRIPTION
        ""
    SYNTAX        INTEGER
    {
        restart(0),
        idle(1)
    }

CfprLicenseDownloaderFsmCurrentFsm ::= TEXTUAL-CONVENTION
    STATUS        current
    DESCRIPTION
        ""
    SYNTAX        INTEGER
    {
        nop(0),
        download(916)
    }

CfprLicenseDownloaderFsmStageName ::= TEXTUAL-CONVENTION
    STATUS        current
    DESCRIPTION
        ""
    SYNTAX        INTEGER
    {
        nop(0),
        downloadBegin(916),
        downloadLocal(917),
        downloadValidateLocal(918),
        downloadCopyRemote(919),
        downloadDeleteLocal(920),
        downloadValidateRemote(921),
        downloadDeleteRemote(922),
        downloadFail(994),
        downloadSuccess(995)
    }

CfprLicenseDownloaderFsmTaskItem ::= TEXTUAL-CONVENTION
    STATUS        current
    DESCRIPTION
        ""
    SYNTAX        INTEGER
    {
        nop(0),
        download(916)
    }

CfprLicenseFeatureType ::= TEXTUAL-CONVENTION
    STATUS        current
    DESCRIPTION
        ""
    SYNTAX        INTEGER
    {
        counted(0),
        boolean(1)
    }

CfprLicenseFileFsmCurrentFsm ::= TEXTUAL-CONVENTION
    STATUS        current
    DESCRIPTION
        ""
    SYNTAX        INTEGER
    {
        nop(0),
        install(923),
        clear(926)
    }

CfprLicenseFileFsmStageName ::= TEXTUAL-CONVENTION
    STATUS        current
    DESCRIPTION
        ""
    SYNTAX        INTEGER
    {
        nop(0),
        installBegin(923),
        installLocal(924),
        installRemote(925),
        clearBegin(926),
        clearLocal(927),
        clearRemote(928),
        clearFail(996),
        clearSuccess(997),
        installFail(998),
        installSuccess(999)
    }

CfprLicenseFileFsmTaskItem ::= TEXTUAL-CONVENTION
    STATUS        current
    DESCRIPTION
        ""
    SYNTAX        INTEGER
    {
        nop(0),
        install(923),
        clear(926)
    }

CfprLicenseFileState ::= TEXTUAL-CONVENTION
    STATUS        current
    DESCRIPTION
        ""
    SYNTAX        INTEGER
    {
        unknown(0),
        installPending(1),
        installing(2),
        stale(3),
        installed(4),
        installFailed(5),
        deletePending(6),
        deleting(7),
        deleted(8),
        deleteFailed(9),
        validated(10)
    }

CfprLicenseInstanceFsmCurrentFsm ::= TEXTUAL-CONVENTION
    STATUS        current
    DESCRIPTION
        ""
    SYNTAX        INTEGER
    {
        nop(0),
        updateFlexlm(929)
    }

CfprLicenseInstanceFsmStageName ::= TEXTUAL-CONVENTION
    STATUS        current
    DESCRIPTION
        ""
    SYNTAX        INTEGER
    {
        nop(0),
        updateFlexlmBegin(929),
        updateFlexlmLocal(930),
        updateFlexlmRemote(931),
        updateFlexlmFail(1000),
        updateFlexlmSuccess(1001)
    }

CfprLicenseInstanceFsmTaskItem ::= TEXTUAL-CONVENTION
    STATUS        current
    DESCRIPTION
        ""
    SYNTAX        INTEGER
    {
        nop(0),
        updateFlexlm(929)
    }

CfprLicensePeerStatus ::= TEXTUAL-CONVENTION
    STATUS        current
    DESCRIPTION
        ""
    SYNTAX        INTEGER
    {
        noPeer(0),
        unknown(1),
        lacks(2),
        exceeds(3),
        matching(4)
    }

CfprLicenseScope ::= TEXTUAL-CONVENTION
    STATUS        current
    DESCRIPTION
        ""
    SYNTAX        INTEGER
    {
        a(1),
        b(2),
        server(3),
        unknown(4)
    }

CfprLicenseSmartConfigFsmCurrentFsm ::= TEXTUAL-CONVENTION
    STATUS        current
    DESCRIPTION
        ""
    SYNTAX        INTEGER
    {
        nop(0),
        setConfig(1723)
    }

CfprLicenseSmartConfigFsmStageName ::= TEXTUAL-CONVENTION
    STATUS        current
    DESCRIPTION
        ""
    SYNTAX        INTEGER
    {
        nop(0),
        setConfigBegin(1723),
        setConfigLocal(1724),
        setConfigFail(1788),
        setConfigSuccess(1789)
    }

CfprLicenseSmartConfigFsmTaskItem ::= TEXTUAL-CONVENTION
    STATUS        current
    DESCRIPTION
        ""
    SYNTAX        INTEGER
    {
        nop(0),
        setConfig(1723)
    }

CfprLicenseState ::= TEXTUAL-CONVENTION
    STATUS        current
    DESCRIPTION
        ""
    SYNTAX        INTEGER
    {
        unknown(0),
        licenseOk(1),
        licenseInsufficient(2),
        licenseGraceperiod(3),
        licenseExpired(4),
        notApplicable(5)
    }

CfprLicenseTransferState ::= TEXTUAL-CONVENTION
    STATUS        current
    DESCRIPTION
        ""
    SYNTAX        INTEGER
    {
        init(0),
        downloading(1),
        downloaded(2),
        failed(3)
    }

CfprLicenseTransport ::= TEXTUAL-CONVENTION
    STATUS        current
    DESCRIPTION
        ""
    SYNTAX        INTEGER
    {
        ftp(0),
        tftp(1),
        scp(2),
        sftp(3),
        local(4)
    }

CfprLicenseType ::= TEXTUAL-CONVENTION
    STATUS        current
    DESCRIPTION
        ""
    SYNTAX        INTEGER
    {
        increment(0),
        upgrade(1),
        feature(2)
    }

CfprLicenseForceOption ::= TEXTUAL-CONVENTION
    STATUS        current
    DESCRIPTION
        ""
    SYNTAX        INTEGER
    {
        force(1)
    }

CfprLicenseModeType ::= TEXTUAL-CONVENTION
    STATUS        current
    DESCRIPTION
        ""
    SYNTAX        INTEGER
    {
        universal(0)
    }

CfprLsAgentCapability ::= TEXTUAL-CONVENTION
    STATUS        current
    DESCRIPTION
        ""
    SYNTAX        INTEGER
    {
        l2IfConfig(1),
        l3IfConfig(2),
        hostNameConfig(4),
        stats(8),
        states(16)
    }

CfprLsAgentMode ::= TEXTUAL-CONVENTION
    STATUS        current
    DESCRIPTION
        ""
    SYNTAX        INTEGER
    {
        noAgent(1),
        readOnly(2),
        full(4)
    }

CfprLsApply ::= TEXTUAL-CONVENTION
    STATUS        current
    DESCRIPTION
        ""
    SYNTAX        INTEGER
    {
        onAssociation(1),
        runTime(2)
    }

CfprLsAssignment ::= TEXTUAL-CONVENTION
    STATUS        current
    DESCRIPTION
        ""
    SYNTAX        INTEGER
    {
        unassigned(0),
        assigned(1),
        failed(2)
    }

CfprLsAssocState ::= TEXTUAL-CONVENTION
    STATUS        current
    DESCRIPTION
        ""
    SYNTAX        INTEGER
    {
        unassociated(0),
        associating(1),
        associated(2),
        disassociating(3),
        failed(4)
    }

CfprLsComputeBindingOperState ::= TEXTUAL-CONVENTION
    STATUS        current
    DESCRIPTION
        ""
    SYNTAX        INTEGER
    {
        unused(0),
        used(1),
        failedToApply(2)
    }

CfprLsConfigIssues ::= TEXTUAL-CONVENTION
    STATUS        current
    DESCRIPTION
        ""
    SYNTAX        BITS
    {
        insufficientResources(0),
        vnicCapacity(1),
        vhbaCapacity(2),
        fcoeCapacity(3),
        switchVirtualIfCapacity(4),
        macAddressAssignment(5),
        wwpnAssignment(6),
        wwnnAssignment(7),
        systemUuidAssignment(8),
        bootOrderSanImagePath(9),
        bootOrderPxe(10),
        computeUndiscovered(11),
        adaptorProtectedEthCapability(12),
        adaptorFcoeCapability(13),
        incompatibleNumberOfLocalDisks(14),
        adaptorRequirement(15),
        memoryRequirement(16),
        processorRequirement(17),
        serverPositionRequirement(18),
        computeUnavailable(19),
        wwnnDerivationFromVhba(20),
        bootConfigurationInvalid(21),
        connectionPlacement(22),
        wwpnDerivationVirtualizedPort(23),
        macDerivationVirtualizedPort(24),
        qosPolicyInvalid(25),
        vlanPortCapacity(26),
        physicalRequirement(27),
        destructiveLocalDiskConfig(28),
        powerGroupRequirement(29),
        migration(30),
        incompatibleBiosImage(31),
        incompatibleDiskTypes(32),
        incompatibleRaidLevel(33),
        invalidWwn(34),
        insufficientPowerBudget(35),
        bootipPolicyInvalid(36),
        hostimgPolicyInvalid(37),
        imgsecPolicyInvalid(38),
        provsrvPolicyInvalid(39),
        incompatBiosForSriovVnics(40),
        iscsiConfig(41),
        vnicNotHaReady(42),
        missingPrimaryVlan(43),
        missingRaidKey(44),
        bootOrderIscsi(45),
        vfcVnicPvlanConflict(46),
        vifResourcesOverprovisioned(47),
        pinningVlanMismatch(48),
        vnicVlanAssignmentError(49),
        iscsiInitiatorIpAddress(50),
        storagePathConfigurationError(51),
        zoneCapacity(52),
        dynamicVfVnic(53),
        boardControllerUpdateUnsupported(54),
        vnicVconProvisioningChange(55),
        namedVlanInaccessible(56),
        pinningInvalid(57),
        nonInterruptFsmRunning(58),
        missingFirmwareImage(59),
        remotePolicy(60),
        resourceOwnershipConflict(61),
        duplicateAddressConflict(62)
    }

CfprLsConfigState ::= TEXTUAL-CONVENTION
    STATUS        current
    DESCRIPTION
        ""
    SYNTAX        INTEGER
    {
        notApplied(0),
        applying(1),
        failedToApply(2),
        applied(3)
    }

CfprLsConfigWarnings ::= TEXTUAL-CONVENTION
    STATUS        current
    DESCRIPTION
        ""
    SYNTAX        BITS
    {
        kvmMgmtPolicyUnsupported(0)
    }

CfprLsFcZoneGroupSwitchId ::= TEXTUAL-CONVENTION
    STATUS        current
    DESCRIPTION
        ""
    SYNTAX        INTEGER
    {
        none(0),
        a(1),
        b(2),
        dual(3)
    }

CfprLsFcZoneState ::= TEXTUAL-CONVENTION
    STATUS        current
    DESCRIPTION
        ""
    SYNTAX        INTEGER
    {
        notApplied(0),
        applied(1),
        applying(2),
        applyPending(3),
        notActive(4),
        active(5),
        created(6),
        createFailed(7),
        deleted(8),
        zoneMergeFailure(9)
    }

CfprLsOperState ::= TEXTUAL-CONVENTION
    STATUS        current
    DESCRIPTION
        ""
    SYNTAX        INTEGER
    {
        indeterminate(0),
        unassociated(1),
        ok(10),
        discovery(11),
        config(12),
        unconfig(13),
        powerOff(14),
        restart(15),
        maintenance(20),
        test(21),
        computeMismatch(29),
        computeFailed(30),
        degraded(31),
        discoveryFailed(32),
        configFailure(33),
        unconfigFailed(34),
        testFailed(35),
        maintenanceFailed(36),
        removed(40),
        disabled(41),
        inaccessible(50),
        thermalProblem(60),
        powerProblem(61),
        voltageProblem(62),
        inoperable(63),
        decomissioning(101),
        decomissioned(102),
        biosRestore(201),
        cmosReset(202),
        diagnostics(203),
        diagnosticsFailed(204),
        pendingReboot(210),
        pendingReassociation(211),
        svnicNotPresent(212)
    }

CfprLsOwner ::= TEXTUAL-CONVENTION
    STATUS        current
    DESCRIPTION
        ""
    SYNTAX        INTEGER
    {
        management(1),
        physicalInherit(2),
        physicalDefaultConfig(4),
        tier(8)
    }

CfprLsPowerState ::= TEXTUAL-CONVENTION
    STATUS        current
    DESCRIPTION
        ""
    SYNTAX        INTEGER
    {
        down(0),
        up(1),
        cycleImmediate(2),
        cycleWait(3),
        hardResetImmediate(4),
        hardResetWait(5),
        softShutDown(6),
        softShutDownOnly(7),
        cmosResetImmediate(12),
        bmcResetImmediate(13),
        bmcResetWait(14),
        diagnosticInterrupt(15),
        kvmReset(16),
        adminUp(31),
        adminDown(32),
        ipmiReset(33)
    }

CfprLsResolveFromRemoteServer ::= TEXTUAL-CONVENTION
    STATUS        current
    DESCRIPTION
        ""
    SYNTAX        INTEGER
    {
        no(0),
        yes(1)
    }

CfprLsServerFsmCurrentFsm ::= TEXTUAL-CONVENTION
    STATUS        current
    DESCRIPTION
        ""
    SYNTAX        INTEGER
    {
        nop(0),
        configure(857)
    }

CfprLsServerFsmStageName ::= TEXTUAL-CONVENTION
    STATUS        current
    DESCRIPTION
        ""
    SYNTAX        INTEGER
    {
        nop(0),
        configureBegin(857),
        configureApplyTemplate(858),
        configureApplyIdentifiers(859),
        configureApplyPolicies(860),
        configureResolveBootConfig(861),
        configureEvaluateAssociation(862),
        configureAnalyzeImpact(863),
        configureWaitForMaintPermission(864),
        configureWaitForMaintWindow(865),
        configureApplyConfig(866),
        configureFail(1002),
        configureSuccess(1003),
        configureResolveIdentifiers(1270),
        configureApplyDefaultIdentifiers(1271),
        configureResolveDefaultIdentifiers(1272),
        configureResolvePolicies(1273),
        configureResolveDistributableNames(1274),
        configureResolveDistributable(1275),
        configureResolveImages(1276),
        configureResolveSchedule(1277),
        configureProvisionStorage(1278),
        configureWaitForStorageProvision(1279),
        configureCommitStorage(1280),
        configureWaitForCommitStorage(1281),
        configureWaitForAssocCompletion(1282),
        configureResolveNetworkPolicies(1471),
        configureResolveNetworkTemplates(1472),
        configureValidatePolicyOwnership(1473),
        configureCheckAssignedIdentifiersForDup(1674),
        configureCheckAssignedDefaultIdentifiersForDup(1675)
    }

CfprLsServerFsmTaskFlags ::= TEXTUAL-CONVENTION
    STATUS        current
    DESCRIPTION
        ""
    SYNTAX        BITS
    {
        samDmeLsServerConfigureLsRename(4),
        samDmeLsServerConfigureModification(49),
        samDmeLsServerConfigureFinalDisassoc(50)
    }

CfprLsServerFsmTaskItem ::= TEXTUAL-CONVENTION
    STATUS        current
    DESCRIPTION
        ""
    SYNTAX        INTEGER
    {
        nop(0),
        configure(857)
    }

CfprLsType ::= TEXTUAL-CONVENTION
    STATUS        current
    DESCRIPTION
        ""
    SYNTAX        INTEGER
    {
        instance(0),
        initialTemplate(1),
        updatingTemplate(2)
    }

CfprLsbootADefBootMode ::= TEXTUAL-CONVENTION
    STATUS        current
    DESCRIPTION
        ""
    SYNTAX        INTEGER
    {
        legacy(1),
        uefi(2)
    }

CfprLsbootAccessType ::= TEXTUAL-CONVENTION
    STATUS        current
    DESCRIPTION
        ""
    SYNTAX        INTEGER
    {
        readWrite(0),
        readOnly(1),
        readWriteLocal(2),
        readWriteRemote(3),
        readOnlyLocal(4),
        readOnlyRemote(5),
        readWriteDrive(6),
        readOnlyRemoteCimc(7),
        readWriteRemoteCimc(8)
    }

CfprLsbootDefaultLocalImageType ::= TEXTUAL-CONVENTION
    STATUS        current
    DESCRIPTION
        ""
    SYNTAX        INTEGER
    {
        localAny(1),
        sdCard(2),
        localLun(3),
        usbIntern(4),
        usbExtern(5)
    }

CfprLsbootIScsiAccess ::= TEXTUAL-CONVENTION
    STATUS        current
    DESCRIPTION
        ""
    SYNTAX        INTEGER
    {
        readWrite(0),
        readOnly(1),
        readWriteLocal(2),
        readWriteRemote(3),
        readOnlyLocal(4),
        readOnlyRemote(5),
        readWriteDrive(6),
        readOnlyRemoteCimc(7),
        readWriteRemoteCimc(8)
    }

CfprLsbootIScsiType ::= TEXTUAL-CONVENTION
    STATUS        current
    DESCRIPTION
        ""
    SYNTAX        INTEGER
    {
        virtualMedia(1),
        storage(2),
        lan(3),
        iscsi(4),
        san(5)
    }

CfprLsbootIScsiImagePathType ::= TEXTUAL-CONVENTION
    STATUS        current
    DESCRIPTION
        ""
    SYNTAX        INTEGER
    {
        primary(0),
        secondary(1)
    }

CfprLsbootLanAccess ::= TEXTUAL-CONVENTION
    STATUS        current
    DESCRIPTION
        ""
    SYNTAX        INTEGER
    {
        readWrite(0),
        readOnly(1),
        readWriteLocal(2),
        readWriteRemote(3),
        readOnlyLocal(4),
        readOnlyRemote(5),
        readWriteDrive(6),
        readOnlyRemoteCimc(7),
        readWriteRemoteCimc(8)
    }

CfprLsbootLanType ::= TEXTUAL-CONVENTION
    STATUS        current
    DESCRIPTION
        ""
    SYNTAX        INTEGER
    {
        virtualMedia(1),
        storage(2),
        lan(3),
        iscsi(4),
        san(5)
    }

CfprLsbootLanBootProt ::= TEXTUAL-CONVENTION
    STATUS        current
    DESCRIPTION
        ""
    SYNTAX        INTEGER
    {
        pxe(0),
        gpxe(1),
        iSCSI(2)
    }

CfprLsbootLanImagePathType ::= TEXTUAL-CONVENTION
    STATUS        current
    DESCRIPTION
        ""
    SYNTAX        INTEGER
    {
        primary(0),
        secondary(1)
    }

CfprLsbootLocalHddImageType ::= TEXTUAL-CONVENTION
    STATUS        current
    DESCRIPTION
        ""
    SYNTAX        INTEGER
    {
        localAny(1),
        sdCard(2),
        localLun(3),
        usbIntern(4),
        usbExtern(5)
    }

CfprLsbootPurpose ::= TEXTUAL-CONVENTION
    STATUS        current
    DESCRIPTION
        ""
    SYNTAX        INTEGER
    {
        utility(1),
        operational(2)
    }

CfprLsbootSanAccess ::= TEXTUAL-CONVENTION
    STATUS        current
    DESCRIPTION
        ""
    SYNTAX        INTEGER
    {
        readWrite(0),
        readOnly(1),
        readWriteLocal(2),
        readWriteRemote(3),
        readOnlyLocal(4),
        readOnlyRemote(5),
        readWriteDrive(6),
        readOnlyRemoteCimc(7),
        readWriteRemoteCimc(8)
    }

CfprLsbootSanType ::= TEXTUAL-CONVENTION
    STATUS        current
    DESCRIPTION
        ""
    SYNTAX        INTEGER
    {
        virtualMedia(1),
        storage(2),
        lan(3),
        iscsi(4),
        san(5)
    }

CfprLsbootSanCatSanImageType ::= TEXTUAL-CONVENTION
    STATUS        current
    DESCRIPTION
        ""
    SYNTAX        INTEGER
    {
        primary(0),
        secondary(1)
    }

CfprLsbootSanCatSanImagePathType ::= TEXTUAL-CONVENTION
    STATUS        current
    DESCRIPTION
        ""
    SYNTAX        INTEGER
    {
        primary(0),
        secondary(1)
    }

CfprLsbootSanImageType ::= TEXTUAL-CONVENTION
    STATUS        current
    DESCRIPTION
        ""
    SYNTAX        INTEGER
    {
        primary(0),
        secondary(1)
    }

CfprLsbootSanImagePathType ::= TEXTUAL-CONVENTION
    STATUS        current
    DESCRIPTION
        ""
    SYNTAX        INTEGER
    {
        primary(0),
        secondary(1)
    }

CfprLsbootStorageAccess ::= TEXTUAL-CONVENTION
    STATUS        current
    DESCRIPTION
        ""
    SYNTAX        INTEGER
    {
        readWrite(0),
        readOnly(1),
        readWriteLocal(2),
        readWriteRemote(3),
        readOnlyLocal(4),
        readOnlyRemote(5),
        readWriteDrive(6),
        readOnlyRemoteCimc(7),
        readWriteRemoteCimc(8)
    }

CfprLsbootStorageType ::= TEXTUAL-CONVENTION
    STATUS        current
    DESCRIPTION
        ""
    SYNTAX        INTEGER
    {
        virtualMedia(1),
        storage(2),
        lan(3),
        iscsi(4),
        san(5)
    }

CfprLsbootUsbExternalImageType ::= TEXTUAL-CONVENTION
    STATUS        current
    DESCRIPTION
        ""
    SYNTAX        INTEGER
    {
        localAny(1),
        sdCard(2),
        localLun(3),
        usbIntern(4),
        usbExtern(5)
    }

CfprLsbootUsbFlashStorageImageType ::= TEXTUAL-CONVENTION
    STATUS        current
    DESCRIPTION
        ""
    SYNTAX        INTEGER
    {
        localAny(1),
        sdCard(2),
        localLun(3),
        usbIntern(4),
        usbExtern(5)
    }

CfprLsbootUsbInternalImageType ::= TEXTUAL-CONVENTION
    STATUS        current
    DESCRIPTION
        ""
    SYNTAX        INTEGER
    {
        localAny(1),
        sdCard(2),
        localLun(3),
        usbIntern(4),
        usbExtern(5)
    }

CfprLsbootVirtualMediaType ::= TEXTUAL-CONVENTION
    STATUS        current
    DESCRIPTION
        ""
    SYNTAX        INTEGER
    {
        virtualMedia(1),
        storage(2),
        lan(3),
        iscsi(4),
        san(5)
    }

CfprLsmaintAckChangeDetails ::= TEXTUAL-CONVENTION
    STATUS        current
    DESCRIPTION
        ""
    SYNTAX        BITS
    {
        binding(0),
        hostVirtEthIf(1),
        hostNonvirtEthIf(2),
        hostEthIfProfile(3),
        hostEthIfQos(4),
        hostEthIfNwCtrl(5),
        hostVirtFcIf(6),
        hostNonvirtFcIf(7),
        hostVirtFcIfPersBind(8),
        hostNonvirtFcIfPersBind(9),
        hostFcIfProfile(10),
        hostFcIfQos(11),
        hostFcoeIf(12),
        vif(13),
        vlan(14),
        vsan(15),
        ip(16),
        bootOrder(17),
        bootVirtVnic(18),
        bootNonvirtVnic(19),
        bootLocalStorage(20),
        bootVirtPxe(21),
        bootNonvirtPxe(22),
        bladeIdentity(24),
        agentPolicy(25),
        biosFw(26),
        storageControllerFw(27),
        adaptorHostFw(28),
        adaptorNwFw(29),
        mgmtControllerFw(30),
        localDiskPolicy(31),
        pin(32),
        sol(33),
        epAuth(34),
        biosProfile(35),
        checkpoint(36),
        implicitReboot(37),
        implicitHostFcIfProfileRedeploy(38),
        boardControllerFw(39),
        hostEthIfQosHostControl(40),
        localDiskFw(41),
        implicitHostEthIfProfileRedeploy(42),
        storagePath(43),
        bmcUpdateBiosFw(44),
        hostIfPcie(45),
        flexflashConfig(46),
        bootmodeConfig(48),
        securebootConfig(49),
        vmediaConfig(50),
        ssposUpdateFw(51)
    }

CfprLsmaintAckChanges ::= TEXTUAL-CONVENTION
    STATUS        current
    DESCRIPTION
        ""
    SYNTAX        BITS
    {
        serverIdentity(0),
        storage(1),
        networking(2),
        vnicVhbaPlacement(3),
        bootOrder(4),
        serverAssignment(5),
        operationalPolicies(6)
    }

CfprLsmaintAckDisr ::= TEXTUAL-CONVENTION
    STATUS        current
    DESCRIPTION
        ""
    SYNTAX        BITS
    {
        upTime(0),
        acPowerCycle(1)
    }

CfprLsmaintChangeMode ::= TEXTUAL-CONVENTION
    STATUS        current
    DESCRIPTION
        ""
    SYNTAX        INTEGER
    {
        noChange(0),
        unconfig(1),
        forceUnconfig(2),
        rediscover(4),
        config(8),
        diagConfig(16),
        diagUnconfig(32),
        removeConfig(64),
        diag(128)
    }

CfprMacpoolPoolAssignmentOrder ::= TEXTUAL-CONVENTION
    STATUS        current
    DESCRIPTION
        ""
    SYNTAX        INTEGER
    {
        default(0),
        sequential(1)
    }

CfprMemoryAdminState ::= TEXTUAL-CONVENTION
    STATUS        current
    DESCRIPTION
        ""
    SYNTAX        INTEGER
    {
        policy(1),
        resetErrors(2)
    }

CfprMemoryArrayId ::= TEXTUAL-CONVENTION
    STATUS        current
    DESCRIPTION
        ""
    SYNTAX        Gauge32 (1..8)

CfprMemoryArrayEnvStatsThresholded ::= TEXTUAL-CONVENTION
    STATUS        current
    DESCRIPTION
        ""
    SYNTAX        BITS
    {
        inputCurrent(0),
        inputCurrentAvg(1),
        inputCurrentMax(2),
        inputCurrentMin(3)
    }

CfprMemoryArrayEnvStatsHistThresholded ::= TEXTUAL-CONVENTION
    STATUS        current
    DESCRIPTION
        ""
    SYNTAX        BITS
    {
        inputCurrent(0),
        inputCurrentAvg(1),
        inputCurrentMax(2),
        inputCurrentMin(3)
    }

CfprMemoryBufferUnitId ::= TEXTUAL-CONVENTION
    STATUS        current
    DESCRIPTION
        ""
    SYNTAX        Gauge32 (1..16)

CfprMemoryBufferUnitEnvStatsThresholded ::= TEXTUAL-CONVENTION
    STATUS        current
    DESCRIPTION
        ""
    SYNTAX        BITS
    {
        temperature(0),
        temperatureAvg(1),
        temperatureMax(2),
        temperatureMin(3)
    }

CfprMemoryBufferUnitEnvStatsHistThresholded ::= TEXTUAL-CONVENTION
    STATUS        current
    DESCRIPTION
        ""
    SYNTAX        BITS
    {
        temperature(0),
        temperatureAvg(1),
        temperatureMax(2),
        temperatureMin(3)
    }

CfprMemoryErrorCorrection ::= TEXTUAL-CONVENTION
    STATUS        current
    DESCRIPTION
        ""
    SYNTAX        INTEGER
    {
        undiscovered(0),
        other(1),
        unknown(2),
        none(3),
        parity(4),
        singleBitECC(5),
        multiBitECC(6),
        crc(7)
    }

CfprMemoryErrorStatsThresholded ::= TEXTUAL-CONVENTION
    STATUS        current
    DESCRIPTION
        ""
    SYNTAX        BITS
    {
        addressParityErrors(0),
        eccMultibitErrors(1),
        eccSinglebitErrors(2),
        mismatchErrors(3)
    }

CfprMemoryFormFactor ::= TEXTUAL-CONVENTION
    STATUS        current
    DESCRIPTION
        ""
    SYNTAX        INTEGER
    {
        undiscovered(0),
        other(1),
        unknown(2),
        simm(3),
        dimm(9),
        tsop(10),
        rimm(12),
        sodimm(13),
        srimm(14),
        fbDimm(15)
    }

CfprMemoryIssues ::= TEXTUAL-CONVENTION
    STATUS        current
    DESCRIPTION
        ""
    SYNTAX        BITS
    {
        uncorrectableEccError(0),
        correctableEccError(1),
        addressParityError(2),
        memoryMismatchError(3)
    }

CfprMemoryRuntimeThresholded ::= TEXTUAL-CONVENTION
    STATUS        current
    DESCRIPTION
        ""
    SYNTAX        BITS
    {
        available(0),
        availableAvg(1),
        availableMax(2),
        availableMin(3),
        cached(4),
        cachedAvg(5),
        cachedMax(6),
        cachedMin(7),
        total(8),
        totalAvg(9),
        totalMax(10),
        totalMin(11)
    }

CfprMemoryRuntimeType ::= TEXTUAL-CONVENTION
    STATUS        current
    DESCRIPTION
        ""
    SYNTAX        INTEGER
    {
        swap(1),
        total(2)
    }

CfprMemoryRuntimeHistThresholded ::= TEXTUAL-CONVENTION
    STATUS        current
    DESCRIPTION
        ""
    SYNTAX        BITS
    {
        available(0),
        availableAvg(1),
        availableMax(2),
        availableMin(3),
        cached(4),
        cachedAvg(5),
        cachedMax(6),
        cachedMin(7),
        total(8),
        totalAvg(9),
        totalMax(10),
        totalMin(11)
    }

CfprMemoryType ::= TEXTUAL-CONVENTION
    STATUS        current
    DESCRIPTION
        ""
    SYNTAX        INTEGER
    {
        undiscovered(0),
        other(1),
        unknown(2),
        dram(3),
        edram(4),
        vram(5),
        sram(6),
        ram(7),
        rom(8),
        flash(9),
        eeprom(10),
        feprom(11),
        eprom(12),
        cdram(13),
        n3DRAM(14),
        sdram(15),
        sgram(16),
        rdram(17),
        ddr(18),
        ddr2(19),
        ddr2FbDimm(20),
        ddr3(24),
        fbd2(25)
    }

CfprMemoryUnitId ::= TEXTUAL-CONVENTION
    STATUS        current
    DESCRIPTION
        ""
    SYNTAX        Gauge32 (1..256)

CfprMemoryUnitOperability ::= TEXTUAL-CONVENTION
    STATUS        current
    DESCRIPTION
        ""
    SYNTAX        INTEGER
    {
        unknown(0),
        operable(1),
        inoperable(2),
        degraded(3),
        poweredOff(4),
        powerProblem(5),
        removed(6),
        voltageProblem(7),
        thermalProblem(8),
        performanceProblem(9),
        accessibilityProblem(10),
        identityUnestablishable(11),
        biosPostTimeout(12),
        disabled(13),
        malformedFru(14),
        fabricConnProblem(51),
        fabricUnsupportedConn(52),
        config(81),
        equipmentProblem(82),
        decomissioning(83),
        chassisLimitExceeded(84),
        notSupported(100),
        discovery(101),
        discoveryFailed(102),
        identify(103),
        postFailure(104),
        upgradeProblem(105),
        peerCommProblem(106),
        autoUpgrade(107),
        linkActivateBlocked(108)
    }

CfprMemoryUnitEnvStatsThresholded ::= TEXTUAL-CONVENTION
    STATUS        current
    DESCRIPTION
        ""
    SYNTAX        BITS
    {
        temperature(0),
        temperatureAvg(1),
        temperatureMax(2),
        temperatureMin(3)
    }

CfprMemoryUnitEnvStatsHistThresholded ::= TEXTUAL-CONVENTION
    STATUS        current
    DESCRIPTION
        ""
    SYNTAX        BITS
    {
        temperature(0),
        temperatureAvg(1),
        temperatureMax(2),
        temperatureMin(3)
    }

CfprMemoryVisibility ::= TEXTUAL-CONVENTION
    STATUS        current
    DESCRIPTION
        ""
    SYNTAX        INTEGER
    {
        unknown(0),
        yes(1),
        no(2)
    }

CfprMgmtAccess ::= TEXTUAL-CONVENTION
    STATUS        current
    DESCRIPTION
        ""
    SYNTAX        INTEGER
    {
        unspecified(0),
        inBand(1),
        outOfBand(2),
        internal(4),
        virtual(8)
    }

CfprMgmtAdminState ::= TEXTUAL-CONVENTION
    STATUS        current
    DESCRIPTION
        ""
    SYNTAX        INTEGER
    {
        disable(0),
        enable(1)
    }

CfprMgmtBackupPostAction ::= TEXTUAL-CONVENTION
    STATUS        current
    DESCRIPTION
        ""
    SYNTAX        INTEGER
    {
        none(0),
        remove(1)
    }

CfprMgmtBackupProto ::= TEXTUAL-CONVENTION
    STATUS        current
    DESCRIPTION
        ""
    SYNTAX        INTEGER
    {
        none(0),
        ftp(1),
        tftp(2),
        scp(3),
        http(4),
        sftp(5),
        nfsCopy(6),
        https(11)
    }

CfprMgmtBackupFsmCurrentFsm ::= TEXTUAL-CONVENTION
    STATUS        current
    DESCRIPTION
        ""
    SYNTAX        INTEGER
    {
        nop(0),
        backup(290)
    }

CfprMgmtBackupFsmStageName ::= TEXTUAL-CONVENTION
    STATUS        current
    DESCRIPTION
        ""
    SYNTAX        INTEGER
    {
        nop(0),
        backupBegin(290),
        backupBackupLocal(291),
        backupUpload(292),
        backupFail(398),
        backupSuccess(399)
    }

CfprMgmtBackupFsmTaskItem ::= TEXTUAL-CONVENTION
    STATUS        current
    DESCRIPTION
        ""
    SYNTAX        INTEGER
    {
        nop(0),
        backup(290)
    }

CfprMgmtBackupInterval ::= TEXTUAL-CONVENTION
    STATUS        current
    DESCRIPTION
        ""
    SYNTAX        INTEGER
    {
        n1day(86400),
        n1week(604800),
        n2week(1209600)
    }

CfprMgmtBackupIssue ::= TEXTUAL-CONVENTION
    STATUS        current
    DESCRIPTION
        ""
    SYNTAX        INTEGER
    {
        none(0),
        outdated(1)
    }

CfprMgmtBackupJob ::= TEXTUAL-CONVENTION
    STATUS        current
    DESCRIPTION
        ""
    SYNTAX        INTEGER
    {
        immediate(2)
    }

CfprMgmtBackupPolicyFsmCurrentFsm ::= TEXTUAL-CONVENTION
    STATUS        current
    DESCRIPTION
        ""
    SYNTAX        INTEGER
    {
        nop(0),
        reportConfigCopy(1372)
    }

CfprMgmtBackupPolicyFsmStageName ::= TEXTUAL-CONVENTION
    STATUS        current
    DESCRIPTION
        ""
    SYNTAX        INTEGER
    {
        nop(0),
        reportConfigCopyBegin(1372),
        reportConfigCopyReport(1373),
        reportConfigCopyFail(1414),
        reportConfigCopySuccess(1415)
    }

CfprMgmtBackupStatus ::= TEXTUAL-CONVENTION
    STATUS        current
    DESCRIPTION
        ""
    SYNTAX        INTEGER
    {
        idle(0),
        exporting(1),
        succeeded(2),
        failed(3)
    }

CfprMgmtBackupType ::= TEXTUAL-CONVENTION
    STATUS        current
    DESCRIPTION
        ""
    SYNTAX        INTEGER
    {
        fullState(1),
        configAll(2),
        configSystem(3),
        configLogical(4)
    }

CfprMgmtCfgExportPolicyFsmCurrentFsm ::= TEXTUAL-CONVENTION
    STATUS        current
    DESCRIPTION
        ""
    SYNTAX        INTEGER
    {
        nop(0),
        reportConfigCopy(1372)
    }

CfprMgmtCfgExportPolicyFsmStageName ::= TEXTUAL-CONVENTION
    STATUS        current
    DESCRIPTION
        ""
    SYNTAX        INTEGER
    {
        nop(0),
        reportConfigCopyBegin(1372),
        reportConfigCopyReport(1373),
        reportConfigCopyFail(1414),
        reportConfigCopySuccess(1415)
    }

CfprMgmtCimcSecureBootAdminState ::= TEXTUAL-CONVENTION
    STATUS        current
    DESCRIPTION
        ""
    SYNTAX        INTEGER
    {
        disable(0),
        enable(1)
    }

CfprMgmtConfigState ::= TEXTUAL-CONVENTION
    STATUS        current
    DESCRIPTION
        ""
    SYNTAX        INTEGER
    {
        incomplete(0),
        unsupportedVlan(1),
        unsupportedServer(2),
        unresolvedVlan(3),
        unsupportedFirmware(4),
        valid(5)
    }

CfprMgmtConnectionState ::= TEXTUAL-CONVENTION
    STATUS        current
    DESCRIPTION
        ""
    SYNTAX        INTEGER
    {
        unInitialized(0),
        acknowledged(1),
        unsupportedConnectivity(2)
    }

CfprMgmtControllerFsmCurrentFsm ::= TEXTUAL-CONVENTION
    STATUS        current
    DESCRIPTION
        ""
    SYNTAX        INTEGER
    {
        nop(0),
        extMgmtIfConfig(17),
        updateSwitch(248),
        updateIOM(253),
        activateIOM(256),
        updateBMC(259),
        activateBMC(262),
        updateFPRManager(467),
        sysConfig(474),
        online(1059),
        registryConfig(1384),
        extMgmtInterfaceConfig(1512),
        lockConfig(1589)
    }

CfprMgmtControllerFsmStageName ::= TEXTUAL-CONVENTION
    STATUS        current
    DESCRIPTION
        ""
    SYNTAX        INTEGER
    {
        nop(0),
        extMgmtIfConfigBegin(17),
        extMgmtIfConfigPrimary(18),
        extMgmtIfConfigSecondary(19),
        updateSwitchBegin(248),
        updateSwitchUpdateLocal(249),
        updateSwitchResetLocal(250),
        updateSwitchUpdateRemote(251),
        updateSwitchResetRemote(252),
        updateIOMBegin(253),
        updateIOMUpdateRequest(254),
        updateIOMPollUpdateStatus(255),
        activateIOMBegin(256),
        activateIOMActivate(257),
        activateIOMReset(258),
        updateBMCBegin(259),
        updateBMCUpdateRequest(260),
        updateBMCPollUpdateStatus(261),
        activateBMCBegin(262),
        activateBMCActivate(263),
        activateBMCReset(264),
        activateBMCFail(400),
        activateBMCSuccess(401),
        activateIOMFail(402),
        activateIOMSuccess(403),
        extMgmtIfConfigFail(404),
        extMgmtIfConfigSuccess(405),
        updateBMCFail(406),
        updateBMCSuccess(407),
        updateIOMFail(408),
        updateIOMSuccess(409),
        updateSwitchFail(412),
        updateSwitchSuccess(413),
        updateFPRManagerBegin(467),
        updateFPRManagerExecute(468),
        updateFPRManagerFail(469),
        updateFPRManagerSuccess(470),
        updateFPRManagerStart(471),
        updateSwitchVerifyLocal(472),
        updateSwitchVerifyRemote(473),
        sysConfigBegin(474),
        sysConfigPrimary(475),
        sysConfigSecondary(476),
        sysConfigFail(477),
        sysConfigSuccess(478),
        onlineBegin(1059),
        onlineBmcConfigureConnLocal(1060),
        onlineSwConfigureConnLocal(1061),
        onlineBmcConfigureConnPeer(1062),
        onlineSwConfigureConnPeer(1063),
        onlineFail(1075),
        onlineSuccess(1076),
        updateFPRManagerCopyExtToLocal(1303),
        updateFPRManagerCopyExtToPeer(1304),
        updateSwitchCopyToLocal(1305),
        updateSwitchCopyToPeer(1306),
        registryConfigBegin(1384),
        registryConfigRemove(1385),
        registryConfigFail(1412),
        registryConfigSuccess(1413),
        extMgmtInterfaceConfigBegin(1512),
        extMgmtInterfaceConfigCIMCVlanCfgLocal(1513),
        extMgmtInterfaceConfigCIMCVlanCfgPeer(1514),
        extMgmtInterfaceConfigCMCVlanCfg(1515),
        extMgmtInterfaceConfigCMCVlanCfgPeer(1516),
        extMgmtInterfaceConfigActive(1517),
        extMgmtInterfaceConfigFail(1555),
        extMgmtInterfaceConfigSuccess(1556),
        updateIOMCopyImgFromRep(1563),
        updateIOMCopyIOMImgToSub(1564),
        lockConfigBegin(1589),
        lockConfigPowerButtonLockConfig(1590),
        lockConfigFail(1595),
        lockConfigSuccess(1596),
        updateSwitchUpdateManager(1990)
    }

CfprMgmtControllerFsmTaskFlags ::= TEXTUAL-CONVENTION
    STATUS        current
    DESCRIPTION
        ""
    SYNTAX        BITS
    {
        samDmeMgmtControllerUpdateSwitchActivate(14),
        samDmeMgmtControllerUpdateSwitchReset(15),
        samDmeMgmtControllerUpdateSwitchApplyInfra(31)
    }

CfprMgmtControllerFsmTaskItem ::= TEXTUAL-CONVENTION
    STATUS        current
    DESCRIPTION
        ""
    SYNTAX        INTEGER
    {
        nop(0),
        extMgmtIfConfig(17),
        updateSwitch(248),
        updateIOM(253),
        activateIOM(256),
        updateBMC(259),
        activateBMC(262),
        updateFPRManager(467),
        sysConfig(474),
        online(1059),
        registryConfig(1384),
        extMgmtInterfaceConfig(1512),
        lockConfig(1589)
    }

CfprMgmtDimmBlacklistingOperState ::= TEXTUAL-CONVENTION
    STATUS        current
    DESCRIPTION
        ""
    SYNTAX        INTEGER
    {
        unknown(0),
        enabled(1),
        disabled(2),
        unsupported(3)
    }

CfprMgmtEntityChassisDeviceIoState1 ::= TEXTUAL-CONVENTION
    STATUS        current
    DESCRIPTION
        ""
    SYNTAX        INTEGER
    {
        unknown(0),
        ok(1),
        openError(2),
        readError(3),
        writeError(4)
    }

CfprMgmtEntityChassisDeviceIoState2 ::= TEXTUAL-CONVENTION
    STATUS        current
    DESCRIPTION
        ""
    SYNTAX        INTEGER
    {
        unknown(0),
        ok(1),
        openError(2),
        readError(3),
        writeError(4)
    }

CfprMgmtEntityChassisDeviceIoState3 ::= TEXTUAL-CONVENTION
    STATUS        current
    DESCRIPTION
        ""
    SYNTAX        INTEGER
    {
        unknown(0),
        ok(1),
        openError(2),
        readError(3),
        writeError(4)
    }

CfprMgmtEntityHaFailureReason ::= TEXTUAL-CONVENTION
    STATUS        current
    DESCRIPTION
        ""
    SYNTAX        INTEGER
    {
        none(0),
        nodeDown(1),
        peerNodeDown(2),
        mgmtServicesUnresponsive(3),
        peerMgmtServicesUnresponsive(4),
        chassisConfigIncomplete(5),
        peerChassisConfigIncomplete(6),
        networkInterfaceDown(7)
    }

CfprMgmtEntityHaReadiness ::= TEXTUAL-CONVENTION
    STATUS        current
    DESCRIPTION
        ""
    SYNTAX        INTEGER
    {
        unknown(0),
        ready(1),
        downgraded(2),
        notReady(3)
    }

CfprMgmtEntityLeadership ::= TEXTUAL-CONVENTION
    STATUS        current
    DESCRIPTION
        ""
    SYNTAX        INTEGER
    {
        unknown(0),
        primary(1),
        subordinate(2),
        inapplicable(3),
        electionInProgress(4),
        electionFailed(5)
    }

CfprMgmtEntityMgmtServicesState ::= TEXTUAL-CONVENTION
    STATUS        current
    DESCRIPTION
        ""
    SYNTAX        INTEGER
    {
        unknown(0),
        up(1),
        unresponsive(2),
        down(3),
        switchoverInProgress(4)
    }

CfprMgmtEntityProblems ::= TEXTUAL-CONVENTION
    STATUS        current
    DESCRIPTION
        ""
    SYNTAX        BITS
    {
        leadership(0),
        membership(1),
        umbilical(2),
        haReady(3),
        versionMismatch(4)
    }

CfprMgmtEntityState ::= TEXTUAL-CONVENTION
    STATUS        current
    DESCRIPTION
        ""
    SYNTAX        INTEGER
    {
        unknown(0),
        up(1),
        down(2)
    }

CfprMgmtEntityUmbilicalState ::= TEXTUAL-CONVENTION
    STATUS        current
    DESCRIPTION
        ""
    SYNTAX        INTEGER
    {
        unknown(0),
        degraded(1),
        full(2),
        failed(3)
    }

CfprMgmtExportPolicyAdminState ::= TEXTUAL-CONVENTION
    STATUS        current
    DESCRIPTION
        ""
    SYNTAX        INTEGER
    {
        disable(0),
        enable(1)
    }

CfprMgmtExportPolicyProto ::= TEXTUAL-CONVENTION
    STATUS        current
    DESCRIPTION
        ""
    SYNTAX        INTEGER
    {
        none(0),
        ftp(1),
        tftp(2),
        scp(3),
        http(4),
        sftp(5),
        nfsCopy(6),
        https(11)
    }

CfprMgmtExportPolicyFsmCurrentFsm ::= TEXTUAL-CONVENTION
    STATUS        current
    DESCRIPTION
        ""
    SYNTAX        INTEGER
    {
        nop(0),
        reportConfigCopy(1372)
    }

CfprMgmtExportPolicyFsmStageName ::= TEXTUAL-CONVENTION
    STATUS        current
    DESCRIPTION
        ""
    SYNTAX        INTEGER
    {
        nop(0),
        reportConfigCopyBegin(1372),
        reportConfigCopyReport(1373),
        reportConfigCopyFail(1414),
        reportConfigCopySuccess(1415)
    }

CfprMgmtExportPolicyFsmTaskItem ::= TEXTUAL-CONVENTION
    STATUS        current
    DESCRIPTION
        ""
    SYNTAX        INTEGER
    {
        nop(0),
        reportConfigCopy(1372)
    }

CfprMgmtIPv6IfAddrFsmCurrentFsm ::= TEXTUAL-CONVENTION
    STATUS        current
    DESCRIPTION
        ""
    SYNTAX        INTEGER
    {
        nop(0),
        swMgmtOobIpv6IfConfig(1495)
    }

CfprMgmtIPv6IfAddrFsmStageName ::= TEXTUAL-CONVENTION
    STATUS        current
    DESCRIPTION
        ""
    SYNTAX        INTEGER
    {
        nop(0),
        swMgmtOobIpv6IfConfigBegin(1495),
        swMgmtOobIpv6IfConfigSwitch(1496),
        swMgmtOobIpv6IfConfigFail(1557),
        swMgmtOobIpv6IfConfigSuccess(1558)
    }

CfprMgmtIPv6IfAddrFsmTaskItem ::= TEXTUAL-CONVENTION
    STATUS        current
    DESCRIPTION
        ""
    SYNTAX        INTEGER
    {
        nop(0),
        swMgmtOobIpv6IfConfig(1495)
    }

CfprMgmtIfFsmCurrentFsm ::= TEXTUAL-CONVENTION
    STATUS        current
    DESCRIPTION
        ""
    SYNTAX        INTEGER
    {
        nop(0),
        swMgmtOobIfConfig(277),
        swMgmtInbandIfConfig(279),
        virtualIfConfig(281),
        enableVip(284),
        disableVip(286),
        enableHA(288)
    }

CfprMgmtIfFsmStageName ::= TEXTUAL-CONVENTION
    STATUS        current
    DESCRIPTION
        ""
    SYNTAX        INTEGER
    {
        nop(0),
        swMgmtOobIfConfigBegin(277),
        swMgmtOobIfConfigSwitch(278),
        swMgmtInbandIfConfigBegin(279),
        swMgmtInbandIfConfigSwitch(280),
        virtualIfConfigBegin(281),
        virtualIfConfigLocal(282),
        virtualIfConfigRemote(283),
        enableVipBegin(284),
        enableVipLocal(285),
        disableVipBegin(286),
        disableVipPeer(287),
        enableHABegin(288),
        enableHALocal(289),
        disableVipFail(414),
        disableVipSuccess(415),
        enableHAFail(416),
        enableHASuccess(417),
        enableVipFail(418),
        enableVipSuccess(419),
        swMgmtInbandIfConfigFail(420),
        swMgmtInbandIfConfigSuccess(421),
        swMgmtOobIfConfigFail(422),
        swMgmtOobIfConfigSuccess(423),
        virtualIfConfigFail(424),
        virtualIfConfigSuccess(425)
    }

CfprMgmtIfFsmTaskItem ::= TEXTUAL-CONVENTION
    STATUS        current
    DESCRIPTION
        ""
    SYNTAX        INTEGER
    {
        nop(0),
        swMgmtOobIfConfig(277),
        swMgmtInbandIfConfig(279),
        virtualIfConfig(281),
        enableVip(284),
        disableVip(286),
        enableHA(288)
    }

CfprMgmtImportAction ::= TEXTUAL-CONVENTION
    STATUS        current
    DESCRIPTION
        ""
    SYNTAX        INTEGER
    {
        merge(0),
        replace(1)
    }

CfprMgmtImportStatus ::= TEXTUAL-CONVENTION
    STATUS        current
    DESCRIPTION
        ""
    SYNTAX        BITS
    {
        downloadSuccess(0),
        configSuccess(1),
        failed(2)
    }

CfprMgmtImporterPostAction ::= TEXTUAL-CONVENTION
    STATUS        current
    DESCRIPTION
        ""
    SYNTAX        INTEGER
    {
        none(0),
        remove(1)
    }

CfprMgmtImporterProto ::= TEXTUAL-CONVENTION
    STATUS        current
    DESCRIPTION
        ""
    SYNTAX        INTEGER
    {
        none(0),
        ftp(1),
        tftp(2),
        scp(3),
        http(4),
        sftp(5),
        nfsCopy(6),
        https(11)
    }

CfprMgmtImporterFsmCurrentFsm ::= TEXTUAL-CONVENTION
    STATUS        current
    DESCRIPTION
        ""
    SYNTAX        INTEGER
    {
        nop(0),
        import(293)
    }

CfprMgmtImporterFsmStageName ::= TEXTUAL-CONVENTION
    STATUS        current
    DESCRIPTION
        ""
    SYNTAX        INTEGER
    {
        nop(0),
        importBegin(293),
        importDownloadLocal(294),
        importFail(426),
        importSuccess(427),
        importConfig(580),
        importReportResults(626),
        importCleanUp(1856),
        importConfigBreakout(1857),
        importWaitForSwitch(1858),
        importVerifyKey(2034)
    }

CfprMgmtImporterFsmTaskItem ::= TEXTUAL-CONVENTION
    STATUS        current
    DESCRIPTION
        ""
    SYNTAX        INTEGER
    {
        nop(0),
        import(293)
    }

CfprMgmtIntAuthPolicyMethod ::= TEXTUAL-CONVENTION
    STATUS        current
    DESCRIPTION
        ""
    SYNTAX        INTEGER
    {
        none(0),
        password(1)
    }

CfprMgmtMode ::= TEXTUAL-CONVENTION
    STATUS        current
    DESCRIPTION
        ""
    SYNTAX        INTEGER
    {
        inBand(0)
    }

CfprMgmtOperState ::= TEXTUAL-CONVENTION
    STATUS        current
    DESCRIPTION
        ""
    SYNTAX        INTEGER
    {
        unknown(0),
        notDeployed(1),
        deployed(2),
        up(3),
        down(4)
    }

CfprMgmtPmonEntryState ::= TEXTUAL-CONVENTION
    STATUS        current
    DESCRIPTION
        ""
    SYNTAX        INTEGER
    {
        unknown(0),
        idle(1),
        running(2),
        pending(3),
        failed(4),
        error(5),
        exitPending(6),
        terminated(7),
        killed(8)
    }

CfprMgmtSecureBootOperState ::= TEXTUAL-CONVENTION
    STATUS        current
    DESCRIPTION
        ""
    SYNTAX        INTEGER
    {
        disabled(0),
        enabled(1),
        unsupported(2),
        enabling(3)
    }

CfprMgmtSource ::= TEXTUAL-CONVENTION
    STATUS        current
    DESCRIPTION
        ""
    SYNTAX        INTEGER
    {
        unspecified(0),
        sharedLom(1),
        sideband(2)
    }

CfprMgmtStateQual ::= TEXTUAL-CONVENTION
    STATUS        current
    DESCRIPTION
        ""
    SYNTAX        INTEGER
    {
        unspecified(0),
        valid(1),
        misconnected(2)
    }

CfprMgmtStorageSubsystemState ::= TEXTUAL-CONVENTION
    STATUS        current
    DESCRIPTION
        ""
    SYNTAX        INTEGER
    {
        unknown(0),
        uninitialized(1),
        initializing(2),
        initialized(3),
        unsupported(4)
    }

CfprMgmtSubject ::= TEXTUAL-CONVENTION
    STATUS        current
    DESCRIPTION
        ""
    SYNTAX        INTEGER
    {
        unknown(0),
        blade(1),
        chassis(2),
        system(4),
        switch(8),
        adaptor(16),
        iocard(32),
        boardController(64)
    }

CfprMgmtUpgradeStatus ::= TEXTUAL-CONVENTION
    STATUS        current
    DESCRIPTION
        ""
    SYNTAX        BITS
    {
        hwChangeDetected(0),
        fwChangeDetected(1),
        hwIncompatible(2),
        fwIncompatible(3),
        unsupportedHwVersion(4),
        unsupportedFwVersion(5),
        hwChangeSuccess(6),
        fwChangeSuccess(7)
    }

CfprMoMoClassId ::= TEXTUAL-CONVENTION
    STATUS        current
    DESCRIPTION
        ""
    SYNTAX        INTEGER
    {
        unspecified(0),
        moTopProps(1),
        topRoot(2),
        topSystem(3),
        fsmTask(4),
        namingNamedObject(5),
        namingNamedIdentifiedObject(6),
        conditionInfo(7),
        conditionReportable(8),
        conditionMutable(9),
        conditionImmutable(10),
        conditionMultiInstanceImmutable(11),
        conditionPolicy(12),
        conditionLog(13),
        conditionLoggable(14),
        aaaLog(15),
        aaaUserAction(16),
        aaaModLR(17),
        aaaSessionLR(18),
        eventEpCtrl(19),
        eventLog(20),
        eventRecord(21),
        eventHolder(22),
        eventInst(23),
        eventPolicy(24),
        faultHolder(25),
        faultInst(26),
        faultPolicy(27),
        statsItem(28),
        statsCurr(29),
        statsHist(30),
        statsHolder(31),
        statsCollectionPolicy(32),
        statsThresholdPolicy(33),
        statsThresholdClass(34),
        statsThresholdDefinition(35),
        statsThr32Definition(36),
        statsThr64Definition(37),
        statsThrFloatDefinition(38),
        statsThresholdValue(39),
        statsThr32Value(40),
        statsThr64Value(41),
        statsThrFloatValue(42),
        equipmentPOSTCodeReporter(43),
        equipmentPOSTCodeData(44),
        equipmentPOSTCode(45),
        equipmentPOST(46),
        swatInjection(47),
        swatTrigger(48),
        swatCondition(49),
        swatTarget(50),
        swatAction(51),
        swatResultstats(52),
        apeControllerManager(53),
        apeControllerChassis(54),
        apeControllerEeprom(55),
        apeNicAgManager(56),
        apeAdapter(57),
        apeMenlo(58),
        apePalo(59),
        apeAdapterVnic(60),
        apeMenloVnic(61),
        apeMenloVnicStats(62),
        apeManager(63),
        apeMc(64),
        apeMcTable(65),
        apeFru(66),
        apeSdr(67),
        apeReading(68),
        apeParam(69),
        apeBootMethod(70),
        apeLANBoot(71),
        apeSANBoot(72),
        apeLocalDiskBoot(73),
        apeVirtualMediaBoot(74),
        apeHostAgent(75),
        clitestTypeTest(76),
        clitestTypeTestParent(77),
        clitestTypeTestChild(78),
        clitestTypeTest2(79),
        fabricInternalDceSrv(80),
        fabricDceSrv(81),
        fabricDceSwSrv(82),
        fabricSwSrvEp(83),
        fabricADceSwSrvEp(84),
        fabricDceSwSrvEp(85),
        fabricSan(86),
        fabricFcSan(87),
        fabricSanEp(88),
        fabricAFcSanEp(89),
        fabricFcSanEp(90),
        fabricFcSanPcEp(91),
        fabricSanPc(92),
        fabricFcSanPc(93),
        fabricFcVsanPortEp(94),
        fabricSanPinGroup(95),
        fabricSanPinTarget(96),
        fabricEp(97),
        fabricCloud(98),
        fabricSanCloud(99),
        fabricLanCloud(100),
        fabricDomain(101),
        fabricExternal(102),
        fabricInternal(103),
        fabricPIoEp(104),
        fabricExternalEp(105),
        fabricInternalEp(106),
        fabricCIoEp(107),
        fabricExternalPc(108),
        fabricInternalPc(109),
        fabricPinGroup(110),
        fabricPinTarget(111),
        fabricLan(112),
        fabricEthLan(113),
        fabricLanEp(114),
        fabricAEthLanEp(115),
        fabricEthLanEp(116),
        fabricEthLanPcEp(117),
        fabricLanPc(118),
        fabricEthLanPc(119),
        fabricLanPinGroup(120),
        fabricLanPinTarget(121),
        fabricLocale(122),
        fabricPath(123),
        fabricPathEp(124),
        fabricPathConn(125),
        fabricVnetEp(126),
        fabricAVlan(127),
        fabricEpVlan(128),
        fabricAVsan(129),
        fabricEpVsan(130),
        fabricVsan(131),
        fabricVsanEp(132),
        fabricVlan(133),
        fabricSwChEp(134),
        fabricSwChPhEp(135),
        fabricComputeEp(136),
        fabricChassisEp(137),
        fabricComputeSlotEp(138),
        fabricIf(139),
        fabricComputePhEp(140),
        fabricLastAckedSlot(141),
        processorUnit(142),
        processorComponent(143),
        processorCore(144),
        processorThread(145),
        processorRuntime(146),
        processorRuntimeHist(147),
        processorQual(148),
        fcPIo(149),
        fcConfig(150),
        fcIfConfig(151),
        fcSwIfConfig(152),
        fcNicIfConfig(153),
        fcStats(154),
        fcStatsHist(155),
        fcErrStats(156),
        fcErrStatsHist(157),
        biosUnit(158),
        vnicTempl(159),
        vnicSanConnTempl(160),
        vnicLanConnTempl(161),
        vnicL3If(162),
        vnicIPIf(163),
        vnicIPv4If(164),
        vnicIpAddr(165),
        vnicIpV4Addr(166),
        vnicIpV4StaticAddr(167),
        vnicIpV4PooledAddr(168),
        vnicIPv4Dhcp(169),
        vnicIPv4Dns(170),
        vnicIPv4StaticRoute(171),
        vnicConnection(172),
        vnicNicConn(173),
        vnicVnic(174),
        vnicIf(175),
        vnicL2Lif(176),
        vnicEthLif(177),
        vnicFcLif(178),
        vnicLifVlan(179),
        vnicLifVsan(180),
        vnicL2If(181),
        vnicAFcIf(182),
        vnicEtherBaseIf(183),
        vnicAEtherIf(184),
        vnicAIpcIf(185),
        vnicAScsiIf(186),
        vnicFcOEIf(187),
        vnicFcIf(188),
        vnicEtherIf(189),
        vnicIpcIf(190),
        vnicScsiIf(191),
        vnicProfileSet(192),
        vnicProfile(193),
        vnicProfileAlias(194),
        vnicDynamicConReq(195),
        vnicDynamicConPolicy(196),
        vnicDynamicCon(197),
        vnicDynamicIdUniverse(198),
        vnicDynamicProvider(199),
        vnicDynamicProviderEp(200),
        vnicFcNode(201),
        vnicFcBase(202),
        vnicFc(203),
        vnicEtherBase(204),
        vnicEther(205),
        vnicIpc(206),
        vnicScsi(207),
        vnicBootTarget(208),
        lsbootItem(209),
        lsbootADef(210),
        lsbootPolicy(211),
        lsbootDef(212),
        lsbootCategory(213),
        lsbootStorage(214),
        lsbootLan(215),
        lsbootVirtualMedia(216),
        lsbootImage(217),
        lsbootRemoteImage(218),
        lsbootSanImage(219),
        lsbootLocalImage(220),
        lsbootLocalStorage(221),
        lsbootImagePath(222),
        lsbootLanImagePath(223),
        lsbootSanImagePath(224),
        procManager(225),
        procProcCounts(226),
        procTxCounts(227),
        procStimulusCounts(228),
        procPrtCounts(229),
        procProcs(230),
        procPrt(231),
        procDoer(232),
        storageController(233),
        storageUnit(234),
        storagePhysical(235),
        storageLogical(236),
        storageLocalLun(237),
        storageLocalDisk(238),
        storageLunDisk(239),
        storageQual(240),
        storageItem(241),
        storageLocalDiskConfig(242),
        storageLocalDiskConfigPolicy(243),
        storageLocalDiskConfigDef(244),
        storageLocalDiskPartition(245),
        memoryArray(246),
        memoryUnit(247),
        memoryRuntime(248),
        memoryRuntimeHist(249),
        memoryQual(250),
        aaaRealm(251),
        aaaAuthRealm(252),
        aaaEp(253),
        aaaRadiusEp(254),
        aaaLdapEp(255),
        aaaTacacsPlusEp(256),
        aaaProvider(257),
        aaaRadiusProvider(258),
        aaaLdapProvider(259),
        aaaTacacsPlusProvider(260),
        pkiEp(261),
        pkiItem(262),
        pkiCertReq(263),
        pkiKeyRing(264),
        pkiTP(265),
        aaaDefinition(266),
        commDefinition(267),
        pkiDefinition(268),
        commSvcEp(269),
        commSvcChannel(270),
        commWebChannel(271),
        commEvtChannel(272),
        commSvc(273),
        commWeb(274),
        commHttp(275),
        commHttps(276),
        commWsman(277),
        commCimxml(278),
        commShell(279),
        commTelnet(280),
        commSsh(281),
        commSmashCLP(282),
        commSnmp(283),
        commDateTime(284),
        commSnmpTrap(285),
        commDns(286),
        commClient(287),
        commNtpProvider(288),
        commDnsProvider(289),
        commSyslog(290),
        commSyslogConsole(291),
        commSyslogMonitor(292),
        commSyslogFile(293),
        commSyslogClient(294),
        aaaUserEp(295),
        aaaSystemUser(296),
        aaaEpAuthProfile(297),
        aaaUserLogin(298),
        aaaShellLogin(299),
        aaaWebLogin(300),
        aaaEpLogin(301),
        aaaRemoteUser(302),
        aaaEpUser(303),
        aaaUser(304),
        aaaSshAuth(305),
        aaaUserRole(306),
        aaaRole(307),
        aaaUserLocale(308),
        aaaLocale(309),
        aaaOrg(310),
        aaaSession(311),
        dcxVifEp(312),
        dcxVc(313),
        dcxVIf(314),
        dcxUniverse(315),
        dcxNs(316),
        adaptorFruCapProvider(317),
        adaptorFwCapProvider(318),
        adaptorCapDef(319),
        adaptorCapQual(320),
        adaptorCapSpec(321),
        adaptorQual(322),
        adaptorBehCap(323),
        adaptorLanCap(324),
        adaptorMgmtCap(325),
        adaptorNwMgmtCap(326),
        adaptorHostMgmtCap(327),
        adaptorUnit(328),
        adaptorHostIf(329),
        adaptorHostEthIf(330),
        adaptorHostFcIf(331),
        adaptorExtIf(332),
        adaptorExtEthIf(333),
        adaptorVsan(334),
        adaptorFcOEIf(335),
        adaptorVlan(336),
        adaptorEthPortStats(337),
        adaptorEthPortStatsHist(338),
        adaptorEthPortBySizeSmallStats(341),
        adaptorEthPortBySizeSmallStatsHist(342),
        adaptorEthPortBySizeLargeStats(343),
        adaptorEthPortBySizeLargeStatsHist(344),
        adaptorEthPortOutsizedStats(345),
        adaptorEthPortOutsizedStatsHist(346),
        adaptorEthPortMcastStats(347),
        adaptorEthPortMcastStatsHist(348),
        adaptorEthPortErrStats(349),
        adaptorEthPortErrStatsHist(350),
        adaptorFcPortStats(351),
        adaptorFcPortStatsHist(352),
        adaptorVnicStats(353),
        adaptorVnicStatsHist(354),
        adaptorFcIfFC4Stats(355),
        adaptorFcIfFC4StatsHist(356),
        adaptorMenloBaseErrorStats(357),
        adaptorMenloBaseErrorStatsHist(358),
        adaptorMenloMcpuStats(359),
        adaptorMenloMcpuStatsHist(360),
        adaptorMenloMcpuErrorStats(361),
        adaptorMenloMcpuErrorStatsHist(362),
        adaptorMenloEthStats(363),
        adaptorMenloEthStatsHist(364),
        adaptorMenloEthErrorStats(365),
        adaptorMenloEthErrorStatsHist(366),
        adaptorMenloFcStats(367),
        adaptorMenloFcStatsHist(368),
        adaptorMenloFcErrorStats(369),
        adaptorMenloFcErrorStatsHist(370),
        adaptorMenloQStats(371),
        adaptorMenloQStatsHist(372),
        adaptorMenloQErrorStats(373),
        adaptorMenloQErrorStatsHist(374),
        adaptorMenloNetEgStats(375),
        adaptorMenloNetEgStatsHist(376),
        adaptorMenloNetInStats(377),
        adaptorMenloNetInStatsHist(378),
        adaptorMenloHostPortStats(379),
        adaptorMenloHostPortStatsHist(380),
        adaptorMenloDcePortStats(381),
        adaptorMenloDcePortStatsHist(382),
        adaptorEtherIfStats(383),
        adaptorEtherIfStatsHist(384),
        adaptorFcIfFrameStats(385),
        adaptorFcIfFrameStatsHist(386),
        adaptorFcIfEventStats(387),
        adaptorFcIfEventStatsHist(388),
        adaptorHostIfProfile(389),
        adaptorHostEthIfProfile(390),
        adaptorHostFcIfProfile(391),
        adaptorProfileItem(392),
        adaptorQueueProfile(393),
        adaptorFcLogiProfile(394),
        adaptorEthQueueProfile(395),
        adaptorFcQueueProfile(396),
        adaptorEthWorkQueueProfile(397),
        adaptorEthRecvQueueProfile(398),
        adaptorEthCompQueueProfile(399),
        adaptorEthInterruptProfile(400),
        adaptorRssProfile(401),
        adaptorRssHashProfile(402),
        adaptorTcpIpRssHashProfile(403),
        adaptorIpV4RssHashProfile(404),
        adaptorIpV6RssHashProfile(405),
        adaptorExtIpV6RssHashProfile(406),
        adaptorEthOffloadProfile(407),
        adaptorEthFailoverProfile(408),
        adaptorFcRecvQueueProfile(409),
        adaptorFcWorkQueueProfile(410),
        adaptorFcCdbWorkQueueProfile(411),
        adaptorFcPortFLogiProfile(412),
        adaptorFcPortPLogiProfile(413),
        adaptorFcPortProfile(414),
        adaptorFcErrorRecoveryProfile(415),
        sysfileEp(416),
        sysfileRepository(417),
        sysfileExporter(418),
        sysfileImporter(419),
        sysfileMutation(420),
        sysfileInstance(421),
        sysdebugEp(422),
        sysdebugRepository(423),
        sysdebugCoreFileRepository(424),
        sysdebugExporter(425),
        sysdebugCoreFileExportTarget(426),
        sysdebugAutoCoreFileExportTarget(427),
        sysdebugManualCoreFileExportTarget(428),
        sysdebugFile(429),
        sysdebugCore(430),
        sysdebugLogControlEp(431),
        sysdebugLogControlDomain(432),
        sysdebugLogControlModule(433),
        sysdebugLogControlDestinationFile(434),
        sysdebugLogControlDestinationSyslog(435),
        ruleDefinition(436),
        ruleItem(437),
        ruleRequirement(438),
        ruleSizeRequirement(439),
        swDomain(440),
        swPIoEp(441),
        swCIoEp(442),
        swBorderDomain(443),
        swBorderEp(444),
        swBorderPc(445),
        swLanBorder(446),
        swLanEp(447),
        swLanPc(448),
        swEthLanBorder(449),
        swEthLanEp(450),
        swEthLanPc(451),
        swVlan(452),
        swUlan(453),
        swAccessDomain(454),
        swAccessEp(455),
        swUtilityDomain(456),
        swSanBorder(457),
        swSanEp(458),
        swFcSanBorder(459),
        swFcSanEp(460),
        swVsan(461),
        swEnvStats(462),
        swEnvStatsHist(463),
        swSystemStats(464),
        swSystemStatsHist(465),
        networkruleDefinition(466),
        networkruleItem(467),
        networkruleRequirement(468),
        etherPIo(469),
        etherServerIntFIo(470),
        etherSwitchIntFIo(471),
        etherConfig(472),
        etherIfConfig(473),
        etherSwIfConfig(474),
        etherNicIfConfig(475),
        etherTxStats(476),
        etherTxStatsHist(477),
        etherRxStats(478),
        etherRxStatsHist(479),
        etherErrStats(480),
        etherErrStatsHist(481),
        etherLossStats(482),
        etherLossStatsHist(483),
        syntheticDirectory(484),
        syntheticFile(485),
        syntheticFsObj(486),
        syntheticTime(487),
        syntheticFileSystem(488),
        firmwareCapProvider(489),
        firmwareCatalogue(490),
        firmwareUnit(491),
        firmwareRunning(492),
        firmwareUpdatable(493),
        firmwareBootUnit(494),
        firmwareBootDefinition(495),
        firmwareImage(496),
        firmwareInstallable(497),
        firmwareDistImage(498),
        firmwareDistributable(499),
        firmwareDownloader(500),
        firmwareCompItem(501),
        firmwareCompSource(502),
        firmwareCompTarget(503),
        firmwarePack(504),
        firmwarePackItem(505),
        firmwareComputePack(506),
        firmwareComputeHostPack(507),
        firmwareComputeMgmtPack(508),
        firmwareType(509),
        firmwareDependency(510),
        osInstance(511),
        osAgent(512),
        capabilityCatalogue(513),
        capabilityProvider(514),
        capabilityDef(515),
        capabilityItem(516),
        portGroup(517),
        portPhysSwitchIo(518),
        portPIo(519),
        portIntFIo(520),
        portServerIntFIo(521),
        portSwitchIntFIo(522),
        portDomainEp(523),
        policyObject(524),
        policyHolder(525),
        policyBinding(526),
        policyDefinition(527),
        orgOrg(528),
        callhomeEp(529),
        callhomeSource(530),
        callhomeSmtp(531),
        callhomePeriodicSystemInventory(532),
        callhomeProfile(533),
        callhomeDest(534),
        callhomePolicy(535),
        callhomeTestAlert(536),
        networkEp(537),
        networkIfEp(538),
        networkPhysEp(539),
        networkPIoEp(540),
        networkCIoEp(541),
        networkVnetEp(542),
        networkDomainEp(543),
        networkElement(544),
        networkConn(545),
        networkIfStats(546),
        uuidpoolPool(547),
        uuidpoolPooled(548),
        uuidpoolBlock(549),
        uuidpoolAddr(550),
        uuidpoolFormat(551),
        uuidpoolPoolable(552),
        uuidpoolUniverse(553),
        mgmtEntity(554),
        mgmtBackup(555),
        mgmtImporter(556),
        mgmtAccessPolicy(557),
        mgmtAccessPolicyItem(558),
        mgmtAccessPort(559),
        mgmtIntAuthPolicy(560),
        mgmtController(561),
        mgmtIf(562),
        ippoolPool(563),
        ippoolPooled(564),
        ippoolBlock(565),
        ippoolAddr(566),
        ippoolPoolable(567),
        ippoolUniverse(568),
        poolUniverse(569),
        poolElement(570),
        poolPoolable(571),
        poolPoolMember(572),
        poolPool(573),
        computeConfigPolicy(574),
        computeInitConfigPolicy(575),
        computeAutoconfigPolicy(576),
        computeBladeInheritPolicy(577),
        computeScrubPolicy(578),
        computeDiscPolicy(579),
        computeBladeDiscPolicy(580),
        computeChassisDiscPolicy(581),
        computePsuDef(582),
        computePsuPolicy(583),
        computePsuControl(584),
        computePool(585),
        computePoolable(586),
        computePooled(587),
        computePooledPhysical(588),
        computePooledSlot(589),
        computePoolingPolicy(590),
        computeQual(591),
        computeQualItem(592),
        computeBladePosQual(593),
        computeChassisQual(594),
        computeSlotQual(595),
        computeQualifiedPolicy(596),
        computeContainer(597),
        computeItem(598),
        computePhysical(599),
        computeLogical(600),
        computeVirtualContainer(601),
        computeVirtual(602),
        computePartition(603),
        computeBlade(604),
        computeBoard(605),
        computeMbPowerStats(606),
        computeMbPowerStatsHist(607),
        computeMbTempStats(608),
        computeMbTempStatsHist(609),
        lsTier(614),
        lsServer(615),
        lsPower(616),
        lsComputeBinding(617),
        lsBinding(618),
        lsRequirement(619),
        lsAgentPolicy(620),
        vmEp(621),
        vmInstance(622),
        vmAdaptor(623),
        vmNic(624),
        vmHba(625),
        vmVlan(626),
        vmVsan(627),
        extvmmEp(628),
        extvmmProvider(629),
        fcpoolInitiators(632),
        fcpoolInitiator(633),
        fcpoolBlock(634),
        fcpoolFormat(635),
        fcpoolAddr(636),
        fcpoolPoolable(637),
        fcpoolUniverse(638),
        fcpoolBootTarget(639),
        macpoolPool(640),
        macpoolPooled(641),
        macpoolFormat(642),
        macpoolBlock(643),
        macpoolAddr(644),
        macpoolPoolable(645),
        macpoolUniverse(646),
        solDef(647),
        solConfig(648),
        solPolicy(649),
        solIf(650),
        dpsecMac(651),
        qosclassDefinition(652),
        qosclassItem(653),
        qosclassFc(654),
        qosclassEth(655),
        qosclassEthBE(656),
        qosclassEthClassified(658),
        qosDefinition(659),
        qosItem(660),
        epqosDefinition(661),
        epqosDefinitionDelTask(662),
        epqosItem(663),
        epqosEgress(664),
        equipmentHwCapProvider(665),
        equipmentBehCap(666),
        equipmentFruCapProvider(667),
        equipmentIntegratedComponentCapProvider(668),
        equipmentHolderCapProvider(669),
        equipmentSwitchCapProvider(670),
        equipmentMgmtCapProvider(671),
        equipmentChassisCapProvider(672),
        equipmentBladeCapProvider(673),
        equipmentBaseBoardCapProvider(674),
        equipmentBladeBiosCapProvider(675),
        equipmentLocalDiskCapProvider(676),
        equipmentLocalDiskControllerCapProvider(677),
        equipmentHostIfCapProvider(678),
        equipmentProcessorUnitCapProvider(679),
        equipmentMemoryUnitCapProvider(680),
        equipmentIOCardCapProvider(681),
        equipmentPsuCapProvider(682),
        equipmentFanModuleCapProvider(683),
        equipmentGemCapProvider(684),
        equipmentManufacturingDef(685),
        equipmentPhysicalDef(686),
        equipmentServiceDef(687),
        equipmentAdaptorDef(688),
        equipmentProcessorUnitDef(689),
        equipmentSlotArrayRef(690),
        equipmentSlotArray(691),
        equipmentItem(692),
        equipmentStateful(693),
        equipmentHolder(694),
        equipmentStatefulChComp(695),
        equipmentStatefulBladeComp(696),
        equipmentPsu(697),
        equipmentFanModule(698),
        equipmentFan(699),
        equipmentEnvSensor(700),
        equipmentCard(701),
        equipmentSwitchCard(702),
        equipmentChassis(703),
        equipmentIOCard(704),
        equipmentLed(705),
        equipmentIndicatorLed(706),
        equipmentLocatorLed(707),
        equipmentChassisStats(708),
        equipmentChassisStatsHist(709),
        equipmentPsuStats(712),
        equipmentPsuStatsHist(713),
        equipmentPsuInputStats(714),
        equipmentPsuInputStatsHist(715),
        equipmentFanModuleStats(716),
        equipmentFanModuleStatsHist(717),
        equipmentFanStats(718),
        equipmentFanStatsHist(719),
        flowctrlDefinition(720),
        flowctrlItem(721),
        aaaEpFsmTask(722),
        aaaRealmFsmTask(723),
        aaaUserEpFsmTask(724),
        adaptorHostFcIfFsmTask(725),
        callhomeEpFsmTask(726),
        commSvcEpFsmTask(727),
        computeBladeFsmTask(728),
        epqosDefinitionDelTaskFsmTask(729),
        epqosDefinitionFsmTask(730),
        equipmentChassisFsmTask(731),
        equipmentIOCardFsmTask(732),
        equipmentLocatorLedFsmTask(733),
        extvmmEpFsmTask(734),
        fabricComputeSlotEpFsmTask(737),
        fabricLanCloudFsmTask(738),
        firmwareDownloaderFsmTask(739),
        firmwareImageFsmTask(740),
        mgmtBackupFsmTask(741),
        mgmtControllerFsmTask(742),
        mgmtIfFsmTask(743),
        mgmtImporterFsmTask(744),
        pkiEpFsmTask(745),
        qosclassDefinitionFsmTask(746),
        statsCollectionPolicyFsmTask(747),
        swAccessDomainFsmTask(748),
        swEthLanBorderFsmTask(749),
        swFcSanBorderFsmTask(750),
        swUtilityDomainFsmTask(751),
        syntheticFsObjFsmTask(752),
        sysdebugAutoCoreFileExportTargetFsmTask(753),
        sysdebugLogControlEpFsmTask(754),
        sysdebugManualCoreFileExportTargetFsmTask(755),
        sysfileMutationFsmTask(756),
        vnicProfileSetFsmTask(757),
        vnicDefBeh(758),
        equipmentLocalDiskDef(759),
        sysdebugMEpLog(762),
        adaptorExtEthIfFsmTask(763),
        equipmentIOCardStats(764),
        equipmentIOCardStatsHist(765),
        adaptorHostEthIfFsmTask(766),
        commSnmpUser(767),
        biosBOT(768),
        biosBootDevGrp(769),
        biosBootDev(770),
        etherPauseStats(771),
        etherPauseStatsHist(772),
        adaptorSanCap(773),
        memoryArrayEnvStats(774),
        memoryArrayEnvStatsHist(775),
        memoryUnitEnvStats(776),
        memoryUnitEnvStatsHist(777),
        processorEnvStats(778),
        processorEnvStatsHist(779),
        aaaExtMgmtCutThruTkn(780),
        nwctrlDefinition(781),
        fabricVCon(789),
        fabricVConProfile(790),
        vmCont(793),
        vmDirCont(794),
        vmDCOrg(795),
        vmDC(796),
        vmOrg(797),
        vmSwitch(798),
        vmVnicProfInst(799),
        vmVnicProfCl(800),
        vmVirtual(801),
        vmHv(802),
        extvmmMasterExtKey(803),
        extvmmKeyInst(804),
        extvmmKeyStore(805),
        extvmmKeyRing(806),
        extvmmSwitchDelTask(807),
        biosVfIntelTurboBoostTech(808),
        biosVfEnhancedIntelSpeedStepTech(809),
        biosVfIntelHyperThreadingTech(810),
        biosVfCoreMultiProcessing(811),
        biosVfExecuteDisableBit(812),
        biosVfIntelVirtualizationTechnology(813),
        biosVfIntelVTForDirectedIO(814),
        biosVfDirectCacheAccess(817),
        biosVfSelectMemoryRASConfiguration(818),
        biosVfNUMAOptimized(819),
        biosVfIntelEntrySASRAIDModule(820),
        biosVfOnboardSATAController(822),
        biosVfSerialPortAEnable(823),
        biosVfMaximumMemoryBelow4GB(825),
        biosVfMemoryMappedIOAbove4GB(826),
        biosVfFrontPanelLockout(828),
        biosVfAssertNMIOnSERR(830),
        biosVfAssertNMIOnPERR(831),
        biosVfResumeOnACPowerLoss(832),
        biosVfConsoleRedirection(835),
        biosVfBootOptionRetry(838),
        biosVfQuietBoot(840),
        biosVfPOSTErrorPause(841),
        biosVProfile(842),
        biosVFeat(843),
        powerAGroup(845),
        powerABudget(848),
        powerGroup(849),
        powerBudget(850),
        sysdebugMEpLogDef(851),
        sysdebugMEpLogPolicy(852),
        sysdebugLogBehavior(853),
        sysdebugBackupBehavior(854),
        bmcSELCounter(857),
        computeBehCap(860),
        computePciCap(861),
        extvmmKeyStoreFsmTask(862),
        extvmmProviderFsmTask(863),
        extvmmSwitchDelTaskFsmTask(864),
        biosVfUSBBootConfig(869),
        biosVfProcessorC3Report(870),
        biosVfProcessorC6Report(871),
        biosVfOSBootWatchdogTimer(873),
        biosVfOSBootWatchdogTimerPolicy(874),
        biosVfACPI10Support(876),
        computeMemoryUnitConstraintDef(879),
        computePCIeFatalProtocolStats(882),
        computePCIeFatalReceiveStats(884),
        computePCIeFatalCompletionStats(886),
        computePCIeFatalStats(888),
        vmLifeCyclePolicy(892),
        diagSrvCapProvider(893),
        diagCtrl(894),
        diagRslt(895),
        diagSrvCtrl(896),
        equipmentSwitchCap(897),
        equipmentMemoryUnitDiscoveryModifierDef(898),
        extvmmMasterExtKeyFsmTask(899),
        adaptorFcInterruptProfile(900),
        capabilityEp(901),
        capabilityUpdater(902),
        capabilityUpdate(903),
        equipmentCatalogCapProvider(904),
        capabilityUpdaterFsmTask(905),
        firmwareDistributableFsmTask(906),
        topMetaInf(907),
        storageRaidBattery(908),
        computeRtcBattery(909),
        vmVif(910),
        memoryBufferUnit(912),
        memoryBufferUnitEnvStats(913),
        memoryBufferUnitEnvStatsHist(914),
        computeIOHub(915),
        computeBoardController(916),
        computeIOHubEnvStats(917),
        computeIOHubEnvStatsHist(918),
        diagRunPolicy(919),
        diagTest(920),
        diagBladeTest(921),
        diagNetworkTest(922),
        biosSettings(926),
        computeDefaults(931),
        computePlatform(932),
        capabilityCatalogueFsmTask(933),
        swVlanPortNs(934),
        processorErrorStats(935),
        biosVfSparingMode(936),
        biosVfMirroringMode(937),
        biosVfLvDIMMSupport(938),
        memoryErrorStats(940),
        commXmlClConnPolicy(941),
        computePhysicalQual(942),
        procSvc(943),
        apeDcosAgManager(944),
        apeSwitchFirmwareInv(945),
        equipmentLocalDiskControllerDef(946),
        equipmentBoardControllerDef(947),
        biosARef(948),
        biosRef(949),
        biosFeatureRef(950),
        biosParameterRef(951),
        biosSettingRef(952),
        adaptorDiagCap(953),
        equipmentPOSTCodeContainer(954),
        equipmentPOSTCodeTemplate(955),
        fabricFcVsanPc(956),
        fabricLanMonCloud(957),
        fabricSanMonCloud(958),
        fabricEthMonLan(959),
        fabricFcMonSan(960),
        fabricMon(961),
        fabricEthMon(962),
        fabricFcMon(963),
        fabricMonDestEp(964),
        fabricEthMonDestEp(965),
        fabricFcMonDestEp(966),
        fabricMonSrcEp(967),
        fabricEthMonSrcEp(968),
        fabricFcMonSrcEp(969),
        fabricMonSrcRef(970),
        fabricEthMonSrcRef(971),
        fabricFcMonSrcRef(972),
        fabricMonSrcFiltEp(973),
        fabricEthMonFiltEp(974),
        fabricFcMonFiltEp(975),
        fabricMonFiltRef(976),
        fabricEthMonFiltRef(977),
        fabricFcMonFiltRef(978),
        fabricFcEstcCloud(979),
        fabricEthEstcCloud(980),
        fabricEthVlanPortEp(981),
        fabricVlanEp(982),
        fabricExternalEstc(983),
        fabricFcEstc(984),
        fabricEthEstc(985),
        fabricEstcEp(986),
        fabricAFcEstcEp(987),
        fabricFcEstcEp(988),
        fabricAFcoeEstcEp(989),
        fabricFcoeEstcEp(990),
        fabricEthEstcEp(991),
        fabricTargetEp(992),
        fabricEthTargetEp(993),
        processorUnitAssocCtx(994),
        biosVfUEFIOSUseLegacyVideo(998),
        vnicIpV4AddrConf(999),
        vnicIpV4AddrExplConf(1000),
        vnicIpV4ProfDerivedAddr(1001),
        storageDevice(1002),
        storageDrive(1003),
        aaaConfig(1004),
        aaaAuthMethod(1005),
        aaaDefaultAuth(1006),
        aaaConsoleAuth(1007),
        aaaDomainAuth(1008),
        aaaDomain(1009),
        aaaLdapGroupRule(1010),
        aaaUserGroup(1011),
        aaaLdapGroup(1012),
        aaaProviderGroup(1013),
        aaaProviderRef(1014),
        adaptorHwAddrCap(1015),
        adaptorUplinkHwAddrCap(1016),
        adaptorHostethHwAddrCap(1017),
        adaptorHostfcHwAddrCap(1018),
        adaptorUnitAssocCtx(1019),
        sysdebugTechSupFileRepository(1020),
        sysdebugTechSupport(1021),
        sysdebugTechSupportCmdOpt(1022),
        powerEp(1023),
        powerPrioWght(1024),
        powerPolicy(1025),
        powerPlacement(1026),
        powerGroupAdditionPolicy(1027),
        powerGroupMember(1028),
        powerChassisMember(1029),
        powerRackUnitMember(1030),
        powerGroupQual(1031),
        powerMgmtPolicy(1032),
        powerGroupStats(1033),
        powerGroupStatsHist(1034),
        swMonSrcEp(1035),
        swEthMonSrcEp(1036),
        swFcMonSrcEp(1037),
        swEstcEp(1038),
        swFcEstcEp(1039),
        swEthEstcEp(1040),
        swTargetEp(1041),
        swEthTargetEp(1042),
        swFcoeEstcEp(1043),
        swMonDomain(1044),
        swLanMon(1045),
        swSanMon(1046),
        swEthLanMon(1047),
        swFcSanMon(1048),
        swMon(1049),
        swEthMon(1050),
        swFcMon(1051),
        swMonDestEp(1052),
        swEthMonDestEp(1053),
        swFcMonDestEp(1054),
        swSanPc(1055),
        swFcSanPc(1056),
        capabilityMgmtExtension(1057),
        pciCard(1058),
        pciUnit(1059),
        licenseEp(1060),
        licenseFeature(1061),
        licenseServerHostId(1062),
        licenseFile(1063),
        licenseSource(1064),
        licenseContents(1065),
        licenseFeatureLine(1066),
        licenseInstance(1067),
        licenseSourceFile(1068),
        licenseProp(1069),
        licenseDownloader(1070),
        licenseCapProvider(1071),
        licenseFeatureCapProvider(1072),
        portTrustMode(1073),
        computePoolPolicyRef(1074),
        computePooledRackUnit(1075),
        computePhysicalAssocCtx(1076),
        computeComputeDiscPolicy(1077),
        computeServerDiscPolicy(1078),
        computeRackUnit(1079),
        lsServerAssocCtx(1080),
        lsmaintMaintPolicy(1081),
        lsmaintAck(1082),
        equipmentPicture(1083),
        equipmentMgmtExtCapProvider(1084),
        equipmentRackUnitCapProvider(1085),
        equipmentBladeAGLibrary(1086),
        equipmentFexCapProvider(1087),
        equipmentPciDef(1088),
        equipmentRaidDef(1089),
        equipmentPortGroupDef(1090),
        equipmentAssocCtx(1091),
        equipmentFexEnvStats(1092),
        equipmentFexEnvStatsHist(1093),
        equipmentFexPowerSummary(1094),
        equipmentFexPowerSummaryHist(1095),
        equipmentFexPsuInputStats(1096),
        equipmentFexPsuInputStatsHist(1097),
        equipmentRackUnitPsuStats(1098),
        equipmentRackUnitPsuStatsHist(1099),
        equipmentRackUnitFanStats(1100),
        equipmentRackUnitFanStatsHist(1101),
        equipmentFex(1102),
        dhcpInst(1103),
        dhcpLease(1104),
        dhcpAcquired(1105),
        trigInst(1106),
        trigWindow(1107),
        trigSched(1108),
        trigSchedWindow(1109),
        trigAbsWindow(1110),
        trigRecurrWindow(1111),
        trigMeta(1112),
        trigTriggered(1113),
        trigTriggerable(1114),
        trigTest(1115),
        trigAck(1116),
        trigConfAck(1117),
        trigResAck(1118),
        capabilityMgmtExtensionFsmTask(1119),
        computePhysicalFsmTask(1120),
        computeRackUnitFsmTask(1121),
        equipmentFexFsmTask(1122),
        fabricSanCloudFsmTask(1124),
        licenseDownloaderFsmTask(1125),
        licenseFileFsmTask(1126),
        licenseInstanceFsmTask(1127),
        lsServerFsmTask(1128),
        swEthMonFsmTask(1129),
        swFcMonFsmTask(1130),
        sysdebugTechSupportFsmTask(1131),
        fabricBHVlan(1132),
        imgprovPolicy(1133),
        imgprovTarget(1134),
        imgsecPolicy(1135),
        imgsecKey(1136),
        hostimgPolicy(1137),
        hostimgTarget(1138),
        equipmentGemPortCap(1143),
        equipmentXcvr(1144),
        portPIoFsmTask(1145),
        vnicBootIpPolicy(1146),
        adaptorLldpCap(1147),
        lldpAcquired(1148),
        extmgmtIf(1149),
        extmgmtIfMonPolicy(1150),
        extmgmtMiiStatus(1151),
        extmgmtGatewayPing(1152),
        extmgmtArpTargets(1153),
        biosVfOptionROMLoad(1154),
        firmwareBundleTypeCapProvider(1155),
        firmwareBundleType(1156),
        storageEnclosure(1157),
        sysdebugCoreFsmTask(1158),
        fabricAEthEstcEp(1159),
        fabricEstcPc(1160),
        fabricEthEstcPc(1161),
        fabricEthEstcPcEp(1162),
        fabricEthVlanPc(1163),
        swEthEstcPc(1164),
        commSyslogSource(1165),
        firmwareSpec(1166),
        computeRackUnitMbTempStats(1167),
        computeRackUnitMbTempStatsHist(1168),
        storageLocalDiskSlotEp(1169),
        computeRackPosQual(1170),
        computeRackQual(1171),
        biosVfCPUPerformance(1172),
        fabricFcoeVsanPortEp(1173),
        pciEquipSlot(1174),
        equipmentDbgPluginCapProvider(1175),
        commSvcLimits(1176),
        commShellSvcLimits(1177),
        commWebSvcLimits(1178),
        adaptorFruCapRef(1179),
        biosVfMaxVariableMTRRSetting(1180),
        biosVfUSBSystemIdlePowerOptimizingSetting(1181),
        biosVfUSBFrontPanelAccessLock(1182),
        biosVfFPRMBootOrderRuleControl(1183),
        equipmentLocalDiskControllerCapRef(1184),
        equipmentDiscoveryCap(1185),
        topSysDefaults(1186),
        iqnpoolPool(1187),
        iqnpoolPooled(1188),
        iqnpoolBlock(1189),
        iqnpoolAddr(1190),
        iqnpoolFormat(1191),
        iqnpoolPoolable(1192),
        iqnpoolUniverse(1193),
        fabricSwSrvPc(1194),
        fabricDceSwSrvPc(1195),
        fabricDceSwSrvPcEp(1196),
        fabricEpMgr(1197),
        biosVfProcessorCState(1198),
        biosVfProcessorC1E(1199),
        biosVIdentityParams(1200),
        vnicIPv4IscsiAddr(1201),
        vnicIPv4PooledIscsiAddr(1202),
        vnicVProfileAlias(1203),
        vnicOProfileAlias(1204),
        vnicInternalProfile(1205),
        vnicVlan(1206),
        vnicIScsiNode(1207),
        vnicIScsi(1208),
        vnicIScsiTargetIf(1209),
        vnicIScsiStaticTargetIf(1210),
        vnicLun(1211),
        vnicIScsiAutoTargetIf(1212),
        lsbootIScsi(1213),
        lsbootIScsiImagePath(1214),
        aaaBanner(1215),
        aaaPreLoginBanner(1216),
        aaaPwdProfile(1217),
        aaaUserData(1218),
        adaptorIScsiCap(1219),
        adaptorHostIscsiIfProfile(1220),
        adaptorProtocolProfile(1221),
        adaptorCIoEp(1222),
        adaptorExternalPc(1223),
        adaptorExtIfPc(1224),
        adaptorExtEthIfPc(1225),
        adaptorPIoEp(1226),
        adaptorExternalEp(1227),
        adaptorExtIfEp(1228),
        adaptorExtEthIfPcEp(1229),
        adaptorHostIscsiIf(1230),
        adaptorIscsiTargetIf(1231),
        adaptorIscsiProt(1232),
        adaptorIscsiAuth(1233),
        swPhys(1234),
        swPhysEtherEp(1235),
        swPhysFcEp(1236),
        swVlanPortNsOverride(1237),
        etherPortChanIdElem(1238),
        etherPortChanIdUniverse(1239),
        etherCIoEp(1240),
        etherPc(1241),
        etherInternalPc(1242),
        etherExternalPc(1243),
        etherServerIntFIoPc(1244),
        etherSwitchIntFIoPc(1245),
        etherPIoEp(1246),
        etherExternalEp(1247),
        etherIntFIoEp(1248),
        etherServerIntFIoPcEp(1249),
        etherSwitchIntFIoPcEp(1250),
        mgmtPmonEntry(1251),
        iscsiAuthProfile(1252),
        computeAChassisDiscPolicy(1254),
        computeChassisConnPolicy(1255),
        vmClientContainer(1256),
        vmComputeEp(1257),
        extvmmSwitchSet(1258),
        equipmentUnifiedPortCapProvider(1259),
        equipmentBeaconCapProvider(1260),
        equipmentHDDFaultMonDef(1261),
        equipmentFanModuleDef(1262),
        equipmentPsuDef(1263),
        equipmentPortGroupAggregationDef(1264),
        equipmentPortGroupSwComplexDef(1265),
        equipmentPortSwComplexRef(1266),
        equipmentBeaconLed(1267),
        equipmentPsuOutputStats(1268),
        equipmentPsuOutputStatsHist(1269),
        equipmentNetworkElementFanStats(1270),
        equipmentNetworkElementFanStatsHist(1271),
        equipmentBeaconLedFsmTask(1272),
        fabricEpMgrFsmTask(1273),
        swPhysFsmTask(1274),
        vmLifeCyclePolicyFsmTask(1275),
        firmwareUpgradeConstraint(1276),
        adaptorFamilyTypeDef(1277),
        adaptorUnitExtn(1278),
        biosVfProcessorC7Report(1279),
        biosVfOptionROMEnable(1280),
        biosVfPCISlotOptionROMEnable(1281),
        biosVfPackageCStateLimit(1282),
        lsVersionBeh(1287),
        equipmentBiosDef(1288),
        equipmentDimmMapping(1289),
        equipmentDimmEntry(1290),
        equipmentBladeConnDef(1291),
        equipmentAdaptorConnDef(1292),
        equipmentIOCardTypeDef(1293),
        computePnuOSImage(1294),
        etherServerIntFIoFsmTask(1295),
        equipmentServerFeatureCap(1296),
        equipmentBladeIOMConnDef(1297),
        biosVfOnboardStorage(1298),
        biosVfOSBootWatchdogTimerTimeout(1299),
        fsmFsm(1300),
        fsmStage(1301),
        faultBaseHolder(1302),
        faultLocalTypedHolder(1303),
        faultBasePolicy(1304),
        faultSuppressPolicy(1305),
        faultSuppressPolicyItem(1306),
        faultSuppressTask(1307),
        faultAffectedClass(1308),
        apePaloVnic(1309),
        apeVnicStats(1310),
        apePaloVnicStats(1311),
        vnicConnDef(1312),
        vnicABeh(1313),
        vnicVnicBehPolicy(1314),
        vnicVhbaBehPolicy(1315),
        vnicFcGroupTempl(1316),
        vnicDynamicConPolicyRef(1317),
        vnicSanConnPolicy(1318),
        vnicLanConnPolicy(1319),
        vnicAGroup(1320),
        vnicFcGroupDef(1321),
        vnicIScsiBase(1322),
        vnicIScsiLCP(1323),
        storageADef(1324),
        storageConnectionPolicy(1325),
        storageIniGroup(1326),
        storageInitiator(1327),
        fabricVnetPermit(1328),
        fabricVlanPermit(1329),
        fabricMulticastPolicy(1330),
        biosVfSriovConfig(1331),
        identMetaVerse(1332),
        identMetaSystem(1333),
        identIdentRequest(1334),
        identRequestEp(1335),
        identIdentCtx(1336),
        identSysInfo(1337),
        fcpoolInitiatorEp(1338),
        vnicRackServerDiscoveryProfile(1339),
        vnicIScsiBootParams(1340),
        vnicIScsiBootVnic(1341),
        policyItem(1342),
        versionEp(1343),
        versionVersion(1344),
        versionApplication(1345),
        extpolConnectorContainer(1346),
        extpolEp(1347),
        extpolConnector(1348),
        extpolSvc(1349),
        extpolRegistry(1350),
        extpolProviderCont(1351),
        extpolProvider(1352),
        extpolControllerCont(1353),
        extpolController(1354),
        extpolClientCont(1355),
        extpolClient(1356),
        extpolSystemContext(1357),
        configSorter(1358),
        nfsEp(1359),
        nfsMountDef(1360),
        nfsMountInst(1361),
        storageEp(1362),
        storageNodeEp(1363),
        storageEpUser(1364),
        storageAuthKey(1365),
        storageTransportIf(1366),
        storageTargetIf(1367),
        storageIScsiTargetIf(1368),
        storageFcTargetIf(1369),
        storageL2If(1370),
        storageFcIf(1371),
        storageEtherIf(1372),
        storageSystem(1373),
        ipIpV4Addr(1374),
        ipIPv4Dns(1375),
        ipServiceIf(1376),
        ipIpV4StaticAddr(1377),
        initiatorEp(1378),
        initiatorRequestorEp(1379),
        initiatorGroupEp(1380),
        initiatorInitiatorEp(1381),
        initiatorIScsiInitiatorEp(1382),
        initiatorFcInitiatorEp(1383),
        initiatorStoreEp(1384),
        initiatorUnitEp(1385),
        initiatorLunEp(1386),
        initiatorRequestorGrpEp(1387),
        initiatorMemberEp(1388),
        storageVirtualDrive(1389),
        storageConnectionDef(1390),
        storageTarget(1391),
        storageFcTargetEp(1392),
        storageVsanRef(1393),
        storageDomainEp(1394),
        firmwareBundleInfo(1395),
        firmwareInfraPack(1396),
        firmwareCatalogPack(1397),
        firmwareSystem(1398),
        firmwareInfra(1399),
        firmwareHost(1400),
        firmwareBlade(1401),
        firmwareRack(1402),
        firmwareStatus(1403),
        firmwareSystemCompCheckResult(1404),
        firmwareInstallImpact(1405),
        firmwareHostPackModImpact(1406),
        firmwareAck(1407),
        firmwareUpgradeInfo(1408),
        firmwareUpgradeDetail(1409),
        firmwareBundleInfoDigest(1410),
        commClientItem(1411),
        aaaItem(1412),
        commItem(1413),
        computeServerMgmtPolicy(1414),
        computePciSlotScanDef(1415),
        swCardEnvStats(1416),
        swCardEnvStatsHist(1417),
        swVlanGroup(1418),
        swVlanRef(1419),
        swFcoeSanEp(1420),
        swFcoeSanPc(1421),
        swFcZoneSet(1422),
        swFcServerZoneGroup(1423),
        swZoneInitiatorMember(1424),
        swFcZone(1425),
        swFcZoneMember(1426),
        swZoneTargetMember(1427),
        swFabricZoneNs(1428),
        swFabricZoneNsOverride(1429),
        etherPIoEndPoint(1430),
        etherFcoeInterfaceStats(1431),
        etherFcoeInterfaceStatsHist(1432),
        policyControlEp(1433),
        policyControl(1434),
        policyDateTime(1435),
        policyCommunication(1436),
        policyDns(1437),
        policySecurity(1438),
        policyMonitoring(1439),
        policyFault(1440),
        policyInfraFirmware(1441),
        policyConfigBackup(1442),
        policyMEp(1443),
        policyDiscovery(1444),
        policyPowerMgmt(1445),
        policyPsu(1446),
        policyControlled(1447),
        policyControlledInstance(1448),
        policyControlledType(1449),
        policyPolicyEp(1450),
        policyPolicyScopeCont(1451),
        policyPolicyScopeContext(1452),
        policyPolicyScope(1453),
        policyPolicyRequestor(1454),
        policyDigest(1455),
        fabricAFcoeSanEp(1456),
        fabricFcoeSanEp(1457),
        fabricFcoeSanPcEp(1458),
        fabricFcoeSanPc(1459),
        fabricFcoeVsanPc(1460),
        fabricVsanMembership(1461),
        fabricVnetReq(1462),
        fabricVlanReq(1463),
        fabricVnetGroupReq(1464),
        fabricVlanGroupReq(1465),
        fabricOrgVlanPolicy(1466),
        fabricNetGroup(1467),
        fabricPooledVlan(1468),
        fabricPoolableVlan(1469),
        fabricLanAccessMgr(1470),
        fabricZoneIdUniverse(1471),
        mgmtExportPolicy(1472),
        mgmtCfgExportPolicy(1473),
        mgmtBackupPolicy(1474),
        mgmtConnection(1475),
        callhomeItem(1476),
        capabilityFeatureLimits(1477),
        capabilitySystemLimits(1478),
        capabilityNetworkLimits(1479),
        capabilityStorageLimits(1480),
        observeObservedCont(1481),
        observeObserved(1482),
        observeFilter(1483),
        lsFcLocale(1484),
        lsFcZoneGroup(1485),
        lsZoneInitiatorMember(1486),
        lsFcZone(1487),
        lsFcZoneMember(1488),
        lsZoneTargetMember(1489),
        lsVConAssign(1490),
        trigToken(1491),
        trigClientToken(1492),
        trigBaseSched(1493),
        trigLocalSched(1494),
        trigBaseAbsWindow(1495),
        trigLocalAbsWindow(1496),
        sysfileDigest(1497),
        fsmStatus(1498),
        computeServerDiscPolicyFsmTask(1499),
        extpolEpFsmTask(1500),
        extpolProviderFsmTask(1501),
        extpolRegistryFsmTask(1502),
        firmwareSystemFsmTask(1503),
        identIdentRequestFsmTask(1504),
        identMetaSystemFsmTask(1505),
        mgmtExportPolicyFsmTask(1506),
        nfsMountDefFsmTask(1507),
        nfsMountInstFsmTask(1508),
        observeObservedFsmTask(1509),
        policyControlEpFsmTask(1510),
        policyPolicyScopeFsmTask(1511),
        storageSystemFsmTask(1512),
        aaaEpFsm(1513),
        aaaEpFsmStage(1514),
        aaaLdapEpFsm(1515),
        aaaLdapEpFsmStage(1516),
        aaaRadiusEpFsm(1517),
        aaaRadiusEpFsmStage(1518),
        aaaTacacsPlusEpFsm(1519),
        aaaTacacsPlusEpFsmStage(1520),
        aaaRealmFsm(1521),
        aaaRealmFsmStage(1522),
        aaaAuthRealmFsm(1523),
        aaaAuthRealmFsmStage(1524),
        aaaUserEpFsm(1525),
        aaaUserEpFsmStage(1526),
        adaptorExtEthIfFsm(1527),
        adaptorExtEthIfFsmStage(1528),
        adaptorHostEthIfFsm(1529),
        adaptorHostEthIfFsmStage(1530),
        adaptorHostFcIfFsm(1531),
        adaptorHostFcIfFsmStage(1532),
        callhomeEpFsm(1533),
        callhomeEpFsmStage(1534),
        capabilityCatalogueFsm(1535),
        capabilityCatalogueFsmStage(1536),
        capabilityMgmtExtensionFsm(1537),
        capabilityMgmtExtensionFsmStage(1538),
        capabilityUpdaterFsm(1539),
        capabilityUpdaterFsmStage(1540),
        commSvcEpFsm(1541),
        commSvcEpFsmStage(1542),
        computeBladeFsm(1543),
        computeBladeFsmStage(1544),
        computePhysicalFsm(1545),
        computePhysicalFsmStage(1546),
        computeRackUnitFsm(1547),
        computeRackUnitFsmStage(1548),
        computeServerDiscPolicyFsm(1549),
        computeServerDiscPolicyFsmStage(1550),
        epqosDefinitionDelTaskFsm(1551),
        epqosDefinitionDelTaskFsmStage(1552),
        epqosDefinitionFsm(1553),
        epqosDefinitionFsmStage(1554),
        equipmentBeaconLedFsm(1555),
        equipmentBeaconLedFsmStage(1556),
        equipmentChassisFsm(1557),
        equipmentChassisFsmStage(1558),
        equipmentFexFsm(1559),
        equipmentFexFsmStage(1560),
        equipmentIOCardFsm(1561),
        equipmentIOCardFsmStage(1562),
        equipmentLocatorLedFsm(1563),
        equipmentLocatorLedFsmStage(1564),
        etherServerIntFIoFsm(1565),
        etherServerIntFIoFsmStage(1566),
        extpolEpFsm(1567),
        extpolEpFsmStage(1568),
        extpolProviderFsm(1569),
        extpolProviderFsmStage(1570),
        extpolRegistryFsm(1571),
        extpolRegistryFsmStage(1572),
        extvmmEpFsm(1573),
        extvmmEpFsmStage(1574),
        extvmmKeyStoreFsm(1575),
        extvmmKeyStoreFsmStage(1576),
        extvmmMasterExtKeyFsm(1577),
        extvmmMasterExtKeyFsmStage(1578),
        extvmmProviderFsm(1579),
        extvmmProviderFsmStage(1580),
        extvmmSwitchDelTaskFsm(1581),
        extvmmSwitchDelTaskFsmStage(1582),
        fabricComputeSlotEpFsm(1583),
        fabricComputeSlotEpFsmStage(1584),
        fabricEpMgrFsm(1585),
        fabricEpMgrFsmStage(1586),
        fabricLanCloudFsm(1587),
        fabricLanCloudFsmStage(1588),
        fabricSanCloudFsm(1589),
        fabricSanCloudFsmStage(1590),
        firmwareDistributableFsm(1591),
        firmwareDistributableFsmStage(1592),
        firmwareDownloaderFsm(1593),
        firmwareDownloaderFsmStage(1594),
        firmwareImageFsm(1595),
        firmwareImageFsmStage(1596),
        firmwareSystemFsm(1597),
        firmwareSystemFsmStage(1598),
        identIdentRequestFsm(1599),
        identIdentRequestFsmStage(1600),
        identMetaSystemFsm(1601),
        identMetaSystemFsmStage(1602),
        licenseDownloaderFsm(1603),
        licenseDownloaderFsmStage(1604),
        licenseFileFsm(1605),
        licenseFileFsmStage(1606),
        licenseInstanceFsm(1607),
        licenseInstanceFsmStage(1608),
        lsServerFsm(1609),
        lsServerFsmStage(1610),
        mgmtBackupFsm(1611),
        mgmtBackupFsmStage(1612),
        mgmtControllerFsm(1613),
        mgmtControllerFsmStage(1614),
        mgmtExportPolicyFsm(1615),
        mgmtExportPolicyFsmStage(1616),
        mgmtBackupPolicyFsm(1617),
        mgmtBackupPolicyFsmStage(1618),
        mgmtCfgExportPolicyFsm(1619),
        mgmtCfgExportPolicyFsmStage(1620),
        mgmtIfFsm(1621),
        mgmtIfFsmStage(1622),
        mgmtImporterFsm(1623),
        mgmtImporterFsmStage(1624),
        nfsMountDefFsm(1625),
        nfsMountDefFsmStage(1626),
        nfsMountInstFsm(1627),
        nfsMountInstFsmStage(1628),
        observeObservedFsm(1629),
        observeObservedFsmStage(1630),
        pkiEpFsm(1631),
        pkiEpFsmStage(1632),
        policyControlEpFsm(1633),
        policyControlEpFsmStage(1634),
        policyPolicyScopeFsm(1635),
        policyPolicyScopeFsmStage(1636),
        portPIoFsm(1637),
        portPIoFsmStage(1638),
        etherPIoFsm(1639),
        etherPIoFsmStage(1640),
        fcPIoFsm(1641),
        fcPIoFsmStage(1642),
        qosclassDefinitionFsm(1643),
        qosclassDefinitionFsmStage(1644),
        statsCollectionPolicyFsm(1645),
        statsCollectionPolicyFsmStage(1646),
        storageSystemFsm(1647),
        storageSystemFsmStage(1648),
        swAccessDomainFsm(1649),
        swAccessDomainFsmStage(1650),
        swEthLanBorderFsm(1651),
        swEthLanBorderFsmStage(1652),
        swEthMonFsm(1653),
        swEthMonFsmStage(1654),
        swFcMonFsm(1655),
        swFcMonFsmStage(1656),
        swFcSanBorderFsm(1657),
        swFcSanBorderFsmStage(1658),
        swPhysFsm(1659),
        swPhysFsmStage(1660),
        swUtilityDomainFsm(1661),
        swUtilityDomainFsmStage(1662),
        syntheticFsObjFsm(1663),
        syntheticFsObjFsmStage(1664),
        sysdebugAutoCoreFileExportTargetFsm(1665),
        sysdebugAutoCoreFileExportTargetFsmStage(1666),
        sysdebugCoreFsm(1667),
        sysdebugCoreFsmStage(1668),
        sysdebugLogControlEpFsm(1669),
        sysdebugLogControlEpFsmStage(1670),
        sysdebugManualCoreFileExportTargetFsm(1671),
        sysdebugManualCoreFileExportTargetFsmStage(1672),
        sysdebugTechSupportFsm(1673),
        sysdebugTechSupportFsmStage(1674),
        sysfileMutationFsm(1675),
        sysfileMutationFsmStage(1676),
        vmLifeCyclePolicyFsm(1677),
        vmLifeCyclePolicyFsmStage(1678),
        vnicProfileSetFsm(1679),
        vnicProfileSetFsmStage(1680),
        gmetaEp(1681),
        gmetaHolder(1682),
        gmetaClass(1683),
        gmetaProp(1684),
        gmetaPolicyMapHolder(1685),
        configImpact(1686),
        fabricVnetEpSyncEp(1687),
        fabricChangedObjectRef(1688),
        changeChangedObjectRef(1689),
        lsServerExtension(1690),
        biosVfDramRefreshRate(1691),
        gmetaPolicyMapElement(1692),
        vnicMacHistory(1693),
        vnicWwpnHistory(1694),
        vnicWwnnHistory(1695),
        vnicIqnHistory(1696),
        vnicIpV4History(1697),
        orgSourceMask(1698),
        configImpactResponse(1699),
        configManagedEpImpactResponse(1700),
        storageTransportableFlashModule(1701),
        aaaCimcSession(1702),
        aaaSessionInfoTable(1703),
        aaaSessionInfo(1704),
        computeHealthLedSensorAlarm(1705),
        policyLocalMap(1706),
        policyElement(1707),
        policyRefReq(1708),
        policyCentraleSync(1709),
        networkOperLevel(1710),
        equipmentRackFanModuleDef(1711),
        equipmentFirmwareConstraint(1712),
        equipmentVersionConstraint(1713),
        equipmentHealthLed(1714),
        lsUuidHistory(1715),
        fabricVnetEpSyncEpFsmTask(1716),
        gmetaHolderFsmTask(1717),
        policyControlledTypeFsmTask(1718),
        fabricVnetEpSyncEpFsm(1719),
        fabricVnetEpSyncEpFsmStage(1720),
        gmetaHolderFsm(1721),
        gmetaHolderFsmStage(1722),
        policyControlledTypeFsm(1723),
        policyControlledTypeFsmStage(1724),
        vnicVmqConReq(1725),
        vnicVmqConPolicy(1726),
        vnicVmqConPolicyRef(1727),
        vnicUsnicConReq(1728),
        vnicUsnicConPolicy(1729),
        vnicUsnicConPolicyRef(1730),
        vnicConReq(1731),
        vnicConPolicyRef(1732),
        vnicIpV6Addr(1733),
        vnicIpV6AddrConf(1734),
        vnicIpV6AddrExplConf(1735),
        vnicIpV6StaticAddr(1736),
        vnicIpV4MgmtPooledAddr(1737),
        vnicIpV6MgmtPooledAddr(1738),
        vnicProfileRef(1739),
        storageControllerBase(1740),
        storageFlexFlashController(1741),
        storageLocalDiskBase(1742),
        storageFlexFlashCard(1743),
        storageFlexFlashDrive(1744),
        storageFlexFlashVirtualDrive(1745),
        queryresultItem(1746),
        queryresultUsage(1747),
        queryresultDependency(1748),
        mgmtCimcInterface(1749),
        mgmtInterface(1750),
        mgmtVnet(1751),
        adaptorHostIfConnDef(1752),
        adaptorUsnicConnDef(1753),
        graphicsCard(1754),
        graphicsController(1755),
        swEthLanFlowMon(1756),
        swFlowMonitor(1757),
        swEthLanFlowMonitor(1758),
        swNetflowMonitor(1759),
        swNetflowMonitorRef(1760),
        swFlowRecordDef(1761),
        swEthLanFlowRecordDef(1762),
        swNetflowRecordDef(1763),
        swFlowMonExporter(1764),
        swEthLanFlowMonExporter(1765),
        swNetflowExporter(1766),
        swEthFlowMonSession(1767),
        swNetflowMonSession(1768),
        swNFExporterRef(1769),
        swIpRoute(1770),
        swVirtL3Intf(1771),
        fabricUdldPolicy(1772),
        fabricEthLinkProfile(1773),
        fabricEthLinkPolicy(1774),
        fabricEthUdldPolicy(1775),
        fabricEthCdpPolicy(1776),
        fabricUdldLinkPolicy(1777),
        fabricCdpLinkPolicy(1778),
        swCmclan(1779),
        fabricLinkPolicy(1780),
        domainFeature(1781),
        domainParameter(1782),
        domainServerFeature(1783),
        domainNetworkFeature(1784),
        domainStorageFeature(1785),
        domainEnvironmentFeature(1786),
        domainServerParam(1787),
        domainNetworkParam(1788),
        domainStorageParam(1789),
        domainEnvironmentParam(1790),
        storageOperation(1791),
        lsbootBootSecurity(1792),
        lsbootSan(1793),
        lsbootSanCatSanImage(1794),
        lsbootLocalMediaItem(1795),
        lsbootDefaultLocalImage(1796),
        lsbootUsbFlashStorageImage(1797),
        lsbootLocalHddImage(1798),
        lsbootUsbInternalImage(1799),
        lsbootUsbExternalImage(1800),
        lsbootSanCatSanImagePath(1801),
        biosVfLocalX2Apic(1802),
        biosVfFPRMBootModeControl(1803),
        commCimcWebService(1804),
        lsIssues(1805),
        ippoolIpV6Pooled(1806),
        ippoolIpV6Block(1807),
        ippoolIpV6Addr(1808),
        ipDnsSuffix(1809),
        ipIPv4WinsServer(1810),
        adaptorHostServiceEthIf(1811),
        firmwareAutoSyncPolicy(1812),
        ipIpV4StaticTargetAddr(1813),
        fabricNetflowIPv4Addr(1814),
        fabricFlowMon(1815),
        fabricLanFlowMon(1816),
        fabricEthLanFlowMon(1817),
        fabricNetflowMonSession(1818),
        fabricFlowMonSrcEp(1819),
        fabricLanFlowMonSrcEp(1820),
        fabricEthLanFlowMonSrcEp(1821),
        fabricNetflowMonSrcEp(1822),
        fabricFlowMonSrcRef(1823),
        fabricEthFlowMonSrcRef(1824),
        fabricNetflowMonSrcRef(1825),
        fabricFlowMonExporterProfile(1826),
        fabricFlowMonDefinition(1827),
        fabricFlowMonItem(1828),
        fabricFlowMonitoringCategory(1829),
        fabricEthLanFlowMonitoring(1830),
        fabricEthFlowMonLan(1831),
        fabricFlowMonitor(1832),
        fabricLanFlowMonitor(1833),
        fabricEthLanFlowMonitor(1834),
        fabricNetflowMonitor(1835),
        fabricNetflowMonitorRef(1836),
        fabricFlowMonCollector(1837),
        fabricLanFlowMonCollector(1838),
        fabricEthLanFlowMonCollector(1839),
        fabricNetflowCollector(1840),
        fabricFlowMonExporter(1841),
        fabricLanFlowMonExporter(1842),
        fabricEthLanFlowMonExporter(1843),
        fabricNetflowMonExporter(1844),
        fabricNetflowMonExporterRef(1845),
        fabricNetflowTimeoutPolicy(1846),
        extvmmNetworkSets(1848),
        extvmmVMNetworkSets(1849),
        extvmmFabricNetwork(1850),
        extvmmFabricNetworkDefinition(1851),
        extvmmVMNetworkDefinition(1852),
        extvmmVMNetwork(1853),
        extvmmVMNDRef(1854),
        extvmmUpLinkPP(1855),
        extvmmFNDReference(1856),
        extmgmtNdiscTargets(1857),
        equipmentAdvancedBootOrder(1858),
        equipmentSecureBoot(1859),
        equipmentTpmCapProvider(1860),
        equipmentGraphicsCardCapProvider(1861),
        equipmentGraphicsCardCapRef(1862),
        equipmentSecureController(1863),
        equipmentTpm(1864),
        equipmentDowngradeConstraint(1865),
        computeFwSyncAck(1866),
        computeMemoryConfigPolicy(1867),
        computeMemoryConfiguration(1868),
        mgmtIPv6IfConfig(1869),
        mgmtIPv6Addr(1870),
        mgmtIPv6IfAddr(1871),
        mgmtInbandProfile(1872),
        mgmtProfDerivedInterface(1873),
        extvmmNetworkSetsFsmTask(1874),
        mgmtIPv6IfAddrFsmTask(1875),
        swEthLanFlowMonFsmTask(1876),
        extvmmNetworkSetsFsm(1877),
        extvmmNetworkSetsFsmStage(1878),
        mgmtIPv6IfAddrFsm(1879),
        mgmtIPv6IfAddrFsmStage(1880),
        swEthLanFlowMonFsm(1881),
        swEthLanFlowMonFsmStage(1882),
        vnicIpV6History(1883),
        domainFeatureCont(1884),
        domainServerFeatureCont(1885),
        domainNetworkFeatureCont(1886),
        domainStorageFeatureCont(1887),
        domainEnvironmentFeatureCont(1888),
        equipmentInbandMgmtCap(1889),
        iqnpoolTransportBlock(1890),
        firmwareImageLock(1891),
        firmwareFprcInfo(1892),
        firmwareABundleTypeCapProvider(1893),
        firmwarePlatformBundleTypeCapProvider(1894),
        equipmentIOCardBase(1895),
        equipmentSwitchIOCard(1896),
        equipmentSwitchIOCardCapProvider(1897),
        equipmentPortCap(1898),
        equipmentPowerCapDef(1899),
        equipmentBladeSwitchConnDef(1900),
        equipmentSwitchTypeDef(1901),
        featureDefinition(1902),
        featureProvider(1903),
        featureBaseRef(1904),
        featureDefinitionRef(1905),
        featureDefinitionInstance(1906),
        featureFruCapProviderRef(1907),
        featureFruCapProviderInstance(1908),
        featureContextEp(1909),
        featureProviderInstance(1910),
        swSubGroup(1911),
        powerProfiledPower(1912),
        fabricSubGroup(1913),
        fabricSwSubGroup(1914),
        iqnpoolAbsBlock(1915),
        portSubGroup(1916),
        equipmentIOCardBaseFsmTask(1917),
        equipmentIOCardBaseFsm(1918),
        equipmentIOCardBaseFsmStage(1919),
        equipmentSwitchIOCardFsm(1920),
        equipmentSwitchIOCardFsmStage(1921),
        biosVfInterleaveConfiguration(1922),
        biosVfPCISlotLinkSpeed(1923),
        biosVfAllUSBDevices(1925),
        biosVfUSBPortConfiguration(1926),
        biosVfProcessorPrefetchConfig(1927),
        biosVfScrubPolicies(1928),
        biosVfVGAPriority(1929),
        biosVfFRB2Timer(1930),
        biosVfProcessorEnergyConfiguration(1931),
        biosVfFrequencyFloorOverride(1932),
        biosVfPSTATECoordination(1933),
        biosVfDRAMClockThrottling(1934),
        biosVfQPILinkFrequencySelect(1935),
        adaptorEthArfsProfile(1936),
        storageMezzFlashLife(1937),
        sdSysSecSvc(1938),
        sdAppInstance(1939),
        sdResource(1940),
        sdLogicalDevice(1941),
        sdExternalPortLink(1942),
        sdMac(1943),
        sdSystemMac(1944),
        sdUserMac(1945),
        sdClusterBootstrap(1946),
        sdLdu(1947),
        sdLink(1948),
        sdExternalLduLink(1949),
        sdAppLduLink(1950),
        computeABoard(1953),
        computeExtBoard(1954),
        computeBoardConnector(1955),
        fabricLacpPolicy(1956),
        cimcvmediaItem(1957),
        cimcvmediaMountConfig(1958),
        cimcvmediaMountConfigDef(1959),
        cimcvmediaMountConfigPolicy(1960),
        cimcvmediaMountInfo(1961),
        cimcvmediaActualMountList(1962),
        cimcvmediaActualMountEntry(1963),
        cimcvmediaExtMgmtRuleEntry(1964),
        cimcvmediaConfigMountEntry(1965),
        mgmtBackupExportExtPolicy(1966),
        mgmtBackupPolicyConfig(1967),
        equipmentCimcVmedia(1968),
        equipmentKvmMgmtCap(1969),
        equipmentFlashLife(1970),
        equipmentBladeAggregationCapRef(1971),
        equipmentPhysDevicesPerBoard(1972),
        sysdebugLogExportStatus(1973),
        sysdebugLogExportPolicy(1974),
        computeKvmMgmtPolicy(1975),
        osController(1976),
        smSecSvc(1977),
        smSlot(1978),
        smMonitor(1979),
        smHeartbeat(1980),
        smDiskFileSystem(1981),
        smLDTemplate(1982),
        smTemplateApp(1983),
        smApp(1984),
        smAppInstance(1985),
        smResource(1986),
        smLogicalDevice(1987),
        smExternalPortLink(1989),
        smMac(1990),
        smSystemMac(1991),
        smUserMac(1992),
        smClusterBootstrap(1993),
        dcxFcoeVifEp(1995),
        nhTableHolder(1996),
        nhLinkTable(1997),
        nhLinks(1999),
        nhPortCfg(2002),
        nhMacVlanCfg(2003),
        nhTableHolderFsmTask(2004),
        osControllerFsmTask(2005),
        sdAppInstanceFsmTask(2006),
        sysdebugLogExportPolicyFsmTask(2007),
        nhTableHolderFsm(2008),
        nhTableHolderFsmStage(2009),
        osControllerFsm(2010),
        osControllerFsmStage(2011),
        sdAppInstanceFsm(2012),
        sdAppInstanceFsmStage(2013),
        sysdebugLogExportPolicyFsm(2014),
        sysdebugLogExportPolicyFsmStage(2015),
        topInfoPolicy(2016),
        adaptorEthNVGREProfile(2017),
        adaptorEthVxLANProfile(2018),
        adaptorEthRoCEProfile(2019),
        biosVfTPMSupport(2020),
        biosVfUSBConfiguration(2021),
        biosVfAltitude(2022),
        callhomeAnonymousReporting(2023),
        etherNiErrStats(2024),
        etherNiErrStatsHist(2025),
        firmwareConstraints(2026),
        firmwareConstraint(2027),
        mgmtCimcSecureBoot(2028),
        licenseTarget(2029),
        equipmentUuidFeatureCap(2030),
        policyIdResolvePolicy(2031),
        adaptorHostPort(2032),
        adaptorHostPortCap(2033),
        networkLanNeighbors(2034),
        networkANeighborEntry(2035),
        networkLanNeighborEntry(2036),
        networkSanNeighbors(2037),
        networkSanNeighborEntry(2038),
        storageFlexFlashControllerFsmTask(2039),
        storageFlexFlashControllerFsm(2040),
        storageFlexFlashControllerFsmStage(2041),
        smHeartbeatConfig(2042),
        smMgmtBootstrap(2043),
        smIP(2044),
        smIPV6(2045),
        smKey(2046),
        smEncryptedKey(2047),
        fabricCabling(2048),
        fabricCablingSw(2049),
        fabricBreakout(2050),
        sdMgmtBootstrap(2051),
        sdIP(2052),
        sdIPV6(2053),
        sdKey(2054),
        sdEncryptedKey(2055),
        swPortBreakout(2056),
        swExtUtility(2057),
        sdLduFsmTask(2058),
        swExtUtilityFsmTask(2059),
        sdLduFsm(2060),
        sdLduFsmStage(2061),
        swExtUtilityFsm(2062),
        swExtUtilityFsmStage(2063),
        smPortRequirement(2064),
        smPortSubType(2065),
        smNetMgmtBootstrapValue(2066),
        smAppAttribute(2067),
        smAppAttributeValue(2068),
        applicationCatalogue(2069),
        applicationDownloader(2070),
        rmetaClass(2071),
        rmetaProp(2072),
        rmetaRnComponent(2073),
        nhEcmpIdent(2074),
        nhIpmcIdent(2075),
        nhEndPoint(2076),
        nhSystemMac(2077),
        nhUserMac(2078),
        firmwarePlatformPack(2079),
        firmwarePlatform(2080),
        licenseSmartConfig(2081),
        equipmentBreakOutCapProvider(2082),
        equipmentMaxPortSpeedCapProvider(2083),
        equipmentServerPortCapProvider(2084),
        nhtestUniTest(2085),
        callhomeHttpProxy(2086),
        sdSlot(2087),
        sdNPPortCfg(2088),
        sdNPInterfaceCfg(2089),
        sdNPPortBundleCfg(2090),
        sdAppAttribute(2091),
        sdAppAttributeCtrl(2092),
        sdMgmtInfo(2093),
        sdNetMgmtBootstrap(2094),
        applicationDownloaderFsmTask(2095),
        firmwarePlatformPackFsmTask(2096),
        licenseSmartConfigFsmTask(2097),
        sdAppAttributeCtrlFsmTask(2098),
        sdExternalLduLinkFsmTask(2099),
        sdLogicalDeviceFsmTask(2100),
        sdMgmtInfoFsmTask(2101),
        sdNetMgmtBootstrapFsmTask(2102),
        sdSlotFsmTask(2103),
        smAppFsmTask(2104),
        smSecSvcFsmTask(2105),
        applicationDownloaderFsm(2106),
        applicationDownloaderFsmStage(2107),
        firmwarePlatformPackFsm(2108),
        firmwarePlatformPackFsmStage(2109),
        licenseSmartConfigFsm(2110),
        licenseSmartConfigFsmStage(2111),
        sdAppAttributeCtrlFsm(2112),
        sdAppAttributeCtrlFsmStage(2113),
        sdExternalLduLinkFsm(2114),
        sdExternalLduLinkFsmStage(2115),
        sdLogicalDeviceFsm(2116),
        sdLogicalDeviceFsmStage(2117),
        sdMgmtInfoFsm(2118),
        sdMgmtInfoFsmStage(2119),
        sdNetMgmtBootstrapFsm(2120),
        sdNetMgmtBootstrapFsmStage(2121),
        sdSlotFsm(2122),
        sdSlotFsmStage(2123),
        smAppFsm(2124),
        smAppFsmStage(2125),
        smSecSvcFsm(2126),
        smSecSvcFsmStage(2127),
        swSspMonDomain(2128),
        swSspLanMon(2129),
        swSspEthLanMon(2130),
        swSspMon(2131),
        swSspEthMon(2132),
        swSspEthMonSrcPhyEp(2133),
        swSspEthMonSrcAppLinksEp(2134),
        swSspEthMonSrcAppEp(2135),
        swSspEthMonFilterEp(2136),
        fabricSspLanMonCloud(2137),
        fabricSspMon(2138),
        fabricSspEthMon(2139),
        fabricSspEthMonSrcPhyTopEp(2140),
        fabricSspEthMonSrcAppLinksEp(2141),
        fabricSspEthMonSrcPhyEp(2142),
        fabricSspEthMonSrcPhyAggrEp(2143),
        fabricSspEthMonSrcAppEp(2144),
        fabricSspEthMonFilterEp(2145),
        swSspEthMonFsmTask(2146),
        swSspEthMonFsm(2147),
        swSspEthMonFsmStage(2148),
        sdClusterBootstrapFsmTask(2149),
        sdClusterBootstrapFsm(2150),
        sdClusterBootstrapFsmStage(2151),
        smNetMgmtBootstrapKeyLimits(2152),
        nhLdevItem(2153),
        smCompatibilityMatrix(2154),
        smAppInstanceFsmTask(2155),
        smAppInstanceFsm(2156),
        smAppInstanceFsmStage(2157),
        equipmentFpga(2158),
        ipsecEp(2159),
        ipsecConnection(2160),
        ipsecAuthority(2161),
        ipsecStats(2162),
        ipsecDefinition(2163),
        commFipsConfig(2164),
        commSshc(2165),
        etherFailToWire(2166),
        etherFtwPortPair(2167),
        sdFtwPortPair(2168),
        sdInternalMgmtBootstrap(2169),
        sdUpgradeTask(2170),
        sdInlinePair(2171),
        mgmtImportConfigInfo(2172),
        licenseSmartDebug(2175),
        licenseResvConfig(2176),
        firmwareCspVersion(2177),
        firmwareCspAppList(2178),
        firmwareDistCspBlackList(2179),
        firmwareSupFirmware(2180),
        etherFtwPortPairFsmTask(2181),
        firmwareSupFirmwareFsmTask(2182),
        ipsecEpFsmTask(2183),
        sdLinkFsmTask(2184),
        sdUpgradeTaskFsmTask(2185),
        swSspEthMonSrcPhyEpFsmTask(2187),
        etherFtwPortPairFsm(2188),
        etherFtwPortPairFsmStage(2189),
        firmwareSupFirmwareFsm(2190),
        firmwareSupFirmwareFsmStage(2191),
        ipsecEpFsm(2192),
        ipsecEpFsmStage(2193),
        sdLinkFsm(2194),
        sdLinkFsmStage(2195),
        sdAppLduLinkFsm(2196),
        sdAppLduLinkFsmStage(2197),
        sdUpgradeTaskFsm(2198),
        sdUpgradeTaskFsmStage(2199),
        swSspEthMonSrcPhyEpFsm(2202),
        swSspEthMonSrcPhyEpFsmStage(2203),
        equipmentChPower(2204),
        pkiCertRevoke(2205),
        pkiImporter(2206),
        commSshPubkey(2207),
        commSshPubkeyChain(2208),
        smCloudConnector(2209),
        smBatchHeartbeat(2210),
        smBaseKey(2211),
        smSupportedHardware(2214),
        smConfigIssue(2218),
        sdBaseKey(2219),
        equipmentEpmFpga(2222),
        equipmentChassisEnv(2223),
        equipmentPsuEnv(2224),
        equipmentFanEnv(2225),
        equipmentBladeEnv(2226),
        firmwareValidationStatus(2227),
        commIpBlock(2228),
        commIPv6Block(2229),
        aaaUserLoginInfo(2230),
        aaaLoginRec(2231),
        aaaRoleRec(2232),
        firmwareValidationStatusFsmTask(2233),
        smCloudConnectorFsmTask(2234),
        smLogicalDeviceFsmTask(2235),
        firmwareValidationStatusFsm(2236),
        firmwareValidationStatusFsmStage(2237),
        smCloudConnectorFsm(2238),
        smCloudConnectorFsmStage(2239),
        smLogicalDeviceFsm(2240),
        smLogicalDeviceFsmStage(2241),
        smPreRequisite(2242),
        smHotfix(2243),
        smError(2244),
        sdHotfix(2245),
        sdPortsBundle(2246),
        sdHotfixFsmTask(2247),
        sdPortsBundleFsmTask(2248),
        sdHotfixFsm(2249),
        sdHotfixFsmStage(2250),
        sdPortsBundleFsm(2251),
        sdPortsBundleFsmStage(2252),
        biosTokenFeatureGroup(2253),
        biosTokenParam(2254),
        biosTokenSettings(2255),
        sysdebugAdaptorCoreStats(2256),
        smUnsignedCspLicense(2257),
        smAppRscProfList(2258),
        smAppRscProfile(2259),
        smLicenseFile(2260),
        smLicenseDevice(2261),
        equipmentBladeCapProviderTypeDef(2262),
        equipmentHwCapDerivativeProvider(2263),
        equipmentCapModSpec(2264),
        nhPcIdent(2265),
        nwctrlCardConfig(2266),
        nwctrlPortConfig(2267),
        firmwareRunnable(2268),
        smLicenseFileFsmTask(2269),
        smUnsignedCspLicenseFsmTask(2270),
        smLicenseFileFsm(2271),
        smLicenseFileFsmStage(2272),
        smUnsignedCspLicenseFsm(2273),
        smUnsignedCspLicenseFsmStage(2274),
        commSyslogPlatform(2275),
        fabricSubIf(2276),
        smAutoMacPool(2277),
        smMacItem(2278),
        smAppInfo(2279),
        smAppInstance2(2280),
        nhSubIfCfg(2281),
        nwctrlSubIf(2282),
        sdBasePortLink(2283),
        sdSubPortLink(2284),
        sdSubLduLink(2285),
        smAppInstance2FsmTask(2286),
        sdSubLduLinkFsm(2287),
        sdSubLduLinkFsmStage(2288),
        smAppInstance2Fsm(2289),
        smAppInstance2FsmStage(2290),
        fabricInnerVlanMgr(2291),
        sdAppInstSettingsTask(2292),
        smReplyInterfaceCfg(2293),
        sdAppInstSettingsTaskFsmTask(2295),
        sdAppInstSettingsTaskFsm(2296),
        sdAppInstSettingsTaskFsmStage(2297),
        smHwCrypto(2298),
        aaaUserOldPwd(2299),
        pkiTpAutoImport(2300),
        commTelemetry(2301),
        sdCspMetaCtrl(2302),
        sdPreAllocatedVnic(2303),
        nhXlateItem(2304),
        firmwareVersionIssue(2305),
        commTelemetryFsmTask(2306),
        sdCspMetaCtrlFsmTask(2307),
        commTelemetryFsm(2308),
        commTelemetryFsmStage(2309),
        sdCspMetaCtrlFsm(2310),
        sdCspMetaCtrlFsmStage(2311)
    }

CfprNetworkConfigIssues ::= TEXTUAL-CONVENTION
    STATUS        current
    DESCRIPTION
        ""
    SYNTAX        BITS
    {
        conflictingVlanAccess(0),
        namedVlanInaccessible(1),
        permitUnresolved(2),
        pinningInvalid(3),
        switchVirtualIfCapacity(4),
        unsupportedMulticastPolicy(5),
        vlanPortCapacity(6),
        networkFeatureCapabilityMismatch(7)
    }

CfprNetworkConnectionType ::= TEXTUAL-CONVENTION
    STATUS        current
    DESCRIPTION
        ""
    SYNTAX        BITS
    {
        lan(0),
        san(1),
        ipc(2)
    }

CfprNetworkElementOperability ::= TEXTUAL-CONVENTION
    STATUS        current
    DESCRIPTION
        ""
    SYNTAX        INTEGER
    {
        unknown(0),
        operable(1),
        inoperable(2),
        removed(3)
    }

CfprNetworkIfStatsType ::= TEXTUAL-CONVENTION
    STATUS        current
    DESCRIPTION
        ""
    SYNTAX        INTEGER
    {
        generic(0),
        broadcast(1),
        multicast(2),
        unicast(3),
        total(4)
    }

CfprNetworkIfStatsUnits ::= TEXTUAL-CONVENTION
    STATUS        current
    DESCRIPTION
        ""
    SYNTAX        INTEGER
    {
        raw(0),
        packets(1),
        octets(2)
    }

CfprNetworkIfStatus ::= TEXTUAL-CONVENTION
    STATUS        current
    DESCRIPTION
        ""
    SYNTAX        INTEGER
    {
        unknown(0),
        down(1),
        up(2)
    }

CfprNetworkInventoryStatus ::= TEXTUAL-CONVENTION
    STATUS        current
    DESCRIPTION
        ""
    SYNTAX        BITS
    {
        switchFru(0),
        vlanPortCount(1),
        cardInventory(2),
        ethPortInventory(3),
        fcPortInventory(4),
        mgmtPortInventory(5),
        ethPcInventory(6),
        fcPcInventory(7),
        switchInventory(8),
        xcvrInventory(9),
        remoteEthPortInventory(10),
        vlanCompGrpInventory(11)
    }

CfprNetworkLocale ::= TEXTUAL-CONVENTION
    STATUS        current
    DESCRIPTION
        ""
    SYNTAX        BITS
    {
        server(0),
        chassis(1),
        internal(2),
        external(3)
    }

CfprNetworkPhysEpIfType ::= TEXTUAL-CONVENTION
    STATUS        current
    DESCRIPTION
        ""
    SYNTAX        INTEGER
    {
        unknown(0),
        physical(1),
        aggregation(2),
        virtual(3)
    }

CfprNetworkPortOperState ::= TEXTUAL-CONVENTION
    STATUS        current
    DESCRIPTION
        ""
    SYNTAX        INTEGER
    {
        indeterminate(0),
        up(1),
        adminDown(2),
        linkDown(3),
        failed(4),
        noLicense(5),
        linkUp(6),
        hardwareFailure(7),
        softwareFailure(8),
        errorDisabled(9),
        sfpNotPresent(10),
        udldAggrDown(11)
    }

CfprNetworkPortRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprNetworkPortType ::= TEXTUAL-CONVENTION
    STATUS        current
    DESCRIPTION
        ""
    SYNTAX        INTEGER
    {
        unknown(0),
        physical(1),
        aggregation(2),
        virtual(3)
    }

CfprNetworkSamConfigStatus ::= TEXTUAL-CONVENTION
    STATUS        current
    DESCRIPTION
        ""
    SYNTAX        INTEGER
    {
        unknown(1),
        present(2),
        missing(3)
    }

CfprNetworkSide ::= TEXTUAL-CONVENTION
    STATUS        current
    DESCRIPTION
        ""
    SYNTAX        INTEGER
    {
        left(0),
        right(1)
    }

CfprNetworkSwitchId ::= TEXTUAL-CONVENTION
    STATUS        current
    DESCRIPTION
        ""
    SYNTAX        INTEGER
    {
        none(0),
        a(1),
        b(2)
    }

CfprNetworkTransport ::= TEXTUAL-CONVENTION
    STATUS        current
    DESCRIPTION
        ""
    SYNTAX        BITS
    {
        ether(0),
        dce(1),
        fc(2)
    }

CfprNetworkVlanCountStatus ::= TEXTUAL-CONVENTION
    STATUS        current
    DESCRIPTION
        ""
    SYNTAX        INTEGER
    {
        withinLimit(0),
        aboveLimit(1)
    }

CfprNetworkVnetEpIfType ::= TEXTUAL-CONVENTION
    STATUS        current
    DESCRIPTION
        ""
    SYNTAX        INTEGER
    {
        unknown(0),
        physical(1),
        aggregation(2),
        virtual(3)
    }

CfprNfsClientConfigState ::= TEXTUAL-CONVENTION
    STATUS        current
    DESCRIPTION
        ""
    SYNTAX        INTEGER
    {
        unregistered(0),
        registered(1),
        configured(2),
        failed(3)
    }

CfprNfsDefAdminState ::= TEXTUAL-CONVENTION
    STATUS        current
    DESCRIPTION
        ""
    SYNTAX        INTEGER
    {
        disabled(0),
        enabled(1),
        suspended(2)
    }

CfprNfsMntAdminState ::= TEXTUAL-CONVENTION
    STATUS        current
    DESCRIPTION
        ""
    SYNTAX        INTEGER
    {
        none(0),
        unmount(1),
        mount(2),
        remount(3)
    }

CfprNfsMntOperState ::= TEXTUAL-CONVENTION
    STATUS        current
    DESCRIPTION
        ""
    SYNTAX        INTEGER
    {
        unmounted(0),
        mounted(1)
    }

CfprNfsMountDefFsmCurrentFsm ::= TEXTUAL-CONVENTION
    STATUS        current
    DESCRIPTION
        ""
    SYNTAX        INTEGER
    {
        nop(0),
        reportNfsMountSuspend(1299)
    }

CfprNfsMountDefFsmStageName ::= TEXTUAL-CONVENTION
    STATUS        current
    DESCRIPTION
        ""
    SYNTAX        INTEGER
    {
        nop(0),
        reportNfsMountSuspendBegin(1299),
        reportNfsMountSuspendReport(1300),
        reportNfsMountSuspendFail(1416),
        reportNfsMountSuspendSuccess(1417)
    }

CfprNfsMountDefFsmTaskItem ::= TEXTUAL-CONVENTION
    STATUS        current
    DESCRIPTION
        ""
    SYNTAX        INTEGER
    {
        nop(0),
        reportNfsMountSuspend(1299)
    }

CfprNfsMountInstFsmCurrentFsm ::= TEXTUAL-CONVENTION
    STATUS        current
    DESCRIPTION
        ""
    SYNTAX        INTEGER
    {
        nop(0),
        mount(1291),
        unmount(1296)
    }

CfprNfsMountInstFsmStageName ::= TEXTUAL-CONVENTION
    STATUS        current
    DESCRIPTION
        ""
    SYNTAX        INTEGER
    {
        nop(0),
        mountBegin(1291),
        mountRegisterClient(1292),
        mountVerifyRegistration(1293),
        mountMountLocal(1294),
        mountMountPeer(1295),
        unmountBegin(1296),
        unmountUnmountLocal(1297),
        unmountUnmountPeer(1298),
        mountFail(1418),
        mountSuccess(1419),
        unmountFail(1420),
        unmountSuccess(1421)
    }

CfprNfsMountInstFsmTaskItem ::= TEXTUAL-CONVENTION
    STATUS        current
    DESCRIPTION
        ""
    SYNTAX        INTEGER
    {
        nop(0),
        mount(1291),
        unmount(1296)
    }

CfprNfsPurpose ::= TEXTUAL-CONVENTION
    STATUS        current
    DESCRIPTION
        ""
    SYNTAX        INTEGER
    {
        image(0),
        backup(1)
    }

CfprNhConfMode ::= TEXTUAL-CONVENTION
    STATUS        current
    DESCRIPTION
        ""
    SYNTAX        INTEGER
    {
        ok(0),
        config(1),
        unconfig(2),
        error(3),
        fail(4)
    }

CfprNhEpIdType ::= TEXTUAL-CONVENTION
    STATUS        current
    DESCRIPTION
        ""
    SYNTAX        INTEGER
    {
        intf(1),
        lbgBlade(2),
        lbgClust(3),
        bcg(4),
        flg(5)
    }

CfprNhEpType ::= TEXTUAL-CONVENTION
    STATUS        current
    DESCRIPTION
        ""
    SYNTAX        INTEGER
    {
        ingress(1),
        egress(2),
        pcGrp(3)
    }

CfprNhExecState ::= TEXTUAL-CONVENTION
    STATUS        current
    DESCRIPTION
        ""
    SYNTAX        INTEGER
    {
        ready(0),
        init(1),
        run(2),
        verify(3)
    }

CfprNhLbHashType ::= TEXTUAL-CONVENTION
    STATUS        current
    DESCRIPTION
        ""
    SYNTAX        INTEGER
    {
        none(0),
        symmetric(1)
    }

CfprNhLinkType ::= TEXTUAL-CONVENTION
    STATUS        current
    DESCRIPTION
        ""
    SYNTAX        INTEGER
    {
        unicast(1),
        bcast(2)
    }

CfprNhMacVlanType ::= TEXTUAL-CONVENTION
    STATUS        current
    DESCRIPTION
        ""
    SYNTAX        INTEGER
    {
        normal(0),
        miss(1),
        ucAll(2),
        mcAll(3),
        macAll(4),
        fpmac(5)
    }

CfprNhPortType ::= TEXTUAL-CONVENTION
    STATUS        current
    DESCRIPTION
        ""
    SYNTAX        INTEGER
    {
        phy(0),
        pch(1),
        vif(2)
    }

CfprNhSSAPortType ::= TEXTUAL-CONVENTION
    STATUS        current
    DESCRIPTION
        ""
    SYNTAX        INTEGER
    {
        data(0),
        mgmt(1),
        cluster(2),
        firepowerEventing(3),
        virtualData(4),
        mtMgmt(6),
        shared(7)
    }

CfprNhTableHolderSysInitReady ::= TEXTUAL-CONVENTION
    STATUS        current
    DESCRIPTION
        ""
    SYNTAX        BITS
    {
        eth(0)
    }

CfprNhTableHolderFsmCurrentFsm ::= TEXTUAL-CONVENTION
    STATUS        current
    DESCRIPTION
        ""
    SYNTAX        INTEGER
    {
        nop(0),
        configureLinks(1650),
        bootstrapLinks(1718)
    }

CfprNhTableHolderFsmStageName ::= TEXTUAL-CONVENTION
    STATUS        current
    DESCRIPTION
        ""
    SYNTAX        INTEGER
    {
        nop(0),
        configureLinksBegin(1650),
        configureLinksApplyConfig(1651),
        configureLinksVerifyLinkConfig(1652),
        configureLinksFail(1655),
        configureLinksSuccess(1656),
        configureLinksConfigInterface(1717),
        bootstrapLinksBegin(1718),
        bootstrapLinksApplyConfig(1719),
        bootstrapLinksFail(1790),
        bootstrapLinksSuccess(1791)
    }

CfprNhTableHolderFsmTaskItem ::= TEXTUAL-CONVENTION
    STATUS        current
    DESCRIPTION
        ""
    SYNTAX        INTEGER
    {
        nop(0),
        configureLinks(1650),
        bootstrapLinks(1718)
    }

CfprNhTableType ::= TEXTUAL-CONVENTION
    STATUS        current
    DESCRIPTION
        ""
    SYNTAX        INTEGER
    {
        data(1),
        ctrl(2)
    }

CfprNhTpHashType ::= TEXTUAL-CONVENTION
    STATUS        current
    DESCRIPTION
        ""
    SYNTAX        INTEGER
    {
        normal(0),
        twoTuple(1)
    }

CfprNhtestTestState ::= TEXTUAL-CONVENTION
    STATUS        current
    DESCRIPTION
        ""
    SYNTAX        INTEGER
    {
        ready(0),
        config(1),
        abort(2),
        unconfig(3),
        portmac(4),
        clean(5),
        delld(6),
        allocip(7),
        freeip(8)
    }

CfprNwctrlAdminState ::= TEXTUAL-CONVENTION
    STATUS        current
    DESCRIPTION
        ""
    SYNTAX        INTEGER
    {
        disabled(0),
        enabled(1)
    }

CfprNwctrlCardAction ::= TEXTUAL-CONVENTION
    STATUS        current
    DESCRIPTION
        ""
    SYNTAX        INTEGER
    {
        none(0),
        ack(1)
    }

CfprNwctrlConfigState ::= TEXTUAL-CONVENTION
    STATUS        current
    DESCRIPTION
        ""
    SYNTAX        INTEGER
    {
        ok(0),
        mismatch(1)
    }

CfprNwctrlLinkFailAction ::= TEXTUAL-CONVENTION
    STATUS        current
    DESCRIPTION
        ""
    SYNTAX        INTEGER
    {
        linkDown(0),
        warning(1)
    }

CfprNwctrlLldpAdminStateBitmask ::= TEXTUAL-CONVENTION
    STATUS        current
    DESCRIPTION
        ""
    SYNTAX        BITS
    {
        transmit(0),
        receive(1)
    }

CfprNwctrlOirState ::= TEXTUAL-CONVENTION
    STATUS        current
    DESCRIPTION
        ""
    SYNTAX        INTEGER
    {
        none(0),
        add(1),
        del(2)
    }

CfprNwctrlRegistrationMode ::= TEXTUAL-CONVENTION
    STATUS        current
    DESCRIPTION
        ""
    SYNTAX        INTEGER
    {
        onlyNativeVlan(0),
        allHostVlans(1)
    }

CfprObserveObservedFsmCurrentFsm ::= TEXTUAL-CONVENTION
    STATUS        current
    DESCRIPTION
        ""
    SYNTAX        INTEGER
    {
        nop(0),
        resolvePolicyFsm(1376),
        resolveResourceFsm(1378),
        resolveVMFsm(1380),
        resolveControllerFsm(1382)
    }

CfprObserveObservedFsmStageName ::= TEXTUAL-CONVENTION
    STATUS        current
    DESCRIPTION
        ""
    SYNTAX        INTEGER
    {
        nop(0),
        resolvePolicyFsmBegin(1376),
        resolvePolicyFsmExecute(1377),
        resolveResourceFsmBegin(1378),
        resolveResourceFsmExecute(1379),
        resolveVMFsmBegin(1380),
        resolveVMFsmExecute(1381),
        resolveControllerFsmBegin(1382),
        resolveControllerFsmExecute(1383),
        resolveControllerFsmFail(1422),
        resolveControllerFsmSuccess(1423),
        resolvePolicyFsmFail(1424),
        resolvePolicyFsmSuccess(1425),
        resolveResourceFsmFail(1426),
        resolveResourceFsmSuccess(1427),
        resolveVMFsmFail(1428),
        resolveVMFsmSuccess(1429)
    }

CfprObserveObservedFsmTaskItem ::= TEXTUAL-CONVENTION
    STATUS        current
    DESCRIPTION
        ""
    SYNTAX        INTEGER
    {
        nop(0),
        resolvePolicyFsm(1376),
        resolveResourceFsm(1378),
        resolveVMFsm(1380),
        resolveControllerFsm(1382)
    }

CfprOrgLevel ::= TEXTUAL-CONVENTION
    STATUS        current
    DESCRIPTION
        ""
    SYNTAX        INTEGER
    {
        root(0),
        n1(1),
        n2(2),
        n3(3),
        n4(4),
        n5(5)
    }

CfprOrgSrcMask ::= TEXTUAL-CONVENTION
    STATUS        current
    DESCRIPTION
        ""
    SYNTAX        BITS
    {
        local(0),
        global(1)
    }

CfprOsBootingUpType ::= TEXTUAL-CONVENTION
    STATUS        current
    DESCRIPTION
        ""
    SYNTAX        INTEGER
    {
        outOfService(0),
        bootingUp(1),
        inService(2),
        failure(3)
    }

CfprOsControllerBootMode ::= TEXTUAL-CONVENTION
    STATUS        current
    DESCRIPTION
        ""
    SYNTAX        INTEGER
    {
        normal(0),
        local(1),
        mio(2)
    }

CfprOsControllerFormatDisk ::= TEXTUAL-CONVENTION
    STATUS        current
    DESCRIPTION
        ""
    SYNTAX        INTEGER
    {
        noOp(0),
        quickFormat(1),
        secureErase(2)
    }

CfprOsControllerFsmCurrentFsm ::= TEXTUAL-CONVENTION
    STATUS        current
    DESCRIPTION
        ""
    SYNTAX        INTEGER
    {
        nop(0),
        deployOS(1640),
        upgradeOS(1729),
        initOS(1735),
        installLicense(1974)
    }

CfprOsControllerFsmStageName ::= TEXTUAL-CONVENTION
    STATUS        current
    DESCRIPTION
        ""
    SYNTAX        INTEGER
    {
        nop(0),
        deployOSBegin(1640),
        deployOSHostPrepareBoot(1641),
        deployOSHostWaitForRommonReady(1642),
        deployOSHostCheckRommonReady(1643),
        deployOSHostCheckUpgradeImageStatus(1644),
        deployOSSuccess(1648),
        deployOSFail(1649),
        deployOSHostPrepareKeyFile(1725),
        deployOSHostWaitForRommonValidateImage(1726),
        deployOSHostCheckImageValidationStatus(1727),
        deployOSHostWaitForSspOsRunning(1728),
        upgradeOSBegin(1729),
        upgradeOSRequestToUpgrade(1730),
        upgradeOSHostWaitForUpgradeComplete(1731),
        upgradeOSRebootHostAfterUpgrade(1732),
        upgradeOSSuccess(1733),
        upgradeOSFail(1734),
        initOSBegin(1735),
        initOSHostPrepareBoot(1736),
        initOSRequestToUpgrade(1737),
        initOSHostWaitForUpgradeComplete(1738),
        initOSRebootHostAfterUpgrade(1739),
        initOSSuccess(1740),
        initOSFail(1741),
        installLicenseBegin(1974),
        installLicenseRequestToUninstallLicense(1975),
        installLicenseRequestToInstallLicense(1976),
        installLicenseWaitForLicInstalledComplete(1977),
        installLicenseSuccess(1978),
        installLicenseFail(1979),
        initOSRequestToInstallLicense(1980),
        initOSHostWaitForLicInstalledComplete(1981)
    }

CfprOsControllerFsmTaskFlags ::= TEXTUAL-CONVENTION
    STATUS        current
    DESCRIPTION
        ""
    SYNTAX        BITS
    {
        samDmeOsControllerDeployOSOsInstall(17),
        samDmeOsControllerUpgradeOSOsUpgrade(18),
        samDmeOsControllerUpgradeOSOsReboot(21),
        samDmeOsControllerInstallLicenseOsInstallLicense(29),
        samDmeOsControllerInstallLicenseOsUninstallLicense(30)
    }

CfprOsControllerFsmTaskItem ::= TEXTUAL-CONVENTION
    STATUS        current
    DESCRIPTION
        ""
    SYNTAX        INTEGER
    {
        nop(0),
        deployOS(1640),
        upgradeOS(1729),
        initOS(1735),
        installLicense(1974)
    }

CfprOsDeployState ::= TEXTUAL-CONVENTION
    STATUS        current
    DESCRIPTION
        ""
    SYNTAX        INTEGER
    {
        undefined(0),
        inProgress(1),
        complete(2),
        retry(3),
        failed(4),
        throttled(5)
    }

CfprOsInitState ::= TEXTUAL-CONVENTION
    STATUS        current
    DESCRIPTION
        ""
    SYNTAX        INTEGER
    {
        undefined(0),
        inProgress(1),
        complete(2),
        retry(3),
        failed(4),
        throttled(5)
    }

CfprOsInstallLicenseState ::= TEXTUAL-CONVENTION
    STATUS        current
    DESCRIPTION
        ""
    SYNTAX        INTEGER
    {
        undefined(0),
        inProgress(1),
        complete(2),
        retry(3),
        failed(4),
        throttled(5)
    }

CfprOsOsMode ::= TEXTUAL-CONVENTION
    STATUS        current
    DESCRIPTION
        ""
    SYNTAX        INTEGER
    {
        normal(0),
        failsafe(1)
    }

CfprOsOsType ::= TEXTUAL-CONVENTION
    STATUS        current
    DESCRIPTION
        ""
    SYNTAX        INTEGER
    {
        unspecified(0),
        pnuOS(1),
        linux(2),
        windows(3),
        solaris(4),
        vmwareESX(5),
        sspOS(6)
    }

CfprOsUpgradeReturnCode ::= TEXTUAL-CONVENTION
    STATUS        current
    DESCRIPTION
        ""
    SYNTAX        INTEGER
    {
        null(0),
        requesting(1),
        successful(2),
        downloading(3),
        validating(4),
        failedComm(5),
        failedDownloading(6),
        failedValidation(7)
    }

CfprOsUpgradeState ::= TEXTUAL-CONVENTION
    STATUS        current
    DESCRIPTION
        ""
    SYNTAX        INTEGER
    {
        undefined(0),
        inProgress(1),
        complete(2),
        retry(3),
        failed(4),
        throttled(5)
    }

CfprPciEquipSlotId ::= TEXTUAL-CONVENTION
    STATUS        current
    DESCRIPTION
        ""
    SYNTAX        Gauge32 (1..5000)

CfprPkiCertRevokeMethod ::= TEXTUAL-CONVENTION
    STATUS        current
    DESCRIPTION
        ""
    SYNTAX        INTEGER
    {
        metinvalid(0),
        crl(1)
    }

CfprPkiCertStatus ::= TEXTUAL-CONVENTION
    STATUS        current
    DESCRIPTION
        ""
    SYNTAX        INTEGER
    {
        valid(0),
        expired(1),
        revoked(2),
        notYetValid(3),
        emptyCert(4),
        unknown(5),
        failedToVerifyWithTp(6),
        failedToVerifyWithPrivateKey(7),
        certChainTooLong(8),
        selfSignedCertificate(9)
    }

CfprPkiEc ::= TEXTUAL-CONVENTION
    STATUS        current
    DESCRIPTION
        ""
    SYNTAX        INTEGER
    {
        ecinvalid(0),
        secp256r1(1),
        secp384r1(2),
        secp521r1(3)
    }

CfprPkiEpFsmCurrentFsm ::= TEXTUAL-CONVENTION
    STATUS        current
    DESCRIPTION
        ""
    SYNTAX        INTEGER
    {
        nop(0),
        updateEp(206)
    }

CfprPkiEpFsmStageName ::= TEXTUAL-CONVENTION
    STATUS        current
    DESCRIPTION
        ""
    SYNTAX        INTEGER
    {
        nop(0),
        updateEpBegin(206),
        updateEpSetKeyRingLocal(207),
        updateEpSetKeyRingPeer(208),
        updateEpFail(428),
        updateEpSuccess(429),
        updateEpPostSetKeyRingLocal(1493),
        updateEpPostSetKeyRingPeer(1494)
    }

CfprPkiEpFsmTaskItem ::= TEXTUAL-CONVENTION
    STATUS        current
    DESCRIPTION
        ""
    SYNTAX        INTEGER
    {
        nop(0),
        updateEp(206)
    }

CfprPkiImportActivity ::= TEXTUAL-CONVENTION
    STATUS        current
    DESCRIPTION
        ""
    SYNTAX        INTEGER
    {
        restart(0),
        idle(1)
    }

CfprPkiKeyringState ::= TEXTUAL-CONVENTION
    STATUS        current
    DESCRIPTION
        ""
    SYNTAX        INTEGER
    {
        started(1),
        created(2),
        reqCreated(3),
        tpSet(4),
        completed(5)
    }

CfprPkiModulus ::= TEXTUAL-CONVENTION
    STATUS        current
    DESCRIPTION
        ""
    SYNTAX        INTEGER
    {
        modinvalid(0),
        mod1536(1536),
        mod2048(2048),
        mod2560(2560),
        mod3072(3072),
        mod3584(3584),
        mod4096(4096)
    }

CfprPkiTpAutoImportImportControlStatus ::= TEXTUAL-CONVENTION
    STATUS        current
    DESCRIPTION
        ""
    SYNTAX        INTEGER
    {
        disabled(0),
        enabled(1)
    }

CfprPkiTransferState ::= TEXTUAL-CONVENTION
    STATUS        current
    DESCRIPTION
        ""
    SYNTAX        INTEGER
    {
        init(0),
        downloading(1),
        downloaded(2),
        failed(3)
    }

CfprPkiTransport ::= TEXTUAL-CONVENTION
    STATUS        current
    DESCRIPTION
        ""
    SYNTAX        INTEGER
    {
        ftp(0),
        tftp(1),
        scp(2),
        sftp(3),
        local(4),
        usbA(5),
        usbB(6),
        https(11),
        http(12)
    }

CfprPkiTransportNoLocal ::= TEXTUAL-CONVENTION
    STATUS        current
    DESCRIPTION
        ""
    SYNTAX        INTEGER
    {
        ftp(0),
        tftp(1),
        scp(2),
        sftp(3),
        usbA(5),
        usbB(6)
    }

CfprPkiType ::= TEXTUAL-CONVENTION
    STATUS        current
    DESCRIPTION
        ""
    SYNTAX        INTEGER
    {
        rsa(1),
        ecdsa(2)
    }

CfprPolicyCleanupMode ::= TEXTUAL-CONVENTION
    STATUS        current
    DESCRIPTION
        ""
    SYNTAX        INTEGER
    {
        localizeGlobal(0),
        deepRemoveGlobal(1)
    }

CfprPolicyControlSource ::= TEXTUAL-CONVENTION
    STATUS        current
    DESCRIPTION
        ""
    SYNTAX        INTEGER
    {
        local(0),
        policy(1),
        pendingPolicy(2)
    }

CfprPolicyControlEpFsmCurrentFsm ::= TEXTUAL-CONVENTION
    STATUS        current
    DESCRIPTION
        ""
    SYNTAX        INTEGER
    {
        nop(0),
        operate(1340)
    }

CfprPolicyControlEpFsmStageName ::= TEXTUAL-CONVENTION
    STATUS        current
    DESCRIPTION
        ""
    SYNTAX        INTEGER
    {
        nop(0),
        operateBegin(1340),
        operateResolve(1341),
        operateFail(1430),
        operateSuccess(1431)
    }

CfprPolicyControlEpFsmTaskItem ::= TEXTUAL-CONVENTION
    STATUS        current
    DESCRIPTION
        ""
    SYNTAX        INTEGER
    {
        nop(0),
        operate(1340)
    }

CfprPolicyControlEpType ::= TEXTUAL-CONVENTION
    STATUS        current
    DESCRIPTION
        ""
    SYNTAX        INTEGER
    {
        policy(0)
    }

CfprPolicyControlledTypeFsmCurrentFsm ::= TEXTUAL-CONVENTION
    STATUS        current
    DESCRIPTION
        ""
    SYNTAX        INTEGER
    {
        nop(0),
        operate(1479)
    }

CfprPolicyControlledTypeFsmStageName ::= TEXTUAL-CONVENTION
    STATUS        current
    DESCRIPTION
        ""
    SYNTAX        INTEGER
    {
        nop(0),
        operateBegin(1479),
        operateResolveAll(1480),
        operateFail(1489),
        operateSuccess(1490)
    }

CfprPolicyControlledTypeFsmTaskItem ::= TEXTUAL-CONVENTION
    STATUS        current
    DESCRIPTION
        ""
    SYNTAX        INTEGER
    {
        nop(0),
        operate(1479)
    }

CfprPolicyIdResolvePolicyType ::= TEXTUAL-CONVENTION
    STATUS        current
    DESCRIPTION
        ""
    SYNTAX        INTEGER
    {
        noDuplicateCheck(0),
        looseDuplicateCheck(1),
        strictDuplicateCheck(2)
    }

CfprPolicyPolicyOperStatus ::= TEXTUAL-CONVENTION
    STATUS        current
    DESCRIPTION
        ""
    SYNTAX        INTEGER
    {
        ok(0),
        resolved(1),
        released(2)
    }

CfprPolicyPolicyOwner ::= TEXTUAL-CONVENTION
    STATUS        current
    DESCRIPTION
        ""
    SYNTAX        INTEGER
    {
        local(0),
        policy(1),
        pendingPolicy(2)
    }

CfprPolicyPolicyResolveType ::= TEXTUAL-CONVENTION
    STATUS        current
    DESCRIPTION
        ""
    SYNTAX        INTEGER
    {
        name(0),
        rn(1)
    }

CfprPolicyPolicyScopeFsmCurrentFsm ::= TEXTUAL-CONVENTION
    STATUS        current
    DESCRIPTION
        ""
    SYNTAX        INTEGER
    {
        nop(0),
        releasePolicyFsm(1342),
        releaseOperationFsm(1344),
        releaseStorageFsm(1346),
        resolveManyPolicyFsm(1348),
        resolveManyOperationFsm(1350),
        resolveManyStorageFsm(1352),
        releaseManyPolicyFsm(1354),
        releaseManyOperationFsm(1356),
        releaseManyStorageFsm(1358),
        resolveAllPolicyFsm(1360),
        resolveAllOperationFsm(1362),
        resolveAllStorageFsm(1364),
        releaseAllPolicyFsm(1366),
        releaseAllOperationFsm(1368),
        releaseAllStorageFsm(1370)
    }

CfprPolicyPolicyScopeFsmStageName ::= TEXTUAL-CONVENTION
    STATUS        current
    DESCRIPTION
        ""
    SYNTAX        INTEGER
    {
        nop(0),
        releasePolicyFsmBegin(1342),
        releasePolicyFsmRelease(1343),
        releaseOperationFsmBegin(1344),
        releaseOperationFsmRelease(1345),
        releaseStorageFsmBegin(1346),
        releaseStorageFsmRelease(1347),
        resolveManyPolicyFsmBegin(1348),
        resolveManyPolicyFsmResolveMany(1349),
        resolveManyOperationFsmBegin(1350),
        resolveManyOperationFsmResolveMany(1351),
        resolveManyStorageFsmBegin(1352),
        resolveManyStorageFsmResolveMany(1353),
        releaseManyPolicyFsmBegin(1354),
        releaseManyPolicyFsmReleaseMany(1355),
        releaseManyOperationFsmBegin(1356),
        releaseManyOperationFsmReleaseMany(1357),
        releaseManyStorageFsmBegin(1358),
        releaseManyStorageFsmReleaseMany(1359),
        resolveAllPolicyFsmBegin(1360),
        resolveAllPolicyFsmResolveAll(1361),
        resolveAllOperationFsmBegin(1362),
        resolveAllOperationFsmResolveAll(1363),
        resolveAllStorageFsmBegin(1364),
        resolveAllStorageFsmResolveAll(1365),
        releaseAllPolicyFsmBegin(1366),
        releaseAllPolicyFsmReleaseAll(1367),
        releaseAllOperationFsmBegin(1368),
        releaseAllOperationFsmReleaseAll(1369),
        releaseAllStorageFsmBegin(1370),
        releaseAllStorageFsmReleaseAll(1371),
        releaseAllOperationFsmFail(1432),
        releaseAllOperationFsmSuccess(1433),
        releaseAllPolicyFsmFail(1434),
        releaseAllPolicyFsmSuccess(1435),
        releaseAllStorageFsmFail(1436),
        releaseAllStorageFsmSuccess(1437),
        releaseManyOperationFsmFail(1438),
        releaseManyOperationFsmSuccess(1439),
        releaseManyPolicyFsmFail(1440),
        releaseManyPolicyFsmSuccess(1441),
        releaseManyStorageFsmFail(1442),
        releaseManyStorageFsmSuccess(1443),
        releaseOperationFsmFail(1444),
        releaseOperationFsmSuccess(1445),
        releasePolicyFsmFail(1446),
        releasePolicyFsmSuccess(1447),
        releaseStorageFsmFail(1448),
        releaseStorageFsmSuccess(1449),
        resolveAllOperationFsmFail(1450),
        resolveAllOperationFsmSuccess(1451),
        resolveAllPolicyFsmFail(1452),
        resolveAllPolicyFsmSuccess(1453),
        resolveAllStorageFsmFail(1454),
        resolveAllStorageFsmSuccess(1455),
        resolveManyOperationFsmFail(1456),
        resolveManyOperationFsmSuccess(1457),
        resolveManyPolicyFsmFail(1458),
        resolveManyPolicyFsmSuccess(1459),
        resolveManyStorageFsmFail(1460),
        resolveManyStorageFsmSuccess(1461)
    }

CfprPolicyPolicyScopeFsmTaskItem ::= TEXTUAL-CONVENTION
    STATUS        current
    DESCRIPTION
        ""
    SYNTAX        INTEGER
    {
        nop(0),
        releasePolicyFsm(1342),
        releaseOperationFsm(1344),
        releaseStorageFsm(1346),
        resolveManyPolicyFsm(1348),
        resolveManyOperationFsm(1350),
        resolveManyStorageFsm(1352),
        releaseManyPolicyFsm(1354),
        releaseManyOperationFsm(1356),
        releaseManyStorageFsm(1358),
        resolveAllPolicyFsm(1360),
        resolveAllOperationFsm(1362),
        resolveAllStorageFsm(1364),
        releaseAllPolicyFsm(1366),
        releaseAllOperationFsm(1368),
        releaseAllStorageFsm(1370)
    }

CfprPolicyRegistrationStateType ::= TEXTUAL-CONVENTION
    STATUS        current
    DESCRIPTION
        ""
    SYNTAX        INTEGER
    {
        registering(0),
        registered(1),
        failed(2),
        lostVisibility(3),
        unregistered(4)
    }

CfprPolicyRepairStateType ::= TEXTUAL-CONVENTION
    STATUS        current
    DESCRIPTION
        ""
    SYNTAX        INTEGER
    {
        done(0),
        notDone(1)
    }

CfprPolicyResumeAckState ::= TEXTUAL-CONVENTION
    STATUS        current
    DESCRIPTION
        ""
    SYNTAX        INTEGER
    {
        noAck(0),
        acked(1)
    }

CfprPolicyState ::= TEXTUAL-CONVENTION
    STATUS        current
    DESCRIPTION
        ""
    SYNTAX        INTEGER
    {
        ok(0),
        outOfSync(1)
    }

CfprPolicySuspendState ::= TEXTUAL-CONVENTION
    STATUS        current
    DESCRIPTION
        ""
    SYNTAX        INTEGER
    {
        off(0),
        on(1)
    }

CfprPoolElementOwner ::= TEXTUAL-CONVENTION
    STATUS        current
    DESCRIPTION
        ""
    SYNTAX        INTEGER
    {
        endPoint(0),
        pool(1)
    }

CfprPoolPoolAssignmentOrder ::= TEXTUAL-CONVENTION
    STATUS        current
    DESCRIPTION
        ""
    SYNTAX        INTEGER
    {
        default(0),
        sequential(1)
    }

CfprPortDuplex ::= TEXTUAL-CONVENTION
    STATUS        current
    DESCRIPTION
        ""
    SYNTAX        INTEGER
    {
        halfDuplex(1),
        fullDuplex(2),
        auto(4)
    }

CfprPortEncap ::= TEXTUAL-CONVENTION
    STATUS        current
    DESCRIPTION
        ""
    SYNTAX        INTEGER
    {
        unknown(0),
        dot1q(1),
        isl(2),
        negotiate(3),
        proprietary(4)
    }

CfprPortEthAdminSpeed ::= TEXTUAL-CONVENTION
    STATUS        current
    DESCRIPTION
        ""
    SYNTAX        INTEGER
    {
        indeterminate(0),
        n1gbps(1),
        n10gbps(2),
        n20gbps(3),
        n40gbps(4)
    }

CfprPortEthSpeed ::= TEXTUAL-CONVENTION
    STATUS        current
    DESCRIPTION
        ""
    SYNTAX        INTEGER
    {
        indeterminate(0),
        n1gbps(1),
        n10gbps(2),
        n20gbps(3),
        n40gbps(4),
        n100gbps(5),
        n10mbps(6),
        n100mbps(7)
    }

CfprPortGroupType ::= TEXTUAL-CONVENTION
    STATUS        current
    DESCRIPTION
        ""
    SYNTAX        INTEGER
    {
        switchEther(1),
        switchFc(4),
        host(8),
        fabric(16),
        fabricPc(17),
        hostPc(18),
        adaptorExt(19),
        adaptorPc(20),
        serverPc(21)
    }

CfprPortMode ::= TEXTUAL-CONVENTION
    STATUS        current
    DESCRIPTION
        ""
    SYNTAX        INTEGER
    {
        unknown(0),
        access(1),
        trunk(2),
        fabric(3),
        nProxy(4),
        f(5),
        e(6),
        sd(7)
    }

CfprPortPIoFsmCurrentFsm ::= TEXTUAL-CONVENTION
    STATUS        current
    DESCRIPTION
        ""
    SYNTAX        INTEGER
    {
        nop(0),
        inCompatSfpPresence(1014),
        inCompatSfpReplaced(1268)
    }

CfprPortPIoFsmStageName ::= TEXTUAL-CONVENTION
    STATUS        current
    DESCRIPTION
        ""
    SYNTAX        INTEGER
    {
        nop(0),
        inCompatSfpPresenceBegin(1014),
        inCompatSfpPresenceShutdown(1015),
        inCompatSfpPresenceFail(1034),
        inCompatSfpPresenceSuccess(1035),
        inCompatSfpReplacedBegin(1268),
        inCompatSfpReplacedEnablePort(1269),
        inCompatSfpReplacedFail(1462),
        inCompatSfpReplacedSuccess(1463)
    }

CfprPortPIoFsmTaskItem ::= TEXTUAL-CONVENTION
    STATUS        current
    DESCRIPTION
        ""
    SYNTAX        INTEGER
    {
        nop(0),
        inCompatSfpPresence(1014),
        inCompatSfpReplaced(1268)
    }

CfprPortSpeed ::= TEXTUAL-CONVENTION
    STATUS        current
    DESCRIPTION
        ""
    SYNTAX        INTEGER
    {
        indeterminate(0),
        n1gbps(1),
        n2gbps(2),
        n4gbps(3),
        n8gbps(4),
        auto(5)
    }

CfprPortSubGroupConfigState ::= TEXTUAL-CONVENTION
    STATUS        current
    DESCRIPTION
        ""
    SYNTAX        INTEGER
    {
        enabled(1),
        disabled(2)
    }

CfprPortSubGroupSlotId ::= TEXTUAL-CONVENTION
    STATUS        current
    DESCRIPTION
        ""
    SYNTAX        Gauge32 (1..4)

CfprPortTrust ::= TEXTUAL-CONVENTION
    STATUS        current
    DESCRIPTION
        ""
    SYNTAX        INTEGER
    {
        trusted(0),
        untrusted(1)
    }

CfprPowerCapAction ::= TEXTUAL-CONVENTION
    STATUS        current
    DESCRIPTION
        ""
    SYNTAX        INTEGER
    {
        nothing(0),
        clockDown(1),
        throttled(2)
    }

CfprPowerChThrAction ::= TEXTUAL-CONVENTION
    STATUS        current
    DESCRIPTION
        ""
    SYNTAX        INTEGER
    {
        nothing(0),
        throttleBladeDisc(1),
        stopBladeDisc(2)
    }

CfprPowerGroupState ::= TEXTUAL-CONVENTION
    STATUS        current
    DESCRIPTION
        ""
    SYNTAX        BITS
    {
        capOk(0),
        capInsufficient(1),
        capMismatch(2)
    }

CfprPowerGroupStatsThresholded ::= TEXTUAL-CONVENTION
    STATUS        current
    DESCRIPTION
        ""
    SYNTAX        BITS
    {
        power(0),
        powerAvg(1),
        powerMax(2),
        powerMin(3)
    }

CfprPowerGroupStatsHistThresholded ::= TEXTUAL-CONVENTION
    STATUS        current
    DESCRIPTION
        ""
    SYNTAX        BITS
    {
        power(0),
        powerAvg(1),
        powerMax(2),
        powerMin(3)
    }

CfprPowerLockState ::= TEXTUAL-CONVENTION
    STATUS        current
    DESCRIPTION
        ""
    SYNTAX        INTEGER
    {
        unknown(0),
        locked(1),
        unlocked(2)
    }

CfprPowerMemberState ::= TEXTUAL-CONVENTION
    STATUS        current
    DESCRIPTION
        ""
    SYNTAX        INTEGER
    {
        uninitialized(0),
        capOk(1),
        fwMismatch(2),
        psuInsufficient(3),
        psuRedundancyFailed(4),
        capInsufficient(5)
    }

CfprPowerMgmtStyle ::= TEXTUAL-CONVENTION
    STATUS        current
    DESCRIPTION
        ""
    SYNTAX        INTEGER
    {
        manualPerBlade(0),
        intelligentPolicyDriven(1)
    }

CfprPowerOperState ::= TEXTUAL-CONVENTION
    STATUS        current
    DESCRIPTION
        ""
    SYNTAX        INTEGER
    {
        notCapped(0),
        budgeting(1),
        budgeted(2),
        deploying(3),
        deployed(4),
        discoveryRetry(5),
        nonCompliant(6),
        firmwareMismatch(7),
        discoveryBudgeted(8),
        unbudgeted(9)
    }

CfprPowerPrioritySharing ::= TEXTUAL-CONVENTION
    STATUS        current
    DESCRIPTION
        ""
    SYNTAX        INTEGER
    {
        noPreference(0),
        highestPrioInChassis(1),
        highestPrioInPowerGroup(2)
    }

CfprPowerProfilingMethod ::= TEXTUAL-CONVENTION
    STATUS        current
    DESCRIPTION
        ""
    SYNTAX        INTEGER
    {
        unknown(0),
        default(1),
        static(2),
        pnuos(3),
        nodemgr(4)
    }

CfprPowerPsuLineMode ::= TEXTUAL-CONVENTION
    STATUS        current
    DESCRIPTION
        ""
    SYNTAX        INTEGER
    {
        unknown(0),
        undetermined(1),
        highLine(2),
        lowLine(3),
        mixedLine(4),
        lowerLine(5),
        lowerDcLine(6)
    }

CfprPowerPsuState ::= TEXTUAL-CONVENTION
    STATUS        current
    DESCRIPTION
        ""
    SYNTAX        INTEGER
    {
        ok(0),
        insufficient(1)
    }

CfprPowerReallocation ::= TEXTUAL-CONVENTION
    STATUS        current
    DESCRIPTION
        ""
    SYNTAX        INTEGER
    {
        chassis(0),
        none(1)
    }

CfprPowerReqConflict ::= TEXTUAL-CONVENTION
    STATUS        current
    DESCRIPTION
        ""
    SYNTAX        INTEGER
    {
        ignore(0),
        failPlacement(1)
    }

CfprProcStatAdminState ::= TEXTUAL-CONVENTION
    STATUS        current
    DESCRIPTION
        ""
    SYNTAX        INTEGER
    {
        on(1),
        clearStats(2),
        logStats(3)
    }

CfprProcessorEnvStatsThresholded ::= TEXTUAL-CONVENTION
    STATUS        current
    DESCRIPTION
        ""
    SYNTAX        BITS
    {
        inputCurrent(0),
        inputCurrentAvg(1),
        inputCurrentMax(2),
        inputCurrentMin(3),
        temperature(4),
        temperatureAvg(5),
        temperatureMax(6),
        temperatureMin(7)
    }

CfprProcessorEnvStatsHistThresholded ::= TEXTUAL-CONVENTION
    STATUS        current
    DESCRIPTION
        ""
    SYNTAX        BITS
    {
        inputCurrent(0),
        inputCurrentAvg(1),
        inputCurrentMax(2),
        inputCurrentMin(3),
        temperature(4),
        temperatureAvg(5),
        temperatureMax(6),
        temperatureMin(7)
    }

CfprProcessorErrorStatsThresholded ::= TEXTUAL-CONVENTION
    STATUS        current
    DESCRIPTION
        ""
    SYNTAX        BITS
    {
        mirroringInterSockErrors(0),
        mirroringIntraSockErrors(1),
        smiLinkCorrErrors(2),
        smiLinkUncorrErrors(3),
        sparingErrors(4)
    }

CfprProcessorQualArch ::= TEXTUAL-CONVENTION
    STATUS        current
    DESCRIPTION
        ""
    SYNTAX        INTEGER
    {
        any(0),
        intelP4C(1),
        opteron(132),
        turion64(134),
        dualCoreOpteron(135),
        pentium4(178),
        xeon(179),
        xeonMP(181)
    }

CfprProcessorRuntimeThresholded ::= TEXTUAL-CONVENTION
    STATUS        current
    DESCRIPTION
        ""
    SYNTAX        BITS
    {
        load(0),
        loadAvg(1),
        loadMax(2),
        loadMin(3)
    }

CfprProcessorRuntimeHistThresholded ::= TEXTUAL-CONVENTION
    STATUS        current
    DESCRIPTION
        ""
    SYNTAX        BITS
    {
        load(0),
        loadAvg(1),
        loadMax(2),
        loadMin(3)
    }

CfprProcessorUnitArch ::= TEXTUAL-CONVENTION
    STATUS        current
    DESCRIPTION
        ""
    SYNTAX        INTEGER
    {
        any(0),
        intelP4C(1),
        opteron(132),
        turion64(134),
        dualCoreOpteron(135),
        pentium4(178),
        xeon(179),
        xeonMP(181)
    }

CfprQosHostControl ::= TEXTUAL-CONVENTION
    STATUS        current
    DESCRIPTION
        ""
    SYNTAX        INTEGER
    {
        none(0),
        full(1),
        fullWithException(2)
    }

CfprQosPriority ::= TEXTUAL-CONVENTION
    STATUS        current
    DESCRIPTION
        ""
    SYNTAX        INTEGER
    {
        fc(1),
        platinum(2),
        gold(3),
        silver(4),
        bronze(5),
        bestEffort(6)
    }

CfprQosclassDefinitionFsmCurrentFsm ::= TEXTUAL-CONVENTION
    STATUS        current
    DESCRIPTION
        ""
    SYNTAX        INTEGER
    {
        nop(0),
        configGlobalQoS(313)
    }

CfprQosclassDefinitionFsmStageName ::= TEXTUAL-CONVENTION
    STATUS        current
    DESCRIPTION
        ""
    SYNTAX        INTEGER
    {
        nop(0),
        configGlobalQoSBegin(313),
        configGlobalQoSSetLocal(314),
        configGlobalQoSSetPeer(315),
        configGlobalQoSFail(430),
        configGlobalQoSSuccess(431)
    }

CfprQosclassDefinitionFsmTaskItem ::= TEXTUAL-CONVENTION
    STATUS        current
    DESCRIPTION
        ""
    SYNTAX        INTEGER
    {
        nop(0),
        configGlobalQoS(313)
    }

CfprQosclassEthBEAdminState ::= TEXTUAL-CONVENTION
    STATUS        current
    DESCRIPTION
        ""
    SYNTAX        INTEGER
    {
        disabled(0),
        enabled(1)
    }

CfprQosclassEthBEDrop ::= TEXTUAL-CONVENTION
    STATUS        current
    DESCRIPTION
        ""
    SYNTAX        INTEGER
    {
        drop(0),
        noDrop(1)
    }

CfprQosclassEthBEPriority ::= TEXTUAL-CONVENTION
    STATUS        current
    DESCRIPTION
        ""
    SYNTAX        INTEGER
    {
        fc(1),
        platinum(2),
        gold(3),
        silver(4),
        bronze(5),
        bestEffort(6)
    }

CfprQosclassEthClassifiedAdminState ::= TEXTUAL-CONVENTION
    STATUS        current
    DESCRIPTION
        ""
    SYNTAX        INTEGER
    {
        disabled(0),
        enabled(1)
    }

CfprQosclassEthClassifiedDrop ::= TEXTUAL-CONVENTION
    STATUS        current
    DESCRIPTION
        ""
    SYNTAX        INTEGER
    {
        drop(0),
        noDrop(1)
    }

CfprQosclassEthClassifiedPriority ::= TEXTUAL-CONVENTION
    STATUS        current
    DESCRIPTION
        ""
    SYNTAX        INTEGER
    {
        fc(1),
        platinum(2),
        gold(3),
        silver(4),
        bronze(5),
        bestEffort(6)
    }

CfprQosclassFcAdminState ::= TEXTUAL-CONVENTION
    STATUS        current
    DESCRIPTION
        ""
    SYNTAX        INTEGER
    {
        disabled(0),
        enabled(1)
    }

CfprQosclassFcDrop ::= TEXTUAL-CONVENTION
    STATUS        current
    DESCRIPTION
        ""
    SYNTAX        INTEGER
    {
        drop(0),
        noDrop(1)
    }

CfprQosclassFcPriority ::= TEXTUAL-CONVENTION
    STATUS        current
    DESCRIPTION
        ""
    SYNTAX        INTEGER
    {
        fc(1),
        platinum(2),
        gold(3),
        silver(4),
        bronze(5),
        bestEffort(6)
    }

CfprRmetaModType ::= TEXTUAL-CONVENTION
    STATUS        current
    DESCRIPTION
        ""
    SYNTAX        INTEGER
    {
        readOnly(0),
        readWrite(1),
        readCreate(2)
    }

CfprSdActionType ::= TEXTUAL-CONVENTION
    STATUS        current
    DESCRIPTION
        ""
    SYNTAX        INTEGER
    {
        none(0),
        add(1),
        update(2),
        delete(3)
    }

CfprSdAppAttributeCtrlFsmCurrentFsm ::= TEXTUAL-CONVENTION
    STATUS        current
    DESCRIPTION
        ""
    SYNTAX        INTEGER
    {
        nop(0),
        getAppAttributes(1778)
    }

CfprSdAppAttributeCtrlFsmStageName ::= TEXTUAL-CONVENTION
    STATUS        current
    DESCRIPTION
        ""
    SYNTAX        INTEGER
    {
        nop(0),
        getAppAttributesBegin(1778),
        getAppAttributesGetAttributes(1779),
        getAppAttributesFail(1792),
        getAppAttributesSuccess(1793)
    }

CfprSdAppAttributeCtrlFsmTaskItem ::= TEXTUAL-CONVENTION
    STATUS        current
    DESCRIPTION
        ""
    SYNTAX        INTEGER
    {
        nop(0),
        getAppAttributes(1778)
    }

CfprSdAppInstAdminState ::= TEXTUAL-CONVENTION
    STATUS        current
    DESCRIPTION
        ""
    SYNTAX        INTEGER
    {
        enabled(0),
        disabled(1)
    }

CfprSdAppInstSettingsTaskFsmCurrentFsm ::= TEXTUAL-CONVENTION
    STATUS        current
    DESCRIPTION
        ""
    SYNTAX        INTEGER
    {
        nop(0),
        sendAppInstSettings(2025)
    }

CfprSdAppInstSettingsTaskFsmStageName ::= TEXTUAL-CONVENTION
    STATUS        current
    DESCRIPTION
        ""
    SYNTAX        INTEGER
    {
        nop(0),
        sendAppInstSettingsBegin(2025),
        sendAppInstSettingsUpdateSettings(2026),
        sendAppInstSettingsFail(2030),
        sendAppInstSettingsSuccess(2031)
    }

CfprSdAppInstSettingsTaskFsmTaskItem ::= TEXTUAL-CONVENTION
    STATUS        current
    DESCRIPTION
        ""
    SYNTAX        INTEGER
    {
        nop(0),
        sendAppInstSettings(2025)
    }

CfprSdAppInstState ::= TEXTUAL-CONVENTION
    STATUS        current
    DESCRIPTION
        ""
    SYNTAX        INTEGER
    {
        notInstalled(0),
        installing(1),
        installFailed(2),
        offline(3),
        starting(4),
        startFailed(5),
        started(6),
        online(7),
        stopping(8),
        stopFailed(9),
        notResponding(10),
        updating(11),
        updateFailed(12),
        updateSucceeded(13),
        unsupported(14),
        fault(15)
    }

CfprSdAppInstanceCurrentJobProgress ::= TEXTUAL-CONVENTION
    STATUS        current
    DESCRIPTION
        ""
    SYNTAX        Gauge32 (0..100)

CfprSdAppInstancePrevAdminState ::= TEXTUAL-CONVENTION
    STATUS        current
    DESCRIPTION
        ""
    SYNTAX        INTEGER
    {
        enabled(0),
        disabled(1),
        notApplicable(2)
    }

CfprSdAppInstanceFsmCurrentFsm ::= TEXTUAL-CONVENTION
    STATUS        current
    DESCRIPTION
        ""
    SYNTAX        INTEGER
    {
        nop(0),
        installApplication(1607),
        startApplication(1686),
        upgradeApplication(1743),
        stopApplication(1747),
        uninstallApplication(1752),
        bundleDataPorts(1758),
        updateClusterConfiguration(1769),
        gracefulStopApp(2050)
    }

CfprSdAppInstanceFsmStageName ::= TEXTUAL-CONVENTION
    STATUS        current
    DESCRIPTION
        ""
    SYNTAX        INTEGER
    {
        nop(0),
        installApplicationBegin(1607),
        installApplicationSendCommand(1608),
        installApplicationWaitStage(1609),
        installApplicationUpdateAppInstance(1610),
        installApplicationFail(1657),
        installApplicationSuccess(1658),
        startApplicationBegin(1686),
        startApplicationSendCommand(1687),
        startApplicationWaitStage(1688),
        startApplicationUpdateAppInstance(1689),
        startApplicationFail(1702),
        startApplicationSuccess(1703),
        upgradeApplicationBegin(1743),
        upgradeApplicationSendCommand(1744),
        upgradeApplicationWaitStage(1745),
        upgradeApplicationUpdateAppInstance(1746),
        stopApplicationBegin(1747),
        stopApplicationReleaseAppLicense(1748),
        stopApplicationSendCommand(1749),
        stopApplicationWaitStage(1750),
        stopApplicationUpdateAppInstance(1751),
        uninstallApplicationBegin(1752),
        uninstallApplicationReleaseAppLicense(1753),
        uninstallApplicationSendCommand(1754),
        uninstallApplicationWaitStage(1755),
        bundleDataPortsBegin(1758),
        bundleDataPortsConfigureLinks(1759),
        bundleDataPortsWaitForConfiguration(1760),
        bundleDataPortsSendBundleStatus(1761),
        updateClusterConfigurationBegin(1769),
        updateClusterConfigurationSendConfig(1770),
        bundleDataPortsFail(1794),
        bundleDataPortsSuccess(1795),
        stopApplicationFail(1796),
        stopApplicationSuccess(1797),
        uninstallApplicationFail(1798),
        uninstallApplicationSuccess(1799),
        updateClusterConfigurationFail(1800),
        updateClusterConfigurationSuccess(1801),
        upgradeApplicationFail(1802),
        upgradeApplicationSuccess(1803),
        bundleDataPortsWaitForConfigCompletion(1826),
        bundleDataPortsUpdateBundleStatus(1827),
        installApplicationInstall(1912),
        startApplicationStart(1913),
        upgradeApplicationUpgrade(1914),
        stopApplicationStop(1915),
        uninstallApplicationUninstall(1916),
        startApplicationDebundlePorts(1964),
        upgradeApplicationDebundlePorts(1965),
        stopApplicationDebundlePorts(1966),
        stopApplicationDeregister(2017),
        startApplicationGracefulStopApp(2043),
        stopApplicationGracefulStopApp(2044),
        gracefulStopAppBegin(2050),
        gracefulStopAppApply(2051),
        gracefulStopAppFail(2063),
        gracefulStopAppSuccess(2064)
    }

CfprSdAppInstanceFsmTaskFlags ::= TEXTUAL-CONVENTION
    STATUS        current
    DESCRIPTION
        ""
    SYNTAX        BITS
    {
        samDmeSdAppInstanceStopApplicationReleaseLicense(22),
        samDmeSdAppInstanceStopApplicationStopAppInstance(23)
    }

CfprSdAppInstanceFsmTaskItem ::= TEXTUAL-CONVENTION
    STATUS        current
    DESCRIPTION
        ""
    SYNTAX        INTEGER
    {
        nop(0),
        installApplication(1607),
        startApplication(1686),
        upgradeApplication(1743),
        stopApplication(1747),
        uninstallApplication(1752),
        bundleDataPorts(1758),
        updateClusterConfiguration(1769),
        gracefulStopApp(2050)
    }

CfprSdAppLduLinkFsmCurrentFsm ::= TEXTUAL-CONVENTION
    STATUS        current
    DESCRIPTION
        ""
    SYNTAX        INTEGER
    {
        nop(0),
        updateInterfaceStatus(1847)
    }

CfprSdAppLduLinkFsmStageName ::= TEXTUAL-CONVENTION
    STATUS        current
    DESCRIPTION
        ""
    SYNTAX        INTEGER
    {
        nop(0),
        updateInterfaceStatusBegin(1847),
        updateInterfaceStatusSendStatus(1848),
        updateInterfaceStatusFail(1882),
        updateInterfaceStatusSuccess(1883)
    }

CfprSdAppRegisterCaps ::= TEXTUAL-CONVENTION
    STATUS        current
    DESCRIPTION
        ""
    SYNTAX        BITS
    {
        clusterConfig(0),
        interfaceMapping(1),
        interfaceStatus(2),
        clusterState(3),
        bundleStatus(4),
        rejoinCluster(5),
        managementInfo(6),
        netMgmtBootstrap(7),
        appAttributes(8),
        license(9),
        serviceChainStatus(10),
        inlinePair(11),
        licenseAuthRenewal(12),
        failToWire(13),
        telemetry(15)
    }

CfprSdAppResetState ::= TEXTUAL-CONVENTION
    STATUS        current
    DESCRIPTION
        ""
    SYNTAX        INTEGER
    {
        none(0),
        waitBladeReboot(1)
    }

CfprSdBasePortLinkPortType ::= TEXTUAL-CONVENTION
    STATUS        current
    DESCRIPTION
        ""
    SYNTAX        INTEGER
    {
        data(0),
        mgmt(1),
        cluster(2),
        firepowerEventing(3),
        virtualData(4),
        dataSharing(5),
        unknown(20)
    }

CfprSdBladeAssocState ::= TEXTUAL-CONVENTION
    STATUS        current
    DESCRIPTION
        ""
    SYNTAX        INTEGER
    {
        complete(0),
        inProgress(1),
        failed(2)
    }

CfprSdCfgPortForwardingMode ::= TEXTUAL-CONVENTION
    STATUS        current
    DESCRIPTION
        ""
    SYNTAX        INTEGER
    {
        none(0),
        individual(1),
        promiscuous(2)
    }

CfprSdClusterBootstrapChassisId ::= TEXTUAL-CONVENTION
    STATUS        current
    DESCRIPTION
        ""
    SYNTAX        Gauge32 (1..16)

CfprSdClusterBootstrapSiteId ::= TEXTUAL-CONVENTION
    STATUS        current
    DESCRIPTION
        ""
    SYNTAX        Gauge32 (0..8)

CfprSdClusterBootstrapFsmCurrentFsm ::= TEXTUAL-CONVENTION
    STATUS        current
    DESCRIPTION
        ""
    SYNTAX        INTEGER
    {
        nop(0),
        updateClusterConfiguration(1828)
    }

CfprSdClusterBootstrapFsmStageName ::= TEXTUAL-CONVENTION
    STATUS        current
    DESCRIPTION
        ""
    SYNTAX        INTEGER
    {
        nop(0),
        updateClusterConfigurationBegin(1828),
        updateClusterConfigurationSendConfig(1829),
        updateClusterConfigurationFail(1831),
        updateClusterConfigurationSuccess(1832)
    }

CfprSdClusterBootstrapFsmTaskItem ::= TEXTUAL-CONVENTION
    STATUS        current
    DESCRIPTION
        ""
    SYNTAX        INTEGER
    {
        nop(0),
        updateClusterConfiguration(1828)
    }

CfprSdClusterStatus ::= TEXTUAL-CONVENTION
    STATUS        current
    DESCRIPTION
        ""
    SYNTAX        INTEGER
    {
        unknown(0),
        joined(1),
        left(2)
    }

CfprSdClusterStatusType ::= TEXTUAL-CONVENTION
    STATUS        current
    DESCRIPTION
        ""
    SYNTAX        INTEGER
    {
        none(0),
        master(1),
        slave(2)
    }

CfprSdCspMetaCtrlFsmCurrentFsm ::= TEXTUAL-CONVENTION
    STATUS        current
    DESCRIPTION
        ""
    SYNTAX        INTEGER
    {
        nop(0),
        retrieveCSPMeta(2048)
    }

CfprSdCspMetaCtrlFsmStageName ::= TEXTUAL-CONVENTION
    STATUS        current
    DESCRIPTION
        ""
    SYNTAX        INTEGER
    {
        nop(0),
        retrieveCSPMetaBegin(2048),
        retrieveCSPMetaRetrieve(2049),
        retrieveCSPMetaFail(2065),
        retrieveCSPMetaSuccess(2066)
    }

CfprSdCspMetaCtrlFsmTaskItem ::= TEXTUAL-CONVENTION
    STATUS        current
    DESCRIPTION
        ""
    SYNTAX        INTEGER
    {
        nop(0),
        retrieveCSPMeta(2048)
    }

CfprSdExternalLduLinkFsmCurrentFsm ::= TEXTUAL-CONVENTION
    STATUS        current
    DESCRIPTION
        ""
    SYNTAX        INTEGER
    {
        nop(0),
        updateInterfaceStatus(1767)
    }

CfprSdExternalLduLinkFsmStageName ::= TEXTUAL-CONVENTION
    STATUS        current
    DESCRIPTION
        ""
    SYNTAX        INTEGER
    {
        nop(0),
        updateInterfaceStatusBegin(1767),
        updateInterfaceStatusSendStatus(1768),
        updateInterfaceStatusFail(1804),
        updateInterfaceStatusSuccess(1805)
    }

CfprSdExternalLduLinkFsmTaskItem ::= TEXTUAL-CONVENTION
    STATUS        current
    DESCRIPTION
        ""
    SYNTAX        INTEGER
    {
        nop(0),
        updateInterfaceStatus(1767)
    }

CfprSdFtwMode ::= TEXTUAL-CONVENTION
    STATUS        current
    DESCRIPTION
        ""
    SYNTAX        INTEGER
    {
        disable(0),
        standby(1),
        bypass(2),
        bypassForce(3),
        unmanaged(4)
    }

CfprSdHotfixCurrentJobProgress ::= TEXTUAL-CONVENTION
    STATUS        current
    DESCRIPTION
        ""
    SYNTAX        Gauge32 (0..100)

CfprSdHotfixFsmCurrentFsm ::= TEXTUAL-CONVENTION
    STATUS        current
    DESCRIPTION
        ""
    SYNTAX        INTEGER
    {
        nop(0),
        installHotfix(1952),
        uninstallHotfix(1955)
    }

CfprSdHotfixFsmStageName ::= TEXTUAL-CONVENTION
    STATUS        current
    DESCRIPTION
        ""
    SYNTAX        INTEGER
    {
        nop(0),
        installHotfixBegin(1952),
        installHotfixInstall(1953),
        installHotfixUpdateHotfix(1954),
        uninstallHotfixBegin(1955),
        uninstallHotfixUninstall(1956),
        uninstallHotfixUpdateHotfix(1957),
        installHotfixFail(1958),
        installHotfixSuccess(1959),
        uninstallHotfixFail(1960),
        uninstallHotfixSuccess(1961)
    }

CfprSdHotfixFsmTaskItem ::= TEXTUAL-CONVENTION
    STATUS        current
    DESCRIPTION
        ""
    SYNTAX        INTEGER
    {
        nop(0),
        installHotfix(1952),
        uninstallHotfix(1955)
    }

CfprSdHotfixState ::= TEXTUAL-CONVENTION
    STATUS        current
    DESCRIPTION
        ""
    SYNTAX        INTEGER
    {
        notInstalled(0),
        installing(1),
        installSucceeded(2),
        installFailed(3),
        uninstalling(4),
        uninstallFailed(5)
    }

CfprSdInterfaceType ::= TEXTUAL-CONVENTION
    STATUS        current
    DESCRIPTION
        ""
    SYNTAX        INTEGER
    {
        root(0),
        sub(1)
    }

CfprSdJobState ::= TEXTUAL-CONVENTION
    STATUS        current
    DESCRIPTION
        ""
    SYNTAX        INTEGER
    {
        unknown(0),
        queued(1),
        failed(2),
        succeeded(3)
    }

CfprSdJobType ::= TEXTUAL-CONVENTION
    STATUS        current
    DESCRIPTION
        ""
    SYNTAX        INTEGER
    {
        unknown(0),
        install(1),
        uninstall(2),
        upgrade(3),
        start(4),
        stop(5),
        formatDisk(6),
        uploadPlatformImage(7),
        installPatch(8),
        uninstallPatch(9),
        installHotfix(10),
        uninstallHotfix(11),
        restart(12),
        uploadPlatformLicense(13),
        deletePlatformLicense(14),
        reinstall(15)
    }

CfprSdLdOperState ::= TEXTUAL-CONVENTION
    STATUS        current
    DESCRIPTION
        ""
    SYNTAX        INTEGER
    {
        unknown(0),
        ok(1),
        incompleteConfiguration(2)
    }

CfprSdLduFsmCurrentFsm ::= TEXTUAL-CONVENTION
    STATUS        current
    DESCRIPTION
        ""
    SYNTAX        INTEGER
    {
        nop(0),
        provisionLDU(1690),
        updateInterfaceStatus(1917)
    }

CfprSdLduFsmStageName ::= TEXTUAL-CONVENTION
    STATUS        current
    DESCRIPTION
        ""
    SYNTAX        INTEGER
    {
        nop(0),
        provisionLDUBegin(1690),
        provisionLDUWaitForAppsInstallation(1691),
        provisionLDUWaitForLinkConfiguration(1692),
        provisionLDUStartApps(1693),
        provisionLDUFail(1704),
        provisionLDUSuccess(1705),
        provisionLDUCheckBladeReadiness(1742),
        updateInterfaceStatusBegin(1917),
        updateInterfaceStatusSendStatus(1918),
        updateInterfaceStatusFail(1935),
        updateInterfaceStatusSuccess(1936)
    }

CfprSdLduFsmTaskItem ::= TEXTUAL-CONVENTION
    STATUS        current
    DESCRIPTION
        ""
    SYNTAX        INTEGER
    {
        nop(0),
        provisionLDU(1690),
        updateInterfaceStatus(1917)
    }

CfprSdLduOperState ::= TEXTUAL-CONVENTION
    STATUS        current
    DESCRIPTION
        ""
    SYNTAX        INTEGER
    {
        unknown(0),
        active(1),
        suspended(2)
    }

CfprSdLinkDirection ::= TEXTUAL-CONVENTION
    STATUS        current
    DESCRIPTION
        ""
    SYNTAX        INTEGER
    {
        rin(1),
        out(2),
        both(3)
    }

CfprSdLinkFsmCurrentFsm ::= TEXTUAL-CONVENTION
    STATUS        current
    DESCRIPTION
        ""
    SYNTAX        INTEGER
    {
        nop(0),
        updateInterfaceStatus(1847)
    }

CfprSdLinkFsmStageName ::= TEXTUAL-CONVENTION
    STATUS        current
    DESCRIPTION
        ""
    SYNTAX        INTEGER
    {
        nop(0),
        updateInterfaceStatusBegin(1847),
        updateInterfaceStatusSendStatus(1848),
        updateInterfaceStatusFail(1882),
        updateInterfaceStatusSuccess(1883)
    }

CfprSdLinkFsmTaskItem ::= TEXTUAL-CONVENTION
    STATUS        current
    DESCRIPTION
        ""
    SYNTAX        INTEGER
    {
        nop(0),
        updateInterfaceStatus(1847)
    }

CfprSdLinkOperState ::= TEXTUAL-CONVENTION
    STATUS        current
    DESCRIPTION
        ""
    SYNTAX        INTEGER
    {
        unknown(0),
        up(1),
        down(2)
    }

CfprSdLogicalDeviceFsmCurrentFsm ::= TEXTUAL-CONVENTION
    STATUS        current
    DESCRIPTION
        ""
    SYNTAX        INTEGER
    {
        nop(0),
        configureLinks(1762),
        configureUserMacs(1919),
        configureMacs(2023)
    }

CfprSdLogicalDeviceFsmStageName ::= TEXTUAL-CONVENTION
    STATUS        current
    DESCRIPTION
        ""
    SYNTAX        INTEGER
    {
        nop(0),
        configureLinksBegin(1762),
        configureLinksSendInterfaces(1763),
        configureLinksUnconfigureLinks(1764),
        configureLinksConfigureSwitch(1765),
        configureLinksWaitForSwitchConfig(1766),
        configureLinksFail(1806),
        configureLinksSuccess(1807),
        configureLinksUnconfigureLogicalDevice(1846),
        configureUserMacsBegin(1919),
        configureUserMacsConfigureSwitch(1920),
        configureUserMacsWaitForSwitchConfig(1921),
        configureUserMacsFail(1937),
        configureUserMacsSuccess(1938),
        configureMacsBegin(2023),
        configureMacsSendInterfaceDeleting(2024),
        configureMacsConfigureSwitch(2025),
        configureMacsWaitForSwitchConfig(2026),
        configureMacsSendInterfaceAdding(2027),
        configureMacsFail(2028),
        configureMacsSuccess(2029)
    }

CfprSdLogicalDeviceFsmTaskItem ::= TEXTUAL-CONVENTION
    STATUS        current
    DESCRIPTION
        ""
    SYNTAX        INTEGER
    {
        nop(0),
        configureLinks(1762),
        configureUserMacs(1919),
        configureMacs(2023)
    }

CfprSdMacType ::= TEXTUAL-CONVENTION
    STATUS        current
    DESCRIPTION
        ""
    SYNTAX        INTEGER
    {
        unicast(1),
        multicast(2)
    }

CfprSdMgmtInfoFsmCurrentFsm ::= TEXTUAL-CONVENTION
    STATUS        current
    DESCRIPTION
        ""
    SYNTAX        INTEGER
    {
        nop(0),
        updateMgmtInfo(1780)
    }

CfprSdMgmtInfoFsmStageName ::= TEXTUAL-CONVENTION
    STATUS        current
    DESCRIPTION
        ""
    SYNTAX        INTEGER
    {
        nop(0),
        updateMgmtInfoBegin(1780),
        updateMgmtInfoSendUpdate(1781),
        updateMgmtInfoFail(1808),
        updateMgmtInfoSuccess(1809)
    }

CfprSdMgmtInfoFsmTaskItem ::= TEXTUAL-CONVENTION
    STATUS        current
    DESCRIPTION
        ""
    SYNTAX        INTEGER
    {
        nop(0),
        updateMgmtInfo(1780)
    }

CfprSdNetMgmtBootstrapFsmCurrentFsm ::= TEXTUAL-CONVENTION
    STATUS        current
    DESCRIPTION
        ""
    SYNTAX        INTEGER
    {
        nop(0),
        updateNetMgmtBootstrap(1782)
    }

CfprSdNetMgmtBootstrapFsmStageName ::= TEXTUAL-CONVENTION
    STATUS        current
    DESCRIPTION
        ""
    SYNTAX        INTEGER
    {
        nop(0),
        updateNetMgmtBootstrapBegin(1782),
        updateNetMgmtBootstrapSendUpdate(1783),
        updateNetMgmtBootstrapFail(1810),
        updateNetMgmtBootstrapSuccess(1811)
    }

CfprSdNetMgmtBootstrapFsmTaskItem ::= TEXTUAL-CONVENTION
    STATUS        current
    DESCRIPTION
        ""
    SYNTAX        INTEGER
    {
        nop(0),
        updateNetMgmtBootstrap(1782)
    }

CfprSdPortBundleOpType ::= TEXTUAL-CONVENTION
    STATUS        current
    DESCRIPTION
        ""
    SYNTAX        INTEGER
    {
        bundled(0),
        deBundled(1)
    }

CfprSdPortBundleStatus ::= TEXTUAL-CONVENTION
    STATUS        current
    DESCRIPTION
        ""
    SYNTAX        INTEGER
    {
        unknown(0),
        failure(1),
        partial(2),
        success(3)
    }

CfprSdPortForwardingMode ::= TEXTUAL-CONVENTION
    STATUS        current
    DESCRIPTION
        ""
    SYNTAX        INTEGER
    {
        individual(0),
        promiscuous(1)
    }

CfprSdPortsBundleFsmCurrentFsm ::= TEXTUAL-CONVENTION
    STATUS        current
    DESCRIPTION
        ""
    SYNTAX        INTEGER
    {
        nop(0),
        bundleDataPorts(1947)
    }

CfprSdPortsBundleFsmStageName ::= TEXTUAL-CONVENTION
    STATUS        current
    DESCRIPTION
        ""
    SYNTAX        INTEGER
    {
        nop(0),
        bundleDataPortsBegin(1947),
        bundleDataPortsConfigureLinks(1948),
        bundleDataPortsWaitForConfigCompletion(1949),
        bundleDataPortsUpdateBundleStatus(1950),
        bundleDataPortsSendBundleStatus(1951),
        bundleDataPortsFail(1962),
        bundleDataPortsSuccess(1963)
    }

CfprSdPortsBundleFsmTaskItem ::= TEXTUAL-CONVENTION
    STATUS        current
    DESCRIPTION
        ""
    SYNTAX        INTEGER
    {
        nop(0),
        bundleDataPorts(1947)
    }

CfprSdSlotFsmCurrentFsm ::= TEXTUAL-CONVENTION
    STATUS        current
    DESCRIPTION
        ""
    SYNTAX        INTEGER
    {
        nop(0),
        changePlatformLogLevel(1756),
        formatDisk(1771),
        synchTimeZone(1776)
    }

CfprSdSlotFsmStageName ::= TEXTUAL-CONVENTION
    STATUS        current
    DESCRIPTION
        ""
    SYNTAX        INTEGER
    {
        nop(0),
        changePlatformLogLevelBegin(1756),
        changePlatformLogLevelSendCommand(1757),
        formatDiskBegin(1771),
        formatDiskCheckBladeReadiness(1772),
        formatDiskStartDiskFormat(1773),
        formatDiskResetBladePower(1774),
        formatDiskWaitForDiskFormatComplete(1775),
        synchTimeZoneBegin(1776),
        synchTimeZoneUpdateTimeZone(1777),
        changePlatformLogLevelFail(1812),
        changePlatformLogLevelSuccess(1813),
        formatDiskFail(1814),
        formatDiskSuccess(1815),
        synchTimeZoneFail(1816),
        synchTimeZoneSuccess(1817),
        formatDiskWaitForDiskFormatSecureComplete(2045),
        formatDiskDecommissionBlade(2046),
        formatDiskWaitforDecommissionComplete(2047)
    }

CfprSdSlotFsmTaskItem ::= TEXTUAL-CONVENTION
    STATUS        current
    DESCRIPTION
        ""
    SYNTAX        INTEGER
    {
        nop(0),
        changePlatformLogLevel(1756),
        formatDisk(1771),
        synchTimeZone(1776)
    }

CfprSdSubLduLinkFsmCurrentFsm ::= TEXTUAL-CONVENTION
    STATUS        current
    DESCRIPTION
        ""
    SYNTAX        INTEGER
    {
        nop(0),
        updateInterfaceStatus(1847)
    }

CfprSdSubLduLinkFsmStageName ::= TEXTUAL-CONVENTION
    STATUS        current
    DESCRIPTION
        ""
    SYNTAX        INTEGER
    {
        nop(0),
        updateInterfaceStatusBegin(1847),
        updateInterfaceStatusSendStatus(1848),
        updateInterfaceStatusFail(1882),
        updateInterfaceStatusSuccess(1883)
    }

CfprSdUpdateState ::= TEXTUAL-CONVENTION
    STATUS        current
    DESCRIPTION
        ""
    SYNTAX        INTEGER
    {
        ready(0),
        pending(1),
        skipped(2)
    }

CfprSdUpgradeTaskFsmCurrentFsm ::= TEXTUAL-CONVENTION
    STATUS        current
    DESCRIPTION
        ""
    SYNTAX        INTEGER
    {
        nop(0),
        stopUpgradeStartApp(1849)
    }

CfprSdUpgradeTaskFsmStageName ::= TEXTUAL-CONVENTION
    STATUS        current
    DESCRIPTION
        ""
    SYNTAX        INTEGER
    {
        nop(0),
        stopUpgradeStartAppBegin(1849),
        stopUpgradeStartAppStopApp(1850),
        stopUpgradeStartAppWaitForStopApp(1851),
        stopUpgradeStartAppWaitForBladeReboot(1852),
        stopUpgradeStartAppUpgradeApp(1853),
        stopUpgradeStartAppWaitForUpgradeApp(1854),
        stopUpgradeStartAppStartApp(1855),
        stopUpgradeStartAppFail(1884),
        stopUpgradeStartAppSuccess(1885)
    }

CfprSdUpgradeTaskFsmTaskItem ::= TEXTUAL-CONVENTION
    STATUS        current
    DESCRIPTION
        ""
    SYNTAX        INTEGER
    {
        nop(0),
        stopUpgradeStartApp(1849)
    }

CfprSdUpgradeType ::= TEXTUAL-CONVENTION
    STATUS        current
    DESCRIPTION
        ""
    SYNTAX        INTEGER
    {
        unknown(0),
        fullUpgrade(1),
        installPatch(2),
        uninstallPatch(3)
    }

CfprServerConfigIssues ::= TEXTUAL-CONVENTION
    STATUS        current
    DESCRIPTION
        ""
    SYNTAX        BITS
    {
        insufficientResources(0),
        boardControllerUpdateUnsupported(1),
        bootConfigurationInvalid(2),
        bootOrderIscsi(3),
        bootOrderPxe(4),
        bootOrderSanImagePath(5),
        computeUnavailable(6),
        computeUndiscovered(7),
        incompatBiosForSriovVnics(8),
        incompatibleBiosImage(9),
        insufficientPowerBudget(10),
        macAddressAssignment(11),
        memoryRequirement(12),
        migration(13),
        missingFirmwareImage(14),
        nonInterruptFsmRunning(15),
        physicalRequirement(16),
        powerGroupRequirement(17),
        processorRequirement(18),
        remotePolicy(19),
        serverPositionRequirement(20),
        remoteServiceProfile(21),
        systemUuidAssignment(22),
        wwnnDerivationFromVhba(23),
        resourceOwnershipConflict(24),
        bootipPolicyInvalid(25),
        hostimgPolicyInvalid(26),
        imgsecPolicyInvalid(27),
        provsrvPolicyInvalid(28),
        qosPolicyInvalid(29),
        bootConfigurationUnsupported(30),
        serverFeatureCapabilityMismatch(31),
        domainRequirement(32),
        duplicateAddressConflict(33),
        vmediaPolicyUnsupported(34),
        bootPolicyVmediaInvalid(35),
        vmediaMountConfigInvalid(36),
        softPinningVlanMismatch(37),
        cimcDowngradeRestriction(38),
        ivbCimcDowngradeRestriction(39),
        ivbBiosDowngradeRestriction(40),
        incompatibleSsposImage(41)
    }

CfprSmActionStages ::= TEXTUAL-CONVENTION
    STATUS        current
    DESCRIPTION
        ""
    SYNTAX        INTEGER
    {
        available(0),
        perform(1),
        performing(2),
        failure(3),
        notAvailable(4)
    }

CfprSmAppAdminState ::= TEXTUAL-CONVENTION
    STATUS        current
    DESCRIPTION
        ""
    SYNTAX        INTEGER
    {
        active(0),
        deleted(1),
        verified(2)
    }

CfprSmAppAggregatorType ::= TEXTUAL-CONVENTION
    STATUS        current
    DESCRIPTION
        ""
    SYNTAX        INTEGER
    {
        unknown(0),
        none(1),
        partial(2),
        full(3),
        serviceStandard(4),
        direct(5)
    }

CfprSmAppClusterOperState ::= TEXTUAL-CONVENTION
    STATUS        current
    DESCRIPTION
        ""
    SYNTAX        INTEGER
    {
        notApplicable(0),
        inCluster(1),
        notInCluster(2),
        joiningCluster(3),
        leavingCluster(4)
    }

CfprSmAppCommand ::= TEXTUAL-CONVENTION
    STATUS        current
    DESCRIPTION
        ""
    SYNTAX        INTEGER
    {
        ok(0),
        retryAction(1),
        clearMgmtBootstrap(2),
        retryHotfixInstall(3),
        retryHotfixUninstall(4),
        restart(5),
        reinstall(6)
    }

CfprSmAppFsmCurrentFsm ::= TEXTUAL-CONVENTION
    STATUS        current
    DESCRIPTION
        ""
    SYNTAX        INTEGER
    {
        nop(0),
        delete(1706),
        verifyApplication(1901)
    }

CfprSmAppFsmStageName ::= TEXTUAL-CONVENTION
    STATUS        current
    DESCRIPTION
        ""
    SYNTAX        INTEGER
    {
        nop(0),
        deleteBegin(1706),
        deleteLocal(1707),
        deleteFail(1818),
        deleteSuccess(1819),
        verifyApplicationBegin(1901),
        verifyApplicationCheckReadiness(1902),
        verifyApplicationVerify(1903),
        verifyApplicationFail(1939),
        verifyApplicationSuccess(1940)
    }

CfprSmAppFsmTaskItem ::= TEXTUAL-CONVENTION
    STATUS        current
    DESCRIPTION
        ""
    SYNTAX        INTEGER
    {
        nop(0),
        delete(1706),
        verifyApplication(1901)
    }

CfprSmAppInstance2ClusterRole ::= TEXTUAL-CONVENTION
    STATUS        current
    DESCRIPTION
        ""
    SYNTAX        INTEGER
    {
        none(0),
        master(1),
        slave(2)
    }

CfprSmAppInstance2CurrentJobProgress ::= TEXTUAL-CONVENTION
    STATUS        current
    DESCRIPTION
        ""
    SYNTAX        Gauge32 (0..100)

CfprSmAppInstance2FsmCurrentFsm ::= TEXTUAL-CONVENTION
    STATUS        current
    DESCRIPTION
        ""
    SYNTAX        INTEGER
    {
        nop(0),
        resetApplication(2008)
    }

CfprSmAppInstance2FsmStageName ::= TEXTUAL-CONVENTION
    STATUS        current
    DESCRIPTION
        ""
    SYNTAX        INTEGER
    {
        nop(0),
        resetApplicationBegin(2008),
        resetApplicationFail(2018),
        resetApplicationSuccess(2019),
        resetApplicationStopApp(2020),
        resetApplicationWaitForStopApp(2021),
        resetApplicationStartApp(2022)
    }

CfprSmAppInstance2FsmTaskItem ::= TEXTUAL-CONVENTION
    STATUS        current
    DESCRIPTION
        ""
    SYNTAX        INTEGER
    {
        nop(0),
        resetApplication(2008)
    }

CfprSmAppInstanceClusterRole ::= TEXTUAL-CONVENTION
    STATUS        current
    DESCRIPTION
        ""
    SYNTAX        INTEGER
    {
        none(0),
        master(1),
        slave(2)
    }

CfprSmAppInstanceCurrentJobProgress ::= TEXTUAL-CONVENTION
    STATUS        current
    DESCRIPTION
        ""
    SYNTAX        Gauge32 (0..100)

CfprSmAppInstanceFsmCurrentFsm ::= TEXTUAL-CONVENTION
    STATUS        current
    DESCRIPTION
        ""
    SYNTAX        INTEGER
    {
        nop(0),
        resetApplication(1833)
    }

CfprSmAppInstanceFsmStageName ::= TEXTUAL-CONVENTION
    STATUS        current
    DESCRIPTION
        ""
    SYNTAX        INTEGER
    {
        nop(0),
        resetApplicationBegin(1833),
        resetApplicationStopDecoratorApps(1834),
        resetApplicationWairForStopDecorators(1835),
        resetApplicationStopMainApp(1836),
        resetApplicationWaitForBladeReboot(1837),
        resetApplicationWaitForStopMainApp(1838),
        resetApplicationStartMainApp(1839),
        resetApplicationWaitForStartMainApp(1840),
        resetApplicationStartDecoratorApps(1841),
        resetApplicationFail(1842),
        resetApplicationSuccess(1843)
    }

CfprSmAppInstanceFsmTaskItem ::= TEXTUAL-CONVENTION
    STATUS        current
    DESCRIPTION
        ""
    SYNTAX        INTEGER
    {
        nop(0),
        resetApplication(1833)
    }

CfprSmAppRscProfileNumCores ::= TEXTUAL-CONVENTION
    STATUS        current
    DESCRIPTION
        ""
    SYNTAX        Gauge32 (6..110)

CfprSmAppRscProfileType ::= TEXTUAL-CONVENTION
    STATUS        current
    DESCRIPTION
        ""
    SYNTAX        INTEGER
    {
        system(0),
        userDefined(1)
    }

CfprSmAppValidationStateType ::= TEXTUAL-CONVENTION
    STATUS        current
    DESCRIPTION
        ""
    SYNTAX        INTEGER
    {
        none(0),
        imageValidated(1),
        imageCorrupted(2),
        inProgress(3),
        queued(4)
    }

CfprSmBladeErrorCode ::= TEXTUAL-CONVENTION
    STATUS        current
    DESCRIPTION
        ""
    SYNTAX        INTEGER
    {
        notApplicable(0),
        discoveryAssociationError(1),
        failsafe(300),
        hddError(301),
        filesystemError(302),
        formatFailed(303),
        vnicError(304),
        hwclockError(305),
        containerError(306),
        diskrepairError(307),
        adapter2Error(308)
    }

CfprSmCloudConnectAdminState ::= TEXTUAL-CONVENTION
    STATUS        current
    DESCRIPTION
        ""
    SYNTAX        INTEGER
    {
        disabled(0),
        enabled(1)
    }

CfprSmCloudConnectOperState ::= TEXTUAL-CONVENTION
    STATUS        current
    DESCRIPTION
        ""
    SYNTAX        INTEGER
    {
        unregistered(0),
        registered(1),
        registerFailure(2),
        unregisterFailure(3),
        registering(4),
        unregistering(5)
    }

CfprSmCloudConnectorFsmCurrentFsm ::= TEXTUAL-CONVENTION
    STATUS        current
    DESCRIPTION
        ""
    SYNTAX        INTEGER
    {
        nop(0),
        registerCloudConnector(1897),
        unRegisterCloudConnector(1899)
    }

CfprSmCloudConnectorFsmStageName ::= TEXTUAL-CONVENTION
    STATUS        current
    DESCRIPTION
        ""
    SYNTAX        INTEGER
    {
        nop(0),
        registerCloudConnectorBegin(1897),
        registerCloudConnectorRegister(1898),
        unRegisterCloudConnectorBegin(1899),
        unRegisterCloudConnectorUnRegister(1900),
        registerCloudConnectorFail(1941),
        registerCloudConnectorSuccess(1942),
        unRegisterCloudConnectorFail(1943),
        unRegisterCloudConnectorSuccess(1944)
    }

CfprSmCloudConnectorFsmTaskItem ::= TEXTUAL-CONVENTION
    STATUS        current
    DESCRIPTION
        ""
    SYNTAX        INTEGER
    {
        nop(0),
        registerCloudConnector(1897),
        unRegisterCloudConnector(1899)
    }

CfprSmCloudRetryAction ::= TEXTUAL-CONVENTION
    STATUS        current
    DESCRIPTION
        ""
    SYNTAX        INTEGER
    {
        ok(0),
        retry(1)
    }

CfprSmClusterBootstrapChassisId ::= TEXTUAL-CONVENTION
    STATUS        current
    DESCRIPTION
        ""
    SYNTAX        Gauge32 (1..16)

CfprSmClusterBootstrapSiteId ::= TEXTUAL-CONVENTION
    STATUS        current
    DESCRIPTION
        ""
    SYNTAX        Gauge32 (0..8)

CfprSmClusterMode ::= TEXTUAL-CONVENTION
    STATUS        current
    DESCRIPTION
        ""
    SYNTAX        INTEGER
    {
        spannedEtherchannel(0)
    }

CfprSmCspType ::= TEXTUAL-CONVENTION
    STATUS        current
    DESCRIPTION
        ""
    SYNTAX        INTEGER
    {
        unknown(0),
        application(1),
        osPatch(2),
        appBaseline(3),
        appPatch(4),
        appHotfix(5)
    }

CfprSmDataType ::= TEXTUAL-CONVENTION
    STATUS        current
    DESCRIPTION
        ""
    SYNTAX        INTEGER
    {
        int(0),
        long(1),
        string(2),
        ipaddress(3)
    }

CfprSmDeployType ::= TEXTUAL-CONVENTION
    STATUS        current
    DESCRIPTION
        ""
    SYNTAX        INTEGER
    {
        unknown(0),
        native(1),
        lxc(2),
        vm(3),
        container(4)
    }

CfprSmDeployTypeBitMask ::= TEXTUAL-CONVENTION
    STATUS        current
    DESCRIPTION
        ""
    SYNTAX        BITS
    {
        native(0),
        lxc(1),
        vm(2),
        container(3)
    }

CfprSmDiskState ::= TEXTUAL-CONVENTION
    STATUS        current
    DESCRIPTION
        ""
    SYNTAX        INTEGER
    {
        ok(0),
        formatting(1),
        formatFailure(2),
        unknown(3),
        secureEraseInProgress(4),
        secureEraseFailed(5)
    }

CfprSmFsmTaskType ::= TEXTUAL-CONVENTION
    STATUS        current
    DESCRIPTION
        ""
    SYNTAX        BITS
    {
        provisionLdu(0),
        configureLinks(1),
        updateClusterConfig(2),
        resetApplicationResourceProfile(3)
    }

CfprSmHeartbeatState ::= TEXTUAL-CONVENTION
    STATUS        current
    DESCRIPTION
        ""
    SYNTAX        INTEGER
    {
        disable(0),
        enable(1)
    }

CfprSmHotfixCurrentJobProgress ::= TEXTUAL-CONVENTION
    STATUS        current
    DESCRIPTION
        ""
    SYNTAX        Gauge32 (0..100)

CfprSmHwCryptoAdminState ::= TEXTUAL-CONVENTION
    STATUS        current
    DESCRIPTION
        ""
    SYNTAX        INTEGER
    {
        disabled(0),
        enabled(1)
    }

CfprSmLdMode ::= TEXTUAL-CONVENTION
    STATUS        current
    DESCRIPTION
        ""
    SYNTAX        INTEGER
    {
        clustered(1),
        standalone(2)
    }

CfprSmLicenseDeviceType ::= TEXTUAL-CONVENTION
    STATUS        current
    DESCRIPTION
        ""
    SYNTAX        INTEGER
    {
        chassis(0),
        securityModule(1)
    }

CfprSmLicenseFileFsmCurrentFsm ::= TEXTUAL-CONVENTION
    STATUS        current
    DESCRIPTION
        ""
    SYNTAX        INTEGER
    {
        nop(0),
        delete(1988)
    }

CfprSmLicenseFileFsmStageName ::= TEXTUAL-CONVENTION
    STATUS        current
    DESCRIPTION
        ""
    SYNTAX        INTEGER
    {
        nop(0),
        deleteBegin(1988),
        deleteLocal(1989),
        deleteFail(2002),
        deleteSuccess(2003)
    }

CfprSmLicenseFileFsmTaskItem ::= TEXTUAL-CONVENTION
    STATUS        current
    DESCRIPTION
        ""
    SYNTAX        INTEGER
    {
        nop(0),
        delete(1988)
    }

CfprSmLogLevel ::= TEXTUAL-CONVENTION
    STATUS        current
    DESCRIPTION
        ""
    SYNTAX        INTEGER
    {
        debug(0),
        info(1),
        warning(2),
        error(3),
        critical(4)
    }

CfprSmLogicalDeviceFsmCurrentFsm ::= TEXTUAL-CONVENTION
    STATUS        current
    DESCRIPTION
        ""
    SYNTAX        INTEGER
    {
        nop(0),
        configure(1906)
    }

CfprSmLogicalDeviceFsmStageName ::= TEXTUAL-CONVENTION
    STATUS        current
    DESCRIPTION
        ""
    SYNTAX        INTEGER
    {
        nop(0),
        configureBegin(1906),
        configureResolvePolicy(1907),
        configureValidateLDConfig(1908),
        configureCheckConfigIssues(1909),
        configureAutoConfig(1910),
        configureApplyConfig(1911),
        configureFail(1945),
        configureSuccess(1946)
    }

CfprSmLogicalDeviceFsmTaskItem ::= TEXTUAL-CONVENTION
    STATUS        current
    DESCRIPTION
        ""
    SYNTAX        INTEGER
    {
        nop(0),
        configure(1906)
    }

CfprSmLogicalDeviceMode ::= TEXTUAL-CONVENTION
    STATUS        current
    DESCRIPTION
        ""
    SYNTAX        INTEGER
    {
        unknown(0),
        clustered(1),
        standalone(2)
    }

CfprSmMgmtSubType ::= TEXTUAL-CONVENTION
    STATUS        current
    DESCRIPTION
        ""
    SYNTAX        INTEGER
    {
        default(0),
        firepower(1)
    }

CfprSmNetMgmtBootstrapScope ::= TEXTUAL-CONVENTION
    STATUS        current
    DESCRIPTION
        ""
    SYNTAX        INTEGER
    {
        global(0),
        instanceOnly(1)
    }

CfprSmNetMgmtBootstrapType ::= TEXTUAL-CONVENTION
    STATUS        current
    DESCRIPTION
        ""
    SYNTAX        INTEGER
    {
        nA(0),
        appagent(1),
        disk(2)
    }

CfprSmSecSvcFsmCurrentFsm ::= TEXTUAL-CONVENTION
    STATUS        current
    DESCRIPTION
        ""
    SYNTAX        INTEGER
    {
        nop(0),
        restoreApplication(1708)
    }

CfprSmSecSvcFsmStageName ::= TEXTUAL-CONVENTION
    STATUS        current
    DESCRIPTION
        ""
    SYNTAX        INTEGER
    {
        nop(0),
        restoreApplicationBegin(1708),
        restoreApplicationRestore(1709),
        restoreApplicationFail(1820),
        restoreApplicationSuccess(1821)
    }

CfprSmSecSvcFsmTaskItem ::= TEXTUAL-CONVENTION
    STATUS        current
    DESCRIPTION
        ""
    SYNTAX        INTEGER
    {
        nop(0),
        restoreApplication(1708)
    }

CfprSmSlotAdminState ::= TEXTUAL-CONVENTION
    STATUS        current
    DESCRIPTION
        ""
    SYNTAX        INTEGER
    {
        ok(0),
        reinitialize(1),
        secureErase(2)
    }

CfprSmSlotOperState ::= TEXTUAL-CONVENTION
    STATUS        current
    DESCRIPTION
        ""
    SYNTAX        INTEGER
    {
        notAvailable(0),
        offline(1),
        online(2),
        notResponding(3),
        fault(4),
        tokenMismatch(5)
    }

CfprSmSupportCclSubnetType ::= TEXTUAL-CONVENTION
    STATUS        current
    DESCRIPTION
        ""
    SYNTAX        INTEGER
    {
        unknown(0),
        supported(1),
        notSupported(2)
    }

CfprSmSupportedLdMode ::= TEXTUAL-CONVENTION
    STATUS        current
    DESCRIPTION
        ""
    SYNTAX        INTEGER
    {
        standalone(0),
        clustered(1),
        all(2)
    }

CfprSmUnsignedCspLicenseLicenseInstallState ::= TEXTUAL-CONVENTION
    STATUS        current
    DESCRIPTION
        ""
    SYNTAX        INTEGER
    {
        uninstall(0),
        install(1)
    }

CfprSmUnsignedCspLicenseFsmCurrentFsm ::= TEXTUAL-CONVENTION
    STATUS        current
    DESCRIPTION
        ""
    SYNTAX        INTEGER
    {
        nop(0),
        deploy(1982)
    }

CfprSmUnsignedCspLicenseFsmStageName ::= TEXTUAL-CONVENTION
    STATUS        current
    DESCRIPTION
        ""
    SYNTAX        INTEGER
    {
        nop(0),
        deployBegin(1982),
        deployOnChassis(1983),
        deployRebootSystem(1984),
        deployWaitForReady(1985),
        deployOnBlades(1986),
        deployWaitForCompletion(1987),
        deployFail(2004),
        deploySuccess(2005)
    }

CfprSmUnsignedCspLicenseFsmTaskItem ::= TEXTUAL-CONVENTION
    STATUS        current
    DESCRIPTION
        ""
    SYNTAX        INTEGER
    {
        nop(0),
        deploy(1982)
    }

CfprSolAdminState ::= TEXTUAL-CONVENTION
    STATUS        current
    DESCRIPTION
        ""
    SYNTAX        INTEGER
    {
        disable(0),
        enable(1)
    }

CfprSolSpeed ::= TEXTUAL-CONVENTION
    STATUS        current
    DESCRIPTION
        ""
    SYNTAX        INTEGER
    {
        n9600(6),
        n19200(7),
        n38400(8),
        n57600(9),
        n115200(10)
    }

CfprStatsCollectionDomain ::= TEXTUAL-CONVENTION
    STATUS        current
    DESCRIPTION
        ""
    SYNTAX        INTEGER
    {
        unknown(0),
        chassis(2),
        port(4),
        host(5),
        adapter(6),
        server(7),
        fex(8)
    }

CfprStatsCollectionInterval ::= TEXTUAL-CONVENTION
    STATUS        current
    DESCRIPTION
        ""
    SYNTAX        INTEGER
    {
        n30seconds(30),
        n1minute(60),
        n2minutes(120),
        n5minutes(300)
    }

CfprStatsCollectionPolicyFsmCurrentFsm ::= TEXTUAL-CONVENTION
    STATUS        current
    DESCRIPTION
        ""
    SYNTAX        INTEGER
    {
        nop(0),
        updateEp(310)
    }

CfprStatsCollectionPolicyFsmStageName ::= TEXTUAL-CONVENTION
    STATUS        current
    DESCRIPTION
        ""
    SYNTAX        INTEGER
    {
        nop(0),
        updateEpBegin(310),
        updateEpSetEpA(311),
        updateEpSetEpB(312),
        updateEpFail(432),
        updateEpSuccess(433)
    }

CfprStatsCollectionPolicyFsmTaskItem ::= TEXTUAL-CONVENTION
    STATUS        current
    DESCRIPTION
        ""
    SYNTAX        INTEGER
    {
        nop(0),
        updateEp(310)
    }

CfprStatsReportingInterval ::= TEXTUAL-CONVENTION
    STATUS        current
    DESCRIPTION
        ""
    SYNTAX        INTEGER
    {
        n2minutes(120),
        n15minutes(900),
        n30minutes(1800),
        n60minutes(3600),
        n2hours(7200),
        n4hours(14400),
        n8hours(28800)
    }

CfprStatsThr32DefinitionPropType ::= TEXTUAL-CONVENTION
    STATUS        current
    DESCRIPTION
        ""
    SYNTAX        INTEGER
    {
        uint32(1),
        uint64(2),
        float(3)
    }

CfprStatsThr32ValuePropType ::= TEXTUAL-CONVENTION
    STATUS        current
    DESCRIPTION
        ""
    SYNTAX        INTEGER
    {
        uint32(1),
        uint64(2),
        float(3)
    }

CfprStatsThr64DefinitionPropType ::= TEXTUAL-CONVENTION
    STATUS        current
    DESCRIPTION
        ""
    SYNTAX        INTEGER
    {
        uint32(1),
        uint64(2),
        float(3)
    }

CfprStatsThr64ValuePropType ::= TEXTUAL-CONVENTION
    STATUS        current
    DESCRIPTION
        ""
    SYNTAX        INTEGER
    {
        uint32(1),
        uint64(2),
        float(3)
    }

CfprStatsThrFloatDefinitionPropType ::= TEXTUAL-CONVENTION
    STATUS        current
    DESCRIPTION
        ""
    SYNTAX        INTEGER
    {
        uint32(1),
        uint64(2),
        float(3)
    }

CfprStatsThrFloatValuePropType ::= TEXTUAL-CONVENTION
    STATUS        current
    DESCRIPTION
        ""
    SYNTAX        INTEGER
    {
        uint32(1),
        uint64(2),
        float(3)
    }

CfprStatsThresholdDirection ::= TEXTUAL-CONVENTION
    STATUS        current
    DESCRIPTION
        ""
    SYNTAX        INTEGER
    {
        aboveNormal(1),
        belowNormal(2)
    }

CfprStorageAccessType ::= TEXTUAL-CONVENTION
    STATUS        current
    DESCRIPTION
        ""
    SYNTAX        INTEGER
    {
        unknown(0),
        readWrite(1),
        readOnly(2),
        blocked(3)
    }

CfprStorageActualWriteType ::= TEXTUAL-CONVENTION
    STATUS        current
    DESCRIPTION
        ""
    SYNTAX        INTEGER
    {
        unknown(0),
        writeThrough(1),
        writeBack(2)
    }

CfprStorageAllocState ::= TEXTUAL-CONVENTION
    STATUS        current
    DESCRIPTION
        ""
    SYNTAX        INTEGER
    {
        none(0),
        allocating(1),
        allocated(2),
        failed(3)
    }

CfprStorageBatteryType ::= TEXTUAL-CONVENTION
    STATUS        current
    DESCRIPTION
        ""
    SYNTAX        INTEGER
    {
        unknown(0),
        battery(1),
        supercap(2)
    }

CfprStorageBbuStatus ::= TEXTUAL-CONVENTION
    STATUS        current
    DESCRIPTION
        ""
    SYNTAX        INTEGER
    {
        unknown(0),
        optimal(1),
        learnCycleActive(2),
        learnCycleNeeded(3),
        failurePredicted(4),
        premiumFeatureReqd(5),
        microcodeUpdateReqd(6),
        replacementNeeded(7),
        noFlashSpace(8),
        notSupported(9),
        notPresent(10)
    }

CfprStorageBootableType ::= TEXTUAL-CONVENTION
    STATUS        current
    DESCRIPTION
        ""
    SYNTAX        INTEGER
    {
        unknown(0),
        true(1),
        false(2)
    }

CfprStorageCacheType ::= TEXTUAL-CONVENTION
    STATUS        current
    DESCRIPTION
        ""
    SYNTAX        INTEGER
    {
        unknown(0),
        noChange(1),
        enable(2),
        disable(3)
    }

CfprStorageConfigIssues ::= TEXTUAL-CONVENTION
    STATUS        current
    DESCRIPTION
        ""
    SYNTAX        BITS
    {
        destructiveLocalDiskConfig(0),
        incompatibleDiskTypes(1),
        incompatibleNumberOfLocalDisks(2),
        incompatibleRaidLevel(3),
        missingRaidKey(4),
        storagePathConfigurationError(5),
        wwnnAssignment(6),
        zoneCapacity(7),
        flexflashController(8),
        flexflashCard(9),
        flexflashMetadata(10),
        storageFeatureCapabilityMismatch(11)
    }

CfprStorageConfiguration ::= TEXTUAL-CONVENTION
    STATUS        current
    DESCRIPTION
        ""
    SYNTAX        INTEGER
    {
        unknown(0),
        supported(1),
        notSupported(2)
    }

CfprStorageConfiguredWriteType ::= TEXTUAL-CONVENTION
    STATUS        current
    DESCRIPTION
        ""
    SYNTAX        INTEGER
    {
        unknown(0),
        writeThrough(1),
        writeBackGoodBbu(2),
        alwaysWriteBack(3)
    }

CfprStorageConnectionProtocol ::= TEXTUAL-CONVENTION
    STATUS        current
    DESCRIPTION
        ""
    SYNTAX        INTEGER
    {
        unspecified(0),
        sas(1),
        sata(2)
    }

CfprStorageControllerFaultMonitoring ::= TEXTUAL-CONVENTION
    STATUS        current
    DESCRIPTION
        ""
    SYNTAX        INTEGER
    {
        supported(1),
        notSupported(2)
    }

CfprStorageControllerId ::= TEXTUAL-CONVENTION
    STATUS        current
    DESCRIPTION
        ""
    SYNTAX        Gauge32 (1..64)

CfprStorageControllerForm ::= TEXTUAL-CONVENTION
    STATUS        current
    DESCRIPTION
        ""
    SYNTAX        INTEGER
    {
        none(0),
        onBoard(1),
        mezzanine(2),
        pci(3),
        embedded(4)
    }

CfprStorageControllerStatus ::= TEXTUAL-CONVENTION
    STATUS        current
    DESCRIPTION
        ""
    SYNTAX        INTEGER
    {
        unknown(0),
        optimal(1),
        failed(2),
        unresponsive(3)
    }

CfprStorageControllerType ::= TEXTUAL-CONVENTION
    STATUS        current
    DESCRIPTION
        ""
    SYNTAX        INTEGER
    {
        unknown(0),
        sas(1),
        sata(2),
        flash(3),
        sd(4)
    }

CfprStorageDisklessAction ::= TEXTUAL-CONVENTION
    STATUS        current
    DESCRIPTION
        ""
    SYNTAX        INTEGER
    {
        unspecified(0),
        yes(1),
        no(2)
    }

CfprStorageEpAccess ::= TEXTUAL-CONVENTION
    STATUS        current
    DESCRIPTION
        ""
    SYNTAX        INTEGER
    {
        readonly(1),
        admin(2)
    }

CfprStorageEtherIfVlanType ::= TEXTUAL-CONVENTION
    STATUS        current
    DESCRIPTION
        ""
    SYNTAX        INTEGER
    {
        regular(0),
        default(1),
        native(2)
    }

CfprStorageFFCardHealth ::= TEXTUAL-CONVENTION
    STATUS        current
    DESCRIPTION
        ""
    SYNTAX        INTEGER
    {
        ffPhyHealthNa(0),
        ffPhyHealthOk(1),
        ffPhyUnhealthyRaid(2),
        ffPhyUnhealthyOther(3)
    }

CfprStorageFFCardMode ::= TEXTUAL-CONVENTION
    STATUS        current
    DESCRIPTION
        ""
    SYNTAX        INTEGER
    {
        ffPhyDriveUnpairedPrimary(0),
        ffPhyDrivePrimary(1),
        ffPhyDriveSecondaryAct(2),
        ffPhyDriveSecondaryUnhealthy(3)
    }

CfprStorageFFCardSizeMismatch ::= TEXTUAL-CONVENTION
    STATUS        current
    DESCRIPTION
        ""
    SYNTAX        INTEGER
    {
        na(0),
        mismatch(1),
        match(2)
    }

CfprStorageFFCardState ::= TEXTUAL-CONVENTION
    STATUS        current
    DESCRIPTION
        ""
    SYNTAX        INTEGER
    {
        undefined(0),
        configured(1),
        initializing(2),
        active(3),
        ignored(4),
        failed(5),
        unknown(6)
    }

CfprStorageFFCardSync ::= TEXTUAL-CONVENTION
    STATUS        current
    DESCRIPTION
        ""
    SYNTAX        INTEGER
    {
        na(0),
        manual(1),
        auto(2),
        unknown(3)
    }

CfprStorageFFCardWriteEnable ::= TEXTUAL-CONVENTION
    STATUS        current
    DESCRIPTION
        ""
    SYNTAX        INTEGER
    {
        no(0),
        yes(1)
    }

CfprStorageFFControllerHealth ::= TEXTUAL-CONVENTION
    STATUS        current
    DESCRIPTION
        ""
    SYNTAX        INTEGER
    {
        ffchOk(0),
        ffchMetadataFailure(1),
        ffchErrorCardsAccessError(2),
        ffchErrorOldFirmwareRunning(3),
        ffchErrorMediaWriteProtected(4),
        ffchErrorInvalidSize(5),
        ffchErrorCardSizeMismatch(6),
        ffchInconsistentMetadata(7),
        ffchErrorSecondaryUnhealthyCard(8),
        ffchErrorSdCardNotConfigured(9),
        ffchErrorInconsistantMetadataIgnored(10),
        ffchErrorSd253WithUnOrSd247(11),
        ffchErrorRebootedDuringRebuild(12),
        ffchErrorSd247CardDetected(13),
        ffchFlexdErrorSdCardOpModeMismatch(14),
        ffchFlexdErrorSdOpModeMismatchWithUn(15),
        ffchFlexdErrorImSdUnhealthySdUnIgnored(16),
        ffchFlexdErrorImSdHealthySdUnIgnored(17),
        ffchFlexdErrorImSdCardsOpModeMismatch(18),
        ffchFlexdErrorSdCard0UnhealthyOpModeMismatch(19),
        ffchFlexdErrorSdCard0HealthyOpModeMismatch(20),
        ffchFlexdErrorSdCard1UnhealthyOpModeMismatch(21),
        ffchFlexdErrorSdCard1HealthyOpModeMismatch(22),
        ffchFlexdErrorImSd0IgnoredSd1(23),
        ffchFlexdErrorImSd0Sd1Ignored(24)
    }

CfprStorageFFControllerState ::= TEXTUAL-CONVENTION
    STATUS        current
    DESCRIPTION
        ""
    SYNTAX        INTEGER
    {
        ffcUninitalized(0),
        ffcSoftwareErr(1),
        ffcInit(2),
        ffcConfig(3),
        ffcWaitUser(4),
        ffcUsbDisconnecting(5),
        ffcUsbDisconnected(6),
        ffcUsbConnecting(7),
        ffcUsbConnected(8),
        ffcRebuilding(9),
        ffcFailed(10)
    }

CfprStorageFFDriveRemovable ::= TEXTUAL-CONVENTION
    STATUS        current
    DESCRIPTION
        ""
    SYNTAX        INTEGER
    {
        na(0),
        yes(1),
        no(2)
    }

CfprStorageFFDriveState ::= TEXTUAL-CONVENTION
    STATUS        current
    DESCRIPTION
        ""
    SYNTAX        INTEGER
    {
        nonraid(0),
        raid(1)
    }

CfprStorageFFDriveType ::= TEXTUAL-CONVENTION
    STATUS        current
    DESCRIPTION
        ""
    SYNTAX        INTEGER
    {
        unknown(0),
        scu(1),
        huu(2),
        hv(3),
        drivers(4)
    }

CfprStorageFFDriveVisible ::= TEXTUAL-CONVENTION
    STATUS        current
    DESCRIPTION
        ""
    SYNTAX        INTEGER
    {
        no(0),
        yes(1)
    }

CfprStorageFFFormatRunning ::= TEXTUAL-CONVENTION
    STATUS        current
    DESCRIPTION
        ""
    SYNTAX        INTEGER
    {
        na(0),
        yes(1),
        no(2)
    }

CfprStorageFFHasError ::= TEXTUAL-CONVENTION
    STATUS        current
    DESCRIPTION
        ""
    SYNTAX        INTEGER
    {
        error(0),
        noError(1)
    }

CfprStorageFFRAIDHealth ::= TEXTUAL-CONVENTION
    STATUS        current
    DESCRIPTION
        ""
    SYNTAX        INTEGER
    {
        ffrHealthNa(0),
        ffrHealthOk(1),
        ffrHealthDegraded(2),
        ffrHealthNotReporting(3)
    }

CfprStorageFFRAIDState ::= TEXTUAL-CONVENTION
    STATUS        current
    DESCRIPTION
        ""
    SYNTAX        INTEGER
    {
        ffrStateDisabled(0),
        ffrStateEnabledNotPaired(1),
        ffrStateEnabledPairedInvalidSecondary(2),
        ffrStateEnabledPairedInvalidPrimary(3),
        ffrStateEnabledPairedInvalidBoth(4),
        ffrStateEnabledPaired(5)
    }

CfprStorageFFRWType ::= TEXTUAL-CONVENTION
    STATUS        current
    DESCRIPTION
        ""
    SYNTAX        INTEGER
    {
        readWrite(0),
        readOnly(1)
    }

CfprStorageFFRaidSyncSupport ::= TEXTUAL-CONVENTION
    STATUS        current
    DESCRIPTION
        ""
    SYNTAX        INTEGER
    {
        no(0),
        yes(1)
    }

CfprStorageFFSlotENUM ::= TEXTUAL-CONVENTION
    STATUS        current
    DESCRIPTION
        ""
    SYNTAX        INTEGER
    {
        na(0),
        n1(1),
        n2(2)
    }

CfprStorageFFType ::= TEXTUAL-CONVENTION
    STATUS        current
    DESCRIPTION
        ""
    SYNTAX        INTEGER
    {
        unknown(0),
        astoria(1),
        fx3s(2)
    }

CfprStorageFcZoningType ::= TEXTUAL-CONVENTION
    STATUS        current
    DESCRIPTION
        ""
    SYNTAX        INTEGER
    {
        none(0),
        sist(1),
        simt(2)
    }

CfprStorageFileSystemStatus ::= TEXTUAL-CONVENTION
    STATUS        current
    DESCRIPTION
        ""
    SYNTAX        INTEGER
    {
        unknown(0),
        clean(1),
        notClean(2),
        mounted(3),
        unmounted(4)
    }

CfprStorageFlexFlashControllerId ::= TEXTUAL-CONVENTION
    STATUS        current
    DESCRIPTION
        ""
    SYNTAX        Gauge32 (1..64)

CfprStorageFlexFlashControllerFsmCurrentFsm ::= TEXTUAL-CONVENTION
    STATUS        current
    DESCRIPTION
        ""
    SYNTAX        INTEGER
    {
        nop(0),
        mopsReset(1661),
        mopsFormat(1663),
        mopsPair(1665)
    }

CfprStorageFlexFlashControllerFsmStageName ::= TEXTUAL-CONVENTION
    STATUS        current
    DESCRIPTION
        ""
    SYNTAX        INTEGER
    {
        nop(0),
        mopsResetBegin(1661),
        mopsResetReset(1662),
        mopsFormatBegin(1663),
        mopsFormatFormat(1664),
        mopsPairBegin(1665),
        mopsPairPair(1666),
        mopsFormatFail(1680),
        mopsFormatSuccess(1681),
        mopsPairFail(1682),
        mopsPairSuccess(1683),
        mopsResetFail(1684),
        mopsResetSuccess(1685)
    }

CfprStorageFlexFlashControllerFsmTaskItem ::= TEXTUAL-CONVENTION
    STATUS        current
    DESCRIPTION
        ""
    SYNTAX        INTEGER
    {
        nop(0),
        mopsReset(1661),
        mopsFormat(1663),
        mopsPair(1665)
    }

CfprStorageIOType ::= TEXTUAL-CONVENTION
    STATUS        current
    DESCRIPTION
        ""
    SYNTAX        INTEGER
    {
        unknown(0),
        direct(1),
        cached(2)
    }

CfprStorageIniGroupOperProtocol ::= TEXTUAL-CONVENTION
    STATUS        current
    DESCRIPTION
        ""
    SYNTAX        INTEGER
    {
        derived(0),
        fc(1),
        iscsi(2)
    }

CfprStorageIniGroupOwner ::= TEXTUAL-CONVENTION
    STATUS        current
    DESCRIPTION
        ""
    SYNTAX        INTEGER
    {
        unknown(0),
        physical(1),
        policy(2),
        logical(4),
        connPolicy(8)
    }

CfprStorageIniGroupProtocol ::= TEXTUAL-CONVENTION
    STATUS        current
    DESCRIPTION
        ""
    SYNTAX        INTEGER
    {
        derived(0),
        fc(1),
        iscsi(2)
    }

CfprStorageKeyType ::= TEXTUAL-CONVENTION
    STATUS        current
    DESCRIPTION
        ""
    SYNTAX        INTEGER
    {
        initiator(1),
        target(2)
    }

CfprStorageLearnCycleRequested ::= TEXTUAL-CONVENTION
    STATUS        current
    DESCRIPTION
        ""
    SYNTAX        INTEGER
    {
        unknown(0),
        true(1),
        false(2)
    }

CfprStorageLearnMode ::= TEXTUAL-CONVENTION
    STATUS        current
    DESCRIPTION
        ""
    SYNTAX        INTEGER
    {
        unknown(0),
        auto(1),
        disabled(2),
        warn(3)
    }

CfprStorageLinkSpeed ::= TEXTUAL-CONVENTION
    STATUS        current
    DESCRIPTION
        ""
    SYNTAX        INTEGER
    {
        unknown(0),
        n15Gbps(1),
        n3Gbps(2),
        n6Gbps(3),
        n12Gbps(4)
    }

CfprStorageLocalDiskConfigFlexFlashRAIDReportingState ::= TEXTUAL-CONVENTION
    STATUS        current
    DESCRIPTION
        ""
    SYNTAX        INTEGER
    {
        disable(0),
        enable(1)
    }

CfprStorageLocalDiskConfigFlexFlashState ::= TEXTUAL-CONVENTION
    STATUS        current
    DESCRIPTION
        ""
    SYNTAX        INTEGER
    {
        disable(0),
        enable(1)
    }

CfprStorageLocalDiskMode ::= TEXTUAL-CONVENTION
    STATUS        current
    DESCRIPTION
        ""
    SYNTAX        INTEGER
    {
        noLocalStorage(1),
        singleDisk(2),
        dualDisk(3),
        raidStriped(4),
        raidMirrored(5),
        bestEffortMirrored(6),
        bestEffortStriped(7),
        anyConfiguration(8),
        noRaid(9),
        raidStripedParity(10),
        raidStripedDualParity(11),
        raidMirroredStriped(12),
        bestEffortStripedParity(13),
        bestEffortStripedDualParity(14),
        bestEffortMirroredStriped(15),
        raidStripedParityStriped(16),
        raidStripedDualParityStriped(17)
    }

CfprStorageLocalDiskPartitionType ::= TEXTUAL-CONVENTION
    STATUS        current
    DESCRIPTION
        ""
    SYNTAX        INTEGER
    {
        none(1),
        swap(2),
        ext2(3),
        ext3(4),
        ntfs(5),
        fat32(6)
    }

CfprStorageLunType ::= TEXTUAL-CONVENTION
    STATUS        current
    DESCRIPTION
        ""
    SYNTAX        INTEGER
    {
        unspecified(0),
        simple(1),
        mirror(2),
        stripe(3),
        raid(4),
        stripeParity(5),
        stripeDualParity(6),
        mirrorStripe(7),
        stripeParityStripe(8),
        stripeDualParityStripe(9)
    }

CfprStorageOperState ::= TEXTUAL-CONVENTION
    STATUS        current
    DESCRIPTION
        ""
    SYNTAX        INTEGER
    {
        ok(0),
        misconfigured(1)
    }

CfprStorageOperatingModeType ::= TEXTUAL-CONVENTION
    STATUS        current
    DESCRIPTION
        ""
    SYNTAX        INTEGER
    {
        unknown(0),
        mirror(1),
        util(2)
    }

CfprStorageOperationRequestType ::= TEXTUAL-CONVENTION
    STATUS        current
    DESCRIPTION
        ""
    SYNTAX        INTEGER
    {
        unknown(0),
        format(1),
        reset(2),
        pair(3)
    }

CfprStorageOperationState ::= TEXTUAL-CONVENTION
    STATUS        current
    DESCRIPTION
        ""
    SYNTAX        INTEGER
    {
        unknown(0),
        inProgress(1),
        completed(2),
        failed(3)
    }

CfprStorageOperationStateType ::= TEXTUAL-CONVENTION
    STATUS        current
    DESCRIPTION
        ""
    SYNTAX        INTEGER
    {
        partitionNonMirrored(0),
        partitionMirrored(1),
        partitionMirroredSyncing(2),
        partitionMirroredErasing(3),
        partitionMirroredUpdating(4),
        partitionNonMirroredUpdating(5),
        partitionNonMirroredErasing(6),
        partitionMirroredSyncingFail(7),
        partitionMirroredErasingFail(8),
        partitionMirroredUpdatingFail(9),
        partitionNonMirroredUpdatingFail(10),
        partitionNonMirroredErasingFail(11),
        partitionMirroredSyncingSuccess(12),
        partitionMirroredErasingSuccess(13),
        partitionMirroredUpdatingSuccess(14),
        partitionNonMirroredUpdatingSuccess(15),
        partitionNonMirroredErasingSuccess(16),
        unknown(17)
    }

CfprStorageOperationType ::= TEXTUAL-CONVENTION
    STATUS        current
    DESCRIPTION
        ""
    SYNTAX        INTEGER
    {
        reconstruction(0),
        relearning(1),
        patrolRead(2),
        consistencyCheck(3),
        rebuild(4),
        initialization(5)
    }

CfprStoragePDriveStatus ::= TEXTUAL-CONVENTION
    STATUS        current
    DESCRIPTION
        ""
    SYNTAX        INTEGER
    {
        unknown(0),
        online(1),
        unconfiguredGood(2),
        globalHotSpare(3),
        dedicatedHotSpare(4),
        jbod(5),
        offline(6),
        rebuilding(7),
        copyback(8),
        failed(9),
        unconfiguredBad(10),
        predictiveFailure(11),
        disabledForRemoval(12),
        foreignConfiguration(13)
    }

CfprStoragePathHA ::= TEXTUAL-CONVENTION
    STATUS        current
    DESCRIPTION
        ""
    SYNTAX        BITS
    {
        initiator(0),
        target(1),
        fabric(2)
    }

CfprStoragePowerState ::= TEXTUAL-CONVENTION
    STATUS        current
    DESCRIPTION
        ""
    SYNTAX        INTEGER
    {
        unknown(0),
        active(1),
        powersave(2),
        transitioning(3)
    }

CfprStorageProtocol ::= TEXTUAL-CONVENTION
    STATUS        current
    DESCRIPTION
        ""
    SYNTAX        INTEGER
    {
        derived(0),
        fc(1),
        iscsi(2)
    }

CfprStorageRaidBatteryOperabilityQualifier ::= TEXTUAL-CONVENTION
    STATUS        current
    DESCRIPTION
        ""
    SYNTAX        INTEGER
    {
        unknown(0)
    }

CfprStorageReadType ::= TEXTUAL-CONVENTION
    STATUS        current
    DESCRIPTION
        ""
    SYNTAX        INTEGER
    {
        unknown(0),
        readAhead(1),
        normal(2)
    }

CfprStorageSystemFsmCurrentFsm ::= TEXTUAL-CONVENTION
    STATUS        current
    DESCRIPTION
        ""
    SYNTAX        INTEGER
    {
        nop(0),
        sync(1301)
    }

CfprStorageSystemFsmStageName ::= TEXTUAL-CONVENTION
    STATUS        current
    DESCRIPTION
        ""
    SYNTAX        INTEGER
    {
        nop(0),
        syncBegin(1301),
        syncExecute(1302),
        syncFail(1464),
        syncSuccess(1465)
    }

CfprStorageSystemFsmTaskItem ::= TEXTUAL-CONVENTION
    STATUS        current
    DESCRIPTION
        ""
    SYNTAX        INTEGER
    {
        nop(0),
        sync(1301)
    }

CfprStorageTargetPath ::= TEXTUAL-CONVENTION
    STATUS        current
    DESCRIPTION
        ""
    SYNTAX        INTEGER
    {
        none(0),
        a(1),
        b(2),
        dual(3)
    }

CfprStorageTechnology ::= TEXTUAL-CONVENTION
    STATUS        current
    DESCRIPTION
        ""
    SYNTAX        INTEGER
    {
        unspecified(0),
        hdd(1),
        ssd(2)
    }

CfprStorageVDriveState ::= TEXTUAL-CONVENTION
    STATUS        current
    DESCRIPTION
        ""
    SYNTAX        INTEGER
    {
        unknown(0),
        optimal(1),
        cacheDegraded(2),
        partiallyDegraded(3),
        degraded(4),
        offline(5)
    }

CfprStorageVsanRefSwitchId ::= TEXTUAL-CONVENTION
    STATUS        current
    DESCRIPTION
        ""
    SYNTAX        INTEGER
    {
        none(0),
        a(1),
        b(2),
        dual(3)
    }

CfprSwAccessDomainLocale ::= TEXTUAL-CONVENTION
    STATUS        current
    DESCRIPTION
        ""
    SYNTAX        BITS
    {
        server(0),
        chassis(1),
        internal(2),
        external(3)
    }

CfprSwAccessDomainType ::= TEXTUAL-CONVENTION
    STATUS        current
    DESCRIPTION
        ""
    SYNTAX        BITS
    {
        lan(0),
        san(1),
        ipc(2)
    }

CfprSwAccessDomainFsmCurrentFsm ::= TEXTUAL-CONVENTION
    STATUS        current
    DESCRIPTION
        ""
    SYNTAX        INTEGER
    {
        nop(0),
        deploy(222)
    }

CfprSwAccessDomainFsmStageName ::= TEXTUAL-CONVENTION
    STATUS        current
    DESCRIPTION
        ""
    SYNTAX        INTEGER
    {
        nop(0),
        deployBegin(222),
        deployUpdateConnectivity(223),
        deployFail(434),
        deploySuccess(435)
    }

CfprSwAccessDomainFsmTaskItem ::= TEXTUAL-CONVENTION
    STATUS        current
    DESCRIPTION
        ""
    SYNTAX        INTEGER
    {
        nop(0),
        deploy(222)
    }

CfprSwAccessEpLocale ::= TEXTUAL-CONVENTION
    STATUS        current
    DESCRIPTION
        ""
    SYNTAX        BITS
    {
        server(0),
        chassis(1),
        internal(2),
        external(3)
    }

CfprSwAccessEpTransport ::= TEXTUAL-CONVENTION
    STATUS        current
    DESCRIPTION
        ""
    SYNTAX        BITS
    {
        ether(0),
        dce(1),
        fc(2)
    }

CfprSwAdminState ::= TEXTUAL-CONVENTION
    STATUS        current
    DESCRIPTION
        ""
    SYNTAX        INTEGER
    {
        enabled(1),
        disabled(2)
    }

CfprSwBorderDomainLocale ::= TEXTUAL-CONVENTION
    STATUS        current
    DESCRIPTION
        ""
    SYNTAX        BITS
    {
        server(0),
        chassis(1),
        internal(2),
        external(3)
    }

CfprSwBorderEpLocale ::= TEXTUAL-CONVENTION
    STATUS        current
    DESCRIPTION
        ""
    SYNTAX        BITS
    {
        server(0),
        chassis(1),
        internal(2),
        external(3)
    }

CfprSwBorderPcLocale ::= TEXTUAL-CONVENTION
    STATUS        current
    DESCRIPTION
        ""
    SYNTAX        BITS
    {
        server(0),
        chassis(1),
        internal(2),
        external(3)
    }

CfprSwBreakoutType ::= TEXTUAL-CONVENTION
    STATUS        current
    DESCRIPTION
        ""
    SYNTAX        INTEGER
    {
        unknown(0),
        n10g4x(1)
    }

CfprSwCIoEpIfType ::= TEXTUAL-CONVENTION
    STATUS        current
    DESCRIPTION
        ""
    SYNTAX        INTEGER
    {
        unknown(0),
        physical(1),
        aggregation(2),
        virtual(3)
    }

CfprSwCardEnvStatsThresholded ::= TEXTUAL-CONVENTION
    STATUS        current
    DESCRIPTION
        ""
    SYNTAX        BITS
    {
        slotOutlet1(0),
        slotOutlet1Avg(1),
        slotOutlet1Max(2),
        slotOutlet1Min(3),
        slotOutlet2(4),
        slotOutlet2Avg(5),
        slotOutlet2Max(6),
        slotOutlet2Min(7),
        slotOutlet3(8),
        slotOutlet3Avg(9),
        slotOutlet3Max(10),
        slotOutlet3Min(11)
    }

CfprSwCardEnvStatsHistThresholded ::= TEXTUAL-CONVENTION
    STATUS        current
    DESCRIPTION
        ""
    SYNTAX        BITS
    {
        slotOutlet1(0),
        slotOutlet1Avg(1),
        slotOutlet1Max(2),
        slotOutlet1Min(3),
        slotOutlet2(4),
        slotOutlet2Avg(5),
        slotOutlet2Max(6),
        slotOutlet2Min(7),
        slotOutlet3(8),
        slotOutlet3Avg(9),
        slotOutlet3Max(10),
        slotOutlet3Min(11)
    }

CfprSwCimcId ::= TEXTUAL-CONVENTION
    STATUS        current
    DESCRIPTION
        ""
    SYNTAX        BITS
    {
        unused(1)
    }

CfprSwConfMode ::= TEXTUAL-CONVENTION
    STATUS        current
    DESCRIPTION
        ""
    SYNTAX        INTEGER
    {
        none(0),
        inProgress(1),
        verifying(2),
        failed(3)
    }

CfprSwConfigStatus ::= TEXTUAL-CONVENTION
    STATUS        current
    DESCRIPTION
        ""
    SYNTAX        INTEGER
    {
        none(1),
        noVlanComp(2)
    }

CfprSwEnvStatsThresholded ::= TEXTUAL-CONVENTION
    STATUS        current
    DESCRIPTION
        ""
    SYNTAX        BITS
    {
        fanCtrlrInlet1(0),
        fanCtrlrInlet1Avg(1),
        fanCtrlrInlet1Max(2),
        fanCtrlrInlet1Min(3),
        fanCtrlrInlet2(4),
        fanCtrlrInlet2Avg(5),
        fanCtrlrInlet2Max(6),
        fanCtrlrInlet2Min(7),
        fanCtrlrInlet3(8),
        fanCtrlrInlet3Avg(9),
        fanCtrlrInlet3Max(10),
        fanCtrlrInlet3Min(11),
        fanCtrlrInlet4(12),
        fanCtrlrInlet4Avg(13),
        fanCtrlrInlet4Max(14),
        fanCtrlrInlet4Min(15),
        mainBoardOutlet1(16),
        mainBoardOutlet1Avg(17),
        mainBoardOutlet1Max(18),
        mainBoardOutlet1Min(19),
        mainBoardOutlet2(20),
        mainBoardOutlet2Avg(21),
        mainBoardOutlet2Max(22),
        mainBoardOutlet2Min(23),
        psuCtrlrInlet1(24),
        psuCtrlrInlet1Avg(25),
        psuCtrlrInlet1Max(26),
        psuCtrlrInlet1Min(27),
        psuCtrlrInlet2(28),
        psuCtrlrInlet2Avg(29),
        psuCtrlrInlet2Max(30),
        psuCtrlrInlet2Min(31)
    }

CfprSwEnvStatsHistThresholded ::= TEXTUAL-CONVENTION
    STATUS        current
    DESCRIPTION
        ""
    SYNTAX        BITS
    {
        fanCtrlrInlet1(0),
        fanCtrlrInlet1Avg(1),
        fanCtrlrInlet1Max(2),
        fanCtrlrInlet1Min(3),
        fanCtrlrInlet2(4),
        fanCtrlrInlet2Avg(5),
        fanCtrlrInlet2Max(6),
        fanCtrlrInlet2Min(7),
        fanCtrlrInlet3(8),
        fanCtrlrInlet3Avg(9),
        fanCtrlrInlet3Max(10),
        fanCtrlrInlet3Min(11),
        fanCtrlrInlet4(12),
        fanCtrlrInlet4Avg(13),
        fanCtrlrInlet4Max(14),
        fanCtrlrInlet4Min(15),
        mainBoardOutlet1(16),
        mainBoardOutlet1Avg(17),
        mainBoardOutlet1Max(18),
        mainBoardOutlet1Min(19),
        mainBoardOutlet2(20),
        mainBoardOutlet2Avg(21),
        mainBoardOutlet2Max(22),
        mainBoardOutlet2Min(23),
        psuCtrlrInlet1(24),
        psuCtrlrInlet1Avg(25),
        psuCtrlrInlet1Max(26),
        psuCtrlrInlet1Min(27),
        psuCtrlrInlet2(28),
        psuCtrlrInlet2Avg(29),
        psuCtrlrInlet2Max(30),
        psuCtrlrInlet2Min(31)
    }

CfprSwEstcEpLocale ::= TEXTUAL-CONVENTION
    STATUS        current
    DESCRIPTION
        ""
    SYNTAX        BITS
    {
        server(0),
        chassis(1),
        internal(2),
        external(3)
    }

CfprSwEthEstcEpTransport ::= TEXTUAL-CONVENTION
    STATUS        current
    DESCRIPTION
        ""
    SYNTAX        BITS
    {
        ether(0),
        dce(1),
        fc(2)
    }

CfprSwEthEstcPcTransport ::= TEXTUAL-CONVENTION
    STATUS        current
    DESCRIPTION
        ""
    SYNTAX        BITS
    {
        ether(0),
        dce(1),
        fc(2)
    }

CfprSwEthFlowMonSessionTransport ::= TEXTUAL-CONVENTION
    STATUS        current
    DESCRIPTION
        ""
    SYNTAX        BITS
    {
        ether(0),
        dce(1),
        fc(2)
    }

CfprSwEthFlowMonSessionType ::= TEXTUAL-CONVENTION
    STATUS        current
    DESCRIPTION
        ""
    SYNTAX        BITS
    {
        lan(0),
        san(1),
        ipc(2)
    }

CfprSwEthLanBorderTransport ::= TEXTUAL-CONVENTION
    STATUS        current
    DESCRIPTION
        ""
    SYNTAX        BITS
    {
        ether(0),
        dce(1),
        fc(2)
    }

CfprSwEthLanBorderFsmCurrentFsm ::= TEXTUAL-CONVENTION
    STATUS        current
    DESCRIPTION
        ""
    SYNTAX        INTEGER
    {
        nop(0),
        deploy(224)
    }

CfprSwEthLanBorderFsmStageName ::= TEXTUAL-CONVENTION
    STATUS        current
    DESCRIPTION
        ""
    SYNTAX        INTEGER
    {
        nop(0),
        deployBegin(224),
        deployUpdateConnectivity(225),
        deployFail(436),
        deploySuccess(437),
        deployUpdateVlanGroups(1331)
    }

CfprSwEthLanBorderFsmTaskFlags ::= TEXTUAL-CONVENTION
    STATUS        current
    DESCRIPTION
        ""
    SYNTAX        BITS
    {
        samDmeSwEthLanBorderDeployVlanGroupConfig(6),
        samDmeSwEthLanBorderDeployVlanGroupRetry(7),
        samDmeSwEthLanBorderDeployPortConfig(8)
    }

CfprSwEthLanBorderFsmTaskItem ::= TEXTUAL-CONVENTION
    STATUS        current
    DESCRIPTION
        ""
    SYNTAX        INTEGER
    {
        nop(0),
        deploy(224)
    }

CfprSwEthLanEpInlineState ::= TEXTUAL-CONVENTION
    STATUS        current
    DESCRIPTION
        ""
    SYNTAX        INTEGER
    {
        enabled(1),
        disabled(2)
    }

CfprSwEthLanEpTransport ::= TEXTUAL-CONVENTION
    STATUS        current
    DESCRIPTION
        ""
    SYNTAX        BITS
    {
        ether(0),
        dce(1),
        fc(2)
    }

CfprSwEthLanEpUdldAdminState ::= TEXTUAL-CONVENTION
    STATUS        current
    DESCRIPTION
        ""
    SYNTAX        INTEGER
    {
        enabled(1),
        disabled(2)
    }

CfprSwEthLanEpUdldMode ::= TEXTUAL-CONVENTION
    STATUS        current
    DESCRIPTION
        ""
    SYNTAX        INTEGER
    {
        normal(0),
        aggressive(1)
    }

CfprSwEthLanFlowMonTransport ::= TEXTUAL-CONVENTION
    STATUS        current
    DESCRIPTION
        ""
    SYNTAX        BITS
    {
        ether(0),
        dce(1),
        fc(2)
    }

CfprSwEthLanFlowMonExporterTransport ::= TEXTUAL-CONVENTION
    STATUS        current
    DESCRIPTION
        ""
    SYNTAX        BITS
    {
        ether(0),
        dce(1),
        fc(2)
    }

CfprSwEthLanFlowMonExporterType ::= TEXTUAL-CONVENTION
    STATUS        current
    DESCRIPTION
        ""
    SYNTAX        BITS
    {
        lan(0),
        san(1),
        ipc(2)
    }

CfprSwEthLanFlowMonFsmCurrentFsm ::= TEXTUAL-CONVENTION
    STATUS        current
    DESCRIPTION
        ""
    SYNTAX        INTEGER
    {
        nop(0),
        deploy(1491)
    }

CfprSwEthLanFlowMonFsmStageName ::= TEXTUAL-CONVENTION
    STATUS        current
    DESCRIPTION
        ""
    SYNTAX        INTEGER
    {
        nop(0),
        deployBegin(1491),
        deployUpdateEthFlowMon(1492),
        deployFail(1559),
        deploySuccess(1560)
    }

CfprSwEthLanFlowMonFsmTaskItem ::= TEXTUAL-CONVENTION
    STATUS        current
    DESCRIPTION
        ""
    SYNTAX        INTEGER
    {
        nop(0),
        deploy(1491)
    }

CfprSwEthLanFlowMonitorTransport ::= TEXTUAL-CONVENTION
    STATUS        current
    DESCRIPTION
        ""
    SYNTAX        BITS
    {
        ether(0),
        dce(1),
        fc(2)
    }

CfprSwEthLanFlowMonitorType ::= TEXTUAL-CONVENTION
    STATUS        current
    DESCRIPTION
        ""
    SYNTAX        BITS
    {
        lan(0),
        san(1),
        ipc(2)
    }

CfprSwEthLanFlowRecordDefTransport ::= TEXTUAL-CONVENTION
    STATUS        current
    DESCRIPTION
        ""
    SYNTAX        BITS
    {
        ether(0),
        dce(1),
        fc(2)
    }

CfprSwEthLanFlowRecordDefType ::= TEXTUAL-CONVENTION
    STATUS        current
    DESCRIPTION
        ""
    SYNTAX        BITS
    {
        lan(0),
        san(1),
        ipc(2)
    }

CfprSwEthLanMonTransport ::= TEXTUAL-CONVENTION
    STATUS        current
    DESCRIPTION
        ""
    SYNTAX        BITS
    {
        ether(0),
        dce(1),
        fc(2)
    }

CfprSwEthLanPcInlineState ::= TEXTUAL-CONVENTION
    STATUS        current
    DESCRIPTION
        ""
    SYNTAX        INTEGER
    {
        enabled(1),
        disabled(2)
    }

CfprSwEthLanPcTransport ::= TEXTUAL-CONVENTION
    STATUS        current
    DESCRIPTION
        ""
    SYNTAX        BITS
    {
        ether(0),
        dce(1),
        fc(2)
    }

CfprSwEthMonTransport ::= TEXTUAL-CONVENTION
    STATUS        current
    DESCRIPTION
        ""
    SYNTAX        BITS
    {
        ether(0),
        dce(1),
        fc(2)
    }

CfprSwEthMonType ::= TEXTUAL-CONVENTION
    STATUS        current
    DESCRIPTION
        ""
    SYNTAX        BITS
    {
        lan(0),
        san(1),
        ipc(2)
    }

CfprSwEthMonDestEpTransport ::= TEXTUAL-CONVENTION
    STATUS        current
    DESCRIPTION
        ""
    SYNTAX        BITS
    {
        ether(0),
        dce(1),
        fc(2)
    }

CfprSwEthMonFsmCurrentFsm ::= TEXTUAL-CONVENTION
    STATUS        current
    DESCRIPTION
        ""
    SYNTAX        INTEGER
    {
        nop(0),
        deploy(867)
    }

CfprSwEthMonFsmStageName ::= TEXTUAL-CONVENTION
    STATUS        current
    DESCRIPTION
        ""
    SYNTAX        INTEGER
    {
        nop(0),
        deployBegin(867),
        deployUpdateEthMon(868),
        deployFail(1004),
        deploySuccess(1005)
    }

CfprSwEthMonFsmTaskItem ::= TEXTUAL-CONVENTION
    STATUS        current
    DESCRIPTION
        ""
    SYNTAX        INTEGER
    {
        nop(0),
        deploy(867)
    }

CfprSwEthMonSrcEpTransport ::= TEXTUAL-CONVENTION
    STATUS        current
    DESCRIPTION
        ""
    SYNTAX        BITS
    {
        ether(0),
        dce(1),
        fc(2)
    }

CfprSwEthTargetEpAdminState ::= TEXTUAL-CONVENTION
    STATUS        current
    DESCRIPTION
        ""
    SYNTAX        INTEGER
    {
        enabled(1),
        disabled(2)
    }

CfprSwEthTargetEpTransport ::= TEXTUAL-CONVENTION
    STATUS        current
    DESCRIPTION
        ""
    SYNTAX        BITS
    {
        ether(0),
        dce(1),
        fc(2)
    }

CfprSwExtUtilityFsmCurrentFsm ::= TEXTUAL-CONVENTION
    STATUS        current
    DESCRIPTION
        ""
    SYNTAX        INTEGER
    {
        nop(0),
        confPortBreakout(1694)
    }

CfprSwExtUtilityFsmStageName ::= TEXTUAL-CONVENTION
    STATUS        current
    DESCRIPTION
        ""
    SYNTAX        INTEGER
    {
        nop(0),
        confPortBreakoutBegin(1694),
        confPortBreakoutPortInventorySwA(1695),
        confPortBreakoutPortInventorySwB(1696),
        confPortBreakoutConfigSwA(1697),
        confPortBreakoutConfigSwB(1698),
        confPortBreakoutVerifyBreakoutConfig(1699),
        confPortBreakoutSuccess(1700),
        confPortBreakoutFail(1701)
    }

CfprSwExtUtilityFsmTaskItem ::= TEXTUAL-CONVENTION
    STATUS        current
    DESCRIPTION
        ""
    SYNTAX        INTEGER
    {
        nop(0),
        confPortBreakout(1694)
    }

CfprSwFabricZoneNsAllocStatus ::= TEXTUAL-CONVENTION
    STATUS        current
    DESCRIPTION
        ""
    SYNTAX        INTEGER
    {
        available(0),
        full(1)
    }

CfprSwFcEstcEpTransport ::= TEXTUAL-CONVENTION
    STATUS        current
    DESCRIPTION
        ""
    SYNTAX        BITS
    {
        ether(0),
        dce(1),
        fc(2)
    }

CfprSwFcMonTransport ::= TEXTUAL-CONVENTION
    STATUS        current
    DESCRIPTION
        ""
    SYNTAX        BITS
    {
        ether(0),
        dce(1),
        fc(2)
    }

CfprSwFcMonType ::= TEXTUAL-CONVENTION
    STATUS        current
    DESCRIPTION
        ""
    SYNTAX        BITS
    {
        lan(0),
        san(1),
        ipc(2)
    }

CfprSwFcMonDestEpTransport ::= TEXTUAL-CONVENTION
    STATUS        current
    DESCRIPTION
        ""
    SYNTAX        BITS
    {
        ether(0),
        dce(1),
        fc(2)
    }

CfprSwFcMonFsmCurrentFsm ::= TEXTUAL-CONVENTION
    STATUS        current
    DESCRIPTION
        ""
    SYNTAX        INTEGER
    {
        nop(0),
        deploy(869)
    }

CfprSwFcMonFsmStageName ::= TEXTUAL-CONVENTION
    STATUS        current
    DESCRIPTION
        ""
    SYNTAX        INTEGER
    {
        nop(0),
        deployBegin(869),
        deployUpdateFcMon(870),
        deployFail(1006),
        deploySuccess(1007)
    }

CfprSwFcMonFsmTaskItem ::= TEXTUAL-CONVENTION
    STATUS        current
    DESCRIPTION
        ""
    SYNTAX        INTEGER
    {
        nop(0),
        deploy(869)
    }

CfprSwFcMonSrcEpTransport ::= TEXTUAL-CONVENTION
    STATUS        current
    DESCRIPTION
        ""
    SYNTAX        BITS
    {
        ether(0),
        dce(1),
        fc(2)
    }

CfprSwFcSanBorderTransport ::= TEXTUAL-CONVENTION
    STATUS        current
    DESCRIPTION
        ""
    SYNTAX        BITS
    {
        ether(0),
        dce(1),
        fc(2)
    }

CfprSwFcSanBorderUplinkTrunking ::= TEXTUAL-CONVENTION
    STATUS        current
    DESCRIPTION
        ""
    SYNTAX        INTEGER
    {
        disabled(0),
        enabled(1)
    }

CfprSwFcSanBorderFsmCurrentFsm ::= TEXTUAL-CONVENTION
    STATUS        current
    DESCRIPTION
        ""
    SYNTAX        INTEGER
    {
        nop(0),
        deploy(226),
        activateZoneSet(1332)
    }

CfprSwFcSanBorderFsmStageName ::= TEXTUAL-CONVENTION
    STATUS        current
    DESCRIPTION
        ""
    SYNTAX        INTEGER
    {
        nop(0),
        deployBegin(226),
        deployUpdateConnectivity(227),
        deployFail(438),
        deploySuccess(439),
        activateZoneSetBegin(1332),
        activateZoneSetUpdateZones(1333),
        activateZoneSetFail(1466),
        activateZoneSetSuccess(1467)
    }

CfprSwFcSanBorderFsmTaskItem ::= TEXTUAL-CONVENTION
    STATUS        current
    DESCRIPTION
        ""
    SYNTAX        INTEGER
    {
        nop(0),
        deploy(226),
        activateZoneSet(1332)
    }

CfprSwFcSanEpTransport ::= TEXTUAL-CONVENTION
    STATUS        current
    DESCRIPTION
        ""
    SYNTAX        BITS
    {
        ether(0),
        dce(1),
        fc(2)
    }

CfprSwFcSanMonTransport ::= TEXTUAL-CONVENTION
    STATUS        current
    DESCRIPTION
        ""
    SYNTAX        BITS
    {
        ether(0),
        dce(1),
        fc(2)
    }

CfprSwFcSanPcTransport ::= TEXTUAL-CONVENTION
    STATUS        current
    DESCRIPTION
        ""
    SYNTAX        BITS
    {
        ether(0),
        dce(1),
        fc(2)
    }

CfprSwFcServerZoneGroupLc ::= TEXTUAL-CONVENTION
    STATUS        current
    DESCRIPTION
        ""
    SYNTAX        INTEGER
    {
        available(0),
        allocated(1),
        deallocated(2),
        repurposed(3)
    }

CfprSwFcZoneLc ::= TEXTUAL-CONVENTION
    STATUS        current
    DESCRIPTION
        ""
    SYNTAX        INTEGER
    {
        available(0),
        allocated(1),
        deallocated(2),
        repurposed(3)
    }

CfprSwFcZoneMemberLc ::= TEXTUAL-CONVENTION
    STATUS        current
    DESCRIPTION
        ""
    SYNTAX        INTEGER
    {
        available(0),
        allocated(1),
        deallocated(2),
        repurposed(3)
    }

CfprSwFcZoneSetLc ::= TEXTUAL-CONVENTION
    STATUS        current
    DESCRIPTION
        ""
    SYNTAX        INTEGER
    {
        available(0),
        allocated(1),
        deallocated(2),
        repurposed(3)
    }

CfprSwFcoeEstcEpTransport ::= TEXTUAL-CONVENTION
    STATUS        current
    DESCRIPTION
        ""
    SYNTAX        BITS
    {
        ether(0),
        dce(1),
        fc(2)
    }

CfprSwFcoeSanEpTransport ::= TEXTUAL-CONVENTION
    STATUS        current
    DESCRIPTION
        ""
    SYNTAX        BITS
    {
        ether(0),
        dce(1),
        fc(2)
    }

CfprSwFcoeSanEpUdldAdminState ::= TEXTUAL-CONVENTION
    STATUS        current
    DESCRIPTION
        ""
    SYNTAX        INTEGER
    {
        enabled(1),
        disabled(2)
    }

CfprSwFcoeSanEpUdldMode ::= TEXTUAL-CONVENTION
    STATUS        current
    DESCRIPTION
        ""
    SYNTAX        INTEGER
    {
        normal(0),
        aggressive(1)
    }

CfprSwFcoeSanPcTransport ::= TEXTUAL-CONVENTION
    STATUS        current
    DESCRIPTION
        ""
    SYNTAX        BITS
    {
        ether(0),
        dce(1),
        fc(2)
    }

CfprSwFlowMonitorAdminState ::= TEXTUAL-CONVENTION
    STATUS        current
    DESCRIPTION
        ""
    SYNTAX        INTEGER
    {
        enabled(1),
        disabled(2)
    }

CfprSwLanBorderType ::= TEXTUAL-CONVENTION
    STATUS        current
    DESCRIPTION
        ""
    SYNTAX        BITS
    {
        lan(0),
        san(1),
        ipc(2)
    }

CfprSwLanEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprSwLanEpType ::= TEXTUAL-CONVENTION
    STATUS        current
    DESCRIPTION
        ""
    SYNTAX        BITS
    {
        lan(0),
        san(1),
        ipc(2)
    }

CfprSwLanMonType ::= TEXTUAL-CONVENTION
    STATUS        current
    DESCRIPTION
        ""
    SYNTAX        BITS
    {
        lan(0),
        san(1),
        ipc(2)
    }

CfprSwLanPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprSwLanPcType ::= TEXTUAL-CONVENTION
    STATUS        current
    DESCRIPTION
        ""
    SYNTAX        BITS
    {
        lan(0),
        san(1),
        ipc(2)
    }

CfprSwMonAdminState ::= TEXTUAL-CONVENTION
    STATUS        current
    DESCRIPTION
        ""
    SYNTAX        INTEGER
    {
        enabled(1),
        disabled(2)
    }

CfprSwMonDomainLocale ::= TEXTUAL-CONVENTION
    STATUS        current
    DESCRIPTION
        ""
    SYNTAX        BITS
    {
        server(0),
        chassis(1),
        internal(2),
        external(3)
    }

CfprSwMonLifeCycle ::= TEXTUAL-CONVENTION
    STATUS        current
    DESCRIPTION
        ""
    SYNTAX        INTEGER
    {
        normal(1),
        new(2),
        deleted(3)
    }

CfprSwMonSrcEpLocale ::= TEXTUAL-CONVENTION
    STATUS        current
    DESCRIPTION
        ""
    SYNTAX        BITS
    {
        server(0),
        chassis(1),
        internal(2),
        external(3)
    }

CfprSwNFConfigStatus ::= TEXTUAL-CONVENTION
    STATUS        current
    DESCRIPTION
        ""
    SYNTAX        INTEGER
    {
        ok(1),
        incomplete(2)
    }

CfprSwNetflowExporterProtocol ::= TEXTUAL-CONVENTION
    STATUS        current
    DESCRIPTION
        ""
    SYNTAX        INTEGER
    {
        netflow(1)
    }

CfprSwNetflowMonSessionProtocol ::= TEXTUAL-CONVENTION
    STATUS        current
    DESCRIPTION
        ""
    SYNTAX        INTEGER
    {
        netflow(1)
    }

CfprSwNetflowMonitorProtocol ::= TEXTUAL-CONVENTION
    STATUS        current
    DESCRIPTION
        ""
    SYNTAX        INTEGER
    {
        netflow(1)
    }

CfprSwNetflowRecordDefProtocol ::= TEXTUAL-CONVENTION
    STATUS        current
    DESCRIPTION
        ""
    SYNTAX        INTEGER
    {
        netflow(1)
    }

CfprSwPIoEpIfType ::= TEXTUAL-CONVENTION
    STATUS        current
    DESCRIPTION
        ""
    SYNTAX        INTEGER
    {
        unknown(0),
        physical(1),
        aggregation(2),
        virtual(3)
    }

CfprSwPIoEpLc ::= TEXTUAL-CONVENTION
    STATUS        current
    DESCRIPTION
        ""
    SYNTAX        INTEGER
    {
        available(0),
        allocated(1),
        deallocated(2),
        repurposed(3),
        pending(4)
    }

CfprSwPcMode ::= TEXTUAL-CONVENTION
    STATUS        current
    DESCRIPTION
        ""
    SYNTAX        INTEGER
    {
        active(0),
        on(1)
    }

CfprSwPcModeState ::= TEXTUAL-CONVENTION
    STATUS        current
    DESCRIPTION
        ""
    SYNTAX        INTEGER
    {
        disabled(0),
        enabled(1)
    }

CfprSwPeerStatus ::= TEXTUAL-CONVENTION
    STATUS        current
    DESCRIPTION
        ""
    SYNTAX        INTEGER
    {
        existing(1),
        nonexisting(2)
    }

CfprSwPhysFsmCurrentFsm ::= TEXTUAL-CONVENTION
    STATUS        current
    DESCRIPTION
        ""
    SYNTAX        INTEGER
    {
        nop(0),
        confPhysical(1121)
    }

CfprSwPhysFsmStageName ::= TEXTUAL-CONVENTION
    STATUS        current
    DESCRIPTION
        ""
    SYNTAX        INTEGER
    {
        nop(0),
        confPhysicalBegin(1121),
        confPhysicalPortInventorySwA(1122),
        confPhysicalPortInventorySwB(1123),
        confPhysicalConfigSwA(1124),
        confPhysicalConfigSwB(1125),
        confPhysicalVerifyPhysConfig(1126),
        confPhysicalSuccess(1127),
        confPhysicalFail(1128)
    }

CfprSwPhysFsmTaskItem ::= TEXTUAL-CONVENTION
    STATUS        current
    DESCRIPTION
        ""
    SYNTAX        INTEGER
    {
        nop(0),
        confPhysical(1121)
    }

CfprSwPktCaptureLifeCycle ::= TEXTUAL-CONVENTION
    STATUS        current
    DESCRIPTION
        ""
    SYNTAX        INTEGER
    {
        normal(1),
        new(2),
        deleted(3)
    }

CfprSwPortBreakoutPortId ::= TEXTUAL-CONVENTION
    STATUS        current
    DESCRIPTION
        ""
    SYNTAX        Gauge32 (1..4)

CfprSwPortBreakoutSlotId ::= TEXTUAL-CONVENTION
    STATUS        current
    DESCRIPTION
        ""
    SYNTAX        Gauge32 (2..3)

CfprSwSanBorderType ::= TEXTUAL-CONVENTION
    STATUS        current
    DESCRIPTION
        ""
    SYNTAX        BITS
    {
        lan(0),
        san(1),
        ipc(2)
    }

CfprSwSanEpIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprSwSanEpType ::= TEXTUAL-CONVENTION
    STATUS        current
    DESCRIPTION
        ""
    SYNTAX        BITS
    {
        lan(0),
        san(1),
        ipc(2)
    }

CfprSwSanMonType ::= TEXTUAL-CONVENTION
    STATUS        current
    DESCRIPTION
        ""
    SYNTAX        BITS
    {
        lan(0),
        san(1),
        ipc(2)
    }

CfprSwSanPcIfRole ::= TEXTUAL-CONVENTION
    STATUS        current
    DESCRIPTION
        ""
    SYNTAX        INTEGER
    {
        unknown(0),
        network(1),
        server(2),
        mgmt(3),
        diag(4),
        storage(5),
        monitor(6),
        fcoeStorage(7),
        nasStorage(8),
        fcoeNasStorage(9),
        fcoeUplink(10),
        networkFcoeUplink(11),
        service(12)
    }

CfprSwSanPcType ::= TEXTUAL-CONVENTION
    STATUS        current
    DESCRIPTION
        ""
    SYNTAX        BITS
    {
        lan(0),
        san(1),
        ipc(2)
    }

CfprSwSspEthLanMonTransport ::= TEXTUAL-CONVENTION
    STATUS        current
    DESCRIPTION
        ""
    SYNTAX        BITS
    {
        ether(0),
        dce(1),
        fc(2)
    }

CfprSwSspEthMonTransport ::= TEXTUAL-CONVENTION
    STATUS        current
    DESCRIPTION
        ""
    SYNTAX        BITS
    {
        ether(0),
        dce(1),
        fc(2)
    }

CfprSwSspEthMonType ::= TEXTUAL-CONVENTION
    STATUS        current
    DESCRIPTION
        ""
    SYNTAX        BITS
    {
        lan(0),
        san(1),
        ipc(2)
    }

CfprSwSspEthMonFsmCurrentFsm ::= TEXTUAL-CONVENTION
    STATUS        current
    DESCRIPTION
        ""
    SYNTAX        INTEGER
    {
        nop(0),
        deploy(1822)
    }

CfprSwSspEthMonFsmStageName ::= TEXTUAL-CONVENTION
    STATUS        current
    DESCRIPTION
        ""
    SYNTAX        INTEGER
    {
        nop(0),
        deployBegin(1822),
        deployUpdateSspEthMon(1823),
        deployFail(1824),
        deploySuccess(1825),
        deployReenableSspEthMon(2053)
    }

CfprSwSspEthMonFsmTaskFlags ::= TEXTUAL-CONVENTION
    STATUS        current
    DESCRIPTION
        ""
    SYNTAX        BITS
    {
        samDmeSwSspEthMonDeployNormal(37),
        samDmeSwSspEthMonDeployReenable(38)
    }

CfprSwSspEthMonFsmTaskItem ::= TEXTUAL-CONVENTION
    STATUS        current
    DESCRIPTION
        ""
    SYNTAX        INTEGER
    {
        nop(0),
        deploy(1822)
    }

CfprSwSspEthMonSrcPhyEpFsmCurrentFsm ::= TEXTUAL-CONVENTION
    STATUS        current
    DESCRIPTION
        ""
    SYNTAX        INTEGER
    {
        nop(0),
        delete(1859)
    }

CfprSwSspEthMonSrcPhyEpFsmStageName ::= TEXTUAL-CONVENTION
    STATUS        current
    DESCRIPTION
        ""
    SYNTAX        INTEGER
    {
        nop(0),
        deleteBegin(1859),
        deleteDeletePcapFile(1860),
        deleteFail(1890),
        deleteSuccess(1891)
    }

CfprSwSspEthMonSrcPhyEpFsmTaskItem ::= TEXTUAL-CONVENTION
    STATUS        current
    DESCRIPTION
        ""
    SYNTAX        INTEGER
    {
        nop(0),
        delete(1859)
    }

CfprSwSspLanMonType ::= TEXTUAL-CONVENTION
    STATUS        current
    DESCRIPTION
        ""
    SYNTAX        BITS
    {
        lan(0),
        san(1),
        ipc(2)
    }

CfprSwSspMonAdminState ::= TEXTUAL-CONVENTION
    STATUS        current
    DESCRIPTION
        ""
    SYNTAX        INTEGER
    {
        enabled(1),
        disabled(2)
    }

CfprSwSspMonDelPcap ::= TEXTUAL-CONVENTION
    STATUS        current
    DESCRIPTION
        ""
    SYNTAX        INTEGER
    {
        enabled(1),
        disabled(2)
    }

CfprSwSspMonDomainLocale ::= TEXTUAL-CONVENTION
    STATUS        current
    DESCRIPTION
        ""
    SYNTAX        BITS
    {
        server(0),
        chassis(1),
        internal(2),
        external(3)
    }

CfprSwSubGroupAggrPortId ::= TEXTUAL-CONVENTION
    STATUS        current
    DESCRIPTION
        ""
    SYNTAX        Gauge32 (1..48)

CfprSwSubGroupSlotId ::= TEXTUAL-CONVENTION
    STATUS        current
    DESCRIPTION
        ""
    SYNTAX        Gauge32 (1..4)

CfprSwSystemStatsThresholded ::= TEXTUAL-CONVENTION
    STATUS        current
    DESCRIPTION
        ""
    SYNTAX        BITS
    {
        load(0),
        loadAvg(1),
        loadMax(2),
        loadMin(3),
        memAvailable(4),
        memAvailableAvg(5),
        memAvailableMax(6),
        memAvailableMin(7),
        memCached(8),
        memCachedAvg(9),
        memCachedMax(10),
        memCachedMin(11)
    }

CfprSwSystemStatsHistThresholded ::= TEXTUAL-CONVENTION
    STATUS        current
    DESCRIPTION
        ""
    SYNTAX        BITS
    {
        load(0),
        loadAvg(1),
        loadMax(2),
        loadMin(3),
        memAvailable(4),
        memAvailableAvg(5),
        memAvailableMax(6),
        memAvailableMin(7),
        memCached(8),
        memCachedAvg(9),
        memCachedMax(10),
        memCachedMin(11)
    }

CfprSwTargetEpType ::= TEXTUAL-CONVENTION
    STATUS        current
    DESCRIPTION
        ""
    SYNTAX        BITS
    {
        lan(0),
        san(1),
        ipc(2)
    }

CfprSwUlanPurpose ::= TEXTUAL-CONVENTION
    STATUS        current
    DESCRIPTION
        ""
    SYNTAX        INTEGER
    {
        management(1),
        boot(2),
        reserved1(3),
        reserved2(4)
    }

CfprSwUtilityDomainLocale ::= TEXTUAL-CONVENTION
    STATUS        current
    DESCRIPTION
        ""
    SYNTAX        BITS
    {
        server(0),
        chassis(1),
        internal(2),
        external(3)
    }

CfprSwUtilityDomainType ::= TEXTUAL-CONVENTION
    STATUS        current
    DESCRIPTION
        ""
    SYNTAX        BITS
    {
        lan(0),
        san(1),
        ipc(2)
    }

CfprSwUtilityDomainFsmCurrentFsm ::= TEXTUAL-CONVENTION
    STATUS        current
    DESCRIPTION
        ""
    SYNTAX        INTEGER
    {
        nop(0),
        deploy(228)
    }

CfprSwUtilityDomainFsmStageName ::= TEXTUAL-CONVENTION
    STATUS        current
    DESCRIPTION
        ""
    SYNTAX        INTEGER
    {
        nop(0),
        deployBegin(228),
        deployUpdateConnectivity(229),
        deployFail(440),
        deploySuccess(441)
    }

CfprSwUtilityDomainFsmTaskItem ::= TEXTUAL-CONVENTION
    STATUS        current
    DESCRIPTION
        ""
    SYNTAX        INTEGER
    {
        nop(0),
        deploy(228)
    }

CfprSwVlanLc ::= TEXTUAL-CONVENTION
    STATUS        current
    DESCRIPTION
        ""
    SYNTAX        INTEGER
    {
        available(0),
        allocated(1),
        deallocated(2),
        repurposed(3),
        pending(4),
        provisioned(5)
    }

CfprSwVlanCompType ::= TEXTUAL-CONVENTION
    STATUS        current
    DESCRIPTION
        ""
    SYNTAX        INTEGER
    {
        included(1),
        excluded(2)
    }

CfprSwVlanConfigStatusType ::= TEXTUAL-CONVENTION
    STATUS        current
    DESCRIPTION
        ""
    SYNTAX        INTEGER
    {
        applied(1),
        unApplied(2)
    }

CfprSwVlanGroupType ::= TEXTUAL-CONVENTION
    STATUS        current
    DESCRIPTION
        ""
    SYNTAX        INTEGER
    {
        compressed(1),
        uncompressed(2)
    }

CfprSwVlanPortNsAllocStatus ::= TEXTUAL-CONVENTION
    STATUS        current
    DESCRIPTION
        ""
    SYNTAX        INTEGER
    {
        available(0),
        exceeded(1)
    }

CfprSysdebugAutoCoreFileExportTargetProto ::= TEXTUAL-CONVENTION
    STATUS        current
    DESCRIPTION
        ""
    SYNTAX        INTEGER
    {
        none(0),
        ftp(1),
        tftp(2),
        scp(3),
        http(4),
        sftp(5),
        nfsCopy(6),
        https(11)
    }

CfprSysdebugAutoCoreFileExportTargetFsmCurrentFsm ::= TEXTUAL-CONVENTION
    STATUS        current
    DESCRIPTION
        ""
    SYNTAX        INTEGER
    {
        nop(0),
        configure(216)
    }

CfprSysdebugAutoCoreFileExportTargetFsmStageName ::= TEXTUAL-CONVENTION
    STATUS        current
    DESCRIPTION
        ""
    SYNTAX        INTEGER
    {
        nop(0),
        configureBegin(216),
        configureLocal(217),
        configurePeer(218),
        configureFail(444),
        configureSuccess(445)
    }

CfprSysdebugAutoCoreFileExportTargetFsmTaskItem ::= TEXTUAL-CONVENTION
    STATUS        current
    DESCRIPTION
        ""
    SYNTAX        INTEGER
    {
        nop(0),
        configure(216)
    }

CfprSysdebugBackupBehaviorInterval ::= TEXTUAL-CONVENTION
    STATUS        current
    DESCRIPTION
        ""
    SYNTAX        INTEGER
    {
        never(0),
        n1hour(3600),
        n2hours(7200),
        n4hours(14400),
        n8hours(28800),
        n24hours(86400),
        n1week(604800),
        n1month(2592000)
    }

CfprSysdebugBackupBehaviorProto ::= TEXTUAL-CONVENTION
    STATUS        current
    DESCRIPTION
        ""
    SYNTAX        INTEGER
    {
        none(0),
        ftp(1),
        tftp(2),
        scp(3),
        http(4),
        sftp(5),
        nfsCopy(6),
        https(11)
    }

CfprSysdebugBackupFormat ::= TEXTUAL-CONVENTION
    STATUS        current
    DESCRIPTION
        ""
    SYNTAX        INTEGER
    {
        ascii(1),
        binary(2)
    }

CfprSysdebugCoreExportStatus ::= TEXTUAL-CONVENTION
    STATUS        current
    DESCRIPTION
        ""
    SYNTAX        INTEGER
    {
        success(1),
        failure(2)
    }

CfprSysdebugCoreFileAdminState ::= TEXTUAL-CONVENTION
    STATUS        current
    DESCRIPTION
        ""
    SYNTAX        INTEGER
    {
        init(0),
        prepareDownload(1),
        downloaded(2)
    }

CfprSysdebugCoreFileOperState ::= TEXTUAL-CONVENTION
    STATUS        current
    DESCRIPTION
        ""
    SYNTAX        INTEGER
    {
        unavailable(0),
        available(1),
        availableOnSubordinate(2),
        inProgress(3),
        failed(4)
    }

CfprSysdebugCoreFsmCurrentFsm ::= TEXTUAL-CONVENTION
    STATUS        current
    DESCRIPTION
        ""
    SYNTAX        INTEGER
    {
        nop(0),
        download(1041)
    }

CfprSysdebugCoreFsmStageName ::= TEXTUAL-CONVENTION
    STATUS        current
    DESCRIPTION
        ""
    SYNTAX        INTEGER
    {
        nop(0),
        downloadBegin(1041),
        downloadCopySub(1042),
        downloadCopyPrimary(1043),
        downloadDeleteSub(1044),
        downloadDeletePrimary(1045),
        downloadFail(1053),
        downloadSuccess(1054)
    }

CfprSysdebugCoreFsmTaskItem ::= TEXTUAL-CONVENTION
    STATUS        current
    DESCRIPTION
        ""
    SYNTAX        INTEGER
    {
        nop(0),
        download(1041)
    }

CfprSysdebugEpLogAdminState ::= TEXTUAL-CONVENTION
    STATUS        current
    DESCRIPTION
        ""
    SYNTAX        INTEGER
    {
        policy(0),
        backup(1),
        clear(2)
    }

CfprSysdebugEpLogBackupAction ::= TEXTUAL-CONVENTION
    STATUS        current
    DESCRIPTION
        ""
    SYNTAX        BITS
    {
        logFull(0),
        onClear(1),
        timer(2),
        onAssocChange(3)
    }

CfprSysdebugEpLogCapacity ::= TEXTUAL-CONVENTION
    STATUS        current
    DESCRIPTION
        ""
    SYNTAX        INTEGER
    {
        unknown(0),
        available(1),
        low(2),
        veryLow(3),
        full(4)
    }

CfprSysdebugEpLogType ::= TEXTUAL-CONVENTION
    STATUS        current
    DESCRIPTION
        ""
    SYNTAX        INTEGER
    {
        sel(1),
        obfl(2),
        syslog(3)
    }

CfprSysdebugExportStatus ::= TEXTUAL-CONVENTION
    STATUS        current
    DESCRIPTION
        ""
    SYNTAX        INTEGER
    {
        success(1),
        failure(2)
    }

CfprSysdebugLogControlDomainEnum ::= TEXTUAL-CONVENTION
    STATUS        current
    DESCRIPTION
        ""
    SYNTAX        INTEGER
    {
        sysmgmt(0)
    }

CfprSysdebugLogControlEpFsmCurrentFsm ::= TEXTUAL-CONVENTION
    STATUS        current
    DESCRIPTION
        ""
    SYNTAX        INTEGER
    {
        nop(0),
        logControlPersist(219)
    }

CfprSysdebugLogControlEpFsmStageName ::= TEXTUAL-CONVENTION
    STATUS        current
    DESCRIPTION
        ""
    SYNTAX        INTEGER
    {
        nop(0),
        logControlPersistBegin(219),
        logControlPersistLocal(220),
        logControlPersistPeer(221),
        logControlPersistFail(446),
        logControlPersistSuccess(447)
    }

CfprSysdebugLogControlEpFsmTaskItem ::= TEXTUAL-CONVENTION
    STATUS        current
    DESCRIPTION
        ""
    SYNTAX        INTEGER
    {
        nop(0),
        logControlPersist(219)
    }

CfprSysdebugLogControlLevel ::= TEXTUAL-CONVENTION
    STATUS        current
    DESCRIPTION
        ""
    SYNTAX        INTEGER
    {
        debug0(0),
        debug1(1),
        debug2(2),
        debug3(3),
        debug4(4),
        info(5),
        warn(6),
        minor(7),
        major(8),
        crit(9)
    }

CfprSysdebugLogExportPolicyProto ::= TEXTUAL-CONVENTION
    STATUS        current
    DESCRIPTION
        ""
    SYNTAX        INTEGER
    {
        none(0),
        ftp(1),
        tftp(2),
        scp(3),
        http(4),
        sftp(5),
        nfsCopy(6),
        https(11)
    }

CfprSysdebugLogExportPolicyFsmCurrentFsm ::= TEXTUAL-CONVENTION
    STATUS        current
    DESCRIPTION
        ""
    SYNTAX        INTEGER
    {
        nop(0),
        configure(1611)
    }

CfprSysdebugLogExportPolicyFsmStageName ::= TEXTUAL-CONVENTION
    STATUS        current
    DESCRIPTION
        ""
    SYNTAX        INTEGER
    {
        nop(0),
        configureBegin(1611),
        configureLocal(1612),
        configurePeer(1613),
        configureFail(1659),
        configureSuccess(1660)
    }

CfprSysdebugLogExportPolicyFsmTaskItem ::= TEXTUAL-CONVENTION
    STATUS        current
    DESCRIPTION
        ""
    SYNTAX        INTEGER
    {
        nop(0),
        configure(1611)
    }

CfprSysdebugMEpLogOperState ::= TEXTUAL-CONVENTION
    STATUS        current
    DESCRIPTION
        ""
    SYNTAX        INTEGER
    {
        ok(0),
        permissionDeniedError(1),
        remoteCommunicationError(2),
        bmcCommunicationError(3),
        internalFprmError(4)
    }

CfprSysdebugManualCoreFileExportTargetAdminState ::= TEXTUAL-CONVENTION
    STATUS        current
    DESCRIPTION
        ""
    SYNTAX        INTEGER
    {
        enabled(1),
        disabled(2)
    }

CfprSysdebugManualCoreFileExportTargetProto ::= TEXTUAL-CONVENTION
    STATUS        current
    DESCRIPTION
        ""
    SYNTAX        INTEGER
    {
        none(0),
        ftp(1),
        tftp(2),
        scp(3),
        http(4),
        sftp(5),
        nfsCopy(6),
        https(11)
    }

CfprSysdebugManualCoreFileExportTargetFsmCurrentFsm ::= TEXTUAL-CONVENTION
    STATUS        current
    DESCRIPTION
        ""
    SYNTAX        INTEGER
    {
        nop(0),
        export(214)
    }

CfprSysdebugManualCoreFileExportTargetFsmStageName ::= TEXTUAL-CONVENTION
    STATUS        current
    DESCRIPTION
        ""
    SYNTAX        INTEGER
    {
        nop(0),
        exportBegin(214),
        exportExecute(215),
        exportFail(448),
        exportSuccess(449)
    }

CfprSysdebugManualCoreFileExportTargetFsmTaskItem ::= TEXTUAL-CONVENTION
    STATUS        current
    DESCRIPTION
        ""
    SYNTAX        INTEGER
    {
        nop(0),
        export(214)
    }

CfprSysdebugTSCmdOptMajorType ::= TEXTUAL-CONVENTION
    STATUS        current
    DESCRIPTION
        ""
    SYNTAX        INTEGER
    {
        chassis(0),
        fex(1),
        server(2),
        fprm(3),
        fprmMgmt(4)
    }

CfprSysdebugTechSupportAdminState ::= TEXTUAL-CONVENTION
    STATUS        current
    DESCRIPTION
        ""
    SYNTAX        INTEGER
    {
        init(0),
        start(1),
        created(2),
        prepareDownload(3),
        delete(4)
    }

CfprSysdebugTechSupportFsmCurrentFsm ::= TEXTUAL-CONVENTION
    STATUS        current
    DESCRIPTION
        ""
    SYNTAX        INTEGER
    {
        nop(0),
        initiate(881),
        deleteTechSupFile(883),
        download(886)
    }

CfprSysdebugTechSupportFsmStageName ::= TEXTUAL-CONVENTION
    STATUS        current
    DESCRIPTION
        ""
    SYNTAX        INTEGER
    {
        nop(0),
        initiateBegin(881),
        initiateLocal(882),
        deleteTechSupFileBegin(883),
        deleteTechSupFileLocal(884),
        deleteTechSupFilePeer(885),
        downloadBegin(886),
        downloadCopySub(887),
        downloadCopyPrimary(888),
        downloadDeleteSub(889),
        downloadDeletePrimary(890),
        deleteTechSupFileFail(1008),
        deleteTechSupFileSuccess(1009),
        downloadFail(1010),
        downloadSuccess(1011),
        initiateFail(1012),
        initiateSuccess(1013)
    }

CfprSysdebugTechSupportFsmTaskItem ::= TEXTUAL-CONVENTION
    STATUS        current
    DESCRIPTION
        ""
    SYNTAX        INTEGER
    {
        nop(0),
        initiate(881),
        deleteTechSupFile(883),
        download(886)
    }

CfprSysdebugTechSupportOperState ::= TEXTUAL-CONVENTION
    STATUS        current
    DESCRIPTION
        ""
    SYNTAX        INTEGER
    {
        unavailable(0),
        available(1),
        availableOnSubordinate(2),
        inProgress(3),
        failed(4)
    }

CfprSysfileExporterPostAction ::= TEXTUAL-CONVENTION
    STATUS        current
    DESCRIPTION
        ""
    SYNTAX        INTEGER
    {
        none(0),
        remove(1)
    }

CfprSysfileMutationAction ::= TEXTUAL-CONVENTION
    STATUS        current
    DESCRIPTION
        ""
    SYNTAX        INTEGER
    {
        none(0),
        remove(1)
    }

CfprSysfileMutationFsmCurrentFsm ::= TEXTUAL-CONVENTION
    STATUS        current
    DESCRIPTION
        ""
    SYNTAX        INTEGER
    {
        nop(0),
        single(209),
        global(211)
    }

CfprSysfileMutationFsmStageName ::= TEXTUAL-CONVENTION
    STATUS        current
    DESCRIPTION
        ""
    SYNTAX        INTEGER
    {
        nop(0),
        singleBegin(209),
        singleExecute(210),
        globalBegin(211),
        globalLocal(212),
        globalPeer(213),
        globalFail(450),
        globalSuccess(451),
        singleFail(452),
        singleSuccess(453)
    }

CfprSysfileMutationFsmTaskItem ::= TEXTUAL-CONVENTION
    STATUS        current
    DESCRIPTION
        ""
    SYNTAX        INTEGER
    {
        nop(0),
        single(209),
        global(211)
    }

CfprTopInfoPolicyState ::= TEXTUAL-CONVENTION
    STATUS        current
    DESCRIPTION
        ""
    SYNTAX        INTEGER
    {
        disabled(0),
        enabled(1)
    }

CfprTopMode ::= TEXTUAL-CONVENTION
    STATUS        current
    DESCRIPTION
        ""
    SYNTAX        INTEGER
    {
        unspecified(0),
        standAlone(1),
        cluster(2)
    }

CfprTrigAckOperState ::= TEXTUAL-CONVENTION
    STATUS        current
    DESCRIPTION
        ""
    SYNTAX        INTEGER
    {
        untriggered(0),
        evaluationPending(1),
        evaluated(2),
        waitingForUser(3),
        waitingForMaintWindow(4),
        applyPending(5),
        applied(6),
        waitingForDependency(7),
        none(8),
        expired(9),
        pending(10),
        active(11)
    }

CfprTrigAckPrevOperState ::= TEXTUAL-CONVENTION
    STATUS        current
    DESCRIPTION
        ""
    SYNTAX        INTEGER
    {
        untriggered(0),
        evaluationPending(1),
        evaluated(2),
        waitingForUser(3),
        waitingForMaintWindow(4),
        applyPending(5),
        applied(6),
        waitingForDependency(7),
        none(8),
        expired(9),
        pending(10),
        active(11)
    }

CfprTrigAckChangeDetails ::= TEXTUAL-CONVENTION
    STATUS        current
    DESCRIPTION
        ""
    SYNTAX        BITS
    {
        binding(0),
        hostVirtEthIf(1),
        hostNonvirtEthIf(2),
        hostEthIfProfile(3),
        hostEthIfQos(4),
        hostEthIfNwCtrl(5),
        hostVirtFcIf(6),
        hostNonvirtFcIf(7),
        hostVirtFcIfPersBind(8),
        hostNonvirtFcIfPersBind(9),
        hostFcIfProfile(10),
        hostFcIfQos(11),
        hostFcoeIf(12),
        vif(13),
        vlan(14),
        vsan(15),
        ip(16),
        bootOrder(17),
        bootVirtVnic(18),
        bootNonvirtVnic(19),
        bootLocalStorage(20),
        bootVirtPxe(21),
        bootNonvirtPxe(22),
        bladeIdentity(24),
        agentPolicy(25),
        biosFw(26),
        storageControllerFw(27),
        adaptorHostFw(28),
        adaptorNwFw(29),
        mgmtControllerFw(30),
        localDiskPolicy(31),
        pin(32),
        sol(33),
        epAuth(34),
        biosProfile(35),
        checkpoint(36),
        implicitReboot(37),
        implicitHostFcIfProfileRedeploy(38),
        boardControllerFw(39),
        hostEthIfQosHostControl(40),
        localDiskFw(41),
        implicitHostEthIfProfileRedeploy(42),
        storagePath(43),
        bmcUpdateBiosFw(44),
        hostIfPcie(45),
        flexflashConfig(46),
        bootmodeConfig(48),
        securebootConfig(49),
        vmediaConfig(50),
        ssposUpdateFw(51)
    }

CfprTrigAckChanges ::= TEXTUAL-CONVENTION
    STATUS        current
    DESCRIPTION
        ""
    SYNTAX        BITS
    {
        serverIdentity(0),
        storage(1),
        networking(2),
        vnicVhbaPlacement(3),
        bootOrder(4),
        serverAssignment(5),
        operationalPolicies(6)
    }

CfprTrigAckDisr ::= TEXTUAL-CONVENTION
    STATUS        current
    DESCRIPTION
        ""
    SYNTAX        BITS
    {
        upTime(0),
        acPowerCycle(1)
    }

CfprTrigAckMode ::= TEXTUAL-CONVENTION
    STATUS        current
    DESCRIPTION
        ""
    SYNTAX        INTEGER
    {
        immediate(0),
        userAck(1),
        timerAutomatic(2)
    }

CfprTrigAdminState ::= TEXTUAL-CONVENTION
    STATUS        current
    DESCRIPTION
        ""
    SYNTAX        INTEGER
    {
        triggerImmediate(0),
        trigger(1),
        triggered(2),
        untriggered(3),
        userAck(4),
        userDiscard(5)
    }

CfprTrigDay ::= TEXTUAL-CONVENTION
    STATUS        current
    DESCRIPTION
        ""
    SYNTAX        INTEGER
    {
        everyDay(0),
        monday(1),
        tuesday(2),
        wednesday(3),
        thursday(4),
        friday(5),
        saturday(6),
        sunday(7),
        oddDay(8),
        evenDay(9)
    }

CfprTrigOperState ::= TEXTUAL-CONVENTION
    STATUS        current
    DESCRIPTION
        ""
    SYNTAX        INTEGER
    {
        pending(0),
        inProgress(1),
        failed(2),
        triggered(3),
        capReached(4)
    }

CfprTrigTokenOperState ::= TEXTUAL-CONVENTION
    STATUS        current
    DESCRIPTION
        ""
    SYNTAX        INTEGER
    {
        valid(0),
        expired(1)
    }

CfprTrigTrigOperState ::= TEXTUAL-CONVENTION
    STATUS        current
    DESCRIPTION
        ""
    SYNTAX        INTEGER
    {
        untriggered(0),
        evaluationPending(1),
        evaluated(2),
        waitingForUser(3),
        waitingForMaintWindow(4),
        applyPending(5),
        applied(6),
        waitingForDependency(7),
        none(8),
        expired(9),
        pending(10),
        active(11)
    }

CfprTrigTriggeredState ::= TEXTUAL-CONVENTION
    STATUS        current
    DESCRIPTION
        ""
    SYNTAX        INTEGER
    {
        pending(0),
        inProgress(1),
        failed(2),
        triggered(3)
    }

CfprUuidpoolPoolAssignmentOrder ::= TEXTUAL-CONVENTION
    STATUS        current
    DESCRIPTION
        ""
    SYNTAX        INTEGER
    {
        default(0),
        sequential(1)
    }

CfprVmAdaptorOwner ::= TEXTUAL-CONVENTION
    STATUS        current
    DESCRIPTION
        ""
    SYNTAX        INTEGER
    {
        unknown(0),
        physical(1),
        policy(2),
        logical(4),
        connPolicy(8)
    }

CfprVmComputeEpClInstType ::= TEXTUAL-CONVENTION
    STATUS        current
    DESCRIPTION
        ""
    SYNTAX        INTEGER
    {
        vm(0),
        hv(1),
        computeEp(2)
    }

CfprVmHbaType ::= TEXTUAL-CONVENTION
    STATUS        current
    DESCRIPTION
        ""
    SYNTAX        INTEGER
    {
        unknown(0),
        ether(1),
        fc(4),
        scsi(8),
        ipc(16)
    }

CfprVmHvClInstType ::= TEXTUAL-CONVENTION
    STATUS        current
    DESCRIPTION
        ""
    SYNTAX        INTEGER
    {
        vm(0),
        hv(1),
        computeEp(2)
    }

CfprVmHvType ::= TEXTUAL-CONVENTION
    STATUS        current
    DESCRIPTION
        ""
    SYNTAX        INTEGER
    {
        unspecified(0),
        esx(1),
        kvm(2),
        hyperv(3),
        xen(4)
    }

CfprVmInstType ::= TEXTUAL-CONVENTION
    STATUS        current
    DESCRIPTION
        ""
    SYNTAX        INTEGER
    {
        vm(0),
        hv(1),
        computeEp(2)
    }

CfprVmLifeCyclePolicyFsmCurrentFsm ::= TEXTUAL-CONVENTION
    STATUS        current
    DESCRIPTION
        ""
    SYNTAX        INTEGER
    {
        nop(0),
        config(1132)
    }

CfprVmLifeCyclePolicyFsmStageName ::= TEXTUAL-CONVENTION
    STATUS        current
    DESCRIPTION
        ""
    SYNTAX        INTEGER
    {
        nop(0),
        configBegin(1132),
        configLocal(1133),
        configPeer(1134),
        configFail(1146),
        configSuccess(1147)
    }

CfprVmLifeCyclePolicyFsmTaskItem ::= TEXTUAL-CONVENTION
    STATUS        current
    DESCRIPTION
        ""
    SYNTAX        INTEGER
    {
        nop(0),
        config(1132)
    }

CfprVmMgmtPlane ::= TEXTUAL-CONVENTION
    STATUS        current
    DESCRIPTION
        ""
    SYNTAX        INTEGER
    {
        unmanaged(0),
        vcenter(1),
        rhevM(2),
        scvmm(3)
    }

CfprVmNicType ::= TEXTUAL-CONVENTION
    STATUS        current
    DESCRIPTION
        ""
    SYNTAX        INTEGER
    {
        unknown(0),
        ether(1),
        fc(4),
        scsi(8),
        ipc(16)
    }

CfprVmOsHvVendor ::= TEXTUAL-CONVENTION
    STATUS        current
    DESCRIPTION
        ""
    SYNTAX        INTEGER
    {
        unspecified(0),
        vmware(1),
        redhat(2),
        microsoft(3),
        novell(4),
        oracle(5),
        citrix(6)
    }

CfprVmStatus ::= TEXTUAL-CONVENTION
    STATUS        current
    DESCRIPTION
        ""
    SYNTAX        INTEGER
    {
        unknown(0),
        online(1),
        offline(2)
    }

CfprVmSwitchAdminState ::= TEXTUAL-CONVENTION
    STATUS        current
    DESCRIPTION
        ""
    SYNTAX        INTEGER
    {
        disable(0),
        enable(1)
    }

CfprVmSwitchVendor ::= TEXTUAL-CONVENTION
    STATUS        current
    DESCRIPTION
        ""
    SYNTAX        INTEGER
    {
        undetermined(0),
        vmware(1),
        microsoft(2)
    }

CfprVnicAEtherIfType ::= TEXTUAL-CONVENTION
    STATUS        current
    DESCRIPTION
        ""
    SYNTAX        INTEGER
    {
        unknown(0),
        ether(1),
        fc(4),
        scsi(8),
        ipc(16)
    }

CfprVnicAFcIfType ::= TEXTUAL-CONVENTION
    STATUS        current
    DESCRIPTION
        ""
    SYNTAX        INTEGER
    {
        unknown(0),
        ether(1),
        fc(4),
        scsi(8),
        ipc(16)
    }

CfprVnicAIpcIfType ::= TEXTUAL-CONVENTION
    STATUS        current
    DESCRIPTION
        ""
    SYNTAX        INTEGER
    {
        unknown(0),
        ether(1),
        fc(4),
        scsi(8),
        ipc(16)
    }

CfprVnicAScsiIfType ::= TEXTUAL-CONVENTION
    STATUS        current
    DESCRIPTION
        ""
    SYNTAX        INTEGER
    {
        unknown(0),
        ether(1),
        fc(4),
        scsi(8),
        ipc(16)
    }

CfprVnicAppRole ::= TEXTUAL-CONVENTION
    STATUS        current
    DESCRIPTION
        ""
    SYNTAX        INTEGER
    {
        none(0),
        mainCp(1),
        appCp(2),
        appIntMgmt(3),
        appExtMgmt(4),
        asaDp(5),
        appDp(6),
        offloadDp(7),
        redirectDp(8),
        appExtData(9),
        appInstMgmt(10),
        turboAsaDp(11)
    }

CfprVnicConfigIssues ::= TEXTUAL-CONVENTION
    STATUS        current
    DESCRIPTION
        ""
    SYNTAX        BITS
    {
        pinningVlanMismatch(0),
        vnicVlanAssignmentError(1),
        missingPrimaryVlan(2),
        pinnedTargetMisconfig(3),
        unresolvedVlanName(4),
        inaccessibleVlan(5),
        unresolvedVsanName(6),
        unresolvedRemoteVlanName(7),
        unresolvedRemoteVsanName(8),
        adaptorFcoeCapability(9),
        adaptorProtectedEthCapability(10),
        adaptorRequirement(11),
        connectionPlacement(12),
        dynamicVfVnic(13),
        fcoeCapacity(14),
        insufficientVhbaCapacity(15),
        insufficientVnicCapacity(16),
        invalidWwn(17),
        macDerivationVirtualizedPort(18),
        vfcVnicPvlanConflict(19),
        vifResourcesOverprovisioned(20),
        vnicNotHaReady(21),
        vnicVconProvisioningChange(22),
        wwpnAssignment(23),
        wwpnDerivationVirtualizedPort(24),
        unableToUpdateFprm(25),
        unassociatedVlan(26),
        serviceProfileVirtualizationConflict(27),
        vnicVirtualizationConflict(28),
        virtualizationNotSupported(29),
        ungroupedDomain(30),
        missingIpv4InbandMgmtAddr(31),
        missingIpv6InbandMgmtAddr(32),
        missingIpv4Addr(33),
        vnicVirtualizationNetflowConflict(34),
        softPinningVlanMismatch(35),
        unsupportedRoceVmq(36),
        unsupportedRoceNetflow(37),
        unsupportedRoce(38),
        unsupportedVxlan(39),
        unsupportedNvgre(40),
        unsupportedNvgreDynamicVnic(41),
        unsupportedNvgreUsnic(42),
        unsupportedVxlanDynamicVnic(43),
        unsupportedVxlanUsnic(44),
        unsupportedNvgreVmq(45),
        unsupportedVxlanVmq(46),
        unsupportedVxlanNetflow(47),
        unsupportedNvgreNetflow(48)
    }

CfprVnicConnectionOwner ::= TEXTUAL-CONVENTION
    STATUS        current
    DESCRIPTION
        ""
    SYNTAX        INTEGER
    {
        unknown(0),
        physical(1),
        policy(2),
        logical(4),
        connPolicy(8)
    }

CfprVnicConnectionType ::= TEXTUAL-CONVENTION
    STATUS        current
    DESCRIPTION
        ""
    SYNTAX        INTEGER
    {
        unknown(0),
        ether(1),
        fc(4),
        scsi(8),
        ipc(16)
    }

CfprVnicDefBehType ::= TEXTUAL-CONVENTION
    STATUS        current
    DESCRIPTION
        ""
    SYNTAX        INTEGER
    {
        vnic(1),
        vhba(2)
    }

CfprVnicDefaultAction ::= TEXTUAL-CONVENTION
    STATUS        current
    DESCRIPTION
        ""
    SYNTAX        INTEGER
    {
        none(0),
        hwInherit(1)
    }

CfprVnicDynamicConReqProtection ::= TEXTUAL-CONVENTION
    STATUS        current
    DESCRIPTION
        ""
    SYNTAX        INTEGER
    {
        none(0),
        protectedPrefA(1),
        protectedPrefB(2),
        protected(3)
    }

CfprVnicEtherType ::= TEXTUAL-CONVENTION
    STATUS        current
    DESCRIPTION
        ""
    SYNTAX        INTEGER
    {
        unknown(0),
        ether(1),
        fc(4),
        scsi(8),
        ipc(16)
    }

CfprVnicEtherBaseSwitchId ::= TEXTUAL-CONVENTION
    STATUS        current
    DESCRIPTION
        ""
    SYNTAX        INTEGER
    {
        none(0),
        a(1),
        b(2),
        aB(5),
        bA(6)
    }

CfprVnicExternalMgmtIPMode ::= TEXTUAL-CONVENTION
    STATUS        current
    DESCRIPTION
        ""
    SYNTAX        INTEGER
    {
        none(1),
        static(2),
        pooled(3)
    }

CfprVnicFcBasePersBind ::= TEXTUAL-CONVENTION
    STATUS        current
    DESCRIPTION
        ""
    SYNTAX        INTEGER
    {
        disabled(0),
        enabled(4)
    }

CfprVnicFcBaseType ::= TEXTUAL-CONVENTION
    STATUS        current
    DESCRIPTION
        ""
    SYNTAX        INTEGER
    {
        unknown(0),
        ether(1),
        fc(4),
        scsi(8),
        ipc(16)
    }

CfprVnicFcNodeOwner ::= TEXTUAL-CONVENTION
    STATUS        current
    DESCRIPTION
        ""
    SYNTAX        INTEGER
    {
        unknown(0),
        physical(1),
        policy(2),
        logical(4),
        connPolicy(8)
    }

CfprVnicHostNwIOPerfPref ::= TEXTUAL-CONVENTION
    STATUS        current
    DESCRIPTION
        ""
    SYNTAX        INTEGER
    {
        none(0),
        highPerfReqd(1)
    }

CfprVnicIPv4DnsPref ::= TEXTUAL-CONVENTION
    STATUS        current
    DESCRIPTION
        ""
    SYNTAX        INTEGER
    {
        preferred(0),
        alternate(1)
    }

CfprVnicIScsiConfigIssues ::= TEXTUAL-CONVENTION
    STATUS        current
    DESCRIPTION
        ""
    SYNTAX        BITS
    {
        initiatorName(0),
        iqnPoolName(1),
        targetName(2),
        authProfileSame(3),
        invalidTargetName(4),
        noLuns(5),
        iscsiCardinality(6),
        autoTargetAuth(7),
        autoTargetInit(8),
        noVlanIp(9),
        staticTargetMix(10),
        ipAddrDhcp(11),
        unclassified(12),
        internalCfgError(13),
        missingVlan(14),
        vnicName(15),
        allowedVlan(16),
        iscsiConfig(17),
        iscsiInitiatorIpAddress(18),
        invalidMac(19),
        nativeVlan(20),
        initTargetPasswd(21),
        initIdentity(22)
    }

CfprVnicIScsiIfDefType ::= TEXTUAL-CONVENTION
    STATUS        current
    DESCRIPTION
        ""
    SYNTAX        INTEGER
    {
        static(0),
        dynamicNw(1),
        option17(2),
        option43(4)
    }

CfprVnicIScsiNodeOwner ::= TEXTUAL-CONVENTION
    STATUS        current
    DESCRIPTION
        ""
    SYNTAX        INTEGER
    {
        unknown(0),
        physical(1),
        policy(2),
        logical(4),
        connPolicy(8)
    }

CfprVnicIfOperState ::= TEXTUAL-CONVENTION
    STATUS        current
    DESCRIPTION
        ""
    SYNTAX        INTEGER
    {
        indeterminate(0),
        up(1),
        down(2),
        failed(4)
    }

CfprVnicInstantiation ::= TEXTUAL-CONVENTION
    STATUS        current
    DESCRIPTION
        ""
    SYNTAX        INTEGER
    {
        manual(0),
        default(1),
        dynamic(2),
        dynamicVf(3)
    }

CfprVnicIpcType ::= TEXTUAL-CONVENTION
    STATUS        current
    DESCRIPTION
        ""
    SYNTAX        INTEGER
    {
        unknown(0),
        ether(1),
        fc(4),
        scsi(8),
        ipc(16)
    }

CfprVnicL2IfSwitchId ::= TEXTUAL-CONVENTION
    STATUS        current
    DESCRIPTION
        ""
    SYNTAX        INTEGER
    {
        none(0),
        a(1),
        b(2),
        aB(5),
        bA(6)
    }

CfprVnicLanConnTemplSwitchId ::= TEXTUAL-CONVENTION
    STATUS        current
    DESCRIPTION
        ""
    SYNTAX        INTEGER
    {
        none(0),
        a(1),
        b(2),
        aB(5),
        bA(6)
    }

CfprVnicLunId ::= TEXTUAL-CONVENTION
    STATUS        current
    DESCRIPTION
        ""
    SYNTAX        Gauge32 (0..65535)

CfprVnicMezzMappingScheme ::= TEXTUAL-CONVENTION
    STATUS        current
    DESCRIPTION
        ""
    SYNTAX        INTEGER
    {
        physicalCapFirst(1),
        capLoadDistribute(2)
    }

CfprVnicOrderScheme ::= TEXTUAL-CONVENTION
    STATUS        current
    DESCRIPTION
        ""
    SYNTAX        INTEGER
    {
        zeroFuncAll(0),
        multiFuncAll(1),
        staticZeroFunc(2)
    }

CfprVnicPlacement ::= TEXTUAL-CONVENTION
    STATUS        current
    DESCRIPTION
        ""
    SYNTAX        INTEGER
    {
        allVnic(0),
        staticAllFirst(1),
        dynamicAllLast(2)
    }

CfprVnicProfileConfigQualifier ::= TEXTUAL-CONVENTION
    STATUS        current
    DESCRIPTION
        ""
    SYNTAX        INTEGER
    {
        normal(0),
        invalidName(1)
    }

CfprVnicProfileSetFsmCurrentFsm ::= TEXTUAL-CONVENTION
    STATUS        current
    DESCRIPTION
        ""
    SYNTAX        INTEGER
    {
        nop(0),
        deploy(187),
        deployAlias(1118)
    }

CfprVnicProfileSetFsmStageName ::= TEXTUAL-CONVENTION
    STATUS        current
    DESCRIPTION
        ""
    SYNTAX        INTEGER
    {
        nop(0),
        deployBegin(187),
        deployLocal(188),
        deployPeer(189),
        deployFail(456),
        deploySuccess(457),
        deployAliasBegin(1118),
        deployAliasLocal(1119),
        deployAliasPeer(1120),
        deployAliasFail(1148),
        deployAliasSuccess(1149)
    }

CfprVnicProfileSetFsmTaskItem ::= TEXTUAL-CONVENTION
    STATUS        current
    DESCRIPTION
        ""
    SYNTAX        INTEGER
    {
        nop(0),
        deploy(187),
        deployAlias(1118)
    }

CfprVnicSanConnTemplTarget ::= TEXTUAL-CONVENTION
    STATUS        current
    DESCRIPTION
        ""
    SYNTAX        BITS
    {
        vm(0),
        adaptor(1)
    }

CfprVnicScsiType ::= TEXTUAL-CONVENTION
    STATUS        current
    DESCRIPTION
        ""
    SYNTAX        INTEGER
    {
        unknown(0),
        ether(1),
        fc(4),
        scsi(8),
        ipc(16)
    }

CfprVnicTemplateTarget ::= TEXTUAL-CONVENTION
    STATUS        current
    DESCRIPTION
        ""
    SYNTAX        BITS
    {
        vm(0),
        adaptor(1)
    }

CfprVnicTemplateType ::= TEXTUAL-CONVENTION
    STATUS        current
    DESCRIPTION
        ""
    SYNTAX        INTEGER
    {
        initialTemplate(1),
        updatingTemplate(2)
    }

CfprVnicVhbaBehPolicyType ::= TEXTUAL-CONVENTION
    STATUS        current
    DESCRIPTION
        ""
    SYNTAX        INTEGER
    {
        vnic(1),
        vhba(2)
    }

CfprVnicVirtualizationPreferenceType ::= TEXTUAL-CONVENTION
    STATUS        current
    DESCRIPTION
        ""
    SYNTAX        INTEGER
    {
        none(0),
        sriov(2),
        sriovVmfex(3),
        sriovUsnic(4),
        vmq(5)
    }

CfprVnicVnicBootDev ::= TEXTUAL-CONVENTION
    STATUS        current
    DESCRIPTION
        ""
    SYNTAX        INTEGER
    {
        disabled(0),
        enabled(1)
    }

CfprVnicVnicOperHostPort ::= TEXTUAL-CONVENTION
    STATUS        current
    DESCRIPTION
        ""
    SYNTAX        INTEGER
    {
        any(0),
        n1(1),
        n2(2),
        none(10)
    }

CfprVnicVnicBehPolicyType ::= TEXTUAL-CONVENTION
    STATUS        current
    DESCRIPTION
        ""
    SYNTAX        INTEGER
    {
        vnic(1),
        vhba(2)
    }

CfprVnicPortProfileType ::= TEXTUAL-CONVENTION
    STATUS        current
    DESCRIPTION
        ""
    SYNTAX        INTEGER
    {
        regular(0),
        slaOnly(1)
    }

END
