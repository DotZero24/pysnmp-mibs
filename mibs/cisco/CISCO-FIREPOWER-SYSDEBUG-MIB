-- *********************************************************************
-- CISCO-FIREPOWER-SYSDEBUG-MIB.my
--
-- MIB representation of the Cisco Firepower
-- SYSDEBUG management information model package
--
-- Created March 2020 by Charles Bullis
--
-- Copyright (c) 2005-2020 Cisco Systems, Inc. All rights reserved.
--
-- *********************************************************************

CISCO-FIREPOWER-SYSDEBUG-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIBObjects,
    CfprManagedObjectId,
    CfprManagedObjectDn
        FROM CISCO-FIREPOWER-MIB
    CfprCommClientAdminState,
    CfprConditionRemoteInvRslt,
    CfprFsmCompletion,
    CfprFsmFlags,
    CfprFsmFsmStageStatus,
    CfprNetworkSwitchId,
    CfprPolicyPolicyOwner,
    CfprSysdebugAutoCoreFileExportTargetFsmCurrentFsm,
    CfprSysdebugAutoCoreFileExportTargetFsmStageName,
    CfprSysdebugAutoCoreFileExportTargetFsmTaskItem,
    CfprSysdebugAutoCoreFileExportTargetProto,
    CfprSysdebugBackupBehaviorInterval,
    CfprSysdebugBackupBehaviorProto,
    CfprSysdebugBackupFormat,
    CfprSysdebugCoreExportStatus,
    CfprSysdebugCoreFileAdminState,
    CfprSysdebugCoreFileOperState,
    CfprSysdebugCoreFsmCurrentFsm,
    CfprSysdebugCoreFsmStageName,
    CfprSysdebugCoreFsmTaskItem,
    CfprSysdebugEpLogAdminState,
    CfprSysdebugEpLogBackupAction,
    CfprSysdebugEpLogCapacity,
    CfprSysdebugEpLogType,
    CfprSysdebugExportStatus,
    CfprSysdebugLogControlDomainEnum,
    CfprSysdebugLogControlEpFsmCurrentFsm,
    CfprSysdebugLogControlEpFsmStageName,
    CfprSysdebugLogControlEpFsmTaskItem,
    CfprSysdebugLogControlLevel,
    CfprSysdebugLogExportPolicyFsmCurrentFsm,
    CfprSysdebugLogExportPolicyFsmStageName,
    CfprSysdebugLogExportPolicyFsmTaskItem,
    CfprSysdebugLogExportPolicyProto,
    CfprSysdebugMEpLogOperState,
    CfprSysdebugManualCoreFileExportTargetAdminState,
    CfprSysdebugManualCoreFileExportTargetFsmCurrentFsm,
    CfprSysdebugManualCoreFileExportTargetFsmStageName,
    CfprSysdebugManualCoreFileExportTargetFsmTaskItem,
    CfprSysdebugManualCoreFileExportTargetProto,
    CfprSysdebugTSCmdOptMajorType,
    CfprSysdebugTechSupportAdminState,
    CfprSysdebugTechSupportFsmCurrentFsm,
    CfprSysdebugTechSupportFsmStageName,
    CfprSysdebugTechSupportFsmTaskItem,
    CfprSysdebugTechSupportOperState,
    CfprSysfileExporterPostAction
        FROM CISCO-FIREPOWER-TC-MIB;

cfprSysdebugObjects MODULE-IDENTITY
    LAST-UPDATED    "202003100000Z"
    ORGANIZATION    "Cisco Systems Inc."
    CONTACT-INFO
        "Cisco Systems
        Customer Service

        Postal: 170 W Tasman Drive
        San Jose, CA  95134
        USA

        Tel: +1 800 553-NETS

        E-mail: firepower-mibs@cisco.com"
    DESCRIPTION
        "MIB representation of the Cisco Firepower
        SYSDEBUG management information model package"
    ::= { ciscoFirepowerMIBObjects 76 }

cfprSysdebugAdaptorCoreStatsTable OBJECT-TYPE
    SYNTAX           SEQUENCE OF CfprSysdebugAdaptorCoreStatsEntry
    MAX-ACCESS       not-accessible
    STATUS           current
    DESCRIPTION
        "Cisco Firepower sysdebug:AdaptorCoreStats managed object table"
    ::= { cfprSysdebugObjects 37 }

cfprSysdebugAdaptorCoreStatsEntry OBJECT-TYPE
    SYNTAX           CfprSysdebugAdaptorCoreStatsEntry
    MAX-ACCESS       not-accessible
    STATUS           current
    DESCRIPTION
        "Entry for the cfprSysdebugAdaptorCoreStatsTable table."
    INDEX { cfprSysdebugAdaptorCoreStatsInstanceId }
    ::= { cfprSysdebugAdaptorCoreStatsTable 1 }

CfprSysdebugAdaptorCoreStatsEntry ::= SEQUENCE {
    cfprSysdebugAdaptorCoreStatsInstanceId                           CfprManagedObjectId,
    cfprSysdebugAdaptorCoreStatsDn                                   CfprManagedObjectDn,
    cfprSysdebugAdaptorCoreStatsRn                                   SnmpAdminString,
    cfprSysdebugAdaptorCoreStatsAdaptorId                            Gauge32,
    cfprSysdebugAdaptorCoreStatsExcessiveCore                        TruthValue,
    cfprSysdebugAdaptorCoreStatsNumCore                              Gauge32,
    cfprSysdebugAdaptorCoreStatsSlotId                               Gauge32
}

cfprSysdebugAdaptorCoreStatsInstanceId OBJECT-TYPE
    SYNTAX       CfprManagedObjectId
    MAX-ACCESS   not-accessible
    STATUS       current
    DESCRIPTION
        "Instance identifier of the managed object."
    ::= { cfprSysdebugAdaptorCoreStatsEntry 1 }

cfprSysdebugAdaptorCoreStatsDn OBJECT-TYPE
    SYNTAX       CfprManagedObjectDn
    MAX-ACCESS   read-only
    STATUS       current
    DESCRIPTION
        "Cisco Firepower sysdebug:AdaptorCoreStats:dn managed
        object property"
    ::= { cfprSysdebugAdaptorCoreStatsEntry 2 }

cfprSysdebugAdaptorCoreStatsRn OBJECT-TYPE
    SYNTAX       SnmpAdminString
    MAX-ACCESS   read-only
    STATUS       current
    DESCRIPTION
        "Cisco Firepower sysdebug:AdaptorCoreStats:rn managed
        object property"
    ::= { cfprSysdebugAdaptorCoreStatsEntry 3 }

cfprSysdebugAdaptorCoreStatsAdaptorId OBJECT-TYPE
    SYNTAX       Gauge32
    MAX-ACCESS   read-only
    STATUS       current
    DESCRIPTION
        "Cisco Firepower sysdebug:AdaptorCoreStats:adaptorId
        managed object property"
    ::= { cfprSysdebugAdaptorCoreStatsEntry 4 }

cfprSysdebugAdaptorCoreStatsExcessiveCore OBJECT-TYPE
    SYNTAX       TruthValue
    MAX-ACCESS   read-only
    STATUS       current
    DESCRIPTION
        "Cisco Firepower sysdebug:AdaptorCoreStats:excessiveCore
        managed object property"
    ::= { cfprSysdebugAdaptorCoreStatsEntry 5 }

cfprSysdebugAdaptorCoreStatsNumCore OBJECT-TYPE
    SYNTAX       Gauge32
    MAX-ACCESS   read-only
    STATUS       current
    DESCRIPTION
        "Cisco Firepower sysdebug:AdaptorCoreStats:numCore
        managed object property"
    ::= { cfprSysdebugAdaptorCoreStatsEntry 6 }

cfprSysdebugAdaptorCoreStatsSlotId OBJECT-TYPE
    SYNTAX       Gauge32
    MAX-ACCESS   read-only
    STATUS       current
    DESCRIPTION
        "Cisco Firepower sysdebug:AdaptorCoreStats:slotId
        managed object property"
    ::= { cfprSysdebugAdaptorCoreStatsEntry 7 }

cfprSysdebugAutoCoreFileExportTargetTable OBJECT-TYPE
    SYNTAX           SEQUENCE OF CfprSysdebugAutoCoreFileExportTargetEntry
    MAX-ACCESS       not-accessible
    STATUS           current
    DESCRIPTION
        "Cisco Firepower sysdebug:AutoCoreFileExportTarget
        managed object table"
    ::= { cfprSysdebugObjects 1 }

cfprSysdebugAutoCoreFileExportTargetEntry OBJECT-TYPE
    SYNTAX           CfprSysdebugAutoCoreFileExportTargetEntry
    MAX-ACCESS       not-accessible
    STATUS           current
    DESCRIPTION
        "Entry for the cfprSysdebugAutoCoreFileExportTargetTable table."
    INDEX { cfprSysdebugAutoCoreFileExportTargetInstanceId }
    ::= { cfprSysdebugAutoCoreFileExportTargetTable 1 }

CfprSysdebugAutoCoreFileExportTargetEntry ::= SEQUENCE {
    cfprSysdebugAutoCoreFileExportTargetInstanceId                   CfprManagedObjectId,
    cfprSysdebugAutoCoreFileExportTargetDn                           CfprManagedObjectDn,
    cfprSysdebugAutoCoreFileExportTargetRn                           SnmpAdminString,
    cfprSysdebugAutoCoreFileExportTargetAdminState                   CfprCommClientAdminState,
    cfprSysdebugAutoCoreFileExportTargetDescr                        SnmpAdminString,
    cfprSysdebugAutoCoreFileExportTargetExportFailureReason          SnmpAdminString,
    cfprSysdebugAutoCoreFileExportTargetExportStatus                 CfprSysdebugCoreExportStatus,
    cfprSysdebugAutoCoreFileExportTargetFsmDescr                     SnmpAdminString,
    cfprSysdebugAutoCoreFileExportTargetFsmPrev                      SnmpAdminString,
    cfprSysdebugAutoCoreFileExportTargetFsmProgr                     Gauge32,
    cfprSysdebugAutoCoreFileExportTargetFsmRmtInvErrCode             Gauge32,
    cfprSysdebugAutoCoreFileExportTargetFsmRmtInvErrDescr            SnmpAdminString,
    cfprSysdebugAutoCoreFileExportTargetFsmRmtInvRslt                CfprConditionRemoteInvRslt,
    cfprSysdebugAutoCoreFileExportTargetFsmStageDescr                SnmpAdminString,
    cfprSysdebugAutoCoreFileExportTargetFsmStamp                     DateAndTime,
    cfprSysdebugAutoCoreFileExportTargetFsmStatus                    SnmpAdminString,
    cfprSysdebugAutoCoreFileExportTargetFsmTry                       Gauge32,
    cfprSysdebugAutoCoreFileExportTargetHostname                     SnmpAdminString,
    cfprSysdebugAutoCoreFileExportTargetIntId                        SnmpAdminString,
    cfprSysdebugAutoCoreFileExportTargetName                         SnmpAdminString,
    cfprSysdebugAutoCoreFileExportTargetPath                         SnmpAdminString,
    cfprSysdebugAutoCoreFileExportTargetPolicyLevel                  Gauge32,
    cfprSysdebugAutoCoreFileExportTargetPolicyOwner                  CfprPolicyPolicyOwner,
    cfprSysdebugAutoCoreFileExportTargetPort                         Gauge32,
    cfprSysdebugAutoCoreFileExportTargetPostAction                   CfprSysfileExporterPostAction,
    cfprSysdebugAutoCoreFileExportTargetProto                        CfprSysdebugAutoCoreFileExportTargetProto
}

cfprSysdebugAutoCoreFileExportTargetInstanceId OBJECT-TYPE
    SYNTAX       CfprManagedObjectId
    MAX-ACCESS   not-accessible
    STATUS       current
    DESCRIPTION
        "Instance identifier of the managed object."
    ::= { cfprSysdebugAutoCoreFileExportTargetEntry 1 }

cfprSysdebugAutoCoreFileExportTargetDn OBJECT-TYPE
    SYNTAX       CfprManagedObjectDn
    MAX-ACCESS   read-only
    STATUS       current
    DESCRIPTION
        "Cisco Firepower sysdebug:AutoCoreFileExportTarget:dn
        managed object property"
    ::= { cfprSysdebugAutoCoreFileExportTargetEntry 2 }

cfprSysdebugAutoCoreFileExportTargetRn OBJECT-TYPE
    SYNTAX       SnmpAdminString
    MAX-ACCESS   read-only
    STATUS       current
    DESCRIPTION
        "Cisco Firepower sysdebug:AutoCoreFileExportTarget:rn
        managed object property"
    ::= { cfprSysdebugAutoCoreFileExportTargetEntry 3 }

cfprSysdebugAutoCoreFileExportTargetAdminState OBJECT-TYPE
    SYNTAX       CfprCommClientAdminState
    MAX-ACCESS   read-only
    STATUS       current
    DESCRIPTION
        "Cisco Firepower sysdebug:AutoCoreFileExportTarget:adminState
        managed object property"
    ::= { cfprSysdebugAutoCoreFileExportTargetEntry 4 }

cfprSysdebugAutoCoreFileExportTargetDescr OBJECT-TYPE
    SYNTAX       SnmpAdminString
    MAX-ACCESS   read-only
    STATUS       current
    DESCRIPTION
        "Cisco Firepower sysdebug:AutoCoreFileExportTarget:descr
        managed object property"
    ::= { cfprSysdebugAutoCoreFileExportTargetEntry 5 }

cfprSysdebugAutoCoreFileExportTargetExportFailureReason OBJECT-TYPE
    SYNTAX       SnmpAdminString
    MAX-ACCESS   read-only
    STATUS       current
    DESCRIPTION
        "Cisco Firepower sysdebug:AutoCoreFileExportTarget:exportFailureRe
        ason managed object property"
    ::= { cfprSysdebugAutoCoreFileExportTargetEntry 6 }

cfprSysdebugAutoCoreFileExportTargetExportStatus OBJECT-TYPE
    SYNTAX       CfprSysdebugCoreExportStatus
    MAX-ACCESS   read-only
    STATUS       current
    DESCRIPTION
        "Cisco Firepower sysdebug:AutoCoreFileExportTarget:exportStatus
        managed object property"
    ::= { cfprSysdebugAutoCoreFileExportTargetEntry 7 }

cfprSysdebugAutoCoreFileExportTargetFsmDescr OBJECT-TYPE
    SYNTAX       SnmpAdminString
    MAX-ACCESS   read-only
    STATUS       current
    DESCRIPTION
        "Cisco Firepower sysdebug:AutoCoreFileExportTarget:fsmDescr
        managed object property"
    ::= { cfprSysdebugAutoCoreFileExportTargetEntry 8 }

cfprSysdebugAutoCoreFileExportTargetFsmPrev OBJECT-TYPE
    SYNTAX       SnmpAdminString
    MAX-ACCESS   read-only
    STATUS       current
    DESCRIPTION
        "Cisco Firepower sysdebug:AutoCoreFileExportTarget:fsmPrev
        managed object property"
    ::= { cfprSysdebugAutoCoreFileExportTargetEntry 9 }

cfprSysdebugAutoCoreFileExportTargetFsmProgr OBJECT-TYPE
    SYNTAX       Gauge32
    MAX-ACCESS   read-only
    STATUS       current
    DESCRIPTION
        "Cisco Firepower sysdebug:AutoCoreFileExportTarget:fsmProgr
        managed object property"
    ::= { cfprSysdebugAutoCoreFileExportTargetEntry 10 }

cfprSysdebugAutoCoreFileExportTargetFsmRmtInvErrCode OBJECT-TYPE
    SYNTAX       Gauge32
    MAX-ACCESS   read-only
    STATUS       current
    DESCRIPTION
        "Cisco Firepower sysdebug:AutoCoreFileExportTarget:fsmRmtInvErrCod
        e managed object property"
    ::= { cfprSysdebugAutoCoreFileExportTargetEntry 11 }

cfprSysdebugAutoCoreFileExportTargetFsmRmtInvErrDescr OBJECT-TYPE
    SYNTAX       SnmpAdminString
    MAX-ACCESS   read-only
    STATUS       current
    DESCRIPTION
        "Cisco Firepower sysdebug:AutoCoreFileExportTarget:fsmRmtInvErrDes
        cr managed object property"
    ::= { cfprSysdebugAutoCoreFileExportTargetEntry 12 }

cfprSysdebugAutoCoreFileExportTargetFsmRmtInvRslt OBJECT-TYPE
    SYNTAX       CfprConditionRemoteInvRslt
    MAX-ACCESS   read-only
    STATUS       current
    DESCRIPTION
        "Cisco Firepower sysdebug:AutoCoreFileExportTarget:fsmRmtInvRslt
        managed object property"
    ::= { cfprSysdebugAutoCoreFileExportTargetEntry 13 }

cfprSysdebugAutoCoreFileExportTargetFsmStageDescr OBJECT-TYPE
    SYNTAX       SnmpAdminString
    MAX-ACCESS   read-only
    STATUS       current
    DESCRIPTION
        "Cisco Firepower sysdebug:AutoCoreFileExportTarget:fsmStageDescr
        managed object property"
    ::= { cfprSysdebugAutoCoreFileExportTargetEntry 14 }

cfprSysdebugAutoCoreFileExportTargetFsmStamp OBJECT-TYPE
    SYNTAX       DateAndTime
    MAX-ACCESS   read-only
    STATUS       current
    DESCRIPTION
        "Cisco Firepower sysdebug:AutoCoreFileExportTarget:fsmStamp
        managed object property"
    ::= { cfprSysdebugAutoCoreFileExportTargetEntry 15 }

cfprSysdebugAutoCoreFileExportTargetFsmStatus OBJECT-TYPE
    SYNTAX       SnmpAdminString
    MAX-ACCESS   read-only
    STATUS       current
    DESCRIPTION
        "Cisco Firepower sysdebug:AutoCoreFileExportTarget:fsmStatus
        managed object property"
    ::= { cfprSysdebugAutoCoreFileExportTargetEntry 16 }

cfprSysdebugAutoCoreFileExportTargetFsmTry OBJECT-TYPE
    SYNTAX       Gauge32
    MAX-ACCESS   read-only
    STATUS       current
    DESCRIPTION
        "Cisco Firepower sysdebug:AutoCoreFileExportTarget:fsmTry
        managed object property"
    ::= { cfprSysdebugAutoCoreFileExportTargetEntry 17 }

cfprSysdebugAutoCoreFileExportTargetHostname OBJECT-TYPE
    SYNTAX       SnmpAdminString
    MAX-ACCESS   read-only
    STATUS       current
    DESCRIPTION
        "Cisco Firepower sysdebug:AutoCoreFileExportTarget:hostname
        managed object property"
    ::= { cfprSysdebugAutoCoreFileExportTargetEntry 18 }

cfprSysdebugAutoCoreFileExportTargetIntId OBJECT-TYPE
    SYNTAX       SnmpAdminString
    MAX-ACCESS   read-only
    STATUS       current
    DESCRIPTION
        "Cisco Firepower sysdebug:AutoCoreFileExportTarget:intId
        managed object property"
    ::= { cfprSysdebugAutoCoreFileExportTargetEntry 19 }

cfprSysdebugAutoCoreFileExportTargetName OBJECT-TYPE
    SYNTAX       SnmpAdminString
    MAX-ACCESS   read-only
    STATUS       current
    DESCRIPTION
        "Cisco Firepower sysdebug:AutoCoreFileExportTarget:name
        managed object property"
    ::= { cfprSysdebugAutoCoreFileExportTargetEntry 20 }

cfprSysdebugAutoCoreFileExportTargetPath OBJECT-TYPE
    SYNTAX       SnmpAdminString
    MAX-ACCESS   read-only
    STATUS       current
    DESCRIPTION
        "Cisco Firepower sysdebug:AutoCoreFileExportTarget:path
        managed object property"
    ::= { cfprSysdebugAutoCoreFileExportTargetEntry 21 }

cfprSysdebugAutoCoreFileExportTargetPolicyLevel OBJECT-TYPE
    SYNTAX       Gauge32
    MAX-ACCESS   read-only
    STATUS       current
    DESCRIPTION
        "Cisco Firepower sysdebug:AutoCoreFileExportTarget:policyLevel
        managed object property"
    ::= { cfprSysdebugAutoCoreFileExportTargetEntry 22 }

cfprSysdebugAutoCoreFileExportTargetPolicyOwner OBJECT-TYPE
    SYNTAX       CfprPolicyPolicyOwner
    MAX-ACCESS   read-only
    STATUS       current
    DESCRIPTION
        "Cisco Firepower sysdebug:AutoCoreFileExportTarget:policyOwner
        managed object property"
    ::= { cfprSysdebugAutoCoreFileExportTargetEntry 23 }

cfprSysdebugAutoCoreFileExportTargetPort OBJECT-TYPE
    SYNTAX       Gauge32
    MAX-ACCESS   read-only
    STATUS       current
    DESCRIPTION
        "Cisco Firepower sysdebug:AutoCoreFileExportTarget:port
        managed object property"
    ::= { cfprSysdebugAutoCoreFileExportTargetEntry 24 }

cfprSysdebugAutoCoreFileExportTargetPostAction OBJECT-TYPE
    SYNTAX       CfprSysfileExporterPostAction
    MAX-ACCESS   read-only
    STATUS       current
    DESCRIPTION
        "Cisco Firepower sysdebug:AutoCoreFileExportTarget:postAction
        managed object property"
    ::= { cfprSysdebugAutoCoreFileExportTargetEntry 25 }

cfprSysdebugAutoCoreFileExportTargetProto OBJECT-TYPE
    SYNTAX       CfprSysdebugAutoCoreFileExportTargetProto
    MAX-ACCESS   read-only
    STATUS       current
    DESCRIPTION
        "Cisco Firepower sysdebug:AutoCoreFileExportTarget:proto
        managed object property"
    ::= { cfprSysdebugAutoCoreFileExportTargetEntry 26 }

cfprSysdebugAutoCoreFileExportTargetFsmTable OBJECT-TYPE
    SYNTAX           SEQUENCE OF CfprSysdebugAutoCoreFileExportTargetFsmEntry
    MAX-ACCESS       not-accessible
    STATUS           current
    DESCRIPTION
        "Cisco Firepower sysdebug:AutoCoreFileExportTargetFsm
        managed object table"
    ::= { cfprSysdebugObjects 2 }

cfprSysdebugAutoCoreFileExportTargetFsmEntry OBJECT-TYPE
    SYNTAX           CfprSysdebugAutoCoreFileExportTargetFsmEntry
    MAX-ACCESS       not-accessible
    STATUS           current
    DESCRIPTION
        "Entry for the cfprSysdebugAutoCoreFileExportTargetFsmTable table."
    INDEX { cfprSysdebugAutoCoreFileExportTargetFsmInstanceId }
    ::= { cfprSysdebugAutoCoreFileExportTargetFsmTable 1 }

CfprSysdebugAutoCoreFileExportTargetFsmEntry ::= SEQUENCE {
    cfprSysdebugAutoCoreFileExportTargetFsmInstanceId                CfprManagedObjectId,
    cfprSysdebugAutoCoreFileExportTargetFsmDn                        CfprManagedObjectDn,
    cfprSysdebugAutoCoreFileExportTargetFsmRn                        SnmpAdminString,
    cfprSysdebugAutoCoreFileExportTargetFsmCompletionTime            DateAndTime,
    cfprSysdebugAutoCoreFileExportTargetFsmCurrentFsm                CfprSysdebugAutoCoreFileExportTargetFsmCurrentFsm,
    cfprSysdebugAutoCoreFileExportTargetFsmDescrData                 SnmpAdminString,
    cfprSysdebugAutoCoreFileExportTargetFsmFsmStatus                 CfprFsmFsmStageStatus,
    cfprSysdebugAutoCoreFileExportTargetFsmProgress                  Gauge32,
    cfprSysdebugAutoCoreFileExportTargetFsmRmtErrCode                Gauge32,
    cfprSysdebugAutoCoreFileExportTargetFsmRmtErrDescr               SnmpAdminString,
    cfprSysdebugAutoCoreFileExportTargetFsmRmtRslt                   CfprConditionRemoteInvRslt
}

cfprSysdebugAutoCoreFileExportTargetFsmInstanceId OBJECT-TYPE
    SYNTAX       CfprManagedObjectId
    MAX-ACCESS   not-accessible
    STATUS       current
    DESCRIPTION
        "Instance identifier of the managed object."
    ::= { cfprSysdebugAutoCoreFileExportTargetFsmEntry 1 }

cfprSysdebugAutoCoreFileExportTargetFsmDn OBJECT-TYPE
    SYNTAX       CfprManagedObjectDn
    MAX-ACCESS   read-only
    STATUS       current
    DESCRIPTION
        "Cisco Firepower sysdebug:AutoCoreFileExportTargetFsm:dn
        managed object property"
    ::= { cfprSysdebugAutoCoreFileExportTargetFsmEntry 2 }

cfprSysdebugAutoCoreFileExportTargetFsmRn OBJECT-TYPE
    SYNTAX       SnmpAdminString
    MAX-ACCESS   read-only
    STATUS       current
    DESCRIPTION
        "Cisco Firepower sysdebug:AutoCoreFileExportTargetFsm:rn
        managed object property"
    ::= { cfprSysdebugAutoCoreFileExportTargetFsmEntry 3 }

cfprSysdebugAutoCoreFileExportTargetFsmCompletionTime OBJECT-TYPE
    SYNTAX       DateAndTime
    MAX-ACCESS   read-only
    STATUS       current
    DESCRIPTION
        "Cisco Firepower sysdebug:AutoCoreFileExportTargetFsm:completionTi
        me managed object property"
    ::= { cfprSysdebugAutoCoreFileExportTargetFsmEntry 4 }

cfprSysdebugAutoCoreFileExportTargetFsmCurrentFsm OBJECT-TYPE
    SYNTAX       CfprSysdebugAutoCoreFileExportTargetFsmCurrentFsm
    MAX-ACCESS   read-only
    STATUS       current
    DESCRIPTION
        "Cisco Firepower sysdebug:AutoCoreFileExportTargetFsm:currentFsm
        managed object property"
    ::= { cfprSysdebugAutoCoreFileExportTargetFsmEntry 5 }

cfprSysdebugAutoCoreFileExportTargetFsmDescrData OBJECT-TYPE
    SYNTAX       SnmpAdminString
    MAX-ACCESS   read-only
    STATUS       current
    DESCRIPTION
        "Cisco Firepower sysdebug:AutoCoreFileExportTargetFsm:descr
        managed object property"
    ::= { cfprSysdebugAutoCoreFileExportTargetFsmEntry 6 }

cfprSysdebugAutoCoreFileExportTargetFsmFsmStatus OBJECT-TYPE
    SYNTAX       CfprFsmFsmStageStatus
    MAX-ACCESS   read-only
    STATUS       current
    DESCRIPTION
        "Cisco Firepower sysdebug:AutoCoreFileExportTargetFsm:fsmStatus
        managed object property"
    ::= { cfprSysdebugAutoCoreFileExportTargetFsmEntry 7 }

cfprSysdebugAutoCoreFileExportTargetFsmProgress OBJECT-TYPE
    SYNTAX       Gauge32
    MAX-ACCESS   read-only
    STATUS       current
    DESCRIPTION
        "Cisco Firepower sysdebug:AutoCoreFileExportTargetFsm:progress
        managed object property"
    ::= { cfprSysdebugAutoCoreFileExportTargetFsmEntry 8 }

cfprSysdebugAutoCoreFileExportTargetFsmRmtErrCode OBJECT-TYPE
    SYNTAX       Gauge32
    MAX-ACCESS   read-only
    STATUS       current
    DESCRIPTION
        "Cisco Firepower sysdebug:AutoCoreFileExportTargetFsm:rmtErrCode
        managed object property"
    ::= { cfprSysdebugAutoCoreFileExportTargetFsmEntry 9 }

cfprSysdebugAutoCoreFileExportTargetFsmRmtErrDescr OBJECT-TYPE
    SYNTAX       SnmpAdminString
    MAX-ACCESS   read-only
    STATUS       current
    DESCRIPTION
        "Cisco Firepower sysdebug:AutoCoreFileExportTargetFsm:rmtErrDescr
        managed object property"
    ::= { cfprSysdebugAutoCoreFileExportTargetFsmEntry 10 }

cfprSysdebugAutoCoreFileExportTargetFsmRmtRslt OBJECT-TYPE
    SYNTAX       CfprConditionRemoteInvRslt
    MAX-ACCESS   read-only
    STATUS       current
    DESCRIPTION
        "Cisco Firepower sysdebug:AutoCoreFileExportTargetFsm:rmtRslt
        managed object property"
    ::= { cfprSysdebugAutoCoreFileExportTargetFsmEntry 11 }

cfprSysdebugAutoCoreFileExportTargetFsmStageTable OBJECT-TYPE
    SYNTAX           SEQUENCE OF CfprSysdebugAutoCoreFileExportTargetFsmStageEntry
    MAX-ACCESS       not-accessible
    STATUS           current
    DESCRIPTION
        "Cisco Firepower sysdebug:AutoCoreFileExportTargetFsmStage
        managed object table"
    ::= { cfprSysdebugObjects 3 }

cfprSysdebugAutoCoreFileExportTargetFsmStageEntry OBJECT-TYPE
    SYNTAX           CfprSysdebugAutoCoreFileExportTargetFsmStageEntry
    MAX-ACCESS       not-accessible
    STATUS           current
    DESCRIPTION
        "Entry for the cfprSysdebugAutoCoreFileExportTargetFsmStageTable table."
    INDEX { cfprSysdebugAutoCoreFileExportTargetFsmStageInstanceId }
    ::= { cfprSysdebugAutoCoreFileExportTargetFsmStageTable 1 }

CfprSysdebugAutoCoreFileExportTargetFsmStageEntry ::= SEQUENCE {
    cfprSysdebugAutoCoreFileExportTargetFsmStageInstanceId           CfprManagedObjectId,
    cfprSysdebugAutoCoreFileExportTargetFsmStageDn                   CfprManagedObjectDn,
    cfprSysdebugAutoCoreFileExportTargetFsmStageRn                   SnmpAdminString,
    cfprSysdebugAutoCoreFileExportTargetFsmStageDescrData            SnmpAdminString,
    cfprSysdebugAutoCoreFileExportTargetFsmStageLastUpdateTime       DateAndTime,
    cfprSysdebugAutoCoreFileExportTargetFsmStageName                 CfprSysdebugAutoCoreFileExportTargetFsmStageName,
    cfprSysdebugAutoCoreFileExportTargetFsmStageOrder                Gauge32,
    cfprSysdebugAutoCoreFileExportTargetFsmStageRetry                Gauge32,
    cfprSysdebugAutoCoreFileExportTargetFsmStageStageStatus          CfprFsmFsmStageStatus
}

cfprSysdebugAutoCoreFileExportTargetFsmStageInstanceId OBJECT-TYPE
    SYNTAX       CfprManagedObjectId
    MAX-ACCESS   not-accessible
    STATUS       current
    DESCRIPTION
        "Instance identifier of the managed object."
    ::= { cfprSysdebugAutoCoreFileExportTargetFsmStageEntry 1 }

cfprSysdebugAutoCoreFileExportTargetFsmStageDn OBJECT-TYPE
    SYNTAX       CfprManagedObjectDn
    MAX-ACCESS   read-only
    STATUS       current
    DESCRIPTION
        "Cisco Firepower sysdebug:AutoCoreFileExportTargetFsmStage:dn
        managed object property"
    ::= { cfprSysdebugAutoCoreFileExportTargetFsmStageEntry 2 }

cfprSysdebugAutoCoreFileExportTargetFsmStageRn OBJECT-TYPE
    SYNTAX       SnmpAdminString
    MAX-ACCESS   read-only
    STATUS       current
    DESCRIPTION
        "Cisco Firepower sysdebug:AutoCoreFileExportTargetFsmStage:rn
        managed object property"
    ::= { cfprSysdebugAutoCoreFileExportTargetFsmStageEntry 3 }

cfprSysdebugAutoCoreFileExportTargetFsmStageDescrData OBJECT-TYPE
    SYNTAX       SnmpAdminString
    MAX-ACCESS   read-only
    STATUS       current
    DESCRIPTION
        "Cisco Firepower sysdebug:AutoCoreFileExportTargetFsmStage:descr
        managed object property"
    ::= { cfprSysdebugAutoCoreFileExportTargetFsmStageEntry 4 }

cfprSysdebugAutoCoreFileExportTargetFsmStageLastUpdateTime OBJECT-TYPE
    SYNTAX       DateAndTime
    MAX-ACCESS   read-only
    STATUS       current
    DESCRIPTION
        "Cisco Firepower sysdebug:AutoCoreFileExportTargetFsmStage:lastUpd
        ateTime managed object property"
    ::= { cfprSysdebugAutoCoreFileExportTargetFsmStageEntry 5 }

cfprSysdebugAutoCoreFileExportTargetFsmStageName OBJECT-TYPE
    SYNTAX       CfprSysdebugAutoCoreFileExportTargetFsmStageName
    MAX-ACCESS   read-only
    STATUS       current
    DESCRIPTION
        "Cisco Firepower sysdebug:AutoCoreFileExportTargetFsmStage:name
        managed object property"
    ::= { cfprSysdebugAutoCoreFileExportTargetFsmStageEntry 6 }

cfprSysdebugAutoCoreFileExportTargetFsmStageOrder OBJECT-TYPE
    SYNTAX       Gauge32
    MAX-ACCESS   read-only
    STATUS       current
    DESCRIPTION
        "Cisco Firepower sysdebug:AutoCoreFileExportTargetFsmStage:order
        managed object property"
    ::= { cfprSysdebugAutoCoreFileExportTargetFsmStageEntry 7 }

cfprSysdebugAutoCoreFileExportTargetFsmStageRetry OBJECT-TYPE
    SYNTAX       Gauge32
    MAX-ACCESS   read-only
    STATUS       current
    DESCRIPTION
        "Cisco Firepower sysdebug:AutoCoreFileExportTargetFsmStage:retry
        managed object property"
    ::= { cfprSysdebugAutoCoreFileExportTargetFsmStageEntry 8 }

cfprSysdebugAutoCoreFileExportTargetFsmStageStageStatus OBJECT-TYPE
    SYNTAX       CfprFsmFsmStageStatus
    MAX-ACCESS   read-only
    STATUS       current
    DESCRIPTION
        "Cisco Firepower sysdebug:AutoCoreFileExportTargetFsmStage:stageSt
        atus managed object property"
    ::= { cfprSysdebugAutoCoreFileExportTargetFsmStageEntry 9 }

cfprSysdebugAutoCoreFileExportTargetFsmTaskTable OBJECT-TYPE
    SYNTAX           SEQUENCE OF CfprSysdebugAutoCoreFileExportTargetFsmTaskEntry
    MAX-ACCESS       not-accessible
    STATUS           current
    DESCRIPTION
        "Cisco Firepower sysdebug:AutoCoreFileExportTargetFsmTask
        managed object table"
    ::= { cfprSysdebugObjects 4 }

cfprSysdebugAutoCoreFileExportTargetFsmTaskEntry OBJECT-TYPE
    SYNTAX           CfprSysdebugAutoCoreFileExportTargetFsmTaskEntry
    MAX-ACCESS       not-accessible
    STATUS           current
    DESCRIPTION
        "Entry for the cfprSysdebugAutoCoreFileExportTargetFsmTaskTable table."
    INDEX { cfprSysdebugAutoCoreFileExportTargetFsmTaskInstanceId }
    ::= { cfprSysdebugAutoCoreFileExportTargetFsmTaskTable 1 }

CfprSysdebugAutoCoreFileExportTargetFsmTaskEntry ::= SEQUENCE {
    cfprSysdebugAutoCoreFileExportTargetFsmTaskInstanceId            CfprManagedObjectId,
    cfprSysdebugAutoCoreFileExportTargetFsmTaskDn                    CfprManagedObjectDn,
    cfprSysdebugAutoCoreFileExportTargetFsmTaskRn                    SnmpAdminString,
    cfprSysdebugAutoCoreFileExportTargetFsmTaskCompletion            CfprFsmCompletion,
    cfprSysdebugAutoCoreFileExportTargetFsmTaskFlags                 CfprFsmFlags,
    cfprSysdebugAutoCoreFileExportTargetFsmTaskItem                  CfprSysdebugAutoCoreFileExportTargetFsmTaskItem,
    cfprSysdebugAutoCoreFileExportTargetFsmTaskSeqId                 Gauge32
}

cfprSysdebugAutoCoreFileExportTargetFsmTaskInstanceId OBJECT-TYPE
    SYNTAX       CfprManagedObjectId
    MAX-ACCESS   not-accessible
    STATUS       current
    DESCRIPTION
        "Instance identifier of the managed object."
    ::= { cfprSysdebugAutoCoreFileExportTargetFsmTaskEntry 1 }

cfprSysdebugAutoCoreFileExportTargetFsmTaskDn OBJECT-TYPE
    SYNTAX       CfprManagedObjectDn
    MAX-ACCESS   read-only
    STATUS       current
    DESCRIPTION
        "Cisco Firepower sysdebug:AutoCoreFileExportTargetFsmTask:dn
        managed object property"
    ::= { cfprSysdebugAutoCoreFileExportTargetFsmTaskEntry 2 }

cfprSysdebugAutoCoreFileExportTargetFsmTaskRn OBJECT-TYPE
    SYNTAX       SnmpAdminString
    MAX-ACCESS   read-only
    STATUS       current
    DESCRIPTION
        "Cisco Firepower sysdebug:AutoCoreFileExportTargetFsmTask:rn
        managed object property"
    ::= { cfprSysdebugAutoCoreFileExportTargetFsmTaskEntry 3 }

cfprSysdebugAutoCoreFileExportTargetFsmTaskCompletion OBJECT-TYPE
    SYNTAX       CfprFsmCompletion
    MAX-ACCESS   read-only
    STATUS       current
    DESCRIPTION
        "Cisco Firepower sysdebug:AutoCoreFileExportTargetFsmTask:completi
        on managed object property"
    ::= { cfprSysdebugAutoCoreFileExportTargetFsmTaskEntry 4 }

cfprSysdebugAutoCoreFileExportTargetFsmTaskFlags OBJECT-TYPE
    SYNTAX       CfprFsmFlags
    MAX-ACCESS   read-only
    STATUS       current
    DESCRIPTION
        "Cisco Firepower sysdebug:AutoCoreFileExportTargetFsmTask:flags
        managed object property"
    ::= { cfprSysdebugAutoCoreFileExportTargetFsmTaskEntry 5 }

cfprSysdebugAutoCoreFileExportTargetFsmTaskItem OBJECT-TYPE
    SYNTAX       CfprSysdebugAutoCoreFileExportTargetFsmTaskItem
    MAX-ACCESS   read-only
    STATUS       current
    DESCRIPTION
        "Cisco Firepower sysdebug:AutoCoreFileExportTargetFsmTask:item
        managed object property"
    ::= { cfprSysdebugAutoCoreFileExportTargetFsmTaskEntry 6 }

cfprSysdebugAutoCoreFileExportTargetFsmTaskSeqId OBJECT-TYPE
    SYNTAX       Gauge32
    MAX-ACCESS   read-only
    STATUS       current
    DESCRIPTION
        "Cisco Firepower sysdebug:AutoCoreFileExportTargetFsmTask:seqId
        managed object property"
    ::= { cfprSysdebugAutoCoreFileExportTargetFsmTaskEntry 7 }

cfprSysdebugBackupBehaviorTable OBJECT-TYPE
    SYNTAX           SEQUENCE OF CfprSysdebugBackupBehaviorEntry
    MAX-ACCESS       not-accessible
    STATUS           current
    DESCRIPTION
        "Cisco Firepower sysdebug:BackupBehavior managed object table"
    ::= { cfprSysdebugObjects 5 }

cfprSysdebugBackupBehaviorEntry OBJECT-TYPE
    SYNTAX           CfprSysdebugBackupBehaviorEntry
    MAX-ACCESS       not-accessible
    STATUS           current
    DESCRIPTION
        "Entry for the cfprSysdebugBackupBehaviorTable table."
    INDEX { cfprSysdebugBackupBehaviorInstanceId }
    ::= { cfprSysdebugBackupBehaviorTable 1 }

CfprSysdebugBackupBehaviorEntry ::= SEQUENCE {
    cfprSysdebugBackupBehaviorInstanceId                             CfprManagedObjectId,
    cfprSysdebugBackupBehaviorDn                                     CfprManagedObjectDn,
    cfprSysdebugBackupBehaviorRn                                     SnmpAdminString,
    cfprSysdebugBackupBehaviorAction                                 CfprSysdebugEpLogBackupAction,
    cfprSysdebugBackupBehaviorClearOnBackup                          TruthValue,
    cfprSysdebugBackupBehaviorFormat                                 CfprSysdebugBackupFormat,
    cfprSysdebugBackupBehaviorHostname                               SnmpAdminString,
    cfprSysdebugBackupBehaviorInterval                               CfprSysdebugBackupBehaviorInterval,
    cfprSysdebugBackupBehaviorProto                                  CfprSysdebugBackupBehaviorProto,
    cfprSysdebugBackupBehaviorPwd                                    SnmpAdminString,
    cfprSysdebugBackupBehaviorRemotePath                             SnmpAdminString,
    cfprSysdebugBackupBehaviorUser                                   SnmpAdminString
}

cfprSysdebugBackupBehaviorInstanceId OBJECT-TYPE
    SYNTAX       CfprManagedObjectId
    MAX-ACCESS   not-accessible
    STATUS       current
    DESCRIPTION
        "Instance identifier of the managed object."
    ::= { cfprSysdebugBackupBehaviorEntry 1 }

cfprSysdebugBackupBehaviorDn OBJECT-TYPE
    SYNTAX       CfprManagedObjectDn
    MAX-ACCESS   read-only
    STATUS       current
    DESCRIPTION
        "Cisco Firepower sysdebug:BackupBehavior:dn managed
        object property"
    ::= { cfprSysdebugBackupBehaviorEntry 2 }

cfprSysdebugBackupBehaviorRn OBJECT-TYPE
    SYNTAX       SnmpAdminString
    MAX-ACCESS   read-only
    STATUS       current
    DESCRIPTION
        "Cisco Firepower sysdebug:BackupBehavior:rn managed
        object property"
    ::= { cfprSysdebugBackupBehaviorEntry 3 }

cfprSysdebugBackupBehaviorAction OBJECT-TYPE
    SYNTAX       CfprSysdebugEpLogBackupAction
    MAX-ACCESS   read-only
    STATUS       current
    DESCRIPTION
        "Cisco Firepower sysdebug:BackupBehavior:action
        managed object property"
    ::= { cfprSysdebugBackupBehaviorEntry 4 }

cfprSysdebugBackupBehaviorClearOnBackup OBJECT-TYPE
    SYNTAX       TruthValue
    MAX-ACCESS   read-only
    STATUS       current
    DESCRIPTION
        "Cisco Firepower sysdebug:BackupBehavior:clearOnBackup
        managed object property"
    ::= { cfprSysdebugBackupBehaviorEntry 5 }

cfprSysdebugBackupBehaviorFormat OBJECT-TYPE
    SYNTAX       CfprSysdebugBackupFormat
    MAX-ACCESS   read-only
    STATUS       current
    DESCRIPTION
        "Cisco Firepower sysdebug:BackupBehavior:format
        managed object property"
    ::= { cfprSysdebugBackupBehaviorEntry 6 }

cfprSysdebugBackupBehaviorHostname OBJECT-TYPE
    SYNTAX       SnmpAdminString
    MAX-ACCESS   read-only
    STATUS       current
    DESCRIPTION
        "Cisco Firepower sysdebug:BackupBehavior:hostname
        managed object property"
    ::= { cfprSysdebugBackupBehaviorEntry 7 }

cfprSysdebugBackupBehaviorInterval OBJECT-TYPE
    SYNTAX       CfprSysdebugBackupBehaviorInterval
    MAX-ACCESS   read-only
    STATUS       current
    DESCRIPTION
        "Cisco Firepower sysdebug:BackupBehavior:interval
        managed object property"
    ::= { cfprSysdebugBackupBehaviorEntry 8 }

cfprSysdebugBackupBehaviorProto OBJECT-TYPE
    SYNTAX       CfprSysdebugBackupBehaviorProto
    MAX-ACCESS   read-only
    STATUS       current
    DESCRIPTION
        "Cisco Firepower sysdebug:BackupBehavior:proto
        managed object property"
    ::= { cfprSysdebugBackupBehaviorEntry 9 }

cfprSysdebugBackupBehaviorPwd OBJECT-TYPE
    SYNTAX       SnmpAdminString
    MAX-ACCESS   read-only
    STATUS       current
    DESCRIPTION
        "Cisco Firepower sysdebug:BackupBehavior:pwd managed
        object property"
    ::= { cfprSysdebugBackupBehaviorEntry 10 }

cfprSysdebugBackupBehaviorRemotePath OBJECT-TYPE
    SYNTAX       SnmpAdminString
    MAX-ACCESS   read-only
    STATUS       current
    DESCRIPTION
        "Cisco Firepower sysdebug:BackupBehavior:remotePath
        managed object property"
    ::= { cfprSysdebugBackupBehaviorEntry 11 }

cfprSysdebugBackupBehaviorUser OBJECT-TYPE
    SYNTAX       SnmpAdminString
    MAX-ACCESS   read-only
    STATUS       current
    DESCRIPTION
        "Cisco Firepower sysdebug:BackupBehavior:user managed
        object property"
    ::= { cfprSysdebugBackupBehaviorEntry 12 }

cfprSysdebugCoreTable OBJECT-TYPE
    SYNTAX           SEQUENCE OF CfprSysdebugCoreEntry
    MAX-ACCESS       not-accessible
    STATUS           current
    DESCRIPTION
        "Cisco Firepower sysdebug:Core managed object table"
    ::= { cfprSysdebugObjects 6 }

cfprSysdebugCoreEntry OBJECT-TYPE
    SYNTAX           CfprSysdebugCoreEntry
    MAX-ACCESS       not-accessible
    STATUS           current
    DESCRIPTION
        "Entry for the cfprSysdebugCoreTable table."
    INDEX { cfprSysdebugCoreInstanceId }
    ::= { cfprSysdebugCoreTable 1 }

CfprSysdebugCoreEntry ::= SEQUENCE {
    cfprSysdebugCoreInstanceId                                       CfprManagedObjectId,
    cfprSysdebugCoreDn                                               CfprManagedObjectDn,
    cfprSysdebugCoreRn                                               SnmpAdminString,
    cfprSysdebugCoreAdminState                                       CfprSysdebugCoreFileAdminState,
    cfprSysdebugCoreDescr                                            SnmpAdminString,
    cfprSysdebugCoreFsmDescr                                         SnmpAdminString,
    cfprSysdebugCoreFsmPrev                                          SnmpAdminString,
    cfprSysdebugCoreFsmProgr                                         Gauge32,
    cfprSysdebugCoreFsmRmtInvErrCode                                 Gauge32,
    cfprSysdebugCoreFsmRmtInvErrDescr                                SnmpAdminString,
    cfprSysdebugCoreFsmRmtInvRslt                                    CfprConditionRemoteInvRslt,
    cfprSysdebugCoreFsmStageDescr                                    SnmpAdminString,
    cfprSysdebugCoreFsmStamp                                         DateAndTime,
    cfprSysdebugCoreFsmStatus                                        SnmpAdminString,
    cfprSysdebugCoreFsmTry                                           Gauge32,
    cfprSysdebugCoreName                                             SnmpAdminString,
    cfprSysdebugCoreOperState                                        CfprSysdebugCoreFileOperState,
    cfprSysdebugCoreSize                                             Gauge32,
    cfprSysdebugCoreSwitchId                                         CfprNetworkSwitchId,
    cfprSysdebugCoreTs                                               DateAndTime,
    cfprSysdebugCoreUri                                              SnmpAdminString
}

cfprSysdebugCoreInstanceId OBJECT-TYPE
    SYNTAX       CfprManagedObjectId
    MAX-ACCESS   not-accessible
    STATUS       current
    DESCRIPTION
        "Instance identifier of the managed object."
    ::= { cfprSysdebugCoreEntry 1 }

cfprSysdebugCoreDn OBJECT-TYPE
    SYNTAX       CfprManagedObjectDn
    MAX-ACCESS   read-only
    STATUS       current
    DESCRIPTION
        "Cisco Firepower sysdebug:Core:dn managed object property"
    ::= { cfprSysdebugCoreEntry 2 }

cfprSysdebugCoreRn OBJECT-TYPE
    SYNTAX       SnmpAdminString
    MAX-ACCESS   read-only
    STATUS       current
    DESCRIPTION
        "Cisco Firepower sysdebug:Core:rn managed object property"
    ::= { cfprSysdebugCoreEntry 3 }

cfprSysdebugCoreAdminState OBJECT-TYPE
    SYNTAX       CfprSysdebugCoreFileAdminState
    MAX-ACCESS   read-only
    STATUS       current
    DESCRIPTION
        "Cisco Firepower sysdebug:Core:adminState managed object property"
    ::= { cfprSysdebugCoreEntry 4 }

cfprSysdebugCoreDescr OBJECT-TYPE
    SYNTAX       SnmpAdminString
    MAX-ACCESS   read-only
    STATUS       current
    DESCRIPTION
        "Cisco Firepower sysdebug:Core:descr managed object property"
    ::= { cfprSysdebugCoreEntry 5 }

cfprSysdebugCoreFsmDescr OBJECT-TYPE
    SYNTAX       SnmpAdminString
    MAX-ACCESS   read-only
    STATUS       current
    DESCRIPTION
        "Cisco Firepower sysdebug:Core:fsmDescr managed object property"
    ::= { cfprSysdebugCoreEntry 6 }

cfprSysdebugCoreFsmPrev OBJECT-TYPE
    SYNTAX       SnmpAdminString
    MAX-ACCESS   read-only
    STATUS       current
    DESCRIPTION
        "Cisco Firepower sysdebug:Core:fsmPrev managed object property"
    ::= { cfprSysdebugCoreEntry 7 }

cfprSysdebugCoreFsmProgr OBJECT-TYPE
    SYNTAX       Gauge32
    MAX-ACCESS   read-only
    STATUS       current
    DESCRIPTION
        "Cisco Firepower sysdebug:Core:fsmProgr managed object property"
    ::= { cfprSysdebugCoreEntry 8 }

cfprSysdebugCoreFsmRmtInvErrCode OBJECT-TYPE
    SYNTAX       Gauge32
    MAX-ACCESS   read-only
    STATUS       current
    DESCRIPTION
        "Cisco Firepower sysdebug:Core:fsmRmtInvErrCode
        managed object property"
    ::= { cfprSysdebugCoreEntry 9 }

cfprSysdebugCoreFsmRmtInvErrDescr OBJECT-TYPE
    SYNTAX       SnmpAdminString
    MAX-ACCESS   read-only
    STATUS       current
    DESCRIPTION
        "Cisco Firepower sysdebug:Core:fsmRmtInvErrDescr
        managed object property"
    ::= { cfprSysdebugCoreEntry 10 }

cfprSysdebugCoreFsmRmtInvRslt OBJECT-TYPE
    SYNTAX       CfprConditionRemoteInvRslt
    MAX-ACCESS   read-only
    STATUS       current
    DESCRIPTION
        "Cisco Firepower sysdebug:Core:fsmRmtInvRslt managed
        object property"
    ::= { cfprSysdebugCoreEntry 11 }

cfprSysdebugCoreFsmStageDescr OBJECT-TYPE
    SYNTAX       SnmpAdminString
    MAX-ACCESS   read-only
    STATUS       current
    DESCRIPTION
        "Cisco Firepower sysdebug:Core:fsmStageDescr managed
        object property"
    ::= { cfprSysdebugCoreEntry 12 }

cfprSysdebugCoreFsmStamp OBJECT-TYPE
    SYNTAX       DateAndTime
    MAX-ACCESS   read-only
    STATUS       current
    DESCRIPTION
        "Cisco Firepower sysdebug:Core:fsmStamp managed object property"
    ::= { cfprSysdebugCoreEntry 13 }

cfprSysdebugCoreFsmStatus OBJECT-TYPE
    SYNTAX       SnmpAdminString
    MAX-ACCESS   read-only
    STATUS       current
    DESCRIPTION
        "Cisco Firepower sysdebug:Core:fsmStatus managed object property"
    ::= { cfprSysdebugCoreEntry 14 }

cfprSysdebugCoreFsmTry OBJECT-TYPE
    SYNTAX       Gauge32
    MAX-ACCESS   read-only
    STATUS       current
    DESCRIPTION
        "Cisco Firepower sysdebug:Core:fsmTry managed object property"
    ::= { cfprSysdebugCoreEntry 15 }

cfprSysdebugCoreName OBJECT-TYPE
    SYNTAX       SnmpAdminString
    MAX-ACCESS   read-only
    STATUS       current
    DESCRIPTION
        "Cisco Firepower sysdebug:Core:name managed object property"
    ::= { cfprSysdebugCoreEntry 16 }

cfprSysdebugCoreOperState OBJECT-TYPE
    SYNTAX       CfprSysdebugCoreFileOperState
    MAX-ACCESS   read-only
    STATUS       current
    DESCRIPTION
        "Cisco Firepower sysdebug:Core:operState managed object property"
    ::= { cfprSysdebugCoreEntry 17 }

cfprSysdebugCoreSize OBJECT-TYPE
    SYNTAX       Gauge32
    MAX-ACCESS   read-only
    STATUS       current
    DESCRIPTION
        "Cisco Firepower sysdebug:Core:size managed object property"
    ::= { cfprSysdebugCoreEntry 18 }

cfprSysdebugCoreSwitchId OBJECT-TYPE
    SYNTAX       CfprNetworkSwitchId
    MAX-ACCESS   read-only
    STATUS       current
    DESCRIPTION
        "Cisco Firepower sysdebug:Core:switchId managed object property"
    ::= { cfprSysdebugCoreEntry 19 }

cfprSysdebugCoreTs OBJECT-TYPE
    SYNTAX       DateAndTime
    MAX-ACCESS   read-only
    STATUS       current
    DESCRIPTION
        "Cisco Firepower sysdebug:Core:ts managed object property"
    ::= { cfprSysdebugCoreEntry 20 }

cfprSysdebugCoreUri OBJECT-TYPE
    SYNTAX       SnmpAdminString
    MAX-ACCESS   read-only
    STATUS       current
    DESCRIPTION
        "Cisco Firepower sysdebug:Core:uri managed object property"
    ::= { cfprSysdebugCoreEntry 21 }

cfprSysdebugCoreFileRepositoryTable OBJECT-TYPE
    SYNTAX           SEQUENCE OF CfprSysdebugCoreFileRepositoryEntry
    MAX-ACCESS       not-accessible
    STATUS           current
    DESCRIPTION
        "Cisco Firepower sysdebug:CoreFileRepository managed object table"
    ::= { cfprSysdebugObjects 7 }

cfprSysdebugCoreFileRepositoryEntry OBJECT-TYPE
    SYNTAX           CfprSysdebugCoreFileRepositoryEntry
    MAX-ACCESS       not-accessible
    STATUS           current
    DESCRIPTION
        "Entry for the cfprSysdebugCoreFileRepositoryTable table."
    INDEX { cfprSysdebugCoreFileRepositoryInstanceId }
    ::= { cfprSysdebugCoreFileRepositoryTable 1 }

CfprSysdebugCoreFileRepositoryEntry ::= SEQUENCE {
    cfprSysdebugCoreFileRepositoryInstanceId                         CfprManagedObjectId,
    cfprSysdebugCoreFileRepositoryDn                                 CfprManagedObjectDn,
    cfprSysdebugCoreFileRepositoryRn                                 SnmpAdminString
}

cfprSysdebugCoreFileRepositoryInstanceId OBJECT-TYPE
    SYNTAX       CfprManagedObjectId
    MAX-ACCESS   not-accessible
    STATUS       current
    DESCRIPTION
        "Instance identifier of the managed object."
    ::= { cfprSysdebugCoreFileRepositoryEntry 1 }

cfprSysdebugCoreFileRepositoryDn OBJECT-TYPE
    SYNTAX       CfprManagedObjectDn
    MAX-ACCESS   read-only
    STATUS       current
    DESCRIPTION
        "Cisco Firepower sysdebug:CoreFileRepository:dn
        managed object property"
    ::= { cfprSysdebugCoreFileRepositoryEntry 2 }

cfprSysdebugCoreFileRepositoryRn OBJECT-TYPE
    SYNTAX       SnmpAdminString
    MAX-ACCESS   read-only
    STATUS       current
    DESCRIPTION
        "Cisco Firepower sysdebug:CoreFileRepository:rn
        managed object property"
    ::= { cfprSysdebugCoreFileRepositoryEntry 3 }

cfprSysdebugCoreFsmTable OBJECT-TYPE
    SYNTAX           SEQUENCE OF CfprSysdebugCoreFsmEntry
    MAX-ACCESS       not-accessible
    STATUS           current
    DESCRIPTION
        "Cisco Firepower sysdebug:CoreFsm managed object table"
    ::= { cfprSysdebugObjects 8 }

cfprSysdebugCoreFsmEntry OBJECT-TYPE
    SYNTAX           CfprSysdebugCoreFsmEntry
    MAX-ACCESS       not-accessible
    STATUS           current
    DESCRIPTION
        "Entry for the cfprSysdebugCoreFsmTable table."
    INDEX { cfprSysdebugCoreFsmInstanceId }
    ::= { cfprSysdebugCoreFsmTable 1 }

CfprSysdebugCoreFsmEntry ::= SEQUENCE {
    cfprSysdebugCoreFsmInstanceId                                    CfprManagedObjectId,
    cfprSysdebugCoreFsmDn                                            CfprManagedObjectDn,
    cfprSysdebugCoreFsmRn                                            SnmpAdminString,
    cfprSysdebugCoreFsmCompletionTime                                DateAndTime,
    cfprSysdebugCoreFsmCurrentFsm                                    CfprSysdebugCoreFsmCurrentFsm,
    cfprSysdebugCoreFsmDescrData                                     SnmpAdminString,
    cfprSysdebugCoreFsmFsmStatus                                     CfprFsmFsmStageStatus,
    cfprSysdebugCoreFsmProgress                                      Gauge32,
    cfprSysdebugCoreFsmRmtErrCode                                    Gauge32,
    cfprSysdebugCoreFsmRmtErrDescr                                   SnmpAdminString,
    cfprSysdebugCoreFsmRmtRslt                                       CfprConditionRemoteInvRslt
}

cfprSysdebugCoreFsmInstanceId OBJECT-TYPE
    SYNTAX       CfprManagedObjectId
    MAX-ACCESS   not-accessible
    STATUS       current
    DESCRIPTION
        "Instance identifier of the managed object."
    ::= { cfprSysdebugCoreFsmEntry 1 }

cfprSysdebugCoreFsmDn OBJECT-TYPE
    SYNTAX       CfprManagedObjectDn
    MAX-ACCESS   read-only
    STATUS       current
    DESCRIPTION
        "Cisco Firepower sysdebug:CoreFsm:dn managed object property"
    ::= { cfprSysdebugCoreFsmEntry 2 }

cfprSysdebugCoreFsmRn OBJECT-TYPE
    SYNTAX       SnmpAdminString
    MAX-ACCESS   read-only
    STATUS       current
    DESCRIPTION
        "Cisco Firepower sysdebug:CoreFsm:rn managed object property"
    ::= { cfprSysdebugCoreFsmEntry 3 }

cfprSysdebugCoreFsmCompletionTime OBJECT-TYPE
    SYNTAX       DateAndTime
    MAX-ACCESS   read-only
    STATUS       current
    DESCRIPTION
        "Cisco Firepower sysdebug:CoreFsm:completionTime
        managed object property"
    ::= { cfprSysdebugCoreFsmEntry 4 }

cfprSysdebugCoreFsmCurrentFsm OBJECT-TYPE
    SYNTAX       CfprSysdebugCoreFsmCurrentFsm
    MAX-ACCESS   read-only
    STATUS       current
    DESCRIPTION
        "Cisco Firepower sysdebug:CoreFsm:currentFsm managed
        object property"
    ::= { cfprSysdebugCoreFsmEntry 5 }

cfprSysdebugCoreFsmDescrData OBJECT-TYPE
    SYNTAX       SnmpAdminString
    MAX-ACCESS   read-only
    STATUS       current
    DESCRIPTION
        "Cisco Firepower sysdebug:CoreFsm:descr managed object property"
    ::= { cfprSysdebugCoreFsmEntry 6 }

cfprSysdebugCoreFsmFsmStatus OBJECT-TYPE
    SYNTAX       CfprFsmFsmStageStatus
    MAX-ACCESS   read-only
    STATUS       current
    DESCRIPTION
        "Cisco Firepower sysdebug:CoreFsm:fsmStatus managed
        object property"
    ::= { cfprSysdebugCoreFsmEntry 7 }

cfprSysdebugCoreFsmProgress OBJECT-TYPE
    SYNTAX       Gauge32
    MAX-ACCESS   read-only
    STATUS       current
    DESCRIPTION
        "Cisco Firepower sysdebug:CoreFsm:progress managed
        object property"
    ::= { cfprSysdebugCoreFsmEntry 8 }

cfprSysdebugCoreFsmRmtErrCode OBJECT-TYPE
    SYNTAX       Gauge32
    MAX-ACCESS   read-only
    STATUS       current
    DESCRIPTION
        "Cisco Firepower sysdebug:CoreFsm:rmtErrCode managed
        object property"
    ::= { cfprSysdebugCoreFsmEntry 9 }

cfprSysdebugCoreFsmRmtErrDescr OBJECT-TYPE
    SYNTAX       SnmpAdminString
    MAX-ACCESS   read-only
    STATUS       current
    DESCRIPTION
        "Cisco Firepower sysdebug:CoreFsm:rmtErrDescr managed
        object property"
    ::= { cfprSysdebugCoreFsmEntry 10 }

cfprSysdebugCoreFsmRmtRslt OBJECT-TYPE
    SYNTAX       CfprConditionRemoteInvRslt
    MAX-ACCESS   read-only
    STATUS       current
    DESCRIPTION
        "Cisco Firepower sysdebug:CoreFsm:rmtRslt managed object property"
    ::= { cfprSysdebugCoreFsmEntry 11 }

cfprSysdebugCoreFsmStageTable OBJECT-TYPE
    SYNTAX           SEQUENCE OF CfprSysdebugCoreFsmStageEntry
    MAX-ACCESS       not-accessible
    STATUS           current
    DESCRIPTION
        "Cisco Firepower sysdebug:CoreFsmStage managed object table"
    ::= { cfprSysdebugObjects 9 }

cfprSysdebugCoreFsmStageEntry OBJECT-TYPE
    SYNTAX           CfprSysdebugCoreFsmStageEntry
    MAX-ACCESS       not-accessible
    STATUS           current
    DESCRIPTION
        "Entry for the cfprSysdebugCoreFsmStageTable table."
    INDEX { cfprSysdebugCoreFsmStageInstanceId }
    ::= { cfprSysdebugCoreFsmStageTable 1 }

CfprSysdebugCoreFsmStageEntry ::= SEQUENCE {
    cfprSysdebugCoreFsmStageInstanceId                               CfprManagedObjectId,
    cfprSysdebugCoreFsmStageDn                                       CfprManagedObjectDn,
    cfprSysdebugCoreFsmStageRn                                       SnmpAdminString,
    cfprSysdebugCoreFsmStageDescrData                                SnmpAdminString,
    cfprSysdebugCoreFsmStageLastUpdateTime                           DateAndTime,
    cfprSysdebugCoreFsmStageName                                     CfprSysdebugCoreFsmStageName,
    cfprSysdebugCoreFsmStageOrder                                    Gauge32,
    cfprSysdebugCoreFsmStageRetry                                    Gauge32,
    cfprSysdebugCoreFsmStageStageStatus                              CfprFsmFsmStageStatus
}

cfprSysdebugCoreFsmStageInstanceId OBJECT-TYPE
    SYNTAX       CfprManagedObjectId
    MAX-ACCESS   not-accessible
    STATUS       current
    DESCRIPTION
        "Instance identifier of the managed object."
    ::= { cfprSysdebugCoreFsmStageEntry 1 }

cfprSysdebugCoreFsmStageDn OBJECT-TYPE
    SYNTAX       CfprManagedObjectDn
    MAX-ACCESS   read-only
    STATUS       current
    DESCRIPTION
        "Cisco Firepower sysdebug:CoreFsmStage:dn managed object property"
    ::= { cfprSysdebugCoreFsmStageEntry 2 }

cfprSysdebugCoreFsmStageRn OBJECT-TYPE
    SYNTAX       SnmpAdminString
    MAX-ACCESS   read-only
    STATUS       current
    DESCRIPTION
        "Cisco Firepower sysdebug:CoreFsmStage:rn managed object property"
    ::= { cfprSysdebugCoreFsmStageEntry 3 }

cfprSysdebugCoreFsmStageDescrData OBJECT-TYPE
    SYNTAX       SnmpAdminString
    MAX-ACCESS   read-only
    STATUS       current
    DESCRIPTION
        "Cisco Firepower sysdebug:CoreFsmStage:descr managed
        object property"
    ::= { cfprSysdebugCoreFsmStageEntry 4 }

cfprSysdebugCoreFsmStageLastUpdateTime OBJECT-TYPE
    SYNTAX       DateAndTime
    MAX-ACCESS   read-only
    STATUS       current
    DESCRIPTION
        "Cisco Firepower sysdebug:CoreFsmStage:lastUpdateTime
        managed object property"
    ::= { cfprSysdebugCoreFsmStageEntry 5 }

cfprSysdebugCoreFsmStageName OBJECT-TYPE
    SYNTAX       CfprSysdebugCoreFsmStageName
    MAX-ACCESS   read-only
    STATUS       current
    DESCRIPTION
        "Cisco Firepower sysdebug:CoreFsmStage:name managed
        object property"
    ::= { cfprSysdebugCoreFsmStageEntry 6 }

cfprSysdebugCoreFsmStageOrder OBJECT-TYPE
    SYNTAX       Gauge32
    MAX-ACCESS   read-only
    STATUS       current
    DESCRIPTION
        "Cisco Firepower sysdebug:CoreFsmStage:order managed
        object property"
    ::= { cfprSysdebugCoreFsmStageEntry 7 }

cfprSysdebugCoreFsmStageRetry OBJECT-TYPE
    SYNTAX       Gauge32
    MAX-ACCESS   read-only
    STATUS       current
    DESCRIPTION
        "Cisco Firepower sysdebug:CoreFsmStage:retry managed
        object property"
    ::= { cfprSysdebugCoreFsmStageEntry 8 }

cfprSysdebugCoreFsmStageStageStatus OBJECT-TYPE
    SYNTAX       CfprFsmFsmStageStatus
    MAX-ACCESS   read-only
    STATUS       current
    DESCRIPTION
        "Cisco Firepower sysdebug:CoreFsmStage:stageStatus
        managed object property"
    ::= { cfprSysdebugCoreFsmStageEntry 9 }

cfprSysdebugCoreFsmTaskTable OBJECT-TYPE
    SYNTAX           SEQUENCE OF CfprSysdebugCoreFsmTaskEntry
    MAX-ACCESS       not-accessible
    STATUS           current
    DESCRIPTION
        "Cisco Firepower sysdebug:CoreFsmTask managed object table"
    ::= { cfprSysdebugObjects 10 }

cfprSysdebugCoreFsmTaskEntry OBJECT-TYPE
    SYNTAX           CfprSysdebugCoreFsmTaskEntry
    MAX-ACCESS       not-accessible
    STATUS           current
    DESCRIPTION
        "Entry for the cfprSysdebugCoreFsmTaskTable table."
    INDEX { cfprSysdebugCoreFsmTaskInstanceId }
    ::= { cfprSysdebugCoreFsmTaskTable 1 }

CfprSysdebugCoreFsmTaskEntry ::= SEQUENCE {
    cfprSysdebugCoreFsmTaskInstanceId                                CfprManagedObjectId,
    cfprSysdebugCoreFsmTaskDn                                        CfprManagedObjectDn,
    cfprSysdebugCoreFsmTaskRn                                        SnmpAdminString,
    cfprSysdebugCoreFsmTaskCompletion                                CfprFsmCompletion,
    cfprSysdebugCoreFsmTaskFlags                                     CfprFsmFlags,
    cfprSysdebugCoreFsmTaskItem                                      CfprSysdebugCoreFsmTaskItem,
    cfprSysdebugCoreFsmTaskSeqId                                     Gauge32
}

cfprSysdebugCoreFsmTaskInstanceId OBJECT-TYPE
    SYNTAX       CfprManagedObjectId
    MAX-ACCESS   not-accessible
    STATUS       current
    DESCRIPTION
        "Instance identifier of the managed object."
    ::= { cfprSysdebugCoreFsmTaskEntry 1 }

cfprSysdebugCoreFsmTaskDn OBJECT-TYPE
    SYNTAX       CfprManagedObjectDn
    MAX-ACCESS   read-only
    STATUS       current
    DESCRIPTION
        "Cisco Firepower sysdebug:CoreFsmTask:dn managed object property"
    ::= { cfprSysdebugCoreFsmTaskEntry 2 }

cfprSysdebugCoreFsmTaskRn OBJECT-TYPE
    SYNTAX       SnmpAdminString
    MAX-ACCESS   read-only
    STATUS       current
    DESCRIPTION
        "Cisco Firepower sysdebug:CoreFsmTask:rn managed object property"
    ::= { cfprSysdebugCoreFsmTaskEntry 3 }

cfprSysdebugCoreFsmTaskCompletion OBJECT-TYPE
    SYNTAX       CfprFsmCompletion
    MAX-ACCESS   read-only
    STATUS       current
    DESCRIPTION
        "Cisco Firepower sysdebug:CoreFsmTask:completion
        managed object property"
    ::= { cfprSysdebugCoreFsmTaskEntry 4 }

cfprSysdebugCoreFsmTaskFlags OBJECT-TYPE
    SYNTAX       CfprFsmFlags
    MAX-ACCESS   read-only
    STATUS       current
    DESCRIPTION
        "Cisco Firepower sysdebug:CoreFsmTask:flags managed
        object property"
    ::= { cfprSysdebugCoreFsmTaskEntry 5 }

cfprSysdebugCoreFsmTaskItem OBJECT-TYPE
    SYNTAX       CfprSysdebugCoreFsmTaskItem
    MAX-ACCESS   read-only
    STATUS       current
    DESCRIPTION
        "Cisco Firepower sysdebug:CoreFsmTask:item managed
        object property"
    ::= { cfprSysdebugCoreFsmTaskEntry 6 }

cfprSysdebugCoreFsmTaskSeqId OBJECT-TYPE
    SYNTAX       Gauge32
    MAX-ACCESS   read-only
    STATUS       current
    DESCRIPTION
        "Cisco Firepower sysdebug:CoreFsmTask:seqId managed
        object property"
    ::= { cfprSysdebugCoreFsmTaskEntry 7 }

cfprSysdebugEpTable OBJECT-TYPE
    SYNTAX           SEQUENCE OF CfprSysdebugEpEntry
    MAX-ACCESS       not-accessible
    STATUS           current
    DESCRIPTION
        "Cisco Firepower sysdebug:Ep managed object table"
    ::= { cfprSysdebugObjects 11 }

cfprSysdebugEpEntry OBJECT-TYPE
    SYNTAX           CfprSysdebugEpEntry
    MAX-ACCESS       not-accessible
    STATUS           current
    DESCRIPTION
        "Entry for the cfprSysdebugEpTable table."
    INDEX { cfprSysdebugEpInstanceId }
    ::= { cfprSysdebugEpTable 1 }

CfprSysdebugEpEntry ::= SEQUENCE {
    cfprSysdebugEpInstanceId                                         CfprManagedObjectId,
    cfprSysdebugEpDn                                                 CfprManagedObjectDn,
    cfprSysdebugEpRn                                                 SnmpAdminString
}

cfprSysdebugEpInstanceId OBJECT-TYPE
    SYNTAX       CfprManagedObjectId
    MAX-ACCESS   not-accessible
    STATUS       current
    DESCRIPTION
        "Instance identifier of the managed object."
    ::= { cfprSysdebugEpEntry 1 }

cfprSysdebugEpDn OBJECT-TYPE
    SYNTAX       CfprManagedObjectDn
    MAX-ACCESS   read-only
    STATUS       current
    DESCRIPTION
        "Cisco Firepower sysdebug:Ep:dn managed object property"
    ::= { cfprSysdebugEpEntry 2 }

cfprSysdebugEpRn OBJECT-TYPE
    SYNTAX       SnmpAdminString
    MAX-ACCESS   read-only
    STATUS       current
    DESCRIPTION
        "Cisco Firepower sysdebug:Ep:rn managed object property"
    ::= { cfprSysdebugEpEntry 3 }

cfprSysdebugLogControlDestinationFileTable OBJECT-TYPE
    SYNTAX           SEQUENCE OF CfprSysdebugLogControlDestinationFileEntry
    MAX-ACCESS       not-accessible
    STATUS           current
    DESCRIPTION
        "Cisco Firepower sysdebug:LogControlDestinationFile
        managed object table"
    ::= { cfprSysdebugObjects 12 }

cfprSysdebugLogControlDestinationFileEntry OBJECT-TYPE
    SYNTAX           CfprSysdebugLogControlDestinationFileEntry
    MAX-ACCESS       not-accessible
    STATUS           current
    DESCRIPTION
        "Entry for the cfprSysdebugLogControlDestinationFileTable table."
    INDEX { cfprSysdebugLogControlDestinationFileInstanceId }
    ::= { cfprSysdebugLogControlDestinationFileTable 1 }

CfprSysdebugLogControlDestinationFileEntry ::= SEQUENCE {
    cfprSysdebugLogControlDestinationFileInstanceId                  CfprManagedObjectId,
    cfprSysdebugLogControlDestinationFileDn                          CfprManagedObjectDn,
    cfprSysdebugLogControlDestinationFileRn                          SnmpAdminString,
    cfprSysdebugLogControlDestinationFileBackupCount                 Gauge32,
    cfprSysdebugLogControlDestinationFileDefaultLevel                CfprSysdebugLogControlLevel,
    cfprSysdebugLogControlDestinationFileDefaultSize                 Gauge32,
    cfprSysdebugLogControlDestinationFileLevel                       CfprSysdebugLogControlLevel,
    cfprSysdebugLogControlDestinationFileSize                        Gauge32
}

cfprSysdebugLogControlDestinationFileInstanceId OBJECT-TYPE
    SYNTAX       CfprManagedObjectId
    MAX-ACCESS   not-accessible
    STATUS       current
    DESCRIPTION
        "Instance identifier of the managed object."
    ::= { cfprSysdebugLogControlDestinationFileEntry 1 }

cfprSysdebugLogControlDestinationFileDn OBJECT-TYPE
    SYNTAX       CfprManagedObjectDn
    MAX-ACCESS   read-only
    STATUS       current
    DESCRIPTION
        "Cisco Firepower sysdebug:LogControlDestinationFile:dn
        managed object property"
    ::= { cfprSysdebugLogControlDestinationFileEntry 2 }

cfprSysdebugLogControlDestinationFileRn OBJECT-TYPE
    SYNTAX       SnmpAdminString
    MAX-ACCESS   read-only
    STATUS       current
    DESCRIPTION
        "Cisco Firepower sysdebug:LogControlDestinationFile:rn
        managed object property"
    ::= { cfprSysdebugLogControlDestinationFileEntry 3 }

cfprSysdebugLogControlDestinationFileBackupCount OBJECT-TYPE
    SYNTAX       Gauge32
    MAX-ACCESS   read-only
    STATUS       current
    DESCRIPTION
        "Cisco Firepower sysdebug:LogControlDestinationFile:backupCount
        managed object property"
    ::= { cfprSysdebugLogControlDestinationFileEntry 4 }

cfprSysdebugLogControlDestinationFileDefaultLevel OBJECT-TYPE
    SYNTAX       CfprSysdebugLogControlLevel
    MAX-ACCESS   read-only
    STATUS       current
    DESCRIPTION
        "Cisco Firepower sysdebug:LogControlDestinationFile:defaultLevel
        managed object property"
    ::= { cfprSysdebugLogControlDestinationFileEntry 5 }

cfprSysdebugLogControlDestinationFileDefaultSize OBJECT-TYPE
    SYNTAX       Gauge32
    MAX-ACCESS   read-only
    STATUS       current
    DESCRIPTION
        "Cisco Firepower sysdebug:LogControlDestinationFile:defaultSize
        managed object property"
    ::= { cfprSysdebugLogControlDestinationFileEntry 6 }

cfprSysdebugLogControlDestinationFileLevel OBJECT-TYPE
    SYNTAX       CfprSysdebugLogControlLevel
    MAX-ACCESS   read-only
    STATUS       current
    DESCRIPTION
        "Cisco Firepower sysdebug:LogControlDestinationFile:level
        managed object property"
    ::= { cfprSysdebugLogControlDestinationFileEntry 7 }

cfprSysdebugLogControlDestinationFileSize OBJECT-TYPE
    SYNTAX       Gauge32
    MAX-ACCESS   read-only
    STATUS       current
    DESCRIPTION
        "Cisco Firepower sysdebug:LogControlDestinationFile:size
        managed object property"
    ::= { cfprSysdebugLogControlDestinationFileEntry 8 }

cfprSysdebugLogControlDestinationSyslogTable OBJECT-TYPE
    SYNTAX           SEQUENCE OF CfprSysdebugLogControlDestinationSyslogEntry
    MAX-ACCESS       not-accessible
    STATUS           current
    DESCRIPTION
        "Cisco Firepower sysdebug:LogControlDestinationSyslog
        managed object table"
    ::= { cfprSysdebugObjects 13 }

cfprSysdebugLogControlDestinationSyslogEntry OBJECT-TYPE
    SYNTAX           CfprSysdebugLogControlDestinationSyslogEntry
    MAX-ACCESS       not-accessible
    STATUS           current
    DESCRIPTION
        "Entry for the cfprSysdebugLogControlDestinationSyslogTable table."
    INDEX { cfprSysdebugLogControlDestinationSyslogInstanceId }
    ::= { cfprSysdebugLogControlDestinationSyslogTable 1 }

CfprSysdebugLogControlDestinationSyslogEntry ::= SEQUENCE {
    cfprSysdebugLogControlDestinationSyslogInstanceId                CfprManagedObjectId,
    cfprSysdebugLogControlDestinationSyslogDn                        CfprManagedObjectDn,
    cfprSysdebugLogControlDestinationSyslogRn                        SnmpAdminString,
    cfprSysdebugLogControlDestinationSyslogDefaultLevel              CfprSysdebugLogControlLevel,
    cfprSysdebugLogControlDestinationSyslogLevel                     CfprSysdebugLogControlLevel
}

cfprSysdebugLogControlDestinationSyslogInstanceId OBJECT-TYPE
    SYNTAX       CfprManagedObjectId
    MAX-ACCESS   not-accessible
    STATUS       current
    DESCRIPTION
        "Instance identifier of the managed object."
    ::= { cfprSysdebugLogControlDestinationSyslogEntry 1 }

cfprSysdebugLogControlDestinationSyslogDn OBJECT-TYPE
    SYNTAX       CfprManagedObjectDn
    MAX-ACCESS   read-only
    STATUS       current
    DESCRIPTION
        "Cisco Firepower sysdebug:LogControlDestinationSyslog:dn
        managed object property"
    ::= { cfprSysdebugLogControlDestinationSyslogEntry 2 }

cfprSysdebugLogControlDestinationSyslogRn OBJECT-TYPE
    SYNTAX       SnmpAdminString
    MAX-ACCESS   read-only
    STATUS       current
    DESCRIPTION
        "Cisco Firepower sysdebug:LogControlDestinationSyslog:rn
        managed object property"
    ::= { cfprSysdebugLogControlDestinationSyslogEntry 3 }

cfprSysdebugLogControlDestinationSyslogDefaultLevel OBJECT-TYPE
    SYNTAX       CfprSysdebugLogControlLevel
    MAX-ACCESS   read-only
    STATUS       current
    DESCRIPTION
        "Cisco Firepower sysdebug:LogControlDestinationSyslog:defaultLevel
         managed object property"
    ::= { cfprSysdebugLogControlDestinationSyslogEntry 4 }

cfprSysdebugLogControlDestinationSyslogLevel OBJECT-TYPE
    SYNTAX       CfprSysdebugLogControlLevel
    MAX-ACCESS   read-only
    STATUS       current
    DESCRIPTION
        "Cisco Firepower sysdebug:LogControlDestinationSyslog:level
        managed object property"
    ::= { cfprSysdebugLogControlDestinationSyslogEntry 5 }

cfprSysdebugLogControlDomainTable OBJECT-TYPE
    SYNTAX           SEQUENCE OF CfprSysdebugLogControlDomainEntry
    MAX-ACCESS       not-accessible
    STATUS           current
    DESCRIPTION
        "Cisco Firepower sysdebug:LogControlDomain managed object table"
    ::= { cfprSysdebugObjects 14 }

cfprSysdebugLogControlDomainEntry OBJECT-TYPE
    SYNTAX           CfprSysdebugLogControlDomainEntry
    MAX-ACCESS       not-accessible
    STATUS           current
    DESCRIPTION
        "Entry for the cfprSysdebugLogControlDomainTable table."
    INDEX { cfprSysdebugLogControlDomainInstanceId }
    ::= { cfprSysdebugLogControlDomainTable 1 }

CfprSysdebugLogControlDomainEntry ::= SEQUENCE {
    cfprSysdebugLogControlDomainInstanceId                           CfprManagedObjectId,
    cfprSysdebugLogControlDomainDn                                   CfprManagedObjectDn,
    cfprSysdebugLogControlDomainRn                                   SnmpAdminString,
    cfprSysdebugLogControlDomainLevel                                CfprSysdebugLogControlLevel,
    cfprSysdebugLogControlDomainLevelFlag                            TruthValue,
    cfprSysdebugLogControlDomainName                                 CfprSysdebugLogControlDomainEnum,
    cfprSysdebugLogControlDomainPersist                              TruthValue,
    cfprSysdebugLogControlDomainReset                                TruthValue
}

cfprSysdebugLogControlDomainInstanceId OBJECT-TYPE
    SYNTAX       CfprManagedObjectId
    MAX-ACCESS   not-accessible
    STATUS       current
    DESCRIPTION
        "Instance identifier of the managed object."
    ::= { cfprSysdebugLogControlDomainEntry 1 }

cfprSysdebugLogControlDomainDn OBJECT-TYPE
    SYNTAX       CfprManagedObjectDn
    MAX-ACCESS   read-only
    STATUS       current
    DESCRIPTION
        "Cisco Firepower sysdebug:LogControlDomain:dn managed
        object property"
    ::= { cfprSysdebugLogControlDomainEntry 2 }

cfprSysdebugLogControlDomainRn OBJECT-TYPE
    SYNTAX       SnmpAdminString
    MAX-ACCESS   read-only
    STATUS       current
    DESCRIPTION
        "Cisco Firepower sysdebug:LogControlDomain:rn managed
        object property"
    ::= { cfprSysdebugLogControlDomainEntry 3 }

cfprSysdebugLogControlDomainLevel OBJECT-TYPE
    SYNTAX       CfprSysdebugLogControlLevel
    MAX-ACCESS   read-only
    STATUS       current
    DESCRIPTION
        "Cisco Firepower sysdebug:LogControlDomain:level
        managed object property"
    ::= { cfprSysdebugLogControlDomainEntry 4 }

cfprSysdebugLogControlDomainLevelFlag OBJECT-TYPE
    SYNTAX       TruthValue
    MAX-ACCESS   read-only
    STATUS       current
    DESCRIPTION
        "Cisco Firepower sysdebug:LogControlDomain:levelFlag
        managed object property"
    ::= { cfprSysdebugLogControlDomainEntry 5 }

cfprSysdebugLogControlDomainName OBJECT-TYPE
    SYNTAX       CfprSysdebugLogControlDomainEnum
    MAX-ACCESS   read-only
    STATUS       current
    DESCRIPTION
        "Cisco Firepower sysdebug:LogControlDomain:name
        managed object property"
    ::= { cfprSysdebugLogControlDomainEntry 6 }

cfprSysdebugLogControlDomainPersist OBJECT-TYPE
    SYNTAX       TruthValue
    MAX-ACCESS   read-only
    STATUS       current
    DESCRIPTION
        "Cisco Firepower sysdebug:LogControlDomain:persist
        managed object property"
    ::= { cfprSysdebugLogControlDomainEntry 7 }

cfprSysdebugLogControlDomainReset OBJECT-TYPE
    SYNTAX       TruthValue
    MAX-ACCESS   read-only
    STATUS       current
    DESCRIPTION
        "Cisco Firepower sysdebug:LogControlDomain:reset
        managed object property"
    ::= { cfprSysdebugLogControlDomainEntry 8 }

cfprSysdebugLogControlEpTable OBJECT-TYPE
    SYNTAX           SEQUENCE OF CfprSysdebugLogControlEpEntry
    MAX-ACCESS       not-accessible
    STATUS           current
    DESCRIPTION
        "Cisco Firepower sysdebug:LogControlEp managed object table"
    ::= { cfprSysdebugObjects 15 }

cfprSysdebugLogControlEpEntry OBJECT-TYPE
    SYNTAX           CfprSysdebugLogControlEpEntry
    MAX-ACCESS       not-accessible
    STATUS           current
    DESCRIPTION
        "Entry for the cfprSysdebugLogControlEpTable table."
    INDEX { cfprSysdebugLogControlEpInstanceId }
    ::= { cfprSysdebugLogControlEpTable 1 }

CfprSysdebugLogControlEpEntry ::= SEQUENCE {
    cfprSysdebugLogControlEpInstanceId                               CfprManagedObjectId,
    cfprSysdebugLogControlEpDn                                       CfprManagedObjectDn,
    cfprSysdebugLogControlEpRn                                       SnmpAdminString,
    cfprSysdebugLogControlEpFsmDescr                                 SnmpAdminString,
    cfprSysdebugLogControlEpFsmPrev                                  SnmpAdminString,
    cfprSysdebugLogControlEpFsmProgr                                 Gauge32,
    cfprSysdebugLogControlEpFsmRmtInvErrCode                         Gauge32,
    cfprSysdebugLogControlEpFsmRmtInvErrDescr                        SnmpAdminString,
    cfprSysdebugLogControlEpFsmRmtInvRslt                            CfprConditionRemoteInvRslt,
    cfprSysdebugLogControlEpFsmStageDescr                            SnmpAdminString,
    cfprSysdebugLogControlEpFsmStamp                                 DateAndTime,
    cfprSysdebugLogControlEpFsmStatus                                SnmpAdminString,
    cfprSysdebugLogControlEpFsmTry                                   Gauge32,
    cfprSysdebugLogControlEpLevel                                    CfprSysdebugLogControlLevel,
    cfprSysdebugLogControlEpLevelFlag                                TruthValue,
    cfprSysdebugLogControlEpPersist                                  TruthValue,
    cfprSysdebugLogControlEpReset                                    TruthValue
}

cfprSysdebugLogControlEpInstanceId OBJECT-TYPE
    SYNTAX       CfprManagedObjectId
    MAX-ACCESS   not-accessible
    STATUS       current
    DESCRIPTION
        "Instance identifier of the managed object."
    ::= { cfprSysdebugLogControlEpEntry 1 }

cfprSysdebugLogControlEpDn OBJECT-TYPE
    SYNTAX       CfprManagedObjectDn
    MAX-ACCESS   read-only
    STATUS       current
    DESCRIPTION
        "Cisco Firepower sysdebug:LogControlEp:dn managed object property"
    ::= { cfprSysdebugLogControlEpEntry 2 }

cfprSysdebugLogControlEpRn OBJECT-TYPE
    SYNTAX       SnmpAdminString
    MAX-ACCESS   read-only
    STATUS       current
    DESCRIPTION
        "Cisco Firepower sysdebug:LogControlEp:rn managed object property"
    ::= { cfprSysdebugLogControlEpEntry 3 }

cfprSysdebugLogControlEpFsmDescr OBJECT-TYPE
    SYNTAX       SnmpAdminString
    MAX-ACCESS   read-only
    STATUS       current
    DESCRIPTION
        "Cisco Firepower sysdebug:LogControlEp:fsmDescr
        managed object property"
    ::= { cfprSysdebugLogControlEpEntry 4 }

cfprSysdebugLogControlEpFsmPrev OBJECT-TYPE
    SYNTAX       SnmpAdminString
    MAX-ACCESS   read-only
    STATUS       current
    DESCRIPTION
        "Cisco Firepower sysdebug:LogControlEp:fsmPrev
        managed object property"
    ::= { cfprSysdebugLogControlEpEntry 5 }

cfprSysdebugLogControlEpFsmProgr OBJECT-TYPE
    SYNTAX       Gauge32
    MAX-ACCESS   read-only
    STATUS       current
    DESCRIPTION
        "Cisco Firepower sysdebug:LogControlEp:fsmProgr
        managed object property"
    ::= { cfprSysdebugLogControlEpEntry 6 }

cfprSysdebugLogControlEpFsmRmtInvErrCode OBJECT-TYPE
    SYNTAX       Gauge32
    MAX-ACCESS   read-only
    STATUS       current
    DESCRIPTION
        "Cisco Firepower sysdebug:LogControlEp:fsmRmtInvErrCode
        managed object property"
    ::= { cfprSysdebugLogControlEpEntry 7 }

cfprSysdebugLogControlEpFsmRmtInvErrDescr OBJECT-TYPE
    SYNTAX       SnmpAdminString
    MAX-ACCESS   read-only
    STATUS       current
    DESCRIPTION
        "Cisco Firepower sysdebug:LogControlEp:fsmRmtInvErrDescr
        managed object property"
    ::= { cfprSysdebugLogControlEpEntry 8 }

cfprSysdebugLogControlEpFsmRmtInvRslt OBJECT-TYPE
    SYNTAX       CfprConditionRemoteInvRslt
    MAX-ACCESS   read-only
    STATUS       current
    DESCRIPTION
        "Cisco Firepower sysdebug:LogControlEp:fsmRmtInvRslt
        managed object property"
    ::= { cfprSysdebugLogControlEpEntry 9 }

cfprSysdebugLogControlEpFsmStageDescr OBJECT-TYPE
    SYNTAX       SnmpAdminString
    MAX-ACCESS   read-only
    STATUS       current
    DESCRIPTION
        "Cisco Firepower sysdebug:LogControlEp:fsmStageDescr
        managed object property"
    ::= { cfprSysdebugLogControlEpEntry 10 }

cfprSysdebugLogControlEpFsmStamp OBJECT-TYPE
    SYNTAX       DateAndTime
    MAX-ACCESS   read-only
    STATUS       current
    DESCRIPTION
        "Cisco Firepower sysdebug:LogControlEp:fsmStamp
        managed object property"
    ::= { cfprSysdebugLogControlEpEntry 11 }

cfprSysdebugLogControlEpFsmStatus OBJECT-TYPE
    SYNTAX       SnmpAdminString
    MAX-ACCESS   read-only
    STATUS       current
    DESCRIPTION
        "Cisco Firepower sysdebug:LogControlEp:fsmStatus
        managed object property"
    ::= { cfprSysdebugLogControlEpEntry 12 }

cfprSysdebugLogControlEpFsmTry OBJECT-TYPE
    SYNTAX       Gauge32
    MAX-ACCESS   read-only
    STATUS       current
    DESCRIPTION
        "Cisco Firepower sysdebug:LogControlEp:fsmTry managed
        object property"
    ::= { cfprSysdebugLogControlEpEntry 13 }

cfprSysdebugLogControlEpLevel OBJECT-TYPE
    SYNTAX       CfprSysdebugLogControlLevel
    MAX-ACCESS   read-only
    STATUS       current
    DESCRIPTION
        "Cisco Firepower sysdebug:LogControlEp:level managed
        object property"
    ::= { cfprSysdebugLogControlEpEntry 14 }

cfprSysdebugLogControlEpLevelFlag OBJECT-TYPE
    SYNTAX       TruthValue
    MAX-ACCESS   read-only
    STATUS       current
    DESCRIPTION
        "Cisco Firepower sysdebug:LogControlEp:levelFlag
        managed object property"
    ::= { cfprSysdebugLogControlEpEntry 15 }

cfprSysdebugLogControlEpPersist OBJECT-TYPE
    SYNTAX       TruthValue
    MAX-ACCESS   read-only
    STATUS       current
    DESCRIPTION
        "Cisco Firepower sysdebug:LogControlEp:persist
        managed object property"
    ::= { cfprSysdebugLogControlEpEntry 16 }

cfprSysdebugLogControlEpReset OBJECT-TYPE
    SYNTAX       TruthValue
    MAX-ACCESS   read-only
    STATUS       current
    DESCRIPTION
        "Cisco Firepower sysdebug:LogControlEp:reset managed
        object property"
    ::= { cfprSysdebugLogControlEpEntry 17 }

cfprSysdebugLogControlEpFsmTable OBJECT-TYPE
    SYNTAX           SEQUENCE OF CfprSysdebugLogControlEpFsmEntry
    MAX-ACCESS       not-accessible
    STATUS           current
    DESCRIPTION
        "Cisco Firepower sysdebug:LogControlEpFsm managed object table"
    ::= { cfprSysdebugObjects 16 }

cfprSysdebugLogControlEpFsmEntry OBJECT-TYPE
    SYNTAX           CfprSysdebugLogControlEpFsmEntry
    MAX-ACCESS       not-accessible
    STATUS           current
    DESCRIPTION
        "Entry for the cfprSysdebugLogControlEpFsmTable table."
    INDEX { cfprSysdebugLogControlEpFsmInstanceId }
    ::= { cfprSysdebugLogControlEpFsmTable 1 }

CfprSysdebugLogControlEpFsmEntry ::= SEQUENCE {
    cfprSysdebugLogControlEpFsmInstanceId                            CfprManagedObjectId,
    cfprSysdebugLogControlEpFsmDn                                    CfprManagedObjectDn,
    cfprSysdebugLogControlEpFsmRn                                    SnmpAdminString,
    cfprSysdebugLogControlEpFsmCompletionTime                        DateAndTime,
    cfprSysdebugLogControlEpFsmCurrentFsm                            CfprSysdebugLogControlEpFsmCurrentFsm,
    cfprSysdebugLogControlEpFsmDescrData                             SnmpAdminString,
    cfprSysdebugLogControlEpFsmFsmStatus                             CfprFsmFsmStageStatus,
    cfprSysdebugLogControlEpFsmProgress                              Gauge32,
    cfprSysdebugLogControlEpFsmRmtErrCode                            Gauge32,
    cfprSysdebugLogControlEpFsmRmtErrDescr                           SnmpAdminString,
    cfprSysdebugLogControlEpFsmRmtRslt                               CfprConditionRemoteInvRslt
}

cfprSysdebugLogControlEpFsmInstanceId OBJECT-TYPE
    SYNTAX       CfprManagedObjectId
    MAX-ACCESS   not-accessible
    STATUS       current
    DESCRIPTION
        "Instance identifier of the managed object."
    ::= { cfprSysdebugLogControlEpFsmEntry 1 }

cfprSysdebugLogControlEpFsmDn OBJECT-TYPE
    SYNTAX       CfprManagedObjectDn
    MAX-ACCESS   read-only
    STATUS       current
    DESCRIPTION
        "Cisco Firepower sysdebug:LogControlEpFsm:dn managed
        object property"
    ::= { cfprSysdebugLogControlEpFsmEntry 2 }

cfprSysdebugLogControlEpFsmRn OBJECT-TYPE
    SYNTAX       SnmpAdminString
    MAX-ACCESS   read-only
    STATUS       current
    DESCRIPTION
        "Cisco Firepower sysdebug:LogControlEpFsm:rn managed
        object property"
    ::= { cfprSysdebugLogControlEpFsmEntry 3 }

cfprSysdebugLogControlEpFsmCompletionTime OBJECT-TYPE
    SYNTAX       DateAndTime
    MAX-ACCESS   read-only
    STATUS       current
    DESCRIPTION
        "Cisco Firepower sysdebug:LogControlEpFsm:completionTime
        managed object property"
    ::= { cfprSysdebugLogControlEpFsmEntry 4 }

cfprSysdebugLogControlEpFsmCurrentFsm OBJECT-TYPE
    SYNTAX       CfprSysdebugLogControlEpFsmCurrentFsm
    MAX-ACCESS   read-only
    STATUS       current
    DESCRIPTION
        "Cisco Firepower sysdebug:LogControlEpFsm:currentFsm
        managed object property"
    ::= { cfprSysdebugLogControlEpFsmEntry 5 }

cfprSysdebugLogControlEpFsmDescrData OBJECT-TYPE
    SYNTAX       SnmpAdminString
    MAX-ACCESS   read-only
    STATUS       current
    DESCRIPTION
        "Cisco Firepower sysdebug:LogControlEpFsm:descr
        managed object property"
    ::= { cfprSysdebugLogControlEpFsmEntry 6 }

cfprSysdebugLogControlEpFsmFsmStatus OBJECT-TYPE
    SYNTAX       CfprFsmFsmStageStatus
    MAX-ACCESS   read-only
    STATUS       current
    DESCRIPTION
        "Cisco Firepower sysdebug:LogControlEpFsm:fsmStatus
        managed object property"
    ::= { cfprSysdebugLogControlEpFsmEntry 7 }

cfprSysdebugLogControlEpFsmProgress OBJECT-TYPE
    SYNTAX       Gauge32
    MAX-ACCESS   read-only
    STATUS       current
    DESCRIPTION
        "Cisco Firepower sysdebug:LogControlEpFsm:progress
        managed object property"
    ::= { cfprSysdebugLogControlEpFsmEntry 8 }

cfprSysdebugLogControlEpFsmRmtErrCode OBJECT-TYPE
    SYNTAX       Gauge32
    MAX-ACCESS   read-only
    STATUS       current
    DESCRIPTION
        "Cisco Firepower sysdebug:LogControlEpFsm:rmtErrCode
        managed object property"
    ::= { cfprSysdebugLogControlEpFsmEntry 9 }

cfprSysdebugLogControlEpFsmRmtErrDescr OBJECT-TYPE
    SYNTAX       SnmpAdminString
    MAX-ACCESS   read-only
    STATUS       current
    DESCRIPTION
        "Cisco Firepower sysdebug:LogControlEpFsm:rmtErrDescr
        managed object property"
    ::= { cfprSysdebugLogControlEpFsmEntry 10 }

cfprSysdebugLogControlEpFsmRmtRslt OBJECT-TYPE
    SYNTAX       CfprConditionRemoteInvRslt
    MAX-ACCESS   read-only
    STATUS       current
    DESCRIPTION
        "Cisco Firepower sysdebug:LogControlEpFsm:rmtRslt
        managed object property"
    ::= { cfprSysdebugLogControlEpFsmEntry 11 }

cfprSysdebugLogControlEpFsmStageTable OBJECT-TYPE
    SYNTAX           SEQUENCE OF CfprSysdebugLogControlEpFsmStageEntry
    MAX-ACCESS       not-accessible
    STATUS           current
    DESCRIPTION
        "Cisco Firepower sysdebug:LogControlEpFsmStage
        managed object table"
    ::= { cfprSysdebugObjects 17 }

cfprSysdebugLogControlEpFsmStageEntry OBJECT-TYPE
    SYNTAX           CfprSysdebugLogControlEpFsmStageEntry
    MAX-ACCESS       not-accessible
    STATUS           current
    DESCRIPTION
        "Entry for the cfprSysdebugLogControlEpFsmStageTable table."
    INDEX { cfprSysdebugLogControlEpFsmStageInstanceId }
    ::= { cfprSysdebugLogControlEpFsmStageTable 1 }

CfprSysdebugLogControlEpFsmStageEntry ::= SEQUENCE {
    cfprSysdebugLogControlEpFsmStageInstanceId                       CfprManagedObjectId,
    cfprSysdebugLogControlEpFsmStageDn                               CfprManagedObjectDn,
    cfprSysdebugLogControlEpFsmStageRn                               SnmpAdminString,
    cfprSysdebugLogControlEpFsmStageDescrData                        SnmpAdminString,
    cfprSysdebugLogControlEpFsmStageLastUpdateTime                   DateAndTime,
    cfprSysdebugLogControlEpFsmStageName                             CfprSysdebugLogControlEpFsmStageName,
    cfprSysdebugLogControlEpFsmStageOrder                            Gauge32,
    cfprSysdebugLogControlEpFsmStageRetry                            Gauge32,
    cfprSysdebugLogControlEpFsmStageStageStatus                      CfprFsmFsmStageStatus
}

cfprSysdebugLogControlEpFsmStageInstanceId OBJECT-TYPE
    SYNTAX       CfprManagedObjectId
    MAX-ACCESS   not-accessible
    STATUS       current
    DESCRIPTION
        "Instance identifier of the managed object."
    ::= { cfprSysdebugLogControlEpFsmStageEntry 1 }

cfprSysdebugLogControlEpFsmStageDn OBJECT-TYPE
    SYNTAX       CfprManagedObjectDn
    MAX-ACCESS   read-only
    STATUS       current
    DESCRIPTION
        "Cisco Firepower sysdebug:LogControlEpFsmStage:dn
        managed object property"
    ::= { cfprSysdebugLogControlEpFsmStageEntry 2 }

cfprSysdebugLogControlEpFsmStageRn OBJECT-TYPE
    SYNTAX       SnmpAdminString
    MAX-ACCESS   read-only
    STATUS       current
    DESCRIPTION
        "Cisco Firepower sysdebug:LogControlEpFsmStage:rn
        managed object property"
    ::= { cfprSysdebugLogControlEpFsmStageEntry 3 }

cfprSysdebugLogControlEpFsmStageDescrData OBJECT-TYPE
    SYNTAX       SnmpAdminString
    MAX-ACCESS   read-only
    STATUS       current
    DESCRIPTION
        "Cisco Firepower sysdebug:LogControlEpFsmStage:descr
        managed object property"
    ::= { cfprSysdebugLogControlEpFsmStageEntry 4 }

cfprSysdebugLogControlEpFsmStageLastUpdateTime OBJECT-TYPE
    SYNTAX       DateAndTime
    MAX-ACCESS   read-only
    STATUS       current
    DESCRIPTION
        "Cisco Firepower sysdebug:LogControlEpFsmStage:lastUpdateTime
        managed object property"
    ::= { cfprSysdebugLogControlEpFsmStageEntry 5 }

cfprSysdebugLogControlEpFsmStageName OBJECT-TYPE
    SYNTAX       CfprSysdebugLogControlEpFsmStageName
    MAX-ACCESS   read-only
    STATUS       current
    DESCRIPTION
        "Cisco Firepower sysdebug:LogControlEpFsmStage:name
        managed object property"
    ::= { cfprSysdebugLogControlEpFsmStageEntry 6 }

cfprSysdebugLogControlEpFsmStageOrder OBJECT-TYPE
    SYNTAX       Gauge32
    MAX-ACCESS   read-only
    STATUS       current
    DESCRIPTION
        "Cisco Firepower sysdebug:LogControlEpFsmStage:order
        managed object property"
    ::= { cfprSysdebugLogControlEpFsmStageEntry 7 }

cfprSysdebugLogControlEpFsmStageRetry OBJECT-TYPE
    SYNTAX       Gauge32
    MAX-ACCESS   read-only
    STATUS       current
    DESCRIPTION
        "Cisco Firepower sysdebug:LogControlEpFsmStage:retry
        managed object property"
    ::= { cfprSysdebugLogControlEpFsmStageEntry 8 }

cfprSysdebugLogControlEpFsmStageStageStatus OBJECT-TYPE
    SYNTAX       CfprFsmFsmStageStatus
    MAX-ACCESS   read-only
    STATUS       current
    DESCRIPTION
        "Cisco Firepower sysdebug:LogControlEpFsmStage:stageStatus
        managed object property"
    ::= { cfprSysdebugLogControlEpFsmStageEntry 9 }

cfprSysdebugLogControlEpFsmTaskTable OBJECT-TYPE
    SYNTAX           SEQUENCE OF CfprSysdebugLogControlEpFsmTaskEntry
    MAX-ACCESS       not-accessible
    STATUS           current
    DESCRIPTION
        "Cisco Firepower sysdebug:LogControlEpFsmTask managed
        object table"
    ::= { cfprSysdebugObjects 18 }

cfprSysdebugLogControlEpFsmTaskEntry OBJECT-TYPE
    SYNTAX           CfprSysdebugLogControlEpFsmTaskEntry
    MAX-ACCESS       not-accessible
    STATUS           current
    DESCRIPTION
        "Entry for the cfprSysdebugLogControlEpFsmTaskTable table."
    INDEX { cfprSysdebugLogControlEpFsmTaskInstanceId }
    ::= { cfprSysdebugLogControlEpFsmTaskTable 1 }

CfprSysdebugLogControlEpFsmTaskEntry ::= SEQUENCE {
    cfprSysdebugLogControlEpFsmTaskInstanceId                        CfprManagedObjectId,
    cfprSysdebugLogControlEpFsmTaskDn                                CfprManagedObjectDn,
    cfprSysdebugLogControlEpFsmTaskRn                                SnmpAdminString,
    cfprSysdebugLogControlEpFsmTaskCompletion                        CfprFsmCompletion,
    cfprSysdebugLogControlEpFsmTaskFlags                             CfprFsmFlags,
    cfprSysdebugLogControlEpFsmTaskItem                              CfprSysdebugLogControlEpFsmTaskItem,
    cfprSysdebugLogControlEpFsmTaskSeqId                             Gauge32
}

cfprSysdebugLogControlEpFsmTaskInstanceId OBJECT-TYPE
    SYNTAX       CfprManagedObjectId
    MAX-ACCESS   not-accessible
    STATUS       current
    DESCRIPTION
        "Instance identifier of the managed object."
    ::= { cfprSysdebugLogControlEpFsmTaskEntry 1 }

cfprSysdebugLogControlEpFsmTaskDn OBJECT-TYPE
    SYNTAX       CfprManagedObjectDn
    MAX-ACCESS   read-only
    STATUS       current
    DESCRIPTION
        "Cisco Firepower sysdebug:LogControlEpFsmTask:dn
        managed object property"
    ::= { cfprSysdebugLogControlEpFsmTaskEntry 2 }

cfprSysdebugLogControlEpFsmTaskRn OBJECT-TYPE
    SYNTAX       SnmpAdminString
    MAX-ACCESS   read-only
    STATUS       current
    DESCRIPTION
        "Cisco Firepower sysdebug:LogControlEpFsmTask:rn
        managed object property"
    ::= { cfprSysdebugLogControlEpFsmTaskEntry 3 }

cfprSysdebugLogControlEpFsmTaskCompletion OBJECT-TYPE
    SYNTAX       CfprFsmCompletion
    MAX-ACCESS   read-only
    STATUS       current
    DESCRIPTION
        "Cisco Firepower sysdebug:LogControlEpFsmTask:completion
        managed object property"
    ::= { cfprSysdebugLogControlEpFsmTaskEntry 4 }

cfprSysdebugLogControlEpFsmTaskFlags OBJECT-TYPE
    SYNTAX       CfprFsmFlags
    MAX-ACCESS   read-only
    STATUS       current
    DESCRIPTION
        "Cisco Firepower sysdebug:LogControlEpFsmTask:flags
        managed object property"
    ::= { cfprSysdebugLogControlEpFsmTaskEntry 5 }

cfprSysdebugLogControlEpFsmTaskItem OBJECT-TYPE
    SYNTAX       CfprSysdebugLogControlEpFsmTaskItem
    MAX-ACCESS   read-only
    STATUS       current
    DESCRIPTION
        "Cisco Firepower sysdebug:LogControlEpFsmTask:item
        managed object property"
    ::= { cfprSysdebugLogControlEpFsmTaskEntry 6 }

cfprSysdebugLogControlEpFsmTaskSeqId OBJECT-TYPE
    SYNTAX       Gauge32
    MAX-ACCESS   read-only
    STATUS       current
    DESCRIPTION
        "Cisco Firepower sysdebug:LogControlEpFsmTask:seqId
        managed object property"
    ::= { cfprSysdebugLogControlEpFsmTaskEntry 7 }

cfprSysdebugLogControlModuleTable OBJECT-TYPE
    SYNTAX           SEQUENCE OF CfprSysdebugLogControlModuleEntry
    MAX-ACCESS       not-accessible
    STATUS           current
    DESCRIPTION
        "Cisco Firepower sysdebug:LogControlModule managed object table"
    ::= { cfprSysdebugObjects 19 }

cfprSysdebugLogControlModuleEntry OBJECT-TYPE
    SYNTAX           CfprSysdebugLogControlModuleEntry
    MAX-ACCESS       not-accessible
    STATUS           current
    DESCRIPTION
        "Entry for the cfprSysdebugLogControlModuleTable table."
    INDEX { cfprSysdebugLogControlModuleInstanceId }
    ::= { cfprSysdebugLogControlModuleTable 1 }

CfprSysdebugLogControlModuleEntry ::= SEQUENCE {
    cfprSysdebugLogControlModuleInstanceId                           CfprManagedObjectId,
    cfprSysdebugLogControlModuleDn                                   CfprManagedObjectDn,
    cfprSysdebugLogControlModuleRn                                   SnmpAdminString,
    cfprSysdebugLogControlModuleDefaultLevel                         CfprSysdebugLogControlLevel,
    cfprSysdebugLogControlModuleLevel                                CfprSysdebugLogControlLevel,
    cfprSysdebugLogControlModuleName                                 SnmpAdminString,
    cfprSysdebugLogControlModuleReset                                TruthValue
}

cfprSysdebugLogControlModuleInstanceId OBJECT-TYPE
    SYNTAX       CfprManagedObjectId
    MAX-ACCESS   not-accessible
    STATUS       current
    DESCRIPTION
        "Instance identifier of the managed object."
    ::= { cfprSysdebugLogControlModuleEntry 1 }

cfprSysdebugLogControlModuleDn OBJECT-TYPE
    SYNTAX       CfprManagedObjectDn
    MAX-ACCESS   read-only
    STATUS       current
    DESCRIPTION
        "Cisco Firepower sysdebug:LogControlModule:dn managed
        object property"
    ::= { cfprSysdebugLogControlModuleEntry 2 }

cfprSysdebugLogControlModuleRn OBJECT-TYPE
    SYNTAX       SnmpAdminString
    MAX-ACCESS   read-only
    STATUS       current
    DESCRIPTION
        "Cisco Firepower sysdebug:LogControlModule:rn managed
        object property"
    ::= { cfprSysdebugLogControlModuleEntry 3 }

cfprSysdebugLogControlModuleDefaultLevel OBJECT-TYPE
    SYNTAX       CfprSysdebugLogControlLevel
    MAX-ACCESS   read-only
    STATUS       current
    DESCRIPTION
        "Cisco Firepower sysdebug:LogControlModule:defaultLevel
        managed object property"
    ::= { cfprSysdebugLogControlModuleEntry 4 }

cfprSysdebugLogControlModuleLevel OBJECT-TYPE
    SYNTAX       CfprSysdebugLogControlLevel
    MAX-ACCESS   read-only
    STATUS       current
    DESCRIPTION
        "Cisco Firepower sysdebug:LogControlModule:level
        managed object property"
    ::= { cfprSysdebugLogControlModuleEntry 5 }

cfprSysdebugLogControlModuleName OBJECT-TYPE
    SYNTAX       SnmpAdminString
    MAX-ACCESS   read-only
    STATUS       current
    DESCRIPTION
        "Cisco Firepower sysdebug:LogControlModule:name
        managed object property"
    ::= { cfprSysdebugLogControlModuleEntry 6 }

cfprSysdebugLogControlModuleReset OBJECT-TYPE
    SYNTAX       TruthValue
    MAX-ACCESS   read-only
    STATUS       current
    DESCRIPTION
        "Cisco Firepower sysdebug:LogControlModule:reset
        managed object property"
    ::= { cfprSysdebugLogControlModuleEntry 7 }

cfprSysdebugLogExportPolicyTable OBJECT-TYPE
    SYNTAX           SEQUENCE OF CfprSysdebugLogExportPolicyEntry
    MAX-ACCESS       not-accessible
    STATUS           current
    DESCRIPTION
        "Cisco Firepower sysdebug:LogExportPolicy managed object table"
    ::= { cfprSysdebugObjects 20 }

cfprSysdebugLogExportPolicyEntry OBJECT-TYPE
    SYNTAX           CfprSysdebugLogExportPolicyEntry
    MAX-ACCESS       not-accessible
    STATUS           current
    DESCRIPTION
        "Entry for the cfprSysdebugLogExportPolicyTable table."
    INDEX { cfprSysdebugLogExportPolicyInstanceId }
    ::= { cfprSysdebugLogExportPolicyTable 1 }

CfprSysdebugLogExportPolicyEntry ::= SEQUENCE {
    cfprSysdebugLogExportPolicyInstanceId                            CfprManagedObjectId,
    cfprSysdebugLogExportPolicyDn                                    CfprManagedObjectDn,
    cfprSysdebugLogExportPolicyRn                                    SnmpAdminString,
    cfprSysdebugLogExportPolicyAdminState                            CfprCommClientAdminState,
    cfprSysdebugLogExportPolicyDescr                                 SnmpAdminString,
    cfprSysdebugLogExportPolicyFsmDescr                              SnmpAdminString,
    cfprSysdebugLogExportPolicyFsmPrev                               SnmpAdminString,
    cfprSysdebugLogExportPolicyFsmProgr                              Gauge32,
    cfprSysdebugLogExportPolicyFsmRmtInvErrCode                      Gauge32,
    cfprSysdebugLogExportPolicyFsmRmtInvErrDescr                     SnmpAdminString,
    cfprSysdebugLogExportPolicyFsmRmtInvRslt                         CfprConditionRemoteInvRslt,
    cfprSysdebugLogExportPolicyFsmStageDescr                         SnmpAdminString,
    cfprSysdebugLogExportPolicyFsmStamp                              DateAndTime,
    cfprSysdebugLogExportPolicyFsmStatus                             SnmpAdminString,
    cfprSysdebugLogExportPolicyFsmTry                                Gauge32,
    cfprSysdebugLogExportPolicyHostname                              SnmpAdminString,
    cfprSysdebugLogExportPolicyIntId                                 SnmpAdminString,
    cfprSysdebugLogExportPolicyName                                  SnmpAdminString,
    cfprSysdebugLogExportPolicyPasswordlessSsh                       TruthValue,
    cfprSysdebugLogExportPolicyPath                                  SnmpAdminString,
    cfprSysdebugLogExportPolicyPolicyLevel                           Gauge32,
    cfprSysdebugLogExportPolicyPolicyOwner                           CfprPolicyPolicyOwner,
    cfprSysdebugLogExportPolicyPostAction                            CfprSysfileExporterPostAction,
    cfprSysdebugLogExportPolicyProto                                 CfprSysdebugLogExportPolicyProto,
    cfprSysdebugLogExportPolicyPwd                                   SnmpAdminString,
    cfprSysdebugLogExportPolicyUser                                  SnmpAdminString
}

cfprSysdebugLogExportPolicyInstanceId OBJECT-TYPE
    SYNTAX       CfprManagedObjectId
    MAX-ACCESS   not-accessible
    STATUS       current
    DESCRIPTION
        "Instance identifier of the managed object."
    ::= { cfprSysdebugLogExportPolicyEntry 1 }

cfprSysdebugLogExportPolicyDn OBJECT-TYPE
    SYNTAX       CfprManagedObjectDn
    MAX-ACCESS   read-only
    STATUS       current
    DESCRIPTION
        "Cisco Firepower sysdebug:LogExportPolicy:dn managed
        object property"
    ::= { cfprSysdebugLogExportPolicyEntry 2 }

cfprSysdebugLogExportPolicyRn OBJECT-TYPE
    SYNTAX       SnmpAdminString
    MAX-ACCESS   read-only
    STATUS       current
    DESCRIPTION
        "Cisco Firepower sysdebug:LogExportPolicy:rn managed
        object property"
    ::= { cfprSysdebugLogExportPolicyEntry 3 }

cfprSysdebugLogExportPolicyAdminState OBJECT-TYPE
    SYNTAX       CfprCommClientAdminState
    MAX-ACCESS   read-only
    STATUS       current
    DESCRIPTION
        "Cisco Firepower sysdebug:LogExportPolicy:adminState
        managed object property"
    ::= { cfprSysdebugLogExportPolicyEntry 4 }

cfprSysdebugLogExportPolicyDescr OBJECT-TYPE
    SYNTAX       SnmpAdminString
    MAX-ACCESS   read-only
    STATUS       current
    DESCRIPTION
        "Cisco Firepower sysdebug:LogExportPolicy:descr
        managed object property"
    ::= { cfprSysdebugLogExportPolicyEntry 5 }

cfprSysdebugLogExportPolicyFsmDescr OBJECT-TYPE
    SYNTAX       SnmpAdminString
    MAX-ACCESS   read-only
    STATUS       current
    DESCRIPTION
        "Cisco Firepower sysdebug:LogExportPolicy:fsmDescr
        managed object property"
    ::= { cfprSysdebugLogExportPolicyEntry 6 }

cfprSysdebugLogExportPolicyFsmPrev OBJECT-TYPE
    SYNTAX       SnmpAdminString
    MAX-ACCESS   read-only
    STATUS       current
    DESCRIPTION
        "Cisco Firepower sysdebug:LogExportPolicy:fsmPrev
        managed object property"
    ::= { cfprSysdebugLogExportPolicyEntry 7 }

cfprSysdebugLogExportPolicyFsmProgr OBJECT-TYPE
    SYNTAX       Gauge32
    MAX-ACCESS   read-only
    STATUS       current
    DESCRIPTION
        "Cisco Firepower sysdebug:LogExportPolicy:fsmProgr
        managed object property"
    ::= { cfprSysdebugLogExportPolicyEntry 8 }

cfprSysdebugLogExportPolicyFsmRmtInvErrCode OBJECT-TYPE
    SYNTAX       Gauge32
    MAX-ACCESS   read-only
    STATUS       current
    DESCRIPTION
        "Cisco Firepower sysdebug:LogExportPolicy:fsmRmtInvErrCode
        managed object property"
    ::= { cfprSysdebugLogExportPolicyEntry 9 }

cfprSysdebugLogExportPolicyFsmRmtInvErrDescr OBJECT-TYPE
    SYNTAX       SnmpAdminString
    MAX-ACCESS   read-only
    STATUS       current
    DESCRIPTION
        "Cisco Firepower sysdebug:LogExportPolicy:fsmRmtInvErrDescr
        managed object property"
    ::= { cfprSysdebugLogExportPolicyEntry 10 }

cfprSysdebugLogExportPolicyFsmRmtInvRslt OBJECT-TYPE
    SYNTAX       CfprConditionRemoteInvRslt
    MAX-ACCESS   read-only
    STATUS       current
    DESCRIPTION
        "Cisco Firepower sysdebug:LogExportPolicy:fsmRmtInvRslt
        managed object property"
    ::= { cfprSysdebugLogExportPolicyEntry 11 }

cfprSysdebugLogExportPolicyFsmStageDescr OBJECT-TYPE
    SYNTAX       SnmpAdminString
    MAX-ACCESS   read-only
    STATUS       current
    DESCRIPTION
        "Cisco Firepower sysdebug:LogExportPolicy:fsmStageDescr
        managed object property"
    ::= { cfprSysdebugLogExportPolicyEntry 12 }

cfprSysdebugLogExportPolicyFsmStamp OBJECT-TYPE
    SYNTAX       DateAndTime
    MAX-ACCESS   read-only
    STATUS       current
    DESCRIPTION
        "Cisco Firepower sysdebug:LogExportPolicy:fsmStamp
        managed object property"
    ::= { cfprSysdebugLogExportPolicyEntry 13 }

cfprSysdebugLogExportPolicyFsmStatus OBJECT-TYPE
    SYNTAX       SnmpAdminString
    MAX-ACCESS   read-only
    STATUS       current
    DESCRIPTION
        "Cisco Firepower sysdebug:LogExportPolicy:fsmStatus
        managed object property"
    ::= { cfprSysdebugLogExportPolicyEntry 14 }

cfprSysdebugLogExportPolicyFsmTry OBJECT-TYPE
    SYNTAX       Gauge32
    MAX-ACCESS   read-only
    STATUS       current
    DESCRIPTION
        "Cisco Firepower sysdebug:LogExportPolicy:fsmTry
        managed object property"
    ::= { cfprSysdebugLogExportPolicyEntry 15 }

cfprSysdebugLogExportPolicyHostname OBJECT-TYPE
    SYNTAX       SnmpAdminString
    MAX-ACCESS   read-only
    STATUS       current
    DESCRIPTION
        "Cisco Firepower sysdebug:LogExportPolicy:hostname
        managed object property"
    ::= { cfprSysdebugLogExportPolicyEntry 16 }

cfprSysdebugLogExportPolicyIntId OBJECT-TYPE
    SYNTAX       SnmpAdminString
    MAX-ACCESS   read-only
    STATUS       current
    DESCRIPTION
        "Cisco Firepower sysdebug:LogExportPolicy:intId
        managed object property"
    ::= { cfprSysdebugLogExportPolicyEntry 17 }

cfprSysdebugLogExportPolicyName OBJECT-TYPE
    SYNTAX       SnmpAdminString
    MAX-ACCESS   read-only
    STATUS       current
    DESCRIPTION
        "Cisco Firepower sysdebug:LogExportPolicy:name
        managed object property"
    ::= { cfprSysdebugLogExportPolicyEntry 18 }

cfprSysdebugLogExportPolicyPasswordlessSsh OBJECT-TYPE
    SYNTAX       TruthValue
    MAX-ACCESS   read-only
    STATUS       current
    DESCRIPTION
        "Cisco Firepower sysdebug:LogExportPolicy:passwordlessSsh
        managed object property"
    ::= { cfprSysdebugLogExportPolicyEntry 19 }

cfprSysdebugLogExportPolicyPath OBJECT-TYPE
    SYNTAX       SnmpAdminString
    MAX-ACCESS   read-only
    STATUS       current
    DESCRIPTION
        "Cisco Firepower sysdebug:LogExportPolicy:path
        managed object property"
    ::= { cfprSysdebugLogExportPolicyEntry 20 }

cfprSysdebugLogExportPolicyPolicyLevel OBJECT-TYPE
    SYNTAX       Gauge32
    MAX-ACCESS   read-only
    STATUS       current
    DESCRIPTION
        "Cisco Firepower sysdebug:LogExportPolicy:policyLevel
        managed object property"
    ::= { cfprSysdebugLogExportPolicyEntry 21 }

cfprSysdebugLogExportPolicyPolicyOwner OBJECT-TYPE
    SYNTAX       CfprPolicyPolicyOwner
    MAX-ACCESS   read-only
    STATUS       current
    DESCRIPTION
        "Cisco Firepower sysdebug:LogExportPolicy:policyOwner
        managed object property"
    ::= { cfprSysdebugLogExportPolicyEntry 22 }

cfprSysdebugLogExportPolicyPostAction OBJECT-TYPE
    SYNTAX       CfprSysfileExporterPostAction
    MAX-ACCESS   read-only
    STATUS       current
    DESCRIPTION
        "Cisco Firepower sysdebug:LogExportPolicy:postAction
        managed object property"
    ::= { cfprSysdebugLogExportPolicyEntry 23 }

cfprSysdebugLogExportPolicyProto OBJECT-TYPE
    SYNTAX       CfprSysdebugLogExportPolicyProto
    MAX-ACCESS   read-only
    STATUS       current
    DESCRIPTION
        "Cisco Firepower sysdebug:LogExportPolicy:proto
        managed object property"
    ::= { cfprSysdebugLogExportPolicyEntry 24 }

cfprSysdebugLogExportPolicyPwd OBJECT-TYPE
    SYNTAX       SnmpAdminString
    MAX-ACCESS   read-only
    STATUS       current
    DESCRIPTION
        "Cisco Firepower sysdebug:LogExportPolicy:pwd managed
        object property"
    ::= { cfprSysdebugLogExportPolicyEntry 25 }

cfprSysdebugLogExportPolicyUser OBJECT-TYPE
    SYNTAX       SnmpAdminString
    MAX-ACCESS   read-only
    STATUS       current
    DESCRIPTION
        "Cisco Firepower sysdebug:LogExportPolicy:user
        managed object property"
    ::= { cfprSysdebugLogExportPolicyEntry 26 }

cfprSysdebugLogExportPolicyFsmTable OBJECT-TYPE
    SYNTAX           SEQUENCE OF CfprSysdebugLogExportPolicyFsmEntry
    MAX-ACCESS       not-accessible
    STATUS           current
    DESCRIPTION
        "Cisco Firepower sysdebug:LogExportPolicyFsm managed object table"
    ::= { cfprSysdebugObjects 21 }

cfprSysdebugLogExportPolicyFsmEntry OBJECT-TYPE
    SYNTAX           CfprSysdebugLogExportPolicyFsmEntry
    MAX-ACCESS       not-accessible
    STATUS           current
    DESCRIPTION
        "Entry for the cfprSysdebugLogExportPolicyFsmTable table."
    INDEX { cfprSysdebugLogExportPolicyFsmInstanceId }
    ::= { cfprSysdebugLogExportPolicyFsmTable 1 }

CfprSysdebugLogExportPolicyFsmEntry ::= SEQUENCE {
    cfprSysdebugLogExportPolicyFsmInstanceId                         CfprManagedObjectId,
    cfprSysdebugLogExportPolicyFsmDn                                 CfprManagedObjectDn,
    cfprSysdebugLogExportPolicyFsmRn                                 SnmpAdminString,
    cfprSysdebugLogExportPolicyFsmCompletionTime                     DateAndTime,
    cfprSysdebugLogExportPolicyFsmCurrentFsm                         CfprSysdebugLogExportPolicyFsmCurrentFsm,
    cfprSysdebugLogExportPolicyFsmDescrData                          SnmpAdminString,
    cfprSysdebugLogExportPolicyFsmFsmStatus                          CfprFsmFsmStageStatus,
    cfprSysdebugLogExportPolicyFsmProgress                           Gauge32,
    cfprSysdebugLogExportPolicyFsmRmtErrCode                         Gauge32,
    cfprSysdebugLogExportPolicyFsmRmtErrDescr                        SnmpAdminString,
    cfprSysdebugLogExportPolicyFsmRmtRslt                            CfprConditionRemoteInvRslt
}

cfprSysdebugLogExportPolicyFsmInstanceId OBJECT-TYPE
    SYNTAX       CfprManagedObjectId
    MAX-ACCESS   not-accessible
    STATUS       current
    DESCRIPTION
        "Instance identifier of the managed object."
    ::= { cfprSysdebugLogExportPolicyFsmEntry 1 }

cfprSysdebugLogExportPolicyFsmDn OBJECT-TYPE
    SYNTAX       CfprManagedObjectDn
    MAX-ACCESS   read-only
    STATUS       current
    DESCRIPTION
        "Cisco Firepower sysdebug:LogExportPolicyFsm:dn
        managed object property"
    ::= { cfprSysdebugLogExportPolicyFsmEntry 2 }

cfprSysdebugLogExportPolicyFsmRn OBJECT-TYPE
    SYNTAX       SnmpAdminString
    MAX-ACCESS   read-only
    STATUS       current
    DESCRIPTION
        "Cisco Firepower sysdebug:LogExportPolicyFsm:rn
        managed object property"
    ::= { cfprSysdebugLogExportPolicyFsmEntry 3 }

cfprSysdebugLogExportPolicyFsmCompletionTime OBJECT-TYPE
    SYNTAX       DateAndTime
    MAX-ACCESS   read-only
    STATUS       current
    DESCRIPTION
        "Cisco Firepower sysdebug:LogExportPolicyFsm:completionTime
        managed object property"
    ::= { cfprSysdebugLogExportPolicyFsmEntry 4 }

cfprSysdebugLogExportPolicyFsmCurrentFsm OBJECT-TYPE
    SYNTAX       CfprSysdebugLogExportPolicyFsmCurrentFsm
    MAX-ACCESS   read-only
    STATUS       current
    DESCRIPTION
        "Cisco Firepower sysdebug:LogExportPolicyFsm:currentFsm
        managed object property"
    ::= { cfprSysdebugLogExportPolicyFsmEntry 5 }

cfprSysdebugLogExportPolicyFsmDescrData OBJECT-TYPE
    SYNTAX       SnmpAdminString
    MAX-ACCESS   read-only
    STATUS       current
    DESCRIPTION
        "Cisco Firepower sysdebug:LogExportPolicyFsm:descr
        managed object property"
    ::= { cfprSysdebugLogExportPolicyFsmEntry 6 }

cfprSysdebugLogExportPolicyFsmFsmStatus OBJECT-TYPE
    SYNTAX       CfprFsmFsmStageStatus
    MAX-ACCESS   read-only
    STATUS       current
    DESCRIPTION
        "Cisco Firepower sysdebug:LogExportPolicyFsm:fsmStatus
        managed object property"
    ::= { cfprSysdebugLogExportPolicyFsmEntry 7 }

cfprSysdebugLogExportPolicyFsmProgress OBJECT-TYPE
    SYNTAX       Gauge32
    MAX-ACCESS   read-only
    STATUS       current
    DESCRIPTION
        "Cisco Firepower sysdebug:LogExportPolicyFsm:progress
        managed object property"
    ::= { cfprSysdebugLogExportPolicyFsmEntry 8 }

cfprSysdebugLogExportPolicyFsmRmtErrCode OBJECT-TYPE
    SYNTAX       Gauge32
    MAX-ACCESS   read-only
    STATUS       current
    DESCRIPTION
        "Cisco Firepower sysdebug:LogExportPolicyFsm:rmtErrCode
        managed object property"
    ::= { cfprSysdebugLogExportPolicyFsmEntry 9 }

cfprSysdebugLogExportPolicyFsmRmtErrDescr OBJECT-TYPE
    SYNTAX       SnmpAdminString
    MAX-ACCESS   read-only
    STATUS       current
    DESCRIPTION
        "Cisco Firepower sysdebug:LogExportPolicyFsm:rmtErrDescr
        managed object property"
    ::= { cfprSysdebugLogExportPolicyFsmEntry 10 }

cfprSysdebugLogExportPolicyFsmRmtRslt OBJECT-TYPE
    SYNTAX       CfprConditionRemoteInvRslt
    MAX-ACCESS   read-only
    STATUS       current
    DESCRIPTION
        "Cisco Firepower sysdebug:LogExportPolicyFsm:rmtRslt
        managed object property"
    ::= { cfprSysdebugLogExportPolicyFsmEntry 11 }

cfprSysdebugLogExportPolicyFsmStageTable OBJECT-TYPE
    SYNTAX           SEQUENCE OF CfprSysdebugLogExportPolicyFsmStageEntry
    MAX-ACCESS       not-accessible
    STATUS           current
    DESCRIPTION
        "Cisco Firepower sysdebug:LogExportPolicyFsmStage
        managed object table"
    ::= { cfprSysdebugObjects 22 }

cfprSysdebugLogExportPolicyFsmStageEntry OBJECT-TYPE
    SYNTAX           CfprSysdebugLogExportPolicyFsmStageEntry
    MAX-ACCESS       not-accessible
    STATUS           current
    DESCRIPTION
        "Entry for the cfprSysdebugLogExportPolicyFsmStageTable table."
    INDEX { cfprSysdebugLogExportPolicyFsmStageInstanceId }
    ::= { cfprSysdebugLogExportPolicyFsmStageTable 1 }

CfprSysdebugLogExportPolicyFsmStageEntry ::= SEQUENCE {
    cfprSysdebugLogExportPolicyFsmStageInstanceId                    CfprManagedObjectId,
    cfprSysdebugLogExportPolicyFsmStageDn                            CfprManagedObjectDn,
    cfprSysdebugLogExportPolicyFsmStageRn                            SnmpAdminString,
    cfprSysdebugLogExportPolicyFsmStageDescrData                     SnmpAdminString,
    cfprSysdebugLogExportPolicyFsmStageLastUpdateTime                DateAndTime,
    cfprSysdebugLogExportPolicyFsmStageName                          CfprSysdebugLogExportPolicyFsmStageName,
    cfprSysdebugLogExportPolicyFsmStageOrder                         Gauge32,
    cfprSysdebugLogExportPolicyFsmStageRetry                         Gauge32,
    cfprSysdebugLogExportPolicyFsmStageStageStatus                   CfprFsmFsmStageStatus
}

cfprSysdebugLogExportPolicyFsmStageInstanceId OBJECT-TYPE
    SYNTAX       CfprManagedObjectId
    MAX-ACCESS   not-accessible
    STATUS       current
    DESCRIPTION
        "Instance identifier of the managed object."
    ::= { cfprSysdebugLogExportPolicyFsmStageEntry 1 }

cfprSysdebugLogExportPolicyFsmStageDn OBJECT-TYPE
    SYNTAX       CfprManagedObjectDn
    MAX-ACCESS   read-only
    STATUS       current
    DESCRIPTION
        "Cisco Firepower sysdebug:LogExportPolicyFsmStage:dn
        managed object property"
    ::= { cfprSysdebugLogExportPolicyFsmStageEntry 2 }

cfprSysdebugLogExportPolicyFsmStageRn OBJECT-TYPE
    SYNTAX       SnmpAdminString
    MAX-ACCESS   read-only
    STATUS       current
    DESCRIPTION
        "Cisco Firepower sysdebug:LogExportPolicyFsmStage:rn
        managed object property"
    ::= { cfprSysdebugLogExportPolicyFsmStageEntry 3 }

cfprSysdebugLogExportPolicyFsmStageDescrData OBJECT-TYPE
    SYNTAX       SnmpAdminString
    MAX-ACCESS   read-only
    STATUS       current
    DESCRIPTION
        "Cisco Firepower sysdebug:LogExportPolicyFsmStage:descr
        managed object property"
    ::= { cfprSysdebugLogExportPolicyFsmStageEntry 4 }

cfprSysdebugLogExportPolicyFsmStageLastUpdateTime OBJECT-TYPE
    SYNTAX       DateAndTime
    MAX-ACCESS   read-only
    STATUS       current
    DESCRIPTION
        "Cisco Firepower sysdebug:LogExportPolicyFsmStage:lastUpdateTime
        managed object property"
    ::= { cfprSysdebugLogExportPolicyFsmStageEntry 5 }

cfprSysdebugLogExportPolicyFsmStageName OBJECT-TYPE
    SYNTAX       CfprSysdebugLogExportPolicyFsmStageName
    MAX-ACCESS   read-only
    STATUS       current
    DESCRIPTION
        "Cisco Firepower sysdebug:LogExportPolicyFsmStage:name
        managed object property"
    ::= { cfprSysdebugLogExportPolicyFsmStageEntry 6 }

cfprSysdebugLogExportPolicyFsmStageOrder OBJECT-TYPE
    SYNTAX       Gauge32
    MAX-ACCESS   read-only
    STATUS       current
    DESCRIPTION
        "Cisco Firepower sysdebug:LogExportPolicyFsmStage:order
        managed object property"
    ::= { cfprSysdebugLogExportPolicyFsmStageEntry 7 }

cfprSysdebugLogExportPolicyFsmStageRetry OBJECT-TYPE
    SYNTAX       Gauge32
    MAX-ACCESS   read-only
    STATUS       current
    DESCRIPTION
        "Cisco Firepower sysdebug:LogExportPolicyFsmStage:retry
        managed object property"
    ::= { cfprSysdebugLogExportPolicyFsmStageEntry 8 }

cfprSysdebugLogExportPolicyFsmStageStageStatus OBJECT-TYPE
    SYNTAX       CfprFsmFsmStageStatus
    MAX-ACCESS   read-only
    STATUS       current
    DESCRIPTION
        "Cisco Firepower sysdebug:LogExportPolicyFsmStage:stageStatus
        managed object property"
    ::= { cfprSysdebugLogExportPolicyFsmStageEntry 9 }

cfprSysdebugLogExportPolicyFsmTaskTable OBJECT-TYPE
    SYNTAX           SEQUENCE OF CfprSysdebugLogExportPolicyFsmTaskEntry
    MAX-ACCESS       not-accessible
    STATUS           current
    DESCRIPTION
        "Cisco Firepower sysdebug:LogExportPolicyFsmTask
        managed object table"
    ::= { cfprSysdebugObjects 23 }

cfprSysdebugLogExportPolicyFsmTaskEntry OBJECT-TYPE
    SYNTAX           CfprSysdebugLogExportPolicyFsmTaskEntry
    MAX-ACCESS       not-accessible
    STATUS           current
    DESCRIPTION
        "Entry for the cfprSysdebugLogExportPolicyFsmTaskTable table."
    INDEX { cfprSysdebugLogExportPolicyFsmTaskInstanceId }
    ::= { cfprSysdebugLogExportPolicyFsmTaskTable 1 }

CfprSysdebugLogExportPolicyFsmTaskEntry ::= SEQUENCE {
    cfprSysdebugLogExportPolicyFsmTaskInstanceId                     CfprManagedObjectId,
    cfprSysdebugLogExportPolicyFsmTaskDn                             CfprManagedObjectDn,
    cfprSysdebugLogExportPolicyFsmTaskRn                             SnmpAdminString,
    cfprSysdebugLogExportPolicyFsmTaskCompletion                     CfprFsmCompletion,
    cfprSysdebugLogExportPolicyFsmTaskFlags                          CfprFsmFlags,
    cfprSysdebugLogExportPolicyFsmTaskItem                           CfprSysdebugLogExportPolicyFsmTaskItem,
    cfprSysdebugLogExportPolicyFsmTaskSeqId                          Gauge32
}

cfprSysdebugLogExportPolicyFsmTaskInstanceId OBJECT-TYPE
    SYNTAX       CfprManagedObjectId
    MAX-ACCESS   not-accessible
    STATUS       current
    DESCRIPTION
        "Instance identifier of the managed object."
    ::= { cfprSysdebugLogExportPolicyFsmTaskEntry 1 }

cfprSysdebugLogExportPolicyFsmTaskDn OBJECT-TYPE
    SYNTAX       CfprManagedObjectDn
    MAX-ACCESS   read-only
    STATUS       current
    DESCRIPTION
        "Cisco Firepower sysdebug:LogExportPolicyFsmTask:dn
        managed object property"
    ::= { cfprSysdebugLogExportPolicyFsmTaskEntry 2 }

cfprSysdebugLogExportPolicyFsmTaskRn OBJECT-TYPE
    SYNTAX       SnmpAdminString
    MAX-ACCESS   read-only
    STATUS       current
    DESCRIPTION
        "Cisco Firepower sysdebug:LogExportPolicyFsmTask:rn
        managed object property"
    ::= { cfprSysdebugLogExportPolicyFsmTaskEntry 3 }

cfprSysdebugLogExportPolicyFsmTaskCompletion OBJECT-TYPE
    SYNTAX       CfprFsmCompletion
    MAX-ACCESS   read-only
    STATUS       current
    DESCRIPTION
        "Cisco Firepower sysdebug:LogExportPolicyFsmTask:completion
        managed object property"
    ::= { cfprSysdebugLogExportPolicyFsmTaskEntry 4 }

cfprSysdebugLogExportPolicyFsmTaskFlags OBJECT-TYPE
    SYNTAX       CfprFsmFlags
    MAX-ACCESS   read-only
    STATUS       current
    DESCRIPTION
        "Cisco Firepower sysdebug:LogExportPolicyFsmTask:flags
        managed object property"
    ::= { cfprSysdebugLogExportPolicyFsmTaskEntry 5 }

cfprSysdebugLogExportPolicyFsmTaskItem OBJECT-TYPE
    SYNTAX       CfprSysdebugLogExportPolicyFsmTaskItem
    MAX-ACCESS   read-only
    STATUS       current
    DESCRIPTION
        "Cisco Firepower sysdebug:LogExportPolicyFsmTask:item
        managed object property"
    ::= { cfprSysdebugLogExportPolicyFsmTaskEntry 6 }

cfprSysdebugLogExportPolicyFsmTaskSeqId OBJECT-TYPE
    SYNTAX       Gauge32
    MAX-ACCESS   read-only
    STATUS       current
    DESCRIPTION
        "Cisco Firepower sysdebug:LogExportPolicyFsmTask:seqId
        managed object property"
    ::= { cfprSysdebugLogExportPolicyFsmTaskEntry 7 }

cfprSysdebugLogExportStatusTable OBJECT-TYPE
    SYNTAX           SEQUENCE OF CfprSysdebugLogExportStatusEntry
    MAX-ACCESS       not-accessible
    STATUS           current
    DESCRIPTION
        "Cisco Firepower sysdebug:LogExportStatus managed object table"
    ::= { cfprSysdebugObjects 24 }

cfprSysdebugLogExportStatusEntry OBJECT-TYPE
    SYNTAX           CfprSysdebugLogExportStatusEntry
    MAX-ACCESS       not-accessible
    STATUS           current
    DESCRIPTION
        "Entry for the cfprSysdebugLogExportStatusTable table."
    INDEX { cfprSysdebugLogExportStatusInstanceId }
    ::= { cfprSysdebugLogExportStatusTable 1 }

CfprSysdebugLogExportStatusEntry ::= SEQUENCE {
    cfprSysdebugLogExportStatusInstanceId                            CfprManagedObjectId,
    cfprSysdebugLogExportStatusDn                                    CfprManagedObjectDn,
    cfprSysdebugLogExportStatusRn                                    SnmpAdminString,
    cfprSysdebugLogExportStatusExportFailureReason                   SnmpAdminString,
    cfprSysdebugLogExportStatusExportStatus                          CfprSysdebugExportStatus,
    cfprSysdebugLogExportStatusSwitchId                              CfprNetworkSwitchId
}

cfprSysdebugLogExportStatusInstanceId OBJECT-TYPE
    SYNTAX       CfprManagedObjectId
    MAX-ACCESS   not-accessible
    STATUS       current
    DESCRIPTION
        "Instance identifier of the managed object."
    ::= { cfprSysdebugLogExportStatusEntry 1 }

cfprSysdebugLogExportStatusDn OBJECT-TYPE
    SYNTAX       CfprManagedObjectDn
    MAX-ACCESS   read-only
    STATUS       current
    DESCRIPTION
        "Cisco Firepower sysdebug:LogExportStatus:dn managed
        object property"
    ::= { cfprSysdebugLogExportStatusEntry 2 }

cfprSysdebugLogExportStatusRn OBJECT-TYPE
    SYNTAX       SnmpAdminString
    MAX-ACCESS   read-only
    STATUS       current
    DESCRIPTION
        "Cisco Firepower sysdebug:LogExportStatus:rn managed
        object property"
    ::= { cfprSysdebugLogExportStatusEntry 3 }

cfprSysdebugLogExportStatusExportFailureReason OBJECT-TYPE
    SYNTAX       SnmpAdminString
    MAX-ACCESS   read-only
    STATUS       current
    DESCRIPTION
        "Cisco Firepower sysdebug:LogExportStatus:exportFailureReason
        managed object property"
    ::= { cfprSysdebugLogExportStatusEntry 4 }

cfprSysdebugLogExportStatusExportStatus OBJECT-TYPE
    SYNTAX       CfprSysdebugExportStatus
    MAX-ACCESS   read-only
    STATUS       current
    DESCRIPTION
        "Cisco Firepower sysdebug:LogExportStatus:exportStatus
        managed object property"
    ::= { cfprSysdebugLogExportStatusEntry 5 }

cfprSysdebugLogExportStatusSwitchId OBJECT-TYPE
    SYNTAX       CfprNetworkSwitchId
    MAX-ACCESS   read-only
    STATUS       current
    DESCRIPTION
        "Cisco Firepower sysdebug:LogExportStatus:switchId
        managed object property"
    ::= { cfprSysdebugLogExportStatusEntry 6 }

cfprSysdebugMEpLogTable OBJECT-TYPE
    SYNTAX           SEQUENCE OF CfprSysdebugMEpLogEntry
    MAX-ACCESS       not-accessible
    STATUS           current
    DESCRIPTION
        "Cisco Firepower sysdebug:MEpLog managed object table"
    ::= { cfprSysdebugObjects 25 }

cfprSysdebugMEpLogEntry OBJECT-TYPE
    SYNTAX           CfprSysdebugMEpLogEntry
    MAX-ACCESS       not-accessible
    STATUS           current
    DESCRIPTION
        "Entry for the cfprSysdebugMEpLogTable table."
    INDEX { cfprSysdebugMEpLogInstanceId }
    ::= { cfprSysdebugMEpLogTable 1 }

CfprSysdebugMEpLogEntry ::= SEQUENCE {
    cfprSysdebugMEpLogInstanceId                                     CfprManagedObjectId,
    cfprSysdebugMEpLogDn                                             CfprManagedObjectDn,
    cfprSysdebugMEpLogRn                                             SnmpAdminString,
    cfprSysdebugMEpLogAdminState                                     CfprSysdebugEpLogAdminState,
    cfprSysdebugMEpLogCapacity                                       CfprSysdebugEpLogCapacity,
    cfprSysdebugMEpLogId                                             Gauge32,
    cfprSysdebugMEpLogLastUpdate                                     DateAndTime,
    cfprSysdebugMEpLogOperState                                      CfprSysdebugMEpLogOperState,
    cfprSysdebugMEpLogType                                           CfprSysdebugEpLogType
}

cfprSysdebugMEpLogInstanceId OBJECT-TYPE
    SYNTAX       CfprManagedObjectId
    MAX-ACCESS   not-accessible
    STATUS       current
    DESCRIPTION
        "Instance identifier of the managed object."
    ::= { cfprSysdebugMEpLogEntry 1 }

cfprSysdebugMEpLogDn OBJECT-TYPE
    SYNTAX       CfprManagedObjectDn
    MAX-ACCESS   read-only
    STATUS       current
    DESCRIPTION
        "Cisco Firepower sysdebug:MEpLog:dn managed object property"
    ::= { cfprSysdebugMEpLogEntry 2 }

cfprSysdebugMEpLogRn OBJECT-TYPE
    SYNTAX       SnmpAdminString
    MAX-ACCESS   read-only
    STATUS       current
    DESCRIPTION
        "Cisco Firepower sysdebug:MEpLog:rn managed object property"
    ::= { cfprSysdebugMEpLogEntry 3 }

cfprSysdebugMEpLogAdminState OBJECT-TYPE
    SYNTAX       CfprSysdebugEpLogAdminState
    MAX-ACCESS   read-only
    STATUS       current
    DESCRIPTION
        "Cisco Firepower sysdebug:MEpLog:adminState managed
        object property"
    ::= { cfprSysdebugMEpLogEntry 4 }

cfprSysdebugMEpLogCapacity OBJECT-TYPE
    SYNTAX       CfprSysdebugEpLogCapacity
    MAX-ACCESS   read-only
    STATUS       current
    DESCRIPTION
        "Cisco Firepower sysdebug:MEpLog:capacity managed object property"
    ::= { cfprSysdebugMEpLogEntry 5 }

cfprSysdebugMEpLogId OBJECT-TYPE
    SYNTAX       Gauge32
    MAX-ACCESS   read-only
    STATUS       current
    DESCRIPTION
        "Cisco Firepower sysdebug:MEpLog:id managed object property"
    ::= { cfprSysdebugMEpLogEntry 6 }

cfprSysdebugMEpLogLastUpdate OBJECT-TYPE
    SYNTAX       DateAndTime
    MAX-ACCESS   read-only
    STATUS       current
    DESCRIPTION
        "Cisco Firepower sysdebug:MEpLog:lastUpdate managed
        object property"
    ::= { cfprSysdebugMEpLogEntry 7 }

cfprSysdebugMEpLogOperState OBJECT-TYPE
    SYNTAX       CfprSysdebugMEpLogOperState
    MAX-ACCESS   read-only
    STATUS       current
    DESCRIPTION
        "Cisco Firepower sysdebug:MEpLog:operState managed
        object property"
    ::= { cfprSysdebugMEpLogEntry 8 }

cfprSysdebugMEpLogType OBJECT-TYPE
    SYNTAX       CfprSysdebugEpLogType
    MAX-ACCESS   read-only
    STATUS       current
    DESCRIPTION
        "Cisco Firepower sysdebug:MEpLog:type managed object property"
    ::= { cfprSysdebugMEpLogEntry 9 }

cfprSysdebugMEpLogPolicyTable OBJECT-TYPE
    SYNTAX           SEQUENCE OF CfprSysdebugMEpLogPolicyEntry
    MAX-ACCESS       not-accessible
    STATUS           current
    DESCRIPTION
        "Cisco Firepower sysdebug:MEpLogPolicy managed object table"
    ::= { cfprSysdebugObjects 26 }

cfprSysdebugMEpLogPolicyEntry OBJECT-TYPE
    SYNTAX           CfprSysdebugMEpLogPolicyEntry
    MAX-ACCESS       not-accessible
    STATUS           current
    DESCRIPTION
        "Entry for the cfprSysdebugMEpLogPolicyTable table."
    INDEX { cfprSysdebugMEpLogPolicyInstanceId }
    ::= { cfprSysdebugMEpLogPolicyTable 1 }

CfprSysdebugMEpLogPolicyEntry ::= SEQUENCE {
    cfprSysdebugMEpLogPolicyInstanceId                               CfprManagedObjectId,
    cfprSysdebugMEpLogPolicyDn                                       CfprManagedObjectDn,
    cfprSysdebugMEpLogPolicyRn                                       SnmpAdminString,
    cfprSysdebugMEpLogPolicyDescr                                    SnmpAdminString,
    cfprSysdebugMEpLogPolicyIntId                                    SnmpAdminString,
    cfprSysdebugMEpLogPolicyName                                     SnmpAdminString,
    cfprSysdebugMEpLogPolicyPolicyLevel                              Gauge32,
    cfprSysdebugMEpLogPolicyPolicyOwner                              CfprPolicyPolicyOwner,
    cfprSysdebugMEpLogPolicyType                                     CfprSysdebugEpLogType
}

cfprSysdebugMEpLogPolicyInstanceId OBJECT-TYPE
    SYNTAX       CfprManagedObjectId
    MAX-ACCESS   not-accessible
    STATUS       current
    DESCRIPTION
        "Instance identifier of the managed object."
    ::= { cfprSysdebugMEpLogPolicyEntry 1 }

cfprSysdebugMEpLogPolicyDn OBJECT-TYPE
    SYNTAX       CfprManagedObjectDn
    MAX-ACCESS   read-only
    STATUS       current
    DESCRIPTION
        "Cisco Firepower sysdebug:MEpLogPolicy:dn managed object property"
    ::= { cfprSysdebugMEpLogPolicyEntry 2 }

cfprSysdebugMEpLogPolicyRn OBJECT-TYPE
    SYNTAX       SnmpAdminString
    MAX-ACCESS   read-only
    STATUS       current
    DESCRIPTION
        "Cisco Firepower sysdebug:MEpLogPolicy:rn managed object property"
    ::= { cfprSysdebugMEpLogPolicyEntry 3 }

cfprSysdebugMEpLogPolicyDescr OBJECT-TYPE
    SYNTAX       SnmpAdminString
    MAX-ACCESS   read-only
    STATUS       current
    DESCRIPTION
        "Cisco Firepower sysdebug:MEpLogPolicy:descr managed
        object property"
    ::= { cfprSysdebugMEpLogPolicyEntry 4 }

cfprSysdebugMEpLogPolicyIntId OBJECT-TYPE
    SYNTAX       SnmpAdminString
    MAX-ACCESS   read-only
    STATUS       current
    DESCRIPTION
        "Cisco Firepower sysdebug:MEpLogPolicy:intId managed
        object property"
    ::= { cfprSysdebugMEpLogPolicyEntry 5 }

cfprSysdebugMEpLogPolicyName OBJECT-TYPE
    SYNTAX       SnmpAdminString
    MAX-ACCESS   read-only
    STATUS       current
    DESCRIPTION
        "Cisco Firepower sysdebug:MEpLogPolicy:name managed
        object property"
    ::= { cfprSysdebugMEpLogPolicyEntry 6 }

cfprSysdebugMEpLogPolicyPolicyLevel OBJECT-TYPE
    SYNTAX       Gauge32
    MAX-ACCESS   read-only
    STATUS       current
    DESCRIPTION
        "Cisco Firepower sysdebug:MEpLogPolicy:policyLevel
        managed object property"
    ::= { cfprSysdebugMEpLogPolicyEntry 7 }

cfprSysdebugMEpLogPolicyPolicyOwner OBJECT-TYPE
    SYNTAX       CfprPolicyPolicyOwner
    MAX-ACCESS   read-only
    STATUS       current
    DESCRIPTION
        "Cisco Firepower sysdebug:MEpLogPolicy:policyOwner
        managed object property"
    ::= { cfprSysdebugMEpLogPolicyEntry 8 }

cfprSysdebugMEpLogPolicyType OBJECT-TYPE
    SYNTAX       CfprSysdebugEpLogType
    MAX-ACCESS   read-only
    STATUS       current
    DESCRIPTION
        "Cisco Firepower sysdebug:MEpLogPolicy:type managed
        object property"
    ::= { cfprSysdebugMEpLogPolicyEntry 9 }

cfprSysdebugManualCoreFileExportTargetTable OBJECT-TYPE
    SYNTAX           SEQUENCE OF CfprSysdebugManualCoreFileExportTargetEntry
    MAX-ACCESS       not-accessible
    STATUS           current
    DESCRIPTION
        "Cisco Firepower sysdebug:ManualCoreFileExportTarget
        managed object table"
    ::= { cfprSysdebugObjects 27 }

cfprSysdebugManualCoreFileExportTargetEntry OBJECT-TYPE
    SYNTAX           CfprSysdebugManualCoreFileExportTargetEntry
    MAX-ACCESS       not-accessible
    STATUS           current
    DESCRIPTION
        "Entry for the cfprSysdebugManualCoreFileExportTargetTable table."
    INDEX { cfprSysdebugManualCoreFileExportTargetInstanceId }
    ::= { cfprSysdebugManualCoreFileExportTargetTable 1 }

CfprSysdebugManualCoreFileExportTargetEntry ::= SEQUENCE {
    cfprSysdebugManualCoreFileExportTargetInstanceId                 CfprManagedObjectId,
    cfprSysdebugManualCoreFileExportTargetDn                         CfprManagedObjectDn,
    cfprSysdebugManualCoreFileExportTargetRn                         SnmpAdminString,
    cfprSysdebugManualCoreFileExportTargetAdminState                 CfprSysdebugManualCoreFileExportTargetAdminState,
    cfprSysdebugManualCoreFileExportTargetDescr                      SnmpAdminString,
    cfprSysdebugManualCoreFileExportTargetExportFailureReason        SnmpAdminString,
    cfprSysdebugManualCoreFileExportTargetExportStatus               CfprSysdebugCoreExportStatus,
    cfprSysdebugManualCoreFileExportTargetFsmDescr                   SnmpAdminString,
    cfprSysdebugManualCoreFileExportTargetFsmPrev                    SnmpAdminString,
    cfprSysdebugManualCoreFileExportTargetFsmProgr                   Gauge32,
    cfprSysdebugManualCoreFileExportTargetFsmRmtInvErrCode           Gauge32,
    cfprSysdebugManualCoreFileExportTargetFsmRmtInvErrDescr          SnmpAdminString,
    cfprSysdebugManualCoreFileExportTargetFsmRmtInvRslt              CfprConditionRemoteInvRslt,
    cfprSysdebugManualCoreFileExportTargetFsmStageDescr              SnmpAdminString,
    cfprSysdebugManualCoreFileExportTargetFsmStamp                   DateAndTime,
    cfprSysdebugManualCoreFileExportTargetFsmStatus                  SnmpAdminString,
    cfprSysdebugManualCoreFileExportTargetFsmTry                     Gauge32,
    cfprSysdebugManualCoreFileExportTargetHostname                   SnmpAdminString,
    cfprSysdebugManualCoreFileExportTargetIntId                      SnmpAdminString,
    cfprSysdebugManualCoreFileExportTargetName                       SnmpAdminString,
    cfprSysdebugManualCoreFileExportTargetPath                       SnmpAdminString,
    cfprSysdebugManualCoreFileExportTargetPolicyLevel                Gauge32,
    cfprSysdebugManualCoreFileExportTargetPolicyOwner                CfprPolicyPolicyOwner,
    cfprSysdebugManualCoreFileExportTargetPort                       Gauge32,
    cfprSysdebugManualCoreFileExportTargetPostAction                 CfprSysfileExporterPostAction,
    cfprSysdebugManualCoreFileExportTargetProto                      CfprSysdebugManualCoreFileExportTargetProto
}

cfprSysdebugManualCoreFileExportTargetInstanceId OBJECT-TYPE
    SYNTAX       CfprManagedObjectId
    MAX-ACCESS   not-accessible
    STATUS       current
    DESCRIPTION
        "Instance identifier of the managed object."
    ::= { cfprSysdebugManualCoreFileExportTargetEntry 1 }

cfprSysdebugManualCoreFileExportTargetDn OBJECT-TYPE
    SYNTAX       CfprManagedObjectDn
    MAX-ACCESS   read-only
    STATUS       current
    DESCRIPTION
        "Cisco Firepower sysdebug:ManualCoreFileExportTarget:dn
        managed object property"
    ::= { cfprSysdebugManualCoreFileExportTargetEntry 2 }

cfprSysdebugManualCoreFileExportTargetRn OBJECT-TYPE
    SYNTAX       SnmpAdminString
    MAX-ACCESS   read-only
    STATUS       current
    DESCRIPTION
        "Cisco Firepower sysdebug:ManualCoreFileExportTarget:rn
        managed object property"
    ::= { cfprSysdebugManualCoreFileExportTargetEntry 3 }

cfprSysdebugManualCoreFileExportTargetAdminState OBJECT-TYPE
    SYNTAX       CfprSysdebugManualCoreFileExportTargetAdminState
    MAX-ACCESS   read-only
    STATUS       current
    DESCRIPTION
        "Cisco Firepower sysdebug:ManualCoreFileExportTarget:adminState
        managed object property"
    ::= { cfprSysdebugManualCoreFileExportTargetEntry 4 }

cfprSysdebugManualCoreFileExportTargetDescr OBJECT-TYPE
    SYNTAX       SnmpAdminString
    MAX-ACCESS   read-only
    STATUS       current
    DESCRIPTION
        "Cisco Firepower sysdebug:ManualCoreFileExportTarget:descr
        managed object property"
    ::= { cfprSysdebugManualCoreFileExportTargetEntry 5 }

cfprSysdebugManualCoreFileExportTargetExportFailureReason OBJECT-TYPE
    SYNTAX       SnmpAdminString
    MAX-ACCESS   read-only
    STATUS       current
    DESCRIPTION
        "Cisco Firepower sysdebug:ManualCoreFileExportTarget:exportFailure
        Reason managed object property"
    ::= { cfprSysdebugManualCoreFileExportTargetEntry 6 }

cfprSysdebugManualCoreFileExportTargetExportStatus OBJECT-TYPE
    SYNTAX       CfprSysdebugCoreExportStatus
    MAX-ACCESS   read-only
    STATUS       current
    DESCRIPTION
        "Cisco Firepower sysdebug:ManualCoreFileExportTarget:exportStatus
        managed object property"
    ::= { cfprSysdebugManualCoreFileExportTargetEntry 7 }

cfprSysdebugManualCoreFileExportTargetFsmDescr OBJECT-TYPE
    SYNTAX       SnmpAdminString
    MAX-ACCESS   read-only
    STATUS       current
    DESCRIPTION
        "Cisco Firepower sysdebug:ManualCoreFileExportTarget:fsmDescr
        managed object property"
    ::= { cfprSysdebugManualCoreFileExportTargetEntry 8 }

cfprSysdebugManualCoreFileExportTargetFsmPrev OBJECT-TYPE
    SYNTAX       SnmpAdminString
    MAX-ACCESS   read-only
    STATUS       current
    DESCRIPTION
        "Cisco Firepower sysdebug:ManualCoreFileExportTarget:fsmPrev
        managed object property"
    ::= { cfprSysdebugManualCoreFileExportTargetEntry 9 }

cfprSysdebugManualCoreFileExportTargetFsmProgr OBJECT-TYPE
    SYNTAX       Gauge32
    MAX-ACCESS   read-only
    STATUS       current
    DESCRIPTION
        "Cisco Firepower sysdebug:ManualCoreFileExportTarget:fsmProgr
        managed object property"
    ::= { cfprSysdebugManualCoreFileExportTargetEntry 10 }

cfprSysdebugManualCoreFileExportTargetFsmRmtInvErrCode OBJECT-TYPE
    SYNTAX       Gauge32
    MAX-ACCESS   read-only
    STATUS       current
    DESCRIPTION
        "Cisco Firepower sysdebug:ManualCoreFileExportTarget:fsmRmtInvErrC
        ode managed object property"
    ::= { cfprSysdebugManualCoreFileExportTargetEntry 11 }

cfprSysdebugManualCoreFileExportTargetFsmRmtInvErrDescr OBJECT-TYPE
    SYNTAX       SnmpAdminString
    MAX-ACCESS   read-only
    STATUS       current
    DESCRIPTION
        "Cisco Firepower sysdebug:ManualCoreFileExportTarget:fsmRmtInvErrD
        escr managed object property"
    ::= { cfprSysdebugManualCoreFileExportTargetEntry 12 }

cfprSysdebugManualCoreFileExportTargetFsmRmtInvRslt OBJECT-TYPE
    SYNTAX       CfprConditionRemoteInvRslt
    MAX-ACCESS   read-only
    STATUS       current
    DESCRIPTION
        "Cisco Firepower sysdebug:ManualCoreFileExportTarget:fsmRmtInvRslt
         managed object property"
    ::= { cfprSysdebugManualCoreFileExportTargetEntry 13 }

cfprSysdebugManualCoreFileExportTargetFsmStageDescr OBJECT-TYPE
    SYNTAX       SnmpAdminString
    MAX-ACCESS   read-only
    STATUS       current
    DESCRIPTION
        "Cisco Firepower sysdebug:ManualCoreFileExportTarget:fsmStageDescr
         managed object property"
    ::= { cfprSysdebugManualCoreFileExportTargetEntry 14 }

cfprSysdebugManualCoreFileExportTargetFsmStamp OBJECT-TYPE
    SYNTAX       DateAndTime
    MAX-ACCESS   read-only
    STATUS       current
    DESCRIPTION
        "Cisco Firepower sysdebug:ManualCoreFileExportTarget:fsmStamp
        managed object property"
    ::= { cfprSysdebugManualCoreFileExportTargetEntry 15 }

cfprSysdebugManualCoreFileExportTargetFsmStatus OBJECT-TYPE
    SYNTAX       SnmpAdminString
    MAX-ACCESS   read-only
    STATUS       current
    DESCRIPTION
        "Cisco Firepower sysdebug:ManualCoreFileExportTarget:fsmStatus
        managed object property"
    ::= { cfprSysdebugManualCoreFileExportTargetEntry 16 }

cfprSysdebugManualCoreFileExportTargetFsmTry OBJECT-TYPE
    SYNTAX       Gauge32
    MAX-ACCESS   read-only
    STATUS       current
    DESCRIPTION
        "Cisco Firepower sysdebug:ManualCoreFileExportTarget:fsmTry
        managed object property"
    ::= { cfprSysdebugManualCoreFileExportTargetEntry 17 }

cfprSysdebugManualCoreFileExportTargetHostname OBJECT-TYPE
    SYNTAX       SnmpAdminString
    MAX-ACCESS   read-only
    STATUS       current
    DESCRIPTION
        "Cisco Firepower sysdebug:ManualCoreFileExportTarget:hostname
        managed object property"
    ::= { cfprSysdebugManualCoreFileExportTargetEntry 18 }

cfprSysdebugManualCoreFileExportTargetIntId OBJECT-TYPE
    SYNTAX       SnmpAdminString
    MAX-ACCESS   read-only
    STATUS       current
    DESCRIPTION
        "Cisco Firepower sysdebug:ManualCoreFileExportTarget:intId
        managed object property"
    ::= { cfprSysdebugManualCoreFileExportTargetEntry 19 }

cfprSysdebugManualCoreFileExportTargetName OBJECT-TYPE
    SYNTAX       SnmpAdminString
    MAX-ACCESS   read-only
    STATUS       current
    DESCRIPTION
        "Cisco Firepower sysdebug:ManualCoreFileExportTarget:name
        managed object property"
    ::= { cfprSysdebugManualCoreFileExportTargetEntry 20 }

cfprSysdebugManualCoreFileExportTargetPath OBJECT-TYPE
    SYNTAX       SnmpAdminString
    MAX-ACCESS   read-only
    STATUS       current
    DESCRIPTION
        "Cisco Firepower sysdebug:ManualCoreFileExportTarget:path
        managed object property"
    ::= { cfprSysdebugManualCoreFileExportTargetEntry 21 }

cfprSysdebugManualCoreFileExportTargetPolicyLevel OBJECT-TYPE
    SYNTAX       Gauge32
    MAX-ACCESS   read-only
    STATUS       current
    DESCRIPTION
        "Cisco Firepower sysdebug:ManualCoreFileExportTarget:policyLevel
        managed object property"
    ::= { cfprSysdebugManualCoreFileExportTargetEntry 22 }

cfprSysdebugManualCoreFileExportTargetPolicyOwner OBJECT-TYPE
    SYNTAX       CfprPolicyPolicyOwner
    MAX-ACCESS   read-only
    STATUS       current
    DESCRIPTION
        "Cisco Firepower sysdebug:ManualCoreFileExportTarget:policyOwner
        managed object property"
    ::= { cfprSysdebugManualCoreFileExportTargetEntry 23 }

cfprSysdebugManualCoreFileExportTargetPort OBJECT-TYPE
    SYNTAX       Gauge32
    MAX-ACCESS   read-only
    STATUS       current
    DESCRIPTION
        "Cisco Firepower sysdebug:ManualCoreFileExportTarget:port
        managed object property"
    ::= { cfprSysdebugManualCoreFileExportTargetEntry 24 }

cfprSysdebugManualCoreFileExportTargetPostAction OBJECT-TYPE
    SYNTAX       CfprSysfileExporterPostAction
    MAX-ACCESS   read-only
    STATUS       current
    DESCRIPTION
        "Cisco Firepower sysdebug:ManualCoreFileExportTarget:postAction
        managed object property"
    ::= { cfprSysdebugManualCoreFileExportTargetEntry 25 }

cfprSysdebugManualCoreFileExportTargetProto OBJECT-TYPE
    SYNTAX       CfprSysdebugManualCoreFileExportTargetProto
    MAX-ACCESS   read-only
    STATUS       current
    DESCRIPTION
        "Cisco Firepower sysdebug:ManualCoreFileExportTarget:proto
        managed object property"
    ::= { cfprSysdebugManualCoreFileExportTargetEntry 26 }

cfprSysdebugManualCoreFileExportTargetFsmTable OBJECT-TYPE
    SYNTAX           SEQUENCE OF CfprSysdebugManualCoreFileExportTargetFsmEntry
    MAX-ACCESS       not-accessible
    STATUS           current
    DESCRIPTION
        "Cisco Firepower sysdebug:ManualCoreFileExportTargetFsm
        managed object table"
    ::= { cfprSysdebugObjects 28 }

cfprSysdebugManualCoreFileExportTargetFsmEntry OBJECT-TYPE
    SYNTAX           CfprSysdebugManualCoreFileExportTargetFsmEntry
    MAX-ACCESS       not-accessible
    STATUS           current
    DESCRIPTION
        "Entry for the cfprSysdebugManualCoreFileExportTargetFsmTable table."
    INDEX { cfprSysdebugManualCoreFileExportTargetFsmInstanceId }
    ::= { cfprSysdebugManualCoreFileExportTargetFsmTable 1 }

CfprSysdebugManualCoreFileExportTargetFsmEntry ::= SEQUENCE {
    cfprSysdebugManualCoreFileExportTargetFsmInstanceId              CfprManagedObjectId,
    cfprSysdebugManualCoreFileExportTargetFsmDn                      CfprManagedObjectDn,
    cfprSysdebugManualCoreFileExportTargetFsmRn                      SnmpAdminString,
    cfprSysdebugManualCoreFileExportTargetFsmCompletionTime          DateAndTime,
    cfprSysdebugManualCoreFileExportTargetFsmCurrentFsm              CfprSysdebugManualCoreFileExportTargetFsmCurrentFsm,
    cfprSysdebugManualCoreFileExportTargetFsmDescrData               SnmpAdminString,
    cfprSysdebugManualCoreFileExportTargetFsmFsmStatus               CfprFsmFsmStageStatus,
    cfprSysdebugManualCoreFileExportTargetFsmProgress                Gauge32,
    cfprSysdebugManualCoreFileExportTargetFsmRmtErrCode              Gauge32,
    cfprSysdebugManualCoreFileExportTargetFsmRmtErrDescr             SnmpAdminString,
    cfprSysdebugManualCoreFileExportTargetFsmRmtRslt                 CfprConditionRemoteInvRslt
}

cfprSysdebugManualCoreFileExportTargetFsmInstanceId OBJECT-TYPE
    SYNTAX       CfprManagedObjectId
    MAX-ACCESS   not-accessible
    STATUS       current
    DESCRIPTION
        "Instance identifier of the managed object."
    ::= { cfprSysdebugManualCoreFileExportTargetFsmEntry 1 }

cfprSysdebugManualCoreFileExportTargetFsmDn OBJECT-TYPE
    SYNTAX       CfprManagedObjectDn
    MAX-ACCESS   read-only
    STATUS       current
    DESCRIPTION
        "Cisco Firepower sysdebug:ManualCoreFileExportTargetFsm:dn
        managed object property"
    ::= { cfprSysdebugManualCoreFileExportTargetFsmEntry 2 }

cfprSysdebugManualCoreFileExportTargetFsmRn OBJECT-TYPE
    SYNTAX       SnmpAdminString
    MAX-ACCESS   read-only
    STATUS       current
    DESCRIPTION
        "Cisco Firepower sysdebug:ManualCoreFileExportTargetFsm:rn
        managed object property"
    ::= { cfprSysdebugManualCoreFileExportTargetFsmEntry 3 }

cfprSysdebugManualCoreFileExportTargetFsmCompletionTime OBJECT-TYPE
    SYNTAX       DateAndTime
    MAX-ACCESS   read-only
    STATUS       current
    DESCRIPTION
        "Cisco Firepower sysdebug:ManualCoreFileExportTargetFsm:completion
        Time managed object property"
    ::= { cfprSysdebugManualCoreFileExportTargetFsmEntry 4 }

cfprSysdebugManualCoreFileExportTargetFsmCurrentFsm OBJECT-TYPE
    SYNTAX       CfprSysdebugManualCoreFileExportTargetFsmCurrentFsm
    MAX-ACCESS   read-only
    STATUS       current
    DESCRIPTION
        "Cisco Firepower sysdebug:ManualCoreFileExportTargetFsm:currentFsm
         managed object property"
    ::= { cfprSysdebugManualCoreFileExportTargetFsmEntry 5 }

cfprSysdebugManualCoreFileExportTargetFsmDescrData OBJECT-TYPE
    SYNTAX       SnmpAdminString
    MAX-ACCESS   read-only
    STATUS       current
    DESCRIPTION
        "Cisco Firepower sysdebug:ManualCoreFileExportTargetFsm:descr
        managed object property"
    ::= { cfprSysdebugManualCoreFileExportTargetFsmEntry 6 }

cfprSysdebugManualCoreFileExportTargetFsmFsmStatus OBJECT-TYPE
    SYNTAX       CfprFsmFsmStageStatus
    MAX-ACCESS   read-only
    STATUS       current
    DESCRIPTION
        "Cisco Firepower sysdebug:ManualCoreFileExportTargetFsm:fsmStatus
        managed object property"
    ::= { cfprSysdebugManualCoreFileExportTargetFsmEntry 7 }

cfprSysdebugManualCoreFileExportTargetFsmProgress OBJECT-TYPE
    SYNTAX       Gauge32
    MAX-ACCESS   read-only
    STATUS       current
    DESCRIPTION
        "Cisco Firepower sysdebug:ManualCoreFileExportTargetFsm:progress
        managed object property"
    ::= { cfprSysdebugManualCoreFileExportTargetFsmEntry 8 }

cfprSysdebugManualCoreFileExportTargetFsmRmtErrCode OBJECT-TYPE
    SYNTAX       Gauge32
    MAX-ACCESS   read-only
    STATUS       current
    DESCRIPTION
        "Cisco Firepower sysdebug:ManualCoreFileExportTargetFsm:rmtErrCode
         managed object property"
    ::= { cfprSysdebugManualCoreFileExportTargetFsmEntry 9 }

cfprSysdebugManualCoreFileExportTargetFsmRmtErrDescr OBJECT-TYPE
    SYNTAX       SnmpAdminString
    MAX-ACCESS   read-only
    STATUS       current
    DESCRIPTION
        "Cisco Firepower sysdebug:ManualCoreFileExportTargetFsm:rmtErrDesc
        r managed object property"
    ::= { cfprSysdebugManualCoreFileExportTargetFsmEntry 10 }

cfprSysdebugManualCoreFileExportTargetFsmRmtRslt OBJECT-TYPE
    SYNTAX       CfprConditionRemoteInvRslt
    MAX-ACCESS   read-only
    STATUS       current
    DESCRIPTION
        "Cisco Firepower sysdebug:ManualCoreFileExportTargetFsm:rmtRslt
        managed object property"
    ::= { cfprSysdebugManualCoreFileExportTargetFsmEntry 11 }

cfprSysdebugManualCoreFileExportTargetFsmStageTable OBJECT-TYPE
    SYNTAX           SEQUENCE OF CfprSysdebugManualCoreFileExportTargetFsmStageEntry
    MAX-ACCESS       not-accessible
    STATUS           current
    DESCRIPTION
        "Cisco Firepower sysdebug:ManualCoreFileExportTargetFsmStage
        managed object table"
    ::= { cfprSysdebugObjects 29 }

cfprSysdebugManualCoreFileExportTargetFsmStageEntry OBJECT-TYPE
    SYNTAX           CfprSysdebugManualCoreFileExportTargetFsmStageEntry
    MAX-ACCESS       not-accessible
    STATUS           current
    DESCRIPTION
        "Entry for the cfprSysdebugManualCoreFileExportTargetFsmStageTable table."
    INDEX { cfprSysdebugManualCoreFileExportTargetFsmStageInstanceId }
    ::= { cfprSysdebugManualCoreFileExportTargetFsmStageTable 1 }

CfprSysdebugManualCoreFileExportTargetFsmStageEntry ::= SEQUENCE {
    cfprSysdebugManualCoreFileExportTargetFsmStageInstanceId         CfprManagedObjectId,
    cfprSysdebugManualCoreFileExportTargetFsmStageDn                 CfprManagedObjectDn,
    cfprSysdebugManualCoreFileExportTargetFsmStageRn                 SnmpAdminString,
    cfprSysdebugManualCoreFileExportTargetFsmStageDescrData          SnmpAdminString,
    cfprSysdebugManualCoreFileExportTargetFsmStageLastUpdateTime     DateAndTime,
    cfprSysdebugManualCoreFileExportTargetFsmStageName               CfprSysdebugManualCoreFileExportTargetFsmStageName,
    cfprSysdebugManualCoreFileExportTargetFsmStageOrder              Gauge32,
    cfprSysdebugManualCoreFileExportTargetFsmStageRetry              Gauge32,
    cfprSysdebugManualCoreFileExportTargetFsmStageStageStatus        CfprFsmFsmStageStatus
}

cfprSysdebugManualCoreFileExportTargetFsmStageInstanceId OBJECT-TYPE
    SYNTAX       CfprManagedObjectId
    MAX-ACCESS   not-accessible
    STATUS       current
    DESCRIPTION
        "Instance identifier of the managed object."
    ::= { cfprSysdebugManualCoreFileExportTargetFsmStageEntry 1 }

cfprSysdebugManualCoreFileExportTargetFsmStageDn OBJECT-TYPE
    SYNTAX       CfprManagedObjectDn
    MAX-ACCESS   read-only
    STATUS       current
    DESCRIPTION
        "Cisco Firepower sysdebug:ManualCoreFileExportTargetFsmStage:dn
        managed object property"
    ::= { cfprSysdebugManualCoreFileExportTargetFsmStageEntry 2 }

cfprSysdebugManualCoreFileExportTargetFsmStageRn OBJECT-TYPE
    SYNTAX       SnmpAdminString
    MAX-ACCESS   read-only
    STATUS       current
    DESCRIPTION
        "Cisco Firepower sysdebug:ManualCoreFileExportTargetFsmStage:rn
        managed object property"
    ::= { cfprSysdebugManualCoreFileExportTargetFsmStageEntry 3 }

cfprSysdebugManualCoreFileExportTargetFsmStageDescrData OBJECT-TYPE
    SYNTAX       SnmpAdminString
    MAX-ACCESS   read-only
    STATUS       current
    DESCRIPTION
        "Cisco Firepower sysdebug:ManualCoreFileExportTargetFsmStage:descr
         managed object property"
    ::= { cfprSysdebugManualCoreFileExportTargetFsmStageEntry 4 }

cfprSysdebugManualCoreFileExportTargetFsmStageLastUpdateTime OBJECT-TYPE
    SYNTAX       DateAndTime
    MAX-ACCESS   read-only
    STATUS       current
    DESCRIPTION
        "Cisco Firepower sysdebug:ManualCoreFileExportTargetFsmStage:lastU
        pdateTime managed object property"
    ::= { cfprSysdebugManualCoreFileExportTargetFsmStageEntry 5 }

cfprSysdebugManualCoreFileExportTargetFsmStageName OBJECT-TYPE
    SYNTAX       CfprSysdebugManualCoreFileExportTargetFsmStageName
    MAX-ACCESS   read-only
    STATUS       current
    DESCRIPTION
        "Cisco Firepower sysdebug:ManualCoreFileExportTargetFsmStage:name
        managed object property"
    ::= { cfprSysdebugManualCoreFileExportTargetFsmStageEntry 6 }

cfprSysdebugManualCoreFileExportTargetFsmStageOrder OBJECT-TYPE
    SYNTAX       Gauge32
    MAX-ACCESS   read-only
    STATUS       current
    DESCRIPTION
        "Cisco Firepower sysdebug:ManualCoreFileExportTargetFsmStage:order
         managed object property"
    ::= { cfprSysdebugManualCoreFileExportTargetFsmStageEntry 7 }

cfprSysdebugManualCoreFileExportTargetFsmStageRetry OBJECT-TYPE
    SYNTAX       Gauge32
    MAX-ACCESS   read-only
    STATUS       current
    DESCRIPTION
        "Cisco Firepower sysdebug:ManualCoreFileExportTargetFsmStage:retry
         managed object property"
    ::= { cfprSysdebugManualCoreFileExportTargetFsmStageEntry 8 }

cfprSysdebugManualCoreFileExportTargetFsmStageStageStatus OBJECT-TYPE
    SYNTAX       CfprFsmFsmStageStatus
    MAX-ACCESS   read-only
    STATUS       current
    DESCRIPTION
        "Cisco Firepower sysdebug:ManualCoreFileExportTargetFsmStage:stage
        Status managed object property"
    ::= { cfprSysdebugManualCoreFileExportTargetFsmStageEntry 9 }

cfprSysdebugManualCoreFileExportTargetFsmTaskTable OBJECT-TYPE
    SYNTAX           SEQUENCE OF CfprSysdebugManualCoreFileExportTargetFsmTaskEntry
    MAX-ACCESS       not-accessible
    STATUS           current
    DESCRIPTION
        "Cisco Firepower sysdebug:ManualCoreFileExportTargetFsmTask
        managed object table"
    ::= { cfprSysdebugObjects 30 }

cfprSysdebugManualCoreFileExportTargetFsmTaskEntry OBJECT-TYPE
    SYNTAX           CfprSysdebugManualCoreFileExportTargetFsmTaskEntry
    MAX-ACCESS       not-accessible
    STATUS           current
    DESCRIPTION
        "Entry for the cfprSysdebugManualCoreFileExportTargetFsmTaskTable table."
    INDEX { cfprSysdebugManualCoreFileExportTargetFsmTaskInstanceId }
    ::= { cfprSysdebugManualCoreFileExportTargetFsmTaskTable 1 }

CfprSysdebugManualCoreFileExportTargetFsmTaskEntry ::= SEQUENCE {
    cfprSysdebugManualCoreFileExportTargetFsmTaskInstanceId          CfprManagedObjectId,
    cfprSysdebugManualCoreFileExportTargetFsmTaskDn                  CfprManagedObjectDn,
    cfprSysdebugManualCoreFileExportTargetFsmTaskRn                  SnmpAdminString,
    cfprSysdebugManualCoreFileExportTargetFsmTaskCompletion          CfprFsmCompletion,
    cfprSysdebugManualCoreFileExportTargetFsmTaskFlags               CfprFsmFlags,
    cfprSysdebugManualCoreFileExportTargetFsmTaskItem                CfprSysdebugManualCoreFileExportTargetFsmTaskItem,
    cfprSysdebugManualCoreFileExportTargetFsmTaskSeqId               Gauge32
}

cfprSysdebugManualCoreFileExportTargetFsmTaskInstanceId OBJECT-TYPE
    SYNTAX       CfprManagedObjectId
    MAX-ACCESS   not-accessible
    STATUS       current
    DESCRIPTION
        "Instance identifier of the managed object."
    ::= { cfprSysdebugManualCoreFileExportTargetFsmTaskEntry 1 }

cfprSysdebugManualCoreFileExportTargetFsmTaskDn OBJECT-TYPE
    SYNTAX       CfprManagedObjectDn
    MAX-ACCESS   read-only
    STATUS       current
    DESCRIPTION
        "Cisco Firepower sysdebug:ManualCoreFileExportTargetFsmTask:dn
        managed object property"
    ::= { cfprSysdebugManualCoreFileExportTargetFsmTaskEntry 2 }

cfprSysdebugManualCoreFileExportTargetFsmTaskRn OBJECT-TYPE
    SYNTAX       SnmpAdminString
    MAX-ACCESS   read-only
    STATUS       current
    DESCRIPTION
        "Cisco Firepower sysdebug:ManualCoreFileExportTargetFsmTask:rn
        managed object property"
    ::= { cfprSysdebugManualCoreFileExportTargetFsmTaskEntry 3 }

cfprSysdebugManualCoreFileExportTargetFsmTaskCompletion OBJECT-TYPE
    SYNTAX       CfprFsmCompletion
    MAX-ACCESS   read-only
    STATUS       current
    DESCRIPTION
        "Cisco Firepower sysdebug:ManualCoreFileExportTargetFsmTask:comple
        tion managed object property"
    ::= { cfprSysdebugManualCoreFileExportTargetFsmTaskEntry 4 }

cfprSysdebugManualCoreFileExportTargetFsmTaskFlags OBJECT-TYPE
    SYNTAX       CfprFsmFlags
    MAX-ACCESS   read-only
    STATUS       current
    DESCRIPTION
        "Cisco Firepower sysdebug:ManualCoreFileExportTargetFsmTask:flags
        managed object property"
    ::= { cfprSysdebugManualCoreFileExportTargetFsmTaskEntry 5 }

cfprSysdebugManualCoreFileExportTargetFsmTaskItem OBJECT-TYPE
    SYNTAX       CfprSysdebugManualCoreFileExportTargetFsmTaskItem
    MAX-ACCESS   read-only
    STATUS       current
    DESCRIPTION
        "Cisco Firepower sysdebug:ManualCoreFileExportTargetFsmTask:item
        managed object property"
    ::= { cfprSysdebugManualCoreFileExportTargetFsmTaskEntry 6 }

cfprSysdebugManualCoreFileExportTargetFsmTaskSeqId OBJECT-TYPE
    SYNTAX       Gauge32
    MAX-ACCESS   read-only
    STATUS       current
    DESCRIPTION
        "Cisco Firepower sysdebug:ManualCoreFileExportTargetFsmTask:seqId
        managed object property"
    ::= { cfprSysdebugManualCoreFileExportTargetFsmTaskEntry 7 }

cfprSysdebugTechSupFileRepositoryTable OBJECT-TYPE
    SYNTAX           SEQUENCE OF CfprSysdebugTechSupFileRepositoryEntry
    MAX-ACCESS       not-accessible
    STATUS           current
    DESCRIPTION
        "Cisco Firepower sysdebug:TechSupFileRepository
        managed object table"
    ::= { cfprSysdebugObjects 31 }

cfprSysdebugTechSupFileRepositoryEntry OBJECT-TYPE
    SYNTAX           CfprSysdebugTechSupFileRepositoryEntry
    MAX-ACCESS       not-accessible
    STATUS           current
    DESCRIPTION
        "Entry for the cfprSysdebugTechSupFileRepositoryTable table."
    INDEX { cfprSysdebugTechSupFileRepositoryInstanceId }
    ::= { cfprSysdebugTechSupFileRepositoryTable 1 }

CfprSysdebugTechSupFileRepositoryEntry ::= SEQUENCE {
    cfprSysdebugTechSupFileRepositoryInstanceId                      CfprManagedObjectId,
    cfprSysdebugTechSupFileRepositoryDn                              CfprManagedObjectDn,
    cfprSysdebugTechSupFileRepositoryRn                              SnmpAdminString
}

cfprSysdebugTechSupFileRepositoryInstanceId OBJECT-TYPE
    SYNTAX       CfprManagedObjectId
    MAX-ACCESS   not-accessible
    STATUS       current
    DESCRIPTION
        "Instance identifier of the managed object."
    ::= { cfprSysdebugTechSupFileRepositoryEntry 1 }

cfprSysdebugTechSupFileRepositoryDn OBJECT-TYPE
    SYNTAX       CfprManagedObjectDn
    MAX-ACCESS   read-only
    STATUS       current
    DESCRIPTION
        "Cisco Firepower sysdebug:TechSupFileRepository:dn
        managed object property"
    ::= { cfprSysdebugTechSupFileRepositoryEntry 2 }

cfprSysdebugTechSupFileRepositoryRn OBJECT-TYPE
    SYNTAX       SnmpAdminString
    MAX-ACCESS   read-only
    STATUS       current
    DESCRIPTION
        "Cisco Firepower sysdebug:TechSupFileRepository:rn
        managed object property"
    ::= { cfprSysdebugTechSupFileRepositoryEntry 3 }

cfprSysdebugTechSupportTable OBJECT-TYPE
    SYNTAX           SEQUENCE OF CfprSysdebugTechSupportEntry
    MAX-ACCESS       not-accessible
    STATUS           current
    DESCRIPTION
        "Cisco Firepower sysdebug:TechSupport managed object table"
    ::= { cfprSysdebugObjects 32 }

cfprSysdebugTechSupportEntry OBJECT-TYPE
    SYNTAX           CfprSysdebugTechSupportEntry
    MAX-ACCESS       not-accessible
    STATUS           current
    DESCRIPTION
        "Entry for the cfprSysdebugTechSupportTable table."
    INDEX { cfprSysdebugTechSupportInstanceId }
    ::= { cfprSysdebugTechSupportTable 1 }

CfprSysdebugTechSupportEntry ::= SEQUENCE {
    cfprSysdebugTechSupportInstanceId                                CfprManagedObjectId,
    cfprSysdebugTechSupportDn                                        CfprManagedObjectDn,
    cfprSysdebugTechSupportRn                                        SnmpAdminString,
    cfprSysdebugTechSupportAdminState                                CfprSysdebugTechSupportAdminState,
    cfprSysdebugTechSupportCreationTS                                Unsigned64,
    cfprSysdebugTechSupportDescr                                     SnmpAdminString,
    cfprSysdebugTechSupportFsmDescr                                  SnmpAdminString,
    cfprSysdebugTechSupportFsmPrev                                   SnmpAdminString,
    cfprSysdebugTechSupportFsmProgr                                  Gauge32,
    cfprSysdebugTechSupportFsmRmtInvErrCode                          Gauge32,
    cfprSysdebugTechSupportFsmRmtInvErrDescr                         SnmpAdminString,
    cfprSysdebugTechSupportFsmRmtInvRslt                             CfprConditionRemoteInvRslt,
    cfprSysdebugTechSupportFsmStageDescr                             SnmpAdminString,
    cfprSysdebugTechSupportFsmStamp                                  DateAndTime,
    cfprSysdebugTechSupportFsmStatus                                 SnmpAdminString,
    cfprSysdebugTechSupportFsmTry                                    Gauge32,
    cfprSysdebugTechSupportName                                      SnmpAdminString,
    cfprSysdebugTechSupportOperState                                 CfprSysdebugTechSupportOperState,
    cfprSysdebugTechSupportSize                                      Gauge32,
    cfprSysdebugTechSupportSwitchId                                  CfprNetworkSwitchId,
    cfprSysdebugTechSupportTs                                        DateAndTime,
    cfprSysdebugTechSupportUri                                       SnmpAdminString
}

cfprSysdebugTechSupportInstanceId OBJECT-TYPE
    SYNTAX       CfprManagedObjectId
    MAX-ACCESS   not-accessible
    STATUS       current
    DESCRIPTION
        "Instance identifier of the managed object."
    ::= { cfprSysdebugTechSupportEntry 1 }

cfprSysdebugTechSupportDn OBJECT-TYPE
    SYNTAX       CfprManagedObjectDn
    MAX-ACCESS   read-only
    STATUS       current
    DESCRIPTION
        "Cisco Firepower sysdebug:TechSupport:dn managed object property"
    ::= { cfprSysdebugTechSupportEntry 2 }

cfprSysdebugTechSupportRn OBJECT-TYPE
    SYNTAX       SnmpAdminString
    MAX-ACCESS   read-only
    STATUS       current
    DESCRIPTION
        "Cisco Firepower sysdebug:TechSupport:rn managed object property"
    ::= { cfprSysdebugTechSupportEntry 3 }

cfprSysdebugTechSupportAdminState OBJECT-TYPE
    SYNTAX       CfprSysdebugTechSupportAdminState
    MAX-ACCESS   read-only
    STATUS       current
    DESCRIPTION
        "Cisco Firepower sysdebug:TechSupport:adminState
        managed object property"
    ::= { cfprSysdebugTechSupportEntry 4 }

cfprSysdebugTechSupportCreationTS OBJECT-TYPE
    SYNTAX       Unsigned64
    MAX-ACCESS   read-only
    STATUS       current
    DESCRIPTION
        "Cisco Firepower sysdebug:TechSupport:creationTS
        managed object property"
    ::= { cfprSysdebugTechSupportEntry 5 }

cfprSysdebugTechSupportDescr OBJECT-TYPE
    SYNTAX       SnmpAdminString
    MAX-ACCESS   read-only
    STATUS       current
    DESCRIPTION
        "Cisco Firepower sysdebug:TechSupport:descr managed
        object property"
    ::= { cfprSysdebugTechSupportEntry 6 }

cfprSysdebugTechSupportFsmDescr OBJECT-TYPE
    SYNTAX       SnmpAdminString
    MAX-ACCESS   read-only
    STATUS       current
    DESCRIPTION
        "Cisco Firepower sysdebug:TechSupport:fsmDescr
        managed object property"
    ::= { cfprSysdebugTechSupportEntry 7 }

cfprSysdebugTechSupportFsmPrev OBJECT-TYPE
    SYNTAX       SnmpAdminString
    MAX-ACCESS   read-only
    STATUS       current
    DESCRIPTION
        "Cisco Firepower sysdebug:TechSupport:fsmPrev managed
        object property"
    ::= { cfprSysdebugTechSupportEntry 8 }

cfprSysdebugTechSupportFsmProgr OBJECT-TYPE
    SYNTAX       Gauge32
    MAX-ACCESS   read-only
    STATUS       current
    DESCRIPTION
        "Cisco Firepower sysdebug:TechSupport:fsmProgr
        managed object property"
    ::= { cfprSysdebugTechSupportEntry 9 }

cfprSysdebugTechSupportFsmRmtInvErrCode OBJECT-TYPE
    SYNTAX       Gauge32
    MAX-ACCESS   read-only
    STATUS       current
    DESCRIPTION
        "Cisco Firepower sysdebug:TechSupport:fsmRmtInvErrCode
        managed object property"
    ::= { cfprSysdebugTechSupportEntry 10 }

cfprSysdebugTechSupportFsmRmtInvErrDescr OBJECT-TYPE
    SYNTAX       SnmpAdminString
    MAX-ACCESS   read-only
    STATUS       current
    DESCRIPTION
        "Cisco Firepower sysdebug:TechSupport:fsmRmtInvErrDescr
        managed object property"
    ::= { cfprSysdebugTechSupportEntry 11 }

cfprSysdebugTechSupportFsmRmtInvRslt OBJECT-TYPE
    SYNTAX       CfprConditionRemoteInvRslt
    MAX-ACCESS   read-only
    STATUS       current
    DESCRIPTION
        "Cisco Firepower sysdebug:TechSupport:fsmRmtInvRslt
        managed object property"
    ::= { cfprSysdebugTechSupportEntry 12 }

cfprSysdebugTechSupportFsmStageDescr OBJECT-TYPE
    SYNTAX       SnmpAdminString
    MAX-ACCESS   read-only
    STATUS       current
    DESCRIPTION
        "Cisco Firepower sysdebug:TechSupport:fsmStageDescr
        managed object property"
    ::= { cfprSysdebugTechSupportEntry 13 }

cfprSysdebugTechSupportFsmStamp OBJECT-TYPE
    SYNTAX       DateAndTime
    MAX-ACCESS   read-only
    STATUS       current
    DESCRIPTION
        "Cisco Firepower sysdebug:TechSupport:fsmStamp
        managed object property"
    ::= { cfprSysdebugTechSupportEntry 14 }

cfprSysdebugTechSupportFsmStatus OBJECT-TYPE
    SYNTAX       SnmpAdminString
    MAX-ACCESS   read-only
    STATUS       current
    DESCRIPTION
        "Cisco Firepower sysdebug:TechSupport:fsmStatus
        managed object property"
    ::= { cfprSysdebugTechSupportEntry 15 }

cfprSysdebugTechSupportFsmTry OBJECT-TYPE
    SYNTAX       Gauge32
    MAX-ACCESS   read-only
    STATUS       current
    DESCRIPTION
        "Cisco Firepower sysdebug:TechSupport:fsmTry managed
        object property"
    ::= { cfprSysdebugTechSupportEntry 16 }

cfprSysdebugTechSupportName OBJECT-TYPE
    SYNTAX       SnmpAdminString
    MAX-ACCESS   read-only
    STATUS       current
    DESCRIPTION
        "Cisco Firepower sysdebug:TechSupport:name managed
        object property"
    ::= { cfprSysdebugTechSupportEntry 17 }

cfprSysdebugTechSupportOperState OBJECT-TYPE
    SYNTAX       CfprSysdebugTechSupportOperState
    MAX-ACCESS   read-only
    STATUS       current
    DESCRIPTION
        "Cisco Firepower sysdebug:TechSupport:operState
        managed object property"
    ::= { cfprSysdebugTechSupportEntry 18 }

cfprSysdebugTechSupportSize OBJECT-TYPE
    SYNTAX       Gauge32
    MAX-ACCESS   read-only
    STATUS       current
    DESCRIPTION
        "Cisco Firepower sysdebug:TechSupport:size managed
        object property"
    ::= { cfprSysdebugTechSupportEntry 19 }

cfprSysdebugTechSupportSwitchId OBJECT-TYPE
    SYNTAX       CfprNetworkSwitchId
    MAX-ACCESS   read-only
    STATUS       current
    DESCRIPTION
        "Cisco Firepower sysdebug:TechSupport:switchId
        managed object property"
    ::= { cfprSysdebugTechSupportEntry 20 }

cfprSysdebugTechSupportTs OBJECT-TYPE
    SYNTAX       DateAndTime
    MAX-ACCESS   read-only
    STATUS       current
    DESCRIPTION
        "Cisco Firepower sysdebug:TechSupport:ts managed object property"
    ::= { cfprSysdebugTechSupportEntry 21 }

cfprSysdebugTechSupportUri OBJECT-TYPE
    SYNTAX       SnmpAdminString
    MAX-ACCESS   read-only
    STATUS       current
    DESCRIPTION
        "Cisco Firepower sysdebug:TechSupport:uri managed object property"
    ::= { cfprSysdebugTechSupportEntry 22 }

cfprSysdebugTechSupportCmdOptTable OBJECT-TYPE
    SYNTAX           SEQUENCE OF CfprSysdebugTechSupportCmdOptEntry
    MAX-ACCESS       not-accessible
    STATUS           current
    DESCRIPTION
        "Cisco Firepower sysdebug:TechSupportCmdOpt managed object table"
    ::= { cfprSysdebugObjects 33 }

cfprSysdebugTechSupportCmdOptEntry OBJECT-TYPE
    SYNTAX           CfprSysdebugTechSupportCmdOptEntry
    MAX-ACCESS       not-accessible
    STATUS           current
    DESCRIPTION
        "Entry for the cfprSysdebugTechSupportCmdOptTable table."
    INDEX { cfprSysdebugTechSupportCmdOptInstanceId }
    ::= { cfprSysdebugTechSupportCmdOptTable 1 }

CfprSysdebugTechSupportCmdOptEntry ::= SEQUENCE {
    cfprSysdebugTechSupportCmdOptInstanceId                          CfprManagedObjectId,
    cfprSysdebugTechSupportCmdOptDn                                  CfprManagedObjectDn,
    cfprSysdebugTechSupportCmdOptRn                                  SnmpAdminString,
    cfprSysdebugTechSupportCmdOptChassisCimcId                       Gauge32,
    cfprSysdebugTechSupportCmdOptChassisId                           Gauge32,
    cfprSysdebugTechSupportCmdOptChassisIomId                        Gauge32,
    cfprSysdebugTechSupportCmdOptCimcAdapterId                       Gauge32,
    cfprSysdebugTechSupportCmdOptFabExtId                            Gauge32,
    cfprSysdebugTechSupportCmdOptMajorOptType                        CfprSysdebugTSCmdOptMajorType,
    cfprSysdebugTechSupportCmdOptRackServerAdapterId                 Gauge32,
    cfprSysdebugTechSupportCmdOptRackServerId                        Gauge32
}

cfprSysdebugTechSupportCmdOptInstanceId OBJECT-TYPE
    SYNTAX       CfprManagedObjectId
    MAX-ACCESS   not-accessible
    STATUS       current
    DESCRIPTION
        "Instance identifier of the managed object."
    ::= { cfprSysdebugTechSupportCmdOptEntry 1 }

cfprSysdebugTechSupportCmdOptDn OBJECT-TYPE
    SYNTAX       CfprManagedObjectDn
    MAX-ACCESS   read-only
    STATUS       current
    DESCRIPTION
        "Cisco Firepower sysdebug:TechSupportCmdOpt:dn
        managed object property"
    ::= { cfprSysdebugTechSupportCmdOptEntry 2 }

cfprSysdebugTechSupportCmdOptRn OBJECT-TYPE
    SYNTAX       SnmpAdminString
    MAX-ACCESS   read-only
    STATUS       current
    DESCRIPTION
        "Cisco Firepower sysdebug:TechSupportCmdOpt:rn
        managed object property"
    ::= { cfprSysdebugTechSupportCmdOptEntry 3 }

cfprSysdebugTechSupportCmdOptChassisCimcId OBJECT-TYPE
    SYNTAX       Gauge32
    MAX-ACCESS   read-only
    STATUS       current
    DESCRIPTION
        "Cisco Firepower sysdebug:TechSupportCmdOpt:chassisCimcId
        managed object property"
    ::= { cfprSysdebugTechSupportCmdOptEntry 4 }

cfprSysdebugTechSupportCmdOptChassisId OBJECT-TYPE
    SYNTAX       Gauge32
    MAX-ACCESS   read-only
    STATUS       current
    DESCRIPTION
        "Cisco Firepower sysdebug:TechSupportCmdOpt:chassisId
        managed object property"
    ::= { cfprSysdebugTechSupportCmdOptEntry 5 }

cfprSysdebugTechSupportCmdOptChassisIomId OBJECT-TYPE
    SYNTAX       Gauge32
    MAX-ACCESS   read-only
    STATUS       current
    DESCRIPTION
        "Cisco Firepower sysdebug:TechSupportCmdOpt:chassisIomId
        managed object property"
    ::= { cfprSysdebugTechSupportCmdOptEntry 6 }

cfprSysdebugTechSupportCmdOptCimcAdapterId OBJECT-TYPE
    SYNTAX       Gauge32
    MAX-ACCESS   read-only
    STATUS       current
    DESCRIPTION
        "Cisco Firepower sysdebug:TechSupportCmdOpt:cimcAdapterId
        managed object property"
    ::= { cfprSysdebugTechSupportCmdOptEntry 7 }

cfprSysdebugTechSupportCmdOptFabExtId OBJECT-TYPE
    SYNTAX       Gauge32
    MAX-ACCESS   read-only
    STATUS       current
    DESCRIPTION
        "Cisco Firepower sysdebug:TechSupportCmdOpt:fabExtId
        managed object property"
    ::= { cfprSysdebugTechSupportCmdOptEntry 8 }

cfprSysdebugTechSupportCmdOptMajorOptType OBJECT-TYPE
    SYNTAX       CfprSysdebugTSCmdOptMajorType
    MAX-ACCESS   read-only
    STATUS       current
    DESCRIPTION
        "Cisco Firepower sysdebug:TechSupportCmdOpt:majorOptType
        managed object property"
    ::= { cfprSysdebugTechSupportCmdOptEntry 9 }

cfprSysdebugTechSupportCmdOptRackServerAdapterId OBJECT-TYPE
    SYNTAX       Gauge32
    MAX-ACCESS   read-only
    STATUS       current
    DESCRIPTION
        "Cisco Firepower sysdebug:TechSupportCmdOpt:rackServerAdapterId
        managed object property"
    ::= { cfprSysdebugTechSupportCmdOptEntry 10 }

cfprSysdebugTechSupportCmdOptRackServerId OBJECT-TYPE
    SYNTAX       Gauge32
    MAX-ACCESS   read-only
    STATUS       current
    DESCRIPTION
        "Cisco Firepower sysdebug:TechSupportCmdOpt:rackServerId
        managed object property"
    ::= { cfprSysdebugTechSupportCmdOptEntry 11 }

cfprSysdebugTechSupportFsmTable OBJECT-TYPE
    SYNTAX           SEQUENCE OF CfprSysdebugTechSupportFsmEntry
    MAX-ACCESS       not-accessible
    STATUS           current
    DESCRIPTION
        "Cisco Firepower sysdebug:TechSupportFsm managed object table"
    ::= { cfprSysdebugObjects 34 }

cfprSysdebugTechSupportFsmEntry OBJECT-TYPE
    SYNTAX           CfprSysdebugTechSupportFsmEntry
    MAX-ACCESS       not-accessible
    STATUS           current
    DESCRIPTION
        "Entry for the cfprSysdebugTechSupportFsmTable table."
    INDEX { cfprSysdebugTechSupportFsmInstanceId }
    ::= { cfprSysdebugTechSupportFsmTable 1 }

CfprSysdebugTechSupportFsmEntry ::= SEQUENCE {
    cfprSysdebugTechSupportFsmInstanceId                             CfprManagedObjectId,
    cfprSysdebugTechSupportFsmDn                                     CfprManagedObjectDn,
    cfprSysdebugTechSupportFsmRn                                     SnmpAdminString,
    cfprSysdebugTechSupportFsmCompletionTime                         DateAndTime,
    cfprSysdebugTechSupportFsmCurrentFsm                             CfprSysdebugTechSupportFsmCurrentFsm,
    cfprSysdebugTechSupportFsmDescrData                              SnmpAdminString,
    cfprSysdebugTechSupportFsmFsmStatus                              CfprFsmFsmStageStatus,
    cfprSysdebugTechSupportFsmProgress                               Gauge32,
    cfprSysdebugTechSupportFsmRmtErrCode                             Gauge32,
    cfprSysdebugTechSupportFsmRmtErrDescr                            SnmpAdminString,
    cfprSysdebugTechSupportFsmRmtRslt                                CfprConditionRemoteInvRslt
}

cfprSysdebugTechSupportFsmInstanceId OBJECT-TYPE
    SYNTAX       CfprManagedObjectId
    MAX-ACCESS   not-accessible
    STATUS       current
    DESCRIPTION
        "Instance identifier of the managed object."
    ::= { cfprSysdebugTechSupportFsmEntry 1 }

cfprSysdebugTechSupportFsmDn OBJECT-TYPE
    SYNTAX       CfprManagedObjectDn
    MAX-ACCESS   read-only
    STATUS       current
    DESCRIPTION
        "Cisco Firepower sysdebug:TechSupportFsm:dn managed
        object property"
    ::= { cfprSysdebugTechSupportFsmEntry 2 }

cfprSysdebugTechSupportFsmRn OBJECT-TYPE
    SYNTAX       SnmpAdminString
    MAX-ACCESS   read-only
    STATUS       current
    DESCRIPTION
        "Cisco Firepower sysdebug:TechSupportFsm:rn managed
        object property"
    ::= { cfprSysdebugTechSupportFsmEntry 3 }

cfprSysdebugTechSupportFsmCompletionTime OBJECT-TYPE
    SYNTAX       DateAndTime
    MAX-ACCESS   read-only
    STATUS       current
    DESCRIPTION
        "Cisco Firepower sysdebug:TechSupportFsm:completionTime
        managed object property"
    ::= { cfprSysdebugTechSupportFsmEntry 4 }

cfprSysdebugTechSupportFsmCurrentFsm OBJECT-TYPE
    SYNTAX       CfprSysdebugTechSupportFsmCurrentFsm
    MAX-ACCESS   read-only
    STATUS       current
    DESCRIPTION
        "Cisco Firepower sysdebug:TechSupportFsm:currentFsm
        managed object property"
    ::= { cfprSysdebugTechSupportFsmEntry 5 }

cfprSysdebugTechSupportFsmDescrData OBJECT-TYPE
    SYNTAX       SnmpAdminString
    MAX-ACCESS   read-only
    STATUS       current
    DESCRIPTION
        "Cisco Firepower sysdebug:TechSupportFsm:descr
        managed object property"
    ::= { cfprSysdebugTechSupportFsmEntry 6 }

cfprSysdebugTechSupportFsmFsmStatus OBJECT-TYPE
    SYNTAX       CfprFsmFsmStageStatus
    MAX-ACCESS   read-only
    STATUS       current
    DESCRIPTION
        "Cisco Firepower sysdebug:TechSupportFsm:fsmStatus
        managed object property"
    ::= { cfprSysdebugTechSupportFsmEntry 7 }

cfprSysdebugTechSupportFsmProgress OBJECT-TYPE
    SYNTAX       Gauge32
    MAX-ACCESS   read-only
    STATUS       current
    DESCRIPTION
        "Cisco Firepower sysdebug:TechSupportFsm:progress
        managed object property"
    ::= { cfprSysdebugTechSupportFsmEntry 8 }

cfprSysdebugTechSupportFsmRmtErrCode OBJECT-TYPE
    SYNTAX       Gauge32
    MAX-ACCESS   read-only
    STATUS       current
    DESCRIPTION
        "Cisco Firepower sysdebug:TechSupportFsm:rmtErrCode
        managed object property"
    ::= { cfprSysdebugTechSupportFsmEntry 9 }

cfprSysdebugTechSupportFsmRmtErrDescr OBJECT-TYPE
    SYNTAX       SnmpAdminString
    MAX-ACCESS   read-only
    STATUS       current
    DESCRIPTION
        "Cisco Firepower sysdebug:TechSupportFsm:rmtErrDescr
        managed object property"
    ::= { cfprSysdebugTechSupportFsmEntry 10 }

cfprSysdebugTechSupportFsmRmtRslt OBJECT-TYPE
    SYNTAX       CfprConditionRemoteInvRslt
    MAX-ACCESS   read-only
    STATUS       current
    DESCRIPTION
        "Cisco Firepower sysdebug:TechSupportFsm:rmtRslt
        managed object property"
    ::= { cfprSysdebugTechSupportFsmEntry 11 }

cfprSysdebugTechSupportFsmStageTable OBJECT-TYPE
    SYNTAX           SEQUENCE OF CfprSysdebugTechSupportFsmStageEntry
    MAX-ACCESS       not-accessible
    STATUS           current
    DESCRIPTION
        "Cisco Firepower sysdebug:TechSupportFsmStage managed
        object table"
    ::= { cfprSysdebugObjects 35 }

cfprSysdebugTechSupportFsmStageEntry OBJECT-TYPE
    SYNTAX           CfprSysdebugTechSupportFsmStageEntry
    MAX-ACCESS       not-accessible
    STATUS           current
    DESCRIPTION
        "Entry for the cfprSysdebugTechSupportFsmStageTable table."
    INDEX { cfprSysdebugTechSupportFsmStageInstanceId }
    ::= { cfprSysdebugTechSupportFsmStageTable 1 }

CfprSysdebugTechSupportFsmStageEntry ::= SEQUENCE {
    cfprSysdebugTechSupportFsmStageInstanceId                        CfprManagedObjectId,
    cfprSysdebugTechSupportFsmStageDn                                CfprManagedObjectDn,
    cfprSysdebugTechSupportFsmStageRn                                SnmpAdminString,
    cfprSysdebugTechSupportFsmStageDescrData                         SnmpAdminString,
    cfprSysdebugTechSupportFsmStageLastUpdateTime                    DateAndTime,
    cfprSysdebugTechSupportFsmStageName                              CfprSysdebugTechSupportFsmStageName,
    cfprSysdebugTechSupportFsmStageOrder                             Gauge32,
    cfprSysdebugTechSupportFsmStageRetry                             Gauge32,
    cfprSysdebugTechSupportFsmStageStageStatus                       CfprFsmFsmStageStatus
}

cfprSysdebugTechSupportFsmStageInstanceId OBJECT-TYPE
    SYNTAX       CfprManagedObjectId
    MAX-ACCESS   not-accessible
    STATUS       current
    DESCRIPTION
        "Instance identifier of the managed object."
    ::= { cfprSysdebugTechSupportFsmStageEntry 1 }

cfprSysdebugTechSupportFsmStageDn OBJECT-TYPE
    SYNTAX       CfprManagedObjectDn
    MAX-ACCESS   read-only
    STATUS       current
    DESCRIPTION
        "Cisco Firepower sysdebug:TechSupportFsmStage:dn
        managed object property"
    ::= { cfprSysdebugTechSupportFsmStageEntry 2 }

cfprSysdebugTechSupportFsmStageRn OBJECT-TYPE
    SYNTAX       SnmpAdminString
    MAX-ACCESS   read-only
    STATUS       current
    DESCRIPTION
        "Cisco Firepower sysdebug:TechSupportFsmStage:rn
        managed object property"
    ::= { cfprSysdebugTechSupportFsmStageEntry 3 }

cfprSysdebugTechSupportFsmStageDescrData OBJECT-TYPE
    SYNTAX       SnmpAdminString
    MAX-ACCESS   read-only
    STATUS       current
    DESCRIPTION
        "Cisco Firepower sysdebug:TechSupportFsmStage:descr
        managed object property"
    ::= { cfprSysdebugTechSupportFsmStageEntry 4 }

cfprSysdebugTechSupportFsmStageLastUpdateTime OBJECT-TYPE
    SYNTAX       DateAndTime
    MAX-ACCESS   read-only
    STATUS       current
    DESCRIPTION
        "Cisco Firepower sysdebug:TechSupportFsmStage:lastUpdateTime
        managed object property"
    ::= { cfprSysdebugTechSupportFsmStageEntry 5 }

cfprSysdebugTechSupportFsmStageName OBJECT-TYPE
    SYNTAX       CfprSysdebugTechSupportFsmStageName
    MAX-ACCESS   read-only
    STATUS       current
    DESCRIPTION
        "Cisco Firepower sysdebug:TechSupportFsmStage:name
        managed object property"
    ::= { cfprSysdebugTechSupportFsmStageEntry 6 }

cfprSysdebugTechSupportFsmStageOrder OBJECT-TYPE
    SYNTAX       Gauge32
    MAX-ACCESS   read-only
    STATUS       current
    DESCRIPTION
        "Cisco Firepower sysdebug:TechSupportFsmStage:order
        managed object property"
    ::= { cfprSysdebugTechSupportFsmStageEntry 7 }

cfprSysdebugTechSupportFsmStageRetry OBJECT-TYPE
    SYNTAX       Gauge32
    MAX-ACCESS   read-only
    STATUS       current
    DESCRIPTION
        "Cisco Firepower sysdebug:TechSupportFsmStage:retry
        managed object property"
    ::= { cfprSysdebugTechSupportFsmStageEntry 8 }

cfprSysdebugTechSupportFsmStageStageStatus OBJECT-TYPE
    SYNTAX       CfprFsmFsmStageStatus
    MAX-ACCESS   read-only
    STATUS       current
    DESCRIPTION
        "Cisco Firepower sysdebug:TechSupportFsmStage:stageStatus
        managed object property"
    ::= { cfprSysdebugTechSupportFsmStageEntry 9 }

cfprSysdebugTechSupportFsmTaskTable OBJECT-TYPE
    SYNTAX           SEQUENCE OF CfprSysdebugTechSupportFsmTaskEntry
    MAX-ACCESS       not-accessible
    STATUS           current
    DESCRIPTION
        "Cisco Firepower sysdebug:TechSupportFsmTask managed object table"
    ::= { cfprSysdebugObjects 36 }

cfprSysdebugTechSupportFsmTaskEntry OBJECT-TYPE
    SYNTAX           CfprSysdebugTechSupportFsmTaskEntry
    MAX-ACCESS       not-accessible
    STATUS           current
    DESCRIPTION
        "Entry for the cfprSysdebugTechSupportFsmTaskTable table."
    INDEX { cfprSysdebugTechSupportFsmTaskInstanceId }
    ::= { cfprSysdebugTechSupportFsmTaskTable 1 }

CfprSysdebugTechSupportFsmTaskEntry ::= SEQUENCE {
    cfprSysdebugTechSupportFsmTaskInstanceId                         CfprManagedObjectId,
    cfprSysdebugTechSupportFsmTaskDn                                 CfprManagedObjectDn,
    cfprSysdebugTechSupportFsmTaskRn                                 SnmpAdminString,
    cfprSysdebugTechSupportFsmTaskCompletion                         CfprFsmCompletion,
    cfprSysdebugTechSupportFsmTaskFlags                              CfprFsmFlags,
    cfprSysdebugTechSupportFsmTaskItem                               CfprSysdebugTechSupportFsmTaskItem,
    cfprSysdebugTechSupportFsmTaskSeqId                              Gauge32
}

cfprSysdebugTechSupportFsmTaskInstanceId OBJECT-TYPE
    SYNTAX       CfprManagedObjectId
    MAX-ACCESS   not-accessible
    STATUS       current
    DESCRIPTION
        "Instance identifier of the managed object."
    ::= { cfprSysdebugTechSupportFsmTaskEntry 1 }

cfprSysdebugTechSupportFsmTaskDn OBJECT-TYPE
    SYNTAX       CfprManagedObjectDn
    MAX-ACCESS   read-only
    STATUS       current
    DESCRIPTION
        "Cisco Firepower sysdebug:TechSupportFsmTask:dn
        managed object property"
    ::= { cfprSysdebugTechSupportFsmTaskEntry 2 }

cfprSysdebugTechSupportFsmTaskRn OBJECT-TYPE
    SYNTAX       SnmpAdminString
    MAX-ACCESS   read-only
    STATUS       current
    DESCRIPTION
        "Cisco Firepower sysdebug:TechSupportFsmTask:rn
        managed object property"
    ::= { cfprSysdebugTechSupportFsmTaskEntry 3 }

cfprSysdebugTechSupportFsmTaskCompletion OBJECT-TYPE
    SYNTAX       CfprFsmCompletion
    MAX-ACCESS   read-only
    STATUS       current
    DESCRIPTION
        "Cisco Firepower sysdebug:TechSupportFsmTask:completion
        managed object property"
    ::= { cfprSysdebugTechSupportFsmTaskEntry 4 }

cfprSysdebugTechSupportFsmTaskFlags OBJECT-TYPE
    SYNTAX       CfprFsmFlags
    MAX-ACCESS   read-only
    STATUS       current
    DESCRIPTION
        "Cisco Firepower sysdebug:TechSupportFsmTask:flags
        managed object property"
    ::= { cfprSysdebugTechSupportFsmTaskEntry 5 }

cfprSysdebugTechSupportFsmTaskItem OBJECT-TYPE
    SYNTAX       CfprSysdebugTechSupportFsmTaskItem
    MAX-ACCESS   read-only
    STATUS       current
    DESCRIPTION
        "Cisco Firepower sysdebug:TechSupportFsmTask:item
        managed object property"
    ::= { cfprSysdebugTechSupportFsmTaskEntry 6 }

cfprSysdebugTechSupportFsmTaskSeqId OBJECT-TYPE
    SYNTAX       Gauge32
    MAX-ACCESS   read-only
    STATUS       current
    DESCRIPTION
        "Cisco Firepower sysdebug:TechSupportFsmTask:seqId
        managed object property"
    ::= { cfprSysdebugTechSupportFsmTaskEntry 7 }

END
