-- *********************************************************************
-- CISCO-FIREPOWER-AAA-MIB.my
--
-- MIB representation of the Cisco Firepower
-- AAA management information model package
--
-- Created March 2020 by Charles Bullis
--
-- Copyright (c) 2005-2020 Cisco Systems, Inc. All rights reserved.
--
-- *********************************************************************

CISCO-FIREPOWER-AAA-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIBObjects,
    CfprManagedObjectId,
    CfprManagedObjectDn
        FROM CISCO-FIREPOWER-MIB
    CfprAaaAccess,
    CfprAaaAccountStatus,
    CfprAaaAuthRealmFsmCurrentFsm,
    CfprAaaAuthRealmFsmStageName,
    CfprAaaCimcSessionType,
    CfprAaaCipherMode,
    CfprAaaClear,
    CfprAaaConfigState,
    CfprAaaDomainAuthRealm,
    CfprAaaEpAccess,
    CfprAaaEpFsmCurrentFsm,
    CfprAaaEpFsmStageName,
    CfprAaaEpFsmTaskItem,
    CfprAaaExtMgmtAccess,
    CfprAaaIpmiOverLan,
    CfprAaaLdapEpFsmCurrentFsm,
    CfprAaaLdapEpFsmStageName,
    CfprAaaLdapGroupRuleAuthorization,
    CfprAaaLdapGroupRuleTraversal,
    CfprAaaLdapVendor,
    CfprAaaNoRolePolicy,
    CfprAaaPwdPolicy,
    CfprAaaRadiusEpFsmCurrentFsm,
    CfprAaaRadiusEpFsmStageName,
    CfprAaaRadiusService,
    CfprAaaRealm,
    CfprAaaRealmFsmCurrentFsm,
    CfprAaaRealmFsmStageName,
    CfprAaaRealmFsmTaskItem,
    CfprAaaRevokePolicy,
    CfprAaaSession,
    CfprAaaSessionState,
    CfprAaaSshStr,
    CfprAaaTacacsPlusEpFsmCurrentFsm,
    CfprAaaTacacsPlusEpFsmStageName,
    CfprAaaUserEpFsmCurrentFsm,
    CfprAaaUserEpFsmStageName,
    CfprAaaUserEpFsmTaskItem,
    CfprAaaUserInterface,
    CfprCommTlsVerType,
    CfprConditionActionIndicator,
    CfprConditionCause,
    CfprConditionCode,
    CfprConditionRemoteInvRslt,
    CfprConditionSeverity,
    CfprFsmCompletion,
    CfprFsmFlags,
    CfprFsmFsmStageStatus,
    CfprNetworkSwitchId,
    CfprPolicyPolicyOwner
        FROM CISCO-FIREPOWER-TC-MIB;

cfprAaaObjects MODULE-IDENTITY
    LAST-UPDATED    "202003100000Z"
    ORGANIZATION    "Cisco Systems Inc."
    CONTACT-INFO
        "Cisco Systems
        Customer Service

        Postal: 170 W Tasman Drive
        San Jose, CA  95134
        USA

        Tel: +1 800 553-NETS

        E-mail: firepower-mibs@cisco.com"
    DESCRIPTION
        "MIB representation of the Cisco Firepower
        AAA management information model package"
    ::= { ciscoFirepowerMIBObjects 2 }

cfprAaaAuthRealmTable OBJECT-TYPE
    SYNTAX           SEQUENCE OF CfprAaaAuthRealmEntry
    MAX-ACCESS       not-accessible
    STATUS           current
    DESCRIPTION
        "Cisco Firepower aaa:AuthRealm managed object table"
    ::= { cfprAaaObjects 1 }

cfprAaaAuthRealmEntry OBJECT-TYPE
    SYNTAX           CfprAaaAuthRealmEntry
    MAX-ACCESS       not-accessible
    STATUS           current
    DESCRIPTION
        "Entry for the cfprAaaAuthRealmTable table."
    INDEX { cfprAaaAuthRealmInstanceId }
    ::= { cfprAaaAuthRealmTable 1 }

CfprAaaAuthRealmEntry ::= SEQUENCE {
    cfprAaaAuthRealmInstanceId                                       CfprManagedObjectId,
    cfprAaaAuthRealmDn                                               CfprManagedObjectDn,
    cfprAaaAuthRealmRn                                               SnmpAdminString,
    cfprAaaAuthRealmConLogin                                         CfprAaaRealm,
    cfprAaaAuthRealmDefLogin                                         CfprAaaRealm,
    cfprAaaAuthRealmDefRolePolicy                                    CfprAaaNoRolePolicy,
    cfprAaaAuthRealmDescr                                            SnmpAdminString,
    cfprAaaAuthRealmFsmDescr                                         SnmpAdminString,
    cfprAaaAuthRealmFsmPrev                                          SnmpAdminString,
    cfprAaaAuthRealmFsmProgr                                         Gauge32,
    cfprAaaAuthRealmFsmRmtInvErrCode                                 Gauge32,
    cfprAaaAuthRealmFsmRmtInvErrDescr                                SnmpAdminString,
    cfprAaaAuthRealmFsmRmtInvRslt                                    CfprConditionRemoteInvRslt,
    cfprAaaAuthRealmFsmStageDescr                                    SnmpAdminString,
    cfprAaaAuthRealmFsmStamp                                         DateAndTime,
    cfprAaaAuthRealmFsmStatus                                        SnmpAdminString,
    cfprAaaAuthRealmFsmTry                                           Gauge32,
    cfprAaaAuthRealmIntId                                            SnmpAdminString,
    cfprAaaAuthRealmName                                             SnmpAdminString,
    cfprAaaAuthRealmPolicyLevel                                      Gauge32,
    cfprAaaAuthRealmPolicyOwner                                      CfprPolicyPolicyOwner
}

cfprAaaAuthRealmInstanceId OBJECT-TYPE
    SYNTAX       CfprManagedObjectId
    MAX-ACCESS   not-accessible
    STATUS       current
    DESCRIPTION
        "Instance identifier of the managed object."
    ::= { cfprAaaAuthRealmEntry 1 }

cfprAaaAuthRealmDn OBJECT-TYPE
    SYNTAX       CfprManagedObjectDn
    MAX-ACCESS   read-only
    STATUS       current
    DESCRIPTION
        "Cisco Firepower aaa:AuthRealm:dn managed object property"
    ::= { cfprAaaAuthRealmEntry 2 }

cfprAaaAuthRealmRn OBJECT-TYPE
    SYNTAX       SnmpAdminString
    MAX-ACCESS   read-only
    STATUS       current
    DESCRIPTION
        "Cisco Firepower aaa:AuthRealm:rn managed object property"
    ::= { cfprAaaAuthRealmEntry 3 }

cfprAaaAuthRealmConLogin OBJECT-TYPE
    SYNTAX       CfprAaaRealm
    MAX-ACCESS   read-only
    STATUS       current
    DESCRIPTION
        "Cisco Firepower aaa:AuthRealm:conLogin managed object property"
    ::= { cfprAaaAuthRealmEntry 4 }

cfprAaaAuthRealmDefLogin OBJECT-TYPE
    SYNTAX       CfprAaaRealm
    MAX-ACCESS   read-only
    STATUS       current
    DESCRIPTION
        "Cisco Firepower aaa:AuthRealm:defLogin managed object property"
    ::= { cfprAaaAuthRealmEntry 5 }

cfprAaaAuthRealmDefRolePolicy OBJECT-TYPE
    SYNTAX       CfprAaaNoRolePolicy
    MAX-ACCESS   read-only
    STATUS       current
    DESCRIPTION
        "Cisco Firepower aaa:AuthRealm:defRolePolicy managed
        object property"
    ::= { cfprAaaAuthRealmEntry 6 }

cfprAaaAuthRealmDescr OBJECT-TYPE
    SYNTAX       SnmpAdminString
    MAX-ACCESS   read-only
    STATUS       current
    DESCRIPTION
        "Cisco Firepower aaa:AuthRealm:descr managed object property"
    ::= { cfprAaaAuthRealmEntry 7 }

cfprAaaAuthRealmFsmDescr OBJECT-TYPE
    SYNTAX       SnmpAdminString
    MAX-ACCESS   read-only
    STATUS       current
    DESCRIPTION
        "Cisco Firepower aaa:AuthRealm:fsmDescr managed object property"
    ::= { cfprAaaAuthRealmEntry 8 }

cfprAaaAuthRealmFsmPrev OBJECT-TYPE
    SYNTAX       SnmpAdminString
    MAX-ACCESS   read-only
    STATUS       current
    DESCRIPTION
        "Cisco Firepower aaa:AuthRealm:fsmPrev managed object property"
    ::= { cfprAaaAuthRealmEntry 9 }

cfprAaaAuthRealmFsmProgr OBJECT-TYPE
    SYNTAX       Gauge32
    MAX-ACCESS   read-only
    STATUS       current
    DESCRIPTION
        "Cisco Firepower aaa:AuthRealm:fsmProgr managed object property"
    ::= { cfprAaaAuthRealmEntry 10 }

cfprAaaAuthRealmFsmRmtInvErrCode OBJECT-TYPE
    SYNTAX       Gauge32
    MAX-ACCESS   read-only
    STATUS       current
    DESCRIPTION
        "Cisco Firepower aaa:AuthRealm:fsmRmtInvErrCode
        managed object property"
    ::= { cfprAaaAuthRealmEntry 11 }

cfprAaaAuthRealmFsmRmtInvErrDescr OBJECT-TYPE
    SYNTAX       SnmpAdminString
    MAX-ACCESS   read-only
    STATUS       current
    DESCRIPTION
        "Cisco Firepower aaa:AuthRealm:fsmRmtInvErrDescr
        managed object property"
    ::= { cfprAaaAuthRealmEntry 12 }

cfprAaaAuthRealmFsmRmtInvRslt OBJECT-TYPE
    SYNTAX       CfprConditionRemoteInvRslt
    MAX-ACCESS   read-only
    STATUS       current
    DESCRIPTION
        "Cisco Firepower aaa:AuthRealm:fsmRmtInvRslt managed
        object property"
    ::= { cfprAaaAuthRealmEntry 13 }

cfprAaaAuthRealmFsmStageDescr OBJECT-TYPE
    SYNTAX       SnmpAdminString
    MAX-ACCESS   read-only
    STATUS       current
    DESCRIPTION
        "Cisco Firepower aaa:AuthRealm:fsmStageDescr managed
        object property"
    ::= { cfprAaaAuthRealmEntry 14 }

cfprAaaAuthRealmFsmStamp OBJECT-TYPE
    SYNTAX       DateAndTime
    MAX-ACCESS   read-only
    STATUS       current
    DESCRIPTION
        "Cisco Firepower aaa:AuthRealm:fsmStamp managed object property"
    ::= { cfprAaaAuthRealmEntry 15 }

cfprAaaAuthRealmFsmStatus OBJECT-TYPE
    SYNTAX       SnmpAdminString
    MAX-ACCESS   read-only
    STATUS       current
    DESCRIPTION
        "Cisco Firepower aaa:AuthRealm:fsmStatus managed object property"
    ::= { cfprAaaAuthRealmEntry 16 }

cfprAaaAuthRealmFsmTry OBJECT-TYPE
    SYNTAX       Gauge32
    MAX-ACCESS   read-only
    STATUS       current
    DESCRIPTION
        "Cisco Firepower aaa:AuthRealm:fsmTry managed object property"
    ::= { cfprAaaAuthRealmEntry 17 }

cfprAaaAuthRealmIntId OBJECT-TYPE
    SYNTAX       SnmpAdminString
    MAX-ACCESS   read-only
    STATUS       current
    DESCRIPTION
        "Cisco Firepower aaa:AuthRealm:intId managed object property"
    ::= { cfprAaaAuthRealmEntry 18 }

cfprAaaAuthRealmName OBJECT-TYPE
    SYNTAX       SnmpAdminString
    MAX-ACCESS   read-only
    STATUS       current
    DESCRIPTION
        "Cisco Firepower aaa:AuthRealm:name managed object property"
    ::= { cfprAaaAuthRealmEntry 19 }

cfprAaaAuthRealmPolicyLevel OBJECT-TYPE
    SYNTAX       Gauge32
    MAX-ACCESS   read-only
    STATUS       current
    DESCRIPTION
        "Cisco Firepower aaa:AuthRealm:policyLevel managed
        object property"
    ::= { cfprAaaAuthRealmEntry 20 }

cfprAaaAuthRealmPolicyOwner OBJECT-TYPE
    SYNTAX       CfprPolicyPolicyOwner
    MAX-ACCESS   read-only
    STATUS       current
    DESCRIPTION
        "Cisco Firepower aaa:AuthRealm:policyOwner managed
        object property"
    ::= { cfprAaaAuthRealmEntry 21 }

cfprAaaAuthRealmFsmTable OBJECT-TYPE
    SYNTAX           SEQUENCE OF CfprAaaAuthRealmFsmEntry
    MAX-ACCESS       not-accessible
    STATUS           current
    DESCRIPTION
        "Cisco Firepower aaa:AuthRealmFsm managed object table"
    ::= { cfprAaaObjects 2 }

cfprAaaAuthRealmFsmEntry OBJECT-TYPE
    SYNTAX           CfprAaaAuthRealmFsmEntry
    MAX-ACCESS       not-accessible
    STATUS           current
    DESCRIPTION
        "Entry for the cfprAaaAuthRealmFsmTable table."
    INDEX { cfprAaaAuthRealmFsmInstanceId }
    ::= { cfprAaaAuthRealmFsmTable 1 }

CfprAaaAuthRealmFsmEntry ::= SEQUENCE {
    cfprAaaAuthRealmFsmInstanceId                                    CfprManagedObjectId,
    cfprAaaAuthRealmFsmDn                                            CfprManagedObjectDn,
    cfprAaaAuthRealmFsmRn                                            SnmpAdminString,
    cfprAaaAuthRealmFsmCompletionTime                                DateAndTime,
    cfprAaaAuthRealmFsmCurrentFsm                                    CfprAaaAuthRealmFsmCurrentFsm,
    cfprAaaAuthRealmFsmDescrData                                     SnmpAdminString,
    cfprAaaAuthRealmFsmFsmStatus                                     CfprFsmFsmStageStatus,
    cfprAaaAuthRealmFsmProgress                                      Gauge32,
    cfprAaaAuthRealmFsmRmtErrCode                                    Gauge32,
    cfprAaaAuthRealmFsmRmtErrDescr                                   SnmpAdminString,
    cfprAaaAuthRealmFsmRmtRslt                                       CfprConditionRemoteInvRslt
}

cfprAaaAuthRealmFsmInstanceId OBJECT-TYPE
    SYNTAX       CfprManagedObjectId
    MAX-ACCESS   not-accessible
    STATUS       current
    DESCRIPTION
        "Instance identifier of the managed object."
    ::= { cfprAaaAuthRealmFsmEntry 1 }

cfprAaaAuthRealmFsmDn OBJECT-TYPE
    SYNTAX       CfprManagedObjectDn
    MAX-ACCESS   read-only
    STATUS       current
    DESCRIPTION
        "Cisco Firepower aaa:AuthRealmFsm:dn managed object property"
    ::= { cfprAaaAuthRealmFsmEntry 2 }

cfprAaaAuthRealmFsmRn OBJECT-TYPE
    SYNTAX       SnmpAdminString
    MAX-ACCESS   read-only
    STATUS       current
    DESCRIPTION
        "Cisco Firepower aaa:AuthRealmFsm:rn managed object property"
    ::= { cfprAaaAuthRealmFsmEntry 3 }

cfprAaaAuthRealmFsmCompletionTime OBJECT-TYPE
    SYNTAX       DateAndTime
    MAX-ACCESS   read-only
    STATUS       current
    DESCRIPTION
        "Cisco Firepower aaa:AuthRealmFsm:completionTime
        managed object property"
    ::= { cfprAaaAuthRealmFsmEntry 4 }

cfprAaaAuthRealmFsmCurrentFsm OBJECT-TYPE
    SYNTAX       CfprAaaAuthRealmFsmCurrentFsm
    MAX-ACCESS   read-only
    STATUS       current
    DESCRIPTION
        "Cisco Firepower aaa:AuthRealmFsm:currentFsm managed
        object property"
    ::= { cfprAaaAuthRealmFsmEntry 5 }

cfprAaaAuthRealmFsmDescrData OBJECT-TYPE
    SYNTAX       SnmpAdminString
    MAX-ACCESS   read-only
    STATUS       current
    DESCRIPTION
        "Cisco Firepower aaa:AuthRealmFsm:descr managed object property"
    ::= { cfprAaaAuthRealmFsmEntry 6 }

cfprAaaAuthRealmFsmFsmStatus OBJECT-TYPE
    SYNTAX       CfprFsmFsmStageStatus
    MAX-ACCESS   read-only
    STATUS       current
    DESCRIPTION
        "Cisco Firepower aaa:AuthRealmFsm:fsmStatus managed
        object property"
    ::= { cfprAaaAuthRealmFsmEntry 7 }

cfprAaaAuthRealmFsmProgress OBJECT-TYPE
    SYNTAX       Gauge32
    MAX-ACCESS   read-only
    STATUS       current
    DESCRIPTION
        "Cisco Firepower aaa:AuthRealmFsm:progress managed
        object property"
    ::= { cfprAaaAuthRealmFsmEntry 8 }

cfprAaaAuthRealmFsmRmtErrCode OBJECT-TYPE
    SYNTAX       Gauge32
    MAX-ACCESS   read-only
    STATUS       current
    DESCRIPTION
        "Cisco Firepower aaa:AuthRealmFsm:rmtErrCode managed
        object property"
    ::= { cfprAaaAuthRealmFsmEntry 9 }

cfprAaaAuthRealmFsmRmtErrDescr OBJECT-TYPE
    SYNTAX       SnmpAdminString
    MAX-ACCESS   read-only
    STATUS       current
    DESCRIPTION
        "Cisco Firepower aaa:AuthRealmFsm:rmtErrDescr managed
        object property"
    ::= { cfprAaaAuthRealmFsmEntry 10 }

cfprAaaAuthRealmFsmRmtRslt OBJECT-TYPE
    SYNTAX       CfprConditionRemoteInvRslt
    MAX-ACCESS   read-only
    STATUS       current
    DESCRIPTION
        "Cisco Firepower aaa:AuthRealmFsm:rmtRslt managed object property"
    ::= { cfprAaaAuthRealmFsmEntry 11 }

cfprAaaAuthRealmFsmStageTable OBJECT-TYPE
    SYNTAX           SEQUENCE OF CfprAaaAuthRealmFsmStageEntry
    MAX-ACCESS       not-accessible
    STATUS           current
    DESCRIPTION
        "Cisco Firepower aaa:AuthRealmFsmStage managed object table"
    ::= { cfprAaaObjects 3 }

cfprAaaAuthRealmFsmStageEntry OBJECT-TYPE
    SYNTAX           CfprAaaAuthRealmFsmStageEntry
    MAX-ACCESS       not-accessible
    STATUS           current
    DESCRIPTION
        "Entry for the cfprAaaAuthRealmFsmStageTable table."
    INDEX { cfprAaaAuthRealmFsmStageInstanceId }
    ::= { cfprAaaAuthRealmFsmStageTable 1 }

CfprAaaAuthRealmFsmStageEntry ::= SEQUENCE {
    cfprAaaAuthRealmFsmStageInstanceId                               CfprManagedObjectId,
    cfprAaaAuthRealmFsmStageDn                                       CfprManagedObjectDn,
    cfprAaaAuthRealmFsmStageRn                                       SnmpAdminString,
    cfprAaaAuthRealmFsmStageDescrData                                SnmpAdminString,
    cfprAaaAuthRealmFsmStageLastUpdateTime                           DateAndTime,
    cfprAaaAuthRealmFsmStageName                                     CfprAaaAuthRealmFsmStageName,
    cfprAaaAuthRealmFsmStageOrder                                    Gauge32,
    cfprAaaAuthRealmFsmStageRetry                                    Gauge32,
    cfprAaaAuthRealmFsmStageStageStatus                              CfprFsmFsmStageStatus
}

cfprAaaAuthRealmFsmStageInstanceId OBJECT-TYPE
    SYNTAX       CfprManagedObjectId
    MAX-ACCESS   not-accessible
    STATUS       current
    DESCRIPTION
        "Instance identifier of the managed object."
    ::= { cfprAaaAuthRealmFsmStageEntry 1 }

cfprAaaAuthRealmFsmStageDn OBJECT-TYPE
    SYNTAX       CfprManagedObjectDn
    MAX-ACCESS   read-only
    STATUS       current
    DESCRIPTION
        "Cisco Firepower aaa:AuthRealmFsmStage:dn managed object property"
    ::= { cfprAaaAuthRealmFsmStageEntry 2 }

cfprAaaAuthRealmFsmStageRn OBJECT-TYPE
    SYNTAX       SnmpAdminString
    MAX-ACCESS   read-only
    STATUS       current
    DESCRIPTION
        "Cisco Firepower aaa:AuthRealmFsmStage:rn managed object property"
    ::= { cfprAaaAuthRealmFsmStageEntry 3 }

cfprAaaAuthRealmFsmStageDescrData OBJECT-TYPE
    SYNTAX       SnmpAdminString
    MAX-ACCESS   read-only
    STATUS       current
    DESCRIPTION
        "Cisco Firepower aaa:AuthRealmFsmStage:descr managed
        object property"
    ::= { cfprAaaAuthRealmFsmStageEntry 4 }

cfprAaaAuthRealmFsmStageLastUpdateTime OBJECT-TYPE
    SYNTAX       DateAndTime
    MAX-ACCESS   read-only
    STATUS       current
    DESCRIPTION
        "Cisco Firepower aaa:AuthRealmFsmStage:lastUpdateTime
        managed object property"
    ::= { cfprAaaAuthRealmFsmStageEntry 5 }

cfprAaaAuthRealmFsmStageName OBJECT-TYPE
    SYNTAX       CfprAaaAuthRealmFsmStageName
    MAX-ACCESS   read-only
    STATUS       current
    DESCRIPTION
        "Cisco Firepower aaa:AuthRealmFsmStage:name managed
        object property"
    ::= { cfprAaaAuthRealmFsmStageEntry 6 }

cfprAaaAuthRealmFsmStageOrder OBJECT-TYPE
    SYNTAX       Gauge32
    MAX-ACCESS   read-only
    STATUS       current
    DESCRIPTION
        "Cisco Firepower aaa:AuthRealmFsmStage:order managed
        object property"
    ::= { cfprAaaAuthRealmFsmStageEntry 7 }

cfprAaaAuthRealmFsmStageRetry OBJECT-TYPE
    SYNTAX       Gauge32
    MAX-ACCESS   read-only
    STATUS       current
    DESCRIPTION
        "Cisco Firepower aaa:AuthRealmFsmStage:retry managed
        object property"
    ::= { cfprAaaAuthRealmFsmStageEntry 8 }

cfprAaaAuthRealmFsmStageStageStatus OBJECT-TYPE
    SYNTAX       CfprFsmFsmStageStatus
    MAX-ACCESS   read-only
    STATUS       current
    DESCRIPTION
        "Cisco Firepower aaa:AuthRealmFsmStage:stageStatus
        managed object property"
    ::= { cfprAaaAuthRealmFsmStageEntry 9 }

cfprAaaCimcSessionTable OBJECT-TYPE
    SYNTAX           SEQUENCE OF CfprAaaCimcSessionEntry
    MAX-ACCESS       not-accessible
    STATUS           current
    DESCRIPTION
        "Cisco Firepower aaa:CimcSession managed object table"
    ::= { cfprAaaObjects 4 }

cfprAaaCimcSessionEntry OBJECT-TYPE
    SYNTAX           CfprAaaCimcSessionEntry
    MAX-ACCESS       not-accessible
    STATUS           current
    DESCRIPTION
        "Entry for the cfprAaaCimcSessionTable table."
    INDEX { cfprAaaCimcSessionInstanceId }
    ::= { cfprAaaCimcSessionTable 1 }

CfprAaaCimcSessionEntry ::= SEQUENCE {
    cfprAaaCimcSessionInstanceId                                     CfprManagedObjectId,
    cfprAaaCimcSessionDn                                             CfprManagedObjectDn,
    cfprAaaCimcSessionRn                                             SnmpAdminString,
    cfprAaaCimcSessionAdminState                                     CfprAaaSessionState,
    cfprAaaCimcSessionCimcAddr                                       SnmpAdminString,
    cfprAaaCimcSessionId                                             SnmpAdminString,
    cfprAaaCimcSessionIntDel                                         TruthValue,
    cfprAaaCimcSessionIsDelete                                       CfprAaaClear,
    cfprAaaCimcSessionLastUpdatedTime                                DateAndTime,
    cfprAaaCimcSessionLoginTime                                      DateAndTime,
    cfprAaaCimcSessionLsDn                                           SnmpAdminString,
    cfprAaaCimcSessionPid                                            Gauge32,
    cfprAaaCimcSessionPnDn                                           SnmpAdminString,
    cfprAaaCimcSessionPriv                                           SnmpAdminString,
    cfprAaaCimcSessionSourceAddr                                     SnmpAdminString,
    cfprAaaCimcSessionType                                           CfprAaaCimcSessionType,
    cfprAaaCimcSessionUser                                           SnmpAdminString
}

cfprAaaCimcSessionInstanceId OBJECT-TYPE
    SYNTAX       CfprManagedObjectId
    MAX-ACCESS   not-accessible
    STATUS       current
    DESCRIPTION
        "Instance identifier of the managed object."
    ::= { cfprAaaCimcSessionEntry 1 }

cfprAaaCimcSessionDn OBJECT-TYPE
    SYNTAX       CfprManagedObjectDn
    MAX-ACCESS   read-only
    STATUS       current
    DESCRIPTION
        "Cisco Firepower aaa:CimcSession:dn managed object property"
    ::= { cfprAaaCimcSessionEntry 2 }

cfprAaaCimcSessionRn OBJECT-TYPE
    SYNTAX       SnmpAdminString
    MAX-ACCESS   read-only
    STATUS       current
    DESCRIPTION
        "Cisco Firepower aaa:CimcSession:rn managed object property"
    ::= { cfprAaaCimcSessionEntry 3 }

cfprAaaCimcSessionAdminState OBJECT-TYPE
    SYNTAX       CfprAaaSessionState
    MAX-ACCESS   read-only
    STATUS       current
    DESCRIPTION
        "Cisco Firepower aaa:CimcSession:adminState managed
        object property"
    ::= { cfprAaaCimcSessionEntry 4 }

cfprAaaCimcSessionCimcAddr OBJECT-TYPE
    SYNTAX       SnmpAdminString
    MAX-ACCESS   read-only
    STATUS       current
    DESCRIPTION
        "Cisco Firepower aaa:CimcSession:cimcAddr managed object property"
    ::= { cfprAaaCimcSessionEntry 5 }

cfprAaaCimcSessionId OBJECT-TYPE
    SYNTAX       SnmpAdminString
    MAX-ACCESS   read-only
    STATUS       current
    DESCRIPTION
        "Cisco Firepower aaa:CimcSession:id managed object property"
    ::= { cfprAaaCimcSessionEntry 6 }

cfprAaaCimcSessionIntDel OBJECT-TYPE
    SYNTAX       TruthValue
    MAX-ACCESS   read-only
    STATUS       current
    DESCRIPTION
        "Cisco Firepower aaa:CimcSession:intDel managed object property"
    ::= { cfprAaaCimcSessionEntry 7 }

cfprAaaCimcSessionIsDelete OBJECT-TYPE
    SYNTAX       CfprAaaClear
    MAX-ACCESS   read-only
    STATUS       current
    DESCRIPTION
        "Cisco Firepower aaa:CimcSession:isDelete managed object property"
    ::= { cfprAaaCimcSessionEntry 8 }

cfprAaaCimcSessionLastUpdatedTime OBJECT-TYPE
    SYNTAX       DateAndTime
    MAX-ACCESS   read-only
    STATUS       current
    DESCRIPTION
        "Cisco Firepower aaa:CimcSession:lastUpdatedTime
        managed object property"
    ::= { cfprAaaCimcSessionEntry 9 }

cfprAaaCimcSessionLoginTime OBJECT-TYPE
    SYNTAX       DateAndTime
    MAX-ACCESS   read-only
    STATUS       current
    DESCRIPTION
        "Cisco Firepower aaa:CimcSession:loginTime managed
        object property"
    ::= { cfprAaaCimcSessionEntry 10 }

cfprAaaCimcSessionLsDn OBJECT-TYPE
    SYNTAX       SnmpAdminString
    MAX-ACCESS   read-only
    STATUS       current
    DESCRIPTION
        "Cisco Firepower aaa:CimcSession:lsDn managed object property"
    ::= { cfprAaaCimcSessionEntry 11 }

cfprAaaCimcSessionPid OBJECT-TYPE
    SYNTAX       Gauge32
    MAX-ACCESS   read-only
    STATUS       current
    DESCRIPTION
        "Cisco Firepower aaa:CimcSession:pid managed object property"
    ::= { cfprAaaCimcSessionEntry 12 }

cfprAaaCimcSessionPnDn OBJECT-TYPE
    SYNTAX       SnmpAdminString
    MAX-ACCESS   read-only
    STATUS       current
    DESCRIPTION
        "Cisco Firepower aaa:CimcSession:pnDn managed object property"
    ::= { cfprAaaCimcSessionEntry 13 }

cfprAaaCimcSessionPriv OBJECT-TYPE
    SYNTAX       SnmpAdminString
    MAX-ACCESS   read-only
    STATUS       current
    DESCRIPTION
        "Cisco Firepower aaa:CimcSession:priv managed object property"
    ::= { cfprAaaCimcSessionEntry 14 }

cfprAaaCimcSessionSourceAddr OBJECT-TYPE
    SYNTAX       SnmpAdminString
    MAX-ACCESS   read-only
    STATUS       current
    DESCRIPTION
        "Cisco Firepower aaa:CimcSession:sourceAddr managed
        object property"
    ::= { cfprAaaCimcSessionEntry 15 }

cfprAaaCimcSessionType OBJECT-TYPE
    SYNTAX       CfprAaaCimcSessionType
    MAX-ACCESS   read-only
    STATUS       current
    DESCRIPTION
        "Cisco Firepower aaa:CimcSession:type managed object property"
    ::= { cfprAaaCimcSessionEntry 16 }

cfprAaaCimcSessionUser OBJECT-TYPE
    SYNTAX       SnmpAdminString
    MAX-ACCESS   read-only
    STATUS       current
    DESCRIPTION
        "Cisco Firepower aaa:CimcSession:user managed object property"
    ::= { cfprAaaCimcSessionEntry 17 }

cfprAaaConsoleAuthTable OBJECT-TYPE
    SYNTAX           SEQUENCE OF CfprAaaConsoleAuthEntry
    MAX-ACCESS       not-accessible
    STATUS           current
    DESCRIPTION
        "Cisco Firepower aaa:ConsoleAuth managed object table"
    ::= { cfprAaaObjects 5 }

cfprAaaConsoleAuthEntry OBJECT-TYPE
    SYNTAX           CfprAaaConsoleAuthEntry
    MAX-ACCESS       not-accessible
    STATUS           current
    DESCRIPTION
        "Entry for the cfprAaaConsoleAuthTable table."
    INDEX { cfprAaaConsoleAuthInstanceId }
    ::= { cfprAaaConsoleAuthTable 1 }

CfprAaaConsoleAuthEntry ::= SEQUENCE {
    cfprAaaConsoleAuthInstanceId                                     CfprManagedObjectId,
    cfprAaaConsoleAuthDn                                             CfprManagedObjectDn,
    cfprAaaConsoleAuthRn                                             SnmpAdminString,
    cfprAaaConsoleAuthDescr                                          SnmpAdminString,
    cfprAaaConsoleAuthName                                           SnmpAdminString,
    cfprAaaConsoleAuthOperProviderGroup                              SnmpAdminString,
    cfprAaaConsoleAuthOperRealm                                      CfprAaaRealm,
    cfprAaaConsoleAuthProviderGroup                                  SnmpAdminString,
    cfprAaaConsoleAuthRealm                                          CfprAaaRealm,
    cfprAaaConsoleAuthUse2Factor                                     TruthValue
}

cfprAaaConsoleAuthInstanceId OBJECT-TYPE
    SYNTAX       CfprManagedObjectId
    MAX-ACCESS   not-accessible
    STATUS       current
    DESCRIPTION
        "Instance identifier of the managed object."
    ::= { cfprAaaConsoleAuthEntry 1 }

cfprAaaConsoleAuthDn OBJECT-TYPE
    SYNTAX       CfprManagedObjectDn
    MAX-ACCESS   read-only
    STATUS       current
    DESCRIPTION
        "Cisco Firepower aaa:ConsoleAuth:dn managed object property"
    ::= { cfprAaaConsoleAuthEntry 2 }

cfprAaaConsoleAuthRn OBJECT-TYPE
    SYNTAX       SnmpAdminString
    MAX-ACCESS   read-only
    STATUS       current
    DESCRIPTION
        "Cisco Firepower aaa:ConsoleAuth:rn managed object property"
    ::= { cfprAaaConsoleAuthEntry 3 }

cfprAaaConsoleAuthDescr OBJECT-TYPE
    SYNTAX       SnmpAdminString
    MAX-ACCESS   read-only
    STATUS       current
    DESCRIPTION
        "Cisco Firepower aaa:ConsoleAuth:descr managed object property"
    ::= { cfprAaaConsoleAuthEntry 4 }

cfprAaaConsoleAuthName OBJECT-TYPE
    SYNTAX       SnmpAdminString
    MAX-ACCESS   read-only
    STATUS       current
    DESCRIPTION
        "Cisco Firepower aaa:ConsoleAuth:name managed object property"
    ::= { cfprAaaConsoleAuthEntry 5 }

cfprAaaConsoleAuthOperProviderGroup OBJECT-TYPE
    SYNTAX       SnmpAdminString
    MAX-ACCESS   read-only
    STATUS       current
    DESCRIPTION
        "Cisco Firepower aaa:ConsoleAuth:operProviderGroup
        managed object property"
    ::= { cfprAaaConsoleAuthEntry 6 }

cfprAaaConsoleAuthOperRealm OBJECT-TYPE
    SYNTAX       CfprAaaRealm
    MAX-ACCESS   read-only
    STATUS       current
    DESCRIPTION
        "Cisco Firepower aaa:ConsoleAuth:operRealm managed
        object property"
    ::= { cfprAaaConsoleAuthEntry 7 }

cfprAaaConsoleAuthProviderGroup OBJECT-TYPE
    SYNTAX       SnmpAdminString
    MAX-ACCESS   read-only
    STATUS       current
    DESCRIPTION
        "Cisco Firepower aaa:ConsoleAuth:providerGroup
        managed object property"
    ::= { cfprAaaConsoleAuthEntry 8 }

cfprAaaConsoleAuthRealm OBJECT-TYPE
    SYNTAX       CfprAaaRealm
    MAX-ACCESS   read-only
    STATUS       current
    DESCRIPTION
        "Cisco Firepower aaa:ConsoleAuth:realm managed object property"
    ::= { cfprAaaConsoleAuthEntry 9 }

cfprAaaConsoleAuthUse2Factor OBJECT-TYPE
    SYNTAX       TruthValue
    MAX-ACCESS   read-only
    STATUS       current
    DESCRIPTION
        "Cisco Firepower aaa:ConsoleAuth:use2Factor managed
        object property"
    ::= { cfprAaaConsoleAuthEntry 10 }

cfprAaaDefaultAuthTable OBJECT-TYPE
    SYNTAX           SEQUENCE OF CfprAaaDefaultAuthEntry
    MAX-ACCESS       not-accessible
    STATUS           current
    DESCRIPTION
        "Cisco Firepower aaa:DefaultAuth managed object table"
    ::= { cfprAaaObjects 6 }

cfprAaaDefaultAuthEntry OBJECT-TYPE
    SYNTAX           CfprAaaDefaultAuthEntry
    MAX-ACCESS       not-accessible
    STATUS           current
    DESCRIPTION
        "Entry for the cfprAaaDefaultAuthTable table."
    INDEX { cfprAaaDefaultAuthInstanceId }
    ::= { cfprAaaDefaultAuthTable 1 }

CfprAaaDefaultAuthEntry ::= SEQUENCE {
    cfprAaaDefaultAuthInstanceId                                     CfprManagedObjectId,
    cfprAaaDefaultAuthDn                                             CfprManagedObjectDn,
    cfprAaaDefaultAuthRn                                             SnmpAdminString,
    cfprAaaDefaultAuthDescr                                          SnmpAdminString,
    cfprAaaDefaultAuthName                                           SnmpAdminString,
    cfprAaaDefaultAuthOperProviderGroup                              SnmpAdminString,
    cfprAaaDefaultAuthOperRealm                                      CfprAaaRealm,
    cfprAaaDefaultAuthProviderGroup                                  SnmpAdminString,
    cfprAaaDefaultAuthRealm                                          CfprAaaRealm,
    cfprAaaDefaultAuthRefreshPeriod                                  Gauge32,
    cfprAaaDefaultAuthSessionTimeout                                 Gauge32,
    cfprAaaDefaultAuthUse2Factor                                     TruthValue,
    cfprAaaDefaultAuthAbsoluteSessionTimeout                         Gauge32,
    cfprAaaDefaultAuthConAbsoluteSessionTimeout                      Gauge32,
    cfprAaaDefaultAuthConSessionTimeout                              Gauge32
}

cfprAaaDefaultAuthInstanceId OBJECT-TYPE
    SYNTAX       CfprManagedObjectId
    MAX-ACCESS   not-accessible
    STATUS       current
    DESCRIPTION
        "Instance identifier of the managed object."
    ::= { cfprAaaDefaultAuthEntry 1 }

cfprAaaDefaultAuthDn OBJECT-TYPE
    SYNTAX       CfprManagedObjectDn
    MAX-ACCESS   read-only
    STATUS       current
    DESCRIPTION
        "Cisco Firepower aaa:DefaultAuth:dn managed object property"
    ::= { cfprAaaDefaultAuthEntry 2 }

cfprAaaDefaultAuthRn OBJECT-TYPE
    SYNTAX       SnmpAdminString
    MAX-ACCESS   read-only
    STATUS       current
    DESCRIPTION
        "Cisco Firepower aaa:DefaultAuth:rn managed object property"
    ::= { cfprAaaDefaultAuthEntry 3 }

cfprAaaDefaultAuthDescr OBJECT-TYPE
    SYNTAX       SnmpAdminString
    MAX-ACCESS   read-only
    STATUS       current
    DESCRIPTION
        "Cisco Firepower aaa:DefaultAuth:descr managed object property"
    ::= { cfprAaaDefaultAuthEntry 4 }

cfprAaaDefaultAuthName OBJECT-TYPE
    SYNTAX       SnmpAdminString
    MAX-ACCESS   read-only
    STATUS       current
    DESCRIPTION
        "Cisco Firepower aaa:DefaultAuth:name managed object property"
    ::= { cfprAaaDefaultAuthEntry 5 }

cfprAaaDefaultAuthOperProviderGroup OBJECT-TYPE
    SYNTAX       SnmpAdminString
    MAX-ACCESS   read-only
    STATUS       current
    DESCRIPTION
        "Cisco Firepower aaa:DefaultAuth:operProviderGroup
        managed object property"
    ::= { cfprAaaDefaultAuthEntry 6 }

cfprAaaDefaultAuthOperRealm OBJECT-TYPE
    SYNTAX       CfprAaaRealm
    MAX-ACCESS   read-only
    STATUS       current
    DESCRIPTION
        "Cisco Firepower aaa:DefaultAuth:operRealm managed
        object property"
    ::= { cfprAaaDefaultAuthEntry 7 }

cfprAaaDefaultAuthProviderGroup OBJECT-TYPE
    SYNTAX       SnmpAdminString
    MAX-ACCESS   read-only
    STATUS       current
    DESCRIPTION
        "Cisco Firepower aaa:DefaultAuth:providerGroup
        managed object property"
    ::= { cfprAaaDefaultAuthEntry 8 }

cfprAaaDefaultAuthRealm OBJECT-TYPE
    SYNTAX       CfprAaaRealm
    MAX-ACCESS   read-only
    STATUS       current
    DESCRIPTION
        "Cisco Firepower aaa:DefaultAuth:realm managed object property"
    ::= { cfprAaaDefaultAuthEntry 9 }

cfprAaaDefaultAuthRefreshPeriod OBJECT-TYPE
    SYNTAX       Gauge32
    MAX-ACCESS   read-only
    STATUS       current
    DESCRIPTION
        "Cisco Firepower aaa:DefaultAuth:refreshPeriod
        managed object property"
    ::= { cfprAaaDefaultAuthEntry 10 }

cfprAaaDefaultAuthSessionTimeout OBJECT-TYPE
    SYNTAX       Gauge32
    MAX-ACCESS   read-only
    STATUS       current
    DESCRIPTION
        "Cisco Firepower aaa:DefaultAuth:sessionTimeout
        managed object property"
    ::= { cfprAaaDefaultAuthEntry 11 }

cfprAaaDefaultAuthUse2Factor OBJECT-TYPE
    SYNTAX       TruthValue
    MAX-ACCESS   read-only
    STATUS       current
    DESCRIPTION
        "Cisco Firepower aaa:DefaultAuth:use2Factor managed
        object property"
    ::= { cfprAaaDefaultAuthEntry 12 }

cfprAaaDefaultAuthAbsoluteSessionTimeout OBJECT-TYPE
    SYNTAX       Gauge32
    MAX-ACCESS   read-only
    STATUS       current
    DESCRIPTION
        "Cisco Firepower aaa:DefaultAuth:absoluteSessionTimeout
        managed object property"
    ::= { cfprAaaDefaultAuthEntry 13 }

cfprAaaDefaultAuthConAbsoluteSessionTimeout OBJECT-TYPE
    SYNTAX       Gauge32
    MAX-ACCESS   read-only
    STATUS       current
    DESCRIPTION
        "Cisco Firepower aaa:DefaultAuth:conAbsoluteSessionTimeout
        managed object property"
    ::= { cfprAaaDefaultAuthEntry 14 }

cfprAaaDefaultAuthConSessionTimeout OBJECT-TYPE
    SYNTAX       Gauge32
    MAX-ACCESS   read-only
    STATUS       current
    DESCRIPTION
        "Cisco Firepower aaa:DefaultAuth:conSessionTimeout
        managed object property"
    ::= { cfprAaaDefaultAuthEntry 15 }

cfprAaaDomainTable OBJECT-TYPE
    SYNTAX           SEQUENCE OF CfprAaaDomainEntry
    MAX-ACCESS       not-accessible
    STATUS           current
    DESCRIPTION
        "Cisco Firepower aaa:Domain managed object table"
    ::= { cfprAaaObjects 7 }

cfprAaaDomainEntry OBJECT-TYPE
    SYNTAX           CfprAaaDomainEntry
    MAX-ACCESS       not-accessible
    STATUS           current
    DESCRIPTION
        "Entry for the cfprAaaDomainTable table."
    INDEX { cfprAaaDomainInstanceId }
    ::= { cfprAaaDomainTable 1 }

CfprAaaDomainEntry ::= SEQUENCE {
    cfprAaaDomainInstanceId                                          CfprManagedObjectId,
    cfprAaaDomainDn                                                  CfprManagedObjectDn,
    cfprAaaDomainRn                                                  SnmpAdminString,
    cfprAaaDomainDescr                                               SnmpAdminString,
    cfprAaaDomainName                                                SnmpAdminString,
    cfprAaaDomainRefreshPeriod                                       Gauge32,
    cfprAaaDomainSessionTimeout                                      Gauge32,
    cfprAaaDomainAbsoluteSessionTimeout                              Gauge32,
    cfprAaaDomainConAbsoluteSessionTimeout                           Gauge32,
    cfprAaaDomainConSessionTimeout                                   Gauge32
}

cfprAaaDomainInstanceId OBJECT-TYPE
    SYNTAX       CfprManagedObjectId
    MAX-ACCESS   not-accessible
    STATUS       current
    DESCRIPTION
        "Instance identifier of the managed object."
    ::= { cfprAaaDomainEntry 1 }

cfprAaaDomainDn OBJECT-TYPE
    SYNTAX       CfprManagedObjectDn
    MAX-ACCESS   read-only
    STATUS       current
    DESCRIPTION
        "Cisco Firepower aaa:Domain:dn managed object property"
    ::= { cfprAaaDomainEntry 2 }

cfprAaaDomainRn OBJECT-TYPE
    SYNTAX       SnmpAdminString
    MAX-ACCESS   read-only
    STATUS       current
    DESCRIPTION
        "Cisco Firepower aaa:Domain:rn managed object property"
    ::= { cfprAaaDomainEntry 3 }

cfprAaaDomainDescr OBJECT-TYPE
    SYNTAX       SnmpAdminString
    MAX-ACCESS   read-only
    STATUS       current
    DESCRIPTION
        "Cisco Firepower aaa:Domain:descr managed object property"
    ::= { cfprAaaDomainEntry 4 }

cfprAaaDomainName OBJECT-TYPE
    SYNTAX       SnmpAdminString
    MAX-ACCESS   read-only
    STATUS       current
    DESCRIPTION
        "Cisco Firepower aaa:Domain:name managed object property"
    ::= { cfprAaaDomainEntry 5 }

cfprAaaDomainRefreshPeriod OBJECT-TYPE
    SYNTAX       Gauge32
    MAX-ACCESS   read-only
    STATUS       current
    DESCRIPTION
        "Cisco Firepower aaa:Domain:refreshPeriod managed object property"
    ::= { cfprAaaDomainEntry 6 }

cfprAaaDomainSessionTimeout OBJECT-TYPE
    SYNTAX       Gauge32
    MAX-ACCESS   read-only
    STATUS       current
    DESCRIPTION
        "Cisco Firepower aaa:Domain:sessionTimeout managed
        object property"
    ::= { cfprAaaDomainEntry 7 }

cfprAaaDomainAbsoluteSessionTimeout OBJECT-TYPE
    SYNTAX       Gauge32
    MAX-ACCESS   read-only
    STATUS       current
    DESCRIPTION
        "Cisco Firepower aaa:Domain:absoluteSessionTimeout
        managed object property"
    ::= { cfprAaaDomainEntry 8 }

cfprAaaDomainConAbsoluteSessionTimeout OBJECT-TYPE
    SYNTAX       Gauge32
    MAX-ACCESS   read-only
    STATUS       current
    DESCRIPTION
        "Cisco Firepower aaa:Domain:conAbsoluteSessionTimeout
        managed object property"
    ::= { cfprAaaDomainEntry 9 }

cfprAaaDomainConSessionTimeout OBJECT-TYPE
    SYNTAX       Gauge32
    MAX-ACCESS   read-only
    STATUS       current
    DESCRIPTION
        "Cisco Firepower aaa:Domain:conSessionTimeout managed
        object property"
    ::= { cfprAaaDomainEntry 10 }

cfprAaaDomainAuthTable OBJECT-TYPE
    SYNTAX           SEQUENCE OF CfprAaaDomainAuthEntry
    MAX-ACCESS       not-accessible
    STATUS           current
    DESCRIPTION
        "Cisco Firepower aaa:DomainAuth managed object table"
    ::= { cfprAaaObjects 8 }

cfprAaaDomainAuthEntry OBJECT-TYPE
    SYNTAX           CfprAaaDomainAuthEntry
    MAX-ACCESS       not-accessible
    STATUS           current
    DESCRIPTION
        "Entry for the cfprAaaDomainAuthTable table."
    INDEX { cfprAaaDomainAuthInstanceId }
    ::= { cfprAaaDomainAuthTable 1 }

CfprAaaDomainAuthEntry ::= SEQUENCE {
    cfprAaaDomainAuthInstanceId                                      CfprManagedObjectId,
    cfprAaaDomainAuthDn                                              CfprManagedObjectDn,
    cfprAaaDomainAuthRn                                              SnmpAdminString,
    cfprAaaDomainAuthDescr                                           SnmpAdminString,
    cfprAaaDomainAuthName                                            SnmpAdminString,
    cfprAaaDomainAuthOperProviderGroup                               SnmpAdminString,
    cfprAaaDomainAuthOperRealm                                       CfprAaaRealm,
    cfprAaaDomainAuthProviderGroup                                   SnmpAdminString,
    cfprAaaDomainAuthRealm                                           CfprAaaDomainAuthRealm,
    cfprAaaDomainAuthUse2Factor                                      TruthValue
}

cfprAaaDomainAuthInstanceId OBJECT-TYPE
    SYNTAX       CfprManagedObjectId
    MAX-ACCESS   not-accessible
    STATUS       current
    DESCRIPTION
        "Instance identifier of the managed object."
    ::= { cfprAaaDomainAuthEntry 1 }

cfprAaaDomainAuthDn OBJECT-TYPE
    SYNTAX       CfprManagedObjectDn
    MAX-ACCESS   read-only
    STATUS       current
    DESCRIPTION
        "Cisco Firepower aaa:DomainAuth:dn managed object property"
    ::= { cfprAaaDomainAuthEntry 2 }

cfprAaaDomainAuthRn OBJECT-TYPE
    SYNTAX       SnmpAdminString
    MAX-ACCESS   read-only
    STATUS       current
    DESCRIPTION
        "Cisco Firepower aaa:DomainAuth:rn managed object property"
    ::= { cfprAaaDomainAuthEntry 3 }

cfprAaaDomainAuthDescr OBJECT-TYPE
    SYNTAX       SnmpAdminString
    MAX-ACCESS   read-only
    STATUS       current
    DESCRIPTION
        "Cisco Firepower aaa:DomainAuth:descr managed object property"
    ::= { cfprAaaDomainAuthEntry 4 }

cfprAaaDomainAuthName OBJECT-TYPE
    SYNTAX       SnmpAdminString
    MAX-ACCESS   read-only
    STATUS       current
    DESCRIPTION
        "Cisco Firepower aaa:DomainAuth:name managed object property"
    ::= { cfprAaaDomainAuthEntry 5 }

cfprAaaDomainAuthOperProviderGroup OBJECT-TYPE
    SYNTAX       SnmpAdminString
    MAX-ACCESS   read-only
    STATUS       current
    DESCRIPTION
        "Cisco Firepower aaa:DomainAuth:operProviderGroup
        managed object property"
    ::= { cfprAaaDomainAuthEntry 6 }

cfprAaaDomainAuthOperRealm OBJECT-TYPE
    SYNTAX       CfprAaaRealm
    MAX-ACCESS   read-only
    STATUS       current
    DESCRIPTION
        "Cisco Firepower aaa:DomainAuth:operRealm managed object property"
    ::= { cfprAaaDomainAuthEntry 7 }

cfprAaaDomainAuthProviderGroup OBJECT-TYPE
    SYNTAX       SnmpAdminString
    MAX-ACCESS   read-only
    STATUS       current
    DESCRIPTION
        "Cisco Firepower aaa:DomainAuth:providerGroup managed
        object property"
    ::= { cfprAaaDomainAuthEntry 8 }

cfprAaaDomainAuthRealm OBJECT-TYPE
    SYNTAX       CfprAaaDomainAuthRealm
    MAX-ACCESS   read-only
    STATUS       current
    DESCRIPTION
        "Cisco Firepower aaa:DomainAuth:realm managed object property"
    ::= { cfprAaaDomainAuthEntry 9 }

cfprAaaDomainAuthUse2Factor OBJECT-TYPE
    SYNTAX       TruthValue
    MAX-ACCESS   read-only
    STATUS       current
    DESCRIPTION
        "Cisco Firepower aaa:DomainAuth:use2Factor managed
        object property"
    ::= { cfprAaaDomainAuthEntry 10 }

cfprAaaEpAuthProfileTable OBJECT-TYPE
    SYNTAX           SEQUENCE OF CfprAaaEpAuthProfileEntry
    MAX-ACCESS       not-accessible
    STATUS           current
    DESCRIPTION
        "Cisco Firepower aaa:EpAuthProfile managed object table"
    ::= { cfprAaaObjects 9 }

cfprAaaEpAuthProfileEntry OBJECT-TYPE
    SYNTAX           CfprAaaEpAuthProfileEntry
    MAX-ACCESS       not-accessible
    STATUS           current
    DESCRIPTION
        "Entry for the cfprAaaEpAuthProfileTable table."
    INDEX { cfprAaaEpAuthProfileInstanceId }
    ::= { cfprAaaEpAuthProfileTable 1 }

CfprAaaEpAuthProfileEntry ::= SEQUENCE {
    cfprAaaEpAuthProfileInstanceId                                   CfprManagedObjectId,
    cfprAaaEpAuthProfileDn                                           CfprManagedObjectDn,
    cfprAaaEpAuthProfileRn                                           SnmpAdminString,
    cfprAaaEpAuthProfileDescr                                        SnmpAdminString,
    cfprAaaEpAuthProfileIntId                                        SnmpAdminString,
    cfprAaaEpAuthProfileIpmiOverLan                                  CfprAaaIpmiOverLan,
    cfprAaaEpAuthProfileName                                         SnmpAdminString,
    cfprAaaEpAuthProfilePolicyLevel                                  Gauge32,
    cfprAaaEpAuthProfilePolicyOwner                                  CfprPolicyPolicyOwner
}

cfprAaaEpAuthProfileInstanceId OBJECT-TYPE
    SYNTAX       CfprManagedObjectId
    MAX-ACCESS   not-accessible
    STATUS       current
    DESCRIPTION
        "Instance identifier of the managed object."
    ::= { cfprAaaEpAuthProfileEntry 1 }

cfprAaaEpAuthProfileDn OBJECT-TYPE
    SYNTAX       CfprManagedObjectDn
    MAX-ACCESS   read-only
    STATUS       current
    DESCRIPTION
        "Cisco Firepower aaa:EpAuthProfile:dn managed object property"
    ::= { cfprAaaEpAuthProfileEntry 2 }

cfprAaaEpAuthProfileRn OBJECT-TYPE
    SYNTAX       SnmpAdminString
    MAX-ACCESS   read-only
    STATUS       current
    DESCRIPTION
        "Cisco Firepower aaa:EpAuthProfile:rn managed object property"
    ::= { cfprAaaEpAuthProfileEntry 3 }

cfprAaaEpAuthProfileDescr OBJECT-TYPE
    SYNTAX       SnmpAdminString
    MAX-ACCESS   read-only
    STATUS       current
    DESCRIPTION
        "Cisco Firepower aaa:EpAuthProfile:descr managed object property"
    ::= { cfprAaaEpAuthProfileEntry 4 }

cfprAaaEpAuthProfileIntId OBJECT-TYPE
    SYNTAX       SnmpAdminString
    MAX-ACCESS   read-only
    STATUS       current
    DESCRIPTION
        "Cisco Firepower aaa:EpAuthProfile:intId managed object property"
    ::= { cfprAaaEpAuthProfileEntry 5 }

cfprAaaEpAuthProfileIpmiOverLan OBJECT-TYPE
    SYNTAX       CfprAaaIpmiOverLan
    MAX-ACCESS   read-only
    STATUS       current
    DESCRIPTION
        "Cisco Firepower aaa:EpAuthProfile:ipmiOverLan
        managed object property"
    ::= { cfprAaaEpAuthProfileEntry 6 }

cfprAaaEpAuthProfileName OBJECT-TYPE
    SYNTAX       SnmpAdminString
    MAX-ACCESS   read-only
    STATUS       current
    DESCRIPTION
        "Cisco Firepower aaa:EpAuthProfile:name managed object property"
    ::= { cfprAaaEpAuthProfileEntry 7 }

cfprAaaEpAuthProfilePolicyLevel OBJECT-TYPE
    SYNTAX       Gauge32
    MAX-ACCESS   read-only
    STATUS       current
    DESCRIPTION
        "Cisco Firepower aaa:EpAuthProfile:policyLevel
        managed object property"
    ::= { cfprAaaEpAuthProfileEntry 8 }

cfprAaaEpAuthProfilePolicyOwner OBJECT-TYPE
    SYNTAX       CfprPolicyPolicyOwner
    MAX-ACCESS   read-only
    STATUS       current
    DESCRIPTION
        "Cisco Firepower aaa:EpAuthProfile:policyOwner
        managed object property"
    ::= { cfprAaaEpAuthProfileEntry 9 }

cfprAaaEpFsmTable OBJECT-TYPE
    SYNTAX           SEQUENCE OF CfprAaaEpFsmEntry
    MAX-ACCESS       not-accessible
    STATUS           current
    DESCRIPTION
        "Cisco Firepower aaa:EpFsm managed object table"
    ::= { cfprAaaObjects 10 }

cfprAaaEpFsmEntry OBJECT-TYPE
    SYNTAX           CfprAaaEpFsmEntry
    MAX-ACCESS       not-accessible
    STATUS           current
    DESCRIPTION
        "Entry for the cfprAaaEpFsmTable table."
    INDEX { cfprAaaEpFsmInstanceId }
    ::= { cfprAaaEpFsmTable 1 }

CfprAaaEpFsmEntry ::= SEQUENCE {
    cfprAaaEpFsmInstanceId                                           CfprManagedObjectId,
    cfprAaaEpFsmDn                                                   CfprManagedObjectDn,
    cfprAaaEpFsmRn                                                   SnmpAdminString,
    cfprAaaEpFsmCompletionTime                                       DateAndTime,
    cfprAaaEpFsmCurrentFsm                                           CfprAaaEpFsmCurrentFsm,
    cfprAaaEpFsmDescr                                                SnmpAdminString,
    cfprAaaEpFsmFsmStatus                                            CfprFsmFsmStageStatus,
    cfprAaaEpFsmProgress                                             Gauge32,
    cfprAaaEpFsmRmtErrCode                                           Gauge32,
    cfprAaaEpFsmRmtErrDescr                                          SnmpAdminString,
    cfprAaaEpFsmRmtRslt                                              CfprConditionRemoteInvRslt
}

cfprAaaEpFsmInstanceId OBJECT-TYPE
    SYNTAX       CfprManagedObjectId
    MAX-ACCESS   not-accessible
    STATUS       current
    DESCRIPTION
        "Instance identifier of the managed object."
    ::= { cfprAaaEpFsmEntry 1 }

cfprAaaEpFsmDn OBJECT-TYPE
    SYNTAX       CfprManagedObjectDn
    MAX-ACCESS   read-only
    STATUS       current
    DESCRIPTION
        "Cisco Firepower aaa:EpFsm:dn managed object property"
    ::= { cfprAaaEpFsmEntry 2 }

cfprAaaEpFsmRn OBJECT-TYPE
    SYNTAX       SnmpAdminString
    MAX-ACCESS   read-only
    STATUS       current
    DESCRIPTION
        "Cisco Firepower aaa:EpFsm:rn managed object property"
    ::= { cfprAaaEpFsmEntry 3 }

cfprAaaEpFsmCompletionTime OBJECT-TYPE
    SYNTAX       DateAndTime
    MAX-ACCESS   read-only
    STATUS       current
    DESCRIPTION
        "Cisco Firepower aaa:EpFsm:completionTime managed object property"
    ::= { cfprAaaEpFsmEntry 4 }

cfprAaaEpFsmCurrentFsm OBJECT-TYPE
    SYNTAX       CfprAaaEpFsmCurrentFsm
    MAX-ACCESS   read-only
    STATUS       current
    DESCRIPTION
        "Cisco Firepower aaa:EpFsm:currentFsm managed object property"
    ::= { cfprAaaEpFsmEntry 5 }

cfprAaaEpFsmDescr OBJECT-TYPE
    SYNTAX       SnmpAdminString
    MAX-ACCESS   read-only
    STATUS       current
    DESCRIPTION
        "Cisco Firepower aaa:EpFsm:descr managed object property"
    ::= { cfprAaaEpFsmEntry 6 }

cfprAaaEpFsmFsmStatus OBJECT-TYPE
    SYNTAX       CfprFsmFsmStageStatus
    MAX-ACCESS   read-only
    STATUS       current
    DESCRIPTION
        "Cisco Firepower aaa:EpFsm:fsmStatus managed object property"
    ::= { cfprAaaEpFsmEntry 7 }

cfprAaaEpFsmProgress OBJECT-TYPE
    SYNTAX       Gauge32
    MAX-ACCESS   read-only
    STATUS       current
    DESCRIPTION
        "Cisco Firepower aaa:EpFsm:progress managed object property"
    ::= { cfprAaaEpFsmEntry 8 }

cfprAaaEpFsmRmtErrCode OBJECT-TYPE
    SYNTAX       Gauge32
    MAX-ACCESS   read-only
    STATUS       current
    DESCRIPTION
        "Cisco Firepower aaa:EpFsm:rmtErrCode managed object property"
    ::= { cfprAaaEpFsmEntry 9 }

cfprAaaEpFsmRmtErrDescr OBJECT-TYPE
    SYNTAX       SnmpAdminString
    MAX-ACCESS   read-only
    STATUS       current
    DESCRIPTION
        "Cisco Firepower aaa:EpFsm:rmtErrDescr managed object property"
    ::= { cfprAaaEpFsmEntry 10 }

cfprAaaEpFsmRmtRslt OBJECT-TYPE
    SYNTAX       CfprConditionRemoteInvRslt
    MAX-ACCESS   read-only
    STATUS       current
    DESCRIPTION
        "Cisco Firepower aaa:EpFsm:rmtRslt managed object property"
    ::= { cfprAaaEpFsmEntry 11 }

cfprAaaEpFsmStageTable OBJECT-TYPE
    SYNTAX           SEQUENCE OF CfprAaaEpFsmStageEntry
    MAX-ACCESS       not-accessible
    STATUS           current
    DESCRIPTION
        "Cisco Firepower aaa:EpFsmStage managed object table"
    ::= { cfprAaaObjects 11 }

cfprAaaEpFsmStageEntry OBJECT-TYPE
    SYNTAX           CfprAaaEpFsmStageEntry
    MAX-ACCESS       not-accessible
    STATUS           current
    DESCRIPTION
        "Entry for the cfprAaaEpFsmStageTable table."
    INDEX { cfprAaaEpFsmStageInstanceId }
    ::= { cfprAaaEpFsmStageTable 1 }

CfprAaaEpFsmStageEntry ::= SEQUENCE {
    cfprAaaEpFsmStageInstanceId                                      CfprManagedObjectId,
    cfprAaaEpFsmStageDn                                              CfprManagedObjectDn,
    cfprAaaEpFsmStageRn                                              SnmpAdminString,
    cfprAaaEpFsmStageDescr                                           SnmpAdminString,
    cfprAaaEpFsmStageLastUpdateTime                                  DateAndTime,
    cfprAaaEpFsmStageName                                            CfprAaaEpFsmStageName,
    cfprAaaEpFsmStageOrder                                           Gauge32,
    cfprAaaEpFsmStageRetry                                           Gauge32,
    cfprAaaEpFsmStageStageStatus                                     CfprFsmFsmStageStatus
}

cfprAaaEpFsmStageInstanceId OBJECT-TYPE
    SYNTAX       CfprManagedObjectId
    MAX-ACCESS   not-accessible
    STATUS       current
    DESCRIPTION
        "Instance identifier of the managed object."
    ::= { cfprAaaEpFsmStageEntry 1 }

cfprAaaEpFsmStageDn OBJECT-TYPE
    SYNTAX       CfprManagedObjectDn
    MAX-ACCESS   read-only
    STATUS       current
    DESCRIPTION
        "Cisco Firepower aaa:EpFsmStage:dn managed object property"
    ::= { cfprAaaEpFsmStageEntry 2 }

cfprAaaEpFsmStageRn OBJECT-TYPE
    SYNTAX       SnmpAdminString
    MAX-ACCESS   read-only
    STATUS       current
    DESCRIPTION
        "Cisco Firepower aaa:EpFsmStage:rn managed object property"
    ::= { cfprAaaEpFsmStageEntry 3 }

cfprAaaEpFsmStageDescr OBJECT-TYPE
    SYNTAX       SnmpAdminString
    MAX-ACCESS   read-only
    STATUS       current
    DESCRIPTION
        "Cisco Firepower aaa:EpFsmStage:descr managed object property"
    ::= { cfprAaaEpFsmStageEntry 4 }

cfprAaaEpFsmStageLastUpdateTime OBJECT-TYPE
    SYNTAX       DateAndTime
    MAX-ACCESS   read-only
    STATUS       current
    DESCRIPTION
        "Cisco Firepower aaa:EpFsmStage:lastUpdateTime
        managed object property"
    ::= { cfprAaaEpFsmStageEntry 5 }

cfprAaaEpFsmStageName OBJECT-TYPE
    SYNTAX       CfprAaaEpFsmStageName
    MAX-ACCESS   read-only
    STATUS       current
    DESCRIPTION
        "Cisco Firepower aaa:EpFsmStage:name managed object property"
    ::= { cfprAaaEpFsmStageEntry 6 }

cfprAaaEpFsmStageOrder OBJECT-TYPE
    SYNTAX       Gauge32
    MAX-ACCESS   read-only
    STATUS       current
    DESCRIPTION
        "Cisco Firepower aaa:EpFsmStage:order managed object property"
    ::= { cfprAaaEpFsmStageEntry 7 }

cfprAaaEpFsmStageRetry OBJECT-TYPE
    SYNTAX       Gauge32
    MAX-ACCESS   read-only
    STATUS       current
    DESCRIPTION
        "Cisco Firepower aaa:EpFsmStage:retry managed object property"
    ::= { cfprAaaEpFsmStageEntry 8 }

cfprAaaEpFsmStageStageStatus OBJECT-TYPE
    SYNTAX       CfprFsmFsmStageStatus
    MAX-ACCESS   read-only
    STATUS       current
    DESCRIPTION
        "Cisco Firepower aaa:EpFsmStage:stageStatus managed
        object property"
    ::= { cfprAaaEpFsmStageEntry 9 }

cfprAaaEpFsmTaskTable OBJECT-TYPE
    SYNTAX           SEQUENCE OF CfprAaaEpFsmTaskEntry
    MAX-ACCESS       not-accessible
    STATUS           current
    DESCRIPTION
        "Cisco Firepower aaa:EpFsmTask managed object table"
    ::= { cfprAaaObjects 12 }

cfprAaaEpFsmTaskEntry OBJECT-TYPE
    SYNTAX           CfprAaaEpFsmTaskEntry
    MAX-ACCESS       not-accessible
    STATUS           current
    DESCRIPTION
        "Entry for the cfprAaaEpFsmTaskTable table."
    INDEX { cfprAaaEpFsmTaskInstanceId }
    ::= { cfprAaaEpFsmTaskTable 1 }

CfprAaaEpFsmTaskEntry ::= SEQUENCE {
    cfprAaaEpFsmTaskInstanceId                                       CfprManagedObjectId,
    cfprAaaEpFsmTaskDn                                               CfprManagedObjectDn,
    cfprAaaEpFsmTaskRn                                               SnmpAdminString,
    cfprAaaEpFsmTaskCompletion                                       CfprFsmCompletion,
    cfprAaaEpFsmTaskFlags                                            CfprFsmFlags,
    cfprAaaEpFsmTaskItem                                             CfprAaaEpFsmTaskItem,
    cfprAaaEpFsmTaskSeqId                                            Gauge32
}

cfprAaaEpFsmTaskInstanceId OBJECT-TYPE
    SYNTAX       CfprManagedObjectId
    MAX-ACCESS   not-accessible
    STATUS       current
    DESCRIPTION
        "Instance identifier of the managed object."
    ::= { cfprAaaEpFsmTaskEntry 1 }

cfprAaaEpFsmTaskDn OBJECT-TYPE
    SYNTAX       CfprManagedObjectDn
    MAX-ACCESS   read-only
    STATUS       current
    DESCRIPTION
        "Cisco Firepower aaa:EpFsmTask:dn managed object property"
    ::= { cfprAaaEpFsmTaskEntry 2 }

cfprAaaEpFsmTaskRn OBJECT-TYPE
    SYNTAX       SnmpAdminString
    MAX-ACCESS   read-only
    STATUS       current
    DESCRIPTION
        "Cisco Firepower aaa:EpFsmTask:rn managed object property"
    ::= { cfprAaaEpFsmTaskEntry 3 }

cfprAaaEpFsmTaskCompletion OBJECT-TYPE
    SYNTAX       CfprFsmCompletion
    MAX-ACCESS   read-only
    STATUS       current
    DESCRIPTION
        "Cisco Firepower aaa:EpFsmTask:completion managed object property"
    ::= { cfprAaaEpFsmTaskEntry 4 }

cfprAaaEpFsmTaskFlags OBJECT-TYPE
    SYNTAX       CfprFsmFlags
    MAX-ACCESS   read-only
    STATUS       current
    DESCRIPTION
        "Cisco Firepower aaa:EpFsmTask:flags managed object property"
    ::= { cfprAaaEpFsmTaskEntry 5 }

cfprAaaEpFsmTaskItem OBJECT-TYPE
    SYNTAX       CfprAaaEpFsmTaskItem
    MAX-ACCESS   read-only
    STATUS       current
    DESCRIPTION
        "Cisco Firepower aaa:EpFsmTask:item managed object property"
    ::= { cfprAaaEpFsmTaskEntry 6 }

cfprAaaEpFsmTaskSeqId OBJECT-TYPE
    SYNTAX       Gauge32
    MAX-ACCESS   read-only
    STATUS       current
    DESCRIPTION
        "Cisco Firepower aaa:EpFsmTask:seqId managed object property"
    ::= { cfprAaaEpFsmTaskEntry 7 }

cfprAaaEpLoginTable OBJECT-TYPE
    SYNTAX           SEQUENCE OF CfprAaaEpLoginEntry
    MAX-ACCESS       not-accessible
    STATUS           current
    DESCRIPTION
        "Cisco Firepower aaa:EpLogin managed object table"
    ::= { cfprAaaObjects 13 }

cfprAaaEpLoginEntry OBJECT-TYPE
    SYNTAX           CfprAaaEpLoginEntry
    MAX-ACCESS       not-accessible
    STATUS           current
    DESCRIPTION
        "Entry for the cfprAaaEpLoginTable table."
    INDEX { cfprAaaEpLoginInstanceId }
    ::= { cfprAaaEpLoginTable 1 }

CfprAaaEpLoginEntry ::= SEQUENCE {
    cfprAaaEpLoginInstanceId                                         CfprManagedObjectId,
    cfprAaaEpLoginDn                                                 CfprManagedObjectDn,
    cfprAaaEpLoginRn                                                 SnmpAdminString,
    cfprAaaEpLoginDescr                                              SnmpAdminString,
    cfprAaaEpLoginId                                                 SnmpAdminString,
    cfprAaaEpLoginIntId                                              SnmpAdminString,
    cfprAaaEpLoginLocalHost                                          SnmpAdminString,
    cfprAaaEpLoginName                                               SnmpAdminString,
    cfprAaaEpLoginPolicyLevel                                        Gauge32,
    cfprAaaEpLoginPolicyOwner                                        CfprPolicyPolicyOwner,
    cfprAaaEpLoginRemoteHost                                         SnmpAdminString,
    cfprAaaEpLoginSession                                            CfprAaaSession,
    cfprAaaEpLoginSwitchId                                           CfprNetworkSwitchId
}

cfprAaaEpLoginInstanceId OBJECT-TYPE
    SYNTAX       CfprManagedObjectId
    MAX-ACCESS   not-accessible
    STATUS       current
    DESCRIPTION
        "Instance identifier of the managed object."
    ::= { cfprAaaEpLoginEntry 1 }

cfprAaaEpLoginDn OBJECT-TYPE
    SYNTAX       CfprManagedObjectDn
    MAX-ACCESS   read-only
    STATUS       current
    DESCRIPTION
        "Cisco Firepower aaa:EpLogin:dn managed object property"
    ::= { cfprAaaEpLoginEntry 2 }

cfprAaaEpLoginRn OBJECT-TYPE
    SYNTAX       SnmpAdminString
    MAX-ACCESS   read-only
    STATUS       current
    DESCRIPTION
        "Cisco Firepower aaa:EpLogin:rn managed object property"
    ::= { cfprAaaEpLoginEntry 3 }

cfprAaaEpLoginDescr OBJECT-TYPE
    SYNTAX       SnmpAdminString
    MAX-ACCESS   read-only
    STATUS       current
    DESCRIPTION
        "Cisco Firepower aaa:EpLogin:descr managed object property"
    ::= { cfprAaaEpLoginEntry 4 }

cfprAaaEpLoginId OBJECT-TYPE
    SYNTAX       SnmpAdminString
    MAX-ACCESS   read-only
    STATUS       current
    DESCRIPTION
        "Cisco Firepower aaa:EpLogin:id managed object property"
    ::= { cfprAaaEpLoginEntry 5 }

cfprAaaEpLoginIntId OBJECT-TYPE
    SYNTAX       SnmpAdminString
    MAX-ACCESS   read-only
    STATUS       current
    DESCRIPTION
        "Cisco Firepower aaa:EpLogin:intId managed object property"
    ::= { cfprAaaEpLoginEntry 6 }

cfprAaaEpLoginLocalHost OBJECT-TYPE
    SYNTAX       SnmpAdminString
    MAX-ACCESS   read-only
    STATUS       current
    DESCRIPTION
        "Cisco Firepower aaa:EpLogin:localHost managed object property"
    ::= { cfprAaaEpLoginEntry 7 }

cfprAaaEpLoginName OBJECT-TYPE
    SYNTAX       SnmpAdminString
    MAX-ACCESS   read-only
    STATUS       current
    DESCRIPTION
        "Cisco Firepower aaa:EpLogin:name managed object property"
    ::= { cfprAaaEpLoginEntry 8 }

cfprAaaEpLoginPolicyLevel OBJECT-TYPE
    SYNTAX       Gauge32
    MAX-ACCESS   read-only
    STATUS       current
    DESCRIPTION
        "Cisco Firepower aaa:EpLogin:policyLevel managed object property"
    ::= { cfprAaaEpLoginEntry 9 }

cfprAaaEpLoginPolicyOwner OBJECT-TYPE
    SYNTAX       CfprPolicyPolicyOwner
    MAX-ACCESS   read-only
    STATUS       current
    DESCRIPTION
        "Cisco Firepower aaa:EpLogin:policyOwner managed object property"
    ::= { cfprAaaEpLoginEntry 10 }

cfprAaaEpLoginRemoteHost OBJECT-TYPE
    SYNTAX       SnmpAdminString
    MAX-ACCESS   read-only
    STATUS       current
    DESCRIPTION
        "Cisco Firepower aaa:EpLogin:remoteHost managed object property"
    ::= { cfprAaaEpLoginEntry 11 }

cfprAaaEpLoginSession OBJECT-TYPE
    SYNTAX       CfprAaaSession
    MAX-ACCESS   read-only
    STATUS       current
    DESCRIPTION
        "Cisco Firepower aaa:EpLogin:session managed object property"
    ::= { cfprAaaEpLoginEntry 12 }

cfprAaaEpLoginSwitchId OBJECT-TYPE
    SYNTAX       CfprNetworkSwitchId
    MAX-ACCESS   read-only
    STATUS       current
    DESCRIPTION
        "Cisco Firepower aaa:EpLogin:switchId managed object property"
    ::= { cfprAaaEpLoginEntry 13 }

cfprAaaEpUserTable OBJECT-TYPE
    SYNTAX           SEQUENCE OF CfprAaaEpUserEntry
    MAX-ACCESS       not-accessible
    STATUS           current
    DESCRIPTION
        "Cisco Firepower aaa:EpUser managed object table"
    ::= { cfprAaaObjects 14 }

cfprAaaEpUserEntry OBJECT-TYPE
    SYNTAX           CfprAaaEpUserEntry
    MAX-ACCESS       not-accessible
    STATUS           current
    DESCRIPTION
        "Entry for the cfprAaaEpUserTable table."
    INDEX { cfprAaaEpUserInstanceId }
    ::= { cfprAaaEpUserTable 1 }

CfprAaaEpUserEntry ::= SEQUENCE {
    cfprAaaEpUserInstanceId                                          CfprManagedObjectId,
    cfprAaaEpUserDn                                                  CfprManagedObjectDn,
    cfprAaaEpUserRn                                                  SnmpAdminString,
    cfprAaaEpUserConfigState                                         CfprAaaConfigState,
    cfprAaaEpUserConfigStatusMessage                                 SnmpAdminString,
    cfprAaaEpUserDescr                                               SnmpAdminString,
    cfprAaaEpUserName                                                SnmpAdminString,
    cfprAaaEpUserPriv                                                CfprAaaEpAccess,
    cfprAaaEpUserPwd                                                 SnmpAdminString,
    cfprAaaEpUserPwdSet                                              TruthValue
}

cfprAaaEpUserInstanceId OBJECT-TYPE
    SYNTAX       CfprManagedObjectId
    MAX-ACCESS   not-accessible
    STATUS       current
    DESCRIPTION
        "Instance identifier of the managed object."
    ::= { cfprAaaEpUserEntry 1 }

cfprAaaEpUserDn OBJECT-TYPE
    SYNTAX       CfprManagedObjectDn
    MAX-ACCESS   read-only
    STATUS       current
    DESCRIPTION
        "Cisco Firepower aaa:EpUser:dn managed object property"
    ::= { cfprAaaEpUserEntry 2 }

cfprAaaEpUserRn OBJECT-TYPE
    SYNTAX       SnmpAdminString
    MAX-ACCESS   read-only
    STATUS       current
    DESCRIPTION
        "Cisco Firepower aaa:EpUser:rn managed object property"
    ::= { cfprAaaEpUserEntry 3 }

cfprAaaEpUserConfigState OBJECT-TYPE
    SYNTAX       CfprAaaConfigState
    MAX-ACCESS   read-only
    STATUS       current
    DESCRIPTION
        "Cisco Firepower aaa:EpUser:configState managed object property"
    ::= { cfprAaaEpUserEntry 4 }

cfprAaaEpUserConfigStatusMessage OBJECT-TYPE
    SYNTAX       SnmpAdminString
    MAX-ACCESS   read-only
    STATUS       current
    DESCRIPTION
        "Cisco Firepower aaa:EpUser:configStatusMessage
        managed object property"
    ::= { cfprAaaEpUserEntry 5 }

cfprAaaEpUserDescr OBJECT-TYPE
    SYNTAX       SnmpAdminString
    MAX-ACCESS   read-only
    STATUS       current
    DESCRIPTION
        "Cisco Firepower aaa:EpUser:descr managed object property"
    ::= { cfprAaaEpUserEntry 6 }

cfprAaaEpUserName OBJECT-TYPE
    SYNTAX       SnmpAdminString
    MAX-ACCESS   read-only
    STATUS       current
    DESCRIPTION
        "Cisco Firepower aaa:EpUser:name managed object property"
    ::= { cfprAaaEpUserEntry 7 }

cfprAaaEpUserPriv OBJECT-TYPE
    SYNTAX       CfprAaaEpAccess
    MAX-ACCESS   read-only
    STATUS       current
    DESCRIPTION
        "Cisco Firepower aaa:EpUser:priv managed object property"
    ::= { cfprAaaEpUserEntry 8 }

cfprAaaEpUserPwd OBJECT-TYPE
    SYNTAX       SnmpAdminString
    MAX-ACCESS   read-only
    STATUS       current
    DESCRIPTION
        "Cisco Firepower aaa:EpUser:pwd managed object property"
    ::= { cfprAaaEpUserEntry 9 }

cfprAaaEpUserPwdSet OBJECT-TYPE
    SYNTAX       TruthValue
    MAX-ACCESS   read-only
    STATUS       current
    DESCRIPTION
        "Cisco Firepower aaa:EpUser:pwdSet managed object property"
    ::= { cfprAaaEpUserEntry 10 }

cfprAaaExtMgmtCutThruTknTable OBJECT-TYPE
    SYNTAX           SEQUENCE OF CfprAaaExtMgmtCutThruTknEntry
    MAX-ACCESS       not-accessible
    STATUS           current
    DESCRIPTION
        "Cisco Firepower aaa:ExtMgmtCutThruTkn managed object table"
    ::= { cfprAaaObjects 15 }

cfprAaaExtMgmtCutThruTknEntry OBJECT-TYPE
    SYNTAX           CfprAaaExtMgmtCutThruTknEntry
    MAX-ACCESS       not-accessible
    STATUS           current
    DESCRIPTION
        "Entry for the cfprAaaExtMgmtCutThruTknTable table."
    INDEX { cfprAaaExtMgmtCutThruTknInstanceId }
    ::= { cfprAaaExtMgmtCutThruTknTable 1 }

CfprAaaExtMgmtCutThruTknEntry ::= SEQUENCE {
    cfprAaaExtMgmtCutThruTknInstanceId                               CfprManagedObjectId,
    cfprAaaExtMgmtCutThruTknDn                                       CfprManagedObjectDn,
    cfprAaaExtMgmtCutThruTknRn                                       SnmpAdminString,
    cfprAaaExtMgmtCutThruTknAuthDomain                               SnmpAdminString,
    cfprAaaExtMgmtCutThruTknAuthUser                                 SnmpAdminString,
    cfprAaaExtMgmtCutThruTknCreationTime                             DateAndTime,
    cfprAaaExtMgmtCutThruTknDescr                                    SnmpAdminString,
    cfprAaaExtMgmtCutThruTknIntId                                    SnmpAdminString,
    cfprAaaExtMgmtCutThruTknLocales                                  SnmpAdminString,
    cfprAaaExtMgmtCutThruTknName                                     SnmpAdminString,
    cfprAaaExtMgmtCutThruTknPnDn                                     SnmpAdminString,
    cfprAaaExtMgmtCutThruTknPolicyLevel                              Gauge32,
    cfprAaaExtMgmtCutThruTknPolicyOwner                              CfprPolicyPolicyOwner,
    cfprAaaExtMgmtCutThruTknPriv                                     CfprAaaAccess,
    cfprAaaExtMgmtCutThruTknRemote                                   TruthValue,
    cfprAaaExtMgmtCutThruTknToken                                    SnmpAdminString,
    cfprAaaExtMgmtCutThruTknType                                     CfprAaaExtMgmtAccess,
    cfprAaaExtMgmtCutThruTknUser                                     SnmpAdminString
}

cfprAaaExtMgmtCutThruTknInstanceId OBJECT-TYPE
    SYNTAX       CfprManagedObjectId
    MAX-ACCESS   not-accessible
    STATUS       current
    DESCRIPTION
        "Instance identifier of the managed object."
    ::= { cfprAaaExtMgmtCutThruTknEntry 1 }

cfprAaaExtMgmtCutThruTknDn OBJECT-TYPE
    SYNTAX       CfprManagedObjectDn
    MAX-ACCESS   read-only
    STATUS       current
    DESCRIPTION
        "Cisco Firepower aaa:ExtMgmtCutThruTkn:dn managed object property"
    ::= { cfprAaaExtMgmtCutThruTknEntry 2 }

cfprAaaExtMgmtCutThruTknRn OBJECT-TYPE
    SYNTAX       SnmpAdminString
    MAX-ACCESS   read-only
    STATUS       current
    DESCRIPTION
        "Cisco Firepower aaa:ExtMgmtCutThruTkn:rn managed object property"
    ::= { cfprAaaExtMgmtCutThruTknEntry 3 }

cfprAaaExtMgmtCutThruTknAuthDomain OBJECT-TYPE
    SYNTAX       SnmpAdminString
    MAX-ACCESS   read-only
    STATUS       current
    DESCRIPTION
        "Cisco Firepower aaa:ExtMgmtCutThruTkn:authDomain
        managed object property"
    ::= { cfprAaaExtMgmtCutThruTknEntry 4 }

cfprAaaExtMgmtCutThruTknAuthUser OBJECT-TYPE
    SYNTAX       SnmpAdminString
    MAX-ACCESS   read-only
    STATUS       current
    DESCRIPTION
        "Cisco Firepower aaa:ExtMgmtCutThruTkn:authUser
        managed object property"
    ::= { cfprAaaExtMgmtCutThruTknEntry 5 }

cfprAaaExtMgmtCutThruTknCreationTime OBJECT-TYPE
    SYNTAX       DateAndTime
    MAX-ACCESS   read-only
    STATUS       current
    DESCRIPTION
        "Cisco Firepower aaa:ExtMgmtCutThruTkn:creationTime
        managed object property"
    ::= { cfprAaaExtMgmtCutThruTknEntry 6 }

cfprAaaExtMgmtCutThruTknDescr OBJECT-TYPE
    SYNTAX       SnmpAdminString
    MAX-ACCESS   read-only
    STATUS       current
    DESCRIPTION
        "Cisco Firepower aaa:ExtMgmtCutThruTkn:descr managed
        object property"
    ::= { cfprAaaExtMgmtCutThruTknEntry 7 }

cfprAaaExtMgmtCutThruTknIntId OBJECT-TYPE
    SYNTAX       SnmpAdminString
    MAX-ACCESS   read-only
    STATUS       current
    DESCRIPTION
        "Cisco Firepower aaa:ExtMgmtCutThruTkn:intId managed
        object property"
    ::= { cfprAaaExtMgmtCutThruTknEntry 8 }

cfprAaaExtMgmtCutThruTknLocales OBJECT-TYPE
    SYNTAX       SnmpAdminString
    MAX-ACCESS   read-only
    STATUS       current
    DESCRIPTION
        "Cisco Firepower aaa:ExtMgmtCutThruTkn:locales
        managed object property"
    ::= { cfprAaaExtMgmtCutThruTknEntry 9 }

cfprAaaExtMgmtCutThruTknName OBJECT-TYPE
    SYNTAX       SnmpAdminString
    MAX-ACCESS   read-only
    STATUS       current
    DESCRIPTION
        "Cisco Firepower aaa:ExtMgmtCutThruTkn:name managed
        object property"
    ::= { cfprAaaExtMgmtCutThruTknEntry 10 }

cfprAaaExtMgmtCutThruTknPnDn OBJECT-TYPE
    SYNTAX       SnmpAdminString
    MAX-ACCESS   read-only
    STATUS       current
    DESCRIPTION
        "Cisco Firepower aaa:ExtMgmtCutThruTkn:pnDn managed
        object property"
    ::= { cfprAaaExtMgmtCutThruTknEntry 11 }

cfprAaaExtMgmtCutThruTknPolicyLevel OBJECT-TYPE
    SYNTAX       Gauge32
    MAX-ACCESS   read-only
    STATUS       current
    DESCRIPTION
        "Cisco Firepower aaa:ExtMgmtCutThruTkn:policyLevel
        managed object property"
    ::= { cfprAaaExtMgmtCutThruTknEntry 12 }

cfprAaaExtMgmtCutThruTknPolicyOwner OBJECT-TYPE
    SYNTAX       CfprPolicyPolicyOwner
    MAX-ACCESS   read-only
    STATUS       current
    DESCRIPTION
        "Cisco Firepower aaa:ExtMgmtCutThruTkn:policyOwner
        managed object property"
    ::= { cfprAaaExtMgmtCutThruTknEntry 13 }

cfprAaaExtMgmtCutThruTknPriv OBJECT-TYPE
    SYNTAX       CfprAaaAccess
    MAX-ACCESS   read-only
    STATUS       current
    DESCRIPTION
        "Cisco Firepower aaa:ExtMgmtCutThruTkn:priv managed
        object property"
    ::= { cfprAaaExtMgmtCutThruTknEntry 14 }

cfprAaaExtMgmtCutThruTknRemote OBJECT-TYPE
    SYNTAX       TruthValue
    MAX-ACCESS   read-only
    STATUS       current
    DESCRIPTION
        "Cisco Firepower aaa:ExtMgmtCutThruTkn:remote managed
        object property"
    ::= { cfprAaaExtMgmtCutThruTknEntry 15 }

cfprAaaExtMgmtCutThruTknToken OBJECT-TYPE
    SYNTAX       SnmpAdminString
    MAX-ACCESS   read-only
    STATUS       current
    DESCRIPTION
        "Cisco Firepower aaa:ExtMgmtCutThruTkn:token managed
        object property"
    ::= { cfprAaaExtMgmtCutThruTknEntry 16 }

cfprAaaExtMgmtCutThruTknType OBJECT-TYPE
    SYNTAX       CfprAaaExtMgmtAccess
    MAX-ACCESS   read-only
    STATUS       current
    DESCRIPTION
        "Cisco Firepower aaa:ExtMgmtCutThruTkn:type managed
        object property"
    ::= { cfprAaaExtMgmtCutThruTknEntry 17 }

cfprAaaExtMgmtCutThruTknUser OBJECT-TYPE
    SYNTAX       SnmpAdminString
    MAX-ACCESS   read-only
    STATUS       current
    DESCRIPTION
        "Cisco Firepower aaa:ExtMgmtCutThruTkn:user managed
        object property"
    ::= { cfprAaaExtMgmtCutThruTknEntry 18 }

cfprAaaLdapEpTable OBJECT-TYPE
    SYNTAX           SEQUENCE OF CfprAaaLdapEpEntry
    MAX-ACCESS       not-accessible
    STATUS           current
    DESCRIPTION
        "Cisco Firepower aaa:LdapEp managed object table"
    ::= { cfprAaaObjects 16 }

cfprAaaLdapEpEntry OBJECT-TYPE
    SYNTAX           CfprAaaLdapEpEntry
    MAX-ACCESS       not-accessible
    STATUS           current
    DESCRIPTION
        "Entry for the cfprAaaLdapEpTable table."
    INDEX { cfprAaaLdapEpInstanceId }
    ::= { cfprAaaLdapEpTable 1 }

CfprAaaLdapEpEntry ::= SEQUENCE {
    cfprAaaLdapEpInstanceId                                          CfprManagedObjectId,
    cfprAaaLdapEpDn                                                  CfprManagedObjectDn,
    cfprAaaLdapEpRn                                                  SnmpAdminString,
    cfprAaaLdapEpAttribute                                           SnmpAdminString,
    cfprAaaLdapEpBasedn                                              SnmpAdminString,
    cfprAaaLdapEpDescr                                               SnmpAdminString,
    cfprAaaLdapEpFilter                                              SnmpAdminString,
    cfprAaaLdapEpFsmDescr                                            SnmpAdminString,
    cfprAaaLdapEpFsmPrev                                             SnmpAdminString,
    cfprAaaLdapEpFsmProgr                                            Gauge32,
    cfprAaaLdapEpFsmRmtInvErrCode                                    Gauge32,
    cfprAaaLdapEpFsmRmtInvErrDescr                                   SnmpAdminString,
    cfprAaaLdapEpFsmRmtInvRslt                                       CfprConditionRemoteInvRslt,
    cfprAaaLdapEpFsmStageDescr                                       SnmpAdminString,
    cfprAaaLdapEpFsmStamp                                            DateAndTime,
    cfprAaaLdapEpFsmStatus                                           SnmpAdminString,
    cfprAaaLdapEpFsmTry                                              Gauge32,
    cfprAaaLdapEpIntId                                               SnmpAdminString,
    cfprAaaLdapEpName                                                SnmpAdminString,
    cfprAaaLdapEpPolicyLevel                                         Gauge32,
    cfprAaaLdapEpPolicyOwner                                         CfprPolicyPolicyOwner,
    cfprAaaLdapEpRetries                                             Gauge32,
    cfprAaaLdapEpTimeout                                             Gauge32,
    cfprAaaLdapEpTlsVer                                              CfprCommTlsVerType
}

cfprAaaLdapEpInstanceId OBJECT-TYPE
    SYNTAX       CfprManagedObjectId
    MAX-ACCESS   not-accessible
    STATUS       current
    DESCRIPTION
        "Instance identifier of the managed object."
    ::= { cfprAaaLdapEpEntry 1 }

cfprAaaLdapEpDn OBJECT-TYPE
    SYNTAX       CfprManagedObjectDn
    MAX-ACCESS   read-only
    STATUS       current
    DESCRIPTION
        "Cisco Firepower aaa:LdapEp:dn managed object property"
    ::= { cfprAaaLdapEpEntry 2 }

cfprAaaLdapEpRn OBJECT-TYPE
    SYNTAX       SnmpAdminString
    MAX-ACCESS   read-only
    STATUS       current
    DESCRIPTION
        "Cisco Firepower aaa:LdapEp:rn managed object property"
    ::= { cfprAaaLdapEpEntry 3 }

cfprAaaLdapEpAttribute OBJECT-TYPE
    SYNTAX       SnmpAdminString
    MAX-ACCESS   read-only
    STATUS       current
    DESCRIPTION
        "Cisco Firepower aaa:LdapEp:attribute managed object property"
    ::= { cfprAaaLdapEpEntry 4 }

cfprAaaLdapEpBasedn OBJECT-TYPE
    SYNTAX       SnmpAdminString
    MAX-ACCESS   read-only
    STATUS       current
    DESCRIPTION
        "Cisco Firepower aaa:LdapEp:basedn managed object property"
    ::= { cfprAaaLdapEpEntry 5 }

cfprAaaLdapEpDescr OBJECT-TYPE
    SYNTAX       SnmpAdminString
    MAX-ACCESS   read-only
    STATUS       current
    DESCRIPTION
        "Cisco Firepower aaa:LdapEp:descr managed object property"
    ::= { cfprAaaLdapEpEntry 6 }

cfprAaaLdapEpFilter OBJECT-TYPE
    SYNTAX       SnmpAdminString
    MAX-ACCESS   read-only
    STATUS       current
    DESCRIPTION
        "Cisco Firepower aaa:LdapEp:filter managed object property"
    ::= { cfprAaaLdapEpEntry 7 }

cfprAaaLdapEpFsmDescr OBJECT-TYPE
    SYNTAX       SnmpAdminString
    MAX-ACCESS   read-only
    STATUS       current
    DESCRIPTION
        "Cisco Firepower aaa:LdapEp:fsmDescr managed object property"
    ::= { cfprAaaLdapEpEntry 8 }

cfprAaaLdapEpFsmPrev OBJECT-TYPE
    SYNTAX       SnmpAdminString
    MAX-ACCESS   read-only
    STATUS       current
    DESCRIPTION
        "Cisco Firepower aaa:LdapEp:fsmPrev managed object property"
    ::= { cfprAaaLdapEpEntry 9 }

cfprAaaLdapEpFsmProgr OBJECT-TYPE
    SYNTAX       Gauge32
    MAX-ACCESS   read-only
    STATUS       current
    DESCRIPTION
        "Cisco Firepower aaa:LdapEp:fsmProgr managed object property"
    ::= { cfprAaaLdapEpEntry 10 }

cfprAaaLdapEpFsmRmtInvErrCode OBJECT-TYPE
    SYNTAX       Gauge32
    MAX-ACCESS   read-only
    STATUS       current
    DESCRIPTION
        "Cisco Firepower aaa:LdapEp:fsmRmtInvErrCode managed
        object property"
    ::= { cfprAaaLdapEpEntry 11 }

cfprAaaLdapEpFsmRmtInvErrDescr OBJECT-TYPE
    SYNTAX       SnmpAdminString
    MAX-ACCESS   read-only
    STATUS       current
    DESCRIPTION
        "Cisco Firepower aaa:LdapEp:fsmRmtInvErrDescr managed
        object property"
    ::= { cfprAaaLdapEpEntry 12 }

cfprAaaLdapEpFsmRmtInvRslt OBJECT-TYPE
    SYNTAX       CfprConditionRemoteInvRslt
    MAX-ACCESS   read-only
    STATUS       current
    DESCRIPTION
        "Cisco Firepower aaa:LdapEp:fsmRmtInvRslt managed object property"
    ::= { cfprAaaLdapEpEntry 13 }

cfprAaaLdapEpFsmStageDescr OBJECT-TYPE
    SYNTAX       SnmpAdminString
    MAX-ACCESS   read-only
    STATUS       current
    DESCRIPTION
        "Cisco Firepower aaa:LdapEp:fsmStageDescr managed object property"
    ::= { cfprAaaLdapEpEntry 14 }

cfprAaaLdapEpFsmStamp OBJECT-TYPE
    SYNTAX       DateAndTime
    MAX-ACCESS   read-only
    STATUS       current
    DESCRIPTION
        "Cisco Firepower aaa:LdapEp:fsmStamp managed object property"
    ::= { cfprAaaLdapEpEntry 15 }

cfprAaaLdapEpFsmStatus OBJECT-TYPE
    SYNTAX       SnmpAdminString
    MAX-ACCESS   read-only
    STATUS       current
    DESCRIPTION
        "Cisco Firepower aaa:LdapEp:fsmStatus managed object property"
    ::= { cfprAaaLdapEpEntry 16 }

cfprAaaLdapEpFsmTry OBJECT-TYPE
    SYNTAX       Gauge32
    MAX-ACCESS   read-only
    STATUS       current
    DESCRIPTION
        "Cisco Firepower aaa:LdapEp:fsmTry managed object property"
    ::= { cfprAaaLdapEpEntry 17 }

cfprAaaLdapEpIntId OBJECT-TYPE
    SYNTAX       SnmpAdminString
    MAX-ACCESS   read-only
    STATUS       current
    DESCRIPTION
        "Cisco Firepower aaa:LdapEp:intId managed object property"
    ::= { cfprAaaLdapEpEntry 18 }

cfprAaaLdapEpName OBJECT-TYPE
    SYNTAX       SnmpAdminString
    MAX-ACCESS   read-only
    STATUS       current
    DESCRIPTION
        "Cisco Firepower aaa:LdapEp:name managed object property"
    ::= { cfprAaaLdapEpEntry 19 }

cfprAaaLdapEpPolicyLevel OBJECT-TYPE
    SYNTAX       Gauge32
    MAX-ACCESS   read-only
    STATUS       current
    DESCRIPTION
        "Cisco Firepower aaa:LdapEp:policyLevel managed object property"
    ::= { cfprAaaLdapEpEntry 20 }

cfprAaaLdapEpPolicyOwner OBJECT-TYPE
    SYNTAX       CfprPolicyPolicyOwner
    MAX-ACCESS   read-only
    STATUS       current
    DESCRIPTION
        "Cisco Firepower aaa:LdapEp:policyOwner managed object property"
    ::= { cfprAaaLdapEpEntry 21 }

cfprAaaLdapEpRetries OBJECT-TYPE
    SYNTAX       Gauge32
    MAX-ACCESS   read-only
    STATUS       current
    DESCRIPTION
        "Cisco Firepower aaa:LdapEp:retries managed object property"
    ::= { cfprAaaLdapEpEntry 22 }

cfprAaaLdapEpTimeout OBJECT-TYPE
    SYNTAX       Gauge32
    MAX-ACCESS   read-only
    STATUS       current
    DESCRIPTION
        "Cisco Firepower aaa:LdapEp:timeout managed object property"
    ::= { cfprAaaLdapEpEntry 23 }

cfprAaaLdapEpTlsVer OBJECT-TYPE
    SYNTAX       CfprCommTlsVerType
    MAX-ACCESS   read-only
    STATUS       current
    DESCRIPTION
        "Cisco Firepower aaa:LdapEp:tlsVer managed object property"
    ::= { cfprAaaLdapEpEntry 24 }

cfprAaaLdapEpFsmTable OBJECT-TYPE
    SYNTAX           SEQUENCE OF CfprAaaLdapEpFsmEntry
    MAX-ACCESS       not-accessible
    STATUS           current
    DESCRIPTION
        "Cisco Firepower aaa:LdapEpFsm managed object table"
    ::= { cfprAaaObjects 17 }

cfprAaaLdapEpFsmEntry OBJECT-TYPE
    SYNTAX           CfprAaaLdapEpFsmEntry
    MAX-ACCESS       not-accessible
    STATUS           current
    DESCRIPTION
        "Entry for the cfprAaaLdapEpFsmTable table."
    INDEX { cfprAaaLdapEpFsmInstanceId }
    ::= { cfprAaaLdapEpFsmTable 1 }

CfprAaaLdapEpFsmEntry ::= SEQUENCE {
    cfprAaaLdapEpFsmInstanceId                                       CfprManagedObjectId,
    cfprAaaLdapEpFsmDn                                               CfprManagedObjectDn,
    cfprAaaLdapEpFsmRn                                               SnmpAdminString,
    cfprAaaLdapEpFsmCompletionTime                                   DateAndTime,
    cfprAaaLdapEpFsmCurrentFsm                                       CfprAaaLdapEpFsmCurrentFsm,
    cfprAaaLdapEpFsmDescrData                                        SnmpAdminString,
    cfprAaaLdapEpFsmFsmStatus                                        CfprFsmFsmStageStatus,
    cfprAaaLdapEpFsmProgress                                         Gauge32,
    cfprAaaLdapEpFsmRmtErrCode                                       Gauge32,
    cfprAaaLdapEpFsmRmtErrDescr                                      SnmpAdminString,
    cfprAaaLdapEpFsmRmtRslt                                          CfprConditionRemoteInvRslt
}

cfprAaaLdapEpFsmInstanceId OBJECT-TYPE
    SYNTAX       CfprManagedObjectId
    MAX-ACCESS   not-accessible
    STATUS       current
    DESCRIPTION
        "Instance identifier of the managed object."
    ::= { cfprAaaLdapEpFsmEntry 1 }

cfprAaaLdapEpFsmDn OBJECT-TYPE
    SYNTAX       CfprManagedObjectDn
    MAX-ACCESS   read-only
    STATUS       current
    DESCRIPTION
        "Cisco Firepower aaa:LdapEpFsm:dn managed object property"
    ::= { cfprAaaLdapEpFsmEntry 2 }

cfprAaaLdapEpFsmRn OBJECT-TYPE
    SYNTAX       SnmpAdminString
    MAX-ACCESS   read-only
    STATUS       current
    DESCRIPTION
        "Cisco Firepower aaa:LdapEpFsm:rn managed object property"
    ::= { cfprAaaLdapEpFsmEntry 3 }

cfprAaaLdapEpFsmCompletionTime OBJECT-TYPE
    SYNTAX       DateAndTime
    MAX-ACCESS   read-only
    STATUS       current
    DESCRIPTION
        "Cisco Firepower aaa:LdapEpFsm:completionTime managed
        object property"
    ::= { cfprAaaLdapEpFsmEntry 4 }

cfprAaaLdapEpFsmCurrentFsm OBJECT-TYPE
    SYNTAX       CfprAaaLdapEpFsmCurrentFsm
    MAX-ACCESS   read-only
    STATUS       current
    DESCRIPTION
        "Cisco Firepower aaa:LdapEpFsm:currentFsm managed object property"
    ::= { cfprAaaLdapEpFsmEntry 5 }

cfprAaaLdapEpFsmDescrData OBJECT-TYPE
    SYNTAX       SnmpAdminString
    MAX-ACCESS   read-only
    STATUS       current
    DESCRIPTION
        "Cisco Firepower aaa:LdapEpFsm:descr managed object property"
    ::= { cfprAaaLdapEpFsmEntry 6 }

cfprAaaLdapEpFsmFsmStatus OBJECT-TYPE
    SYNTAX       CfprFsmFsmStageStatus
    MAX-ACCESS   read-only
    STATUS       current
    DESCRIPTION
        "Cisco Firepower aaa:LdapEpFsm:fsmStatus managed object property"
    ::= { cfprAaaLdapEpFsmEntry 7 }

cfprAaaLdapEpFsmProgress OBJECT-TYPE
    SYNTAX       Gauge32
    MAX-ACCESS   read-only
    STATUS       current
    DESCRIPTION
        "Cisco Firepower aaa:LdapEpFsm:progress managed object property"
    ::= { cfprAaaLdapEpFsmEntry 8 }

cfprAaaLdapEpFsmRmtErrCode OBJECT-TYPE
    SYNTAX       Gauge32
    MAX-ACCESS   read-only
    STATUS       current
    DESCRIPTION
        "Cisco Firepower aaa:LdapEpFsm:rmtErrCode managed object property"
    ::= { cfprAaaLdapEpFsmEntry 9 }

cfprAaaLdapEpFsmRmtErrDescr OBJECT-TYPE
    SYNTAX       SnmpAdminString
    MAX-ACCESS   read-only
    STATUS       current
    DESCRIPTION
        "Cisco Firepower aaa:LdapEpFsm:rmtErrDescr managed
        object property"
    ::= { cfprAaaLdapEpFsmEntry 10 }

cfprAaaLdapEpFsmRmtRslt OBJECT-TYPE
    SYNTAX       CfprConditionRemoteInvRslt
    MAX-ACCESS   read-only
    STATUS       current
    DESCRIPTION
        "Cisco Firepower aaa:LdapEpFsm:rmtRslt managed object property"
    ::= { cfprAaaLdapEpFsmEntry 11 }

cfprAaaLdapEpFsmStageTable OBJECT-TYPE
    SYNTAX           SEQUENCE OF CfprAaaLdapEpFsmStageEntry
    MAX-ACCESS       not-accessible
    STATUS           current
    DESCRIPTION
        "Cisco Firepower aaa:LdapEpFsmStage managed object table"
    ::= { cfprAaaObjects 18 }

cfprAaaLdapEpFsmStageEntry OBJECT-TYPE
    SYNTAX           CfprAaaLdapEpFsmStageEntry
    MAX-ACCESS       not-accessible
    STATUS           current
    DESCRIPTION
        "Entry for the cfprAaaLdapEpFsmStageTable table."
    INDEX { cfprAaaLdapEpFsmStageInstanceId }
    ::= { cfprAaaLdapEpFsmStageTable 1 }

CfprAaaLdapEpFsmStageEntry ::= SEQUENCE {
    cfprAaaLdapEpFsmStageInstanceId                                  CfprManagedObjectId,
    cfprAaaLdapEpFsmStageDn                                          CfprManagedObjectDn,
    cfprAaaLdapEpFsmStageRn                                          SnmpAdminString,
    cfprAaaLdapEpFsmStageDescrData                                   SnmpAdminString,
    cfprAaaLdapEpFsmStageLastUpdateTime                              DateAndTime,
    cfprAaaLdapEpFsmStageName                                        CfprAaaLdapEpFsmStageName,
    cfprAaaLdapEpFsmStageOrder                                       Gauge32,
    cfprAaaLdapEpFsmStageRetry                                       Gauge32,
    cfprAaaLdapEpFsmStageStageStatus                                 CfprFsmFsmStageStatus
}

cfprAaaLdapEpFsmStageInstanceId OBJECT-TYPE
    SYNTAX       CfprManagedObjectId
    MAX-ACCESS   not-accessible
    STATUS       current
    DESCRIPTION
        "Instance identifier of the managed object."
    ::= { cfprAaaLdapEpFsmStageEntry 1 }

cfprAaaLdapEpFsmStageDn OBJECT-TYPE
    SYNTAX       CfprManagedObjectDn
    MAX-ACCESS   read-only
    STATUS       current
    DESCRIPTION
        "Cisco Firepower aaa:LdapEpFsmStage:dn managed object property"
    ::= { cfprAaaLdapEpFsmStageEntry 2 }

cfprAaaLdapEpFsmStageRn OBJECT-TYPE
    SYNTAX       SnmpAdminString
    MAX-ACCESS   read-only
    STATUS       current
    DESCRIPTION
        "Cisco Firepower aaa:LdapEpFsmStage:rn managed object property"
    ::= { cfprAaaLdapEpFsmStageEntry 3 }

cfprAaaLdapEpFsmStageDescrData OBJECT-TYPE
    SYNTAX       SnmpAdminString
    MAX-ACCESS   read-only
    STATUS       current
    DESCRIPTION
        "Cisco Firepower aaa:LdapEpFsmStage:descr managed object property"
    ::= { cfprAaaLdapEpFsmStageEntry 4 }

cfprAaaLdapEpFsmStageLastUpdateTime OBJECT-TYPE
    SYNTAX       DateAndTime
    MAX-ACCESS   read-only
    STATUS       current
    DESCRIPTION
        "Cisco Firepower aaa:LdapEpFsmStage:lastUpdateTime
        managed object property"
    ::= { cfprAaaLdapEpFsmStageEntry 5 }

cfprAaaLdapEpFsmStageName OBJECT-TYPE
    SYNTAX       CfprAaaLdapEpFsmStageName
    MAX-ACCESS   read-only
    STATUS       current
    DESCRIPTION
        "Cisco Firepower aaa:LdapEpFsmStage:name managed object property"
    ::= { cfprAaaLdapEpFsmStageEntry 6 }

cfprAaaLdapEpFsmStageOrder OBJECT-TYPE
    SYNTAX       Gauge32
    MAX-ACCESS   read-only
    STATUS       current
    DESCRIPTION
        "Cisco Firepower aaa:LdapEpFsmStage:order managed object property"
    ::= { cfprAaaLdapEpFsmStageEntry 7 }

cfprAaaLdapEpFsmStageRetry OBJECT-TYPE
    SYNTAX       Gauge32
    MAX-ACCESS   read-only
    STATUS       current
    DESCRIPTION
        "Cisco Firepower aaa:LdapEpFsmStage:retry managed object property"
    ::= { cfprAaaLdapEpFsmStageEntry 8 }

cfprAaaLdapEpFsmStageStageStatus OBJECT-TYPE
    SYNTAX       CfprFsmFsmStageStatus
    MAX-ACCESS   read-only
    STATUS       current
    DESCRIPTION
        "Cisco Firepower aaa:LdapEpFsmStage:stageStatus
        managed object property"
    ::= { cfprAaaLdapEpFsmStageEntry 9 }

cfprAaaLdapGroupTable OBJECT-TYPE
    SYNTAX           SEQUENCE OF CfprAaaLdapGroupEntry
    MAX-ACCESS       not-accessible
    STATUS           current
    DESCRIPTION
        "Cisco Firepower aaa:LdapGroup managed object table"
    ::= { cfprAaaObjects 19 }

cfprAaaLdapGroupEntry OBJECT-TYPE
    SYNTAX           CfprAaaLdapGroupEntry
    MAX-ACCESS       not-accessible
    STATUS           current
    DESCRIPTION
        "Entry for the cfprAaaLdapGroupTable table."
    INDEX { cfprAaaLdapGroupInstanceId }
    ::= { cfprAaaLdapGroupTable 1 }

CfprAaaLdapGroupEntry ::= SEQUENCE {
    cfprAaaLdapGroupInstanceId                                       CfprManagedObjectId,
    cfprAaaLdapGroupDn                                               CfprManagedObjectDn,
    cfprAaaLdapGroupRn                                               SnmpAdminString,
    cfprAaaLdapGroupDescr                                            SnmpAdminString,
    cfprAaaLdapGroupName                                             SnmpAdminString
}

cfprAaaLdapGroupInstanceId OBJECT-TYPE
    SYNTAX       CfprManagedObjectId
    MAX-ACCESS   not-accessible
    STATUS       current
    DESCRIPTION
        "Instance identifier of the managed object."
    ::= { cfprAaaLdapGroupEntry 1 }

cfprAaaLdapGroupDn OBJECT-TYPE
    SYNTAX       CfprManagedObjectDn
    MAX-ACCESS   read-only
    STATUS       current
    DESCRIPTION
        "Cisco Firepower aaa:LdapGroup:dn managed object property"
    ::= { cfprAaaLdapGroupEntry 2 }

cfprAaaLdapGroupRn OBJECT-TYPE
    SYNTAX       SnmpAdminString
    MAX-ACCESS   read-only
    STATUS       current
    DESCRIPTION
        "Cisco Firepower aaa:LdapGroup:rn managed object property"
    ::= { cfprAaaLdapGroupEntry 3 }

cfprAaaLdapGroupDescr OBJECT-TYPE
    SYNTAX       SnmpAdminString
    MAX-ACCESS   read-only
    STATUS       current
    DESCRIPTION
        "Cisco Firepower aaa:LdapGroup:descr managed object property"
    ::= { cfprAaaLdapGroupEntry 4 }

cfprAaaLdapGroupName OBJECT-TYPE
    SYNTAX       SnmpAdminString
    MAX-ACCESS   read-only
    STATUS       current
    DESCRIPTION
        "Cisco Firepower aaa:LdapGroup:name managed object property"
    ::= { cfprAaaLdapGroupEntry 5 }

cfprAaaLdapGroupRuleTable OBJECT-TYPE
    SYNTAX           SEQUENCE OF CfprAaaLdapGroupRuleEntry
    MAX-ACCESS       not-accessible
    STATUS           current
    DESCRIPTION
        "Cisco Firepower aaa:LdapGroupRule managed object table"
    ::= { cfprAaaObjects 20 }

cfprAaaLdapGroupRuleEntry OBJECT-TYPE
    SYNTAX           CfprAaaLdapGroupRuleEntry
    MAX-ACCESS       not-accessible
    STATUS           current
    DESCRIPTION
        "Entry for the cfprAaaLdapGroupRuleTable table."
    INDEX { cfprAaaLdapGroupRuleInstanceId }
    ::= { cfprAaaLdapGroupRuleTable 1 }

CfprAaaLdapGroupRuleEntry ::= SEQUENCE {
    cfprAaaLdapGroupRuleInstanceId                                   CfprManagedObjectId,
    cfprAaaLdapGroupRuleDn                                           CfprManagedObjectDn,
    cfprAaaLdapGroupRuleRn                                           SnmpAdminString,
    cfprAaaLdapGroupRuleAuthorization                                CfprAaaLdapGroupRuleAuthorization,
    cfprAaaLdapGroupRuleDescr                                        SnmpAdminString,
    cfprAaaLdapGroupRuleName                                         SnmpAdminString,
    cfprAaaLdapGroupRuleTargetAttr                                   SnmpAdminString,
    cfprAaaLdapGroupRuleTraversal                                    CfprAaaLdapGroupRuleTraversal,
    cfprAaaLdapGroupRuleUsePrimaryGroup                              TruthValue
}

cfprAaaLdapGroupRuleInstanceId OBJECT-TYPE
    SYNTAX       CfprManagedObjectId
    MAX-ACCESS   not-accessible
    STATUS       current
    DESCRIPTION
        "Instance identifier of the managed object."
    ::= { cfprAaaLdapGroupRuleEntry 1 }

cfprAaaLdapGroupRuleDn OBJECT-TYPE
    SYNTAX       CfprManagedObjectDn
    MAX-ACCESS   read-only
    STATUS       current
    DESCRIPTION
        "Cisco Firepower aaa:LdapGroupRule:dn managed object property"
    ::= { cfprAaaLdapGroupRuleEntry 2 }

cfprAaaLdapGroupRuleRn OBJECT-TYPE
    SYNTAX       SnmpAdminString
    MAX-ACCESS   read-only
    STATUS       current
    DESCRIPTION
        "Cisco Firepower aaa:LdapGroupRule:rn managed object property"
    ::= { cfprAaaLdapGroupRuleEntry 3 }

cfprAaaLdapGroupRuleAuthorization OBJECT-TYPE
    SYNTAX       CfprAaaLdapGroupRuleAuthorization
    MAX-ACCESS   read-only
    STATUS       current
    DESCRIPTION
        "Cisco Firepower aaa:LdapGroupRule:authorization
        managed object property"
    ::= { cfprAaaLdapGroupRuleEntry 4 }

cfprAaaLdapGroupRuleDescr OBJECT-TYPE
    SYNTAX       SnmpAdminString
    MAX-ACCESS   read-only
    STATUS       current
    DESCRIPTION
        "Cisco Firepower aaa:LdapGroupRule:descr managed object property"
    ::= { cfprAaaLdapGroupRuleEntry 5 }

cfprAaaLdapGroupRuleName OBJECT-TYPE
    SYNTAX       SnmpAdminString
    MAX-ACCESS   read-only
    STATUS       current
    DESCRIPTION
        "Cisco Firepower aaa:LdapGroupRule:name managed object property"
    ::= { cfprAaaLdapGroupRuleEntry 6 }

cfprAaaLdapGroupRuleTargetAttr OBJECT-TYPE
    SYNTAX       SnmpAdminString
    MAX-ACCESS   read-only
    STATUS       current
    DESCRIPTION
        "Cisco Firepower aaa:LdapGroupRule:targetAttr managed
        object property"
    ::= { cfprAaaLdapGroupRuleEntry 7 }

cfprAaaLdapGroupRuleTraversal OBJECT-TYPE
    SYNTAX       CfprAaaLdapGroupRuleTraversal
    MAX-ACCESS   read-only
    STATUS       current
    DESCRIPTION
        "Cisco Firepower aaa:LdapGroupRule:traversal managed
        object property"
    ::= { cfprAaaLdapGroupRuleEntry 8 }

cfprAaaLdapGroupRuleUsePrimaryGroup OBJECT-TYPE
    SYNTAX       TruthValue
    MAX-ACCESS   read-only
    STATUS       current
    DESCRIPTION
        "Cisco Firepower aaa:LdapGroupRule:usePrimaryGroup
        managed object property"
    ::= { cfprAaaLdapGroupRuleEntry 9 }

cfprAaaLdapProviderTable OBJECT-TYPE
    SYNTAX           SEQUENCE OF CfprAaaLdapProviderEntry
    MAX-ACCESS       not-accessible
    STATUS           current
    DESCRIPTION
        "Cisco Firepower aaa:LdapProvider managed object table"
    ::= { cfprAaaObjects 21 }

cfprAaaLdapProviderEntry OBJECT-TYPE
    SYNTAX           CfprAaaLdapProviderEntry
    MAX-ACCESS       not-accessible
    STATUS           current
    DESCRIPTION
        "Entry for the cfprAaaLdapProviderTable table."
    INDEX { cfprAaaLdapProviderInstanceId }
    ::= { cfprAaaLdapProviderTable 1 }

CfprAaaLdapProviderEntry ::= SEQUENCE {
    cfprAaaLdapProviderInstanceId                                    CfprManagedObjectId,
    cfprAaaLdapProviderDn                                            CfprManagedObjectDn,
    cfprAaaLdapProviderRn                                            SnmpAdminString,
    cfprAaaLdapProviderAttribute                                     SnmpAdminString,
    cfprAaaLdapProviderBasedn                                        SnmpAdminString,
    cfprAaaLdapProviderDescr                                         SnmpAdminString,
    cfprAaaLdapProviderEnableSSL                                     TruthValue,
    cfprAaaLdapProviderEncKey                                        SnmpAdminString,
    cfprAaaLdapProviderFilter                                        SnmpAdminString,
    cfprAaaLdapProviderKey                                           SnmpAdminString,
    cfprAaaLdapProviderKeySet                                        TruthValue,
    cfprAaaLdapProviderName                                          SnmpAdminString,
    cfprAaaLdapProviderOrder                                         Gauge32,
    cfprAaaLdapProviderPort                                          Gauge32,
    cfprAaaLdapProviderRetries                                       Gauge32,
    cfprAaaLdapProviderRootdn                                        SnmpAdminString,
    cfprAaaLdapProviderTimeout                                       Gauge32,
    cfprAaaLdapProviderVendor                                        CfprAaaLdapVendor,
    cfprAaaLdapProviderKeyring                                       SnmpAdminString,
    cfprAaaLdapProviderRevokePolicy                                  CfprAaaRevokePolicy,
    cfprAaaLdapProviderCipher                                        SnmpAdminString,
    cfprAaaLdapProviderCiphermode                                    CfprAaaCipherMode
}

cfprAaaLdapProviderInstanceId OBJECT-TYPE
    SYNTAX       CfprManagedObjectId
    MAX-ACCESS   not-accessible
    STATUS       current
    DESCRIPTION
        "Instance identifier of the managed object."
    ::= { cfprAaaLdapProviderEntry 1 }

cfprAaaLdapProviderDn OBJECT-TYPE
    SYNTAX       CfprManagedObjectDn
    MAX-ACCESS   read-only
    STATUS       current
    DESCRIPTION
        "Cisco Firepower aaa:LdapProvider:dn managed object property"
    ::= { cfprAaaLdapProviderEntry 2 }

cfprAaaLdapProviderRn OBJECT-TYPE
    SYNTAX       SnmpAdminString
    MAX-ACCESS   read-only
    STATUS       current
    DESCRIPTION
        "Cisco Firepower aaa:LdapProvider:rn managed object property"
    ::= { cfprAaaLdapProviderEntry 3 }

cfprAaaLdapProviderAttribute OBJECT-TYPE
    SYNTAX       SnmpAdminString
    MAX-ACCESS   read-only
    STATUS       current
    DESCRIPTION
        "Cisco Firepower aaa:LdapProvider:attribute managed
        object property"
    ::= { cfprAaaLdapProviderEntry 4 }

cfprAaaLdapProviderBasedn OBJECT-TYPE
    SYNTAX       SnmpAdminString
    MAX-ACCESS   read-only
    STATUS       current
    DESCRIPTION
        "Cisco Firepower aaa:LdapProvider:basedn managed object property"
    ::= { cfprAaaLdapProviderEntry 5 }

cfprAaaLdapProviderDescr OBJECT-TYPE
    SYNTAX       SnmpAdminString
    MAX-ACCESS   read-only
    STATUS       current
    DESCRIPTION
        "Cisco Firepower aaa:LdapProvider:descr managed object property"
    ::= { cfprAaaLdapProviderEntry 6 }

cfprAaaLdapProviderEnableSSL OBJECT-TYPE
    SYNTAX       TruthValue
    MAX-ACCESS   read-only
    STATUS       current
    DESCRIPTION
        "Cisco Firepower aaa:LdapProvider:enableSSL managed
        object property"
    ::= { cfprAaaLdapProviderEntry 7 }

cfprAaaLdapProviderEncKey OBJECT-TYPE
    SYNTAX       SnmpAdminString
    MAX-ACCESS   read-only
    STATUS       current
    DESCRIPTION
        "Cisco Firepower aaa:LdapProvider:encKey managed object property"
    ::= { cfprAaaLdapProviderEntry 8 }

cfprAaaLdapProviderFilter OBJECT-TYPE
    SYNTAX       SnmpAdminString
    MAX-ACCESS   read-only
    STATUS       current
    DESCRIPTION
        "Cisco Firepower aaa:LdapProvider:filter managed object property"
    ::= { cfprAaaLdapProviderEntry 9 }

cfprAaaLdapProviderKey OBJECT-TYPE
    SYNTAX       SnmpAdminString
    MAX-ACCESS   read-only
    STATUS       current
    DESCRIPTION
        "Cisco Firepower aaa:LdapProvider:key managed object property"
    ::= { cfprAaaLdapProviderEntry 10 }

cfprAaaLdapProviderKeySet OBJECT-TYPE
    SYNTAX       TruthValue
    MAX-ACCESS   read-only
    STATUS       current
    DESCRIPTION
        "Cisco Firepower aaa:LdapProvider:keySet managed object property"
    ::= { cfprAaaLdapProviderEntry 11 }

cfprAaaLdapProviderName OBJECT-TYPE
    SYNTAX       SnmpAdminString
    MAX-ACCESS   read-only
    STATUS       current
    DESCRIPTION
        "Cisco Firepower aaa:LdapProvider:name managed object property"
    ::= { cfprAaaLdapProviderEntry 12 }

cfprAaaLdapProviderOrder OBJECT-TYPE
    SYNTAX       Gauge32
    MAX-ACCESS   read-only
    STATUS       current
    DESCRIPTION
        "Cisco Firepower aaa:LdapProvider:order managed object property"
    ::= { cfprAaaLdapProviderEntry 13 }

cfprAaaLdapProviderPort OBJECT-TYPE
    SYNTAX       Gauge32
    MAX-ACCESS   read-only
    STATUS       current
    DESCRIPTION
        "Cisco Firepower aaa:LdapProvider:port managed object property"
    ::= { cfprAaaLdapProviderEntry 14 }

cfprAaaLdapProviderRetries OBJECT-TYPE
    SYNTAX       Gauge32
    MAX-ACCESS   read-only
    STATUS       current
    DESCRIPTION
        "Cisco Firepower aaa:LdapProvider:retries managed object property"
    ::= { cfprAaaLdapProviderEntry 15 }

cfprAaaLdapProviderRootdn OBJECT-TYPE
    SYNTAX       SnmpAdminString
    MAX-ACCESS   read-only
    STATUS       current
    DESCRIPTION
        "Cisco Firepower aaa:LdapProvider:rootdn managed object property"
    ::= { cfprAaaLdapProviderEntry 16 }

cfprAaaLdapProviderTimeout OBJECT-TYPE
    SYNTAX       Gauge32
    MAX-ACCESS   read-only
    STATUS       current
    DESCRIPTION
        "Cisco Firepower aaa:LdapProvider:timeout managed object property"
    ::= { cfprAaaLdapProviderEntry 17 }

cfprAaaLdapProviderVendor OBJECT-TYPE
    SYNTAX       CfprAaaLdapVendor
    MAX-ACCESS   read-only
    STATUS       current
    DESCRIPTION
        "Cisco Firepower aaa:LdapProvider:vendor managed object property"
    ::= { cfprAaaLdapProviderEntry 18 }

cfprAaaLdapProviderKeyring OBJECT-TYPE
    SYNTAX       SnmpAdminString
    MAX-ACCESS   read-only
    STATUS       current
    DESCRIPTION
        "Cisco Firepower aaa:LdapProvider:keyring managed object property"
    ::= { cfprAaaLdapProviderEntry 19 }

cfprAaaLdapProviderRevokePolicy OBJECT-TYPE
    SYNTAX       CfprAaaRevokePolicy
    MAX-ACCESS   read-only
    STATUS       current
    DESCRIPTION
        "Cisco Firepower aaa:LdapProvider:revokePolicy
        managed object property"
    ::= { cfprAaaLdapProviderEntry 20 }

cfprAaaLdapProviderCipher OBJECT-TYPE
    SYNTAX       SnmpAdminString
    MAX-ACCESS   read-only
    STATUS       current
    DESCRIPTION
        "Cisco Firepower aaa:LdapProvider:cipher managed object property"
    ::= { cfprAaaLdapProviderEntry 21 }

cfprAaaLdapProviderCiphermode OBJECT-TYPE
    SYNTAX       CfprAaaCipherMode
    MAX-ACCESS   read-only
    STATUS       current
    DESCRIPTION
        "Cisco Firepower aaa:LdapProvider:ciphermode managed
        object property"
    ::= { cfprAaaLdapProviderEntry 22 }

cfprAaaLocaleTable OBJECT-TYPE
    SYNTAX           SEQUENCE OF CfprAaaLocaleEntry
    MAX-ACCESS       not-accessible
    STATUS           current
    DESCRIPTION
        "Cisco Firepower aaa:Locale managed object table"
    ::= { cfprAaaObjects 22 }

cfprAaaLocaleEntry OBJECT-TYPE
    SYNTAX           CfprAaaLocaleEntry
    MAX-ACCESS       not-accessible
    STATUS           current
    DESCRIPTION
        "Entry for the cfprAaaLocaleTable table."
    INDEX { cfprAaaLocaleInstanceId }
    ::= { cfprAaaLocaleTable 1 }

CfprAaaLocaleEntry ::= SEQUENCE {
    cfprAaaLocaleInstanceId                                          CfprManagedObjectId,
    cfprAaaLocaleDn                                                  CfprManagedObjectDn,
    cfprAaaLocaleRn                                                  SnmpAdminString,
    cfprAaaLocaleConfigState                                         CfprAaaConfigState,
    cfprAaaLocaleConfigStatusMessage                                 SnmpAdminString,
    cfprAaaLocaleDescr                                               SnmpAdminString,
    cfprAaaLocaleIntId                                               SnmpAdminString,
    cfprAaaLocaleName                                                SnmpAdminString,
    cfprAaaLocalePolicyLevel                                         Gauge32,
    cfprAaaLocalePolicyOwner                                         CfprPolicyPolicyOwner
}

cfprAaaLocaleInstanceId OBJECT-TYPE
    SYNTAX       CfprManagedObjectId
    MAX-ACCESS   not-accessible
    STATUS       current
    DESCRIPTION
        "Instance identifier of the managed object."
    ::= { cfprAaaLocaleEntry 1 }

cfprAaaLocaleDn OBJECT-TYPE
    SYNTAX       CfprManagedObjectDn
    MAX-ACCESS   read-only
    STATUS       current
    DESCRIPTION
        "Cisco Firepower aaa:Locale:dn managed object property"
    ::= { cfprAaaLocaleEntry 2 }

cfprAaaLocaleRn OBJECT-TYPE
    SYNTAX       SnmpAdminString
    MAX-ACCESS   read-only
    STATUS       current
    DESCRIPTION
        "Cisco Firepower aaa:Locale:rn managed object property"
    ::= { cfprAaaLocaleEntry 3 }

cfprAaaLocaleConfigState OBJECT-TYPE
    SYNTAX       CfprAaaConfigState
    MAX-ACCESS   read-only
    STATUS       current
    DESCRIPTION
        "Cisco Firepower aaa:Locale:configState managed object property"
    ::= { cfprAaaLocaleEntry 4 }

cfprAaaLocaleConfigStatusMessage OBJECT-TYPE
    SYNTAX       SnmpAdminString
    MAX-ACCESS   read-only
    STATUS       current
    DESCRIPTION
        "Cisco Firepower aaa:Locale:configStatusMessage
        managed object property"
    ::= { cfprAaaLocaleEntry 5 }

cfprAaaLocaleDescr OBJECT-TYPE
    SYNTAX       SnmpAdminString
    MAX-ACCESS   read-only
    STATUS       current
    DESCRIPTION
        "Cisco Firepower aaa:Locale:descr managed object property"
    ::= { cfprAaaLocaleEntry 6 }

cfprAaaLocaleIntId OBJECT-TYPE
    SYNTAX       SnmpAdminString
    MAX-ACCESS   read-only
    STATUS       current
    DESCRIPTION
        "Cisco Firepower aaa:Locale:intId managed object property"
    ::= { cfprAaaLocaleEntry 7 }

cfprAaaLocaleName OBJECT-TYPE
    SYNTAX       SnmpAdminString
    MAX-ACCESS   read-only
    STATUS       current
    DESCRIPTION
        "Cisco Firepower aaa:Locale:name managed object property"
    ::= { cfprAaaLocaleEntry 8 }

cfprAaaLocalePolicyLevel OBJECT-TYPE
    SYNTAX       Gauge32
    MAX-ACCESS   read-only
    STATUS       current
    DESCRIPTION
        "Cisco Firepower aaa:Locale:policyLevel managed object property"
    ::= { cfprAaaLocaleEntry 9 }

cfprAaaLocalePolicyOwner OBJECT-TYPE
    SYNTAX       CfprPolicyPolicyOwner
    MAX-ACCESS   read-only
    STATUS       current
    DESCRIPTION
        "Cisco Firepower aaa:Locale:policyOwner managed object property"
    ::= { cfprAaaLocaleEntry 10 }

cfprAaaLogTable OBJECT-TYPE
    SYNTAX           SEQUENCE OF CfprAaaLogEntry
    MAX-ACCESS       not-accessible
    STATUS           current
    DESCRIPTION
        "Cisco Firepower aaa:Log managed object table"
    ::= { cfprAaaObjects 23 }

cfprAaaLogEntry OBJECT-TYPE
    SYNTAX           CfprAaaLogEntry
    MAX-ACCESS       not-accessible
    STATUS           current
    DESCRIPTION
        "Entry for the cfprAaaLogTable table."
    INDEX { cfprAaaLogInstanceId }
    ::= { cfprAaaLogTable 1 }

CfprAaaLogEntry ::= SEQUENCE {
    cfprAaaLogInstanceId                                             CfprManagedObjectId,
    cfprAaaLogDn                                                     CfprManagedObjectDn,
    cfprAaaLogRn                                                     SnmpAdminString,
    cfprAaaLogMaxSize                                                Gauge32,
    cfprAaaLogPurgeWindow                                            Gauge32,
    cfprAaaLogSize                                                   Gauge32
}

cfprAaaLogInstanceId OBJECT-TYPE
    SYNTAX       CfprManagedObjectId
    MAX-ACCESS   not-accessible
    STATUS       current
    DESCRIPTION
        "Instance identifier of the managed object."
    ::= { cfprAaaLogEntry 1 }

cfprAaaLogDn OBJECT-TYPE
    SYNTAX       CfprManagedObjectDn
    MAX-ACCESS   read-only
    STATUS       current
    DESCRIPTION
        "Cisco Firepower aaa:Log:dn managed object property"
    ::= { cfprAaaLogEntry 2 }

cfprAaaLogRn OBJECT-TYPE
    SYNTAX       SnmpAdminString
    MAX-ACCESS   read-only
    STATUS       current
    DESCRIPTION
        "Cisco Firepower aaa:Log:rn managed object property"
    ::= { cfprAaaLogEntry 3 }

cfprAaaLogMaxSize OBJECT-TYPE
    SYNTAX       Gauge32
    MAX-ACCESS   read-only
    STATUS       current
    DESCRIPTION
        "Cisco Firepower aaa:Log:maxSize managed object property"
    ::= { cfprAaaLogEntry 4 }

cfprAaaLogPurgeWindow OBJECT-TYPE
    SYNTAX       Gauge32
    MAX-ACCESS   read-only
    STATUS       current
    DESCRIPTION
        "Cisco Firepower aaa:Log:purgeWindow managed object property"
    ::= { cfprAaaLogEntry 5 }

cfprAaaLogSize OBJECT-TYPE
    SYNTAX       Gauge32
    MAX-ACCESS   read-only
    STATUS       current
    DESCRIPTION
        "Cisco Firepower aaa:Log:size managed object property"
    ::= { cfprAaaLogEntry 6 }

cfprAaaLoginRecTable OBJECT-TYPE
    SYNTAX           SEQUENCE OF CfprAaaLoginRecEntry
    MAX-ACCESS       not-accessible
    STATUS           current
    DESCRIPTION
        "Cisco Firepower aaa:LoginRec managed object table"
    ::= { cfprAaaObjects 58 }

cfprAaaLoginRecEntry OBJECT-TYPE
    SYNTAX           CfprAaaLoginRecEntry
    MAX-ACCESS       not-accessible
    STATUS           current
    DESCRIPTION
        "Entry for the cfprAaaLoginRecTable table."
    INDEX { cfprAaaLoginRecInstanceId }
    ::= { cfprAaaLoginRecTable 1 }

CfprAaaLoginRecEntry ::= SEQUENCE {
    cfprAaaLoginRecInstanceId                                        CfprManagedObjectId,
    cfprAaaLoginRecDn                                                CfprManagedObjectDn,
    cfprAaaLoginRecRn                                                SnmpAdminString,
    cfprAaaLoginRecHost                                              SnmpAdminString,
    cfprAaaLoginRecName                                              SnmpAdminString,
    cfprAaaLoginRecTime                                              SnmpAdminString,
    cfprAaaLoginRecUser                                              SnmpAdminString
}

cfprAaaLoginRecInstanceId OBJECT-TYPE
    SYNTAX       CfprManagedObjectId
    MAX-ACCESS   not-accessible
    STATUS       current
    DESCRIPTION
        "Instance identifier of the managed object."
    ::= { cfprAaaLoginRecEntry 1 }

cfprAaaLoginRecDn OBJECT-TYPE
    SYNTAX       CfprManagedObjectDn
    MAX-ACCESS   read-only
    STATUS       current
    DESCRIPTION
        "Cisco Firepower aaa:LoginRec:dn managed object property"
    ::= { cfprAaaLoginRecEntry 2 }

cfprAaaLoginRecRn OBJECT-TYPE
    SYNTAX       SnmpAdminString
    MAX-ACCESS   read-only
    STATUS       current
    DESCRIPTION
        "Cisco Firepower aaa:LoginRec:rn managed object property"
    ::= { cfprAaaLoginRecEntry 3 }

cfprAaaLoginRecHost OBJECT-TYPE
    SYNTAX       SnmpAdminString
    MAX-ACCESS   read-only
    STATUS       current
    DESCRIPTION
        "Cisco Firepower aaa:LoginRec:host managed object property"
    ::= { cfprAaaLoginRecEntry 4 }

cfprAaaLoginRecName OBJECT-TYPE
    SYNTAX       SnmpAdminString
    MAX-ACCESS   read-only
    STATUS       current
    DESCRIPTION
        "Cisco Firepower aaa:LoginRec:name managed object property"
    ::= { cfprAaaLoginRecEntry 5 }

cfprAaaLoginRecTime OBJECT-TYPE
    SYNTAX       SnmpAdminString
    MAX-ACCESS   read-only
    STATUS       current
    DESCRIPTION
        "Cisco Firepower aaa:LoginRec:time managed object property"
    ::= { cfprAaaLoginRecEntry 6 }

cfprAaaLoginRecUser OBJECT-TYPE
    SYNTAX       SnmpAdminString
    MAX-ACCESS   read-only
    STATUS       current
    DESCRIPTION
        "Cisco Firepower aaa:LoginRec:user managed object property"
    ::= { cfprAaaLoginRecEntry 7 }

cfprAaaModLRTable OBJECT-TYPE
    SYNTAX           SEQUENCE OF CfprAaaModLREntry
    MAX-ACCESS       not-accessible
    STATUS           current
    DESCRIPTION
        "Cisco Firepower aaa:ModLR managed object table"
    ::= { cfprAaaObjects 24 }

cfprAaaModLREntry OBJECT-TYPE
    SYNTAX           CfprAaaModLREntry
    MAX-ACCESS       not-accessible
    STATUS           current
    DESCRIPTION
        "Entry for the cfprAaaModLRTable table."
    INDEX { cfprAaaModLRInstanceId }
    ::= { cfprAaaModLRTable 1 }

CfprAaaModLREntry ::= SEQUENCE {
    cfprAaaModLRInstanceId                                           CfprManagedObjectId,
    cfprAaaModLRDn                                                   CfprManagedObjectDn,
    cfprAaaModLRRn                                                   SnmpAdminString,
    cfprAaaModLRAffected                                             SnmpAdminString,
    cfprAaaModLRCause                                                CfprConditionCause,
    cfprAaaModLRChangeSet                                            SnmpAdminString,
    cfprAaaModLRCode                                                 CfprConditionCode,
    cfprAaaModLRCreated                                              DateAndTime,
    cfprAaaModLRDescr                                                SnmpAdminString,
    cfprAaaModLRId                                                   Gauge32,
    cfprAaaModLRInd                                                  CfprConditionActionIndicator,
    cfprAaaModLRSessionId                                            SnmpAdminString,
    cfprAaaModLRSeverity                                             CfprConditionSeverity,
    cfprAaaModLRTrig                                                 Gauge32,
    cfprAaaModLRTxId                                                 Unsigned64,
    cfprAaaModLRUser                                                 SnmpAdminString
}

cfprAaaModLRInstanceId OBJECT-TYPE
    SYNTAX       CfprManagedObjectId
    MAX-ACCESS   not-accessible
    STATUS       current
    DESCRIPTION
        "Instance identifier of the managed object."
    ::= { cfprAaaModLREntry 1 }

cfprAaaModLRDn OBJECT-TYPE
    SYNTAX       CfprManagedObjectDn
    MAX-ACCESS   read-only
    STATUS       current
    DESCRIPTION
        "Cisco Firepower aaa:ModLR:dn managed object property"
    ::= { cfprAaaModLREntry 2 }

cfprAaaModLRRn OBJECT-TYPE
    SYNTAX       SnmpAdminString
    MAX-ACCESS   read-only
    STATUS       current
    DESCRIPTION
        "Cisco Firepower aaa:ModLR:rn managed object property"
    ::= { cfprAaaModLREntry 3 }

cfprAaaModLRAffected OBJECT-TYPE
    SYNTAX       SnmpAdminString
    MAX-ACCESS   read-only
    STATUS       current
    DESCRIPTION
        "Cisco Firepower aaa:ModLR:affected managed object property"
    ::= { cfprAaaModLREntry 4 }

cfprAaaModLRCause OBJECT-TYPE
    SYNTAX       CfprConditionCause
    MAX-ACCESS   read-only
    STATUS       current
    DESCRIPTION
        "Cisco Firepower aaa:ModLR:cause managed object property"
    ::= { cfprAaaModLREntry 5 }

cfprAaaModLRChangeSet OBJECT-TYPE
    SYNTAX       SnmpAdminString
    MAX-ACCESS   read-only
    STATUS       current
    DESCRIPTION
        "Cisco Firepower aaa:ModLR:changeSet managed object property"
    ::= { cfprAaaModLREntry 6 }

cfprAaaModLRCode OBJECT-TYPE
    SYNTAX       CfprConditionCode
    MAX-ACCESS   read-only
    STATUS       current
    DESCRIPTION
        "Cisco Firepower aaa:ModLR:code managed object property"
    ::= { cfprAaaModLREntry 7 }

cfprAaaModLRCreated OBJECT-TYPE
    SYNTAX       DateAndTime
    MAX-ACCESS   read-only
    STATUS       current
    DESCRIPTION
        "Cisco Firepower aaa:ModLR:created managed object property"
    ::= { cfprAaaModLREntry 8 }

cfprAaaModLRDescr OBJECT-TYPE
    SYNTAX       SnmpAdminString
    MAX-ACCESS   read-only
    STATUS       current
    DESCRIPTION
        "Cisco Firepower aaa:ModLR:descr managed object property"
    ::= { cfprAaaModLREntry 9 }

cfprAaaModLRId OBJECT-TYPE
    SYNTAX       Gauge32
    MAX-ACCESS   read-only
    STATUS       current
    DESCRIPTION
        "Cisco Firepower aaa:ModLR:id managed object property"
    ::= { cfprAaaModLREntry 10 }

cfprAaaModLRInd OBJECT-TYPE
    SYNTAX       CfprConditionActionIndicator
    MAX-ACCESS   read-only
    STATUS       current
    DESCRIPTION
        "Cisco Firepower aaa:ModLR:ind managed object property"
    ::= { cfprAaaModLREntry 11 }

cfprAaaModLRSessionId OBJECT-TYPE
    SYNTAX       SnmpAdminString
    MAX-ACCESS   read-only
    STATUS       current
    DESCRIPTION
        "Cisco Firepower aaa:ModLR:sessionId managed object property"
    ::= { cfprAaaModLREntry 12 }

cfprAaaModLRSeverity OBJECT-TYPE
    SYNTAX       CfprConditionSeverity
    MAX-ACCESS   read-only
    STATUS       current
    DESCRIPTION
        "Cisco Firepower aaa:ModLR:severity managed object property"
    ::= { cfprAaaModLREntry 13 }

cfprAaaModLRTrig OBJECT-TYPE
    SYNTAX       Gauge32
    MAX-ACCESS   read-only
    STATUS       current
    DESCRIPTION
        "Cisco Firepower aaa:ModLR:trig managed object property"
    ::= { cfprAaaModLREntry 14 }

cfprAaaModLRTxId OBJECT-TYPE
    SYNTAX       Unsigned64
    MAX-ACCESS   read-only
    STATUS       current
    DESCRIPTION
        "Cisco Firepower aaa:ModLR:txId managed object property"
    ::= { cfprAaaModLREntry 15 }

cfprAaaModLRUser OBJECT-TYPE
    SYNTAX       SnmpAdminString
    MAX-ACCESS   read-only
    STATUS       current
    DESCRIPTION
        "Cisco Firepower aaa:ModLR:user managed object property"
    ::= { cfprAaaModLREntry 16 }

cfprAaaOrgTable OBJECT-TYPE
    SYNTAX           SEQUENCE OF CfprAaaOrgEntry
    MAX-ACCESS       not-accessible
    STATUS           current
    DESCRIPTION
        "Cisco Firepower aaa:Org managed object table"
    ::= { cfprAaaObjects 25 }

cfprAaaOrgEntry OBJECT-TYPE
    SYNTAX           CfprAaaOrgEntry
    MAX-ACCESS       not-accessible
    STATUS           current
    DESCRIPTION
        "Entry for the cfprAaaOrgTable table."
    INDEX { cfprAaaOrgInstanceId }
    ::= { cfprAaaOrgTable 1 }

CfprAaaOrgEntry ::= SEQUENCE {
    cfprAaaOrgInstanceId                                             CfprManagedObjectId,
    cfprAaaOrgDn                                                     CfprManagedObjectDn,
    cfprAaaOrgRn                                                     SnmpAdminString,
    cfprAaaOrgConfigState                                            CfprAaaConfigState,
    cfprAaaOrgConfigStatusMessage                                    SnmpAdminString,
    cfprAaaOrgDescr                                                  SnmpAdminString,
    cfprAaaOrgName                                                   SnmpAdminString,
    cfprAaaOrgOrgDn                                                  SnmpAdminString
}

cfprAaaOrgInstanceId OBJECT-TYPE
    SYNTAX       CfprManagedObjectId
    MAX-ACCESS   not-accessible
    STATUS       current
    DESCRIPTION
        "Instance identifier of the managed object."
    ::= { cfprAaaOrgEntry 1 }

cfprAaaOrgDn OBJECT-TYPE
    SYNTAX       CfprManagedObjectDn
    MAX-ACCESS   read-only
    STATUS       current
    DESCRIPTION
        "Cisco Firepower aaa:Org:dn managed object property"
    ::= { cfprAaaOrgEntry 2 }

cfprAaaOrgRn OBJECT-TYPE
    SYNTAX       SnmpAdminString
    MAX-ACCESS   read-only
    STATUS       current
    DESCRIPTION
        "Cisco Firepower aaa:Org:rn managed object property"
    ::= { cfprAaaOrgEntry 3 }

cfprAaaOrgConfigState OBJECT-TYPE
    SYNTAX       CfprAaaConfigState
    MAX-ACCESS   read-only
    STATUS       current
    DESCRIPTION
        "Cisco Firepower aaa:Org:configState managed object property"
    ::= { cfprAaaOrgEntry 4 }

cfprAaaOrgConfigStatusMessage OBJECT-TYPE
    SYNTAX       SnmpAdminString
    MAX-ACCESS   read-only
    STATUS       current
    DESCRIPTION
        "Cisco Firepower aaa:Org:configStatusMessage managed
        object property"
    ::= { cfprAaaOrgEntry 5 }

cfprAaaOrgDescr OBJECT-TYPE
    SYNTAX       SnmpAdminString
    MAX-ACCESS   read-only
    STATUS       current
    DESCRIPTION
        "Cisco Firepower aaa:Org:descr managed object property"
    ::= { cfprAaaOrgEntry 6 }

cfprAaaOrgName OBJECT-TYPE
    SYNTAX       SnmpAdminString
    MAX-ACCESS   read-only
    STATUS       current
    DESCRIPTION
        "Cisco Firepower aaa:Org:name managed object property"
    ::= { cfprAaaOrgEntry 7 }

cfprAaaOrgOrgDn OBJECT-TYPE
    SYNTAX       SnmpAdminString
    MAX-ACCESS   read-only
    STATUS       current
    DESCRIPTION
        "Cisco Firepower aaa:Org:orgDn managed object property"
    ::= { cfprAaaOrgEntry 8 }

cfprAaaPreLoginBannerTable OBJECT-TYPE
    SYNTAX           SEQUENCE OF CfprAaaPreLoginBannerEntry
    MAX-ACCESS       not-accessible
    STATUS           current
    DESCRIPTION
        "Cisco Firepower aaa:PreLoginBanner managed object table"
    ::= { cfprAaaObjects 26 }

cfprAaaPreLoginBannerEntry OBJECT-TYPE
    SYNTAX           CfprAaaPreLoginBannerEntry
    MAX-ACCESS       not-accessible
    STATUS           current
    DESCRIPTION
        "Entry for the cfprAaaPreLoginBannerTable table."
    INDEX { cfprAaaPreLoginBannerInstanceId }
    ::= { cfprAaaPreLoginBannerTable 1 }

CfprAaaPreLoginBannerEntry ::= SEQUENCE {
    cfprAaaPreLoginBannerInstanceId                                  CfprManagedObjectId,
    cfprAaaPreLoginBannerDn                                          CfprManagedObjectDn,
    cfprAaaPreLoginBannerRn                                          SnmpAdminString,
    cfprAaaPreLoginBannerDescr                                       SnmpAdminString,
    cfprAaaPreLoginBannerIntId                                       SnmpAdminString,
    cfprAaaPreLoginBannerMessage                                     SnmpAdminString,
    cfprAaaPreLoginBannerName                                        SnmpAdminString,
    cfprAaaPreLoginBannerPolicyLevel                                 Gauge32,
    cfprAaaPreLoginBannerPolicyOwner                                 CfprPolicyPolicyOwner
}

cfprAaaPreLoginBannerInstanceId OBJECT-TYPE
    SYNTAX       CfprManagedObjectId
    MAX-ACCESS   not-accessible
    STATUS       current
    DESCRIPTION
        "Instance identifier of the managed object."
    ::= { cfprAaaPreLoginBannerEntry 1 }

cfprAaaPreLoginBannerDn OBJECT-TYPE
    SYNTAX       CfprManagedObjectDn
    MAX-ACCESS   read-only
    STATUS       current
    DESCRIPTION
        "Cisco Firepower aaa:PreLoginBanner:dn managed object property"
    ::= { cfprAaaPreLoginBannerEntry 2 }

cfprAaaPreLoginBannerRn OBJECT-TYPE
    SYNTAX       SnmpAdminString
    MAX-ACCESS   read-only
    STATUS       current
    DESCRIPTION
        "Cisco Firepower aaa:PreLoginBanner:rn managed object property"
    ::= { cfprAaaPreLoginBannerEntry 3 }

cfprAaaPreLoginBannerDescr OBJECT-TYPE
    SYNTAX       SnmpAdminString
    MAX-ACCESS   read-only
    STATUS       current
    DESCRIPTION
        "Cisco Firepower aaa:PreLoginBanner:descr managed object property"
    ::= { cfprAaaPreLoginBannerEntry 4 }

cfprAaaPreLoginBannerIntId OBJECT-TYPE
    SYNTAX       SnmpAdminString
    MAX-ACCESS   read-only
    STATUS       current
    DESCRIPTION
        "Cisco Firepower aaa:PreLoginBanner:intId managed object property"
    ::= { cfprAaaPreLoginBannerEntry 5 }

cfprAaaPreLoginBannerMessage OBJECT-TYPE
    SYNTAX       SnmpAdminString
    MAX-ACCESS   read-only
    STATUS       current
    DESCRIPTION
        "Cisco Firepower aaa:PreLoginBanner:message managed
        object property"
    ::= { cfprAaaPreLoginBannerEntry 6 }

cfprAaaPreLoginBannerName OBJECT-TYPE
    SYNTAX       SnmpAdminString
    MAX-ACCESS   read-only
    STATUS       current
    DESCRIPTION
        "Cisco Firepower aaa:PreLoginBanner:name managed object property"
    ::= { cfprAaaPreLoginBannerEntry 7 }

cfprAaaPreLoginBannerPolicyLevel OBJECT-TYPE
    SYNTAX       Gauge32
    MAX-ACCESS   read-only
    STATUS       current
    DESCRIPTION
        "Cisco Firepower aaa:PreLoginBanner:policyLevel
        managed object property"
    ::= { cfprAaaPreLoginBannerEntry 8 }

cfprAaaPreLoginBannerPolicyOwner OBJECT-TYPE
    SYNTAX       CfprPolicyPolicyOwner
    MAX-ACCESS   read-only
    STATUS       current
    DESCRIPTION
        "Cisco Firepower aaa:PreLoginBanner:policyOwner
        managed object property"
    ::= { cfprAaaPreLoginBannerEntry 9 }

cfprAaaProviderGroupTable OBJECT-TYPE
    SYNTAX           SEQUENCE OF CfprAaaProviderGroupEntry
    MAX-ACCESS       not-accessible
    STATUS           current
    DESCRIPTION
        "Cisco Firepower aaa:ProviderGroup managed object table"
    ::= { cfprAaaObjects 27 }

cfprAaaProviderGroupEntry OBJECT-TYPE
    SYNTAX           CfprAaaProviderGroupEntry
    MAX-ACCESS       not-accessible
    STATUS           current
    DESCRIPTION
        "Entry for the cfprAaaProviderGroupTable table."
    INDEX { cfprAaaProviderGroupInstanceId }
    ::= { cfprAaaProviderGroupTable 1 }

CfprAaaProviderGroupEntry ::= SEQUENCE {
    cfprAaaProviderGroupInstanceId                                   CfprManagedObjectId,
    cfprAaaProviderGroupDn                                           CfprManagedObjectDn,
    cfprAaaProviderGroupRn                                           SnmpAdminString,
    cfprAaaProviderGroupConfigState                                  CfprAaaConfigState,
    cfprAaaProviderGroupDescr                                        SnmpAdminString,
    cfprAaaProviderGroupName                                         SnmpAdminString,
    cfprAaaProviderGroupSize                                         Gauge32
}

cfprAaaProviderGroupInstanceId OBJECT-TYPE
    SYNTAX       CfprManagedObjectId
    MAX-ACCESS   not-accessible
    STATUS       current
    DESCRIPTION
        "Instance identifier of the managed object."
    ::= { cfprAaaProviderGroupEntry 1 }

cfprAaaProviderGroupDn OBJECT-TYPE
    SYNTAX       CfprManagedObjectDn
    MAX-ACCESS   read-only
    STATUS       current
    DESCRIPTION
        "Cisco Firepower aaa:ProviderGroup:dn managed object property"
    ::= { cfprAaaProviderGroupEntry 2 }

cfprAaaProviderGroupRn OBJECT-TYPE
    SYNTAX       SnmpAdminString
    MAX-ACCESS   read-only
    STATUS       current
    DESCRIPTION
        "Cisco Firepower aaa:ProviderGroup:rn managed object property"
    ::= { cfprAaaProviderGroupEntry 3 }

cfprAaaProviderGroupConfigState OBJECT-TYPE
    SYNTAX       CfprAaaConfigState
    MAX-ACCESS   read-only
    STATUS       current
    DESCRIPTION
        "Cisco Firepower aaa:ProviderGroup:configState
        managed object property"
    ::= { cfprAaaProviderGroupEntry 4 }

cfprAaaProviderGroupDescr OBJECT-TYPE
    SYNTAX       SnmpAdminString
    MAX-ACCESS   read-only
    STATUS       current
    DESCRIPTION
        "Cisco Firepower aaa:ProviderGroup:descr managed object property"
    ::= { cfprAaaProviderGroupEntry 5 }

cfprAaaProviderGroupName OBJECT-TYPE
    SYNTAX       SnmpAdminString
    MAX-ACCESS   read-only
    STATUS       current
    DESCRIPTION
        "Cisco Firepower aaa:ProviderGroup:name managed object property"
    ::= { cfprAaaProviderGroupEntry 6 }

cfprAaaProviderGroupSize OBJECT-TYPE
    SYNTAX       Gauge32
    MAX-ACCESS   read-only
    STATUS       current
    DESCRIPTION
        "Cisco Firepower aaa:ProviderGroup:size managed object property"
    ::= { cfprAaaProviderGroupEntry 7 }

cfprAaaProviderRefTable OBJECT-TYPE
    SYNTAX           SEQUENCE OF CfprAaaProviderRefEntry
    MAX-ACCESS       not-accessible
    STATUS           current
    DESCRIPTION
        "Cisco Firepower aaa:ProviderRef managed object table"
    ::= { cfprAaaObjects 28 }

cfprAaaProviderRefEntry OBJECT-TYPE
    SYNTAX           CfprAaaProviderRefEntry
    MAX-ACCESS       not-accessible
    STATUS           current
    DESCRIPTION
        "Entry for the cfprAaaProviderRefTable table."
    INDEX { cfprAaaProviderRefInstanceId }
    ::= { cfprAaaProviderRefTable 1 }

CfprAaaProviderRefEntry ::= SEQUENCE {
    cfprAaaProviderRefInstanceId                                     CfprManagedObjectId,
    cfprAaaProviderRefDn                                             CfprManagedObjectDn,
    cfprAaaProviderRefRn                                             SnmpAdminString,
    cfprAaaProviderRefDescr                                          SnmpAdminString,
    cfprAaaProviderRefName                                           SnmpAdminString,
    cfprAaaProviderRefOrder                                          Gauge32
}

cfprAaaProviderRefInstanceId OBJECT-TYPE
    SYNTAX       CfprManagedObjectId
    MAX-ACCESS   not-accessible
    STATUS       current
    DESCRIPTION
        "Instance identifier of the managed object."
    ::= { cfprAaaProviderRefEntry 1 }

cfprAaaProviderRefDn OBJECT-TYPE
    SYNTAX       CfprManagedObjectDn
    MAX-ACCESS   read-only
    STATUS       current
    DESCRIPTION
        "Cisco Firepower aaa:ProviderRef:dn managed object property"
    ::= { cfprAaaProviderRefEntry 2 }

cfprAaaProviderRefRn OBJECT-TYPE
    SYNTAX       SnmpAdminString
    MAX-ACCESS   read-only
    STATUS       current
    DESCRIPTION
        "Cisco Firepower aaa:ProviderRef:rn managed object property"
    ::= { cfprAaaProviderRefEntry 3 }

cfprAaaProviderRefDescr OBJECT-TYPE
    SYNTAX       SnmpAdminString
    MAX-ACCESS   read-only
    STATUS       current
    DESCRIPTION
        "Cisco Firepower aaa:ProviderRef:descr managed object property"
    ::= { cfprAaaProviderRefEntry 4 }

cfprAaaProviderRefName OBJECT-TYPE
    SYNTAX       SnmpAdminString
    MAX-ACCESS   read-only
    STATUS       current
    DESCRIPTION
        "Cisco Firepower aaa:ProviderRef:name managed object property"
    ::= { cfprAaaProviderRefEntry 5 }

cfprAaaProviderRefOrder OBJECT-TYPE
    SYNTAX       Gauge32
    MAX-ACCESS   read-only
    STATUS       current
    DESCRIPTION
        "Cisco Firepower aaa:ProviderRef:order managed object property"
    ::= { cfprAaaProviderRefEntry 6 }

cfprAaaPwdProfileTable OBJECT-TYPE
    SYNTAX           SEQUENCE OF CfprAaaPwdProfileEntry
    MAX-ACCESS       not-accessible
    STATUS           current
    DESCRIPTION
        "Cisco Firepower aaa:PwdProfile managed object table"
    ::= { cfprAaaObjects 29 }

cfprAaaPwdProfileEntry OBJECT-TYPE
    SYNTAX           CfprAaaPwdProfileEntry
    MAX-ACCESS       not-accessible
    STATUS           current
    DESCRIPTION
        "Entry for the cfprAaaPwdProfileTable table."
    INDEX { cfprAaaPwdProfileInstanceId }
    ::= { cfprAaaPwdProfileTable 1 }

CfprAaaPwdProfileEntry ::= SEQUENCE {
    cfprAaaPwdProfileInstanceId                                      CfprManagedObjectId,
    cfprAaaPwdProfileDn                                              CfprManagedObjectDn,
    cfprAaaPwdProfileRn                                              SnmpAdminString,
    cfprAaaPwdProfileChangeCount                                     Gauge32,
    cfprAaaPwdProfileChangeDuringInterval                            CfprAaaPwdPolicy,
    cfprAaaPwdProfileChangeInterval                                  Gauge32,
    cfprAaaPwdProfileDescr                                           SnmpAdminString,
    cfprAaaPwdProfileExpirationWarnTime                              Gauge32,
    cfprAaaPwdProfileHistoryCount                                    Gauge32,
    cfprAaaPwdProfileIntId                                           SnmpAdminString,
    cfprAaaPwdProfileName                                            SnmpAdminString,
    cfprAaaPwdProfileNoChangeInterval                                Gauge32,
    cfprAaaPwdProfilePolicyLevel                                     Gauge32,
    cfprAaaPwdProfilePolicyOwner                                     CfprPolicyPolicyOwner,
    cfprAaaPwdProfileExpirationDays                                  Gauge32,
    cfprAaaPwdProfileExpirationGracePeriod                           Gauge32,
    cfprAaaPwdProfileReuseTime                                       Gauge32
}

cfprAaaPwdProfileInstanceId OBJECT-TYPE
    SYNTAX       CfprManagedObjectId
    MAX-ACCESS   not-accessible
    STATUS       current
    DESCRIPTION
        "Instance identifier of the managed object."
    ::= { cfprAaaPwdProfileEntry 1 }

cfprAaaPwdProfileDn OBJECT-TYPE
    SYNTAX       CfprManagedObjectDn
    MAX-ACCESS   read-only
    STATUS       current
    DESCRIPTION
        "Cisco Firepower aaa:PwdProfile:dn managed object property"
    ::= { cfprAaaPwdProfileEntry 2 }

cfprAaaPwdProfileRn OBJECT-TYPE
    SYNTAX       SnmpAdminString
    MAX-ACCESS   read-only
    STATUS       current
    DESCRIPTION
        "Cisco Firepower aaa:PwdProfile:rn managed object property"
    ::= { cfprAaaPwdProfileEntry 3 }

cfprAaaPwdProfileChangeCount OBJECT-TYPE
    SYNTAX       Gauge32
    MAX-ACCESS   read-only
    STATUS       current
    DESCRIPTION
        "Cisco Firepower aaa:PwdProfile:changeCount managed
        object property"
    ::= { cfprAaaPwdProfileEntry 4 }

cfprAaaPwdProfileChangeDuringInterval OBJECT-TYPE
    SYNTAX       CfprAaaPwdPolicy
    MAX-ACCESS   read-only
    STATUS       current
    DESCRIPTION
        "Cisco Firepower aaa:PwdProfile:changeDuringInterval
        managed object property"
    ::= { cfprAaaPwdProfileEntry 5 }

cfprAaaPwdProfileChangeInterval OBJECT-TYPE
    SYNTAX       Gauge32
    MAX-ACCESS   read-only
    STATUS       current
    DESCRIPTION
        "Cisco Firepower aaa:PwdProfile:changeInterval
        managed object property"
    ::= { cfprAaaPwdProfileEntry 6 }

cfprAaaPwdProfileDescr OBJECT-TYPE
    SYNTAX       SnmpAdminString
    MAX-ACCESS   read-only
    STATUS       current
    DESCRIPTION
        "Cisco Firepower aaa:PwdProfile:descr managed object property"
    ::= { cfprAaaPwdProfileEntry 7 }

cfprAaaPwdProfileExpirationWarnTime OBJECT-TYPE
    SYNTAX       Gauge32
    MAX-ACCESS   read-only
    STATUS       current
    DESCRIPTION
        "Cisco Firepower aaa:PwdProfile:expirationWarnTime
        managed object property"
    ::= { cfprAaaPwdProfileEntry 8 }

cfprAaaPwdProfileHistoryCount OBJECT-TYPE
    SYNTAX       Gauge32
    MAX-ACCESS   read-only
    STATUS       current
    DESCRIPTION
        "Cisco Firepower aaa:PwdProfile:historyCount managed
        object property"
    ::= { cfprAaaPwdProfileEntry 9 }

cfprAaaPwdProfileIntId OBJECT-TYPE
    SYNTAX       SnmpAdminString
    MAX-ACCESS   read-only
    STATUS       current
    DESCRIPTION
        "Cisco Firepower aaa:PwdProfile:intId managed object property"
    ::= { cfprAaaPwdProfileEntry 10 }

cfprAaaPwdProfileName OBJECT-TYPE
    SYNTAX       SnmpAdminString
    MAX-ACCESS   read-only
    STATUS       current
    DESCRIPTION
        "Cisco Firepower aaa:PwdProfile:name managed object property"
    ::= { cfprAaaPwdProfileEntry 11 }

cfprAaaPwdProfileNoChangeInterval OBJECT-TYPE
    SYNTAX       Gauge32
    MAX-ACCESS   read-only
    STATUS       current
    DESCRIPTION
        "Cisco Firepower aaa:PwdProfile:noChangeInterval
        managed object property"
    ::= { cfprAaaPwdProfileEntry 12 }

cfprAaaPwdProfilePolicyLevel OBJECT-TYPE
    SYNTAX       Gauge32
    MAX-ACCESS   read-only
    STATUS       current
    DESCRIPTION
        "Cisco Firepower aaa:PwdProfile:policyLevel managed
        object property"
    ::= { cfprAaaPwdProfileEntry 13 }

cfprAaaPwdProfilePolicyOwner OBJECT-TYPE
    SYNTAX       CfprPolicyPolicyOwner
    MAX-ACCESS   read-only
    STATUS       current
    DESCRIPTION
        "Cisco Firepower aaa:PwdProfile:policyOwner managed
        object property"
    ::= { cfprAaaPwdProfileEntry 14 }

cfprAaaPwdProfileExpirationDays OBJECT-TYPE
    SYNTAX       Gauge32
    MAX-ACCESS   read-only
    STATUS       current
    DESCRIPTION
        "Cisco Firepower aaa:PwdProfile:expirationDays
        managed object property"
    ::= { cfprAaaPwdProfileEntry 15 }

cfprAaaPwdProfileExpirationGracePeriod OBJECT-TYPE
    SYNTAX       Gauge32
    MAX-ACCESS   read-only
    STATUS       current
    DESCRIPTION
        "Cisco Firepower aaa:PwdProfile:expirationGracePeriod
        managed object property"
    ::= { cfprAaaPwdProfileEntry 16 }

cfprAaaPwdProfileReuseTime OBJECT-TYPE
    SYNTAX       Gauge32
    MAX-ACCESS   read-only
    STATUS       current
    DESCRIPTION
        "Cisco Firepower aaa:PwdProfile:reuseTime managed object property"
    ::= { cfprAaaPwdProfileEntry 17 }

cfprAaaRadiusEpTable OBJECT-TYPE
    SYNTAX           SEQUENCE OF CfprAaaRadiusEpEntry
    MAX-ACCESS       not-accessible
    STATUS           current
    DESCRIPTION
        "Cisco Firepower aaa:RadiusEp managed object table"
    ::= { cfprAaaObjects 30 }

cfprAaaRadiusEpEntry OBJECT-TYPE
    SYNTAX           CfprAaaRadiusEpEntry
    MAX-ACCESS       not-accessible
    STATUS           current
    DESCRIPTION
        "Entry for the cfprAaaRadiusEpTable table."
    INDEX { cfprAaaRadiusEpInstanceId }
    ::= { cfprAaaRadiusEpTable 1 }

CfprAaaRadiusEpEntry ::= SEQUENCE {
    cfprAaaRadiusEpInstanceId                                        CfprManagedObjectId,
    cfprAaaRadiusEpDn                                                CfprManagedObjectDn,
    cfprAaaRadiusEpRn                                                SnmpAdminString,
    cfprAaaRadiusEpDescr                                             SnmpAdminString,
    cfprAaaRadiusEpFsmDescr                                          SnmpAdminString,
    cfprAaaRadiusEpFsmPrev                                           SnmpAdminString,
    cfprAaaRadiusEpFsmProgr                                          Gauge32,
    cfprAaaRadiusEpFsmRmtInvErrCode                                  Gauge32,
    cfprAaaRadiusEpFsmRmtInvErrDescr                                 SnmpAdminString,
    cfprAaaRadiusEpFsmRmtInvRslt                                     CfprConditionRemoteInvRslt,
    cfprAaaRadiusEpFsmStageDescr                                     SnmpAdminString,
    cfprAaaRadiusEpFsmStamp                                          DateAndTime,
    cfprAaaRadiusEpFsmStatus                                         SnmpAdminString,
    cfprAaaRadiusEpFsmTry                                            Gauge32,
    cfprAaaRadiusEpIntId                                             SnmpAdminString,
    cfprAaaRadiusEpName                                              SnmpAdminString,
    cfprAaaRadiusEpPolicyLevel                                       Gauge32,
    cfprAaaRadiusEpPolicyOwner                                       CfprPolicyPolicyOwner,
    cfprAaaRadiusEpRetries                                           Gauge32,
    cfprAaaRadiusEpTimeout                                           Gauge32
}

cfprAaaRadiusEpInstanceId OBJECT-TYPE
    SYNTAX       CfprManagedObjectId
    MAX-ACCESS   not-accessible
    STATUS       current
    DESCRIPTION
        "Instance identifier of the managed object."
    ::= { cfprAaaRadiusEpEntry 1 }

cfprAaaRadiusEpDn OBJECT-TYPE
    SYNTAX       CfprManagedObjectDn
    MAX-ACCESS   read-only
    STATUS       current
    DESCRIPTION
        "Cisco Firepower aaa:RadiusEp:dn managed object property"
    ::= { cfprAaaRadiusEpEntry 2 }

cfprAaaRadiusEpRn OBJECT-TYPE
    SYNTAX       SnmpAdminString
    MAX-ACCESS   read-only
    STATUS       current
    DESCRIPTION
        "Cisco Firepower aaa:RadiusEp:rn managed object property"
    ::= { cfprAaaRadiusEpEntry 3 }

cfprAaaRadiusEpDescr OBJECT-TYPE
    SYNTAX       SnmpAdminString
    MAX-ACCESS   read-only
    STATUS       current
    DESCRIPTION
        "Cisco Firepower aaa:RadiusEp:descr managed object property"
    ::= { cfprAaaRadiusEpEntry 4 }

cfprAaaRadiusEpFsmDescr OBJECT-TYPE
    SYNTAX       SnmpAdminString
    MAX-ACCESS   read-only
    STATUS       current
    DESCRIPTION
        "Cisco Firepower aaa:RadiusEp:fsmDescr managed object property"
    ::= { cfprAaaRadiusEpEntry 5 }

cfprAaaRadiusEpFsmPrev OBJECT-TYPE
    SYNTAX       SnmpAdminString
    MAX-ACCESS   read-only
    STATUS       current
    DESCRIPTION
        "Cisco Firepower aaa:RadiusEp:fsmPrev managed object property"
    ::= { cfprAaaRadiusEpEntry 6 }

cfprAaaRadiusEpFsmProgr OBJECT-TYPE
    SYNTAX       Gauge32
    MAX-ACCESS   read-only
    STATUS       current
    DESCRIPTION
        "Cisco Firepower aaa:RadiusEp:fsmProgr managed object property"
    ::= { cfprAaaRadiusEpEntry 7 }

cfprAaaRadiusEpFsmRmtInvErrCode OBJECT-TYPE
    SYNTAX       Gauge32
    MAX-ACCESS   read-only
    STATUS       current
    DESCRIPTION
        "Cisco Firepower aaa:RadiusEp:fsmRmtInvErrCode
        managed object property"
    ::= { cfprAaaRadiusEpEntry 8 }

cfprAaaRadiusEpFsmRmtInvErrDescr OBJECT-TYPE
    SYNTAX       SnmpAdminString
    MAX-ACCESS   read-only
    STATUS       current
    DESCRIPTION
        "Cisco Firepower aaa:RadiusEp:fsmRmtInvErrDescr
        managed object property"
    ::= { cfprAaaRadiusEpEntry 9 }

cfprAaaRadiusEpFsmRmtInvRslt OBJECT-TYPE
    SYNTAX       CfprConditionRemoteInvRslt
    MAX-ACCESS   read-only
    STATUS       current
    DESCRIPTION
        "Cisco Firepower aaa:RadiusEp:fsmRmtInvRslt managed
        object property"
    ::= { cfprAaaRadiusEpEntry 10 }

cfprAaaRadiusEpFsmStageDescr OBJECT-TYPE
    SYNTAX       SnmpAdminString
    MAX-ACCESS   read-only
    STATUS       current
    DESCRIPTION
        "Cisco Firepower aaa:RadiusEp:fsmStageDescr managed
        object property"
    ::= { cfprAaaRadiusEpEntry 11 }

cfprAaaRadiusEpFsmStamp OBJECT-TYPE
    SYNTAX       DateAndTime
    MAX-ACCESS   read-only
    STATUS       current
    DESCRIPTION
        "Cisco Firepower aaa:RadiusEp:fsmStamp managed object property"
    ::= { cfprAaaRadiusEpEntry 12 }

cfprAaaRadiusEpFsmStatus OBJECT-TYPE
    SYNTAX       SnmpAdminString
    MAX-ACCESS   read-only
    STATUS       current
    DESCRIPTION
        "Cisco Firepower aaa:RadiusEp:fsmStatus managed object property"
    ::= { cfprAaaRadiusEpEntry 13 }

cfprAaaRadiusEpFsmTry OBJECT-TYPE
    SYNTAX       Gauge32
    MAX-ACCESS   read-only
    STATUS       current
    DESCRIPTION
        "Cisco Firepower aaa:RadiusEp:fsmTry managed object property"
    ::= { cfprAaaRadiusEpEntry 14 }

cfprAaaRadiusEpIntId OBJECT-TYPE
    SYNTAX       SnmpAdminString
    MAX-ACCESS   read-only
    STATUS       current
    DESCRIPTION
        "Cisco Firepower aaa:RadiusEp:intId managed object property"
    ::= { cfprAaaRadiusEpEntry 15 }

cfprAaaRadiusEpName OBJECT-TYPE
    SYNTAX       SnmpAdminString
    MAX-ACCESS   read-only
    STATUS       current
    DESCRIPTION
        "Cisco Firepower aaa:RadiusEp:name managed object property"
    ::= { cfprAaaRadiusEpEntry 16 }

cfprAaaRadiusEpPolicyLevel OBJECT-TYPE
    SYNTAX       Gauge32
    MAX-ACCESS   read-only
    STATUS       current
    DESCRIPTION
        "Cisco Firepower aaa:RadiusEp:policyLevel managed object property"
    ::= { cfprAaaRadiusEpEntry 17 }

cfprAaaRadiusEpPolicyOwner OBJECT-TYPE
    SYNTAX       CfprPolicyPolicyOwner
    MAX-ACCESS   read-only
    STATUS       current
    DESCRIPTION
        "Cisco Firepower aaa:RadiusEp:policyOwner managed object property"
    ::= { cfprAaaRadiusEpEntry 18 }

cfprAaaRadiusEpRetries OBJECT-TYPE
    SYNTAX       Gauge32
    MAX-ACCESS   read-only
    STATUS       current
    DESCRIPTION
        "Cisco Firepower aaa:RadiusEp:retries managed object property"
    ::= { cfprAaaRadiusEpEntry 19 }

cfprAaaRadiusEpTimeout OBJECT-TYPE
    SYNTAX       Gauge32
    MAX-ACCESS   read-only
    STATUS       current
    DESCRIPTION
        "Cisco Firepower aaa:RadiusEp:timeout managed object property"
    ::= { cfprAaaRadiusEpEntry 20 }

cfprAaaRadiusEpFsmTable OBJECT-TYPE
    SYNTAX           SEQUENCE OF CfprAaaRadiusEpFsmEntry
    MAX-ACCESS       not-accessible
    STATUS           current
    DESCRIPTION
        "Cisco Firepower aaa:RadiusEpFsm managed object table"
    ::= { cfprAaaObjects 31 }

cfprAaaRadiusEpFsmEntry OBJECT-TYPE
    SYNTAX           CfprAaaRadiusEpFsmEntry
    MAX-ACCESS       not-accessible
    STATUS           current
    DESCRIPTION
        "Entry for the cfprAaaRadiusEpFsmTable table."
    INDEX { cfprAaaRadiusEpFsmInstanceId }
    ::= { cfprAaaRadiusEpFsmTable 1 }

CfprAaaRadiusEpFsmEntry ::= SEQUENCE {
    cfprAaaRadiusEpFsmInstanceId                                     CfprManagedObjectId,
    cfprAaaRadiusEpFsmDn                                             CfprManagedObjectDn,
    cfprAaaRadiusEpFsmRn                                             SnmpAdminString,
    cfprAaaRadiusEpFsmCompletionTime                                 DateAndTime,
    cfprAaaRadiusEpFsmCurrentFsm                                     CfprAaaRadiusEpFsmCurrentFsm,
    cfprAaaRadiusEpFsmDescrData                                      SnmpAdminString,
    cfprAaaRadiusEpFsmFsmStatus                                      CfprFsmFsmStageStatus,
    cfprAaaRadiusEpFsmProgress                                       Gauge32,
    cfprAaaRadiusEpFsmRmtErrCode                                     Gauge32,
    cfprAaaRadiusEpFsmRmtErrDescr                                    SnmpAdminString,
    cfprAaaRadiusEpFsmRmtRslt                                        CfprConditionRemoteInvRslt
}

cfprAaaRadiusEpFsmInstanceId OBJECT-TYPE
    SYNTAX       CfprManagedObjectId
    MAX-ACCESS   not-accessible
    STATUS       current
    DESCRIPTION
        "Instance identifier of the managed object."
    ::= { cfprAaaRadiusEpFsmEntry 1 }

cfprAaaRadiusEpFsmDn OBJECT-TYPE
    SYNTAX       CfprManagedObjectDn
    MAX-ACCESS   read-only
    STATUS       current
    DESCRIPTION
        "Cisco Firepower aaa:RadiusEpFsm:dn managed object property"
    ::= { cfprAaaRadiusEpFsmEntry 2 }

cfprAaaRadiusEpFsmRn OBJECT-TYPE
    SYNTAX       SnmpAdminString
    MAX-ACCESS   read-only
    STATUS       current
    DESCRIPTION
        "Cisco Firepower aaa:RadiusEpFsm:rn managed object property"
    ::= { cfprAaaRadiusEpFsmEntry 3 }

cfprAaaRadiusEpFsmCompletionTime OBJECT-TYPE
    SYNTAX       DateAndTime
    MAX-ACCESS   read-only
    STATUS       current
    DESCRIPTION
        "Cisco Firepower aaa:RadiusEpFsm:completionTime
        managed object property"
    ::= { cfprAaaRadiusEpFsmEntry 4 }

cfprAaaRadiusEpFsmCurrentFsm OBJECT-TYPE
    SYNTAX       CfprAaaRadiusEpFsmCurrentFsm
    MAX-ACCESS   read-only
    STATUS       current
    DESCRIPTION
        "Cisco Firepower aaa:RadiusEpFsm:currentFsm managed
        object property"
    ::= { cfprAaaRadiusEpFsmEntry 5 }

cfprAaaRadiusEpFsmDescrData OBJECT-TYPE
    SYNTAX       SnmpAdminString
    MAX-ACCESS   read-only
    STATUS       current
    DESCRIPTION
        "Cisco Firepower aaa:RadiusEpFsm:descr managed object property"
    ::= { cfprAaaRadiusEpFsmEntry 6 }

cfprAaaRadiusEpFsmFsmStatus OBJECT-TYPE
    SYNTAX       CfprFsmFsmStageStatus
    MAX-ACCESS   read-only
    STATUS       current
    DESCRIPTION
        "Cisco Firepower aaa:RadiusEpFsm:fsmStatus managed
        object property"
    ::= { cfprAaaRadiusEpFsmEntry 7 }

cfprAaaRadiusEpFsmProgress OBJECT-TYPE
    SYNTAX       Gauge32
    MAX-ACCESS   read-only
    STATUS       current
    DESCRIPTION
        "Cisco Firepower aaa:RadiusEpFsm:progress managed object property"
    ::= { cfprAaaRadiusEpFsmEntry 8 }

cfprAaaRadiusEpFsmRmtErrCode OBJECT-TYPE
    SYNTAX       Gauge32
    MAX-ACCESS   read-only
    STATUS       current
    DESCRIPTION
        "Cisco Firepower aaa:RadiusEpFsm:rmtErrCode managed
        object property"
    ::= { cfprAaaRadiusEpFsmEntry 9 }

cfprAaaRadiusEpFsmRmtErrDescr OBJECT-TYPE
    SYNTAX       SnmpAdminString
    MAX-ACCESS   read-only
    STATUS       current
    DESCRIPTION
        "Cisco Firepower aaa:RadiusEpFsm:rmtErrDescr managed
        object property"
    ::= { cfprAaaRadiusEpFsmEntry 10 }

cfprAaaRadiusEpFsmRmtRslt OBJECT-TYPE
    SYNTAX       CfprConditionRemoteInvRslt
    MAX-ACCESS   read-only
    STATUS       current
    DESCRIPTION
        "Cisco Firepower aaa:RadiusEpFsm:rmtRslt managed object property"
    ::= { cfprAaaRadiusEpFsmEntry 11 }

cfprAaaRadiusEpFsmStageTable OBJECT-TYPE
    SYNTAX           SEQUENCE OF CfprAaaRadiusEpFsmStageEntry
    MAX-ACCESS       not-accessible
    STATUS           current
    DESCRIPTION
        "Cisco Firepower aaa:RadiusEpFsmStage managed object table"
    ::= { cfprAaaObjects 32 }

cfprAaaRadiusEpFsmStageEntry OBJECT-TYPE
    SYNTAX           CfprAaaRadiusEpFsmStageEntry
    MAX-ACCESS       not-accessible
    STATUS           current
    DESCRIPTION
        "Entry for the cfprAaaRadiusEpFsmStageTable table."
    INDEX { cfprAaaRadiusEpFsmStageInstanceId }
    ::= { cfprAaaRadiusEpFsmStageTable 1 }

CfprAaaRadiusEpFsmStageEntry ::= SEQUENCE {
    cfprAaaRadiusEpFsmStageInstanceId                                CfprManagedObjectId,
    cfprAaaRadiusEpFsmStageDn                                        CfprManagedObjectDn,
    cfprAaaRadiusEpFsmStageRn                                        SnmpAdminString,
    cfprAaaRadiusEpFsmStageDescrData                                 SnmpAdminString,
    cfprAaaRadiusEpFsmStageLastUpdateTime                            DateAndTime,
    cfprAaaRadiusEpFsmStageName                                      CfprAaaRadiusEpFsmStageName,
    cfprAaaRadiusEpFsmStageOrder                                     Gauge32,
    cfprAaaRadiusEpFsmStageRetry                                     Gauge32,
    cfprAaaRadiusEpFsmStageStageStatus                               CfprFsmFsmStageStatus
}

cfprAaaRadiusEpFsmStageInstanceId OBJECT-TYPE
    SYNTAX       CfprManagedObjectId
    MAX-ACCESS   not-accessible
    STATUS       current
    DESCRIPTION
        "Instance identifier of the managed object."
    ::= { cfprAaaRadiusEpFsmStageEntry 1 }

cfprAaaRadiusEpFsmStageDn OBJECT-TYPE
    SYNTAX       CfprManagedObjectDn
    MAX-ACCESS   read-only
    STATUS       current
    DESCRIPTION
        "Cisco Firepower aaa:RadiusEpFsmStage:dn managed object property"
    ::= { cfprAaaRadiusEpFsmStageEntry 2 }

cfprAaaRadiusEpFsmStageRn OBJECT-TYPE
    SYNTAX       SnmpAdminString
    MAX-ACCESS   read-only
    STATUS       current
    DESCRIPTION
        "Cisco Firepower aaa:RadiusEpFsmStage:rn managed object property"
    ::= { cfprAaaRadiusEpFsmStageEntry 3 }

cfprAaaRadiusEpFsmStageDescrData OBJECT-TYPE
    SYNTAX       SnmpAdminString
    MAX-ACCESS   read-only
    STATUS       current
    DESCRIPTION
        "Cisco Firepower aaa:RadiusEpFsmStage:descr managed
        object property"
    ::= { cfprAaaRadiusEpFsmStageEntry 4 }

cfprAaaRadiusEpFsmStageLastUpdateTime OBJECT-TYPE
    SYNTAX       DateAndTime
    MAX-ACCESS   read-only
    STATUS       current
    DESCRIPTION
        "Cisco Firepower aaa:RadiusEpFsmStage:lastUpdateTime
        managed object property"
    ::= { cfprAaaRadiusEpFsmStageEntry 5 }

cfprAaaRadiusEpFsmStageName OBJECT-TYPE
    SYNTAX       CfprAaaRadiusEpFsmStageName
    MAX-ACCESS   read-only
    STATUS       current
    DESCRIPTION
        "Cisco Firepower aaa:RadiusEpFsmStage:name managed
        object property"
    ::= { cfprAaaRadiusEpFsmStageEntry 6 }

cfprAaaRadiusEpFsmStageOrder OBJECT-TYPE
    SYNTAX       Gauge32
    MAX-ACCESS   read-only
    STATUS       current
    DESCRIPTION
        "Cisco Firepower aaa:RadiusEpFsmStage:order managed
        object property"
    ::= { cfprAaaRadiusEpFsmStageEntry 7 }

cfprAaaRadiusEpFsmStageRetry OBJECT-TYPE
    SYNTAX       Gauge32
    MAX-ACCESS   read-only
    STATUS       current
    DESCRIPTION
        "Cisco Firepower aaa:RadiusEpFsmStage:retry managed
        object property"
    ::= { cfprAaaRadiusEpFsmStageEntry 8 }

cfprAaaRadiusEpFsmStageStageStatus OBJECT-TYPE
    SYNTAX       CfprFsmFsmStageStatus
    MAX-ACCESS   read-only
    STATUS       current
    DESCRIPTION
        "Cisco Firepower aaa:RadiusEpFsmStage:stageStatus
        managed object property"
    ::= { cfprAaaRadiusEpFsmStageEntry 9 }

cfprAaaRadiusProviderTable OBJECT-TYPE
    SYNTAX           SEQUENCE OF CfprAaaRadiusProviderEntry
    MAX-ACCESS       not-accessible
    STATUS           current
    DESCRIPTION
        "Cisco Firepower aaa:RadiusProvider managed object table"
    ::= { cfprAaaObjects 33 }

cfprAaaRadiusProviderEntry OBJECT-TYPE
    SYNTAX           CfprAaaRadiusProviderEntry
    MAX-ACCESS       not-accessible
    STATUS           current
    DESCRIPTION
        "Entry for the cfprAaaRadiusProviderTable table."
    INDEX { cfprAaaRadiusProviderInstanceId }
    ::= { cfprAaaRadiusProviderTable 1 }

CfprAaaRadiusProviderEntry ::= SEQUENCE {
    cfprAaaRadiusProviderInstanceId                                  CfprManagedObjectId,
    cfprAaaRadiusProviderDn                                          CfprManagedObjectDn,
    cfprAaaRadiusProviderRn                                          SnmpAdminString,
    cfprAaaRadiusProviderAuthPort                                    Gauge32,
    cfprAaaRadiusProviderDescr                                       SnmpAdminString,
    cfprAaaRadiusProviderEncKey                                      SnmpAdminString,
    cfprAaaRadiusProviderKey                                         SnmpAdminString,
    cfprAaaRadiusProviderKeySet                                      TruthValue,
    cfprAaaRadiusProviderName                                        SnmpAdminString,
    cfprAaaRadiusProviderOrder                                       Gauge32,
    cfprAaaRadiusProviderRetries                                     Gauge32,
    cfprAaaRadiusProviderService                                     CfprAaaRadiusService,
    cfprAaaRadiusProviderTimeout                                     Gauge32
}

cfprAaaRadiusProviderInstanceId OBJECT-TYPE
    SYNTAX       CfprManagedObjectId
    MAX-ACCESS   not-accessible
    STATUS       current
    DESCRIPTION
        "Instance identifier of the managed object."
    ::= { cfprAaaRadiusProviderEntry 1 }

cfprAaaRadiusProviderDn OBJECT-TYPE
    SYNTAX       CfprManagedObjectDn
    MAX-ACCESS   read-only
    STATUS       current
    DESCRIPTION
        "Cisco Firepower aaa:RadiusProvider:dn managed object property"
    ::= { cfprAaaRadiusProviderEntry 2 }

cfprAaaRadiusProviderRn OBJECT-TYPE
    SYNTAX       SnmpAdminString
    MAX-ACCESS   read-only
    STATUS       current
    DESCRIPTION
        "Cisco Firepower aaa:RadiusProvider:rn managed object property"
    ::= { cfprAaaRadiusProviderEntry 3 }

cfprAaaRadiusProviderAuthPort OBJECT-TYPE
    SYNTAX       Gauge32
    MAX-ACCESS   read-only
    STATUS       current
    DESCRIPTION
        "Cisco Firepower aaa:RadiusProvider:authPort managed
        object property"
    ::= { cfprAaaRadiusProviderEntry 4 }

cfprAaaRadiusProviderDescr OBJECT-TYPE
    SYNTAX       SnmpAdminString
    MAX-ACCESS   read-only
    STATUS       current
    DESCRIPTION
        "Cisco Firepower aaa:RadiusProvider:descr managed object property"
    ::= { cfprAaaRadiusProviderEntry 5 }

cfprAaaRadiusProviderEncKey OBJECT-TYPE
    SYNTAX       SnmpAdminString
    MAX-ACCESS   read-only
    STATUS       current
    DESCRIPTION
        "Cisco Firepower aaa:RadiusProvider:encKey managed
        object property"
    ::= { cfprAaaRadiusProviderEntry 6 }

cfprAaaRadiusProviderKey OBJECT-TYPE
    SYNTAX       SnmpAdminString
    MAX-ACCESS   read-only
    STATUS       current
    DESCRIPTION
        "Cisco Firepower aaa:RadiusProvider:key managed object property"
    ::= { cfprAaaRadiusProviderEntry 7 }

cfprAaaRadiusProviderKeySet OBJECT-TYPE
    SYNTAX       TruthValue
    MAX-ACCESS   read-only
    STATUS       current
    DESCRIPTION
        "Cisco Firepower aaa:RadiusProvider:keySet managed
        object property"
    ::= { cfprAaaRadiusProviderEntry 8 }

cfprAaaRadiusProviderName OBJECT-TYPE
    SYNTAX       SnmpAdminString
    MAX-ACCESS   read-only
    STATUS       current
    DESCRIPTION
        "Cisco Firepower aaa:RadiusProvider:name managed object property"
    ::= { cfprAaaRadiusProviderEntry 9 }

cfprAaaRadiusProviderOrder OBJECT-TYPE
    SYNTAX       Gauge32
    MAX-ACCESS   read-only
    STATUS       current
    DESCRIPTION
        "Cisco Firepower aaa:RadiusProvider:order managed object property"
    ::= { cfprAaaRadiusProviderEntry 10 }

cfprAaaRadiusProviderRetries OBJECT-TYPE
    SYNTAX       Gauge32
    MAX-ACCESS   read-only
    STATUS       current
    DESCRIPTION
        "Cisco Firepower aaa:RadiusProvider:retries managed
        object property"
    ::= { cfprAaaRadiusProviderEntry 11 }

cfprAaaRadiusProviderService OBJECT-TYPE
    SYNTAX       CfprAaaRadiusService
    MAX-ACCESS   read-only
    STATUS       current
    DESCRIPTION
        "Cisco Firepower aaa:RadiusProvider:service managed
        object property"
    ::= { cfprAaaRadiusProviderEntry 12 }

cfprAaaRadiusProviderTimeout OBJECT-TYPE
    SYNTAX       Gauge32
    MAX-ACCESS   read-only
    STATUS       current
    DESCRIPTION
        "Cisco Firepower aaa:RadiusProvider:timeout managed
        object property"
    ::= { cfprAaaRadiusProviderEntry 13 }

cfprAaaRealmFsmTable OBJECT-TYPE
    SYNTAX           SEQUENCE OF CfprAaaRealmFsmEntry
    MAX-ACCESS       not-accessible
    STATUS           current
    DESCRIPTION
        "Cisco Firepower aaa:RealmFsm managed object table"
    ::= { cfprAaaObjects 34 }

cfprAaaRealmFsmEntry OBJECT-TYPE
    SYNTAX           CfprAaaRealmFsmEntry
    MAX-ACCESS       not-accessible
    STATUS           current
    DESCRIPTION
        "Entry for the cfprAaaRealmFsmTable table."
    INDEX { cfprAaaRealmFsmInstanceId }
    ::= { cfprAaaRealmFsmTable 1 }

CfprAaaRealmFsmEntry ::= SEQUENCE {
    cfprAaaRealmFsmInstanceId                                        CfprManagedObjectId,
    cfprAaaRealmFsmDn                                                CfprManagedObjectDn,
    cfprAaaRealmFsmRn                                                SnmpAdminString,
    cfprAaaRealmFsmCompletionTime                                    DateAndTime,
    cfprAaaRealmFsmCurrentFsm                                        CfprAaaRealmFsmCurrentFsm,
    cfprAaaRealmFsmDescr                                             SnmpAdminString,
    cfprAaaRealmFsmFsmStatus                                         CfprFsmFsmStageStatus,
    cfprAaaRealmFsmProgress                                          Gauge32,
    cfprAaaRealmFsmRmtErrCode                                        Gauge32,
    cfprAaaRealmFsmRmtErrDescr                                       SnmpAdminString,
    cfprAaaRealmFsmRmtRslt                                           CfprConditionRemoteInvRslt
}

cfprAaaRealmFsmInstanceId OBJECT-TYPE
    SYNTAX       CfprManagedObjectId
    MAX-ACCESS   not-accessible
    STATUS       current
    DESCRIPTION
        "Instance identifier of the managed object."
    ::= { cfprAaaRealmFsmEntry 1 }

cfprAaaRealmFsmDn OBJECT-TYPE
    SYNTAX       CfprManagedObjectDn
    MAX-ACCESS   read-only
    STATUS       current
    DESCRIPTION
        "Cisco Firepower aaa:RealmFsm:dn managed object property"
    ::= { cfprAaaRealmFsmEntry 2 }

cfprAaaRealmFsmRn OBJECT-TYPE
    SYNTAX       SnmpAdminString
    MAX-ACCESS   read-only
    STATUS       current
    DESCRIPTION
        "Cisco Firepower aaa:RealmFsm:rn managed object property"
    ::= { cfprAaaRealmFsmEntry 3 }

cfprAaaRealmFsmCompletionTime OBJECT-TYPE
    SYNTAX       DateAndTime
    MAX-ACCESS   read-only
    STATUS       current
    DESCRIPTION
        "Cisco Firepower aaa:RealmFsm:completionTime managed
        object property"
    ::= { cfprAaaRealmFsmEntry 4 }

cfprAaaRealmFsmCurrentFsm OBJECT-TYPE
    SYNTAX       CfprAaaRealmFsmCurrentFsm
    MAX-ACCESS   read-only
    STATUS       current
    DESCRIPTION
        "Cisco Firepower aaa:RealmFsm:currentFsm managed object property"
    ::= { cfprAaaRealmFsmEntry 5 }

cfprAaaRealmFsmDescr OBJECT-TYPE
    SYNTAX       SnmpAdminString
    MAX-ACCESS   read-only
    STATUS       current
    DESCRIPTION
        "Cisco Firepower aaa:RealmFsm:descr managed object property"
    ::= { cfprAaaRealmFsmEntry 6 }

cfprAaaRealmFsmFsmStatus OBJECT-TYPE
    SYNTAX       CfprFsmFsmStageStatus
    MAX-ACCESS   read-only
    STATUS       current
    DESCRIPTION
        "Cisco Firepower aaa:RealmFsm:fsmStatus managed object property"
    ::= { cfprAaaRealmFsmEntry 7 }

cfprAaaRealmFsmProgress OBJECT-TYPE
    SYNTAX       Gauge32
    MAX-ACCESS   read-only
    STATUS       current
    DESCRIPTION
        "Cisco Firepower aaa:RealmFsm:progress managed object property"
    ::= { cfprAaaRealmFsmEntry 8 }

cfprAaaRealmFsmRmtErrCode OBJECT-TYPE
    SYNTAX       Gauge32
    MAX-ACCESS   read-only
    STATUS       current
    DESCRIPTION
        "Cisco Firepower aaa:RealmFsm:rmtErrCode managed object property"
    ::= { cfprAaaRealmFsmEntry 9 }

cfprAaaRealmFsmRmtErrDescr OBJECT-TYPE
    SYNTAX       SnmpAdminString
    MAX-ACCESS   read-only
    STATUS       current
    DESCRIPTION
        "Cisco Firepower aaa:RealmFsm:rmtErrDescr managed object property"
    ::= { cfprAaaRealmFsmEntry 10 }

cfprAaaRealmFsmRmtRslt OBJECT-TYPE
    SYNTAX       CfprConditionRemoteInvRslt
    MAX-ACCESS   read-only
    STATUS       current
    DESCRIPTION
        "Cisco Firepower aaa:RealmFsm:rmtRslt managed object property"
    ::= { cfprAaaRealmFsmEntry 11 }

cfprAaaRealmFsmStageTable OBJECT-TYPE
    SYNTAX           SEQUENCE OF CfprAaaRealmFsmStageEntry
    MAX-ACCESS       not-accessible
    STATUS           current
    DESCRIPTION
        "Cisco Firepower aaa:RealmFsmStage managed object table"
    ::= { cfprAaaObjects 35 }

cfprAaaRealmFsmStageEntry OBJECT-TYPE
    SYNTAX           CfprAaaRealmFsmStageEntry
    MAX-ACCESS       not-accessible
    STATUS           current
    DESCRIPTION
        "Entry for the cfprAaaRealmFsmStageTable table."
    INDEX { cfprAaaRealmFsmStageInstanceId }
    ::= { cfprAaaRealmFsmStageTable 1 }

CfprAaaRealmFsmStageEntry ::= SEQUENCE {
    cfprAaaRealmFsmStageInstanceId                                   CfprManagedObjectId,
    cfprAaaRealmFsmStageDn                                           CfprManagedObjectDn,
    cfprAaaRealmFsmStageRn                                           SnmpAdminString,
    cfprAaaRealmFsmStageDescr                                        SnmpAdminString,
    cfprAaaRealmFsmStageLastUpdateTime                               DateAndTime,
    cfprAaaRealmFsmStageName                                         CfprAaaRealmFsmStageName,
    cfprAaaRealmFsmStageOrder                                        Gauge32,
    cfprAaaRealmFsmStageRetry                                        Gauge32,
    cfprAaaRealmFsmStageStageStatus                                  CfprFsmFsmStageStatus
}

cfprAaaRealmFsmStageInstanceId OBJECT-TYPE
    SYNTAX       CfprManagedObjectId
    MAX-ACCESS   not-accessible
    STATUS       current
    DESCRIPTION
        "Instance identifier of the managed object."
    ::= { cfprAaaRealmFsmStageEntry 1 }

cfprAaaRealmFsmStageDn OBJECT-TYPE
    SYNTAX       CfprManagedObjectDn
    MAX-ACCESS   read-only
    STATUS       current
    DESCRIPTION
        "Cisco Firepower aaa:RealmFsmStage:dn managed object property"
    ::= { cfprAaaRealmFsmStageEntry 2 }

cfprAaaRealmFsmStageRn OBJECT-TYPE
    SYNTAX       SnmpAdminString
    MAX-ACCESS   read-only
    STATUS       current
    DESCRIPTION
        "Cisco Firepower aaa:RealmFsmStage:rn managed object property"
    ::= { cfprAaaRealmFsmStageEntry 3 }

cfprAaaRealmFsmStageDescr OBJECT-TYPE
    SYNTAX       SnmpAdminString
    MAX-ACCESS   read-only
    STATUS       current
    DESCRIPTION
        "Cisco Firepower aaa:RealmFsmStage:descr managed object property"
    ::= { cfprAaaRealmFsmStageEntry 4 }

cfprAaaRealmFsmStageLastUpdateTime OBJECT-TYPE
    SYNTAX       DateAndTime
    MAX-ACCESS   read-only
    STATUS       current
    DESCRIPTION
        "Cisco Firepower aaa:RealmFsmStage:lastUpdateTime
        managed object property"
    ::= { cfprAaaRealmFsmStageEntry 5 }

cfprAaaRealmFsmStageName OBJECT-TYPE
    SYNTAX       CfprAaaRealmFsmStageName
    MAX-ACCESS   read-only
    STATUS       current
    DESCRIPTION
        "Cisco Firepower aaa:RealmFsmStage:name managed object property"
    ::= { cfprAaaRealmFsmStageEntry 6 }

cfprAaaRealmFsmStageOrder OBJECT-TYPE
    SYNTAX       Gauge32
    MAX-ACCESS   read-only
    STATUS       current
    DESCRIPTION
        "Cisco Firepower aaa:RealmFsmStage:order managed object property"
    ::= { cfprAaaRealmFsmStageEntry 7 }

cfprAaaRealmFsmStageRetry OBJECT-TYPE
    SYNTAX       Gauge32
    MAX-ACCESS   read-only
    STATUS       current
    DESCRIPTION
        "Cisco Firepower aaa:RealmFsmStage:retry managed object property"
    ::= { cfprAaaRealmFsmStageEntry 8 }

cfprAaaRealmFsmStageStageStatus OBJECT-TYPE
    SYNTAX       CfprFsmFsmStageStatus
    MAX-ACCESS   read-only
    STATUS       current
    DESCRIPTION
        "Cisco Firepower aaa:RealmFsmStage:stageStatus
        managed object property"
    ::= { cfprAaaRealmFsmStageEntry 9 }

cfprAaaRealmFsmTaskTable OBJECT-TYPE
    SYNTAX           SEQUENCE OF CfprAaaRealmFsmTaskEntry
    MAX-ACCESS       not-accessible
    STATUS           current
    DESCRIPTION
        "Cisco Firepower aaa:RealmFsmTask managed object table"
    ::= { cfprAaaObjects 36 }

cfprAaaRealmFsmTaskEntry OBJECT-TYPE
    SYNTAX           CfprAaaRealmFsmTaskEntry
    MAX-ACCESS       not-accessible
    STATUS           current
    DESCRIPTION
        "Entry for the cfprAaaRealmFsmTaskTable table."
    INDEX { cfprAaaRealmFsmTaskInstanceId }
    ::= { cfprAaaRealmFsmTaskTable 1 }

CfprAaaRealmFsmTaskEntry ::= SEQUENCE {
    cfprAaaRealmFsmTaskInstanceId                                    CfprManagedObjectId,
    cfprAaaRealmFsmTaskDn                                            CfprManagedObjectDn,
    cfprAaaRealmFsmTaskRn                                            SnmpAdminString,
    cfprAaaRealmFsmTaskCompletion                                    CfprFsmCompletion,
    cfprAaaRealmFsmTaskFlags                                         CfprFsmFlags,
    cfprAaaRealmFsmTaskItem                                          CfprAaaRealmFsmTaskItem,
    cfprAaaRealmFsmTaskSeqId                                         Gauge32
}

cfprAaaRealmFsmTaskInstanceId OBJECT-TYPE
    SYNTAX       CfprManagedObjectId
    MAX-ACCESS   not-accessible
    STATUS       current
    DESCRIPTION
        "Instance identifier of the managed object."
    ::= { cfprAaaRealmFsmTaskEntry 1 }

cfprAaaRealmFsmTaskDn OBJECT-TYPE
    SYNTAX       CfprManagedObjectDn
    MAX-ACCESS   read-only
    STATUS       current
    DESCRIPTION
        "Cisco Firepower aaa:RealmFsmTask:dn managed object property"
    ::= { cfprAaaRealmFsmTaskEntry 2 }

cfprAaaRealmFsmTaskRn OBJECT-TYPE
    SYNTAX       SnmpAdminString
    MAX-ACCESS   read-only
    STATUS       current
    DESCRIPTION
        "Cisco Firepower aaa:RealmFsmTask:rn managed object property"
    ::= { cfprAaaRealmFsmTaskEntry 3 }

cfprAaaRealmFsmTaskCompletion OBJECT-TYPE
    SYNTAX       CfprFsmCompletion
    MAX-ACCESS   read-only
    STATUS       current
    DESCRIPTION
        "Cisco Firepower aaa:RealmFsmTask:completion managed
        object property"
    ::= { cfprAaaRealmFsmTaskEntry 4 }

cfprAaaRealmFsmTaskFlags OBJECT-TYPE
    SYNTAX       CfprFsmFlags
    MAX-ACCESS   read-only
    STATUS       current
    DESCRIPTION
        "Cisco Firepower aaa:RealmFsmTask:flags managed object property"
    ::= { cfprAaaRealmFsmTaskEntry 5 }

cfprAaaRealmFsmTaskItem OBJECT-TYPE
    SYNTAX       CfprAaaRealmFsmTaskItem
    MAX-ACCESS   read-only
    STATUS       current
    DESCRIPTION
        "Cisco Firepower aaa:RealmFsmTask:item managed object property"
    ::= { cfprAaaRealmFsmTaskEntry 6 }

cfprAaaRealmFsmTaskSeqId OBJECT-TYPE
    SYNTAX       Gauge32
    MAX-ACCESS   read-only
    STATUS       current
    DESCRIPTION
        "Cisco Firepower aaa:RealmFsmTask:seqId managed object property"
    ::= { cfprAaaRealmFsmTaskEntry 7 }

cfprAaaRemoteUserTable OBJECT-TYPE
    SYNTAX           SEQUENCE OF CfprAaaRemoteUserEntry
    MAX-ACCESS       not-accessible
    STATUS           current
    DESCRIPTION
        "Cisco Firepower aaa:RemoteUser managed object table"
    ::= { cfprAaaObjects 37 }

cfprAaaRemoteUserEntry OBJECT-TYPE
    SYNTAX           CfprAaaRemoteUserEntry
    MAX-ACCESS       not-accessible
    STATUS           current
    DESCRIPTION
        "Entry for the cfprAaaRemoteUserTable table."
    INDEX { cfprAaaRemoteUserInstanceId }
    ::= { cfprAaaRemoteUserTable 1 }

CfprAaaRemoteUserEntry ::= SEQUENCE {
    cfprAaaRemoteUserInstanceId                                      CfprManagedObjectId,
    cfprAaaRemoteUserDn                                              CfprManagedObjectDn,
    cfprAaaRemoteUserRn                                              SnmpAdminString,
    cfprAaaRemoteUserConfigState                                     CfprAaaConfigState,
    cfprAaaRemoteUserConfigStatusMessage                             SnmpAdminString,
    cfprAaaRemoteUserDescr                                           SnmpAdminString,
    cfprAaaRemoteUserName                                            SnmpAdminString,
    cfprAaaRemoteUserPwd                                             SnmpAdminString,
    cfprAaaRemoteUserPwdSet                                          TruthValue
}

cfprAaaRemoteUserInstanceId OBJECT-TYPE
    SYNTAX       CfprManagedObjectId
    MAX-ACCESS   not-accessible
    STATUS       current
    DESCRIPTION
        "Instance identifier of the managed object."
    ::= { cfprAaaRemoteUserEntry 1 }

cfprAaaRemoteUserDn OBJECT-TYPE
    SYNTAX       CfprManagedObjectDn
    MAX-ACCESS   read-only
    STATUS       current
    DESCRIPTION
        "Cisco Firepower aaa:RemoteUser:dn managed object property"
    ::= { cfprAaaRemoteUserEntry 2 }

cfprAaaRemoteUserRn OBJECT-TYPE
    SYNTAX       SnmpAdminString
    MAX-ACCESS   read-only
    STATUS       current
    DESCRIPTION
        "Cisco Firepower aaa:RemoteUser:rn managed object property"
    ::= { cfprAaaRemoteUserEntry 3 }

cfprAaaRemoteUserConfigState OBJECT-TYPE
    SYNTAX       CfprAaaConfigState
    MAX-ACCESS   read-only
    STATUS       current
    DESCRIPTION
        "Cisco Firepower aaa:RemoteUser:configState managed
        object property"
    ::= { cfprAaaRemoteUserEntry 4 }

cfprAaaRemoteUserConfigStatusMessage OBJECT-TYPE
    SYNTAX       SnmpAdminString
    MAX-ACCESS   read-only
    STATUS       current
    DESCRIPTION
        "Cisco Firepower aaa:RemoteUser:configStatusMessage
        managed object property"
    ::= { cfprAaaRemoteUserEntry 5 }

cfprAaaRemoteUserDescr OBJECT-TYPE
    SYNTAX       SnmpAdminString
    MAX-ACCESS   read-only
    STATUS       current
    DESCRIPTION
        "Cisco Firepower aaa:RemoteUser:descr managed object property"
    ::= { cfprAaaRemoteUserEntry 6 }

cfprAaaRemoteUserName OBJECT-TYPE
    SYNTAX       SnmpAdminString
    MAX-ACCESS   read-only
    STATUS       current
    DESCRIPTION
        "Cisco Firepower aaa:RemoteUser:name managed object property"
    ::= { cfprAaaRemoteUserEntry 7 }

cfprAaaRemoteUserPwd OBJECT-TYPE
    SYNTAX       SnmpAdminString
    MAX-ACCESS   read-only
    STATUS       current
    DESCRIPTION
        "Cisco Firepower aaa:RemoteUser:pwd managed object property"
    ::= { cfprAaaRemoteUserEntry 8 }

cfprAaaRemoteUserPwdSet OBJECT-TYPE
    SYNTAX       TruthValue
    MAX-ACCESS   read-only
    STATUS       current
    DESCRIPTION
        "Cisco Firepower aaa:RemoteUser:pwdSet managed object property"
    ::= { cfprAaaRemoteUserEntry 9 }

cfprAaaRoleTable OBJECT-TYPE
    SYNTAX           SEQUENCE OF CfprAaaRoleEntry
    MAX-ACCESS       not-accessible
    STATUS           current
    DESCRIPTION
        "Cisco Firepower aaa:Role managed object table"
    ::= { cfprAaaObjects 38 }

cfprAaaRoleEntry OBJECT-TYPE
    SYNTAX           CfprAaaRoleEntry
    MAX-ACCESS       not-accessible
    STATUS           current
    DESCRIPTION
        "Entry for the cfprAaaRoleTable table."
    INDEX { cfprAaaRoleInstanceId }
    ::= { cfprAaaRoleTable 1 }

CfprAaaRoleEntry ::= SEQUENCE {
    cfprAaaRoleInstanceId                                            CfprManagedObjectId,
    cfprAaaRoleDn                                                    CfprManagedObjectDn,
    cfprAaaRoleRn                                                    SnmpAdminString,
    cfprAaaRoleConfigState                                           CfprAaaConfigState,
    cfprAaaRoleConfigStatusMessage                                   SnmpAdminString,
    cfprAaaRoleDescr                                                 SnmpAdminString,
    cfprAaaRoleIntId                                                 SnmpAdminString,
    cfprAaaRoleName                                                  SnmpAdminString,
    cfprAaaRolePolicyLevel                                           Gauge32,
    cfprAaaRolePolicyOwner                                           CfprPolicyPolicyOwner,
    cfprAaaRolePriv                                                  CfprAaaAccess
}

cfprAaaRoleInstanceId OBJECT-TYPE
    SYNTAX       CfprManagedObjectId
    MAX-ACCESS   not-accessible
    STATUS       current
    DESCRIPTION
        "Instance identifier of the managed object."
    ::= { cfprAaaRoleEntry 1 }

cfprAaaRoleDn OBJECT-TYPE
    SYNTAX       CfprManagedObjectDn
    MAX-ACCESS   read-only
    STATUS       current
    DESCRIPTION
        "Cisco Firepower aaa:Role:dn managed object property"
    ::= { cfprAaaRoleEntry 2 }

cfprAaaRoleRn OBJECT-TYPE
    SYNTAX       SnmpAdminString
    MAX-ACCESS   read-only
    STATUS       current
    DESCRIPTION
        "Cisco Firepower aaa:Role:rn managed object property"
    ::= { cfprAaaRoleEntry 3 }

cfprAaaRoleConfigState OBJECT-TYPE
    SYNTAX       CfprAaaConfigState
    MAX-ACCESS   read-only
    STATUS       current
    DESCRIPTION
        "Cisco Firepower aaa:Role:configState managed object property"
    ::= { cfprAaaRoleEntry 4 }

cfprAaaRoleConfigStatusMessage OBJECT-TYPE
    SYNTAX       SnmpAdminString
    MAX-ACCESS   read-only
    STATUS       current
    DESCRIPTION
        "Cisco Firepower aaa:Role:configStatusMessage managed
        object property"
    ::= { cfprAaaRoleEntry 5 }

cfprAaaRoleDescr OBJECT-TYPE
    SYNTAX       SnmpAdminString
    MAX-ACCESS   read-only
    STATUS       current
    DESCRIPTION
        "Cisco Firepower aaa:Role:descr managed object property"
    ::= { cfprAaaRoleEntry 6 }

cfprAaaRoleIntId OBJECT-TYPE
    SYNTAX       SnmpAdminString
    MAX-ACCESS   read-only
    STATUS       current
    DESCRIPTION
        "Cisco Firepower aaa:Role:intId managed object property"
    ::= { cfprAaaRoleEntry 7 }

cfprAaaRoleName OBJECT-TYPE
    SYNTAX       SnmpAdminString
    MAX-ACCESS   read-only
    STATUS       current
    DESCRIPTION
        "Cisco Firepower aaa:Role:name managed object property"
    ::= { cfprAaaRoleEntry 8 }

cfprAaaRolePolicyLevel OBJECT-TYPE
    SYNTAX       Gauge32
    MAX-ACCESS   read-only
    STATUS       current
    DESCRIPTION
        "Cisco Firepower aaa:Role:policyLevel managed object property"
    ::= { cfprAaaRoleEntry 9 }

cfprAaaRolePolicyOwner OBJECT-TYPE
    SYNTAX       CfprPolicyPolicyOwner
    MAX-ACCESS   read-only
    STATUS       current
    DESCRIPTION
        "Cisco Firepower aaa:Role:policyOwner managed object property"
    ::= { cfprAaaRoleEntry 10 }

cfprAaaRolePriv OBJECT-TYPE
    SYNTAX       CfprAaaAccess
    MAX-ACCESS   read-only
    STATUS       current
    DESCRIPTION
        "Cisco Firepower aaa:Role:priv managed object property"
    ::= { cfprAaaRoleEntry 11 }

cfprAaaRoleRecTable OBJECT-TYPE
    SYNTAX           SEQUENCE OF CfprAaaRoleRecEntry
    MAX-ACCESS       not-accessible
    STATUS           current
    DESCRIPTION
        "Cisco Firepower aaa:RoleRec managed object table"
    ::= { cfprAaaObjects 59 }

cfprAaaRoleRecEntry OBJECT-TYPE
    SYNTAX           CfprAaaRoleRecEntry
    MAX-ACCESS       not-accessible
    STATUS           current
    DESCRIPTION
        "Entry for the cfprAaaRoleRecTable table."
    INDEX { cfprAaaRoleRecInstanceId }
    ::= { cfprAaaRoleRecTable 1 }

CfprAaaRoleRecEntry ::= SEQUENCE {
    cfprAaaRoleRecInstanceId                                         CfprManagedObjectId,
    cfprAaaRoleRecDn                                                 CfprManagedObjectDn,
    cfprAaaRoleRecRn                                                 SnmpAdminString,
    cfprAaaRoleRecCrntRole                                           SnmpAdminString,
    cfprAaaRoleRecName                                               SnmpAdminString,
    cfprAaaRoleRecPrevRole                                           SnmpAdminString,
    cfprAaaRoleRecTime                                               SnmpAdminString,
    cfprAaaRoleRecUser                                               SnmpAdminString
}

cfprAaaRoleRecInstanceId OBJECT-TYPE
    SYNTAX       CfprManagedObjectId
    MAX-ACCESS   not-accessible
    STATUS       current
    DESCRIPTION
        "Instance identifier of the managed object."
    ::= { cfprAaaRoleRecEntry 1 }

cfprAaaRoleRecDn OBJECT-TYPE
    SYNTAX       CfprManagedObjectDn
    MAX-ACCESS   read-only
    STATUS       current
    DESCRIPTION
        "Cisco Firepower aaa:RoleRec:dn managed object property"
    ::= { cfprAaaRoleRecEntry 2 }

cfprAaaRoleRecRn OBJECT-TYPE
    SYNTAX       SnmpAdminString
    MAX-ACCESS   read-only
    STATUS       current
    DESCRIPTION
        "Cisco Firepower aaa:RoleRec:rn managed object property"
    ::= { cfprAaaRoleRecEntry 3 }

cfprAaaRoleRecCrntRole OBJECT-TYPE
    SYNTAX       SnmpAdminString
    MAX-ACCESS   read-only
    STATUS       current
    DESCRIPTION
        "Cisco Firepower aaa:RoleRec:crntRole managed object property"
    ::= { cfprAaaRoleRecEntry 4 }

cfprAaaRoleRecName OBJECT-TYPE
    SYNTAX       SnmpAdminString
    MAX-ACCESS   read-only
    STATUS       current
    DESCRIPTION
        "Cisco Firepower aaa:RoleRec:name managed object property"
    ::= { cfprAaaRoleRecEntry 5 }

cfprAaaRoleRecPrevRole OBJECT-TYPE
    SYNTAX       SnmpAdminString
    MAX-ACCESS   read-only
    STATUS       current
    DESCRIPTION
        "Cisco Firepower aaa:RoleRec:prevRole managed object property"
    ::= { cfprAaaRoleRecEntry 6 }

cfprAaaRoleRecTime OBJECT-TYPE
    SYNTAX       SnmpAdminString
    MAX-ACCESS   read-only
    STATUS       current
    DESCRIPTION
        "Cisco Firepower aaa:RoleRec:time managed object property"
    ::= { cfprAaaRoleRecEntry 7 }

cfprAaaRoleRecUser OBJECT-TYPE
    SYNTAX       SnmpAdminString
    MAX-ACCESS   read-only
    STATUS       current
    DESCRIPTION
        "Cisco Firepower aaa:RoleRec:user managed object property"
    ::= { cfprAaaRoleRecEntry 8 }

cfprAaaSessionTable OBJECT-TYPE
    SYNTAX           SEQUENCE OF CfprAaaSessionEntry
    MAX-ACCESS       not-accessible
    STATUS           current
    DESCRIPTION
        "Cisco Firepower aaa:Session managed object table"
    ::= { cfprAaaObjects 39 }

cfprAaaSessionEntry OBJECT-TYPE
    SYNTAX           CfprAaaSessionEntry
    MAX-ACCESS       not-accessible
    STATUS           current
    DESCRIPTION
        "Entry for the cfprAaaSessionTable table."
    INDEX { cfprAaaSessionInstanceId }
    ::= { cfprAaaSessionTable 1 }

CfprAaaSessionEntry ::= SEQUENCE {
    cfprAaaSessionInstanceId                                         CfprManagedObjectId,
    cfprAaaSessionDn                                                 CfprManagedObjectDn,
    cfprAaaSessionRn                                                 SnmpAdminString,
    cfprAaaSessionHost                                               SnmpAdminString,
    cfprAaaSessionId                                                 SnmpAdminString,
    cfprAaaSessionIntDel                                             TruthValue,
    cfprAaaSessionLoginTime                                          DateAndTime,
    cfprAaaSessionPid                                                Gauge32,
    cfprAaaSessionRefreshPeriod                                      Gauge32,
    cfprAaaSessionSessionTimeout                                     Gauge32,
    cfprAaaSessionSwitchId                                           CfprNetworkSwitchId,
    cfprAaaSessionTerm                                               SnmpAdminString,
    cfprAaaSessionUi                                                 CfprAaaUserInterface,
    cfprAaaSessionUser                                               SnmpAdminString,
    cfprAaaSessionAbsoluteSessionTimeout                             Gauge32
}

cfprAaaSessionInstanceId OBJECT-TYPE
    SYNTAX       CfprManagedObjectId
    MAX-ACCESS   not-accessible
    STATUS       current
    DESCRIPTION
        "Instance identifier of the managed object."
    ::= { cfprAaaSessionEntry 1 }

cfprAaaSessionDn OBJECT-TYPE
    SYNTAX       CfprManagedObjectDn
    MAX-ACCESS   read-only
    STATUS       current
    DESCRIPTION
        "Cisco Firepower aaa:Session:dn managed object property"
    ::= { cfprAaaSessionEntry 2 }

cfprAaaSessionRn OBJECT-TYPE
    SYNTAX       SnmpAdminString
    MAX-ACCESS   read-only
    STATUS       current
    DESCRIPTION
        "Cisco Firepower aaa:Session:rn managed object property"
    ::= { cfprAaaSessionEntry 3 }

cfprAaaSessionHost OBJECT-TYPE
    SYNTAX       SnmpAdminString
    MAX-ACCESS   read-only
    STATUS       current
    DESCRIPTION
        "Cisco Firepower aaa:Session:host managed object property"
    ::= { cfprAaaSessionEntry 4 }

cfprAaaSessionId OBJECT-TYPE
    SYNTAX       SnmpAdminString
    MAX-ACCESS   read-only
    STATUS       current
    DESCRIPTION
        "Cisco Firepower aaa:Session:id managed object property"
    ::= { cfprAaaSessionEntry 5 }

cfprAaaSessionIntDel OBJECT-TYPE
    SYNTAX       TruthValue
    MAX-ACCESS   read-only
    STATUS       current
    DESCRIPTION
        "Cisco Firepower aaa:Session:intDel managed object property"
    ::= { cfprAaaSessionEntry 6 }

cfprAaaSessionLoginTime OBJECT-TYPE
    SYNTAX       DateAndTime
    MAX-ACCESS   read-only
    STATUS       current
    DESCRIPTION
        "Cisco Firepower aaa:Session:loginTime managed object property"
    ::= { cfprAaaSessionEntry 7 }

cfprAaaSessionPid OBJECT-TYPE
    SYNTAX       Gauge32
    MAX-ACCESS   read-only
    STATUS       current
    DESCRIPTION
        "Cisco Firepower aaa:Session:pid managed object property"
    ::= { cfprAaaSessionEntry 8 }

cfprAaaSessionRefreshPeriod OBJECT-TYPE
    SYNTAX       Gauge32
    MAX-ACCESS   read-only
    STATUS       current
    DESCRIPTION
        "Cisco Firepower aaa:Session:refreshPeriod managed
        object property"
    ::= { cfprAaaSessionEntry 9 }

cfprAaaSessionSessionTimeout OBJECT-TYPE
    SYNTAX       Gauge32
    MAX-ACCESS   read-only
    STATUS       current
    DESCRIPTION
        "Cisco Firepower aaa:Session:sessionTimeout managed
        object property"
    ::= { cfprAaaSessionEntry 10 }

cfprAaaSessionSwitchId OBJECT-TYPE
    SYNTAX       CfprNetworkSwitchId
    MAX-ACCESS   read-only
    STATUS       current
    DESCRIPTION
        "Cisco Firepower aaa:Session:switchId managed object property"
    ::= { cfprAaaSessionEntry 11 }

cfprAaaSessionTerm OBJECT-TYPE
    SYNTAX       SnmpAdminString
    MAX-ACCESS   read-only
    STATUS       current
    DESCRIPTION
        "Cisco Firepower aaa:Session:term managed object property"
    ::= { cfprAaaSessionEntry 12 }

cfprAaaSessionUi OBJECT-TYPE
    SYNTAX       CfprAaaUserInterface
    MAX-ACCESS   read-only
    STATUS       current
    DESCRIPTION
        "Cisco Firepower aaa:Session:ui managed object property"
    ::= { cfprAaaSessionEntry 13 }

cfprAaaSessionUser OBJECT-TYPE
    SYNTAX       SnmpAdminString
    MAX-ACCESS   read-only
    STATUS       current
    DESCRIPTION
        "Cisco Firepower aaa:Session:user managed object property"
    ::= { cfprAaaSessionEntry 14 }

cfprAaaSessionAbsoluteSessionTimeout OBJECT-TYPE
    SYNTAX       Gauge32
    MAX-ACCESS   read-only
    STATUS       current
    DESCRIPTION
        "Cisco Firepower aaa:Session:absoluteSessionTimeout
        managed object property"
    ::= { cfprAaaSessionEntry 15 }

cfprAaaSessionInfoTable OBJECT-TYPE
    SYNTAX           SEQUENCE OF CfprAaaSessionInfoEntry
    MAX-ACCESS       not-accessible
    STATUS           current
    DESCRIPTION
        "Cisco Firepower aaa:SessionInfo managed object table"
    ::= { cfprAaaObjects 40 }

cfprAaaSessionInfoEntry OBJECT-TYPE
    SYNTAX           CfprAaaSessionInfoEntry
    MAX-ACCESS       not-accessible
    STATUS           current
    DESCRIPTION
        "Entry for the cfprAaaSessionInfoTable table."
    INDEX { cfprAaaSessionInfoInstanceId }
    ::= { cfprAaaSessionInfoTable 1 }

CfprAaaSessionInfoEntry ::= SEQUENCE {
    cfprAaaSessionInfoInstanceId                                     CfprManagedObjectId,
    cfprAaaSessionInfoDn                                             CfprManagedObjectDn,
    cfprAaaSessionInfoRn                                             SnmpAdminString,
    cfprAaaSessionInfoAddress                                        SnmpAdminString,
    cfprAaaSessionInfoDestIp                                         SnmpAdminString,
    cfprAaaSessionInfoEtime                                          DateAndTime,
    cfprAaaSessionInfoId                                             SnmpAdminString,
    cfprAaaSessionInfoPriv                                           SnmpAdminString,
    cfprAaaSessionInfoType                                           CfprAaaCimcSessionType,
    cfprAaaSessionInfoUser                                           SnmpAdminString,
    cfprAaaSessionInfoUserType                                       CfprAaaSession
}

cfprAaaSessionInfoInstanceId OBJECT-TYPE
    SYNTAX       CfprManagedObjectId
    MAX-ACCESS   not-accessible
    STATUS       current
    DESCRIPTION
        "Instance identifier of the managed object."
    ::= { cfprAaaSessionInfoEntry 1 }

cfprAaaSessionInfoDn OBJECT-TYPE
    SYNTAX       CfprManagedObjectDn
    MAX-ACCESS   read-only
    STATUS       current
    DESCRIPTION
        "Cisco Firepower aaa:SessionInfo:dn managed object property"
    ::= { cfprAaaSessionInfoEntry 2 }

cfprAaaSessionInfoRn OBJECT-TYPE
    SYNTAX       SnmpAdminString
    MAX-ACCESS   read-only
    STATUS       current
    DESCRIPTION
        "Cisco Firepower aaa:SessionInfo:rn managed object property"
    ::= { cfprAaaSessionInfoEntry 3 }

cfprAaaSessionInfoAddress OBJECT-TYPE
    SYNTAX       SnmpAdminString
    MAX-ACCESS   read-only
    STATUS       current
    DESCRIPTION
        "Cisco Firepower aaa:SessionInfo:address managed object property"
    ::= { cfprAaaSessionInfoEntry 4 }

cfprAaaSessionInfoDestIp OBJECT-TYPE
    SYNTAX       SnmpAdminString
    MAX-ACCESS   read-only
    STATUS       current
    DESCRIPTION
        "Cisco Firepower aaa:SessionInfo:destIp managed object property"
    ::= { cfprAaaSessionInfoEntry 5 }

cfprAaaSessionInfoEtime OBJECT-TYPE
    SYNTAX       DateAndTime
    MAX-ACCESS   read-only
    STATUS       current
    DESCRIPTION
        "Cisco Firepower aaa:SessionInfo:etime managed object property"
    ::= { cfprAaaSessionInfoEntry 6 }

cfprAaaSessionInfoId OBJECT-TYPE
    SYNTAX       SnmpAdminString
    MAX-ACCESS   read-only
    STATUS       current
    DESCRIPTION
        "Cisco Firepower aaa:SessionInfo:id managed object property"
    ::= { cfprAaaSessionInfoEntry 7 }

cfprAaaSessionInfoPriv OBJECT-TYPE
    SYNTAX       SnmpAdminString
    MAX-ACCESS   read-only
    STATUS       current
    DESCRIPTION
        "Cisco Firepower aaa:SessionInfo:priv managed object property"
    ::= { cfprAaaSessionInfoEntry 8 }

cfprAaaSessionInfoType OBJECT-TYPE
    SYNTAX       CfprAaaCimcSessionType
    MAX-ACCESS   read-only
    STATUS       current
    DESCRIPTION
        "Cisco Firepower aaa:SessionInfo:type managed object property"
    ::= { cfprAaaSessionInfoEntry 9 }

cfprAaaSessionInfoUser OBJECT-TYPE
    SYNTAX       SnmpAdminString
    MAX-ACCESS   read-only
    STATUS       current
    DESCRIPTION
        "Cisco Firepower aaa:SessionInfo:user managed object property"
    ::= { cfprAaaSessionInfoEntry 10 }

cfprAaaSessionInfoUserType OBJECT-TYPE
    SYNTAX       CfprAaaSession
    MAX-ACCESS   read-only
    STATUS       current
    DESCRIPTION
        "Cisco Firepower aaa:SessionInfo:userType managed object property"
    ::= { cfprAaaSessionInfoEntry 11 }

cfprAaaSessionInfoTableTable OBJECT-TYPE
    SYNTAX           SEQUENCE OF CfprAaaSessionInfoTableEntry
    MAX-ACCESS       not-accessible
    STATUS           current
    DESCRIPTION
        "Cisco Firepower aaa:SessionInfoTable managed object table"
    ::= { cfprAaaObjects 41 }

cfprAaaSessionInfoTableEntry OBJECT-TYPE
    SYNTAX           CfprAaaSessionInfoTableEntry
    MAX-ACCESS       not-accessible
    STATUS           current
    DESCRIPTION
        "Entry for the cfprAaaSessionInfoTableTable table."
    INDEX { cfprAaaSessionInfoTableInstanceId }
    ::= { cfprAaaSessionInfoTableTable 1 }

CfprAaaSessionInfoTableEntry ::= SEQUENCE {
    cfprAaaSessionInfoTableInstanceId                                CfprManagedObjectId,
    cfprAaaSessionInfoTableDn                                        CfprManagedObjectDn,
    cfprAaaSessionInfoTableRn                                        SnmpAdminString
}

cfprAaaSessionInfoTableInstanceId OBJECT-TYPE
    SYNTAX       CfprManagedObjectId
    MAX-ACCESS   not-accessible
    STATUS       current
    DESCRIPTION
        "Instance identifier of the managed object."
    ::= { cfprAaaSessionInfoTableEntry 1 }

cfprAaaSessionInfoTableDn OBJECT-TYPE
    SYNTAX       CfprManagedObjectDn
    MAX-ACCESS   read-only
    STATUS       current
    DESCRIPTION
        "Cisco Firepower aaa:SessionInfoTable:dn managed object property"
    ::= { cfprAaaSessionInfoTableEntry 2 }

cfprAaaSessionInfoTableRn OBJECT-TYPE
    SYNTAX       SnmpAdminString
    MAX-ACCESS   read-only
    STATUS       current
    DESCRIPTION
        "Cisco Firepower aaa:SessionInfoTable:rn managed object property"
    ::= { cfprAaaSessionInfoTableEntry 3 }

cfprAaaSessionLRTable OBJECT-TYPE
    SYNTAX           SEQUENCE OF CfprAaaSessionLREntry
    MAX-ACCESS       not-accessible
    STATUS           current
    DESCRIPTION
        "Cisco Firepower aaa:SessionLR managed object table"
    ::= { cfprAaaObjects 42 }

cfprAaaSessionLREntry OBJECT-TYPE
    SYNTAX           CfprAaaSessionLREntry
    MAX-ACCESS       not-accessible
    STATUS           current
    DESCRIPTION
        "Entry for the cfprAaaSessionLRTable table."
    INDEX { cfprAaaSessionLRInstanceId }
    ::= { cfprAaaSessionLRTable 1 }

CfprAaaSessionLREntry ::= SEQUENCE {
    cfprAaaSessionLRInstanceId                                       CfprManagedObjectId,
    cfprAaaSessionLRDn                                               CfprManagedObjectDn,
    cfprAaaSessionLRRn                                               SnmpAdminString,
    cfprAaaSessionLRAffected                                         SnmpAdminString,
    cfprAaaSessionLRCause                                            CfprConditionCause,
    cfprAaaSessionLRChangeSet                                        SnmpAdminString,
    cfprAaaSessionLRCode                                             CfprConditionCode,
    cfprAaaSessionLRCreated                                          DateAndTime,
    cfprAaaSessionLRDescr                                            SnmpAdminString,
    cfprAaaSessionLRId                                               Gauge32,
    cfprAaaSessionLRInd                                              CfprConditionActionIndicator,
    cfprAaaSessionLRSessionId                                        SnmpAdminString,
    cfprAaaSessionLRSeverity                                         CfprConditionSeverity,
    cfprAaaSessionLRTrig                                             Gauge32,
    cfprAaaSessionLRTxId                                             Unsigned64,
    cfprAaaSessionLRUser                                             SnmpAdminString
}

cfprAaaSessionLRInstanceId OBJECT-TYPE
    SYNTAX       CfprManagedObjectId
    MAX-ACCESS   not-accessible
    STATUS       current
    DESCRIPTION
        "Instance identifier of the managed object."
    ::= { cfprAaaSessionLREntry 1 }

cfprAaaSessionLRDn OBJECT-TYPE
    SYNTAX       CfprManagedObjectDn
    MAX-ACCESS   read-only
    STATUS       current
    DESCRIPTION
        "Cisco Firepower aaa:SessionLR:dn managed object property"
    ::= { cfprAaaSessionLREntry 2 }

cfprAaaSessionLRRn OBJECT-TYPE
    SYNTAX       SnmpAdminString
    MAX-ACCESS   read-only
    STATUS       current
    DESCRIPTION
        "Cisco Firepower aaa:SessionLR:rn managed object property"
    ::= { cfprAaaSessionLREntry 3 }

cfprAaaSessionLRAffected OBJECT-TYPE
    SYNTAX       SnmpAdminString
    MAX-ACCESS   read-only
    STATUS       current
    DESCRIPTION
        "Cisco Firepower aaa:SessionLR:affected managed object property"
    ::= { cfprAaaSessionLREntry 4 }

cfprAaaSessionLRCause OBJECT-TYPE
    SYNTAX       CfprConditionCause
    MAX-ACCESS   read-only
    STATUS       current
    DESCRIPTION
        "Cisco Firepower aaa:SessionLR:cause managed object property"
    ::= { cfprAaaSessionLREntry 5 }

cfprAaaSessionLRChangeSet OBJECT-TYPE
    SYNTAX       SnmpAdminString
    MAX-ACCESS   read-only
    STATUS       current
    DESCRIPTION
        "Cisco Firepower aaa:SessionLR:changeSet managed object property"
    ::= { cfprAaaSessionLREntry 6 }

cfprAaaSessionLRCode OBJECT-TYPE
    SYNTAX       CfprConditionCode
    MAX-ACCESS   read-only
    STATUS       current
    DESCRIPTION
        "Cisco Firepower aaa:SessionLR:code managed object property"
    ::= { cfprAaaSessionLREntry 7 }

cfprAaaSessionLRCreated OBJECT-TYPE
    SYNTAX       DateAndTime
    MAX-ACCESS   read-only
    STATUS       current
    DESCRIPTION
        "Cisco Firepower aaa:SessionLR:created managed object property"
    ::= { cfprAaaSessionLREntry 8 }

cfprAaaSessionLRDescr OBJECT-TYPE
    SYNTAX       SnmpAdminString
    MAX-ACCESS   read-only
    STATUS       current
    DESCRIPTION
        "Cisco Firepower aaa:SessionLR:descr managed object property"
    ::= { cfprAaaSessionLREntry 9 }

cfprAaaSessionLRId OBJECT-TYPE
    SYNTAX       Gauge32
    MAX-ACCESS   read-only
    STATUS       current
    DESCRIPTION
        "Cisco Firepower aaa:SessionLR:id managed object property"
    ::= { cfprAaaSessionLREntry 10 }

cfprAaaSessionLRInd OBJECT-TYPE
    SYNTAX       CfprConditionActionIndicator
    MAX-ACCESS   read-only
    STATUS       current
    DESCRIPTION
        "Cisco Firepower aaa:SessionLR:ind managed object property"
    ::= { cfprAaaSessionLREntry 11 }

cfprAaaSessionLRSessionId OBJECT-TYPE
    SYNTAX       SnmpAdminString
    MAX-ACCESS   read-only
    STATUS       current
    DESCRIPTION
        "Cisco Firepower aaa:SessionLR:sessionId managed object property"
    ::= { cfprAaaSessionLREntry 12 }

cfprAaaSessionLRSeverity OBJECT-TYPE
    SYNTAX       CfprConditionSeverity
    MAX-ACCESS   read-only
    STATUS       current
    DESCRIPTION
        "Cisco Firepower aaa:SessionLR:severity managed object property"
    ::= { cfprAaaSessionLREntry 13 }

cfprAaaSessionLRTrig OBJECT-TYPE
    SYNTAX       Gauge32
    MAX-ACCESS   read-only
    STATUS       current
    DESCRIPTION
        "Cisco Firepower aaa:SessionLR:trig managed object property"
    ::= { cfprAaaSessionLREntry 14 }

cfprAaaSessionLRTxId OBJECT-TYPE
    SYNTAX       Unsigned64
    MAX-ACCESS   read-only
    STATUS       current
    DESCRIPTION
        "Cisco Firepower aaa:SessionLR:txId managed object property"
    ::= { cfprAaaSessionLREntry 15 }

cfprAaaSessionLRUser OBJECT-TYPE
    SYNTAX       SnmpAdminString
    MAX-ACCESS   read-only
    STATUS       current
    DESCRIPTION
        "Cisco Firepower aaa:SessionLR:user managed object property"
    ::= { cfprAaaSessionLREntry 16 }

cfprAaaShellLoginTable OBJECT-TYPE
    SYNTAX           SEQUENCE OF CfprAaaShellLoginEntry
    MAX-ACCESS       not-accessible
    STATUS           current
    DESCRIPTION
        "Cisco Firepower aaa:ShellLogin managed object table"
    ::= { cfprAaaObjects 43 }

cfprAaaShellLoginEntry OBJECT-TYPE
    SYNTAX           CfprAaaShellLoginEntry
    MAX-ACCESS       not-accessible
    STATUS           current
    DESCRIPTION
        "Entry for the cfprAaaShellLoginTable table."
    INDEX { cfprAaaShellLoginInstanceId }
    ::= { cfprAaaShellLoginTable 1 }

CfprAaaShellLoginEntry ::= SEQUENCE {
    cfprAaaShellLoginInstanceId                                      CfprManagedObjectId,
    cfprAaaShellLoginDn                                              CfprManagedObjectDn,
    cfprAaaShellLoginRn                                              SnmpAdminString,
    cfprAaaShellLoginDescr                                           SnmpAdminString,
    cfprAaaShellLoginId                                              SnmpAdminString,
    cfprAaaShellLoginIntId                                           SnmpAdminString,
    cfprAaaShellLoginLocalHost                                       SnmpAdminString,
    cfprAaaShellLoginName                                            SnmpAdminString,
    cfprAaaShellLoginPolicyLevel                                     Gauge32,
    cfprAaaShellLoginPolicyOwner                                     CfprPolicyPolicyOwner,
    cfprAaaShellLoginRemoteHost                                      SnmpAdminString,
    cfprAaaShellLoginSession                                         CfprAaaSession,
    cfprAaaShellLoginSwitchId                                        CfprNetworkSwitchId
}

cfprAaaShellLoginInstanceId OBJECT-TYPE
    SYNTAX       CfprManagedObjectId
    MAX-ACCESS   not-accessible
    STATUS       current
    DESCRIPTION
        "Instance identifier of the managed object."
    ::= { cfprAaaShellLoginEntry 1 }

cfprAaaShellLoginDn OBJECT-TYPE
    SYNTAX       CfprManagedObjectDn
    MAX-ACCESS   read-only
    STATUS       current
    DESCRIPTION
        "Cisco Firepower aaa:ShellLogin:dn managed object property"
    ::= { cfprAaaShellLoginEntry 2 }

cfprAaaShellLoginRn OBJECT-TYPE
    SYNTAX       SnmpAdminString
    MAX-ACCESS   read-only
    STATUS       current
    DESCRIPTION
        "Cisco Firepower aaa:ShellLogin:rn managed object property"
    ::= { cfprAaaShellLoginEntry 3 }

cfprAaaShellLoginDescr OBJECT-TYPE
    SYNTAX       SnmpAdminString
    MAX-ACCESS   read-only
    STATUS       current
    DESCRIPTION
        "Cisco Firepower aaa:ShellLogin:descr managed object property"
    ::= { cfprAaaShellLoginEntry 4 }

cfprAaaShellLoginId OBJECT-TYPE
    SYNTAX       SnmpAdminString
    MAX-ACCESS   read-only
    STATUS       current
    DESCRIPTION
        "Cisco Firepower aaa:ShellLogin:id managed object property"
    ::= { cfprAaaShellLoginEntry 5 }

cfprAaaShellLoginIntId OBJECT-TYPE
    SYNTAX       SnmpAdminString
    MAX-ACCESS   read-only
    STATUS       current
    DESCRIPTION
        "Cisco Firepower aaa:ShellLogin:intId managed object property"
    ::= { cfprAaaShellLoginEntry 6 }

cfprAaaShellLoginLocalHost OBJECT-TYPE
    SYNTAX       SnmpAdminString
    MAX-ACCESS   read-only
    STATUS       current
    DESCRIPTION
        "Cisco Firepower aaa:ShellLogin:localHost managed object property"
    ::= { cfprAaaShellLoginEntry 7 }

cfprAaaShellLoginName OBJECT-TYPE
    SYNTAX       SnmpAdminString
    MAX-ACCESS   read-only
    STATUS       current
    DESCRIPTION
        "Cisco Firepower aaa:ShellLogin:name managed object property"
    ::= { cfprAaaShellLoginEntry 8 }

cfprAaaShellLoginPolicyLevel OBJECT-TYPE
    SYNTAX       Gauge32
    MAX-ACCESS   read-only
    STATUS       current
    DESCRIPTION
        "Cisco Firepower aaa:ShellLogin:policyLevel managed
        object property"
    ::= { cfprAaaShellLoginEntry 9 }

cfprAaaShellLoginPolicyOwner OBJECT-TYPE
    SYNTAX       CfprPolicyPolicyOwner
    MAX-ACCESS   read-only
    STATUS       current
    DESCRIPTION
        "Cisco Firepower aaa:ShellLogin:policyOwner managed
        object property"
    ::= { cfprAaaShellLoginEntry 10 }

cfprAaaShellLoginRemoteHost OBJECT-TYPE
    SYNTAX       SnmpAdminString
    MAX-ACCESS   read-only
    STATUS       current
    DESCRIPTION
        "Cisco Firepower aaa:ShellLogin:remoteHost managed
        object property"
    ::= { cfprAaaShellLoginEntry 11 }

cfprAaaShellLoginSession OBJECT-TYPE
    SYNTAX       CfprAaaSession
    MAX-ACCESS   read-only
    STATUS       current
    DESCRIPTION
        "Cisco Firepower aaa:ShellLogin:session managed object property"
    ::= { cfprAaaShellLoginEntry 12 }

cfprAaaShellLoginSwitchId OBJECT-TYPE
    SYNTAX       CfprNetworkSwitchId
    MAX-ACCESS   read-only
    STATUS       current
    DESCRIPTION
        "Cisco Firepower aaa:ShellLogin:switchId managed object property"
    ::= { cfprAaaShellLoginEntry 13 }

cfprAaaSshAuthTable OBJECT-TYPE
    SYNTAX           SEQUENCE OF CfprAaaSshAuthEntry
    MAX-ACCESS       not-accessible
    STATUS           current
    DESCRIPTION
        "Cisco Firepower aaa:SshAuth managed object table"
    ::= { cfprAaaObjects 44 }

cfprAaaSshAuthEntry OBJECT-TYPE
    SYNTAX           CfprAaaSshAuthEntry
    MAX-ACCESS       not-accessible
    STATUS           current
    DESCRIPTION
        "Entry for the cfprAaaSshAuthTable table."
    INDEX { cfprAaaSshAuthInstanceId }
    ::= { cfprAaaSshAuthTable 1 }

CfprAaaSshAuthEntry ::= SEQUENCE {
    cfprAaaSshAuthInstanceId                                         CfprManagedObjectId,
    cfprAaaSshAuthDn                                                 CfprManagedObjectDn,
    cfprAaaSshAuthRn                                                 SnmpAdminString,
    cfprAaaSshAuthData                                               SnmpAdminString,
    cfprAaaSshAuthOldStrType                                         CfprAaaSshStr,
    cfprAaaSshAuthStrType                                            CfprAaaSshStr
}

cfprAaaSshAuthInstanceId OBJECT-TYPE
    SYNTAX       CfprManagedObjectId
    MAX-ACCESS   not-accessible
    STATUS       current
    DESCRIPTION
        "Instance identifier of the managed object."
    ::= { cfprAaaSshAuthEntry 1 }

cfprAaaSshAuthDn OBJECT-TYPE
    SYNTAX       CfprManagedObjectDn
    MAX-ACCESS   read-only
    STATUS       current
    DESCRIPTION
        "Cisco Firepower aaa:SshAuth:dn managed object property"
    ::= { cfprAaaSshAuthEntry 2 }

cfprAaaSshAuthRn OBJECT-TYPE
    SYNTAX       SnmpAdminString
    MAX-ACCESS   read-only
    STATUS       current
    DESCRIPTION
        "Cisco Firepower aaa:SshAuth:rn managed object property"
    ::= { cfprAaaSshAuthEntry 3 }

cfprAaaSshAuthData OBJECT-TYPE
    SYNTAX       SnmpAdminString
    MAX-ACCESS   read-only
    STATUS       current
    DESCRIPTION
        "Cisco Firepower aaa:SshAuth:data managed object property"
    ::= { cfprAaaSshAuthEntry 4 }

cfprAaaSshAuthOldStrType OBJECT-TYPE
    SYNTAX       CfprAaaSshStr
    MAX-ACCESS   read-only
    STATUS       current
    DESCRIPTION
        "Cisco Firepower aaa:SshAuth:oldStrType managed object property"
    ::= { cfprAaaSshAuthEntry 5 }

cfprAaaSshAuthStrType OBJECT-TYPE
    SYNTAX       CfprAaaSshStr
    MAX-ACCESS   read-only
    STATUS       current
    DESCRIPTION
        "Cisco Firepower aaa:SshAuth:strType managed object property"
    ::= { cfprAaaSshAuthEntry 6 }

cfprAaaTacacsPlusEpTable OBJECT-TYPE
    SYNTAX           SEQUENCE OF CfprAaaTacacsPlusEpEntry
    MAX-ACCESS       not-accessible
    STATUS           current
    DESCRIPTION
        "Cisco Firepower aaa:TacacsPlusEp managed object table"
    ::= { cfprAaaObjects 45 }

cfprAaaTacacsPlusEpEntry OBJECT-TYPE
    SYNTAX           CfprAaaTacacsPlusEpEntry
    MAX-ACCESS       not-accessible
    STATUS           current
    DESCRIPTION
        "Entry for the cfprAaaTacacsPlusEpTable table."
    INDEX { cfprAaaTacacsPlusEpInstanceId }
    ::= { cfprAaaTacacsPlusEpTable 1 }

CfprAaaTacacsPlusEpEntry ::= SEQUENCE {
    cfprAaaTacacsPlusEpInstanceId                                    CfprManagedObjectId,
    cfprAaaTacacsPlusEpDn                                            CfprManagedObjectDn,
    cfprAaaTacacsPlusEpRn                                            SnmpAdminString,
    cfprAaaTacacsPlusEpDescr                                         SnmpAdminString,
    cfprAaaTacacsPlusEpFsmDescr                                      SnmpAdminString,
    cfprAaaTacacsPlusEpFsmPrev                                       SnmpAdminString,
    cfprAaaTacacsPlusEpFsmProgr                                      Gauge32,
    cfprAaaTacacsPlusEpFsmRmtInvErrCode                              Gauge32,
    cfprAaaTacacsPlusEpFsmRmtInvErrDescr                             SnmpAdminString,
    cfprAaaTacacsPlusEpFsmRmtInvRslt                                 CfprConditionRemoteInvRslt,
    cfprAaaTacacsPlusEpFsmStageDescr                                 SnmpAdminString,
    cfprAaaTacacsPlusEpFsmStamp                                      DateAndTime,
    cfprAaaTacacsPlusEpFsmStatus                                     SnmpAdminString,
    cfprAaaTacacsPlusEpFsmTry                                        Gauge32,
    cfprAaaTacacsPlusEpIntId                                         SnmpAdminString,
    cfprAaaTacacsPlusEpName                                          SnmpAdminString,
    cfprAaaTacacsPlusEpPolicyLevel                                   Gauge32,
    cfprAaaTacacsPlusEpPolicyOwner                                   CfprPolicyPolicyOwner,
    cfprAaaTacacsPlusEpRetries                                       Gauge32,
    cfprAaaTacacsPlusEpTimeout                                       Gauge32
}

cfprAaaTacacsPlusEpInstanceId OBJECT-TYPE
    SYNTAX       CfprManagedObjectId
    MAX-ACCESS   not-accessible
    STATUS       current
    DESCRIPTION
        "Instance identifier of the managed object."
    ::= { cfprAaaTacacsPlusEpEntry 1 }

cfprAaaTacacsPlusEpDn OBJECT-TYPE
    SYNTAX       CfprManagedObjectDn
    MAX-ACCESS   read-only
    STATUS       current
    DESCRIPTION
        "Cisco Firepower aaa:TacacsPlusEp:dn managed object property"
    ::= { cfprAaaTacacsPlusEpEntry 2 }

cfprAaaTacacsPlusEpRn OBJECT-TYPE
    SYNTAX       SnmpAdminString
    MAX-ACCESS   read-only
    STATUS       current
    DESCRIPTION
        "Cisco Firepower aaa:TacacsPlusEp:rn managed object property"
    ::= { cfprAaaTacacsPlusEpEntry 3 }

cfprAaaTacacsPlusEpDescr OBJECT-TYPE
    SYNTAX       SnmpAdminString
    MAX-ACCESS   read-only
    STATUS       current
    DESCRIPTION
        "Cisco Firepower aaa:TacacsPlusEp:descr managed object property"
    ::= { cfprAaaTacacsPlusEpEntry 4 }

cfprAaaTacacsPlusEpFsmDescr OBJECT-TYPE
    SYNTAX       SnmpAdminString
    MAX-ACCESS   read-only
    STATUS       current
    DESCRIPTION
        "Cisco Firepower aaa:TacacsPlusEp:fsmDescr managed
        object property"
    ::= { cfprAaaTacacsPlusEpEntry 5 }

cfprAaaTacacsPlusEpFsmPrev OBJECT-TYPE
    SYNTAX       SnmpAdminString
    MAX-ACCESS   read-only
    STATUS       current
    DESCRIPTION
        "Cisco Firepower aaa:TacacsPlusEp:fsmPrev managed object property"
    ::= { cfprAaaTacacsPlusEpEntry 6 }

cfprAaaTacacsPlusEpFsmProgr OBJECT-TYPE
    SYNTAX       Gauge32
    MAX-ACCESS   read-only
    STATUS       current
    DESCRIPTION
        "Cisco Firepower aaa:TacacsPlusEp:fsmProgr managed
        object property"
    ::= { cfprAaaTacacsPlusEpEntry 7 }

cfprAaaTacacsPlusEpFsmRmtInvErrCode OBJECT-TYPE
    SYNTAX       Gauge32
    MAX-ACCESS   read-only
    STATUS       current
    DESCRIPTION
        "Cisco Firepower aaa:TacacsPlusEp:fsmRmtInvErrCode
        managed object property"
    ::= { cfprAaaTacacsPlusEpEntry 8 }

cfprAaaTacacsPlusEpFsmRmtInvErrDescr OBJECT-TYPE
    SYNTAX       SnmpAdminString
    MAX-ACCESS   read-only
    STATUS       current
    DESCRIPTION
        "Cisco Firepower aaa:TacacsPlusEp:fsmRmtInvErrDescr
        managed object property"
    ::= { cfprAaaTacacsPlusEpEntry 9 }

cfprAaaTacacsPlusEpFsmRmtInvRslt OBJECT-TYPE
    SYNTAX       CfprConditionRemoteInvRslt
    MAX-ACCESS   read-only
    STATUS       current
    DESCRIPTION
        "Cisco Firepower aaa:TacacsPlusEp:fsmRmtInvRslt
        managed object property"
    ::= { cfprAaaTacacsPlusEpEntry 10 }

cfprAaaTacacsPlusEpFsmStageDescr OBJECT-TYPE
    SYNTAX       SnmpAdminString
    MAX-ACCESS   read-only
    STATUS       current
    DESCRIPTION
        "Cisco Firepower aaa:TacacsPlusEp:fsmStageDescr
        managed object property"
    ::= { cfprAaaTacacsPlusEpEntry 11 }

cfprAaaTacacsPlusEpFsmStamp OBJECT-TYPE
    SYNTAX       DateAndTime
    MAX-ACCESS   read-only
    STATUS       current
    DESCRIPTION
        "Cisco Firepower aaa:TacacsPlusEp:fsmStamp managed
        object property"
    ::= { cfprAaaTacacsPlusEpEntry 12 }

cfprAaaTacacsPlusEpFsmStatus OBJECT-TYPE
    SYNTAX       SnmpAdminString
    MAX-ACCESS   read-only
    STATUS       current
    DESCRIPTION
        "Cisco Firepower aaa:TacacsPlusEp:fsmStatus managed
        object property"
    ::= { cfprAaaTacacsPlusEpEntry 13 }

cfprAaaTacacsPlusEpFsmTry OBJECT-TYPE
    SYNTAX       Gauge32
    MAX-ACCESS   read-only
    STATUS       current
    DESCRIPTION
        "Cisco Firepower aaa:TacacsPlusEp:fsmTry managed object property"
    ::= { cfprAaaTacacsPlusEpEntry 14 }

cfprAaaTacacsPlusEpIntId OBJECT-TYPE
    SYNTAX       SnmpAdminString
    MAX-ACCESS   read-only
    STATUS       current
    DESCRIPTION
        "Cisco Firepower aaa:TacacsPlusEp:intId managed object property"
    ::= { cfprAaaTacacsPlusEpEntry 15 }

cfprAaaTacacsPlusEpName OBJECT-TYPE
    SYNTAX       SnmpAdminString
    MAX-ACCESS   read-only
    STATUS       current
    DESCRIPTION
        "Cisco Firepower aaa:TacacsPlusEp:name managed object property"
    ::= { cfprAaaTacacsPlusEpEntry 16 }

cfprAaaTacacsPlusEpPolicyLevel OBJECT-TYPE
    SYNTAX       Gauge32
    MAX-ACCESS   read-only
    STATUS       current
    DESCRIPTION
        "Cisco Firepower aaa:TacacsPlusEp:policyLevel managed
        object property"
    ::= { cfprAaaTacacsPlusEpEntry 17 }

cfprAaaTacacsPlusEpPolicyOwner OBJECT-TYPE
    SYNTAX       CfprPolicyPolicyOwner
    MAX-ACCESS   read-only
    STATUS       current
    DESCRIPTION
        "Cisco Firepower aaa:TacacsPlusEp:policyOwner managed
        object property"
    ::= { cfprAaaTacacsPlusEpEntry 18 }

cfprAaaTacacsPlusEpRetries OBJECT-TYPE
    SYNTAX       Gauge32
    MAX-ACCESS   read-only
    STATUS       current
    DESCRIPTION
        "Cisco Firepower aaa:TacacsPlusEp:retries managed object property"
    ::= { cfprAaaTacacsPlusEpEntry 19 }

cfprAaaTacacsPlusEpTimeout OBJECT-TYPE
    SYNTAX       Gauge32
    MAX-ACCESS   read-only
    STATUS       current
    DESCRIPTION
        "Cisco Firepower aaa:TacacsPlusEp:timeout managed object property"
    ::= { cfprAaaTacacsPlusEpEntry 20 }

cfprAaaTacacsPlusEpFsmTable OBJECT-TYPE
    SYNTAX           SEQUENCE OF CfprAaaTacacsPlusEpFsmEntry
    MAX-ACCESS       not-accessible
    STATUS           current
    DESCRIPTION
        "Cisco Firepower aaa:TacacsPlusEpFsm managed object table"
    ::= { cfprAaaObjects 46 }

cfprAaaTacacsPlusEpFsmEntry OBJECT-TYPE
    SYNTAX           CfprAaaTacacsPlusEpFsmEntry
    MAX-ACCESS       not-accessible
    STATUS           current
    DESCRIPTION
        "Entry for the cfprAaaTacacsPlusEpFsmTable table."
    INDEX { cfprAaaTacacsPlusEpFsmInstanceId }
    ::= { cfprAaaTacacsPlusEpFsmTable 1 }

CfprAaaTacacsPlusEpFsmEntry ::= SEQUENCE {
    cfprAaaTacacsPlusEpFsmInstanceId                                 CfprManagedObjectId,
    cfprAaaTacacsPlusEpFsmDn                                         CfprManagedObjectDn,
    cfprAaaTacacsPlusEpFsmRn                                         SnmpAdminString,
    cfprAaaTacacsPlusEpFsmCompletionTime                             DateAndTime,
    cfprAaaTacacsPlusEpFsmCurrentFsm                                 CfprAaaTacacsPlusEpFsmCurrentFsm,
    cfprAaaTacacsPlusEpFsmDescrData                                  SnmpAdminString,
    cfprAaaTacacsPlusEpFsmFsmStatus                                  CfprFsmFsmStageStatus,
    cfprAaaTacacsPlusEpFsmProgress                                   Gauge32,
    cfprAaaTacacsPlusEpFsmRmtErrCode                                 Gauge32,
    cfprAaaTacacsPlusEpFsmRmtErrDescr                                SnmpAdminString,
    cfprAaaTacacsPlusEpFsmRmtRslt                                    CfprConditionRemoteInvRslt
}

cfprAaaTacacsPlusEpFsmInstanceId OBJECT-TYPE
    SYNTAX       CfprManagedObjectId
    MAX-ACCESS   not-accessible
    STATUS       current
    DESCRIPTION
        "Instance identifier of the managed object."
    ::= { cfprAaaTacacsPlusEpFsmEntry 1 }

cfprAaaTacacsPlusEpFsmDn OBJECT-TYPE
    SYNTAX       CfprManagedObjectDn
    MAX-ACCESS   read-only
    STATUS       current
    DESCRIPTION
        "Cisco Firepower aaa:TacacsPlusEpFsm:dn managed object property"
    ::= { cfprAaaTacacsPlusEpFsmEntry 2 }

cfprAaaTacacsPlusEpFsmRn OBJECT-TYPE
    SYNTAX       SnmpAdminString
    MAX-ACCESS   read-only
    STATUS       current
    DESCRIPTION
        "Cisco Firepower aaa:TacacsPlusEpFsm:rn managed object property"
    ::= { cfprAaaTacacsPlusEpFsmEntry 3 }

cfprAaaTacacsPlusEpFsmCompletionTime OBJECT-TYPE
    SYNTAX       DateAndTime
    MAX-ACCESS   read-only
    STATUS       current
    DESCRIPTION
        "Cisco Firepower aaa:TacacsPlusEpFsm:completionTime
        managed object property"
    ::= { cfprAaaTacacsPlusEpFsmEntry 4 }

cfprAaaTacacsPlusEpFsmCurrentFsm OBJECT-TYPE
    SYNTAX       CfprAaaTacacsPlusEpFsmCurrentFsm
    MAX-ACCESS   read-only
    STATUS       current
    DESCRIPTION
        "Cisco Firepower aaa:TacacsPlusEpFsm:currentFsm
        managed object property"
    ::= { cfprAaaTacacsPlusEpFsmEntry 5 }

cfprAaaTacacsPlusEpFsmDescrData OBJECT-TYPE
    SYNTAX       SnmpAdminString
    MAX-ACCESS   read-only
    STATUS       current
    DESCRIPTION
        "Cisco Firepower aaa:TacacsPlusEpFsm:descr managed
        object property"
    ::= { cfprAaaTacacsPlusEpFsmEntry 6 }

cfprAaaTacacsPlusEpFsmFsmStatus OBJECT-TYPE
    SYNTAX       CfprFsmFsmStageStatus
    MAX-ACCESS   read-only
    STATUS       current
    DESCRIPTION
        "Cisco Firepower aaa:TacacsPlusEpFsm:fsmStatus
        managed object property"
    ::= { cfprAaaTacacsPlusEpFsmEntry 7 }

cfprAaaTacacsPlusEpFsmProgress OBJECT-TYPE
    SYNTAX       Gauge32
    MAX-ACCESS   read-only
    STATUS       current
    DESCRIPTION
        "Cisco Firepower aaa:TacacsPlusEpFsm:progress managed
        object property"
    ::= { cfprAaaTacacsPlusEpFsmEntry 8 }

cfprAaaTacacsPlusEpFsmRmtErrCode OBJECT-TYPE
    SYNTAX       Gauge32
    MAX-ACCESS   read-only
    STATUS       current
    DESCRIPTION
        "Cisco Firepower aaa:TacacsPlusEpFsm:rmtErrCode
        managed object property"
    ::= { cfprAaaTacacsPlusEpFsmEntry 9 }

cfprAaaTacacsPlusEpFsmRmtErrDescr OBJECT-TYPE
    SYNTAX       SnmpAdminString
    MAX-ACCESS   read-only
    STATUS       current
    DESCRIPTION
        "Cisco Firepower aaa:TacacsPlusEpFsm:rmtErrDescr
        managed object property"
    ::= { cfprAaaTacacsPlusEpFsmEntry 10 }

cfprAaaTacacsPlusEpFsmRmtRslt OBJECT-TYPE
    SYNTAX       CfprConditionRemoteInvRslt
    MAX-ACCESS   read-only
    STATUS       current
    DESCRIPTION
        "Cisco Firepower aaa:TacacsPlusEpFsm:rmtRslt managed
        object property"
    ::= { cfprAaaTacacsPlusEpFsmEntry 11 }

cfprAaaTacacsPlusEpFsmStageTable OBJECT-TYPE
    SYNTAX           SEQUENCE OF CfprAaaTacacsPlusEpFsmStageEntry
    MAX-ACCESS       not-accessible
    STATUS           current
    DESCRIPTION
        "Cisco Firepower aaa:TacacsPlusEpFsmStage managed object table"
    ::= { cfprAaaObjects 47 }

cfprAaaTacacsPlusEpFsmStageEntry OBJECT-TYPE
    SYNTAX           CfprAaaTacacsPlusEpFsmStageEntry
    MAX-ACCESS       not-accessible
    STATUS           current
    DESCRIPTION
        "Entry for the cfprAaaTacacsPlusEpFsmStageTable table."
    INDEX { cfprAaaTacacsPlusEpFsmStageInstanceId }
    ::= { cfprAaaTacacsPlusEpFsmStageTable 1 }

CfprAaaTacacsPlusEpFsmStageEntry ::= SEQUENCE {
    cfprAaaTacacsPlusEpFsmStageInstanceId                            CfprManagedObjectId,
    cfprAaaTacacsPlusEpFsmStageDn                                    CfprManagedObjectDn,
    cfprAaaTacacsPlusEpFsmStageRn                                    SnmpAdminString,
    cfprAaaTacacsPlusEpFsmStageDescrData                             SnmpAdminString,
    cfprAaaTacacsPlusEpFsmStageLastUpdateTime                        DateAndTime,
    cfprAaaTacacsPlusEpFsmStageName                                  CfprAaaTacacsPlusEpFsmStageName,
    cfprAaaTacacsPlusEpFsmStageOrder                                 Gauge32,
    cfprAaaTacacsPlusEpFsmStageRetry                                 Gauge32,
    cfprAaaTacacsPlusEpFsmStageStageStatus                           CfprFsmFsmStageStatus
}

cfprAaaTacacsPlusEpFsmStageInstanceId OBJECT-TYPE
    SYNTAX       CfprManagedObjectId
    MAX-ACCESS   not-accessible
    STATUS       current
    DESCRIPTION
        "Instance identifier of the managed object."
    ::= { cfprAaaTacacsPlusEpFsmStageEntry 1 }

cfprAaaTacacsPlusEpFsmStageDn OBJECT-TYPE
    SYNTAX       CfprManagedObjectDn
    MAX-ACCESS   read-only
    STATUS       current
    DESCRIPTION
        "Cisco Firepower aaa:TacacsPlusEpFsmStage:dn managed
        object property"
    ::= { cfprAaaTacacsPlusEpFsmStageEntry 2 }

cfprAaaTacacsPlusEpFsmStageRn OBJECT-TYPE
    SYNTAX       SnmpAdminString
    MAX-ACCESS   read-only
    STATUS       current
    DESCRIPTION
        "Cisco Firepower aaa:TacacsPlusEpFsmStage:rn managed
        object property"
    ::= { cfprAaaTacacsPlusEpFsmStageEntry 3 }

cfprAaaTacacsPlusEpFsmStageDescrData OBJECT-TYPE
    SYNTAX       SnmpAdminString
    MAX-ACCESS   read-only
    STATUS       current
    DESCRIPTION
        "Cisco Firepower aaa:TacacsPlusEpFsmStage:descr
        managed object property"
    ::= { cfprAaaTacacsPlusEpFsmStageEntry 4 }

cfprAaaTacacsPlusEpFsmStageLastUpdateTime OBJECT-TYPE
    SYNTAX       DateAndTime
    MAX-ACCESS   read-only
    STATUS       current
    DESCRIPTION
        "Cisco Firepower aaa:TacacsPlusEpFsmStage:lastUpdateTime
        managed object property"
    ::= { cfprAaaTacacsPlusEpFsmStageEntry 5 }

cfprAaaTacacsPlusEpFsmStageName OBJECT-TYPE
    SYNTAX       CfprAaaTacacsPlusEpFsmStageName
    MAX-ACCESS   read-only
    STATUS       current
    DESCRIPTION
        "Cisco Firepower aaa:TacacsPlusEpFsmStage:name
        managed object property"
    ::= { cfprAaaTacacsPlusEpFsmStageEntry 6 }

cfprAaaTacacsPlusEpFsmStageOrder OBJECT-TYPE
    SYNTAX       Gauge32
    MAX-ACCESS   read-only
    STATUS       current
    DESCRIPTION
        "Cisco Firepower aaa:TacacsPlusEpFsmStage:order
        managed object property"
    ::= { cfprAaaTacacsPlusEpFsmStageEntry 7 }

cfprAaaTacacsPlusEpFsmStageRetry OBJECT-TYPE
    SYNTAX       Gauge32
    MAX-ACCESS   read-only
    STATUS       current
    DESCRIPTION
        "Cisco Firepower aaa:TacacsPlusEpFsmStage:retry
        managed object property"
    ::= { cfprAaaTacacsPlusEpFsmStageEntry 8 }

cfprAaaTacacsPlusEpFsmStageStageStatus OBJECT-TYPE
    SYNTAX       CfprFsmFsmStageStatus
    MAX-ACCESS   read-only
    STATUS       current
    DESCRIPTION
        "Cisco Firepower aaa:TacacsPlusEpFsmStage:stageStatus
        managed object property"
    ::= { cfprAaaTacacsPlusEpFsmStageEntry 9 }

cfprAaaTacacsPlusProviderTable OBJECT-TYPE
    SYNTAX           SEQUENCE OF CfprAaaTacacsPlusProviderEntry
    MAX-ACCESS       not-accessible
    STATUS           current
    DESCRIPTION
        "Cisco Firepower aaa:TacacsPlusProvider managed object table"
    ::= { cfprAaaObjects 48 }

cfprAaaTacacsPlusProviderEntry OBJECT-TYPE
    SYNTAX           CfprAaaTacacsPlusProviderEntry
    MAX-ACCESS       not-accessible
    STATUS           current
    DESCRIPTION
        "Entry for the cfprAaaTacacsPlusProviderTable table."
    INDEX { cfprAaaTacacsPlusProviderInstanceId }
    ::= { cfprAaaTacacsPlusProviderTable 1 }

CfprAaaTacacsPlusProviderEntry ::= SEQUENCE {
    cfprAaaTacacsPlusProviderInstanceId                              CfprManagedObjectId,
    cfprAaaTacacsPlusProviderDn                                      CfprManagedObjectDn,
    cfprAaaTacacsPlusProviderRn                                      SnmpAdminString,
    cfprAaaTacacsPlusProviderDescr                                   SnmpAdminString,
    cfprAaaTacacsPlusProviderEncKey                                  SnmpAdminString,
    cfprAaaTacacsPlusProviderKey                                     SnmpAdminString,
    cfprAaaTacacsPlusProviderKeySet                                  TruthValue,
    cfprAaaTacacsPlusProviderName                                    SnmpAdminString,
    cfprAaaTacacsPlusProviderOrder                                   Gauge32,
    cfprAaaTacacsPlusProviderPort                                    Gauge32,
    cfprAaaTacacsPlusProviderRetries                                 Gauge32,
    cfprAaaTacacsPlusProviderTimeout                                 Gauge32
}

cfprAaaTacacsPlusProviderInstanceId OBJECT-TYPE
    SYNTAX       CfprManagedObjectId
    MAX-ACCESS   not-accessible
    STATUS       current
    DESCRIPTION
        "Instance identifier of the managed object."
    ::= { cfprAaaTacacsPlusProviderEntry 1 }

cfprAaaTacacsPlusProviderDn OBJECT-TYPE
    SYNTAX       CfprManagedObjectDn
    MAX-ACCESS   read-only
    STATUS       current
    DESCRIPTION
        "Cisco Firepower aaa:TacacsPlusProvider:dn managed
        object property"
    ::= { cfprAaaTacacsPlusProviderEntry 2 }

cfprAaaTacacsPlusProviderRn OBJECT-TYPE
    SYNTAX       SnmpAdminString
    MAX-ACCESS   read-only
    STATUS       current
    DESCRIPTION
        "Cisco Firepower aaa:TacacsPlusProvider:rn managed
        object property"
    ::= { cfprAaaTacacsPlusProviderEntry 3 }

cfprAaaTacacsPlusProviderDescr OBJECT-TYPE
    SYNTAX       SnmpAdminString
    MAX-ACCESS   read-only
    STATUS       current
    DESCRIPTION
        "Cisco Firepower aaa:TacacsPlusProvider:descr managed
        object property"
    ::= { cfprAaaTacacsPlusProviderEntry 4 }

cfprAaaTacacsPlusProviderEncKey OBJECT-TYPE
    SYNTAX       SnmpAdminString
    MAX-ACCESS   read-only
    STATUS       current
    DESCRIPTION
        "Cisco Firepower aaa:TacacsPlusProvider:encKey
        managed object property"
    ::= { cfprAaaTacacsPlusProviderEntry 5 }

cfprAaaTacacsPlusProviderKey OBJECT-TYPE
    SYNTAX       SnmpAdminString
    MAX-ACCESS   read-only
    STATUS       current
    DESCRIPTION
        "Cisco Firepower aaa:TacacsPlusProvider:key managed
        object property"
    ::= { cfprAaaTacacsPlusProviderEntry 6 }

cfprAaaTacacsPlusProviderKeySet OBJECT-TYPE
    SYNTAX       TruthValue
    MAX-ACCESS   read-only
    STATUS       current
    DESCRIPTION
        "Cisco Firepower aaa:TacacsPlusProvider:keySet
        managed object property"
    ::= { cfprAaaTacacsPlusProviderEntry 7 }

cfprAaaTacacsPlusProviderName OBJECT-TYPE
    SYNTAX       SnmpAdminString
    MAX-ACCESS   read-only
    STATUS       current
    DESCRIPTION
        "Cisco Firepower aaa:TacacsPlusProvider:name managed
        object property"
    ::= { cfprAaaTacacsPlusProviderEntry 8 }

cfprAaaTacacsPlusProviderOrder OBJECT-TYPE
    SYNTAX       Gauge32
    MAX-ACCESS   read-only
    STATUS       current
    DESCRIPTION
        "Cisco Firepower aaa:TacacsPlusProvider:order managed
        object property"
    ::= { cfprAaaTacacsPlusProviderEntry 9 }

cfprAaaTacacsPlusProviderPort OBJECT-TYPE
    SYNTAX       Gauge32
    MAX-ACCESS   read-only
    STATUS       current
    DESCRIPTION
        "Cisco Firepower aaa:TacacsPlusProvider:port managed
        object property"
    ::= { cfprAaaTacacsPlusProviderEntry 10 }

cfprAaaTacacsPlusProviderRetries OBJECT-TYPE
    SYNTAX       Gauge32
    MAX-ACCESS   read-only
    STATUS       current
    DESCRIPTION
        "Cisco Firepower aaa:TacacsPlusProvider:retries
        managed object property"
    ::= { cfprAaaTacacsPlusProviderEntry 11 }

cfprAaaTacacsPlusProviderTimeout OBJECT-TYPE
    SYNTAX       Gauge32
    MAX-ACCESS   read-only
    STATUS       current
    DESCRIPTION
        "Cisco Firepower aaa:TacacsPlusProvider:timeout
        managed object property"
    ::= { cfprAaaTacacsPlusProviderEntry 12 }

cfprAaaUserTable OBJECT-TYPE
    SYNTAX           SEQUENCE OF CfprAaaUserEntry
    MAX-ACCESS       not-accessible
    STATUS           current
    DESCRIPTION
        "Cisco Firepower aaa:User managed object table"
    ::= { cfprAaaObjects 49 }

cfprAaaUserEntry OBJECT-TYPE
    SYNTAX           CfprAaaUserEntry
    MAX-ACCESS       not-accessible
    STATUS           current
    DESCRIPTION
        "Entry for the cfprAaaUserTable table."
    INDEX { cfprAaaUserInstanceId }
    ::= { cfprAaaUserTable 1 }

CfprAaaUserEntry ::= SEQUENCE {
    cfprAaaUserInstanceId                                            CfprManagedObjectId,
    cfprAaaUserDn                                                    CfprManagedObjectDn,
    cfprAaaUserRn                                                    SnmpAdminString,
    cfprAaaUserAccountStatus                                         CfprAaaAccountStatus,
    cfprAaaUserClearPwdHistory                                       CfprAaaClear,
    cfprAaaUserConfigState                                           CfprAaaConfigState,
    cfprAaaUserConfigStatusMessage                                   SnmpAdminString,
    cfprAaaUserDescr                                                 SnmpAdminString,
    cfprAaaUserEmail                                                 SnmpAdminString,
    cfprAaaUserEncPwd                                                SnmpAdminString,
    cfprAaaUserEncPwdSet                                             TruthValue,
    cfprAaaUserExpiration                                            DateAndTime,
    cfprAaaUserExpires                                               TruthValue,
    cfprAaaUserFirstName                                             SnmpAdminString,
    cfprAaaUserLastName                                              SnmpAdminString,
    cfprAaaUserName                                                  SnmpAdminString,
    cfprAaaUserPhone                                                 SnmpAdminString,
    cfprAaaUserPriv                                                  CfprAaaAccess,
    cfprAaaUserPwd                                                   SnmpAdminString,
    cfprAaaUserPwdLifeTime                                           Gauge32,
    cfprAaaUserPwdSet                                                TruthValue,
    cfprAaaUserClearLockStatus                                       CfprAaaClear,
    cfprAaaUserPwdExpDate                                            DateAndTime
}

cfprAaaUserInstanceId OBJECT-TYPE
    SYNTAX       CfprManagedObjectId
    MAX-ACCESS   not-accessible
    STATUS       current
    DESCRIPTION
        "Instance identifier of the managed object."
    ::= { cfprAaaUserEntry 1 }

cfprAaaUserDn OBJECT-TYPE
    SYNTAX       CfprManagedObjectDn
    MAX-ACCESS   read-only
    STATUS       current
    DESCRIPTION
        "Cisco Firepower aaa:User:dn managed object property"
    ::= { cfprAaaUserEntry 2 }

cfprAaaUserRn OBJECT-TYPE
    SYNTAX       SnmpAdminString
    MAX-ACCESS   read-only
    STATUS       current
    DESCRIPTION
        "Cisco Firepower aaa:User:rn managed object property"
    ::= { cfprAaaUserEntry 3 }

cfprAaaUserAccountStatus OBJECT-TYPE
    SYNTAX       CfprAaaAccountStatus
    MAX-ACCESS   read-only
    STATUS       current
    DESCRIPTION
        "Cisco Firepower aaa:User:accountStatus managed object property"
    ::= { cfprAaaUserEntry 4 }

cfprAaaUserClearPwdHistory OBJECT-TYPE
    SYNTAX       CfprAaaClear
    MAX-ACCESS   read-only
    STATUS       current
    DESCRIPTION
        "Cisco Firepower aaa:User:clearPwdHistory managed object property"
    ::= { cfprAaaUserEntry 5 }

cfprAaaUserConfigState OBJECT-TYPE
    SYNTAX       CfprAaaConfigState
    MAX-ACCESS   read-only
    STATUS       current
    DESCRIPTION
        "Cisco Firepower aaa:User:configState managed object property"
    ::= { cfprAaaUserEntry 6 }

cfprAaaUserConfigStatusMessage OBJECT-TYPE
    SYNTAX       SnmpAdminString
    MAX-ACCESS   read-only
    STATUS       current
    DESCRIPTION
        "Cisco Firepower aaa:User:configStatusMessage managed
        object property"
    ::= { cfprAaaUserEntry 7 }

cfprAaaUserDescr OBJECT-TYPE
    SYNTAX       SnmpAdminString
    MAX-ACCESS   read-only
    STATUS       current
    DESCRIPTION
        "Cisco Firepower aaa:User:descr managed object property"
    ::= { cfprAaaUserEntry 8 }

cfprAaaUserEmail OBJECT-TYPE
    SYNTAX       SnmpAdminString
    MAX-ACCESS   read-only
    STATUS       current
    DESCRIPTION
        "Cisco Firepower aaa:User:email managed object property"
    ::= { cfprAaaUserEntry 9 }

cfprAaaUserEncPwd OBJECT-TYPE
    SYNTAX       SnmpAdminString
    MAX-ACCESS   read-only
    STATUS       current
    DESCRIPTION
        "Cisco Firepower aaa:User:encPwd managed object property"
    ::= { cfprAaaUserEntry 10 }

cfprAaaUserEncPwdSet OBJECT-TYPE
    SYNTAX       TruthValue
    MAX-ACCESS   read-only
    STATUS       current
    DESCRIPTION
        "Cisco Firepower aaa:User:encPwdSet managed object property"
    ::= { cfprAaaUserEntry 11 }

cfprAaaUserExpiration OBJECT-TYPE
    SYNTAX       DateAndTime
    MAX-ACCESS   read-only
    STATUS       current
    DESCRIPTION
        "Cisco Firepower aaa:User:expiration managed object property"
    ::= { cfprAaaUserEntry 12 }

cfprAaaUserExpires OBJECT-TYPE
    SYNTAX       TruthValue
    MAX-ACCESS   read-only
    STATUS       current
    DESCRIPTION
        "Cisco Firepower aaa:User:expires managed object property"
    ::= { cfprAaaUserEntry 13 }

cfprAaaUserFirstName OBJECT-TYPE
    SYNTAX       SnmpAdminString
    MAX-ACCESS   read-only
    STATUS       current
    DESCRIPTION
        "Cisco Firepower aaa:User:firstName managed object property"
    ::= { cfprAaaUserEntry 14 }

cfprAaaUserLastName OBJECT-TYPE
    SYNTAX       SnmpAdminString
    MAX-ACCESS   read-only
    STATUS       current
    DESCRIPTION
        "Cisco Firepower aaa:User:lastName managed object property"
    ::= { cfprAaaUserEntry 15 }

cfprAaaUserName OBJECT-TYPE
    SYNTAX       SnmpAdminString
    MAX-ACCESS   read-only
    STATUS       current
    DESCRIPTION
        "Cisco Firepower aaa:User:name managed object property"
    ::= { cfprAaaUserEntry 16 }

cfprAaaUserPhone OBJECT-TYPE
    SYNTAX       SnmpAdminString
    MAX-ACCESS   read-only
    STATUS       current
    DESCRIPTION
        "Cisco Firepower aaa:User:phone managed object property"
    ::= { cfprAaaUserEntry 17 }

cfprAaaUserPriv OBJECT-TYPE
    SYNTAX       CfprAaaAccess
    MAX-ACCESS   read-only
    STATUS       current
    DESCRIPTION
        "Cisco Firepower aaa:User:priv managed object property"
    ::= { cfprAaaUserEntry 18 }

cfprAaaUserPwd OBJECT-TYPE
    SYNTAX       SnmpAdminString
    MAX-ACCESS   read-only
    STATUS       current
    DESCRIPTION
        "Cisco Firepower aaa:User:pwd managed object property"
    ::= { cfprAaaUserEntry 19 }

cfprAaaUserPwdLifeTime OBJECT-TYPE
    SYNTAX       Gauge32
    MAX-ACCESS   read-only
    STATUS       current
    DESCRIPTION
        "Cisco Firepower aaa:User:pwdLifeTime managed object property"
    ::= { cfprAaaUserEntry 20 }

cfprAaaUserPwdSet OBJECT-TYPE
    SYNTAX       TruthValue
    MAX-ACCESS   read-only
    STATUS       current
    DESCRIPTION
        "Cisco Firepower aaa:User:pwdSet managed object property"
    ::= { cfprAaaUserEntry 21 }

cfprAaaUserClearLockStatus OBJECT-TYPE
    SYNTAX       CfprAaaClear
    MAX-ACCESS   read-only
    STATUS       current
    DESCRIPTION
        "Cisco Firepower aaa:User:clearLockStatus managed object property"
    ::= { cfprAaaUserEntry 22 }

cfprAaaUserPwdExpDate OBJECT-TYPE
    SYNTAX       DateAndTime
    MAX-ACCESS   read-only
    STATUS       current
    DESCRIPTION
        "Cisco Firepower aaa:User:pwdExpDate managed object property"
    ::= { cfprAaaUserEntry 23 }

cfprAaaUserDataTable OBJECT-TYPE
    SYNTAX           SEQUENCE OF CfprAaaUserDataEntry
    MAX-ACCESS       not-accessible
    STATUS           current
    DESCRIPTION
        "Cisco Firepower aaa:UserData managed object table"
    ::= { cfprAaaObjects 50 }

cfprAaaUserDataEntry OBJECT-TYPE
    SYNTAX           CfprAaaUserDataEntry
    MAX-ACCESS       not-accessible
    STATUS           current
    DESCRIPTION
        "Entry for the cfprAaaUserDataTable table."
    INDEX { cfprAaaUserDataInstanceId }
    ::= { cfprAaaUserDataTable 1 }

CfprAaaUserDataEntry ::= SEQUENCE {
    cfprAaaUserDataInstanceId                                        CfprManagedObjectId,
    cfprAaaUserDataDn                                                CfprManagedObjectDn,
    cfprAaaUserDataRn                                                SnmpAdminString,
    cfprAaaUserDataDescr                                             SnmpAdminString,
    cfprAaaUserDataIntId                                             SnmpAdminString,
    cfprAaaUserDataName                                              SnmpAdminString,
    cfprAaaUserDataPolicyLevel                                       Gauge32,
    cfprAaaUserDataPolicyOwner                                       CfprPolicyPolicyOwner,
    cfprAaaUserDataPwdChangeCount                                    Gauge32,
    cfprAaaUserDataPwdChangeIntervalBegin                            DateAndTime,
    cfprAaaUserDataPwdChangedDate                                    DateAndTime,
    cfprAaaUserDataPwdHistory                                        SnmpAdminString
}

cfprAaaUserDataInstanceId OBJECT-TYPE
    SYNTAX       CfprManagedObjectId
    MAX-ACCESS   not-accessible
    STATUS       current
    DESCRIPTION
        "Instance identifier of the managed object."
    ::= { cfprAaaUserDataEntry 1 }

cfprAaaUserDataDn OBJECT-TYPE
    SYNTAX       CfprManagedObjectDn
    MAX-ACCESS   read-only
    STATUS       current
    DESCRIPTION
        "Cisco Firepower aaa:UserData:dn managed object property"
    ::= { cfprAaaUserDataEntry 2 }

cfprAaaUserDataRn OBJECT-TYPE
    SYNTAX       SnmpAdminString
    MAX-ACCESS   read-only
    STATUS       current
    DESCRIPTION
        "Cisco Firepower aaa:UserData:rn managed object property"
    ::= { cfprAaaUserDataEntry 3 }

cfprAaaUserDataDescr OBJECT-TYPE
    SYNTAX       SnmpAdminString
    MAX-ACCESS   read-only
    STATUS       current
    DESCRIPTION
        "Cisco Firepower aaa:UserData:descr managed object property"
    ::= { cfprAaaUserDataEntry 4 }

cfprAaaUserDataIntId OBJECT-TYPE
    SYNTAX       SnmpAdminString
    MAX-ACCESS   read-only
    STATUS       current
    DESCRIPTION
        "Cisco Firepower aaa:UserData:intId managed object property"
    ::= { cfprAaaUserDataEntry 5 }

cfprAaaUserDataName OBJECT-TYPE
    SYNTAX       SnmpAdminString
    MAX-ACCESS   read-only
    STATUS       current
    DESCRIPTION
        "Cisco Firepower aaa:UserData:name managed object property"
    ::= { cfprAaaUserDataEntry 6 }

cfprAaaUserDataPolicyLevel OBJECT-TYPE
    SYNTAX       Gauge32
    MAX-ACCESS   read-only
    STATUS       current
    DESCRIPTION
        "Cisco Firepower aaa:UserData:policyLevel managed object property"
    ::= { cfprAaaUserDataEntry 7 }

cfprAaaUserDataPolicyOwner OBJECT-TYPE
    SYNTAX       CfprPolicyPolicyOwner
    MAX-ACCESS   read-only
    STATUS       current
    DESCRIPTION
        "Cisco Firepower aaa:UserData:policyOwner managed object property"
    ::= { cfprAaaUserDataEntry 8 }

cfprAaaUserDataPwdChangeCount OBJECT-TYPE
    SYNTAX       Gauge32
    MAX-ACCESS   read-only
    STATUS       current
    DESCRIPTION
        "Cisco Firepower aaa:UserData:pwdChangeCount managed
        object property"
    ::= { cfprAaaUserDataEntry 9 }

cfprAaaUserDataPwdChangeIntervalBegin OBJECT-TYPE
    SYNTAX       DateAndTime
    MAX-ACCESS   read-only
    STATUS       current
    DESCRIPTION
        "Cisco Firepower aaa:UserData:pwdChangeIntervalBegin
        managed object property"
    ::= { cfprAaaUserDataEntry 10 }

cfprAaaUserDataPwdChangedDate OBJECT-TYPE
    SYNTAX       DateAndTime
    MAX-ACCESS   read-only
    STATUS       current
    DESCRIPTION
        "Cisco Firepower aaa:UserData:pwdChangedDate managed
        object property"
    ::= { cfprAaaUserDataEntry 11 }

cfprAaaUserDataPwdHistory OBJECT-TYPE
    SYNTAX       SnmpAdminString
    MAX-ACCESS   read-only
    STATUS       current
    DESCRIPTION
        "Cisco Firepower aaa:UserData:pwdHistory managed object property"
    ::= { cfprAaaUserDataEntry 12 }

cfprAaaUserEpTable OBJECT-TYPE
    SYNTAX           SEQUENCE OF CfprAaaUserEpEntry
    MAX-ACCESS       not-accessible
    STATUS           current
    DESCRIPTION
        "Cisco Firepower aaa:UserEp managed object table"
    ::= { cfprAaaObjects 51 }

cfprAaaUserEpEntry OBJECT-TYPE
    SYNTAX           CfprAaaUserEpEntry
    MAX-ACCESS       not-accessible
    STATUS           current
    DESCRIPTION
        "Entry for the cfprAaaUserEpTable table."
    INDEX { cfprAaaUserEpInstanceId }
    ::= { cfprAaaUserEpTable 1 }

CfprAaaUserEpEntry ::= SEQUENCE {
    cfprAaaUserEpInstanceId                                          CfprManagedObjectId,
    cfprAaaUserEpDn                                                  CfprManagedObjectDn,
    cfprAaaUserEpRn                                                  SnmpAdminString,
    cfprAaaUserEpDescr                                               SnmpAdminString,
    cfprAaaUserEpFsmDescr                                            SnmpAdminString,
    cfprAaaUserEpFsmPrev                                             SnmpAdminString,
    cfprAaaUserEpFsmProgr                                            Gauge32,
    cfprAaaUserEpFsmRmtInvErrCode                                    Gauge32,
    cfprAaaUserEpFsmRmtInvErrDescr                                   SnmpAdminString,
    cfprAaaUserEpFsmRmtInvRslt                                       CfprConditionRemoteInvRslt,
    cfprAaaUserEpFsmStageDescr                                       SnmpAdminString,
    cfprAaaUserEpFsmStamp                                            DateAndTime,
    cfprAaaUserEpFsmStatus                                           SnmpAdminString,
    cfprAaaUserEpFsmTry                                              Gauge32,
    cfprAaaUserEpIntId                                               SnmpAdminString,
    cfprAaaUserEpName                                                SnmpAdminString,
    cfprAaaUserEpPolicyLevel                                         Gauge32,
    cfprAaaUserEpPolicyOwner                                         CfprPolicyPolicyOwner,
    cfprAaaUserEpPwdStrengthCheck                                    TruthValue,
    cfprAaaUserEpMaxLoginAttempts                                    Gauge32,
    cfprAaaUserEpMinPwdLength                                        Gauge32,
    cfprAaaUserEpUserAccountUnlockTime                               Gauge32,
    cfprAaaUserEpIsPasswordEncryptionKeySet                          TruthValue,
    cfprAaaUserEpPasswordEncryptionKey                               SnmpAdminString
}

cfprAaaUserEpInstanceId OBJECT-TYPE
    SYNTAX       CfprManagedObjectId
    MAX-ACCESS   not-accessible
    STATUS       current
    DESCRIPTION
        "Instance identifier of the managed object."
    ::= { cfprAaaUserEpEntry 1 }

cfprAaaUserEpDn OBJECT-TYPE
    SYNTAX       CfprManagedObjectDn
    MAX-ACCESS   read-only
    STATUS       current
    DESCRIPTION
        "Cisco Firepower aaa:UserEp:dn managed object property"
    ::= { cfprAaaUserEpEntry 2 }

cfprAaaUserEpRn OBJECT-TYPE
    SYNTAX       SnmpAdminString
    MAX-ACCESS   read-only
    STATUS       current
    DESCRIPTION
        "Cisco Firepower aaa:UserEp:rn managed object property"
    ::= { cfprAaaUserEpEntry 3 }

cfprAaaUserEpDescr OBJECT-TYPE
    SYNTAX       SnmpAdminString
    MAX-ACCESS   read-only
    STATUS       current
    DESCRIPTION
        "Cisco Firepower aaa:UserEp:descr managed object property"
    ::= { cfprAaaUserEpEntry 4 }

cfprAaaUserEpFsmDescr OBJECT-TYPE
    SYNTAX       SnmpAdminString
    MAX-ACCESS   read-only
    STATUS       current
    DESCRIPTION
        "Cisco Firepower aaa:UserEp:fsmDescr managed object property"
    ::= { cfprAaaUserEpEntry 5 }

cfprAaaUserEpFsmPrev OBJECT-TYPE
    SYNTAX       SnmpAdminString
    MAX-ACCESS   read-only
    STATUS       current
    DESCRIPTION
        "Cisco Firepower aaa:UserEp:fsmPrev managed object property"
    ::= { cfprAaaUserEpEntry 6 }

cfprAaaUserEpFsmProgr OBJECT-TYPE
    SYNTAX       Gauge32
    MAX-ACCESS   read-only
    STATUS       current
    DESCRIPTION
        "Cisco Firepower aaa:UserEp:fsmProgr managed object property"
    ::= { cfprAaaUserEpEntry 7 }

cfprAaaUserEpFsmRmtInvErrCode OBJECT-TYPE
    SYNTAX       Gauge32
    MAX-ACCESS   read-only
    STATUS       current
    DESCRIPTION
        "Cisco Firepower aaa:UserEp:fsmRmtInvErrCode managed
        object property"
    ::= { cfprAaaUserEpEntry 8 }

cfprAaaUserEpFsmRmtInvErrDescr OBJECT-TYPE
    SYNTAX       SnmpAdminString
    MAX-ACCESS   read-only
    STATUS       current
    DESCRIPTION
        "Cisco Firepower aaa:UserEp:fsmRmtInvErrDescr managed
        object property"
    ::= { cfprAaaUserEpEntry 9 }

cfprAaaUserEpFsmRmtInvRslt OBJECT-TYPE
    SYNTAX       CfprConditionRemoteInvRslt
    MAX-ACCESS   read-only
    STATUS       current
    DESCRIPTION
        "Cisco Firepower aaa:UserEp:fsmRmtInvRslt managed object property"
    ::= { cfprAaaUserEpEntry 10 }

cfprAaaUserEpFsmStageDescr OBJECT-TYPE
    SYNTAX       SnmpAdminString
    MAX-ACCESS   read-only
    STATUS       current
    DESCRIPTION
        "Cisco Firepower aaa:UserEp:fsmStageDescr managed object property"
    ::= { cfprAaaUserEpEntry 11 }

cfprAaaUserEpFsmStamp OBJECT-TYPE
    SYNTAX       DateAndTime
    MAX-ACCESS   read-only
    STATUS       current
    DESCRIPTION
        "Cisco Firepower aaa:UserEp:fsmStamp managed object property"
    ::= { cfprAaaUserEpEntry 12 }

cfprAaaUserEpFsmStatus OBJECT-TYPE
    SYNTAX       SnmpAdminString
    MAX-ACCESS   read-only
    STATUS       current
    DESCRIPTION
        "Cisco Firepower aaa:UserEp:fsmStatus managed object property"
    ::= { cfprAaaUserEpEntry 13 }

cfprAaaUserEpFsmTry OBJECT-TYPE
    SYNTAX       Gauge32
    MAX-ACCESS   read-only
    STATUS       current
    DESCRIPTION
        "Cisco Firepower aaa:UserEp:fsmTry managed object property"
    ::= { cfprAaaUserEpEntry 14 }

cfprAaaUserEpIntId OBJECT-TYPE
    SYNTAX       SnmpAdminString
    MAX-ACCESS   read-only
    STATUS       current
    DESCRIPTION
        "Cisco Firepower aaa:UserEp:intId managed object property"
    ::= { cfprAaaUserEpEntry 15 }

cfprAaaUserEpName OBJECT-TYPE
    SYNTAX       SnmpAdminString
    MAX-ACCESS   read-only
    STATUS       current
    DESCRIPTION
        "Cisco Firepower aaa:UserEp:name managed object property"
    ::= { cfprAaaUserEpEntry 16 }

cfprAaaUserEpPolicyLevel OBJECT-TYPE
    SYNTAX       Gauge32
    MAX-ACCESS   read-only
    STATUS       current
    DESCRIPTION
        "Cisco Firepower aaa:UserEp:policyLevel managed object property"
    ::= { cfprAaaUserEpEntry 17 }

cfprAaaUserEpPolicyOwner OBJECT-TYPE
    SYNTAX       CfprPolicyPolicyOwner
    MAX-ACCESS   read-only
    STATUS       current
    DESCRIPTION
        "Cisco Firepower aaa:UserEp:policyOwner managed object property"
    ::= { cfprAaaUserEpEntry 18 }

cfprAaaUserEpPwdStrengthCheck OBJECT-TYPE
    SYNTAX       TruthValue
    MAX-ACCESS   read-only
    STATUS       current
    DESCRIPTION
        "Cisco Firepower aaa:UserEp:pwdStrengthCheck managed
        object property"
    ::= { cfprAaaUserEpEntry 19 }

cfprAaaUserEpMaxLoginAttempts OBJECT-TYPE
    SYNTAX       Gauge32
    MAX-ACCESS   read-only
    STATUS       current
    DESCRIPTION
        "Cisco Firepower aaa:UserEp:maxLoginAttempts managed
        object property"
    ::= { cfprAaaUserEpEntry 20 }

cfprAaaUserEpMinPwdLength OBJECT-TYPE
    SYNTAX       Gauge32
    MAX-ACCESS   read-only
    STATUS       current
    DESCRIPTION
        "Cisco Firepower aaa:UserEp:minPwdLength managed object property"
    ::= { cfprAaaUserEpEntry 21 }

cfprAaaUserEpUserAccountUnlockTime OBJECT-TYPE
    SYNTAX       Gauge32
    MAX-ACCESS   read-only
    STATUS       current
    DESCRIPTION
        "Cisco Firepower aaa:UserEp:userAccountUnlockTime
        managed object property"
    ::= { cfprAaaUserEpEntry 22 }

cfprAaaUserEpIsPasswordEncryptionKeySet OBJECT-TYPE
    SYNTAX       TruthValue
    MAX-ACCESS   read-only
    STATUS       current
    DESCRIPTION
        "Cisco Firepower aaa:UserEp:isPasswordEncryptionKeySet
        managed object property"
    ::= { cfprAaaUserEpEntry 23 }

cfprAaaUserEpPasswordEncryptionKey OBJECT-TYPE
    SYNTAX       SnmpAdminString
    MAX-ACCESS   read-only
    STATUS       current
    DESCRIPTION
        "Cisco Firepower aaa:UserEp:passwordEncryptionKey
        managed object property"
    ::= { cfprAaaUserEpEntry 24 }

cfprAaaUserEpFsmTable OBJECT-TYPE
    SYNTAX           SEQUENCE OF CfprAaaUserEpFsmEntry
    MAX-ACCESS       not-accessible
    STATUS           current
    DESCRIPTION
        "Cisco Firepower aaa:UserEpFsm managed object table"
    ::= { cfprAaaObjects 52 }

cfprAaaUserEpFsmEntry OBJECT-TYPE
    SYNTAX           CfprAaaUserEpFsmEntry
    MAX-ACCESS       not-accessible
    STATUS           current
    DESCRIPTION
        "Entry for the cfprAaaUserEpFsmTable table."
    INDEX { cfprAaaUserEpFsmInstanceId }
    ::= { cfprAaaUserEpFsmTable 1 }

CfprAaaUserEpFsmEntry ::= SEQUENCE {
    cfprAaaUserEpFsmInstanceId                                       CfprManagedObjectId,
    cfprAaaUserEpFsmDn                                               CfprManagedObjectDn,
    cfprAaaUserEpFsmRn                                               SnmpAdminString,
    cfprAaaUserEpFsmCompletionTime                                   DateAndTime,
    cfprAaaUserEpFsmCurrentFsm                                       CfprAaaUserEpFsmCurrentFsm,
    cfprAaaUserEpFsmDescrData                                        SnmpAdminString,
    cfprAaaUserEpFsmFsmStatus                                        CfprFsmFsmStageStatus,
    cfprAaaUserEpFsmProgress                                         Gauge32,
    cfprAaaUserEpFsmRmtErrCode                                       Gauge32,
    cfprAaaUserEpFsmRmtErrDescr                                      SnmpAdminString,
    cfprAaaUserEpFsmRmtRslt                                          CfprConditionRemoteInvRslt
}

cfprAaaUserEpFsmInstanceId OBJECT-TYPE
    SYNTAX       CfprManagedObjectId
    MAX-ACCESS   not-accessible
    STATUS       current
    DESCRIPTION
        "Instance identifier of the managed object."
    ::= { cfprAaaUserEpFsmEntry 1 }

cfprAaaUserEpFsmDn OBJECT-TYPE
    SYNTAX       CfprManagedObjectDn
    MAX-ACCESS   read-only
    STATUS       current
    DESCRIPTION
        "Cisco Firepower aaa:UserEpFsm:dn managed object property"
    ::= { cfprAaaUserEpFsmEntry 2 }

cfprAaaUserEpFsmRn OBJECT-TYPE
    SYNTAX       SnmpAdminString
    MAX-ACCESS   read-only
    STATUS       current
    DESCRIPTION
        "Cisco Firepower aaa:UserEpFsm:rn managed object property"
    ::= { cfprAaaUserEpFsmEntry 3 }

cfprAaaUserEpFsmCompletionTime OBJECT-TYPE
    SYNTAX       DateAndTime
    MAX-ACCESS   read-only
    STATUS       current
    DESCRIPTION
        "Cisco Firepower aaa:UserEpFsm:completionTime managed
        object property"
    ::= { cfprAaaUserEpFsmEntry 4 }

cfprAaaUserEpFsmCurrentFsm OBJECT-TYPE
    SYNTAX       CfprAaaUserEpFsmCurrentFsm
    MAX-ACCESS   read-only
    STATUS       current
    DESCRIPTION
        "Cisco Firepower aaa:UserEpFsm:currentFsm managed object property"
    ::= { cfprAaaUserEpFsmEntry 5 }

cfprAaaUserEpFsmDescrData OBJECT-TYPE
    SYNTAX       SnmpAdminString
    MAX-ACCESS   read-only
    STATUS       current
    DESCRIPTION
        "Cisco Firepower aaa:UserEpFsm:descr managed object property"
    ::= { cfprAaaUserEpFsmEntry 6 }

cfprAaaUserEpFsmFsmStatus OBJECT-TYPE
    SYNTAX       CfprFsmFsmStageStatus
    MAX-ACCESS   read-only
    STATUS       current
    DESCRIPTION
        "Cisco Firepower aaa:UserEpFsm:fsmStatus managed object property"
    ::= { cfprAaaUserEpFsmEntry 7 }

cfprAaaUserEpFsmProgress OBJECT-TYPE
    SYNTAX       Gauge32
    MAX-ACCESS   read-only
    STATUS       current
    DESCRIPTION
        "Cisco Firepower aaa:UserEpFsm:progress managed object property"
    ::= { cfprAaaUserEpFsmEntry 8 }

cfprAaaUserEpFsmRmtErrCode OBJECT-TYPE
    SYNTAX       Gauge32
    MAX-ACCESS   read-only
    STATUS       current
    DESCRIPTION
        "Cisco Firepower aaa:UserEpFsm:rmtErrCode managed object property"
    ::= { cfprAaaUserEpFsmEntry 9 }

cfprAaaUserEpFsmRmtErrDescr OBJECT-TYPE
    SYNTAX       SnmpAdminString
    MAX-ACCESS   read-only
    STATUS       current
    DESCRIPTION
        "Cisco Firepower aaa:UserEpFsm:rmtErrDescr managed
        object property"
    ::= { cfprAaaUserEpFsmEntry 10 }

cfprAaaUserEpFsmRmtRslt OBJECT-TYPE
    SYNTAX       CfprConditionRemoteInvRslt
    MAX-ACCESS   read-only
    STATUS       current
    DESCRIPTION
        "Cisco Firepower aaa:UserEpFsm:rmtRslt managed object property"
    ::= { cfprAaaUserEpFsmEntry 11 }

cfprAaaUserEpFsmStageTable OBJECT-TYPE
    SYNTAX           SEQUENCE OF CfprAaaUserEpFsmStageEntry
    MAX-ACCESS       not-accessible
    STATUS           current
    DESCRIPTION
        "Cisco Firepower aaa:UserEpFsmStage managed object table"
    ::= { cfprAaaObjects 53 }

cfprAaaUserEpFsmStageEntry OBJECT-TYPE
    SYNTAX           CfprAaaUserEpFsmStageEntry
    MAX-ACCESS       not-accessible
    STATUS           current
    DESCRIPTION
        "Entry for the cfprAaaUserEpFsmStageTable table."
    INDEX { cfprAaaUserEpFsmStageInstanceId }
    ::= { cfprAaaUserEpFsmStageTable 1 }

CfprAaaUserEpFsmStageEntry ::= SEQUENCE {
    cfprAaaUserEpFsmStageInstanceId                                  CfprManagedObjectId,
    cfprAaaUserEpFsmStageDn                                          CfprManagedObjectDn,
    cfprAaaUserEpFsmStageRn                                          SnmpAdminString,
    cfprAaaUserEpFsmStageDescrData                                   SnmpAdminString,
    cfprAaaUserEpFsmStageLastUpdateTime                              DateAndTime,
    cfprAaaUserEpFsmStageName                                        CfprAaaUserEpFsmStageName,
    cfprAaaUserEpFsmStageOrder                                       Gauge32,
    cfprAaaUserEpFsmStageRetry                                       Gauge32,
    cfprAaaUserEpFsmStageStageStatus                                 CfprFsmFsmStageStatus
}

cfprAaaUserEpFsmStageInstanceId OBJECT-TYPE
    SYNTAX       CfprManagedObjectId
    MAX-ACCESS   not-accessible
    STATUS       current
    DESCRIPTION
        "Instance identifier of the managed object."
    ::= { cfprAaaUserEpFsmStageEntry 1 }

cfprAaaUserEpFsmStageDn OBJECT-TYPE
    SYNTAX       CfprManagedObjectDn
    MAX-ACCESS   read-only
    STATUS       current
    DESCRIPTION
        "Cisco Firepower aaa:UserEpFsmStage:dn managed object property"
    ::= { cfprAaaUserEpFsmStageEntry 2 }

cfprAaaUserEpFsmStageRn OBJECT-TYPE
    SYNTAX       SnmpAdminString
    MAX-ACCESS   read-only
    STATUS       current
    DESCRIPTION
        "Cisco Firepower aaa:UserEpFsmStage:rn managed object property"
    ::= { cfprAaaUserEpFsmStageEntry 3 }

cfprAaaUserEpFsmStageDescrData OBJECT-TYPE
    SYNTAX       SnmpAdminString
    MAX-ACCESS   read-only
    STATUS       current
    DESCRIPTION
        "Cisco Firepower aaa:UserEpFsmStage:descr managed object property"
    ::= { cfprAaaUserEpFsmStageEntry 4 }

cfprAaaUserEpFsmStageLastUpdateTime OBJECT-TYPE
    SYNTAX       DateAndTime
    MAX-ACCESS   read-only
    STATUS       current
    DESCRIPTION
        "Cisco Firepower aaa:UserEpFsmStage:lastUpdateTime
        managed object property"
    ::= { cfprAaaUserEpFsmStageEntry 5 }

cfprAaaUserEpFsmStageName OBJECT-TYPE
    SYNTAX       CfprAaaUserEpFsmStageName
    MAX-ACCESS   read-only
    STATUS       current
    DESCRIPTION
        "Cisco Firepower aaa:UserEpFsmStage:name managed object property"
    ::= { cfprAaaUserEpFsmStageEntry 6 }

cfprAaaUserEpFsmStageOrder OBJECT-TYPE
    SYNTAX       Gauge32
    MAX-ACCESS   read-only
    STATUS       current
    DESCRIPTION
        "Cisco Firepower aaa:UserEpFsmStage:order managed object property"
    ::= { cfprAaaUserEpFsmStageEntry 7 }

cfprAaaUserEpFsmStageRetry OBJECT-TYPE
    SYNTAX       Gauge32
    MAX-ACCESS   read-only
    STATUS       current
    DESCRIPTION
        "Cisco Firepower aaa:UserEpFsmStage:retry managed object property"
    ::= { cfprAaaUserEpFsmStageEntry 8 }

cfprAaaUserEpFsmStageStageStatus OBJECT-TYPE
    SYNTAX       CfprFsmFsmStageStatus
    MAX-ACCESS   read-only
    STATUS       current
    DESCRIPTION
        "Cisco Firepower aaa:UserEpFsmStage:stageStatus
        managed object property"
    ::= { cfprAaaUserEpFsmStageEntry 9 }

cfprAaaUserEpFsmTaskTable OBJECT-TYPE
    SYNTAX           SEQUENCE OF CfprAaaUserEpFsmTaskEntry
    MAX-ACCESS       not-accessible
    STATUS           current
    DESCRIPTION
        "Cisco Firepower aaa:UserEpFsmTask managed object table"
    ::= { cfprAaaObjects 54 }

cfprAaaUserEpFsmTaskEntry OBJECT-TYPE
    SYNTAX           CfprAaaUserEpFsmTaskEntry
    MAX-ACCESS       not-accessible
    STATUS           current
    DESCRIPTION
        "Entry for the cfprAaaUserEpFsmTaskTable table."
    INDEX { cfprAaaUserEpFsmTaskInstanceId }
    ::= { cfprAaaUserEpFsmTaskTable 1 }

CfprAaaUserEpFsmTaskEntry ::= SEQUENCE {
    cfprAaaUserEpFsmTaskInstanceId                                   CfprManagedObjectId,
    cfprAaaUserEpFsmTaskDn                                           CfprManagedObjectDn,
    cfprAaaUserEpFsmTaskRn                                           SnmpAdminString,
    cfprAaaUserEpFsmTaskCompletion                                   CfprFsmCompletion,
    cfprAaaUserEpFsmTaskFlags                                        CfprFsmFlags,
    cfprAaaUserEpFsmTaskItem                                         CfprAaaUserEpFsmTaskItem,
    cfprAaaUserEpFsmTaskSeqId                                        Gauge32
}

cfprAaaUserEpFsmTaskInstanceId OBJECT-TYPE
    SYNTAX       CfprManagedObjectId
    MAX-ACCESS   not-accessible
    STATUS       current
    DESCRIPTION
        "Instance identifier of the managed object."
    ::= { cfprAaaUserEpFsmTaskEntry 1 }

cfprAaaUserEpFsmTaskDn OBJECT-TYPE
    SYNTAX       CfprManagedObjectDn
    MAX-ACCESS   read-only
    STATUS       current
    DESCRIPTION
        "Cisco Firepower aaa:UserEpFsmTask:dn managed object property"
    ::= { cfprAaaUserEpFsmTaskEntry 2 }

cfprAaaUserEpFsmTaskRn OBJECT-TYPE
    SYNTAX       SnmpAdminString
    MAX-ACCESS   read-only
    STATUS       current
    DESCRIPTION
        "Cisco Firepower aaa:UserEpFsmTask:rn managed object property"
    ::= { cfprAaaUserEpFsmTaskEntry 3 }

cfprAaaUserEpFsmTaskCompletion OBJECT-TYPE
    SYNTAX       CfprFsmCompletion
    MAX-ACCESS   read-only
    STATUS       current
    DESCRIPTION
        "Cisco Firepower aaa:UserEpFsmTask:completion managed
        object property"
    ::= { cfprAaaUserEpFsmTaskEntry 4 }

cfprAaaUserEpFsmTaskFlags OBJECT-TYPE
    SYNTAX       CfprFsmFlags
    MAX-ACCESS   read-only
    STATUS       current
    DESCRIPTION
        "Cisco Firepower aaa:UserEpFsmTask:flags managed object property"
    ::= { cfprAaaUserEpFsmTaskEntry 5 }

cfprAaaUserEpFsmTaskItem OBJECT-TYPE
    SYNTAX       CfprAaaUserEpFsmTaskItem
    MAX-ACCESS   read-only
    STATUS       current
    DESCRIPTION
        "Cisco Firepower aaa:UserEpFsmTask:item managed object property"
    ::= { cfprAaaUserEpFsmTaskEntry 6 }

cfprAaaUserEpFsmTaskSeqId OBJECT-TYPE
    SYNTAX       Gauge32
    MAX-ACCESS   read-only
    STATUS       current
    DESCRIPTION
        "Cisco Firepower aaa:UserEpFsmTask:seqId managed object property"
    ::= { cfprAaaUserEpFsmTaskEntry 7 }

cfprAaaUserLocaleTable OBJECT-TYPE
    SYNTAX           SEQUENCE OF CfprAaaUserLocaleEntry
    MAX-ACCESS       not-accessible
    STATUS           current
    DESCRIPTION
        "Cisco Firepower aaa:UserLocale managed object table"
    ::= { cfprAaaObjects 55 }

cfprAaaUserLocaleEntry OBJECT-TYPE
    SYNTAX           CfprAaaUserLocaleEntry
    MAX-ACCESS       not-accessible
    STATUS           current
    DESCRIPTION
        "Entry for the cfprAaaUserLocaleTable table."
    INDEX { cfprAaaUserLocaleInstanceId }
    ::= { cfprAaaUserLocaleTable 1 }

CfprAaaUserLocaleEntry ::= SEQUENCE {
    cfprAaaUserLocaleInstanceId                                      CfprManagedObjectId,
    cfprAaaUserLocaleDn                                              CfprManagedObjectDn,
    cfprAaaUserLocaleRn                                              SnmpAdminString,
    cfprAaaUserLocaleConfigState                                     CfprAaaConfigState,
    cfprAaaUserLocaleConfigStatusMessage                             SnmpAdminString,
    cfprAaaUserLocaleDescr                                           SnmpAdminString,
    cfprAaaUserLocaleName                                            SnmpAdminString
}

cfprAaaUserLocaleInstanceId OBJECT-TYPE
    SYNTAX       CfprManagedObjectId
    MAX-ACCESS   not-accessible
    STATUS       current
    DESCRIPTION
        "Instance identifier of the managed object."
    ::= { cfprAaaUserLocaleEntry 1 }

cfprAaaUserLocaleDn OBJECT-TYPE
    SYNTAX       CfprManagedObjectDn
    MAX-ACCESS   read-only
    STATUS       current
    DESCRIPTION
        "Cisco Firepower aaa:UserLocale:dn managed object property"
    ::= { cfprAaaUserLocaleEntry 2 }

cfprAaaUserLocaleRn OBJECT-TYPE
    SYNTAX       SnmpAdminString
    MAX-ACCESS   read-only
    STATUS       current
    DESCRIPTION
        "Cisco Firepower aaa:UserLocale:rn managed object property"
    ::= { cfprAaaUserLocaleEntry 3 }

cfprAaaUserLocaleConfigState OBJECT-TYPE
    SYNTAX       CfprAaaConfigState
    MAX-ACCESS   read-only
    STATUS       current
    DESCRIPTION
        "Cisco Firepower aaa:UserLocale:configState managed
        object property"
    ::= { cfprAaaUserLocaleEntry 4 }

cfprAaaUserLocaleConfigStatusMessage OBJECT-TYPE
    SYNTAX       SnmpAdminString
    MAX-ACCESS   read-only
    STATUS       current
    DESCRIPTION
        "Cisco Firepower aaa:UserLocale:configStatusMessage
        managed object property"
    ::= { cfprAaaUserLocaleEntry 5 }

cfprAaaUserLocaleDescr OBJECT-TYPE
    SYNTAX       SnmpAdminString
    MAX-ACCESS   read-only
    STATUS       current
    DESCRIPTION
        "Cisco Firepower aaa:UserLocale:descr managed object property"
    ::= { cfprAaaUserLocaleEntry 6 }

cfprAaaUserLocaleName OBJECT-TYPE
    SYNTAX       SnmpAdminString
    MAX-ACCESS   read-only
    STATUS       current
    DESCRIPTION
        "Cisco Firepower aaa:UserLocale:name managed object property"
    ::= { cfprAaaUserLocaleEntry 7 }

cfprAaaUserLoginInfoTable OBJECT-TYPE
    SYNTAX           SEQUENCE OF CfprAaaUserLoginInfoEntry
    MAX-ACCESS       not-accessible
    STATUS           current
    DESCRIPTION
        "Cisco Firepower aaa:UserLoginInfo managed object table"
    ::= { cfprAaaObjects 60 }

cfprAaaUserLoginInfoEntry OBJECT-TYPE
    SYNTAX           CfprAaaUserLoginInfoEntry
    MAX-ACCESS       not-accessible
    STATUS           current
    DESCRIPTION
        "Entry for the cfprAaaUserLoginInfoTable table."
    INDEX { cfprAaaUserLoginInfoInstanceId }
    ::= { cfprAaaUserLoginInfoTable 1 }

CfprAaaUserLoginInfoEntry ::= SEQUENCE {
    cfprAaaUserLoginInfoInstanceId                                   CfprManagedObjectId,
    cfprAaaUserLoginInfoDn                                           CfprManagedObjectDn,
    cfprAaaUserLoginInfoRn                                           SnmpAdminString,
    cfprAaaUserLoginInfoNumFailedLogin                               Gauge32,
    cfprAaaUserLoginInfoNumSuccessLogin                              Gauge32
}

cfprAaaUserLoginInfoInstanceId OBJECT-TYPE
    SYNTAX       CfprManagedObjectId
    MAX-ACCESS   not-accessible
    STATUS       current
    DESCRIPTION
        "Instance identifier of the managed object."
    ::= { cfprAaaUserLoginInfoEntry 1 }

cfprAaaUserLoginInfoDn OBJECT-TYPE
    SYNTAX       CfprManagedObjectDn
    MAX-ACCESS   read-only
    STATUS       current
    DESCRIPTION
        "Cisco Firepower aaa:UserLoginInfo:dn managed object property"
    ::= { cfprAaaUserLoginInfoEntry 2 }

cfprAaaUserLoginInfoRn OBJECT-TYPE
    SYNTAX       SnmpAdminString
    MAX-ACCESS   read-only
    STATUS       current
    DESCRIPTION
        "Cisco Firepower aaa:UserLoginInfo:rn managed object property"
    ::= { cfprAaaUserLoginInfoEntry 3 }

cfprAaaUserLoginInfoNumFailedLogin OBJECT-TYPE
    SYNTAX       Gauge32
    MAX-ACCESS   read-only
    STATUS       current
    DESCRIPTION
        "Cisco Firepower aaa:UserLoginInfo:numFailedLogin
        managed object property"
    ::= { cfprAaaUserLoginInfoEntry 4 }

cfprAaaUserLoginInfoNumSuccessLogin OBJECT-TYPE
    SYNTAX       Gauge32
    MAX-ACCESS   read-only
    STATUS       current
    DESCRIPTION
        "Cisco Firepower aaa:UserLoginInfo:numSuccessLogin
        managed object property"
    ::= { cfprAaaUserLoginInfoEntry 5 }

cfprAaaUserOldPwdTable OBJECT-TYPE
    SYNTAX           SEQUENCE OF CfprAaaUserOldPwdEntry
    MAX-ACCESS       not-accessible
    STATUS           current
    DESCRIPTION
        "Cisco Firepower aaa:UserOldPwd managed object table"
    ::= { cfprAaaObjects 61 }

cfprAaaUserOldPwdEntry OBJECT-TYPE
    SYNTAX           CfprAaaUserOldPwdEntry
    MAX-ACCESS       not-accessible
    STATUS           current
    DESCRIPTION
        "Entry for the cfprAaaUserOldPwdTable table."
    INDEX { cfprAaaUserOldPwdInstanceId }
    ::= { cfprAaaUserOldPwdTable 1 }

CfprAaaUserOldPwdEntry ::= SEQUENCE {
    cfprAaaUserOldPwdInstanceId                                      CfprManagedObjectId,
    cfprAaaUserOldPwdDn                                              CfprManagedObjectDn,
    cfprAaaUserOldPwdRn                                              SnmpAdminString,
    cfprAaaUserOldPwdDescr                                           SnmpAdminString,
    cfprAaaUserOldPwdEncPwd                                          SnmpAdminString,
    cfprAaaUserOldPwdIntId                                           SnmpAdminString,
    cfprAaaUserOldPwdName                                            SnmpAdminString,
    cfprAaaUserOldPwdPolicyLevel                                     Gauge32,
    cfprAaaUserOldPwdPolicyOwner                                     CfprPolicyPolicyOwner,
    cfprAaaUserOldPwdPwdEndDate                                      DateAndTime
}

cfprAaaUserOldPwdInstanceId OBJECT-TYPE
    SYNTAX       CfprManagedObjectId
    MAX-ACCESS   not-accessible
    STATUS       current
    DESCRIPTION
        "Instance identifier of the managed object."
    ::= { cfprAaaUserOldPwdEntry 1 }

cfprAaaUserOldPwdDn OBJECT-TYPE
    SYNTAX       CfprManagedObjectDn
    MAX-ACCESS   read-only
    STATUS       current
    DESCRIPTION
        "Cisco Firepower aaa:UserOldPwd:dn managed object property"
    ::= { cfprAaaUserOldPwdEntry 2 }

cfprAaaUserOldPwdRn OBJECT-TYPE
    SYNTAX       SnmpAdminString
    MAX-ACCESS   read-only
    STATUS       current
    DESCRIPTION
        "Cisco Firepower aaa:UserOldPwd:rn managed object property"
    ::= { cfprAaaUserOldPwdEntry 3 }

cfprAaaUserOldPwdDescr OBJECT-TYPE
    SYNTAX       SnmpAdminString
    MAX-ACCESS   read-only
    STATUS       current
    DESCRIPTION
        "Cisco Firepower aaa:UserOldPwd:descr managed object property"
    ::= { cfprAaaUserOldPwdEntry 4 }

cfprAaaUserOldPwdEncPwd OBJECT-TYPE
    SYNTAX       SnmpAdminString
    MAX-ACCESS   read-only
    STATUS       current
    DESCRIPTION
        "Cisco Firepower aaa:UserOldPwd:encPwd managed object property"
    ::= { cfprAaaUserOldPwdEntry 5 }

cfprAaaUserOldPwdIntId OBJECT-TYPE
    SYNTAX       SnmpAdminString
    MAX-ACCESS   read-only
    STATUS       current
    DESCRIPTION
        "Cisco Firepower aaa:UserOldPwd:intId managed object property"
    ::= { cfprAaaUserOldPwdEntry 6 }

cfprAaaUserOldPwdName OBJECT-TYPE
    SYNTAX       SnmpAdminString
    MAX-ACCESS   read-only
    STATUS       current
    DESCRIPTION
        "Cisco Firepower aaa:UserOldPwd:name managed object property"
    ::= { cfprAaaUserOldPwdEntry 7 }

cfprAaaUserOldPwdPolicyLevel OBJECT-TYPE
    SYNTAX       Gauge32
    MAX-ACCESS   read-only
    STATUS       current
    DESCRIPTION
        "Cisco Firepower aaa:UserOldPwd:policyLevel managed
        object property"
    ::= { cfprAaaUserOldPwdEntry 8 }

cfprAaaUserOldPwdPolicyOwner OBJECT-TYPE
    SYNTAX       CfprPolicyPolicyOwner
    MAX-ACCESS   read-only
    STATUS       current
    DESCRIPTION
        "Cisco Firepower aaa:UserOldPwd:policyOwner managed
        object property"
    ::= { cfprAaaUserOldPwdEntry 9 }

cfprAaaUserOldPwdPwdEndDate OBJECT-TYPE
    SYNTAX       DateAndTime
    MAX-ACCESS   read-only
    STATUS       current
    DESCRIPTION
        "Cisco Firepower aaa:UserOldPwd:pwdEndDate managed
        object property"
    ::= { cfprAaaUserOldPwdEntry 10 }

cfprAaaUserRoleTable OBJECT-TYPE
    SYNTAX           SEQUENCE OF CfprAaaUserRoleEntry
    MAX-ACCESS       not-accessible
    STATUS           current
    DESCRIPTION
        "Cisco Firepower aaa:UserRole managed object table"
    ::= { cfprAaaObjects 56 }

cfprAaaUserRoleEntry OBJECT-TYPE
    SYNTAX           CfprAaaUserRoleEntry
    MAX-ACCESS       not-accessible
    STATUS           current
    DESCRIPTION
        "Entry for the cfprAaaUserRoleTable table."
    INDEX { cfprAaaUserRoleInstanceId }
    ::= { cfprAaaUserRoleTable 1 }

CfprAaaUserRoleEntry ::= SEQUENCE {
    cfprAaaUserRoleInstanceId                                        CfprManagedObjectId,
    cfprAaaUserRoleDn                                                CfprManagedObjectDn,
    cfprAaaUserRoleRn                                                SnmpAdminString,
    cfprAaaUserRoleConfigState                                       CfprAaaConfigState,
    cfprAaaUserRoleConfigStatusMessage                               SnmpAdminString,
    cfprAaaUserRoleDescr                                             SnmpAdminString,
    cfprAaaUserRoleName                                              SnmpAdminString
}

cfprAaaUserRoleInstanceId OBJECT-TYPE
    SYNTAX       CfprManagedObjectId
    MAX-ACCESS   not-accessible
    STATUS       current
    DESCRIPTION
        "Instance identifier of the managed object."
    ::= { cfprAaaUserRoleEntry 1 }

cfprAaaUserRoleDn OBJECT-TYPE
    SYNTAX       CfprManagedObjectDn
    MAX-ACCESS   read-only
    STATUS       current
    DESCRIPTION
        "Cisco Firepower aaa:UserRole:dn managed object property"
    ::= { cfprAaaUserRoleEntry 2 }

cfprAaaUserRoleRn OBJECT-TYPE
    SYNTAX       SnmpAdminString
    MAX-ACCESS   read-only
    STATUS       current
    DESCRIPTION
        "Cisco Firepower aaa:UserRole:rn managed object property"
    ::= { cfprAaaUserRoleEntry 3 }

cfprAaaUserRoleConfigState OBJECT-TYPE
    SYNTAX       CfprAaaConfigState
    MAX-ACCESS   read-only
    STATUS       current
    DESCRIPTION
        "Cisco Firepower aaa:UserRole:configState managed object property"
    ::= { cfprAaaUserRoleEntry 4 }

cfprAaaUserRoleConfigStatusMessage OBJECT-TYPE
    SYNTAX       SnmpAdminString
    MAX-ACCESS   read-only
    STATUS       current
    DESCRIPTION
        "Cisco Firepower aaa:UserRole:configStatusMessage
        managed object property"
    ::= { cfprAaaUserRoleEntry 5 }

cfprAaaUserRoleDescr OBJECT-TYPE
    SYNTAX       SnmpAdminString
    MAX-ACCESS   read-only
    STATUS       current
    DESCRIPTION
        "Cisco Firepower aaa:UserRole:descr managed object property"
    ::= { cfprAaaUserRoleEntry 6 }

cfprAaaUserRoleName OBJECT-TYPE
    SYNTAX       SnmpAdminString
    MAX-ACCESS   read-only
    STATUS       current
    DESCRIPTION
        "Cisco Firepower aaa:UserRole:name managed object property"
    ::= { cfprAaaUserRoleEntry 7 }

cfprAaaWebLoginTable OBJECT-TYPE
    SYNTAX           SEQUENCE OF CfprAaaWebLoginEntry
    MAX-ACCESS       not-accessible
    STATUS           current
    DESCRIPTION
        "Cisco Firepower aaa:WebLogin managed object table"
    ::= { cfprAaaObjects 57 }

cfprAaaWebLoginEntry OBJECT-TYPE
    SYNTAX           CfprAaaWebLoginEntry
    MAX-ACCESS       not-accessible
    STATUS           current
    DESCRIPTION
        "Entry for the cfprAaaWebLoginTable table."
    INDEX { cfprAaaWebLoginInstanceId }
    ::= { cfprAaaWebLoginTable 1 }

CfprAaaWebLoginEntry ::= SEQUENCE {
    cfprAaaWebLoginInstanceId                                        CfprManagedObjectId,
    cfprAaaWebLoginDn                                                CfprManagedObjectDn,
    cfprAaaWebLoginRn                                                SnmpAdminString,
    cfprAaaWebLoginDescr                                             SnmpAdminString,
    cfprAaaWebLoginId                                                SnmpAdminString,
    cfprAaaWebLoginIntId                                             SnmpAdminString,
    cfprAaaWebLoginLocalHost                                         SnmpAdminString,
    cfprAaaWebLoginName                                              SnmpAdminString,
    cfprAaaWebLoginPolicyLevel                                       Gauge32,
    cfprAaaWebLoginPolicyOwner                                       CfprPolicyPolicyOwner,
    cfprAaaWebLoginRemoteHost                                        SnmpAdminString,
    cfprAaaWebLoginSession                                           CfprAaaSession,
    cfprAaaWebLoginSwitchId                                          CfprNetworkSwitchId
}

cfprAaaWebLoginInstanceId OBJECT-TYPE
    SYNTAX       CfprManagedObjectId
    MAX-ACCESS   not-accessible
    STATUS       current
    DESCRIPTION
        "Instance identifier of the managed object."
    ::= { cfprAaaWebLoginEntry 1 }

cfprAaaWebLoginDn OBJECT-TYPE
    SYNTAX       CfprManagedObjectDn
    MAX-ACCESS   read-only
    STATUS       current
    DESCRIPTION
        "Cisco Firepower aaa:WebLogin:dn managed object property"
    ::= { cfprAaaWebLoginEntry 2 }

cfprAaaWebLoginRn OBJECT-TYPE
    SYNTAX       SnmpAdminString
    MAX-ACCESS   read-only
    STATUS       current
    DESCRIPTION
        "Cisco Firepower aaa:WebLogin:rn managed object property"
    ::= { cfprAaaWebLoginEntry 3 }

cfprAaaWebLoginDescr OBJECT-TYPE
    SYNTAX       SnmpAdminString
    MAX-ACCESS   read-only
    STATUS       current
    DESCRIPTION
        "Cisco Firepower aaa:WebLogin:descr managed object property"
    ::= { cfprAaaWebLoginEntry 4 }

cfprAaaWebLoginId OBJECT-TYPE
    SYNTAX       SnmpAdminString
    MAX-ACCESS   read-only
    STATUS       current
    DESCRIPTION
        "Cisco Firepower aaa:WebLogin:id managed object property"
    ::= { cfprAaaWebLoginEntry 5 }

cfprAaaWebLoginIntId OBJECT-TYPE
    SYNTAX       SnmpAdminString
    MAX-ACCESS   read-only
    STATUS       current
    DESCRIPTION
        "Cisco Firepower aaa:WebLogin:intId managed object property"
    ::= { cfprAaaWebLoginEntry 6 }

cfprAaaWebLoginLocalHost OBJECT-TYPE
    SYNTAX       SnmpAdminString
    MAX-ACCESS   read-only
    STATUS       current
    DESCRIPTION
        "Cisco Firepower aaa:WebLogin:localHost managed object property"
    ::= { cfprAaaWebLoginEntry 7 }

cfprAaaWebLoginName OBJECT-TYPE
    SYNTAX       SnmpAdminString
    MAX-ACCESS   read-only
    STATUS       current
    DESCRIPTION
        "Cisco Firepower aaa:WebLogin:name managed object property"
    ::= { cfprAaaWebLoginEntry 8 }

cfprAaaWebLoginPolicyLevel OBJECT-TYPE
    SYNTAX       Gauge32
    MAX-ACCESS   read-only
    STATUS       current
    DESCRIPTION
        "Cisco Firepower aaa:WebLogin:policyLevel managed object property"
    ::= { cfprAaaWebLoginEntry 9 }

cfprAaaWebLoginPolicyOwner OBJECT-TYPE
    SYNTAX       CfprPolicyPolicyOwner
    MAX-ACCESS   read-only
    STATUS       current
    DESCRIPTION
        "Cisco Firepower aaa:WebLogin:policyOwner managed object property"
    ::= { cfprAaaWebLoginEntry 10 }

cfprAaaWebLoginRemoteHost OBJECT-TYPE
    SYNTAX       SnmpAdminString
    MAX-ACCESS   read-only
    STATUS       current
    DESCRIPTION
        "Cisco Firepower aaa:WebLogin:remoteHost managed object property"
    ::= { cfprAaaWebLoginEntry 11 }

cfprAaaWebLoginSession OBJECT-TYPE
    SYNTAX       CfprAaaSession
    MAX-ACCESS   read-only
    STATUS       current
    DESCRIPTION
        "Cisco Firepower aaa:WebLogin:session managed object property"
    ::= { cfprAaaWebLoginEntry 12 }

cfprAaaWebLoginSwitchId OBJECT-TYPE
    SYNTAX       CfprNetworkSwitchId
    MAX-ACCESS   read-only
    STATUS       current
    DESCRIPTION
        "Cisco Firepower aaa:WebLogin:switchId managed object property"
    ::= { cfprAaaWebLoginEntry 13 }

END
