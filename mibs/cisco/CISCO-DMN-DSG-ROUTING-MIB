--*****************************************************************
-- CISCO_DMN_DSG_Routing.mib: MIB file for Ethernet routing information.
--
-- February 2012, Aaron Curtin
--
-- Copyright (c) 2012 by Cisco Systems, Inc. All rights reserved.
--*****************************************************************

CISCO-DMN-DSG-ROUTING-MIB

DEFINITIONS ::= BEGIN

IMPORTS
    OBJECT-TYPE,
    MODULE-IDENTITY, Integer32, IpAddress, Counter32
        FROM SNMPv2-SMI
    DisplayString, RowStatus
        FROM SNMPv2-TC
    OBJECT-GROUP, MODULE-COMPLIANCE
        FROM SNMPv2-CONF
    ciscoDSGUtilities
        FROM CISCO-DMN-DSG-ROOT-MIB;


ciscoDSGRouting MODULE-IDENTITY
    LAST-UPDATED    "201205141500Z"
    ORGANIZATION    "Cisco Systems, Inc."
    CONTACT-INFO
       "Cisco Systems, Inc.
        Customer Service
        Postal: 170 W Tasman Drive
        San Jose, CA 95134
        USA
        Tel: +1 800 553 NETS

        E-mail: cs-ipsla@cisco.com"
    DESCRIPTION     "Cisco Routing MIB."

    REVISION        "201205141500Z"
    DESCRIPTION     "V01.00.01 2012-05-14
                    Updated to adopt RowStatus."

    REVISION        "201203070730Z"
    DESCRIPTION     "V01.00.00 2012-03-07
                    Initial Version."

    ::= { ciscoDSGUtilities 40 }

--**************************************
-- Multicast Route Table
--**************************************
multicastRouteTable  OBJECT-TYPE
     SYNTAX  SEQUENCE OF MulticastRouteEntry
     MAX-ACCESS not-accessible
     STATUS  current
     DESCRIPTION
         "Multicast Route Table."
     ::= { ciscoDSGRouting 1 }

multicastRouteEntry OBJECT-TYPE
     SYNTAX  MulticastRouteEntry
     MAX-ACCESS  not-accessible
     STATUS  current
     DESCRIPTION
         "Entry for Multicast Route table."
     INDEX  { multicastRouteIndex }
     ::= { multicastRouteTable 1 }

MulticastRouteEntry ::=  SEQUENCE
{
    multicastRouteIndex                        Integer32,
    multicastRouteV4IPAddr                     IpAddress,
    multicastRouteRowStatus                    RowStatus
}

multicastRouteIndex  OBJECT-TYPE
    SYNTAX  Integer32 (1..16)
    MAX-ACCESS read-only
    STATUS  current
    DESCRIPTION
        "Multicast Route Index."
    ::= { multicastRouteEntry 1 }

multicastRouteV4IPAddr  OBJECT-TYPE
    SYNTAX  IpAddress
    MAX-ACCESS read-write
    STATUS  current
    DESCRIPTION
        "Destination IP Address."
    ::= { multicastRouteEntry 2 }

multicastRouteRowStatus  OBJECT-TYPE
    SYNTAX  RowStatus
    MAX-ACCESS read-write
    STATUS  current
    DESCRIPTION
        "To be used for creating and deleting rows in this table."
    ::= { multicastRouteEntry 3 }

--**************************************
-- Static Route Table
--**************************************
staticRouteTable  OBJECT-TYPE
     SYNTAX  SEQUENCE OF StaticRouteEntry
     MAX-ACCESS not-accessible
     STATUS  current
     DESCRIPTION
         "Static Route Table."
     ::= { ciscoDSGRouting 2 }

staticRouteEntry OBJECT-TYPE
     SYNTAX  StaticRouteEntry
     MAX-ACCESS  not-accessible
     STATUS  current
     DESCRIPTION
         "Entry for Static Route table."
     INDEX  { staticRouteIndex }
     ::= { staticRouteTable 1 }

StaticRouteEntry ::=  SEQUENCE
{
    staticRouteIndex                         Integer32,
    staticRouteV4IPAddr                      IpAddress,
    staticRouteV4Mask                        Integer32,
    staticRouteV4Gateway                     IpAddress,
    staticRoutePort1Enable                   INTEGER,
    staticRoutePort2Enable                   INTEGER,
    staticRoutePort3Enable                   INTEGER,
    staticRouteRowStatus                     RowStatus
}

staticRouteIndex  OBJECT-TYPE
    SYNTAX  Integer32 (1..20)
    MAX-ACCESS read-only
    STATUS  current
    DESCRIPTION
        "Static Route Index."
    ::= { staticRouteEntry 1 }

staticRouteV4IPAddr  OBJECT-TYPE
    SYNTAX  IpAddress
    MAX-ACCESS read-write
    STATUS  current
    DESCRIPTION
        "Destination IP Address."
    ::= { staticRouteEntry 2 }

staticRouteV4Mask  OBJECT-TYPE
    SYNTAX  Integer32 (8..30)
    MAX-ACCESS read-write
    STATUS  current
    DESCRIPTION
        "Destination Network Mask"
    ::= { staticRouteEntry 3 }

staticRouteV4Gateway  OBJECT-TYPE
    SYNTAX  IpAddress
    MAX-ACCESS read-write
    STATUS  current
    DESCRIPTION
        "Gateway IP Address."
    ::= { staticRouteEntry 4 }

staticRoutePort1Enable  OBJECT-TYPE
    SYNTAX  INTEGER {
                        no(1),
                        yes(2)
                    }
    MAX-ACCESS read-write
    STATUS  current
    DESCRIPTION
        "Applicable for Port 1."
    ::= { staticRouteEntry 5 }

staticRoutePort2Enable  OBJECT-TYPE
    SYNTAX  INTEGER {
                        no(1),
                        yes(2)
                    }
    MAX-ACCESS read-write
    STATUS  current
    DESCRIPTION
        "Applicable for Port 2."
    ::= { staticRouteEntry 6 }

staticRoutePort3Enable  OBJECT-TYPE
    SYNTAX  INTEGER {
                        no(1),
                        yes(2)
                    }
    MAX-ACCESS read-write
    STATUS  current
    DESCRIPTION
        "Applicable for Port 3."
    ::= { staticRouteEntry 7 }

staticRouteRowStatus  OBJECT-TYPE
    SYNTAX  RowStatus
    MAX-ACCESS read-write
    STATUS  current
    DESCRIPTION
        "To be used for creating and deleting rows in this table."
    ::= { staticRouteEntry 8 }

--**************************************
-- Unicast Route Table
--**************************************
unicastRoutesTable  OBJECT-TYPE
     SYNTAX  SEQUENCE OF UnicastRoutesEntry
     MAX-ACCESS not-accessible
     STATUS  current
     DESCRIPTION
         "Unicast Route Table."
     ::= { ciscoDSGRouting 3 }

unicastRoutesEntry OBJECT-TYPE
     SYNTAX  UnicastRoutesEntry
     MAX-ACCESS  not-accessible
     STATUS  current
     DESCRIPTION
         "Entry for Unicast Route table."
     INDEX  { unicastRoutesIndex }
     ::= { unicastRoutesTable 1 }

UnicastRoutesEntry ::=  SEQUENCE
{
    unicastRoutesIndex                        Integer32,
    unicastRoutesPortID                       Integer32,
    unicastRoutesV4IPAddr                     IpAddress,
    unicastRoutesV4Mask                       Integer32,
    unicastRoutesV4Gateway                    IpAddress,
    unicastRoutesMTU                          Counter32,
    unicastRoutesTTL                          Counter32,
    unicastRoutesGWOrHost                     INTEGER,
    unicastRoutesType                         INTEGER
}

unicastRoutesIndex  OBJECT-TYPE
    SYNTAX  Integer32 (1..30)
    MAX-ACCESS read-only
    STATUS  current
    DESCRIPTION
        "Unicast Route Index."
    ::= { unicastRoutesEntry 1 }

unicastRoutesPortID  OBJECT-TYPE
    SYNTAX  Integer32 (1..3)
    MAX-ACCESS read-only
    STATUS  current
    DESCRIPTION
        "Port ID."
    ::= { unicastRoutesEntry 2 }

unicastRoutesV4IPAddr  OBJECT-TYPE
    SYNTAX  IpAddress
    MAX-ACCESS read-only
    STATUS  current
    DESCRIPTION
        "Destination IP Address."
    ::= { unicastRoutesEntry 3 }

unicastRoutesV4Mask  OBJECT-TYPE
    SYNTAX  Integer32 (0..32)
    MAX-ACCESS read-only
    STATUS  current
    DESCRIPTION
        "Destination IP Address."
    ::= { unicastRoutesEntry 4 }

unicastRoutesV4Gateway  OBJECT-TYPE
    SYNTAX  IpAddress
    MAX-ACCESS read-only
    STATUS  current
    DESCRIPTION
        "Destination IP Gateway."
    ::= { unicastRoutesEntry 5 }

unicastRoutesMTU  OBJECT-TYPE
    SYNTAX  Counter32
    MAX-ACCESS read-only
    STATUS  current
    DESCRIPTION
        "MTU."
    ::= { unicastRoutesEntry 6 }

unicastRoutesTTL  OBJECT-TYPE
    SYNTAX  Counter32
    MAX-ACCESS read-only
    STATUS  current
    DESCRIPTION
        "TTL (ms)."
    ::= { unicastRoutesEntry 7 }

unicastRoutesGWOrHost  OBJECT-TYPE
    SYNTAX  INTEGER {
                        gateway(1),
                        host(2)
                    }
    MAX-ACCESS read-only
    STATUS  current
    DESCRIPTION
        "Gateway or Host."
    ::= { unicastRoutesEntry 8 }

unicastRoutesType  OBJECT-TYPE
    SYNTAX  INTEGER {
                        dynamic(1),
                        static(2)
                    }
    MAX-ACCESS read-only
    STATUS  current
    DESCRIPTION
        "Route Type."
    ::= { unicastRoutesEntry 9 }

END
