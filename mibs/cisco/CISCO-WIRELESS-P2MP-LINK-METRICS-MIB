-- *********************************************************************
-- CISCO-WIRELESS-P2MP-LINK-METRICS-MIB.my:  Cisco Wireless Radio Point
-- to MultiPoint Lins Metrics
-- MIB.

-- January 2000, Allan Figueredo

-- Copyright (c) 2005 by Cisco Systems, Inc.
-- All rights reserved.

-- ********************************************************************

CISCO-WIRELESS-P2MP-LINK-METRICS-MIB DEFINITIONS ::= BEGIN

IMPORTS
    MODULE-IDENTITY,
    OBJECT-TYPE,
    Counter32,
    Integer32,
    Gauge32,
    NOTIFICATION-TYPE,
    Unsigned32
        FROM SNMPv2-SMI
    TimeInterval,
    MacAddress
        FROM SNMPv2-TC
    MODULE-COMPLIANCE,
    OBJECT-GROUP,
    NOTIFICATION-GROUP
        FROM SNMPv2-CONF
    ifIndex
        FROM IF-MIB
    CwrCwErrorFreeSecond,
    WirelessGauge64,
    CwrCwErroredSecond,
    CwrCwSeverelyErroredSecond,
    CwrCwConsecutiveSevErrSecond,
    CwrCwDegradedSecond,
    CwrFixedPointScale,
    CwrFixedPointPrecision,
    CwrFixedPointValue,
    CwrPercentageValue,
    CwrUpdateTime
        FROM CISCO-WIRELESS-TC-MIB
    ciscoMgmt
        FROM CISCO-SMI;

ciscoWirelessLinkMetricsMIB MODULE-IDENTITY
    LAST-UPDATED    "200601041003Z"
    ORGANIZATION    "Cisco Systems Inc."
    CONTACT-INFO
            "Cisco Systems
            Customer Service

            Postal: 170 W Tasman Drive
               San Jose, CA  95134
               USA

               Tel: +1 800 553-NETS
               E-mail: firestorm-sw@cisco.com"
    DESCRIPTION
            "This is the MIB Module for the Cisco Wireless Radio
            Point to MultiPoint interface link metrics
            specification.

    Glossary

    The following terms are used in the MIB definitions below.

    Radio Interface:  The interface that provides wireless communication
                      features.
    Radio Link:       The bi-directional wireless link between two
                      communicating wireless radios.
    Radio PHY:        Represents the transmission characteristics of the
                      Radio link.

    Link Admin Up:    This is the system time when the link is configured
                      to be 'administratively up'. The user can configure
                      the link to be up either by executing a 'no shut'
                      command via the CLI or by setting the ifAdminStatus
                      object in the IF-MIB to 'up(1)' via SNMP.

    Cisco Wireless MIB Organization

    The Cisco Wireless Point to Multipoint Radio Link Metrics MIB is
    divided into 2 main groups.

    Head End:        These objects are supported on the Head End only.
    Subscriber Unit: These objects are supported on the Subscriber
                     unit only."

    REVISION        "200601041003Z"
    DESCRIPTION
            "Imported Unsigned32 from SNMPv2-SMI."
    REVISION        "200002141910Z"
    DESCRIPTION
            "The initial version of this MIB module."
    ::= { ciscoMgmt 181 }

-- The Cisco Wireless P2MP Radio Link Metrics MIB Tree
p2mpLinkMetricsGroup OBJECT IDENTIFIER
    ::= { ciscoWirelessLinkMetricsMIB 1 }

p2mpSuLinkMetricsGroup OBJECT IDENTIFIER
    ::= { ciscoWirelessLinkMetricsMIB 2 }

p2mpHeLinkMetricsGroup OBJECT IDENTIFIER
    ::= { ciscoWirelessLinkMetricsMIB 3 }

p2mpMetricsPrecisionTable OBJECT-TYPE
    SYNTAX          SEQUENCE OF P2mpMetricsPrecisionEntry
    MAX-ACCESS      not-accessible
    STATUS          current
    DESCRIPTION
            "This table contains the precision and scale values to
            be used when interpreting fixed point values in this
            MIB.  This information is encapsulated in a table to
            accomodate for multiple cards in the same system having
            different precision values.
            This table is indexed by the ifIndex for the physical
            card (propDocsWirelessMaclayer).  The user can refer to
            the entAliasMappingTable in the ENTITY-MIB to determine
            the upstream/downstream channels associated with
            each card."
    ::= { p2mpLinkMetricsGroup 1 }

p2mpMetricsPrecisionEntry OBJECT-TYPE
    SYNTAX          P2mpMetricsPrecisionEntry
    MAX-ACCESS      not-accessible
    STATUS          current
    DESCRIPTION
            "This represents one entry in the
            p2mpMetricsPrecisionTable. This table is indexed by
            the ifIndex of propDocsWirelessMaclayer."
    INDEX           { ifIndex }
    ::= { p2mpMetricsPrecisionTable 1 }

P2mpMetricsPrecisionEntry ::= SEQUENCE {
    p2mpLinkMetricsScale      CwrFixedPointScale,
    p2mpLinkMetricsPrecision  CwrFixedPointPrecision
}

p2mpLinkMetricsScale OBJECT-TYPE
    SYNTAX          CwrFixedPointScale
    MAX-ACCESS      read-only
    STATUS          current
    DESCRIPTION
            "This variable indicates the exponent to apply to the
            fixed-point values."
    ::= { p2mpMetricsPrecisionEntry 1 }

p2mpLinkMetricsPrecision OBJECT-TYPE
    SYNTAX          CwrFixedPointPrecision
    MAX-ACCESS      read-only
    STATUS          current
    DESCRIPTION
            "This variable indicates the number of decimal places
            used for precision when interpreting the fixed-point
            values."
    ::= { p2mpMetricsPrecisionEntry 2 }

-- SUBSCRIBER UNIT ONLY!!!!!


-- Definitions:

-- Codeword Error:
-- A codeword with errors in it, that could NOT be corrected.
-- A codeword that cannot be corrected is dropped so reducing the
-- total data throughput.

-- Error Free Second (CwrCwErrorFreeSecond):
-- A Codeword Error Free Second (EFS) is defined as a second when
-- the radio link was synchronized and no codeword errors detected
-- on the link.

-- Errored Second (CwrCwErroredSecond):
-- A Codeword Errored Second (ES) is defined as a second when the
-- radio link was synchronized and 1 or more codeword errors were
-- detected on the link.

-- Severely Errored Second (CwrCwSeverelyErroredSecond):
-- A Codeword Severely Errored Second (SES) is defined as a second
-- when the radio link was synchronized and the number of codeword
-- errors received was greater than the threshold specified by
-- p2mpSuLinkSESThresh.

-- An Available second:
-- Is defined to be 1 second during which the link was available
-- for data transmission/reception. It is equal to:
-- Error Free Seconds + Errored Seconds - Severely Errored Seconds.

-- Sync Loss Seconds:
-- The time in seconds for the two ends of the link to synchronize
-- after the link is configured administratively

-- Unavailable Seconds:
-- Represent the number of seconds that the user wanted the link
-- to be available but was not. It is equal to:
-- Severely Errored Seconds + Sync Loss Seconds.

-- Link Up Seconds :
-- Interval in seconds, between the time the link was
-- administratively configured up and when it was
-- administratively configured down. It is equal to:
-- Available Seconds + Unavailable Seconds.

-- An Operational Second :
-- Is defined as a second during which the ends of a radio link are
-- synchronized and ready for duplex communication.

-- An Operational Hour :
-- Is 3600 operational seconds.

-- Degraded Second (CwrCwDegradedSecond):
-- A Codeword Degraded Second (DS) is defined as a 1 second
-- interval during which the number of codeword errors was between
-- cwrLinkLowCwErrThresh and cwrLinkHighCwErrThresh.

-- Consecutively Severely Errored Second (CwrCwConsecutiveSevErrSecond):
-- A Codeword Consecutively Severely Errored Seconds (CSES) is
-- defined as the metric that measures the number of times a
-- sequence of Codeword Severely Errored Seconds(SES) crosses the
-- cwrLinkCSESThresh value.  It is independent of the length of the
-- SES sequence.  In other words this counter is incremented by one
-- and only one for every such occurrence.
-- This metric measures the stability of the link i.e. if this
-- count is high, it implies that the link is oscillating between
-- usable v/s unusable extremes.


-- This section contains the following information:

-- o) Link Metric Thresholds. This table provides facilities to
-- establish thresholds that control the collection of the link
-- metrics.

-- o) Cumulative link metrics. This table provides cumulative
-- metrics about the link since the last reboot of the radio
-- card.

-- o) 1 Hour Metrics. This includes cumulative values of the
-- metrics for every hour for a maximum duration of 24 hours.
-- The information in table is identical to the information in
-- the 1 Minute Metrics except that the data has been
-- aggregated over 1 hour.

-- o) 1 Minute Metrics. This includes cumulative values of the
-- every minute for a maximum duration of 60 minutes.

-- o) 1 Second Metrics. This table includes updates received from
-- hardware over the last 1 second. This contains hardware
-- reported information cumulated over 1 second.
p2mpSuLinkMetricsThreshTable OBJECT-TYPE
    SYNTAX          SEQUENCE OF P2mpSuLinkMetricsThreshEntry
    MAX-ACCESS      not-accessible
    STATUS          current
    DESCRIPTION
            "This table contains threshold values that are the
            trigger points for controlling the collection of the
            Link Metrics such as Codeword Errored Seconds and
            others."
    ::= { p2mpSuLinkMetricsGroup 1 }

p2mpSuLinkMetricsThreshEntry OBJECT-TYPE
    SYNTAX          P2mpSuLinkMetricsThreshEntry
    MAX-ACCESS      not-accessible
    STATUS          current
    DESCRIPTION
            "This represents one entry in the table.  There exists
            one such entry for every interface in the ifTable which
            has an ifType of propDocsWirelessDownstream.

            Each of these entries are indexed by the value of
            ifIndex as defined in RFC2233."
    INDEX           { ifIndex }
    ::= { p2mpSuLinkMetricsThreshTable 1 }

P2mpSuLinkMetricsThreshEntry ::= SEQUENCE {
    p2mpSuLinkESThresh            Unsigned32,
    p2mpSuLinkDSThresh            CwrPercentageValue,
    p2mpSuLinkSESThresh           CwrPercentageValue,
    p2mpSuLinkCSESThresh          Unsigned32,
    p2mpSuLink1HrESAlarmThresh    Unsigned32,
    p2mpSuLink1HrSESAlarmThresh   Unsigned32,
    p2mpSuLink1HrCSESAlarmThresh  Unsigned32,
    p2mpSuLink1HrDCSAlarmThresh   Unsigned32
}

p2mpSuLinkESThresh OBJECT-TYPE
    SYNTAX          Unsigned32
    MAX-ACCESS      read-write
    STATUS          current
    DESCRIPTION
            "When the number of Codeword Errors detected in a single
            Operational second is greater than this value, that
            second  is  counted as an Errored Second."
    ::= { p2mpSuLinkMetricsThreshEntry 1 }

p2mpSuLinkDSThresh OBJECT-TYPE
    SYNTAX          CwrPercentageValue
    UNITS           "0.00001 percent"
    MAX-ACCESS      read-write
    STATUS          current
    DESCRIPTION
            "When the percentage of codeword errors detected to the
            total codewords received in one second is equal to or
            greater than this value, and less than
            p2mpLinkSESThresh, the second is counted as a Codeword
            Degraded Second."
    ::= { p2mpSuLinkMetricsThreshEntry 2 }

p2mpSuLinkSESThresh OBJECT-TYPE
    SYNTAX          CwrPercentageValue
    UNITS           "0.00001 percent"
    MAX-ACCESS      read-write
    STATUS          current
    DESCRIPTION
            "When the percentage of codeword errors detected to
            the total codewords received in one second equals or
            exceeds this value, that second is counted as a
            Severely Errored Second."
    ::= { p2mpSuLinkMetricsThreshEntry 3 }

p2mpSuLinkCSESThresh OBJECT-TYPE
    SYNTAX          Unsigned32
    MAX-ACCESS      read-write
    STATUS          current
    DESCRIPTION
            "When the number of severely errored codewords detected
            consecutively in one second equals or exceeds this
            value, the second is counted as a Consecutively
            Severely Errored Second."
    ::= { p2mpSuLinkMetricsThreshEntry 4 }

p2mpSuLink1HrESAlarmThresh OBJECT-TYPE
    SYNTAX          Unsigned32
    MAX-ACCESS      read-write
    STATUS          current
    DESCRIPTION
            "This object specifies the one hour Codeword Error
            Second threshold. When the number of Codeword Error
            Seconds in a 1 Operational Hour period exceeds this
            value, the p2mpSuErrSecAlarmTrap trap will be generated.
            Time measurement starts after the first operational
            second."
    ::= { p2mpSuLinkMetricsThreshEntry 5 }

p2mpSuLink1HrSESAlarmThresh OBJECT-TYPE
    SYNTAX          Unsigned32
    MAX-ACCESS      read-write
    STATUS          current
    DESCRIPTION
            "This object specifies the one hour Codeword Severely
            Errored Seconds        threshold. When the number of Codeword
            Severely Errored Seconds in a 1 Operational Hour period
            exceeds this value, the p2mpSuSevErrSecAlarmTrap trap
            will be generated. Time measurement starts after the
            first operational second."
    ::= { p2mpSuLinkMetricsThreshEntry 6 }

p2mpSuLink1HrCSESAlarmThresh OBJECT-TYPE
    SYNTAX          Unsigned32
    MAX-ACCESS      read-write
    STATUS          current
    DESCRIPTION
            "This object specifies the one hour Codeword
            Consecutively Severely Errored Seconds threshold. When
            the number of Codeword Severely Errored Seconds in a 1
            Operational Hour period exceeds this value, the
            p2mpSuConsecSevErrSecAlarmTrap trap will be generated.
            Time measurement starts        after the first operational
            second."
    ::= { p2mpSuLinkMetricsThreshEntry 7 }

p2mpSuLink1HrDCSAlarmThresh OBJECT-TYPE
    SYNTAX          Unsigned32
    MAX-ACCESS      read-write
    STATUS          current
    DESCRIPTION
            "This object specifies the one hour Degraded Codeword
            Seconds threshold. When the number of Degraded Codeword
            Seconds in a 1 Operational Hour period exceeds this
            value, the p2mpSuDegradedSecAlarmTrap trap will be
            generated. Time measurement starts after the first
            operational second."
    ::= { p2mpSuLinkMetricsThreshEntry 8 }

p2mpSu1SecMetricsTable OBJECT-TYPE
    SYNTAX          SEQUENCE OF P2mpSu1SecMetricsEntry
    MAX-ACCESS      not-accessible
    STATUS          current
    DESCRIPTION
            "This table contains metrics collected over the duration
            of one second.

            This table will have a maximum of 60 entries providing
            cumulative status of the link, identified by ifIndex of
            propDocsWirelessDownstream, over the past one minute.

            This table is updated once every second.  After 60
            seconds, only the latest 60 entries will be stored in
            the table."
    ::= { p2mpSuLinkMetricsGroup 2 }

p2mpSu1SecMetricsEntry OBJECT-TYPE
    SYNTAX          P2mpSu1SecMetricsEntry
    MAX-ACCESS      not-accessible
    STATUS          current
    DESCRIPTION
            "This represents one entry in the p2mpSu1SecMetricsTable
            indexed by the ifIndex of propDocsWirelessDownstream and
            p2mpSu1SecIndex.

            The first entry in the table (p2mpSu1SecIndex = 1)
            represents the chronologically oldest data available."
    INDEX           {
                        ifIndex,
                        p2mpSu1SecIndex
                    }
    ::= { p2mpSu1SecMetricsTable 1 }

P2mpSu1SecMetricsEntry ::= SEQUENCE {
    p2mpSu1SecIndex              Integer32,
    p2mpSu1SecUpdateTime         CwrUpdateTime,
    p2mpSu1SecType               INTEGER,
    p2mpSu1SecTotalCodewords     WirelessGauge64,
    p2mpSu1SecTotalErrCodewords  WirelessGauge64,
    p2mpSu1SecValidDataPkt       Counter32
}

p2mpSu1SecIndex OBJECT-TYPE
    SYNTAX          Integer32 (1..60)
    MAX-ACCESS      not-accessible
    STATUS          current
    DESCRIPTION
            "This object, along with ifIndex, identifies exactly one
            entry in the table."
    ::= { p2mpSu1SecMetricsEntry 1 }

p2mpSu1SecUpdateTime OBJECT-TYPE
    SYNTAX          CwrUpdateTime
    UNITS           "seconds"
    MAX-ACCESS      read-only
    STATUS          current
    DESCRIPTION
            "This object represents time in seconds since system
            power up at which time this entry was last updated."
    ::= { p2mpSu1SecMetricsEntry 2 }

p2mpSu1SecType OBJECT-TYPE
    SYNTAX          INTEGER {
                        unknown(0),
                        errorFree(1),
                        errored(2),
                        degraded(3),
                        sevErrored(4),
                        syncLoss(5)
                    }
    MAX-ACCESS      read-only
    STATUS          current
    DESCRIPTION
            "This object identifies the nature of the measured
            second."
    ::= { p2mpSu1SecMetricsEntry 3 }

p2mpSu1SecTotalCodewords OBJECT-TYPE
    SYNTAX          WirelessGauge64
    MAX-ACCESS      read-only
    STATUS          current
    DESCRIPTION
            "This object represents the total number of codewords
            received by this radio link from the last Link Admin Up
            time until the current operational second."
    ::= { p2mpSu1SecMetricsEntry 4 }

p2mpSu1SecTotalErrCodewords OBJECT-TYPE
    SYNTAX          WirelessGauge64
    MAX-ACCESS      read-only
    STATUS          current
    DESCRIPTION
            "This object represents the total number of errored
            codewords received by this radio link from the last
            Link Admin Up time until the current operational
            second."
    ::= { p2mpSu1SecMetricsEntry 5 }

p2mpSu1SecValidDataPkt OBJECT-TYPE
    SYNTAX          Counter32
    MAX-ACCESS      read-only
    STATUS          current
    DESCRIPTION
            "This variable indicates the number of data packets
            received without any bit errors from the last Link Admin
            Up time until the current operational second."
    ::= { p2mpSu1SecMetricsEntry 6 }

p2mpSu1MinMetricsTable OBJECT-TYPE
    SYNTAX          SEQUENCE OF P2mpSu1MinMetricsEntry
    MAX-ACCESS      not-accessible
    STATUS          current
    DESCRIPTION
            "This table contains metrics collected over the duration
            of one minute.

            This table will have a maximum of 60 entries providing
            cumulative statistics of the link, identified by ifIndex
            of propDocsWirelessDownstream, over the past one hour.

            This table is updated once every minute."
    ::= { p2mpSuLinkMetricsGroup 3 }

p2mpSu1MinMetricsEntry OBJECT-TYPE
    SYNTAX          P2mpSu1MinMetricsEntry
    MAX-ACCESS      not-accessible
    STATUS          current
    DESCRIPTION
            "This represents one entry in the p2mpSu1MinMetricsTable
            indexed by ifIndex of propDocsWirelessDownstream and
            p2mpSu1MinIndex.

            The first entry in the table (p2mpSu1MinIndex = 1)
            represents the chronologically oldest data available."
    INDEX           {
                        ifIndex,
                        p2mpSu1MinIndex
                    }
    ::= { p2mpSu1MinMetricsTable 1 }

P2mpSu1MinMetricsEntry ::= SEQUENCE {
    p2mpSu1MinIndex                Integer32,
    p2mpSu1MinUpdateTime           CwrUpdateTime,
    p2mpSu1MinTotalCodewords       WirelessGauge64,
    p2mpSu1MinTotalErrCodewords    WirelessGauge64,
    p2mpSu1MinValidDataPkt         Counter32,
    p2mpSu1MinErrorFreeSeconds     CwrCwErrorFreeSecond,
    p2mpSu1MinErroredSeconds       CwrCwErroredSecond,
    p2mpSu1MinDegradedSeconds      CwrCwDegradedSecond,
    p2mpSu1MinSevErroredSeconds    CwrCwSeverelyErroredSecond,
    p2mpSu1MinConsecSevErrSeconds  CwrCwConsecutiveSevErrSecond,
    p2mpSu1MinSyncLossSeconds      Counter32,
    p2mpSu1MinTxPowerMax           CwrFixedPointValue,
    p2mpSu1MinTxPowerMin           CwrFixedPointValue,
    p2mpSu1MinTxPowerAvg           CwrFixedPointValue,
    p2mpSu1MinMainAntRxPowerMax    CwrFixedPointValue,
    p2mpSu1MinMainAntRxPowerMin    CwrFixedPointValue,
    p2mpSu1MinMainAntRxPowerAvg    CwrFixedPointValue,
    p2mpSu1MinDivAntRxPowerMax     CwrFixedPointValue,
    p2mpSu1MinDivAntRxPowerMin     CwrFixedPointValue,
    p2mpSu1MinDivAntRxPowerAvg     CwrFixedPointValue
}

p2mpSu1MinIndex OBJECT-TYPE
    SYNTAX          Integer32 (1..60)
    MAX-ACCESS      not-accessible
    STATUS          current
    DESCRIPTION
            "This object, along with ifIndex, identifies exactly one
            entry in the table."
    ::= { p2mpSu1MinMetricsEntry 1 }

p2mpSu1MinUpdateTime OBJECT-TYPE
    SYNTAX          CwrUpdateTime
    UNITS           "seconds"
    MAX-ACCESS      read-only
    STATUS          current
    DESCRIPTION
            "This object represents time in seconds since system
            power up until the time this entry was last updated."
    ::= { p2mpSu1MinMetricsEntry 2 }

p2mpSu1MinTotalCodewords OBJECT-TYPE
    SYNTAX          WirelessGauge64
    MAX-ACCESS      read-only
    STATUS          current
    DESCRIPTION
            "This object represents the cumulative sum of received
            codewords from the last Link Admin Up time until the
            current operational second."
    ::= { p2mpSu1MinMetricsEntry 3 }

p2mpSu1MinTotalErrCodewords OBJECT-TYPE
    SYNTAX          WirelessGauge64
    MAX-ACCESS      read-only
    STATUS          current
    DESCRIPTION
            "This object represents the cumulative sum of received
            errored codewords from the last Link Admin Up time until
            the current operational second."
    ::= { p2mpSu1MinMetricsEntry 4 }

p2mpSu1MinValidDataPkt OBJECT-TYPE
    SYNTAX          Counter32
    MAX-ACCESS      read-only
    STATUS          current
    DESCRIPTION
            "This variable indicates the number of data packets
            received without any bit errors from the last Link Admin
            Up time until the current operational second."
    ::= { p2mpSu1MinMetricsEntry 5 }

p2mpSu1MinErrorFreeSeconds OBJECT-TYPE
    SYNTAX          CwrCwErrorFreeSecond
    MAX-ACCESS      read-only
    STATUS          current
    DESCRIPTION
            "This object represents the cumulative Codeword Error
            Free Seconds (EFS) detected from the last Link Admin Up
            time until the current operational second."
    ::= { p2mpSu1MinMetricsEntry 6 }

p2mpSu1MinErroredSeconds OBJECT-TYPE
    SYNTAX          CwrCwErroredSecond
    MAX-ACCESS      read-only
    STATUS          current
    DESCRIPTION
            "This object represents the cumulative Codeword Errored
            Seconds (ES) detected from the last Link Admin Up time
            until the current operational second."
    ::= { p2mpSu1MinMetricsEntry 7 }

p2mpSu1MinDegradedSeconds OBJECT-TYPE
    SYNTAX          CwrCwDegradedSecond
    MAX-ACCESS      read-only
    STATUS          current
    DESCRIPTION
            "This object represents the cumulative Codeword Degraded
            Seconds (DS) detected from the last Link Admin Up time
            until the current operational second."
    ::= { p2mpSu1MinMetricsEntry 8 }

p2mpSu1MinSevErroredSeconds OBJECT-TYPE
    SYNTAX          CwrCwSeverelyErroredSecond
    MAX-ACCESS      read-only
    STATUS          current
    DESCRIPTION
            "This object represents the cumulative Codeword Severely
            Errored Seconds (SES) detected from the last Link Admin
            Up time until the current operational second."
    ::= { p2mpSu1MinMetricsEntry 9 }

p2mpSu1MinConsecSevErrSeconds OBJECT-TYPE
    SYNTAX          CwrCwConsecutiveSevErrSecond
    MAX-ACCESS      read-only
    STATUS          current
    DESCRIPTION
            "This object represents the cumulative Codeword
            Consecutively Severely Errored Seconds (CSES) detected
            from the last Link Admin Up time until the current
            operational second."
    ::= { p2mpSu1MinMetricsEntry 10 }

p2mpSu1MinSyncLossSeconds OBJECT-TYPE
    SYNTAX          Counter32
    MAX-ACCESS      read-only
    STATUS          current
    DESCRIPTION
            "This object represents the cumulative number of seconds
            from the last Link Admin Up time to the current
            operational minute the link was out of synchronization."
    ::= { p2mpSu1MinMetricsEntry 11 }

p2mpSu1MinTxPowerMax OBJECT-TYPE
    SYNTAX          CwrFixedPointValue
    UNITS           "dBm - decibel milliwatts"
    MAX-ACCESS      read-only
    STATUS          current
    DESCRIPTION
            "This variable represents the maximum transmit power of
            the subscriber unit measured during the current
            operational minute. This is not a cumulative value."
    ::= { p2mpSu1MinMetricsEntry 12 }

p2mpSu1MinTxPowerMin OBJECT-TYPE
    SYNTAX          CwrFixedPointValue
    UNITS           "dBm - decibel milliwatts"
    MAX-ACCESS      read-only
    STATUS          current
    DESCRIPTION
            "This variable indicates the minimum transmit power of
            the subscriber unit measured during the current
            operational minute. This is not a cumulative value."
    ::= { p2mpSu1MinMetricsEntry 13 }

p2mpSu1MinTxPowerAvg OBJECT-TYPE
    SYNTAX          CwrFixedPointValue
    UNITS           "dBm - decibel milliwatts"
    MAX-ACCESS      read-only
    STATUS          current
    DESCRIPTION
            "This variable indicates the average measured transmit
            power of the subscriber unit measured during the
            current operational minute. This is not a cumulative
            value."
    ::= { p2mpSu1MinMetricsEntry 14 }

p2mpSu1MinMainAntRxPowerMax OBJECT-TYPE
    SYNTAX          CwrFixedPointValue
    UNITS           "dBm - decibel milliwatts"
    MAX-ACCESS      read-only
    STATUS          current
    DESCRIPTION
            "This variable indicates the maximum receive power
            measured at the main antenna during the current
            operational minute.  This is not a cumulative value."
    ::= { p2mpSu1MinMetricsEntry 15 }

p2mpSu1MinMainAntRxPowerMin OBJECT-TYPE
    SYNTAX          CwrFixedPointValue
    UNITS           "dBm - decibel milliwatts"
    MAX-ACCESS      read-only
    STATUS          current
    DESCRIPTION
            "This variable indicates the minimum receive power
            measured at the main antenna during the current
            operational minute.  This is not a cumulative value."
    ::= { p2mpSu1MinMetricsEntry 16 }

p2mpSu1MinMainAntRxPowerAvg OBJECT-TYPE
    SYNTAX          CwrFixedPointValue
    UNITS           "dBm - decibel milliwatts"
    MAX-ACCESS      read-only
    STATUS          current
    DESCRIPTION
            "This variable indicates the average receive power
            measured at the main antenna during the current
            operational minute.  This is not a cumulative value."
    ::= { p2mpSu1MinMetricsEntry 17 }

p2mpSu1MinDivAntRxPowerMax OBJECT-TYPE
    SYNTAX          CwrFixedPointValue
    UNITS           "dBm - decibel milliwatts"
    MAX-ACCESS      read-only
    STATUS          current
    DESCRIPTION
            "This variable indicates the maximum receive power
            measured at the diversity antenna during the current
            operational minute.  This is not a cumulative value."
    ::= { p2mpSu1MinMetricsEntry 18 }

p2mpSu1MinDivAntRxPowerMin OBJECT-TYPE
    SYNTAX          CwrFixedPointValue
    UNITS           "dBm - decibel milliwatts"
    MAX-ACCESS      read-only
    STATUS          current
    DESCRIPTION
            "This variable indicates the minimum receive power
            measured at the diversity antenna during the current
            operational minute.  This is not a cumulative value."
    ::= { p2mpSu1MinMetricsEntry 19 }

p2mpSu1MinDivAntRxPowerAvg OBJECT-TYPE
    SYNTAX          CwrFixedPointValue
    UNITS           "dBm - decibel milliwatts"
    MAX-ACCESS      read-only
    STATUS          current
    DESCRIPTION
            "This variable indicates the average received power
            measured at the diversity antenna during the current
            operational minute.  This is not a cumulative value."
    ::= { p2mpSu1MinMetricsEntry 20 }

p2mpSu1HrMetricsTable OBJECT-TYPE
    SYNTAX          SEQUENCE OF P2mpSu1HrMetricsEntry
    MAX-ACCESS      not-accessible
    STATUS          current
    DESCRIPTION
            "This table contains metrics collected over the duration
            of one hour.

            This table will have a maximum of 24 entries providing
            cumulative status of the link, identified by ifIndex,
            over the past 24 hours.

            This table is updated once every hour."
    ::= { p2mpSuLinkMetricsGroup 4 }

p2mpSu1HrMetricsEntry OBJECT-TYPE
    SYNTAX          P2mpSu1HrMetricsEntry
    MAX-ACCESS      not-accessible
    STATUS          current
    DESCRIPTION
            "This represents one entry in the p2mpSu1HrMetricsTable
            indexed by ifIndex of propDocsWirelessDownstream and
            p2mpSu1HrIndex.

            The first entry in the table (p2mpSu1HrIndex = 1)
            represents the chronologically oldest data available."
    INDEX           {
                        ifIndex,
                        p2mpSu1HrIndex
                    }
    ::= { p2mpSu1HrMetricsTable 1 }

P2mpSu1HrMetricsEntry ::= SEQUENCE {
    p2mpSu1HrIndex               Integer32,
    p2mpSu1HrUpdateTime          CwrUpdateTime,
    p2mpSu1HrTotalCodewords      WirelessGauge64,
    p2mpSu1HrTotalErrCodewords   WirelessGauge64,
    p2mpSu1HrValidDataPkt        Counter32,
    p2mpSu1HrErrorFreeSeconds    CwrCwErrorFreeSecond,
    p2mpSu1HrErroredSeconds      CwrCwErroredSecond,
    p2mpSu1HrSevErroredSeconds   CwrCwSeverelyErroredSecond,
    p2mpSu1HrConsecSvErrSeconds  CwrCwConsecutiveSevErrSecond,
    p2mpSu1HrSyncLossSeconds     Counter32,
    p2mpSu1HrDegradedSeconds     CwrCwDegradedSecond,
    p2mpSu1HrTxPowerMax          CwrFixedPointValue,
    p2mpSu1HrTxPowerMin          CwrFixedPointValue,
    p2mpSu1HrTxPowerAvg          CwrFixedPointValue,
    p2mpSu1HrMainAntRxPowerMax   CwrFixedPointValue,
    p2mpSu1HrMainAntRxPowerMin   CwrFixedPointValue,
    p2mpSu1HrMainAntRxPowerAvg   CwrFixedPointValue,
    p2mpSu1HrDivAntRxPowerMax    CwrFixedPointValue,
    p2mpSu1HrDivAntRxPowerMin    CwrFixedPointValue,
    p2mpSu1HrDivAntRxPowerAvg    CwrFixedPointValue
}

p2mpSu1HrIndex OBJECT-TYPE
    SYNTAX          Integer32 (1..24)
    MAX-ACCESS      not-accessible
    STATUS          current
    DESCRIPTION
            "This object, along with ifIndex, identifies exactly one
            entry in the table."
    ::= { p2mpSu1HrMetricsEntry 1 }

p2mpSu1HrUpdateTime OBJECT-TYPE
    SYNTAX          CwrUpdateTime
    UNITS           "seconds"
    MAX-ACCESS      read-only
    STATUS          current
    DESCRIPTION
            "This object represents time in seconds since system
            power up at which time this entry was last updated."
    ::= { p2mpSu1HrMetricsEntry 2 }

p2mpSu1HrTotalCodewords OBJECT-TYPE
    SYNTAX          WirelessGauge64
    MAX-ACCESS      read-only
    STATUS          current
    DESCRIPTION
            "This object represents the total received codewords
            detected from the last Link Admin Up time until the
            current operational hour."
    ::= { p2mpSu1HrMetricsEntry 3 }

p2mpSu1HrTotalErrCodewords OBJECT-TYPE
    SYNTAX          WirelessGauge64
    MAX-ACCESS      read-only
    STATUS          current
    DESCRIPTION
            "This object represents the total number of errored
            codewords received from the last Link Admin Up time
            until the current operational hour."
    ::= { p2mpSu1HrMetricsEntry 4 }

p2mpSu1HrValidDataPkt OBJECT-TYPE
    SYNTAX          Counter32
    MAX-ACCESS      read-only
    STATUS          current
    DESCRIPTION
            "This variable indicates the number of data packets
            received without any bit errors from the last Link Admin
            Up time until the current operational hour."
    ::= { p2mpSu1HrMetricsEntry 5 }

p2mpSu1HrErrorFreeSeconds OBJECT-TYPE
    SYNTAX          CwrCwErrorFreeSecond
    MAX-ACCESS      read-only
    STATUS          current
    DESCRIPTION
            "This object represents the cumulative Codeword Error
            Free Seconds (EFS) detected from the last Link Admin Up
            time until the current operational hour."
    ::= { p2mpSu1HrMetricsEntry 6 }

p2mpSu1HrErroredSeconds OBJECT-TYPE
    SYNTAX          CwrCwErroredSecond
    MAX-ACCESS      read-only
    STATUS          current
    DESCRIPTION
            "This object represents the cumulative Codeword Errored
            Seconds (ES) detected from the last Link Admin Up time
            until the current operational hour"
    ::= { p2mpSu1HrMetricsEntry 7 }

p2mpSu1HrSevErroredSeconds OBJECT-TYPE
    SYNTAX          CwrCwSeverelyErroredSecond
    MAX-ACCESS      read-only
    STATUS          current
    DESCRIPTION
            "This object represents the cumulative Codeword Severely
            Errored Seconds (SES) detected from the last Link Admin
            Up time until the current operational hour"
    ::= { p2mpSu1HrMetricsEntry 8 }

p2mpSu1HrConsecSvErrSeconds OBJECT-TYPE
    SYNTAX          CwrCwConsecutiveSevErrSecond
    MAX-ACCESS      read-only
    STATUS          current
    DESCRIPTION
            "This object represents the cumulative Codeword
            Consecutive Severely Errored Seconds (CSES) detected
            from the last Link Admin Up time until the current
            operational hour"
    ::= { p2mpSu1HrMetricsEntry 9 }

p2mpSu1HrSyncLossSeconds OBJECT-TYPE
    SYNTAX          Counter32
    MAX-ACCESS      read-only
    STATUS          current
    DESCRIPTION
            "This object represents the cumulative number of
            seconds from the last Link Admin Up time to the current
            operational hour the link was out of synchronization."
    ::= { p2mpSu1HrMetricsEntry 10 }

p2mpSu1HrDegradedSeconds OBJECT-TYPE
    SYNTAX          CwrCwDegradedSecond
    MAX-ACCESS      read-only
    STATUS          current
    DESCRIPTION
            "This object represents the cumulative Codeword Degraded
            Seconds detected from the last Link Admin Up time until
            the current operational hour"
    ::= { p2mpSu1HrMetricsEntry 11 }

p2mpSu1HrTxPowerMax OBJECT-TYPE
    SYNTAX          CwrFixedPointValue
    UNITS           "dBm - decibel milliwatts"
    MAX-ACCESS      read-only
    STATUS          current
    DESCRIPTION
            "This variable indicates the maximum transmit power
            measured during the current operational hour.  This is
            not a cumulative value."
    ::= { p2mpSu1HrMetricsEntry 12 }

p2mpSu1HrTxPowerMin OBJECT-TYPE
    SYNTAX          CwrFixedPointValue
    UNITS           "dBm - decibel milliwatts"
    MAX-ACCESS      read-only
    STATUS          current
    DESCRIPTION
            "This variable indicates the minimum transmit power
            measured during the current operational hour.  This is
            not a cumulative value."
    ::= { p2mpSu1HrMetricsEntry 13 }

p2mpSu1HrTxPowerAvg OBJECT-TYPE
    SYNTAX          CwrFixedPointValue
    UNITS           "dBm - decibel milliwatts"
    MAX-ACCESS      read-only
    STATUS          current
    DESCRIPTION
            "This variable indicates the average transmit power
            measured during the current operational hour.  This is
            not a cumulative value."
    ::= { p2mpSu1HrMetricsEntry 14 }

p2mpSu1HrMainAntRxPowerMax OBJECT-TYPE
    SYNTAX          CwrFixedPointValue
    UNITS           "dBm - decibel milliwatts"
    MAX-ACCESS      read-only
    STATUS          current
    DESCRIPTION
            "This variable indicates the maximum receive power
            measured at the main antenna during the current
            operational hour.  This is not a cumulative value."
    ::= { p2mpSu1HrMetricsEntry 15 }

p2mpSu1HrMainAntRxPowerMin OBJECT-TYPE
    SYNTAX          CwrFixedPointValue
    UNITS           "dBm - decibel milliwatts"
    MAX-ACCESS      read-only
    STATUS          current
    DESCRIPTION
            "This variable indicates the minimum receive power
            measured at the main antenna during the current
            operational hour.  This is not a cumulative value."
    ::= { p2mpSu1HrMetricsEntry 16 }

p2mpSu1HrMainAntRxPowerAvg OBJECT-TYPE
    SYNTAX          CwrFixedPointValue
    UNITS           "dBm - decibel milliwatts"
    MAX-ACCESS      read-only
    STATUS          current
    DESCRIPTION
            "This variable indicates the average received power
            measured at the main antenna during the current
            operational hour.  This is not a cumulative value."
    ::= { p2mpSu1HrMetricsEntry 17 }

p2mpSu1HrDivAntRxPowerMax OBJECT-TYPE
    SYNTAX          CwrFixedPointValue
    UNITS           "dBm - decibel milliwatts"
    MAX-ACCESS      read-only
    STATUS          current
    DESCRIPTION
            "This variable indicates the maximum receive power
            measured at the diversity antenna during the current
            operational hour.  This is not a cumulative value."
    ::= { p2mpSu1HrMetricsEntry 18 }

p2mpSu1HrDivAntRxPowerMin OBJECT-TYPE
    SYNTAX          CwrFixedPointValue
    UNITS           "dBm - decibel milliwatts"
    MAX-ACCESS      read-only
    STATUS          current
    DESCRIPTION
            "This variable indicates the minimum receive power
            measured at the diversity antenna during the current
            operational hour.  This is not a cumulative value."
    ::= { p2mpSu1HrMetricsEntry 19 }

p2mpSu1HrDivAntRxPowerAvg OBJECT-TYPE
    SYNTAX          CwrFixedPointValue
    UNITS           "dBm - decibel milliwatts"
    MAX-ACCESS      read-only
    STATUS          current
    DESCRIPTION
            "This variable indicates the average received power
            measured at the diversity antenna during the current
            operational hour.  This is not a cumulative value."
    ::= { p2mpSu1HrMetricsEntry 20 }

p2mpSuCumulativeLinkMetricsTable OBJECT-TYPE
    SYNTAX          SEQUENCE OF P2mpSuCumulativeLinkMetricsEntry
    MAX-ACCESS      not-accessible
    STATUS          current
    DESCRIPTION
            "This table contains metrics used to measure the quality
            of the radio link identified by the ifIndex. The metrics
            in this table are cumulated since the last Link Admin Up
            time."
    ::= { p2mpSuLinkMetricsGroup 6 }

p2mpSuCumulativeLinkMetricsEntry OBJECT-TYPE
    SYNTAX          P2mpSuCumulativeLinkMetricsEntry
    MAX-ACCESS      not-accessible
    STATUS          current
    DESCRIPTION
            "There exists one such entry for every interface in the
            ifTable which has an ifType of
            propDocsWirelessDownstream.

            Each of these entries are indexed by the value of
            ifIndex as defined in RFC2233."
    INDEX           { ifIndex }
    ::= { p2mpSuCumulativeLinkMetricsTable 1 }

P2mpSuCumulativeLinkMetricsEntry ::= SEQUENCE {
    p2mpSuAvailableSeconds      Counter32,
    p2mpSuUnAvailableSeconds    Counter32,
    p2mpSuPctAvailSeconds       CwrPercentageValue,
    p2mpSuSyncLossSeconds       Counter32,
    p2mpSuPctErrorFreeSeconds   CwrPercentageValue,
    p2mpSuPctErroredSeconds     CwrPercentageValue,
    p2mpSuPctSevErroredSeconds  CwrPercentageValue,
    p2mpSuPctDegradedSeconds    CwrPercentageValue,
    p2mpSuInitialSyncSeconds    Counter32,
    p2mpSuSyncSuccessCount      Counter32,
    p2mpSuLastSyncSuccessTime   TimeInterval,
    p2mpSuSyncFailureCount      Counter32,
    p2mpSuLastSyncFailTime      TimeInterval,
    p2mpSuSyncMedEffort         Counter32,
    p2mpSuSyncHighEffort        Counter32,
    p2mpSuEffectiveDataRate     Gauge32,
    p2mpSuPercentEfficiency     CwrPercentageValue
}

p2mpSuAvailableSeconds OBJECT-TYPE
    SYNTAX          Counter32
    MAX-ACCESS      read-only
    STATUS          current
    DESCRIPTION
            "This object represents the total number of Available
            Seconds since the last Link Admin Up time.
            It is equal to:
            Error Free Seconds + Errored Seconds - Severely Errored
            Seconds"
    ::= { p2mpSuCumulativeLinkMetricsEntry 1 }

p2mpSuUnAvailableSeconds OBJECT-TYPE
    SYNTAX          Counter32
    MAX-ACCESS      read-only
    STATUS          current
    DESCRIPTION
            "This object represents the total number of seconds
            since the last Link Admin Up time that the link was not
            available for use. It is equal to:
            Severely Errored Seconds + Sync Loss Seconds."
    ::= { p2mpSuCumulativeLinkMetricsEntry 2 }

p2mpSuPctAvailSeconds OBJECT-TYPE
    SYNTAX          CwrPercentageValue
    UNITS           "0.00001 percent"
    MAX-ACCESS      read-only
    STATUS          current
    DESCRIPTION
            "This object represents the ratio of cumulative
            Available seconds to Link Admin Up seconds, expressed
            as a percentage."
    ::= { p2mpSuCumulativeLinkMetricsEntry 3 }

p2mpSuSyncLossSeconds OBJECT-TYPE
    SYNTAX          Counter32
    MAX-ACCESS      read-only
    STATUS          current
    DESCRIPTION
            "This object represents the number of seconds since the
            last Link Admin Up time during which the radio link was
            out of sync with the remote end."
    ::= { p2mpSuCumulativeLinkMetricsEntry 4 }

p2mpSuPctErrorFreeSeconds OBJECT-TYPE
    SYNTAX          CwrPercentageValue
    UNITS           "0.00001 percent"
    MAX-ACCESS      read-only
    STATUS          current
    DESCRIPTION
            "This object represents the ratio of cumulative Codeword
            Error Free Seconds (EFS) to Link Admin Up seconds,
            expressed as a percentage."
    ::= { p2mpSuCumulativeLinkMetricsEntry 5 }

p2mpSuPctErroredSeconds OBJECT-TYPE
    SYNTAX          CwrPercentageValue
    UNITS           "0.00001 percent"
    MAX-ACCESS      read-only
    STATUS          current
    DESCRIPTION
            "This object represents the ratio of cumulative Codeword
            Errored Seconds (ES) to Link Admin Up seconds, expressed
            as a percentage."
    ::= { p2mpSuCumulativeLinkMetricsEntry 6 }

p2mpSuPctSevErroredSeconds OBJECT-TYPE
    SYNTAX          CwrPercentageValue
    UNITS           "0.00001 percent"
    MAX-ACCESS      read-only
    STATUS          current
    DESCRIPTION
            "This object represents the ratio of cumulative Codeword
            Severely Errored Seconds (SES) to Link Admin Up seconds,
            expressed as a percentage."
    ::= { p2mpSuCumulativeLinkMetricsEntry 7 }

p2mpSuPctDegradedSeconds OBJECT-TYPE
    SYNTAX          CwrPercentageValue
    UNITS           "0.00001 percent"
    MAX-ACCESS      read-only
    STATUS          current
    DESCRIPTION
            "This object represents the ratio of degraded seconds
            (DS) to Link Admin Up seconds, expressed as a
            percentage."
    ::= { p2mpSuCumulativeLinkMetricsEntry 8 }

p2mpSuInitialSyncSeconds OBJECT-TYPE
    SYNTAX          Counter32
    MAX-ACCESS      read-only
    STATUS          current
    DESCRIPTION
            "Time spent in acquiring sync for the first time after
            the link is administratively configured up"
    ::= { p2mpSuCumulativeLinkMetricsEntry 9 }

p2mpSuSyncSuccessCount OBJECT-TYPE
    SYNTAX          Counter32
    MAX-ACCESS      read-only
    STATUS          current
    DESCRIPTION
            "This object represents the number of times the
            subscriber unit successfully synchronized with the head
            end."
    ::= { p2mpSuCumulativeLinkMetricsEntry 10 }

p2mpSuLastSyncSuccessTime OBJECT-TYPE
    SYNTAX          TimeInterval
    MAX-ACCESS      read-only
    STATUS          current
    DESCRIPTION
            "This object represents elapsed time since the
            subscriber unit last successfully synchronized with the
            head end."
    ::= { p2mpSuCumulativeLinkMetricsEntry 11 }

p2mpSuSyncFailureCount OBJECT-TYPE
    SYNTAX          Counter32
    MAX-ACCESS      read-only
    STATUS          current
    DESCRIPTION
            "This object represents the number of times the
            subscriber unit attempted, but failed, to synchronize
            with the head end."
    ::= { p2mpSuCumulativeLinkMetricsEntry 12 }

p2mpSuLastSyncFailTime OBJECT-TYPE
    SYNTAX          TimeInterval
    MAX-ACCESS      read-only
    STATUS          current
    DESCRIPTION
            "This object represents elapsed time since the
            subscriber unit last lost synchronization with the
            remote end."
    ::= { p2mpSuCumulativeLinkMetricsEntry 13 }

p2mpSuSyncMedEffort OBJECT-TYPE
    SYNTAX          Counter32
    MAX-ACCESS      read-only
    STATUS          current
    DESCRIPTION
            "This object indicates how many times sync was regained
            (since Link Admin Up time) without the subscriber unit
            having to scan through the channels."
    ::= { p2mpSuCumulativeLinkMetricsEntry 14 }

p2mpSuSyncHighEffort OBJECT-TYPE
    SYNTAX          Counter32
    MAX-ACCESS      read-only
    STATUS          current
    DESCRIPTION
            "This object indicates how many times the channels were
            scanned due to sync loss (after first sync at Link Admin
            Up time)."
    ::= { p2mpSuCumulativeLinkMetricsEntry 15 }

p2mpSuEffectiveDataRate OBJECT-TYPE
    SYNTAX          Gauge32
    MAX-ACCESS      read-only
    STATUS          current
    DESCRIPTION
            "Represents the effective data throughput while the link
            was last synchronized. For a given bandwidth and
            throughput selection, it represents the data throughput
            being achieved."
    ::= { p2mpSuCumulativeLinkMetricsEntry 16 }

p2mpSuPercentEfficiency OBJECT-TYPE
    SYNTAX          CwrPercentageValue
    UNITS           "0.00001 percent"
    MAX-ACCESS      read-only
    STATUS          current
    DESCRIPTION
            "Represents the ratio of total good codewords received
            to the total number of codewords received since Link
            Admin Up, stated as a percentage"
    ::= { p2mpSuCumulativeLinkMetricsEntry 17 }

-- HEAD END ONLY!!!!!

-- The Metrics group is supported at the head end only.
p2mpHeLinkMetricsThreshTable OBJECT-TYPE
    SYNTAX          SEQUENCE OF P2mpHeLinkMetricsThreshEntry
    MAX-ACCESS      not-accessible
    STATUS          current
    DESCRIPTION
            "This table contains thresholds that are the trigger
            points to determine if an excessive number of errored
            codewords are being transmitted.

            The thresholds can be set for each upstream channel.
            This helps determine if a particular upstream channel is
            experiencing excessive errors.

            The thresholds can also be set for all the subscriber
            units communicating with the head end.  These thresholds
            will not be set on a per subscriber basis.  Instead,
            there is only one entry in this table for all the
            subscriber units."
    ::= { p2mpHeLinkMetricsGroup 1 }

p2mpHeLinkMetricsThreshEntry OBJECT-TYPE
    SYNTAX          P2mpHeLinkMetricsThreshEntry
    MAX-ACCESS      not-accessible
    STATUS          current
    DESCRIPTION
            "This represents one entry in the tablei.

            The first entry in this table is applicable to all the
            subscriber units communicating with the head end.  This
            entry uses the ifIndex of propDocsWirelessMaclayer.

            Subsequent entries in this table apply to the upstream
            channels and are indexed by the ifIndex of
            propDocsWirelessUpstream."
    INDEX           { ifIndex }
    ::= { p2mpHeLinkMetricsThreshTable 1 }

P2mpHeLinkMetricsThreshEntry ::= SEQUENCE {
    p2mpHe1HrMinTotalCWThresh  Unsigned32,
    p2mpHe1HrPctErrCWThresh    CwrPercentageValue
}

p2mpHe1HrMinTotalCWThresh OBJECT-TYPE
    SYNTAX          Unsigned32
    MAX-ACCESS      read-write
    STATUS          current
    DESCRIPTION
            "This object specifies the threshold for the minimum
            number of total codewords that should be transmitted in
            an operational hour before the percentage of errored
            codewords is evaluated against the
            p2mpHe1HrPctErrCWThresh."
    ::= { p2mpHeLinkMetricsThreshEntry 1 }

p2mpHe1HrPctErrCWThresh OBJECT-TYPE
    SYNTAX          CwrPercentageValue
    UNITS           "0.00001 percent"
    MAX-ACCESS      read-write
    STATUS          current
    DESCRIPTION
            "This object represents the threshold for the acceptable
            ratio of errored codewords to the total codewords
            transmitted in an operational hour.

            For an Upstream Channel:
            When the percentage of errored codewords to total
            codewords transmitted on a upstream channel crosses this
            threshold, the p2mpHeChPctErrCWThreshTrap is sent out
            (provided the number of total codewords transmitted on
            the upstream channel in an operational hour, exceeds the
            value represented by p2mpHe1HrMinTotalCWThresh).

            For a Subscriber Unit (SU):
            When the percentage of errored codewords to total
            codewords transmitted by a SU crosses this threshold,
            the SU is added to a list of SU's that have also crossed
            this threshold (provided the number of total codewords
            transmitted by the SU exceed the value represented by
            p2mpHe1HrMinTotalCWThresh).  The head end sends out the
            p2mpHeMacPctErrCWThreshTrap to indicate that an SU has
            been added to the 'bad SU list'."
    ::= { p2mpHeLinkMetricsThreshEntry 2 }

p2mpHeBadSuTable OBJECT-TYPE
    SYNTAX          SEQUENCE OF P2mpHeBadSuEntry
    MAX-ACCESS      not-accessible
    STATUS          current
    DESCRIPTION
            "This table lists all the subscriber units who have
            either failed to transmit a minimum number of codewords
            in an operational hour OR have transmitted a total
            number of codewords equal to or greater than
            p2mpHe1HrMinTotalCWThresh but have a codeword error
            percentage (ratio of errored codewords to the total
            number of codewords transmitted) greater than
            p2mpHe1HrPctErrCWThresh."
    ::= { p2mpHeLinkMetricsGroup 2 }

p2mpHeBadSuEntry OBJECT-TYPE
    SYNTAX          P2mpHeBadSuEntry
    MAX-ACCESS      not-accessible
    STATUS          current
    DESCRIPTION
            "This represents one entry in the p2mpHeBadSuTable.
            This entry uses the ifIndex of propDocsWirelessMaclayer.

            An entry is created in this table when a 'bad'
            subscriber unit is detected in the managed system.  The
            entry is removed from this table when the subscriber
            units performance recovers."
    INDEX           {
                        ifIndex,
                        p2mpBadSuIndex
                    }
    ::= { p2mpHeBadSuTable 1 }

P2mpHeBadSuEntry ::= SEQUENCE {
    p2mpBadSuIndex             Integer32,
    p2mpBadSuUpdateTime        CwrUpdateTime,
    p2mpBadSuMacAddress        MacAddress,
    p2mpTotalErroredCodewords  Unsigned32,
    p2mpPctErroredCodewords    Unsigned32
}

p2mpBadSuIndex OBJECT-TYPE
    SYNTAX          Integer32 (1..2147483647)
    MAX-ACCESS      not-accessible
    STATUS          current
    DESCRIPTION
            "This object, along with the ifIndex of the MAC layer,
            identifies exactly one entry in the table."
    ::= { p2mpHeBadSuEntry 1 }

p2mpBadSuUpdateTime OBJECT-TYPE
    SYNTAX          CwrUpdateTime
    UNITS           "seconds"
    MAX-ACCESS      read-only
    STATUS          current
    DESCRIPTION
            "This object represents time in seconds since system
            power up at which time this entry was last updated."
    ::= { p2mpHeBadSuEntry 2 }

p2mpBadSuMacAddress OBJECT-TYPE
    SYNTAX          MacAddress
    MAX-ACCESS      read-only
    STATUS          current
    DESCRIPTION
            "This object identifies the subscriber unit that either
            failed to transmit a minimum number of codewords in an
            operational hour OR whose percentage of errored
            codewords transmitted exceeded the threshold."
    ::= { p2mpHeBadSuEntry 3 }

p2mpTotalErroredCodewords OBJECT-TYPE
    SYNTAX          Unsigned32
    MAX-ACCESS      read-only
    STATUS          current
    DESCRIPTION
            "This object represents the total errored codewords
            transmitted by this subscriber unit in the current
            operational hour."
    ::= { p2mpHeBadSuEntry 4 }

p2mpPctErroredCodewords OBJECT-TYPE
    SYNTAX          Unsigned32
    MAX-ACCESS      read-only
    STATUS          current
    DESCRIPTION
            "This object represent the percentage of errored
            codewords to total codewords transmitted by the
            subscriber unit in the current operational hour."
    ::= { p2mpHeBadSuEntry 5 }

p2mpHeCodewordErrorTable OBJECT-TYPE
    SYNTAX          SEQUENCE OF P2mpHeCodewordErrorEntry
    MAX-ACCESS      not-accessible
    STATUS          current
    DESCRIPTION
            "This table contains codeword error history for the past 24
            hours, at 1 hour intervals, on a per subscriber basis.

            This table will have a maximum of 24 entries providing
            cumulative status of the link, identified by ifIndex, over the
            past 24 hours.

            This table is updated once every hour."
    ::= { p2mpHeLinkMetricsGroup 3 }

p2mpHeCodewordErrorEntry OBJECT-TYPE
    SYNTAX          P2mpHeCodewordErrorEntry
    MAX-ACCESS      not-accessible
    STATUS          current
    DESCRIPTION
            "This represents one entry in the p2mpHeCodewordErrorTable
            indexed by ifIndex of propDocsWirelessMaclayer, the MAC
            address of the subscriber unit, and p2mpHeCWErrorIndex

            Every entry represents the cumulative sum of the previous entry
            plus last hour before the entry is updated.

            The first entry in the table (p2mpHeCWErrorIndex = 1) represents
            the chronologically oldest data available."
    INDEX           {
                        ifIndex,
                        p2mpSuMacAddress,
                        p2mpHeCWErrorIndex
                    }
    ::= { p2mpHeCodewordErrorTable 1 }

P2mpHeCodewordErrorEntry ::= SEQUENCE {
    p2mpSuMacAddress         MacAddress,
    p2mpHeCWErrorIndex       Integer32,
    p2mpHeCWErrorUpdateTime  CwrUpdateTime,
    p2mpTotalCodewords       WirelessGauge64,
    p2mpErroredCodewords     WirelessGauge64,
    p2mpSINR                 CwrFixedPointValue
}

p2mpSuMacAddress OBJECT-TYPE
    SYNTAX          MacAddress
    MAX-ACCESS      not-accessible
    STATUS          current
    DESCRIPTION
            "This object is used to index this table.  It indicates the MAC
            address of the subscriber unit."
    ::= { p2mpHeCodewordErrorEntry 1 }

p2mpHeCWErrorIndex OBJECT-TYPE
    SYNTAX          Integer32 (1..24)
    MAX-ACCESS      not-accessible
    STATUS          current
    DESCRIPTION
            "This object identifies exactly one entry in the table."
    ::= { p2mpHeCodewordErrorEntry 2 }

p2mpHeCWErrorUpdateTime OBJECT-TYPE
    SYNTAX          CwrUpdateTime
    UNITS           "seconds"
    MAX-ACCESS      read-only
    STATUS          current
    DESCRIPTION
            "This object represents time in seconds since system power up at
            which time this entry was last updated."
    ::= { p2mpHeCodewordErrorEntry 3 }

p2mpTotalCodewords OBJECT-TYPE
    SYNTAX          WirelessGauge64
    MAX-ACCESS      read-only
    STATUS          current
    DESCRIPTION
            "This object represents the total received codewords
            detected on the subscriber unit identified by
            p2mpSuMacAddress from Link Admin Up time until the
            current operational hour."
    ::= { p2mpHeCodewordErrorEntry 4 }

p2mpErroredCodewords OBJECT-TYPE
    SYNTAX          WirelessGauge64
    MAX-ACCESS      read-only
    STATUS          current
    DESCRIPTION
            "This object represents the total received errored
            codewords detected on the subscriber unit identified by
            p2mpSuMacAddress from Link Admin Up time until the
            current operational hour."
    ::= { p2mpHeCodewordErrorEntry 5 }

p2mpSINR OBJECT-TYPE
    SYNTAX          CwrFixedPointValue
    MAX-ACCESS      read-only
    STATUS          current
    DESCRIPTION
            "This object represents the ratio of signal to
            (interference + noise) from Link Admin Up time until
            the current operational hour."
    ::= { p2mpHeCodewordErrorEntry 6 }

p2mpHe1SecMetricsTable OBJECT-TYPE
    SYNTAX          SEQUENCE OF P2mpHe1SecMetricsEntry
    MAX-ACCESS      not-accessible
    STATUS          current
    DESCRIPTION
            "This table contains metrics collected over the duration
            of one second.

            This table will have a maximum of 60 entries providing
            cumulative status of the upstream channel, identified by
            ifIndex of propDocsWirelessUpstream, over the past one
            minute.

            This table is updated once every second."
    ::= { p2mpHeLinkMetricsGroup 4 }

p2mpHe1SecMetricsEntry OBJECT-TYPE
    SYNTAX          P2mpHe1SecMetricsEntry
    MAX-ACCESS      not-accessible
    STATUS          current
    DESCRIPTION
            "This represents one entry in the p2mpHe1SecMetricsTable
            indexed by the ifIndex of propDocsWirelessUpstream and
            p2mpHe1SecIndex.

            Every entry represents the cumulative sum of the
            previous entry plus the last second before the entry is
            updated.

            The first entry in the table (p2mpHe1SecIndex = 1)
            represents the chronologically oldest data available."
    INDEX           {
                        ifIndex,
                        p2mpHe1SecIndex
                    }
    ::= { p2mpHe1SecMetricsTable 1 }

P2mpHe1SecMetricsEntry ::= SEQUENCE {
    p2mpHe1SecIndex             Integer32,
    p2mpHe1SecUpdateTime        CwrUpdateTime,
    p2mpHe1SecTotalCodewords    WirelessGauge64,
    p2mpHe1SecErroredCodewords  WirelessGauge64
}

p2mpHe1SecIndex OBJECT-TYPE
    SYNTAX          Integer32 (1..60)
    MAX-ACCESS      not-accessible
    STATUS          current
    DESCRIPTION
            "This object, along with ifIndex, identifies exactly one
            entry in the table."
    ::= { p2mpHe1SecMetricsEntry 1 }

p2mpHe1SecUpdateTime OBJECT-TYPE
    SYNTAX          CwrUpdateTime
    UNITS           "seconds"
    MAX-ACCESS      read-only
    STATUS          current
    DESCRIPTION
            "This object represents time in seconds since system power up at
            which time this entry was last updated."
    ::= { p2mpHe1SecMetricsEntry 2 }

p2mpHe1SecTotalCodewords OBJECT-TYPE
    SYNTAX          WirelessGauge64
    MAX-ACCESS      read-only
    STATUS          current
    DESCRIPTION
            "This object represents the total number of codewords
            received on a channel from the last Link Admin Up time
            until the current operational second."
    ::= { p2mpHe1SecMetricsEntry 3 }

p2mpHe1SecErroredCodewords OBJECT-TYPE
    SYNTAX          WirelessGauge64
    MAX-ACCESS      read-only
    STATUS          current
    DESCRIPTION
            "This object represents the total number of errored
            codewords received on a channel from the last Link Admin
            Up time until the current operational second."
    ::= { p2mpHe1SecMetricsEntry 4 }

p2mpHe1MinMetricsTable OBJECT-TYPE
    SYNTAX          SEQUENCE OF P2mpHe1MinMetricsEntry
    MAX-ACCESS      not-accessible
    STATUS          current
    DESCRIPTION
            "This table contains metrics collected over the duration
            of one minute.

            This table will have a maximum of 60 entries providing
            cumulative status of the upstream channel, identified by
            ifIndex of propDocsWirelessUpstream, over the past one
            hour.

            This table is updated once every minute."
    ::= { p2mpHeLinkMetricsGroup 5 }

p2mpHe1MinMetricsEntry OBJECT-TYPE
    SYNTAX          P2mpHe1MinMetricsEntry
    MAX-ACCESS      not-accessible
    STATUS          current
    DESCRIPTION
            "This represents one entry in the p2mpHe1MinMetricsTable
            indexed by ifIndex of propDocsWirelessUpstream and
            p2mpHe1MinIndex.

            Every entry represents the cumulative sum of the
            previous entry plus the last 1 minute before the entry
            was updated.

            The first entry in the table (p2mpHe1MinIndex = 1)
            represents the chronologically oldest data available."
    INDEX           {
                        ifIndex,
                        p2mpHe1MinIndex
                    }
    ::= { p2mpHe1MinMetricsTable 1 }

P2mpHe1MinMetricsEntry ::= SEQUENCE {
    p2mpHe1MinIndex             Integer32,
    p2mpHe1MinUpdateTime        CwrUpdateTime,
    p2mpHe1MinTotalCodewords    WirelessGauge64,
    p2mpHe1MinErroredCodewords  WirelessGauge64
}

p2mpHe1MinIndex OBJECT-TYPE
    SYNTAX          Integer32 (1..60)
    MAX-ACCESS      not-accessible
    STATUS          current
    DESCRIPTION
            "This object, along with ifIndex, identifies exactly one
            entry in the table."
    ::= { p2mpHe1MinMetricsEntry 1 }

p2mpHe1MinUpdateTime OBJECT-TYPE
    SYNTAX          CwrUpdateTime
    UNITS           "seconds"
    MAX-ACCESS      read-only
    STATUS          current
    DESCRIPTION
            "This object represents time in seconds since system
            power up at which time this entry was last updated."
    ::= { p2mpHe1MinMetricsEntry 2 }

p2mpHe1MinTotalCodewords OBJECT-TYPE
    SYNTAX          WirelessGauge64
    MAX-ACCESS      read-only
    STATUS          current
    DESCRIPTION
            "This object represents the cumulative sum of codewords
            received on a channel from the last Link Admin Up time
            until the current operational minute."
    ::= { p2mpHe1MinMetricsEntry 3 }

p2mpHe1MinErroredCodewords OBJECT-TYPE
    SYNTAX          WirelessGauge64
    MAX-ACCESS      read-only
    STATUS          current
    DESCRIPTION
            "This object represents the cumulative sum of errored
            codewords received on a channel from the last Link Admin
            Up time until the current operational minute."
    ::= { p2mpHe1MinMetricsEntry 4 }

p2mpHe1HrMetricsTable OBJECT-TYPE
    SYNTAX          SEQUENCE OF P2mpHe1HrMetricsEntry
    MAX-ACCESS      not-accessible
    STATUS          current
    DESCRIPTION
            "This table contains metrics collected over the duration
            of one hour.

            This table will have a maximum of 24 entries providing
            cumulative status of the upstream channel, identified by
            ifIndex of propDocsWirelessUpstream, over the past 24
            hours.

            This table is updated once every hour."
    ::= { p2mpHeLinkMetricsGroup 6 }

p2mpHe1HrMetricsEntry OBJECT-TYPE
    SYNTAX          P2mpHe1HrMetricsEntry
    MAX-ACCESS      not-accessible
    STATUS          current
    DESCRIPTION
            "This represents one entry in the p2mpHe1HrMetricsTable
            indexed by ifIndex of propDocsWirelessUpstream and
            p2mpHe1HrIndex.

            Every entry represents the cumulative sum of the
            previous entry plus the last 1 hour before the entry was
            updated.

            The first entry in the table (p2mpHe1HrIndex = 1)
            represents the chronologically oldest data available."
    INDEX           {
                        ifIndex,
                        p2mpHe1HrIndex
                    }
    ::= { p2mpHe1HrMetricsTable 1 }

P2mpHe1HrMetricsEntry ::= SEQUENCE {
    p2mpHe1HrIndex             Integer32,
    p2mpHe1HrUpdateTime        CwrUpdateTime,
    p2mpHe1HrTotalCodewords    WirelessGauge64,
    p2mpHe1HrErroredCodewords  WirelessGauge64
}

p2mpHe1HrIndex OBJECT-TYPE
    SYNTAX          Integer32 (1..24)
    MAX-ACCESS      not-accessible
    STATUS          current
    DESCRIPTION
            "This object, along with ifIndex, identifies exactly one
            entry in the table."
    ::= { p2mpHe1HrMetricsEntry 1 }

p2mpHe1HrUpdateTime OBJECT-TYPE
    SYNTAX          CwrUpdateTime
    UNITS           "seconds"
    MAX-ACCESS      read-only
    STATUS          current
    DESCRIPTION
            "This object represents time in seconds since system power up at
            which time this entry was last updated."
    ::= { p2mpHe1HrMetricsEntry 2 }

p2mpHe1HrTotalCodewords OBJECT-TYPE
    SYNTAX          WirelessGauge64
    MAX-ACCESS      read-only
    STATUS          current
    DESCRIPTION
            "This object represents the total number of codewords
            received on this channel at the time this entry was
            updated."
    ::= { p2mpHe1HrMetricsEntry 3 }

p2mpHe1HrErroredCodewords OBJECT-TYPE
    SYNTAX          WirelessGauge64
    MAX-ACCESS      read-only
    STATUS          current
    DESCRIPTION
            "This object represents the total number of errored
            codewords received on this channel in the last 1 hour."
    ::= { p2mpHe1HrMetricsEntry 4 }

p2mpMetricsMIBNotificationPrefix OBJECT IDENTIFIER
    ::= { p2mpLinkMetricsGroup 2 }

p2mpMetricsMIBNotification OBJECT IDENTIFIER
    ::= { p2mpMetricsMIBNotificationPrefix 0 }

p2mpHeChPctErrCWThreshTrap NOTIFICATION-TYPE
    OBJECTS         { p2mpHe1HrPctErrCWThresh }
    STATUS          current
    DESCRIPTION
            "The p2mpHe1HrPctErrCWThresh for an upstream channel was
            exceeded."
    ::= { p2mpMetricsMIBNotification 1 }

p2mpHeMacPctErrCWThreshTrap NOTIFICATION-TYPE
    OBJECTS         {
                        p2mpBadSuMacAddress,
                        p2mpTotalErroredCodewords,
                        p2mpPctErroredCodewords
                    }
    STATUS          current
    DESCRIPTION
            "The p2mpHe1HrPctErrCWThresh for the subscriber
            unit was exceeded.  The subscriber unit was added to
            the p2mpHeBadSuTable."
    ::= { p2mpMetricsMIBNotification 2 }

p2mpSuErrSecAlarmTrap NOTIFICATION-TYPE
    OBJECTS         { p2mpSuLink1HrESAlarmThresh }
    STATUS          current
    DESCRIPTION     "The p2mpSuLink1HrESAlarmThresh was exceeded."
    ::= { p2mpMetricsMIBNotification 3 }

p2mpSuSevErrSecAlarmTrap NOTIFICATION-TYPE
    OBJECTS         { p2mpSuLink1HrSESAlarmThresh }
    STATUS          current
    DESCRIPTION     "The p2mpSuLink1HrSESAlarmThresh was exceeded."
    ::= { p2mpMetricsMIBNotification 4 }

p2mpSuConsecSevErrSecAlarmTrap NOTIFICATION-TYPE
    OBJECTS         { p2mpSuLink1HrCSESAlarmThresh }
    STATUS          current
    DESCRIPTION     "The p2mpSuLink1HrCSESAlarmThresh was exceeded."
    ::= { p2mpMetricsMIBNotification 5 }

p2mpSuDegradedSecAlarmTrap NOTIFICATION-TYPE
    OBJECTS         { p2mpSuLink1HrDCSAlarmThresh }
    STATUS          current
    DESCRIPTION     "The p2mpSuLink1HrDCSAlarmThresh was exceeded."
    ::= { p2mpMetricsMIBNotification 6 }

-- ====================================================================

-- Compliance Statements
p2mpRadioLinkConformance OBJECT IDENTIFIER
    ::= { ciscoWirelessLinkMetricsMIB 4 }

p2mpRadioLinkCompliances OBJECT IDENTIFIER
    ::= { p2mpRadioLinkConformance 1 }

p2mpRadioLinkGroups OBJECT IDENTIFIER
    ::= { p2mpRadioLinkConformance 2 }

p2mpRadioLinkCompliance MODULE-COMPLIANCE
    STATUS          current
    DESCRIPTION
            "The compliance statement for devices implementing the
            Point to MultiPoint wireless interface compliant to
            Cisco Systems Inc. specification."
    MODULE          -- this module
    MANDATORY-GROUPS { p2mpComplianceLinkMetricsGroup }

    GROUP           p2mpComplianceSuMetricsGroup
    DESCRIPTION
            "This group is mandatory at the Subscriber Unit.
            It is not implemented at the Head End."

    GROUP           p2mpComplianceHeMetricsGroup
    DESCRIPTION
            "This group is mandatory at the Head End.
            It is not implemented at the Subscriber Unit."

    GROUP  p2mpComplianceNotifGroup
    DESCRIPTION
           "Implementation of the notifications specified
            by this group is optional."

    ::= { p2mpRadioLinkCompliances 1 }

-- unconditionally mandatory groups
p2mpComplianceLinkMetricsGroup OBJECT-GROUP
    OBJECTS         {
                        p2mpLinkMetricsScale,
                        p2mpLinkMetricsPrecision
                    }
    STATUS          current
    DESCRIPTION
            "Objects implemented to indicate scaling factors for
            fixed point values.  This group is mandatory on the
            Head End and the Subscriber Unit."
    ::= { p2mpRadioLinkGroups 1 }

-- conditionally mandatory group
p2mpComplianceSuMetricsGroup OBJECT-GROUP
    OBJECTS         {
                        p2mpSuLinkESThresh,
                        p2mpSuLinkDSThresh,
                        p2mpSuLinkSESThresh,
                        p2mpSuLinkCSESThresh,
                        p2mpSuLink1HrESAlarmThresh,
                        p2mpSuLink1HrSESAlarmThresh,
                        p2mpSuLink1HrCSESAlarmThresh,
                        p2mpSuLink1HrDCSAlarmThresh,
                        p2mpSu1SecUpdateTime,
                        p2mpSu1SecType,
                        p2mpSu1SecTotalCodewords,
                        p2mpSu1SecTotalErrCodewords,
                        p2mpSu1SecValidDataPkt,
                        p2mpSu1MinUpdateTime,
                        p2mpSu1MinTotalCodewords,
                        p2mpSu1MinTotalErrCodewords,
                        p2mpSu1MinValidDataPkt,
                        p2mpSu1MinErrorFreeSeconds,
                        p2mpSu1MinErroredSeconds,
                        p2mpSu1MinSevErroredSeconds,
                        p2mpSu1MinConsecSevErrSeconds,
                        p2mpSu1MinSyncLossSeconds,
                        p2mpSu1MinDegradedSeconds,
                        p2mpSu1MinTxPowerMax,
                        p2mpSu1MinTxPowerMin,
                        p2mpSu1MinTxPowerAvg,
                        p2mpSu1MinMainAntRxPowerMax,
                        p2mpSu1MinMainAntRxPowerMin,
                        p2mpSu1MinMainAntRxPowerAvg,
                        p2mpSu1MinDivAntRxPowerMax,
                        p2mpSu1MinDivAntRxPowerMin,
                        p2mpSu1MinDivAntRxPowerAvg,
                        p2mpSu1HrUpdateTime,
                        p2mpSu1HrTotalCodewords,
                        p2mpSu1HrTotalErrCodewords,
                        p2mpSu1HrValidDataPkt,
                        p2mpSu1HrErrorFreeSeconds,
                        p2mpSu1HrErroredSeconds,
                        p2mpSu1HrSevErroredSeconds,
                        p2mpSu1HrConsecSvErrSeconds,
                        p2mpSu1HrSyncLossSeconds,
                        p2mpSu1HrDegradedSeconds,
                        p2mpSu1HrTxPowerMax,
                        p2mpSu1HrTxPowerMin,
                        p2mpSu1HrTxPowerAvg,
                        p2mpSu1HrMainAntRxPowerMax,
                        p2mpSu1HrMainAntRxPowerMin,
                        p2mpSu1HrMainAntRxPowerAvg,
                        p2mpSu1HrDivAntRxPowerMax,
                        p2mpSu1HrDivAntRxPowerMin,
                        p2mpSu1HrDivAntRxPowerAvg,
                        p2mpSuAvailableSeconds,
                        p2mpSuUnAvailableSeconds,
                        p2mpSuPctAvailSeconds,
                        p2mpSuSyncLossSeconds,
                        p2mpSuPctErrorFreeSeconds,
                        p2mpSuPctErroredSeconds,
                        p2mpSuPctSevErroredSeconds,
                        p2mpSuPctDegradedSeconds,
                        p2mpSuInitialSyncSeconds,
                        p2mpSuSyncSuccessCount,
                        p2mpSuLastSyncSuccessTime,
                        p2mpSuSyncMedEffort,
                        p2mpSuSyncHighEffort,
                        p2mpSuSyncFailureCount,
                        p2mpSuLastSyncFailTime,
                        p2mpSuEffectiveDataRate,
                        p2mpSuPercentEfficiency
                    }
    STATUS          current
    DESCRIPTION
            "Group of objects implemented at the Subscriber unit."
    ::= { p2mpRadioLinkGroups 2 }

p2mpComplianceHeMetricsGroup OBJECT-GROUP
    OBJECTS         {
                        p2mpHe1HrMinTotalCWThresh,
                        p2mpHe1HrPctErrCWThresh,
                        p2mpBadSuUpdateTime,
                        p2mpBadSuMacAddress,
                        p2mpTotalErroredCodewords,
                        p2mpPctErroredCodewords,
                        p2mpHeCWErrorUpdateTime,
                        p2mpTotalCodewords,
                        p2mpErroredCodewords,
                        p2mpSINR,
                        p2mpHe1SecUpdateTime,
                        p2mpHe1SecTotalCodewords,
                        p2mpHe1SecErroredCodewords,
                        p2mpHe1MinUpdateTime,
                        p2mpHe1MinTotalCodewords,
                        p2mpHe1MinErroredCodewords,
                        p2mpHe1HrUpdateTime,
                        p2mpHe1HrTotalCodewords,
                        p2mpHe1HrErroredCodewords
                    }
    STATUS          current
    DESCRIPTION     "Group of objects implemented at the Head End."
    ::= { p2mpRadioLinkGroups 3 }

p2mpComplianceNotifGroup  NOTIFICATION-GROUP
    NOTIFICATIONS  { p2mpHeChPctErrCWThreshTrap,
                     p2mpHeMacPctErrCWThreshTrap,
                     p2mpSuErrSecAlarmTrap,
                     p2mpSuSevErrSecAlarmTrap,
                     p2mpSuConsecSevErrSecAlarmTrap,
                     p2mpSuDegradedSecAlarmTrap
                   }
      STATUS  current
      DESCRIPTION
              "Group of notifications which indicate that a threshold was
              exceeded."
    ::= { p2mpRadioLinkGroups 4 }

END
