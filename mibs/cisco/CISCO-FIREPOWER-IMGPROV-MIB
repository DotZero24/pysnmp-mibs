-- *********************************************************************
-- CISCO-FIREPOWER-IMGPROV-MIB.my
--
-- MIB representation of the Cisco Firepower
-- IMGPROV management information model package
--
-- Created March 2020 by Charles Bullis
--
-- Copyright (c) 2005-2020 Cisco Systems, Inc. All rights reserved.
--
-- *********************************************************************

CISCO-FIREPOWER-IMGPROV-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIBObjects,
    CfprManagedObjectId,
    CfprManagedObjectDn
        FROM CISCO-FIREPOWER-MIB
    CfprPolicyPolicyOwner
        FROM CISCO-FIREPOWER-TC-MIB;

cfprImgprovObjects MODULE-IDENTITY
    LAST-UPDATED    "202003100000Z"
    ORGANIZATION    "Cisco Systems Inc."
    CONTACT-INFO
        "Cisco Systems
        Customer Service

        Postal: 170 W Tasman Drive
        San Jose, CA  95134
        USA

        Tel: +1 800 553-NETS

        E-mail: firepower-mibs@cisco.com"
    DESCRIPTION
        "MIB representation of the Cisco Firepower
        IMGPROV management information model package"
    ::= { ciscoFirepowerMIBObjects 37 }

cfprImgprovPolicyTable OBJECT-TYPE
    SYNTAX           SEQUENCE OF CfprImgprovPolicyEntry
    MAX-ACCESS       not-accessible
    STATUS           current
    DESCRIPTION
        "Cisco Firepower imgprov:Policy managed object table"
    ::= { cfprImgprovObjects 1 }

cfprImgprovPolicyEntry OBJECT-TYPE
    SYNTAX           CfprImgprovPolicyEntry
    MAX-ACCESS       not-accessible
    STATUS           current
    DESCRIPTION
        "Entry for the cfprImgprovPolicyTable table."
    INDEX { cfprImgprovPolicyInstanceId }
    ::= { cfprImgprovPolicyTable 1 }

CfprImgprovPolicyEntry ::= SEQUENCE {
    cfprImgprovPolicyInstanceId                                      CfprManagedObjectId,
    cfprImgprovPolicyDn                                              CfprManagedObjectDn,
    cfprImgprovPolicyRn                                              SnmpAdminString,
    cfprImgprovPolicyDescr                                           SnmpAdminString,
    cfprImgprovPolicyIntId                                           SnmpAdminString,
    cfprImgprovPolicyName                                            SnmpAdminString,
    cfprImgprovPolicyPolicyLevel                                     Gauge32,
    cfprImgprovPolicyPolicyOwner                                     CfprPolicyPolicyOwner
}

cfprImgprovPolicyInstanceId OBJECT-TYPE
    SYNTAX       CfprManagedObjectId
    MAX-ACCESS   not-accessible
    STATUS       current
    DESCRIPTION
        "Instance identifier of the managed object."
    ::= { cfprImgprovPolicyEntry 1 }

cfprImgprovPolicyDn OBJECT-TYPE
    SYNTAX       CfprManagedObjectDn
    MAX-ACCESS   read-only
    STATUS       current
    DESCRIPTION
        "Cisco Firepower imgprov:Policy:dn managed object property"
    ::= { cfprImgprovPolicyEntry 2 }

cfprImgprovPolicyRn OBJECT-TYPE
    SYNTAX       SnmpAdminString
    MAX-ACCESS   read-only
    STATUS       current
    DESCRIPTION
        "Cisco Firepower imgprov:Policy:rn managed object property"
    ::= { cfprImgprovPolicyEntry 3 }

cfprImgprovPolicyDescr OBJECT-TYPE
    SYNTAX       SnmpAdminString
    MAX-ACCESS   read-only
    STATUS       current
    DESCRIPTION
        "Cisco Firepower imgprov:Policy:descr managed object property"
    ::= { cfprImgprovPolicyEntry 4 }

cfprImgprovPolicyIntId OBJECT-TYPE
    SYNTAX       SnmpAdminString
    MAX-ACCESS   read-only
    STATUS       current
    DESCRIPTION
        "Cisco Firepower imgprov:Policy:intId managed object property"
    ::= { cfprImgprovPolicyEntry 5 }

cfprImgprovPolicyName OBJECT-TYPE
    SYNTAX       SnmpAdminString
    MAX-ACCESS   read-only
    STATUS       current
    DESCRIPTION
        "Cisco Firepower imgprov:Policy:name managed object property"
    ::= { cfprImgprovPolicyEntry 6 }

cfprImgprovPolicyPolicyLevel OBJECT-TYPE
    SYNTAX       Gauge32
    MAX-ACCESS   read-only
    STATUS       current
    DESCRIPTION
        "Cisco Firepower imgprov:Policy:policyLevel managed
        object property"
    ::= { cfprImgprovPolicyEntry 7 }

cfprImgprovPolicyPolicyOwner OBJECT-TYPE
    SYNTAX       CfprPolicyPolicyOwner
    MAX-ACCESS   read-only
    STATUS       current
    DESCRIPTION
        "Cisco Firepower imgprov:Policy:policyOwner managed
        object property"
    ::= { cfprImgprovPolicyEntry 8 }

cfprImgprovTargetTable OBJECT-TYPE
    SYNTAX           SEQUENCE OF CfprImgprovTargetEntry
    MAX-ACCESS       not-accessible
    STATUS           current
    DESCRIPTION
        "Cisco Firepower imgprov:Target managed object table"
    ::= { cfprImgprovObjects 2 }

cfprImgprovTargetEntry OBJECT-TYPE
    SYNTAX           CfprImgprovTargetEntry
    MAX-ACCESS       not-accessible
    STATUS           current
    DESCRIPTION
        "Entry for the cfprImgprovTargetTable table."
    INDEX { cfprImgprovTargetInstanceId }
    ::= { cfprImgprovTargetTable 1 }

CfprImgprovTargetEntry ::= SEQUENCE {
    cfprImgprovTargetInstanceId                                      CfprManagedObjectId,
    cfprImgprovTargetDn                                              CfprManagedObjectDn,
    cfprImgprovTargetRn                                              SnmpAdminString,
    cfprImgprovTargetName                                            SnmpAdminString
}

cfprImgprovTargetInstanceId OBJECT-TYPE
    SYNTAX       CfprManagedObjectId
    MAX-ACCESS   not-accessible
    STATUS       current
    DESCRIPTION
        "Instance identifier of the managed object."
    ::= { cfprImgprovTargetEntry 1 }

cfprImgprovTargetDn OBJECT-TYPE
    SYNTAX       CfprManagedObjectDn
    MAX-ACCESS   read-only
    STATUS       current
    DESCRIPTION
        "Cisco Firepower imgprov:Target:dn managed object property"
    ::= { cfprImgprovTargetEntry 2 }

cfprImgprovTargetRn OBJECT-TYPE
    SYNTAX       SnmpAdminString
    MAX-ACCESS   read-only
    STATUS       current
    DESCRIPTION
        "Cisco Firepower imgprov:Target:rn managed object property"
    ::= { cfprImgprovTargetEntry 3 }

cfprImgprovTargetName OBJECT-TYPE
    SYNTAX       SnmpAdminString
    MAX-ACCESS   read-only
    STATUS       current
    DESCRIPTION
        "Cisco Firepower imgprov:Target:name managed object property"
    ::= { cfprImgprovTargetEntry 4 }

END
