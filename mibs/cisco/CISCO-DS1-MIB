-- *****************************************************************
-- ciscoDS1 MIB
--
-- Jan 2022, Gaurav Sharma
--
-- Copyright (c) 1999-2000, 2003, 2006, 2022 by cisco Systems, Inc.
-- All rights reserved.
-- *****************************************************************


CISCO-DS1-MIB DEFINITIONS ::= BEGIN
IMPORTS
    MODULE-IDENTITY,
    OBJECT-TYPE,
    NOTIFICATION-TYPE,
    Counter32,
    Integer32,
    Gauge32,
    Unsigned32                  FROM SNMPv2-SMI
    TruthValue,
    TEXTUAL-CONVENTION          FROM SNMPv2-TC
    MODULE-COMPLIANCE,
    OBJECT-GROUP,
    NOTIFICATION-GROUP          FROM SNMPv2-CONF
    InterfaceIndex,
    ifIndex,
    ifDescr                     FROM IF-MIB
    ciscoMgmt                   FROM CISCO-SMI;

ciscoDs1MIB MODULE-IDENTITY
        LAST-UPDATED    "200303070000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
        DESCRIPTION
                "The MIB module to describe e1 interfaces
                 objects. This is an extension to the standard DS1
                 MIB(RFC 2558)."
        ::= { ciscoMgmt 1055 }


ciscoDs1MIBNotifs     OBJECT IDENTIFIER ::= {ciscoDs1MIB 0}
ciscoDs1MIBObjects    OBJECT IDENTIFIER ::= {ciscoDs1MIB 1}

-- sonet section/line/farend line pm  data
ciscoDS1PMData               OBJECT IDENTIFIER ::=
                                        {ciscoDs1MIBObjects 1}
-- Textual conventions

CoiIntervalType ::= TEXTUAL-CONVENTION
    STATUS          current
    DESCRIPTION
        "This value indicates the time period over which performance
        monitoring data has been collected. Valid values are -

        fifteenMin(1)  -  values for the 15 min interval.
        oneDay(2)      -  values for the 1  Day interval."
    SYNTAX          INTEGER  {
                        fifteenMin(1),
                        oneDay(2)
                    }


coiDS1PMCurrentTable OBJECT-TYPE
    SYNTAX          SEQUENCE OF CoiDS1PMCurrentEntry
    MAX-ACCESS      not-accessible
    STATUS          current
    DESCRIPTION
        "Table containing current pm data for ds1 interface,
	applicable intervals are 15-min and 24-hour"
    ::= { ciscoDS1PMData 1 }

coiDS1PMCurrentEntry OBJECT-TYPE
    SYNTAX          CoiDS1PMCurrentEntry
    MAX-ACCESS      not-accessible
    STATUS          current
    DESCRIPTION
        "An entry containing current ds1 pm data"
    INDEX           {
                        ifIndex,
                        coiDS1CurrentIntervalType
                    }
    ::= { coiDS1PMCurrentTable 1 }

CoiDS1PMCurrentEntry ::= SEQUENCE {
           coiDS1CurrentIntervalType    CoiIntervalType,
           coiDS1CurrentLCVs      Counter32,
           coiDS1CurrentPCVs      Counter32,
           coiDS1CurrentSELSs      Counter32,
           coiDS1CurrentLESs      Counter32,
           coiDS1CurrentAISs      Counter32,
           coiDS1CurrentFCPs      Counter32,
           coiDS1CurrentESs      Counter32,
           coiDS1CurrentSESs     Counter32,
           coiDS1CurrentUASs     Counter32,
           coiDS1CurrentESFEs      Counter32,
           coiDS1CurrentSESFEs      Counter32,
           coiDS1CurrentUASFEs      Counter32,
           coiDS1currentPMValidData TruthValue
}

coiDS1CurrentIntervalType OBJECT-TYPE
    SYNTAX          CoiIntervalType
    MAX-ACCESS      not-accessible
    STATUS          current
    DESCRIPTION
        "This object gives the interval for which current pm data is collected"
    ::= { coiDS1PMCurrentEntry 1 }

coiDS1CurrentLCVs OBJECT-TYPE
       SYNTAX  Counter32
       MAX-ACCESS  read-only
       STATUS  current
       DESCRIPTION
          "This count will be incremented whenever Line code violation(LCV) event is
	  detected due to either a Bipolar Violation (BPV) or
	  Excessive Zeros (EXZ) error event "
        ::= { coiDS1PMCurrentEntry 2 }

coiDS1CurrentPCVs OBJECT-TYPE
       SYNTAX  Counter32
       MAX-ACCESS  read-only
       STATUS  current
       DESCRIPTION
          "Counter for path code violations"
        ::= { coiDS1PMCurrentEntry 3 }

coiDS1CurrentSELSs OBJECT-TYPE
       SYNTAX  Counter32
       MAX-ACCESS  read-only
       STATUS  current
       DESCRIPTION
          "Counter for frame loss second, This counter is Incremented when an
	  out-of-frame error is detected and will reset when it is cleared."
        ::= { coiDS1PMCurrentEntry 4 }

coiDS1CurrentLESs OBJECT-TYPE
       SYNTAX  Counter32
       MAX-ACCESS  read-only
       STATUS  current
       DESCRIPTION
          "Counter for Line Error seconds, Incremented when Line Code Violation
	  errors are detected."
        ::= { coiDS1PMCurrentEntry 5 }

coiDS1CurrentAISs OBJECT-TYPE
       SYNTAX  Counter32
       MAX-ACCESS  read-only
       STATUS  current
       DESCRIPTION
          "Counter for AIS,Incremented when alarm indication
	  signal is detected."
        ::= { coiDS1PMCurrentEntry 6 }

coiDS1CurrentFCPs OBJECT-TYPE
       SYNTAX  Counter32
       MAX-ACCESS  read-only
       STATUS  current
       DESCRIPTION
          "Failure count at path(FCP), This counter is incremented
	  at event of any AIS, LOF for first time assertion and re-assertion."
        ::= { coiDS1PMCurrentEntry 7 }

coiDS1CurrentESs OBJECT-TYPE
       SYNTAX  Counter32
       MAX-ACCESS  read-only
       STATUS  current
       DESCRIPTION
          "Error Seconds(ES), This counter will be incremented in
	  one of the cases mentioned below
	      -One or more Path Code Violations.
	      -One or more Controlled Slip events "
        ::= { coiDS1PMCurrentEntry 8 }

coiDS1CurrentSESs OBJECT-TYPE
       SYNTAX  Counter32
       MAX-ACCESS  read-only
       STATUS  current
       DESCRIPTION
          "Severly Error Seconds(ES),  This count will be incremented
	  in below conditions
	     -320 or more Path Code Violation errors.
	     -One or more Out of Frame defects.
	     -An AIS defect.
	     Note:It will not be incremented during UAS"
        ::= { coiDS1PMCurrentEntry 9 }

coiDS1CurrentUASs OBJECT-TYPE
       SYNTAX  Counter32
       MAX-ACCESS  read-only
       STATUS  current
       DESCRIPTION
          "Unavailable Error Seconds(UAS)"
        ::= { coiDS1PMCurrentEntry 10 }

coiDS1CurrentESFEs OBJECT-TYPE
       SYNTAX  Counter32
       MAX-ACCESS  read-only
       STATUS  current
       DESCRIPTION
          "Error second at FAR end"
        ::= { coiDS1PMCurrentEntry 11 }

coiDS1CurrentSESFEs OBJECT-TYPE
       SYNTAX  Counter32
       MAX-ACCESS  read-only
       STATUS  current
       DESCRIPTION
          "Severly Error second at FAR end"
        ::= { coiDS1PMCurrentEntry 12 }

coiDS1CurrentUASFEs OBJECT-TYPE
       SYNTAX  Counter32
       MAX-ACCESS  read-only
       STATUS  current
       DESCRIPTION
          "Unavailable Error second at FAR end"
        ::= { coiDS1PMCurrentEntry 13 }

coiDS1currentPMValidData OBJECT-TYPE
    SYNTAX          TruthValue
    MAX-ACCESS      read-only
    STATUS          current
    DESCRIPTION
        "This variable indicates if the ds1 pm data for the
         interval identified by coiOtnsecPMCurrentIntervalType is valid."
    ::= { coiDS1PMCurrentEntry 14 }

coiDS1PMHisTable OBJECT-TYPE
    SYNTAX          SEQUENCE OF CoiDS1PMHisEntry
    MAX-ACCESS      not-accessible
    STATUS          current
    DESCRIPTION
        "Table containing current pm data for sonet/sdh section,line and farend line,
	applicable intervals are 15-min and 24-hour"
    ::= { ciscoDS1PMData 2 }

 coiDS1PMHisEntry OBJECT-TYPE
    SYNTAX          CoiDS1PMHisEntry
    MAX-ACCESS      not-accessible
    STATUS          current
    DESCRIPTION
        "An entry containing current ds1 pm data"
    INDEX           {
                        ifIndex,
                        coiDS1PMHisIntervalType,
			coiDS1PMHisBucketNumber
                    }
    ::= { coiDS1PMHisTable 1 }

CoiDS1PMHisEntry ::= SEQUENCE {
           coiDS1PMHisIntervalType    CoiIntervalType,
	   coiDS1PMHisBucketNumber   Unsigned32,
	   coiDS1HisLCVs      Counter32,
           coiDS1HisPCVs      Counter32,
           coiDS1HisSELSs      Counter32,
           coiDS1HisLESs      Counter32,
           coiDS1HisAISs      Counter32,
           coiDS1HisFCPs      Counter32,
           coiDS1HisESs      Counter32,
           coiDS1HisSESs     Counter32,
           coiDS1HisUASs     Counter32,
           coiDS1HisESFEs      Counter32,
           coiDS1HisSESFEs      Counter32,
           coiDS1HisUASFEs      Counter32,
           coiDS1HisPMValidData TruthValue
}

coiDS1PMHisIntervalType OBJECT-TYPE
    SYNTAX          CoiIntervalType
    MAX-ACCESS      not-accessible
    STATUS          current
    DESCRIPTION
        "This object gives the interval for which ds1 current pm data is collected"
    ::= { coiDS1PMHisEntry 1 }

coiDS1PMHisBucketNumber OBJECT-TYPE
    SYNTAX          Unsigned32 (1..32)
    MAX-ACCESS      not-accessible
    STATUS          current
    DESCRIPTION
        "This object gives the bucket number for DS1
         pm data in given interval."
    ::= { coiDS1PMHisEntry 2 }

coiDS1HisLCVs OBJECT-TYPE
       SYNTAX  Counter32
       MAX-ACCESS  read-only
       STATUS  current
       DESCRIPTION
          "This count will be incremented whenever Line code violation(LCV) event is
	  detected due to either a Bipolar Violation (BPV) or
	  Excessive Zeros (EXZ) error event "
        ::= { coiDS1PMHisEntry 3 }

coiDS1HisPCVs OBJECT-TYPE
       SYNTAX  Counter32
       MAX-ACCESS  read-only
       STATUS  current
       DESCRIPTION
          "Counter for path code violations"
        ::= { coiDS1PMHisEntry 4 }

coiDS1HisSELSs OBJECT-TYPE
       SYNTAX  Counter32
       MAX-ACCESS  read-only
       STATUS  current
       DESCRIPTION
          "Counter for frame loss second, This counter is Incremented when an
	  out-of-frame error is detected and will reset when it is cleared."
        ::= { coiDS1PMHisEntry 5 }

coiDS1HisLESs OBJECT-TYPE
       SYNTAX  Counter32
       MAX-ACCESS  read-only
       STATUS  current
       DESCRIPTION
          "Counter for Line Error seconds, Incremented when Line Code Violation
	  errors are detected."
        ::= { coiDS1PMHisEntry 6 }

coiDS1HisAISs OBJECT-TYPE
       SYNTAX  Counter32
       MAX-ACCESS  read-only
       STATUS  current
       DESCRIPTION
          "Counter for AIS,Incremented when alarm indication
	  signal is detected."
        ::= { coiDS1PMHisEntry 7 }

coiDS1HisFCPs OBJECT-TYPE
       SYNTAX  Counter32
       MAX-ACCESS  read-only
       STATUS  current
       DESCRIPTION
          "Failure count at path(FCP), This counter is incremented
	  at event of any AIS, LOF for first time assertion and re-assertion."
        ::= { coiDS1PMHisEntry 8 }

coiDS1HisESs OBJECT-TYPE
       SYNTAX  Counter32
       MAX-ACCESS  read-only
       STATUS  current
       DESCRIPTION
          "Error Seconds(ES), This counter will be incremented in
	  one of the cases mentioned below
	      -One or more Path Code Violations.
	      -One or more Controlled Slip events "
        ::= { coiDS1PMHisEntry 9 }

coiDS1HisSESs OBJECT-TYPE
       SYNTAX  Counter32
       MAX-ACCESS  read-only
       STATUS  current
       DESCRIPTION
          "Severly Error Seconds(ES),  This count will be incremented
	  in below conditions
	     -320 or more Path Code Violation errors.
	     -One or more Out of Frame defects.
	     -An AIS defect.
	     Note:It will not be incremented during UAS"
        ::= { coiDS1PMHisEntry 10 }

coiDS1HisUASs OBJECT-TYPE
       SYNTAX  Counter32
       MAX-ACCESS  read-only
       STATUS  current
       DESCRIPTION
          "Unavailable Error Seconds(UAS)"
        ::= { coiDS1PMHisEntry 11 }

coiDS1HisESFEs OBJECT-TYPE
       SYNTAX  Counter32
       MAX-ACCESS  read-only
       STATUS  current
       DESCRIPTION
          "Error second at FAR end"
        ::= { coiDS1PMHisEntry 12 }

coiDS1HisSESFEs OBJECT-TYPE
       SYNTAX  Counter32
       MAX-ACCESS  read-only
       STATUS  current
       DESCRIPTION
          "Severly Error second at FAR end"
        ::= { coiDS1PMHisEntry 13 }

coiDS1HisUASFEs OBJECT-TYPE
       SYNTAX  Counter32
       MAX-ACCESS  read-only
       STATUS  current
       DESCRIPTION
          "Unavailable Error second at FAR end"
        ::= { coiDS1PMHisEntry 14 }

coiDS1HisPMValidData OBJECT-TYPE
    SYNTAX          TruthValue
    MAX-ACCESS      read-only
    STATUS          current
    DESCRIPTION
        "This variable indicates if the ds1 pm data for the
         interval identified by coiDS1PMHisIntervalType is valid."
    ::= { coiDS1PMHisEntry 15 }

END
