--*****************************************************************
-- CISCO-DMN-DSG-REMINDER.mib: MIB file for program reminder.
--
-- August 2010, TEL MIB Team
--
-- Copyright (c) 2010 by Cisco Systems, Inc.
-- All rights reserved.
--*****************************************************************

CISCO-DMN-DSG-REMINDER-MIB

DEFINITIONS ::= BEGIN

IMPORTS
    MODULE-IDENTITY,
    OBJECT-TYPE, Integer32
        FROM SNMPv2-SMI
    DisplayString, RowStatus
        FROM SNMPv2-TC
    OBJECT-GROUP, MODULE-COMPLIANCE
        FROM SNMPv2-CONF
    ciscoDSGUtilities
        FROM CISCO-DMN-DSG-ROOT-MIB;


ciscoDSGReminder MODULE-IDENTITY
    LAST-UPDATED    "201008301100Z" -- August 30 2010 11:00:00 GMT
    ORGANIZATION    "Cisco Systems, Inc."
    CONTACT-INFO
       "Cisco Systems, Inc.
        Customer Service
        Postal: 170 W Tasman Drive
        San Jose, CA 95134
        USA
        Tel: +1 800 553 NETS
        E-mail: cs-ipsla@cisco.com"
    DESCRIPTION     "Cisco DSG Reminder Timer MIB."

    REVISION       "201008301100Z"
    DESCRIPTION    "V01.00.02 2010-08-30
                   Updated for adherence to SNMPv2 format."

    REVISION        "201006170600Z"
    DESCRIPTION     "V01.00.01 2010-06-17
                     The enum option for reminderTimerFrequency is
                     corrected."

    REVISION        "201004120600Z"
    DESCRIPTION     "V01.00.00 2010-04-12
                     Initial revision."

    ::= { ciscoDSGUtilities 30 }

reminderTable              OBJECT IDENTIFIER ::= { ciscoDSGReminder 2 }

-- *************************************
-- reminderTimerTable Branch
-- *************************************

reminderTimerTable OBJECT-TYPE
     SYNTAX  SEQUENCE OF ReminderTimerEntry
     MAX-ACCESS  not-accessible
     STATUS  current
     DESCRIPTION
         "Reminder Timer table."
     ::= { reminderTable 1 }

reminderTimerEntry OBJECT-TYPE
     SYNTAX  ReminderTimerEntry
     MAX-ACCESS  not-accessible
     STATUS  current
     DESCRIPTION
         "Entry for Reminder Timer Table."
     INDEX   { reminderTimerID }
     ::= { reminderTimerTable 1 }

ReminderTimerEntry ::=  SEQUENCE
{
    reminderTimerID                 Integer32,
    reminderTimerChType             INTEGER,
    reminderTimerChNum              Integer32,
    reminderTimerChName             DisplayString,
    reminderTimerEvtName            DisplayString,
    reminderTimerDay                INTEGER,
    reminderTimerStartTime          DisplayString,
    reminderTimerEndTime            DisplayString,
    reminderTimerEvtParentalRating  Integer32,
    reminderTimerFrequency          INTEGER,
    reminderTimerRowStatus          RowStatus
}

reminderTimerID OBJECT-TYPE
     SYNTAX  Integer32(1..50)
     MAX-ACCESS  not-accessible
     STATUS  current
     DESCRIPTION
         "Reminder Timer table Index."
     ::= { reminderTimerEntry 1 }

reminderTimerChType OBJECT-TYPE
     SYNTAX  INTEGER{
            tv(1),
            radio(2),
            other(3)
        }
     MAX-ACCESS  read-only
     STATUS  current
     DESCRIPTION
         "Channel type."
     ::= { reminderTimerEntry 2 }

reminderTimerChNum OBJECT-TYPE
     SYNTAX  Integer32(0..65535)
     MAX-ACCESS  read-only
     STATUS  current
     DESCRIPTION
         "Actual channel number."
     ::= { reminderTimerEntry 3 }

reminderTimerChName OBJECT-TYPE
     SYNTAX  DisplayString(SIZE(0..31))
     MAX-ACCESS  read-only
     STATUS  current
     DESCRIPTION
         "Name of channel for which timer has been set."
     ::= { reminderTimerEntry 4 }

reminderTimerEvtName OBJECT-TYPE
     SYNTAX  DisplayString(SIZE(0..31))
     MAX-ACCESS  read-only
     STATUS  current
     DESCRIPTION
         "Name of the event for which timer has been set."
     ::= { reminderTimerEntry 5 }

reminderTimerDay OBJECT-TYPE
     SYNTAX  INTEGER {
            monday(1),
            tuesday(2),
            wednesday(3),
            thursday(4),
            friday(5),
            saturday(6),
            sunday(7)
        }
     MAX-ACCESS  read-only
     STATUS  current
     DESCRIPTION
         "On the day to be reminded."
     ::= { reminderTimerEntry 6 }

reminderTimerStartTime OBJECT-TYPE
     SYNTAX  DisplayString(SIZE(0..31))
     MAX-ACCESS  read-only
     STATUS  current
     DESCRIPTION
         "Timer start time. Format is yyyy-mm-dd hh:mm:ss"
     ::= { reminderTimerEntry 7 }

reminderTimerEndTime OBJECT-TYPE
     SYNTAX  DisplayString(SIZE(0..31))
     MAX-ACCESS  read-only
     STATUS  current
     DESCRIPTION
         "Timer end time. Format is yyyy-mm-dd hh:mm:ss"
     ::= { reminderTimerEntry 8 }

reminderTimerEvtParentalRating OBJECT-TYPE
     SYNTAX  Integer32(1..16)
     MAX-ACCESS  read-only
     STATUS  current
     DESCRIPTION
         "Parental rating of the event to be reminded."
     ::= { reminderTimerEntry 9 }

reminderTimerFrequency OBJECT-TYPE
     SYNTAX  INTEGER {
            once(1),
            daily(2),
            weekly(3),
            weekDays(4)
        }
     MAX-ACCESS  read-only
     STATUS  current
     DESCRIPTION
         "Frequency of timer."
     ::= { reminderTimerEntry 10 }

reminderTimerRowStatus OBJECT-TYPE
     SYNTAX  RowStatus
     MAX-ACCESS  read-only
     STATUS  current
     DESCRIPTION
         " Status of the row."
     ::= { reminderTimerEntry 11 }


END
