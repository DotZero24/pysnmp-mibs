-- *****************************************************************
-- CISCO-DTI-EXT-MIB.my
--
-- Copyright(c) 2014 by cisco Systems Inc.
-- All rights reserved.
--
-- *****************************************************************

CISCO-DTI-EXT-MIB DEFINITIONS ::= BEGIN

IMPORTS
    MODULE-IDENTITY,
    OBJECT-TYPE,
    NOTIFICATION-TYPE
        FROM SNMPv2-SMI
    MODULE-COMPLIANCE,
    NOTIFICATION-GROUP,
    OBJECT-GROUP
        FROM SNMPv2-CONF
    TruthValue
        FROM SNMPv2-TC
    dtiProtocolServerStatusFlag,
    dtiProtocolClientStatusFlag
        FROM DTI-MIB
    ciscoMgmt
        FROM CISCO-SMI;


ciscoDtiExtMIB MODULE-IDENTITY
    LAST-UPDATED    "201408220000Z"
    ORGANIZATION    "Cisco Systems, Inc."
    CONTACT-INFO
            "Cisco Systems
            Customer Service

            Postal: 170 W Tasman Drive
                    San Jose, CA  95134
                    USA

            Tel: +1 800 553-NETS

            E-mail: cs-rfgw10@cisco.com"
    DESCRIPTION
        "This MIB module provides the trap objects necessary to monitor
        the DOCSIS Timing Interface devices."
    REVISION        "201408220000Z"
    DESCRIPTION
        "Latest version of this MIB module."
    ::= { ciscoMgmt 822 }


-- Textual Conventions definition will be defined before this line

ciscoDtiExtNotifs  OBJECT IDENTIFIER
    ::= { ciscoDtiExtMIB 0 }

ciscoDtiExtObjects  OBJECT IDENTIFIER
    ::= { ciscoDtiExtMIB 1 }

ciscoDtiExtConform  OBJECT IDENTIFIER
    ::= { ciscoDtiExtMIB 2 }


-- Default Notification Type

cdeServerStatusChange NOTIFICATION-TYPE
    OBJECTS         { dtiProtocolServerStatusFlag }
    STATUS          current
    DESCRIPTION
        "A cdeServerStatusChange notification is sent
        when the DTI Server state changes."
   ::= { ciscoDtiExtNotifs 1 }

cdeClientStatusChange NOTIFICATION-TYPE
    OBJECTS         { dtiProtocolClientStatusFlag }
    STATUS          current
    DESCRIPTION
        "A cdeClientStatusChange notification is sent
        when the DTI client state changes."
   ::= { ciscoDtiExtNotifs 2 }
ciscoDtiExtCompliances  OBJECT IDENTIFIER
    ::= { ciscoDtiExtConform 1 }


cdeServerStatusChangeEnable OBJECT-TYPE
    SYNTAX          TruthValue
    MAX-ACCESS      read-write
    STATUS          current
    DESCRIPTION
        "This object specifies whether the system produces
        cdeServerStatusChange notifications. A false
        value will prevent cdeserverStatusChange
        notifications from being generated by this system."
    DEFVAL          { false }
    ::= { ciscoDtiExtObjects 1 }

cdeClientStatusChangeEnable OBJECT-TYPE
    SYNTAX          TruthValue
    MAX-ACCESS      read-write
    STATUS          current
    DESCRIPTION
        "This object specifies whether the system produces
        cdeClientStatusChange notifications. A false
        value will prevent cdeClientStatusChange
        notifications from being generated by this system."
    DEFVAL          { false }
    ::= { ciscoDtiExtObjects 2 }
ciscoDtiExtGroups  OBJECT IDENTIFIER
    ::= { ciscoDtiExtConform 2 }


ciscoDtiExtCompliance MODULE-COMPLIANCE
    STATUS          current
    DESCRIPTION
        "This is a default module-compliance
        containing default object groups."
    MODULE          -- this module
    MANDATORY-GROUPS {
                        ciscoDtiExtNotifsControlGroup,
                        ciscoDtiExtNotifsGroup
                    }
    ::= { ciscoDtiExtCompliances 1 }

-- Units of Conformance

ciscoDtiExtNotifsControlGroup OBJECT-GROUP
    OBJECTS         {
                        cdeServerStatusChangeEnable,
                        cdeClientStatusChangeEnable
                    }
    STATUS          current
    DESCRIPTION
        "Contains the group of objects for determining the status of DTI
        client and server status."
    ::= { ciscoDtiExtGroups 1 }

ciscoDtiExtNotifsGroup NOTIFICATION-GROUP
   NOTIFICATIONS    {
                        cdeServerStatusChange,
                        cdeClientStatusChange
                    }
    STATUS          current
    DESCRIPTION
        "Contains the group of notification objects for DTI client and
        server status."
    ::= { ciscoDtiExtGroups 2 }

END
