-- *****************************************************************
-- CISCO-IETF-DOT11-QOS-MIB.my: CISCO IEEE 802.11E QOS MIB file
--
-- February 2002, Francis Pang
--
-- Copyright (c) 2002 by Cisco Systems, Inc.
-- All rights reserved.
-- *****************************************************************
--

-- This MIB is a Cisco implementation of the QoS MIB in
-- IEEE 802.11e/D1.42.0, October November 2001,
-- "Draft Supplement to STANDARD FOR Telecommunications and
-- Information Exchange Between Systems -
-- LAN/MAN Specific Requirements -
-- Part 11: Wireless Medium Access Control (MAC)
-- and physical layer (PHY) specifications:
-- Medium Access Control (MAC) Enhancements for
-- Quality of Service (QoS)".
-- The MIB objects are extracted from 802.11e_nov_2001.pdf file.
-- Both the standard and the MIB are still under development.

CISCO-IETF-DOT11-QOS-MIB DEFINITIONS ::= BEGIN

IMPORTS
        MODULE-IDENTITY,
        OBJECT-TYPE,
        Unsigned32,
        Counter32
                FROM SNMPv2-SMI
        MODULE-COMPLIANCE,
        OBJECT-GROUP
                FROM SNMPv2-CONF
        TEXTUAL-CONVENTION,
        TruthValue
                FROM SNMPv2-TC
        ifIndex
                FROM IF-MIB
        ciscoExperiment
                FROM CISCO-SMI;



ciscoIetfDot11QosMIB MODULE-IDENTITY
        LAST-UPDATED    "200203280000Z"
        ORGANIZATION    "Cisco System Inc."
        CONTACT-INFO
                "       Cisco Systems
                        Customer Service

                Postal: 170 West Tasman Drive,
                        San Jose CA 95134-1706.
                        USA

                   Tel: +1 800 553-NETS

                E-mail: cs-dot11@cisco.com"
        DESCRIPTION
                "This MIB module provides network management
                support for QoS on wireless LAN devices. All
                objects defined in this MIB are listed (object
                names have been modified to adopt Cisco MIB object
                naming convention) in the IEEE 802.11E November
                2001 draft. The original names of the objects
                in the standard are included in the REFERENCE
                clauses. The standard is still under development.
                The standard IEEE 802.11E MIB can replace some of
                the MIB objects in this MIB once the standard is
                finalized.


                          GLOSSARY and ACRONYMS

                Access point (AP)
                    Transmitter/receiver (transceiver) device
                    that commonly connects and transports data
                    between a wireless network and a wired network.

                AIFS
                    Arbitration Interframe Space. It is one of the
                    five different IFSs defined to provide priority
                    levels for access to the wireless media. It shall
                    be used by QSTAs to transmit data type frames
                    (MPDUs) and management type frames (MMPDUs).

                BSS
                    IEEE 802.11 Basic Service Set (Radio Cell). The
                    BSS of an AP comprises of the stations directly
                    associating with the AP.

                CW
                    Contention Window. It is the time period between
                    radio signal collisions caused by simultaneous
                    broadcast from multiple wireless stations.
                    The contention window is used to compute the
                    random backoff of the radio broadcast. The IEEE
                    802.11b does not specify the unit for the time
                    period.

                CWP Factor
                    Contention Window Persistence Factor. It indicates
                    the factor used in computing new CW values on every
                    15 unsuccessful attempt to transmit an MPDU or an
                    MMPDU of a traffic category. It is a scaling factor
                    in units of 1/16 ths.

                IFS
                    Inter-Frame Space is the time interval between
                    frames. A STA shall determine that the medium
                    is idle through the use of the carrier sense
                    function for the interval specified. In other
                    words, the size of the IFS determines the length
                    of the backoff time interval of a device to the
                    medium. In this case, the medium is the radio
                    wave spectrum. The IEEE 802.11b standard does not
                    specify any unit for the time interval.

                BSS
                    IEEE 802.11 Basic Service Set (Radio Cell). The
                MAC
                    Medium Access Control. Layer 2 in the network
                    model.

                MPDU
                    MAC protocol data unit. The unit of data exchanged
                    between two peer MAC entities using the services
                    of the physical layer (PHY).

                MMPDU
                    Management type MAC protocol data unit.

                MSDU
                    MAC service data unit. Information that is
                    delivered as a unit between MAC service access
                    points.

                QBSS
                    Quality of service basic service set.

                QSTA
                    QoS station.

                STA (WSTA)
                    A non-AP IEEE 802.11 wireless station."

        REVISION        "200203280000Z"
        DESCRIPTION
                "Changing the name of cid11QosDiscardedFragments
                to cid11QosIfDiscardedFragments and description
                to indicate it is for transmit fragments only.
                Updating the description of cid11QosDiscardedFrames
                to indicate it is for transmit frame only.
                Modify the default value and range for cid11CWmin
                and cid11CWmax."
        REVISION        "200201290000Z"
        DESCRIPTION
                "Initial version of this MIB module."
        ::= { ciscoExperiment 89 }



ciscoIetfDot11QosMIBObjects       OBJECT IDENTIFIER
        ::= { ciscoIetfDot11QosMIB 1 }

ciscoIetfDot11QosMIBConformance   OBJECT IDENTIFIER
        ::= { ciscoIetfDot11QosMIB 2 }

ciscoIetfDot11QosConfig           OBJECT IDENTIFIER
        ::= { ciscoIetfDot11QosMIBObjects 1 }

ciscoIetfDot11QosQueue            OBJECT IDENTIFIER
        ::= { ciscoIetfDot11QosMIBObjects 2 }

ciscoIetfDot11QosStatistics       OBJECT IDENTIFIER
        ::= { ciscoIetfDot11QosMIBObjects 3 }


-- Textual Conventions


Cid11QosTrafficCategory ::= TEXTUAL-CONVENTION
        STATUS     current
        DESCRIPTION
                "This is the 802.1D IP traffic category. There are
                a total of 8 categories. Each category can be
                mapped to a 802.1P priority level of IP packets.
                The priority levels are implemented using the
                Precedence Bits in the IP packets. The default
                priority levels start from 'background', the
                lowest, to the highest, 'networkControl':
                    background(1)        - background traffic
                                           (lowest priority)
                    spare(2)             - spare traffic
                                           (2nd lowest)
                    bestEffort(0)        - best effort delivery
                                           (this is the default
                                           type for all traffic)
                    excellentEffort(3)   - execellent effect
                    controlledLoad(4)    - controlled load
                    interactiveVideo(5)  - video traffic
                    interactiveVoice(6)  - voice traffic
                    networkControl(7)    - network control
                                           packets (highest)."
        REFERENCE
                "IEEE 802.1D-1998, Annex H.2.10 and
                IEEE 802.11E-2001, section 7.5.1."
        SYNTAX     INTEGER {
                        bestEffort(0),
                        background(1),
                        spare(2),
                        excellentEffort(3),
                        controlledLoad(4),
                        interactiveVideo(5),
                        interactiveVoice(6),
                        networkControl(7) }



-- Configuration and Support Objects

cid11QosConfigTable OBJECT-TYPE
        SYNTAX     SEQUENCE OF Cid11QosConfigEntry
        MAX-ACCESS not-accessible
        STATUS     current
        DESCRIPTION
                "This table contains the basic set of attributes
                to configure QoS for a wireless LAN device. This
                table has a sparse dependent relationship with
                the ifTable. Each IEEE 802.11 wireless interface
                has a set of configuration parameters for each IP
                network traffic category. For each entry in this
                table, there exists an entry in the ifTable of
                ifType ieee80211(71)."
        ::= { ciscoIetfDot11QosConfig 1 }

cid11QosConfigEntry OBJECT-TYPE
        SYNTAX     Cid11QosConfigEntry
        MAX-ACCESS not-accessible
        STATUS     current
        DESCRIPTION
                "Each entry contains parameters to configure
                traffic contention window, AIFS, priority
                and MSDU lifetime for each traffic category
                on an IEEE 802.11 interface."
        INDEX      {
                ifIndex,
                cid11TrafficCategory }
        ::= { cid11QosConfigTable 1 }

Cid11QosConfigEntry ::=
        SEQUENCE {
                cid11TrafficCategory  Cid11QosTrafficCategory,
                cid11CWmin            Unsigned32,
                cid11CWmax            Unsigned32,
                cid11CWPFactor        Unsigned32,
                cid11AIFS             Unsigned32,
                cid11TrafficPriority  Unsigned32,
                cid11MSDULifetime     Unsigned32 }

cid11TrafficCategory OBJECT-TYPE
        SYNTAX     Cid11QosTrafficCategory
        MAX-ACCESS not-accessible
        STATUS     current
        DESCRIPTION
                "This object specifies the traffic category."
        ::= { cid11QosConfigEntry 1 }

cid11CWmin OBJECT-TYPE
        SYNTAX     Unsigned32(0..1023)
        MAX-ACCESS read-write
        STATUS     current
        DESCRIPTION
                "This specifies the minimum contention
                window value for a traffic category. The
                backoff interval of a radio is calculated
                from a pseudo random integer drawn from
                a uniform distribution over the interval
                [1, CW+1], where CW is an integer within
                the range of values of the cid11CWmin and
                cid11CWmax."
        REFERENCE
                "dot11CWmin, IEEE 802.11E-2001/D1."
        DEFVAL     { 0 }
        ::= { cid11QosConfigEntry 2 }

cid11CWmax OBJECT-TYPE
        SYNTAX     Unsigned32(0..1023)
        MAX-ACCESS read-write
        STATUS     current
        DESCRIPTION
                "This object specifies the maximum contention
                window value for a traffic category. The
                backoff interval of a radio is calculated
                from a pseudo random integer drawn from
                a uniform distribution over the interval
                [1, CW+1], where CW is an integer within
                the range of values of the cid11CWmin and
                cid11CWmax."
        REFERENCE
                "dot11CWmax, IEEE 802.11E-2001/D1."
        DEFVAL     { 1023 }
        ::= { cid11QosConfigEntry 3 }

cid11CWPFactor OBJECT-TYPE
        SYNTAX     Unsigned32(0..255)
        MAX-ACCESS read-write
        STATUS     current
        DESCRIPTION
                "This object specifies the contention window
                persistence factor for a traffic category."
        REFERENCE
                "dot11CWPFactor, IEEE 802.11E-2001/D1."
        DEFVAL     { 32 }
        ::= { cid11QosConfigEntry 4 }

cid11AIFS OBJECT-TYPE
        SYNTAX     Unsigned32(2..10)
        MAX-ACCESS read-write
        STATUS     current
        DESCRIPTION
                "This object specifies the AIFS for a traffic
                category."
        REFERENCE
                "dot11AIFS, IEEE 802.11E-2001/D1."
        DEFVAL     { 2 }
        ::= { cid11QosConfigEntry 5 }

cid11TrafficPriority OBJECT-TYPE
        SYNTAX     Unsigned32(0..7)
        MAX-ACCESS read-write
        STATUS     current
        DESCRIPTION
                "This object specifies the actual priority this
                agent is going to use to delivery packets for a
                traffic category. This allows multiple traffic
                categories to map to the same priority level.
                The priority 7 is the highest priority and
                priority 1 is the lowest priority, with priority
                0, which is used for best effort traffic, ordered
                between priority 3 and priority 2. The resulting
                default ordering is {7,6,5,4,3,0,2,1}. The default
                value is same as the traffic category value."
        REFERENCE
                "dot11PriorityMap, IEEE 802.11E-2001/D1
                and IEEE 802.1D-1998, Annex H.2.10."
        ::= { cid11QosConfigEntry 6 }

cid11MSDULifetime OBJECT-TYPE
        SYNTAX     Unsigned32(0..65535)
        MAX-ACCESS read-write
        STATUS     current
        DESCRIPTION
                "This object specifies the MSDU lifetime for a
                traffic category."
        REFERENCE
                "dot11MSDULifetime, IEEE 802.11E-2001/D1."
        DEFVAL     { 65535 }
        ::= { cid11QosConfigEntry 7 }


cid11QosSupportTable OBJECT-TYPE
        SYNTAX     SEQUENCE OF Cid11QosSupportEntry
        MAX-ACCESS not-accessible
        STATUS     current
        DESCRIPTION
                "This table contains the attributes indicating
                QoS support information on the IEEE 802.11
                interfaces of the device. This table has a
                sparse dependent relationship with the ifTable.
                For each entry in this table, there exists an
                entry in the ifTable of ifType ieee80211(71)."
        ::= { ciscoIetfDot11QosConfig 2 }

cid11QosSupportEntry OBJECT-TYPE
        SYNTAX     Cid11QosSupportEntry
        MAX-ACCESS not-accessible
        STATUS     current
        DESCRIPTION
                "Each entry contains attributes to indicate
                if Qos and priority queue are supported for
                an IEEE 802.11 interface."
        INDEX      { ifIndex }
        ::= { cid11QosSupportTable 1 }

Cid11QosSupportEntry ::=
        SEQUENCE {
                cid11QosOptionImplemented  TruthValue,
                cid11QueuesAvailable       Unsigned32 }

cid11QosOptionImplemented OBJECT-TYPE
        SYNTAX     TruthValue
        MAX-ACCESS read-only
        STATUS     current
        DESCRIPTION
                "This object indicates if QoS is supported
                on this IEEE 802.11 network interface."
        REFERENCE
                "dot11QosOptionImplemented, IEEE 802.11E-2001/D1."
        ::= { cid11QosSupportEntry 1 }

cid11QueuesAvailable OBJECT-TYPE
        SYNTAX     Unsigned32(4..8)
        MAX-ACCESS read-only
        STATUS     current
        DESCRIPTION
                "This object shows the number of QoS
                priority queues are available on this
                IEEE 802.11 network interface."
        REFERENCE
                "dot11QueuesAvailable, IEEE 802.11E-2001/D1."
        ::= { cid11QosSupportEntry 2 }


-- Qos Queue Objects

cid11QueueTable OBJECT-TYPE
        SYNTAX     SEQUENCE OF Cid11QueueEntry
        MAX-ACCESS not-accessible
        STATUS     current
        DESCRIPTION
                "This table contains the queue weight and size
                information and statistics for each traffic
                category on each the IEEE 802.11 interface. This
                table has a sparse dependent relationship with the
                ifTable. For each entry in this table, there exists
                an entry in the ifTable of ifType ieee80211(71)."
        ::= { ciscoIetfDot11QosQueue 1 }

cid11QueueEntry OBJECT-TYPE
        SYNTAX     Cid11QueueEntry
        MAX-ACCESS not-accessible
        STATUS     current
        DESCRIPTION
                "Each entry contains the current queue weight, size,
                and peak size information for each traffic category
                on an IEEE 802.11 interface."
        INDEX      {
                ifIndex,
                cid11TrafficCategory }
        ::= { cid11QueueTable 1 }

Cid11QueueEntry ::=
        SEQUENCE {
                cid11QueueSize      Unsigned32,
                cid11QueuePeakSize  Counter32 }

cid11QueueSize OBJECT-TYPE
        SYNTAX     Unsigned32(0..511)
        MAX-ACCESS read-only
        STATUS     current
        DESCRIPTION
                "This is the current QoS priority queue size
                for the traffic category."
        REFERENCE
                "dot11QueueSizeTC, IEEE 802.11E-2001/D1."
        ::= { cid11QueueEntry 1 }

cid11QueuePeakSize OBJECT-TYPE
        SYNTAX     Counter32
        MAX-ACCESS read-only
        STATUS     current
        DESCRIPTION
                "This is the peak QoS priority queue size
                for the traffic category."
        REFERENCE
                "dot11QueuePeakSizeTC, IEEE 802.11E-2001/D1."
        ::= { cid11QueueEntry 2 }


-- Statistics Objects

cid11QosStatisticsTable OBJECT-TYPE
        SYNTAX     SEQUENCE OF Cid11QosStatisticsEntry
        MAX-ACCESS not-accessible
        STATUS     current
        DESCRIPTION
                "This table contains the QoS statistics
                by traffic category on each the IEEE 802.11
                network interface. This table has a sparse
                dependent relationship with the ifTable.
                For each entry in this table, there exists an
                entry in the ifTable of ifType ieee80211(71)."
        ::= { ciscoIetfDot11QosStatistics 1 }

cid11QosStatisticsEntry OBJECT-TYPE
        SYNTAX     Cid11QosStatisticsEntry
        MAX-ACCESS not-accessible
        STATUS     current
        DESCRIPTION
                "Each entry contain QoS statistics for data
                transmission and receive for each traffic
                category on an IEEE 802.11 interface."
        INDEX      {
                ifIndex,
                cid11TrafficCategory }
        ::= { cid11QosStatisticsTable 1 }

Cid11QosStatisticsEntry ::=
        SEQUENCE {
                cid11QosReceivedMPDUs         Counter32,
                cid11QosReceivedRetries       Counter32,
                cid11QosDiscardedFrames       Counter32,
                cid11QosTransmittedFragments  Counter32,
                cid11QosFails                 Counter32,
                cid11QosRetries               Counter32,
                cid11QosMutipleRetries        Counter32,
                cid11QosFrameDuplicates       Counter32,
                cid11QosReceivedFragments     Counter32,
                cid11QosTransmittedFrames     Counter32 }


cid11QosReceivedMPDUs OBJECT-TYPE
        SYNTAX     Counter32
        MAX-ACCESS read-only
        STATUS     current
        DESCRIPTION
                "This is the counter for QoS MPDUs received on
                this IEEE 802.11 interface for the traffic
                category."
        REFERENCE
                "dot11QoSMPDUsReceivedCountTC, IEEE 802.11E-2001/D1."
        ::= { cid11QosStatisticsEntry 1 }

cid11QosReceivedRetries OBJECT-TYPE
        SYNTAX     Counter32
        MAX-ACCESS read-only
        STATUS     current
        DESCRIPTION
                "This is the counter for Qos retries received on
                this IEEE 802.11 interface for the traffic category."
        REFERENCE
                "dot11QoSRetriesReceivedCountTC, IEEE 802.11E-2001/D1."
        ::= { cid11QosStatisticsEntry 2 }

cid11QosDiscardedFrames OBJECT-TYPE
        SYNTAX     Counter32
        MAX-ACCESS read-only
        STATUS     current
        DESCRIPTION
                "This is the counter for Qos discarded frames
                transmitting from this IEEE 802.11 interface for
                the traffic category."
        REFERENCE
                "dot11QosDiscardedFrameCountTC, IEEE 802.11E-2001/D1."
        ::= { cid11QosStatisticsEntry 3 }

cid11QosTransmittedFragments OBJECT-TYPE
        SYNTAX     Counter32
        MAX-ACCESS read-only
        STATUS     current
        DESCRIPTION
                "This is the counter for Qos fragments transmitted
                this IEEE 802.11 interface for the traffic
                category."
        REFERENCE
                "dot11QosTransmittedFragmentCountTC,
                IEEE 802.11E-2001/D1."
        ::= { cid11QosStatisticsEntry 4 }

cid11QosFails OBJECT-TYPE
        SYNTAX     Counter32
        MAX-ACCESS read-only
        STATUS     current
        DESCRIPTION
                "This is the counter for Qos failures on
                this IEEE 802.11 interface for the traffic category."
        REFERENCE
                "dot11QosFailedCountTC, IEEE 802.11E-2001/D1."
        ::= { cid11QosStatisticsEntry 5 }

cid11QosRetries OBJECT-TYPE
        SYNTAX     Counter32
        MAX-ACCESS read-only
        STATUS     current
        DESCRIPTION
                "This is the counter for Qos retries performed on
                this IEEE 802.11 interface for the traffic category."
        REFERENCE
                "dot11QosRetryCountTC, IEEE 802.11E-2001/D1."
        ::= { cid11QosStatisticsEntry 6 }

cid11QosMutipleRetries OBJECT-TYPE
        SYNTAX     Counter32
        MAX-ACCESS read-only
        STATUS     current
        DESCRIPTION
                "This is the counter for Qos multiple retries
                performed on this IEEE 802.11 interface for the
                traffic category."
        REFERENCE
                "dot11QosMutipleRetryCountTC, IEEE 802.11E-2001/D1."
        ::= { cid11QosStatisticsEntry 7 }

cid11QosFrameDuplicates OBJECT-TYPE
        SYNTAX     Counter32
        MAX-ACCESS read-only
        STATUS     current
        DESCRIPTION
                "This is the counter for Qos frame duplications
                performed on this IEEE 802.11 interface for the
                traffic category."
        REFERENCE
                "dot11QosFrameDuplicateCountTC, IEEE 802.11E-2001/D1."
        ::= { cid11QosStatisticsEntry 8 }

cid11QosReceivedFragments OBJECT-TYPE
        SYNTAX     Counter32
        MAX-ACCESS read-only
        STATUS     current
        DESCRIPTION
                "This is the counter for Qos fragments received
                on this IEEE 802.11 interface for the traffic
                category."
        REFERENCE
                "dot11QosReceivedFragmentCountTC,
                IEEE 802.11E-2001/D1."
        ::= { cid11QosStatisticsEntry 9 }

cid11QosTransmittedFrames OBJECT-TYPE
        SYNTAX     Counter32
        MAX-ACCESS read-only
        STATUS     current
        DESCRIPTION
                "This is the counter for Qos frames transmitted
                from this IEEE 802.11 interface for the traffic
                category."
        REFERENCE
                "dot11QosTransmittedFrameCountTC,
                IEEE 802.11E-2001/D1."
        ::= { cid11QosStatisticsEntry 10 }


cid11QosIfStatisticsTable OBJECT-TYPE
        SYNTAX     SEQUENCE OF Cid11QosIfStatisticsEntry
        MAX-ACCESS not-accessible
        STATUS     current
        DESCRIPTION
                "This table contains the attributes indicating
                QoS statistics on the IEEE 802.11 interfaces
                of the device. This table has a sparse dependent
                relationship with the ifTable. For each entry in
                this table, there exists an entry in the ifTable
                of ifType ieee80211(71)."
        ::= { ciscoIetfDot11QosStatistics 2 }

cid11QosIfStatisticsEntry OBJECT-TYPE
        SYNTAX     Cid11QosIfStatisticsEntry
        MAX-ACCESS not-accessible
        STATUS     current
        DESCRIPTION
                "Each entry contains attributes to support
                QoS statistics on an IEEE 802.11 interface."
        INDEX      { ifIndex }
        ::= { cid11QosIfStatisticsTable 1 }


Cid11QosIfStatisticsEntry ::=
        SEQUENCE {
                cid11QosIfDiscardedFragments Counter32 }

cid11QosIfDiscardedFragments OBJECT-TYPE
        SYNTAX     Counter32
        MAX-ACCESS read-only
        STATUS     current
        DESCRIPTION
                "This object counts the number of QoS discarded
                transmitting fragments."
        REFERENCE
                "dot11QosDiscardedFragments,
                IEEE 802.11E-2001/D1."
        ::= { cid11QosIfStatisticsEntry 1 }



-- *****************************************************************
--   Conformance information
-- *****************************************************************

ciscoIetfDot11QosMIBCompliances OBJECT IDENTIFIER
        ::= { ciscoIetfDot11QosMIBConformance 1 }

ciscoIetfDot11QosMIBGroups OBJECT IDENTIFIER
        ::= { ciscoIetfDot11QosMIBConformance 2 }


-- *****************************************************************
--   Compliance statements
-- *****************************************************************


ciscoIetfDot11QosMIBCompliance MODULE-COMPLIANCE
        STATUS     current
        DESCRIPTION
                "The compliance statement for the
                configuration and status groups."
        MODULE
        MANDATORY-GROUPS {
                ciscoIetfDot11QosConfigGroup,
                ciscoIetfDot11QosQueueGroup,
                ciscoIetfDot11QosStatsGroup }
        ::= { ciscoIetfDot11QosMIBCompliances 1 }



-- *****************************************************************
--   Units of conformance
-- *****************************************************************

ciscoIetfDot11QosConfigGroup OBJECT-GROUP
        OBJECTS {
                cid11CWmin,
                cid11CWmax,
                cid11CWPFactor,
                cid11AIFS,
                cid11TrafficPriority,
                cid11MSDULifetime,
                cid11QosOptionImplemented,
                cid11QueuesAvailable }
        STATUS     current
        DESCRIPTION
                "Configurations for IEEE 802.11 QoS."
        ::= { ciscoIetfDot11QosMIBGroups 1 }


ciscoIetfDot11QosQueueGroup OBJECT-GROUP
        OBJECTS {
                cid11QueueSize,
                cid11QueuePeakSize }
        STATUS     current
        DESCRIPTION
                "Configurations and statistics for
                IEEE 802.11 QoS queue."
        ::= { ciscoIetfDot11QosMIBGroups 2 }


ciscoIetfDot11QosStatsGroup OBJECT-GROUP
        OBJECTS {
                cid11QosIfDiscardedFragments,
                cid11QosReceivedMPDUs,
                cid11QosReceivedRetries,
                cid11QosDiscardedFrames,
                cid11QosTransmittedFragments,
                cid11QosFails,
                cid11QosRetries,
                cid11QosMutipleRetries,
                cid11QosFrameDuplicates,
                cid11QosReceivedFragments,
                cid11QosTransmittedFrames }
        STATUS     current
        DESCRIPTION
                "Status and statistics for IEEE 802.11 QoS."
        ::= { ciscoIetfDot11QosMIBGroups 3 }

END
