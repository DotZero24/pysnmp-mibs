-- *****************************************************************
-- CISCO-WAN-CES-RSRC-PART-MIB: CES(Circuit Emulation Service )
--  Resource Partition MIB in MGX82xx series.
--
-- September 2002, Subra Hegde
--
-- Copyright (c) 2002 by cisco Systems, Inc.
-- All rights reserved.
-- *****************************************************************
CISCO-WAN-CES-RSRC-PART-MIB DEFINITIONS ::= BEGIN
IMPORTS
        MODULE-IDENTITY,
        OBJECT-TYPE,
        Integer32           FROM    SNMPv2-SMI
        MODULE-COMPLIANCE,
        OBJECT-GROUP        FROM    SNMPv2-CONF
        cesmPort            FROM    CISCO-WAN-CES-PORT-MIB
        ciscoWan            FROM    CISCOWAN-SMI;

ciscoWanCesRsrcPartMIB MODULE-IDENTITY
        LAST-UPDATED    "200209030000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
    DESCRIPTION
        "The mib module to configure the resource
        partition on Circuit Emulation Service(CES)
        ports. This is applicable for service modules
        providing the Circuit Emulation Services."

    REVISION    "200209030000Z"
    DESCRIPTION
        "Initial version of the MIB.

        The content of this MIB was originally available
        in CISCO-WAN-AXIPOP-MIB defined using SMIv1.
        The applicable objects from CISCO-WAN-AXIPOP-MIB
        are defined using SMIv2 in this MIB. Also the
        descriptions of some of the objects have been
        modified."
    ::= { ciscoWan 41 }


cesmPortCnfResPartGrp            OBJECT IDENTIFIER ::= { cesmPort 2 }

-- ******************************************************************
--
--
--              LOGICAL PORT CONFIG Resource Partition Group
--
--
-- ******************************************************************

cesmPortCnfResPartGrpTable	OBJECT-TYPE
	SYNTAX     SEQUENCE OF CesmPortCnfResPartGrpEntry
	MAX-ACCESS not-accessible
	STATUS     current
	DESCRIPTION
            "This table is for configuring the resource partition
            parameters. "
	::= {cesmPortCnfResPartGrp 1}

cesmPortCnfResPartGrpEntry		OBJECT-TYPE
	SYNTAX     CesmPortCnfResPartGrpEntry
	MAX-ACCESS not-accessible
	STATUS     current
	DESCRIPTION
	    "An entry for a resource partition. A resource
            partition have to be created before connections
            can be added to the logical ports."
	INDEX  { cesmResPartPortNum, cesmResPartCtrlrNum }
	::= { cesmPortCnfResPartGrpTable 1 }

CesmPortCnfResPartGrpEntry ::=
	SEQUENCE {
		cesmResPartPortNum     	 Integer32,
		cesmResPartCtrlrNum      INTEGER,
		cesmResPartRowStatus	 INTEGER,
		cesmResPartNumOfLcnAvail Integer32,
		cesmResPartLcnLow	 Integer32,
		cesmResPartLcnHigh	 Integer32,
		cesmResPartIngrPctBW	 Integer32,
		cesmResPartEgrPctBW	 Integer32,
		cesmResPartCtrlrID       Integer32
	}

cesmResPartPortNum	OBJECT-TYPE
        SYNTAX     Integer32 (1..2048)
        MAX-ACCESS read-only
        STATUS     current
        DESCRIPTION
            "The value of this object identifies the CES port.
            The value of this object must be same as the value
            of 'cesPortNum' from cesmPortCnfGrpTable."
        ::= { cesmPortCnfResPartGrpEntry 1 }

cesmResPartCtrlrNum OBJECT-TYPE
        SYNTAX  INTEGER {
		par (1),
		pnni(2),
		tag (3)
	}
        MAX-ACCESS  read-only
        STATUS  current
        DESCRIPTION
            "This object identifies the controller
            which can be used for accessing the resources.

             The possible values are :
               par(1) : Portable Auto Route controller.
                      : This value is applicable in Release 1.x.

               pnni(2): PNNI  Controller.
                      : This value is applicable in Release 2.x.

               tag(3) : MPLS(Formerly known as Tag Switch)Controller"
        ::= { cesmPortCnfResPartGrpEntry 2 }

cesmResPartRowStatus OBJECT-TYPE
        SYNTAX  INTEGER {
		add (1),
		del (2),
		mod (3)
	}
        MAX-ACCESS  read-write
        STATUS  current
        DESCRIPTION
            "This object is used for adding/deleting/modifying
            resource partition on a CES port.

            In MGX Release 1.x:
                To add an entry, this object should be set to
                add(1), value for other objects should not be
                specified.

            In MGX Release 2.x:
                To add an entry, this object should be set to add(1).

            To delete an entry, this object has to be set to del(2).

            The resource partition can be deleted only after
            deleting all the connections (LCNs)."
        ::= { cesmPortCnfResPartGrpEntry 3 }

cesmResPartNumOfLcnAvail OBJECT-TYPE
        SYNTAX     Integer32 (0..2048)
        MAX-ACCESS read-write
        STATUS     current
        DESCRIPTION
            "This represents number of LCNs available for this
	    controller and this port.
	    In CESM-T3/E3 and 8-T1/E1,this value is 1."
        ::= { cesmPortCnfResPartGrpEntry 4 }

cesmResPartLcnLow OBJECT-TYPE
        SYNTAX     Integer32 (1..2048)
        MAX-ACCESS read-write
        STATUS     current
        DESCRIPTION
            "This represents low end of reserved LCN
	    In CESM-8T1/E1 and T3/E3, this refers to the
            logical port."
        ::= { cesmPortCnfResPartGrpEntry 5 }

cesmResPartLcnHigh OBJECT-TYPE
        SYNTAX     Integer32 (1..2048)
        MAX-ACCESS read-write
        STATUS     current
        DESCRIPTION
            "This represents high end of reserved LCN
	    In CESM-8T1/E1 and T3/E3, this refers to the
            logical port."
        ::= { cesmPortCnfResPartGrpEntry 6 }

cesmResPartIngrPctBW OBJECT-TYPE
        SYNTAX     Integer32 (0..100)
        MAX-ACCESS read-write
        STATUS     current
        DESCRIPTION
                "The percentage of total ingress bandwidth reserved.
                 In CESM-8T1/E1 and T3/E3, as
                 there is only one LCN per port and it could be
                 used by only one controller,this value is
                 100% for that controller.
                "
        ::= { cesmPortCnfResPartGrpEntry 7 }

cesmResPartEgrPctBW OBJECT-TYPE
        SYNTAX     Integer32 (0..100)
        MAX-ACCESS read-write
        STATUS     current
        DESCRIPTION
            "The percentage of total egress bandwidth reserved
            In CESM-8T1/E1 and T3/E3, as
            there is only one LCN per port and it could be
            used by only one controller,this value is
            100% for that controller."
        ::= { cesmPortCnfResPartGrpEntry 8 }

cesmResPartCtrlrID OBJECT-TYPE
        SYNTAX     Integer32(1..255)
        MAX-ACCESS read-write
        STATUS     current
        DESCRIPTION
            "This is the controller identifier for the  resource patition.
            The  default value is set for PNNI controller."
        DEFVAL { 2 }

        ::= { cesmPortCnfResPartGrpEntry 9 }

-- conformance information

cwcRsrcPartMIBConformance OBJECT IDENTIFIER ::=
                              { ciscoWanCesRsrcPartMIB 2 }

cwcRsrcPartMIBCompliances OBJECT IDENTIFIER ::=
                              { cwcRsrcPartMIBConformance 1 }

cwcRsrcPartMIBGroups      OBJECT IDENTIFIER ::=
                              { cwcRsrcPartMIBConformance 2 }


-- compliance statements

ciscoWanCesRsrcPartCompliance MODULE-COMPLIANCE
    STATUS  current
    DESCRIPTION
        "The compliance statement for entities which implement
        the Broad band Interface Resource Partition MIB."
    MODULE  -- this module
        MANDATORY-GROUPS { ciscoWanCesRsrcPartGroup }
    ::= { cwcRsrcPartMIBCompliances 1 }

ciscoWanCesRsrcPartGroup OBJECT-GROUP
    OBJECTS {
        cesmResPartPortNum,
	cesmResPartCtrlrNum,
	cesmResPartRowStatus,
	cesmResPartNumOfLcnAvail,
	cesmResPartLcnLow,
	cesmResPartLcnHigh,
	cesmResPartIngrPctBW,
	cesmResPartEgrPctBW,
	cesmResPartCtrlrID
    }
    STATUS current
    DESCRIPTION
        "A collection of objects providing the
        resource partition configuration on CES
        ports."
    ::= { cwcRsrcPartMIBGroups 1 }

END
