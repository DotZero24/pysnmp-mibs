-- *************************************************************
 -- CISCO EPM NOTIFICATION MIB
 -- MARCH 2002, Tara Jagannathan, John Ahlstrom
 --
    -- Copyright (c) 2002, 2003, 2004 by Cisco Systems, Inc.
 -- All rights reserved.
 -- *************************************************************

 CISCO-EPM-NOTIFICATION-MIB DEFINITIONS ::= BEGIN

 IMPORTS

     MODULE-IDENTITY,
     NOTIFICATION-TYPE,
     Integer32,
     Unsigned32,
     OBJECT-TYPE        FROM SNMPv2-SMI
     MODULE-COMPLIANCE,
     NOTIFICATION-GROUP,
     OBJECT-GROUP       FROM SNMPv2-CONF
     TimeStamp          FROM SNMPv2-TC
     SnmpAdminString    FROM SNMP-FRAMEWORK-MIB
     InetAddressType,
     InetAddress        FROM INET-ADDRESS-MIB
     ciscoMgmt          FROM CISCO-SMI
     ;

 ciscoEpmNotificationMIB MODULE-IDENTITY
     LAST-UPDATED   "200406070000Z"
     ORGANIZATION   "Cisco Systems, Inc."
     CONTACT-INFO   "Cisco Systems
                     Customer Service

                     Postal: 170 W Tasman Drive
                     San Jose, CA 95134

                     Tel: +1 800 553-NETS

                     E-mail: tac@cisco.com"
     DESCRIPTION
     "Notifications directly from hardware and software and processed
     notifications from various management applications can be further
     processed and forwarded by still other management applications to
     indicate the status of devices and software (managed objects).
     The status of these managed objects can be reported by traps.

     The CISCO-EPM-NOTIFICATION-MIB contains the trap structure which
     carries the identity and status info of the managed object as
     analyzed by such an event processor. It is not possible for
     receivers of these traps to query the mib objects.

     A unique but optional feature of the application generating the
     trap defined in this mib is the ability to contain multiple
     partitions in the same system running the application. A
     'Partition' is a logical grouping of a set of managed devices.
     These devices can belong to only one partition at any given
     time. The trap structure will contain information on the exact
     partition number and the partition name of the device where it
     resides.

     The need for trap generation is to enable multiple management
     applications in the network to have a consolidated view of the
     whole network of Cisco and non-Cisco devices."

     REVISION     "200406070000Z"
     DESCRIPTION
     "Updated the cenAlarmEntry to include new attributes. The new
     attributes carries information that adds more value to the already
     existing trap structure.

     The Management application computes events for a device via
     polling snmp mib objects on the device and/or by listening to
     SNMP Traps. Multiple events on a single device roll up into what
     is called an Alert - there can be only one alert for a given
     device at any given time. The objects contained in the
     cenAlarmEntry are the same for both Alert and Event based
     notification. The attribute cenAlarmMode added in this revision
     of the mib can be used to distinguish between the Alert based and
     event based notification.

     In case of event based notification, the cenAlertID would contain
     the alert id, as computed by the management system, to which the
     generated event has been rolled up.

     Traps generated from systems that support mutiple Partition, the
     cenPartitionNumber and cenPartitionName attributes will carry the
     exact partition details of the device for which the trap is
     generated.

     Through the management application user interface, the user can
     customize few attributes of the trap structure. Two attributes
     included in this mib revision that allows the user to customize
     each trap sent out are cenCustomerIdentification and
     cenCustomerRevision.

     ciscoEpmNotificationObjectsGroup, ciscoEpmNotificationAlarm, and
     ciscoEpmNotificationMIBCompliance have been deprecated in this
     revision.

     ciscoEpmNotificationAlarmRev1,
     ciscoEpmNotificationAlarmGroupRev1,
     ciscoEpmNotificationMIBComplianceRev1,
     and ciscoEpmNotificationObjectsGroupRev1 have been newly created
     in this revision."

     REVISION     "200308210000Z"
     DESCRIPTION
     "Included imports for Integer32, Unsigned32, and
     NOTIFICATION-GROUP."

     REVISION     "200207281420Z"
     DESCRIPTION
     "Initial version of this MIB."
     ::= { ciscoMgmt 311 }

 -- MIB Object Definitions

 ciscoEpmNotificationMIBNotifs  OBJECT IDENTIFIER
                                 ::= { ciscoEpmNotificationMIB 0 }
 ciscoEpmNotificationMIBObjects OBJECT IDENTIFIER
                                 ::= { ciscoEpmNotificationMIB 1 }
 ciscoEpmNotificationMIBConform OBJECT IDENTIFIER
                                 ::= { ciscoEpmNotificationMIB 2 }

 cenAlarmData                   OBJECT IDENTIFIER
                                 ::= { ciscoEpmNotificationMIBObjects 1}

 cenAlarmTableMaxLength    OBJECT-TYPE
       SYNTAX              Unsigned32 ( 1..4294967295 )
       MAX-ACCESS          read-write
       STATUS              current
       DESCRIPTION
       "Maximum number of entries permissible in the cenAlarmTable."
       DEFVAL { 1 }
       ::= { cenAlarmData 1 }


 cenAlarmTable             OBJECT-TYPE
       SYNTAX              SEQUENCE OF CenAlarmEntry
       MAX-ACCESS          not-accessible
       STATUS              current
       DESCRIPTION
       "A table containing the device identification and
       alarm value. The maximum number of entries permissible
       in this table is defined by cenAlarmTableMaxLength. When
       the number of entries in the table reaches the maximum
       limit, the next entry would replace the oldest existing
       entry in the table."
       ::= { cenAlarmData 2 }

 cenAlarmEntry          OBJECT-TYPE
       SYNTAX           CenAlarmEntry
       MAX-ACCESS       not-accessible
       STATUS           current
       DESCRIPTION
       "The information regarding a single device status alarm.
       An entry is created when an alarm is processed."
       INDEX            { cenAlarmIndex }
       ::= { cenAlarmTable 1 }

 CenAlarmEntry ::=
         SEQUENCE  {
            cenAlarmIndex                       Unsigned32,
            cenAlarmVersion                     SnmpAdminString,
            cenAlarmTimestamp                   TimeStamp,
            cenAlarmUpdatedTimestamp            TimeStamp,
            cenAlarmInstanceID                  SnmpAdminString,
            cenAlarmStatus                      Integer32,
            cenAlarmStatusDefinition            SnmpAdminString,
            cenAlarmType                        INTEGER,
            cenAlarmCategory                    Integer32,
            cenAlarmCategoryDefinition          SnmpAdminString,
            cenAlarmServerAddressType           InetAddressType,
            cenAlarmServerAddress               InetAddress,
            cenAlarmManagedObjectClass          SnmpAdminString,
            cenAlarmManagedObjectAddressType    InetAddressType,
            cenAlarmManagedObjectAddress        InetAddress,
            cenAlarmDescription                 OCTET STRING,
            cenAlarmSeverity                    Integer32,
            cenAlarmSeverityDefinition          SnmpAdminString,
            cenAlarmTriageValue                 Integer32,
            cenEventIDList                      OCTET STRING,
            cenUserMessage1                     SnmpAdminString,
            cenUserMessage2                     SnmpAdminString,
            cenUserMessage3                     SnmpAdminString,
            cenAlarmMode                        INTEGER,
            cenPartitionNumber                  Unsigned32,
            cenPartitionName                    SnmpAdminString,
            cenCustomerIdentification           SnmpAdminString,
            cenCustomerRevision                 SnmpAdminString,
            cenAlertID                          SnmpAdminString
          }

 -- Alarm attributes

 cenAlarmIndex      OBJECT-TYPE
       SYNTAX       Unsigned32 (1..4294967295)
       MAX-ACCESS   not-accessible
       STATUS       current
       DESCRIPTION
       "A monotonically increasing integer for the sole
       purpose of indexing the attributes in
       ciscoEpmNotificationMIBObjects. When the maximum value is
       reached, this value wraps back to 1."
       ::= { cenAlarmEntry 1 }

 cenAlarmVersion      OBJECT-TYPE
         SYNTAX       SnmpAdminString (SIZE(1..16))
         MAX-ACCESS   read-only
         STATUS       current
         DESCRIPTION
         "The release version of this MIB. The version string will
         be of the form <major version>.<minorversion>."
         ::= { cenAlarmEntry 2 }

 cenAlarmTimestamp      OBJECT-TYPE
         SYNTAX         TimeStamp
         MAX-ACCESS     read-only
         STATUS         current
         DESCRIPTION
         "The time when the alarm was raised."
         ::= { cenAlarmEntry 3 }

 cenAlarmUpdatedTimestamp      OBJECT-TYPE
         SYNTAX                TimeStamp
         MAX-ACCESS            read-only
         STATUS                current
         DESCRIPTION
         "Alarms persist over time and can have their field(s)
         change values. The last time a field(s) changed, this
         alarm is updated. The updated time denotes this time.
         Each alarm is identified by the unique alarm instance
         id, cenAlarmInstanceID."
         ::= { cenAlarmEntry 4 }

 cenAlarmInstanceID      OBJECT-TYPE
         SYNTAX          SnmpAdminString (SIZE(1..20))
         MAX-ACCESS      read-only
         STATUS          current
         DESCRIPTION
         "The Unique Alarm Instance ID."
         ::= { cenAlarmEntry 5 }

 cenAlarmStatus          OBJECT-TYPE
         SYNTAX          Integer32 (1..250)
         MAX-ACCESS      read-only
         STATUS          current
         DESCRIPTION
         "The alarm status indicates the status of the alarm
         in integer value."
         ::= { cenAlarmEntry 6 }

 cenAlarmStatusDefinition      OBJECT-TYPE
         SYNTAX                SnmpAdminString (SIZE(1..255))
         MAX-ACCESS            read-only
         STATUS                current
         DESCRIPTION
         "The short description of the status of the alarm.
         The string is formatted in
         '<integer>,<alarmStatus description>' tuples. The <integer>
         value is the same value that the 'cenAlarmStatus'
         attribute holds. <alarmStatus description> contains one line
         description of the alarm status generated."
         ::= { cenAlarmEntry 7 }

 cenAlarmType            OBJECT-TYPE
         SYNTAX          INTEGER  {
               unknown(1),
               direct(2),
               indirect(3),
               mixed(4)
         }
         MAX-ACCESS      read-only
         STATUS          current
         DESCRIPTION
         "unknown:  When the value for this attribute could not be
                    determined.
          direct:   Denotes an alarm generated by a set of events where
                    all events are reported by an observation(s) of a
                    managed object.
          indirect: Denotes an alarm generated by a set of events where
                    all events were deduced or inferred by the status of
                    managed objects as determined by the network
                    management system.
          mixed:    Denotes an alarm generated by a set of events which
                    were either direct or indirect."
         ::= { cenAlarmEntry 8 }

 cenAlarmCategory        OBJECT-TYPE
         SYNTAX          Integer32 (1..250)
         MAX-ACCESS      read-only
         STATUS          current
         DESCRIPTION
         "The category of the alarm generated represented in
         integer value."
         ::= { cenAlarmEntry 9 }

 cenAlarmCategoryDefinition    OBJECT-TYPE
         SYNTAX                SnmpAdminString (SIZE(1..255))
         MAX-ACCESS            read-only
         STATUS                current
         DESCRIPTION
         "The short description of the category of the alarm
         generated. The String is formatted in
         '<integer>,<alarmCategory description>' tuples. The <integer>
         value is the same value that the 'cenAlarmCategory'
         attribute holds. <alarmCategory description> contains one
         line description of the alarm category generated."
         ::= { cenAlarmEntry 10 }

 cenAlarmServerAddressType   OBJECT-TYPE
         SYNTAX              InetAddressType
         MAX-ACCESS          read-only
         STATUS              current
         DESCRIPTION
         "The type of Internet address by which the server
         is reachable. The Server is the server
         that is generating this trap."
         ::= { cenAlarmEntry 11 }

 cenAlarmServerAddress       OBJECT-TYPE
         SYNTAX              InetAddress
         MAX-ACCESS          read-only
         STATUS              current
         DESCRIPTION
         "The IP Address or the DNS name of the Management
         Server that raised this alarm to be notified."
         ::= { cenAlarmEntry 12 }

 cenAlarmManagedObjectClass    OBJECT-TYPE
         SYNTAX                SnmpAdminString (SIZE(1..255))
         MAX-ACCESS            read-only
         STATUS                current
         DESCRIPTION
         "The class of the managed object for which this
         alarm was  generated. For example, Router, Switch,
         GateKeeper and VoicePort."
         ::= { cenAlarmEntry  13 }

 cenAlarmManagedObjectAddressType   OBJECT-TYPE
         SYNTAX                     InetAddressType
         MAX-ACCESS                 read-only
         STATUS                     current
         DESCRIPTION
         "The type of Internet address by which the managed
         object is reachable."
         ::= { cenAlarmEntry 14 }

 cenAlarmManagedObjectAddress       OBJECT-TYPE
         SYNTAX                     InetAddress
         MAX-ACCESS                 read-only
         STATUS                     current
         DESCRIPTION
         "The IP Address or the DNS name of the Managed Object."
         ::= { cenAlarmEntry 15 }

 cenAlarmDescription          OBJECT-TYPE
         SYNTAX               OCTET STRING (SIZE(1..1024))
         MAX-ACCESS           read-only
         STATUS               current
         DESCRIPTION
         "A detailed description of the alarm."
         ::= { cenAlarmEntry 16 }

 cenAlarmSeverity        OBJECT-TYPE
         SYNTAX          Integer32  (0..100)
         MAX-ACCESS      read-only
         STATUS          current
         DESCRIPTION
         "The alarm severity indicates the severity of the alarm
         in integer value."
         ::= { cenAlarmEntry 17 }

 cenAlarmSeverityDefinition      OBJECT-TYPE
         SYNTAX                  SnmpAdminString (SIZE(1..255))
         MAX-ACCESS              read-only
         STATUS                  current
         DESCRIPTION
         "The short description of the severity of the alarm
         generated. The String is formatted in
         '<integer>,<alarmSeverity  description>' tuples. The <integer>
         value is the same value that the 'cenAlarmSeverity '
         attribute holds. <alarmSeverity description> contains one line
         description of the alarm severity generated."
         ::= { cenAlarmEntry 18 }

 cenAlarmTriageValue     OBJECT-TYPE
         SYNTAX          Integer32(0..100)
         MAX-ACCESS      read-only
         STATUS          current
         DESCRIPTION
         "The triage value of an alarm is a hierarchical weighting value
         (applied by the application, and more importantly customizable
         by the end  user) to allow an artificial form of evaluating
         impact, interest, or other user-determined functions between
         alarms. The value is a positive number or zero where zero
         denotes an undetermined or uncomputable value."
         ::= { cenAlarmEntry 19 }

 cenEventIDList          OBJECT-TYPE
         SYNTAX          OCTET STRING (SIZE(1..1024))
         MAX-ACCESS      read-only
         STATUS          current
         DESCRIPTION
         "Comma separated list of the Unique Event identifiers
         that led to the generation of this Alarm."
         ::= { cenAlarmEntry 20 }

 cenUserMessage1         OBJECT-TYPE
         SYNTAX          SnmpAdminString (SIZE(1..255))
         MAX-ACCESS      read-only
         STATUS          current
         DESCRIPTION
         "User input message. This value can be configured."
         ::= { cenAlarmEntry 21 }

 cenUserMessage2         OBJECT-TYPE
         SYNTAX          SnmpAdminString (SIZE(1..255))
         MAX-ACCESS      read-only
         STATUS          current
         DESCRIPTION
         "User input message. This value can be configured."
         ::= { cenAlarmEntry 22 }

 cenUserMessage3         OBJECT-TYPE
         SYNTAX          SnmpAdminString (SIZE(1..255))
         MAX-ACCESS      read-only
         STATUS          current
         DESCRIPTION
         "User input message. This value can be configured."
         ::= { cenAlarmEntry 23 }

 cenAlarmMode            OBJECT-TYPE
         SYNTAX          INTEGER  {
               unknown(1),
               alert(2),
               event(3)
         }
         MAX-ACCESS      read-only
         STATUS          current
         DESCRIPTION
         "unknown:  When the value for this attribute could not be
                    determined.
          alert:    Denotes an alarm generated by a set of events where
                    all events are reported by polling of managed
                    objects and/or listening to SNMP notifications.
          event:    Denotes an event generated by polling of managed
                    ojects and/or listening to SNMP notifications."
         ::= { cenAlarmEntry 24 }

 cenPartitionNumber      OBJECT-TYPE
         SYNTAX          Unsigned32(0..100)
         MAX-ACCESS      read-only
         STATUS          current
         DESCRIPTION
         "In traps generated by the management application that support
         multiple partitions, the attribute will carry the integer
         value assigned to identify the logical group where the managed
         device resides."
         ::= { cenAlarmEntry 25 }

 cenPartitionName        OBJECT-TYPE
         SYNTAX          SnmpAdminString (SIZE(1..255))
         MAX-ACCESS      read-only
         STATUS          current
         DESCRIPTION
         "In traps generated by the management application that support
         multiple partitions, the attribute will carry the name
         assigned to identify the logical group where the managed
         device resides."
         ::= { cenAlarmEntry 26 }

 cenCustomerIdentification      OBJECT-TYPE
         SYNTAX                 SnmpAdminString (SIZE(1..255))
         MAX-ACCESS             read-only
         STATUS                 current
         DESCRIPTION
         "User input message. The attribute takes in a free format
         text. This attribute can be used by advanced management
         applications to sort responses from the fault management
         server."
         ::= { cenAlarmEntry 27 }

 cenCustomerRevision     OBJECT-TYPE
         SYNTAX          SnmpAdminString (SIZE(1..255))
         MAX-ACCESS      read-only
         STATUS          current
         DESCRIPTION
         "User input message. The attribute takes in a free format
         text. This attribute can be used by advanced management
         applications to sort responses from the fault management
         server."
         ::= { cenAlarmEntry 28 }

 cenAlertID     OBJECT-TYPE
         SYNTAX          SnmpAdminString (SIZE(1..20))
         MAX-ACCESS      read-only
         STATUS          current
         DESCRIPTION
         "In event based notification, this attribute will contain the
         alert id to which the generated event has been rolled up
         to. In alert based notification, the cenAlarmInstanceId and
         cenAlertID would be identical."
         ::= { cenAlarmEntry 29 }

ciscoEpmNotificationAlarm    NOTIFICATION-TYPE
        OBJECTS  {
                    cenAlarmVersion,
                    cenAlarmTimestamp,
                    cenAlarmUpdatedTimestamp,
                    cenAlarmInstanceID,
                    cenAlarmStatus,
                    cenAlarmStatusDefinition,
                    cenAlarmType,
                    cenAlarmCategory,
                    cenAlarmCategoryDefinition,
                    cenAlarmServerAddressType,
                    cenAlarmServerAddress,
                    cenAlarmManagedObjectClass,
                    cenAlarmManagedObjectAddressType,
                    cenAlarmManagedObjectAddress,
                    cenAlarmDescription,
                    cenAlarmSeverity,
                    cenAlarmSeverityDefinition,
                    cenAlarmTriageValue,
                    cenEventIDList,
                    cenUserMessage1,
                    cenUserMessage2,
                    cenUserMessage3
        }
        STATUS           deprecated
        DESCRIPTION
        "Notification of the status of the managed object as
        generated by the  management server.

        New attributes are added to the ciscoEpmNotificationAlarmRev1.
        Hence this notification is deprecated."
        ::= { ciscoEpmNotificationMIBNotifs 1 }

 ciscoEpmNotificationAlarmRev1    NOTIFICATION-TYPE
         OBJECTS  {
                     cenAlarmVersion,
                     cenAlarmTimestamp,
                     cenAlarmUpdatedTimestamp,
                     cenAlarmInstanceID,
                     cenAlarmStatus,
                     cenAlarmStatusDefinition,
                     cenAlarmType,
                     cenAlarmCategory,
                     cenAlarmCategoryDefinition,
                     cenAlarmServerAddressType,
                     cenAlarmServerAddress,
                     cenAlarmManagedObjectClass,
                     cenAlarmManagedObjectAddressType,
                     cenAlarmManagedObjectAddress,
                     cenAlarmDescription,
                     cenAlarmSeverity,
                     cenAlarmSeverityDefinition,
                     cenAlarmTriageValue,
                     cenEventIDList,
                     cenUserMessage1,
                     cenUserMessage2,
                     cenUserMessage3,
                     cenAlarmMode,
                     cenPartitionNumber,
                     cenPartitionName,
                     cenCustomerIdentification,
                     cenCustomerRevision,
                     cenAlertID
         }
         STATUS           current
         DESCRIPTION
         "Notification of the status of the managed object as
         generated by the  management server."
         ::= { ciscoEpmNotificationMIBNotifs 2 }


 -- Conformance information

 ciscoEpmNotificationMIBCompliances OBJECT IDENTIFIER
                            ::= { ciscoEpmNotificationMIBConform 1 }
 ciscoEpmNotificationMIBGroups OBJECT IDENTIFIER
                            ::= { ciscoEpmNotificationMIBConform 2 }
 -- Compliance

 ciscoEpmNotificationMIBCompliance MODULE-COMPLIANCE
         STATUS deprecated
         DESCRIPTION
         "The compliance statement for entities which
         implement the CISCO-EPM-NOTIFICATION-MIB.


         New attributes are included in
         ciscoEpmNotificationMIBComplianceRev1. Hence this object is
         deprecated."
         MODULE -- this module
         MANDATORY-GROUPS {
             ciscoEpmNotificationObjectsGroup,
             ciscoEpmNotificationAlarmGroup
         }

         GROUP       ciscoEpmAlarmConfigGroup
         DESCRIPTION
         "This group is optional."

         OBJECT cenAlarmTableMaxLength
         MIN-ACCESS read-only
         DESCRIPTION
         "Write access is not required."

         OBJECT cenAlarmVersion
         MIN-ACCESS accessible-for-notify
         DESCRIPTION
             "Read access is not required."

         OBJECT cenAlarmTimestamp
         MIN-ACCESS accessible-for-notify
         DESCRIPTION
             "Read access is not required."

         OBJECT cenAlarmUpdatedTimestamp
         MIN-ACCESS accessible-for-notify
         DESCRIPTION
             "Read access is not required."

         OBJECT cenAlarmInstanceID
         MIN-ACCESS accessible-for-notify
         DESCRIPTION
             "Read access is not required."

         OBJECT cenAlarmStatus
         MIN-ACCESS accessible-for-notify
         DESCRIPTION
             "Read access is not required."

         OBJECT cenAlarmStatusDefinition
         MIN-ACCESS accessible-for-notify
         DESCRIPTION
             "Read access is not required."

         OBJECT cenAlarmType
         MIN-ACCESS accessible-for-notify
         DESCRIPTION
             "Read access is not required."

         OBJECT cenAlarmCategory
         MIN-ACCESS accessible-for-notify
         DESCRIPTION
             "Read access is not required."

         OBJECT cenAlarmCategoryDefinition
         MIN-ACCESS accessible-for-notify
         DESCRIPTION
             "Read access is not required."

         OBJECT cenAlarmServerAddressType
         MIN-ACCESS accessible-for-notify
         DESCRIPTION
             "Read access is not required."

         OBJECT cenAlarmServerAddress
         MIN-ACCESS accessible-for-notify
         DESCRIPTION
             "Read access is not required."

         OBJECT cenAlarmManagedObjectClass
         MIN-ACCESS accessible-for-notify
         DESCRIPTION
             "Read access is not required."

         OBJECT cenAlarmManagedObjectAddressType
         MIN-ACCESS accessible-for-notify
         DESCRIPTION
             "Read access is not required."

         OBJECT cenAlarmManagedObjectAddress
         MIN-ACCESS accessible-for-notify
         DESCRIPTION
             "Read access is not required."

         OBJECT cenAlarmDescription
         MIN-ACCESS accessible-for-notify
         DESCRIPTION
             "Read access is not required."

         OBJECT cenAlarmSeverity
         MIN-ACCESS accessible-for-notify
         DESCRIPTION
             "Read access is not required."

         OBJECT cenAlarmSeverityDefinition
         MIN-ACCESS accessible-for-notify
         DESCRIPTION
             "Read access is not required."

         OBJECT cenAlarmTriageValue
         MIN-ACCESS accessible-for-notify
         DESCRIPTION
             "Read access is not required."

         OBJECT cenEventIDList
         MIN-ACCESS accessible-for-notify
         DESCRIPTION
             "Read access is not required."

         OBJECT cenUserMessage1
         MIN-ACCESS accessible-for-notify
         DESCRIPTION
             "Read access is not required."

         OBJECT cenUserMessage2
         MIN-ACCESS accessible-for-notify
         DESCRIPTION
             "Read access is not required."

         OBJECT cenUserMessage3
         MIN-ACCESS accessible-for-notify
         DESCRIPTION
             "Read access is not required."
         ::= { ciscoEpmNotificationMIBCompliances  1 }

 ciscoEpmNotificationMIBComplianceRev1 MODULE-COMPLIANCE
         STATUS current
         DESCRIPTION
         "The compliance statement for entities which
         implement the CISCO-EPM-NOTIFICATION-MIB."
         MODULE -- this module
         MANDATORY-GROUPS {
             ciscoEpmNotificationObjectsGroupRev1,
             ciscoEpmNotificationAlarmGroupRev1
         }

         GROUP       ciscoEpmAlarmConfigGroup
         DESCRIPTION
         "This group is optional."

         OBJECT cenAlarmTableMaxLength
         MIN-ACCESS read-only
         DESCRIPTION
         "Write access is not required."

         OBJECT cenAlarmVersion
         MIN-ACCESS accessible-for-notify
         DESCRIPTION
             "Read access is not required."

         OBJECT cenAlarmTimestamp
         MIN-ACCESS accessible-for-notify
         DESCRIPTION
             "Read access is not required."

         OBJECT cenAlarmUpdatedTimestamp
         MIN-ACCESS accessible-for-notify
         DESCRIPTION
             "Read access is not required."

         OBJECT cenAlarmInstanceID
         MIN-ACCESS accessible-for-notify
         DESCRIPTION
             "Read access is not required."

         OBJECT cenAlarmStatus
         MIN-ACCESS accessible-for-notify
         DESCRIPTION
             "Read access is not required."

         OBJECT cenAlarmStatusDefinition
         MIN-ACCESS accessible-for-notify
         DESCRIPTION
             "Read access is not required."

         OBJECT cenAlarmType
         MIN-ACCESS accessible-for-notify
         DESCRIPTION
             "Read access is not required."

         OBJECT cenAlarmCategory
         MIN-ACCESS accessible-for-notify
         DESCRIPTION
             "Read access is not required."

         OBJECT cenAlarmCategoryDefinition
         MIN-ACCESS accessible-for-notify
         DESCRIPTION
             "Read access is not required."

         OBJECT cenAlarmServerAddressType
         MIN-ACCESS accessible-for-notify
         DESCRIPTION
             "Read access is not required."

         OBJECT cenAlarmServerAddress
         MIN-ACCESS accessible-for-notify
         DESCRIPTION
             "Read access is not required."

         OBJECT cenAlarmManagedObjectClass
         MIN-ACCESS accessible-for-notify
         DESCRIPTION
             "Read access is not required."

         OBJECT cenAlarmManagedObjectAddressType
         MIN-ACCESS accessible-for-notify
         DESCRIPTION
             "Read access is not required."

         OBJECT cenAlarmManagedObjectAddress
         MIN-ACCESS accessible-for-notify
         DESCRIPTION
             "Read access is not required."

         OBJECT cenAlarmDescription
         MIN-ACCESS accessible-for-notify
         DESCRIPTION
             "Read access is not required."

         OBJECT cenAlarmSeverity
         MIN-ACCESS accessible-for-notify
         DESCRIPTION
             "Read access is not required."

         OBJECT cenAlarmSeverityDefinition
         MIN-ACCESS accessible-for-notify
         DESCRIPTION
             "Read access is not required."

         OBJECT cenAlarmTriageValue
         MIN-ACCESS accessible-for-notify
         DESCRIPTION
             "Read access is not required."

         OBJECT cenEventIDList
         MIN-ACCESS accessible-for-notify
         DESCRIPTION
             "Read access is not required."

         OBJECT cenUserMessage1
         MIN-ACCESS accessible-for-notify
         DESCRIPTION
             "Read access is not required."

         OBJECT cenUserMessage2
         MIN-ACCESS accessible-for-notify
         DESCRIPTION
             "Read access is not required."

         OBJECT cenUserMessage3
         MIN-ACCESS accessible-for-notify
         DESCRIPTION
             "Read access is not required."

         OBJECT cenAlarmMode
         MIN-ACCESS accessible-for-notify
         DESCRIPTION
             "Read access is not required."

         OBJECT cenPartitionNumber
         MIN-ACCESS accessible-for-notify
         DESCRIPTION
             "Read access is not required."

         OBJECT cenPartitionName
         MIN-ACCESS accessible-for-notify
         DESCRIPTION
             "Read access is not required."

         OBJECT cenCustomerIdentification
         MIN-ACCESS accessible-for-notify
         DESCRIPTION
             "Read access is not required."

         OBJECT cenCustomerRevision
         MIN-ACCESS accessible-for-notify
         DESCRIPTION
             "Read access is not required."

         OBJECT cenAlertID
         MIN-ACCESS accessible-for-notify
         DESCRIPTION
             "Read access is not required."

         ::= { ciscoEpmNotificationMIBCompliance  2 }

 -- Units of Conformance

 ciscoEpmNotificationAlarmGroup NOTIFICATION-GROUP
     NOTIFICATIONS {
         ciscoEpmNotificationAlarm
     }
     STATUS      deprecated
     DESCRIPTION
     "The collection of notifications used to indicate managed
     object status.

     ciscoEpmNotificationAlarmGroupRev1 is defined. Hence this
     object is deprecated."
     ::= { ciscoEpmNotificationMIBGroups 1 }

 ciscoEpmNotificationObjectsGroup    OBJECT-GROUP
     OBJECTS {
                     cenAlarmVersion,
                     cenAlarmTimestamp,
                     cenAlarmUpdatedTimestamp,
                     cenAlarmInstanceID,
                     cenAlarmStatus,
                     cenAlarmStatusDefinition,
                     cenAlarmType,
                     cenAlarmCategory,
                     cenAlarmCategoryDefinition,
                     cenAlarmServerAddressType,
                     cenAlarmServerAddress,
                     cenAlarmManagedObjectClass,
                     cenAlarmManagedObjectAddressType,
                     cenAlarmManagedObjectAddress,
                     cenAlarmDescription,
                     cenAlarmSeverity,
                     cenAlarmSeverityDefinition,
                     cenAlarmTriageValue,
                     cenEventIDList,
                     cenUserMessage1,
                     cenUserMessage2,
                     cenUserMessage3
     }
     STATUS      deprecated
     DESCRIPTION
     "Trap reflecting the alarm.

     New attributes are added to the new notification
     ciscoEpmNotificationObjectsGroupRev1. Hence
     this object is deprecated."
     ::= { ciscoEpmNotificationMIBGroups   2 }

 ciscoEpmAlarmConfigGroup    OBJECT-GROUP
     OBJECTS { cenAlarmTableMaxLength }
     STATUS      current
     DESCRIPTION
     "A collection of objects providing information
     about the total number of cenAlarmTable entries
     maintained."
     ::= { ciscoEpmNotificationMIBGroups   3 }

 ciscoEpmNotificationAlarmGroupRev1 NOTIFICATION-GROUP
     NOTIFICATIONS {
         ciscoEpmNotificationAlarmRev1
     }
     STATUS      current
     DESCRIPTION
     "The collection of notifications used to indicate managed object
     status."
     ::= { ciscoEpmNotificationMIBGroups 4 }

 ciscoEpmNotificationObjectsGroupRev1    OBJECT-GROUP
     OBJECTS {
                     cenAlarmVersion,
                     cenAlarmTimestamp,
                     cenAlarmUpdatedTimestamp,
                     cenAlarmInstanceID,
                     cenAlarmStatus,
                     cenAlarmStatusDefinition,
                     cenAlarmType,
                     cenAlarmCategory,
                     cenAlarmCategoryDefinition,
                     cenAlarmServerAddressType,
                     cenAlarmServerAddress,
                     cenAlarmManagedObjectClass,
                     cenAlarmManagedObjectAddressType,
                     cenAlarmManagedObjectAddress,
                     cenAlarmDescription,
                     cenAlarmSeverity,
                     cenAlarmSeverityDefinition,
                     cenAlarmTriageValue,
                     cenEventIDList,
                     cenUserMessage1,
                     cenUserMessage2,
                     cenUserMessage3,
                     cenAlarmMode,
                     cenPartitionNumber,
                     cenPartitionName,
                     cenCustomerIdentification,
                     cenCustomerRevision,
                     cenAlertID
     }
     STATUS      current
     DESCRIPTION
     "Notification reflecting the alarm."
     ::= { ciscoEpmNotificationMIBGroups   5 }

END
