--------------------------------------------------------------------
-- Cisco version of the supplemental AtoM MIB for switch reg. Addresses
--
-- January 1996, Kartik Chandrasekhar
--
-- Copyright (c) 1996 by cisco Systems, Inc.
-- All rights reserved.
--------------------------------------------------------------------
--


CISCO-ATM-ADDR-MIB DEFINITIONS ::= BEGIN

IMPORTS
    MODULE-IDENTITY,
    OBJECT-TYPE                      FROM SNMPv2-SMI
    TEXTUAL-CONVENTION,
    RowStatus                        FROM SNMPv2-TC
    MODULE-COMPLIANCE,
    OBJECT-GROUP                     FROM SNMPv2-CONF
    ifIndex                          FROM IF-MIB
    ciscoExperiment                  FROM CISCO-SMI;


ciscoAtmAddrMIB MODULE-IDENTITY
    LAST-UPDATED	"9605060000Z"
    ORGANIZATION	"Cisco Systems, Inc."
    CONTACT-INFO
		"       Cisco Systems
			Customer Service

		Postal: 170 W Tasman Drive
			San Jose, CA  95134
			USA

		   Tel: +1 800 553-NETS

		E-mail: cs-atm@cisco.com"
    DESCRIPTION
		"ATM address MIB"
    REVISION	"9605060000Z"
	DESCRIPTION
			"Initial version of this MIB module."

    ::= { ciscoExperiment 12 }    -- assigned by cana@cisco.com


-- AtmAddr defined here for completeness.  Over time it should be
-- imported from the ATMTC-MIB under development by the IETF
AtmAddr ::= TEXTUAL-CONVENTION
    STATUS  current
    DESCRIPTION
		"The ATM address used by the network entity.  The
		address types are: no address (0 octets), E.164 (8
		octets), network prefix (13 octets), and NSAP (20
		octets).  Note: The E.164 address is encoded in
		BCD format."
SYNTAX    OCTET STRING (SIZE(0|8|13|20))



ciscoAtmAddrMIBObjects  OBJECT IDENTIFIER ::= { ciscoAtmAddrMIB 1 }

          -- ATM Interface Administrative Address Table
          -- This table contains a list of the valid calling party
          -- addresses for a UNI in the case of both PVCs and SVCs.
          -- For PVCs, if addresses are not used then an entry in
          -- this table is not necessary.

ciscoAtmIfAdminAddrTable    OBJECT-TYPE
    SYNTAX       SEQUENCE OF CiscoAtmIfAdminAddrEntry
    MAX-ACCESS   not-accessible
    STATUS       current
    DESCRIPTION
                 "This table contains an address list on a per interface
                 basis.  This table only applies to switches or networks
                 and only for interfaces that have more than one address
                 assigned."
    ::= { ciscoAtmAddrMIBObjects 1 }

ciscoAtmIfAdminAddrEntry    OBJECT-TYPE
    SYNTAX            CiscoAtmIfAdminAddrEntry
    MAX-ACCESS        not-accessible
    STATUS            current
    DESCRIPTION
                 "An entry in the CiscoAtmIfAdminAddrTable."
    INDEX { ifIndex, ciscoAtmIfAdminAddrAddress }
    ::= { ciscoAtmIfAdminAddrTable 1 }

CiscoAtmIfAdminAddrEntry    ::=
    SEQUENCE  {
        ciscoAtmIfAdminAddrAddress     AtmAddr,
        ciscoAtmIfAdminAddrRowStatus   RowStatus
    }

ciscoAtmIfAdminAddrAddress   OBJECT-TYPE
    SYNTAX             AtmAddr
    MAX-ACCESS         not-accessible
    STATUS             current
    DESCRIPTION
                "A valid address for a given switch or network
                 interface."
    ::= { ciscoAtmIfAdminAddrEntry 1}

ciscoAtmIfAdminAddrRowStatus OBJECT-TYPE
    SYNTAX             RowStatus
    MAX-ACCESS         read-write
    STATUS             current
    DESCRIPTION
                 "This object is used to create and delete rows in the
                 atmIfAdminAddrTable."
    ::= { ciscoAtmIfAdminAddrEntry 2}



-- Conformance Information

ciscoAtmIfAdminAddrMIBConformance
              OBJECT IDENTIFIER ::= { ciscoAtmAddrMIB 3 }
ciscoAtmIfAdminAddrMIBCompliances
              OBJECT IDENTIFIER ::= { ciscoAtmIfAdminAddrMIBConformance 1 }
ciscoAtmIfAdminAddrMIBGroups
              OBJECT IDENTIFIER ::= { ciscoAtmIfAdminAddrMIBConformance 2 }


-- Compliance Statements

ciscoAtmIfAdminAddrMIBCompliance MODULE-COMPLIANCE
    STATUS  current
    DESCRIPTION
                  "The compliance statement for the Cisco ATM address
                   group."
    MODULE  -- this module
            MANDATORY-GROUPS { ciscoAtmIfAdminAddrMIBGroup }

    ::= { ciscoAtmIfAdminAddrMIBCompliances 1 }


-- Units of Conformance


ciscoAtmIfAdminAddrMIBGroup  OBJECT-GROUP
    OBJECTS {
	ciscoAtmIfAdminAddrRowStatus
    }
    STATUS    current
    DESCRIPTION
                  "This object is used to create and delete rows in the
                   atmIfAdminAddrTable."
    ::= { ciscoAtmIfAdminAddrMIBGroups 1 }




END
