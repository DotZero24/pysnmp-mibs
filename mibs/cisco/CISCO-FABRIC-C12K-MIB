-- *****************************************************************
-- CISCO-FABRIC-C12K-MIB.my: Cisco Fabric MIB for c12000 series.
--
-- July 2002,  K.Muralidhar
--
-- Copyright (c) 2002 by cisco Systems, Inc.
-- All rights reserved.
-- *****************************************************************

CISCO-FABRIC-C12K-MIB DEFINITIONS ::= BEGIN

IMPORTS

    Counter32,
    Unsigned32,
    MODULE-IDENTITY,
    OBJECT-TYPE,
    NOTIFICATION-TYPE
        FROM SNMPv2-SMI
    TEXTUAL-CONVENTION,
    TruthValue
        FROM SNMPv2-TC
    SnmpAdminString
        FROM SNMP-FRAMEWORK-MIB
    MODULE-COMPLIANCE,
    NOTIFICATION-GROUP,
    OBJECT-GROUP
        FROM SNMPv2-CONF
    PhysicalIndex,
    entPhysicalIndex,
    entPhysicalName
        FROM ENTITY-MIB
    EntPhysicalIndexOrZero
        FROM CISCO-TC
    ciscoMgmt
        FROM CISCO-SMI;

ciscoFabricC12kMIB MODULE-IDENTITY
    LAST-UPDATED    "200209200000Z"
    ORGANIZATION    "Cisco Systems, Inc."
    CONTACT-INFO
            "       Cisco Systems
                    Customer Service

            Postal: 170 W. Tasman Drive
                    San Jose, CA  95134
                    USA

            Tel: +1 800 553-NETS

            E-mail: gsr-netman@cisco.com"
    DESCRIPTION
        "Cisco Fabric MIB module for c12000 series of routers.
        This MIB module is used for managing/tracking the c12000
        fabric entities and fabric related configuration, status
        and statistics information.

        C12000 fabric architecture is based on NxN non-blocking
        crossbar switch fabric, where N stands for the maximum
        number of LCs that can be supported in the chassis (this
        includes the RP). The connections through the switch
        fabric is controlled by a scheduler (CSC), the CSC
        accepts transmission requests from line cards, issues
        grants to access the fabric, and provides a reference
        clock to all the cards in the system to synchronize data
        transfer across the crossbar.

        Some of the error status objects in the MIB are read-clear,
        that is the value of the object is cleared on a query of the
        object.

        Details about the various fabric related attributes
        specified in the MIB could be found at following link,
        http://www.cisco.com/warp/public/108/hwts_12000_22281.html

        Acronyms and terms used in the MIB module:
        GSR           - Gigabit Switch Router.
        RP            - Route Processor.
        LC            - Line Card.
        SFC           - Switch Fabric Card.
        CRC           - Cyclic Redundancy Check.
        CSC           - Clock Scheduler Card.
        CiscoCell     - The unit of data that is exchanged
                        between line cards through the switch
                        fabric.
        FIA           - Fabric Interface Asic, this Asic
                        resides on the line card and is
                        used to interface line card and
                        switch fabric.
        ToFabFIA      - Represents the ToFabric FIA, FIA
                        which transmits data from the
                        line card to the fabric.
        FrFabFIA      - Represents the From Fabric FIA, FIA
                        which receives data from the fabric.
        SCA           - Scheduler Control Asic, this Asic
                        resides on each CSC and is used to
                        arbitrate among the line card
                        requests to transmit CiscoCells
                        through the switch fabric.
        Xbar          - Crossbar Switch Asic, this Asic
                        resides on each fabric card and provides
                        the functionality of a crossbar
                        switch.
        SLI           - Serial Link interface block, this
                        block resides on the FIA on the line
                        cards and the Xbar and SCA on the
                        switch fabric. The functionality of SLI
                        is to interface the linecards and fabric
                        cards.
        BMA           - Buffer Manager Asic, this Asic is
                        located on a Pre OC-192 linecard.
                        It provides the packet buffering
                        and buffer queue management.
        MCC           - Memory Communication Controller Asic,
                        this Asic is located on a OC-192
                        linecard and is an enhanced packet buffer
                        Asic. MCC captures the data and control
                        path information for packets destined
                        to all line cards in the system. On the
                        receive side MCC interfaces with the
                        Rx Asic where the packets are looked up
                        and sent to the MCC for buffering. On the
                        transmit side it interfaces with the
                        ToFabFIA where packets arrived from MCC
                        will be segmented into CiscoCells before
                        being sent across the fabric.
        CSAR          - Cisco Cell Segmentation And Reassembly,
                        The name of an FPGA used on the RP which
                        handles traffic between the processor
                        and switch fabric.
        Request       - A signal sent by a FIA (on a line card)
                        to the SCA (on Master CSC) requesting a
                        switch connection to a output linecard as an
                        intent to transmit CiscoCells across.
        Grant         - A signal sent by the SCA to a FIA (on a
                        line card) granting a switch connection which
                        was requested by the FIA.
        SRAM          - Static Random Access Memory.
        LOS           - Loss Of Signal.
        FPGA          - Field Programmable Gate Array."

    REVISION        "200209200000Z"
    DESCRIPTION
        "Initial version of this MIB module."

    ::= { ciscoMgmt 281 }

ciscoFabricC12kMIBNotifs
    OBJECT IDENTIFIER         ::= { ciscoFabricC12kMIB 0 }
ciscoFabricC12kMIBObjects
    OBJECT IDENTIFIER         ::= { ciscoFabricC12kMIB 1 }
ciscoFabricC12kMIBConform
    OBJECT IDENTIFIER         ::= { ciscoFabricC12kMIB 2 }

--
-- Generic information pertained to Fabric
--

cfcGeneric
    OBJECT IDENTIFIER ::= { ciscoFabricC12kMIBObjects 1 }
cfcGenericGlobal
    OBJECT IDENTIFIER ::= { cfcGeneric 1 }
cfcGenericFab
    OBJECT IDENTIFIER ::= { cfcGeneric 2 }
cfcGenericSca
    OBJECT IDENTIFIER ::= { cfcGeneric 3 }
cfcGenericXbar
    OBJECT IDENTIFIER ::= { cfcGeneric 4 }

--
-- Information pertained to Pre-OC192 Fabric
--

cfcPreOc192
    OBJECT IDENTIFIER ::= { ciscoFabricC12kMIBObjects 2 }
cfcPreOc192Fab
    OBJECT IDENTIFIER ::= { cfcPreOc192 1 }
cfcPreOc192Sca
    OBJECT IDENTIFIER ::= { cfcPreOc192 2 }
cfcPreOc192Xbar
    OBJECT IDENTIFIER ::= { cfcPreOc192 3 }

--
-- Information pertained to OC192 Fabric
--

cfcOc192
    OBJECT IDENTIFIER ::= { ciscoFabricC12kMIBObjects 3 }
cfcOc192Fab
    OBJECT IDENTIFIER ::= { cfcOc192 1 }
cfcOc192Sca
    OBJECT IDENTIFIER ::= { cfcOc192 2 }
cfcOc192Xbar
    OBJECT IDENTIFIER ::= { cfcOc192 3 }

--
-- Notification Enable object
--

cfcNotif
    OBJECT IDENTIFIER ::= { ciscoFabricC12kMIBObjects 4 }

--
-- Textual Conventions
--

CfcFabricConfigMode ::= TEXTUAL-CONVENTION
    STATUS      current
    DESCRIPTION
           "An enumerated value that provides the current bandwidth
           and redundancy configuration of the fabric.

           The c12000 can have the following fabric configurations
           based on the number of fabric cards present in the system.

           1) Invalid configuration mode, this mode indicates that
              the current fabric mode is invalid, this may be due to
              insufficient number of CSC or SFC cards in the system.

           2) Quarter bandwidth non-redundant mode, this mode
              indicates that the bandwidth supported per slot by the
              switch is 1/4 th of the full bandwidth and there is no
              redundancy for the fabric failure.

           3) Quarter bandwidth redundant mode, this mode indicates
              that the bandwidth supported per slot by the switch is
              1/4 th of the full bandwidth and there is redundancy
              for the fabric failure.

           4) Full bandwidth non-redundant mode, this mode indicates
              that the full bandwidth is supported per slot by the
              switch and there is no redundancy for the fabric
              failure.

           5) Full bandwidth redundant mode, this mode indicates
              that the full bandwidth is supported per slot by the
              switch and there is redundancy for the fabric failure.

          Quarter bandwidth modes are applicable only for the systems
          with pre-OC192 fabric cards."
    SYNTAX      INTEGER {
                         invalidMode                  (1),
                         quarterBwNonRedundant        (2),
                         quarterBwRedundant           (3),
                         fullBwNonRedundant           (4),
                         fullBwRedundant              (5)
        }

CfcFabricFiaState ::= TEXTUAL-CONVENTION
    STATUS      current
    DESCRIPTION
           "Provides the current state of the FIA.

              active - FIA is currently active.

              halted - On reaching a test point for errors on FIA,
              the FIA will be moved to halted state. On clearance of
              the error state the FIA will be moved back to active
              state."
    SYNTAX  INTEGER {
                     active (1),
                     halted (2)
                    }

CfcScaInterrupts ::= TEXTUAL-CONVENTION
    STATUS      current
    DESCRIPTION
           "Indicates different alarm conditions in the SCA.

             lossOfSync (0)   -- Interrupt caused by a loss-of-sync
                                 detection by SCA.
             parityError (1)  -- Interrupt caused by a request parity
                                 error detection by SCA.
             overflow (2)     -- Interrupt caused by a request
                                 overflow detection."
    SYNTAX BITS {
                  lossOfSync (0),
                  parityError (1),
                  overflow (2)
                }

CfcSlotMask ::= TEXTUAL-CONVENTION
    STATUS      current
    DESCRIPTION
           "Each bit in this value is used to represent a module,
            where the bit position represents the slot number of the
            module.
            Ex: To represent a module which is in slot 1, the bit
            position 1 in the octet string is set."
    SYNTAX OCTET STRING (SIZE(0..255))

--
--  Fabric Global Information
--

cfcGenericGlobalFabConfigMode OBJECT-TYPE
    SYNTAX      CfcFabricConfigMode
    MAX-ACCESS  read-only
    STATUS      current
    DESCRIPTION
           "This object gives the current bandwidth and
            redundancy configuration of fabric in the system."
    ::= { cfcGenericGlobal 1 }

cfcGenericGlobalFabMasterSched OBJECT-TYPE
    SYNTAX       EntPhysicalIndexOrZero
    MAX-ACCESS   read-only
    STATUS       current
    DESCRIPTION
           "This object gives the entPhysicalIndex of the master
            scheduler fabric card in the system. If there is no
            master scheduler card then this object will return the
            value zero."
    ::= { cfcGenericGlobal 2 }

--
-- Switch Fabric group
--

--
-- Generic ToFabric FIA statistics/information
--

cfcGenericFabToFabTable OBJECT-TYPE
    SYNTAX      SEQUENCE OF CfcGenericFabToFabEntry
    MAX-ACCESS  not-accessible
    STATUS      current
    DESCRIPTION
           "A table providing ToFabFIA statistics and
            information in the managed system."
    ::= { cfcGenericFab 1 }

cfcGenericFabToFabEntry OBJECT-TYPE
    SYNTAX      CfcGenericFabToFabEntry
    MAX-ACCESS  not-accessible
    STATUS      current
    DESCRIPTION
           "An entry providing various ToFabFIA statistics and
            information of the associated linecard identified
            by entPhysicalIndex."
    INDEX       { entPhysicalIndex }
    ::= { cfcGenericFabToFabTable 1 }

CfcGenericFabToFabEntry ::=
    SEQUENCE {
        cfcGenericFabToFabState                 CfcFabricFiaState,
        cfcGenericFabToFabGrantPEs              Counter32,
        cfcGenericFabToFabRequestPEs            Counter32,
        cfcGenericFabToFabCellFifoPEs           Counter32
        }

cfcGenericFabToFabState OBJECT-TYPE
    SYNTAX      CfcFabricFiaState
    MAX-ACCESS  read-only
    STATUS      current
    DESCRIPTION
           "Indicates the current state of the ToFabFIA.

             active - ToFabFIA is currently active.

             On reaching a test point for the FIA errors, the
             ToFabFIA will be moved to halted state."
    ::= { cfcGenericFabToFabEntry 1 }

cfcGenericFabToFabGrantPEs OBJECT-TYPE
    SYNTAX      Counter32
    MAX-ACCESS  read-only
    STATUS      current
    DESCRIPTION
           "Count of parity errors detected by the ToFabFIA
            on the grant lines to SCA."
    ::= { cfcGenericFabToFabEntry 2 }

cfcGenericFabToFabRequestPEs OBJECT-TYPE
    SYNTAX      Counter32
    MAX-ACCESS  read-only
    STATUS      current
    DESCRIPTION
           "Count of parity errors detected by the ToFabFIA
            on the request lines to SCA. These errors are detected
            by the SCA and fed back to the ToFabFIA."
    ::= { cfcGenericFabToFabEntry 3 }

cfcGenericFabToFabCellFifoPEs OBJECT-TYPE
    SYNTAX      Counter32
    MAX-ACCESS  read-only
    STATUS      current
    DESCRIPTION
           "Count of cell parity errors detected by the ToFabFIA
            while dequeuing cells from the cell fifo."
    ::= { cfcGenericFabToFabEntry 4 }

--
-- From Fabric FIA statistics/information
--

cfcGenericFabFrFabTable OBJECT-TYPE
    SYNTAX      SEQUENCE OF CfcGenericFabFrFabEntry
    MAX-ACCESS  not-accessible
    STATUS      current
    DESCRIPTION
           "A table providing FrFabFIA information in the
            managed system."
    ::= { cfcGenericFab 2 }

cfcGenericFabFrFabEntry OBJECT-TYPE
    SYNTAX      CfcGenericFabFrFabEntry
    MAX-ACCESS  not-accessible
    STATUS      current
    DESCRIPTION
           "An entry providing FrFabFIA information of the
            associated linecard identified by entPhysicalIndex."
    INDEX       { entPhysicalIndex }
    ::= { cfcGenericFabFrFabTable 1 }

CfcGenericFabFrFabEntry ::=
    SEQUENCE {
        cfcGenericFabFrFabState                 CfcFabricFiaState
        }

cfcGenericFabFrFabState OBJECT-TYPE
    SYNTAX      CfcFabricFiaState
    MAX-ACCESS  read-only
    STATUS      current
    DESCRIPTION
           "Indicates the current state of the FrFabFIA.

             active - FrFabFIA is currently active.

             On reaching a test point for the FIA errors, the
             FrFabFIA will be moved to halted state"
    ::= { cfcGenericFabFrFabEntry 1 }

--
-- Per serial link information maintained by the FrFabFIA.
--

cfcGenericFabFrFabSliTable OBJECT-TYPE
    SYNTAX      SEQUENCE OF CfcGenericFabFrFabSliEntry
    MAX-ACCESS  not-accessible
    STATUS      current
    DESCRIPTION
           "A table providing per serial link information maintained
            by the FrFabFIA in the managed system."
    ::= { cfcGenericFab 3 }

cfcGenericFabFrFabSliEntry OBJECT-TYPE
    SYNTAX      CfcGenericFabFrFabSliEntry
    MAX-ACCESS  not-accessible
    STATUS      current
    DESCRIPTION
           "An entry providing per serial link information maintained
            by the FrFabFIA on an associated linecard."
    INDEX       { entPhysicalIndex, cfcGenericFabFrFabSliFabIndex }
    ::= { cfcGenericFabFrFabSliTable 1 }

CfcGenericFabFrFabSliEntry ::=
    SEQUENCE {
        cfcGenericFabFrFabSliFabIndex           PhysicalIndex,
        cfcGenericFabFrFabSliLOSErrors          Counter32,
        cfcGenericFabFrFabSliCRCErrors          Counter32,
        cfcGenericFabFrFabSliLOSState           INTEGER
        }

cfcGenericFabFrFabSliFabIndex OBJECT-TYPE
    SYNTAX      PhysicalIndex
    MAX-ACCESS  not-accessible
    STATUS      current
    DESCRIPTION
           "The entPhysicalIndex of the switch fabric cards (CSC/SFC)
            present in the monitored system."
    ::= { cfcGenericFabFrFabSliEntry 1 }

cfcGenericFabFrFabSliLOSErrors OBJECT-TYPE
    SYNTAX      Counter32
    MAX-ACCESS  read-only
    STATUS      current
    DESCRIPTION
           "Count of LOS errors detected by the FrFabFIA
            on the serial link to the fabric card identified by
            cfcGenericFabFrFabSliFabIndex."
    ::= { cfcGenericFabFrFabSliEntry 2 }

cfcGenericFabFrFabSliCRCErrors OBJECT-TYPE
    SYNTAX      Counter32
    MAX-ACCESS  read-only
    STATUS      current
    DESCRIPTION
           "Count of CRC errors detected by the FrFabFIA
            on the serial link to the fabric card identified by
            cfcGenericFabFrFabSliFabIndex."
    ::= { cfcGenericFabFrFabSliEntry 3 }

cfcGenericFabFrFabSliLOSState OBJECT-TYPE
    SYNTAX    INTEGER {
                        losOff (1),
                        losOn (2)
                       }
    MAX-ACCESS  read-only
    STATUS      current
    DESCRIPTION
           "State of LOS detection as enabled on FrFabFIA
           (identified by entPhysicalIndex) for the serial link
           to the switch fabric card identified by
           cfcGenericFabFrFabSliFabIndex.
           Value is either,
                     (1) losOff
                     (2) losOn
            A losOff state normally indicates that the FrFabFIA
            has detected a state of persisting LOS on the serial
            link and has disabled LOS detection for that serial
            link."
    ::= { cfcGenericFabFrFabSliEntry 4 }

--
-- Generic Sca statistics/information
--

cfcGenericScaTable OBJECT-TYPE
    SYNTAX      SEQUENCE OF CfcGenericScaEntry
    MAX-ACCESS  not-accessible
    STATUS      current
    DESCRIPTION
           "A table providing SCA statistics and information in
            the managed system."
    ::= { cfcGenericSca 1 }

cfcGenericScaEntry OBJECT-TYPE
    SYNTAX      CfcGenericScaEntry
    MAX-ACCESS  not-accessible
    STATUS      current
    DESCRIPTION
           "An entry providing various statistics and information
            of SCA on an associated CSC identified by the
            respective entPhysicalIndex."
    INDEX       { entPhysicalIndex }
    ::= { cfcGenericScaTable 1 }

CfcGenericScaEntry ::=
    SEQUENCE {
        cfcGenericScaIdentifier         SnmpAdminString,
        cfcGenericScaIntrStatus         CfcScaInterrupts,
        cfcGenericScaIntrsEnabled       CfcScaInterrupts,
        cfcGenericScaConfig             BITS,
        cfcGenericScaPELog              CfcSlotMask,
        cfcGenericScaFifoOverflowLog    CfcSlotMask,
        cfcGenericScaLCsEnabled         CfcSlotMask,
        cfcGenericScaForcedBackPressure CfcSlotMask,
        cfcGenericScaPreOc192LCsPresent CfcSlotMask,
        cfcGenericScaOc192LCsPresent    CfcSlotMask
        }

cfcGenericScaIdentifier OBJECT-TYPE
    SYNTAX      SnmpAdminString
    MAX-ACCESS  read-only
    STATUS      current
    DESCRIPTION
           "The vendor-specific identifier string of SCA ASIC. This
            identifier generally includes the revision number and the
            manufacturing part number of SCA."
    ::= { cfcGenericScaEntry 1 }

cfcGenericScaIntrStatus OBJECT-TYPE
    SYNTAX      CfcScaInterrupts
    MAX-ACCESS  read-only
    STATUS      current
    DESCRIPTION
           "Gives the status/occurrence of different alarm conditions
            in the SCA. This object is a read-clear object, that is
            the value of the object is cleared on every read."
    ::= { cfcGenericScaEntry 2 }

cfcGenericScaIntrsEnabled OBJECT-TYPE
    SYNTAX      CfcScaInterrupts
    MAX-ACCESS  read-only
    STATUS      current
    DESCRIPTION
           "Gives the list of different alarm conditions enabled to
            be generated by the SCA."
    ::= { cfcGenericScaEntry 3 }

cfcGenericScaConfig OBJECT-TYPE
    SYNTAX      BITS {
                       quarterBandwidth (0),
                       halfBandwidth (1),
                       fullBandwidth (2),
                       enableParity (3),
                       priMcast (4),
                       priUnicast (5),
                       priAlternating (6),
                       earlyIntrOnLOS (7),
                       noEarlyIntrOnLOS (8),
                       forceXbarParityXer (9),
                       forceGrantParityXer (10),
                       unicastAcceptMode (11),
                       forceXbarCrcOnCtlLink0 (12),
                       forceXbarCrcOnCtlLink1 (13),
                       forceXbarCrcOnCtlLink2 (14),
                       forceXbarCrcOnCtlLink3 (15)
                     }
    MAX-ACCESS  read-only
    STATUS      current
    DESCRIPTION
           "Gives the current configuration of the SCA ASIC.

            quarterBandwidth (0)       -- 1/4th of the full bandwidth
                                          is supported per slot by
                                          the switch.
            halfBandwidth (1)          -- 1/2th of the full bandwidth
                                          is supported per slot by
                                          the switch.
            fullBandwidth (2)          -- Full bandwidth is supported
                                          per slot by the switch.
            enableParity (3)           -- Parity handling by SCA is
                                          enabled.
            priMcast (4)               -- Priority of Multicast
                                          requests is greater then
                                          Unicast requests.
            priUnicast (5)             -- Priority of Unicast
                                          requests is greater then
                                          Multicast requests.
            priAlternating (6)         -- Alternate the priority
                                          between pri-mcast and
                                          pri-unicast modes every
                                          cell clock.
            earlyIntrOnLOS (7)         -- Cause early interrupt on
                                          loss-of-sync error.
            noEarlyIntrOnLOS (8)       -- Allow time to resync on
                                          loss-of-sync error.
            forceXbarParityXer (9)     -- Force bad parity on xbar
                                          on every cell clock.
            forceGrantParityXer (10)   -- Force bad partity on grant
                                          to every line card.
            unicastAcceptMode (11)     -- Enable unicast accept
                                          pointer updating only on
                                          cell periods when Unicast
                                          has higher priority over
                                          multicast.
            forceXbarCrcOnCtlLink0 (12)-- Force CRC error on Xbar
                                          control link 0.
            forceXbarCrcOnCtlLink0 (13)-- Force CRC error on Xbar
                                          control link 1.
            forceXbarCrcOnCtlLink0 (14)-- Force CRC error on Xbar
                                          control link 2.
            forceXbarCrcOnCtlLink0 (15)-- Force CRC error on Xbar
                                          control link 3."
    ::= { cfcGenericScaEntry 4 }

cfcGenericScaPELog OBJECT-TYPE
    SYNTAX      CfcSlotMask
    MAX-ACCESS  read-only
    STATUS      current
    DESCRIPTION
           "Indicates the modules which caused the parity error and
            resulted in an interrupt. The corresponding bit is set on
            occurrence of parity error for a module. This object is a
            read-clear object, that is the value of the object is
            cleared on every read."
    ::= { cfcGenericScaEntry 5 }

cfcGenericScaFifoOverflowLog OBJECT-TYPE
    SYNTAX      CfcSlotMask
    MAX-ACCESS  read-only
    STATUS      current
    DESCRIPTION
           "Indicates the modules which caused an overflow at the
            request fifo and resulted in an interrupt. The
            corresponding bit is set on occurrence of fifo overflow
            for a module. This object is a read-clear object, that is
            the value of the object is cleared on every read."
    ::= { cfcGenericScaEntry 6 }

cfcGenericScaLCsEnabled OBJECT-TYPE
    SYNTAX      CfcSlotMask
    MAX-ACCESS  read-only
    STATUS      current
    DESCRIPTION
           "Indicates the modules which are present and the SCA has
            been configured to start accepting requests from this
            module."
    ::= { cfcGenericScaEntry 7 }

cfcGenericScaForcedBackPressure OBJECT-TYPE
    SYNTAX      CfcSlotMask
    MAX-ACCESS  read-only
    STATUS      current
    DESCRIPTION
           "Indicates the linecards which exerted backpressure.
            SCA will not grant Xbar connection to these linecards."
    ::= { cfcGenericScaEntry 8 }

cfcGenericScaOc192LCsPresent OBJECT-TYPE
    SYNTAX      CfcSlotMask
    MAX-ACCESS  read-only
    STATUS      current
    DESCRIPTION
           "Indicates the OC192 linecards present in the monitored
            system. The corresponding bit is set for each linecard
            present, indicating the postion."
    ::= { cfcGenericScaEntry 9 }

cfcGenericScaPreOc192LCsPresent OBJECT-TYPE
    SYNTAX      CfcSlotMask
    MAX-ACCESS  read-only
    STATUS      current
    DESCRIPTION
           "Indicates the Pre-OC192 linecards present in the
            monitored system. The corresponding bit is set for
            each linecard present, indicating the position."
    ::= { cfcGenericScaEntry 10 }

--
--  Generic Xbar information
--

cfcGenericXbarTable OBJECT-TYPE
    SYNTAX      SEQUENCE OF CfcGenericXbarEntry
    MAX-ACCESS  not-accessible
    STATUS      current
    DESCRIPTION
           "A table providing Xbar information in the
            managed system."
    ::= { cfcGenericXbar 1 }

cfcGenericXbarEntry OBJECT-TYPE
    SYNTAX      CfcGenericXbarEntry
    MAX-ACCESS  not-accessible
    STATUS      current
    DESCRIPTION
           "An entry providing Xbar information on an associated
            fabric card identified by entPhysicalIndex."
    INDEX       { entPhysicalIndex }
    ::= { cfcGenericXbarTable 1 }

CfcGenericXbarEntry ::=
    SEQUENCE {
        cfcGenericXbarIdentifier         SnmpAdminString
        }

cfcGenericXbarIdentifier OBJECT-TYPE
    SYNTAX      SnmpAdminString
    MAX-ACCESS  read-only
    STATUS      current
    DESCRIPTION
           "The vendor-specific identifier string of Xbar ASIC. This
            identifier generally includes the revision number and the
            manufacturing part number of Xbar."
    ::= { cfcGenericXbarEntry 1 }

--
--  Pre-OC192 Group
--

--
--  Pre-OC192 Fabric information
--

cfcPreOc192FabToFabTable OBJECT-TYPE
    SYNTAX      SEQUENCE OF CfcPreOc192FabToFabEntry
    MAX-ACCESS  not-accessible
    STATUS      current
    DESCRIPTION
           "A table providing pre-OC192 ToFabFIA statistics and
            information in the managed system."
    ::= { cfcPreOc192Fab 1 }

cfcPreOc192FabToFabEntry OBJECT-TYPE
    SYNTAX      CfcPreOc192FabToFabEntry
    MAX-ACCESS  not-accessible
    STATUS      current
    DESCRIPTION
           "An entry providing various statistics and
            counters of pre-OC192 ToFabFIA on an associated
            linecard identified by entPhysicalIndex."
    INDEX       { entPhysicalIndex }
    ::= { cfcPreOc192FabToFabTable 1 }

CfcPreOc192FabToFabEntry ::=
    SEQUENCE {
        cfcPreOc192FabToFabScaLosts              Counter32,
        cfcPreOc192FabToFabUCFifoOvFlws          Counter32,
        cfcPreOc192FabToFabUCFifoUnFlws          Counter32,
        cfcPreOc192FabToFabMCFifoErrs            Counter32,
        cfcPreOc192FabToFabBmaPEs                Counter32,
        cfcPreOc192FabToFabBmaHskErrs            Counter32,
        cfcPreOc192FabToFabUniDestMCRqs          Counter32,
        cfcPreOc192FabToFabMultiDstUCRqs         Counter32,
        cfcPreOc192FabToFabEmptyDestRqs          Counter32
        }

cfcPreOc192FabToFabScaLosts OBJECT-TYPE
    SYNTAX      Counter32
    MAX-ACCESS  read-only
    STATUS      current
    DESCRIPTION
           "Indicates the number of times the ToFabFIA lost contact
            with SCA(scheduler controller Asic) on master CSC."
    ::= { cfcPreOc192FabToFabEntry 1 }

cfcPreOc192FabToFabUCFifoOvFlws OBJECT-TYPE
    SYNTAX      Counter32
    MAX-ACCESS  read-only
    STATUS      current
    DESCRIPTION
           "Count of unicast fifo overflow errors on the ToFabFIA.
            Problems between BMA/CSAR and the ToFabFIA may be one
            of the reasons for these errors."
    ::= { cfcPreOc192FabToFabEntry 2 }

cfcPreOc192FabToFabUCFifoUnFlws OBJECT-TYPE
    SYNTAX      Counter32
    MAX-ACCESS  read-only
    STATUS      current
    DESCRIPTION
           "Count of unicast fifo underflow errors on the ToFabFIA.
            These errors are caused by the SCA granting without
            actually getting a request from the ToFabFIA."
    ::= { cfcPreOc192FabToFabEntry 3 }

cfcPreOc192FabToFabMCFifoErrs OBJECT-TYPE
    SYNTAX      Counter32
    MAX-ACCESS  read-only
    STATUS      current
    DESCRIPTION
           "Count of multicast fifo overflow and underflow errors
            on the ToFabFIA. Problems between BMA/CSAR and the
            ToFabFIA may be one of the reasons for multicast fifo
            overflow errors. Underflow errors are caused by the SCA
            granting without actually getting a request from the
            ToFabFIA."
    ::= { cfcPreOc192FabToFabEntry 4 }

cfcPreOc192FabToFabBmaPEs OBJECT-TYPE
    SYNTAX      Counter32
    MAX-ACCESS  read-only
    STATUS      current
    DESCRIPTION
           "Count of parity errors on cells received from BMA by the
            ToFabFIA."
    ::= { cfcPreOc192FabToFabEntry 5 }

cfcPreOc192FabToFabBmaHskErrs OBJECT-TYPE
    SYNTAX      Counter32
    MAX-ACCESS  read-only
    STATUS      current
    DESCRIPTION
           "Count of handshake errors between the BMA/CSAR and the
            ToFabFIA."
    ::= { cfcPreOc192FabToFabEntry 6 }

cfcPreOc192FabToFabUniDestMCRqs OBJECT-TYPE
    SYNTAX      Counter32
    MAX-ACCESS  read-only
    STATUS      current
    DESCRIPTION
           "Count of requests with single destination in a multicast
            request detected by ToFabFIA. The FIA will send this
            cell to the destination."
    ::= { cfcPreOc192FabToFabEntry 7 }

cfcPreOc192FabToFabMultiDstUCRqs OBJECT-TYPE
    SYNTAX      Counter32
    MAX-ACCESS  read-only
    STATUS      current
    DESCRIPTION
           "Count of requests with multiple destinations in a unicast
            request detected by a ToFabFIA. The FIA will drop this
            cell."
    ::= { cfcPreOc192FabToFabEntry 8 }

cfcPreOc192FabToFabEmptyDestRqs OBJECT-TYPE
    SYNTAX      Counter32
    MAX-ACCESS  read-only
    STATUS      current
    DESCRIPTION
           "Count of requests with empty destination detected by
            ToFabFIA. The FIA will drop this cell."
    ::= { cfcPreOc192FabToFabEntry 9 }

--
-- From Fabric PreOC192 FIA statistics/information
--

cfcPreOc192FabFrFabTable OBJECT-TYPE
    SYNTAX      SEQUENCE OF CfcPreOc192FabFrFabEntry
    MAX-ACCESS  not-accessible
    STATUS      current
    DESCRIPTION
           "A table providing pre-OC192 FrFabFIA statistics and
            information in the managed system."
    ::= { cfcPreOc192Fab 2 }

cfcPreOc192FabFrFabEntry OBJECT-TYPE
    SYNTAX      CfcPreOc192FabFrFabEntry
    MAX-ACCESS  not-accessible
    STATUS      current
    DESCRIPTION
           "An entry providing various statistics and information
            of pre-OC192 FrFabFIA on an associated linecard
            identified by entPhysicalIndex."
    INDEX       { entPhysicalIndex }
    ::= { cfcPreOc192FabFrFabTable 1 }

CfcPreOc192FabFrFabEntry ::=
    SEQUENCE {
        cfcPreOc192FabFrFabCellFifoPEs            Counter32,
        cfcPreOc192FabFrFabRedFifoPEs             Counter32,
        cfcPreOc192FabFrFabRedFifoOvflws          Counter32,
        cfcPreOc192FabFrFabCellDrops              Counter32
        }

cfcPreOc192FabFrFabCellFifoPEs OBJECT-TYPE
    SYNTAX      Counter32
    MAX-ACCESS  read-only
    STATUS      current
    DESCRIPTION
           "Count of cisco cell fifo parity errors detected by the
            FrFabFIA while dequeuing cells from the cell fifo."
    ::= { cfcPreOc192FabFrFabEntry 1 }

cfcPreOc192FabFrFabRedFifoPEs OBJECT-TYPE
    SYNTAX      Counter32
    MAX-ACCESS  read-only
    STATUS      current
    DESCRIPTION
           "Count of redundant data fifo parity errors detected by
            the FrFabFIA."
    ::= { cfcPreOc192FabFrFabEntry 2 }

cfcPreOc192FabFrFabRedFifoOvflws OBJECT-TYPE
    SYNTAX      Counter32
    MAX-ACCESS  read-only
    STATUS      current
    DESCRIPTION
           "Count of redundant data fifo overflow errors detected by
            the FrFabFIA. This is caused if the back pressure
            is broken (i.e. the FrFabFIA exerts back pressure and the
            SCA keeps giving more data to it)."
    ::= { cfcPreOc192FabFrFabEntry 3 }

cfcPreOc192FabFrFabCellDrops OBJECT-TYPE
    SYNTAX      Counter32
    MAX-ACCESS  read-only
    STATUS      current
    DESCRIPTION
           "Count of number of cells dropped by the FrFabFIA.
            In case of non-redundant fabric configuration, cell drops
            can occur when a parity error is detected on one or more
            than one serial link. In case of redundant fabric
            configuration cell drops can occur when a cell gets
            corrupted on more than one serial link."
    ::= { cfcPreOc192FabFrFabEntry 4 }

--
-- Pre Oc192 SCA Information
--

cfcPreOc192ScaTable OBJECT-TYPE
    SYNTAX      SEQUENCE OF CfcPreOc192ScaEntry
    MAX-ACCESS  not-accessible
    STATUS      current
    DESCRIPTION
           "A table providing pre-OC192 SCA statistics and
            information in the managed system."
    ::= { cfcPreOc192Sca 1 }

cfcPreOc192ScaEntry OBJECT-TYPE
    SYNTAX      CfcPreOc192ScaEntry
    MAX-ACCESS  not-accessible
    STATUS      current
    DESCRIPTION
           "An entry providing various statistics and information
            of pre-OC192 SCA on an associated CSC identified by
            entPhysicalIndex."
    INDEX       { entPhysicalIndex }
    ::= { cfcPreOc192ScaTable 1 }

CfcPreOc192ScaEntry ::=
    SEQUENCE {
        cfcPreOc192ScaReSyncDelay       Unsigned32,
        cfcPreOc192ScaLOSLog            CfcSlotMask
        }

cfcPreOc192ScaReSyncDelay OBJECT-TYPE
    SYNTAX      Unsigned32
    MAX-ACCESS  read-only
    STATUS      current
    DESCRIPTION
           "The number of cell periods that the SCA will allow
            the serial links connected to a module and Xbar to be
            resynced, if a loss-of-sync has occurred on the
            corresponding module. The value '0' indicates that on
            occurrence of LOS, the sca will only log the LOS event
            and do the scheduling for that module as normal."
    ::= { cfcPreOc192ScaEntry 1 }

cfcPreOc192ScaLOSLog OBJECT-TYPE
    SYNTAX      CfcSlotMask
    MAX-ACCESS  read-only
    STATUS      current
    DESCRIPTION
           "Indicates the LOS event occurrence on each linecard
            connected to this CSC. The corresponding bit is set on
            occurrence of LOS event on a line card. This object is
            a read-clear object, that is the value of the object is
            cleared on every read."
    ::= { cfcPreOc192ScaEntry 2 }

--
--  Pre-Oc192 Xbar information
--

cfcPreOc192XbarTable OBJECT-TYPE
    SYNTAX      SEQUENCE OF CfcPreOc192XbarEntry
    MAX-ACCESS  not-accessible
    STATUS      current
    DESCRIPTION
           "A table providing Pre-OC192 Xbar statistics and
            information in the managed system."
    ::= { cfcPreOc192Xbar 1 }

cfcPreOc192XbarEntry OBJECT-TYPE
    SYNTAX      CfcPreOc192XbarEntry
    MAX-ACCESS  not-accessible
    STATUS      current
    DESCRIPTION
           "An entry providing various statistics and information
            of Pre-OC192 Xbar on an associated fabric card identified
            by entPhysicalIndex."
    INDEX       { entPhysicalIndex }
    ::= { cfcPreOc192XbarTable 1 }

CfcPreOc192XbarEntry ::=
    SEQUENCE {
        cfcPreOc192XbarIntrStatus         BITS,
        cfcPreOc192XbarParityChkStatus    TruthValue
        }

cfcPreOc192XbarIntrStatus OBJECT-TYPE
    SYNTAX      BITS {
                       frameLossOfSync(0),
                       parityErrorFromSca(1)
                     }
    MAX-ACCESS  read-only
    STATUS      current
    DESCRIPTION
           "Indicates the occurrence of different alarm conditions in
            Xbar. This object is a read-clear object, that is the
            value of the object is cleared on every read."
    ::= { cfcPreOc192XbarEntry 1 }

cfcPreOc192XbarParityChkStatus OBJECT-TYPE
    SYNTAX      TruthValue
    MAX-ACCESS  read-only
    STATUS      current
    DESCRIPTION
           "Indicates the parity check state in control data received
            from SCA to the Xbar.

            true(1) indicates that the parity check is enabled.
            false(2) indicates that the parity check is disabled."
    ::= { cfcPreOc192XbarEntry 2 }

--
-- Oc192 Fabric information/statistics
--

cfcOc192FabToFabTable OBJECT-TYPE
    SYNTAX      SEQUENCE OF CfcOc192FabToFabEntry
    MAX-ACCESS  not-accessible
    STATUS      current
    DESCRIPTION
           "A table providing OC192 ToFabFIA statistics
            and information in the managed system."
    ::= { cfcOc192Fab 1 }

cfcOc192FabToFabEntry OBJECT-TYPE
    SYNTAX      CfcOc192FabToFabEntry
    MAX-ACCESS  not-accessible
    STATUS      current
    DESCRIPTION
           "An entry providing various statistics and information
            of OC192 ToFabFIA on an associated linecard identified
            by entPhysicalIndex."
    INDEX       { entPhysicalIndex }
    ::= { cfcOc192FabToFabTable 1 }

CfcOc192FabToFabEntry ::=
    SEQUENCE {
        cfcOc192FabToFabMccDataPEs               Counter32,
        cfcOc192FabToFabMccCmdPEs                Counter32,
        cfcOc192FabToFabBackPressurePEs          Counter32,
        cfcOc192FabToFabCellFifoOvFlws           Counter32,
        cfcOc192FabToFabCellFifoUnFlws           Counter32,
        cfcOc192FabToFabMccCmdSeqEndErrs         Counter32,
        cfcOc192FabToFabMccCmdSeqStrErrs         Counter32
        }

cfcOc192FabToFabMccDataPEs OBJECT-TYPE
    SYNTAX      Counter32
    MAX-ACCESS  read-only
    STATUS      current
    DESCRIPTION
           "Count of the parity errors on data lines from
            MCC to ToFabFIA. This error would cause the
            ToFabFIA to halt."
    ::= { cfcOc192FabToFabEntry 1 }

cfcOc192FabToFabMccCmdPEs OBJECT-TYPE
    SYNTAX      Counter32
    MAX-ACCESS  read-only
    STATUS      current
    DESCRIPTION
           "Count of the parity errors on command lines from
            MCC to ToFabFIA. This error would cause the
            ToFabFIA to halt."
    ::= { cfcOc192FabToFabEntry 2 }

cfcOc192FabToFabBackPressurePEs OBJECT-TYPE
    SYNTAX      Counter32
    MAX-ACCESS  read-only
    STATUS      current
    DESCRIPTION
           "Count of the parity errors on back pressure line from
            FrFabFIA to ToFabFIA. This error would cause the
            ToFabFIA to halt."
    ::= { cfcOc192FabToFabEntry 3 }

cfcOc192FabToFabCellFifoOvFlws OBJECT-TYPE
    SYNTAX      Counter32
    MAX-ACCESS  read-only
    STATUS      current
    DESCRIPTION
           "Count of the cell fifo overflow errors detected by the
            ToFabFIA. This error would cause the ToFabFIA to halt."
    ::= { cfcOc192FabToFabEntry 4 }

cfcOc192FabToFabCellFifoUnFlws OBJECT-TYPE
    SYNTAX      Counter32
    MAX-ACCESS  read-only
    STATUS      current
    DESCRIPTION
           "Count of the cell fifo underflow errors detected by the
            ToFabFIA. This error would cause the ToFabFIA to halt."
    ::= { cfcOc192FabToFabEntry 5 }

cfcOc192FabToFabMccCmdSeqEndErrs OBJECT-TYPE
    SYNTAX      Counter32
    MAX-ACCESS  read-only
    STATUS      current
    DESCRIPTION
           "Count of the illegal sequence of command errors where
            a middle or start command followed by a start command
            is received from MCC."
    ::= { cfcOc192FabToFabEntry 6 }

cfcOc192FabToFabMccCmdSeqStrErrs OBJECT-TYPE
    SYNTAX      Counter32
    MAX-ACCESS  read-only
    STATUS      current
    DESCRIPTION
           "Count of the illegal sequence of command errors where
            an end command followed by an end or middle command
            is received from MCC."
    ::= { cfcOc192FabToFabEntry 7 }

--
-- OC192 From Fabric FIA information
--

cfcOc192FabFrFabTable OBJECT-TYPE
    SYNTAX      SEQUENCE OF CfcOc192FabFrFabEntry
    MAX-ACCESS  not-accessible
    STATUS      current
    DESCRIPTION
           "A table providing FrFabFIA statistics and
            information in the managed system."
    ::= { cfcOc192Fab 2 }

cfcOc192FabFrFabEntry OBJECT-TYPE
    SYNTAX      CfcOc192FabFrFabEntry
    MAX-ACCESS  not-accessible
    STATUS      current
    DESCRIPTION
           "An entry providing various statistics and information
            of OC192 FrFabFIA on an associated linecard identified
            by entPhysicalIndex."
    INDEX       { entPhysicalIndex }
    ::= { cfcOc192FabFrFabTable 1 }

CfcOc192FabFrFabEntry ::=
    SEQUENCE {
        cfcOc192FabFrFabPktLenErrs           Counter32,
        cfcOc192FabFrFabExtRamPEs            Counter32,
        cfcOc192FabFrFabPktLenPEs            Counter32,
        cfcOc192FabFrFabHdrSramPEs           Counter32,
        cfcOc192FabFrFabTxCtrlPEs            Counter32,
        cfcOc192FabFrFabHdrFifoOvFlws        Counter32,
        cfcOc192FabFrFabExtSramOvFlws        Counter32,
        cfcOc192FabFrFabFirstLastErrs        Counter32,
        cfcOc192FabFrFabSeqErrs              Counter32
        }

cfcOc192FabFrFabPktLenErrs OBJECT-TYPE
    SYNTAX      Counter32
    MAX-ACCESS  read-only
    STATUS      current
    DESCRIPTION
           "Count of the packets (after reassembly from Cisco
            cells) which exceed the maximum permitted packet
            length of FrFabFIA. These packets will be dropped."
    ::= { cfcOc192FabFrFabEntry 1 }

cfcOc192FabFrFabExtRamPEs OBJECT-TYPE
    SYNTAX      Counter32
    MAX-ACCESS  read-only
    STATUS      current
    DESCRIPTION
           "Count of the parity errors detected in FrFabFIA's
            external SRAM."
    ::= { cfcOc192FabFrFabEntry 2 }

cfcOc192FabFrFabPktLenPEs OBJECT-TYPE
    SYNTAX      Counter32
    MAX-ACCESS  read-only
    STATUS      current
    DESCRIPTION
           "Count of the parity errors detected in payload packet
            length field of the FrFabFIA's Payload Header SRAM."
    ::= { cfcOc192FabFrFabEntry 3 }

cfcOc192FabFrFabHdrSramPEs OBJECT-TYPE
    SYNTAX      Counter32
    MAX-ACCESS  read-only
    STATUS      current
    DESCRIPTION
           "Count of the parity errors detected in payload header
            field of the FrFabFIA's Payload Header SRAM."
    ::= { cfcOc192FabFrFabEntry 4 }

cfcOc192FabFrFabTxCtrlPEs OBJECT-TYPE
    SYNTAX      Counter32
    MAX-ACCESS  read-only
    STATUS      current
    DESCRIPTION
           "Count of the parity errors detected on the Tx control
            bits of FrFabFIA."
    ::= { cfcOc192FabFrFabEntry 5 }

cfcOc192FabFrFabHdrFifoOvFlws OBJECT-TYPE
    SYNTAX      Counter32
    MAX-ACCESS  read-only
    STATUS      current
    DESCRIPTION
           "Count of the overflow errors in the FrFabFIA's reassembly
            fifos in the on-chip payload header SRAM."
    ::= { cfcOc192FabFrFabEntry 6 }

cfcOc192FabFrFabExtSramOvFlws OBJECT-TYPE
    SYNTAX      Counter32
    MAX-ACCESS  read-only
    STATUS      current
    DESCRIPTION
           "Count of the overflow errors in the FrFabFIA's reassembly
            external SRAM's payload fifos."
    ::= { cfcOc192FabFrFabEntry 7 }

cfcOc192FabFrFabFirstLastErrs OBJECT-TYPE
    SYNTAX      Counter32
    MAX-ACCESS  read-only
    STATUS      current
    DESCRIPTION
           "Count of the First-Last errors detected by FrFabFIA's.
            If a first cell is received for a reassembly fifo, while
            an earlier packet in the same reassembly fifo is still
            waiting for its last cell, then it is called a First-Last
            Error."
    ::= { cfcOc192FabFrFabEntry 8 }

cfcOc192FabFrFabSeqErrs OBJECT-TYPE
    SYNTAX      Counter32
    MAX-ACCESS  read-only
    STATUS      current
    DESCRIPTION
           "Count of the sequence errors detected by FrFabFIA in
            the cells received for reassembly. If a cell is received
            whose sequence number is not an unit increment from the
            previous cell of the same packet then it is a sequence
            error."
    ::= { cfcOc192FabFrFabEntry 9 }

--
-- Oc192 SLI Table
--

cfcOc192FabFrFabSliTable OBJECT-TYPE
    SYNTAX      SEQUENCE OF CfcOc192FabFrFabSliEntry
    MAX-ACCESS  not-accessible
    STATUS      current
    DESCRIPTION
           "A table providing per serial link information maintained
            by the OC192 FrFabFIA in the managed system."
    ::= { cfcOc192Fab 3 }

cfcOc192FabFrFabSliEntry OBJECT-TYPE
    SYNTAX      CfcOc192FabFrFabSliEntry
    MAX-ACCESS  not-accessible
    STATUS      current
    DESCRIPTION
           "An entry providing per serial link information maintained
            by the OC192 FrFabFIA on an associated linecard identified
            by entPhysicalIndex."
    INDEX       { entPhysicalIndex, cfcOc192FabFrFabSliSwitchIndex }
    ::= { cfcOc192FabFrFabSliTable 1 }

CfcOc192FabFrFabSliEntry ::=
    SEQUENCE {
        cfcOc192FabFrFabSliSwitchIndex          PhysicalIndex,
        cfcOc192FabFrFabSliXorErrs              Counter32,
        cfcOc192FabFrFabSliCellDrops            Counter32
        }

cfcOc192FabFrFabSliSwitchIndex OBJECT-TYPE
    SYNTAX      PhysicalIndex
    MAX-ACCESS  not-accessible
    STATUS      current
    DESCRIPTION
           "The entPhysicalIndex of the switch fabric cards (CSC/SFC)
            present in the monitored system."
    ::= { cfcOc192FabFrFabSliEntry 1 }

cfcOc192FabFrFabSliXorErrs OBJECT-TYPE
    SYNTAX      Counter32
    MAX-ACCESS  read-only
    STATUS      current
    DESCRIPTION
           "Count of the XOR check errors detected by FrFabFIA
            reassembly. The data paths are horizontally XORed and
            the result is expected to match the contents of the
            redundant path else it is counted as XOR error, this
            error applies only in redundant mode of fabric."
    ::= { cfcOc192FabFrFabSliEntry 2 }

cfcOc192FabFrFabSliCellDrops OBJECT-TYPE
    SYNTAX      Counter32
    MAX-ACCESS  read-only
    STATUS      current
    DESCRIPTION
           "Count of the total cells dropped by the FrFabFIA from
            the fabric card due to uncorrectable errors. Uncorrectable
            errors are the errors other than CRC, LOS, Horizontal XOR
            and idle cell which cannot be corrected."
    ::= { cfcOc192FabFrFabSliEntry 3 }


--
--  Per LC stats maintained in FrFabFIA
--

cfcOc192FabFrFabStatTable OBJECT-TYPE
    SYNTAX      SEQUENCE OF CfcOc192FabFrFabStatEntry
    MAX-ACCESS  not-accessible
    STATUS      current
    DESCRIPTION
           "A table providing per module statistics information
            maintained by the OC192 FrFabFIA in the managed system."
    ::= { cfcOc192Fab 4 }

cfcOc192FabFrFabStatEntry OBJECT-TYPE
    SYNTAX      CfcOc192FabFrFabStatEntry
    MAX-ACCESS  not-accessible
    STATUS      current
    DESCRIPTION
           "An entry providing per module statistics information
            maintained by the OC192 FrFabFIA on an associated
            linecard identified by entPhysicalIndex."
    INDEX       { entPhysicalIndex, cfcOc192FabFrFabStatLCIndex }
    ::= { cfcOc192FabFrFabStatTable 1 }

CfcOc192FabFrFabStatEntry ::=
    SEQUENCE {
        cfcOc192FabFrFabStatLCIndex          PhysicalIndex,
        cfcOc192FabFrFabStatUCHiPktDrops     Counter32,
        cfcOc192FabFrFabStatUCLoPktDrops     Counter32,
        cfcOc192FabFrFabStatMCHiPktDrops     Counter32,
        cfcOc192FabFrFabStatMCLoPktDrops     Counter32
        }

cfcOc192FabFrFabStatLCIndex OBJECT-TYPE
    SYNTAX      PhysicalIndex
    MAX-ACCESS  not-accessible
    STATUS      current
    DESCRIPTION
           "The entPhysicalIndex of the Line card present in the
            monitored system."
    ::= { cfcOc192FabFrFabStatEntry 1 }

cfcOc192FabFrFabStatUCHiPktDrops OBJECT-TYPE
    SYNTAX      Counter32
    MAX-ACCESS  read-only
    STATUS      current
    DESCRIPTION
           "Count of Unicast high priority packets dropped, from
            source module indicated by cfcOc192FabFrFabStatLCIndex."
    ::= { cfcOc192FabFrFabStatEntry 2 }

cfcOc192FabFrFabStatUCLoPktDrops OBJECT-TYPE
    SYNTAX      Counter32
    MAX-ACCESS  read-only
    STATUS      current
    DESCRIPTION
           "Count of Unicast low priority packets dropped, from
            source module indicated by cfcOc192FabFrFabStatLCIndex."
    ::= { cfcOc192FabFrFabStatEntry 3 }

cfcOc192FabFrFabStatMCHiPktDrops OBJECT-TYPE
    SYNTAX      Counter32
    MAX-ACCESS  read-only
    STATUS      current
    DESCRIPTION
           "Count of Multicast high priority packets dropped, from
            source module indicated by cfcOc192FabFrFabStatLCIndex."
    ::= { cfcOc192FabFrFabStatEntry 4 }

cfcOc192FabFrFabStatMCLoPktDrops OBJECT-TYPE
    SYNTAX      Counter32
    MAX-ACCESS  read-only
    STATUS      current
    DESCRIPTION
           "Count of Multicast low priority packets dropped, from
            source module indicated by cfcOc192FabFrFabStatLCIndex."
    ::= { cfcOc192FabFrFabStatEntry 5 }

--
-- Oc192 SCA Information
--

cfcOc192ScaTable OBJECT-TYPE
    SYNTAX      SEQUENCE OF CfcOc192ScaEntry
    MAX-ACCESS  not-accessible
    STATUS      current
    DESCRIPTION
           "A table providing OC192 SCA statistics and information in
            the managed system."
    ::= { cfcOc192Sca 1 }

cfcOc192ScaEntry OBJECT-TYPE
    SYNTAX      CfcOc192ScaEntry
    MAX-ACCESS  not-accessible
    STATUS      current
    DESCRIPTION
           "An entry providing various statistics and information
            of OC192 SCA on an associated CSC identified by
            entPhysicalIndex."
    INDEX       { entPhysicalIndex }
    ::= { cfcOc192ScaTable 1 }

CfcOc192ScaEntry ::=
    SEQUENCE {
        cfcOc192ScaRotationPeriod       Unsigned32,
        cfcOc192ScaDisableGrants        CfcSlotMask
        }

cfcOc192ScaRotationPeriod OBJECT-TYPE
    SYNTAX      Unsigned32
    MAX-ACCESS  read-only
    STATUS      current
    DESCRIPTION
           "Determines the period of rotating the priority between
            Unicast and Multicast, in cell periods, when the SCA is
            configured with alternating priority mode.
            For example, if the value of this object is 63 then
            the priority will change every 64 cell periods, if the
            value is 0 then the priority will change every cell
            period."
    ::= { cfcOc192ScaEntry 1 }

cfcOc192ScaDisableGrants OBJECT-TYPE
    SYNTAX      CfcSlotMask
    MAX-ACCESS  read-only
    STATUS      current
    DESCRIPTION
           "Indicates the disable of grants by SCA to any requests
            coming from a specific module. The corresponding bit
            is set for each module."
    ::= { cfcOc192ScaEntry 2 }

--
--  Oc192 Xbar information
--

cfcOc192XbarTable OBJECT-TYPE
    SYNTAX      SEQUENCE OF CfcOc192XbarEntry
    MAX-ACCESS  not-accessible
    STATUS      current
    DESCRIPTION
           "A table providing OC192 Xbar statistics and information
            in the managed system."
    ::= { cfcOc192Xbar 1 }

cfcOc192XbarEntry OBJECT-TYPE
    SYNTAX      CfcOc192XbarEntry
    MAX-ACCESS  not-accessible
    STATUS      current
    DESCRIPTION
           "An entry providing various statistics and information
            of OC192 Xbar on an associated fabric card identified
            by entPhysicalIndex."
    INDEX       { entPhysicalIndex }
    ::= { cfcOc192XbarTable 1 }

CfcOc192XbarEntry ::=
    SEQUENCE {
        cfcOc192XbarCtrlLOSStatus         BITS,
        cfcOc192XbarCtrlCRCErr            BITS
        }

cfcOc192XbarCtrlLOSStatus OBJECT-TYPE
    SYNTAX      BITS {
                       frameLosErr (0),
                       sliErrorOnControlLink0 (1),
                       sliErrorOnControlLink1 (2),
                       sliErrorOnControlLink2 (3),
                       sliErrorOnControlLink3 (4)
                      }
    MAX-ACCESS  read-only
    STATUS      current
    DESCRIPTION
           "Indicates the occurrence of LOS errors on the control path
            of Xbar.
               frameLosErr (0)               -- Frame LOS error.
               sliErrorOnControlLink0 (1)    -- LOS detected on SLI
                                                control link 0.
               sliErrorOnControlLink1 (2)    -- LOS detected on SLI
                                                control link 1.
               sliErrorOnControlLink2 (3)    -- LOS detected on SLI
                                                control link 2.
               sliErrorOnControlLink3 (4)    -- LOS detected on SLI
                                                control link 3.
            This object is a read-clear object, that is the value
            of the object is cleared on every read."
    ::= { cfcOc192XbarEntry 1 }

cfcOc192XbarCtrlCRCErr OBJECT-TYPE
    SYNTAX      BITS {
                       ctlCrcErrorLink0 (0),
                       ctlCrcErrorLink1 (1),
                       ctlCrcErrorLink2 (2),
                       ctlCrcErrorLink3 (3)
                      }
    MAX-ACCESS  read-only
    STATUS      current
    DESCRIPTION
           "Indicates the occurrence of CRC error on any of the
            four control links. This object is a read-clear object,
            that is the value of the object is cleared on every read."
    ::= { cfcOc192XbarEntry 2 }

-- Notification Enable object

cfcNotifEnable  OBJECT-TYPE
    SYNTAX      TruthValue
    MAX-ACCESS  read-write
    STATUS      current
    DESCRIPTION
           "This variable indicates whether the system
            produces the notifications defined in the MIB.
            A false value will prevent the notifications in
            the MIB from being generated by the system."
    DEFVAL { false }
    ::= { cfcNotif 1 }

-- Notification

ciscoFabricC12kMIBFabMasterSchCh NOTIFICATION-TYPE
    OBJECTS {
              cfcGenericGlobalFabMasterSched,
              entPhysicalName
             }
    STATUS  current
    DESCRIPTION
         "This notification is generated when master scheduler
          on the system changes. It typically indicates the
          switchover of the scheduler card.
          cfcGenericGlobalFabMasterSched represents the
          entPhysicalIndex of the new master scheduler card,
          while entPhysicalName represents the entity physical
          name of the card. The case of all scheduler cards going
          down would be represented by a value 0 for the
          cfcGenericGlobalFabMasterSched and noSuchInstance for the
          entPhysicalName."
    ::= { ciscoFabricC12kMIBNotifs 1 }

-- conformance information


ciscoFabricC12kMIBCompliances OBJECT IDENTIFIER
                            ::= { ciscoFabricC12kMIBConform 1 }
ciscoFabricC12kMIBGroups      OBJECT IDENTIFIER
                            ::= { ciscoFabricC12kMIBConform 2 }


-- Compliances statement

ciscoFabricC12kMIBCompliance MODULE-COMPLIANCE
    STATUS  current
    DESCRIPTION
            "The compliance statement for entities which implement
             the CISCO-FABRIC-C12K-MIB."
    MODULE  -- this module
    MANDATORY-GROUPS {
                       ciscoFabricC12kGlobalGroup,
                       ciscoFabricC12kFiaGroup,
                       ciscoFabricC12kScaGroup,
                       ciscoFabricC12kXbarGroup,
                       ciscoFabricC12kPreOc192FiaGroup,
                       ciscoFabricC12kNotifEnableGroup,
                       ciscoFabricC12kNotifGroup
                      }

    GROUP ciscoFabricC12kPreOc192ScaGroup
    DESCRIPTION
            "This group is mandatory only if PreOC192 clock scheduler
             cards are present in the managed system"

    GROUP ciscoFabricC12kPreOc192XbarGroup
    DESCRIPTION
            "This group is mandatory only if PreOC192 fabric cards
             are present in the managed system"

    GROUP ciscoFabricC12kOc192FiaGroup
    DESCRIPTION
            "This group is mandatory only if OC192 line cards are
             supported in the managed system"

    GROUP ciscoFabricC12kOc192LCGroup
    DESCRIPTION
            "This group is mandatory only if OC192 line cards are
             supported in the managed system"

    GROUP ciscoFabricC12kOc192ScaGroup
    DESCRIPTION
            "This group is mandatory only if OC192 clock scheduler
             cards are present in the managed system"

    GROUP ciscoFabricC12kOc192XbarGroup
    DESCRIPTION
            "This group is mandatory only if OC192 fabric cards
             are present in the managed system"

    ::= { ciscoFabricC12kMIBCompliances 1 }

-- units of compliances

ciscoFabricC12kGlobalGroup  OBJECT-GROUP
    OBJECTS {
              cfcGenericGlobalFabConfigMode,
              cfcGenericGlobalFabMasterSched
            }
    STATUS  current
    DESCRIPTION
            "A collection of Global fabric configuration
             objects."
    ::= { ciscoFabricC12kMIBGroups 1 }

ciscoFabricC12kFiaGroup  OBJECT-GROUP
    OBJECTS {
              cfcGenericFabToFabState,
              cfcGenericFabToFabGrantPEs,
              cfcGenericFabToFabRequestPEs,
              cfcGenericFabToFabCellFifoPEs,
              cfcGenericFabFrFabState,
              cfcGenericFabFrFabSliLOSErrors,
              cfcGenericFabFrFabSliCRCErrors,
              cfcGenericFabFrFabSliLOSState
            }
    STATUS  current
    DESCRIPTION
            "A collection of generic FIA status and statistics
             objects."
    ::= { ciscoFabricC12kMIBGroups 2 }

ciscoFabricC12kScaGroup  OBJECT-GROUP
    OBJECTS {
              cfcGenericScaIdentifier,
              cfcGenericScaIntrStatus,
              cfcGenericScaIntrsEnabled,
              cfcGenericScaConfig,
              cfcGenericScaPELog,
              cfcGenericScaFifoOverflowLog,
              cfcGenericScaLCsEnabled,
              cfcGenericScaForcedBackPressure,
              cfcGenericScaPreOc192LCsPresent
            }
    STATUS  current
    DESCRIPTION
            "A collection of generic SCA status objects."
    ::= { ciscoFabricC12kMIBGroups 3 }

ciscoFabricC12kXbarGroup  OBJECT-GROUP
    OBJECTS {
              cfcGenericXbarIdentifier
            }
    STATUS  current
    DESCRIPTION
            "A collection of generic Xbar status objects."
    ::= { ciscoFabricC12kMIBGroups 4 }

ciscoFabricC12kPreOc192FiaGroup  OBJECT-GROUP
    OBJECTS {
              cfcPreOc192FabToFabScaLosts,
              cfcPreOc192FabToFabUCFifoOvFlws,
              cfcPreOc192FabToFabUCFifoUnFlws,
              cfcPreOc192FabToFabMCFifoErrs,
              cfcPreOc192FabToFabBmaPEs,
              cfcPreOc192FabToFabBmaHskErrs,
              cfcPreOc192FabToFabUniDestMCRqs,
              cfcPreOc192FabToFabMultiDstUCRqs,
              cfcPreOc192FabToFabEmptyDestRqs,
              cfcPreOc192FabFrFabCellFifoPEs,
              cfcPreOc192FabFrFabRedFifoPEs,
              cfcPreOc192FabFrFabRedFifoOvflws,
              cfcPreOc192FabFrFabCellDrops
            }
    STATUS  current
    DESCRIPTION
            "A collection of pre-OC192 FIA status and statistics
             objects."
    ::= { ciscoFabricC12kMIBGroups 5 }

ciscoFabricC12kPreOc192ScaGroup  OBJECT-GROUP
    OBJECTS {
              cfcPreOc192ScaReSyncDelay,
              cfcPreOc192ScaLOSLog
            }
    STATUS  current
    DESCRIPTION
            "A collection of Pre-OC192 SCA status objects."
    ::= { ciscoFabricC12kMIBGroups 6 }

ciscoFabricC12kPreOc192XbarGroup  OBJECT-GROUP
    OBJECTS {
              cfcPreOc192XbarIntrStatus,
              cfcPreOc192XbarParityChkStatus
            }
    STATUS  current
    DESCRIPTION
            "A collection of Pre-Oc192 Xbar status objects."
    ::= { ciscoFabricC12kMIBGroups 7 }

ciscoFabricC12kOc192FiaGroup  OBJECT-GROUP
    OBJECTS {
              cfcOc192FabToFabMccDataPEs,
              cfcOc192FabToFabMccCmdPEs,
              cfcOc192FabToFabBackPressurePEs,
              cfcOc192FabToFabCellFifoOvFlws,
              cfcOc192FabToFabCellFifoUnFlws,
              cfcOc192FabToFabMccCmdSeqEndErrs,
              cfcOc192FabToFabMccCmdSeqStrErrs,
              cfcOc192FabFrFabPktLenErrs,
              cfcOc192FabFrFabExtRamPEs,
              cfcOc192FabFrFabPktLenPEs,
              cfcOc192FabFrFabHdrSramPEs,
              cfcOc192FabFrFabTxCtrlPEs,
              cfcOc192FabFrFabHdrFifoOvFlws,
              cfcOc192FabFrFabExtSramOvFlws,
              cfcOc192FabFrFabFirstLastErrs,
              cfcOc192FabFrFabSeqErrs,
              cfcOc192FabFrFabSliXorErrs,
              cfcOc192FabFrFabSliCellDrops,
              cfcOc192FabFrFabStatUCHiPktDrops,
              cfcOc192FabFrFabStatUCLoPktDrops,
              cfcOc192FabFrFabStatMCHiPktDrops,
              cfcOc192FabFrFabStatMCLoPktDrops
            }
    STATUS  current
    DESCRIPTION
            "A collection of OC192 FIA status and statistics
             objects."
    ::= { ciscoFabricC12kMIBGroups 8 }

ciscoFabricC12kOc192LCGroup OBJECT-GROUP
    OBJECTS {
              cfcGenericScaOc192LCsPresent
            }
    STATUS  current
    DESCRIPTION
            "A collection of OC192 linecard generic objects."
    ::= { ciscoFabricC12kMIBGroups 9 }

ciscoFabricC12kOc192ScaGroup  OBJECT-GROUP
    OBJECTS {
              cfcOc192ScaRotationPeriod,
              cfcOc192ScaDisableGrants
            }
    STATUS  current
    DESCRIPTION
            "A collection of OC192 SCA status objects."
    ::= { ciscoFabricC12kMIBGroups 10 }

ciscoFabricC12kOc192XbarGroup  OBJECT-GROUP
    OBJECTS {
              cfcOc192XbarCtrlLOSStatus,
              cfcOc192XbarCtrlCRCErr
            }
    STATUS  current
    DESCRIPTION
            "A collection of OC192 Xbar status objects."
    ::= { ciscoFabricC12kMIBGroups 11 }

ciscoFabricC12kNotifEnableGroup OBJECT-GROUP
    OBJECTS {
             cfcNotifEnable
             }
    STATUS  current
    DESCRIPTION
        "The collection of objects which are used to
         control generation of notification."
    ::= { ciscoFabricC12kMIBGroups 12 }

ciscoFabricC12kNotifGroup  NOTIFICATION-GROUP
    NOTIFICATIONS {
                   ciscoFabricC12kMIBFabMasterSchCh
                  }
    STATUS  current
    DESCRIPTION
            "A collection of notifications generated by
             the devices supporting this MIB."
    ::= { ciscoFabricC12kMIBGroups 13 }

END
