-- *****************************************************************
-- L A N O P T I C S - E T H E R N E T - O P T I O N - M I B . m y
--
-- March 1996, Keith Horil
--
-- Copyright (c) 1996 by cisco Systems, Inc.
-- All rights reserved.
-- *****************************************************************
--
-- This mib was developed by LanOptics


LANOPTICS-ETHERNET-OPTION-MIB DEFINITIONS ::= BEGIN

-- MIB II Extension Definitions for Ethernet Manager Option

IMPORTS
         OBJECT-TYPE
       	        FROM RFC-1212
         enterprises
       	        FROM RFC1155-SMI;

	lanOptics    OBJECT IDENTIFIER ::= { enterprises 224 }
	lanOpticsDot3Monitor    OBJECT IDENTIFIER ::= { lanOptics 3 }

etAlertsLevel OBJECT-TYPE
	SYNTAX  OCTET STRING
	ACCESS  read-write
	STATUS  mandatory
	DESCRIPTION
	"An array of 6 WORDs (16 bits) values that determines the
        alerts' thresholds for this agent."
	::= { lanOpticsDot3Monitor 1 }



etAlertsBuffer OBJECT-TYPE
	SYNTAX  OCTET STRING
	ACCESS  read-only
	STATUS  mandatory
	DESCRIPTION
	"A buffer holding a list of the last Ethernet manager specific
        alerts (traps), in an internal representation."
	::= { lanOpticsDot3Monitor 2 }

etFullStatisticsBuffer OBJECT-TYPE
	SYNTAX  OCTET STRING
	ACCESS  read-only
	STATUS  mandatory
	DESCRIPTION
	"A buffer holding a full statistics information of a certain Ethernet port, in internal representation."
	::= { lanOpticsDot3Monitor 3 }

etResetBuffers OBJECT-TYPE
	SYNTAX  INTEGER{
	        reset(1)
	               }
	ACCESS  read-write
	STATUS  mandatory
	DESCRIPTION
	"Setting this value to 1 will flush the alerts and full statistics buffers of this agent"
	::= { lanOpticsDot3Monitor 4 }

etSlotsTable  OBJECT-TYPE
	SYNTAX  SEQUENCE OF EtSlotsEntry
	ACCESS  not-accessible
	STATUS  mandatory
	DESCRIPTION
	"Ethernet information per slot"
	::= { lanOpticsDot3Monitor 5 }

etSlotsEntry  OBJECT-TYPE
	SYNTAX  EtSlotsEntry
	ACCESS  not-accessible
	STATUS  mandatory
	DESCRIPTION
	"A slot entry containing low level information of an Ethernet the card in the slot."
        INDEX   { INTEGER }
	::=   { etSlotsTable 1 }

EtSlotsEntry ::= SEQUENCE {
	etSlotPollStruct
		      OCTET STRING
	}

etSlotPollStruct OBJECT-TYPE
	SYNTAX  OCTET STRING
	ACCESS  read-only
	STATUS  mandatory
	DESCRIPTION
	"A structure holding in internal representation, the detailed status of the Ethernet module in this slot"
	::=  { etSlotsEntry 1 }

END
