-- *****************************************************************
-- BASIS-ONLINE-DIAG-MIB
--  Online diagnostics mib
--
-- June 2003 Subra Hegde
--
-- Copyright (c) 2003 by cisco Systems, Inc.
-- All rights reserved.
-- *****************************************************************


BASIS-ONLINE-DIAG-MIB DEFINITIONS ::= BEGIN
IMPORTS
    MODULE-IDENTITY,
    OBJECT-TYPE,
    Integer32
                               FROM SNMPv2-SMI
    MODULE-COMPLIANCE,
    OBJECT-GROUP               FROM SNMPv2-CONF
    ciscoWan                   FROM CISCOWAN-SMI
    axisDiagnostics            FROM BASIS-MIB;

basisOnlineDiagMIB MODULE-IDENTITY
    LAST-UPDATED "200306110000Z"
    ORGANIZATION "Cisco Systems, Inc."
    CONTACT-INFO
                 "       Cisco Systems
                        Customer Service

                Postal: 170 W Tasman Drive
                        San Jose, CA  95134
                        USA

                        Tel: +1 800 553-NETS

                E-mail: cs-wanatm@cisco.com"
    DESCRIPTION
        "This MIB contains information on the online diagnostics
        in MGX82xx(MGX8250, MGX8220, MGX8230 etc) products."

    REVISION    "200306110000Z"
    DESCRIPTION
        "Initial version of the MIB.

        The content of this MIB was originally available
        in CISCO-WAN-AXIPOP-MIB defined using SMIv1.
        The applicable objects from CISCO-WAN-AXIPOP-MIB
        are defined using SMIv2 in this MIB. Also the
        descriptions of some of the objects have been
        modified."

    ::= { ciscoWan 80 }

onlineDiagnostics  OBJECT IDENTIFIER ::= { axisDiagnostics 3 }

diagType OBJECT-TYPE
    SYNTAX  INTEGER {
                post      (1),
                onlinediag(2)
            }
    MAX-ACCESS read-only
    STATUS     current
    DESCRIPTION
        "This is used to identify the type of diagnostics.

        post (1)      : Power On Self Test.
        onlineDiag(2) : Online Diagnostics.

        When a trap is sent to report diagnostics results
        this is used as a varbind to indicate the type of
        diagnostics."
    ::= { onlineDiagnostics 1 }

diagResult     OBJECT-TYPE
    SYNTAX  INTEGER {
                passed(1),
                failed(2)
            }
    MAX-ACCESS read-only
    STATUS     current
    DESCRIPTION
        "This is used to indicate the result of the diagnostics."
    ::= { onlineDiagnostics 2 }

diagTestId     OBJECT-TYPE
    SYNTAX     Integer32(0..2147483647)
    MAX-ACCESS read-only
    STATUS     current
    DESCRIPTION
        "This is used to indicate the test number of the
        diagnostics test that failed. The value depends upon
        the implementation in the each of the MGX82xx product."
    ::= { onlineDiagnostics 3 }

-- conformance information

boDiagMIBConformance OBJECT IDENTIFIER ::= { basisOnlineDiagMIB 2 }

boDiagMIBCompliances OBJECT IDENTIFIER ::= { boDiagMIBConformance 1 }

boDiagMIBGroups      OBJECT IDENTIFIER ::= { boDiagMIBConformance 2 }

-- compliance statements

boDiagCompliance MODULE-COMPLIANCE
    STATUS  current
    DESCRIPTION
        "The compliance statement for entities which implement
        the basis online diagnostics MIB."
    MODULE  -- this module
    MANDATORY-GROUPS {
        boDiagGroup
    }
    ::= { boDiagMIBCompliances 1 }

boDiagGroup OBJECT-GROUP
    OBJECTS {
        diagType,
        diagResult,
        diagTestId
    }
    STATUS current
    DESCRIPTION
        "A collection of objects providing the
         online diagnostics information."
    ::= { boDiagMIBGroups 1 }

END
