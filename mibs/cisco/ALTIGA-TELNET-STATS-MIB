-- *------------------------------------------------------------------
-- * ALTIGA-TELNET-STATS-MIB.my:  Altiga TELNET Statistics MIB.
-- *
-- * Altiga Networks was acquired by Cisco Systems on March 29, 2000
-- *
-- * Copyright (c) 2002 by Cisco Systems, Inc.
-- * All rights reserved.
-- *
-- *------------------------------------------------------------------

ALTIGA-TELNET-STATS-MIB DEFINITIONS ::= BEGIN

   IMPORTS
      MODULE-IDENTITY, OBJECT-TYPE, Integer32, IpAddress, Gauge32, Counter32
         FROM SNMPv2-SMI
      RowStatus, DisplayString
         FROM SNMPv2-TC
      OBJECT-GROUP, MODULE-COMPLIANCE
         FROM SNMPv2-CONF
      alStatsTelnet, alTelnetGroup
         FROM ALTIGA-MIB
      alTelnetMibModule
         FROM ALTIGA-GLOBAL-REG;

   altigaTelnetStatsMibModule MODULE-IDENTITY
      LAST-UPDATED   "200209051300Z"
      ORGANIZATION   "Cisco Systems, Inc."
      CONTACT-INFO
         "Cisco Systems
          170 W Tasman Drive
          San Jose, CA  95134
          USA

          Tel: +1 800 553-NETS
          E-mail: cs-cvpn3000@cisco.com"

      DESCRIPTION
         "The Altiga TELNET Statistics MIB models counters and objects that are
          of management interest for telnet sessions.

          Acronyms
          The following acronyms are used in this document:

            MIB:        Management Information Base

         "

        REVISION "200209051300Z"
        DESCRIPTION
                "Added module compliance."

        REVISION "200207100000Z"
        DESCRIPTION
                "Updated with new header"

      ::= { alTelnetMibModule 2 }

-- +++++++++++++++++++++++++++++++++++++++++++++++++++++++
-- MIB Objects
-- +++++++++++++++++++++++++++++++++++++++++++++++++++++++

alStatsTelnetGlobal  OBJECT IDENTIFIER ::= { alStatsTelnet 1 }

alTelnetStatsActiveSessions   OBJECT-TYPE
   SYNTAX         Gauge32
   MAX-ACCESS     read-only
   STATUS         current
   DESCRIPTION
          "The number of active Telnet sessions."
   ::= { alStatsTelnetGlobal 1 }

alTelnetStatsAttemptedSessions   OBJECT-TYPE
   SYNTAX         Counter32
   MAX-ACCESS     read-only
   STATUS         current
   DESCRIPTION
          "The number of attempts made to establish Telnet sessions."
   ::= { alStatsTelnetGlobal 2 }

alTelnetStatsSuccessfulSessions  OBJECT-TYPE
   SYNTAX         Counter32
   MAX-ACCESS     read-only
   STATUS         current
   DESCRIPTION
          "The number of successfully established Telnet sessions."
   ::= { alStatsTelnetGlobal 3 }

alTelnetStatsInNetPackets  OBJECT-TYPE
   SYNTAX         Counter32
   MAX-ACCESS     read-only
   STATUS         current
   DESCRIPTION
          "The total number of Telnet packets that were received from the network
           since the system was booted."
   ::= { alStatsTelnetGlobal 4 }

alTelnetStatsInNetOctets   OBJECT-TYPE
   SYNTAX         Counter32
   MAX-ACCESS     read-only
   STATUS         current
   DESCRIPTION
          "The total number of Telnet octets that were received from the network
           since the system was booted."
   ::= { alStatsTelnetGlobal 5 }

alTelnetStatsInNetCmdOctets   OBJECT-TYPE
   SYNTAX         Counter32
   MAX-ACCESS     read-only
   STATUS         current
   DESCRIPTION
          "The total number of octets that contained Telnet commands or options
      that were received from the network since the system was booted."
   ::= { alStatsTelnetGlobal 6 }

-- /* Syncs sequences are not yet supported, but when they are add the following:
-- /* should move it to the bottom to avoid renumbering, but this is it's pos in TNSTATS
-- alTelnetStatsSyncSeqs      OBJECT-TYPE
--    SYNTAX         Counter32
--    MAX-ACCESS     read-only
--    STATUS         current
--    DESCRIPTION
--           "The total number of Telnet sync sequences that were received from
--       the network since the system was booted."
--    ::= { alStatsTelnetGlobal X }

alTelnetStatsInNetDropPackets OBJECT-TYPE
   SYNTAX         Counter32
   MAX-ACCESS     read-only
   STATUS         current
   DESCRIPTION
          "The total number of Telnet packets from the network that were
      dropped during input processing since the system was booted."
   ::= { alStatsTelnetGlobal 7 }

alTelnetStatsInNetDropOctets  OBJECT-TYPE
   SYNTAX         Counter32
   MAX-ACCESS     read-only
   STATUS         current
   DESCRIPTION
          "The total number of Telnet octets from the network that were
      dropped during input processing since the system was booted."
   ::= { alStatsTelnetGlobal 8 }

-- /* Out Net

alTelnetStatsOutNetPackets OBJECT-TYPE
   SYNTAX         Counter32
   MAX-ACCESS     read-only
   STATUS         current
   DESCRIPTION
          "The total number of Telnet packets that were transmitted to the network
           since the system was booted."
   ::= { alStatsTelnetGlobal 9 }

alTelnetStatsOutNetOctets  OBJECT-TYPE
   SYNTAX         Counter32
   MAX-ACCESS     read-only
   STATUS         current
   DESCRIPTION
          "The total number of Telnet octets that were transmitted to the network
           since the system was booted."
   ::= { alStatsTelnetGlobal 10 }

alTelnetStatsOutNetDropPackets   OBJECT-TYPE
   SYNTAX         Counter32
   MAX-ACCESS     read-only
   STATUS         current
   DESCRIPTION
          "The total number of Telnet packets destined for the network that were
      dropped during output processing since the system was booted."
   ::= { alStatsTelnetGlobal 11 }

alTelnetStatsOutNetDropOctets OBJECT-TYPE
   SYNTAX         Counter32
   MAX-ACCESS     read-only
   STATUS         current
   DESCRIPTION
          "The total number of Telnet octets destined for the network that were
      dropped during output processing since the system was booted."
   ::= { alStatsTelnetGlobal 12 }

--   In Shell

alTelnetStatsInShPackets   OBJECT-TYPE
   SYNTAX         Counter32
   MAX-ACCESS     read-only
   STATUS         current
   DESCRIPTION
          "The total number of Telnet packets that were received from the shell
           since the system was booted."
   ::= { alStatsTelnetGlobal 13 }

alTelnetStatsInShOctets    OBJECT-TYPE
   SYNTAX         Counter32
   MAX-ACCESS     read-only
   STATUS         current
   DESCRIPTION
          "The total number of Telnet octets that were received from the shell
           since the system was booted."
   ::= { alStatsTelnetGlobal 14 }

alTelnetStatsInShDropPackets  OBJECT-TYPE
   SYNTAX         Counter32
   MAX-ACCESS     read-only
   STATUS         current
   DESCRIPTION
          "The total number of Telnet packets from the shell that were
      dropped during input processing since the system was booted."
   ::= { alStatsTelnetGlobal 15 }

alTelnetStatsInShDropOctets   OBJECT-TYPE
   SYNTAX         Counter32
   MAX-ACCESS     read-only
   STATUS         current
   DESCRIPTION
          "The total number of Telnet octets from the shell that were
      dropped during input processing since the system was booted."
   ::= { alStatsTelnetGlobal 16 }

--   Out Shell

alTelnetStatsOutShPackets  OBJECT-TYPE
   SYNTAX         Counter32
   MAX-ACCESS     read-only
   STATUS         current
   DESCRIPTION
          "The total number of Telnet packets that were transmitted to the shell
           since the system was booted."
   ::= { alStatsTelnetGlobal 17 }

alTelnetStatsOutShOctets   OBJECT-TYPE
   SYNTAX         Counter32
   MAX-ACCESS     read-only
   STATUS         current
   DESCRIPTION
          "The total number of Telnet octets that were transmitted to the shell
           since the system was booted."
   ::= { alStatsTelnetGlobal 18 }

alTelnetStatsOutShDropPackets OBJECT-TYPE
   SYNTAX         Counter32
   MAX-ACCESS     read-only
   STATUS         current
   DESCRIPTION
          "The total number of Telnet packets destined for the shell that were
      dropped during output processing since the system was booted."
   ::= { alStatsTelnetGlobal 19 }

alTelnetStatsOutShDropOctets  OBJECT-TYPE
   SYNTAX         Counter32
   MAX-ACCESS     read-only
   STATUS         current
   DESCRIPTION
          "The total number of Telnet octets destined for the shell that were
      dropped during output processing since the system was booted."
   ::= { alStatsTelnetGlobal 20 }


--   Per session stats

alTelnetStatsSessionTable  OBJECT-TYPE
   SYNTAX         SEQUENCE OF AlTelnetStatsSessionEntry
   MAX-ACCESS     not-accessible
   STATUS         current
   DESCRIPTION
          "List of active sessions."
   ::= { alStatsTelnet 2 }

alTelnetStatsSessionEntry  OBJECT-TYPE
   SYNTAX         AlTelnetStatsSessionEntry
   MAX-ACCESS     not-accessible
   STATUS         current
   DESCRIPTION
          "An entry in the alTelnetStatsSessionTable."
   INDEX       { alTelnetStatsSessionId }
   ::= { alTelnetStatsSessionTable 1 }

AlTelnetStatsSessionEntry ::= SEQUENCE {
   alTelnetStatsSessionRowStatus          RowStatus,
   alTelnetStatsSessionId                 Integer32,
   alTelnetStatsSessionIpAddr             IpAddress,
   alTelnetStatsSessionSrcPort            Integer32,
   alTelnetStatsSessionName               DisplayString,
   alTelnetStatsSessionInNetPackets       Counter32,
   alTelnetStatsSessionInNetOctets        Counter32,
   alTelnetStatsSessionInNetCmdOctets     Counter32,
-- alTelnetStatsSessionSyncSeqs           Counter32,
   alTelnetStatsSessionInNetDropPackets   Counter32,
   alTelnetStatsSessionInNetDropOctets    Counter32,
   alTelnetStatsSessionOutNetPackets      Counter32,
   alTelnetStatsSessionOutNetOctets       Counter32,
   alTelnetStatsSessionOutNetDropPackets  Counter32,
   alTelnetStatsSessionOutNetDropOctets   Counter32,
   alTelnetStatsSessionInShPackets        Counter32,
   alTelnetStatsSessionInShOctets         Counter32,
   alTelnetStatsSessionInShDropPackets    Counter32,
   alTelnetStatsSessionInShDropOctets     Counter32,
   alTelnetStatsSessionOutShPackets       Counter32,
   alTelnetStatsSessionOutShOctets        Counter32,
   alTelnetStatsSessionOutShDropPackets   Counter32,
   alTelnetStatsSessionOutShDropOctets    Counter32
}

alTelnetStatsSessionRowStatus OBJECT-TYPE
   SYNTAX         RowStatus
   MAX-ACCESS     read-write
   STATUS         current
   DESCRIPTION
          "The status of this row. Used to terminate the session,
      cannot be used to create a Session."
   ::= { alTelnetStatsSessionEntry 1 }

alTelnetStatsSessionId     OBJECT-TYPE
   SYNTAX         Integer32
   MAX-ACCESS     read-only
   STATUS         current
   DESCRIPTION
          "The unique Telnet session process ID, used as the
           index for this row."
   ::= { alTelnetStatsSessionEntry 2 }

alTelnetStatsSessionIpAddr OBJECT-TYPE
   SYNTAX         IpAddress
   MAX-ACCESS     read-only
   STATUS         current
   DESCRIPTION
      "The IP address of the remote client."
   ::= { alTelnetStatsSessionEntry 3 }

alTelnetStatsSessionSrcPort   OBJECT-TYPE
   SYNTAX         Integer32
   MAX-ACCESS     read-only
   STATUS         current
   DESCRIPTION
      "The TCP source port number of the remote client."
   ::= { alTelnetStatsSessionEntry 4 }

alTelnetStatsSessionName   OBJECT-TYPE
   SYNTAX         DisplayString
   MAX-ACCESS     read-only
   STATUS         current
   DESCRIPTION
          "The unique Telnet session process name, used as the
           index for this row."
   ::= { alTelnetStatsSessionEntry 5 }

alTelnetStatsSessionInNetPackets OBJECT-TYPE
   SYNTAX         Counter32
   MAX-ACCESS     read-only
   STATUS         current
   DESCRIPTION
          "The per session number of Telnet packets that were received from the network
           since the system was booted."
   ::= { alTelnetStatsSessionEntry 6 }

alTelnetStatsSessionInNetOctets  OBJECT-TYPE
   SYNTAX         Counter32
   MAX-ACCESS     read-only
   STATUS         current
   DESCRIPTION
          "The per session number of Telnet octets that were received from the network
           since the system was booted."
   ::= { alTelnetStatsSessionEntry 7 }

alTelnetStatsSessionInNetCmdOctets  OBJECT-TYPE
   SYNTAX         Counter32
   MAX-ACCESS     read-only
   STATUS         current
   DESCRIPTION
          "The per session number of octets that contained Telnet commands or options
      that were received from the network since the system was booted."
   ::= { alTelnetStatsSessionEntry 8 }

--   Syncs sequences are not yet supported, but when they are add the following:
--   should move it to the bottom to avoid renumbering, but this is it's pos in TNSTATS
-- alTelnetStatsSessionSyncSeqs     OBJECT-TYPE
--    SYNTAX         Counter32
--    MAX-ACCESS     read-only
--    STATUS         current
--    DESCRIPTION
--           "The per session number of Telnet sync sequences that were received from
--       the network since the system was booted."
--    ::= { alTelnetStatsSessionEntry XX }

alTelnetStatsSessionInNetDropPackets   OBJECT-TYPE
   SYNTAX         Counter32
   MAX-ACCESS     read-only
   STATUS         current
   DESCRIPTION
          "The per session number of Telnet packets from the network that were
      dropped during input processing since the system was booted."
   ::= { alTelnetStatsSessionEntry 9 }

alTelnetStatsSessionInNetDropOctets OBJECT-TYPE
   SYNTAX         Counter32
   MAX-ACCESS     read-only
   STATUS         current
   DESCRIPTION
          "The per session number of Telnet octets from the network that were
      dropped during input processing since the system was booted."
   ::= { alTelnetStatsSessionEntry 10 }

--   Out Net

alTelnetStatsSessionOutNetPackets   OBJECT-TYPE
   SYNTAX         Counter32
   MAX-ACCESS     read-only
   STATUS         current
   DESCRIPTION
          "The per session number of Telnet packets that were transmitted to the network
           since the system was booted."
   ::= { alTelnetStatsSessionEntry 11 }

alTelnetStatsSessionOutNetOctets OBJECT-TYPE
   SYNTAX         Counter32
   MAX-ACCESS     read-only
   STATUS         current
   DESCRIPTION
          "The per session number of Telnet octets that were transmitted to the network
           since the system was booted."
   ::= { alTelnetStatsSessionEntry 12 }

alTelnetStatsSessionOutNetDropPackets  OBJECT-TYPE
   SYNTAX         Counter32
   MAX-ACCESS     read-only
   STATUS         current
   DESCRIPTION
          "The per session number of Telnet packets destined for the network that were
      dropped during output processing since the system was booted."
   ::= { alTelnetStatsSessionEntry 13 }

alTelnetStatsSessionOutNetDropOctets   OBJECT-TYPE
   SYNTAX         Counter32
   MAX-ACCESS     read-only
   STATUS         current
   DESCRIPTION
          "The per session number of Telnet octets destined for the network that were
      dropped during output processing since the system was booted."
   ::= { alTelnetStatsSessionEntry 14 }

--   In Shell

alTelnetStatsSessionInShPackets  OBJECT-TYPE
   SYNTAX         Counter32
   MAX-ACCESS     read-only
   STATUS         current
   DESCRIPTION
          "The per session number of Telnet packets that were received from the shell
           since the system was booted."
   ::= { alTelnetStatsSessionEntry 15 }

alTelnetStatsSessionInShOctets      OBJECT-TYPE
   SYNTAX         Counter32
   MAX-ACCESS     read-only
   STATUS         current
   DESCRIPTION
          "The per session number of Telnet octets that were received from the shell
           since the system was booted."
   ::= { alTelnetStatsSessionEntry 16 }

alTelnetStatsSessionInShDropPackets OBJECT-TYPE
   SYNTAX         Counter32
   MAX-ACCESS     read-only
   STATUS         current
   DESCRIPTION
          "The per session number of Telnet packets from the shell that were
      dropped during input processing since the system was booted."
   ::= { alTelnetStatsSessionEntry 17 }

alTelnetStatsSessionInShDropOctets  OBJECT-TYPE
   SYNTAX         Counter32
   MAX-ACCESS     read-only
   STATUS         current
   DESCRIPTION
          "The per session number of Telnet octets from the shell that were
      dropped during input processing since the system was booted."
   ::= { alTelnetStatsSessionEntry 18 }

--   Out Shell

alTelnetStatsSessionOutShPackets OBJECT-TYPE
   SYNTAX         Counter32
   MAX-ACCESS     read-only
   STATUS         current
   DESCRIPTION
          "The per session number of Telnet packets that were transmitted to the shell
           since the system was booted."
   ::= { alTelnetStatsSessionEntry 19 }

alTelnetStatsSessionOutShOctets  OBJECT-TYPE
   SYNTAX         Counter32
   MAX-ACCESS     read-only
   STATUS         current
   DESCRIPTION
          "The per session number of Telnet octets that were transmitted to the shell
           since the system was booted."
   ::= { alTelnetStatsSessionEntry 20 }

alTelnetStatsSessionOutShDropPackets   OBJECT-TYPE
   SYNTAX         Counter32
   MAX-ACCESS     read-only
   STATUS         current
   DESCRIPTION
          "The per session number of Telnet packets destined for the shell that were
      dropped during output processing since the system was booted."
   ::= { alTelnetStatsSessionEntry 21 }

alTelnetStatsSessionOutShDropOctets OBJECT-TYPE
   SYNTAX         Counter32
   MAX-ACCESS     read-only
   STATUS         current
   DESCRIPTION
          "The per session number of Telnet octets destined for the shell that were
      dropped during output processing since the system was booted."
   ::= { alTelnetStatsSessionEntry 22 }

altigaTelnetStatsMibConformance OBJECT IDENTIFIER ::= { altigaTelnetStatsMibModule 1 }
altigaTelnetStatsMibCompliances OBJECT IDENTIFIER ::= { altigaTelnetStatsMibConformance 1 }

altigaTelnetStatsMibCompliance MODULE-COMPLIANCE
   STATUS         current
   DESCRIPTION
      "The compliance statement for agents which
       implement the Altiga Telnet Statistics MIB."
   MODULE
   MANDATORY-GROUPS {
      altigaTelnetStatsGroup
   }
   ::= { altigaTelnetStatsMibCompliances 1 }

altigaTelnetStatsGroup OBJECT-GROUP
   OBJECTS
   {
      alTelnetStatsActiveSessions,
      alTelnetStatsAttemptedSessions,
      alTelnetStatsSuccessfulSessions,
      alTelnetStatsInNetPackets,
      alTelnetStatsInNetOctets,
      alTelnetStatsInNetCmdOctets,
--    alTelnetStatsSyncSeqs,
      alTelnetStatsInNetDropPackets,
      alTelnetStatsInNetDropOctets,
      alTelnetStatsOutNetPackets,
      alTelnetStatsOutNetOctets,
      alTelnetStatsOutNetDropPackets,
      alTelnetStatsOutNetDropOctets,
      alTelnetStatsInShPackets,
      alTelnetStatsInShOctets,
      alTelnetStatsInShDropPackets,
      alTelnetStatsInShDropOctets,
      alTelnetStatsOutShPackets,
      alTelnetStatsOutShOctets,
      alTelnetStatsOutShDropPackets,
      alTelnetStatsOutShDropOctets,
      alTelnetStatsSessionRowStatus,
      alTelnetStatsSessionId,
      alTelnetStatsSessionIpAddr,
      alTelnetStatsSessionSrcPort,
      alTelnetStatsSessionName,
      alTelnetStatsSessionInNetPackets,
      alTelnetStatsSessionInNetOctets,
      alTelnetStatsSessionInNetCmdOctets,
--    alTelnetStatsSessionSyncSeqs,
      alTelnetStatsSessionInNetDropPackets,
      alTelnetStatsSessionInNetDropOctets,
      alTelnetStatsSessionOutNetPackets,
      alTelnetStatsSessionOutNetOctets,
      alTelnetStatsSessionOutNetDropPackets,
      alTelnetStatsSessionOutNetDropOctets,
      alTelnetStatsSessionInShPackets,
      alTelnetStatsSessionInShOctets,
      alTelnetStatsSessionInShDropPackets,
      alTelnetStatsSessionInShDropOctets,
      alTelnetStatsSessionOutShPackets,
      alTelnetStatsSessionOutShOctets,
      alTelnetStatsSessionOutShDropPackets,
      alTelnetStatsSessionOutShDropOctets
   }
   STATUS   current
   DESCRIPTION
          "The objects for the Telnet Server statistics."
   ::= { alTelnetGroup 2 }

END
