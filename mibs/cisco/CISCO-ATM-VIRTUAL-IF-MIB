-- *****************************************************************
-- ciscoAtmVirtualIf MIB
--
-- Oct. 2002, Prasanna Mucharikar
--
-- Copyright (c) 1999, 2002 by cisco Systems, Inc.
-- All rights reserved.
-- *****************************************************************

CISCO-ATM-VIRTUAL-IF-MIB DEFINITIONS ::= BEGIN
IMPORTS
        MODULE-IDENTITY,
        OBJECT-TYPE,
        Integer32,
        Counter64,
        Counter32,
        Unsigned32              FROM SNMPv2-SMI
        RowStatus               FROM SNMPv2-TC
        AtmVpIdentifier         FROM ATM-TC-MIB
        MODULE-COMPLIANCE,
        OBJECT-GROUP            FROM SNMPv2-CONF
        InterfaceIndex,
        ifIndex                 FROM IF-MIB
        ciscoMgmt               FROM CISCO-SMI;

ciscoAtmVirtualIfMIB MODULE-IDENTITY
        LAST-UPDATED        "200210110000Z"
        ORGANIZATION        "Cisco Systems, Inc."
        CONTACT-INFO
                "       Cisco Systems
                        Customer Service

                Postal: 170 W Tasman Drive
                        San Jose, CA  95134
                        USA

                   Tel: +1 800 553-NETS

                E-mail: cs-wanatm@cisco.com"

         DESCRIPTION
            "The MIB module to manage ATM Virtual interface objects.
             ATM virtual interfaces are configured on a physical line."

	 REVISION        "200210110000Z"
         DESCRIPTION
            "1. Added caviIngressIntervalTable. "

         REVISION        "200205070000Z"
         DESCRIPTION
            "1. Added following objects to caviStatEgressTable, as
                upper 32-bits for 64-bit wide counters:
                caviHighEgrRcvClp0Cells, caviHighEgrRcvClp1Cells,
                caviHighEgrClp0DiscCells, caviHighEgrClp1DiscCells,
                caviHighEgrXmtClp0Cells, caviHighEgrXmtClp1Cells.
             2. Added following 64-bit objects to
                caviStatEgressTable for 64-bit counter support:
                caviHEgrRcvClp0Cells, caviHEgrClp0DiscCells,
                caviHEgrClp0DiscCells, caviHEgrClp1DiscCells.
             3. Added following objects to caviEgressIntervalTable,
                as upper 32-bits for 64-bit wide counters:
                caviHighIntEgrRcvClp0Cells,
                caviHighIntEgrRcvClp1Cells,
                caviHighIntEgrClp0DiscCells,
                caviHighIntEgrClp1DiscCells,
                caviHighIntEgrXmtClp0Cells,
                caviHighIntEgrXmtClp1Cells.
             4. Added following 64-bit objects to
                caviEgressIntervalTable:
                caviHIntEgrRcvClp0Cells, caviHIntEgrRcvClp1Cells,
                caviHIntEgrClp0DiscCells, caviHIntEgrClp1DiscCells,
                caviHIntEgrXmtClp0Cells, caviHIntEgrXmtClp1Cells.
             5. Added following objects to caviStatIngressTable, as
                upper 32-bits for 64-bit wide counters:
                caviHighIngRcvClp0Cells, caviHighIngRcvClp1Cells,
                caviHighIngClp0DiscCells, caviHighIngClp1DiscCells,
                caviHighIngXmtClp0Cells, caviHighIngXmtClp1Cells.
             6. Added following 64-bit objects to
                caviStatIngressTable:
                caviHIngClp0DiscCells, caviHIngClp1DiscCells,
                caviHIngXmtClp0Cells, caviHIngXmtClp1Cells.
             7. Changed IMPORT for Unsigned32 to SNMPv2-SMI, instead
                of CISCO-TC."

         REVISION        "200109030000Z"
         DESCRIPTION
            "Added caviMinVpiNum and caviMaxVpiNum. Modified description
             for caviEntry and caviIfType."

         REVISION        "200008110000Z"
         DESCRIPTION
            "Changed description of objects caviMinRate and caviMaxRate.
             Modified range for caviMinRate, caviMaxRate and
             caviFileId."

         REVISION        "200001140000Z"
         DESCRIPTION
            "Initial version of this MIB module."

         ::= {ciscoMgmt 129 }

ciscoAtmVirtualIfMIBObjects
                        OBJECT IDENTIFIER ::= { ciscoAtmVirtualIfMIB 1}
caviConfig              OBJECT IDENTIFIER ::= { ciscoAtmVirtualIfMIBObjects 1}
caviStatistics          OBJECT IDENTIFIER ::= { ciscoAtmVirtualIfMIBObjects 2}

-- ---------------------------------------------------------------------
-- cisco ATM Virtual Interface Config Group
-- ---------------------------------------------------------------------

caviTable OBJECT-TYPE
        SYNTAX  SEQUENCE OF CaviEntry
        MAX-ACCESS not-accessible
        STATUS     current
        DESCRIPTION
          "This table is used for creating ATM virtual Interfaces.
           The ATM virtual interfaces are created on physical interfaces.
           For each entry created in this table, there will be an entry
           created in the ifTable with ifType atmVirtual(149).
           For each entry deleted from this table, the corresponding entry
           from ifTable will be deleted. The ifIndex value for ifType
           atmVirtual(149) is used for indexing to atmInterfaceConfTable
           for getting information on a ATM virtual interface."
        ::= { caviConfig 1 }

caviEntry OBJECT-TYPE
        SYNTAX     CaviEntry
        MAX-ACCESS not-accessible
        STATUS     current
        DESCRIPTION
            "An entry in the caviTable table for each ATM virtual interface.
             An entry in this table can only be created if values for all
             objects in a row are provided.

             The caviVpiNum object is applicable only to interfaces of
             caviIfType vnni (3) or vuni (4).

             The caviMinVpiNum and caviMaxVpiNum are applicable only to
             interfaces of caviIfType evuni(5) or evnni(6)."
        INDEX   { caviIndex }
        ::= { caviTable 1 }

CaviEntry ::=
        SEQUENCE {
              caviIndex              Integer32,
              caviPhyIfIndex         InterfaceIndex ,
              caviViIfIndex          InterfaceIndex,
              caviMinRate            Unsigned32,
              caviMaxRate            Unsigned32,
              caviFileId             Unsigned32,
              caviIfType             INTEGER,
              caviVpiNum             AtmVpIdentifier,
              caviRowStatus          RowStatus,
              caviMinVpiNum          AtmVpIdentifier,
              caviMaxVpiNum          AtmVpIdentifier
              }

caviIndex OBJECT-TYPE
        SYNTAX Integer32  (1..2147483647)
        MAX-ACCESS not-accessible
        STATUS  current
        DESCRIPTION
           "A unique value for the ATM virtual interface."
        ::= { caviEntry 1 }

caviPhyIfIndex OBJECT-TYPE
        SYNTAX InterfaceIndex
        MAX-ACCESS  read-create
        STATUS  current
        DESCRIPTION
           "This object identifies the interface number ( 'ifIndex' ) assigned
            to  sonet(39),ds3(30),ds1(18),atmIma(107)."
        ::= { caviEntry 2 }

caviViIfIndex OBJECT-TYPE
        SYNTAX InterfaceIndex
        MAX-ACCESS  read-only
        STATUS  current
        DESCRIPTION
            "This object identifies the ATM virtual interface number
              ('ifIndex') assigned to this entry, and is used
              to identify corresponding rows in the IF-MIB.
              Note that re-inititalization of the management agent may
              cause a client's 'caviViIfIndex' to change."
        ::= { caviEntry 3 }

caviMinRate OBJECT-TYPE
        SYNTAX     Unsigned32
        UNITS      "cells-per-second"
        MAX-ACCESS read-create
        STATUS current
        DESCRIPTION
             "ATM virtual interface's guaranteed cell rate.
              This is the guaranteed bandwidth allocated for
              the interface. The sum of caviMinRate of all ATM
              virtual interfaces configured on a single physical line,
              must not exceed the bandwidth of the physical line. Creation
              of a row is rejected when the sum of caviMinRate of all existing
              ATM virtual interfaces exceeds the physical line bandwidth.
              The value of this object can't exceed the 'ifSpeed' or
              'ifHighSpeed' value in ifTable for the associated
              'caviPhyIfIndex'.
              ATM cell bandwidths for various physical lines are:

              OC192 line : 22605280 cells/sec
              OC48  line : 5651320 cells/sec
              OC12  line : 1412830 cells/sec
              OC3   line :  353207 cells/sec
              T3    line :   96000 cells/sec
              E3    line :   80000 cells/sec."
        ::= { caviEntry 4 }

caviMaxRate OBJECT-TYPE
        SYNTAX     Unsigned32
        UNITS     "cells-per-second"
        MAX-ACCESS read-create
        STATUS     current
        DESCRIPTION
            "ATM virtual interface's maximum cell rate.
             If bandwidth is available, the interface will
             be allocated bandwidth upto this value.
             The total bandwidth of connections configured over this
             interface cannot exceed this value.
             The value of this object can't exceed the 'ifSpeed' or
             'ifHighSpeed' value in ifTable for the associated
             'caviPhyIfIndex'.
             ATM cell bandwidths for various physical lines are:

             OC192 line : 22605280 cells/sec
             OC48  line : 5651320 cells/sec
             OC12  line : 1412830 cells/sec
             OC3   line :  353207 cells/sec
             T3    line :   96000 cells/sec
             E3    line :   80000 cells/sec."
        ::= {caviEntry 5 }

caviFileId OBJECT-TYPE
        SYNTAX     Unsigned32
        MAX-ACCESS read-create
        STATUS     current
        DESCRIPTION
           "The ID of the  file that holds module specific configuration
            parameters for this ATM virtual interface."
        DEFVAL { 0 }
        ::= { caviEntry 6 }

caviIfType OBJECT-TYPE
    SYNTAX  INTEGER  {
               uni(1),
               nni(2),
               vnni(3),
               vuni(4),
               evuni(5),
               evnni(6)
               }
    MAX-ACCESS read-create
    STATUS     current
    DESCRIPTION
       "This object reflects the type of ATM virtual interface that can be
        configured within a physical interface. The supported types of virtual
        interfaces and their description is shown below:

        uni : Only one virtual interface of uni type can be configured within
              a physical interface. The ATM cells used in this interface would
              use a 8 bit VPI and a 4 bit GFC.
        nni : Only one virtual interface of nni type can be configured within
              a physical interface.The ATM cells used in this interface would
              use a 12 bit VPI.
        vnni: Multiple virtual interfaces of vnni type can be configured
              within a physical interface. However, all cells sent on this
              interface belong to a single VPI (defined by caviVpiNum) and
              the cells use a 12 bit VPI.
        vuni: Multiple virtual interfaces of vuni type can be configured
              within a physical interface. However, all cells sent on this
              interface belong to a single VPI (defined by caviVpiNum) and
              the cells use a 8 bit VPI and a 4 bit GFC.
        evuni: Multiple virtual interfaces of evuni type can be configured
              within a physical interface. However, all cells sent on this
              interface belong to a range of VPI (defined by caviMinVpiNum
              & caviMaxVpiNum) and the cells use a 8 bit VPI and a 4 bit GFC.
        evnni: Multiple virtual interfaces of evuni type can be configured
              within a physical interface. However, all cells sent on this
              interface belong to a range of VPI (defined by caviMinVpiNum
              & caviMaxVpiNum) and the cells use a 12 bit VPI."
    DEFVAL { uni }
    ::= { caviEntry 7 }


caviVpiNum OBJECT-TYPE
        SYNTAX  AtmVpIdentifier
        MAX-ACCESS read-create
        STATUS     current
        DESCRIPTION
           "This object is used when configuring ATM virtual interfaces of
            caviIftype vuni(4) or vnni (3). A non-zero value is required
            for vuni / vnni operation.

            The value set in this object for other type of caviIfTypes
            would be ignored by the agent. The GET operation on this object
            would return 0 for caviIfTypes other than vuni/vnni."
        DEFVAL { 0 }
        ::= { caviEntry 8 }

caviRowStatus OBJECT-TYPE
    SYNTAX     RowStatus
    MAX-ACCESS read-create
    STATUS     current
    DESCRIPTION
       "This object allows create and delete operations on caviTable
        entries.
        An entry is created in the table by setting this object to
        createAndGo(4).
        An entry is deleted from the table by setting this object to
        destroy(6).
        An entry in this table may be modified after creation."
    ::= {caviEntry 9 }

caviMinVpiNum OBJECT-TYPE
        SYNTAX  AtmVpIdentifier
        MAX-ACCESS read-create
        STATUS     current
        DESCRIPTION
           "This object is mandatory while configuring this ATM virtual
            interface as caviIfType evuni(5) or evnni(6). The range of
            VPI accepted by the agent depends on caviIfType.

            The evuni accepts a range from 0 to 255, while the evnni accepts
            a range from 0 to 4095.

            The object specifies the minimum VPI for a evuni/evnni interface.

            The agent ignores a SET on this object for any interface other
            than a evuni/evnni. A GET operation for interfaces other than a
            evuni/evnni would always yield 0"
        DEFVAL { 0 }
        ::= { caviEntry 10 }

caviMaxVpiNum OBJECT-TYPE
        SYNTAX  AtmVpIdentifier
        MAX-ACCESS read-create
        STATUS     current
        DESCRIPTION
           "This object is mandatory while configuring this ATM virtual
            interface as caviIfType evuni(5) or evnni(6). The range of
            VPI accepted by the agent depends on caviIfType.

            The evuni accepts a range from 0 to 255, while the evnni accepts
            a range from 0 to 4095.

            The agent rejects a SET on this object for any interface other
            than a evuni/evnni. A GET operation for interfaces other than a
            evuni/evnni would always yield 0"
        ::= { caviEntry 11 }

-- ---------------------------------------------------------------------
-- ATM Virtual Interface Egress Statistics Table
-- ---------------------------------------------------------------------

caviStatEgressTable OBJECT-TYPE
        SYNTAX  SEQUENCE OF CaviStatEgressEntry
        MAX-ACCESS not-accessible
        STATUS     current
        DESCRIPTION
           "This table reflects real time statistics associated with
            each of the ATM virtual interfaces on the egress side.

            Ingress direction means coming from network into switch,
            Egress direction means going from switch into the network."
        ::= { caviStatistics 1 }

caviStatEgressEntry OBJECT-TYPE
        SYNTAX     CaviStatEgressEntry
        MAX-ACCESS not-accessible
        STATUS     current
        DESCRIPTION
          "An entry for egress ATM virtual interface statistics. In all the following
           descriptions,
           CLP-0 means Cell Loss Priority = 0,
           CLP-1 means Cell Loss Priority = 1.

           Statistics are being collected before and after the traffic
           management and policing device."
        INDEX   { ifIndex }
        ::= { caviStatEgressTable 1 }

CaviStatEgressEntry ::=
        SEQUENCE {
            caviEgrRcvClp0Cells      	Counter32,
            caviEgrRcvClp1Cells      	Counter32,
            caviEgrClp0DiscCells     	Counter32,
            caviEgrClp1DiscCells     	Counter32,
            caviEgrXmtClp0Cells      	Counter32,
            caviEgrXmtClp1Cells      	Counter32,
            caviEgrRcvOAMCells       	Counter32,
            caviEgrRMCells           	Counter32,
            caviEgrXmtEFCICells      	Counter32,
            caviEgrRcvEFCICells      	Counter32,
            caviEgrXmtOAMCells       	Counter32,
            caviHEgrXmtClp0Cells     	Counter64,
            caviHEgrXmtClp1Cells     	Counter64,
	    caviHighEgrRcvClp0Cells  	Counter32,
            caviHighEgrRcvClp1Cells  	Counter32,
            caviHighEgrClp0DiscCells 	Counter32,
            caviHighEgrClp1DiscCells 	Counter32,
            caviHighEgrXmtClp0Cells  	Counter32,
            caviHighEgrXmtClp1Cells  	Counter32,
	    caviHEgrRcvClp0Cells    	Counter64,
            caviHEgrRcvClp1Cells    	Counter64,
            caviHEgrClp0DiscCells   	Counter64,
            caviHEgrClp1DiscCells   	Counter64
            }

caviEgrRcvClp0Cells OBJECT-TYPE
        SYNTAX     Counter32
        MAX-ACCESS read-only
        STATUS     current
        DESCRIPTION
           "The number of CLP-0 cells received from switch
            at the traffic management and policing device."
        ::= {caviStatEgressEntry 1 }

caviEgrRcvClp1Cells OBJECT-TYPE
        SYNTAX      Counter32
        MAX-ACCESS  read-only
        STATUS      current
        DESCRIPTION
           "The number of CLP-1 cells received from switch
            at the traffic management and policing device."
        ::= {caviStatEgressEntry 2 }

caviEgrClp0DiscCells OBJECT-TYPE
        SYNTAX      Counter32
        MAX-ACCESS  read-only
        STATUS      current
        DESCRIPTION
            "The number of CLP-0 cells discarded due to policing."
        ::= {caviStatEgressEntry 3 }

caviEgrClp1DiscCells OBJECT-TYPE
        SYNTAX     Counter32
        MAX-ACCESS read-only
        STATUS     current
        DESCRIPTION
           "The number of CLP-1 cells discarded due to policing."
        ::= {caviStatEgressEntry 4 }

caviEgrXmtClp0Cells OBJECT-TYPE
        SYNTAX     Counter32
        MAX-ACCESS read-only
        STATUS     current
        DESCRIPTION
           "The number of CLP-0 cells transmitted to the network
            after traffic management and policing."
        ::= {caviStatEgressEntry 5 }

caviEgrXmtClp1Cells OBJECT-TYPE
        SYNTAX     Counter32
        MAX-ACCESS read-only
        STATUS     current
        DESCRIPTION
           "The number of CLP-1 cells transmitted to the network
            after traffic management and policing."
        ::= {caviStatEgressEntry 6 }

caviEgrRcvOAMCells OBJECT-TYPE
    SYNTAX     Counter32
    MAX-ACCESS read-only
    STATUS     current
    DESCRIPTION
       "The number of OAM cells received from the switch
        at the traffic management and policing device."
    ::= {caviStatEgressEntry 7 }

caviEgrRMCells OBJECT-TYPE
    SYNTAX     Counter32
    MAX-ACCESS read-only
    STATUS     current
    DESCRIPTION
       "The number of RM cells transmitted to the network from the switch."
    ::= {caviStatEgressEntry 8 }

caviEgrXmtEFCICells OBJECT-TYPE
    SYNTAX     Counter32
    MAX-ACCESS read-only
    STATUS     current
    DESCRIPTION
       "The number of EFCI cells transmitted to the network
        after traffic management and policing."
    ::= {caviStatEgressEntry 9 }

caviEgrRcvEFCICells OBJECT-TYPE
    SYNTAX     Counter32
    MAX-ACCESS read-only
    STATUS     current
    DESCRIPTION
       "The number of EFCI cells received from the switch
        at traffic management and policing device."
    ::= {caviStatEgressEntry 10 }

caviEgrXmtOAMCells OBJECT-TYPE
        SYNTAX     Counter32
        MAX-ACCESS read-only
        STATUS     current
        DESCRIPTION
           "The number of OAM loopback cells transmitted to network
            after traffic management and policing."
        ::= {caviStatEgressEntry 11 }

caviHEgrXmtClp0Cells OBJECT-TYPE
        SYNTAX     Counter64
        MAX-ACCESS read-only
        STATUS     current
        DESCRIPTION
           "The 64-bit version of caviEgrXmtClp0Cells."
        ::= {caviStatEgressEntry 12 }

caviHEgrXmtClp1Cells OBJECT-TYPE
        SYNTAX     Counter64
        MAX-ACCESS read-only
        STATUS     current
        DESCRIPTION
           "The 64-bit version of caviEgrXmtClp1Cells."
        ::= {caviStatEgressEntry 13 }


caviHighEgrRcvClp0Cells OBJECT-TYPE
        SYNTAX     Counter32
        MAX-ACCESS read-only
        STATUS     current
        DESCRIPTION
           "The Upper 32 bit of the number of CLP-0 cells received
            from switch at the traffic management and policing
            device."
        ::= {caviStatEgressEntry 14 }

caviHighEgrRcvClp1Cells OBJECT-TYPE
        SYNTAX      Counter32
        MAX-ACCESS  read-only
        STATUS      current
        DESCRIPTION
           "The Upper 32 bit of the number of CLP-1 cells received
            from switch at the traffic management and policing
            device."
        ::= {caviStatEgressEntry 15 }

caviHighEgrClp0DiscCells OBJECT-TYPE
        SYNTAX      Counter32
        MAX-ACCESS  read-only
        STATUS      current
        DESCRIPTION
            "The Upper 32 bit of the number of CLP-0 cells discarded
             due to policing."
        ::= {caviStatEgressEntry 16 }

caviHighEgrClp1DiscCells OBJECT-TYPE
        SYNTAX     Counter32
        MAX-ACCESS read-only
        STATUS     current
        DESCRIPTION
           "The Upper 32 bit of the number of CLP-1 cells discarded
            due to policing."
        ::= {caviStatEgressEntry 17 }

caviHighEgrXmtClp0Cells OBJECT-TYPE
        SYNTAX     Counter32
        MAX-ACCESS read-only
        STATUS     current
        DESCRIPTION
           "The Upper 32 bit of the number of CLP-0 cells
            transmitted to the network after traffic management and
            policing."
        ::= {caviStatEgressEntry 18 }

caviHighEgrXmtClp1Cells OBJECT-TYPE
        SYNTAX     Counter32
        MAX-ACCESS read-only
        STATUS     current
        DESCRIPTION
           "The Upper 32 bit of the number of CLP-1 cells
            transmitted to the network after traffic management and
            policing."
        ::= {caviStatEgressEntry 19 }

caviHEgrRcvClp0Cells OBJECT-TYPE
        SYNTAX     Counter64
        MAX-ACCESS read-only
        STATUS     current
        DESCRIPTION
           "The 64 bit version of the number of CLP-0 cells received
            from switch at the traffic management and policing
            device."
        ::= {caviStatEgressEntry 20 }

caviHEgrRcvClp1Cells OBJECT-TYPE
        SYNTAX      Counter64
        MAX-ACCESS  read-only
        STATUS      current
        DESCRIPTION
           "The 64 bit version of the number of CLP-1 cells received
            from switch at the traffic management and policing
            device."
        ::= {caviStatEgressEntry 21 }

caviHEgrClp0DiscCells OBJECT-TYPE
        SYNTAX      Counter64
        MAX-ACCESS  read-only
        STATUS      current
        DESCRIPTION
            "The 64 bit version of the number of CLP-0 cells
             discarded due to policing."
        ::= {caviStatEgressEntry 22 }

caviHEgrClp1DiscCells OBJECT-TYPE
        SYNTAX     Counter64
        MAX-ACCESS read-only
        STATUS     current
        DESCRIPTION
           "The 64 bit version of the number of CLP-1 cells
            discarded due to policing."
        ::= {caviStatEgressEntry 23 }

-- ---------------------------------------------------------------------
-- ATM Virtual Interface Egress Interval Statistics Table
-- ---------------------------------------------------------------------

caviEgressIntervalTable OBJECT-TYPE
        SYNTAX  SEQUENCE OF CaviEgressIntervalEntry
        MAX-ACCESS not-accessible
        STATUS     current
        DESCRIPTION
           "This table reflects interval statistics associated with
            each of the ATM virtual interfaces in egress direction."
        ::= { caviStatistics 2 }

caviEgressIntervalEntry OBJECT-TYPE
        SYNTAX     CaviEgressIntervalEntry
        MAX-ACCESS not-accessible
        STATUS     current
        DESCRIPTION
          "An entry for egress ATM virtual interface interval statistics.
           In addition to the current 15-minute interval bucket, the previous
           24 hours worth of 15-minute interval buckets are collected for each
           ATM virtual interface.

           Statistics are being collected before and after the traffic
           management and policing device, in egress direction."
        INDEX   { ifIndex, caviEgressIntervalNumber }
        ::= { caviEgressIntervalTable 1 }

CaviEgressIntervalEntry ::=
        SEQUENCE {
            caviEgressIntervalNumber    Unsigned32,
            caviIntEgrRcvClp0Cells      Counter32,
            caviIntEgrRcvClp1Cells      Counter32,
            caviIntEgrClp0DiscCells     Counter32,
            caviIntEgrClp1DiscCells     Counter32,
            caviIntEgrXmtClp0Cells      Counter32,
            caviIntEgrXmtClp1Cells      Counter32,
            caviIntEgrRcvOAMCells       Counter32,
            caviIntEgrRMCells           Counter32,
            caviIntEgrXmtEFCICells      Counter32,
            caviIntEgrRcvEFCICells      Counter32,
            caviIntEgrXmtOAMCells       Counter32,
            caviHighIntEgrRcvClp0Cells  Counter32,
            caviHighIntEgrRcvClp1Cells  Counter32,
            caviHighIntEgrClp0DiscCells Counter32,
            caviHighIntEgrClp1DiscCells Counter32,
            caviHighIntEgrXmtClp0Cells  Counter32,
            caviHighIntEgrXmtClp1Cells  Counter32,
            caviHIntEgrRcvClp0Cells	Counter64,
            caviHIntEgrRcvClp1Cells    	Counter64,
            caviHIntEgrClp0DiscCells   	Counter64,
            caviHIntEgrClp1DiscCells   	Counter64,
            caviHIntEgrXmtClp0Cells    	Counter64,
            caviHIntEgrXmtClp1Cells    	Counter64
            }

caviEgressIntervalNumber OBJECT-TYPE
        SYNTAX  Unsigned32(0..96)
        MAX-ACCESS  read-only
        STATUS  current
        DESCRIPTION
          "A number used to uniquely identify a ATM virtual interface's
           interval statistics. 0 is used to identify the current
           15-minute interval. 1-96 identify the previous 24 hours
           of 15-minute interval buckets."
        ::= { caviEgressIntervalEntry 1 }

caviIntEgrRcvClp0Cells OBJECT-TYPE
        SYNTAX     Counter32
        MAX-ACCESS read-only
        STATUS     current
        DESCRIPTION
           "The number of CLP-0 cells received from switch
            at the traffic management and policing device
            during a 15 minute interval."
        ::= { caviEgressIntervalEntry 2 }

caviIntEgrRcvClp1Cells OBJECT-TYPE
        SYNTAX      Counter32
        MAX-ACCESS  read-only
        STATUS      current
        DESCRIPTION
           "The number of CLP-1 cells received from switch
            at the traffic management and policing device
            during a 15 minute interval."
        ::= { caviEgressIntervalEntry 3 }

caviIntEgrClp0DiscCells OBJECT-TYPE
        SYNTAX      Counter32
        MAX-ACCESS  read-only
        STATUS      current
        DESCRIPTION
            "The number of CLP-0 cells discarded due to policing
             during a 15 minute interval."
        ::= { caviEgressIntervalEntry 4 }

caviIntEgrClp1DiscCells OBJECT-TYPE
        SYNTAX     Counter32
        MAX-ACCESS read-only
        STATUS     current
        DESCRIPTION
           "The number of CLP-1 cells discarded due to policing
            during a 15 minute interval."
        ::= { caviEgressIntervalEntry 5 }

caviIntEgrXmtClp0Cells OBJECT-TYPE
        SYNTAX     Counter32
        MAX-ACCESS read-only
        STATUS     current
        DESCRIPTION
           "The number of CLP-0 cells transmitted to the network
            after traffic management and policing
            during a 15 minute interval."
        ::= { caviEgressIntervalEntry 6 }

caviIntEgrXmtClp1Cells OBJECT-TYPE
        SYNTAX     Counter32
        MAX-ACCESS read-only
        STATUS     current
        DESCRIPTION
           "The number of CLP-1 cells transmitted to the network
            after traffic management and policing during a 15 minute
            interval."
        ::= { caviEgressIntervalEntry 7 }

caviIntEgrRcvOAMCells OBJECT-TYPE
    SYNTAX     Counter32
    MAX-ACCESS read-only
    STATUS     current
    DESCRIPTION
       "The number of OAM cells received from the switch
        at the traffic management and policing device
        during a 15 minute interval."
    ::= { caviEgressIntervalEntry 8 }

caviIntEgrRMCells OBJECT-TYPE
    SYNTAX     Counter32
    MAX-ACCESS read-only
    STATUS     current
    DESCRIPTION
       "The number of RM cells transmitted to the network from the switch
        during a 15 minute interval."
    ::= { caviEgressIntervalEntry 9 }

caviIntEgrXmtEFCICells OBJECT-TYPE
    SYNTAX     Counter32
    MAX-ACCESS read-only
    STATUS     current
    DESCRIPTION
       "The number of EFCI cells transmitted to the network
        after traffic management and policing during a 15 minute
        interval."
    ::= { caviEgressIntervalEntry 10 }

caviIntEgrRcvEFCICells OBJECT-TYPE
    SYNTAX     Counter32
    MAX-ACCESS read-only
    STATUS     current
    DESCRIPTION
       "The number of EFCI cells received from the switch
        at traffic management and policing device during a 15
        minute interval."
    ::= { caviEgressIntervalEntry 11 }

caviIntEgrXmtOAMCells OBJECT-TYPE
        SYNTAX     Counter32
        MAX-ACCESS read-only
        STATUS     current
        DESCRIPTION
           "The number of OAM loopback cells transmitted to network
            after traffic management and policing during a 15 minute
            interval."
        ::= { caviEgressIntervalEntry 12 }

caviHighIntEgrRcvClp0Cells OBJECT-TYPE
        SYNTAX     Counter32
        MAX-ACCESS read-only
        STATUS     current
        DESCRIPTION
           "The upper 32 bits of the number of CLP-0 cells received
            from switch at the traffic management and policing
            device during a 15 minute interval."
        ::= { caviEgressIntervalEntry 13 }

caviHighIntEgrRcvClp1Cells OBJECT-TYPE
        SYNTAX      Counter32
        MAX-ACCESS  read-only
        STATUS      current
        DESCRIPTION
           "The upper 32 bits of the number of CLP-1 cells received
            from switch at the traffic management and policing
            device during a 15 minute interval."
        ::= { caviEgressIntervalEntry 14 }

caviHighIntEgrClp0DiscCells OBJECT-TYPE
        SYNTAX      Counter32
        MAX-ACCESS  read-only
        STATUS      current
        DESCRIPTION
            "The upper 32 bits of the number of CLP-0 cells discarded
             due to policing during a 15 minute interval."
        ::= { caviEgressIntervalEntry 15 }

caviHighIntEgrClp1DiscCells OBJECT-TYPE
        SYNTAX     Counter32
        MAX-ACCESS read-only
        STATUS     current
        DESCRIPTION
           "The upper 32 bits of the number of CLP-1 cells discarded
            due to policing during a 15 minute interval."
        ::= { caviEgressIntervalEntry 16 }

caviHighIntEgrXmtClp0Cells OBJECT-TYPE
        SYNTAX     Counter32
        MAX-ACCESS read-only
        STATUS     current
        DESCRIPTION
           "The upper 32 bits of the number of CLP-0 cells
            transmitted to the network after traffic management and
            policing during a 15 minute interval."
        ::= { caviEgressIntervalEntry 17 }

caviHighIntEgrXmtClp1Cells OBJECT-TYPE
        SYNTAX     Counter32
        MAX-ACCESS read-only
        STATUS     current
        DESCRIPTION
           "The upper 32 bits of the number of CLP-1 cells
            transmitted to the network after traffic management and
            policing during a 15 minute interval."
        ::= { caviEgressIntervalEntry 18 }

caviHIntEgrRcvClp0Cells OBJECT-TYPE
        SYNTAX     Counter64
        MAX-ACCESS read-only
        STATUS     current
        DESCRIPTION
           "The 64 bit version of the number of CLP-0 cells received
            from switch at the traffic management and policing
            device during a 15 minute interval."
        ::= { caviEgressIntervalEntry 19 }

caviHIntEgrRcvClp1Cells OBJECT-TYPE
        SYNTAX      Counter64
        MAX-ACCESS  read-only
        STATUS      current
        DESCRIPTION
           "The 64 bit version of the number of CLP-1 cells received
            from switch at the traffic management and policing
            device during a 15 minute interval."
        ::= { caviEgressIntervalEntry 20 }

caviHIntEgrClp0DiscCells OBJECT-TYPE
        SYNTAX      Counter64
        MAX-ACCESS  read-only
        STATUS      current
        DESCRIPTION
            "The 64 bit version of the number of CLP-0 cells
             discarded due to policing during a 15 minute
             interval."
        ::= { caviEgressIntervalEntry 21 }

caviHIntEgrClp1DiscCells OBJECT-TYPE
        SYNTAX     Counter64
        MAX-ACCESS read-only
        STATUS     current
        DESCRIPTION
           "The 64 bit version of the number of CLP-1 cells
            discarded due to policing during a 15 minute
            interval."
        ::= { caviEgressIntervalEntry 22 }

caviHIntEgrXmtClp0Cells OBJECT-TYPE
        SYNTAX     Counter64
        MAX-ACCESS read-only
        STATUS     current
        DESCRIPTION
           "The 64 bit version of the number of CLP-0 cells
            transmitted to the network after traffic management and
            policing during a 15 minute interval."
        ::= { caviEgressIntervalEntry 23 }

caviHIntEgrXmtClp1Cells OBJECT-TYPE
        SYNTAX     Counter64
        MAX-ACCESS read-only
        STATUS     current
        DESCRIPTION
           "The 64 bit version of the number of CLP-1 cells
            transmitted to the network after traffic management and
            policing during a 15 minute interval."
        ::= { caviEgressIntervalEntry 24 }

-- ---------------------------------------------------------------------
-- ATM Virtual Interface Ingress Statistics Table
-- ---------------------------------------------------------------------

caviStatIngressTable OBJECT-TYPE
        SYNTAX  SEQUENCE OF CaviStatIngressEntry
        MAX-ACCESS not-accessible
        STATUS     current
        DESCRIPTION
           "This table reflects real time statistics associated with
            each of the ATM virtual interfaces on the ingress side."
        ::= { caviStatistics 3 }

caviStatIngressEntry OBJECT-TYPE
        SYNTAX     CaviStatIngressEntry
        MAX-ACCESS not-accessible
        STATUS     current
        DESCRIPTION
          "An entry for egress ATM virtual  interface statistics. In all the following
           descriptions,
           CLP-0 means Cell Loss Priority = 0,
           CLP-1 means Cell Loss Priority = 1.

           Statistics are being collected before and after the traffic
           management and policing device."
        INDEX   { ifIndex }
        ::= { caviStatIngressTable 1 }

CaviStatIngressEntry ::=
        SEQUENCE {
            caviIngRcvClp0Cells      	Counter32,
            caviIngRcvClp1Cells      	Counter32,
            caviIngClp0DiscCells     	Counter32,
            caviIngClp1DiscCells     	Counter32,
            caviIngXmtClp0Cells      	Counter32,
            caviIngXmtClp1Cells      	Counter32,
            caviIngRcvOAMCells       	Counter32,
            caviIngRMCells           	Counter32,
            caviIngXmtEFCICells      	Counter32,
            caviIngRcvEFCICells      	Counter32,
            caviIngXmtOAMCells       	Counter32,
            caviHIngRcvClp0Cells     	Counter64,
            caviHIngRcvClp1Cells     	Counter64,
            caviHighIngRcvClp0Cells  	Counter32,
            caviHighIngRcvClp1Cells  	Counter32,
            caviHighIngClp0DiscCells 	Counter32,
            caviHighIngClp1DiscCells 	Counter32,
            caviHighIngXmtClp0Cells  	Counter32,
            caviHighIngXmtClp1Cells  	Counter32,
            caviHIngClp0DiscCells	Counter64,
            caviHIngClp1DiscCells   	Counter64,
            caviHIngXmtClp0Cells    	Counter64,
            caviHIngXmtClp1Cells    	Counter64
            }

caviIngRcvClp0Cells OBJECT-TYPE
        SYNTAX     Counter32
        MAX-ACCESS read-only
        STATUS     current
        DESCRIPTION
           "The number of CLP-0 cells received from network
            at the traffic management and policing device in
            ingress direction."
        ::= {caviStatIngressEntry 1 }

caviIngRcvClp1Cells OBJECT-TYPE
        SYNTAX      Counter32
        MAX-ACCESS  read-only
        STATUS      current
        DESCRIPTION
           "The number of CLP-1 cells received from network
            at the traffic management and policing device in
            ingress direction."
        ::= {caviStatIngressEntry 2 }

caviIngClp0DiscCells OBJECT-TYPE
        SYNTAX      Counter32
        MAX-ACCESS  read-only
        STATUS      current
        DESCRIPTION
            "The number of CLP-0 cells discarded due to policing in
            ingress direction."
        ::= {caviStatIngressEntry 3 }

caviIngClp1DiscCells OBJECT-TYPE
        SYNTAX     Counter32
        MAX-ACCESS read-only
        STATUS     current
        DESCRIPTION
           "The number of CLP-1 cells discarded due to policing in
            ingress direction."
        ::= {caviStatIngressEntry 4 }

caviIngXmtClp0Cells OBJECT-TYPE
        SYNTAX     Counter32
        MAX-ACCESS read-only
        STATUS     current
        DESCRIPTION
           "The number of CLP-0 cells transmitted to the switch
            after traffic management and policing in
            ingress direction."
        ::= {caviStatIngressEntry 5 }

caviIngXmtClp1Cells OBJECT-TYPE
        SYNTAX     Counter32
        MAX-ACCESS read-only
        STATUS     current
        DESCRIPTION
           "The number of CLP-1 cells transmitted to the switch
            after traffic management and policing in
            ingress direction."
        ::= {caviStatIngressEntry 6 }

caviIngRcvOAMCells OBJECT-TYPE
    SYNTAX     Counter32
    MAX-ACCESS read-only
    STATUS     current
    DESCRIPTION
       "The number of OAM cells received from the network
        at the traffic management and policing device in
        ingress direction."
    ::= {caviStatIngressEntry 7 }

caviIngRMCells OBJECT-TYPE
    SYNTAX     Counter32
    MAX-ACCESS read-only
    STATUS     current
    DESCRIPTION
       "The number of RM cells transmitted to the switch from the network in
        ingress direction."
    ::= {caviStatIngressEntry 8 }

caviIngXmtEFCICells OBJECT-TYPE
    SYNTAX     Counter32
    MAX-ACCESS read-only
    STATUS     current
    DESCRIPTION
       "The number of EFCI cells transmitted to the switch
        after traffic management and policing in
        ingress direction."
    ::= {caviStatIngressEntry 9 }

caviIngRcvEFCICells OBJECT-TYPE
    SYNTAX     Counter32
    MAX-ACCESS read-only
    STATUS     current
    DESCRIPTION
       "The number of EFCI cells received from the network
        at traffic management and policing device in
        ingress direction."
    ::= {caviStatIngressEntry 10 }

caviIngXmtOAMCells OBJECT-TYPE
        SYNTAX     Counter32
        MAX-ACCESS read-only
        STATUS     current
        DESCRIPTION
           "The number of OAM loopback cells transmitted to switch
            after traffic management and policing in
            ingress direction."
        ::= {caviStatIngressEntry 11 }

caviHIngRcvClp0Cells OBJECT-TYPE
        SYNTAX     Counter64
        MAX-ACCESS read-only
        STATUS     current
        DESCRIPTION
           "The 64-bit version of caviIngRcvClp0Cells in
            ingress direction."
        ::= {caviStatIngressEntry 12 }

caviHIngRcvClp1Cells OBJECT-TYPE
        SYNTAX     Counter64
        MAX-ACCESS read-only
        STATUS     current
        DESCRIPTION
           "The 64-bit version of caviIngRcvClp1Cells in
            ingress direction."
        ::= {caviStatIngressEntry 13 }


caviHighIngRcvClp0Cells OBJECT-TYPE
        SYNTAX     Counter32
        MAX-ACCESS read-only
        STATUS     current
        DESCRIPTION
           "The upper 32 bits of the number of CLP-0 cells received
            from network at the traffic management and policing device
            in ingress direction."
        ::= {caviStatIngressEntry 14 }

caviHighIngRcvClp1Cells OBJECT-TYPE
        SYNTAX      Counter32
        MAX-ACCESS  read-only
        STATUS      current
        DESCRIPTION
           "The upper 32 bits of the number of CLP-1 cells received
            from network at the traffic management and policing device
            in ingress direction."
        ::= {caviStatIngressEntry 15 }

caviHighIngClp0DiscCells OBJECT-TYPE
        SYNTAX      Counter32
        MAX-ACCESS  read-only
        STATUS      current
        DESCRIPTION
            "The upper 32 bits of the number of CLP-0 cells discarded
             due to policing in ingress direction."
        ::= {caviStatIngressEntry 16 }

caviHighIngClp1DiscCells OBJECT-TYPE
        SYNTAX     Counter32
        MAX-ACCESS read-only
        STATUS     current
        DESCRIPTION
           "The upper 32 bits of the number of CLP-1 cells discarded
            due to policing in ingress direction."
        ::= {caviStatIngressEntry 17 }

caviHighIngXmtClp0Cells OBJECT-TYPE
        SYNTAX     Counter32
        MAX-ACCESS read-only
        STATUS     current
        DESCRIPTION
           "The upper 32 bits of the number of CLP-0 cells transmitted
            to the switch after traffic management and policing in
            ingress direction."
        ::= {caviStatIngressEntry 18 }

caviHighIngXmtClp1Cells OBJECT-TYPE
        SYNTAX     Counter32
        MAX-ACCESS read-only
        STATUS     current
        DESCRIPTION
           "The upper 32 bits of the number of CLP-1 cells transmitted
            to the switch after traffic management and policing in
            ingress direction."
        ::= {caviStatIngressEntry 19 }

caviHIngClp0DiscCells OBJECT-TYPE
        SYNTAX      Counter64
        MAX-ACCESS  read-only
        STATUS      current
        DESCRIPTION
            "The 64 bit version of the number of CLP-0 cells discarded
             due to policing in ingress direction."
        ::= {caviStatIngressEntry 20 }

caviHIngClp1DiscCells OBJECT-TYPE
        SYNTAX     Counter64
        MAX-ACCESS read-only
        STATUS     current
        DESCRIPTION
           "The 64 bit version of the number of CLP-1 cells discarded
            due to policing in ingress direction."
        ::= {caviStatIngressEntry 21 }

caviHIngXmtClp0Cells OBJECT-TYPE
        SYNTAX     Counter64
        MAX-ACCESS read-only
        STATUS     current
        DESCRIPTION
           "The 64 bit version of the number of CLP-0 cells transmitted
            to the switch after traffic management and policing in
            ingress direction."
        ::= {caviStatIngressEntry 22 }

caviHIngXmtClp1Cells OBJECT-TYPE
        SYNTAX     Counter64
        MAX-ACCESS read-only
        STATUS     current
        DESCRIPTION
           "The 64 bit version of the number of CLP-1 cells transmitted
            to the switch after traffic management and policing in
            ingress direction."
        ::= {caviStatIngressEntry 23 }

-- ---------------------------------------------------------------------
-- ATM Virtual Interface Ingress  Interval Statistics Table
-- ---------------------------------------------------------------------

caviIngressIntervalTable OBJECT-TYPE
        SYNTAX  SEQUENCE OF CaviIngressIntervalEntry
        MAX-ACCESS not-accessible
        STATUS     current
        DESCRIPTION
           "This table reflects interval statistics associated with
            each of the ATM virtual interfaces on the ingress side."
        ::= { caviStatistics 4 }

caviIngressIntervalEntry OBJECT-TYPE
        SYNTAX     CaviIngressIntervalEntry
        MAX-ACCESS not-accessible
        STATUS     current
        DESCRIPTION
          "An entry for ingress ATM virtual interface interval
           statistics.
           In addition to the current 15-minute interval bucket,
           the previous 24 hours worth of 15-minute interval buckets
           are collected for each ATM virtual interface.

           Statistics are being collected before and after the traffic
           management and policing device, in ingress direction."
        INDEX   { ifIndex, caviIngressIntervalNumber }
        ::= { caviIngressIntervalTable 1 }

CaviIngressIntervalEntry ::=
        SEQUENCE {
            caviIngressIntervalNumber   Unsigned32,
            caviIntIngRcvClp0Cells      Counter32,
            caviIntIngRcvClp1Cells      Counter32,
            caviIntIngClp0DiscCells     Counter32,
            caviIntIngClp1DiscCells     Counter32,
            caviIntIngXmtClp0Cells      Counter32,
            caviIntIngXmtClp1Cells      Counter32,
            caviIntIngRcvOAMCells       Counter32,
            caviIntIngRMCells           Counter32,
            caviIntIngXmtEFCICells      Counter32,
            caviIntIngRcvEFCICells      Counter32,
            caviIntIngXmtOAMCells       Counter32,
            caviHighIntIngRcvClp0Cells  Counter32,
            caviHighIntIngRcvClp1Cells  Counter32,
            caviHighIntIngClp0DiscCells Counter32,
            caviHighIntIngClp1DiscCells Counter32,
            caviHighIntIngXmtClp0Cells  Counter32,
            caviHighIntIngXmtClp1Cells  Counter32,
            caviHIntIngRcvClp0Cells     Counter64,
            caviHIntIngRcvClp1Cells     Counter64,
            caviHIntIngClp0DiscCells	Counter64,
            caviHIntIngClp1DiscCells   	Counter64,
            caviHIntIngXmtClp0Cells    	Counter64,
            caviHIntIngXmtClp1Cells    	Counter64
            }

caviIngressIntervalNumber OBJECT-TYPE
        SYNTAX  Unsigned32(0..96)
        MAX-ACCESS  not-accessible
        STATUS  current
        DESCRIPTION
          "A number used to uniquely identify a ATM virtual interface's
           interval statistics. 0 is used to identify the current
           15-minute interval, which is  currently being updated.
           1-96 identify the previous 24 hours of 15-minute interval
           buckets, where interval 1 representing the most recent
           15-minute interval and interval  96 representing the least
           recent 15-minute interval"
        ::= { caviIngressIntervalEntry 1 }

caviIntIngRcvClp0Cells OBJECT-TYPE
        SYNTAX     Counter32
        MAX-ACCESS read-only
        STATUS     current
        DESCRIPTION
           "The number of CLP-0 cells received from network
            at the traffic management and policing device in
            ingress direction, during a 15-minute interval."
        ::= {caviIngressIntervalEntry 2 }

caviIntIngRcvClp1Cells OBJECT-TYPE
        SYNTAX      Counter32
        MAX-ACCESS  read-only
        STATUS      current
        DESCRIPTION
           "The number of CLP-1 cells received from network
            at the traffic management and policing device in
            ingress direction, during a 15-minute interval."
        ::= {caviIngressIntervalEntry 3 }

caviIntIngClp0DiscCells OBJECT-TYPE
        SYNTAX      Counter32
        MAX-ACCESS  read-only
        STATUS      current
        DESCRIPTION
            "The number of CLP-0 cells discarded due to policing in
            ingress direction, during a 15-minute interval."
        ::= {caviIngressIntervalEntry 4 }

caviIntIngClp1DiscCells OBJECT-TYPE
        SYNTAX     Counter32
        MAX-ACCESS read-only
        STATUS     current
        DESCRIPTION
           "The number of CLP-1 cells discarded due to policing in
            ingress direction, during a 15-minute interval ."
        ::= {caviIngressIntervalEntry 5 }

caviIntIngXmtClp0Cells OBJECT-TYPE
        SYNTAX     Counter32
        MAX-ACCESS read-only
        STATUS     current
        DESCRIPTION
           "The number of CLP-0 cells transmitted to the switch
            after traffic management and policing in
            ingress direction, during a 15-minute interval."
        ::= {caviIngressIntervalEntry 6 }

caviIntIngXmtClp1Cells OBJECT-TYPE
        SYNTAX     Counter32
        MAX-ACCESS read-only
        STATUS     current
        DESCRIPTION
           "The number of CLP-1 cells transmitted to the switch
            after traffic management and policing in
            ingress direction, during a 15-minute interval."
        ::= {caviIngressIntervalEntry 7 }

caviIntIngRcvOAMCells OBJECT-TYPE
    SYNTAX     Counter32
    MAX-ACCESS read-only
    STATUS     current
    DESCRIPTION
       "The number of OAM cells received from the network
        at the traffic management and policing device in
        ingress direction, during a 15-minute interval."
    ::= {caviIngressIntervalEntry 8 }

caviIntIngRMCells OBJECT-TYPE
    SYNTAX     Counter32
    MAX-ACCESS read-only
    STATUS     current
    DESCRIPTION
       "The number of RM cells transmitted to the switch from the
        network in ingress direction, during a 15-minute interval."
    ::= {caviIngressIntervalEntry 9 }

caviIntIngXmtEFCICells OBJECT-TYPE
    SYNTAX     Counter32
    MAX-ACCESS read-only
    STATUS     current
    DESCRIPTION
       "The number of EFCI cells transmitted to the switch
        after traffic management and policing in
        ingress direction, during a 15-minute interval."
    ::= {caviIngressIntervalEntry 10 }

caviIntIngRcvEFCICells OBJECT-TYPE
    SYNTAX     Counter32
    MAX-ACCESS read-only
    STATUS     current
    DESCRIPTION
       "The number of EFCI cells received from the network
        at traffic management and policing device in
        ingress direction, during a 15-minute interval."
    ::= {caviIngressIntervalEntry 11 }

caviIntIngXmtOAMCells OBJECT-TYPE
        SYNTAX     Counter32
        MAX-ACCESS read-only
        STATUS     current
        DESCRIPTION
           "The number of OAM loopback cells transmitted to switch
            after traffic management and policing in
            ingress direction, during a 15-minute interval."
        ::= {caviIngressIntervalEntry 12 }

caviHighIntIngRcvClp0Cells OBJECT-TYPE
        SYNTAX     Counter32
        MAX-ACCESS read-only
        STATUS     current
        DESCRIPTION
           "The upper 32 bits of the number of CLP-0 cells received
            from network at the traffic management and policing device
            in ingress direction, during a 15-minute interval."
        ::= {caviIngressIntervalEntry 13 }

caviHighIntIngRcvClp1Cells OBJECT-TYPE
        SYNTAX      Counter32
        MAX-ACCESS  read-only
        STATUS      current
        DESCRIPTION
           "The upper 32 bits of the number of CLP-1 cells received
            from network at the traffic management and policing device
            in ingress direction, during a 15-minute interval."
        ::= {caviIngressIntervalEntry 14 }

caviHighIntIngClp0DiscCells OBJECT-TYPE
        SYNTAX      Counter32
        MAX-ACCESS  read-only
        STATUS      current
        DESCRIPTION
            "The upper 32 bits of the number of CLP-0 cells discarded
             due to policing in ingress direction, during a 15-minute
             interval."
        ::= {caviIngressIntervalEntry 15 }

caviHighIntIngClp1DiscCells OBJECT-TYPE
        SYNTAX     Counter32
        MAX-ACCESS read-only
        STATUS     current
        DESCRIPTION
           "The upper 32 bits of the number of CLP-1 cells discarded
            due to policing in ingress direction, during a 15-minute
            interval."
        ::= {caviIngressIntervalEntry 16 }

caviHighIntIngXmtClp0Cells OBJECT-TYPE
        SYNTAX     Counter32
        MAX-ACCESS read-only
        STATUS     current
        DESCRIPTION
           "The upper 32 bits of the number of CLP-0 cells transmitted
            to the switch after traffic management and policing in
            ingress direction, during a 15-minute interval."
        ::= {caviIngressIntervalEntry 17 }

caviHighIntIngXmtClp1Cells OBJECT-TYPE
        SYNTAX     Counter32
        MAX-ACCESS read-only
        STATUS     current
        DESCRIPTION
           "The upper 32 bits of the number of CLP-1 cells transmitted
            to the switch after traffic management and policing in
            ingress direction, during a 15-minute interval."
        ::= {caviIngressIntervalEntry 18 }

caviHIntIngRcvClp0Cells OBJECT-TYPE
        SYNTAX     Counter64
        MAX-ACCESS read-only
        STATUS     current
        DESCRIPTION
           "The 64-bit version of the number of CLP-0 cells received
            from network at the traffic management and policing device
            in ingress direction, during a 15-minute interval."
        ::= {caviIngressIntervalEntry 19 }

caviHIntIngRcvClp1Cells OBJECT-TYPE
        SYNTAX     Counter64
        MAX-ACCESS read-only
        STATUS     current
        DESCRIPTION
           "The 64-bit version of the number of CLP-1 cells received
            from network at the traffic management and policing device
            in ingress direction, during a 15-minute interval."
        ::= {caviIngressIntervalEntry 20 }

caviHIntIngClp0DiscCells OBJECT-TYPE
        SYNTAX      Counter64
        MAX-ACCESS  read-only
        STATUS      current
        DESCRIPTION
            "The 64 bit version of the number of CLP-0 cells discarded
             due to policing in ingress direction, during a 15-minute
             interval."
        ::= {caviIngressIntervalEntry 21 }

caviHIntIngClp1DiscCells OBJECT-TYPE
        SYNTAX     Counter64
        MAX-ACCESS read-only
        STATUS     current
        DESCRIPTION
           "The 64 bit version of the number of CLP-1 cells discarded
            due to policing in ingress direction, during a 15-minute
            interval."
        ::= {caviIngressIntervalEntry 22 }

caviHIntIngXmtClp0Cells OBJECT-TYPE
        SYNTAX     Counter64
        MAX-ACCESS read-only
        STATUS     current
        DESCRIPTION
           "The 64 bit version of the number of CLP-0 cells transmitted
            to the switch after traffic management and policing in
            ingress direction, during a 15-minute interval."
        ::= {caviIngressIntervalEntry 23 }

caviHIntIngXmtClp1Cells OBJECT-TYPE
        SYNTAX     Counter64
        MAX-ACCESS read-only
        STATUS     current
        DESCRIPTION
           "The 64 bit version of the number of CLP-1 cells transmitted
            to the switch after traffic management and policing in
            ingress direction, during a 15-minute interval."
        ::= {caviIngressIntervalEntry 24 }

-- conformance information

caviMIBConformance OBJECT IDENTIFIER ::= {ciscoAtmVirtualIfMIB 3}

caviMIBCompliances OBJECT IDENTIFIER ::= {caviMIBConformance 1}
caviMIBGroups      OBJECT IDENTIFIER ::= {caviMIBConformance 2}

caviMIBCompliance MODULE-COMPLIANCE
        STATUS    deprecated   -- replaced by caviMIBComplianceRev1
        DESCRIPTION
           "The Compliance statement for cisco AtmVirtualIf management group."
        MODULE -- this module
        MANDATORY-GROUPS { caviMIBGroup, caviEgressStatMIBGroup }
        GROUP caviEgressHighSpeedStatMIBGroup
        DESCRIPTION
            "This group is mandatory for the system that has interface speeds of OC12 or
             higher."
        GROUP caviEgressIntervalMIBGroup
        DESCRIPTION
            "This group is mandatory for the system that supports ATM virtual interface
             interval statistics."
        GROUP caviIngressStatMIBGroup
        DESCRIPTION
            "This group is mandatory for the system that supports ATM  virtual interface
             Ingress statistics."
        GROUP caviIngressHighSpeedStatMIBGroup
        DESCRIPTION
            "This group is mandatory for the system that supports ATM  virtual interface
             Ingress statistics for interface speeds of OC12 or higher."
        ::= {caviMIBCompliances 1}

caviMIBComplianceRev1 MODULE-COMPLIANCE
        STATUS        deprecated -- replaced by caviMIBComplianceRev2
        DESCRIPTION
           "Compliance statement for cisco AtmVirtualIf management group
            with support for virtual user and network ports"
        MODULE        -- this module
        MANDATORY-GROUPS { caviMIBGroupRev1, caviEgressStatMIBGroup }
        GROUP caviEgressHighSpeedStatMIBGroup
        DESCRIPTION
            "This group is mandatory for the system that has interface speeds
             of OC12 or higher."
        GROUP caviEgressIntervalMIBGroup
        DESCRIPTION
            "This group is mandatory for the system that supports ATM virtual
             interface interval statistics."
        GROUP caviIngressStatMIBGroup
        DESCRIPTION
            "This group is mandatory for the system that supports ATM  virtual
             interface Ingress statistics."
        GROUP caviIngressHighSpeedStatMIBGroup
        DESCRIPTION
            "This group is mandatory for the system that supports ATM  virtual
             interface Ingress statistics for interface speeds of OC12 or
             higher."
        ::= {caviMIBCompliances 2}

caviMIBComplianceRev2 MODULE-COMPLIANCE
        STATUS        deprecated -- replaced by caviMIBComplianceRev3
        DESCRIPTION
           "Compliance statement for cisco AtmVirtualIf management
            group with support for virtual user and network ports"
        MODULE        -- this module
        MANDATORY-GROUPS { caviMIBGroupRev1, caviEgressStatMIBGroup1 }
        GROUP caviEgressHighSpeedStatMIBGroup1
        DESCRIPTION
            "This group is mandatory for the system that has
             interface speeds of OC12 or higher."
        GROUP caviEgressIntervalMIBGroup1
        DESCRIPTION
            "This group is mandatory for the system that supports
             ATM virtual interface interval statistics."
        GROUP caviIngressStatMIBGroup1
        DESCRIPTION
            "This group is mandatory for the system that supports
             ATM  virtual interface Ingress statistics."
        GROUP caviIngHighSpeedStatMIBGroup1
        DESCRIPTION
            "This group is mandatory for the system that supports
             ATM  virtual interface Ingress statistics for interface
             speeds of OC12 or higher."
        ::= {caviMIBCompliances 3}

caviMIBComplianceRev3 MODULE-COMPLIANCE
        STATUS        current
        DESCRIPTION
           "Compliance statement for cisco AtmVirtualIf management
            group with support for virtual user and network ports"
        MODULE        -- this module
        MANDATORY-GROUPS { caviMIBGroupRev1, caviEgressStatMIBGroup1 }
        GROUP caviEgressHighSpeedStatMIBGroup1
        DESCRIPTION
            "This group is mandatory for the system that has
             interface speeds of OC12 or higher."
        GROUP caviEgressIntervalMIBGroup1
        DESCRIPTION
            "This group is mandatory for the system that supports
             ATM virtual interface interval statistics."
        GROUP caviIngressStatMIBGroup1
        DESCRIPTION
            "This group is mandatory for the system that supports
             ATM  virtual interface Ingress statistics."
        GROUP caviIngHighSpeedStatMIBGroup2
        DESCRIPTION
            "This group is mandatory for the system that supports
             ATM  virtual interface Ingress statistics for interface
             speeds of OC12 or higher."
	GROUP caviIngressIntervalStatMIBGroup
	DESCRIPTION
            "This group is mandatory for the system that supports
             ATM  virtual interface Ingress statistics."
        ::= {caviMIBCompliances 4}

-- units of conformance
caviMIBGroup OBJECT-GROUP
       OBJECTS {
        caviPhyIfIndex,
        caviViIfIndex,
        caviMinRate,
        caviMaxRate,
        caviFileId,
        caviIfType,
        caviVpiNum,
        caviRowStatus
       }
       STATUS    deprecated   -- replaced by caviMIBGroupRev1
       DESCRIPTION
          "These are objects related to ciscoAtmVirtualIf configuration group."
       ::= { caviMIBGroups 1}

caviEgressStatMIBGroup OBJECT-GROUP
        OBJECTS {
        caviEgrRcvClp0Cells,
        caviEgrRcvClp1Cells,
        caviEgrClp0DiscCells,
        caviEgrClp1DiscCells,
        caviEgrXmtClp0Cells,
        caviEgrXmtClp1Cells,
        caviEgrRcvOAMCells,
        caviEgrRMCells,
        caviEgrXmtEFCICells,
        caviEgrRcvEFCICells,
        caviEgrXmtOAMCells
        }
       STATUS deprecated -- replaced by caviEgressStatMIBGroup1
       DESCRIPTION
          "These are objects related to the ATM virtual interface statistics
           group caviStatistics."
       ::= { caviMIBGroups 2}

caviEgressHighSpeedStatMIBGroup OBJECT-GROUP
        OBJECTS {
        caviHEgrXmtClp0Cells,
        caviHEgrXmtClp1Cells
        }
       STATUS deprecated -- replaced by
                         -- caviEgressHighSpeedStatMIBGroup1
       DESCRIPTION
          "These statistics apply to ingress ATM virtual interfaces with speed of
           OC12 or higher."
       ::= { caviMIBGroups 3}

caviEgressIntervalMIBGroup OBJECT-GROUP
        OBJECTS {
        caviEgressIntervalNumber,
        caviIntEgrRcvClp0Cells,
        caviIntEgrRcvClp1Cells,
        caviIntEgrClp0DiscCells,
        caviIntEgrClp1DiscCells,
        caviIntEgrXmtClp0Cells,
        caviIntEgrXmtClp1Cells,
        caviIntEgrRcvOAMCells,
        caviIntEgrRMCells,
        caviIntEgrXmtEFCICells,
        caviIntEgrRcvEFCICells,
        caviIntEgrXmtOAMCells
        }
        STATUS deprecated -- relaced by caviEgressIntervalMIBGroup1
        DESCRIPTION
           "These are objects related to the ATM virtual interface
            interval statistics group."
        ::= { caviMIBGroups 4}

caviIngressStatMIBGroup OBJECT-GROUP
        OBJECTS {
        caviIngRcvClp0Cells,
        caviIngRcvClp1Cells,
        caviIngClp0DiscCells,
        caviIngClp1DiscCells,
        caviIngXmtClp0Cells,
        caviIngXmtClp1Cells,
        caviIngRcvOAMCells,
        caviIngRMCells,
        caviIngXmtEFCICells,
        caviIngRcvEFCICells,
        caviIngXmtOAMCells
        }
       STATUS deprecated  -- replaced by caviIngressStatMIBGroup1
       DESCRIPTION
          "These are objects related to the ingress ATM virtual
           interface statistics."
       ::= { caviMIBGroups 5}

caviIngressHighSpeedStatMIBGroup OBJECT-GROUP
        OBJECTS {
        caviHIngRcvClp0Cells,
        caviHIngRcvClp1Cells
        }
       STATUS deprecated  -- replaced by caviIngHighSpeedStatMIBGroup1
       DESCRIPTION
          "These statistics apply to ingress ATM virtual interfaces with speed of
           OC12 or higher."
       ::= { caviMIBGroups 6}

caviMIBGroupRev1 OBJECT-GROUP
       OBJECTS {
        caviPhyIfIndex,
        caviViIfIndex,
        caviMinRate,
        caviMaxRate,
        caviFileId,
        caviIfType,
        caviVpiNum,
        caviRowStatus,
        caviMinVpiNum,
        caviMaxVpiNum
       }
       STATUS current
       DESCRIPTION
          "Definition of additional objects caviMinVpiNum and caviMaxVpiNum,
           which are required to support the evuni and evnni functionality."
       ::= { caviMIBGroups 7}

caviEgressStatMIBGroup1 OBJECT-GROUP
        OBJECTS {
        caviEgrRcvClp0Cells,
        caviEgrRcvClp1Cells,
        caviEgrClp0DiscCells,
        caviEgrClp1DiscCells,
        caviEgrXmtClp0Cells,
        caviEgrXmtClp1Cells,
        caviEgrRcvOAMCells,
        caviEgrRMCells,
        caviEgrXmtEFCICells,
        caviEgrRcvEFCICells,
        caviEgrXmtOAMCells,
        caviHighEgrRcvClp0Cells,
        caviHighEgrRcvClp1Cells,
        caviHighEgrClp0DiscCells,
        caviHighEgrClp1DiscCells,
        caviHighEgrXmtClp0Cells,
        caviHighEgrXmtClp1Cells
        }
       STATUS current
       DESCRIPTION
          "These are objects related to the ATM virtual interface
           statistics group caviStatistics."
       ::= { caviMIBGroups 8}

caviEgressHighSpeedStatMIBGroup1 OBJECT-GROUP
        OBJECTS {
        caviHEgrXmtClp0Cells,
        caviHEgrXmtClp1Cells,
	caviHEgrRcvClp0Cells,
        caviHEgrRcvClp1Cells,
	caviHEgrClp0DiscCells,
        caviHEgrClp1DiscCells,
	caviHIntEgrRcvClp0Cells,
        caviHIntEgrRcvClp1Cells,
        caviHIntEgrClp0DiscCells,
        caviHIntEgrClp1DiscCells,
        caviHIntEgrXmtClp0Cells,
        caviHIntEgrXmtClp1Cells
        }
       STATUS current
       DESCRIPTION
          "These statistics apply to ingress ATM virtual interfaces
           with speed of OC12 or higher."
       ::= { caviMIBGroups 9}

caviEgressIntervalMIBGroup1 OBJECT-GROUP
        OBJECTS {
        caviEgressIntervalNumber,
        caviIntEgrRcvClp0Cells,
        caviIntEgrRcvClp1Cells,
        caviIntEgrClp0DiscCells,
        caviIntEgrClp1DiscCells,
        caviIntEgrXmtClp0Cells,
        caviIntEgrXmtClp1Cells,
        caviIntEgrRcvOAMCells,
        caviIntEgrRMCells,
        caviIntEgrXmtEFCICells,
        caviIntEgrRcvEFCICells,
        caviIntEgrXmtOAMCells,
        caviHighIntEgrRcvClp0Cells,
        caviHighIntEgrRcvClp1Cells,
        caviHighIntEgrClp0DiscCells,
        caviHighIntEgrClp1DiscCells,
        caviHighIntEgrXmtClp0Cells,
        caviHighIntEgrXmtClp1Cells
        }
        STATUS current
        DESCRIPTION
           "These are objects related to the ATM virtual interface
            interval statistics group."
        ::= { caviMIBGroups 10}


caviIngressStatMIBGroup1 OBJECT-GROUP
        OBJECTS {
        caviIngRcvClp0Cells,
        caviIngRcvClp1Cells,
        caviIngClp0DiscCells,
        caviIngClp1DiscCells,
        caviIngXmtClp0Cells,
        caviIngXmtClp1Cells,
        caviIngRcvOAMCells,
        caviIngRMCells,
        caviIngXmtEFCICells,
        caviIngRcvEFCICells,
        caviIngXmtOAMCells,
        caviHighIngRcvClp0Cells,
        caviHighIngRcvClp1Cells,
        caviHighIngClp0DiscCells,
        caviHighIngClp1DiscCells,
        caviHighIngXmtClp0Cells,
        caviHighIngXmtClp1Cells
        }
       STATUS current
       DESCRIPTION
          "These are objects related to the ingress ATM virtual
           interface statistics."
       ::= { caviMIBGroups 11}

caviIngHighSpeedStatMIBGroup1 OBJECT-GROUP
        OBJECTS {
        caviHIngRcvClp0Cells,
        caviHIngRcvClp1Cells,
        caviHIngClp0DiscCells,
        caviHIngClp1DiscCells,
        caviHIngXmtClp0Cells,
        caviHIngXmtClp1Cells
        }
       STATUS deprecated -- replaced by caviIngHighSpeedStatMIBGroup2
       DESCRIPTION
          "These statistics apply to ingress ATM virtual interfaces
           with speed of OC12 or higher."
       ::= { caviMIBGroups 12}

caviIngressIntervalStatMIBGroup OBJECT-GROUP
        OBJECTS {
        caviIntIngRcvClp0Cells,
        caviIntIngRcvClp1Cells,
        caviIntIngClp0DiscCells,
        caviIntIngClp1DiscCells,
        caviIntIngXmtClp0Cells,
        caviIntIngXmtClp1Cells,
        caviIntIngRcvOAMCells,
        caviIntIngRMCells,
        caviIntIngXmtEFCICells,
        caviIntIngRcvEFCICells,
        caviIntIngXmtOAMCells
        }
       STATUS current
       DESCRIPTION
          "These are objects related to the ingress ATM virtual
           interface statistics."
       ::= { caviMIBGroups 13}

caviIngHighSpeedStatMIBGroup2 OBJECT-GROUP
        OBJECTS {
        caviHighIntIngRcvClp0Cells,
        caviHighIntIngRcvClp1Cells,
        caviHighIntIngClp0DiscCells,
        caviHighIntIngClp1DiscCells,
        caviHighIntIngXmtClp0Cells,
        caviHighIntIngXmtClp1Cells,
        caviHIngRcvClp0Cells,
        caviHIngRcvClp1Cells,
        caviHIngClp0DiscCells,
        caviHIngClp1DiscCells,
        caviHIngXmtClp0Cells,
        caviHIngXmtClp1Cells,
	caviHIntIngRcvClp0Cells,
        caviHIntIngRcvClp1Cells,
        caviHIntIngClp0DiscCells,
        caviHIntIngClp1DiscCells,
        caviHIntIngXmtClp0Cells,
        caviHIntIngXmtClp1Cells
        }
       STATUS current
       DESCRIPTION
          "These statistics apply to ingress ATM virtual interfaces
           with speed of OC12 or higher."
       ::= { caviMIBGroups 14}
END
