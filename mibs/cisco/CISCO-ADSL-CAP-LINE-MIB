-- *****************************************************************
-- Description of managed objects for ADSL CAP line interfaces.
--
-- October 1999 Patrick Gili
--
-- Copyright (c) 1999, 2000, 2001 by cisco Systems, Inc.
-- All rights reserved.
-- *****************************************************************

CISCO-ADSL-CAP-LINE-MIB DEFINITIONS ::= BEGIN

IMPORTS
    Counter32,
    Gauge32,
    Integer32,
    MODULE-IDENTITY,
    OBJECT-TYPE                         FROM SNMPv2-SMI
    TEXTUAL-CONVENTION,
    TruthValue                          FROM SNMPv2-TC
    MODULE-COMPLIANCE,
    OBJECT-GROUP                        FROM SNMPv2-CONF
    ciscoMgmt                           FROM CISCO-SMI
    AdslPerfCurrDayCount,
    AdslPerfPrevDayCount                FROM ADSL-TC-MIB
    adslAtucIntervalNumber,
    adslLineConfProfileName             FROM ADSL-LINE-MIB
    ifIndex                             FROM IF-MIB
    PerfCurrentCount,
    PerfIntervalCount                   FROM PerfHist-TC-MIB
;

ciscoAdslLineCapMIB MODULE-IDENTITY
    LAST-UPDATED   "200103010000Z"
    ORGANIZATION   "Cisco Systems, Inc."
    CONTACT-INFO   "Cisco Systems
                    Customer Service

                    Postal: 170 W Tasman Drive
                    San Jose, CA 95134

                    Tel: +1 800 553-NETS

                    E-mail: cs-dslam.com"
    DESCRIPTION
        "This MIB module serves as an enterprise-specific extension of
        the ADSL-LINE-MIB.  The structure of this MIB module shadows
        the structure of the ADSL-LINE-MIB, table for table.  The tables
        defined by this MIB module contain managed objects that meet the
        following criteria:

        1)  A managed object represents an attribute or characteristic
            specific to CAP (Carrierless AM/PM) modems.

        2)  The ADSL-CAP-LINE-MIB does not already contain a managed
            object representing the same information as this managed
            object.

        Observe that entries contained by the tables in this MIB module
        do not augment the corresponding entries in the ADSL-LINE-MIB,
        as every modem represented by the ADSL-LINE-MIB is not
        necessarily a CAP modem.

        Also observe that entries contained by the tables in this MIB
        module do not augment the corresponding entries in the
        ADSL-CAP-LINE-MIB, as this assumes that the ADSL-CAP-LINE-MIB
        defines tables that correspond to every table defined by the
        ADSL-LINE-MIB.  At this time, this assumption does not hold
        true.

        *** ABBREVIATIONS, ACRONYMS, AND SYMBOLS ***

        ADSL - Asymmetric Digital Subscriber Line.

        ATM - Asynchronous Transfer Mode.

        ATU-C - ADSL Transceiver Unit, Central Office end.

        ATU-R - ADSL Transceiver Unit, Remote terminal end.

        BER - Bit Error Ratio.

        CAP - Carrierless Amplitude Modulation / Pulse Modulation.

        DSL - Digital Subscriber Line.

        SNR - Signal-to-Noise Ratio.

        STM - Synchronous Transfer Mode.

        *** DEFINITIONS ***

        DOWNSTREAM
            The flow of data in the direction from the ATU-C to ATU-R.

        MARGIN (also referred to as 'SNR margin')
            The difference between the SNR of the received signal and
            the SNR required to provide a BER of 10E-7.

        SYMBOL
            The number of bits the transmitter is capable of
            multiplexing and modulating in a single signalling interval.

        SYMBOL RATE
            The rate at which all symbols are transmitted.

        UPSTREAM
            The flow of data in the direction from the ATU-R to ATU-C."

    REVISION       "200103010000Z"
    DESCRIPTION
            "Changed MAX-ACCESS for cAdslAtucCapConfUp17KBaudEnable to
             read-create due to the the bug fix of MAX-ACCESS in the
             broken MIB object."

    ::= { ciscoMgmt 149 }

-- Textual Conventions

AdslLineCapDownstreamRate ::= TEXTUAL-CONVENTION
    STATUS current
    DESCRIPTION
        "The downstream line rate at which an ADSL line can train at,
        given an ATU-C and ATU-R implementing the CAP line code."
    SYNTAX      INTEGER ( 7168000 |
                          6272000 |
                          5120000 |
                          4480000 |
                          3200000 |
                          2688000 |
                          2560000 |
                          2240000 |
                          1920000 |
                          1600000 |
                          1280000 |
                          1024000 |
                           960000 |
                           896000 |
                           768000 |
                           640000 |
                           512000 |
                           384000 |
                           256000 |
                                0 )

AdslLineCapUpstreamRate ::= TEXTUAL-CONVENTION
    STATUS current
    DESCRIPTION
        "The upstream line rate at which an ADSL line can train at,
        given an ATU-C and ATU-R implementing the CAP line code."
        SYNTAX      INTEGER ( 1088000 |
                               952000 |
                               816000 |
                               680000 |
                               544000 |
                               408000 |
                               272000 |
                                91000 |
                                    0 )

-- MIB Objects Definitions

ciscoAdslLineCapMIBObjects OBJECT IDENTIFIER
    ::= { ciscoAdslLineCapMIB 1 }

-- ADSL ATU-C CAP Physical-Layer Parameters Table

cAdslAtucCapPhysTable OBJECT-TYPE
    SYNTAX      SEQUENCE OF CAdslAtucCapPhysEntry
    MAX-ACCESS  not-accessible
    STATUS      current
    DESCRIPTION
        "This table extends the adslAtucPhysTable and contains
        enterprise-specific physical layer parameters for the ATU-C
        class devices supported by the system."
    ::= { ciscoAdslLineCapMIBObjects 2 }

cAdslAtucCapPhysEntry OBJECT-TYPE
    SYNTAX      CAdslAtucCapPhysEntry
    MAX-ACCESS  not-accessible
    STATUS      current
    DESCRIPTION
        "A set of enterprise-specific physical-layer parameters for an
        ATU-C class device supported by the system.  There exists an
        entry for each ifEntry with an ifType of adsl(94) and an
        adslLineCoding of cap(3)."
    INDEX       { ifIndex }
    ::= { cAdslAtucCapPhysTable 1 }

CAdslAtucCapPhysEntry ::= SEQUENCE {
    cAdslAtucCapCurrState  INTEGER,
    cAdslAtucCapCurrRxGain Gauge32,
    cAdslAtucCapCurrRxSnr  Gauge32
}

cAdslAtucCapCurrState OBJECT-TYPE
    SYNTAX      INTEGER {
        other(1),
        idle(2),            -- Administratively down.
        training(3),        -- Transceiver training in progress.
        steadyState(4),     -- Nominal mode of operation.
        downloading(5),     -- ATU-C code download in progress.
        downloadFailed(6),  -- ATU-C code download failed.
        testing(7)          -- Test in progress.
        }
    MAX-ACCESS  read-only
    STATUS      current
    DESCRIPTION
        "This object specifies the state of the ATU-C transceiver.

        The value of this managed is 'idle' for an ATU-C that has
        been provisioned, but is not physically present in the system."
    ::= { cAdslAtucCapPhysEntry 1 }

cAdslAtucCapCurrRxGain OBJECT-TYPE
    SYNTAX      Gauge32
    UNITS       "tenth dB"
    MAX-ACCESS  read-only
    STATUS      current
    DESCRIPTION
        "This managed object represents the gain applied to the ATU-C
        receiver.

        The value of this managed object is '0' for an ATU-C that has
        been provisioned, but is not physically present in the system."
    ::= { cAdslAtucCapPhysEntry 2 }

cAdslAtucCapCurrRxSnr OBJECT-TYPE
    SYNTAX      Gauge32
    UNITS       "tenth dB"
    MAX-ACCESS  read-only
    STATUS      current
    DESCRIPTION
        "This managed object represents the signal-to-noise ratio
        measured across the the ATU-C receive pair.

        The value of this managed object is '0' for an ATU-C that has
        been provisioned, but is not physically present in the system."
    ::= { cAdslAtucCapPhysEntry 3 }

-- ADSL ATU-R CAP Physical-Layer Parameters Table

cAdslAturCapPhysTable OBJECT-TYPE
    SYNTAX      SEQUENCE OF CAdslAturCapPhysEntry
    MAX-ACCESS  not-accessible
    STATUS      current
    DESCRIPTION
        "This table extends the adslAturPhysTable and contains
        enterprise-specific physical layer parameters for the ATU-R
        class devices supported by the system."
    ::= { ciscoAdslLineCapMIBObjects 3 }

cAdslAturCapPhysEntry OBJECT-TYPE
    SYNTAX      CAdslAturCapPhysEntry
    MAX-ACCESS  not-accessible
    STATUS      current
    DESCRIPTION
        "A set of enterprise-specific physical-layer parameters for an
        ATU-R class device supported by the system.  There exists an
        entry for each ifEntry with an ifType of adsl(94) and an
        adslLineCoding of cap(3)."
    INDEX       { ifIndex }
    ::= { cAdslAturCapPhysTable 1 }

CAdslAturCapPhysEntry ::= SEQUENCE {
    cAdslAturCapCurrRxGain          Gauge32
}

cAdslAturCapCurrRxGain OBJECT-TYPE
    SYNTAX      Gauge32
    UNITS       "tenth dB"
    MAX-ACCESS  read-only
    STATUS      current
    DESCRIPTION
        "This managed object represents the gain applied to the ATU-R
        receiver.

        The value of this managed object is '0' if the corresponding
        ATU-C has been provisioned, but is not physically present in
        the system."
    ::= { cAdslAturCapPhysEntry 1 }

-- ADSL ATU-C CAP Physical-Layer Statistics Table

cAdslAtucCapPerfDataTable OBJECT-TYPE
    SYNTAX      SEQUENCE OF CAdslAtucCapPerfDataEntry
    MAX-ACCESS  not-accessible
    STATUS      current
    DESCRIPTION
        "This table extends the adslAtucPerfDataTable and contains
        enterprise-specific physical layer statistics for the ATU-C
        class devices supported by the system."
    ::= { ciscoAdslLineCapMIBObjects 6 }

cAdslAtucCapPerfDataEntry OBJECT-TYPE
    SYNTAX      CAdslAtucCapPerfDataEntry
    MAX-ACCESS  not-accessible
    STATUS      current
    DESCRIPTION
        "A set of enterprise-specific physical-layer statistics for an
        ATU-C class device supported by the system.  There exists an
        entry for each ifEntry with an ifType of adsl(94) and an
        adslLineCoding of cap(3)."
    INDEX       { ifIndex }
    ::= { cAdslAtucCapPerfDataTable 1 }

CAdslAtucCapPerfDataEntry ::= SEQUENCE {
    cAdslAtucCapPerfInitFailures          Counter32,
    cAdslAtucCapPerfCurr15MinInitFailures PerfCurrentCount,
    cAdslAtucCapPerfCurr1DayInitFailures  AdslPerfCurrDayCount,
    cAdslAtucCapPerfPrev1DayInitFailures  AdslPerfPrevDayCount
}

cAdslAtucCapPerfInitFailures OBJECT-TYPE
    SYNTAX      Counter32
    MAX-ACCESS  read-only
    STATUS      current
    DESCRIPTION
        "This object specifies the number of line initialization
        failures relative to sysUpTime."
    ::= { cAdslAtucCapPerfDataEntry 1 }

cAdslAtucCapPerfCurr15MinInitFailures OBJECT-TYPE
    SYNTAX      PerfCurrentCount
    MAX-ACCESS  read-only
    STATUS      current
    DESCRIPTION
        "This object specifies the number of line initialization
        failures in the current 15-minute interval."
    ::= { cAdslAtucCapPerfDataEntry 2 }

cAdslAtucCapPerfCurr1DayInitFailures OBJECT-TYPE
    SYNTAX      AdslPerfCurrDayCount
    MAX-ACCESS  read-only
    STATUS      current
    DESCRIPTION
        "This object specifies the number of line initialization
        failures in the current 1-day interval."
    ::= { cAdslAtucCapPerfDataEntry 3 }

cAdslAtucCapPerfPrev1DayInitFailures OBJECT-TYPE
    SYNTAX      AdslPerfPrevDayCount
    MAX-ACCESS  read-only
    STATUS      current
    DESCRIPTION
        "This object specifies the number of line initialization
        failures in the previous 1-day interval."
    ::= { cAdslAtucCapPerfDataEntry 4 }

-- ADSL ATU-C CAP Physical-Layer Statistics 15-Minute Interval Table

cAdslAtucCapIntervalTable OBJECT-TYPE
    SYNTAX      SEQUENCE OF CAdslAtucCapIntervalEntry
    MAX-ACCESS  not-accessible
    STATUS      current
    DESCRIPTION
        "This table extends the adslAtucIntervalTable and contains
        enterprise-specific physical layer statistics intervals for
        the ATU-C class devices supported by the system."
    ::= { ciscoAdslLineCapMIBObjects 8 }

cAdslAtucCapIntervalEntry OBJECT-TYPE
    SYNTAX      CAdslAtucCapIntervalEntry
    MAX-ACCESS  not-accessible
    STATUS      current
    DESCRIPTION
        "A 15-minute interval of enterprise-specific physical-layer
        statistics for an ATU-C class device supported by the system.
        There exists up to 96 entries for each ifEntry with an ifType
        of adsl(94) and an adslLineCoding of cap(3)."
    INDEX       { ifIndex, adslAtucIntervalNumber}
    ::= { cAdslAtucCapIntervalTable 1 }

CAdslAtucCapIntervalEntry ::= SEQUENCE {
    cAdslAtucCapIntervalInitFailures PerfIntervalCount
}

cAdslAtucCapIntervalInitFailures OBJECT-TYPE
    SYNTAX      PerfIntervalCount
    MAX-ACCESS  read-only
    STATUS      current
    DESCRIPTION
        "This object specifies the number of line initialization
        failures in the interval."
    ::= { cAdslAtucCapIntervalEntry 1 }

-- Configuration Profile Table

cAdslLineCapConfProfileTable OBJECT-TYPE
    SYNTAX      SEQUENCE OF CAdslLineCapConfProfileEntry
    MAX-ACCESS  not-accessible
    STATUS      current
    DESCRIPTION
        "This table extends the adslLineConfProfileTable and contains
        enterprise-specific ADSL line configuration information."
    ::= { ciscoAdslLineCapMIBObjects 14 }

cAdslLineCapConfProfileEntry OBJECT-TYPE
    SYNTAX      CAdslLineCapConfProfileEntry
    MAX-ACCESS  not-accessible
    STATUS      current
    DESCRIPTION
        "A configuration profile containing enterprise-specific ADSL
        line configuration information."
    INDEX       { IMPLIED adslLineConfProfileName }
    ::= { cAdslLineCapConfProfileTable 1 }

CAdslLineCapConfProfileEntry ::= SEQUENCE {
    cAdslLineCapConfTrainingMode        INTEGER,
    cAdslLineCapConfInterleaveDelay     INTEGER,
    cAdslLineCapConfCpeSignature        INTEGER,
    cAdslAtucCapConfTargetSnrMgn        INTEGER,
    cAdslAtucCapConfMinTxRate           AdslLineCapDownstreamRate,
    cAdslAtucCapConfMaxTxRate           AdslLineCapDownstreamRate,
    cAdslAtucCapConfDown136KBaudEnable  TruthValue,
    cAdslAtucCapConfUp68KBaudEnable     TruthValue,
    cAdslAtucCapConfUp17KBaudEnable     TruthValue,
    cAdslAtucCapConfPsdmLevel           Integer32,
    cAdslAturCapConfTargetSnrMgn        INTEGER,
    cAdslAturCapConfMinTxRate           AdslLineCapUpstreamRate,
    cAdslAturCapConfMaxTxRate           AdslLineCapUpstreamRate,
    cAdslAturCapConfPsdmLevel           Integer32
}

cAdslLineCapConfTrainingMode OBJECT-TYPE
    SYNTAX      INTEGER {
        standard(1),
        fast(2)
        }
    MAX-ACCESS  read-create
    STATUS      current
    DESCRIPTION
        "This object specifies the mode employed by the ATU-C and
        ATU-R when training against each other.  One of two training
        modes can be employed:

        - Standard
            An ATU-C initiates a training sequence using the method
            defined by T1E1.4/99-161R3.  This training mode is the
            default for ADSL modems employing the CAP line code.

        - Fast
            An ATU-C initiates a vendor-specific training sequence that
            can possibly provide a shorter training sequence."
    REFERENCE
        "ANSI T1E1.4/99-161R3, Single-Carrier Rate Adaptive Digital
        Subscriber Line (RADSL)."
    DEFVAL      { standard }
    ::= { cAdslLineCapConfProfileEntry 1 }

cAdslLineCapConfInterleaveDelay OBJECT-TYPE
    SYNTAX      INTEGER {
        none(1),
        short(2),
        long(3)
    }
    MAX-ACCESS  read-create
    STATUS      current
    DESCRIPTION
        "This object specifies the interleave delay for the
        downstream channel.  The value of this object specifies the
        mapping (relative spacing) between subsequent input bytes at
        the interleaver input and their placement in the bit stream
        at the interleaver output.  The value 'long' provides greater
        separation between consecutive input bytes in the output bit
        stream, thereby allowing for improved impulse noise immunity
        at the expense of payload latency."
    REFERENCE
        "ANSI T1E1.4/99-161R3, Single-Carrier Rate Adaptive Digital
        Subscriber Line (RADSL)."
    DEFVAL      { short }
    ::= { cAdslLineCapConfProfileEntry 2 }

cAdslLineCapConfCpeSignature OBJECT-TYPE
    SYNTAX      INTEGER (0..127)
    MAX-ACCESS  read-create
    STATUS      current
    DESCRIPTION
        "This object specifies the value of the minimum CPE signature
        expected from ATU-R during training.  The value of the CPE
        signature corresponds to the software version of the ATU-R.

        If the CPE signature advertised by an ATU-R is less than the
        value of this object, then the ATU-C will be placed into an
        idle state, thereby preventing the line from training.

        In addition, the agent increments the value of the
        cAdslAtucCapPerfInitFailures object for each attempt to train
        by an ATU-R advertising a CPE signature less than the value of
        this object.  When a management client observes the value of
        cAdslAtucCapPerfInitFailures increasing, it should retrieve the
        value of the adslAturInvSerialNumber object (for more details,
        see the ADSL-LINE-MIB) .  This value of this object reflects the
        CPE signature advertised by an ATU-R implementing the CAP line
        code.  If the CPE signature of the ATU-R is not known, the value
        of the adslAturInvSerialNumber object should be a zero-length
        string."
    DEFVAL      { 0 }
    ::= { cAdslLineCapConfProfileEntry 3 }

cAdslAtucCapConfTargetSnrMgn OBJECT-TYPE
    SYNTAX      INTEGER (0..310)
    UNITS       "tenth dB"
    MAX-ACCESS  read-create
    STATUS      current
    DESCRIPTION
        "This object specifies the target SNR margin.  This is the
        desired noise margin the ATU-C must achieve with a BER of
        10-7 or better to successfully complete training."
    DEFVAL      { 60 }
    ::= { cAdslLineCapConfProfileEntry 4 }

cAdslAtucCapConfMinTxRate OBJECT-TYPE
    SYNTAX      AdslLineCapDownstreamRate
    UNITS       "bps"
    MAX-ACCESS  read-create
    STATUS      current
    DESCRIPTION
        "This object specifies the minimum acceptable downstream
        line rate."
    DEFVAL      { 0 }
    ::= { cAdslLineCapConfProfileEntry 5 }

cAdslAtucCapConfMaxTxRate OBJECT-TYPE
    SYNTAX      AdslLineCapDownstreamRate
    UNITS       "bps"
    MAX-ACCESS  read-create
    STATUS      current
    DESCRIPTION
        "This object specifies the desired line rate which the ATU-C
        will attempt to train at."
    DEFVAL      { 640000 }
    ::= { cAdslLineCapConfProfileEntry 6 }

cAdslAtucCapConfDown136KBaudEnable OBJECT-TYPE
    SYNTAX      TruthValue
    MAX-ACCESS  read-create
    STATUS      current
    DESCRIPTION
        "This object specifies whether the modem can train the
        downstream channel using a symbol rate of 136K symbols
        per second."
    REFERENCE
        "ANSI T1E1.4/99-161R3, Single-Carrier Rate Adaptive Digital
        Subscriber Line (RADSL)."
    DEFVAL      { true }
    ::= { cAdslLineCapConfProfileEntry 7 }

cAdslAtucCapConfUp68KBaudEnable OBJECT-TYPE
    SYNTAX      TruthValue
    MAX-ACCESS  read-create
    STATUS      current
    DESCRIPTION
        "This object specifies whether the modem can train the
        upstream channel using a symbol rate of 68K symbols
        per second.

        The value of this object does not effect whether the modem
        can train at any other symbol rate; that is, the values of
        this object and cAdslAtucCapConfUp17KBaudEnable are not
        mutually exclusive."
    REFERENCE
        "ANSI T1E1.4/99-161R3, Single-Carrier Rate Adaptive Digital
        Subscriber Line (RADSL)."
    DEFVAL      { true }
    ::= { cAdslLineCapConfProfileEntry 8 }

cAdslAtucCapConfUp17KBaudEnable OBJECT-TYPE
    SYNTAX      TruthValue
    MAX-ACCESS  read-create
    STATUS      current
    DESCRIPTION
        "This object specifies whether the modem can train the
        upstream channel using a symbol rate of 17K symbols
        per second.

        The value of this object does not effect whether the modem
        can train at any other symbol rate; that is, the values of
        this object and cAdslAtucCapConfUp68KBaudEnable are not
        mutually exclusive."
    REFERENCE
        "ANSI T1E1.4/99-161R3, Single-Carrier Rate Adaptive Digital
        Subscriber Line (RADSL)."
    DEFVAL      { true }
    ::= { cAdslLineCapConfProfileEntry 9 }

cAdslAtucCapConfPsdmLevel OBJECT-TYPE
    SYNTAX      Integer32 ( -52 | -49 | -46 | -43 | -40 | -37 )
    UNITS       "dBm/Hz"
    MAX-ACCESS  read-create
    STATUS      current
    DESCRIPTION
        "This managed object specifies the nominal power output of the
        ATU-C across the entire transmit spectrum.  Observe that this
        implies the attenuation of the signal for some data rates.

        This value does not take effect until the modem has retrained
        against the ATU-C to which the ATU-R has a connection."
    REFERENCE
        "ANSI T1E1.4/99-161R3, Single-Carrier Rate Adaptive Digital
        Subscriber Line (RADSL)."
    DEFVAL      { -40 }
    ::= { cAdslLineCapConfProfileEntry 10 }

cAdslAturCapConfTargetSnrMgn OBJECT-TYPE
    SYNTAX      INTEGER (0..310)
    UNITS       "tenth dB"
    MAX-ACCESS  read-create
    STATUS      current
    DESCRIPTION
        "This object specifies the target SNR margin.  This is the
        desired noise margin the ATU-R must achieve with a BER of
        10-7 or better to successfully complete training."
    DEFVAL      { 60 }
    ::= { cAdslLineCapConfProfileEntry 11 }

cAdslAturCapConfMinTxRate OBJECT-TYPE
    SYNTAX      AdslLineCapUpstreamRate
    UNITS       "bps"
    MAX-ACCESS  read-create
    STATUS      current
    DESCRIPTION
        "This object specifies the minimum acceptable upstream
        line rate."
    DEFVAL      { 0 }
    ::= { cAdslLineCapConfProfileEntry 12 }

cAdslAturCapConfMaxTxRate OBJECT-TYPE
    SYNTAX      AdslLineCapUpstreamRate
    UNITS       "bps"
    MAX-ACCESS  read-create
    STATUS      current
    DESCRIPTION
        "This object specifies the desired line rate which the ATU-R
        will attempt to train at."
    DEFVAL      { 91000 }
    ::= { cAdslLineCapConfProfileEntry 13 }

cAdslAturCapConfPsdmLevel OBJECT-TYPE
    SYNTAX      Integer32 ( -53 | -50 | -47 | -44 | -41 | -38 )
    UNITS       "dBm/Hz"
    MAX-ACCESS  read-create
    STATUS      current
    DESCRIPTION
        "This managed object specifies the nominal power output of the
        ATU-R across the entire transmit spectrum.  Observe that this
        implies the attenuation of the signal for some data rates.

        This value does not take effect until the modem has retrained
        against the ATU-C to which the ATU-R has a connection."
    REFERENCE
        "ANSI T1E1.4/99-161R3, Single-Carrier Rate Adaptive Digital
        Subscriber Line (RADSL)."
    DEFVAL      { -38 }
    ::= { cAdslLineCapConfProfileEntry 14 }

-- MIB Notification Definitions

cAdslLineCapMIBNotificationsPrefix OBJECT IDENTIFIER
    ::= { ciscoAdslLineCapMIB 2 }

cAdslLineCapMIBNotifications OBJECT IDENTIFIER
    ::= { cAdslLineCapMIBNotificationsPrefix 0 }

-- MIB Conformance Statements

ciscoAdslLineCapMIBConformance OBJECT IDENTIFIER
    ::= { ciscoAdslLineCapMIB 3 }

ciscoAdslLineCapMIBCompliances OBJECT IDENTIFIER
    ::= { ciscoAdslLineCapMIBConformance 1 }

ciscoAdslLineCapMIBGroups OBJECT IDENTIFIER
    ::= { ciscoAdslLineCapMIBConformance 2 }

-- Compliance

ciscoAdslLineCapMIBAtucCompliance MODULE-COMPLIANCE
    STATUS current
    DESCRIPTION
        "The compliance statement for entities that implement the
        CISCO-ADSL-CAP-LINE-MIB.  Implementation of this MIB is
        mandatory for any platform that supports one or more ADSL
        line interfaces that implement the CAP line code."

    MODULE -- this module
        MANDATORY-GROUPS {
            cAdslAtucCapBasicGroup
        }

        GROUP       cAdslAturCapGroup
        DESCRIPTION
            "The implementation of this group is optional.  However,
            this statement recommends the implementation of this group
            if the ATU-C and ATU-R support a remote management
            capability."

        GROUP       cAdslAtucCapPM15MinIntervalGroup
        DESCRIPTION
            "The implementation of this group is optional."

        GROUP       cAdslAtucCapPM1DayIntervalGroup
        DESCRIPTION
            "The implementation of this group is optional."
   ::= { ciscoAdslLineCapMIBCompliances 1 }

ciscoAdslLineCapMIBAturCompliance MODULE-COMPLIANCE
    STATUS current
    DESCRIPTION
        "The compliance statement for entities that implement the
        CISCO-ADSL-CAP-LINE-MIB and manage ADSL ATU-R class devices.
        Implementation of this MIB is mandatory for any platform
        that supports one or more ADSL line interfaces that implement
        the CAP line code."

    MODULE -- this module
        MANDATORY-GROUPS {
            cAdslAturBasicGroup
        }

    ::= { ciscoAdslLineCapMIBCompliances 2 }

-- Units of Conformance

cAdslAtucCapBasicGroup OBJECT-GROUP
    OBJECTS {
        cAdslAtucCapCurrState,
        cAdslAtucCapCurrRxGain,
        cAdslAtucCapCurrRxSnr,
        cAdslAtucCapPerfInitFailures,
        cAdslLineCapConfTrainingMode,
        cAdslLineCapConfInterleaveDelay,
        cAdslLineCapConfCpeSignature,
        cAdslAtucCapConfTargetSnrMgn,
        cAdslAtucCapConfMinTxRate,
        cAdslAtucCapConfMaxTxRate,
        cAdslAtucCapConfDown136KBaudEnable,
        cAdslAtucCapConfUp68KBaudEnable,
        cAdslAtucCapConfUp17KBaudEnable,
        cAdslAtucCapConfPsdmLevel
    }
    STATUS current
    DESCRIPTION
        "A collection of managed objects defining the basic operation
        of an ATU-C implementing the CAP line code."
    ::= { ciscoAdslLineCapMIBGroups 1 }

cAdslAturBasicGroup OBJECT-GROUP
    OBJECTS {
        cAdslAturCapCurrRxGain,
        cAdslLineCapConfTrainingMode,
        cAdslAturCapConfTargetSnrMgn,
        cAdslAturCapConfMinTxRate,
        cAdslAturCapConfMaxTxRate,
        cAdslAturCapConfPsdmLevel
    }
    STATUS current
    DESCRIPTION
        "A collection of managed objects defining the basic operation
        of an ATU-R implementing the CAP line code."
    ::= { ciscoAdslLineCapMIBGroups 2 }

cAdslAturCapGroup OBJECT-GROUP
    OBJECTS {
        cAdslAturCapCurrRxGain,
        cAdslAturCapConfTargetSnrMgn,
        cAdslAturCapConfMinTxRate,
        cAdslAturCapConfMaxTxRate,
        cAdslAturCapConfPsdmLevel
    }
    STATUS current
    DESCRIPTION
        "A collection of managed objects defining the capability to
        remotely manage a ATU-R."
    ::= { ciscoAdslLineCapMIBGroups 3 }

cAdslAtucCapPM15MinIntervalGroup OBJECT-GROUP
    OBJECTS {
        cAdslAtucCapPerfCurr15MinInitFailures,
        cAdslAtucCapIntervalInitFailures
    }
    STATUS current
    DESCRIPTION
        "A collection of managed objects defining near-end performance
        data collection capability using 15-minute intervals."
    ::= { ciscoAdslLineCapMIBGroups 4 }

cAdslAtucCapPM1DayIntervalGroup OBJECT-GROUP
    OBJECTS {
        cAdslAtucCapPerfCurr1DayInitFailures,
        cAdslAtucCapPerfPrev1DayInitFailures
    }
    STATUS current
    DESCRIPTION
        "A collection of managed objects defining near-end performance
        data collection capability using 1-day intervals."
    ::= { ciscoAdslLineCapMIBGroups 5 }

END
