-- *****************************************************************
-- CISCO-BBSM-MIB.my:  Cisco BBSM MIB file
--
-- April 3 2004, Ting Wu
--
-- Copyright (c) 2004 by cisco Systems, Inc.
-- All rights reserved.
--
-- *****************************************************************


CISCO-BBSM-MIB DEFINITIONS ::= BEGIN

IMPORTS
   NOTIFICATION-TYPE,
   MODULE-IDENTITY,
   OBJECT-TYPE,
   Unsigned32
      FROM SNMPv2-SMI
   MODULE-COMPLIANCE,
   OBJECT-GROUP,
   NOTIFICATION-GROUP
      FROM SNMPv2-CONF
   DateAndTime
      FROM SNMPv2-TC
   SnmpAdminString
      FROM SNMP-FRAMEWORK-MIB
   ciscoMgmt
      FROM CISCO-SMI;

ciscoBbsmMIB MODULE-IDENTITY
   LAST-UPDATED    "200404030000Z"
   ORGANIZATION    "Cisco Systems, Inc."
   CONTACT-INFO
                "       Cisco Systems
                        Customer Service

                Postal: 170 W Tasman Drive
                        San Jose, CA  95134
                        USA

                   Tel: +1 800 553-NETS

                E-mail: cs-bbsm@cisco.com"
   DESCRIPTION
      "This mib is designed to send BBSM specific
       notifications.  There are variables that contain detail data
       that are bind to a notification. The SNMP Manager that
       receives the notifications should look at the binding
       variables for further details of the notification data.

       BBSM stands for Building Broadband Service Manager.  It is a
       software-based service platform that enables customers to
       create, market, and operate broadband access services,
       such as high-speed Internet access with plug-and-play,
       multiple authentication and billing options and Web-based
       management, reporting, and configuration."

   REVISION        "200404030000Z"
   DESCRIPTION
       "Initial revision of this MIB module."
   ::= { ciscoMgmt 358 }

--object definitions
ciscoBbsmNotifications OBJECT IDENTIFIER ::= { ciscoBbsmMIB 0 }
ciscoBbsmMIBObjects OBJECT IDENTIFIER ::=  { ciscoBbsmMIB 1 }

ciscoBbsmEventInfo OBJECT IDENTIFIER ::= { ciscoBbsmMIBObjects 1}

cbbsmEventDescription OBJECT-TYPE
       SYNTAX      OCTET STRING
       MAX-ACCESS  accessible-for-notify
       STATUS      current
       DESCRIPTION
          "The cbbsmEventDescription binds with notification.
           It displays the description of an event that caused
           a notification to be sent.

           Examples of cbbsmEventDescription value would be
           'Failed to connect to RADIUS server xx.yy.zz.aa' or
           'Failed to connect to ICS server xx.yy.zz.aa'"
       ::= { ciscoBbsmEventInfo 1 }

cbbsmEventSource OBJECT-TYPE
       SYNTAX      SnmpAdminString
       MAX-ACCESS  accessible-for-notify
       STATUS      current
       DESCRIPTION
          "The cbbsmEventSource binds with a notification. It displays
           the source of an event that caused the notification to be
           sent.  The cbbsmEventSource also binds with
           cbbsmEventDescription.

           Examples of cbbsmEventSource value would be
           'BBSM_RADIUS' or
           'BBSM_ICS' "
       ::= { ciscoBbsmEventInfo 2 }

cbbsmEventID OBJECT-TYPE
       SYNTAX      Unsigned32
       MAX-ACCESS  accessible-for-notify
       STATUS      current
       DESCRIPTION
          "The cbbsmEventID binds with a notification. It displays
           event ID of an event that caused the notification to be
           sent. The cbbsmEventID also binds with
           cbbsmEventDescription.

           Examples of a cbbsmEventID would be 1, 2, ..."
       ::= { ciscoBbsmEventInfo 3 }

cbbsmEventType OBJECT-TYPE
       SYNTAX      INTEGER
           {   error       (1),
               warning     (2),
               information (3)
           }
       MAX-ACCESS  accessible-for-notify
       STATUS      current
       DESCRIPTION
          "The cbbsmEventType binds with the notification. It displays
           the event type of an event that caused notification to be
           sent.  The cbbsmEventType also binds with
           cbbsmEventDescription.

           error(1) : An Error event indicates a significant problem,
           such as loss of data or loss of functionality.

           warning(2): A Warning event is not necessarily significant,
           but may indicate a possible future problem.

           information(3): An Information event describes the
           successful operation of an application, driver, or service."
       ::= { ciscoBbsmEventInfo 4 }

cbbsmEventTime OBJECT-TYPE
       SYNTAX      DateAndTime
       MAX-ACCESS  accessible-for-notify
       STATUS      current
       DESCRIPTION
          "The cbbsmEventTime binds with the notification. It is a
           date and time string that displays the time of the event
           that caused notification to be sent."
       ::= { ciscoBbsmEventInfo 5 }

-- notification definitions

ciscoBbsmEvent NOTIFICATION-TYPE
       OBJECTS  {cbbsmEventDescription,
                  cbbsmEventSource,
                  cbbsmEventID,
                  cbbsmEventType,
                  cbbsmEventTime
                }
       STATUS   current
       DESCRIPTION
          "Notification of a BBSM event.  The details of the
           event is binded in variables listed.  These variables
           are identical to the same event logged on the Microsoft
           Event Viewer.

           For example, if BBSM had problem connecting to RADIUS
           server and SNMP Service on BBSM is configured to send
           notifications, a notification of ciscoBbsmEvent will
           be sent and binded variables will have following values
           cbbsmEventDescription = 'Failed to connect to RADIUS server
           xx.yy.zz.aa'
           cbbsmEventSource = 'BBSM_RADIUS'
           cbbsmEventID = '1'
           cbbsmEventType = 2
           "
       ::= { ciscoBbsmNotifications 1 }

-- conformance information

ciscoBbsmMIBConformance OBJECT IDENTIFIER ::= { ciscoBbsmMIB 2 }

ciscoBbsmMIBCompliances OBJECT IDENTIFIER
       ::= { ciscoBbsmMIBConformance 1 }
ciscoBbsmMIBGroups      OBJECT IDENTIFIER
       ::= { ciscoBbsmMIBConformance 2 }

-- Compliance
ciscoBbsmMIBCompliance MODULE-COMPLIANCE
        STATUS current
        DESCRIPTION
                "The compliance statement for entities which implement
                the Cisco BBSM MIB"
        MODULE        -- this module
                MANDATORY-GROUPS { ciscoBbsmMIBGroup,
                                   ciscoBbsmMIBNotificationGroup }
        ::= { ciscoBbsmMIBCompliances 1 }

-- Conformance
ciscoBbsmMIBGroup OBJECT-GROUP
        OBJECTS {
            cbbsmEventDescription,
            cbbsmEventSource,
            cbbsmEventID,
            cbbsmEventType,
            cbbsmEventTime  }
        STATUS current
        DESCRIPTION
                "A set of objects providing details of a event
                to a Cisco agent."
        ::= { ciscoBbsmMIBGroups 1 }

ciscoBbsmMIBNotificationGroup NOTIFICATION-GROUP
        NOTIFICATIONS { ciscoBbsmEvent }
        STATUS  current
        DESCRIPTION
                "Set of notifications implemented in this module."
        ::= { ciscoBbsmMIBGroups 2 }

END
