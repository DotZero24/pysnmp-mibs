-- *****************************************************************
-- C I S C O  A T M   Traffic  Parameter  Extensions
--
-- December 1995, Michael Grobelch
--
-- Copyright (c) 1996-1997, 2001 by Cisco Systems, Inc.
-- All rights reserved.
-- *****************************************************************
--
CISCO-ATM-TRAFFIC-MIB DEFINITIONS ::= BEGIN

IMPORTS
    MODULE-IDENTITY, OBJECT-TYPE, OBJECT-IDENTITY
                                     FROM SNMPv2-SMI
    atmTrafficDescrParamEntry        FROM ATM-MIB        -- RFC 1695
    ciscoExperiment                  FROM CISCO-SMI
    MODULE-COMPLIANCE, OBJECT-GROUP  FROM SNMPv2-CONF
    SnmpAdminString                  FROM SNMP-FRAMEWORK-MIB;

ciscoAtmTrafficExtMIB   MODULE-IDENTITY
    LAST-UPDATED "200208260000Z"
    ORGANIZATION "Cisco System Inc."
    CONTACT-INFO
                 "Cisco Systems
                  Customer Service

                  Postal: 170 W. Tasman Drive
                          San Jose, CA  95134
                          USA

                  Tel: +1 800 553-NETS

                  E-mail: cs-atm@cisco.com"
    DESCRIPTION
          "This MIB module is an extension to traffic OIDs
           and variables defined in rfc1695."
    REVISION        "200208260000Z"
    DESCRIPTION
          "Deprecated atmNoClpNoScrCdvt as a similar object
           atmNoClpNoScrCdvt defined in RFC-2514 can be used instead."
    REVISION        "200111010000Z"
    DESCRIPTION
          "Added an object to identify the traffic descriptor by a
           name in human readable form."
    REVISION        "9705290000Z"
    DESCRIPTION
          "Added traffic for types dual-leaky bucket and mcr support
           made possible on the LS1010 by the Feature Card Per Flow
           Queueing support for per-VC queueing hardware structures."
    ::= { ciscoExperiment 11 }

ciscoAtmTrafficExtMIBObjects OBJECT IDENTIFIER ::=
                                          { ciscoAtmTrafficExtMIB 1 }

-- This MIB defines a two Groups:
--
--    1. the ATM Traffic Type Extension  Group, extending the
--       RFC 1695 mib Traffic Types.
--    2. the ATM Traffic Descriptor Parameter Table Extension Group,
--       extending the RFC 1695 mib Traffic Table.

ciscoAtmTrafficTypeExt OBJECT IDENTIFIER ::=
                                   { ciscoAtmTrafficExtMIBObjects 1 }
ciscoAtmTrafficTableExt OBJECT IDENTIFIER ::=
                                   { ciscoAtmTrafficExtMIBObjects 2 }

--
-- The ATM Traffic Type Extension  Group
--

atmNoClpNoScrCdvt OBJECT-IDENTITY
     STATUS     deprecated  -- superceded by atmNoClpNoScrCdvt
                            -- OID in RFC 2514.
     DESCRIPTION
      "Specifies peak cell rate for CLP, and
       cell delay variation tolerance:
       Parameter 1: CLP=0+1 peak cell rate in
                    cells per second
       Parameter 2: CDVT in cell-times
       Parameter 3: not used
       Parameter 4: not used
       Parameter 5: not used.
       This traffic descriptor is for cbr, abr
       or ubr service categories, desiring to
       specify the cdvt as well as pcr."
   ::= { ciscoAtmTrafficTypeExt 1 }

atmClpScrMbsCdvt OBJECT-IDENTITY
     STATUS     current
     DESCRIPTION
      "This traffic descriptor is for Peak
       Cell Rate (PCR), Sustained Cell Rate (SCR),
       Maximum Burst Size applied to SCR,
       and Cell Delay Variation Tolerance
       applied to PCR.
       The use of the parameter vector for this type:
       Parameter 1: CLP=0+1 peak cell rate in
                    cells per second
       Parameter 2: CLP=0 sustained cell rate in
                    cells per second.
       Parameter 3: maximum burst size in cells
       Parameter 4: CDVT in cell-times
       Parameter 5: not used."
     ::= { ciscoAtmTrafficTypeExt 2 }

atmNoClpScrMbsCdvt OBJECT-IDENTITY
     STATUS     current
     DESCRIPTION
      "This traffic descriptor is for Peak
       Cell Rate (PCR), Sustained Cell Rate (SCR),
       Maximum Burst Size applied to SCR,
       and Cell Delay Variation Tolerance
       applied to PCR.
       The use of the parameter vector for this type:
       Parameter 1: CLP=0+1 peak cell rate in
                    cells per second
       Parameter 2: CLP=0+1 sustained cell rate in
                    cells per second.
       Parameter 3: maximum burst size in cells
       Parameter 4: CDVT in cell-times
       Parameter 5: not used."
     ::= { ciscoAtmTrafficTypeExt 3 }

atmNoClpMcr OBJECT-IDENTITY
     STATUS     current
     DESCRIPTION
      "This traffic descriptor is for Peak
       Cell Rate (PCR) and Minimum Cell Rate
       (MCR).
       The use of the parameter vector for this type:
       Parameter 1: CLP=0+1 peak cell rate in
                    cells per second
       Parameter 2: CLP=0+1 minimum cell rate in
                    cells per second.
       Parameter 3: not used.
       Parameter 4: not used.
       Parameter 5: not used."
     ::= { ciscoAtmTrafficTypeExt 4 }

atmNoClpMcrCdvt OBJECT-IDENTITY
     STATUS     current
     DESCRIPTION
      "This traffic descriptor is for Peak
       Cell Rate (PCR), Minimum Cell Rate (MCR),
       and Cell Delay Variation Tolerance
       applied to PCR.
       The use of the parameter vector for this type:
       Parameter 1: CLP=0+1 peak cell rate in
                    cells per second
       Parameter 2: CDVT in cell-times
       Parameter 3: CLP=0+1 minimum cell rate in
                    cells per second.
       Parameter 4: not used.
       Parameter 5: not used."
     ::= { ciscoAtmTrafficTypeExt 5 }

--
-- The ATM Traffic Descriptor Parameter Table Extension  Group
--

atmTrafficDescrParamExtTable  OBJECT-TYPE
    SYNTAX     SEQUENCE OF AtmTrafficDescrParamExtEntry
    MAX-ACCESS not-accessible
    STATUS     current
    DESCRIPTION
       "Provide additional information specifying traffic parameters
        for a VC/VP."
    ::= { ciscoAtmTrafficTableExt 1 }

atmTrafficDescrParamExtEntry OBJECT-TYPE
    SYNTAX     AtmTrafficDescrParamExtEntry
    MAX-ACCESS not-accessible
    STATUS     current
    DESCRIPTION
        " An entry in the Traffic Parameter Descriptor extension
          table."
    AUGMENTS { atmTrafficDescrParamEntry }
    ::= { atmTrafficDescrParamExtTable 1 }

AtmTrafficDescrParamExtEntry ::=
    SEQUENCE {
        atmTrafficExplicitServCategory  INTEGER,
        atmTrafficDerivedServCategory   INTEGER,
        atmTrafficDescriptorName        SnmpAdminString
    }

atmTrafficExplicitServCategory   OBJECT-TYPE
    SYNTAX  INTEGER {
              cbr     (1),
              vbrRt   (2),
              vbrNrt  (3),
              abr     (4),
              ubr     (5),
              notDef  (6)
              }
    MAX-ACCESS  read-create
    STATUS  current
    DESCRIPTION
        "This objects indicates the Service Category
         specified by the Traffic Descriptor.
         If it is defined, the setting of this
         object determines the Service Category used
         for the connection. This then limits the
         possible Traffic Descriptor Types as follows:

         Explicit
         Service
         Category       Type may only be
         -----------------------------------------
         cbr            atmNoClpNoScr.
                        atmClpNoTaggingNoScr
                        atmClpTaggingNoScr
                        atmNoClpNoScrCdvt

         abr/ubr        atmNoTrafficDescriptor
                        atmNoClpNoScr.
                        atmNoClpNoScrCdvt
                        atmNoClpMcr -- ubr+/abr
                        atmNoClpMcrCdvt -- ubr+/abr

         vbr            atmNoClpScr
                        atmClpNoTaggingScr
                        atmClpTaggingScr
                        atmClpScrMbsCdvt
                        atmNoClpScrMbsCdvt
         -----------------------------------------
         If the settings of Service Category and Traffic
         Descriptor Type are not compatible, the row can
         not be made active."
    DEFVAL { notDef }
     ::= { atmTrafficDescrParamExtEntry 1 }

atmTrafficDerivedServCategory   OBJECT-TYPE
    SYNTAX  INTEGER {
              cbr     (1),
              vbrRt   (2),
              vbrNrt  (3),
              abr     (4),
              ubr     (5)
              }
    MAX-ACCESS  read-only
    STATUS  current
    DESCRIPTION
        "This object indicates the Service Category
         derived from the Traffic Descriptor. If the
         object atmTrafficExplicitServCategory has
         a defined value, then this object mirrors
         that value. If Explicit Service Category
         has the value notDef, then this object
         reflects the Service Category derived from
         the Traffic Descriptor Type as follows:

         Traffic Descriptor       Service
             Type                 Category
         -----------------------------------------
         atmNoTrafficDescriptor   ubr

         atmNoClpMcr              abr
         atmNoClpMcrCdvt          abr

         atmNoClpNoScr      --|
         atmClpNoTaggingNoScr |-- cbr
         atmClpTaggingNoScr   |
         atmNoClpNoScrCdvt  --|

         atmNoClpScr        --|
         atmClpNoTaggingScr   |-- vbr-rt
         atmClpScrMbsCdvt     |
         atmNoClpScrMbsCdvt   |
         atmClpTaggingScr   --|
         -----------------------------------------"
     ::= { atmTrafficDescrParamExtEntry 2 }

atmTrafficDescriptorName  OBJECT-TYPE
     SYNTAX        SnmpAdminString
     MAX-ACCESS    read-create
     STATUS        current
     DESCRIPTION
        "A human readable string that contains the unique name
         of this Traffic Descriptor.
         This object will return a zero-length string if value is
         not set."
     DEFVAL { "" }
     ::= { atmTrafficDescrParamExtEntry 3 }


-- conformance information

ciscoAtmTrafficExtMIBConformance
          OBJECT IDENTIFIER ::= { ciscoAtmTrafficExtMIB 3 }
ciscoAtmTrafficExtMIBCompliances
          OBJECT IDENTIFIER ::= { ciscoAtmTrafficExtMIBConformance 1 }
ciscoAtmTrafficExtMIBGroups
          OBJECT IDENTIFIER ::= { ciscoAtmTrafficExtMIBConformance 2 }

-- compliance statements

ciscoAtmTrafficExtMIBCompliance MODULE-COMPLIANCE
    STATUS  deprecated
    DESCRIPTION
    "The compliance statement for the Cisco ATM Traffic Extension MIB."
    MODULE  -- this module
            MANDATORY-GROUPS { ciscoAtmTrafficTableExtMIBGroup }
    ::= { ciscoAtmTrafficExtMIBCompliances 1 }

ciscoAtmTrafficExtMIBComplianceRev1 MODULE-COMPLIANCE
    STATUS  current
    DESCRIPTION
    "The compliance statement for the Cisco ATM Traffic Extension MIB."
    MODULE  -- this module
            MANDATORY-GROUPS { ciscoAtmTrafficTableExtMIBGroup }

    GROUP ciscoAtmTrafficNmsGroup
    DESCRIPTION
      "This group is optional."
    ::= { ciscoAtmTrafficExtMIBCompliances 2 }

-- units of conformance

ciscoAtmTrafficTableExtMIBGroup   OBJECT-GROUP
    OBJECTS {
             atmTrafficExplicitServCategory,
             atmTrafficDerivedServCategory
            }
    STATUS  current
    DESCRIPTION
            "A collection of objects which provide extensions to  the
             ATM Traffic Parameter Descriptor Table."
    ::= {  ciscoAtmTrafficExtMIBGroups 1 }

ciscoAtmTrafficNmsGroup   OBJECT-GROUP
    OBJECTS {
             atmTrafficDescriptorName
            }
    STATUS  current
    DESCRIPTION
            "A collection of objects which provide additional
             information for a management system."
    ::= {  ciscoAtmTrafficExtMIBGroups 2 }

END
