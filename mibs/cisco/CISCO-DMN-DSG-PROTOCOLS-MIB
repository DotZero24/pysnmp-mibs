--*****************************************************************
-- CISCO_DMN_DSG_Protocols.mib: MIB file for protocol settings.
--
-- February 2012, Aaron Curtin
--
-- Copyright (c) 2012 by Cisco Systems, Inc. All rights reserved.
--*****************************************************************

CISCO-DMN-DSG-PROTOCOLS-MIB

DEFINITIONS ::= BEGIN

IMPORTS
    OBJECT-TYPE,
    MODULE-IDENTITY, Counter32
        FROM SNMPv2-SMI
    DisplayString
        FROM SNMPv2-TC
    OBJECT-GROUP, MODULE-COMPLIANCE
        FROM SNMPv2-CONF
    ciscoDSGUtilities
        FROM CISCO-DMN-DSG-ROOT-MIB;


ciscoDSGProtocols MODULE-IDENTITY
    LAST-UPDATED    "201307101903Z"
    ORGANIZATION    "Cisco Systems, Inc."
    CONTACT-INFO
       "Cisco Systems, Inc.
        Customer Service
        Postal: 170 W Tasman Drive
        San Jose, CA 95134
        USA
        Tel: +1 800 553 NETS

        E-mail: cs-ipsla@cisco.com"
    DESCRIPTION     "Cisco Routing MIB."

    REVISION        "201307101903Z"
    DESCRIPTION     "V01.00.01 2013-07-10
                    Replace DTX with Syslog."

    REVISION        "201203070730Z"
    DESCRIPTION     "V01.00.00 2012-03-07
                    Initial Version."

    ::= { ciscoDSGUtilities 39 }

--**************************************
-- Protocols
--**************************************

protocolsCtrlTelnet  OBJECT-TYPE
    SYNTAX  INTEGER {
                      disable(1),
                      enable(2)
                    }
    MAX-ACCESS read-write
    STATUS  current
    DESCRIPTION
        "Select whether to allow Telnet connections or not"
    ::= { ciscoDSGProtocols 1 }

protocolsCtrlSSH  OBJECT-TYPE
    SYNTAX  INTEGER {
                      disable(1),
                      enable(2)
                    }
    MAX-ACCESS read-write
    STATUS  current
    DESCRIPTION
        "Select whether to allow secure shell connections or not."
    ::= { ciscoDSGProtocols 2 }

protocolsCtrlHTTP  OBJECT-TYPE
    SYNTAX  INTEGER {
                      disable(1),
                      enable(2),
                      secure(3)
                    }
    MAX-ACCESS read-write
    STATUS  current
    DESCRIPTION
        "Select whether to allow web connections or not and choose
         secure or unsecure mode."
    ::= { ciscoDSGProtocols 3 }

protocolsCtrlSNMP  OBJECT-TYPE
    SYNTAX  INTEGER {
                      disable(1),
                      enable(2)
                    }
    MAX-ACCESS read-write
    STATUS  current
    DESCRIPTION
        "Select whether to allow SNMP connections or not."
    ::= { ciscoDSGProtocols 5 }

protocolsCtrlRIP  OBJECT-TYPE
    SYNTAX  INTEGER {
                      disable(1),
                      enable(2)
                    }
    MAX-ACCESS read-write
    STATUS  current
    DESCRIPTION
        "Select whether to allow RIPv2 protocol or not."
    ::= { ciscoDSGProtocols 6 }

protocolsCtrlMPE  OBJECT-TYPE
    SYNTAX  INTEGER {
                      fwdNone(1),
                      fwdAll(2),
                      fwdFiltered(3)
                    }
    MAX-ACCESS read-write
    STATUS  current
    DESCRIPTION
        "Select whether to allow MPE protocol or not and select a mode."
    ::= { ciscoDSGProtocols 7 }

protocolsCtrlIGMP  OBJECT-TYPE
    SYNTAX  INTEGER {
                      disable(1),
                      v3(2),
                      v2(3)
                    }
    MAX-ACCESS read-write
    STATUS  current
    DESCRIPTION
        "Select whether to allow IGMP protocol or not."
    ::= { ciscoDSGProtocols 8 }

protocolslTimeoutsIdleSessonGlobal  OBJECT-TYPE
    SYNTAX  INTEGER (0..1209600)
    MAX-ACCESS read-write
    STATUS  current
    DESCRIPTION
        "Number of seconds after which an idle session will timeout.
         Enter 0 to never timeout. Minimum timeout is 30 seconds."
    ::= { ciscoDSGProtocols 9 }

protocolsCtrlSyslog OBJECT-TYPE
    SYNTAX  INTEGER {
                      disable(1),
                      legacy(2),
                      syslogTcp(3),
                      syslogUdp(4)
                    }
    MAX-ACCESS read-write
    STATUS  current
    DESCRIPTION
        "Select whether to allow Syslog and select a mode."
    ::= { ciscoDSGProtocols 10 }

protocolsCtrlSyslogCfgIpAddr OBJECT-TYPE
    SYNTAX  IpAddress
    MAX-ACCESS read-write
    STATUS  current
    DESCRIPTION
        "Syslog server entry IP Address."
    ::= { ciscoDSGProtocols 11 }

protocolsCtrlSyslogCfgPort OBJECT-TYPE
    SYNTAX  Integer32 (1..65535)
    MAX-ACCESS read-write
    STATUS  current
    DESCRIPTION
        "Syslog server entry port number."
    ::= { ciscoDSGProtocols 12 }
END
