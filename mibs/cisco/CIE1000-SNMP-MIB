-- *****************************************************************
-- SNMP-MIB:  Cisco private MIB
-- ****************************************************************

CIE1000-SNMP-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    cie1000SwitchMgmt FROM CISCO-IE1000-MIB
    CIE1000DisplayString FROM CIE1000-TC
    CIE1000InetAddress FROM CIE1000-TC
    CIE1000RowEditorState FROM CIE1000-TC
    CIE1000Unsigned16 FROM CIE1000-TC
    InetAddressIPv6 FROM INET-ADDRESS-MIB
    Integer32 FROM SNMPv2-SMI
    IpAddress FROM SNMPv2-SMI
    TruthValue FROM SNMPv2-TC
    ;

cie1000SnmpMib MODULE-IDENTITY
    LAST-UPDATED "201604060000Z"
    ORGANIZATION
        "Cisco Systems, Inc."
    CONTACT-INFO
        "Cisco Systems
	 Customer Service

	 Postal: 170 West Tasman Drive
	 San Jose, CA  95134
	 USA

	 Tel: +1 800 553-NETS

	 E-mail: cs-snmp@cisco.com"
    DESCRIPTION
        "This is a private version of SNMP"
    REVISION    "201604060000Z"
    DESCRIPTION
        "Improve descriptions for use of security_model. Change trap source
         table."
    REVISION    "201603070000Z"
    DESCRIPTION
        "Add trap receiver and source tables."
    REVISION    "201602230000Z"
    DESCRIPTION
        "Move IPv6 enabled communities to seperate SnmpConfigCommunity6Table.
         Rename community fields for backward compatibility."
    REVISION    "201602110000Z"
    DESCRIPTION
        "Add SourceIpType as well as SourceIPv6 / SourceIPv6PrefixSize to
         SnmpConfigCommunityTable."
    REVISION    "201512110000Z"
    DESCRIPTION
        "Remove version and communities from vtssSnmpConfigGlobals, and update
         SnmpConfigCommunityTable with security_name"
    REVISION    "201507240000Z"
    DESCRIPTION
        "Correct the valid length of AuthPassword and PrivPassword, and correct
         the description of vtssSnmpConfigViewViewType"
    REVISION    "201407180000Z"
    DESCRIPTION
        "Initial version"
    ::= { cie1000SwitchMgmt 36 }


CIE1000SnmpAuthProtocl ::= TEXTUAL-CONVENTION
    STATUS      current
    DESCRIPTION
        "The SNMP authentication protocol"
    SYNTAX      INTEGER { snmpNoAuthProtocol(0),
                          snmpMD5AuthProtocol(1),
                          snmpSHAAuthProtocol(2) }

CIE1000SnmpPrivProtocl ::= TEXTUAL-CONVENTION
    STATUS      current
    DESCRIPTION
        "The SNMP privacy protocol"
    SYNTAX      INTEGER { snmpNoPrivProtocol(0),
                          snmpDESPrivProtocol(1),
                          snmpAESPrivProtocol(2) }

CIE1000SnmpSecurityLevel ::= TEXTUAL-CONVENTION
    STATUS      current
    DESCRIPTION
        "The SNMP authentication protocol"
    SYNTAX      INTEGER { snmpNoAuthNoPriv(1), snmpAuthNoPriv(2),
                          snmpAuthPriv(3) }

CIE1000SnmpSecurityModel ::= TEXTUAL-CONVENTION
    STATUS      current
    DESCRIPTION
        "The SNMP security model"
    SYNTAX      INTEGER { any(0), v1(1), v2c(2), usm(3) }

CIE1000SnmpTrapNotifyType ::= TEXTUAL-CONVENTION
    STATUS      current
    DESCRIPTION
        "The SNMP trap notify type"
    SYNTAX      INTEGER { trap(0), inform(1) }

CIE1000SnmpVersion ::= TEXTUAL-CONVENTION
    STATUS      current
    DESCRIPTION
        "The version of SNMP"
    SYNTAX      INTEGER { snmpV1(0), snmpV2c(1), snmpV3(2) }

CIE1000SnmpViewType ::= TEXTUAL-CONVENTION
    STATUS      current
    DESCRIPTION
        "The SNMP view type"
    SYNTAX      INTEGER { included(0), excluded(1) }

cie1000SnmpMibObjects OBJECT IDENTIFIER
    ::= { cie1000SnmpMib 1 }

cie1000SnmpConfig OBJECT IDENTIFIER
    ::= { cie1000SnmpMibObjects 2 }

cie1000SnmpConfigGlobals OBJECT IDENTIFIER
    ::= { cie1000SnmpConfig 1 }

cie1000SnmpConfigGlobalsMode OBJECT-TYPE
    SYNTAX      TruthValue
    MAX-ACCESS  read-write
    STATUS      current
    DESCRIPTION
        "Global mode of SNMP."
    ::= { cie1000SnmpConfigGlobals 1 }

cie1000SnmpConfigGlobalsEngineId OBJECT-TYPE
    SYNTAX      OCTET STRING (SIZE(5..32))
    MAX-ACCESS  read-write
    STATUS      current
    DESCRIPTION
        "SNMPv3 engine ID. The size of Engine ID is between 5 ~ 32 bytes.But
         all-zeros and all-'F's are not allowed."
    ::= { cie1000SnmpConfigGlobals 5 }

cie1000SnmpConfigCommunityTable OBJECT-TYPE
    SYNTAX      SEQUENCE OF CIE1000SnmpConfigCommunityEntry
    MAX-ACCESS  not-accessible
    STATUS      current
    DESCRIPTION
        "This is a table for configuring SNMPv3 communities."
    ::= { cie1000SnmpConfig 2 }

cie1000SnmpConfigCommunityEntry OBJECT-TYPE
    SYNTAX      CIE1000SnmpConfigCommunityEntry
    MAX-ACCESS  not-accessible
    STATUS      current
    DESCRIPTION
        "The entry index key is community."
    INDEX       { cie1000SnmpConfigCommunityName,
                  cie1000SnmpConfigCommunitySourceIP,
                  cie1000SnmpConfigCommunitySourceIPPrefixSize }
    ::= { cie1000SnmpConfigCommunityTable 1 }

CIE1000SnmpConfigCommunityEntry ::= SEQUENCE {
    cie1000SnmpConfigCommunityName                CIE1000DisplayString,
    cie1000SnmpConfigCommunitySourceIP            IpAddress,
    cie1000SnmpConfigCommunitySourceIPPrefixSize  Integer32,
    cie1000SnmpConfigCommunitySecret              CIE1000DisplayString,
    cie1000SnmpConfigCommunityAction              CIE1000RowEditorState
}

cie1000SnmpConfigCommunityName OBJECT-TYPE
    SYNTAX      CIE1000DisplayString (SIZE(0..32))
    MAX-ACCESS  accessible-for-notify
    STATUS      current
    DESCRIPTION
        "Name of SNMP community"
    ::= { cie1000SnmpConfigCommunityEntry 1 }

cie1000SnmpConfigCommunitySourceIP OBJECT-TYPE
    SYNTAX      IpAddress
    MAX-ACCESS  accessible-for-notify
    STATUS      current
    DESCRIPTION
        "The SNMP access source IPv4 address"
    ::= { cie1000SnmpConfigCommunityEntry 2 }

cie1000SnmpConfigCommunitySourceIPPrefixSize OBJECT-TYPE
    SYNTAX      Integer32 (0..32)
    MAX-ACCESS  accessible-for-notify
    STATUS      current
    DESCRIPTION
        "The SNMP access source IPv4 prefix size"
    ::= { cie1000SnmpConfigCommunityEntry 3 }

cie1000SnmpConfigCommunitySecret OBJECT-TYPE
    SYNTAX      CIE1000DisplayString
    MAX-ACCESS  read-write
    STATUS      current
    DESCRIPTION
        "The community secret of the SNMP community."
    ::= { cie1000SnmpConfigCommunityEntry 4 }

cie1000SnmpConfigCommunityAction OBJECT-TYPE
    SYNTAX      CIE1000RowEditorState
    MAX-ACCESS  read-write
    STATUS      current
    DESCRIPTION
        "Action"
    ::= { cie1000SnmpConfigCommunityEntry 100 }

cie1000SnmpConfigCommunityTableRowEditor OBJECT IDENTIFIER
    ::= { cie1000SnmpConfig 3 }

cie1000SnmpConfigCommunityTableRowEditorName OBJECT-TYPE
    SYNTAX      CIE1000DisplayString (SIZE(0..32))
    MAX-ACCESS  read-write
    STATUS      current
    DESCRIPTION
        "Name of SNMP community"
    ::= { cie1000SnmpConfigCommunityTableRowEditor 1 }

cie1000SnmpConfigCommunityTableRowEditorSourceIP OBJECT-TYPE
    SYNTAX      IpAddress
    MAX-ACCESS  read-write
    STATUS      current
    DESCRIPTION
        "The SNMP access source IPv4 address"
    ::= { cie1000SnmpConfigCommunityTableRowEditor 2 }

cie1000SnmpConfigCommunityTableRowEditorSourceIPPrefixSize OBJECT-TYPE
    SYNTAX      Integer32 (0..32)
    MAX-ACCESS  read-write
    STATUS      current
    DESCRIPTION
        "The SNMP access source IPv4 prefix size"
    ::= { cie1000SnmpConfigCommunityTableRowEditor 3 }

cie1000SnmpConfigCommunityTableRowEditorSecret OBJECT-TYPE
    SYNTAX      CIE1000DisplayString
    MAX-ACCESS  read-write
    STATUS      current
    DESCRIPTION
        "The community secret of the SNMP community."
    ::= { cie1000SnmpConfigCommunityTableRowEditor 4 }

cie1000SnmpConfigCommunityTableRowEditorAction OBJECT-TYPE
    SYNTAX      CIE1000RowEditorState
    MAX-ACCESS  read-write
    STATUS      current
    DESCRIPTION
        "Action"
    ::= { cie1000SnmpConfigCommunityTableRowEditor 100 }

cie1000SnmpConfigUserTable OBJECT-TYPE
    SYNTAX      SEQUENCE OF CIE1000SnmpConfigUserEntry
    MAX-ACCESS  not-accessible
    STATUS      current
    DESCRIPTION
        "This is a table for configuring SNMPv3 users."
    ::= { cie1000SnmpConfig 4 }

cie1000SnmpConfigUserEntry OBJECT-TYPE
    SYNTAX      CIE1000SnmpConfigUserEntry
    MAX-ACCESS  not-accessible
    STATUS      current
    DESCRIPTION
        "The entry index keys are engine ID and user name."
    INDEX       { cie1000SnmpConfigUserEngineId,
                  cie1000SnmpConfigUserUserName }
    ::= { cie1000SnmpConfigUserTable 1 }

CIE1000SnmpConfigUserEntry ::= SEQUENCE {
    cie1000SnmpConfigUserEngineId       OCTET STRING,
    cie1000SnmpConfigUserUserName       CIE1000DisplayString,
    cie1000SnmpConfigUserSecurityLevel  CIE1000SnmpSecurityLevel,
    cie1000SnmpConfigUserAuthProtocol   CIE1000SnmpAuthProtocl,
    cie1000SnmpConfigUserAuthPassword   CIE1000DisplayString,
    cie1000SnmpConfigUserPrivProtocol   CIE1000SnmpPrivProtocl,
    cie1000SnmpConfigUserPrivPassword   CIE1000DisplayString,
    cie1000SnmpConfigUserAction         CIE1000RowEditorState
}

cie1000SnmpConfigUserEngineId OBJECT-TYPE
    SYNTAX      OCTET STRING (SIZE(5..32))
    MAX-ACCESS  accessible-for-notify
    STATUS      current
    DESCRIPTION
        "SNMPv3 engine ID. The length is between 5 ~ 32 bytes. But all-zeros and
         all-'F's are not allowed."
    ::= { cie1000SnmpConfigUserEntry 1 }

cie1000SnmpConfigUserUserName OBJECT-TYPE
    SYNTAX      CIE1000DisplayString (SIZE(0..32))
    MAX-ACCESS  accessible-for-notify
    STATUS      current
    DESCRIPTION
        "The name of this entry"
    ::= { cie1000SnmpConfigUserEntry 2 }

cie1000SnmpConfigUserSecurityLevel OBJECT-TYPE
    SYNTAX      CIE1000SnmpSecurityLevel
    MAX-ACCESS  read-write
    STATUS      current
    DESCRIPTION
        "The security level of this entry. The object is read-only if the entry
         is existent."
    ::= { cie1000SnmpConfigUserEntry 3 }

cie1000SnmpConfigUserAuthProtocol OBJECT-TYPE
    SYNTAX      CIE1000SnmpAuthProtocl
    MAX-ACCESS  read-write
    STATUS      current
    DESCRIPTION
        "The authentication protocol of this entry. The object is read-only if
         the entry is existent."
    ::= { cie1000SnmpConfigUserEntry 4 }

cie1000SnmpConfigUserAuthPassword OBJECT-TYPE
    SYNTAX      CIE1000DisplayString
    MAX-ACCESS  read-write
    STATUS      current
    DESCRIPTION
        "The authentication password of this entry. Acceptable string length
         range from 8 to 40.The object is read-only if the entry is existent."
    ::= { cie1000SnmpConfigUserEntry 5 }

cie1000SnmpConfigUserPrivProtocol OBJECT-TYPE
    SYNTAX      CIE1000SnmpPrivProtocl
    MAX-ACCESS  read-write
    STATUS      current
    DESCRIPTION
        "The privacy protocol of this entry. The object is read-only if the
         entry is existent."
    ::= { cie1000SnmpConfigUserEntry 6 }

cie1000SnmpConfigUserPrivPassword OBJECT-TYPE
    SYNTAX      CIE1000DisplayString
    MAX-ACCESS  read-write
    STATUS      current
    DESCRIPTION
        "The privacy password of this entry. Acceptable string length range from
         8 to 32.The object is read-only if the entry is existent."
    ::= { cie1000SnmpConfigUserEntry 7 }

cie1000SnmpConfigUserAction OBJECT-TYPE
    SYNTAX      CIE1000RowEditorState
    MAX-ACCESS  read-write
    STATUS      current
    DESCRIPTION
        "Action"
    ::= { cie1000SnmpConfigUserEntry 100 }

cie1000SnmpConfigUserTableRowEditor OBJECT IDENTIFIER
    ::= { cie1000SnmpConfig 5 }

cie1000SnmpConfigUserTableRowEditorEngineId OBJECT-TYPE
    SYNTAX      OCTET STRING (SIZE(5..32))
    MAX-ACCESS  read-write
    STATUS      current
    DESCRIPTION
        "SNMPv3 engine ID. The length is between 5 ~ 32 bytes. But all-zeros and
         all-'F's are not allowed."
    ::= { cie1000SnmpConfigUserTableRowEditor 1 }

cie1000SnmpConfigUserTableRowEditorUserName OBJECT-TYPE
    SYNTAX      CIE1000DisplayString (SIZE(0..32))
    MAX-ACCESS  read-write
    STATUS      current
    DESCRIPTION
        "The name of this entry"
    ::= { cie1000SnmpConfigUserTableRowEditor 2 }

cie1000SnmpConfigUserTableRowEditorSecurityLevel OBJECT-TYPE
    SYNTAX      CIE1000SnmpSecurityLevel
    MAX-ACCESS  read-write
    STATUS      current
    DESCRIPTION
        "The security level of this entry. The object is read-only if the entry
         is existent."
    ::= { cie1000SnmpConfigUserTableRowEditor 3 }

cie1000SnmpConfigUserTableRowEditorAuthProtocol OBJECT-TYPE
    SYNTAX      CIE1000SnmpAuthProtocl
    MAX-ACCESS  read-write
    STATUS      current
    DESCRIPTION
        "The authentication protocol of this entry. The object is read-only if
         the entry is existent."
    ::= { cie1000SnmpConfigUserTableRowEditor 4 }

cie1000SnmpConfigUserTableRowEditorAuthPassword OBJECT-TYPE
    SYNTAX      CIE1000DisplayString
    MAX-ACCESS  read-write
    STATUS      current
    DESCRIPTION
        "The authentication password of this entry. Acceptable string length
         range from 8 to 40.The object is read-only if the entry is existent."
    ::= { cie1000SnmpConfigUserTableRowEditor 5 }

cie1000SnmpConfigUserTableRowEditorPrivProtocol OBJECT-TYPE
    SYNTAX      CIE1000SnmpPrivProtocl
    MAX-ACCESS  read-write
    STATUS      current
    DESCRIPTION
        "The privacy protocol of this entry. The object is read-only if the
         entry is existent."
    ::= { cie1000SnmpConfigUserTableRowEditor 6 }

cie1000SnmpConfigUserTableRowEditorPrivPassword OBJECT-TYPE
    SYNTAX      CIE1000DisplayString
    MAX-ACCESS  read-write
    STATUS      current
    DESCRIPTION
        "The privacy password of this entry. Acceptable string length range from
         8 to 32.The object is read-only if the entry is existent."
    ::= { cie1000SnmpConfigUserTableRowEditor 7 }

cie1000SnmpConfigUserTableRowEditorAction OBJECT-TYPE
    SYNTAX      CIE1000RowEditorState
    MAX-ACCESS  read-write
    STATUS      current
    DESCRIPTION
        "Action"
    ::= { cie1000SnmpConfigUserTableRowEditor 100 }

cie1000SnmpConfigUserToAccessGroupTable OBJECT-TYPE
    SYNTAX      SEQUENCE OF CIE1000SnmpConfigUserToAccessGroupEntry
    MAX-ACCESS  not-accessible
    STATUS      current
    DESCRIPTION
        "This is a table for configuring SNMPv3 groups."
    ::= { cie1000SnmpConfig 6 }

cie1000SnmpConfigUserToAccessGroupEntry OBJECT-TYPE
    SYNTAX      CIE1000SnmpConfigUserToAccessGroupEntry
    MAX-ACCESS  not-accessible
    STATUS      current
    DESCRIPTION
        "The entry index keys are security model and user/community name."
    INDEX       { cie1000SnmpConfigUserToAccessGroupSecurityModel,
                  cie1000SnmpConfigUserToAccessGroupUserOrCommunity }
    ::= { cie1000SnmpConfigUserToAccessGroupTable 1 }

CIE1000SnmpConfigUserToAccessGroupEntry ::= SEQUENCE {
    cie1000SnmpConfigUserToAccessGroupSecurityModel    CIE1000SnmpSecurityModel,
    cie1000SnmpConfigUserToAccessGroupUserOrCommunity  CIE1000DisplayString,
    cie1000SnmpConfigUserToAccessGroupAccessGroupName  CIE1000DisplayString,
    cie1000SnmpConfigUserToAccessGroupAction           CIE1000RowEditorState
}

cie1000SnmpConfigUserToAccessGroupSecurityModel OBJECT-TYPE
    SYNTAX      CIE1000SnmpSecurityModel
    MAX-ACCESS  accessible-for-notify
    STATUS      current
    DESCRIPTION
        "The security model of this entry. When v1 or v2c UserOrCommunity maps
         to community, when v3 UserOrCommunity maps to user. The value 'any' is
         not allowed."
    ::= { cie1000SnmpConfigUserToAccessGroupEntry 1 }

cie1000SnmpConfigUserToAccessGroupUserOrCommunity OBJECT-TYPE
    SYNTAX      CIE1000DisplayString (SIZE(0..32))
    MAX-ACCESS  accessible-for-notify
    STATUS      current
    DESCRIPTION
        "The security name (user or community) of this entry"
    ::= { cie1000SnmpConfigUserToAccessGroupEntry 2 }

cie1000SnmpConfigUserToAccessGroupAccessGroupName OBJECT-TYPE
    SYNTAX      CIE1000DisplayString (SIZE(0..32))
    MAX-ACCESS  read-write
    STATUS      current
    DESCRIPTION
        "The access group name of this entry."
    ::= { cie1000SnmpConfigUserToAccessGroupEntry 3 }

cie1000SnmpConfigUserToAccessGroupAction OBJECT-TYPE
    SYNTAX      CIE1000RowEditorState
    MAX-ACCESS  read-write
    STATUS      current
    DESCRIPTION
        "Action"
    ::= { cie1000SnmpConfigUserToAccessGroupEntry 100 }

cie1000SnmpConfigUserToAccessGroupTableRowEditor OBJECT IDENTIFIER
    ::= { cie1000SnmpConfig 7 }

cie1000SnmpConfigUserToAccessGroupTableRowEditorSecurityModel OBJECT-TYPE
    SYNTAX      CIE1000SnmpSecurityModel
    MAX-ACCESS  read-write
    STATUS      current
    DESCRIPTION
        "The security model of this entry. When v1 or v2c UserOrCommunity maps
         to community, when v3 UserOrCommunity maps to user. The value 'any' is
         not allowed."
    ::= { cie1000SnmpConfigUserToAccessGroupTableRowEditor 1 }

cie1000SnmpConfigUserToAccessGroupTableRowEditorUserOrCommunity OBJECT-TYPE
    SYNTAX      CIE1000DisplayString (SIZE(0..32))
    MAX-ACCESS  read-write
    STATUS      current
    DESCRIPTION
        "The security name (user or community) of this entry"
    ::= { cie1000SnmpConfigUserToAccessGroupTableRowEditor 2 }

cie1000SnmpConfigUserToAccessGroupTableRowEditorAccessGroupName OBJECT-TYPE
    SYNTAX      CIE1000DisplayString (SIZE(0..32))
    MAX-ACCESS  read-write
    STATUS      current
    DESCRIPTION
        "The access group name of this entry."
    ::= { cie1000SnmpConfigUserToAccessGroupTableRowEditor 3 }

cie1000SnmpConfigUserToAccessGroupTableRowEditorAction OBJECT-TYPE
    SYNTAX      CIE1000RowEditorState
    MAX-ACCESS  read-write
    STATUS      current
    DESCRIPTION
        "Action"
    ::= { cie1000SnmpConfigUserToAccessGroupTableRowEditor 100 }

cie1000SnmpConfigAccessGroupTable OBJECT-TYPE
    SYNTAX      SEQUENCE OF CIE1000SnmpConfigAccessGroupEntry
    MAX-ACCESS  not-accessible
    STATUS      current
    DESCRIPTION
        "This is a table for configuring SNMPv3 accesse groups."
    ::= { cie1000SnmpConfig 8 }

cie1000SnmpConfigAccessGroupEntry OBJECT-TYPE
    SYNTAX      CIE1000SnmpConfigAccessGroupEntry
    MAX-ACCESS  not-accessible
    STATUS      current
    DESCRIPTION
        "The entry index keys are access group name, security model and security
         level."
    INDEX       { cie1000SnmpConfigAccessGroupAccessGroupName,
                  cie1000SnmpConfigAccessGroupSecurityModel,
                  cie1000SnmpConfigAccessGroupSecurityLevel }
    ::= { cie1000SnmpConfigAccessGroupTable 1 }

CIE1000SnmpConfigAccessGroupEntry ::= SEQUENCE {
    cie1000SnmpConfigAccessGroupAccessGroupName  CIE1000DisplayString,
    cie1000SnmpConfigAccessGroupSecurityModel    CIE1000SnmpSecurityModel,
    cie1000SnmpConfigAccessGroupSecurityLevel    CIE1000SnmpSecurityLevel,
    cie1000SnmpConfigAccessGroupReadViewName     CIE1000DisplayString,
    cie1000SnmpConfigAccessGroupWriteViewName    CIE1000DisplayString,
    cie1000SnmpConfigAccessGroupAction           CIE1000RowEditorState
}

cie1000SnmpConfigAccessGroupAccessGroupName OBJECT-TYPE
    SYNTAX      CIE1000DisplayString (SIZE(0..32))
    MAX-ACCESS  accessible-for-notify
    STATUS      current
    DESCRIPTION
        "The access group name of this entry"
    ::= { cie1000SnmpConfigAccessGroupEntry 1 }

cie1000SnmpConfigAccessGroupSecurityModel OBJECT-TYPE
    SYNTAX      CIE1000SnmpSecurityModel
    MAX-ACCESS  accessible-for-notify
    STATUS      current
    DESCRIPTION
        "The security model of this entry. Can be v1, v2c, usm or any."
    ::= { cie1000SnmpConfigAccessGroupEntry 2 }

cie1000SnmpConfigAccessGroupSecurityLevel OBJECT-TYPE
    SYNTAX      CIE1000SnmpSecurityLevel
    MAX-ACCESS  accessible-for-notify
    STATUS      current
    DESCRIPTION
        "The security level of this entry"
    ::= { cie1000SnmpConfigAccessGroupEntry 3 }

cie1000SnmpConfigAccessGroupReadViewName OBJECT-TYPE
    SYNTAX      CIE1000DisplayString (SIZE(0..32))
    MAX-ACCESS  read-write
    STATUS      current
    DESCRIPTION
        "The name of the MIB view defining the MIB objects for which this
         request may request the current values."
    ::= { cie1000SnmpConfigAccessGroupEntry 4 }

cie1000SnmpConfigAccessGroupWriteViewName OBJECT-TYPE
    SYNTAX      CIE1000DisplayString (SIZE(0..32))
    MAX-ACCESS  read-write
    STATUS      current
    DESCRIPTION
        "The name of the MIB view defining the MIB objects for which this
         request may potentially set new values."
    ::= { cie1000SnmpConfigAccessGroupEntry 5 }

cie1000SnmpConfigAccessGroupAction OBJECT-TYPE
    SYNTAX      CIE1000RowEditorState
    MAX-ACCESS  read-write
    STATUS      current
    DESCRIPTION
        "Action"
    ::= { cie1000SnmpConfigAccessGroupEntry 100 }

cie1000SnmpConfigAccessGroupTableRowEditor OBJECT IDENTIFIER
    ::= { cie1000SnmpConfig 9 }

cie1000SnmpConfigAccessGroupTableRowEditorAccessGroupName OBJECT-TYPE
    SYNTAX      CIE1000DisplayString (SIZE(0..32))
    MAX-ACCESS  read-write
    STATUS      current
    DESCRIPTION
        "The access group name of this entry"
    ::= { cie1000SnmpConfigAccessGroupTableRowEditor 1 }

cie1000SnmpConfigAccessGroupTableRowEditorSecurityModel OBJECT-TYPE
    SYNTAX      CIE1000SnmpSecurityModel
    MAX-ACCESS  read-write
    STATUS      current
    DESCRIPTION
        "The security model of this entry. Can be v1, v2c, usm or any."
    ::= { cie1000SnmpConfigAccessGroupTableRowEditor 2 }

cie1000SnmpConfigAccessGroupTableRowEditorSecurityLevel OBJECT-TYPE
    SYNTAX      CIE1000SnmpSecurityLevel
    MAX-ACCESS  read-write
    STATUS      current
    DESCRIPTION
        "The security level of this entry"
    ::= { cie1000SnmpConfigAccessGroupTableRowEditor 3 }

cie1000SnmpConfigAccessGroupTableRowEditorReadViewName OBJECT-TYPE
    SYNTAX      CIE1000DisplayString (SIZE(0..32))
    MAX-ACCESS  read-write
    STATUS      current
    DESCRIPTION
        "The name of the MIB view defining the MIB objects for which this
         request may request the current values."
    ::= { cie1000SnmpConfigAccessGroupTableRowEditor 4 }

cie1000SnmpConfigAccessGroupTableRowEditorWriteViewName OBJECT-TYPE
    SYNTAX      CIE1000DisplayString (SIZE(0..32))
    MAX-ACCESS  read-write
    STATUS      current
    DESCRIPTION
        "The name of the MIB view defining the MIB objects for which this
         request may potentially set new values."
    ::= { cie1000SnmpConfigAccessGroupTableRowEditor 5 }

cie1000SnmpConfigAccessGroupTableRowEditorAction OBJECT-TYPE
    SYNTAX      CIE1000RowEditorState
    MAX-ACCESS  read-write
    STATUS      current
    DESCRIPTION
        "Action"
    ::= { cie1000SnmpConfigAccessGroupTableRowEditor 100 }

cie1000SnmpConfigViewTable OBJECT-TYPE
    SYNTAX      SEQUENCE OF CIE1000SnmpConfigViewEntry
    MAX-ACCESS  not-accessible
    STATUS      current
    DESCRIPTION
        "This is a table for configuring SNMPv3 views."
    ::= { cie1000SnmpConfig 10 }

cie1000SnmpConfigViewEntry OBJECT-TYPE
    SYNTAX      CIE1000SnmpConfigViewEntry
    MAX-ACCESS  not-accessible
    STATUS      current
    DESCRIPTION
        "The entry index keys are name and subtree."
    INDEX       { cie1000SnmpConfigViewName,
                  cie1000SnmpConfigViewSubtree }
    ::= { cie1000SnmpConfigViewTable 1 }

CIE1000SnmpConfigViewEntry ::= SEQUENCE {
    cie1000SnmpConfigViewName      CIE1000DisplayString,
    cie1000SnmpConfigViewSubtree   CIE1000DisplayString,
    cie1000SnmpConfigViewViewType  CIE1000SnmpViewType,
    cie1000SnmpConfigViewAction    CIE1000RowEditorState
}

cie1000SnmpConfigViewName OBJECT-TYPE
    SYNTAX      CIE1000DisplayString (SIZE(0..32))
    MAX-ACCESS  accessible-for-notify
    STATUS      current
    DESCRIPTION
        "The name of this entry"
    ::= { cie1000SnmpConfigViewEntry 1 }

cie1000SnmpConfigViewSubtree OBJECT-TYPE
    SYNTAX      CIE1000DisplayString (SIZE(0..64))
    MAX-ACCESS  accessible-for-notify
    STATUS      current
    DESCRIPTION
        "The OID defining the root of the subtree to add to the named view."
    ::= { cie1000SnmpConfigViewEntry 2 }

cie1000SnmpConfigViewViewType OBJECT-TYPE
    SYNTAX      CIE1000SnmpViewType
    MAX-ACCESS  read-write
    STATUS      current
    DESCRIPTION
        "The view type of this entry. The value can be set to 'included' or
         'excluded','included' indicates the view subtree is visible, otherwise
         the view subtree is invisible."
    ::= { cie1000SnmpConfigViewEntry 3 }

cie1000SnmpConfigViewAction OBJECT-TYPE
    SYNTAX      CIE1000RowEditorState
    MAX-ACCESS  read-write
    STATUS      current
    DESCRIPTION
        "Action"
    ::= { cie1000SnmpConfigViewEntry 100 }

cie1000SnmpConfigViewTableRowEditor OBJECT IDENTIFIER
    ::= { cie1000SnmpConfig 11 }

cie1000SnmpConfigViewTableRowEditorName OBJECT-TYPE
    SYNTAX      CIE1000DisplayString (SIZE(0..32))
    MAX-ACCESS  read-write
    STATUS      current
    DESCRIPTION
        "The name of this entry"
    ::= { cie1000SnmpConfigViewTableRowEditor 1 }

cie1000SnmpConfigViewTableRowEditorSubtree OBJECT-TYPE
    SYNTAX      CIE1000DisplayString (SIZE(0..64))
    MAX-ACCESS  read-write
    STATUS      current
    DESCRIPTION
        "The OID defining the root of the subtree to add to the named view."
    ::= { cie1000SnmpConfigViewTableRowEditor 2 }

cie1000SnmpConfigViewTableRowEditorViewType OBJECT-TYPE
    SYNTAX      CIE1000SnmpViewType
    MAX-ACCESS  read-write
    STATUS      current
    DESCRIPTION
        "The view type of this entry. The value can be set to 'included' or
         'excluded','included' indicates the view subtree is visible, otherwise
         the view subtree is invisible."
    ::= { cie1000SnmpConfigViewTableRowEditor 3 }

cie1000SnmpConfigViewTableRowEditorAction OBJECT-TYPE
    SYNTAX      CIE1000RowEditorState
    MAX-ACCESS  read-write
    STATUS      current
    DESCRIPTION
        "Action"
    ::= { cie1000SnmpConfigViewTableRowEditor 100 }

cie1000SnmpConfigCommunity6Table OBJECT-TYPE
    SYNTAX      SEQUENCE OF CIE1000SnmpConfigCommunity6Entry
    MAX-ACCESS  not-accessible
    STATUS      current
    DESCRIPTION
        "This is a table for configuring SNMPv3 communities for IPv6."
    ::= { cie1000SnmpConfig 12 }

cie1000SnmpConfigCommunity6Entry OBJECT-TYPE
    SYNTAX      CIE1000SnmpConfigCommunity6Entry
    MAX-ACCESS  not-accessible
    STATUS      current
    DESCRIPTION
        "The entry index key is community."
    INDEX       { cie1000SnmpConfigCommunity6Name,
                  cie1000SnmpConfigCommunity6SourceIPv6,
                  cie1000SnmpConfigCommunity6SourceIPv6PrefixSize }
    ::= { cie1000SnmpConfigCommunity6Table 1 }

CIE1000SnmpConfigCommunity6Entry ::= SEQUENCE {
    cie1000SnmpConfigCommunity6Name                  CIE1000DisplayString,
    cie1000SnmpConfigCommunity6SourceIPv6            InetAddressIPv6,
    cie1000SnmpConfigCommunity6SourceIPv6PrefixSize  Integer32,
    cie1000SnmpConfigCommunity6Secret                CIE1000DisplayString,
    cie1000SnmpConfigCommunity6Action                CIE1000RowEditorState
}

cie1000SnmpConfigCommunity6Name OBJECT-TYPE
    SYNTAX      CIE1000DisplayString (SIZE(0..32))
    MAX-ACCESS  accessible-for-notify
    STATUS      current
    DESCRIPTION
        "Name of SNMP community"
    ::= { cie1000SnmpConfigCommunity6Entry 1 }

cie1000SnmpConfigCommunity6SourceIPv6 OBJECT-TYPE
    SYNTAX      InetAddressIPv6
    MAX-ACCESS  accessible-for-notify
    STATUS      current
    DESCRIPTION
        "The SNMP access source IPv6 address"
    ::= { cie1000SnmpConfigCommunity6Entry 2 }

cie1000SnmpConfigCommunity6SourceIPv6PrefixSize OBJECT-TYPE
    SYNTAX      Integer32 (0..128)
    MAX-ACCESS  accessible-for-notify
    STATUS      current
    DESCRIPTION
        "The SNMP access source IPv6 prefix size"
    ::= { cie1000SnmpConfigCommunity6Entry 3 }

cie1000SnmpConfigCommunity6Secret OBJECT-TYPE
    SYNTAX      CIE1000DisplayString
    MAX-ACCESS  read-write
    STATUS      current
    DESCRIPTION
        "The community secret of the SNMP community."
    ::= { cie1000SnmpConfigCommunity6Entry 4 }

cie1000SnmpConfigCommunity6Action OBJECT-TYPE
    SYNTAX      CIE1000RowEditorState
    MAX-ACCESS  read-write
    STATUS      current
    DESCRIPTION
        "Action"
    ::= { cie1000SnmpConfigCommunity6Entry 100 }

cie1000SnmpConfigCommunity6TableRowEditor OBJECT IDENTIFIER
    ::= { cie1000SnmpConfig 13 }

cie1000SnmpConfigCommunity6TableRowEditorName OBJECT-TYPE
    SYNTAX      CIE1000DisplayString (SIZE(0..32))
    MAX-ACCESS  read-write
    STATUS      current
    DESCRIPTION
        "Name of SNMP community"
    ::= { cie1000SnmpConfigCommunity6TableRowEditor 1 }

cie1000SnmpConfigCommunity6TableRowEditorSourceIPv6 OBJECT-TYPE
    SYNTAX      InetAddressIPv6
    MAX-ACCESS  read-write
    STATUS      current
    DESCRIPTION
        "The SNMP access source IPv6 address"
    ::= { cie1000SnmpConfigCommunity6TableRowEditor 2 }

cie1000SnmpConfigCommunity6TableRowEditorSourceIPv6PrefixSize OBJECT-TYPE
    SYNTAX      Integer32 (0..128)
    MAX-ACCESS  read-write
    STATUS      current
    DESCRIPTION
        "The SNMP access source IPv6 prefix size"
    ::= { cie1000SnmpConfigCommunity6TableRowEditor 3 }

cie1000SnmpConfigCommunity6TableRowEditorSecret OBJECT-TYPE
    SYNTAX      CIE1000DisplayString
    MAX-ACCESS  read-write
    STATUS      current
    DESCRIPTION
        "The community secret of the SNMP community."
    ::= { cie1000SnmpConfigCommunity6TableRowEditor 4 }

cie1000SnmpConfigCommunity6TableRowEditorAction OBJECT-TYPE
    SYNTAX      CIE1000RowEditorState
    MAX-ACCESS  read-write
    STATUS      current
    DESCRIPTION
        "Action"
    ::= { cie1000SnmpConfigCommunity6TableRowEditor 100 }

cie1000SnmpConfigTrapReceiverTable OBJECT-TYPE
    SYNTAX      SEQUENCE OF CIE1000SnmpConfigTrapReceiverEntry
    MAX-ACCESS  not-accessible
    STATUS      current
    DESCRIPTION
        "This is a table for configuring SNMP trap receivers."
    ::= { cie1000SnmpConfig 20 }

cie1000SnmpConfigTrapReceiverEntry OBJECT-TYPE
    SYNTAX      CIE1000SnmpConfigTrapReceiverEntry
    MAX-ACCESS  not-accessible
    STATUS      current
    DESCRIPTION
        "The entry index keys is trap receiver name."
    INDEX       { cie1000SnmpConfigTrapReceiverName }
    ::= { cie1000SnmpConfigTrapReceiverTable 1 }

CIE1000SnmpConfigTrapReceiverEntry ::= SEQUENCE {
    cie1000SnmpConfigTrapReceiverName        CIE1000DisplayString,
    cie1000SnmpConfigTrapReceiverEnable      TruthValue,
    cie1000SnmpConfigTrapReceiverAddress     CIE1000InetAddress,
    cie1000SnmpConfigTrapReceiverPort        CIE1000Unsigned16,
    cie1000SnmpConfigTrapReceiverVersion     CIE1000SnmpVersion,
    cie1000SnmpConfigTrapReceiverCommunity   CIE1000DisplayString,
    cie1000SnmpConfigTrapReceiverNotifyType  CIE1000SnmpTrapNotifyType,
    cie1000SnmpConfigTrapReceiverTimeout     Integer32,
    cie1000SnmpConfigTrapReceiverRetries     Integer32,
    cie1000SnmpConfigTrapReceiverEngineId    OCTET STRING,
    cie1000SnmpConfigTrapReceiverUserName    CIE1000DisplayString,
    cie1000SnmpConfigTrapReceiverAction      CIE1000RowEditorState
}

cie1000SnmpConfigTrapReceiverName OBJECT-TYPE
    SYNTAX      CIE1000DisplayString (SIZE(0..32))
    MAX-ACCESS  accessible-for-notify
    STATUS      current
    DESCRIPTION
        "Name of trap receiver"
    ::= { cie1000SnmpConfigTrapReceiverEntry 1 }

cie1000SnmpConfigTrapReceiverEnable OBJECT-TYPE
    SYNTAX      TruthValue
    MAX-ACCESS  read-write
    STATUS      current
    DESCRIPTION
        "SNMP trap receiver enabled."
    ::= { cie1000SnmpConfigTrapReceiverEntry 2 }

cie1000SnmpConfigTrapReceiverAddress OBJECT-TYPE
    SYNTAX      CIE1000InetAddress
    MAX-ACCESS  read-write
    STATUS      current
    DESCRIPTION
        "Internet address of the SNMP trap receiver."
    ::= { cie1000SnmpConfigTrapReceiverEntry 3 }

cie1000SnmpConfigTrapReceiverPort OBJECT-TYPE
    SYNTAX      CIE1000Unsigned16
    MAX-ACCESS  read-write
    STATUS      current
    DESCRIPTION
        "Port number of the SNMP trap receiver."
    ::= { cie1000SnmpConfigTrapReceiverEntry 4 }

cie1000SnmpConfigTrapReceiverVersion OBJECT-TYPE
    SYNTAX      CIE1000SnmpVersion
    MAX-ACCESS  read-write
    STATUS      current
    DESCRIPTION
        "SNMP Version. The supported versions are snmpV1, snmpV2c, snmpV3."
    ::= { cie1000SnmpConfigTrapReceiverEntry 5 }

cie1000SnmpConfigTrapReceiverCommunity OBJECT-TYPE
    SYNTAX      CIE1000DisplayString
    MAX-ACCESS  read-write
    STATUS      current
    DESCRIPTION
        "The community secret to use for SNMP traps."
    ::= { cie1000SnmpConfigTrapReceiverEntry 6 }

cie1000SnmpConfigTrapReceiverNotifyType OBJECT-TYPE
    SYNTAX      CIE1000SnmpTrapNotifyType
    MAX-ACCESS  read-write
    STATUS      current
    DESCRIPTION
        "Notification type: trap or inform."
    ::= { cie1000SnmpConfigTrapReceiverEntry 7 }

cie1000SnmpConfigTrapReceiverTimeout OBJECT-TYPE
    SYNTAX      Integer32 (1..2147)
    MAX-ACCESS  read-write
    STATUS      current
    DESCRIPTION
        "Timeout. Only relevant for informs."
    ::= { cie1000SnmpConfigTrapReceiverEntry 8 }

cie1000SnmpConfigTrapReceiverRetries OBJECT-TYPE
    SYNTAX      Integer32 (1..255)
    MAX-ACCESS  read-write
    STATUS      current
    DESCRIPTION
        "Retries. Only relevant for informs."
    ::= { cie1000SnmpConfigTrapReceiverEntry 9 }

cie1000SnmpConfigTrapReceiverEngineId OBJECT-TYPE
    SYNTAX      OCTET STRING (SIZE(5..32))
    MAX-ACCESS  read-write
    STATUS      current
    DESCRIPTION
        "SNMPv3 engine ID. The length is between 5 ~ 32 bytes. But all-zeros and
         all-'F's are not allowed."
    ::= { cie1000SnmpConfigTrapReceiverEntry 10 }

cie1000SnmpConfigTrapReceiverUserName OBJECT-TYPE
    SYNTAX      CIE1000DisplayString (SIZE(0..32))
    MAX-ACCESS  read-write
    STATUS      current
    DESCRIPTION
        "SNMPv3 user name."
    ::= { cie1000SnmpConfigTrapReceiverEntry 11 }

cie1000SnmpConfigTrapReceiverAction OBJECT-TYPE
    SYNTAX      CIE1000RowEditorState
    MAX-ACCESS  read-write
    STATUS      current
    DESCRIPTION
        "Action"
    ::= { cie1000SnmpConfigTrapReceiverEntry 100 }

cie1000SnmpConfigTrapReceiverTableRowEditor OBJECT IDENTIFIER
    ::= { cie1000SnmpConfig 21 }

cie1000SnmpConfigTrapReceiverTableRowEditorName OBJECT-TYPE
    SYNTAX      CIE1000DisplayString (SIZE(0..32))
    MAX-ACCESS  read-write
    STATUS      current
    DESCRIPTION
        "Name of trap receiver"
    ::= { cie1000SnmpConfigTrapReceiverTableRowEditor 1 }

cie1000SnmpConfigTrapReceiverTableRowEditorEnable OBJECT-TYPE
    SYNTAX      TruthValue
    MAX-ACCESS  read-write
    STATUS      current
    DESCRIPTION
        "SNMP trap receiver enabled."
    ::= { cie1000SnmpConfigTrapReceiverTableRowEditor 2 }

cie1000SnmpConfigTrapReceiverTableRowEditorAddress OBJECT-TYPE
    SYNTAX      CIE1000InetAddress
    MAX-ACCESS  read-write
    STATUS      current
    DESCRIPTION
        "Internet address of the SNMP trap receiver."
    ::= { cie1000SnmpConfigTrapReceiverTableRowEditor 3 }

cie1000SnmpConfigTrapReceiverTableRowEditorPort OBJECT-TYPE
    SYNTAX      CIE1000Unsigned16
    MAX-ACCESS  read-write
    STATUS      current
    DESCRIPTION
        "Port number of the SNMP trap receiver."
    ::= { cie1000SnmpConfigTrapReceiverTableRowEditor 4 }

cie1000SnmpConfigTrapReceiverTableRowEditorVersion OBJECT-TYPE
    SYNTAX      CIE1000SnmpVersion
    MAX-ACCESS  read-write
    STATUS      current
    DESCRIPTION
        "SNMP Version. The supported versions are snmpV1, snmpV2c, snmpV3."
    ::= { cie1000SnmpConfigTrapReceiverTableRowEditor 5 }

cie1000SnmpConfigTrapReceiverTableRowEditorCommunity OBJECT-TYPE
    SYNTAX      CIE1000DisplayString
    MAX-ACCESS  read-write
    STATUS      current
    DESCRIPTION
        "The community secret to use for SNMP traps."
    ::= { cie1000SnmpConfigTrapReceiverTableRowEditor 6 }

cie1000SnmpConfigTrapReceiverTableRowEditorNotifyType OBJECT-TYPE
    SYNTAX      CIE1000SnmpTrapNotifyType
    MAX-ACCESS  read-write
    STATUS      current
    DESCRIPTION
        "Notification type: trap or inform."
    ::= { cie1000SnmpConfigTrapReceiverTableRowEditor 7 }

cie1000SnmpConfigTrapReceiverTableRowEditorTimeout OBJECT-TYPE
    SYNTAX      Integer32 (1..2147)
    MAX-ACCESS  read-write
    STATUS      current
    DESCRIPTION
        "Timeout. Only relevant for informs."
    ::= { cie1000SnmpConfigTrapReceiverTableRowEditor 8 }

cie1000SnmpConfigTrapReceiverTableRowEditorRetries OBJECT-TYPE
    SYNTAX      Integer32 (1..255)
    MAX-ACCESS  read-write
    STATUS      current
    DESCRIPTION
        "Retries. Only relevant for informs."
    ::= { cie1000SnmpConfigTrapReceiverTableRowEditor 9 }

cie1000SnmpConfigTrapReceiverTableRowEditorEngineId OBJECT-TYPE
    SYNTAX      OCTET STRING (SIZE(5..32))
    MAX-ACCESS  read-write
    STATUS      current
    DESCRIPTION
        "SNMPv3 engine ID. The length is between 5 ~ 32 bytes. But all-zeros and
         all-'F's are not allowed."
    ::= { cie1000SnmpConfigTrapReceiverTableRowEditor 10 }

cie1000SnmpConfigTrapReceiverTableRowEditorUserName OBJECT-TYPE
    SYNTAX      CIE1000DisplayString (SIZE(0..32))
    MAX-ACCESS  read-write
    STATUS      current
    DESCRIPTION
        "SNMPv3 user name."
    ::= { cie1000SnmpConfigTrapReceiverTableRowEditor 11 }

cie1000SnmpConfigTrapReceiverTableRowEditorAction OBJECT-TYPE
    SYNTAX      CIE1000RowEditorState
    MAX-ACCESS  read-write
    STATUS      current
    DESCRIPTION
        "Action"
    ::= { cie1000SnmpConfigTrapReceiverTableRowEditor 100 }

cie1000SnmpConfigTrapSourceTable OBJECT-TYPE
    SYNTAX      SEQUENCE OF CIE1000SnmpConfigTrapSourceEntry
    MAX-ACCESS  not-accessible
    STATUS      current
    DESCRIPTION
        "This is a table for configuring SNMP trap sources.

         A trap is sent for the given trap source if at least one filter with
         filter_type included matches the filter, and no filters with
         filter_type excluded matches."
    ::= { cie1000SnmpConfig 22 }

cie1000SnmpConfigTrapSourceEntry OBJECT-TYPE
    SYNTAX      CIE1000SnmpConfigTrapSourceEntry
    MAX-ACCESS  not-accessible
    STATUS      current
    DESCRIPTION
        "The entry index keys is trap source name and a filter ID.

         The filter matches an index OID if the index_filter matches the OID of
         the index taking index_mask into account.

         Each bit of index_mask corresponds to a sub-identifier of index_filter,
         with the most significant bit of the i-th octet of this octet string
         value (extended if necessary) corresponding to the (8*i - 7)-th
         sub-identifier.

         Each bit of index_mask specifies whether or not the corresponding
         sub-identifiers must match when determining if an OID matches; a '1'
         indicates that an exact match must occur; a '0' indicates 'wild card'.

         If the value of index_mask is M bits long and there are more than M
         sub-identifiers in index_filter, then the bit mask is extended with 1's
         to be the required length."
    INDEX       { cie1000SnmpConfigTrapSourceName,
                  cie1000SnmpConfigTrapSourceIndexFilterID }
    ::= { cie1000SnmpConfigTrapSourceTable 1 }

CIE1000SnmpConfigTrapSourceEntry ::= SEQUENCE {
    cie1000SnmpConfigTrapSourceName           CIE1000DisplayString,
    cie1000SnmpConfigTrapSourceIndexFilterID  Integer32,
    cie1000SnmpConfigTrapSourceIndexFilter    OCTET STRING,
    cie1000SnmpConfigTrapSourceIndexMask      OCTET STRING,
    cie1000SnmpConfigTrapSourceFilterType     CIE1000SnmpViewType,
    cie1000SnmpConfigTrapSourceAction         CIE1000RowEditorState
}

cie1000SnmpConfigTrapSourceName OBJECT-TYPE
    SYNTAX      CIE1000DisplayString (SIZE(0..64))
    MAX-ACCESS  accessible-for-notify
    STATUS      current
    DESCRIPTION
        "SNMP trap event/table name"
    ::= { cie1000SnmpConfigTrapSourceEntry 1 }

cie1000SnmpConfigTrapSourceIndexFilterID OBJECT-TYPE
    SYNTAX      Integer32 (0..127)
    MAX-ACCESS  accessible-for-notify
    STATUS      current
    DESCRIPTION
        "ID of filter for this SNMP trap"
    ::= { cie1000SnmpConfigTrapSourceEntry 2 }

cie1000SnmpConfigTrapSourceIndexFilter OBJECT-TYPE
    SYNTAX      OCTET STRING (SIZE(0..508))
    MAX-ACCESS  read-write
    STATUS      current
    DESCRIPTION
        "OID subtree to use as index filter. Every OID is hex encoded as 4
         bytes."
    ::= { cie1000SnmpConfigTrapSourceEntry 3 }

cie1000SnmpConfigTrapSourceIndexMask OBJECT-TYPE
    SYNTAX      OCTET STRING (SIZE(0..16))
    MAX-ACCESS  read-write
    STATUS      current
    DESCRIPTION
        "Mask for the OID subtree to use as index filter."
    ::= { cie1000SnmpConfigTrapSourceEntry 4 }

cie1000SnmpConfigTrapSourceFilterType OBJECT-TYPE
    SYNTAX      CIE1000SnmpViewType
    MAX-ACCESS  read-write
    STATUS      current
    DESCRIPTION
        "The filter type of this entry. The value can be set to 'included' or
         'excluded'."
    ::= { cie1000SnmpConfigTrapSourceEntry 5 }

cie1000SnmpConfigTrapSourceAction OBJECT-TYPE
    SYNTAX      CIE1000RowEditorState
    MAX-ACCESS  read-write
    STATUS      current
    DESCRIPTION
        "Action"
    ::= { cie1000SnmpConfigTrapSourceEntry 100 }

cie1000SnmpConfigTrapSourceTableRowEditor OBJECT IDENTIFIER
    ::= { cie1000SnmpConfig 23 }

cie1000SnmpConfigTrapSourceTableRowEditorName OBJECT-TYPE
    SYNTAX      CIE1000DisplayString (SIZE(0..64))
    MAX-ACCESS  read-write
    STATUS      current
    DESCRIPTION
        "SNMP trap event/table name"
    ::= { cie1000SnmpConfigTrapSourceTableRowEditor 1 }

cie1000SnmpConfigTrapSourceTableRowEditorIndexFilterID OBJECT-TYPE
    SYNTAX      Integer32 (0..127)
    MAX-ACCESS  read-write
    STATUS      current
    DESCRIPTION
        "ID of filter for this SNMP trap"
    ::= { cie1000SnmpConfigTrapSourceTableRowEditor 2 }

cie1000SnmpConfigTrapSourceTableRowEditorIndexFilter OBJECT-TYPE
    SYNTAX      OCTET STRING (SIZE(0..508))
    MAX-ACCESS  read-write
    STATUS      current
    DESCRIPTION
        "OID subtree to use as index filter. Every OID is hex encoded as 4
         bytes."
    ::= { cie1000SnmpConfigTrapSourceTableRowEditor 3 }

cie1000SnmpConfigTrapSourceTableRowEditorIndexMask OBJECT-TYPE
    SYNTAX      OCTET STRING (SIZE(0..16))
    MAX-ACCESS  read-write
    STATUS      current
    DESCRIPTION
        "Mask for the OID subtree to use as index filter."
    ::= { cie1000SnmpConfigTrapSourceTableRowEditor 4 }

cie1000SnmpConfigTrapSourceTableRowEditorFilterType OBJECT-TYPE
    SYNTAX      CIE1000SnmpViewType
    MAX-ACCESS  read-write
    STATUS      current
    DESCRIPTION
        "The filter type of this entry. The value can be set to 'included' or
         'excluded'."
    ::= { cie1000SnmpConfigTrapSourceTableRowEditor 5 }

cie1000SnmpConfigTrapSourceTableRowEditorAction OBJECT-TYPE
    SYNTAX      CIE1000RowEditorState
    MAX-ACCESS  read-write
    STATUS      current
    DESCRIPTION
        "Action"
    ::= { cie1000SnmpConfigTrapSourceTableRowEditor 100 }

cie1000SnmpMibConformance OBJECT IDENTIFIER
    ::= { cie1000SnmpMib 2 }

cie1000SnmpMibCompliances OBJECT IDENTIFIER
    ::= { cie1000SnmpMibConformance 1 }

cie1000SnmpMibGroups OBJECT IDENTIFIER
    ::= { cie1000SnmpMibConformance 2 }

cie1000SnmpConfigGlobalsInfoGroup OBJECT-GROUP
    OBJECTS     { cie1000SnmpConfigGlobalsMode,
                  cie1000SnmpConfigGlobalsEngineId }
    STATUS      current
    DESCRIPTION
        "A collection of objects."
    ::= { cie1000SnmpMibGroups 1 }

cie1000SnmpConfigCommunityTableInfoGroup OBJECT-GROUP
    OBJECTS     { cie1000SnmpConfigCommunityName,
                  cie1000SnmpConfigCommunitySourceIP,
                  cie1000SnmpConfigCommunitySourceIPPrefixSize,
                  cie1000SnmpConfigCommunitySecret,
                  cie1000SnmpConfigCommunityAction }
    STATUS      current
    DESCRIPTION
        "A collection of objects."
    ::= { cie1000SnmpMibGroups 2 }

cie1000SnmpConfigCommunityTableRowEditorInfoGroup OBJECT-GROUP
    OBJECTS     { cie1000SnmpConfigCommunityTableRowEditorName,
                  cie1000SnmpConfigCommunityTableRowEditorSourceIP,
                  cie1000SnmpConfigCommunityTableRowEditorSourceIPPrefixSize,
                  cie1000SnmpConfigCommunityTableRowEditorSecret,
                  cie1000SnmpConfigCommunityTableRowEditorAction }
    STATUS      current
    DESCRIPTION
        "A collection of objects."
    ::= { cie1000SnmpMibGroups 3 }

cie1000SnmpConfigUserTableInfoGroup OBJECT-GROUP
    OBJECTS     { cie1000SnmpConfigUserEngineId,
                  cie1000SnmpConfigUserUserName,
                  cie1000SnmpConfigUserSecurityLevel,
                  cie1000SnmpConfigUserAuthProtocol,
                  cie1000SnmpConfigUserAuthPassword,
                  cie1000SnmpConfigUserPrivProtocol,
                  cie1000SnmpConfigUserPrivPassword,
                  cie1000SnmpConfigUserAction }
    STATUS      current
    DESCRIPTION
        "A collection of objects."
    ::= { cie1000SnmpMibGroups 4 }

cie1000SnmpConfigUserTableRowEditorInfoGroup OBJECT-GROUP
    OBJECTS     { cie1000SnmpConfigUserTableRowEditorEngineId,
                  cie1000SnmpConfigUserTableRowEditorUserName,
                  cie1000SnmpConfigUserTableRowEditorSecurityLevel,
                  cie1000SnmpConfigUserTableRowEditorAuthProtocol,
                  cie1000SnmpConfigUserTableRowEditorAuthPassword,
                  cie1000SnmpConfigUserTableRowEditorPrivProtocol,
                  cie1000SnmpConfigUserTableRowEditorPrivPassword,
                  cie1000SnmpConfigUserTableRowEditorAction }
    STATUS      current
    DESCRIPTION
        "A collection of objects."
    ::= { cie1000SnmpMibGroups 5 }

cie1000SnmpConfigUserToAccessGroupTableInfoGroup OBJECT-GROUP
    OBJECTS     { cie1000SnmpConfigUserToAccessGroupSecurityModel,
                  cie1000SnmpConfigUserToAccessGroupUserOrCommunity,
                  cie1000SnmpConfigUserToAccessGroupAccessGroupName,
                  cie1000SnmpConfigUserToAccessGroupAction }
    STATUS      current
    DESCRIPTION
        "A collection of objects."
    ::= { cie1000SnmpMibGroups 6 }

cie1000SnmpConfigUserToAccessGroupTableRowEditorInfoGroup OBJECT-GROUP
    OBJECTS     {                   cie1000SnmpConfigUserToAccessGroupTableRowEditorSecurityModel,
                  cie1000SnmpConfigUserToAccessGroupTableRowEditorUserOrCommunity,
                  cie1000SnmpConfigUserToAccessGroupTableRowEditorAccessGroupName,
                  cie1000SnmpConfigUserToAccessGroupTableRowEditorAction }
    STATUS      current
    DESCRIPTION
        "A collection of objects."
    ::= { cie1000SnmpMibGroups 7 }

cie1000SnmpConfigAccessGroupTableInfoGroup OBJECT-GROUP
    OBJECTS     { cie1000SnmpConfigAccessGroupAccessGroupName,
                  cie1000SnmpConfigAccessGroupSecurityModel,
                  cie1000SnmpConfigAccessGroupSecurityLevel,
                  cie1000SnmpConfigAccessGroupReadViewName,
                  cie1000SnmpConfigAccessGroupWriteViewName,
                  cie1000SnmpConfigAccessGroupAction }
    STATUS      current
    DESCRIPTION
        "A collection of objects."
    ::= { cie1000SnmpMibGroups 8 }

cie1000SnmpConfigAccessGroupTableRowEditorInfoGroup OBJECT-GROUP
    OBJECTS     {                   cie1000SnmpConfigAccessGroupTableRowEditorAccessGroupName,
                  cie1000SnmpConfigAccessGroupTableRowEditorSecurityModel,
                  cie1000SnmpConfigAccessGroupTableRowEditorSecurityLevel,
                  cie1000SnmpConfigAccessGroupTableRowEditorReadViewName,
                  cie1000SnmpConfigAccessGroupTableRowEditorWriteViewName,
                  cie1000SnmpConfigAccessGroupTableRowEditorAction }
    STATUS      current
    DESCRIPTION
        "A collection of objects."
    ::= { cie1000SnmpMibGroups 9 }

cie1000SnmpConfigViewTableInfoGroup OBJECT-GROUP
    OBJECTS     { cie1000SnmpConfigViewName,
                  cie1000SnmpConfigViewSubtree,
                  cie1000SnmpConfigViewViewType,
                  cie1000SnmpConfigViewAction }
    STATUS      current
    DESCRIPTION
        "A collection of objects."
    ::= { cie1000SnmpMibGroups 10 }

cie1000SnmpConfigViewTableRowEditorInfoGroup OBJECT-GROUP
    OBJECTS     { cie1000SnmpConfigViewTableRowEditorName,
                  cie1000SnmpConfigViewTableRowEditorSubtree,
                  cie1000SnmpConfigViewTableRowEditorViewType,
                  cie1000SnmpConfigViewTableRowEditorAction }
    STATUS      current
    DESCRIPTION
        "A collection of objects."
    ::= { cie1000SnmpMibGroups 11 }

cie1000SnmpConfigCommunity6TableInfoGroup OBJECT-GROUP
    OBJECTS     { cie1000SnmpConfigCommunity6Name,
                  cie1000SnmpConfigCommunity6SourceIPv6,
                  cie1000SnmpConfigCommunity6SourceIPv6PrefixSize,
                  cie1000SnmpConfigCommunity6Secret,
                  cie1000SnmpConfigCommunity6Action }
    STATUS      current
    DESCRIPTION
        "A collection of objects."
    ::= { cie1000SnmpMibGroups 12 }

cie1000SnmpConfigCommunity6TableRowEditorInfoGroup OBJECT-GROUP
    OBJECTS     { cie1000SnmpConfigCommunity6TableRowEditorName,
                  cie1000SnmpConfigCommunity6TableRowEditorSourceIPv6,
                  cie1000SnmpConfigCommunity6TableRowEditorSourceIPv6PrefixSize,
                  cie1000SnmpConfigCommunity6TableRowEditorSecret,
                  cie1000SnmpConfigCommunity6TableRowEditorAction }
    STATUS      current
    DESCRIPTION
        "A collection of objects."
    ::= { cie1000SnmpMibGroups 13 }

cie1000SnmpConfigTrapReceiverTableInfoGroup OBJECT-GROUP
    OBJECTS     { cie1000SnmpConfigTrapReceiverName,
                  cie1000SnmpConfigTrapReceiverEnable,
                  cie1000SnmpConfigTrapReceiverAddress,
                  cie1000SnmpConfigTrapReceiverPort,
                  cie1000SnmpConfigTrapReceiverVersion,
                  cie1000SnmpConfigTrapReceiverCommunity,
                  cie1000SnmpConfigTrapReceiverNotifyType,
                  cie1000SnmpConfigTrapReceiverTimeout,
                  cie1000SnmpConfigTrapReceiverRetries,
                  cie1000SnmpConfigTrapReceiverEngineId,
                  cie1000SnmpConfigTrapReceiverUserName,
                  cie1000SnmpConfigTrapReceiverAction }
    STATUS      current
    DESCRIPTION
        "A collection of objects."
    ::= { cie1000SnmpMibGroups 14 }

cie1000SnmpConfigTrapReceiverTableRowEditorInfoGroup OBJECT-GROUP
    OBJECTS     { cie1000SnmpConfigTrapReceiverTableRowEditorName,
                  cie1000SnmpConfigTrapReceiverTableRowEditorEnable,
                  cie1000SnmpConfigTrapReceiverTableRowEditorAddress,
                  cie1000SnmpConfigTrapReceiverTableRowEditorPort,
                  cie1000SnmpConfigTrapReceiverTableRowEditorVersion,
                  cie1000SnmpConfigTrapReceiverTableRowEditorCommunity,
                  cie1000SnmpConfigTrapReceiverTableRowEditorNotifyType,
                  cie1000SnmpConfigTrapReceiverTableRowEditorTimeout,
                  cie1000SnmpConfigTrapReceiverTableRowEditorRetries,
                  cie1000SnmpConfigTrapReceiverTableRowEditorEngineId,
                  cie1000SnmpConfigTrapReceiverTableRowEditorUserName,
                  cie1000SnmpConfigTrapReceiverTableRowEditorAction }
    STATUS      current
    DESCRIPTION
        "A collection of objects."
    ::= { cie1000SnmpMibGroups 15 }

cie1000SnmpConfigTrapSourceTableInfoGroup OBJECT-GROUP
    OBJECTS     { cie1000SnmpConfigTrapSourceName,
                  cie1000SnmpConfigTrapSourceIndexFilterID,
                  cie1000SnmpConfigTrapSourceIndexFilter,
                  cie1000SnmpConfigTrapSourceIndexMask,
                  cie1000SnmpConfigTrapSourceFilterType,
                  cie1000SnmpConfigTrapSourceAction }
    STATUS      current
    DESCRIPTION
        "A collection of objects."
    ::= { cie1000SnmpMibGroups 16 }

cie1000SnmpConfigTrapSourceTableRowEditorInfoGroup OBJECT-GROUP
    OBJECTS     { cie1000SnmpConfigTrapSourceTableRowEditorName,
                  cie1000SnmpConfigTrapSourceTableRowEditorIndexFilterID,
                  cie1000SnmpConfigTrapSourceTableRowEditorIndexFilter,
                  cie1000SnmpConfigTrapSourceTableRowEditorIndexMask,
                  cie1000SnmpConfigTrapSourceTableRowEditorFilterType,
                  cie1000SnmpConfigTrapSourceTableRowEditorAction }
    STATUS      current
    DESCRIPTION
        "A collection of objects."
    ::= { cie1000SnmpMibGroups 17 }

cie1000SnmpMibCompliance MODULE-COMPLIANCE
    STATUS      current
    DESCRIPTION
        "The compliance statement for the implementation."

    MODULE      -- this module

    MANDATORY-GROUPS { cie1000SnmpConfigGlobalsInfoGroup,
                       cie1000SnmpConfigCommunityTableInfoGroup,
                       cie1000SnmpConfigCommunityTableRowEditorInfoGroup,
                       cie1000SnmpConfigUserTableInfoGroup,
                       cie1000SnmpConfigUserTableRowEditorInfoGroup,
                       cie1000SnmpConfigUserToAccessGroupTableInfoGroup,
                       cie1000SnmpConfigUserToAccessGroupTableRowEditorInfoGroup,
                       cie1000SnmpConfigAccessGroupTableInfoGroup,
                       cie1000SnmpConfigAccessGroupTableRowEditorInfoGroup,
                       cie1000SnmpConfigViewTableInfoGroup,
                       cie1000SnmpConfigViewTableRowEditorInfoGroup,
                       cie1000SnmpConfigCommunity6TableInfoGroup,
                       cie1000SnmpConfigCommunity6TableRowEditorInfoGroup,
                       cie1000SnmpConfigTrapReceiverTableInfoGroup,
                       cie1000SnmpConfigTrapReceiverTableRowEditorInfoGroup,
                       cie1000SnmpConfigTrapSourceTableInfoGroup,
                       cie1000SnmpConfigTrapSourceTableRowEditorInfoGroup }

    ::= { cie1000SnmpMibCompliances 1 }

END
