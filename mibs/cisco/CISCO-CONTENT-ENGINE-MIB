-- *****************************************************************
-- Cisco Content Engine
--
-- Copyright (c) 2000, 2002, 2003, 2004 by Cisco Systems, Inc.
-- All rights reserved.
-- *****************************************************************


CISCO-CONTENT-ENGINE-MIB DEFINITIONS ::= BEGIN

IMPORTS
    MODULE-IDENTITY,
    OBJECT-TYPE,
    NOTIFICATION-TYPE,
    Counter32, Counter64,
    Gauge32, Integer32, Unsigned32      FROM SNMPv2-SMI
    MODULE-COMPLIANCE, OBJECT-GROUP,
    NOTIFICATION-GROUP                  FROM SNMPv2-CONF
    TEXTUAL-CONVENTION,TimeStamp        FROM SNMPv2-TC
    ciscoMgmt                           FROM CISCO-SMI;

ciscoContentEngineMIB MODULE-IDENTITY
    LAST-UPDATED "200404210000Z"
    ORGANIZATION "Cisco Systems, Inc."
    CONTACT-INFO
        "Cisco Systems Customer Service
         Postal: 170 W Tasman Drive
             San Jose, CA 95134-1706
             USA
             Tel: +1 800 553-NETS
             E-mail: cs-webcache@cisco.com"
    DESCRIPTION
        "The MIB module for the Cisco Content Engine from
         Cisco Systems, Inc."
    REVISION     "200404210000Z"
    DESCRIPTION
        "Added cceWmtReqGroupRev1 and cceWmtHCGroupRev1,
         deprecated cceWmtReqGroup and cceWmtHCGroup,
         the new groups are introduced to support WMT 9.0."
    REVISION     "200402100000Z"
    DESCRIPTION
        "(1) Added all alarm related objects.
         (2) Deprecated ciscoContentEngineDataDiskFailed object
             and replaced it by ciscoContentEngineDiskFailed.
         (3) Added cceFailedDiskName objects."
    REVISION     "200205200000Z"
    DESCRIPTION
        "Added cceWmtGroup, cceCseGroup, and cceRpGroup groups."
    REVISION     "200002100000Z"
    DESCRIPTION
        "Initial version of this MIB module."
    ::= { ciscoMgmt 178 }

ciscoContentEngineMIBObjects
    OBJECT IDENTIFIER ::= { ciscoContentEngineMIB 1 }

-- HTTP proxy application group
cceHttpGroup
    OBJECT IDENTIFIER ::= { ciscoContentEngineMIBObjects 1 }

-- Window Media Technology application group
cceWmtGroup
    OBJECT IDENTIFIER ::= { ciscoContentEngineMIBObjects 2 }

-- Cisco Streaming Engine application group
cceCseGroup
    OBJECT IDENTIFIER ::= { ciscoContentEngineMIBObjects 3 }

-- Real Proxy application group
cceRpGroup
    OBJECT IDENTIFIER ::= { ciscoContentEngineMIBObjects 4 }

-- Notification Info group
cceNotificationInfo
    OBJECT IDENTIFIER ::= { ciscoContentEngineMIBObjects 5 }

-- Cisco Content Engine Alarm group
cceAlarmGroup
    OBJECT IDENTIFIER ::= { ciscoContentEngineMIBObjects 6 }


-- Major categories for HTTP proxy group
cceHttpRequests         OBJECT IDENTIFIER  ::= { cceHttpGroup 1 }
cceHttpPerf             OBJECT IDENTIFIER  ::= { cceHttpGroup 2 }

-- Major categories for WMT(Windows Media Technology) proxy/server group
cceWmtRequests          OBJECT IDENTIFIER  ::= { cceWmtGroup 1 }
cceWmtHCRequests        OBJECT IDENTIFIER  ::= { cceWmtGroup 2 }
cceWmtPerf              OBJECT IDENTIFIER  ::= { cceWmtGroup 3 }

-- Major categories for Cisco Streaming Engine group
cceCseRequests           OBJECT IDENTIFIER  ::= { cceCseGroup 1 }
cceCseHCRequests         OBJECT IDENTIFIER  ::= { cceCseGroup 2 }
cceCsePerf               OBJECT IDENTIFIER  ::= { cceCseGroup 3 }

-- Major categories for Real proxy  group
cceRpRequests           OBJECT IDENTIFIER  ::= { cceRpGroup 1 }
cceRpHCRequests         OBJECT IDENTIFIER  ::= { cceRpGroup 2 }


-- Major categories for Alarm  group
cceAlarmHistory           OBJECT IDENTIFIER  ::= { cceAlarmGroup 1 }
cceAlarmMonitoring        OBJECT IDENTIFIER  ::= { cceAlarmGroup 2 }

-- The following section describes the objects that are present
-- in the requests category of the HTTP proxy group

cceHttpRequestsTotal   OBJECT-TYPE
    SYNTAX          Counter32
    MAX-ACCESS      read-only
    STATUS          current
    DESCRIPTION
        "Total number of end-user requests the HTTP proxy
        has received."
    ::= { cceHttpRequests 1 }

cceHttpRequestsNoCacheTotal   OBJECT-TYPE
    SYNTAX          Counter32
    MAX-ACCESS      read-only
    STATUS          current
    DESCRIPTION
        "Total number of end-user requests the HTTP proxy
        has received which contain a header directive indicating
        that the object cannot be cached."
    ::= { cceHttpRequests 2 }

cceHttpRequestsClientErrorTotal   OBJECT-TYPE
    SYNTAX          Counter32
    MAX-ACCESS      read-only
    STATUS          current
    DESCRIPTION
        "Total number of times the HTTP proxy has failed to fulfill
         a request due to errors caused by client connections."
    ::= { cceHttpRequests 3 }

cceHttpRequestsServerErrorTotal   OBJECT-TYPE
    SYNTAX          Counter32
    MAX-ACCESS      read-only
    STATUS          current
    DESCRIPTION
        "Total number of times the HTTP proxy has failed to fulfill
         a request due to errors while fetching objects not in cache
         from remote servers."
    ::= { cceHttpRequests 4 }

cceHttpRequestsBlocked   OBJECT-TYPE
    SYNTAX          Counter32
    MAX-ACCESS      read-only
    STATUS          current
    DESCRIPTION
        "The number of times the HTTP proxy has blocked a request
         due to URL filtering or rules template blocking."
    ::= { cceHttpRequests 5 }

cceHttpRequestsHits    OBJECT-TYPE
    SYNTAX          Counter32
    MAX-ACCESS      read-only
    STATUS          current
    DESCRIPTION
        "Total number of end-user requests whose response body was
        retrieved from the populated cache of the HTTP proxy."
    ::= { cceHttpRequests 6 }

cceHttpRequestsMisses    OBJECT-TYPE
    SYNTAX          Counter32
    MAX-ACCESS      read-only
    STATUS          current
    DESCRIPTION
        "Total number of end-user requests whose response body is
        retrieved from remote servers."
    ::= { cceHttpRequests 7 }

cceHttpRequestsBytesServedHits    OBJECT-TYPE
    SYNTAX          Counter32
    MAX-ACCESS      read-only
    STATUS          current
    DESCRIPTION
        "Total number of bytes in the response bodies the HTTP proxy
        retrieved directly from its populated cache."
    ::= { cceHttpRequests 8 }

cceHttpRequestsBytesServedMisses  OBJECT-TYPE
    SYNTAX          Counter32
    MAX-ACCESS      read-only
    STATUS          current
    DESCRIPTION
        "Total number of bytes in the response bodies the HTTP proxy
         retrieved from remote servers."
    ::= { cceHttpRequests 9 }

cceHttpRequestsImsInmTotalCache   OBJECT-TYPE
    SYNTAX          Counter32
    MAX-ACCESS      read-only
    STATUS          current
    DESCRIPTION
        "Total number of If-Modified-Since (IMS) and If-Not-Matched
        (INM) requests from the client served from the populated
        cache of the HTTP proxy without revalidation."
    ::= { cceHttpRequests 10 }

cceHttpRequestsImsInmTotalReval  OBJECT-TYPE
    SYNTAX          Counter32
    MAX-ACCESS      read-only
    STATUS          current
    DESCRIPTION
        "Total number of If-Modified-Since (IMS) and If-Not-Matched
         (INM) requests from the client served from the populated
         cache of the HTTP proxy and revalidated with an IMS to the
         server."
    ::= { cceHttpRequests 11 }

cceHttpRequestsBytesClientIn  OBJECT-TYPE
    SYNTAX          Counter32
    MAX-ACCESS      read-only
    STATUS          current
    DESCRIPTION
        "Total number of bytes received by the HTTP proxy from
         clients."
    ::= { cceHttpRequests 12 }

cceHttpRequestsBytesClientOut  OBJECT-TYPE
    SYNTAX          Counter32
    MAX-ACCESS      read-only
    STATUS          current
    DESCRIPTION
        "Total number of bytes delivered by the HTTP proxy to
         clients."
    ::= { cceHttpRequests 13 }

cceHttpRequestsBytesServerIn  OBJECT-TYPE
    SYNTAX          Counter32
    MAX-ACCESS      read-only
    STATUS          current
    DESCRIPTION
        "Total number of bytes received by the HTTP proxy from
         remote servers."
    ::= { cceHttpRequests 14 }

cceHttpRequestsBytesServerOut  OBJECT-TYPE
    SYNTAX          Counter32
    MAX-ACCESS      read-only
    STATUS          current
    DESCRIPTION
        "Total number of bytes transmitted by the HTTP proxy
         to remote servers."
    ::= { cceHttpRequests 15 }

-- The following objects are the "High Capacity" versions
-- the objects listed above in the HTTP proxy requests
-- category (cceHttpRequests).
-- These objects are all 64-bit versions of the 32-bit
-- counters above.
-- These objects all have the same basic semantics as their
-- 32-bit counterparts, however, their syntax has been
-- extended to 64 bits.

cceHttpHCRequestsTotal   OBJECT-TYPE
    SYNTAX          Counter64
    MAX-ACCESS      read-only
    STATUS          current
    DESCRIPTION
        "Total number of end-user requests the HTTP proxy
         has received.  This object is a 64-bit
         version of cceHttpRequestsTotal."
    ::= { cceHttpRequests 16}

cceHttpHCRequestsNoCacheTotal   OBJECT-TYPE
    SYNTAX          Counter64
    MAX-ACCESS      read-only
    STATUS          current
    DESCRIPTION
        "Total number of end-user requests the HTTP proxy
         has received which contain a header directive
         indicating that the object cannot be cached.
         This object is a 64-bit version of
         cceHttpRequestsNoCacheTotal."
    ::= { cceHttpRequests 17 }

cceHttpHCRequestsClientErrorTotal   OBJECT-TYPE
    SYNTAX          Counter64
    MAX-ACCESS      read-only
    STATUS          current
    DESCRIPTION
        "Total number of times the HTTP proxy has failed to fulfill
         a request due to errors caused by client connections.
         This object is a 64-bit version of
         cceHttpRequestsClientErrorTotal."
    ::= { cceHttpRequests 18 }

cceHttpHCRequestsServerErrorTotal   OBJECT-TYPE
    SYNTAX          Counter64
    MAX-ACCESS      read-only
    STATUS          current
    DESCRIPTION
        "Total number of times the HTTP proxy has failed to fulfill
         a request due to errors while fetching objects not in cache
         from remote servers.  This object is a 64-bit version of
         cceHttpRequestsServerErrorTotal."
    ::= { cceHttpRequests 19 }

cceHttpHCRequestsBlocked   OBJECT-TYPE
    SYNTAX          Counter64
    MAX-ACCESS      read-only
    STATUS          current
    DESCRIPTION
        "The number of times the HTTP proxy has blocked a request
         due to URL filtering or rules template blocking.
         This object is a 64-bit version of cceHttpRequestsBlocked."
    ::= { cceHttpRequests 20 }

cceHttpHCRequestsHits    OBJECT-TYPE
    SYNTAX          Counter64
    MAX-ACCESS      read-only
    STATUS          current
    DESCRIPTION
        "Total number of end-user requests whose response body was
         retrieved from the populated cache of the HTTP proxy.
         This object is a 64-bit version of cceHttpRequestsHits."
    ::= { cceHttpRequests 21 }

cceHttpHCRequestsMisses    OBJECT-TYPE
    SYNTAX          Counter64
    MAX-ACCESS      read-only
    STATUS          current
    DESCRIPTION
        "Total number of end-user requests whose response body is
         retrieved from remote servers.  This object is a 64-bit
         version of cceHttpRequestsMisses."
    ::= { cceHttpRequests 22 }

cceHttpHCRequestsBytesServedHits    OBJECT-TYPE
    SYNTAX          Counter64
    MAX-ACCESS      read-only
    STATUS          current
    DESCRIPTION
        "Total number of bytes in the response bodies the HTTP proxy
         retrieved directly from its populated cache.  This object
         is a 64-bit version of cceHttpRequestsBytesServedHits."
    ::= { cceHttpRequests 23 }

cceHttpHCRequestsBytesServedMisses  OBJECT-TYPE
    SYNTAX          Counter64
    MAX-ACCESS      read-only
    STATUS          current
    DESCRIPTION
        "Total number of bytes in the response bodies the HTTP proxy
        retrieved from remote servers. This object is a 64-bit
        version of cceHttpRequestsBytesServedMisses."
    ::= { cceHttpRequests 24 }

cceHttpHCRequestsImsInmTotalCache   OBJECT-TYPE
    SYNTAX          Counter64
    MAX-ACCESS      read-only
    STATUS          current
    DESCRIPTION
        "Total number of If-Modified-Since (IMS) and If-Not-Matched
         (INM) requests from the client served from the populated
         cache of the HTTP proxy without revalidation. This object
         is a 64-bit version of cceHttpRequestsImsInmTotalCache."
    ::= { cceHttpRequests 25 }

cceHttpHCRequestsImsInmTotalReval   OBJECT-TYPE
    SYNTAX          Counter64
    MAX-ACCESS      read-only
    STATUS          current
    DESCRIPTION
        "Total number of If-Modified-Since (IMS) and If-Not-Matched
         (INM) requests from the client served from the populated
         cache of the HTTP proxy and revalidated with an IMS to the
         server.  This object is a 64-bit version of
         cceHttpRequestsImsInmTotalReval."
    ::= { cceHttpRequests 26 }

cceHttpHCRequestsBytesClientIn  OBJECT-TYPE
    SYNTAX          Counter64
    MAX-ACCESS      read-only
    STATUS          current
    DESCRIPTION
        "Total number of bytes received by the HTTP proxy from
         clients.  This object is a 64-bit version of
         cceHttpRequestsBytesClientIn."
    ::= { cceHttpRequests 27 }

cceHttpHCRequestsBytesClientOut  OBJECT-TYPE
    SYNTAX          Counter64
    MAX-ACCESS      read-only
    STATUS          current
    DESCRIPTION
        "Total number of bytes delivered by the HTTP proxy to
         clients.  This object is a 64-bit version of
         cceHttpRequestsBytesClientOut."
    ::= { cceHttpRequests 28 }

cceHttpHCRequestsBytesServerIn  OBJECT-TYPE
    SYNTAX          Counter64
    MAX-ACCESS      read-only
    STATUS          current
    DESCRIPTION
        "Total number of bytes received by the HTTP proxy from
         remote servers.  This object is a 64-bit version of
         cceHttpRequestsBytesServerIn."
    ::= { cceHttpRequests 29 }

cceHttpHCRequestsBytesServerOut  OBJECT-TYPE
    SYNTAX          Counter64
    MAX-ACCESS      read-only
    STATUS          current
    DESCRIPTION
        "Total number of bytes transmitted by the HTTP proxy
         to remote servers.  This object is a 64-bit version of
         cceHttpRequestsBytesServerOut."
    ::= { cceHttpRequests 30 }

-- The following section describes the objects that are present
-- in the performance category of the HTTP proxy group

cceHttpPerfSamplingTime    OBJECT-TYPE
    SYNTAX          Unsigned32 (0..4294967295)
    UNITS           "seconds"
    MAX-ACCESS      read-only
    STATUS          current
    DESCRIPTION
        "Number of seconds in the last sampling time interval
         used to calculate the value of the cceHttpPerfReqPerSec
         and cceHttpPerfBytesPerSec objects."
    ::= { cceHttpPerf 1 }

cceHttpPerfReqPerSec    OBJECT-TYPE
    SYNTAX          Unsigned32 (0..4294967295)
    MAX-ACCESS      read-only
    STATUS          current
    DESCRIPTION
        "Number of requests per second the HTTP proxy
         has been servicing in the last sampling time."
    ::= { cceHttpPerf 2 }

cceHttpPerfBytesPerSec    OBJECT-TYPE
    SYNTAX          Unsigned32 (0..4294967295)
    UNITS           "bytes-per-second"
    MAX-ACCESS      read-only
    STATUS          current
    DESCRIPTION
        "Bytes per second served in the last sampling time."
    ::= { cceHttpPerf 3 }

cceHttpPerfServiceTime       OBJECT-TYPE
    SYNTAX          Unsigned32 (0..4294967295)
    UNITS           "milliseconds-per-req"
    MAX-ACCESS      read-only
    STATUS          current
    DESCRIPTION
        "Average duration of each connection serviced by the
         HTTP proxy."
    ::= { cceHttpPerf 4 }

cceHttpPerfHitServiceTime    OBJECT-TYPE
    SYNTAX          Unsigned32 (0..4294967295)
    UNITS           "milliseconds-per-req"
    MAX-ACCESS      read-only
    STATUS          current
    DESCRIPTION
        "Average duration required for the HTTP proxy to send a
         hit response.  A hit response is a response for which
         the object can be serviced from the populated cache of
         the HTTP proxy."
    ::= { cceHttpPerf 5 }

cceHttpPerfMissServiceTime       OBJECT-TYPE
    SYNTAX          Unsigned32 (0..4294967295)
    UNITS           "milliseconds-per-req"
    MAX-ACCESS      read-only
    STATUS          current
    DESCRIPTION
        "Average duration required for the HTTP proxy to send a
         miss response.  A miss response is a response for which
         the object cannot be serviced from the populated cache
         of the HTTP proxy."
    ::= { cceHttpPerf 6 }

cceHttpPerfObjectSize       OBJECT-TYPE
    SYNTAX          Unsigned32 (0..4294967295)
    UNITS           "bytes"
    MAX-ACCESS      read-only
    STATUS          current
    DESCRIPTION
        "Average size of the object served from the HTTP proxy."
    ::= { cceHttpPerf 7 }

cceHttpPerfCpuLoad       OBJECT-TYPE
    SYNTAX          Unsigned32 (0..100)
    UNITS           "percentage"
    MAX-ACCESS      read-only
    STATUS          current
    DESCRIPTION
        "Percentage of CPU load for the last 4 second sampling
         time interval."
    ::= { cceHttpPerf 8 }

-- The following section describes the objects that are present
-- in the request category of the WMT group

cceWmtTotalRequests   OBJECT-TYPE
    SYNTAX          Counter32
    MAX-ACCESS      read-only
    STATUS          current
    DESCRIPTION
         "Total number of end-user requests the WMT proxy/server
          has received."
    ::= { cceWmtRequests 1 }

cceWmtTotalClientErrors OBJECT-TYPE
    SYNTAX          Counter32
    MAX-ACCESS      read-only
    STATUS          current
    DESCRIPTION
         "Total number of times the WMT proxy/server has failed to
         fulfill a request due to errors caused by client connections."
    ::= { cceWmtRequests 2 }

cceWmtTotalServerErrors OBJECT-TYPE
    SYNTAX          Counter32
    MAX-ACCESS      read-only
    STATUS          current
    DESCRIPTION
         "Total number of times the WMT proxy has failed to fulfill
          a request due to errors while fetching objects not in cache
          from remote servers."
    ::= { cceWmtRequests 3 }

cceWmtBlockedRequests OBJECT-TYPE
    SYNTAX          Counter32
    MAX-ACCESS      read-only
    STATUS          current
    DESCRIPTION
         "The number of times the WMT proxy/server has blocked a request
         due to URL filtering or rules template blocking."
    ::= { cceWmtRequests 4 }

cceWmtRequestHits OBJECT-TYPE
    SYNTAX          Counter32
    MAX-ACCESS      read-only
    STATUS          current
    DESCRIPTION
         "Total number of end-user requests whose response body was
          retrieved from the populated cache of the WMT proxy."
    ::= { cceWmtRequests 5 }

cceWmtRequestMisses OBJECT-TYPE
    SYNTAX          Counter32
    MAX-ACCESS      read-only
    STATUS          current
    DESCRIPTION
         "Total number of end-user requests whose response body is
          retrieved from remote servers."
    ::= { cceWmtRequests 6 }

cceWmtRequestHitsBytesServed OBJECT-TYPE
    SYNTAX          Counter32
    UNITS           "Bytes"
    MAX-ACCESS      read-only
    STATUS          current
    DESCRIPTION
         "Total number of bytes in the response bodies the WMT proxy
         retrieved directly from its populated cache."
    ::= { cceWmtRequests 7 }

cceWmtRequestMissesBytesServed  OBJECT-TYPE
    SYNTAX          Counter32
    UNITS           "Bytes"
    MAX-ACCESS      read-only
    STATUS          current
    DESCRIPTION
         "Total number of bytes in the response bodies the WMT proxy
         retrieved from remote servers."
    ::= { cceWmtRequests 8 }

cceWmtTotalLiveRequests OBJECT-TYPE
    SYNTAX          Counter32
    MAX-ACCESS      read-only
    STATUS          current
    DESCRIPTION
         "Total number of end-user live requests the WMT proxy/server
          has received."
    ::= { cceWmtRequests 9 }

cceWmtLiveRequestBytes  OBJECT-TYPE
    SYNTAX          Counter32
    UNITS           "Bytes"
    MAX-ACCESS      read-only
    STATUS          current
    DESCRIPTION
         "Total number of live splitting bytes served from the WMT
         proxy/server."
    ::= { cceWmtRequests 10 }

cceWmtTotalMmsuRequests OBJECT-TYPE
    SYNTAX          Counter32
    MAX-ACCESS      read-only
    STATUS          current
    DESCRIPTION
         "Total number of end-user
         MMSU (Microsoft Media Service over UDP)
         requests the WMT proxy/server has received."
    ::= { cceWmtRequests 11 }

cceWmtTotalMmsuBytes  OBJECT-TYPE
    SYNTAX          Counter32
    UNITS           "Bytes"
    MAX-ACCESS      read-only
    STATUS          current
    DESCRIPTION
         "Total number of bytes served through MMSU from WMT
         proxy/server."
    ::= { cceWmtRequests 12 }

cceWmtTotalMmstRequests OBJECT-TYPE
    SYNTAX          Counter32
    MAX-ACCESS      read-only
    STATUS          current
    DESCRIPTION
         "Total number of end-user
         MMST (Microsoft Media Service over TCP)
         requests the WMT proxy/server has received."
    ::= { cceWmtRequests 13 }

cceWmtTotalMmstBytes  OBJECT-TYPE
    SYNTAX          Counter32
    UNITS           "Bytes"
    MAX-ACCESS      read-only
    STATUS          current
    DESCRIPTION
         "Total number of bytes served through MMST from WMT
         proxy/server."
    ::= { cceWmtRequests 14 }

cceWmtTotalHttpRequests OBJECT-TYPE
    SYNTAX          Counter32
    MAX-ACCESS      read-only
    STATUS          current
    DESCRIPTION
       "Total number of end-user HTTP requests the WMT proxy/server
       has received."
    ::= { cceWmtRequests 15 }

cceWmtTotalHttpBytes  OBJECT-TYPE
    SYNTAX          Counter32
    UNITS           "Bytes"
    MAX-ACCESS      read-only
    STATUS          current
    DESCRIPTION
         "Total number of bytes served through HTTP from WMT
         proxy/server."
    ::= { cceWmtRequests 16 }

cceWmtTotalMulticastBytes  OBJECT-TYPE
    SYNTAX          Counter32
    UNITS           "Bytes"
    MAX-ACCESS      read-only
    STATUS          current
    DESCRIPTION
         "Total number of bytes served through multicast from
         WMT server."
    ::= { cceWmtRequests 17 }

cceWmtTotalRtspuRequests OBJECT-TYPE
    SYNTAX          Counter32
    MAX-ACCESS      read-only
    STATUS          current
    DESCRIPTION
         "Total number of end-user
         RTSPU (Microsoft Media Service over UDP)
         requests the WMT proxy/server has received."
    ::= { cceWmtRequests 18 }

cceWmtTotalRtspuBytes  OBJECT-TYPE
    SYNTAX          Counter32
    UNITS           "Bytes"
    MAX-ACCESS      read-only
    STATUS          current
    DESCRIPTION
         "Total number of bytes served through RTSPU from WMT
         proxy/server."
    ::= { cceWmtRequests 19 }

cceWmtTotalRtsptRequests OBJECT-TYPE
    SYNTAX          Counter32
    MAX-ACCESS      read-only
    STATUS          current
    DESCRIPTION
         "Total number of end-user
         RTSPT (Microsoft Media Service over TCP)
         requests the WMT proxy/server has received."
    ::= { cceWmtRequests 20 }

cceWmtTotalRtsptBytes  OBJECT-TYPE
    SYNTAX          Counter32
    UNITS           "Bytes"
    MAX-ACCESS      read-only
    STATUS          current
    DESCRIPTION
         "Total number of bytes served through RTSPT from WMT
         proxy/server."
    ::= { cceWmtRequests 21 }

-- The following objects are the "High Capacity" versions
-- of the objects listed above in the WMT group (cceWmtRequests).
-- These objects are all 64-bit versions of the 32-bit
-- counters above.
-- These objects all have the same basic semantics as their
-- 32-bit counterparts, however, their syntax has been
-- extended to 64 bits.

cceWmtHCRequestHitsBytesServed OBJECT-TYPE
    SYNTAX          Counter64
    UNITS           "Bytes"
    MAX-ACCESS      read-only
    STATUS          current
    DESCRIPTION
         "Total number of bytes in the response bodies the WMT proxy
          retrieved directly from its populated cache."
    ::= { cceWmtHCRequests 1 }

cceWmtHCRequestMissesBytesServed  OBJECT-TYPE
    SYNTAX          Counter64
    UNITS           "Bytes"
    MAX-ACCESS      read-only
    STATUS          current
    DESCRIPTION
         "Total number of bytes in the response bodies the WMT proxy
          retrieved from remote servers."
    ::= { cceWmtHCRequests 2 }

cceWmtHCLiveRequestBytes  OBJECT-TYPE
    SYNTAX          Counter64
    UNITS           "Bytes"
    MAX-ACCESS      read-only
    STATUS          current
    DESCRIPTION
         "Total number of live splitting bytes served from the WMT
         proxy/server."
    ::= { cceWmtHCRequests 3 }

cceWmtHCTotalMmsuBytes  OBJECT-TYPE
    SYNTAX          Counter64
    UNITS           "Bytes"
    MAX-ACCESS      read-only
    STATUS          current
    DESCRIPTION
         "Total number of bytes served through MMSU from WMT
          proxy/server."
    ::= { cceWmtHCRequests 4 }

cceWmtHCTotalMmstBytes  OBJECT-TYPE
    SYNTAX          Counter64
    UNITS           "Bytes"
    MAX-ACCESS      read-only
    STATUS          current
    DESCRIPTION
         "Total number of bytes served through MMST from WMT
          proxy/server."
    ::= { cceWmtHCRequests 5 }

cceWmtHCTotalHttpBytes  OBJECT-TYPE
    SYNTAX          Counter64
    UNITS           "Bytes"
    MAX-ACCESS      read-only
    STATUS          current
    DESCRIPTION
         "Total number of bytes served through HTTP from WMT
         proxy/server."
    ::= { cceWmtHCRequests 6 }

cceWmtHCTotalMulticastBytes OBJECT-TYPE
    SYNTAX          Counter64
    UNITS           "Bytes"
    MAX-ACCESS      read-only
    STATUS          current
    DESCRIPTION
         "Total number of bytes served through multicast
          from WMT server."
    ::= { cceWmtHCRequests 7 }

cceWmtHCTotalRtspuBytes  OBJECT-TYPE
    SYNTAX          Counter64
    UNITS           "Bytes"
    MAX-ACCESS      read-only
    STATUS          current
    DESCRIPTION
         "Total number of bytes served through RTSPU from WMT
          proxy/server."
    ::= { cceWmtHCRequests 8 }

cceWmtHCTotalRtsptBytes  OBJECT-TYPE
    SYNTAX          Counter64
    UNITS           "Bytes"
    MAX-ACCESS      read-only
    STATUS          current
    DESCRIPTION
         "Total number of bytes served through RTSPT from WMT
          proxy/server."
    ::= { cceWmtHCRequests 9 }

-- The following section describes the objects that are present
-- in the performance category of the WMT group

cceWmtPerfConcurrentRequests OBJECT-TYPE
    SYNTAX          Gauge32
    MAX-ACCESS      read-only
    STATUS          current
    DESCRIPTION
         "Number of concurrent requests the WMT proxy/server
          is servicing at the current time."
    ::= { cceWmtPerf 1 }

cceWmtPerfKbitsPerSec OBJECT-TYPE
    SYNTAX          Gauge32
    UNITS           "Kbits-per-sec"
    MAX-ACCESS      read-only
    STATUS          current
    DESCRIPTION
         "Kilobits per second to end-users served at the current time."
    ::= { cceWmtPerf 2 }

cceWmtPerfMulticastSessions OBJECT-TYPE
    SYNTAX          Gauge32
    UNITS           "sessions"
    MAX-ACCESS      read-only
    STATUS          current
    DESCRIPTION
         "Number of concurrent active multicast sessions at
         the current time."
    ::= { cceWmtPerf 3 }

cceWmtPerfMulticastKbitsPerSec  OBJECT-TYPE
    SYNTAX          Gauge32
    UNITS           "Kbits-per-sec"
    MAX-ACCESS      read-only
    STATUS          current
    DESCRIPTION
         "Kilobits per second served through multicast at current time."
    ::= { cceWmtPerf 4 }


-- The following section describes the objects that are present
-- in the requests category of Cisco Streaming Engine group


cceCseTotalRequests OBJECT-TYPE
    SYNTAX          Counter32
    MAX-ACCESS      read-only
    STATUS          current
    DESCRIPTION
          "Total number of end-user requests the
          Cisco Streaming Engine has received."
    ::= { cceCseRequests 1 }

cceCseRequestPacketsServed  OBJECT-TYPE
    SYNTAX          Counter32
    UNITS           "packets"
    MAX-ACCESS      read-only
    STATUS          current
    DESCRIPTION
        "Total number of packets in the response served
        by the Cisco Streaming Engine."
    ::= { cceCseRequests 2 }

cceCseRequestBytesServed  OBJECT-TYPE
    SYNTAX          Counter32
    UNITS           "Bytes"
    MAX-ACCESS      read-only
    STATUS          current
    DESCRIPTION
        "Total number of bytes in the response served by the Cisco
        Streaming Engine."
    ::= { cceCseRequests 3 }

-- The following objects are the "High Capacity" versions
-- of the objects listed above in the Cisco Streaming Engine
-- category (cceCseRequests).
-- These objects are all 64-bit versions of the 32-bit
-- counters above.

cceCseHCRequestPacketsServed  OBJECT-TYPE
    SYNTAX          Counter64
    UNITS           "packets"
    MAX-ACCESS      read-only
    STATUS          current
    DESCRIPTION
        "Total number of packets in the response served by
        the Cisco Streaming Engine."
    ::= { cceCseHCRequests  1 }

cceCseHCRequestBytesServed  OBJECT-TYPE
    SYNTAX          Counter64
    UNITS           "Bytes"
    MAX-ACCESS      read-only
    STATUS          current
    DESCRIPTION
        "Total number of bytes in the response served by
        the Cisco Streaming Engine."
    ::= { cceCseHCRequests 2 }

-- The following section describes the objects that are present
-- in the performance category of the Cisco Streaming Engine group

cceCsePerfConcurrentReqs OBJECT-TYPE
    SYNTAX          Gauge32
    MAX-ACCESS      read-only
    STATUS          current
    DESCRIPTION
         "Number of concurrent requests the Cisco Streaming Engine
          is servicing at the current time."
    ::= { cceCsePerf 1 }

cceCsePerfCurrentBandwidth  OBJECT-TYPE
    SYNTAX          Gauge32
    UNITS           "Kbits"
    MAX-ACCESS      read-only
    STATUS          current
    DESCRIPTION
         "The bandwidth reserved(Kilobits) for the current requests
         the Cisco Streaming Engine is serving."
    ::= { cceCsePerf 2 }

-- The following section describes the objects that are present
-- in the requests category of the Real Proxy group.

cceRpTotalHits OBJECT-TYPE
    SYNTAX          Counter32
    MAX-ACCESS      read-only
    STATUS          current
    DESCRIPTION
         "Total number of end-user requests whose response body
         was retrieved from the populated cache of the Real Proxy."
    ::= { cceRpRequests 1 }

cceRpTotalMisses OBJECT-TYPE
    SYNTAX          Counter32
    MAX-ACCESS      read-only
    STATUS          current
    DESCRIPTION
         "Total number of end-user requests whose response body was
         retrieved from remote servers."
    ::= { cceRpRequests 2 }

cceRpTotalVodPassThroughs OBJECT-TYPE
    SYNTAX          Counter32
    MAX-ACCESS      read-only
    STATUS          current
    DESCRIPTION
         "Total number of end-user VOD (Video On Demand) requests
         which cannot be cached by the Real Proxy."
    ::= { cceRpRequests 3 }

cceRpTotalLiveSplitReqs OBJECT-TYPE
    SYNTAX          Counter32
    MAX-ACCESS      read-only
    STATUS          current
    DESCRIPTION
         "Total number of end-user live requests for Real Proxy."
    ::= { cceRpRequests 4 }

cceRpTotalLivePassThruSplitReqs OBJECT-TYPE
    SYNTAX          Counter32
    MAX-ACCESS      read-only
    STATUS          current
    DESCRIPTION
         "Total number of end-user live requests, which Real Proxy
         cannot split."
    ::= { cceRpRequests 5 }

cceRpTotalIncomingBytes OBJECT-TYPE
    SYNTAX          Counter32
    UNITS           "Bytes"
    MAX-ACCESS      read-only
    STATUS          current
    DESCRIPTION
         "Total bytes received by the Real Proxy from remote servers."
    ::= { cceRpRequests 6 }

cceRpTotalOutgoingBytes OBJECT-TYPE
    SYNTAX          Counter32
    UNITS           "Bytes"
    MAX-ACCESS      read-only
    STATUS          current
    DESCRIPTION
         "Total bytes sent by the Real Proxy to end-users."
    ::= { cceRpRequests 7 }

-- The following objects are the "High Capacity" versions
-- of the objects listed above in the Real Proxy
-- category (cceRpRequests).
-- These objects are all 64-bit versions of the 32-bit
-- counters above.

cceRpHCTotalHits OBJECT-TYPE
    SYNTAX          Counter64
    MAX-ACCESS      read-only
    STATUS          current
    DESCRIPTION
         "Total number of end-user requests whose response body
         was retrieved from the populated cache of the Real Proxy."
    ::= { cceRpHCRequests 1 }

cceRpHCTotalMisses OBJECT-TYPE
    SYNTAX          Counter64
    MAX-ACCESS      read-only
    STATUS          current
    DESCRIPTION
         "Total number of end-user requests whose response body was
         retrieved from remote servers."
    ::= { cceRpHCRequests 2 }

cceRpHCTotalVodPassThroughs OBJECT-TYPE
    SYNTAX          Counter64
    MAX-ACCESS      read-only
    STATUS          current
    DESCRIPTION
         "Total number of end-user VOD (Video On Demand) requests
         which cannot be cached by the Real Proxy."
    ::= { cceRpHCRequests 3 }

cceRpHCTotalLiveSplitReqs OBJECT-TYPE
    SYNTAX          Counter64
    MAX-ACCESS      read-only
    STATUS          current
    DESCRIPTION
         "Total number of end-user live requests for Real Proxy."
    ::= { cceRpHCRequests 4 }

cceRpHCTotalLivePassThruSplitReqs OBJECT-TYPE
    SYNTAX          Counter64
    MAX-ACCESS      read-only
    STATUS          current
    DESCRIPTION
         "Total number of end-user live requests, which Real Proxy
         cannot split."
    ::= { cceRpHCRequests 5 }

cceRpHCTotalIncomingBytes OBJECT-TYPE
    SYNTAX          Counter64
    UNITS           "Bytes"
    MAX-ACCESS      read-only
    STATUS          current
    DESCRIPTION
         "Total bytes received by the Real Proxy from remote servers."
    ::= { cceRpHCRequests 6 }

cceRpHCTotalOutgoingBytes OBJECT-TYPE
    SYNTAX          Counter64
    UNITS           "Bytes"
    MAX-ACCESS      read-only
    STATUS          current
    DESCRIPTION
         "Total bytes sent by the Real Proxy to end-users."
    ::= { cceRpHCRequests 7 }

--
-- Notification related info
-- MIB Objects used by notifications
--
cceFailedDiskName OBJECT-TYPE
    SYNTAX          OCTET STRING (SIZE (0..32))
    MAX-ACCESS      accessible-for-notify
    STATUS          current
    DESCRIPTION
        "The Name of the disk on which disk-failure event occurred."
  ::= { cceNotificationInfo 1 }

--
-- The following section describes the objects that are present
-- in the cceAlarmGroup.
--
AlarmSeverity ::= TEXTUAL-CONVENTION
    STATUS current
    DESCRIPTION
        "Each alarm type defined by a vendor type employed by the
        system has an associated severity.  Bellcore TR-NWT-000474
        defines these severities as follows:

        'critical'  An alarm used to indicate a severe, service-
                    affecting condition has occurred and that immediate
                    corrective action is imperative, regardless of the
                    time of day or day of the week.

        'major'     An alarm used for hardware or software conditions
                    that indicate a serious disruption of service or
                    the malfunctioning or failure of important
                    hardware.

                    These troubles require the immediate attention and
                    response of a technician to restore or maintain
                    system capability.  The urgency is less than in
                    critical situations because of a lesser immediate
                    or impending effect on service or system
                    performance.

        'minor'     An alarm used for troubles that do not have a
                    serious effect on service to customers or for
                    troubles in hardware that are not essential to
                    the operation of the system."

    SYNTAX INTEGER {
        critical(1),
        major(2),
        minor(3)
    }

cceAlarmCriticalCount OBJECT-TYPE
    SYNTAX      Gauge32
    MAX-ACCESS  read-only
    STATUS      current
    DESCRIPTION
        "The value of this object specifies the number of alarms
        currently raised with a severity of 'critical'."
    ::= { cceAlarmMonitoring 1 }

cceAlarmMajorCount OBJECT-TYPE
    SYNTAX      Gauge32
    MAX-ACCESS  read-only
    STATUS      current
    DESCRIPTION
        "The value of this object specifies the number of alarms
        currently raised with a severity of 'major'."
    ::= { cceAlarmMonitoring 2 }

cceAlarmMinorCount OBJECT-TYPE
    SYNTAX      Gauge32
    MAX-ACCESS  read-only
    STATUS      current
    DESCRIPTION
        "The value of this object specifies the number of alarms
        currently raised with a severity of 'minor'."
    ::= { cceAlarmMonitoring 3 }

cceAlarmHistTableSize OBJECT-TYPE
    SYNTAX      INTEGER (0..500)
    MAX-ACCESS  read-write
    STATUS      current
    DESCRIPTION
        "This object specifies the number of entries that the
        cceAlarmHistTable can contain.  When a alarm gets
        generated, and the capacity of the cceAlarmHistTable
        has reached the value specified by this object, then the
        agent deletes the oldest entity in order to accommodate
        the new entry. A value of '0' prevents
        any history from being retained.  "
    ::= { cceAlarmHistory 1 }
--
-- Alarm Table
--
cceAlarmHistTable OBJECT-TYPE
    SYNTAX      SEQUENCE OF CceAlarmHistEntry
    MAX-ACCESS  not-accessible
    STATUS      current
    DESCRIPTION
        "This table contains a history of cceAlarmIndicate and
        cceAlarmClear traps generated by the agent."
    ::= { cceAlarmHistory 2 }

cceAlarmHistEntry OBJECT-TYPE
    SYNTAX      CceAlarmHistEntry
    MAX-ACCESS  not-accessible
    STATUS      current
    DESCRIPTION
        "The information conveyed by a cceAlarmIndicate or
        cceAlarmClear trap."
    INDEX       { cceAlarmHistIndex }
    ::= { cceAlarmHistTable 1 }

CceAlarmHistEntry ::= SEQUENCE {
    cceAlarmHistIndex            Unsigned32,
    cceAlarmHistId               Unsigned32,
    cceAlarmHistModuleId         Unsigned32,
    cceAlarmHistType             INTEGER,
    cceAlarmHistCategory         Integer32,
    cceAlarmHistSeverity         AlarmSeverity,
    cceAlarmHistInfo             OCTET STRING,
    cceAlarmHistTimeStamp        TimeStamp
}
cceAlarmHistIndex OBJECT-TYPE
    SYNTAX      Unsigned32
    MAX-ACCESS  not-accessible
    STATUS      current
    DESCRIPTION
        "An integer value uniquely identifying the entry in the table.
        The value of this object starts at '1' and monotonically
        increases for each alarm condition transition monitored by the
        agent.  If the value of this object is '4294967295', the agent
        will reset it to '1' upon monitoring the next alarm condition
        transition."
    ::= { cceAlarmHistEntry 1 }

cceAlarmHistId OBJECT-TYPE
    SYNTAX      Unsigned32
    MAX-ACCESS  read-only
    STATUS      current
    DESCRIPTION
        "This object specifies the type of alarm generated. Each error
         condition is mapped to an unique alarm-id."
    ::= { cceAlarmHistEntry 2 }

cceAlarmHistModuleId OBJECT-TYPE
    SYNTAX      Unsigned32
    MAX-ACCESS  read-only
    STATUS      current
    DESCRIPTION
        "This object specifies a ACNS Module-Id which generated
         the alarm."
    ::= { cceAlarmHistEntry 3 }

cceAlarmHistType OBJECT-TYPE
    SYNTAX      INTEGER { raised(1), cleared(2) }
    MAX-ACCESS  read-only
    STATUS      current
    DESCRIPTION
        "This object specifies whether the agent created the entry
         as the result of an alarm being Raised or cleared."
    ::= { cceAlarmHistEntry 4 }

cceAlarmHistCategory OBJECT-TYPE
    SYNTAX      Integer32 (1..256)
    MAX-ACCESS  read-only
    STATUS      current
    DESCRIPTION
        "This object specifies the probable cause that caused the
         alarm to be generated."
    ::= { cceAlarmHistEntry 5 }

cceAlarmHistSeverity OBJECT-TYPE
    SYNTAX      AlarmSeverity
    MAX-ACCESS  read-only
    STATUS      current
    DESCRIPTION
        "This object specifies the severity of the alarm generated."
    ::= { cceAlarmHistEntry 6 }

cceAlarmHistInfo OBJECT-TYPE
    SYNTAX      OCTET STRING (SIZE (0..255))
    MAX-ACCESS  read-only
    STATUS      current
    DESCRIPTION
        "This object specifies a human-readable message describing
         the alarm."
  ::= { cceAlarmHistEntry 7 }

cceAlarmHistTimeStamp OBJECT-TYPE
    SYNTAX      TimeStamp
    MAX-ACCESS  read-only
    STATUS      current
    DESCRIPTION
        "This object specifies the value of the sysUpTime object at
        the time the alarm was generated."
    ::= { cceAlarmHistEntry 8 }

-- Notifications
ciscoContentEngineMIBNotificationPrefix
    OBJECT IDENTIFIER ::= { ciscoContentEngineMIB 2 }

ciscoContentEngineMIBNotifications
    OBJECT IDENTIFIER ::= {ciscoContentEngineMIBNotificationPrefix 0}

ciscoContentEngineReadDiskError     NOTIFICATION-TYPE
    STATUS    current
    DESCRIPTION
        "First read error occurred on the disk that is being
         accessed.  Additional information about the error
         is logged to syslog."
    ::= { ciscoContentEngineMIBNotifications 1 }

ciscoContentEngineWriteDiskError    NOTIFICATION-TYPE
    STATUS    current
    DESCRIPTION
        "First write error occurred on the disk that is being
         accessed.  Additional information about the error
         is logged to syslog."
    ::= { ciscoContentEngineMIBNotifications 2 }

ciscoContentEngineWriteTransFailed  NOTIFICATION-TYPE
    STATUS    current
    DESCRIPTION
        "Failed writing to working transaction log located in
         /local1/working.log.  Possible causes are system
         errors or the log having been removed."
    ::= { ciscoContentEngineMIBNotifications 3 }

ciscoContentEngineDataDiskFailed    NOTIFICATION-TYPE
    STATUS    deprecated
    DESCRIPTION
        "A Content Engine data drive failed.  Additional
         information about the error is logged to syslog."
    ::= { ciscoContentEngineMIBNotifications 4 }

ciscoContentEngineOverloadBypass   NOTIFICATION-TYPE
    STATUS    current
    DESCRIPTION
        "A high watermark of percentage of capacity for transparent
         requests redirected to the Content Engine via WCCP
         (Web Cache Control Protocol) has been reached.
         Subsequent WCCP requests are rejected and forwarded
         to the Origin Server until the utilization falls
         below a low watermark."
    ::= { ciscoContentEngineMIBNotifications 5 }

ciscoContentEngineDiskFailed    NOTIFICATION-TYPE
    OBJECTS {
       cceFailedDiskName
    }
    STATUS    current
    DESCRIPTION
        "A Content Engine data drive failed.  This object supersedes
          ciscoContentEngineDataDiskFailed. Additional
         information about the error is logged to syslog."
    ::= { ciscoContentEngineMIBNotifications 6 }

cceAlarmCriticalRaised NOTIFICATION-TYPE
    OBJECTS    {
       cceAlarmHistId,
       cceAlarmHistModuleId,
       cceAlarmHistCategory,
       cceAlarmHistInfo,
       cceAlarmHistTimeStamp
    }
    STATUS    current
    DESCRIPTION
        "The Agent generates this trap when any module raises
         a Critical alarm."
    ::= { ciscoContentEngineMIBNotifications 7 }

cceAlarmCriticalCleared NOTIFICATION-TYPE
    OBJECTS    {
       cceAlarmHistId,
       cceAlarmHistModuleId,
       cceAlarmHistCategory,
       cceAlarmHistInfo,
       cceAlarmHistTimeStamp
    }
    STATUS    current
    DESCRIPTION
        "The Agent generates this trap when any module clears
         a Critical alarm."
    ::= { ciscoContentEngineMIBNotifications 8 }

cceAlarmMajorRaised NOTIFICATION-TYPE
    OBJECTS    {
       cceAlarmHistId,
       cceAlarmHistModuleId,
       cceAlarmHistCategory,
       cceAlarmHistInfo,
       cceAlarmHistTimeStamp
    }
    STATUS    current
    DESCRIPTION
        "The Agent generates this trap when any module raises
         a Major alarm."
    ::= { ciscoContentEngineMIBNotifications 9 }

cceAlarmMajorCleared NOTIFICATION-TYPE
    OBJECTS    {
       cceAlarmHistId,
       cceAlarmHistModuleId,
       cceAlarmHistCategory,
       cceAlarmHistInfo,
       cceAlarmHistTimeStamp
    }
    STATUS    current
    DESCRIPTION
        "The Agent generates this trap when any module clears
         a Major alarm."
    ::= { ciscoContentEngineMIBNotifications 10 }

cceAlarmMinorRaised NOTIFICATION-TYPE
    OBJECTS    {
       cceAlarmHistId,
       cceAlarmHistModuleId,
       cceAlarmHistCategory,
       cceAlarmHistInfo,
       cceAlarmHistTimeStamp
    }
    STATUS    current
    DESCRIPTION
        "The Agent generates this trap when any module raises
         a Minor alarm."
    ::= { ciscoContentEngineMIBNotifications 11 }

cceAlarmMinorCleared NOTIFICATION-TYPE
    OBJECTS    {
       cceAlarmHistId,
       cceAlarmHistModuleId,
       cceAlarmHistCategory,
       cceAlarmHistInfo,
       cceAlarmHistTimeStamp
    }
    STATUS    current
    DESCRIPTION
        "The Agent generates this trap when any module clears
         a Minor alarm."
    ::= { ciscoContentEngineMIBNotifications 12 }

ciscoContentEngineMIBConformance
    OBJECT IDENTIFIER ::= { ciscoContentEngineMIB 3 }

ciscoContentEngineMIBCompliances
    OBJECT IDENTIFIER ::= { ciscoContentEngineMIBConformance 1 }

ciscoContentEngineMIBGroups
    OBJECT IDENTIFIER ::= { ciscoContentEngineMIBConformance 2 }

-- Conformance
ciscoContentEngineMIBCompliance    MODULE-COMPLIANCE
    STATUS  deprecated -- superceeded by
                       -- ciscoContentEngineMIBComplianceRev1
    DESCRIPTION
        "The compliance statement for Cisco Systems entities which
         implement the Content Engine applications."
    MODULE  -- this module
    MANDATORY-GROUPS {
            cceHttpReqGroup,
            cceHttpPerfGroup
    }
    ::= { ciscoContentEngineMIBCompliances 1 }

ciscoContentEngineMIBComplianceRev1    MODULE-COMPLIANCE
    STATUS  deprecated -- superceeded by
                       -- ciscoContentEngineMIBComplianceRev2
    DESCRIPTION
        "The compliance statement for Cisco Systems entities which
         implement the Content Engine applications."
    MODULE  -- this module
    MANDATORY-GROUPS {
            cceHttpReqGroup,
            cceHttpPerfGroup,
            cceCseReqGroup,
            cceCseHCGroup,
            cceCsePerfGroup
    }
    ::= { ciscoContentEngineMIBCompliances 2 }

ciscoContentEngineMIBComplianceRev2    MODULE-COMPLIANCE
    STATUS  deprecated -- superceeded by
                       -- ciscoContentEngineMIBComplianceRev3
    DESCRIPTION
        "The compliance statement for Cisco Systems entities which
         implement the Content Engine applications."
    MODULE  -- this module
    MANDATORY-GROUPS {
            cceHttpReqGroup,
            cceHttpPerfGroup,
            cceCseReqGroup,
            cceCseHCGroup,
            cceCsePerfGroup,
            cceWmtReqGroup,
            cceWmtPerfGroup,
            cceWmtHCGroup,
            cceRpReqGroup,
            cceAlarmInfoGroup,
            cceHttpHCReqGroup,
            cceRpHCReqGroup,
            cceNotificationGroupRev1,
            cceNotificationInfoGroup
    }
    ::= { ciscoContentEngineMIBCompliances 3 }

ciscoContentEngineMIBComplianceRev3    MODULE-COMPLIANCE
    STATUS  current
    DESCRIPTION
        "The compliance statement for Cisco Systems entities which
         implement the Content Engine applications."
    MODULE  -- this module
    MANDATORY-GROUPS {
            cceHttpReqGroup,
            cceHttpPerfGroup,
            cceCseReqGroup,
            cceCseHCGroup,
            cceCsePerfGroup,
            cceWmtReqGroupRev1,
            cceWmtPerfGroup,
            cceWmtHCGroupRev1,
            cceRpReqGroup,
            cceAlarmInfoGroup,
            cceHttpHCReqGroup,
            cceRpHCReqGroup,
            cceNotificationGroupRev1,
            cceNotificationInfoGroup
    }
    ::= { ciscoContentEngineMIBCompliances 4 }

-- Units of Conformance
cceHttpReqGroup  OBJECT-GROUP
    OBJECTS {
        cceHttpRequestsTotal,
        cceHttpRequestsNoCacheTotal,
        cceHttpRequestsClientErrorTotal,
        cceHttpRequestsServerErrorTotal,
        cceHttpRequestsBlocked,
        cceHttpRequestsHits,
        cceHttpRequestsMisses,
        cceHttpRequestsBytesServedHits,
        cceHttpRequestsBytesServedMisses,
        cceHttpRequestsImsInmTotalCache,
        cceHttpRequestsImsInmTotalReval,
        cceHttpRequestsBytesClientIn,
        cceHttpRequestsBytesClientOut,
        cceHttpRequestsBytesServerIn,
        cceHttpRequestsBytesServerOut
    }
    STATUS current
    DESCRIPTION
        "HTTP proxy request group with low capacity
         Counter32 objects."
    ::= { ciscoContentEngineMIBGroups 1 }

-- This group of high capacity counters is mandatory.
cceHttpHCReqGroup  OBJECT-GROUP
    OBJECTS {
        cceHttpHCRequestsTotal,
        cceHttpHCRequestsNoCacheTotal,
        cceHttpHCRequestsClientErrorTotal,
        cceHttpHCRequestsServerErrorTotal,
        cceHttpHCRequestsBlocked,
        cceHttpHCRequestsHits,
        cceHttpHCRequestsMisses,
        cceHttpHCRequestsBytesServedHits,
        cceHttpHCRequestsBytesServedMisses,
        cceHttpHCRequestsImsInmTotalCache,
        cceHttpHCRequestsImsInmTotalReval,
        cceHttpHCRequestsBytesClientIn,
        cceHttpHCRequestsBytesClientOut,
        cceHttpHCRequestsBytesServerIn,
        cceHttpHCRequestsBytesServerOut
    }
    STATUS current
    DESCRIPTION
        "HTTP proxy request group with high capacity
         Counter64 objects."
    ::= { ciscoContentEngineMIBGroups 2 }

cceHttpPerfGroup  OBJECT-GROUP
    OBJECTS {
        cceHttpPerfSamplingTime,
        cceHttpPerfReqPerSec,
        cceHttpPerfBytesPerSec,
        cceHttpPerfServiceTime,
        cceHttpPerfHitServiceTime,
        cceHttpPerfMissServiceTime,
        cceHttpPerfObjectSize,
        cceHttpPerfCpuLoad
    }
    STATUS current
    DESCRIPTION
        "HTTP proxy performance group."
    ::= { ciscoContentEngineMIBGroups 3 }

cceNotificationGroup NOTIFICATION-GROUP
     NOTIFICATIONS {
        ciscoContentEngineReadDiskError,
        ciscoContentEngineWriteDiskError,
        ciscoContentEngineWriteTransFailed,
        ciscoContentEngineDataDiskFailed,
        ciscoContentEngineOverloadBypass
     }
     STATUS deprecated -- replaced by cceNotificationGroupRev1
     DESCRIPTION
        "A collection of notifications used for
        monitoring errors."
     ::= { ciscoContentEngineMIBGroups 4 }

cceWmtReqGroup OBJECT-GROUP
    OBJECTS {
        cceWmtTotalRequests,
        cceWmtTotalClientErrors,
        cceWmtTotalServerErrors,
        cceWmtBlockedRequests,
        cceWmtRequestHits,
        cceWmtRequestMisses,
        cceWmtRequestHitsBytesServed,
        cceWmtRequestMissesBytesServed,
        cceWmtTotalLiveRequests,
        cceWmtLiveRequestBytes,
        cceWmtTotalMmsuRequests,
        cceWmtTotalMmsuBytes,
        cceWmtTotalMmstRequests,
        cceWmtTotalMmstBytes,
        cceWmtTotalHttpRequests,
        cceWmtTotalHttpBytes,
        cceWmtTotalMulticastBytes
    }
    STATUS deprecated -- replaced by cceWmtReqGroupRev1
    DESCRIPTION
        "A collection of objects providing request statistics
         of WMT proxy and server."
   ::= { ciscoContentEngineMIBGroups 5 }

cceWmtHCGroup OBJECT-GROUP
    OBJECTS {
        cceWmtHCRequestHitsBytesServed,
        cceWmtHCRequestMissesBytesServed,
        cceWmtHCLiveRequestBytes,
        cceWmtHCTotalMmsuBytes,
        cceWmtHCTotalMmstBytes,
        cceWmtHCTotalHttpBytes,
        cceWmtHCTotalMulticastBytes
    }
    STATUS deprecated -- replaced by cceWmtHCGroupRev1
    DESCRIPTION
        "A collection of 64-bit WMT counters"
    ::= { ciscoContentEngineMIBGroups 6 }

cceWmtPerfGroup OBJECT-GROUP
    OBJECTS {
        cceWmtPerfConcurrentRequests,
        cceWmtPerfKbitsPerSec,
        cceWmtPerfMulticastSessions,
        cceWmtPerfMulticastKbitsPerSec
    }
    STATUS current
    DESCRIPTION
        "A collection of objects providing performance statistics
         of WMT proxy and server."
    ::= { ciscoContentEngineMIBGroups 7 }

cceCseReqGroup OBJECT-GROUP
    OBJECTS {
        cceCseTotalRequests,
        cceCseRequestPacketsServed,
        cceCseRequestBytesServed
    }
    STATUS current
    DESCRIPTION
        "A collection of objects providing request statistics
        of a Cisco Streaming Engine."
    ::= { ciscoContentEngineMIBGroups 8 }

cceCseHCGroup OBJECT-GROUP
    OBJECTS {
        cceCseHCRequestPacketsServed,
        cceCseHCRequestBytesServed
    }
    STATUS current
    DESCRIPTION
        "A collection of 64 bit counters."
    ::= { ciscoContentEngineMIBGroups 9 }

cceCsePerfGroup OBJECT-GROUP
    OBJECTS {
        cceCsePerfConcurrentReqs,
        cceCsePerfCurrentBandwidth
    }
    STATUS current
    DESCRIPTION
        "A collection of objects providing
         performance statistics of a Cisco Streaming Engine."
    ::= { ciscoContentEngineMIBGroups 10 }

cceRpReqGroup OBJECT-GROUP
    OBJECTS {
        cceRpTotalHits,
        cceRpTotalMisses,
        cceRpTotalVodPassThroughs,
        cceRpTotalLiveSplitReqs,
        cceRpTotalLivePassThruSplitReqs,
        cceRpTotalIncomingBytes,
        cceRpTotalOutgoingBytes
    }
    STATUS current
    DESCRIPTION
        "A collection of objects providing
        request statistics of a Real Proxy."
    ::= { ciscoContentEngineMIBGroups 11 }

cceRpHCReqGroup OBJECT-GROUP
    OBJECTS {
        cceRpHCTotalHits,
        cceRpHCTotalMisses,
        cceRpHCTotalVodPassThroughs,
        cceRpHCTotalLiveSplitReqs,
        cceRpHCTotalLivePassThruSplitReqs,
        cceRpHCTotalIncomingBytes,
        cceRpHCTotalOutgoingBytes
    }
    STATUS current
    DESCRIPTION
        "A collection of 64-bit Real Proxy counters"
    ::= { ciscoContentEngineMIBGroups 12 }

cceNotificationGroupRev1 NOTIFICATION-GROUP
     NOTIFICATIONS {
        ciscoContentEngineReadDiskError,
        ciscoContentEngineWriteDiskError,
        ciscoContentEngineWriteTransFailed,
        ciscoContentEngineOverloadBypass,
        ciscoContentEngineDiskFailed,
        cceAlarmCriticalRaised,
        cceAlarmCriticalCleared,
        cceAlarmMajorRaised,
        cceAlarmMajorCleared,
        cceAlarmMinorRaised,
        cceAlarmMinorCleared
     }
     STATUS current
     DESCRIPTION
        "A collection of notifications used for
        monitoring errors."
     ::= { ciscoContentEngineMIBGroups 13 }

cceAlarmInfoGroup OBJECT-GROUP
    OBJECTS {
        cceAlarmCriticalCount,
        cceAlarmMajorCount,
        cceAlarmMinorCount,
        cceAlarmHistTableSize,
        cceAlarmHistId,
        cceAlarmHistModuleId,
        cceAlarmHistSeverity,
        cceAlarmHistType,
        cceAlarmHistCategory,
        cceAlarmHistInfo,
        cceAlarmHistTimeStamp
     }
    STATUS current
    DESCRIPTION
        "A collection of objects which provides info about
         Cisco Content Engine alarms."
    ::= { ciscoContentEngineMIBGroups 14 }

cceNotificationInfoGroup OBJECT-GROUP
    OBJECTS {
        cceFailedDiskName
    }
    STATUS current
    DESCRIPTION
        "A collection of objects which provides info
         about notifications."
    ::= { ciscoContentEngineMIBGroups 15 }

cceWmtReqGroupRev1 OBJECT-GROUP
    OBJECTS {
        cceWmtTotalRequests,
        cceWmtTotalClientErrors,
        cceWmtTotalServerErrors,
        cceWmtBlockedRequests,
        cceWmtRequestHits,
        cceWmtRequestMisses,
        cceWmtRequestHitsBytesServed,
        cceWmtRequestMissesBytesServed,
        cceWmtTotalLiveRequests,
        cceWmtLiveRequestBytes,
        cceWmtTotalMmsuRequests,
        cceWmtTotalMmsuBytes,
        cceWmtTotalMmstRequests,
        cceWmtTotalMmstBytes,
        cceWmtTotalHttpRequests,
        cceWmtTotalHttpBytes,
        cceWmtTotalRtspuRequests,
        cceWmtTotalRtspuBytes,
        cceWmtTotalRtsptRequests,
        cceWmtTotalRtsptBytes,
        cceWmtTotalMulticastBytes
    }
    STATUS current
    DESCRIPTION
        "A collection of objects providing request statistics
         of WMT proxy and server."
   ::= { ciscoContentEngineMIBGroups 16 }

cceWmtHCGroupRev1 OBJECT-GROUP
    OBJECTS {
        cceWmtHCRequestHitsBytesServed,
        cceWmtHCRequestMissesBytesServed,
        cceWmtHCLiveRequestBytes,
        cceWmtHCTotalMmsuBytes,
        cceWmtHCTotalMmstBytes,
        cceWmtHCTotalHttpBytes,
        cceWmtHCTotalRtspuBytes,
        cceWmtHCTotalRtsptBytes,
        cceWmtHCTotalMulticastBytes
    }
    STATUS current
    DESCRIPTION
        "A collection of 64-bit WMT counters"
    ::= { ciscoContentEngineMIBGroups 17 }

END
