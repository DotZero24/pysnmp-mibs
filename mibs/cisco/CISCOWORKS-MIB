-- *****************************************************************
-- CISCOWORKS-MIB.my
--
-- April 1995,  Author Teyao Chen
--
-- Copyright (c) 1995, 2003 by Cisco Systems, Inc.
-- All rights reserved.
-- *****************************************************************
CISCOWORKS-MIB DEFINITIONS ::= BEGIN
IMPORTS
       MODULE-IDENTITY,
       NOTIFICATION-TYPE,
       OBJECT-TYPE
           FROM SNMPv2-SMI

       sysUpTime
           FROM RFC1213-MIB

       DisplayString
           FROM SNMPv2-TC

       ciscoworks
           FROM CISCO-SMI

       MODULE-COMPLIANCE,
       NOTIFICATION-GROUP,
       OBJECT-GROUP
             FROM SNMPv2-CONF;


    -- CiscoWorks enterprise ID

cwLogMIB               MODULE-IDENTITY
       LAST-UPDATED    "200302180000Z"
       ORGANIZATION    "Cisco Systems, Inc."
       CONTACT-INFO
                "       Cisco Systems
                        Customer Service

                Postal: 170 W. Tasman Drive
                        San Jose, CA 95134
                        USA

                   Tel: +1 800 553-NETS
                e-mail: cs-snmp@cisco.com"
       DESCRIPTION
                " This MIB describes the traps and trap and trap
                  variables used by CiscoWorks.  Originally the
                  CiscoWorks classic nmlogd process forwarded
                  messages logged by applications and devices to
                  NM platforms as traps.  Now it is used by
                  CiscoWorks Blue to send DLSw and APPN/SNASw
                  traps to NM platforms."

       REVISION           "200302180000Z"
       DESCRIPTION
                "Updated for SNMPv2 and for publishing."

       REVISION           "199504020000Z"
       DESCRIPTION
                "Initial version of this MIB module."
           ::= { ciscoworks 1 }

-- Top-level structure of the MIB
cwLog               OBJECT IDENTIFIER ::= { cwLogMIB 1 }
cwTrapsPrefix       OBJECT IDENTIFIER ::= { cwLogMIB 2 }
cwMIBConform        OBJECT IDENTIFIER ::= { cwLogMIB 3 }


-- **************************************************************
-- *                                                            *
-- * cwLog group                                                *
-- *                                                            *
-- **************************************************************

cwLogDate          OBJECT-TYPE
   SYNTAX          DisplayString (SIZE (15))
   MAX-ACCESS      read-only
   STATUS          current
   DESCRIPTION
           "Date in the format of 'MMM DD HH:MM:SS' when the message
            is logged.  The time zone used is configured on
            CiscoWorks workstation."
   ::= { cwLog 1 }

cwLogSource        OBJECT-TYPE
   SYNTAX          INTEGER {
                       other(1),
                       ciscoworks(2),
                       device(3)
                   }
   MAX-ACCESS      read-only
   STATUS          current
   DESCRIPTION
           "The source of the log message as follows.
             'other'      - The source of the log entry is a source
                            other than ciscoworks application or
                            Cisco device.
             'ciscoworks' - Indicates the message is generated by
                            CiscoWorks applications (e.g. nmpolld).
             'device'     - Indicates the message is generated by
                            Cisco devices."
   ::= { cwLog 2 }

cwLogApp           OBJECT-TYPE
   SYNTAX          DisplayString (SIZE (0..32))
   MAX-ACCESS      read-only
   STATUS          current
   DESCRIPTION
           "The name of the application that generates the log
            message If the message is generated by a device, this
            string will be empty."
   ::= { cwLog 3 }

cwLogMsg           OBJECT-TYPE
   SYNTAX          DisplayString (SIZE (0..255))
   MAX-ACCESS      read-only
   STATUS          current
   DESCRIPTION
           "The text of the log message."
   ::= { cwLog 4 }


cwTraps OBJECT IDENTIFIER ::= { cwTrapsPrefix 0 }
--  *************************************************************
--  *                                                           *
--  * Traps for CiscoWorks nmlogd                               *
--  *                                                           *
--  *************************************************************
cwAppLogTrap       NOTIFICATION-TYPE
   OBJECTS { sysUpTime,
             cwLogDate,
             cwLogSource,
             cwLogApp,
             cwLogMsg
   }
   STATUS          current
   DESCRIPTION
       "A cwAppLogTrap is sent by nmlogd when a CiscoWorks
        application logs a message to system log file on
        CiscoWorks workstation.  This is also sent by
        CiscoWorks Blue processes."
     ::= { cwTraps 1 }

cwDevLogTrap       NOTIFICATION-TYPE
   OBJECTS { sysUpTime,
             cwLogDate,
             cwLogSource,
             cwLogMsg }
   STATUS          current
   DESCRIPTION
           "A cwDevLogTrap is sent by nmlogd when a device logs
            a message to system log file on CiscoWorks
            workstation."
     ::= { cwTraps 2 }



-- Conformance Information
--
ciscoCwMIBCompliances OBJECT IDENTIFIER ::= { cwMIBConform 1}
ciscoCwMIBGroups      OBJECT IDENTIFIER ::= { cwMIBConform 2}

-- Compliance

ciscoCwMIBCompliance MODULE-COMPLIANCE
        STATUS current
        DESCRIPTION
                "The compliance statement for entities which
                 implement the CISCOWORKS-MIB."
        MODULE -- this module
                MANDATORY-GROUPS { ciscoCwObjectsGroup,
                                   ciscoCwNotificationsGroup
                }

        ::= { ciscoCwMIBCompliances 1 }


-- Units of Conformance

ciscoCwObjectsGroup       OBJECT-GROUP
        OBJECTS { cwLogDate,
                  cwLogSource,
                  cwLogApp,
                  cwLogMsg
        }
        STATUS       current
        DESCRIPTION
                "Cisco Works Objects Group"
        ::= { ciscoCwMIBGroups 7 }

ciscoCwNotificationsGroup NOTIFICATION-GROUP
        NOTIFICATIONS { cwAppLogTrap,
                        cwDevLogTrap
        }
        STATUS       current
        DESCRIPTION
                "Cisco Works Notification Objects Group."
        ::= { ciscoCwMIBGroups 12 }
END
