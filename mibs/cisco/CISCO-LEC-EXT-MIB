-- *****************************************************************
-- An extension to the ATM Forum LEC MIB for Cisco propietary objects
--
-- May 1997, Chris Young
--
-- Copyright (c) 1997, 1998 by cisco Systems, Inc.
-- All rights reserved.
-- *****************************************************************
--


CISCO-LEC-EXT-MIB DEFINITIONS ::= BEGIN

IMPORTS
        MODULE-IDENTITY, OBJECT-TYPE    FROM SNMPv2-SMI
        MODULE-COMPLIANCE, OBJECT-GROUP FROM SNMPv2-CONF
        ciscoMgmt                       FROM CISCO-SMI
        lecConfigEntry                  FROM LAN-EMULATION-CLIENT-MIB
        VlanIndex                       FROM CISCO-VTP-MIB;

ciscoLecExtMIB MODULE-IDENTITY
        LAST-UPDATED "9705091230Z"
        ORGANIZATION "Cisco Systems, Inc."
        CONTACT-INFO
                   "       Cisco Systems
                           Customer Service

                   Postal: 170 W Tasman Drive
                           San Jose, CA  95134
                           USA

                      Tel: +1 800 553-NETS

                   E-mail: cs-atm@cisco.com"
        DESCRIPTION
                "This MIB module is a Cisco extension to the ATM
                Forum's LANE Client MIB."
        REVISION     "9705091230Z"
        DESCRIPTION
                "Initial version of this MIB module."
        ::= { ciscoMgmt 77 }

ciscoLecExtMIBObjects  OBJECT IDENTIFIER ::= { ciscoLecExtMIB 1 }

cLecExtVlan OBJECT IDENTIFIER ::=
	{ ciscoLecExtMIBObjects 1 }

--Textual Conventions
--
-- none

-- LEC to VLAN mapping

cLecToVlanTable OBJECT-TYPE
        SYNTAX        SEQUENCE OF CLecToVlanEntry
        MAX-ACCESS    not-accessible
        STATUS        current
        DESCRIPTION
                "An extension to the lecConfig table in the
                LAN-EMULATION-CLIENT-MIB that identifies which VLAN a
                LEC is associated with."
        ::= { cLecExtVlan 1 }


cLecToVlanEntry OBJECT-TYPE
        SYNTAX        CLecToVlanEntry
        MAX-ACCESS    not-accessible
        STATUS        current
        DESCRIPTION
                " Each entry in this table shows the correlation
                between a LAN Emulation client and the VLAN that it
                extends."
        AUGMENTS { lecConfigEntry }
        ::= { cLecToVlanTable 1 }

CLecToVlanEntry ::= SEQUENCE {
        cLecToVlanId        VlanIndex
}

cLecToVlanId   OBJECT-TYPE
        SYNTAX        VlanIndex
        MAX-ACCESS    read-create
        STATUS        current
        DESCRIPTION
                " The VLAN ID of the VLAN to which the specified LEC
                is attributed."
        ::= { cLecToVlanEntry 1 }

-- Notifications

ciscoLecExtMIBNotificationPrefix OBJECT IDENTIFIER ::=
	{ ciscoLecExtMIB 2 }
ciscoLecExtMIBNotifications OBJECT IDENTIFIER ::=
	{ ciscoLecExtMIBNotificationPrefix 0 }
-- none

-- conformance information

ciscoLecExtMIBConformance
                OBJECT IDENTIFIER ::= { ciscoLecExtMIB 3 }
ciscoLecExtMIBCompliances
                OBJECT IDENTIFIER ::= { ciscoLecExtMIBConformance 1 }
ciscoLecExtMIBGroups
                OBJECT IDENTIFIER ::= { ciscoLecExtMIBConformance 2 }


-- compliance statements

ciscoLecExtMIBCompliance MODULE-COMPLIANCE
        STATUS        current
        DESCRIPTION
                "This module should be implemented by all Cisco
                 devices supporting ATM LAN Emulation Clients."
        MODULE        -- this module
        MANDATORY-GROUPS
                { ciscoLecExtVlanMIBGroup }

        ::= { ciscoLecExtMIBCompliances 1 }

-- units of conformance

ciscoLecExtVlanMIBGroup OBJECT-GROUP
        OBJECTS       { cLecToVlanId }
        STATUS        current
        DESCRIPTION
                "A collection of objects related to identifying
                a LANE Client associated VLAN information."
        ::= { ciscoLecExtMIBGroups 1 }

END
