--*****************************************************************
-- CISCO-DMN-DSG-FETHRESHOLDS.mib : Muting Thresholds Mib file.
--
-- August 2010, TEL MIB Team
--
-- Copyright (c) 1999-2010 by Cisco Systems, Inc.
-- All rights reserved.
--*****************************************************************

CISCO-DMN-DSG-FETHRESHOLDS-MIB

DEFINITIONS ::= BEGIN

IMPORTS
    MODULE-IDENTITY,
    OBJECT-TYPE, Integer32
        FROM SNMPv2-SMI
    OBJECT-GROUP, MODULE-COMPLIANCE
        FROM SNMPv2-CONF
    ciscoDSGUtilities
        FROM CISCO-DMN-DSG-ROOT-MIB;


ciscoDSGFeThresholds  MODULE-IDENTITY
    LAST-UPDATED  "201008301100Z" -- August 30 2010 11:00:00 GMT
    ORGANIZATION    "Cisco Systems, Inc."
    CONTACT-INFO
       "Cisco Systems, Inc.
        Customer Service
        Postal: 170 W Tasman Drive
        San Jose, CA 95134
        USA
        Tel: +1 800 553 NETS

        E-mail: cs-ipsla@cisco.com"
    DESCRIPTION   "Cisco FE Muting Thresholds MIB."

    REVISION       "201008301100Z"
    DESCRIPTION    "V01.00.03 2010-08-30
                   Updated for adherence to SNMPv2 format."

    REVISION      "201004260500Z"
    DESCRIPTION   "V01.00.02 2010-04-26
                   The name of MIB objects are modified to make the
                   terminology common across the OSD, WebUI and MIB."

    REVISION      "201003220500Z"
    DESCRIPTION   "V01.00.01 2010-03-22
                   The Syntax of Unsigned32 MIB objects whose range is
                   within the range of Integer32, is updated to
                   Integer32."

    REVISION      "200912071200Z"
    DESCRIPTION   "V01.00.00 2009-12-07
                   Initial Version."

    ::= { ciscoDSGUtilities 9 }


-- *************************************
-- mutingThresholdsTable Branch
-- *************************************

mutingThresholdsTable OBJECT-TYPE
     SYNTAX  SEQUENCE OF MutingThresholdsEntry
     MAX-ACCESS  not-accessible
     STATUS  current
     DESCRIPTION
         "Muting Thresholds Table."
     ::= { ciscoDSGFeThresholds 1 }

mutingThresholdsEntry OBJECT-TYPE
     SYNTAX  MutingThresholdsEntry
     MAX-ACCESS  not-accessible
     STATUS  current
     DESCRIPTION
         "Entry for Muting Thresholds Table."
     INDEX { mutingThreshholdsInstance }
     ::= { mutingThresholdsTable 1 }

MutingThresholdsEntry ::= SEQUENCE
{
  mutingThreshholdsInstance      Integer32,
  mutThreshRestoreDefaults       INTEGER,
  mutThreshControl               INTEGER,
  mutThreshDVBSTransportMute     Integer32,
  mutThreshDVBSTransportRestore  Integer32,
  mutThreshDVBSAudioMute         Integer32,
  mutThreshDVBSAudioRestore      Integer32,
  mutThreshDVBS2TransportMute    Integer32,
  mutThreshDVBS2TransportRestore Integer32,
  mutThreshDVBS2AudioMute        Integer32,
  mutThreshDVBS2AudioRestore     Integer32
}

mutingThreshholdsInstance OBJECT-TYPE
     SYNTAX  Integer32 (1..1)
     MAX-ACCESS  not-accessible
     STATUS  current
     DESCRIPTION
         "Instance for Muting Thresholds Table."
     ::= { mutingThresholdsEntry 1 }

mutThreshRestoreDefaults OBJECT-TYPE
     SYNTAX  INTEGER {
             writeOnly(1),
             yes(2)
          }
     MAX-ACCESS  read-write
     STATUS  current
     DESCRIPTION
         "Control restores software defaults to the Muting Thresholds.
          When set to yes( 2 ) it restores Default Muting BER Levels."
     ::= { mutingThresholdsEntry 2 }

mutThreshControl OBJECT-TYPE
     SYNTAX  INTEGER {
             disable(1),
             enable(2)
          }
     MAX-ACCESS  read-write
     STATUS  current
     DESCRIPTION
         "Turns on or off the muting algorithm."
     ::= { mutingThresholdsEntry 3 }

mutThreshDVBSTransportMute OBJECT-TYPE
     SYNTAX  Integer32(-50..200)
     MAX-ACCESS  read-write
     STATUS  current
     DESCRIPTION
         "Transport Mute CN Margin ( DVB-S )in dB in steps of 1.
          The scaling factor is 1/10."
     ::= { mutingThresholdsEntry 4 }

mutThreshDVBSTransportRestore OBJECT-TYPE
     SYNTAX  Integer32(-50..200)
     MAX-ACCESS  read-write
     STATUS  current
     DESCRIPTION
         "Transport Restore CN Margin ( DVB-S )in dB in steps of 1.
          The scaling factor is 1/10.."
     ::= { mutingThresholdsEntry 5 }

mutThreshDVBSAudioMute OBJECT-TYPE
     SYNTAX  Integer32(-50..200)
     MAX-ACCESS  read-write
     STATUS  current
     DESCRIPTION
         "Audio Mute CN Margin ( DVB-S )in dB in steps of 1.
          The scaling factor is 1/10."
     ::= { mutingThresholdsEntry 6 }

mutThreshDVBSAudioRestore OBJECT-TYPE
     SYNTAX  Integer32 (-50..200)
     MAX-ACCESS  read-write
     STATUS  current
     DESCRIPTION
         "Audio Restore CN Margin ( DVB-S )in dB in steps of 1.
          The scaling factor is 1/10."
     ::= { mutingThresholdsEntry 7 }

mutThreshDVBS2TransportMute OBJECT-TYPE
     SYNTAX  Integer32(-50..200)
     MAX-ACCESS  read-write
     STATUS  current
     DESCRIPTION
         "Transport Mute CN Margin ( DVB-S2 )in dB in steps of 1.
          The scaling factor is 1/10."
     ::= { mutingThresholdsEntry 8 }

mutThreshDVBS2TransportRestore OBJECT-TYPE
     SYNTAX  Integer32(-50..200)
     MAX-ACCESS  read-write
     STATUS  current
     DESCRIPTION
         "Transport Restore CN Margin ( DVB-S2 )in dB in steps of 1.
          The scaling factor is 1/10."
     ::= { mutingThresholdsEntry 9 }

mutThreshDVBS2AudioMute OBJECT-TYPE
     SYNTAX  Integer32(-50..200)
     MAX-ACCESS  read-write
     STATUS  current
     DESCRIPTION
         "Audio Mute CN Margin (DVB-S2)in dB in steps of 1.
          The scaling factor is 1/10."
     ::= { mutingThresholdsEntry 10 }

mutThreshDVBS2AudioRestore OBJECT-TYPE
     SYNTAX  Integer32(-50..200)
     MAX-ACCESS  read-write
     STATUS  current
     DESCRIPTION
         "Audio Restore Margin ( DVB-S2 ) in dB in steps of 1.
          The scaling factor is 1/10."
     ::= { mutingThresholdsEntry 11 }

END
