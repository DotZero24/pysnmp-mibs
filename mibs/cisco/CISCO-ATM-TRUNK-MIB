-- *********************************************************************
-- CISCO-VOICE-ATM-TRUNK-MIB.my:
--
-- Cisco ATM Trunk MIB
--
--
-- January 2003, Feng Luo
--
-- Copyright (c) 2003 by cisco Systems, Inc.
-- All rights reserved.
--
-- *********************************************************************


CISCO-ATM-TRUNK-MIB DEFINITIONS ::= BEGIN

IMPORTS
    RowStatus,
    TimeStamp,
    TruthValue,
    TEXTUAL-CONVENTION     FROM SNMPv2-TC
    MODULE-COMPLIANCE,
    OBJECT-GROUP           FROM SNMPv2-CONF
    OBJECT-TYPE,
    MODULE-IDENTITY,
    Integer32,
    Gauge32,
    Unsigned32             FROM SNMPv2-SMI
    ifIndex,
    InterfaceIndex         FROM IF-MIB
    CiscoAal2ProfileNumber,
    CiscoAal2ProfileType   FROM CISCO-VOICE-AALX-PROFILE-MIB
    ciscoMgmt              FROM CISCO-SMI
    ConfigIterator,
    BulkConfigResult       FROM CISCO-TC
    OwnerString            FROM RMON-MIB
    CvcSpeechCoderRate,
    CvcCoderTypeRate       FROM CISCO-VOICE-COMMON-DIAL-CONTROL-MIB;



ciscoAtmTrunkMIB MODULE-IDENTITY
    LAST-UPDATED "200307180000Z"
    ORGANIZATION "Cisco Systems, Inc."
    CONTACT-INFO
            "       Cisco Systems
                    Customer Service

                Postal: 170 W Tasman Drive
                        San Jose, CA 95134
                        USA

                        Tel: +1 800 553-NETS

                E-mail: cs-voice-gateway@cisco.com"
    DESCRIPTION
        "The MIB for voice and Nx64 over ATM Trunking applications.

         The following lists the abbreviations used in this MIB:
            AAL       ATM Adaption Layer
            AIS       Alarm Indication Signal
            CID       Channel Identifier
            DSP       Digital Signal Processing
            DTMF      Dual Tone Multi Frequency
            FCS       Frame Check Sequence
            TDM       Time Division Multiplexing
            PVC       Permanent Virtual Circuit
            RAI       Remote Alarm Indication
            RDI       Remote Defect Indication
            SID       Silence Insertion Descriptor
            SVC       Switched Virtual Circuit
            VAD       Voice Activity Detection
            VBD       Voice Band Data
            VC        Virtual Circuit
        "
    REVISION "200307180000Z"
    DESCRIPTION
        "Initial version of the MIB module."

    ::= { ciscoMgmt 351 }


cAtmTrunkMIBNotifications
                    OBJECT IDENTIFIER ::= { ciscoAtmTrunkMIB 0 }
cAtmTrunkMIBObjects
                    OBJECT IDENTIFIER ::= { ciscoAtmTrunkMIB 1 }
cAtmTrunkCidConfig
                    OBJECT IDENTIFIER ::= { cAtmTrunkMIBObjects 1 }
cAtmTrunkCidConnStats
                    OBJECT IDENTIFIER ::= { cAtmTrunkMIBObjects 2 }
cAtmTrunkAal1Config
                    OBJECT IDENTIFIER ::= { cAtmTrunkMIBObjects 3 }
cAtmTrunkAal1ConnStats
                    OBJECT IDENTIFIER ::= { cAtmTrunkMIBObjects 4 }
cAtmTrunkAal5Config
                    OBJECT IDENTIFIER ::= { cAtmTrunkMIBObjects 5 }
cAtmTrunkAal5ConnStats
                    OBJECT IDENTIFIER ::= { cAtmTrunkMIBObjects 6 }

--
-- Textual Conventions
--
Counter32SinceReset ::= TEXTUAL-CONVENTION
    STATUS        current
    DESCRIPTION
        "This textual convention defines a counter type that is
         similar to Counter32 but can be reset. The value of the
         objects of this type indicates the statistics since last
         counter reset.

         Once the value of the counter object of this type reaches
         its maximum, it will restart from zero again.
        "
    SYNTAX        Unsigned32 (0..2147483647)

--
-- caTrunkCidTable
--
catmtCidTable  OBJECT-TYPE
    SYNTAX        SEQUENCE OF CatmtCidEntry
    MAX-ACCESS    not-accessible
    STATUS        current
    DESCRIPTION
        "This table is used to establish the mapping of one or more
         DS0 channels from a single DS1 interface to an AAL2 connection
         identified by a Channel IDentification number(CID).

         This table is created and used for ATM AAL2 trunking
         applications including both voice and data.
        "
    ::= { cAtmTrunkCidConfig 1 }

catmtCidEntry  OBJECT-TYPE
    SYNTAX        CatmtCidEntry
    MAX-ACCESS    not-accessible
    STATUS        current
    DESCRIPTION
        "An entry in the catmtCidTable.
         Each entry represents an AAL2 trunking connection which
         is uniquely identified by the PVC index and the CID number.

         An AAL2 trunking connection is established by binding
         one or more DS0 channels from a single DS1 interface to
         an AAL2 ATM connection identified by the CID.

         The Channel IDentification (CID) is the standard term
         used to identify an ATM AAL2 connection (ITU-T I.366.2).
         CID is unique within a VC, either a PVC or SVC connection.
        "
    INDEX { ifIndex, catmtCidVpi, catmtCidVci, catmtCid }
    ::= { catmtCidTable 1 }


CatmtCidEntry ::=
    SEQUENCE {
        catmtCidVpi                    Unsigned32,
        catmtCidVci                    Unsigned32,
        catmtCid                       Integer32,
        catmtCidDs1                    InterfaceIndex,
        catmtCidDs0GroupIndex          Integer32,
        catmtCidProfileType            CiscoAal2ProfileType,
        catmtCidProfileNumber          CiscoAal2ProfileNumber,
        catmtCidVoiceCodec             CvcSpeechCoderRate,
        catmtCidVBDCodec               CvcCoderTypeRate,
        catmtCidNx64Enable             TruthValue,
        catmtCidNx64Profile            Integer32,
        catmtCidStateBitMap            BITS,
        catmtCidRepetition             ConfigIterator,
        catmtCidRepetitionOwner        OwnerString,
        catmtCidRepetitionResult       BulkConfigResult,
        catmtCidRowStatus              RowStatus
}


catmtCidVpi  OBJECT-TYPE
    SYNTAX        Unsigned32 (0..4095)
    MAX-ACCESS    not-accessible
    STATUS        current
    DESCRIPTION
        "This object is the VPI value of an ATM PVC connection.
        "
    ::= { catmtCidEntry  1 }

catmtCidVci  OBJECT-TYPE
    SYNTAX        Unsigned32 (0..65535)
    MAX-ACCESS    not-accessible
    STATUS        current
    DESCRIPTION
        "This object is the VCI value of an ATM PVC connection.
        "
    ::= { catmtCidEntry  2 }

catmtCid  OBJECT-TYPE
    SYNTAX        Integer32 (8..255)
    MAX-ACCESS    not-accessible
    STATUS        current
    DESCRIPTION
        "This object is the CID of an ATM AAL2 connection,
         it is unique within a PVC or SVC connection.

         The CID number at both sides of an AAL2 connection
         must be the same.

         Value of 0 is not used, and values of 1 to 7 are reserved
         for layer management by ITU-T I.366.2 standard.
        "
    REFERENCE
        "ITU-T recommendation I.366.2. "
    ::= { catmtCidEntry  3 }

catmtCidDs1  OBJECT-TYPE
    SYNTAX        InterfaceIndex
    MAX-ACCESS    read-create
    STATUS        current
    DESCRIPTION
        "The value of this object equals to the 'ifIndex' of the
         DS1 interface.

         This object is mandatory when adding a CID entry.  Once a
         CID entry is added, this object can not be modified.
        "
    ::= { catmtCidEntry  4 }

catmtCidDs0GroupIndex  OBJECT-TYPE
    SYNTAX        Integer32 (0..30)
    MAX-ACCESS    read-create
    STATUS        current
    DESCRIPTION
        "An arbitrary index that uniquely identifies a DS0 group
         which contains one or more DS0(s) within a DS1 interface
         specified by 'catmtCidDs1'.

         This object is mandatory when adding a CID entry. Once a
         CID entry is added, this object can not be modified.
        "
    ::= { catmtCidEntry  5 }

catmtCidProfileType  OBJECT-TYPE
    SYNTAX        CiscoAal2ProfileType
    MAX-ACCESS    read-create
    STATUS        current
    DESCRIPTION
        "This object specifies the type of the AAL2 CODEC profile.
         The combination of the profile type and profile number
         specified by 'catmtCidProfileNumber' defines an AAL2
         CODEC profile.

         This parameter is mandatory for adding and a voice trunking
         CID entry.

         This object is applicable when catmtCidNx64Enable is
         is set to 'false'. It is used for voice trunking applications
         only.
        "
    ::= { catmtCidEntry  6 }

catmtCidProfileNumber  OBJECT-TYPE
    SYNTAX        CiscoAal2ProfileNumber
    MAX-ACCESS    read-create
    STATUS        current
    DESCRIPTION
        "This object specifies the AAL2 CODEC profile number.
         The combination of profile type and profile number defines
         an AAL2 CODEC profile.

         A profile contains one or more entries, with each entry
         specifying an encoding algorithm and information regarding
         how the TDM data is to be packed into a packet.

         This parameter is mandatory for adding a voice trunking CID
         entry.

         This object is applicable when catmtCidNx64Enable is
         is set to 'false'. It is used for voice trunking applications
         only.
        "
    REFERENCE
        " ITU-T recommendation I.366.2."
    ::= { catmtCidEntry  7 }

catmtCidVoiceCodec  OBJECT-TYPE
    SYNTAX        CvcSpeechCoderRate
    MAX-ACCESS    read-create
    STATUS        current
    DESCRIPTION
        "This object specifies the CODEC type used for the AAL2
         trunking connection.

         The following table lists the CODEC types specified
         in each profile table by ITU I.366.2 standard.

         ----------------------------------------------------
         Profile     Profile                         Packet
          type       Number     CODEC      SID       time(ms)
         ----------------------------------------------------
          ITU          1       G.711u     No SID       5
                               G.711a     No SID       5
         ----------------------------------------------------
          ITU          2       G.711u     SIDG         5
                               G.711a     SIDG         5
         ----------------------------------------------------
          ITU          3       G.711u     SIDG         5
                               G.711a     SIDG         5
                               G726-40    SIDG         5
                               G726-32    SIDG         5
                               G726-24    SIDG         5
                               G726-16    SIDG         5
         ----------------------------------------------------
          ITU          7       G.711u     SIDG         5
                               G.711a     SIDG         5
                               G.729ab    SID729       10
                               G.729a     No SID       10
         ----------------------------------------------------
          ITU          8       G.711u     No SID       5
                               G.711a     No SID       5
                               G.726-32   No SID       5
                               G.729ab    SID729       10
                               G.729a     SID729       10
         ----------------------------------------------------
          Custom       100     G.711u     SIDG         5
                               G.711a     SIDG         5
                               G.726-32   SIGD         10
         ----------------------------------------------------
          Custom       101     G.711u     No SID       5
                               G.711a     No SID       5
                               G.726-32   No SID       10
                               G.729ab    SID729       10
                               G.729a     No SID       10
         ----------------------------------------------------
          Custom       110     G.711u     SIDG         5
                               G.711a     SIDG         5
                               G.726-32   SIDG         10
                               G.729ab    SID729       30
                               G.729a     No SID       30
         ----------------------------------------------------
          Custom       200     clearChan  No SID       5
         ----------------------------------------------------

         This object can only be set to the CODECs defined by
         the profile specified by catmtCidProfileType and
         catmtCidProfileNumber.

         This object is applicable when catmtCidNx64Enable is
         is set to 'false'. It is used for voice trunking applications
         only.

         This object is mandatory when adding a voice trunking CID
         entry.
        "
    ::= { catmtCidEntry  8 }

catmtCidVBDCodec  OBJECT-TYPE
    SYNTAX        CvcCoderTypeRate
    MAX-ACCESS    read-create
    STATUS        current
    DESCRIPTION
        "This object specifies the CODEC type to be used for Voice
         Band Data (VBD) upspeed.

         Upspeed is to change the transmission rate of a voice
         interface to a higher rate of CODEC type for fax/modem
         transportation.

         This object is applicable when catmtCidNx64Enable is
         is set to 'false'. It is used for voice trunking applications
         only.

         This object is mandatory when adding a voice trunking CID
         entry.
        "
     ::= { catmtCidEntry 9 }

catmtCidNx64Enable  OBJECT-TYPE
    SYNTAX        TruthValue
    MAX-ACCESS    read-create
    STATUS        current
    DESCRIPTION
        "This object specifies whether a CID entry is in the Nx64
         packet stream mode.

         When this object is set to 'false', the CID connection is
         for voice trunking applications only; when it is set to
         'true', the CID connection is for data trunking using
         Nx64 packet stream (N>=1).

         This object can not be modified.
        "
  DEFVAL { false }
    ::= { catmtCidEntry  10 }

catmtCidNx64Profile  OBJECT-TYPE
    SYNTAX        Integer32 (1..65535)
    MAX-ACCESS    read-create
    STATUS        current
    DESCRIPTION
        "This object specifies the Nx64 data profile for an AAL2
         data trunking connection.

         The value of this object is a valid index of the
         cdapNx64ProfileTable in the CISCO-DATA-AALX-PROFILE-MIB.

         This object is only applicable when catmtCidNx64Enable
         is set to 'true'.
        "
    DEFVAL { 1 }
    ::= { catmtCidEntry  11 }

catmtCidStateBitMap  OBJECT-TYPE
    SYNTAX        BITS {
                     pvcAdminDown(0),
                     pvcFailure(1),
                     extAIS(2),
                     extRAI(3),
                     aal2ConnAIS(4),
                     aal2ConnRDI(5),
                     lineAlarm(6) }
    MAX-ACCESS    read-only
    STATUS        current
    DESCRIPTION
        "This object is used to indicate the state of the CID.

         All bits setting to 0 which means status 'okay'.
        "
    REFERENCE
        " ITU-T recommendation I.366.2 Annex N."
    ::= { catmtCidEntry 12 }

catmtCidRepetition  OBJECT-TYPE
   SYNTAX         ConfigIterator
   MAX-ACCESS     read-create
   STATUS         current
   DESCRIPTION
       "This object is used to repeatedly apply the writable objects
        of catmtCidTable specified in the same SNMP PDU starting
        from the row defined by the index object for the number of
        rows specified by this object.

        The repetition operation works differently for data trunking
        and voice trunking applications. When catmtCidNx64Enable is
        set to 'false' (voice trunking), it is iterated through the
        value of DS0's and CID number. When catmtCidNx64Enable is
        set to 'true' (data trunking), the order of repetition
        operation is iterated through the value of DS1 index and CID
        number.

        (1) For voice trunking applications:
            At each iteration, the value of CID (catmtCid), DS0
            (catmtCidDs0GroupIndex) and DS1(catmtCidDs1) will
            be incremented. When the value of catmtCidDs0GroupIndex
            reaches its maximum, catmtCidDs1 will be incremented
            to the next logical order of DS1 interface.

        (2) For data trunking applications:
            At each iteration, the value of catmtCid, catmtCidDs1
            will be incremented. In other words,  the Nx64 packet
            stream repetition iterates on the DS1, with each DS1
            interface having the same DS0 group
            (catmtCidDs0GroupIndex) configuration.

        The repetition iteration will stop once the value of catmtCid
        reaches its maximum value 255 or when the next CID is not
        available or already configured for different type of trunking
        application. For example, a non-Nx64 repetition will stop if
        the next CID has been configured for Nx64 packet stream
        trunking, and vise versa. The repetition will also stop if the
        next contiguous DS0 group index is not available.

        The maximum value of this object is 248 which is the maximum
        number of CID or AAL2 connections allowed within a VC
        connection.
       "
    DEFVAL { 1 }
    ::= { catmtCidEntry 13 }

catmtCidRepetitionOwner  OBJECT-TYPE
   SYNTAX         OwnerString
   MAX-ACCESS     read-create
   STATUS         current
   DESCRIPTION
       "This object is used for error reporting of the bulk
        provisioning operation specified by catmtCidRepetition.

        The value of this object is set by the SNMP manager with its
        own identifier at the time of setting catmtCidRepetition
        to issue the bulk provisioning operation.

        Later on, the SNMP manager checks the value of this object.
        If it matches its own name, the value of
        catmtCidRepetitionResult will be set to indicate the result
        of bulk operation initiated by this SNMP manager.
       "
    ::= { catmtCidEntry 14 }

catmtCidRepetitionResult  OBJECT-TYPE
   SYNTAX         BulkConfigResult
   MAX-ACCESS     read-only
   STATUS         current
   DESCRIPTION
       "This object indicates the result of the bulk provisioning
        specified in catmtCidRepetition.

        The format might look at (but not limited to):
           'COMPLETION=<number of rows completed before any error
            occurred>/<number of rows was designated>,
            ERROR=<error code>/<index where the error occurred>:
            <error text>'

        For example:
           'COMPLETION=22/100,ERROR=38/44:Invalid DS1 line coding
            for the line type'
       "
    ::= { catmtCidEntry 15 }

catmtCidRowStatus  OBJECT-TYPE
    SYNTAX        RowStatus
    MAX-ACCESS    read-create
    STATUS        current
    DESCRIPTION
        "This object is used for adding/deleting the entries from the
         catmtCidTable.

         In order to create a CID entry, the following parameters are
         mandatory and must be provided:

         For voice trunking applications:
                 catmtDs1,
                 catmtDs0GroupIndex,
                 catmtCidProfileType,
                 catmtCidProfileNumber,
                 catmtCidVoiceCodec,
                 catmtCidVBDCodec

         For data trunking applications:
                 catmtDs1,
                 catmtDs0GroupIndex
        "
    ::= { catmtCidEntry 16 }


--
--  catmtCidStatsTable
--
 catmtCidStatsTable  OBJECT-TYPE
    SYNTAX  SEQUENCE OF CatmtCidStatsEntry
    MAX-ACCESS    not-accessible
    STATUS        current
    DESCRIPTION
        "This table contains the statistical information
         on a per CID connection basis for AAL2 Trunking
         applications.
        "
    ::= { cAtmTrunkCidConnStats 1 }

catmtCidStatsEntry  OBJECT-TYPE
    SYNTAX        CatmtCidStatsEntry
    MAX-ACCESS    not-accessible
    STATUS        current
    DESCRIPTION
        "This table contains statistical information for an AAL2
         connection. Each entry in this table corresponds to an AAL2
         bearer connection that has been setup by mapping one or
         more DS1/DS0s to an AAL2 connection identified by CID.

         The entries in this table are implicitly created/deleted
         at the time of creation/deletion of entries in the
         catmtCidTable.
        "
    INDEX { ifIndex, catmtCidVpi, catmtCidVci, catmtCid }
    ::= { catmtCidStatsTable  1 }


CatmtCidStatsEntry ::=
    SEQUENCE {
        catmtCidSentPackets                 Counter32SinceReset,
        catmtCidRcvdPackets                 Counter32SinceReset,
        catmtCidSentOctets                  Counter32SinceReset,
        catmtCidRcvdOctets                  Counter32SinceReset,
        catmtCidLostPackets                 Counter32SinceReset,
        catmtCidJitter                      Gauge32,
        catmtCidExtAISCnts                  Counter32SinceReset,
        catmtCidExtRAICnts                  Counter32SinceReset,
        catmtCidConnAISCnts                 Counter32SinceReset,
        catmtCidConnRDICnts                 Counter32SinceReset,
        catmtCidNx64FramesTxToTDM           Counter32SinceReset,
        catmtCidNx64FramesRxFromTDM         Counter32SinceReset,
        catmtCidNx64EncBytesTxToTDM         Counter32SinceReset,
        catmtCidNx64EncBytesRxFromTDM       Counter32SinceReset,
        catmtCidNx64InvalidFCSFrames        Counter32SinceReset,
        catmtCidNx64AbortSeqFrames          Counter32SinceReset,
        catmtCidNx64InvalidShortFrames      Counter32SinceReset,
        catmtCidNx64InvalidLongFrames       Counter32SinceReset,
        catmtCidNx64NoByteAlignErrorFrames  Counter32SinceReset,
        catmtCidNx64RASTimeOutFrames        Counter32SinceReset,
        catmtCidLastResetTime               TimeStamp,
        catmtCidCounterClear                TruthValue
}

catmtCidSentPackets  OBJECT-TYPE
    SYNTAX        Counter32SinceReset
    UNITS         "packets"
    MAX-ACCESS    read-only
    STATUS        current
    DESCRIPTION
        "This object indicates the number of packets sent towards
         network side since the connection setup.
        "
    ::= { catmtCidStatsEntry  1 }

catmtCidRcvdPackets  OBJECT-TYPE
    SYNTAX        Counter32SinceReset
    UNITS         "packets"
    MAX-ACCESS    read-only
    STATUS        current
    DESCRIPTION
        "This object indicates the count of packets received
         from network side since the connection setup.
        "
    ::= { catmtCidStatsEntry  2 }

catmtCidSentOctets  OBJECT-TYPE
    SYNTAX        Counter32SinceReset
    UNITS         "bytes"
    MAX-ACCESS    read-only
    STATUS        current
    DESCRIPTION
        "This object indicates the count of bytes sent towards
         network side since connection setup.
        "
    ::= { catmtCidStatsEntry  3 }

catmtCidRcvdOctets  OBJECT-TYPE
    SYNTAX        Counter32SinceReset
    UNITS         "bytes"
    MAX-ACCESS    read-only
    STATUS        current
    DESCRIPTION
        "This object indicates the count of bytes received from
         network since connection setup.
        "
    ::= { catmtCidStatsEntry  4 }

catmtCidLostPackets  OBJECT-TYPE
    SYNTAX        Counter32SinceReset
    UNITS         "packets"
    MAX-ACCESS    read-only
    STATUS        current
    DESCRIPTION
        "This object indicates the count of packets lost in
         the egress direction (from the network).

         This number is computed based on the expected number
         of packets and the actual number of packets arrived
         from the network.
        "
    ::= { catmtCidStatsEntry  5 }

catmtCidJitter  OBJECT-TYPE
    SYNTAX        Gauge32 (0..65535)
    UNITS          "milliseconds"
    MAX-ACCESS    read-only
    STATUS        current
    DESCRIPTION
        "This object indicates the jitter (a.k.a interarrival jitter).
         This value is determined by the gateway DSP and obtained by
         the processor running on gateway upon querying the DSP
         periodically.
        "
    ::= { catmtCidStatsEntry  6 }

catmtCidExtAISCnts  OBJECT-TYPE
    SYNTAX        Counter32SinceReset
    MAX-ACCESS    read-only
    STATUS        current
    DESCRIPTION
        "This object contains the number of external AIS AAL2 Type3
         packets received.

         External AIS : alarm indication signal associated with
         a maintenance alarm detected on a defective maintenance
         span, that is transmitted in the direction of the defect
         as a substitute for normal signal. The purpose is to show
         the downstream entities that a defect has been identified
         and to prevent other maintenance alarms consequent to this
         first defect.
        "
    REFERENCE
        "ITU-T G.366.2 Annex N"
    ::= { catmtCidStatsEntry 7 }

catmtCidExtRAICnts  OBJECT-TYPE
    SYNTAX       Counter32SinceReset
    MAX-ACCESS   read-only
    STATUS       current
    DESCRIPTION
        "This object contains the number of external RAI AAL2 Type3
         packets received.

         External RAI is transmitted upstream from an entity that
         has detected defects persisting long enough to constitute
         a received signal failure. External RAI is to report in
         the backward direction to indicate there is an interruption
         of service in the forward direction.
        "
    REFERENCE
        "ITU-T G.366.2 Annex N"
    ::= { catmtCidStatsEntry 8 }

catmtCidConnAISCnts  OBJECT-TYPE
    SYNTAX       Counter32SinceReset
    MAX-ACCESS   read-only
    STATUS       current
    DESCRIPTION
        "This object contains the number of external connection AIS
         AAL2 packets received.

         External Conn AIS is a Alarm Indicating Signal transmitted
         in the downstream direction from the AAL2 connecting point
         that first detects the defect affecting the AAL2 connection
         including defects indicated by the lower layers.
        "
    REFERENCE
        "ITU-T G.366.2 Annex N"
    ::= { catmtCidStatsEntry 9 }

catmtCidConnRDICnts  OBJECT-TYPE
    SYNTAX       Counter32SinceReset
    MAX-ACCESS   read-only
    STATUS       current
    DESCRIPTION
        "This object contains the number of external connection
         RDI AAL2 packets received.

         External Connection RDI -  is a signal transmitted in the
         upstream direction by an AAL2 endpoint that is in alarm
         state, as the result of having received an AAL2 connection
         AIS or having detected a defect that affects the AAL2
         connection.
        "
    REFERENCE
        "ITU-T G.366.2 Annex N"
    ::= { catmtCidStatsEntry 10 }

catmtCidNx64FramesTxToTDM  OBJECT-TYPE
    SYNTAX       Counter32SinceReset
    MAX-ACCESS   read-only
    STATUS       current
    DESCRIPTION
        "This object contains the number of frames transmitted
         to the TDM interface.

         This object is only applicable when catmtCidNx64Mode
         is set to to 'hdlc'.
        "
    ::= { catmtCidStatsEntry 11 }

catmtCidNx64FramesRxFromTDM  OBJECT-TYPE
    SYNTAX       Counter32SinceReset
    MAX-ACCESS   read-only
    STATUS       current
    DESCRIPTION
        "This object contains the number of frames received from
         the TDM interface.

         This object is only applicable when catmtCidNx64Mode is
         set to to 'hdlc'.
        "
    ::= { catmtCidStatsEntry 12 }

catmtCidNx64EncBytesTxToTDM  OBJECT-TYPE
    SYNTAX       Counter32SinceReset
    MAX-ACCESS   read-only
    STATUS       current
    DESCRIPTION
        "This object contains the number of encoded bytes
         transmitted to the TDM interface.
        "
    ::= { catmtCidStatsEntry 13 }

catmtCidNx64EncBytesRxFromTDM  OBJECT-TYPE
    SYNTAX       Counter32SinceReset
    MAX-ACCESS   read-only
    STATUS       current
    DESCRIPTION
        "This object contains the number of encoded bytes
         received from the TDM interface.
        "
    ::= { catmtCidStatsEntry 14 }

catmtCidNx64InvalidFCSFrames  OBJECT-TYPE
    SYNTAX       Counter32SinceReset
    MAX-ACCESS   read-only
    STATUS       current
    DESCRIPTION
        "This object contains the number of invalid frames
         received with invalid Frame Check Sequence (FCS) error.

         This object is only applicable when catmtCidNx64Mode is
         set to to 'hdlc'.
        "
    ::= { catmtCidStatsEntry 15 }

catmtCidNx64AbortSeqFrames  OBJECT-TYPE
    SYNTAX       Counter32SinceReset
    MAX-ACCESS   read-only
    STATUS       current
    DESCRIPTION
        "This object contains the number of invalid frames
         received with invalid frame abort sequence error.

         This object is only applicable when catmtCidNx64Mode
         is set to to 'hdlc'.
        "
    ::= { catmtCidStatsEntry 16 }

catmtCidNx64InvalidShortFrames OBJECT-TYPE
    SYNTAX       Counter32SinceReset
    MAX-ACCESS   read-only
    STATUS       current
    DESCRIPTION
        "This object contains the number of invalid short
         frames (length less than minimum length) received.

         This object is only applicable when catmtCidNx64Mode
         is set to to 'hdlc'.
        "
    ::= { catmtCidStatsEntry 17 }

catmtCidNx64InvalidLongFrames  OBJECT-TYPE
    SYNTAX       Counter32SinceReset
    MAX-ACCESS   read-only
    STATUS       current
    DESCRIPTION
        "This object contains the number of invalid long
         frames (length greater than maximum length) received.

         This object is only applicable when catmtCidNx64Mode
         is set to to 'hdlc'.
        "
    ::= { catmtCidStatsEntry 18 }

catmtCidNx64NoByteAlignErrorFrames  OBJECT-TYPE
    SYNTAX       Counter32SinceReset
    MAX-ACCESS   read-only
    STATUS       current
    DESCRIPTION
        "This object contains the number of invalid frames
         received with no byte alignment.

         This object is only applicable when catmtCidNx64Mode
         is set to to 'hdlc'.
        "
    ::= { catmtCidStatsEntry 19 }

catmtCidNx64RASTimeOutFrames  OBJECT-TYPE
    SYNTAX       Counter32SinceReset
    MAX-ACCESS   read-only
    STATUS       current
    DESCRIPTION
        "This object contains the number of frames received
         with RAS timer timeout.

         This object is only applicable when catmtCidNx64Mode
         is set to to 'hdlc'.
          "
    ::= { catmtCidStatsEntry 20 }

catmtCidLastResetTime  OBJECT-TYPE
    SYNTAX       TimeStamp
    MAX-ACCESS   read-only
    STATUS       current
    DESCRIPTION
        "This object contains the value of sysUpTime when the
         last counter reset occurred.

         If no counter reset has occurred since the last time
         connection is established, this object will contain
         value of zero.
        "
    ::= { catmtCidStatsEntry  21 }

catmtCidCounterClear  OBJECT-TYPE
    SYNTAX       TruthValue
    MAX-ACCESS   read-write
    STATUS       current
    DESCRIPTION
        "When this object is set to value of true(1), all statistics
         counters with type of Counter32SinceReset in the table
         catmtCidStatsTable will be reset to zero.

         Setting this object to a value of false(2) has no implication.

         This object will always return 'false' upon any SNMP
         get operation. I
        "
    ::= { catmtCidStatsEntry  22 }

--
--   AAL1 Trunking MIB
--
catmtAal1Table  OBJECT-TYPE
    SYNTAX       SEQUENCE OF CatmtAal1Entry
    MAX-ACCESS   not-accessible
    STATUS       current
    DESCRIPTION
        "This table is used to establish the mapping of a
         DS0 to an AAL1 ATM connection.

         This table is created and used for ATM AAL1 trunking
         applications only.
        "
    ::= { cAtmTrunkAal1Config 1 }

catmtAal1Entry  OBJECT-TYPE
    SYNTAX       CatmtAal1Entry
    MAX-ACCESS   not-accessible
    STATUS       current
    DESCRIPTION
        "An entry in the catmtAal1Table.

         Each entry represents an AAL1 trunking connection which
         is uniquely identified by the PVC index.

         An AAL1 trunking connection is established by binding
         one or more DS0(s) from one single DS1 interface
         to an AAL1 ATM connection identified the PVC index.
        "
    INDEX { ifIndex, catmtAal1Vpi, catmtAal1Vci }
    ::= { catmtAal1Table 1 }


CatmtAal1Entry ::=
    SEQUENCE {
       catmtAal1Vpi            Unsigned32,
       catmtAal1Vci            Unsigned32,
       catmtAal1Ds1            InterfaceIndex,
       catmtAal1Ds0GroupIndex  Integer32,
       catmtAal1Nx64Profile    Integer32,
       catmtAal1RowStatus      RowStatus
}

catmtAal1Vpi  OBJECT-TYPE
    SYNTAX        Unsigned32 (0..4095)
    MAX-ACCESS    not-accessible
    STATUS        current
    DESCRIPTION
        "This object is the VPI value of an ATM PVC connection.
        "
    ::= { catmtAal1Entry  1 }

catmtAal1Vci  OBJECT-TYPE
    SYNTAX        Unsigned32 (0..65535)
    MAX-ACCESS    not-accessible
    STATUS        current
    DESCRIPTION
        "This object is the VCI value of an ATM PVC connection.
        "
    ::= { catmtAal1Entry  2 }

catmtAal1Ds1  OBJECT-TYPE
    SYNTAX       InterfaceIndex
    MAX-ACCESS   read-create
    STATUS       current
    DESCRIPTION
        "The value of this object is equivalent to the 'ifIndex'
         of the DS1 interface.

         This object is mandatory when adding an AAL1 entry.
         Once an AAL1 entry is added, this object can not be
         modified.
        "
    ::= { catmtAal1Entry  3 }

catmtAal1Ds0GroupIndex  OBJECT-TYPE
    SYNTAX       Integer32 (0..30)
    MAX-ACCESS   read-create
    STATUS       current
    DESCRIPTION
        "An arbitrary index that uniquely identifies one or a group
         of DS0s to be connected to an AAL1 trunking connection.

         When catmtAal1Nx64Enable is set to 'false', the AAL1
         trunking connection can only be a mapping of one single DS0
         to one AAL1 ATM connection.

         This object is mandatory when adding an AAL1 entry. Once
         an AAL1 entry is added, this object can not be modified.
        "
    ::= { catmtAal1Entry  4 }

catmtAal1Nx64Profile  OBJECT-TYPE
   SYNTAX        Integer32 (1..65535)
   MAX-ACCESS    read-create
   STATUS        current
   DESCRIPTION
       "This object specifies the Nx64 AAL1 data profile for an AAL1
        trunking connection.

        The value of this object is a valid index of
        cdapNx64Aal1ProfileTable in CISCO-DATA-AALX-PROFILE-MIB.
       "
   DEFVAL { 1 }
   ::= { catmtAal1Entry 5 }

catmtAal1RowStatus  OBJECT-TYPE
    SYNTAX       RowStatus
    MAX-ACCESS   read-create
    STATUS       current
    DESCRIPTION
        "This object is used for adding/deleting the entries from
         the catmtAal1Table.

         In order to create an AAL1 trunking entry, the following
         parameters are mandatory and must be provided:
                 catmtAal1Ds1,
                 catmtAal1Ds0GroupIdx
        "
    ::= { catmtAal1Entry 6 }


--
--   AAL1 Trunking Statistics MIB
--
catmtAal1StatsTable  OBJECT-TYPE
    SYNTAX  SEQUENCE OF CatmtAal1StatsEntry
    MAX-ACCESS   not-accessible
    STATUS       current
    DESCRIPTION
        "This table contains the statistics information
         on a per AAL1 connection basis for ATM AAL1
         Trunking applications.
        "
    ::= { cAtmTrunkAal1ConnStats 1 }


catmtAal1StatsEntry  OBJECT-TYPE
    SYNTAX       CatmtAal1StatsEntry
    MAX-ACCESS   not-accessible
    STATUS       current
    DESCRIPTION
        "This table contains statistics information for an AAL1
         trunking connection.

         Each entry in this table corresponds to an AAL1 connection
         that has been setup by binding an DS0 to an AAL1 connection
         identified by (ifIndex, catmtAal1Vpi, catmtAal1Vci).

         The entries in this table are implicitly created/deleted
         at the time of creation/deletion of entries in the
         catmtAal1Table.
        "
    INDEX { ifIndex, catmtAal1Vpi, catmtAal1Vci }
    ::= { catmtAal1StatsTable  1 }

CatmtAal1StatsEntry ::=
    SEQUENCE {
        catmtAal1TxCells            Counter32SinceReset,
        catmtAal1RxCells            Counter32SinceReset,
        catmtAal1TxPayloadBytes     Counter32SinceReset,
        catmtAal1RxPayloadBytes     Counter32SinceReset,
        catmtAal1Jitter             Gauge32,
        catmtAal1LastResetTime      TimeStamp,
        catmtAal1CounterClear       TruthValue
}

catmtAal1TxCells  OBJECT-TYPE
    SYNTAX       Counter32SinceReset
    MAX-ACCESS   read-only
    STATUS       current
    DESCRIPTION
        "This object contains the number of ATM AAL1 cells
         transmitted from gateway to ATM network.
        "
    ::= { catmtAal1StatsEntry 1 }

catmtAal1RxCells  OBJECT-TYPE
    SYNTAX       Counter32SinceReset
    MAX-ACCESS   read-only
    STATUS       current
    DESCRIPTION
        "This object contains the number of ATM AAL1 cells
         gateway has received from ATM network.
        "
    ::= { catmtAal1StatsEntry 2 }

catmtAal1TxPayloadBytes  OBJECT-TYPE
    SYNTAX       Counter32SinceReset
    MAX-ACCESS   read-only
    STATUS       current
    DESCRIPTION
        "This object contains the number of payload bytes
         transmitted from gateway to ATM network.
        "
    ::= { catmtAal1StatsEntry 3 }

catmtAal1RxPayloadBytes  OBJECT-TYPE
    SYNTAX       Counter32SinceReset
    MAX-ACCESS   read-only
    STATUS       current
    DESCRIPTION
        "This object contains the number of payload bytes
         gateway has received from ATM network.
        "
    ::= { catmtAal1StatsEntry 4 }

catmtAal1Jitter  OBJECT-TYPE
    SYNTAX       Gauge32
    MAX-ACCESS   read-only
    STATUS       current
    DESCRIPTION
        "This object indicates the jitter (a.k.a interarrival jitter).

         The value of this object is determined by the gateway DSP
         and obtained by the processor running on gateway upon querying
         the DSP periodically.
        "
    ::= { catmtAal1StatsEntry 5 }

catmtAal1LastResetTime  OBJECT-TYPE
    SYNTAX       TimeStamp
    MAX-ACCESS   read-only
    STATUS       current
    DESCRIPTION
        "This object contains the value of sysUpTime when the
         last counter reset occurred.

         If no counter reset has occurred since the last time
         system is up, this object will contain value of zero.
        "
    ::= { catmtAal1StatsEntry 6 }

catmtAal1CounterClear  OBJECT-TYPE
    SYNTAX       TruthValue
    MAX-ACCESS   read-write
    STATUS       current
    DESCRIPTION
        "When this object is set to value of true(1), all statistics
         counters with type of Counter32SinceReset in the table
         catmtAal1StatsTable will be reset to zero.

         Setting this object to value of false(2) has no implication.

         This object will always return 'false' upon any SNMP
         get operation. I
        "
    ::= { catmtAal1StatsEntry 7 }


--
--   AAL5 Trunking MIB
--
catmtAal5Table  OBJECT-TYPE
    SYNTAX       SEQUENCE OF CatmtAal5Entry
    MAX-ACCESS   not-accessible
    STATUS       current
    DESCRIPTION
        "This table is used to establish the mapping of a
         DS0 to an AAL5 ATM connection.

         This table is created and used for ATM AAL5
         trunking applications only.
        "
    ::= { cAtmTrunkAal5Config 1 }

catmtAal5Entry  OBJECT-TYPE
    SYNTAX       CatmtAal5Entry
    MAX-ACCESS   not-accessible
    STATUS       current
    DESCRIPTION
        "An entry in the catmtAal5Table.

         Each entry represents an AAL5 trunking connection which
         is uniquely identified by the PVC index.

         An AAL5 trunking connection is established by binding
         a DS0 group voice interface containing one or more DS0
         channels from one single DS1 interface to an AAL5 ATM
         connection identified the PVC index.
        "
    INDEX { ifIndex, catmtAal5Vpi, catmtAal5Vci }
    ::= { catmtAal5Table 1 }



CatmtAal5Entry ::=
    SEQUENCE {
       catmtAal5Vpi                   Unsigned32,
       catmtAal5Vci                   Unsigned32,
       catmtAal5Ds1                   InterfaceIndex,
       catmtAal5Ds0GroupIndex         Integer32,
       catmtAal5Nx64Profile           Integer32,
       catmtAal5RowStatus             RowStatus
}

catmtAal5Vpi  OBJECT-TYPE
    SYNTAX        Unsigned32 (0..4095)
    MAX-ACCESS    not-accessible
    STATUS        current
    DESCRIPTION
        "This object is the VPI value of an ATM PVC connection."
    ::= { catmtAal5Entry 1 }

catmtAal5Vci  OBJECT-TYPE
    SYNTAX        Unsigned32 (0..65535)
    MAX-ACCESS    not-accessible
    STATUS        current
    DESCRIPTION
        "This object is the VCI value of an ATM PVC connection."
    ::= { catmtAal5Entry 2 }

catmtAal5Ds1  OBJECT-TYPE
    SYNTAX       InterfaceIndex
    MAX-ACCESS   read-create
    STATUS       current
    DESCRIPTION
        "The value of this object equals to the 'ifIndex' of
         the DS1 interface.

         This object is mandatory when adding an AAL5 entry.
         Once an AAL5 entry is added, this object can not be
         modified.
        "
    ::= { catmtAal5Entry 3 }

catmtAal5Ds0GroupIndex  OBJECT-TYPE
    SYNTAX       Integer32 (0..30)
    MAX-ACCESS   read-create
    STATUS       current
    DESCRIPTION
        "An arbitrary index that uniquely identifies a DS0 group
         containing one or more DS0 that connect to an AAL5
         trunking connection.

         This object is mandatory when adding an AAL5 entry. Once
         an AAL5 entry is added, this object can not be modified.
        "
    ::= { catmtAal5Entry 4 }

catmtAal5Nx64Profile  OBJECT-TYPE
    SYNTAX       Integer32 (1..65535)
    MAX-ACCESS   read-create
    STATUS       current
    DESCRIPTION
        "This object specifies the Nx64 data profile for an AAL5
         trunking connection.

         The value of this object is a valid index of the
         cdapNx64ProfileTable in CISCO-DATA-AALX-PROFILE-MIB.
        "
    DEFVAL {1}
    ::= { catmtAal5Entry 5 }

catmtAal5RowStatus  OBJECT-TYPE
    SYNTAX       RowStatus
    MAX-ACCESS   read-create
    STATUS       current
    DESCRIPTION
        "This object is used for adding/deleting the entries from
         the catmtAal5Table.

         In order to create an AAL5 trunking entry, the following
         parameters are mandatory and must be provided:
                catmtAal5Ds1,
                catmtAal5Ds0GroupIdx
        "
    ::= { catmtAal5Entry 6 }


--
--   AAL5 Trunking Statistics MIB
--
catmtAal5StatsTable  OBJECT-TYPE
    SYNTAX  SEQUENCE OF CatmtAal5StatsEntry
    MAX-ACCESS   not-accessible
    STATUS       current
    DESCRIPTION
        "This table contains the statistical information
         on a per AAL5 connection basis for ATM AAL5
         Trunking applications.
        "
    ::= { cAtmTrunkAal5ConnStats 1 }

catmtAal5StatsEntry  OBJECT-TYPE
    SYNTAX       CatmtAal5StatsEntry
    MAX-ACCESS   not-accessible
    STATUS       current
    DESCRIPTION
        "This table contains statistical information for an AAL5
         trunking connection.

         Each entry in this table corresponds to an AAL5 connection
         that has been setup by mapping one or more DS0(s) to an
         AAL5 connection identified by ifIndex, catmtAal5Vpi and
         atmtAal5Vci.

         The entries in this table are implicitly created/deleted
         at the time of creation/deletion of entries in the
         catmtAal5Table.
        "
    INDEX { ifIndex, catmtAal5Vpi, catmtAal5Vci }
    ::= { catmtAal5StatsTable  1 }


CatmtAal5StatsEntry ::=
    SEQUENCE {
        catmtAal5SentPackets             Counter32SinceReset,
        catmtAal5RcvdPackets             Counter32SinceReset,
        catmtAal5SentOctets              Counter32SinceReset,
        catmtAal5RcvdOctets              Counter32SinceReset,
        catmtAal5FramesTxToTDM           Counter32SinceReset,
        catmtAal5FramesRxFromTDM         Counter32SinceReset,
        catmtAal5EncBytesTxToTDM         Counter32SinceReset,
        catmtAal5EncBytesRxFromTDM       Counter32SinceReset,
        catmtAal5InvalidFCSFrames        Counter32SinceReset,
        catmtAal5AbortSeqFrames          Counter32SinceReset,
        catmtAal5InvalidShortFrames      Counter32SinceReset,
        catmtAal5InvalidLongFrames       Counter32SinceReset,
        catmtAal5NoByteAlignErrorFrames  Counter32SinceReset,
        catmtAal5LastResetTime           TimeStamp,
        catmtAal5CounterClear            TruthValue
}

catmtAal5SentPackets  OBJECT-TYPE
    SYNTAX       Counter32SinceReset
    UNITS        "packets"
    MAX-ACCESS   read-only
    STATUS       current
    DESCRIPTION
        "This object indicates the number of packets sent towards
         network side since the connection is up.
        "
    ::= { catmtAal5StatsEntry 1 }

catmtAal5RcvdPackets  OBJECT-TYPE
    SYNTAX       Counter32SinceReset
    UNITS        "packets"
    MAX-ACCESS   read-only
    STATUS       current
    DESCRIPTION
        "This object indicates the count of packets received
         from network side since the connection setup.
         "
    ::= { catmtAal5StatsEntry 2 }

catmtAal5SentOctets  OBJECT-TYPE
    SYNTAX       Counter32SinceReset
    UNITS        "bytes"
    MAX-ACCESS   read-only
    STATUS       current
    DESCRIPTION
        "This object indicates the count of bytes sent towards
         network side since connection setup.
        "
    ::= { catmtAal5StatsEntry 3 }

catmtAal5RcvdOctets  OBJECT-TYPE
    SYNTAX       Counter32SinceReset
    UNITS        "bytes"
    MAX-ACCESS   read-only
    STATUS       current
    DESCRIPTION
        "This object indicates the count of bytes received from
         network since connection setup.
        "
    ::= { catmtAal5StatsEntry 4 }

catmtAal5FramesTxToTDM  OBJECT-TYPE
    SYNTAX       Counter32SinceReset
    MAX-ACCESS   read-only
    STATUS       current
    DESCRIPTION
        "This object contains the number of frames transmitted
         to the TDM interface.

         This object is only applicable when catmtAal5Nx64Mode
         is set to to 'hdlc'.
        "
    ::= { catmtAal5StatsEntry 5 }

catmtAal5FramesRxFromTDM  OBJECT-TYPE
    SYNTAX       Counter32SinceReset
    MAX-ACCESS   read-only
    STATUS       current
    DESCRIPTION
        "This object contains the number of frames received from
         the TDM interface.

         This object is only applicable when catmtAal5Nx64Mode
         is set to to 'hdlc'.
        "
    ::= { catmtAal5StatsEntry 6 }

catmtAal5EncBytesTxToTDM  OBJECT-TYPE
    SYNTAX       Counter32SinceReset
    MAX-ACCESS   read-only
    STATUS       current
    DESCRIPTION
        "This object contains the number of encoded bytes
         transmitted to the TDM interface.
        "
    ::= { catmtAal5StatsEntry 7 }

catmtAal5EncBytesRxFromTDM  OBJECT-TYPE
    SYNTAX       Counter32SinceReset
    MAX-ACCESS   read-only
    STATUS       current
    DESCRIPTION
        "This object contains the number of encoded bytes
         received from TDM interface.
        "
    ::= { catmtAal5StatsEntry 8 }

catmtAal5InvalidFCSFrames  OBJECT-TYPE
    SYNTAX       Counter32SinceReset
    MAX-ACCESS   read-only
    STATUS       current
    DESCRIPTION
        "This object contains the number of invalid frames
         received with invalid Frame Check Sequence (FCS)
         error.

         This object is only applicable when catmtAal5Nx64Mode
         is set to to 'hdlc'.
        "
    ::= { catmtAal5StatsEntry 9 }

catmtAal5AbortSeqFrames  OBJECT-TYPE
    SYNTAX       Counter32SinceReset
    MAX-ACCESS   read-only
    STATUS       current
    DESCRIPTION
        "This object contains the number of invalid frames
         received with invalid frame abort sequence error.

         This object is only applicable when catmtAal5Nx64Mode
         is set to to 'hdlc'.
        "
    ::= { catmtAal5StatsEntry 10 }

catmtAal5InvalidShortFrames  OBJECT-TYPE
    SYNTAX       Counter32SinceReset
    MAX-ACCESS   read-only
    STATUS       current
    DESCRIPTION
        "This object contains the number of invalid short
         frames (length less than minimum length) received.

         This object is only applicable when catmtAal5Nx64Mode
         is set to to 'hdlc'.
        "
    ::= { catmtAal5StatsEntry 11 }

catmtAal5InvalidLongFrames  OBJECT-TYPE
    SYNTAX       Counter32SinceReset
    MAX-ACCESS   read-only
    STATUS       current
    DESCRIPTION
        "This object contains the number of invalid long
         frames (length greater than maximum length) received.

         This object is only applicable when catmtAal5Nx64Mode
         is set to to 'hdlc'.
        "
      ::= { catmtAal5StatsEntry 12 }

catmtAal5NoByteAlignErrorFrames  OBJECT-TYPE
    SYNTAX       Counter32SinceReset
    MAX-ACCESS   read-only
    STATUS       current
    DESCRIPTION
        "This object contains the number of invalid frames
         received with no byte alignment.

         This object is only applicable when catmtAal5Nx64Mode
         is set to to 'hdlc'.
        "
    ::= { catmtAal5StatsEntry 13 }

catmtAal5LastResetTime  OBJECT-TYPE
    SYNTAX       TimeStamp
    MAX-ACCESS   read-only
    STATUS       current
    DESCRIPTION
        "This object contains the value of sysUpTime when the
         last counter reset occurred.

         If no counter reset has occurred since the last time
         system is up, this object will contain value of zero.
        "
    ::= { catmtAal5StatsEntry 14 }

catmtAal5CounterClear  OBJECT-TYPE
    SYNTAX       TruthValue
    MAX-ACCESS   read-write
    STATUS       current
    DESCRIPTION
        "When this object is set to value of true(1), all statistics
         counters with type of Counter32SinceReset in the table
         catmtAal5StatsTable will be reset to zero.

         Setting this object to a value of false(2) has no implication.

         This object will always return 'false' upon any SNMP
         get operation. I
        "
    ::= { catmtAal5StatsEntry  15 }

--
-- conformance information
--

cAtmTrunkMIBConformance
      OBJECT IDENTIFIER ::= { ciscoAtmTrunkMIB 2 }
cAtmTrunkMIBCompliances
      OBJECT IDENTIFIER ::= { cAtmTrunkMIBConformance 1 }
cAtmTrunkMIBGroups
      OBJECT IDENTIFIER ::= { cAtmTrunkMIBConformance 2 }

-- compliance statements


cAtmTrunkMIBCompliance MODULE-COMPLIANCE
     STATUS current
     DESCRIPTION
         "Compliance statement for CISCO-VOICE-ATM-TRUNK-MIB."
          MODULE -- this module
          MANDATORY-GROUPS {
               cAtmTrunkCidMIBGroup,
               cAtmTrunkAal1MIBGroup,
               cAtmTrunkAal5MIBGroup,
               cAtmTrunkCidConnStatsMIBGroup,
               cAtmTrunkAal1ConnStatsMIBGroup,
               cAtmTrunkAal5ConnStatsMIBGroup
         }
     ::= { cAtmTrunkMIBCompliances 1 }


--
-- units of conformance
--

cAtmTrunkCidMIBGroup OBJECT-GROUP
   OBJECTS {
        catmtCidDs1,
        catmtCidDs0GroupIndex,
        catmtCidProfileType,
        catmtCidProfileNumber,
        catmtCidVoiceCodec,
        catmtCidVBDCodec,
        catmtCidNx64Enable,
        catmtCidNx64Profile,
        catmtCidStateBitMap,
        catmtCidRepetition,
        catmtCidRepetitionOwner,
        catmtCidRepetitionResult,
        catmtCidRowStatus
        }
    STATUS current
    DESCRIPTION
        "This group contains objects related to
         ATM AAL2 trunking CID level parameters."
    ::= { cAtmTrunkMIBGroups 1}


cAtmTrunkAal1MIBGroup OBJECT-GROUP
   OBJECTS {
        catmtAal1Ds1,
        catmtAal1Ds0GroupIndex,
        catmtAal1Nx64Profile,
        catmtAal1RowStatus
        }
    STATUS current
    DESCRIPTION
        "This group contains objects related to
         ATM AAL1 trunking parameters."
    ::= { cAtmTrunkMIBGroups 2}


cAtmTrunkAal5MIBGroup OBJECT-GROUP
   OBJECTS {
        catmtAal5Ds1,
        catmtAal5Ds0GroupIndex,
        catmtAal5Nx64Profile,
        catmtAal5RowStatus
        }
    STATUS current
    DESCRIPTION
        "This group contains objects related to
         ATM AAL5 trunking parameters."
    ::= { cAtmTrunkMIBGroups 3}



cAtmTrunkCidConnStatsMIBGroup        OBJECT-GROUP
   OBJECTS {
           catmtCidSentPackets,
           catmtCidRcvdPackets,
           catmtCidSentOctets,
           catmtCidRcvdOctets,
           catmtCidLostPackets,
           catmtCidJitter,
           catmtCidExtAISCnts,
           catmtCidExtRAICnts,
           catmtCidConnAISCnts,
           catmtCidConnRDICnts,
           catmtCidNx64FramesTxToTDM,
           catmtCidNx64FramesRxFromTDM,
           catmtCidNx64EncBytesTxToTDM,
           catmtCidNx64EncBytesRxFromTDM,
           catmtCidNx64InvalidFCSFrames,
           catmtCidNx64AbortSeqFrames,
           catmtCidNx64InvalidShortFrames,
           catmtCidNx64InvalidLongFrames,
           catmtCidNx64NoByteAlignErrorFrames,
           catmtCidNx64RASTimeOutFrames,
           catmtCidLastResetTime,
           catmtCidCounterClear
           }
    STATUS current
    DESCRIPTION
        "This group contains objects for AAL2 bearer connection
         statistics information used for ATM AAL2 trunking."
    ::= { cAtmTrunkMIBGroups 4}


cAtmTrunkAal1ConnStatsMIBGroup        OBJECT-GROUP
   OBJECTS {
           catmtAal1TxCells,
           catmtAal1RxCells,
           catmtAal1TxPayloadBytes,
           catmtAal1RxPayloadBytes,
           catmtAal1Jitter,
           catmtAal1LastResetTime,
           catmtAal1CounterClear
           }
    STATUS current
    DESCRIPTION
        "This group contains objects for AAL1 connection
         statistics information used for ATM AAL1 trunking."
    ::= { cAtmTrunkMIBGroups 5}


cAtmTrunkAal5ConnStatsMIBGroup        OBJECT-GROUP
   OBJECTS {
           catmtAal5SentPackets,
           catmtAal5RcvdPackets,
           catmtAal5SentOctets,
           catmtAal5RcvdOctets,
           catmtAal5FramesTxToTDM,
           catmtAal5FramesRxFromTDM,
           catmtAal5EncBytesTxToTDM,
           catmtAal5EncBytesRxFromTDM,
           catmtAal5InvalidFCSFrames,
           catmtAal5AbortSeqFrames,
           catmtAal5InvalidShortFrames,
           catmtAal5InvalidLongFrames,
           catmtAal5NoByteAlignErrorFrames,
           catmtAal5LastResetTime,
           catmtAal5CounterClear
           }
    STATUS current
    DESCRIPTION
        "This group contains objects for AAL5 bearer connection
         statistics information used for ATM AAL5 trunking."
    ::= { cAtmTrunkMIBGroups 6}

END
