-- *****************************************************************
-- CISCO-VIDEO-SESSION-MIB.my: Video Session MIB file
--
-- Jan, 2010, Valerie Wong
--
-- Copyright (c) 2010-2011 by cisco Systems Inc.
-- All rights reserved.
--
-- *****************************************************************

CISCO-VIDEO-SESSION-MIB DEFINITIONS ::= BEGIN

IMPORTS
    MODULE-IDENTITY,
    OBJECT-TYPE,
    Gauge32,
    Counter64,
    Unsigned32
        FROM SNMPv2-SMI
    MODULE-COMPLIANCE,
    OBJECT-GROUP
        FROM SNMPv2-CONF
    TEXTUAL-CONVENTION
        FROM SNMPv2-TC
    AbsoluteCounter32,
    callActiveSetupTime,
    callActiveIndex
        FROM DIAL-CONTROL-MIB
    CvcVideoLevel,
    CvcVideoProfile,
    CvcVideoCodecAnnexMap,
    CvcVideoRtpPayloadFormat
        FROM CISCO-VIDEO-TC
    CvcGUid,
    CvcVideoCoderRate,
    CvcCallReferenceIdOrZero
        FROM CISCO-VOICE-COMMON-DIAL-CONTROL-MIB
    cCallHistoryIndex
        FROM CISCO-DIAL-CONTROL-MIB
    ciscoMgmt
        FROM CISCO-SMI;


ciscoVideoSessionMIB MODULE-IDENTITY
    LAST-UPDATED    "201104200000Z"
    ORGANIZATION    "Cisco Systems, Inc."
    CONTACT-INFO
            "Cisco Systems
            Customer Service

            Postal: 170 W Tasman Drive
            San Jose, CA  95134
            USA

            Tel: +1 800 553-NETS

            E-mail: cs-<list>@cisco.com"
    DESCRIPTION
        "This MIB module complements the CISCO-VOICE-DIAL-CONTROL-MIB,
        which provides voice telephony peer information, by providing
        management of video telephony peer information.  This MIB
        module
        enhances the IETF Dial Control MIB (RFC2128) by providing video
        call information over an IP network.

        A video call is different from an audio call in that a video
        call typically consists of 2 call legs - audio and video - and
        each call leg is represented by one call entry.  Therefore,
        each video call creates 2 call entries.  In order to associate
        the video and audio entries of the same video call, a call
        reference ID is used, i.e., the video and audio entries of the
        same video call have the same call reference ID.

        There are 4 tables (Common, Common Statistics, Conferee and
        Call) in this MIB, where each table contains different
        information depending on the
        type of the video call:
        1. 'common' and 'common statistics' table entries are created
        for all video calls;
        2. A 'conferee' table entry is created for calls that belong to
        a video conference; conferee means a participant of a
        conference; and
        3. A 'call' table entry is created for point-to-point video
        calls.
        I.e., for a video conference call, there are valid information
        in the 'common,' 'common statistics' and 'conferee' tables; for
        a video point-to-point call, there are valid information in the
        'common,' 'common statistics' and 'call' tables.

        Transmit(TX) and Receive(RX) Directions:
        The video stream direction is defined with respect to the video
        endpoint.  I.e., transmit(TX) refers to the video stream sent by
        the endpoint and receive(RX) refers to the video stream received
        by the endpoint.

        REFERENCE
        [1] RFC 2128 Dial Control Management Information
        Base using SMIv2."
    REVISION        "201104200000Z"
    DESCRIPTION
        "1.  Deprecated video-specific textual conventions and import
        them from CISCO-VIDEO-TC instead : CvcVideoLevel,
        CvcVideoProfile, CvcVideoCodecAnnexMap and CvcRtpPayloadFormat.

        2.  Added cVideoCommonHistorySessionId and
        cVideoCommonActiveSessionId to cVideoCommonHistoryTable and
        cVideoCommonActiveTable, respectively.

        3.  Added monitoredCall to CvcVoIPCallServiceType TC.

        4.  Added cVideoCommonStatsHistoryTable with these objects:
        cVideoCommonStatsHistoryTxTotalLostPackets,
        cVideoCommonStatsHistoryTxPercentLostPackets,
        cVideoCommonStatsHistoryTxTotalOutOfOrderPackets,
        cVideoCommonStatsHistoryTxMaxJitter,
        cVideoCommonStatsHistoryTxAvgJitter,
        cVideoCommonStatsHistoryTxMaxDelay,
        cVideoCommonStatsHistoryTxAvgDelay,
        cVideoCommonStatsHistoryRxTotalLostPackets and
        cVideoCommonStatsHistoryRxPercentLostPackets.

        5.  Added cVideoCommonStatsActiveTable with these objects:
        cVideoCommonStatsActiveTxActualBitrate,
        cVideoCommonStatsActiveTxTotalLostPackets,
        cVideoCommonStatsActiveTxPercentLostPackets,
        cVideoCommonStatsActiveTxCurrentLostPackets,
        cVideoCommonStatsActiveTxTotalOutOfOrderPackets,
        cVideoCommonStatsActiveTxCurrentOutOfOrderPackets,
        cVideoCommonStatsActiveTxMaxJitter,
        cVideoCommonStatsActiveTxAvgJitter,
        cVideoCommonStatsActiveTxCurrentJitter,
        cVideoCommonStatsActiveTxMaxDelay,
        cVideoCommonStatsActiveTxAvgDelay,
        cVideoCommonStatsActiveTxCurrentDelay,
        cVideoCommonStatsActiveRxActualBitrate,
        cVideoCommonStatsActiveRxTotalLostPackets,
        cVideoCommonStatsActiveRxPercentLostPackets and
        cVideoCommonStatsActiveRxCurrentLostPackets.

        6.  Deprecated cVideoConfereeHistoryMaxJitter,
        cVideoConfereeHistoryMaxDelay,
        cVideoConfereeHistoryTotalOutOfOrderPackets and
        cVideoConfereeHistoryTotalLostPackets from
        cVideoConfereeHistoryTable, replacing them with
        cVideoCommonStatsHistoryTxMaxJitter,
        cVideoCommonStatsHistoryTxMaxDelay,
        cVideoCommonStatsHistoryTxTotalOutOfOrderPackets and
        cVideoCommonStatsHistoryTxTotalLostPackets, respectively, in
        cVideoCommonStatsHistoryTable.

        7.  Deprecated cVideoCallHistoryTxOutOfOrderPackets and
        cVideoCallHistoryTxLostPackets in cVideoCallHistoryTable,
        replacing them with
        cVideoCommonStatsHistoryTxTotalOutOfOrderPackets and
        cVideoCommonStatsHistoryTxTotalLostPackets, respectively, in
        cVideoCommonStatsHistoryTable.

        8.  Deprecated cVideoConfereeActiveActualBitrate,
        cVideoConfereeActiveTable,
        cVideoConfereeActiveTotalOutOfOrderPackets,
        cVideoConfereeActiveCurrentOutOfOrderPackets,
        cVideoConfereeActiveTotalLostPackets,
        cVideoConfereeActiveCurrentLostPackets,
        cVideoConfereeActiveMaxJitter,
        cVideoConfereeActiveCurrentJitter, cVideoConfereeActiveMaxDelay
        and cVideoConfereeActiveCurrentDelay, replacing them with
        cVideoCommonStatsActiveTxActualBitrate,
        cVideoCommonStatsActiveTxTotalOutOfOrderPackets,
        cVideoCommonStatsActiveTxCurrentOutOfOrderPackets,
        cVideoCommonStatsActiveTxTotalLostPackets,
        cVideoCommonStatsActiveTxCurrentLostPackets,
        cVideoCommonStatsActiveTxMaxJitter,
        cVideoCommonStatsActiveTxAvgJitter,
        cVideoCommonStatsActiveTxMaxDelay and
        cVideoCommonStatsActiveTxCurrentDelay, respectively, in
        cVideoCommonStatsActiveTable.

        9.  Deprecated cVideoCallActiveRxActualBitrate and
        cVideoCallActiveTxLostPackets in cVideoCallActiveTable,
        replacing them with cVideoCommonStatsActiveRxActualBitrate and
        cVideoCommonStatsActiveTxTotalLostPackets, respectively, in
        cVideoCommonStatsActiveTable.

        10.  Added new compliance groups: cVideoSessionCommonStatusGroup,
        cVideoSessionCommonStatisticsGroup,
        cVideoSessionCallStatisticsGroup and
        cVideoSessionConfereeStatisticsGroup;
        and deprecated old ones: cVideoSessionHistoryGroup and
        cVideoSessionActiveGroup.

        11.  Added new compliance statement
        (cVideoSessionMIBComplianceRev1) to include the new compliance
        groups and deprecated the old one (cVideoSessionMIBCompliance)."
    REVISION        "201007210000Z"
    DESCRIPTION
        "Latest version of this MIB module."
    ::= { ciscoMgmt 753 }



CvcVoIPCallServiceType ::= TEXTUAL-CONVENTION
    STATUS          current
    DESCRIPTION
        "This object describes the call type of this call entry.

        conferenceCall   (1) - This call belongs to a video conference.
        pointToPointCall (2) - This call belongs to a point-to-point
        video call.
        monitoredCall    (3) - This call is monitored for video quality."
    SYNTAX          INTEGER  {
                        conferenceCall(1),
                        pointToPointCall(2),
                        monitoredCall(3),
                        other(255)
                    }

CvcVideoLevel ::= TEXTUAL-CONVENTION
    STATUS          deprecated
    DESCRIPTION
        "This object specifies the H.264 level of the video stream.

        Level 1b  (9)
        Level 1   (10)
        Level 1.1 (11)
        Level 1.2 (12)
        Level 1.3 (13)
        Level 2   (20)
        Level 2.1 (21)
        Level 2.2 (22)
        Level 3   (30)
        Level 3.1 (31)
        Level 3.2 (32)
        Level 4   (40)
        Level 4.1 (41)
        Level 4.2 (42)
        Level 5   (50)
        Level 5.1 (51)

        CvcVideoLevel object is superseded by CvcVideoLevel
        in CISCO-VIDEO-TC."

    REFERENCE       "ITU-T H.264: Annex A.3 Levels"
    SYNTAX          INTEGER  {
                        level1b(9),
                        level1(10),
                        level11(11),
                        level12(12),
                        level13(13),
                        level2(20),
                        level21(21),
                        level22(22),
                        level3(30),
                        level31(31),
                        level32(32),
                        level4(40),
                        level41(41),
                        level42(42),
                        level5(50),
                        level51(51),
                        other(255)
                    }

CvcVideoProfile ::= TEXTUAL-CONVENTION
    STATUS          deprecated
    DESCRIPTION
        "This object specifies the H.264 profile of the video stream.

        H.263 Profiles:
        Profile 0 (10)
        Profile 1 (11)
        Profile 2 (12)
        Profile 3 (13)
        Profile 4 (14)
        Profile 5 (15)
        Profile 6 (16)
        Profile 7 (17)
        Profile 8 (18)

        H.264 Profiles:
        Baseline Profile (100)
        Main Profile (101)
        Extended Profile (102)
        High Profile (103)
        High 10 Profile (104)
        High 4:2:2 Profile (105)
        High 4:4:4 Predictive Profile (106)
        High 10 Intra Profile (107)
        High 4:2:2 Intra Profile (108)
        High 4:4:4 Intra Profile (109)
        CAVLC 4:4:4 Intra Profile (110)

        CvcVideoProfile object is superseded by CvcVideoProfile
        in CISCO-VIDEO-TC."

    REFERENCE
        "ITU-T H.263: Annex X.2 Profiles of preferred mode support
        ITU-T H.264: Annex A.2 Profiles"
    SYNTAX          INTEGER  {
                        h263Profile0(10),
                        h263Profile1(11),
                        h263Profile2(12),
                        h263Profile3(13),
                        h263Profile4(14),
                        h263Profile5(15),
                        h263Profile6(16),
                        h263Profile7(17),
                        h263Profile8(18),
                        h264ProfileBaseline(100),
                        h264ProfileMain(101),
                        h264ProfileExtended(102),
                        h264ProfileHigh(103),
                        h264ProfileHigh10(104),
                        h264ProfileHigh422(105),
                        h264ProfileHigh444Predictive(106),
                        h264ProfileHigh10Intra(107),
                        h264ProfileHigh422Intra(108),
                        h264ProfileHigh444Intra(109),
                        h264ProfileCavlc444Intra(110),
                        other(255)
                    }

CvcVideoCodecAnnexMap ::= TEXTUAL-CONVENTION
    STATUS          deprecated
    DESCRIPTION
        "This is a bit map that describes the annex(es) present for
        the video codec.  Multiple annexes can be present; bits that
        are set to 1 indicate the supported annex(es) correspondingly.

        No annex  - 0x000000 (no bit is on)
        Annex D.1 - 0x000001 (bit 0)
        Annex D.2 - 0x000002 (bit 1)
        Annex E   - 0x000004 (bit 2)
        Annex F   - 0x000008 (bit 3)
        Annex G   - 0x000010 (bit 4)
        Annex H   - 0x000020 (bit 5)
        Annex I   - 0x000040 (bit 6)
        Annex J   - 0x000080 (bit 7)
        Annex K   - 0x000100 (bit 8)
        Annex L   - 0x000200 (bit 9)
        Annex M   - 0x000400 (bit 10)
        Annex N   - 0x000800 (bit 11)
        Annex O   - 0x001000 (bit 12)
        Annex P   - 0x002000 (bit 13)
        Annex Q   - 0x004000 (bit 14)
        Annex R   - 0x008000 (bit 15)
        Annex S   - 0x010000 (bit 16)
        Annex T   - 0x020000 (bit 17)
        Annex U   - 0x040000 (bit 18)
        Annex V   - 0x080000 (bit 19)
        Annex W   - 0x100000 (bit 20)

        CvcVideoCodecAnnexMap object is superseded by CvcVideoCodecAnnexMap
        in CISCO-VIDEO-TC."

    REFERENCE
        "ITU-T H.263
            Annex A - Inverse transform accuracy specification
            Annex B - Hypothetical Reference Decoder
            Annex C - Considerations for multipoint
            Annex D - Unrestricted Motion Vector Mode
            Annex E - Syntax-based Arithmetic Coding mode
            Annex F - Advanced Prediction mode
            Annex G - PB-frames mode
            Annex H - Forward error correction for coded video
        signal
            Annex I - Advanced INTRA Coding mode
            Annex J - Deblocking Filter mode
            Annex K - Slice Structured mode
            Annex L - Supplemental enhancement information
        specification
            Annex M - Improved PB-frames mode
            Annex N - Reference Picture selection mode
            Annex O - Temporal, SNR, and Spatial Scalability mode
            Annex P - Reference picture resampling
            Annex Q - Reduced-Resolution Update mode
            Annex R - Independent Segment Decoding mode
            Annex S - Alternative INTER VLC mode
            Annex T - Modified Quantization mode
            Annex U - Enhanced reference picture selection mode
            Annex V - Data-partitioned slice mode
            Annex W - Additional supplemental enhancement
        information specification

        ITU-T H.264
            Annex C - Hypothetical reference decoder
            Annex D - Supplemental enhancement information
            Annex E - Video usability information
            Annex G - Scalable video coding
            Annex H - Multiview video coding"
    SYNTAX          BITS {
                        annexNone(0),
                        annexD1(1),
                        annexD2(2),
                        annexE(3),
                        annexF(4),
                        annexG(5),
                        annexH(6),
                        annexI(7),
                        annexJ(8),
                        annexK(9),
                        annexL(10),
                        annexM(11),
                        annexN(12),
                        annexO(13),
                        annexP(14),
                        annexQ(15),
                        annexR(16),
                        annexS(17),
                        annexT(18),
                        annexU(19),
                        annexV(20),
                        annexW(21)
                    }

CvcRtpPayloadFormat ::= TEXTUAL-CONVENTION
    STATUS          deprecated
    DESCRIPTION
        "This object specifies the RTP payload format used for the video
        stream.

        RFC2190 (1) - RTP payload format for video codec H.263
        RFC2429 (2) - RTP payload format for video codec H.263
        RFC4629 (3) - RTP payload format for video codec H.263
        RFC3984 (4) - RTP payload format for video codec H.264

        CvcRtpPayloadFormat object is superseded by CvcVideoRtpPayloadFormat
        in CISCO-VIDEO-TC."

    REFERENCE
        "RFC 2190 - RTP Payload Format for H.263 Video Streams
        RFC 2429 - RTP Payload Format for the 1998 Version of
        ITU-T Rec. H.263 Video (H.263+)
        RFC 4629 - RTP Payload Format for ITU-T Rec. H.263 Video
        RFC 3984 - RTP Payload Format for H.264 Video"
    SYNTAX          INTEGER  {
                        rfc2190(1),
                        rfc2429(2),
                        rfc4629(3),
                        rfc3984(4),
                        other(255)
                    }
-- Textual Conventions definition will be defined before this line

ciscoVideoSessionMIBNotifs  OBJECT IDENTIFIER
    ::= { ciscoVideoSessionMIB 0 }

ciscoVideoSessionMIBObjects  OBJECT IDENTIFIER
    ::= { ciscoVideoSessionMIB 1 }

ciscoVideoSessionMIBConform  OBJECT IDENTIFIER
    ::= { ciscoVideoSessionMIB 2 }

cVideoSessionHistory  OBJECT IDENTIFIER
    ::= { ciscoVideoSessionMIBObjects 1 }

cVideoSessionActive  OBJECT IDENTIFIER
    ::= { ciscoVideoSessionMIBObjects 2 }


cVideoCommonHistoryTable OBJECT-TYPE
    SYNTAX          SEQUENCE OF CVideoCommonHistoryEntry
    MAX-ACCESS      not-accessible
    STATUS          current
    DESCRIPTION
        "This table provides the video extension to the call history
        table of Cisco Dial Control MIB. It contains common video call
        leg information and statistics for both a video conference call
        (video conferee) and a point-to-point video call."
    ::= { cVideoSessionHistory 1 }

cVideoCommonHistoryEntry OBJECT-TYPE
    SYNTAX          CVideoCommonHistoryEntry
    MAX-ACCESS      not-accessible
    STATUS          current
    DESCRIPTION
        "The common information for a single video call leg.

        An entry is created when the below conditions are met:
        1.  An associated call history entry in cCallHistoryTable of the
        Cisco Dial Control MIB with video cCallHistoryInfoType is
        created.
        2.  An associated call history entry in cVoIPCallHistoryTable of
        the Cisco Voice Dial Control MIB with SCCP
        cVoIPCallHistorySessionProtocol is created.
        3.  cVideoCommonHistoryCallType of this call entry is
        'pointToPointCall', 'conferenceCall' or 'monitoredCall'.

        The entry is deleted when its associated call history entries
        in cCallHistoryTable of the Cisco Dial Control MIB and
        cVoIPCallHistoryTable of the Cisco Voice Dial Control MIB are
        deleted."
    INDEX           { cCallHistoryIndex }
    ::= { cVideoCommonHistoryTable 1 }

CVideoCommonHistoryEntry ::= SEQUENCE {
        cVideoCommonHistoryConnectionId      CvcGUid,
        cVideoCommonHistoryCallReferenceId   CvcCallReferenceIdOrZero,
        cVideoCommonHistoryCallType          CvcVoIPCallServiceType,
        cVideoCommonHistoryTxCodec           CvcVideoCoderRate,
        cVideoCommonHistoryTxPictureWidth    Unsigned32,
        cVideoCommonHistoryTxPictureHeight   Unsigned32,
        cVideoCommonHistoryTxConfigFrameRate Unsigned32,
        cVideoCommonHistoryTxConfigBitrate   Unsigned32,
        cVideoCommonHistoryTxPayloadFormat   CvcVideoRtpPayloadFormat,
        cVideoCommonHistoryTxAnnex           CvcVideoCodecAnnexMap,
        cVideoCommonHistoryTxProfile         CvcVideoProfile,
        cVideoCommonHistoryTxLevel           CvcVideoLevel,
        cVideoCommonHistoryTxPackets         AbsoluteCounter32,
        cVideoCommonHistoryTxBytes           Counter64,
        cVideoCommonHistoryTxDuration        Unsigned32,
        cVideoCommonHistoryRxCodec           CvcVideoCoderRate,
        cVideoCommonHistoryRxPictureWidth    Unsigned32,
        cVideoCommonHistoryRxPictureHeight   Unsigned32,
        cVideoCommonHistoryRxConfigFrameRate Unsigned32,
        cVideoCommonHistoryRxConfigBitrate   Unsigned32,
        cVideoCommonHistoryRxPayloadFormat   CvcVideoRtpPayloadFormat,
        cVideoCommonHistoryRxAnnex           CvcVideoCodecAnnexMap,
        cVideoCommonHistoryRxProfile         CvcVideoProfile,
        cVideoCommonHistoryRxLevel           CvcVideoLevel,
        cVideoCommonHistoryRxPackets         AbsoluteCounter32,
        cVideoCommonHistoryRxBytes           Counter64,
        cVideoCommonHistoryRxDuration        Unsigned32,
        cVideoCommonHistorySessionId         Unsigned32
}

cVideoCommonHistoryConnectionId OBJECT-TYPE
    SYNTAX          CvcGUid
    MAX-ACCESS      read-only
    STATUS          current
    DESCRIPTION
        "The global call identifier for a video call session."
    ::= { cVideoCommonHistoryEntry 1 }

cVideoCommonHistoryCallReferenceId OBJECT-TYPE
    SYNTAX          CvcCallReferenceIdOrZero
    MAX-ACCESS      read-only
    STATUS          current
    DESCRIPTION
        "The call reference ID associates the video call entry and voice
        call entry of the same endpoint.  The call reference ID is
        assigned by the call manager and is non-zero for a video call
        session."
    ::= { cVideoCommonHistoryEntry 2 }

cVideoCommonHistoryCallType OBJECT-TYPE
    SYNTAX          CvcVoIPCallServiceType
    MAX-ACCESS      read-only
    STATUS          current
    DESCRIPTION
        "This object describes the call type of this call entry."
    ::= { cVideoCommonHistoryEntry 3 }

cVideoCommonHistoryTxCodec OBJECT-TYPE
    SYNTAX          CvcVideoCoderRate
    MAX-ACCESS      read-only
    STATUS          current
    DESCRIPTION
        "The encoding type used to compress the video data in transmit
        direction for a video call session."
    ::= { cVideoCommonHistoryEntry 4 }

cVideoCommonHistoryTxPictureWidth OBJECT-TYPE
    SYNTAX          Unsigned32
    UNITS           "pixels"
    MAX-ACCESS      read-only
    STATUS          current
    DESCRIPTION
        "The picture width in transmit direction for a video call
        session."
    ::= { cVideoCommonHistoryEntry 5 }

cVideoCommonHistoryTxPictureHeight OBJECT-TYPE
    SYNTAX          Unsigned32
    UNITS           "pixels"
    MAX-ACCESS      read-only
    STATUS          current
    DESCRIPTION
        "The picture height in transmit direction for a video call
        session."
    ::= { cVideoCommonHistoryEntry 6 }

cVideoCommonHistoryTxConfigFrameRate OBJECT-TYPE
    SYNTAX          Unsigned32
    UNITS           "frames per second"
    MAX-ACCESS      read-only
    STATUS          current
    DESCRIPTION
        "The video stream frame rate in transmit direction for a video
        call session."
    ::= { cVideoCommonHistoryEntry 7 }

cVideoCommonHistoryTxConfigBitrate OBJECT-TYPE
    SYNTAX          Unsigned32
    UNITS           "kilobits per second"
    MAX-ACCESS      read-only
    STATUS          current
    DESCRIPTION
        "The video stream bitrate in transmit direction for a video call
        session."
    ::= { cVideoCommonHistoryEntry 8 }

cVideoCommonHistoryTxPayloadFormat OBJECT-TYPE
    SYNTAX          CvcVideoRtpPayloadFormat
    MAX-ACCESS      read-only
    STATUS          current
    DESCRIPTION
        "The video stream RTP payload format in transmit direction for a
        video call session."
    ::= { cVideoCommonHistoryEntry 9 }

cVideoCommonHistoryTxAnnex OBJECT-TYPE
    SYNTAX          CvcVideoCodecAnnexMap
    MAX-ACCESS      read-only
    STATUS          current
    DESCRIPTION
        "The video codec annex extension in transmit direction for a
        video call session."
    REFERENCE
        "ITU-T H.263
            Annex A - Inverse transform accuracy specification
            Annex B - Hypothetical Reference Decoder
            Annex C - Considerations for multipoint
            Annex D - Unrestricted Motion Vector Mode
            Annex E - Syntax-based Arithmetic Coding mode
            Annex F - Advanced Prediction mode
            Annex G - PB-frames mode
            Annex H - Forward error correction for coded video
        signal
            Annex I - Advanced INTRA Coding mode
            Annex J - Deblocking Filter mode
            Annex K - Slice Structured mode
            Annex L - Supplemental enhancement information
        specification
            Annex M - Improved PB-frames mode
            Annex N - Reference Picture selection mode
            Annex O - Temporal, SNR, and Spatial Scalability mode
            Annex P - Reference picture resampling
            Annex Q - Reduced-Resolution Update mode
            Annex R - Independent Segment Decoding mode
            Annex S - Alternative INTER VLC mode
            Annex T - Modified Quantization mode
            Annex U - Enhanced reference picture selection mode
            Annex V - Data-partitioned slice mode
            Annex W - Additional supplemental enhancement
        information specification

        ITU-T H.264
            Annex C - Hypothetical reference decoder
            Annex D - Supplemental enhancement information
            Annex E - Video usability information
            Annex G - Scalable video coding
            Annex H - Multiview video coding"
    ::= { cVideoCommonHistoryEntry 10 }

cVideoCommonHistoryTxProfile OBJECT-TYPE
    SYNTAX          CvcVideoProfile
    MAX-ACCESS      read-only
    STATUS          current
    DESCRIPTION
        "The video stream profile in transmit direction for a video call
        session."
    REFERENCE
        "ITU-T H.263: Annex X.2 Profiles of preferred mode support
        ITU-T H.264: Annex A.2 Profiles"
    ::= { cVideoCommonHistoryEntry 11 }

cVideoCommonHistoryTxLevel OBJECT-TYPE
    SYNTAX          CvcVideoLevel
    MAX-ACCESS      read-only
    STATUS          current
    DESCRIPTION
        "The video stream level in transmit direction for a video call
        session."
    REFERENCE       "ITU-T H.264: Annex A.3 Levels"
    ::= { cVideoCommonHistoryEntry 12 }

cVideoCommonHistoryTxPackets OBJECT-TYPE
    SYNTAX          AbsoluteCounter32
    UNITS           "packets"
    MAX-ACCESS      read-only
    STATUS          current
    DESCRIPTION
        "The total number of video data packets transmitted for the
        video call session."
    ::= { cVideoCommonHistoryEntry 13 }

cVideoCommonHistoryTxBytes OBJECT-TYPE
    SYNTAX          Counter64
    UNITS           "bytes"
    MAX-ACCESS      read-only
    STATUS          current
    DESCRIPTION
        "The total number of video data bytes transmitted for the video
        call session."
    ::= { cVideoCommonHistoryEntry 14 }

cVideoCommonHistoryTxDuration OBJECT-TYPE
    SYNTAX          Unsigned32
    UNITS           "seconds"
    MAX-ACCESS      read-only
    STATUS          current
    DESCRIPTION
        "Duration of video stream path, in transmit direction, opened
        for the call leg."
    ::= { cVideoCommonHistoryEntry 15 }

cVideoCommonHistoryRxCodec OBJECT-TYPE
    SYNTAX          CvcVideoCoderRate
    MAX-ACCESS      read-only
    STATUS          current
    DESCRIPTION
        "The encoding type used to compress the video data in receive
        direction for a video call session."
    ::= { cVideoCommonHistoryEntry 16 }

cVideoCommonHistoryRxPictureWidth OBJECT-TYPE
    SYNTAX          Unsigned32
    UNITS           "pixels"
    MAX-ACCESS      read-only
    STATUS          current
    DESCRIPTION
        "The picture width in receive direction for a video call
        session."
    ::= { cVideoCommonHistoryEntry 17 }

cVideoCommonHistoryRxPictureHeight OBJECT-TYPE
    SYNTAX          Unsigned32
    UNITS           "pixels"
    MAX-ACCESS      read-only
    STATUS          current
    DESCRIPTION
        "The picture height in receive direction for a video call
        session."
    ::= { cVideoCommonHistoryEntry 18 }

cVideoCommonHistoryRxConfigFrameRate OBJECT-TYPE
    SYNTAX          Unsigned32
    UNITS           "frames per second"
    MAX-ACCESS      read-only
    STATUS          current
    DESCRIPTION
        "The video stream frame rate in receive direction for a video
        call session."
    ::= { cVideoCommonHistoryEntry 19 }

cVideoCommonHistoryRxConfigBitrate OBJECT-TYPE
    SYNTAX          Unsigned32
    UNITS           "kilobits per second"
    MAX-ACCESS      read-only
    STATUS          current
    DESCRIPTION
        "The video stream bitrate in receive direction for a video call
        session."
    ::= { cVideoCommonHistoryEntry 20 }

cVideoCommonHistoryRxPayloadFormat OBJECT-TYPE
    SYNTAX          CvcVideoRtpPayloadFormat
    MAX-ACCESS      read-only
    STATUS          current
    DESCRIPTION
        "The video stream RTP payload format in receive direction for a
        video call session."
    ::= { cVideoCommonHistoryEntry 21 }

cVideoCommonHistoryRxAnnex OBJECT-TYPE
    SYNTAX          CvcVideoCodecAnnexMap
    MAX-ACCESS      read-only
    STATUS          current
    DESCRIPTION
        "The video codec annex extension in receive direction for a
        video call session."
    REFERENCE
        "ITU-T H.263
            Annex A - Inverse transform accuracy specification
            Annex B - Hypothetical Reference Decoder
            Annex C - Considerations for multipoint
            Annex D - Unrestricted Motion Vector Mode
            Annex E - Syntax-based Arithmetic Coding mode
            Annex F - Advanced Prediction mode
            Annex G - PB-frames mode
            Annex H - Forward error correction for coded video
        signal
            Annex I - Advanced INTRA Coding mode
            Annex J - Deblocking Filter mode
            Annex K - Slice Structured mode
            Annex L - Supplemental enhancement information
        specification
            Annex M - Improved PB-frames mode
            Annex N - Reference Picture selection mode
            Annex O - Temporal, SNR, and Spatial Scalability mode
            Annex P - Reference picture resampling
            Annex Q - Reduced-Resolution Update mode
            Annex R - Independent Segment Decoding mode
            Annex S - Alternative INTER VLC mode
            Annex T - Modified Quantization mode
            Annex U - Enhanced reference picture selection mode
            Annex V - Data-partitioned slice mode
            Annex W - Additional supplemental enhancement
        information specification

        ITU-T H.264
            Annex C - Hypothetical reference decoder
            Annex D - Supplemental enhancement information
            Annex E - Video usability information
            Annex G - Scalable video coding
            Annex H - Multiview video coding"
    ::= { cVideoCommonHistoryEntry 22 }

cVideoCommonHistoryRxProfile OBJECT-TYPE
    SYNTAX          CvcVideoProfile
    MAX-ACCESS      read-only
    STATUS          current
    DESCRIPTION
        "The video stream profile in receive direction for a video call
        session."
    REFERENCE
        "ITU-T H.263: Annex X.2 Profiles of preferred mode support
        ITU-T H.264: Annex A.2 Profiles"
    ::= { cVideoCommonHistoryEntry 23 }

cVideoCommonHistoryRxLevel OBJECT-TYPE
    SYNTAX          CvcVideoLevel
    MAX-ACCESS      read-only
    STATUS          current
    DESCRIPTION
        "The video stream level in receive direction for a video call
        session."
    REFERENCE       "ITU-T H.264: Annex A.3 Levels"
    ::= { cVideoCommonHistoryEntry 24 }

cVideoCommonHistoryRxPackets OBJECT-TYPE
    SYNTAX          AbsoluteCounter32
    UNITS           "packets"
    MAX-ACCESS      read-only
    STATUS          current
    DESCRIPTION
        "The total number of video data packets received for the video
        call session."
    ::= { cVideoCommonHistoryEntry 25 }

cVideoCommonHistoryRxBytes OBJECT-TYPE
    SYNTAX          Counter64
    UNITS           "bytes"
    MAX-ACCESS      read-only
    STATUS          current
    DESCRIPTION
        "The total number of video data bytes received for the video
        call session."
    ::= { cVideoCommonHistoryEntry 26 }

cVideoCommonHistoryRxDuration OBJECT-TYPE
    SYNTAX          Unsigned32
    UNITS           "seconds"
    MAX-ACCESS      read-only
    STATUS          current
    DESCRIPTION
        "Duration of video stream path, in receive direction, opened for
        the call leg."
    ::= { cVideoCommonHistoryEntry 27 }

cVideoCommonHistorySessionId OBJECT-TYPE
    SYNTAX          Unsigned32
    MAX-ACCESS      read-only
    STATUS          current
    DESCRIPTION
        "Session ID is assigned by the call manager to identify call
        legs that belong to the same call session."
    ::= { cVideoCommonHistoryEntry 28 }



cVideoConfereeHistoryTable OBJECT-TYPE
    SYNTAX          SEQUENCE OF CVideoConfereeHistoryEntry
    MAX-ACCESS      not-accessible
    STATUS          current
    DESCRIPTION
        "This table provides the video extension to the call history
        table of Cisco Dial Control MIB. It contains video call
        leg information and statistics for a video conference call
        (video conferee)."
    ::= { cVideoSessionHistory 2 }

cVideoConfereeHistoryEntry OBJECT-TYPE
    SYNTAX          CVideoConfereeHistoryEntry
    MAX-ACCESS      not-accessible
    STATUS          current
    DESCRIPTION
        "The information regarding a single video conferee call leg.
        This entry is an extension to the cVideoCommonHistoryEntry,
        providing information specific to a video call entry that
        belongs to a conference.

        An entry is created when the below conditions are met:
        1.  An associated call history entry in cCallHistoryTable of the
        Cisco Dial Control MIB with video cCallHistoryInfoType is
        created.
        2.  An associated call history entry in cVoIPCallHistoryTable of
        the Cisco Voice Dial Control MIB with SCCP
        cVoIPCallHistorySessionProtocol is created.
        3.  This call entry belongs to a video conference call, i.e.
        cVideoCommonHistoryCallType in cVideoCommonHistoryEntry has
        value 'conferenceCall'.

        The entry is deleted when its associated call history entries in
        cCallHistoryTable of the Cisco Dial Control MIB and
        cVoIPCallHistoryTable of the Cisco Voice Dial Control MIB are
        deleted."
    INDEX           { cCallHistoryIndex }
    ::= { cVideoConfereeHistoryTable 1 }

CVideoConfereeHistoryEntry ::= SEQUENCE {
        cVideoConfereeHistoryTotalDroppedPackets    AbsoluteCounter32,
        cVideoConfereeHistoryMaxJitter              Gauge32,
        cVideoConfereeHistoryMaxDelay               Gauge32,
        cVideoConfereeHistoryTotalOutOfOrderPackets AbsoluteCounter32,
        cVideoConfereeHistoryMaxOutOfSyncDelay      Gauge32,
        cVideoConfereeHistoryTotalLostPackets       AbsoluteCounter32
}

cVideoConfereeHistoryTotalDroppedPackets OBJECT-TYPE
    SYNTAX          AbsoluteCounter32
    UNITS           "packets"
    MAX-ACCESS      read-only
    STATUS          current
    DESCRIPTION
        "The total number of dropped video data packets for the
        video call session."
    ::= { cVideoConfereeHistoryEntry 1 }

cVideoConfereeHistoryMaxJitter OBJECT-TYPE
    SYNTAX          Gauge32
    UNITS           "milliseconds"
    MAX-ACCESS      read-only
    STATUS          deprecated
    DESCRIPTION
        "This object is superseded by cVideoCommonStatsHistoryTxMaxJitter
        in cVideoCommonStatsHistoryTable.

        Maximum jitter measured since the beginning of the video call
        session."
    ::= { cVideoConfereeHistoryEntry 2 }

cVideoConfereeHistoryMaxDelay OBJECT-TYPE
    SYNTAX          Gauge32
    UNITS           "milliseconds"
    MAX-ACCESS      read-only
    STATUS          deprecated
    DESCRIPTION
        "This object is superseded by cVideoCommonStatsHistoryTxMaxDelay
        in cVideoCommonStatsHistoryTable.

        Maximum delay measured since the beginning of the video call
        session."
    ::= { cVideoConfereeHistoryEntry 3 }

cVideoConfereeHistoryTotalOutOfOrderPackets OBJECT-TYPE
    SYNTAX          AbsoluteCounter32
    UNITS           "packets"
    MAX-ACCESS      read-only
    STATUS          deprecated
    DESCRIPTION
        "This object is superseded by
        cVideoCommonStatsHistoryTxTotalOutOfOrderPackets
        in cVideoCommonStatsHistoryTable.

        The total number of out-of-order video data packets for the
        video call session."
    ::= { cVideoConfereeHistoryEntry 4 }

cVideoConfereeHistoryMaxOutOfSyncDelay OBJECT-TYPE
    SYNTAX          Gauge32
    UNITS           "milliseconds"
    MAX-ACCESS      read-only
    STATUS          current
    DESCRIPTION
        "Maximum out-of-sync delay measured since the beginning of the
        video call session."
    ::= { cVideoConfereeHistoryEntry 5 }

cVideoConfereeHistoryTotalLostPackets OBJECT-TYPE
    SYNTAX          AbsoluteCounter32
    UNITS           "packets"
    MAX-ACCESS      read-only
    STATUS          deprecated
    DESCRIPTION
        "This object is superseded by
        cVideoCommonStatsHistoryTxTotalLostPackets
        in cVideoCommonStatsHistoryTable.

        The total number of lost video data packets for the video call
        session."
    ::= { cVideoConfereeHistoryEntry 6 }



cVideoCallHistoryTable OBJECT-TYPE
    SYNTAX          SEQUENCE OF CVideoCallHistoryEntry
    MAX-ACCESS      not-accessible
    STATUS          current
    DESCRIPTION
        "This table provides the video extension to the call history
        table of Cisco Dial Control MIB. It contains video call leg
        information and statistics for a point-to-point video call."
    ::= { cVideoSessionHistory 3 }

cVideoCallHistoryEntry OBJECT-TYPE
    SYNTAX          CVideoCallHistoryEntry
    MAX-ACCESS      not-accessible
    STATUS          current
    DESCRIPTION
        "The information regarding a single video call leg.  This entry
        is an extension to the cVideoCommonHistoryEntry, providing
        information specific to a point-to-point video call entry.

        An entry is created when the below conditions are met:
        1.  An associated call history entry in cCallHistoryTable of the
        Cisco Dial Control MIB with video cCallHistoryInfoType is
        created.
        2.  An associated call history entry in cVoIPCallHistoryTable of
        the Cisco Voice Dial Control MIB with SCCP
        cVoIPCallHistorySessionProtocol is created.
        3.  This call history entry belongs to a point-to-point video
        call, i.e. cVideoCommonHistoryCallType in
        cVideoCommonHistoryEntry has value 'pointToPointCall'.

        The entry is deleted when its associated call history entries in
        cCallHistoryTable of the Cisco Dial Control MIB and
        cVoIPCallHistoryTable of the Cisco Voice Dial Control MIB are
        deleted."
    INDEX           { cCallHistoryIndex }
    ::= { cVideoCallHistoryTable 1 }

CVideoCallHistoryEntry ::= SEQUENCE {
        cVideoCallHistoryTxMacroblocksConcealed AbsoluteCounter32,
        cVideoCallHistoryTxFramesConcealed      AbsoluteCounter32,
        cVideoCallHistoryTxBadHeaderPackets     AbsoluteCounter32,
        cVideoCallHistoryTxOverflowPackets      AbsoluteCounter32,
        cVideoCallHistoryTxOutOfOrderPackets    AbsoluteCounter32,
        cVideoCallHistoryTxLostPackets          AbsoluteCounter32
}

cVideoCallHistoryTxMacroblocksConcealed OBJECT-TYPE
    SYNTAX          AbsoluteCounter32
    UNITS           "macroblocks"
    MAX-ACCESS      read-only
    STATUS          current
    DESCRIPTION
        "Number of concealed macroblocks measured in transmit direction
        of the video call session.
        One macroblock is 16 pixels by 16 pixels."
    ::= { cVideoCallHistoryEntry 1 }

cVideoCallHistoryTxFramesConcealed OBJECT-TYPE
    SYNTAX          AbsoluteCounter32
    UNITS           "frames"
    MAX-ACCESS      read-only
    STATUS          current
    DESCRIPTION
        "Number of concealed frames measured in transmit direction of
        the video call session."
    ::= { cVideoCallHistoryEntry 2 }

cVideoCallHistoryTxBadHeaderPackets OBJECT-TYPE
    SYNTAX          AbsoluteCounter32
    UNITS           "packets"
    MAX-ACCESS      read-only
    STATUS          current
    DESCRIPTION
        "Number of bad header packets measured in transmit direction of
        the video call session."
    ::= { cVideoCallHistoryEntry 3 }

cVideoCallHistoryTxOverflowPackets OBJECT-TYPE
    SYNTAX          AbsoluteCounter32
    UNITS           "packets"
    MAX-ACCESS      read-only
    STATUS          current
    DESCRIPTION
        "Number of overflow packets measured in transmit direction of
        the video call session."
    ::= { cVideoCallHistoryEntry 4 }

cVideoCallHistoryTxOutOfOrderPackets OBJECT-TYPE
    SYNTAX          AbsoluteCounter32
    UNITS           "packets"
    MAX-ACCESS      read-only
    STATUS          deprecated
    DESCRIPTION
        "This object is superseded by
        cVideoCommonStatsHistoryTxTotalOutOfOrderPackets in
        cVideoCommonStatsHistoryTable.

        Number of out-of-order packets measured in transmit direction
        of the video call session."
    ::= { cVideoCallHistoryEntry 5 }

cVideoCallHistoryTxLostPackets OBJECT-TYPE
    SYNTAX          AbsoluteCounter32
    UNITS           "packets"
    MAX-ACCESS      read-only
    STATUS          deprecated
    DESCRIPTION
        "This object is superseded by
        cVideoCommonStatsHistoryTxTotalLostPackets
        in cVideoCommonStatsHistoryTable.

        Number of lost packets measured in transmit direction of the
        video call session."
    ::= { cVideoCallHistoryEntry 6 }



cVideoCommonStatsHistoryTable OBJECT-TYPE
    SYNTAX          SEQUENCE OF CVideoCommonStatsHistoryEntry
    MAX-ACCESS      not-accessible
    STATUS          current
    DESCRIPTION
        "This table provides the video extension to the call history
        table of Cisco Dial Control MIB. It contains common video call
        leg statistics for both a video call within a conference (video
        conferee) and a simple video call."
    ::= { cVideoSessionHistory 4 }

cVideoCommonStatsHistoryEntry OBJECT-TYPE
    SYNTAX          CVideoCommonStatsHistoryEntry
    MAX-ACCESS      not-accessible
    STATUS          current
    DESCRIPTION
        "The common network statistics for a single video call leg.
        This entry accompanies cVideoCommonActiveEntry with more
        detailed statistics.

        An entry is created when the below conditions are met:
        1.  An associated call history entry in cCallHistoryTable of the
        Cisco Dial Control MIB with video cCallHistoryInfoType is
        created.
        2.  An associated call history entry in cVoIPCallHistoryTable of
        the Cisco Voice Dial Control MIB with SCCP
        cVoIPCallHistorySessionProtocol is created.
        3.  cVideoCommonHistoryCallType of this call entry is
        'pointToPointCall' or 'conferenceCall'.

        The entry is deleted when its associated call history entries in
        cCallHistoryTable of the Cisco Dial Control MIB and
        cVoIPCallHistoryTable of the Cisco Voice Dial Control MIB are
        deleted."
    INDEX           { cCallHistoryIndex }
    ::= { cVideoCommonStatsHistoryTable 1 }

CVideoCommonStatsHistoryEntry ::= SEQUENCE {
        cVideoCommonStatsHistoryTxTotalLostPackets       AbsoluteCounter32,
        cVideoCommonStatsHistoryTxPercentLostPackets     Unsigned32,
        cVideoCommonStatsHistoryTxTotalOutOfOrderPackets AbsoluteCounter32,
        cVideoCommonStatsHistoryTxMaxJitter              Gauge32,
        cVideoCommonStatsHistoryTxAvgJitter              Gauge32,
        cVideoCommonStatsHistoryTxMaxDelay               Gauge32,
        cVideoCommonStatsHistoryTxAvgDelay               Gauge32,
        cVideoCommonStatsHistoryRxTotalLostPackets       AbsoluteCounter32,
        cVideoCommonStatsHistoryRxPercentLostPackets     Unsigned32
}

cVideoCommonStatsHistoryTxTotalLostPackets OBJECT-TYPE
    SYNTAX          AbsoluteCounter32
    UNITS           "packets"
    MAX-ACCESS      read-only
    STATUS          current
    DESCRIPTION
        "Number of lost packets of the video call session measured in
        transmit direction."
    ::= { cVideoCommonStatsHistoryEntry 1 }

cVideoCommonStatsHistoryTxPercentLostPackets OBJECT-TYPE
    SYNTAX          Unsigned32 (0..100)
    UNITS           "percent"
    MAX-ACCESS      read-only
    STATUS          current
    DESCRIPTION
        "The percentage of lost video data packets for the entire
        duration of the video call session in transmit direction."
    ::= { cVideoCommonStatsHistoryEntry 2 }

cVideoCommonStatsHistoryTxTotalOutOfOrderPackets OBJECT-TYPE
    SYNTAX          AbsoluteCounter32
    UNITS           "packets"
    MAX-ACCESS      read-only
    STATUS          current
    DESCRIPTION
        "Number of out-of-order packets of the video call session
        measured in transmit direction."
    ::= { cVideoCommonStatsHistoryEntry 3 }

cVideoCommonStatsHistoryTxMaxJitter OBJECT-TYPE
    SYNTAX          Gauge32
    UNITS           "milliseconds"
    MAX-ACCESS      read-only
    STATUS          current
    DESCRIPTION
        "Maximum jitter measured since the beginning of the video call
        session in transmit direction."
    ::= { cVideoCommonStatsHistoryEntry 4 }

cVideoCommonStatsHistoryTxAvgJitter OBJECT-TYPE
    SYNTAX          Gauge32
    UNITS           "milliseconds"
    MAX-ACCESS      read-only
    STATUS          current
    DESCRIPTION
        "Average jitter measured since the beginning of the video call
        session in transmit direction."
    ::= { cVideoCommonStatsHistoryEntry 5 }

cVideoCommonStatsHistoryTxMaxDelay OBJECT-TYPE
    SYNTAX          Gauge32
    UNITS           "milliseconds"
    MAX-ACCESS      read-only
    STATUS          current
    DESCRIPTION
        "Maximum delay measured since the beginning of the video call
        session in transmit direction."
    ::= { cVideoCommonStatsHistoryEntry 6 }

cVideoCommonStatsHistoryTxAvgDelay OBJECT-TYPE
    SYNTAX          Gauge32
    UNITS           "milliseconds"
    MAX-ACCESS      read-only
    STATUS          current
    DESCRIPTION
        "Average delay since the beginning of the video call session
        measured in transmit direction."
    ::= { cVideoCommonStatsHistoryEntry 7 }

cVideoCommonStatsHistoryRxTotalLostPackets OBJECT-TYPE
    SYNTAX          AbsoluteCounter32
    UNITS           "packets"
    MAX-ACCESS      read-only
    STATUS          current
    DESCRIPTION
        "The total number of lost video data packets for the video call
        session in receive direction."
    ::= { cVideoCommonStatsHistoryEntry 8 }

cVideoCommonStatsHistoryRxPercentLostPackets OBJECT-TYPE
    SYNTAX          Unsigned32 (0..100)
    UNITS           "percent"
    MAX-ACCESS      read-only
    STATUS          current
    DESCRIPTION
        "The percentage of lost video data packets for the entire
        duration of the video call session in receive direction."
    ::= { cVideoCommonStatsHistoryEntry 9 }



cVideoCommonActiveTable OBJECT-TYPE
    SYNTAX          SEQUENCE OF CVideoCommonActiveEntry
    MAX-ACCESS      not-accessible
    STATUS          current
    DESCRIPTION
        "This table provides the video extension to the call active
        table of IETF Dial Control MIB. It contains common video call
        leg information and statistics for both a video call within a
        conference (video conferee) and a simple video call."
    ::= { cVideoSessionActive 1 }

cVideoCommonActiveEntry OBJECT-TYPE
    SYNTAX          CVideoCommonActiveEntry
    MAX-ACCESS      not-accessible
    STATUS          current
    DESCRIPTION
        "The information regarding a single video call leg.

        An entry is created when the below conditions are met:
        1.  An associated call active entry in callActiveTable of the
        IETF Dial Control MIB with video callActiveInfoType is created.
        2.  An associated call active entry in cVoIPCallActiveTable of
        the Cisco Voice Dial Control MIB with SCCP
        cVoIPCallActiveSessionProtocol is created.
        3.  cVideoCommonActiveCallType of this call entry is
        'pointToPointCall', conferenceCall, or 'monitoredCall'.

        The entry is deleted when its associated call active entries in
        callActiveTable of the IETF Dial Control MIB and
        cVoIPCallActiveTable of the Cisco Voice Dial Control MIB are
        deleted."
    INDEX           {
                        callActiveSetupTime,
                        callActiveIndex
                    }
    ::= { cVideoCommonActiveTable 1 }

CVideoCommonActiveEntry ::= SEQUENCE {
        cVideoCommonActiveConnectionId      CvcGUid,
        cVideoCommonActiveCallReferenceId   CvcCallReferenceIdOrZero,
        cVideoCommonActiveCallType          CvcVoIPCallServiceType,
        cVideoCommonActiveTxCodec           CvcVideoCoderRate,
        cVideoCommonActiveTxPictureWidth    Unsigned32,
        cVideoCommonActiveTxPictureHeight   Unsigned32,
        cVideoCommonActiveTxConfigFrameRate Unsigned32,
        cVideoCommonActiveTxConfigBitrate   Unsigned32,
        cVideoCommonActiveTxPayloadFormat   CvcVideoRtpPayloadFormat,
        cVideoCommonActiveTxAnnex           CvcVideoCodecAnnexMap,
        cVideoCommonActiveTxProfile         CvcVideoProfile,
        cVideoCommonActiveTxLevel           CvcVideoLevel,
        cVideoCommonActiveTxPackets         AbsoluteCounter32,
        cVideoCommonActiveTxBytes           Counter64,
        cVideoCommonActiveTxDuration        Unsigned32,
        cVideoCommonActiveRxCodec           CvcVideoCoderRate,
        cVideoCommonActiveRxPictureWidth    Unsigned32,
        cVideoCommonActiveRxPictureHeight   Unsigned32,
        cVideoCommonActiveRxConfigFrameRate Unsigned32,
        cVideoCommonActiveRxConfigBitrate   Unsigned32,
        cVideoCommonActiveRxPayloadFormat   CvcVideoRtpPayloadFormat,
        cVideoCommonActiveRxAnnex           CvcVideoCodecAnnexMap,
        cVideoCommonActiveRxProfile         CvcVideoProfile,
        cVideoCommonActiveRxLevel           CvcVideoLevel,
        cVideoCommonActiveRxPackets         AbsoluteCounter32,
        cVideoCommonActiveRxBytes           Counter64,
        cVideoCommonActiveRxDuration        Unsigned32,
        cVideoCommonActiveSessionId         Unsigned32
}

cVideoCommonActiveConnectionId OBJECT-TYPE
    SYNTAX          CvcGUid
    MAX-ACCESS      read-only
    STATUS          current
    DESCRIPTION
        "The global call identifier for a video call leg."
    ::= { cVideoCommonActiveEntry 1 }

cVideoCommonActiveCallReferenceId OBJECT-TYPE
    SYNTAX          CvcCallReferenceIdOrZero
    MAX-ACCESS      read-only
    STATUS          current
    DESCRIPTION
        "The call reference ID associates the video call entry and voice
        call entry of the same endpoint.  The call reference ID is
        assigned by the call manager and is non-zero for a video call
        session."
    ::= { cVideoCommonActiveEntry 2 }

cVideoCommonActiveCallType OBJECT-TYPE
    SYNTAX          CvcVoIPCallServiceType
    MAX-ACCESS      read-only
    STATUS          current
    DESCRIPTION
        "This object describes the call type of this call entry."
    ::= { cVideoCommonActiveEntry 3 }

cVideoCommonActiveTxCodec OBJECT-TYPE
    SYNTAX          CvcVideoCoderRate
    MAX-ACCESS      read-only
    STATUS          current
    DESCRIPTION
        "The encoding type used to compress the video data in transmit
        direction for a video call session."
    ::= { cVideoCommonActiveEntry 4 }

cVideoCommonActiveTxPictureWidth OBJECT-TYPE
    SYNTAX          Unsigned32
    UNITS           "pixels"
    MAX-ACCESS      read-only
    STATUS          current
    DESCRIPTION
        "The picture width in transmit direction for a video call
        session."
    ::= { cVideoCommonActiveEntry 5 }

cVideoCommonActiveTxPictureHeight OBJECT-TYPE
    SYNTAX          Unsigned32
    UNITS           "pixels"
    MAX-ACCESS      read-only
    STATUS          current
    DESCRIPTION
        "The picture height in transmit direction for a video
        call session."
    ::= { cVideoCommonActiveEntry 6 }

cVideoCommonActiveTxConfigFrameRate OBJECT-TYPE
    SYNTAX          Unsigned32
    UNITS           "frames per second"
    MAX-ACCESS      read-only
    STATUS          current
    DESCRIPTION
        "The video stream frame rate in transmit direction for a video
        call session."
    ::= { cVideoCommonActiveEntry 7 }

cVideoCommonActiveTxConfigBitrate OBJECT-TYPE
    SYNTAX          Unsigned32
    UNITS           "kilobits per second"
    MAX-ACCESS      read-only
    STATUS          current
    DESCRIPTION
        "The video stream bitrate in transmit direction for a video call
        session."
    ::= { cVideoCommonActiveEntry 8 }

cVideoCommonActiveTxPayloadFormat OBJECT-TYPE
    SYNTAX          CvcVideoRtpPayloadFormat
    MAX-ACCESS      read-only
    STATUS          current
    DESCRIPTION
        "The video stream RTP payload format in transmit direction for a
        video call session."
    ::= { cVideoCommonActiveEntry 9 }

cVideoCommonActiveTxAnnex OBJECT-TYPE
    SYNTAX          CvcVideoCodecAnnexMap
    MAX-ACCESS      read-only
    STATUS          current
    DESCRIPTION
        "The video codec annex extension in transmit direction for a
        video call session."
    REFERENCE
        "ITU-T H.263
            Annex A - Inverse transform accuracy specification
            Annex B - Hypothetical Reference Decoder
            Annex C - Considerations for multipoint
            Annex D - Unrestricted Motion Vector Mode
            Annex E - Syntax-based Arithmetic Coding mode
            Annex F - Advanced Prediction mode
            Annex G - PB-frames mode
            Annex H - Forward error correction for coded video
        signal
            Annex I - Advanced INTRA Coding mode
            Annex J - Deblocking Filter mode
            Annex K - Slice Structured mode
            Annex L - Supplemental enhancement information
        specification
            Annex M - Improved PB-frames mode
            Annex N - Reference Picture selection mode
            Annex O - Temporal, SNR, and Spatial Scalability mode
            Annex P - Reference picture resampling
            Annex Q - Reduced-Resolution Update mode
            Annex R - Independent Segment Decoding mode
            Annex S - Alternative INTER VLC mode
            Annex T - Modified Quantization mode
            Annex U - Enhanced reference picture selection mode
            Annex V - Data-partitioned slice mode
            Annex W - Additional supplemental enhancement
        information specification

        ITU-T H.264
            Annex C - Hypothetical reference decoder
            Annex D - Supplemental enhancement information
            Annex E - Video usability information
            Annex G - Scalable video coding
            Annex H - Multiview video coding"
    ::= { cVideoCommonActiveEntry 10 }

cVideoCommonActiveTxProfile OBJECT-TYPE
    SYNTAX          CvcVideoProfile
    MAX-ACCESS      read-only
    STATUS          current
    DESCRIPTION
        "The video stream profile in transmit direction for a video call
        session."
    REFERENCE
        "ITU-T H.263: Annex X.2 Profiles of preferred mode support
        ITU-T H.264: Annex A.2 Profiles"
    ::= { cVideoCommonActiveEntry 11 }

cVideoCommonActiveTxLevel OBJECT-TYPE
    SYNTAX          CvcVideoLevel
    MAX-ACCESS      read-only
    STATUS          current
    DESCRIPTION
        "The video stream level in transmit direction for a video call
        session."
    REFERENCE       "ITU-T H.264: Annex A.3 Levels"
    ::= { cVideoCommonActiveEntry 12 }

cVideoCommonActiveTxPackets OBJECT-TYPE
    SYNTAX          AbsoluteCounter32
    UNITS           "packets"
    MAX-ACCESS      read-only
    STATUS          current
    DESCRIPTION
        "The total number of video data packets transmitted for the
        video call session."
    ::= { cVideoCommonActiveEntry 13 }

cVideoCommonActiveTxBytes OBJECT-TYPE
    SYNTAX          Counter64
    UNITS           "bytes"
    MAX-ACCESS      read-only
    STATUS          current
    DESCRIPTION
        "The total number of video data bytes transmitted for the video
        call session."
    ::= { cVideoCommonActiveEntry 14 }

cVideoCommonActiveTxDuration OBJECT-TYPE
    SYNTAX          Unsigned32
    UNITS           "seconds"
    MAX-ACCESS      read-only
    STATUS          current
    DESCRIPTION
        "Duration of video stream path, in transmit direction, opened
        for the call leg."
    ::= { cVideoCommonActiveEntry 15 }

cVideoCommonActiveRxCodec OBJECT-TYPE
    SYNTAX          CvcVideoCoderRate
    MAX-ACCESS      read-only
    STATUS          current
    DESCRIPTION
        "The negotiated encoding type used to compress the video data in
        receive direction for a video call session."
    ::= { cVideoCommonActiveEntry 16 }

cVideoCommonActiveRxPictureWidth OBJECT-TYPE
    SYNTAX          Unsigned32
    UNITS           "pixels"
    MAX-ACCESS      read-only
    STATUS          current
    DESCRIPTION
        "The negotiated picture width in receive direction for a video
        call session."
    ::= { cVideoCommonActiveEntry 17 }

cVideoCommonActiveRxPictureHeight OBJECT-TYPE
    SYNTAX          Unsigned32
    UNITS           "pixels"
    MAX-ACCESS      read-only
    STATUS          current
    DESCRIPTION
        "The negotiated picture height in receive direction for a video
        call session."
    ::= { cVideoCommonActiveEntry 18 }

cVideoCommonActiveRxConfigFrameRate OBJECT-TYPE
    SYNTAX          Unsigned32
    UNITS           "frames per second"
    MAX-ACCESS      read-only
    STATUS          current
    DESCRIPTION
        "The negotiated video stream frame rate in receive direction
        for a video call session."
    ::= { cVideoCommonActiveEntry 19 }

cVideoCommonActiveRxConfigBitrate OBJECT-TYPE
    SYNTAX          Unsigned32
    UNITS           "kilobits per second"
    MAX-ACCESS      read-only
    STATUS          current
    DESCRIPTION
        "The negotiated video stream bitrate in receive direction for a
        video call session."
    ::= { cVideoCommonActiveEntry 20 }

cVideoCommonActiveRxPayloadFormat OBJECT-TYPE
    SYNTAX          CvcVideoRtpPayloadFormat
    MAX-ACCESS      read-only
    STATUS          current
    DESCRIPTION
        "The video stream RTP payload format in receive direction for a
        video call session."
    ::= { cVideoCommonActiveEntry 21 }

cVideoCommonActiveRxAnnex OBJECT-TYPE
    SYNTAX          CvcVideoCodecAnnexMap
    MAX-ACCESS      read-only
    STATUS          current
    DESCRIPTION
        "The video codec annex extension in receive direction for a
        video call session."
    REFERENCE
        "ITU-T H.263
            Annex A - Inverse transform accuracy specification
            Annex B - Hypothetical Reference Decoder
            Annex C - Considerations for multipoint
            Annex D - Unrestricted Motion Vector Mode
            Annex E - Syntax-based Arithmetic Coding mode
            Annex F - Advanced Prediction mode
            Annex G - PB-frames mode
            Annex H - Forward error correction for coded video
        signal
            Annex I - Advanced INTRA Coding mode
            Annex J - Deblocking Filter mode
            Annex K - Slice Structured mode
            Annex L - Supplemental enhancement information
        specification
            Annex M - Improved PB-frames mode
            Annex N - Reference Picture selection mode
            Annex O - Temporal, SNR, and Spatial Scalability mode
            Annex P - Reference picture resampling
            Annex Q - Reduced-Resolution Update mode
            Annex R - Independent Segment Decoding mode
            Annex S - Alternative INTER VLC mode
            Annex T - Modified Quantization mode
            Annex U - Enhanced reference picture selection mode
            Annex V - Data-partitioned slice mode
            Annex W - Additional supplemental enhancement
        information specification

        ITU-T H.264
            Annex C - Hypothetical reference decoder
            Annex D - Supplemental enhancement information
            Annex E - Video usability information
            Annex G - Scalable video coding
            Annex H - Multiview video coding"
    ::= { cVideoCommonActiveEntry 22 }

cVideoCommonActiveRxProfile OBJECT-TYPE
    SYNTAX          CvcVideoProfile
    MAX-ACCESS      read-only
    STATUS          current
    DESCRIPTION
        "The negotiated video stream profile in receive direction for a
        video call session."
    REFERENCE
        "ITU-T H.263: Annex X.2 Profiles of preferred mode support
        ITU-T H.264: Annex A.2 Profiles"
    ::= { cVideoCommonActiveEntry 23 }

cVideoCommonActiveRxLevel OBJECT-TYPE
    SYNTAX          CvcVideoLevel
    MAX-ACCESS      read-only
    STATUS          current
    DESCRIPTION
        "The negotiated video stream level in receive direction for a
        video call session."
    REFERENCE       "ITU-T H.264: Annex A.3 Levels"
    ::= { cVideoCommonActiveEntry 24 }

cVideoCommonActiveRxPackets OBJECT-TYPE
    SYNTAX          AbsoluteCounter32
    UNITS           "packets"
    MAX-ACCESS      read-only
    STATUS          current
    DESCRIPTION
        "The total number of video data packets received for the video
        call session."
    ::= { cVideoCommonActiveEntry 25 }

cVideoCommonActiveRxBytes OBJECT-TYPE
    SYNTAX          Counter64
    UNITS           "bytes"
    MAX-ACCESS      read-only
    STATUS          current
    DESCRIPTION
        "The total number of video data bytes received for the video
        call session."
    ::= { cVideoCommonActiveEntry 26 }

cVideoCommonActiveRxDuration OBJECT-TYPE
    SYNTAX          Unsigned32
    UNITS           "seconds"
    MAX-ACCESS      read-only
    STATUS          current
    DESCRIPTION
        "Duration of video stream path, in receive direction, opened for
        the call leg."
    ::= { cVideoCommonActiveEntry 27 }

cVideoCommonActiveSessionId OBJECT-TYPE
    SYNTAX          Unsigned32
    MAX-ACCESS      read-only
    STATUS          current
    DESCRIPTION
        "Session ID is assigned by the call manager to identify call
        legs that belong to the same call session."
    ::= { cVideoCommonActiveEntry 28 }



cVideoConfereeActiveTable OBJECT-TYPE
    SYNTAX          SEQUENCE OF CVideoConfereeActiveEntry
    MAX-ACCESS      not-accessible
    STATUS          current
    DESCRIPTION
        "This table provides the video extension to the call active
        table of IETF Dial Control MIB. It contains video call leg
        information and statistics for a video call within a conference
        (video conferee)."
    ::= { cVideoSessionActive 2 }

cVideoConfereeActiveEntry OBJECT-TYPE
    SYNTAX          CVideoConfereeActiveEntry
    MAX-ACCESS      not-accessible
    STATUS          current
    DESCRIPTION
        "The information regarding a single video conferee call leg.
        This entry is an extension to the cVideoCommonActiveEntry,
        providing information specific to a video call entry that
        belongs to a conference.

        An entry is created when the below conditions are met:
        1.  An associated call active entry in callActiveTable of the
        IETF
        Dial Control MIB with video callActiveInfoType is created.
        2.  An associated call active entry in cVoIPCallActiveTable of
        the Cisco Voice Dial Control MIB with SCCP
        cVoIPCallActiveSessionProtocol is created.
        3.  This call entry belongs to a video conference, i.e.
        cVideoCommonActiveCallType in cVideoCommonActiveEntry has value
        'conferenceCall'.

        The entry is deleted when its associated call active entries in
        callActiveTable of the IETF Dial Control MIB and
        cVoIPCallActiveTable of the Cisco Voice Dial Control MIB are
        deleted."
    INDEX           {
                        callActiveSetupTime,
                        callActiveIndex
                    }
    ::= { cVideoConfereeActiveTable 1 }

CVideoConfereeActiveEntry ::= SEQUENCE {
        cVideoConfereeActiveActualFrameRate          Unsigned32,
        cVideoConfereeActiveActualBitrate            Unsigned32,
        cVideoConfereeActiveTotalDroppedPackets      AbsoluteCounter32,
        cVideoConfereeActiveCurrentDroppedPackets    AbsoluteCounter32,
        cVideoConfereeActiveTotalOutOfOrderPackets   AbsoluteCounter32,
        cVideoConfereeActiveCurrentOutOfOrderPackets AbsoluteCounter32,
        cVideoConfereeActiveTotalLostPackets         AbsoluteCounter32,
        cVideoConfereeActiveCurrentLostPackets       AbsoluteCounter32,
        cVideoConfereeActiveMaxJitter                Gauge32,
        cVideoConfereeActiveCurrentJitter            Gauge32,
        cVideoConfereeActiveMaxDelay                 Gauge32,
        cVideoConfereeActiveCurrentDelay             Gauge32,
        cVideoConfereeActiveMaxOutOfSyncDelay        Gauge32,
        cVideoConfereeActiveCurrentOutOfSyncDelay    Gauge32,
        cVideoConfereeActiveFastVideoUpdateRate      AbsoluteCounter32
}

cVideoConfereeActiveActualFrameRate OBJECT-TYPE
    SYNTAX          Unsigned32
    UNITS           "frames per second"
    MAX-ACCESS      read-only
    STATUS          current
    DESCRIPTION
        "The actual measured video stream frame rate for a video call
        session."
    ::= { cVideoConfereeActiveEntry 1 }

cVideoConfereeActiveActualBitrate OBJECT-TYPE
    SYNTAX          Unsigned32
    UNITS           "kilobits per second"
    MAX-ACCESS      read-only
    STATUS          deprecated
    DESCRIPTION
        "This object is superseded by
        cVideoCommonStatsActiveTxActualBitrate
        in cVideoCommonStatsActiveTable.

        The actual measured video stream bitrate for a video call
        session."
    ::= { cVideoConfereeActiveEntry 2 }

cVideoConfereeActiveTotalDroppedPackets OBJECT-TYPE
    SYNTAX          AbsoluteCounter32
    UNITS           "packets"
    MAX-ACCESS      read-only
    STATUS          current
    DESCRIPTION
        "The total number of dropped video data packets for the
        video call session."
    ::= { cVideoConfereeActiveEntry 3 }

cVideoConfereeActiveCurrentDroppedPackets OBJECT-TYPE
    SYNTAX          AbsoluteCounter32
    UNITS           "packets"
    MAX-ACCESS      read-only
    STATUS          current
    DESCRIPTION
        "The number of dropped video data packets within the last 5
        seconds for the video call session."
    ::= { cVideoConfereeActiveEntry 4 }

cVideoConfereeActiveTotalOutOfOrderPackets OBJECT-TYPE
    SYNTAX          AbsoluteCounter32
    UNITS           "packets"
    MAX-ACCESS      read-only
    STATUS          deprecated
    DESCRIPTION
        "This object is superseded by
        cVideoCommonStatsActiveTxTotalOutOfOrderPackets
        in cVideoCommonStatsActiveTable.

        The total number of out-of-order video data packets for the
        video call session."
    ::= { cVideoConfereeActiveEntry 5 }

cVideoConfereeActiveCurrentOutOfOrderPackets OBJECT-TYPE
    SYNTAX          AbsoluteCounter32
    UNITS           "packets"
    MAX-ACCESS      read-only
    STATUS          deprecated
    DESCRIPTION
        "This object is superseded by
        cVideoCommonStatsActiveTxCurrentOutOfOrderPackets
        in cVideoCommonStatsActiveTable.

        The number of out-of-order video data packets within the last 5
        seconds for the video call session."
    ::= { cVideoConfereeActiveEntry 6 }

cVideoConfereeActiveTotalLostPackets OBJECT-TYPE
    SYNTAX          AbsoluteCounter32
    UNITS           "packets"
    MAX-ACCESS      read-only
    STATUS          deprecated
    DESCRIPTION
        "This object is superseded by
        cVideoCommonStatsActiveTxTotalLostPackets
        in cVideoCommonStatsActiveTable.

        The total number of lost video data packets for the video call
        session."
    ::= { cVideoConfereeActiveEntry 7 }

cVideoConfereeActiveCurrentLostPackets OBJECT-TYPE
    SYNTAX          AbsoluteCounter32
    UNITS           "packets"
    MAX-ACCESS      read-only
    STATUS          deprecated
    DESCRIPTION
        "This object is superseded by
        cVideoCommonStatsActiveTxCurrentLostPackets
        in cVideoCommonStatsActiveTable.

        The number of lost video data packets within the last 5 seconds
        for the video call session."
    ::= { cVideoConfereeActiveEntry 8 }

cVideoConfereeActiveMaxJitter OBJECT-TYPE
    SYNTAX          Gauge32
    UNITS           "milliseconds"
    MAX-ACCESS      read-only
    STATUS          deprecated
    DESCRIPTION
        "This object is superseded by cVideoCommonStatsActiveTxMaxJitter
        in cVideoCommonStatsActiveTable.

        Maximum jitter measured since the beginning of the video call
        session."
    ::= { cVideoConfereeActiveEntry 9 }

cVideoConfereeActiveCurrentJitter OBJECT-TYPE
    SYNTAX          Gauge32
    UNITS           "milliseconds"
    MAX-ACCESS      read-only
    STATUS          deprecated
    DESCRIPTION
        "This object is superseded by cVideoCommonStatsActiveTxAvgJitter
        in cVideoCommonStatsActiveTable.

        Average jitter measured within the last 5 seconds of the video
        call session."
    ::= { cVideoConfereeActiveEntry 10 }

cVideoConfereeActiveMaxDelay OBJECT-TYPE
    SYNTAX          Gauge32
    UNITS           "milliseconds"
    MAX-ACCESS      read-only
    STATUS          deprecated
    DESCRIPTION
        "This object is superseded by cVideoCommonStatsActiveTxMaxDelay
        in cVideoCommonStatsActiveTable.

        Maximum delay measured since the beginning of the video call
        session."
    ::= { cVideoConfereeActiveEntry 11 }

cVideoConfereeActiveCurrentDelay OBJECT-TYPE
    SYNTAX          Gauge32
    UNITS           "milliseconds"
    MAX-ACCESS      read-only
    STATUS          deprecated
    DESCRIPTION
        "This object is superseded by
        cVideoCommonStatsActiveTxCurrentDelay
        in cVideoCommonStatsActiveTable.

        Average delay measured within the last 5 seconds of the video
        call session."
    ::= { cVideoConfereeActiveEntry 12 }

cVideoConfereeActiveMaxOutOfSyncDelay OBJECT-TYPE
    SYNTAX          Gauge32
    UNITS           "milliseconds"
    MAX-ACCESS      read-only
    STATUS          current
    DESCRIPTION
        "Maximum out-of-sync delay measured since the beginning of the
        video call session."
    ::= { cVideoConfereeActiveEntry 13 }

cVideoConfereeActiveCurrentOutOfSyncDelay OBJECT-TYPE
    SYNTAX          Gauge32
    UNITS           "milliseconds"
    MAX-ACCESS      read-only
    STATUS          current
    DESCRIPTION
        "Average out-of-sync delay measured within the last 5 seconds of
        the video call session."
    ::= { cVideoConfereeActiveEntry 14 }

cVideoConfereeActiveFastVideoUpdateRate OBJECT-TYPE
    SYNTAX          AbsoluteCounter32
    MAX-ACCESS      read-only
    STATUS          current
    DESCRIPTION
        "Number of fast video update requests within the last 60
        seconds."
    ::= { cVideoConfereeActiveEntry 15 }



cVideoCallActiveTable OBJECT-TYPE
    SYNTAX          SEQUENCE OF CVideoCallActiveEntry
    MAX-ACCESS      not-accessible
    STATUS          current
    DESCRIPTION
        "This table provides the video extension to the call active
        table of IETF Dial Control MIB. It contains video call leg
        information and statistics for a point-to-point video call."
    ::= { cVideoSessionActive 3 }

cVideoCallActiveEntry OBJECT-TYPE
    SYNTAX          CVideoCallActiveEntry
    MAX-ACCESS      not-accessible
    STATUS          current
    DESCRIPTION
        "The information regarding a single video call leg.  This entry
        is an extension to the cVideoCommonActiveEntry, providing
        information specific to a point-to-point video call entry.

        An entry is created when the below conditions are met:
        1.  An associated call active entry in callActiveTable of the
        IETF Dial Control MIB with video callActiveInfoType is created.
        2.  An associated call active entry in cVoIPCallActiveTable of
        the Cisco Voice Dial Control MIB with SCCP
        cVoIPCallActiveSessionProtocol is created.
        3.  This call entry belongs to a point-to-point video call,
        i.e. cVideoCommonActiveCallType in cVideoCommonActiveEntry has
        value 'pointToPointCall'.

        The entry is deleted when its associated call active entries in
        callActiveTable of the IETF Dial Control MIB and
        cVoIPCallActiveTable of the Cisco Voice Dial Control MIB are
        deleted."
    INDEX           {
                        callActiveSetupTime,
                        callActiveIndex
                    }
    ::= { cVideoCallActiveTable 1 }

CVideoCallActiveEntry ::= SEQUENCE {
        cVideoCallActiveRxActualBitrate        Unsigned32,
        cVideoCallActiveTxMacroblocksConcealed AbsoluteCounter32,
        cVideoCallActiveTxFramesConcealed      AbsoluteCounter32,
        cVideoCallActiveTxBadHeaderPackets     AbsoluteCounter32,
        cVideoCallActiveTxOverflowPackets      AbsoluteCounter32,
        cVideoCallActiveTxLostPackets          AbsoluteCounter32
}

cVideoCallActiveRxActualBitrate OBJECT-TYPE
    SYNTAX          Unsigned32
    UNITS           "kilobits per second"
    MAX-ACCESS      read-only
    STATUS          deprecated
    DESCRIPTION
        "This object is superseded by
        cVideoCommonStatsActiveRxActualBitrate
        in cVideoCommonStatsActiveTable.

        The actual measured video stream bitrate in receive direction
        for a video call session."
    ::= { cVideoCallActiveEntry 1 }

cVideoCallActiveTxMacroblocksConcealed OBJECT-TYPE
    SYNTAX          AbsoluteCounter32
    UNITS           "macroblocks"
    MAX-ACCESS      read-only
    STATUS          current
    DESCRIPTION
        "Number of concealed macroblocks measured in transmit direction
        of the video call session.
        One macroblock is 16 pixels by 16 pixels."
    ::= { cVideoCallActiveEntry 2 }

cVideoCallActiveTxFramesConcealed OBJECT-TYPE
    SYNTAX          AbsoluteCounter32
    UNITS           "frames"
    MAX-ACCESS      read-only
    STATUS          current
    DESCRIPTION
        "Number of concealed frames measured in transmit direction of
        the video call session."
    ::= { cVideoCallActiveEntry 3 }

cVideoCallActiveTxBadHeaderPackets OBJECT-TYPE
    SYNTAX          AbsoluteCounter32
    UNITS           "packets"
    MAX-ACCESS      read-only
    STATUS          current
    DESCRIPTION
        "Number of bad header packets measured in transmit direction of
        the video call session."
    ::= { cVideoCallActiveEntry 4 }

cVideoCallActiveTxOverflowPackets OBJECT-TYPE
    SYNTAX          AbsoluteCounter32
    UNITS           "packets"
    MAX-ACCESS      read-only
    STATUS          current
    DESCRIPTION
        "Number of overflow packets measured in transmit direction of
        the video call session."
    ::= { cVideoCallActiveEntry 5 }

cVideoCallActiveTxLostPackets OBJECT-TYPE
    SYNTAX          AbsoluteCounter32
    UNITS           "packets"
    MAX-ACCESS      read-only
    STATUS          deprecated
    DESCRIPTION
        "This object is superseded by
        cVideoCommonStatsActiveTxTotalLostPackets
        in cVideoCommonStatsActiveTable.

        Number of lost packets measured in transmit direction of the
        video call session."
    ::= { cVideoCallActiveEntry 6 }



cVideoCommonStatsActiveTable OBJECT-TYPE
    SYNTAX          SEQUENCE OF CVideoCommonStatsActiveEntry
    MAX-ACCESS      not-accessible
    STATUS          current
    DESCRIPTION
        "This table provides the video extension to the call active
        table of IETF Dial Control MIB. It contains common video call
        leg statistics for both a video call within a conference (video
        conferee) and a simple video call."
    ::= { cVideoSessionActive 4 }

cVideoCommonStatsActiveEntry OBJECT-TYPE
    SYNTAX          CVideoCommonStatsActiveEntry
    MAX-ACCESS      not-accessible
    STATUS          current
    DESCRIPTION
        "The common network statistics regarding a single video call
        leg.  This entry accompanies cVideoCommonActiveEntry with more
        detailed statistics.

        An entry is created when the below conditions are met:
        1.  An associated call active entry in callActiveTable of the
        IETF Dial Control MIB with video callActiveInfoType is created.
        2.  An associated call active entry in cVoIPCallActiveTable of
        the Cisco Voice Dial Control MIB with SCCP
        cVoIPCallActiveSessionProtocol is created.
        3.  cVideoCommonActiveCallType of this call entry is
        'pointToPointCall' or 'conferenceCall'.

        The entry is deleted when its associated call active entries in
        callActiveTable of the IETF Dial Control MIB and
        cVoIPCallActiveTable of the Cisco Voice Dial Control MIB are
        deleted."
    INDEX           {
                        callActiveSetupTime,
                        callActiveIndex
                    }
    ::= { cVideoCommonStatsActiveTable 1 }

CVideoCommonStatsActiveEntry ::= SEQUENCE {
        cVideoCommonStatsActiveTxActualBitrate            Unsigned32,
        cVideoCommonStatsActiveTxTotalLostPackets         AbsoluteCounter32,
        cVideoCommonStatsActiveTxPercentLostPackets       Unsigned32,
        cVideoCommonStatsActiveTxCurrentLostPackets       AbsoluteCounter32,
        cVideoCommonStatsActiveTxTotalOutOfOrderPackets   AbsoluteCounter32,
        cVideoCommonStatsActiveTxCurrentOutOfOrderPackets AbsoluteCounter32,
        cVideoCommonStatsActiveTxMaxJitter                Gauge32,
        cVideoCommonStatsActiveTxAvgJitter                Gauge32,
        cVideoCommonStatsActiveTxCurrentJitter            Gauge32,
        cVideoCommonStatsActiveTxMaxDelay                 Gauge32,
        cVideoCommonStatsActiveTxAvgDelay                 Gauge32,
        cVideoCommonStatsActiveTxCurrentDelay             Gauge32,
        cVideoCommonStatsActiveRxActualBitrate            Unsigned32,
        cVideoCommonStatsActiveRxTotalLostPackets         AbsoluteCounter32,
        cVideoCommonStatsActiveRxPercentLostPackets       Unsigned32,
        cVideoCommonStatsActiveRxCurrentLostPackets       AbsoluteCounter32
}

cVideoCommonStatsActiveTxActualBitrate OBJECT-TYPE
    SYNTAX          Unsigned32
    UNITS           "kilobits per second"
    MAX-ACCESS      read-only
    STATUS          current
    DESCRIPTION
        "The actual measured video stream bitrate in transmit direction
        for a video call session."
    ::= { cVideoCommonStatsActiveEntry 1 }

cVideoCommonStatsActiveTxTotalLostPackets OBJECT-TYPE
    SYNTAX          AbsoluteCounter32
    UNITS           "packets"
    MAX-ACCESS      read-only
    STATUS          current
    DESCRIPTION
        "The total number of lost video data packets for the video call
        session in transmit direction."
    ::= { cVideoCommonStatsActiveEntry 2 }

cVideoCommonStatsActiveTxPercentLostPackets OBJECT-TYPE
    SYNTAX          Unsigned32 (0..100)
    UNITS           "percent"
    MAX-ACCESS      read-only
    STATUS          current
    DESCRIPTION
        "The percentage of lost video data packets for the entire
        duration of the video call session in transmit direction."
    ::= { cVideoCommonStatsActiveEntry 3 }

cVideoCommonStatsActiveTxCurrentLostPackets OBJECT-TYPE
    SYNTAX          AbsoluteCounter32
    UNITS           "packets"
    MAX-ACCESS      read-only
    STATUS          current
    DESCRIPTION
        "Number of lost packets within the last 5 seconds of the video
        call session in transmit direction."
    ::= { cVideoCommonStatsActiveEntry 4 }

cVideoCommonStatsActiveTxTotalOutOfOrderPackets OBJECT-TYPE
    SYNTAX          AbsoluteCounter32
    UNITS           "packets"
    MAX-ACCESS      read-only
    STATUS          current
    DESCRIPTION
        "The total number of out-of-order video data packets for the
        video call session."
    ::= { cVideoCommonStatsActiveEntry 5 }

cVideoCommonStatsActiveTxCurrentOutOfOrderPackets OBJECT-TYPE
    SYNTAX          AbsoluteCounter32
    UNITS           "packets"
    MAX-ACCESS      read-only
    STATUS          current
    DESCRIPTION
        "The number of out-of-order video data packets within the last 5
        seconds for the video call session in transmit direction."
    ::= { cVideoCommonStatsActiveEntry 6 }

cVideoCommonStatsActiveTxMaxJitter OBJECT-TYPE
    SYNTAX          Gauge32
    UNITS           "milliseconds"
    MAX-ACCESS      read-only
    STATUS          current
    DESCRIPTION
        "Maximum jitter measured since the beginning of the video call
        session in transmit direction."
    ::= { cVideoCommonStatsActiveEntry 7 }

cVideoCommonStatsActiveTxAvgJitter OBJECT-TYPE
    SYNTAX          Gauge32
    UNITS           "milliseconds"
    MAX-ACCESS      read-only
    STATUS          current
    DESCRIPTION
        "Average jitter calculated over the entire duration of the
        video call session in transmit direction."
    ::= { cVideoCommonStatsActiveEntry 8 }

cVideoCommonStatsActiveTxCurrentJitter OBJECT-TYPE
    SYNTAX          Gauge32
    UNITS           "milliseconds"
    MAX-ACCESS      read-only
    STATUS          current
    DESCRIPTION
        "Average jitter measured within the last 5 seconds of the video
        call session in transmit direction."
    ::= { cVideoCommonStatsActiveEntry 9 }

cVideoCommonStatsActiveTxMaxDelay OBJECT-TYPE
    SYNTAX          Gauge32
    UNITS           "milliseconds"
    MAX-ACCESS      read-only
    STATUS          current
    DESCRIPTION
        "Maximum delay measured since the beginning of the video call
        session in transmit direction."
    ::= { cVideoCommonStatsActiveEntry 10 }

cVideoCommonStatsActiveTxAvgDelay OBJECT-TYPE
    SYNTAX          Gauge32
    UNITS           "milliseconds"
    MAX-ACCESS      read-only
    STATUS          current
    DESCRIPTION
        "Average delay calculated over the entire duration of the video
        call session in transmit direction."
    ::= { cVideoCommonStatsActiveEntry 11 }

cVideoCommonStatsActiveTxCurrentDelay OBJECT-TYPE
    SYNTAX          Gauge32
    UNITS           "milliseconds"
    MAX-ACCESS      read-only
    STATUS          current
    DESCRIPTION
        "Average delay measured within the last 5 seconds of the video
        call session in transmit direction."
    ::= { cVideoCommonStatsActiveEntry 12 }

cVideoCommonStatsActiveRxActualBitrate OBJECT-TYPE
    SYNTAX          Unsigned32
    UNITS           "kilobits per second"
    MAX-ACCESS      read-only
    STATUS          current
    DESCRIPTION
        "The actual measured video stream bitrate in receive direction
        for a video call session."
    ::= { cVideoCommonStatsActiveEntry 13 }

cVideoCommonStatsActiveRxTotalLostPackets OBJECT-TYPE
    SYNTAX          AbsoluteCounter32
    UNITS           "packets"
    MAX-ACCESS      read-only
    STATUS          current
    DESCRIPTION
        "The total number of lost video data packets for the video call
        session in receive direction."
    ::= { cVideoCommonStatsActiveEntry 14 }

cVideoCommonStatsActiveRxPercentLostPackets OBJECT-TYPE
    SYNTAX          Unsigned32 (0..100)
    UNITS           "percent"
    MAX-ACCESS      read-only
    STATUS          current
    DESCRIPTION
        "The percentage of lost video data packets for the entire
        duration of the video call session in receive direction."
    ::= { cVideoCommonStatsActiveEntry 15 }

cVideoCommonStatsActiveRxCurrentLostPackets OBJECT-TYPE
    SYNTAX          AbsoluteCounter32
    UNITS           "packets"
    MAX-ACCESS      read-only
    STATUS          current
    DESCRIPTION
        "Number of lost packets within the last 5 seconds of the video
        call session in receive direction."
    ::= { cVideoCommonStatsActiveEntry 16 }


ciscoVideoSessionMIBCompliances  OBJECT IDENTIFIER
    ::= { ciscoVideoSessionMIBConform 1 }

ciscoVideoSessionMIBGroups  OBJECT IDENTIFIER
    ::= { ciscoVideoSessionMIBConform 2 }


cVideoSessionMIBCompliance MODULE-COMPLIANCE
    STATUS          deprecated
    DESCRIPTION
        "The compliance statement for the SNMP entities
        that implement ciscoVideoSessionMIB module."
    MODULE          -- this module
    MANDATORY-GROUPS {
                        cVideoSessionHistoryGroup,
                        cVideoSessionActiveGroup
                    }
    ::= { ciscoVideoSessionMIBCompliances 1 }

cVideoSessionMIBComplianceRev1 MODULE-COMPLIANCE
    STATUS          current
    DESCRIPTION
        "The compliance statement for the SNMP entities
        that implement ciscoVideoSessionMIB module."
    MODULE          -- this module
    MANDATORY-GROUPS {
                        cVideoSessionCommonStatusGroup,
                        cVideoSessionCommonStatisticsGroup,
                        cVideoSessionCallStatisticsGroup,
                        cVideoSessionConfereeStatisticsGroup
                    }
    ::= { ciscoVideoSessionMIBCompliances 2 }

cVideoSessionHistoryGroup OBJECT-GROUP
    OBJECTS         {
                        cVideoCommonHistoryConnectionId,
                        cVideoCommonHistoryCallReferenceId,
                        cVideoCommonHistoryCallType,
                        cVideoCommonHistoryTxCodec,
                        cVideoCommonHistoryTxPictureWidth,
                        cVideoCommonHistoryTxPictureHeight,
                        cVideoCommonHistoryTxConfigFrameRate,
                        cVideoCommonHistoryTxConfigBitrate,
                        cVideoCommonHistoryTxPayloadFormat,
                        cVideoCommonHistoryTxAnnex,
                        cVideoCommonHistoryTxProfile,
                        cVideoCommonHistoryTxLevel,
                        cVideoCommonHistoryTxPackets,
                        cVideoCommonHistoryTxBytes,
                        cVideoCommonHistoryTxDuration,
                        cVideoCommonHistoryRxCodec,
                        cVideoCommonHistoryRxPictureWidth,
                        cVideoCommonHistoryRxPictureHeight,
                        cVideoCommonHistoryRxConfigFrameRate,
                        cVideoCommonHistoryRxConfigBitrate,
                        cVideoCommonHistoryRxPayloadFormat,
                        cVideoCommonHistoryRxAnnex,
                        cVideoCommonHistoryRxProfile,
                        cVideoCommonHistoryRxLevel,
                        cVideoCommonHistoryRxPackets,
                        cVideoCommonHistoryRxBytes,
                        cVideoCommonHistoryRxDuration,
                        cVideoConfereeHistoryTotalDroppedPackets,
                        cVideoConfereeHistoryMaxJitter,
                        cVideoConfereeHistoryMaxDelay,
                        cVideoConfereeHistoryTotalOutOfOrderPackets,
                        cVideoConfereeHistoryMaxOutOfSyncDelay,
                        cVideoConfereeHistoryTotalLostPackets,
                        cVideoCallHistoryTxMacroblocksConcealed,
                        cVideoCallHistoryTxFramesConcealed,
                        cVideoCallHistoryTxBadHeaderPackets,
                        cVideoCallHistoryTxOverflowPackets,
                        cVideoCallHistoryTxOutOfOrderPackets,
                        cVideoCallHistoryTxLostPackets
                    }
    STATUS          deprecated
    DESCRIPTION
        "This collection of objects provide the video call leg history."
    ::= { ciscoVideoSessionMIBGroups 1 }

cVideoSessionActiveGroup OBJECT-GROUP
    OBJECTS         {
                        cVideoCommonActiveConnectionId,
                        cVideoCommonActiveCallReferenceId,
                        cVideoCommonActiveCallType,
                        cVideoCommonActiveTxCodec,
                        cVideoCommonActiveTxPictureWidth,
                        cVideoCommonActiveTxPictureHeight,
                        cVideoCommonActiveTxConfigFrameRate,
                        cVideoCommonActiveTxConfigBitrate,
                        cVideoCommonActiveTxPayloadFormat,
                        cVideoCommonActiveTxAnnex,
                        cVideoCommonActiveTxProfile,
                        cVideoCommonActiveTxLevel,
                        cVideoCommonActiveTxPackets,
                        cVideoCommonActiveTxBytes,
                        cVideoCommonActiveTxDuration,
                        cVideoCommonActiveRxCodec,
                        cVideoCommonActiveRxPictureWidth,
                        cVideoCommonActiveRxPictureHeight,
                        cVideoCommonActiveRxConfigFrameRate,
                        cVideoCommonActiveRxConfigBitrate,
                        cVideoCommonActiveRxPayloadFormat,
                        cVideoCommonActiveRxAnnex,
                        cVideoCommonActiveRxProfile,
                        cVideoCommonActiveRxLevel,
                        cVideoCommonActiveRxPackets,
                        cVideoCommonActiveRxBytes,
                        cVideoCommonActiveRxDuration,
                        cVideoConfereeActiveActualFrameRate,
                        cVideoConfereeActiveActualBitrate,
                        cVideoConfereeActiveTotalDroppedPackets,
                        cVideoConfereeActiveCurrentDroppedPackets,
                        cVideoConfereeActiveTotalOutOfOrderPackets,
                        cVideoConfereeActiveCurrentOutOfOrderPackets,
                        cVideoConfereeActiveTotalLostPackets,
                        cVideoConfereeActiveCurrentLostPackets,
                        cVideoConfereeActiveMaxJitter,
                        cVideoConfereeActiveCurrentJitter,
                        cVideoConfereeActiveMaxDelay,
                        cVideoConfereeActiveCurrentDelay,
                        cVideoConfereeActiveMaxOutOfSyncDelay,
                        cVideoConfereeActiveCurrentOutOfSyncDelay,
                        cVideoConfereeActiveFastVideoUpdateRate,
                        cVideoCallActiveRxActualBitrate,
                        cVideoCallActiveTxMacroblocksConcealed,
                        cVideoCallActiveTxFramesConcealed,
                        cVideoCallActiveTxBadHeaderPackets,
                        cVideoCallActiveTxOverflowPackets,
                        cVideoCallActiveTxLostPackets
                    }
    STATUS          deprecated
    DESCRIPTION
        "This collection of objects provide the active video call
        information."
    ::= { ciscoVideoSessionMIBGroups 2 }

cVideoSessionCommonStatusGroup OBJECT-GROUP
    OBJECTS         {
                        cVideoCommonHistoryConnectionId,
                        cVideoCommonHistoryCallReferenceId,
                        cVideoCommonHistoryCallType,
                        cVideoCommonHistoryTxCodec,
                        cVideoCommonHistoryTxPictureWidth,
                        cVideoCommonHistoryTxPictureHeight,
                        cVideoCommonHistoryTxConfigFrameRate,
                        cVideoCommonHistoryTxConfigBitrate,
                        cVideoCommonHistoryTxPayloadFormat,
                        cVideoCommonHistoryTxAnnex,
                        cVideoCommonHistoryTxProfile,
                        cVideoCommonHistoryTxLevel,
                        cVideoCommonHistoryTxPackets,
                        cVideoCommonHistoryTxBytes,
                        cVideoCommonHistoryTxDuration,
                        cVideoCommonHistoryRxCodec,
                        cVideoCommonHistoryRxPictureWidth,
                        cVideoCommonHistoryRxPictureHeight,
                        cVideoCommonHistoryRxConfigFrameRate,
                        cVideoCommonHistoryRxConfigBitrate,
                        cVideoCommonHistoryRxPayloadFormat,
                        cVideoCommonHistoryRxAnnex,
                        cVideoCommonHistoryRxProfile,
                        cVideoCommonHistoryRxLevel,
                        cVideoCommonHistoryRxPackets,
                        cVideoCommonHistoryRxBytes,
                        cVideoCommonHistoryRxDuration,
                        cVideoCommonHistorySessionId,
                        cVideoCommonActiveConnectionId,
                        cVideoCommonActiveCallReferenceId,
                        cVideoCommonActiveCallType,
                        cVideoCommonActiveTxCodec,
                        cVideoCommonActiveTxPictureWidth,
                        cVideoCommonActiveTxPictureHeight,
                        cVideoCommonActiveTxConfigFrameRate,
                        cVideoCommonActiveTxConfigBitrate,
                        cVideoCommonActiveTxPayloadFormat,
                        cVideoCommonActiveTxAnnex,
                        cVideoCommonActiveTxProfile,
                        cVideoCommonActiveTxLevel,
                        cVideoCommonActiveTxPackets,
                        cVideoCommonActiveTxBytes,
                        cVideoCommonActiveTxDuration,
                        cVideoCommonActiveRxCodec,
                        cVideoCommonActiveRxPictureWidth,
                        cVideoCommonActiveRxPictureHeight,
                        cVideoCommonActiveRxConfigFrameRate,
                        cVideoCommonActiveRxConfigBitrate,
                        cVideoCommonActiveRxPayloadFormat,
                        cVideoCommonActiveRxAnnex,
                        cVideoCommonActiveRxProfile,
                        cVideoCommonActiveRxLevel,
                        cVideoCommonActiveRxPackets,
                        cVideoCommonActiveRxBytes,
                        cVideoCommonActiveRxDuration,
                        cVideoCommonActiveSessionId
                    }
    STATUS          current
    DESCRIPTION
        "This collection of objects provides basic information and
        statistics for a video call leg."
    ::= { ciscoVideoSessionMIBGroups 3 }

cVideoSessionCommonStatisticsGroup OBJECT-GROUP
    OBJECTS         {
                        cVideoCommonStatsHistoryTxTotalLostPackets,
                        cVideoCommonStatsHistoryTxPercentLostPackets,
                        cVideoCommonStatsHistoryTxTotalOutOfOrderPackets,
                        cVideoCommonStatsHistoryTxMaxJitter,
                        cVideoCommonStatsHistoryTxAvgJitter,
                        cVideoCommonStatsHistoryTxMaxDelay,
                        cVideoCommonStatsHistoryTxAvgDelay,
                        cVideoCommonStatsHistoryRxTotalLostPackets,
                        cVideoCommonStatsHistoryRxPercentLostPackets,
                        cVideoCommonStatsActiveTxActualBitrate,
                        cVideoCommonStatsActiveTxTotalLostPackets,
                        cVideoCommonStatsActiveTxPercentLostPackets,
                        cVideoCommonStatsActiveTxCurrentLostPackets,
                        cVideoCommonStatsActiveTxTotalOutOfOrderPackets,
                        cVideoCommonStatsActiveTxCurrentOutOfOrderPackets,
                        cVideoCommonStatsActiveTxMaxJitter,
                        cVideoCommonStatsActiveTxAvgJitter,
                        cVideoCommonStatsActiveTxCurrentJitter,
                        cVideoCommonStatsActiveTxMaxDelay,
                        cVideoCommonStatsActiveTxAvgDelay,
                        cVideoCommonStatsActiveTxCurrentDelay,
                        cVideoCommonStatsActiveRxActualBitrate,
                        cVideoCommonStatsActiveRxTotalLostPackets,
                        cVideoCommonStatsActiveRxPercentLostPackets,
                        cVideoCommonStatsActiveRxCurrentLostPackets
                    }
    STATUS          current
    DESCRIPTION
        "This collection of objects provides more detailed statistics
        for a video call leg."
    ::= { ciscoVideoSessionMIBGroups 4 }

cVideoSessionCallStatisticsGroup OBJECT-GROUP
    OBJECTS         {
                        cVideoCallHistoryTxMacroblocksConcealed,
                        cVideoCallHistoryTxFramesConcealed,
                        cVideoCallHistoryTxBadHeaderPackets,
                        cVideoCallHistoryTxOverflowPackets,
                        cVideoCallActiveTxMacroblocksConcealed,
                        cVideoCallActiveTxFramesConcealed,
                        cVideoCallActiveTxBadHeaderPackets,
                        cVideoCallActiveTxOverflowPackets
                    }
    STATUS          current
    DESCRIPTION
        "This collection of objects provides more detailed statistics
        for a point-to-point video call leg."
    ::= { ciscoVideoSessionMIBGroups 5 }

cVideoSessionConfereeStatisticsGroup OBJECT-GROUP
    OBJECTS         {
                        cVideoConfereeHistoryTotalDroppedPackets,
                        cVideoConfereeHistoryMaxOutOfSyncDelay,
                        cVideoConfereeActiveActualFrameRate,
                        cVideoConfereeActiveTotalDroppedPackets,
                        cVideoConfereeActiveCurrentDroppedPackets,
                        cVideoConfereeActiveMaxOutOfSyncDelay,
                        cVideoConfereeActiveCurrentOutOfSyncDelay,
                        cVideoConfereeActiveFastVideoUpdateRate
                    }
    STATUS          current
    DESCRIPTION
        "This collection of objects provides more detailed statistics
        for a video call leg within a conference (video conferee)."
    ::= { ciscoVideoSessionMIBGroups 6 }

END
