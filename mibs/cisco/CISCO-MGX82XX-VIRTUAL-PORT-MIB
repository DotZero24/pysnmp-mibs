-- *****************************************************************
-- CISCO-MGX82XX-VIRTUAL-PORT-MIB
--  Virtual Port MIB for MGX82xx series.
--
-- August 2002, Subra Hegde
--
-- Copyright (c) 2002 by cisco Systems, Inc.
-- All rights reserved.
-- *****************************************************************

CISCO-MGX82XX-VIRTUAL-PORT-MIB DEFINITIONS ::= BEGIN
IMPORTS
        MODULE-IDENTITY,
        OBJECT-TYPE,
        Integer32,
        Counter32            FROM    SNMPv2-SMI
        MODULE-COMPLIANCE,
        OBJECT-GROUP         FROM    SNMPv2-CONF
        virtualInterface     FROM BASIS-MIB
        ciscoWan             FROM    CISCOWAN-SMI;

ciscoMgx82xxVirtualPortMIB MODULE-IDENTITY
        LAST-UPDATED    "200208300000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
    DESCRIPTION
        "The MIB module for configuration ond reporting
        statistics of virtual ports in PXM1 Service module
        in MGX82xx series."

    REVISION    "200208300000Z"
    DESCRIPTION
        "Initial version of the MIB.

        The content of this MIB was originally available
        in CISCO-WAN-AXIPOP-MIB defined using SMIv1.
        The applicable objects from CISCO-WAN-AXIPOP-MIB
        are defined using SMIv2 in this MIB. Also the
        descriptions of some of the objects have been
        modified."
    ::= { ciscoWan 38 }


virtualInterfaceCnf       OBJECT IDENTIFIER ::= { virtualInterface 1 }
virtualInterfaceCnt       OBJECT IDENTIFIER ::= { virtualInterface 2 }
virtualInterfaceQbinCnf   OBJECT IDENTIFIER ::= { virtualInterface 3 }
virtualInterfaceQbinCnt   OBJECT IDENTIFIER ::= { virtualInterface 4 }

-- ---------------------------------------------------------------------
--
-- Port Virtual Interface Group
--
-- ---------------------------------------------------------------------

vrtlIntrConfigTable OBJECT-TYPE
	  SYNTAX     SEQUENCE OF VrtlIntrConfigEntry
	  MAX-ACCESS not-accessible
	  STATUS     current
	  DESCRIPTION
	      "Virtual Interface Configuration Table."
	   ::= { virtualInterfaceCnf 1 }

vrtlIntrConfigEntry OBJECT-TYPE
	  SYNTAX     VrtlIntrConfigEntry
	  MAX-ACCESS not-accessible
	  STATUS     current
	  DESCRIPTION
              "An entry in the Virtual Interface configuration Table."
	   INDEX {configVrtlIntrNum}
	   ::= { vrtlIntrConfigTable 1 }

VrtlIntrConfigEntry ::=
	  SEQUENCE {
		   configVrtlIntrNum	        Integer32,
		   vrtlIntrPortNum              Integer32,
		   vrtlIntrState              	INTEGER,
		   vrtlIntrMaxQueMem            Integer32,
		   vrtlIntrMinCellRate          Integer32,
		   vrtlIntrMaxCellRate          Integer32,
		   vrtlIntrCurrConfigPaths	Integer32
	  }


configVrtlIntrNum OBJECT-TYPE
	  SYNTAX     Integer32 (1..32)
	  MAX-ACCESS read-only
	  STATUS     current
	  DESCRIPTION
              "Virtual Interface Number. There are totaly.
             32 Virtual Interfaces on the card (egress)."
	  ::= { vrtlIntrConfigEntry 1 }

vrtlIntrPortNum OBJECT-TYPE
	  SYNTAX     Integer32 (0..4)
	  MAX-ACCESS read-write
	  STATUS     current
	  DESCRIPTION
              "Port number which will be connected to the
	      Virtual Interface. Value zero meens that this
	      virtual interface is not connected to any port."
	  ::= { vrtlIntrConfigEntry 2 }

vrtlIntrState OBJECT-TYPE
	SYNTAX  INTEGER {
		down (1),
		up   (2)
	}
	MAX-ACCESS read-write
	STATUS     current
	DESCRIPTION
            "Virtual Interface State."
	::= { vrtlIntrConfigEntry 3 }

vrtlIntrMaxQueMem OBJECT-TYPE
	SYNTAX     Integer32 (1..8)
	MAX-ACCESS read-write
	STATUS     current
	DESCRIPTION
	    "Virtual Interface's Max queue memory.
		1 = 4Kcells
		2 = 8Kcells
		3 = 16Kcells
		4 = 32Kcells
		5 = 64Kcells
		6 = 128Kcells
		7 = 256Kcells
		8 = 512Kcells."
	::= { vrtlIntrConfigEntry 4 }

vrtlIntrMinCellRate OBJECT-TYPE
	SYNTAX  Integer32 (103384..353208)
	MAX-ACCESS  read-write
	STATUS  current
	DESCRIPTION
            "Virtual Interface's minimum cell rate.
		The default value:
		for OC12 port is 1412832 cells/sec
		for OC3  port is  353208 cells/sec
		for T3   port is   96000 cells/sec
		for E3   port is   80000 cells/sec"
	::= { vrtlIntrConfigEntry 5 }

vrtlIntrMaxCellRate OBJECT-TYPE
	SYNTAX     Integer32 (103384..353208)
	MAX-ACCESS read-write
	STATUS     current
	DESCRIPTION
	    "Virtual Interface's maximum cell rate.
	     The default value:
		for OC12 port is 1412832 cells/sec
		for OC3  port is  353208 cells/sec
		for T3   port is   96000 cells/sec
		for E3   port is   80000 cells/sec"
	::= { vrtlIntrConfigEntry 6 }

vrtlIntrCurrConfigPaths OBJECT-TYPE
	SYNTAX     Integer32
	MAX-ACCESS read-only
	STATUS     current
	DESCRIPTION
	    "This is not a configurable parameter.
            This gives the count of paths currently configured on this
            virtual interface."
	::= { vrtlIntrConfigEntry 7 }

-- *************************************************************************
--
-- Port Virtual Interface Counter32s Group
--
-- *************************************************************************

vrtlIntrCounterTable OBJECT-TYPE
	  SYNTAX     SEQUENCE OF VrtlIntrCounterEntry
	  MAX-ACCESS not-accessible
	  STATUS     current
	  DESCRIPTION
		 "Virtual Interface Counter32s Table."
	   ::= { virtualInterfaceCnt 1 }

vrtlIntrCounterEntry OBJECT-TYPE
	  SYNTAX     VrtlIntrCounterEntry
	  MAX-ACCESS not-accessible
	  STATUS     current
	  DESCRIPTION
		 "An entry in the Virtual Interface Counter32 Table."
	   INDEX {countVrtlIntrNum}
	   ::= { vrtlIntrCounterTable 1 }

VrtlIntrCounterEntry ::=
	  SEQUENCE {
		   countVrtlIntrNum                         Integer32,
		   vrtlIntrTotalCellCnt                     Counter32,
		   vrtlIntrTotalQbinCellCnt                 Counter32,
		   vrtlIntrRxdValidOAMCellCnt               Counter32,
		   vrtlIntrRxdRmCellCnt                     Counter32,
		   vrtlIntrRxdClpUntaggedCellCnt            Counter32,
		   vrtlIntrRxdClpTaggedCellCnt              Counter32,
		   vrtlIntrRxdClpUntaggedDiscardedCellCnt   Counter32,
		   vrtlIntrRxdClpTaggedDiscardedCellCnt     Counter32,
		   vrtlIntrXmtdOAMCellCnt                   Counter32,
		   vrtlIntrXmtdRmCellCnt                    Counter32,
		   vrtlIntrXmtdClpUntaggedCellCnt           Counter32,
		   vrtlIntrXmtdClpTaggedCellCnt             Counter32
	  }


countVrtlIntrNum OBJECT-TYPE
	SYNTAX     Integer32 (1..32)
	MAX-ACCESS read-only
	STATUS     current
	DESCRIPTION
	    "Virtual Interface Number."
	::= { vrtlIntrCounterEntry 1 }

vrtlIntrTotalCellCnt OBJECT-TYPE
	SYNTAX     Counter32
	MAX-ACCESS read-only
	STATUS     current
	DESCRIPTION "
		Total number of cells (VC plus Qbin) that belong to
		this Virtual Interface."
	::= { vrtlIntrCounterEntry 2 }

vrtlIntrTotalQbinCellCnt OBJECT-TYPE
	SYNTAX     Counter32
	MAX-ACCESS read-only
	STATUS     current
	DESCRIPTION
            "Total number of cells in the Qbin belonging
	    to this Virtual Interface."
	::= { vrtlIntrCounterEntry 3 }

vrtlIntrRxdValidOAMCellCnt OBJECT-TYPE
	  SYNTAX     Counter32
	  MAX-ACCESS read-only
	  STATUS     current
	  DESCRIPTION
		 "Total number of OAM cell received."
	  ::= { vrtlIntrCounterEntry 4 }

vrtlIntrRxdRmCellCnt OBJECT-TYPE
	  SYNTAX     Counter32
	  MAX-ACCESS read-only
	  STATUS     current
	  DESCRIPTION
		 "Total number of RM cells Received."
	  ::= { vrtlIntrCounterEntry 5 }

vrtlIntrRxdClpUntaggedCellCnt OBJECT-TYPE
	  SYNTAX     Counter32
	  MAX-ACCESS read-only
	  STATUS     current
	  DESCRIPTION
		 "Total number of CLP-0 cells Received."
	  ::= { vrtlIntrCounterEntry 6 }

vrtlIntrRxdClpTaggedCellCnt OBJECT-TYPE
	  SYNTAX     Counter32
	  MAX-ACCESS read-only
	  STATUS     current
	  DESCRIPTION
		 "Total number of CLP-1 cells Received."
	  ::= { vrtlIntrCounterEntry 7 }

vrtlIntrRxdClpUntaggedDiscardedCellCnt OBJECT-TYPE
	  SYNTAX     Counter32
	  MAX-ACCESS read-only
	  STATUS     current
	  DESCRIPTION
		 "Total number of CLP-0 cells discarded at Ingress."
	  ::= { vrtlIntrCounterEntry 8 }

vrtlIntrRxdClpTaggedDiscardedCellCnt OBJECT-TYPE
	  SYNTAX     Counter32
	  MAX-ACCESS read-only
	  STATUS     current
	  DESCRIPTION
		 "Total number of CLP-1 cells discarded at Ingress."
	  ::= { vrtlIntrCounterEntry 9 }

vrtlIntrXmtdOAMCellCnt OBJECT-TYPE
	  SYNTAX     Counter32
	  MAX-ACCESS read-only
	  STATUS     current
	  DESCRIPTION
		 "Total number of OAM cells transmitted."
	  ::= { vrtlIntrCounterEntry 10 }

vrtlIntrXmtdRmCellCnt OBJECT-TYPE
	  SYNTAX     Counter32
	  MAX-ACCESS read-only
	  STATUS     current
	  DESCRIPTION
		 "Total number of RM(Resource Monitoring)
                 cells transmitted."
	  ::= { vrtlIntrCounterEntry 11 }

vrtlIntrXmtdClpUntaggedCellCnt OBJECT-TYPE
	  SYNTAX     Counter32
	  MAX-ACCESS read-only
	  STATUS     current
	  DESCRIPTION
		 "Total number of CLP-0 cells transmitted."
	  ::= { vrtlIntrCounterEntry 12 }

vrtlIntrXmtdClpTaggedCellCnt OBJECT-TYPE
	  SYNTAX     Counter32
	  MAX-ACCESS read-only
	  STATUS     current
	  DESCRIPTION
		 "Total number of CLP-1 cells transmitted."
	  ::= { vrtlIntrCounterEntry 13 }


-- *************************************************************************
--
-- Port Virtual Interface Qbin Configuration Group
--
-- *************************************************************************

vrtlIntrQbinConfigTable OBJECT-TYPE
	  SYNTAX     SEQUENCE OF VrtlIntrQbinConfigEntry
	  MAX-ACCESS not-accessible
	  STATUS     current
	  DESCRIPTION
		 "Virtual Interface QBin Configuration Table."
	   ::= { virtualInterfaceQbinCnf 1 }

vrtlIntrQbinConfigEntry OBJECT-TYPE
	  SYNTAX     VrtlIntrQbinConfigEntry
	  MAX-ACCESS not-accessible
	  STATUS     current
	  DESCRIPTION
		 "An entry in the Virtual Interface Qbin Config Table."
	   INDEX {queConfigVrtlIntrNum, queConfigVrtlIntrQbinNum}
	   ::= { vrtlIntrQbinConfigTable 1 }

VrtlIntrQbinConfigEntry ::=
	  SEQUENCE {
		   queConfigVrtlIntrNum               Integer32,
		   queConfigVrtlIntrQbinNum  	      Integer32,
		   vrtlIntrQbinState                  INTEGER,
		   vrtlIntrQbinPri                    Integer32,
		   vrtlIntrQbinRate                   Integer32,
		   vrtlIntrQbinDiscardSelection       INTEGER,
		   vrtlIntrQbinMaxThreshold 	      Integer32,
		   vrtlIntrQbinClpHiThreshold 	      Integer32,
		   vrtlIntrQbinClpLoThreshold 	      Integer32,
		   vrtlIntrQbinFrameDiscardThreshold  Integer32,
		   vrtlIntrQbinEfciThreshold          Integer32
	  }

queConfigVrtlIntrNum OBJECT-TYPE
	  SYNTAX     Integer32 (1..32)
	  MAX-ACCESS read-only
	  STATUS     current
	  DESCRIPTION
		 " Virtual Interface Number."
	  ::= { vrtlIntrQbinConfigEntry 1 }

queConfigVrtlIntrQbinNum OBJECT-TYPE
	  SYNTAX     Integer32 (1..16)
	  MAX-ACCESS read-only
	  STATUS     current
	  DESCRIPTION
		 " Virtual Interface Qbin Number. There are totaly 16  Qbin
		   per Virtual Interface."
	  ::= { vrtlIntrQbinConfigEntry 2 }

vrtlIntrQbinState OBJECT-TYPE
	  SYNTAX  INTEGER {
	              down (1),
	              up   (2)
	          }
	  MAX-ACCESS read-write
	  STATUS     current
	  DESCRIPTION
		 "Virtual Interface QBIN state."
	  ::= { vrtlIntrQbinConfigEntry 3 }

vrtlIntrQbinPri OBJECT-TYPE
	  SYNTAX     Integer32 (1..16)
	  MAX-ACCESS read-write
	  STATUS     current
	  DESCRIPTION
		 "This indicates the priority of the QBIN service
		   within the Virtual Interface."
	  ::= { vrtlIntrQbinConfigEntry 4 }

vrtlIntrQbinRate OBJECT-TYPE
	  SYNTAX     Integer32 (0..353208)
	  MAX-ACCESS read-write
	  STATUS     current
	  DESCRIPTION
		 "The rate at which cells in the QBIN are serviced.
		   Max Cell rate for OC3 interface is 353208 cell/sec."
	  ::= { vrtlIntrQbinConfigEntry 5 }

vrtlIntrQbinDiscardSelection OBJECT-TYPE
	  SYNTAX  INTEGER {
		  clpHysteresis(1),
		  frameDiscard(3)
	  }
	  MAX-ACCESS  read-write
	  STATUS  current
	  DESCRIPTION
		 " Virtual Interface QBin Congestion control option."
	  DEFVAL { clpHysteresis }
	  ::= { vrtlIntrQbinConfigEntry 6 }

vrtlIntrQbinMaxThreshold OBJECT-TYPE
	  SYNTAX     Integer32 (0..512000)
	  MAX-ACCESS read-write
	  STATUS     current
	  DESCRIPTION
		 "Max cells that can be queued in the QBIN.
		  The Get value will be different from the Set
		  value because of FW internal round up."
	  ::= { vrtlIntrQbinConfigEntry 7 }

vrtlIntrQbinClpHiThreshold OBJECT-TYPE
	  SYNTAX     Integer32 (0..512000)
	  MAX-ACCESS read-write
	  STATUS     current
	  DESCRIPTION
		 "The threshold above which the tagged cells
		  will be dropped.
		  The Get value will be different from the Set
		  value because of FW internal round up."
	  ::= { vrtlIntrQbinConfigEntry 8 }

vrtlIntrQbinClpLoThreshold OBJECT-TYPE
	  SYNTAX     Integer32 (0..512000)
	  MAX-ACCESS read-write
	  STATUS     current
	  DESCRIPTION
		 "Valid only if congestion control is set to
		  CLP hysterises. The threshold upto which the
		  dropping of the tagged cells should continue once
		  it has crossed CLP HI threshold.
		  The Get value will be different from the Set
		  value because of FW internal round up."
	  ::= { vrtlIntrQbinConfigEntry 9 }

vrtlIntrQbinFrameDiscardThreshold OBJECT-TYPE
	  SYNTAX     Integer32 (0..512000)
	  MAX-ACCESS read-write
	  STATUS     current
	  DESCRIPTION
		 "Valid only if congestion control is set to
		  Frame Discard. It is the threshold after which
		  the QE will start discarding the entire frame
		  if one or more cells of the frame is discarded..
		  The Get value will be different from the Set
		  value because of FW internal round up."
	  ::= { vrtlIntrQbinConfigEntry 10 }

vrtlIntrQbinEfciThreshold OBJECT-TYPE
	  SYNTAX     Integer32 (0..512000)
	  MAX-ACCESS read-write
	  STATUS     current
	  DESCRIPTION
		 "The threshold above which the EFCI bits of
		  the cell is set.
		  The Get value will be different from the Set
		  value because of FW internal round up."
	  ::= { vrtlIntrQbinConfigEntry 11 }


-- *************************************************************************
--
-- Port Virtual Interface Qbin Counter32s Group
--
-- *************************************************************************

vrtlIntrQbinCounterTable OBJECT-TYPE
	  SYNTAX  SEQUENCE OF VrtlIntrQbinCounterEntry
	  MAX-ACCESS  not-accessible
	  STATUS  current
	  DESCRIPTION
		 "Virtual Interface QBin Counter Table."
	   ::= { virtualInterfaceQbinCnt 1 }

vrtlIntrQbinCounterEntry OBJECT-TYPE
	  SYNTAX VrtlIntrQbinCounterEntry
	  MAX-ACCESS  not-accessible
	  STATUS  current
	  DESCRIPTION
		 "An entry in the Virtual Interface Qbin Counter Table.
                 Each entry contains information on the statistics supported
                 for an interface."
	   INDEX {queConuterVrtlIntrNum, queCounterVrtlIntrQbinNum}
	   ::= { vrtlIntrQbinCounterTable 1 }

VrtlIntrQbinCounterEntry ::=
	  SEQUENCE {
		   queConuterVrtlIntrNum                  INTEGER,
		   queCounterVrtlIntrQbinNum              INTEGER,
		   vrtlIntrQbinCurrentCellCnt             Counter32,
		   vrtlIntrQbinRxdCellCnt                 Counter32,
		   vrtlIntrQbinTxdCellCnt                 Counter32,
		   vrtlIntrQbinDiscardedCellCnt           Counter32
	  }


queConuterVrtlIntrNum OBJECT-TYPE
	  SYNTAX  INTEGER (1..32)
	  MAX-ACCESS  read-only
	  STATUS  current
	  DESCRIPTION
		 " Virtual Interface Number."
	  ::= { vrtlIntrQbinCounterEntry 1 }

queCounterVrtlIntrQbinNum OBJECT-TYPE
	  SYNTAX  INTEGER (1..16)
	  MAX-ACCESS  read-only
	  STATUS  current
	  DESCRIPTION
		 "Virtual Interface Qbin Number. There are totaly 16  Qbin
		   per Virtual Interface."
	  ::= { vrtlIntrQbinCounterEntry 2 }

vrtlIntrQbinCurrentCellCnt OBJECT-TYPE
	  SYNTAX  Counter32
	  MAX-ACCESS  read-only
	  STATUS  current
	  DESCRIPTION
		 " Total number of cells currently in the Qbin."
	  ::= { vrtlIntrQbinCounterEntry 3 }

vrtlIntrQbinRxdCellCnt OBJECT-TYPE
	  SYNTAX  Counter32
	  MAX-ACCESS  read-only
	  STATUS  current
	  DESCRIPTION
		 " Total number of cells arrived to the QBIN."
	  ::= { vrtlIntrQbinCounterEntry 4 }

vrtlIntrQbinTxdCellCnt OBJECT-TYPE
	  SYNTAX  Counter32
	  MAX-ACCESS  read-only
	  STATUS  current
	  DESCRIPTION
		 "Total number of cells departured from QBIN."
	  ::= { vrtlIntrQbinCounterEntry 5 }

vrtlIntrQbinDiscardedCellCnt OBJECT-TYPE
	SYNTAX  Counter32
	MAX-ACCESS  read-only
	STATUS  current
	DESCRIPTION
		"Total number of arrivals to QBIN which were discarded."
	::= { vrtlIntrQbinCounterEntry 6 }

-- conformance information

cmvPortMIBConformance  OBJECT IDENTIFIER ::= { ciscoMgx82xxVirtualPortMIB 2 }

cmvPortMIBGroups       OBJECT IDENTIFIER ::= { cmvPortMIBConformance 1 }

cmvPortMIBCompliances  OBJECT IDENTIFIER ::= { cmvPortMIBConformance 2 }

-- compliance statements

cmvPortCompliance MODULE-COMPLIANCE
    STATUS  current
    DESCRIPTION
        "The compliance statement for objects related
        to SRM MIB."
    MODULE  -- this module
    MANDATORY-GROUPS {
        cmvPortConfGroup,
        cmvPortStatsGroup,
        cmvPortQbinConfGroup,
        cmvPortQbinStatsGroup
    }
    ::= { cmvPortMIBCompliances 1 }

cmvPortConfGroup OBJECT-GROUP
    OBJECTS {
        configVrtlIntrNum,
	vrtlIntrPortNum,
	vrtlIntrState,
	vrtlIntrMaxQueMem,
	vrtlIntrMinCellRate,
	vrtlIntrMaxCellRate,
	vrtlIntrCurrConfigPaths
      }
      STATUS current
      DESCRIPTION
          "The collection of objects which are used for
          configuring Virtual Ports in PXM1 service module."
      ::= { cmvPortMIBGroups 1 }

cmvPortStatsGroup OBJECT-GROUP
    OBJECTS {
        countVrtlIntrNum,
	vrtlIntrTotalCellCnt,
	vrtlIntrTotalQbinCellCnt,
	vrtlIntrRxdValidOAMCellCnt,
	vrtlIntrRxdRmCellCnt,
	vrtlIntrRxdClpUntaggedCellCnt,
	vrtlIntrRxdClpTaggedCellCnt,
	vrtlIntrRxdClpUntaggedDiscardedCellCnt,
	vrtlIntrRxdClpTaggedDiscardedCellCnt,
	vrtlIntrXmtdOAMCellCnt,
	vrtlIntrXmtdRmCellCnt,
	vrtlIntrXmtdClpUntaggedCellCnt,
	vrtlIntrXmtdClpTaggedCellCnt
      }
      STATUS current
      DESCRIPTION
          "The collection of objects related to
          statistics for Virtual Ports in PXM1 service module."
      ::= { cmvPortMIBGroups 2 }

cmvPortQbinConfGroup OBJECT-GROUP
    OBJECTS {
        queConfigVrtlIntrNum,
	queConfigVrtlIntrQbinNum,
	vrtlIntrQbinState,
	vrtlIntrQbinPri,
	vrtlIntrQbinRate,
	vrtlIntrQbinDiscardSelection,
	vrtlIntrQbinMaxThreshold,
	vrtlIntrQbinClpHiThreshold,
	vrtlIntrQbinClpLoThreshold,
	vrtlIntrQbinFrameDiscardThreshold,
	vrtlIntrQbinEfciThreshold
      }
      STATUS current
      DESCRIPTION
          "The collection of objects related to
          configuration of Qbin related things in PXM1
          service module."
      ::= { cmvPortMIBGroups 3 }

cmvPortQbinStatsGroup OBJECT-GROUP
    OBJECTS {
        queConuterVrtlIntrNum,
	queCounterVrtlIntrQbinNum,
	vrtlIntrQbinCurrentCellCnt,
	vrtlIntrQbinRxdCellCnt,
	vrtlIntrQbinTxdCellCnt,
	vrtlIntrQbinDiscardedCellCnt
      }
      STATUS current
      DESCRIPTION
          "The collection of objects related to
          statistics for Qbin related things in PXM1
          service module."
      ::= { cmvPortMIBGroups 4 }

END
