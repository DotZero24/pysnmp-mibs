-- *****************************************************************
-- CISCO-SYSLOG-EVENT-EXT-MIB.my:
-- CISCO SYSLOG EVENT EXTENSION MIB file
--
-- February 2002, Francis Pang
--
-- Copyright (c) 2002 by Cisco Systems, Inc.
-- All rights reserved.
-- *****************************************************************
--
CISCO-SYSLOG-EVENT-EXT-MIB DEFINITIONS ::= BEGIN

IMPORTS
        MODULE-IDENTITY,
        OBJECT-TYPE,
        Counter32
                FROM SNMPv2-SMI
        MODULE-COMPLIANCE,
        OBJECT-GROUP
                FROM SNMPv2-CONF
        TEXTUAL-CONVENTION
                FROM SNMPv2-TC
        SyslogSeverity
                FROM CISCO-SYSLOG-MIB
        ciscoMgmt
                FROM CISCO-SMI;


ciscoSyslogEventExtMIB MODULE-IDENTITY
        LAST-UPDATED    "200202120000Z"
        ORGANIZATION    "Cisco System Inc."
        CONTACT-INFO
                "       Cisco Systems
                        Customer Service

                Postal: 170 West Tasman Drive,
                        San Jose CA 95134-1706.
                        USA

                   Tel: +1 800 553-NETS

                E-mail: cs-snmp@cisco.com"
        DESCRIPTION
                "This MIB module extends the Cisco Syslog
                MIB and provides network management support
                to handle and process Syslog messages as
                device events."
        REVISION        "200202120000Z"
        DESCRIPTION
                "Initial version of this MIB module."
        ::= { ciscoMgmt 270 }




ciscoSyslogEventExtMIBObjects OBJECT IDENTIFIER
        ::= { ciscoSyslogEventExtMIB 1 }

cslogEventConfig OBJECT IDENTIFIER
        ::= { ciscoSyslogEventExtMIBObjects 1}


CslogEventDisposition ::= TEXTUAL-CONVENTION
        STATUS     current
        DESCRIPTION
                "This definition specifies the manner in which a
                Syslog message should be handled by the system as
                a device event. Events are first recorded by the
                Syslog subsystem, and then they can be counted,
                displayed on the console, or forward to external
                device. The four disposition mechanisms are:
                    none(0)     - Record only, no further handling.
                    count(1)    - All Syslog messages received after
                                  this bit is set will be counted
                                  according to their corresponding
                                  event types.
                    display(2)  - All Syslog messages received after
                                  this bit is set will be displayed on
                                  the device console, HTML console
                                  or WEB pages (pending on severity
                                  level configuration of each display
                                  types).
                    notify(3)   - All Syslog messages received after
                                  this bit is set will cause
                                  notification to be sent."
        SYNTAX     BITS {
                none(0),
                count(1),
                display(2),
                notify(3) }



cslogEventDetailDefault OBJECT-TYPE
        SYNTAX     INTEGER {
                noDisplay(1),
                sparseDetail(2),
                normalDetail(3),
                verboseDetail(4),
                exhaustiveDetail(5) }
        MAX-ACCESS read-write
        STATUS     current
        DESCRIPTION
                "This object defines the detail level at which
                Syslog messages are displayed on the console or
                HTML user interface. Detail level classifications
                are:
                    noDisplay(1)         - No display at all.
                    sparseDetail(2)      - Minimum detail.
                    normalDetail(3)      - General detail.
                    verboseDetail(4)     - Verbose detail.
                    exhaustiveDetail(5)  - Full detail."
        DEFVAL     { normalDetail }
        ::= { cslogEventConfig 1 }

cslogEventSeverityDispConsole OBJECT-TYPE
        SYNTAX     SyslogSeverity
        MAX-ACCESS read-write
        STATUS     current
        DESCRIPTION
                "This object indicates which syslog severity
                level messages can be displayed on the console.
                A high severity value implies a low severity.
                If the display bit on the object
                cslogEventDisposition is set for this severity,
                all messages have severity values less than or
                equal to clogMaxSeverity and this object will
                be displayed on the console."
        DEFVAL     { info }
        ::= { cslogEventConfig 2 }

cslogEventSeverityDispHtmlGUI OBJECT-TYPE
        SYNTAX     SyslogSeverity
        MAX-ACCESS read-write
        STATUS     current
        DESCRIPTION
                "This object indicates which syslog severity
                level messages can be displayed on the event log
                GUI. A high severity value implies a low severity.
                If the display bit on the object
                cslogEventDisposition is set for this severity,
                all messages have severity values less than or
                equal to clogMaxSeverity and this object will
                be displayed on the event log GUI web pages."
        DEFVAL     { info }
        ::= { cslogEventConfig 3 }

cslogEventSeverityDispHtmlConsol OBJECT-TYPE
        SYNTAX     SyslogSeverity
        MAX-ACCESS read-write
        STATUS     current
        DESCRIPTION
                "This object indicates which syslog severity
                level messages can be displayed on the HTML
                event log console.
                A high severity value implies a low severity.
                If the display bit on the object
                cslogEventDisposition is set for this severity,
                all messages have severity values less than or
                equal to clogMaxSeverity and this object will
                be displayed on the GUI browser console page."
        DEFVAL     { info }
        ::= { cslogEventConfig 4 }


cslogEventDispositionTable OBJECT-TYPE
        SYNTAX     SEQUENCE OF CslogEventDispositionEntry
        MAX-ACCESS not-accessible
        STATUS     current
        DESCRIPTION
                "This table contains parameters to configure
                Syslog message disposition mechanisms and keep
                message counts."
        ::= { cslogEventConfig 5 }

cslogEventDispositionEntry OBJECT-TYPE
        SYNTAX     CslogEventDispositionEntry
        MAX-ACCESS not-accessible
        STATUS     current
        DESCRIPTION
                "There is one entry per Syslog severity in the
                cslogEventDispositionTable. Each entry contains
                parameters for message disposition and count."
        INDEX { cslogEventDispositionSeverity }
        ::= { cslogEventDispositionTable 1 }


CslogEventDispositionEntry ::= SEQUENCE {
        cslogEventDispositionSeverity  SyslogSeverity,
        cslogEventDisposition          CslogEventDisposition,
        cslogEventDispositionCount     Counter32 }


cslogEventDispositionSeverity OBJECT-TYPE
        SYNTAX     SyslogSeverity
        MAX-ACCESS not-accessible
        STATUS     current
        DESCRIPTION
                "This object defines the Syslog serverity."
        ::= { cslogEventDispositionEntry 1 }

cslogEventDisposition OBJECT-TYPE
        SYNTAX     CslogEventDisposition
        MAX-ACCESS read-write
        STATUS     current
        DESCRIPTION
                "This object defines the disposition method for
                Syslog messages of a specific severity."
        DEFVAL     { {none} }
        ::= { cslogEventDispositionEntry 2 }


cslogEventDispositionCount OBJECT-TYPE
        SYNTAX     Counter32
        MAX-ACCESS read-only
        STATUS     current
        DESCRIPTION
                "This is the number of Syslog messages of a specific
                severity."
        ::= { cslogEventDispositionEntry 3 }


-- *****************************************************************
--   Conformance information
-- *****************************************************************

ciscoSlogEventExtMIBConformance
      OBJECT IDENTIFIER ::= { ciscoSyslogEventExtMIB 2 }

ciscoSlogEventExtMIBCompliances
      OBJECT IDENTIFIER ::= { ciscoSlogEventExtMIBConformance 1 }

ciscoSlogEventExtMIBGroups
      OBJECT IDENTIFIER ::= { ciscoSlogEventExtMIBConformance 2 }


-- *****************************************************************
--   Compliance statements
-- *****************************************************************

ciscoSlogEventExtCompliance MODULE-COMPLIANCE
        STATUS     current
        DESCRIPTION
                "The compliance statement for the cslogEventExt
                groups."
        MODULE
                MANDATORY-GROUPS {
                        ciscoSlogEventExtConfigGroup,
                        ciscoSlogEventExtStatsGroup
                                 }
        ::= { ciscoSlogEventExtMIBCompliances 1 }

-- *****************************************************************
--   Units of conformance
-- *****************************************************************

ciscoSlogEventExtConfigGroup OBJECT-GROUP
        OBJECTS {
                cslogEventDetailDefault,
                cslogEventSeverityDispConsole,
                cslogEventSeverityDispHtmlGUI,
                cslogEventSeverityDispHtmlConsol,
                cslogEventDisposition }
        STATUS     current
        DESCRIPTION
                "These are objects supporting Syslog event
                configuration."
        ::= { ciscoSlogEventExtMIBGroups 1 }

ciscoSlogEventExtStatsGroup OBJECT-GROUP
        OBJECTS {
                cslogEventDispositionCount }
        STATUS     current
        DESCRIPTION
                "These are objects to provide Syslog event
                statistics."
        ::= { ciscoSlogEventExtMIBGroups 2 }


END
