--**********************************************************************
-- CISCO-DMN-DSG-DISEQC-DISH-POSITION.mib : Mib file for DiSEqc Control
--
-- August 2010, Tel MIB Team
--
--
-- Copyright (c) 1999-2010 by Cisco Systems, Inc.
-- All rights reserved.
--**********************************************************************

CISCO-DMN-DSG-DISEQC-DISH-POSITION-MIB

DEFINITIONS ::= BEGIN

IMPORTS
    MODULE-IDENTITY,
    OBJECT-TYPE, Integer32
        FROM SNMPv2-SMI
    DisplayString
        FROM SNMPv2-TC
    OBJECT-GROUP, MODULE-COMPLIANCE
        FROM SNMPv2-CONF
    ciscoDSGUtilities
        FROM CISCO-DMN-DSG-ROOT-MIB;


ciscoDSGDiSEqC  MODULE-IDENTITY
    LAST-UPDATED  "201008301100Z" -- August 30 2010 11:00:00 GMT
    ORGANIZATION    "Cisco Systems, Inc."
    CONTACT-INFO
       "Cisco Systems, Inc.
        Customer Service
        Postal: 170 W Tasman Drive
        San Jose, CA 95134
        USA
        Tel: +1 800 553 NETS

        E-mail: cs-ipsla@cisco.com"
    DESCRIPTION    "Cisco DiSEqC Dish Position MIB."

    REVISION      "201008301100Z"
    DESCRIPTION   "V01.00.03 2010-08-30
                   Updated for adherence to SNMPv2 format."

    REVISION       "201003220500Z"
    DESCRIPTION    "V01.00.02 2010-03-22
                    The Syntax of Unsigned32 MIB objects whose range is
                    within the range of Integer32, is updated to
                    Integer32."

    REVISION      "201002121200Z"
    DESCRIPTION   "V01.00.01 2010-02-12
                   The Syntax of read-only object is updated to
                   DisplayString."

    REVISION      "200912071200Z"
    DESCRIPTION   "V01.00.00 2009-12-07
                   Initial Version."

    ::= { ciscoDSGUtilities 19 }

--********************************************
--diSEqC Table Branch
--********************************************

diSEqCTable OBJECT-TYPE
     SYNTAX  SEQUENCE OF DiSEqCEntry
     MAX-ACCESS  not-accessible
     STATUS  current
     DESCRIPTION
         "DiSEqC Table."
     ::= { ciscoDSGDiSEqC 1 }

diSEqCEntry OBJECT-TYPE
     SYNTAX  DiSEqCEntry
     MAX-ACCESS  not-accessible
     STATUS  current
     DESCRIPTION
         "Entry for DiSEqC Table."
     INDEX { diSEqCInstance }
     ::= { diSEqCTable 1 }

DiSEqCEntry ::= SEQUENCE
{
  diSEqCInstance            Integer32,
  diSEqCEnable              INTEGER,
  diSEqCDishPosition        Integer32,
  diSEqCPositionJog         INTEGER,
  diSEqCEWFlag              INTEGER,
  diSEqCSatSelect           Integer32,
  diSEqCInstallerAction     INTEGER,
  diSEqCUserAction          INTEGER,
  diSEqCMode                INTEGER,
  diSEqCAction              INTEGER,
  diSEqCStatusMode          INTEGER,
  diSEqCStatusDishPosition  DisplayString,
  diSEqCStatusEastWestFlag  INTEGER,
  diSEqCStatusLastAction    INTEGER,
  diSEqCStatusEnable        INTEGER
}

diSEqCInstance OBJECT-TYPE
     SYNTAX  Integer32 (1..1)
     MAX-ACCESS  not-accessible
     STATUS  current
     DESCRIPTION
         "Instance for DiSEqC Table."
     ::= { diSEqCEntry 1 }

diSEqCEnable OBJECT-TYPE
     SYNTAX  INTEGER {
             disable(1),
             enable(2)
         }
     MAX-ACCESS  read-write
     STATUS  current
     DESCRIPTION
         "DiSEqC On/off."
     ::= { diSEqCEntry 2 }

diSEqCDishPosition OBJECT-TYPE
     SYNTAX  Integer32 (0..750)
     MAX-ACCESS  read-write
     STATUS  current
     DESCRIPTION
         "Absolute Dish Position in steps of 1.
          The scaling factor is 1/10."
     ::= { diSEqCEntry 3 }

diSEqCPositionJog OBJECT-TYPE
     SYNTAX  INTEGER {
             writeOnly(1),
             coarseAdjustmentEast(2),
             coarseAdjustmentWest(3),
             fineAdjustmentEast(4),
             fineAdjustmentWest(5)
         }
     MAX-ACCESS  read-write
     STATUS  current
     DESCRIPTION
         "Dish position fine adjustment - amount of steps
         ( each step is 2 degrees ). This is a diSEqc control object."
     ::= { diSEqCEntry 4 }

diSEqCEWFlag OBJECT-TYPE
     SYNTAX  INTEGER {
             east(1),
             west(2),
             notApplicable(3)
         }
     MAX-ACCESS  read-write
     STATUS  current
     DESCRIPTION
         "Dish direction."
     ::= { diSEqCEntry 5 }

diSEqCSatSelect OBJECT-TYPE
     SYNTAX  Integer32 (1..255)
     MAX-ACCESS   read-write
     STATUS  current
     DESCRIPTION
         " Satellite Select."
     ::= { diSEqCEntry 6 }

diSEqCInstallerAction OBJECT-TYPE
     SYNTAX  INTEGER {
             none(1),
             continuousWestMovement(2),
             continuousEastMovement(3),
             stopMove(4),
             gotoAbsolutePositionWest(5),
             gotoAbsolutePositionEast(6),
             gotoReference(7),
             gotoSatellite(8),
             storeSatellite(9),
             clearLimits(10),
             storeEastLimits(11),
             storeWestLimits(12),
             calculatePosition(13)
         }
     MAX-ACCESS  read-write
     STATUS  current
     DESCRIPTION
         "Installer Action."
     ::= { diSEqCEntry 7 }

diSEqCUserAction OBJECT-TYPE
     SYNTAX  INTEGER {
             none(1),
             gotoSatellite(2)
         }
     MAX-ACCESS  read-write
     STATUS  current
     DESCRIPTION
         "User Action."
     ::= { diSEqCEntry 8 }

diSEqCMode OBJECT-TYPE
     SYNTAX  INTEGER {
             installer(1),
             user(2)
         }
     MAX-ACCESS  read-write
     STATUS  current
     DESCRIPTION
         "Installation Mode,User has limited rights."
     ::= { diSEqCEntry 9 }

diSEqCAction OBJECT-TYPE
     SYNTAX  INTEGER {
             writeOnly(1),
             activate(2)
         }
     MAX-ACCESS  read-write
     STATUS  current
     DESCRIPTION
         "DiSEqC Control Action.Setting this MIB object to activate( 2 )
         moves the dish to the position determined by the diSEqC
         setting parameters."
     ::= { diSEqCEntry 10 }

diSEqCStatusMode OBJECT-TYPE
     SYNTAX  INTEGER {
             installer(1),
             user(2)
         }
     MAX-ACCESS  read-only
     STATUS  current
     DESCRIPTION
         "DiSEqC Mode Status."
     ::= { diSEqCEntry 11 }

diSEqCStatusDishPosition OBJECT-TYPE
     SYNTAX  DisplayString (SIZE(0..32))
     MAX-ACCESS  read-only
     STATUS  current
     DESCRIPTION
         "Dish Position Status.The range is from 0.0 to 75.0 in
         steps of 0.1."
     ::= { diSEqCEntry 12 }

diSEqCStatusEastWestFlag  OBJECT-TYPE
     SYNTAX  INTEGER {
             east(1),
             west(2),
             notApplicable(3)
         }
     MAX-ACCESS  read-only
     STATUS  current
     DESCRIPTION
         "DiSEqC East/West Flag Status."
     ::= { diSEqCEntry 13 }

diSEqCStatusLastAction  OBJECT-TYPE
     SYNTAX  INTEGER {
             clear(1),
             coarseAdjustmentEast(2),
             coarseAdjustmenWest(3),
             fineAdjustmenEast(4),
             fineAdjustmentWest(5),
             installerAction(6),
             userAction(7)
         }
     MAX-ACCESS  read-only
     STATUS  current
     DESCRIPTION
         "DiSEqC Status - Last Action."
     ::= { diSEqCEntry 14 }

diSEqCStatusEnable OBJECT-TYPE
     SYNTAX  INTEGER {
             disabled(1),
             enabled(2)
         }
     MAX-ACCESS  read-only
     STATUS  current
     DESCRIPTION
         "DiSEqC Status - Enable Status."
     ::= { diSEqCEntry 15 }

END
