-- *****************************************************************
-- CISCO-DYNTAMIC-TEMPLATE-TC-MIB
-- Definitions of textual conventions used by MIB modules describing
-- and using dynamic templates.
--
-- September 2007, Patrick R. Gili
--
-- Copyright (c) 2007, 2011-2012 by Cisco Systems Inc.
-- All rights reserved.
-- *****************************************************************

CISCO-DYNAMIC-TEMPLATE-TC-MIB DEFINITIONS ::= BEGIN

IMPORTS
    MODULE-IDENTITY
        FROM SNMPv2-SMI
    TEXTUAL-CONVENTION
        FROM SNMPv2-TC
    ciscoMgmt
        FROM CISCO-SMI;


ciscoDynamicTemplateTcMIB MODULE-IDENTITY
    LAST-UPDATED    "201201270000Z"
    ORGANIZATION    "Cisco Systems, Inc."
    CONTACT-INFO
            "Cisco Systems
            Customer Service

            Postal: 170 W Tasman Drive
            San Jose, CA 95134

            Tel: +1 800 553-NETS

            E-mail: cs-snmp@cisco.com"
    DESCRIPTION
        "This MIB module defines textual conventions used by the
        CISCO-DYNAMIC-TEMPLATE-MIB and MIB modules that use and expand
        on dynamic templates."
    REVISION        "200709060000Z"
    DESCRIPTION
        "The initial version of the MIB module."
    ::= { ciscoMgmt 783 }



DynamicTemplateName ::= TEXTUAL-CONVENTION
    STATUS          current
    DESCRIPTION
        "A string-value that identifies a dynamic template.  The
        semantics of the string-value are the same as those specified
        by the SnmpAdminString textual convention defined by the
        SNMP-FRAMEWORK-MIB [RFC3411]."

    REFERENCE
        "D. Harrington, R. Resuhn, B. Wijnen, 'An Architecture for
        Describing Simple Network Management Protocol (SNMP)
        Management
        Frameworks', RFC-3411, December 2002."
    SYNTAX          OCTET STRING (SIZE (1..64))

DynamicTemplateType ::= TEXTUAL-CONVENTION
    STATUS          current
    DESCRIPTION
        "An enumerated integer-value describing the type of dynamic
        template:

        'other'
            The implementation of the MIB module using this textual
            convention does not recognize the type of dynamic template.

        'derived'
            A configuration resulting from the union of the attributes
            contained by all the dynamic templates associated with a
            target.  The system generates a derived configuration, and
            an EMS/NMS cannot directly modify it.  An EMS/NMS can only
            affect a derived configuration by modifying one or more of
            the dynamic templates associated with the target.

        'ppp'
            A PPP template is a set of locally-configured attributes
            relating to the configuration of a PPP interface.

        'ethernet'
            An Ethernet template is a set of locally-configured
            attributes used by the system to configure dynamic
            interfaces initiated on Ethernet virtual interfaces (e.g.,
            EoMPLS) or automatically created VLANs.

        'ipSubscriber'
            An IP subscriber template is a set of locally-configured
            attributes used by the system to configure certain types of
            IP and L2 subscriber sessions.

        'service'
            A service template is a set of locally-configured attributes
            used by the system to configure subscriber sessions.  These
            attributes specifically relate to services, and the system
            applies these attributes in response to subscriber session
            life-cycle events."
    SYNTAX          INTEGER  {
                        other(1),
                        derived(2),
                        ppp(3),
                        ethernet(4),
                        ipSubscriber(5),
                        service(6)
                    }

DynamicTemplateTargetType ::= TEXTUAL-CONVENTION
    STATUS          current
    DESCRIPTION
        "An enumerated integer-value describing the type of target
        associated with one or more dynamic templates:

            'other'
                The implementation of the MIB module using this textual
                convention does not recognize the type of target.

            'interface'
                The target is a physical, logical, or virtual interface
                represented by an ifEntry (defined by the IF-MIB).

        An implementation must ensure that DynamicTemplateTargetType
        object and any associated DynamicTemplateTargetId objects are
        consistent.  An attempt to set a DynamicTemplateTargetType
        object to a value inconsistent with the associated
        DynamicTemplateTargetId object must result in a response with
        an
        error-status of 'inconsistentValue'."

    REFERENCE
        "K. McCloghrie and F. Kastenholtz, 'The Interfaces Group
        MIB',
        RFC-2863, June 2000."
    SYNTAX          INTEGER  {
                        other(1),
                        interface(2)
                    }

DynamicTemplateTargetId ::= TEXTUAL-CONVENTION
    STATUS          current
    DESCRIPTION
        "An binary string-value in network byte order identifying a
        target associated with one or more dynamic templates.

        An implementation must interpret a DynamicTemplateTargetId
        value
        within the context of a DynamicTemplateTargetType.  Every usage
        of the DynamicTemplateTargetId textual convention must have a
        corresponding object specifying the DynamicTemplateType that
        provides this context.  It is most appropriate that a MIB
        module
        logical registers the DynamicTemplateType object before the use
        of the DynamicTemplateTargetId textual convention within the
        same logical row.

        The value of a DynamicTemplateTargetId object must always be
        consistent with the value of the associated
        DynamicTemplateTargetType object.  An attempt to set a
        DynamicTemplateTargetId object to a value inconsistent with the
        with the associated DynamicTemplateTargetType object must
        result
        in a response with an error-status of 'inconsistentValue'.

        If the DynamicTemplateTargetType is 'interface', then the representation
        of DynamicTemplateTargetId is as below

        octets   contents              encoding
         1-4     ifIndex               network-byte order"

    REFERENCE
        "K. McCloghrie and F. Kastenholtz, 'The Interfaces Group
        MIB',
        RFC-2863, June 2000."
    SYNTAX          OCTET STRING (SIZE (1..20))

END
