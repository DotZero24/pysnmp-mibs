-- *********************************************************************
-- CISCO-FIREPOWER-COMPUTE-MIB.my
--
-- MIB representation of the Cisco Firepower
-- COMPUTE management information model package
--
-- Created March 2020 by Charles Bullis
--
-- Copyright (c) 2005-2020 Cisco Systems, Inc. All rights reserved.
--
-- *********************************************************************

CISCO-FIREPOWER-COMPUTE-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIBObjects,
    CfprManagedObjectId,
    CfprManagedObjectDn
        FROM CISCO-FIREPOWER-MIB
    CfprComputeABoardPower,
    CfprComputeAdminLinkAggregation,
    CfprComputeAdminMemoryState,
    CfprComputeAdminPowerState,
    CfprComputeAdminState,
    CfprComputeAdminTrigger,
    CfprComputeAlarmSeverity,
    CfprComputeAssociation,
    CfprComputeAvailability,
    CfprComputeBlackListing,
    CfprComputeBladeFsmCurrentFsm,
    CfprComputeBladeFsmStageName,
    CfprComputeBladeFsmTaskFlags,
    CfprComputeBladeFsmTaskItem,
    CfprComputeBladeSlotId,
    CfprComputeChassisConnPolicyChassisId,
    CfprComputeChassisDiscAction,
    CfprComputeChassisQualMaxId,
    CfprComputeChassisQualMinId,
    CfprComputeCheckPoint,
    CfprComputeConnectivityRebalancing,
    CfprComputeDiscovery,
    CfprComputeIOHubEnvStatsHistThresholded,
    CfprComputeIOHubEnvStatsThresholded,
    CfprComputeIssues,
    CfprComputeKvmMgmtPolicyVmediaEncryption,
    CfprComputeLinkAggregation,
    CfprComputeMbPowerStatsHistThresholded,
    CfprComputeMbPowerStatsThresholded,
    CfprComputeMbTempStatsHistThresholded,
    CfprComputeMbTempStatsThresholded,
    CfprComputeMemoryUnitConstraintType,
    CfprComputeMode,
    CfprComputeOwner,
    CfprComputePCIeFatalCompletionStatsThresholded,
    CfprComputePCIeFatalProtocolStatsThresholded,
    CfprComputePCIeFatalReceiveStatsThresholded,
    CfprComputePCIeFatalStatsThresholded,
    CfprComputePciCapOrder,
    CfprComputePhysicalFsmCurrentFsm,
    CfprComputePhysicalFsmStageName,
    CfprComputePhysicalFsmTaskFlags,
    CfprComputePhysicalFsmTaskItem,
    CfprComputePhysicalLowVoltageMemory,
    CfprComputePooledRackUnitId,
    CfprComputePooledSlotSlotId,
    CfprComputePsuClusterState,
    CfprComputePsuControlRedundancy,
    CfprComputePsuRedundancy,
    CfprComputePsuRedundancyOperQualifier,
    CfprComputePsuRedundancyOperState,
    CfprComputeRackQualMaxId,
    CfprComputeRackQualMinId,
    CfprComputeRackUnitFsmCurrentFsm,
    CfprComputeRackUnitFsmStageName,
    CfprComputeRackUnitFsmTaskFlags,
    CfprComputeRackUnitFsmTaskItem,
    CfprComputeRackUnitId,
    CfprComputeRackUnitMbTempStatsHistThresholded,
    CfprComputeRackUnitMbTempStatsThresholded,
    CfprComputeScrubAction,
    CfprComputeServerDiscPolicyFsmCurrentFsm,
    CfprComputeServerDiscPolicyFsmStageName,
    CfprComputeServerDiscPolicyFsmTaskItem,
    CfprComputeServerMgmtDiscAction,
    CfprComputeSlotQualMaxId,
    CfprComputeSlotQualMinId,
    CfprComputeUpgradeStatus,
    CfprConditionRemoteInvRslt,
    CfprEquipmentBiosPostState,
    CfprEquipmentBoardAggregationRole,
    CfprEquipmentBoardConnectorType,
    CfprEquipmentConnectionStatus,
    CfprEquipmentCpuType,
    CfprEquipmentOperability,
    CfprEquipmentPowerState,
    CfprEquipmentPresence,
    CfprEquipmentSensorThresholdStatus,
    CfprEquipmentSlotStatus,
    CfprFsmCompletion,
    CfprFsmFlags,
    CfprFsmFsmStageStatus,
    CfprLsOperState,
    CfprNetworkSwitchId,
    CfprPolicyPolicyOwner,
    CfprPoolPoolAssignmentOrder,
    CfprTrigAckChangeDetails,
    CfprTrigAckChanges,
    CfprTrigAckDisr,
    CfprTrigAckOperState,
    CfprTrigAckPrevOperState,
    CfprTrigAdminState
        FROM CISCO-FIREPOWER-TC-MIB;

cfprComputeObjects MODULE-IDENTITY
    LAST-UPDATED    "202003100000Z"
    ORGANIZATION    "Cisco Systems Inc."
    CONTACT-INFO
        "Cisco Systems
        Customer Service

        Postal: 170 W Tasman Drive
        San Jose, CA  95134
        USA

        Tel: +1 800 553-NETS

        E-mail: firepower-mibs@cisco.com"
    DESCRIPTION
        "MIB representation of the Cisco Firepower
        COMPUTE management information model package"
    ::= { ciscoFirepowerMIBObjects 12 }

cfprComputeAutoconfigPolicyTable OBJECT-TYPE
    SYNTAX           SEQUENCE OF CfprComputeAutoconfigPolicyEntry
    MAX-ACCESS       not-accessible
    STATUS           current
    DESCRIPTION
        "Cisco Firepower compute:AutoconfigPolicy managed object table"
    ::= { cfprComputeObjects 1 }

cfprComputeAutoconfigPolicyEntry OBJECT-TYPE
    SYNTAX           CfprComputeAutoconfigPolicyEntry
    MAX-ACCESS       not-accessible
    STATUS           current
    DESCRIPTION
        "Entry for the cfprComputeAutoconfigPolicyTable table."
    INDEX { cfprComputeAutoconfigPolicyInstanceId }
    ::= { cfprComputeAutoconfigPolicyTable 1 }

CfprComputeAutoconfigPolicyEntry ::= SEQUENCE {
    cfprComputeAutoconfigPolicyInstanceId                            CfprManagedObjectId,
    cfprComputeAutoconfigPolicyDn                                    CfprManagedObjectDn,
    cfprComputeAutoconfigPolicyRn                                    SnmpAdminString,
    cfprComputeAutoconfigPolicyDescr                                 SnmpAdminString,
    cfprComputeAutoconfigPolicyDstDn                                 SnmpAdminString,
    cfprComputeAutoconfigPolicyIntId                                 SnmpAdminString,
    cfprComputeAutoconfigPolicyName                                  SnmpAdminString,
    cfprComputeAutoconfigPolicyPolicyLevel                           Gauge32,
    cfprComputeAutoconfigPolicyPolicyOwner                           CfprPolicyPolicyOwner,
    cfprComputeAutoconfigPolicyQualifier                             SnmpAdminString,
    cfprComputeAutoconfigPolicySrcTemplName                          SnmpAdminString
}

cfprComputeAutoconfigPolicyInstanceId OBJECT-TYPE
    SYNTAX       CfprManagedObjectId
    MAX-ACCESS   not-accessible
    STATUS       current
    DESCRIPTION
        "Instance identifier of the managed object."
    ::= { cfprComputeAutoconfigPolicyEntry 1 }

cfprComputeAutoconfigPolicyDn OBJECT-TYPE
    SYNTAX       CfprManagedObjectDn
    MAX-ACCESS   read-only
    STATUS       current
    DESCRIPTION
        "Cisco Firepower compute:AutoconfigPolicy:dn managed
        object property"
    ::= { cfprComputeAutoconfigPolicyEntry 2 }

cfprComputeAutoconfigPolicyRn OBJECT-TYPE
    SYNTAX       SnmpAdminString
    MAX-ACCESS   read-only
    STATUS       current
    DESCRIPTION
        "Cisco Firepower compute:AutoconfigPolicy:rn managed
        object property"
    ::= { cfprComputeAutoconfigPolicyEntry 3 }

cfprComputeAutoconfigPolicyDescr OBJECT-TYPE
    SYNTAX       SnmpAdminString
    MAX-ACCESS   read-only
    STATUS       current
    DESCRIPTION
        "Cisco Firepower compute:AutoconfigPolicy:descr
        managed object property"
    ::= { cfprComputeAutoconfigPolicyEntry 4 }

cfprComputeAutoconfigPolicyDstDn OBJECT-TYPE
    SYNTAX       SnmpAdminString
    MAX-ACCESS   read-only
    STATUS       current
    DESCRIPTION
        "Cisco Firepower compute:AutoconfigPolicy:dstDn
        managed object property"
    ::= { cfprComputeAutoconfigPolicyEntry 5 }

cfprComputeAutoconfigPolicyIntId OBJECT-TYPE
    SYNTAX       SnmpAdminString
    MAX-ACCESS   read-only
    STATUS       current
    DESCRIPTION
        "Cisco Firepower compute:AutoconfigPolicy:intId
        managed object property"
    ::= { cfprComputeAutoconfigPolicyEntry 6 }

cfprComputeAutoconfigPolicyName OBJECT-TYPE
    SYNTAX       SnmpAdminString
    MAX-ACCESS   read-only
    STATUS       current
    DESCRIPTION
        "Cisco Firepower compute:AutoconfigPolicy:name
        managed object property"
    ::= { cfprComputeAutoconfigPolicyEntry 7 }

cfprComputeAutoconfigPolicyPolicyLevel OBJECT-TYPE
    SYNTAX       Gauge32
    MAX-ACCESS   read-only
    STATUS       current
    DESCRIPTION
        "Cisco Firepower compute:AutoconfigPolicy:policyLevel
        managed object property"
    ::= { cfprComputeAutoconfigPolicyEntry 8 }

cfprComputeAutoconfigPolicyPolicyOwner OBJECT-TYPE
    SYNTAX       CfprPolicyPolicyOwner
    MAX-ACCESS   read-only
    STATUS       current
    DESCRIPTION
        "Cisco Firepower compute:AutoconfigPolicy:policyOwner
        managed object property"
    ::= { cfprComputeAutoconfigPolicyEntry 9 }

cfprComputeAutoconfigPolicyQualifier OBJECT-TYPE
    SYNTAX       SnmpAdminString
    MAX-ACCESS   read-only
    STATUS       current
    DESCRIPTION
        "Cisco Firepower compute:AutoconfigPolicy:qualifier
        managed object property"
    ::= { cfprComputeAutoconfigPolicyEntry 10 }

cfprComputeAutoconfigPolicySrcTemplName OBJECT-TYPE
    SYNTAX       SnmpAdminString
    MAX-ACCESS   read-only
    STATUS       current
    DESCRIPTION
        "Cisco Firepower compute:AutoconfigPolicy:srcTemplName
        managed object property"
    ::= { cfprComputeAutoconfigPolicyEntry 11 }

cfprComputeBladeTable OBJECT-TYPE
    SYNTAX           SEQUENCE OF CfprComputeBladeEntry
    MAX-ACCESS       not-accessible
    STATUS           current
    DESCRIPTION
        "Cisco Firepower compute:Blade managed object table"
    ::= { cfprComputeObjects 2 }

cfprComputeBladeEntry OBJECT-TYPE
    SYNTAX           CfprComputeBladeEntry
    MAX-ACCESS       not-accessible
    STATUS           current
    DESCRIPTION
        "Entry for the cfprComputeBladeTable table."
    INDEX { cfprComputeBladeInstanceId }
    ::= { cfprComputeBladeTable 1 }

CfprComputeBladeEntry ::= SEQUENCE {
    cfprComputeBladeInstanceId                                       CfprManagedObjectId,
    cfprComputeBladeDn                                               CfprManagedObjectDn,
    cfprComputeBladeRn                                               SnmpAdminString,
    cfprComputeBladeAdminPower                                       CfprComputeAdminPowerState,
    cfprComputeBladeAdminState                                       CfprComputeAdminState,
    cfprComputeBladeAssignedToDn                                     SnmpAdminString,
    cfprComputeBladeAssociation                                      CfprComputeAssociation,
    cfprComputeBladeAvailability                                     CfprComputeAvailability,
    cfprComputeBladeAvailableMemory                                  Gauge32,
    cfprComputeBladeChassisId                                        Gauge32,
    cfprComputeBladeCheckPoint                                       CfprComputeCheckPoint,
    cfprComputeBladeConnPath                                         CfprEquipmentConnectionStatus,
    cfprComputeBladeConnStatus                                       CfprEquipmentConnectionStatus,
    cfprComputeBladeDescr                                            SnmpAdminString,
    cfprComputeBladeDiscovery                                        CfprComputeDiscovery,
    cfprComputeBladeFltAggr                                          Unsigned64,
    cfprComputeBladeFsmDescr                                         SnmpAdminString,
    cfprComputeBladeFsmFlags                                         SnmpAdminString,
    cfprComputeBladeFsmPrev                                          SnmpAdminString,
    cfprComputeBladeFsmProgr                                         Gauge32,
    cfprComputeBladeFsmRmtInvErrCode                                 Gauge32,
    cfprComputeBladeFsmRmtInvErrDescr                                SnmpAdminString,
    cfprComputeBladeFsmRmtInvRslt                                    CfprConditionRemoteInvRslt,
    cfprComputeBladeFsmStageDescr                                    SnmpAdminString,
    cfprComputeBladeFsmStamp                                         DateAndTime,
    cfprComputeBladeFsmStatus                                        SnmpAdminString,
    cfprComputeBladeFsmTry                                           Gauge32,
    cfprComputeBladeIntId                                            SnmpAdminString,
    cfprComputeBladeLc                                               CfprComputeAdminTrigger,
    cfprComputeBladeLcTs                                             DateAndTime,
    cfprComputeBladeLocalId                                          SnmpAdminString,
    cfprComputeBladeLowVoltageMemory                                 CfprComputePhysicalLowVoltageMemory,
    cfprComputeBladeManagingInst                                     CfprNetworkSwitchId,
    cfprComputeBladeMemorySpeed                                      Gauge32,
    cfprComputeBladeMfgTime                                          DateAndTime,
    cfprComputeBladeModel                                            SnmpAdminString,
    cfprComputeBladeName                                             SnmpAdminString,
    cfprComputeBladeNumOfAdaptors                                    Gauge32,
    cfprComputeBladeNumOfCores                                       Gauge32,
    cfprComputeBladeNumOfCoresEnabled                                Gauge32,
    cfprComputeBladeNumOfCpus                                        Gauge32,
    cfprComputeBladeNumOfEthHostIfs                                  Gauge32,
    cfprComputeBladeNumOfFcHostIfs                                   Gauge32,
    cfprComputeBladeNumOfThreads                                     Gauge32,
    cfprComputeBladeOperPower                                        CfprEquipmentPowerState,
    cfprComputeBladeOperQualifier                                    CfprComputeIssues,
    cfprComputeBladeOperState                                        CfprLsOperState,
    cfprComputeBladeOperability                                      CfprEquipmentOperability,
    cfprComputeBladeOriginalUuid                                     SnmpAdminString,
    cfprComputeBladePartNumber                                       SnmpAdminString,
    cfprComputeBladePolicyLevel                                      Gauge32,
    cfprComputeBladePolicyOwner                                      CfprPolicyPolicyOwner,
    cfprComputeBladePresence                                         CfprEquipmentSlotStatus,
    cfprComputeBladeRevision                                         SnmpAdminString,
    cfprComputeBladeScaledMode                                       CfprComputeMode,
    cfprComputeBladeSerial                                           SnmpAdminString,
    cfprComputeBladeServerId                                         SnmpAdminString,
    cfprComputeBladeSlotId                                           CfprComputeBladeSlotId,
    cfprComputeBladeTotalMemory                                      Gauge32,
    cfprComputeBladeUpgradeScenario                                  CfprComputeUpgradeStatus,
    cfprComputeBladeUsrLbl                                           SnmpAdminString,
    cfprComputeBladeUuid                                             SnmpAdminString,
    cfprComputeBladeVendor                                           SnmpAdminString,
    cfprComputeBladeVid                                              SnmpAdminString,
    cfprComputeBladeLastAdaptorCrashReset                            SnmpAdminString,
    cfprComputeBladeLastBiosHangReset                                DateAndTime,
    cfprComputeBladePostState                                        CfprEquipmentBiosPostState,
    cfprComputeBladePostWaitCount                                    Gauge32,
    cfprComputeBladeResetCount                                       Gauge32
}

cfprComputeBladeInstanceId OBJECT-TYPE
    SYNTAX       CfprManagedObjectId
    MAX-ACCESS   not-accessible
    STATUS       current
    DESCRIPTION
        "Instance identifier of the managed object."
    ::= { cfprComputeBladeEntry 1 }

cfprComputeBladeDn OBJECT-TYPE
    SYNTAX       CfprManagedObjectDn
    MAX-ACCESS   read-only
    STATUS       current
    DESCRIPTION
        "Cisco Firepower compute:Blade:dn managed object property"
    ::= { cfprComputeBladeEntry 2 }

cfprComputeBladeRn OBJECT-TYPE
    SYNTAX       SnmpAdminString
    MAX-ACCESS   read-only
    STATUS       current
    DESCRIPTION
        "Cisco Firepower compute:Blade:rn managed object property"
    ::= { cfprComputeBladeEntry 3 }

cfprComputeBladeAdminPower OBJECT-TYPE
    SYNTAX       CfprComputeAdminPowerState
    MAX-ACCESS   read-only
    STATUS       current
    DESCRIPTION
        "Cisco Firepower compute:Blade:adminPower managed object property"
    ::= { cfprComputeBladeEntry 4 }

cfprComputeBladeAdminState OBJECT-TYPE
    SYNTAX       CfprComputeAdminState
    MAX-ACCESS   read-only
    STATUS       current
    DESCRIPTION
        "Cisco Firepower compute:Blade:adminState managed object property"
    ::= { cfprComputeBladeEntry 5 }

cfprComputeBladeAssignedToDn OBJECT-TYPE
    SYNTAX       SnmpAdminString
    MAX-ACCESS   read-only
    STATUS       current
    DESCRIPTION
        "Cisco Firepower compute:Blade:assignedToDn managed
        object property"
    ::= { cfprComputeBladeEntry 6 }

cfprComputeBladeAssociation OBJECT-TYPE
    SYNTAX       CfprComputeAssociation
    MAX-ACCESS   read-only
    STATUS       current
    DESCRIPTION
        "Cisco Firepower compute:Blade:association managed
        object property"
    ::= { cfprComputeBladeEntry 7 }

cfprComputeBladeAvailability OBJECT-TYPE
    SYNTAX       CfprComputeAvailability
    MAX-ACCESS   read-only
    STATUS       current
    DESCRIPTION
        "Cisco Firepower compute:Blade:availability managed
        object property"
    ::= { cfprComputeBladeEntry 8 }

cfprComputeBladeAvailableMemory OBJECT-TYPE
    SYNTAX       Gauge32
    MAX-ACCESS   read-only
    STATUS       current
    DESCRIPTION
        "Cisco Firepower compute:Blade:availableMemory
        managed object property"
    ::= { cfprComputeBladeEntry 9 }

cfprComputeBladeChassisId OBJECT-TYPE
    SYNTAX       Gauge32
    MAX-ACCESS   read-only
    STATUS       current
    DESCRIPTION
        "Cisco Firepower compute:Blade:chassisId managed object property"
    ::= { cfprComputeBladeEntry 10 }

cfprComputeBladeCheckPoint OBJECT-TYPE
    SYNTAX       CfprComputeCheckPoint
    MAX-ACCESS   read-only
    STATUS       current
    DESCRIPTION
        "Cisco Firepower compute:Blade:checkPoint managed object property"
    ::= { cfprComputeBladeEntry 11 }

cfprComputeBladeConnPath OBJECT-TYPE
    SYNTAX       CfprEquipmentConnectionStatus
    MAX-ACCESS   read-only
    STATUS       current
    DESCRIPTION
        "Cisco Firepower compute:Blade:connPath managed object property"
    ::= { cfprComputeBladeEntry 12 }

cfprComputeBladeConnStatus OBJECT-TYPE
    SYNTAX       CfprEquipmentConnectionStatus
    MAX-ACCESS   read-only
    STATUS       current
    DESCRIPTION
        "Cisco Firepower compute:Blade:connStatus managed object property"
    ::= { cfprComputeBladeEntry 13 }

cfprComputeBladeDescr OBJECT-TYPE
    SYNTAX       SnmpAdminString
    MAX-ACCESS   read-only
    STATUS       current
    DESCRIPTION
        "Cisco Firepower compute:Blade:descr managed object property"
    ::= { cfprComputeBladeEntry 14 }

cfprComputeBladeDiscovery OBJECT-TYPE
    SYNTAX       CfprComputeDiscovery
    MAX-ACCESS   read-only
    STATUS       current
    DESCRIPTION
        "Cisco Firepower compute:Blade:discovery managed object property"
    ::= { cfprComputeBladeEntry 15 }

cfprComputeBladeFltAggr OBJECT-TYPE
    SYNTAX       Unsigned64
    MAX-ACCESS   read-only
    STATUS       current
    DESCRIPTION
        "Cisco Firepower compute:Blade:fltAggr managed object property"
    ::= { cfprComputeBladeEntry 16 }

cfprComputeBladeFsmDescr OBJECT-TYPE
    SYNTAX       SnmpAdminString
    MAX-ACCESS   read-only
    STATUS       current
    DESCRIPTION
        "Cisco Firepower compute:Blade:fsmDescr managed object property"
    ::= { cfprComputeBladeEntry 17 }

cfprComputeBladeFsmFlags OBJECT-TYPE
    SYNTAX       SnmpAdminString
    MAX-ACCESS   read-only
    STATUS       current
    DESCRIPTION
        "Cisco Firepower compute:Blade:fsmFlags managed object property"
    ::= { cfprComputeBladeEntry 18 }

cfprComputeBladeFsmPrev OBJECT-TYPE
    SYNTAX       SnmpAdminString
    MAX-ACCESS   read-only
    STATUS       current
    DESCRIPTION
        "Cisco Firepower compute:Blade:fsmPrev managed object property"
    ::= { cfprComputeBladeEntry 19 }

cfprComputeBladeFsmProgr OBJECT-TYPE
    SYNTAX       Gauge32
    MAX-ACCESS   read-only
    STATUS       current
    DESCRIPTION
        "Cisco Firepower compute:Blade:fsmProgr managed object property"
    ::= { cfprComputeBladeEntry 20 }

cfprComputeBladeFsmRmtInvErrCode OBJECT-TYPE
    SYNTAX       Gauge32
    MAX-ACCESS   read-only
    STATUS       current
    DESCRIPTION
        "Cisco Firepower compute:Blade:fsmRmtInvErrCode
        managed object property"
    ::= { cfprComputeBladeEntry 21 }

cfprComputeBladeFsmRmtInvErrDescr OBJECT-TYPE
    SYNTAX       SnmpAdminString
    MAX-ACCESS   read-only
    STATUS       current
    DESCRIPTION
        "Cisco Firepower compute:Blade:fsmRmtInvErrDescr
        managed object property"
    ::= { cfprComputeBladeEntry 22 }

cfprComputeBladeFsmRmtInvRslt OBJECT-TYPE
    SYNTAX       CfprConditionRemoteInvRslt
    MAX-ACCESS   read-only
    STATUS       current
    DESCRIPTION
        "Cisco Firepower compute:Blade:fsmRmtInvRslt managed
        object property"
    ::= { cfprComputeBladeEntry 23 }

cfprComputeBladeFsmStageDescr OBJECT-TYPE
    SYNTAX       SnmpAdminString
    MAX-ACCESS   read-only
    STATUS       current
    DESCRIPTION
        "Cisco Firepower compute:Blade:fsmStageDescr managed
        object property"
    ::= { cfprComputeBladeEntry 24 }

cfprComputeBladeFsmStamp OBJECT-TYPE
    SYNTAX       DateAndTime
    MAX-ACCESS   read-only
    STATUS       current
    DESCRIPTION
        "Cisco Firepower compute:Blade:fsmStamp managed object property"
    ::= { cfprComputeBladeEntry 25 }

cfprComputeBladeFsmStatus OBJECT-TYPE
    SYNTAX       SnmpAdminString
    MAX-ACCESS   read-only
    STATUS       current
    DESCRIPTION
        "Cisco Firepower compute:Blade:fsmStatus managed object property"
    ::= { cfprComputeBladeEntry 26 }

cfprComputeBladeFsmTry OBJECT-TYPE
    SYNTAX       Gauge32
    MAX-ACCESS   read-only
    STATUS       current
    DESCRIPTION
        "Cisco Firepower compute:Blade:fsmTry managed object property"
    ::= { cfprComputeBladeEntry 27 }

cfprComputeBladeIntId OBJECT-TYPE
    SYNTAX       SnmpAdminString
    MAX-ACCESS   read-only
    STATUS       current
    DESCRIPTION
        "Cisco Firepower compute:Blade:intId managed object property"
    ::= { cfprComputeBladeEntry 28 }

cfprComputeBladeLc OBJECT-TYPE
    SYNTAX       CfprComputeAdminTrigger
    MAX-ACCESS   read-only
    STATUS       current
    DESCRIPTION
        "Cisco Firepower compute:Blade:lc managed object property"
    ::= { cfprComputeBladeEntry 29 }

cfprComputeBladeLcTs OBJECT-TYPE
    SYNTAX       DateAndTime
    MAX-ACCESS   read-only
    STATUS       current
    DESCRIPTION
        "Cisco Firepower compute:Blade:lcTs managed object property"
    ::= { cfprComputeBladeEntry 30 }

cfprComputeBladeLocalId OBJECT-TYPE
    SYNTAX       SnmpAdminString
    MAX-ACCESS   read-only
    STATUS       current
    DESCRIPTION
        "Cisco Firepower compute:Blade:localId managed object property"
    ::= { cfprComputeBladeEntry 31 }

cfprComputeBladeLowVoltageMemory OBJECT-TYPE
    SYNTAX       CfprComputePhysicalLowVoltageMemory
    MAX-ACCESS   read-only
    STATUS       current
    DESCRIPTION
        "Cisco Firepower compute:Blade:lowVoltageMemory
        managed object property"
    ::= { cfprComputeBladeEntry 32 }

cfprComputeBladeManagingInst OBJECT-TYPE
    SYNTAX       CfprNetworkSwitchId
    MAX-ACCESS   read-only
    STATUS       current
    DESCRIPTION
        "Cisco Firepower compute:Blade:managingInst managed
        object property"
    ::= { cfprComputeBladeEntry 33 }

cfprComputeBladeMemorySpeed OBJECT-TYPE
    SYNTAX       Gauge32
    MAX-ACCESS   read-only
    STATUS       current
    DESCRIPTION
        "Cisco Firepower compute:Blade:memorySpeed managed
        object property"
    ::= { cfprComputeBladeEntry 34 }

cfprComputeBladeMfgTime OBJECT-TYPE
    SYNTAX       DateAndTime
    MAX-ACCESS   read-only
    STATUS       current
    DESCRIPTION
        "Cisco Firepower compute:Blade:mfgTime managed object property"
    ::= { cfprComputeBladeEntry 35 }

cfprComputeBladeModel OBJECT-TYPE
    SYNTAX       SnmpAdminString
    MAX-ACCESS   read-only
    STATUS       current
    DESCRIPTION
        "Cisco Firepower compute:Blade:model managed object property"
    ::= { cfprComputeBladeEntry 36 }

cfprComputeBladeName OBJECT-TYPE
    SYNTAX       SnmpAdminString
    MAX-ACCESS   read-only
    STATUS       current
    DESCRIPTION
        "Cisco Firepower compute:Blade:name managed object property"
    ::= { cfprComputeBladeEntry 37 }

cfprComputeBladeNumOfAdaptors OBJECT-TYPE
    SYNTAX       Gauge32
    MAX-ACCESS   read-only
    STATUS       current
    DESCRIPTION
        "Cisco Firepower compute:Blade:numOfAdaptors managed
        object property"
    ::= { cfprComputeBladeEntry 38 }

cfprComputeBladeNumOfCores OBJECT-TYPE
    SYNTAX       Gauge32
    MAX-ACCESS   read-only
    STATUS       current
    DESCRIPTION
        "Cisco Firepower compute:Blade:numOfCores managed object property"
    ::= { cfprComputeBladeEntry 39 }

cfprComputeBladeNumOfCoresEnabled OBJECT-TYPE
    SYNTAX       Gauge32
    MAX-ACCESS   read-only
    STATUS       current
    DESCRIPTION
        "Cisco Firepower compute:Blade:numOfCoresEnabled
        managed object property"
    ::= { cfprComputeBladeEntry 40 }

cfprComputeBladeNumOfCpus OBJECT-TYPE
    SYNTAX       Gauge32
    MAX-ACCESS   read-only
    STATUS       current
    DESCRIPTION
        "Cisco Firepower compute:Blade:numOfCpus managed object property"
    ::= { cfprComputeBladeEntry 41 }

cfprComputeBladeNumOfEthHostIfs OBJECT-TYPE
    SYNTAX       Gauge32
    MAX-ACCESS   read-only
    STATUS       current
    DESCRIPTION
        "Cisco Firepower compute:Blade:numOfEthHostIfs
        managed object property"
    ::= { cfprComputeBladeEntry 42 }

cfprComputeBladeNumOfFcHostIfs OBJECT-TYPE
    SYNTAX       Gauge32
    MAX-ACCESS   read-only
    STATUS       current
    DESCRIPTION
        "Cisco Firepower compute:Blade:numOfFcHostIfs managed
        object property"
    ::= { cfprComputeBladeEntry 43 }

cfprComputeBladeNumOfThreads OBJECT-TYPE
    SYNTAX       Gauge32
    MAX-ACCESS   read-only
    STATUS       current
    DESCRIPTION
        "Cisco Firepower compute:Blade:numOfThreads managed
        object property"
    ::= { cfprComputeBladeEntry 44 }

cfprComputeBladeOperPower OBJECT-TYPE
    SYNTAX       CfprEquipmentPowerState
    MAX-ACCESS   read-only
    STATUS       current
    DESCRIPTION
        "Cisco Firepower compute:Blade:operPower managed object property"
    ::= { cfprComputeBladeEntry 45 }

cfprComputeBladeOperQualifier OBJECT-TYPE
    SYNTAX       CfprComputeIssues
    MAX-ACCESS   read-only
    STATUS       current
    DESCRIPTION
        "Cisco Firepower compute:Blade:operQualifier managed
        object property"
    ::= { cfprComputeBladeEntry 46 }

cfprComputeBladeOperState OBJECT-TYPE
    SYNTAX       CfprLsOperState
    MAX-ACCESS   read-only
    STATUS       current
    DESCRIPTION
        "Cisco Firepower compute:Blade:operState managed object property"
    ::= { cfprComputeBladeEntry 47 }

cfprComputeBladeOperability OBJECT-TYPE
    SYNTAX       CfprEquipmentOperability
    MAX-ACCESS   read-only
    STATUS       current
    DESCRIPTION
        "Cisco Firepower compute:Blade:operability managed
        object property"
    ::= { cfprComputeBladeEntry 48 }

cfprComputeBladeOriginalUuid OBJECT-TYPE
    SYNTAX       SnmpAdminString
    MAX-ACCESS   read-only
    STATUS       current
    DESCRIPTION
        "Cisco Firepower compute:Blade:originalUuid managed
        object property"
    ::= { cfprComputeBladeEntry 49 }

cfprComputeBladePartNumber OBJECT-TYPE
    SYNTAX       SnmpAdminString
    MAX-ACCESS   read-only
    STATUS       current
    DESCRIPTION
        "Cisco Firepower compute:Blade:partNumber managed object property"
    ::= { cfprComputeBladeEntry 50 }

cfprComputeBladePolicyLevel OBJECT-TYPE
    SYNTAX       Gauge32
    MAX-ACCESS   read-only
    STATUS       current
    DESCRIPTION
        "Cisco Firepower compute:Blade:policyLevel managed
        object property"
    ::= { cfprComputeBladeEntry 51 }

cfprComputeBladePolicyOwner OBJECT-TYPE
    SYNTAX       CfprPolicyPolicyOwner
    MAX-ACCESS   read-only
    STATUS       current
    DESCRIPTION
        "Cisco Firepower compute:Blade:policyOwner managed
        object property"
    ::= { cfprComputeBladeEntry 52 }

cfprComputeBladePresence OBJECT-TYPE
    SYNTAX       CfprEquipmentSlotStatus
    MAX-ACCESS   read-only
    STATUS       current
    DESCRIPTION
        "Cisco Firepower compute:Blade:presence managed object property"
    ::= { cfprComputeBladeEntry 53 }

cfprComputeBladeRevision OBJECT-TYPE
    SYNTAX       SnmpAdminString
    MAX-ACCESS   read-only
    STATUS       current
    DESCRIPTION
        "Cisco Firepower compute:Blade:revision managed object property"
    ::= { cfprComputeBladeEntry 54 }

cfprComputeBladeScaledMode OBJECT-TYPE
    SYNTAX       CfprComputeMode
    MAX-ACCESS   read-only
    STATUS       current
    DESCRIPTION
        "Cisco Firepower compute:Blade:scaledMode managed object property"
    ::= { cfprComputeBladeEntry 55 }

cfprComputeBladeSerial OBJECT-TYPE
    SYNTAX       SnmpAdminString
    MAX-ACCESS   read-only
    STATUS       current
    DESCRIPTION
        "Cisco Firepower compute:Blade:serial managed object property"
    ::= { cfprComputeBladeEntry 56 }

cfprComputeBladeServerId OBJECT-TYPE
    SYNTAX       SnmpAdminString
    MAX-ACCESS   read-only
    STATUS       current
    DESCRIPTION
        "Cisco Firepower compute:Blade:serverId managed object property"
    ::= { cfprComputeBladeEntry 57 }

cfprComputeBladeSlotId OBJECT-TYPE
    SYNTAX       CfprComputeBladeSlotId
    MAX-ACCESS   read-only
    STATUS       current
    DESCRIPTION
        "Cisco Firepower compute:Blade:slotId managed object property"
    ::= { cfprComputeBladeEntry 58 }

cfprComputeBladeTotalMemory OBJECT-TYPE
    SYNTAX       Gauge32
    MAX-ACCESS   read-only
    STATUS       current
    DESCRIPTION
        "Cisco Firepower compute:Blade:totalMemory managed
        object property"
    ::= { cfprComputeBladeEntry 59 }

cfprComputeBladeUpgradeScenario OBJECT-TYPE
    SYNTAX       CfprComputeUpgradeStatus
    MAX-ACCESS   read-only
    STATUS       current
    DESCRIPTION
        "Cisco Firepower compute:Blade:upgradeScenario
        managed object property"
    ::= { cfprComputeBladeEntry 60 }

cfprComputeBladeUsrLbl OBJECT-TYPE
    SYNTAX       SnmpAdminString
    MAX-ACCESS   read-only
    STATUS       current
    DESCRIPTION
        "Cisco Firepower compute:Blade:usrLbl managed object property"
    ::= { cfprComputeBladeEntry 61 }

cfprComputeBladeUuid OBJECT-TYPE
    SYNTAX       SnmpAdminString
    MAX-ACCESS   read-only
    STATUS       current
    DESCRIPTION
        "Cisco Firepower compute:Blade:uuid managed object property"
    ::= { cfprComputeBladeEntry 62 }

cfprComputeBladeVendor OBJECT-TYPE
    SYNTAX       SnmpAdminString
    MAX-ACCESS   read-only
    STATUS       current
    DESCRIPTION
        "Cisco Firepower compute:Blade:vendor managed object property"
    ::= { cfprComputeBladeEntry 63 }

cfprComputeBladeVid OBJECT-TYPE
    SYNTAX       SnmpAdminString
    MAX-ACCESS   read-only
    STATUS       current
    DESCRIPTION
        "Cisco Firepower compute:Blade:vid managed object property"
    ::= { cfprComputeBladeEntry 64 }

cfprComputeBladeLastAdaptorCrashReset OBJECT-TYPE
    SYNTAX       SnmpAdminString
    MAX-ACCESS   read-only
    STATUS       current
    DESCRIPTION
        "Cisco Firepower compute:Blade:lastAdaptorCrashReset
        managed object property"
    ::= { cfprComputeBladeEntry 65 }

cfprComputeBladeLastBiosHangReset OBJECT-TYPE
    SYNTAX       DateAndTime
    MAX-ACCESS   read-only
    STATUS       current
    DESCRIPTION
        "Cisco Firepower compute:Blade:lastBiosHangReset
        managed object property"
    ::= { cfprComputeBladeEntry 66 }

cfprComputeBladePostState OBJECT-TYPE
    SYNTAX       CfprEquipmentBiosPostState
    MAX-ACCESS   read-only
    STATUS       current
    DESCRIPTION
        "Cisco Firepower compute:Blade:postState managed object property"
    ::= { cfprComputeBladeEntry 67 }

cfprComputeBladePostWaitCount OBJECT-TYPE
    SYNTAX       Gauge32
    MAX-ACCESS   read-only
    STATUS       current
    DESCRIPTION
        "Cisco Firepower compute:Blade:postWaitCount managed
        object property"
    ::= { cfprComputeBladeEntry 68 }

cfprComputeBladeResetCount OBJECT-TYPE
    SYNTAX       Gauge32
    MAX-ACCESS   read-only
    STATUS       current
    DESCRIPTION
        "Cisco Firepower compute:Blade:resetCount managed object property"
    ::= { cfprComputeBladeEntry 69 }

cfprComputeBladeDiscPolicyTable OBJECT-TYPE
    SYNTAX           SEQUENCE OF CfprComputeBladeDiscPolicyEntry
    MAX-ACCESS       not-accessible
    STATUS           current
    DESCRIPTION
        "Cisco Firepower compute:BladeDiscPolicy managed object table"
    ::= { cfprComputeObjects 3 }

cfprComputeBladeDiscPolicyEntry OBJECT-TYPE
    SYNTAX           CfprComputeBladeDiscPolicyEntry
    MAX-ACCESS       not-accessible
    STATUS           current
    DESCRIPTION
        "Entry for the cfprComputeBladeDiscPolicyTable table."
    INDEX { cfprComputeBladeDiscPolicyInstanceId }
    ::= { cfprComputeBladeDiscPolicyTable 1 }

CfprComputeBladeDiscPolicyEntry ::= SEQUENCE {
    cfprComputeBladeDiscPolicyInstanceId                             CfprManagedObjectId,
    cfprComputeBladeDiscPolicyDn                                     CfprManagedObjectDn,
    cfprComputeBladeDiscPolicyRn                                     SnmpAdminString,
    cfprComputeBladeDiscPolicyAction                                 SnmpAdminString,
    cfprComputeBladeDiscPolicyDescr                                  SnmpAdminString,
    cfprComputeBladeDiscPolicyIntId                                  SnmpAdminString,
    cfprComputeBladeDiscPolicyName                                   SnmpAdminString,
    cfprComputeBladeDiscPolicyPolicyLevel                            Gauge32,
    cfprComputeBladeDiscPolicyPolicyOwner                            CfprPolicyPolicyOwner,
    cfprComputeBladeDiscPolicyQualifier                              SnmpAdminString,
    cfprComputeBladeDiscPolicyScrubPolicyName                        SnmpAdminString
}

cfprComputeBladeDiscPolicyInstanceId OBJECT-TYPE
    SYNTAX       CfprManagedObjectId
    MAX-ACCESS   not-accessible
    STATUS       current
    DESCRIPTION
        "Instance identifier of the managed object."
    ::= { cfprComputeBladeDiscPolicyEntry 1 }

cfprComputeBladeDiscPolicyDn OBJECT-TYPE
    SYNTAX       CfprManagedObjectDn
    MAX-ACCESS   read-only
    STATUS       current
    DESCRIPTION
        "Cisco Firepower compute:BladeDiscPolicy:dn managed
        object property"
    ::= { cfprComputeBladeDiscPolicyEntry 2 }

cfprComputeBladeDiscPolicyRn OBJECT-TYPE
    SYNTAX       SnmpAdminString
    MAX-ACCESS   read-only
    STATUS       current
    DESCRIPTION
        "Cisco Firepower compute:BladeDiscPolicy:rn managed
        object property"
    ::= { cfprComputeBladeDiscPolicyEntry 3 }

cfprComputeBladeDiscPolicyAction OBJECT-TYPE
    SYNTAX       SnmpAdminString
    MAX-ACCESS   read-only
    STATUS       current
    DESCRIPTION
        "Cisco Firepower compute:BladeDiscPolicy:action
        managed object property"
    ::= { cfprComputeBladeDiscPolicyEntry 4 }

cfprComputeBladeDiscPolicyDescr OBJECT-TYPE
    SYNTAX       SnmpAdminString
    MAX-ACCESS   read-only
    STATUS       current
    DESCRIPTION
        "Cisco Firepower compute:BladeDiscPolicy:descr
        managed object property"
    ::= { cfprComputeBladeDiscPolicyEntry 5 }

cfprComputeBladeDiscPolicyIntId OBJECT-TYPE
    SYNTAX       SnmpAdminString
    MAX-ACCESS   read-only
    STATUS       current
    DESCRIPTION
        "Cisco Firepower compute:BladeDiscPolicy:intId
        managed object property"
    ::= { cfprComputeBladeDiscPolicyEntry 6 }

cfprComputeBladeDiscPolicyName OBJECT-TYPE
    SYNTAX       SnmpAdminString
    MAX-ACCESS   read-only
    STATUS       current
    DESCRIPTION
        "Cisco Firepower compute:BladeDiscPolicy:name managed
        object property"
    ::= { cfprComputeBladeDiscPolicyEntry 7 }

cfprComputeBladeDiscPolicyPolicyLevel OBJECT-TYPE
    SYNTAX       Gauge32
    MAX-ACCESS   read-only
    STATUS       current
    DESCRIPTION
        "Cisco Firepower compute:BladeDiscPolicy:policyLevel
        managed object property"
    ::= { cfprComputeBladeDiscPolicyEntry 8 }

cfprComputeBladeDiscPolicyPolicyOwner OBJECT-TYPE
    SYNTAX       CfprPolicyPolicyOwner
    MAX-ACCESS   read-only
    STATUS       current
    DESCRIPTION
        "Cisco Firepower compute:BladeDiscPolicy:policyOwner
        managed object property"
    ::= { cfprComputeBladeDiscPolicyEntry 9 }

cfprComputeBladeDiscPolicyQualifier OBJECT-TYPE
    SYNTAX       SnmpAdminString
    MAX-ACCESS   read-only
    STATUS       current
    DESCRIPTION
        "Cisco Firepower compute:BladeDiscPolicy:qualifier
        managed object property"
    ::= { cfprComputeBladeDiscPolicyEntry 10 }

cfprComputeBladeDiscPolicyScrubPolicyName OBJECT-TYPE
    SYNTAX       SnmpAdminString
    MAX-ACCESS   read-only
    STATUS       current
    DESCRIPTION
        "Cisco Firepower compute:BladeDiscPolicy:scrubPolicyName
        managed object property"
    ::= { cfprComputeBladeDiscPolicyEntry 11 }

cfprComputeBladeFsmTable OBJECT-TYPE
    SYNTAX           SEQUENCE OF CfprComputeBladeFsmEntry
    MAX-ACCESS       not-accessible
    STATUS           current
    DESCRIPTION
        "Cisco Firepower compute:BladeFsm managed object table"
    ::= { cfprComputeObjects 4 }

cfprComputeBladeFsmEntry OBJECT-TYPE
    SYNTAX           CfprComputeBladeFsmEntry
    MAX-ACCESS       not-accessible
    STATUS           current
    DESCRIPTION
        "Entry for the cfprComputeBladeFsmTable table."
    INDEX { cfprComputeBladeFsmInstanceId }
    ::= { cfprComputeBladeFsmTable 1 }

CfprComputeBladeFsmEntry ::= SEQUENCE {
    cfprComputeBladeFsmInstanceId                                    CfprManagedObjectId,
    cfprComputeBladeFsmDn                                            CfprManagedObjectDn,
    cfprComputeBladeFsmRn                                            SnmpAdminString,
    cfprComputeBladeFsmCompletionTime                                DateAndTime,
    cfprComputeBladeFsmCurrentFsm                                    CfprComputeBladeFsmCurrentFsm,
    cfprComputeBladeFsmDescrData                                     SnmpAdminString,
    cfprComputeBladeFsmFsmStatus                                     CfprFsmFsmStageStatus,
    cfprComputeBladeFsmProgress                                      Gauge32,
    cfprComputeBladeFsmRmtErrCode                                    Gauge32,
    cfprComputeBladeFsmRmtErrDescr                                   SnmpAdminString,
    cfprComputeBladeFsmRmtRslt                                       CfprConditionRemoteInvRslt
}

cfprComputeBladeFsmInstanceId OBJECT-TYPE
    SYNTAX       CfprManagedObjectId
    MAX-ACCESS   not-accessible
    STATUS       current
    DESCRIPTION
        "Instance identifier of the managed object."
    ::= { cfprComputeBladeFsmEntry 1 }

cfprComputeBladeFsmDn OBJECT-TYPE
    SYNTAX       CfprManagedObjectDn
    MAX-ACCESS   read-only
    STATUS       current
    DESCRIPTION
        "Cisco Firepower compute:BladeFsm:dn managed object property"
    ::= { cfprComputeBladeFsmEntry 2 }

cfprComputeBladeFsmRn OBJECT-TYPE
    SYNTAX       SnmpAdminString
    MAX-ACCESS   read-only
    STATUS       current
    DESCRIPTION
        "Cisco Firepower compute:BladeFsm:rn managed object property"
    ::= { cfprComputeBladeFsmEntry 3 }

cfprComputeBladeFsmCompletionTime OBJECT-TYPE
    SYNTAX       DateAndTime
    MAX-ACCESS   read-only
    STATUS       current
    DESCRIPTION
        "Cisco Firepower compute:BladeFsm:completionTime
        managed object property"
    ::= { cfprComputeBladeFsmEntry 4 }

cfprComputeBladeFsmCurrentFsm OBJECT-TYPE
    SYNTAX       CfprComputeBladeFsmCurrentFsm
    MAX-ACCESS   read-only
    STATUS       current
    DESCRIPTION
        "Cisco Firepower compute:BladeFsm:currentFsm managed
        object property"
    ::= { cfprComputeBladeFsmEntry 5 }

cfprComputeBladeFsmDescrData OBJECT-TYPE
    SYNTAX       SnmpAdminString
    MAX-ACCESS   read-only
    STATUS       current
    DESCRIPTION
        "Cisco Firepower compute:BladeFsm:descr managed object property"
    ::= { cfprComputeBladeFsmEntry 6 }

cfprComputeBladeFsmFsmStatus OBJECT-TYPE
    SYNTAX       CfprFsmFsmStageStatus
    MAX-ACCESS   read-only
    STATUS       current
    DESCRIPTION
        "Cisco Firepower compute:BladeFsm:fsmStatus managed
        object property"
    ::= { cfprComputeBladeFsmEntry 7 }

cfprComputeBladeFsmProgress OBJECT-TYPE
    SYNTAX       Gauge32
    MAX-ACCESS   read-only
    STATUS       current
    DESCRIPTION
        "Cisco Firepower compute:BladeFsm:progress managed
        object property"
    ::= { cfprComputeBladeFsmEntry 8 }

cfprComputeBladeFsmRmtErrCode OBJECT-TYPE
    SYNTAX       Gauge32
    MAX-ACCESS   read-only
    STATUS       current
    DESCRIPTION
        "Cisco Firepower compute:BladeFsm:rmtErrCode managed
        object property"
    ::= { cfprComputeBladeFsmEntry 9 }

cfprComputeBladeFsmRmtErrDescr OBJECT-TYPE
    SYNTAX       SnmpAdminString
    MAX-ACCESS   read-only
    STATUS       current
    DESCRIPTION
        "Cisco Firepower compute:BladeFsm:rmtErrDescr managed
        object property"
    ::= { cfprComputeBladeFsmEntry 10 }

cfprComputeBladeFsmRmtRslt OBJECT-TYPE
    SYNTAX       CfprConditionRemoteInvRslt
    MAX-ACCESS   read-only
    STATUS       current
    DESCRIPTION
        "Cisco Firepower compute:BladeFsm:rmtRslt managed object property"
    ::= { cfprComputeBladeFsmEntry 11 }

cfprComputeBladeFsmStageTable OBJECT-TYPE
    SYNTAX           SEQUENCE OF CfprComputeBladeFsmStageEntry
    MAX-ACCESS       not-accessible
    STATUS           current
    DESCRIPTION
        "Cisco Firepower compute:BladeFsmStage managed object table"
    ::= { cfprComputeObjects 5 }

cfprComputeBladeFsmStageEntry OBJECT-TYPE
    SYNTAX           CfprComputeBladeFsmStageEntry
    MAX-ACCESS       not-accessible
    STATUS           current
    DESCRIPTION
        "Entry for the cfprComputeBladeFsmStageTable table."
    INDEX { cfprComputeBladeFsmStageInstanceId }
    ::= { cfprComputeBladeFsmStageTable 1 }

CfprComputeBladeFsmStageEntry ::= SEQUENCE {
    cfprComputeBladeFsmStageInstanceId                               CfprManagedObjectId,
    cfprComputeBladeFsmStageDn                                       CfprManagedObjectDn,
    cfprComputeBladeFsmStageRn                                       SnmpAdminString,
    cfprComputeBladeFsmStageDescrData                                SnmpAdminString,
    cfprComputeBladeFsmStageLastUpdateTime                           DateAndTime,
    cfprComputeBladeFsmStageName                                     CfprComputeBladeFsmStageName,
    cfprComputeBladeFsmStageOrder                                    Gauge32,
    cfprComputeBladeFsmStageRetry                                    Gauge32,
    cfprComputeBladeFsmStageStageStatus                              CfprFsmFsmStageStatus
}

cfprComputeBladeFsmStageInstanceId OBJECT-TYPE
    SYNTAX       CfprManagedObjectId
    MAX-ACCESS   not-accessible
    STATUS       current
    DESCRIPTION
        "Instance identifier of the managed object."
    ::= { cfprComputeBladeFsmStageEntry 1 }

cfprComputeBladeFsmStageDn OBJECT-TYPE
    SYNTAX       CfprManagedObjectDn
    MAX-ACCESS   read-only
    STATUS       current
    DESCRIPTION
        "Cisco Firepower compute:BladeFsmStage:dn managed object property"
    ::= { cfprComputeBladeFsmStageEntry 2 }

cfprComputeBladeFsmStageRn OBJECT-TYPE
    SYNTAX       SnmpAdminString
    MAX-ACCESS   read-only
    STATUS       current
    DESCRIPTION
        "Cisco Firepower compute:BladeFsmStage:rn managed object property"
    ::= { cfprComputeBladeFsmStageEntry 3 }

cfprComputeBladeFsmStageDescrData OBJECT-TYPE
    SYNTAX       SnmpAdminString
    MAX-ACCESS   read-only
    STATUS       current
    DESCRIPTION
        "Cisco Firepower compute:BladeFsmStage:descr managed
        object property"
    ::= { cfprComputeBladeFsmStageEntry 4 }

cfprComputeBladeFsmStageLastUpdateTime OBJECT-TYPE
    SYNTAX       DateAndTime
    MAX-ACCESS   read-only
    STATUS       current
    DESCRIPTION
        "Cisco Firepower compute:BladeFsmStage:lastUpdateTime
        managed object property"
    ::= { cfprComputeBladeFsmStageEntry 5 }

cfprComputeBladeFsmStageName OBJECT-TYPE
    SYNTAX       CfprComputeBladeFsmStageName
    MAX-ACCESS   read-only
    STATUS       current
    DESCRIPTION
        "Cisco Firepower compute:BladeFsmStage:name managed
        object property"
    ::= { cfprComputeBladeFsmStageEntry 6 }

cfprComputeBladeFsmStageOrder OBJECT-TYPE
    SYNTAX       Gauge32
    MAX-ACCESS   read-only
    STATUS       current
    DESCRIPTION
        "Cisco Firepower compute:BladeFsmStage:order managed
        object property"
    ::= { cfprComputeBladeFsmStageEntry 7 }

cfprComputeBladeFsmStageRetry OBJECT-TYPE
    SYNTAX       Gauge32
    MAX-ACCESS   read-only
    STATUS       current
    DESCRIPTION
        "Cisco Firepower compute:BladeFsmStage:retry managed
        object property"
    ::= { cfprComputeBladeFsmStageEntry 8 }

cfprComputeBladeFsmStageStageStatus OBJECT-TYPE
    SYNTAX       CfprFsmFsmStageStatus
    MAX-ACCESS   read-only
    STATUS       current
    DESCRIPTION
        "Cisco Firepower compute:BladeFsmStage:stageStatus
        managed object property"
    ::= { cfprComputeBladeFsmStageEntry 9 }

cfprComputeBladeFsmTaskTable OBJECT-TYPE
    SYNTAX           SEQUENCE OF CfprComputeBladeFsmTaskEntry
    MAX-ACCESS       not-accessible
    STATUS           current
    DESCRIPTION
        "Cisco Firepower compute:BladeFsmTask managed object table"
    ::= { cfprComputeObjects 6 }

cfprComputeBladeFsmTaskEntry OBJECT-TYPE
    SYNTAX           CfprComputeBladeFsmTaskEntry
    MAX-ACCESS       not-accessible
    STATUS           current
    DESCRIPTION
        "Entry for the cfprComputeBladeFsmTaskTable table."
    INDEX { cfprComputeBladeFsmTaskInstanceId }
    ::= { cfprComputeBladeFsmTaskTable 1 }

CfprComputeBladeFsmTaskEntry ::= SEQUENCE {
    cfprComputeBladeFsmTaskInstanceId                                CfprManagedObjectId,
    cfprComputeBladeFsmTaskDn                                        CfprManagedObjectDn,
    cfprComputeBladeFsmTaskRn                                        SnmpAdminString,
    cfprComputeBladeFsmTaskCompletion                                CfprFsmCompletion,
    cfprComputeBladeFsmTaskFlags                                     CfprComputeBladeFsmTaskFlags,
    cfprComputeBladeFsmTaskItem                                      CfprComputeBladeFsmTaskItem,
    cfprComputeBladeFsmTaskSeqId                                     Gauge32
}

cfprComputeBladeFsmTaskInstanceId OBJECT-TYPE
    SYNTAX       CfprManagedObjectId
    MAX-ACCESS   not-accessible
    STATUS       current
    DESCRIPTION
        "Instance identifier of the managed object."
    ::= { cfprComputeBladeFsmTaskEntry 1 }

cfprComputeBladeFsmTaskDn OBJECT-TYPE
    SYNTAX       CfprManagedObjectDn
    MAX-ACCESS   read-only
    STATUS       current
    DESCRIPTION
        "Cisco Firepower compute:BladeFsmTask:dn managed object property"
    ::= { cfprComputeBladeFsmTaskEntry 2 }

cfprComputeBladeFsmTaskRn OBJECT-TYPE
    SYNTAX       SnmpAdminString
    MAX-ACCESS   read-only
    STATUS       current
    DESCRIPTION
        "Cisco Firepower compute:BladeFsmTask:rn managed object property"
    ::= { cfprComputeBladeFsmTaskEntry 3 }

cfprComputeBladeFsmTaskCompletion OBJECT-TYPE
    SYNTAX       CfprFsmCompletion
    MAX-ACCESS   read-only
    STATUS       current
    DESCRIPTION
        "Cisco Firepower compute:BladeFsmTask:completion
        managed object property"
    ::= { cfprComputeBladeFsmTaskEntry 4 }

cfprComputeBladeFsmTaskFlags OBJECT-TYPE
    SYNTAX       CfprComputeBladeFsmTaskFlags
    MAX-ACCESS   read-only
    STATUS       current
    DESCRIPTION
        "Cisco Firepower compute:BladeFsmTask:flags managed
        object property"
    ::= { cfprComputeBladeFsmTaskEntry 5 }

cfprComputeBladeFsmTaskItem OBJECT-TYPE
    SYNTAX       CfprComputeBladeFsmTaskItem
    MAX-ACCESS   read-only
    STATUS       current
    DESCRIPTION
        "Cisco Firepower compute:BladeFsmTask:item managed
        object property"
    ::= { cfprComputeBladeFsmTaskEntry 6 }

cfprComputeBladeFsmTaskSeqId OBJECT-TYPE
    SYNTAX       Gauge32
    MAX-ACCESS   read-only
    STATUS       current
    DESCRIPTION
        "Cisco Firepower compute:BladeFsmTask:seqId managed
        object property"
    ::= { cfprComputeBladeFsmTaskEntry 7 }

cfprComputeBladeInheritPolicyTable OBJECT-TYPE
    SYNTAX           SEQUENCE OF CfprComputeBladeInheritPolicyEntry
    MAX-ACCESS       not-accessible
    STATUS           current
    DESCRIPTION
        "Cisco Firepower compute:BladeInheritPolicy managed object table"
    ::= { cfprComputeObjects 7 }

cfprComputeBladeInheritPolicyEntry OBJECT-TYPE
    SYNTAX           CfprComputeBladeInheritPolicyEntry
    MAX-ACCESS       not-accessible
    STATUS           current
    DESCRIPTION
        "Entry for the cfprComputeBladeInheritPolicyTable table."
    INDEX { cfprComputeBladeInheritPolicyInstanceId }
    ::= { cfprComputeBladeInheritPolicyTable 1 }

CfprComputeBladeInheritPolicyEntry ::= SEQUENCE {
    cfprComputeBladeInheritPolicyInstanceId                          CfprManagedObjectId,
    cfprComputeBladeInheritPolicyDn                                  CfprManagedObjectDn,
    cfprComputeBladeInheritPolicyRn                                  SnmpAdminString,
    cfprComputeBladeInheritPolicyDescr                               SnmpAdminString,
    cfprComputeBladeInheritPolicyDstDn                               SnmpAdminString,
    cfprComputeBladeInheritPolicyIntId                               SnmpAdminString,
    cfprComputeBladeInheritPolicyName                                SnmpAdminString,
    cfprComputeBladeInheritPolicyPolicyLevel                         Gauge32,
    cfprComputeBladeInheritPolicyPolicyOwner                         CfprPolicyPolicyOwner,
    cfprComputeBladeInheritPolicyQualifier                           SnmpAdminString
}

cfprComputeBladeInheritPolicyInstanceId OBJECT-TYPE
    SYNTAX       CfprManagedObjectId
    MAX-ACCESS   not-accessible
    STATUS       current
    DESCRIPTION
        "Instance identifier of the managed object."
    ::= { cfprComputeBladeInheritPolicyEntry 1 }

cfprComputeBladeInheritPolicyDn OBJECT-TYPE
    SYNTAX       CfprManagedObjectDn
    MAX-ACCESS   read-only
    STATUS       current
    DESCRIPTION
        "Cisco Firepower compute:BladeInheritPolicy:dn
        managed object property"
    ::= { cfprComputeBladeInheritPolicyEntry 2 }

cfprComputeBladeInheritPolicyRn OBJECT-TYPE
    SYNTAX       SnmpAdminString
    MAX-ACCESS   read-only
    STATUS       current
    DESCRIPTION
        "Cisco Firepower compute:BladeInheritPolicy:rn
        managed object property"
    ::= { cfprComputeBladeInheritPolicyEntry 3 }

cfprComputeBladeInheritPolicyDescr OBJECT-TYPE
    SYNTAX       SnmpAdminString
    MAX-ACCESS   read-only
    STATUS       current
    DESCRIPTION
        "Cisco Firepower compute:BladeInheritPolicy:descr
        managed object property"
    ::= { cfprComputeBladeInheritPolicyEntry 4 }

cfprComputeBladeInheritPolicyDstDn OBJECT-TYPE
    SYNTAX       SnmpAdminString
    MAX-ACCESS   read-only
    STATUS       current
    DESCRIPTION
        "Cisco Firepower compute:BladeInheritPolicy:dstDn
        managed object property"
    ::= { cfprComputeBladeInheritPolicyEntry 5 }

cfprComputeBladeInheritPolicyIntId OBJECT-TYPE
    SYNTAX       SnmpAdminString
    MAX-ACCESS   read-only
    STATUS       current
    DESCRIPTION
        "Cisco Firepower compute:BladeInheritPolicy:intId
        managed object property"
    ::= { cfprComputeBladeInheritPolicyEntry 6 }

cfprComputeBladeInheritPolicyName OBJECT-TYPE
    SYNTAX       SnmpAdminString
    MAX-ACCESS   read-only
    STATUS       current
    DESCRIPTION
        "Cisco Firepower compute:BladeInheritPolicy:name
        managed object property"
    ::= { cfprComputeBladeInheritPolicyEntry 7 }

cfprComputeBladeInheritPolicyPolicyLevel OBJECT-TYPE
    SYNTAX       Gauge32
    MAX-ACCESS   read-only
    STATUS       current
    DESCRIPTION
        "Cisco Firepower compute:BladeInheritPolicy:policyLevel
        managed object property"
    ::= { cfprComputeBladeInheritPolicyEntry 8 }

cfprComputeBladeInheritPolicyPolicyOwner OBJECT-TYPE
    SYNTAX       CfprPolicyPolicyOwner
    MAX-ACCESS   read-only
    STATUS       current
    DESCRIPTION
        "Cisco Firepower compute:BladeInheritPolicy:policyOwner
        managed object property"
    ::= { cfprComputeBladeInheritPolicyEntry 9 }

cfprComputeBladeInheritPolicyQualifier OBJECT-TYPE
    SYNTAX       SnmpAdminString
    MAX-ACCESS   read-only
    STATUS       current
    DESCRIPTION
        "Cisco Firepower compute:BladeInheritPolicy:qualifier
        managed object property"
    ::= { cfprComputeBladeInheritPolicyEntry 10 }

cfprComputeBoardTable OBJECT-TYPE
    SYNTAX           SEQUENCE OF CfprComputeBoardEntry
    MAX-ACCESS       not-accessible
    STATUS           current
    DESCRIPTION
        "Cisco Firepower compute:Board managed object table"
    ::= { cfprComputeObjects 8 }

cfprComputeBoardEntry OBJECT-TYPE
    SYNTAX           CfprComputeBoardEntry
    MAX-ACCESS       not-accessible
    STATUS           current
    DESCRIPTION
        "Entry for the cfprComputeBoardTable table."
    INDEX { cfprComputeBoardInstanceId }
    ::= { cfprComputeBoardTable 1 }

CfprComputeBoardEntry ::= SEQUENCE {
    cfprComputeBoardInstanceId                                       CfprManagedObjectId,
    cfprComputeBoardDn                                               CfprManagedObjectDn,
    cfprComputeBoardRn                                               SnmpAdminString,
    cfprComputeBoardCmosVoltage                                      CfprEquipmentSensorThresholdStatus,
    cfprComputeBoardCpuType                                          CfprEquipmentCpuType,
    cfprComputeBoardFaultQualifier                                   SnmpAdminString,
    cfprComputeBoardId                                               Gauge32,
    cfprComputeBoardLocationDn                                       SnmpAdminString,
    cfprComputeBoardModel                                            SnmpAdminString,
    cfprComputeBoardOperPower                                        CfprEquipmentPowerState,
    cfprComputeBoardOperQualifierReason                              SnmpAdminString,
    cfprComputeBoardOperState                                        CfprEquipmentOperability,
    cfprComputeBoardOperability                                      CfprEquipmentOperability,
    cfprComputeBoardPerf                                             CfprEquipmentSensorThresholdStatus,
    cfprComputeBoardPower                                            CfprComputeABoardPower,
    cfprComputeBoardPowerUsage                                       CfprEquipmentSensorThresholdStatus,
    cfprComputeBoardPresence                                         CfprEquipmentPresence,
    cfprComputeBoardRevision                                         SnmpAdminString,
    cfprComputeBoardSerial                                           SnmpAdminString,
    cfprComputeBoardThermal                                          CfprEquipmentSensorThresholdStatus,
    cfprComputeBoardVendor                                           SnmpAdminString,
    cfprComputeBoardVoltage                                          CfprEquipmentSensorThresholdStatus
}

cfprComputeBoardInstanceId OBJECT-TYPE
    SYNTAX       CfprManagedObjectId
    MAX-ACCESS   not-accessible
    STATUS       current
    DESCRIPTION
        "Instance identifier of the managed object."
    ::= { cfprComputeBoardEntry 1 }

cfprComputeBoardDn OBJECT-TYPE
    SYNTAX       CfprManagedObjectDn
    MAX-ACCESS   read-only
    STATUS       current
    DESCRIPTION
        "Cisco Firepower compute:Board:dn managed object property"
    ::= { cfprComputeBoardEntry 2 }

cfprComputeBoardRn OBJECT-TYPE
    SYNTAX       SnmpAdminString
    MAX-ACCESS   read-only
    STATUS       current
    DESCRIPTION
        "Cisco Firepower compute:Board:rn managed object property"
    ::= { cfprComputeBoardEntry 3 }

cfprComputeBoardCmosVoltage OBJECT-TYPE
    SYNTAX       CfprEquipmentSensorThresholdStatus
    MAX-ACCESS   read-only
    STATUS       current
    DESCRIPTION
        "Cisco Firepower compute:Board:cmosVoltage managed
        object property"
    ::= { cfprComputeBoardEntry 4 }

cfprComputeBoardCpuType OBJECT-TYPE
    SYNTAX       CfprEquipmentCpuType
    MAX-ACCESS   read-only
    STATUS       current
    DESCRIPTION
        "Cisco Firepower compute:Board:cpuType managed object property"
    ::= { cfprComputeBoardEntry 5 }

cfprComputeBoardFaultQualifier OBJECT-TYPE
    SYNTAX       SnmpAdminString
    MAX-ACCESS   read-only
    STATUS       current
    DESCRIPTION
        "Cisco Firepower compute:Board:faultQualifier managed
        object property"
    ::= { cfprComputeBoardEntry 6 }

cfprComputeBoardId OBJECT-TYPE
    SYNTAX       Gauge32
    MAX-ACCESS   read-only
    STATUS       current
    DESCRIPTION
        "Cisco Firepower compute:Board:id managed object property"
    ::= { cfprComputeBoardEntry 7 }

cfprComputeBoardLocationDn OBJECT-TYPE
    SYNTAX       SnmpAdminString
    MAX-ACCESS   read-only
    STATUS       current
    DESCRIPTION
        "Cisco Firepower compute:Board:locationDn managed object property"
    ::= { cfprComputeBoardEntry 8 }

cfprComputeBoardModel OBJECT-TYPE
    SYNTAX       SnmpAdminString
    MAX-ACCESS   read-only
    STATUS       current
    DESCRIPTION
        "Cisco Firepower compute:Board:model managed object property"
    ::= { cfprComputeBoardEntry 9 }

cfprComputeBoardOperPower OBJECT-TYPE
    SYNTAX       CfprEquipmentPowerState
    MAX-ACCESS   read-only
    STATUS       current
    DESCRIPTION
        "Cisco Firepower compute:Board:operPower managed object property"
    ::= { cfprComputeBoardEntry 10 }

cfprComputeBoardOperQualifierReason OBJECT-TYPE
    SYNTAX       SnmpAdminString
    MAX-ACCESS   read-only
    STATUS       current
    DESCRIPTION
        "Cisco Firepower compute:Board:operQualifierReason
        managed object property"
    ::= { cfprComputeBoardEntry 11 }

cfprComputeBoardOperState OBJECT-TYPE
    SYNTAX       CfprEquipmentOperability
    MAX-ACCESS   read-only
    STATUS       current
    DESCRIPTION
        "Cisco Firepower compute:Board:operState managed object property"
    ::= { cfprComputeBoardEntry 12 }

cfprComputeBoardOperability OBJECT-TYPE
    SYNTAX       CfprEquipmentOperability
    MAX-ACCESS   read-only
    STATUS       current
    DESCRIPTION
        "Cisco Firepower compute:Board:operability managed
        object property"
    ::= { cfprComputeBoardEntry 13 }

cfprComputeBoardPerf OBJECT-TYPE
    SYNTAX       CfprEquipmentSensorThresholdStatus
    MAX-ACCESS   read-only
    STATUS       current
    DESCRIPTION
        "Cisco Firepower compute:Board:perf managed object property"
    ::= { cfprComputeBoardEntry 14 }

cfprComputeBoardPower OBJECT-TYPE
    SYNTAX       CfprComputeABoardPower
    MAX-ACCESS   read-only
    STATUS       current
    DESCRIPTION
        "Cisco Firepower compute:Board:power managed object property"
    ::= { cfprComputeBoardEntry 15 }

cfprComputeBoardPowerUsage OBJECT-TYPE
    SYNTAX       CfprEquipmentSensorThresholdStatus
    MAX-ACCESS   read-only
    STATUS       current
    DESCRIPTION
        "Cisco Firepower compute:Board:powerUsage managed object property"
    ::= { cfprComputeBoardEntry 16 }

cfprComputeBoardPresence OBJECT-TYPE
    SYNTAX       CfprEquipmentPresence
    MAX-ACCESS   read-only
    STATUS       current
    DESCRIPTION
        "Cisco Firepower compute:Board:presence managed object property"
    ::= { cfprComputeBoardEntry 17 }

cfprComputeBoardRevision OBJECT-TYPE
    SYNTAX       SnmpAdminString
    MAX-ACCESS   read-only
    STATUS       current
    DESCRIPTION
        "Cisco Firepower compute:Board:revision managed object property"
    ::= { cfprComputeBoardEntry 18 }

cfprComputeBoardSerial OBJECT-TYPE
    SYNTAX       SnmpAdminString
    MAX-ACCESS   read-only
    STATUS       current
    DESCRIPTION
        "Cisco Firepower compute:Board:serial managed object property"
    ::= { cfprComputeBoardEntry 19 }

cfprComputeBoardThermal OBJECT-TYPE
    SYNTAX       CfprEquipmentSensorThresholdStatus
    MAX-ACCESS   read-only
    STATUS       current
    DESCRIPTION
        "Cisco Firepower compute:Board:thermal managed object property"
    ::= { cfprComputeBoardEntry 20 }

cfprComputeBoardVendor OBJECT-TYPE
    SYNTAX       SnmpAdminString
    MAX-ACCESS   read-only
    STATUS       current
    DESCRIPTION
        "Cisco Firepower compute:Board:vendor managed object property"
    ::= { cfprComputeBoardEntry 21 }

cfprComputeBoardVoltage OBJECT-TYPE
    SYNTAX       CfprEquipmentSensorThresholdStatus
    MAX-ACCESS   read-only
    STATUS       current
    DESCRIPTION
        "Cisco Firepower compute:Board:voltage managed object property"
    ::= { cfprComputeBoardEntry 22 }

cfprComputeBoardConnectorTable OBJECT-TYPE
    SYNTAX           SEQUENCE OF CfprComputeBoardConnectorEntry
    MAX-ACCESS       not-accessible
    STATUS           current
    DESCRIPTION
        "Cisco Firepower compute:BoardConnector managed object table"
    ::= { cfprComputeObjects 9 }

cfprComputeBoardConnectorEntry OBJECT-TYPE
    SYNTAX           CfprComputeBoardConnectorEntry
    MAX-ACCESS       not-accessible
    STATUS           current
    DESCRIPTION
        "Entry for the cfprComputeBoardConnectorTable table."
    INDEX { cfprComputeBoardConnectorInstanceId }
    ::= { cfprComputeBoardConnectorTable 1 }

CfprComputeBoardConnectorEntry ::= SEQUENCE {
    cfprComputeBoardConnectorInstanceId                              CfprManagedObjectId,
    cfprComputeBoardConnectorDn                                      CfprManagedObjectDn,
    cfprComputeBoardConnectorRn                                      SnmpAdminString,
    cfprComputeBoardConnectorBoardConnectorType                      CfprEquipmentBoardConnectorType,
    cfprComputeBoardConnectorMasterSlotId                            Gauge32,
    cfprComputeBoardConnectorSlaveSlotId                             Gauge32
}

cfprComputeBoardConnectorInstanceId OBJECT-TYPE
    SYNTAX       CfprManagedObjectId
    MAX-ACCESS   not-accessible
    STATUS       current
    DESCRIPTION
        "Instance identifier of the managed object."
    ::= { cfprComputeBoardConnectorEntry 1 }

cfprComputeBoardConnectorDn OBJECT-TYPE
    SYNTAX       CfprManagedObjectDn
    MAX-ACCESS   read-only
    STATUS       current
    DESCRIPTION
        "Cisco Firepower compute:BoardConnector:dn managed
        object property"
    ::= { cfprComputeBoardConnectorEntry 2 }

cfprComputeBoardConnectorRn OBJECT-TYPE
    SYNTAX       SnmpAdminString
    MAX-ACCESS   read-only
    STATUS       current
    DESCRIPTION
        "Cisco Firepower compute:BoardConnector:rn managed
        object property"
    ::= { cfprComputeBoardConnectorEntry 3 }

cfprComputeBoardConnectorBoardConnectorType OBJECT-TYPE
    SYNTAX       CfprEquipmentBoardConnectorType
    MAX-ACCESS   read-only
    STATUS       current
    DESCRIPTION
        "Cisco Firepower compute:BoardConnector:boardConnectorType
        managed object property"
    ::= { cfprComputeBoardConnectorEntry 4 }

cfprComputeBoardConnectorMasterSlotId OBJECT-TYPE
    SYNTAX       Gauge32
    MAX-ACCESS   read-only
    STATUS       current
    DESCRIPTION
        "Cisco Firepower compute:BoardConnector:masterSlotId
        managed object property"
    ::= { cfprComputeBoardConnectorEntry 5 }

cfprComputeBoardConnectorSlaveSlotId OBJECT-TYPE
    SYNTAX       Gauge32
    MAX-ACCESS   read-only
    STATUS       current
    DESCRIPTION
        "Cisco Firepower compute:BoardConnector:slaveSlotId
        managed object property"
    ::= { cfprComputeBoardConnectorEntry 6 }

cfprComputeBoardControllerTable OBJECT-TYPE
    SYNTAX           SEQUENCE OF CfprComputeBoardControllerEntry
    MAX-ACCESS       not-accessible
    STATUS           current
    DESCRIPTION
        "Cisco Firepower compute:BoardController managed object table"
    ::= { cfprComputeObjects 10 }

cfprComputeBoardControllerEntry OBJECT-TYPE
    SYNTAX           CfprComputeBoardControllerEntry
    MAX-ACCESS       not-accessible
    STATUS           current
    DESCRIPTION
        "Entry for the cfprComputeBoardControllerTable table."
    INDEX { cfprComputeBoardControllerInstanceId }
    ::= { cfprComputeBoardControllerTable 1 }

CfprComputeBoardControllerEntry ::= SEQUENCE {
    cfprComputeBoardControllerInstanceId                             CfprManagedObjectId,
    cfprComputeBoardControllerDn                                     CfprManagedObjectDn,
    cfprComputeBoardControllerRn                                     SnmpAdminString,
    cfprComputeBoardControllerId                                     Gauge32,
    cfprComputeBoardControllerLocationDn                             SnmpAdminString,
    cfprComputeBoardControllerModel                                  SnmpAdminString,
    cfprComputeBoardControllerOperQualifierReason                    SnmpAdminString,
    cfprComputeBoardControllerOperState                              CfprEquipmentOperability,
    cfprComputeBoardControllerOperability                            CfprEquipmentOperability,
    cfprComputeBoardControllerPerf                                   CfprEquipmentSensorThresholdStatus,
    cfprComputeBoardControllerPower                                  CfprEquipmentPowerState,
    cfprComputeBoardControllerPresence                               CfprEquipmentPresence,
    cfprComputeBoardControllerRevision                               SnmpAdminString,
    cfprComputeBoardControllerSerial                                 SnmpAdminString,
    cfprComputeBoardControllerThermal                                CfprEquipmentSensorThresholdStatus,
    cfprComputeBoardControllerVendor                                 SnmpAdminString,
    cfprComputeBoardControllerVoltage                                CfprEquipmentSensorThresholdStatus
}

cfprComputeBoardControllerInstanceId OBJECT-TYPE
    SYNTAX       CfprManagedObjectId
    MAX-ACCESS   not-accessible
    STATUS       current
    DESCRIPTION
        "Instance identifier of the managed object."
    ::= { cfprComputeBoardControllerEntry 1 }

cfprComputeBoardControllerDn OBJECT-TYPE
    SYNTAX       CfprManagedObjectDn
    MAX-ACCESS   read-only
    STATUS       current
    DESCRIPTION
        "Cisco Firepower compute:BoardController:dn managed
        object property"
    ::= { cfprComputeBoardControllerEntry 2 }

cfprComputeBoardControllerRn OBJECT-TYPE
    SYNTAX       SnmpAdminString
    MAX-ACCESS   read-only
    STATUS       current
    DESCRIPTION
        "Cisco Firepower compute:BoardController:rn managed
        object property"
    ::= { cfprComputeBoardControllerEntry 3 }

cfprComputeBoardControllerId OBJECT-TYPE
    SYNTAX       Gauge32
    MAX-ACCESS   read-only
    STATUS       current
    DESCRIPTION
        "Cisco Firepower compute:BoardController:id managed
        object property"
    ::= { cfprComputeBoardControllerEntry 4 }

cfprComputeBoardControllerLocationDn OBJECT-TYPE
    SYNTAX       SnmpAdminString
    MAX-ACCESS   read-only
    STATUS       current
    DESCRIPTION
        "Cisco Firepower compute:BoardController:locationDn
        managed object property"
    ::= { cfprComputeBoardControllerEntry 5 }

cfprComputeBoardControllerModel OBJECT-TYPE
    SYNTAX       SnmpAdminString
    MAX-ACCESS   read-only
    STATUS       current
    DESCRIPTION
        "Cisco Firepower compute:BoardController:model
        managed object property"
    ::= { cfprComputeBoardControllerEntry 6 }

cfprComputeBoardControllerOperQualifierReason OBJECT-TYPE
    SYNTAX       SnmpAdminString
    MAX-ACCESS   read-only
    STATUS       current
    DESCRIPTION
        "Cisco Firepower compute:BoardController:operQualifierReason
        managed object property"
    ::= { cfprComputeBoardControllerEntry 7 }

cfprComputeBoardControllerOperState OBJECT-TYPE
    SYNTAX       CfprEquipmentOperability
    MAX-ACCESS   read-only
    STATUS       current
    DESCRIPTION
        "Cisco Firepower compute:BoardController:operState
        managed object property"
    ::= { cfprComputeBoardControllerEntry 8 }

cfprComputeBoardControllerOperability OBJECT-TYPE
    SYNTAX       CfprEquipmentOperability
    MAX-ACCESS   read-only
    STATUS       current
    DESCRIPTION
        "Cisco Firepower compute:BoardController:operability
        managed object property"
    ::= { cfprComputeBoardControllerEntry 9 }

cfprComputeBoardControllerPerf OBJECT-TYPE
    SYNTAX       CfprEquipmentSensorThresholdStatus
    MAX-ACCESS   read-only
    STATUS       current
    DESCRIPTION
        "Cisco Firepower compute:BoardController:perf managed
        object property"
    ::= { cfprComputeBoardControllerEntry 10 }

cfprComputeBoardControllerPower OBJECT-TYPE
    SYNTAX       CfprEquipmentPowerState
    MAX-ACCESS   read-only
    STATUS       current
    DESCRIPTION
        "Cisco Firepower compute:BoardController:power
        managed object property"
    ::= { cfprComputeBoardControllerEntry 11 }

cfprComputeBoardControllerPresence OBJECT-TYPE
    SYNTAX       CfprEquipmentPresence
    MAX-ACCESS   read-only
    STATUS       current
    DESCRIPTION
        "Cisco Firepower compute:BoardController:presence
        managed object property"
    ::= { cfprComputeBoardControllerEntry 12 }

cfprComputeBoardControllerRevision OBJECT-TYPE
    SYNTAX       SnmpAdminString
    MAX-ACCESS   read-only
    STATUS       current
    DESCRIPTION
        "Cisco Firepower compute:BoardController:revision
        managed object property"
    ::= { cfprComputeBoardControllerEntry 13 }

cfprComputeBoardControllerSerial OBJECT-TYPE
    SYNTAX       SnmpAdminString
    MAX-ACCESS   read-only
    STATUS       current
    DESCRIPTION
        "Cisco Firepower compute:BoardController:serial
        managed object property"
    ::= { cfprComputeBoardControllerEntry 14 }

cfprComputeBoardControllerThermal OBJECT-TYPE
    SYNTAX       CfprEquipmentSensorThresholdStatus
    MAX-ACCESS   read-only
    STATUS       current
    DESCRIPTION
        "Cisco Firepower compute:BoardController:thermal
        managed object property"
    ::= { cfprComputeBoardControllerEntry 15 }

cfprComputeBoardControllerVendor OBJECT-TYPE
    SYNTAX       SnmpAdminString
    MAX-ACCESS   read-only
    STATUS       current
    DESCRIPTION
        "Cisco Firepower compute:BoardController:vendor
        managed object property"
    ::= { cfprComputeBoardControllerEntry 16 }

cfprComputeBoardControllerVoltage OBJECT-TYPE
    SYNTAX       CfprEquipmentSensorThresholdStatus
    MAX-ACCESS   read-only
    STATUS       current
    DESCRIPTION
        "Cisco Firepower compute:BoardController:voltage
        managed object property"
    ::= { cfprComputeBoardControllerEntry 17 }

cfprComputeChassisConnPolicyTable OBJECT-TYPE
    SYNTAX           SEQUENCE OF CfprComputeChassisConnPolicyEntry
    MAX-ACCESS       not-accessible
    STATUS           current
    DESCRIPTION
        "Cisco Firepower compute:ChassisConnPolicy managed object table"
    ::= { cfprComputeObjects 11 }

cfprComputeChassisConnPolicyEntry OBJECT-TYPE
    SYNTAX           CfprComputeChassisConnPolicyEntry
    MAX-ACCESS       not-accessible
    STATUS           current
    DESCRIPTION
        "Entry for the cfprComputeChassisConnPolicyTable table."
    INDEX { cfprComputeChassisConnPolicyInstanceId }
    ::= { cfprComputeChassisConnPolicyTable 1 }

CfprComputeChassisConnPolicyEntry ::= SEQUENCE {
    cfprComputeChassisConnPolicyInstanceId                           CfprManagedObjectId,
    cfprComputeChassisConnPolicyDn                                   CfprManagedObjectDn,
    cfprComputeChassisConnPolicyRn                                   SnmpAdminString,
    cfprComputeChassisConnPolicyAdminState                           CfprComputeAdminLinkAggregation,
    cfprComputeChassisConnPolicyChassisId                            CfprComputeChassisConnPolicyChassisId,
    cfprComputeChassisConnPolicyDescr                                SnmpAdminString,
    cfprComputeChassisConnPolicyIntId                                SnmpAdminString,
    cfprComputeChassisConnPolicyName                                 SnmpAdminString,
    cfprComputeChassisConnPolicyPolicyLevel                          Gauge32,
    cfprComputeChassisConnPolicyPolicyOwner                          CfprPolicyPolicyOwner,
    cfprComputeChassisConnPolicyQualifier                            SnmpAdminString,
    cfprComputeChassisConnPolicySwitchId                             CfprNetworkSwitchId
}

cfprComputeChassisConnPolicyInstanceId OBJECT-TYPE
    SYNTAX       CfprManagedObjectId
    MAX-ACCESS   not-accessible
    STATUS       current
    DESCRIPTION
        "Instance identifier of the managed object."
    ::= { cfprComputeChassisConnPolicyEntry 1 }

cfprComputeChassisConnPolicyDn OBJECT-TYPE
    SYNTAX       CfprManagedObjectDn
    MAX-ACCESS   read-only
    STATUS       current
    DESCRIPTION
        "Cisco Firepower compute:ChassisConnPolicy:dn managed
        object property"
    ::= { cfprComputeChassisConnPolicyEntry 2 }

cfprComputeChassisConnPolicyRn OBJECT-TYPE
    SYNTAX       SnmpAdminString
    MAX-ACCESS   read-only
    STATUS       current
    DESCRIPTION
        "Cisco Firepower compute:ChassisConnPolicy:rn managed
        object property"
    ::= { cfprComputeChassisConnPolicyEntry 3 }

cfprComputeChassisConnPolicyAdminState OBJECT-TYPE
    SYNTAX       CfprComputeAdminLinkAggregation
    MAX-ACCESS   read-only
    STATUS       current
    DESCRIPTION
        "Cisco Firepower compute:ChassisConnPolicy:adminState
        managed object property"
    ::= { cfprComputeChassisConnPolicyEntry 4 }

cfprComputeChassisConnPolicyChassisId OBJECT-TYPE
    SYNTAX       CfprComputeChassisConnPolicyChassisId
    MAX-ACCESS   read-only
    STATUS       current
    DESCRIPTION
        "Cisco Firepower compute:ChassisConnPolicy:chassisId
        managed object property"
    ::= { cfprComputeChassisConnPolicyEntry 5 }

cfprComputeChassisConnPolicyDescr OBJECT-TYPE
    SYNTAX       SnmpAdminString
    MAX-ACCESS   read-only
    STATUS       current
    DESCRIPTION
        "Cisco Firepower compute:ChassisConnPolicy:descr
        managed object property"
    ::= { cfprComputeChassisConnPolicyEntry 6 }

cfprComputeChassisConnPolicyIntId OBJECT-TYPE
    SYNTAX       SnmpAdminString
    MAX-ACCESS   read-only
    STATUS       current
    DESCRIPTION
        "Cisco Firepower compute:ChassisConnPolicy:intId
        managed object property"
    ::= { cfprComputeChassisConnPolicyEntry 7 }

cfprComputeChassisConnPolicyName OBJECT-TYPE
    SYNTAX       SnmpAdminString
    MAX-ACCESS   read-only
    STATUS       current
    DESCRIPTION
        "Cisco Firepower compute:ChassisConnPolicy:name
        managed object property"
    ::= { cfprComputeChassisConnPolicyEntry 8 }

cfprComputeChassisConnPolicyPolicyLevel OBJECT-TYPE
    SYNTAX       Gauge32
    MAX-ACCESS   read-only
    STATUS       current
    DESCRIPTION
        "Cisco Firepower compute:ChassisConnPolicy:policyLevel
        managed object property"
    ::= { cfprComputeChassisConnPolicyEntry 9 }

cfprComputeChassisConnPolicyPolicyOwner OBJECT-TYPE
    SYNTAX       CfprPolicyPolicyOwner
    MAX-ACCESS   read-only
    STATUS       current
    DESCRIPTION
        "Cisco Firepower compute:ChassisConnPolicy:policyOwner
        managed object property"
    ::= { cfprComputeChassisConnPolicyEntry 10 }

cfprComputeChassisConnPolicyQualifier OBJECT-TYPE
    SYNTAX       SnmpAdminString
    MAX-ACCESS   read-only
    STATUS       current
    DESCRIPTION
        "Cisco Firepower compute:ChassisConnPolicy:qualifier
        managed object property"
    ::= { cfprComputeChassisConnPolicyEntry 11 }

cfprComputeChassisConnPolicySwitchId OBJECT-TYPE
    SYNTAX       CfprNetworkSwitchId
    MAX-ACCESS   read-only
    STATUS       current
    DESCRIPTION
        "Cisco Firepower compute:ChassisConnPolicy:switchId
        managed object property"
    ::= { cfprComputeChassisConnPolicyEntry 12 }

cfprComputeChassisDiscPolicyTable OBJECT-TYPE
    SYNTAX           SEQUENCE OF CfprComputeChassisDiscPolicyEntry
    MAX-ACCESS       not-accessible
    STATUS           current
    DESCRIPTION
        "Cisco Firepower compute:ChassisDiscPolicy managed object table"
    ::= { cfprComputeObjects 12 }

cfprComputeChassisDiscPolicyEntry OBJECT-TYPE
    SYNTAX           CfprComputeChassisDiscPolicyEntry
    MAX-ACCESS       not-accessible
    STATUS           current
    DESCRIPTION
        "Entry for the cfprComputeChassisDiscPolicyTable table."
    INDEX { cfprComputeChassisDiscPolicyInstanceId }
    ::= { cfprComputeChassisDiscPolicyTable 1 }

CfprComputeChassisDiscPolicyEntry ::= SEQUENCE {
    cfprComputeChassisDiscPolicyInstanceId                           CfprManagedObjectId,
    cfprComputeChassisDiscPolicyDn                                   CfprManagedObjectDn,
    cfprComputeChassisDiscPolicyRn                                   SnmpAdminString,
    cfprComputeChassisDiscPolicyAction                               CfprComputeChassisDiscAction,
    cfprComputeChassisDiscPolicyDescr                                SnmpAdminString,
    cfprComputeChassisDiscPolicyIntId                                SnmpAdminString,
    cfprComputeChassisDiscPolicyLinkAggregationPref                  CfprComputeLinkAggregation,
    cfprComputeChassisDiscPolicyName                                 SnmpAdminString,
    cfprComputeChassisDiscPolicyPolicyLevel                          Gauge32,
    cfprComputeChassisDiscPolicyPolicyOwner                          CfprPolicyPolicyOwner,
    cfprComputeChassisDiscPolicyQualifier                            SnmpAdminString,
    cfprComputeChassisDiscPolicyRebalance                            CfprComputeConnectivityRebalancing
}

cfprComputeChassisDiscPolicyInstanceId OBJECT-TYPE
    SYNTAX       CfprManagedObjectId
    MAX-ACCESS   not-accessible
    STATUS       current
    DESCRIPTION
        "Instance identifier of the managed object."
    ::= { cfprComputeChassisDiscPolicyEntry 1 }

cfprComputeChassisDiscPolicyDn OBJECT-TYPE
    SYNTAX       CfprManagedObjectDn
    MAX-ACCESS   read-only
    STATUS       current
    DESCRIPTION
        "Cisco Firepower compute:ChassisDiscPolicy:dn managed
        object property"
    ::= { cfprComputeChassisDiscPolicyEntry 2 }

cfprComputeChassisDiscPolicyRn OBJECT-TYPE
    SYNTAX       SnmpAdminString
    MAX-ACCESS   read-only
    STATUS       current
    DESCRIPTION
        "Cisco Firepower compute:ChassisDiscPolicy:rn managed
        object property"
    ::= { cfprComputeChassisDiscPolicyEntry 3 }

cfprComputeChassisDiscPolicyAction OBJECT-TYPE
    SYNTAX       CfprComputeChassisDiscAction
    MAX-ACCESS   read-only
    STATUS       current
    DESCRIPTION
        "Cisco Firepower compute:ChassisDiscPolicy:action
        managed object property"
    ::= { cfprComputeChassisDiscPolicyEntry 4 }

cfprComputeChassisDiscPolicyDescr OBJECT-TYPE
    SYNTAX       SnmpAdminString
    MAX-ACCESS   read-only
    STATUS       current
    DESCRIPTION
        "Cisco Firepower compute:ChassisDiscPolicy:descr
        managed object property"
    ::= { cfprComputeChassisDiscPolicyEntry 5 }

cfprComputeChassisDiscPolicyIntId OBJECT-TYPE
    SYNTAX       SnmpAdminString
    MAX-ACCESS   read-only
    STATUS       current
    DESCRIPTION
        "Cisco Firepower compute:ChassisDiscPolicy:intId
        managed object property"
    ::= { cfprComputeChassisDiscPolicyEntry 6 }

cfprComputeChassisDiscPolicyLinkAggregationPref OBJECT-TYPE
    SYNTAX       CfprComputeLinkAggregation
    MAX-ACCESS   read-only
    STATUS       current
    DESCRIPTION
        "Cisco Firepower compute:ChassisDiscPolicy:linkAggregationPref
        managed object property"
    ::= { cfprComputeChassisDiscPolicyEntry 7 }

cfprComputeChassisDiscPolicyName OBJECT-TYPE
    SYNTAX       SnmpAdminString
    MAX-ACCESS   read-only
    STATUS       current
    DESCRIPTION
        "Cisco Firepower compute:ChassisDiscPolicy:name
        managed object property"
    ::= { cfprComputeChassisDiscPolicyEntry 8 }

cfprComputeChassisDiscPolicyPolicyLevel OBJECT-TYPE
    SYNTAX       Gauge32
    MAX-ACCESS   read-only
    STATUS       current
    DESCRIPTION
        "Cisco Firepower compute:ChassisDiscPolicy:policyLevel
        managed object property"
    ::= { cfprComputeChassisDiscPolicyEntry 9 }

cfprComputeChassisDiscPolicyPolicyOwner OBJECT-TYPE
    SYNTAX       CfprPolicyPolicyOwner
    MAX-ACCESS   read-only
    STATUS       current
    DESCRIPTION
        "Cisco Firepower compute:ChassisDiscPolicy:policyOwner
        managed object property"
    ::= { cfprComputeChassisDiscPolicyEntry 10 }

cfprComputeChassisDiscPolicyQualifier OBJECT-TYPE
    SYNTAX       SnmpAdminString
    MAX-ACCESS   read-only
    STATUS       current
    DESCRIPTION
        "Cisco Firepower compute:ChassisDiscPolicy:qualifier
        managed object property"
    ::= { cfprComputeChassisDiscPolicyEntry 11 }

cfprComputeChassisDiscPolicyRebalance OBJECT-TYPE
    SYNTAX       CfprComputeConnectivityRebalancing
    MAX-ACCESS   read-only
    STATUS       current
    DESCRIPTION
        "Cisco Firepower compute:ChassisDiscPolicy:rebalance
        managed object property"
    ::= { cfprComputeChassisDiscPolicyEntry 12 }

cfprComputeChassisQualTable OBJECT-TYPE
    SYNTAX           SEQUENCE OF CfprComputeChassisQualEntry
    MAX-ACCESS       not-accessible
    STATUS           current
    DESCRIPTION
        "Cisco Firepower compute:ChassisQual managed object table"
    ::= { cfprComputeObjects 13 }

cfprComputeChassisQualEntry OBJECT-TYPE
    SYNTAX           CfprComputeChassisQualEntry
    MAX-ACCESS       not-accessible
    STATUS           current
    DESCRIPTION
        "Entry for the cfprComputeChassisQualTable table."
    INDEX { cfprComputeChassisQualInstanceId }
    ::= { cfprComputeChassisQualTable 1 }

CfprComputeChassisQualEntry ::= SEQUENCE {
    cfprComputeChassisQualInstanceId                                 CfprManagedObjectId,
    cfprComputeChassisQualDn                                         CfprManagedObjectDn,
    cfprComputeChassisQualRn                                         SnmpAdminString,
    cfprComputeChassisQualMaxId                                      CfprComputeChassisQualMaxId,
    cfprComputeChassisQualMinId                                      CfprComputeChassisQualMinId
}

cfprComputeChassisQualInstanceId OBJECT-TYPE
    SYNTAX       CfprManagedObjectId
    MAX-ACCESS   not-accessible
    STATUS       current
    DESCRIPTION
        "Instance identifier of the managed object."
    ::= { cfprComputeChassisQualEntry 1 }

cfprComputeChassisQualDn OBJECT-TYPE
    SYNTAX       CfprManagedObjectDn
    MAX-ACCESS   read-only
    STATUS       current
    DESCRIPTION
        "Cisco Firepower compute:ChassisQual:dn managed object property"
    ::= { cfprComputeChassisQualEntry 2 }

cfprComputeChassisQualRn OBJECT-TYPE
    SYNTAX       SnmpAdminString
    MAX-ACCESS   read-only
    STATUS       current
    DESCRIPTION
        "Cisco Firepower compute:ChassisQual:rn managed object property"
    ::= { cfprComputeChassisQualEntry 3 }

cfprComputeChassisQualMaxId OBJECT-TYPE
    SYNTAX       CfprComputeChassisQualMaxId
    MAX-ACCESS   read-only
    STATUS       current
    DESCRIPTION
        "Cisco Firepower compute:ChassisQual:maxId managed
        object property"
    ::= { cfprComputeChassisQualEntry 4 }

cfprComputeChassisQualMinId OBJECT-TYPE
    SYNTAX       CfprComputeChassisQualMinId
    MAX-ACCESS   read-only
    STATUS       current
    DESCRIPTION
        "Cisco Firepower compute:ChassisQual:minId managed
        object property"
    ::= { cfprComputeChassisQualEntry 5 }

cfprComputeDefaultsTable OBJECT-TYPE
    SYNTAX           SEQUENCE OF CfprComputeDefaultsEntry
    MAX-ACCESS       not-accessible
    STATUS           current
    DESCRIPTION
        "Cisco Firepower compute:Defaults managed object table"
    ::= { cfprComputeObjects 14 }

cfprComputeDefaultsEntry OBJECT-TYPE
    SYNTAX           CfprComputeDefaultsEntry
    MAX-ACCESS       not-accessible
    STATUS           current
    DESCRIPTION
        "Entry for the cfprComputeDefaultsTable table."
    INDEX { cfprComputeDefaultsInstanceId }
    ::= { cfprComputeDefaultsTable 1 }

CfprComputeDefaultsEntry ::= SEQUENCE {
    cfprComputeDefaultsInstanceId                                    CfprManagedObjectId,
    cfprComputeDefaultsDn                                            CfprManagedObjectDn,
    cfprComputeDefaultsRn                                            SnmpAdminString
}

cfprComputeDefaultsInstanceId OBJECT-TYPE
    SYNTAX       CfprManagedObjectId
    MAX-ACCESS   not-accessible
    STATUS       current
    DESCRIPTION
        "Instance identifier of the managed object."
    ::= { cfprComputeDefaultsEntry 1 }

cfprComputeDefaultsDn OBJECT-TYPE
    SYNTAX       CfprManagedObjectDn
    MAX-ACCESS   read-only
    STATUS       current
    DESCRIPTION
        "Cisco Firepower compute:Defaults:dn managed object property"
    ::= { cfprComputeDefaultsEntry 2 }

cfprComputeDefaultsRn OBJECT-TYPE
    SYNTAX       SnmpAdminString
    MAX-ACCESS   read-only
    STATUS       current
    DESCRIPTION
        "Cisco Firepower compute:Defaults:rn managed object property"
    ::= { cfprComputeDefaultsEntry 3 }

cfprComputeExtBoardTable OBJECT-TYPE
    SYNTAX           SEQUENCE OF CfprComputeExtBoardEntry
    MAX-ACCESS       not-accessible
    STATUS           current
    DESCRIPTION
        "Cisco Firepower compute:ExtBoard managed object table"
    ::= { cfprComputeObjects 15 }

cfprComputeExtBoardEntry OBJECT-TYPE
    SYNTAX           CfprComputeExtBoardEntry
    MAX-ACCESS       not-accessible
    STATUS           current
    DESCRIPTION
        "Entry for the cfprComputeExtBoardTable table."
    INDEX { cfprComputeExtBoardInstanceId }
    ::= { cfprComputeExtBoardTable 1 }

CfprComputeExtBoardEntry ::= SEQUENCE {
    cfprComputeExtBoardInstanceId                                    CfprManagedObjectId,
    cfprComputeExtBoardDn                                            CfprManagedObjectDn,
    cfprComputeExtBoardRn                                            SnmpAdminString,
    cfprComputeExtBoardBoardAggregationRole                          CfprEquipmentBoardAggregationRole,
    cfprComputeExtBoardChassisId                                     Gauge32,
    cfprComputeExtBoardCmosVoltage                                   CfprEquipmentSensorThresholdStatus,
    cfprComputeExtBoardConnPath                                      CfprEquipmentConnectionStatus,
    cfprComputeExtBoardConnStatus                                    CfprEquipmentConnectionStatus,
    cfprComputeExtBoardFaultQualifier                                SnmpAdminString,
    cfprComputeExtBoardId                                            Gauge32,
    cfprComputeExtBoardLocationDn                                    SnmpAdminString,
    cfprComputeExtBoardManagingInst                                  CfprNetworkSwitchId,
    cfprComputeExtBoardModel                                         SnmpAdminString,
    cfprComputeExtBoardOperPower                                     CfprEquipmentPowerState,
    cfprComputeExtBoardOperQualifierReason                           SnmpAdminString,
    cfprComputeExtBoardOperState                                     CfprEquipmentOperability,
    cfprComputeExtBoardOperability                                   CfprEquipmentOperability,
    cfprComputeExtBoardPerf                                          CfprEquipmentSensorThresholdStatus,
    cfprComputeExtBoardPower                                         CfprComputeABoardPower,
    cfprComputeExtBoardPowerUsage                                    CfprEquipmentSensorThresholdStatus,
    cfprComputeExtBoardPresence                                      CfprEquipmentPresence,
    cfprComputeExtBoardRevision                                      SnmpAdminString,
    cfprComputeExtBoardSerial                                        SnmpAdminString,
    cfprComputeExtBoardSlotId                                        Gauge32,
    cfprComputeExtBoardThermal                                       CfprEquipmentSensorThresholdStatus,
    cfprComputeExtBoardVendor                                        SnmpAdminString,
    cfprComputeExtBoardVoltage                                       CfprEquipmentSensorThresholdStatus
}

cfprComputeExtBoardInstanceId OBJECT-TYPE
    SYNTAX       CfprManagedObjectId
    MAX-ACCESS   not-accessible
    STATUS       current
    DESCRIPTION
        "Instance identifier of the managed object."
    ::= { cfprComputeExtBoardEntry 1 }

cfprComputeExtBoardDn OBJECT-TYPE
    SYNTAX       CfprManagedObjectDn
    MAX-ACCESS   read-only
    STATUS       current
    DESCRIPTION
        "Cisco Firepower compute:ExtBoard:dn managed object property"
    ::= { cfprComputeExtBoardEntry 2 }

cfprComputeExtBoardRn OBJECT-TYPE
    SYNTAX       SnmpAdminString
    MAX-ACCESS   read-only
    STATUS       current
    DESCRIPTION
        "Cisco Firepower compute:ExtBoard:rn managed object property"
    ::= { cfprComputeExtBoardEntry 3 }

cfprComputeExtBoardBoardAggregationRole OBJECT-TYPE
    SYNTAX       CfprEquipmentBoardAggregationRole
    MAX-ACCESS   read-only
    STATUS       current
    DESCRIPTION
        "Cisco Firepower compute:ExtBoard:boardAggregationRole
        managed object property"
    ::= { cfprComputeExtBoardEntry 4 }

cfprComputeExtBoardChassisId OBJECT-TYPE
    SYNTAX       Gauge32
    MAX-ACCESS   read-only
    STATUS       current
    DESCRIPTION
        "Cisco Firepower compute:ExtBoard:chassisId managed
        object property"
    ::= { cfprComputeExtBoardEntry 5 }

cfprComputeExtBoardCmosVoltage OBJECT-TYPE
    SYNTAX       CfprEquipmentSensorThresholdStatus
    MAX-ACCESS   read-only
    STATUS       current
    DESCRIPTION
        "Cisco Firepower compute:ExtBoard:cmosVoltage managed
        object property"
    ::= { cfprComputeExtBoardEntry 6 }

cfprComputeExtBoardConnPath OBJECT-TYPE
    SYNTAX       CfprEquipmentConnectionStatus
    MAX-ACCESS   read-only
    STATUS       current
    DESCRIPTION
        "Cisco Firepower compute:ExtBoard:connPath managed
        object property"
    ::= { cfprComputeExtBoardEntry 7 }

cfprComputeExtBoardConnStatus OBJECT-TYPE
    SYNTAX       CfprEquipmentConnectionStatus
    MAX-ACCESS   read-only
    STATUS       current
    DESCRIPTION
        "Cisco Firepower compute:ExtBoard:connStatus managed
        object property"
    ::= { cfprComputeExtBoardEntry 8 }

cfprComputeExtBoardFaultQualifier OBJECT-TYPE
    SYNTAX       SnmpAdminString
    MAX-ACCESS   read-only
    STATUS       current
    DESCRIPTION
        "Cisco Firepower compute:ExtBoard:faultQualifier
        managed object property"
    ::= { cfprComputeExtBoardEntry 9 }

cfprComputeExtBoardId OBJECT-TYPE
    SYNTAX       Gauge32
    MAX-ACCESS   read-only
    STATUS       current
    DESCRIPTION
        "Cisco Firepower compute:ExtBoard:id managed object property"
    ::= { cfprComputeExtBoardEntry 10 }

cfprComputeExtBoardLocationDn OBJECT-TYPE
    SYNTAX       SnmpAdminString
    MAX-ACCESS   read-only
    STATUS       current
    DESCRIPTION
        "Cisco Firepower compute:ExtBoard:locationDn managed
        object property"
    ::= { cfprComputeExtBoardEntry 11 }

cfprComputeExtBoardManagingInst OBJECT-TYPE
    SYNTAX       CfprNetworkSwitchId
    MAX-ACCESS   read-only
    STATUS       current
    DESCRIPTION
        "Cisco Firepower compute:ExtBoard:managingInst
        managed object property"
    ::= { cfprComputeExtBoardEntry 12 }

cfprComputeExtBoardModel OBJECT-TYPE
    SYNTAX       SnmpAdminString
    MAX-ACCESS   read-only
    STATUS       current
    DESCRIPTION
        "Cisco Firepower compute:ExtBoard:model managed object property"
    ::= { cfprComputeExtBoardEntry 13 }

cfprComputeExtBoardOperPower OBJECT-TYPE
    SYNTAX       CfprEquipmentPowerState
    MAX-ACCESS   read-only
    STATUS       current
    DESCRIPTION
        "Cisco Firepower compute:ExtBoard:operPower managed
        object property"
    ::= { cfprComputeExtBoardEntry 14 }

cfprComputeExtBoardOperQualifierReason OBJECT-TYPE
    SYNTAX       SnmpAdminString
    MAX-ACCESS   read-only
    STATUS       current
    DESCRIPTION
        "Cisco Firepower compute:ExtBoard:operQualifierReason
        managed object property"
    ::= { cfprComputeExtBoardEntry 15 }

cfprComputeExtBoardOperState OBJECT-TYPE
    SYNTAX       CfprEquipmentOperability
    MAX-ACCESS   read-only
    STATUS       current
    DESCRIPTION
        "Cisco Firepower compute:ExtBoard:operState managed
        object property"
    ::= { cfprComputeExtBoardEntry 16 }

cfprComputeExtBoardOperability OBJECT-TYPE
    SYNTAX       CfprEquipmentOperability
    MAX-ACCESS   read-only
    STATUS       current
    DESCRIPTION
        "Cisco Firepower compute:ExtBoard:operability managed
        object property"
    ::= { cfprComputeExtBoardEntry 17 }

cfprComputeExtBoardPerf OBJECT-TYPE
    SYNTAX       CfprEquipmentSensorThresholdStatus
    MAX-ACCESS   read-only
    STATUS       current
    DESCRIPTION
        "Cisco Firepower compute:ExtBoard:perf managed object property"
    ::= { cfprComputeExtBoardEntry 18 }

cfprComputeExtBoardPower OBJECT-TYPE
    SYNTAX       CfprComputeABoardPower
    MAX-ACCESS   read-only
    STATUS       current
    DESCRIPTION
        "Cisco Firepower compute:ExtBoard:power managed object property"
    ::= { cfprComputeExtBoardEntry 19 }

cfprComputeExtBoardPowerUsage OBJECT-TYPE
    SYNTAX       CfprEquipmentSensorThresholdStatus
    MAX-ACCESS   read-only
    STATUS       current
    DESCRIPTION
        "Cisco Firepower compute:ExtBoard:powerUsage managed
        object property"
    ::= { cfprComputeExtBoardEntry 20 }

cfprComputeExtBoardPresence OBJECT-TYPE
    SYNTAX       CfprEquipmentPresence
    MAX-ACCESS   read-only
    STATUS       current
    DESCRIPTION
        "Cisco Firepower compute:ExtBoard:presence managed
        object property"
    ::= { cfprComputeExtBoardEntry 21 }

cfprComputeExtBoardRevision OBJECT-TYPE
    SYNTAX       SnmpAdminString
    MAX-ACCESS   read-only
    STATUS       current
    DESCRIPTION
        "Cisco Firepower compute:ExtBoard:revision managed
        object property"
    ::= { cfprComputeExtBoardEntry 22 }

cfprComputeExtBoardSerial OBJECT-TYPE
    SYNTAX       SnmpAdminString
    MAX-ACCESS   read-only
    STATUS       current
    DESCRIPTION
        "Cisco Firepower compute:ExtBoard:serial managed object property"
    ::= { cfprComputeExtBoardEntry 23 }

cfprComputeExtBoardSlotId OBJECT-TYPE
    SYNTAX       Gauge32
    MAX-ACCESS   read-only
    STATUS       current
    DESCRIPTION
        "Cisco Firepower compute:ExtBoard:slotId managed object property"
    ::= { cfprComputeExtBoardEntry 24 }

cfprComputeExtBoardThermal OBJECT-TYPE
    SYNTAX       CfprEquipmentSensorThresholdStatus
    MAX-ACCESS   read-only
    STATUS       current
    DESCRIPTION
        "Cisco Firepower compute:ExtBoard:thermal managed object property"
    ::= { cfprComputeExtBoardEntry 25 }

cfprComputeExtBoardVendor OBJECT-TYPE
    SYNTAX       SnmpAdminString
    MAX-ACCESS   read-only
    STATUS       current
    DESCRIPTION
        "Cisco Firepower compute:ExtBoard:vendor managed object property"
    ::= { cfprComputeExtBoardEntry 26 }

cfprComputeExtBoardVoltage OBJECT-TYPE
    SYNTAX       CfprEquipmentSensorThresholdStatus
    MAX-ACCESS   read-only
    STATUS       current
    DESCRIPTION
        "Cisco Firepower compute:ExtBoard:voltage managed object property"
    ::= { cfprComputeExtBoardEntry 27 }

cfprComputeFwSyncAckTable OBJECT-TYPE
    SYNTAX           SEQUENCE OF CfprComputeFwSyncAckEntry
    MAX-ACCESS       not-accessible
    STATUS           current
    DESCRIPTION
        "Cisco Firepower compute:FwSyncAck managed object table"
    ::= { cfprComputeObjects 16 }

cfprComputeFwSyncAckEntry OBJECT-TYPE
    SYNTAX           CfprComputeFwSyncAckEntry
    MAX-ACCESS       not-accessible
    STATUS           current
    DESCRIPTION
        "Entry for the cfprComputeFwSyncAckTable table."
    INDEX { cfprComputeFwSyncAckInstanceId }
    ::= { cfprComputeFwSyncAckTable 1 }

CfprComputeFwSyncAckEntry ::= SEQUENCE {
    cfprComputeFwSyncAckInstanceId                                   CfprManagedObjectId,
    cfprComputeFwSyncAckDn                                           CfprManagedObjectDn,
    cfprComputeFwSyncAckRn                                           SnmpAdminString,
    cfprComputeFwSyncAckAcked                                        DateAndTime,
    cfprComputeFwSyncAckAckedBy                                      SnmpAdminString,
    cfprComputeFwSyncAckAdminState                                   CfprTrigAdminState,
    cfprComputeFwSyncAckAutoDelete                                   TruthValue,
    cfprComputeFwSyncAckChangeBy                                     SnmpAdminString,
    cfprComputeFwSyncAckChangeDetails                                CfprTrigAckChangeDetails,
    cfprComputeFwSyncAckChanges                                      CfprTrigAckChanges,
    cfprComputeFwSyncAckDescr                                        SnmpAdminString,
    cfprComputeFwSyncAckDisr                                         CfprTrigAckDisr,
    cfprComputeFwSyncAckIgnoreCap                                    TruthValue,
    cfprComputeFwSyncAckIntId                                        SnmpAdminString,
    cfprComputeFwSyncAckModified                                     DateAndTime,
    cfprComputeFwSyncAckName                                         SnmpAdminString,
    cfprComputeFwSyncAckOperScheduler                                SnmpAdminString,
    cfprComputeFwSyncAckOperState                                    CfprTrigAckOperState,
    cfprComputeFwSyncAckPolicyLevel                                  Gauge32,
    cfprComputeFwSyncAckPolicyOwner                                  CfprPolicyPolicyOwner,
    cfprComputeFwSyncAckPrevOperState                                CfprTrigAckPrevOperState,
    cfprComputeFwSyncAckScheduler                                    SnmpAdminString
}

cfprComputeFwSyncAckInstanceId OBJECT-TYPE
    SYNTAX       CfprManagedObjectId
    MAX-ACCESS   not-accessible
    STATUS       current
    DESCRIPTION
        "Instance identifier of the managed object."
    ::= { cfprComputeFwSyncAckEntry 1 }

cfprComputeFwSyncAckDn OBJECT-TYPE
    SYNTAX       CfprManagedObjectDn
    MAX-ACCESS   read-only
    STATUS       current
    DESCRIPTION
        "Cisco Firepower compute:FwSyncAck:dn managed object property"
    ::= { cfprComputeFwSyncAckEntry 2 }

cfprComputeFwSyncAckRn OBJECT-TYPE
    SYNTAX       SnmpAdminString
    MAX-ACCESS   read-only
    STATUS       current
    DESCRIPTION
        "Cisco Firepower compute:FwSyncAck:rn managed object property"
    ::= { cfprComputeFwSyncAckEntry 3 }

cfprComputeFwSyncAckAcked OBJECT-TYPE
    SYNTAX       DateAndTime
    MAX-ACCESS   read-only
    STATUS       current
    DESCRIPTION
        "Cisco Firepower compute:FwSyncAck:acked managed object property"
    ::= { cfprComputeFwSyncAckEntry 4 }

cfprComputeFwSyncAckAckedBy OBJECT-TYPE
    SYNTAX       SnmpAdminString
    MAX-ACCESS   read-only
    STATUS       current
    DESCRIPTION
        "Cisco Firepower compute:FwSyncAck:ackedBy managed
        object property"
    ::= { cfprComputeFwSyncAckEntry 5 }

cfprComputeFwSyncAckAdminState OBJECT-TYPE
    SYNTAX       CfprTrigAdminState
    MAX-ACCESS   read-only
    STATUS       current
    DESCRIPTION
        "Cisco Firepower compute:FwSyncAck:adminState managed
        object property"
    ::= { cfprComputeFwSyncAckEntry 6 }

cfprComputeFwSyncAckAutoDelete OBJECT-TYPE
    SYNTAX       TruthValue
    MAX-ACCESS   read-only
    STATUS       current
    DESCRIPTION
        "Cisco Firepower compute:FwSyncAck:autoDelete managed
        object property"
    ::= { cfprComputeFwSyncAckEntry 7 }

cfprComputeFwSyncAckChangeBy OBJECT-TYPE
    SYNTAX       SnmpAdminString
    MAX-ACCESS   read-only
    STATUS       current
    DESCRIPTION
        "Cisco Firepower compute:FwSyncAck:changeBy managed
        object property"
    ::= { cfprComputeFwSyncAckEntry 8 }

cfprComputeFwSyncAckChangeDetails OBJECT-TYPE
    SYNTAX       CfprTrigAckChangeDetails
    MAX-ACCESS   read-only
    STATUS       current
    DESCRIPTION
        "Cisco Firepower compute:FwSyncAck:changeDetails
        managed object property"
    ::= { cfprComputeFwSyncAckEntry 9 }

cfprComputeFwSyncAckChanges OBJECT-TYPE
    SYNTAX       CfprTrigAckChanges
    MAX-ACCESS   read-only
    STATUS       current
    DESCRIPTION
        "Cisco Firepower compute:FwSyncAck:changes managed
        object property"
    ::= { cfprComputeFwSyncAckEntry 10 }

cfprComputeFwSyncAckDescr OBJECT-TYPE
    SYNTAX       SnmpAdminString
    MAX-ACCESS   read-only
    STATUS       current
    DESCRIPTION
        "Cisco Firepower compute:FwSyncAck:descr managed object property"
    ::= { cfprComputeFwSyncAckEntry 11 }

cfprComputeFwSyncAckDisr OBJECT-TYPE
    SYNTAX       CfprTrigAckDisr
    MAX-ACCESS   read-only
    STATUS       current
    DESCRIPTION
        "Cisco Firepower compute:FwSyncAck:disr managed object property"
    ::= { cfprComputeFwSyncAckEntry 12 }

cfprComputeFwSyncAckIgnoreCap OBJECT-TYPE
    SYNTAX       TruthValue
    MAX-ACCESS   read-only
    STATUS       current
    DESCRIPTION
        "Cisco Firepower compute:FwSyncAck:ignoreCap managed
        object property"
    ::= { cfprComputeFwSyncAckEntry 13 }

cfprComputeFwSyncAckIntId OBJECT-TYPE
    SYNTAX       SnmpAdminString
    MAX-ACCESS   read-only
    STATUS       current
    DESCRIPTION
        "Cisco Firepower compute:FwSyncAck:intId managed object property"
    ::= { cfprComputeFwSyncAckEntry 14 }

cfprComputeFwSyncAckModified OBJECT-TYPE
    SYNTAX       DateAndTime
    MAX-ACCESS   read-only
    STATUS       current
    DESCRIPTION
        "Cisco Firepower compute:FwSyncAck:modified managed
        object property"
    ::= { cfprComputeFwSyncAckEntry 15 }

cfprComputeFwSyncAckName OBJECT-TYPE
    SYNTAX       SnmpAdminString
    MAX-ACCESS   read-only
    STATUS       current
    DESCRIPTION
        "Cisco Firepower compute:FwSyncAck:name managed object property"
    ::= { cfprComputeFwSyncAckEntry 16 }

cfprComputeFwSyncAckOperScheduler OBJECT-TYPE
    SYNTAX       SnmpAdminString
    MAX-ACCESS   read-only
    STATUS       current
    DESCRIPTION
        "Cisco Firepower compute:FwSyncAck:operScheduler
        managed object property"
    ::= { cfprComputeFwSyncAckEntry 17 }

cfprComputeFwSyncAckOperState OBJECT-TYPE
    SYNTAX       CfprTrigAckOperState
    MAX-ACCESS   read-only
    STATUS       current
    DESCRIPTION
        "Cisco Firepower compute:FwSyncAck:operState managed
        object property"
    ::= { cfprComputeFwSyncAckEntry 18 }

cfprComputeFwSyncAckPolicyLevel OBJECT-TYPE
    SYNTAX       Gauge32
    MAX-ACCESS   read-only
    STATUS       current
    DESCRIPTION
        "Cisco Firepower compute:FwSyncAck:policyLevel
        managed object property"
    ::= { cfprComputeFwSyncAckEntry 19 }

cfprComputeFwSyncAckPolicyOwner OBJECT-TYPE
    SYNTAX       CfprPolicyPolicyOwner
    MAX-ACCESS   read-only
    STATUS       current
    DESCRIPTION
        "Cisco Firepower compute:FwSyncAck:policyOwner
        managed object property"
    ::= { cfprComputeFwSyncAckEntry 20 }

cfprComputeFwSyncAckPrevOperState OBJECT-TYPE
    SYNTAX       CfprTrigAckPrevOperState
    MAX-ACCESS   read-only
    STATUS       current
    DESCRIPTION
        "Cisco Firepower compute:FwSyncAck:prevOperState
        managed object property"
    ::= { cfprComputeFwSyncAckEntry 21 }

cfprComputeFwSyncAckScheduler OBJECT-TYPE
    SYNTAX       SnmpAdminString
    MAX-ACCESS   read-only
    STATUS       current
    DESCRIPTION
        "Cisco Firepower compute:FwSyncAck:scheduler managed
        object property"
    ::= { cfprComputeFwSyncAckEntry 22 }

cfprComputeHealthLedSensorAlarmTable OBJECT-TYPE
    SYNTAX           SEQUENCE OF CfprComputeHealthLedSensorAlarmEntry
    MAX-ACCESS       not-accessible
    STATUS           current
    DESCRIPTION
        "Cisco Firepower compute:HealthLedSensorAlarm managed
        object table"
    ::= { cfprComputeObjects 17 }

cfprComputeHealthLedSensorAlarmEntry OBJECT-TYPE
    SYNTAX           CfprComputeHealthLedSensorAlarmEntry
    MAX-ACCESS       not-accessible
    STATUS           current
    DESCRIPTION
        "Entry for the cfprComputeHealthLedSensorAlarmTable table."
    INDEX { cfprComputeHealthLedSensorAlarmInstanceId }
    ::= { cfprComputeHealthLedSensorAlarmTable 1 }

CfprComputeHealthLedSensorAlarmEntry ::= SEQUENCE {
    cfprComputeHealthLedSensorAlarmInstanceId                        CfprManagedObjectId,
    cfprComputeHealthLedSensorAlarmDn                                CfprManagedObjectDn,
    cfprComputeHealthLedSensorAlarmRn                                SnmpAdminString,
    cfprComputeHealthLedSensorAlarmAlarmDesc                         SnmpAdminString,
    cfprComputeHealthLedSensorAlarmAlarmSeverity                     CfprComputeAlarmSeverity,
    cfprComputeHealthLedSensorAlarmSensorId                          Gauge32,
    cfprComputeHealthLedSensorAlarmSensorName                        SnmpAdminString
}

cfprComputeHealthLedSensorAlarmInstanceId OBJECT-TYPE
    SYNTAX       CfprManagedObjectId
    MAX-ACCESS   not-accessible
    STATUS       current
    DESCRIPTION
        "Instance identifier of the managed object."
    ::= { cfprComputeHealthLedSensorAlarmEntry 1 }

cfprComputeHealthLedSensorAlarmDn OBJECT-TYPE
    SYNTAX       CfprManagedObjectDn
    MAX-ACCESS   read-only
    STATUS       current
    DESCRIPTION
        "Cisco Firepower compute:HealthLedSensorAlarm:dn
        managed object property"
    ::= { cfprComputeHealthLedSensorAlarmEntry 2 }

cfprComputeHealthLedSensorAlarmRn OBJECT-TYPE
    SYNTAX       SnmpAdminString
    MAX-ACCESS   read-only
    STATUS       current
    DESCRIPTION
        "Cisco Firepower compute:HealthLedSensorAlarm:rn
        managed object property"
    ::= { cfprComputeHealthLedSensorAlarmEntry 3 }

cfprComputeHealthLedSensorAlarmAlarmDesc OBJECT-TYPE
    SYNTAX       SnmpAdminString
    MAX-ACCESS   read-only
    STATUS       current
    DESCRIPTION
        "Cisco Firepower compute:HealthLedSensorAlarm:alarmDesc
        managed object property"
    ::= { cfprComputeHealthLedSensorAlarmEntry 4 }

cfprComputeHealthLedSensorAlarmAlarmSeverity OBJECT-TYPE
    SYNTAX       CfprComputeAlarmSeverity
    MAX-ACCESS   read-only
    STATUS       current
    DESCRIPTION
        "Cisco Firepower compute:HealthLedSensorAlarm:alarmSeverity
        managed object property"
    ::= { cfprComputeHealthLedSensorAlarmEntry 5 }

cfprComputeHealthLedSensorAlarmSensorId OBJECT-TYPE
    SYNTAX       Gauge32
    MAX-ACCESS   read-only
    STATUS       current
    DESCRIPTION
        "Cisco Firepower compute:HealthLedSensorAlarm:sensorId
        managed object property"
    ::= { cfprComputeHealthLedSensorAlarmEntry 6 }

cfprComputeHealthLedSensorAlarmSensorName OBJECT-TYPE
    SYNTAX       SnmpAdminString
    MAX-ACCESS   read-only
    STATUS       current
    DESCRIPTION
        "Cisco Firepower compute:HealthLedSensorAlarm:sensorName
        managed object property"
    ::= { cfprComputeHealthLedSensorAlarmEntry 7 }

cfprComputeIOHubTable OBJECT-TYPE
    SYNTAX           SEQUENCE OF CfprComputeIOHubEntry
    MAX-ACCESS       not-accessible
    STATUS           current
    DESCRIPTION
        "Cisco Firepower compute:IOHub managed object table"
    ::= { cfprComputeObjects 18 }

cfprComputeIOHubEntry OBJECT-TYPE
    SYNTAX           CfprComputeIOHubEntry
    MAX-ACCESS       not-accessible
    STATUS           current
    DESCRIPTION
        "Entry for the cfprComputeIOHubTable table."
    INDEX { cfprComputeIOHubInstanceId }
    ::= { cfprComputeIOHubTable 1 }

CfprComputeIOHubEntry ::= SEQUENCE {
    cfprComputeIOHubInstanceId                                       CfprManagedObjectId,
    cfprComputeIOHubDn                                               CfprManagedObjectDn,
    cfprComputeIOHubRn                                               SnmpAdminString,
    cfprComputeIOHubId                                               Gauge32,
    cfprComputeIOHubLocationDn                                       SnmpAdminString,
    cfprComputeIOHubModel                                            SnmpAdminString,
    cfprComputeIOHubOperQualifierReason                              SnmpAdminString,
    cfprComputeIOHubOperState                                        CfprEquipmentOperability,
    cfprComputeIOHubOperability                                      CfprEquipmentOperability,
    cfprComputeIOHubPerf                                             CfprEquipmentSensorThresholdStatus,
    cfprComputeIOHubPower                                            CfprEquipmentPowerState,
    cfprComputeIOHubPresence                                         CfprEquipmentPresence,
    cfprComputeIOHubRevision                                         SnmpAdminString,
    cfprComputeIOHubSerial                                           SnmpAdminString,
    cfprComputeIOHubThermal                                          CfprEquipmentSensorThresholdStatus,
    cfprComputeIOHubVendor                                           SnmpAdminString,
    cfprComputeIOHubVoltage                                          CfprEquipmentSensorThresholdStatus
}

cfprComputeIOHubInstanceId OBJECT-TYPE
    SYNTAX       CfprManagedObjectId
    MAX-ACCESS   not-accessible
    STATUS       current
    DESCRIPTION
        "Instance identifier of the managed object."
    ::= { cfprComputeIOHubEntry 1 }

cfprComputeIOHubDn OBJECT-TYPE
    SYNTAX       CfprManagedObjectDn
    MAX-ACCESS   read-only
    STATUS       current
    DESCRIPTION
        "Cisco Firepower compute:IOHub:dn managed object property"
    ::= { cfprComputeIOHubEntry 2 }

cfprComputeIOHubRn OBJECT-TYPE
    SYNTAX       SnmpAdminString
    MAX-ACCESS   read-only
    STATUS       current
    DESCRIPTION
        "Cisco Firepower compute:IOHub:rn managed object property"
    ::= { cfprComputeIOHubEntry 3 }

cfprComputeIOHubId OBJECT-TYPE
    SYNTAX       Gauge32
    MAX-ACCESS   read-only
    STATUS       current
    DESCRIPTION
        "Cisco Firepower compute:IOHub:id managed object property"
    ::= { cfprComputeIOHubEntry 4 }

cfprComputeIOHubLocationDn OBJECT-TYPE
    SYNTAX       SnmpAdminString
    MAX-ACCESS   read-only
    STATUS       current
    DESCRIPTION
        "Cisco Firepower compute:IOHub:locationDn managed object property"
    ::= { cfprComputeIOHubEntry 5 }

cfprComputeIOHubModel OBJECT-TYPE
    SYNTAX       SnmpAdminString
    MAX-ACCESS   read-only
    STATUS       current
    DESCRIPTION
        "Cisco Firepower compute:IOHub:model managed object property"
    ::= { cfprComputeIOHubEntry 6 }

cfprComputeIOHubOperQualifierReason OBJECT-TYPE
    SYNTAX       SnmpAdminString
    MAX-ACCESS   read-only
    STATUS       current
    DESCRIPTION
        "Cisco Firepower compute:IOHub:operQualifierReason
        managed object property"
    ::= { cfprComputeIOHubEntry 7 }

cfprComputeIOHubOperState OBJECT-TYPE
    SYNTAX       CfprEquipmentOperability
    MAX-ACCESS   read-only
    STATUS       current
    DESCRIPTION
        "Cisco Firepower compute:IOHub:operState managed object property"
    ::= { cfprComputeIOHubEntry 8 }

cfprComputeIOHubOperability OBJECT-TYPE
    SYNTAX       CfprEquipmentOperability
    MAX-ACCESS   read-only
    STATUS       current
    DESCRIPTION
        "Cisco Firepower compute:IOHub:operability managed
        object property"
    ::= { cfprComputeIOHubEntry 9 }

cfprComputeIOHubPerf OBJECT-TYPE
    SYNTAX       CfprEquipmentSensorThresholdStatus
    MAX-ACCESS   read-only
    STATUS       current
    DESCRIPTION
        "Cisco Firepower compute:IOHub:perf managed object property"
    ::= { cfprComputeIOHubEntry 10 }

cfprComputeIOHubPower OBJECT-TYPE
    SYNTAX       CfprEquipmentPowerState
    MAX-ACCESS   read-only
    STATUS       current
    DESCRIPTION
        "Cisco Firepower compute:IOHub:power managed object property"
    ::= { cfprComputeIOHubEntry 11 }

cfprComputeIOHubPresence OBJECT-TYPE
    SYNTAX       CfprEquipmentPresence
    MAX-ACCESS   read-only
    STATUS       current
    DESCRIPTION
        "Cisco Firepower compute:IOHub:presence managed object property"
    ::= { cfprComputeIOHubEntry 12 }

cfprComputeIOHubRevision OBJECT-TYPE
    SYNTAX       SnmpAdminString
    MAX-ACCESS   read-only
    STATUS       current
    DESCRIPTION
        "Cisco Firepower compute:IOHub:revision managed object property"
    ::= { cfprComputeIOHubEntry 13 }

cfprComputeIOHubSerial OBJECT-TYPE
    SYNTAX       SnmpAdminString
    MAX-ACCESS   read-only
    STATUS       current
    DESCRIPTION
        "Cisco Firepower compute:IOHub:serial managed object property"
    ::= { cfprComputeIOHubEntry 14 }

cfprComputeIOHubThermal OBJECT-TYPE
    SYNTAX       CfprEquipmentSensorThresholdStatus
    MAX-ACCESS   read-only
    STATUS       current
    DESCRIPTION
        "Cisco Firepower compute:IOHub:thermal managed object property"
    ::= { cfprComputeIOHubEntry 15 }

cfprComputeIOHubVendor OBJECT-TYPE
    SYNTAX       SnmpAdminString
    MAX-ACCESS   read-only
    STATUS       current
    DESCRIPTION
        "Cisco Firepower compute:IOHub:vendor managed object property"
    ::= { cfprComputeIOHubEntry 16 }

cfprComputeIOHubVoltage OBJECT-TYPE
    SYNTAX       CfprEquipmentSensorThresholdStatus
    MAX-ACCESS   read-only
    STATUS       current
    DESCRIPTION
        "Cisco Firepower compute:IOHub:voltage managed object property"
    ::= { cfprComputeIOHubEntry 17 }

cfprComputeIOHubEnvStatsTable OBJECT-TYPE
    SYNTAX           SEQUENCE OF CfprComputeIOHubEnvStatsEntry
    MAX-ACCESS       not-accessible
    STATUS           current
    DESCRIPTION
        "Cisco Firepower compute:IOHubEnvStats managed object table"
    ::= { cfprComputeObjects 19 }

cfprComputeIOHubEnvStatsEntry OBJECT-TYPE
    SYNTAX           CfprComputeIOHubEnvStatsEntry
    MAX-ACCESS       not-accessible
    STATUS           current
    DESCRIPTION
        "Entry for the cfprComputeIOHubEnvStatsTable table."
    INDEX { cfprComputeIOHubEnvStatsInstanceId }
    ::= { cfprComputeIOHubEnvStatsTable 1 }

CfprComputeIOHubEnvStatsEntry ::= SEQUENCE {
    cfprComputeIOHubEnvStatsInstanceId                               CfprManagedObjectId,
    cfprComputeIOHubEnvStatsDn                                       CfprManagedObjectDn,
    cfprComputeIOHubEnvStatsRn                                       SnmpAdminString,
    cfprComputeIOHubEnvStatsIntervals                                Gauge32,
    cfprComputeIOHubEnvStatsSuspect                                  TruthValue,
    cfprComputeIOHubEnvStatsTemperature                              INTEGER,
    cfprComputeIOHubEnvStatsTemperatureAvg                           INTEGER,
    cfprComputeIOHubEnvStatsTemperatureMax                           INTEGER,
    cfprComputeIOHubEnvStatsTemperatureMin                           INTEGER,
    cfprComputeIOHubEnvStatsThresholded                              CfprComputeIOHubEnvStatsThresholded,
    cfprComputeIOHubEnvStatsTimeCollected                            DateAndTime,
    cfprComputeIOHubEnvStatsUpdate                                   Gauge32
}

cfprComputeIOHubEnvStatsInstanceId OBJECT-TYPE
    SYNTAX       CfprManagedObjectId
    MAX-ACCESS   not-accessible
    STATUS       current
    DESCRIPTION
        "Instance identifier of the managed object."
    ::= { cfprComputeIOHubEnvStatsEntry 1 }

cfprComputeIOHubEnvStatsDn OBJECT-TYPE
    SYNTAX       CfprManagedObjectDn
    MAX-ACCESS   read-only
    STATUS       current
    DESCRIPTION
        "Cisco Firepower compute:IOHubEnvStats:dn managed object property"
    ::= { cfprComputeIOHubEnvStatsEntry 2 }

cfprComputeIOHubEnvStatsRn OBJECT-TYPE
    SYNTAX       SnmpAdminString
    MAX-ACCESS   read-only
    STATUS       current
    DESCRIPTION
        "Cisco Firepower compute:IOHubEnvStats:rn managed object property"
    ::= { cfprComputeIOHubEnvStatsEntry 3 }

cfprComputeIOHubEnvStatsIntervals OBJECT-TYPE
    SYNTAX       Gauge32
    MAX-ACCESS   read-only
    STATUS       current
    DESCRIPTION
        "Cisco Firepower compute:IOHubEnvStats:intervals
        managed object property"
    ::= { cfprComputeIOHubEnvStatsEntry 4 }

cfprComputeIOHubEnvStatsSuspect OBJECT-TYPE
    SYNTAX       TruthValue
    MAX-ACCESS   read-only
    STATUS       current
    DESCRIPTION
        "Cisco Firepower compute:IOHubEnvStats:suspect
        managed object property"
    ::= { cfprComputeIOHubEnvStatsEntry 5 }

cfprComputeIOHubEnvStatsTemperature OBJECT-TYPE
    SYNTAX       INTEGER
    MAX-ACCESS   read-only
    STATUS       current
    DESCRIPTION
        "Cisco Firepower compute:IOHubEnvStats:temperature
        managed object property"
    ::= { cfprComputeIOHubEnvStatsEntry 6 }

cfprComputeIOHubEnvStatsTemperatureAvg OBJECT-TYPE
    SYNTAX       INTEGER
    MAX-ACCESS   read-only
    STATUS       current
    DESCRIPTION
        "Cisco Firepower compute:IOHubEnvStats:temperatureAvg
        managed object property"
    ::= { cfprComputeIOHubEnvStatsEntry 7 }

cfprComputeIOHubEnvStatsTemperatureMax OBJECT-TYPE
    SYNTAX       INTEGER
    MAX-ACCESS   read-only
    STATUS       current
    DESCRIPTION
        "Cisco Firepower compute:IOHubEnvStats:temperatureMax
        managed object property"
    ::= { cfprComputeIOHubEnvStatsEntry 8 }

cfprComputeIOHubEnvStatsTemperatureMin OBJECT-TYPE
    SYNTAX       INTEGER
    MAX-ACCESS   read-only
    STATUS       current
    DESCRIPTION
        "Cisco Firepower compute:IOHubEnvStats:temperatureMin
        managed object property"
    ::= { cfprComputeIOHubEnvStatsEntry 9 }

cfprComputeIOHubEnvStatsThresholded OBJECT-TYPE
    SYNTAX       CfprComputeIOHubEnvStatsThresholded
    MAX-ACCESS   read-only
    STATUS       current
    DESCRIPTION
        "Cisco Firepower compute:IOHubEnvStats:thresholded
        managed object property"
    ::= { cfprComputeIOHubEnvStatsEntry 10 }

cfprComputeIOHubEnvStatsTimeCollected OBJECT-TYPE
    SYNTAX       DateAndTime
    MAX-ACCESS   read-only
    STATUS       current
    DESCRIPTION
        "Cisco Firepower compute:IOHubEnvStats:timeCollected
        managed object property"
    ::= { cfprComputeIOHubEnvStatsEntry 11 }

cfprComputeIOHubEnvStatsUpdate OBJECT-TYPE
    SYNTAX       Gauge32
    MAX-ACCESS   read-only
    STATUS       current
    DESCRIPTION
        "Cisco Firepower compute:IOHubEnvStats:update managed
        object property"
    ::= { cfprComputeIOHubEnvStatsEntry 12 }

cfprComputeIOHubEnvStatsHistTable OBJECT-TYPE
    SYNTAX           SEQUENCE OF CfprComputeIOHubEnvStatsHistEntry
    MAX-ACCESS       not-accessible
    STATUS           current
    DESCRIPTION
        "Cisco Firepower compute:IOHubEnvStatsHist managed object table"
    ::= { cfprComputeObjects 20 }

cfprComputeIOHubEnvStatsHistEntry OBJECT-TYPE
    SYNTAX           CfprComputeIOHubEnvStatsHistEntry
    MAX-ACCESS       not-accessible
    STATUS           current
    DESCRIPTION
        "Entry for the cfprComputeIOHubEnvStatsHistTable table."
    INDEX { cfprComputeIOHubEnvStatsHistInstanceId }
    ::= { cfprComputeIOHubEnvStatsHistTable 1 }

CfprComputeIOHubEnvStatsHistEntry ::= SEQUENCE {
    cfprComputeIOHubEnvStatsHistInstanceId                           CfprManagedObjectId,
    cfprComputeIOHubEnvStatsHistDn                                   CfprManagedObjectDn,
    cfprComputeIOHubEnvStatsHistRn                                   SnmpAdminString,
    cfprComputeIOHubEnvStatsHistId                                   Unsigned64,
    cfprComputeIOHubEnvStatsHistMostRecent                           TruthValue,
    cfprComputeIOHubEnvStatsHistSuspect                              TruthValue,
    cfprComputeIOHubEnvStatsHistTemperature                          INTEGER,
    cfprComputeIOHubEnvStatsHistTemperatureAvg                       INTEGER,
    cfprComputeIOHubEnvStatsHistTemperatureMax                       INTEGER,
    cfprComputeIOHubEnvStatsHistTemperatureMin                       INTEGER,
    cfprComputeIOHubEnvStatsHistThresholded                          CfprComputeIOHubEnvStatsHistThresholded,
    cfprComputeIOHubEnvStatsHistTimeCollected                        DateAndTime
}

cfprComputeIOHubEnvStatsHistInstanceId OBJECT-TYPE
    SYNTAX       CfprManagedObjectId
    MAX-ACCESS   not-accessible
    STATUS       current
    DESCRIPTION
        "Instance identifier of the managed object."
    ::= { cfprComputeIOHubEnvStatsHistEntry 1 }

cfprComputeIOHubEnvStatsHistDn OBJECT-TYPE
    SYNTAX       CfprManagedObjectDn
    MAX-ACCESS   read-only
    STATUS       current
    DESCRIPTION
        "Cisco Firepower compute:IOHubEnvStatsHist:dn managed
        object property"
    ::= { cfprComputeIOHubEnvStatsHistEntry 2 }

cfprComputeIOHubEnvStatsHistRn OBJECT-TYPE
    SYNTAX       SnmpAdminString
    MAX-ACCESS   read-only
    STATUS       current
    DESCRIPTION
        "Cisco Firepower compute:IOHubEnvStatsHist:rn managed
        object property"
    ::= { cfprComputeIOHubEnvStatsHistEntry 3 }

cfprComputeIOHubEnvStatsHistId OBJECT-TYPE
    SYNTAX       Unsigned64
    MAX-ACCESS   read-only
    STATUS       current
    DESCRIPTION
        "Cisco Firepower compute:IOHubEnvStatsHist:id managed
        object property"
    ::= { cfprComputeIOHubEnvStatsHistEntry 4 }

cfprComputeIOHubEnvStatsHistMostRecent OBJECT-TYPE
    SYNTAX       TruthValue
    MAX-ACCESS   read-only
    STATUS       current
    DESCRIPTION
        "Cisco Firepower compute:IOHubEnvStatsHist:mostRecent
        managed object property"
    ::= { cfprComputeIOHubEnvStatsHistEntry 5 }

cfprComputeIOHubEnvStatsHistSuspect OBJECT-TYPE
    SYNTAX       TruthValue
    MAX-ACCESS   read-only
    STATUS       current
    DESCRIPTION
        "Cisco Firepower compute:IOHubEnvStatsHist:suspect
        managed object property"
    ::= { cfprComputeIOHubEnvStatsHistEntry 6 }

cfprComputeIOHubEnvStatsHistTemperature OBJECT-TYPE
    SYNTAX       INTEGER
    MAX-ACCESS   read-only
    STATUS       current
    DESCRIPTION
        "Cisco Firepower compute:IOHubEnvStatsHist:temperature
        managed object property"
    ::= { cfprComputeIOHubEnvStatsHistEntry 7 }

cfprComputeIOHubEnvStatsHistTemperatureAvg OBJECT-TYPE
    SYNTAX       INTEGER
    MAX-ACCESS   read-only
    STATUS       current
    DESCRIPTION
        "Cisco Firepower compute:IOHubEnvStatsHist:temperatureAvg
        managed object property"
    ::= { cfprComputeIOHubEnvStatsHistEntry 8 }

cfprComputeIOHubEnvStatsHistTemperatureMax OBJECT-TYPE
    SYNTAX       INTEGER
    MAX-ACCESS   read-only
    STATUS       current
    DESCRIPTION
        "Cisco Firepower compute:IOHubEnvStatsHist:temperatureMax
        managed object property"
    ::= { cfprComputeIOHubEnvStatsHistEntry 9 }

cfprComputeIOHubEnvStatsHistTemperatureMin OBJECT-TYPE
    SYNTAX       INTEGER
    MAX-ACCESS   read-only
    STATUS       current
    DESCRIPTION
        "Cisco Firepower compute:IOHubEnvStatsHist:temperatureMin
        managed object property"
    ::= { cfprComputeIOHubEnvStatsHistEntry 10 }

cfprComputeIOHubEnvStatsHistThresholded OBJECT-TYPE
    SYNTAX       CfprComputeIOHubEnvStatsHistThresholded
    MAX-ACCESS   read-only
    STATUS       current
    DESCRIPTION
        "Cisco Firepower compute:IOHubEnvStatsHist:thresholded
        managed object property"
    ::= { cfprComputeIOHubEnvStatsHistEntry 11 }

cfprComputeIOHubEnvStatsHistTimeCollected OBJECT-TYPE
    SYNTAX       DateAndTime
    MAX-ACCESS   read-only
    STATUS       current
    DESCRIPTION
        "Cisco Firepower compute:IOHubEnvStatsHist:timeCollected
        managed object property"
    ::= { cfprComputeIOHubEnvStatsHistEntry 12 }

cfprComputeKvmMgmtPolicyTable OBJECT-TYPE
    SYNTAX           SEQUENCE OF CfprComputeKvmMgmtPolicyEntry
    MAX-ACCESS       not-accessible
    STATUS           current
    DESCRIPTION
        "Cisco Firepower compute:KvmMgmtPolicy managed object table"
    ::= { cfprComputeObjects 21 }

cfprComputeKvmMgmtPolicyEntry OBJECT-TYPE
    SYNTAX           CfprComputeKvmMgmtPolicyEntry
    MAX-ACCESS       not-accessible
    STATUS           current
    DESCRIPTION
        "Entry for the cfprComputeKvmMgmtPolicyTable table."
    INDEX { cfprComputeKvmMgmtPolicyInstanceId }
    ::= { cfprComputeKvmMgmtPolicyTable 1 }

CfprComputeKvmMgmtPolicyEntry ::= SEQUENCE {
    cfprComputeKvmMgmtPolicyInstanceId                               CfprManagedObjectId,
    cfprComputeKvmMgmtPolicyDn                                       CfprManagedObjectDn,
    cfprComputeKvmMgmtPolicyRn                                       SnmpAdminString,
    cfprComputeKvmMgmtPolicyDescr                                    SnmpAdminString,
    cfprComputeKvmMgmtPolicyIntId                                    SnmpAdminString,
    cfprComputeKvmMgmtPolicyName                                     SnmpAdminString,
    cfprComputeKvmMgmtPolicyPolicyLevel                              Gauge32,
    cfprComputeKvmMgmtPolicyPolicyOwner                              CfprPolicyPolicyOwner,
    cfprComputeKvmMgmtPolicyVmediaEncryption                         CfprComputeKvmMgmtPolicyVmediaEncryption
}

cfprComputeKvmMgmtPolicyInstanceId OBJECT-TYPE
    SYNTAX       CfprManagedObjectId
    MAX-ACCESS   not-accessible
    STATUS       current
    DESCRIPTION
        "Instance identifier of the managed object."
    ::= { cfprComputeKvmMgmtPolicyEntry 1 }

cfprComputeKvmMgmtPolicyDn OBJECT-TYPE
    SYNTAX       CfprManagedObjectDn
    MAX-ACCESS   read-only
    STATUS       current
    DESCRIPTION
        "Cisco Firepower compute:KvmMgmtPolicy:dn managed object property"
    ::= { cfprComputeKvmMgmtPolicyEntry 2 }

cfprComputeKvmMgmtPolicyRn OBJECT-TYPE
    SYNTAX       SnmpAdminString
    MAX-ACCESS   read-only
    STATUS       current
    DESCRIPTION
        "Cisco Firepower compute:KvmMgmtPolicy:rn managed object property"
    ::= { cfprComputeKvmMgmtPolicyEntry 3 }

cfprComputeKvmMgmtPolicyDescr OBJECT-TYPE
    SYNTAX       SnmpAdminString
    MAX-ACCESS   read-only
    STATUS       current
    DESCRIPTION
        "Cisco Firepower compute:KvmMgmtPolicy:descr managed
        object property"
    ::= { cfprComputeKvmMgmtPolicyEntry 4 }

cfprComputeKvmMgmtPolicyIntId OBJECT-TYPE
    SYNTAX       SnmpAdminString
    MAX-ACCESS   read-only
    STATUS       current
    DESCRIPTION
        "Cisco Firepower compute:KvmMgmtPolicy:intId managed
        object property"
    ::= { cfprComputeKvmMgmtPolicyEntry 5 }

cfprComputeKvmMgmtPolicyName OBJECT-TYPE
    SYNTAX       SnmpAdminString
    MAX-ACCESS   read-only
    STATUS       current
    DESCRIPTION
        "Cisco Firepower compute:KvmMgmtPolicy:name managed
        object property"
    ::= { cfprComputeKvmMgmtPolicyEntry 6 }

cfprComputeKvmMgmtPolicyPolicyLevel OBJECT-TYPE
    SYNTAX       Gauge32
    MAX-ACCESS   read-only
    STATUS       current
    DESCRIPTION
        "Cisco Firepower compute:KvmMgmtPolicy:policyLevel
        managed object property"
    ::= { cfprComputeKvmMgmtPolicyEntry 7 }

cfprComputeKvmMgmtPolicyPolicyOwner OBJECT-TYPE
    SYNTAX       CfprPolicyPolicyOwner
    MAX-ACCESS   read-only
    STATUS       current
    DESCRIPTION
        "Cisco Firepower compute:KvmMgmtPolicy:policyOwner
        managed object property"
    ::= { cfprComputeKvmMgmtPolicyEntry 8 }

cfprComputeKvmMgmtPolicyVmediaEncryption OBJECT-TYPE
    SYNTAX       CfprComputeKvmMgmtPolicyVmediaEncryption
    MAX-ACCESS   read-only
    STATUS       current
    DESCRIPTION
        "Cisco Firepower compute:KvmMgmtPolicy:vmediaEncryption
        managed object property"
    ::= { cfprComputeKvmMgmtPolicyEntry 9 }

cfprComputeMbPowerStatsTable OBJECT-TYPE
    SYNTAX           SEQUENCE OF CfprComputeMbPowerStatsEntry
    MAX-ACCESS       not-accessible
    STATUS           current
    DESCRIPTION
        "Cisco Firepower compute:MbPowerStats managed object table"
    ::= { cfprComputeObjects 22 }

cfprComputeMbPowerStatsEntry OBJECT-TYPE
    SYNTAX           CfprComputeMbPowerStatsEntry
    MAX-ACCESS       not-accessible
    STATUS           current
    DESCRIPTION
        "Entry for the cfprComputeMbPowerStatsTable table."
    INDEX { cfprComputeMbPowerStatsInstanceId }
    ::= { cfprComputeMbPowerStatsTable 1 }

CfprComputeMbPowerStatsEntry ::= SEQUENCE {
    cfprComputeMbPowerStatsInstanceId                                CfprManagedObjectId,
    cfprComputeMbPowerStatsDn                                        CfprManagedObjectDn,
    cfprComputeMbPowerStatsRn                                        SnmpAdminString,
    cfprComputeMbPowerStatsConsumedPower                             INTEGER,
    cfprComputeMbPowerStatsConsumedPowerAvg                          INTEGER,
    cfprComputeMbPowerStatsConsumedPowerMax                          INTEGER,
    cfprComputeMbPowerStatsConsumedPowerMin                          INTEGER,
    cfprComputeMbPowerStatsInputCurrent                              INTEGER,
    cfprComputeMbPowerStatsInputCurrentAvg                           INTEGER,
    cfprComputeMbPowerStatsInputCurrentMax                           INTEGER,
    cfprComputeMbPowerStatsInputCurrentMin                           INTEGER,
    cfprComputeMbPowerStatsInputVoltage                              INTEGER,
    cfprComputeMbPowerStatsInputVoltageAvg                           INTEGER,
    cfprComputeMbPowerStatsInputVoltageMax                           INTEGER,
    cfprComputeMbPowerStatsInputVoltageMin                           INTEGER,
    cfprComputeMbPowerStatsIntervals                                 Gauge32,
    cfprComputeMbPowerStatsSuspect                                   TruthValue,
    cfprComputeMbPowerStatsThresholded                               CfprComputeMbPowerStatsThresholded,
    cfprComputeMbPowerStatsTimeCollected                             DateAndTime,
    cfprComputeMbPowerStatsUpdate                                    Gauge32
}

cfprComputeMbPowerStatsInstanceId OBJECT-TYPE
    SYNTAX       CfprManagedObjectId
    MAX-ACCESS   not-accessible
    STATUS       current
    DESCRIPTION
        "Instance identifier of the managed object."
    ::= { cfprComputeMbPowerStatsEntry 1 }

cfprComputeMbPowerStatsDn OBJECT-TYPE
    SYNTAX       CfprManagedObjectDn
    MAX-ACCESS   read-only
    STATUS       current
    DESCRIPTION
        "Cisco Firepower compute:MbPowerStats:dn managed object property"
    ::= { cfprComputeMbPowerStatsEntry 2 }

cfprComputeMbPowerStatsRn OBJECT-TYPE
    SYNTAX       SnmpAdminString
    MAX-ACCESS   read-only
    STATUS       current
    DESCRIPTION
        "Cisco Firepower compute:MbPowerStats:rn managed object property"
    ::= { cfprComputeMbPowerStatsEntry 3 }

cfprComputeMbPowerStatsConsumedPower OBJECT-TYPE
    SYNTAX       INTEGER
    MAX-ACCESS   read-only
    STATUS       current
    DESCRIPTION
        "Cisco Firepower compute:MbPowerStats:consumedPower
        managed object property"
    ::= { cfprComputeMbPowerStatsEntry 4 }

cfprComputeMbPowerStatsConsumedPowerAvg OBJECT-TYPE
    SYNTAX       INTEGER
    MAX-ACCESS   read-only
    STATUS       current
    DESCRIPTION
        "Cisco Firepower compute:MbPowerStats:consumedPowerAvg
        managed object property"
    ::= { cfprComputeMbPowerStatsEntry 5 }

cfprComputeMbPowerStatsConsumedPowerMax OBJECT-TYPE
    SYNTAX       INTEGER
    MAX-ACCESS   read-only
    STATUS       current
    DESCRIPTION
        "Cisco Firepower compute:MbPowerStats:consumedPowerMax
        managed object property"
    ::= { cfprComputeMbPowerStatsEntry 6 }

cfprComputeMbPowerStatsConsumedPowerMin OBJECT-TYPE
    SYNTAX       INTEGER
    MAX-ACCESS   read-only
    STATUS       current
    DESCRIPTION
        "Cisco Firepower compute:MbPowerStats:consumedPowerMin
        managed object property"
    ::= { cfprComputeMbPowerStatsEntry 7 }

cfprComputeMbPowerStatsInputCurrent OBJECT-TYPE
    SYNTAX       INTEGER
    MAX-ACCESS   read-only
    STATUS       current
    DESCRIPTION
        "Cisco Firepower compute:MbPowerStats:inputCurrent
        managed object property"
    ::= { cfprComputeMbPowerStatsEntry 8 }

cfprComputeMbPowerStatsInputCurrentAvg OBJECT-TYPE
    SYNTAX       INTEGER
    MAX-ACCESS   read-only
    STATUS       current
    DESCRIPTION
        "Cisco Firepower compute:MbPowerStats:inputCurrentAvg
        managed object property"
    ::= { cfprComputeMbPowerStatsEntry 9 }

cfprComputeMbPowerStatsInputCurrentMax OBJECT-TYPE
    SYNTAX       INTEGER
    MAX-ACCESS   read-only
    STATUS       current
    DESCRIPTION
        "Cisco Firepower compute:MbPowerStats:inputCurrentMax
        managed object property"
    ::= { cfprComputeMbPowerStatsEntry 10 }

cfprComputeMbPowerStatsInputCurrentMin OBJECT-TYPE
    SYNTAX       INTEGER
    MAX-ACCESS   read-only
    STATUS       current
    DESCRIPTION
        "Cisco Firepower compute:MbPowerStats:inputCurrentMin
        managed object property"
    ::= { cfprComputeMbPowerStatsEntry 11 }

cfprComputeMbPowerStatsInputVoltage OBJECT-TYPE
    SYNTAX       INTEGER
    MAX-ACCESS   read-only
    STATUS       current
    DESCRIPTION
        "Cisco Firepower compute:MbPowerStats:inputVoltage
        managed object property"
    ::= { cfprComputeMbPowerStatsEntry 12 }

cfprComputeMbPowerStatsInputVoltageAvg OBJECT-TYPE
    SYNTAX       INTEGER
    MAX-ACCESS   read-only
    STATUS       current
    DESCRIPTION
        "Cisco Firepower compute:MbPowerStats:inputVoltageAvg
        managed object property"
    ::= { cfprComputeMbPowerStatsEntry 13 }

cfprComputeMbPowerStatsInputVoltageMax OBJECT-TYPE
    SYNTAX       INTEGER
    MAX-ACCESS   read-only
    STATUS       current
    DESCRIPTION
        "Cisco Firepower compute:MbPowerStats:inputVoltageMax
        managed object property"
    ::= { cfprComputeMbPowerStatsEntry 14 }

cfprComputeMbPowerStatsInputVoltageMin OBJECT-TYPE
    SYNTAX       INTEGER
    MAX-ACCESS   read-only
    STATUS       current
    DESCRIPTION
        "Cisco Firepower compute:MbPowerStats:inputVoltageMin
        managed object property"
    ::= { cfprComputeMbPowerStatsEntry 15 }

cfprComputeMbPowerStatsIntervals OBJECT-TYPE
    SYNTAX       Gauge32
    MAX-ACCESS   read-only
    STATUS       current
    DESCRIPTION
        "Cisco Firepower compute:MbPowerStats:intervals
        managed object property"
    ::= { cfprComputeMbPowerStatsEntry 16 }

cfprComputeMbPowerStatsSuspect OBJECT-TYPE
    SYNTAX       TruthValue
    MAX-ACCESS   read-only
    STATUS       current
    DESCRIPTION
        "Cisco Firepower compute:MbPowerStats:suspect managed
        object property"
    ::= { cfprComputeMbPowerStatsEntry 17 }

cfprComputeMbPowerStatsThresholded OBJECT-TYPE
    SYNTAX       CfprComputeMbPowerStatsThresholded
    MAX-ACCESS   read-only
    STATUS       current
    DESCRIPTION
        "Cisco Firepower compute:MbPowerStats:thresholded
        managed object property"
    ::= { cfprComputeMbPowerStatsEntry 18 }

cfprComputeMbPowerStatsTimeCollected OBJECT-TYPE
    SYNTAX       DateAndTime
    MAX-ACCESS   read-only
    STATUS       current
    DESCRIPTION
        "Cisco Firepower compute:MbPowerStats:timeCollected
        managed object property"
    ::= { cfprComputeMbPowerStatsEntry 19 }

cfprComputeMbPowerStatsUpdate OBJECT-TYPE
    SYNTAX       Gauge32
    MAX-ACCESS   read-only
    STATUS       current
    DESCRIPTION
        "Cisco Firepower compute:MbPowerStats:update managed
        object property"
    ::= { cfprComputeMbPowerStatsEntry 20 }

cfprComputeMbPowerStatsHistTable OBJECT-TYPE
    SYNTAX           SEQUENCE OF CfprComputeMbPowerStatsHistEntry
    MAX-ACCESS       not-accessible
    STATUS           current
    DESCRIPTION
        "Cisco Firepower compute:MbPowerStatsHist managed object table"
    ::= { cfprComputeObjects 23 }

cfprComputeMbPowerStatsHistEntry OBJECT-TYPE
    SYNTAX           CfprComputeMbPowerStatsHistEntry
    MAX-ACCESS       not-accessible
    STATUS           current
    DESCRIPTION
        "Entry for the cfprComputeMbPowerStatsHistTable table."
    INDEX { cfprComputeMbPowerStatsHistInstanceId }
    ::= { cfprComputeMbPowerStatsHistTable 1 }

CfprComputeMbPowerStatsHistEntry ::= SEQUENCE {
    cfprComputeMbPowerStatsHistInstanceId                            CfprManagedObjectId,
    cfprComputeMbPowerStatsHistDn                                    CfprManagedObjectDn,
    cfprComputeMbPowerStatsHistRn                                    SnmpAdminString,
    cfprComputeMbPowerStatsHistConsumedPower                         INTEGER,
    cfprComputeMbPowerStatsHistConsumedPowerAvg                      INTEGER,
    cfprComputeMbPowerStatsHistConsumedPowerMax                      INTEGER,
    cfprComputeMbPowerStatsHistConsumedPowerMin                      INTEGER,
    cfprComputeMbPowerStatsHistId                                    Unsigned64,
    cfprComputeMbPowerStatsHistInputCurrent                          INTEGER,
    cfprComputeMbPowerStatsHistInputCurrentAvg                       INTEGER,
    cfprComputeMbPowerStatsHistInputCurrentMax                       INTEGER,
    cfprComputeMbPowerStatsHistInputCurrentMin                       INTEGER,
    cfprComputeMbPowerStatsHistInputVoltage                          INTEGER,
    cfprComputeMbPowerStatsHistInputVoltageAvg                       INTEGER,
    cfprComputeMbPowerStatsHistInputVoltageMax                       INTEGER,
    cfprComputeMbPowerStatsHistInputVoltageMin                       INTEGER,
    cfprComputeMbPowerStatsHistMostRecent                            TruthValue,
    cfprComputeMbPowerStatsHistSuspect                               TruthValue,
    cfprComputeMbPowerStatsHistThresholded                           CfprComputeMbPowerStatsHistThresholded,
    cfprComputeMbPowerStatsHistTimeCollected                         DateAndTime
}

cfprComputeMbPowerStatsHistInstanceId OBJECT-TYPE
    SYNTAX       CfprManagedObjectId
    MAX-ACCESS   not-accessible
    STATUS       current
    DESCRIPTION
        "Instance identifier of the managed object."
    ::= { cfprComputeMbPowerStatsHistEntry 1 }

cfprComputeMbPowerStatsHistDn OBJECT-TYPE
    SYNTAX       CfprManagedObjectDn
    MAX-ACCESS   read-only
    STATUS       current
    DESCRIPTION
        "Cisco Firepower compute:MbPowerStatsHist:dn managed
        object property"
    ::= { cfprComputeMbPowerStatsHistEntry 2 }

cfprComputeMbPowerStatsHistRn OBJECT-TYPE
    SYNTAX       SnmpAdminString
    MAX-ACCESS   read-only
    STATUS       current
    DESCRIPTION
        "Cisco Firepower compute:MbPowerStatsHist:rn managed
        object property"
    ::= { cfprComputeMbPowerStatsHistEntry 3 }

cfprComputeMbPowerStatsHistConsumedPower OBJECT-TYPE
    SYNTAX       INTEGER
    MAX-ACCESS   read-only
    STATUS       current
    DESCRIPTION
        "Cisco Firepower compute:MbPowerStatsHist:consumedPower
        managed object property"
    ::= { cfprComputeMbPowerStatsHistEntry 4 }

cfprComputeMbPowerStatsHistConsumedPowerAvg OBJECT-TYPE
    SYNTAX       INTEGER
    MAX-ACCESS   read-only
    STATUS       current
    DESCRIPTION
        "Cisco Firepower compute:MbPowerStatsHist:consumedPowerAvg
        managed object property"
    ::= { cfprComputeMbPowerStatsHistEntry 5 }

cfprComputeMbPowerStatsHistConsumedPowerMax OBJECT-TYPE
    SYNTAX       INTEGER
    MAX-ACCESS   read-only
    STATUS       current
    DESCRIPTION
        "Cisco Firepower compute:MbPowerStatsHist:consumedPowerMax
        managed object property"
    ::= { cfprComputeMbPowerStatsHistEntry 6 }

cfprComputeMbPowerStatsHistConsumedPowerMin OBJECT-TYPE
    SYNTAX       INTEGER
    MAX-ACCESS   read-only
    STATUS       current
    DESCRIPTION
        "Cisco Firepower compute:MbPowerStatsHist:consumedPowerMin
        managed object property"
    ::= { cfprComputeMbPowerStatsHistEntry 7 }

cfprComputeMbPowerStatsHistId OBJECT-TYPE
    SYNTAX       Unsigned64
    MAX-ACCESS   read-only
    STATUS       current
    DESCRIPTION
        "Cisco Firepower compute:MbPowerStatsHist:id managed
        object property"
    ::= { cfprComputeMbPowerStatsHistEntry 8 }

cfprComputeMbPowerStatsHistInputCurrent OBJECT-TYPE
    SYNTAX       INTEGER
    MAX-ACCESS   read-only
    STATUS       current
    DESCRIPTION
        "Cisco Firepower compute:MbPowerStatsHist:inputCurrent
        managed object property"
    ::= { cfprComputeMbPowerStatsHistEntry 9 }

cfprComputeMbPowerStatsHistInputCurrentAvg OBJECT-TYPE
    SYNTAX       INTEGER
    MAX-ACCESS   read-only
    STATUS       current
    DESCRIPTION
        "Cisco Firepower compute:MbPowerStatsHist:inputCurrentAvg
        managed object property"
    ::= { cfprComputeMbPowerStatsHistEntry 10 }

cfprComputeMbPowerStatsHistInputCurrentMax OBJECT-TYPE
    SYNTAX       INTEGER
    MAX-ACCESS   read-only
    STATUS       current
    DESCRIPTION
        "Cisco Firepower compute:MbPowerStatsHist:inputCurrentMax
        managed object property"
    ::= { cfprComputeMbPowerStatsHistEntry 11 }

cfprComputeMbPowerStatsHistInputCurrentMin OBJECT-TYPE
    SYNTAX       INTEGER
    MAX-ACCESS   read-only
    STATUS       current
    DESCRIPTION
        "Cisco Firepower compute:MbPowerStatsHist:inputCurrentMin
        managed object property"
    ::= { cfprComputeMbPowerStatsHistEntry 12 }

cfprComputeMbPowerStatsHistInputVoltage OBJECT-TYPE
    SYNTAX       INTEGER
    MAX-ACCESS   read-only
    STATUS       current
    DESCRIPTION
        "Cisco Firepower compute:MbPowerStatsHist:inputVoltage
        managed object property"
    ::= { cfprComputeMbPowerStatsHistEntry 13 }

cfprComputeMbPowerStatsHistInputVoltageAvg OBJECT-TYPE
    SYNTAX       INTEGER
    MAX-ACCESS   read-only
    STATUS       current
    DESCRIPTION
        "Cisco Firepower compute:MbPowerStatsHist:inputVoltageAvg
        managed object property"
    ::= { cfprComputeMbPowerStatsHistEntry 14 }

cfprComputeMbPowerStatsHistInputVoltageMax OBJECT-TYPE
    SYNTAX       INTEGER
    MAX-ACCESS   read-only
    STATUS       current
    DESCRIPTION
        "Cisco Firepower compute:MbPowerStatsHist:inputVoltageMax
        managed object property"
    ::= { cfprComputeMbPowerStatsHistEntry 15 }

cfprComputeMbPowerStatsHistInputVoltageMin OBJECT-TYPE
    SYNTAX       INTEGER
    MAX-ACCESS   read-only
    STATUS       current
    DESCRIPTION
        "Cisco Firepower compute:MbPowerStatsHist:inputVoltageMin
        managed object property"
    ::= { cfprComputeMbPowerStatsHistEntry 16 }

cfprComputeMbPowerStatsHistMostRecent OBJECT-TYPE
    SYNTAX       TruthValue
    MAX-ACCESS   read-only
    STATUS       current
    DESCRIPTION
        "Cisco Firepower compute:MbPowerStatsHist:mostRecent
        managed object property"
    ::= { cfprComputeMbPowerStatsHistEntry 17 }

cfprComputeMbPowerStatsHistSuspect OBJECT-TYPE
    SYNTAX       TruthValue
    MAX-ACCESS   read-only
    STATUS       current
    DESCRIPTION
        "Cisco Firepower compute:MbPowerStatsHist:suspect
        managed object property"
    ::= { cfprComputeMbPowerStatsHistEntry 18 }

cfprComputeMbPowerStatsHistThresholded OBJECT-TYPE
    SYNTAX       CfprComputeMbPowerStatsHistThresholded
    MAX-ACCESS   read-only
    STATUS       current
    DESCRIPTION
        "Cisco Firepower compute:MbPowerStatsHist:thresholded
        managed object property"
    ::= { cfprComputeMbPowerStatsHistEntry 19 }

cfprComputeMbPowerStatsHistTimeCollected OBJECT-TYPE
    SYNTAX       DateAndTime
    MAX-ACCESS   read-only
    STATUS       current
    DESCRIPTION
        "Cisco Firepower compute:MbPowerStatsHist:timeCollected
        managed object property"
    ::= { cfprComputeMbPowerStatsHistEntry 20 }

cfprComputeMbTempStatsTable OBJECT-TYPE
    SYNTAX           SEQUENCE OF CfprComputeMbTempStatsEntry
    MAX-ACCESS       not-accessible
    STATUS           current
    DESCRIPTION
        "Cisco Firepower compute:MbTempStats managed object table"
    ::= { cfprComputeObjects 24 }

cfprComputeMbTempStatsEntry OBJECT-TYPE
    SYNTAX           CfprComputeMbTempStatsEntry
    MAX-ACCESS       not-accessible
    STATUS           current
    DESCRIPTION
        "Entry for the cfprComputeMbTempStatsTable table."
    INDEX { cfprComputeMbTempStatsInstanceId }
    ::= { cfprComputeMbTempStatsTable 1 }

CfprComputeMbTempStatsEntry ::= SEQUENCE {
    cfprComputeMbTempStatsInstanceId                                 CfprManagedObjectId,
    cfprComputeMbTempStatsDn                                         CfprManagedObjectDn,
    cfprComputeMbTempStatsRn                                         SnmpAdminString,
    cfprComputeMbTempStatsFmTempSenIo                                INTEGER,
    cfprComputeMbTempStatsFmTempSenIoAvg                             INTEGER,
    cfprComputeMbTempStatsFmTempSenIoMax                             INTEGER,
    cfprComputeMbTempStatsFmTempSenIoMin                             INTEGER,
    cfprComputeMbTempStatsFmTempSenRear                              INTEGER,
    cfprComputeMbTempStatsFmTempSenRearAvg                           INTEGER,
    cfprComputeMbTempStatsFmTempSenRearL                             INTEGER,
    cfprComputeMbTempStatsFmTempSenRearLAvg                          INTEGER,
    cfprComputeMbTempStatsFmTempSenRearLMax                          INTEGER,
    cfprComputeMbTempStatsFmTempSenRearLMin                          INTEGER,
    cfprComputeMbTempStatsFmTempSenRearMax                           INTEGER,
    cfprComputeMbTempStatsFmTempSenRearMin                           INTEGER,
    cfprComputeMbTempStatsFmTempSenRearR                             INTEGER,
    cfprComputeMbTempStatsFmTempSenRearRAvg                          INTEGER,
    cfprComputeMbTempStatsFmTempSenRearRMax                          INTEGER,
    cfprComputeMbTempStatsFmTempSenRearRMin                          INTEGER,
    cfprComputeMbTempStatsIntervals                                  Gauge32,
    cfprComputeMbTempStatsSuspect                                    TruthValue,
    cfprComputeMbTempStatsThresholded                                CfprComputeMbTempStatsThresholded,
    cfprComputeMbTempStatsTimeCollected                              DateAndTime,
    cfprComputeMbTempStatsUpdate                                     Gauge32
}

cfprComputeMbTempStatsInstanceId OBJECT-TYPE
    SYNTAX       CfprManagedObjectId
    MAX-ACCESS   not-accessible
    STATUS       current
    DESCRIPTION
        "Instance identifier of the managed object."
    ::= { cfprComputeMbTempStatsEntry 1 }

cfprComputeMbTempStatsDn OBJECT-TYPE
    SYNTAX       CfprManagedObjectDn
    MAX-ACCESS   read-only
    STATUS       current
    DESCRIPTION
        "Cisco Firepower compute:MbTempStats:dn managed object property"
    ::= { cfprComputeMbTempStatsEntry 2 }

cfprComputeMbTempStatsRn OBJECT-TYPE
    SYNTAX       SnmpAdminString
    MAX-ACCESS   read-only
    STATUS       current
    DESCRIPTION
        "Cisco Firepower compute:MbTempStats:rn managed object property"
    ::= { cfprComputeMbTempStatsEntry 3 }

cfprComputeMbTempStatsFmTempSenIo OBJECT-TYPE
    SYNTAX       INTEGER
    MAX-ACCESS   read-only
    STATUS       current
    DESCRIPTION
        "Cisco Firepower compute:MbTempStats:fmTempSenIo
        managed object property"
    ::= { cfprComputeMbTempStatsEntry 4 }

cfprComputeMbTempStatsFmTempSenIoAvg OBJECT-TYPE
    SYNTAX       INTEGER
    MAX-ACCESS   read-only
    STATUS       current
    DESCRIPTION
        "Cisco Firepower compute:MbTempStats:fmTempSenIoAvg
        managed object property"
    ::= { cfprComputeMbTempStatsEntry 5 }

cfprComputeMbTempStatsFmTempSenIoMax OBJECT-TYPE
    SYNTAX       INTEGER
    MAX-ACCESS   read-only
    STATUS       current
    DESCRIPTION
        "Cisco Firepower compute:MbTempStats:fmTempSenIoMax
        managed object property"
    ::= { cfprComputeMbTempStatsEntry 6 }

cfprComputeMbTempStatsFmTempSenIoMin OBJECT-TYPE
    SYNTAX       INTEGER
    MAX-ACCESS   read-only
    STATUS       current
    DESCRIPTION
        "Cisco Firepower compute:MbTempStats:fmTempSenIoMin
        managed object property"
    ::= { cfprComputeMbTempStatsEntry 7 }

cfprComputeMbTempStatsFmTempSenRear OBJECT-TYPE
    SYNTAX       INTEGER
    MAX-ACCESS   read-only
    STATUS       current
    DESCRIPTION
        "Cisco Firepower compute:MbTempStats:fmTempSenRear
        managed object property"
    ::= { cfprComputeMbTempStatsEntry 8 }

cfprComputeMbTempStatsFmTempSenRearAvg OBJECT-TYPE
    SYNTAX       INTEGER
    MAX-ACCESS   read-only
    STATUS       current
    DESCRIPTION
        "Cisco Firepower compute:MbTempStats:fmTempSenRearAvg
        managed object property"
    ::= { cfprComputeMbTempStatsEntry 9 }

cfprComputeMbTempStatsFmTempSenRearL OBJECT-TYPE
    SYNTAX       INTEGER
    MAX-ACCESS   read-only
    STATUS       current
    DESCRIPTION
        "Cisco Firepower compute:MbTempStats:fmTempSenRearL
        managed object property"
    ::= { cfprComputeMbTempStatsEntry 10 }

cfprComputeMbTempStatsFmTempSenRearLAvg OBJECT-TYPE
    SYNTAX       INTEGER
    MAX-ACCESS   read-only
    STATUS       current
    DESCRIPTION
        "Cisco Firepower compute:MbTempStats:fmTempSenRearLAvg
        managed object property"
    ::= { cfprComputeMbTempStatsEntry 11 }

cfprComputeMbTempStatsFmTempSenRearLMax OBJECT-TYPE
    SYNTAX       INTEGER
    MAX-ACCESS   read-only
    STATUS       current
    DESCRIPTION
        "Cisco Firepower compute:MbTempStats:fmTempSenRearLMax
        managed object property"
    ::= { cfprComputeMbTempStatsEntry 12 }

cfprComputeMbTempStatsFmTempSenRearLMin OBJECT-TYPE
    SYNTAX       INTEGER
    MAX-ACCESS   read-only
    STATUS       current
    DESCRIPTION
        "Cisco Firepower compute:MbTempStats:fmTempSenRearLMin
        managed object property"
    ::= { cfprComputeMbTempStatsEntry 13 }

cfprComputeMbTempStatsFmTempSenRearMax OBJECT-TYPE
    SYNTAX       INTEGER
    MAX-ACCESS   read-only
    STATUS       current
    DESCRIPTION
        "Cisco Firepower compute:MbTempStats:fmTempSenRearMax
        managed object property"
    ::= { cfprComputeMbTempStatsEntry 14 }

cfprComputeMbTempStatsFmTempSenRearMin OBJECT-TYPE
    SYNTAX       INTEGER
    MAX-ACCESS   read-only
    STATUS       current
    DESCRIPTION
        "Cisco Firepower compute:MbTempStats:fmTempSenRearMin
        managed object property"
    ::= { cfprComputeMbTempStatsEntry 15 }

cfprComputeMbTempStatsFmTempSenRearR OBJECT-TYPE
    SYNTAX       INTEGER
    MAX-ACCESS   read-only
    STATUS       current
    DESCRIPTION
        "Cisco Firepower compute:MbTempStats:fmTempSenRearR
        managed object property"
    ::= { cfprComputeMbTempStatsEntry 16 }

cfprComputeMbTempStatsFmTempSenRearRAvg OBJECT-TYPE
    SYNTAX       INTEGER
    MAX-ACCESS   read-only
    STATUS       current
    DESCRIPTION
        "Cisco Firepower compute:MbTempStats:fmTempSenRearRAvg
        managed object property"
    ::= { cfprComputeMbTempStatsEntry 17 }

cfprComputeMbTempStatsFmTempSenRearRMax OBJECT-TYPE
    SYNTAX       INTEGER
    MAX-ACCESS   read-only
    STATUS       current
    DESCRIPTION
        "Cisco Firepower compute:MbTempStats:fmTempSenRearRMax
        managed object property"
    ::= { cfprComputeMbTempStatsEntry 18 }

cfprComputeMbTempStatsFmTempSenRearRMin OBJECT-TYPE
    SYNTAX       INTEGER
    MAX-ACCESS   read-only
    STATUS       current
    DESCRIPTION
        "Cisco Firepower compute:MbTempStats:fmTempSenRearRMin
        managed object property"
    ::= { cfprComputeMbTempStatsEntry 19 }

cfprComputeMbTempStatsIntervals OBJECT-TYPE
    SYNTAX       Gauge32
    MAX-ACCESS   read-only
    STATUS       current
    DESCRIPTION
        "Cisco Firepower compute:MbTempStats:intervals
        managed object property"
    ::= { cfprComputeMbTempStatsEntry 20 }

cfprComputeMbTempStatsSuspect OBJECT-TYPE
    SYNTAX       TruthValue
    MAX-ACCESS   read-only
    STATUS       current
    DESCRIPTION
        "Cisco Firepower compute:MbTempStats:suspect managed
        object property"
    ::= { cfprComputeMbTempStatsEntry 21 }

cfprComputeMbTempStatsThresholded OBJECT-TYPE
    SYNTAX       CfprComputeMbTempStatsThresholded
    MAX-ACCESS   read-only
    STATUS       current
    DESCRIPTION
        "Cisco Firepower compute:MbTempStats:thresholded
        managed object property"
    ::= { cfprComputeMbTempStatsEntry 22 }

cfprComputeMbTempStatsTimeCollected OBJECT-TYPE
    SYNTAX       DateAndTime
    MAX-ACCESS   read-only
    STATUS       current
    DESCRIPTION
        "Cisco Firepower compute:MbTempStats:timeCollected
        managed object property"
    ::= { cfprComputeMbTempStatsEntry 23 }

cfprComputeMbTempStatsUpdate OBJECT-TYPE
    SYNTAX       Gauge32
    MAX-ACCESS   read-only
    STATUS       current
    DESCRIPTION
        "Cisco Firepower compute:MbTempStats:update managed
        object property"
    ::= { cfprComputeMbTempStatsEntry 24 }

cfprComputeMbTempStatsHistTable OBJECT-TYPE
    SYNTAX           SEQUENCE OF CfprComputeMbTempStatsHistEntry
    MAX-ACCESS       not-accessible
    STATUS           current
    DESCRIPTION
        "Cisco Firepower compute:MbTempStatsHist managed object table"
    ::= { cfprComputeObjects 25 }

cfprComputeMbTempStatsHistEntry OBJECT-TYPE
    SYNTAX           CfprComputeMbTempStatsHistEntry
    MAX-ACCESS       not-accessible
    STATUS           current
    DESCRIPTION
        "Entry for the cfprComputeMbTempStatsHistTable table."
    INDEX { cfprComputeMbTempStatsHistInstanceId }
    ::= { cfprComputeMbTempStatsHistTable 1 }

CfprComputeMbTempStatsHistEntry ::= SEQUENCE {
    cfprComputeMbTempStatsHistInstanceId                             CfprManagedObjectId,
    cfprComputeMbTempStatsHistDn                                     CfprManagedObjectDn,
    cfprComputeMbTempStatsHistRn                                     SnmpAdminString,
    cfprComputeMbTempStatsHistFmTempSenIo                            INTEGER,
    cfprComputeMbTempStatsHistFmTempSenIoAvg                         INTEGER,
    cfprComputeMbTempStatsHistFmTempSenIoMax                         INTEGER,
    cfprComputeMbTempStatsHistFmTempSenIoMin                         INTEGER,
    cfprComputeMbTempStatsHistFmTempSenRear                          INTEGER,
    cfprComputeMbTempStatsHistFmTempSenRearAvg                       INTEGER,
    cfprComputeMbTempStatsHistFmTempSenRearL                         INTEGER,
    cfprComputeMbTempStatsHistFmTempSenRearLAvg                      INTEGER,
    cfprComputeMbTempStatsHistFmTempSenRearLMax                      INTEGER,
    cfprComputeMbTempStatsHistFmTempSenRearLMin                      INTEGER,
    cfprComputeMbTempStatsHistFmTempSenRearMax                       INTEGER,
    cfprComputeMbTempStatsHistFmTempSenRearMin                       INTEGER,
    cfprComputeMbTempStatsHistFmTempSenRearR                         INTEGER,
    cfprComputeMbTempStatsHistFmTempSenRearRAvg                      INTEGER,
    cfprComputeMbTempStatsHistFmTempSenRearRMax                      INTEGER,
    cfprComputeMbTempStatsHistFmTempSenRearRMin                      INTEGER,
    cfprComputeMbTempStatsHistId                                     Unsigned64,
    cfprComputeMbTempStatsHistMostRecent                             TruthValue,
    cfprComputeMbTempStatsHistSuspect                                TruthValue,
    cfprComputeMbTempStatsHistThresholded                            CfprComputeMbTempStatsHistThresholded,
    cfprComputeMbTempStatsHistTimeCollected                          DateAndTime
}

cfprComputeMbTempStatsHistInstanceId OBJECT-TYPE
    SYNTAX       CfprManagedObjectId
    MAX-ACCESS   not-accessible
    STATUS       current
    DESCRIPTION
        "Instance identifier of the managed object."
    ::= { cfprComputeMbTempStatsHistEntry 1 }

cfprComputeMbTempStatsHistDn OBJECT-TYPE
    SYNTAX       CfprManagedObjectDn
    MAX-ACCESS   read-only
    STATUS       current
    DESCRIPTION
        "Cisco Firepower compute:MbTempStatsHist:dn managed
        object property"
    ::= { cfprComputeMbTempStatsHistEntry 2 }

cfprComputeMbTempStatsHistRn OBJECT-TYPE
    SYNTAX       SnmpAdminString
    MAX-ACCESS   read-only
    STATUS       current
    DESCRIPTION
        "Cisco Firepower compute:MbTempStatsHist:rn managed
        object property"
    ::= { cfprComputeMbTempStatsHistEntry 3 }

cfprComputeMbTempStatsHistFmTempSenIo OBJECT-TYPE
    SYNTAX       INTEGER
    MAX-ACCESS   read-only
    STATUS       current
    DESCRIPTION
        "Cisco Firepower compute:MbTempStatsHist:fmTempSenIo
        managed object property"
    ::= { cfprComputeMbTempStatsHistEntry 4 }

cfprComputeMbTempStatsHistFmTempSenIoAvg OBJECT-TYPE
    SYNTAX       INTEGER
    MAX-ACCESS   read-only
    STATUS       current
    DESCRIPTION
        "Cisco Firepower compute:MbTempStatsHist:fmTempSenIoAvg
        managed object property"
    ::= { cfprComputeMbTempStatsHistEntry 5 }

cfprComputeMbTempStatsHistFmTempSenIoMax OBJECT-TYPE
    SYNTAX       INTEGER
    MAX-ACCESS   read-only
    STATUS       current
    DESCRIPTION
        "Cisco Firepower compute:MbTempStatsHist:fmTempSenIoMax
        managed object property"
    ::= { cfprComputeMbTempStatsHistEntry 6 }

cfprComputeMbTempStatsHistFmTempSenIoMin OBJECT-TYPE
    SYNTAX       INTEGER
    MAX-ACCESS   read-only
    STATUS       current
    DESCRIPTION
        "Cisco Firepower compute:MbTempStatsHist:fmTempSenIoMin
        managed object property"
    ::= { cfprComputeMbTempStatsHistEntry 7 }

cfprComputeMbTempStatsHistFmTempSenRear OBJECT-TYPE
    SYNTAX       INTEGER
    MAX-ACCESS   read-only
    STATUS       current
    DESCRIPTION
        "Cisco Firepower compute:MbTempStatsHist:fmTempSenRear
        managed object property"
    ::= { cfprComputeMbTempStatsHistEntry 8 }

cfprComputeMbTempStatsHistFmTempSenRearAvg OBJECT-TYPE
    SYNTAX       INTEGER
    MAX-ACCESS   read-only
    STATUS       current
    DESCRIPTION
        "Cisco Firepower compute:MbTempStatsHist:fmTempSenRearAvg
        managed object property"
    ::= { cfprComputeMbTempStatsHistEntry 9 }

cfprComputeMbTempStatsHistFmTempSenRearL OBJECT-TYPE
    SYNTAX       INTEGER
    MAX-ACCESS   read-only
    STATUS       current
    DESCRIPTION
        "Cisco Firepower compute:MbTempStatsHist:fmTempSenRearL
        managed object property"
    ::= { cfprComputeMbTempStatsHistEntry 10 }

cfprComputeMbTempStatsHistFmTempSenRearLAvg OBJECT-TYPE
    SYNTAX       INTEGER
    MAX-ACCESS   read-only
    STATUS       current
    DESCRIPTION
        "Cisco Firepower compute:MbTempStatsHist:fmTempSenRearLAvg
        managed object property"
    ::= { cfprComputeMbTempStatsHistEntry 11 }

cfprComputeMbTempStatsHistFmTempSenRearLMax OBJECT-TYPE
    SYNTAX       INTEGER
    MAX-ACCESS   read-only
    STATUS       current
    DESCRIPTION
        "Cisco Firepower compute:MbTempStatsHist:fmTempSenRearLMax
        managed object property"
    ::= { cfprComputeMbTempStatsHistEntry 12 }

cfprComputeMbTempStatsHistFmTempSenRearLMin OBJECT-TYPE
    SYNTAX       INTEGER
    MAX-ACCESS   read-only
    STATUS       current
    DESCRIPTION
        "Cisco Firepower compute:MbTempStatsHist:fmTempSenRearLMin
        managed object property"
    ::= { cfprComputeMbTempStatsHistEntry 13 }

cfprComputeMbTempStatsHistFmTempSenRearMax OBJECT-TYPE
    SYNTAX       INTEGER
    MAX-ACCESS   read-only
    STATUS       current
    DESCRIPTION
        "Cisco Firepower compute:MbTempStatsHist:fmTempSenRearMax
        managed object property"
    ::= { cfprComputeMbTempStatsHistEntry 14 }

cfprComputeMbTempStatsHistFmTempSenRearMin OBJECT-TYPE
    SYNTAX       INTEGER
    MAX-ACCESS   read-only
    STATUS       current
    DESCRIPTION
        "Cisco Firepower compute:MbTempStatsHist:fmTempSenRearMin
        managed object property"
    ::= { cfprComputeMbTempStatsHistEntry 15 }

cfprComputeMbTempStatsHistFmTempSenRearR OBJECT-TYPE
    SYNTAX       INTEGER
    MAX-ACCESS   read-only
    STATUS       current
    DESCRIPTION
        "Cisco Firepower compute:MbTempStatsHist:fmTempSenRearR
        managed object property"
    ::= { cfprComputeMbTempStatsHistEntry 16 }

cfprComputeMbTempStatsHistFmTempSenRearRAvg OBJECT-TYPE
    SYNTAX       INTEGER
    MAX-ACCESS   read-only
    STATUS       current
    DESCRIPTION
        "Cisco Firepower compute:MbTempStatsHist:fmTempSenRearRAvg
        managed object property"
    ::= { cfprComputeMbTempStatsHistEntry 17 }

cfprComputeMbTempStatsHistFmTempSenRearRMax OBJECT-TYPE
    SYNTAX       INTEGER
    MAX-ACCESS   read-only
    STATUS       current
    DESCRIPTION
        "Cisco Firepower compute:MbTempStatsHist:fmTempSenRearRMax
        managed object property"
    ::= { cfprComputeMbTempStatsHistEntry 18 }

cfprComputeMbTempStatsHistFmTempSenRearRMin OBJECT-TYPE
    SYNTAX       INTEGER
    MAX-ACCESS   read-only
    STATUS       current
    DESCRIPTION
        "Cisco Firepower compute:MbTempStatsHist:fmTempSenRearRMin
        managed object property"
    ::= { cfprComputeMbTempStatsHistEntry 19 }

cfprComputeMbTempStatsHistId OBJECT-TYPE
    SYNTAX       Unsigned64
    MAX-ACCESS   read-only
    STATUS       current
    DESCRIPTION
        "Cisco Firepower compute:MbTempStatsHist:id managed
        object property"
    ::= { cfprComputeMbTempStatsHistEntry 20 }

cfprComputeMbTempStatsHistMostRecent OBJECT-TYPE
    SYNTAX       TruthValue
    MAX-ACCESS   read-only
    STATUS       current
    DESCRIPTION
        "Cisco Firepower compute:MbTempStatsHist:mostRecent
        managed object property"
    ::= { cfprComputeMbTempStatsHistEntry 21 }

cfprComputeMbTempStatsHistSuspect OBJECT-TYPE
    SYNTAX       TruthValue
    MAX-ACCESS   read-only
    STATUS       current
    DESCRIPTION
        "Cisco Firepower compute:MbTempStatsHist:suspect
        managed object property"
    ::= { cfprComputeMbTempStatsHistEntry 22 }

cfprComputeMbTempStatsHistThresholded OBJECT-TYPE
    SYNTAX       CfprComputeMbTempStatsHistThresholded
    MAX-ACCESS   read-only
    STATUS       current
    DESCRIPTION
        "Cisco Firepower compute:MbTempStatsHist:thresholded
        managed object property"
    ::= { cfprComputeMbTempStatsHistEntry 23 }

cfprComputeMbTempStatsHistTimeCollected OBJECT-TYPE
    SYNTAX       DateAndTime
    MAX-ACCESS   read-only
    STATUS       current
    DESCRIPTION
        "Cisco Firepower compute:MbTempStatsHist:timeCollected
        managed object property"
    ::= { cfprComputeMbTempStatsHistEntry 24 }

cfprComputeMemoryConfigPolicyTable OBJECT-TYPE
    SYNTAX           SEQUENCE OF CfprComputeMemoryConfigPolicyEntry
    MAX-ACCESS       not-accessible
    STATUS           current
    DESCRIPTION
        "Cisco Firepower compute:MemoryConfigPolicy managed object table"
    ::= { cfprComputeObjects 26 }

cfprComputeMemoryConfigPolicyEntry OBJECT-TYPE
    SYNTAX           CfprComputeMemoryConfigPolicyEntry
    MAX-ACCESS       not-accessible
    STATUS           current
    DESCRIPTION
        "Entry for the cfprComputeMemoryConfigPolicyTable table."
    INDEX { cfprComputeMemoryConfigPolicyInstanceId }
    ::= { cfprComputeMemoryConfigPolicyTable 1 }

CfprComputeMemoryConfigPolicyEntry ::= SEQUENCE {
    cfprComputeMemoryConfigPolicyInstanceId                          CfprManagedObjectId,
    cfprComputeMemoryConfigPolicyDn                                  CfprManagedObjectDn,
    cfprComputeMemoryConfigPolicyRn                                  SnmpAdminString,
    cfprComputeMemoryConfigPolicyBlackListing                        CfprComputeBlackListing,
    cfprComputeMemoryConfigPolicyDescr                               SnmpAdminString,
    cfprComputeMemoryConfigPolicyIntId                               SnmpAdminString,
    cfprComputeMemoryConfigPolicyName                                SnmpAdminString,
    cfprComputeMemoryConfigPolicyPolicyLevel                         Gauge32,
    cfprComputeMemoryConfigPolicyPolicyOwner                         CfprPolicyPolicyOwner
}

cfprComputeMemoryConfigPolicyInstanceId OBJECT-TYPE
    SYNTAX       CfprManagedObjectId
    MAX-ACCESS   not-accessible
    STATUS       current
    DESCRIPTION
        "Instance identifier of the managed object."
    ::= { cfprComputeMemoryConfigPolicyEntry 1 }

cfprComputeMemoryConfigPolicyDn OBJECT-TYPE
    SYNTAX       CfprManagedObjectDn
    MAX-ACCESS   read-only
    STATUS       current
    DESCRIPTION
        "Cisco Firepower compute:MemoryConfigPolicy:dn
        managed object property"
    ::= { cfprComputeMemoryConfigPolicyEntry 2 }

cfprComputeMemoryConfigPolicyRn OBJECT-TYPE
    SYNTAX       SnmpAdminString
    MAX-ACCESS   read-only
    STATUS       current
    DESCRIPTION
        "Cisco Firepower compute:MemoryConfigPolicy:rn
        managed object property"
    ::= { cfprComputeMemoryConfigPolicyEntry 3 }

cfprComputeMemoryConfigPolicyBlackListing OBJECT-TYPE
    SYNTAX       CfprComputeBlackListing
    MAX-ACCESS   read-only
    STATUS       current
    DESCRIPTION
        "Cisco Firepower compute:MemoryConfigPolicy:blackListing
        managed object property"
    ::= { cfprComputeMemoryConfigPolicyEntry 4 }

cfprComputeMemoryConfigPolicyDescr OBJECT-TYPE
    SYNTAX       SnmpAdminString
    MAX-ACCESS   read-only
    STATUS       current
    DESCRIPTION
        "Cisco Firepower compute:MemoryConfigPolicy:descr
        managed object property"
    ::= { cfprComputeMemoryConfigPolicyEntry 5 }

cfprComputeMemoryConfigPolicyIntId OBJECT-TYPE
    SYNTAX       SnmpAdminString
    MAX-ACCESS   read-only
    STATUS       current
    DESCRIPTION
        "Cisco Firepower compute:MemoryConfigPolicy:intId
        managed object property"
    ::= { cfprComputeMemoryConfigPolicyEntry 6 }

cfprComputeMemoryConfigPolicyName OBJECT-TYPE
    SYNTAX       SnmpAdminString
    MAX-ACCESS   read-only
    STATUS       current
    DESCRIPTION
        "Cisco Firepower compute:MemoryConfigPolicy:name
        managed object property"
    ::= { cfprComputeMemoryConfigPolicyEntry 7 }

cfprComputeMemoryConfigPolicyPolicyLevel OBJECT-TYPE
    SYNTAX       Gauge32
    MAX-ACCESS   read-only
    STATUS       current
    DESCRIPTION
        "Cisco Firepower compute:MemoryConfigPolicy:policyLevel
        managed object property"
    ::= { cfprComputeMemoryConfigPolicyEntry 8 }

cfprComputeMemoryConfigPolicyPolicyOwner OBJECT-TYPE
    SYNTAX       CfprPolicyPolicyOwner
    MAX-ACCESS   read-only
    STATUS       current
    DESCRIPTION
        "Cisco Firepower compute:MemoryConfigPolicy:policyOwner
        managed object property"
    ::= { cfprComputeMemoryConfigPolicyEntry 9 }

cfprComputeMemoryConfigurationTable OBJECT-TYPE
    SYNTAX           SEQUENCE OF CfprComputeMemoryConfigurationEntry
    MAX-ACCESS       not-accessible
    STATUS           current
    DESCRIPTION
        "Cisco Firepower compute:MemoryConfiguration managed object table"
    ::= { cfprComputeObjects 27 }

cfprComputeMemoryConfigurationEntry OBJECT-TYPE
    SYNTAX           CfprComputeMemoryConfigurationEntry
    MAX-ACCESS       not-accessible
    STATUS           current
    DESCRIPTION
        "Entry for the cfprComputeMemoryConfigurationTable table."
    INDEX { cfprComputeMemoryConfigurationInstanceId }
    ::= { cfprComputeMemoryConfigurationTable 1 }

CfprComputeMemoryConfigurationEntry ::= SEQUENCE {
    cfprComputeMemoryConfigurationInstanceId                         CfprManagedObjectId,
    cfprComputeMemoryConfigurationDn                                 CfprManagedObjectDn,
    cfprComputeMemoryConfigurationRn                                 SnmpAdminString,
    cfprComputeMemoryConfigurationAdminMemoryState                   CfprComputeAdminMemoryState,
    cfprComputeMemoryConfigurationBlackListing                       CfprComputeBlackListing
}

cfprComputeMemoryConfigurationInstanceId OBJECT-TYPE
    SYNTAX       CfprManagedObjectId
    MAX-ACCESS   not-accessible
    STATUS       current
    DESCRIPTION
        "Instance identifier of the managed object."
    ::= { cfprComputeMemoryConfigurationEntry 1 }

cfprComputeMemoryConfigurationDn OBJECT-TYPE
    SYNTAX       CfprManagedObjectDn
    MAX-ACCESS   read-only
    STATUS       current
    DESCRIPTION
        "Cisco Firepower compute:MemoryConfiguration:dn
        managed object property"
    ::= { cfprComputeMemoryConfigurationEntry 2 }

cfprComputeMemoryConfigurationRn OBJECT-TYPE
    SYNTAX       SnmpAdminString
    MAX-ACCESS   read-only
    STATUS       current
    DESCRIPTION
        "Cisco Firepower compute:MemoryConfiguration:rn
        managed object property"
    ::= { cfprComputeMemoryConfigurationEntry 3 }

cfprComputeMemoryConfigurationAdminMemoryState OBJECT-TYPE
    SYNTAX       CfprComputeAdminMemoryState
    MAX-ACCESS   read-only
    STATUS       current
    DESCRIPTION
        "Cisco Firepower compute:MemoryConfiguration:adminMemoryState
        managed object property"
    ::= { cfprComputeMemoryConfigurationEntry 4 }

cfprComputeMemoryConfigurationBlackListing OBJECT-TYPE
    SYNTAX       CfprComputeBlackListing
    MAX-ACCESS   read-only
    STATUS       current
    DESCRIPTION
        "Cisco Firepower compute:MemoryConfiguration:blackListing
        managed object property"
    ::= { cfprComputeMemoryConfigurationEntry 5 }

cfprComputeMemoryUnitConstraintDefTable OBJECT-TYPE
    SYNTAX           SEQUENCE OF CfprComputeMemoryUnitConstraintDefEntry
    MAX-ACCESS       not-accessible
    STATUS           current
    DESCRIPTION
        "Cisco Firepower compute:MemoryUnitConstraintDef
        managed object table"
    ::= { cfprComputeObjects 28 }

cfprComputeMemoryUnitConstraintDefEntry OBJECT-TYPE
    SYNTAX           CfprComputeMemoryUnitConstraintDefEntry
    MAX-ACCESS       not-accessible
    STATUS           current
    DESCRIPTION
        "Entry for the cfprComputeMemoryUnitConstraintDefTable table."
    INDEX { cfprComputeMemoryUnitConstraintDefInstanceId }
    ::= { cfprComputeMemoryUnitConstraintDefTable 1 }

CfprComputeMemoryUnitConstraintDefEntry ::= SEQUENCE {
    cfprComputeMemoryUnitConstraintDefInstanceId                     CfprManagedObjectId,
    cfprComputeMemoryUnitConstraintDefDn                             CfprManagedObjectDn,
    cfprComputeMemoryUnitConstraintDefRn                             SnmpAdminString,
    cfprComputeMemoryUnitConstraintDefDescr                          SnmpAdminString,
    cfprComputeMemoryUnitConstraintDefIntId                          SnmpAdminString,
    cfprComputeMemoryUnitConstraintDefName                           SnmpAdminString,
    cfprComputeMemoryUnitConstraintDefPolicyLevel                    Gauge32,
    cfprComputeMemoryUnitConstraintDefPolicyOwner                    CfprPolicyPolicyOwner,
    cfprComputeMemoryUnitConstraintDefRevisionModifier               SnmpAdminString,
    cfprComputeMemoryUnitConstraintDefType                           CfprComputeMemoryUnitConstraintType
}

cfprComputeMemoryUnitConstraintDefInstanceId OBJECT-TYPE
    SYNTAX       CfprManagedObjectId
    MAX-ACCESS   not-accessible
    STATUS       current
    DESCRIPTION
        "Instance identifier of the managed object."
    ::= { cfprComputeMemoryUnitConstraintDefEntry 1 }

cfprComputeMemoryUnitConstraintDefDn OBJECT-TYPE
    SYNTAX       CfprManagedObjectDn
    MAX-ACCESS   read-only
    STATUS       current
    DESCRIPTION
        "Cisco Firepower compute:MemoryUnitConstraintDef:dn
        managed object property"
    ::= { cfprComputeMemoryUnitConstraintDefEntry 2 }

cfprComputeMemoryUnitConstraintDefRn OBJECT-TYPE
    SYNTAX       SnmpAdminString
    MAX-ACCESS   read-only
    STATUS       current
    DESCRIPTION
        "Cisco Firepower compute:MemoryUnitConstraintDef:rn
        managed object property"
    ::= { cfprComputeMemoryUnitConstraintDefEntry 3 }

cfprComputeMemoryUnitConstraintDefDescr OBJECT-TYPE
    SYNTAX       SnmpAdminString
    MAX-ACCESS   read-only
    STATUS       current
    DESCRIPTION
        "Cisco Firepower compute:MemoryUnitConstraintDef:descr
        managed object property"
    ::= { cfprComputeMemoryUnitConstraintDefEntry 4 }

cfprComputeMemoryUnitConstraintDefIntId OBJECT-TYPE
    SYNTAX       SnmpAdminString
    MAX-ACCESS   read-only
    STATUS       current
    DESCRIPTION
        "Cisco Firepower compute:MemoryUnitConstraintDef:intId
        managed object property"
    ::= { cfprComputeMemoryUnitConstraintDefEntry 5 }

cfprComputeMemoryUnitConstraintDefName OBJECT-TYPE
    SYNTAX       SnmpAdminString
    MAX-ACCESS   read-only
    STATUS       current
    DESCRIPTION
        "Cisco Firepower compute:MemoryUnitConstraintDef:name
        managed object property"
    ::= { cfprComputeMemoryUnitConstraintDefEntry 6 }

cfprComputeMemoryUnitConstraintDefPolicyLevel OBJECT-TYPE
    SYNTAX       Gauge32
    MAX-ACCESS   read-only
    STATUS       current
    DESCRIPTION
        "Cisco Firepower compute:MemoryUnitConstraintDef:policyLevel
        managed object property"
    ::= { cfprComputeMemoryUnitConstraintDefEntry 7 }

cfprComputeMemoryUnitConstraintDefPolicyOwner OBJECT-TYPE
    SYNTAX       CfprPolicyPolicyOwner
    MAX-ACCESS   read-only
    STATUS       current
    DESCRIPTION
        "Cisco Firepower compute:MemoryUnitConstraintDef:policyOwner
        managed object property"
    ::= { cfprComputeMemoryUnitConstraintDefEntry 8 }

cfprComputeMemoryUnitConstraintDefRevisionModifier OBJECT-TYPE
    SYNTAX       SnmpAdminString
    MAX-ACCESS   read-only
    STATUS       current
    DESCRIPTION
        "Cisco Firepower compute:MemoryUnitConstraintDef:revisionModifier
        managed object property"
    ::= { cfprComputeMemoryUnitConstraintDefEntry 9 }

cfprComputeMemoryUnitConstraintDefType OBJECT-TYPE
    SYNTAX       CfprComputeMemoryUnitConstraintType
    MAX-ACCESS   read-only
    STATUS       current
    DESCRIPTION
        "Cisco Firepower compute:MemoryUnitConstraintDef:type
        managed object property"
    ::= { cfprComputeMemoryUnitConstraintDefEntry 10 }

cfprComputePCIeFatalCompletionStatsTable OBJECT-TYPE
    SYNTAX           SEQUENCE OF CfprComputePCIeFatalCompletionStatsEntry
    MAX-ACCESS       not-accessible
    STATUS           current
    DESCRIPTION
        "Cisco Firepower compute:PCIeFatalCompletionStats
        managed object table"
    ::= { cfprComputeObjects 29 }

cfprComputePCIeFatalCompletionStatsEntry OBJECT-TYPE
    SYNTAX           CfprComputePCIeFatalCompletionStatsEntry
    MAX-ACCESS       not-accessible
    STATUS           current
    DESCRIPTION
        "Entry for the cfprComputePCIeFatalCompletionStatsTable table."
    INDEX { cfprComputePCIeFatalCompletionStatsInstanceId }
    ::= { cfprComputePCIeFatalCompletionStatsTable 1 }

CfprComputePCIeFatalCompletionStatsEntry ::= SEQUENCE {
    cfprComputePCIeFatalCompletionStatsInstanceId                    CfprManagedObjectId,
    cfprComputePCIeFatalCompletionStatsDn                            CfprManagedObjectDn,
    cfprComputePCIeFatalCompletionStatsRn                            SnmpAdminString,
    cfprComputePCIeFatalCompletionStatsAbortErrors                   Counter32,
    cfprComputePCIeFatalCompletionStatsAbortErrors15Min              Gauge32,
    cfprComputePCIeFatalCompletionStatsAbortErrors15MinH             Gauge32,
    cfprComputePCIeFatalCompletionStatsAbortErrors1Day               Gauge32,
    cfprComputePCIeFatalCompletionStatsAbortErrors1DayH              Gauge32,
    cfprComputePCIeFatalCompletionStatsAbortErrors1Hour              Gauge32,
    cfprComputePCIeFatalCompletionStatsAbortErrors1HourH             Gauge32,
    cfprComputePCIeFatalCompletionStatsAbortErrors1Week              Gauge32,
    cfprComputePCIeFatalCompletionStatsAbortErrors1WeekH             Gauge32,
    cfprComputePCIeFatalCompletionStatsAbortErrors2Weeks             Gauge32,
    cfprComputePCIeFatalCompletionStatsAbortErrors2WeeksH            Gauge32,
    cfprComputePCIeFatalCompletionStatsTimeoutErrors                 Counter32,
    cfprComputePCIeFatalCompletionStatsTimeoutErrors15Min            Gauge32,
    cfprComputePCIeFatalCompletionStatsTimeoutErrors15MinH           Gauge32,
    cfprComputePCIeFatalCompletionStatsTimeoutErrors1Day             Gauge32,
    cfprComputePCIeFatalCompletionStatsTimeoutErrors1DayH            Gauge32,
    cfprComputePCIeFatalCompletionStatsTimeoutErrors1Hour            Gauge32,
    cfprComputePCIeFatalCompletionStatsTimeoutErrors1HourH           Gauge32,
    cfprComputePCIeFatalCompletionStatsTimeoutErrors1Week            Gauge32,
    cfprComputePCIeFatalCompletionStatsTimeoutErrors1WeekH           Gauge32,
    cfprComputePCIeFatalCompletionStatsTimeoutErrors2Weeks           Gauge32,
    cfprComputePCIeFatalCompletionStatsTimeoutErrors2WeeksH          Gauge32,
    cfprComputePCIeFatalCompletionStatsIntervals                     Gauge32,
    cfprComputePCIeFatalCompletionStatsSuspect                       TruthValue,
    cfprComputePCIeFatalCompletionStatsThresholded                   CfprComputePCIeFatalCompletionStatsThresholded,
    cfprComputePCIeFatalCompletionStatsTimeCollected                 DateAndTime,
    cfprComputePCIeFatalCompletionStatsUnexpectedErrors              Counter32,
    cfprComputePCIeFatalCompletionStatsUnexpectedErrors15Min         Gauge32,
    cfprComputePCIeFatalCompletionStatsUnexpectedErrors15MinH        Gauge32,
    cfprComputePCIeFatalCompletionStatsUnexpectedErrors1Day          Gauge32,
    cfprComputePCIeFatalCompletionStatsUnexpectedErrors1DayH         Gauge32,
    cfprComputePCIeFatalCompletionStatsUnexpectedErrors1Hour         Gauge32,
    cfprComputePCIeFatalCompletionStatsUnexpectedErrors1HourH        Gauge32,
    cfprComputePCIeFatalCompletionStatsUnexpectedErrors1Week         Gauge32,
    cfprComputePCIeFatalCompletionStatsUnexpectedErrors1WeekH        Gauge32,
    cfprComputePCIeFatalCompletionStatsUnexpectedErrors2Weeks        Gauge32,
    cfprComputePCIeFatalCompletionStatsUnexpectedErrors2WeeksH       Gauge32,
    cfprComputePCIeFatalCompletionStatsUpdate                        Gauge32
}

cfprComputePCIeFatalCompletionStatsInstanceId OBJECT-TYPE
    SYNTAX       CfprManagedObjectId
    MAX-ACCESS   not-accessible
    STATUS       current
    DESCRIPTION
        "Instance identifier of the managed object."
    ::= { cfprComputePCIeFatalCompletionStatsEntry 1 }

cfprComputePCIeFatalCompletionStatsDn OBJECT-TYPE
    SYNTAX       CfprManagedObjectDn
    MAX-ACCESS   read-only
    STATUS       current
    DESCRIPTION
        "Cisco Firepower compute:PCIeFatalCompletionStats:dn
        managed object property"
    ::= { cfprComputePCIeFatalCompletionStatsEntry 2 }

cfprComputePCIeFatalCompletionStatsRn OBJECT-TYPE
    SYNTAX       SnmpAdminString
    MAX-ACCESS   read-only
    STATUS       current
    DESCRIPTION
        "Cisco Firepower compute:PCIeFatalCompletionStats:rn
        managed object property"
    ::= { cfprComputePCIeFatalCompletionStatsEntry 3 }

cfprComputePCIeFatalCompletionStatsAbortErrors OBJECT-TYPE
    SYNTAX       Counter32
    MAX-ACCESS   read-only
    STATUS       current
    DESCRIPTION
        "Cisco Firepower compute:PCIeFatalCompletionStats:AbortErrors
        managed object property"
    ::= { cfprComputePCIeFatalCompletionStatsEntry 4 }

cfprComputePCIeFatalCompletionStatsAbortErrors15Min OBJECT-TYPE
    SYNTAX       Gauge32
    MAX-ACCESS   read-only
    STATUS       current
    DESCRIPTION
        "Cisco Firepower compute:PCIeFatalCompletionStats:AbortErrors15Min
         managed object property"
    ::= { cfprComputePCIeFatalCompletionStatsEntry 5 }

cfprComputePCIeFatalCompletionStatsAbortErrors15MinH OBJECT-TYPE
    SYNTAX       Gauge32
    MAX-ACCESS   read-only
    STATUS       current
    DESCRIPTION
        "Cisco Firepower compute:PCIeFatalCompletionStats:AbortErrors15Min
        H managed object property"
    ::= { cfprComputePCIeFatalCompletionStatsEntry 6 }

cfprComputePCIeFatalCompletionStatsAbortErrors1Day OBJECT-TYPE
    SYNTAX       Gauge32
    MAX-ACCESS   read-only
    STATUS       current
    DESCRIPTION
        "Cisco Firepower compute:PCIeFatalCompletionStats:AbortErrors1Day
        managed object property"
    ::= { cfprComputePCIeFatalCompletionStatsEntry 7 }

cfprComputePCIeFatalCompletionStatsAbortErrors1DayH OBJECT-TYPE
    SYNTAX       Gauge32
    MAX-ACCESS   read-only
    STATUS       current
    DESCRIPTION
        "Cisco Firepower compute:PCIeFatalCompletionStats:AbortErrors1DayH
         managed object property"
    ::= { cfprComputePCIeFatalCompletionStatsEntry 8 }

cfprComputePCIeFatalCompletionStatsAbortErrors1Hour OBJECT-TYPE
    SYNTAX       Gauge32
    MAX-ACCESS   read-only
    STATUS       current
    DESCRIPTION
        "Cisco Firepower compute:PCIeFatalCompletionStats:AbortErrors1Hour
         managed object property"
    ::= { cfprComputePCIeFatalCompletionStatsEntry 9 }

cfprComputePCIeFatalCompletionStatsAbortErrors1HourH OBJECT-TYPE
    SYNTAX       Gauge32
    MAX-ACCESS   read-only
    STATUS       current
    DESCRIPTION
        "Cisco Firepower compute:PCIeFatalCompletionStats:AbortErrors1Hour
        H managed object property"
    ::= { cfprComputePCIeFatalCompletionStatsEntry 10 }

cfprComputePCIeFatalCompletionStatsAbortErrors1Week OBJECT-TYPE
    SYNTAX       Gauge32
    MAX-ACCESS   read-only
    STATUS       current
    DESCRIPTION
        "Cisco Firepower compute:PCIeFatalCompletionStats:AbortErrors1Week
         managed object property"
    ::= { cfprComputePCIeFatalCompletionStatsEntry 11 }

cfprComputePCIeFatalCompletionStatsAbortErrors1WeekH OBJECT-TYPE
    SYNTAX       Gauge32
    MAX-ACCESS   read-only
    STATUS       current
    DESCRIPTION
        "Cisco Firepower compute:PCIeFatalCompletionStats:AbortErrors1Week
        H managed object property"
    ::= { cfprComputePCIeFatalCompletionStatsEntry 12 }

cfprComputePCIeFatalCompletionStatsAbortErrors2Weeks OBJECT-TYPE
    SYNTAX       Gauge32
    MAX-ACCESS   read-only
    STATUS       current
    DESCRIPTION
        "Cisco Firepower compute:PCIeFatalCompletionStats:AbortErrors2Week
        s managed object property"
    ::= { cfprComputePCIeFatalCompletionStatsEntry 13 }

cfprComputePCIeFatalCompletionStatsAbortErrors2WeeksH OBJECT-TYPE
    SYNTAX       Gauge32
    MAX-ACCESS   read-only
    STATUS       current
    DESCRIPTION
        "Cisco Firepower compute:PCIeFatalCompletionStats:AbortErrors2Week
        sH managed object property"
    ::= { cfprComputePCIeFatalCompletionStatsEntry 14 }

cfprComputePCIeFatalCompletionStatsTimeoutErrors OBJECT-TYPE
    SYNTAX       Counter32
    MAX-ACCESS   read-only
    STATUS       current
    DESCRIPTION
        "Cisco Firepower compute:PCIeFatalCompletionStats:TimeoutErrors
        managed object property"
    ::= { cfprComputePCIeFatalCompletionStatsEntry 15 }

cfprComputePCIeFatalCompletionStatsTimeoutErrors15Min OBJECT-TYPE
    SYNTAX       Gauge32
    MAX-ACCESS   read-only
    STATUS       current
    DESCRIPTION
        "Cisco Firepower compute:PCIeFatalCompletionStats:TimeoutErrors15M
        in managed object property"
    ::= { cfprComputePCIeFatalCompletionStatsEntry 16 }

cfprComputePCIeFatalCompletionStatsTimeoutErrors15MinH OBJECT-TYPE
    SYNTAX       Gauge32
    MAX-ACCESS   read-only
    STATUS       current
    DESCRIPTION
        "Cisco Firepower compute:PCIeFatalCompletionStats:TimeoutErrors15M
        inH managed object property"
    ::= { cfprComputePCIeFatalCompletionStatsEntry 17 }

cfprComputePCIeFatalCompletionStatsTimeoutErrors1Day OBJECT-TYPE
    SYNTAX       Gauge32
    MAX-ACCESS   read-only
    STATUS       current
    DESCRIPTION
        "Cisco Firepower compute:PCIeFatalCompletionStats:TimeoutErrors1Da
        y managed object property"
    ::= { cfprComputePCIeFatalCompletionStatsEntry 18 }

cfprComputePCIeFatalCompletionStatsTimeoutErrors1DayH OBJECT-TYPE
    SYNTAX       Gauge32
    MAX-ACCESS   read-only
    STATUS       current
    DESCRIPTION
        "Cisco Firepower compute:PCIeFatalCompletionStats:TimeoutErrors1Da
        yH managed object property"
    ::= { cfprComputePCIeFatalCompletionStatsEntry 19 }

cfprComputePCIeFatalCompletionStatsTimeoutErrors1Hour OBJECT-TYPE
    SYNTAX       Gauge32
    MAX-ACCESS   read-only
    STATUS       current
    DESCRIPTION
        "Cisco Firepower compute:PCIeFatalCompletionStats:TimeoutErrors1Ho
        ur managed object property"
    ::= { cfprComputePCIeFatalCompletionStatsEntry 20 }

cfprComputePCIeFatalCompletionStatsTimeoutErrors1HourH OBJECT-TYPE
    SYNTAX       Gauge32
    MAX-ACCESS   read-only
    STATUS       current
    DESCRIPTION
        "Cisco Firepower compute:PCIeFatalCompletionStats:TimeoutErrors1Ho
        urH managed object property"
    ::= { cfprComputePCIeFatalCompletionStatsEntry 21 }

cfprComputePCIeFatalCompletionStatsTimeoutErrors1Week OBJECT-TYPE
    SYNTAX       Gauge32
    MAX-ACCESS   read-only
    STATUS       current
    DESCRIPTION
        "Cisco Firepower compute:PCIeFatalCompletionStats:TimeoutErrors1We
        ek managed object property"
    ::= { cfprComputePCIeFatalCompletionStatsEntry 22 }

cfprComputePCIeFatalCompletionStatsTimeoutErrors1WeekH OBJECT-TYPE
    SYNTAX       Gauge32
    MAX-ACCESS   read-only
    STATUS       current
    DESCRIPTION
        "Cisco Firepower compute:PCIeFatalCompletionStats:TimeoutErrors1We
        ekH managed object property"
    ::= { cfprComputePCIeFatalCompletionStatsEntry 23 }

cfprComputePCIeFatalCompletionStatsTimeoutErrors2Weeks OBJECT-TYPE
    SYNTAX       Gauge32
    MAX-ACCESS   read-only
    STATUS       current
    DESCRIPTION
        "Cisco Firepower compute:PCIeFatalCompletionStats:TimeoutErrors2We
        eks managed object property"
    ::= { cfprComputePCIeFatalCompletionStatsEntry 24 }

cfprComputePCIeFatalCompletionStatsTimeoutErrors2WeeksH OBJECT-TYPE
    SYNTAX       Gauge32
    MAX-ACCESS   read-only
    STATUS       current
    DESCRIPTION
        "Cisco Firepower compute:PCIeFatalCompletionStats:TimeoutErrors2We
        eksH managed object property"
    ::= { cfprComputePCIeFatalCompletionStatsEntry 25 }

cfprComputePCIeFatalCompletionStatsIntervals OBJECT-TYPE
    SYNTAX       Gauge32
    MAX-ACCESS   read-only
    STATUS       current
    DESCRIPTION
        "Cisco Firepower compute:PCIeFatalCompletionStats:intervals
        managed object property"
    ::= { cfprComputePCIeFatalCompletionStatsEntry 26 }

cfprComputePCIeFatalCompletionStatsSuspect OBJECT-TYPE
    SYNTAX       TruthValue
    MAX-ACCESS   read-only
    STATUS       current
    DESCRIPTION
        "Cisco Firepower compute:PCIeFatalCompletionStats:suspect
        managed object property"
    ::= { cfprComputePCIeFatalCompletionStatsEntry 27 }

cfprComputePCIeFatalCompletionStatsThresholded OBJECT-TYPE
    SYNTAX       CfprComputePCIeFatalCompletionStatsThresholded
    MAX-ACCESS   read-only
    STATUS       current
    DESCRIPTION
        "Cisco Firepower compute:PCIeFatalCompletionStats:thresholded
        managed object property"
    ::= { cfprComputePCIeFatalCompletionStatsEntry 28 }

cfprComputePCIeFatalCompletionStatsTimeCollected OBJECT-TYPE
    SYNTAX       DateAndTime
    MAX-ACCESS   read-only
    STATUS       current
    DESCRIPTION
        "Cisco Firepower compute:PCIeFatalCompletionStats:timeCollected
        managed object property"
    ::= { cfprComputePCIeFatalCompletionStatsEntry 29 }

cfprComputePCIeFatalCompletionStatsUnexpectedErrors OBJECT-TYPE
    SYNTAX       Counter32
    MAX-ACCESS   read-only
    STATUS       current
    DESCRIPTION
        "Cisco Firepower compute:PCIeFatalCompletionStats:unexpectedErrors
         managed object property"
    ::= { cfprComputePCIeFatalCompletionStatsEntry 30 }

cfprComputePCIeFatalCompletionStatsUnexpectedErrors15Min OBJECT-TYPE
    SYNTAX       Gauge32
    MAX-ACCESS   read-only
    STATUS       current
    DESCRIPTION
        "Cisco Firepower compute:PCIeFatalCompletionStats:unexpectedErrors
        15Min managed object property"
    ::= { cfprComputePCIeFatalCompletionStatsEntry 31 }

cfprComputePCIeFatalCompletionStatsUnexpectedErrors15MinH OBJECT-TYPE
    SYNTAX       Gauge32
    MAX-ACCESS   read-only
    STATUS       current
    DESCRIPTION
        "Cisco Firepower compute:PCIeFatalCompletionStats:unexpectedErrors
        15MinH managed object property"
    ::= { cfprComputePCIeFatalCompletionStatsEntry 32 }

cfprComputePCIeFatalCompletionStatsUnexpectedErrors1Day OBJECT-TYPE
    SYNTAX       Gauge32
    MAX-ACCESS   read-only
    STATUS       current
    DESCRIPTION
        "Cisco Firepower compute:PCIeFatalCompletionStats:unexpectedErrors
        1Day managed object property"
    ::= { cfprComputePCIeFatalCompletionStatsEntry 33 }

cfprComputePCIeFatalCompletionStatsUnexpectedErrors1DayH OBJECT-TYPE
    SYNTAX       Gauge32
    MAX-ACCESS   read-only
    STATUS       current
    DESCRIPTION
        "Cisco Firepower compute:PCIeFatalCompletionStats:unexpectedErrors
        1DayH managed object property"
    ::= { cfprComputePCIeFatalCompletionStatsEntry 34 }

cfprComputePCIeFatalCompletionStatsUnexpectedErrors1Hour OBJECT-TYPE
    SYNTAX       Gauge32
    MAX-ACCESS   read-only
    STATUS       current
    DESCRIPTION
        "Cisco Firepower compute:PCIeFatalCompletionStats:unexpectedErrors
        1Hour managed object property"
    ::= { cfprComputePCIeFatalCompletionStatsEntry 35 }

cfprComputePCIeFatalCompletionStatsUnexpectedErrors1HourH OBJECT-TYPE
    SYNTAX       Gauge32
    MAX-ACCESS   read-only
    STATUS       current
    DESCRIPTION
        "Cisco Firepower compute:PCIeFatalCompletionStats:unexpectedErrors
        1HourH managed object property"
    ::= { cfprComputePCIeFatalCompletionStatsEntry 36 }

cfprComputePCIeFatalCompletionStatsUnexpectedErrors1Week OBJECT-TYPE
    SYNTAX       Gauge32
    MAX-ACCESS   read-only
    STATUS       current
    DESCRIPTION
        "Cisco Firepower compute:PCIeFatalCompletionStats:unexpectedErrors
        1Week managed object property"
    ::= { cfprComputePCIeFatalCompletionStatsEntry 37 }

cfprComputePCIeFatalCompletionStatsUnexpectedErrors1WeekH OBJECT-TYPE
    SYNTAX       Gauge32
    MAX-ACCESS   read-only
    STATUS       current
    DESCRIPTION
        "Cisco Firepower compute:PCIeFatalCompletionStats:unexpectedErrors
        1WeekH managed object property"
    ::= { cfprComputePCIeFatalCompletionStatsEntry 38 }

cfprComputePCIeFatalCompletionStatsUnexpectedErrors2Weeks OBJECT-TYPE
    SYNTAX       Gauge32
    MAX-ACCESS   read-only
    STATUS       current
    DESCRIPTION
        "Cisco Firepower compute:PCIeFatalCompletionStats:unexpectedErrors
        2Weeks managed object property"
    ::= { cfprComputePCIeFatalCompletionStatsEntry 39 }

cfprComputePCIeFatalCompletionStatsUnexpectedErrors2WeeksH OBJECT-TYPE
    SYNTAX       Gauge32
    MAX-ACCESS   read-only
    STATUS       current
    DESCRIPTION
        "Cisco Firepower compute:PCIeFatalCompletionStats:unexpectedErrors
        2WeeksH managed object property"
    ::= { cfprComputePCIeFatalCompletionStatsEntry 40 }

cfprComputePCIeFatalCompletionStatsUpdate OBJECT-TYPE
    SYNTAX       Gauge32
    MAX-ACCESS   read-only
    STATUS       current
    DESCRIPTION
        "Cisco Firepower compute:PCIeFatalCompletionStats:update
        managed object property"
    ::= { cfprComputePCIeFatalCompletionStatsEntry 41 }

cfprComputePCIeFatalProtocolStatsTable OBJECT-TYPE
    SYNTAX           SEQUENCE OF CfprComputePCIeFatalProtocolStatsEntry
    MAX-ACCESS       not-accessible
    STATUS           current
    DESCRIPTION
        "Cisco Firepower compute:PCIeFatalProtocolStats
        managed object table"
    ::= { cfprComputeObjects 30 }

cfprComputePCIeFatalProtocolStatsEntry OBJECT-TYPE
    SYNTAX           CfprComputePCIeFatalProtocolStatsEntry
    MAX-ACCESS       not-accessible
    STATUS           current
    DESCRIPTION
        "Entry for the cfprComputePCIeFatalProtocolStatsTable table."
    INDEX { cfprComputePCIeFatalProtocolStatsInstanceId }
    ::= { cfprComputePCIeFatalProtocolStatsTable 1 }

CfprComputePCIeFatalProtocolStatsEntry ::= SEQUENCE {
    cfprComputePCIeFatalProtocolStatsInstanceId                      CfprManagedObjectId,
    cfprComputePCIeFatalProtocolStatsDn                              CfprManagedObjectDn,
    cfprComputePCIeFatalProtocolStatsRn                              SnmpAdminString,
    cfprComputePCIeFatalProtocolStatsDllpErrors                      Counter32,
    cfprComputePCIeFatalProtocolStatsDllpErrors15Min                 Gauge32,
    cfprComputePCIeFatalProtocolStatsDllpErrors15MinH                Gauge32,
    cfprComputePCIeFatalProtocolStatsDllpErrors1Day                  Gauge32,
    cfprComputePCIeFatalProtocolStatsDllpErrors1DayH                 Gauge32,
    cfprComputePCIeFatalProtocolStatsDllpErrors1Hour                 Gauge32,
    cfprComputePCIeFatalProtocolStatsDllpErrors1HourH                Gauge32,
    cfprComputePCIeFatalProtocolStatsDllpErrors1Week                 Gauge32,
    cfprComputePCIeFatalProtocolStatsDllpErrors1WeekH                Gauge32,
    cfprComputePCIeFatalProtocolStatsDllpErrors2Weeks                Gauge32,
    cfprComputePCIeFatalProtocolStatsDllpErrors2WeeksH               Gauge32,
    cfprComputePCIeFatalProtocolStatsFlowControlErrors               Counter32,
    cfprComputePCIeFatalProtocolStatsFlowControlErrors15Min          Gauge32,
    cfprComputePCIeFatalProtocolStatsFlowControlErrors15MinH         Gauge32,
    cfprComputePCIeFatalProtocolStatsFlowControlErrors1Day           Gauge32,
    cfprComputePCIeFatalProtocolStatsFlowControlErrors1DayH          Gauge32,
    cfprComputePCIeFatalProtocolStatsFlowControlErrors1Hour          Gauge32,
    cfprComputePCIeFatalProtocolStatsFlowControlErrors1HourH         Gauge32,
    cfprComputePCIeFatalProtocolStatsFlowControlErrors1Week          Gauge32,
    cfprComputePCIeFatalProtocolStatsFlowControlErrors1WeekH         Gauge32,
    cfprComputePCIeFatalProtocolStatsFlowControlErrors2Weeks         Gauge32,
    cfprComputePCIeFatalProtocolStatsFlowControlErrors2WeeksH        Gauge32,
    cfprComputePCIeFatalProtocolStatsIntervals                       Gauge32,
    cfprComputePCIeFatalProtocolStatsSuspect                         TruthValue,
    cfprComputePCIeFatalProtocolStatsThresholded                     CfprComputePCIeFatalProtocolStatsThresholded,
    cfprComputePCIeFatalProtocolStatsTimeCollected                   DateAndTime,
    cfprComputePCIeFatalProtocolStatsUpdate                          Gauge32
}

cfprComputePCIeFatalProtocolStatsInstanceId OBJECT-TYPE
    SYNTAX       CfprManagedObjectId
    MAX-ACCESS   not-accessible
    STATUS       current
    DESCRIPTION
        "Instance identifier of the managed object."
    ::= { cfprComputePCIeFatalProtocolStatsEntry 1 }

cfprComputePCIeFatalProtocolStatsDn OBJECT-TYPE
    SYNTAX       CfprManagedObjectDn
    MAX-ACCESS   read-only
    STATUS       current
    DESCRIPTION
        "Cisco Firepower compute:PCIeFatalProtocolStats:dn
        managed object property"
    ::= { cfprComputePCIeFatalProtocolStatsEntry 2 }

cfprComputePCIeFatalProtocolStatsRn OBJECT-TYPE
    SYNTAX       SnmpAdminString
    MAX-ACCESS   read-only
    STATUS       current
    DESCRIPTION
        "Cisco Firepower compute:PCIeFatalProtocolStats:rn
        managed object property"
    ::= { cfprComputePCIeFatalProtocolStatsEntry 3 }

cfprComputePCIeFatalProtocolStatsDllpErrors OBJECT-TYPE
    SYNTAX       Counter32
    MAX-ACCESS   read-only
    STATUS       current
    DESCRIPTION
        "Cisco Firepower compute:PCIeFatalProtocolStats:dllpErrors
        managed object property"
    ::= { cfprComputePCIeFatalProtocolStatsEntry 4 }

cfprComputePCIeFatalProtocolStatsDllpErrors15Min OBJECT-TYPE
    SYNTAX       Gauge32
    MAX-ACCESS   read-only
    STATUS       current
    DESCRIPTION
        "Cisco Firepower compute:PCIeFatalProtocolStats:dllpErrors15Min
        managed object property"
    ::= { cfprComputePCIeFatalProtocolStatsEntry 5 }

cfprComputePCIeFatalProtocolStatsDllpErrors15MinH OBJECT-TYPE
    SYNTAX       Gauge32
    MAX-ACCESS   read-only
    STATUS       current
    DESCRIPTION
        "Cisco Firepower compute:PCIeFatalProtocolStats:dllpErrors15MinH
        managed object property"
    ::= { cfprComputePCIeFatalProtocolStatsEntry 6 }

cfprComputePCIeFatalProtocolStatsDllpErrors1Day OBJECT-TYPE
    SYNTAX       Gauge32
    MAX-ACCESS   read-only
    STATUS       current
    DESCRIPTION
        "Cisco Firepower compute:PCIeFatalProtocolStats:dllpErrors1Day
        managed object property"
    ::= { cfprComputePCIeFatalProtocolStatsEntry 7 }

cfprComputePCIeFatalProtocolStatsDllpErrors1DayH OBJECT-TYPE
    SYNTAX       Gauge32
    MAX-ACCESS   read-only
    STATUS       current
    DESCRIPTION
        "Cisco Firepower compute:PCIeFatalProtocolStats:dllpErrors1DayH
        managed object property"
    ::= { cfprComputePCIeFatalProtocolStatsEntry 8 }

cfprComputePCIeFatalProtocolStatsDllpErrors1Hour OBJECT-TYPE
    SYNTAX       Gauge32
    MAX-ACCESS   read-only
    STATUS       current
    DESCRIPTION
        "Cisco Firepower compute:PCIeFatalProtocolStats:dllpErrors1Hour
        managed object property"
    ::= { cfprComputePCIeFatalProtocolStatsEntry 9 }

cfprComputePCIeFatalProtocolStatsDllpErrors1HourH OBJECT-TYPE
    SYNTAX       Gauge32
    MAX-ACCESS   read-only
    STATUS       current
    DESCRIPTION
        "Cisco Firepower compute:PCIeFatalProtocolStats:dllpErrors1HourH
        managed object property"
    ::= { cfprComputePCIeFatalProtocolStatsEntry 10 }

cfprComputePCIeFatalProtocolStatsDllpErrors1Week OBJECT-TYPE
    SYNTAX       Gauge32
    MAX-ACCESS   read-only
    STATUS       current
    DESCRIPTION
        "Cisco Firepower compute:PCIeFatalProtocolStats:dllpErrors1Week
        managed object property"
    ::= { cfprComputePCIeFatalProtocolStatsEntry 11 }

cfprComputePCIeFatalProtocolStatsDllpErrors1WeekH OBJECT-TYPE
    SYNTAX       Gauge32
    MAX-ACCESS   read-only
    STATUS       current
    DESCRIPTION
        "Cisco Firepower compute:PCIeFatalProtocolStats:dllpErrors1WeekH
        managed object property"
    ::= { cfprComputePCIeFatalProtocolStatsEntry 12 }

cfprComputePCIeFatalProtocolStatsDllpErrors2Weeks OBJECT-TYPE
    SYNTAX       Gauge32
    MAX-ACCESS   read-only
    STATUS       current
    DESCRIPTION
        "Cisco Firepower compute:PCIeFatalProtocolStats:dllpErrors2Weeks
        managed object property"
    ::= { cfprComputePCIeFatalProtocolStatsEntry 13 }

cfprComputePCIeFatalProtocolStatsDllpErrors2WeeksH OBJECT-TYPE
    SYNTAX       Gauge32
    MAX-ACCESS   read-only
    STATUS       current
    DESCRIPTION
        "Cisco Firepower compute:PCIeFatalProtocolStats:dllpErrors2WeeksH
        managed object property"
    ::= { cfprComputePCIeFatalProtocolStatsEntry 14 }

cfprComputePCIeFatalProtocolStatsFlowControlErrors OBJECT-TYPE
    SYNTAX       Counter32
    MAX-ACCESS   read-only
    STATUS       current
    DESCRIPTION
        "Cisco Firepower compute:PCIeFatalProtocolStats:flowControlErrors
        managed object property"
    ::= { cfprComputePCIeFatalProtocolStatsEntry 15 }

cfprComputePCIeFatalProtocolStatsFlowControlErrors15Min OBJECT-TYPE
    SYNTAX       Gauge32
    MAX-ACCESS   read-only
    STATUS       current
    DESCRIPTION
        "Cisco Firepower compute:PCIeFatalProtocolStats:flowControlErrors1
        5Min managed object property"
    ::= { cfprComputePCIeFatalProtocolStatsEntry 16 }

cfprComputePCIeFatalProtocolStatsFlowControlErrors15MinH OBJECT-TYPE
    SYNTAX       Gauge32
    MAX-ACCESS   read-only
    STATUS       current
    DESCRIPTION
        "Cisco Firepower compute:PCIeFatalProtocolStats:flowControlErrors1
        5MinH managed object property"
    ::= { cfprComputePCIeFatalProtocolStatsEntry 17 }

cfprComputePCIeFatalProtocolStatsFlowControlErrors1Day OBJECT-TYPE
    SYNTAX       Gauge32
    MAX-ACCESS   read-only
    STATUS       current
    DESCRIPTION
        "Cisco Firepower compute:PCIeFatalProtocolStats:flowControlErrors1
        Day managed object property"
    ::= { cfprComputePCIeFatalProtocolStatsEntry 18 }

cfprComputePCIeFatalProtocolStatsFlowControlErrors1DayH OBJECT-TYPE
    SYNTAX       Gauge32
    MAX-ACCESS   read-only
    STATUS       current
    DESCRIPTION
        "Cisco Firepower compute:PCIeFatalProtocolStats:flowControlErrors1
        DayH managed object property"
    ::= { cfprComputePCIeFatalProtocolStatsEntry 19 }

cfprComputePCIeFatalProtocolStatsFlowControlErrors1Hour OBJECT-TYPE
    SYNTAX       Gauge32
    MAX-ACCESS   read-only
    STATUS       current
    DESCRIPTION
        "Cisco Firepower compute:PCIeFatalProtocolStats:flowControlErrors1
        Hour managed object property"
    ::= { cfprComputePCIeFatalProtocolStatsEntry 20 }

cfprComputePCIeFatalProtocolStatsFlowControlErrors1HourH OBJECT-TYPE
    SYNTAX       Gauge32
    MAX-ACCESS   read-only
    STATUS       current
    DESCRIPTION
        "Cisco Firepower compute:PCIeFatalProtocolStats:flowControlErrors1
        HourH managed object property"
    ::= { cfprComputePCIeFatalProtocolStatsEntry 21 }

cfprComputePCIeFatalProtocolStatsFlowControlErrors1Week OBJECT-TYPE
    SYNTAX       Gauge32
    MAX-ACCESS   read-only
    STATUS       current
    DESCRIPTION
        "Cisco Firepower compute:PCIeFatalProtocolStats:flowControlErrors1
        Week managed object property"
    ::= { cfprComputePCIeFatalProtocolStatsEntry 22 }

cfprComputePCIeFatalProtocolStatsFlowControlErrors1WeekH OBJECT-TYPE
    SYNTAX       Gauge32
    MAX-ACCESS   read-only
    STATUS       current
    DESCRIPTION
        "Cisco Firepower compute:PCIeFatalProtocolStats:flowControlErrors1
        WeekH managed object property"
    ::= { cfprComputePCIeFatalProtocolStatsEntry 23 }

cfprComputePCIeFatalProtocolStatsFlowControlErrors2Weeks OBJECT-TYPE
    SYNTAX       Gauge32
    MAX-ACCESS   read-only
    STATUS       current
    DESCRIPTION
        "Cisco Firepower compute:PCIeFatalProtocolStats:flowControlErrors2
        Weeks managed object property"
    ::= { cfprComputePCIeFatalProtocolStatsEntry 24 }

cfprComputePCIeFatalProtocolStatsFlowControlErrors2WeeksH OBJECT-TYPE
    SYNTAX       Gauge32
    MAX-ACCESS   read-only
    STATUS       current
    DESCRIPTION
        "Cisco Firepower compute:PCIeFatalProtocolStats:flowControlErrors2
        WeeksH managed object property"
    ::= { cfprComputePCIeFatalProtocolStatsEntry 25 }

cfprComputePCIeFatalProtocolStatsIntervals OBJECT-TYPE
    SYNTAX       Gauge32
    MAX-ACCESS   read-only
    STATUS       current
    DESCRIPTION
        "Cisco Firepower compute:PCIeFatalProtocolStats:intervals
        managed object property"
    ::= { cfprComputePCIeFatalProtocolStatsEntry 26 }

cfprComputePCIeFatalProtocolStatsSuspect OBJECT-TYPE
    SYNTAX       TruthValue
    MAX-ACCESS   read-only
    STATUS       current
    DESCRIPTION
        "Cisco Firepower compute:PCIeFatalProtocolStats:suspect
        managed object property"
    ::= { cfprComputePCIeFatalProtocolStatsEntry 27 }

cfprComputePCIeFatalProtocolStatsThresholded OBJECT-TYPE
    SYNTAX       CfprComputePCIeFatalProtocolStatsThresholded
    MAX-ACCESS   read-only
    STATUS       current
    DESCRIPTION
        "Cisco Firepower compute:PCIeFatalProtocolStats:thresholded
        managed object property"
    ::= { cfprComputePCIeFatalProtocolStatsEntry 28 }

cfprComputePCIeFatalProtocolStatsTimeCollected OBJECT-TYPE
    SYNTAX       DateAndTime
    MAX-ACCESS   read-only
    STATUS       current
    DESCRIPTION
        "Cisco Firepower compute:PCIeFatalProtocolStats:timeCollected
        managed object property"
    ::= { cfprComputePCIeFatalProtocolStatsEntry 29 }

cfprComputePCIeFatalProtocolStatsUpdate OBJECT-TYPE
    SYNTAX       Gauge32
    MAX-ACCESS   read-only
    STATUS       current
    DESCRIPTION
        "Cisco Firepower compute:PCIeFatalProtocolStats:update
        managed object property"
    ::= { cfprComputePCIeFatalProtocolStatsEntry 30 }

cfprComputePCIeFatalReceiveStatsTable OBJECT-TYPE
    SYNTAX           SEQUENCE OF CfprComputePCIeFatalReceiveStatsEntry
    MAX-ACCESS       not-accessible
    STATUS           current
    DESCRIPTION
        "Cisco Firepower compute:PCIeFatalReceiveStats
        managed object table"
    ::= { cfprComputeObjects 31 }

cfprComputePCIeFatalReceiveStatsEntry OBJECT-TYPE
    SYNTAX           CfprComputePCIeFatalReceiveStatsEntry
    MAX-ACCESS       not-accessible
    STATUS           current
    DESCRIPTION
        "Entry for the cfprComputePCIeFatalReceiveStatsTable table."
    INDEX { cfprComputePCIeFatalReceiveStatsInstanceId }
    ::= { cfprComputePCIeFatalReceiveStatsTable 1 }

CfprComputePCIeFatalReceiveStatsEntry ::= SEQUENCE {
    cfprComputePCIeFatalReceiveStatsInstanceId                       CfprManagedObjectId,
    cfprComputePCIeFatalReceiveStatsDn                               CfprManagedObjectDn,
    cfprComputePCIeFatalReceiveStatsRn                               SnmpAdminString,
    cfprComputePCIeFatalReceiveStatsBufferOverflowErrors             Counter32,
    cfprComputePCIeFatalReceiveStatsBufferOverflowErrors15Min        Gauge32,
    cfprComputePCIeFatalReceiveStatsBufferOverflowErrors15MinH       Gauge32,
    cfprComputePCIeFatalReceiveStatsBufferOverflowErrors1Day         Gauge32,
    cfprComputePCIeFatalReceiveStatsBufferOverflowErrors1DayH        Gauge32,
    cfprComputePCIeFatalReceiveStatsBufferOverflowErrors1Hour        Gauge32,
    cfprComputePCIeFatalReceiveStatsBufferOverflowErrors1HourH       Gauge32,
    cfprComputePCIeFatalReceiveStatsBufferOverflowErrors1Week        Gauge32,
    cfprComputePCIeFatalReceiveStatsBufferOverflowErrors1WeekH       Gauge32,
    cfprComputePCIeFatalReceiveStatsBufferOverflowErrors2Weeks       Gauge32,
    cfprComputePCIeFatalReceiveStatsBufferOverflowErrors2WeeksH      Gauge32,
    cfprComputePCIeFatalReceiveStatsErrFatalErrors                   Counter32,
    cfprComputePCIeFatalReceiveStatsErrFatalErrors15Min              Gauge32,
    cfprComputePCIeFatalReceiveStatsErrFatalErrors15MinH             Gauge32,
    cfprComputePCIeFatalReceiveStatsErrFatalErrors1Day               Gauge32,
    cfprComputePCIeFatalReceiveStatsErrFatalErrors1DayH              Gauge32,
    cfprComputePCIeFatalReceiveStatsErrFatalErrors1Hour              Gauge32,
    cfprComputePCIeFatalReceiveStatsErrFatalErrors1HourH             Gauge32,
    cfprComputePCIeFatalReceiveStatsErrFatalErrors1Week              Gauge32,
    cfprComputePCIeFatalReceiveStatsErrFatalErrors1WeekH             Gauge32,
    cfprComputePCIeFatalReceiveStatsErrFatalErrors2Weeks             Gauge32,
    cfprComputePCIeFatalReceiveStatsErrFatalErrors2WeeksH            Gauge32,
    cfprComputePCIeFatalReceiveStatsErrNonFatalErrors                Counter32,
    cfprComputePCIeFatalReceiveStatsErrNonFatalErrors15Min           Gauge32,
    cfprComputePCIeFatalReceiveStatsErrNonFatalErrors15MinH          Gauge32,
    cfprComputePCIeFatalReceiveStatsErrNonFatalErrors1Day            Gauge32,
    cfprComputePCIeFatalReceiveStatsErrNonFatalErrors1DayH           Gauge32,
    cfprComputePCIeFatalReceiveStatsErrNonFatalErrors1Hour           Gauge32,
    cfprComputePCIeFatalReceiveStatsErrNonFatalErrors1HourH          Gauge32,
    cfprComputePCIeFatalReceiveStatsErrNonFatalErrors1Week           Gauge32,
    cfprComputePCIeFatalReceiveStatsErrNonFatalErrors1WeekH          Gauge32,
    cfprComputePCIeFatalReceiveStatsErrNonFatalErrors2Weeks          Gauge32,
    cfprComputePCIeFatalReceiveStatsErrNonFatalErrors2WeeksH         Gauge32,
    cfprComputePCIeFatalReceiveStatsIntervals                        Gauge32,
    cfprComputePCIeFatalReceiveStatsSuspect                          TruthValue,
    cfprComputePCIeFatalReceiveStatsThresholded                      CfprComputePCIeFatalReceiveStatsThresholded,
    cfprComputePCIeFatalReceiveStatsTimeCollected                    DateAndTime,
    cfprComputePCIeFatalReceiveStatsUnsupportedRequestErrors         Counter32,
    cfprComputePCIeFatalReceiveStatsUnsupportedRequestErrors15Min    Gauge32,
    cfprComputePCIeFatalReceiveStatsUnsupportedRequestErrors15MinH   Gauge32,
    cfprComputePCIeFatalReceiveStatsUnsupportedRequestErrors1Day     Gauge32,
    cfprComputePCIeFatalReceiveStatsUnsupportedRequestErrors1DayH    Gauge32,
    cfprComputePCIeFatalReceiveStatsUnsupportedRequestErrors1Hour    Gauge32,
    cfprComputePCIeFatalReceiveStatsUnsupportedRequestErrors1HourH   Gauge32,
    cfprComputePCIeFatalReceiveStatsUnsupportedRequestErrors1Week    Gauge32,
    cfprComputePCIeFatalReceiveStatsUnsupportedRequestErrors1WeekH   Gauge32,
    cfprComputePCIeFatalReceiveStatsUnsupportedRequestErrors2Weeks   Gauge32,
    cfprComputePCIeFatalReceiveStatsUnsupportedRequestErrors2WeeksH  Gauge32,
    cfprComputePCIeFatalReceiveStatsUpdate                           Gauge32
}

cfprComputePCIeFatalReceiveStatsInstanceId OBJECT-TYPE
    SYNTAX       CfprManagedObjectId
    MAX-ACCESS   not-accessible
    STATUS       current
    DESCRIPTION
        "Instance identifier of the managed object."
    ::= { cfprComputePCIeFatalReceiveStatsEntry 1 }

cfprComputePCIeFatalReceiveStatsDn OBJECT-TYPE
    SYNTAX       CfprManagedObjectDn
    MAX-ACCESS   read-only
    STATUS       current
    DESCRIPTION
        "Cisco Firepower compute:PCIeFatalReceiveStats:dn
        managed object property"
    ::= { cfprComputePCIeFatalReceiveStatsEntry 2 }

cfprComputePCIeFatalReceiveStatsRn OBJECT-TYPE
    SYNTAX       SnmpAdminString
    MAX-ACCESS   read-only
    STATUS       current
    DESCRIPTION
        "Cisco Firepower compute:PCIeFatalReceiveStats:rn
        managed object property"
    ::= { cfprComputePCIeFatalReceiveStatsEntry 3 }

cfprComputePCIeFatalReceiveStatsBufferOverflowErrors OBJECT-TYPE
    SYNTAX       Counter32
    MAX-ACCESS   read-only
    STATUS       current
    DESCRIPTION
        "Cisco Firepower compute:PCIeFatalReceiveStats:bufferOverflowError
        s managed object property"
    ::= { cfprComputePCIeFatalReceiveStatsEntry 4 }

cfprComputePCIeFatalReceiveStatsBufferOverflowErrors15Min OBJECT-TYPE
    SYNTAX       Gauge32
    MAX-ACCESS   read-only
    STATUS       current
    DESCRIPTION
        "Cisco Firepower compute:PCIeFatalReceiveStats:bufferOverflowError
        s15Min managed object property"
    ::= { cfprComputePCIeFatalReceiveStatsEntry 5 }

cfprComputePCIeFatalReceiveStatsBufferOverflowErrors15MinH OBJECT-TYPE
    SYNTAX       Gauge32
    MAX-ACCESS   read-only
    STATUS       current
    DESCRIPTION
        "Cisco Firepower compute:PCIeFatalReceiveStats:bufferOverflowError
        s15MinH managed object property"
    ::= { cfprComputePCIeFatalReceiveStatsEntry 6 }

cfprComputePCIeFatalReceiveStatsBufferOverflowErrors1Day OBJECT-TYPE
    SYNTAX       Gauge32
    MAX-ACCESS   read-only
    STATUS       current
    DESCRIPTION
        "Cisco Firepower compute:PCIeFatalReceiveStats:bufferOverflowError
        s1Day managed object property"
    ::= { cfprComputePCIeFatalReceiveStatsEntry 7 }

cfprComputePCIeFatalReceiveStatsBufferOverflowErrors1DayH OBJECT-TYPE
    SYNTAX       Gauge32
    MAX-ACCESS   read-only
    STATUS       current
    DESCRIPTION
        "Cisco Firepower compute:PCIeFatalReceiveStats:bufferOverflowError
        s1DayH managed object property"
    ::= { cfprComputePCIeFatalReceiveStatsEntry 8 }

cfprComputePCIeFatalReceiveStatsBufferOverflowErrors1Hour OBJECT-TYPE
    SYNTAX       Gauge32
    MAX-ACCESS   read-only
    STATUS       current
    DESCRIPTION
        "Cisco Firepower compute:PCIeFatalReceiveStats:bufferOverflowError
        s1Hour managed object property"
    ::= { cfprComputePCIeFatalReceiveStatsEntry 9 }

cfprComputePCIeFatalReceiveStatsBufferOverflowErrors1HourH OBJECT-TYPE
    SYNTAX       Gauge32
    MAX-ACCESS   read-only
    STATUS       current
    DESCRIPTION
        "Cisco Firepower compute:PCIeFatalReceiveStats:bufferOverflowError
        s1HourH managed object property"
    ::= { cfprComputePCIeFatalReceiveStatsEntry 10 }

cfprComputePCIeFatalReceiveStatsBufferOverflowErrors1Week OBJECT-TYPE
    SYNTAX       Gauge32
    MAX-ACCESS   read-only
    STATUS       current
    DESCRIPTION
        "Cisco Firepower compute:PCIeFatalReceiveStats:bufferOverflowError
        s1Week managed object property"
    ::= { cfprComputePCIeFatalReceiveStatsEntry 11 }

cfprComputePCIeFatalReceiveStatsBufferOverflowErrors1WeekH OBJECT-TYPE
    SYNTAX       Gauge32
    MAX-ACCESS   read-only
    STATUS       current
    DESCRIPTION
        "Cisco Firepower compute:PCIeFatalReceiveStats:bufferOverflowError
        s1WeekH managed object property"
    ::= { cfprComputePCIeFatalReceiveStatsEntry 12 }

cfprComputePCIeFatalReceiveStatsBufferOverflowErrors2Weeks OBJECT-TYPE
    SYNTAX       Gauge32
    MAX-ACCESS   read-only
    STATUS       current
    DESCRIPTION
        "Cisco Firepower compute:PCIeFatalReceiveStats:bufferOverflowError
        s2Weeks managed object property"
    ::= { cfprComputePCIeFatalReceiveStatsEntry 13 }

cfprComputePCIeFatalReceiveStatsBufferOverflowErrors2WeeksH OBJECT-TYPE
    SYNTAX       Gauge32
    MAX-ACCESS   read-only
    STATUS       current
    DESCRIPTION
        "Cisco Firepower compute:PCIeFatalReceiveStats:bufferOverflowError
        s2WeeksH managed object property"
    ::= { cfprComputePCIeFatalReceiveStatsEntry 14 }

cfprComputePCIeFatalReceiveStatsErrFatalErrors OBJECT-TYPE
    SYNTAX       Counter32
    MAX-ACCESS   read-only
    STATUS       current
    DESCRIPTION
        "Cisco Firepower compute:PCIeFatalReceiveStats:errFatalErrors
        managed object property"
    ::= { cfprComputePCIeFatalReceiveStatsEntry 15 }

cfprComputePCIeFatalReceiveStatsErrFatalErrors15Min OBJECT-TYPE
    SYNTAX       Gauge32
    MAX-ACCESS   read-only
    STATUS       current
    DESCRIPTION
        "Cisco Firepower compute:PCIeFatalReceiveStats:errFatalErrors15Min
         managed object property"
    ::= { cfprComputePCIeFatalReceiveStatsEntry 16 }

cfprComputePCIeFatalReceiveStatsErrFatalErrors15MinH OBJECT-TYPE
    SYNTAX       Gauge32
    MAX-ACCESS   read-only
    STATUS       current
    DESCRIPTION
        "Cisco Firepower compute:PCIeFatalReceiveStats:errFatalErrors15Min
        H managed object property"
    ::= { cfprComputePCIeFatalReceiveStatsEntry 17 }

cfprComputePCIeFatalReceiveStatsErrFatalErrors1Day OBJECT-TYPE
    SYNTAX       Gauge32
    MAX-ACCESS   read-only
    STATUS       current
    DESCRIPTION
        "Cisco Firepower compute:PCIeFatalReceiveStats:errFatalErrors1Day
        managed object property"
    ::= { cfprComputePCIeFatalReceiveStatsEntry 18 }

cfprComputePCIeFatalReceiveStatsErrFatalErrors1DayH OBJECT-TYPE
    SYNTAX       Gauge32
    MAX-ACCESS   read-only
    STATUS       current
    DESCRIPTION
        "Cisco Firepower compute:PCIeFatalReceiveStats:errFatalErrors1DayH
         managed object property"
    ::= { cfprComputePCIeFatalReceiveStatsEntry 19 }

cfprComputePCIeFatalReceiveStatsErrFatalErrors1Hour OBJECT-TYPE
    SYNTAX       Gauge32
    MAX-ACCESS   read-only
    STATUS       current
    DESCRIPTION
        "Cisco Firepower compute:PCIeFatalReceiveStats:errFatalErrors1Hour
         managed object property"
    ::= { cfprComputePCIeFatalReceiveStatsEntry 20 }

cfprComputePCIeFatalReceiveStatsErrFatalErrors1HourH OBJECT-TYPE
    SYNTAX       Gauge32
    MAX-ACCESS   read-only
    STATUS       current
    DESCRIPTION
        "Cisco Firepower compute:PCIeFatalReceiveStats:errFatalErrors1Hour
        H managed object property"
    ::= { cfprComputePCIeFatalReceiveStatsEntry 21 }

cfprComputePCIeFatalReceiveStatsErrFatalErrors1Week OBJECT-TYPE
    SYNTAX       Gauge32
    MAX-ACCESS   read-only
    STATUS       current
    DESCRIPTION
        "Cisco Firepower compute:PCIeFatalReceiveStats:errFatalErrors1Week
         managed object property"
    ::= { cfprComputePCIeFatalReceiveStatsEntry 22 }

cfprComputePCIeFatalReceiveStatsErrFatalErrors1WeekH OBJECT-TYPE
    SYNTAX       Gauge32
    MAX-ACCESS   read-only
    STATUS       current
    DESCRIPTION
        "Cisco Firepower compute:PCIeFatalReceiveStats:errFatalErrors1Week
        H managed object property"
    ::= { cfprComputePCIeFatalReceiveStatsEntry 23 }

cfprComputePCIeFatalReceiveStatsErrFatalErrors2Weeks OBJECT-TYPE
    SYNTAX       Gauge32
    MAX-ACCESS   read-only
    STATUS       current
    DESCRIPTION
        "Cisco Firepower compute:PCIeFatalReceiveStats:errFatalErrors2Week
        s managed object property"
    ::= { cfprComputePCIeFatalReceiveStatsEntry 24 }

cfprComputePCIeFatalReceiveStatsErrFatalErrors2WeeksH OBJECT-TYPE
    SYNTAX       Gauge32
    MAX-ACCESS   read-only
    STATUS       current
    DESCRIPTION
        "Cisco Firepower compute:PCIeFatalReceiveStats:errFatalErrors2Week
        sH managed object property"
    ::= { cfprComputePCIeFatalReceiveStatsEntry 25 }

cfprComputePCIeFatalReceiveStatsErrNonFatalErrors OBJECT-TYPE
    SYNTAX       Counter32
    MAX-ACCESS   read-only
    STATUS       current
    DESCRIPTION
        "Cisco Firepower compute:PCIeFatalReceiveStats:errNonFatalErrors
        managed object property"
    ::= { cfprComputePCIeFatalReceiveStatsEntry 26 }

cfprComputePCIeFatalReceiveStatsErrNonFatalErrors15Min OBJECT-TYPE
    SYNTAX       Gauge32
    MAX-ACCESS   read-only
    STATUS       current
    DESCRIPTION
        "Cisco Firepower compute:PCIeFatalReceiveStats:errNonFatalErrors15
        Min managed object property"
    ::= { cfprComputePCIeFatalReceiveStatsEntry 27 }

cfprComputePCIeFatalReceiveStatsErrNonFatalErrors15MinH OBJECT-TYPE
    SYNTAX       Gauge32
    MAX-ACCESS   read-only
    STATUS       current
    DESCRIPTION
        "Cisco Firepower compute:PCIeFatalReceiveStats:errNonFatalErrors15
        MinH managed object property"
    ::= { cfprComputePCIeFatalReceiveStatsEntry 28 }

cfprComputePCIeFatalReceiveStatsErrNonFatalErrors1Day OBJECT-TYPE
    SYNTAX       Gauge32
    MAX-ACCESS   read-only
    STATUS       current
    DESCRIPTION
        "Cisco Firepower compute:PCIeFatalReceiveStats:errNonFatalErrors1D
        ay managed object property"
    ::= { cfprComputePCIeFatalReceiveStatsEntry 29 }

cfprComputePCIeFatalReceiveStatsErrNonFatalErrors1DayH OBJECT-TYPE
    SYNTAX       Gauge32
    MAX-ACCESS   read-only
    STATUS       current
    DESCRIPTION
        "Cisco Firepower compute:PCIeFatalReceiveStats:errNonFatalErrors1D
        ayH managed object property"
    ::= { cfprComputePCIeFatalReceiveStatsEntry 30 }

cfprComputePCIeFatalReceiveStatsErrNonFatalErrors1Hour OBJECT-TYPE
    SYNTAX       Gauge32
    MAX-ACCESS   read-only
    STATUS       current
    DESCRIPTION
        "Cisco Firepower compute:PCIeFatalReceiveStats:errNonFatalErrors1H
        our managed object property"
    ::= { cfprComputePCIeFatalReceiveStatsEntry 31 }

cfprComputePCIeFatalReceiveStatsErrNonFatalErrors1HourH OBJECT-TYPE
    SYNTAX       Gauge32
    MAX-ACCESS   read-only
    STATUS       current
    DESCRIPTION
        "Cisco Firepower compute:PCIeFatalReceiveStats:errNonFatalErrors1H
        ourH managed object property"
    ::= { cfprComputePCIeFatalReceiveStatsEntry 32 }

cfprComputePCIeFatalReceiveStatsErrNonFatalErrors1Week OBJECT-TYPE
    SYNTAX       Gauge32
    MAX-ACCESS   read-only
    STATUS       current
    DESCRIPTION
        "Cisco Firepower compute:PCIeFatalReceiveStats:errNonFatalErrors1W
        eek managed object property"
    ::= { cfprComputePCIeFatalReceiveStatsEntry 33 }

cfprComputePCIeFatalReceiveStatsErrNonFatalErrors1WeekH OBJECT-TYPE
    SYNTAX       Gauge32
    MAX-ACCESS   read-only
    STATUS       current
    DESCRIPTION
        "Cisco Firepower compute:PCIeFatalReceiveStats:errNonFatalErrors1W
        eekH managed object property"
    ::= { cfprComputePCIeFatalReceiveStatsEntry 34 }

cfprComputePCIeFatalReceiveStatsErrNonFatalErrors2Weeks OBJECT-TYPE
    SYNTAX       Gauge32
    MAX-ACCESS   read-only
    STATUS       current
    DESCRIPTION
        "Cisco Firepower compute:PCIeFatalReceiveStats:errNonFatalErrors2W
        eeks managed object property"
    ::= { cfprComputePCIeFatalReceiveStatsEntry 35 }

cfprComputePCIeFatalReceiveStatsErrNonFatalErrors2WeeksH OBJECT-TYPE
    SYNTAX       Gauge32
    MAX-ACCESS   read-only
    STATUS       current
    DESCRIPTION
        "Cisco Firepower compute:PCIeFatalReceiveStats:errNonFatalErrors2W
        eeksH managed object property"
    ::= { cfprComputePCIeFatalReceiveStatsEntry 36 }

cfprComputePCIeFatalReceiveStatsIntervals OBJECT-TYPE
    SYNTAX       Gauge32
    MAX-ACCESS   read-only
    STATUS       current
    DESCRIPTION
        "Cisco Firepower compute:PCIeFatalReceiveStats:intervals
        managed object property"
    ::= { cfprComputePCIeFatalReceiveStatsEntry 37 }

cfprComputePCIeFatalReceiveStatsSuspect OBJECT-TYPE
    SYNTAX       TruthValue
    MAX-ACCESS   read-only
    STATUS       current
    DESCRIPTION
        "Cisco Firepower compute:PCIeFatalReceiveStats:suspect
        managed object property"
    ::= { cfprComputePCIeFatalReceiveStatsEntry 38 }

cfprComputePCIeFatalReceiveStatsThresholded OBJECT-TYPE
    SYNTAX       CfprComputePCIeFatalReceiveStatsThresholded
    MAX-ACCESS   read-only
    STATUS       current
    DESCRIPTION
        "Cisco Firepower compute:PCIeFatalReceiveStats:thresholded
        managed object property"
    ::= { cfprComputePCIeFatalReceiveStatsEntry 39 }

cfprComputePCIeFatalReceiveStatsTimeCollected OBJECT-TYPE
    SYNTAX       DateAndTime
    MAX-ACCESS   read-only
    STATUS       current
    DESCRIPTION
        "Cisco Firepower compute:PCIeFatalReceiveStats:timeCollected
        managed object property"
    ::= { cfprComputePCIeFatalReceiveStatsEntry 40 }

cfprComputePCIeFatalReceiveStatsUnsupportedRequestErrors OBJECT-TYPE
    SYNTAX       Counter32
    MAX-ACCESS   read-only
    STATUS       current
    DESCRIPTION
        "Cisco Firepower compute:PCIeFatalReceiveStats:unsupportedRequestE
        rrors managed object property"
    ::= { cfprComputePCIeFatalReceiveStatsEntry 41 }

cfprComputePCIeFatalReceiveStatsUnsupportedRequestErrors15Min OBJECT-TYPE
    SYNTAX       Gauge32
    MAX-ACCESS   read-only
    STATUS       current
    DESCRIPTION
        "Cisco Firepower compute:PCIeFatalReceiveStats:unsupportedRequestE
        rrors15Min managed object property"
    ::= { cfprComputePCIeFatalReceiveStatsEntry 42 }

cfprComputePCIeFatalReceiveStatsUnsupportedRequestErrors15MinH OBJECT-TYPE
    SYNTAX       Gauge32
    MAX-ACCESS   read-only
    STATUS       current
    DESCRIPTION
        "Cisco Firepower compute:PCIeFatalReceiveStats:unsupportedRequestE
        rrors15MinH managed object property"
    ::= { cfprComputePCIeFatalReceiveStatsEntry 43 }

cfprComputePCIeFatalReceiveStatsUnsupportedRequestErrors1Day OBJECT-TYPE
    SYNTAX       Gauge32
    MAX-ACCESS   read-only
    STATUS       current
    DESCRIPTION
        "Cisco Firepower compute:PCIeFatalReceiveStats:unsupportedRequestE
        rrors1Day managed object property"
    ::= { cfprComputePCIeFatalReceiveStatsEntry 44 }

cfprComputePCIeFatalReceiveStatsUnsupportedRequestErrors1DayH OBJECT-TYPE
    SYNTAX       Gauge32
    MAX-ACCESS   read-only
    STATUS       current
    DESCRIPTION
        "Cisco Firepower compute:PCIeFatalReceiveStats:unsupportedRequestE
        rrors1DayH managed object property"
    ::= { cfprComputePCIeFatalReceiveStatsEntry 45 }

cfprComputePCIeFatalReceiveStatsUnsupportedRequestErrors1Hour OBJECT-TYPE
    SYNTAX       Gauge32
    MAX-ACCESS   read-only
    STATUS       current
    DESCRIPTION
        "Cisco Firepower compute:PCIeFatalReceiveStats:unsupportedRequestE
        rrors1Hour managed object property"
    ::= { cfprComputePCIeFatalReceiveStatsEntry 46 }

cfprComputePCIeFatalReceiveStatsUnsupportedRequestErrors1HourH OBJECT-TYPE
    SYNTAX       Gauge32
    MAX-ACCESS   read-only
    STATUS       current
    DESCRIPTION
        "Cisco Firepower compute:PCIeFatalReceiveStats:unsupportedRequestE
        rrors1HourH managed object property"
    ::= { cfprComputePCIeFatalReceiveStatsEntry 47 }

cfprComputePCIeFatalReceiveStatsUnsupportedRequestErrors1Week OBJECT-TYPE
    SYNTAX       Gauge32
    MAX-ACCESS   read-only
    STATUS       current
    DESCRIPTION
        "Cisco Firepower compute:PCIeFatalReceiveStats:unsupportedRequestE
        rrors1Week managed object property"
    ::= { cfprComputePCIeFatalReceiveStatsEntry 48 }

cfprComputePCIeFatalReceiveStatsUnsupportedRequestErrors1WeekH OBJECT-TYPE
    SYNTAX       Gauge32
    MAX-ACCESS   read-only
    STATUS       current
    DESCRIPTION
        "Cisco Firepower compute:PCIeFatalReceiveStats:unsupportedRequestE
        rrors1WeekH managed object property"
    ::= { cfprComputePCIeFatalReceiveStatsEntry 49 }

cfprComputePCIeFatalReceiveStatsUnsupportedRequestErrors2Weeks OBJECT-TYPE
    SYNTAX       Gauge32
    MAX-ACCESS   read-only
    STATUS       current
    DESCRIPTION
        "Cisco Firepower compute:PCIeFatalReceiveStats:unsupportedRequestE
        rrors2Weeks managed object property"
    ::= { cfprComputePCIeFatalReceiveStatsEntry 50 }

cfprComputePCIeFatalReceiveStatsUnsupportedRequestErrors2WeeksH OBJECT-TYPE
    SYNTAX       Gauge32
    MAX-ACCESS   read-only
    STATUS       current
    DESCRIPTION
        "Cisco Firepower compute:PCIeFatalReceiveStats:unsupportedRequestE
        rrors2WeeksH managed object property"
    ::= { cfprComputePCIeFatalReceiveStatsEntry 51 }

cfprComputePCIeFatalReceiveStatsUpdate OBJECT-TYPE
    SYNTAX       Gauge32
    MAX-ACCESS   read-only
    STATUS       current
    DESCRIPTION
        "Cisco Firepower compute:PCIeFatalReceiveStats:update
        managed object property"
    ::= { cfprComputePCIeFatalReceiveStatsEntry 52 }

cfprComputePCIeFatalStatsTable OBJECT-TYPE
    SYNTAX           SEQUENCE OF CfprComputePCIeFatalStatsEntry
    MAX-ACCESS       not-accessible
    STATUS           current
    DESCRIPTION
        "Cisco Firepower compute:PCIeFatalStats managed object table"
    ::= { cfprComputeObjects 32 }

cfprComputePCIeFatalStatsEntry OBJECT-TYPE
    SYNTAX           CfprComputePCIeFatalStatsEntry
    MAX-ACCESS       not-accessible
    STATUS           current
    DESCRIPTION
        "Entry for the cfprComputePCIeFatalStatsTable table."
    INDEX { cfprComputePCIeFatalStatsInstanceId }
    ::= { cfprComputePCIeFatalStatsTable 1 }

CfprComputePCIeFatalStatsEntry ::= SEQUENCE {
    cfprComputePCIeFatalStatsInstanceId                              CfprManagedObjectId,
    cfprComputePCIeFatalStatsDn                                      CfprManagedObjectDn,
    cfprComputePCIeFatalStatsRn                                      SnmpAdminString,
    cfprComputePCIeFatalStatsAcsViolationErrors                      Counter32,
    cfprComputePCIeFatalStatsAcsViolationErrors15Min                 Gauge32,
    cfprComputePCIeFatalStatsAcsViolationErrors15MinH                Gauge32,
    cfprComputePCIeFatalStatsAcsViolationErrors1Day                  Gauge32,
    cfprComputePCIeFatalStatsAcsViolationErrors1DayH                 Gauge32,
    cfprComputePCIeFatalStatsAcsViolationErrors1Hour                 Gauge32,
    cfprComputePCIeFatalStatsAcsViolationErrors1HourH                Gauge32,
    cfprComputePCIeFatalStatsAcsViolationErrors1Week                 Gauge32,
    cfprComputePCIeFatalStatsAcsViolationErrors1WeekH                Gauge32,
    cfprComputePCIeFatalStatsAcsViolationErrors2Weeks                Gauge32,
    cfprComputePCIeFatalStatsAcsViolationErrors2WeeksH               Gauge32,
    cfprComputePCIeFatalStatsIntervals                               Gauge32,
    cfprComputePCIeFatalStatsMalformedTLPErrors                      Counter32,
    cfprComputePCIeFatalStatsMalformedTLPErrors15Min                 Gauge32,
    cfprComputePCIeFatalStatsMalformedTLPErrors15MinH                Gauge32,
    cfprComputePCIeFatalStatsMalformedTLPErrors1Day                  Gauge32,
    cfprComputePCIeFatalStatsMalformedTLPErrors1DayH                 Gauge32,
    cfprComputePCIeFatalStatsMalformedTLPErrors1Hour                 Gauge32,
    cfprComputePCIeFatalStatsMalformedTLPErrors1HourH                Gauge32,
    cfprComputePCIeFatalStatsMalformedTLPErrors1Week                 Gauge32,
    cfprComputePCIeFatalStatsMalformedTLPErrors1WeekH                Gauge32,
    cfprComputePCIeFatalStatsMalformedTLPErrors2Weeks                Gauge32,
    cfprComputePCIeFatalStatsMalformedTLPErrors2WeeksH               Gauge32,
    cfprComputePCIeFatalStatsPoisonedTLPErrors                       Counter32,
    cfprComputePCIeFatalStatsPoisonedTLPErrors15Min                  Gauge32,
    cfprComputePCIeFatalStatsPoisonedTLPErrors15MinH                 Gauge32,
    cfprComputePCIeFatalStatsPoisonedTLPErrors1Day                   Gauge32,
    cfprComputePCIeFatalStatsPoisonedTLPErrors1DayH                  Gauge32,
    cfprComputePCIeFatalStatsPoisonedTLPErrors1Hour                  Gauge32,
    cfprComputePCIeFatalStatsPoisonedTLPErrors1HourH                 Gauge32,
    cfprComputePCIeFatalStatsPoisonedTLPErrors1Week                  Gauge32,
    cfprComputePCIeFatalStatsPoisonedTLPErrors1WeekH                 Gauge32,
    cfprComputePCIeFatalStatsPoisonedTLPErrors2Weeks                 Gauge32,
    cfprComputePCIeFatalStatsPoisonedTLPErrors2WeeksH                Gauge32,
    cfprComputePCIeFatalStatsSurpriseLinkDownErrors                  Counter32,
    cfprComputePCIeFatalStatsSurpriseLinkDownErrors15Min             Gauge32,
    cfprComputePCIeFatalStatsSurpriseLinkDownErrors15MinH            Gauge32,
    cfprComputePCIeFatalStatsSurpriseLinkDownErrors1Day              Gauge32,
    cfprComputePCIeFatalStatsSurpriseLinkDownErrors1DayH             Gauge32,
    cfprComputePCIeFatalStatsSurpriseLinkDownErrors1Hour             Gauge32,
    cfprComputePCIeFatalStatsSurpriseLinkDownErrors1HourH            Gauge32,
    cfprComputePCIeFatalStatsSurpriseLinkDownErrors1Week             Gauge32,
    cfprComputePCIeFatalStatsSurpriseLinkDownErrors1WeekH            Gauge32,
    cfprComputePCIeFatalStatsSurpriseLinkDownErrors2Weeks            Gauge32,
    cfprComputePCIeFatalStatsSurpriseLinkDownErrors2WeeksH           Gauge32,
    cfprComputePCIeFatalStatsSuspect                                 TruthValue,
    cfprComputePCIeFatalStatsThresholded                             CfprComputePCIeFatalStatsThresholded,
    cfprComputePCIeFatalStatsTimeCollected                           DateAndTime,
    cfprComputePCIeFatalStatsUpdate                                  Gauge32
}

cfprComputePCIeFatalStatsInstanceId OBJECT-TYPE
    SYNTAX       CfprManagedObjectId
    MAX-ACCESS   not-accessible
    STATUS       current
    DESCRIPTION
        "Instance identifier of the managed object."
    ::= { cfprComputePCIeFatalStatsEntry 1 }

cfprComputePCIeFatalStatsDn OBJECT-TYPE
    SYNTAX       CfprManagedObjectDn
    MAX-ACCESS   read-only
    STATUS       current
    DESCRIPTION
        "Cisco Firepower compute:PCIeFatalStats:dn managed
        object property"
    ::= { cfprComputePCIeFatalStatsEntry 2 }

cfprComputePCIeFatalStatsRn OBJECT-TYPE
    SYNTAX       SnmpAdminString
    MAX-ACCESS   read-only
    STATUS       current
    DESCRIPTION
        "Cisco Firepower compute:PCIeFatalStats:rn managed
        object property"
    ::= { cfprComputePCIeFatalStatsEntry 3 }

cfprComputePCIeFatalStatsAcsViolationErrors OBJECT-TYPE
    SYNTAX       Counter32
    MAX-ACCESS   read-only
    STATUS       current
    DESCRIPTION
        "Cisco Firepower compute:PCIeFatalStats:acsViolationErrors
        managed object property"
    ::= { cfprComputePCIeFatalStatsEntry 4 }

cfprComputePCIeFatalStatsAcsViolationErrors15Min OBJECT-TYPE
    SYNTAX       Gauge32
    MAX-ACCESS   read-only
    STATUS       current
    DESCRIPTION
        "Cisco Firepower compute:PCIeFatalStats:acsViolationErrors15Min
        managed object property"
    ::= { cfprComputePCIeFatalStatsEntry 5 }

cfprComputePCIeFatalStatsAcsViolationErrors15MinH OBJECT-TYPE
    SYNTAX       Gauge32
    MAX-ACCESS   read-only
    STATUS       current
    DESCRIPTION
        "Cisco Firepower compute:PCIeFatalStats:acsViolationErrors15MinH
        managed object property"
    ::= { cfprComputePCIeFatalStatsEntry 6 }

cfprComputePCIeFatalStatsAcsViolationErrors1Day OBJECT-TYPE
    SYNTAX       Gauge32
    MAX-ACCESS   read-only
    STATUS       current
    DESCRIPTION
        "Cisco Firepower compute:PCIeFatalStats:acsViolationErrors1Day
        managed object property"
    ::= { cfprComputePCIeFatalStatsEntry 7 }

cfprComputePCIeFatalStatsAcsViolationErrors1DayH OBJECT-TYPE
    SYNTAX       Gauge32
    MAX-ACCESS   read-only
    STATUS       current
    DESCRIPTION
        "Cisco Firepower compute:PCIeFatalStats:acsViolationErrors1DayH
        managed object property"
    ::= { cfprComputePCIeFatalStatsEntry 8 }

cfprComputePCIeFatalStatsAcsViolationErrors1Hour OBJECT-TYPE
    SYNTAX       Gauge32
    MAX-ACCESS   read-only
    STATUS       current
    DESCRIPTION
        "Cisco Firepower compute:PCIeFatalStats:acsViolationErrors1Hour
        managed object property"
    ::= { cfprComputePCIeFatalStatsEntry 9 }

cfprComputePCIeFatalStatsAcsViolationErrors1HourH OBJECT-TYPE
    SYNTAX       Gauge32
    MAX-ACCESS   read-only
    STATUS       current
    DESCRIPTION
        "Cisco Firepower compute:PCIeFatalStats:acsViolationErrors1HourH
        managed object property"
    ::= { cfprComputePCIeFatalStatsEntry 10 }

cfprComputePCIeFatalStatsAcsViolationErrors1Week OBJECT-TYPE
    SYNTAX       Gauge32
    MAX-ACCESS   read-only
    STATUS       current
    DESCRIPTION
        "Cisco Firepower compute:PCIeFatalStats:acsViolationErrors1Week
        managed object property"
    ::= { cfprComputePCIeFatalStatsEntry 11 }

cfprComputePCIeFatalStatsAcsViolationErrors1WeekH OBJECT-TYPE
    SYNTAX       Gauge32
    MAX-ACCESS   read-only
    STATUS       current
    DESCRIPTION
        "Cisco Firepower compute:PCIeFatalStats:acsViolationErrors1WeekH
        managed object property"
    ::= { cfprComputePCIeFatalStatsEntry 12 }

cfprComputePCIeFatalStatsAcsViolationErrors2Weeks OBJECT-TYPE
    SYNTAX       Gauge32
    MAX-ACCESS   read-only
    STATUS       current
    DESCRIPTION
        "Cisco Firepower compute:PCIeFatalStats:acsViolationErrors2Weeks
        managed object property"
    ::= { cfprComputePCIeFatalStatsEntry 13 }

cfprComputePCIeFatalStatsAcsViolationErrors2WeeksH OBJECT-TYPE
    SYNTAX       Gauge32
    MAX-ACCESS   read-only
    STATUS       current
    DESCRIPTION
        "Cisco Firepower compute:PCIeFatalStats:acsViolationErrors2WeeksH
        managed object property"
    ::= { cfprComputePCIeFatalStatsEntry 14 }

cfprComputePCIeFatalStatsIntervals OBJECT-TYPE
    SYNTAX       Gauge32
    MAX-ACCESS   read-only
    STATUS       current
    DESCRIPTION
        "Cisco Firepower compute:PCIeFatalStats:intervals
        managed object property"
    ::= { cfprComputePCIeFatalStatsEntry 15 }

cfprComputePCIeFatalStatsMalformedTLPErrors OBJECT-TYPE
    SYNTAX       Counter32
    MAX-ACCESS   read-only
    STATUS       current
    DESCRIPTION
        "Cisco Firepower compute:PCIeFatalStats:malformedTLPErrors
        managed object property"
    ::= { cfprComputePCIeFatalStatsEntry 16 }

cfprComputePCIeFatalStatsMalformedTLPErrors15Min OBJECT-TYPE
    SYNTAX       Gauge32
    MAX-ACCESS   read-only
    STATUS       current
    DESCRIPTION
        "Cisco Firepower compute:PCIeFatalStats:malformedTLPErrors15Min
        managed object property"
    ::= { cfprComputePCIeFatalStatsEntry 17 }

cfprComputePCIeFatalStatsMalformedTLPErrors15MinH OBJECT-TYPE
    SYNTAX       Gauge32
    MAX-ACCESS   read-only
    STATUS       current
    DESCRIPTION
        "Cisco Firepower compute:PCIeFatalStats:malformedTLPErrors15MinH
        managed object property"
    ::= { cfprComputePCIeFatalStatsEntry 18 }

cfprComputePCIeFatalStatsMalformedTLPErrors1Day OBJECT-TYPE
    SYNTAX       Gauge32
    MAX-ACCESS   read-only
    STATUS       current
    DESCRIPTION
        "Cisco Firepower compute:PCIeFatalStats:malformedTLPErrors1Day
        managed object property"
    ::= { cfprComputePCIeFatalStatsEntry 19 }

cfprComputePCIeFatalStatsMalformedTLPErrors1DayH OBJECT-TYPE
    SYNTAX       Gauge32
    MAX-ACCESS   read-only
    STATUS       current
    DESCRIPTION
        "Cisco Firepower compute:PCIeFatalStats:malformedTLPErrors1DayH
        managed object property"
    ::= { cfprComputePCIeFatalStatsEntry 20 }

cfprComputePCIeFatalStatsMalformedTLPErrors1Hour OBJECT-TYPE
    SYNTAX       Gauge32
    MAX-ACCESS   read-only
    STATUS       current
    DESCRIPTION
        "Cisco Firepower compute:PCIeFatalStats:malformedTLPErrors1Hour
        managed object property"
    ::= { cfprComputePCIeFatalStatsEntry 21 }

cfprComputePCIeFatalStatsMalformedTLPErrors1HourH OBJECT-TYPE
    SYNTAX       Gauge32
    MAX-ACCESS   read-only
    STATUS       current
    DESCRIPTION
        "Cisco Firepower compute:PCIeFatalStats:malformedTLPErrors1HourH
        managed object property"
    ::= { cfprComputePCIeFatalStatsEntry 22 }

cfprComputePCIeFatalStatsMalformedTLPErrors1Week OBJECT-TYPE
    SYNTAX       Gauge32
    MAX-ACCESS   read-only
    STATUS       current
    DESCRIPTION
        "Cisco Firepower compute:PCIeFatalStats:malformedTLPErrors1Week
        managed object property"
    ::= { cfprComputePCIeFatalStatsEntry 23 }

cfprComputePCIeFatalStatsMalformedTLPErrors1WeekH OBJECT-TYPE
    SYNTAX       Gauge32
    MAX-ACCESS   read-only
    STATUS       current
    DESCRIPTION
        "Cisco Firepower compute:PCIeFatalStats:malformedTLPErrors1WeekH
        managed object property"
    ::= { cfprComputePCIeFatalStatsEntry 24 }

cfprComputePCIeFatalStatsMalformedTLPErrors2Weeks OBJECT-TYPE
    SYNTAX       Gauge32
    MAX-ACCESS   read-only
    STATUS       current
    DESCRIPTION
        "Cisco Firepower compute:PCIeFatalStats:malformedTLPErrors2Weeks
        managed object property"
    ::= { cfprComputePCIeFatalStatsEntry 25 }

cfprComputePCIeFatalStatsMalformedTLPErrors2WeeksH OBJECT-TYPE
    SYNTAX       Gauge32
    MAX-ACCESS   read-only
    STATUS       current
    DESCRIPTION
        "Cisco Firepower compute:PCIeFatalStats:malformedTLPErrors2WeeksH
        managed object property"
    ::= { cfprComputePCIeFatalStatsEntry 26 }

cfprComputePCIeFatalStatsPoisonedTLPErrors OBJECT-TYPE
    SYNTAX       Counter32
    MAX-ACCESS   read-only
    STATUS       current
    DESCRIPTION
        "Cisco Firepower compute:PCIeFatalStats:poisonedTLPErrors
        managed object property"
    ::= { cfprComputePCIeFatalStatsEntry 27 }

cfprComputePCIeFatalStatsPoisonedTLPErrors15Min OBJECT-TYPE
    SYNTAX       Gauge32
    MAX-ACCESS   read-only
    STATUS       current
    DESCRIPTION
        "Cisco Firepower compute:PCIeFatalStats:poisonedTLPErrors15Min
        managed object property"
    ::= { cfprComputePCIeFatalStatsEntry 28 }

cfprComputePCIeFatalStatsPoisonedTLPErrors15MinH OBJECT-TYPE
    SYNTAX       Gauge32
    MAX-ACCESS   read-only
    STATUS       current
    DESCRIPTION
        "Cisco Firepower compute:PCIeFatalStats:poisonedTLPErrors15MinH
        managed object property"
    ::= { cfprComputePCIeFatalStatsEntry 29 }

cfprComputePCIeFatalStatsPoisonedTLPErrors1Day OBJECT-TYPE
    SYNTAX       Gauge32
    MAX-ACCESS   read-only
    STATUS       current
    DESCRIPTION
        "Cisco Firepower compute:PCIeFatalStats:poisonedTLPErrors1Day
        managed object property"
    ::= { cfprComputePCIeFatalStatsEntry 30 }

cfprComputePCIeFatalStatsPoisonedTLPErrors1DayH OBJECT-TYPE
    SYNTAX       Gauge32
    MAX-ACCESS   read-only
    STATUS       current
    DESCRIPTION
        "Cisco Firepower compute:PCIeFatalStats:poisonedTLPErrors1DayH
        managed object property"
    ::= { cfprComputePCIeFatalStatsEntry 31 }

cfprComputePCIeFatalStatsPoisonedTLPErrors1Hour OBJECT-TYPE
    SYNTAX       Gauge32
    MAX-ACCESS   read-only
    STATUS       current
    DESCRIPTION
        "Cisco Firepower compute:PCIeFatalStats:poisonedTLPErrors1Hour
        managed object property"
    ::= { cfprComputePCIeFatalStatsEntry 32 }

cfprComputePCIeFatalStatsPoisonedTLPErrors1HourH OBJECT-TYPE
    SYNTAX       Gauge32
    MAX-ACCESS   read-only
    STATUS       current
    DESCRIPTION
        "Cisco Firepower compute:PCIeFatalStats:poisonedTLPErrors1HourH
        managed object property"
    ::= { cfprComputePCIeFatalStatsEntry 33 }

cfprComputePCIeFatalStatsPoisonedTLPErrors1Week OBJECT-TYPE
    SYNTAX       Gauge32
    MAX-ACCESS   read-only
    STATUS       current
    DESCRIPTION
        "Cisco Firepower compute:PCIeFatalStats:poisonedTLPErrors1Week
        managed object property"
    ::= { cfprComputePCIeFatalStatsEntry 34 }

cfprComputePCIeFatalStatsPoisonedTLPErrors1WeekH OBJECT-TYPE
    SYNTAX       Gauge32
    MAX-ACCESS   read-only
    STATUS       current
    DESCRIPTION
        "Cisco Firepower compute:PCIeFatalStats:poisonedTLPErrors1WeekH
        managed object property"
    ::= { cfprComputePCIeFatalStatsEntry 35 }

cfprComputePCIeFatalStatsPoisonedTLPErrors2Weeks OBJECT-TYPE
    SYNTAX       Gauge32
    MAX-ACCESS   read-only
    STATUS       current
    DESCRIPTION
        "Cisco Firepower compute:PCIeFatalStats:poisonedTLPErrors2Weeks
        managed object property"
    ::= { cfprComputePCIeFatalStatsEntry 36 }

cfprComputePCIeFatalStatsPoisonedTLPErrors2WeeksH OBJECT-TYPE
    SYNTAX       Gauge32
    MAX-ACCESS   read-only
    STATUS       current
    DESCRIPTION
        "Cisco Firepower compute:PCIeFatalStats:poisonedTLPErrors2WeeksH
        managed object property"
    ::= { cfprComputePCIeFatalStatsEntry 37 }

cfprComputePCIeFatalStatsSurpriseLinkDownErrors OBJECT-TYPE
    SYNTAX       Counter32
    MAX-ACCESS   read-only
    STATUS       current
    DESCRIPTION
        "Cisco Firepower compute:PCIeFatalStats:surpriseLinkDownErrors
        managed object property"
    ::= { cfprComputePCIeFatalStatsEntry 38 }

cfprComputePCIeFatalStatsSurpriseLinkDownErrors15Min OBJECT-TYPE
    SYNTAX       Gauge32
    MAX-ACCESS   read-only
    STATUS       current
    DESCRIPTION
        "Cisco Firepower compute:PCIeFatalStats:surpriseLinkDownErrors15Mi
        n managed object property"
    ::= { cfprComputePCIeFatalStatsEntry 39 }

cfprComputePCIeFatalStatsSurpriseLinkDownErrors15MinH OBJECT-TYPE
    SYNTAX       Gauge32
    MAX-ACCESS   read-only
    STATUS       current
    DESCRIPTION
        "Cisco Firepower compute:PCIeFatalStats:surpriseLinkDownErrors15Mi
        nH managed object property"
    ::= { cfprComputePCIeFatalStatsEntry 40 }

cfprComputePCIeFatalStatsSurpriseLinkDownErrors1Day OBJECT-TYPE
    SYNTAX       Gauge32
    MAX-ACCESS   read-only
    STATUS       current
    DESCRIPTION
        "Cisco Firepower compute:PCIeFatalStats:surpriseLinkDownErrors1Day
         managed object property"
    ::= { cfprComputePCIeFatalStatsEntry 41 }

cfprComputePCIeFatalStatsSurpriseLinkDownErrors1DayH OBJECT-TYPE
    SYNTAX       Gauge32
    MAX-ACCESS   read-only
    STATUS       current
    DESCRIPTION
        "Cisco Firepower compute:PCIeFatalStats:surpriseLinkDownErrors1Day
        H managed object property"
    ::= { cfprComputePCIeFatalStatsEntry 42 }

cfprComputePCIeFatalStatsSurpriseLinkDownErrors1Hour OBJECT-TYPE
    SYNTAX       Gauge32
    MAX-ACCESS   read-only
    STATUS       current
    DESCRIPTION
        "Cisco Firepower compute:PCIeFatalStats:surpriseLinkDownErrors1Hou
        r managed object property"
    ::= { cfprComputePCIeFatalStatsEntry 43 }

cfprComputePCIeFatalStatsSurpriseLinkDownErrors1HourH OBJECT-TYPE
    SYNTAX       Gauge32
    MAX-ACCESS   read-only
    STATUS       current
    DESCRIPTION
        "Cisco Firepower compute:PCIeFatalStats:surpriseLinkDownErrors1Hou
        rH managed object property"
    ::= { cfprComputePCIeFatalStatsEntry 44 }

cfprComputePCIeFatalStatsSurpriseLinkDownErrors1Week OBJECT-TYPE
    SYNTAX       Gauge32
    MAX-ACCESS   read-only
    STATUS       current
    DESCRIPTION
        "Cisco Firepower compute:PCIeFatalStats:surpriseLinkDownErrors1Wee
        k managed object property"
    ::= { cfprComputePCIeFatalStatsEntry 45 }

cfprComputePCIeFatalStatsSurpriseLinkDownErrors1WeekH OBJECT-TYPE
    SYNTAX       Gauge32
    MAX-ACCESS   read-only
    STATUS       current
    DESCRIPTION
        "Cisco Firepower compute:PCIeFatalStats:surpriseLinkDownErrors1Wee
        kH managed object property"
    ::= { cfprComputePCIeFatalStatsEntry 46 }

cfprComputePCIeFatalStatsSurpriseLinkDownErrors2Weeks OBJECT-TYPE
    SYNTAX       Gauge32
    MAX-ACCESS   read-only
    STATUS       current
    DESCRIPTION
        "Cisco Firepower compute:PCIeFatalStats:surpriseLinkDownErrors2Wee
        ks managed object property"
    ::= { cfprComputePCIeFatalStatsEntry 47 }

cfprComputePCIeFatalStatsSurpriseLinkDownErrors2WeeksH OBJECT-TYPE
    SYNTAX       Gauge32
    MAX-ACCESS   read-only
    STATUS       current
    DESCRIPTION
        "Cisco Firepower compute:PCIeFatalStats:surpriseLinkDownErrors2Wee
        ksH managed object property"
    ::= { cfprComputePCIeFatalStatsEntry 48 }

cfprComputePCIeFatalStatsSuspect OBJECT-TYPE
    SYNTAX       TruthValue
    MAX-ACCESS   read-only
    STATUS       current
    DESCRIPTION
        "Cisco Firepower compute:PCIeFatalStats:suspect
        managed object property"
    ::= { cfprComputePCIeFatalStatsEntry 49 }

cfprComputePCIeFatalStatsThresholded OBJECT-TYPE
    SYNTAX       CfprComputePCIeFatalStatsThresholded
    MAX-ACCESS   read-only
    STATUS       current
    DESCRIPTION
        "Cisco Firepower compute:PCIeFatalStats:thresholded
        managed object property"
    ::= { cfprComputePCIeFatalStatsEntry 50 }

cfprComputePCIeFatalStatsTimeCollected OBJECT-TYPE
    SYNTAX       DateAndTime
    MAX-ACCESS   read-only
    STATUS       current
    DESCRIPTION
        "Cisco Firepower compute:PCIeFatalStats:timeCollected
        managed object property"
    ::= { cfprComputePCIeFatalStatsEntry 51 }

cfprComputePCIeFatalStatsUpdate OBJECT-TYPE
    SYNTAX       Gauge32
    MAX-ACCESS   read-only
    STATUS       current
    DESCRIPTION
        "Cisco Firepower compute:PCIeFatalStats:update
        managed object property"
    ::= { cfprComputePCIeFatalStatsEntry 52 }

cfprComputePciCapTable OBJECT-TYPE
    SYNTAX           SEQUENCE OF CfprComputePciCapEntry
    MAX-ACCESS       not-accessible
    STATUS           current
    DESCRIPTION
        "Cisco Firepower compute:PciCap managed object table"
    ::= { cfprComputeObjects 33 }

cfprComputePciCapEntry OBJECT-TYPE
    SYNTAX           CfprComputePciCapEntry
    MAX-ACCESS       not-accessible
    STATUS           current
    DESCRIPTION
        "Entry for the cfprComputePciCapTable table."
    INDEX { cfprComputePciCapInstanceId }
    ::= { cfprComputePciCapTable 1 }

CfprComputePciCapEntry ::= SEQUENCE {
    cfprComputePciCapInstanceId                                      CfprManagedObjectId,
    cfprComputePciCapDn                                              CfprManagedObjectDn,
    cfprComputePciCapRn                                              SnmpAdminString,
    cfprComputePciCapMaxBusIdPerSlot                                 Gauge32,
    cfprComputePciCapNumOfPhysSlots                                  Gauge32,
    cfprComputePciCapOrder                                           CfprComputePciCapOrder,
    cfprComputePciCapStartsWith                                      Gauge32
}

cfprComputePciCapInstanceId OBJECT-TYPE
    SYNTAX       CfprManagedObjectId
    MAX-ACCESS   not-accessible
    STATUS       current
    DESCRIPTION
        "Instance identifier of the managed object."
    ::= { cfprComputePciCapEntry 1 }

cfprComputePciCapDn OBJECT-TYPE
    SYNTAX       CfprManagedObjectDn
    MAX-ACCESS   read-only
    STATUS       current
    DESCRIPTION
        "Cisco Firepower compute:PciCap:dn managed object property"
    ::= { cfprComputePciCapEntry 2 }

cfprComputePciCapRn OBJECT-TYPE
    SYNTAX       SnmpAdminString
    MAX-ACCESS   read-only
    STATUS       current
    DESCRIPTION
        "Cisco Firepower compute:PciCap:rn managed object property"
    ::= { cfprComputePciCapEntry 3 }

cfprComputePciCapMaxBusIdPerSlot OBJECT-TYPE
    SYNTAX       Gauge32
    MAX-ACCESS   read-only
    STATUS       current
    DESCRIPTION
        "Cisco Firepower compute:PciCap:maxBusIdPerSlot
        managed object property"
    ::= { cfprComputePciCapEntry 4 }

cfprComputePciCapNumOfPhysSlots OBJECT-TYPE
    SYNTAX       Gauge32
    MAX-ACCESS   read-only
    STATUS       current
    DESCRIPTION
        "Cisco Firepower compute:PciCap:numOfPhysSlots
        managed object property"
    ::= { cfprComputePciCapEntry 5 }

cfprComputePciCapOrder OBJECT-TYPE
    SYNTAX       CfprComputePciCapOrder
    MAX-ACCESS   read-only
    STATUS       current
    DESCRIPTION
        "Cisco Firepower compute:PciCap:order managed object property"
    ::= { cfprComputePciCapEntry 6 }

cfprComputePciCapStartsWith OBJECT-TYPE
    SYNTAX       Gauge32
    MAX-ACCESS   read-only
    STATUS       current
    DESCRIPTION
        "Cisco Firepower compute:PciCap:startsWith managed
        object property"
    ::= { cfprComputePciCapEntry 7 }

cfprComputePciSlotScanDefTable OBJECT-TYPE
    SYNTAX           SEQUENCE OF CfprComputePciSlotScanDefEntry
    MAX-ACCESS       not-accessible
    STATUS           current
    DESCRIPTION
        "Cisco Firepower compute:PciSlotScanDef managed object table"
    ::= { cfprComputeObjects 34 }

cfprComputePciSlotScanDefEntry OBJECT-TYPE
    SYNTAX           CfprComputePciSlotScanDefEntry
    MAX-ACCESS       not-accessible
    STATUS           current
    DESCRIPTION
        "Entry for the cfprComputePciSlotScanDefTable table."
    INDEX { cfprComputePciSlotScanDefInstanceId }
    ::= { cfprComputePciSlotScanDefTable 1 }

CfprComputePciSlotScanDefEntry ::= SEQUENCE {
    cfprComputePciSlotScanDefInstanceId                              CfprManagedObjectId,
    cfprComputePciSlotScanDefDn                                      CfprManagedObjectDn,
    cfprComputePciSlotScanDefRn                                      SnmpAdminString,
    cfprComputePciSlotScanDefDescr                                   SnmpAdminString,
    cfprComputePciSlotScanDefIntId                                   SnmpAdminString,
    cfprComputePciSlotScanDefName                                    SnmpAdminString,
    cfprComputePciSlotScanDefPolicyLevel                             Gauge32,
    cfprComputePciSlotScanDefPolicyOwner                             CfprPolicyPolicyOwner,
    cfprComputePciSlotScanDefScanOrder                               Gauge32,
    cfprComputePciSlotScanDefSlotId                                  Gauge32
}

cfprComputePciSlotScanDefInstanceId OBJECT-TYPE
    SYNTAX       CfprManagedObjectId
    MAX-ACCESS   not-accessible
    STATUS       current
    DESCRIPTION
        "Instance identifier of the managed object."
    ::= { cfprComputePciSlotScanDefEntry 1 }

cfprComputePciSlotScanDefDn OBJECT-TYPE
    SYNTAX       CfprManagedObjectDn
    MAX-ACCESS   read-only
    STATUS       current
    DESCRIPTION
        "Cisco Firepower compute:PciSlotScanDef:dn managed
        object property"
    ::= { cfprComputePciSlotScanDefEntry 2 }

cfprComputePciSlotScanDefRn OBJECT-TYPE
    SYNTAX       SnmpAdminString
    MAX-ACCESS   read-only
    STATUS       current
    DESCRIPTION
        "Cisco Firepower compute:PciSlotScanDef:rn managed
        object property"
    ::= { cfprComputePciSlotScanDefEntry 3 }

cfprComputePciSlotScanDefDescr OBJECT-TYPE
    SYNTAX       SnmpAdminString
    MAX-ACCESS   read-only
    STATUS       current
    DESCRIPTION
        "Cisco Firepower compute:PciSlotScanDef:descr managed
        object property"
    ::= { cfprComputePciSlotScanDefEntry 4 }

cfprComputePciSlotScanDefIntId OBJECT-TYPE
    SYNTAX       SnmpAdminString
    MAX-ACCESS   read-only
    STATUS       current
    DESCRIPTION
        "Cisco Firepower compute:PciSlotScanDef:intId managed
        object property"
    ::= { cfprComputePciSlotScanDefEntry 5 }

cfprComputePciSlotScanDefName OBJECT-TYPE
    SYNTAX       SnmpAdminString
    MAX-ACCESS   read-only
    STATUS       current
    DESCRIPTION
        "Cisco Firepower compute:PciSlotScanDef:name managed
        object property"
    ::= { cfprComputePciSlotScanDefEntry 6 }

cfprComputePciSlotScanDefPolicyLevel OBJECT-TYPE
    SYNTAX       Gauge32
    MAX-ACCESS   read-only
    STATUS       current
    DESCRIPTION
        "Cisco Firepower compute:PciSlotScanDef:policyLevel
        managed object property"
    ::= { cfprComputePciSlotScanDefEntry 7 }

cfprComputePciSlotScanDefPolicyOwner OBJECT-TYPE
    SYNTAX       CfprPolicyPolicyOwner
    MAX-ACCESS   read-only
    STATUS       current
    DESCRIPTION
        "Cisco Firepower compute:PciSlotScanDef:policyOwner
        managed object property"
    ::= { cfprComputePciSlotScanDefEntry 8 }

cfprComputePciSlotScanDefScanOrder OBJECT-TYPE
    SYNTAX       Gauge32
    MAX-ACCESS   read-only
    STATUS       current
    DESCRIPTION
        "Cisco Firepower compute:PciSlotScanDef:scanOrder
        managed object property"
    ::= { cfprComputePciSlotScanDefEntry 9 }

cfprComputePciSlotScanDefSlotId OBJECT-TYPE
    SYNTAX       Gauge32
    MAX-ACCESS   read-only
    STATUS       current
    DESCRIPTION
        "Cisco Firepower compute:PciSlotScanDef:slotId
        managed object property"
    ::= { cfprComputePciSlotScanDefEntry 10 }

cfprComputePhysicalAssocCtxTable OBJECT-TYPE
    SYNTAX           SEQUENCE OF CfprComputePhysicalAssocCtxEntry
    MAX-ACCESS       not-accessible
    STATUS           current
    DESCRIPTION
        "Cisco Firepower compute:PhysicalAssocCtx managed object table"
    ::= { cfprComputeObjects 35 }

cfprComputePhysicalAssocCtxEntry OBJECT-TYPE
    SYNTAX           CfprComputePhysicalAssocCtxEntry
    MAX-ACCESS       not-accessible
    STATUS           current
    DESCRIPTION
        "Entry for the cfprComputePhysicalAssocCtxTable table."
    INDEX { cfprComputePhysicalAssocCtxInstanceId }
    ::= { cfprComputePhysicalAssocCtxTable 1 }

CfprComputePhysicalAssocCtxEntry ::= SEQUENCE {
    cfprComputePhysicalAssocCtxInstanceId                            CfprManagedObjectId,
    cfprComputePhysicalAssocCtxDn                                    CfprManagedObjectDn,
    cfprComputePhysicalAssocCtxRn                                    SnmpAdminString,
    cfprComputePhysicalAssocCtxFruCapDn                              SnmpAdminString
}

cfprComputePhysicalAssocCtxInstanceId OBJECT-TYPE
    SYNTAX       CfprManagedObjectId
    MAX-ACCESS   not-accessible
    STATUS       current
    DESCRIPTION
        "Instance identifier of the managed object."
    ::= { cfprComputePhysicalAssocCtxEntry 1 }

cfprComputePhysicalAssocCtxDn OBJECT-TYPE
    SYNTAX       CfprManagedObjectDn
    MAX-ACCESS   read-only
    STATUS       current
    DESCRIPTION
        "Cisco Firepower compute:PhysicalAssocCtx:dn managed
        object property"
    ::= { cfprComputePhysicalAssocCtxEntry 2 }

cfprComputePhysicalAssocCtxRn OBJECT-TYPE
    SYNTAX       SnmpAdminString
    MAX-ACCESS   read-only
    STATUS       current
    DESCRIPTION
        "Cisco Firepower compute:PhysicalAssocCtx:rn managed
        object property"
    ::= { cfprComputePhysicalAssocCtxEntry 3 }

cfprComputePhysicalAssocCtxFruCapDn OBJECT-TYPE
    SYNTAX       SnmpAdminString
    MAX-ACCESS   read-only
    STATUS       current
    DESCRIPTION
        "Cisco Firepower compute:PhysicalAssocCtx:fruCapDn
        managed object property"
    ::= { cfprComputePhysicalAssocCtxEntry 4 }

cfprComputePhysicalFsmTable OBJECT-TYPE
    SYNTAX           SEQUENCE OF CfprComputePhysicalFsmEntry
    MAX-ACCESS       not-accessible
    STATUS           current
    DESCRIPTION
        "Cisco Firepower compute:PhysicalFsm managed object table"
    ::= { cfprComputeObjects 36 }

cfprComputePhysicalFsmEntry OBJECT-TYPE
    SYNTAX           CfprComputePhysicalFsmEntry
    MAX-ACCESS       not-accessible
    STATUS           current
    DESCRIPTION
        "Entry for the cfprComputePhysicalFsmTable table."
    INDEX { cfprComputePhysicalFsmInstanceId }
    ::= { cfprComputePhysicalFsmTable 1 }

CfprComputePhysicalFsmEntry ::= SEQUENCE {
    cfprComputePhysicalFsmInstanceId                                 CfprManagedObjectId,
    cfprComputePhysicalFsmDn                                         CfprManagedObjectDn,
    cfprComputePhysicalFsmRn                                         SnmpAdminString,
    cfprComputePhysicalFsmCompletionTime                             DateAndTime,
    cfprComputePhysicalFsmCurrentFsm                                 CfprComputePhysicalFsmCurrentFsm,
    cfprComputePhysicalFsmDescr                                      SnmpAdminString,
    cfprComputePhysicalFsmFsmStatus                                  CfprFsmFsmStageStatus,
    cfprComputePhysicalFsmProgress                                   Gauge32,
    cfprComputePhysicalFsmRmtErrCode                                 Gauge32,
    cfprComputePhysicalFsmRmtErrDescr                                SnmpAdminString,
    cfprComputePhysicalFsmRmtRslt                                    CfprConditionRemoteInvRslt
}

cfprComputePhysicalFsmInstanceId OBJECT-TYPE
    SYNTAX       CfprManagedObjectId
    MAX-ACCESS   not-accessible
    STATUS       current
    DESCRIPTION
        "Instance identifier of the managed object."
    ::= { cfprComputePhysicalFsmEntry 1 }

cfprComputePhysicalFsmDn OBJECT-TYPE
    SYNTAX       CfprManagedObjectDn
    MAX-ACCESS   read-only
    STATUS       current
    DESCRIPTION
        "Cisco Firepower compute:PhysicalFsm:dn managed object property"
    ::= { cfprComputePhysicalFsmEntry 2 }

cfprComputePhysicalFsmRn OBJECT-TYPE
    SYNTAX       SnmpAdminString
    MAX-ACCESS   read-only
    STATUS       current
    DESCRIPTION
        "Cisco Firepower compute:PhysicalFsm:rn managed object property"
    ::= { cfprComputePhysicalFsmEntry 3 }

cfprComputePhysicalFsmCompletionTime OBJECT-TYPE
    SYNTAX       DateAndTime
    MAX-ACCESS   read-only
    STATUS       current
    DESCRIPTION
        "Cisco Firepower compute:PhysicalFsm:completionTime
        managed object property"
    ::= { cfprComputePhysicalFsmEntry 4 }

cfprComputePhysicalFsmCurrentFsm OBJECT-TYPE
    SYNTAX       CfprComputePhysicalFsmCurrentFsm
    MAX-ACCESS   read-only
    STATUS       current
    DESCRIPTION
        "Cisco Firepower compute:PhysicalFsm:currentFsm
        managed object property"
    ::= { cfprComputePhysicalFsmEntry 5 }

cfprComputePhysicalFsmDescr OBJECT-TYPE
    SYNTAX       SnmpAdminString
    MAX-ACCESS   read-only
    STATUS       current
    DESCRIPTION
        "Cisco Firepower compute:PhysicalFsm:descr managed
        object property"
    ::= { cfprComputePhysicalFsmEntry 6 }

cfprComputePhysicalFsmFsmStatus OBJECT-TYPE
    SYNTAX       CfprFsmFsmStageStatus
    MAX-ACCESS   read-only
    STATUS       current
    DESCRIPTION
        "Cisco Firepower compute:PhysicalFsm:fsmStatus
        managed object property"
    ::= { cfprComputePhysicalFsmEntry 7 }

cfprComputePhysicalFsmProgress OBJECT-TYPE
    SYNTAX       Gauge32
    MAX-ACCESS   read-only
    STATUS       current
    DESCRIPTION
        "Cisco Firepower compute:PhysicalFsm:progress managed
        object property"
    ::= { cfprComputePhysicalFsmEntry 8 }

cfprComputePhysicalFsmRmtErrCode OBJECT-TYPE
    SYNTAX       Gauge32
    MAX-ACCESS   read-only
    STATUS       current
    DESCRIPTION
        "Cisco Firepower compute:PhysicalFsm:rmtErrCode
        managed object property"
    ::= { cfprComputePhysicalFsmEntry 9 }

cfprComputePhysicalFsmRmtErrDescr OBJECT-TYPE
    SYNTAX       SnmpAdminString
    MAX-ACCESS   read-only
    STATUS       current
    DESCRIPTION
        "Cisco Firepower compute:PhysicalFsm:rmtErrDescr
        managed object property"
    ::= { cfprComputePhysicalFsmEntry 10 }

cfprComputePhysicalFsmRmtRslt OBJECT-TYPE
    SYNTAX       CfprConditionRemoteInvRslt
    MAX-ACCESS   read-only
    STATUS       current
    DESCRIPTION
        "Cisco Firepower compute:PhysicalFsm:rmtRslt managed
        object property"
    ::= { cfprComputePhysicalFsmEntry 11 }

cfprComputePhysicalFsmStageTable OBJECT-TYPE
    SYNTAX           SEQUENCE OF CfprComputePhysicalFsmStageEntry
    MAX-ACCESS       not-accessible
    STATUS           current
    DESCRIPTION
        "Cisco Firepower compute:PhysicalFsmStage managed object table"
    ::= { cfprComputeObjects 37 }

cfprComputePhysicalFsmStageEntry OBJECT-TYPE
    SYNTAX           CfprComputePhysicalFsmStageEntry
    MAX-ACCESS       not-accessible
    STATUS           current
    DESCRIPTION
        "Entry for the cfprComputePhysicalFsmStageTable table."
    INDEX { cfprComputePhysicalFsmStageInstanceId }
    ::= { cfprComputePhysicalFsmStageTable 1 }

CfprComputePhysicalFsmStageEntry ::= SEQUENCE {
    cfprComputePhysicalFsmStageInstanceId                            CfprManagedObjectId,
    cfprComputePhysicalFsmStageDn                                    CfprManagedObjectDn,
    cfprComputePhysicalFsmStageRn                                    SnmpAdminString,
    cfprComputePhysicalFsmStageDescr                                 SnmpAdminString,
    cfprComputePhysicalFsmStageLastUpdateTime                        DateAndTime,
    cfprComputePhysicalFsmStageName                                  CfprComputePhysicalFsmStageName,
    cfprComputePhysicalFsmStageOrder                                 Gauge32,
    cfprComputePhysicalFsmStageRetry                                 Gauge32,
    cfprComputePhysicalFsmStageStageStatus                           CfprFsmFsmStageStatus
}

cfprComputePhysicalFsmStageInstanceId OBJECT-TYPE
    SYNTAX       CfprManagedObjectId
    MAX-ACCESS   not-accessible
    STATUS       current
    DESCRIPTION
        "Instance identifier of the managed object."
    ::= { cfprComputePhysicalFsmStageEntry 1 }

cfprComputePhysicalFsmStageDn OBJECT-TYPE
    SYNTAX       CfprManagedObjectDn
    MAX-ACCESS   read-only
    STATUS       current
    DESCRIPTION
        "Cisco Firepower compute:PhysicalFsmStage:dn managed
        object property"
    ::= { cfprComputePhysicalFsmStageEntry 2 }

cfprComputePhysicalFsmStageRn OBJECT-TYPE
    SYNTAX       SnmpAdminString
    MAX-ACCESS   read-only
    STATUS       current
    DESCRIPTION
        "Cisco Firepower compute:PhysicalFsmStage:rn managed
        object property"
    ::= { cfprComputePhysicalFsmStageEntry 3 }

cfprComputePhysicalFsmStageDescr OBJECT-TYPE
    SYNTAX       SnmpAdminString
    MAX-ACCESS   read-only
    STATUS       current
    DESCRIPTION
        "Cisco Firepower compute:PhysicalFsmStage:descr
        managed object property"
    ::= { cfprComputePhysicalFsmStageEntry 4 }

cfprComputePhysicalFsmStageLastUpdateTime OBJECT-TYPE
    SYNTAX       DateAndTime
    MAX-ACCESS   read-only
    STATUS       current
    DESCRIPTION
        "Cisco Firepower compute:PhysicalFsmStage:lastUpdateTime
        managed object property"
    ::= { cfprComputePhysicalFsmStageEntry 5 }

cfprComputePhysicalFsmStageName OBJECT-TYPE
    SYNTAX       CfprComputePhysicalFsmStageName
    MAX-ACCESS   read-only
    STATUS       current
    DESCRIPTION
        "Cisco Firepower compute:PhysicalFsmStage:name
        managed object property"
    ::= { cfprComputePhysicalFsmStageEntry 6 }

cfprComputePhysicalFsmStageOrder OBJECT-TYPE
    SYNTAX       Gauge32
    MAX-ACCESS   read-only
    STATUS       current
    DESCRIPTION
        "Cisco Firepower compute:PhysicalFsmStage:order
        managed object property"
    ::= { cfprComputePhysicalFsmStageEntry 7 }

cfprComputePhysicalFsmStageRetry OBJECT-TYPE
    SYNTAX       Gauge32
    MAX-ACCESS   read-only
    STATUS       current
    DESCRIPTION
        "Cisco Firepower compute:PhysicalFsmStage:retry
        managed object property"
    ::= { cfprComputePhysicalFsmStageEntry 8 }

cfprComputePhysicalFsmStageStageStatus OBJECT-TYPE
    SYNTAX       CfprFsmFsmStageStatus
    MAX-ACCESS   read-only
    STATUS       current
    DESCRIPTION
        "Cisco Firepower compute:PhysicalFsmStage:stageStatus
        managed object property"
    ::= { cfprComputePhysicalFsmStageEntry 9 }

cfprComputePhysicalFsmTaskTable OBJECT-TYPE
    SYNTAX           SEQUENCE OF CfprComputePhysicalFsmTaskEntry
    MAX-ACCESS       not-accessible
    STATUS           current
    DESCRIPTION
        "Cisco Firepower compute:PhysicalFsmTask managed object table"
    ::= { cfprComputeObjects 38 }

cfprComputePhysicalFsmTaskEntry OBJECT-TYPE
    SYNTAX           CfprComputePhysicalFsmTaskEntry
    MAX-ACCESS       not-accessible
    STATUS           current
    DESCRIPTION
        "Entry for the cfprComputePhysicalFsmTaskTable table."
    INDEX { cfprComputePhysicalFsmTaskInstanceId }
    ::= { cfprComputePhysicalFsmTaskTable 1 }

CfprComputePhysicalFsmTaskEntry ::= SEQUENCE {
    cfprComputePhysicalFsmTaskInstanceId                             CfprManagedObjectId,
    cfprComputePhysicalFsmTaskDn                                     CfprManagedObjectDn,
    cfprComputePhysicalFsmTaskRn                                     SnmpAdminString,
    cfprComputePhysicalFsmTaskCompletion                             CfprFsmCompletion,
    cfprComputePhysicalFsmTaskFlags                                  CfprComputePhysicalFsmTaskFlags,
    cfprComputePhysicalFsmTaskItem                                   CfprComputePhysicalFsmTaskItem,
    cfprComputePhysicalFsmTaskSeqId                                  Gauge32
}

cfprComputePhysicalFsmTaskInstanceId OBJECT-TYPE
    SYNTAX       CfprManagedObjectId
    MAX-ACCESS   not-accessible
    STATUS       current
    DESCRIPTION
        "Instance identifier of the managed object."
    ::= { cfprComputePhysicalFsmTaskEntry 1 }

cfprComputePhysicalFsmTaskDn OBJECT-TYPE
    SYNTAX       CfprManagedObjectDn
    MAX-ACCESS   read-only
    STATUS       current
    DESCRIPTION
        "Cisco Firepower compute:PhysicalFsmTask:dn managed
        object property"
    ::= { cfprComputePhysicalFsmTaskEntry 2 }

cfprComputePhysicalFsmTaskRn OBJECT-TYPE
    SYNTAX       SnmpAdminString
    MAX-ACCESS   read-only
    STATUS       current
    DESCRIPTION
        "Cisco Firepower compute:PhysicalFsmTask:rn managed
        object property"
    ::= { cfprComputePhysicalFsmTaskEntry 3 }

cfprComputePhysicalFsmTaskCompletion OBJECT-TYPE
    SYNTAX       CfprFsmCompletion
    MAX-ACCESS   read-only
    STATUS       current
    DESCRIPTION
        "Cisco Firepower compute:PhysicalFsmTask:completion
        managed object property"
    ::= { cfprComputePhysicalFsmTaskEntry 4 }

cfprComputePhysicalFsmTaskFlags OBJECT-TYPE
    SYNTAX       CfprComputePhysicalFsmTaskFlags
    MAX-ACCESS   read-only
    STATUS       current
    DESCRIPTION
        "Cisco Firepower compute:PhysicalFsmTask:flags
        managed object property"
    ::= { cfprComputePhysicalFsmTaskEntry 5 }

cfprComputePhysicalFsmTaskItem OBJECT-TYPE
    SYNTAX       CfprComputePhysicalFsmTaskItem
    MAX-ACCESS   read-only
    STATUS       current
    DESCRIPTION
        "Cisco Firepower compute:PhysicalFsmTask:item managed
        object property"
    ::= { cfprComputePhysicalFsmTaskEntry 6 }

cfprComputePhysicalFsmTaskSeqId OBJECT-TYPE
    SYNTAX       Gauge32
    MAX-ACCESS   read-only
    STATUS       current
    DESCRIPTION
        "Cisco Firepower compute:PhysicalFsmTask:seqId
        managed object property"
    ::= { cfprComputePhysicalFsmTaskEntry 7 }

cfprComputePhysicalQualTable OBJECT-TYPE
    SYNTAX           SEQUENCE OF CfprComputePhysicalQualEntry
    MAX-ACCESS       not-accessible
    STATUS           current
    DESCRIPTION
        "Cisco Firepower compute:PhysicalQual managed object table"
    ::= { cfprComputeObjects 39 }

cfprComputePhysicalQualEntry OBJECT-TYPE
    SYNTAX           CfprComputePhysicalQualEntry
    MAX-ACCESS       not-accessible
    STATUS           current
    DESCRIPTION
        "Entry for the cfprComputePhysicalQualTable table."
    INDEX { cfprComputePhysicalQualInstanceId }
    ::= { cfprComputePhysicalQualTable 1 }

CfprComputePhysicalQualEntry ::= SEQUENCE {
    cfprComputePhysicalQualInstanceId                                CfprManagedObjectId,
    cfprComputePhysicalQualDn                                        CfprManagedObjectDn,
    cfprComputePhysicalQualRn                                        SnmpAdminString,
    cfprComputePhysicalQualModel                                     SnmpAdminString
}

cfprComputePhysicalQualInstanceId OBJECT-TYPE
    SYNTAX       CfprManagedObjectId
    MAX-ACCESS   not-accessible
    STATUS       current
    DESCRIPTION
        "Instance identifier of the managed object."
    ::= { cfprComputePhysicalQualEntry 1 }

cfprComputePhysicalQualDn OBJECT-TYPE
    SYNTAX       CfprManagedObjectDn
    MAX-ACCESS   read-only
    STATUS       current
    DESCRIPTION
        "Cisco Firepower compute:PhysicalQual:dn managed object property"
    ::= { cfprComputePhysicalQualEntry 2 }

cfprComputePhysicalQualRn OBJECT-TYPE
    SYNTAX       SnmpAdminString
    MAX-ACCESS   read-only
    STATUS       current
    DESCRIPTION
        "Cisco Firepower compute:PhysicalQual:rn managed object property"
    ::= { cfprComputePhysicalQualEntry 3 }

cfprComputePhysicalQualModel OBJECT-TYPE
    SYNTAX       SnmpAdminString
    MAX-ACCESS   read-only
    STATUS       current
    DESCRIPTION
        "Cisco Firepower compute:PhysicalQual:model managed
        object property"
    ::= { cfprComputePhysicalQualEntry 4 }

cfprComputePlatformTable OBJECT-TYPE
    SYNTAX           SEQUENCE OF CfprComputePlatformEntry
    MAX-ACCESS       not-accessible
    STATUS           current
    DESCRIPTION
        "Cisco Firepower compute:Platform managed object table"
    ::= { cfprComputeObjects 40 }

cfprComputePlatformEntry OBJECT-TYPE
    SYNTAX           CfprComputePlatformEntry
    MAX-ACCESS       not-accessible
    STATUS           current
    DESCRIPTION
        "Entry for the cfprComputePlatformTable table."
    INDEX { cfprComputePlatformInstanceId }
    ::= { cfprComputePlatformTable 1 }

CfprComputePlatformEntry ::= SEQUENCE {
    cfprComputePlatformInstanceId                                    CfprManagedObjectId,
    cfprComputePlatformDn                                            CfprManagedObjectDn,
    cfprComputePlatformRn                                            SnmpAdminString,
    cfprComputePlatformModel                                         SnmpAdminString,
    cfprComputePlatformProductName                                   SnmpAdminString,
    cfprComputePlatformRevision                                      SnmpAdminString,
    cfprComputePlatformVendor                                        SnmpAdminString
}

cfprComputePlatformInstanceId OBJECT-TYPE
    SYNTAX       CfprManagedObjectId
    MAX-ACCESS   not-accessible
    STATUS       current
    DESCRIPTION
        "Instance identifier of the managed object."
    ::= { cfprComputePlatformEntry 1 }

cfprComputePlatformDn OBJECT-TYPE
    SYNTAX       CfprManagedObjectDn
    MAX-ACCESS   read-only
    STATUS       current
    DESCRIPTION
        "Cisco Firepower compute:Platform:dn managed object property"
    ::= { cfprComputePlatformEntry 2 }

cfprComputePlatformRn OBJECT-TYPE
    SYNTAX       SnmpAdminString
    MAX-ACCESS   read-only
    STATUS       current
    DESCRIPTION
        "Cisco Firepower compute:Platform:rn managed object property"
    ::= { cfprComputePlatformEntry 3 }

cfprComputePlatformModel OBJECT-TYPE
    SYNTAX       SnmpAdminString
    MAX-ACCESS   read-only
    STATUS       current
    DESCRIPTION
        "Cisco Firepower compute:Platform:model managed object property"
    ::= { cfprComputePlatformEntry 4 }

cfprComputePlatformProductName OBJECT-TYPE
    SYNTAX       SnmpAdminString
    MAX-ACCESS   read-only
    STATUS       current
    DESCRIPTION
        "Cisco Firepower compute:Platform:productName managed
        object property"
    ::= { cfprComputePlatformEntry 5 }

cfprComputePlatformRevision OBJECT-TYPE
    SYNTAX       SnmpAdminString
    MAX-ACCESS   read-only
    STATUS       current
    DESCRIPTION
        "Cisco Firepower compute:Platform:revision managed
        object property"
    ::= { cfprComputePlatformEntry 6 }

cfprComputePlatformVendor OBJECT-TYPE
    SYNTAX       SnmpAdminString
    MAX-ACCESS   read-only
    STATUS       current
    DESCRIPTION
        "Cisco Firepower compute:Platform:vendor managed object property"
    ::= { cfprComputePlatformEntry 7 }

cfprComputePnuOSImageTable OBJECT-TYPE
    SYNTAX           SEQUENCE OF CfprComputePnuOSImageEntry
    MAX-ACCESS       not-accessible
    STATUS           current
    DESCRIPTION
        "Cisco Firepower compute:PnuOSImage managed object table"
    ::= { cfprComputeObjects 41 }

cfprComputePnuOSImageEntry OBJECT-TYPE
    SYNTAX           CfprComputePnuOSImageEntry
    MAX-ACCESS       not-accessible
    STATUS           current
    DESCRIPTION
        "Entry for the cfprComputePnuOSImageTable table."
    INDEX { cfprComputePnuOSImageInstanceId }
    ::= { cfprComputePnuOSImageTable 1 }

CfprComputePnuOSImageEntry ::= SEQUENCE {
    cfprComputePnuOSImageInstanceId                                  CfprManagedObjectId,
    cfprComputePnuOSImageDn                                          CfprManagedObjectDn,
    cfprComputePnuOSImageRn                                          SnmpAdminString,
    cfprComputePnuOSImageImgLFBFFName                                SnmpAdminString,
    cfprComputePnuOSImageImgLoc                                      SnmpAdminString,
    cfprComputePnuOSImageImgName                                     SnmpAdminString
}

cfprComputePnuOSImageInstanceId OBJECT-TYPE
    SYNTAX       CfprManagedObjectId
    MAX-ACCESS   not-accessible
    STATUS       current
    DESCRIPTION
        "Instance identifier of the managed object."
    ::= { cfprComputePnuOSImageEntry 1 }

cfprComputePnuOSImageDn OBJECT-TYPE
    SYNTAX       CfprManagedObjectDn
    MAX-ACCESS   read-only
    STATUS       current
    DESCRIPTION
        "Cisco Firepower compute:PnuOSImage:dn managed object property"
    ::= { cfprComputePnuOSImageEntry 2 }

cfprComputePnuOSImageRn OBJECT-TYPE
    SYNTAX       SnmpAdminString
    MAX-ACCESS   read-only
    STATUS       current
    DESCRIPTION
        "Cisco Firepower compute:PnuOSImage:rn managed object property"
    ::= { cfprComputePnuOSImageEntry 3 }

cfprComputePnuOSImageImgLFBFFName OBJECT-TYPE
    SYNTAX       SnmpAdminString
    MAX-ACCESS   read-only
    STATUS       current
    DESCRIPTION
        "Cisco Firepower compute:PnuOSImage:imgLFBFFName
        managed object property"
    ::= { cfprComputePnuOSImageEntry 4 }

cfprComputePnuOSImageImgLoc OBJECT-TYPE
    SYNTAX       SnmpAdminString
    MAX-ACCESS   read-only
    STATUS       current
    DESCRIPTION
        "Cisco Firepower compute:PnuOSImage:imgLoc managed
        object property"
    ::= { cfprComputePnuOSImageEntry 5 }

cfprComputePnuOSImageImgName OBJECT-TYPE
    SYNTAX       SnmpAdminString
    MAX-ACCESS   read-only
    STATUS       current
    DESCRIPTION
        "Cisco Firepower compute:PnuOSImage:imgName managed
        object property"
    ::= { cfprComputePnuOSImageEntry 6 }

cfprComputePoolTable OBJECT-TYPE
    SYNTAX           SEQUENCE OF CfprComputePoolEntry
    MAX-ACCESS       not-accessible
    STATUS           current
    DESCRIPTION
        "Cisco Firepower compute:Pool managed object table"
    ::= { cfprComputeObjects 42 }

cfprComputePoolEntry OBJECT-TYPE
    SYNTAX           CfprComputePoolEntry
    MAX-ACCESS       not-accessible
    STATUS           current
    DESCRIPTION
        "Entry for the cfprComputePoolTable table."
    INDEX { cfprComputePoolInstanceId }
    ::= { cfprComputePoolTable 1 }

CfprComputePoolEntry ::= SEQUENCE {
    cfprComputePoolInstanceId                                        CfprManagedObjectId,
    cfprComputePoolDn                                                CfprManagedObjectDn,
    cfprComputePoolRn                                                SnmpAdminString,
    cfprComputePoolAssigned                                          Gauge32,
    cfprComputePoolAssignmentOrder                                   CfprPoolPoolAssignmentOrder,
    cfprComputePoolDescr                                             SnmpAdminString,
    cfprComputePoolIntId                                             SnmpAdminString,
    cfprComputePoolName                                              SnmpAdminString,
    cfprComputePoolPolicyLevel                                       Gauge32,
    cfprComputePoolPolicyOwner                                       CfprPolicyPolicyOwner,
    cfprComputePoolSize                                              Gauge32
}

cfprComputePoolInstanceId OBJECT-TYPE
    SYNTAX       CfprManagedObjectId
    MAX-ACCESS   not-accessible
    STATUS       current
    DESCRIPTION
        "Instance identifier of the managed object."
    ::= { cfprComputePoolEntry 1 }

cfprComputePoolDn OBJECT-TYPE
    SYNTAX       CfprManagedObjectDn
    MAX-ACCESS   read-only
    STATUS       current
    DESCRIPTION
        "Cisco Firepower compute:Pool:dn managed object property"
    ::= { cfprComputePoolEntry 2 }

cfprComputePoolRn OBJECT-TYPE
    SYNTAX       SnmpAdminString
    MAX-ACCESS   read-only
    STATUS       current
    DESCRIPTION
        "Cisco Firepower compute:Pool:rn managed object property"
    ::= { cfprComputePoolEntry 3 }

cfprComputePoolAssigned OBJECT-TYPE
    SYNTAX       Gauge32
    MAX-ACCESS   read-only
    STATUS       current
    DESCRIPTION
        "Cisco Firepower compute:Pool:assigned managed object property"
    ::= { cfprComputePoolEntry 4 }

cfprComputePoolAssignmentOrder OBJECT-TYPE
    SYNTAX       CfprPoolPoolAssignmentOrder
    MAX-ACCESS   read-only
    STATUS       current
    DESCRIPTION
        "Cisco Firepower compute:Pool:assignmentOrder managed
        object property"
    ::= { cfprComputePoolEntry 5 }

cfprComputePoolDescr OBJECT-TYPE
    SYNTAX       SnmpAdminString
    MAX-ACCESS   read-only
    STATUS       current
    DESCRIPTION
        "Cisco Firepower compute:Pool:descr managed object property"
    ::= { cfprComputePoolEntry 6 }

cfprComputePoolIntId OBJECT-TYPE
    SYNTAX       SnmpAdminString
    MAX-ACCESS   read-only
    STATUS       current
    DESCRIPTION
        "Cisco Firepower compute:Pool:intId managed object property"
    ::= { cfprComputePoolEntry 7 }

cfprComputePoolName OBJECT-TYPE
    SYNTAX       SnmpAdminString
    MAX-ACCESS   read-only
    STATUS       current
    DESCRIPTION
        "Cisco Firepower compute:Pool:name managed object property"
    ::= { cfprComputePoolEntry 8 }

cfprComputePoolPolicyLevel OBJECT-TYPE
    SYNTAX       Gauge32
    MAX-ACCESS   read-only
    STATUS       current
    DESCRIPTION
        "Cisco Firepower compute:Pool:policyLevel managed object property"
    ::= { cfprComputePoolEntry 9 }

cfprComputePoolPolicyOwner OBJECT-TYPE
    SYNTAX       CfprPolicyPolicyOwner
    MAX-ACCESS   read-only
    STATUS       current
    DESCRIPTION
        "Cisco Firepower compute:Pool:policyOwner managed object property"
    ::= { cfprComputePoolEntry 10 }

cfprComputePoolSize OBJECT-TYPE
    SYNTAX       Gauge32
    MAX-ACCESS   read-only
    STATUS       current
    DESCRIPTION
        "Cisco Firepower compute:Pool:size managed object property"
    ::= { cfprComputePoolEntry 11 }

cfprComputePoolPolicyRefTable OBJECT-TYPE
    SYNTAX           SEQUENCE OF CfprComputePoolPolicyRefEntry
    MAX-ACCESS       not-accessible
    STATUS           current
    DESCRIPTION
        "Cisco Firepower compute:PoolPolicyRef managed object table"
    ::= { cfprComputeObjects 43 }

cfprComputePoolPolicyRefEntry OBJECT-TYPE
    SYNTAX           CfprComputePoolPolicyRefEntry
    MAX-ACCESS       not-accessible
    STATUS           current
    DESCRIPTION
        "Entry for the cfprComputePoolPolicyRefTable table."
    INDEX { cfprComputePoolPolicyRefInstanceId }
    ::= { cfprComputePoolPolicyRefTable 1 }

CfprComputePoolPolicyRefEntry ::= SEQUENCE {
    cfprComputePoolPolicyRefInstanceId                               CfprManagedObjectId,
    cfprComputePoolPolicyRefDn                                       CfprManagedObjectDn,
    cfprComputePoolPolicyRefRn                                       SnmpAdminString,
    cfprComputePoolPolicyRefId                                       Unsigned64,
    cfprComputePoolPolicyRefPolicyDn                                 SnmpAdminString
}

cfprComputePoolPolicyRefInstanceId OBJECT-TYPE
    SYNTAX       CfprManagedObjectId
    MAX-ACCESS   not-accessible
    STATUS       current
    DESCRIPTION
        "Instance identifier of the managed object."
    ::= { cfprComputePoolPolicyRefEntry 1 }

cfprComputePoolPolicyRefDn OBJECT-TYPE
    SYNTAX       CfprManagedObjectDn
    MAX-ACCESS   read-only
    STATUS       current
    DESCRIPTION
        "Cisco Firepower compute:PoolPolicyRef:dn managed object property"
    ::= { cfprComputePoolPolicyRefEntry 2 }

cfprComputePoolPolicyRefRn OBJECT-TYPE
    SYNTAX       SnmpAdminString
    MAX-ACCESS   read-only
    STATUS       current
    DESCRIPTION
        "Cisco Firepower compute:PoolPolicyRef:rn managed object property"
    ::= { cfprComputePoolPolicyRefEntry 3 }

cfprComputePoolPolicyRefId OBJECT-TYPE
    SYNTAX       Unsigned64
    MAX-ACCESS   read-only
    STATUS       current
    DESCRIPTION
        "Cisco Firepower compute:PoolPolicyRef:id managed object property"
    ::= { cfprComputePoolPolicyRefEntry 4 }

cfprComputePoolPolicyRefPolicyDn OBJECT-TYPE
    SYNTAX       SnmpAdminString
    MAX-ACCESS   read-only
    STATUS       current
    DESCRIPTION
        "Cisco Firepower compute:PoolPolicyRef:policyDn
        managed object property"
    ::= { cfprComputePoolPolicyRefEntry 5 }

cfprComputePoolableTable OBJECT-TYPE
    SYNTAX           SEQUENCE OF CfprComputePoolableEntry
    MAX-ACCESS       not-accessible
    STATUS           current
    DESCRIPTION
        "Cisco Firepower compute:Poolable managed object table"
    ::= { cfprComputeObjects 44 }

cfprComputePoolableEntry OBJECT-TYPE
    SYNTAX           CfprComputePoolableEntry
    MAX-ACCESS       not-accessible
    STATUS           current
    DESCRIPTION
        "Entry for the cfprComputePoolableTable table."
    INDEX { cfprComputePoolableInstanceId }
    ::= { cfprComputePoolableTable 1 }

CfprComputePoolableEntry ::= SEQUENCE {
    cfprComputePoolableInstanceId                                    CfprManagedObjectId,
    cfprComputePoolableDn                                            CfprManagedObjectDn,
    cfprComputePoolableRn                                            SnmpAdminString,
    cfprComputePoolableId                                            Unsigned64,
    cfprComputePoolablePoolDn                                        SnmpAdminString
}

cfprComputePoolableInstanceId OBJECT-TYPE
    SYNTAX       CfprManagedObjectId
    MAX-ACCESS   not-accessible
    STATUS       current
    DESCRIPTION
        "Instance identifier of the managed object."
    ::= { cfprComputePoolableEntry 1 }

cfprComputePoolableDn OBJECT-TYPE
    SYNTAX       CfprManagedObjectDn
    MAX-ACCESS   read-only
    STATUS       current
    DESCRIPTION
        "Cisco Firepower compute:Poolable:dn managed object property"
    ::= { cfprComputePoolableEntry 2 }

cfprComputePoolableRn OBJECT-TYPE
    SYNTAX       SnmpAdminString
    MAX-ACCESS   read-only
    STATUS       current
    DESCRIPTION
        "Cisco Firepower compute:Poolable:rn managed object property"
    ::= { cfprComputePoolableEntry 3 }

cfprComputePoolableId OBJECT-TYPE
    SYNTAX       Unsigned64
    MAX-ACCESS   read-only
    STATUS       current
    DESCRIPTION
        "Cisco Firepower compute:Poolable:id managed object property"
    ::= { cfprComputePoolableEntry 4 }

cfprComputePoolablePoolDn OBJECT-TYPE
    SYNTAX       SnmpAdminString
    MAX-ACCESS   read-only
    STATUS       current
    DESCRIPTION
        "Cisco Firepower compute:Poolable:poolDn managed object property"
    ::= { cfprComputePoolableEntry 5 }

cfprComputePooledRackUnitTable OBJECT-TYPE
    SYNTAX           SEQUENCE OF CfprComputePooledRackUnitEntry
    MAX-ACCESS       not-accessible
    STATUS           current
    DESCRIPTION
        "Cisco Firepower compute:PooledRackUnit managed object table"
    ::= { cfprComputeObjects 45 }

cfprComputePooledRackUnitEntry OBJECT-TYPE
    SYNTAX           CfprComputePooledRackUnitEntry
    MAX-ACCESS       not-accessible
    STATUS           current
    DESCRIPTION
        "Entry for the cfprComputePooledRackUnitTable table."
    INDEX { cfprComputePooledRackUnitInstanceId }
    ::= { cfprComputePooledRackUnitTable 1 }

CfprComputePooledRackUnitEntry ::= SEQUENCE {
    cfprComputePooledRackUnitInstanceId                              CfprManagedObjectId,
    cfprComputePooledRackUnitDn                                      CfprManagedObjectDn,
    cfprComputePooledRackUnitRn                                      SnmpAdminString,
    cfprComputePooledRackUnitAssigned                                TruthValue,
    cfprComputePooledRackUnitAssignedToDn                            SnmpAdminString,
    cfprComputePooledRackUnitId                                      CfprComputePooledRackUnitId,
    cfprComputePooledRackUnitOwner                                   CfprComputeOwner,
    cfprComputePooledRackUnitPoolableDn                              SnmpAdminString,
    cfprComputePooledRackUnitPrevAssignedToDn                        SnmpAdminString
}

cfprComputePooledRackUnitInstanceId OBJECT-TYPE
    SYNTAX       CfprManagedObjectId
    MAX-ACCESS   not-accessible
    STATUS       current
    DESCRIPTION
        "Instance identifier of the managed object."
    ::= { cfprComputePooledRackUnitEntry 1 }

cfprComputePooledRackUnitDn OBJECT-TYPE
    SYNTAX       CfprManagedObjectDn
    MAX-ACCESS   read-only
    STATUS       current
    DESCRIPTION
        "Cisco Firepower compute:PooledRackUnit:dn managed
        object property"
    ::= { cfprComputePooledRackUnitEntry 2 }

cfprComputePooledRackUnitRn OBJECT-TYPE
    SYNTAX       SnmpAdminString
    MAX-ACCESS   read-only
    STATUS       current
    DESCRIPTION
        "Cisco Firepower compute:PooledRackUnit:rn managed
        object property"
    ::= { cfprComputePooledRackUnitEntry 3 }

cfprComputePooledRackUnitAssigned OBJECT-TYPE
    SYNTAX       TruthValue
    MAX-ACCESS   read-only
    STATUS       current
    DESCRIPTION
        "Cisco Firepower compute:PooledRackUnit:assigned
        managed object property"
    ::= { cfprComputePooledRackUnitEntry 4 }

cfprComputePooledRackUnitAssignedToDn OBJECT-TYPE
    SYNTAX       SnmpAdminString
    MAX-ACCESS   read-only
    STATUS       current
    DESCRIPTION
        "Cisco Firepower compute:PooledRackUnit:assignedToDn
        managed object property"
    ::= { cfprComputePooledRackUnitEntry 5 }

cfprComputePooledRackUnitId OBJECT-TYPE
    SYNTAX       CfprComputePooledRackUnitId
    MAX-ACCESS   read-only
    STATUS       current
    DESCRIPTION
        "Cisco Firepower compute:PooledRackUnit:id managed
        object property"
    ::= { cfprComputePooledRackUnitEntry 6 }

cfprComputePooledRackUnitOwner OBJECT-TYPE
    SYNTAX       CfprComputeOwner
    MAX-ACCESS   read-only
    STATUS       current
    DESCRIPTION
        "Cisco Firepower compute:PooledRackUnit:owner managed
        object property"
    ::= { cfprComputePooledRackUnitEntry 7 }

cfprComputePooledRackUnitPoolableDn OBJECT-TYPE
    SYNTAX       SnmpAdminString
    MAX-ACCESS   read-only
    STATUS       current
    DESCRIPTION
        "Cisco Firepower compute:PooledRackUnit:poolableDn
        managed object property"
    ::= { cfprComputePooledRackUnitEntry 8 }

cfprComputePooledRackUnitPrevAssignedToDn OBJECT-TYPE
    SYNTAX       SnmpAdminString
    MAX-ACCESS   read-only
    STATUS       current
    DESCRIPTION
        "Cisco Firepower compute:PooledRackUnit:prevAssignedToDn
        managed object property"
    ::= { cfprComputePooledRackUnitEntry 9 }

cfprComputePooledSlotTable OBJECT-TYPE
    SYNTAX           SEQUENCE OF CfprComputePooledSlotEntry
    MAX-ACCESS       not-accessible
    STATUS           current
    DESCRIPTION
        "Cisco Firepower compute:PooledSlot managed object table"
    ::= { cfprComputeObjects 46 }

cfprComputePooledSlotEntry OBJECT-TYPE
    SYNTAX           CfprComputePooledSlotEntry
    MAX-ACCESS       not-accessible
    STATUS           current
    DESCRIPTION
        "Entry for the cfprComputePooledSlotTable table."
    INDEX { cfprComputePooledSlotInstanceId }
    ::= { cfprComputePooledSlotTable 1 }

CfprComputePooledSlotEntry ::= SEQUENCE {
    cfprComputePooledSlotInstanceId                                  CfprManagedObjectId,
    cfprComputePooledSlotDn                                          CfprManagedObjectDn,
    cfprComputePooledSlotRn                                          SnmpAdminString,
    cfprComputePooledSlotAssigned                                    TruthValue,
    cfprComputePooledSlotAssignedToDn                                SnmpAdminString,
    cfprComputePooledSlotChassisId                                   Gauge32,
    cfprComputePooledSlotOwner                                       CfprComputeOwner,
    cfprComputePooledSlotPoolableDn                                  SnmpAdminString,
    cfprComputePooledSlotPrevAssignedToDn                            SnmpAdminString,
    cfprComputePooledSlotSlotId                                      CfprComputePooledSlotSlotId
}

cfprComputePooledSlotInstanceId OBJECT-TYPE
    SYNTAX       CfprManagedObjectId
    MAX-ACCESS   not-accessible
    STATUS       current
    DESCRIPTION
        "Instance identifier of the managed object."
    ::= { cfprComputePooledSlotEntry 1 }

cfprComputePooledSlotDn OBJECT-TYPE
    SYNTAX       CfprManagedObjectDn
    MAX-ACCESS   read-only
    STATUS       current
    DESCRIPTION
        "Cisco Firepower compute:PooledSlot:dn managed object property"
    ::= { cfprComputePooledSlotEntry 2 }

cfprComputePooledSlotRn OBJECT-TYPE
    SYNTAX       SnmpAdminString
    MAX-ACCESS   read-only
    STATUS       current
    DESCRIPTION
        "Cisco Firepower compute:PooledSlot:rn managed object property"
    ::= { cfprComputePooledSlotEntry 3 }

cfprComputePooledSlotAssigned OBJECT-TYPE
    SYNTAX       TruthValue
    MAX-ACCESS   read-only
    STATUS       current
    DESCRIPTION
        "Cisco Firepower compute:PooledSlot:assigned managed
        object property"
    ::= { cfprComputePooledSlotEntry 4 }

cfprComputePooledSlotAssignedToDn OBJECT-TYPE
    SYNTAX       SnmpAdminString
    MAX-ACCESS   read-only
    STATUS       current
    DESCRIPTION
        "Cisco Firepower compute:PooledSlot:assignedToDn
        managed object property"
    ::= { cfprComputePooledSlotEntry 5 }

cfprComputePooledSlotChassisId OBJECT-TYPE
    SYNTAX       Gauge32
    MAX-ACCESS   read-only
    STATUS       current
    DESCRIPTION
        "Cisco Firepower compute:PooledSlot:chassisId managed
        object property"
    ::= { cfprComputePooledSlotEntry 6 }

cfprComputePooledSlotOwner OBJECT-TYPE
    SYNTAX       CfprComputeOwner
    MAX-ACCESS   read-only
    STATUS       current
    DESCRIPTION
        "Cisco Firepower compute:PooledSlot:owner managed object property"
    ::= { cfprComputePooledSlotEntry 7 }

cfprComputePooledSlotPoolableDn OBJECT-TYPE
    SYNTAX       SnmpAdminString
    MAX-ACCESS   read-only
    STATUS       current
    DESCRIPTION
        "Cisco Firepower compute:PooledSlot:poolableDn
        managed object property"
    ::= { cfprComputePooledSlotEntry 8 }

cfprComputePooledSlotPrevAssignedToDn OBJECT-TYPE
    SYNTAX       SnmpAdminString
    MAX-ACCESS   read-only
    STATUS       current
    DESCRIPTION
        "Cisco Firepower compute:PooledSlot:prevAssignedToDn
        managed object property"
    ::= { cfprComputePooledSlotEntry 9 }

cfprComputePooledSlotSlotId OBJECT-TYPE
    SYNTAX       CfprComputePooledSlotSlotId
    MAX-ACCESS   read-only
    STATUS       current
    DESCRIPTION
        "Cisco Firepower compute:PooledSlot:slotId managed
        object property"
    ::= { cfprComputePooledSlotEntry 10 }

cfprComputePoolingPolicyTable OBJECT-TYPE
    SYNTAX           SEQUENCE OF CfprComputePoolingPolicyEntry
    MAX-ACCESS       not-accessible
    STATUS           current
    DESCRIPTION
        "Cisco Firepower compute:PoolingPolicy managed object table"
    ::= { cfprComputeObjects 47 }

cfprComputePoolingPolicyEntry OBJECT-TYPE
    SYNTAX           CfprComputePoolingPolicyEntry
    MAX-ACCESS       not-accessible
    STATUS           current
    DESCRIPTION
        "Entry for the cfprComputePoolingPolicyTable table."
    INDEX { cfprComputePoolingPolicyInstanceId }
    ::= { cfprComputePoolingPolicyTable 1 }

CfprComputePoolingPolicyEntry ::= SEQUENCE {
    cfprComputePoolingPolicyInstanceId                               CfprManagedObjectId,
    cfprComputePoolingPolicyDn                                       CfprManagedObjectDn,
    cfprComputePoolingPolicyRn                                       SnmpAdminString,
    cfprComputePoolingPolicyDescr                                    SnmpAdminString,
    cfprComputePoolingPolicyIntId                                    SnmpAdminString,
    cfprComputePoolingPolicyName                                     SnmpAdminString,
    cfprComputePoolingPolicyPolicyLevel                              Gauge32,
    cfprComputePoolingPolicyPolicyOwner                              CfprPolicyPolicyOwner,
    cfprComputePoolingPolicyPoolDn                                   SnmpAdminString,
    cfprComputePoolingPolicyQualifier                                SnmpAdminString
}

cfprComputePoolingPolicyInstanceId OBJECT-TYPE
    SYNTAX       CfprManagedObjectId
    MAX-ACCESS   not-accessible
    STATUS       current
    DESCRIPTION
        "Instance identifier of the managed object."
    ::= { cfprComputePoolingPolicyEntry 1 }

cfprComputePoolingPolicyDn OBJECT-TYPE
    SYNTAX       CfprManagedObjectDn
    MAX-ACCESS   read-only
    STATUS       current
    DESCRIPTION
        "Cisco Firepower compute:PoolingPolicy:dn managed object property"
    ::= { cfprComputePoolingPolicyEntry 2 }

cfprComputePoolingPolicyRn OBJECT-TYPE
    SYNTAX       SnmpAdminString
    MAX-ACCESS   read-only
    STATUS       current
    DESCRIPTION
        "Cisco Firepower compute:PoolingPolicy:rn managed object property"
    ::= { cfprComputePoolingPolicyEntry 3 }

cfprComputePoolingPolicyDescr OBJECT-TYPE
    SYNTAX       SnmpAdminString
    MAX-ACCESS   read-only
    STATUS       current
    DESCRIPTION
        "Cisco Firepower compute:PoolingPolicy:descr managed
        object property"
    ::= { cfprComputePoolingPolicyEntry 4 }

cfprComputePoolingPolicyIntId OBJECT-TYPE
    SYNTAX       SnmpAdminString
    MAX-ACCESS   read-only
    STATUS       current
    DESCRIPTION
        "Cisco Firepower compute:PoolingPolicy:intId managed
        object property"
    ::= { cfprComputePoolingPolicyEntry 5 }

cfprComputePoolingPolicyName OBJECT-TYPE
    SYNTAX       SnmpAdminString
    MAX-ACCESS   read-only
    STATUS       current
    DESCRIPTION
        "Cisco Firepower compute:PoolingPolicy:name managed
        object property"
    ::= { cfprComputePoolingPolicyEntry 6 }

cfprComputePoolingPolicyPolicyLevel OBJECT-TYPE
    SYNTAX       Gauge32
    MAX-ACCESS   read-only
    STATUS       current
    DESCRIPTION
        "Cisco Firepower compute:PoolingPolicy:policyLevel
        managed object property"
    ::= { cfprComputePoolingPolicyEntry 7 }

cfprComputePoolingPolicyPolicyOwner OBJECT-TYPE
    SYNTAX       CfprPolicyPolicyOwner
    MAX-ACCESS   read-only
    STATUS       current
    DESCRIPTION
        "Cisco Firepower compute:PoolingPolicy:policyOwner
        managed object property"
    ::= { cfprComputePoolingPolicyEntry 8 }

cfprComputePoolingPolicyPoolDn OBJECT-TYPE
    SYNTAX       SnmpAdminString
    MAX-ACCESS   read-only
    STATUS       current
    DESCRIPTION
        "Cisco Firepower compute:PoolingPolicy:poolDn managed
        object property"
    ::= { cfprComputePoolingPolicyEntry 9 }

cfprComputePoolingPolicyQualifier OBJECT-TYPE
    SYNTAX       SnmpAdminString
    MAX-ACCESS   read-only
    STATUS       current
    DESCRIPTION
        "Cisco Firepower compute:PoolingPolicy:qualifier
        managed object property"
    ::= { cfprComputePoolingPolicyEntry 10 }

cfprComputePsuControlTable OBJECT-TYPE
    SYNTAX           SEQUENCE OF CfprComputePsuControlEntry
    MAX-ACCESS       not-accessible
    STATUS           current
    DESCRIPTION
        "Cisco Firepower compute:PsuControl managed object table"
    ::= { cfprComputeObjects 48 }

cfprComputePsuControlEntry OBJECT-TYPE
    SYNTAX           CfprComputePsuControlEntry
    MAX-ACCESS       not-accessible
    STATUS           current
    DESCRIPTION
        "Entry for the cfprComputePsuControlTable table."
    INDEX { cfprComputePsuControlInstanceId }
    ::= { cfprComputePsuControlTable 1 }

CfprComputePsuControlEntry ::= SEQUENCE {
    cfprComputePsuControlInstanceId                                  CfprManagedObjectId,
    cfprComputePsuControlDn                                          CfprManagedObjectDn,
    cfprComputePsuControlRn                                          SnmpAdminString,
    cfprComputePsuControlClusterState                                CfprComputePsuClusterState,
    cfprComputePsuControlDescr                                       SnmpAdminString,
    cfprComputePsuControlInputPowerState                             CfprEquipmentSensorThresholdStatus,
    cfprComputePsuControlIntId                                       SnmpAdminString,
    cfprComputePsuControlName                                        SnmpAdminString,
    cfprComputePsuControlOperQualifier                               CfprComputePsuRedundancyOperQualifier,
    cfprComputePsuControlOperState                                   CfprComputePsuRedundancyOperState,
    cfprComputePsuControlOutputPowerState                            CfprEquipmentSensorThresholdStatus,
    cfprComputePsuControlPolicyLevel                                 Gauge32,
    cfprComputePsuControlPolicyOwner                                 CfprPolicyPolicyOwner,
    cfprComputePsuControlRedundancy                                  CfprComputePsuControlRedundancy
}

cfprComputePsuControlInstanceId OBJECT-TYPE
    SYNTAX       CfprManagedObjectId
    MAX-ACCESS   not-accessible
    STATUS       current
    DESCRIPTION
        "Instance identifier of the managed object."
    ::= { cfprComputePsuControlEntry 1 }

cfprComputePsuControlDn OBJECT-TYPE
    SYNTAX       CfprManagedObjectDn
    MAX-ACCESS   read-only
    STATUS       current
    DESCRIPTION
        "Cisco Firepower compute:PsuControl:dn managed object property"
    ::= { cfprComputePsuControlEntry 2 }

cfprComputePsuControlRn OBJECT-TYPE
    SYNTAX       SnmpAdminString
    MAX-ACCESS   read-only
    STATUS       current
    DESCRIPTION
        "Cisco Firepower compute:PsuControl:rn managed object property"
    ::= { cfprComputePsuControlEntry 3 }

cfprComputePsuControlClusterState OBJECT-TYPE
    SYNTAX       CfprComputePsuClusterState
    MAX-ACCESS   read-only
    STATUS       current
    DESCRIPTION
        "Cisco Firepower compute:PsuControl:clusterState
        managed object property"
    ::= { cfprComputePsuControlEntry 4 }

cfprComputePsuControlDescr OBJECT-TYPE
    SYNTAX       SnmpAdminString
    MAX-ACCESS   read-only
    STATUS       current
    DESCRIPTION
        "Cisco Firepower compute:PsuControl:descr managed object property"
    ::= { cfprComputePsuControlEntry 5 }

cfprComputePsuControlInputPowerState OBJECT-TYPE
    SYNTAX       CfprEquipmentSensorThresholdStatus
    MAX-ACCESS   read-only
    STATUS       current
    DESCRIPTION
        "Cisco Firepower compute:PsuControl:inputPowerState
        managed object property"
    ::= { cfprComputePsuControlEntry 6 }

cfprComputePsuControlIntId OBJECT-TYPE
    SYNTAX       SnmpAdminString
    MAX-ACCESS   read-only
    STATUS       current
    DESCRIPTION
        "Cisco Firepower compute:PsuControl:intId managed object property"
    ::= { cfprComputePsuControlEntry 7 }

cfprComputePsuControlName OBJECT-TYPE
    SYNTAX       SnmpAdminString
    MAX-ACCESS   read-only
    STATUS       current
    DESCRIPTION
        "Cisco Firepower compute:PsuControl:name managed object property"
    ::= { cfprComputePsuControlEntry 8 }

cfprComputePsuControlOperQualifier OBJECT-TYPE
    SYNTAX       CfprComputePsuRedundancyOperQualifier
    MAX-ACCESS   read-only
    STATUS       current
    DESCRIPTION
        "Cisco Firepower compute:PsuControl:operQualifier
        managed object property"
    ::= { cfprComputePsuControlEntry 9 }

cfprComputePsuControlOperState OBJECT-TYPE
    SYNTAX       CfprComputePsuRedundancyOperState
    MAX-ACCESS   read-only
    STATUS       current
    DESCRIPTION
        "Cisco Firepower compute:PsuControl:operState managed
        object property"
    ::= { cfprComputePsuControlEntry 10 }

cfprComputePsuControlOutputPowerState OBJECT-TYPE
    SYNTAX       CfprEquipmentSensorThresholdStatus
    MAX-ACCESS   read-only
    STATUS       current
    DESCRIPTION
        "Cisco Firepower compute:PsuControl:outputPowerState
        managed object property"
    ::= { cfprComputePsuControlEntry 11 }

cfprComputePsuControlPolicyLevel OBJECT-TYPE
    SYNTAX       Gauge32
    MAX-ACCESS   read-only
    STATUS       current
    DESCRIPTION
        "Cisco Firepower compute:PsuControl:policyLevel
        managed object property"
    ::= { cfprComputePsuControlEntry 12 }

cfprComputePsuControlPolicyOwner OBJECT-TYPE
    SYNTAX       CfprPolicyPolicyOwner
    MAX-ACCESS   read-only
    STATUS       current
    DESCRIPTION
        "Cisco Firepower compute:PsuControl:policyOwner
        managed object property"
    ::= { cfprComputePsuControlEntry 13 }

cfprComputePsuControlRedundancy OBJECT-TYPE
    SYNTAX       CfprComputePsuControlRedundancy
    MAX-ACCESS   read-only
    STATUS       current
    DESCRIPTION
        "Cisco Firepower compute:PsuControl:redundancy
        managed object property"
    ::= { cfprComputePsuControlEntry 14 }

cfprComputePsuPolicyTable OBJECT-TYPE
    SYNTAX           SEQUENCE OF CfprComputePsuPolicyEntry
    MAX-ACCESS       not-accessible
    STATUS           current
    DESCRIPTION
        "Cisco Firepower compute:PsuPolicy managed object table"
    ::= { cfprComputeObjects 49 }

cfprComputePsuPolicyEntry OBJECT-TYPE
    SYNTAX           CfprComputePsuPolicyEntry
    MAX-ACCESS       not-accessible
    STATUS           current
    DESCRIPTION
        "Entry for the cfprComputePsuPolicyTable table."
    INDEX { cfprComputePsuPolicyInstanceId }
    ::= { cfprComputePsuPolicyTable 1 }

CfprComputePsuPolicyEntry ::= SEQUENCE {
    cfprComputePsuPolicyInstanceId                                   CfprManagedObjectId,
    cfprComputePsuPolicyDn                                           CfprManagedObjectDn,
    cfprComputePsuPolicyRn                                           SnmpAdminString,
    cfprComputePsuPolicyDescr                                        SnmpAdminString,
    cfprComputePsuPolicyIntId                                        SnmpAdminString,
    cfprComputePsuPolicyName                                         SnmpAdminString,
    cfprComputePsuPolicyPolicyLevel                                  Gauge32,
    cfprComputePsuPolicyPolicyOwner                                  CfprPolicyPolicyOwner,
    cfprComputePsuPolicyRedundancy                                   CfprComputePsuRedundancy
}

cfprComputePsuPolicyInstanceId OBJECT-TYPE
    SYNTAX       CfprManagedObjectId
    MAX-ACCESS   not-accessible
    STATUS       current
    DESCRIPTION
        "Instance identifier of the managed object."
    ::= { cfprComputePsuPolicyEntry 1 }

cfprComputePsuPolicyDn OBJECT-TYPE
    SYNTAX       CfprManagedObjectDn
    MAX-ACCESS   read-only
    STATUS       current
    DESCRIPTION
        "Cisco Firepower compute:PsuPolicy:dn managed object property"
    ::= { cfprComputePsuPolicyEntry 2 }

cfprComputePsuPolicyRn OBJECT-TYPE
    SYNTAX       SnmpAdminString
    MAX-ACCESS   read-only
    STATUS       current
    DESCRIPTION
        "Cisco Firepower compute:PsuPolicy:rn managed object property"
    ::= { cfprComputePsuPolicyEntry 3 }

cfprComputePsuPolicyDescr OBJECT-TYPE
    SYNTAX       SnmpAdminString
    MAX-ACCESS   read-only
    STATUS       current
    DESCRIPTION
        "Cisco Firepower compute:PsuPolicy:descr managed object property"
    ::= { cfprComputePsuPolicyEntry 4 }

cfprComputePsuPolicyIntId OBJECT-TYPE
    SYNTAX       SnmpAdminString
    MAX-ACCESS   read-only
    STATUS       current
    DESCRIPTION
        "Cisco Firepower compute:PsuPolicy:intId managed object property"
    ::= { cfprComputePsuPolicyEntry 5 }

cfprComputePsuPolicyName OBJECT-TYPE
    SYNTAX       SnmpAdminString
    MAX-ACCESS   read-only
    STATUS       current
    DESCRIPTION
        "Cisco Firepower compute:PsuPolicy:name managed object property"
    ::= { cfprComputePsuPolicyEntry 6 }

cfprComputePsuPolicyPolicyLevel OBJECT-TYPE
    SYNTAX       Gauge32
    MAX-ACCESS   read-only
    STATUS       current
    DESCRIPTION
        "Cisco Firepower compute:PsuPolicy:policyLevel
        managed object property"
    ::= { cfprComputePsuPolicyEntry 7 }

cfprComputePsuPolicyPolicyOwner OBJECT-TYPE
    SYNTAX       CfprPolicyPolicyOwner
    MAX-ACCESS   read-only
    STATUS       current
    DESCRIPTION
        "Cisco Firepower compute:PsuPolicy:policyOwner
        managed object property"
    ::= { cfprComputePsuPolicyEntry 8 }

cfprComputePsuPolicyRedundancy OBJECT-TYPE
    SYNTAX       CfprComputePsuRedundancy
    MAX-ACCESS   read-only
    STATUS       current
    DESCRIPTION
        "Cisco Firepower compute:PsuPolicy:redundancy managed
        object property"
    ::= { cfprComputePsuPolicyEntry 9 }

cfprComputeQualTable OBJECT-TYPE
    SYNTAX           SEQUENCE OF CfprComputeQualEntry
    MAX-ACCESS       not-accessible
    STATUS           current
    DESCRIPTION
        "Cisco Firepower compute:Qual managed object table"
    ::= { cfprComputeObjects 50 }

cfprComputeQualEntry OBJECT-TYPE
    SYNTAX           CfprComputeQualEntry
    MAX-ACCESS       not-accessible
    STATUS           current
    DESCRIPTION
        "Entry for the cfprComputeQualTable table."
    INDEX { cfprComputeQualInstanceId }
    ::= { cfprComputeQualTable 1 }

CfprComputeQualEntry ::= SEQUENCE {
    cfprComputeQualInstanceId                                        CfprManagedObjectId,
    cfprComputeQualDn                                                CfprManagedObjectDn,
    cfprComputeQualRn                                                SnmpAdminString,
    cfprComputeQualDescr                                             SnmpAdminString,
    cfprComputeQualIntId                                             SnmpAdminString,
    cfprComputeQualName                                              SnmpAdminString,
    cfprComputeQualPolicyLevel                                       Gauge32,
    cfprComputeQualPolicyOwner                                       CfprPolicyPolicyOwner
}

cfprComputeQualInstanceId OBJECT-TYPE
    SYNTAX       CfprManagedObjectId
    MAX-ACCESS   not-accessible
    STATUS       current
    DESCRIPTION
        "Instance identifier of the managed object."
    ::= { cfprComputeQualEntry 1 }

cfprComputeQualDn OBJECT-TYPE
    SYNTAX       CfprManagedObjectDn
    MAX-ACCESS   read-only
    STATUS       current
    DESCRIPTION
        "Cisco Firepower compute:Qual:dn managed object property"
    ::= { cfprComputeQualEntry 2 }

cfprComputeQualRn OBJECT-TYPE
    SYNTAX       SnmpAdminString
    MAX-ACCESS   read-only
    STATUS       current
    DESCRIPTION
        "Cisco Firepower compute:Qual:rn managed object property"
    ::= { cfprComputeQualEntry 3 }

cfprComputeQualDescr OBJECT-TYPE
    SYNTAX       SnmpAdminString
    MAX-ACCESS   read-only
    STATUS       current
    DESCRIPTION
        "Cisco Firepower compute:Qual:descr managed object property"
    ::= { cfprComputeQualEntry 4 }

cfprComputeQualIntId OBJECT-TYPE
    SYNTAX       SnmpAdminString
    MAX-ACCESS   read-only
    STATUS       current
    DESCRIPTION
        "Cisco Firepower compute:Qual:intId managed object property"
    ::= { cfprComputeQualEntry 5 }

cfprComputeQualName OBJECT-TYPE
    SYNTAX       SnmpAdminString
    MAX-ACCESS   read-only
    STATUS       current
    DESCRIPTION
        "Cisco Firepower compute:Qual:name managed object property"
    ::= { cfprComputeQualEntry 6 }

cfprComputeQualPolicyLevel OBJECT-TYPE
    SYNTAX       Gauge32
    MAX-ACCESS   read-only
    STATUS       current
    DESCRIPTION
        "Cisco Firepower compute:Qual:policyLevel managed object property"
    ::= { cfprComputeQualEntry 7 }

cfprComputeQualPolicyOwner OBJECT-TYPE
    SYNTAX       CfprPolicyPolicyOwner
    MAX-ACCESS   read-only
    STATUS       current
    DESCRIPTION
        "Cisco Firepower compute:Qual:policyOwner managed object property"
    ::= { cfprComputeQualEntry 8 }

cfprComputeRackQualTable OBJECT-TYPE
    SYNTAX           SEQUENCE OF CfprComputeRackQualEntry
    MAX-ACCESS       not-accessible
    STATUS           current
    DESCRIPTION
        "Cisco Firepower compute:RackQual managed object table"
    ::= { cfprComputeObjects 51 }

cfprComputeRackQualEntry OBJECT-TYPE
    SYNTAX           CfprComputeRackQualEntry
    MAX-ACCESS       not-accessible
    STATUS           current
    DESCRIPTION
        "Entry for the cfprComputeRackQualTable table."
    INDEX { cfprComputeRackQualInstanceId }
    ::= { cfprComputeRackQualTable 1 }

CfprComputeRackQualEntry ::= SEQUENCE {
    cfprComputeRackQualInstanceId                                    CfprManagedObjectId,
    cfprComputeRackQualDn                                            CfprManagedObjectDn,
    cfprComputeRackQualRn                                            SnmpAdminString,
    cfprComputeRackQualMaxId                                         CfprComputeRackQualMaxId,
    cfprComputeRackQualMinId                                         CfprComputeRackQualMinId
}

cfprComputeRackQualInstanceId OBJECT-TYPE
    SYNTAX       CfprManagedObjectId
    MAX-ACCESS   not-accessible
    STATUS       current
    DESCRIPTION
        "Instance identifier of the managed object."
    ::= { cfprComputeRackQualEntry 1 }

cfprComputeRackQualDn OBJECT-TYPE
    SYNTAX       CfprManagedObjectDn
    MAX-ACCESS   read-only
    STATUS       current
    DESCRIPTION
        "Cisco Firepower compute:RackQual:dn managed object property"
    ::= { cfprComputeRackQualEntry 2 }

cfprComputeRackQualRn OBJECT-TYPE
    SYNTAX       SnmpAdminString
    MAX-ACCESS   read-only
    STATUS       current
    DESCRIPTION
        "Cisco Firepower compute:RackQual:rn managed object property"
    ::= { cfprComputeRackQualEntry 3 }

cfprComputeRackQualMaxId OBJECT-TYPE
    SYNTAX       CfprComputeRackQualMaxId
    MAX-ACCESS   read-only
    STATUS       current
    DESCRIPTION
        "Cisco Firepower compute:RackQual:maxId managed object property"
    ::= { cfprComputeRackQualEntry 4 }

cfprComputeRackQualMinId OBJECT-TYPE
    SYNTAX       CfprComputeRackQualMinId
    MAX-ACCESS   read-only
    STATUS       current
    DESCRIPTION
        "Cisco Firepower compute:RackQual:minId managed object property"
    ::= { cfprComputeRackQualEntry 5 }

cfprComputeRackUnitTable OBJECT-TYPE
    SYNTAX           SEQUENCE OF CfprComputeRackUnitEntry
    MAX-ACCESS       not-accessible
    STATUS           current
    DESCRIPTION
        "Cisco Firepower compute:RackUnit managed object table"
    ::= { cfprComputeObjects 52 }

cfprComputeRackUnitEntry OBJECT-TYPE
    SYNTAX           CfprComputeRackUnitEntry
    MAX-ACCESS       not-accessible
    STATUS           current
    DESCRIPTION
        "Entry for the cfprComputeRackUnitTable table."
    INDEX { cfprComputeRackUnitInstanceId }
    ::= { cfprComputeRackUnitTable 1 }

CfprComputeRackUnitEntry ::= SEQUENCE {
    cfprComputeRackUnitInstanceId                                    CfprManagedObjectId,
    cfprComputeRackUnitDn                                            CfprManagedObjectDn,
    cfprComputeRackUnitRn                                            SnmpAdminString,
    cfprComputeRackUnitAdminPower                                    CfprComputeAdminPowerState,
    cfprComputeRackUnitAdminState                                    CfprComputeAdminState,
    cfprComputeRackUnitAssignedToDn                                  SnmpAdminString,
    cfprComputeRackUnitAssociation                                   CfprComputeAssociation,
    cfprComputeRackUnitAvailability                                  CfprComputeAvailability,
    cfprComputeRackUnitAvailableMemory                               Gauge32,
    cfprComputeRackUnitCheckPoint                                    CfprComputeCheckPoint,
    cfprComputeRackUnitConnPath                                      CfprEquipmentConnectionStatus,
    cfprComputeRackUnitConnStatus                                    CfprEquipmentConnectionStatus,
    cfprComputeRackUnitDescr                                         SnmpAdminString,
    cfprComputeRackUnitDiscovery                                     CfprComputeDiscovery,
    cfprComputeRackUnitFltAggr                                       Unsigned64,
    cfprComputeRackUnitFsmDescr                                      SnmpAdminString,
    cfprComputeRackUnitFsmFlags                                      SnmpAdminString,
    cfprComputeRackUnitFsmPrev                                       SnmpAdminString,
    cfprComputeRackUnitFsmProgr                                      Gauge32,
    cfprComputeRackUnitFsmRmtInvErrCode                              Gauge32,
    cfprComputeRackUnitFsmRmtInvErrDescr                             SnmpAdminString,
    cfprComputeRackUnitFsmRmtInvRslt                                 CfprConditionRemoteInvRslt,
    cfprComputeRackUnitFsmStageDescr                                 SnmpAdminString,
    cfprComputeRackUnitFsmStamp                                      DateAndTime,
    cfprComputeRackUnitFsmStatus                                     SnmpAdminString,
    cfprComputeRackUnitFsmTry                                        Gauge32,
    cfprComputeRackUnitId                                            CfprComputeRackUnitId,
    cfprComputeRackUnitIntId                                         SnmpAdminString,
    cfprComputeRackUnitLc                                            CfprComputeAdminTrigger,
    cfprComputeRackUnitLcTs                                          DateAndTime,
    cfprComputeRackUnitLocalId                                       SnmpAdminString,
    cfprComputeRackUnitLowVoltageMemory                              CfprComputePhysicalLowVoltageMemory,
    cfprComputeRackUnitManagingInst                                  CfprNetworkSwitchId,
    cfprComputeRackUnitMemorySpeed                                   Gauge32,
    cfprComputeRackUnitMfgTime                                       DateAndTime,
    cfprComputeRackUnitModel                                         SnmpAdminString,
    cfprComputeRackUnitName                                          SnmpAdminString,
    cfprComputeRackUnitNumOfAdaptors                                 Gauge32,
    cfprComputeRackUnitNumOfCores                                    Gauge32,
    cfprComputeRackUnitNumOfCoresEnabled                             Gauge32,
    cfprComputeRackUnitNumOfCpus                                     Gauge32,
    cfprComputeRackUnitNumOfEthHostIfs                               Gauge32,
    cfprComputeRackUnitNumOfFcHostIfs                                Gauge32,
    cfprComputeRackUnitNumOfThreads                                  Gauge32,
    cfprComputeRackUnitOperPower                                     CfprEquipmentPowerState,
    cfprComputeRackUnitOperQualifier                                 CfprComputeIssues,
    cfprComputeRackUnitOperState                                     CfprLsOperState,
    cfprComputeRackUnitOperability                                   CfprEquipmentOperability,
    cfprComputeRackUnitOriginalUuid                                  SnmpAdminString,
    cfprComputeRackUnitPartNumber                                    SnmpAdminString,
    cfprComputeRackUnitPolicyLevel                                   Gauge32,
    cfprComputeRackUnitPolicyOwner                                   CfprPolicyPolicyOwner,
    cfprComputeRackUnitPresence                                      CfprEquipmentSlotStatus,
    cfprComputeRackUnitRevision                                      SnmpAdminString,
    cfprComputeRackUnitSerial                                        SnmpAdminString,
    cfprComputeRackUnitServerId                                      SnmpAdminString,
    cfprComputeRackUnitTotalMemory                                   Gauge32,
    cfprComputeRackUnitUsrLbl                                        SnmpAdminString,
    cfprComputeRackUnitUuid                                          SnmpAdminString,
    cfprComputeRackUnitVendor                                        SnmpAdminString,
    cfprComputeRackUnitVersionHolder                                 TruthValue,
    cfprComputeRackUnitVid                                           SnmpAdminString,
    cfprComputeRackUnitPostState                                     CfprEquipmentBiosPostState
}

cfprComputeRackUnitInstanceId OBJECT-TYPE
    SYNTAX       CfprManagedObjectId
    MAX-ACCESS   not-accessible
    STATUS       current
    DESCRIPTION
        "Instance identifier of the managed object."
    ::= { cfprComputeRackUnitEntry 1 }

cfprComputeRackUnitDn OBJECT-TYPE
    SYNTAX       CfprManagedObjectDn
    MAX-ACCESS   read-only
    STATUS       current
    DESCRIPTION
        "Cisco Firepower compute:RackUnit:dn managed object property"
    ::= { cfprComputeRackUnitEntry 2 }

cfprComputeRackUnitRn OBJECT-TYPE
    SYNTAX       SnmpAdminString
    MAX-ACCESS   read-only
    STATUS       current
    DESCRIPTION
        "Cisco Firepower compute:RackUnit:rn managed object property"
    ::= { cfprComputeRackUnitEntry 3 }

cfprComputeRackUnitAdminPower OBJECT-TYPE
    SYNTAX       CfprComputeAdminPowerState
    MAX-ACCESS   read-only
    STATUS       current
    DESCRIPTION
        "Cisco Firepower compute:RackUnit:adminPower managed
        object property"
    ::= { cfprComputeRackUnitEntry 4 }

cfprComputeRackUnitAdminState OBJECT-TYPE
    SYNTAX       CfprComputeAdminState
    MAX-ACCESS   read-only
    STATUS       current
    DESCRIPTION
        "Cisco Firepower compute:RackUnit:adminState managed
        object property"
    ::= { cfprComputeRackUnitEntry 5 }

cfprComputeRackUnitAssignedToDn OBJECT-TYPE
    SYNTAX       SnmpAdminString
    MAX-ACCESS   read-only
    STATUS       current
    DESCRIPTION
        "Cisco Firepower compute:RackUnit:assignedToDn
        managed object property"
    ::= { cfprComputeRackUnitEntry 6 }

cfprComputeRackUnitAssociation OBJECT-TYPE
    SYNTAX       CfprComputeAssociation
    MAX-ACCESS   read-only
    STATUS       current
    DESCRIPTION
        "Cisco Firepower compute:RackUnit:association managed
        object property"
    ::= { cfprComputeRackUnitEntry 7 }

cfprComputeRackUnitAvailability OBJECT-TYPE
    SYNTAX       CfprComputeAvailability
    MAX-ACCESS   read-only
    STATUS       current
    DESCRIPTION
        "Cisco Firepower compute:RackUnit:availability
        managed object property"
    ::= { cfprComputeRackUnitEntry 8 }

cfprComputeRackUnitAvailableMemory OBJECT-TYPE
    SYNTAX       Gauge32
    MAX-ACCESS   read-only
    STATUS       current
    DESCRIPTION
        "Cisco Firepower compute:RackUnit:availableMemory
        managed object property"
    ::= { cfprComputeRackUnitEntry 9 }

cfprComputeRackUnitCheckPoint OBJECT-TYPE
    SYNTAX       CfprComputeCheckPoint
    MAX-ACCESS   read-only
    STATUS       current
    DESCRIPTION
        "Cisco Firepower compute:RackUnit:checkPoint managed
        object property"
    ::= { cfprComputeRackUnitEntry 10 }

cfprComputeRackUnitConnPath OBJECT-TYPE
    SYNTAX       CfprEquipmentConnectionStatus
    MAX-ACCESS   read-only
    STATUS       current
    DESCRIPTION
        "Cisco Firepower compute:RackUnit:connPath managed
        object property"
    ::= { cfprComputeRackUnitEntry 11 }

cfprComputeRackUnitConnStatus OBJECT-TYPE
    SYNTAX       CfprEquipmentConnectionStatus
    MAX-ACCESS   read-only
    STATUS       current
    DESCRIPTION
        "Cisco Firepower compute:RackUnit:connStatus managed
        object property"
    ::= { cfprComputeRackUnitEntry 12 }

cfprComputeRackUnitDescr OBJECT-TYPE
    SYNTAX       SnmpAdminString
    MAX-ACCESS   read-only
    STATUS       current
    DESCRIPTION
        "Cisco Firepower compute:RackUnit:descr managed object property"
    ::= { cfprComputeRackUnitEntry 13 }

cfprComputeRackUnitDiscovery OBJECT-TYPE
    SYNTAX       CfprComputeDiscovery
    MAX-ACCESS   read-only
    STATUS       current
    DESCRIPTION
        "Cisco Firepower compute:RackUnit:discovery managed
        object property"
    ::= { cfprComputeRackUnitEntry 14 }

cfprComputeRackUnitFltAggr OBJECT-TYPE
    SYNTAX       Unsigned64
    MAX-ACCESS   read-only
    STATUS       current
    DESCRIPTION
        "Cisco Firepower compute:RackUnit:fltAggr managed object property"
    ::= { cfprComputeRackUnitEntry 15 }

cfprComputeRackUnitFsmDescr OBJECT-TYPE
    SYNTAX       SnmpAdminString
    MAX-ACCESS   read-only
    STATUS       current
    DESCRIPTION
        "Cisco Firepower compute:RackUnit:fsmDescr managed
        object property"
    ::= { cfprComputeRackUnitEntry 16 }

cfprComputeRackUnitFsmFlags OBJECT-TYPE
    SYNTAX       SnmpAdminString
    MAX-ACCESS   read-only
    STATUS       current
    DESCRIPTION
        "Cisco Firepower compute:RackUnit:fsmFlags managed
        object property"
    ::= { cfprComputeRackUnitEntry 17 }

cfprComputeRackUnitFsmPrev OBJECT-TYPE
    SYNTAX       SnmpAdminString
    MAX-ACCESS   read-only
    STATUS       current
    DESCRIPTION
        "Cisco Firepower compute:RackUnit:fsmPrev managed object property"
    ::= { cfprComputeRackUnitEntry 18 }

cfprComputeRackUnitFsmProgr OBJECT-TYPE
    SYNTAX       Gauge32
    MAX-ACCESS   read-only
    STATUS       current
    DESCRIPTION
        "Cisco Firepower compute:RackUnit:fsmProgr managed
        object property"
    ::= { cfprComputeRackUnitEntry 19 }

cfprComputeRackUnitFsmRmtInvErrCode OBJECT-TYPE
    SYNTAX       Gauge32
    MAX-ACCESS   read-only
    STATUS       current
    DESCRIPTION
        "Cisco Firepower compute:RackUnit:fsmRmtInvErrCode
        managed object property"
    ::= { cfprComputeRackUnitEntry 20 }

cfprComputeRackUnitFsmRmtInvErrDescr OBJECT-TYPE
    SYNTAX       SnmpAdminString
    MAX-ACCESS   read-only
    STATUS       current
    DESCRIPTION
        "Cisco Firepower compute:RackUnit:fsmRmtInvErrDescr
        managed object property"
    ::= { cfprComputeRackUnitEntry 21 }

cfprComputeRackUnitFsmRmtInvRslt OBJECT-TYPE
    SYNTAX       CfprConditionRemoteInvRslt
    MAX-ACCESS   read-only
    STATUS       current
    DESCRIPTION
        "Cisco Firepower compute:RackUnit:fsmRmtInvRslt
        managed object property"
    ::= { cfprComputeRackUnitEntry 22 }

cfprComputeRackUnitFsmStageDescr OBJECT-TYPE
    SYNTAX       SnmpAdminString
    MAX-ACCESS   read-only
    STATUS       current
    DESCRIPTION
        "Cisco Firepower compute:RackUnit:fsmStageDescr
        managed object property"
    ::= { cfprComputeRackUnitEntry 23 }

cfprComputeRackUnitFsmStamp OBJECT-TYPE
    SYNTAX       DateAndTime
    MAX-ACCESS   read-only
    STATUS       current
    DESCRIPTION
        "Cisco Firepower compute:RackUnit:fsmStamp managed
        object property"
    ::= { cfprComputeRackUnitEntry 24 }

cfprComputeRackUnitFsmStatus OBJECT-TYPE
    SYNTAX       SnmpAdminString
    MAX-ACCESS   read-only
    STATUS       current
    DESCRIPTION
        "Cisco Firepower compute:RackUnit:fsmStatus managed
        object property"
    ::= { cfprComputeRackUnitEntry 25 }

cfprComputeRackUnitFsmTry OBJECT-TYPE
    SYNTAX       Gauge32
    MAX-ACCESS   read-only
    STATUS       current
    DESCRIPTION
        "Cisco Firepower compute:RackUnit:fsmTry managed object property"
    ::= { cfprComputeRackUnitEntry 26 }

cfprComputeRackUnitId OBJECT-TYPE
    SYNTAX       CfprComputeRackUnitId
    MAX-ACCESS   read-only
    STATUS       current
    DESCRIPTION
        "Cisco Firepower compute:RackUnit:id managed object property"
    ::= { cfprComputeRackUnitEntry 27 }

cfprComputeRackUnitIntId OBJECT-TYPE
    SYNTAX       SnmpAdminString
    MAX-ACCESS   read-only
    STATUS       current
    DESCRIPTION
        "Cisco Firepower compute:RackUnit:intId managed object property"
    ::= { cfprComputeRackUnitEntry 28 }

cfprComputeRackUnitLc OBJECT-TYPE
    SYNTAX       CfprComputeAdminTrigger
    MAX-ACCESS   read-only
    STATUS       current
    DESCRIPTION
        "Cisco Firepower compute:RackUnit:lc managed object property"
    ::= { cfprComputeRackUnitEntry 29 }

cfprComputeRackUnitLcTs OBJECT-TYPE
    SYNTAX       DateAndTime
    MAX-ACCESS   read-only
    STATUS       current
    DESCRIPTION
        "Cisco Firepower compute:RackUnit:lcTs managed object property"
    ::= { cfprComputeRackUnitEntry 30 }

cfprComputeRackUnitLocalId OBJECT-TYPE
    SYNTAX       SnmpAdminString
    MAX-ACCESS   read-only
    STATUS       current
    DESCRIPTION
        "Cisco Firepower compute:RackUnit:localId managed object property"
    ::= { cfprComputeRackUnitEntry 31 }

cfprComputeRackUnitLowVoltageMemory OBJECT-TYPE
    SYNTAX       CfprComputePhysicalLowVoltageMemory
    MAX-ACCESS   read-only
    STATUS       current
    DESCRIPTION
        "Cisco Firepower compute:RackUnit:lowVoltageMemory
        managed object property"
    ::= { cfprComputeRackUnitEntry 32 }

cfprComputeRackUnitManagingInst OBJECT-TYPE
    SYNTAX       CfprNetworkSwitchId
    MAX-ACCESS   read-only
    STATUS       current
    DESCRIPTION
        "Cisco Firepower compute:RackUnit:managingInst
        managed object property"
    ::= { cfprComputeRackUnitEntry 33 }

cfprComputeRackUnitMemorySpeed OBJECT-TYPE
    SYNTAX       Gauge32
    MAX-ACCESS   read-only
    STATUS       current
    DESCRIPTION
        "Cisco Firepower compute:RackUnit:memorySpeed managed
        object property"
    ::= { cfprComputeRackUnitEntry 34 }

cfprComputeRackUnitMfgTime OBJECT-TYPE
    SYNTAX       DateAndTime
    MAX-ACCESS   read-only
    STATUS       current
    DESCRIPTION
        "Cisco Firepower compute:RackUnit:mfgTime managed object property"
    ::= { cfprComputeRackUnitEntry 35 }

cfprComputeRackUnitModel OBJECT-TYPE
    SYNTAX       SnmpAdminString
    MAX-ACCESS   read-only
    STATUS       current
    DESCRIPTION
        "Cisco Firepower compute:RackUnit:model managed object property"
    ::= { cfprComputeRackUnitEntry 36 }

cfprComputeRackUnitName OBJECT-TYPE
    SYNTAX       SnmpAdminString
    MAX-ACCESS   read-only
    STATUS       current
    DESCRIPTION
        "Cisco Firepower compute:RackUnit:name managed object property"
    ::= { cfprComputeRackUnitEntry 37 }

cfprComputeRackUnitNumOfAdaptors OBJECT-TYPE
    SYNTAX       Gauge32
    MAX-ACCESS   read-only
    STATUS       current
    DESCRIPTION
        "Cisco Firepower compute:RackUnit:numOfAdaptors
        managed object property"
    ::= { cfprComputeRackUnitEntry 38 }

cfprComputeRackUnitNumOfCores OBJECT-TYPE
    SYNTAX       Gauge32
    MAX-ACCESS   read-only
    STATUS       current
    DESCRIPTION
        "Cisco Firepower compute:RackUnit:numOfCores managed
        object property"
    ::= { cfprComputeRackUnitEntry 39 }

cfprComputeRackUnitNumOfCoresEnabled OBJECT-TYPE
    SYNTAX       Gauge32
    MAX-ACCESS   read-only
    STATUS       current
    DESCRIPTION
        "Cisco Firepower compute:RackUnit:numOfCoresEnabled
        managed object property"
    ::= { cfprComputeRackUnitEntry 40 }

cfprComputeRackUnitNumOfCpus OBJECT-TYPE
    SYNTAX       Gauge32
    MAX-ACCESS   read-only
    STATUS       current
    DESCRIPTION
        "Cisco Firepower compute:RackUnit:numOfCpus managed
        object property"
    ::= { cfprComputeRackUnitEntry 41 }

cfprComputeRackUnitNumOfEthHostIfs OBJECT-TYPE
    SYNTAX       Gauge32
    MAX-ACCESS   read-only
    STATUS       current
    DESCRIPTION
        "Cisco Firepower compute:RackUnit:numOfEthHostIfs
        managed object property"
    ::= { cfprComputeRackUnitEntry 42 }

cfprComputeRackUnitNumOfFcHostIfs OBJECT-TYPE
    SYNTAX       Gauge32
    MAX-ACCESS   read-only
    STATUS       current
    DESCRIPTION
        "Cisco Firepower compute:RackUnit:numOfFcHostIfs
        managed object property"
    ::= { cfprComputeRackUnitEntry 43 }

cfprComputeRackUnitNumOfThreads OBJECT-TYPE
    SYNTAX       Gauge32
    MAX-ACCESS   read-only
    STATUS       current
    DESCRIPTION
        "Cisco Firepower compute:RackUnit:numOfThreads
        managed object property"
    ::= { cfprComputeRackUnitEntry 44 }

cfprComputeRackUnitOperPower OBJECT-TYPE
    SYNTAX       CfprEquipmentPowerState
    MAX-ACCESS   read-only
    STATUS       current
    DESCRIPTION
        "Cisco Firepower compute:RackUnit:operPower managed
        object property"
    ::= { cfprComputeRackUnitEntry 45 }

cfprComputeRackUnitOperQualifier OBJECT-TYPE
    SYNTAX       CfprComputeIssues
    MAX-ACCESS   read-only
    STATUS       current
    DESCRIPTION
        "Cisco Firepower compute:RackUnit:operQualifier
        managed object property"
    ::= { cfprComputeRackUnitEntry 46 }

cfprComputeRackUnitOperState OBJECT-TYPE
    SYNTAX       CfprLsOperState
    MAX-ACCESS   read-only
    STATUS       current
    DESCRIPTION
        "Cisco Firepower compute:RackUnit:operState managed
        object property"
    ::= { cfprComputeRackUnitEntry 47 }

cfprComputeRackUnitOperability OBJECT-TYPE
    SYNTAX       CfprEquipmentOperability
    MAX-ACCESS   read-only
    STATUS       current
    DESCRIPTION
        "Cisco Firepower compute:RackUnit:operability managed
        object property"
    ::= { cfprComputeRackUnitEntry 48 }

cfprComputeRackUnitOriginalUuid OBJECT-TYPE
    SYNTAX       SnmpAdminString
    MAX-ACCESS   read-only
    STATUS       current
    DESCRIPTION
        "Cisco Firepower compute:RackUnit:originalUuid
        managed object property"
    ::= { cfprComputeRackUnitEntry 49 }

cfprComputeRackUnitPartNumber OBJECT-TYPE
    SYNTAX       SnmpAdminString
    MAX-ACCESS   read-only
    STATUS       current
    DESCRIPTION
        "Cisco Firepower compute:RackUnit:partNumber managed
        object property"
    ::= { cfprComputeRackUnitEntry 50 }

cfprComputeRackUnitPolicyLevel OBJECT-TYPE
    SYNTAX       Gauge32
    MAX-ACCESS   read-only
    STATUS       current
    DESCRIPTION
        "Cisco Firepower compute:RackUnit:policyLevel managed
        object property"
    ::= { cfprComputeRackUnitEntry 51 }

cfprComputeRackUnitPolicyOwner OBJECT-TYPE
    SYNTAX       CfprPolicyPolicyOwner
    MAX-ACCESS   read-only
    STATUS       current
    DESCRIPTION
        "Cisco Firepower compute:RackUnit:policyOwner managed
        object property"
    ::= { cfprComputeRackUnitEntry 52 }

cfprComputeRackUnitPresence OBJECT-TYPE
    SYNTAX       CfprEquipmentSlotStatus
    MAX-ACCESS   read-only
    STATUS       current
    DESCRIPTION
        "Cisco Firepower compute:RackUnit:presence managed
        object property"
    ::= { cfprComputeRackUnitEntry 53 }

cfprComputeRackUnitRevision OBJECT-TYPE
    SYNTAX       SnmpAdminString
    MAX-ACCESS   read-only
    STATUS       current
    DESCRIPTION
        "Cisco Firepower compute:RackUnit:revision managed
        object property"
    ::= { cfprComputeRackUnitEntry 54 }

cfprComputeRackUnitSerial OBJECT-TYPE
    SYNTAX       SnmpAdminString
    MAX-ACCESS   read-only
    STATUS       current
    DESCRIPTION
        "Cisco Firepower compute:RackUnit:serial managed object property"
    ::= { cfprComputeRackUnitEntry 55 }

cfprComputeRackUnitServerId OBJECT-TYPE
    SYNTAX       SnmpAdminString
    MAX-ACCESS   read-only
    STATUS       current
    DESCRIPTION
        "Cisco Firepower compute:RackUnit:serverId managed
        object property"
    ::= { cfprComputeRackUnitEntry 56 }

cfprComputeRackUnitTotalMemory OBJECT-TYPE
    SYNTAX       Gauge32
    MAX-ACCESS   read-only
    STATUS       current
    DESCRIPTION
        "Cisco Firepower compute:RackUnit:totalMemory managed
        object property"
    ::= { cfprComputeRackUnitEntry 57 }

cfprComputeRackUnitUsrLbl OBJECT-TYPE
    SYNTAX       SnmpAdminString
    MAX-ACCESS   read-only
    STATUS       current
    DESCRIPTION
        "Cisco Firepower compute:RackUnit:usrLbl managed object property"
    ::= { cfprComputeRackUnitEntry 58 }

cfprComputeRackUnitUuid OBJECT-TYPE
    SYNTAX       SnmpAdminString
    MAX-ACCESS   read-only
    STATUS       current
    DESCRIPTION
        "Cisco Firepower compute:RackUnit:uuid managed object property"
    ::= { cfprComputeRackUnitEntry 59 }

cfprComputeRackUnitVendor OBJECT-TYPE
    SYNTAX       SnmpAdminString
    MAX-ACCESS   read-only
    STATUS       current
    DESCRIPTION
        "Cisco Firepower compute:RackUnit:vendor managed object property"
    ::= { cfprComputeRackUnitEntry 60 }

cfprComputeRackUnitVersionHolder OBJECT-TYPE
    SYNTAX       TruthValue
    MAX-ACCESS   read-only
    STATUS       current
    DESCRIPTION
        "Cisco Firepower compute:RackUnit:versionHolder
        managed object property"
    ::= { cfprComputeRackUnitEntry 61 }

cfprComputeRackUnitVid OBJECT-TYPE
    SYNTAX       SnmpAdminString
    MAX-ACCESS   read-only
    STATUS       current
    DESCRIPTION
        "Cisco Firepower compute:RackUnit:vid managed object property"
    ::= { cfprComputeRackUnitEntry 62 }

cfprComputeRackUnitPostState OBJECT-TYPE
    SYNTAX       CfprEquipmentBiosPostState
    MAX-ACCESS   read-only
    STATUS       current
    DESCRIPTION
        "Cisco Firepower compute:RackUnit:postState managed
        object property"
    ::= { cfprComputeRackUnitEntry 63 }

cfprComputeRackUnitFsmTable OBJECT-TYPE
    SYNTAX           SEQUENCE OF CfprComputeRackUnitFsmEntry
    MAX-ACCESS       not-accessible
    STATUS           current
    DESCRIPTION
        "Cisco Firepower compute:RackUnitFsm managed object table"
    ::= { cfprComputeObjects 53 }

cfprComputeRackUnitFsmEntry OBJECT-TYPE
    SYNTAX           CfprComputeRackUnitFsmEntry
    MAX-ACCESS       not-accessible
    STATUS           current
    DESCRIPTION
        "Entry for the cfprComputeRackUnitFsmTable table."
    INDEX { cfprComputeRackUnitFsmInstanceId }
    ::= { cfprComputeRackUnitFsmTable 1 }

CfprComputeRackUnitFsmEntry ::= SEQUENCE {
    cfprComputeRackUnitFsmInstanceId                                 CfprManagedObjectId,
    cfprComputeRackUnitFsmDn                                         CfprManagedObjectDn,
    cfprComputeRackUnitFsmRn                                         SnmpAdminString,
    cfprComputeRackUnitFsmCompletionTime                             DateAndTime,
    cfprComputeRackUnitFsmCurrentFsm                                 CfprComputeRackUnitFsmCurrentFsm,
    cfprComputeRackUnitFsmDescrData                                  SnmpAdminString,
    cfprComputeRackUnitFsmFsmStatus                                  CfprFsmFsmStageStatus,
    cfprComputeRackUnitFsmProgress                                   Gauge32,
    cfprComputeRackUnitFsmRmtErrCode                                 Gauge32,
    cfprComputeRackUnitFsmRmtErrDescr                                SnmpAdminString,
    cfprComputeRackUnitFsmRmtRslt                                    CfprConditionRemoteInvRslt
}

cfprComputeRackUnitFsmInstanceId OBJECT-TYPE
    SYNTAX       CfprManagedObjectId
    MAX-ACCESS   not-accessible
    STATUS       current
    DESCRIPTION
        "Instance identifier of the managed object."
    ::= { cfprComputeRackUnitFsmEntry 1 }

cfprComputeRackUnitFsmDn OBJECT-TYPE
    SYNTAX       CfprManagedObjectDn
    MAX-ACCESS   read-only
    STATUS       current
    DESCRIPTION
        "Cisco Firepower compute:RackUnitFsm:dn managed object property"
    ::= { cfprComputeRackUnitFsmEntry 2 }

cfprComputeRackUnitFsmRn OBJECT-TYPE
    SYNTAX       SnmpAdminString
    MAX-ACCESS   read-only
    STATUS       current
    DESCRIPTION
        "Cisco Firepower compute:RackUnitFsm:rn managed object property"
    ::= { cfprComputeRackUnitFsmEntry 3 }

cfprComputeRackUnitFsmCompletionTime OBJECT-TYPE
    SYNTAX       DateAndTime
    MAX-ACCESS   read-only
    STATUS       current
    DESCRIPTION
        "Cisco Firepower compute:RackUnitFsm:completionTime
        managed object property"
    ::= { cfprComputeRackUnitFsmEntry 4 }

cfprComputeRackUnitFsmCurrentFsm OBJECT-TYPE
    SYNTAX       CfprComputeRackUnitFsmCurrentFsm
    MAX-ACCESS   read-only
    STATUS       current
    DESCRIPTION
        "Cisco Firepower compute:RackUnitFsm:currentFsm
        managed object property"
    ::= { cfprComputeRackUnitFsmEntry 5 }

cfprComputeRackUnitFsmDescrData OBJECT-TYPE
    SYNTAX       SnmpAdminString
    MAX-ACCESS   read-only
    STATUS       current
    DESCRIPTION
        "Cisco Firepower compute:RackUnitFsm:descr managed
        object property"
    ::= { cfprComputeRackUnitFsmEntry 6 }

cfprComputeRackUnitFsmFsmStatus OBJECT-TYPE
    SYNTAX       CfprFsmFsmStageStatus
    MAX-ACCESS   read-only
    STATUS       current
    DESCRIPTION
        "Cisco Firepower compute:RackUnitFsm:fsmStatus
        managed object property"
    ::= { cfprComputeRackUnitFsmEntry 7 }

cfprComputeRackUnitFsmProgress OBJECT-TYPE
    SYNTAX       Gauge32
    MAX-ACCESS   read-only
    STATUS       current
    DESCRIPTION
        "Cisco Firepower compute:RackUnitFsm:progress managed
        object property"
    ::= { cfprComputeRackUnitFsmEntry 8 }

cfprComputeRackUnitFsmRmtErrCode OBJECT-TYPE
    SYNTAX       Gauge32
    MAX-ACCESS   read-only
    STATUS       current
    DESCRIPTION
        "Cisco Firepower compute:RackUnitFsm:rmtErrCode
        managed object property"
    ::= { cfprComputeRackUnitFsmEntry 9 }

cfprComputeRackUnitFsmRmtErrDescr OBJECT-TYPE
    SYNTAX       SnmpAdminString
    MAX-ACCESS   read-only
    STATUS       current
    DESCRIPTION
        "Cisco Firepower compute:RackUnitFsm:rmtErrDescr
        managed object property"
    ::= { cfprComputeRackUnitFsmEntry 10 }

cfprComputeRackUnitFsmRmtRslt OBJECT-TYPE
    SYNTAX       CfprConditionRemoteInvRslt
    MAX-ACCESS   read-only
    STATUS       current
    DESCRIPTION
        "Cisco Firepower compute:RackUnitFsm:rmtRslt managed
        object property"
    ::= { cfprComputeRackUnitFsmEntry 11 }

cfprComputeRackUnitFsmStageTable OBJECT-TYPE
    SYNTAX           SEQUENCE OF CfprComputeRackUnitFsmStageEntry
    MAX-ACCESS       not-accessible
    STATUS           current
    DESCRIPTION
        "Cisco Firepower compute:RackUnitFsmStage managed object table"
    ::= { cfprComputeObjects 54 }

cfprComputeRackUnitFsmStageEntry OBJECT-TYPE
    SYNTAX           CfprComputeRackUnitFsmStageEntry
    MAX-ACCESS       not-accessible
    STATUS           current
    DESCRIPTION
        "Entry for the cfprComputeRackUnitFsmStageTable table."
    INDEX { cfprComputeRackUnitFsmStageInstanceId }
    ::= { cfprComputeRackUnitFsmStageTable 1 }

CfprComputeRackUnitFsmStageEntry ::= SEQUENCE {
    cfprComputeRackUnitFsmStageInstanceId                            CfprManagedObjectId,
    cfprComputeRackUnitFsmStageDn                                    CfprManagedObjectDn,
    cfprComputeRackUnitFsmStageRn                                    SnmpAdminString,
    cfprComputeRackUnitFsmStageDescrData                             SnmpAdminString,
    cfprComputeRackUnitFsmStageLastUpdateTime                        DateAndTime,
    cfprComputeRackUnitFsmStageName                                  CfprComputeRackUnitFsmStageName,
    cfprComputeRackUnitFsmStageOrder                                 Gauge32,
    cfprComputeRackUnitFsmStageRetry                                 Gauge32,
    cfprComputeRackUnitFsmStageStageStatus                           CfprFsmFsmStageStatus
}

cfprComputeRackUnitFsmStageInstanceId OBJECT-TYPE
    SYNTAX       CfprManagedObjectId
    MAX-ACCESS   not-accessible
    STATUS       current
    DESCRIPTION
        "Instance identifier of the managed object."
    ::= { cfprComputeRackUnitFsmStageEntry 1 }

cfprComputeRackUnitFsmStageDn OBJECT-TYPE
    SYNTAX       CfprManagedObjectDn
    MAX-ACCESS   read-only
    STATUS       current
    DESCRIPTION
        "Cisco Firepower compute:RackUnitFsmStage:dn managed
        object property"
    ::= { cfprComputeRackUnitFsmStageEntry 2 }

cfprComputeRackUnitFsmStageRn OBJECT-TYPE
    SYNTAX       SnmpAdminString
    MAX-ACCESS   read-only
    STATUS       current
    DESCRIPTION
        "Cisco Firepower compute:RackUnitFsmStage:rn managed
        object property"
    ::= { cfprComputeRackUnitFsmStageEntry 3 }

cfprComputeRackUnitFsmStageDescrData OBJECT-TYPE
    SYNTAX       SnmpAdminString
    MAX-ACCESS   read-only
    STATUS       current
    DESCRIPTION
        "Cisco Firepower compute:RackUnitFsmStage:descr
        managed object property"
    ::= { cfprComputeRackUnitFsmStageEntry 4 }

cfprComputeRackUnitFsmStageLastUpdateTime OBJECT-TYPE
    SYNTAX       DateAndTime
    MAX-ACCESS   read-only
    STATUS       current
    DESCRIPTION
        "Cisco Firepower compute:RackUnitFsmStage:lastUpdateTime
        managed object property"
    ::= { cfprComputeRackUnitFsmStageEntry 5 }

cfprComputeRackUnitFsmStageName OBJECT-TYPE
    SYNTAX       CfprComputeRackUnitFsmStageName
    MAX-ACCESS   read-only
    STATUS       current
    DESCRIPTION
        "Cisco Firepower compute:RackUnitFsmStage:name
        managed object property"
    ::= { cfprComputeRackUnitFsmStageEntry 6 }

cfprComputeRackUnitFsmStageOrder OBJECT-TYPE
    SYNTAX       Gauge32
    MAX-ACCESS   read-only
    STATUS       current
    DESCRIPTION
        "Cisco Firepower compute:RackUnitFsmStage:order
        managed object property"
    ::= { cfprComputeRackUnitFsmStageEntry 7 }

cfprComputeRackUnitFsmStageRetry OBJECT-TYPE
    SYNTAX       Gauge32
    MAX-ACCESS   read-only
    STATUS       current
    DESCRIPTION
        "Cisco Firepower compute:RackUnitFsmStage:retry
        managed object property"
    ::= { cfprComputeRackUnitFsmStageEntry 8 }

cfprComputeRackUnitFsmStageStageStatus OBJECT-TYPE
    SYNTAX       CfprFsmFsmStageStatus
    MAX-ACCESS   read-only
    STATUS       current
    DESCRIPTION
        "Cisco Firepower compute:RackUnitFsmStage:stageStatus
        managed object property"
    ::= { cfprComputeRackUnitFsmStageEntry 9 }

cfprComputeRackUnitFsmTaskTable OBJECT-TYPE
    SYNTAX           SEQUENCE OF CfprComputeRackUnitFsmTaskEntry
    MAX-ACCESS       not-accessible
    STATUS           current
    DESCRIPTION
        "Cisco Firepower compute:RackUnitFsmTask managed object table"
    ::= { cfprComputeObjects 55 }

cfprComputeRackUnitFsmTaskEntry OBJECT-TYPE
    SYNTAX           CfprComputeRackUnitFsmTaskEntry
    MAX-ACCESS       not-accessible
    STATUS           current
    DESCRIPTION
        "Entry for the cfprComputeRackUnitFsmTaskTable table."
    INDEX { cfprComputeRackUnitFsmTaskInstanceId }
    ::= { cfprComputeRackUnitFsmTaskTable 1 }

CfprComputeRackUnitFsmTaskEntry ::= SEQUENCE {
    cfprComputeRackUnitFsmTaskInstanceId                             CfprManagedObjectId,
    cfprComputeRackUnitFsmTaskDn                                     CfprManagedObjectDn,
    cfprComputeRackUnitFsmTaskRn                                     SnmpAdminString,
    cfprComputeRackUnitFsmTaskCompletion                             CfprFsmCompletion,
    cfprComputeRackUnitFsmTaskFlags                                  CfprComputeRackUnitFsmTaskFlags,
    cfprComputeRackUnitFsmTaskItem                                   CfprComputeRackUnitFsmTaskItem,
    cfprComputeRackUnitFsmTaskSeqId                                  Gauge32
}

cfprComputeRackUnitFsmTaskInstanceId OBJECT-TYPE
    SYNTAX       CfprManagedObjectId
    MAX-ACCESS   not-accessible
    STATUS       current
    DESCRIPTION
        "Instance identifier of the managed object."
    ::= { cfprComputeRackUnitFsmTaskEntry 1 }

cfprComputeRackUnitFsmTaskDn OBJECT-TYPE
    SYNTAX       CfprManagedObjectDn
    MAX-ACCESS   read-only
    STATUS       current
    DESCRIPTION
        "Cisco Firepower compute:RackUnitFsmTask:dn managed
        object property"
    ::= { cfprComputeRackUnitFsmTaskEntry 2 }

cfprComputeRackUnitFsmTaskRn OBJECT-TYPE
    SYNTAX       SnmpAdminString
    MAX-ACCESS   read-only
    STATUS       current
    DESCRIPTION
        "Cisco Firepower compute:RackUnitFsmTask:rn managed
        object property"
    ::= { cfprComputeRackUnitFsmTaskEntry 3 }

cfprComputeRackUnitFsmTaskCompletion OBJECT-TYPE
    SYNTAX       CfprFsmCompletion
    MAX-ACCESS   read-only
    STATUS       current
    DESCRIPTION
        "Cisco Firepower compute:RackUnitFsmTask:completion
        managed object property"
    ::= { cfprComputeRackUnitFsmTaskEntry 4 }

cfprComputeRackUnitFsmTaskFlags OBJECT-TYPE
    SYNTAX       CfprComputeRackUnitFsmTaskFlags
    MAX-ACCESS   read-only
    STATUS       current
    DESCRIPTION
        "Cisco Firepower compute:RackUnitFsmTask:flags
        managed object property"
    ::= { cfprComputeRackUnitFsmTaskEntry 5 }

cfprComputeRackUnitFsmTaskItem OBJECT-TYPE
    SYNTAX       CfprComputeRackUnitFsmTaskItem
    MAX-ACCESS   read-only
    STATUS       current
    DESCRIPTION
        "Cisco Firepower compute:RackUnitFsmTask:item managed
        object property"
    ::= { cfprComputeRackUnitFsmTaskEntry 6 }

cfprComputeRackUnitFsmTaskSeqId OBJECT-TYPE
    SYNTAX       Gauge32
    MAX-ACCESS   read-only
    STATUS       current
    DESCRIPTION
        "Cisco Firepower compute:RackUnitFsmTask:seqId
        managed object property"
    ::= { cfprComputeRackUnitFsmTaskEntry 7 }

cfprComputeRackUnitMbTempStatsTable OBJECT-TYPE
    SYNTAX           SEQUENCE OF CfprComputeRackUnitMbTempStatsEntry
    MAX-ACCESS       not-accessible
    STATUS           current
    DESCRIPTION
        "Cisco Firepower compute:RackUnitMbTempStats managed object table"
    ::= { cfprComputeObjects 56 }

cfprComputeRackUnitMbTempStatsEntry OBJECT-TYPE
    SYNTAX           CfprComputeRackUnitMbTempStatsEntry
    MAX-ACCESS       not-accessible
    STATUS           current
    DESCRIPTION
        "Entry for the cfprComputeRackUnitMbTempStatsTable table."
    INDEX { cfprComputeRackUnitMbTempStatsInstanceId }
    ::= { cfprComputeRackUnitMbTempStatsTable 1 }

CfprComputeRackUnitMbTempStatsEntry ::= SEQUENCE {
    cfprComputeRackUnitMbTempStatsInstanceId                         CfprManagedObjectId,
    cfprComputeRackUnitMbTempStatsDn                                 CfprManagedObjectDn,
    cfprComputeRackUnitMbTempStatsRn                                 SnmpAdminString,
    cfprComputeRackUnitMbTempStatsAmbientTemp                        INTEGER,
    cfprComputeRackUnitMbTempStatsAmbientTempAvg                     INTEGER,
    cfprComputeRackUnitMbTempStatsAmbientTempMax                     INTEGER,
    cfprComputeRackUnitMbTempStatsAmbientTempMin                     INTEGER,
    cfprComputeRackUnitMbTempStatsFrontTemp                          INTEGER,
    cfprComputeRackUnitMbTempStatsFrontTempAvg                       INTEGER,
    cfprComputeRackUnitMbTempStatsFrontTempMax                       INTEGER,
    cfprComputeRackUnitMbTempStatsFrontTempMin                       INTEGER,
    cfprComputeRackUnitMbTempStatsIntervals                          Gauge32,
    cfprComputeRackUnitMbTempStatsIoh1Temp                           INTEGER,
    cfprComputeRackUnitMbTempStatsIoh1TempAvg                        INTEGER,
    cfprComputeRackUnitMbTempStatsIoh1TempMax                        INTEGER,
    cfprComputeRackUnitMbTempStatsIoh1TempMin                        INTEGER,
    cfprComputeRackUnitMbTempStatsIoh2Temp                           INTEGER,
    cfprComputeRackUnitMbTempStatsIoh2TempAvg                        INTEGER,
    cfprComputeRackUnitMbTempStatsIoh2TempMax                        INTEGER,
    cfprComputeRackUnitMbTempStatsIoh2TempMin                        INTEGER,
    cfprComputeRackUnitMbTempStatsRearTemp                           INTEGER,
    cfprComputeRackUnitMbTempStatsRearTempAvg                        INTEGER,
    cfprComputeRackUnitMbTempStatsRearTempMax                        INTEGER,
    cfprComputeRackUnitMbTempStatsRearTempMin                        INTEGER,
    cfprComputeRackUnitMbTempStatsSuspect                            TruthValue,
    cfprComputeRackUnitMbTempStatsThresholded                        CfprComputeRackUnitMbTempStatsThresholded,
    cfprComputeRackUnitMbTempStatsTimeCollected                      DateAndTime,
    cfprComputeRackUnitMbTempStatsUpdate                             Gauge32
}

cfprComputeRackUnitMbTempStatsInstanceId OBJECT-TYPE
    SYNTAX       CfprManagedObjectId
    MAX-ACCESS   not-accessible
    STATUS       current
    DESCRIPTION
        "Instance identifier of the managed object."
    ::= { cfprComputeRackUnitMbTempStatsEntry 1 }

cfprComputeRackUnitMbTempStatsDn OBJECT-TYPE
    SYNTAX       CfprManagedObjectDn
    MAX-ACCESS   read-only
    STATUS       current
    DESCRIPTION
        "Cisco Firepower compute:RackUnitMbTempStats:dn
        managed object property"
    ::= { cfprComputeRackUnitMbTempStatsEntry 2 }

cfprComputeRackUnitMbTempStatsRn OBJECT-TYPE
    SYNTAX       SnmpAdminString
    MAX-ACCESS   read-only
    STATUS       current
    DESCRIPTION
        "Cisco Firepower compute:RackUnitMbTempStats:rn
        managed object property"
    ::= { cfprComputeRackUnitMbTempStatsEntry 3 }

cfprComputeRackUnitMbTempStatsAmbientTemp OBJECT-TYPE
    SYNTAX       INTEGER
    MAX-ACCESS   read-only
    STATUS       current
    DESCRIPTION
        "Cisco Firepower compute:RackUnitMbTempStats:ambientTemp
        managed object property"
    ::= { cfprComputeRackUnitMbTempStatsEntry 4 }

cfprComputeRackUnitMbTempStatsAmbientTempAvg OBJECT-TYPE
    SYNTAX       INTEGER
    MAX-ACCESS   read-only
    STATUS       current
    DESCRIPTION
        "Cisco Firepower compute:RackUnitMbTempStats:ambientTempAvg
        managed object property"
    ::= { cfprComputeRackUnitMbTempStatsEntry 5 }

cfprComputeRackUnitMbTempStatsAmbientTempMax OBJECT-TYPE
    SYNTAX       INTEGER
    MAX-ACCESS   read-only
    STATUS       current
    DESCRIPTION
        "Cisco Firepower compute:RackUnitMbTempStats:ambientTempMax
        managed object property"
    ::= { cfprComputeRackUnitMbTempStatsEntry 6 }

cfprComputeRackUnitMbTempStatsAmbientTempMin OBJECT-TYPE
    SYNTAX       INTEGER
    MAX-ACCESS   read-only
    STATUS       current
    DESCRIPTION
        "Cisco Firepower compute:RackUnitMbTempStats:ambientTempMin
        managed object property"
    ::= { cfprComputeRackUnitMbTempStatsEntry 7 }

cfprComputeRackUnitMbTempStatsFrontTemp OBJECT-TYPE
    SYNTAX       INTEGER
    MAX-ACCESS   read-only
    STATUS       current
    DESCRIPTION
        "Cisco Firepower compute:RackUnitMbTempStats:frontTemp
        managed object property"
    ::= { cfprComputeRackUnitMbTempStatsEntry 8 }

cfprComputeRackUnitMbTempStatsFrontTempAvg OBJECT-TYPE
    SYNTAX       INTEGER
    MAX-ACCESS   read-only
    STATUS       current
    DESCRIPTION
        "Cisco Firepower compute:RackUnitMbTempStats:frontTempAvg
        managed object property"
    ::= { cfprComputeRackUnitMbTempStatsEntry 9 }

cfprComputeRackUnitMbTempStatsFrontTempMax OBJECT-TYPE
    SYNTAX       INTEGER
    MAX-ACCESS   read-only
    STATUS       current
    DESCRIPTION
        "Cisco Firepower compute:RackUnitMbTempStats:frontTempMax
        managed object property"
    ::= { cfprComputeRackUnitMbTempStatsEntry 10 }

cfprComputeRackUnitMbTempStatsFrontTempMin OBJECT-TYPE
    SYNTAX       INTEGER
    MAX-ACCESS   read-only
    STATUS       current
    DESCRIPTION
        "Cisco Firepower compute:RackUnitMbTempStats:frontTempMin
        managed object property"
    ::= { cfprComputeRackUnitMbTempStatsEntry 11 }

cfprComputeRackUnitMbTempStatsIntervals OBJECT-TYPE
    SYNTAX       Gauge32
    MAX-ACCESS   read-only
    STATUS       current
    DESCRIPTION
        "Cisco Firepower compute:RackUnitMbTempStats:intervals
        managed object property"
    ::= { cfprComputeRackUnitMbTempStatsEntry 12 }

cfprComputeRackUnitMbTempStatsIoh1Temp OBJECT-TYPE
    SYNTAX       INTEGER
    MAX-ACCESS   read-only
    STATUS       current
    DESCRIPTION
        "Cisco Firepower compute:RackUnitMbTempStats:ioh1Temp
        managed object property"
    ::= { cfprComputeRackUnitMbTempStatsEntry 13 }

cfprComputeRackUnitMbTempStatsIoh1TempAvg OBJECT-TYPE
    SYNTAX       INTEGER
    MAX-ACCESS   read-only
    STATUS       current
    DESCRIPTION
        "Cisco Firepower compute:RackUnitMbTempStats:ioh1TempAvg
        managed object property"
    ::= { cfprComputeRackUnitMbTempStatsEntry 14 }

cfprComputeRackUnitMbTempStatsIoh1TempMax OBJECT-TYPE
    SYNTAX       INTEGER
    MAX-ACCESS   read-only
    STATUS       current
    DESCRIPTION
        "Cisco Firepower compute:RackUnitMbTempStats:ioh1TempMax
        managed object property"
    ::= { cfprComputeRackUnitMbTempStatsEntry 15 }

cfprComputeRackUnitMbTempStatsIoh1TempMin OBJECT-TYPE
    SYNTAX       INTEGER
    MAX-ACCESS   read-only
    STATUS       current
    DESCRIPTION
        "Cisco Firepower compute:RackUnitMbTempStats:ioh1TempMin
        managed object property"
    ::= { cfprComputeRackUnitMbTempStatsEntry 16 }

cfprComputeRackUnitMbTempStatsIoh2Temp OBJECT-TYPE
    SYNTAX       INTEGER
    MAX-ACCESS   read-only
    STATUS       current
    DESCRIPTION
        "Cisco Firepower compute:RackUnitMbTempStats:ioh2Temp
        managed object property"
    ::= { cfprComputeRackUnitMbTempStatsEntry 17 }

cfprComputeRackUnitMbTempStatsIoh2TempAvg OBJECT-TYPE
    SYNTAX       INTEGER
    MAX-ACCESS   read-only
    STATUS       current
    DESCRIPTION
        "Cisco Firepower compute:RackUnitMbTempStats:ioh2TempAvg
        managed object property"
    ::= { cfprComputeRackUnitMbTempStatsEntry 18 }

cfprComputeRackUnitMbTempStatsIoh2TempMax OBJECT-TYPE
    SYNTAX       INTEGER
    MAX-ACCESS   read-only
    STATUS       current
    DESCRIPTION
        "Cisco Firepower compute:RackUnitMbTempStats:ioh2TempMax
        managed object property"
    ::= { cfprComputeRackUnitMbTempStatsEntry 19 }

cfprComputeRackUnitMbTempStatsIoh2TempMin OBJECT-TYPE
    SYNTAX       INTEGER
    MAX-ACCESS   read-only
    STATUS       current
    DESCRIPTION
        "Cisco Firepower compute:RackUnitMbTempStats:ioh2TempMin
        managed object property"
    ::= { cfprComputeRackUnitMbTempStatsEntry 20 }

cfprComputeRackUnitMbTempStatsRearTemp OBJECT-TYPE
    SYNTAX       INTEGER
    MAX-ACCESS   read-only
    STATUS       current
    DESCRIPTION
        "Cisco Firepower compute:RackUnitMbTempStats:rearTemp
        managed object property"
    ::= { cfprComputeRackUnitMbTempStatsEntry 21 }

cfprComputeRackUnitMbTempStatsRearTempAvg OBJECT-TYPE
    SYNTAX       INTEGER
    MAX-ACCESS   read-only
    STATUS       current
    DESCRIPTION
        "Cisco Firepower compute:RackUnitMbTempStats:rearTempAvg
        managed object property"
    ::= { cfprComputeRackUnitMbTempStatsEntry 22 }

cfprComputeRackUnitMbTempStatsRearTempMax OBJECT-TYPE
    SYNTAX       INTEGER
    MAX-ACCESS   read-only
    STATUS       current
    DESCRIPTION
        "Cisco Firepower compute:RackUnitMbTempStats:rearTempMax
        managed object property"
    ::= { cfprComputeRackUnitMbTempStatsEntry 23 }

cfprComputeRackUnitMbTempStatsRearTempMin OBJECT-TYPE
    SYNTAX       INTEGER
    MAX-ACCESS   read-only
    STATUS       current
    DESCRIPTION
        "Cisco Firepower compute:RackUnitMbTempStats:rearTempMin
        managed object property"
    ::= { cfprComputeRackUnitMbTempStatsEntry 24 }

cfprComputeRackUnitMbTempStatsSuspect OBJECT-TYPE
    SYNTAX       TruthValue
    MAX-ACCESS   read-only
    STATUS       current
    DESCRIPTION
        "Cisco Firepower compute:RackUnitMbTempStats:suspect
        managed object property"
    ::= { cfprComputeRackUnitMbTempStatsEntry 25 }

cfprComputeRackUnitMbTempStatsThresholded OBJECT-TYPE
    SYNTAX       CfprComputeRackUnitMbTempStatsThresholded
    MAX-ACCESS   read-only
    STATUS       current
    DESCRIPTION
        "Cisco Firepower compute:RackUnitMbTempStats:thresholded
        managed object property"
    ::= { cfprComputeRackUnitMbTempStatsEntry 26 }

cfprComputeRackUnitMbTempStatsTimeCollected OBJECT-TYPE
    SYNTAX       DateAndTime
    MAX-ACCESS   read-only
    STATUS       current
    DESCRIPTION
        "Cisco Firepower compute:RackUnitMbTempStats:timeCollected
        managed object property"
    ::= { cfprComputeRackUnitMbTempStatsEntry 27 }

cfprComputeRackUnitMbTempStatsUpdate OBJECT-TYPE
    SYNTAX       Gauge32
    MAX-ACCESS   read-only
    STATUS       current
    DESCRIPTION
        "Cisco Firepower compute:RackUnitMbTempStats:update
        managed object property"
    ::= { cfprComputeRackUnitMbTempStatsEntry 28 }

cfprComputeRackUnitMbTempStatsHistTable OBJECT-TYPE
    SYNTAX           SEQUENCE OF CfprComputeRackUnitMbTempStatsHistEntry
    MAX-ACCESS       not-accessible
    STATUS           current
    DESCRIPTION
        "Cisco Firepower compute:RackUnitMbTempStatsHist
        managed object table"
    ::= { cfprComputeObjects 57 }

cfprComputeRackUnitMbTempStatsHistEntry OBJECT-TYPE
    SYNTAX           CfprComputeRackUnitMbTempStatsHistEntry
    MAX-ACCESS       not-accessible
    STATUS           current
    DESCRIPTION
        "Entry for the cfprComputeRackUnitMbTempStatsHistTable table."
    INDEX { cfprComputeRackUnitMbTempStatsHistInstanceId }
    ::= { cfprComputeRackUnitMbTempStatsHistTable 1 }

CfprComputeRackUnitMbTempStatsHistEntry ::= SEQUENCE {
    cfprComputeRackUnitMbTempStatsHistInstanceId                     CfprManagedObjectId,
    cfprComputeRackUnitMbTempStatsHistDn                             CfprManagedObjectDn,
    cfprComputeRackUnitMbTempStatsHistRn                             SnmpAdminString,
    cfprComputeRackUnitMbTempStatsHistAmbientTemp                    INTEGER,
    cfprComputeRackUnitMbTempStatsHistAmbientTempAvg                 INTEGER,
    cfprComputeRackUnitMbTempStatsHistAmbientTempMax                 INTEGER,
    cfprComputeRackUnitMbTempStatsHistAmbientTempMin                 INTEGER,
    cfprComputeRackUnitMbTempStatsHistFrontTemp                      INTEGER,
    cfprComputeRackUnitMbTempStatsHistFrontTempAvg                   INTEGER,
    cfprComputeRackUnitMbTempStatsHistFrontTempMax                   INTEGER,
    cfprComputeRackUnitMbTempStatsHistFrontTempMin                   INTEGER,
    cfprComputeRackUnitMbTempStatsHistId                             Unsigned64,
    cfprComputeRackUnitMbTempStatsHistIoh1Temp                       INTEGER,
    cfprComputeRackUnitMbTempStatsHistIoh1TempAvg                    INTEGER,
    cfprComputeRackUnitMbTempStatsHistIoh1TempMax                    INTEGER,
    cfprComputeRackUnitMbTempStatsHistIoh1TempMin                    INTEGER,
    cfprComputeRackUnitMbTempStatsHistIoh2Temp                       INTEGER,
    cfprComputeRackUnitMbTempStatsHistIoh2TempAvg                    INTEGER,
    cfprComputeRackUnitMbTempStatsHistIoh2TempMax                    INTEGER,
    cfprComputeRackUnitMbTempStatsHistIoh2TempMin                    INTEGER,
    cfprComputeRackUnitMbTempStatsHistMostRecent                     TruthValue,
    cfprComputeRackUnitMbTempStatsHistRearTemp                       INTEGER,
    cfprComputeRackUnitMbTempStatsHistRearTempAvg                    INTEGER,
    cfprComputeRackUnitMbTempStatsHistRearTempMax                    INTEGER,
    cfprComputeRackUnitMbTempStatsHistRearTempMin                    INTEGER,
    cfprComputeRackUnitMbTempStatsHistSuspect                        TruthValue,
    cfprComputeRackUnitMbTempStatsHistThresholded                    CfprComputeRackUnitMbTempStatsHistThresholded,
    cfprComputeRackUnitMbTempStatsHistTimeCollected                  DateAndTime
}

cfprComputeRackUnitMbTempStatsHistInstanceId OBJECT-TYPE
    SYNTAX       CfprManagedObjectId
    MAX-ACCESS   not-accessible
    STATUS       current
    DESCRIPTION
        "Instance identifier of the managed object."
    ::= { cfprComputeRackUnitMbTempStatsHistEntry 1 }

cfprComputeRackUnitMbTempStatsHistDn OBJECT-TYPE
    SYNTAX       CfprManagedObjectDn
    MAX-ACCESS   read-only
    STATUS       current
    DESCRIPTION
        "Cisco Firepower compute:RackUnitMbTempStatsHist:dn
        managed object property"
    ::= { cfprComputeRackUnitMbTempStatsHistEntry 2 }

cfprComputeRackUnitMbTempStatsHistRn OBJECT-TYPE
    SYNTAX       SnmpAdminString
    MAX-ACCESS   read-only
    STATUS       current
    DESCRIPTION
        "Cisco Firepower compute:RackUnitMbTempStatsHist:rn
        managed object property"
    ::= { cfprComputeRackUnitMbTempStatsHistEntry 3 }

cfprComputeRackUnitMbTempStatsHistAmbientTemp OBJECT-TYPE
    SYNTAX       INTEGER
    MAX-ACCESS   read-only
    STATUS       current
    DESCRIPTION
        "Cisco Firepower compute:RackUnitMbTempStatsHist:ambientTemp
        managed object property"
    ::= { cfprComputeRackUnitMbTempStatsHistEntry 4 }

cfprComputeRackUnitMbTempStatsHistAmbientTempAvg OBJECT-TYPE
    SYNTAX       INTEGER
    MAX-ACCESS   read-only
    STATUS       current
    DESCRIPTION
        "Cisco Firepower compute:RackUnitMbTempStatsHist:ambientTempAvg
        managed object property"
    ::= { cfprComputeRackUnitMbTempStatsHistEntry 5 }

cfprComputeRackUnitMbTempStatsHistAmbientTempMax OBJECT-TYPE
    SYNTAX       INTEGER
    MAX-ACCESS   read-only
    STATUS       current
    DESCRIPTION
        "Cisco Firepower compute:RackUnitMbTempStatsHist:ambientTempMax
        managed object property"
    ::= { cfprComputeRackUnitMbTempStatsHistEntry 6 }

cfprComputeRackUnitMbTempStatsHistAmbientTempMin OBJECT-TYPE
    SYNTAX       INTEGER
    MAX-ACCESS   read-only
    STATUS       current
    DESCRIPTION
        "Cisco Firepower compute:RackUnitMbTempStatsHist:ambientTempMin
        managed object property"
    ::= { cfprComputeRackUnitMbTempStatsHistEntry 7 }

cfprComputeRackUnitMbTempStatsHistFrontTemp OBJECT-TYPE
    SYNTAX       INTEGER
    MAX-ACCESS   read-only
    STATUS       current
    DESCRIPTION
        "Cisco Firepower compute:RackUnitMbTempStatsHist:frontTemp
        managed object property"
    ::= { cfprComputeRackUnitMbTempStatsHistEntry 8 }

cfprComputeRackUnitMbTempStatsHistFrontTempAvg OBJECT-TYPE
    SYNTAX       INTEGER
    MAX-ACCESS   read-only
    STATUS       current
    DESCRIPTION
        "Cisco Firepower compute:RackUnitMbTempStatsHist:frontTempAvg
        managed object property"
    ::= { cfprComputeRackUnitMbTempStatsHistEntry 9 }

cfprComputeRackUnitMbTempStatsHistFrontTempMax OBJECT-TYPE
    SYNTAX       INTEGER
    MAX-ACCESS   read-only
    STATUS       current
    DESCRIPTION
        "Cisco Firepower compute:RackUnitMbTempStatsHist:frontTempMax
        managed object property"
    ::= { cfprComputeRackUnitMbTempStatsHistEntry 10 }

cfprComputeRackUnitMbTempStatsHistFrontTempMin OBJECT-TYPE
    SYNTAX       INTEGER
    MAX-ACCESS   read-only
    STATUS       current
    DESCRIPTION
        "Cisco Firepower compute:RackUnitMbTempStatsHist:frontTempMin
        managed object property"
    ::= { cfprComputeRackUnitMbTempStatsHistEntry 11 }

cfprComputeRackUnitMbTempStatsHistId OBJECT-TYPE
    SYNTAX       Unsigned64
    MAX-ACCESS   read-only
    STATUS       current
    DESCRIPTION
        "Cisco Firepower compute:RackUnitMbTempStatsHist:id
        managed object property"
    ::= { cfprComputeRackUnitMbTempStatsHistEntry 12 }

cfprComputeRackUnitMbTempStatsHistIoh1Temp OBJECT-TYPE
    SYNTAX       INTEGER
    MAX-ACCESS   read-only
    STATUS       current
    DESCRIPTION
        "Cisco Firepower compute:RackUnitMbTempStatsHist:ioh1Temp
        managed object property"
    ::= { cfprComputeRackUnitMbTempStatsHistEntry 13 }

cfprComputeRackUnitMbTempStatsHistIoh1TempAvg OBJECT-TYPE
    SYNTAX       INTEGER
    MAX-ACCESS   read-only
    STATUS       current
    DESCRIPTION
        "Cisco Firepower compute:RackUnitMbTempStatsHist:ioh1TempAvg
        managed object property"
    ::= { cfprComputeRackUnitMbTempStatsHistEntry 14 }

cfprComputeRackUnitMbTempStatsHistIoh1TempMax OBJECT-TYPE
    SYNTAX       INTEGER
    MAX-ACCESS   read-only
    STATUS       current
    DESCRIPTION
        "Cisco Firepower compute:RackUnitMbTempStatsHist:ioh1TempMax
        managed object property"
    ::= { cfprComputeRackUnitMbTempStatsHistEntry 15 }

cfprComputeRackUnitMbTempStatsHistIoh1TempMin OBJECT-TYPE
    SYNTAX       INTEGER
    MAX-ACCESS   read-only
    STATUS       current
    DESCRIPTION
        "Cisco Firepower compute:RackUnitMbTempStatsHist:ioh1TempMin
        managed object property"
    ::= { cfprComputeRackUnitMbTempStatsHistEntry 16 }

cfprComputeRackUnitMbTempStatsHistIoh2Temp OBJECT-TYPE
    SYNTAX       INTEGER
    MAX-ACCESS   read-only
    STATUS       current
    DESCRIPTION
        "Cisco Firepower compute:RackUnitMbTempStatsHist:ioh2Temp
        managed object property"
    ::= { cfprComputeRackUnitMbTempStatsHistEntry 17 }

cfprComputeRackUnitMbTempStatsHistIoh2TempAvg OBJECT-TYPE
    SYNTAX       INTEGER
    MAX-ACCESS   read-only
    STATUS       current
    DESCRIPTION
        "Cisco Firepower compute:RackUnitMbTempStatsHist:ioh2TempAvg
        managed object property"
    ::= { cfprComputeRackUnitMbTempStatsHistEntry 18 }

cfprComputeRackUnitMbTempStatsHistIoh2TempMax OBJECT-TYPE
    SYNTAX       INTEGER
    MAX-ACCESS   read-only
    STATUS       current
    DESCRIPTION
        "Cisco Firepower compute:RackUnitMbTempStatsHist:ioh2TempMax
        managed object property"
    ::= { cfprComputeRackUnitMbTempStatsHistEntry 19 }

cfprComputeRackUnitMbTempStatsHistIoh2TempMin OBJECT-TYPE
    SYNTAX       INTEGER
    MAX-ACCESS   read-only
    STATUS       current
    DESCRIPTION
        "Cisco Firepower compute:RackUnitMbTempStatsHist:ioh2TempMin
        managed object property"
    ::= { cfprComputeRackUnitMbTempStatsHistEntry 20 }

cfprComputeRackUnitMbTempStatsHistMostRecent OBJECT-TYPE
    SYNTAX       TruthValue
    MAX-ACCESS   read-only
    STATUS       current
    DESCRIPTION
        "Cisco Firepower compute:RackUnitMbTempStatsHist:mostRecent
        managed object property"
    ::= { cfprComputeRackUnitMbTempStatsHistEntry 21 }

cfprComputeRackUnitMbTempStatsHistRearTemp OBJECT-TYPE
    SYNTAX       INTEGER
    MAX-ACCESS   read-only
    STATUS       current
    DESCRIPTION
        "Cisco Firepower compute:RackUnitMbTempStatsHist:rearTemp
        managed object property"
    ::= { cfprComputeRackUnitMbTempStatsHistEntry 22 }

cfprComputeRackUnitMbTempStatsHistRearTempAvg OBJECT-TYPE
    SYNTAX       INTEGER
    MAX-ACCESS   read-only
    STATUS       current
    DESCRIPTION
        "Cisco Firepower compute:RackUnitMbTempStatsHist:rearTempAvg
        managed object property"
    ::= { cfprComputeRackUnitMbTempStatsHistEntry 23 }

cfprComputeRackUnitMbTempStatsHistRearTempMax OBJECT-TYPE
    SYNTAX       INTEGER
    MAX-ACCESS   read-only
    STATUS       current
    DESCRIPTION
        "Cisco Firepower compute:RackUnitMbTempStatsHist:rearTempMax
        managed object property"
    ::= { cfprComputeRackUnitMbTempStatsHistEntry 24 }

cfprComputeRackUnitMbTempStatsHistRearTempMin OBJECT-TYPE
    SYNTAX       INTEGER
    MAX-ACCESS   read-only
    STATUS       current
    DESCRIPTION
        "Cisco Firepower compute:RackUnitMbTempStatsHist:rearTempMin
        managed object property"
    ::= { cfprComputeRackUnitMbTempStatsHistEntry 25 }

cfprComputeRackUnitMbTempStatsHistSuspect OBJECT-TYPE
    SYNTAX       TruthValue
    MAX-ACCESS   read-only
    STATUS       current
    DESCRIPTION
        "Cisco Firepower compute:RackUnitMbTempStatsHist:suspect
        managed object property"
    ::= { cfprComputeRackUnitMbTempStatsHistEntry 26 }

cfprComputeRackUnitMbTempStatsHistThresholded OBJECT-TYPE
    SYNTAX       CfprComputeRackUnitMbTempStatsHistThresholded
    MAX-ACCESS   read-only
    STATUS       current
    DESCRIPTION
        "Cisco Firepower compute:RackUnitMbTempStatsHist:thresholded
        managed object property"
    ::= { cfprComputeRackUnitMbTempStatsHistEntry 27 }

cfprComputeRackUnitMbTempStatsHistTimeCollected OBJECT-TYPE
    SYNTAX       DateAndTime
    MAX-ACCESS   read-only
    STATUS       current
    DESCRIPTION
        "Cisco Firepower compute:RackUnitMbTempStatsHist:timeCollected
        managed object property"
    ::= { cfprComputeRackUnitMbTempStatsHistEntry 28 }

cfprComputeRtcBatteryTable OBJECT-TYPE
    SYNTAX           SEQUENCE OF CfprComputeRtcBatteryEntry
    MAX-ACCESS       not-accessible
    STATUS           current
    DESCRIPTION
        "Cisco Firepower compute:RtcBattery managed object table"
    ::= { cfprComputeObjects 58 }

cfprComputeRtcBatteryEntry OBJECT-TYPE
    SYNTAX           CfprComputeRtcBatteryEntry
    MAX-ACCESS       not-accessible
    STATUS           current
    DESCRIPTION
        "Entry for the cfprComputeRtcBatteryTable table."
    INDEX { cfprComputeRtcBatteryInstanceId }
    ::= { cfprComputeRtcBatteryTable 1 }

CfprComputeRtcBatteryEntry ::= SEQUENCE {
    cfprComputeRtcBatteryInstanceId                                  CfprManagedObjectId,
    cfprComputeRtcBatteryDn                                          CfprManagedObjectDn,
    cfprComputeRtcBatteryRn                                          SnmpAdminString,
    cfprComputeRtcBatteryId                                          Gauge32,
    cfprComputeRtcBatteryLocationDn                                  SnmpAdminString,
    cfprComputeRtcBatteryModel                                       SnmpAdminString,
    cfprComputeRtcBatteryOperQualifierReason                         SnmpAdminString,
    cfprComputeRtcBatteryOperState                                   CfprEquipmentOperability,
    cfprComputeRtcBatteryOperability                                 CfprEquipmentOperability,
    cfprComputeRtcBatteryPerf                                        CfprEquipmentSensorThresholdStatus,
    cfprComputeRtcBatteryPower                                       CfprEquipmentPowerState,
    cfprComputeRtcBatteryPresence                                    CfprEquipmentPresence,
    cfprComputeRtcBatteryRevision                                    SnmpAdminString,
    cfprComputeRtcBatterySerial                                      SnmpAdminString,
    cfprComputeRtcBatteryThermal                                     CfprEquipmentSensorThresholdStatus,
    cfprComputeRtcBatteryVendor                                      SnmpAdminString,
    cfprComputeRtcBatteryVoltage                                     CfprEquipmentSensorThresholdStatus
}

cfprComputeRtcBatteryInstanceId OBJECT-TYPE
    SYNTAX       CfprManagedObjectId
    MAX-ACCESS   not-accessible
    STATUS       current
    DESCRIPTION
        "Instance identifier of the managed object."
    ::= { cfprComputeRtcBatteryEntry 1 }

cfprComputeRtcBatteryDn OBJECT-TYPE
    SYNTAX       CfprManagedObjectDn
    MAX-ACCESS   read-only
    STATUS       current
    DESCRIPTION
        "Cisco Firepower compute:RtcBattery:dn managed object property"
    ::= { cfprComputeRtcBatteryEntry 2 }

cfprComputeRtcBatteryRn OBJECT-TYPE
    SYNTAX       SnmpAdminString
    MAX-ACCESS   read-only
    STATUS       current
    DESCRIPTION
        "Cisco Firepower compute:RtcBattery:rn managed object property"
    ::= { cfprComputeRtcBatteryEntry 3 }

cfprComputeRtcBatteryId OBJECT-TYPE
    SYNTAX       Gauge32
    MAX-ACCESS   read-only
    STATUS       current
    DESCRIPTION
        "Cisco Firepower compute:RtcBattery:id managed object property"
    ::= { cfprComputeRtcBatteryEntry 4 }

cfprComputeRtcBatteryLocationDn OBJECT-TYPE
    SYNTAX       SnmpAdminString
    MAX-ACCESS   read-only
    STATUS       current
    DESCRIPTION
        "Cisco Firepower compute:RtcBattery:locationDn
        managed object property"
    ::= { cfprComputeRtcBatteryEntry 5 }

cfprComputeRtcBatteryModel OBJECT-TYPE
    SYNTAX       SnmpAdminString
    MAX-ACCESS   read-only
    STATUS       current
    DESCRIPTION
        "Cisco Firepower compute:RtcBattery:model managed object property"
    ::= { cfprComputeRtcBatteryEntry 6 }

cfprComputeRtcBatteryOperQualifierReason OBJECT-TYPE
    SYNTAX       SnmpAdminString
    MAX-ACCESS   read-only
    STATUS       current
    DESCRIPTION
        "Cisco Firepower compute:RtcBattery:operQualifierReason
        managed object property"
    ::= { cfprComputeRtcBatteryEntry 7 }

cfprComputeRtcBatteryOperState OBJECT-TYPE
    SYNTAX       CfprEquipmentOperability
    MAX-ACCESS   read-only
    STATUS       current
    DESCRIPTION
        "Cisco Firepower compute:RtcBattery:operState managed
        object property"
    ::= { cfprComputeRtcBatteryEntry 8 }

cfprComputeRtcBatteryOperability OBJECT-TYPE
    SYNTAX       CfprEquipmentOperability
    MAX-ACCESS   read-only
    STATUS       current
    DESCRIPTION
        "Cisco Firepower compute:RtcBattery:operability
        managed object property"
    ::= { cfprComputeRtcBatteryEntry 9 }

cfprComputeRtcBatteryPerf OBJECT-TYPE
    SYNTAX       CfprEquipmentSensorThresholdStatus
    MAX-ACCESS   read-only
    STATUS       current
    DESCRIPTION
        "Cisco Firepower compute:RtcBattery:perf managed object property"
    ::= { cfprComputeRtcBatteryEntry 10 }

cfprComputeRtcBatteryPower OBJECT-TYPE
    SYNTAX       CfprEquipmentPowerState
    MAX-ACCESS   read-only
    STATUS       current
    DESCRIPTION
        "Cisco Firepower compute:RtcBattery:power managed object property"
    ::= { cfprComputeRtcBatteryEntry 11 }

cfprComputeRtcBatteryPresence OBJECT-TYPE
    SYNTAX       CfprEquipmentPresence
    MAX-ACCESS   read-only
    STATUS       current
    DESCRIPTION
        "Cisco Firepower compute:RtcBattery:presence managed
        object property"
    ::= { cfprComputeRtcBatteryEntry 12 }

cfprComputeRtcBatteryRevision OBJECT-TYPE
    SYNTAX       SnmpAdminString
    MAX-ACCESS   read-only
    STATUS       current
    DESCRIPTION
        "Cisco Firepower compute:RtcBattery:revision managed
        object property"
    ::= { cfprComputeRtcBatteryEntry 13 }

cfprComputeRtcBatterySerial OBJECT-TYPE
    SYNTAX       SnmpAdminString
    MAX-ACCESS   read-only
    STATUS       current
    DESCRIPTION
        "Cisco Firepower compute:RtcBattery:serial managed
        object property"
    ::= { cfprComputeRtcBatteryEntry 14 }

cfprComputeRtcBatteryThermal OBJECT-TYPE
    SYNTAX       CfprEquipmentSensorThresholdStatus
    MAX-ACCESS   read-only
    STATUS       current
    DESCRIPTION
        "Cisco Firepower compute:RtcBattery:thermal managed
        object property"
    ::= { cfprComputeRtcBatteryEntry 15 }

cfprComputeRtcBatteryVendor OBJECT-TYPE
    SYNTAX       SnmpAdminString
    MAX-ACCESS   read-only
    STATUS       current
    DESCRIPTION
        "Cisco Firepower compute:RtcBattery:vendor managed
        object property"
    ::= { cfprComputeRtcBatteryEntry 16 }

cfprComputeRtcBatteryVoltage OBJECT-TYPE
    SYNTAX       CfprEquipmentSensorThresholdStatus
    MAX-ACCESS   read-only
    STATUS       current
    DESCRIPTION
        "Cisco Firepower compute:RtcBattery:voltage managed
        object property"
    ::= { cfprComputeRtcBatteryEntry 17 }

cfprComputeScrubPolicyTable OBJECT-TYPE
    SYNTAX           SEQUENCE OF CfprComputeScrubPolicyEntry
    MAX-ACCESS       not-accessible
    STATUS           current
    DESCRIPTION
        "Cisco Firepower compute:ScrubPolicy managed object table"
    ::= { cfprComputeObjects 59 }

cfprComputeScrubPolicyEntry OBJECT-TYPE
    SYNTAX           CfprComputeScrubPolicyEntry
    MAX-ACCESS       not-accessible
    STATUS           current
    DESCRIPTION
        "Entry for the cfprComputeScrubPolicyTable table."
    INDEX { cfprComputeScrubPolicyInstanceId }
    ::= { cfprComputeScrubPolicyTable 1 }

CfprComputeScrubPolicyEntry ::= SEQUENCE {
    cfprComputeScrubPolicyInstanceId                                 CfprManagedObjectId,
    cfprComputeScrubPolicyDn                                         CfprManagedObjectDn,
    cfprComputeScrubPolicyRn                                         SnmpAdminString,
    cfprComputeScrubPolicyBiosSettingsScrub                          CfprComputeScrubAction,
    cfprComputeScrubPolicyDescr                                      SnmpAdminString,
    cfprComputeScrubPolicyDiskScrub                                  CfprComputeScrubAction,
    cfprComputeScrubPolicyFlexFlashScrub                             CfprComputeScrubAction,
    cfprComputeScrubPolicyIntId                                      SnmpAdminString,
    cfprComputeScrubPolicyName                                       SnmpAdminString,
    cfprComputeScrubPolicyPolicyLevel                                Gauge32,
    cfprComputeScrubPolicyPolicyOwner                                CfprPolicyPolicyOwner
}

cfprComputeScrubPolicyInstanceId OBJECT-TYPE
    SYNTAX       CfprManagedObjectId
    MAX-ACCESS   not-accessible
    STATUS       current
    DESCRIPTION
        "Instance identifier of the managed object."
    ::= { cfprComputeScrubPolicyEntry 1 }

cfprComputeScrubPolicyDn OBJECT-TYPE
    SYNTAX       CfprManagedObjectDn
    MAX-ACCESS   read-only
    STATUS       current
    DESCRIPTION
        "Cisco Firepower compute:ScrubPolicy:dn managed object property"
    ::= { cfprComputeScrubPolicyEntry 2 }

cfprComputeScrubPolicyRn OBJECT-TYPE
    SYNTAX       SnmpAdminString
    MAX-ACCESS   read-only
    STATUS       current
    DESCRIPTION
        "Cisco Firepower compute:ScrubPolicy:rn managed object property"
    ::= { cfprComputeScrubPolicyEntry 3 }

cfprComputeScrubPolicyBiosSettingsScrub OBJECT-TYPE
    SYNTAX       CfprComputeScrubAction
    MAX-ACCESS   read-only
    STATUS       current
    DESCRIPTION
        "Cisco Firepower compute:ScrubPolicy:biosSettingsScrub
        managed object property"
    ::= { cfprComputeScrubPolicyEntry 4 }

cfprComputeScrubPolicyDescr OBJECT-TYPE
    SYNTAX       SnmpAdminString
    MAX-ACCESS   read-only
    STATUS       current
    DESCRIPTION
        "Cisco Firepower compute:ScrubPolicy:descr managed
        object property"
    ::= { cfprComputeScrubPolicyEntry 5 }

cfprComputeScrubPolicyDiskScrub OBJECT-TYPE
    SYNTAX       CfprComputeScrubAction
    MAX-ACCESS   read-only
    STATUS       current
    DESCRIPTION
        "Cisco Firepower compute:ScrubPolicy:diskScrub
        managed object property"
    ::= { cfprComputeScrubPolicyEntry 6 }

cfprComputeScrubPolicyFlexFlashScrub OBJECT-TYPE
    SYNTAX       CfprComputeScrubAction
    MAX-ACCESS   read-only
    STATUS       current
    DESCRIPTION
        "Cisco Firepower compute:ScrubPolicy:flexFlashScrub
        managed object property"
    ::= { cfprComputeScrubPolicyEntry 7 }

cfprComputeScrubPolicyIntId OBJECT-TYPE
    SYNTAX       SnmpAdminString
    MAX-ACCESS   read-only
    STATUS       current
    DESCRIPTION
        "Cisco Firepower compute:ScrubPolicy:intId managed
        object property"
    ::= { cfprComputeScrubPolicyEntry 8 }

cfprComputeScrubPolicyName OBJECT-TYPE
    SYNTAX       SnmpAdminString
    MAX-ACCESS   read-only
    STATUS       current
    DESCRIPTION
        "Cisco Firepower compute:ScrubPolicy:name managed object property"
    ::= { cfprComputeScrubPolicyEntry 9 }

cfprComputeScrubPolicyPolicyLevel OBJECT-TYPE
    SYNTAX       Gauge32
    MAX-ACCESS   read-only
    STATUS       current
    DESCRIPTION
        "Cisco Firepower compute:ScrubPolicy:policyLevel
        managed object property"
    ::= { cfprComputeScrubPolicyEntry 10 }

cfprComputeScrubPolicyPolicyOwner OBJECT-TYPE
    SYNTAX       CfprPolicyPolicyOwner
    MAX-ACCESS   read-only
    STATUS       current
    DESCRIPTION
        "Cisco Firepower compute:ScrubPolicy:policyOwner
        managed object property"
    ::= { cfprComputeScrubPolicyEntry 11 }

cfprComputeServerDiscPolicyTable OBJECT-TYPE
    SYNTAX           SEQUENCE OF CfprComputeServerDiscPolicyEntry
    MAX-ACCESS       not-accessible
    STATUS           current
    DESCRIPTION
        "Cisco Firepower compute:ServerDiscPolicy managed object table"
    ::= { cfprComputeObjects 60 }

cfprComputeServerDiscPolicyEntry OBJECT-TYPE
    SYNTAX           CfprComputeServerDiscPolicyEntry
    MAX-ACCESS       not-accessible
    STATUS           current
    DESCRIPTION
        "Entry for the cfprComputeServerDiscPolicyTable table."
    INDEX { cfprComputeServerDiscPolicyInstanceId }
    ::= { cfprComputeServerDiscPolicyTable 1 }

CfprComputeServerDiscPolicyEntry ::= SEQUENCE {
    cfprComputeServerDiscPolicyInstanceId                            CfprManagedObjectId,
    cfprComputeServerDiscPolicyDn                                    CfprManagedObjectDn,
    cfprComputeServerDiscPolicyRn                                    SnmpAdminString,
    cfprComputeServerDiscPolicyAction                                SnmpAdminString,
    cfprComputeServerDiscPolicyDescr                                 SnmpAdminString,
    cfprComputeServerDiscPolicyFsmDescr                              SnmpAdminString,
    cfprComputeServerDiscPolicyFsmPrev                               SnmpAdminString,
    cfprComputeServerDiscPolicyFsmProgr                              Gauge32,
    cfprComputeServerDiscPolicyFsmRmtInvErrCode                      Gauge32,
    cfprComputeServerDiscPolicyFsmRmtInvErrDescr                     SnmpAdminString,
    cfprComputeServerDiscPolicyFsmRmtInvRslt                         CfprConditionRemoteInvRslt,
    cfprComputeServerDiscPolicyFsmStageDescr                         SnmpAdminString,
    cfprComputeServerDiscPolicyFsmStamp                              DateAndTime,
    cfprComputeServerDiscPolicyFsmStatus                             SnmpAdminString,
    cfprComputeServerDiscPolicyFsmTry                                Gauge32,
    cfprComputeServerDiscPolicyIntId                                 SnmpAdminString,
    cfprComputeServerDiscPolicyName                                  SnmpAdminString,
    cfprComputeServerDiscPolicyPolicyLevel                           Gauge32,
    cfprComputeServerDiscPolicyPolicyOwner                           CfprPolicyPolicyOwner,
    cfprComputeServerDiscPolicyQualifier                             SnmpAdminString,
    cfprComputeServerDiscPolicyScrubPolicyName                       SnmpAdminString
}

cfprComputeServerDiscPolicyInstanceId OBJECT-TYPE
    SYNTAX       CfprManagedObjectId
    MAX-ACCESS   not-accessible
    STATUS       current
    DESCRIPTION
        "Instance identifier of the managed object."
    ::= { cfprComputeServerDiscPolicyEntry 1 }

cfprComputeServerDiscPolicyDn OBJECT-TYPE
    SYNTAX       CfprManagedObjectDn
    MAX-ACCESS   read-only
    STATUS       current
    DESCRIPTION
        "Cisco Firepower compute:ServerDiscPolicy:dn managed
        object property"
    ::= { cfprComputeServerDiscPolicyEntry 2 }

cfprComputeServerDiscPolicyRn OBJECT-TYPE
    SYNTAX       SnmpAdminString
    MAX-ACCESS   read-only
    STATUS       current
    DESCRIPTION
        "Cisco Firepower compute:ServerDiscPolicy:rn managed
        object property"
    ::= { cfprComputeServerDiscPolicyEntry 3 }

cfprComputeServerDiscPolicyAction OBJECT-TYPE
    SYNTAX       SnmpAdminString
    MAX-ACCESS   read-only
    STATUS       current
    DESCRIPTION
        "Cisco Firepower compute:ServerDiscPolicy:action
        managed object property"
    ::= { cfprComputeServerDiscPolicyEntry 4 }

cfprComputeServerDiscPolicyDescr OBJECT-TYPE
    SYNTAX       SnmpAdminString
    MAX-ACCESS   read-only
    STATUS       current
    DESCRIPTION
        "Cisco Firepower compute:ServerDiscPolicy:descr
        managed object property"
    ::= { cfprComputeServerDiscPolicyEntry 5 }

cfprComputeServerDiscPolicyFsmDescr OBJECT-TYPE
    SYNTAX       SnmpAdminString
    MAX-ACCESS   read-only
    STATUS       current
    DESCRIPTION
        "Cisco Firepower compute:ServerDiscPolicy:fsmDescr
        managed object property"
    ::= { cfprComputeServerDiscPolicyEntry 6 }

cfprComputeServerDiscPolicyFsmPrev OBJECT-TYPE
    SYNTAX       SnmpAdminString
    MAX-ACCESS   read-only
    STATUS       current
    DESCRIPTION
        "Cisco Firepower compute:ServerDiscPolicy:fsmPrev
        managed object property"
    ::= { cfprComputeServerDiscPolicyEntry 7 }

cfprComputeServerDiscPolicyFsmProgr OBJECT-TYPE
    SYNTAX       Gauge32
    MAX-ACCESS   read-only
    STATUS       current
    DESCRIPTION
        "Cisco Firepower compute:ServerDiscPolicy:fsmProgr
        managed object property"
    ::= { cfprComputeServerDiscPolicyEntry 8 }

cfprComputeServerDiscPolicyFsmRmtInvErrCode OBJECT-TYPE
    SYNTAX       Gauge32
    MAX-ACCESS   read-only
    STATUS       current
    DESCRIPTION
        "Cisco Firepower compute:ServerDiscPolicy:fsmRmtInvErrCode
        managed object property"
    ::= { cfprComputeServerDiscPolicyEntry 9 }

cfprComputeServerDiscPolicyFsmRmtInvErrDescr OBJECT-TYPE
    SYNTAX       SnmpAdminString
    MAX-ACCESS   read-only
    STATUS       current
    DESCRIPTION
        "Cisco Firepower compute:ServerDiscPolicy:fsmRmtInvErrDescr
        managed object property"
    ::= { cfprComputeServerDiscPolicyEntry 10 }

cfprComputeServerDiscPolicyFsmRmtInvRslt OBJECT-TYPE
    SYNTAX       CfprConditionRemoteInvRslt
    MAX-ACCESS   read-only
    STATUS       current
    DESCRIPTION
        "Cisco Firepower compute:ServerDiscPolicy:fsmRmtInvRslt
        managed object property"
    ::= { cfprComputeServerDiscPolicyEntry 11 }

cfprComputeServerDiscPolicyFsmStageDescr OBJECT-TYPE
    SYNTAX       SnmpAdminString
    MAX-ACCESS   read-only
    STATUS       current
    DESCRIPTION
        "Cisco Firepower compute:ServerDiscPolicy:fsmStageDescr
        managed object property"
    ::= { cfprComputeServerDiscPolicyEntry 12 }

cfprComputeServerDiscPolicyFsmStamp OBJECT-TYPE
    SYNTAX       DateAndTime
    MAX-ACCESS   read-only
    STATUS       current
    DESCRIPTION
        "Cisco Firepower compute:ServerDiscPolicy:fsmStamp
        managed object property"
    ::= { cfprComputeServerDiscPolicyEntry 13 }

cfprComputeServerDiscPolicyFsmStatus OBJECT-TYPE
    SYNTAX       SnmpAdminString
    MAX-ACCESS   read-only
    STATUS       current
    DESCRIPTION
        "Cisco Firepower compute:ServerDiscPolicy:fsmStatus
        managed object property"
    ::= { cfprComputeServerDiscPolicyEntry 14 }

cfprComputeServerDiscPolicyFsmTry OBJECT-TYPE
    SYNTAX       Gauge32
    MAX-ACCESS   read-only
    STATUS       current
    DESCRIPTION
        "Cisco Firepower compute:ServerDiscPolicy:fsmTry
        managed object property"
    ::= { cfprComputeServerDiscPolicyEntry 15 }

cfprComputeServerDiscPolicyIntId OBJECT-TYPE
    SYNTAX       SnmpAdminString
    MAX-ACCESS   read-only
    STATUS       current
    DESCRIPTION
        "Cisco Firepower compute:ServerDiscPolicy:intId
        managed object property"
    ::= { cfprComputeServerDiscPolicyEntry 16 }

cfprComputeServerDiscPolicyName OBJECT-TYPE
    SYNTAX       SnmpAdminString
    MAX-ACCESS   read-only
    STATUS       current
    DESCRIPTION
        "Cisco Firepower compute:ServerDiscPolicy:name
        managed object property"
    ::= { cfprComputeServerDiscPolicyEntry 17 }

cfprComputeServerDiscPolicyPolicyLevel OBJECT-TYPE
    SYNTAX       Gauge32
    MAX-ACCESS   read-only
    STATUS       current
    DESCRIPTION
        "Cisco Firepower compute:ServerDiscPolicy:policyLevel
        managed object property"
    ::= { cfprComputeServerDiscPolicyEntry 18 }

cfprComputeServerDiscPolicyPolicyOwner OBJECT-TYPE
    SYNTAX       CfprPolicyPolicyOwner
    MAX-ACCESS   read-only
    STATUS       current
    DESCRIPTION
        "Cisco Firepower compute:ServerDiscPolicy:policyOwner
        managed object property"
    ::= { cfprComputeServerDiscPolicyEntry 19 }

cfprComputeServerDiscPolicyQualifier OBJECT-TYPE
    SYNTAX       SnmpAdminString
    MAX-ACCESS   read-only
    STATUS       current
    DESCRIPTION
        "Cisco Firepower compute:ServerDiscPolicy:qualifier
        managed object property"
    ::= { cfprComputeServerDiscPolicyEntry 20 }

cfprComputeServerDiscPolicyScrubPolicyName OBJECT-TYPE
    SYNTAX       SnmpAdminString
    MAX-ACCESS   read-only
    STATUS       current
    DESCRIPTION
        "Cisco Firepower compute:ServerDiscPolicy:scrubPolicyName
        managed object property"
    ::= { cfprComputeServerDiscPolicyEntry 21 }

cfprComputeServerDiscPolicyFsmTable OBJECT-TYPE
    SYNTAX           SEQUENCE OF CfprComputeServerDiscPolicyFsmEntry
    MAX-ACCESS       not-accessible
    STATUS           current
    DESCRIPTION
        "Cisco Firepower compute:ServerDiscPolicyFsm managed object table"
    ::= { cfprComputeObjects 61 }

cfprComputeServerDiscPolicyFsmEntry OBJECT-TYPE
    SYNTAX           CfprComputeServerDiscPolicyFsmEntry
    MAX-ACCESS       not-accessible
    STATUS           current
    DESCRIPTION
        "Entry for the cfprComputeServerDiscPolicyFsmTable table."
    INDEX { cfprComputeServerDiscPolicyFsmInstanceId }
    ::= { cfprComputeServerDiscPolicyFsmTable 1 }

CfprComputeServerDiscPolicyFsmEntry ::= SEQUENCE {
    cfprComputeServerDiscPolicyFsmInstanceId                         CfprManagedObjectId,
    cfprComputeServerDiscPolicyFsmDn                                 CfprManagedObjectDn,
    cfprComputeServerDiscPolicyFsmRn                                 SnmpAdminString,
    cfprComputeServerDiscPolicyFsmCompletionTime                     DateAndTime,
    cfprComputeServerDiscPolicyFsmCurrentFsm                         CfprComputeServerDiscPolicyFsmCurrentFsm,
    cfprComputeServerDiscPolicyFsmDescrData                          SnmpAdminString,
    cfprComputeServerDiscPolicyFsmFsmStatus                          CfprFsmFsmStageStatus,
    cfprComputeServerDiscPolicyFsmProgress                           Gauge32,
    cfprComputeServerDiscPolicyFsmRmtErrCode                         Gauge32,
    cfprComputeServerDiscPolicyFsmRmtErrDescr                        SnmpAdminString,
    cfprComputeServerDiscPolicyFsmRmtRslt                            CfprConditionRemoteInvRslt
}

cfprComputeServerDiscPolicyFsmInstanceId OBJECT-TYPE
    SYNTAX       CfprManagedObjectId
    MAX-ACCESS   not-accessible
    STATUS       current
    DESCRIPTION
        "Instance identifier of the managed object."
    ::= { cfprComputeServerDiscPolicyFsmEntry 1 }

cfprComputeServerDiscPolicyFsmDn OBJECT-TYPE
    SYNTAX       CfprManagedObjectDn
    MAX-ACCESS   read-only
    STATUS       current
    DESCRIPTION
        "Cisco Firepower compute:ServerDiscPolicyFsm:dn
        managed object property"
    ::= { cfprComputeServerDiscPolicyFsmEntry 2 }

cfprComputeServerDiscPolicyFsmRn OBJECT-TYPE
    SYNTAX       SnmpAdminString
    MAX-ACCESS   read-only
    STATUS       current
    DESCRIPTION
        "Cisco Firepower compute:ServerDiscPolicyFsm:rn
        managed object property"
    ::= { cfprComputeServerDiscPolicyFsmEntry 3 }

cfprComputeServerDiscPolicyFsmCompletionTime OBJECT-TYPE
    SYNTAX       DateAndTime
    MAX-ACCESS   read-only
    STATUS       current
    DESCRIPTION
        "Cisco Firepower compute:ServerDiscPolicyFsm:completionTime
        managed object property"
    ::= { cfprComputeServerDiscPolicyFsmEntry 4 }

cfprComputeServerDiscPolicyFsmCurrentFsm OBJECT-TYPE
    SYNTAX       CfprComputeServerDiscPolicyFsmCurrentFsm
    MAX-ACCESS   read-only
    STATUS       current
    DESCRIPTION
        "Cisco Firepower compute:ServerDiscPolicyFsm:currentFsm
        managed object property"
    ::= { cfprComputeServerDiscPolicyFsmEntry 5 }

cfprComputeServerDiscPolicyFsmDescrData OBJECT-TYPE
    SYNTAX       SnmpAdminString
    MAX-ACCESS   read-only
    STATUS       current
    DESCRIPTION
        "Cisco Firepower compute:ServerDiscPolicyFsm:descr
        managed object property"
    ::= { cfprComputeServerDiscPolicyFsmEntry 6 }

cfprComputeServerDiscPolicyFsmFsmStatus OBJECT-TYPE
    SYNTAX       CfprFsmFsmStageStatus
    MAX-ACCESS   read-only
    STATUS       current
    DESCRIPTION
        "Cisco Firepower compute:ServerDiscPolicyFsm:fsmStatus
        managed object property"
    ::= { cfprComputeServerDiscPolicyFsmEntry 7 }

cfprComputeServerDiscPolicyFsmProgress OBJECT-TYPE
    SYNTAX       Gauge32
    MAX-ACCESS   read-only
    STATUS       current
    DESCRIPTION
        "Cisco Firepower compute:ServerDiscPolicyFsm:progress
        managed object property"
    ::= { cfprComputeServerDiscPolicyFsmEntry 8 }

cfprComputeServerDiscPolicyFsmRmtErrCode OBJECT-TYPE
    SYNTAX       Gauge32
    MAX-ACCESS   read-only
    STATUS       current
    DESCRIPTION
        "Cisco Firepower compute:ServerDiscPolicyFsm:rmtErrCode
        managed object property"
    ::= { cfprComputeServerDiscPolicyFsmEntry 9 }

cfprComputeServerDiscPolicyFsmRmtErrDescr OBJECT-TYPE
    SYNTAX       SnmpAdminString
    MAX-ACCESS   read-only
    STATUS       current
    DESCRIPTION
        "Cisco Firepower compute:ServerDiscPolicyFsm:rmtErrDescr
        managed object property"
    ::= { cfprComputeServerDiscPolicyFsmEntry 10 }

cfprComputeServerDiscPolicyFsmRmtRslt OBJECT-TYPE
    SYNTAX       CfprConditionRemoteInvRslt
    MAX-ACCESS   read-only
    STATUS       current
    DESCRIPTION
        "Cisco Firepower compute:ServerDiscPolicyFsm:rmtRslt
        managed object property"
    ::= { cfprComputeServerDiscPolicyFsmEntry 11 }

cfprComputeServerDiscPolicyFsmStageTable OBJECT-TYPE
    SYNTAX           SEQUENCE OF CfprComputeServerDiscPolicyFsmStageEntry
    MAX-ACCESS       not-accessible
    STATUS           current
    DESCRIPTION
        "Cisco Firepower compute:ServerDiscPolicyFsmStage
        managed object table"
    ::= { cfprComputeObjects 62 }

cfprComputeServerDiscPolicyFsmStageEntry OBJECT-TYPE
    SYNTAX           CfprComputeServerDiscPolicyFsmStageEntry
    MAX-ACCESS       not-accessible
    STATUS           current
    DESCRIPTION
        "Entry for the cfprComputeServerDiscPolicyFsmStageTable table."
    INDEX { cfprComputeServerDiscPolicyFsmStageInstanceId }
    ::= { cfprComputeServerDiscPolicyFsmStageTable 1 }

CfprComputeServerDiscPolicyFsmStageEntry ::= SEQUENCE {
    cfprComputeServerDiscPolicyFsmStageInstanceId                    CfprManagedObjectId,
    cfprComputeServerDiscPolicyFsmStageDn                            CfprManagedObjectDn,
    cfprComputeServerDiscPolicyFsmStageRn                            SnmpAdminString,
    cfprComputeServerDiscPolicyFsmStageDescrData                     SnmpAdminString,
    cfprComputeServerDiscPolicyFsmStageLastUpdateTime                DateAndTime,
    cfprComputeServerDiscPolicyFsmStageName                          CfprComputeServerDiscPolicyFsmStageName,
    cfprComputeServerDiscPolicyFsmStageOrder                         Gauge32,
    cfprComputeServerDiscPolicyFsmStageRetry                         Gauge32,
    cfprComputeServerDiscPolicyFsmStageStageStatus                   CfprFsmFsmStageStatus
}

cfprComputeServerDiscPolicyFsmStageInstanceId OBJECT-TYPE
    SYNTAX       CfprManagedObjectId
    MAX-ACCESS   not-accessible
    STATUS       current
    DESCRIPTION
        "Instance identifier of the managed object."
    ::= { cfprComputeServerDiscPolicyFsmStageEntry 1 }

cfprComputeServerDiscPolicyFsmStageDn OBJECT-TYPE
    SYNTAX       CfprManagedObjectDn
    MAX-ACCESS   read-only
    STATUS       current
    DESCRIPTION
        "Cisco Firepower compute:ServerDiscPolicyFsmStage:dn
        managed object property"
    ::= { cfprComputeServerDiscPolicyFsmStageEntry 2 }

cfprComputeServerDiscPolicyFsmStageRn OBJECT-TYPE
    SYNTAX       SnmpAdminString
    MAX-ACCESS   read-only
    STATUS       current
    DESCRIPTION
        "Cisco Firepower compute:ServerDiscPolicyFsmStage:rn
        managed object property"
    ::= { cfprComputeServerDiscPolicyFsmStageEntry 3 }

cfprComputeServerDiscPolicyFsmStageDescrData OBJECT-TYPE
    SYNTAX       SnmpAdminString
    MAX-ACCESS   read-only
    STATUS       current
    DESCRIPTION
        "Cisco Firepower compute:ServerDiscPolicyFsmStage:descr
        managed object property"
    ::= { cfprComputeServerDiscPolicyFsmStageEntry 4 }

cfprComputeServerDiscPolicyFsmStageLastUpdateTime OBJECT-TYPE
    SYNTAX       DateAndTime
    MAX-ACCESS   read-only
    STATUS       current
    DESCRIPTION
        "Cisco Firepower compute:ServerDiscPolicyFsmStage:lastUpdateTime
        managed object property"
    ::= { cfprComputeServerDiscPolicyFsmStageEntry 5 }

cfprComputeServerDiscPolicyFsmStageName OBJECT-TYPE
    SYNTAX       CfprComputeServerDiscPolicyFsmStageName
    MAX-ACCESS   read-only
    STATUS       current
    DESCRIPTION
        "Cisco Firepower compute:ServerDiscPolicyFsmStage:name
        managed object property"
    ::= { cfprComputeServerDiscPolicyFsmStageEntry 6 }

cfprComputeServerDiscPolicyFsmStageOrder OBJECT-TYPE
    SYNTAX       Gauge32
    MAX-ACCESS   read-only
    STATUS       current
    DESCRIPTION
        "Cisco Firepower compute:ServerDiscPolicyFsmStage:order
        managed object property"
    ::= { cfprComputeServerDiscPolicyFsmStageEntry 7 }

cfprComputeServerDiscPolicyFsmStageRetry OBJECT-TYPE
    SYNTAX       Gauge32
    MAX-ACCESS   read-only
    STATUS       current
    DESCRIPTION
        "Cisco Firepower compute:ServerDiscPolicyFsmStage:retry
        managed object property"
    ::= { cfprComputeServerDiscPolicyFsmStageEntry 8 }

cfprComputeServerDiscPolicyFsmStageStageStatus OBJECT-TYPE
    SYNTAX       CfprFsmFsmStageStatus
    MAX-ACCESS   read-only
    STATUS       current
    DESCRIPTION
        "Cisco Firepower compute:ServerDiscPolicyFsmStage:stageStatus
        managed object property"
    ::= { cfprComputeServerDiscPolicyFsmStageEntry 9 }

cfprComputeServerDiscPolicyFsmTaskTable OBJECT-TYPE
    SYNTAX           SEQUENCE OF CfprComputeServerDiscPolicyFsmTaskEntry
    MAX-ACCESS       not-accessible
    STATUS           current
    DESCRIPTION
        "Cisco Firepower compute:ServerDiscPolicyFsmTask
        managed object table"
    ::= { cfprComputeObjects 63 }

cfprComputeServerDiscPolicyFsmTaskEntry OBJECT-TYPE
    SYNTAX           CfprComputeServerDiscPolicyFsmTaskEntry
    MAX-ACCESS       not-accessible
    STATUS           current
    DESCRIPTION
        "Entry for the cfprComputeServerDiscPolicyFsmTaskTable table."
    INDEX { cfprComputeServerDiscPolicyFsmTaskInstanceId }
    ::= { cfprComputeServerDiscPolicyFsmTaskTable 1 }

CfprComputeServerDiscPolicyFsmTaskEntry ::= SEQUENCE {
    cfprComputeServerDiscPolicyFsmTaskInstanceId                     CfprManagedObjectId,
    cfprComputeServerDiscPolicyFsmTaskDn                             CfprManagedObjectDn,
    cfprComputeServerDiscPolicyFsmTaskRn                             SnmpAdminString,
    cfprComputeServerDiscPolicyFsmTaskCompletion                     CfprFsmCompletion,
    cfprComputeServerDiscPolicyFsmTaskFlags                          CfprFsmFlags,
    cfprComputeServerDiscPolicyFsmTaskItem                           CfprComputeServerDiscPolicyFsmTaskItem,
    cfprComputeServerDiscPolicyFsmTaskSeqId                          Gauge32
}

cfprComputeServerDiscPolicyFsmTaskInstanceId OBJECT-TYPE
    SYNTAX       CfprManagedObjectId
    MAX-ACCESS   not-accessible
    STATUS       current
    DESCRIPTION
        "Instance identifier of the managed object."
    ::= { cfprComputeServerDiscPolicyFsmTaskEntry 1 }

cfprComputeServerDiscPolicyFsmTaskDn OBJECT-TYPE
    SYNTAX       CfprManagedObjectDn
    MAX-ACCESS   read-only
    STATUS       current
    DESCRIPTION
        "Cisco Firepower compute:ServerDiscPolicyFsmTask:dn
        managed object property"
    ::= { cfprComputeServerDiscPolicyFsmTaskEntry 2 }

cfprComputeServerDiscPolicyFsmTaskRn OBJECT-TYPE
    SYNTAX       SnmpAdminString
    MAX-ACCESS   read-only
    STATUS       current
    DESCRIPTION
        "Cisco Firepower compute:ServerDiscPolicyFsmTask:rn
        managed object property"
    ::= { cfprComputeServerDiscPolicyFsmTaskEntry 3 }

cfprComputeServerDiscPolicyFsmTaskCompletion OBJECT-TYPE
    SYNTAX       CfprFsmCompletion
    MAX-ACCESS   read-only
    STATUS       current
    DESCRIPTION
        "Cisco Firepower compute:ServerDiscPolicyFsmTask:completion
        managed object property"
    ::= { cfprComputeServerDiscPolicyFsmTaskEntry 4 }

cfprComputeServerDiscPolicyFsmTaskFlags OBJECT-TYPE
    SYNTAX       CfprFsmFlags
    MAX-ACCESS   read-only
    STATUS       current
    DESCRIPTION
        "Cisco Firepower compute:ServerDiscPolicyFsmTask:flags
        managed object property"
    ::= { cfprComputeServerDiscPolicyFsmTaskEntry 5 }

cfprComputeServerDiscPolicyFsmTaskItem OBJECT-TYPE
    SYNTAX       CfprComputeServerDiscPolicyFsmTaskItem
    MAX-ACCESS   read-only
    STATUS       current
    DESCRIPTION
        "Cisco Firepower compute:ServerDiscPolicyFsmTask:item
        managed object property"
    ::= { cfprComputeServerDiscPolicyFsmTaskEntry 6 }

cfprComputeServerDiscPolicyFsmTaskSeqId OBJECT-TYPE
    SYNTAX       Gauge32
    MAX-ACCESS   read-only
    STATUS       current
    DESCRIPTION
        "Cisco Firepower compute:ServerDiscPolicyFsmTask:seqId
        managed object property"
    ::= { cfprComputeServerDiscPolicyFsmTaskEntry 7 }

cfprComputeServerMgmtPolicyTable OBJECT-TYPE
    SYNTAX           SEQUENCE OF CfprComputeServerMgmtPolicyEntry
    MAX-ACCESS       not-accessible
    STATUS           current
    DESCRIPTION
        "Cisco Firepower compute:ServerMgmtPolicy managed object table"
    ::= { cfprComputeObjects 64 }

cfprComputeServerMgmtPolicyEntry OBJECT-TYPE
    SYNTAX           CfprComputeServerMgmtPolicyEntry
    MAX-ACCESS       not-accessible
    STATUS           current
    DESCRIPTION
        "Entry for the cfprComputeServerMgmtPolicyTable table."
    INDEX { cfprComputeServerMgmtPolicyInstanceId }
    ::= { cfprComputeServerMgmtPolicyTable 1 }

CfprComputeServerMgmtPolicyEntry ::= SEQUENCE {
    cfprComputeServerMgmtPolicyInstanceId                            CfprManagedObjectId,
    cfprComputeServerMgmtPolicyDn                                    CfprManagedObjectDn,
    cfprComputeServerMgmtPolicyRn                                    SnmpAdminString,
    cfprComputeServerMgmtPolicyAction                                CfprComputeServerMgmtDiscAction,
    cfprComputeServerMgmtPolicyDescr                                 SnmpAdminString,
    cfprComputeServerMgmtPolicyIntId                                 SnmpAdminString,
    cfprComputeServerMgmtPolicyName                                  SnmpAdminString,
    cfprComputeServerMgmtPolicyPolicyLevel                           Gauge32,
    cfprComputeServerMgmtPolicyPolicyOwner                           CfprPolicyPolicyOwner,
    cfprComputeServerMgmtPolicyQualifier                             SnmpAdminString
}

cfprComputeServerMgmtPolicyInstanceId OBJECT-TYPE
    SYNTAX       CfprManagedObjectId
    MAX-ACCESS   not-accessible
    STATUS       current
    DESCRIPTION
        "Instance identifier of the managed object."
    ::= { cfprComputeServerMgmtPolicyEntry 1 }

cfprComputeServerMgmtPolicyDn OBJECT-TYPE
    SYNTAX       CfprManagedObjectDn
    MAX-ACCESS   read-only
    STATUS       current
    DESCRIPTION
        "Cisco Firepower compute:ServerMgmtPolicy:dn managed
        object property"
    ::= { cfprComputeServerMgmtPolicyEntry 2 }

cfprComputeServerMgmtPolicyRn OBJECT-TYPE
    SYNTAX       SnmpAdminString
    MAX-ACCESS   read-only
    STATUS       current
    DESCRIPTION
        "Cisco Firepower compute:ServerMgmtPolicy:rn managed
        object property"
    ::= { cfprComputeServerMgmtPolicyEntry 3 }

cfprComputeServerMgmtPolicyAction OBJECT-TYPE
    SYNTAX       CfprComputeServerMgmtDiscAction
    MAX-ACCESS   read-only
    STATUS       current
    DESCRIPTION
        "Cisco Firepower compute:ServerMgmtPolicy:action
        managed object property"
    ::= { cfprComputeServerMgmtPolicyEntry 4 }

cfprComputeServerMgmtPolicyDescr OBJECT-TYPE
    SYNTAX       SnmpAdminString
    MAX-ACCESS   read-only
    STATUS       current
    DESCRIPTION
        "Cisco Firepower compute:ServerMgmtPolicy:descr
        managed object property"
    ::= { cfprComputeServerMgmtPolicyEntry 5 }

cfprComputeServerMgmtPolicyIntId OBJECT-TYPE
    SYNTAX       SnmpAdminString
    MAX-ACCESS   read-only
    STATUS       current
    DESCRIPTION
        "Cisco Firepower compute:ServerMgmtPolicy:intId
        managed object property"
    ::= { cfprComputeServerMgmtPolicyEntry 6 }

cfprComputeServerMgmtPolicyName OBJECT-TYPE
    SYNTAX       SnmpAdminString
    MAX-ACCESS   read-only
    STATUS       current
    DESCRIPTION
        "Cisco Firepower compute:ServerMgmtPolicy:name
        managed object property"
    ::= { cfprComputeServerMgmtPolicyEntry 7 }

cfprComputeServerMgmtPolicyPolicyLevel OBJECT-TYPE
    SYNTAX       Gauge32
    MAX-ACCESS   read-only
    STATUS       current
    DESCRIPTION
        "Cisco Firepower compute:ServerMgmtPolicy:policyLevel
        managed object property"
    ::= { cfprComputeServerMgmtPolicyEntry 8 }

cfprComputeServerMgmtPolicyPolicyOwner OBJECT-TYPE
    SYNTAX       CfprPolicyPolicyOwner
    MAX-ACCESS   read-only
    STATUS       current
    DESCRIPTION
        "Cisco Firepower compute:ServerMgmtPolicy:policyOwner
        managed object property"
    ::= { cfprComputeServerMgmtPolicyEntry 9 }

cfprComputeServerMgmtPolicyQualifier OBJECT-TYPE
    SYNTAX       SnmpAdminString
    MAX-ACCESS   read-only
    STATUS       current
    DESCRIPTION
        "Cisco Firepower compute:ServerMgmtPolicy:qualifier
        managed object property"
    ::= { cfprComputeServerMgmtPolicyEntry 10 }

cfprComputeSlotQualTable OBJECT-TYPE
    SYNTAX           SEQUENCE OF CfprComputeSlotQualEntry
    MAX-ACCESS       not-accessible
    STATUS           current
    DESCRIPTION
        "Cisco Firepower compute:SlotQual managed object table"
    ::= { cfprComputeObjects 65 }

cfprComputeSlotQualEntry OBJECT-TYPE
    SYNTAX           CfprComputeSlotQualEntry
    MAX-ACCESS       not-accessible
    STATUS           current
    DESCRIPTION
        "Entry for the cfprComputeSlotQualTable table."
    INDEX { cfprComputeSlotQualInstanceId }
    ::= { cfprComputeSlotQualTable 1 }

CfprComputeSlotQualEntry ::= SEQUENCE {
    cfprComputeSlotQualInstanceId                                    CfprManagedObjectId,
    cfprComputeSlotQualDn                                            CfprManagedObjectDn,
    cfprComputeSlotQualRn                                            SnmpAdminString,
    cfprComputeSlotQualMaxId                                         CfprComputeSlotQualMaxId,
    cfprComputeSlotQualMinId                                         CfprComputeSlotQualMinId
}

cfprComputeSlotQualInstanceId OBJECT-TYPE
    SYNTAX       CfprManagedObjectId
    MAX-ACCESS   not-accessible
    STATUS       current
    DESCRIPTION
        "Instance identifier of the managed object."
    ::= { cfprComputeSlotQualEntry 1 }

cfprComputeSlotQualDn OBJECT-TYPE
    SYNTAX       CfprManagedObjectDn
    MAX-ACCESS   read-only
    STATUS       current
    DESCRIPTION
        "Cisco Firepower compute:SlotQual:dn managed object property"
    ::= { cfprComputeSlotQualEntry 2 }

cfprComputeSlotQualRn OBJECT-TYPE
    SYNTAX       SnmpAdminString
    MAX-ACCESS   read-only
    STATUS       current
    DESCRIPTION
        "Cisco Firepower compute:SlotQual:rn managed object property"
    ::= { cfprComputeSlotQualEntry 3 }

cfprComputeSlotQualMaxId OBJECT-TYPE
    SYNTAX       CfprComputeSlotQualMaxId
    MAX-ACCESS   read-only
    STATUS       current
    DESCRIPTION
        "Cisco Firepower compute:SlotQual:maxId managed object property"
    ::= { cfprComputeSlotQualEntry 4 }

cfprComputeSlotQualMinId OBJECT-TYPE
    SYNTAX       CfprComputeSlotQualMinId
    MAX-ACCESS   read-only
    STATUS       current
    DESCRIPTION
        "Cisco Firepower compute:SlotQual:minId managed object property"
    ::= { cfprComputeSlotQualEntry 5 }

END
