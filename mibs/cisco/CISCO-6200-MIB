-- ****************************************************
-- CISCO-C6200-MIB.my:     c6200 Platform Specific MIB
--
-- February 1998, the dms team
--
-- Copyright (c) 1998 by Cisco Systems, Inc.
-- All rights reserved.
--
-- ****************************************************

-- Glossary of terms
--
-- CAP:   Carrierless Amplitude Phase Modulation
-- DMT:   Discrete Multitone Modulation
-- DSLAM: Digital Subscriber Line ATM Multiplexor
-- RADSL: Rate Adaptive Digital Subscriber Loop
--

CISCO-6200-MIB DEFINITIONS ::= BEGIN

IMPORTS
        MODULE-IDENTITY, OBJECT-TYPE,
        Counter32, Gauge32, Integer32      FROM SNMPv2-SMI
        MODULE-COMPLIANCE, OBJECT-GROUP    FROM SNMPv2-CONF
        TEXTUAL-CONVENTION, DisplayString,
        DateAndTime                        FROM SNMPv2-TC
        ciscoExperiment                    FROM CISCO-SMI;

cisco6200MIB MODULE-IDENTITY
    LAST-UPDATED "9807280000Z"
    ORGANIZATION "Cisco System, Inc."
    CONTACT-INFO
           "Cisco Systems Customer Service
            Postal: 170 West Tasman Drive
                    San Jose, CA 95134
                    USA
            Tel: +1 800 553-NETS

            E-mail: cs-c6200@cisco.com"
    DESCRIPTION
        "This MIB provides CISCO 6200 product information It is
        structured as following groups: system - not part of indices,
        defines system, slot and port level scalars."
    REVISION	"9802260000Z"
    DESCRIPTION
	"The initial release of this MIB only supported CAP line cards."
::= { ciscoExperiment 26 }

--
-- OBJECT IDENTIFIER assignment for various groups
--

cisco6200MibObjects   OBJECT IDENTIFIER ::= { cisco6200MIB 1 }

c62System        OBJECT IDENTIFIER ::= { cisco6200MibObjects 1 }

c62Slot          OBJECT IDENTIFIER ::= { cisco6200MibObjects 2 }

c62OCInterface   OBJECT IDENTIFIER ::= { cisco6200MibObjects 3 }

c62LineInterface OBJECT IDENTIFIER ::= { cisco6200MibObjects 4 }

c62Subscriber    OBJECT IDENTIFIER ::= { cisco6200MibObjects 5 }

--
-- Textual conventions
--

C6200CardType ::= TEXTUAL-CONVENTION
    STATUS current
    DESCRIPTION
        "Represents card types contained in the C6200 product lines.
          oc3si    - one port, single mode, intermediate reach OC3
                   - based interface card
          ctl      - controller card
          cap8     - eight port CAP RADSL interface card
          cap16    - sixteen port CAP RADSL interface card
          oc3ss    - one port, single mode, short reach OC3 based
                   - interface card
          oc3mm    - one port, multi mode OC3 based interface card
          stm1si   - one port, single mode, intermediate reach STM1
                     based interface card
          stm1mm   - one port, multi mode STM1 based interface card
          dmt8     - eight port DMT RADSL interface card
          none     - marks slot as vacant"
    SYNTAX INTEGER {
          oc3si  (1),
          ctl    (2),
          cap8   (3),
          cap16  (4),
          oc3ss  (5),
          oc3mm  (6),
          stm1si (7),
          stm1mm (8),
          dmt8   (9),
          none   (-1)
	}

CommandValue ::= TEXTUAL-CONVENTION
    STATUS current
    DESCRIPTION
        "This parameter controls execution of a command. The intended
        command can be triggered by setting its value to execute.  Its
        value goes back to ready when intended command execution is
        complete."
    SYNTAX INTEGER {
        ready   (1),
        execute (2)
    }

AlarmLevel ::= TEXTUAL-CONVENTION
    STATUS	current
    DESCRIPTION
        "Represents error status."
    SYNTAX  INTEGER {
        none     (1),
        minor    (2),
        major    (3),
        critical (4),
        unknown  (5)
    }

InterfaceStatus ::= TEXTUAL-CONVENTION
    STATUS	current
    DESCRIPTION
        "Represents interface status."
    SYNTAX INTEGER {
              enabled  (1),
              disabled (2)
    }

TestStatus ::= TEXTUAL-CONVENTION
    STATUS current
    DESCRIPTION
        "Represents status of the test per subscriber line. Please refer
        to lineTestTable for details on how to start a test. Once test
        completes or aborted, status stays as pass, fail, or aborted
        respectively until user clears it by setting it to inactive or
        starts new test and that operation changes this to active."
    SYNTAX INTEGER {
        inactive  (1),  -- subscriber line is available for testing
        active    (2),  -- test is in progress on desired subscriber
                        -- line
        pass      (3),  -- bit error rate is less than bit error limit
        fail      (4),  -- bit error rate is more than bit error limit
        aborted   (5),  -- user aborted the test
        waiting   (6)   -- waiting for the CPE to deliver the results of the
                        -- test
	}

TestType ::= TEXTUAL-CONVENTION
    STATUS current
    DESCRIPTION
	"Represents Types of tests support per line."
    SYNTAX INTEGER {
        none            (0), -- No Test has been selected for this line
	lineQuality     (1), -- CAP line quality test
	capHardware     (2), -- CAP hardware test on the line card
        dmtLocalTest    (3)  -- DMT Local Test
	}

--
-- C6200 System parameters
--

--
-- System configuration allows user to change card type information.
-- It is useful to create static system configuration which acts as
-- inventory. This information is used by the system to monitor and
-- and report any runtime configuration mismatch.
--
systemType OBJECT-TYPE
    SYNTAX INTEGER {
        c62OC3 (1) -- system with OC3 based network interface
    }
    MAX-ACCESS read-only
    STATUS current
    DESCRIPTION
        "This type provides specific details about C6200 system type and
        what kind of network interface it uses."
::= { c62System 1 }

systemAlarmLevel OBJECT-TYPE
    SYNTAX AlarmLevel
    MAX-ACCESS read-only
    STATUS current
    DESCRIPTION
        "This reflects the alarm level of the C6200 system. It is the
        aggregation of the slot/port level alarms. Alarm levels
        supported at the system level are none, minor, major and
        critical.  Unknown has no meaning."
::= { c62System 2 }

systemAlarmLevelChngCounter OBJECT-TYPE
    SYNTAX Counter32
    MAX-ACCESS read-only
    STATUS current
    DESCRIPTION
        "Counter indicating a change in the system alarm level due to
        change either at the slot or port alarm level. This will be
        incremented by the system whenever any new alarm is raised or
        cleared at slot or port level. This is needed as rising or
        clearing of an alarm at port or slot level may not cause
        systemAlarmLevel to change.  This counter, in such case helps
        manager application to recognize that alarm levels below system
        level has changed without causing change in the
        systemAlarmLevel. e.g. Say: System has two subscriber lines
        experiencing a minor alarm condition.  systemAlarmLevel will be
        a minor alarm in such case. Now if one of the port level minor
        alarms clear, a port alarm level would become OK but the system
        and slot alarm levels may stay as a minor alarm."
::= { c62System 3 }

systemReset OBJECT-TYPE
    SYNTAX CommandValue
    MAX-ACCESS read-write
    STATUS current
    DESCRIPTION
        "This parameter allows user to reboot the system with system
        configuration from NVRAM (non-volatile memory). It can be used
        for following purposes:
          (1) Undo changes made to the system and not yet saved in the
              NVRAM.
          (2) Force the system to reboot from NVRAM configuration.
        This command disrupts service to all the subscribers associated
        with the system, so it should be use sparingly."
::= { c62System 4 }

systemSaveCnfg OBJECT-TYPE
    SYNTAX CommandValue
    MAX-ACCESS read-write
    STATUS current
    DESCRIPTION
        "This parameter allows user/operator to make system changes
        permanent. It causes system to write the system configuration on
        a non-volatile memory (NVRAM). There is no need to restart the
        system to make these changes effective."
::= { c62System 5 }

systemProvChngCounter OBJECT-TYPE
    SYNTAX Counter32
    MAX-ACCESS read-only
    STATUS current
    DESCRIPTION
        "Counter indicating a card or subscriber provisioning change.
        This will be incremented by the system whenever any change is
        made. This is used to avoid unneccessary polling."
::= { c62System 6 }

--
-- Environment Alarm Parameters
--
--
-- Slot table defines the individual cards that make up the
-- CISCO 6200 system.
--

systemHClockAlarmLevel OBJECT-TYPE
    SYNTAX AlarmLevel
    MAX-ACCESS read-only
    STATUS current
    DESCRIPTION
        "This reflects the alarm level of the H-bus backplane clock.
        H-bus clock error results in critical alarm at the at system
        level (systemAlarmLevel = critical)."
::= { c62System 7 }

systemFanAlarmLevel OBJECT-TYPE
    SYNTAX AlarmLevel
    MAX-ACCESS read-only
    STATUS current
    DESCRIPTION
        "This reflects the alarm level of the fans. Error for this
        parameter indicates failure of one or more fans. This error
        results in minor alarm at the system level (systemAlarmLevel =
        minor)."
::= { c62System 8 }

systemTemperatureAlarmLevel OBJECT-TYPE
    SYNTAX AlarmLevel
    MAX-ACCESS read-only
    STATUS current
    DESCRIPTION
        "This reflects the alarm level of the system temperature. When
        temperature exceeds system preconfigured system allowable limit
        this parameter indicates an error. This error results in minor
        alarm at the system level (systemAlarmLevel = minor)."
::= { c62System 9 }

systemACO OBJECT-TYPE
    SYNTAX CommandValue
    MAX-ACCESS read-write
    STATUS current
    DESCRIPTION
        "This parameter deactivates the audible alarm at the system.
        Audible alarm is generated by the system to announce detection
        of new alarm(s). Once deactivated, system may activate it again
	if it detects new additional alarm(s)."
::= { c62System 10 }

slotTable OBJECT-TYPE
    SYNTAX SEQUENCE OF SlotEntry
    MAX-ACCESS not-accessible
    STATUS current
    DESCRIPTION
        "Table contains slot level information such as status, status
        change time, card type and software version. It is indexed using
        slot identifier. Empty entries are indicated using status empty
        and card type none.

        Operator can provision a new card in the system by setting
        slotCnfType parameter in this table.

        Changes to the slot configuration are temporary until user
        actually requests save operation through systemSaveCnfg.  Only
        at that point system writes information in the NVRAM storage and
        information becomes permanent."
::= { c62Slot 1 }

slotEntry OBJECT-TYPE
    SYNTAX SlotEntry
    MAX-ACCESS not-accessible
    STATUS current
    DESCRIPTION
        "Entry in the slot table"
    INDEX { slotID }
::= { slotTable 1 }

SlotEntry ::=
    SEQUENCE {
        slotID                          INTEGER,
        slotType                        C6200CardType,
        slotStatus                      INTEGER,
        slotSwVersion                   Integer32,
        slotAlarmLevelChngCounter       Counter32,
        slotCnfType                     C6200CardType,
        slotSubscriberChngCounter       Counter32,
        slotAlarmLevel		        AlarmLevel
}

slotID OBJECT-TYPE
    SYNTAX INTEGER (1..14)
    MAX-ACCESS not-accessible
    STATUS current
    DESCRIPTION
        "Slot Identifier for the selected slot."
::= { slotEntry 1 }

slotType OBJECT-TYPE
    SYNTAX C6200CardType
    MAX-ACCESS read-only
    STATUS current
    DESCRIPTION
        "The current type of card in the physical cage, as reported by
        the system."
::= { slotEntry 2 }

slotStatus OBJECT-TYPE
    SYNTAX INTEGER {
        empty           (1),  -- Slot is empty.
        notProvisioned  (2),  -- A card has been detected in the slot,
                              -- but has not been provisioned.
        missing         (3),  -- Slot has been provisioned, but there is
                              -- no card in the slot.
        mismatch        (4),  -- Slot has been provisioned, but the card
                              -- in the slot is not the correct type.
        match           (5)   -- Slot has been provisioned and the card
                              -- in the slot is the correct type.
    }
    MAX-ACCESS read-only
    STATUS current
    DESCRIPTION
        "The current status of the slot."
::= { slotEntry 3 }

slotSwVersion OBJECT-TYPE
    SYNTAX Integer32
    MAX-ACCESS read-only
    STATUS current
    DESCRIPTION
        "The currently active firmware version number as a positive
        whole number, e.g. 100."
::= {slotEntry 4 }

slotAlarmLevelChngCounter OBJECT-TYPE
    SYNTAX Counter32
    MAX-ACCESS read-only
    STATUS current
    DESCRIPTION
        "Counter indicating change in the port alarm level. This is
        needed as rising or clearing of an port level alarm may not
        cause slotAlarmLevel to change. This counter, in such case helps
        a manager application to recognize that the alarm levels below
        slot level have changed without change in the slotAlarmLevel
        (e.g. Say: a line card has two subscriber lines experiencing
        Minor alarm condition.  The slot alarm level will be minor alarm
        in such case. Now if one of the port level minor alarms clear,
        the port alarm level would become OK but slot alarm level will
        stay as a minor alarm. Alarm level change includes rising or
        clearing of a new alarm at slot/port level)."
::= {slotEntry 5 }

slotCnfType OBJECT-TYPE
    SYNTAX C6200CardType
    MAX-ACCESS read-write
    STATUS current
    DESCRIPTION
        "Card type, as provisioned by the operator used to compare
        against card type reported by the system for monitoring
        purposes. If slotType and slotCnfType do not match and
        slotCnfType is not set to none, slotStatus is set to mismatch.
        This condition only clears when operator corrects the
        configuration to make them match.

        The valid card type for each slot is as follows:

        slot      1: oc3si, oc3mm, stm1si and stm1mm
        slot      2: ctl
        slot 3 &  4: none
        slot 5 - 14: cap8 and dmt8"
::= { slotEntry 6 }

slotSubscriberChngCounter OBJECT-TYPE
    SYNTAX Counter32
    MAX-ACCESS read-only
    STATUS current
    DESCRIPTION
        "Counter indicating change in the subscriber table.  This will
        be incremented by the slot whenever any change is made at the
        port level. This is used to avoid unneccessary polling at the
        subscriber table level."
::= { slotEntry 7 }

slotAlarmLevel OBJECT-TYPE
    SYNTAX AlarmLevel
    MAX-ACCESS read-only
    STATUS current
    DESCRIPTION
        "This reflects the alarm level of the slot. It is the
        aggregation of the port level alarms. Alarm levels supported at
        the slot level are none, minor, major, critical and unknown."
::= { slotEntry 8 }

--
-- Lets define portID which will be used to access OC3 port as well
-- as subscriber line information
--

portID OBJECT-TYPE
    SYNTAX Integer32(0..64)
    MAX-ACCESS not-accessible
    STATUS current
    DESCRIPTION
        "Port Identifier on the targeted slot. PortID value depends on
        the slot type."
::= { c62Slot 2 }

--
-- Optical Interface Fault Parameters
--

oCInterfaceTable OBJECT-TYPE
    SYNTAX SEQUENCE OF OCInterfaceEntry
    MAX-ACCESS not-accessible
    STATUS current
    DESCRIPTION
        "This table contains SONET alarm information. It is indexed
        using slot and port identifier. Each object represents the alarm
        level of individual SONET alarm condition."
::= { c62OCInterface 1 }

oCInterfaceEntry OBJECT-TYPE
    SYNTAX OCInterfaceEntry
    MAX-ACCESS not-accessible
    STATUS current
    DESCRIPTION
        "Each entry represents a SONET alarm condition. Following are
        the definition of SONET level alarms:
           EQF  - Equipment Failure (Local) (causes slotStatus to be
                  critical)
        Near End Alarms (causes slotStatus to be critical):
           LOS  - Loss of Signal
           LOF  - Loss of Frame
           LAIS - Line Alarm Indication Signal
           LOP  - Loss of Pointer
           PAIS -  Path Alarm Indication Signal
           SLM  - Signal Label Mismatch
        Far End Alarms: (causes slotStatus to be critical)
           LRFI - Line Remote Failure Indication
           PRFI - Path Remote Failure Indication
        Miscellaneous. Alarms:
           LOST - Loss Of Synchronization (causes slotStatus to be major)
           LOCD - Loss 0f Cell Delineation.  (causes slotStatus to be
                  critical)

	Individual alarm description describes any interdependencies
        between alarm types. It also contains port status and interface
        mode."
    INDEX { slotID, portID }
::= { oCInterfaceTable 1 }

OCInterfaceEntry ::=
    SEQUENCE {
        oCIAlarmLevel    AlarmLevel,
        oCIEQF           AlarmLevel,
        oCILOS           AlarmLevel,
        oCILOF           AlarmLevel,
        oCILAIS          AlarmLevel,
        oCILOP           AlarmLevel,
        oCIPAIS          AlarmLevel,
        oCISLM           AlarmLevel,
        oCILRFI          AlarmLevel,
        oCIPRFI          AlarmLevel,
        oCILOST          AlarmLevel,
        oCILOCD          AlarmLevel,
        oCILoopMode      INTEGER
}

oCIAlarmLevel OBJECT-TYPE
    SYNTAX AlarmLevel
    MAX-ACCESS read-only
    STATUS current
    DESCRIPTION
        "The current alarm level on the optical interface, may be none,
        major, critical or unknown. When the port is experiencing
        equipment failure or any of the near end alarm condition, the
        alarm level is marked critical. When the port is experiencing a
        far end alarm condition, the alarm level is marked major. When
        the port is in loopback mode, the alarm level is marked as
        unknown."
::= { oCInterfaceEntry 2 }

oCIEQF OBJECT-TYPE
    SYNTAX AlarmLevel
    MAX-ACCESS read-only
    STATUS current
    DESCRIPTION
        "Local equipment failure indication. Possible values are none or
        critical.  When this attribute is critical, all other alarm
        conditions are unknown."
::= { oCInterfaceEntry 3 }

--
-- Near End Alarms
--

oCILOS OBJECT-TYPE
    SYNTAX AlarmLevel
    MAX-ACCESS read-only
    STATUS current
    DESCRIPTION
        "Loss of signal indication. Possible values are none or
        critical. When this attribute is critical, oCILOF, oCILOP, oCILAIS,
        oCIPAIS, oCISLM, oCILRFI, oCIPRFI and oCILOCD are unknown."
::= { oCInterfaceEntry 4 }

oCILOF OBJECT-TYPE
    SYNTAX AlarmLevel
    MAX-ACCESS read-only
    STATUS current
    DESCRIPTION
        "Loss of frame indication. Possible values are none, critical or
        unknown. When this attribute is critical, oCILAIS, oCILOP,
        oCIPAIS, oCISLM, oCILRFI, oCIPRFI and oCILOCD are unknown."
::= { oCInterfaceEntry 5 }

oCILAIS OBJECT-TYPE
    SYNTAX AlarmLevel
    MAX-ACCESS read-only
    STATUS current
    DESCRIPTION
        "Line alarm indication signal. Possible values are none,
        critical or unknown. When this attribute is critical, oCILOP and
        oCISLM are unknown."
::= { oCInterfaceEntry 6 }

oCILOP OBJECT-TYPE
    SYNTAX AlarmLevel
    MAX-ACCESS read-only
    STATUS current
    DESCRIPTION
        "Loss of pointer indication. Possible values are none, critical
        or unknown. When this attribute is critical, oCIPAIS, oCISLM and
        oCILOCD are unknown."
::= { oCInterfaceEntry 7 }

oCIPAIS OBJECT-TYPE
    SYNTAX AlarmLevel
    MAX-ACCESS read-only
    STATUS current
    DESCRIPTION
        "Path alarm indication signal. Possible values are none,
        critical or unknown. When this attribute is critical, oCISLM is
        unknown."
::= { oCInterfaceEntry 8 }

oCISLM OBJECT-TYPE
    SYNTAX AlarmLevel
    MAX-ACCESS read-only
    STATUS current
    DESCRIPTION
        "Signal label mismatch indication. Possible values are none,
        critical or unknown."
::= { oCInterfaceEntry 9 }

--
-- Far End Alarms
--

oCILRFI OBJECT-TYPE
    SYNTAX AlarmLevel
    MAX-ACCESS read-only
    STATUS current
    DESCRIPTION
        "Line remote failure indication. Possible values are none,
        critical or unknown."
::= { oCInterfaceEntry 10 }

oCIPRFI OBJECT-TYPE
    SYNTAX AlarmLevel
    MAX-ACCESS read-only
    STATUS current
	DESCRIPTION
        "Path remote failure indication. Possible values are none,
        critical or unknown."
::= { oCInterfaceEntry 11 }

--
-- Miscellaneous Alarms
--

oCILOST OBJECT-TYPE
    SYNTAX AlarmLevel
    MAX-ACCESS read-only
    STATUS current
    DESCRIPTION
        "Loss of synchronization indication. Possible values are none,
        major or unknown."
::= { oCInterfaceEntry 12 }

oCILOCD OBJECT-TYPE
    SYNTAX AlarmLevel
    MAX-ACCESS read-only
    STATUS current
    DESCRIPTION
        "Loss of cell delineation. Possible values are none, critical or
        unknown."
::= { oCInterfaceEntry 13 }

oCILoopMode OBJECT-TYPE
    SYNTAX INTEGER {
         enable (1),
         disable (2)
    }
    MAX-ACCESS read-write
    STATUS current
    DESCRIPTION
        "This parameter puts the optical interface of C6200 system in
        facility (far end) loopback mode. It causes the node to loop all
        the traffic received on the optical interface back to the
        network. It does not generate any traffic or perform any kind of
        testing locally. This mode affects services to all the users
        connected through the node, so this facility must be used with
        care. User must set it back to disable mode once the testing
        completes. System will stay in loopback mode, if enabled, until
        the user disables the loop mode through NMS Manager or the
        system terminates - in which case loop mode is disabled
        automatically.

        It is only meaningful when the out of band management channel is
        used for management. It may not be useful when the in-band
        management channel is used for management traffic, as it causes
        breakdown in the management communications channel.

        The alarm level of the port is set to unknown while loopback
        mode is enabled."

::= { oCInterfaceEntry 14 }

--
-- Optical Interface Performance Parameters
--
oCPerfTable OBJECT-TYPE
    SYNTAX SEQUENCE OF OCPerfEntry
    MAX-ACCESS not-accessible
    STATUS current
    DESCRIPTION
       "This table contains SONET Performance parameters."
::= { c62OCInterface 2 }

oCPerfEntry OBJECT-TYPE
    SYNTAX OCPerfEntry
    MAX-ACCESS not-accessible
    STATUS current
    DESCRIPTION
        "Each entry represents a SONET performance parameters for the
        targeted port."
    INDEX { slotID, portID }
::= { oCPerfTable 1 }

OCPerfEntry ::=
    SEQUENCE {
        oCPTxCellCount       Counter32,
        oCPRxCellCount       Counter32,
        oCPHecErrCount       Counter32
}

oCPTxCellCount OBJECT-TYPE
    SYNTAX Counter32
    MAX-ACCESS read-only
    STATUS current
    DESCRIPTION
        "Count of number of non-idle ATM cells inserted into the
        transmit SONET payload since system start time. This is free
        running counter and rolls back to zero when the value exceeds
        2^32."
::= { oCPerfEntry 1 }

oCPRxCellCount OBJECT-TYPE
    SYNTAX Counter32
    MAX-ACCESS read-only
    STATUS current
    DESCRIPTION
        "Count of number of ATM cells received at SONET interface since
        system start time. Idle cells and cells with uncorrectable
        header errors are not included in the count. This is a free
        running counter which rolls back to zero when the value exceeds
        2^32."
::= { oCPerfEntry 2 }

oCPHecErrCount OBJECT-TYPE
    SYNTAX Counter32
    MAX-ACCESS read-only
    STATUS current
    DESCRIPTION
        "A count of uncorrectable header errors since system start time.
        This is a free running counter which rolls back to zero when the
        value exceeds 2^32."
::= { oCPerfEntry 3 }

--
-- Line Interface Parameters
--

lineInterfaceTable OBJECT-TYPE
    SYNTAX SEQUENCE OF LineInterfaceEntry
    MAX-ACCESS not-accessible
    STATUS current
    DESCRIPTION
        "The line table describes basic identification and runtime fault
        information on the individual subscriber line. A subscriber line
        consists of a port on the line card, Customer Premises
        Equipment (CPE) and a physical line connecting both. Fault
        monitoring is supported for both ends of the line. Subscriber
        line information consists of upstream (local port) information
        as well as downstream (Remote CPE) information.

        Downstream (ATU-C->ATU-R) information is reported by the
        individual port of the line card locally.

        Upstream (ATU-R->ATU-C) information is remote end (CPE)
        information which can be obtained via heartbeat messages generated
        by the CPE, other proprietary or standards based mechanisms. This
        information is proxied by the line card on the C6200 system.

        Entries in the table with non-assigned port have their mode
        disabled, so no service is available unless the port is
        configured and assigned to a subscriber."
::= { c62LineInterface 1 }

lineInterfaceEntry OBJECT-TYPE
    SYNTAX LineInterfaceEntry
    MAX-ACCESS not-accessible
    STATUS current
    DESCRIPTION
        "The entry describes the fields being supported by the line
        table."
    INDEX { slotID, portID }
::= { lineInterfaceTable 1 }

LineInterfaceEntry ::=
    SEQUENCE {
        lineAlarmLevel        AlarmLevel,
        lineDwnSNRMargin      Integer32,
        lineDwnLOCD           AlarmLevel,
        lineDwnErrSecs        Counter32,
        lineDwnLineRate       Gauge32,
        lineUpSNRMargin       Integer32,
        lineUpLOCD            AlarmLevel,
        lineUpErrSecs         Counter32,
        lineUpLineRate        Gauge32,
        lineRateAlarm         INTEGER,
        lineMode              INTEGER,
        lineDMTDwnAttenuation Gauge32,
        lineDMTUpAttenuation  Gauge32,
        lineDMTDwnLPR         AlarmLevel,
        lineDMTUpLOS          AlarmLevel,
        lineDMTUpLOF          AlarmLevel,
        lineDMTLoopback       INTEGER
}

lineAlarmLevel OBJECT-TYPE
    SYNTAX AlarmLevel
    MAX-ACCESS read-only
    STATUS current
    DESCRIPTION
        "The current alarm level of the port.  Refer to
        TEXTUAL-CONVENTION section for details on AlarmLevel. Only
        following values for the AlarmLevel are possible for this
        attribute:
            none  - Everything is fine
            minor - Local end or remote end is experiencing problems,
                 e.g.
                 (1) loss of Cell Delineation is observed on the
                     downstream direction.
                 (2) subscriberDwnLineRate and lineDwnLineRate do not
                     match.
                 (3) subscriberUpLineRate and lineUpLineRate do not
                     match.
		 (4) Both Up/down line rates do not match with the
                     subscriber requested rates.
                 (5) loss of signal is observed in the downstream
                     direction for DMT cards and the object
                     subscriberDMTLOSConfig is configured to alarm
                     this condition.
                 (6) loss of frame is observed in the downstream
                     direction for DMT cards.
            unknown - Remote end is non-reachable. This could be
               either due to power down at the CPE or due to break in
               the connection between C6200 system and the CPE.  This is
               exhibited by the lineDMTUpLOS alarm."
::= { lineInterfaceEntry 1 }

--
-- ATU-C (Downstream) information
--

lineDwnSNRMargin OBJECT-TYPE
    SYNTAX Integer32
    UNITS "dB"
    MAX-ACCESS read-only
    STATUS current
    DESCRIPTION
        "In db, the difference between the current downstream signal
        to noise ratio and the SNR required for the selected line
        rate.  as seen by the cpe.  This object must be divided by 10
        to obtain the real value for CAP only.  Following are the
        possible values:
          Negative number - bad SNR margin for the desired line rate.
          0               - adequate SNR (no margin) for the desired line
                            rate.
          Positive number - Good SNR margin for the desired line rate.
                            Higher number means better SNR margin and
                            better line quality."

::= { lineInterfaceEntry 2 }

lineDwnLOCD OBJECT-TYPE
    SYNTAX AlarmLevel
    MAX-ACCESS read-only
    STATUS deprecated
    DESCRIPTION
        "Downstream loss of cell delineation. It indicates that the cpe
        received cells on the line do not contain a valid header error
        check (HEC).

        This object is no longer supported."
::= { lineInterfaceEntry 3 }

lineDwnErrSecs OBJECT-TYPE
    SYNTAX Counter32
    MAX-ACCESS read-only
    STATUS current
    DESCRIPTION
        "Downstream count of errored seconds received by the cpe. An error
        second is a second with line quality problems due to a HEC error
        in CAP cards or CRC, LOS or SEF events in DMT cards."
::= { lineInterfaceEntry 4 }

lineDwnLineRate OBJECT-TYPE
    SYNTAX Gauge32
    UNITS "kbps"
    MAX-ACCESS read-only
    STATUS current
    DESCRIPTION
        "Current downstream line rate in kbps. It is adapted by the line
        card using rate adaptation logic."
::= { lineInterfaceEntry 5 }

--
-- ATU-R (Upstream) information
--

lineUpSNRMargin OBJECT-TYPE
    SYNTAX Integer32
    UNITS "dB"
    MAX-ACCESS read-only
    STATUS current
    DESCRIPTION
        "In db, the difference between the current upstream signal to
        noise ratio and the SNR required for the selected line rate as
        seen by the co.  This object must be divided by 10 to obtain
        the real value for CAP only.  Following are the possible values:
          Negative number - bad SNR margin for the desired line rate.
          0               - adequate SNR (no margin) for the desired line
                            rate.
          Positive number - Good SNR margin for the desired line rate.
                            Higher number means better SNR margin and
                            better line quality."
::= { lineInterfaceEntry 6 }

lineUpLOCD OBJECT-TYPE
    SYNTAX AlarmLevel
    MAX-ACCESS read-only
    STATUS current
    DESCRIPTION
        "Upstream loss of cell delineation. It indicates that the co
        received cells on the line do not contain a valid header
        error check (HEC). This alarm will be marked unknown if
        lineDMTDwnLPR, lineDMTUpLOS or lineDMTUpLOF on a DMT card are
        minor."
::= { lineInterfaceEntry 7 }

lineUpErrSecs OBJECT-TYPE
    SYNTAX Counter32
    MAX-ACCESS read-only
    STATUS current
    DESCRIPTION
        "Upstream count of errored seconds recieved by the co. An error
        second is a second with line quality problems due to a HEC error.
        or CRC, LOS or SEF events in DMT cards."
::= { lineInterfaceEntry 8 }

lineUpLineRate OBJECT-TYPE
    SYNTAX Gauge32
    UNITS "kbps"
    MAX-ACCESS read-only
    STATUS current
    DESCRIPTION
       "Current upstream line rate in kbps. This is adapted by the line
        card using rate adaptation logic."
::= { lineInterfaceEntry 9 }

lineRateAlarm OBJECT-TYPE
    SYNTAX INTEGER {
        ok        (1),
        down      (2),
        up        (3),
        downAndUp (4)
    }
    MAX-ACCESS read-only
    STATUS current
    DESCRIPTION
        "This parameter is the comparison between actual
        (lineDwnLineRate/ lineUpLineRate) and the user requested line
        rates (subscriberDwnLineRate/subscriberUpLineRate).  User
        requested rates are part of the subscriber section of the MIB.
        Following is the list of possible values:
        1 - both the line rates match user requested rates.
        2 - Downstream line rate does not match user requested rate.
        3 - Upstream line rate does not match user requested rate.
        4 - Both rates do not match user requested rates."
::= { lineInterfaceEntry 10 }

lineMode OBJECT-TYPE
    SYNTAX INTEGER {
           testing  (1), -- line is under test.
           training (2), -- line is trying to acquire user requested
                         -- rate or in rate adaptation mode.
           active   (3), -- line is active and in data transfer mode.
           down     (4)  -- subscriber line is administratively disabled.
        }
    MAX-ACCESS read-only
    STATUS current
    DESCRIPTION
        "This parameter shows current mode of the line. The possible
        modes are as shown above. Normally line stays in active mode, if
        everything is fine. If the line test fails, it goes into
        training mode and tries to acquire next possible lower rate. The
        line can also go into the training mode when the line card is
        unable to communicate to the remote end. It does not come out of
        the training mode until it is able to acquire a user requested
        rate or a lower rate, if that is unattainable. This mode is
        changed by the system to down, when the subscriber line is
        administratively disabled."
::= { lineInterfaceEntry 11 }

lineDMTDwnAttenuation OBJECT-TYPE
    SYNTAX Gauge32
    UNITS "dB"
    MAX-ACCESS read-only
    STATUS current
    DESCRIPTION
        "Measures downstream attenuation of the line reported by the CPE
        for the DMT card only. The units for this value are in decibels
        (dB).  This object is instantiated for the CAP card."
::= { lineInterfaceEntry 12 }

lineDMTUpAttenuation OBJECT-TYPE
    SYNTAX Gauge32
    UNITS "dB"
    MAX-ACCESS read-only
    STATUS current
    DESCRIPTION
        "Measures upstream attenuation of the line reported by the CO
        for the DMT card only. The units for this value are in decibels
        (dB).  This object is instantiated for the CAP card."
::= { lineInterfaceEntry 13 }

lineDMTDwnLPR OBJECT-TYPE
    SYNTAX AlarmLevel
    MAX-ACCESS read-only
    STATUS current
    DESCRIPTION
        "Downstream loss of power indicator reported by the CPE for
        the DMT card only.  Valid values are minor, unknown, or none.
        When this alarm is minor, lineUpLOS, lineUpLOF and lineUpLOCD
        are unknown.  This object is instantiated for the CAP card."
::= { lineInterfaceEntry 14 }

lineDMTUpLOS OBJECT-TYPE
    SYNTAX AlarmLevel
    MAX-ACCESS read-only
    STATUS current
    DESCRIPTION
        "Upstream loss of signal alarm indicator reported by the CO
        for the DMT card only.  Valid values are minor or none.  When
        this alarm is minor, lineDMTUpLOF and lineUpLOCD are unknown.
        This object is instantiated for the CAP card."
::= { lineInterfaceEntry 15 }

lineDMTUpLOF OBJECT-TYPE
    SYNTAX AlarmLevel
    MAX-ACCESS read-only
    STATUS current
    DESCRIPTION
        "Upstream loss of frame alarm indicator reported by the CO for
        the DMT card only.  Valid values are minor or none.  When this
        alarm is minor, lineUpLOCD is unknown.  This alarm value is
        unknown when lineDMTDwnLPR or lineDMTUpLOS is minor.  This
        object is instantiated for the CAP card."
::= { lineInterfaceEntry 16 }

lineDMTLoopback OBJECT-TYPE
    SYNTAX INTEGER {
         none     (1),
         dslline (2),
         local    (3)
    }
    MAX-ACCESS read-write
    STATUS current
    DESCRIPTION
        "DMT supported ATM layer loopback.  dslline loops all ATM
        cells toward the CO modem back to the CPE.  Local loops all
        ATM cells sent by the ATM trunk card toward the ATM trunk
        card.  When this object is not set to none, lineMode will be
        set to testing.  This object is instantiated for the CAP
        card."
::= { lineInterfaceEntry 17 }

--
-- ATU-C (Line Interface) Performance Parameters
--
linePerfTable OBJECT-TYPE
    SYNTAX SEQUENCE OF LinePerfEntry
    MAX-ACCESS not-accessible
    STATUS current
    DESCRIPTION
        "This table contains line performance parameters. It contains
        one entry per subscriber line. Only the ATU-C (local)
        performance parameters are reported in this table."
::= { c62LineInterface 2 }

linePerfEntry OBJECT-TYPE
    SYNTAX LinePerfEntry
    MAX-ACCESS not-accessible
    STATUS current
    DESCRIPTION
        "Each entry represents a performance parameter for the targeted
        subscriber line."
    INDEX { slotID, portID }
::= { linePerfTable 1 }

LinePerfEntry ::=
    SEQUENCE {
        lineTxCellCount        Counter32,
        lineRxCellCount        Counter32,
        lineHecErrCount        Counter32,
        lineDMTDwnFECCount     Counter32,
        lineDMTUpFECCount      Counter32,
        lineDMTDwnCRCCount     Counter32,
        lineDMTUpCRCCount      Counter32,
        lineDMTDwnLOSCount     Counter32,
        lineDMTUpLOSCount      Counter32,
        lineDMTDwnSEFCount     Counter32,
        lineDMTUpRDICount      Counter32
}

lineTxCellCount OBJECT-TYPE
    SYNTAX Counter32
    MAX-ACCESS 	read-only
    STATUS current
    DESCRIPTION
        "Total cell count in the downstream direction (ATU-C->ATU-R)
        reported by the CPE. The counter value does not include cells
        with uncorrectable HEC errors.  This is a free running counter
        which rolls back to zero when the value exceeds 2^32."
::= { linePerfEntry 1 }

lineRxCellCount OBJECT-TYPE
    SYNTAX Counter32
    MAX-ACCESS 	read-only
    STATUS current
    DESCRIPTION
        "Total cell count in the upstream direction (ATU-R->ATU-C)
        reported by the CO. The counter value does not include cells
        with uncorrectable HEC errors.  This is a free running counter
        which rolls back to zero when the value exceeds 2^32."
::= { linePerfEntry 2 }

lineHecErrCount OBJECT-TYPE
    SYNTAX Counter32
    MAX-ACCESS 	read-only
    STATUS current
    DESCRIPTION
        "Total HEC error count in the upstream (ATU-R->ATU-C) direction
        reported by the CO.  This is a free running counter which rolls
        back to zero when the value exceeds 2^32."
::= { linePerfEntry 3 }

lineDMTDwnFECCount OBJECT-TYPE
    SYNTAX Counter32
    MAX-ACCESS read-only
    STATUS current
    DESCRIPTION
        "Downstream count of forward error correction (FEC) events
        reported by the CPE for the DMT card only."
::= { linePerfEntry 4 }

lineDMTUpFECCount OBJECT-TYPE
    SYNTAX Counter32
    MAX-ACCESS read-only
    STATUS current
    DESCRIPTION
        "Upstream count of forward error correction (FEC) events
        reported by the CO for the DMT card only.  This object is
        instantiated for the CAP card."
::= { linePerfEntry 5 }

lineDMTDwnCRCCount OBJECT-TYPE
    SYNTAX Counter32
    MAX-ACCESS read-only
    STATUS current
    DESCRIPTION
        "Downstream count of cyclical error correction (CRC) events
        reported by the CPE for the DMT card only.  This object is
        instantiated for the CAP card."
::= { linePerfEntry 6 }

lineDMTUpCRCCount OBJECT-TYPE
    SYNTAX Counter32
    MAX-ACCESS read-only
    STATUS current
    DESCRIPTION
        "Upstream count of cyclical error correction (CRC) events
        reported by the CO for the DMT card only.  This object is
        instantiated for the CAP card."
::= { linePerfEntry 7 }

lineDMTDwnLOSCount OBJECT-TYPE
    SYNTAX Counter32
    MAX-ACCESS read-only
    STATUS current
    DESCRIPTION
        "Downstream count of loss of signal (LOS) events reported by
        the CPE for the DMT card only.  This object is instantiated
        for the CAP card."
::= { linePerfEntry 8 }

lineDMTUpLOSCount OBJECT-TYPE
    SYNTAX Counter32
    MAX-ACCESS read-only
    STATUS current
    DESCRIPTION
        "Upstream count of loss of signal (LOS) events reported by the
        CO for the DMT card only.  This object is instantiated for the
        CAP card."
::= { linePerfEntry 9 }

lineDMTDwnSEFCount OBJECT-TYPE
    SYNTAX Counter32
    MAX-ACCESS read-only
    STATUS current
    DESCRIPTION
        "Downstream count of severly errored frame (SEF) events
        reported by the CPE for the DMT card only.  This object is
        instantiated for the CAP card."
::= { linePerfEntry 10 }

lineDMTUpRDICount OBJECT-TYPE
    SYNTAX Counter32
    MAX-ACCESS read-only
    STATUS current
    DESCRIPTION
        "Upstream count of remote defect indication (RDI) events
        reported by the CO for the DMT card only.  This object is
        instantiated for the CAP card."
::= { linePerfEntry 11 }

--
-- Line Test Table
--

lineTestTable OBJECT-TYPE
    SYNTAX SEQUENCE OF LineTestEntry
    MAX-ACCESS not-accessible
    STATUS current
    DESCRIPTION
        "The Line test table contains the line test parameters per
        subscriber line. It controls access to the testing capabilities
        at the subscriber line level. This table contains an entry per
        subscriber line."
::= { c62LineInterface 3 }

lineTestEntry OBJECT-TYPE
    SYNTAX LineTestEntry
    MAX-ACCESS not-accessible
    STATUS current
    DESCRIPTION
        "The entry describes the fields supported by the line test
        table."
    INDEX { slotID, portID }
::= { lineTestTable 1 }

LineTestEntry ::=
    SEQUENCE {
        lineTestTrigger         INTEGER,
        lineTestType            TestType,
        lineTestTimeIntvl       INTEGER,
        lineTestStatus          TestStatus,
        lineTestDwnBitErrRate   Integer32,
        lineTestUpBitErrRate    Integer32,
        lineTestStartTime       DateAndTime,
        lineTestCmplTime        DateAndTime,
        lineTestBitErrRateLimit Integer32
}

lineTestTrigger OBJECT-TYPE
    SYNTAX INTEGER {
        stop  (1),
        start (2),
        clear (3)
				}
    MAX-ACCESS read-write
    STATUS current
    DESCRIPTION
        "Starts or stops (aborts) a test in progress. The agent will
        only start a new test, if no test is active on the targeted
        port.  The user must set lineTestTimeIntvl to an appropriate
        value before starting test by setting this parameter to start.
        The System resets the value back to stop when the test
        completes.  This parameter value affects lineTestStatus as
        following:

             value   current lineTestStatus  new lineTestStatus
             -----   ----------------------  ------------------
             start   inactive/pass/fail/     active
                     aborted
             stop    active                  aborted
             clear   pass/fail/aborted       inactive

        The rest of the combinations will result in error.

        Starting of the test may fail due to a line test already in
        progress on the selected subscriber line.

        Agent updates lineTestStartTime, when it accepts the line test.
        Agent updates lineTestCmplTime, when the test completes or when
        user aborts the test.

        Stopping a test resets lineTestUpBitErrRate and
        lineTestDwnBitErrRate.

        Clearing a test resets lineTestStartTime, lineTestCmplTime,
        lineTestUpBitErrRate, and lineTestDwnBitErrRate to zero.
        lineTestTimeIntvl and lineTestBitErrRateLimit get set back to
        their defaults.  Finally, lineTestStatus is set to inactive.

        Line test information only resets when the user sets this
        parameter to clear, otherwise parameters from the previous run
        of the test are preserved until system is rebooted. All of the
        parameters are initialized on reboot."
::= { lineTestEntry 1 }

lineTestType OBJECT-TYPE
    SYNTAX TestType
    MAX-ACCESS read-write
    STATUS current
    DESCRIPTION
        "The type of the test to be performed.  If capHardware test
        is selected, time interval is determined by the system. Both
        the test types are destructive: affects the service on that
        line.  The agent will only change lineTestType, if no test is
        active on the targeted port.

        For DMT cards, the DMTLocalTest is available.  It is a
        destructive test that affects service on that line."
::= { lineTestEntry 2 }

lineTestTimeIntvl OBJECT-TYPE
    SYNTAX INTEGER (0..60)
    UNITS "minutes"
    MAX-ACCESS read-write
    STATUS current
    DESCRIPTION
        "Time interval in minutes between 0 - 60 minutes.  This
        parameter is only meaningful, if test type is the line
        quality test. Default value is 30 minutes.  The agent will
        only change lineTestTimeIntvl, if no test is active on the
        targeted port."
    DEFVAL { 30 }
::= { lineTestEntry 3 }

lineTestStatus OBJECT-TYPE
    SYNTAX TestStatus
    MAX-ACCESS read-only
    STATUS current
    DESCRIPTION
        "System changes values for this variable based on trigger value
        as well as based on system reported result. When test completes,
        system compares lineTestDwnBitErrRate and lineTestUpBitErrRate
        to lineTestBitErrRateLimit in order to determine whether the
        line test failed or passed. Agent sets this variable based on
        this comparison."
::= { lineTestEntry 4 }

lineTestDwnBitErrRate OBJECT-TYPE
    SYNTAX Integer32
    MAX-ACCESS read-only
    STATUS current
    DESCRIPTION
        "This is positive integer value representing a negative exponent
        of 10 for the error rate in the downstream direction. It is only
        meaningful when the line quality test is done on the affected
        subscriber line. It is compared against lineTestBitErrRateLimit
        to determine lineTestStatus value when the line quality test
        completes. This value is interpreted as following:
           < 10-7  - Bad line quality
           10-7    - Acceptable line quality
           > 10-7  - Better line quality"
::= { lineTestEntry 5 }

lineTestUpBitErrRate OBJECT-TYPE
    SYNTAX Integer32
    MAX-ACCESS read-only
    STATUS current
    DESCRIPTION
        "This is positive integer value representing a negative exponent
        of 10 for the error rate in the upstream direction. It is only
        meaningful when the line quality test is done on the affected
        subscriber line. It is compared against lineTestBitErrRateLimit
        to determine lineTestStatus value when the line quality test
        completes. This value is interpreted as following:
           < 10-7  - Bad line quality
           10-7    - Acceptable line quality
           > 10-7  - Better line quality"
::= { lineTestEntry 6 }

lineTestStartTime OBJECT-TYPE
    SYNTAX DateAndTime
    MAX-ACCESS read-only
    STATUS current
    DESCRIPTION
        "Time stamp in displayable format. This is the time when the
        system starts the requested test."
::= { lineTestEntry 7 }

lineTestCmplTime OBJECT-TYPE
    SYNTAX DateAndTime
    MAX-ACCESS read-only
    STATUS current
    DESCRIPTION
       "Time stamp in displayable format. This is the time when the
        system completes the requested test or when the user aborts the
        test."
::= { lineTestEntry 8 }

lineTestBitErrRateLimit OBJECT-TYPE
    SYNTAX Integer32(3..10)
    MAX-ACCESS read-write
    STATUS current
    DESCRIPTION
        "This is a positive integer representing a negative exponent
        of 10.  It represents bit error rate limit allowed for the
        subscriber line quality test. The system compares the bit
        error rates reported at the end of line quality test to this
        limit to determine line quality. Allowable error rates are
        between 10-3 and 10-10. The agent will only change
        lineTestBitErrRateLimit, if no test is active on the targeted
        port."
::= { lineTestEntry 9 }

--
-- Subscriber Provisioning Parameters
--
subscriberTable OBJECT-TYPE
    SYNTAX SEQUENCE OF SubscriberEntry
    MAX-ACCESS not-accessible
    STATUS current
    DESCRIPTION
        "The subscriber table contains configuration information per
        subscriber line. Non-assigned entries are identified by NULL
        string for the subscriber name. It contains provisionable
        information such as subscriber name, line rate and subscriber
        line state..

        The subscriber provisioning request may fail, if the targeted
        subscriber line is under test.

        Changes to the subscriber information are temporary until user
        actually requests save operation through systemSaveCnfg.  Only
        at that point system writes information in the NVRAM storage and
        information becomes permanent."
::= { c62Subscriber 1 }

subscriberEntry OBJECT-TYPE
    SYNTAX SubscriberEntry
    MAX-ACCESS not-accessible
    STATUS current
    DESCRIPTION
        "The entry describes the fields being supported by the
        subscriber table."
    INDEX { slotID, portID }
::= { subscriberTable 1 }

SubscriberEntry ::=
    SEQUENCE {
        subscriberName           DisplayString,
        subscriberUpLineRate     Integer32,
        subscriberDwnLineRate    Integer32,
        subscriberLineState      InterfaceStatus,
        subscriberDMTLOSConfig   InterfaceStatus
}

subscriberName OBJECT-TYPE
    SYNTAX DisplayString (SIZE (0..24))
    MAX-ACCESS read-write
    STATUS current
    DESCRIPTION
        "The subscriber Id, free format string field. First character
        can not be a space. Set this field to NULL string to delete a
        subscriber entry from the database. The delete operation will
        also disable the affected subscriber line. The system resets all
        the subscriber information such as subscriberUpLineRate,
        subscriberDwnLineRate, and subscriberLineState to default values
        on the delete or for non assigned entries."
    DEFVAL { "DSL<slotID>/<portID>" }
::= { subscriberEntry 1 }

subscriberUpLineRate OBJECT-TYPE
    SYNTAX Integer32
    UNITS "kbps"
    MAX-ACCESS read-write
    STATUS current
    DESCRIPTION
        "Desired maximum line rate. Actual rate may be lower following
        training sequence to acquire that rate. Refer to system features
        document for valid range. When this value is set to -1, system
        automatically adapts to maximum available rate. Following are
        the possible rates in kbps the CAP card:
           1088, 952, 816, 680, 544, 408, 272 and 91.
        For the DMT card, the rates range from 64 Kbps to 1024 Kbps in
        increments of 32 Kbps."
::= { subscriberEntry 2 }

subscriberDwnLineRate OBJECT-TYPE
    SYNTAX Integer32
    UNITS "kbps"
    MAX-ACCESS read-write
    STATUS current
    DESCRIPTION
        "Desired maximum line rate. Actual rate may be lower following
        training sequence to acquire that rate. Refer to system features
        document for valid range. When this value is set to -1, system
        automatically adapts to maximum possible rate. Following are the
        possible rates in kbps for the CAP card:
           7168, 6272, 4480, 2688, 2560, 2240, 1920, 1600, 1280, 960 and
           640.
        For the DMT card, the rates range from 64 Kbps to 8168 Kbps in
        increments of 32 Kbps."
::= { subscriberEntry 3 }

subscriberLineState OBJECT-TYPE
    SYNTAX InterfaceStatus
    MAX-ACCESS read-write
    STATUS current
    DESCRIPTION
        "This parameter reflects current state of the subscriber
        line. It allows targeted subscriber line to be enabled or
        disabled. Disabling the line cuts off services to the affected
        subscriber. All the empty lines are disabled by the system. User
        deletion, by setting subscriberName to NULL, also results in
        disabling of the line."
    DEFVAL { disabled }
::= { subscriberEntry 4 }

subscriberDMTLOSConfig OBJECT-TYPE
    SYNTAX InterfaceStatus
    MAX-ACCESS read-write
    STATUS current
    DESCRIPTION
        "This value determines whether or not the LOS condition on the
        subscriber line generates a minor alarm.  By default, this value
        is set to disabled which means that an alarm is not generated when
        LOS is detected on the subscriber line."
    DEFVAL { disabled }
::= { subscriberEntry 5 }

-- Conformance

ciscoC6200MIBConformance  OBJECT IDENTIFIER ::= { cisco6200MIB 2 }
ciscoC6200MIBCompliances  OBJECT IDENTIFIER ::= { ciscoC6200MIBConformance 1 }
ciscoC6200MIBGroups       OBJECT IDENTIFIER ::= { ciscoC6200MIBConformance 2 }

-- Compliance

ciscoC6200MIBCompliance MODULE-COMPLIANCE
	STATUS obsolete -- superceded by ciscoC6200MIBCompliance2
	DESCRIPTION
		"The compliance statement for entities which implement
		the Cisco C6200 MIB. This device-specific MIB will be
		implemented only by members of the C6200 product line."
	MODULE	-- this module
		MANDATORY-GROUPS {
                        ciscoC6200SystemGroup,
                        ciscoC6200SlotGroup,
                        ciscoC6200oCIGroup,
                        ciscoC6200oCIPerfGroup,
                        ciscoC6200lineGroup,
                        ciscoC6200lineTestGroup,
                        ciscoC6200linePerfGroup,
                        ciscoC6200subscriberGroup
}
	::= { ciscoC6200MIBCompliances 1 }

ciscoC6200MIBCompliance2 MODULE-COMPLIANCE
	STATUS current
	DESCRIPTION
		"The compliance statement for entities which implement
		the Cisco C6200 MIB. This device-specific MIB will be
		implemented only by members of the C6200 product line.
                This compliance takes effect from IOS Release 11.3(1)DA3."
	MODULE	-- this module
		MANDATORY-GROUPS {
                        ciscoC6200SystemGroup2,
                        ciscoC6200SlotGroup2,
                        ciscoC6200oCIGroup2,
                        ciscoC6200oCIPerfGroup2,
                        ciscoC6200lineGroup2,
                        ciscoC6200lineTestGroup2,
                        ciscoC6200linePerfGroup2,
                        ciscoC6200subscriberGroup2
}
	::= { ciscoC6200MIBCompliances 2 }

-- Units of Conformance

ciscoC6200SystemGroup OBJECT-GROUP
	OBJECTS {
                systemType,
                systemAlarmLevel,
                systemAlarmLevelChngCounter,
                systemReset,
                systemSaveCnfg,
                systemProvChngCounter,
                systemHClockAlarmLevel,
                systemFanAlarmLevel,
                systemTemperatureAlarmLevel,
                systemACO
	}
	STATUS obsolete -- superceded by ciscoC6200SystemGroup2
	DESCRIPTION
		"System-level information for a C6200 device."
	::= { ciscoC6200MIBGroups 1 }

ciscoC6200SlotGroup OBJECT-GROUP
	OBJECTS {
                slotType,
                slotStatus,
                slotSwVersion,
                slotAlarmLevelChngCounter,
                slotCnfType,
                slotSubscriberChngCounter,
                slotAlarmLevel
	}
	STATUS obsolete -- superceded by ciscoC6200SlotGroup2
	DESCRIPTION
		"Slot-level information for a C6200 device."
	::= { ciscoC6200MIBGroups 2 }

ciscoC6200oCIGroup OBJECT-GROUP
	OBJECTS {
                oCIAlarmLevel,
                oCIEQF,
                oCILOS,
                oCILOF,
                oCILAIS,
                oCILOP,
                oCIPAIS,
                oCISLM,
                oCILRFI,
                oCIPRFI,
                oCILOST,
                oCILOCD,
                oCILoopMode
	}
	STATUS obsolete -- superceded by ciscoC6200oCIGroup2
	DESCRIPTION
		"NTC information for a C6200 device."
	::= { ciscoC6200MIBGroups 3 }

ciscoC6200oCIPerfGroup OBJECT-GROUP
	OBJECTS {
                oCPTxCellCount,
                oCPRxCellCount,
                oCPHecErrCount
	}
	STATUS obsolete -- superceded by ciscoC6200oCIPerfGroup2
	DESCRIPTION
		"NTC performance information for a C6200 device."
	::= { ciscoC6200MIBGroups 4 }

ciscoC6200lineGroup OBJECT-GROUP
	OBJECTS {
        	lineAlarmLevel,
        	lineDwnSNRMargin,
        	lineDwnLOCD,
        	lineDwnErrSecs,
        	lineDwnLineRate,
        	lineUpSNRMargin,
        	lineUpLOCD,
        	lineUpErrSecs,
        	lineUpLineRate,
        	lineRateAlarm,
        	lineMode
	}
	STATUS obsolete -- superceded by ciscoC6200lineGroup2
	DESCRIPTION
		"Line-level information for a C6200 device."
	::= { ciscoC6200MIBGroups 5 }

ciscoC6200linePerfGroup OBJECT-GROUP
	OBJECTS {
                lineTxCellCount,
                lineRxCellCount,
                lineHecErrCount
	}
	STATUS obsolete -- superceded by ciscoC6200linePerfGroup2
	DESCRIPTION
		"Line-level performance information for a C6200 device."
	::= { ciscoC6200MIBGroups 6 }

ciscoC6200lineTestGroup OBJECT-GROUP
	OBJECTS {
                lineTestTrigger,
                lineTestType,
                lineTestTimeIntvl,
                lineTestStatus,
                lineTestDwnBitErrRate,
                lineTestUpBitErrRate,
                lineTestStartTime,
                lineTestCmplTime,
                lineTestBitErrRateLimit
	}
	STATUS obsolete -- superceded by ciscoC6200lineTestGroup2
	DESCRIPTION
		"Line-level test information for a C6200 device."
	::= { ciscoC6200MIBGroups 7 }

ciscoC6200subscriberGroup OBJECT-GROUP
	OBJECTS {
                subscriberName,
                subscriberUpLineRate,
                subscriberDwnLineRate,
                subscriberLineState
	}
	STATUS obsolete -- superceded by ciscoC6200subscriberGroup2
	DESCRIPTION
		"Subscriber-level information for a C6200 device."
	::= { ciscoC6200MIBGroups 8 }

ciscoC6200SystemGroup2 OBJECT-GROUP
	OBJECTS {
                systemType,
                systemAlarmLevel,
                systemAlarmLevelChngCounter,
                systemReset,
                systemSaveCnfg,
                systemProvChngCounter,
                systemHClockAlarmLevel,
                systemFanAlarmLevel,
                systemTemperatureAlarmLevel,
                systemACO
	}
	STATUS current
	DESCRIPTION
		"System-level information for a C6200 device."
	::= { ciscoC6200MIBGroups 9 }

ciscoC6200SlotGroup2 OBJECT-GROUP
	OBJECTS {
                slotType,
                slotStatus,
                slotSwVersion,
                slotAlarmLevelChngCounter,
                slotCnfType,
                slotSubscriberChngCounter,
                slotAlarmLevel
	}
	STATUS current
	DESCRIPTION
		"Slot-level information for a C6200 device."
	::= { ciscoC6200MIBGroups 10 }

ciscoC6200oCIGroup2 OBJECT-GROUP
	OBJECTS {
                oCIAlarmLevel,
                oCIEQF,
                oCILOS,
                oCILOF,
                oCILAIS,
                oCILOP,
                oCIPAIS,
                oCISLM,
                oCILRFI,
                oCIPRFI,
                oCILOST,
                oCILOCD,
                oCILoopMode
	}
	STATUS current
	DESCRIPTION
		"NTC information for a C6200 device."
	::= { ciscoC6200MIBGroups 11 }

ciscoC6200oCIPerfGroup2 OBJECT-GROUP
	OBJECTS {
                oCPTxCellCount,
                oCPRxCellCount,
                oCPHecErrCount
	}
	STATUS current
	DESCRIPTION
		"NTC performance information for a C6200 device."
	::= { ciscoC6200MIBGroups 12 }

ciscoC6200lineGroup2 OBJECT-GROUP
	OBJECTS {
        	lineAlarmLevel,
        	lineDwnSNRMargin,
        	lineDwnErrSecs,
        	lineDwnLineRate,
        	lineUpSNRMargin,
        	lineUpLOCD,
        	lineUpErrSecs,
        	lineUpLineRate,
        	lineRateAlarm,
        	lineMode,
                lineDMTDwnAttenuation,
                lineDMTUpAttenuation,
                lineDMTDwnLPR,
                lineDMTUpLOS,
                lineDMTUpLOF,
                lineDMTLoopback
	}
	STATUS current
	DESCRIPTION
		"Line-level information for a C6200 device."
	::= { ciscoC6200MIBGroups 13 }

ciscoC6200linePerfGroup2 OBJECT-GROUP
	OBJECTS {
                lineTxCellCount,
                lineRxCellCount,
                lineHecErrCount,
                lineDMTDwnFECCount,
                lineDMTUpFECCount,
                lineDMTDwnCRCCount,
                lineDMTUpCRCCount,
                lineDMTDwnLOSCount,
                lineDMTUpLOSCount,
                lineDMTDwnSEFCount,
                lineDMTUpRDICount
	}
	STATUS current
	DESCRIPTION
		"Line-level performance information for a C6200 device."
	::= { ciscoC6200MIBGroups 14 }

ciscoC6200lineTestGroup2 OBJECT-GROUP
	OBJECTS {
                lineTestTrigger,
                lineTestType,
                lineTestTimeIntvl,
                lineTestStatus,
                lineTestDwnBitErrRate,
                lineTestUpBitErrRate,
                lineTestStartTime,
                lineTestCmplTime,
                lineTestBitErrRateLimit
	}
	STATUS current
	DESCRIPTION
		"Line-level test information for a C6200 device."
	::= { ciscoC6200MIBGroups 15 }

ciscoC6200subscriberGroup2 OBJECT-GROUP
	OBJECTS {
                subscriberName,
                subscriberUpLineRate,
                subscriberDwnLineRate,
                subscriberLineState,
                subscriberDMTLOSConfig
	}
	STATUS current
	DESCRIPTION
		"Subscriber-level information for a C6200 device."
	::= { ciscoC6200MIBGroups 16 }

END
