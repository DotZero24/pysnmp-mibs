-- *****************************************************************
-- LLDP-MIB:  Cisco private MIB
-- ****************************************************************

CIE1000-LLDP-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    cie1000SwitchMgmt FROM CISCO-IE1000-MIB
    CIE1000DisplayString FROM CIE1000-TC
    CIE1000Integer64 FROM CIE1000-TC
    CIE1000InterfaceIndex FROM CIE1000-TC
    CIE1000RowEditorState FROM CIE1000-TC
    CIE1000Unsigned16 FROM CIE1000-TC
    CIE1000Unsigned64 FROM CIE1000-TC
    CIE1000Unsigned8 FROM CIE1000-TC
    Integer32 FROM SNMPv2-SMI
    Unsigned32 FROM SNMPv2-SMI
    TruthValue FROM SNMPv2-TC
    ;

cie1000LldpMib MODULE-IDENTITY
    LAST-UPDATED "201604070000Z"
    ORGANIZATION
        "Cisco Systems, Inc."
    CONTACT-INFO
        "Cisco Systems
	 Customer Service

	 Postal: 170 West Tasman Drive
	 San Jose, CA  95134
	 USA

	 Tel: +1 800 553-NETS

	 E-mail: cs-snmp@cisco.com"
    DESCRIPTION
        "This is a private version of the LLDP MIB"
    REVISION    "201604070000Z"
    DESCRIPTION
        "Add SnmpNotificationEna to lldpConfig table"
    REVISION    "201407010000Z"
    DESCRIPTION
        "Initial version"
    ::= { cie1000SwitchMgmt 34 }


CIE1000lldpAdminState ::= TEXTUAL-CONVENTION
    STATUS      current
    DESCRIPTION
        "This enumerations the admin state."
    SYNTAX      INTEGER { disabled(0), txAndRx(1), txOnly(2),
                          rxOnly(3) }

CIE1000lldpmedAltitudeType ::= TEXTUAL-CONVENTION
    STATUS      current
    DESCRIPTION
        "This enumerations the altitude type."
    SYNTAX      INTEGER { meters(1), floors(2) }

CIE1000lldpmedCivicAddressType ::= TEXTUAL-CONVENTION
    STATUS      current
    DESCRIPTION
        "This enumerations the civic address type."
    SYNTAX      INTEGER { state(1), county(2), city(3), district(4),
                          block(5), street(6),
                          leadingStreetDirection(16),
                          trailingStreetSuffix(17), streetSuffix(18),
                          houseNo(19), houseNoSuffix(20),
                          landmark(21), additionalInfo(22), name(23),
                          zipCode(24), building(25), apartment(26),
                          floor(27), roomNumber(28), placeType(29),
                          postalCommunityName(30), poBox(31),
                          additionalCode(32) }

CIE1000lldpmedDatumType ::= TEXTUAL-CONVENTION
    STATUS      current
    DESCRIPTION
        "This enumerations the datum (geodetic system)."
    SYNTAX      INTEGER { wgs84(1), nad83navd88(2), nad83mllw(3) }

CIE1000lldpmedDeviceType ::= TEXTUAL-CONVENTION
    STATUS      current
    DESCRIPTION
        "This enumerations the device type that the device shall operate as."
    SYNTAX      INTEGER { connectivity(0), endpoint(1) }

CIE1000lldpmedRemoteDeviceType ::= TEXTUAL-CONVENTION
    STATUS      current
    DESCRIPTION
        "This enumerations the remote neighbor's device type."
    SYNTAX      INTEGER { notDefined(0), endpointClassI(1),
                          endpointClassII(2), endpointClassIII(3),
                          networkConnectivity(4), reserved(5) }

CIE1000lldpmedRemoteNetworkPolicyApplicationType ::= TEXTUAL-CONVENTION
    STATUS      current
    DESCRIPTION
        "This enumerations the remote neighbor's network policy's application
         type."
    SYNTAX      INTEGER { voice(1), voiceSignaling(2), guestVoice(3),
                          guestVoiceSignaling(4), softphoneVoice(5),
                          videoConferencing(6), streamingVideo(7),
                          videoSignaling(8) }

cie1000LldpMibObjects OBJECT IDENTIFIER
    ::= { cie1000LldpMib 1 }

cie1000LldpConfig OBJECT IDENTIFIER
    ::= { cie1000LldpMibObjects 2 }

cie1000LldpConfigGlobal OBJECT IDENTIFIER
    ::= { cie1000LldpConfig 1 }

cie1000LldpConfigGlobalReInitDelay OBJECT-TYPE
    SYNTAX      CIE1000Unsigned16
    MAX-ACCESS  read-write
    STATUS      current
    DESCRIPTION
        "Set the LLDP tx reinitialization delay in seconds. Valid range 1-10.

         When a port is disabled, LLDP is disabled or the switch is rebooted, a
         LLDP shutdown frame is transmitted to the neighboring units, signaling
         that the LLDP information isn't valid anymore.

         Tx reinitialization delay controls the amount of seconds between the
         shutdown frame and a new LLDP initialization."
    ::= { cie1000LldpConfigGlobal 1 }

cie1000LldpConfigGlobalMsgTxHold OBJECT-TYPE
    SYNTAX      CIE1000Unsigned16
    MAX-ACCESS  read-write
    STATUS      current
    DESCRIPTION
        "Set the LLDP tx hold times . Valid range 2-10.

         Each LLDP frame contains information about how long time the
         information in the LLDP frame shall be considered valid. The LLDP
         information valid period is set to tx hold times multiplied by tx
         interval seconds."
    ::= { cie1000LldpConfigGlobal 2 }

cie1000LldpConfigGlobalMsgTxInterval OBJECT-TYPE
    SYNTAX      CIE1000Unsigned16
    MAX-ACCESS  read-write
    STATUS      current
    DESCRIPTION
        "Set the LLDP tx interval in seconds.

         The switch periodically transmits LLDP frames to its neighbors for
         having the network discovery information up-to-date. The interval
         between each LLDP frame is determined by the tx Interval value.



         Valid range 5-32768 seconds."
    ::= { cie1000LldpConfigGlobal 3 }

cie1000LldpConfigGlobalTxDelay OBJECT-TYPE
    SYNTAX      CIE1000Unsigned16
    MAX-ACCESS  read-write
    STATUS      current
    DESCRIPTION
        "Set the LLDP tx delay in seconds. Valid range 1-8192.

         If some configuration is changed (e.g. the IP address) a new LLDP frame
         is transmitted, but the time between the LLDP frames will always be at
         least the value of tx delay seconds.

         Note: tx Delay cannot be larger than 1/4 of the tx interval."
    ::= { cie1000LldpConfigGlobal 4 }

cie1000LldpConfigTable OBJECT-TYPE
    SYNTAX      SEQUENCE OF CIE1000LldpConfigEntry
    MAX-ACCESS  not-accessible
    STATUS      current
    DESCRIPTION
        "This is a table to configure LLDP configurations for a specific
         interface."
    ::= { cie1000LldpConfig 2 }

cie1000LldpConfigEntry OBJECT-TYPE
    SYNTAX      CIE1000LldpConfigEntry
    MAX-ACCESS  not-accessible
    STATUS      current
    DESCRIPTION
        "Each interface has a set of control parameters"
    INDEX       { cie1000LldpConfigIfIndex }
    ::= { cie1000LldpConfigTable 1 }

CIE1000LldpConfigEntry ::= SEQUENCE {
    cie1000LldpConfigIfIndex              CIE1000InterfaceIndex,
    cie1000LldpConfigAdminState           CIE1000lldpAdminState,
    cie1000LldpConfigCdpAware             TruthValue,
    cie1000LldpConfigOptionalTlvs         CIE1000Unsigned8,
    cie1000LldpConfigSnmpNotificationEna  TruthValue
}

cie1000LldpConfigIfIndex OBJECT-TYPE
    SYNTAX      CIE1000InterfaceIndex
    MAX-ACCESS  accessible-for-notify
    STATUS      current
    DESCRIPTION
        "Logical interface number index."
    ::= { cie1000LldpConfigEntry 1 }

cie1000LldpConfigAdminState OBJECT-TYPE
    SYNTAX      CIE1000lldpAdminState
    MAX-ACCESS  read-write
    STATUS      current
    DESCRIPTION
        "Sets the LLDP admin state for the interface."
    ::= { cie1000LldpConfigEntry 3 }

cie1000LldpConfigCdpAware OBJECT-TYPE
    SYNTAX      TruthValue
    MAX-ACCESS  read-write
    STATUS      current
    DESCRIPTION
        "Enables/disables CDP awareness for the interface.

         CDP is Cisco's equivalent to LLDP.



         The CDP operation is restricted to decoding incoming CDP frames (The
         switch doesn't transmit CDP frames). CDP frames are only decoded if
         LLDP on the port is enabled.



         Only CDP TLVs that can be mapped to a corresponding field in the LLDP
         neighbors' table are decoded. All other TLVs are discarded
         (Unrecognized CDP TLVs and discarded CDP frames are not shown in the
         LLDP statistics.).

         CDP TLVs are mapped onto LLDP neighbors' table as shown below.

         CDP TLV 'Device ID' is mapped to the LLDP 'Chassis ID' field.

         CDP TLV 'Address' is mapped to the LLDP 'Management Address' field. The
         CDP address TLV can contain multiple addresses, but only the first
         address is shown in the LLDP neighbors table.

         CDP TLV 'Port ID' is mapped to the LLDP 'Port ID' field.

         CDP TLV 'Version and Platform' is mapped to the LLDP 'System
         Description' field.

         Both the CDP and LLDP support 'system capabilities', but the CDP
         capabilities cover capabilities that are not part of the LLDP. These
         capabilities are shown as 'others' in the LLDP neighbors' table.



         If all ports have CDP awareness disabled the switch forwards CDP frames
         received from neighbor devices. If at least one port has CDP awareness
         enabled all CDP frames are terminated by the switch.



         Note: When CDP awareness on a port is disabled the CDP information
         isn't removed immediately, but gets removed when the hold time is
         exceeded."
    ::= { cie1000LldpConfigEntry 4 }

cie1000LldpConfigOptionalTlvs OBJECT-TYPE
    SYNTAX      CIE1000Unsigned8
    MAX-ACCESS  read-write
    STATUS      current
    DESCRIPTION
        "Enables/Disables the LLDP optional TLVs. Bit mask, where setting the
         bit to 1 means enable transmission of the corresponding TLV.

         Bit 0 represents Port Description TLV.

         Bit 1 represents System Name TLV.

         Bit 2 represents System Description.

         Bit 3 represents System Capabilities TLV.

         Bit 4 represents Management Address TLV."
    ::= { cie1000LldpConfigEntry 5 }

cie1000LldpConfigSnmpNotificationEna OBJECT-TYPE
    SYNTAX      TruthValue
    MAX-ACCESS  read-write
    STATUS      current
    DESCRIPTION
        "Enable/disable of SNMP Trap notification."
    ::= { cie1000LldpConfigEntry 6 }

cie1000LldpConfigMed OBJECT IDENTIFIER
    ::= { cie1000LldpConfig 3 }

cie1000LldpConfigMedTable OBJECT-TYPE
    SYNTAX      SEQUENCE OF CIE1000LldpConfigMedEntry
    MAX-ACCESS  not-accessible
    STATUS      current
    DESCRIPTION
        "This is a table to configure LLDP MEDIA configurations for a specific
         interface."
    ::= { cie1000LldpConfigMed 1 }

cie1000LldpConfigMedEntry OBJECT-TYPE
    SYNTAX      CIE1000LldpConfigMedEntry
    MAX-ACCESS  not-accessible
    STATUS      current
    DESCRIPTION
        "Each interface has a set of control parameters"
    INDEX       { cie1000LldpConfigMedIfIndex }
    ::= { cie1000LldpConfigMedTable 1 }

CIE1000LldpConfigMedEntry ::= SEQUENCE {
    cie1000LldpConfigMedIfIndex       CIE1000InterfaceIndex,
    cie1000LldpConfigMedOptionalTlvs  CIE1000Unsigned8,
    cie1000LldpConfigMedDeviceType    CIE1000lldpmedDeviceType
}

cie1000LldpConfigMedIfIndex OBJECT-TYPE
    SYNTAX      CIE1000InterfaceIndex
    MAX-ACCESS  accessible-for-notify
    STATUS      current
    DESCRIPTION
        "Logical interface number index."
    ::= { cie1000LldpConfigMedEntry 1 }

cie1000LldpConfigMedOptionalTlvs OBJECT-TYPE
    SYNTAX      CIE1000Unsigned8
    MAX-ACCESS  read-write
    STATUS      current
    DESCRIPTION
        "Enables/Disables the LLDP optional TLVs. Bit mask, where setting the
         bit to 1 means

         enable transmission of the corresponding optional TLV.

         Bit 0 represents the capabilities TLV.

         Bit 1 represents the network Policy TLV.

         Bit 2 represents the location TLV.

         Bit 3 represents the PoE TLV."
    ::= { cie1000LldpConfigMedEntry 3 }

cie1000LldpConfigMedDeviceType OBJECT-TYPE
    SYNTAX      CIE1000lldpmedDeviceType
    MAX-ACCESS  read-write
    STATUS      current
    DESCRIPTION
        "Setting device type to configure the mode the device shall operate as."
    ::= { cie1000LldpConfigMedEntry 4 }

cie1000LldpConfigMedPolicyTable OBJECT-TYPE
    SYNTAX      SEQUENCE OF CIE1000LldpConfigMedPolicyEntry
    MAX-ACCESS  not-accessible
    STATUS      current
    DESCRIPTION
        "This is a table to configure LLDP MED Policies for the device."
    ::= { cie1000LldpConfigMed 2 }

cie1000LldpConfigMedPolicyEntry OBJECT-TYPE
    SYNTAX      CIE1000LldpConfigMedPolicyEntry
    MAX-ACCESS  not-accessible
    STATUS      current
    DESCRIPTION
        "Network Policy Discovery enables the efficient discovery and diagnosis
         of mismatch issues with the VLAN configuration, along with the
         associated Layer 2 and Layer 3 attributes, which apply for a set of
         specific protocol applications on that port. Improper network policy
         configurations are a very significant issue in VoIP environments that
         frequently result in voice quality degradation or loss of service.
         Policies are only intended for use with applications that have specific
         'real-time' network policy requirements, such as interactive voice
         and/or video services."
    INDEX       { cie1000LldpConfigMedPolicyLldpmedPolicy }
    ::= { cie1000LldpConfigMedPolicyTable 1 }

CIE1000LldpConfigMedPolicyEntry ::= SEQUENCE {
    cie1000LldpConfigMedPolicyLldpmedPolicy    Integer32,
    cie1000LldpConfigMedPolicyApplicationType  CIE1000lldpmedRemoteNetworkPolicyApplicationType,
    cie1000LldpConfigMedPolicyTagged           TruthValue,
    cie1000LldpConfigMedPolicyVlanId           CIE1000Unsigned16,
    cie1000LldpConfigMedPolicyL2Priority       CIE1000Unsigned8,
    cie1000LldpConfigMedPolicyDscp             CIE1000Unsigned8,
    cie1000LldpConfigMedPolicyAction           CIE1000RowEditorState
}

cie1000LldpConfigMedPolicyLldpmedPolicy OBJECT-TYPE
    SYNTAX      Integer32 (0..31)
    MAX-ACCESS  accessible-for-notify
    STATUS      current
    DESCRIPTION
        "Policy index."
    ::= { cie1000LldpConfigMedPolicyEntry 1 }

cie1000LldpConfigMedPolicyApplicationType OBJECT-TYPE
    SYNTAX      CIE1000lldpmedRemoteNetworkPolicyApplicationType
    MAX-ACCESS  read-write
    STATUS      current
    DESCRIPTION
        "The LLDP policy application type."
    ::= { cie1000LldpConfigMedPolicyEntry 3 }

cie1000LldpConfigMedPolicyTagged OBJECT-TYPE
    SYNTAX      TruthValue
    MAX-ACCESS  read-write
    STATUS      current
    DESCRIPTION
        "The LLDP policy tagged flag. Defines if LLDP policy uses tagged VLAN."
    ::= { cie1000LldpConfigMedPolicyEntry 4 }

cie1000LldpConfigMedPolicyVlanId OBJECT-TYPE
    SYNTAX      CIE1000Unsigned16 (1..4095)
    MAX-ACCESS  read-write
    STATUS      current
    DESCRIPTION
        "The LLDP policy VLAN ID. Only valid when policy 'Tagged' is TRUE"
    ::= { cie1000LldpConfigMedPolicyEntry 5 }

cie1000LldpConfigMedPolicyL2Priority OBJECT-TYPE
    SYNTAX      CIE1000Unsigned8 (0..7)
    MAX-ACCESS  read-write
    STATUS      current
    DESCRIPTION
        "The LLDP policy L2 priority."
    ::= { cie1000LldpConfigMedPolicyEntry 6 }

cie1000LldpConfigMedPolicyDscp OBJECT-TYPE
    SYNTAX      CIE1000Unsigned8 (0..63)
    MAX-ACCESS  read-write
    STATUS      current
    DESCRIPTION
        "The LLDP policy DSCP."
    ::= { cie1000LldpConfigMedPolicyEntry 7 }

cie1000LldpConfigMedPolicyAction OBJECT-TYPE
    SYNTAX      CIE1000RowEditorState
    MAX-ACCESS  read-write
    STATUS      current
    DESCRIPTION
        "Action"
    ::= { cie1000LldpConfigMedPolicyEntry 100 }

cie1000LldpConfigMedPolicyListTable OBJECT-TYPE
    SYNTAX      SEQUENCE OF CIE1000LldpConfigMedPolicyListEntry
    MAX-ACCESS  not-accessible
    STATUS      current
    DESCRIPTION
        "Each interface can be mapped to multiple policies. Set to TRUE in order
         to enable the corresponding policy to be transmitted at the interface.
         It is a requirement that the policy is defined."
    ::= { cie1000LldpConfigMed 3 }

cie1000LldpConfigMedPolicyListEntry OBJECT-TYPE
    SYNTAX      CIE1000LldpConfigMedPolicyListEntry
    MAX-ACCESS  not-accessible
    STATUS      current
    DESCRIPTION
        "Each location information has a control parameter"
    INDEX       { cie1000LldpConfigMedPolicyListIfIndex,
                  cie1000LldpConfigMedPolicyListLldpmedPolicy }
    ::= { cie1000LldpConfigMedPolicyListTable 1 }

CIE1000LldpConfigMedPolicyListEntry ::= SEQUENCE {
    cie1000LldpConfigMedPolicyListIfIndex              CIE1000InterfaceIndex,
    cie1000LldpConfigMedPolicyListLldpmedPolicy        Integer32,
    cie1000LldpConfigMedPolicyListLldpmedPoliciesList  TruthValue
}

cie1000LldpConfigMedPolicyListIfIndex OBJECT-TYPE
    SYNTAX      CIE1000InterfaceIndex
    MAX-ACCESS  accessible-for-notify
    STATUS      current
    DESCRIPTION
        "Logical interface number index."
    ::= { cie1000LldpConfigMedPolicyListEntry 1 }

cie1000LldpConfigMedPolicyListLldpmedPolicy OBJECT-TYPE
    SYNTAX      Integer32 (0..31)
    MAX-ACCESS  accessible-for-notify
    STATUS      current
    DESCRIPTION
        "Policy index."
    ::= { cie1000LldpConfigMedPolicyListEntry 3 }

cie1000LldpConfigMedPolicyListLldpmedPoliciesList OBJECT-TYPE
    SYNTAX      TruthValue
    MAX-ACCESS  read-write
    STATUS      current
    DESCRIPTION
        "Set to TRUE assign the corresponding policy index to the interface."
    ::= { cie1000LldpConfigMedPolicyListEntry 4 }

cie1000LldpConfigMedGlobal OBJECT IDENTIFIER
    ::= { cie1000LldpConfigMed 4 }

cie1000LldpConfigMedGlobalFastRepeatCount OBJECT-TYPE
    SYNTAX      CIE1000Unsigned8 (1..10)
    MAX-ACCESS  read-write
    STATUS      current
    DESCRIPTION
        "Number of times to repeat LLDP frame transmission at fast start

         Rapid startup and Emergency Call Service Location Identification
         Discovery of endpoints is a critically important aspect of VoIP systems
         in general. In addition, it is best to advertise only those pieces of
         information which are specifically relevant to particular endpoint
         types (for example only advertise the voice network policy to permitted
         voice-capable devices), both in order to conserve the limited LLDPU
         space and to reduce security and system integrity issues that can come
         with inappropriate knowledge of the network policy.

         With this in mind LLDP-MED defines an LLDP-MED Fast Start interaction
         between the protocol and the application layers on top of the protocol,
         in order to achieve these related properties. Initially, a Network
         Connectivity Device will only transmit LLDP TLVs in an LLDPDU. Only
         after an LLDP-MED Endpoint Device is detected, will an LLDP-MED capable
         Network Connectivity Device start to advertise LLDP-MED TLVs in
         outgoing LLDPDUs on the associated port. The LLDP-MED application will
         temporarily speed up the transmission of the LLDPDU to start within a
         second, when a new LLDP-MED neighbor has been detected in order share
         LLDP-MED information as fast as possible to new neighbors.

         Because there is a risk of an LLDP frame being lost during transmission
         between neighbors, it is recommended to repeat the fast start
         transmission multiple times to increase the possibility of the
         neighbors receiving the LLDP frame. With fast start repeat count it is
         possible to specify the number of times the fast start transmission
         would be repeated. The recommended value is 4 times, given that 4 LLDP
         frames with a 1 second interval will be transmitted, when an LLDP frame
         with new information is received.

         It should be noted that LLDP-MED and the LLDP-MED Fast Start mechanism
         is only intended to run on links between LLDP-MED Network Connectivity
         Devices and Endpoint Devices, and as such does not apply to links
         between LAN infrastructure elements, including Network Connectivity
         Devices, or other types of links."
    ::= { cie1000LldpConfigMedGlobal 1 }

cie1000LldpConfigMedGlobalLatitude OBJECT-TYPE
    SYNTAX      CIE1000Integer64
    MAX-ACCESS  read-write
    STATUS      current
    DESCRIPTION
        "Latitude degrees in 2s-complement as specified in RFC 3825. Positive
         numbers are north of the equator and negative numbers are south of the
         equator."
    ::= { cie1000LldpConfigMedGlobal 2 }

cie1000LldpConfigMedGlobalLongitude OBJECT-TYPE
    SYNTAX      CIE1000Integer64
    MAX-ACCESS  read-write
    STATUS      current
    DESCRIPTION
        "Longitude degrees in 2s-complement as specified in RFC 3825. Positive
         values are East of the prime meridian and negative numbers are West of
         the prime meridian."
    ::= { cie1000LldpConfigMedGlobal 3 }

cie1000LldpConfigMedGlobalAltitudeType OBJECT-TYPE
    SYNTAX      CIE1000lldpmedAltitudeType
    MAX-ACCESS  read-write
    STATUS      current
    DESCRIPTION
        "Setting altitude type

         Possible to select between two altitude types (floors or meters).
         Meters are representing meters of altitude defined by the vertical
         datum specified. Floors are representing altitude in a form more
         relevant in buildings which have different floor-to-floor dimensions.
         An altitude = 0.0 is meaningful even outside a building, and represents
         ground level at the given latitude and longitude. Inside a building,
         0.0 represents the floor level associated with ground level at the main
         entrance."
    ::= { cie1000LldpConfigMedGlobal 4 }

cie1000LldpConfigMedGlobalAltitude OBJECT-TYPE
    SYNTAX      Integer32
    MAX-ACCESS  read-write
    STATUS      current
    DESCRIPTION
        "Altitude value in 2s-complement as specified in RFC 3825"
    ::= { cie1000LldpConfigMedGlobal 5 }

cie1000LldpConfigMedGlobalElinAddr OBJECT-TYPE
    SYNTAX      CIE1000DisplayString (SIZE(0..25))
    MAX-ACCESS  read-write
    STATUS      current
    DESCRIPTION
        "Emergency Call Service ELIN identifier data format is defined to carry
         the ELIN identifier as used during emergency call setup to a
         traditional CAMA or ISDN trunk-based PSAP. This format consists of a
         numerical digit string, corresponding to the ELIN to be used for
         emergency calling. Maximum number of octets are 25."
    ::= { cie1000LldpConfigMedGlobal 6 }

cie1000LldpConfigMedGlobalDatum OBJECT-TYPE
    SYNTAX      CIE1000lldpmedDatumType
    MAX-ACCESS  read-write
    STATUS      current
    DESCRIPTION
        "Setting datum to configure the datum (geodetic system) to use.

         The Map Datum is used for the coordinates given in these options:

         WGS84: (Geographical 3D) - World Geodesic System 1984, CRS Code 4327,
         Prime Meridian Name: Greenwich.

         NAD83/NAVD88: North American Datum 1983, CRS Code 4269, Prime Meridian
         Name: Greenwich;The associated vertical datum is the North American
         Vertical Datum of 1988 (NAVD88).This datum pair is to be used when
         referencing locations on land, not near tidal water(which would use
         Datum = NAD83/MLLW).

         NAD83/MLLW: North American Datum 1983, CRS Code 4269, Prime Meridian
         Name: Greenwich; The associated vertical datum is Mean Lower Low Water
         (MLLW). This datum pair is to be used when referencing locations on
         water/sea/ocean."
    ::= { cie1000LldpConfigMedGlobal 7 }

cie1000LldpConfigMedGlobalCountryCode OBJECT-TYPE
    SYNTAX      CIE1000DisplayString (SIZE(0..2))
    MAX-ACCESS  read-write
    STATUS      current
    DESCRIPTION
        "The two-letter ISO 3166 country code in capital ASCII letters -
         Example: DK, DE or US."
    ::= { cie1000LldpConfigMedGlobal 8 }

cie1000LldpConfigMedLocationInfTable OBJECT-TYPE
    SYNTAX      SEQUENCE OF CIE1000LldpConfigMedLocationInfEntry
    MAX-ACCESS  not-accessible
    STATUS      current
    DESCRIPTION
        "The civic address location information. Each civic address can contain
         up to 250 characters, but the total amount of characters for the
         combined civic address locations must not exceed 250 bytes. Note: If an
         civic address location is non-empty it uses the amount of characters
         plus addition two characters. This is described in TIA1057, Section
         10.2.4.3.2."
    ::= { cie1000LldpConfigMed 5 }

cie1000LldpConfigMedLocationInfEntry OBJECT-TYPE
    SYNTAX      CIE1000LldpConfigMedLocationInfEntry
    MAX-ACCESS  not-accessible
    STATUS      current
    DESCRIPTION
        "Each civic address type as defined in TIA1057, Section 3.4 in Annex B"
    INDEX       { cie1000LldpConfigMedLocationInfLldpmedIndex }
    ::= { cie1000LldpConfigMedLocationInfTable 1 }

CIE1000LldpConfigMedLocationInfEntry ::= SEQUENCE {
    cie1000LldpConfigMedLocationInfLldpmedIndex  CIE1000lldpmedCivicAddressType,
    cie1000LldpConfigMedLocationInfCivicAddress  CIE1000DisplayString
}

cie1000LldpConfigMedLocationInfLldpmedIndex OBJECT-TYPE
    SYNTAX      CIE1000lldpmedCivicAddressType
    MAX-ACCESS  accessible-for-notify
    STATUS      current
    DESCRIPTION
        "Civic address type.

         1 - State/National subdivisions

         2 - County, parish, gun (JP), district (IN)

         3 - City, township

         4 - City division, borough, city district, ward, chou (JP)

         5 - Neighborhood, block

         6 - Street

         16 - Leading street direction

         17 - Trailing street direction

         18 - Street suffix

         19 - House number

         20 - House number suffix

         21 - Landmark or vanity address

         22 - Additional location information

         23 - Name

         24 - Postal/zip code

         25 - Building

         26 - Unit

         27 - Floor

         28 - Room

         29 - Place type

         30 - Postal

         31 - Post office

         32 - Additional code"
    ::= { cie1000LldpConfigMedLocationInfEntry 2 }

cie1000LldpConfigMedLocationInfCivicAddress OBJECT-TYPE
    SYNTAX      CIE1000DisplayString (SIZE(0..250))
    MAX-ACCESS  read-write
    STATUS      current
    DESCRIPTION
        "Civic address"
    ::= { cie1000LldpConfigMedLocationInfEntry 3 }

cie1000LldpConfigMedPolicyRowEditor OBJECT IDENTIFIER
    ::= { cie1000LldpConfigMed 6 }

cie1000LldpConfigMedPolicyRowEditorLldpmedPolicy OBJECT-TYPE
    SYNTAX      Integer32 (0..31)
    MAX-ACCESS  read-write
    STATUS      current
    DESCRIPTION
        "Policy index."
    ::= { cie1000LldpConfigMedPolicyRowEditor 1 }

cie1000LldpConfigMedPolicyRowEditorApplicationType OBJECT-TYPE
    SYNTAX      CIE1000lldpmedRemoteNetworkPolicyApplicationType
    MAX-ACCESS  read-write
    STATUS      current
    DESCRIPTION
        "The LLDP policy application type."
    ::= { cie1000LldpConfigMedPolicyRowEditor 3 }

cie1000LldpConfigMedPolicyRowEditorTagged OBJECT-TYPE
    SYNTAX      TruthValue
    MAX-ACCESS  read-write
    STATUS      current
    DESCRIPTION
        "The LLDP policy tagged flag. Defines if LLDP policy uses tagged VLAN."
    ::= { cie1000LldpConfigMedPolicyRowEditor 4 }

cie1000LldpConfigMedPolicyRowEditorVlanId OBJECT-TYPE
    SYNTAX      CIE1000Unsigned16 (1..4095)
    MAX-ACCESS  read-write
    STATUS      current
    DESCRIPTION
        "The LLDP policy VLAN ID. Only valid when policy 'Tagged' is TRUE"
    ::= { cie1000LldpConfigMedPolicyRowEditor 5 }

cie1000LldpConfigMedPolicyRowEditorL2Priority OBJECT-TYPE
    SYNTAX      CIE1000Unsigned8 (0..7)
    MAX-ACCESS  read-write
    STATUS      current
    DESCRIPTION
        "The LLDP policy L2 priority."
    ::= { cie1000LldpConfigMedPolicyRowEditor 6 }

cie1000LldpConfigMedPolicyRowEditorDscp OBJECT-TYPE
    SYNTAX      CIE1000Unsigned8 (0..63)
    MAX-ACCESS  read-write
    STATUS      current
    DESCRIPTION
        "The LLDP policy DSCP."
    ::= { cie1000LldpConfigMedPolicyRowEditor 7 }

cie1000LldpConfigMedPolicyRowEditorAction OBJECT-TYPE
    SYNTAX      CIE1000RowEditorState
    MAX-ACCESS  read-write
    STATUS      current
    DESCRIPTION
        "Action"
    ::= { cie1000LldpConfigMedPolicyRowEditor 100 }

cie1000LldpStatus OBJECT IDENTIFIER
    ::= { cie1000LldpMibObjects 3 }

cie1000LldpStatusStatistics OBJECT IDENTIFIER
    ::= { cie1000LldpStatus 1 }

cie1000LldpStatusStatisticsGlobalCounters OBJECT IDENTIFIER
    ::= { cie1000LldpStatusStatistics 1 }

cie1000LldpStatusStatisticsGlobalCountersTableInserts OBJECT-TYPE
    SYNTAX      Unsigned32
    MAX-ACCESS  read-only
    STATUS      current
    DESCRIPTION
        "Shows the number of new entries added since switch reboot."
    ::= { cie1000LldpStatusStatisticsGlobalCounters 1 }

cie1000LldpStatusStatisticsGlobalCountersTableDeletes OBJECT-TYPE
    SYNTAX      Unsigned32
    MAX-ACCESS  read-only
    STATUS      current
    DESCRIPTION
        "Shows the number of new entries deleted since switch reboot."
    ::= { cie1000LldpStatusStatisticsGlobalCounters 2 }

cie1000LldpStatusStatisticsGlobalCountersTableDrops OBJECT-TYPE
    SYNTAX      Unsigned32
    MAX-ACCESS  read-only
    STATUS      current
    DESCRIPTION
        "Shows the number of LLDP frames dropped due to the entry table being
         full."
    ::= { cie1000LldpStatusStatisticsGlobalCounters 3 }

cie1000LldpStatusStatisticsGlobalCountersTableAgeOuts OBJECT-TYPE
    SYNTAX      Unsigned32
    MAX-ACCESS  read-only
    STATUS      current
    DESCRIPTION
        "Shows the number of entries deleted due to Time-To-Live expiring."
    ::= { cie1000LldpStatusStatisticsGlobalCounters 4 }

cie1000LldpStatusStatisticsGlobalCountersLastChangeTime OBJECT-TYPE
    SYNTAX      CIE1000Unsigned64
    MAX-ACCESS  read-only
    STATUS      current
    DESCRIPTION
        "Shows the time when the last entry was last deleted or added. It also
         shows the time elapsed since the last change was detected."
    ::= { cie1000LldpStatusStatisticsGlobalCounters 5 }

cie1000LldpStatusStatisticsTable OBJECT-TYPE
    SYNTAX      SEQUENCE OF CIE1000LldpStatusStatisticsEntry
    MAX-ACCESS  not-accessible
    STATUS      current
    DESCRIPTION
        "This table represents the LLDP interface counters"
    ::= { cie1000LldpStatusStatistics 2 }

cie1000LldpStatusStatisticsEntry OBJECT-TYPE
    SYNTAX      CIE1000LldpStatusStatisticsEntry
    MAX-ACCESS  not-accessible
    STATUS      current
    DESCRIPTION
        "Each port interface has a set of statistics counters"
    INDEX       { cie1000LldpStatusStatisticsIfIndex }
    ::= { cie1000LldpStatusStatisticsTable 1 }

CIE1000LldpStatusStatisticsEntry ::= SEQUENCE {
    cie1000LldpStatusStatisticsIfIndex           CIE1000InterfaceIndex,
    cie1000LldpStatusStatisticsTxTotal           Unsigned32,
    cie1000LldpStatusStatisticsRxTotal           Unsigned32,
    cie1000LldpStatusStatisticsRxError           Unsigned32,
    cie1000LldpStatusStatisticsRxDiscarded       Unsigned32,
    cie1000LldpStatusStatisticsTLVsDiscarded     Unsigned32,
    cie1000LldpStatusStatisticsTLVsUnrecognized  Unsigned32,
    cie1000LldpStatusStatisticsTLVsOrgDiscarded  Unsigned32,
    cie1000LldpStatusStatisticsAgeOuts           Unsigned32
}

cie1000LldpStatusStatisticsIfIndex OBJECT-TYPE
    SYNTAX      CIE1000InterfaceIndex
    MAX-ACCESS  accessible-for-notify
    STATUS      current
    DESCRIPTION
        "Logical interface number index."
    ::= { cie1000LldpStatusStatisticsEntry 1 }

cie1000LldpStatusStatisticsTxTotal OBJECT-TYPE
    SYNTAX      Unsigned32
    MAX-ACCESS  read-only
    STATUS      current
    DESCRIPTION
        "Shows the number of LLDP frames transmitted."
    ::= { cie1000LldpStatusStatisticsEntry 2 }

cie1000LldpStatusStatisticsRxTotal OBJECT-TYPE
    SYNTAX      Unsigned32
    MAX-ACCESS  read-only
    STATUS      current
    DESCRIPTION
        "Shows the number of LLDP frames received."
    ::= { cie1000LldpStatusStatisticsEntry 3 }

cie1000LldpStatusStatisticsRxError OBJECT-TYPE
    SYNTAX      Unsigned32
    MAX-ACCESS  read-only
    STATUS      current
    DESCRIPTION
        "Shows the number of received LLDP frames containing some kind of error."
    ::= { cie1000LldpStatusStatisticsEntry 4 }

cie1000LldpStatusStatisticsRxDiscarded OBJECT-TYPE
    SYNTAX      Unsigned32
    MAX-ACCESS  read-only
    STATUS      current
    DESCRIPTION
        "Show the number of LLDP frames discarded. If a LLDP frame is received
         at an interface, and the switch's internal table has run full, the LLDP
         frame is counted and discarded. This situation is known as 'Too Many
         Neighbors' in the LLDP standard. LLDP frames require a new entry in the
         table when the Chassis ID or Remote Port ID is not already contained
         within the table. Entries are removed from the table when a given
         interface's link is down, an LLDP shutdown frame is received, or when
         the entry ages out."
    ::= { cie1000LldpStatusStatisticsEntry 5 }

cie1000LldpStatusStatisticsTLVsDiscarded OBJECT-TYPE
    SYNTAX      Unsigned32
    MAX-ACCESS  read-only
    STATUS      current
    DESCRIPTION
        "Shows the number of TLVs discarded. Each LLDP frame can contain
         multiple pieces of information, known as TLVs (TLV is short for 'Type
         Length Value'). If a TLV is malformed, it is counted and discarded."
    ::= { cie1000LldpStatusStatisticsEntry 6 }

cie1000LldpStatusStatisticsTLVsUnrecognized OBJECT-TYPE
    SYNTAX      Unsigned32
    MAX-ACCESS  read-only
    STATUS      current
    DESCRIPTION
        "Shows the number of well-formed TLVs, but with an unknown type value."
    ::= { cie1000LldpStatusStatisticsEntry 7 }

cie1000LldpStatusStatisticsTLVsOrgDiscarded OBJECT-TYPE
    SYNTAX      Unsigned32
    MAX-ACCESS  read-only
    STATUS      current
    DESCRIPTION
        "Shows the number of well-formed TLVs, but with an organizationally TLV
         which is not supported."
    ::= { cie1000LldpStatusStatisticsEntry 8 }

cie1000LldpStatusStatisticsAgeOuts OBJECT-TYPE
    SYNTAX      Unsigned32
    MAX-ACCESS  read-only
    STATUS      current
    DESCRIPTION
        "Show the number of age-outs. Each frame contains information about how
         long time the LLDP information is valid (age-out time). If no new LLDP
         frame is received within the age out time, the information is removed,
         and the counter is incremented."
    ::= { cie1000LldpStatusStatisticsEntry 9 }

cie1000LldpStatusNeighborsInfTable OBJECT-TYPE
    SYNTAX      SEQUENCE OF CIE1000LldpStatusNeighborsInfEntry
    MAX-ACCESS  not-accessible
    STATUS      current
    DESCRIPTION
        "This is a table to show the LLDP neighbors information for a specific
         interface."
    ::= { cie1000LldpStatus 2 }

cie1000LldpStatusNeighborsInfEntry OBJECT-TYPE
    SYNTAX      CIE1000LldpStatusNeighborsInfEntry
    MAX-ACCESS  not-accessible
    STATUS      current
    DESCRIPTION
        "Each interface has a set of neighbors information"
    INDEX       { cie1000LldpStatusNeighborsInfIfIndex,
                  cie1000LldpStatusNeighborsInfLldpmedIndex }
    ::= { cie1000LldpStatusNeighborsInfTable 1 }

CIE1000LldpStatusNeighborsInfEntry ::= SEQUENCE {
    cie1000LldpStatusNeighborsInfIfIndex                   CIE1000InterfaceIndex,
    cie1000LldpStatusNeighborsInfLldpmedIndex              Integer32,
    cie1000LldpStatusNeighborsInfChassisId                 CIE1000DisplayString,
    cie1000LldpStatusNeighborsInfPortId                    CIE1000DisplayString,
    cie1000LldpStatusNeighborsInfPortDescription           CIE1000DisplayString,
    cie1000LldpStatusNeighborsInfSystemName                CIE1000DisplayString,
    cie1000LldpStatusNeighborsInfSystemDescription         CIE1000DisplayString,
    cie1000LldpStatusNeighborsInfSystemCapabilities        CIE1000Unsigned16,
    cie1000LldpStatusNeighborsInfSystemCapabilitiesEnable  CIE1000Unsigned16
}

cie1000LldpStatusNeighborsInfIfIndex OBJECT-TYPE
    SYNTAX      CIE1000InterfaceIndex
    MAX-ACCESS  accessible-for-notify
    STATUS      current
    DESCRIPTION
        "Logical interface number index."
    ::= { cie1000LldpStatusNeighborsInfEntry 1 }

cie1000LldpStatusNeighborsInfLldpmedIndex OBJECT-TYPE
    SYNTAX      Integer32 (0..192)
    MAX-ACCESS  accessible-for-notify
    STATUS      current
    DESCRIPTION
        "Neighbor information table entry index."
    ::= { cie1000LldpStatusNeighborsInfEntry 2 }

cie1000LldpStatusNeighborsInfChassisId OBJECT-TYPE
    SYNTAX      CIE1000DisplayString (SIZE(0..254))
    MAX-ACCESS  read-only
    STATUS      current
    DESCRIPTION
        "Shows the LLDP neighbor's chassis Id."
    ::= { cie1000LldpStatusNeighborsInfEntry 4 }

cie1000LldpStatusNeighborsInfPortId OBJECT-TYPE
    SYNTAX      CIE1000DisplayString (SIZE(0..254))
    MAX-ACCESS  read-only
    STATUS      current
    DESCRIPTION
        "Shows the LLDP neighbor's port id."
    ::= { cie1000LldpStatusNeighborsInfEntry 5 }

cie1000LldpStatusNeighborsInfPortDescription OBJECT-TYPE
    SYNTAX      CIE1000DisplayString (SIZE(0..254))
    MAX-ACCESS  read-only
    STATUS      current
    DESCRIPTION
        "Shows the LLDP neighbor's port description."
    ::= { cie1000LldpStatusNeighborsInfEntry 6 }

cie1000LldpStatusNeighborsInfSystemName OBJECT-TYPE
    SYNTAX      CIE1000DisplayString (SIZE(0..254))
    MAX-ACCESS  read-only
    STATUS      current
    DESCRIPTION
        "Shows the LLDP neighbor's system name."
    ::= { cie1000LldpStatusNeighborsInfEntry 7 }

cie1000LldpStatusNeighborsInfSystemDescription OBJECT-TYPE
    SYNTAX      CIE1000DisplayString (SIZE(0..254))
    MAX-ACCESS  read-only
    STATUS      current
    DESCRIPTION
        "Shows the LLDP neighbor's system description."
    ::= { cie1000LldpStatusNeighborsInfEntry 8 }

cie1000LldpStatusNeighborsInfSystemCapabilities OBJECT-TYPE
    SYNTAX      CIE1000Unsigned16
    MAX-ACCESS  read-only
    STATUS      current
    DESCRIPTION
        "Shows the LLDP neighbor's system capabilities as bit mask.

         If the bit is set, it means that the functionality is supported by the
         neighbor system.

         Bit 0 represents Other.

         Bit 1 represents Repeater.

         Bit 2 represents Bridge.

         Bit 3 represents WLAN Access Point.

         Bit 4 represents Router.

         Bit 5 represents Telephone.

         Bit 6 represents DOCSIS cable device.

         Bit 7 represents Station Only.

         Bit 8 represents Reserved."
    ::= { cie1000LldpStatusNeighborsInfEntry 9 }

cie1000LldpStatusNeighborsInfSystemCapabilitiesEnable OBJECT-TYPE
    SYNTAX      CIE1000Unsigned16
    MAX-ACCESS  read-only
    STATUS      current
    DESCRIPTION
        "Shows the LLDP neighbor's system capabilities which is enabled.

         If the bit is set, it means that the functionality is currently enabled
         at the neighbor system.

         Bit 0 represents Other.

         Bit 1 represents Repeater.

         Bit 2 represents Bridge.

         Bit 3 represents WLAN Access Point.

         Bit 4 represents Router.

         Bit 5 represents Telephone.

         Bit 6 represents DOCSIS cable device.

         Bit 7 represents Station Only.

         Bit 8 represents Reserved."
    ::= { cie1000LldpStatusNeighborsInfEntry 10 }

cie1000LldpStatusNeighborsMgmtInfTable OBJECT-TYPE
    SYNTAX      SEQUENCE OF CIE1000LldpStatusNeighborsMgmtInfEntry
    MAX-ACCESS  not-accessible
    STATUS      current
    DESCRIPTION
        "This is a table to show the LLDP neighbors information for a specific
         interface."
    ::= { cie1000LldpStatus 3 }

cie1000LldpStatusNeighborsMgmtInfEntry OBJECT-TYPE
    SYNTAX      CIE1000LldpStatusNeighborsMgmtInfEntry
    MAX-ACCESS  not-accessible
    STATUS      current
    DESCRIPTION
        "Each interface has a set of neighbors information"
    INDEX       { cie1000LldpStatusNeighborsMgmtInfIfIndex,
                  cie1000LldpStatusNeighborsMgmtInfLldpmedIndex,
                  cie1000LldpStatusNeighborsMgmtInfLldpManagement }
    ::= { cie1000LldpStatusNeighborsMgmtInfTable 1 }

CIE1000LldpStatusNeighborsMgmtInfEntry ::= SEQUENCE {
    cie1000LldpStatusNeighborsMgmtInfIfIndex                     CIE1000InterfaceIndex,
    cie1000LldpStatusNeighborsMgmtInfLldpmedIndex                Integer32,
    cie1000LldpStatusNeighborsMgmtInfLldpManagement              Integer32,
    cie1000LldpStatusNeighborsMgmtInfSystemMgmAddressSubtype     CIE1000Unsigned8,
    cie1000LldpStatusNeighborsMgmtInfSystemMgmtAddress           CIE1000DisplayString,
    cie1000LldpStatusNeighborsMgmtInfSystemMgmtInterfaceSubtype  Integer32,
    cie1000LldpStatusNeighborsMgmtInfSystemMgmtInterface         Integer32,
    cie1000LldpStatusNeighborsMgmtInfSystemMgmtOid               OBJECT IDENTIFIER
}

cie1000LldpStatusNeighborsMgmtInfIfIndex OBJECT-TYPE
    SYNTAX      CIE1000InterfaceIndex
    MAX-ACCESS  accessible-for-notify
    STATUS      current
    DESCRIPTION
        "Logical interface number index."
    ::= { cie1000LldpStatusNeighborsMgmtInfEntry 1 }

cie1000LldpStatusNeighborsMgmtInfLldpmedIndex OBJECT-TYPE
    SYNTAX      Integer32 (0..192)
    MAX-ACCESS  accessible-for-notify
    STATUS      current
    DESCRIPTION
        "Neighbor information table entry index."
    ::= { cie1000LldpStatusNeighborsMgmtInfEntry 2 }

cie1000LldpStatusNeighborsMgmtInfLldpManagement OBJECT-TYPE
    SYNTAX      Integer32 (0..1)
    MAX-ACCESS  accessible-for-notify
    STATUS      current
    DESCRIPTION
        "Neighbor management information table entry index."
    ::= { cie1000LldpStatusNeighborsMgmtInfEntry 4 }

cie1000LldpStatusNeighborsMgmtInfSystemMgmAddressSubtype OBJECT-TYPE
    SYNTAX      CIE1000Unsigned8
    MAX-ACCESS  read-only
    STATUS      current
    DESCRIPTION
        "LLDP neighbor's management address subtype , section 9.5.9.3
         IEEE802.1AB-2005."
    ::= { cie1000LldpStatusNeighborsMgmtInfEntry 5 }

cie1000LldpStatusNeighborsMgmtInfSystemMgmtAddress OBJECT-TYPE
    SYNTAX      CIE1000DisplayString (SIZE(0..31))
    MAX-ACCESS  read-only
    STATUS      current
    DESCRIPTION
        "LLDP neighbor's management address string, section 9.5.9.4
         IEEE802.1AB-2005."
    ::= { cie1000LldpStatusNeighborsMgmtInfEntry 6 }

cie1000LldpStatusNeighborsMgmtInfSystemMgmtInterfaceSubtype OBJECT-TYPE
    SYNTAX      Integer32
    MAX-ACCESS  read-only
    STATUS      current
    DESCRIPTION
        "Interface numbering subtype, section 9.5.9.5 IEEE802.1AB-2005."
    ::= { cie1000LldpStatusNeighborsMgmtInfEntry 7 }

cie1000LldpStatusNeighborsMgmtInfSystemMgmtInterface OBJECT-TYPE
    SYNTAX      Integer32
    MAX-ACCESS  read-only
    STATUS      current
    DESCRIPTION
        "Interface number, section 9.5.9.6 IEEE802.1AB-2005."
    ::= { cie1000LldpStatusNeighborsMgmtInfEntry 8 }

cie1000LldpStatusNeighborsMgmtInfSystemMgmtOid OBJECT-TYPE
    SYNTAX      OBJECT IDENTIFIER
    MAX-ACCESS  read-only
    STATUS      current
    DESCRIPTION
        "Object identifier, section 9.5.9.8 IEEE802.1AB-2005."
    ::= { cie1000LldpStatusNeighborsMgmtInfEntry 9 }

cie1000LldpStatusMed OBJECT IDENTIFIER
    ::= { cie1000LldpStatus 4 }

cie1000LldpStatusMedRemoteDeviceInfoTable OBJECT-TYPE
    SYNTAX      SEQUENCE OF CIE1000LldpStatusMedRemoteDeviceInfoEntry
    MAX-ACCESS  not-accessible
    STATUS      current
    DESCRIPTION
        "This is a table to show the LLDP neighbors information for a specific
         interface."
    ::= { cie1000LldpStatusMed 1 }

cie1000LldpStatusMedRemoteDeviceInfoEntry OBJECT-TYPE
    SYNTAX      CIE1000LldpStatusMedRemoteDeviceInfoEntry
    MAX-ACCESS  not-accessible
    STATUS      current
    DESCRIPTION
        "Each interface has a set of neighbors information"
    INDEX       { cie1000LldpStatusMedRemoteDeviceInfoIfIndex,
                  cie1000LldpStatusMedRemoteDeviceInfoLldpmedIndex }
    ::= { cie1000LldpStatusMedRemoteDeviceInfoTable 1 }

CIE1000LldpStatusMedRemoteDeviceInfoEntry ::= SEQUENCE {
    cie1000LldpStatusMedRemoteDeviceInfoIfIndex              CIE1000InterfaceIndex,
    cie1000LldpStatusMedRemoteDeviceInfoLldpmedIndex         Integer32,
    cie1000LldpStatusMedRemoteDeviceInfoCapabilities         CIE1000Unsigned16,
    cie1000LldpStatusMedRemoteDeviceInfoCapabilitiesEnabled  CIE1000Unsigned16,
    cie1000LldpStatusMedRemoteDeviceInfoLatitude             CIE1000Integer64,
    cie1000LldpStatusMedRemoteDeviceInfoLongitude            CIE1000Integer64,
    cie1000LldpStatusMedRemoteDeviceInfoAltitudeType         CIE1000lldpmedAltitudeType,
    cie1000LldpStatusMedRemoteDeviceInfoAltitude             Integer32,
    cie1000LldpStatusMedRemoteDeviceInfoDatum                CIE1000lldpmedDatumType,
    cie1000LldpStatusMedRemoteDeviceInfoElinaddr             CIE1000DisplayString,
    cie1000LldpStatusMedRemoteDeviceInfoDeviceType           CIE1000lldpmedRemoteDeviceType,
    cie1000LldpStatusMedRemoteDeviceInfoHwRev                CIE1000DisplayString,
    cie1000LldpStatusMedRemoteDeviceInfoFwRev                CIE1000DisplayString,
    cie1000LldpStatusMedRemoteDeviceInfoSwRev                CIE1000DisplayString,
    cie1000LldpStatusMedRemoteDeviceInfoSerialNo             CIE1000DisplayString,
    cie1000LldpStatusMedRemoteDeviceInfoManufacturerName     CIE1000DisplayString,
    cie1000LldpStatusMedRemoteDeviceInfoModelName            CIE1000DisplayString,
    cie1000LldpStatusMedRemoteDeviceInfoAssetId              CIE1000DisplayString,
    cie1000LldpStatusMedRemoteDeviceInfoEeeRxTwSys           CIE1000Unsigned16,
    cie1000LldpStatusMedRemoteDeviceInfoEeeTxTwSys           CIE1000Unsigned16,
    cie1000LldpStatusMedRemoteDeviceInfoEeeFbTwSys           CIE1000Unsigned16,
    cie1000LldpStatusMedRemoteDeviceInfoEeeTxTwSysEcho       CIE1000Unsigned16,
    cie1000LldpStatusMedRemoteDeviceInfoEeeRxTwSysEcho       CIE1000Unsigned16
}

cie1000LldpStatusMedRemoteDeviceInfoIfIndex OBJECT-TYPE
    SYNTAX      CIE1000InterfaceIndex
    MAX-ACCESS  accessible-for-notify
    STATUS      current
    DESCRIPTION
        "Logical interface number index."
    ::= { cie1000LldpStatusMedRemoteDeviceInfoEntry 1 }

cie1000LldpStatusMedRemoteDeviceInfoLldpmedIndex OBJECT-TYPE
    SYNTAX      Integer32 (0..192)
    MAX-ACCESS  accessible-for-notify
    STATUS      current
    DESCRIPTION
        "Neighbor information table entry index."
    ::= { cie1000LldpStatusMedRemoteDeviceInfoEntry 2 }

cie1000LldpStatusMedRemoteDeviceInfoCapabilities OBJECT-TYPE
    SYNTAX      CIE1000Unsigned16
    MAX-ACCESS  read-only
    STATUS      current
    DESCRIPTION
        "LLDP neighbor's capabilities bit mask.

         Bit 0 represents LLDP-MED capabilities.

         Bit 1 represents Network Policy.

         Bit 2 represents Location Identification.

         Bit 3 represents Extended Power via MDI - PSE.

         Bit 4 represents Extended Power via MDI - PD

         Bit 5 represents Inventory

         "
    ::= { cie1000LldpStatusMedRemoteDeviceInfoEntry 4 }

cie1000LldpStatusMedRemoteDeviceInfoCapabilitiesEnabled OBJECT-TYPE
    SYNTAX      CIE1000Unsigned16
    MAX-ACCESS  read-only
    STATUS      current
    DESCRIPTION
        "LLDP neighbor's capabilities bit mask for the capabilities which are
         currently enabled.

         Bit 0 represents LLDP-MED capabilities.

         Bit 1 represents Network Policy.

         Bit 2 represents Location Identification.

         Bit 3 represents Extended Power via MDI - PSE.

         Bit 4 represents Extended Power via MDI - PD

         Bit 5 represents Inventory

         "
    ::= { cie1000LldpStatusMedRemoteDeviceInfoEntry 5 }

cie1000LldpStatusMedRemoteDeviceInfoLatitude OBJECT-TYPE
    SYNTAX      CIE1000Integer64
    MAX-ACCESS  read-only
    STATUS      current
    DESCRIPTION
        "Latitude degrees in 2s-complement as specified in RFC 3825. Positive
         numbers are north of the equator and negative numbers are south of the
         equator."
    ::= { cie1000LldpStatusMedRemoteDeviceInfoEntry 6 }

cie1000LldpStatusMedRemoteDeviceInfoLongitude OBJECT-TYPE
    SYNTAX      CIE1000Integer64
    MAX-ACCESS  read-only
    STATUS      current
    DESCRIPTION
        "Longitude degrees in 2s-complement as specified in RFC 3825. Positive
         values are East of the prime meridian and negative numbers are West of
         the prime meridian."
    ::= { cie1000LldpStatusMedRemoteDeviceInfoEntry 7 }

cie1000LldpStatusMedRemoteDeviceInfoAltitudeType OBJECT-TYPE
    SYNTAX      CIE1000lldpmedAltitudeType
    MAX-ACCESS  read-only
    STATUS      current
    DESCRIPTION
        "Altitude type as either floors or meters. Meters are representing
         meters of altitude defined by the vertical datum specified. Floors are
         representing altitude in a form more relevant in buildings which have
         different floor-to-floor dimensions. An altitude = 0.0 is meaningful
         even outside a building, and represents ground level at the given
         latitude and longitude. Inside a building, 0.0 represents the floor
         level associated with ground level at the main entrance."
    ::= { cie1000LldpStatusMedRemoteDeviceInfoEntry 8 }

cie1000LldpStatusMedRemoteDeviceInfoAltitude OBJECT-TYPE
    SYNTAX      Integer32
    MAX-ACCESS  read-only
    STATUS      current
    DESCRIPTION
        "Altitude value in 2s-complement as specified in RFC 3825"
    ::= { cie1000LldpStatusMedRemoteDeviceInfoEntry 9 }

cie1000LldpStatusMedRemoteDeviceInfoDatum OBJECT-TYPE
    SYNTAX      CIE1000lldpmedDatumType
    MAX-ACCESS  read-only
    STATUS      current
    DESCRIPTION
        "Datum (geodetic system) .

         The Map Datum is used for the coordinates given in these options:

         WGS84: (Geographical 3D) - World Geodesic System 1984, CRS Code 4327,
         Prime Meridian Name: Greenwich.

         NAD83/NAVD88: North American Datum 1983, CRS Code 4269, Prime Meridian
         Name: Greenwich; The associated vertical datum is the North American
         Vertical Datum of 1988 (NAVD88). This datum pair is to be used when
         referencing locations on land, not near tidal water(which would use
         Datum = NAD83/MLLW).

         NAD83/MLLW: North American Datum 1983, CRS Code 4269, Prime Meridian
         Name: Greenwich; The associated vertical datum is Mean Lower Low Water
         (MLLW). This datum pair is to be used when referencing locations on
         water/sea/ocean."
    ::= { cie1000LldpStatusMedRemoteDeviceInfoEntry 10 }

cie1000LldpStatusMedRemoteDeviceInfoElinaddr OBJECT-TYPE
    SYNTAX      CIE1000DisplayString (SIZE(0..25))
    MAX-ACCESS  read-only
    STATUS      current
    DESCRIPTION
        "Emergency Call Service ELIN identifier data format is defined to carry
         the ELIN identifier as used during emergency call setup to a
         traditional CAMA or ISDN trunk-based PSAP. This format consists of a
         numerical digit string, corresponding to the ELIN to be used for
         emergency calling. Maximum number of octets are 25."
    ::= { cie1000LldpStatusMedRemoteDeviceInfoEntry 11 }

cie1000LldpStatusMedRemoteDeviceInfoDeviceType OBJECT-TYPE
    SYNTAX      CIE1000lldpmedRemoteDeviceType
    MAX-ACCESS  read-only
    STATUS      current
    DESCRIPTION
        "Shows the LLDP neighbor's device type."
    ::= { cie1000LldpStatusMedRemoteDeviceInfoEntry 12 }

cie1000LldpStatusMedRemoteDeviceInfoHwRev OBJECT-TYPE
    SYNTAX      CIE1000DisplayString (SIZE(0..31))
    MAX-ACCESS  read-only
    STATUS      current
    DESCRIPTION
        "Shows the LLDP neighbor's hardware revision."
    ::= { cie1000LldpStatusMedRemoteDeviceInfoEntry 13 }

cie1000LldpStatusMedRemoteDeviceInfoFwRev OBJECT-TYPE
    SYNTAX      CIE1000DisplayString (SIZE(0..31))
    MAX-ACCESS  read-only
    STATUS      current
    DESCRIPTION
        "Shows the LLDP neighbor's firmware revision."
    ::= { cie1000LldpStatusMedRemoteDeviceInfoEntry 14 }

cie1000LldpStatusMedRemoteDeviceInfoSwRev OBJECT-TYPE
    SYNTAX      CIE1000DisplayString (SIZE(0..31))
    MAX-ACCESS  read-only
    STATUS      current
    DESCRIPTION
        "Shows the LLDP neighbor's software revision."
    ::= { cie1000LldpStatusMedRemoteDeviceInfoEntry 15 }

cie1000LldpStatusMedRemoteDeviceInfoSerialNo OBJECT-TYPE
    SYNTAX      CIE1000DisplayString (SIZE(0..31))
    MAX-ACCESS  read-only
    STATUS      current
    DESCRIPTION
        "Shows the LLDP neighbor's serial number."
    ::= { cie1000LldpStatusMedRemoteDeviceInfoEntry 16 }

cie1000LldpStatusMedRemoteDeviceInfoManufacturerName OBJECT-TYPE
    SYNTAX      CIE1000DisplayString (SIZE(0..31))
    MAX-ACCESS  read-only
    STATUS      current
    DESCRIPTION
        "Shows the LLDP neighbor's manufacturer name."
    ::= { cie1000LldpStatusMedRemoteDeviceInfoEntry 17 }

cie1000LldpStatusMedRemoteDeviceInfoModelName OBJECT-TYPE
    SYNTAX      CIE1000DisplayString (SIZE(0..31))
    MAX-ACCESS  read-only
    STATUS      current
    DESCRIPTION
        "Shows the LLDP neighbor's model name."
    ::= { cie1000LldpStatusMedRemoteDeviceInfoEntry 18 }

cie1000LldpStatusMedRemoteDeviceInfoAssetId OBJECT-TYPE
    SYNTAX      CIE1000DisplayString (SIZE(0..31))
    MAX-ACCESS  read-only
    STATUS      current
    DESCRIPTION
        "Shows the LLDP neighbor's asset id."
    ::= { cie1000LldpStatusMedRemoteDeviceInfoEntry 19 }

cie1000LldpStatusMedRemoteDeviceInfoEeeRxTwSys OBJECT-TYPE
    SYNTAX      CIE1000Unsigned16
    MAX-ACCESS  read-only
    STATUS      current
    DESCRIPTION
        "Shows the LLDP neighbor's Receive tw_sys_rx . Tw_sys_rx is defined as
         the time (expressed in microseconds) that the transmitting link partner
         will wait before it starts transmitting data after leaving the Low
         Power Idle (LPI) mode. Section 79.3.5.2, IEEE802.3az."
    ::= { cie1000LldpStatusMedRemoteDeviceInfoEntry 20 }

cie1000LldpStatusMedRemoteDeviceInfoEeeTxTwSys OBJECT-TYPE
    SYNTAX      CIE1000Unsigned16
    MAX-ACCESS  read-only
    STATUS      current
    DESCRIPTION
        "Shows the LLDP neighbor's Transmit Tw_sys_tx . Tw_sys_tx is defined as
         the time (expressed in microseconds) that the receiving link partner is
         requesting the transmitting link partner to wait before starting the
         transmission data following the Low Power Idle (LPI) mode. Section
         79.3.5.1, IEEE802.3az."
    ::= { cie1000LldpStatusMedRemoteDeviceInfoEntry 21 }

cie1000LldpStatusMedRemoteDeviceInfoEeeFbTwSys OBJECT-TYPE
    SYNTAX      CIE1000Unsigned16
    MAX-ACCESS  read-only
    STATUS      current
    DESCRIPTION
        "Shows the LLDP neighbor's Fallback tw_sys_tx. A receiving link partner
         may inform the transmitter of an alternate desired Tw_sys_tx. Since a
         receiving link partner is likely to have discrete levels for savings,
         this provides the transmitter with additional information that it may
         use for a more efficient allocation. Section 79.3.5.3, IEEE802.3az."
    ::= { cie1000LldpStatusMedRemoteDeviceInfoEntry 22 }

cie1000LldpStatusMedRemoteDeviceInfoEeeTxTwSysEcho OBJECT-TYPE
    SYNTAX      CIE1000Unsigned16
    MAX-ACCESS  read-only
    STATUS      current
    DESCRIPTION
        "Shows the LLDP neighbor's echo transmit Tw. The respective echo values
         shall be defined as the local link partners reflection (echo) of the
         remote link partners respective values. When a local link partner
         receives its echoed values from the remote link partner it can
         determine whether or not the remote link partner has received,
         registered, and processed its most recent values. Section 79.3.5.4,
         IEEE802.3az."
    ::= { cie1000LldpStatusMedRemoteDeviceInfoEntry 23 }

cie1000LldpStatusMedRemoteDeviceInfoEeeRxTwSysEcho OBJECT-TYPE
    SYNTAX      CIE1000Unsigned16
    MAX-ACCESS  read-only
    STATUS      current
    DESCRIPTION
        "Shows the LLDP neighbor's echo receive Tw. The respective echo values
         shall be defined as the local link partners reflection (echo) of the
         remote link partners respective values. When a local link partner
         receives its echoed values from the remote link partner it can
         determine whether or not the remote link partner has received,
         registered, and processed its most recent values. Section 79.3.5.4,
         IEEE802.3az."
    ::= { cie1000LldpStatusMedRemoteDeviceInfoEntry 24 }

cie1000LldpStatusMedRemoteDeviceLocInfoTable OBJECT-TYPE
    SYNTAX      SEQUENCE OF CIE1000LldpStatusMedRemoteDeviceLocInfoEntry
    MAX-ACCESS  not-accessible
    STATUS      current
    DESCRIPTION
        "This is a table to show the LLDP-MED remote device (neighbor) civic
         location information for a specific interface."
    ::= { cie1000LldpStatusMed 2 }

cie1000LldpStatusMedRemoteDeviceLocInfoEntry OBJECT-TYPE
    SYNTAX      CIE1000LldpStatusMedRemoteDeviceLocInfoEntry
    MAX-ACCESS  not-accessible
    STATUS      current
    DESCRIPTION
        "Each interface has a set of neighbors information"
    INDEX       { cie1000LldpStatusMedRemoteDeviceLocInfoIfIndex,
                  cie1000LldpStatusMedRemoteDeviceLocInfoLldpmedIndex }
    ::= { cie1000LldpStatusMedRemoteDeviceLocInfoTable 1 }

CIE1000LldpStatusMedRemoteDeviceLocInfoEntry ::= SEQUENCE {
    cie1000LldpStatusMedRemoteDeviceLocInfoIfIndex                 CIE1000InterfaceIndex,
    cie1000LldpStatusMedRemoteDeviceLocInfoLldpmedIndex            Integer32,
    cie1000LldpStatusMedRemoteDeviceLocInfoState                   CIE1000DisplayString,
    cie1000LldpStatusMedRemoteDeviceLocInfoCounty                  CIE1000DisplayString,
    cie1000LldpStatusMedRemoteDeviceLocInfoCity                    CIE1000DisplayString,
    cie1000LldpStatusMedRemoteDeviceLocInfoDistrict                CIE1000DisplayString,
    cie1000LldpStatusMedRemoteDeviceLocInfoBlock                   CIE1000DisplayString,
    cie1000LldpStatusMedRemoteDeviceLocInfoStreet                  CIE1000DisplayString,
    cie1000LldpStatusMedRemoteDeviceLocInfoLeadingStreetDirection  CIE1000DisplayString,
    cie1000LldpStatusMedRemoteDeviceLocInfoTrailingStreetSuffix    CIE1000DisplayString,
    cie1000LldpStatusMedRemoteDeviceLocInfoStreetSuffix            CIE1000DisplayString,
    cie1000LldpStatusMedRemoteDeviceLocInfoHouseNo                 CIE1000DisplayString,
    cie1000LldpStatusMedRemoteDeviceLocInfoHouseNoSuffix           CIE1000DisplayString,
    cie1000LldpStatusMedRemoteDeviceLocInfoLandmark                CIE1000DisplayString,
    cie1000LldpStatusMedRemoteDeviceLocInfoAdditionalInfo          CIE1000DisplayString,
    cie1000LldpStatusMedRemoteDeviceLocInfoName                    CIE1000DisplayString,
    cie1000LldpStatusMedRemoteDeviceLocInfoZipCode                 CIE1000DisplayString,
    cie1000LldpStatusMedRemoteDeviceLocInfoBuilding                CIE1000DisplayString,
    cie1000LldpStatusMedRemoteDeviceLocInfoApartment               CIE1000DisplayString,
    cie1000LldpStatusMedRemoteDeviceLocInfoFloor                   CIE1000DisplayString,
    cie1000LldpStatusMedRemoteDeviceLocInfoRoomNumber              CIE1000DisplayString,
    cie1000LldpStatusMedRemoteDeviceLocInfoPlaceType               CIE1000DisplayString,
    cie1000LldpStatusMedRemoteDeviceLocInfoPostalCommunityName     CIE1000DisplayString,
    cie1000LldpStatusMedRemoteDeviceLocInfoPoBox                   CIE1000DisplayString,
    cie1000LldpStatusMedRemoteDeviceLocInfoAdditionalCode          CIE1000DisplayString,
    cie1000LldpStatusMedRemoteDeviceLocInfoCountryCode             CIE1000DisplayString
}

cie1000LldpStatusMedRemoteDeviceLocInfoIfIndex OBJECT-TYPE
    SYNTAX      CIE1000InterfaceIndex
    MAX-ACCESS  accessible-for-notify
    STATUS      current
    DESCRIPTION
        "Logical interface number index."
    ::= { cie1000LldpStatusMedRemoteDeviceLocInfoEntry 1 }

cie1000LldpStatusMedRemoteDeviceLocInfoLldpmedIndex OBJECT-TYPE
    SYNTAX      Integer32 (0..192)
    MAX-ACCESS  accessible-for-notify
    STATUS      current
    DESCRIPTION
        "Neighbor information table entry index."
    ::= { cie1000LldpStatusMedRemoteDeviceLocInfoEntry 2 }

cie1000LldpStatusMedRemoteDeviceLocInfoState OBJECT-TYPE
    SYNTAX      CIE1000DisplayString (SIZE(0..250))
    MAX-ACCESS  read-only
    STATUS      current
    DESCRIPTION
        "National subdivision"
    ::= { cie1000LldpStatusMedRemoteDeviceLocInfoEntry 5 }

cie1000LldpStatusMedRemoteDeviceLocInfoCounty OBJECT-TYPE
    SYNTAX      CIE1000DisplayString (SIZE(0..250))
    MAX-ACCESS  read-only
    STATUS      current
    DESCRIPTION
        "County"
    ::= { cie1000LldpStatusMedRemoteDeviceLocInfoEntry 6 }

cie1000LldpStatusMedRemoteDeviceLocInfoCity OBJECT-TYPE
    SYNTAX      CIE1000DisplayString (SIZE(0..250))
    MAX-ACCESS  read-only
    STATUS      current
    DESCRIPTION
        "City"
    ::= { cie1000LldpStatusMedRemoteDeviceLocInfoEntry 7 }

cie1000LldpStatusMedRemoteDeviceLocInfoDistrict OBJECT-TYPE
    SYNTAX      CIE1000DisplayString (SIZE(0..250))
    MAX-ACCESS  read-only
    STATUS      current
    DESCRIPTION
        "City district"
    ::= { cie1000LldpStatusMedRemoteDeviceLocInfoEntry 8 }

cie1000LldpStatusMedRemoteDeviceLocInfoBlock OBJECT-TYPE
    SYNTAX      CIE1000DisplayString (SIZE(0..250))
    MAX-ACCESS  read-only
    STATUS      current
    DESCRIPTION
        "Block (Neighborhood)"
    ::= { cie1000LldpStatusMedRemoteDeviceLocInfoEntry 9 }

cie1000LldpStatusMedRemoteDeviceLocInfoStreet OBJECT-TYPE
    SYNTAX      CIE1000DisplayString (SIZE(0..250))
    MAX-ACCESS  read-only
    STATUS      current
    DESCRIPTION
        "Street"
    ::= { cie1000LldpStatusMedRemoteDeviceLocInfoEntry 10 }

cie1000LldpStatusMedRemoteDeviceLocInfoLeadingStreetDirection OBJECT-TYPE
    SYNTAX      CIE1000DisplayString (SIZE(0..250))
    MAX-ACCESS  read-only
    STATUS      current
    DESCRIPTION
        "Street Direction"
    ::= { cie1000LldpStatusMedRemoteDeviceLocInfoEntry 11 }

cie1000LldpStatusMedRemoteDeviceLocInfoTrailingStreetSuffix OBJECT-TYPE
    SYNTAX      CIE1000DisplayString (SIZE(0..250))
    MAX-ACCESS  read-only
    STATUS      current
    DESCRIPTION
        "Trailing Street Suffix"
    ::= { cie1000LldpStatusMedRemoteDeviceLocInfoEntry 12 }

cie1000LldpStatusMedRemoteDeviceLocInfoStreetSuffix OBJECT-TYPE
    SYNTAX      CIE1000DisplayString (SIZE(0..250))
    MAX-ACCESS  read-only
    STATUS      current
    DESCRIPTION
        "Street Suffix"
    ::= { cie1000LldpStatusMedRemoteDeviceLocInfoEntry 13 }

cie1000LldpStatusMedRemoteDeviceLocInfoHouseNo OBJECT-TYPE
    SYNTAX      CIE1000DisplayString (SIZE(0..250))
    MAX-ACCESS  read-only
    STATUS      current
    DESCRIPTION
        "House No."
    ::= { cie1000LldpStatusMedRemoteDeviceLocInfoEntry 14 }

cie1000LldpStatusMedRemoteDeviceLocInfoHouseNoSuffix OBJECT-TYPE
    SYNTAX      CIE1000DisplayString (SIZE(0..250))
    MAX-ACCESS  read-only
    STATUS      current
    DESCRIPTION
        "House No. Suffix"
    ::= { cie1000LldpStatusMedRemoteDeviceLocInfoEntry 15 }

cie1000LldpStatusMedRemoteDeviceLocInfoLandmark OBJECT-TYPE
    SYNTAX      CIE1000DisplayString (SIZE(0..250))
    MAX-ACCESS  read-only
    STATUS      current
    DESCRIPTION
        "Landmark"
    ::= { cie1000LldpStatusMedRemoteDeviceLocInfoEntry 16 }

cie1000LldpStatusMedRemoteDeviceLocInfoAdditionalInfo OBJECT-TYPE
    SYNTAX      CIE1000DisplayString (SIZE(0..250))
    MAX-ACCESS  read-only
    STATUS      current
    DESCRIPTION
        "Additional Location Info"
    ::= { cie1000LldpStatusMedRemoteDeviceLocInfoEntry 17 }

cie1000LldpStatusMedRemoteDeviceLocInfoName OBJECT-TYPE
    SYNTAX      CIE1000DisplayString (SIZE(0..250))
    MAX-ACCESS  read-only
    STATUS      current
    DESCRIPTION
        "Name"
    ::= { cie1000LldpStatusMedRemoteDeviceLocInfoEntry 18 }

cie1000LldpStatusMedRemoteDeviceLocInfoZipCode OBJECT-TYPE
    SYNTAX      CIE1000DisplayString (SIZE(0..250))
    MAX-ACCESS  read-only
    STATUS      current
    DESCRIPTION
        "Zip code"
    ::= { cie1000LldpStatusMedRemoteDeviceLocInfoEntry 19 }

cie1000LldpStatusMedRemoteDeviceLocInfoBuilding OBJECT-TYPE
    SYNTAX      CIE1000DisplayString (SIZE(0..250))
    MAX-ACCESS  read-only
    STATUS      current
    DESCRIPTION
        "Building"
    ::= { cie1000LldpStatusMedRemoteDeviceLocInfoEntry 20 }

cie1000LldpStatusMedRemoteDeviceLocInfoApartment OBJECT-TYPE
    SYNTAX      CIE1000DisplayString (SIZE(0..250))
    MAX-ACCESS  read-only
    STATUS      current
    DESCRIPTION
        "Apartment/unit"
    ::= { cie1000LldpStatusMedRemoteDeviceLocInfoEntry 21 }

cie1000LldpStatusMedRemoteDeviceLocInfoFloor OBJECT-TYPE
    SYNTAX      CIE1000DisplayString (SIZE(0..250))
    MAX-ACCESS  read-only
    STATUS      current
    DESCRIPTION
        "Floor"
    ::= { cie1000LldpStatusMedRemoteDeviceLocInfoEntry 22 }

cie1000LldpStatusMedRemoteDeviceLocInfoRoomNumber OBJECT-TYPE
    SYNTAX      CIE1000DisplayString (SIZE(0..250))
    MAX-ACCESS  read-only
    STATUS      current
    DESCRIPTION
        "Room Number"
    ::= { cie1000LldpStatusMedRemoteDeviceLocInfoEntry 23 }

cie1000LldpStatusMedRemoteDeviceLocInfoPlaceType OBJECT-TYPE
    SYNTAX      CIE1000DisplayString (SIZE(0..250))
    MAX-ACCESS  read-only
    STATUS      current
    DESCRIPTION
        "Place type"
    ::= { cie1000LldpStatusMedRemoteDeviceLocInfoEntry 24 }

cie1000LldpStatusMedRemoteDeviceLocInfoPostalCommunityName OBJECT-TYPE
    SYNTAX      CIE1000DisplayString (SIZE(0..250))
    MAX-ACCESS  read-only
    STATUS      current
    DESCRIPTION
        "Postal Community Name"
    ::= { cie1000LldpStatusMedRemoteDeviceLocInfoEntry 25 }

cie1000LldpStatusMedRemoteDeviceLocInfoPoBox OBJECT-TYPE
    SYNTAX      CIE1000DisplayString (SIZE(0..250))
    MAX-ACCESS  read-only
    STATUS      current
    DESCRIPTION
        "Post Office Box"
    ::= { cie1000LldpStatusMedRemoteDeviceLocInfoEntry 26 }

cie1000LldpStatusMedRemoteDeviceLocInfoAdditionalCode OBJECT-TYPE
    SYNTAX      CIE1000DisplayString (SIZE(0..250))
    MAX-ACCESS  read-only
    STATUS      current
    DESCRIPTION
        "Additional Code"
    ::= { cie1000LldpStatusMedRemoteDeviceLocInfoEntry 27 }

cie1000LldpStatusMedRemoteDeviceLocInfoCountryCode OBJECT-TYPE
    SYNTAX      CIE1000DisplayString (SIZE(0..2))
    MAX-ACCESS  read-only
    STATUS      current
    DESCRIPTION
        "The two-letter ISO 3166 country code in capital ASCII letters -
         Example: DK, DE or US."
    ::= { cie1000LldpStatusMedRemoteDeviceLocInfoEntry 28 }

cie1000LldpStatusMedRemoteDeviceNetworkPolicyInfoTable OBJECT-TYPE
    SYNTAX      SEQUENCE OF CIE1000LldpStatusMedRemoteDeviceNetworkPolicyInfoEntry
    MAX-ACCESS  not-accessible
    STATUS      current
    DESCRIPTION
        "This is a table to show the LLDP-MED remote device (neighbor) network
         policies information for a specific interface."
    ::= { cie1000LldpStatusMed 3 }

cie1000LldpStatusMedRemoteDeviceNetworkPolicyInfoEntry OBJECT-TYPE
    SYNTAX      CIE1000LldpStatusMedRemoteDeviceNetworkPolicyInfoEntry
    MAX-ACCESS  not-accessible
    STATUS      current
    DESCRIPTION
        "Each interface has a set of neighbors information"
    INDEX       {                   cie1000LldpStatusMedRemoteDeviceNetworkPolicyInfoIfIndex,
                  cie1000LldpStatusMedRemoteDeviceNetworkPolicyInfoLldpmedIndex,
                  cie1000LldpStatusMedRemoteDeviceNetworkPolicyInfoLldpmedPolicy }
    ::= { cie1000LldpStatusMedRemoteDeviceNetworkPolicyInfoTable 1 }

CIE1000LldpStatusMedRemoteDeviceNetworkPolicyInfoEntry ::= SEQUENCE {
    cie1000LldpStatusMedRemoteDeviceNetworkPolicyInfoIfIndex          CIE1000InterfaceIndex,
    cie1000LldpStatusMedRemoteDeviceNetworkPolicyInfoLldpmedIndex     Integer32,
    cie1000LldpStatusMedRemoteDeviceNetworkPolicyInfoLldpmedPolicy    Integer32,
    cie1000LldpStatusMedRemoteDeviceNetworkPolicyInfoApplicationType  CIE1000lldpmedRemoteNetworkPolicyApplicationType,
    cie1000LldpStatusMedRemoteDeviceNetworkPolicyInfoUnknownPolicy    TruthValue,
    cie1000LldpStatusMedRemoteDeviceNetworkPolicyInfoTagged           TruthValue,
    cie1000LldpStatusMedRemoteDeviceNetworkPolicyInfoVlanId           CIE1000Unsigned16,
    cie1000LldpStatusMedRemoteDeviceNetworkPolicyInfoL2Priority       CIE1000Unsigned8,
    cie1000LldpStatusMedRemoteDeviceNetworkPolicyInfoDscp             CIE1000Unsigned8
}

cie1000LldpStatusMedRemoteDeviceNetworkPolicyInfoIfIndex OBJECT-TYPE
    SYNTAX      CIE1000InterfaceIndex
    MAX-ACCESS  accessible-for-notify
    STATUS      current
    DESCRIPTION
        "Logical interface number index."
    ::= { cie1000LldpStatusMedRemoteDeviceNetworkPolicyInfoEntry 1 }

cie1000LldpStatusMedRemoteDeviceNetworkPolicyInfoLldpmedIndex OBJECT-TYPE
    SYNTAX      Integer32 (0..192)
    MAX-ACCESS  accessible-for-notify
    STATUS      current
    DESCRIPTION
        "Neighbor information table entry index."
    ::= { cie1000LldpStatusMedRemoteDeviceNetworkPolicyInfoEntry 2 }

cie1000LldpStatusMedRemoteDeviceNetworkPolicyInfoLldpmedPolicy OBJECT-TYPE
    SYNTAX      Integer32 (0..31)
    MAX-ACCESS  accessible-for-notify
    STATUS      current
    DESCRIPTION
        "Policy index."
    ::= { cie1000LldpStatusMedRemoteDeviceNetworkPolicyInfoEntry 3 }

cie1000LldpStatusMedRemoteDeviceNetworkPolicyInfoApplicationType OBJECT-TYPE
    SYNTAX      CIE1000lldpmedRemoteNetworkPolicyApplicationType
    MAX-ACCESS  read-only
    STATUS      current
    DESCRIPTION
        "The LLDP policy application type."
    ::= { cie1000LldpStatusMedRemoteDeviceNetworkPolicyInfoEntry 5 }

cie1000LldpStatusMedRemoteDeviceNetworkPolicyInfoUnknownPolicy OBJECT-TYPE
    SYNTAX      TruthValue
    MAX-ACCESS  read-only
    STATUS      current
    DESCRIPTION
        "Policy indicates that an Endpoint Device wants to explicitly advertise
         that the policy is required by the device. Can be either Defined or
         Unknown

         Unknown: The network policy for the specified application type is
         currently unknown.

         Defined: The network policy is defined (known)."
    ::= { cie1000LldpStatusMedRemoteDeviceNetworkPolicyInfoEntry 6 }

cie1000LldpStatusMedRemoteDeviceNetworkPolicyInfoTagged OBJECT-TYPE
    SYNTAX      TruthValue
    MAX-ACCESS  read-only
    STATUS      current
    DESCRIPTION
        "Defines if LLDP policy uses tagged VLAN."
    ::= { cie1000LldpStatusMedRemoteDeviceNetworkPolicyInfoEntry 7 }

cie1000LldpStatusMedRemoteDeviceNetworkPolicyInfoVlanId OBJECT-TYPE
    SYNTAX      CIE1000Unsigned16 (1..4095)
    MAX-ACCESS  read-only
    STATUS      current
    DESCRIPTION
        "The policy VLAN ID. Only valid when policy 'Tagged' is TRUE"
    ::= { cie1000LldpStatusMedRemoteDeviceNetworkPolicyInfoEntry 8 }

cie1000LldpStatusMedRemoteDeviceNetworkPolicyInfoL2Priority OBJECT-TYPE
    SYNTAX      CIE1000Unsigned8 (0..7)
    MAX-ACCESS  read-only
    STATUS      current
    DESCRIPTION
        "Shows the LLDP neighbor's policy L2 priority."
    ::= { cie1000LldpStatusMedRemoteDeviceNetworkPolicyInfoEntry 9 }

cie1000LldpStatusMedRemoteDeviceNetworkPolicyInfoDscp OBJECT-TYPE
    SYNTAX      CIE1000Unsigned8 (0..63)
    MAX-ACCESS  read-only
    STATUS      current
    DESCRIPTION
        "LLDP policy DSCP."
    ::= { cie1000LldpStatusMedRemoteDeviceNetworkPolicyInfoEntry 10 }

cie1000LldpControl OBJECT IDENTIFIER
    ::= { cie1000LldpMibObjects 4 }

cie1000LldpControlStatisticsClear OBJECT IDENTIFIER
    ::= { cie1000LldpControl 1 }

cie1000LldpControlStatisticsClearTable OBJECT-TYPE
    SYNTAX      SEQUENCE OF CIE1000LldpControlStatisticsClearEntry
    MAX-ACCESS  not-accessible
    STATUS      current
    DESCRIPTION
        "This is a table to clear LLDP statistics for a specific interface."
    ::= { cie1000LldpControlStatisticsClear 1 }

cie1000LldpControlStatisticsClearEntry OBJECT-TYPE
    SYNTAX      CIE1000LldpControlStatisticsClearEntry
    MAX-ACCESS  not-accessible
    STATUS      current
    DESCRIPTION
        "Each interface has a set of statistics counters"
    INDEX       { cie1000LldpControlStatisticsClearIfIndex }
    ::= { cie1000LldpControlStatisticsClearTable 1 }

CIE1000LldpControlStatisticsClearEntry ::= SEQUENCE {
    cie1000LldpControlStatisticsClearIfIndex          CIE1000InterfaceIndex,
    cie1000LldpControlStatisticsClearStatisticsClear  TruthValue
}

cie1000LldpControlStatisticsClearIfIndex OBJECT-TYPE
    SYNTAX      CIE1000InterfaceIndex
    MAX-ACCESS  accessible-for-notify
    STATUS      current
    DESCRIPTION
        "Logical interface number index."
    ::= { cie1000LldpControlStatisticsClearEntry 1 }

cie1000LldpControlStatisticsClearStatisticsClear OBJECT-TYPE
    SYNTAX      TruthValue
    MAX-ACCESS  read-write
    STATUS      current
    DESCRIPTION
        "Set to TRUE to clear the LLDP statistics of an interface."
    ::= { cie1000LldpControlStatisticsClearEntry 2 }

cie1000LldpControlStatisticsClearGlobal OBJECT IDENTIFIER
    ::= { cie1000LldpControlStatisticsClear 2 }

cie1000LldpControlStatisticsClearGlobalClear OBJECT-TYPE
    SYNTAX      TruthValue
    MAX-ACCESS  read-write
    STATUS      current
    DESCRIPTION
        "Set to TRUE to clear the LLDP global statistics."
    ::= { cie1000LldpControlStatisticsClearGlobal 1 }

cie1000LldpMibConformance OBJECT IDENTIFIER
    ::= { cie1000LldpMib 2 }

cie1000LldpMibCompliances OBJECT IDENTIFIER
    ::= { cie1000LldpMibConformance 1 }

cie1000LldpMibGroups OBJECT IDENTIFIER
    ::= { cie1000LldpMibConformance 2 }

cie1000LldpConfigGlobalInfoGroup OBJECT-GROUP
    OBJECTS     { cie1000LldpConfigGlobalReInitDelay,
                  cie1000LldpConfigGlobalMsgTxHold,
                  cie1000LldpConfigGlobalMsgTxInterval,
                  cie1000LldpConfigGlobalTxDelay }
    STATUS      current
    DESCRIPTION
        "A collection of objects."
    ::= { cie1000LldpMibGroups 1 }

cie1000LldpConfigInfoGroup OBJECT-GROUP
    OBJECTS     { cie1000LldpConfigIfIndex,
                  cie1000LldpConfigAdminState,
                  cie1000LldpConfigCdpAware,
                  cie1000LldpConfigOptionalTlvs,
                  cie1000LldpConfigSnmpNotificationEna }
    STATUS      current
    DESCRIPTION
        "A collection of objects."
    ::= { cie1000LldpMibGroups 2 }

cie1000LldpConfigMedInfoGroup OBJECT-GROUP
    OBJECTS     { cie1000LldpConfigMedIfIndex,
                  cie1000LldpConfigMedOptionalTlvs,
                  cie1000LldpConfigMedDeviceType }
    STATUS      current
    DESCRIPTION
        "A collection of objects."
    ::= { cie1000LldpMibGroups 3 }

cie1000LldpConfigMedPolicyInfoGroup OBJECT-GROUP
    OBJECTS     { cie1000LldpConfigMedPolicyLldpmedPolicy,
                  cie1000LldpConfigMedPolicyApplicationType,
                  cie1000LldpConfigMedPolicyTagged,
                  cie1000LldpConfigMedPolicyVlanId,
                  cie1000LldpConfigMedPolicyL2Priority,
                  cie1000LldpConfigMedPolicyDscp,
                  cie1000LldpConfigMedPolicyAction }
    STATUS      current
    DESCRIPTION
        "A collection of objects."
    ::= { cie1000LldpMibGroups 4 }

cie1000LldpConfigMedPolicyListInfoGroup OBJECT-GROUP
    OBJECTS     { cie1000LldpConfigMedPolicyListIfIndex,
                  cie1000LldpConfigMedPolicyListLldpmedPolicy,
                  cie1000LldpConfigMedPolicyListLldpmedPoliciesList }
    STATUS      current
    DESCRIPTION
        "A collection of objects."
    ::= { cie1000LldpMibGroups 5 }

cie1000LldpConfigMedGlobalInfoGroup OBJECT-GROUP
    OBJECTS     { cie1000LldpConfigMedGlobalFastRepeatCount,
                  cie1000LldpConfigMedGlobalLatitude,
                  cie1000LldpConfigMedGlobalLongitude,
                  cie1000LldpConfigMedGlobalAltitudeType,
                  cie1000LldpConfigMedGlobalAltitude,
                  cie1000LldpConfigMedGlobalElinAddr,
                  cie1000LldpConfigMedGlobalDatum,
                  cie1000LldpConfigMedGlobalCountryCode }
    STATUS      current
    DESCRIPTION
        "A collection of objects."
    ::= { cie1000LldpMibGroups 6 }

cie1000LldpConfigMedLocationInfInfoGroup OBJECT-GROUP
    OBJECTS     { cie1000LldpConfigMedLocationInfLldpmedIndex,
                  cie1000LldpConfigMedLocationInfCivicAddress }
    STATUS      current
    DESCRIPTION
        "A collection of objects."
    ::= { cie1000LldpMibGroups 7 }

cie1000LldpConfigMedPolicyRowEditorInfoGroup OBJECT-GROUP
    OBJECTS     { cie1000LldpConfigMedPolicyRowEditorLldpmedPolicy,
                  cie1000LldpConfigMedPolicyRowEditorApplicationType,
                  cie1000LldpConfigMedPolicyRowEditorTagged,
                  cie1000LldpConfigMedPolicyRowEditorVlanId,
                  cie1000LldpConfigMedPolicyRowEditorL2Priority,
                  cie1000LldpConfigMedPolicyRowEditorDscp,
                  cie1000LldpConfigMedPolicyRowEditorAction }
    STATUS      current
    DESCRIPTION
        "A collection of objects."
    ::= { cie1000LldpMibGroups 8 }

cie1000LldpStatusStatisticsGlobalCountersInfoGroup OBJECT-GROUP
    OBJECTS     {                   cie1000LldpStatusStatisticsGlobalCountersTableInserts,
                  cie1000LldpStatusStatisticsGlobalCountersTableDeletes,
                  cie1000LldpStatusStatisticsGlobalCountersTableDrops,
                  cie1000LldpStatusStatisticsGlobalCountersTableAgeOuts,
                  cie1000LldpStatusStatisticsGlobalCountersLastChangeTime }
    STATUS      current
    DESCRIPTION
        "A collection of objects."
    ::= { cie1000LldpMibGroups 9 }

cie1000LldpStatusStatisticsTableInfoGroup OBJECT-GROUP
    OBJECTS     { cie1000LldpStatusStatisticsIfIndex,
                  cie1000LldpStatusStatisticsTxTotal,
                  cie1000LldpStatusStatisticsRxTotal,
                  cie1000LldpStatusStatisticsRxError,
                  cie1000LldpStatusStatisticsRxDiscarded,
                  cie1000LldpStatusStatisticsTLVsDiscarded,
                  cie1000LldpStatusStatisticsTLVsUnrecognized,
                  cie1000LldpStatusStatisticsTLVsOrgDiscarded,
                  cie1000LldpStatusStatisticsAgeOuts }
    STATUS      current
    DESCRIPTION
        "A collection of objects."
    ::= { cie1000LldpMibGroups 10 }

cie1000LldpStatusNeighborsInfInfoGroup OBJECT-GROUP
    OBJECTS     { cie1000LldpStatusNeighborsInfIfIndex,
                  cie1000LldpStatusNeighborsInfLldpmedIndex,
                  cie1000LldpStatusNeighborsInfChassisId,
                  cie1000LldpStatusNeighborsInfPortId,
                  cie1000LldpStatusNeighborsInfPortDescription,
                  cie1000LldpStatusNeighborsInfSystemName,
                  cie1000LldpStatusNeighborsInfSystemDescription,
                  cie1000LldpStatusNeighborsInfSystemCapabilities,
                  cie1000LldpStatusNeighborsInfSystemCapabilitiesEnable }
    STATUS      current
    DESCRIPTION
        "A collection of objects."
    ::= { cie1000LldpMibGroups 11 }

cie1000LldpStatusNeighborsMgmtInfInfoGroup OBJECT-GROUP
    OBJECTS     { cie1000LldpStatusNeighborsMgmtInfIfIndex,
                  cie1000LldpStatusNeighborsMgmtInfLldpmedIndex,
                  cie1000LldpStatusNeighborsMgmtInfLldpManagement,
                  cie1000LldpStatusNeighborsMgmtInfSystemMgmAddressSubtype,
                  cie1000LldpStatusNeighborsMgmtInfSystemMgmtAddress,
                  cie1000LldpStatusNeighborsMgmtInfSystemMgmtInterfaceSubtype,
                  cie1000LldpStatusNeighborsMgmtInfSystemMgmtInterface,
                  cie1000LldpStatusNeighborsMgmtInfSystemMgmtOid }
    STATUS      current
    DESCRIPTION
        "A collection of objects."
    ::= { cie1000LldpMibGroups 12 }

cie1000LldpStatusMedRemoteDeviceInfoInfoGroup OBJECT-GROUP
    OBJECTS     { cie1000LldpStatusMedRemoteDeviceInfoIfIndex,
                  cie1000LldpStatusMedRemoteDeviceInfoLldpmedIndex,
                  cie1000LldpStatusMedRemoteDeviceInfoCapabilities,
                  cie1000LldpStatusMedRemoteDeviceInfoCapabilitiesEnabled,
                  cie1000LldpStatusMedRemoteDeviceInfoLatitude,
                  cie1000LldpStatusMedRemoteDeviceInfoLongitude,
                  cie1000LldpStatusMedRemoteDeviceInfoAltitudeType,
                  cie1000LldpStatusMedRemoteDeviceInfoAltitude,
                  cie1000LldpStatusMedRemoteDeviceInfoDatum,
                  cie1000LldpStatusMedRemoteDeviceInfoElinaddr,
                  cie1000LldpStatusMedRemoteDeviceInfoDeviceType,
                  cie1000LldpStatusMedRemoteDeviceInfoHwRev,
                  cie1000LldpStatusMedRemoteDeviceInfoFwRev,
                  cie1000LldpStatusMedRemoteDeviceInfoSwRev,
                  cie1000LldpStatusMedRemoteDeviceInfoSerialNo,
                  cie1000LldpStatusMedRemoteDeviceInfoManufacturerName,
                  cie1000LldpStatusMedRemoteDeviceInfoModelName,
                  cie1000LldpStatusMedRemoteDeviceInfoAssetId,
                  cie1000LldpStatusMedRemoteDeviceInfoEeeRxTwSys,
                  cie1000LldpStatusMedRemoteDeviceInfoEeeTxTwSys,
                  cie1000LldpStatusMedRemoteDeviceInfoEeeFbTwSys,
                  cie1000LldpStatusMedRemoteDeviceInfoEeeTxTwSysEcho,
                  cie1000LldpStatusMedRemoteDeviceInfoEeeRxTwSysEcho }
    STATUS      current
    DESCRIPTION
        "A collection of objects."
    ::= { cie1000LldpMibGroups 13 }

cie1000LldpStatusMedRemoteDeviceLocInfoInfoGroup OBJECT-GROUP
    OBJECTS     { cie1000LldpStatusMedRemoteDeviceLocInfoIfIndex,
                  cie1000LldpStatusMedRemoteDeviceLocInfoLldpmedIndex,
                  cie1000LldpStatusMedRemoteDeviceLocInfoState,
                  cie1000LldpStatusMedRemoteDeviceLocInfoCounty,
                  cie1000LldpStatusMedRemoteDeviceLocInfoCity,
                  cie1000LldpStatusMedRemoteDeviceLocInfoDistrict,
                  cie1000LldpStatusMedRemoteDeviceLocInfoBlock,
                  cie1000LldpStatusMedRemoteDeviceLocInfoStreet,
                  cie1000LldpStatusMedRemoteDeviceLocInfoLeadingStreetDirection,
                  cie1000LldpStatusMedRemoteDeviceLocInfoTrailingStreetSuffix,
                  cie1000LldpStatusMedRemoteDeviceLocInfoStreetSuffix,
                  cie1000LldpStatusMedRemoteDeviceLocInfoHouseNo,
                  cie1000LldpStatusMedRemoteDeviceLocInfoHouseNoSuffix,
                  cie1000LldpStatusMedRemoteDeviceLocInfoLandmark,
                  cie1000LldpStatusMedRemoteDeviceLocInfoAdditionalInfo,
                  cie1000LldpStatusMedRemoteDeviceLocInfoName,
                  cie1000LldpStatusMedRemoteDeviceLocInfoZipCode,
                  cie1000LldpStatusMedRemoteDeviceLocInfoBuilding,
                  cie1000LldpStatusMedRemoteDeviceLocInfoApartment,
                  cie1000LldpStatusMedRemoteDeviceLocInfoFloor,
                  cie1000LldpStatusMedRemoteDeviceLocInfoRoomNumber,
                  cie1000LldpStatusMedRemoteDeviceLocInfoPlaceType,
                  cie1000LldpStatusMedRemoteDeviceLocInfoPostalCommunityName,
                  cie1000LldpStatusMedRemoteDeviceLocInfoPoBox,
                  cie1000LldpStatusMedRemoteDeviceLocInfoAdditionalCode,
                  cie1000LldpStatusMedRemoteDeviceLocInfoCountryCode }
    STATUS      current
    DESCRIPTION
        "A collection of objects."
    ::= { cie1000LldpMibGroups 14 }

cie1000LldpStatusMedRemoteDeviceNetworkPolicyInfoInfoGroup OBJECT-GROUP
    OBJECTS     {                   cie1000LldpStatusMedRemoteDeviceNetworkPolicyInfoIfIndex,
                  cie1000LldpStatusMedRemoteDeviceNetworkPolicyInfoLldpmedIndex,
                  cie1000LldpStatusMedRemoteDeviceNetworkPolicyInfoLldpmedPolicy,
                  cie1000LldpStatusMedRemoteDeviceNetworkPolicyInfoApplicationType,
                  cie1000LldpStatusMedRemoteDeviceNetworkPolicyInfoUnknownPolicy,
                  cie1000LldpStatusMedRemoteDeviceNetworkPolicyInfoTagged,
                  cie1000LldpStatusMedRemoteDeviceNetworkPolicyInfoVlanId,
                  cie1000LldpStatusMedRemoteDeviceNetworkPolicyInfoL2Priority,
                  cie1000LldpStatusMedRemoteDeviceNetworkPolicyInfoDscp }
    STATUS      current
    DESCRIPTION
        "A collection of objects."
    ::= { cie1000LldpMibGroups 15 }

cie1000LldpControlStatisticsClearTableInfoGroup OBJECT-GROUP
    OBJECTS     { cie1000LldpControlStatisticsClearIfIndex,
                  cie1000LldpControlStatisticsClearStatisticsClear }
    STATUS      current
    DESCRIPTION
        "A collection of objects."
    ::= { cie1000LldpMibGroups 16 }

cie1000LldpControlStatisticsClearGlobalInfoGroup OBJECT-GROUP
    OBJECTS     { cie1000LldpControlStatisticsClearGlobalClear }
    STATUS      current
    DESCRIPTION
        "A collection of objects."
    ::= { cie1000LldpMibGroups 17 }

cie1000LldpMibCompliance MODULE-COMPLIANCE
    STATUS      current
    DESCRIPTION
        "The compliance statement for the implementation."

    MODULE      -- this module

    MANDATORY-GROUPS { cie1000LldpConfigGlobalInfoGroup,
                       cie1000LldpConfigInfoGroup,
                       cie1000LldpConfigMedInfoGroup,
                       cie1000LldpConfigMedPolicyInfoGroup,
                       cie1000LldpConfigMedPolicyListInfoGroup,
                       cie1000LldpConfigMedGlobalInfoGroup,
                       cie1000LldpConfigMedLocationInfInfoGroup,
                       cie1000LldpConfigMedPolicyRowEditorInfoGroup,
                       cie1000LldpStatusStatisticsGlobalCountersInfoGroup,
                       cie1000LldpStatusStatisticsTableInfoGroup,
                       cie1000LldpStatusNeighborsInfInfoGroup,
                       cie1000LldpStatusNeighborsMgmtInfInfoGroup,
                       cie1000LldpStatusMedRemoteDeviceInfoInfoGroup,
                       cie1000LldpStatusMedRemoteDeviceLocInfoInfoGroup,
                       cie1000LldpStatusMedRemoteDeviceNetworkPolicyInfoInfoGroup,
                       cie1000LldpControlStatisticsClearTableInfoGroup,
                       cie1000LldpControlStatisticsClearGlobalInfoGroup }

    ::= { cie1000LldpMibCompliances 1 }

END
