-- *****************************************************************
-- ciscoMgx82xxRpmRsrcPartMIB
--
-- * Resource Partition MIB for RPM router blade
--   in MGX82xx products
--
-- September 2002, Subra Hegde
--
-- Copyright (c) 2002 by cisco Systems, Inc.
-- All rights reserved.
-- *****************************************************************

CISCO-MGX82XX-RPM-RSRC-PART-MIB DEFINITIONS ::= BEGIN
IMPORTS
    MODULE-IDENTITY,
    OBJECT-TYPE,
    Integer32
                         FROM SNMPv2-SMI
    MODULE-COMPLIANCE,
    OBJECT-GROUP 	 FROM SNMPv2-CONF
    rpmInterface         FROM BASIS-MIB
    ciscoWan       	 FROM CISCOWAN-SMI;

ciscoMgx82xxRpmRsrcPartMIB MODULE-IDENTITY
    LAST-UPDATED   "200209170000Z"
    ORGANIZATION   "Cisco Systems, Inc."
    CONTACT-INFO
                   "Cisco Systems
                    Customer Service

            Postal: 170 W Tasman Drive
                    San Jose, CA  95134
                    USA

              Tel: +1 800 553-NETS

            E-mail: cs-wanatm@cisco.com"

    DESCRIPTION
        "The MIB module to manage resource partition objects.
        A resource partition is configured on a RPM subinterface.
        An administrator can partition connection related
        resources like VPI, VCI ranges, bandwidth and total
        amount of available connection entries in the switch
        through these MIB tables."

    REVISION    "200209170000Z"
    DESCRIPTION
        "Initial version of the MIB.

        The content of this MIB was originally available
        in CISCO-WAN-AXIPOP-MIB defined using SMIv1.
        The applicable objects from CISCO-WAN-AXIPOP-MIB
        are defined using SMIv2 in this MIB. Also the
        descriptions of some of the objects have been
        modified."
    ::= {ciscoWan 61 }

rpmIfCnfResPart  OBJECT IDENTIFIER ::= { rpmInterface 2 }

rpmIfCnfRscPartTable  OBJECT-TYPE
    SYNTAX     SEQUENCE OF RpmIfCnfRscPartEntry
    MAX-ACCESS not-accessible
    STATUS     current
    DESCRIPTION
       "The table is for RPM interface
       resource partition."
    ::= { rpmIfCnfResPart 1 }

rpmIfCnfRscPartEntry  OBJECT-TYPE
    SYNTAX     RpmIfCnfRscPartEntry
    MAX-ACCESS not-accessible
    STATUS     current
    DESCRIPTION
        "An entry for resource partition configuration
        on a logical interface. A resource partition need
        to be configured before connections(or connection endpoints)
        can be added to the interface."
    INDEX   { rpmIfRscSlotNum, rpmIfRscPartIfNum, rpmIfRscPartCtrlrNum }
    ::= { rpmIfCnfRscPartTable 1 }

RpmIfCnfRscPartEntry ::=
    SEQUENCE {
	rpmIfRscSlotNum             Integer32,
        rpmIfRscPartIfNum           Integer32,
        rpmIfRscPartCtrlrNum        INTEGER,
        rpmIfRscPrtRowStatus        INTEGER,
        rpmIfRscPrtIngrPctBandwidth Integer32,
        rpmIfRscPrtEgrPctBandwidth  Integer32,
        rpmIfRscPrtVpiLow           Integer32,
        rpmIfRscPrtVpiHigh          Integer32,
        rpmIfRscPrtVciLow           Integer32,
        rpmIfRscPrtVciHigh          Integer32,
        rpmIfRscPrtMaxChans         Integer32
    }

rpmIfRscSlotNum OBJECT-TYPE
    SYNTAX     Integer32 (1..30)
    MAX-ACCESS read-only
    STATUS     current
    DESCRIPTION
        "This object identifies the slot number of the
        RPM card in MGX shelf."
    ::= { rpmIfCnfRscPartEntry 1}

rpmIfRscPartIfNum OBJECT-TYPE
    SYNTAX     Integer32(1..2147483647)
    MAX-ACCESS read-only
    STATUS     current
    DESCRIPTION
        "This is backplane interface number.
        Currently there is only one interface and value
        1 is the only value supported."
    ::= { rpmIfCnfRscPartEntry 2}

rpmIfRscPartCtrlrNum OBJECT-TYPE
	SYNTAX  INTEGER {
		par  (1),
		pnni (2),
		tag  (3)
	}
    MAX-ACCESS read-only
    STATUS     current
    DESCRIPTION
       "This object identifies the type of the controller
       which owns the resource partition.

        par(1) : Portable Auto Route Controller. This is a controller
                 software implementing Cisco Proprietary protocol
                 for network routing and topology.

        pnni(2): Private Network-to-Network Interface(PNNI)
                 controller. This is a controller implementing
                 ATM Forum PNNI protocol for routing.

        tag(3) : Tag Switching(MPLS) controller. This is
                 a controller supporting MPLS protocol."
    ::= { rpmIfCnfRscPartEntry 3}

rpmIfRscPrtRowStatus OBJECT-TYPE
    SYNTAX  INTEGER {
                add (1),
                del (2),
                mod (3)
            }
    MAX-ACCESS read-only
    STATUS     current
    DESCRIPTION
        "This object contains the information on whether
        subinterface exists or being modified.

        add(1)  : sub-interface exists
        del(2)  : sub-interface deleted
        mod(2)  : sub-interface being modified"
    DEFVAL { del }
    ::= { rpmIfCnfRscPartEntry 4}

rpmIfRscPrtIngrPctBandwidth OBJECT-TYPE
    SYNTAX     Integer32 (0..100)
    MAX-ACCESS read-only
    STATUS     current
    DESCRIPTION
        "The percentage of logical interface bandwidth."
    DEFVAL { 0 }
    ::= { rpmIfCnfRscPartEntry 5 }

rpmIfRscPrtEgrPctBandwidth OBJECT-TYPE
    SYNTAX     Integer32 (0..100)
    MAX-ACCESS read-only
    STATUS     current
    DESCRIPTION
        "The percentage of logical interface bandwidth."
    DEFVAL { 0 }
    ::= { rpmIfCnfRscPartEntry 6 }

rpmIfRscPrtVpiLow OBJECT-TYPE
    SYNTAX     Integer32 (0..255)
    MAX-ACCESS read-only
    STATUS     current
    DESCRIPTION
        "The beginning of the VPI range
        reserved for this partition."
    ::= { rpmIfCnfRscPartEntry 7 }

rpmIfRscPrtVpiHigh OBJECT-TYPE
    SYNTAX     Integer32 (0..255)
    MAX-ACCESS read-only
    STATUS     current
    DESCRIPTION
        "The end of the VPI range
        reserved for this partition."
    ::= { rpmIfCnfRscPartEntry 8 }

rpmIfRscPrtVciLow OBJECT-TYPE
    SYNTAX     Integer32 (0..65535)
    MAX-ACCESS read-only
    STATUS     current
    DESCRIPTION
        "The beginning of the VCI range reserved
        for this partition.  This field is only
        valid for logical interfaces configured
        with a single VPI."
    ::= { rpmIfCnfRscPartEntry 9 }

rpmIfRscPrtVciHigh OBJECT-TYPE
    SYNTAX     Integer32 (0..65535)
    MAX-ACCESS read-only
    STATUS     current
    DESCRIPTION
        "The end of the VCI range reserved
        for this partition.  This field is
        only valid for logical interfaces
        configured with a single VPI."
    ::= { rpmIfCnfRscPartEntry 10 }

rpmIfRscPrtMaxChans OBJECT-TYPE
    SYNTAX     Integer32 (0..4047)
    MAX-ACCESS read-only
    STATUS     current
    DESCRIPTION
        "This represents maximum number of
        channels(connections) that are available
        to the controller."
    ::= { rpmIfCnfRscPartEntry 11 }

-- conformance information

cmrRsrcPartMIBConformance OBJECT IDENTIFIER ::=
                              {ciscoMgx82xxRpmRsrcPartMIB 3}

cmrRsrcPartMIBCompliances OBJECT IDENTIFIER
                              ::= { cmrRsrcPartMIBConformance 1 }

cmrRsrcPartMIBGroups  OBJECT IDENTIFIER
                          ::= { cmrRsrcPartMIBConformance 2 }

cmrRsrcPartMIBCompliance MODULE-COMPLIANCE
    STATUS current
    DESCRIPTION
       "The Compliance statement for Resource partition
        management group."
    MODULE -- this module
    MANDATORY-GROUPS { cmrRsrcPartMIBGroup }
    ::={ cmrRsrcPartMIBCompliances 1 }

-- units of conformance
cmrRsrcPartMIBGroup OBJECT-GROUP
        OBJECTS {
	    rpmIfRscSlotNum,
            rpmIfRscPartIfNum,
            rpmIfRscPartCtrlrNum,
            rpmIfRscPrtRowStatus,
            rpmIfRscPrtIngrPctBandwidth,
            rpmIfRscPrtEgrPctBandwidth,
            rpmIfRscPrtVpiLow,
            rpmIfRscPrtVpiHigh,
            rpmIfRscPrtVciLow,
            rpmIfRscPrtVciHigh,
            rpmIfRscPrtMaxChans
        }
       STATUS current
       DESCRIPTION
          "The collection of objects related to
          configuration of Resource partition."
       ::={ cmrRsrcPartMIBGroups 1}

END
