-- *****************************************************************
-- PORT-MIB:  Cisco private MIB
-- ****************************************************************

CIE1000-PORT-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    cie1000SwitchMgmt FROM CISCO-IE1000-MIB
    CIE1000DisplayString FROM CIE1000-TC
    CIE1000InterfaceIndex FROM CIE1000-TC
    CIE1000PortStatusSpeed FROM CIE1000-TC
    CIE1000SfpTransceiver FROM CIE1000-TC
    CIE1000Unsigned8 FROM CIE1000-TC
    Counter64 FROM SNMPv2-SMI
    Integer32 FROM SNMPv2-SMI
    Unsigned32 FROM SNMPv2-SMI
    TruthValue FROM SNMPv2-TC
    ;

cie1000PortMib MODULE-IDENTITY
    LAST-UPDATED "201507070000Z"
    ORGANIZATION
        "Cisco Systems, Inc."
    CONTACT-INFO
        "Cisco Systems
	 Customer Service

	 Postal: 170 West Tasman Drive
	 San Jose, CA  95134
	 USA

	 Tel: +1 800 553-NETS

	 E-mail: cs-snmp@cisco.com"
    DESCRIPTION
        "This is a private version of the PORT MIB"
    REVISION    "201507070000Z"
    DESCRIPTION
        "Port speed is moved into the TC MIB"
    REVISION    "201407010000Z"
    DESCRIPTION
        "Initial version"
    ::= { cie1000SwitchMgmt 11 }


CIE1000PortFc ::= TEXTUAL-CONVENTION
    STATUS      current
    DESCRIPTION
        "This enumeration controls the interface flow control."
    SYNTAX      INTEGER { off(0), on(1) }

CIE1000PortMedia ::= TEXTUAL-CONVENTION
    STATUS      current
    DESCRIPTION
        "This enumeration controls the interface media type."
    SYNTAX      INTEGER { rj45(0), sfp(1), dual(2) }

CIE1000PortPhyVeriPhyStatus ::= TEXTUAL-CONVENTION
    STATUS      current
    DESCRIPTION
        "This enumerations show the VeriPhy status."
    SYNTAX      INTEGER { correctlyTerminatedPair(0), openPair(1),
                          shortPair(2), abnormalTermination(4),
                          crossPairShortToPairA(8),
                          crossPairShortToPairB(9),
                          crossPairShortToPairC(10),
                          crossPairShortToPairD(11),
                          abnormalCrossPairCouplingToPairA(12),
                          abnormalCrossPairCouplingToPairB(13),
                          abnormalCrossPairCouplingToPairC(14),
                          abnormalCrossPairCouplingToPairD(15),
                          unknownResult(16), veriPhyRunning(17) }

CIE1000PortSpeed ::= TEXTUAL-CONVENTION
    STATUS      current
    DESCRIPTION
        "This enumeration controls the interface speed. E.g force10ModeFdx means
         force 10Mbs full duplex."
    SYNTAX      INTEGER { force10ModeFdx(0), force10ModeHdx(1),
                          force100ModeFdx(2), force100ModeHdx(3),
                          force1GModeFdx(4), autoNegMode(5),
                          force2G5ModeFdx(6), force5GModeFdx(7),
                          force10GModeFdx(8), force12GModeFdx(9) }

cie1000PortMibObjects OBJECT IDENTIFIER
    ::= { cie1000PortMib 1 }

cie1000PortConfig OBJECT IDENTIFIER
    ::= { cie1000PortMibObjects 2 }

cie1000PortConfigTable OBJECT-TYPE
    SYNTAX      SEQUENCE OF CIE1000PortConfigEntry
    MAX-ACCESS  not-accessible
    STATUS      current
    DESCRIPTION
        "This is a table of the port interface parameters"
    ::= { cie1000PortConfig 1 }

cie1000PortConfigEntry OBJECT-TYPE
    SYNTAX      CIE1000PortConfigEntry
    MAX-ACCESS  not-accessible
    STATUS      current
    DESCRIPTION
        "Each port interface has a set of parameters"
    INDEX       { cie1000PortConfigIfIndex }
    ::= { cie1000PortConfigTable 1 }

CIE1000PortConfigEntry ::= SEQUENCE {
    cie1000PortConfigIfIndex            CIE1000InterfaceIndex,
    cie1000PortConfigShutdown           TruthValue,
    cie1000PortConfigSpeed              CIE1000PortSpeed,
    cie1000PortConfigAdvertiseDisabled  CIE1000Unsigned8,
    cie1000PortConfigMediaType          CIE1000PortMedia,
    cie1000PortConfigFC                 CIE1000PortFc,
    cie1000PortConfigMTU                Unsigned32,
    cie1000PortConfigExcessiveRestart   TruthValue,
    cie1000PortConfigPFC                CIE1000Unsigned8,
    cie1000PortConfigFrameLengthCheck   TruthValue
}

cie1000PortConfigIfIndex OBJECT-TYPE
    SYNTAX      CIE1000InterfaceIndex
    MAX-ACCESS  accessible-for-notify
    STATUS      current
    DESCRIPTION
        "Logical interface number."
    ::= { cie1000PortConfigEntry 1 }

cie1000PortConfigShutdown OBJECT-TYPE
    SYNTAX      TruthValue
    MAX-ACCESS  read-write
    STATUS      current
    DESCRIPTION
        "Controls whether interface is shutdown or powered up. Set to TRUE in
         order to power down the interface."
    ::= { cie1000PortConfigEntry 2 }

cie1000PortConfigSpeed OBJECT-TYPE
    SYNTAX      CIE1000PortSpeed
    MAX-ACCESS  read-write
    STATUS      current
    DESCRIPTION
        "Controls the port speed and duplex."
    ::= { cie1000PortConfigEntry 3 }

cie1000PortConfigAdvertiseDisabled OBJECT-TYPE
    SYNTAX      CIE1000Unsigned8
    MAX-ACCESS  read-write
    STATUS      current
    DESCRIPTION
        "In auto mode, bitmask that allows features not to be advertised.

         Bit 0: Disable half duplex advertising.

         Bit 1: Disable full duplex advertising.

         Bit 4: Disable 1G advertising.

         Bit 6: Disable 100M advertising.

         Bit 7: Disable 10M advertising.

         When not in auto mode, the value shall be zero."
    ::= { cie1000PortConfigEntry 4 }

cie1000PortConfigMediaType OBJECT-TYPE
    SYNTAX      CIE1000PortMedia
    MAX-ACCESS  read-write
    STATUS      current
    DESCRIPTION
        "Controls the port media type."
    ::= { cie1000PortConfigEntry 5 }

cie1000PortConfigFC OBJECT-TYPE
    SYNTAX      CIE1000PortFc
    MAX-ACCESS  read-write
    STATUS      current
    DESCRIPTION
        "Controls the port flow control mode."
    ::= { cie1000PortConfigEntry 6 }

cie1000PortConfigMTU OBJECT-TYPE
    SYNTAX      Unsigned32
    MAX-ACCESS  read-write
    STATUS      current
    DESCRIPTION
        "Controls the port's Maximum Transmission Unit."
    ::= { cie1000PortConfigEntry 7 }

cie1000PortConfigExcessiveRestart OBJECT-TYPE
    SYNTAX      TruthValue
    MAX-ACCESS  read-write
    STATUS      current
    DESCRIPTION
        "TRUE to restart half-duplex back-off algorithm after 16 collisions.
         FALSE to discard frame after 16 collisions"
    ::= { cie1000PortConfigEntry 8 }

cie1000PortConfigPFC OBJECT-TYPE
    SYNTAX      CIE1000Unsigned8
    MAX-ACCESS  read-write
    STATUS      current
    DESCRIPTION
        "802.1Qbb Priority Flow Control bitmask, one bit for each prioritet.E.g.
         0x01 = prio 0, 0x80 = prio 7, 0xFF = prio 0-7"
    ::= { cie1000PortConfigEntry 9 }

cie1000PortConfigFrameLengthCheck OBJECT-TYPE
    SYNTAX      TruthValue
    MAX-ACCESS  read-write
    STATUS      current
    DESCRIPTION
        "TRUE to enforce 802.3 frame length check (from Ethertype field). If
         enabled frames with length that doesn't match the frame length field
         will be dropped."
    ::= { cie1000PortConfigEntry 10 }

cie1000PortStatus OBJECT IDENTIFIER
    ::= { cie1000PortMibObjects 3 }

cie1000PortStatusInformationTable OBJECT-TYPE
    SYNTAX      SEQUENCE OF CIE1000PortStatusInformationEntry
    MAX-ACCESS  not-accessible
    STATUS      current
    DESCRIPTION
        "This table represents the status of the ports"
    ::= { cie1000PortStatus 1 }

cie1000PortStatusInformationEntry OBJECT-TYPE
    SYNTAX      CIE1000PortStatusInformationEntry
    MAX-ACCESS  not-accessible
    STATUS      current
    DESCRIPTION
        "Each port interface has a set of status parameters"
    INDEX       { cie1000PortStatusInformationIfIndex }
    ::= { cie1000PortStatusInformationTable 1 }

CIE1000PortStatusInformationEntry ::= SEQUENCE {
    cie1000PortStatusInformationIfIndex             CIE1000InterfaceIndex,
    cie1000PortStatusInformationLink                TruthValue,
    cie1000PortStatusInformationFdx                 TruthValue,
    cie1000PortStatusInformationFiber               TruthValue,
    cie1000PortStatusInformationSpeed               CIE1000PortStatusSpeed,
    cie1000PortStatusInformationSFPType             CIE1000SfpTransceiver,
    cie1000PortStatusInformationSFPVendorName       CIE1000DisplayString,
    cie1000PortStatusInformationSFPVendorPN         CIE1000DisplayString,
    cie1000PortStatusInformationSFPVendorRev        CIE1000DisplayString,
    cie1000PortStatusInformationSFPVendorSN         CIE1000DisplayString,
    cie1000PortStatusInformationRxUtilization       Unsigned32,
    cie1000PortStatusInformationTxUtilization       Unsigned32,
    cie1000PortStatusInformationRxErrorUtilization  Unsigned32,
    cie1000PortStatusInformationTxErrorUtilization  Unsigned32
}

cie1000PortStatusInformationIfIndex OBJECT-TYPE
    SYNTAX      CIE1000InterfaceIndex
    MAX-ACCESS  accessible-for-notify
    STATUS      current
    DESCRIPTION
        "Logical interface number."
    ::= { cie1000PortStatusInformationEntry 1 }

cie1000PortStatusInformationLink OBJECT-TYPE
    SYNTAX      TruthValue
    MAX-ACCESS  read-only
    STATUS      current
    DESCRIPTION
        "Shows whether interface has link."
    ::= { cie1000PortStatusInformationEntry 2 }

cie1000PortStatusInformationFdx OBJECT-TYPE
    SYNTAX      TruthValue
    MAX-ACCESS  read-only
    STATUS      current
    DESCRIPTION
        "Shows whether interface is running in full duplex."
    ::= { cie1000PortStatusInformationEntry 3 }

cie1000PortStatusInformationFiber OBJECT-TYPE
    SYNTAX      TruthValue
    MAX-ACCESS  read-only
    STATUS      current
    DESCRIPTION
        "Shows whether interface is a fiber link (fiber SFP or cu SFP)."
    ::= { cie1000PortStatusInformationEntry 4 }

cie1000PortStatusInformationSpeed OBJECT-TYPE
    SYNTAX      CIE1000PortStatusSpeed
    MAX-ACCESS  read-only
    STATUS      current
    DESCRIPTION
        "Shows the current interface speed."
    ::= { cie1000PortStatusInformationEntry 5 }

cie1000PortStatusInformationSFPType OBJECT-TYPE
    SYNTAX      CIE1000SfpTransceiver
    MAX-ACCESS  read-only
    STATUS      current
    DESCRIPTION
        "Shows the current interface SFP type."
    ::= { cie1000PortStatusInformationEntry 6 }

cie1000PortStatusInformationSFPVendorName OBJECT-TYPE
    SYNTAX      CIE1000DisplayString (SIZE(0..19))
    MAX-ACCESS  read-only
    STATUS      current
    DESCRIPTION
        "Shows the SFP vendor name."
    ::= { cie1000PortStatusInformationEntry 7 }

cie1000PortStatusInformationSFPVendorPN OBJECT-TYPE
    SYNTAX      CIE1000DisplayString (SIZE(0..19))
    MAX-ACCESS  read-only
    STATUS      current
    DESCRIPTION
        "Shows the SFP vendor Product Number."
    ::= { cie1000PortStatusInformationEntry 8 }

cie1000PortStatusInformationSFPVendorRev OBJECT-TYPE
    SYNTAX      CIE1000DisplayString (SIZE(0..5))
    MAX-ACCESS  read-only
    STATUS      current
    DESCRIPTION
        "Shows the SFP vendor Revision."
    ::= { cie1000PortStatusInformationEntry 9 }

cie1000PortStatusInformationSFPVendorSN OBJECT-TYPE
    SYNTAX      CIE1000DisplayString (SIZE(0..19))
    MAX-ACCESS  read-only
    STATUS      current
    DESCRIPTION
        "Shows the SFP vendor Serial Number."
    ::= { cie1000PortStatusInformationEntry 10 }

cie1000PortStatusInformationRxUtilization OBJECT-TYPE
    SYNTAX      Unsigned32
    MAX-ACCESS  read-only
    STATUS      current
    DESCRIPTION
        "Rx utilization in percent."
    ::= { cie1000PortStatusInformationEntry 11 }

cie1000PortStatusInformationTxUtilization OBJECT-TYPE
    SYNTAX      Unsigned32
    MAX-ACCESS  read-only
    STATUS      current
    DESCRIPTION
        "Tx utilization in percent."
    ::= { cie1000PortStatusInformationEntry 12 }

cie1000PortStatusInformationRxErrorUtilization OBJECT-TYPE
    SYNTAX      Unsigned32
    MAX-ACCESS  read-only
    STATUS      current
    DESCRIPTION
        "Rx error utilization in percent."
    ::= { cie1000PortStatusInformationEntry 13 }

cie1000PortStatusInformationTxErrorUtilization OBJECT-TYPE
    SYNTAX      Unsigned32
    MAX-ACCESS  read-only
    STATUS      current
    DESCRIPTION
        "Tx error utilization in percent."
    ::= { cie1000PortStatusInformationEntry 14 }

cie1000PortStatusVeriPhyResult OBJECT IDENTIFIER
    ::= { cie1000PortStatus 3 }

cie1000PortStatusVeriPhyResultTable OBJECT-TYPE
    SYNTAX      SEQUENCE OF CIE1000PortStatusVeriPhyResultEntry
    MAX-ACCESS  not-accessible
    STATUS      current
    DESCRIPTION
        "This table represents the VeriPhy result from the last VeriPhy run for
         the interface"
    ::= { cie1000PortStatusVeriPhyResult 1 }

cie1000PortStatusVeriPhyResultEntry OBJECT-TYPE
    SYNTAX      CIE1000PortStatusVeriPhyResultEntry
    MAX-ACCESS  not-accessible
    STATUS      current
    DESCRIPTION
        "Each port has a set of VeriPhy results"
    INDEX       { cie1000PortStatusVeriPhyResultIfIndex }
    ::= { cie1000PortStatusVeriPhyResultTable 1 }

CIE1000PortStatusVeriPhyResultEntry ::= SEQUENCE {
    cie1000PortStatusVeriPhyResultIfIndex                   CIE1000InterfaceIndex,
    cie1000PortStatusVeriPhyResultVeriPhyStatusPairA        CIE1000PortPhyVeriPhyStatus,
    cie1000PortStatusVeriPhyResultVeriPhyStatusPairB        CIE1000PortPhyVeriPhyStatus,
    cie1000PortStatusVeriPhyResultVeriPhyStatusPairC        CIE1000PortPhyVeriPhyStatus,
    cie1000PortStatusVeriPhyResultVeriPhyStatusPairD        CIE1000PortPhyVeriPhyStatus,
    cie1000PortStatusVeriPhyResultVeriPhyLengthStatusPairA  CIE1000Unsigned8,
    cie1000PortStatusVeriPhyResultVeriPhyLengthStatusPairB  CIE1000Unsigned8,
    cie1000PortStatusVeriPhyResultVeriPhyLengthStatusPairC  CIE1000Unsigned8,
    cie1000PortStatusVeriPhyResultVeriPhyLengthStatusPairD  CIE1000Unsigned8
}

cie1000PortStatusVeriPhyResultIfIndex OBJECT-TYPE
    SYNTAX      CIE1000InterfaceIndex
    MAX-ACCESS  accessible-for-notify
    STATUS      current
    DESCRIPTION
        "Logical interface number."
    ::= { cie1000PortStatusVeriPhyResultEntry 1 }

cie1000PortStatusVeriPhyResultVeriPhyStatusPairA OBJECT-TYPE
    SYNTAX      CIE1000PortPhyVeriPhyStatus
    MAX-ACCESS  read-only
    STATUS      current
    DESCRIPTION
        "VeriPhy status for the cable pair

         0 - Cable is Correctly terminated pair

         1 - Open pair

         2 - Shorted pair

         4 - Abnormal termination

         8 - Cross-pair short to pair A

         9 - Cross-pair short to pair B

         10 - Cross-pair short to pair C

         11 - Cross-pair short to pair D

         12 - Abnormal cross-pair coupling - pair A

         13 - Abnormal cross-pair coupling - pair B

         14 - Abnormal cross-pair coupling - pair C

         15 - Abnormal cross-pair coupling - pair D"
    ::= { cie1000PortStatusVeriPhyResultEntry 2 }

cie1000PortStatusVeriPhyResultVeriPhyStatusPairB OBJECT-TYPE
    SYNTAX      CIE1000PortPhyVeriPhyStatus
    MAX-ACCESS  read-only
    STATUS      current
    DESCRIPTION
        "VeriPhy status for the cable pair

         0 - Cable is Correctly terminated pair

         1 - Open pair

         2 - Shorted pair

         4 - Abnormal termination

         8 - Cross-pair short to pair A

         9 - Cross-pair short to pair B

         10 - Cross-pair short to pair C

         11 - Cross-pair short to pair D

         12 - Abnormal cross-pair coupling - pair A

         13 - Abnormal cross-pair coupling - pair B

         14 - Abnormal cross-pair coupling - pair C

         15 - Abnormal cross-pair coupling - pair D"
    ::= { cie1000PortStatusVeriPhyResultEntry 3 }

cie1000PortStatusVeriPhyResultVeriPhyStatusPairC OBJECT-TYPE
    SYNTAX      CIE1000PortPhyVeriPhyStatus
    MAX-ACCESS  read-only
    STATUS      current
    DESCRIPTION
        "VeriPhy status for the cable pair

         0 - Cable is Correctly terminated pair

         1 - Open pair

         2 - Shorted pair

         4 - Abnormal termination

         8 - Cross-pair short to pair A

         9 - Cross-pair short to pair B

         10 - Cross-pair short to pair C

         11 - Cross-pair short to pair D

         12 - Abnormal cross-pair coupling - pair A

         13 - Abnormal cross-pair coupling - pair B

         14 - Abnormal cross-pair coupling - pair C

         15 - Abnormal cross-pair coupling - pair D"
    ::= { cie1000PortStatusVeriPhyResultEntry 4 }

cie1000PortStatusVeriPhyResultVeriPhyStatusPairD OBJECT-TYPE
    SYNTAX      CIE1000PortPhyVeriPhyStatus
    MAX-ACCESS  read-only
    STATUS      current
    DESCRIPTION
        "VeriPhy status for the cable pair

         0 - Cable is Correctly terminated pair

         1 - Open pair

         2 - Shorted pair

         4 - Abnormal termination

         8 - Cross-pair short to pair A

         9 - Cross-pair short to pair B

         10 - Cross-pair short to pair C

         11 - Cross-pair short to pair D

         12 - Abnormal cross-pair coupling - pair A

         13 - Abnormal cross-pair coupling - pair B

         14 - Abnormal cross-pair coupling - pair C

         15 - Abnormal cross-pair coupling - pair D"
    ::= { cie1000PortStatusVeriPhyResultEntry 5 }

cie1000PortStatusVeriPhyResultVeriPhyLengthStatusPairA OBJECT-TYPE
    SYNTAX      CIE1000Unsigned8
    MAX-ACCESS  read-only
    STATUS      current
    DESCRIPTION
        "VeriPhy status cable length i meters for the cable pair. When VeriPhy
         is completed, the cable diagnostics results is shown in the VeriPhy
         status table. Note that VeriPHY is only accurate for cables of length 7
         - 140 meters.

         The resolution is 3 meters"
    ::= { cie1000PortStatusVeriPhyResultEntry 6 }

cie1000PortStatusVeriPhyResultVeriPhyLengthStatusPairB OBJECT-TYPE
    SYNTAX      CIE1000Unsigned8
    MAX-ACCESS  read-only
    STATUS      current
    DESCRIPTION
        "VeriPhy status cable length i meters for the cable pair. When VeriPhy
         is completed, the cable diagnostics results is shown in the VeriPhy
         status table. Note that VeriPHY is only accurate for cables of length 7
         - 140 meters.

         The resolution is 3 meters"
    ::= { cie1000PortStatusVeriPhyResultEntry 7 }

cie1000PortStatusVeriPhyResultVeriPhyLengthStatusPairC OBJECT-TYPE
    SYNTAX      CIE1000Unsigned8
    MAX-ACCESS  read-only
    STATUS      current
    DESCRIPTION
        "VeriPhy status cable length i meters for the cable pair. When VeriPhy
         is completed, the cable diagnostics results is shown in the VeriPhy
         status table. Note that VeriPHY is only accurate for cables of length 7
         - 140 meters.

         The resolution is 3 meters"
    ::= { cie1000PortStatusVeriPhyResultEntry 8 }

cie1000PortStatusVeriPhyResultVeriPhyLengthStatusPairD OBJECT-TYPE
    SYNTAX      CIE1000Unsigned8
    MAX-ACCESS  read-only
    STATUS      current
    DESCRIPTION
        "VeriPhy status cable length i meters for the cable pair. When VeriPhy
         is completed, the cable diagnostics results is shown in the VeriPhy
         status table. Note that VeriPHY is only accurate for cables of length 7
         - 140 meters.

         The resolution is 3 meters"
    ::= { cie1000PortStatusVeriPhyResultEntry 9 }

cie1000PortControl OBJECT IDENTIFIER
    ::= { cie1000PortMibObjects 4 }

cie1000PortControlStatisticsClear OBJECT IDENTIFIER
    ::= { cie1000PortControl 1 }

cie1000PortControlStatisticsClearTable OBJECT-TYPE
    SYNTAX      SEQUENCE OF CIE1000PortControlStatisticsClearEntry
    MAX-ACCESS  not-accessible
    STATUS      current
    DESCRIPTION
        "This is a table to clear port Interface statistics"
    ::= { cie1000PortControlStatisticsClear 1 }

cie1000PortControlStatisticsClearEntry OBJECT-TYPE
    SYNTAX      CIE1000PortControlStatisticsClearEntry
    MAX-ACCESS  not-accessible
    STATUS      current
    DESCRIPTION
        "Each port has a set of control parameters"
    INDEX       { cie1000PortControlStatisticsClearIfIndex }
    ::= { cie1000PortControlStatisticsClearTable 1 }

CIE1000PortControlStatisticsClearEntry ::= SEQUENCE {
    cie1000PortControlStatisticsClearIfIndex          CIE1000InterfaceIndex,
    cie1000PortControlStatisticsClearStatisticsClear  TruthValue
}

cie1000PortControlStatisticsClearIfIndex OBJECT-TYPE
    SYNTAX      CIE1000InterfaceIndex
    MAX-ACCESS  accessible-for-notify
    STATUS      current
    DESCRIPTION
        "Logical interface number."
    ::= { cie1000PortControlStatisticsClearEntry 1 }

cie1000PortControlStatisticsClearStatisticsClear OBJECT-TYPE
    SYNTAX      TruthValue
    MAX-ACCESS  read-write
    STATUS      current
    DESCRIPTION
        "Set to TRUE to clear the statistics of an interface."
    ::= { cie1000PortControlStatisticsClearEntry 2 }

cie1000PortControlVeriPhyStart OBJECT IDENTIFIER
    ::= { cie1000PortControl 2 }

cie1000PortControlVeriPhyStartTable OBJECT-TYPE
    SYNTAX      SEQUENCE OF CIE1000PortControlVeriPhyStartEntry
    MAX-ACCESS  not-accessible
    STATUS      current
    DESCRIPTION
        "This is a table to start VeriPhy for the interface"
    ::= { cie1000PortControlVeriPhyStart 1 }

cie1000PortControlVeriPhyStartEntry OBJECT-TYPE
    SYNTAX      CIE1000PortControlVeriPhyStartEntry
    MAX-ACCESS  not-accessible
    STATUS      current
    DESCRIPTION
        "Each port has a set of control parameters"
    INDEX       { cie1000PortControlVeriPhyStartIfIndex }
    ::= { cie1000PortControlVeriPhyStartTable 1 }

CIE1000PortControlVeriPhyStartEntry ::= SEQUENCE {
    cie1000PortControlVeriPhyStartIfIndex  CIE1000InterfaceIndex,
    cie1000PortControlVeriPhyStartStart    TruthValue
}

cie1000PortControlVeriPhyStartIfIndex OBJECT-TYPE
    SYNTAX      CIE1000InterfaceIndex
    MAX-ACCESS  accessible-for-notify
    STATUS      current
    DESCRIPTION
        "Logical interface number."
    ::= { cie1000PortControlVeriPhyStartEntry 1 }

cie1000PortControlVeriPhyStartStart OBJECT-TYPE
    SYNTAX      TruthValue
    MAX-ACCESS  read-write
    STATUS      current
    DESCRIPTION
        "Set to TRUE to start VeriPHy for the interface.

         When running 10 and 100 Mbps, ports will be linked down while running
         VeriPHY. Therefore, running VeriPHY on a 10 or 100 Mbps management port
         will cause the switch to stop responding until VeriPHY is complete."
    ::= { cie1000PortControlVeriPhyStartEntry 2 }

cie1000PortStatistics OBJECT IDENTIFIER
    ::= { cie1000PortMibObjects 5 }

cie1000PortStatisticsRmonStatisticsTable OBJECT-TYPE
    SYNTAX      SEQUENCE OF CIE1000PortStatisticsRmonStatisticsEntry
    MAX-ACCESS  not-accessible
    STATUS      current
    DESCRIPTION
        "This table represents the port interface RMON statistics counters"
    ::= { cie1000PortStatistics 1 }

cie1000PortStatisticsRmonStatisticsEntry OBJECT-TYPE
    SYNTAX      CIE1000PortStatisticsRmonStatisticsEntry
    MAX-ACCESS  not-accessible
    STATUS      current
    DESCRIPTION
        "Each port interface has a set of statistics counters"
    INDEX       { cie1000PortStatisticsRmonStatisticsIfIndex }
    ::= { cie1000PortStatisticsRmonStatisticsTable 1 }

CIE1000PortStatisticsRmonStatisticsEntry ::= SEQUENCE {
    cie1000PortStatisticsRmonStatisticsIfIndex            CIE1000InterfaceIndex,
    cie1000PortStatisticsRmonStatisticsRxDropEvents       Counter64,
    cie1000PortStatisticsRmonStatisticsRxOctets           Counter64,
    cie1000PortStatisticsRmonStatisticsRxPkts             Counter64,
    cie1000PortStatisticsRmonStatisticsRxBroadcastPkts    Counter64,
    cie1000PortStatisticsRmonStatisticsRxMulticastPkts    Counter64,
    cie1000PortStatisticsRmonStatisticsRxCrcAlignErrPkts  Counter64,
    cie1000PortStatisticsRmonStatisticsRxUndersizePkts    Counter64,
    cie1000PortStatisticsRmonStatisticsRxOversizePkts     Counter64,
    cie1000PortStatisticsRmonStatisticsRxFragmentsPkts    Counter64,
    cie1000PortStatisticsRmonStatisticsRxJabbersPkts      Counter64,
    cie1000PortStatisticsRmonStatisticsRx64Pkts           Counter64,
    cie1000PortStatisticsRmonStatisticsRx65to127Pkts      Counter64,
    cie1000PortStatisticsRmonStatisticsRx128to255Pkts     Counter64,
    cie1000PortStatisticsRmonStatisticsRx256to511Pkts     Counter64,
    cie1000PortStatisticsRmonStatisticsRx512to1023Pkts    Counter64,
    cie1000PortStatisticsRmonStatisticsRx1024to1518Pkts   Counter64,
    cie1000PortStatisticsRmonStatisticsRx1519PktsToMax    Counter64,
    cie1000PortStatisticsRmonStatisticsTxDropEvents       Counter64,
    cie1000PortStatisticsRmonStatisticsTxOctets           Counter64,
    cie1000PortStatisticsRmonStatisticsTxPkts             Counter64,
    cie1000PortStatisticsRmonStatisticsTxBroadcastPkts    Counter64,
    cie1000PortStatisticsRmonStatisticsTxMulticastPkts    Counter64,
    cie1000PortStatisticsRmonStatisticsTx64Pkts           Counter64,
    cie1000PortStatisticsRmonStatisticsTx65to127Pkts      Counter64,
    cie1000PortStatisticsRmonStatisticsTx128to255Pkts     Counter64,
    cie1000PortStatisticsRmonStatisticsTx256to511Pkts     Counter64,
    cie1000PortStatisticsRmonStatisticsTx512to1023Pkts    Counter64,
    cie1000PortStatisticsRmonStatisticsTx1024to1518Pkts   Counter64,
    cie1000PortStatisticsRmonStatisticsTx1519PktsToMax    Counter64
}

cie1000PortStatisticsRmonStatisticsIfIndex OBJECT-TYPE
    SYNTAX      CIE1000InterfaceIndex
    MAX-ACCESS  accessible-for-notify
    STATUS      current
    DESCRIPTION
        "Logical interface number."
    ::= { cie1000PortStatisticsRmonStatisticsEntry 1 }

cie1000PortStatisticsRmonStatisticsRxDropEvents OBJECT-TYPE
    SYNTAX      Counter64
    MAX-ACCESS  read-only
    STATUS      current
    DESCRIPTION
        "Shows the number of frames discarded due to ingress congestion."
    ::= { cie1000PortStatisticsRmonStatisticsEntry 2 }

cie1000PortStatisticsRmonStatisticsRxOctets OBJECT-TYPE
    SYNTAX      Counter64
    MAX-ACCESS  read-only
    STATUS      current
    DESCRIPTION
        "Shows the number of received (good and bad) bytes. Includes FCS, but
         excludes framing bits."
    ::= { cie1000PortStatisticsRmonStatisticsEntry 3 }

cie1000PortStatisticsRmonStatisticsRxPkts OBJECT-TYPE
    SYNTAX      Counter64
    MAX-ACCESS  read-only
    STATUS      current
    DESCRIPTION
        "Shows the number of received (good and bad) packets."
    ::= { cie1000PortStatisticsRmonStatisticsEntry 4 }

cie1000PortStatisticsRmonStatisticsRxBroadcastPkts OBJECT-TYPE
    SYNTAX      Counter64
    MAX-ACCESS  read-only
    STATUS      current
    DESCRIPTION
        "Shows the number of received (good and bad) broadcast packets."
    ::= { cie1000PortStatisticsRmonStatisticsEntry 5 }

cie1000PortStatisticsRmonStatisticsRxMulticastPkts OBJECT-TYPE
    SYNTAX      Counter64
    MAX-ACCESS  read-only
    STATUS      current
    DESCRIPTION
        "Shows the number of received (good and bad) multicast packets."
    ::= { cie1000PortStatisticsRmonStatisticsEntry 6 }

cie1000PortStatisticsRmonStatisticsRxCrcAlignErrPkts OBJECT-TYPE
    SYNTAX      Counter64
    MAX-ACCESS  read-only
    STATUS      current
    DESCRIPTION
        "Shows the number of frames received with CRC or alignment errors."
    ::= { cie1000PortStatisticsRmonStatisticsEntry 7 }

cie1000PortStatisticsRmonStatisticsRxUndersizePkts OBJECT-TYPE
    SYNTAX      Counter64
    MAX-ACCESS  read-only
    STATUS      current
    DESCRIPTION
        "Shows the number of short frames (frames that are smaller than 64
         bytes) received with valid CRC."
    ::= { cie1000PortStatisticsRmonStatisticsEntry 8 }

cie1000PortStatisticsRmonStatisticsRxOversizePkts OBJECT-TYPE
    SYNTAX      Counter64
    MAX-ACCESS  read-only
    STATUS      current
    DESCRIPTION
        "Shows the number of long frames received with valid CRC."
    ::= { cie1000PortStatisticsRmonStatisticsEntry 9 }

cie1000PortStatisticsRmonStatisticsRxFragmentsPkts OBJECT-TYPE
    SYNTAX      Counter64
    MAX-ACCESS  read-only
    STATUS      current
    DESCRIPTION
        "Shows the number of short frames (frames that are smaller than 64
         bytes) received with invalid CRC."
    ::= { cie1000PortStatisticsRmonStatisticsEntry 10 }

cie1000PortStatisticsRmonStatisticsRxJabbersPkts OBJECT-TYPE
    SYNTAX      Counter64
    MAX-ACCESS  read-only
    STATUS      current
    DESCRIPTION
        "The number of long frames (frames that are longer than the configured
         maximum frame length for this interface) received with invalid CRC."
    ::= { cie1000PortStatisticsRmonStatisticsEntry 11 }

cie1000PortStatisticsRmonStatisticsRx64Pkts OBJECT-TYPE
    SYNTAX      Counter64
    MAX-ACCESS  read-only
    STATUS      current
    DESCRIPTION
        "The number of 64 bytes frames received."
    ::= { cie1000PortStatisticsRmonStatisticsEntry 12 }

cie1000PortStatisticsRmonStatisticsRx65to127Pkts OBJECT-TYPE
    SYNTAX      Counter64
    MAX-ACCESS  read-only
    STATUS      current
    DESCRIPTION
        "The number of received frames with size within 65 to 127 bytes."
    ::= { cie1000PortStatisticsRmonStatisticsEntry 13 }

cie1000PortStatisticsRmonStatisticsRx128to255Pkts OBJECT-TYPE
    SYNTAX      Counter64
    MAX-ACCESS  read-only
    STATUS      current
    DESCRIPTION
        "The number of received frames with size within 128 to 255 bytes."
    ::= { cie1000PortStatisticsRmonStatisticsEntry 14 }

cie1000PortStatisticsRmonStatisticsRx256to511Pkts OBJECT-TYPE
    SYNTAX      Counter64
    MAX-ACCESS  read-only
    STATUS      current
    DESCRIPTION
        "The number of received frames with size within 256 to 511 bytes."
    ::= { cie1000PortStatisticsRmonStatisticsEntry 15 }

cie1000PortStatisticsRmonStatisticsRx512to1023Pkts OBJECT-TYPE
    SYNTAX      Counter64
    MAX-ACCESS  read-only
    STATUS      current
    DESCRIPTION
        "The number of received frames with size within 512 to 1023 bytes."
    ::= { cie1000PortStatisticsRmonStatisticsEntry 16 }

cie1000PortStatisticsRmonStatisticsRx1024to1518Pkts OBJECT-TYPE
    SYNTAX      Counter64
    MAX-ACCESS  read-only
    STATUS      current
    DESCRIPTION
        "The number of received frames with size within 1024 to 1518 bytes."
    ::= { cie1000PortStatisticsRmonStatisticsEntry 17 }

cie1000PortStatisticsRmonStatisticsRx1519PktsToMax OBJECT-TYPE
    SYNTAX      Counter64
    MAX-ACCESS  read-only
    STATUS      current
    DESCRIPTION
        "The number of received frames with size larger than 1518 bytes."
    ::= { cie1000PortStatisticsRmonStatisticsEntry 18 }

cie1000PortStatisticsRmonStatisticsTxDropEvents OBJECT-TYPE
    SYNTAX      Counter64
    MAX-ACCESS  read-only
    STATUS      current
    DESCRIPTION
        "Shows the number of frames discarded due to egress congestion."
    ::= { cie1000PortStatisticsRmonStatisticsEntry 19 }

cie1000PortStatisticsRmonStatisticsTxOctets OBJECT-TYPE
    SYNTAX      Counter64
    MAX-ACCESS  read-only
    STATUS      current
    DESCRIPTION
        "Shows the number of transmitted (good and bad) bytes. Includes FCS, but
         excludes framing bits."
    ::= { cie1000PortStatisticsRmonStatisticsEntry 20 }

cie1000PortStatisticsRmonStatisticsTxPkts OBJECT-TYPE
    SYNTAX      Counter64
    MAX-ACCESS  read-only
    STATUS      current
    DESCRIPTION
        "Shows the number of transmitted (good and bad) packets."
    ::= { cie1000PortStatisticsRmonStatisticsEntry 21 }

cie1000PortStatisticsRmonStatisticsTxBroadcastPkts OBJECT-TYPE
    SYNTAX      Counter64
    MAX-ACCESS  read-only
    STATUS      current
    DESCRIPTION
        "Shows the number of transmitted (good and bad) broadcast packets."
    ::= { cie1000PortStatisticsRmonStatisticsEntry 22 }

cie1000PortStatisticsRmonStatisticsTxMulticastPkts OBJECT-TYPE
    SYNTAX      Counter64
    MAX-ACCESS  read-only
    STATUS      current
    DESCRIPTION
        "Shows the number of transmitted (good and bad) multicast packets."
    ::= { cie1000PortStatisticsRmonStatisticsEntry 23 }

cie1000PortStatisticsRmonStatisticsTx64Pkts OBJECT-TYPE
    SYNTAX      Counter64
    MAX-ACCESS  read-only
    STATUS      current
    DESCRIPTION
        "The number of 64 bytes frames transmitted."
    ::= { cie1000PortStatisticsRmonStatisticsEntry 24 }

cie1000PortStatisticsRmonStatisticsTx65to127Pkts OBJECT-TYPE
    SYNTAX      Counter64
    MAX-ACCESS  read-only
    STATUS      current
    DESCRIPTION
        "The number of transmitted frames with size within 65 to 127 bytes."
    ::= { cie1000PortStatisticsRmonStatisticsEntry 25 }

cie1000PortStatisticsRmonStatisticsTx128to255Pkts OBJECT-TYPE
    SYNTAX      Counter64
    MAX-ACCESS  read-only
    STATUS      current
    DESCRIPTION
        "The number of transmitted frames with size within 128 to 255 bytes."
    ::= { cie1000PortStatisticsRmonStatisticsEntry 26 }

cie1000PortStatisticsRmonStatisticsTx256to511Pkts OBJECT-TYPE
    SYNTAX      Counter64
    MAX-ACCESS  read-only
    STATUS      current
    DESCRIPTION
        "The number of transmitted frames with size within 256 to 511 bytes."
    ::= { cie1000PortStatisticsRmonStatisticsEntry 27 }

cie1000PortStatisticsRmonStatisticsTx512to1023Pkts OBJECT-TYPE
    SYNTAX      Counter64
    MAX-ACCESS  read-only
    STATUS      current
    DESCRIPTION
        "The number of transmitted frames with size within 512 to 1023 bytes."
    ::= { cie1000PortStatisticsRmonStatisticsEntry 28 }

cie1000PortStatisticsRmonStatisticsTx1024to1518Pkts OBJECT-TYPE
    SYNTAX      Counter64
    MAX-ACCESS  read-only
    STATUS      current
    DESCRIPTION
        "The number of transmitted frames with size within 1024 to 1518 bytes."
    ::= { cie1000PortStatisticsRmonStatisticsEntry 29 }

cie1000PortStatisticsRmonStatisticsTx1519PktsToMax OBJECT-TYPE
    SYNTAX      Counter64
    MAX-ACCESS  read-only
    STATUS      current
    DESCRIPTION
        "The number of transmitted frames with size larger than 1518 bytes."
    ::= { cie1000PortStatisticsRmonStatisticsEntry 30 }

cie1000PortStatisticsIfGroupStatisticsTable OBJECT-TYPE
    SYNTAX      SEQUENCE OF CIE1000PortStatisticsIfGroupStatisticsEntry
    MAX-ACCESS  not-accessible
    STATUS      current
    DESCRIPTION
        "This table represents the port interfaces group (RFC 2863) counters"
    ::= { cie1000PortStatistics 2 }

cie1000PortStatisticsIfGroupStatisticsEntry OBJECT-TYPE
    SYNTAX      CIE1000PortStatisticsIfGroupStatisticsEntry
    MAX-ACCESS  not-accessible
    STATUS      current
    DESCRIPTION
        "Each port interface has a set of statistics counters"
    INDEX       { cie1000PortStatisticsIfGroupStatisticsIfIndex }
    ::= { cie1000PortStatisticsIfGroupStatisticsTable 1 }

CIE1000PortStatisticsIfGroupStatisticsEntry ::= SEQUENCE {
    cie1000PortStatisticsIfGroupStatisticsIfIndex           CIE1000InterfaceIndex,
    cie1000PortStatisticsIfGroupStatisticsRxOctets          Counter64,
    cie1000PortStatisticsIfGroupStatisticsRxUnicastPkts     Counter64,
    cie1000PortStatisticsIfGroupStatisticsRxMulticastPkts   Counter64,
    cie1000PortStatisticsIfGroupStatisticsRxBroadcastPkts   Counter64,
    cie1000PortStatisticsIfGroupStatisticsRxNonUnicastPkts  Counter64,
    cie1000PortStatisticsIfGroupStatisticsRxDiscards        Counter64,
    cie1000PortStatisticsIfGroupStatisticsRxErrors          Counter64,
    cie1000PortStatisticsIfGroupStatisticsTxOctets          Counter64,
    cie1000PortStatisticsIfGroupStatisticsTxUnicastPkts     Counter64,
    cie1000PortStatisticsIfGroupStatisticsTxMulticastPkts   Counter64,
    cie1000PortStatisticsIfGroupStatisticsTxBroadcastPkts   Counter64,
    cie1000PortStatisticsIfGroupStatisticsTxNonUnicastPkts  Counter64,
    cie1000PortStatisticsIfGroupStatisticsTxDiscardPkts     Counter64,
    cie1000PortStatisticsIfGroupStatisticsTxErrorPkts       Counter64
}

cie1000PortStatisticsIfGroupStatisticsIfIndex OBJECT-TYPE
    SYNTAX      CIE1000InterfaceIndex
    MAX-ACCESS  accessible-for-notify
    STATUS      current
    DESCRIPTION
        "Logical interface number."
    ::= { cie1000PortStatisticsIfGroupStatisticsEntry 1 }

cie1000PortStatisticsIfGroupStatisticsRxOctets OBJECT-TYPE
    SYNTAX      Counter64
    MAX-ACCESS  read-only
    STATUS      current
    DESCRIPTION
        "Shows the number of bytes received."
    ::= { cie1000PortStatisticsIfGroupStatisticsEntry 2 }

cie1000PortStatisticsIfGroupStatisticsRxUnicastPkts OBJECT-TYPE
    SYNTAX      Counter64
    MAX-ACCESS  read-only
    STATUS      current
    DESCRIPTION
        "Shows the number of uni-cast frames received."
    ::= { cie1000PortStatisticsIfGroupStatisticsEntry 3 }

cie1000PortStatisticsIfGroupStatisticsRxMulticastPkts OBJECT-TYPE
    SYNTAX      Counter64
    MAX-ACCESS  read-only
    STATUS      current
    DESCRIPTION
        "Shows the number of multi-cast frames received."
    ::= { cie1000PortStatisticsIfGroupStatisticsEntry 4 }

cie1000PortStatisticsIfGroupStatisticsRxBroadcastPkts OBJECT-TYPE
    SYNTAX      Counter64
    MAX-ACCESS  read-only
    STATUS      current
    DESCRIPTION
        "Shows the number of broad-cast frames received."
    ::= { cie1000PortStatisticsIfGroupStatisticsEntry 5 }

cie1000PortStatisticsIfGroupStatisticsRxNonUnicastPkts OBJECT-TYPE
    SYNTAX      Counter64
    MAX-ACCESS  read-only
    STATUS      current
    DESCRIPTION
        "Shows the number of non uni-cast frames received."
    ::= { cie1000PortStatisticsIfGroupStatisticsEntry 6 }

cie1000PortStatisticsIfGroupStatisticsRxDiscards OBJECT-TYPE
    SYNTAX      Counter64
    MAX-ACCESS  read-only
    STATUS      current
    DESCRIPTION
        "Shows the number of received frames discarded."
    ::= { cie1000PortStatisticsIfGroupStatisticsEntry 7 }

cie1000PortStatisticsIfGroupStatisticsRxErrors OBJECT-TYPE
    SYNTAX      Counter64
    MAX-ACCESS  read-only
    STATUS      current
    DESCRIPTION
        "Shows the number of frames with errors received."
    ::= { cie1000PortStatisticsIfGroupStatisticsEntry 8 }

cie1000PortStatisticsIfGroupStatisticsTxOctets OBJECT-TYPE
    SYNTAX      Counter64
    MAX-ACCESS  read-only
    STATUS      current
    DESCRIPTION
        "Shows the number of bytes transmitted."
    ::= { cie1000PortStatisticsIfGroupStatisticsEntry 9 }

cie1000PortStatisticsIfGroupStatisticsTxUnicastPkts OBJECT-TYPE
    SYNTAX      Counter64
    MAX-ACCESS  read-only
    STATUS      current
    DESCRIPTION
        "Shows the number of uni-cast frames transmitted."
    ::= { cie1000PortStatisticsIfGroupStatisticsEntry 10 }

cie1000PortStatisticsIfGroupStatisticsTxMulticastPkts OBJECT-TYPE
    SYNTAX      Counter64
    MAX-ACCESS  read-only
    STATUS      current
    DESCRIPTION
        "Shows the number of multi-cast frames transmitted."
    ::= { cie1000PortStatisticsIfGroupStatisticsEntry 11 }

cie1000PortStatisticsIfGroupStatisticsTxBroadcastPkts OBJECT-TYPE
    SYNTAX      Counter64
    MAX-ACCESS  read-only
    STATUS      current
    DESCRIPTION
        "Shows the number of broad-cast frames transmitted."
    ::= { cie1000PortStatisticsIfGroupStatisticsEntry 12 }

cie1000PortStatisticsIfGroupStatisticsTxNonUnicastPkts OBJECT-TYPE
    SYNTAX      Counter64
    MAX-ACCESS  read-only
    STATUS      current
    DESCRIPTION
        "Shows the number of non uni-cast frames transmitted."
    ::= { cie1000PortStatisticsIfGroupStatisticsEntry 13 }

cie1000PortStatisticsIfGroupStatisticsTxDiscardPkts OBJECT-TYPE
    SYNTAX      Counter64
    MAX-ACCESS  read-only
    STATUS      current
    DESCRIPTION
        "Shows the number of discard frames which should been transmitted."
    ::= { cie1000PortStatisticsIfGroupStatisticsEntry 14 }

cie1000PortStatisticsIfGroupStatisticsTxErrorPkts OBJECT-TYPE
    SYNTAX      Counter64
    MAX-ACCESS  read-only
    STATUS      current
    DESCRIPTION
        "Shows the number of frames transmit with error."
    ::= { cie1000PortStatisticsIfGroupStatisticsEntry 15 }

cie1000PortStatisticsEthernetLikeStatisticsTable OBJECT-TYPE
    SYNTAX      SEQUENCE OF CIE1000PortStatisticsEthernetLikeStatisticsEntry
    MAX-ACCESS  not-accessible
    STATUS      current
    DESCRIPTION
        "This table represents the port Ethernet-like interfaces counters"
    ::= { cie1000PortStatistics 3 }

cie1000PortStatisticsEthernetLikeStatisticsEntry OBJECT-TYPE
    SYNTAX      CIE1000PortStatisticsEthernetLikeStatisticsEntry
    MAX-ACCESS  not-accessible
    STATUS      current
    DESCRIPTION
        "Each port interface has a set of statistics counters"
    INDEX       {                   cie1000PortStatisticsEthernetLikeStatisticsIfIndex }
    ::= { cie1000PortStatisticsEthernetLikeStatisticsTable 1 }

CIE1000PortStatisticsEthernetLikeStatisticsEntry ::= SEQUENCE {
    cie1000PortStatisticsEthernetLikeStatisticsIfIndex        CIE1000InterfaceIndex,
    cie1000PortStatisticsEthernetLikeStatisticsRxPauseFrames  Counter64,
    cie1000PortStatisticsEthernetLikeStatisticsTxPauseFrames  Counter64
}

cie1000PortStatisticsEthernetLikeStatisticsIfIndex OBJECT-TYPE
    SYNTAX      CIE1000InterfaceIndex
    MAX-ACCESS  accessible-for-notify
    STATUS      current
    DESCRIPTION
        "Logical interface number."
    ::= { cie1000PortStatisticsEthernetLikeStatisticsEntry 1 }

cie1000PortStatisticsEthernetLikeStatisticsRxPauseFrames OBJECT-TYPE
    SYNTAX      Counter64
    MAX-ACCESS  read-only
    STATUS      current
    DESCRIPTION
        "The number of pause frames received."
    ::= { cie1000PortStatisticsEthernetLikeStatisticsEntry 2 }

cie1000PortStatisticsEthernetLikeStatisticsTxPauseFrames OBJECT-TYPE
    SYNTAX      Counter64
    MAX-ACCESS  read-only
    STATUS      current
    DESCRIPTION
        "The number of pause frames transmitted."
    ::= { cie1000PortStatisticsEthernetLikeStatisticsEntry 3 }

cie1000PortStatisticsQueuesStatisticsTable OBJECT-TYPE
    SYNTAX      SEQUENCE OF CIE1000PortStatisticsQueuesStatisticsEntry
    MAX-ACCESS  not-accessible
    STATUS      current
    DESCRIPTION
        "This table represents the port interfaces queues counters"
    ::= { cie1000PortStatistics 4 }

cie1000PortStatisticsQueuesStatisticsEntry OBJECT-TYPE
    SYNTAX      CIE1000PortStatisticsQueuesStatisticsEntry
    MAX-ACCESS  not-accessible
    STATUS      current
    DESCRIPTION
        "Each port interface has a set of statistics counters"
    INDEX       { cie1000PortStatisticsQueuesStatisticsIfIndex,
                  cie1000PortStatisticsQueuesStatisticsQueue }
    ::= { cie1000PortStatisticsQueuesStatisticsTable 1 }

CIE1000PortStatisticsQueuesStatisticsEntry ::= SEQUENCE {
    cie1000PortStatisticsQueuesStatisticsIfIndex  CIE1000InterfaceIndex,
    cie1000PortStatisticsQueuesStatisticsQueue    Integer32,
    cie1000PortStatisticsQueuesStatisticsRxPrio   Counter64,
    cie1000PortStatisticsQueuesStatisticsTxPrio   Counter64
}

cie1000PortStatisticsQueuesStatisticsIfIndex OBJECT-TYPE
    SYNTAX      CIE1000InterfaceIndex
    MAX-ACCESS  accessible-for-notify
    STATUS      current
    DESCRIPTION
        "Logical interface number."
    ::= { cie1000PortStatisticsQueuesStatisticsEntry 1 }

cie1000PortStatisticsQueuesStatisticsQueue OBJECT-TYPE
    SYNTAX      Integer32 (0..7)
    MAX-ACCESS  accessible-for-notify
    STATUS      current
    DESCRIPTION
        "Queue index."
    ::= { cie1000PortStatisticsQueuesStatisticsEntry 2 }

cie1000PortStatisticsQueuesStatisticsRxPrio OBJECT-TYPE
    SYNTAX      Counter64
    MAX-ACCESS  read-only
    STATUS      current
    DESCRIPTION
        "The number of frames received for the queue."
    ::= { cie1000PortStatisticsQueuesStatisticsEntry 3 }

cie1000PortStatisticsQueuesStatisticsTxPrio OBJECT-TYPE
    SYNTAX      Counter64
    MAX-ACCESS  read-only
    STATUS      current
    DESCRIPTION
        "The number of frames transmitted for the queue."
    ::= { cie1000PortStatisticsQueuesStatisticsEntry 4 }

cie1000PortStatisticsBridgeStatisticsTable OBJECT-TYPE
    SYNTAX      SEQUENCE OF CIE1000PortStatisticsBridgeStatisticsEntry
    MAX-ACCESS  not-accessible
    STATUS      current
    DESCRIPTION
        "This table represents the port interface bridge counters"
    ::= { cie1000PortStatistics 5 }

cie1000PortStatisticsBridgeStatisticsEntry OBJECT-TYPE
    SYNTAX      CIE1000PortStatisticsBridgeStatisticsEntry
    MAX-ACCESS  not-accessible
    STATUS      current
    DESCRIPTION
        "Each port interface has a set of statistics counters"
    INDEX       { cie1000PortStatisticsBridgeStatisticsIfIndex }
    ::= { cie1000PortStatisticsBridgeStatisticsTable 1 }

CIE1000PortStatisticsBridgeStatisticsEntry ::= SEQUENCE {
    cie1000PortStatisticsBridgeStatisticsIfIndex          CIE1000InterfaceIndex,
    cie1000PortStatisticsBridgeStatisticsRxBridgeDiscard  Counter64
}

cie1000PortStatisticsBridgeStatisticsIfIndex OBJECT-TYPE
    SYNTAX      CIE1000InterfaceIndex
    MAX-ACCESS  accessible-for-notify
    STATUS      current
    DESCRIPTION
        "Logical interface number."
    ::= { cie1000PortStatisticsBridgeStatisticsEntry 1 }

cie1000PortStatisticsBridgeStatisticsRxBridgeDiscard OBJECT-TYPE
    SYNTAX      Counter64
    MAX-ACCESS  read-only
    STATUS      current
    DESCRIPTION
        "The number of bridge frames discarded."
    ::= { cie1000PortStatisticsBridgeStatisticsEntry 2 }

cie1000PortMibConformance OBJECT IDENTIFIER
    ::= { cie1000PortMib 2 }

cie1000PortMibCompliances OBJECT IDENTIFIER
    ::= { cie1000PortMibConformance 1 }

cie1000PortMibGroups OBJECT IDENTIFIER
    ::= { cie1000PortMibConformance 2 }

cie1000PortConfigInfoGroup OBJECT-GROUP
    OBJECTS     { cie1000PortConfigIfIndex, cie1000PortConfigShutdown,
                  cie1000PortConfigSpeed,
                  cie1000PortConfigAdvertiseDisabled,
                  cie1000PortConfigMediaType, cie1000PortConfigFC,
                  cie1000PortConfigMTU,
                  cie1000PortConfigExcessiveRestart,
                  cie1000PortConfigPFC,
                  cie1000PortConfigFrameLengthCheck }
    STATUS      current
    DESCRIPTION
        "A collection of objects."
    ::= { cie1000PortMibGroups 1 }

cie1000PortStatusInformationTableInfoGroup OBJECT-GROUP
    OBJECTS     { cie1000PortStatusInformationIfIndex,
                  cie1000PortStatusInformationLink,
                  cie1000PortStatusInformationFdx,
                  cie1000PortStatusInformationFiber,
                  cie1000PortStatusInformationSpeed,
                  cie1000PortStatusInformationSFPType,
                  cie1000PortStatusInformationSFPVendorName,
                  cie1000PortStatusInformationSFPVendorPN,
                  cie1000PortStatusInformationSFPVendorRev,
                  cie1000PortStatusInformationSFPVendorSN,
                  cie1000PortStatusInformationRxUtilization,
                  cie1000PortStatusInformationTxUtilization,
                  cie1000PortStatusInformationRxErrorUtilization,
                  cie1000PortStatusInformationTxErrorUtilization }
    STATUS      current
    DESCRIPTION
        "A collection of objects."
    ::= { cie1000PortMibGroups 2 }

cie1000PortStatusVeriPhyResultTableInfoGroup OBJECT-GROUP
    OBJECTS     { cie1000PortStatusVeriPhyResultIfIndex,
                  cie1000PortStatusVeriPhyResultVeriPhyStatusPairA,
                  cie1000PortStatusVeriPhyResultVeriPhyStatusPairB,
                  cie1000PortStatusVeriPhyResultVeriPhyStatusPairC,
                  cie1000PortStatusVeriPhyResultVeriPhyStatusPairD,
                  cie1000PortStatusVeriPhyResultVeriPhyLengthStatusPairA,
                  cie1000PortStatusVeriPhyResultVeriPhyLengthStatusPairB,
                  cie1000PortStatusVeriPhyResultVeriPhyLengthStatusPairC,
                  cie1000PortStatusVeriPhyResultVeriPhyLengthStatusPairD }
    STATUS      current
    DESCRIPTION
        "A collection of objects."
    ::= { cie1000PortMibGroups 3 }

cie1000PortControlStatisticsClearTableInfoGroup OBJECT-GROUP
    OBJECTS     { cie1000PortControlStatisticsClearIfIndex,
                  cie1000PortControlStatisticsClearStatisticsClear }
    STATUS      current
    DESCRIPTION
        "A collection of objects."
    ::= { cie1000PortMibGroups 4 }

cie1000PortControlVeriPhyStartTableInfoGroup OBJECT-GROUP
    OBJECTS     { cie1000PortControlVeriPhyStartIfIndex,
                  cie1000PortControlVeriPhyStartStart }
    STATUS      current
    DESCRIPTION
        "A collection of objects."
    ::= { cie1000PortMibGroups 5 }

cie1000PortStatisticsRmonStatisticsTableInfoGroup OBJECT-GROUP
    OBJECTS     { cie1000PortStatisticsRmonStatisticsIfIndex,
                  cie1000PortStatisticsRmonStatisticsRxDropEvents,
                  cie1000PortStatisticsRmonStatisticsRxOctets,
                  cie1000PortStatisticsRmonStatisticsRxPkts,
                  cie1000PortStatisticsRmonStatisticsRxBroadcastPkts,
                  cie1000PortStatisticsRmonStatisticsRxMulticastPkts,
                  cie1000PortStatisticsRmonStatisticsRxCrcAlignErrPkts,
                  cie1000PortStatisticsRmonStatisticsRxUndersizePkts,
                  cie1000PortStatisticsRmonStatisticsRxOversizePkts,
                  cie1000PortStatisticsRmonStatisticsRxFragmentsPkts,
                  cie1000PortStatisticsRmonStatisticsRxJabbersPkts,
                  cie1000PortStatisticsRmonStatisticsRx64Pkts,
                  cie1000PortStatisticsRmonStatisticsRx65to127Pkts,
                  cie1000PortStatisticsRmonStatisticsRx128to255Pkts,
                  cie1000PortStatisticsRmonStatisticsRx256to511Pkts,
                  cie1000PortStatisticsRmonStatisticsRx512to1023Pkts,
                  cie1000PortStatisticsRmonStatisticsRx1024to1518Pkts,
                  cie1000PortStatisticsRmonStatisticsRx1519PktsToMax,
                  cie1000PortStatisticsRmonStatisticsTxDropEvents,
                  cie1000PortStatisticsRmonStatisticsTxOctets,
                  cie1000PortStatisticsRmonStatisticsTxPkts,
                  cie1000PortStatisticsRmonStatisticsTxBroadcastPkts,
                  cie1000PortStatisticsRmonStatisticsTxMulticastPkts,
                  cie1000PortStatisticsRmonStatisticsTx64Pkts,
                  cie1000PortStatisticsRmonStatisticsTx65to127Pkts,
                  cie1000PortStatisticsRmonStatisticsTx128to255Pkts,
                  cie1000PortStatisticsRmonStatisticsTx256to511Pkts,
                  cie1000PortStatisticsRmonStatisticsTx512to1023Pkts,
                  cie1000PortStatisticsRmonStatisticsTx1024to1518Pkts,
                  cie1000PortStatisticsRmonStatisticsTx1519PktsToMax }
    STATUS      current
    DESCRIPTION
        "A collection of objects."
    ::= { cie1000PortMibGroups 6 }

cie1000PortStatisticsIfGroupStatisticsTableInfoGroup OBJECT-GROUP
    OBJECTS     { cie1000PortStatisticsIfGroupStatisticsIfIndex,
                  cie1000PortStatisticsIfGroupStatisticsRxOctets,
                  cie1000PortStatisticsIfGroupStatisticsRxUnicastPkts,
                  cie1000PortStatisticsIfGroupStatisticsRxMulticastPkts,
                  cie1000PortStatisticsIfGroupStatisticsRxBroadcastPkts,
                  cie1000PortStatisticsIfGroupStatisticsRxNonUnicastPkts,
                  cie1000PortStatisticsIfGroupStatisticsRxDiscards,
                  cie1000PortStatisticsIfGroupStatisticsRxErrors,
                  cie1000PortStatisticsIfGroupStatisticsTxOctets,
                  cie1000PortStatisticsIfGroupStatisticsTxUnicastPkts,
                  cie1000PortStatisticsIfGroupStatisticsTxMulticastPkts,
                  cie1000PortStatisticsIfGroupStatisticsTxBroadcastPkts,
                  cie1000PortStatisticsIfGroupStatisticsTxNonUnicastPkts,
                  cie1000PortStatisticsIfGroupStatisticsTxDiscardPkts,
                  cie1000PortStatisticsIfGroupStatisticsTxErrorPkts }
    STATUS      current
    DESCRIPTION
        "A collection of objects."
    ::= { cie1000PortMibGroups 7 }

cie1000PortStatisticsEthernetLikeStatisticsTableInfoGroup OBJECT-GROUP
    OBJECTS     {                   cie1000PortStatisticsEthernetLikeStatisticsIfIndex,
                  cie1000PortStatisticsEthernetLikeStatisticsRxPauseFrames,
                  cie1000PortStatisticsEthernetLikeStatisticsTxPauseFrames }
    STATUS      current
    DESCRIPTION
        "A collection of objects."
    ::= { cie1000PortMibGroups 8 }

cie1000PortStatisticsQueuesStatisticsTableInfoGroup OBJECT-GROUP
    OBJECTS     { cie1000PortStatisticsQueuesStatisticsIfIndex,
                  cie1000PortStatisticsQueuesStatisticsQueue,
                  cie1000PortStatisticsQueuesStatisticsRxPrio,
                  cie1000PortStatisticsQueuesStatisticsTxPrio }
    STATUS      current
    DESCRIPTION
        "A collection of objects."
    ::= { cie1000PortMibGroups 9 }

cie1000PortStatisticsBridgeStatisticsTableInfoGroup OBJECT-GROUP
    OBJECTS     { cie1000PortStatisticsBridgeStatisticsIfIndex,
                  cie1000PortStatisticsBridgeStatisticsRxBridgeDiscard }
    STATUS      current
    DESCRIPTION
        "A collection of objects."
    ::= { cie1000PortMibGroups 10 }

cie1000PortMibCompliance MODULE-COMPLIANCE
    STATUS      current
    DESCRIPTION
        "The compliance statement for the implementation."

    MODULE      -- this module

    MANDATORY-GROUPS { cie1000PortConfigInfoGroup,
                       cie1000PortStatusInformationTableInfoGroup,
                       cie1000PortStatusVeriPhyResultTableInfoGroup,
                       cie1000PortControlStatisticsClearTableInfoGroup,
                       cie1000PortControlVeriPhyStartTableInfoGroup,
                       cie1000PortStatisticsRmonStatisticsTableInfoGroup,
                       cie1000PortStatisticsIfGroupStatisticsTableInfoGroup,
                       cie1000PortStatisticsEthernetLikeStatisticsTableInfoGroup,
                       cie1000PortStatisticsQueuesStatisticsTableInfoGroup,
                       cie1000PortStatisticsBridgeStatisticsTableInfoGroup }

    ::= { cie1000PortMibCompliances 1 }

END
