-- *------------------------------------------------------------------
-- * ALTIGA-SYNC-STATS-MIB.my:  Altiga Sync Statistics MIB.
-- *
-- * Altiga Networks was acquired by Cisco Systems on March 29, 2000
-- *
-- * Copyright (c) 2002 by Cisco Systems, Inc.
-- * All rights reserved.
-- *
-- *------------------------------------------------------------------

ALTIGA-SYNC-STATS-MIB DEFINITIONS ::= BEGIN

   IMPORTS
      MODULE-IDENTITY, OBJECT-TYPE, Integer32, Counter32
         FROM SNMPv2-SMI
      RowStatus
         FROM SNMPv2-TC
      OBJECT-GROUP, MODULE-COMPLIANCE
         FROM SNMPv2-CONF
      alStatsSync, alSyncGroup
         FROM ALTIGA-MIB
      alSyncMibModule
         FROM ALTIGA-GLOBAL-REG
      InterfaceIndex
         FROM IF-MIB;

   altigaSyncStatsMibModule MODULE-IDENTITY
      LAST-UPDATED   "200209051300Z"
      ORGANIZATION   "Cisco Systems, Inc."
      CONTACT-INFO
         "Cisco Systems
          170 W Tasman Drive
          San Jose, CA  95134
          USA

          Tel: +1 800 553-NETS
          E-mail: cs-cvpn3000@cisco.com"

      DESCRIPTION
         "The Altiga Sync Statistics MIB models counters and objects
          that are of management interest.

          Acronyms
          The following acronyms are used in this document:

            CRC:        Cyclic Redundancy Check

            HDLC:       High-level Data Link Control

            MIB:        Management Information Base

            MTU:        Maximum Transmission Unit

         "

        REVISION "200209051300Z"
        DESCRIPTION
                "Added module compliance."

        REVISION "200207100000Z"
        DESCRIPTION
                "Updated with new header"

      ::= { alSyncMibModule 2 }

-- +++++++++++++++++++++++++++++++++++++++++++++++++++++++
-- MIB Objects
-- +++++++++++++++++++++++++++++++++++++++++++++++++++++++

alStatsSyncGlobal OBJECT IDENTIFIER ::= { alStatsSync 1 }

alSyncStatsTable     OBJECT-TYPE
   SYNTAX         SEQUENCE OF AlSyncStatsEntry
   MAX-ACCESS     not-accessible
   STATUS         current
   DESCRIPTION
      "The SYNC interface statistics MIB."
   ::= { alStatsSync 2 }

alSyncStatsEntry     OBJECT-TYPE
   SYNTAX         AlSyncStatsEntry
   MAX-ACCESS     not-accessible
   STATUS         current
   DESCRIPTION
      "An entry the alSyncStatsTable."
   INDEX    { alSyncStatsSlot, alSyncStatsConn, alSyncStatsChannel }
   ::= { alSyncStatsTable 1 }

AlSyncStatsEntry ::= SEQUENCE {
   alSyncStatsRowStatus                RowStatus,
   alSyncStatsSlot                     Integer32,
   alSyncStatsConn                     Integer32,
   alSyncStatsChannel                  Integer32,
   alSyncStatsIfIndex                  InterfaceIndex,
   alSyncStatsPortState                INTEGER,
   alSyncStatsRxFrames                 Counter32,
   alSyncStatsRxOctets                 Counter32,
   alSyncStatsRxReplenFails            Counter32,
   alSyncStatsRxClockErrors            Counter32,
   alSyncStatsRxDpllErrors             Counter32,
   alSyncStatsRxFrameTooLongErrors     Counter32,
   alSyncStatsRxFrameOctetAlignErrors  Counter32,
   alSyncStatsRxAbortErrors            Counter32,
   alSyncStatsRxCrcErrors              Counter32,
   alSyncStatsRxRcvrOverrunErrors      Counter32,
   alSyncStatsTxFrames                 Counter32,
   alSyncStatsTxOctets                 Counter32,
   alSyncStatsTxRingFullDropsErrors    Counter32,
   alSyncStatsTxClockErrors            Counter32,
   alSyncStatsTxFrameTooLongErrors     Counter32,
   alSyncStatsTxUnderrunErrors         Counter32
}

alSyncStatsRowStatus    OBJECT-TYPE
   SYNTAX         RowStatus
   MAX-ACCESS     read-create
   STATUS         current
   DESCRIPTION
      "The status of this row."
   ::= { alSyncStatsEntry 1 }

alSyncStatsSlot         OBJECT-TYPE
   SYNTAX         Integer32 (0..2147483647)
   MAX-ACCESS     read-only
   STATUS         current
   DESCRIPTION
      "The physical slot for this Sync port. Part of the index."
   ::= { alSyncStatsEntry 2 }

alSyncStatsConn         OBJECT-TYPE
   SYNTAX         Integer32 (0..2147483647)
   MAX-ACCESS     read-only
   STATUS         current
   DESCRIPTION
      "The physical connector for this Sync port. Part of the index."
   ::= { alSyncStatsEntry 3 }

alSyncStatsChannel      OBJECT-TYPE
   SYNTAX         Integer32 (0..2147483647)
   MAX-ACCESS     read-only
   STATUS         current
   DESCRIPTION
      "The virtual channel for this Sync port. Part of the index."
   ::= { alSyncStatsEntry 4 }

alSyncStatsIfIndex      OBJECT-TYPE
   SYNTAX         InterfaceIndex
   MAX-ACCESS     read-only
   STATUS         current
   DESCRIPTION
      "The IfIndex of this SYNC slot/conn/channel. This is
       configured, but configuration is not available via
       SNMP."
   ::= { alSyncStatsEntry 5 }

alSyncStatsPortState OBJECT-TYPE
   SYNTAX         INTEGER {
                     init(1),      -- port is coming up
                     running(2),   -- port has finished initialization
                                   -- and is waiting to transition to
                                   -- data state
                     up(3),        -- ready to pass packets
                     down(4)       -- port is down, unable to pass
                                   -- packets
                  }
   MAX-ACCESS     read-only
   STATUS         current
   DESCRIPTION
      "The current operational state of the interface.
       The init(1) state indicates the port is in the state
       of trying to come up. It will transition to running(2)
       once initialization is complete. up(3) indicates the
       interface is capable of passing packets. down(4) indicates
       the interface is no longer capable of passing packets."
   ::= { alSyncStatsEntry 6 }

alSyncStatsRxFrames     OBJECT-TYPE
   SYNTAX         Counter32
   MAX-ACCESS     read-only
   STATUS         current
   DESCRIPTION
      "The number of frames received on this HDLC interface."
   ::= { alSyncStatsEntry 7 }

alSyncStatsRxOctets     OBJECT-TYPE
   SYNTAX         Counter32
   MAX-ACCESS     read-only
   STATUS         current
   DESCRIPTION
      "The number of octets received on this HDLC interface."
   ::= { alSyncStatsEntry 8 }

alSyncStatsRxReplenFails   OBJECT-TYPE
   SYNTAX         Counter32
   MAX-ACCESS     read-only
   STATUS         current
   DESCRIPTION
      "The number of times receive buffers could not be allocated
      on this HDLC interface."
   ::= { alSyncStatsEntry 9 }

alSyncStatsRxClockErrors   OBJECT-TYPE
   SYNTAX         Counter32
   MAX-ACCESS     read-only
   STATUS         current
   DESCRIPTION
      "The number of clock errors on this HDLC interface."
   ::= { alSyncStatsEntry 10 }

alSyncStatsRxDpllErrors OBJECT-TYPE
   SYNTAX         Counter32
   MAX-ACCESS     read-only
   STATUS         current
   DESCRIPTION
      "The number of DPLL errors received on this HDLC interface."
   ::= { alSyncStatsEntry 11 }

alSyncStatsRxFrameTooLongErrors     OBJECT-TYPE
   SYNTAX         Counter32
   MAX-ACCESS     read-only
   STATUS         current
   DESCRIPTION
      "The number of received long frame errors received on this
       HDLC interface."
   ::= { alSyncStatsEntry 12 }

alSyncStatsRxFrameOctetAlignErrors     OBJECT-TYPE
   SYNTAX         Counter32
   MAX-ACCESS     read-only
   STATUS         current
   DESCRIPTION
      "The number of received long frame errors received on
       this HDLC interface."
   ::= { alSyncStatsEntry 13 }

alSyncStatsRxAbortErrors      OBJECT-TYPE
   SYNTAX         Counter32
   MAX-ACCESS     read-only
   STATUS         current
   DESCRIPTION
      "The number of received abort errors received on
       this HDLC interface."
   ::= { alSyncStatsEntry 14 }

alSyncStatsRxCrcErrors     OBJECT-TYPE
   SYNTAX         Counter32
   MAX-ACCESS     read-only
   STATUS         current
   DESCRIPTION
      "The number of received CRC errors received on
       this HDLC interface."
   ::= { alSyncStatsEntry 15 }

alSyncStatsRxRcvrOverrunErrors      OBJECT-TYPE
   SYNTAX         Counter32
   MAX-ACCESS     read-only
   STATUS         current
   DESCRIPTION
      "The number of received CRC errors received on
       this HDLC interface."
   ::= { alSyncStatsEntry 16 }

alSyncStatsTxFrames     OBJECT-TYPE
   SYNTAX         Counter32
   MAX-ACCESS     read-only
   STATUS         current
   DESCRIPTION
      "The number of transmitted frames on this HDLC interface."
   ::= { alSyncStatsEntry 17 }

alSyncStatsTxOctets     OBJECT-TYPE
   SYNTAX         Counter32
   MAX-ACCESS     read-only
   STATUS         current
   DESCRIPTION
      "The number of transmitted frames on this HDLC interface."
   ::= { alSyncStatsEntry 18 }

alSyncStatsTxRingFullDropsErrors    OBJECT-TYPE
   SYNTAX         Counter32
   MAX-ACCESS     read-only
   STATUS         current
   DESCRIPTION
      "The number of frames dropped on this HDLC interface because
       the transmit ring was full."
   ::= { alSyncStatsEntry 19 }

alSyncStatsTxClockErrors      OBJECT-TYPE
   SYNTAX         Counter32
   MAX-ACCESS     read-only
   STATUS         current
   DESCRIPTION
      "The number of transmit clock errors on this HDLC interface."
   ::= { alSyncStatsEntry 20 }

alSyncStatsTxFrameTooLongErrors     OBJECT-TYPE
   SYNTAX         Counter32
   MAX-ACCESS     read-only
   STATUS         current
   DESCRIPTION
      "The number of frames dropped this HDLC interface because they
       were long than the interface's MTU."
   ::= { alSyncStatsEntry 21 }

alSyncStatsTxUnderrunErrors      OBJECT-TYPE
   SYNTAX         Counter32
   MAX-ACCESS     read-only
   STATUS         current
   DESCRIPTION
      "The number of transmitter underruns on this HDLC interface."
   ::= { alSyncStatsEntry 22 }

altigaSyncStatsMibConformance OBJECT IDENTIFIER
   ::= { altigaSyncStatsMibModule 1 }

altigaSyncStatsMibCompliances OBJECT IDENTIFIER
   ::= { altigaSyncStatsMibConformance 1 }

altigaSyncStatsMibCompliance MODULE-COMPLIANCE
   STATUS         current
   DESCRIPTION
      "The compliance statement for agents which
       implement the Altiga Sync Statistics MIB."
   MODULE
   MANDATORY-GROUPS {
      altigaSyncStatsGroup
   }
   ::= { altigaSyncStatsMibCompliances 1 }

altigaSyncStatsGroup OBJECT-GROUP
   OBJECTS
   {
      alSyncStatsRowStatus,
      alSyncStatsSlot,
      alSyncStatsConn,
      alSyncStatsChannel,
      alSyncStatsIfIndex,
      alSyncStatsPortState,
      alSyncStatsRxFrames,
      alSyncStatsRxOctets,
      alSyncStatsRxReplenFails,
      alSyncStatsRxClockErrors,
      alSyncStatsRxDpllErrors,
      alSyncStatsRxFrameTooLongErrors,
      alSyncStatsRxFrameOctetAlignErrors,
      alSyncStatsRxAbortErrors,
      alSyncStatsRxCrcErrors,
      alSyncStatsRxRcvrOverrunErrors,
      alSyncStatsTxFrames,
      alSyncStatsTxOctets,
      alSyncStatsTxRingFullDropsErrors,
      alSyncStatsTxClockErrors,
      alSyncStatsTxFrameTooLongErrors,
      alSyncStatsTxUnderrunErrors
   }
   STATUS   current
   DESCRIPTION
          "The objects for SYNC configuration."
   ::= { alSyncGroup 2 }

END
