-- ****************************************************************
-- ciscoMgx82xxDs1MIB
--   The MIB for DS1/E1 interface configuration and
--   Alarm Configuration for Line Cards/Service Modules
--   in MGX products.
--
-- March 2003, Subra Hegde
--
-- Copyright (c) 2003 by cisco Systems, Inc.
-- All rights reserved.
-- ****************************************************************

CISCO-MGX82XX-DSX1-MIB DEFINITIONS ::= BEGIN
IMPORTS
    MODULE-IDENTITY,
    OBJECT-TYPE,
    Integer32,
    Counter32
                               FROM SNMPv2-SMI
    MODULE-COMPLIANCE,
    OBJECT-GROUP               FROM SNMPv2-CONF
    dsx1Line                   FROM BASIS-MIB
    ciscoWan                   FROM CISCOWAN-SMI;

ciscoMgx82xxDsx1MIB MODULE-IDENTITY
    LAST-UPDATED    "200303310000Z"
    ORGANIZATION    "Cisco Systems, Inc."
    CONTACT-INFO
            "       Cisco Systems
                        Customer Service

                Postal: 170 W Tasman Drive
                        San Jose, CA  95134
                        USA

                        Tel: +1 800 553-NETS

                E-mail: cs-wanatm@cisco.com"
    DESCRIPTION
        "The MIB module to configure DS1/E1 interface
        objects. This mib also contains the alarm
        configuration of DS1/E1 interfaces. This mib
        is supported in T1/E1 service modules."

    REVISION    "200303310000Z"
    DESCRIPTION
        "Initial version of the MIB.

        The content of this MIB was originally available
        in SMIv1 version. The MIB has been converted to
        SMIv2 version and descriptions of some of the objects
        have been modified."
    ::= { ciscoWan 58 }


dsx1CnfGrp		OBJECT IDENTIFIER ::= { dsx1Line 1 }
dsx1AlmCnfGrp		OBJECT IDENTIFIER ::= { dsx1Line 2 }
dsx1AlmGrp		OBJECT IDENTIFIER ::= { dsx1Line 3 }
dsx1CntGrp		OBJECT IDENTIFIER ::= { dsx1Line 4 }

--
-- ds1 interface configuration table
--

dsx1CnfGrpTable OBJECT-TYPE
	SYNTAX	   SEQUENCE OF Dsx1CnfGrpEntry
	MAX-ACCESS not-accessible
	STATUS	   current
	DESCRIPTION
		"The DS1/E1 Configuration table. The table size is
		 given by the value of lineNumofValidEntries
		"
	::= { dsx1CnfGrp 1 }

dsx1CnfGrpEntry OBJECT-TYPE
	SYNTAX	   Dsx1CnfGrpEntry
	MAX-ACCESS not-accessible
	STATUS	   current
	DESCRIPTION
	    "An entry in the DS1 Configuration table."
        INDEX	{ lineNum }
	::= { dsx1CnfGrpTable 1 }

Dsx1CnfGrpEntry ::=
	SEQUENCE {
	    lineNum                    Integer32,
            lineConnectorType          INTEGER,
	    lineEnable                 INTEGER,
	    lineType                   INTEGER,
	    lineCoding                 INTEGER,
       	    lineLength                 INTEGER,
	    lineXmtClockSource         INTEGER,
	    lineLoopbackCommand        INTEGER,
	    lineSendCode               INTEGER,
	    lineLoopbackCodeDetection  INTEGER,
	    lineUsedTimeslotsBitMap    Integer32,
	    lineBERTEnable             INTEGER,
	    lineBERTPattern            INTEGER,
	    lineBERTResult             INTEGER,
	    bERTResultClrButton        INTEGER
    	}

lineNum OBJECT-TYPE
	SYNTAX	   Integer32 (1..2147483647)
	MAX-ACCESS read-only
	STATUS     current
	DESCRIPTION
	    "This object is the identifier of a DS1/E1
	    Interface on a managed device. If there is an
	    ifEntry that is directly associated with this
	    and only this DS1/E1 interface, it should have
	    the same value as ifIndex.  Otherwise, number
	    the ds1LineIndices with an unique identifier
	    following the rules of choosing a number that
	    is greater than ifNumber and numbering the
	    inside interfaces (e.g., equipment side) with
	    even numbers and outside interfaces (e.g,
	    network side) with odd numbers.

            The supported ranges depend upon the type of
            the card(4 port/8 port etc):

              For 4 port card             : 1 - 4
              For 8 port card             : 1 - 8
              For 2 Port Channelized card : 56 (28*2)."
	::= { dsx1CnfGrpEntry 1 }

lineConnectorType OBJECT-TYPE
	SYNTAX  INTEGER {
		    db15(1),
		    bnc(2),
                    rj48(3),
		    unused(4),
		    smb(5)
   		}
	MAX-ACCESS read-write
	STATUS     current
	DESCRIPTION
            "This variable indicates  the  connector as well
	    as the backcard type. 1 = T1; 2 = E1.
	    This field is set to unused(4) for FRSM-VHS cards."
	::= { dsx1CnfGrpEntry 2 }

lineEnable  OBJECT-TYPE
	SYNTAX	INTEGER {
		    disable(1),
	       	    enable(2),
	            modify(3)
		}
	MAX-ACCESS read-write
   	STATUS     current
   	DESCRIPTION
      	    "This variable disables, enables or modifies a line
      	       1 - disable
	       2 - enable
	       3 - modify
	     In FRSM-2CT3, if the DS3 line is enabled, then the DS1
	     channels for that line will all be automatically enabled.
	     No independent enable/disable is allowed for each of the
	     28 DS1 lines in FRSM-2CT3."
	DEFVAL {disable}
	::= { dsx1CnfGrpEntry 3 }

lineType OBJECT-TYPE
	SYNTAX  INTEGER {
		    dsx1ESF            (1),
		    dsx1D4             (2),
		    dsx1E1             (3),
		    dsx1E1CRC          (4),
		    dsx1E1MF           (5),
		    dsx1E1CRC-MF       (6),
		    dsx1E1clearchannel (7),
                    dsx1E1Q50          (8),
                    dsx1E1Q50CRC       (9)
   		}
	MAX-ACCESS read-write
	STATUS     current
	DESCRIPTION
		"This variable indicates  the  variety  of  DS1
		 Line  implementing  this  circuit.  The type of
		 circuit affects the number of bits  per  second
       	 	 that  the circuit can reasonably carry, as well
		 as the interpretation of the  usage  and  error statistics.
		 The values, in sequence, describe:
		 TITLE:        SPECIFICATION:
		 dsx1ESF       Extended SuperFrame DS1
		 dsx1D4        AT&T D4 format DS1
		 dsx1E1        CCITT Recommendation G.704
			       (Table 4a)
		 dsx1E1-CRC    CCITT Recommendation G.704
                	       (Table 4b)
		 dsxE1-MF      G.704 (Table 4a) with TS16
                	       multiframing enabled
		 dsx1E1-CRC-MF G.704 (Table 4b) with TS16
                	       multiframing enabled
		 dsx1E1clearchannel E1 clear channel, all DS0s can be used
                 dsx1E1Q50     G.704 (table 14) In TS16 bits 5,7,8 will be
                               set to 100 for all other cases bits 5,7,8 will
                               have a value of 111.
                 dsx1E1Q50CRC  same as dsx1E1Q50 but with CRC.

		NOTE: All E1, E1-CRC, E1-MF or E1-CRC-MF are using DS0
                on slot 1 for signaling and E1-MF or E1-CRC-MF use DS0
                on slot 17 for synchronization.
		(Slot 1 and 16 is based on index 1 to 32 DS0)
		All DS0s can be used for any port when lineType is
		dsx1E1clearchannel.
		On a CESM card, only 'dsx1E1clearchannel' option is supported.

                When the lineType is dsx1E1Q50 the bits 5,7,8 of TS16
                of frame zero will be forced to 100 else it will be 111.

      		The default value for T1 is 'dsx1ESF' and for E1
                is 'dsx1E1CCS'."
	::= { dsx1CnfGrpEntry 4 }

lineCoding OBJECT-TYPE
	SYNTAX  INTEGER {
                     dsx1JBZS (1),
                     dsx1B8ZS (2),
                     dsx1HDB3 (3),
                     dsx1AMI  (4),
		     unused   (5)
   		}
	MAX-ACCESS read-write
	STATUS     current
	DESCRIPTION
		"This variable describes the  variety  of  Zero
		Code  Suppression  used  on  the link, which in
		turn affects a number of its characteristics.

		dsx1JBZS(1): refers the Jammed  Bit  Zero suppression
		             in  which  the  AT&T specification of at
                             least one pulse every 8 bit periods is
                             literally  implemented  by forcing a pulse
                             in bit 8 of each channel.  Thus, only seven
                             bits per  chan- nel, or 1.344 Mbps, is available
                             for data.

		dsx1B8ZS(2): refers to the use of a specified  pattern
		             of  normal  bits  and  bipolar violations
		             which are used to replace a sequence  of  eight
                             zero bits.

		E1 links, with or without CRC, use dsx1HDB3  or
        	dsx1AMI.

        	dsx1AMI(4): refers to a mode wherein no  zero  code
                            suppression  is  present  and the line encoding
                            does not solve the problem directly. In this
        	            application, the higher layer must provide data
        	            which meets or exceeds the  pulse  density
        	            requirements, such as inverting HDLC data.

		The default value for T1 is 'dsx1JBZS' and for E1
		is 'dsx1HDB3'.
                This field is not applicable for FRSM-VHS cards
                and is set to notUsed(5)."
	::= { dsx1CnfGrpEntry 5 }

lineLength OBJECT-TYPE
	SYNTAX  INTEGER {
		lineLength0To110Feet   (1),
		lineLength110To220Feet (2),
		lineLength220To330Feet (3),
		lineLength330To440Feet (4),
		lineLength440To550Feet (5),
		lineLength550To660Feet (6),
		lineLength660FeetPlus  (7),
		lineLength-75-Ohm      (8),
		lineLength-120-Ohm     (9),
		lineLength0To131Feet   (10),
		lineLength131To262Feet (11),
		lineLength262To393Feet (12),
		lineLength393To524Feet (13),
		lineLength524To655Feet (14),
		lineLength655FeetPlus  (15),
		notRequired            (16)
			}
  	MAX-ACCESS read-write
	STATUS     current
	DESCRIPTION
		"This is not a standard RFC 1407 DS1 variable, it is
		 specific to BASIS implementation. It specifies the line length:
		 1 - 0 to 110 ft (T1 line only)
		 2 - 110 to 220 ft (T1 line only)
		 3 - 220 to 330 ft (T1 line only)
		 4 - 330 to 440 ft (T1 line only)
		 5 - 440 to 550 ft (T1 line only)
		 6 - 550 to 660 ft (T1 line only)
		 7 - greater than 660 ft (T1 line only)
		 8 - 75 ohms (E1 line only (BNC))
		 9 - 120 ohms (E1 line only (DB-15))

		The default value for T1 is 1, for E1, if the connector
		type is DB15 then the default is 9, if BNC, it's 8.
		For FRSM-2CT3, the line length of DS1 has no meaning
		as there are no physical DS1 lines. So, for this
		card, the value is set to notRequired (16).
		"
	::= { dsx1CnfGrpEntry 6 }

lineXmtClockSource OBJECT-TYPE
    SYNTAX  INTEGER {
                loopTiming  (1),
                localTiming (2)
               }
    MAX-ACCESS read-write
    STATUS     current
    DESCRIPTION
        "The source of Transmit Clock.

               loopTiming(1): indicates that the recovered
           	              receive clock is used as the
                              transmit clock.
               localTiming(2): indicates  that  a  local  clock
           	               source is used."
    DEFVAL {loopTiming}
    ::= { dsx1CnfGrpEntry 7 }

lineLoopbackCommand OBJECT-TYPE
	SYNTAX  INTEGER {
                    dsx1NoLoop      (1),
                    dsx1RemoteLoop  (2),
                    dsx1LocalLoop   (3),
                    dsx1PayloadLoop (4)
   		}
         MAX-ACCESS read-write
         STATUS     current
         DESCRIPTION
		"This variable represents the  loopback  confi-
        	 guration of the DS1 interface.  Agents support-
        	 ing read/write access should return badValue in
        	 response to a requested loopback state that the
        	 interface does not support.  The values mean:

        	 dsx1NoLoop
             	 	Not in the loopback state.  A device  that
             	 	is not capable of performing a loopback on
             		the interface shall always return this  as
             		it's value.

        	 dsx1RemoteLoop
             		The received signal at this  interface  is
             		looped  through  the device. Typically the
             		received signal is  looped  back  for
             		retransmission  after  it has passed through
             		the device's framing function.

        	 dsx1LocalLoop
             		The local data is looped back
                 dsx1PayloadLoop
                         This will loop only the payload and not
                         framing/sync bit.
		"
	DEFVAL {dsx1NoLoop}
	::= { dsx1CnfGrpEntry 8 }

lineSendCode OBJECT-TYPE
	SYNTAX  INTEGER {
                    dsx1SendNoCode      (1),
                    dsx1SendLineCode    (2),
                    dsx1SendPayloadCode (3),
                    dsx1SendResetCode   (4)
   		}
	MAX-ACCESS read-write
	STATUS     current
	DESCRIPTION
        	"This variable indicates what type of  code  is
        	 being sent across the DS1 interface by the dev-
        	 ice.  The values mean:

        	 dsx1SendNoCode
             		sending looped or normal data

        	 dsx1SendLineCode
             		sending a request for a line loopback

        	 dsx1SendPayloadCode
             		sending a request for a payload loopback

        	 dsx1SendResetCode
             		sending a loopback termination request

		"
	DEFVAL {dsx1SendNoCode}
	::= { dsx1CnfGrpEntry 9 }

lineUsedTimeslotsBitMap OBJECT-TYPE
	SYNTAX     Integer32(0..2147483647)
  	MAX-ACCESS read-only
	STATUS     current
	DESCRIPTION
	    "Bit map of used DS0 for this line."
	::= { dsx1CnfGrpEntry 10 }

lineLoopbackCodeDetection OBJECT-TYPE
        SYNTAX  INTEGER {
                    codeDetectDisabled(1),
                    codeDetectEnabled(2)
                 }
        MAX-ACCESS read-write
        STATUS     current
        DESCRIPTION
                "Enable detection of line Loopback Codes
                "
	DEFVAL {codeDetectDisabled}
        ::= { dsx1CnfGrpEntry 11 }

lineBERTEnable OBJECT-TYPE
	SYNTAX	INTEGER {
		    disable (1),
		    enable  (2)
		}
	MAX-ACCESS read-write
        STATUS  current
        DESCRIPTION
		"This variable enables Bit Error Rate Testing(BERT)."
	DEFVAL { disable }
	::= { dsx1CnfGrpEntry 12 }

lineBERTPattern OBJECT-TYPE
	SYNTAX  INTEGER {
          	    allZeros         (1),
                    allOnes          (2),
                    alternateONeZero (3),
                    doubleOneZero    (4),
                    userOneWords     (5),
                    userTwoWords     (6),
                    userThreeWords   (7),
                    userFourWords    (8),
                    fifteenBit       (9),
                    twentyBit        (10),
                    twentyBitQRSS    (11),
                    twentythreeBit   (12)
                }
        	MAX-ACCESS read-write
        	STATUS     current
        	DESCRIPTION
           	"This variable determines BERT pattern to transmit
		"
	DEFVAL { allZeros }
	::= { dsx1CnfGrpEntry 13 }

lineBERTResult OBJECT-TYPE
    SYNTAX	INTEGER {
		    failed(1),
		    passed(2)
		}
    MAX-ACCESS read-write
    STATUS  current
    DESCRIPTION
        "This shows the result of the BERT."
    DEFVAL { failed }
    ::= { dsx1CnfGrpEntry 14 }

bERTResultClrButton OBJECT-TYPE
    SYNTAX     INTEGER {
                   noaction (1),
		   clear    (2)
		}
    MAX-ACCESS read-write
    STATUS     current
    DESCRIPTION
        "This clears the result of the BERT."
    DEFVAL { noaction }
    ::= { dsx1CnfGrpEntry 15 }

lineNumofValidEntries OBJECT-TYPE
	SYNTAX	   Integer32 (0..128)
	MAX-ACCESS read-only
	STATUS	   current
	DESCRIPTION
	    "The number of DS1 configuration entries (regardless
	    of their current configuration) in the dsx1CnfGrpTable."
	::= { dsx1CnfGrp 2 }

dsx1CntGrpTable OBJECT-TYPE
    SYNTAX	SEQUENCE OF Dsx1CntGrpEntry
    MAX-ACCESS	not-accessible
    STATUS	current
    DESCRIPTION
        "The DS1 Counter table. This table contains
        statistics since the system was up or last
        re-initialization."
   ::= { dsx1CntGrp 1 }

dsx1CntGrpEntry OBJECT-TYPE
    SYNTAX	Dsx1CntGrpEntry
    MAX-ACCESS  not-accessible
    STATUS  current
    DESCRIPTION
        "An entry in the DS1 counter table."
    INDEX	{ cntLineNum }
    ::= { dsx1CntGrpTable 1 }

Dsx1CntGrpEntry ::=
    SEQUENCE {
        cntLineNum           Integer32,
	rcvLOSCount          Counter32,
	rcvOOFCount          Counter32,
	rcvRAICount          Counter32,
	rcvFECount           Counter32,
	counterClearButton   INTEGER
    }

cntLineNum OBJECT-TYPE
    SYNTAX     Integer32 (1..2147483647)
    MAX-ACCESS read-only
    STATUS     current
    DESCRIPTION
        "This object identifies the DS1/E1 interface.
        The value for this object must be same as the
        value of lineNum from dsx1CnfGrpTable."
	::= { dsx1CntGrpEntry 1 }

rcvLOSCount OBJECT-TYPE
    SYNTAX     Counter32
    MAX-ACCESS read-only
    STATUS     current
    DESCRIPTION
        "The number of times the Loss of Signal was detected
        with or without integrating to LOS alarm."
    ::= { dsx1CntGrpEntry 2 }

rcvOOFCount OBJECT-TYPE
    SYNTAX     Counter32
    MAX-ACCESS read-only
    STATUS     current
    DESCRIPTION
    "The number of times the Out of Frame was detected
    with or without integrating to OOF alarm."
    ::= { dsx1CntGrpEntry 3 }

rcvRAICount OBJECT-TYPE
    SYNTAX     Counter32
    MAX-ACCESS read-only
    STATUS     current
    DESCRIPTION
        "The number of times Yellow Alarms was detected with
        or without integrating to RAI alarm."
    ::= { dsx1CntGrpEntry 4 }

rcvFECount OBJECT-TYPE
    SYNTAX     Counter32
    MAX-ACCESS read-only
    STATUS     current
    DESCRIPTION
        "The number of Framing Pattern Errors encountered by
        a DS1 interface."
    ::= { dsx1CntGrpEntry 5 }

counterClearButton OBJECT-TYPE
    SYNTAX  INTEGER {
                    noaction(1),
                    clear (2)
            }
    MAX-ACCESS read-write
    STATUS     current
    DESCRIPTION
        "This variable is used to clear all the counters."
    ::= { dsx1CntGrpEntry 6 }


-- ------------------------------------------------------------------------
-- ds1AlmConfig group
--
-- This group contains ds1 line alarm configuration table
-- ------------------------------------------------------------------------

dsx1AlmCnfGrpTable OBJECT-TYPE
    SYNTAX	SEQUENCE OF Dsx1AlmCnfGrpEntry
    MAX-ACCESS	not-accessible
    STATUS	current
    DESCRIPTION
        "The DS1 interface alarm configuration table.
        "
    ::= { dsx1AlmCnfGrp 1 }
dsx1AlmCnfGrpEntry OBJECT-TYPE
    SYNTAX	Dsx1AlmCnfGrpEntry
    MAX-ACCESS  not-accessible
    STATUS  current
    DESCRIPTION
        "An entry in the DS1 Alarm Configuration table."
    INDEX	{ almCnfLineNum }
    ::= { dsx1AlmCnfGrpTable 1 }

Dsx1AlmCnfGrpEntry ::=
    SEQUENCE {
	almCnfLineNum  	        	Integer32,
	redSeverity     	        INTEGER,
	rAISeverity	                INTEGER,
       	nEAlarmUpCount	            	Integer32,
	nEAlarmDownCount                Integer32,
	nEAlarmThreshold                Integer32,
	fEAlarmUpCount                  Integer32,
	fEAlarmDownCount                Integer32,
	fEAlarmThreshold                Integer32,
        statisticalAlarmSeverity        INTEGER,
	lCV15MinThreshold               Integer32,
        lCV24HrThreshold                Integer32,
	lES15MinThreshold               Integer32,
        lES24HrThreshold                Integer32,
	lSES15MinThreshold              Integer32,
        lSES24HrThreshold               Integer32,
	cRC15MinThreshold               Integer32,
        cRC24HrThreshold                Integer32,
	cRCES15MinThreshold             Integer32,
        cRCES24HrThreshold              Integer32,
	cRCSES15MinThreshold            Integer32,
        cRCSES24HrThreshold             Integer32,
	sEFS15MinThreshold              Integer32,
        sEFS24HrThreshold               Integer32,
	aISS15MinThreshold              Integer32,
        aISS24HrThreshold               Integer32,
	uAS15MinThreshold               Integer32,
        uAS24HrThreshold                Integer32
                	}

almCnfLineNum OBJECT-TYPE
    SYNTAX     Integer32 (1..2147483647)
    MAX-ACCESS read-only
    STATUS     current
    DESCRIPTION
        "This object identifies the DS1/E1 interface.
        The value for this object must be same as the
        value of lineNum from dsx1CnfGrpTable."
    ::= { dsx1AlmCnfGrpEntry 1 }

redSeverity OBJECT-TYPE
    SYNTAX	INTEGER {
		    minor(1),
	            major(2)
                }
    MAX-ACCESS	read-write
    STATUS  current
    DESCRIPTION
        "This variable is used to setup the severity of RED
        alarm. So when RED alarm is detected by the card, an
        alarm with appropriate severity status will be sent."
    DEFVAL { major }
    ::= { dsx1AlmCnfGrpEntry 2 }

rAISeverity OBJECT-TYPE
    SYNTAX	INTEGER {
                    minor(1),
                    major(2)
            }
    MAX-ACCESS	read-write
    STATUS  current
    DESCRIPTION
        "This variable is used to setup the severity of RAI
        alarm. So when LOS alarm is detected the card, an
        alarm with appropriate severity status will be sent."
    DEFVAL { minor }
    ::= { dsx1AlmCnfGrpEntry 3 }

nEAlarmUpCount OBJECT-TYPE
    SYNTAX     Integer32 (0..2147483647)
    MAX-ACCESS read-write
    STATUS     current
    DESCRIPTION
        "This parameter specifies the integration counter,
        the local alarms are LOS and LOF. Default value
        is 6 and update counter every 10 ms to reach the
        threshold set in threshold object.
        This is the up counter."
    DEFVAL { 6 }
    ::= { dsx1AlmCnfGrpEntry 4 }

nEAlarmDownCount OBJECT-TYPE
    SYNTAX  Integer32 (0..2147483647)
    MAX-ACCESS	read-write
    STATUS	current
    DESCRIPTION
        "This parameter specifies the integration counter,
        the Near-End alarms are LOS and LOF. Default value
        is 1 and update counter every 10 ms to reach 0.
        This is the down counter."
    DEFVAL { 1 }
    ::= { dsx1AlmCnfGrpEntry 5 }

nEAlarmThreshold OBJECT-TYPE
    SYNTAX     Integer32 (0..2147483647)
    MAX-ACCESS read-write
    STATUS     current
    DESCRIPTION
        "The value set in this object determines the value
        to declare Near-End alarm. A count of 1500 gives
        2.5 sec to declare LOS with an up count value of
        6."
    DEFVAL { 1500 }
    ::= { dsx1AlmCnfGrpEntry 6 }

fEAlarmUpCount OBJECT-TYPE
    SYNTAX  Integer32 (0..2147483647)
    MAX-ACCESS	read-write
    STATUS	current
    DESCRIPTION
        "This parameter specifies the integration counter,
        the Far-End alarms are AIS and YEL. Default value
        is 6 and update counter 10 ms to reach the
        threshold set in threshold object.
        This is the up counter."
    DEFVAL { 6 }
    ::= { dsx1AlmCnfGrpEntry 7 }

fEAlarmDownCount OBJECT-TYPE
    SYNTAX     Integer32 (0..2147483647)
    MAX-ACCESS read-write
    STATUS     current
    DESCRIPTION
        "This parameter specifies the integration counter,
        the Far-End alarms are AIS and YEL. Default value
        is 1 and update counter every 10 ms to reach 0.
        This is the down counter."
    DEFVAL { 1 }
    ::= { dsx1AlmCnfGrpEntry 8 }

fEAlarmThreshold OBJECT-TYPE
    SYNTAX     Integer32 (0..2147483647)
    MAX-ACCESS read-write
    STATUS     current
    DESCRIPTION
        "The value set in this object determines the value
        to declare Far-End alarm. A count of 1500 gives 2.5
        secs to declare LOS with an up count value of 6."
    DEFVAL { 1500 }
    ::= { dsx1AlmCnfGrpEntry 9 }

statisticalAlarmSeverity OBJECT-TYPE
    SYNTAX	INTEGER {
                    minor(1),
                    major(2),
                    inhibit(3)
                }
    MAX-ACCESS	read-write
    STATUS  current
    DESCRIPTION
        "This variable is used to setup the severity of Statistical
        alarm. So when any statistical alarm is detected by the card,
        an alarm with appropriate severity status will be sent."
    ::= { dsx1AlmCnfGrpEntry 10 }

lCV15MinThreshold OBJECT-TYPE
    SYNTAX     Integer32 (0..2147483647)
    MAX-ACCESS read-write
    STATUS     current
    DESCRIPTION
        "Code Violation - is the occurrence of a received CRC-6
        code that is not identical to the corresponding locally.
        calculated code. The value set in this object determines
        the value which when exceeded in a 15 minute window causes
        a statistical alarm to be declared."
    DEFVAL { 14 }
    ::= { dsx1AlmCnfGrpEntry 11 }

lCV24HrThreshold OBJECT-TYPE
    SYNTAX     Integer32 (0..2147483647)
    MAX-ACCESS read-write
    STATUS     current
    DESCRIPTION
        "Code Violation - is the occurence of a received CRC-6
        code that is not identical to the corresponding locally.
        The value set in this object determines the value
        which when exceeded in a sliding 24 hour window causes
        a statistical alarm to be declared. The threshold is
        checked every 15 minutes for the preceding 24 hour interval"
        DEFVAL { 134 }
    ::= { dsx1AlmCnfGrpEntry 12 }

lES15MinThreshold OBJECT-TYPE
    SYNTAX     Integer32 (0..2147483647)
    MAX-ACCESS read-write
    STATUS     current
    DESCRIPTION
        "Errored Second - is any second with at least one
        code violation. The value set in this object determines
        the value which when exceeded in a 15 minute window causes
        a statistical alarm to be declared."
    DEFVAL { 12 }
    ::= { dsx1AlmCnfGrpEntry 13 }

lES24HrThreshold OBJECT-TYPE
    SYNTAX     Integer32 (0..2147483647)
    MAX-ACCESS read-write
    STATUS     current
    DESCRIPTION
        "Errored Second - is any second with at least one
        code violation. The value set in this object determines
        the value which when exceeded in a sliding 24 hour window
        causes a statistical alarm to be declared. The threshold is
        checked every 15 minutes for the preceding 24 hour interval"
    DEFVAL { 121 }
    ::= { dsx1AlmCnfGrpEntry 14 }

lSES15MinThreshold OBJECT-TYPE
    SYNTAX     Integer32 (0..2147483647)
    MAX-ACCESS read-write
    STATUS     current
    DESCRIPTION
        "Severely Errored Second - is any second with 15 or more
        code violations. The value set in this object determines
        the value which when exceeded in a 15 minute window causes
        a statistical alarm to be declared."
    DEFVAL { 10 }
    ::= { dsx1AlmCnfGrpEntry 15 }

lSES24HrThreshold OBJECT-TYPE
    SYNTAX     Integer32 (0..2147483647)
    MAX-ACCESS read-write
    STATUS     current
    DESCRIPTION
        "Severely Errored Second - is any second with 15 or more
        code violations. The value set in this object determines
        the value which when exceeded in a sliding 24 hour window causes
        a statistical alarm to be declared. The threshold is
        checked every 15 minutes for the preceding 24 hour interval"
    DEFVAL { 100 }
    ::= { dsx1AlmCnfGrpEntry 16 }

cRC15MinThreshold OBJECT-TYPE
    SYNTAX     Integer32 (0..2147483647)
    MAX-ACCESS read-write
    STATUS     current
    DESCRIPTION
        "The value set in this object determines the value
        which when exceeded in a 15 minute window causes
        a statistical alarm to be declared."
    DEFVAL { 14 }
    ::= { dsx1AlmCnfGrpEntry 17 }

cRC24HrThreshold OBJECT-TYPE
    SYNTAX     Integer32 (0..2147483647)
    MAX-ACCESS read-write
    STATUS     current
    DESCRIPTION
        "The value set in this object determines the value
        which when exceeded in a sliding 24 hour window causes
        a statistical alarm to be declared. The threshold is
        checked every 15 minutes for the preceding 24 hour interval"
    DEFVAL { 134 }
    ::= { dsx1AlmCnfGrpEntry 18 }

cRCES15MinThreshold OBJECT-TYPE
    SYNTAX     Integer32 (0..2147483647)
    MAX-ACCESS read-write
    STATUS     current
    DESCRIPTION
        "The value set in this object determines the value
        which when exceeded in a 15 minute window causes
        a statistical alarm to be declared."
    DEFVAL { 12 }
::= { dsx1AlmCnfGrpEntry 19 }

cRCES24HrThreshold OBJECT-TYPE
    SYNTAX     Integer32 (0..2147483647)
    MAX-ACCESS read-write
    STATUS     current
    DESCRIPTION
        "The value set in this object determines the value
        which when exceeded in a sliding 24 hour window causes
        a statistical alarm to be declared. The threshold is
        checked every 15 minutes for the preceding 24 hour interval"
    DEFVAL { 121 }
    ::= { dsx1AlmCnfGrpEntry 20 }

cRCSES15MinThreshold OBJECT-TYPE
    SYNTAX     Integer32 (0..2147483647)
    MAX-ACCESS read-write
    STATUS     current
    DESCRIPTION
        "The value set in this object determines the value
        which when exceeded in a 15 minute window causes
        a statistical alarm to be declared."
    DEFVAL { 10 }
    ::= { dsx1AlmCnfGrpEntry 21 }

cRCSES24HrThreshold OBJECT-TYPE
    SYNTAX     Integer32 (0..2147483647)
    MAX-ACCESS read-write
    STATUS     current
    DESCRIPTION
        "The value set in this object determines the value
        when exceeded in a sliding 24 hour window causes
        a statistical alarm to be declared. The threshold is
        checked every 15 minutes for the preceding 24 hour interval"
    DEFVAL { 100 }
    ::= { dsx1AlmCnfGrpEntry 22 }

sEFS15MinThreshold OBJECT-TYPE
    SYNTAX     Integer32 (0..2147483647)
    MAX-ACCESS read-write
    STATUS     current
    DESCRIPTION
        "Severely Errored Framing Second - is a count of one-second
        intervals containing one or more SEF events.
        The value set in this object determines the value
        which when exceeded in a 15 minute window causes
        a statistical alarm to be declared."
    DEFVAL { 2 }
    ::= { dsx1AlmCnfGrpEntry 23 }

sEFS24HrThreshold OBJECT-TYPE
    SYNTAX     Integer32 (0..2147483647)
    MAX-ACCESS read-write
    STATUS     current
    DESCRIPTION
        "Severely Errored Framing Second - is a count of one-second
        intervals containing one or more SEF events.
        The value set in this object determines the value
        which when exceeded in a sliding 24 hour window causes
        a statistical alarm to be declared. The threshold is
        checked every 15 minutes for the preceding 24 hour interval"
    DEFVAL { 17 }
::= { dsx1AlmCnfGrpEntry 24 }

aISS15MinThreshold OBJECT-TYPE
    SYNTAX     Integer32 (0..2147483647)
    MAX-ACCESS read-write
    STATUS     current
    DESCRIPTION
        "Alarm Indication Signal Second - is a count of one-second
        intervals containing one or more incoming AIS.
        The value set in this object determines the value
        which when exceeded in a 15 minute window causes
        a statistical alarm to be declared."
    DEFVAL { 2 }
    ::= { dsx1AlmCnfGrpEntry 25 }

aISS24HrThreshold OBJECT-TYPE
    SYNTAX     Integer32 (0..2147483647)
    MAX-ACCESS read-write
    STATUS     current
    DESCRIPTION
        "Alarm Indication Signal Second - is a count of one-second
        intervals containing one or more incoming AIS.
        The value set in this object determines the value
        which when exceeded in a sliding 24 hour window causes
        a statistical alarm to be declared. The threshold is
        checked every 15 minutes for the preceding 24 hour interval"
    DEFVAL { 17 }
    ::= { dsx1AlmCnfGrpEntry 26 }

uAS15MinThreshold OBJECT-TYPE
    SYNTAX     Integer32 (0..2147483647)
    MAX-ACCESS read-write
    STATUS     current
    DESCRIPTION
        "Unavailable Second - is a count of seconds during
        which the DS1 Layer service is unavailable.
        The value set in this object determines the value
        which when exceeded in a 15 minute window causes
        a statistical alarm to be declared."
    DEFVAL { 10 }
::= { dsx1AlmCnfGrpEntry 27 }

uAS24HrThreshold OBJECT-TYPE
    SYNTAX     Integer32 (0..2147483647)
    MAX-ACCESS read-write
    STATUS     current
    DESCRIPTION
        "Unavailable Second - is a count of seconds during
        which the DS1 Layer service is unavailable.
        The value set in this object determines the value
        which when exceeded in a sliding 24 hour window causes
        a statistical alarm to be declared. The threshold is
        checked every 15 minutes for the preceding 24 hour interval"
    DEFVAL { 10 }
    ::= { dsx1AlmCnfGrpEntry 28 }


-- ------------------------------------------------------------------------
-- ds1Alm group
--
-- This group contains ds1 line alarm table
-- ------------------------------------------------------------------------

dsx1AlmGrpTable OBJECT-TYPE
    SYNTAX	SEQUENCE OF Dsx1AlmGrpEntry
    MAX-ACCESS	not-accessible
    STATUS	current
    DESCRIPTION
        "The DS1 interface alarm configuration table."
    ::= { dsx1AlmGrp 1 }

dsx1AlmGrpEntry OBJECT-TYPE
    SYNTAX	Dsx1AlmGrpEntry
    MAX-ACCESS  not-accessible
    STATUS  current
    DESCRIPTION
        "An entry in the DS1 Alarm table. Each entry
        represents the current, 15 minute and 24 Hour bucket
        intervals for different performance parameters."
    INDEX	{ almLineNum }
    ::= { dsx1AlmGrpTable 1 }

Dsx1AlmGrpEntry ::=
    SEQUENCE {
        almLineNum     	            Integer32,
        lineAlarmState     	    Integer32,
        lineStatisticalAlarmState   Integer32,
        lCVCurrent                  Counter32,
        lCV15MinBucket              Counter32,
        lCV24HrBucket               Counter32,
        lESCurrent                  Counter32,
        lES15MinBucket              Counter32,
        lES24HrBucket               Counter32,
        lSESCurrent                 Counter32,
        lSES15MinBucket             Counter32,
        lSES24HrBucket              Counter32,
        cRCCurrent                  Counter32,
        cRC15MinBucket              Counter32,
        cRC24HrBucket               Counter32,
        cRCESCurrent                Counter32,
        cRCES15MinBucket            Counter32,
        cRCES24HrBucket             Counter32,
        cRCSESCurrent               Counter32,
        cRCSES15MinBucket           Counter32,
        cRCSES24HrBucket            Counter32,
        sEFSCurrent                 Counter32,
        sEFS15MinBucket             Counter32,
        sEFS24HrBucket              Counter32,
        aISSCurrent                 Counter32,
        aISS15MinBucket             Counter32,
        aISS24HrBucket              Counter32,
        uASCurrent                  Counter32,
        uAS15MinBucket              Counter32,
        uAS24HrBucket               Counter32,
        percentEFS                  Integer32,
        alarmClrButton		    INTEGER
    }

almLineNum OBJECT-TYPE
    SYNTAX     Integer32 (1..2147483647)
    MAX-ACCESS read-only
    STATUS     current
    DESCRIPTION
        "This object identifies the DS1/E1 interface.
        The value for this object must be same as the
        value of lineNum from dsx1CnfGrpTable."
    ::= { dsx1AlmGrpEntry 1 }

lineAlarmState OBJECT-TYPE
    SYNTAX	Integer32 (0..65535)
    MAX-ACCESS	read-only
    STATUS  current
    DESCRIPTION
        "This variable is a bitmap of the DSX1 Line Alarms.
        A value of zero indicates no alarms.
        Itemized below are the individual bits:
        BitPosition    Alarm
        -----------    -----
        0              Receiving RAI
        1              Transmitting RAI
        2              Receiving AIS
        3              Transmitting AIS
        4              Receiving OOF
        5              Receiving LOS
        6              Near End Local Loopback in effect
        7              Near End Remote Loopback in effect
        8              Near End Remote Payload Loopback
        9              Receiving CRC MF OOF (E1)
        10             Receiving Sig MF OOF (E1)
        11             Receiving MF RAI (E1)
        12             Receiving MF AIS (E1)
        13             BERT in effect
        14             Far End Remote Loopback in effect
        15             Detected Near End Remote Loopback in
                       effect"
    ::= { dsx1AlmGrpEntry 2 }

lineStatisticalAlarmState OBJECT-TYPE
    SYNTAX     Integer32 (0..2147483647)
    MAX-ACCESS read-only
    STATUS     current
    DESCRIPTION
        "This variable is a bitmap of the DSX1 Line Statistical
        Alarms. A value of zero indicates no alarms.
        Itemized below are the individual alarm bits:
        BitPosition    Alarm
        -----------    -----
        0              LCV 15 minute threshold exceeded
        1              LCV 24 hour threshold exceeded
        2              LES 15 minute threshold exceeded
        3              LES 24 hour threshold exceeded
        4              LSES 15 minute threshold exceeded
        5              LSES 24 hour threshold exceeded
        6              CRC 15 minute threshold exceeded
        7              CRC 24 hour threshold exceeded
        8              CRCES 15 minute threshold exceeded
        9              CRCES 24 hour threshold exceeded
        10             CRCSES 15 minute threshold exceeded
        11             CRCSES 24 hour threshold exceeded
        12             SEFS 15 minute threshold exceeded
        13             SEFS 24 hour threshold exceeded
        14             AISS 15 minute threshold exceeded
        15             AISS 24 hour threshold exceeded
        16             UAS 15 minute threshold exceeded
        17             UAS 24 hour threshold exceeded."
    ::= { dsx1AlmGrpEntry 3 }
lCVCurrent      OBJECT-TYPE
    SYNTAX	Counter32
    MAX-ACCESS	read-only
    STATUS	current
    DESCRIPTION
        "This counter counts the number of
        Line code violations encountered by the interface."
    ::= { dsx1AlmGrpEntry 4 }

lCV15MinBucket  OBJECT-TYPE
    SYNTAX     Counter32
    MAX-ACCESS read-only
    STATUS     current
    DESCRIPTION
        "The counter associated with the number of
        Line code violations in the last 15 minute period
        encountered by the interface."
    ::= { dsx1AlmGrpEntry 5 }

lCV24HrBucket   OBJECT-TYPE
    SYNTAX     Counter32
    MAX-ACCESS read-only
    STATUS     current
    DESCRIPTION
        "The counter associated with the number of
        Line code violations in the last 24 hour period
        encountered by the interface."
    ::= { dsx1AlmGrpEntry 6 }

lESCurrent      OBJECT-TYPE
    SYNTAX     Counter32
    MAX-ACCESS read-only
    STATUS     current
    DESCRIPTION
        "This counter counts the number of
        Line code violations Errored Seconds
        encountered by the interface."
    ::= { dsx1AlmGrpEntry 7 }

lES15MinBucket  OBJECT-TYPE
    SYNTAX     Counter32
    MAX-ACCESS read-only
    STATUS     current
    DESCRIPTION
        "This counter counts the number of
        Line code violations Errored Seconds in the last 15 minutes
        encountered by the interface."
    ::= { dsx1AlmGrpEntry 8 }

lES24HrBucket   OBJECT-TYPE
    SYNTAX     Counter32
    MAX-ACCESS read-only
    STATUS     current
    DESCRIPTION
        "This counter counts the number of
        Line code violations Errored Seconds in the last 24 hours
        encountered by the interface."
    ::= { dsx1AlmGrpEntry 9 }

lSESCurrent     OBJECT-TYPE
    SYNTAX	Counter32
    MAX-ACCESS	read-only
    STATUS	current
    DESCRIPTION
        "This counter counts the number of
        Line code violations Severely Errored Seconds
        encountered by the interface."
    ::= { dsx1AlmGrpEntry 10 }

lSES15MinBucket  OBJECT-TYPE
    SYNTAX     Counter32
    MAX-ACCESS read-only
    STATUS     current
    DESCRIPTION
        "This counter counts the number of
        LCV Severely Errored Seconds in the last 15 minutes
        encountered by the interface."
    ::= { dsx1AlmGrpEntry 11 }

lSES24HrBucket  OBJECT-TYPE
    SYNTAX     Counter32
    MAX-ACCESS read-only
    STATUS     current
    DESCRIPTION
        "This counter counts the number of
        LCV Severely Errored Seconds in the last 24 hours
        encountered by the interface."
    ::= { dsx1AlmGrpEntry 12 }

cRCCurrent    OBJECT-TYPE
    SYNTAX     Counter32
    MAX-ACCESS read-only
    STATUS     current
    DESCRIPTION
        "This counter counts the number of
        P Bit code violations
        encountered by the interface."
    ::= { dsx1AlmGrpEntry 13 }

cRC15MinBucket  OBJECT-TYPE
    SYNTAX     Counter32
    MAX-ACCESS read-only
    STATUS     current
    DESCRIPTION
        "This counter counts the number of
        P Bit code violations in the last 15 minutes
        encountered by the interface."
    ::= { dsx1AlmGrpEntry 14 }

cRC24HrBucket   OBJECT-TYPE
    SYNTAX     Counter32
    MAX-ACCESS read-only
    STATUS     current
    DESCRIPTION
        "This counter counts the number of
        P Bit code violations in the last 24 hours
        encountered by the interface."
    ::= { dsx1AlmGrpEntry 15 }
cRCESCurrent      OBJECT-TYPE
    SYNTAX     Counter32
    MAX-ACCESS read-only
    STATUS     current
    DESCRIPTION
        "This counter counts the number of
        PCV Errored Seconds
        encountered by the interface."
::= { dsx1AlmGrpEntry 16 }

cRCES15MinBucket  OBJECT-TYPE
    SYNTAX     Counter32
    MAX-ACCESS read-only
    STATUS     current
    DESCRIPTION
        "This counter counts the number of
        PCV Errored Seconds in the last 15 minutes
        encountered by the interface."
    ::= { dsx1AlmGrpEntry 17 }

cRCES24HrBucket   OBJECT-TYPE
    SYNTAX     Counter32
    MAX-ACCESS read-only
    STATUS     current
    DESCRIPTION
        "This counter counts the number of
        PCV Errored Seconds in the last 24 hours
        encountered by the interface."
    ::= { dsx1AlmGrpEntry 18 }

cRCSESCurrent     OBJECT-TYPE
    SYNTAX     Counter32
    MAX-ACCESS read-only
    STATUS     current
    DESCRIPTION
        "This counter counts the number of
        P Bit code violations Severely Errored Seconds
        encountered by the interface."
    ::= { dsx1AlmGrpEntry 19 }

cRCSES15MinBucket  OBJECT-TYPE
    SYNTAX     Counter32
    MAX-ACCESS read-only
    STATUS     current
    DESCRIPTION
        "This counter counts the number of
        PCV Severely Errored Seconds in the last 15 minutes
        encountered by the interface."
    ::= { dsx1AlmGrpEntry 20 }

cRCSES24HrBucket  OBJECT-TYPE
    SYNTAX     Counter32
    MAX-ACCESS read-only
    STATUS     current
    DESCRIPTION
        "This counter counts the number of
        PCV Severely Errored Seconds in the last 24 hours
        encountered by the interface."
    ::= { dsx1AlmGrpEntry 21 }

sEFSCurrent     OBJECT-TYPE
    SYNTAX     Counter32
    MAX-ACCESS read-only
    STATUS     current
    DESCRIPTION
        "This counter counts the number of
        Severely Errored Framing Seconds
        encountered by the interface."
    ::= { dsx1AlmGrpEntry 22 }

sEFS15MinBucket  OBJECT-TYPE
    SYNTAX     Counter32
    MAX-ACCESS read-only
    STATUS     current
    DESCRIPTION
        "This counter counts the number of
        Severely Errored Framing Seconds in the last 15 minutes
        encountered by the interface."
    ::= { dsx1AlmGrpEntry 23 }

sEFS24HrBucket  OBJECT-TYPE
    SYNTAX     Counter32
    MAX-ACCESS read-only
    STATUS     current
    DESCRIPTION
        "This counter counts the number of
        Severely Errored Framing Seconds in the last 24 hours
        encountered by the interface."
    ::= { dsx1AlmGrpEntry 24 }

aISSCurrent     OBJECT-TYPE
    SYNTAX     Counter32
    MAX-ACCESS read-only
    STATUS     current
    DESCRIPTION
        "This counter counts the number of
        AIS Severely Errored Seconds
        encountered by the interface."
    ::= { dsx1AlmGrpEntry 25 }

aISS15MinBucket  OBJECT-TYPE
    SYNTAX     Counter32
    MAX-ACCESS read-only
    STATUS     current
    DESCRIPTION
        "This counter counts the number of
        AIS Severely Errored Seconds in the last 15 minutes
        encountered by the interface."
    ::= { dsx1AlmGrpEntry 26 }

aISS24HrBucket  OBJECT-TYPE
    SYNTAX     Counter32
    MAX-ACCESS read-only
    STATUS     current
    DESCRIPTION
        "This counter counts the number of
        AIS Severely Errored Seconds in the last 24 hours
        encountered by the interface."
    ::= { dsx1AlmGrpEntry 27 }

uASCurrent      OBJECT-TYPE
    SYNTAX     Counter32
    MAX-ACCESS read-only
    STATUS     current
    DESCRIPTION
        "This counter counts the number of
        Unavailable Seconds
        encountered by the interface."
    ::= { dsx1AlmGrpEntry 28 }

uAS15MinBucket  OBJECT-TYPE
    SYNTAX     Counter32
    MAX-ACCESS read-only
    STATUS     current
    DESCRIPTION
        "This counter counts the number of
        Unavailable Seconds in the last 15 minutes
        encountered by the interface."
    ::= { dsx1AlmGrpEntry 29 }

uAS24HrBucket   OBJECT-TYPE
    SYNTAX     Counter32
    MAX-ACCESS read-only
    STATUS     current
    DESCRIPTION
        "This counter counts the number of
        Unavailable Seconds in the last 24 hours
        encountered by the interface."
    ::= { dsx1AlmGrpEntry 30 }

percentEFS      OBJECT-TYPE
    SYNTAX     Integer32(0..100)
    MAX-ACCESS read-only
    STATUS     current
    DESCRIPTION
        "This counter counts the %LCV
        Error Free Seconds."
    ::= { dsx1AlmGrpEntry 31 }

alarmClrButton OBJECT-TYPE
    SYNTAX  INTEGER {
                noaction (1),
                clear (2)
            }
    MAX-ACCESS read-write
    STATUS     current
    DESCRIPTION
        "This variable is used to clear all the alarms
        for the line.
            1 = No action
            2 = Clear alarm
        "
    ::= { dsx1AlmGrpEntry 32 }

-- conformance information

cmDsx1MIBConformance  OBJECT IDENTIFIER ::= { ciscoMgx82xxDsx1MIB 2 }

cmDsx1MIBGroups       OBJECT IDENTIFIER ::=
                              { cmDsx1MIBConformance 1 }

cmDsx1MIBCompliances  OBJECT IDENTIFIER ::=
                              { cmDsx1MIBConformance 2 }

-- compliance statements

cmDsx1Compliance MODULE-COMPLIANCE
    STATUS  current
    DESCRIPTION
        "The compliance statement for objects related
        to DS1/E1 mib."
    MODULE  -- this module
        MANDATORY-GROUPS {
            cmDsx1GeneralGroup,
            cmDsx1ConfGroup,
            cmDsx1CountGroup,
            cmDsx1AlarmConfGroup,
            cmDsx1AlarmGroup
        }
    ::= { cmDsx1MIBCompliances 1 }

cmDsx1GeneralGroup OBJECT-GROUP
    OBJECTS {
        lineNumofValidEntries
     }
     STATUS current
     DESCRIPTION
         "The collection of objects used for
         DS1/E1 interfaces."
     ::= { cmDsx1MIBGroups 1 }

cmDsx1ConfGroup OBJECT-GROUP
    OBJECTS {
        lineNum,
        lineConnectorType,
	lineEnable,
	lineType,
	lineCoding,
       	lineLength,
	lineXmtClockSource,
	lineLoopbackCommand,
	lineSendCode,
	lineLoopbackCodeDetection,
	lineUsedTimeslotsBitMap,
	lineBERTEnable,
	lineBERTPattern,
	lineBERTResult,
	bERTResultClrButton
      }
      STATUS current
      DESCRIPTION
          "The collection of objects used for
          DS1/E1 interface configuration."
      ::= { cmDsx1MIBGroups 2 }

cmDsx1CountGroup OBJECT-GROUP
    OBJECTS {
        cntLineNum,
	rcvLOSCount,
	rcvOOFCount,
	rcvRAICount,
	rcvFECount,
	counterClearButton
      }
    STATUS current
      DESCRIPTION
         "The collection of objects related to
         DS1/E1 statistics."
      ::= { cmDsx1MIBGroups 3 }

cmDsx1AlarmConfGroup OBJECT-GROUP
    OBJECTS {
        almCnfLineNum,
        redSeverity,
        rAISeverity,
        nEAlarmUpCount,
        nEAlarmDownCount,
        nEAlarmThreshold,
        fEAlarmUpCount,
        fEAlarmDownCount,
        fEAlarmThreshold,
        statisticalAlarmSeverity,
        lCV15MinThreshold,
        lCV24HrThreshold,
        lES15MinThreshold,
        lES24HrThreshold,
        lSES15MinThreshold,
        lSES24HrThreshold,
        cRC15MinThreshold,
        cRC24HrThreshold,
        cRCES15MinThreshold,
        cRCES24HrThreshold,
        cRCSES15MinThreshold,
        cRCSES24HrThreshold,
        sEFS15MinThreshold,
        sEFS24HrThreshold,
        aISS15MinThreshold,
        aISS24HrThreshold,
        uAS15MinThreshold,
        uAS24HrThreshold
       }
    STATUS current
    DESCRIPTION
        "The collection of objects used for
         DS1/E1 Alarm threshold configuration."
      ::= { cmDsx1MIBGroups 4 }

cmDsx1AlarmGroup OBJECT-GROUP
    OBJECTS {
        almLineNum,
        lineAlarmState,
        lineStatisticalAlarmState,
        lCVCurrent,
        lCV15MinBucket,
        lCV24HrBucket,
        lESCurrent,
        lES15MinBucket,
        lES24HrBucket,
        lSESCurrent,
        lSES15MinBucket,
        lSES24HrBucket,
        cRCCurrent,
        cRC15MinBucket,
        cRC24HrBucket,
        cRCESCurrent,
        cRCES15MinBucket,
        cRCES24HrBucket,
        cRCSESCurrent,
        cRCSES15MinBucket,
        cRCSES24HrBucket,
        sEFSCurrent,
        sEFS15MinBucket,
        sEFS24HrBucket,
        aISSCurrent,
        aISS15MinBucket,
        aISS24HrBucket,
        uASCurrent,
        uAS15MinBucket,
        uAS24HrBucket,
        percentEFS,
        alarmClrButton
}
     STATUS current
     DESCRIPTION
         "The collection of objects used for
         DS1/E1 Alarm configuration."
     ::= { cmDsx1MIBGroups 5 }

END
