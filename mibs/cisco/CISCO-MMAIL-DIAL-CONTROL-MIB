-- *****************************************************************
-- CISCO-MMAIL-DIAL-CONTROL-MIB.my:
-- Multi-media Mail Dial Control MIB file
--
-- May 1998  Hongchi Shih
--
-- Copyright (c) 1998, 1999 by cisco Systems, Inc.
-- All rights reserved.
-- *****************************************************************

CISCO-MMAIL-DIAL-CONTROL-MIB DEFINITIONS ::= BEGIN

IMPORTS
        MODULE-IDENTITY,
        OBJECT-TYPE,
        IpAddress
                FROM SNMPv2-SMI
        TEXTUAL-CONVENTION,
        DisplayString,
        TruthValue
                FROM SNMPv2-TC
        MODULE-COMPLIANCE,
        OBJECT-GROUP
                FROM SNMPv2-CONF
        callActiveSetupTime,
        callActiveIndex,
        AbsoluteCounter32
                FROM DIAL-CONTROL-MIB
        cCallHistoryIndex
                FROM CISCO-DIAL-CONTROL-MIB
        CvcGUid
                FROM CISCO-VOICE-COMMON-DIAL-CONTROL-MIB
        ifIndex
                FROM IF-MIB
        ciscoMgmt
                FROM CISCO-SMI;


ciscoMediaMailDialControlMIB MODULE-IDENTITY
        LAST-UPDATED    "200202250000Z"
        ORGANIZATION    "Cisco Systems, Inc."
        CONTACT-INFO
                "       Cisco Systems
                        Customer Service

                Postal: 170 W. Tasman Drive
                        San Jose, CA  95134
                        USA

                Tel: +1 800 553-NETS

                E-mail: cs-voice@cisco.com"
        DESCRIPTION
                "This MIB module enhances the IETF Dial Control MIB
                 (RFC2128) for providing management of dial peers on
                 both a circuit-switched telephony network, and a mail
                 server on IP network.
                "
        REVISION        "200202250000Z"
        DESCRIPTION
                "Fix for CSCdu86743 and CSCdu86778. The change include:
                 - DEFVAL for cmmIpPeerCfgDeliStatNotification
                 - Add dsnMdn option for cmmIpCallActiveNotification
                   and cmmIpCallHistoryNotification
                 - Object descriptor name change due to length
                   exceeding 32. These are :
                   cmmIpPeerCfgDeliStatNotification
                   cmmIpCallHistoryAcceptMimeTypes
                   cmmIpCallHistoryDiscdMimeTypes
                 - All the lines exceed length 72 are being rewitten
                 "
        ::= { ciscoMgmt 102 }


--
-- Textual Conventions
--

--
--  Media Mail image resolution textual convention
--

CmmImgResolution ::= TEXTUAL-CONVENTION
        STATUS      current
        DESCRIPTION
            "Represents possible image resolution in Media Mail.
             standard  - standard resolution.
             fine      - fine resolution.
             superFine - super fine resolution.
            "
        REFERENCE
            "RFC2301: Section 4.5.2 Encoding and Resolution."

        SYNTAX      INTEGER {
            standard         (2),
            fine             (3),
            superFine        (4)
        }

CmmImgResolutionOrTransparent ::= TEXTUAL-CONVENTION

        STATUS      current
        DESCRIPTION
            "Represents possible image resolution and transparent mode.
             transparent - pass through mode.
             standard    - standard resolution.
             fine        - fine resolution.
             superFine   - super fine resolution.
            "
        REFERENCE
            "RFC2301: Section 4.5.2 Encoding and Resolution."
        SYNTAX      INTEGER {
            transparent      (1),
            standard         (2),
            fine             (3),
            superFine        (4)
        }

CmmImgEncoding ::= TEXTUAL-CONVENTION
        STATUS      current
        DESCRIPTION
            "Represents possible image encoding types in Media Mail.
             modifiedHuffman     - Modified Huffman (MH).
             modifiedREAD        - Modified READ (MR).
             modifiedMR          - Modified Modified READ (MMR).
            "
        REFERENCE
            "RFC2301: Section 1.3 Overview of this draft.
             ITU-T Rec. T.4 (MH - Modified Huffman).
             ITU-T Rec. T.4 (MR - Modified READ).
             ITU-T Rec. T.6 (MRR - Modified MR).
            "
        SYNTAX      INTEGER {
            modifiedHuffman      (2),
            modifiedREAD         (3),
            modifiedMR           (4)
        }

CmmImgEncodingOrTransparent ::= TEXTUAL-CONVENTION
        STATUS      current
        DESCRIPTION
            "Represents possible image encoding types and transparent
             mode.
             transparent          - pass through mode.
             modifiedHuffman      - Modified Huffman (MH).
             modifiedREAD         - Modified READ (MR).
             modifiedMR           - Modified Modified READ (MMR).
            "
        REFERENCE
            "RFC2301: Section 1.3 Overview of this draft.
             ITU-T Rec. T.4 (MH - Modified Huffman).
             ITU-T Rec. T.4 (MR - Modified READ).
             ITU-T Rec. T.6 (MRR - Modified MR).
            "
        SYNTAX      INTEGER {
            transparent          (1),
            modifiedHuffman      (2),
            modifiedREAD         (3),
            modifiedMR           (4)
        }

CmmFaxHeadingString ::= TEXTUAL-CONVENTION
        STATUS      current
        DESCRIPTION
            "The regular expression for the FAX heading at the top of
             cover page or text page.  The regular expression syntax
             used in this object is the same as that used by the UNIX
             grep program. The embedded pattern substitutions are
             defined as follows:
             $p$ - translates to the page number as passed by
                   FAX processing.
             $a$ - translates to human readable year-month-day
                   that is defined in DateAndTime of SNMPv2-TC.
             $d$ - translates to the called party address.
             $s$ - translates to the calling party address.
             $t$ - translates to the time of transmission of the
                   first FAX/image page. The human readable format
                   is defined as year-month-day,hour:minutes:second
                   in the DateAndTime of SNMPv2-TC.

             Example,
             'Date:$a$' means replacing the heading of a FAX page with
             the the string and date substitution.

             'From $s$ Broadcast Service' means replacing the heading
              of FAX page with the the string and calling party address
              substitution.

             'Page:$p$' means replacing the heading of a FAX page with
             the string and page number substitution.
            "
        SYNTAX      DisplayString (SIZE(0..80))


--
-- Overview of Media Mail Gateway Call between Data and Telephony
-- network
--
--     | Media Mail   |  Voice  |   Voice    |   Telephony  |
-- <===+==== Peer ====+=Gateway=+=== Peer ===+= Interfaces =+==========>
-- Data| :  I | T | M | Media   |            | DS0    T1/E1 | Telephony
-- Network |P | C | A | Mail    | Voice/FAX  | ISDN B       | Network
--     |      | P | I | session |encapsulation        FXO   |
--     |      |   | L |         |            |        E&M   |
--     |      |   |   |         |            |        FXS   |
--                              |Voice      P|
--   <==========================+Fax   <=*=>C+================>
--           E-Mail              Mail    |  M    PCM data
--                                     CODEC
--

--
-- Media Mail Gateway call leg connections are as follows:
--
--  [1] Call establishment using a local telephony interface
--  Call establishment using a local telephony interface involves
--  the Media Session Control module, the Media Mail Protocol module,
--  and the Telephony interface itself. Media Session Control is
--  responsible for controlling the local telephony interfaces and
--  assigning a Voice/FAX encapsulation module, with its associated
--  CODEC  (most CODECs execute in DSP code) or FAX modem to the call.
--  The CODEC/FAX modem is responsible for encode/decode, as well has
--  the generation and detection of signaling information, such as call
--  progress tones, DTMF or pulse dialing signals, etc. During an active
--  call, the selected CODEC/Fax modem is responsible for collecting the
--  voice and fax statistics for the call.
--
-- [2] Call establishment using the media session protocol over IP
-- network
-- Call establishment using the media session protocol over IP network
-- involves the Media Session Control module and
-- Media Mail encapsulation module.
-- Media Session Control is responsible for controlling the selected
-- session protocol and assigning a Media encapsulation module with
-- store and forward method for media mail connection.
--
-- This MIB uses IETF Dial Control MIB (RFC2128) as a base and adds
-- features to support media mail calls via a Multi service gateway.
-- The gateway call supports connection establishment of both telephony
-- circuit-switched call and the media mail session.
-- The following architectural diagram illustrates this:
--
-- +================================================================+
-- |                    Media Mail Gateway                          |
-- +===+ +=========+ +=======+ +=======+ +=========+ +=============+
--     | |         | |       | |       | |         | |
--     | |         | |       | |       | |         | |
--     | |         | |       | |       | |         | |
--     | |         | |       | |       | |         | |
--     | |         | |       | |       | |         | |
--     | |         | |       | |       | |         | |
--     | |         | |       | |       | |         | |
--     | |         | |       | |       | |         | |<== appears active
--   +=+ +=+     +=+ +=+   +=+ +=+   +=+ +=+     +=+ +=+
--   |VOICE|     |VOICE|   |VOICE|   |VOICE|     |MMAIL| VOICE
--   | for |     | for |   | for |   | for |     | for | ifEntry with
--   |Peer1|     |Peer2|   |Peer3|   |Peer4|     |Peer5| shadow
--   |     |     |     |   |     |   |     |     |     | Voice PeerEntry
--   +=====+     +=+ +=+   +=+ +=+   +=+ +=+     +=====+
--                 | |       | |       | |           <== appears active
--  +=======+   +==+ +==+ +==+ +==+    | |           when the VOICE
--  |   B   |   |   B   | |  DS0  |    | |           connects to
--  |channel|   |channel| |channel|    | |           telephony interface
--  +==+ +==+   +==+ +==+ +==+ +==+    | |
--     | |         | |       | |       | |
-- +===+ +=========+ +==+ +==+ +==+ +==+ +======+
-- |  ISDN BRI/PRI      | | T1/E1 | |E&M/FXO/FXS|
-- +====================+ +=======+ +===========+
--
--
-- In this model, each Voice peer must have an associated encapsulation
-- interface ifEntry. Refer to CISCO-VOICE-DIAL-CONTROL-MIB for the
-- detailed information.
--
-- Each Media Mail Encapsulation ifEntry contains the ifType
-- 'mediaMailOverIp'
-- For each Media Mail encapsulation associated peer, the
-- dialCtlPeerCfgIfType object of IETF Dial Control MIB must set to
-- 'other' and dialCtlPeerCfgLowerIf
-- must set to '0'.
--


-- ifEntry for the 'mediaMailOverIp' encapsulation
--
-- The ifEntry for the 'mediaMailOverIp' encapsulation supports the
-- ifGeneralInformationGroup of Cisco IF-MIB

-- ifTable       Comments
-- ============= ===========================================
-- ifIndex       Each mediaMailOverIp encapsulation is represented by an
--               ifEntry.
-- ifDescr       Textual description
--               "Media Mail Over IP Encapsulation: ".
-- ifType        The IANA value of mediaMailOverIp(139).
-- ifSpeed       contains a zero value.
-- ifPhysAddress contains an octet string of zero length.
--
-- ifAdminStatus The desired administrative status of the
--               Media Mail encapsulation.
-- ifOperStatus  The current operational status of the Media Mail
--               encapsulation.
-- ifLastChange  Refer to RFC 1573.
-- ifLinkUpDownTrapEnable
--               Only support the read-only ifLinkUpDownTrapEnable.
--               It contains a 'disabled(2)' value.
-- ifConnectorPresent
--               Refer to RFC 1573.
-- ifHighSpeed   contains a zero value.
-- ifName        Refer to RFC 1573.
-- ifAlias       Only support the read-only ifAlias. It contains an
--               octet string of zero length.
--


-- Media Mail Dial Control MIB objects definitions

cmmdcMIBObjects OBJECT IDENTIFIER ::= { ciscoMediaMailDialControlMIB 1 }


-- The Media Mail Dial Control MIB consists of the following group
-- [1] Media Mail Peer Configuration Group (cmmPeer)
-- [2] Media Mail Call Active Group(cmmCallActive)
-- [3] Media Mail Call History Group(cmmCallHistory)
-- [4] FAX General configuration Group(cmmFaxGeneralCfg)

cmmPeer               OBJECT IDENTIFIER ::= { cmmdcMIBObjects 1 }
cmmCallActive         OBJECT IDENTIFIER ::= { cmmdcMIBObjects 2 }
cmmCallHistory        OBJECT IDENTIFIER ::= { cmmdcMIBObjects 3 }
cmmFaxGeneralCfg      OBJECT IDENTIFIER ::= { cmmdcMIBObjects 4 }


--
--  Media Mail specific Peer Configuration Table
--

cmmIpPeerCfgTable OBJECT-TYPE
        SYNTAX      SEQUENCE OF CmmIpPeerCfgEntry
        MAX-ACCESS  not-accessible
        STATUS      current
        DESCRIPTION
            "The table contains the Media mail peer specific
             information that is required to accept mail connection or
             to which it will connect them via IP network with the
             specified session protocol in cmmIpPeerCfgSessionProtocol.
            "
       ::= { cmmPeer 1 }

cmmIpPeerCfgEntry OBJECT-TYPE
        SYNTAX      CmmIpPeerCfgEntry
        MAX-ACCESS  not-accessible
        STATUS      current
        DESCRIPTION
            "A single Media Mail specific Peer. One entry per media mail
             encapsulation. The entry is created when its associated
             'mediaMailOverIp(139)' encapsulation ifEntry is created.
             This entry is deleted when its associated ifEntry is
             deleted.
            "
        INDEX       { ifIndex }
      ::= { cmmIpPeerCfgTable 1 }

CmmIpPeerCfgEntry ::= SEQUENCE {
      cmmIpPeerCfgSessionProtocol         INTEGER,
      cmmIpPeerCfgSessionTarget           DisplayString,
      cmmIpPeerCfgImgEncodingType         CmmImgEncodingOrTransparent,
      cmmIpPeerCfgImgResolution           CmmImgResolutionOrTransparent,
      cmmIpPeerCfgMsgDispoNotification    TruthValue,
      cmmIpPeerCfgDeliStatNotification    BITS
     }

cmmIpPeerCfgSessionProtocol OBJECT-TYPE
        SYNTAX      INTEGER {
            smtp     (1)

        }
        MAX-ACCESS  read-write
        STATUS      current
        DESCRIPTION
            "The object specifies the session protocol to be used
             for  sending/receiving media mail between local and remote
             mail sever via IP network.
             smtp - Simple Mail Transfer Protocol.
            "
        DEFVAL      { smtp }
        ::= { cmmIpPeerCfgEntry 1 }


cmmIpPeerCfgSessionTarget OBJECT-TYPE
        SYNTAX      DisplayString
        MAX-ACCESS  read-write
        STATUS      current
        DESCRIPTION
            "The object specifies the session target of the peer.
             Session Targets definitions:
             The session target has the syntax used by the IETF service
             location protocol. The syntax is as follows:

             mapping-type:type-specific-syntax

             The mapping-type specifies a scheme for mapping the
             matching dial string to a session target. The
             type-specific-syntax is exactly that, something that the
             particular mapping scheme can understand.
             For example,
             Session target    mailto:+$d$@fax.cisco.com

             The valid Mapping type definitions for the peer are as
             follows:
             mailto  - Syntax: mailto:w@x.y.z
            "
        DEFVAL      { "" }
        ::= { cmmIpPeerCfgEntry 2 }

cmmIpPeerCfgImgEncodingType OBJECT-TYPE
        SYNTAX      CmmImgEncodingOrTransparent
        MAX-ACCESS  read-write
        STATUS      current
        DESCRIPTION
            "This object specifies the image encoding conversion for
             outgoing mail connection to mail server.
             If the value of this object is transparent, it means
             'pass through' without encoding conversion.
            "
        DEFVAL      { transparent }
        ::= { cmmIpPeerCfgEntry 3 }

cmmIpPeerCfgImgResolution OBJECT-TYPE
        SYNTAX      CmmImgResolutionOrTransparent
        MAX-ACCESS  read-write
        STATUS      current
        DESCRIPTION
            "This object specifies the image resolution conversion for
             outgoing mail connection to mail server.
             If the value of this object is transparent, it means
             'pass through' without resolution conversion.
            "
        DEFVAL      { transparent }
        ::= { cmmIpPeerCfgEntry 4 }

cmmIpPeerCfgMsgDispoNotification OBJECT-TYPE
        SYNTAX      TruthValue
        MAX-ACCESS  read-write
        STATUS      current
        DESCRIPTION
            "This object specifies the Request of Message Disposition
             Notification.
             true  - Request Message Disposition Notification.
             false - No  Message Disposition Notification.
            "
        DEFVAL      { false }
        ::= { cmmIpPeerCfgEntry 5 }

cmmIpPeerCfgDeliStatNotification OBJECT-TYPE
        SYNTAX      BITS {
            success  (0),
            failure  (1),
            delayed  (2)
        }
        MAX-ACCESS  read-write
        STATUS      current
        DESCRIPTION
            "This object specifies the Request of Delivery Status
             Notification.
             success - Request Notification if the media mail is
                       successfully delivered to the recipient.
             failure - Request Notification if the media mail is failed
                       to deliver to the recipient.
             delayed - Request Notification if the media mail is delayed
                       to deliver to the recipient.
            "
        DEFVAL      { {} }
        ::= { cmmIpPeerCfgEntry 6 }


--**********************************************************************
-- Media Mail Call Active Group
--**********************************************************************
--
-- For a Media Mail Gateway call, it normally has two or  more call leg
-- entries appear in the call active table after a successful
-- Gateway call establishment between a mail server and FAX or voice
-- capable device(s) on the telephony network. All call legs for a given
-- gateway call will contain the same global call identifier.
--

--
-- Media Mail Call Active Table
--

cmmIpCallActiveTable OBJECT-TYPE
        SYNTAX      SEQUENCE OF CmmIpCallActiveEntry
        MAX-ACCESS  not-accessible
        STATUS      current
        DESCRIPTION
            "This table is the Media Mail over IP extension to the call
             active table of IETF Dial Control MIB. It contains Media
             Mail over IP call leg information.
            "
        ::= { cmmCallActive  1 }

cmmIpCallActiveEntry OBJECT-TYPE
        SYNTAX      CmmIpCallActiveEntry
        MAX-ACCESS  not-accessible
        STATUS      current
        DESCRIPTION
            "The information regarding a single Media mail over IP call
             leg. The call leg entry is identified by using the same
             index objects that are used by Call Active table of IETF
             Dial Control MIB to identify the call.
             An entry of this table is created when its associated call
             active entry in the IETF Dial Control MIB is created and
             the call active entry contains information for the call
             establishment to the mail server peer on the IP network
             via a Media Mail over IP peer.
             The entry is deleted when its associated call active entry
             in the IETF Dial Control MIB is deleted.
            "
        INDEX       { callActiveSetupTime, callActiveIndex }
        ::= { cmmIpCallActiveTable 1 }


CmmIpCallActiveEntry ::=
        SEQUENCE {
            cmmIpCallActiveConnectionId              CvcGUid,
            cmmIpCallActiveRemoteIPAddress           IpAddress,
            cmmIpCallActiveSessionProtocol           INTEGER,
            cmmIpCallActiveSessionTarget             DisplayString,
            cmmIpCallActiveMessageId                 DisplayString,
            cmmIpCallActiveAccountId                 DisplayString,
            cmmIpCallActiveImgEncodingType           CmmImgEncoding,
            cmmIpCallActiveImgResolution             CmmImgResolution,
            cmmIpCallActiveAcceptMimeTypes           AbsoluteCounter32,
            cmmIpCallActiveDiscdMimeTypes            AbsoluteCounter32,
            cmmIpCallActiveNotification              INTEGER
        }

cmmIpCallActiveConnectionId OBJECT-TYPE
        SYNTAX      CvcGUid
        MAX-ACCESS  read-only
        STATUS      current
        DESCRIPTION
            "The global call identifier for the gateway call."
        ::= { cmmIpCallActiveEntry 1 }


cmmIpCallActiveRemoteIPAddress OBJECT-TYPE
        SYNTAX      IpAddress
        MAX-ACCESS  read-only
        STATUS      current
        DESCRIPTION
            "Remote mail server IP address for the Media mail call.
            "
        ::= { cmmIpCallActiveEntry 2 }

cmmIpCallActiveSessionProtocol OBJECT-TYPE
        SYNTAX      INTEGER {
            smtp     (1)

        }
        MAX-ACCESS  read-only
        STATUS      current
        DESCRIPTION
            "The object specifies the session protocol to be used
             for the media mail call between local and remote mail
             server via IP network.
            "
        ::= { cmmIpCallActiveEntry 3 }

cmmIpCallActiveSessionTarget OBJECT-TYPE
        SYNTAX      DisplayString
        MAX-ACCESS  read-only
        STATUS      current
        DESCRIPTION
            "The object specifies the session target of the peer that
             is used for the call. This object is set with the
             information in the call associated
             cmmIpPeerCfgSessionTarget object when the media mail call
             is connected.
            "
        ::= { cmmIpCallActiveEntry 4 }


cmmIpCallActiveMessageId OBJECT-TYPE
        SYNTAX      DisplayString
        MAX-ACCESS  read-only
        STATUS      current
        DESCRIPTION
            "The global unique message identification of
             the Media mail.
            "
        ::= { cmmIpCallActiveEntry 5 }

cmmIpCallActiveAccountId OBJECT-TYPE
        SYNTAX      DisplayString
        MAX-ACCESS  read-only
        STATUS      current
        DESCRIPTION
            "The Account ID of Media mail."
        ::= { cmmIpCallActiveEntry 6 }

cmmIpCallActiveImgEncodingType OBJECT-TYPE
        SYNTAX      CmmImgEncoding
        MAX-ACCESS  read-only
        STATUS      current
        DESCRIPTION
            "The image encoding type of Media mail."
        ::= { cmmIpCallActiveEntry 7 }

cmmIpCallActiveImgResolution OBJECT-TYPE
        SYNTAX      CmmImgResolution
        MAX-ACCESS  read-only
        STATUS      current
        DESCRIPTION
            "The image resolution of Media mail."
        ::= { cmmIpCallActiveEntry 8 }

cmmIpCallActiveAcceptMimeTypes OBJECT-TYPE
        SYNTAX      AbsoluteCounter32
        MAX-ACCESS  read-only
        STATUS      current
        DESCRIPTION
            "The number of accepted MIME types for the Media mail call.
            "
        ::= { cmmIpCallActiveEntry 9 }

cmmIpCallActiveDiscdMimeTypes OBJECT-TYPE
        SYNTAX      AbsoluteCounter32
        MAX-ACCESS  read-only
        STATUS      current
        DESCRIPTION
            "The number of discarded MIME types for the Media mail call.
            "
        ::= { cmmIpCallActiveEntry 10 }

cmmIpCallActiveNotification OBJECT-TYPE
        SYNTAX      INTEGER {
            none     (1),
            mdn      (2),
            dsn      (3),
            dsnMdn   (4)
        }
        MAX-ACCESS  read-only
        STATUS      current
        DESCRIPTION
            "The notification type of the Media mail call.
             none - No notification.
             mdn  - Message Disposition notification.
             dsn  - Delivery Status notification.
             dsnMdn - Both Delivery Status and Message Disposition
                      notification
            "
        ::= { cmmIpCallActiveEntry 11 }


--**********************************************************************
-- Media Mail Dial Control Gateway Call History Group
--**********************************************************************

--
-- Media mail over IP Call History Table
--

cmmIpCallHistoryTable OBJECT-TYPE
        SYNTAX      SEQUENCE OF CmmIpCallHistoryEntry
        MAX-ACCESS  not-accessible
        STATUS      current
        DESCRIPTION
            "This table is the Media Mail extension to the call history
             table of IETF Dial Control MIB. It contains Media Mail call
             leg information about specific Media mail gateway call.
            "
        ::= { cmmCallHistory 1 }

cmmIpCallHistoryEntry OBJECT-TYPE
        SYNTAX      CmmIpCallHistoryEntry
        MAX-ACCESS  not-accessible
        STATUS      current
        DESCRIPTION
            "The information regarding a single Media Mail call leg.
             The call leg entry is identified by using the same index
             objects that are used by Call Active table of IETF Dial
             Control MIB to identify the call.
             An entry of this table is created when its associated call
             history entry in the IETF Dial Control MIB is created and
             the call history entry contains information for the call
             establishment to the mail server on the IP network via a
             Media Mail over IP peer.
             The entry is deleted when its associated call history entry
             in the IETF Dial Control MIB is deleted.
            "
        INDEX       { cCallHistoryIndex }
        ::= { cmmIpCallHistoryTable 1 }


CmmIpCallHistoryEntry ::=
        SEQUENCE {
            cmmIpCallHistoryConnectionId             CvcGUid,
            cmmIpCallHistoryRemoteIPAddress          IpAddress,
            cmmIpCallHistorySessionProtocol          INTEGER,
            cmmIpCallHistorySessionTarget            DisplayString,
            cmmIpCallHistoryMessageId                DisplayString,
            cmmIpCallHistoryAccountId                DisplayString,
            cmmIpCallHistoryImgEncodingType          CmmImgEncoding,
            cmmIpCallHistoryImgResolution            CmmImgResolution,
            cmmIpCallHistoryAcceptMimeTypes          AbsoluteCounter32,
            cmmIpCallHistoryDiscdMimeTypes           AbsoluteCounter32,
            cmmIpCallHistoryNotification             INTEGER
        }

cmmIpCallHistoryConnectionId OBJECT-TYPE
        SYNTAX      CvcGUid
        MAX-ACCESS  read-only
        STATUS      current
        DESCRIPTION
            "The global call identifier for the gateway call."
        ::= { cmmIpCallHistoryEntry 1 }


cmmIpCallHistoryRemoteIPAddress OBJECT-TYPE
        SYNTAX      IpAddress
        MAX-ACCESS  read-only
        STATUS      current
        DESCRIPTION
            "Remote mail server IP address for the media mail call.
            "
        ::= { cmmIpCallHistoryEntry 2 }

cmmIpCallHistorySessionProtocol OBJECT-TYPE
        SYNTAX      INTEGER {
            smtp     (1)
        }
        MAX-ACCESS  read-only
        STATUS      current
        DESCRIPTION
            "The object specifies the session protocol to be used
             for the media mail call between local and remote mail
             server via IP network.
            "
        ::= { cmmIpCallHistoryEntry 3 }

cmmIpCallHistorySessionTarget OBJECT-TYPE
        SYNTAX      DisplayString
        MAX-ACCESS  read-only
        STATUS      current
        DESCRIPTION
            "The object specifies the session target of the peer that
             is used for the call. This object is set with the
             information in the call associated
             cmmIpPeerCfgSessionTarget object when the media mail call
             is connected.
            "
        ::= { cmmIpCallHistoryEntry 4 }


cmmIpCallHistoryMessageId OBJECT-TYPE
        SYNTAX      DisplayString
        MAX-ACCESS  read-only
        STATUS      current
        DESCRIPTION
            "The global unique message identification of
             the Media mail.
            "
        ::= { cmmIpCallHistoryEntry 5 }

cmmIpCallHistoryAccountId OBJECT-TYPE
        SYNTAX      DisplayString
        MAX-ACCESS  read-only
        STATUS      current
        DESCRIPTION
            "The Account ID of Media mail."
        ::= { cmmIpCallHistoryEntry 6 }

cmmIpCallHistoryImgEncodingType OBJECT-TYPE
        SYNTAX      CmmImgEncoding
        MAX-ACCESS  read-only
        STATUS      current
        DESCRIPTION
            "The image encoding type of Media mail."
        ::= { cmmIpCallHistoryEntry 7 }

cmmIpCallHistoryImgResolution OBJECT-TYPE
        SYNTAX      CmmImgResolution
        MAX-ACCESS  read-only
        STATUS      current
        DESCRIPTION
            "The image resolution of Media mail."
        ::= { cmmIpCallHistoryEntry 8 }

cmmIpCallHistoryAcceptMimeTypes OBJECT-TYPE
        SYNTAX      AbsoluteCounter32
        MAX-ACCESS  read-only
        STATUS      current
        DESCRIPTION
            "The number of accepted MIME types for the Media mail call.
            "
        ::= { cmmIpCallHistoryEntry 9 }

cmmIpCallHistoryDiscdMimeTypes OBJECT-TYPE
        SYNTAX      AbsoluteCounter32
        MAX-ACCESS  read-only
        STATUS      current
        DESCRIPTION
            "The number of discarded MIME types for the Media mail call.
            "
        ::= { cmmIpCallHistoryEntry 10 }

cmmIpCallHistoryNotification OBJECT-TYPE
        SYNTAX      INTEGER {
            none     (1),
            mdn      (2),
            dsn      (3),
            dsnMdn   (4)
        }
        MAX-ACCESS  read-only
        STATUS      current
        DESCRIPTION
            "The notification type of the Media mail call.
             none - No notification.
             mdn  - Message Disposition notification.
             dsn  - Delivery Status notification.
             dsnMdn - Both Delivery Status and Message Disposition
                      notification
            "
        ::= { cmmIpCallHistoryEntry 11 }

--**********************************************************************
-- FAX general configuration Group
--**********************************************************************

cmmFaxCfgCalledSubscriberId OBJECT-TYPE
        SYNTAX      DisplayString (SIZE (0..20))
        MAX-ACCESS  read-write
        STATUS      current
        DESCRIPTION
            "The regular expression for the FAX called subscriber
             identification (CSI) coding format.
             $d$ in the regular expression substitute CSI with the
             destination number of the call.
            "
        REFERENCE
            "ITU-T T30: Section 5.3.6.2.4 CSI coding format.
            "
        ::= { cmmFaxGeneralCfg 1 }

cmmFaxCfgXmitSubscriberId OBJECT-TYPE
        SYNTAX      DisplayString (SIZE (0..20))
        MAX-ACCESS  read-write
        STATUS      current
        DESCRIPTION
            "The regular expression for the FAX Transmitting subscriber
             identification (TSI) coding format.
             $s$ in the regular expression substitute TSI with the
             caller ID of the call.
            "
        REFERENCE
            "ITU-T T30: Section 5.3.6.2.6 TSI coding format.
            "
        ::= { cmmFaxGeneralCfg 2 }

cmmFaxCfgRightHeadingString OBJECT-TYPE
        SYNTAX      CmmFaxHeadingString
        MAX-ACCESS  read-write
        STATUS      current
        DESCRIPTION
            "The regular expression for the FAX right heading at the top
             of cover page or text page.

             The default value of this object is an empty string.
            "
        ::= { cmmFaxGeneralCfg 3 }

cmmFaxCfgCenterHeadingString OBJECT-TYPE
        SYNTAX      CmmFaxHeadingString
        MAX-ACCESS  read-write
        STATUS      current
        DESCRIPTION
            "The regular expression for the FAX center heading at the
             top of cover page or text page.

             The default value of this object is an empty string.
            "
        ::= { cmmFaxGeneralCfg 4 }

cmmFaxCfgLeftHeadingString OBJECT-TYPE
        SYNTAX      CmmFaxHeadingString
        MAX-ACCESS  read-write
        STATUS      current
        DESCRIPTION
            "The regular expression for the FAX left heading at the top
             of cover page or text page.

             The default value of this object is an empty string.
            "
        ::= { cmmFaxGeneralCfg 5 }

cmmFaxCfgCovergPageControl OBJECT-TYPE
        SYNTAX      BITS {
            coverPageEnable       (0),
            coverPageCtlByEmail   (1),
            coverPageDetailEnable (2)
        }
        MAX-ACCESS  read-write
        STATUS      current
        DESCRIPTION
            "The object controls the generation of cover page of FAX.
             coverPageEnable     - enable the managed system to generate
                                   the FAX cover page.
             coverPageCtlByEmail - allow email to control the FAX cover
                                   page generation.
             coverPageDetailEnable- enable the detailed mail header on
                                    the cover page.
            "
        ::= { cmmFaxGeneralCfg 6 }

cmmFaxCfgCovergPageComment OBJECT-TYPE
        SYNTAX      DisplayString
        MAX-ACCESS  read-write
        STATUS      current
        DESCRIPTION
            "The object contains the comment on the FAX cover page.
            "
        ::= { cmmFaxGeneralCfg 7 }

cmmFaxCfgFaxProfile OBJECT-TYPE
        SYNTAX      BITS {
            profileS     (0),
            profileF     (1),
            profileJ     (2),
            profileC     (3),
            profileL     (4),
            profileM     (5)
        }
        MAX-ACCESS  read-write
        STATUS      current
        DESCRIPTION
            "The profile that applies to TIFF file for facsimile. The
             default value of this object is profileF.
            "
        REFERENCE
            "RFC 2301: Section 2.2.4 New TIFF fields recommended for fax
             modes.
            "
        ::= { cmmFaxGeneralCfg 8 }

cmmdcMIBConformance OBJECT IDENTIFIER ::=
                                { ciscoMediaMailDialControlMIB 3 }
cmmdcMIBCompliances OBJECT IDENTIFIER ::=
                                { cmmdcMIBConformance 1 }
cmmdcMIBGroups      OBJECT IDENTIFIER ::=
                                { cmmdcMIBConformance 2 }

-- compliance statements

cmmdcMIBCompliance MODULE-COMPLIANCE
        STATUS      current
        DESCRIPTION
            "The compliance statement for entities which
             implement the CISCO MMAIL DIAL CONTROL MIB"
        MODULE      -- this module
        GROUP cmmdcPeerCfgGroup
        DESCRIPTION
            "This group is mandatory for dial peer configuration
             which is related to Media Mail.
            "
        GROUP cmmIpCallGeneralGroup
        DESCRIPTION
            "This group is mandatory for general Media Mail related
             active call and call history via IP network.
            "
        GROUP cmmIpCallImageGroup
        DESCRIPTION
            "This group is mandatory for Image related Media Mail
             related active call and call history via IP network.
            "
        GROUP cmmFaxGroup
        DESCRIPTION
            "This group is mandatory for store and forward FAX general
             configuration.
            "
        OBJECT  cmmFaxCfgFaxProfile
        MIN-ACCESS  read-only
        DESCRIPTION
            "Only the defalut value  'profileF ' is allowed.
             Write access is not required.
            "
        ::= { cmmdcMIBCompliances 1 }



-- units of conformance



cmmdcPeerCfgGroup OBJECT-GROUP
        OBJECTS {
            cmmIpPeerCfgSessionProtocol,
            cmmIpPeerCfgSessionTarget,
            cmmIpPeerCfgImgEncodingType,
            cmmIpPeerCfgImgResolution,
            cmmIpPeerCfgMsgDispoNotification,
            cmmIpPeerCfgDeliStatNotification
        }
        STATUS      current
        DESCRIPTION
            "A collection of objects providing the Media Mail Dial
             Control configuration capability.
            "
        ::= { cmmdcMIBGroups 1 }


cmmIpCallGeneralGroup OBJECT-GROUP
        OBJECTS {
            cmmIpCallActiveConnectionId,
            cmmIpCallActiveRemoteIPAddress,
            cmmIpCallActiveSessionProtocol,
            cmmIpCallActiveSessionTarget,
            cmmIpCallActiveMessageId,
            cmmIpCallActiveAccountId,
            cmmIpCallActiveAcceptMimeTypes,
            cmmIpCallActiveDiscdMimeTypes,
            cmmIpCallActiveNotification,
            cmmIpCallHistoryConnectionId,
            cmmIpCallHistoryRemoteIPAddress,
            cmmIpCallHistorySessionProtocol,
            cmmIpCallHistorySessionTarget,
            cmmIpCallHistoryMessageId,
            cmmIpCallHistoryAccountId,
            cmmIpCallHistoryAcceptMimeTypes,
            cmmIpCallHistoryDiscdMimeTypes,
            cmmIpCallHistoryNotification
        }
        STATUS      current
        DESCRIPTION
            "A collection of objects providing the General Media Mail
             Call capability.
            "
        ::= { cmmdcMIBGroups 2 }

cmmIpCallImageGroup OBJECT-GROUP
        OBJECTS {
            cmmIpCallActiveImgEncodingType,
            cmmIpCallActiveImgResolution,
            cmmIpCallHistoryImgEncodingType,
            cmmIpCallHistoryImgResolution
        }
        STATUS      current
        DESCRIPTION
            "A collection of objects providing the Image related Media
             Mail Call capability.
            "
        ::= { cmmdcMIBGroups 3 }

cmmFaxGroup OBJECT-GROUP
        OBJECTS {
            cmmFaxCfgCalledSubscriberId,
            cmmFaxCfgXmitSubscriberId,
            cmmFaxCfgRightHeadingString,
            cmmFaxCfgCenterHeadingString,
            cmmFaxCfgLeftHeadingString,
            cmmFaxCfgCovergPageControl,
            cmmFaxCfgCovergPageComment,
            cmmFaxCfgFaxProfile
        }
        STATUS      current
        DESCRIPTION
            "A collection of objects providing the general FAX
             configuration capability.
            "
        ::= { cmmdcMIBGroups 4 }
END
