-- $Source: $
-- *****************************************************************
-- OLD-CISCO-CHASSIS-MIB.my:  Cisco Chassis MIB file
--
--
-- May 1994, Jeffrey T. Johnson
--
-- Copyright (c) 1994-2023 by cisco Systems, Inc.
-- All rights reserved.
--
-- NOTE WELL
-- Starting with IOS 12.0, all objects defined in this mib have been
-- deprecated.  They have been replaces with objects defined in the
-- ENTITY-MIB.my document. Management applications should no longer
-- be examining the objects defined in this document.
-- NOTE WELL
--
-- *****************************************************************
-- $Log: $
-- *****************************************************************
-- $Endlog$
--
--
               OLD-CISCO-CHASSIS-MIB DEFINITIONS ::= BEGIN

               IMPORTS
                    TimeTicks
                        FROM RFC1155-SMI
                    OBJECT-TYPE
			FROM RFC-1212
                    DisplayString
			FROM RFC1213-MIB
		    temporary
			FROM CISCO-SMI;

               chassis             OBJECT IDENTIFIER ::= { temporary 6 }

               -- Temporary Chassis Section


               -- (not the same as the IETF Chassis MIB)

          -- This group is present in all products.

               chassisType OBJECT-TYPE
                   SYNTAX  INTEGER {
			unknown(1)
			,multibus(2)
			,agsplus(3)
			,igs(4)
			,c2000(5)
			,c3000(6)
			,c4000(7)
			,c7000(8)
			,cs500(9)
			,c7010(10)
			,c2500(11)
			,c4500(12)
			,c2102(13)
			,c2202(14)
			,c2501(15)
			,c2502(16)
			,c2503(17)
			,c2504(18)
			,c2505(19)
			,c2506(20)
			,c2507(21)
			,c2508(22)
			,c2509(23)
			,c2510(24)
			,c2511(25)
			,c2512(26)
			,c2513(27)
			,c2514(28)
			,c2515(29)
			,c3101(30)
			,c3102(31)
			,c3103(32)
			,c3104(33)
			,c3202(34)
			,c3204(35)
			,accessProRC(36)
			,accessProEC(37)
			,c1000(38)
			,c1003(39)
			,c1004(40)
			,c2516(41)
			,c7507(42)
			,c7513(43)
			,c7506(44)
			,c7505(45)
			,c1005(46)
			,c4700(47)
			,c2517(48)
			,c2518(49)
			,c2519(50)
			,c2520(51)
			,c2521(52)
			,c2522(53)
			,c2523(54)
			,c2524(55)
			,c2525(56)
			,c4700S(57)
			,c7206(58)
			,c3640(59)
			,as5200(60)
			,c1601(61)
			,c1602(62)
			,c1603(63)
			,c1604(64)
			,c7204(65)
			,c3620(66)
			,wsx3011(68)
			,mc3810(69)
			,c1503(72)
			,as5300(73)
			,as2509RJ(74)
			,as2511RJ(75)
			,c2501FRADFX(77)
			,c2501LANFRADFX(78)
			,c2502LANFRADFX(79)
			,wsx5302(80)
			,c1605(81)
			,c12012(82)
			,c12008(85)
			,ubr7246(86)			-- Universal Broadband Router
			,c2610(87)			-- c2600 with 1 integrated ethernet interface
			,c2612(88)			-- c2600 with an integrated ethernet and token ring interface
			,c2611(89)			-- c2600 with 2 integrated ethernet interfaces
			,ubr904(90)			-- Cisco Cable Modem (ubr - universal broadband router)
			,c6200(91)			-- Digital Subscriber Line Access Multiplexer(DSLAM)
			,c3660(92)                      -- Six slot MARS Router
			,c7202(94)                      -- Modular two slot router in the cisco7200 family
			,c2620(95)			-- c2600 platform with an onboard fast ethernet
			,c2621(96)			-- c2600 platform with two onboard fast ethernets
			,rpm(99)			-- Router Processor Module
			,c1710(100)			-- VPN(Virtual Private Network) Security Router with 1 FastEthernet and 1 Ethernet interface onboard
			,c1720(101)
			,c7576(102)			-- Dual Independent RSP platform, 13 slots
			,c1401(103)			-- Router with 1 ethernet and 1 ATM25 interface
			,c2613(104)			-- c2600 with 1 integrated token ring interface
			,ubr7223(105)			-- Universal Broadband Router
			,c6400Nrp(106)			-- c6400 Network Routing Processor
			,c801(107)			-- Cisco 800 platform with 1 ethernet and 1 BRI/ST
			,c802(108)			-- Cisco 800 platform with 1 ethernet and 1 BRI U
			,c803(109)			-- Cisco 800 platform with 1 ethernet 4-port hub, 1 BRI S/T, and 2 POTs
			,c804(110)			-- Cisco 800 platform with 1 ethernet 4-port hub, 1 BRI U, and 2 POTs
			,c7206VXR(111)			-- Cisco 7200 platform, VXR series chassis with 6 slots
			,c7204VXR(112)			-- Cisco 7200 platform, VXR series chassis with 4 slots
			,c1750(113)			-- VoIP (Voice over IP) capable Cisco 1700 platform with 2 WIC/VIC slots and 1 VIC-only slot
			,mgx8850(114)			-- Cisco MGX8850 Multiservice Gigabit Switch with 32 half height slots
			,c805(116)			-- Cisco 800 platform with 1 ethernet and 1 serial WIC
			,ws-c3508g-xl(117)		-- Cisco Catalyst 3508G-XL switch with 8 GBIC Gigabit ports, can run Standard or Enterprise edition software.
			,ws-c3512-xl(118)		-- Cisco Catalyst 3512XL switch with 12 10/100BaseTX ports and 2 GBIC Gigabit ports, can run Standard or Enterprise edition software.
			,ws-c3524-xl(119)		-- Cisco Catalyst 3524XL switch with 24 10/100BaseTX ports and 2 GBIC Gigabit ports, can run Standard or Enterprise edition software.
			,ws-c2908-xl(120)		-- Cisco Catalyst 2900XL series 8 port 10/100BaseTX switch
			,ws-c2916m-xl(121)		-- Cisco Catalyst 2916M-XL switch with 16 10/100BaseTX ports and 2 uplink slots.
			,ws-c2924-xl-v(122)		-- Cisco Catalyst 2924XL switch with 24 autosensing 10/100BaseTX ports; supports p I ports, Wireless and CUE
			,ws-c2924c-xl-v(123)		-- Cisco Catalyst 2924C-XL switch with 22 autosensing 10/100BaseTX ports and 2 100BaseFX ports; supports port-based VLANs, can run Standard or Enterprise edition software.
			,ws-c2912-xl(124)		-- Cisco Catalyst 2912XL switch with 12 autosensing 10/100BaseTX ports, can run Standard or Enterprise edition software.
			,ws-c2924m-xl(125)		-- Cisco Catalyst 2924M-XL switch with 24 autosensing 10/100BaseTX ports and 2 uplink slots, can run Standard or Enterprise edition software.
			,ws-c2912mf-xl(126)		-- Cisco Catalyst 2912MF-XL switch with 12 100BaseFX ports and 2 uplink slots; can only run Enterprise edition software.
			,c1417(128)			-- Cisco 1400 series router with 1 Ethernet and 1 ADSL interface, with 1417 chipset
			,cOpticalRegenerator(129)	-- Cisco Optical Regenerator
			,ws-c2924-xl(130)		-- Cisco Catalyst 2924XL with 24 10/100BaseTX switch ports; doesn't support port-based VLANs.
			,ws-c2924c-xl(131)		-- Cisco Catalyst 2924C-XL; doesn't support port-based VLANs.
			,ubr924(132)			-- Cisco UBR Cable Modem which is a UBR904 with 2 FXS Voice ports
                        ,ws-x6302-msm(133)              -- Catalyst 6000 or 6500 Series Multilayer Switch Module WS-X6302-MSM that directly interfaces to the switch's backplane to provide layer 3 switching.
			,cat5k-rsfc(134)		-- Router Switching Feature Card for the Catalyst 5000 that is treated as a standalone system by the NMS
			,c7120-quadt1(136)		-- 7120 Series chassis with 2 10/100 FE interfaces, 4 T1/E1 interfaces
			,c7120-t3(137)			-- 7120 Series chassis with 2 10/100 FE interfaces, 1 T3 interface
			,c7120-e3(138)			-- 7120 Series chassis with 2 10/100 FE interfaces, 1 E3 interface
			,c7120-at3(139)			-- 7120 Series chassis with 2 10/100 FE interfaces, 1 T3 ATM interface
			,c7120-ae3(140)			-- 7120 Series chassis with 2 10/100 FE interfaces, 1 E3 ATM interface
			,c7120-smi3(141)		-- 7120 Series chassis with 2 10/100 FE interfaces, 1 OC3SMI ATM interface
			,c7140-dualt3(142)		-- 7140 Series chassis with 2 10/100 FE interfaces, 2 T3 interfaces
			,c7140-duale3(143)		-- 7140 Series chassis with 2 10/100 FE interfaces, 2 E3 interfaces
			,c7140-dualat3(144)		-- 7140 Series chassis with 2 10/100 FE interfaces, 2 T3 ATM interfaces
			,c7140-dualae3(145)		-- 7140 Series chassis with 2 10/100 FE interfaces, 2 E3 ATM interfaces
			,c7140-dualmm3(146)		-- 7140 Series chassis with 2 10/100 FE interfaces, 2 OC3MM ATM interfaces
			,ubr-7246-vxr(148)              -- Cisco 7246 Universal Broadband Router, VXR series
			,c12016(150)			-- Cisco 12000 platform with 16 slots
			,as5400(151)			-- Cisco AS5400
			,c7140-octt1(152)		-- 7140 Series chassis with 8 integrated T1/E1 serial ports
			,c7140-dualfe(153)		-- 7140 Series chassis with 2 integrated 10/100 FE interfaces
			,cat3548xl(154)			-- Catalyst 3548XL switch (WS-C3548-XL)
			,cat6006(155)			-- Catalyst 6000 with 6 slots
			,cat6009(156)			-- Catalyst 6000 with 9 slots
			,cat6506(157)			-- Catalyst 6000 Plus with 6 slots
			,cat6509(158)			-- Catalyst 6000 Plus with 9 slots
			,mc3810-v3(160)			-- Cisco MC3810-V3, capable of data, voice and video.  Supports 2 additional ports than the MC3810-V, used for optional access cards.
			,c7507z(162)			-- Cisco 7507z chassis, Czbus capable, 7 slots
			,c7513z(163)			-- Cisco 7513z chassis, Czbus capable, 13 slots
			,c7507mx(164)			-- Cisco 7507mx chassis, Czbus capable, TDM (Time Division Multiplexing) backplane support, 7 slots
			,c7513mx(165)			-- Cisco 7513mx chassis, Czbus capable, TDM (Time Division Multiplexing) backplane support, 13 slots
			,ubr912-c(166)			-- Cisco uBR912-C Cable Modem with CSU/DSU WIC
			,ubr912-s(167)			-- Cisco uBR912-S Cable Modem with Serial WIC
			,ubr914(168)			-- Cisco uBR914 Cable Modem with removable WIC
			,c6160(171)			-- Cisco 6160 DSLAM chassis
			,cat4232-l3(173)	-- Cisco Catalyst 4232-L3 layer 3 line card that is treated as a standalone system by the NMS
			,cOpticalRegeneratorDCPower(174)	-- Cisco Optical Regenerator with DC power supply
			,cva122(180)			--   Cisco CVA122 Cable Voice Adapter (Residential Cable Modem with two Voice Ports)
			,cva124(181)			--   Cisco CVA124 Cable Voice Adapter (Residential Cable Modem with four Voice Ports)
			,as5850(182)			--  High End Dial Access Server
			,mgx8240(185)			-- High Density Circuit Emulation Service Gateway chassis with two shelf controller slots and fifteen Service Modulesfor Private Line Service
			,ubr925(191)		-- Cisco UBR925 Cable Modem/Router with VOIP and hardware accelerated IPSEC
			,ubr10012(192)		-- Cisco uBR10000 platform with 8 broadband slots and 4 WAN slots
			,c12016-8r(194)		-- Teracore ready 8 rail chassis for Cisco 12000 platform
			,c2650(195)		-- c2650 platform with 1 integrated fast ethernet interface
			,c2651(196)		-- c2650 platform with 2 integrated fast ethernet interfaces
			,c1751(202)		-- Digital voice capable Cisco 1700 platform with 2 WIC/VIC slots and 1 VIC-only slot
			,c626(205)		-- Cisco 600 DSL CPE pltaform with ADSL, DMT issue 1, 25M ATM interface
			,c627(206)		-- Cisco 600 DSL CPE pltaform with ADSL, DMT issue 2, 25M ATM interface
			,c633(207)		-- Cisco 600 DSL CPE platform with SDSL, 2B1Q line coding, serial interface (V.35/X.21)
			,c673(208)		-- Cisco 600 DSL CPE platform with SDSL, 2B1Q line coding, ethernet interface
			,c675(209)		-- Cisco 600 DSL CPE platform with ADSL, CAP, ethernet interface, POTS connector
			,c675e(210)		-- Cisco 600 DSL CPE platform with ADSL, CAP, ethernet interface, universal power supply
			,c676(211)		-- Cisco 600 DSL CPE platform with ADSL, DMT issue 1, ethernet interface
			,c677(212)		-- Cisco 600 DSL CPE platform with ADSL, DMT issue 2, ethernet interface
			,c678(213)		-- Cisco 600 DSL CPE platform with ADSL, CAP/DMT/G.Lite, ethernet interface
			,c3661-ac(214)		-- 1 Fast Ethernet version of c3660 with a AC power supply
			,c3661-dc(215)		-- 1 Fast Ethernet version of c3660 with a DC power supply
			,c3662-ac(216)		-- 2 Fast Ethernet version of c3660 with a AC power supply
			,c3662-dc(217)		-- 2 Fast Ethernet version of c3660 with a DC power supply
			,c3662-ac-co(218)		-- 2 Fast Ethernet version of c3660 with a AC power supply for Telco's
			,c3662-dc-co(219)		-- 2 Fast Ethernet version of c3660 with a DC power supply for Telco's
			,ubr7111(220)			-- Low-end version of the Universal Broadband Router with 1 PA slot, 1 fixed RF line card (MC11C) and integrated upconvertor, designed for hotels, MDUs and smaller cable operators
			,ubr7114(222)			-- Low-end version of the Universal Broadband Router with 1 PA slot, 1 fixed RF line card (MC14C) and integrated upconvertor, designed for hotels, MDUs and smaller cable operators
			,c12010(224)			-- Cisco 12000 platform with 10 slots
			,c8110(225)			-- Cisco 8110 (ATM network termination device) with 3 Line Interface module slots
			,ubr905(227)			-- Cisco uBR905 Cable Modem with hardware accelerated IPSEC
			,c7150-dualfe(231)		-- 7150 Series chassis with 2 integrated 10/100 FE interfaces
			,c7150-octt1(232)		-- 7150 Series chassis with 8 integrated T1/E1 serial ports
			,c7150-dualt3(233)		-- 7150 Series chassis with 2 10/100 FE interfaces, 2 T3 interfaces
			,cvps1110(236)			-- Cisco VLAN Policy Server 1110 manages VLAN-based policies to control user access to a LAN, leveraging existing authentication mechanisms such as Windows Domain Controllers and Novell's NDS. This policy server is part of CiscoWorks2000 User Registration Tool product.
			,ccontentengine(237)		-- Cisco Content Engine Chassis.  The Cisco Content Engine is a Content Networking product that accelerates content delivery, ensuring maximum scalability and availability of content.  The Content Engines offer caching, Content Delivery Network (CDN) services, employee internet management (e.g., URL filtering) and proxy services
			,ciad2420(238)			-- Integrated Access Device 2420 (IAD2420) chassis with Analog (8/16) FXS ports with T1 or ADSL (Asymmetrical Digital Subscriber Line) Uplinks
			,c677i(239)			-- Cisco 600 DSL CPE platform with ASDL, DMT issue 2 over ISDN, ethernet interface
			,c674(240)			-- Cisco 600 DSL CPE platform with G.SHDSL, ethernet interface
			,cdpa7630(241)			-- The Cisco Digital PBX Adapter (DPA) enables the integration of Cisco Call Manager with Octel voice mail systems
			,cat355024(242)			-- Catalyst 3550 24 10/100 ports + 2 Gig uplinks fixed configuration Layer 2/Layer 3 Ethernet Switch
			,cat355048(243)			-- Catalyst 3550 48 10/100 ports + 2 Gig uplinks fixed configuration Layer 2/Layer 3 Ethernet Switch
			,cat355012t(244)		-- Catalyst 3550 12 1000T ports fixed configuration Layer 2/Layer 3 Ethernet Switch
			,cat2924-lre-xl(245)		-- Cisco Catalyst c2924XL switch (WS-C2924-LRE-XL) with 24 10BaseS VDSL ports and 4 10/100BaseTX ports
			,cat2912-lre-xl(246)		-- Cisco Catalyst c2912XL switch (WS-C2912-LRE-XL) with 12 10BaseS VDSL ports and 4 10/100BaseTX ports
			,cva122e(247)			-- Cisco CVA122-e Cable Voice Adapter(Residential Cable Modem with two voice ports)- European version
			,cva124e(248)			-- Cisco CVA124-e Cable Voice Adapter(Residential Cable Modem with four voice ports)- European version
			,curm(249)			-- Universal Router Module for the IGX platform
			,curm2fe(250)			-- Universal router module with 2 Fast Ethernet interfaces for IGX platform
			,curm2fe2v(251)			-- Universal Router Module, with 2 Fast Ethernet ports, and 2 digital voice ports (T1 or E1)
			,c7401VXR(252)			-- Cisco 7400 Family, 1 Slot router
			,cap340(255)			-- Aironet Wireless LAN Access Point 340 series
			,cap350(256)			-- Cisco Wireless LAN Access Point 350 series
			,cdpa7610(257)			-- The Cisco Digital PBX Adapter (DPA) enables the integration of Cisco Call Manager with Octel voice mail systems
			,c12416(261)			-- Cisco 12000 platform with 16 slots and 10G Fabric card
			,ws-c2948g-l3-dc(262)		-- A fixed-configuration Layer 3 Ethernet switch featuring IP, IPX, and IP mulitcast with 48 10/100BaseTX ports and 2 GBIC Gigabit ports using DC power
			,ws-c4908g-l3-dc(263)		-- A fixed-configuration L3 Ethernet switch featuring IP,IPX and IP multicast with 8 GBIC ports using DC power
			,c12406(264)			-- Cisco 12400 platform with 6 slots
			,pix-firewall506(265)		-- Cisco PIX Firewall 506
			,pix-firewall515(266)		-- Cisco PIX Firewall 515
			,pix-firewall520(267)		-- Cisco PIX Firewall 520
			,pix-firewall525(268)		-- Cisco PIX Firewall 525
			,pix-firewall535(269)		-- Cisco PIX Firewall 535
			,c12410(270)			-- Cisco 12410 platform with 10 slots
			,c811(271)			-- ISDN router for Japan with 1 10BaseT Ethernet port, 1 ISDN BRI(Basic Rate Interface) U, integrated DSU(Data Service Unit)
			,c813(272)			-- ISDN router for Japan with 10 BaseT 4 ports hub , 1 ISDN BRI(Basic Rate Interface) U, integrated DSU(Data Service Unit) and 2 RJ-11
			,c10720(273)			-- IP + Optical Access Router
            ,cMWR1900(274)			-- The Mobile Wireless router is a router targeted at application in a cell site Base Transciever Station (BTS) providing T1/E1 backhaul connections to the aggregation node in Radio Access Networks (RAN)
			,c4224(275)			-- A standalone 24 port powered Ethernet switch, router and voice gateway
			,cWSC6513(276)			-- Catalyst 6000 series chassis with 13 slots
			,c7603(277)			-- Cisco Internet Router 7600 Series Chassis with 3 slots
			,c7606(278)			-- Cisco Internet Router 7600 Series Chassis with 6 slots
			,c7401ASR(279)			-- Cisco 7400 platform, ASR series with 1 slot
			,cVG248(280)			-- Cisco VoIP Voice Gateway for connecting analog telephones fax machines to a Cisco Call Manager based system
			,c1105(281)			-- CiscoWorks network management chassis
			,cCe507(284)			-- Cisco Content Engine Model 507
			,cCe560(285)			-- Cisco Content Engine Model 560
			,cCe590(286)			-- Cisco Content Engine Model 590
			,cCe7320(287)			-- Cisco Content Engine Model 7320
			,c2691(288)			-- One Network Module slot, three WIC slot, two Fast Ethernet port MARS router
			,c3725(289)			-- Two Network Module slot, three WIC slot, two Fast Ethernet port MARS router
			,c1760(291)			-- Analog/digital voice capable, 19" rack-mount (1RU) Cisco 1700 platform with 2 WIC/VIC slots and 2 VIC-only slots
			,pix-firewall501(292)		-- Cisco PIX Firewall 501
			,c2610M(293)			-- c2600M chassis  with 1 integrated ethernet interface
			,c2611M(294)			-- c2600M chassis with 2 integrated ethernet interfaces
			,c12404(298)			-- Cisco 12400 platform with 4 slots
			,c9004(299)			-- Cisco 9000 Chassis
			,cat355012g(306)		-- 10 Gig (GBIC) + 2 10/100/1000baseT ports, fixed configuration layer 2/3 Ethernet switch
			,cCe507av(307)			-- Cisco Content Engine Model 507-AV
			,cCe560av(308)			-- Cisco Content Engine Model 560-AV
			,cIe2105(309)			-- The Cisco Intelligence Engine 2100 series is a new form of network device that provides intelligent network interface to applications and users
			,c10005(311)			-- Cisco 10000 platform with 7 slots
			,c10008(312)			-- Cisco 10000 platform with 7 slots
			,c7304(313)			-- Cisco 7300 Chassis
			,cWSC6503(322)			-- Catalyst 6000 series chassis with 3 slots
			,pix-firewall506e(323)		-- Cisco PIX Firewall 506E
			,pix-firewall515e(324)		-- Cisco PIX Firewall 515E
			,cat355024-dc(325)		-- Catalyst 3550 10/100Base-Tx ports + 2 Gig uplinks fixed configuration Layer 2/Layer 3 Ethernet Switch with DC power
			,ccontentengine2636(326)	-- Cisco Content Engine Module for 26xx and 36xx series platforms
			,ccontentengine-dw2636(327)	-- Double Wide Cisco Content Engine Module for 26xx and 36xx series
			,mgx-14-8830(329)		-- Cisco Multiservice Gigabit Switch with 14 half height slots
			,c6400-uac(332)                 -- Cisco 6400 Universal Access Concentrator
			,c2610XM(334)                   -- Cisco 2610XM platform with 1 integrated fast ethernet interfaces with SDRAM
			,c2611XM(335)                   -- Cisco 2611XM platform with 2 integrated fast ethernet interfaces with SDRAM
			,c2620XM(336)                   -- Cisco 2620XM platform with 1 integrated fast ethernet interfaces with SDRAM
			,c2621XM(337)                   -- Cisco 2621XM platform with 2 integrated fast ethernet interfaces with SDRAM
			,c2650XM(338)                   -- Cisco 2650XM platform with 1 integrated fast ethernet interfaces with SDRAM
			,c2651XM(339)                   -- Cisco 2651XM platform with 2 integrated fast ethernet interfaces with SDRAM
			,c12816(344)			-- Cisco 12816 platform with 16 slot
			,c12810(345)			-- Cisco 12810 platform with 10 slots
			,cat295024sx(350)		-- Cisco Catalyst c2950 switch with 24 10/100 BaseTX ports and 2 fixed 1000Base Multimode fiber (SX) ports (WS-C2950SX-24)
			,cat2955-t12(351)		-- Cisco Catalyst c2950 Industrial switch with 12 10/100 and 2 10/100/1000 BaseT ports
			,cat2955-c12(352)		-- Cisco Catalyst c2950 Industrial switch with 12 10/100 BaseTX ports and 2 100 Base-FX ports
			,as5400-hpx(353) 		-- chassis for cisco As5400HPX
			,as5350-hpx(354)                -- chassis for cisco AS5350HPX
			,airap-1100(362)		-- 1100 series WLAN Access Point with 1 10/100TX port, 1 IEEE 802.11 radio port
			,cat2955-s12(364)		-- Cisco Catalyst c2955 Industrial switch with 12 10/100 Base T ports and 2 100 Base-LX Single Mode Uplink ports
			,c7609(365)			-- 9 slots chassis in Cisco 7600 family
			,cMWR1941DC(371)		-- The Mobile Wireless Router (MWR-1941-DC) is a router with a universal power supply targeted at application in a cell site Base Transceiver Station (BTS) providing T1/E1 backhaul connections to the aggregation node in Radio Access Networks (RAN)
			,cVG200(372)			-- The Cisco VG200 chassis for Voice-over-IP (VoIP) Gateway
			,airap1210(373)			-- 1200 series WLAN Access Point on Cisco IOS platform with 1 10/100TX port, 1 CardBus slot, 1 Mini PCI slot
			,cat375048PS(374)		-- Catalyst 3750 48 10/100 ports with In-Line Power + 2 Gigabit SFP ports fixed configuration Layer 2/Layer 3 Ethernet Stackable Switch.(SFP Small Formfactor Pluggable)
			,cat375024PS(375)		-- Catalyst 3750 24 10/100 ports with In-Line Power + 2 Gigabit SFP ports fixed configuration Layer 2/Layer 3 Ethernet Stackable Switch(SFP Small Formfactor Pluggable)
			,cat297024(376)			-- Catalyst 2970 24: 24 10/100/1000 ports fixed configuration Layer 2 Ethernet Switch
			,c7613(377)			-- Cisco Internet router 7600 Series Chassis with 13 slots
			,cat3750-12ge-sfp(379)		-- Catalyst 3750 12 Ethernet Gigabit SFP ports stackable switch. (SFP: Small Form factor Pluggable)
			,airbr-1410(380)		-- 1410 Series Wireless LAN Bridge on Cisco IOS platform with 1 10/100Tx port and 1 5-GHz radio
			,cWSC6509neba(381)		-- Catalyst 6500 series chassis with 9 slots
			,c1711(382)			-- Enhanced security router with 4 FastEthernet switch ports, 1 Analog modem port, 1 FastEthernet port and a hardware encryption module
			,c1712(383)			-- Enhanced security router with 4 FastEthernet switch ports, 1 Basic Rate Interface(S/T)  data port, 1 FastEthernet port and a hardware encryption module.
			,c1701(384)			-- c1701 is a re-packaging of existing products to create a fixed configuration sku. It has ADSLoPOTs WIC and ISDN BRI (S/T) WIC riveted into it.
			,cat29408TT(385)		-- Catalyst 2940 L2 switch with 8 10/100 copper ports and 1 10/100/1000 copper uplink port.
			,cat29408TF(386)		-- Catalyst 2940 L2 switch with 8 10/100 copper ports, 1 100 FX Uplink port and 1 Gigabit SFP Module slot.
			,c2430iad-24fxs(389)		-- cIAD2430 with 24FXS, 2FE
			,c2431iad-8fxs(390)		-- cIAD2431 with 8FXS, 2FE, 1T1/E1, 1 vwic slot
			,c2431iad-16fxs(391)		-- cIAD2431 with 16FXS, 2FE, 1T1/E1, 1 vwic slot
			,c2431iad-1t1e1(392)		-- cIAD2431 with 2FE, 2T1/E1, 1 vwic slot
			,c2432iad-24fxs(393)		-- cIAD2432 with 24FXS, 2FE, 2T1E1, 1 vwic slot
			,airap350ios(394)		-- Cisco Wireless LAN Access Point 350 series on IOS platform with 1 10/100TX port, 1 IEEE 802.11 radio port
			,cat295024-lre-st-997(396)      -- Cisco Catalyst2905 Long Reach Ethernet switch that confirms to ETSI 997 with 24 LRE interfaces, 2 10/100/1000 Small form factor copper interfaces and DC power supply(WS-C2905ST-24-LRE-997)
			,cVG224(397)			-- Line side Analog Gateway with 24FXS Analog ports
			,cat295048t(398)		-- Cisco Catalyst c2950 switch with 48 10/100BaseT ports and 2 10/100/1000 BaseT ports
			,cat295048sx(399)		-- Cisco Catalyst c2950 switch with 48 10/100BaseTX ports and 2 fixed 1000Base Multimode fiber (SX) ports
			,cat6k-sup720(400)		-- Catalyst 6500 Supervisor Module 720 CPU board that is treated as a standalone system by the NMS
			,cat297024-ts(401)		-- Catalyst 2970 24 10/100/1000 ports + 4 Gigabit SFP ports fixed configuration Layer 2 Ethernet Switch
			,cat356048-ps(402)		-- Catalyst 3560 48 10/100 ports with In-Line Power + 4 Gigabit SFP ports fixed configuration Layer 2/Layer 3 Ethernet Switch.(SFP Small Formfactor Pluggable)
			,cat356024-ps(403)			-- Catalyst 3560 24 10/100 ports with In-Line Power + 2 Gigabit SFP ports fixed configuration Layer 2/Layer 3 Ethernet Switch.(SFP Small Formfactor Pluggable)
			,airbr-1300(404)			-- Cisco Aironet 1300 Series Wireless Bridge with 1 10/100 TX Ethernet port, 1 IEEE 802.11g radio port
			,c878(410)			-- Cisco 878 platform with 1 SHDSL WAN interface, 4-port 10/100 Base-T LAN Ethernet switch, 4 USB ports, 1 ISDN BRI S/T interface, hardware encryption and an optional Wireless LAN card
			,c871(411)			-- Cisco 871 platform with 1 10/100T ethernet WAN interface, 4-port 10/100 Base-T LAN Ethernet switch, 4 USB ports, hardware encryption and an optional Wireless LAN card
			,c2811(413)			-- 2800 Family Router with two integrated fast ethernets and integrated VPN
			,c2821(414)			-- 2800 Family Router with two integrated gigabit ethernets and integrated VPN
			,c2851(415)			-- 2800 Family Router with two integrated gigabit ethernets and integrated VPN
			,cat375024-me(416)		-- Metro Ethernet Catalyst  3750 24-10/100 + 2 SFP ports for downlinks and 2 SFP ES (Enhanched Service) ports for uplinks
			,cat3750g-16td(420)		-- Cisco Catalyst 3750 switch with 16 gigabit and one 10G ethernet port (WS-C3750G-16TD)
			,cigesm(422)			--  Cisco Systems Intelligent Gigabit Ethernet Switch Module for IBM eServer BladeCenter (OS-CIGESM-18TT-E)
			,c1841(423)			--  1700 Next Generation data only router with 2 slots
			,c2801(424)			--  1700 Next Generation data only router with 4 slots
			,cat3750G24-ps(426)		--  Catalyst 3750 24 10/100/1000 Power over Ethernet ports + 4 Gigabit SFP ports fixed configuration Layer 2/Layer 3 Ethernet Stackable Switch. (SFP Small Formfactor Pluggable)
			,cat3750G48-ps(427)		--  Catalyst 3750 48 10/100/1000 Power over Ethernet ports + 4 Gigabit SFP ports fixed configuration Layer 2/Layer 3 Ethernet Stackable Switch. (SFP Small Formfactor Pluggable)
			,cat3750G48-ts(428)		--  Catalyst 3750 48 10/100/1000 ports + 4 Gigabit Ethernet SFP ports Layer 2/Layer 3 Module.(SFP Small Form factor Pluggable)
			,cds-x9132-k9(430)		--  DS-X9132-K9 MDS 9132 Chassis
			,cds-x9116-k9(431)		--  DS-X9116-K9 MDS 9116 Chassis
			,cat3560G24-ps(432)		--  Catalyst 3560 24 10/100/1000 Power over Ethernet ports + 4 Gigabit Ethernet SFP ports Layer 2/Layer 3 Switch.(SFP Small Form factor Pluggable)
			,cat3560G24-ts(433)		--  Catalyst 3560 24 10/100/1000 Ethernet ports + 4 Gigabit Ethernet SFP ports Layer 2/Layer 3 Switch.(SFP Small Form factor Pluggable)
			,cat3560G48-ps(434)		--  Catalyst 3560 48 10/100/1000 Power over Ethernet ports + 4 Gigabit Ethernet SFP ports Layer 2/Layer 3 Switch.(SFP Small Form factor Pluggable)
			,cat3560G48-ts(435)		--  Catalyst 3560 48 10/100/1000 ports + 4 Gigabit Ethernet SFP ports Layer 2/Layer 3 Switch.(SFP Small Form factor Pluggable)
			,cds-c9216i-k9(436)		--  2-Slot MDS fabric switch chassis
			,as5400-xm(437)			--  Chassis for Cisco AS5400XM
			,as5350-xm(438)			--  Chassis for Cisco AS5350XM
			,airap-1130(439)		--  Cisco Aironet 1130 series WLAN Access Point with 1 10/100TX port, dual IEEE 802.11a and 802.11g  radio port
			,c7604(440)			--  Cisco 7604 chassis, a 4-slot chassis.
			,cat3750G24-ts1u(441)		--  Catalyst 3750 24 10/100/1000 Ethernet ports + 4 Gigabit Ethernet SFP ports Layer 2/Layer 3 Module.(SFP Small Form factor Plugable)
                        ,cn7kc7010(442)                 --  Nexus7000 10 slot N7K chassis
			,c371098-hp-001(443)		--  24 port Gigabit Ethernet switch module for HP ProLiant BL p-class server chassis
			,cat356024-ts(447)		--  Catalyst 3560 24 10/100 ports + 2 Gigabit SFP ports fixed configuration Layer 2/Layer 3 Ethernet Switch. (SFP Small Formfactor Pluggable)
			,cat356048-ts(448)		--  Catalyst 3560 48 10/100 ports + 4 Gigabit SFP ports fixed configuration Layer 2/Layer 3 Ethernet Switch. (SFP Small Formfactor Pluggable)
			,cwlse1130(454)			--  Chassis for Cisco WLSE 1130.
			,cwlse1030(455)			--  Chassis for Cisco WLSE 1030.
			,cids4210(457)			--  Cisco Intrusion Detection System 4210
			,cids4215(458)			--  Cisco Intrusion Detection System 4215
			,cids4235(459)			--  Cisco Intrusion Detection System 4235
			,cids4240(460)			--  Cisco Intrusion Prevention System 4240
			,cids4250(461)			--  Cisco Intrusion Detection System 4250
			,cids4250sx(462)			--  Cisco Intrusion Detection System 4250 with fiber interface
			,cids4250xl(463)			--  Cisco Intrusion Detection System 4250 with accelerator card
			,cids4255(464)			--  Cisco Intrusion Prevention System 4255
			,cat375024-fs(465)			--  Catalyst 3750 24 100BaseFX ports + 2 Ethernet Gigabit SFP ports fixed configuration Layer 2/Layer 3 Ethernet switch.   (SFP:Small Formfactor Pluggable)
			,cWSC6504E(466)			--  Catalyst 6000 series chassis with 4 slots
			,cigesm-sfp(467)			--  Cisco Systems Intelligent Gigabit Ethernet Switch Module with SFPs for IBM eServer BladeCenter (OS-CIGESM-18-SFP-E)
			,cfe-6326-k9(468)			-- Cisco File Engine Model FE-6326-K9
			,dsC9120ClK9(471)			-- DS-C9120-CL-K9  - MDS 9120-CL, 20-Port 4 Gbps Fibre Channel Fabric Switch, Commercial
			,cat3750-ge12-sfp-dc(476)			-- Catalyst 3750 12 Gigabit Ethernet SFP (small Form Factor Plugable) port chassis
			,cat296024 (477)			-- Catalyst 2960 24 10/100 ports + 2 dual purpose Gigabit Ethernet ports fixed configuration Layer 2 Ethernet switch
			,cat296048 (478)			-- Catalyst 2960 48 10/100 ports + 2 dual purpose Gigabit Ethernet ports fixed configuration Layer 2 Ethernet switch
			,cat2960-g24 (479)			-- Catalyst 2960 20 10/100/1000 ports + 4 dual purpose Gigabit Ethernet ports fixed configuration Layer 2 Ethernet switch
			,cat2960-g48 (480)			-- Catalyst 2960 44 10/100/1000 ports + 4 dual purpose Gigabit Ethernet ports fixed configuration Layer 2 Ethernet switch
			,cat6k-msfc2a (481)			-- Multilevel Switching Feature Card Version 2a for Catalyst 6000 that is treated as a standalone system by the NMS
			,cme6340aca (482)			-- DSL Switch 48 port ADSL2/2+, Annex A, AC
			,cme6340dca (483)			-- DSL Switch 48 port ADSL2/2+, Annex A, DC
			,cme6340dcb (484)			-- DSL Switch 48 port ADSL2/2+, Annex B, DC
			,cat296024-tt (485)			-- Catalyst 2960 24 10/100 ports + 2 10/100/1000 ports fixed configuration Layer 2 Ethernet Switch
			,cat296048-tt (486)			-- Catalyst 2960 48 10/100 ports + 2 10/100/1000 ports fixed configuration Layer 2 Ethernet Switch
			,cige-sms-sfp-t (487)			-- Cisco Systems Intelligent Gigabit Ethernet Switch Module with SFPs for IBM eServer BladeCenter Telco Chassis (OS-CIGESM-18-SFP-E)
			,cMEC6524gs8s (488)			-- Cisco ME 6524 chassis with 24 port SFP and 8 SFP uplinks
			,cMEC6524gt8s (489)			-- Cisco ME 6524 chassis with 24 port 10/100/1000BaseT and 8 SFP uplinks
			,cPaldron (492)			-- ARM Development Platform
			,nm-16es-1ge (493)			-- 16 Ports next genaration 10BaseT/100BaseTX EtherSwitch module with 1 GE and Inline Power
			,nm-x-24es-1ge (494)			-- 24 Ports extended next genaration 10BaseT/100BaseTX EtherSwitch module with 1 GE and Inline Power
			,nm-xd-24es-2st (495)			-- 24 Ports extended double-wide next genaration 10BaseT/100BaseTX EtherSwitch module with 2 stacking ports and Inline Power
			,nm-xd-48es-2ge (496)			-- 48 Ports extended double-wide next genaration 10BaseT/100BaseTX EtherSwitch module with 2 GE and Inline Power
			,nm-16es-1ge-no-pwr (497)			-- 16 Ports next genaration 10BaseT/100BaseTX EtherSwitch module with 1 GE
			,nm-xd-24es-2st-no-pwr (498)			-- 24 Ports extended double-wide next genaration 10BaseT/100BaseTX EtherSwitch module with 2 stacking ports
			,nm-xd-48es-2ge-no-pwr (499)			-- 48 Ports extended double-wide next genaration 10BaseT/100BaseTX EtherSwitch module with 2 GE
			,nm-x-24es-1ge-no-pwr (500)			-- 24 Ports extended next genaration 10BaseT/100BaseTX EtherSwitch module with 1 GE
			,cigesm-t (501)			-- Cisco Systems Intelligent Gigabit Ethernet Switch Module for IBM eServer BladeCenter Telco Chassis (OS-CIGESM-18TT-E)
			,catCE500-24tt (502)			-- Catalyst Express 500 24 10/100 ports + 2 Gigabit Ethernet ports fixed configuration Layer 2 Ethernet switch
			,catCE500-24lc (503)			-- Catalyst Express 500 24 10/100 ports (4 Power Over Ethernet Ports) + 2 dual purpose Gigabit Ethernet ports fixed configuration Layer 2 Ethernet switch
			,catCE500-24pc (504)			-- Catalyst Express 500 24 10/100 Power Over Ethernet Ports + 2 dual purpose Gigabit Ethernet ports fixed configuration Layer 2 Ethernet switch
			,catCE500-12tc (505)			-- Catalyst Express 500 8 Gigabit Ethernet Ports + 4 dual purpose Gigabit Ethernet ports fixed configuration Layer 2 Ethernet switch
			,c5750 (506)			-- High Assurance Router
			,cMWR1941DCA(507)		-- The Mobile Wireless Router (MWR-1941-DC-A) is a router with a universal power supply targeted at application in a cell site Base Transceiver Station (BTS) providing backhaul connections to the aggregation node in Radio Access Networks (RAN) and support for AIM module.
			,c815(508)			-- Cisco 815 platform fixed configuration cable modem router with 4 FastEthernet switch ports, 1 Cable modem port, 1 FastEthernet port
			,c240024-tsa (509)			-- Metro Ethernet 2400, 24 10/100 Fast Ethernet + 2 SFP ports fixed configuration Layer 2 Ethernet switch, AC power
			,c240024-tsd (510)			-- Metro Ethernet 2400, 24 10/100 Fast Ethernet + 2 SFP ports fixed configuration Layer 2 Ethernet switch, DC power
			,c340024-tsa (511)			-- Metro Ethernet 3400, 24 10/100 Fast Ethernet + 2 SFP ports fixed configuration Layer 2/3 Ethernet switch, AC power
			,c340024-tsd (512)			-- Metro Ethernet 3400, 24 10/100 Fast Ethernet + 2 SFP ports fixed configuration Layer 2/3 Ethernet switch, DC power
			,cCRS18-linecard (513)			-- Cisco CRS-1 Series 8 slot Line Card Chassis
			,cCRS1-fabric (514)			-- Cisco CRS-1 Series Fabric Card Chassis
			,cids4220 (515)				-- Cisco Intrusion Detection System 4220
			,cids4230 (516)				-- Cisco Intrusion Detection System 4230
			,ws-3020-hpq(518)			-- Cisco Catalyst Bladeswitch 3020 for HP
			,ws-3030-del(519)			-- Cisco Catalyst Bladeswitch 3030 for Dell
			,cwlse-1133(520)			-- Chassis for Cisco WLSE 1133.
			,airap-1250(521)			-- Cisco Aironet 1250 series WLAN Access Point with one 10/100/1000TX port and dual IEEE 802.11n radio ports
			,cat3750-g24-ws(523)			-- Catalyst 3750 Unified Access Switch with 24 10/100/1000 Power over Ethernet ports + 2 Gigabit Ethernet SFP ports and integrated Wireless Controller
			,me-3400g-12cs-a(524)			-- Metro Ethernet 3400 , 12 GE/SFP ports + 4 SFP ports fixed configuration Layer 2/3 Ethernet switch, AC power
			,me-3400g-12cs-d(525)			-- Metro Ethernet 3400 , 12 GE/SFP ports + 4 SFP ports fixed configuration Layer 2/3 Ethernet switch, DC power
			,c877-m(526)				-- Cisco 877 platform with 1 ADSL Annex M over POTS WAN interface, 4-port 10/100 BASE-T LAN Ethernet switch, hardware encryption and an optional Wireless LAN card
			,c1801-m(527)				-- Cisco 1800 platform with 1 ADSL Annex M over POTS WAN interface, 8-port 10/100 BASE-T LAN Ethernet switch, 1 ISDN BRI S/T interface and an optional Wireless LAN.
			,ws-cbs3040-fsc(528)			-- Cisco Catalyst Blade Switch 3040 for FSC
			,spa-ipsec-2g-2(529)			-- IPSec Shared Port Adapter with 2 Gbps DES/3DES/AES (SPA-IPSEC-2G-2)
			,cDSC9124(530)				-- Chassis of 24-port 1/2/4 Gig Supervisor Storage Switch
			,cat3750e-48-td(531)			-- Catalyst 3750E 48 10/100/1000 ports + 2 TenGigabit Ethernet (X2) ports fixed configuration Layer 2/Layer 3 Ethernet Stackable switch
			,cat3750e-24-td(532)			-- Catalyst 3750E 24 10/100/1000 ports + 2 TenGigabit Ethernet (X2) ports fixed configuration Layer 2/Layer 3 Ethernet Stackable switch
			,cat3750e-24-pd(533)                    -- Catalyst 3750E 24 10/100/1000 Power over Ethernet ports + 2 TenGigabit Ethernet (X2) ports fixed configuration Layer 2/Layer 3 Ethernet Stackable switch
			,cat3750e-48-pd(534)			-- Catalyst 3750E 48 10/100/1000 Power over Ethernet ports + 2 TenGigabit Ethernet (X2) ports fixed configuration Layer 2/Layer 3 Ethernet Stackable switch
			,cat3560e-24-td(535)			-- Catalyst 3560E 24 10/100/1000 ports + 2 TenGigabit Ethernet (X2) ports fixed configuration Layer 2/Layer 3 Ethernet Stackable switch
			,cat3560e-48-td(536)			-- Catalyst 3560E 48 10/100/1000 ports + 2 TenGigabit Ethernet (X2) ports fixed configuration Layer 2/Layer 3 Ethernet Stackable switch
			,cat3560e-24-pd(537)                    -- Catalyst 3560E 24 10/100/1000 Power over Ethernet ports + 2 TenGigabit Ethernet (X2) ports fixed configuration Layer 2/Layer 3 Ethernet Stackable switch
			,cat3560e-48-pd(538)                    -- Catalyst 3560E 48 10/100/1000 Power over Ethernet ports + 2 TenGigabit Ethernet (X2) ports fixed configuration Layer 2/Layer 3 Ethernet Stackable switch
			,cat3560-8pc(539)			-- Catalyst 3560 8 10/100 Power over Ethernet ports + 1 dual purpose Gigabit Ethernet Ports fixed configuration Layer 2 /Layer 3 Ethernet Switch
			,cat2960-8tc(540)			-- Catalyst 2960 8 10/100 Ethernet ports + 1 dual purpose Gigabit Ethernet Port fixed configuration Layer 2 Ethernet Switch
			,cat2960-g8-tc(541)			-- Catalyst 2960 7 10/100/1000 Ethernet ports + 1 dual purpose Gigabit Ethernet Port fixed configuration Layer 2 Ethernet Switch
			,cDSIBMFC(542)				-- Chassis of Cisco 4Gb Fibre Channel Switch Module for IBM BladeCenter
			,cips-virtual(543)			-- Cisco Intrusion Prevention System virtual sensor
			,c5720(544)				-- Integrated Encryption Router
			,cDSHPFC(545)				-- Chassis of Cisco 4Gb Fibre Channel Switch Module for HP BladeSystem
			,c3205WMIC(546)				-- Cisco 3205 Wireless MIC (Mobile Interface card) with 802.11a wireless interface in the PC104+ form factor. An interface card for the existing MAR 3200 products(Mobile Access Router)
			,me-3400g-2cs-a(547)			-- Metro Ethernet 3400, 2 GE/SFP ports + 2 SFP ports fixed configuration Layer 2/3 Ethernet switch, AC power
			,c7201(548)				-- Cisco 7201 platform, 1 Rack Unit (RU) application specific router with 1 slot
			,ds-c9222i-k9(549)			-- DS-C9222i-K9 Coco chassis
			,cUBR-7225-vxr(550)			-- Cisco 7225 Universal Broadband Router, VXR series
			,cWSC6509ve(552)			-- Catalyst 6500 enhanced 9-slot vertical chassis
			,cDSC9134(553)				-- Chassis of 32-port 1/2/4 with 10 Gig Supervisor Storage
			,c5740(557)				-- Integrated Encryption Router
			,c867(560)                              -- c867 with 1 ADSL2/2+ AnnexA, 4 switch ports, 1 Console/Aux port, and an optional Wireless LAN
                        ,c886(566)                              -- c886 with 1 ADSL2/2+ AnnexB, 4 switch ports, 1 USB 1.1 port, 1 Console/Aux port, 1 ISDN, and an optional Wireless LAN
                        ,c886-g(567)                            -- c886G with 1 ADSL2/2+ AnnexB, 4 switch ports, 1 USB 2.0 port, 1 Console/Aux port, 1 3G PCMCIA slot, and an optional Wireless LAN
                        ,cIad-886-f(568)                        -- IAD886F with 1 ADSL2/2+ AnnexB, 4 switch ports, 1 USB 1.1 port, 1 Console/Aux port, 1 ISDN, 4 FXS ports, and an optional Wireless LAN
                        ,cIad-886-b(569)                        -- IAD886B with 1 ADSL2/2+ AnnexB, 4 switch ports, 1 USB 1.1 port, 1 Console/Aux port, 1 ISDN, 2 PBX BRI ports, and an optional Wireless LAN
                        ,c886-srst(570)                         -- c886SRST with 1 ADSL2/2+ AnnexB, 4 switch ports, 1 USB 1.1 port, 1 Console/Aux port, 4 FXS ports, 1 PSTN BRI port, and an optional Wireless LAN
                        ,c887(571)                              -- c887 with 1 ADSL2/2+ AnnexA, 4 switch ports, 1 USB 1.1 port, 1 Console/Aux port, 1 ISDN, and an optional Wireless LAN
                        ,c887-g(572)                            -- c887G with 1 ADSL2/2+ AnnexA, 4 switch ports, 1 USB 2.0 port, 1 Console/Aux port, 1 3G PCMCIA slot, and an optional Wireless LAN
                        ,cIad-887-f(573)                        -- IAD887 with 1 ADSL2/2+ AnnexA, 4 switch ports, 1 USB 1.1 port, 1 Console/Aux port, 1 ISDN, 4 FXS ports, and an optional Wireless LAN
                        ,cIad-887-b(574)                        -- IAD887B with 1 ADSL2/2+ AnnexA, 4 switch ports, 1 USB 1.1 port, 1 Console/Aux port, 1 ISDN, 2 PBX BRI ports, and an optional Wireless LAN
                        ,c887-srst(575)                         -- c887SRST with 1 ADSL2/2+ AnnexA, 4 switch ports, 1 USB 1.1 port, 1 Console/Aux port, 4 FXS ports, 1 PSTN BRI port, and an optional Wireless LAN
			,c7816-h(586)				-- MCS-7816H class of servers Starting with CCM 6.0 release
			,c7603s(587)				-- 3 slots S-Series chassis in Cisco 7600 family
			,c7606s(588)				-- 6 slots S-Series chassis in Cisco 7600 family
			,c7609s(589)				-- 9 slots S-Series chassis in Cisco 7600 family
			,cmds-dsc-9222i(590)			-- MDS 9222i 18-port FC and 4-port GE + 1-slot Modular Switch
			,cuc500(591)				-- Cisco Unified Communication 500 (UC500)
			,c860-ap(592)	   			-- Cisco 860 AP is the embedded wireless access point module for Cisco 860 router. It has one IEEE 802.11 b/g/n radio port which operates in 2.4 GHz.
			,c880-ap(593)				-- Cisco 880 AP is the embedded wireless access point module for Cisco 880 router. It has one IEEE 802.11 b/g/n radio port which operates in 2.4 GHz.
			,c890-ap(594)				-- Cisco 890 AP is the embedded wireless access point module for Cisco 890 router. It has one IEEE 802.11 b/g/n radio port which operates in 2.4 GHz and one IEEE 802.11 a/n radio port which operates in 5 GHz
			,c1900-ap(595)				-- Cisco 1900 AP is the embedded wireless access point module for Cisco 1900 router. It has one IEEE 802.11 b/g/n radio port which operates in 2.4 GHz and one IEEE 802.11 a/n radio port which operates in 5 GHz
			,me-3400-24fs-a(596)			-- Metro Ethernet 3400, 24 100BaseFX Fast Ethernet + 2 SFP ports fixed configuration Layer 2/3 Ethernet switch, AC power
			,cuc520s-8u-4fxo-k9(597)                -- UC500 with support for 8 switch ports and 4 FXO ports
			,cuc520s-8u-4fxo-w-k9(598)              -- UC500 with support for 8 switch ports, 4 FXO ports, and Wi-Fi
 			,cuc520s-8u-2bri-k9(599)                -- UC500 with support for 8 switch ports and 2 BRI
			,cuc520s-8u-2bri-w-k9(600)              -- UC500 with support for 8 switch ports and 2 BRI, and Wi-Fi
			,cuc520s-16u-4fxo-k9(601)               -- UC500 with support for 16 switch ports and 4 FXO ports
			,cuc520s-16u-4fxo-w-k9(602)             -- UC500 with support for 16 switch ports, 4 FXO ports, and Wi-Fi
			,cuc520s-16u-2bri-k9(603)               -- UC500 with support for 16 switch ports and 2 BRI
			,cuc520s-16u-2bri-w-k9(604)             -- UC500 with support for 16 switch ports and 2 BRI, and Wi-Fi
			,cuc520m-32u-8fxo-k9(605)               -- UC500 with support for 32 switch ports and 8 FXO ports
			,cuc520m-32u-8fxo-w-k9(606)             -- UC500 with support for 32 switch ports and 8 FXO ports, and Wi-Fi
			,cuc520m-32u-4bri-k9(607)		-- UC500 with support for 32 switch ports and 4 BRI
			,cuc520m-32u-4bri-w-k9(608)		-- UC500 with support for 32 switch ports and 4 BRI, and Wi-Fi
			,cuc520m-48u-12fxo-k9(609)              -- UC500 with support for 48 switch ports and 12 FXO ports
			,cuc520m-48u-12fxo-w-k9(610)		-- UC500 with support for 48 switch ports and 12 FXO ports, and Wi-Fi
			,cuc520m-48u-6bri-k9(611)               -- UC500 with support for 48 switch ports and 6 BRI
			,cuc520m-48u-6bri-w-k9(612)		-- UC500 with support for 48 switch ports and 6 BRI, and Wi-Fi
			,cuc520m-48u-1t1e1-f-k9(613)            -- UC500 with support for 48 switch ports,1 T1E1 and 4 FXO ports
			,cuc520m-48u-1t1e1-b-k9(614)            -- UC500 with support for 48 switch ports ,1 T1E1 and BRI
		        ,c7828-h(615)				-- MCS-7828H class of servers Starting with CCM 6.0 release
			,c7816-i(616)				-- MCS-7816I class of servers Starting with CCM 6.0 release
			,c7828-i(617)				-- MCS-7828I class of servers Starting with CCM 6.0 release
			,c1861-uc-2b-k9(618)                    -- C1861 UC with support for 2 BRI ports and CUE
                        ,c1861-uc-4f-k9(619)                    -- C1861 UC with support for 4 FXO ports and CUE
                        ,c1861-srst-2b-k9(620)                  -- C1861 SRST with support for 2 BRI ports
			,c1861-srst-4f-k9(621)			-- C1861 SRST with support for 4 FXO ports
			,c7330-oe-k9(622)			-- Cisco Optimization Engine Model OE-7330-K9.
			,c7350-oe-k9(623)			-- Cisco Optimization Engine Model OE-7350-K9.
                        ,cat2960-48tc-s(628)                    -- WS-C2960-48TC-S chassis
                        ,cat2960-24tc-s(629)                    -- WS-C2960-24TC-S chassis
                        ,cat2960-24-s(630)                      -- WS-C2960-24-S chassis
                        ,cat2960-24pc-l(631)                    -- WS-C2960-24PC-L chassis
                        ,cat2960-24lt-l(632)                    -- WS-C2960-24LT-L chassis
                        ,cat2960pd-8tt-l(633)                   -- WS-C2960PD-8TT-L chassis
                        ,casr1002(634)                          -- Cisco Aggregation Services Router 1000 Series 2RU Chassis
                        ,casr1004(635)                          -- Cisco Aggregation Services Router 1000 Series 4RU Chassis
                        ,casr1006(636)                          -- Cisco Aggregation Services Router 1000 Series 6RU Chassis
                        ,catrfgw(637)                           -- RF gateway chassis with 2SUP+10RF+2TCC+12RFSW slots
                        ,catce520-24pc(638)                     -- Catalyst Express 520 24 10/100 Power over Ethernet ports + 2 dual purpose Gigabit Ethernet Ports fixed configuration Layer 2 Ethernet Switch
                        ,catce520-24lc(639)                     -- Catalyst Express 520 4 10/100 Power over Ethernet ports + 20 10/100 ports + 2 dual purpose Gigabit Ethernet Ports fixed configuration Layer 2 Ethernet Switch
                        ,catce520-24tt(640)                     -- Catalyst Express 520 4 10/100 Power over Ethernet ports + 20 10/100 ports + 2 dual purpose Gigabit Ethernet Ports fixed configuration Layer 2 Ethernet Switch
                        ,catce520-g24tc(641)                    -- Catalyst Express 520 24 10/100/1000 ports + 2 dual purpose Gigabit Ethernet Ports fixed configuration Layer 2 Ethernet Switch
                        ,c1861-srst-2b-cue-k9(642)              -- C1861 SRST with support for 2 BRI ports and CUE
                        ,c1861-srst-4f-cue-k9(643)              -- C1861 SRST with support for 4 FXO ports and CUE
                        ,cvgd-1t3(644)                          -- VGD Voice Gateway with 1xCT3 supporting CCM and MGCP
                        ,ws-cbs3130g-s(648)                     -- Cisco Catalyst Blade Switch 3130G for Dell %DNP until Mar 2008, contact unknown /* Earlier contact was alexv */
                        ,ws-cbs3130x-s(649)                     -- Cisco Catalyst Blade Switch 3130X for Dell %DNP until Mar 2008, contact unknown /* Earlier contact was alexv */
                        ,cat3560e-12-sd(650)                    -- Catalyst 3560E, 12 SFP Gigabit Ethernet ports + 2 TenGigabit Ethernet (X2) ports
                        ,ccisco-optimization-engine-674(651)    -- Cisco Optimization Engine 674
                        ,cie3000-4tc(652)                       -- Cisco Industrial Ethernet 3000 Switch, 4 10/100 + 2 T/SFP
                        ,cie3000-8tc(653)                       -- Cisco Industrial Ethernet 3000 Switch, 4 10/100 + 2 T/SFP
                        ,craie1783-ms06(654)                    -- Rockwell brand Industrial Ethernet  Switch, 4 10/100 + 2 T/SFP
                        ,craie1783-ms10t(655)                   -- Rockwell brand Industrial Ethernet Switch, 8 10/100 + 2 T/SFP
                        ,c2435iad-8fxs(656)                     -- IAD2435 with 8FXS,2FE and 1T1E1
                        ,vg204(657)                             -- Line side Analog Gateway with 4FXS Analog ports
                        ,vg202(658)                             -- Line side Analog Gateway with 2FXS Analog ports
                        ,cat2918-24tt(659)                      -- Catalyst 2918 24 10/100 ports + 2 10/100/1000 Ethernet ports fixed configuration Layer 2 Ethernet switch
                        ,cat2918-24tc(660)                      -- Catalyst 2918 24 10/100 ports + 2 dual purpose Gigabit Ethernet ports fixed configuration Layer 2 Ethernet switch
                        ,cat2918-48tt(661)                      -- Catalyst 2918 48 10/100 ports + 2 10/100/1000 Ethernet ports fixed configuration Layer 2 Ethernet switch
                        ,cat2918-48tc(662)                      -- Catalyst 2918 48 10/100 ports + 2 dual purpose Gigabit Ethernet ports fixed configuration Layer 2 Ethernet switch
                        ,cuc520-24u-4bri-k9(663)                -- UC500 with support for 24U CME Base, CUE and Phone FL w/4BRI, 1VIC
                        ,cuc520-24u-8fxo-k9(664)                -- UC 500 with support for 24U CME Base, CUE and Phone FL w/8FXO, 1VIC
                        ,cuc520s-8u-2bri-w-j-k9(665)            -- UC500 for Japan with support for 8 switch ports and 2 BRI, and Wi-Fi
                        ,cuc520s-16u-2bri-w-j-k9(666)           -- UC500 for Japan with support for 16 switch ports and 2 BRI, and Wi-Fi
                        ,c1805(667)                             -- Cisco1805 is a repackaging effort for design to address the low end cable access market. C1805 is deployed as cut down and fixed version of Cisco C1841
                        ,cmwr-2941-dc(669)                      -- The Mobile Wireless Router (MWR-2941-DC) is an environmentally hardened router targeted for application in a cell site Base Transceiver Station (BTS) providing backhaul connections to the aggregation node in Radio Access Networks (RAN).
                        ,coe574(670)                            -- Cisco Optimization Engine 574
                        ,coe474(671)                            -- Cisco Optimization Engine 474
                        ,coe274(672)                            -- Cisco Optimization Engine 274
                        ,c7816c(673)                            -- MCS-7816C class of servers Base model CAM-16
                        ,cap801agn(674)                         -- Cisco AP801 Access Point with dual IEEE 802.11a/g/n radio ports
                        ,cap801gn(675)                          -- Cisco AP801 Access Point with single IEEE 802.11g/n radio port
                        ,c1861W-srst-4f-cue-k9(676)             -- C1861 SRST with support for 4 FXO ports, Wireless and CUE
                        ,c1861W-srst-2b-cue-k9(677)             -- C1861 SRST with support for 2 BRI ports, Wireless and CUE
                        ,c1861W-srst-4f-k9(678)                 -- C1861 SRST with support for 4 FXO ports and Wireless
                        ,c1861W-srst-2b-k9(679)                 -- C1861 SRST with support for 2 BRI ports and Wireless
                        ,c1861W-uc-4f-k9(680)                   -- C1861 UC with support for 4 FXO ports, Wireless and CUE
                        ,c1861W-uc-2b-k9(681)                   -- support for 2 BRI ports, Wireless and CUE
                        ,cme-3400e-24ts-m(682)                  -- Metro Ethernet 3400E, 24 10/100 Fast Ethernet + 2 SFP ports fixed configuration Layer 2/3 Ethernet switch, modular power
                        ,cme-3400eg-12cs-m(683)                 -- Metro Ethernet 3400 , 12 GE/SFP ports + 4 SFP ports fixed configuration Layer 2/3 Ethernet switch, modular power
                        ,cme-3400eg-2cs-a(684)                  -- Metro Ethernet 3400E, 2 GE/SFP ports + 2 SFP ports fixed configuration Layer 2/3 Ethernet switch, AC power
                        ,cce674(685)                            -- Cisco Content Engine 674
                        ,ccam35(686)                            -- Four port GigE Common Appliance Model 35 for Service Control Operating System
                        ,cce7341(692)                           -- Cisco Content Engine  7341
                        ,cce7371(693)                           -- Cisco Content Engine  7371
                        ,cat2960-48tts(694)                     -- Catalyst 2960 48 10/100 ports + 2 10/100/1000 Ethernet ports fixed configuration Layer 2 Ethernet switch
                        ,cat2960-8tcs(695)                      -- Catalyst 2960 8 10/100 ports + 1 dual purpose Gigabit Ethernet port fixed configuration Layer 2 Ethernet switch
                        ,sr520fe(697)                           -- SR520 with 1 10/100T ethernet WAN interface, 4-port 10/100 Base-T LAN Ethernet switch, hardware encryption and an optional Wireless LAN card
                        ,sr520adsl(698)                         -- SR520 with 1 ADSL over POTS WAN interface, 4-port 10/100 BASE-T LAN Ethernet switch, hardware encryption and an optional Wireless LAN card
                        ,sr520adsli(699)                        -- SR520 with 1 ADSL over ISDN WAN interface, 4-port 10/100 Base-T LAN Ethernet switch, hardware encryption and an optional Wireless LAN card
                        ,cn7kc7018(700)                         -- Nexus7000 18 slot N7K chassis
                        ,cat3560-12pcs(702)                     -- Catalyst 3560 12 10/100 Power over Ethernet ports + 1 dual purpose Gigabit Ethernet port fixed  configuration Layer 2 Ethernet switch
                        ,cat2960-48pstl(703)                    -- Catalyst 2960 48 10/100 Power over Ethernet ports + 2 10/100/1000 Ethernet Ports + 2 SFP fixed configuration Layer 2 Ethernet switch
                        ,cat3560v2-24ts-d(704)                  -- 24 10/100 ports + 2 Ethernet Gigabit SFP ports fixed configuration Layer 2/Layer 3 Ethernet Non-stackable switch, DC power
                        ,cat3560v2-24ts(705)                    -- 24 10/100 ports + 2 Ethernet Gigabit SFP ports fixed configuration Layer 2/Layer 3 Ethernet Non-stackable switch
                        ,cat3560v2-24ps(706)                    -- 24 10/100 ports + 2 Ethernet Gigabit SFP ports fixed configuration Layer 2/Layer 3 Ethernet Non-stackable PoE switch
                        ,cat3750v2-24ts(707)                    -- 24 10/100 ports + 2 Ethernet Gigabit SFP ports fixed configuration Layer 2/Layer 3 Ethernet Stackable switch
                        ,cat3750v2-24ps(708)                    -- 24 10/100 ports + 2 Ethernet Gigabit SFP ports fixed configuration Layer 2/Layer 3 Ethernet Stackable PoE switch
                        ,cat3560v2-48ts(709)                    -- 48 10/100 ports + 4 Ethernet Gigabit SFP ports fixed configuration Layer 2/Layer 3 Ethernet Non-stackable switch
                        ,cat3560v2-48ps(710)                    -- 48 10/100 ports + 4 Ethernet Gigabit SFP ports fixed configuration Layer 2/Layer 3 Ethernet Non-stackable PoE switch
                        ,cat3750v2-48ts(711)                    -- 48 10/100 ports + 4 Ethernet Gigabit SFP ports fixed configuration Layer 2/Layer 3 Ethernet Stackable switch
                        ,cat3750v2-48ps(712)                    -- 48 10/100 ports + 4 Ethernet Gigabit SFP ports fixed configuration Layer 2/Layer 3 Ethernet Stackable PoE switch
                        ,airbr-1430(713)                        -- Cisco 1400 series wireless LAN bridge with three Gigabit Ethernet ports and one 802.11A radio
                        ,namapp2204-rj45(714)                   -- Cisco NAM Appliance 2204 with RJ45 connector
                        ,namapp2220(715)                        -- Cisco NAM Appliance 2220
                        ,airap-1141(716)                        -- Cisco Aironet 1140 series WLAN Access Point with one 10/100/1000TX port and single IEEE 802.11n radio port
                        ,airap-1142(717)                        -- Cisco Aironet 1140 series WLAN Access Point with one 10/100/1000TX port and dual IEEE 802.11n radio ports
                        ,c887-vdsl2(718)                        -- c887Vdsl2 with 1 VDSL2 only over POTS, 4 switch ports, 1 USB 1.1 port, 1 Console/Aux port and 1 ISDN
                        ,c1941(719)                             -- Cisco 1941(2 GE, 2 EHWIC)
                        ,c2901(720)                             -- Cisco 2901(2 GE, 4 EHWIC, 2 DSP)
                        ,c2911(721)                             -- Cisco 2911(3 GE, 4 EHWIC, 1 SM, 2 DSP)
                        ,c2921(722)                             -- Cisco 2921(3 GE, 4 EHWIC, 1 SM, 3 DSP)
                        ,c2951(723)                             -- Cisco 2951(3 GE, 4 EHWIC, 2 SM, 3 DSP)
                        ,c3925(724)                             -- Cisco 3925 w/ SPE100(3 GE, 4 EHWIC, 2 SM, 4 DSP)
                        ,c3945(725)                             -- Cisco 3945 w/ SPE150(3 GE, 4 EHWIC, 4 SM, 4 DSP)
                        ,csr520-t1(726)                         -- This is a voice and data platform with 2 FE and 1 T1 port. This is done by Small Business Technology Group
                        ,nam-app2204-sfp(728)                   -- Cisco NAM Appliance 2204 with SFP connector
                        ,c1941w(735)                            -- Cisco 1941(2GE, 2 EHWIC, 801.11n  WLAN)
                        ,c888e(736)                             -- c888 with 1 EFM based 4 port G.SHDSL , 4 switch ports, 1 USB 1.1 port, 1 Console/Aux port, 1 ISDN, and an optional Wireless LAN
                        ,c888eg(737)                            -- c888EG with 1 EFM based 4 pair G.SHDSL, 4 switch ports, 1 USB 2.0 port, 1 Console/Aux port, 1 3G PCMCIA slot, and an optional Wireless LAN
                        ,iad888ef(738)                          -- IAD888EF with 1 EFM based 4 pair G.SHDSL, 4 switch ports, 1 USB 1.1 port, 1 Console/Aux port, 1 ISDN, 4 FXS ports, and an optional Wireless LAN
                        ,iad888eb(739)                          -- IAD888EB with 1 EFM based 4 pair G.SHDSL, 4 switch ports, 1 USB 1.1 port, 1 Console/Aux port, 1 ISDN, 2 PBX BRI ports, and an optional Wireless LAN
                        ,c888esrst(740)                         -- c888ESRST with 1 EFM based 4 pair G.SHDSL, 4 switch ports, 1 USB 1.1 port, 1 Console/Aux port, 4 FXS ports, 1 PSTN BRI port, and an optional Wireless LAN
                        ,c3845nv(741)                           -- Four Network Module Slots, Four WIC slots, Two Gigabit Ethernet ports 3800nv family router
                        ,c3825nv(742)                           -- Two Network Module Slots, Four WIC slots, Two Gigabit Ethernet ports 3800nv family router
                        ,ws-c2350-48td(743)                     -- Catalyst 2350 48 10/100/1000 ports + 2 TenGigabit Ethernet (X2) ports fixed configuration Layer 2 Ethernet Switch
                        ,c887-m(744)                             -- c887 with 1 ADSL2/2+ AnnexM, 4 switch ports, 1 USB 1.1 port, 1 Console/Aux port, 1 ISDN, and an optional Wireless LAN
                        ,casr1002f(751)                          -- Cisco Aggregation Services Router 1000 Series, 2RU Fixed Chassis
                        ,cairap-3501(758)                        -- Cisco Aironet 3500 Series WLAN Access Point with one 10/100/1000TX port and single IEEE 802.11n radio port
                        ,cairap-3502(759)                        -- Cisco Aironet 3500 Series WLAN Access Point with one 10/100/1000TX port and dual IEEE 802.11n radio ports
                        ,cdscde200(760)                          -- Cisco Content Delivery System Model CDE-200
                        ,cdscde100(761)                          -- Cisco Content Delivery System Model CDE-100
                        ,cdscde300(762)                          -- Cisco Content Delivery System Model CDE-300
                        ,cdscde400(763)                          -- Cisco Content Delivery System Model CDE-400
                        ,catsps-2004-b(767)                      -- Metro Ethernet Switch with 1 1000Base-BX-U WAN port and 5 10/100/1000M LAN ports
                        ,catsps-204-b(768)                       -- Metro Ethernet Switch with 1 100Base-BX-U WAN and 5 10/100/1000M LAN ports
                        ,cap541n-a-k9(772)                       -- 802.11a/b/g/n Wireless LAN Access Point for North America, FCC band plan
                        ,cap541n-e-k9(773)                       -- 802.11a/b/g/n Wireless LAN Access Point for Europe, ETSI band plan
                        ,cap541n-n-k9(774)                       -- 802.11a/b/g/n Wireless LAN Access Point for ANZ band plan
                        ,csrp521(775)                            -- Service Ready Platform router with Fast Ethernet WAN port
                        ,csrp526(776)                            -- Service Ready Platform router with ADSL2+ over ISDN WAN port
                        ,csrp527(777)                            -- Service Ready Platform router with ADSL2+ over POTS WAN port
                        ,csrp541(778)                            -- Service Ready Platform router with GE WAN port
                        ,csrp546(779)                            -- Service Ready Platform router with ADSL2+ over ISDN WAN port as well as GE WAN port
                        ,csrp547(780)                            -- Service Ready Platform router with ADSL2+ over POTS WAN port as well as GE WAN port
                        ,cvs510-fxo(781)                         -- Call control solution for 4-24 phone
                        ,c887-gvdsl2(782)                        -- c887G with 1 VDSL2 only over POTS, 4 switch ports, 1 USB 2.0 port, 1 Console/Aux port, 1 3G PCMCIA slot, and an optional Wireless LAN
                        ,c887-srstvdsl2(783)                     -- c887SRSTVdsl2 with 1 VDSL2 over POTS, 4 switch ports, 1 USB 1.1 port, 1 Console/Aux port, 4 FXS ports, 1 PSTN BRI port,and an optional Wireless LAN
                        ,c59xx(786)                              -- Chassis Type for 59xx embedded services family of routers
                        ,cat2960-24-lcs(787)                     -- Catalyst 2960 8 10/100 Power over Ethernet ports + 16 10/100 Ethernet ports + 2 dual purpose Gigabit Ethernet ports fixed configuration Layer 2 Ethernet switch
                        ,cat2960-24-pcs(788)                     -- Catalyst 2960 24 10/100 Power over Ethernet ports + 2 dual purpose Gigabit Ethernet ports fixed configuration Layer 2 Ethernet switch
                        ,cat2960-48-psts(789)                    -- Catalyst 2960 48 10/100 Power over Ethernet ports + 2 10/100/1000 Ethernet ports + 2 SFP ports fixed configuration Layer 2 Ethernet switch
                        ,cnm-wae-900(790)                        -- Cisco Network Module Intergrated Service Engine 900
                        ,cnm-wae-700(791)                        -- Cisco Network Module Intergrated Service Engine 700
                        ,c5940(792)                              -- Chassis Type for 5940 embedded services family of routers
                        ,cn4kibmeth(793)                         -- Chassis of Cisco 10Gb Ethernet Switch Module for IBM BladeCenter
                        ,casr1001(794)                           -- Cisco Aggregation Services Router 1000 Series, 1RU Chassis
                        ,casr1013(795)                           -- Cisco Aggregation Services Router 1000 Series, 13RU Chassis
                        ,craie1783-rms06t(796)                   -- Cisco Rockwell brand Layer 3 Industrial Ethernet Switch, 4 10/100 + 2 T/SFP
                        ,craie1783-rms10t(797)                   -- Rockwell brand Industrial Ethernet Switch, 8 10/100 + 2 T/SFP
                        ,cesw-540-8p-k9(798)                     -- Cisco ESW 540 8-port 10/100/1000 PoE switch
                        ,cesw-520-8p-k9(799)                     -- Cisco ESW 520 8-port 10/100 PoE switch
                        ,casa5555(814)                           -- Chassis type for Adaptive Security Appliance that features multiple expansion module slots, and multi-gigabit performance
                        ,cn7kc7009(815)                          -- N7K-C7009 nexus-9-slot chassis
                        ,cn4kibm-cisco-eth(816)                  -- Chassis of Cisco 10Gb Ethernet Switch Module for IBM BladeCenter Cisco sold version
                        ,cmwr-2941-dca(817)                      -- Wireless Router (MWR-2941-DC) is an environmentally hardened router
                        ,c1841ck9(832)                           -- Cisco 1841C/K9 data only router with 2 HWIC slots
                        ,c2801ck9(833)                           -- Cisco 2801C/K9 voice enabled router with 4 HWIC slots
                        ,c2811ck9(834)                           -- Cisco 2811C/K9 router with two integrated fast ethernets and integrated VPN
                        ,c2821ck9(835)                           -- Cisco 2821C/K9 router with two integrated gigabit ethernets and integrated VPN
                        ,c3825ck9(837)                           -- Cisco 3825C/K9 router with Two Network Module Slots, Four WIC slots, Two Gigabit Ethernet ports
                        ,c3845ck9(838)                           -- Cisco 3845C/K9 router with Four Network Module Slots, Four WIC slots, Two Gigabit Ethernet ports
                        ,cairap-1261(841)                        -- Cisco Aironet 1260 Series WLAN Access Point with one 10/100/1000TX port and dual IEEE 802.11n radio ports
                        ,cairap-1262(842)                        -- Cisco Aironet 1260 Series WLAN Access Point with one 10/100/1000TX port and single IEEE 802.11n radio port
                        ,c892-f(843)                             -- c892F with 1 GE/SFP port, 8 switch ports, 2 USB 2.0 ports, 2 Console/Aux ports, 1 ISDN, 1 Backup FE, and an optional Wireless LAN
                        ,cme3600x-24fsm(844)                     -- Cisco ME 3600X Ethernet Access Switch, 24 GE SFP ports + 2 10Gbps/1Gbps SFP+/SFP ports fixed configuration Layer 2/3 Ethernet switch, modular power
                        ,cme3600x-24tsm(845)                     -- Cisco ME 3600X Ethernet Access Switch, 24 10/100/1000 ports + 2 10Gbps/1Gbps SFP+/SFP ports fixed configuration Layer 2/3 Ethernet switch, modular power
                        ,cme3800x-24fsm(846)                     -- Cisco ME 3800X Carrier Ethernet Switch Router, 24 GE SFP ports + 2 10Gbps/1Gbps SFP+/SFP ports fixed configuration Layer 2/3 Carrier Ethernet Switch Router, modular power
                        ,cgr2010(847)                             -- Cisco Connected Grid Router 2010 with 2 GE, 4 GRWIC
                        ,cws-c2960s-24td-l(854)                  -- Catalyst 2960S 24 Gig Downlinks and 2 SFP+ uplink with support for a 2 x 10G stacking module
                        ,c1906ck9(859)                             -- Cisco 1906c Router(2 GE, Serial 1T, 1 EHWIC)
                        ,cairap-1042(861)                        -- Cisco Aironet 1040 series WLAN Access Point with one 10/100/1000TX port and dual IEEE 802.11n radio ports
                        ,cairap-1041(862)                        -- Cisco Aironet 1040 series WLAN Access Point with one 10/100/1000TX port and single IEEE 802.11n radio ports
                        ,c887-va(863)                            -- c887-v2 with 1 VDSL/ADSL over POTS, 4 switch ports, 1 USB 1.1 port, 1 Console/Aux port, 1 ISDN and an optional Wireless LAN
                        ,c886-va(864)                            -- c886-v2 with 1 VDSL/ADSL over ISDN, 4 switch ports, 1 USB 1.1 port, 1 Console/Aux port, 1 ISDN and an optional Wireless LAN
                        ,c867-va(865)                            -- c867-v2 with 1 VDSL/ADSL over POTS, 4 switch ports, 1 USB 1.1 port, 1 Console/Aux port, 1 ISDN and an optional Wireless LAN
                        ,c887va-m(866)                           -- c887m-v2 AnnexM with 1 VDSL/ADSL over POTS, 4 switch ports, 1 USB 1.1 port, 1 Console/Aux port, 1 ISDN and an optional Wireless LAN
                        ,casr1001-idc-2poc3pos(867)              -- ASR1001 chassis with 2xOc3Pos Integrated Daughter Card
                        ,casr1001-idc-4pt3(868)                  -- ASR1001 chassis with 4xT3 Integrated Daughter Card
                        ,casr1001-idc-4pg(869)                   -- ASR1000 1RU chassis with 4xGe Integrated Daughter Card
                        ,casr1001-idc-8pct1e1(870)               -- ASR1000 1RU chassis with 8xChT1/E1 Integrated Daughter Card
                        ,casr1001-idc-hdd(871)                   -- ASR1000 1RU chassis with harddisk Integrated Daughter Card
                        ,cat2960cpd8tt(872)                      -- Catalyst 2960c 8 10/100 ports + 2 Gigabit Ethernet PD ports fixed configuration Layer 2 Ethernet Switch
                        ,cgs252024tc(873)                        -- Cisco Connected Grid 2520 Switch, 24 10/100 + 2 T/SFP
                        ,cgs252016s8pc(874)                      -- Cisco Connected Grid 2520 Switch, 16 100 SFP + 8 10/100 + 2 T/SFP
                        ,cws-c2360-48td-s(875)                   -- Catalyst 2360 Top Of Rack 48 GigE, 4 x 10G SFP+ LAN Lite
                        ,c881-g2(876)                            -- c881G with 1 FE, 4 switch ports, 1 USB 2.0 port, 1 Console/Aux port, 1 embedded PCIe 3G modem
                        ,cws-c3750v2-24fs-s(877)                 -- Catalyst 3750 24FS: 24 10/100 ports + 2 Ethernet Gigabit SFP ports fixed configuration Layer 2/Layer 3 Ethernet Stackable switch
                        ,crs-16-s-b(878)                         -- Enhanced CRS 16 slots Line Card Chassis
                        ,ie301016s8pc(883)                       -- Cisco Industrial Ethernet 3010 Switch, 16 100 SFP + 8 10/100 + 2 T/SFP
                        ,ie301024tc(884)                         -- Cisco Industrial Ethernet 3010 Switch, 24 10/100 + 2 T/SFP
                        ,raie1783rmsb10t(885)                    -- Stratix 8300 L3 Base Industrial Ethernet Switch, 8 10/100 + 2 T/SFP
                        ,cwave-284-k9(887)                       -- Cisco Wide Area Virtualization Engine 284
                        ,cwave-584-k9(888)                       -- Cisco Wide Area Virtualization Engine 584
                        ,cwave-684-k9(889)                       -- Cisco Wide Area Virtualization Engine 684
                        ,cwave-7441-k9(890)                      -- Cisco Wide Area Virtualization Engine 7441
                        ,cwave-7471-k9(891)                      -- Cisco Wide Area Virtualization Engine 7471
                        ,cwave-7626-k9(892)                      -- Cisco Wide Area Virtualization Engine 7626
                        ,cat2928-48tcc(895)                      -- Catalyst 48 10/100 ports + 2 10/100/1000 Ethernet ports fixed configuration Layer 2 Ethernet switch
                        ,cat2928-24tcc(896)                      -- Catalyst 24 10/100 ports + 2 10/100/1000 Ethernet ports fixed configuration Layer 2 Ethernet switch
                        ,cat2928-24ltc(897)                      -- Catalyst 2928 24 10/100 ports + 2 10/100/1000 Ethernet ports fixed configuration Layer 2 Ethernet switch POE support for 123 W
                        ,cgrwic-d-es-2s-8pc(899)                    -- Grid Router Switching Module with 2 GE(1 combo, 1 SFP) interfaces and 8 100BaseT interfaces supporting PoE
                        ,cgrwic-d-es-6s(900)                        -- Grid Router Switching Module with 2 GE(1 combo, 1 SFP) interfaces and 4 100FX interfaces
                        ,c1861e-uc-2bri-k9(901)                  -- C1861E UC with support for 2 BRI ports and CUE
                        ,c1861e-uc-4fxo-k9(902)                  -- C1861E UC with support for 4 FXO ports and CUE
                        ,c1861e-srst-f-k9(903)                   -- C1861E SRST with support for 4 FXO ports
                        ,c1861e-srst-b-k9(904)                   -- C1861E SRST with support for 2 BRI ports
                        ,c1861e-srst-c-f-k9(905)                 -- C1861E SRST with support for 4 FXO ports and CUE
                        ,c1861e-srst-c-b-k9(906)                 -- C1861E SRST with support for 4 BRI ports and CUE
                        ,c88xg-2dsl(907)                         -- c88XG with 1 xDSL, 1 FE, 4 switch ports, 1 USB 2.0 port, 1 Console/Aux port, 1 embedded PCIe 3G modem
                        ,c5915(908)                              -- Chassis Type for 5915 Embedded Services Router
                        ,cn7k-c7006(909)                         -- Nexus7000 6slot elsie n7k chassis N7K-C7006
                        ,c86xvae(910)                            -- Chassis for Cisco 86xVAE series products
                        ,cap802-agn(911)                         -- Cisco AP802 Access Point with dual IEEE 802.11a/g/n radio ports %DNP until Jun 2011, contact vnanduri
                        ,cap802-gn(912)                          -- Cisco AP802 Access Point with single IEEE 802.11g/n radio port %DNP until Jun 2011, contact vnanduri
                        ,c2811ve(913)                            -- Cisco 2811ve router with two integrated fast ethernets and integrated VPN
                        ,c1841ve(914)                            -- Cisco 1841ve data only router with 2 HWIC slots
                        ,c2960c-8tc-s(915)                       -- Catalyst 2960C 8 10/100 FE ports + 2 Gig Dual Media Uplinks fixed configuration Layer 2 Ethernet switch, lanlite only Chassis
                        ,c2960c-8tc-l(916)                       -- Catalyst 2960C 8 10/100 FE ports + 2 Gig Dual Media Uplinks fixed configuration Layer 2 Ethernet switch Chassis
                        ,c2960c-8pc-l(917)                       -- Catalyst 2960C 8 10/100 FE with PoE + 2 Gig Dual Media Uplinks fixed configuration Layer 2 Ethernet switch Chassis
                        ,c2960c-12pc-l(918)                      -- Catalyst 2960C 12 10/100 FE with POE + 2 Gig Dual Media Uplinks fixed configuration Layer 2 Ethernet switch Chassis
                        ,c3560cpd-8pt-s(919)                     -- Catalyst 3560C 8 10/100/1000 with PoE and 2 Gig Copper PoE+ Uplinks fixed configuration Layer 2/Layer 3 Ethernet switch Chassis
                        ,c886vag7-k9(920)                        -- C886G w/ 1 WAN VDSL2/ADSL2+ over ISDN, 4 switch ports, 1 embedded Global 3G HSPA+ modem with GPS and SMS
                        ,c887vag-s-k9(921)                       -- C887G w/ 1 WAN VDSL2/ADSL2+ over POTS, 4 switch ports, 1 embedded Sprint 3G EVDO modem with GPS and SMS
                        ,c887vag7-k9(922)                        -- C887G w/ 1 WAN VDSL2/ADSL2+ over POTS, 4 switch ports, 1 embedded Global 3G HSPA+ modem with GPS and SMS
                        ,c887vamg7-k9(923)                       -- C887G w/ 1 WAN VDSL2/ADSL2+ over POTS (Annex M), 4 switch ports, 1 embedded Global 3G HSPA+ modem with GPS and SMS
                        ,c888eg7-k9(924)                         -- C888EG w/ 1 WAN G.SHDSL (EFM), 4 switch ports, 1 embedded Global 3G HSPA+ modem with GPS and SMS
                        ,c881g-u-k9(925)                         -- C881G w/ 1 WAN FE, 4 switch ports, 1 embedded Global 3G HSPA modem with GPS and SMS
                        ,c881g-s-k9(926)                         -- C881G w/ 1 WAN FE, 4 switch ports, 1 embedded Sprint 3G EVDO Rev A modem with GPS and SMS
                        ,c881g-v-k9(927)                         -- C881G w/ 1 WAN FE, 4 switch ports, 1 embedded Verizon 3G EVDO Rev A modem with GPS and SMS
                        ,c881g-b-k9(928)                         -- C881G w/ 1 WAN FE, 4 switch ports, 1 embedded BSNL 3G EVDO Rev A modem with GPS and SMS
                        ,c881g7-k9(929)                          -- C881G w/ 1 WAN FE, 4 switch ports, 1 embedded Global 3G HSPA+ modem with GPS and SMS
                        ,c881g7-a-k9(930)                        -- C881G w/ 1 WAN FE, 4 switch ports, 1 embedded ATT 3G HSPA+ modem with GPS and SMS
                        ,c881w(933)                              -- C881W Router series with 1 Fast Ethernet WAN, 4 Fast Ethernet LAN with 2 PoE, Wireless LAN, 1 USB 2.0 port, 1 Console/Aux port, 256MB flash memory and 512MB DRAM
                        ,c886va-w(934)                           -- C886VA-W Router series with 1 ADSL2/2+ Annex B, 1 ISDN,  4 Fast Ethernet LAN with 2 PoE, Wireless LAN, 1 USB 2.0 port, 1 Console/Aux port, 256MB flash memory and 512MB DRAM
                        ,c887vam-w(935)                          -- C887VAM-W Router series with 1 ADSL2/2+ Annex M, 4 Fast Ethernet LAN with 2 PoE, Wireless LAN, 1 USB 2.0 port, 1 Console/Aux port, 256MB flash memory and 512MB DRAM
                        ,c887va-w(936)                           -- C887VA-W Router series with 1 VDSL, 4 Fast Ethernet LAN with 2 PoE, Wireless LAN, 1 USB 2.0 port, 1 Console/Aux port, 256MB flash memory and 512MB DRAM
                        ,c819g(937)                              -- C819G Router series with 1 Gigabit Ethernet WAN, 4 Fast Ethernet LAN, 1 3G/LTE WAN, 1 Serial, 1 Console/Aux ports, 256MB flash memory and 512MB DRAM
                        ,c819hg(938)                             -- C819HG Hardened Router series with 1 Gigabit Ethernet WAN, 4 Fast Ethernet LAN, 1 3G/LTE WAN, 1 Serial, 1 Console/Aux ports, 256 MB flash memory, 512MB DRAM
                        ,ciad886va(939)                          -- iad886-v2 with 1 VDSL/ADSL over ISDN, 4 switch ports, 1 USB 1.1 port, 1 Console/Aux port, 1 ISDN and an optional Wireless LAN
                        ,ciad886va-j(940)                        -- iad886j-v2 Annex J with 1 VDSL/ADSL over ISDN, 4 switch ports, 1 USB 1.1 port, 1 Console/Aux port, 1 ISDN and an optional Wireless LAN
                        ,ciad887va(941)                          -- iad887-v2 with 1 VDSL/ADSL over POTS, 4 switch ports, 1 USB 1.1 port, 1 Console/Aux port, 1 ISDN and an optional Wireless LAN
                        ,ciad887va-m(942)                        -- iad887m-v2 AnnexM with 1 VDSL/ADSL over POTS, 4 switch ports, 1 USB 1.1 port, 1 Console/Aux port, 1 ISDN and an optional Wireless LAN
                        ,cecds-v-b(949)                          -- Cisco Media Delivery Engine
                        ,c3560c-12pc-s(953)                      -- Catalyst 3560C 12 10/100 with PoE + 2 Gig Dual Media Uplinks fixed configuration Layer 2/Layer 3 Ethernet switch chassis
                        ,c3560c-8pc-s(954)                       -- Catalyst 3560C 8 10/100 with PoE + 2 Gig Dual Media Uplinks fixed configuration Layer 2/Layer 3 Ethernet switch chassis
                        ,craie1783bms20cgpk(960)                 -- Rockwell Conformal coating Industrial Ethernet 2000 Switch, 16 10/100 T + 2 100 T + 2 1000 T/SFP
                        ,craie1783bms20cg(961)                   -- Rockwell Industrial Ethernet 2000 Switch, 16 10/100 T + 2 100 T + 2 1000 T/SFP
                        ,craie1783bms20c(962)                    -- Rockwell Industrial Ethernet 2000 Switch, 16 10/100 T + 2 100 T + 2 100 T/SFP
                        ,craie1783bms10cg(963)                   -- Rockwell Industrial Ethernet 2000 Switch, 8 10/100 T + 2 1000 T/SFP
                        ,craie1783bms10c(964)                    -- Rockwell Industrial Ethernet 2000 Switch, 8 10/100 T + 2 100 T/SFP
                        ,craie1783bms06tg(965)                   -- Rockwell Industrial Ethernet 2000 Switch, 4 10/100 T + 2 1000 T
                        ,craie1783bms06sg(966)                   -- Rockwell Industrial Ethernet 2000 Switch, 4 10/100 T + 2 1000 SFP
                        ,craie1783bms06t(967)                    -- Rockwell Industrial Ethernet 2000 Switch, 4 10/100 T + 2 100 T
                        ,craie1783bms06s(968)                    -- Rockwell Industrial Ethernet 2000 Switch, 4 10/100 T + 2 100 SFP
                        ,cie200016tcgx(969)                      -- Cisco Conformal coating Industrial Ethernet 2000 Switch, 16 10/100 T + 2 100 T + 2 1000 T/SFP
                        ,cie200016tcg(970)                       -- Cisco Industrial Ethernet 2000 Switch, 16 10/100 T + 2 100 T + 2 1000 T/SFP
                        ,cie200016tc(971)                        -- Cisco Industrial Ethernet 2000 Switch, 16 10/100 T + 2 100 T + 2 100 T/SFP
                        ,cie20008tcg(972)                        -- Cisco Industrial Ethernet 2000 Switch, 8 10/100 T + 2 1000 T/SFP
                        ,cie20008tc(973)                         -- Cisco Industrial Ethernet 2000 Switch, 8 10/100 T + 2 100 T/SFP
                        ,cie20004tg(974)                         -- Cisco Industrial Ethernet 2000 Switch, 4 10/100 T + 2 1000 T
                        ,cie20004tsg(975)                        -- Cisco Industrial Ethernet 2000 Switch, 4 10/100 T + 2 1000 SFP
                        ,cie20004t(976)                          -- Cisco Industrial Ethernet 2000 Switch, 4 10/100 T + 2 100 T
                        ,cie20004ts(977)                         -- Cisco Industrial Ethernet 2000 Switch, 4 10/100 T + 2 100 SFP


                        ,casr901(987)                            -- Pura-C platform
                        ,casr901e(988)                           -- Pura-E platform
                        ,cecds50ivb(990)                         -- Cisco Enterprise Content Delivery System Model MDE50IVB
                        ,casr1002x(993)                         -- Cisco Aggregation Services Router 1000 Series, ASR1002-X Chassis
                        ,ccsr1000v(995)                          -- Cisco Cloud Services Router 1000v Chassis
                        ,casr9001(997)                           -- Cisco Aggregation Services Router (ASR) 9001 Chassis
                        ,c881gw(998)                             -- C881GW series router with 1 Fast Ethernet WAN, 4 Fast Ethernet LAN with 2 PoE, 3G, Wireless LAN, 1 USB 2.0   port, 1 Console/Aux port, 256MB flash memory and 512MB DRAM
                        ,c887vagw(999)                           -- C887VAGW series router with 1 WAN VDSL2/ADSL2+ over POTS, 4 Fast Ethernet LAN with 2 PoE, Wireless LAN, 3G, 1 USB   2.0 port, 1 Console/Aux port, 256MB flash memory and 512MB DRAM
                        ,c887vawd(1000)                          -- C887VA-WD series router with 1 WAN VDSL2/ADSL2+ over POTS, 4 Fast Ethernet LAN with 2 PoE, Wireless LAN, 1 USB 2.0 port, 1 Console/Aux port, 256MB flash memory and 512MB DRAM
                        ,c881wd(1001)                            -- C881WD series router with 1 Fast Ethernet WAN, 4 Fast Ethernet LAN with 2 PoE, Wireless LAN, 1 USB 2.0 port, 1 Console/Aux port, 256MB flash memory and 512MB DRAM
                        ,c819hgw(1002)                           -- C819HGW Hardened Router series with 1 Gigabit Ethernet WAN, 4 Fast Ethernet LAN, 1 3G WAN, Wireless LAN, 1 Serial, 1 Console/Aux ports, 1GB flash memory, 1GB DRAM
                        ,c819h(1003)                             -- C819H Hardened Router series with 1 Gigabit Ethernet WAN, 4 Fast Ethernet LAN, 1 Serial, 1 Console/Aux ports, 1GB flash memory, 1GB DRAM
                        ,c819hwd(1004)                           -- C819HWD Hardened Router series with 1 Gigabit Ethernet WAN, 4 Fast Ethernet LAN, 1 3G WAN, 1 Serial, 1 Console/Aux ports, 1GB flash memory, 1GB DRAM
                        ,c812g(1005)                             -- C812G Router series with 1 Gigabit Ethernet WAN, 1 3G WAN, 1 Console/Aux ports, 512MB flash memory, 512MB DRAM
                        ,c812gcifi(1006)                         -- C812GCIFI Router series with 1 Gigabit Ethernet WAN, 1 3G WAN, Wireless LAN, 1 Console/Aux ports, 512MB flash memory, 512MB DRAM
                        ,c819gm(1007)                            -- C819GM Router series with 1 Gigabit Ethernet WAN, 4 Fast Ethernet LAN, 1 3G WAN, 1 Serial, 1 Console/Aux ports, 1GB flash memory and 1GB DRAM
                        ,c819hgm(1008)                           -- C819HGM Hardened Router series with 1 Gigabit Ethernet WAN, 4 Fast Ethernet LAN, 1 3G WAN, 1 Serial, 1 Console/Aux ports, 1GB flash memory, 1GB DRAM
                        ,cisr4400(1009)                         -- Cisco ISR 4400 Series Router Chassis
                        ,ca901-4c-f-d(1010)                      -- A new Chassis PID for Ethernet only chassis (with Port based feature)
                        ,ca901-4c-ft-d(1011)                     -- A new Chassis PID  for Ethernet + TDM chassis( with Port based Feature)
                        ,cmde10xvb(1012)                         -- Cisco Enterprise Content Delivery System Model MDE10XVB
                        ,cap802h-agn(1023)                       -- Cisco AP802 Hardened Access Point with dual IEEE 802.11a/g/n radio ports for M2M environments %DNP until August 2012, contact vnanduri
                        ,cairap802-agn(1024)                     -- Cisco AP802 Smart Access Point with dual IEEE 802.11a/g/n radio ports %DNP until August 2012, contact vnanduri
                        ,casr1002xc(1032)                        -- Cisco Aggregation Services Router 1000 Series, ASR1002-XC Chassis
                        ,c86xvaew(1033)                          -- Chassis for Cisco 86xVAEW series products
                        ,cairap1553(1034)                        -- Cisco Aironet 1550 Series Outdoor Mesh Access Points with three IEEE 802.11n radio port
                        ,cairap1552(1035)                        -- Cisco Aironet 1550 Series Outdoor Mesh Access Points with dual IEEE 802.11n radio port
                        ,cairap1602(1036)                        -- Cisco Aironet 1600 Series WLAN Access Point with dual IEEE 802.11n radio port
                        ,cairap1601(1037)                        -- Cisco Aironet 1600 Series WLAN Access Point with single IEEE 802.11n radio port
                        ,cairap2602(1038)                        -- Cisco Aironet 2600 Series WLAN Access Point with dualIEEE 802.11n radio port
                        ,cairap2601(1039)                        -- Cisco Aironet 2600 Series WLAN Access Point with singleIEEE 802.11n radio port
                        ,cairap3602(1040)                        -- Cisco Aironet 3600 Series WLAN Access Point with one10/100/1000TX port and dual IEEE 802.11n radio port
                        ,cairap3601(1041)                        -- Cisco Aironet 3600 Series WLAN Access Point with one10/100/1000TX port and single IEEE 802.11n radio port
                        ,cws-c2960x-24psq-l(1052)                -- Catalyst 2960X 24 Gig Downlinks, 2 Copper, 2 SFP uplink NonStakable
                        ,cie200016tcgp(1057)                     -- Cisco Base + Lite Industrial Ethernet 2000 Switch, 12 10/100 T + 2 1000 T/SFP + 4 POE
                        ,cie200016tcgep(1058)                    -- Cisco Base + 1588 Industrial Ethernet 2000 Switch, 12 10/100 T + 2 1000 T/SFP + 4 POE
                        ,cie200016tcgnxp(1059)                   -- Cisco Base + NAT + 1588 + Conformal Coating Industrial Ethernet 2000 Switch, 12 10/100 T + 2 1000 T/SFP + 4 POE
                        ,cws-c3750x-48u(1060)                    -- Catalyst 3750X 48 10/100/1000 UPoE Ports + 4 SFP Ports + 2 SFP+ Ports Layer 2/Layer 3 Ethernet Stackable Switch
                        ,cws-c3750x-24u(1061)                    -- Catalyst 3750X 24 10/100/1000 UPoE Ports + 4 SFP Ports + 2 SFP+ Ports Layer 2/Layer 3 Ethernet Stackable Switch
                        ,cws-c3560x-48u(1062)                    -- Catalyst 3560X 48 10/100/1000 UPoE Ports + 4 SFP Ports + 2 SFP+ Ports Layer 2/Layer 3 Ethernet Switch
                        ,cws-c3560x-24u(1063)                    -- Catalyst 3560X 24 10/100/1000 UPoE Ports + 4 SFP Ports + 2 SFP+ Ports Layer 2/Layer 3 Ethernet Switch
                        ,craie1783bms12t4e2cgl(1064)              -- Rockwell IA Base + Lite Industrial Ethernet 2000 Switch, 12 10/100 T + 2 1000 T/SFP + 4 POE, contact dsheshad
                        ,craie1783bms12t4e2cgp(1065)             -- Rockwell IA Base + 1588 Industrial Ethernet 2000 Switch, 12 10/100 T + 2 1000 T/SFP + 4 POE, contact dsheshad
                        ,craie1783bms12t4e2cgnk(1066)            -- Rockwell IA Base + NAT + 1588 + Conformal Coating  Industrial Ethernet 2000 Switch, 12 10/100 T + 2 1000 T/SFP + 4 POE, contact dsheshad
			 ,cie20008tcgn(1067)                     -- Cisco Industrial Ethernet 2000 Switch+1588+NAT, 8 10/100 T + 2 1000 T/SFP, contact prashrof
                        ,cie200016tcgn(1068)                     -- Cisco Industrial Ethernet 2000 Switch+1588+NAT, 16 10/100 T + 2 100 T + 2 1000 T/SFP, contact prashrof
                        ,craie1783bms10cgn(1069)                 -- Rockwell Industrial Ethernet 2000 Switch+1588+NAT, 8 10/100 T + 2 1000 T/SFP, contact prashrof
                        ,craie1783bms20cgn(1070)                 -- Rockwell Industrial Ethernet 2000 Switch+1588+NAT, 16 10/100 T + 2 1000 T/SFP, contact prashrof
                        ,cvg202xm(1071)                          -- Line side Analog Gateway VG202XM with 2FXS Analog ports
                        ,cvg204xm(1072)                          -- Line side Analog Gateway VG204XM with 4FXS Analog ports
                        ,casr1001x(1087)			 -- Cisco Aggregation Services Router 1000 Series, ASR1001-X Chassis
                        ,cc881(1088)				 -- C881 router with 1 Fast Ethernet Primary WAN, 4 Fast Ethernet LAN, 2 PoE Optional, 1 USB 2.0 port, 1 Console/Aux port, 256MB flash memory and 1GB DRAM
                        ,cc886va(1089)				 -- C886VA router with 1 VDSL2/ADSL2+ Primary WAN, 1 ISDN BRI S/T interface, 4 Fast Ethernet LAN, 2 PoE Optional, 1 USB 2.0 port, 1 Console/Aux port, 256MB flash memory and 1GB DRAM
                        ,cc887va(1090)				 -- C887VA router with 1 VDSL2/ADSL2+ Primary WAN, 4 Fast Ethernet LAN, 2 PoE Optional, 1 USB 2.0 port, 1 Console/Aux port, 256MB flash memory and 1GB DRAM
                        ,cc888(1091)				 -- C888 router with 1 EFM/ATM over G.SHDSL Primary WAN, 1 ISDN BRI S/T interface, 4 Fast Ethernet LAN, 2 PoE Optional, 1 USB 2.0 port, 1 Console/Aux port, 256MB flash memory and 1GB DRAM
                        ,cc891f(1092)				 -- C891F router with 1 Giga Ethernet Primary WAN, 1 SFP (Small Form-factor Pluggable) Giga Ethernet Primary WAN, 1 Fast Ethernet WAN, 1 V.92, 1 ISDN BRI S/T interface, 8 Giga Ethernet LAN, 4 PoE Optional, 1 USB 2.0 port, 1 Console/Aux port, 256MB flash memory and 1GB DRAM
                        ,cc891fw(1093)				 -- C891FW router with 1 Giga Ethernet Primary WAN, 1 SFP (Small Form-factor Pluggable) Giga Ethernet Primary WAN, 1 Fast Ethernet WAN, 1 V.92, 1 ISDN BRI S/T interface, 1 Dual 2.4/5GHz Wireless LAN, 8 Giga Ethernet LAN, 4 PoE Optional, 1 USB 2.0 port, 1 Console/Aux port, 256MB flash memory and 1GB DRAM
                        ,cairap3702(1094)                        -- Cisco Aironet 3700 Series (IEEE 802.11ac) Access Point
                        ,cairap702(1095)                         -- Cisco Aironet 702 Series (IEEE 802.11n) Access Point
                        ,cairap1532(1096)                        -- Cisco Aironet 1530 Series (IEEE 802.11n) Access point
                        ,cvg310(1130)                            -- VG310 voice gateway ports
                        ,cvg320(1131)                            -- VG320 voice gateway ports
                        ,citprt1081k9(1147)                      -- Router 1081 Fast Ethernet Router
                        ,citprt1091-fk9(1148)                    -- Router 1091 GigaE SecRouter
                        ,citprt2241k9(1149)                      -- Router 2241 w/2 GE,2 EHWIC slots,256MB CF,512MB DRAM,IP Base
                        ,citprt2221k9(1150)                      -- Router 2221 Modular Router, 2 GE, 2 EHWIC slots, 512DRAM, IP Base
                        ,citprt2241wck9(1151)                    -- Router 2241 Router w/802.11 a/b/g/n China Compliant WLAN ISM
                        ,citprt3211k9(1152)                      -- Router 3211 w/3 GE,4 EHWIC,2 DSP,1 SM,256MB CF,512MB DRAM,IPB
                        ,citprt3221k9(1153)                      -- Router 3221 w/3 GE,4 EHWIC,3 DSP,1 SM,256MB CF,512MB DRAM,IPB
                        ,citprt3201k9(1154)                      -- Router 3201 w/2 GE,4 EHWIC,2 DSP,256MB CF,512MB DRAM,IP Base
                        ,c899gw4g(1155)                          -- Chassis for Cisco 899GW4G series products
                        ,c896vagw4g(1156)                        -- Chassis for Cisco 896VAGW4G series products
                        ,c897vagw4g(1157)                        -- Chassis for Cisco 897VAGW4G series products
                        ,c898eagw4g(1158)                        -- Chassis for Cisco 898EAGW4G series products
                        ,c819gw4g(1159)                          -- Chassis for Cisco 819GW4G series products
                        ,c897vab(1160)                           -- C897VAB-K9 router with 1 VDSL2 with bonding/ADSL2+ WAN , 1 Giga Ethernet WAN, 1 SFP (Small Form-factor Pluggable) Giga Ethernet Primary WAN, 8 Giga Ethernet LAN,4 PoE Optional, 1 USB 2.0 port, 1 Console/Aux port, 256MB flash memory and 1GB DRAM
                        ,cairap1702(1161)                        -- Cisco Aironet 1700 Series (IEEE 802.11ac) Access Point
                        ,cws-c3560cx-8pt-s(1162)                 -- Smirnoff catalyst 3560CX 8x GE downlink ,PoE+,2x 1G copper UPOE uplinks.
                        ,cws-C3560cx-12pd-s(1163)                -- Smirnoff catalyst 3560CX 12x GE downlink, PoE+, 2x CU + 2x 10G SFP+ uplinks
                        ,cws-C3560cx-12tc-s(1164)                -- Smirnoff catalyst 3560CX 12x GE downlink, 2x Copper + 2x SFP uplinks
                        ,cws-C3560cx-12pc-s(1165)                -- Smirnoff catalyst 3560CX 12x GE downlink, PoE+, 2x copper + 2x SFP uplink
                        ,cws-C3560cx-8tc-s(1166)                 -- Smirnoff Catalyst 3560CX 8x GE downlink, 2x Copper + 2x SFP uplink
                        ,cws-C3560cx-8pc-s(1167)                 -- Smirnoff Catalyst 3560CX 8x GE downlink, PoE+, 2x Copper + 2x SFP uplink
                        ,cws-C2960cx-8tc-l(1168)                 -- Smirnoff catalyst 2960CX 8 Gig Downlinks, 2 Copper, 2 SFP uplink
                        ,cws-c3560cx-8xpd-s(1169)                -- Smirnoff catalyst 3560CX 2x mGig + 6x GE  downlink ,PoE+, 2x SFP+ uplinks.
                        ,c2911-t(1170)                           -- CISCO2911-T/K9 with 3 GE, 4 EHWIC, 2 DSP, 1 SM , 256 MB CF, 512 MB DRAM, IPB, extended temperature range from -5 to 60 C
                        ,cairap1572(1172)                        -- Cisco Aironet 1570 (IEEE 802.11ac) Series Outdoor Access Points with two radio's
                        ,cairap702w(1173)                        -- Cisco Aironet 702w (IEEE 802.11n) Series Access Points
                        ,c891-24x(1174)                          -- C891-24X Router series with 2 Giga Ethernet WAN Xor'ed with SFP (Small Form-factor Pluggable), 24 Giga Ethernet LAN with 8 PoE, 1 USB 2.0 port, 1 Console/Aux port, 256MB flash memory and 512MB/1GB DRAM
                        ,c841m-4x(1178)                          -- Cisco C841M-4X/K9 router
                        ,c841m-8x(1179)                          -- Cisco C841M-8X/K9 router
                        ,c819GWLTE(1180)                         -- cisco819GWLTE router with 1 4G LTE interface, 4 Fast Ethernet LAN interfaces, 1GE WAN, 1 Serial(sync/async) interface, 2 terminal lines, 1 Virtual Private Network (VPN) Module, 1 cisco Embedded AP, 1 Console/Aux port, and 1GB FLASH
                        ,c1783sr(1181)                           -- S5900 Hardened Router series with 1 Gigabit Ethernet WAN, 4 Fast Ethernet LAN, 1 Serial, 1 Console/Aux ports, 1GB flash memory, 1GB DRAM
                        ,cws-c2960l-24ts-ll(1182)                -- Catalyst 2960L 24 x GE downlink, 4 x GE (4 SFP) uplinks
                        ,cws-c2960l-24ps-ll(1183)                -- Catalyst 2960L 24 x GE downlink, POE support, 4 x GE (4 SFP) uplinks
                        ,cws-c2960l-48ts-ll(1184)                -- Catalyst 2960L 48 x GE downlink, 4 x GE (4 SFP) uplinks
                        ,cws-c2960l-48ps-ll(1185)                -- Catalyst 2960L 48 x GE downlink, POE support, 4 x GE (4 SFP) uplinks
                        ,cws-c2960l-16ts-ll(1186)                -- Catalyst 2960L 16 x GE downlink, 2 x GE (2 SFP) uplinks
                        ,cws-c2960l-16ps-ll(1187)                -- Catalyst 2960L 16 x GE downlink, POE support, 2 x GE (2SFP) uplinks
                        ,cws-c2960l-8ts-ll(1188)                 -- Catalyst 2960L 8 x GE downlink, 2 x GE (2 SFP) uplinks
                        ,cws-c2960l-8ps-ll(1189)                 -- Catalyst 2960L 8 x GE downlink, POE support, 2 x GE (2SFP) uplinks
                        ,c86xvaev2(1190)                         -- Chassis for C86xVAE series products
                        ,cdb-8u(1191)                            -- Catalyst Digital Building 8 Port UPoE
                        ,cdb-8p(1192)                            -- Catalyst Digital Building 8 Port PoE+
                        ,c2911a(1193)                            -- Cisco 2911a (3 GE, 4 EHWIC, 1 SM, 2 DSP)
                        ,cws-c2960l-24tq-ll(1194)                -- Catalyst 2960L 24 x GE downlink, 4 x 10GE (4 SFP+) uplinks
                        ,cws-c2960l-48tq-ll(1195)                -- Catalyst 2960L 48 x GE downlink, 4 x 10GE (4 SFP+) uplinks
                        ,cws-c2960l-24pq-ll(1196)                -- Catalyst 2960L 24 x GE downlink, 4 x 10GE (4 SFP+) uplinks, POE support
                        ,cws-c2960l-48pq-ll(1197)                -- Catalyst 2960L 48 x GE downlink, 4 x 10GE (4 SFP+) uplinks, POE support
                        ,ir807GLTE(1198)                         -- Cisco IR807 series router with 1 4G LTE interface, 2 Fast Ethernet WAN interfaces, 2 Serial(sync/async) interface, 5 terminal lines, 1 Console port, and 4GB FLASH
                        ,c941j-4p(1199)                          -- C941J-4P Router with 4 GE LAN interface, 2GE WAN interface, 1 USB 3.0, 2GB DDR4 DRAM(x64) with ECC, 2GB   eMMC pSLC, Dual 16MB NOR Bootflash
                        ,c921-4p(1200)                           -- C921-4P Router with 4 GE LAN interface, 2GE WAN interface, 1 USB 3.0, 1GB DDR4 DRAM(x32) with ECC, 2GB    eMMC pSLC, Dual 16MB NOR Boot flash
                        ,c931-4p(1201)                           -- C931-4P Router with Internal Power supply, 4 GE LAN interface, 2GE WAN interface, 1 USB 3.0, 1GB DDR4 DRAM(x32) with ECC, 2GB   eMMC pSLC, Dual 16MB NOR Boot flash
                        ,c941j-4plte-jn(1202)                    -- C941J-4PLTEJN Router with 1 4G LTE interface, 4 GE LAN interface, 2GE WAN interface, 1 USB 3.0, 2GB DDR4  DRAM(x32) with ECC, 2GB eMMC pSLC, Dual 16MB NOR Boot flash
                        ,c921-4plte(1203)                        -- C921-4PLTE Router with 1 4G LTE interface, 4 GE LAN interface, 2GE WAN interface, 1 USB 3.0, 1GB DDR4     DRAM (x32) with ECC, 2GB eMMC pSLC, Dual 16MB NOR Bootflash
                        ,c921j-4p(1204)                          -- C921J-4P Router with, 4 GE LAN interface, 2GE WAN interface, 1 USB 3.0, 1GB DDR4 DRAM(x32) with ECC, 2GB  eMMC pSLC, Dual 16MB NOR Boot flash
                        ,c927-4p(1205)                           -- C927-4P Router with, 1 Eth+DSL,4 GE LAN interface, 1GE WAN interface, 1 USB 3.0, 1GB DDR4 DRAM(x32) with  ECC, 2GB eMMC pSLC, Dual 16MB NOR Bootflash
                        ,c927-4pm(1206)                          -- C927-4PM Router with, 1 Eth+DSL,4 GE LAN interface, 1GE WAN interface, 1 USB 3.0, 1GB DDR4 DRAM(x32) with ECC, 2GB eMMC pSLC, Dual 16MB NOR Bootflash
                        ,c926-4p(1207)                           -- C926-4P Router with, 1 Eth+DSL,4 GE LAN interface, 1GE WAN interface, 1 USB 3.0, 1GB DDR4 DRAM(x32) with  ECC, 2GB eMMC pSLC, Dual 16MB NOR Bootflash
                        ,c927-4plte(1208)                        -- C927-4PLTE Router with, 1 LTE interface ,1 Eth+DSL,4 GE LAN interface, 1GE WAN interface, 1 USB 3.0, 1GB   DDR4 DRAM(x32) with ECC, 2GB eMMC pSLC, Dual 16MB NOR Boot flash
                        ,c927-4pmltegb(1209)                     -- C927-4PMLTEGB  Router with 1 Eth+DSL with Annex M, 1 LTE interface,4 GE LAN interface, 1GE WAN interface, 1 USB 3.0, 1GB DDR4 DRAM(x32) with ECC, 2GB eMMC pSLC, Dual 16MB NOR Bootflash
                        ,c926-4pltegb(1210)                      -- C926-4PLTEGB Router with 1 Eth+DSL, 1 LTE interface,4 GE LAN interface, 1GE WAN interface, 1 USB 3.0, 1GB DDR4 DRAM(x32) with ECC, 2GB eMMC pSLC, Dual 16MB NOR Bootflash
                        ,c931j-4p(1214)                          -- C931J-4P Router with External Power Supply 4 GE LAN interface, 2GE WAN interface, 1 USB 3.0, 1GB DDR4 DRAM(x32) with ECC, 2GB eMMC pSLC, Dual 16MB NOR Boot flash
                        ,cws-c2960l-sm-24ts(1215)                -- Catalyst 2960L-SM 24 x GE downlink, 4 x GE (4 SFP) uplinks
                        ,cws-c2960l-sm-24ps(1216)                --  Catalyst 2960L-SM 24 x GE downlink, POE support, 4 x GE (4 SFP) uplinks
                        ,cws-c2960l-sm-48ts(1217)                -- Catalyst 2960L-SM 48 x GE downlink, 4 x GE (4 SFP) uplinks
                        ,cws-c2960l-sm-48ps(1218)                -- Catalyst 2960L-SM 48 x GE downlink, POE support, 4 x GE (4 SFP) uplinks
                        ,cws-c2960l-sm-16ts(1219)                -- Catalyst 2960L-SM 16 x GE downlink, 2 x GE (2 SFP) uplinks
                        ,cws-c2960l-sm-16ps(1220)                --  Catalyst 2960L-SM 16 x GE downlink, POE support, 2 x GE (2SFP) uplinks
                        ,cws-c2960l-sm-8ts(1221)                 --  Catalyst 2960L-SM 8 x GE downlink, 2 x GE (2 SFP) uplinks
                        ,cws-c2960l-sm-8ps(1222)                 -- Catalyst 2960L-SM 8 x GE downlink, POE support, 2 x GE (2SFP) uplinks
                        ,cws-c2960l-sm-24tq(1223)                -- Catalyst 2960L-SM 24 x GE downlink, 4 x 10GE (4 SFP+) uplinks
                        ,cws-c2960l-sm-48tq(1224)                --  Catalyst 2960L-SM 48 x GE downlink, 4 x 10GE (4 SFP+) uplinks
                        ,cws-c2960l-sm-24pq(1225)                -- Catalyst 2960L-SM 24 x GE downlink, 4 x 10GE (4 SFP+) uplinks, POE support
                        ,cws-c2960l-sm-48pq(1226)                -- Catalyst 2960L-SM 48 x GE downlink, 4 x 10GE (4 SFP+) uplinks, POE support
                        ,dn-apl-tta-1x(1230)             -- Cisco DNA Traffic Telemetry Appliance - Model 1X
                       ,cws-c1000-24fet-4g-l(1231)           -- Catalyst 1000, 24x 1FE downlinks + 2x 1G uplink (Combo) + 2x 1G uplink (SFP)
                       ,cws-c1000-24fep-4g-l(1232)           -- Catalyst 1000, 24x 1FE downlinks + 2x 1G uplink (Combo) + 2x 1G uplink (SFP) + Partial PoE
                       ,cws-c1000-48fet-4g-l(1233)           -- Catalyst 1000, 48x 1FE downlinks + 2x 1G uplink (Combo) + 2x 1G uplink (SFP)
                       ,cws-c1000-48fep-4g-l(1234)            -- Catalyst 1000, 48x 1FE downlinks + 2x 1G uplink (Combo) + 2x 1G uplink (SFP) + Partial PoE
                   }
                   ACCESS  read-only
                   STATUS  deprecated
                   DESCRIPTION
                           "Chassis type."
                   ::= { chassis 1 }

               chassisVersion OBJECT-TYPE
                   SYNTAX  DisplayString
                   ACCESS  read-only
                   STATUS  deprecated
                   DESCRIPTION
                           "Chassis hardware revision level, or an empty
                           string if unavailable."
                   ::= { chassis 2 }

               chassisId OBJECT-TYPE
                   SYNTAX  DisplayString
                   ACCESS  read-write
                   STATUS  deprecated
                   DESCRIPTION
                           "Unique ID string. Defaults to chassis serial
                           number if available, otherwise empty. Can
                           also be set with 'snmp-server chassis-id'."
                   ::= { chassis 3 }

               romVersion OBJECT-TYPE
                   SYNTAX  DisplayString
                   ACCESS  read-only
                   STATUS  deprecated
                   DESCRIPTION
                           "ROM monitor version."
                   ::= { chassis 4 }

               romSysVersion OBJECT-TYPE
                   SYNTAX  DisplayString
                   ACCESS  read-only
                   STATUS  deprecated
                   DESCRIPTION
                           "ROM system software version, or an empty
                           string if unavailable."
                   ::= { chassis 5 }

               processorRam OBJECT-TYPE
                   SYNTAX  INTEGER
                   ACCESS  read-only
                   STATUS  deprecated
                   DESCRIPTION
                           "Bytes of RAM available to CPU."
                   ::= { chassis 6 }

               nvRAMSize OBJECT-TYPE
                   SYNTAX  INTEGER
                   ACCESS  read-only
                   STATUS  deprecated
                   DESCRIPTION
                           "Bytes of non-volatile configuration memory."
                   ::= { chassis 7 }

               nvRAMUsed OBJECT-TYPE
                   SYNTAX  INTEGER
                   ACCESS  read-only
                   STATUS  deprecated
                   DESCRIPTION
                           "Bytes of non-volatile configuration memory
                           in use."
                   ::= { chassis 8 }

               configRegister OBJECT-TYPE
                   SYNTAX  INTEGER
                   ACCESS  read-only
                   STATUS  deprecated
                   DESCRIPTION
                           "Value of configuration register."
                   ::= { chassis 9 }

               configRegNext OBJECT-TYPE
                   SYNTAX  INTEGER
                   ACCESS  read-only
                   STATUS  deprecated
                   DESCRIPTION
                           "Value of configuration register at next
                           reload."
                   ::= { chassis 10 }

               cardTable OBJECT-TYPE
                   SYNTAX  SEQUENCE OF CardTableEntry
                   ACCESS  not-accessible
                   STATUS  deprecated
                   DESCRIPTION
                            "Chassis card table."
                   ::= { chassis 11 }

               cardTableEntry OBJECT-TYPE
                   SYNTAX CardTableEntry
                   ACCESS  not-accessible
                   STATUS  deprecated
                   DESCRIPTION
                            "Chassis card table."
                   INDEX { cardIndex }
               ::= { cardTable 1 }

               CardTableEntry ::=
                   SEQUENCE {
                       cardIndex
                           INTEGER,
                       cardType
                           INTEGER,
                       cardDescr
                           DisplayString,
                       cardSerial
                           INTEGER,
                       cardHwVersion
                           DisplayString,
                       cardSwVersion
                           DisplayString,
                       cardSlotNumber
                           INTEGER,
                       cardContainedByIndex
                           INTEGER,
                       cardOperStatus
                           INTEGER,
                       cardSlots
                           INTEGER
                   }


          -- The following section describes the components of the
          -- table.

               cardIndex OBJECT-TYPE
                   SYNTAX  INTEGER
                   ACCESS  read-only
                   STATUS  deprecated
                   DESCRIPTION
                           "Index into cardTable (not physical chassis
                           slot number)."
                   ::= { cardTableEntry 1 }


-- The expansions for some acronyms used for cardType enumerations are:
--	CSU : Channel Service Unit
--	DSU : Dial Service Unit
--	FT1 : Fractional T1
--	WIC : Wan Interface Card
--	DTR : Dedicated Token Ring
--	PM  : Port Module
--	PA  : Port Adapter

               cardType OBJECT-TYPE
                   SYNTAX  INTEGER {
			unknown(1)
			,csc1(2)
			,csc2(3)
			,csc3(4)
			,csc4(5)
			,rp(6)
			,cpu-igs(7)
			,cpu-2500(8)
			,cpu-3000(9)
			,cpu-3100(10)
			,cpu-accessPro(11)
			,cpu-4000(12)
			,cpu-4000m(13)
			,cpu-4500(14)
			,rsp1(15)
			,rsp2(16)
			,cpu-4500m(17)
			,cpu-1003(18)
			,cpu-4700(19)
			,csc-m(20)
			,csc-mt(21)
			,csc-mc(22)
			,csc-mcplus(23)
			,csc-envm(24)
			,chassisInterface(25)
			,cpu-4700S(26)
			,cpu-7200-npe100(27)
			,rsp7000(28)
			,chassisInterface7000(29)
			,rsp4(30)
			,cpu-3600(31)
			,cpu-as5200(32)
			,c7200-io1fe(33)
			,cpu-4700m(34)
			,cpu-1600(35)
			,c7200-io(36)
			,cpu-1503(37)
			,cpu-1502(38)
			,cpu-as5300(39)
			,csc-16(40)
			,csc-p(41)
			,csc-a(50)
			,csc-e1(51)
			,csc-e2(52)
			,csc-y(53)
			,csc-s(54)
			,csc-t(55)
			,csc-r(80)
			,csc-r16(81)
			,csc-r16m(82)
			,csc-1r(83)
			,csc-2r(84)
			,sci4s(56)
			,sci2s2t(57)
			,sci4t(58)
			,mci1t(59)
			,mci2t(60)
			,mci1s(61)
			,mci1s1t(62)
			,mci2s(63)
			,mci1e(64)
			,mci1e1t(65)
			,mci1e2t(66)
			,mci1e1s(67)
			,mci1e1s1t(68)
			,mci1e2s(69)
			,mci2e(70)
			,mci2e1t(71)
			,mci2e2t(72)
			,mci2e1s(73)
			,mci2e1s1t(74)
			,mci2e2s(75)
			,csc-cctl1(100)
			,csc-cctl2(101)
			,csc-mec2(110)
			,csc-mec4(111)
			,csc-mec6(112)
			,csc-fci(113)
			,csc-fcit(114)
			,csc-hsci(115)
			,csc-ctr(116)
			,cpu-7200-npe150(121)
			,cpu-7200-npe200(122)
			,cpu-wsx5302(123)
			,gsr-rp(124)
			,cpu-3810(126)
			,cpu-2600(127)
			,cpu-rpm(128)
			,cpu-ubr904(129)		-- CPU card for Cisco Cable Modem (ubr - universal broadband router)
			,cpu-6200-mpc(130)		-- Maintenance processor card for c6200
			,cpu-1700(131)			-- CPU for Cisco 1700 series
			,cpu-7200-npe300(132)		-- Network processing engine (CPU card) for 7200 series
			,cpu-1400(133)			-- CPU for Cisco 1400 series
			,cpu-800(134)			-- CPU for Cisco 800 series products
			,cpu-psm-1gbps(135)		-- Processor Switch Module 1 with 1.2Gbps switching capacity for MGX 8800 series chassis
			,cpu-7200-npe175(137)		-- Network processing engine (CPU card) for 7200 series
			,cpu-7200-npe225(138)		-- Network processing engine (CPU card) for 7200 series
			,cpu-1417(140)			-- CPU for Cisco 1417 only
			,cpu-psm1-1oc12(141)		-- Cisco MGX8800 Processor Switch Module 1 with 1 622Mbps port
			,cpu-optical-regenerator(142)	-- CPU for the Cisco Optical Regenerator chassis
			,cpu-ubr924(143)		-- CPU for the UBR924 Cisco Cable Modem
			,cpu-7120(144)			-- CPU for the Cisco 7120 series
			,cpu-7140(145)			-- CPU for the Cisco 7140 series
			,cpu-psm1-2t3e3(146)		-- Cisco MGX8800 Processor Switch Module 1 with 2 T3/E3 ports
			,cpu-psm1-4oc3(147)		-- Cisco MGX8800 Processor Switch Module 1 with 4 155Mbps ports
			,cpu-ubr91x(149)		-- CPU card for the UBR91X family of Cable Modems (912-c, 912-s, 914)
			,sp(150)
			,eip(151)
			,fip(152)
			,hip(153)
			,sip(154)
			,trip(155)
			,fsip(156)
			,aip(157)
			,mip(158)
			,ssp(159)
			,cip(160)
			,srs-fip(161)
			,srs-trip(162)
			,feip(163)
			,vip(164)
			,vip2(165)
			,ssip(166)
			,smip(167)
			,posip(168)
			,feip-tx(169)
			,feip-fx(170)
			,cbrt1(178)
			,cbr120e1(179)
			,cbr75e(180)
			,vip2-50(181)
			,feip2(182)
			,acip(183)
			,mc11(184)			-- cable card 1 downstream 1 upstream
			,mc12a(185)			-- cable card 1 downstream 2 upstream
			,io1fe-tx-isl(186)		-- Fast Ethernet I/O Controller which provides RJ45 and MII Connectors
			,geip(187)			-- Gigabit Ethernet Interface Processor
			,vip4(188)			-- 4th Generation Versatile Interface Processor for the c7500 router
			,mc14a(189)			-- cable card 1 downstream 4 upstream
			,mc16a(190)			-- cable card 1 downstream 6 upstream
			,mc11a(191)			-- modem card 1 downstream 1 upstream (ASIC)
			,cip2(192)			-- channel interface processor 2 for the 7500 router family.  supports IBM ESCON and IBM Parallel (Bus & Tag) interface types.
			,mc28(194)			-- cable card 2 downstream 8 upstream
			,vip4-80(195)		-- 4th Generation Versatile Interface Processor for the c7500 router
			,vip4-50(196)		-- 4th Generation Versatile Interface Processor for the c7500 router, lower performance than vip4-80 card
			,io-e-ge(197)		-- C7200 I/O Controller with GE(1000Mbps) + E(10Mbps) interface
			,io-2fe(198)		-- C7200 I/O Controller with 2FE (10/100Mbps) interface
			,npm-4000-fddi-sas(200)
			,npm-4000-fddi-das(201)
			,npm-4000-1e(202)
			,npm-4000-1r(203)
			,npm-4000-2s(204)
			,npm-4000-2e1(205)
			,npm-4000-2e(206)
			,npm-4000-2r1(207)
			,npm-4000-2r(208)
			,npm-4000-4t(209)
			,npm-4000-4b(210)
			,npm-4000-8b(211)
			,npm-4000-ct1(212)
			,npm-4000-ce1(213)
			,npm-4000-1a(214)
     	                ,npm-4000-6e-pci(215)
			,npm-4000-1fe(217)
			,npm-4000-1hssi(218)
			,npm-4000-2e-pci(219)
			,npm-4000-4gb(220)			-- 4-Port Serial E1/G.703
                        ,ws-x4548-gb-rj45vplus(222)             -- Catalyst 4500 series 48-port 10/100/1000BaseT linecard with Power Over Ethernet, upto 30W inline power per port

			,pa-1fe(230)
			,pa-8e(231)
			,pa-4e(232)
			,pa-5e(233)
			,pa-4t(234)
			,pa-4r(235)
			,pa-fddi(236)
			,sa-encryption(237)
			,pa-ah1t(238)
			,pa-ah2t(239)
			,pa-a4t(240)
			,pa-a8t-v35(241)
			,pa-1fe-tx-isl(242)
			,pa-1fe-fx-isl(243)
			,pa-1fe-tx-nisl(244)
			,sa-compression(245)
			,pa-atm-lite-1(246)
			,pa-ct3(247)
			,pa-oc3sm-mux-cbrt1(248)
			,pa-oc3sm-mux-cbr120e1(249)
			,pa-ds3-mux-cbrt1(254)
			,pa-e3-mux-cbr120e1(255)
			,pa-8b-st(257)
			,pa-4b-u(258)
			,pa-fddi-fd(259)
			,pm-cpm-1e2w(260)
			,pm-cpm-2e2w(261)
			,pm-cpm-1e1r2w(262)
			,pm-ct1-csu(263)
			,pm-2ct1-csu(264)
			,pm-ct1-dsx1(265)
			,pm-2ct1-dsx1(266)
			,pm-ce1-balanced(267)
			,pm-2ce1-balanced(268)
			,pm-ce1-unbalanced(269)
			,pm-2ce1-unbalanced(270)
			,pm-4b-u(271)
			,pm-4b-st(272)
			,pm-8b-u(273)
			,pm-8b-st(274)
			,pm-4as(275)
			,pm-8as(276)
			,pm-4e(277)
			,pm-1e(278)
			,pm-m4t(280)
			,pm-16a(281)
			,pm-32a(282)
			,pm-c3600-1fe-tx(283)
			,pm-c3600-compression(284)
			,pm-dmodem(285)
			,pm-8admodem(286)
			,pm-16admodem(287)
			,pm-c3600-1fe-fx(288)
			,pm-1fe-2t1-csu(289)		-- Port Module with 1 Fast Ethernet, 2 T1 with CSU
			,as5200-carrier(290)
			,as5200-2ct1(291)
			,as5200-2ce1(292)
			,as5200-dtd-carrier(293)
			,pm-as5xxx-12m(310)
			,pm-as5xxx-12m-56k(311)
			,pm-as5xxx-12m-v110(312)
-- The expansions for some acronyms used in this section are given below:
--	CSU - Channel Service Unit
--	DSU - Dial Service Unit
--	FT1 - Fractional T1
--	WIC - Wan Interface Card
			,wm-c2500-5in1(330)
			,wm-c2500-t1-csudsu(331)
			,wm-c2500-sw56-2wire-csudsu(332)
			,wm-c2500-sw56-4wire-csudsu(333)
			,wm-c2500-bri(334)
			,wm-c2500-bri-nt1(335)
			,wic-serial-1t(360)
			,wic-serial-2t(361)
			,wic-csu-dsu-4(363)
			,wic-s-t-3420(364)
			,wic-s-t-2186(365)
			,wic-u-3420(366)
			,wic-u-2091(367)
			,wic-u-2091-2081(368)
			,wic-s-t-2186-leased(369)
			,wic-t1-csudsu(370)		-- FT1 CSU/DSU Wan Interface Card
			,wic-serial-2as(371)		-- WAN Interface Card - 2 port Async/Sync
			,aim-compression(372)		-- Compression Advanced Interface Module (AIM)
			,c3660-2fe-tx(373)		-- c3660 onboard 2FE(TX) version
			,pm-oc3mm(374)			-- ATM OC3 multimode Port Module
			,pm-oc3mm-vpd(375)		-- ATM OC3 multimode Port Module with Voice Processing Deck
			,pm-oc3smi-vpd(376)		-- ATM OC3 single mode intermediate reach Port Module with Voice Processing Deck
			,pm-oc3sml-vpd(377)		-- ATM OC3 single mode long reach Port Module with Voice Processing Deck
			,pm-oc3sml(378)			-- ATM OC3 single mode long reach Port Module
			,pm-oc3smi(379)			-- ATM OC3 single mode intermediate reach Port Module
			,pm-ima-4t1(380)		-- 4 port T1 IMA (Inverse Mux for ATM) port module
			,pm-ima-8t1(381)		-- 8 port T1 IMA (Inverse Mux for ATM) port module
			,pm-ima-4e1(382)		-- 4 port E1 IMA (Inverse Mux for ATM) port module
			,pm-ima-8e1(383)		-- 8 port E1 IMA (Inverse Mux for ATM) port module
			,nm-1fe-2w(384)			-- Network Module with 1 Fast Ethernet and 2 WIC/VIC interfaces
			,nm-2fe-2w(385)			-- Network Module with 2 Fast Ethernet and 2 WIC/VIC interfaces
			,nm-1fe-1r-2w(386)		-- Network Module with 1 Fast Ethernet, 1 token ring, and 2 WIC/VIC interfaces
			,nm-2w(387)			-- Network Module with 2 WIC/VIC interfaces
			,aim-encryption(388)		-- Encryption Advanced Interface Module for the c2600, c3620, c3640, and c3660
			,c36xx-1fe-tx(389)		-- Onboard 1FE Interface for the c3660 chassis
			,pa-jt2(400)
			,pa-posdw(401)
			,pa-4me1-bal(402)
			,pa-2ce1-balanced(403)
			,pa-2ct1(404)
			,pa-1vg(405)
			,pa-atmdx-ds3(406)
			,pa-atmdx-e3(407)
			,pa-atmdx-sml-oc3(408)
			,pa-atmdx-smi-oc3(409)
			,pa-atmdx-mm-oc3(410)
			,pa-a8t-x21(414)
			,pa-a8t-rs232(415)
			,pa-4me1-unbal(416)
			,pa-4r-fdx(417)
			,pa-1e3(418)
			,pa-2e3(419)
			,pa-1t3(420)
			,pa-2t3(421)
			,pa-2ce1-unbalanced(422)
			,pa-14e-switch(423)
			,pa-1fe-fx-nisl(424)
			,pa-esc-channel(425)
			,pa-par-channel(426)
			,pa-ge(427)			-- Gigabit Ethernet Port Adapter
			,pa-4ct1-csu(428)		-- 8 Port Channelized T1 with CSU
			,pa-8ct1-csu(429)		-- 8 Port Channelized T1 with CSU
			,c3800-vdm(430)
			,c3800-vdm-dc-2t1e1(431)
			,c3800-vdm-dc-1t1e1-enet(432)
			,pa-2feisl-tx(433)
			,pa-2feisl-fx(434)
			,mc3810-dcm(435)
			,mc3810-mfm-e1balanced-bri(436)
			,mc3810-mfm-e1unbalanced-bri(437)
			,mc3810-mfm-e1-unbalanced(438)
			,mc3810-mfm-dsx1-bri(439)
			,mc3810-mfm-dsx1-csu(440)
			,mc3810-vcm(441)
			,mc3810-avm(442)
			,mc3810-avm-fxs(443)
			,mc3810-avm-fxo(444)
			,mc3810-avm-em(445)
			,mc3810-vcm3(446)		-- MC3810 Voice Compression Module with 3 DSPs (Digital Signal Processor)
			,mc3810-bvm(447)		-- MC3810 Basic Voice Module
			,mc3810-avm-fxo-uk(448)		-- MC3810 Analog Voice Module UK Foreign eXchange Office
			,mc3810-avm-fxo-ger(449)	-- MC3810 Analog Voice Module Germany Foreign eXchange Office
			,mc3810-hcm2(450)		-- MC3810 High (Voice) Compression Module with 2 DSPs (Digital Signal Processor)
			,mc3810-hcm6(451)		-- MC3810 High (Voice) Compression Module with 6 DSPs (Digital Signal Processor)
			,mc3810-avm-fxo-pr3(452)	-- MC3810 Analog Voice Module Singapore or Japan Foreign eXchange Office
			,mc3810-avm-fxo-pr2(453)	-- MC3810 Analog Voice Module Australia or New Zealand Foreign eXchange Office
			,mc3810-vdm(454)		-- MC3810 Video Dial-up Module
			,mc3810-apm-fxs-did(455)	-- MC3810 Foreign Exchange Station (FXS) Direct Inward Dialing (DID) Analog Personality Module
			,mc3810-bvm-nt-te(456)		-- 4 ports NT or TE BRI Voice Module on MC3810
			,mc3810-hcm1(457)		-- High performance compression module for the MC3810 platform equipped with one TI 549 DSP
			,mc3810-hcm3(458)		-- High performance compression module for the MC3810 platform equipped with three TI 549 DSPs
			,mc3810-hcm4(459)		-- High performance compression module for the MC3810 platform equipped with four TI 549 DSPs
-- 460 available
			,pm-dtd-6m(461)
			,pm-dtd-12m(462)		-- mica 12 modem module
			,as5300-4ct1(480)
			,as5300-4ce1(481)
			,as5300-carrier(482)
			,as5300-dtd-carrier(484)
			,as5300-8ct1-4t(485)		-- Channelized octal T1 and 4 serial card
			,as5300-8ce1-4t(486)		-- Channelized octal E1 and 4 serial card
			,as5300-4ct1-4t(487)		-- Channelized quad T1 and 4 serial card
			,as5300-4ce1-4t(488)		-- Channelized quad E1 and 4 serial card
			,as5300-amazon2-carrier(489)	-- Amazon II mica carrier card
			,vic-em(500)
			,vic-fxo(501)
			,vic-fxs(502)
			,vpm-2v(503)
			,vpm-4v(504)
			,dsp-vfc30(505)
			,dspm-c542(507)			-- DSP (Digital Signal Processor) C542  module for the AS5300 and AS5800 series
			,vic-2fxo-eu(508)		-- 2 port Foreign eXchange Office Voice Interface Cards for most of Europe
			,vic-2fxo-m3(509)		-- 2 port Foreign eXchange Office Voice Interface Cards for Australia
			,vic-2fxo-m4(510)		-- 2 port Foreign eXchange Office Voice Interface Cards for Germany
			,vic-2fxo-m5(511)		-- 2 port Foreign eXchange Office Voice Interface Cards for France
			,vic-2fxo-m6(512)		-- 2 port Foreign eXchange Office Voice Interface Cards for Italy
			,vic-2fxo-m7(513)		-- 2 port Foreign eXchange Office Voice Interface Cards for Portugal
			,vic-2fxo-m8(514)		-- 2 port Foreign eXchange Office Voice Interface Cards for Singapore
			,vic-2st-2086(515)		-- 2 port Terminal Endpoint BRI S/T Voice interface daughter card
			,hdv(516)                       -- High Density Voice over IP network module
			,dspm-6c549(517)		-- DSP (Digital Signal Processor) module that contains 6 C549 DSPs, used in AS5300 and AS5800
			,wvic-1dsu-t1(518)-- WAN Voice Interface Card with a single port T1 DSU for 1600, 1700, 2600, or 3600 series
			,wvic-1dsu-e1(519)		-- WAN Voice Interface Card with a single port E1 DSU for 1600, 1700, 2600, or 3600 series
			,wvic-2dsu-t1(520)		-- WAN Voice Interface Card with a dual port T1 DSU for 1600, 1700, 2600, or 3600 series
			,wvic-2dsu-e1(521)		-- WAN Voice Interface Card with a dual port E1 DSU for 1600, 1700, 2600, or 3600 series
			,wvic-2dsu-t1-di(522)		-- WAN Voice Interface Card with a dual port T1 DSU with Drop and Insert for 1600, 1700, 2600, or 3600 series
			,wvic-2dsu-e1-di(523)           -- WAN Voice Interface Card with a dual port E1 DSU with Drop and Insert for 1600, 1700, 2600, or 3600 series
			,vic-2fxo-m2(525)		-- 2 port Foreign eXchange Office Voice Interface Cards (Module 2) for Europe/Australia/New Zealand
			,hda-nm-4fxs(528)		-- High Density Analog Voice Module

			,pos-qoc3-mm(530)
			,pos-qoc3-sm(531)
			,pos-oc12-mm(532)
			,pos-oc12-sm(533)
			,atm-oc12-mm(534)
			,atm-oc12-sm(535)
			,pos-oc48-mm-l(536)
			,pos-oc48-sm-lr-fc(537)		-- GSR 1 port Packet Over Sonet OC-48, single mode, long reach, FC connector card
			,gsr-sfc(538)
			,gsr-csc(539)
			,gsr-csc4(540)
			,gsr-csc8(541)
			,gsr-sfc8(542)
			,atm-qoc3-sm(543)               -- Quad OC3 Line Card ATM Singlemode Fiber Ports
			,atm-qoc3-mm(544)               -- Quad OC3 Line Card ATM Multimode Fiber Ports
			,gsr-oc12chds3-mm(545)		-- OC12 channelised to DS3 multimode
			,gsr-oc12chds3-sm(546)		-- OC12 channelised to DS3 singlemode
			,gsr-1ge(547)			-- GSR 1 Port Gigabit Ethernet Line Card
			,gsr-oc12chsts3-mm(548)		-- GSR OC12 channelized to STS-3c/STM-1 multi-mode line card
			,gsr-oc12chsts3-sm(549)		-- GSR OC12 channelized to STS-3c/STM-1 single-mode line card
			,gsr-qoc12-mm(550)		-- GSR Four Port OC12c/STM-4c Multi-mode ATM Card
			,gsr-qoc12-sm(551)		-- GSR Four Port OC12c/STM-4c Single-Mode ATM Card
			,pos-oc48-sm-sr-fc(552)		-- GSR 1 Port Packet Over SONET OC-48c/STM-16 Single Mode Short Reach with FC connector
			,pos-qoc3-sm-l(553)		-- GSR 4 Port Packet Over SONET OC-3c/STM-1 Single Mode Long Reach
			,pos-8oc3-mm(554)		-- GSR 8 port OC3 Multimode POS
			,pos-8oc3-ir(555)		-- GSR 8 port OC3 SM intermediate reach POS
			,pos-8oc3-lr(556)		-- GSR 8 port OC3 SM long reach POS
			,pos-16oc3-mm(557)		-- GSR 16 port OC3 multimode POS
			,pos-16oc3-ir(558)		-- GSR 16 port OC3 SM intermediate reach POS
			,pos-16oc3-lr(559)		-- GSR 16 port OC3 SM long reach POS
			,pa-8ct1(560)			-- 8 Port Channelized T1
			,pa-8ce1(561)			-- 8 Port Channelized E1
			,pa-ce3(562)			-- Channelized E3 Port Adapter
			,pa-4r-dtr(563)			-- 4 port Dedicated Token Ring port adapter
			,pa-possw-sm(564)		-- Single Width POS (Packet Over Sonet) Port Adapter with Singlemode Fiber
			,pa-possw-mm(565)		-- Single Width POS (Packet Over Sonet) Port Adapter with Multimode Fiber
			,pa-possw-lr(566)		-- Single Width POS (Packet Over Sonet) Port Adapter with Long Range Fiber
			,pa-1t3-plus(567)		-- Improved one port serial T3 plus port adapter
			,pa-2t3-plus(568)		-- Improved 2 port serial T3 plus port adapter
			,pa-ima-t1(569)			-- Implements IMA functionality for the 7200/7500 platform for a T1
			,pa-ima-e1(570)			-- Implements IMA functionality for the 7200/7500 platform for an E1
			,pa-2ct1-csu(571)		-- 2 port multichannel T1 port adapter with built in csu/dsu for the 7200, 7500, and rsp7000 platforms
			,pa-2ce1(572)			-- 2 port multichannel E1 port adapter for the 7200, 7500, and rsp7000 platforms
			,pa-2fe-tx(573)			-- 2-port FastEthernet port adapter with two RJ-45 interfaces
			,pa-2fe-fx(574)			-- 2-port FastEthernet port adapter with two multi-mode fiber interfaces
			,pa1-esc4-channel(575)		-- High Performance ESCON Channel Port Adapter Version 4
			,pa2-oc3-pos-sw(576)		-- Dual Port OC-3c Packet Over Sonet(POS) Single Wide Adapter Card
			,pa-4dtr(577)			-- Four port dedicated tokenring adapter
			,pa-vm-hda-8fxs-did(578)	-- High density analog voice/fax voice module with 8 FXS/DID
			,pa1-oc3-pos-sw(579)		-- Single port OC-3c Packet over Sonet (POS) Single Wide Port Adapter Card
			,pa-mcx-4te1-q(580)		-- 4 port, software configurable Multichannel T1/E1 SS7 Q.703A with TDM

			,pm-1fe-1t1(600)		-- Port Module with 1 Fast Ethernet, 1 T1
			,pm-1fe-2t1(601)		-- Port Module with 1 Fast Ethernet, 2 T1
			,pm-1fe-1e1(602)		-- Port Module with 1 Fast Ethernet, 1 E1
			,pm-1fe-2e1(603)		-- Port Module with 1 Fast Ethernet, 2 E1
			,pm-1fe-1t1-csu(604)            -- Port Module with 1 Fast Ethernet, 1 T1 with CSU
			,pm-atm25(605)			-- 25 Mbits/sec ATM Port Module
			,pm-hssi(606)			-- HSSI Card Port Module
			,as5800-dsc(630)
			,as5800-12t1(631)
			,as5800-12e1(632)
			,as5800-mica-hmm(633)
			,as5800-t3(634)			-- T3 trunk card
			,as5800-1fe-dsi(635)
			,as5800-mica-dmm(636)		-- Mica Double density Modem Module
			,as5800-vcc(637)		-- Voice Carrier Card for the AS5800
			,as5800-dspm-6c549(638)		-- Digital Signal Processor Module with 6 C549's Voice Feature Card for the AS5800
			,as5800-dsp(639)		-- Digital Signal Processor Voice Feature Card for the AS5800
--	650-699:	c6xxx cards
			,slc-cap8(650)			-- Subscriber line card for c6200 - Carrierless Amplitude and Phase modulation - 8 port variation
			,ntc-oc3si(651)			-- Network Trunk card for c6200 - Optical Carrier 3, single-mode, intermediate reach variation
			,ntc-oc3mm(652)			-- Network Trunk card for c6200 -  Optical Carrier 3, multi-mode reach variation
			,ntc-stm1si(653)		-- Network Trunk card for c6200 - Synchronous Transport Module level 1, single-mode, intermediate reach variation
			,ntc-stm1mm(654)		-- Network Trunk card for c6200 - Synchronous Transport Module level 1, multi-mode variation
			,slc-dmt8(655)			-- Subscriber line card for c6200 - Discrete Multi-Tone 8 port variation
			,slc-dmt16(656)			-- Subscriber line card for c6200 - Discrete Multi-Tone 16 port variation
			,ntc-ds3(657)			-- Network Trunk card for c6200 - DS3
			,osm-1oc48-pos-ss(659)		-- Optical Service Module, 1-Port OC48 POS SS w/ 4 GE
			,osm-1oc48-pos-sl(660)		-- Optical Service Module, 1-Port OC48 POS SL w/ 4 GE
			,osm-1oc48-pos-si(661)		-- Optical Service Module, 1-Port OC48 POS SI w/ 4 GE
			,osm-2oc12-pos-sl(664)		-- Optical Service Module, 2-Port OC12 POS SL w/ 4 GE
			,osm-4oc12-pos-sl(665)		-- Optical Service Module, 4-Port OC12 POS SL w/ 4 GE
			,osm-2oc12-pos-mm(666)		-- Optical Service Module, 2-Port OC12 POS MM w/ 4 GE
			,osm-4oc12-pos-mm(667)		-- Optical Service Module, 4-Port OC12 POS MM w/ 4 GE
			,osm-2oc12-pos-si(668)		-- Optical Service Module, 2-Port OC12 POS SI w/ 4 GE
			,osm-4oc12-pos-si(669)		-- Optical Service Module, 4-Port OC12 POS SI w/ 4 GE
			,osm-8oc3-pos-si(670)		-- Optical Service Module, 8-Port OC3 POS SI w/ 4 GE
			,osm-16oc3-pos-si(671)		-- Optical Service Module, 16-Port OC3 POS SI w/ 4 GE
			,osm-8oc3-pos-mm(672)		-- Optical Service Module, 8-Port OC3 POS MM w/ 4 GE
			,osm-16oc3-pos-mm(673)		-- Optical Service Module, 16-Port OC3 POS MM w/ 4 GE
			,osm-8oc3-pos-sl(674)		-- Optical Service Module, 8-Port OC3 POS SL w/ 4 GE
			,osm-16oc3-pos-sl(675)		-- Optical Service Module, 16-Port OC3 POS SL w/ 4 GE
			,osm-4ge-wan-gbic(676)		-- Optical Service Module, 4-Port GE w/ WAN services
			,osm-4ge-4oc12-chds3-sm-ir(680)	-- Optical Service Module, 4-Port OC12 channelized down to DS3 Singlemode Intermediate range with 4 GE
			,osm-4ge-8oc12-chds3-sm-ir(681) -- Optical Service Module, 8-Port OC12 channelized down to DS3 Singlemode Intermediate range with 4 GE
			,osm-4ge-oc48-chds3-sm-sr(682)	-- Optical Service Module, 1-Port OC48 channelized down to DS3 Singlemode Short range with 4 GE
			,osm-4ge-2oc48-chds3-sm-sr(683)	-- Optical Service Module, 2-Port 0C48 channelized down to DS3 Singlemode Short range with 4 GE
			,osm-4ge-oc48-chds3-sm-ir(684)	-- Optical Service Module, 1-Port OC48 channelized down to DS3 Singlemode Intermediate range with 4 GE
			,osm-4ge-2oc48-chds3-sm-ir(685)	-- Optical Service Module, 2-Port OC48 channelized down to DS3 Singlemode Intermediate range with 4 GE
			,osm-4ge-oc12-chds3-sm-ir(686)	-- Optical Service Module, 1-Port OC12 channelized down to DS3 Single Mode Intermediate range with 4 GE
			,osm-4ge-2oc12-chds3-sm-ir(687)	-- Optical Service Module, 2-Port OC12 channelized down to DS3 Single Mode Intermediate range with 4 GE
			,mwam-blade(688)		-- Multiprocessor WAN Application Module - a multipurpose blade for the Cat65xx platform
			,wsx-6582-2pa(689)		-- Flex-Wan2 line card for Catalyst 6xxx - 2-WAN PA line card ws-x6582-2pa
			,wsx-6066-slbsk9(692)		-- CSM-S is a content switching module with integrated SSL acceleration
			,cat6k-wsf-6k-pfc3b(693)		-- Catalyst 6500 Policy feature card 3B
			,cat6k-wsf-6k-dfc3b(694)		-- Catalyst 6500 Distributed forwarding card 3B
			,cat6k-wsf-6700-dfc3b(695)		-- Catalyst 6500 Distributed forwarding card 3B
			,cat6k-wsf-6k-pfc3bxl(696)		-- Catalyst 6500 Policy feature card 3B XL
			,cat6k-wsf-6k-dfc3bxl(697)		-- Catalyst 6500 Distributed forwarding card 3B XL
			,cat6k-wsf-6700-dfc3bxl(698)		-- Catalyst 6500 Distributed forwarding card 3B XL
                        ,cat6k-ws-f6k-dfc4-a(699)               -- Catalyst 6500 Distributed Forwarding Card 4A

			,atmdx-rpm(750)			-- RPM Cell Bus Interface
			,pa-vxc-2t1e1(800)		-- 2 port T1/E1 voice port adapter with 30 DSP's
			,pa-vxb-2t1e1(801)		-- 2 port T1/E1 voice port adapter with 12 DSP's
			,pa-atm-oc12-mm(802)		-- Multimode ATM OC-12 Port Adapter
			,pa-atm-oc12-smi(803)		-- Singlemode ATM OC-12 Intermediate reach Port Adapter
			,pa-mct3(804)			-- Multichannel DS3 single port adapter
			,pa-mc2t3(805)			-- Multichannel DS3 dual port adapter
			,pa-pos-oc12-mm(806)		-- OC-12 Packet Over SONET Port Adapter, Multi-Mode fiber
			,pa-pos-oc12-sm(807)		-- OC-12 Packet Over SONET Port Adapter, Single Mode fiber
			,srp-pa-oc12-mm(808)		-- SRP OC-12/STM-4 Multimode Port Adapter for 7000 series
			,srp-pa-oc12-sm-ir(809)		-- SRP OC-12/STM-4 Single Mode Intermediate Reach Port Adapter for 7000 series
			,srp-pa-oc12-lr(810)		-- SRP OC-12/STM-4 Single Mode Long Reach Port Adapter for 7000 series
			,pa-mcx-2te1(811)		-- 2 port, software configurable Multichannel T1/E1 with TDM Port Adapter
			,pa-mcx-4te1(812)		-- 4 port, software configurable Multichannel T1/E1 with TDM Port Adapter
			,pa-mcx-8te1(813)		-- 8 port, software configurable Multichannel T1/E1 with TDM Port Adapter
			,srp-pa-oc12-sm-xr(814)	-- SRP OC-12/STM-4 Single Mode Extended Reach Port Adapter for 7000 series
			,pa-mc-stm1-smi(817)		-- channelized STM-1 PA for 7500/7200(single mode intermediate reach)
			,pa-mc-stm1-mm(818)		-- channelized STM-1 PA for 7500/7200(multimode)
			,pa-dual-wide-ge(819)		-- Dual Wide Enhanced Gigabit Ethernet Port Adapter
			,pa-vxa-1t1e1-24(820)		-- 1 port T1/E1 voice port adapter w/ 7 DSPs
			,pa-vxa-1t1e1-30(821)		-- 1 port T1/E1 voice port adapter w/ 8 DSPs
			,pa-mc-8t1e1(822)		-- Multichannel T1/E1 (without TDM) Port Adapter
			,pa-mcx-8te1-m(824)		-- 8 port, software configurable Multichannel T1/E1 SS7 with TDM Port Adapter
			,pa-a6-mm-oc3(825)              -- ATM WAN OC3 MM Port Adapter.
			,pa-a6-smi-oc3(826)             -- ATM WAN OC3 SMI Port Adapter.
			,pa-a6-sml-oc3(827)             -- ATM WAN OC3 SML Port Adapter.
			,pa-a6-ds3(828)                 -- ATM WAN OC3 DS3 Port Adapter.
			,pa-a6-e3(829)                  -- ATM WAN OC3 E3 Port Adapter.
			,pa-mc-t3-ec(830)		-- Enhanced 1 port T3 multichannel PA
			,pa-mc-2t3-ec(831)		-- Enhanced 2 port T3 multichannel PA
			,pa-1t3e3-ec(832)		-- Enhanced 1 port T3/E3  clear channel PA
			,pa-2t3e3-ec(833)		-- Enhanced 2 port T3/E3  clear channel PA
			,ausm-8t1(850)			-- ATM User Network Interface Service Module with 8 T1 ports
			,ausm-8e1(851)			-- ATM User Network Interface Service Module with 8 E1 ports
			,cesm-8t1(852)			-- Circuit Emulation Service Module with 8 T1 ports
			,cesm-8e1(853)			-- Circuit Emulation Service Module with 8 E1 ports
			,frsm-8t1(854)			-- Frame Relay Service Module with 8 T1 ports
			,frsm-8e1(855)			-- Frame Relay Service Module with 8 E1 ports
			,frsm-4x21(856)			-- Frame Relay Service Module supporting 4 high speed X.21 ports
			,frsm-2hssi(857)		-- Frame Relay Service Module supporting 2 high speed HSSI ports
			,cesm-1t3(858)			-- Circuit Emulation Service Module (CESM) with one T3 port
			,cesm-1e3(859)			-- Circuit Emulation Service Module (CESM) with one E3 port
			,vism-8t1(860)			-- Voice Interworking Service Module (VISM) with 8 T1 ports
			,vism-8e1(861)			-- Voice Interworking Service Module (VISM) with 8 E1 ports
			,mgx-rpm(862)			-- MGX8800 Route Processor Module having the functionality of a C7200 router
			,mgx-srm-3t3(863)		-- MGX8800 Service Redundancy Module supporting 3 T3 ports on back card, used for providing 1:N redundancy for T1 modules
			,enh-axsm-1oc12(864)		-- AXSM-1-622-E Enhanced ATM Switch Service Module, 1 Port, OC12c/STM-4 compliant
			,enh-axsm-2oc12(865)		-- AXSM-2-622-E Enhanced ATM Switch Service Module, 2 Port, OC12c/STM-4 compliant
			,enh-axsm-4oc3(866)		-- AXSM-4-155-E Enhanced ATM Switch Service Module, 4 Ports, OC3c/STM-1 compliant
			,enh-axsm-8oc3(867)		-- AXSM-8-155-E Enhanced ATM Switch Service Module, 8 Ports, OC3c/STM-1 compliant
			,enh-axsm-4stm1(868)		-- AXSM-4-155-E Enhanced ATM Switch Service Module, 4 Ports, STM-1 Electrical
			,enh-axsm-8stm1(869)		-- AXSM-8-155-E Enhanced ATM Switch Service Module, 8 Ports, STM-1 Electrical
			,enh-axsm-8t3e3(870)		-- Enhanced ATM Switch Service Module, 8 T3/E3 Ports
			,enh-axsm-16t3e3(871)		-- Enhanced ATM Switch Service Module, 16 T3/E3 Ports
			,enh-axsm-8t1(872)		-- Enhanced ATM Switch Service Module, 8 T1 Ports and IMA Support
			,enh-axsm-16t1(873)		-- Enhanced ATM Switch Service Module, 16 T1 Ports and IMA Support
			,enh-axsm-8e1(874)		-- Enhanced ATM Switch Service Module, 8 E1 Ports and IMA Support
                        ,enh-axsm-16e1(875)             -- Enhanced ATM Switch Service Module, 16 E1 Ports and IMA Support
			,mgx-rpm-pr(878)	-- Router Processor Module(RPM) Premium in selected MGX Series
			,vixm-4oc12(883) 		-- Voice Interworking Switching Module(VIXM) 4 port OC12 card
			,vixm-16oc3(884) 		-- Voice Interworking Switching Module(VIXM) 16 port OC3 card
			,cesmb-8e1(886)		-- Circuit Emulation Service Module B (CESN/B) with 8 E1 ports
			,cesmb-8t1(887)		-- Circuit Emulation Service Module B (CESN/B) with 8 T1 ports
			,frsmc-8e1(888)		-- Frame Relay Service Module C (FRSM/C) with 8 E1 ports
			,frsmc-8t1(889)		-- Frame Relay Service Module C (FRSM/C) with 8 T1 ports
			,frsmb-2hssi(890)	-- Frame Relay Service Module B (FRSM/B) with 2 hssi ports
			,frsmb-12in1(891)	-- Frame Relay Service Module B (FRSM/B) with 12 In1
			,hsfr-12t3(892)		-- High Speed Frame Relay Service Module with 12 T3 ports
			,hsfr-12e3(893)		-- High Speed Frame Relay Service Module with 12 E3 ports
			,frsm-12t3(894)		-- Frame Relay Service Module, 12 T3 ports
			,frsm-12e3(895)		-- Frame Relay Service Module, 12 E3 ports
			,frsmb-2t3(896)		-- Frame Relay Service Module B (FRSM/B) with 2 T3 ports
			,frsm-b2e3(898)		-- Frame Relay Service Module B (FRSM/B) with 2 E3 ports
			,vism-pr-8t1(899)	-- Voice Interworking Service Module Premium Card (VISM-PR)with 8 T1 ports
			,wsx-2914(900)			-- 4 port 10/100BaseTX module for Catalyst 2900XL series
			,wsx-2922(901)			-- 2 port 100BaseFX module for Catalyst 2900XL series
			,wsx-2914-v(902)		-- 4 port 10/100BaseTX ISL module for Catalyst 2900XL series
			,wsx-2922-v(903)		-- 2 port 100BaseFX ISL module for Catalyst 2900XL series
			,wsx-2924-v(904)		-- 4 port 100BaseFX module for Catalyst 2900XL series
			,wsx-2951(905)			-- ATM UTP module for Catalyst 2900XL series
			,wsx-2961(906)			-- ATM MMF module for Catalyst 2900XL series
			,wsx-2971(907)			-- ATM SMF-MR module for Catalyst 2900XL series
			,wsx-2972(908)			-- ATM SMF-LR module for Catalyst 2900XL series
			,wsx-2931(909)			-- GBIC Gigabit module for Catalyst 2900XL series
			,mgbic-1000base-lh(911)		-- longhaul multimode fiber gigabit ethernet port adapter
			,mgbic-1000base-zx(912)		-- extended reach singlemode fiber gigabit ethernet port adapter
			,mgbic-1000base-cxstack(913)	-- Cisco gigaStack gigabit ethernet port adapter
			,mgbic-1000baset(914)		-- Copper Unshielded twisted pair gigabit ethernet port adapter
                        ,ws-c2960x-24psq-l(933)         -- Catalyst 2960X 24 Gig Downlinks, 2 Copper, 2 SFP uplink NonStakable
                        ,ws-c2960p-48pst-l(938)         -- 48-port PoE, 2+2 1G uplinks, LAN Base
                        ,ws-c2960p-24pc-l(939)          -- 24-port PoE, 2/2 1G uplinks, LAN Base
                        ,ws-c2960p-24lc-l(940)          -- 24-port, partial PoE 2/2 1G uplinks, LAN Base
                        ,ws-c2960p-48tc-l(941)          -- 48-port, 2/2 1G uplinks, LAN Base
                        ,ws-c2960p-24tc-l(942)          -- 24-port, 2/2 1G uplinks, LAN Base
                        ,ws-c2960p-48pst-s(943)         -- 48-port PoE, 2+2 1G uplinks, LAN Lite
                        ,ws-c2960p-24pc-s(944)          -- 24-port PoE, 2/2 1G uplinks, LAN Lite
                        ,ws-c2960p-24lc-s(945)          -- 24-port, partial PoE 2/2 1G uplinks, LAN Lite
                        ,ws-c2960p-48tc-s(946)          -- 48-port, 2/2 1G uplinks, LAN Lite
                        ,ws-c2960p-24tc-s(947)          -- 24-port, 2/2 1G uplinks, LAN Lite
                        ,ws-c2960xr-48fpd-i(948)        -- Catalyst 2960XR 48 Gig Downlinks and 2 SFP+ uplinks IP Lite Stackable with POE support for 740W
                        ,ws-c2960xr-48lpd-i(949)        -- Catalyst 2960XR 48 Gig Downlinks and 2 SFP+ uplinks IP Lite Stackable with POE support for 370W

			,lm-bnc-2t3(950)		-- Two T3 75-ohm BNC back card
			,lm-bnc-2e3(951)		-- Two E3 75-ohm BNC back card
			,lm-db15-4x21(952)		-- Four X.21 DB-15 back card
			,lm-scsi2-2hssi(953)		-- Two HSSI SCSI-2 back card
			,lm-rj48-8t1(954)		-- Eight T1 RJ48 back card
			,lm-rj48-8t1-r(955)		-- Eight T1 RJ48 redundancy back card
			,lm-rj48-8e1(956)		-- Eight E1 RJ48 back card
			,lm-rj48-8e1-r(957)		-- Eight E1 RJ48 redundancy back card
			,lm-smb-8e1(958)		-- Eight E1 SMB back card
			,lm-smb-8e1-r(959)		-- Eight E1 SMB redundancy back card
			,lm-psm-ui(960)			-- User Interface back card containing 2 RS-232 ports and one ethernet port, T1/E1 timing reference ports for Processor Switch Modules
			,lm-mmf-4oc3(961)		-- 4 port 155Mbps back card, MMF, SC connectors
			,lm-smfir-4oc3(962)		-- 4 port 155Mbps back card, SMF-IR, SC connectors
			,lm-smflr-4oc3(963)		-- 4 port 155Mbps back card, SMF-LR, SC connectors
			,lm-smfir-1oc12(964)		-- 1 port 622Mbps back card, SMF-IR, FC connectors
			,lm-smflr-1oc12(965)		-- 1 port 622Mbps back card, SMF-LR, FC connectors
			,lm-s3-ui(966)			-- Processor Switch Module (PXM) Stratum 3 User Interface back card for PXM1 or PXM2
			,lm-1fe-tx(967)			-- 1 port Fast Ethernet RJ45 connector back card for MGX8800 RPM module
			,lm-1fe-fx(968)			-- 1 port Fast Ethernet MMF connector back card for MGX8800 RPM module
			,lm-1mmf-fddi(969)		-- 1 port FDDI MMF connector back card for MGX8800 RPM module
			,lm-1smf-fddi(970)		-- 1 port FDDI SMF connector back card for MGX8800 RPM module
			,lm-rj45-4e(971)		-- 4 port Ethernet (10BaseT) RJ45 connector back card for MGX8800 RPM module
			,lm-mmf-8oc3(972)		-- 8 port 155Mbps back card, MMF, Small Form Factor MT-RJ connectors
			,lm-smf-ir-8oc3(973)		-- 8 port 155Mbps back card, SMF-IR, Small Form Factor MT-RJ connectors
			,lm-smf-lr-8oc3(974)		-- 8 port 155Mbps back card, SMF-LR, Small Form Factor MT-RJ connectors
			,lm-smf-ir-1oc48(975)		-- 1 port 2488Mbps back card, SMF-IR, FC connector
			,lm-smf-lr-1oc48(976)		-- 1 port 2488Mbps back card, SMF-LR, FC connector
			,lm-psm-hd(977)			-- Hard Disk back card for Processor Service Module
			,lm-smb-8t3(978)		-- 8 port T3 back card, SMB connector
			,lm-smb-8e3(979)		-- 8 port E3 back card, SMB connector
			,lm-smb-4stm1(980)		-- 4 port 155-mbps Electrical Back Card, SMB Connector
			,lm-bnc-3t3(985)		--  3 T3  Back Card , BNC Connector
			,ubr-mc16s(1001)		-- Cable card 1 downstream 6 upstream for Spectrum management
			,ubr-mc11(1002)		-- Cable linecard 1 downstream, 1 upstream, FPGA
			,ubr-mc11c(1003)	-- Cable linecard 1 downstream, 1 upstream, ASIC C
			,ubr-mc12c(1004)	-- Cable linecard 1 downstream, 2 upstream, ASIC C
			,ubr-mc14c(1005)	-- Cable linecard 1 downstream, 4 upstream, ASIC C
			,ubr-mc16a(1006)	-- Cable linecard 1 downstream, 6 upstream, ASIC A
			,ubr-mc16b(1007)	-- Cable linecard 1 downstream, 6 upstream, ASIC B
			,ubr-mc16c(1008)	-- Cable linecard 1 downstream, 6 upstream, ASIC C
			,ubr-mc16e(1009)	-- Cable linecard 1 downstream, 6 upstream, ASIC for Europe
			,ubr-mc28c(1010)		-- Cable linecard 2 downstream, 8 upstream
			,ubr-mc26(1011)		-- Cable linecard 2 downstream, 6 upstream
			,ubr-912c(1012)		-- Cisco uBR912-C Cable Modem Card with CSU/DSU WIC
			,ubr-912s(1013)		-- Cisco uBR912-S Cable Modem Card with Serial WIC
			,ubr-914r(1014)		-- Cisco uBR914 Cable Modem with removable WIC
			,ubr-clk(1015)		-- Cisco Cable Clock Card that provides the national clock signal to Cisco uBR7200 VXR
			,ubr-925(1016)		-- Cisco UBR925 Cable Modem/Router with VOIP and hardware accelerated IPSEC
			,ubr-mc26c(1017)	-- Cable linecard 2 downstream, 6 upstream
			,ubr-mc28cf(1020)	-- Cable linecard 2 downstream, 8 upstream, with F connector
			,ubr-mc28c-bnc(1021)	-- Cable linecard 2 downstream, 8 upstream, with BNC connector
			,ubr-mc26cf(1022)	-- Cable linecard 2 downstream, 6 upstream, with F connector
			,ubr-mc26c-bnc(1023)	-- Cable linecard 2 downstream, 6 upstream, with BNC connector
			,ubr-905(1024)		-- Cisco uBR905 Cable Modem with hardware accelerated IPSEC
			,ubr-dlc24(1025)	-- DLC24 is a Digital Video Broadcasting (DVB) Linecard which supports the DVB in-band (IB) and out-of-band (OOB) standards, as well as the DAVIC OOB standard. It has 2 downstream channels, 4 upstream channels, and 1 ASI interface port
			,ubr-mc520s-f(1029)	-- Cable linecard, 5 downstreams, 20 upstreams, with Spectrum Management, with F connector
			,ubr-mc520s-bnc(1030)	-- Cable linecard, 5 downstreams, 20 upstreams, with Spectrum Management, with BNC connector
			,ubr-mc28u(1033)	-- Docsis compliant intelligent coax cable line card with 2 downstream and 8 upstream ports for ubr72xx series cable routers.
			,ubr-mc16u(1034)	-- Docsis compliant intelligent coax cable line card with 1 downstream and 6 upstream ports for ubr72xx series cable routers.
			,ubr-mc28x(1035)	-- Docsis compliant intelligent coax cable line card with 2 upstream and 8 downstream ports and integrated upstream for ubr72xx routers.
			,ubr-mc16x(1036)	-- Docsis compliant intelligent coax cable line card with 1 upstream and 6 downstream ports and integrated upstream converter for ubr72xx routers.
			,ubr-tccplus(1040)	--  uBR10K Timing, Communications and Control Plus Card
			,ubr-mc16u-e(1041)	--  DOCSIS compliant intelligent coax cable line card with 1 downstream and 6  upstream ports for uBR7225VXR series cable routers
			,ubr-mc28u-e(1042)	--  DOCSIS compliant intelligent coax cable line card with 2 downstream and 8  upstream ports for uBR7225VXR series cable routers
                        ,ubr-dtcc(1043)         --  DOCSIS Timing, Communication, and Control Plus Card for uBR10012
                        ,ubr-mc88v(1045)        --  DOCSIS 3.0 compliant intelligent coax cable line card with 8 downstream and 8  upstream ports
                        ,ubr-mc2020(1046)       --  DOCSIS compliant intelligent coax cable line card with 20 downstream and 20 upstream ports for uBR10000 series cable router

			,gsr-8fe-tx(1050)		-- GSR 8 port Fast Ethernet card with Copper interface
			,gsr-8fe-fx(1051)		-- GSR 8 port Fast Ethernet card with Fiber interface
			,ssrp-oc48-sm-sr(1052)		-- GSR 1 port SONET based SRP OC-48c/STM-16 Single Mode, Short Reach
			,ssrp-oc48-sm-lr(1053)		-- GSR 1 port SONET based SRP OC-48c/STM-16 Single Mode, Long Reach
			,pos-qoc12-sm-lr(1054)		-- GSR 4 port (Quad) OC-12 POS card, single mode, long reach
			,pos-qoc12-mm-sr(1055)		-- GSR 4 port (Quad) OC-12 POS card, multi mode, short reach
			,pos-oc48-sm-lr-sc(1056)	-- GSR 1 port Packet Over Sonet OC-48, single mode, long reach, SC connector card
			,pos-oc48-sm-sr-sc(1057)	-- GSR 1 port Packet Over Sonet OC-48, single mode, short reach, SC connector card
			,srp-oc12-sm-ir(1058)		-- GSR 1 port single mode SRP OC-12/STM-4 intermediate reach module
			,srp-oc12-sm-lr(1059)		-- GSR 1 port single mode SRP OC-12/STM-4 long reach module
			,srp-oc12-mm(1060)		-- GSR 1 port SRP OC-12/STM-4 Multimode Ring line card
			,pos-en-oc48-sr-sc(1061)	-- GSR enhanced OC-48 short reach SC connector line card
			,pos-en-oc48-sr-fc(1062)	-- GSR enhanced OC-48 short reach FC connector line card
			,pos-en-oc48-lr-sc(1063)	-- GSR enhanced OC-48 long reach SC connector line card
			,pos-en-oc48-lr-fc(1064)	-- GSR enhanced OC-48 long reach FC connector line card
			,pos-en-qoc12-sr(1065)		-- GSR enhanced 4 port OC-12 short reach line card
			,pos-en-qoc12-ir(1066)		-- GSR enhanced 4 port OC-12 intermediate reach line card
			,copper-6ds3(1067)		-- GSR 6 port copper DS3 interface line card
			,copper-12ds3(1068)		-- GSR 12 port copper DS3 interface line card
			,pos-oc192-sm-ir-fc(1069)	-- GSR 1 port Packet Over SONET OC-48c/STM-16 Single Mode Intermediate Reach with FC connector
			,pos-oc192-sm-sr-fc(1070)	-- GSR 1 port Packet Over SONET OC-48c/STM-16 Single Mode Short Reach with FC connector
			,pos-oc192-sm-ir-sc(1071)	-- GSR 1 port Packet Over SONET OC-48c/STM-16 Single Mode Intermediate Reach with SC connector
			,pos-oc192-sm-sr-sc(1072)	-- GSR 1 port Packet Over SONET OC-48c/STM-16 Single Mode Short Reach with SC connector
			,gsr-sfc16(1073)		-- GSR Switch Fabric Card for 12016
			,gsr-csc16(1074)		-- GSR 12016 Clock Scheduler Card
			,gsr-3ge(1075)			-- GSR 3 Port Gigabit Ethernet Line Card
			,gsr-alarm16(1076)		-- GSR Alarm module
			,gsr-bus-board16(1077)		-- GSR Bus Board for Power distribution
			,srp-oc12-sm-xr(1078)		-- GSR 1 port single mode SRP OC-12/STM-4 extra long reach module
			,pos-en-qoc12-mm(1079)		-- GSR enhanced 4 port OC-12 multimode line card
			,pos-en-qoc48-sm-sr-fc(1080)	-- GSR enhanced 4 Port Packet Over Sonet OC-48, Single Mode, Short Reach, FC Connector Card
			,pos-en-qoc48-sm-sr-sc(1081)	-- GSR enhanced 4 Port Packet Over Sonet OC-48, Single Mode, Short Reach, SC Connector Card
			,pos-en-qoc48-sm-lr-sc(1082)	-- GSR enhanced 4 Port Packet Over Sonet OC-48, Single Mode, Long Reach, SC Connector Card
			,pos-en-qoc48-sm-lr-fc(1083)	-- GSR enhanced 4 Port Packet Over Sonet OC-48, Single Mode, Long Reach, FC Connector Card
			,gsr-6ct3(1084)			-- GSR 6 Port Channelized T3 Line Card
			,pos-en-oc192-sm-lr-fc(1085)	-- GSR enhanced 1 Port Packet Over Sonet OC-192, Single Mode, Long Reach, FC Connector Card
			,pos-en-oc192-sm-lr-sc(1086)	-- GSR enhanced 1 Port Packet Over Sonet OC-192, Single Mode, Long Reach, SC Connector Card
			,pos-en-oc192-sm-vsr-sc(1087)	-- GSR enhanced 1 Port Packet Over Sonet OC-192, Single Mode, Very Short Reach, SC Connector Card
			,pos-en-oc192-sm-vsr-fc(1088)	-- GSR enhanced 1 Port Packet Over Sonet OC-192, Single Mode, Very Short Reach, FC Connector Card
			,gsr-sfc16-oc192(1091)		-- GSR 12016 OC192 Switch Fabric Card
			,gsr-csc16-oc192(1092)		-- GSR 12016 OC192 Clock Scheduler Card
			,gsr-qoc12-chstsds3-sm-ir-sc(1094)	-- GSR 4 port OC12 channelized to STS-12c/STM-4, STS-3c/STM1, or DS-3, Single Mode, Intermediate Reach and SC connector line card
			,gsr-qoc12-chstsds3-mm-sr-sc(1095)	-- GSR 4 port OC12 channelized to STS-12c/STM-4, STS-3c/STM1, or DS-3, Multi Mode, Short Reach and SC connector line card
			,gsr-oc48-chstsds3-mm-sr-sc(1096)	-- GSR 1 port OC48 channelized to STS-48c/STM16, STS-12c/STM-4, STS-3c/STM1 or DS-3, Multi Mode, Short Reach  and SC  connector line card
			,gsr-oc48-chstsds3-sm-ir-sc(1097)	-- GSR 1 port OC48 channelized to STS-48c/STM16, STS-12c/STM-4, STS-3c/STM1 or DS-3, Single Mode, Intermediate Reach and SC connector line card
			,gsr-oc48-chstsds3-sm-lr-sc(1098)	-- GSR 1 port OC48 channelized to STS-48c/STM16, STS-12c/STM-4, STS-3c/STM1 or DS-3, Single Mode, Long Reach and SC connector line card
			,gsr-16oc3-chstsds3-mm-sr-sc(1099)	--  GSR 16 port OC3 channelized to STS-3c/STM-1 or DS-3; Multi Mode fiber, Short Reach, SC connector line card
			,aim-lc-4e1-compression(1100)	-- Lowcost 4 E-1 Compression AIM
			,vic-2fxo-m1(1101)		-- 2 port Foreign eXchange Office Voice Interface Cards (Module 1) for North America
			,pm-nm-to-aim(1102)		-- Network Module to Advanced Interface Port Module for the 1600 and 3600 series
			,wic-csu-dsu-ft1(1105)		-- Wan Interface Card with 1 Fractional T1 DSU/CSU port for 2600, 3600 series
			,pm-ds3(1106)		-- ATM DS3 port module for 2600, 3600 series
			,pm-e3(1107)		-- ATM E3 port module for 2600, 3600 series
			,vic-2vp-fxs-did(1111)			-- 2 Port Voice Interface Card for 26/3600 Platforms.  Ports can function as Foreign Exchange Station (FXS)or Direct Inward Dialing (DID) Voice Ports (VP)
			,wic-serial-1t-12in1(1112)		-- WAN Interface Card card including 1 port serial interface, 12 in 1 connector type
			,vic-2st-2086-nt-te(1113)		-- Two port NT or TE Endpoint BRI S/T voice interface daughtercard
			,nm-aic64(1114)			-- The new alarm interface card (AIC) network module with 64 monitoring points on the C26xx/C3600 platform
			,mix3660-64(1115)		--  TDM Module that enables TDM switching on C3660 platform
			,wic-async-1am(1116)		--  WAN Interface Card - 1 Port Analog Modem
			,wic-async-2am(1117)		--  WAN Interface Card - Dual Analog Modem
			,aim-4dsps(1119)		--  DSP only AIM with 4 DSPs
			,hdv-4fxs(1120)			-- 4-Port FXS High Density Analog Voice Module
			,c2610m(1121)			-- c2600M with 1 integrated ethernet interface
			,c2611m(1122)			-- c2600M with 2 integrated ethernet interfaces
			,wic-ethernet(1124)		-- WIC-1ENET card for 17xx platforms
			,nm-1t3e3(1130)			-- One port Clear T3/E3 Network Module
			,nm-1ct3e3(1131)		-- One port Channelized T3/E3 Network Module
			,nm-8ct1e1(1132)		-- Eight port Channelized T1/E1 Network Module
			,hda-em-4fxo(1133)              -- 4-port FXO Expansion Module for High Density Analog Voice Interface Daughtercard
                        ,c2610xm-1fe(1134)                  -- Card with 1 integrated fast ethernet interface with SDRAM for Cisco 2610XM platform
                        ,c2611xm-2fe(1135)                  -- Card with 2 integrated fast ethernet interfaces with SDRAM for Cisco 2611XM platform
                        ,c2620xm-1fe(1136)                  -- Card with 1 integrated fast ethernet interface with SDRAM for Cisco 2620XM platform
                        ,c2621xm-2fe(1137)                  -- Card with 2 integrated fast ethernet interfaces with SDRAM for Cisco 2621XM platform
                        ,c2650xm-1fe(1138)                  -- Card with 1 integrated fast ethernet interface with SDRAM for Cisco 2650XM platform
                        ,c2651xm-2fe(1139)                  -- Card with 2 integrated fast ethernet interfaces with SDRAM for Cisco 2651XM platform
			,nm-16as(1140)		 	-- 16 port Async/Sync Network Module provides low speed serial interface for the MAR's family of platforms
			,nm-1ct1e1-pri(1147)		-- One port Primary Rate Interface (PRI)  Channelized T1/E1 Network Module
			,nm-2ct1e1-pri(1148)		-- Two port Primary Rate Interface (PRI)  Channelized T1/E1 Network Module
			,nm-ceoip-4t1e1(1149)		-- Four port T1/E1 Circuit Emulation over IP network module

			,io-2fe-tx-isl(1150)		-- I/O card Dual 10/100 Fast Ethernet ISL card for the 7100 series
			,ism-ipsec-mppe(1151)		-- Integrated Service Module, used only in slot 5 of the 7100 series, is a hardware accelerator for IPSEC Encryption and Compression, and MPPE encryption.
			,vpn-accelerator(1152)		-- VPN Encryption Accelerator Engine
			,vpn-accelerator-module2(1153)	-- VPN Encryption Accelerator Engine 2
			,vpn-accelerator-AES(1154)	-- VPN Encryption Accelerator Engine with AES Support
			,vpn-am-2plus(1155)  -- The VPN Acceleration Module 2+ (VAM2+) is a port adapter that installs in any single port-adapter slot on the Cisco 7204VXR or Cisco 7206VXR router with the NPE-225, NPE-400, or NPE-G1 processor, or the Cisco 7301 router.

			,cre-rp(1180)			-- Central Routing Engine - Route Processor for Cisco 10000 series
			,cre-fp(1181)			-- Central Routing Engine - Forwarding Processor for Cisco 10000 series
			,cpu-as5400(1182)		-- CPU card for AS5400
			,cpu-mc3810-v3(1185)		-- CPU card for the MC3810-V3; higher performance than MC3810 with NEBs compliant changes.
			,cpu-7200-nse1(1186)		-- CPU card for use in the 7200 series, Network Service Engine 1.  Contains a PXF (Parallel Express Forwarding) processor to accelerate layer 3-7 IP features.
			,cpu-as5850(1187)			-- CPU card for AS5850
			,cpu-7200-npe400(1188)		-- Network processing engine (CPU card) for 7200 series
			,cpu-rsp4-plus(1190)		-- RSP4+ is ECC capable RSP4, ie.  With a Tiger5 asic
			,cpu-7150(1191)			-- CPU for the 7150 series
			,cpu-7401-nse(1193)		-- Cisco 7401 Network Processing Engine
			,cpu-rsp16(1195)  -- RSP8 Plus board processor
			,cpu-gsr-prp1(1196)		-- GSR Performance Route Processor 1
			,cpu-c7300-nse100(1197)		-- Network Service Engine 100 (CPU card) for Cisco 7300 platform
			,cpu-pxm1e-1gbps(1198)		-- Cisco MGX88XX Processor Switch Module 1 Enhancement version
			,cpu-pxm1e-2oc12(1199)		-- Cisco MGX88XX Processor Switch Module 1, 2 OC12 ports, Enhanced version with PNNI support
			,cpu-pxm1e-8oc3(1200)		-- Cisco MGX88XX Processor Switch Module 1 Enhancement version with PNNI support
			,cpu-pxm1e-8t3e3(1201)		-- Cisco MGX88XX Processor Switch Module 1 Enhanced version with 8 T3/E3 ports
			,cpu-pxm1e-combo-t3e3oc3(1202)	-- Cisco MGX88XX Processor Switch Module 1 Enhanced version combo card with 8 T3/E3 and 4 OC3 ports
			,cpu-7200-npeg1(1203)		-- Network Processing Engine (CPU card) for 7200VXR series
			,cpu-c2691-2fe(1204)		-- c2691 Motherboard with Fast Ethernet
			,cpu-c3745-2fe(1205)		-- c3745 Motherboard with Fast Ethernet
			,cpu-c3725-2fe(1206)		-- c3725 Motherboard with Fast Ethernet
			,cpu-c3631-1fe(1207)		-- c3631 Motherboard with Fast Ethernet
			,cpu-mwr1900-2fe(1208)		-- MWR 1900 Motherboard with Fast Ethernet
			,cpu-6400-nsp(1209)             -- Cisco 6400 Node Switch Processor
                        ,cpu-6400-nrp(1210)             -- Cisco 6400 Node Route Processor
                        ,cpu-6400-nrp2(1211)            -- Cisco 6400 Node Route Processor 2
                        ,cpu-6400-nrp2-sv(1212)         -- Cisco 6400 Node Route Processor 2 with Shaped VCs
			,cpu-pxm1e-16-t1e1(1215)	-- PXM1E-16-T1E1 processor card supports 16 port T1E1 IMA(Inverse Multplexing for ATM)
			,cpu-c7300-nse100-plus(1216)	-- Network Service Engine 100+ for Cisco 7300 platform
			,cpu-as5400-hpx(1217)		-- CPU card for AS5400HPX
			,cpu-as5350-hpx(1218)		-- CPU card for AS5350HPX
			,cpu-as5850-tb(1221)            -- BCM1250-based CPU card for AS5850 RSC
			,cpu-c7300-npeg100(1222)	-- Network Processing Engine (CPU card) for Cisco 7300 platform
			,cpu-vg224(1224)		-- Line Side Analog Gateway with 24FXS Analog ports
			,cpu-1800-mod(1227)		-- CPU type for 1800 series modular routers
			,cpu-gsr-prp2(1228)		-- GSR Performance Route Processor 2
			,cpu-as5400-xm(1229)		-- CPU card for AS5400XM
			,cpu-as5350-xm(1230)		-- CPU card for AS5350XM
			,cpu-7200-npeg2(1238)			-- Network Processing Engine 2 (CPU card) for 7200VXR series
			,cpu-c2801-2fe(1239)			-- 2801 Motherboard with two integrated fast ethernets
			,cpu-ixp2350-westport-np(1240)		-- Processor used for Paldron development platform
			,cpu-c7300-nse150(1241)			-- Network Services Engine (CPU card) for the Cisco 7304 Platform
			,cpu-7201-npeg2(1243)			-- Network Processing Engine 2 (CPU card) for 7201 series
			,cpu-uc520-s(1247)			-- CPU card for the UC520 UCSO fixed-configuration series
			,cpu-uc520-m(1248)			-- CPU card for the 19 inch rack-mount model of UC520 series
			,cpu-1861(1249)				-- Cpu card for the ISR flavour of freddo
			,cpu-traffic(1250)			-- NME-APA SCE Entity Traffic Processor
                        ,cpu-2941(1251)                         -- CPU for MWR-2941-DC
                        ,cpu-1941-2ge(1252)                     -- c1941 Motherboard, with 2 GE
                        ,cpu-2901-2ge(1253)                     -- c2901 Motherboard, with 2 GE
                        ,cpu-2911-3ge(1254)                     -- c2911 Motherboard, with 3 GE
                        ,cpu-2951-3ge(1255)                     -- c2951 Motherboard, with 3 GE
                        ,cpu-2921-3ge(1256)                     -- c2921 Motherboard, with 3 GE
                        ,cpu-3925-3ge(1257)                     -- c3925 w/SPE100 Motherboard, with 3 GE
                        ,cpu-3945-3ge(1258)                     -- c3945 w/SPE150 Motherboard, with 3 GE
                        ,cpu-sr-520t1(1259)                     -- This is the security router with 1 port T1. Supports Voice and data
                        ,cpu-1941w-2ge(1260)                    -- c1941 Motherboard, with 2 GE, 801.11n WLAN
                        ,cpu-3825nv-2ge(1261)                   -- c3825nv Motherboard with Gigabit Ethernet
                        ,cpu-3845nv-2ge(1262)                   -- c3845nv Motherboard with Gigabit Ethernet
                        ,cpu-3900SPE200-4ge(1269)               -- cisco 3900 Services Performance Engine 200 (SPE200) with 4 GE, 3 EHWIC, 3 DSP
                        ,cpu-3900spe250-4ge(1274)               -- cisco 3900 Services Performance Engine 250 (SPE250) with 4 GE, 3 EHWIC, 3 DSP
                        ,cpu-crs1-fp140(1275)                   -- Cisco CRS Series Forwarding Processor 140G
                        ,cpu-crs1-msc140g(1276)                 -- Cisco CRS Series Modular Services Card 140G
                        ,cpu-c1841c-2fe-k9(1277)                -- 1841C/K9 Motherboard with two integrated fast ethernet
                        ,cpu-c2801c-2fe-k9(1278)                -- 2801C/K9 Motherboard  with two integrated fast ethernets
                        ,cpu-c2811c-2fe-k9(1279)                -- 2811C/K9 Motherboard with two integrated fast ethernets and integrated VPN
                        ,cpu-c2821c-2ge-k9(1280)                -- 2821C/K9 Motherboard with two integrated gigabit ethernets and integrated VPN
                        ,cpu-c3825c-2ge-k9(1282)                -- 3825C/K9 Motherboard with Gigabit Ethernet
                        ,cpu-c3845c-2ge-k9(1283)                -- 3845C/K9 Motherboard with Gigabit Ethernet
                        ,cpu-1906c-k9(1287)                     -- c1906C/K9 Motherboard with 2 GE, Serial 1T
                        ,cpu-5915(1288)                         -- CPU for 5915 Embedded services router
                        ,cpu-86xvae(1297)                       -- CPU for Cisco 86xVAE series products
                        ,cpu-2811ve-2fe(1298)                   -- 2811ve Motherboard with two integrated fast ethernets and integrated VPN
                        ,cpu-1841ve-2fe(1299)                   -- 1841ve Motherboard with two integrated fast ethernet


			,pos-1oc12(1300)		-- 1 port OC12 Packet over Sonet card
			,p6-ct3(1301)			-- 6 port channelized T3 card
			,ge(1302)			-- 1 port Gigabit Ethernet card
			,p1-coc12(1304)			-- 1 port channelized OC12 card
			,p4-chstm1(1305)		-- 4 port channelized STM-1 card
			,acc-24fe-tx(1307)		-- c10720 24 ports fast ethernet Tx access card
			,acc-24fe-fx-mm(1308)		-- c10720 24 ports fast ethernet FX MM (2km) access card
			,acc-24fe-fx-sm(1309)		-- c10720 24 ports fast ethernet FX SM (15km) access card
			,srp-oc48-sr(1310)		-- c10720 1 port OC-48c SRP SM short reach uplink card
			,srp-oc48-ir(1311)		-- c10720 1 port OC-48c SRP SM intermediate reach uplink card
			,atm-4oc3(1313)			-- 4 port OC3 ATM line card with single mode, intermediate reach optics for the C10000 platform
			,srp-pos-1oc48-sm-sr(1315)	-- 1 Port OC48 SRP or POS SM short reach card
			,srp-pos-1oc48-sm-lr(1316)	-- 1 Port OC48 SRP or POS SM long reach card
			,flashcard-48mb(1317)		-- Cisco 10000 48 MB Flash Card
			,flashcard-128mb(1318)		-- Cisco 10000 128 MB Flash Card
			,p24-ct1e1(1319)		-- 24 Port Channelized E1/T1 card
			,acc-4ge8fe-tx(1323)		-- c10720 4 port gigabit ethernet + 8 port fast ethernet access card
			,acc-4ge8fe-fx-mm(1324)		-- c10720 4 port gigabit ethernet + 8 port fast ethernet FX MM (2km) access card
			,acc-4ge8fe-fx-sm(1325)		-- c10720 4 port gigabit ethernet + 8 port fast ethernet FX SM (15km) access card
			,ul-srp48-lr1(1326)		-- c10720 1 port OC-48c SRP SM Long Reach (40Km) uplink card
			,ul-srp48-lr2(1327)		-- c10720 1 port OC-48c SRP SM Long Reach (80Km) uplink card
			,p8-fe(1329)			-- 8 Port Fast Ethernet line card
			,c10720-mnt(1330)		-- C10720 Maintenance card
			,ul-pos-srp48-sm-sr(1332)	-- c10720 OC-48c POS/SRP SM short reach uplink card
			,ul-pos-srp48-sm-ir(1333)	-- c10720 OC-48c POS/SRP SM intermediate reach uplink card
			,ul-pos-srp48-sm-lr1(1334)	-- c10720 OC-48c POS/SRP SM Long Reach (40Km) uplink card
			,ul-pos-srp48-sm-lr2(1335)	-- c10720 OC-48c POS/SRP SM Long Reach (80Km) uplink card
			,acc-24fe-tx-b(1336)		-- c10720 24 ports fast ethernet Tx access card revB.
			,acc-4ge8fe-tx-b(1337)		-- c10720 4 port gigabit ethernet + 8 port fast ethernet access card revB.
			,c10k-spa-jacket(1338)		-- the Shared Port Adaptor (SPA) jacket (or host) card for the c10k. It can host up to 2 SPAs
			,ul-rpr-srp-48(1339)		-- c10720 1 port RPR(802.17)/SRP OC48 uplink card
			,p4-ct3(1340)		-- c10000 4 port channelized half-height T3 card
			,atm-4oc3stm1-lr(1341)		-- c10000 4 port OC3/STM1 ATM line card with long reach optics


			,as5400-dfc-carrier(1350)	-- Carrier card that holds Dial Feature Cards for the AS5400 platform
			,as5400-dfc-np348(1351)		-- Nextport (np) Modem Dial Feature Card consisting of 3 modem modules, 2 of which have 120 modems and that has 108, for a total of 348 modems per card, used in AS5400 and AS5350 platforms
			,as5400-dfc-np192(1352)		-- Nextport (np) Modem Dial Feature Card consisting of 2 modem modules, 1 of which has 120 modems the other 72, for a total of 192 modems per card, used in AS5400 and AS5350 platforms
			,as5400xm-dfc-carrier(1353)	-- Carrier card that holds Dial Feature Cards for the AS5400-XM platform
			,as5400xm-vfc(1354)	-- Voice Feature Card   containing Texas Instruments Digital Signal processor(DSP)

			,dfc-8ce1(1450)			-- 8 Primary Rate Interface (PRI) Channelized E1 (ce1) Dial Feature Card used in AS5400 and AS5800 platforms
			,dfc-8ct1(1451)			-- 8 Primary Rate Interface (PRI) Channelized T1 (ct1) Dial Feature Card used in AS5400 and AS5800 platforms
			,dfc-ct3(1452)			-- Channelized T3 (ct3) Dial Feature Card used in AS5400 and AS5800 platforms
			,dfc-np108(1453)		-- Nextport (np) Modem Dial Feature Card consisting of 3 modem modules, each module has 36 modems, for a total of 108 modems per card, used in AS5400 and AS5800 platforms
			,isa-ipsec-mppe(1454)		-- Integrated Service Port Adapter, used in the 7100 and 7200 series as a module, and in the 7500 series as a Port Adapter.  Hardware Accelerator for IPSEC Encryption and Compression, and MPPE encryption.  May not be used in slot 5 of the 7100.
			,wic-dslsar-20150(1455)		-- DSLSAR ADSL WIC (Wan Interface Card) used in 1720, 1750, 2600 and 3600 series.  DSLSAR - SAR (Segmentation & Reassembly) of ATM cells and can be used with any DSL (Digital Subscriber Line). Uses ADSL (Asymmetric Digital Subscriber Line) as the physical layer.
			,wvic-2dsu-t1-dir(1462)		-- WAN Voice Interface Cards with a dual port T1 DSU with drop & insert and protection switching relay for MWR1900
			,wvic-2dsu-e1-dir(1463)		-- WAN Voice Interface Cards with a dual port E1 DSU with drop & insert and protection switching relay for MWR1900
			,vic-4vp-fxs-did(1464)		-- 4 port Voice Interface Card; Each port can function as Foreign Exchange Station(FXS) or Direct Inward Dialing (DID) Voice Port
			,vic-4fxo-us-m1(1465)		-- Four port Foreign Exchange Office Voice Interface Card for US/North America or M1 interface
			,vic-4fxo-m2-m3(1466)		-- Four port Foreign Exchange Office Voice Interface Card for M2 or M3 interface (software selectable on a card basis)
			,vic-4fxo-cama(1467)		-- Four port Foreign Exchange Office Voice Interface Card for US/North America with CAMA (Centralized Automated Message Accounting) 911 signalling support (software selectable per port basis)
			,mgx-srm-e1-oc3(1469)		-- Cisco MGX88xx Service REdundancy Module (SRM) E
			,vic-8fxo-us-m1(1471)		-- 8 Port FXO Voice Interface Module for US/North America or M1 interface
			,p8-ds3-e3-atm(1472)		-- 8 Port DS3/E3 ATM Line Card
			,wic-dslsar-20174-isdn(1475)	-- Single port ADSL Wan Interface Card to support ADSL over ISDN and dying gasp, to be used on c1700, c2600 and c3700 routers
			,wic-dslsar-20174-pots(1476)	-- Single port ADSL Wan Interface Card to support ADSL over POTS and dying gasp, to be used on c1700, c2600 and c3700 routers
			,nm-se(1477)			-- service engine network module
			,aim-se(1478)			-- service engine Advanced Interface Module
			,wic-se(1479)			-- service engine WIC
			,spa-ipsec-2g(1482)		-- IPSec Shared Port Adapter with 2 Gbps DES/3DES/AES (SPA-IPSEC-2G)
			,spa-2p-oc3-atm(1483)		-- 2-port OC3c/STM1c ATM Shared Port Adapter (SPA-2XOC3-ATM)
			,spa-4p-oc3-atm(1484)		-- 4-port OC3c/STM1c ATM Shared Port Adapter (SPA-4XOC3-ATM)
			,spa-1p-oc12-atm(1485)		-- 1-port OC12c/STM4c ATM Shared Port Adapter (SPA-1XOC12-ATM)
			,spa-1p-oc48-atm(1487)		-- 1-port OC48c/STM16c ATM Shared Port Adapter (SPA-1XOC48-ATM)
			,spa-2p-oc3-pos(1490)		-- 2-port OC3c/STM1c POS Shared Port Adapter (SPA-2XOC3-POS)
			,spa-4p-oc3-pos(1491)		-- 4-port OC3c/STM1c POS Shared Port Adapter (SPA-4XOC3-POS)
			,spa-1p-oc12-pos(1492)		-- 1-port OC12c/STM4c POS Shared Port Adapter (SPA-1XOC12-POS)
			,spa-2p-oc12-pos(1493)		-- 2-port OC12c/STM4c Multirate POS Shared Port Adapter (SPA-2XOC12-POS)
			,spa-8p-oc12-pos(1494)		-- 8-port OC12c/STM4c Multirate POS Shared Port Adapter (SPA-8XOC12-POS)
			,spa-4p-fe-7304(1495)		-- 4-port 10/100 Ethernet Shared Port Adapter (SPA-4FE-7304)
			,spa-2p-ge-7304(1496)		-- 2-port 10/100/1000 Ethernet Shared Port Adapter (SPA-2GE-7304)
			,wic-eswitch4(1497)		-- 4 Ports 10BaseT/100BaseTX Ethernet Switch card
			,spa-1p-oc192-pos-rpr-xfp(1498)	-- 1-port OC192c/STM64c POS/RPR XFP Optics Shared Port Adapter (SPA-OC192POS-XFP)
			,spa-1p-oc192-pos-rpr-sm-lr(1500)	-- 1-port OC192c/STM64c POS/RPR SMLR Optics Shared Port Adapter (SPA-OC192POS-LR)


			,cat6k-wsx-sup-12ge(1502)	-- Supervisor with 2 Gigabit Ethernet ports for the Catalyst 6000 series
			,cat6k-wsx-6408-gbic(1503)	-- Card with 8 Gigabit Ethernet ports for the Catalyst 6000 series
			,cat6k-wsx-6224-100fx-mt(1504)	-- Card with 24 port 100BaseFX MM (MT-RJ) for the Catalyst 6000 series
			,cat6k-wsx-6248-rj45(1505)	-- Card with 48 10/100 RJ45 Fast Ethernet ports for the Catalyst 6000 series
			,cat6k-wsx-6248-tel(1506)	-- Card with 48 10/100 RJ21 Fast Ethernet ports for the Catalyst 6000 series
			,cat6k-wsx-6302-msm(1507)	-- Multilayer Switch Module for the Catalyst 6000 series
			,cat6k-wsx-6024-mtrj(1509)	-- Card with 24 10/100 MTRJ Fast Ethernet ports for the Catalyst 6000 series
			,cat6k-msfc2(1510)		-- Multilevel Switching Feature Card Version 2 for the Catalyst 6000 series
			,cat6k-wsx-6316-ge-tx(1511)		-- 16-port RJ-45 Gigabit ethernet module
			,cat6k-wsx-6416-gbic(1512)		-- 16-port GBIC Gigabit ethernet module
			,cat6k-wsx-6324-100fx(1513)		-- 24-port 100FX multimode MT-RJ with 128K per-port packet buffer
			,cat6k-wsx-6348-rj45(1514)		-- 48-port 10/100 ethernet module
			,cat6k-wsx-6502-10ge(1515)		-- 10 Gigabit Ethernet Base Module
			,cat6k-wsx-6066-slb-apc(1516)		-- Venus: Server Load Balancing Application Processor Complex
			,cat6k-wsx-6548-rj45(1518)		-- 48 port 10/100 Hydra2+/Hydra2V+
			,cat6k-wsx-6248a-tel(1519)		-- Card for C6K with 48 10/100 RJ21 ports with enhanched QoS a.k.a Indus w/ Enhanced QoS
			,cat6k-wsx-sup2-2ge(1520)		-- Supervisor 2 with 2 Gigabit Ethernet ports
			,cat6k-wsc-6500-sfm(1521)		-- Catalyst 6500 Switch Fabric Module
			,cat6k-wsc-6500-sfm2(1522)		--Catalyst 6500 Switch Fabric Module II
			,cat6k-wsx-6816-gbic(1523)		-- Catalyst 6500 16 port 1000BaseX (Layer 3)
			,cat6k-wsx-6348-rj21(1528)	-- Catalyst 6500 48 port 10/100BaseTX (RJ-21)
			,cat6k-wsx-6516-gbic(1529)	-- Catalyst 6500 16 port 1000BaseX GBIC
			,cat6k-wsx-sup1a-2ge(1530)	-- Catalyst 6500 2 port 1000BaseX Supervisor module (GBIC)
			,cat6k-wsx-6548-rj21(1531)	-- Catalyst 6500 48 port 10/100BaseTX (RJ-21)
			,cat6k-wsx-6416-gemt(1532)	-- Catalyst 6500 16 port 1000BaseSX (MT-RJ)
			,cat6k-wsx-6380-nam(1533)	-- Catalyst 6500 Network Analysis Module
			,cat6k-wsx-6248a-rj45(1534)	-- Catalyst 6500 48 port 10/100BaseTX (RJ-45)
			,cat6k-wsx-6408a-gbic(1535)	-- Catalyst 6500 8 port 1000BaseX (GBIC), Enhanced QoS module
			,cat6k-wsx-6381-ids(1536)	-- Catalyst 6500 Intrusion Detection module
			,cat6k-wsx-6524-mmmt(1537)	-- Catalyst 6500 24 port 100BaseX MM (MT-RJ) module
			,cat6k-wsx-6516-getx(1538)	-- Catalyst 6500 16 port 10/100/1000BaseT (RJ-45) module
			,cat6k-wsx-6501-10gex4(1539)	-- Catalyst 6500 1 port 10 Gigabit Ethernet (EX4) module
			,cat6k-wsx-6816-oc3-mm(1540)	-- Catalyst 6500 16 port OC3c Packet Over Sonet Multimode
			,cat6k-wsf-6kvpwr(1541)		-- Catalyst 6500 inline power card
                        ,cat6k-ws-svc-nam1(1542)        -- Catalyst 6500 Network Analysis Module
                        ,cat6k-ws-svc-nam2(1543)        -- Catalyst 6500 Network Analysis Module
                        ,cat6k-ws-svc-fwm1(1544)        -- Catalyst 6500 Firewall Module
                        ,cat6k-ws-svc-ssl1(1545)        -- Catalyst 6500 SSL Module
                        ,cat6k-wsx-6516a-gbic(1546)     -- Catalyst 6500 16 port 1000BaseX (GBIC)
			,ipsec-vpnsm(1549)		-- Gigabit IPsec VPN Service Module for the Catalyst 6500 and 7600
			,dslam-ni2-controller(1553)	-- Cisco 6100, 6130, 6260 DSLAM chassis NI-2 IOS controller Daughter Card
			,wvic-2dsu-e1-di-g703(1554)	-- Two port E1 voice interface daughtercard with Drop and Insert and G.703 for 2600 series and 3600 series routers
			,wvic-1dsu-e1-g703(1555)	-- One port E1 voice interface daughtercard with G.703 for 2600 series and 3600 series routers
			,dspm-pvdm3(1556)		-- Packet Voice DSP module with 3 C549 DSP's used by 17x0, 26x0, and 36x0 platforms
			,dspm-pvdm1(1561)		-- Packet Voice DSP module with 1 C549 DSP used by 17x0, 26x0, and 36x0 platforms
			,dspm-pvdm2(1562)		-- Packet Voice DSP module with 2 C549 DSPs used by 17x0, 26x0, and 36x0 platforms
			,dspm-pvdm4(1563)		-- Packet Voice DSP module with 4 C549 DSPs used by 17x0, 26x0, and 36x0 platforms
			,dspm-pvdm5(1564)		-- Packet Voice DSP module with 5 C549 DSPs used by 17x0, 26x0, and 36x0 platforms
			,hda-em-4dsp(1590)		-- 4-C5421 DSP Daughtercard
			,hda-em-10fxs(1591)		-- 10-port FXS Voice Interface Daughtercard
			,wic-sh-dsl(1565)		-- A WIC (Wan Interface Card) providing Symmetrical HIgh bit rate Digital Subscriber line (SHDSL) for 2600, 3620, 3640 and 3660 platforms
			,hdv-8fxs(1566)			-- 8-Port FXS Voice Interface Daughtercard
			,hdv-4dsp(1567)			-- 4-chip DSP Daughtercard
			,c7300-nse100-db(1568)		-- Network Service Engine 100 Daughtercard for Cisco 7300 platform
			,vic-4vp-fxs-4did(1573)	-- 4-port Direct Inward Dialing (DID) and 4-port Foreign Exchange Station (FXS) Voice Interface Daughtercard
			,c7300-nse100-plus-db(1574)	-- Network Service Engine 100+ Daughtercard for Cisco 7300 platform
			,em-4fxs-4fxo(1581)		-- 8-port voice/fax expansion module - 4FXS/4FXO
			,em-6fxo(1582)			-- 6-port voice/fax expansion module - FXO
			,em-4bri-nt-te(1583)		-- 4-port voice/fax expansion module - BRI
			,vic2-mft1-t1e1(1594)		-- 1-Port RJ-48 Multiflex Voice Trunk - T1/E1
			,vic2-mft2-t1e1(1595)		-- 2-Port RJ-48 Multiflex Voice Trunk - T1/E1
			,em2-hda-4fxo(1596)		-- 4-port voice/fax expansion module - FXO
			,vic-1j1(1597)			-- VIC-1J1,Digital Voice J1 Interface with a single port DB-15 Connector for 2600, 3600 and 3700 series
			,wic-1am-v2(1598)		-- WAN Interface Card - 1 Port Analog Modem
			,wic-2am-v2(1599)		-- WAN Interface Card - 2 port Analog Modem

			,ni2-wan-oc3mm-sub-oc3mm(1600)	-- Network Interface module (OC-3-MM WAN, OC-3-MM Subtend)
			,ni2-wan-ds3-sub-2ds3(1601)	-- Network Interface module (DS-3 WAN, 2 DS-3 Subtend)
			,atuc-1p2-cap(1602)		-- ATU-C dual-line CAP module
			,atuc-1p2-dmt(1603)		-- ATU-C dual-line DMT module
			,atuc-1p4-dmt(1604)		-- ATU-C quad-line DMT module
			,lim(1605)			-- Line Interface Module
			,ni2-wan-oc3sm-sub-oc3sm(1606)	-- Network Interface module (OC-3-SM WAN, OC-3-SM Subtend)
			,ni2-wan-e3-sub2-e3(1607)	-- Network Interface module (E-3 WAN, 2 E-3 Subtend)
			,ni2-wan-ds3-sub8-ds1-ima(1608)	-- Network Interface module (DS-3 WAN, 8 DS-1 IMA Subtend)
			,atuc-1p4-cap(1609)		-- ATU-C quad-line CAP module
			,stuc-1p4(1610)			-- STU-C quad-line module
			,ituc-1p8(1611)			-- ITU-C octal-line module
			,atuc-1p4-flexi-dmt(1612)	-- Flexi DSL line card configured as DMT
			,atuc-1p4-flexi-cap(1613)	-- Flexi DSL line card configured as CAP
			,atuc-1p4-flexi(1614)		-- Generic Flexi DSL line card
			,atuc-1p4-dmt-isdn(1615)	-- DMT over ISDN 4 port line card
			,ni2-wan-oc3sm-sub-2ds3(1616)	-- Network Interface module (OC-3-SM WAN, 2 DS-3 Subtend)
			,ni2-wan-oc3mm-sub-2ds3(1617)	-- Network Interface module (OC-3-MM WAN, 2 DS-3 Subtend)
			,atuc-1p8-dmt(1618)		-- ATU-C octal-line DMT module
			,stuc-1p8(1619)			-- STU-C octal-line module
			,atuc-1p8-dmt-itemp(1620)	-- ATU-C octal-line DMT module industrial temperature grade
			,stuc-1p8-itemp(1621)		-- STU-C octal-line shdsl module industrial temperature grade
			,ni2-wan-ds3-sub-2ds3-rev2(1634)	-- Network Interface module (DS-3 WAN, DS-3 Subtend) Revision 2
			,ni2-wan-oc3sm-sub-oc3sm-rev2(1635)	-- Network Interface module (OC-3-SM WAN, OC-3-SM Subtend) Revision 2
			,ni2-wan-oc3mm-sub-oc3mm-rev2(1636)	-- Network Interface module (OC-3-MM WAN, OC-3-MM Subtend) Revision 2
			,ni2-wan-oc3sm-sub-2ds3-rev2(1637)	-- Network Interface module (OC-3-SM WAN, 2 DS-3 Subtend) Revision 2
			,ni2-wan-oc3mm-sub-2ds3-rev2(1638)	-- Network Interface module (OC-3-MM WAN, 2 DS-3 Subtend) Revision 2
			,ni2-wan-oc3sm-sub-oc3sm-itemp(1639)	-- Network Interface module (OC-3-SM WAN, OC-3-SM Subtend, Itemp)
			,cva122(1700)		--  Cisco CVA122 Cable Voice Adapter (Residential Cable Modem with two Voice Ports)
			,cva124(1701)		--  Cisco CVA124 Cable Voice Adapter (Residential Cable Modem with four Voice Ports)
			,cva122e(1702)		--  Cisco CVA122 Cable Voice Adapter (Residential Cable Modem with two voice ports) - European version
			,cva124e(1703)		--  Cisco CVA124 Cable Voice Adapter (Residential Cable Modem with four voice ports) - European version
			,as5850-epm-2ge(1750)	-- Route Switch Controller Card with 2 port Gigabit Ethernet
			,as5850-ct3-216up(1751)	-- Feature Card with Channelized T3 and 216 Universal Ports
			,as58xx-324up(1753)	-- Feature Card with 324 Universal Ports
			,as5850-24e1(1754)      -- Feature Card with 24 port Channelized E1 for the AS5850 platform
			,as5850-24t1(1755)      -- Feature Card with 24 port Channelized T1 for the AS5850 platform
			,as5350xm-dfc-carrier(1801)     -- Carrier card that holds Dial Feature Cards for the AS5350-XM carrier



			,gsr-16oc3-chstsds3-sm-ir-sc(1900)	--  GSR 16 port OC3 channelized to STS-3c/STM-1 or DS-3; Single Mode fiber, Intermediate Reach, SC connector line card
			,gsr-16oc3-chstsds3-sm-lr-sc(1901)	--  GSR 16 port OC3 channelized to STS-3c/STM-1 or DS-3; Single Mode fiber, Long Reach, SC connector line card
			,gsr-2oc3-chds1(1905)	-- GSR platform card, 2 ports of OC3 (Sonet/SDH); each port is channelized to DS1 level
			,ssrp-oc192-sm-lr(1906)	-- GSR 1 port SONET based SRP OC-192c/STM-64 single mode long reach line card
			,ssrp-oc192-sm-ir(1907)	-- GSR 1 port SONET based SRP OC-192c/STM-64 single mode intermediate reach line card
			,ssrp-oc192-sm-sr(1908)	-- GSR 1 port SONET based SRP OC-192c/STM-64 single mode short reach line card
			,ssrp-oc192-sm-vsr(1909)	-- GSR 1 port SONET based SRP OC-192c/STM-64 single mode very short reach line card
			,gsr-2oc12chds3-mm(1910)	-- 2xOC12 channelized to DS3 multimode
			,gsr-2oc12chds3-sm(1911)	-- OC12 channelised to DS3 singlemode
			,gsr-sfc10(1912)		-- GSR Switch Fabric Card for 12010
			,gsr-csc10(1913)		-- Clock Scheduler Card for GSR 12010
			,gsr-alarm10(1914)		-- GSR Alarm module
			,gsr-bus-board10(1915)		-- GSR Bus Board for Power distribution
			,gsr-oc48-chstsds3-sm-sr-sc(1916)	-- GSR 1-port-OC48, channelized to to STS-48c/STM-16, STS-12c/STM-4, STS-3c/STM-1 or DS3, single mode, short-reach, SC connector
			,gsr-e48-pos-oc48-sm-sr-sc(1917)	-- GSR, Edge Engine 48, (concatenated) 1 port OC48 POS, single mode, short-reach, SC connector
			,gsr-e48-pos-oc48-sm-lr-sc(1918)	-- GSR, Edge Engine 48, (concatenated) 1 port OC48 POS, single mode, short-reach, SC connector
			,gsr-e48-pos-qoc12-sm-ir-sc(1919)	-- GSR, Edge Engine 48, 4 port (concatenated) OC12 POS, single mode, intermediate reach, SC connector
			,gsr-e48-pos-16oc3-sm-ir-sc(1920)	-- GSR, Edge Engine 48, 16 port (concatenated) OC3 POS, single mode, intermediate reach, SC connector
			,copper-6e3(1921)		-- GSR 6 port copper E3 interface line card
			,copper-12e3(1922)		-- GSR 12 port copper E3 interface line card
			,gsr-e48-pos-16oc3-sm-ir-lc(1926)       -- GSR, Edge Engine 48, 16 port (concatenated) OC3 POS, single mode, intermediate reach, LC connector
			,gsr-16oc3-chstsds3-sm-ir-lc(1927)      -- GSR 16 port OC3 channelized to STS-3c/STM-1 or DS-3; single mode fiber, intermediate reach, LC connector
			,gsr-oc12-chds1-sm-ir-sc(1928)		-- GSR 1 port OC12 channelized to DS1, single-mode intermediate reach line card with SC connector
			,gsr-sfc6(1929)			-- GSR 12406 Switch Fabric Card
			,gsr-csc6(1930)			-- GSR 12406 Clock Scheduler Card
			,gsr-alarm6(1931)		-- GSR 12406 Alarm Module
			,pos-en-qoc48-vsr(1932)		-- GSR enhanced 4 Port Packet Over Sonet OC-48, Very Short Reach Card
			,pos-en-qoc48-mm-sr-sc(1933)	-- GSR enhanced 4 Port Packet Over Sonet OC-48, Multi Mode, Short Reach, SC Connector Card
			,pos-en-qoc48-sm-ir-sc(1934)	-- GSR enhanced 4 Port Packet Over Sonet OC-48, Single Mode, Intermediate Reach, SC Connector Card
			,pos-en-qoc48-sm-ir-fc(1935)	-- GSR enhanced 4 Port Packet Over Sonet OC-48, Single Mode, Intermediate Reach, FC Connector Card
			,pos-en-qoc48-sm-vlr-sc(1936)	-- GSR enhanced 4 Port Packet Over Sonet OC-48, Single Mode, Very Long Reach, SC Connector Card
			,pos-en-qoc48-sm-vlr-fc(1937)	-- GSR enhanced 4 Port Packet Over Sonet OC-48, Single Mode, Very Long Reach, FC Connector Card
			,pos-en-qoc48-sm-elr-sc(1938)	-- GSR enhanced 4 Port Packet Over Sonet OC-48, Single Mode, Extremely Long Reach, SC Connector Card
			,pos-en-qoc48-sm-elr-fc(1939)	-- GSR enhanced 4 Port Packet Over Sonet OC-48, Single Mode, Extremely Long Reach, FC Connector Card
			,pos-en-oc192-vsr(1940)		-- GSR enhanced 1 Port Packet Over Sonet OC-192, Very Short Reach Card
			,pos-en-oc192-sm-sr2-sc(1941)	-- GSR enhanced 1 Port Packet Over Sonet OC-192, Single Mode, Short Reach 2, SC Connector Card
			,pos-en-oc192-sm-sr2-fc(1942)	-- GSR enhanced 1 Port Packet Over Sonet OC-192, Single Mode, Short Reach 2, FC Connector Card
			,pos-en-oc192-sm-vlr-sc(1943)	-- GSR enhanced 1 Port Packet Over Sonet OC-192, Single Mode, Very Long Reach, SC Connector Card
			,pos-en-oc192-sm-vlr-fc(1944)	-- GSR enhanced 1 Port Packet Over Sonet OC-192, Single Mode, Very Long Reach, FC Connector Card
			,pos-en-oc192-sm-elr-sc(1945)	-- GSR enhanced 1 Port Packet Over Sonet OC-192, Single Mode, Extremely Long Reach, SC Connector Card
			,pos-en-oc192-sm-elr-fc(1946)	-- GSR enhanced 1 Port Packet Over Sonet OC-192, Single Mode, Extremely Long Reach, FC Connector Card
			,gsr-sfc12410(1947)		-- GSR 12410 Switch Fabric Card
			,gsr-csc12410(1948)		-- GSR 12410 Clock Scheduler Card
			,iad2420-vm-8fxs(1950)			-- This card provides 8 analog Foreign eXchange Stations (FXS) in the Integrated Access Device 2420 (IAD2420) chassis
			,iad2420-16fxs(1951)			-- This card provides 16 analog Foreign eXchange Stations (FXS) in the Integrated Access Device 2420 (IAD2420) chassis
			,iad2420-vm-pwr(1952)			-- This card provides power supply to high density analog FXS voice module in the Integrated Access Device 2420 (IAD2420) chassis
			,iad2420-adsl(1953)			-- This card provides access to ADSL (Asymmetrical Digital Subscriber Line) over ATM (Asynchronous Transfer Mode) AAL2 (ATM Adaptation Layer 2), AAL5 (ATM Adaptation Layer 5) and various class of QoS (Quality of Service) for both voice and data service on the Integrated Access Device 2420 (IAD2420) chassis
			,iad2420-hcm1(1954)			-- High performance compression module for the IAD2420 platform equipped with one TI 549 DSP
			,iad2420-hcm2(1955)			-- High performance compression module for the IAD2420 platform equipped with two TI 549 DSPs
			,iad2420-hcm3(1956)			-- High performance compression module for the IAD2420 platform equipped with three TI 549 DSPs
			,iad2420-hcm4(1957)			-- High performance compression module for the IAD2420 platform equipped with four TI 549 DSPs
			,iad2420-hcm5(1958)			-- High performance compression module for the IAD2420 platform equipped with five TI 549 DSPs
			,iad2420-hcm6(1959)			-- High performance compression module for the IAD2420 platform equipped with six TI 549 DSPs
			,iad2420-cpu(1960)			-- CPU card for IAD2420
			,iad2420-mfm-e1-unbalanced(1961)	-- IAD2420 E1 75 ohms unbalanced
			,iad2420-mfm-e1-dsx1-csu(1962)		-- IAD2420 E1 100/120 ohms balanced
			,iad2420-mfm-t1-dsx1-csu(1963)		-- IAD2420 T1 100/120 ohms balanced only
			,iad2420-8fxo(1964)			--  High density 8 analog Foreign eXchange Office (FXO) module
			,iad2420-16fxs-off-premise(1967)	-- IAD2420 Sixteen FXS Off Premise Analog Voice Module
			,gsr-atm-en-8oc3-mm(1968)		-- GSR enhanced 8 port OC3c/STM-1 Multimode ATM LC
			,gsr-oc48-msr(1969)			-- Cisco 12000 Series 2.5G Modular Services Card
			,pos-e-2oc192-vsr(1970)			-- GSR Edge 2 Port Packet Over Sonet OC-192, Very Short Reach Card
			,pos-e-2oc192-sm-sr2-sc(1971)		-- GSR Edge 2 Port Packet Over Sonet OC-192, Single Mode, Short Reach 2, SC Connector Card
			,pos-e-2oc192-sm-sr2-fc(1972)		-- GSR Edge 2 Port Packet Over Sonet OC-192, Single Mode, Short Reach 2, FC Connector Card
			,pos-e-2oc192-sm-sr-sc(1973)		-- GSR Edge 2 Port Packet Over Sonet OC-192, Single Mode, Short Reach, SC Connector Card
			,pos-e-2oc192-sm-sr-fc(1974)		-- GSR Edge 2 Port Packet Over Sonet OC-192, Single Mode, Short Reach, FC Connector Card
			,pos-e-2oc192-sm-ir-sc(1975)		-- GSR Edge 2 Port Packet Over Sonet OC-192, Single Mode, Intermediate Reach, SC Connector Card
			,pos-e-2oc192-sm-ir-fc(1976)		-- GSR Edge 2 Port Packet Over Sonet OC-192, Single Mode, Intermediate Reach, FC Connector Card
			,pos-e-2oc192-sm-lr-sc(1977)		-- GSR Edge 2 Port Packet Over Sonet OC-192, Single Mode, Long Reach, SC Connector Card
			,pos-e-2oc192-sm-lr-fc(1978)		-- GSR Edge 2 Port Packet Over Sonet OC-192, Single Mode, Long Reach, FC Connector Card
			,pos-e-2oc192-sm-vlr-sc(1979)		-- GSR Edge 2 Port Packet Over Sonet OC-192, Single Mode, Very Long Reach, SC Connector Card
			,pos-e-2oc192-sm-vlr-fc(1980)		-- GSR Edge 2 Port Packet Over Sonet OC-192, Single Mode, Very Long Reach, FC Connector Card
			,pos-e-2oc192-sm-elr-fc(1981)		-- GSR Edge 2 Port Packet Over Sonet OC-192, Single Mode, Extremely Long Reach, FC Connector Card
			,pos-e-2oc192-sm-elr-sc(1982)		-- GSR Edge 2 Port Packet Over Sonet OC-192, Single Mode, Extremely Long Reach, SC Connector Card
			,iad2430-ob-8fxs(1983)			-- This card provides 8 on-board analog Foreign Exchange Stations (FXS) in the Integrated Access Device 2430 (IAD2430) chassis
			,iad2430-ob-16fxs(1984)			-- This card provides 16 on-board analog Foreign Exchange Stations (FXS) in the Integrated Access Device 2430 (IAD2430) chassis
			,iad2430-ob-24fxs(1985)			-- This card provides 24 on-board analog Foreign Exchange Stations (FXS) in the Integrated Access Device 2430 (IAD2430) chassis
			,iad2430-ob-t1e1(1986)			-- This card provides on-board T1/E1 in the Integrated Access Device 2430 (IAD2430) chassis.
                        ,iad2435-ob-t1e1(1987)                  -- This card provides T1/E1  in the Integrated Access Device 2435(IAD2435)
                        ,iad2435-ob-8fxs(1988)                  -- This card provides 8 on-board analog Foreign Exchange Stations(FXS) in the Integrated Access Device 2435 (IAD2435) chassis
                        ,vg204-ob-4fxs(1989)                    -- This card provides 4 on-board analog Foreign Exchange Stations (FXS) in the Voice Gateway 204 (VG204) chassis
                        ,vg202-ob-2fxs(1990)                    -- This card provides 2 on-board analog Foreign Exchange Stations (FXS) in the Voice Gateway 202 (VG202) chassis
                        ,vg202xm-ob-2fxs(1991)                  -- This card provides 2 on-board analog Foreign Exchange Stations (FXS) in the Voice Gateway 202xm (VG202XM) chassis
                        ,vg204xm-ob-4fxs(1992)                  --   This card provides 4 on-board analog Foreign Exchange Stations (FXS) in the Voice Gateway 204XM (VG204XM) chassis

			,mc3810-hcm5(2000)			--  High performance compression module for the MC3810 platform equipped with five TI 549 DSPs
                        ,sm-sre-710-k9(2002)                    --  SM-SRE-710-K9: Service Module for Modular and Integrated Services Routers
                        ,sm-sre-910-k9(2003)                    --  SM-SRE-910-K9: Service Module for Modular and Integrated Services Routers

			,m10000base-lx4(2051)			--  Cisco Wide-WDM 1310nm Laser 10 gigabit ethernet port adapter
			,m10000base-ex4(2052)			--  Cisco Wide-WDM 1550nm Laser 10 gigabit ethernet port adapter
			,m10000base-lr(2053)			--  Cisco Serial 1310nm Laser 10 gigabit ethernet port adapter
			,m10000base-er(2054)			-- Cisco Serial 1550nm Laser 10 gigabit ethernet port adapter
			,m10000base-sx4(2055)			-- Cisco Wide-WDM 850nm Laser 10 gigabit ethernet port adapter
                        ,psm-sre-910-k9(2056)                   -- SRE 910 (4-8GB MEM,2x500GB 7k HDD,2C CPU) for router bundle
                        ,psm-sre-710-k9(2057)                   -- SRE 710 (4GB MEM,500GB 7K HDD,1C CPU) for router bundle

			,c7401(2100)				-- Cisco 7400 Family, 1 Slot Router
			,io-c7401-ge(2101)			-- Cisco 7401 I/O Controller with dual 10/100/1000Mbps GE interfaces
			,c7411-npeg1(2128)			-- Cisco 7400 Family, 1 Slot Router
			,io-c7411-ge(2129)			-- Cisco 7411 I/O Controller with three 10/100/1000Mbps GE interfaces
			,vip6-80(2132)				-- A new VIP card to be used in 7500 box. this card is same as VIP4-80 but with a higher speed CPU.
			,c7300-cc-pa(2138)			-- Port Adaptor Carrier Card for Cisco 7304
			,c7304-msc-100(2139)			-- C7304-MSC-100 is a carrier card for 7304. it can carry up to 2 VPA (Versatile Port Adaptor) cards
			,c7300-6e3(2140)			-- 6-port E3 interface line card for Cisco 7300
			,c7300-1oc12-atm(2141)			-- 1-port OC12 ATM line card for Cisco 7300

			,c7200-vsa(2155)			-- C7200 VPN Services Adapter

			,gsr-1p10ge(2200)			-- One Port 10 Gigabit Ethernet Card for the 12000 series routers
			,gsr-e48-pos-oc48-sm-ir-sc(2201)	-- GSR, Edge Engine, OC48 POS, Single Mode, Intermediate Reach, SC Connector
			,gsr-e-oc192-sm-lr-sc(2203)		-- GSR Edge 1 Port Packet over Sonet OC-192, Single Mode, Long Reach, SC Connector card
			,gsr-e-oc192-sm-vsr-sc(2204)		-- GSR Edge 1 Port Packet over Sonet OC-192, Single Mode, Very Short Reach, SC Connector card
			,gsr-e-oc192-sm-vsr-fc(2205)		-- GSR Edge 1 Port Packet over Sonet OC-192, Single Mode, Very Short Reach, FC Connector card
			,gsr-e-oc192-sm-sr-fc(2206)		-- GSR Edge 1 Port Packet over Sonet OC-192, Single Mode, Short Reach, FC Connector card
			,gsr-e-oc192-sm-sr-sc(2207)		-- GSR Edge 1 Port Packet over Sonet OC-192, Single Mode, Short Reach, SC Connector card
			,gsr-e-oc192-sm-lr-fc(2208)		-- GSR Edge 1 Port Packet over Sonet OC-192, Single Mode, Long Reach, FC Connector card
			,gsr-e-qoc48-sm-lr-fc(2209)		-- GSR Edge 4 Port Packet over Sonet OC-48, Single Mode, Long Reach, FC Connector card
			,gsr-e-qoc48-sm-lr-sc(2210)		-- GSR Edge 4 Port Packet over Sonet OC-48, Single Mode, Long Reach, SC Connector card
			,gsr-e-qoc48-sm-vsr-sc(2211)		-- GSR Edge 4 Port Packet over Sonet OC-48, Single Mode, Very Short Reach, SC Connector card
			,gsr-e-qoc48-sm-vsr-fc(2212)		-- GSR Edge 4 Port Packet over Sonet OC-48, Single Mode, Very Short Reach, FC Connector card
			,gsr-e-qoc48-sm-sr-fc(2213)		-- GSR Edge 4 Port Packet over Sonet OC-48, Single Mode, Short Reach, FC Connector card
			,gsr-e-qoc48-sm-sr-sc(2214)		-- GSR Edge 4 Port Packet over Sonet OC-48, Single Mode, Short Reach, SC Connector card
			,gsr-e-qoc48-vsr(2215)			-- GSR Edge 4 Port Packet over Sonet OC-48, Very Short Reach
			,gsr-e-qoc48-sm-sr2-sc(2216)		-- GSR Edge 4 Port Packet over Sonet OC-48, Single Mode, Short Reach 2, SC Connector card
			,gsr-e-qoc48-sm-sr2-fc(2217)		-- GSR Edge 4 Port Packet over Sonet OC-48, Single Mode, Short Reach 2, FC Connector card
			,gsr-e-qoc48-mm-sr-sc(2218)		-- GSR Edge 4 Port Packet over Sonet OC-48, Multi Mode, Short Reach, SC Connector card
			,gsr-e-qoc48-sm-ir-sc(2219)		-- GSR Edge 4 Port Packet over Sonet OC-48, Single Mode, Intermediate Reach, SC Connector card
			,gsr-e-qoc48-sm-ir-fc(2220)		-- GSR Edge 4 Port Packet over Sonet OC-48, Single Mode, Intermediate Reach, FC Connector card
			,gsr-e-qoc48-sm-vlr-sc(2221)		-- GSR Edge 4 Port Packet over Sonet OC-48, Single Mode, Very Long Reach, SC Connector card
			,gsr-e-qoc48-sm-vlr-fc(2222)		-- GSR Edge 4 Port Packet over Sonet OC-48, Single Mode, Very Long Reach, FC Connector card
			,gsr-e-qoc48-sm-elr-sc(2223)		-- GSR Edge 4 Port Packet over Sonet OC-48, Single Mode, Extremely Long Reach, SC Connector card
			,gsr-e-qoc48-sm-elr-fc(2224)		-- GSR Edge 4 Port Packet over Sonet OC-48, Single Mode, Extremely Long Reach, FC Connector card
			,gsr-e-oc192-vsr(2225)			-- GSR Edge 1 Port Packet over Sonet OC-192, Very Short Reach
			,gsr-e-oc192-sm-sr2-sc(2226)		-- GSR Edge 1 Port Packet over Sonet OC-192, Single Mode, Short Reach 2, SC Connector card
			,gsr-e-oc192-sm-sr2-fc(2227)		-- GSR Edge 1 Port Packet over Sonet OC-192, Single Mode, Short Reach 2, FC Connector card
			,gsr-e-oc192-mm-sr-sc(2228)		-- GSR Edge 1 Port Packet over Sonet OC-192, Multi Mode, Short Reach, SC Connector card
			,gsr-e-oc192-sm-ir-sc(2229)		-- GSR Edge 1 Port Packet over Sonet OC-192, Single Mode, Intermediate Reach, SC Connector card
			,gsr-e-oc192-sm-ir-fc(2230)		-- GSR Edge 1 Port Packet over Sonet OC-192, Single Mode, Intermediate Reach, FC Connector card
			,gsr-e-oc192-sm-vlr-sc(2231)		-- GSR Edge 1 Port Packet over Sonet OC-192, Single Mode, Very Long Reach, SC Connector card
			,gsr-e-oc192-sm-vlr-fc(2232)		-- GSR Edge 1 Port Packet over Sonet OC-192, Single Mode, Very Long Reach, FC Connector card
			,gsr-e-oc192-sm-elr-sc(2233)		-- GSR Edge 1 Port Packet over Sonet OC-192, Single Mode, Extremely Long Reach, SC Connector card
			,gsr-e-oc192-sm-elr-fc(2234)		-- GSR Edge 1 Port Packet over Sonet OC-192, Single Mode, Extremely Long Reach, FC Connector card
			,ssrp-2oc48-srp-sm-sr-lc(2236)		-- GSR 2 port SONET dual SRP/POS OC-48c/STM-16, SRP Mode, Single Mode, Short Reach, LC Connector card
			,ssrp-2oc48-srp-sm-ir-lc(2237)		-- GSR 2 port SONET dual SRP/POS OC-48c/STM-16, SRP Mode, Single Mode, Intermediate Reach, LC Connector card
			,ssrp-2oc48-srp-sm-lr-lc(2238)		-- GSR 2 port SONET dual SRP/POS OC-48c/STM-16, SRP Mode, Single Mode, Long Reach, LC Connector card
			,ssrp-2oc48-pos-sm-sr-lc(2239)		-- GSR 2 port SONET dual SRP/POS OC-48c/STM-16, POS Mode, Single Mode, Short Reach, LC Connector card
			,ssrp-2oc48-pos-sm-ir-lc(2240)		-- GSR 2 port SONET dual SRP/POS OC-48c/STM-16, POS Mode, Single Mode, Intermediate Reach, LC Connector card
			,ssrp-2oc48-pos-sm-lr-lc(2241)		-- GSR 2 port SONET dual SRP/POS OC-48c/STM-16, POS Mode, Single Mode, Long Reach, LC Connector card
			,gsr-e48-pos-qoc12-mm-sr-sc(2243)	-- GSR edge48 Quad OC-12 (concanenated) POS card, Multi Mode (fiber), Short Reach, SC connector
			,gsr-gefe(2244)				-- Modular Gigabit/Fast Ethernet card for GSR
			,gsr-pa-1ge(2245)			-- 1 Port Gigabit Ethernet Port Adapter Of Modular Gigabit/Fast Ethernet card for GSR
			,gsr-pa-3ge(2246)			-- 3 Port Gigabit Ethernet Port Adapter Of Modular Gigabit/Fast Ethernet card for GSR
			,gsr-pa-24fe(2247)			-- 24 Port Fast Ethernet Port Adapter Of Modular Gigabit/Fast Ethernet card for GSR
			,gsr-e48-atm-4oc12-sm-ir-sc(2248)	-- Edge Engine 48, ATM, 4 ports OC12/STM4, Single Mode, Intermediate Reach, SC connector
			,gsr-e48-atm-4oc12-mm-sr-sc(2249)	-- GSR, Edge Engine 48, ATM, 4 ports OC12/STM4, Multi Mode, Short Reach, SC connector
			,lm-1fe-txcp(2253)			-- 1 port Fast Ethernet RJ-45 connector back card with co-processor assist for the MGX8800 RPM PR module
			,lm-smfir-8oc3c(2254)			-- 8 port, 155Mbps, SMFIR-8-155LC/C (Intermediate Reach) Back Card, LC Connector
			,lm-smflr-8oc3c(2255)			-- 8 port, 155Mbps, SMFLR-8-155LC/C (Long Reach) Back Card, LC Connector
			,lm-mmf-8oc3c(2256)			-- 8 port, 155Mbps, MMF-8-155C Back Card, LC Connector
			,lm-smfir-1oc3(2257)			-- 1 port, 155Mbps, SMFIR-1-155 (Intermediate Reach) Back Card
			,lm-smflr-1oc3(2258)			-- 1 port, 155Mbps, SMFLR-1-155 (Long Reach) Back Card
			,lm-smb-1stm1(2259)			-- MGX SMB 1 port STM1 Back Card
			,lm-scsi2b-2hssi(2260)			-- Two HSSI SCSI-2/B Back Card
			,lm-12in1-8s(2261)			-- 12In1-8s Back Card
			,lm-smb-6e3(2262)			-- 6 E3 ports SMB Back Card
			,lm-combo-t3e3-oc3(2263)		-- PXM1E-COMBO-T3E3-155'S Back Card supporting 8 T3/E3 ports and 4 OC3 ports
			,lm-rj48-16t1e1(2264)			-- Sixteen T1/E1 RJ-48 Back Card
			,lm-smf-ir-2oc12c(2265)			-- 2 port, 622Mbps, SMFIR-2-622LC/C (Intermediate Reach) Back Card, LC Connector
			,lm-smf-lr-2oc12c(2266)			-- 2 port, 622Mbps, SMFLR-2-622LC/C (Long Reach) Back Card, LC Connector
			,cat355024-mmf(2267)			-- Catalyst 3550 24 10/100Mbps Multi Mode Fiber ports + 2 Gig uplinks fixed configuration Layer 2/Layer 3 Ethernet Switch
			,ssrp-e48-2oc12-sm-ir(3008)		-- GSR 2 port SONET based SRP OC-12c/STM-4 Single mode Intermediate reach line card
			,ssrp-e48-2oc12-sm-xr(3009)		-- GSR 2 port SONET based SRP OC-12c/STM-4 Single mode Extented reach line card
			,ssrp-e48-1oc12-sm-ir(3010)		-- GSR 1 port SONET based SRP OC-12c/STM-4 Single mode Intermediate reach line card
			,ssrp-e48-1oc12-sm-xr(3011)		-- GSR 1 port SONET based SRP OC-12c/STM-4 Single mode Extented reach line card
			,gsr-csc12816(3012)			-- GSR 12816 Clock Scheduler Card
			,gsr-csc12810(3013)			-- GSR 12810 Clock Scheduler Card
			,gsr-sfc12810(3014)			-- GSR 12810 Switch Fabric Card
			,gsr-sfc12816(3015)			-- GSR 12816 Switch Fabric Card
			,gsr-sip-600(3016)			-- ISE 10G SPA Interface Card
			,gsr-2oc192-pos(3019)			-- GSR 2 Port Packet Over Sonet OC-192c/STM-64 line card
			,gsr-8oc48-pos(3020)			-- GSR 8 Port Packet Over Sonet OC-48/STM-16 line card
			,gsr-6ds3e3-smb(3028)			-- GSR 6 Port DS3/E3 Clear Channel, SMB Connector line card
			,gsr-6ds3e3ct3-smb(3029)		-- GSR 6 Port DS3/E3 Clear channel and/or Channelized to DS1/E1, SMB Connector line card
			,gsr-2oc3-chds1ds3e3-sm-ir-sc(3030)	-- GSR 2 Port STM-1/OC-3 Channelized to DS3/E3/DS1/E1, Single Mode, Intermediate Reach and SC Connector line card
			,gsr-service(3043)		-- GSR Service Card
			,gsr-sip-601(3044)		-- ISE 10G SPA Interface Card
			,gsr-sip-501(3045)		-- ISE 5G SPA Interface Card
			,gsr-sip-401(3046)		-- ISE 2.5G SPA Interface Card
			,gsr-ssrp2-oc48-lc(3047)	-- GSR 2 port SONET based SRP OC-48c/STM-16 (SFP) LC
			,vism-pr-8e1(3050)			-- Voice Interworking Service Module Premium Card (VISM-PR) with 8 E1 ports
			,vxsm-4oc3(3051)			-- Voice switch service module, 4 port OC3/STM-1 compliant
			,mgx-srm-4oc3(3052)			-- MGX88xx voice service redundancy module, used to providing 1:N redundancy for 4 OC3

			,nm-ceoip-4Serial(4000)			-- Four port Serial Interface Circuit Emulation over IP network module
			,nm-1a-oc3mm-ep(4001)			-- Enhanced Performance ATM OC3, multimode network module
			,nm-1a-oc3smi-ep(4002)			-- Enhanced Performance ATM OC3, intermediate reach single mode network module
			,nm-1a-oc3sml-ep(4003)			-- Enhanced Performance ATM OC3, long reach single mode network module
			,hwic-1ge-sfp(4014)			-- Single port Gigabit Ethernet high-speed WAN interface card (HWIC) with Small Formfactor Pluggable (SFP) transceive
			,hd-dsp(4015)				-- 5510 Digital Signal Processor on NM-HD-1V,NM-HD-2V and NM-HD-2VE
			,nm-8am-v2(4020)			--  8 Port Analog Modem Network Module Version 2
			,nm-16am-v2(4021)			--  16 Port Analog Modem Network Module Version 2
			,cpu-c2811-2fe(4023)			--  2811 Motherboard with two integrated fast ethernets and integrated VPN
			,cpu-c2821-2ge(4024)			--  2821 Motherboard with two integrated gigabit ethets and integrated VPN
			,cpu-c2851-2ge(4025)			--  2851 Motherboard with two integrated gigabit ethernets and integrated VPN
			,hwic-serial4t(4026)			--  High Speed Wan Interface Card with 4 serial ports(HWIC-4T)
			,hwic-serial4as(4027)			--  High Speed Wan Interface Card with 4 low speed sync/async serial ports(HWIC-4A/S)
			,hwic-serial8as(4028)			--  High Speed Wan Interface Card with 8 low speed RS232 sync/async serial ports(HWIC-8A/S)
			,hwic-serial8a(4029)			--  High Speed Wan Interface card with 8 RS232 async port(HWIC-8A)
			,hwic-serial16a(4030)			--  High Speed Wan Interface card with 16 RS232 async ports(HWIC-16A)
			,nm-1a-oc3-pom(4031)			--  Single port ATM OC3 network module with POM
			,hwic-1docsis20-cm(4036)		--  High Speed Wan Interface card with 1 DOCSIS 2.0 cable modem port(HWIC-1CM)
			,nm-8ce1t1-pri(4038)			--  8 port T1/E1 clear channel and channelized NM
			,hwic-4t1e1(4039)			--  4 port T1/E1 clear channel HWIC
			,hwic-2ce1t1-pri(4040)			--  2 port T1/E1 channelized/PRI HWIC
			,hwic-1ce1t1-pri(4041)                  --  1 port T1/E1 channelized/PRI HWIC
			,nme-16es-1ge-no-pwr(4042)		--  16 Ports next generation 10BaseT/100BaseTx EtherSwitch module with 1GE
			,nme-x-24es-1ge-no-pwr(4043)		--  24 Ports next generation 10BaseT/100BaseTx EtherSwitch module with 1GE
			,nme-xd-48es-2ge-no-pwr(4044)		--  48 Ports next generation 10BaseT/100BaseTx EtherSwitch module with 2GE
			,nme-xd-24es-2st-no-pwr(4045)		--  24 Ports next generation 10BaseT/100BaseTx EtherSwitch module with 2 stacking ports
			,hwic-1docsis20-cm-ej(4046)	--  High Speed Wan Interface card with 1 Euro-DOCSIS/J-DOCSIS 2.0 cable modem port(HWIC-1CM)
			,cat6k-ws-sup720(4050)		-- Catalyst 6500 Supervisor Module 720 CPU board
			,cat6k-ws-sup720-base(4051)	-- Catalyst 6500 Supervisor Module 720 base board
			,cat6k-wsx-6802-10ge(4052)        -- Catalyst 6500 2 port 10 GE
			,cat6k-wsx-6832-sfp(4053)        -- Catalyst 6500 32 port 1000Base FX (SFP GBIC)
			,cat6k-wsx-6748-getx(4054)        -- Catalyst 6500 48 port 10/100/1000 (RJ-45)
			,cat6k-wsx-6704-10ge(4055)        -- Catalyst 6500 4 port 10 GE
			,cat6k-wsx-6748-sfp(4056)        -- Catalyst 6500 48 port 1000Base FX (SFP GBIC)
			,cat6k-wsx-6724-sfp(4057)        -- Catalyst 6500 24 port 1000Base FX (SFP GBIC)
			,cat6k-wsf-6k-pfc(4058)        --  Catalyst 6500 L3 switching engine
			,cat6k-wsf-6k-pfc2(4059)        -- Catalyst 6500 L3 switching engine II
			,cat6k-wsf-6k-dfc(4060)        -- Catalyst 6500 distributed switching engine
			,cat6k-wsf-6k-pfc3a(4061)        -- Catalyst 6500 Centralized L3 switching engine IIIa
			,cat6k-wsf-6k-dfc3a(4062)        -- Catalyst 6500 Distributed L3 switching engine IIIa
			,cat6k-wsx-6148-ge-tx(4063)	-- Catalyst 6000 48 port10/100/1000BaseT(RJ-45) module
			,cat6k-wsx-6148-rj21(4064)	-- Catalyst 6000 48 port10/100BaseTX(RJ-21) module
			,cat6k-wsx-6148-rj45(4065)	-- Catalyst 6000 48 port10/100BaseTX(RJ-45) module
			,cat6k-wsx-6548-getx(4066)	-- Catalyst 6500 48 port 10/100/1000 (RJ-45)
			,cat6k-wsf-6700-dfc3a(4067)	-- Catalyst 6500 Distributed L3 switching engine IIIa
			,cat6k-wsx-6324-100fx-sm(4068)	-- 24-port 100FX single mode MT-RJ with 128K per-port packet buffer
			,cat6k-ws-svc-idsm2(4069)       -- Catalyst 6500 Intrusion Detection Module
			,cat6k-ws-svc-idsupg(4070)      -- Catalyst 6500 IDS 2 accelerator board
                        ,cat6k-wsx-6148x2-rj45(4071)      -- Catalyst 6500 96-port 10/100BaseTX (RJ-45) module
                        ,cat6k-wsf-6k-fe48x2-af(4072)   -- Catalyst 6500 Inline voice daughter card
			,cat6k-wsf-6k-fe48-af(4073)	-- Cat6k voice daughter cards
			,cat6k-wsf-6k-ge48-af(4074)	-- Cat6k voice daughter cards
			,cat6k-wsf-6k-vpwr-ge(4075)	-- Cat6k voice daughter cards
			,cat6k-wsf-6700-cfc(4076)	-- Catalyst 6500 centralized Forwarding Card
			,cat6k-ws-svc-wlan1-k9(4077)	-- Catalyst 6500 Wireless LAN module
			,cat6k-ws-svc-aon1(4078)	-- Application-Oriented Networking (AON) Service Module
			,cat6k-ws-sup32-ge(4079)	-- Catalyst 6500 Supervisor Module with 8 Gigabit Ethernet SFP uplink ports
			,cat6k-ws-sup32-10ge(4080)	-- Catalyst 6500 Supervisor Module with 2 10-GE uplink ports
			,cat6k-msfc2a(4081)	-- Multilevel Switching   Feature Card Version 2a for the Catalyst 6000 series
			,cat6k-ws-6340-sup(4082)	-- ME6340 Supervisor
			,cat6k-ws-6340-lca(4083)	-- ME6340 48 port ADSL 2/2+ Annex A Module
			,cat6k-ws-6340-lcb(4084)	-- ME6340 48 port ADSL 2/2+ Annex B Module
			,cat6k-mec-6524gs-8s(4085)	-- Cisco ME 6524 module with 24 port SFP and 8 SFP uplinks
			,cat6k-mec-6524gt-8s(4086)	-- Cisco ME 6524 module with 24 port 10/100/1000BaseT and 8 SFP uplinks
			,cat6k-mec-6524-msfc2a(4089)	-- Catalyst 6524 and 6724 Multilevel Switching Feature Card Version 2
			,cat6k-mec-6524-pfc3c(4090)	-- Catalyst 6524 and 6724 Policy feature card 3C
			,cat6k-wsx-6196-rj21(4091)	-- Catalyst 6500 96 port 10/100BaseTX (RJ-21) module
			,cat6k-wsx-6148-fe-sfp(4092)	-- Catalyst 6500 48 port 100Base-X SFP module
			,cat6k-wsx-6148a-getx(4093)	-- Catalyst 6500 48 port 10/100/1000BaseTX (RJ-45) module
			,cat6k-wsx-6148a-rj45(4094)	-- Catalyst 6500 48 port 10/100BaseTX (RJ-45) module
			,cat6k-wsg-6483(4095)	-- Catalyst 6500 10GE-ER Serial 1550nm extended reach module
			,cat6k-wsg-6485(4096)	-- Catalyst 6500 10GE-LX4 Campus 1310nm WWDM long haul/short reach module
			,cat6k-wsg-6488(4097)	-- Catalyst 6500 10GE-LR Serial 1310nm long haul module
			,cat6k-wsg-6489(4098)	-- Catalyst 6500 10GE-SX4 850nm WWDM short reach module
			,cat6k-ws-svc-webvpnk9(4099)  -- Catalyst 6500 Web VPN Module

			,oc3-sfp(4100)			-- Oc3 Small Form Factor Pluggable Optics(SFP)
			,oc12-sfp(4101)			-- Oc12 Small Form Factor Pluggable Optics(SFP)
			,osm-2oc48-pos-ss(4102)		-- Optical Service Module, 2-Port OC48 POS, Single-mode, Short-reach with 4 Gigabit Ethernet ports
			,osm-2oc48-pos-si(4103)			-- Optical Service Module, 2-Port OC48 POS Single-mode, Intermediate-reach with 4 Gigabit Ethernet ports
			,osm-2oc48-pos-sl(4104)		-- Optical Service Module, 2-Port OC48 POS Single-mode, Long-reach with 4 Gigabit Ethernet ports
			,osm-1oc48-srp-ss(4105)		-- Optical Service Module, 1-Port OC48 SONET based SRP,Single-mode, Short-reach with 4 Gigabit Ethernet ports
			,osm-1oc48-srp-si(4106)		-- Optical Service Module, 1-Port OC48 SONET based SRP,Single-mode, Intermediate-reach with 4 Gigabit Ethernet ports
			,osm-1oc48-srp-sl(4107)		-- Optical Service Module, 1-Port OC48 SONET based SRP,Single-mode, Long-reach with 4 Gigabit Ethernet ports
			,oc48-sfp(4108)			-- OC48 Small Form Factor Pluggable Optics(SFP)
			,cat375048-ps(4111)		-- 48 10/100 In-Line Power Ethernet ports + 2 Gigabit Ethernet SFP ports Layer 2/Layer 3 Module.(SFP Small Form factor Plugable)
			,cat375024-ps(4112)		-- 24 10/100 In-Line Power Ethernet ports + 4 Gigabit Ethernet SFP ports Layer 2/Layer 3 Module.(SFP Small Form factor Plugable)
			,pwr-ac-465w(4113)			-- Cisco 465W AC Power Supply.
			,base-sx-1000-sfp(4114)			-- Short wavelength gigabit ethernet SFP.
                        ,base-lx-1000-sfp(4115)                 -- Long wavelength gigabit ethernet SFP.
			,base-t-1000-sfp(4116)			-- copper gigabit ethernet SFP.
			,base-zx-1000-sfp(4117)			-- Extended reach gigabit ethernet SFP.
			,cwdm-1470-sfp(4118)			-- 1470nm color coded CWDM SFP.
			,cwdm-1490-sfp(4119)			-- 1490nm color coded CWDM SFP.
			,cwdm-1510-sfp(4120)			-- 1510nm color coded CWDM SFP.
			,cwdm-1530-sfp(4121)			-- 1530nm color coded CWDM SFP.
			,cwdm-1550-sfp(4122)			-- 1550nm color coded CWDM SFP.
			,cwdm-1570-sfp(4123)			-- 1570nm color coded CWDM SFP.
			,cwdm-1590-sfp(4124)			-- 1590nm color coded CWDM SFP.
			,cwdm-1610-sfp(4125)			-- 1610nm color coded CWDM SFP.
			,base1000-lh-sfp(4126)			-- long haul gigabit ethernet SFP.
			,base1000-cx-sfp(4127)			-- copper wire gigabit ethernet SFP.
			,oc192-xfp-smsr1(4128)			-- OC192 XFP Single Mode Short Reach 1 (2km)
			,oc192-xfp-smir2(4129)			-- OC192 XFP Single Mode Intermediate Reach 2 (40km)
			,oc192-xfp-smlr2(4130)			-- OC192 XFP Single Mode Long Reach 2 (80km)
			,cable50cm-sfp(4131)			-- SFP patch cable, 50cm (centimeters)
			,pwr-ac-125w(4132)			-- Cisco 125W AC Power Supply
			,pwr-ac-60w(4133)			-- Cisco 60W AC Power Supply
			,sr-1oc48-sfp(4134)			-- 1-port OC48 Small form Factor (SFP) Short Reach (SR)
			,ir-1oc48-sfp(4135)			-- 1-port OC48 Small form Factor (SFP) Intermediate Reach (SR)
			,lr2-1oc48-sfp(4136)			-- 1-port OC48 Small form Factor Pluggable (SFP) Long Reach (LR-2)
			,pwr-ac-100w(4137)			-- Cisco 100 Watt DC power supply
			,pwr-dsCAD-6000W(4138)			-- 6000W AC Power Supply
			,pwr-cat3750-ac210w12v(4139)			-- Cisco Catalyst 3750 AC power Supply  210 Watt, 12V DC
			,pwr-cat3750-ac375w48v(4140)			-- Cisco Catalyst 3750 AC power Supply  375 Watt, -48V DC
			,pwr-crs116-power-shelf-ac-delta(4141)			-- Cisco CRS-1 Series AC Delta Power Shelf for 16 Slots Line Card Chassis
			,pwr-crs116-power-shelf-ac-wye(4142)			-- Cisco CRS-1 Series AC Wye Power Shelf for 16 Slots Line Card Chassis
			,pwr-crs116-power-shelf-dc(4143)			-- Cisco CRS-1 Series DC Power Shelf for 16 Slots Line Card Chassis
			,pwr-crs116-ac-rectifier(4144)			-- Cisco CRS-1 Series AC Power Rectifier for 16 Slot Line Card Chassis and Fabric Card Chassis
			,pwr-crs116-dc-pem(4145)			-- Cisco CRS-1 Series DC Power Entry Module for 16 Slot Line Card Chassis and Fabric Card Chassis
			,pwr-ds-cac-3000w(4146)				-- Cisco MDS 9513 Power Supply - DS-CAC-3000W
			,pwr-6000-dc(4147)			-- 6000W DC Power Supply
			,dwdm-3033-sfp(4148)			-- MOD,XCVR,2.5Gb/s,1530.33nm,SM,LR2,3.3V,0 to 70C,LC,SFP,DIGITAL DIAGS FIM32160/201W59
			,dwdm-3112-sfp(4149)			-- MOD,XCVR,2.5Gb/s,1531.12nm,SM,LR2,3.3V,0 to 70C,LC,SFP,DIGITAL DIAGS FIM32160/201W58
			,dwdm-3190-sfp(4150)			-- MOD,XCVR,2.5Gb/s,1531.90nm,SM,LR2,3.3V,0 to 70C,LC,SFP,DIGITAL DIAGS FIM32160/201W57



			,spa-1p-oc192-pos-rpr-vsr(4201)		-- 1-port OC192c/STM64c POS/RPR VSR Optics Shared Port Adapter (SPA-OC192POS-VSR)
			,spa-8p-ct1e1(4202)			-- 8-port Channelized T1/E1 to DS0 Shared Port Adapter (SPA-8XCHT1/E1)
			,spa-2p-ct3(4203)			-- 2-port Channelized T3 to DS0 Shared Port Adapter (SPA-2XCT3/DS0)
			,spa-4p-ct3(4204)			-- 4-port Channelized T3 to DS0 Shared Port Adapter (SPA-2XCT3/DS0)
			,hwic-4fe(4206)				--  HWIC ESW 4 Port Fast Ethernet Cards
			,hwic-9fes(4207)			--  HWIC 9 Port Fast Ethernet Switch Cards
			,hwic-4fes(4208)			--  HWIC 4 Port Fast Ethernet Switch Cards
			,hwic-4ilp(4209)			--  4-Port HWIC-ESW Inline Power Daughter Card
			,hwic-9ilp(4210)			--  9-Port HWIC-ESW Inline Power Daughter Card
			,spa-10p-ge(4211)			--  10-port Gigabit Ethernet Shared Port Adapter (SPA-10X1GE)
			,spa-1p-10ge-xfp(4212)			--  1-port 10 Gigabit Ethernet Shared Port Adapter XFP based (SPA-1XTENGE-XFP)
			,spa-5p-ge(4213)			--  5-port Gigabit Ethernet Shared Port Adapter (SPA-5X1GE)
                        ,hwic-vdsl-pots(4214)                   --  VDSL and ADSL modes over POTS(HWIC-1VDSL)
                        ,hwic-vdsl-isdn(4215)                   --  VDSL and ADSL modes over ISDN(HWIC-1VDSLI)
                        ,ws-ipsec-3(4216)                     --  IPSec Shared Port Adapter with DES/3DES/AES (WS-IPSEC-3)
                        ,spa-2p-t3e3-serial(4217)		--  2-port T3/E3 Serial Shared Port Adapter (SPA-2XT3/E3)
			,spa-4p-t3e3-serial(4218)		--  4-port T3/E3 Serial Shared Port Adapter (SPA-4XT3/E3)
			,spa-2p-ge(4219)			--  2-port Gigabit Ethernet Shared Port Adapter (SPA-2X1GE)
			,hwic-dot11-abg(4220)			--  802.11 a/b/g Access Point
			,hwic-dot11-bg(4221)			--  802.11 b/g Access Point until Jul 2004, contact pgiriraj
			,spa-1p-choc3-stm1(4222)		--  1-port Channelized STM1/OC3 to DS0 Shared Port Adapter (SPA-1XCHSTM1/OC3)
			,aim-vpn-bp(4223)			--  VPN Encryption Advanced Interface Module - Base Performance
			,aim-vpn-ep(4224)			--  VPN Encryption Advanced Interface Module - Enhanced Performance
			,nm-vpn-mp(4225)			--  VPN Encryption Network Module - Mid Performance
			,aim-vpn-hp(4226)			--  VPN Encryption Advanced Interface Module - High
			,aim-vpn-bp2(4227)			--  VPN Encryption Advanced Interface Module - Base Performance (version 2)
			,aim-vpn-ep2(4228)			--  VPN Encryption Advanced Interface Module - Enhanced Performance (version 2)
			,aim-vpn-hp2(4229)			--  VPN Encryption Advanced Interface Module - High Performance (version 2)
			,aim-vpn-bp2-plus(4230)			--  VPN Encryption Advanced Interface Module - Base Performance (version 2 Plus)
			,aim-vpn-ep2-plus(4231)			--  VPN Encryption Advanced Interface Module - Enhanced Performance (version 2 Plus)
			,aim-vpn-hp2-plus(4232)			--  VPN Encryption Advanced Interface Module - High Performance (version 2 Plus)
			,hwic-adsl-bri-pots(4233)			--  ADSL over POTS and BRI S/T
			,hwic-adsl-bri-isdn(4234)			--  ADSL over ISDN and BRI S/T
			,hwic-adsl-isdn(4235)			--  ADSL over ISDN
			,hwic-adsl-pots(4236)			--  ADSL over POTS
			,spa-2p-oc48-pos-rpr-hh(4237)			--  2-Port OC48c/STM16c POS/RPR Shared Port Adapter (SPA-2XOC48POS/RPR)
			,mds-ds-x9530-sf2-k9(4238)			--  DS-X9530-SF2-K9  - Sup-2, Supervisor/Fabric module
			,mds-ds-x9112(4239)			--  DS-X9112-  12-port Fibre Channel switching module
			,mds-ds-x9124(4240)			--  DS-X9124-  24-port Fibre Channel switching module
			,mds-ds-x9148(4241)			--  DS-X9148-  48-port Fibre Channel switching module
			,mds-ds-x9704(4242)			--  DS-X9704-  4-port Fibre Channel switching module
			,nm-cue-ec(4244)			--  Service Engine Network Module with 512MB RAM
			,mds-ds-13-slt-fab1(4245)			--  Cisco MDS 9513 Fabric 1 module
			,mds-ds-c9513-cl(4246)			--  Cisco MDS 9513 clock module - DS-C9513-CL
			,dfc-dl108(4247)			--  These cards are similar to DFC-NP108 and DFC-NP60 used on AS5400 platforms, but they are capable of only dial calls.
			,dfc-dl60(4248)			--  These cards are similar to DFC-NP108 and DFC-NP60 used on AS5400 platforms, but they are capable of only dial calls.
			,nm-wlan-controller(4249)			--  Wireless LAN controller Network Module

			,c356024-ps(4250)			-- 24 10/100 In-Line Power Ethernet ports + 2 Gigabit Ethernet SFP ports Layer 2/Layer 3 Module.(SFP Small Form factor Pluggable)
			,c356048-ps(4251)			-- 48 10/100 In-Line Power Ethernet ports + 4 Gigabit Ethernet SFP ports Layer 2/Layer 3 Module.(SFP Small Form factor Pluggable)
			,c356024-ts(4252)			-- Catalyst 3560 24 Ethernet 10/100 port + 2 Ethernet Gigabit SFP ports module. (SFP: Small Form factor Pluggable)
			,c356048-ts(4253)			-- Catalyst 3560 48 Ethernet 10/100 port + 4 Ethernet Gigabit SFP ports module. (SFP: Small Form factor Pluggable)
			,cat3560e-24-td(4254)			-- Catalyst 3560E 24 10/100/1000 ports + 2 TenGigabit Ethernet (X2)ports
			,cat3560e-48-td(4255)                   -- Catalyst 3560E 24 10/100/1000 ports + 2 TenGigabit Ethernet (X2) ports
			,cat3560e-24-pd(4256)			-- Catalyst 3560E 24 10/100/1000 Power over Ethernet ports + 2 TenGigabit Ethernet (X2) ports
			,cat3560e-48-pd(4257)			-- Catalyst 3560E 48 10/100/1000 Power over Ethernet ports + 2 TenGigabit Ethernet (X2) ports
                        ,nm-wae(4258)                           --  Wan Application Engine Network Module
                        ,cat3560e-12d(4259)                     -- Catalyst 3560E 12 Ten GE (X2) ports
                        ,cat3560e-12-sd(4260)                   -- Catalyst 3560E, 12 SFP Gigabit Ethernet ports + 2 TenGigabit Ethernet (X2) ports

			,c375024-me(4300)                       -- Metro Ethernet Catalyst 3750 Module. 24-10/100 + 2 SFP (Small Formfactor Pluggable) ports for downlinks
			,cat375024ws(4301)                       -- Catalyst 3750 24 10/100 ports + 4 Gigabit SFP ports module. (SFP: Small Form factor Pluggable)
			,cat375024fs(4302)                       -- Catalyst 3750 24 100BaseFX ports + 2 Ethernet Gigabit SFP ports fixed configuration Layer 2/Layer 3 Ethernet switch.   (SFP:Small Formfactor Pluggable)
			,c3750-ge12-sfp-dc(4303)                       -- Catalyst 3750 12 Gigabit Ethernet SFP (small Form Factor Plugable) ports
			,cat3750g-24-ws(4304)			-- Catalyst 3750 Unified Access Switch with 24 10/100/1000 Power over Ethernet ports + 2 Gigabit Ethernet SFP ports and integrated Wireless Controller. (SFP Small Form factor Pluggable)
			,cat3750e-24-td(4305)			-- Catalyst 3750E 24 10/100/1000 ports + 2 TenGigabit Ethernet (X2) ports
			,cat3750e-48-td(4306)                   -- Catalyst 3750E 48 10/100/1000 ports + 2 TenGigabit Ethernet (X2) ports
			,cat3750e-48-pd(4307)                   -- Catalyst 3750E 48 10/100/1000 Power over Ethernet ports + 2 TenGigabit Ethernet (X2) ports
			,cat3750e-24-pd(4308)			-- Catalyst 3750E 24 10/100/1000 Power over Ethernet ports + 2 TenGigabit Ethernet (X2) ports



			,pvdmII-12dm(4350)			-- 12-port digital modem PVDM II (Packet Voice Data Module - II)
			,pvdmII-24dm(4351)			-- 24-port digital modem PVDM II (Packet Voice Data Module - II)
			,pvdmII-36dm(4352)			-- 36-port digital modem PVDM II (Packet Voice Data Module - II)
			,vwic-2T1E1-ran(4356)			-- 2-Port T1/E1 WAN interface card with protection relays and 3GPP RAN Optimization support
			,ce-scsi-2636(4357)			-- SCSI daughter card used by Content Engine Modules for 26xx and 36xx series platforms
			,ce-ide-2636(4358)			-- IDE  daughter card used by Content Engine Modules for 26xx and 36xx series platforms
			,c7300-nse150-db(4359)			-- Network Services Engine 150 Daughtercard for the Cisco 7304 platform
			,vic3-em2(4360)				-- 3rd generation two port EM voice interface daughtercard
			,vic3-fxs-did2(4361)			-- 3rd generation two port FXS DID voice interface daughtercard
			,vic3-fxs-did4(4362)			-- 3rd generation four port FXS DID voice interface daughtercard
			,hda-em3-fxs-did8(4363)			-- 3rd generation eight port FXS DID voice interface daughtercard
			,cm-1docsis20-dc(4364)			-- One port DOCSIS 2.0 cable modem daughter card
			,cm-1docsis20-dc-ej(4365)		-- One port Euro-DOCSIS/J-DOCSIS 2.0 cable modem daughter card
                        ,asm-m2900-top(4366)                    -- Timing over Packet Accessory Serivce Module for the Cisco MWR 2900 Series Mobile Wireless Routers
	                ,vic3-fxs-e-did2(4367)                  -- 3rd generation two port FXS Extended DID voice interface
                        ,pvdm3-64(4370)                         -- PVDM3-64 (packet voice DSP module) is the next-generation Digital Signal Processor(DSP) module supporting high-density voice and video
                        ,pvdm3-32(4371)                         -- PVDM3-32 (packet voice DSP module) is the next-generation Digital Signal Processor(DSP) module supporting high-density voice and video
                        ,pvdm3-128(4372)                        -- PVDM3-128 (packet voice DSP module) is the next-generation Digital Signal Processor(DSP) module supporting high-density voice and video
                        ,pvdm3-192(4373)                        -- PVDM3-192 (packet voice DSP module) is the next-generation Digital Signal Processor(DSP) module supporting high-density voice and video
                        ,pvdm3-256(4374)                        -- PVDM3-256 (packet voice DSP module) is the next-generation Digital Signal Processor(DSP) module supporting high-density voice and video

                        ,nm-2838(4375)                          -- Integrated Service Engine daughter card used by Service Modules for 28xx and 38xx series platforms
                        ,pano-2838(4376)                        -- Video Service Engine daughter card used by Service Modules for 28xx and 38xx series platforms
                        ,vwic3-mft4-t1e1(4379)                  -- VWIC3-4MFT-T1E1 (4 Port) RJ-48 Multi-Flex Trunk -T1/E1
                        ,vwic3-mft1-t1e1(4380)                  -- VWIC3-1MFT-T1E1 (1 Port) RJ-48 Multi-Flex Trunk -T1/E1
                        ,vwic3-mft1-g703(4381)                  -- VWIC3-1MFT-G703 (1 Port) RJ-48 Multi-Flex Trunk - G.703
                        ,vwic3-mft2-t1e1(4382)                  -- VWIC3-2MFT-T1E1 (2 Port) RJ-48 Multi-Flex Trunk -T1/E1
                        ,vwic3-mft2-g703(4383)                  -- VWIC3-2MFT-G703 (2 Port) RJ-48 Multi-Flex Trunk - G.703
                        ,prp3-smdc(4384)                        -- New daughter card for the route processor card on c12000. Please refer to EDCS-883053 for more details
                        ,vg3x0-ob-24fxs(4385)                   -- Dughter card for VG310 and VG320
                        ,ppvdm3-128(4386)                       -- 128-channel high-density voice and video DSP module
                        ,ppvdm3-16(4387)                        -- 16-channel high-density voice and video DSP module
                        ,ppvdm3-192(4388)                       -- 192-channel high-density voice and video DSP module
                        ,ppvdm3-256(4389)                       -- 256-channel high-density voice and video DSP module
                        ,ppvdm3-32(4390)                        -- 32-channel high-density voice and video DSP module
                        ,ppvdm3-64(4391)                        -- 64-channel high-density voice and video DSP module
                        ,pvic3-em2(4392)                        -- Two-port Voice Interface Card - E and M
                        ,pvic3-fxs2-did(4393)                   -- Two-Port Voice Interface Card- FXS and DID
                        ,pvic3-fxs4-did(4394)                   -- Four-Port Voice Interface Card - FXS and DID
                        ,pvwic3-mft1-g703(4395)                 -- 1-Port 3rd Gen Multiflex Trunk Voice/WAN Int. Card - G.703
                        ,pvwic3-mft1-t1e1(4396)                 -- 1-Port 3rd Gen Multiflex Trunk Voice/WAN Int. Card - T1/E1
                        ,pvwic3-mft2-g703(4397)                 -- 2-Port 3rd Gen Multiflex Trunk Voice/WAN Int. Card - G.703
                        ,pvwic3-mft2-t1e1(4398)                 -- 2-Port 3rd Gen Multiflex Trunk Voice/WAN Int. Card - T1/E1
                        ,pvwic3-mft4-t1e1(4399)                 -- 4-Port 3rd Gen Multiflex Trunk Voice/WAN Int. Card - T1/E1



			,rsp720Base(4400)			-- C7600 Router Switch Processor Module 720 Base board
			,rsp32GEBase(4401)			-- C7600 Router Switch Processor Module 32 GE Base board
			,rsp3210GEBase(4402)			-- C7600 Router Switch Processor Module 32 10 GE Base board
			,rsp720(4403)			-- C7600 Router Switch Processor Module 720 CPU board
			,rsp32(4404)			-- C7600 Router Switch Processor Module 32 CPU board
			,rsp720MsfcNaboo(4405)		-- RSP720 Multilevel Switching Feature Card
                        ,rsp72010GEBase(4406)           -- C7600 Route Switch Processor Module 720 - 10 GE Base board
                        ,cat6k-ws-f6k-dfc4-axl(4407)    -- Catalyst 6500 Distributed Forwarding Card 4A XL
                        ,cat6k-ws-x6148e-ge-tx(4411)    -- Catalyst 6500 48-port IEEE802.3at compliant Power over Ethernet Plus module
                        ,cat6k-76-es-t-xc-20g(4426)         -- 7600 ES+ 1x10G 10x1G : C7600 ES+1x10GE,10x1GE Low queue Combo Link Daughter card.
                        ,cat6k-es-t-xc-40g(4427)            -- 7600 ES+ 2x10G 20x1G : C7600 ES+2x10GE,20x1GE Low queue Combo Link Daughter card.
                        ,cat6k-es-t(4428)                   -- C7600 ES+ Low Queue Baseboard
                        ,cat6k-est-8tg(4429)                -- 76-ES+T-8TG : 7600 ES+ 8x10G HD Low queue link Daughter card
                        ,cat6k-esxt-8tg(4430)               -- 7600 ES+ 8x10G HD High-Queue link Daughter card



			,wic-t1-csudsu-v2(4450)			--  Wan Interface Card with 1 Fractional T1 CSU/DSU port, version 2
			,spa-8xfe-tx(4451)			--  8 Port Fast Ethernet Shared Port Adapter
			,nm-integrated-service-engine(4452)			-- Integrated Service Engine for Modular and Integrated Services Routers
			,nm-wa-engine(4453)			-- A network module sittig on the 26xx/37xx/28xx/38xx platforms and running wan application services on linux. The module will be called as wan-application-engine in CLI.
			,spa-2p-ge-v2(4454)			-- 2-port Gigabit Ethernet Shared Port Adapter V2 (SPA-2X1GE-V2)
			,spa-5p-ge-v2(4455)			-- 5-port Gigabit Ethernet Shared Port Adapter V2 (SPA-5X1GE-V2)
			,spa-8p-ge-v2(4456)			-- 8-port Gigabit Ethernet Shared Port Adapter V2 (SPA-8X1GE-V2)
			,spa-10p-ge-v2(4457)			-- 10-port Gigabit Ethernet Shared Port Adapter V2 (SPA-10X1GE-V2)
			,spa-1p-10ge-xfp-v2(4458)			-- 1-port 10 Gigabit Ethernet Shared Port Adapter V2 (SPA-1X10GE-L-V2)
			,spa-8xfe-tx-v2(4459)			--  8-port Fast Ethernet Shared Port Adapter V2 (SPA-8X1FE-TX-V2)
			,crs14-oc192-ir-plim(4460)			-- Cisco CRS-1 Series 4xOC192/STM64 POS/DPT Interface Module/IR
			,spa-8x-ge(4461)			-- 8-Port Gigabit Ethernet Shared Port Adapter (SPA-8X1GE)
			,wic-1-shdsl-v3(4465)			-- WAN Interface Card - ATM (With multi line G.SHDSL module)
			,usb-flash(4466)			-- Universal Serial Bus (USB) Flash Disk
			,usb-token(4467)			-- Universal Serial Bus (USB) Token Disk
			,usb-hub(4468)				-- Universal Serial Bus (USB) Hub
			,v-enc-m(4469)                          -- Video Encoder Module for Modular and Integrated Services Router
			,usb-device(4470)			-- Generic Universal Serial Bus (USB) device
			,spa-1p-oc48-pos-sfp(4471)		-- 1-port OC48c/STM16c POS/RPR SFP Optics Shared Port Adapter (SPA-1XOC48POS/RPR)
			,spa-4p-oc48-pos-sfp(4472)		-- 4-port OC48c/STM16c POS/RPR SFP Optics Shared Port Adapter (SPA-4XOC48POS/RPR)
			,ip-ran-opt-4p(4473)			-- IP-RAN Optimization with four processors
			,aim-ips-1(4474)			-- Intrusion Detection Module for Access Routers 18xx
			,aim-ips-2(4475)			-- Intrusion Detection Module for Access Routers 28xx
			,aim-ips-3(4476)			-- Intrusion Detection Module for Access Routers 38xx
			,nm-cips(4477)				-- Intrusion Detection Module for Access Routers in NM form factor for 18xx, 28xx and 38xx family branch routers
			,hwic-1fe(4478)				-- HWIC-1FE is a 1-port FE on a HWIC interface
			,hwic-2fe(4479)				-- HWIC-2FE is a 2-port FE on a HWIC interface
			,hwic-bri-u-82912(4480)			-- HWIC-1B-U is a BRI U interface module that provides a single Basic Rate ISDN U WAN interface
			,hwic-bri-4b-s-t(4481)			-- HWIC-4B-S/T is a 4 port BRI S/T data only HWIC to replace the NM-4B-S/T and NM-8B-S/T modules
			,hwic-adsl-pots-annexm(4482)		-- ADSL Annex M over POTS
			,mds-ds-x9124-s2-k9(4484)		-- 24-port 1/2/4 Gig Supervisor Fabric Switch
			,cvr-x2-sfp(4485)			-- 2-port SFP port module in X2 form factor
			,spa-24p-ct1e1-cem-atm(4487)		-- 24-port Channelized T1/E1 ATM & Circuit Emulation Shared Port Adapter (SPA-24CHT1-CE-ATM)
			,spa-2p-ct3e3-cem-atm(4488)		-- 2-port Channelized T3/E3 ATM & Circuit Emulation Shared Port Adapter (SPA-2CHT3-CE-ATM)
			,spa-1p-choc3-cem-atm(4489)		-- 1-port Channelized OC3/STM-1 ATM & Circuit Emulation Shared Port Adapter (SPA-1CHOC3-CE-ATM)
			,mds-ds-ibmfc(4490)			-- Cisco 4Gb Fibre Channel Switch Module for IBM BladeCenter
			,mds-ds-hpfc(4493)			-- Fibre Channel Switch Module for HP BladeSystem
			,mds-ds-x9222i-k9-sup(4494)		-- DS-X9222i-K9 coco supervisor
			,aim-atm8(4495)				-- Advanced integration module for the MWR-1951-DC supporting the capacity to allow 8 Inverse Mux over ATM (IMA) groups
			,spa-4xt-serial(4496)			-- 4-port 12in1 Serial Shared Port Adapter (SPA-4XT-SERIAL)
			,mds-ds-x9304-18k9(4497)		-- DS-X9304-18K9 coco Linecard
			,mds-ds-x9314-s2-k9(4498)		-- 32-port 1/2/4 with 10 Gig Supervisor Fabric Switch
			,nm-trans-opt-srvc-eng1(4499)		-- Transport Performance Optimization NM Module(2GB DDRII) for Modular and Integrated Services Routers
			,cat6k-wsx-6708a-10ge(4500)		-- Catalyst 6500 8 port 10 GE
			,cat6k-wsx-6708-10ge(4501)		-- Catalyst 6500 8 port 10 GE with DFC
			,cat6k-wsf-6700-dfc3c(4503)		-- Catalyst 6500 Distributed Forwarding Card 3C
			,cat6k-wsf-6700-dfc3cxl(4504)		-- Catalyst 6500 Distributed Forwarding Card 3C XL
			,cat6k-vs-s720-10g(4505)		-- Catalyst 6500 Supervisor 720 with 10G Ethernet Module
			,cat6k-vs-f6k-pfc3c(4506)		-- Catalyst 6500 Policy Feature Card 3C
			,cat6k-vs-f6k-pfc3cxl(4507)		-- Catalyst 6500 Policy Feature Card 3C XL
			,cat6k-vs-f6k-msfc3(4508)		-- Supervisor Module 720 10G CPU board
			,cat6k-ws-f6k-pisa(4509)                -- Catalyst 6500 Programmable IP Services Accelerator Internal Router Daughtercard
			,cat6k-wsx-6716-10ge(4513)              -- Catalyst 6500 16 port 10 GE
                        ,cat6k-ws-sup32p-ge(4516)               -- Catalyst 6500 Supervisor Module with PISA and 8 Gigabit Ethernet SFP uplink ports
                        ,cat6k-ws-sup32p-10ge(4517)             -- Catalyst 6500 Supervisor Module with PISA and 2 10-GE uplink ports
                        ,cat6k-ws-svc-wism(4525)                -- Wireless Service Module for the Catalyst 6500 and 7600
                        ,cat6k-ws-f6k-48-at(4529)               -- Catalyst 6500 IEEE 802.3at inline power voice daughter card
                        ,cat6k-ws-x6148e-ge-45-at(4530)         -- Catalyst 6500 48-port IEEE802.3at compliant Power over Ethernet Plus module with inline power voice daughter card
                        ,cat6k-ws-x6716-10t(4531)               -- Catalyst 6500 16 port 10 GE RJ-45
                        ,cat6k-ws-svc-asa-sm1(4532)             -- Adaptive Security Appliance (ASA) Service Module for Catalyst switches msgreene
                        ,cat6k-ws-svc-nam-3-k9(4534)            -- Next generation Network Analysis Module msgreene
                        ,cat6k-ws-x6816-10ge(4540)              -- Catalyst 6500 16-port 10 GE (X2)

			,hwic-4shdsl(4551)			-- HWIC G.SHDSL (4 port) with annex F&G and IMA.
			,hwic-2shdsl(4552)			-- HWIC G.SHDSL (2 port) with annex F&G
			,nm-rvpn-sterra(4553)			-- Russia S-Terra VPN Module
			,nm-rvpn(4554)				-- Special Services Engine for Modular and Integrated Services Routers
			,mn-spcl-srvc-eng(4555)			-- Special Services Engine for ISR routers
			,nm-intgrtd-srvc-eng2(4556)		-- Integrated Service Engine2 for ISR router
                        ,aim-ips-k9(4557)			-- Cisco Intrusion Proctection System AIM Adapter
                        ,hwic-1t1e1(4558)                       -- 1 port (2 channel) T1/E1 HWIC
                        ,hwic-1ser(4559)                        -- High Speed Wan Interface Card with 1 serial ports(HWIC-1SER)
                        ,hwic-2ser(4560)                        -- High Speed Wan Interface Card with 2 serial ports(HWIC-2SER)
                        ,internal-service-module-aim(4561)      -- Internal Service Module AIM for Integrated Services Routers
                        ,sm-1nm(4563)                           --  Service Module to Network Module Adapter
                        ,hwic-4ce1t1-pri(4576)                  -- 4 port T1/E1 channelized/PRI HWIC
                        ,ehwic-1ge-sfp-cu(4577)                 -- Single Port Gigabit Ethernet Extended High-Speed Wan Interface Card with either onboard cu port or SFP
                        ,sm1-stm1-mm(4578)                      -- 1 port multichannel STM-1 multimode service module
                        ,sm1-stm1-smi(4579)                     -- 1 port multichannel STM-1 single mode service module
                        ,sm1pa(4580)                            -- Service module to Port adapter
                        ,ehwic-3g-hspa-7(4581)                  -- 3G EHWIC QuadBand HSPA+R7/HSPA/UMTS QuadBand EDGE/GPRS and GPS
                        ,ehwic-3g-hspa-u(4582)                  -- 3G EHWIC QuadBand HSPA/UMTS QuadBand EDGE/GPRS and GPS
                        ,ehwic-3g-evdo(4583)                    -- 3G EHWIC DuoBand EVDO Rev A/Rel 0/1xRTT and GPS
                        ,ehwic-3g-hspa-7-a(4584)                -- 3G WWAN EHWIC-QuadBand HSPA+R7/HSPA/UMTS QuadBand EDGE/GPRS and GPS for AT&T
                        ,ehwic-3g-mm(4585)                      -- 3G WWAN EHWIC - Multimode HSPA+/HSPA/UMTS/EDGE/GPRS EVDO RevA/Rev0/1xRTT
                        ,ehwic-4g-lte-a(4586)                   -- 4G WWAN EHWIC - North America Multimode LTE/DC-HSPA+/HSPA+/HSPA/UMTS/EDGE/GPRS
                        ,ehwic-4g-lte-g(4587)                   -- 4G WWAN EHWIC - Global Multimode LTE/DC-HSPA+/HSPA+/HSPA/UMTS/EDGE/GPRS
                        ,ehwic-4g-lte-v(4588)                   -- 4G WWAN EHWIC - Verizon Multimode LTE/eHRPD/EVDO RevA/Rev0/1xRTT
                        ,sm32a(4589)                            -- 32-port Asynchronous Interface Service Module for ISR G2s (c39XX)
                        ,sm-1t3-e3(4590)                        -- 1 port clear channel T3/E3 SM
                        ,sm-d-48fxs-e(4595)                     -- SM-D-48FXS-E is a double-wide service module with 48 OPX Lite FXS analog ports
                        ,sm-2ge-sfp-cu(4596)                    -- Dual Port Gigabit Ethernet Service Module with either onboard cu or SFP ports




			,dwdm-3268-sfp(4600)			-- MOD,XCVR,2.5Gb/s,1532.68nm,SM,LR2,3.3V,0 to 70C,LC,SFP,DIGITAL DIAGS FIM32160/201W56
			,dwdm-3425-sfp(4601)			-- MOD,XCVR,2.5Gb/s,1534.25nm,SM,LR2,3.3V,0 to 70C,LC,SFP,DIGITAL DIAGS FIM32160/201W54
			,dwdm-3504-sfp(4602)			-- MOD,XCVR,2.5Gb/s,1535.04nm,SM,LR2,3.3V,0 to 70C,LC,SFP,DIGITAL DIAGS FIM32160/201W53
                        ,dwdm-3582-sfp(4603)                    -- MOD,XCVR,2.5Gb/s,1535.82nm,SM,LR2,3.3V,0 to 70C,LC,SFP,DIGITAL DIAGS FIM32160/201W52
                        ,dwdm-3661-sfp(4604)                    -- MOD,XCVR,2.5Gb/s,1536.61nm,SM,LR2,3.3V,0 to 70C,LC,SFP,DIGITAL DIAGS FIM32160/201W51
                        ,dwdm-3819-sfp(4605)                    -- MOD,XCVR,2.5Gb/s,1538.19nm,SM,LR2,3.3V,0 to 70C,LC,SFP,DIGITAL DIAGS FIM32160/201W49
                        ,dwdm-3898-sfp(4606)                    -- MOD,XCVR,2.5Gb/s,1538.98nm,SM,LR2,3.3V,0 to 70C,LC,SFP,DIGITAL DIAGS FIM32160/201W48
                        ,dwdm-3977-sfp(4607)                    -- MOD,XCVR,2.5Gb/s,1539.77nm,SM,LR2,3.3V,0 to 70C,LC,SFP,DIGITAL DIAGS FIM32160/201W47
                        ,dwdm-4056-sfp(4608)                    -- MOD,XCVR,2.5Gb/s,1540.56nm,SM,LR2,3.3V,0 to 70C,LC,SFP,DIGITAL DIAGS FIM32160/201W46
                        ,dwdm-4214-sfp(4609)                    -- MOD,XCVR,2.5Gb/s,1542.14nm,SM,LR2,3.3V,0 to 70C,LC,SFP,DIGITAL DIAGS FIM32160/201W44
                        ,dwdm-4294-sfp(4610)                    -- MOD,XCVR,2.5Gb/s,1542.94nm,SM,LR2,3.3V,0 to 70C,LC,SFP,DIGITAL DIAGS FIM32160/201W43
                        ,dwdm-4373-sfp(4611)                    -- MOD,XCVR,2.5Gb/s,1543.73nm,SM,LR2,3.3V,0 to 70C,LC,SFP,DIGITAL DIAGS FIM32160/201W42
                        ,dwdm-4453-sfp(4612)                    -- MOD,XCVR,2.5Gb/s,1544.53nm,SM,LR2,3.3V,0 to 70C,LC,SFP,DIGITAL DIAGS FIM32160/201W41
                        ,dwdm-4612-sfp(4613)                    -- MOD,XCVR,2.5Gb/s,1546.12nm,SM,LR2,3.3V,0 to 70C,LC,SFP,DIGITAL DIAGS FIM32160/201W39
                        ,dwdm-4692-sfp(4614)                    -- MOD,XCVR,2.5Gb/s,1546.92nm,SM,LR2,3.3V,0 to 70C,LC,SFP,DIGITAL DIAGS FIM32160/201W38
                        ,dwdm-4772-sfp(4615)                    -- MOD,XCVR,2.5Gb/s,1547.72nm,SM,LR2,3.3V,0 to 70C,LC,SFP,DIGITAL DIAGS FIM32160/201W37
                        ,dwdm-4851-sfp(4616)                    -- MOD,XCVR,2.5Gb/s,1548.51nm,SM,LR2,3.3V,0 to 70C,LC,SFP,DIGITAL DIAGS FIM32160/201W36
                        ,dwdm-5012-sfp(4617)                    -- MOD,XCVR,2.5Gb/s,1550.12nm,SM,LR2,3.3V,0 to 70C,LC,SFP,DIGITAL DIAGS FIM32160/201W34
                        ,dwdm-5092-sfp(4618)                    -- MOD,XCVR,2.5Gb/s,1550.92nm,SM,LR2,3.3V,0 to 70C,LC,SFP,DIGITAL DIAGS FIM32160/201W33
                        ,dwdm-5172-sfp(4619)                    -- MOD,XCVR,2.5Gb/s,1551.72nm,SM,LR2,3.3V,0 to 70C,LC,SFP,DIGITAL DIAGS FIM32160/201W32
                        ,dwdm-5252-sfp(4620)                    -- MOD,XCVR,2.5Gb/s,1552.52nm,SM,LR2,3.3V,0 to 70C,LC,SFP,DIGITAL DIAGS FIM32160/201W31
                        ,dwdm-5413-sfp(4621)                    -- MOD,XCVR,2.5Gb/s,1554.13nm,SM,LR2,3.3V,0 to 70C,LC,SFP,DIGITAL DIAGS FIM32160/201W29
                        ,dwdm-5494-sfp(4622)                    -- MOD,XCVR,2.5Gb/s,1554.94nm,SM,LR2,3.3V,0 to 70C,LC,SFP,DIGITAL DIAGS FIM32160/201W28
                        ,dwdm-5575-sfp(4623)                    -- MOD,XCVR,2.5Gb/s,1555.75nm,SM,LR2,3.3V,0 to 70C,LC,SFP,DIGITAL DIAGS FIM32160/201W27
                        ,dwdm-5655-sfp(4624)                    -- MOD,XCVR,2.5Gb/s,1556.55nm,SM,LR2,3.3V,0 to 70C,LC,SFP,DIGITAL DIAGS FIM32160/201W26
                        ,dwdm-5817-sfp(4625)                    -- MOD,XCVR,2.5Gb/s,1558.17nm,SM,LR2,3.3V,0 to 70C,LC,SFP,DIGITAL DIAGS FIM32160/201W24
                        ,dwdm-5898-sfp(4626)                    -- MOD,XCVR,2.5Gb/s,1558.98nm,SM,LR2,3.3V,0 to 70C,LC,SFP,DIGITAL DIAGS FIM32160/201W23
                        ,dwdm-5979-sfp(4627)			-- MOD,XCVR,2.5Gb/s,1559.79nm,SM,LR2,3.3V,0 to 70C,LC,SFP,DIGITAL DIAGS FIM32160/201W22
                        ,dwdm-6061-sfp(4628)                    -- MOD,XCVR,2.5Gb/s,1560.61nm,SM,LR2,3.3V,0 to 70C,LC,SFP,DIGITAL DIAGS FIM32160/201W21
			,pwr-c3k-265w-ac(4630)			-- Catalyst 3K 265 Watt, 12V AC Power Supply
			,pwr-c3k-265w-dc(4631)			-- Catalyst 3K 265 Watt, 12V DC Power Supply
			,pwr-c3k-750w-AC(4632)			-- Catalyst 3K 750 Watt, 12V/-52V AC Power Supply
			,nme-apa-link(4634)			-- Service Classification Element Link between Network side and Subscriber side for NME-APA.
                        ,pwr-ce520-lc-ac-135w-12v(4635)         -- Cisco Catalyst Express 520 AC power Supply 135 Watt, 12V DC
                        ,pwr-ce520-pc-ac-558w-12v(4636)         -- Cisco Catalyst Express 520 AC power Supply 558 Watt, 12V DC
                        ,pwr-ce520-tt-ac-60w-12v(4637)          -- Cisco Catalyst Express 520 AC power Supply 60 Watt, 12V DC
                        ,pwr-ce520-gtc-ac-125w-12v(4638)        -- Cisco Catalyst Express 520 AC power Supply 125 Watt, 12V DC
                        ,pwr-n7k-ac-7500w(4639)                 -- N7K-AC-7.5KW,  AC 7.5KW powersupply for Nexus7000 N7K
                        ,pwr-n7k-ac-6000w(4640)                 -- N7K-AC-6.0KW,  AC 6000W powersupply for Nexus7000 N7K
                        ,pwr-dc-4500w(4641)                     -- RF gateway power supply DC 4500 Watts
                        ,pwr-ie3000-ac(4642)                    -- Cisco Industrial Ethernet Switch IE3000 Power Transformer
                        ,pwr-cat2918-ac60w12v(4643)             -- Cisco Catalyst 2918 AC power supply 60 Watt, 12V DC
                        ,csc-link(4644)                         -- Service control entity link between subscriber side and user side
                        ,pwr-dc-power-supply(4645)              -- Generic DC power supply
                        ,pwr-ac-power-supply(4646)              -- Generic AC power supply

                        ,gsr-e384-cec(4653)                     -- Cisco 12000 Series SPA nterface Processor-701

			,aim-trans-opt-srvc-eng1(4700)		-- Transport Performance Optimization AIM Module(512MB DDRII) for Modular and Integrated Services Routers
			,nm-trans-opt-srvc-eng2(4701)		-- Transport Performance Optimization NM Module for Modular and Integrated Services Routers
			,aim-trans-opt-srvc-eng2(4702)          -- Transport Performance Optimization AIM Module(1GB DDRII) for Modular and Integrated Services Routers
			,mds-ds-c9222i(4703)			-- Supervisor module in slot 1 of MDS 9222i chassis
			,onboard-se(4704)			-- On-board Integrated Service Engine. On-board Integrated Service Engine
			,nme-apa-m(4705)			-- Integrated Service Engine for Application Performance Assurance.
                        ,mds-ds-x9248-fc-48gbps(4706)           -- 48 port 1/2/4/8G 48Gbps FibreChannel linecard A-Oahu PID:DS-X9248-48
                        ,mds-ds-x9248-fc-96gbps(4707)           -- 48 port 1/2/4/8G 96Gbps FibreChannel linecard TwinPeaks PID:DS-X9248-96
                        ,mds-ds-x9316-ssm(4708)                 -- Lanai PID=DS-X9316-SSM, 16 GE port Storage Service Module
                        ,c7600-ssc-400(4709)                    -- 2-subslot Services SPA Carrier-400
                        ,ws-ssc-600(4710)                       -- 2-subslot Services SPA Carrier-600
                        ,hwic-2as(4711)                         -- High speed WAN Interface Card - Serial 2A/S
                        ,hwic-2t(4712)                          -- High speed Wan Interface Card - Serial (2T)
                        ,hwic-1t(4713)                          -- High speed Wan Interface Card - Serial (1T)
                        ,hwic-1dsu-t1(4714)                     -- High speed Wan Interface Card with 1 Fractional T1 CSU/DSU port
                        ,mds-ds-13slt-fab2(4716)                -- Cisco MDS 9513 Fabric2 (evia2)DS-13SLT-FAB2
                        ,mds-ds-x9224-96k9(4718)                -- 24 port singlepeak PID:DS-X9224-96K9
                        ,c4oc192-dpt-ir(4720)                   -- Cisco CRS-1 4xOC-192/STM-64 DPT Interface Module/IR
                        ,ws-ipsec-2(4721)                       -- IPSec Shared Port Adapter with DES/3DES/AES (WS-IPSEC-2)
                        ,aim-vpn-ssl-1(4722)                    -- AIM-VPN/SSL-1 card for Integrated Services Router
                        ,aim-vpn-ssl-2(4723)                    -- AIM-VPN/SSL-2 card for Integrated Services Router
                        ,aim-vpn-ssl-3(4724)                    -- AIM-VPN/SSL-3 card for Integrated Services Router
                        ,ism-sre-300-k9(4726)                   --  Internal Service Module for Modular and Integrated Services Routers(ISM-SRE-300-K9)
                        ,sm-sre-700-k9(4729)                    --  Service Module for Modular and Integrated Services Routers(SM-SRE-700-K9)
                        ,sm-sre-900-k9(4731)                    --  Service Module for Modular and Integrated Services Routers(SM-SRE-900-K9)
                        ,spa-wma-sw(4732)                       --  WebEx Node Shared Port Adaptor (SPA-WMA-K9)
                        ,hwic-4shdsl-efm(4734)                  --  HWIC G.SHDSL (4port) with EFM
                        ,aim-axp102(4735)                       --  AXP Advanced Interface Module with 300MHz and 256MB RAM
                        ,aim-2axp104(4736)                      --  AXP Advanced Interface Module 2 with 600MHz and 512MB RAM
                        ,nm-axp302(4737)                        --  AXP Service Engine Network Module with 1GHz and 512MB RAM
                        ,nm-axp502(4738)                        --  AXP Service Engine Network Module with 1GHz and 1GB RAM
                        ,nm-axp522(4739)                        --  AXP Service Engine Network Module with 1.4GHz and 2GB RAM
                        ,wic-gshdsl-efm(4740)                   --  A G.SHDSL WIC (WAN Interface Card) supporting EFM in C888 platform
                        ,nme-iss(4741)                          --  Integrated Storage System 500GB HDD
                        ,nme-vmss2-16(4742)                     --  Video Management and Storage System 16 streams 500GB HDD
                        ,nme-vmss-hp32(4743)                    --  Video Management and Storage System 32 streams 160GB HDD
                        ,nme-vmss2-hp32(4744)                   --  Video Management and Storage System 32 streams 500GB HDD
                        ,nme-vmss-hp16(4745)                    --  Video Management and Storage System 16 streams 160GB HDD
                        ,nme-vmss-16(4746)                      --  Video Management and Storage System 16 streams 120GB HDD
                        ,mds-ds-x9716-k9(4748)                  --  Midas  DS-X9716-K9 10-Gbps 16-Port ethernet-port FCoE Module
                        ,mds-ds-x9248x256-k9(4749)              --  Zelda DS-X9248-256K9  48-Port 1/2/4/8/10Gbps FC Switching Module

                        ,pwr-n7k-ac-7500w-int(4751)             -- N7K-AC-7.5KW-INT AC powersupply for Nexus7000 N7K
                        ,pwr-n7k-ac-7500w-us(4752)              -- N7K-AC-7.5KW-US AC powersupply for Nexus7000 N7K
                        ,spa-1p-oc3-atm-v2(4753)                --  1-port OC3c SFP Optics ATM Shared Port Adapter (SPA-1XOC3-ATM-V2)
                        ,spa-3p-oc3-atm-v2(4754)                --  3-port OC3c SFP Optics ATM Shared Port Adapter (SPA-3XOC3-ATM-V2)
                        ,pwr-c3900pwr-poe(4755)                 --  Cisco 3925/3945 PoE Power Supply
                        ,pwr-c3900pwr-ac(4756)                  --  Cisco3925/3945 AC Power Supply
                        ,pwr-c2921c2951pwr-poe(4757)            --  Cicco 2921/2951 PoE Power Supply
                        ,pwr-c2921c2951pwr-ac(4758)             --  Cisco 2921/2951 AC Power Supply
                        ,pwr-c2911pwr-poe(4759)                 --  Cisco 2911 PoE Power Supply
                        ,pwr-c2911pwr-ac(4760)                  --  Cisco 2911 AC Power Supply
                        ,pwr-c2901pwr-poe(4761)                 --  Cisco2901 PoE Power Supply
                        ,pwr-c1941c2901pwr-ac(4762)             --  Cisco 2901 AC Power Supply
                        ,pwr-c1941pwr-poe(4763)                 --  Cisco 1941 PoE Power Supply
                        ,pwr-c3900pwr-dc(4764)                  --  Cisco 3925/3945 DC Power Supply
                        ,pwr-c2921c2951pwr-dc(4765)             --  Cisco 2921/2951 DC Power Supply
                        ,pwr-c2911pwr-dc(4766)                  --  Cisco 2911 DC power Supply
                        ,pwr-c2921c2951rps-adptr(4767)          --  Cisco 2921/2951 RPS Adaptor
                        ,pwr-c2911rps-adptr(4768)               --  Cisco 2911 RPS Adaptor
                        ,pwr-c45-6000acv(4769)                  -- 6000W AC power supply for Catalyst 4500 switches
                        ,pwr-n7k-dc6000w(4770)                  -- N7K-DC-6.0KW,  DC 6000W powersupply for Nexus7000 N7K
                        ,pwr-crs1-8-power-shelf-dcmodular(4771) -- Cisco CRS-1 Series Modular DC Power Shelf for 8 Slots LCC
                        ,pwr-crs1-8-power-shelf-acmodular(4772) -- Cisco CRS-1 Series Modular AC Power Shelf for 8 Slots LCC
                        ,pwr-crs1-16fcc-power-shelf-dcmodular(4773) -- Cisco CRS-1 Series Modular DC Power Shelf for FCC
                        ,pwr-crs1-16fcc-power-shelf-acmodular(4774) -- Cisco CRS-1 Series Modular AC Power Shelf for FCC
                        ,pwr-crs1-dc-power-module(4775)         -- Cisco CRS-1 Series DC Power Module 2100W
                        ,pwr-crs1-ac-power-module(4776)         -- Cisco CRS-1 Series AC Power Module 3000W
                        ,pwr-crs1-16lcc-power-shelf-dcmodular(4777) -- Cisco CRS-1 Series Modular DC Power Shelf for 16 Slots LCC
                        ,pwr-crs1-16lcc-power-shelf-acmodular(4778) -- Cisco CRS-1 Series Modular AC Power Shelf for 16 Slots LCC
                        ,pwr-cat-2960ac-235w-12v(4779) -- Cisco Catalyst 2960 AC power Supply 235 Watt, 12V DC
                        ,pwr-cat-2960ac-525w-12v(4780) -- Cisco Catalyst 2960 AC power Supply 525 Watt, 12V DC
                        ,pwr-c1941pwr-ac(4781)         -- C1941 AC Power Supply
                        ,pwr-me3kxac(4783)             -- Metro Ethernet 3600X/3800X AC power supply
                        ,pwr-me3kxdc(4784)             -- Metro Ethernet 3600X/3800X DC power supply
                        ,pwr-cgr20xxcgs25xxpwr-acpoe(4785)     -- Cisco Connected Grid Router 20xx/Switch 25xx AC POE Power Supply
                        ,pwr-cgr20xxcgs25xxpwr-dcpoe(4786)     -- Cisco Connected Grid Router 20xx/Switch 25xx DC POE Power Supply
                        ,pwr-c7225-ac(4787)                  -- 12V/ 540W output PSU, since the older Marin PSU only can provide 300W power(output), can<92>t support the uBR7225 system with 2 new Bajie boards
                        ,pwr-xps-2200(4788)                  -- Cisco eXpandable Power System (XPS-2200) with 9 dual StackPower and RPS power ports
                        ,pwr-ie2000-ac(4789)                 -- Cisco Industrial Ethernet Switch IE2000 Power Transformer

                        ,pwr-asr9k-ac-3kw-v2(4792)           -- 3kW AC Power Module
                        ,pwr-asr9k-dc-2100w-v2(4793)         -- 2kW DC Power Module
                        ,pwr-asr9k-ac-750w(4794)             -- ASR-9001 AC Power Supply
                        ,pwr-asr9k-dc-750w(4795)             -- ASR-9001 DC Power Supply
                        ,pwr-vg350pwr-ac(4796)               -- VG350 AC Power Supply
                        ,pwr-vg350pwr-dc(4797)               -- VG350 DC Power Supply
                        ,mds-ds-x9232x256-k9(4800)         -- Link DS-X9232-256K9  32-Port 1/2/4/8/10Gbps FC Switching Module
                        ,mds-ds13-slot-fabric-evia3(4801)  -- Evia3 DS-13SLT-FAB3  MDS9513 xbar 256Gbps Fabric Module3
                        ,spa-dsp(4818)                       -- Digital Signal Processing Shared Port Adapter (SPA-DSP)
                        ,mds-ds-x9530-sf2a-k9(4819)          -- 2nd gen sup2a DS-X9530-SF2A-K9 for MDS
                        ,crs-4s-140g-fabriccard(4820)        -- Cisco CRS Series 4 Slots Fabric Card / Single (140G)
                        ,crs-8s-140g-fabriccard(4821)        -- Cisco CRS Series 8 Slots Fabric Card / Single (140G)
                        ,crs-16s-140g-fabriccard(4822)       -- Cisco CRS Series 16 Slots Fabric Card / Single (140G)
                        ,crs-16s-140g-fabriccardmulti(4823)  -- Cisco CRS Series 16 Slots Fabric Card / Multi (140G)
                        ,crs1-140g-fccsfc(4824)              -- Cisco CRS Series Fabric Card Chassis Switch Fabric Card (140G)
                        ,hwic-2t-c(4826)                     -- High speed Wan Interface Card - Serial (2T)
                        ,hwic-1t-c(4827)                     -- High speed Wan Interface Card - Serial (1T)
                      ,hwic-9fes-c(4828)                   --  HWIC 9 Port Fast Ethernet Switch Cards
                      ,hwic-4fes-c(4829)                   --  HWIC 4 Port Fast Ethernet Switch Cards
                        ,vwic2-mft1-g703-c(4830)             -- VWIC2-1MFT-G703 (1 Port) RJ-48 Multi-Flex Trunk - G.703
                        ,vwic2-mft2-g703-c(4831)             -- VWIC2-2MFT-G703 (2 Port)) RJ-48 Multi-Flex Trunk - G.703
                        ,nm-16eswitch-c(4832)                -- 16 Ports 10BaseT/100BaseTX EtherSwitch Network module with optional GE and IP Phone Line Power
                        ,harddisk-idc(4835)                  -- HDD IDC drive for ASR1001
                        ,ehwic-4esg(4836)                    -- 4 Port GE Non-POE EHWIC Switch
                        ,ehwic-d-8esg(4837)                  -- 8 Port GE Non-POE EHWIC Switch
                        ,ehwic-d-8esg-p(4838)                -- 8 Port GE POE EHWIC Switch
                        ,ehwic-4esg-p(4839)                  -- 4 Port GE POE EHWIC Switch
                        ,vmss-sm-sre700K9(4840)              -- Video Management and Storage System on SRE-SM-700
                        ,vmss-sm-sre900K9(4841)              -- Video Management and Storage System on SRE-SM-900
                        ,iss-sm-sre700K9(4842)               -- Integrated Storage System on SRE-SM-700
                        ,iss-sm-sre900K9(4843)               -- Integrated Storage System on SRE-SM-900
                        ,modem-3g-gsm504-a(4844)             -- Sierra Wireless 504-A
                        ,modem-3g-gsm504-g(4845)             -- Sierra Wireless 504-g
                        ,modem-3g-cdma5728-v(4846)           -- Sierra Wireless MC5728V(Dual-band EVDO Rev. A/Rev 0/1xRTT)
                        ,modem-3g-gsm-mc8705(4847)           -- Sierra Wireless MC8705 modem(Quad-band HSPA+ and Quad-band GPRS/EDGE)
                        ,modem-3g-gsm-mc8795(4848)           -- Sierra Wireless MC8795V  modem(Quad-band HSPA and Quad-band GPRS/EDGE)

                        ,crs-16-psh-dc-b(4851)               -- CRS Modular DC Power Shelf for CRS-16/S-B
                        ,crs-16-psh-ac-b(4852)               -- CRS Modular AC Power Shelf for CRS-16/S-B
                        ,ism-vpn-ssl-3(4857)                 -- Internal Service Module for VPN and SSL feature acceleration including Suite B Crypto support on Cisco 3900 routers
                        ,ism-vpn-ssl-2(4858)                 -- Internal Service Module for VPN and SSL feature acceleration including Suite B Crypto support on Cisco 2900 routers
                        ,ism-vpn-ssl-1(4859)                 -- Service Module for VPN and SSL feature acceleration including Suite B Crypto support on Cisco 1941 routers
                        ,mds-ds-9708-hpk9(4860)              -- DS-9708-HPK9  HP-Mira-midas
                        ,mds-ds-9708-k9(4861)                -- DS-9708-K9 Mira-midas
                        ,crs-16-lcc-f-ct-b(4863)             -- Cisco CRS-1 Fan Controller for 16 Slots LC Chassis Ver B
                        ,spa-hdwbd-spf(4887)                 -- This is a Wideband SPA card which implements the Wideband protocol for CMTS, and which is upgrade of cevSpa24xwbdSfp
                        ,ca9k-mpa-8X10ge(4889)               -- ASR 9000 8-port 10GE Modular Port Adapter
                        ,spa-14p-sa-serial(4890)             -- 14-port Sync/Async Serial Shared Port Adapter (SPA-14P-SA-SERIAL)
                        ,pism-sre-300-k9(4891)             -- Internal Services Module (ISM) with Services Ready Engine
                        ,phwic-2fe(4892)                   -- Two 10/100 routed port HWIC
                        ,phwic-2t(4893)                    -- 2-Port Serial WAN Interface Card
                        ,phwic-l1t(4894)                   -- 1-Port Serial WAN Interface Card
                        ,phwic-2as(4895)                   -- 2-Port Async/Sync Serial WAN Interface Card
                        ,phwic-1adsl(4896)                 -- 1-port ADSLoPOTS HWIC
                        ,phwic-1adslm(4897)                -- 1-port ADSL HWIC w/Annex M
                        ,pehwic-4esg(4898)                 -- Four port 10/100/1000 Ethernet switch interface card
                        ,pehwic-d-8esg(4899)               -- Eight port 10/100/1000 Ethernet switch interface card
                        ,pwic-1b-s-t-v3(4900)              -- 1-Port ISDN WAN Interface Card (dial and leased line)

                        ,cpu-819hg(4901)                     -- C819HG Hardened Router series with 1 Gigabit Ethernet WAN, 4 Fast Ethernet LAN, 1 3G/LTE WAN, 1 Serial, 1 Console/Aux ports, 256MB flash memory, 256MB DRAM
                        ,cpu-819g(4902)                      -- C819G Router series with 1 Gigabit Ethernet WAN, 4 Fast Ethernet LAN, 1 3G/LTE WAN, 1 Serial, 1 Console/Aux ports, 256MB flash memory and 256MB DRAM
                        ,cpu-881w(4903)                      -- C881W Router series with 1 Fast Ethernet WAN, 4 Fast Ethernet LAN with 2 PoE, Wireless LAN, 1 USB 2.0 port, 1 Console/Aux port, 256MB flash memory and 512MB DRAM
                        ,cpu-886va-w(4904)                   -- C886VA-W Router series with 1 ADSL2/2+ Annex B, 1 ISDN,  4 Fast Ethernet LAN with 2 PoE, Wireless LAN, 1 USB 2.0 port, 1 Console/Aux port, 256MB flash memory and 512MB DRAM
                        ,cpu-887vam-w(4905)                  -- C887VAM-W Router with 1 ADSL2/2+ Annex M, 4 Fast Ethernet LAN with 2 PoE, Wireless LAN, 1 USB 2.0 port, 1 Console/Aux port, 256MB flash memory and 512MB DRAM
                        ,cpu-887va-w(4906)                   -- C887VA-W Router series with 1 VDSL, 4 Fast Ethernet LAN with 2 PoE, Wireless LAN, 1 USB 2.0 port, 1 Console/Aux port, 256MB flash memory and 512MB DRAM
                        ,cpu-asa-sm1(4907)                   -- Central Processing Unit for Cisco Adaptive Security Appliance for Catalyst switches
                        ,cpu-asa-sm1-k7(4908)                -- Central Processing Unit for Cisco Adaptive Security Appliance with No Payload Encryption for Catalyst switches
                        ,cpu-881wd(4914)                     -- C881WD series router with 1 Fast Ethernet WAN, 4 Fast Ethernet LAN with 2 PoE, Wireless LAN, 1 USB 2.0 port, 1 Console/Aux port, 256MB flash memory and 512MB DRAM
                        ,cpu-887vawd(4915)                   -- C887VA-WD series router with 1 WAN VDSL2/ADSL2+ over POTS, 4 Fast Ethernet LAN with 2 PoE, Wireless LAN, 1 USB 2.0 port, 1 Console/Aux port, 256MB flash memory and 512MB DRAM
                        ,cpu-887vagw(4916)                   -- C887VAGW series router with 1 WAN VDSL2/ADSL2+ over POTS, 4 Fast Ethernet LAN with 2 PoE, Wireless LAN, 3G, 1 USB 2.0 port, 1 Console/Aux port, 256MB flash memory and 512MB DRAM
                        ,cpu-881gw(4917)                     -- C881GW series router with 1 Fast Ethernet WAN, 4 Fast Ethernet LAN with 2 PoE, 3G, Wireless LAN, 1 USB 2.0   port, 1 Console/Aux port, 256MB flash memory and 512MB DRAM
                        ,cpu-819hgw(4918)                    -- C819HGW Hardened Router series with 1 Gigabit Ethernet WAN, 4 Fast Ethernet LAN, 1 3G WAN, Wireless LAN, 1 Serial, 1 Console/Aux ports, 1GB flash memory, 1GB DRAM
                        ,cpu-819h(4919)                      -- C819H Hardened Router series with 1 Gigabit Ethernet WAN, 4 Fast Ethernet LAN, 1 Serial, 1 Console/Aux ports, 1GB flash memory, 1GB DRAM
                        ,cpu-819hwd(4920)                    -- C819HWD Hardened Router series with 1 Gigabit Ethernet WAN, 4 Fast Ethernet LAN, Wireless LAN, 1 Serial, 1 Console/Aux ports, 1GB flash memory,1GB DRAM
                        ,cpu-812g(4921)                      -- C812G Router series with 1 Gigabit Ethernet WAN, 1 3G WAN, 1 Console/Aux ports, 512MB flash memory, 512MB DRAM
                        ,cpu-812gcifi(4922)                  -- C812G Router series with 1 Gigabit Ethernet WAN, 1 3G WAN, Wireless LAN, 1 Console/Aux ports, 512MB flash memory, 512MB DRAM
                        ,cpu-819hgm(4923)                    -- C819HGM Hardened Router series with 1 Gigabit Ethernet WAN, 4 Fast Ethernet LAN, 1 3G WAN, 1 Serial, 1 Console/Aux ports, 1GB flash memory, 1GB DRAM
                        ,cpu-819gm(4924)                     -- C819GM Router series with 1 Gigabit Ethernet WAN, 4 Fast Ethernet LAN, 1 3G WAN, 1 Serial, 1 Console/Aux ports, 1GB flash memory and 1GB DRAM
                        ,cpu-vg350(4928)                     -- VG350 High Density Analog Gateway
                       ,cpu-vg202xm(4936)                    -- Line side Analog Gateway VG202XM with 2FXS Analog ports
                       ,cpu-vg204xm(4937)                    -- Line side Analog Gateway VG204XM with 4FXS Analog ports
                       ,cpu-c881(4947)                       -- C881 router with 1 Fast Ethernet Primary WAN, 4 Fast Ethernet LAN, 2 PoE Optional, 1 USB 2.0 port, 1 Console/Aux port, 256MB flash memory and 1GB DRAM
                       ,cpu-c886va(4948)                     -- C886VA router with 1 VDSL2/ADSL2+ Primary WAN, 1 ISDN BRI S/T interface, 4 Fast Ethernet LAN, 2 PoE Optional, 1 USB 2.0 port, 1 Console/Aux port, 256MB flash memory and 1GB DRAM
                       ,cpu-c887va(4949)                     -- C887VA router with 1 VDSL2/ADSL2+ Primary WAN, 4 Fast Ethernet LAN, 2 PoE Optional, 1 USB 2.0 port, 1 Console/Aux port, 256MB flash memory and 1GB DRAM
                       ,cpu-c888(4950)                       -- C888 router with 1 EFM/ATM over G.SHDSL Primary WAN, 1 ISDN BRI S/T interface, 4 Fast Ethernet LAN, 2 PoE Optional, 1 USB 2.0 port, 1 Console/Aux port, 256MB flash memory and 1GB DRAM

                        ,ngsm-xd-3k-48ge-2sfp-poeplus(4951)  -- EtherSwitch Next Generation Service Module Layer3 + PoEPlus + 48 10/100/1000 + 2 SFP
                        ,ngsm-3k-24ge-poeplus(4952)          -- EtherSwitch Next Generation Service Module Layer3 + PoEPlus + 24 10/100/1000
                        ,ngsm-3k-16ge-poeplus(4953)          -- EtherSwitch Next Generation Service Module Layer3 + PoEPlus + 16 10/100/1000
                        ,cev-grwic-serial4t(4954)                -- Connected Grid Rugged Wan Interface Card with 4 serial ports(GRWIC-4T)
                        ,ehwic-4g-lte-jp(4955)               -- 4G WWAN EHWIC - Japan Multimode LTE/DC-HSPA+/HSPA+/HSPA/UMTS/EDGE/GPRS
                        ,ehwic-4g-lte-be(4956)               -- 4G WWAN EHWIC - Canada AWS LTE Multimode LTE/DC-HSPA+/HSPA+/HSPA/UMTS/EDGE/GPRS
                        ,pehwic-1ge-sfp-cu(4957)             -- EHWIC 1 port dual mode SFP(100M/1G) or GE(10M/100M/1G)
                        ,pehwic-3g-hspa-7(4958)              -- (non-US) 3.7G HSPA+ Release 7 EHWIC w/ SMS/GPS (MC8705)
                        ,phwic-serial16a(4959)               -- 16-Port Async HWIC
                        ,phwic-1ce1t1pri(4960)               -- 1 port channelized T1/E1 and PRI HWIC (data only)
                        ,phwic-2ce1t1pri(4961)               -- 2 port channelized T1/E1, and PRI HWIC (data only)
                        ,phwic-serial4as(4962)               -- 4-Port Async/Sync Serial HWIC
                        ,phwic-serial4t(4963)                -- 4-Port Serial HWIC
                        ,phwic-4t1e1(4964)                   -- 4 port clear channel T1/E1 HWIC
                        ,phwic-serial8a(4965)                -- 8-Port Async HWIC
                        ,phwic-serial8as(4966)               -- 8-Port Async/Sync Serial HWIC, EIA-232
                        ,pism-vpn-29(4967)                   -- 3DES/AES/SUITE-B VPN Encryption module
                        ,pvic2-fxo2(4968)                    -- Two-port Voice Interface Card - FXO (Universal)
                        ,pvic2-fxo4(4969)                    -- Four-port Voice Interface Card - FXO (Universal)

                        ,pwr-vg3x0pwr-ac(5004)               -- This card provides AC power supply in voice gateway VG310 and VG320
                        ,pwr-vg3x0pwr-dc(5005)               -- This card provides DC power supply in voice gateway VG310 and VG320
                        ,pwr-rt3201-ac(5009)                 -- Router 3201 AC Power Supply
                        ,pwr-rt3211-ac(5010)                 -- Router 3211 AC Power Supply
                        ,pwr-rt3211-dc(5011)                 -- Router 3211 DC Power Supply
                        ,pwr-rt32-ac(5012)                   -- Router 3200 AC Power Supply
                        ,pwr-rt3211rps-adptr(5013)           -- Router 3211 RPS Adapter for use with External RPS
                        ,pwr-rt32rps-adptr(5014)             -- Router 3200 RPS Adapter for use with External RPS
                        ,pwr-rt2241-ac(5015)                 -- Router 2241 AC Power Supply
                        ,pwr-ac-30w(5016)                    -- Power Supply 30 Watt AC
                        ,pwr-poe-ac-60w(5017)                -- Power Supply 60 Watt AC
                        ,pwr-ac-60w-v2(5018)                 -- Power Supply 60 Watt AC
                        ,pwr-poe-ac-125w(5019)               -- POE power supply
                        ,pwr-c2911pwr-dcpoe(5021)            -- Cisco 2911 DC Power Supply with Power Over Ethernet support

                        ,ws-c2960xr-48td-i(5051)        -- Catalyst 2960XR 48 Gig Downlinks and 2 SFP+ uplinks IP Lite Stackable
                        ,ws-c2960xr-24pd-i(5052)        -- Catalyst 2960XR 24 Gig Downlinks and 2 SFP+ uplinks IP Lite Stackable with POE support for 370W
                        ,ws-c2960xr-24td-i(5053)        -- Catalyst 2960XR 24 Gig Downlinks and 2 SFP+ uplinks IP Lite Stackable
                        ,ws-c2960xr-48fps-i(5054)       -- Catalyst 2960XR 48 Gig Downlinks and 4 SFP uplinks IP Lite Stackable with POE support for 740W
                        ,ws-c2960xr-48lps-i(5055)       -- Catalyst 2960XR 48 Gig Downlinks and 4 SFP uplinks IP Lite Stackable with POE support for 370W
                        ,ws-c2960xr-48ts-i(5056)        -- Catalyst 2960XR 48 Gig Downlinks and 4 SFP uplinks IP Lite Stackable
                        ,ws-c2960xr-24ps-i(5057)        -- Catalyst 2960XR 24 Gig Downlinks and 4 SFP uplinks IP Lite Stackable with POE support for 370W
                        ,ws-c2960xr-24ts-i(5058)        -- Catalyst 2960XR 24 Gig Downlinks and 4 SFP uplinks IP Lite Stackable
                        ,ws-c2960xr-48fpd-l(5059)       -- Catalyst 2960XR 48 Gig Downlinks and 2 SFP+ uplinks LAN Base Stackable with POE support for 740W
                        ,ws-c2960xr-48lpd-l(5060)       -- Catalyst 2960XR 48 Gig Downlinks and 2 SFP+ uplinks LAN Base Stackable with POE support for 370W
                        ,ws-c2960xr-48td-l(5061)        -- Catalyst 2960XR 48 Gig Downlinks and 2 SFP+ uplinks LAN Base Stackable
                        ,ws-c2960xr-24pd-l(5062)        -- Catalyst 2960XR 24 Gig Downlinks and 2 SFP+ uplinks LAN Base Stackable with POE support for 370W
                        ,ws-c2960xr-24td-l(5063)        -- Catalyst 2960XR 24 Gig Downlinks and 2 SFP+ uplinks LAN Base Stackable
                        ,ws-c2960xr-48fps-l(5064)       -- Catalyst 2960XR 48 Gig Downlinks and 4 SFP uplinks LAN Base Stackable with POE support for 740W
                        ,ws-c2960xr-48lps-l(5065)       -- Catalyst 2960XR 48 Gig Downlinks and 4 SFP uplinks LAN Base Stackable with POE support for 370W
                        ,ws-c2960xr-48ts-l(5066)        -- Catalyst 2960XR 48 Gig Downlinks and 4 SFP uplinks LAN Base Stackable
                        ,ws-c2960xr-24ps-l(5067)        -- Catalyst 2960XR 24 Gig Downlinks and 4 SFP uplinks LAN Base Stackable with POE support for 370W
                        ,ws-c2960xr-24ts-l(5068)       -- Catalyst 2960XR 24 Gig Downlinks and 4 SFP uplinks LAN Base Stackable

                       ,cpu-c891f(5101)                      -- C891F router with 1 Giga Ethernet Primary WAN, 1 SFP (Small Form-factor Pluggable) Giga Ethernet Primary WAN, 1 Fast Ethernet WAN, 1 V.92, 1 ISDN BRI S/T interface, 8 Giga Ethernet LAN, 4 PoE Optional, 1 USB 2.0 port, 1 Console/Aux port, 256MB flash memory and 1GB DRAM
                       ,cpu-c891fw(5102)                     -- C891FW router with 1 Giga Ethernet Primary WAN, 1 SFP (Small Form-factor Pluggable) Giga Ethernet Primary WAN, 1 Fast Ethernet WAN, 1 V.92, 1 ISDN BRI S/T interface, 1 Dual 2.4/5GHz Wireless LAN, 8 Giga Ethernet LAN, 4 PoE Optional, 1 USB 2.0 port, 1 Console/Aux port, 256MB flash memory and 1GB DRAM
                       ,cpu-vg310(5103)                      -- cpu card for VG310 voice gateway
                       ,cpu-vg320(5104)                      -- cpu card for VG320 voice gateway
                       ,cpu-rt1081k9(5105)                   -- Router 1081 Fast Ethernet Router
                       ,cpu-rt1091k9(5106)                   -- Router 1091 GigaE SecRouter
                       ,cpu-rt2241k9(5107)                   -- Router 2241 w/2 GE,2 EHWIC slots,256MB CF,512MB DRAM,IP Base
                       ,cpu-rt2221k9(5108)                   -- Router 2221 Modular Router, 2 GE, 2 EHWIC slots, 512DRAM, IP Base
                       ,cpu-rt2241wck9(5109)                 -- Router 2241 Router w/802.11 a/b/g/n China Compliant WLAN ISM
                       ,cpu-rt3211k9(5110)                   -- Router 3211 w/3 GE,4 EHWIC,2 DSP,1 SM,256MB CF,512MB DRAM,IPB
                       ,cpu-rt3221k9(5111)                   -- Router 3221 w/3 GE,4 EHWIC,3 DSP,1 SM,256MB CF,512MB DRAM,IPB
                       ,cpu-rt3201k9(5112)                   -- Router 3201 w/2 GE,4 EHWIC,2 DSP,256MB CF,512MB DRAM,IP Base
                       ,cpu-899gw4g(5113)                    -- CPU for Cisco 899GW4G series products
                       ,cpu-896vagw4g(5114)                  -- CPU for Cisco 896VAGW4G series products
                       ,cpu-897vagw4g(5115)                  -- CPU for Cisco 897VAGW4G series products
                       ,cpu-898eagw4g(5116)                  -- CPU for Cisco 898EAGW4G series products
                       ,cpu-819gw4g(5117)                    -- CPU for Cisco 819GW4G series products
                       ,pwic-1am-v2(5118)                    -- one-port Analog Modem Interface card
                       ,phwic-1dsut1(5119)                   -- 1-Port T1/Fractional T1 DSU/CSU WAN Interface Card
                       ,pehwic-va-dsl-a(5120)                -- Multi-Mode Annex A DSL Card
                       ,pehwic-va-dsl-m(5121)                -- Multi-Mode Annex M DSL Card
                       ,cpu-c897vab(5122)                    -- C897VAB-K9 router with 1 VDSL2 with bonding/ADSL2+ WAN , 1 Giga Ethernet WAN, 1 SFP (Small Form-factor Pluggable) Giga Ethernet Primary WAN, 8 Giga Ethernet LAN,4 PoE Optional, 1 USB 2.0 port, 1 Console/Aux port, 256MB flash memory and 1GB DRAM
                       ,psm-2k-23es-1ge(5123)                -- Enhanced EtherSwitch, L2, SM, 23 FE, 1 GE
                       ,psm-3k-16ge-poe(5124)            -- Enhanced EtherSwitch, L2/L3, SM, 16GE, POE
                       ,psm-xd-2k-48es-2sfp(5125)            -- Enhanced EtherSwitch, L2, SM, 48 FE, 2 SFP
                       ,psm-xd-3k-48-es-2sfp(5126)           -- Enhanced EtherSwitch, L2/L3, SM, 48 FE, 2 SFP, POE
                       ,psm-xd-3k-48ge-2sfp-poe(5127)        -- Enhanced EtherSwitch, L2/L3, SM, 48 FE 1, GE, 2 SFP,POE
                       ,psm-2k-15es-1ge-poe(5128)            -- Enhanced EtherSwitch, L2, SM, 15 FE, 1 GE, POE
                       ,psm-2k-23es-1ge-poe(5129)           -- Enhanced EtherSwitch, L2, SM, 23 FE, 1 GE, POE
                       ,psm-3k-15es-1ge-poe(5130)            -- Enhanced EtherSwitch, L2/L3, SM, 15 FE, 1 GE, POE
                       ,psm-3k-23-es-1ge-poe(5131)           -- Enhanced EtherSwitch, L2/L3, SM, 23 FE, 1 GE, POE
                       ,psm-3k-24ge-poe(5132)                -- Enhanced EtherSwitch, L2/L3, SM, 24 GE, POE
                       ,psm-1nm(5133)                        -- Network Module Adapter for SM Slot on Router 2200, 3200
                       ,phdv2-port2(5135)                    -- IP Communications High-Density Digital Voice NM with 2 T1/EX

                       ,cpu-809(5136)                        -- CPU for Cisco 809 series products
                       ,cpu-829(5137)                        -- CPU for Cisco 829 series products
                       ,cpu-2911-t(5144)                     -- CISCO2911-T/K9 with 3 GE, 4 EHWIC, 2 DSP, 1 SM , 256 MB CF, 512 MB DRAM, IPB, extended temperature range from -5 to 60 C
                       ,c400r-g(5145)                        -- Cisco C400R series router 3G interface card
                       ,cpu-891-24x(5146)                    -- C891-24X Router series with 2 Giga Ethernet WAN Xor'ed with SFP (Small Form-factor Pluggable), 24 Giga Ethernet LAN with 8 PoE, 1 USB 2.0 port, 1 Console/Aux port, 256MB flash memory and 512MB/1GB DRAM
                       ,cpu-c414r(5147)                      -- C414R K9  router with  2-1 Giga Ethernet WAN, 2 WAN modules, 4-1 Giga Ethernet LAN, 1 USB 2.0 port, 1 Console port and 512 MB DRAM
                       ,cpu-c418r(5148)                      -- C418R K9  router with  2-1 Giga Ethernet WAN, 2 WAN modules, 8-1 Giga Ethernet LAN, 1 USB 2.0 port, 1 Console and 1 GB DRAM
                       ,c400r-1t(5149)                       -- Cisco C400R series router 12 in 1 serial interface card
                       ,wim-g(5153)                          -- WIM-3G, Dual SIM, Multimode HSPA+/CDMA WAN Interface Module
                       ,cpu-c841m-4x(5154)                   -- CPU for C841M-4X/K9 router
                       ,cpu-c841m-8x(5155)                   -- CPU for C841M-8X/K9 router
                       ,wim-1t(5156)                         -- WIM-1T, Single Port 12-in-1 Serial WAN Interface Module
                       ,cpu-819gwlte(5157)                  -- c819GWLTE router with 1 4G LTE interface, 4 Fast Ethernet LAN interfaces, 1GE WAN, 1 Serial(sync/async) interface, 2 terminal lines, 1 Virtual Private Network (VPN) Module, 1 cisco Embedded AP, 1 Console/Aux port, and 1GB FLASH
                       ,ehwic-4g-lte-la(5159)                -- 4G WWAN EHWIC - Latin America Multimode LTE/DCHSPA+/HSPA+/HSPA/UMTS/EDGE/GPRS
                       ,ehwic-4g-lte-ci(5160)                -- 4G WWAN EHWIC - China and India Multimode LTE/DC-HSPA+/HSPA+/HSPA/UMTS/EDGE/GPRS
                       ,ehwic-4g-lte-jn(5161)                -- 4G WWAN EHWIC - Japan Multimode LTE/DC-HSPA+/HSPA+/HSPA/UMTS/EDGE/GPRS
                       ,cpu-86xvaev2(5162)                   -- CPU for C86xVAE series products
                       ,cpu-2911a-3ge(5166)                  -- c2911a Motherboard, with 3 GE
                       ,cpu-807(5167)                        -- CPU for Cisco 807 series products
                       ,wim-lte-as(5168)                     -- WIM-4G, Single SIM, Global (India) Multimode LTE WAN Interface Module
                       ,cpu-941j-4p(5169)                    -- C941J-4P Router with 4 GE LAN interface, 2GE WAN interface, 1 USB 3.0, 2GB DDR4 DRAM(x64) with ECC, 2GB   eMMC pSLC, Dual 16MB NOR Bootflash
                       ,cpu-921-4p(5170)                     -- C921-4P Router with 4 GE LAN interface, 2GE WAN interface, 1 USB 3.0, 1GB DDR4 DRAM(x32) with ECC, 2GB    eMMC pSLC, Dual 16MB NOR Boot flash
                       ,cpu-931-4p(5171)                     -- C931-4P Router with Internal Power supply , 4 GE LAN interface, 2GE WAN interface, 1 USB 3.0, 1GB DDR4 DRAM(x32) with ECC, 2GB   eMMC pSLC, Dual 16MB NOR Boot flash
                       ,cpu-941j-4plte-jn(5172)              -- C941J-4PLTEJN Router with 1 4G LTE interface, 4 GE LAN interface, 2GE WAN interface, 1 USB 3.0, 2GB DDR4  DRAM(x32) with ECC, 2GB eMMC pSLC, Dual 16MB NOR Boot flash
                       ,cpu-921-4plte(5173)                  -- C921-4PLTE Router with 1 4G LTE interface, 4 GE LAN interface, 2GE WAN interface, 1 USB 3.0, 1GB DDR4     DRAM (x32) with ECC, 2GB eMMC pSLC, Dual 16MB NOR Bootflash
                       ,cpu-921j-4p(5174)                    -- C921J-4P Router with, 4 GE LAN interface, 2GE WAN interface, 1 USB 3.0, 1GB DDR4 DRAM(x32) with ECC, 2GB  eMMC pSLC, Dual 16MB NOR Boot flash
                       ,cpu-927-4p(5175)                     -- C927-4P Router with, 1 Eth+DSL,4 GE LAN interface, 1GE WAN interface, 1 USB 3.0, 1GB DDR4 DRAM(x32) with  ECC, 2GB eMMC pSLC, Dual 16MB NOR Bootflash
                       ,cpu-927-4pm(5176)                    -- C927-4PM Router with, 1 Eth+DSL,4 GE LAN interface, 1GE WAN interface, 1 USB 3.0, 1GB DDR4 DRAM(x32) with ECC, 2GB eMMC pSLC, Dual 16MB NOR Bootflash
                       ,cpu-926-4p(5177)                     -- C926-4P Router with, 1 Eth+DSL,4 GE LAN interface, 1GE WAN interface, 1 USB 3.0, 1GB DDR4 DRAM(x32) with  ECC, 2GB eMMC pSLC, Dual 16MB NOR Bootflash
                       ,cpu-927-4plte(5178)                  -- C927-4PLTE Router with, 1 LTE interface ,1 Eth+DSL,4 GE LAN interface, 1GE WAN interface, 1 USB 3.0, 1GB   DDR4 DRAM(x32) with ECC, 2GB eMMC pSLC, Dual 16MB NOR Boot flash
                       ,cpu-927-4pmltegb(5179)               -- C927-4PMLTEGB  Router with 1 Eth+DSL with Annex M, 1 LTE interface,4 GE LAN interface, 1GE WAN interface, 1 USB 3.0, 1GB DDR4 DRAM(x32) with ECC, 2GB eMMC pSLC, Dual 16MB NOR Bootflash
                       ,cpu-926-4pltegb(5180)                -- C926-4PLTEGB Router with 1 Eth+DSL, 1 LTE interface,4 GE LAN interface, 1GE WAN interface, 1 USB 3.0, 1GB DDR4 DRAM(x32) with ECC, 2GB eMMC pSLC, Dual 16MB NOR Bootflash
                       ,wim-lte-lt(5184)                     -- WIM-4G, Single SIM, Global (Mexico) Multimode LTE WAN Interface Module
                       ,wim-lte-al(5185)                     -- WIM-4G, Single SIM, Global (SEAsia) Multimode LTE WAN Interface Module
                       ,cpu-931j-4p(5186)                    -- C931J-4P Router with External Power Supply , 4 GE LAN interface, 2GE WAN interface, 1 USB 3.0, 1GB DDR4 DRAM(x32) with ECC, 2GB eMMC pSLC, Dual 16MB NOR Boot flash
                       ,grwic-4g-lte-la(5187)                -- 4G WWAN GRWIC - Latin America and Asia Pacific Multimode LTE/DC-HSPA+/HSPA+/HSPA/UMTS/EDGE/GPRS
                       ,grwic-4g-lte-ea(5188)                -- 4G WWAN GRWIC - North America and Europe Multimode LTE/DC-HSPA+/HSPA+/HSPA/UMTS/EDGE/GPRS
                        }
                   ACCESS  read-only
                   STATUS  deprecated
                   DESCRIPTION
                           "Functional type of this card."
                   ::= { cardTableEntry 2 }

               cardDescr OBJECT-TYPE
                   SYNTAX  DisplayString
                   ACCESS  read-only
                   STATUS  deprecated
                   DESCRIPTION
                           "Text description of this card."
                   ::= { cardTableEntry 3 }

               cardSerial OBJECT-TYPE
                   SYNTAX  INTEGER
                   ACCESS  read-only
                   STATUS  deprecated
                   DESCRIPTION
                           "The serial number of this card, or zero if
                           unavailable."
                   ::= { cardTableEntry 4 }

               cardHwVersion OBJECT-TYPE
                   SYNTAX  DisplayString
                   ACCESS  read-only
                   STATUS  deprecated
                   DESCRIPTION
                           "Hardware revision level of this card, or an
                           empty string if unavailable."
                   ::= { cardTableEntry 5 }

               cardSwVersion OBJECT-TYPE
                   SYNTAX  DisplayString
                   ACCESS  read-only
                   STATUS  deprecated
                   DESCRIPTION
                           "Version of the firmware or microcode
                           installed on this card, or an empty string if
                           unavailable."
                   ::= { cardTableEntry 6 }

               cardSlotNumber OBJECT-TYPE
                   SYNTAX  INTEGER
                   ACCESS  read-only
                   STATUS  deprecated
                   DESCRIPTION
                           "Slot number relative to the containing card or
                           chassis, or -1 if neither applicable nor
                           determinable."
                   ::= { cardTableEntry 7 }

               cardContainedByIndex OBJECT-TYPE
                   SYNTAX  INTEGER
                   ACCESS  read-only
                   STATUS  deprecated
                   DESCRIPTION
                           "cardIndex of the parent card which
                           directly contains this card, or 0 if
                           contained by the chassis, or -1 if not
                           applicable nor determinable."
                   ::= { cardTableEntry 8 }

               cardOperStatus OBJECT-TYPE
                   SYNTAX  INTEGER {
                          not-specified(1),
                          up(2),
                          down(3),
                          standby(4)
                      }
                   ACCESS  read-only
                   STATUS  deprecated
                   DESCRIPTION
                           "The operational status of the card.
                           cardOperStatus is up when a card is
                           recognized by the device and is enabled for
                           operation. cardOperStatus is down if the
                           card is not recognized by the device, or if
                           it is not enabled for operation.
                           cardOperStatus is standby if the card is
                           enabled and acting as a standby slave"
                   ::= { cardTableEntry 9 }

               cardSlots OBJECT-TYPE
                   SYNTAX  INTEGER
                   ACCESS  read-only
                   STATUS  deprecated
                   DESCRIPTION
                           "Number of slots on this card, or 0 if no
                           slots or not applicable, or -1 if not
			   determinable."
                   ::= { cardTableEntry 10 }

               -- End of table


               chassisSlots OBJECT-TYPE
                   SYNTAX  INTEGER
                   ACCESS  read-only
                   STATUS  deprecated
                   DESCRIPTION
                           "Number of slots in this chassis, or -1 of
                           neither applicable nor determinable."
                   ::= { chassis 12 }

               cardIfIndexTable OBJECT-TYPE
                   SYNTAX  SEQUENCE OF CardIfIndexEntry
                   ACCESS  not-accessible
                   STATUS  deprecated
                   DESCRIPTION
                            "Chassis card table."
                   ::= { chassis 13 }

               cardIfIndexEntry OBJECT-TYPE
                   SYNTAX CardIfIndexEntry
                   ACCESS  not-accessible
                   STATUS  deprecated
                   DESCRIPTION
                            "Chassis card table."
                   INDEX { cardIfIndex }
               ::= { cardIfIndexTable 1 }

               CardIfIndexEntry ::=
                   SEQUENCE {
                       cardIfIndex
                           INTEGER,
                       cardIfSlotNumber
                           INTEGER,
                       cardIfPortNumber
                           INTEGER,
                       cardIfCardIndex
                           INTEGER,
                       cardIfConnectorTypeEnabled
                           INTEGER
                   }

               cardIfIndex OBJECT-TYPE
                   SYNTAX  INTEGER
                   ACCESS  read-only
                   STATUS  deprecated
                   DESCRIPTION
                           "matches RFC1213 ifTable IfIndex"
                   ::= { cardIfIndexEntry 1 }

               cardIfSlotNumber OBJECT-TYPE
                   SYNTAX  INTEGER
                   ACCESS  read-only
                   STATUS  deprecated
                   DESCRIPTION
                           "Chassis slot number, or -1 if neither
                           applicable nor determinable."
                   ::= { cardIfIndexEntry 2 }

               cardIfPortNumber OBJECT-TYPE
                   SYNTAX  INTEGER
                   ACCESS  read-only
                   STATUS  deprecated
                   DESCRIPTION
                           "Chassis port number, unique per port on a
                            given card if available. If cardIfPortNumber is not
                            applicable to the card, then the object instance
                            won't be populated"
                   ::= { cardIfIndexEntry 3 }

               cardIfCardIndex OBJECT-TYPE
                   SYNTAX  INTEGER
                   ACCESS  read-only
                   STATUS  deprecated
                   DESCRIPTION
                           "cardIndex of the card in the Chassis
                            cardTable which contains this interface, or -1 if
                            not applicable."
                   ::= { cardIfIndexEntry 4 }

               cardIfConnectorTypeEnabled OBJECT-TYPE
                   SYNTAX  INTEGER {
                           not-specified(1),
                           none (2),
                           rj-45 (3),
                           db-40 (4),
                           db-15 (5),
                           auto-select (6),
                           gbic-sx (7),
                           gbic-lx (8),
                           gbic-lh (9),
                           gbic-cx (10),
                           gbic-zx (11),
                           missing (12),
                           mmf-st (13),
                           mmf-sc (14),
                           rj-11 (15),
                           rj-48s (16),
                           rj-48c (17),
                           db-60 (18),
                           gbic-stack(19),
                           gbic-1000baset(20)
                   }
                   ACCESS  read-only
                   STATUS  deprecated
                   DESCRIPTION
                           "Interface connector type currently
                           enabled. Value will be 1 if not known or not
                           used, or 2 if none of this ports' interface
                           connectors are enabled."
                   ::= { cardIfIndexEntry 5 }

	       -- End of table

               chassisPartner OBJECT-TYPE
                   SYNTAX  INTEGER {
			cisco(1)
			,synoptics(2)
			,chipcom(3)
			,cabletron(4)
			,dec(5)
			,ncr(6)
			,usrobotics(7)
			,alcatel(8)
			,nec(9)
			,dsc(10)
			,microcom(11)
			,oki(12)
			,ubn(13)
			,hp(14)
			,samsung(15)
			,mitsubishi(16)
                   }
                   ACCESS  read-only
                   STATUS  deprecated
                   DESCRIPTION
                           "Used to determine if this is a partner
                            variant of a product."
                   ::= { chassis 14 }

               sysUpTimeAtLastChassisChange OBJECT-TYPE
                   SYNTAX  TimeTicks
                   ACCESS  read-only
                   STATUS  deprecated
                   DESCRIPTION
                           "Time in seconds/100 from the last cold
                           start to the last change in the chassis'
                           configuration. This value will be updated
                           whenever the chassis experiences a change
                           in the count, type, or slot position of
                           a card in cardTable."
                   ::= { chassis 15 }






               END
