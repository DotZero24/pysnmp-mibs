-- *****************************************************************
-- CISCO-WAN-CESM-CONN-STAT-MIB: CESM(Circuit Emulation Service )
--  Connection Statistics MIB in MGX82xx series.
--
-- December 2002, Subra Hegde
--
-- Copyright (c) 2002 by cisco Systems, Inc.
-- All rights reserved.
-- *****************************************************************

CISCO-WAN-CES-CONN-STAT-MIB DEFINITIONS ::= BEGIN
IMPORTS
        MODULE-IDENTITY,
        OBJECT-TYPE,
        Integer32,
        Counter32       FROM    SNMPv2-SMI
        MODULE-COMPLIANCE,
        OBJECT-GROUP    FROM    SNMPv2-CONF
      	cesmChan 	FROM    BASIS-MIB
        ciscoWan        FROM    CISCOWAN-SMI;

ciscoWanCesConnStatMIB MODULE-IDENTITY
        LAST-UPDATED    "200212240000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
    DESCRIPTION
        "The MIB module to provide CES Connections
        statistics.
        This MIB is supported in
        Circuit Emulation Service Modules(CESM)
        in MGX82xx, MGX88xx products.
        The channels and connections are used interchangeably
        in this mib.

        Terminologies Used:

          PXM : Processor Switch Service Module. This is the
                controller card used in MGX switches.

          CESM : Circuit Emulation Service Module.
                 The Card supporting Circuit Emulation Service."

    REVISION    "200212240000Z"
    DESCRIPTION
        "Initial version of the MIB.

        The content of this MIB was originally available
        in CISCO-WAN-AXIPOP-MIB defined using SMIv1.
        The applicable objects from CISCO-WAN-AXIPOP-MIB
        are defined using SMIv2 in this MIB. Also the
        descriptions of some of the objects have been
        modified."
    ::= { ciscoWan 43 }


cesmChanCntGrp          OBJECT IDENTIFIER ::= { cesmChan 2 }

cesmChanCntGrpTable OBJECT-TYPE
	SYNTAX	   SEQUENCE OF CesmChanCntGrpEntry
	MAX-ACCESS not-accessible
	STATUS	   current
	DESCRIPTION
	    "The statistics table for CES connections.
            For every entry in cesmChanCnfGrpTable, there
            will be an entry in this table."
	::= { cesmChanCntGrp 1 }

cesmChanCntGrpEntry OBJECT-TYPE
	SYNTAX	   CesmChanCntGrpEntry
	MAX-ACCESS not-accessible
	STATUS	   current
	DESCRIPTION
	    " An entry in the CES connection statistics table."
	INDEX	{ cesCntChanNum }
	::= { cesmChanCntGrpTable 1}

CesmChanCntGrpEntry ::=
    SEQUENCE {
        cesCntChanNum 	       Integer32,
	cesChanState           INTEGER,
	cesXmtATMState         INTEGER,
	cesRcvATMState         INTEGER,
	cesCellLossStatus      INTEGER,
	cesReassCells          Counter32,
	cesGenCells            Counter32,
	cesHdrErrors	       Counter32,
	cesPointerReframes     Counter32,
	cesLostCells           Counter32,
	cesBufUnderflows       Counter32,
	cesBufOverflows        Counter32,
	cesIngrDiscardedBytes  Counter32,
	cesUflowInsCells       Counter32,
	cesOflowDropBytes      Counter32,
	cesCellSeqMismatchCnt  Counter32,
	counterClrButton       INTEGER,
        cesChanSecUptime       Counter32,
        cesChanSignalingStatus INTEGER,
        cesChanStatusBitMap    Integer32
}

cesCntChanNum OBJECT-TYPE
        SYNTAX     Integer32 (16..2064)
	MAX-ACCESS read-only
	STATUS     current
	DESCRIPTION
            "This object identifies the channel number of the
            CESM channel. The value for this object is same as
            the value specified in 'cesCnfChanNum'."
        REFERENCE
            "CISCO-WAN-CES-CONN-MIB.my"
	::= { cesmChanCntGrpEntry 1}

cesChanState OBJECT-TYPE
	SYNTAX  INTEGER {
                    notConfigured (1),
		    okay          (2),
	            alarm         (3),
                    failed        (4)
		}
	MAX-ACCESS read-only
	STATUS     current
	DESCRIPTION
	    "This object indicates the channel/connection status.

            The possible value(s) are :

             notConfigured (1) : Channel is not configured
	     okay          (2) : channel is ok
	     alarm         (3) : channel is in alarm.
                                 The connection segment is not broken.
             failed        (4) : channel is failed.
                                 The connection segment is broken.
                                 This value is applicable when
                                 PXM running PNNI Control Software."
	::= { cesmChanCntGrpEntry 2}

cesXmtATMState OBJECT-TYPE
	SYNTAX  INTEGER {
                    other       (1),
		    normal      (2),
		    sendingAIS  (3),
		    sendingFERF (4)
		}
	MAX-ACCESS read-only
	STATUS     current
	DESCRIPTION
	    "This object indicates the transmit state of channel
	    on the ATM side (towards the network).

            The possible value(s) are :

            other(1)      : values other than mentioned below.
            normal(2)     : Channel is ok.
            sendingAIS(3) : Sending AIS signal
            sendingFERF(4): Sending FERF."
	::= { cesmChanCntGrpEntry 3}

cesRcvATMState OBJECT-TYPE
	SYNTAX  INTEGER {
                    other         (1),
	            normal        (2),
		    receivingAIS  (3),
		    receivingFERF (4)
		}
	MAX-ACCESS read-only
	STATUS     current
	DESCRIPTION
            "This variable indicates the receive state of channel
	    on the ATM side (from the network).

            The possible value(s) are :

            other(1)         : values other than mentioned below.
            normal(2)        : Channel is ok.
            receivingAIS (3) : receiving AIS signal
            receivingFERF(4) : receiving FERF."
	::= { cesmChanCntGrpEntry 4 }

cesCellLossStatus OBJECT-TYPE
    SYNTAX	INTEGER {
                    noLoss (1),
                    loss   (2)
                }
    MAX-ACCESS	read-only
    STATUS	current
    DESCRIPTION
        "When cells are lost for the CellLossIntegrationPeriod the value
        is set to loss ( 2). when cells are no longer lost, the value is
        set to noLoss(1)."
    ::= { cesmChanCntGrpEntry 5 }

cesReassCells OBJECT-TYPE
	SYNTAX	   Counter32
	MAX-ACCESS read-only
	STATUS     current
	DESCRIPTION
	    "The number of cells played out to T1/E1/T3E3 interface. It
            excludes cells that were discarded for any reason."
	::= { cesmChanCntGrpEntry 6 }

cesGenCells OBJECT-TYPE
	SYNTAX	   Counter32
	MAX-ACCESS read-only
	STATUS     current
	DESCRIPTION
            "The number of cells generated from T1/E1/T3E3 interface
            and sent towards network."
	::= { cesmChanCntGrpEntry 7 }

cesHdrErrors OBJECT-TYPE
	SYNTAX	   Counter32
	MAX-ACCESS read-only
	STATUS	   current
	DESCRIPTION
	    "The number of AAL-1 header errors detected and possibly
            corrected. Header errors include correctable and uncor-
            rectable CRC, plus bad parity."
	::= { cesmChanCntGrpEntry 8 }

cesPointerReframes OBJECT-TYPE
	SYNTAX	   Counter32
	MAX-ACCESS read-only
	STATUS     current
	DESCRIPTION
            "The number of events in which the AAL1 reassembler found
            that an SDT pointer is not where it is expected and the
            and the pointer must be reacquired.
            Not supported in CESM-8P due to limitation in AAL1 SAR.
	    Not applicable for CESM-4T1/E1 and CESM-T3/E3"
	::= { cesmChanCntGrpEntry 9 }

cesLostCells OBJECT-TYPE
	SYNTAX	   Counter32
	MAX-ACCESS read-only
	STATUS	   current
	DESCRIPTION
            "The number of cells lost in egress direction due to
	    AAL 1 header errors and missing cells."
	::= { cesmChanCntGrpEntry	10 }

cesBufUnderflows OBJECT-TYPE
	SYNTAX	   Counter32
	MAX-ACCESS read-only
	STATUS	   current
	DESCRIPTION
	    "The number of buffer underflows in Egress direction
            Not supported in CESM-8P due limitation in AAL1 SAR."
	::= { cesmChanCntGrpEntry 11 }

cesBufOverflows	OBJECT-TYPE
	SYNTAX	   Counter32
	MAX-ACCESS read-only
	STATUS	   current
	DESCRIPTION
	    "The number of buffer overflows in Egress direction
            Not supported in CESM-8P due to limitation in AAL1 SAR."
	::= { cesmChanCntGrpEntry 12 }

cesIngrDiscardedBytes OBJECT-TYPE
	SYNTAX	   Counter32
	MAX-ACCESS read-only
	STATUS	   current
	DESCRIPTION
            "The number of bytes discarded due to shelf alarm in ingress
            direction from port data.
            Not supported in CESM-8P."
	::= { cesmChanCntGrpEntry 13 }

cesUflowInsCells OBJECT-TYPE
	SYNTAX	   Counter32
	MAX-ACCESS read-only
	STATUS     current
	DESCRIPTION
	    "The number of All 1's cells inserted in case of Egress Buffer
	     Underflow Not supported in CESM-8P."
	::= { cesmChanCntGrpEntry 14 }

cesOflowDropBytes OBJECT-TYPE
	SYNTAX	   Counter32
	MAX-ACCESS read-only
	STATUS     current
	DESCRIPTION
            "The number of bytes discarded in Egress direction because of
	    Egress buffer overflow
            Not supported in CESM-8P."
	::= { cesmChanCntGrpEntry 15 }

cesCellSeqMismatchCnt OBJECT-TYPE
	SYNTAX	   Counter32
	MAX-ACCESS read-only
	STATUS     current
	DESCRIPTION
            "The number of times SAR received a valid out of sequence
            AAL-1 cell from CellBus."
	::= { cesmChanCntGrpEntry	16 }

counterClrButton OBJECT-TYPE
        SYNTAX  INTEGER {
                    noAction      (1),
                    resetCounters (2)
                }
        MAX-ACCESS  read-write
        STATUS  current
        DESCRIPTION
           "This object is used for clearing the counters
           in this table.
           If set to resetCounters(2), then counters will be
           cleared."
        DEFVAL { noAction }
	::= { cesmChanCntGrpEntry 17 }

cesChanSecUptime OBJECT-TYPE
	SYNTAX	   Counter32
	MAX-ACCESS read-only
	STATUS	   current
	DESCRIPTION
            "The number of seconds channel is in service
	    This object is only applicable for CESM-8P."
	::= { cesmChanCntGrpEntry 18 }

cesChanSignalingStatus OBJECT-TYPE
    SYNTAX  INTEGER {
                off-hook (1),
                on-hook  (2)
            }
    MAX-ACCESS read-only
    STATUS     current
    DESCRIPTION
        "This variable indicates the connection signalling status
        Connection will be in Idle suppression mode if it in on-hook.
        Not applicable for T3E3 and CESM-4P."
    ::= { cesmChanCntGrpEntry 19 }

cesChanStatusBitMap OBJECT-TYPE
    SYNTAX     Integer32 (0..'ff'h)
    MAX-ACCESS read-only
    STATUS     current
    DESCRIPTION
        "This variable indicates the consolidated bit
        map of the channel alarm state.

        Individual bit positions are as defined below.

        Bit position   Fail/Alarm     Reason
        ------------   ----------     ------
            0           Alarm       Reserved
            1           Alarm       n/w side AIS/RDI Rx
            2           Fail        Conditioned(A bit from n/w)
            3           Alarm       Reserved
            4           Fail        Reserved
            5           Fail        Reserved
            6           Alarm       Reserved
            7           Alarm       Cell loss alarm

            Fail bitmap mask : 0x34
            Alarm bitmap mask: 0xCB

            This object is not applicable to MGX Release 1.x."
    ::= { cesmChanCntGrpEntry 20 }


-- conformance information

cwcConnStatMIBConformance OBJECT IDENTIFIER ::=
                                    { ciscoWanCesConnStatMIB 2 }

cwcConnStatMIBGroups      OBJECT IDENTIFIER ::=
                                    { cwcConnStatMIBConformance 1 }

cwcConnStatMIBCompliances OBJECT IDENTIFIER ::=
                                    { cwcConnStatMIBConformance 2 }


-- compliance statements

cwcConnStatCompliance MODULE-COMPLIANCE
    STATUS  current
    DESCRIPTION
            "The compliance statement for broad band
            interface Connection Statistics MIB."
    MODULE  -- this module
        MANDATORY-GROUPS {
            cwcConnGenStatsGroup
        }

    GROUP cwcConnStatsGroup
    DESCRIPTION
        "Mandatory for those systems where there
         is no limitation in AAL1 SAR."
    ::= { cwcConnStatMIBCompliances 1 }

cwcConnGenStatsGroup OBJECT-GROUP
   OBJECTS {
        cesCntChanNum,
	cesChanState,
	cesXmtATMState,
	cesRcvATMState,
	cesCellLossStatus,
	cesReassCells,
	cesGenCells,
	cesHdrErrors,
	cesPointerReframes,
	cesLostCells,
	cesBufUnderflows,
	cesBufOverflows,
	cesIngrDiscardedBytes,
	cesUflowInsCells,
	cesOflowDropBytes,
	cesCellSeqMismatchCnt,
	counterClrButton,
        cesChanSecUptime,
        cesChanSignalingStatus,
        cesChanStatusBitMap
   }
   STATUS current
   DESCRIPTION
       "The objects related to Circuit Emulation
       connection statistics applicable for multiple
       cards(Service Modules)."
    ::= { cwcConnStatMIBGroups 1 }

cwcConnStatsGroup OBJECT-GROUP
   OBJECTS {
	cesPointerReframes,
	cesBufUnderflows,
	cesBufOverflows,
	cesIngrDiscardedBytes,
	cesUflowInsCells,
	cesOflowDropBytes
   }
   STATUS current
   DESCRIPTION
       "The objects related to Circuit Emulation
       connection statistics applicable for few
       cards(Service Module)."
    ::= { cwcConnStatMIBGroups 2 }

END
