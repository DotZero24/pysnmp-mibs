-- *****************************************************************
-- L A N O P T I C S - B R I D G E - O P T I O N - M I B . m y
--
-- March 1996, Keith Horil
--
-- Copyright (c) 1996 by cisco Systems, Inc.
-- All rights reserved.
-- *****************************************************************
--
-- This mib was developed by LanOptics



LANOPTICS-BRIDGE-OPTION-MIB DEFINITIONS ::= BEGIN

-- MIB II Extension Definitions for Bridge Manager Option

IMPORTS
         OBJECT-TYPE
       	        FROM RFC-1212
         enterprises
       	        FROM RFC1155-SMI;

	lanOptics      OBJECT IDENTIFIER  ::= { enterprises 224 }

	lanOpticsBridgeProxyAgent OBJECT IDENTIFIER ::= { lanOptics 6 }
	lanOpticsLMGRAgent 	OBJECT IDENTIFIER ::= { lanOpticsBridgeProxyAgent 8 }

lanOpticsLMGRLinkID  OBJECT-TYPE
     SYNTAX INTEGER(0..3)
     ACCESS read-only
     STATUS mandatory
     DESCRIPTION
        "When LMGR session is active with PCRouter card through PCBus -
         this variable gives the LRM Session Link Number (0-3) between
         the Host (SNMP agent) and the PCRouter LAN Reporting Mechanism."
     ::= { lanOpticsLMGRAgent 1 }

lanOpticsLMGRCaptCntrlLink  OBJECT-TYPE
     SYNTAX INTEGER {
           enabled (1)
       --    disabled (0)
     }
     ACCESS read-write
     STATUS mandatory
     DESCRIPTION
        "When LMGR session is active with PCRouter card through PCBus -
         this variable is by default enabled (1). It means that the Host
         (SNMP Agent) tries to link to the LRM with the Control Link
         (id = 0). If this MIB variable is disabled the Host tries
         to establish a session with the LRM through other links,
         and if succeeds, it doesn't try to capture link 0."
     ::= { lanOpticsLMGRAgent 2 }

END
