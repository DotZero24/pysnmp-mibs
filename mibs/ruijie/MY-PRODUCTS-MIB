-- *****************************************************************
-- MY-PRODUCTS-MIB.mib:  My Product Object Identifier Assignments
--
-- $Copyright$
--
-- *****************************************************************
--

MY-PRODUCTS-MIB DEFINITIONS ::= BEGIN

IMPORTS
        MODULE-IDENTITY,
        OBJECT-TYPE
                FROM SNMPv2-SMI
        MODULE-COMPLIANCE,
        OBJECT-GROUP,
        NOTIFICATION-GROUP
                FROM SNMPv2-CONF
        myModules,
        mySwitchProducts,
        myRouterProducts,
        myWirelessProducts
                FROM MY-SMI;

myProductsMIB MODULE-IDENTITY
        LAST-UPDATED "200203200000Z"
        ORGANIZATION "$Company$"
        CONTACT-INFO
                "
                Tel: $Telephone$

                E-mail: $E-mail$"
        DESCRIPTION
                "This module defines the object identifiers that are
            		assigned to various hardware platforms, and hence are
            		returned as values for sysObjectID"
        REVISION      "200203200000Z"
        DESCRIPTION
                "Initial version of this MIB module."
        ::= { myModules 1}

-- devices return a sysObjectID value that corresponds to the
-- device model number

-- ****************************** switch ***********************************

s2126G   OBJECT IDENTIFIER ::= { mySwitchProducts 1 }

s2126GL3 OBJECT IDENTIFIER ::= { mySwitchProducts 2 }

s2150G   OBJECT IDENTIFIER ::= { mySwitchProducts 3 }

s2150GL3 OBJECT IDENTIFIER ::= { mySwitchProducts 4 }

s4909 OBJECT IDENTIFIER ::= { mySwitchProducts 5 }

s3550-12G OBJECT IDENTIFIER ::= { mySwitchProducts 6 }

s3550-24G OBJECT IDENTIFIER ::= { mySwitchProducts 8 }

s21-STACKING OBJECT IDENTIFIER ::= { mySwitchProducts 11 }

s3550-24 OBJECT IDENTIFIER ::= { mySwitchProducts 12 }

s3550-48 OBJECT IDENTIFIER ::= { mySwitchProducts 13 }

s3550-12SFP-GT OBJECT IDENTIFIER ::= { mySwitchProducts 15 }

s6806 OBJECT IDENTIFIER ::= { mySwitchProducts 16 }

s6810 OBJECT IDENTIFIER ::= { mySwitchProducts 17 }

s2126S OBJECT IDENTIFIER ::= { mySwitchProducts 18 }

s2126S-STACKING OBJECT IDENTIFIER ::= { mySwitchProducts 19 }

s1908PLUS OBJECT IDENTIFIER ::= { mySwitchProducts 20 }

s1916PLUS OBJECT IDENTIFIER ::= { mySwitchProducts 21 }

s6506 OBJECT IDENTIFIER ::= { mySwitchProducts 22 }

s2126S-08  OBJECT IDENTIFIER ::= { mySwitchProducts 23 }

s2126S-16  OBJECT IDENTIFIER ::= { mySwitchProducts 24 }

s6806E OBJECT IDENTIFIER ::= { mySwitchProducts 25 }

s6810E OBJECT IDENTIFIER ::= { mySwitchProducts 26 }

s2026G OBJECT IDENTIFIER ::= { mySwitchProducts 27 }

s3750-24 OBJECT IDENTIFIER ::= { mySwitchProducts 28 }

s3750-48 OBJECT IDENTIFIER ::= { mySwitchProducts 29 }

s2126    OBJECT IDENTIFIER ::= { mySwitchProducts 30 }

s2126-STACKING    OBJECT IDENTIFIER ::= { mySwitchProducts 31 }

s2026F OBJECT IDENTIFIER ::= { mySwitchProducts 32 }

s3760-48 OBJECT IDENTIFIER ::= { mySwitchProducts 33 }

s3760-12SFP-GT OBJECT IDENTIFIER ::= { mySwitchProducts 34 }

s4009 OBJECT IDENTIFIER ::= { mySwitchProducts 35 }

s3526 OBJECT IDENTIFIER ::= { mySwitchProducts 36 }

s3512G OBJECT IDENTIFIER ::= { mySwitchProducts 37 }

hcl-12GCS-L3 OBJECT IDENTIFIER ::= { mySwitchProducts 38 }

hcl-24GS-L3 OBJECT IDENTIFIER ::= { mySwitchProducts 39 }

hcl-48TMS-2S-S OBJECT IDENTIFIER ::= { mySwitchProducts 40 }

s5750-24GT-12SFP OBJECT IDENTIFIER ::= { mySwitchProducts 41 }

s5750P-24GT-12SFP OBJECT IDENTIFIER ::= { mySwitchProducts 42 }

s8606 OBJECT IDENTIFIER ::= { mySwitchProducts 43 }

s8610 OBJECT IDENTIFIER ::= { mySwitchProducts 44 }

s9610 OBJECT IDENTIFIER ::= { mySwitchProducts 45 }

s9620 OBJECT IDENTIFIER ::= { mySwitchProducts 46 }

s2924 OBJECT IDENTIFIER ::= { mySwitchProducts 47 }

s3760-24 OBJECT IDENTIFIER ::= { mySwitchProducts 48 }

s3760-48V2 OBJECT IDENTIFIER ::= { mySwitchProducts 49 }

s3750E-24 OBJECT IDENTIFIER ::= { mySwitchProducts 50 }

s3750E-48 OBJECT IDENTIFIER ::= { mySwitchProducts 51 }

s3750E-12SFP-GT OBJECT IDENTIFIER ::= { mySwitchProducts 52 }

s5750S-24GT-12SFP OBJECT IDENTIFIER ::= { mySwitchProducts 53 }

s2128G OBJECT IDENTIFIER ::= { mySwitchProducts 54 }

s2927XG OBJECT IDENTIFIER ::= { mySwitchProducts 55 }

s3512GPLUS OBJECT IDENTIFIER ::= { mySwitchProducts 56 }

s6604 OBJECT IDENTIFIER ::= { mySwitchProducts 57 }

s6606 OBJECT IDENTIFIER ::= { mySwitchProducts 58 }

s6610 OBJECT IDENTIFIER ::= { mySwitchProducts 59 }

s5750-24SFP-12GT OBJECT IDENTIFIER ::= { mySwitchProducts 60 }

s5750-48GT-4SFP OBJECT IDENTIFIER ::= { mySwitchProducts 61 }

s5750S-48GT-4SFP OBJECT IDENTIFIER ::= { mySwitchProducts 62 }

s2328G OBJECT IDENTIFIER ::= { mySwitchProducts 63 }

s3250-48 OBJECT IDENTIFIER ::= { mySwitchProducts 64 }

s2951XG OBJECT IDENTIFIER ::= { mySwitchProducts 66 }

s3750-24-UB OBJECT IDENTIFIER ::= { mySwitchProducts 67 }

s3750-48-UB OBJECT IDENTIFIER ::= { mySwitchProducts 68 }

scg5510  OBJECT IDENTIFIER ::= { mySwitchProducts 69 }

s2052G  OBJECT IDENTIFIER ::= { mySwitchProducts 70 }

s2352G  OBJECT IDENTIFIER ::= { mySwitchProducts 71 }

s8614  OBJECT IDENTIFIER ::= { mySwitchProducts 72 }

s5650-24GT-4SFP  OBJECT IDENTIFIER ::= { mySwitchProducts 73 }

s5650-27XG  OBJECT IDENTIFIER ::= { mySwitchProducts 74 }

s5650-51XG  OBJECT IDENTIFIER ::= { mySwitchProducts 75 }

s5450-28GT  OBJECT IDENTIFIER ::= { mySwitchProducts 76 }

s3760E-24  OBJECT IDENTIFIER ::= { mySwitchProducts 77 }

s3250P-24  OBJECT IDENTIFIER ::= { mySwitchProducts 78 }

s2928G  OBJECT IDENTIFIER ::= { mySwitchProducts 79 }

s2952G  OBJECT IDENTIFIER ::= { mySwitchProducts 80 }

s2028G  OBJECT IDENTIFIER ::= { mySwitchProducts 81 }

s2528G  OBJECT IDENTIFIER ::= { mySwitchProducts 82 }

s2552G  OBJECT IDENTIFIER ::= { mySwitchProducts 83 }

s5750R-48GT-4SFP OBJECT IDENTIFIER ::= { mySwitchProducts 84 }

s5750P-48GT-4SFP OBJECT IDENTIFIER ::= { mySwitchProducts 85 }

s5750R-24GT-4SFP OBJECT IDENTIFIER ::= { mySwitchProducts 86 }

s5750P-24GT-4SFP OBJECT IDENTIFIER ::= { mySwitchProducts 87 }

s5750-24GT-4SFP OBJECT IDENTIFIER ::= { mySwitchProducts 88 }

s5750S-24GT-4SFP OBJECT IDENTIFIER ::= { mySwitchProducts 89 }

s5750-48GT-4SFP-A OBJECT IDENTIFIER ::= { mySwitchProducts 92 }

s5750-48GT-4SFP-AP OBJECT IDENTIFIER ::= { mySwitchProducts 93 }

-- s2352G OBJECT IDENTIFIER ::= { mySwitchProducts 94 }

nm2x-24esw OBJECT IDENTIFIER ::= { mySwitchProducts 95 }

nm2x-16esw OBJECT IDENTIFIER ::= { mySwitchProducts 96 }

-- ****************************** router ***********************************

r2620 OBJECT IDENTIFIER ::= { myRouterProducts 1 }

r2624 OBJECT IDENTIFIER ::= { myRouterProducts 2 }

r2690 OBJECT IDENTIFIER ::= { myRouterProducts 3 }

r2692 OBJECT IDENTIFIER ::= { myRouterProducts 4 }

r3642 OBJECT IDENTIFIER ::= { myRouterProducts 5 }

r3662 OBJECT IDENTIFIER ::= { myRouterProducts 6 }

nbr1000 OBJECT IDENTIFIER ::= { myRouterProducts 7 }

nbr200  OBJECT IDENTIFIER ::= { myRouterProducts 8 }

secvpn100 OBJECT IDENTIFIER ::= { myRouterProducts 9 }

r2632 OBJECT IDENTIFIER ::= { myRouterProducts 10 }

r1762 OBJECT IDENTIFIER ::= { myRouterProducts 11 }

rcms OBJECT IDENTIFIER ::= { myRouterProducts 12 }

hcl-r1762 OBJECT IDENTIFIER ::= { myRouterProducts 13 }

hcl-r2632 OBJECT IDENTIFIER ::= { myRouterProducts 14 }

hcl-r2692 OBJECT IDENTIFIER ::= { myRouterProducts 15 }

hcl-r3642 OBJECT IDENTIFIER ::= { myRouterProducts 16 }

hcl-r3662 OBJECT IDENTIFIER ::= { myRouterProducts 17 }

r3740 OBJECT IDENTIFIER ::= { myRouterProducts 18 }

nbr2000 OBJECT IDENTIFIER ::= { myRouterProducts 19 }

nbr300 OBJECT IDENTIFIER ::= { myRouterProducts 20 }

nbr1200 OBJECT IDENTIFIER ::= { myRouterProducts 21 }

nbr1500 OBJECT IDENTIFIER ::= { myRouterProducts 22 }

r2716 OBJECT IDENTIFIER ::= { myRouterProducts 23 }

r2724 OBJECT IDENTIFIER ::= { myRouterProducts 24 }

r3802 OBJECT IDENTIFIER ::= { myRouterProducts 25 }

r3804 OBJECT IDENTIFIER ::= { myRouterProducts 26 }

rsr50-20 OBJECT IDENTIFIER ::= { myRouterProducts 27 }

rsr50-40 OBJECT IDENTIFIER ::= { myRouterProducts 28 }

rsr50-80 OBJECT IDENTIFIER ::= { myRouterProducts 29 }

npe50-20 OBJECT IDENTIFIER ::= { myRouterProducts 30 }

rsr10-02 OBJECT IDENTIFIER ::= { myRouterProducts 31 }

rsr20-04 OBJECT IDENTIFIER ::= { myRouterProducts 32 }

vpn120 OBJECT IDENTIFIER ::= { myRouterProducts 33 }

npe80 OBJECT IDENTIFIER ::= { myRouterProducts 34 }

rsr20-24 OBJECT IDENTIFIER ::= { myRouterProducts 35 }

nm2-16esw OBJECT IDENTIFIER ::= { myRouterProducts 36 }

nm2-24esw OBJECT IDENTIFIER ::= { myRouterProducts 37 }

nmx-24esw OBJECT IDENTIFIER ::= { myRouterProducts 38 }

nmx-24esw-l2 OBJECT IDENTIFIER ::= { myRouterProducts 39 }

nmx-24esw-3gel3 OBJECT IDENTIFIER ::= { myRouterProducts 40 }

rsr20-14 OBJECT IDENTIFIER ::= { myRouterProducts 41 }

rsr30-44 OBJECT IDENTIFIER ::= { myRouterProducts 42 }

r2700v2v3 OBJECT IDENTIFIER ::= { myRouterProducts 43 }

r2700v5 OBJECT IDENTIFIER ::= { myRouterProducts 44 }

npe50-40 OBJECT IDENTIFIER ::= { myRouterProducts 45 }

rsr20-18 OBJECT IDENTIFIER ::= { myRouterProducts 46 }

-- ****************************** wireless ***********************************

wgp500 OBJECT IDENTIFIER ::= { myWirelessProducts 1 }


END
