-- *****************************************************************
-- MY-ANTI-ARPCHEAT-MIB.mib:  My Anti Arpcheat MIB file
--
-- $Copyright$
--
-- *****************************************************************

MY-ANTI-ARPCHEAT-MIB DEFINITIONS ::= BEGIN

IMPORTS
        MODULE-IDENTITY,
        OBJECT-TYPE,
        IpAddress
                FROM SNMPv2-SMI
        MacAddress
                FROM SNMPv2-TC
        MODULE-COMPLIANCE,
        OBJECT-GROUP
                FROM SNMPv2-CONF
        IfIndex
                FROM MY-TC
        VlanId
                FROM Q-BRIDGE-MIB
        myMgmt
                FROM MY-SMI;

myAntiArpcheatMIB MODULE-IDENTITY
        LAST-UPDATED "200701290000Z"
        ORGANIZATION "$Company$"
        CONTACT-INFO
                "
                Tel: $Telephone$

                E-mail: $E-mail$"
        DESCRIPTION
                "This module defines my anti arpcheat mibs."
        REVISION      "200701290000Z"
        DESCRIPTION
                "Initial version of this MIB module."
        ::= { myMgmt 41}

myAntiArpcheatMIBObjects OBJECT IDENTIFIER ::= { myAntiArpcheatMIB 1 }

--
--  user management
--

myTrustedArpDelete OBJECT-TYPE
    SYNTAX Integer32
    MAX-ACCESS read-write
    STATUS      current
    DESCRIPTION
            "该变量设置为0值表示删除当前所有的可信任ARP
	    和二层接口绑定,设置为非0不做任何处理"
    ::= { myAntiArpcheatMIBObjects 1 }


myTrustedArpTable OBJECT-TYPE
    SYNTAX  SEQUENCE OF MyTrustedArpEntry
    ACCESS  not-accessible
    STATUS  current
    DESCRIPTION
            "用于设置可信任ARP，并进行二层接口绑定的表。"
   ::= { myAntiArpcheatMIBObjects 2 }

myTrustedArpEntry OBJECT-TYPE
    SYNTAX  MyTrustedArpEntry
    ACCESS  not-accessible
    STATUS  current
    DESCRIPTION
            "可信任ARP和二层接口绑定表。"
    INDEX   { trustedArpIfIndex,
              trustedArpIp }

    ::= { myTrustedArpTable 1 }

MyTrustedArpEntry ::=
    SEQUENCE {
            trustedArpIfIndex
                     IfIndex,
	          trustedArpIp
                     IpAddress,
            trustedArpMediaPhysAddress
                     MacAddress,
            trustedArpVlan
	                   VlanId,
            trustedArpOperationType
                     Integer32
    }

trustedArpIfIndex OBJECT-TYPE
    SYNTAX  IfIndex
    ACCESS  read-create
    STATUS  current
    DESCRIPTION
            "可信任ARP所对应的接口。"
    ::= { myTrustedArpEntry 1 }

trustedArpIp OBJECT-TYPE
     SYNTAX  IpAddress
     ACCESS  read-create
     STATUS  current
     DESCRIPTION
             "可信任ARP所对应的IP地址。"
     ::= { myTrustedArpEntry 2 }

trustedArpMediaPhysAddress OBJECT-TYPE
     SYNTAX  MacAddress
     ACCESS  read-write
     STATUS  current
     DESCRIPTION
             "可信任ARP所对应的MAC地址"
     ::= { myTrustedArpEntry 3 }

trustedArpVlan OBJECT-TYPE
        SYNTAX  VlanId
        MAX-ACCESS  read-write
        STATUS  current
        DESCRIPTION
              "可信任ARP对应接口所属的VLAN ID"
    ::= { myTrustedArpEntry 4 }

trustedArpOperationType OBJECT-TYPE
    SYNTAX Integer32
    MAX-ACCESS read-write
    STATUS      current
    DESCRIPTION
            "该变量设置为0表示删除该可信任ARP和
	    二层接口绑定，该变量设置为1表示添加
	    该可信任ARP和二层接口绑定，其它值表
	    示不做任何操作。"
    ::= { myTrustedArpEntry 5 }

-- compliance statements

myAntiArpcheatMIBConformance OBJECT IDENTIFIER ::= { myAntiArpcheatMIB 2 }
myAntiArpcheatMIBCompliances OBJECT IDENTIFIER ::= { myAntiArpcheatMIBConformance 1 }
myAntiArpcheatMIBGroups      OBJECT IDENTIFIER ::= { myAntiArpcheatMIBConformance 2 }

myAntiArpcheatMIBCompliance MODULE-COMPLIANCE
        STATUS  current
        DESCRIPTION
                "The compliance statement for entities which implement
                the My Anti Arpcheat MIB"
        MODULE  -- this module
                MANDATORY-GROUPS { myAntiArpcheatMIBGroup
                 }

        ::= { myAntiArpcheatMIBCompliances 1 }

-- units of conformance

myAntiArpcheatMIBGroup OBJECT-GROUP
        OBJECTS {
         myTrustedArpDelete,
	       trustedArpIfIndex,
	       trustedArpIp,
         trustedArpMediaPhysAddress,
         trustedArpVlan,
         trustedArpOperationType
        }
        STATUS  current
        DESCRIPTION
                "A collection of objects providing anti arpcheat management and
                opertion to a My agent."
        ::= { myAntiArpcheatMIBGroups 1 }

END
