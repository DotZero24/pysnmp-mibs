-- Module Name: HMS131R4.MIB (SCTE 94-1)
-- SCTE Status: Draft Revision 4

SCTE-HMS-HE-RF-AMP-MIB DEFINITIONS ::= BEGIN

IMPORTS
    MODULE-COMPLIANCE, OBJECT-GROUP
	FROM SNMPv2-CONF
    OBJECT-TYPE, MODULE-IDENTITY, Unsigned32
        FROM SNMPv2-SMI
    DisplayString
        FROM SNMPv2-TC
    entPhysicalIndex
        FROM ENTITY-MIB
    HeFaultStatus,
    HeTenthdB, HeTenthdBmV
        FROM SCTE-HMS-HEADENDIDENT-MIB
    heRFAmplifierGroup
       FROM SCTE-HMS-HE-RF-MIB;


heRFAmpMIB MODULE-IDENTITY
    LAST-UPDATED "200309110000Z"  -- Sep 11, 2003
    ORGANIZATION "SCTE HMS Working Group"
    CONTACT-INFO
            "SCTE HMS Subcommittee, Chairman
             mailto: standards@SCTE.org"

    DESCRIPTION
		" Change Log:
		  1.  Added Unsigned32 to IMPORTS
		  2.  Removed TEXTUAL-CONVENTION from IMPORTS
		  3.  Corrected 4 digit date code defined in RFC2578
		  4.	Changed the text description of SNMPv2 to SNMP for
			heRFAmpBasicCompliance MODULE-COMPLIANCE
		  5.	Changed OID number of heRFAmpMIBCompliances
			to 1 instead of 2
		  6.	Changed Rf to RF"

    REVISION  "200309110000Z"

    DESCRIPTION
		" Change Log:
		  1.  Reworded the text description for heRFAmpSlopeControl."

	REVISION  "200308290000Z"

        DESCRIPTION
                "The MIB module for the HMS HE RF Amp module
				entities.

				This MIB module is for representing RF
				Amp equipment present in the headend (or indoor)
				and is supported by a SNMP agent.

				This MIB is intended to describe an indoor
				headend amplifier with one input port and one
				or more output ports.

				Refer to the associated notes for information on what
				SNMP responses should be returned for unsupported
				enumerations."

    ::=  {  heRFAmplifierGroup 1  }

heRFAmpMIBObjects OBJECT IDENTIFIER ::= { heRFAmpMIB 1}


-- Every RF Amp described above is modeled by the tables presented
-- in this MIB module. These tables extend the entPhysicalTable
-- according to RFC 2737. The extension index entPhysicalIndex uniquely
-- identifies the RF Amp.

-- Every RF Amp is also modeled by the following tables:
--      entPhysicalEntry - 1 row; (defined in document: RFC2737)
--      heCommonEntry    - 1 row. (defined in document: HMS111)

-- Every RF Amp module will have its alarms modeled by the table:
--		propertyEntry - x rows; (defined in document: HMS026)
--		(where x is the nos. of alarmable analog properties supported
--      by the RF Amp)

--		discretePropertyEntry - y rows; (defined in document: HMS026)
--		(where y is the nos. of alarmable digital properties supported by
--      the RF Amp)

-- Every RF Amp module will have a list of currently active
-- alarms modeled by the table:
--		currentAlarmEntry - z rows; (defined in document: HMS026)
--		(where z is the nos. of current active alarms in the RF
--        Amp)

-- Thus, a RF Amp with one input and two outputs
-- will be represented by one row in entPhysicalTable, one row in
-- heCommonTable, one row in heRFAmpUnitTable, and two rows
-- in heRFAmpOutputTable.




--      the RF Amp Unit Table
heRFAmpUnitTable OBJECT-TYPE
    SYNTAX      SEQUENCE OF HeRFAmpUnitEntry
    MAX-ACCESS  not-accessible
    STATUS      current
    DESCRIPTION
            "A table containing information about RF Amp used
            in an indoor environment."
    ::= { heRFAmpMIBObjects 1 }

heRFAmpUnitEntry OBJECT-TYPE
    SYNTAX HeRFAmpUnitEntry
    MAX-ACCESS not-accessible
    STATUS current
    DESCRIPTION
            "List of information about each RF Amp."
    INDEX { entPhysicalIndex }
        ::= { heRFAmpUnitTable 1 }

HeRFAmpUnitEntry ::= SEQUENCE
{
    heRFAmpGainControlMode			INTEGER,
	heRFAmpAttenuatorControl        HeTenthdB,
	heRFAmpSlopeControl				HeTenthdB
}

heRFAmpGainControlMode OBJECT-TYPE
    SYNTAX      INTEGER {
        none(1),
        alc(2),
		asc(3),
		agc(4),
		alsc(5)
    }
    MAX-ACCESS	  read-write
    STATUS          current
    DESCRIPTION
           "This controls and/or reports the amplifier
		   control mode.
		   none - no automatic control provided
		   alc - automatic level control
		   asc - automatic slope control
		   agc - automatic gain control
		   alsc - automatic level slope control
		   "

    ::= { heRFAmpUnitEntry 1 }

heRFAmpAttenuatorControl OBJECT-TYPE
    SYNTAX      HeTenthdB
    MAX-ACCESS	  read-write
    STATUS          current
    DESCRIPTION
           "This controls and reports the setting of an attenuator
		   in the amplifier RF chain.
		   "

    ::= { heRFAmpUnitEntry 2 }

heRFAmpSlopeControl OBJECT-TYPE
    SYNTAX      HeTenthdB
    MAX-ACCESS	  read-write
    STATUS          current
    DESCRIPTION
           "This controls and reports the slope setting of the amplifier.
		   "

    ::= { heRFAmpUnitEntry 3 }

--      the RF Amp Output Table
heRFAmpOutputTable OBJECT-TYPE
    SYNTAX      SEQUENCE OF HeRFAmpOutputEntry
    MAX-ACCESS  not-accessible
    STATUS      current
    DESCRIPTION
            "A table containing information about each RF Amp
			output used in an indoor environment."
    ::= { heRFAmpMIBObjects 2 }

heRFAmpOutputEntry OBJECT-TYPE
    SYNTAX HeRFAmpOutputEntry
    MAX-ACCESS not-accessible
    STATUS current
    DESCRIPTION
            "List of information about each RF Amp output."
    INDEX { entPhysicalIndex, heRFAmpOutputIndex }
        ::= { heRFAmpOutputTable 1 }

HeRFAmpOutputEntry ::= SEQUENCE
{
	heRFAmpOutputIndex			  Unsigned32,
    heRFAmpOutputDescription      DisplayString,
	heRFAmpOutputLevel			  HeTenthdBmV,
	heRFAmpOutputAttenuatorControl      HeTenthdB
}

heRFAmpOutputIndex OBJECT-TYPE
    SYNTAX      Unsigned32
    MAX-ACCESS  not-accessible
    STATUS      current
    DESCRIPTION
            "Index number corresponding to the RF Output."
    ::= { heRFAmpOutputEntry 1 }

heRFAmpOutputDescription OBJECT-TYPE
	SYNTAX          DisplayString (SIZE (0..32))
	MAX-ACCESS		read-only
	STATUS          current
	DESCRIPTION
		"A description of the Amp output.  The description text is
		to be determined by the equipment manufacturer.  For example,
		Output A or Secondary Output."
    ::= { heRFAmpOutputEntry 2 }

heRFAmpOutputLevel OBJECT-TYPE
	SYNTAX          HeTenthdBmV
	MAX-ACCESS		read-only
	STATUS          current
	DESCRIPTION
		"The output level of the RF amplifier output."
    ::= { heRFAmpOutputEntry 3 }


heRFAmpOutputAttenuatorControl OBJECT-TYPE
    SYNTAX      HeTenthdB
    MAX-ACCESS	  read-write
    STATUS          current
    DESCRIPTION
           "This controls and reports the setting of an attenuator
		   in the amplifier RF chain.
		   "
    ::= { heRFAmpOutputEntry 4 }

-- conformance information
heRFAmpMIBConformance OBJECT IDENTIFIER ::= { heRFAmpMIB 2 }

heRFAmpMIBCompliances OBJECT IDENTIFIER ::= { heRFAmpMIBConformance 1 }

heRFAmpMIBGroups      OBJECT IDENTIFIER ::= { heRFAmpMIBConformance 2 }

heRFAmpBasicCompliance MODULE-COMPLIANCE
    STATUS  current
    DESCRIPTION
            "The compliance statement for SNMP HMS Headend RF
			Amp entities which implement the SNMP
			heRFAmpMIB."
    MODULE  -- this module
        MANDATORY-GROUPS { heRFAmpOutputMandatoryGroup

                         }
    ::= { heRFAmpMIBCompliances 1 }


heRFAmpOutputMandatoryGroup OBJECT-GROUP
    OBJECTS {
              heRFAmpOutputDescription
            }
    STATUS  current
    DESCRIPTION
            "The main group defines heRFAmpOutputTable objects which
			are mandatory to all indoor RF Amp modules."
    ::= { heRFAmpMIBGroups 1 }


heRFAmpUnitGroup OBJECT-GROUP
    OBJECTS {
				heRFAmpGainControlMode,
				heRFAmpAttenuatorControl,
				heRFAmpSlopeControl
            }
    STATUS  current
    DESCRIPTION
	    "The collection of heRFAmpUnitTable objects which are used to
		represent the indoor RF Amp module."
    ::= { heRFAmpMIBGroups 2 }

heRFAmpOutputGroup OBJECT-GROUP
    OBJECTS {
				heRFAmpOutputLevel,
				heRFAmpOutputAttenuatorControl

            }
    STATUS  current
    DESCRIPTION
	    "The collection of heRFAmpOutputTable objects which are used to
		represent the indoor RF Amp module."
    ::= { heRFAmpMIBGroups 3 }



END
