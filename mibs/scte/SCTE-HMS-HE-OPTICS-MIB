-- Module Name: HMS108R10.MIB (SCTE 83-1)
-- SCTE Status: Adopted

SCTE-HMS-HE-OPTICS-MIB DEFINITIONS ::= BEGIN

IMPORTS
    OBJECT-IDENTITY, MODULE-IDENTITY
        FROM SNMPv2-SMI
    heOptics
        FROM SCTE-HMS-HEADENDIDENT-MIB;

heOpticsMib MODULE-IDENTITY
    LAST-UPDATED "200302170000Z" -- February 17, 2003
    ORGANIZATION "SCTE HMS Working Group"
    CONTACT-INFO
            "   SCTE HMS Subcommittee, Chairman
                mailto:standards@scte.org
            "
    DESCRIPTION
            "The MIB module provides the branch object identifiers for the
            headend optics MIBs within the SCTE HMS Headend subtree."

    ::= { heOptics 0 }

-- Registration subtree for headend optical equipment

heOpticalTransmitterGroup    OBJECT-IDENTITY
    STATUS  current
    DESCRIPTION
            "Defines the base OID for the inside plant
            optical transmitters (see SCTE 85-1; formerly HMS112)."
    ::= { heOptics 1 }

heOpticalReceiverGroup    OBJECT-IDENTITY
    STATUS  current
    DESCRIPTION
            "Defines the base OID for the inside plant
            optical receivers (see SCTE 85-2; formerly HMS113)."
    ::= { heOptics 2 }

heOpticalAmplifierGroup   OBJECT-IDENTITY
    STATUS  current
    DESCRIPTION
            "Defines the base OID for the inside plant
            optical amplifiers (see SCTE 85-3; formerly HMS118)."
    ::= { heOptics 3 }

heOpticalSwitchGroup      OBJECT-IDENTITY
    STATUS  current
    DESCRIPTION
            "Defines the base OID for the inside plant
            optical switches (see SCTE 85-4; formerly HMS119)."
    ::= { heOptics 4 }

END
