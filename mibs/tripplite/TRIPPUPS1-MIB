-- Tripplite MIB

-- { iso org(3) dod(6) internet(1) private(4) enterprises(1) tripplite(850) trippUPS1(1) ups(1) }

TRIPPUPS1-MIB DEFINITIONS ::= BEGIN

-- Title                :  UPS MIB for Tripp Lite Uninterruptible Power Supplies
-- Date         :  Dec 9, 1993
-- By           :  Sean T McCartney
-- Note         :  Subagent #1, specific watchdog for Netmon port #1
-- Update       :  Apr 24, 1995
-- By           :  Dave Cole - Systems Enhancement Corporation

IMPORTS
	enterprises, OBJECT-TYPE, NetworkAddress, IpAddress, Counter, Gauge, TimeTicks
		FROM RFC1155-SMI
	DisplayString
		FROM RFC1213-MIB
	TRAP-TYPE
		FROM RFC-1215;

tripplite               OBJECT IDENTIFIER ::= { enterprises 850 }
trippUPS1               OBJECT IDENTIFIER ::= { tripplite 1 }
ups                     OBJECT IDENTIFIER ::= { trippUPS1 1 }

upsIdent                OBJECT IDENTIFIER ::= { ups 1 }
upsBattery              OBJECT IDENTIFIER ::= { ups 2 }
upsInput                OBJECT IDENTIFIER ::= { ups 3 }
upsOutput               OBJECT IDENTIFIER ::= { ups 4 }
upsAlarm                OBJECT IDENTIFIER ::= { ups 6 }
upsWellKnownAlarms      OBJECT IDENTIFIER ::= { ups 7 }
upsTest                 OBJECT IDENTIFIER ::= { ups 8 }
upsControl              OBJECT IDENTIFIER ::= { ups 9 }
upsConfig               OBJECT IDENTIFIER ::= { ups 10 }

-- The Device Identification group.
-- All objects in this group are set at device initialization and remain static.

  upsIdentManufacturer OBJECT-TYPE
      SYNTAX DisplayString (SIZE (0..31))
      ACCESS read-only
      STATUS mandatory
      DESCRIPTION
	      "The name of the UPS manufacturer."
      ::= { upsIdent 1 }

  upsIdentModel OBJECT-TYPE
      SYNTAX DisplayString (SIZE (0..63))
      ACCESS read-only
      STATUS mandatory
      DESCRIPTION
	      "The UPS Model designation."
      ::= { upsIdent 2 }

  upsIdentUPSSoftwareVersion OBJECT-TYPE
      SYNTAX DisplayString (SIZE (0..63))
      ACCESS read-only
      STATUS mandatory
      DESCRIPTION
	      "The UPS Firmware software version(s).  This variable
	      may or may not have the same value as
	      upsIdentAgentSoftwareVersion in some implementations."
      ::= { upsIdent 3 }

  upsIdentAgentSoftwareVersion OBJECT-TYPE
      SYNTAX DisplayString (SIZE(0..63))
      ACCESS read-only
      STATUS mandatory
      DESCRIPTION
	      "The UPS agent software version.  This variable may or
	      may not have the same value as
	      upsIdentUPSSoftwareVersion in some implementations."
      ::= { upsIdent 4 }

  upsIdentName OBJECT-TYPE
      SYNTAX DisplayString (SIZE(0..63))
      ACCESS read-write
      STATUS mandatory
      DESCRIPTION
	      "A string identifying the UPS.  This object should be
	      set by the administrator."
      ::= { upsIdent 5 }

  upsIdentAttachedDevices OBJECT-TYPE
      SYNTAX DisplayString (SIZE(0..63))
      ACCESS read-write
      STATUS mandatory
      DESCRIPTION
	      "A string identifying the devices attached to the
	      output(s) of the UPS.  This object should be set by
	      the administrator."
      ::= { upsIdent 6 }


-- The Battery group.
-- Implementation of this group is mandatory for all systems.

  upsBatteryStatus OBJECT-TYPE
      SYNTAX INTEGER {
		     unknown(1),
		     batteryNormal(2),
		     batteryLow(3),
		     batteryDepleted(4)
		     }
      ACCESS read-only
      STATUS mandatory
      DESCRIPTION
	      "The indication of the capacity remaining in the UPS
	      system's batteries.  A value of batteryNormal
	      indicates that the batteries are fully charged.  A
	      value of batteryLow indicates that the remaining battery
	      run-time is less than or equal to
	      upsConfigMinutesRemaining.  A value of batteryDepleted
	      indicates that the UPS will be unable to sustain the
	      present load when and if the utility power is lost."
      ::= { upsBattery 1 }

  upsSecondsOnBattery OBJECT-TYPE
      SYNTAX INTEGER
      ACCESS read-only
      STATUS mandatory
      DESCRIPTION
	      "If the unit is on battery power, the elapsed time
	      since the UPS last switched to battery power, or the
	      time since the network management subsystem was last
	      restarted, whichever is less.  Zero shall be returned
	      if the unit is not on battery power. UNITS - seconds"
      ::= { upsBattery 2 }

  upsEstimatedMinutesRemaining OBJECT-TYPE
      SYNTAX INTEGER
      ACCESS read-only
      STATUS mandatory
      DESCRIPTION
	      "An estimate of the time to battery charge depletion
	      under the present load conditions if the utility power
	      were to be lost and remain off. UNITS - minutes"
      ::= { upsBattery 3 }

  upsBatteryChargeRemaining OBJECT-TYPE
      SYNTAX INTEGER (0..100)
      ACCESS read-only
      STATUS mandatory
      DESCRIPTION
	      "The estimate of the battery charge remaining expressed
	      as a percent of full charge."
      ::= { upsBattery 4 }

  upsBatteryVoltage OBJECT-TYPE
      SYNTAX INTEGER
      ACCESS read-only
      STATUS mandatory
      DESCRIPTION
	      "The magnitude of the present battery voltage.   UNITS  0.1 Volt DC."
      ::= { upsBattery 5 }

-------------------------------------------------------------------------------
--  Note : upsBatteryCurrent MIB variable removed by Dave Cole (SEC) on 4/24/95
--  To conform with older versions of this MIB,  {upsBattery 6 }  is reserved.
-------------------------------------------------------------------------------

upsBatteryTemperature OBJECT-TYPE
      SYNTAX INTEGER
      ACCESS read-only
      STATUS mandatory
      DESCRIPTION
	      "The ambient temperature at or near the UPS Battery.
	      UNITS degrees Centigrade"
      ::= { upsBattery 7 }

  -- the table group has one attribute of its own - the number of rows in the
  -- contained table.  It also contains the table of names.

-- The Input group.
-- Implementation of this group is mandatory for all systems.

  upsInputFrequency OBJECT-TYPE
      SYNTAX INTEGER
      ACCESS read-only
      STATUS mandatory
      DESCRIPTION
	      "The present input frequency.  UNITS  0.1 Hertz"
      ::= { upsInput 1 }

  upsInputLineBads OBJECT-TYPE
      SYNTAX Counter
      ACCESS read-only
      STATUS mandatory
      DESCRIPTION
	      "A count of the number of times the input entered an
	      out-of-tolerance condition as defined by the manufacturer."
      ::= { upsInput 2 }

  upsInputNumLines OBJECT-TYPE
      SYNTAX INTEGER
      ACCESS read-only
      STATUS mandatory
      DESCRIPTION
	      "The number of input lines utilized in this device.
	      This variable indicates the number of rows in the input table."
      ::= { upsInput 3 }

  upsInputVolt OBJECT-TYPE
      SYNTAX INTEGER
      ACCESS read-only
      STATUS mandatory
      DESCRIPTION
	      "The magnitude of the present input voltage.
	      UNITS     RMS Volts"
      ::= { upsInput 4 }

  upsInputTable OBJECT-TYPE
      SYNTAX SEQUENCE OF UpsInputEntry
      ACCESS not-accessible
      STATUS mandatory
      DESCRIPTION
	      "A list of input table entries.  The number of entries
	      is given by the value of upsInputNumLines."
      ::= { upsInput 5 }

  upsInputEntry OBJECT-TYPE
      SYNTAX UpsInputEntry
      ACCESS not-accessible
      STATUS mandatory
      DESCRIPTION
      "An entry containing information applicable to a
      particular input line."
      INDEX { upsInputLineIndex }
      ::= { upsInputTable 1 }

  UpsInputEntry ::=
      SEQUENCE {
	       upsInputLineIndex INTEGER,
	       upsInputVoltage INTEGER
	       }

  upsInputLineIndex OBJECT-TYPE
      SYNTAX INTEGER
      ACCESS read-only
      STATUS mandatory
      DESCRIPTION
	      "The input line identifier."
      ::= { upsInputEntry 1 }

  upsInputVoltage OBJECT-TYPE
      SYNTAX INTEGER
      ACCESS read-only
      STATUS mandatory
      DESCRIPTION
	      "The magnitude of the present input voltage.
	      UNITS     RMS Volts"
      ::= { upsInputEntry 2 }

-- The Output group.
-- Implementation of this group is mandatory for all systems.

  upsOutputSource OBJECT-TYPE
      SYNTAX INTEGER {
		     other(1),
		     none(2),
		     normal(3),
		     bypass(4),
		     battery(5),
		     booster(6),
		     reducer(7)
		     }
      ACCESS read-only
      STATUS mandatory
      DESCRIPTION
	      "The present source of output power."
      ::= { upsOutput 1 }

  upsOutputFrequency OBJECT-TYPE
      SYNTAX INTEGER
      ACCESS read-only
      STATUS mandatory
      DESCRIPTION
	      "The present output frequency.
	      UNITS     0.1 Hertz"
      ::= { upsOutput 2 }

  upsOutputNumLines OBJECT-TYPE
      SYNTAX INTEGER
      ACCESS read-only
      STATUS mandatory
      DESCRIPTION
	      "The number of output lines utilized in this device.
	      This variable indicates the number of rows in the output table."
      ::= { upsOutput 3 }

  upsOutputPercLoad OBJECT-TYPE
      SYNTAX INTEGER
      ACCESS read-only
      STATUS mandatory
      DESCRIPTION
	      "The percentage of true power capacity presently being used.
	      UNITS     percent"
      ::= { upsOutput 4 }

  upsOutputTable OBJECT-TYPE
      SYNTAX SEQUENCE OF UpsOutputEntry
      ACCESS not-accessible
      STATUS mandatory
      DESCRIPTION
	      "A list of output table entries.  The number of
	      entries is given by the value of upsOutputNumLines."
      ::= { upsOutput 5 }

  upsOutputEntry OBJECT-TYPE
      SYNTAX UpsOutputEntry
      ACCESS not-accessible
      STATUS mandatory
      DESCRIPTION
	      "An entry containing information applicable to a
	      particular output line."
      INDEX { upsOutputLineIndex }
      ::= { upsOutputTable 1 }

  UpsOutputEntry ::= SEQUENCE {
			      upsOutputLineIndex        INTEGER,
			      upsOutputVoltage          INTEGER,
			      upsOutputCurrent          INTEGER,
			      upsOutputPower            INTEGER,
			      upsOutputPercentLoad      INTEGER
			      }

  upsOutputLineIndex OBJECT-TYPE
      SYNTAX INTEGER
      ACCESS read-only
      STATUS mandatory
      DESCRIPTION
	      "The output line identifier."
      ::= { upsOutputEntry 1 }

  upsOutputVoltage OBJECT-TYPE
      SYNTAX INTEGER
      ACCESS read-only
      STATUS mandatory
      DESCRIPTION
	      "The present output voltage.
	      UNITS     RMS Volts"
      ::= { upsOutputEntry 2 }

  upsOutputCurrent OBJECT-TYPE
      SYNTAX INTEGER
      ACCESS read-only
      STATUS mandatory
      DESCRIPTION
	      "The present output mandatory.
	      UNITS     0.1 Amp"
      ::= { upsOutputEntry 3 }

  upsOutputPower OBJECT-TYPE
      SYNTAX INTEGER
      ACCESS read-only
      STATUS mandatory
      DESCRIPTION
	      "The present output true power.
	      UNITS     Watts"
      ::= { upsOutputEntry 4 }

  upsOutputPercentLoad OBJECT-TYPE
      SYNTAX INTEGER
      ACCESS read-only
      STATUS mandatory
      DESCRIPTION
	      "The percentage of true power capacity presently being used.
	      UNITS     percent"
      ::= { upsOutputEntry 5 }

--    Alarm Group

  upsAlarmsPresent OBJECT-TYPE
      SYNTAX Gauge
      ACCESS read-only
      STATUS mandatory
      DESCRIPTION
	      "The present number of active alarm conditions."
      ::= { upsAlarm 1 }

  upsAlarmID OBJECT-TYPE
      SYNTAX INTEGER {
		     upsAlarmBatteryBad(1),
		     upsAlarmOnBattery(2),
		     upsAlarmLowBattery(3),
		     upsAlarmDepletedBattery(4),
		     upsAlarmTempBad(5),
		     upsAlarmOutputOverload(6),
		     upsAlarmOutputOffAsRequested(7),
		     upsAlarmOutputOff(8),
		     upsAlarmDiagnosticTestFailed(9),
		     upsAlarmCommunicationsLost(10),
		     upsAlarmShutdownPending(11),
		     upsAlarmShutdownImminent(12),
		     upsAlarmTestInProgress(13)
		     }
      ACCESS read-only
      STATUS mandatory
      DESCRIPTION
	      "A unique identifier for an alarm condition.  This
	      value must remain constant."
      ::= { upsAlarm 2 }

  upsAlarmDESCR OBJECT-TYPE
      SYNTAX DisplayString (SIZE(0..31))
      ACCESS read-only
      STATUS mandatory
      DESCRIPTION
	      "A reference to an alarm description object.  The
	      object references should not be accessible, but rather
	      be used to provide a unique description of the alarm
	      condition."
      ::= { upsAlarm 3 }

  upsAlarmTable OBJECT-TYPE
      SYNTAX SEQUENCE OF UpsAlarmEntry
      ACCESS not-accessible
      STATUS mandatory
      DESCRIPTION
	      "A list of alarm table entries.  The table consists of
	      zero, one, or may rows at any moment, depending upon
	      the number of alarm conditions in effect.  The table
	      is initially empty at agent startup.  The agent
	      creates a row in the table each time a condition is
	      detected and deletes that row when that condition no
	      longer pertains.  The agent creates the first row with
	      upsAlarmId equal to 1, and increments the value fo
	      upsAlarmId each time a new row is created, wrapping to
	      the first free value greater than or equal to 1 when
	      the maximum value of upsAlarmId would otherwise be
	      exceeded.  Consequently, after multiple operations,
	      the table may become sparse, e.g., containing entries
	      for rows 95, 100, 101, and 203 and the entries are in
	      chronological order until upsAlarmId wraps.

	      Alarms are named by and OBJECT IDENTIFIER,
	      upsAlarmDescr, to allow a single table to reflect well
	      known alarms plus alarms defined by a particular
	      implementation, i.e., as documented in the private
	      enterprise MIB definition for the device.  No two rows
	      will have the same value of upsAlarmDescr, since
	      alarms define conditions.  In order to meet this
	      requirement, care should be take in the definition of
	      the number of active rows in the table at any given
	      time is reflected by the value fo upsAlarms."
	   ::= { upsAlarm 4 }

  upsAlarmEntry OBJECT-TYPE
      SYNTAX UpsAlarmEntry
      ACCESS not-accessible
      STATUS mandatory
      DESCRIPTION
	      "An entry containing information applicable to a
	      particular alarm."
      INDEX { upsAlarmId }
      ::= { upsAlarmTable 1 }

  UpsAlarmEntry ::= SEQUENCE {
	upsAlarmId    INTEGER,
	upsAlarmDescr DisplayString,
	upsAlarmTime  TimeTicks
      }

  upsAlarmId OBJECT-TYPE
      SYNTAX INTEGER
      ACCESS read-only
      STATUS mandatory
      DESCRIPTION
	      "A unique identifier for an alarm condition.  This
	      value must remain constant."
      ::= { upsAlarmEntry 1 }

  upsAlarmDescr OBJECT-TYPE
      SYNTAX DisplayString (SIZE(0..31))
      ACCESS read-only
      STATUS mandatory
      DESCRIPTION
	      "A reference to an alarm description object.  The
	      object references should not be accessible, but rather
	      be used to provide a unique description of the alarm
	      condition."
      ::= { upsAlarmEntry 2 }

  upsAlarmTime OBJECT-TYPE
      SYNTAX TimeTicks
      ACCESS read-only
      STATUS mandatory
      DESCRIPTION
	      "The value of sysUpTime when the alarm condition was
	      detected.  If the alarm condition was detected at the
	      time of agent startup and presumable existed before
	      agent startup, the value of upsAlarmTime shall equal
	      0."
      ::= { upsAlarmEntry 3 }

  upsAlarmBatteryBad OBJECT-TYPE
      SYNTAX INTEGER
      ACCESS read-only
      STATUS mandatory
      DESCRIPTION
	      "One or more batteries have been determined to require
	      replacement."
      ::= { upsWellKnownAlarms 1 }

  upsAlarmOnBattery OBJECT-TYPE
      SYNTAX INTEGER
      ACCESS read-only
      STATUS mandatory
      DESCRIPTION
	      "The UPS is drawing power from the batteries."
      ::= { upsWellKnownAlarms 2 }

  upsAlarmLowBattery OBJECT-TYPE
      SYNTAX INTEGER
      ACCESS read-only
      STATUS mandatory
      DESCRIPTION
	      "The remaining battery run-time is less than or equal
	      to upsConfigMinutesRemaining."
      ::= { upsWellKnownAlarms 3 }

  upsAlarmDepletedBattery OBJECT-TYPE
      SYNTAX INTEGER
      ACCESS read-only
      STATUS mandatory
      DESCRIPTION
	      "The UPS will be unable to sustain the present load
	      when and if the utility power is lost."
      ::= { upsWellKnownAlarms 4 }

  upsAlarmTempBad OBJECT-TYPE
      SYNTAX INTEGER
      ACCESS read-only
      STATUS mandatory
      DESCRIPTION
	      "A temperature is out of tolerance."
      ::= { upsWellKnownAlarms 5 }

  upsAlarmOutputOverload OBJECT-TYPE
      SYNTAX INTEGER
      ACCESS read-only
      STATUS mandatory
      DESCRIPTION
	      "The output load exceeds the UPS output capacity."
      ::= { upsWellKnownAlarms 6 }

  upsAlarmOutputOffAsRequested OBJECT-TYPE
      SYNTAX INTEGER
      ACCESS read-only
      STATUS mandatory
      DESCRIPTION
	      "The UPS has shutdown as commanded, i.e., the output is off."
      ::= { upsWellKnownAlarms 7 }

  upsAlarmUpsOutputOff OBJECT-TYPE
      SYNTAX INTEGER
      ACCESS read-only
      STATUS mandatory
      DESCRIPTION
	      "The UPS is in the off state."
      ::= { upsWellKnownAlarms 8 }

  upsAlarmDiagnosticTestFailed OBJECT-TYPE
      SYNTAX INTEGER
      ACCESS read-only
      STATUS mandatory
      DESCRIPTION
	      "The result of the last diagnostic test indicates a
	      failure."
      ::= { upsWellKnownAlarms 9 }

  upsAlarmCommunicationsLost OBJECT-TYPE
      SYNTAX INTEGER
      ACCESS read-only
      STATUS mandatory
      DESCRIPTION
	      "A problem has been encountered in the
	      communications between the agent and the UPS."
      ::= { upsWellKnownAlarms 10 }

  upsAlarmShutdownPending OBJECT-TYPE
      SYNTAX INTEGER
      ACCESS read-only
      STATUS mandatory
      DESCRIPTION
	      "A upsShutdownAfterDelay countdown is underway."
      ::= { upsWellKnownAlarms 11 }

  upsAlarmShutdownImminent OBJECT-TYPE
      SYNTAX INTEGER
      ACCESS read-only
      STATUS mandatory
      DESCRIPTION
	      "A upsShutdownAfterDelay countdown is underway."
      ::= { upsWellKnownAlarms 12 }

  upsAlarmTestInProgress OBJECT-TYPE
      SYNTAX INTEGER
      ACCESS read-only
      STATUS mandatory
      DESCRIPTION
	      "A upsShutdownAfterDelay countdown is underway."
      ::= { upsWellKnownAlarms 13 }

--    Test Group

  upsTestId OBJECT-TYPE
      SYNTAX INTEGER {
		     noTestsInitiated(1),
		     abortTestInProgress(2),
		     generalSystemsTest(3),
		     checkBatteryTest(4),
		     deepBatteryCalibration(5)
		     }
      ACCESS read-write
      STATUS mandatory
      DESCRIPTION
	      "The test named by an OBJECT IDENTIFIER which
	      allows a standard mechanism for the initiation of
	      test, including the well known tests identified in
	      this document as well as those introduced by a
	      particular implementation, i.e., as
	      documented in the private enterprise MIB definition
	      for the device.

	      Setting this variable initiates the named test.  Sets
	      to this variable require the presence of
	      upsTestSpinLock in the same SNMP message.

	      The set request will be rejected with an appropriate
	      error message if the requested test cannot be
	      performed, including attempts to start a test when
	      another test is already in progress.  Tests in
	      progress may be aborted by setting this variable to
	      upsTestAbortTestInProgress.

	      Read operations return the value of the name of the
	      test in progress if a test is in progress or the name
	      of the last test performed if no test is in progress,
	      unless no test has bee run, in which case the well
	      known value upsTestNoTestsInitiated is returned."
	      ::= { upsTest 1 }


  upsTestResultsSummary         OBJECT-TYPE
      SYNTAX INTEGER {
		     donePass(1),
		     doneWarning(2),
		     doneError(3),
		     aborted(4),
		     inProgress(5),
		     noTestsInitiated(6)
		     }
      ACCESS read-only
      STATUS mandatory
      DESCRIPTION
	      "The results of the mandatory or last UPS diagnostics
	      test performed.  The values for donePass(1),
	      doneWarning(2), and doneError(3) are self-documenting.
	      The value aborted(4) is returned for tests which are
	      aborted by setting the value of upsTestId to
	      upsTestAbortTestInProgress.  Tests which have not yet
	      concluded are indicated by inProgress(5).  The value
	      noTestsInitiated(4) indicates that no previous test
	      results are available, such as in the case when no
	      tests have been run since the last reinitialization of
	      the network management subsystem and the system has no
	      provision for non-volatile storage of test results."
      ::= { upsTest 2 }

--------------------------------------------------------------------------------------------------------------------------
--  Note : upsTestResultsDetail MIB variable removed by Dave Cole (SEC) on 4/24/95
--  To conform with older versions of this MIB, {upsTest 3 } is reserved.
--------------------------------------------------------------------------------------------------------------------------

--------------------------------------------------------------------------------------------------------------------------
--  Note : upsTestStartTime MIB variable removed by Dave Cole (SEC) on 4/24/95
--  To conform with older versions of this MIB, {upsTest 4 } is reserved.
--------------------------------------------------------------------------------------------------------------------------

--    Control Group

  upsShutdownType OBJECT-TYPE
      SYNTAX INTEGER {
		     output(1),
		     system(2)
		     }
      ACCESS read-write
      STATUS mandatory
      DESCRIPTION
	      "Setting this object will start the output after the
	      indicated number of seconds.  Setting this object to 0
	      will cause the UPS to start the output immediately.
	      If the output is already on at the time the delay has
	      counted down, nothing will happen."
      ::= { upsControl 1 }

  upsShutdownAfterDelay OBJECT-TYPE
      SYNTAX INTEGER (-1..32767)
      ACCESS read-write
      STATUS mandatory
      DESCRIPTION
	      "Setting this object will shutdown (i.e., turn off)
	      either the UPS output or the UPS system (as determined
	      by the value of upsShhutdownType at the time of
	      shutdown) after the indicated number of seconds, or
	      less if the UPS batteries become depleted.  Setting
	      this object to 0 will cause the shutdown to occur
	      immediately.  Setting this object to -1 will abort the
	      countdown.  If the system is already in the desired
	      state at the time the countdown reaches 0, then
	      nothing will happen.  That is, there is no additional
	      action at that time if upsShutdownType = system and
	      the system is already off.  Similarly, there is no
	      additional action at that time if upsShutdownType =
	      output and the output is already off.  When read,
	      upsShutdownAfterDelay will return the number of
	      seconds remaining until shutdown, or -1 if no shutdown
	      countdown is in effect.  On some systems, if the agent
	      is restarted while a shutdown countdown is in effect,
	      the countdown may be aborted.  Sets to this object
	      override any upsShutdownAfterDelay already in effect.
	      UNITS seconds"
      ::= { upsControl 2 }

  upsStartupAfterDelay OBJECT-TYPE
      SYNTAX INTEGER (-1..32767)
      ACCESS read-write
      STATUS mandatory
      DESCRIPTION
	      "Setting this object will start the output after the
	      indicated number of seconds, includeing starting the
	      UPS, if necessary.  Setting this object to 0 will
	      cause the start to occur immediately.  Setting this
	      object to -1 will abort the countdown.  If the output
	      is already on at the time the countdown reaches 0,
	      nothing will happen.  Sets to this object
	      override the effect of any upsStartupAfterDelay
	      countdown or upsRebootDuration countdown in progress.
	      When read, upsStartupAfterDelay will return the number
	      of seconds until start, or -1 if no startup
	      countdown is in effect.  If the countdown expires
	      during a utility failure, the startup shall depend
	      upon the value of upsAutoRestart at that time.  On
	      some systems, if the agent is restarted while a
	      startup countdown is in effect, the countdown is
	      aborted.
	      UNITS seconds"
      ::= { upsControl 3 }

  upsRebootDuration OBJECT-TYPE
      SYNTAX INTEGER (-1..100)
      ACCESS read-write
      STATUS mandatory
      DESCRIPTION
	      "Setting this object will immediately shutdown (i.e.,
	      turn off) either the UPS output or the UPS system (as
	      determined by the value of the upsShutdownType at the time
	      of shutdown)  for a period equal to the indicated
	      number of seconds, after which time the output will be
	      started, including starting the UPS, if necessary.  If
	      the number of seconds required to perform the request
	      is greater than the requested duration, then the
	      requested shutdown and startup cycle shall be
	      performed in the minimum time possible, but in no case
	      shall this require more than the requested duration
	      plus 60 seconds.  When read, upsRebootDuration shall
	      return the number of seconds remaining in the
	      countdown, or -1 if no countdown is in progress.  If
	      the startup should occur during a utility failure, the
	      startup shall depend on the value of upsAutoRestart
	      at that time.
	      UNITS seconds"
      ::= { upsControl 4 }

  upsAutoRestart OBJECT-TYPE
      SYNTAX INTEGER {
		     on(1),
		     off(2)
		     }
      ACCESS read-write
      STATUS mandatory
      DESCRIPTION
	      "Setting this object to 'on' will cause the UPS system
	      to restart after a shutdown if/when utility power is present."
      ::= { upsControl 5 }

-- upsConfig group

--------------------------------------------------------------------------------------------------------------------------------
--  Note : upsConfigInputVoltage MIB variable removed by Dave Cole (SEC) on 4/24/95
--  To conform with older versions of this MIB, {upsConfig 1 } is reserved.
--------------------------------------------------------------------------------------------------------------------------------

--------------------------------------------------------------------------------------------------------------------------------
--  Note : upsInputFreq MIB variable removed by Dave Cole (SEC) on 4/24/95
--  To conform with older versions of this MIB, {upsConfig 2 } is reserved.
--------------------------------------------------------------------------------------------------------------------------------

--------------------------------------------------------------------------------------------------------------------------------
--  Note : upsConfigOutputVoltage MIB variable removed by Dave Cole (SEC) on 4/24/95
--  To conform with older versions of this MIB, {upsConfig 3 } is reserved.
--------------------------------------------------------------------------------------------------------------------------------

--------------------------------------------------------------------------------------------------------------------------------
--  Note : upsConfigOutputFreq MIB variable removed by Dave Cole (SEC) on 4/24/95
--  To conform with older versions of this MIB, {upsConfig 4 } is reserved.
--------------------------------------------------------------------------------------------------------------------------------

--------------------------------------------------------------------------------------------------------------------------------
--  Note : upsConfigOutputVA MIB variable removed by Dave Cole (SEC) on 4/24/95
--  To conform with older versions of this MIB, {upsConfig 5 } is reserved.
--------------------------------------------------------------------------------------------------------------------------------

--------------------------------------------------------------------------------------------------------------------------------
--  Note : upsConfigOutputPower MIB variable removed by Dave Cole (SEC) on 4/24/95
--  To conform with older versions of this MIB, {upsConfig 6 } is reserved.
--------------------------------------------------------------------------------------------------------------------------------

--------------------------------------------------------------------------------------------------------------------------------
--  Note : upsConfigLowBattTime MIB variable removed by Dave Cole (SEC) on 4/24/95
--  To conform with older versions of this MIB, {upsConfig 7 } is reserved.
--------------------------------------------------------------------------------------------------------------------------------

--------------------------------------------------------------------------------------------------------------------------------
--  Note : upsConfigAudibleStatus MIB variable removed by Dave Cole (SEC) on 4/24/95
--  To conform with older versions of this MIB, {upsConfig 8 } is reserved.
--------------------------------------------------------------------------------------------------------------------------------

--------------------------------------------------------------------------------------------------------------------------------
--  Note : upsConfigLowVoltageTransferPoint MIB variable removed by Dave Cole (SEC) on
--  4/24/95.  To conform with older versions of this MIB, {upsConfig 9 } is reserved.
--------------------------------------------------------------------------------------------------------------------------------

--------------------------------------------------------------------------------------------------------------------------------
--  Note : upsConfigHighVoltageTransferPoint MIB variable removed by Dave Cole (SEC) on
--  4/24/95.  To conform with older versions of this MIB, {upsConfig 10 } is reserved.
--------------------------------------------------------------------------------------------------------------------------------

upsConfigInputVoltageHigh OBJECT-TYPE
	SYNTAX INTEGER
	ACCESS read-write
	STATUS mandatory
	DESCRIPTION
		"If the value of the input voltage (in Volts) exceeds this value, a
		 utilityVoltageHigh trap will be triggered."
	::= { upsConfig 11 }

upsConfigInputVoltageLow OBJECT-TYPE
	SYNTAX INTEGER
	ACCESS read-write
	STATUS mandatory
	DESCRIPTION
		"If the value of the input voltage (in Volts) falls below this value, a
		 utilityVoltageLow trap will be triggered."
	::= { upsConfig 12 }

upsConfigOutputPercLoadHigh OBJECT-TYPE
	SYNTAX INTEGER
	ACCESS read-write
	STATUS mandatory
	DESCRIPTION
		"If the value of the output percent load exceeds this value, a upsOverload trap
		 will be triggered."
	::= { upsConfig 13 }

upsConfigBatteryPercLow OBJECT-TYPE
	SYNTAX INTEGER
	ACCESS read-write
	STATUS mandatory
	DESCRIPTION
		"If the value of the battery percent capacity falls below this value, a lowBattery
		 trap will be triggered."
	::= { upsConfig 14 }

upsConfigBatteryTemperatureHigh OBJECT-TYPE
	SYNTAX INTEGER
	ACCESS read-write
	STATUS mandatory
	DESCRIPTION
		"If the value of the battery temperature exceeds this value, a
		 batteryTemperatureHigh trap will be triggered."
	::= { upsConfig 15 }

-- Traps

---------------------------------------------------------------------------------------------------------------------------
--  Note : upsOnBattery trap modified by Dave Cole (SEC) on 4/24/95
--  To conform with older versions of this MIB, trap 1 is reserved.
---------------------------------------------------------------------------------------------------------------------------

---------------------------------------------------------------------------------------------------------------------------
--  Note : upsTestCompleted trap removed by Dave Cole (SEC) on 4/24/95
--  To conform with older versions of this MIB, trap 2 is reserved.
---------------------------------------------------------------------------------------------------------------------------

---------------------------------------------------------------------------------------------------------------------------
--  Note : upsAlarmEntryAdded trap removed by Dave Cole (SEC) on 4/24/95
--  To conform with older versions of this MIB, trap 3 is reserved.
---------------------------------------------------------------------------------------------------------------------------

---------------------------------------------------------------------------------------------------------------------------
--  Note : upsAlarmEntryDeleted trap removed by Dave Cole (SEC) on 4/24/95
--  To conform with older versions of this MIB, trap 4 is reserved.
---------------------------------------------------------------------------------------------------------------------------

upsOnBattery TRAP-TYPE
      ENTERPRISE tripplite
      VARIABLES  { upsIdentAttachedDevices, upsEstimatedMinutesRemaining }
      DESCRIPTION
	      "The UPS is on battery."
      ::= 5

  powerRestored TRAP-TYPE
      ENTERPRISE tripplite
      DESCRIPTION
	      "Utility power has been restored."
      ::= 6

lowBattery TRAP-TYPE
      ENTERPRISE tripplite
      DESCRIPTION
	      "The UPS batteries are low and will soon be exhausted."
      ::= 7

returnFromLowBattery TRAP-TYPE
      ENTERPRISE tripplite
      DESCRIPTION
	      "The UPS has returned from a low battery condition."
      ::= 8

communicationEstablished TRAP-TYPE
      ENTERPRISE tripplite
      DESCRIPTION
	      "Communication with the UPS has been established.  This trap will be sent
	   each time there is a transition from a power off condition to a power on condition."
      ::= 9

communicationLost TRAP-TYPE
      ENTERPRISE tripplite
      DESCRIPTION
	      "Communication with the UPS has been lost."
      ::= 10

upsOverload TRAP-TYPE
      ENTERPRISE tripplite
      DESCRIPTION
	      "The UPS has sensed a load greater than the value of the
	   upsConfigOutputPercLoadHigh MIB variable."
      ::= 11

upsDiagnosticsFailed TRAP-TYPE
      ENTERPRISE tripplite
      DESCRIPTION
	      "The UPS failed its self-test."
      ::= 12

upsDiagnosticsPassed TRAP-TYPE
      ENTERPRISE tripplite
      DESCRIPTION
	      "The UPS passed its internal self-test."
      ::= 13

utilityVoltageHigh TRAP-TYPE
      ENTERPRISE tripplite
      DESCRIPTION
	      "The UPS input voltage greater than or equal to the value of
	   the upsConfigInputVoltageHigh MIB variable."
      ::= 14

utilityVoltageLow TRAP-TYPE
      ENTERPRISE tripplite
      DESCRIPTION
	      "The UPS input voltage is less than or equal to the value of
	   the upsConfigInputVoltageLow MIB variable."
      ::= 15

utilityVoltageReturnToNormal TRAP-TYPE
      ENTERPRISE tripplite
      DESCRIPTION
	      "The UPS has returned from a utility voltage high or low condition."
      ::= 16

batteryTemperatureHigh TRAP-TYPE
      ENTERPRISE tripplite
      DESCRIPTION
	      "The UPS battery temperature has exceeded the value of the
	   upsConfigBatteryTemperatureHigh MIB variable."
      ::= 17

shutdownPending TRAP-TYPE
      ENTERPRISE tripplite
      DESCRIPTION
	      "A UPS shutdown countdown is underway."
      ::= 18

upsSleeping TRAP-TYPE
      ENTERPRISE tripplite
      DESCRIPTION
	      "The output of the UPS has been turned off."
      ::= 19

upsWokeup TRAP-TYPE
      ENTERPRISE tripplite
      DESCRIPTION
	      "The output of the UPS has been turned on."
      ::= 20

 upsBatteryNeedsReplacement TRAP-TYPE
      ENTERPRISE tripplite
      DESCRIPTION
	      "The UPS battery needs to be replaced."
      ::= 21
 END
