-- *****************************************************************
-- Copyright (c) 2017 SonicWall Inc.
-- All rights reserved.
-- *****************************************************************

SONICWALL-SMA-APPLIANCE-SERVICE-HEALTH-MIB	DEFINITIONS ::= BEGIN
	IMPORTS
		sonicwallSMAAppliance
			FROM SONICWALL-SMA-MIB
		RowStatus, DisplayString, TruthValue
			FROM SNMPv2-TC
		InternationalDisplayString
			FROM HOST-RESOURCES-MIB
                OBJECT-TYPE, MODULE-IDENTITY,  Integer32, enterprises, NOTIFICATION-TYPE
			FROM SNMPv2-SMI;

sonicwallServiceHealth MODULE-IDENTITY
			LAST-UPDATED       "201804090001Z"
			ORGANIZATION       "SonicWall"
			CONTACT-INFO
				"	SonicWall Inc.

					Tel: +1 408 745 9600
					Fax: +1 408 745 9300

				E-mail: support@sonicwall.com"
			DESCRIPTION        "This SonicWall MIB provides Service Health Info"
        	::= {sonicwallSMAAppliance 3}


serviceTable	OBJECT-TYPE
		SYNTAX		        SEQUENCE  OF  ServiceEntry
		MAX-ACCESS	 not-accessible
		STATUS		        current
		DESCRIPTION	 "The number of ASAP services in the service table."
		::=  { sonicwallServiceHealth  1 }

serviceEntry	OBJECT-TYPE
		SYNTAX		        ServiceEntry
		MAX-ACCESS	 not-accessible
		STATUS		        current
		DESCRIPTION	"This field represents the service table Entry."
		INDEX		{  serviceId  }
		::=  { serviceTable 1 }

ServiceEntry  ::=  SEQUENCE {
	    serviceId                           Integer32,
		serviceDescription           InternationalDisplayString,
		serviceState                   Integer32,
		serviceTableRowStatus    RowStatus
		}

serviceId	OBJECT-TYPE
		SYNTAX			 Integer32
		MAX-ACCESS	 read-only
		STATUS		        current
		DESCRIPTION	 "Index field for Service Table."
		::=  {  serviceEntry  1  }

serviceDescription	OBJECT-TYPE
		SYNTAX			InternationalDisplayString
		MAX-ACCESS		read-only
		STATUS			current
		DESCRIPTION		"Name of the ASAP service. Currently supported are \
							Appliance Management console (AMC), Web Access Service (Extraweb), \
							ASAP Workplace and Syslog-Ng. "
		::=  {  serviceEntry  2  }

serviceState	OBJECT-TYPE
		SYNTAX			Integer32
		MAX-ACCESS	read-only
		STATUS			current
		DESCRIPTION	"This oid conveys service state as \
		                             active(1), down(2) or crashed(6)."
		::=  {  serviceEntry  3  }

serviceTableRowStatus	OBJECT-TYPE
		SYNTAX			RowStatus
		MAX-ACCESS	read-create
		STATUS			current
		DESCRIPTION	"Currently supported row status are \
		                            Active(1), NotInService(2)"
		::=  {  serviceEntry  4  }

asapServiceUp	NOTIFICATION-TYPE
		OBJECTS			{ serviceDescription }
		STATUS			current
		DESCRIPTION	"An ASAP service on the single node system; identified \
		                             by the IP address the trap is sent from has gone up. \
		                             The serviceDescription oid is sent along with this trap."
		::=  {  sonicwallServiceHealth  2  }

asapServiceDown	NOTIFICATION-TYPE
		OBJECTS			{ serviceDescription }
		STATUS			current
		DESCRIPTION	"An ASAP service on the single node system; \
		                             identified by the IP address the trap is sent from has \
		                             gone down. The serviceDescription oid is sent along with this trap."
		::=  {  sonicwallServiceHealth  3  }

END
