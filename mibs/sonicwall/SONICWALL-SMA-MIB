-- *****************************************************************
-- Copyright (c) 2017 SonicWall Inc.
-- All rights reserved.
-- *****************************************************************

SONICWALL-SMA-MIB	DEFINITIONS ::= BEGIN
	IMPORTS
		sonicwallSMA
			FROM SONICWALL-SMI
		OBJECT-TYPE, Integer32, NOTIFICATION-TYPE, MODULE-IDENTITY
			FROM SNMPv2-SMI
		InternationalDisplayString
			FROM HOST-RESOURCES-MIB;

	sonicwallSMAAppliance OBJECT-IDENTITY
		STATUS	current
		DESCRIPTION
			"Sub-tree to register SMA Appliance MIBs."
		::= { sonicwallSMA 1 }

	sonicwallSMACMS OBJECT-IDENTITY
		STATUS	current
		DESCRIPTION
			"Sub-tree to register SMA CMS MIBs."
		::= { sonicwallSMA 2 }

END
