-- *****************************************************************
-- SONICWALL-FIREWALL-TRAP
--
-- February 2001, Initial Version, 					Susan Yan
-- June 2002,     Add new trap type, 				Susan Yan
-- Apr  2003,     Add new trap type, 				Susan Yan
-- May  2003,     Add new trap type, 				Susan Yan
-- Sep  2003,     Add new trap group and type,  	Susan Yan
-- Sep  2003,     Add new trap group,  				Susan Yan
-- Jan  2004,     Add new trap type,  				Susan Yan
-- Dec  2006,     Add Enh 4.0 Traps,                Mike Uy
-- Jan  2007,     Add Std and Enh Traps             Mike Uy
-- 04-29-2007,    Add Enh Traps                     Mike Uy
-- 08-08-2007,    Add Enh Traps                     Mike Uy
-- 03-10-2008,    Removed Imports that are not
--                used to prevent warnings
--                in MIB compilation                Mike Uy
-- 03-10-2008,    new VBs on selected traps			Mike Uy
-- 04-10-2008,    Update Legacy CFA Attack traps
--                Please make sure REVISION log is
--                updated in sonicwallFwTrapModule	Rosalea Real
-- 04-14-2008,    Add trapTypeEnhSystemShutdown     Rosalea Real
-- 06-10-2008,    added application firewall		Mike Uy
--                category and trap(s)
-- 04-02-2009,    added SSL-VPN, SonicPointN and	Mike Uy
--                Anti-Spam categories
-- 04-22-2009,    added Anti-Spam trap types		Mike Uy
-- 04-22-2009,    DNS Rebinding Attack traps		Rosalea Real
-- 04-22-2009,    Updated E-mail CONTACT-INFO		Rosalea Real
-- 04-22-2009,    added Network Monitor category	Rosalea Real
-- 11-11-2009,    Renamed this file from
--                SW-FIREWALL-TRAP.MIB to
--                SONICWALL-FIREWALL-TRAP-MIB.MIB   Mike Uy
-- 11-11-2009,    Updated SonicWall company address, Mike Uy
-- 09-16-2010,    Added trapTypeEnhACDetectionAlert,
--                trapTypeEnhACPreventionAlert      Rosalea Real
-- 04-20-2011,    WAN Acceleration traps.			Akbal Karlcut
--				  Include DHCP Server, FTP, and
--				  DPISSL.
--                Correct position of Application
--				  Control.
-- 11-2-2011,     HA Rename Backup to Secondary		Sharath Devulapalli
-- 07-23-2012,    Updated company copyright and     Mike Uy
--                organization
-- 02-25-2013,    Added traps for Configuration		Laura Ma
--				  Audit Log.
-- 01-08-2015,    Update Postal.
--                Add DPI-SSL Connection Check.     Thomas Tang
--
-- 06-19-2015,    Updated Postal.
--                Added trapTypeEnhSonicPointNStatus,
--                trapTypeEnhSonicPointNProvision,
--                trapTypeEnhSonicPointNHWFailure.  Thomas Tang
--
-- 01-06-17       Updated company copyright and
--                organization,                     Thomas Tang
--
-- 09-08-2021,    Added trapTypeEnhSysEnvPsuFailed,
--                trapTypeEnhSysEnvPsuNotPresent,
--                trapTypeEnhSysEnvPsuOn.           Lucia Wu
--
-- Version:  Enhanced v1.15
--
-- Copyright (c) 2017 SonicWall Inc.
-- All rights reserved.
-- *****************************************************************

SONICWALL-FIREWALL-TRAP-MIB DEFINITIONS ::= BEGIN

IMPORTS
    DisplayString,
    TEXTUAL-CONVENTION		 	FROM SNMPv2-TC

    IpAddress,
    Unsigned32,
	snmpModules,
    OBJECT-TYPE,
    NOTIFICATION-TYPE,
	MODULE-IDENTITY             FROM SNMPv2-SMI

    sonicwallFw           		FROM SONICWALL-SMI;

sonicwallFwTrapModule MODULE-IDENTITY
	LAST-UPDATED "202109080000Z"
	ORGANIZATION "SonicWall"
	CONTACT-INFO "SonicWall Inc.


				  Postal: 5455 Great America Parkway
                          Santa Clara, CA 95054
                          USA

				  Tel: +1 408 745 9600
				  Fax: +1 408 745 9300
				  E-mail: support@sonicwall.com"

	DESCRIPTION  "The MIB Module for SonicWall Firewall Trap."

	REVISION     "202109080000Z"  -- Sep 8, 2021
    DESCRIPTION	 "Added trapTypeEnhSysEnvPsuFailed,
                  trapTypeEnhSysEnvPsuNotPresent, trapTypeEnhSysEnvPsuOn."

	REVISION     "201701060000Z"
	DESCRIPTION  "Updated company copyright and organization."

	REVISION     "201506190000Z"  -- Jun 19, 2015
    DESCRIPTION	 "Updated Postal. Added trapTypeEnhSonicPointNStatus,
                  trapTypeEnhSonicPointNProvision, trapTypeEnhSonicPointNHWFailure."

    REVISION     "201501080000Z" -- Jan 8, 2015
    DESCRIPTION  "Update Postal, Tel, Fax.
                  Add DPI-SSL Connection Check."

	REVISION     "201302250000Z"  -- Feb 25, 2013
	DESCRIPTION  "Added trapTypeCfgChgSucceeded, trapTypeCfgChgFailed, trapTypeCfgChgAttempt."

	REVISION     "201104200000Z"  -- Apr 20, 2011
	DESCRIPTION  "Added trapTypeEnhWxaDeviceUp, trapTypeEnhWxaDeviceDown,
				  trapTypeEnhWxaDeviceUsed, trapTypeEnhWxaDeviceUnused,
			      trapTypeEnhRemoteWxaProbeStop, trapTypeEnhRemoteWxaProbeStart,
		          trapTypeEnhWxaLicenseExpired, swFwTrapEnhDhcpServer,
		          swFwTrapEnhFtp, swFwTrapEnhDPISSL, swFwTrapEnhWanAcceleration."

	REVISION     "201009160000Z"  -- Sep 16, 2010
	DESCRIPTION  "Added trapTypeEnhACDetectionAlert, trapTypeEnhACPreventionAlert"

	REVISION     "200904220000Z"  -- Apr 22, 2009
	DESCRIPTION  "Added trapTypeEnhNetMonPolicyUp, trapTypeEnhNetMonPolicyDown,
	              trapTypeEnhNetMonPolicyUnknown, trapTypeEnhNetMonHostUnknown,
	              trapTypeEnhNetMonHostDown, trapTypeEnhNetMonHostUp,
	              trapTypeEnhDNSRebindAttackDetected,
	              trapTypeEnhDNSRebindAttackBlocked"

	REVISION     "200904220000Z"  -- Apr 22, 2009
	DESCRIPTION  "Added Anti-Spam trap types"

	REVISION     "200904020000Z"  -- Apr 02, 2009
	DESCRIPTION  "Added swFwTrapEnhSslvpn,
	              swFwTrapEnhSonicPointN, swFwTrapEnhAntispam"

	REVISION     "200806100000Z"  -- Jun 10, 2008
	DESCRIPTION  "Added trapTypeEnhAppFwAlert,
	              swFwTrapEnhApplicationFirewall"

	REVISION     "200804140000Z"  -- Apr 14, 2008
	DESCRIPTION  "Add trapTypeEnhSystemShutdown."

	REVISION     "200804100000Z"  -- Apr 10, 2008
	DESCRIPTION  "Register new FwTrapType: 573, 574, 575, 576, 577, 578
                REVISION log clean-up."

	REVISION     "200401030000Z"
	DESCRIPTION  "Add new trap type."

    ::= { sonicwallFw 1 }



-- *********************************************************************

--    Standard Traps

-- *********************************************************************

snmpTraps      OBJECT IDENTIFIER ::= {snmpModules 1 1 5 }

coldStart NOTIFICATION-TYPE
 	 STATUS current
 	 DESCRIPTION
		"This trap signifies that the SonicWall appliance is re-initializing itself
		 such that the agent's configuration or the appliance itself
		 implementation may be altered. "
 	 ::= { snmpTraps 1 }

warmStart NOTIFICATION-TYPE
 	 STATUS current
 	 DESCRIPTION
		"This trap signifies that the SonicWall appliance is re-initializing itself
		 such that neither the agent configuration nor the appliance
		 implementation is altered. "
 	 ::= { snmpTraps 2 }

authenticationFailure NOTIFICATION-TYPE
 	 STATUS current
 	 DESCRIPTION
		"This trap signifies that the SonicWall appliance is the addressee of
		a protocol message that is not properly authenticated. "
 	 ::= { snmpTraps 5 }

-- *********************************************************************

-- Type define


-- *********************************************************************
MacAddress ::= TEXTUAL-CONVENTION
    STATUS current
    DESCRIPTION
        "ethernet address."
    SYNTAX OCTET STRING (SIZE (6))


FwTrapType ::= TEXTUAL-CONVENTION
    STATUS current
    DESCRIPTION
        "Trap type of firewall. The type have 4 digitals, ABCD.
         AB represent trap catalog, CD represent trap type in the catalog."
    SYNTAX INTEGER {

-- =========== System Environment======================================
        trapTypeSysEnvVoltageFail			(101),  -- Voltages Out of Tolerance
        trapTypeSysEnvFanFail				(102),  -- Fan Failure
        trapTypeSysEnvTempYellow			(103),  -- Thermal Yellow
        trapTypeSysEnvTempRed				(104),  -- Thermal Red
        trapTypeSysEnvTempRedExceed			(105),  -- Thermal Red Timer Exceeded

-- =========== Attack =================================================

        trapTypePingOfDeathBlocked			(501),  -- Ping of death blocked
        trapTypeIPSpoofDetected				(502),  -- IP spoof detected
        trapTypePossibleSynFlood			(503),  -- Possible SYN flood attack
        trapTypeProbableSynFlood			(504),  -- Probable SYN flood attack
        trapTypeLandAttack					(505),  -- Land Attack Dropped
        trapTypeAttemptedAdminLoginFromWAN	(506),  -- Attempted administrator login from WAN
        trapTypeLogUnknownSpi				(507),  -- Unknown IPSec SPI
        trapTypeLogIpsecAuthFailure			(508),  -- IPSec Authentication Failed
        trapTypeLogIpsecDecryptFailure		(509),  -- IPSec Decryption Failed
        trapTypeLogIllegalIpsecPeer			(510),  -- IPSec packet from or to an illegal host
        trapTypeNetBusDropped				(511),  -- NetBus Attack Dropped
        trapTypeBackOrificeDropped			(512),  -- Back Orifice Attack Dropped
        trapTypeNetSpyDropped				(513),  -- Net Spy Attack Dropped
        trapTypeSub7Dropped					(514),  -- Sub Seven Attack Dropped
        trapTypeRipperDropped				(515),  -- Ripper Attack Dropped
        trapTypeStrikerDropped				(516),  -- Striker Attack Dropped
        trapTypeSennaSpyDropped				(517),  -- Senna Spy Attack Dropped
        trapTypePriorityDropped				(518),  -- Priority Attack Dropped
        trapTypeIniKillerDropped			(519),  -- Ini Killer Attack Dropped
        trapTypeSmurfDropped				(520),  -- Smurf Amplification Attack Dropped
        trapTypePortScanPossible			(521),  -- Possible Port Scan
        trapTypePortScanProbable			(522),  -- Probable Port Scan
        trapTypeLogIkeProposalReject		(523),  -- IKE Responder: IPSec proposal not acceptable
        trapTypeAVReceivedAlert				(524),  -- Received AV Alert
        trapTypeLogAddTest					(525),  -- Add an attack message
        trapTypeAVExpiredMsg				(526),  -- Received AV Alert: Your SonicWall Network Anti-Virus subscription has expired.
        trapTypeForbiddenAttachment			(527),  -- Forbidden E-mail attachment altered
        trapTypeTcpFinScanDropped			(528),  -- Probable TCP FIN scan
        trapTypeTcpXmasScanDropped			(529),  -- Probable TCP XMAS scan
        trapTypeTcpNullScanDropped			(530),  -- Probable TCP NULL scan
        trapTypeReplayDetected				(531),  -- IPSEC Replay Detected
        trapTypeFakeCertFound				(532),	-- Fraudulent Microsoft Certificate Blocked
        trapTypeDhcpRelayIpSpoof			(533),	-- IP spoof detected on packet to Central Gateway, packet dropped
        trapTypeForbiddenAttDeleted			(534),	-- Forbidden E-mail attachment deleted
        trapTypeIkeProposalBadMode			(535),	-- IKE Responder: Mode %d - not tunnel mode
        trapTypeIkeProposalPhase1IdMismatch	(536),	-- IKE Responder: No matching Phase 1 ID found for proposed remote network
        trapTypeIkeProposalBadZeroRemAddr	(537),	-- IKE Responder: Proposed remote network is 0.0.0.0 but not DHCP relay nor default route
        trapTypeIkeProposalNoRemNetMatch	(538),	-- IKE Responder: No match for proposed remote network address
        trapTypeIkeProposalAddrWithDefGw	(539),	-- IKE Responder: Default LAN gateway is set but peer is not proposing to use this SA as his default route
        trapTypeIkeProposalOutsideNotNatPub	(540),	-- IKE Responder: Tunnel terminates outside firewall but proposed local network is not NAT public address
        trapTypeIkeProposalInsideNotLanDmz	(541),	-- IKE Responder: Tunnel terminates inside firewall but proposed local network is not on LAN or DMZ
        trapTypeIkeProposalLanAddrOnDmz		(542),	-- IKE Responder: Tunnel terminates on DMZ but proposed local network is on LAN
        trapTypeIkeProposalDmzAddrOnLan		(543),	-- IKE Responder: Tunnel terminates on LAN but proposed local network is on DMZ
        trapTypeIkeProposalAhPfsMismatch	(544),	-- IKE Responder: AH Perfect Forward Secrecy mismatch
        trapTypeIkeProposalEspPfsMismatch	(545),	-- IKE Responder: ESP Perfect Forward Secrecy mismatch
        trapTypeIkeProposalAlgKeyMismatch	(546),	-- IKE Responder: Algorithms and/or keys do not match
        trapTypeTcpXmasTreeDropped			(547),	-- TCP Xmas Tree Blocked
        trapTypeIkeProposalOutsideRemNotNatPub (548),	-- Tunnel terminates outside firewall but proposed remote network is not NAT public address
        trapTypeIkeProposalBadZeroLocAddr	(549),	-- IKE Responder: Proposed local network is 0.0.0.0 but SA has no LAN Default Gateway
		trapTypeDroppedMsgPartial			(550),	-- E-Mail fragment dropped
		trapTypeFtpPasvRspSpoof				(551),	-- FTP: PASV response spoof attack dropped
		trapTypeAVExpirationWarningMsg		(552),  -- Received AV Alert: Your SonicWall Network Anti-Virus subscription will expire in 7 days.
		trapTypeIkeProposalAddrWithOutDefGw	(553),  -- IKE Responder: Default LAN gateway is not set but peer is proposing to use this SA as a default route.
		trapTypeMalformedIpPacket			(554),	-- Malformed IP packet dropped.
		trapTypeFtpPortBounceAttack			(555),  -- FTP: PORT bounce attack dropped.
		trapTypeFtpPasvBounceAttack			(556),  -- FTP: PASV response bounce attack dropped.
		trapTypeFtpDataPort					(557),  -- FTP: Data connection from non default port dropped
		trapTypeTcpSynFinDropped			(558),  -- TCP Syn/Fin packet dropped
		trapTypeUserLoginDisabled			(559),  -- User login not enabled from %s
		trapTypeWrongAdminPasswd			(560),  -- Administrator login denied
		trapTypeUserLoginLockout			(561),  -- User login failure rate exceeded - logins from user IP address denied
		trapTypeCFSExpirationWarningMsg		(562),  -- Received CFS Alert: Your SonicWall Content Filtering subscription will expire in 7 days.
		trapTypeCFSExpirationMsg	   		(563),  -- Received CFS Alert: Your SonicWall Content Filtering subscription has expired.
		trapTypeMafiaExpirationWarningMsg	(564),  -- Received E-Mail Filter Alert: Your SonicWall E-Mail Filtering subscription will expire in 7 days.
		trapTypeMafiaExpirationMsg		 	(565),  -- Received E-Mail Filter Alert: Your SonicWall E-Mail Filtering subscription has expired.
		trapTypeMaxFailedDials			 	(566),  -- Maximum sequential failed dial attempts (10) to a single dial-up number: %s
		trapType30MinDialDelay			 	(567),  -- Regulatory requirements prohibit %s from being re-dialed for 30 minutes
		trapTypeSpankAttackDropped		 	(568),  -- Spank attack multicast packet dropped
		trapTypeIDPDetectionAlert		 	(569),  -- IDP Detection Alert: %s
		trapTypeIDPPreventionAlert		 	(570),  -- IDP Prevention Alert: %s
		trapTypeIDPExpiredMsg			 	(571),  -- Received IDP Alert: Your SonicWall Intrusion Prevention (IDP) subscription has expired.
        trapTypeIDPReassemblyDetectionAlert (573),  -- IPS Detection Alert: %s
        trapTypeIDPReassemblyPreventionAlert (574),  -- IPS Prevention Alert: %s
        trapTypeAntiSpywarePreventionAlert  (575),  -- Anti-Spyware Prevention Alert: %s
        trapTypeAntiSpywareDetectionAlert   (576),  -- Anti-Spyware Detection Alert: %s
        trapTypeAntiSpywareExpiredMsg       (577),  -- Anti-Spyware Service Expired
        trapTypeAVGatewayAlert              (578),  -- Gateway Anti-Virus Alert: %s

-- =========== System Errors =================================================
        trapTypeLogFull							(601), -- Log full; deactivating SonicWall
        trapTypeLogProblemLoadingCheckSettings	(602), -- Problem loading the Filter list; check Filter settings
        trapTypeLogProblemLoadingCheckDNS		(603), -- Problem loading the Filter list; check your DNS server
        trapTypeLogProblemEmailingCheckSettings	(604), -- Problem sending log email; check log settings
        trapTypeIllegalLanAddressInUse			(605), -- Illegal LAN address in use
        trapTypeNATCouldntRemap					(606), -- NAT could not remap incoming packet
        trapTypeCacheFull						(607), -- The cache is full; %d open connections; some will be dropped
        trapTypeConnDroppedTooManyIP			(608), -- License exceeded: Connection dropped because too many IP addresses are in use on your LAN
        trapTypeLogOutOfMemory					(609), -- Diagnostic Code E
        trapTypeInternalErr						(610), -- Diagnostic Code D
        trapTypeLogSuspendReboot				(611), -- Diagnostic Code A
        trapTypeLogDeadlockReboot				(612), -- Diagnostic Code B
        trapTypeLogLowMemReboot					(613), -- Diagnostic Code C
        trapTypeHaIdlePrimary					(614), -- Primary firewall has transitioned to Idle
        trapTypeHaMissedHeartbeatPrimary		(615), -- Primary missed heartbeats from Active Secondary: Primary going Active
        trapTypeHaMissedHeartbeatBackup			(616), -- Secondary missed heartbeats from Active Primary: Secondary going Active
        trapTypeHaErrorReceivedPrimary			(617), -- Primary received error signal from Active Secondary: Primary going Active
        trapTypeHaErrorReceivedBackup			(618), -- Secondary received error signal from Active Primary: Secondary going Active
        trapTypeHaBackupPreempt					(619), -- Secondary firewall being preempted by Primary
        trapTypeHaPrimaryPreempt				(620), -- Primary firewall preempting Secondary
        trapTypeLogHttpServerReboot				(621), -- Diagnostic Code F
        trapTypeBackupActivePreempt				(622), -- Secondary going Active in preempt mode after reboot
        trapTypeCflUpdateApplianceNotRegistered	(623), -- Problem loading the Filter list; Appliance not registered.
        trapTypeCflUpdateSubscriptionExpired	(624), -- Problem loading the Filter list; Subscription expired.
        trapTypeCflUpdateErrorTransient			(625), -- Problem loading the Filter list; Try loading it again.
        trapTypeCflUpdateErrorTransientAuto		(626), -- Problem loading the Filter list; Retrying later.
        trapTypeCflUpdateErrorInternal			(627), -- Problem loading the Filter list; Flash write failure.
        trapTypeCflApplianceCflExpired			(628), -- The loaded content filter list has expired.
        trapTypeHaSetError						(629), -- Error setting the IP address of the Secondary, please manually set to Secondary LAN IP
        trapTypeHaSyncError						(630), -- Error updating HA peer configuration
        trapTypeCflSubscriptionExpiredEmail		(631), -- Content filter subscription expired.
        trapTypeDhcpRelayTableSyncFailure		(632), -- Failed to synchronize Relay IP Table
        trapTypeBackupLinkDown					(633), -- Backup WAN link down, Primary going Active
        trapTypePrimaryLinkDown					(634), -- Primary WAN link down, Backup going Active
        trapTypeWanLinkDown   					(635), -- The current WAN interface is not ready to route packets.
        trapTypeWanIpChange						(636), -- Wan IP Changed
        trapTypeWfoProbeFailed					(637), -- Probing failure on %s
        trapTypeWfoProbeSuccess					(638), -- Probing succeeded on %s
        trapTypeWanModeIs            			(639), -- The network connection in use is %s
        trapTypeEtherPortUp						(640), -- %s Ethernet Port Up
        trapTypeEtherPortDown					(641), -- %s Ethernet Port Down
        trapTypeWlanReboot						(642), -- Diagnostic Code D
        trapTypeGlobalVPNClientNotAuthorized	(643), -- Global VPN Client connection is not allowed. Appliance is not registered.
        trapTypeRtcBatteryDead1					(644), -- Real time clock battery failure  Time values may be incorrect
        trapTypeRtcBatteryDead2					(645), -- If not already enabled, enabling NTP is recommended
        trapTypeMultiIfLinkUp					(646), -- Interface %s Link Is Up
        trapTypeMultiIfLinkDown					(647), -- Interface %s Link Is Down
        trapTypeOlderPrefs						(648), -- A prior version of preferences was loaded because the most recent preferences file was inaccessible
        trapTypePrefsTooBig						(649), -- The preferences file is too large to be saved in available flash memory
        trapTypePrefsDefaulted					(650), -- All preference values have been set to factory default values
        trapTypeWlbFailover						(651), -- WLB Failover in progress
        trapTypeWlbFailback						(652), -- WLB Failback initiated by %s
        trapTypeWlbResourceAvailable			(653), -- WLB Resource is now available
        trapTypeWlbResourceFailed				(654), -- WLB Resource failed
        trapTypeLogStackMarginReboot			(655), -- Diagnostic Code G
        trapTypeLogDeleteReboot					(656), -- Diagnostic Code H
        trapTypeLogDeleteStackReboot			(657), -- Diagnostic Code I
        trapTypeVPNClientLicenseExceeded		(658), -- Global VPN Client License Exceeded: Connection denied
        trapTypeFipsChangeState2Error			(659), -- Entering FIPS Error State
        trapTypeBlockQuickModeWithDefaultKeyId	(660), -- Blocked Quick Mode for Client using Default KeyId
        trapTypeLogProblemAddingL2tpIpPool	  	(661), -- Adding L2TP IP pool Address object Failed
        trapTypeHaSyncingError				  	(662), -- Error Synchronizing HA Peer Firewall
		trapTypeHaRebootingError				(663), -- Error Rebooting HA Peer Firewall
		trapTypeHaHaLicenseError				(664), -- License of HA pair doesn't match
		trapTypeHaRebootReceivedPrimary			(665), -- Primary received reboot signal from Secondary
		trapTypeHaRebootReceivedBackup			(666), -- Secondary firewall being preempted by Primary
		trapTypeSrcConnOverLimit				(667), -- Packet dropped; connection limit for this source IP address has been reached
		trapTypeDstConnOverLimit				(668), -- Packet dropped; connection limit for this destination IP address has been reached

-- =========== Blocked Web Sites =================================================
        trapTypeWebSiteBlocked					(701), -- Web site blocked
        trapTypeNewsgroupBlocked				(702), -- Newsgroup blocked
        trapTypeWebSiteAccessed					(703), -- Web site accessed
        trapTypeNewsgroupAccessed				(704), -- Newsgroup accessed
        trapTypeProxyAccessBlocked				(705), -- Access to Proxy Server Blocked

-- =========== Vpn Tunnel Status =================================================
        trapTypeVpnTunnelStatus					(801), -- IPSec tunnel status

-- =========== WIDS ==============================================================
        trapTypeWlanRogueAP						(901), -- Found Rogue Access Point
        trapTypeWlanSeqCheck	   				(902), -- wlan sequence number out of order
        trapTypeWlanAssoFlood					(903), -- Association Flood from wlan station
        trapTypeWlanProbeCheck					(904), -- WLAN client null probing

-- ========== None =================================================

        trapTypeEnhLogHeader1                                         ( 1001),  -- Log (part
        trapTypeEnhLogHeader2                                         ( 1002),  -- ) dumped to email at
        trapTypeEnhLogEmailSubject                                    ( 1003),  -- Log file from SonicWall
        trapTypeEnhAlertEmailSubject                                  ( 1004),  -- *** Alert from SonicWall ***
        trapTypeEnhCode                                               ( 1005),  -- Code:
        trapTypeEnhType                                               ( 1006),  -- Type:
        trapTypeEnhSource                                             ( 1007),  -- Source:
        trapTypeEnhDestination                                        ( 1008),  -- Destination:
        trapTypeEnhRuleIndex                                          ( 1009),  -- Rule
        trapTypeEnhSPI                                                ( 1010),  -- SPI:
        trapTypeEnhLocalRange                                         ( 1011),  -- local range:
        trapTypeEnhRemoteRange                                        ( 1012),  -- remote range:
        trapTypeEnhMTU                                                ( 1013),  -- MTU:
        trapTypeEnhCategory                                           ( 1014),  -- Category:
        trapTypeEnhProtocol                                           ( 1015),  -- Protocol:

-- ========== Unused ===============================================

        trapTypeEnhProbableSynFlood                                   ( 1201),  -- [not found in tip]
        trapTypeEnhNATCouldntRemap                                    ( 1202),  -- NAT could not remap incoming packet
        trapTypeEnhNoICMPRedirectSent                                 ( 1203),  -- No ICMP redirect sent
        trapTypeEnhDataChannelAddFailed                               ( 1204),  -- Failure to add data channel
        trapTypeEnhRADecodeFailed                                     ( 1205),  -- RealAudio decode failure
        trapTypeEnhAVSpare1                                           ( 1206),  -- AV unused/spare
        trapTypeEnhLanPktRcvd                                         ( 1207),  -- [not found in tip]
        trapTypeEnhL2TPNotReady                                       ( 1208),  -- L2TP enabled but not ready
        trapTypeEnhVPNDisDialup                                       ( 1209),  -- VPN disabled for active dial up
        trapTypeEnhVoipSpare25                                        ( 1210),  -- unused/spare
        trapTypeEnhVoipSpare26                                        ( 1211),  -- unused/spare
        trapTypeEnhVoipSpare27                                        ( 1212),  -- unused/spare
        trapTypeEnhMcastSpare29                                       ( 1213),  -- unused/spare
        trapTypeEnhMcastSpare30                                       ( 1214),  -- unused/spare
        trapTypeEnhMcastSpare31                                       ( 1215),  -- unused/spare
        trapTypeEnhMcastSpare32                                       ( 1216),  -- unused/spare
        trapTypeEnhWlanSpare11                                        ( 1217),  -- unused/spare
        trapTypeEnhWlanSpare12                                        ( 1218),  -- unused/spare
        trapTypeEnhWlanSpare13                                        ( 1219),  -- unused/spare
        trapTypeEnhWlanSpare14                                        ( 1220),  -- unused/spare
        trapTypeEnhWlanSpare15                                        ( 1221),  -- unused/spare
        trapTypeEnhUserLoginLdapSpare15                               ( 1222),  -- unused/spare
        trapTypeEnhUserLoginLdapSpare16                               ( 1223),  -- unused/spare
        trapTypeEnhGSCSpare4                                          ( 1224),  -- unused/spare
        trapTypeEnhGSCSpare5                                          ( 1225),  -- unused/spare
        trapTypeEnhMsAdSpare2                                         ( 1226),  -- unused/spare
        trapTypeEnhMsAdSpare3                                         ( 1227),  -- unused/spare
        trapTypeEnhMsAdSpare4                                         ( 1228),  -- unused/spare
        trapTypeEnhDDNSSpare14                                        ( 1229),  -- unused/spare
        trapTypeEnhDDNSSpare15                                        ( 1230),  -- unused/spare
        trapTypeEnhDDNSSpare16                                        ( 1231),  -- unused/spare
        trapTypeEnhIDPSpare3                                          ( 1232),  -- unused/spare
        trapTypeEnhIDPSpare4                                          ( 1233),  -- unused/spare
        trapTypeEnhGmsSpare3                                          ( 1234),  -- unused/spare
        trapTypeEnhGmsSpare4                                          ( 1235),  -- unused/spare
        trapTypeEnhDhcpsSpare2                                        ( 1236),  -- HA unused/spare
        trapTypeEnhDhcpsSpare3                                        ( 1237),  -- HA unused/spare
        trapTypeEnhDhcpsSpare4                                        ( 1238),  -- HA unused/spare
        trapTypeEnhVlanSpare1                                         ( 1239),  -- VLAN unused/spare
        trapTypeEnhVlanSpare2                                         ( 1240),  -- VLAN unused/spare
        trapTypeEnhVlanSpare3                                         ( 1241),  -- VLAN unused/spare
        trapTypeEnhARSSpare1                                          ( 1242),  -- ARS unused/spare
        trapTypeEnhARSSpare2                                          ( 1243),  -- ARS unused/spare
        trapTypeEnhARSSpare3                                          ( 1244),  -- ARS unused/spare
        trapTypeEnhARSSpare4                                          ( 1245),  -- ARS unused/spare
        trapTypeEnhOcspSpare4                                         ( 1246),  -- OCSP unused/spare
        trapTypeEnhSynSpare2                                          ( 1247),  -- SYN unused/spare
        trapTypeEnhSynSpare3                                          ( 1248),  -- SYN unused/spare
        trapTypeEnhIPSNoSigRAM                                        ( 1249),  -- Unable to download IPS/GAV/Aspy Signature database. Firewall must first be restarted to free memory used by downloaded firmware.
        trapTypeEnhSpare888                                           ( 1250),  -- unused/spare
        trapTypeEnhSpare889                                           ( 1251),  -- unused/spare
        trapTypeEnhSpare920                                           ( 1252),  -- unused/spare
        trapTypeEnhSpare921                                           ( 1253),  -- unused/spare
        trapTypeEnhIkeV2Spare1                                        ( 1254),  -- unused/spare
        trapTypeEnhIkeV2Spare2                                        ( 1255),  -- unused/spare
        trapTypeEnhIkeV2Spare3                                        ( 1256),  -- unused/spare
        trapTypeEnhIkeV2Spare4                                        ( 1257),  -- unused/spare

-- ========== Legacy System Maintenance ============================

-- ========== Legacy System Errors =================================

-- ========== Legacy Blocked Web Sites =============================

-- ========== Legacy Blocked Java Etc ==============================

-- ========== Legacy User Activity =================================

-- ========== Legacy Denied LAN IP =================================

-- ========== Legacy Attacks =======================================

-- ========== Legacy Dropped TCP ===================================

-- ========== Legacy Dropped UDP ===================================

-- ========== Legacy Dropped ICMP ==================================

-- ========== Legacy Network Debug =================================

-- ========== Legacy System Environment ============================

-- ========== Legacy VPN Tunnel Status =============================

-- ========== Legacy 802.11b Management ============================

-- ========== Auth Access ==========================================

        trapTypeEnhUserDisconnectDetect                               ( 4201),  -- User logged out - user disconnect detected (heartbeat timer expired)
        trapTypeEnhSuccessfulAdminLogin                               ( 4202),  -- Administrator login allowed
        trapTypeEnhWrongAdminPasswd                                   ( 4203),  -- Administrator login denied due to bad credentials
        trapTypeEnhSuccessfulUserLogin                                ( 4204),  -- Local user login allowed
        trapTypeEnhWrongUserPasswd                                    ( 4205),  -- Local user login denied due to bad credentials
        trapTypeEnhUnknownUserLoginAttempt                            ( 4206),  -- User login denied due to bad credentials
        trapTypeEnhLoginTimedOut                                      ( 4207),  -- Login screen timed out
        trapTypeEnhAdminLoginDisabled                                 ( 4208),  -- Administrator login denied from %s; logins disabled from this interface
        trapTypeEnhSuccessfulAdminLoginFromCLI                        ( 4209),  -- CLI administrator login allowed
        trapTypeEnhWrongAdminPasswdFromCLI                            ( 4210),  -- CLI administrator login denied due to bad credentials
        trapTypeEnhSuccessfulAdminVpnLogin                            ( 4211),  -- VPN zone administrator login allowed
        trapTypeEnhSuccessfulAdminWanLogin                            ( 4212),  -- WAN zone administrator login allowed
        trapTypeEnhSuccessfulUserVpnLogin                             ( 4213),  -- VPN zone remote user login allowed
        trapTypeEnhSuccessfulUserWanLogin                             ( 4214),  -- WAN zone remote user login allowed
        trapTypeEnhAdminLogout                                        ( 4215),  -- Administrator logged out
        trapTypeEnhAdminSessInactivity                                ( 4216),  -- Administrator logged out - inactivity timer expired
        trapTypeEnhUserLogout                                         ( 4217),  -- User logged out
        trapTypeEnhUserSessTimeout                                    ( 4218),  -- User logged out - max session time exceeded
        trapTypeEnhUserSessInactivity                                 ( 4219),  -- User logged out - inactivity timer expired
        trapTypeEnhAdminNameChanged                                   ( 4220),  -- Adminstrator name changed
        trapTypeEnhUserLoginLockout                                   ( 4221),  -- User login failure rate exceeded - logins from user IP address denied
        trapTypeEnhUserLoginLockoutExpire                             ( 4222),  -- Locked-out user logins allowed - lockout period expired
        trapTypeEnhUserLoginLockoutClear                              ( 4223),  -- Locked-out user logins allowed by administrator
        trapTypeEnhWlanNoGuestPrivilege                               ( 4224),  -- User login denied - User has no privileges for WLAN guest service
        trapTypeEnhVpnDisabled                                        ( 4225),  -- VPN disabled by administrator
        trapTypeEnhVpnEnabled                                         ( 4226),  -- VPN enabled by administrator
        trapTypeEnhWlanDisabled                                       ( 4227),  -- WLAN disabled by administrator
        trapTypeEnhWlanEnabled                                        ( 4228),  -- WLAN enabled by administrator
        trapTypeEnhWiFiSecDisabled                                    ( 4229),  -- WiFiSec Enforcement disabled by administrator
        trapTypeEnhWiFiSecEnabled                                     ( 4230),  -- WiFiSec Enforcement enabled by administrator
        trapTypeEnhMacFilterListEnabled                               ( 4231),  -- Wireless MAC Filter List enabled by administrator
        trapTypeEnhMacFilterListDisabled                              ( 4232),  -- Wireless MAC Filter List disabled by administrator
        trapTypeEnhPPPoEUserChanged                                   ( 4233),  -- PPPoE user name changed by Administrator
        trapTypeEnhPPPoEPasswordChanged                               ( 4234),  -- PPPoE password changed by Administrator
        trapTypeEnhAdminLogoutFromCLI                                 ( 4235),  -- CLI administrator logged out
        trapTypeEnhWlanGuestLimit                                     ( 4236),  -- User login failed - Guest service limit reached
        trapTypeEnhWlanSessionTimeout                                 ( 4237),  -- WLAN Guest Session Timeout
        trapTypeEnhWlanAccountTimeout                                 ( 4238),  -- WLAN Guest Account Timeout
        trapTypeEnhWlanGuestAlreadyLoggedIn                           ( 4239),  -- Guest login denied. Guest '%s' is already logged in. Please try again later.
        trapTypeEnhWlanGuestCreated                                   ( 4240),  -- Guest account '%s' created
        trapTypeEnhWlanGuestDeleted                                   ( 4241),  -- Guest account '%s' deleted
        trapTypeEnhWlanGuestDisabled                                  ( 4242),  -- Guest account '%s' disabled
        trapTypeEnhWlanGuestReEnabled                                 ( 4243),  -- Guest account '%s' re-enabled
        trapTypeEnhWlanGuestPruned                                    ( 4244),  -- Guest account '%s' pruned
        trapTypeEnhWlanGuestReGenerated                               ( 4245),  -- Guest account '%s' re-generated
        trapTypeEnhWlanIdleTimeout                                    ( 4246),  -- WLAN Guest Idle Timeout
        trapTypeEnhUserLoginDisabled                                  ( 4247),  -- User login disabled from %s
        trapTypeEnhWlanSchedDisabled                                  ( 4248),  -- WLAN disabled by schedule
        trapTypeEnhWlanSchedEnabled                                   ( 4249),  -- WLAN enabled by schedule
        trapTypeEnhRemoteDialupReceived                               ( 4250),  -- Incoming call received for Remotely Triggered Dial-out session
        trapTypeEnhRemoteDialupAuthReq                                ( 4251),  -- Remotely Triggered Dial-out session started.  Requesting authentication
        trapTypeEnhInvalidRemoteDialupPassword                        ( 4252),  -- Incorrect authentication received for Remotely Triggered Dial-out
        trapTypeEnhValidRemoteDialupPassword                          ( 4253),  -- Successful authentication received for Remotely Triggered Dial-out
        trapTypeEnhRemoteDialupPasswordTimeout                        ( 4254),  -- Authentication timeout during Remotely Triggered Dial-out session
        trapTypeEnhRemoteDialupAbortedForData                         ( 4255),  -- Remotely Triggered Dial-out session ended.  Valid WAN bound data found.  Normal dial-up sequence will commence
        trapTypeEnhUserLoginBarredByRule                              ( 4256),  -- User login denied - not allowed by policy rule
        trapTypeEnhUserLoginNotFoundLocal                             ( 4257),  -- User login denied - not found locally
        trapTypeEnhAdminCfgSessStart                                  ( 4258),  -- Configuration mode administration session started
        trapTypeEnhAdminCfgSessEnd                                    ( 4259),  -- Configuration mode administration session ended
        trapTypeEnhGUIAdminRdOnlySessStart                            ( 4260),  -- Read-only mode GUI administration session started
        trapTypeEnhGUIAdminNonCfgSessStart                            ( 4261),  -- Non-config mode GUI administration session started
        trapTypeEnhGUIAdminSessEnd                                    ( 4262),  -- GUI administration session ended
        trapTypeEnhLdapBindFail                                       ( 4263),  -- Bind to LDAP server failed
        trapTypeEnhLdapNonTLS                                         ( 4264),  -- Using LDAP without TLS - highly insecure
        trapTypeEnhLdapNonAdminAcct                                   ( 4265),  -- LDAP using non-administrative account - VPN client user will not be able to change passwords

-- ========== BOOTP ================================================

        trapTypeEnhBootpCentralAck                                    ( 4401),  -- BOOTP server response relayed to remote device
        trapTypeEnhBootpReplyConflict                                 ( 4402),  -- "BOOTP Client IP address on LAN conflicts with remote device IP, deleting IP address from remote table"
        trapTypeEnhBootpRemoteAck                                     ( 4403),  -- BOOTP reply relayed to local device
        trapTypeEnhBootpRequestMessage                                ( 4404),  -- BOOTP Request received from remote device

-- ========== Crypto Test ==========================================

        trapTypeEnhCryptFipsErrorState                                ( 4601),  -- Entering FIPS ERROR state
        trapTypeEnhCryptDesTestFailed                                 ( 4602),  -- Crypto DES test failed
        trapTypeEnhCryptDhTestFailed                                  ( 4603),  -- Crypto DH test failed
        trapTypeEnhCryptHmacMD5TestFailed                             ( 4604),  -- Crypto Hmac-MD5 fest failed
        trapTypeEnhCryptHmacSha1TestFailed                            ( 4605),  -- Crypto Hmac-Sha1 test failed
        trapTypeEnhCryptRsaTestFailed                                 ( 4606),  -- Crypto RSA test failed
        trapTypeEnhCryptSha1TestFailed                                ( 4607),  -- Crypto Sha1 test failed
        trapTypeEnhCryptHwDesTestFailed                               ( 4608),  -- Crypto hardware DES test failed
        trapTypeEnhCryptHw3DesTestFailed                              ( 4609),  -- Crypto hardware 3DES test failed
        trapTypeEnhCryptHwDesShaTestFailed                            ( 4610),  -- Crypto hardware DES with SHA test failed
        trapTypeEnhCryptHw3DesShaTestFailed                           ( 4611),  -- Crypto Hardware 3DES with SHA test failed
        trapTypeEnhCryptMd5TestFailed                                 ( 4612),  -- Crypto MD5 test failed
        trapTypeEnhFipsChangeState2Error                              ( 4613),  -- Entering FIPS Error State.
        trapTypeEnhCryptHwAesTestFailed                               ( 4614),  -- Crypto Hardware AES test failed

-- ========== DHCP Client ==========================================

        trapTypeEnhDHCPCRetransDiscover                               ( 4801),  -- Retransmitting DHCP DISCOVER.
        trapTypeEnhDHCPCRetransRequestRequest                         ( 4802),  -- Retransmitting DHCP REQUEST (Requesting).
        trapTypeEnhDHCPCRetransRequestRenew                           ( 4803),  -- Retransmitting DHCP REQUEST (Renewing).
        trapTypeEnhDHCPCRetransRequestRebind                          ( 4804),  -- Retransmitting DHCP REQUEST (Rebinding).
        trapTypeEnhDHCPCRetransRequestReboot                          ( 4805),  -- Retransmitting DHCP REQUEST (Rebooting).
        trapTypeEnhDHCPCRetransRequestVerify                          ( 4806),  -- Retransmitting DHCP REQUEST (Verifying).
        trapTypeEnhDHCPCSendDiscover                                  ( 4807),  -- Sending DHCP DISCOVER.
        trapTypeEnhDHCPCNoOffers                                      ( 4808),  -- DHCP Server not available. Did not get any DHCP OFFER.
        trapTypeEnhDHCPCGotOffer                                      ( 4809),  -- Got DHCP OFFER. Selecting.
        trapTypeEnhDHCPCSelecting                                     ( 4810),  -- Sending DHCP REQUEST.
        trapTypeEnhDHCPCRequestFailed                                 ( 4811),  -- DHCP Client did not get DHCP ACK.
        trapTypeEnhDHCPCRequestNAK                                    ( 4812),  -- DHCP Client got NACK.
        trapTypeEnhDHCPCRequestACK                                    ( 4813),  -- DHCP Client got ACK from server.
        trapTypeEnhDHCPCRequestDecline                                ( 4814),  -- DHCP Client is declining address offered by the server.
        trapTypeEnhDHCPCBoundRebind                                   ( 4815),  -- DHCP Client sending REQUEST and going to REBIND state.
        trapTypeEnhDHCPCBoundRenew                                    ( 4816),  -- DHCP Client sending REQUEST and going to RENEW state.
        trapTypeEnhDHCPCRequestRenew                                  ( 4817),  -- Sending DHCP REQUEST (Renewing).
        trapTypeEnhDHCPCRequestRebind                                 ( 4818),  -- Sending DHCP REQUEST (Rebinding).
        trapTypeEnhDHCPCRequestReboot                                 ( 4819),  -- Sending DHCP REQUEST (Rebooting).
        trapTypeEnhDHCPCRequestVerify                                 ( 4820),  -- Sending DHCP REQUEST (Verifying).
        trapTypeEnhDHCPCVerifyFailInit                                ( 4821),  -- DHCP Client failed to verify and lease has expired. Go to INIT state.
        trapTypeEnhDHCPCVerifyFailBound                               ( 4822),  -- DHCP Client failed to verify and lease is still valid. Go to BOUND state.
        trapTypeEnhDHCPCGotNewIP                                      ( 4823),  -- DHCP Client got a new IP address lease.
        trapTypeEnhDHCPCSendRelease                                   ( 4824),  -- Sending DHCP RELEASE.
        trapTypeEnhDHCPNotReady                                       ( 4825),  -- DHCP client  enabled but not ready
        trapTypeEnhDHCPCOfferError                                    ( 4826),  -- Received DHCP offer packet has errors
        trapTypeEnhDHCPCRequestResponseError                          ( 4827),  -- Received response packet for DHCP request has errors

-- ========== DHCP Relay ===========================================

        trapTypeEnhDhcprRemoteRelease                                 ( 5001),  -- DHCP RELEASE relayed to Central Gateway
        trapTypeEnhDhcprRemoteAck                                     ( 5002),  -- DHCP lease relayed to local device
        trapTypeEnhDhcprCentralRelease                                ( 5003),  -- DHCP RELEASE received from remote device
        trapTypeEnhDhcprCentralAck                                    ( 5004),  -- DHCP lease relayed to remote device
        trapTypeEnhDhcprAckConflict                                   ( 5005),  -- "DHCP lease to LAN device conflicts with remote device, deleting remote IP entry"
        trapTypeEnhDhcprAckInStaticTable                              ( 5006),  -- WARNING: DHCP lease relayed from Central Gateway conflicts with IP in Static Devices list
        trapTypeEnhDhcprAckIsRelay                                    ( 5007),  -- DHCP lease dropped.  Lease from Central Gateway conflicts with Relay IP
        trapTypeEnhDhcprIpSpoof                                       ( 5008),  -- "IP spoof detected on packet to Central Gateway, packet dropped"
        trapTypeEnhDhcprRemoteGetTable                                ( 5009),  -- Request for Relay IP Table from Central Gateway
        trapTypeEnhDhcprCentralGetTable                               ( 5010),  -- Requesting Relay IP Table from Remote Gateway
        trapTypeEnhDhcprRemoteSentTable                               ( 5011),  -- Sent Relay IP Table to Central Gateway
        trapTypeEnhDhcprCentralRcvTable                               ( 5012),  -- Obtained Relay IP Table from Remote Gateway
        trapTypeEnhDhcprTableReqTimedOut                              ( 5013),  -- Failed to synchronize Relay IP Table
        trapTypeEnhDhcprNoRelayIpAvailable                            ( 5014),  -- WARNING: Central Gateway does not have a Relay IP Address. DHCP message dropped.
        trapTypeEnhDhcprRequestMessage                                ( 5015),  -- DHCP REQUEST received from remote device
        trapTypeEnhDhcprDiscoverMessage                               ( 5016),  -- DHCP DISCOVER received from remote device
        trapTypeEnhDhcprDeclineMessage                                ( 5017),  -- DHCP DECLINE received from remote device
        trapTypeEnhDhcprOfferMessage                                  ( 5018),  -- DHCP OFFER received from server
        trapTypeEnhDhcprServerNakMessage                              ( 5019),  -- DHCP NACK received from server
        trapTypeEnhDhcpOverVpnTunnelNotDefined                        ( 5020),  -- ERROR: DHCP over VPN policy is not defined. Cannot start IKE.
        trapTypeEnhDhcprDiscoverLocal                                 ( 5021),  -- DHCP DISCOVER received from local device
        trapTypeEnhDhcprRequestLocal                                  ( 5022),  -- DHCP REQUEST received from local device
        trapTypeEnhDhcprAckIsRemoteMgmt                               ( 5023),  -- DHCP lease dropped.  Lease from Central Gateway conflicts with Remote Management IP

-- ========== Firewall Event =======================================

        trapTypeEnhActivated                                          ( 5201),  -- SonicWall activated
        trapTypeEnhRestartingDumpingLog                               ( 5202),  -- Restarting SonicWall; dumping log to email
        trapTypeEnhCacheFull                                          ( 5203),  -- The cache is full; %u open connections; some will be dropped
        trapTypeEnhConnDroppedTooManyIP                               ( 5204),  -- License exceeded: Connection dropped because too many IP addresses are in use on your LAN
        trapTypeEnhWanIpChange                                        ( 5205),  -- Wan IP Changed
        trapTypeEnhLogDebug                                           ( 5206),  -- Log Debug
        trapTypeEnhLogAddTest                                         ( 5207),  -- Add an attack message
        trapTypeEnhFirmwareUpdateEmailSubject                         ( 5208),  -- New firmware available.
        trapTypeEnhWanLinkDown                                        ( 5209),  -- The current WAN interface is not ready to route packets.
        trapTypeEnhEtherPortUp                                        ( 5210),  -- %s Ethernet Port Up
        trapTypeEnhEtherPortDown                                      ( 5211),  -- %s Ethernet Port Down
        trapTypeEnhHttpPortChange                                     ( 5212),  -- HTTP management port has changed
        trapTypeEnhHttpsPortChange                                    ( 5213),  -- HTTPS management port has changed
        trapTypeEnhImportedSAInvalid                                  ( 5214),  -- Imported VPN SA is invalid - disabled
        trapTypeEnhISDNUpdated                                        ( 5215),  -- ISDN Driver Firmware successfully updated
        trapTypeEnhWanNotSetup                                        ( 5216),  -- WAN Interface not setup
        trapTypeEnhWANNotReady                                        ( 5217),  -- WAN not ready
        trapTypeEnhInitializing                                       ( 5218),  -- SonicWall initializing
        trapTypeEnhBwmLimitOnUpgrade                                  ( 5219),  -- Maximum number of Bandwidth Managed rules exceeded upon upgrade to this version.  Some Bandwith settings ignored.
        trapTypeEnhMultiIfLinkUp                                      ( 5220),  -- Interface %s Link Is Up
        trapTypeEnhMultiIfLinkDown                                    ( 5221),  -- Interface %s Link Is Down
        trapTypeEnhIfProtoShutdown                                    ( 5222),  -- Interface IP Assignment changed: Shutting down %s
        trapTypeEnhIfProtoBindInit                                    ( 5223),  -- Interface IP Assignment : Binding and initializing %s
        trapTypeEnhNetworkOverlap                                     ( 5224),  -- Network for interface %s overlaps with another interface.
        trapTypeEnhInvalidNetwork                                     ( 5225),  -- Please connect interface %s to another network to function properly
        trapTypeEnhOlderPrefs                                         ( 5226),  -- A prior version of preferences was loaded because the most recent preferences file was inaccessible
        trapTypeEnhPrefsTooBig                                        ( 5227),  -- The preferences file is too large to be saved in available flash memory
        trapTypeEnhPrefsDefaulted                                     ( 5228),  -- All preference values have been set to factory default values
        trapTypeEnhStdToEnhUpgrade1                                   ( 5229),  -- A SonicOS Standard to Enhanced Upgrade was performed
        trapTypeEnhStdToEnhUpgrade2                                   ( 5230),  -- Not all configurations may have been completely upgraded
        trapTypeEnhStdToEnhUpgrade3                                   ( 5231),  -- Please manually check all system configurations for correctness of Upgrade
        trapTypeEnhSeuNoNetBios                                       ( 5232),  -- NetBIOS settings were not upgraded.  Use Network>IP Helper to configure NetBIOS support
        trapTypeEnhSeuNoLanSubnets                                    ( 5233),  -- LAN Subnet configurations were not upgraded.
        trapTypeEnhSeuNoTODObjects                                    ( 5234),  -- Time of day settings for firewall policies were not upgraded.
        trapTypeEnhSeuNoHF                                            ( 5235),  -- Hardware Failover settings were not upgraded.
        trapTypeEnhConnDroppedTooManyNodes                            ( 5236),  -- WAN node exceeded: Connection dropped because too many IP addresses are in use on your LAN
        trapTypeEnhInterface2DhcpsUpdate                              ( 5237),  -- DHCP Ranges altered automatically due to change in network settings for interface %s
		trapTypeEnhSrcConnOverLimit                                   ( 5238),  -- Packet dropped; connection limit for this source IP address has been reached
		trapTypeEnhDstConnOverLimit                                   ( 5239),  -- Packet dropped; connection limit for this destination IP address has been reached
		trapTypeEnhDhcpsConflictDetected                              ( 5240),  -- DHCP Server: IP conflict detected
		trapTypeEnhDhcpsDeclineFromClient                             ( 5241),  -- DHCP Server: Received DHCP decline from client
        trapTypeEnhSystemShutdown                                     ( 5242),  -- System shutdown by administrator. Power cycle required.

-- ========== Firewall Hardware ====================================

        trapTypeEnhInternalErr                                        ( 5401),  -- Diagnostic Code D
        trapTypeEnhLogSuspendReboot                                   ( 5402),  -- Diagnostic Code A
        trapTypeEnhLogDeadlockReboot                                  ( 5403),  -- Diagnostic Code B
        trapTypeEnhLogLowMemReboot                                    ( 5404),  -- Diagnostic Code C
        trapTypeEnhLogHttpServerReboot                                ( 5405),  -- Diagnostic Code F
        trapTypeEnhVpnHwInitErr                                       ( 5406),  -- Error initializing Hardware acceleration for VPN
        trapTypeEnhLogWlanReboot                                      ( 5407),  -- Diagnostic Code D
        trapTypeEnhRtcBatteryDead1                                    ( 5408),  -- Real time clock battery failure  Time values may be incorrect
        trapTypeEnhRtcBatteryDead2                                    ( 5409),  -- "If not already enabled, enabling NTP is recommended"
        trapTypeEnhSysEnvVoltageFail                                  ( 5410),  -- Voltages Out of Tolerance
        trapTypeEnhSysEnvFanFail                                      ( 5411),  -- Fan Failure
        trapTypeEnhSysEnvTempYellow                                   ( 5412),  -- Thermal Yellow
        trapTypeEnhSysEnvTempRed                                      ( 5413),  -- Thermal Red
        trapTypeEnhSysEnvTempRedExceed                                ( 5414),  -- Thermal Red Timer Exceeded
        trapTypeEnhLogStackMarginReboot                               ( 5415),  -- Diagnostic Code G
        trapTypeEnhLogDeleteReboot                                    ( 5416),  -- Diagnostic Code H
        trapTypeEnhLogDeleteStackReboot                               ( 5417),  -- Diagnostic Code I
        trapTypeEnhCellularModemRemoved                               ( 5418),  -- WWAN Dial-up: Card removed.
        trapTypeEnhCellularModemInserted                              ( 5419),  -- WWAN Dial-up: Card inserted.
        trapTypeEnhCellularModemNoSIM                                 ( 5420),  -- WWAN Dial-up: No SIM detected
        trapTypeEnhCellularModemNotFound                              ( 5421),  -- WWAN Dial-Up No device detected
        trapTypeEnhWWANModemType                                      ( 5422),  -- WWAN %s %s device detected
        trapTypeEnhLogDialupReboot                                    ( 5423),  -- Diagnostic Code J
        trapTypeEnhSysEnvNormal                                       ( 5424),  -- Physical environment normal
        trapTypeEnhSysEnvPwrSupplyDegraded                            ( 5425),  -- Power supply without redundancy
        trapTypeEnhSysEnvPsuFailed                                    ( 5433),  -- PSU is Bad
        trapTypeEnhSysEnvPsuNotPresent                                ( 5434),  -- PSU is Not Present
        trapTypeEnhSysEnvPsuOn                                        ( 5435),  -- PSU is On and OK

-- ========== Firewall Logging =====================================

        trapTypeEnhLogLogCleared                                      ( 5601),  -- Log Cleared
        trapTypeEnhLogSentToEmail                                     ( 5602),  -- Log successfully sent via email
        trapTypeEnhLogFull                                            ( 5603),  -- Log full; deactivating SonicWall
        trapTypeEnhLogProblemEmailingCheckSettings                    ( 5604),  -- Problem sending log email; check log settings
        trapTypeEnhLogEventRateExceeded                               ( 5605),  -- Maximum events per second threshold exceeded
        trapTypeEnhLogSyslogDataRateExceeded                          ( 5606),  -- Maximum syslog data per second threshold exceeded
        trapTypeEnhLogPopBeforeSmtpAuthFailed                         ( 5607),  -- SMTP POP-Before-SMTP authentication failed
        trapTypeEnhTimeChanged                                        ( 5608),  -- System clock manually updated
        trapTypetrapTypeCfgChgSucceeded                               ( 5609),  -- Succeed in configuration changes
        trapTypeCfgChgFailed                                          ( 5610),  -- Failed in configuration changes
        trapTypeCfgChgAttempt                                         ( 5611),  -- Attemp in configuration changes

-- ========== Firewall Rule ========================================

        trapTypeEnhRuleAdded                                          ( 5801),  -- Access rule added
        trapTypeEnhRuleModified                                       ( 5802),  -- Access rule modified
        trapTypeEnhRuleDeleted                                        ( 5803),  -- Access rule deleted
        trapTypeEnhRuleTableDefaulted                                 ( 5804),  -- Access rules restored to defaults

-- ========== GMS ==================================================

        trapTypeEnhLogStatusEvent                                     ( 6001),  -- Status
        trapTypeEnhGmsIfStats                                         ( 6002),  -- Interface statistics report
        trapTypeEnhGmsSpStats                                         ( 6003),  -- SonicPoint statistics report

-- ========== High Availability ====================================

        trapTypeEnhHaActivePrimary                                    ( 6201),  -- Primary firewall has transitioned to Active
        trapTypeEnhHaActiveBackup                                     ( 6202),  -- Secondary firewall has transitioned to Active
        trapTypeEnhHaIdlePrimary                                      ( 6203),  -- Primary firewall has transitioned to Idle
        trapTypeEnhHaIdleBackup                                       ( 6204),  -- Secondary firewall has transitioned to Idle
        trapTypeEnhHaMissedHeartbeatPrimary                           ( 6205),  -- Primary missed heartbeats from Secondary
        trapTypeEnhHaMissedHeartbeatBackup                            ( 6206),  -- Secondary missed heartbeats from Primary
        trapTypeEnhHaErrorReceivedPrimary                             ( 6207),  -- Primary received error signal from Secondary
        trapTypeEnhHaErrorReceivedBackup                              ( 6208),  -- Secondary received error signal from Primary
        trapTypeEnhHaBackupPreempt                                    ( 6209),  -- Secondary firewall being preempted by Primary
        trapTypeEnhHaPrimaryPreempt                                   ( 6210),  -- Primary firewall preempting Secondary
        trapTypeEnhActiveBackupBackdown                               ( 6211),  -- Active Secondary detects Active Primary: Secondary going Idle
        trapTypeEnhHaPrefsImportError                                 ( 6212),  -- Imported HA hardware ID did not match this firewall
        trapTypeEnhHaDiscoveredBackup                                 ( 6213),  -- Discovered HA Secondary Firewall
        trapTypeEnhHaSyncedHaPeer                                     ( 6214),  -- HA Peer Firewall Synchronized (%s)
        trapTypeEnhHaSyncingError                                     ( 6215),  -- Error synchronizing HA peer firewall (%s)
        trapTypeEnhHaWrongSrcPrimary                                  ( 6216),  -- Primary received heartbeat from wrong source
        trapTypeEnhHaWrongSrcBackup                                   ( 6217),  -- Secondary received heartbeat from wrong source
        trapTypeEnhHaPktError                                         ( 6218),  -- HA packet processing error
        trapTypeEnhHaContentNotMatch                                  ( 6219),  -- Heartbeat received from incompatible source
        trapTypeEnhBackupActivePreempt                                ( 6220),  -- Secondary going Active in preempt mode after reboot
        trapTypeEnhHaSetError                                         ( 6221),  -- "Error setting the IP address of the Secondary, please manually set to Secondary LAN IP"
        trapTypeEnhHaSyncError                                        ( 6222),  -- Error updating HA peer configuration
        trapTypeEnhPrimaryLinkDownBackoff                             ( 6223),  -- "Primary WAN link down, Primary going Idle"
        trapTypeEnhBackupLinkDown                                     ( 6224),  -- "Backup WAN link down, Primary going Active"
        trapTypeEnhPrimaryLinkDown                                    ( 6225),  -- "Primary WAN link down, Backup going Active"
        trapTypeEnhPrimaryLinkBackUp                                  ( 6226),  -- "Primary WAN link up, preempting Backup"
        trapTypeEnhHaRebootedHaPeer                                   ( 6227),  -- HA Peer Firewall Rebooted
        trapTypeEnhHaRebootingError                                   ( 6228),  -- Error Rebooting HA Peer Firewall
        trapTypeEnhHaLicenseError                                     ( 6229),  -- License of HA pair doesn't match
        trapTypeEnhHaRebootReceivedPrimary                            ( 6230),  -- Primary received reboot signal from Secondary
        trapTypeEnhHaRebootReceivedBackup                             ( 6231),  -- Secondary received reboot signal from Primary
        trapTypeEnhHaSyncingPref                                      ( 6232),  -- Synchronizing preferences to HA Peer Firewall
        trapTypeEnhHaLogicLinkUp                                      ( 6233),  -- Success to reach Interface %s probe
        trapTypeEnhHaLogicLinkDown                                    ( 6234),  -- Failure to reach Interface %s probe
        trapTypeEnhHaBackupWillShutdown                               ( 6235),  -- Secondary will be shut down in %s minutes
        trapTypeEnhHaBackupShutdown                                   ( 6236),  -- Secondary shut down because license is expired
        trapTypeEnhHaBackupActive                                     ( 6237),  -- Secondary active
        trapTypeEnhHaError                                            ( 6238),  -- %s
        trapTypeEnhHaWarn                                             ( 6239),  -- %s
        trapTypeEnhHaInfo                                             ( 6240),  -- %s
        trapTypeEnhHaAlert                                            ( 6241),  -- %s
        trapTypeEnhHaNotice                                           ( 6242),  -- %s
        trapTypeEnhHaDebug                                            ( 6243),  -- %s

-- ========== Intrusion Detection ==================================

        trapTypeEnhPingOfDeathBlocked                                 ( 6401),  -- Ping of death dropped
        trapTypeEnhIPSpoofDetected                                    ( 6402),  -- IP spoof dropped
        trapTypeEnhPossibleSynFlood                                   ( 6403),  -- Possible SYN flood attack detected
        trapTypeEnhLandAttack                                         ( 6404),  -- Land attack dropped
        trapTypeEnhNetBusDropped                                      ( 6405),  -- NetBus attack dropped
        trapTypeEnhBackOrificeDropped                                 ( 6406),  -- Back Orifice attack dropped
        trapTypeEnhNetSpyDropped                                      ( 6407),  -- Net Spy attack dropped
        trapTypeEnhSub7Dropped                                        ( 6408),  -- Sub Seven attack dropped
        trapTypeEnhRipperDropped                                      ( 6409),  -- Ripper attack dropped
        trapTypeEnhStrikerDropped                                     ( 6410),  -- Striker attack dropped
        trapTypeEnhSennaSpyDropped                                    ( 6411),  -- Senna Spy attack dropped
        trapTypeEnhPriorityDropped                                    ( 6412),  -- Priority attack dropped
        trapTypeEnhIniKillerDropped                                   ( 6413),  -- Ini Killer attack dropped
        trapTypeEnhSmurfDropped                                       ( 6414),  -- Smurf Amplification attack dropped
        trapTypeEnhPortScanPossible                                   ( 6415),  -- Possible port scan detected
        trapTypeEnhPortScanProbable                                   ( 6416),  -- Probable port scan detected
        trapTypeEnhForbiddenAttDisabled                               ( 6417),  -- Forbidden E-Mail attachment disabled
        trapTypeEnhTcpFinScanDropped                                  ( 6418),  -- Probable TCP FIN scan detected
        trapTypeEnhTcpXmasScanDropped                                 ( 6419),  -- Probable TCP XMAS scan detected
        trapTypeEnhTcpNullScanDropped                                 ( 6420),  -- Probable TCP NULL scan detected
        trapTypeEnhFakeCertFound                                      ( 6421),  -- Fraudulent Microsoft certificate found; access denied
        trapTypeEnhForbiddenAttDeleted                                ( 6422),  -- Forbidden E-Mail attachment deleted
        trapTypeEnhTcpXmasTreeDropped                                 ( 6423),  -- TCP Xmas Tree dropped
        trapTypeEnhDropSrcRtPkt                                       ( 6424),  -- Source routed IP packet dropped
        trapTypeEnhDroppedMsgPartial                                  ( 6425),  -- E-Mail fragment dropped
        trapTypeEnhFtpPasvRspSpoof                                    ( 6426),  -- FTP: PASV response spoof attack dropped
        trapTypeEnhFtpPortBounceAttack                                ( 6427),  -- FTP: PORT bounce attack dropped.
        trapTypeEnhFtpPasvBounceAttack                                ( 6428),  -- FTP: PASV response bounce attack dropped.
        trapTypeEnhSpankAttackDropped                                 ( 6429),  -- Spank attack multicast packet dropped
        trapTypeEnhIDPDetectionAlert                                  ( 6430),  -- IPS Detection Alert: %s
        trapTypeEnhIDPPreventionAlert                                 ( 6431),  -- IPS Prevention Alert: %s
        trapTypeEnhPortFltDropped                                     ( 6432),  -- Application Filters Block Alert: %s
        trapTypeEnhPortFltLogged                                      ( 6433),  -- Application Filter Detection Alert: %s
        trapTypeEnhNonSPTrafficDropped                                ( 6434),  -- Drop WLAN traffic from non-SonicPoint devices
        trapTypeEnhIDPReassemblyDetectionAlert                        ( 6435),  -- IPS Detection Alert: %s
        trapTypeEnhIDPReassemblyPreventionAlert                       ( 6436),  -- IPS Prevention Alert: %s
        trapTypeEnhAntiSpywarePreventionAlert                         ( 6437),  -- Anti-Spyware Prevention Alert: %s
        trapTypeEnhAntiSpywareDetectionAlert                          ( 6438),  -- Anti-Spyware Detection Alert: %s
        trapTypeEnhSynFldWatchMode                                    ( 6439),  -- SYN Flood Mode changed by user to: Watch and report possible SYN floods
        trapTypeEnhSynFldTriggerMode                                  ( 6440),  -- SYN Flood Mode changed by user to: Watch and proxy WAN connections when under attack
        trapTypeEnhSynFldProxyMode                                    ( 6441),  -- SYN Flood Mode changed by user to: Always proxy WAN connections
        trapTypeEnhSynFldProxyTriggered                               ( 6442),  -- Possible SYN flood detected on WAN IF %s - switching to connection-proxy mode
        trapTypeEnhSynFldDetected                                     ( 6443),  -- Possible SYN Flood on IF %s
        trapTypeEnhSynFldProxyModeCanceled                            ( 6444),  -- SYN flood ceased or flooding machines blacklisted - connection proxy disabled
        trapTypeEnhSynFldBlacklistOn                                  ( 6445),  -- SYN Flood blacklisting enabled by user
        trapTypeEnhSynFldBlacklistOff                                 ( 6446),  -- SYN Flood blacklisting disabled by user
        trapTypeEnhSynFldMachineBlacklisted                           ( 6447),  -- SYN-Flooding machine %s blacklisted
        trapTypeEnhSynFldMachineUnBlacklisted                         ( 6448),  -- Machine %s removed from SYN flood blacklist
        trapTypeEnhSynFldContinues                                    ( 6449),  -- Possible SYN Flood on IF %s continues
        trapTypeEnhSynFldCeased                                       ( 6450),  -- Possible SYN Flood on IF %s has ceased
        trapTypeEnhSynBlacklistContinues                              ( 6451),  -- SYN Flood Blacklist on IF %s continues
        trapTypeEnhSynReceived                                        ( 6452),  -- TCP SYN received
        trapTypeEnhRstFldMachineBlacklisted                           ( 6453),  -- RST-Flooding machine %s blacklisted
        trapTypeEnhRstBlacklistContinues                              ( 6454),  -- RST Flood Blacklist on IF %s continues
        trapTypeEnhRstFldMachineUnBlacklisted                         ( 6455),  -- Machine %s removed from RST flood blacklist
        trapTypeEnhFinFldMachineBlacklisted                           ( 6456),  -- FIN-Flooding machine %s blacklisted
        trapTypeEnhFinBlacklistContinues                              ( 6457),  -- FIN Flood Blacklist on IF %s continues
        trapTypeEnhFinFldMachineUnBlacklisted                         ( 6458),  -- Machine %s removed from FIN flood blacklist
        trapTypeEnhRstFldDetected                                     ( 6459),  -- Possible RST Flood on IF %s
        trapTypeEnhFinFldDetected                                     ( 6460),  -- Possible FIN Flood on IF %s
        trapTypeEnhRstFldCeased                                       ( 6461),  -- Possible RST Flood on IF %s has ceased
        trapTypeEnhFinFldCeased                                       ( 6462),  -- Possible FIN Flood on IF %s has ceased
        trapTypeEnhRstFldContinues                                    ( 6463),  -- Possible RST Flood on IF %s continues
        trapTypeEnhFinFldContinues                                    ( 6464),  -- Possible FIN Flood on IF %s continues
        trapTypeEnhDNSRebindAttackDetected                            ( 6465),  -- Possible DNS rebind attack detected
        trapTypeEnhDNSRebindAttackBlocked                             ( 6466),  -- DNS rebind attack blocked

-- ========== L2TP Client ==========================================

        trapTypeEnhL2tpTunnelStarting                                 ( 6601),  -- L2TP Tunnel Negotiation Started
        trapTypeEnhL2tpSessionStarting                                ( 6602),  -- L2TP Session Negotiation Started
        trapTypeEnhL2tpMaxReTransExceed                               ( 6603),  -- L2TP Max Retransmission Exceeded
        trapTypeEnhL2tpTunnelFinished                                 ( 6604),  -- L2TP Tunnel Established
        trapTypeEnhL2tpTunnelDisconRem                                ( 6605),  -- L2TP Tunnel Disconnect from Remote
        trapTypeEnhL2tpSessionSuccess                                 ( 6606),  -- L2TP Session Established
        trapTypeEnhL2tpCallDisConnRem                                 ( 6607),  -- L2TP Session Disconnect from Remote
        trapTypeEnhL2tpPPPStarts                                      ( 6608),  -- L2TP PPP Negotiation Started
        trapTypeEnhL2tpLCPDown                                        ( 6609),  -- L2TP LCP Down
        trapTypeEnhL2tpPPPUp                                          ( 6610),  -- L2TP PPP Session Up
        trapTypeEnhL2tpNetDown                                        ( 6611),  -- L2TP PPP Down
        trapTypeEnhL2tpPPPAuthFail                                    ( 6612),  -- L2TP PPP Authentication Failed
        trapTypeEnhL2toLCPUp                                          ( 6613),  -- L2TP LCP Up
        trapTypeEnhL2tpUserDiscon                                     ( 6614),  -- L2TP Disconnect Initiated by the User
        trapTypeEnhL2tpTrafficTimeout                                 ( 6615),  -- Disconnecting L2TP Tunnel due to traffic timeout
        trapTypeEnhL2tpUserCon                                        ( 6616),  -- L2TP Connect Initiated by the User
        trapTypeEnhL2tpPPPDown                                        ( 6617),  -- L2TP PPP link down

-- ========== L2TP Server ==========================================

        trapTypeEnhLogL2TPsTunnelUp                                   ( 6801),  -- L2TP Server : L2TP Tunnel Established.
        trapTypeEnhLogL2TPsSessionUp                                  ( 6802),  -- L2TP Server : L2TP Session Established.
        trapTypeEnhLogL2TPsPPPUp                                      ( 6803),  -- L2TP Server : L2TP PPP Session Established.
        trapTypeEnhLogL2TPsRadAuthFailure                             ( 6804),  -- L2TP Server:  RADIUS/LDAP reports Authentication Failure
        trapTypeEnhLogL2TPsLocalAuthFailure                           ( 6805),  -- L2TP Server:  Local  Authentication Failure
        trapTypeEnhLogL2TPsRadIPFailure                               ( 6806),  -- L2TP Server:  RADIUS/LDAP server not assigned IP address
        trapTypeEnhLogL2TPsLocalIPFailure                             ( 6807),  -- L2TP Server:  No IP address available in the Local IP Pool
        trapTypeEnhLogL2TPsTunnelDiscRemote                           ( 6808),  -- L2TP Server:  L2TP Tunnel Disconnect from the Remote.
        trapTypeEnhLogL2TPsSessionDiscRemote                          ( 6809),  -- L2TP Server:  L2TP Session Disconnect from the Remote.
        trapTypeEnhLogL2TpsPPPTermFromRemote                          ( 6810),  -- L2TP Server:  L2TP Remote terminated the PPP session
        trapTypeEnhLogL2tpsLocalAuthSuccess                           ( 6811),  -- L2TP Server:  Local  Authentication Success.
        trapTypeEnhLogL2tpsRadAuthSuccess                             ( 6812),  -- L2TP Server:  RADIUS/LDAP Authentication Success
        trapTypeEnhLogL2tpsKeepAliveFailure                           ( 6813),  -- L2TP Server:  Keep alive Failure. Closing Tunnel
        trapTypeEnhLogL2TPsCDNFromRemote                              ( 6814),  -- L2TP Server: Call Disconnect from Remote.
        trapTypeEnhLogL2TPsStopCCNFromRemote                          ( 6815),  -- L2TP Server: Tunnel Disconnect from Remote.
        trapTypeEnhLogL2TPsDeleteTunnel                               ( 6816),  -- L2TP Server : Deleting the Tunnel
        trapTypeEnhLogL2TPsDeleteSession                              ( 6817),  -- L2TP Server : Deleting the L2TP active Session
        trapTypeEnhLogL2TPsRetransExceeded                            ( 6818),  -- "L2TP Server : Retransmission Timeout, Deleting the Tunnel"
        trapTypeEnhL2TPsNoPrivForL2TPRadius                           ( 6819),  -- L2TP Server : Access from L2TP VPN Client Privilege not enabled for Radius Users.
        trapTypeEnhL2TPsNoPrivForL2TPLocal                            ( 6820),  -- L2TP Server : User  Name authentication Failure locally.
        trapTypeEnhLogProblemAddingL2tpIpPool                         ( 6821),  -- Adding L2TP IP pool Address object Failed.

-- ========== Network ==============================================

        trapTypeEnhFragmentedPacket                                   ( 7001),  -- Fragmented packet dropped
        trapTypeEnhArpFailure                                         ( 7002),  -- ARP timeout
        trapTypeEnhLogICMPTooBig                                      ( 7003),  -- Received fragmented packet or fragmentation needed
        trapTypeEnhCantResolve                                        ( 7004),  -- Failed to resolve name
        trapTypeEnhTcpFinDropped                                      ( 7005),  -- TCP FIN packet dropped
        trapTypeEnhVpnRcvdPmtuIcmp                                    ( 7006),  -- Received a path MTU icmp message from router/gateway
        trapTypeEnhPmtuIcmp                                           ( 7007),  -- Received a path MTU icmp message from router/gateway
        trapTypeEnhNatOverwrite                                       ( 7008),  -- "NAT translated packet exceeds size limit, packet dropped"
        trapTypeEnhSylogServerUnavailable                             ( 7009),  -- Syslog Server cannot be reached
        trapTypeEnhTcpInvalidSeqDropped                               ( 7010),  -- TCP packet received with invalid SEQ number; TCP packet dropped
        trapTypeEnhTcpInvalidAckDropped                               ( 7011),  -- TCP packet received with invalid ACK number; TCP packet dropped
        trapTypeEnhTcpInvalidFlagDropped                              ( 7012),  -- TCP stateful inspection: Invalid flag; TCP packet dropped
        trapTypeEnhTcpBadHeaderDropped                                ( 7013),  -- TCP stateful inspection: Bad header; TCP packet dropped
        trapTypeEnhTcpConnectionRefused                               ( 7014),  -- TCP connection reject received; TCP connection dropped
        trapTypeEnhTcpConnectionAborted                               ( 7015),  -- TCP connection abort received; TCP connection dropped
        trapTypeEnhArpRequestSent                                     ( 7016),  -- ARP request packet sent
        trapTypeEnhArpResponseRcvd                                    ( 7017),  -- ARP response packet received
        trapTypeEnhArpRequestRcvd                                     ( 7018),  -- ARP request packet received
        trapTypeEnhArpResponseSent                                    ( 7019),  -- ARP response packet sent
        trapTypeEnhArpAddEntryForBoundMac                             ( 7020),  -- Adding Dynamic Entry for Bound MAC Address
        trapTypeEnhArpMacAddrCollision                                ( 7021),  -- MAC address collides with Static ARP Entry with Bound MAC address; packet dropped
        trapTypeEnhArpTooManyGraArp                                   ( 7022),  -- Too many gratuitous ARPs detected
        trapTypeEnhArpSpare4                                          ( 7023),  -- ARP unused/spare
        trapTypeEnhInvalidVlanId                                      ( 7024),  -- Invalid VLAN packet dropped
        trapTypeEnhIPConflict                                         ( 7025),  -- IP address conflict detected from ethernet address %s
        trapTypeEnhTcpBadHeaderLen                                    ( 7026),  -- TCP packet received with invalid header length; TCP packet dropped
        trapTypeEnhTcpNoCache                                         ( 7027),  -- TCP packet received on non-existent/closed connection; TCP packet dropped
        trapTypeEnhTcpNoSynFlag                                       ( 7028),  -- TCP packet received without mandatory SYN flag; TCP packet dropped
        trapTypeEnhTcpNoAckFlag                                       ( 7029),  -- TCP packet received without mandatory ACK flag; TCP packet dropped
        trapTypeEnhTcpClosedConnectionDrop                            ( 7030),  -- TCP packet received on a closing connection; TCP packet dropped
        trapTypeEnhTcpExistingConnectionSyn                           ( 7031),  -- TCP packet received with SYN flag on an existing connection; TCP packet dropped
        trapTypeEnhTcpBadSackOptionLen                                ( 7032),  -- TCP packet received with invalid SACK option length; TCP packet dropped
        trapTypeEnhTcpBadMssOptionLen                                 ( 7033),  -- TCP packet received with invalid MSS option length; TCP packet dropped
        trapTypeEnhTcpBadOptionLen                                    ( 7034),  -- TCP packet received with invalid option length; TCP packet dropped
        trapTypeEnhTcpBadSourcePort                                   ( 7035),  -- TCP packet received with invalid source port; TCP packet dropped
        trapTypeEnhTcpSynFloodCookieInvalid                           ( 7036),  -- TCP packet received with invalid SYN Flood cookie; TCP packet dropped
        trapTypeEnhDropIpTtlExpired                                   ( 7037),  -- Packet Dropped - IP TTL expired
        trapTypeEnhTcpOptionNotPermitted                              ( 7038),  -- TCP packet received with non-permitted option; TCP packet dropped
        trapTypeEnhTcpBadWindowScaleOptionLen                         ( 7039),  -- TCP packet received with invalid Window Scale option length; TCP packet dropped
        trapTypeEnhTcpBadWindowScaleOptionValue                       ( 7040),  -- TCP packet received with invalid Window Scale option value; TCP packet dropped

-- ========== Network Access =======================================

        trapTypeEnhWebSiteBlocked                                     ( 7201),  -- Web site access denied
        trapTypeEnhNewsgroupBlocked                                   ( 7202),  -- Newsgroup access denied
        trapTypeEnhWebSiteAccessed                                    ( 7203),  -- Web site access allowed
        trapTypeEnhNewsgroupAccessed                                  ( 7204),  -- Newsgroup access allowed
        trapTypeEnhActiveXBlocked                                     ( 7205),  -- ActiveX access denied
        trapTypeEnhJavaBlocked                                        ( 7206),  -- Java access denied
        trapTypeEnhArchiveBlocked                                     ( 7207),  -- ActiveX or Java archive access denied
        trapTypeEnhCookieRemoved                                      ( 7208),  -- Cookie removed
        trapTypeEnhTCPDropped                                         ( 7209),  -- TCP connection dropped
        trapTypeEnhUDPDropped                                         ( 7210),  -- UDP packet dropped
        trapTypeEnhICMPDropped                                        ( 7211),  -- ICMP packet dropped
        trapTypeEnhPptpDropped                                        ( 7212),  -- PPTP packet dropped
        trapTypeEnhIpsecDropped                                       ( 7213),  -- IPSec packet dropped
        trapTypeEnhUnknownProtocolDropped                             ( 7214),  -- Unknown protocol dropped
        trapTypeEnhSimultIpsecConnDropped                             ( 7215),  -- IPSec packet dropped; waiting for pending IPSec connection
        trapTypeEnhIpsecInterruptErr                                  ( 7216),  -- IPSec connection interrupt
        trapTypeEnhBroadcastDropped                                   ( 7217),  -- Broadcast packet dropped
        trapTypeEnhOutOfOrderDropped                                  ( 7218),  -- Out-of-order command packet dropped
        trapTypeEnhDuplicatePacketDropped                             ( 7219),  -- Duplicate packet dropped
        trapTypeEnhNoHostTagFound                                     ( 7220),  -- No HOST tag found in HTTP request
        trapTypeEnhProxyAccessBlocked                                 ( 7221),  -- Access to proxy server denied
        trapTypeEnhLanTCPDenied                                       ( 7222),  -- TCP connection from LAN denied
        trapTypeEnhLanUDPDenied                                       ( 7223),  -- UDP packet from LAN dropped
        trapTypeEnhLanICMPDenied                                      ( 7224),  -- ICMP packet from LAN dropped
        trapTypeEnhPktDropInClear                                     ( 7225),  -- Port configured to receive IPSec protocol ONLY; drop packet received in the clear
        trapTypeEnhMalformedIpPacket                                  ( 7226),  -- Malformed or unhandled IP packet dropped
        trapTypeEnhNoMatchICMPDropped                                 ( 7227),  -- ICMP packet dropped
        trapTypeEnhWebAccessRequestDropped                            ( 7228),  -- Web access request dropped
        trapTypeEnhWebAccessRequestRcvd                               ( 7229),  -- Web management request allowed
        trapTypeEnhFtpDataPort                                        ( 7230),  -- FTP: Data connection from non default port dropped
        trapTypeEnhTcpSynFinDropped                                   ( 7231),  -- TCP Syn/Fin packet dropped
        trapTypeEnhLanIpDenied                                        ( 7232),  -- IP type %s packet dropped
        trapTypeEnhICMPAllowed                                        ( 7233),  -- ICMP packet allowed
        trapTypeEnhLanICMPAllowed                                     ( 7234),  -- ICMP packet from LAN allowed
        trapTypeEnhDNSAllowed                                         ( 7235),  -- DNS packet allowed
        trapTypeEnhEIRGPPDropped                                      ( 7236),  -- EIGRP packet dropped
        trapTypeEnhWlanDropByDenyNetwork                              ( 7237),  -- WLAN drop traffic to deny network
        trapTypeEnhWlanPassByAllowNetwork                             ( 7238),  -- WLAN pass traffic to access allow network
        trapTypeEnhWlanMaxUsers                                       ( 7239),  -- WLAN max concurrent users reached already
        trapTypeEnhTcpHandshakeDropped                                ( 7240),  -- TCP handshake violation detected; TCP connection dropped
        trapTypeEnhAFAlert                                            ( 7241),  -- Application Firewall Alert: %s
        trapTypeEnhHttpDropped                                        ( 7242),  -- HTTP method detected; examining stream for host header
        trapTypeEnhIPHeaderChkVDropped                                ( 7243),  -- IP Header checksum error
        trapTypeEnhTCPChkVDropped                                     ( 7244),  -- TCP checksum error
        trapTypeEnhUDPChkVDropped                                     ( 7245),  -- UDP checksum error
        trapTypeEnhICMPChkVDropped                                    ( 7246),  -- ICMP checksum error
        trapTypeEnhCertblockBlacklist                                 ( 7247),  -- SSL Control: Website found in blacklist
        trapTypeEnhCertblockWhitelist                                 ( 7248),  -- SSL Control: Website found in whitelist
        trapTypeEnhCertblockSsl2                                      ( 7249),  -- SSL Control: HTTPS via SSL2
        trapTypeEnhCertblockInvalidDate                               ( 7250),  -- SSL Control: Certificate with invalid date
        trapTypeEnhCertblockSelfsigned                                ( 7251),  -- SSL Control: Self-signed certificate
        trapTypeEnhCertblockWeakCipher                                ( 7252),  -- SSL Control: Weak cipher being used
        trapTypeEnhCertblockNotTrustedCa                              ( 7253),  -- SSL Control: Untrusted CA
        trapTypeEnhCertblockNotCompleteCert                           ( 7254),  -- SSL Control: Certificate chain not complete
        trapTypeEnhCertblockDecodeFailed                              ( 7255),  -- SSL Control: Failed to decode Server Hello

-- ========== Network Traffic ======================================

        trapTypeEnhSyslogWebSiteAccessed                              ( 7401),  -- #Web site hit
        trapTypeEnhSyslogConnectionLogged                             ( 7402),  -- Connection Opened
        trapTypeEnhSyslogCloseLogged                                  ( 7403),  -- Connection Closed

-- ========== PPP Dial Up ==========================================

        trapTypeEnhDialing                                            ( 7601),  -- PPP Dial-Up: Dialing: %s
        trapTypeEnhDialNoDialtone                                     ( 7602),  -- PPP Dial-Up: No dialtone detected - check phone-line connection
        trapTypeEnhDialNoCarrier                                      ( 7603),  -- PPP Dial-Up: No link carrier detected - check phone number
        trapTypeEnhDialBusy                                           ( 7604),  -- PPP Dial-Up: Dialed number is busy
        trapTypeEnhDialNoAnswer                                       ( 7605),  -- PPP Dial-Up: Dialed number did not answer
        trapTypeEnhDialStartingPpp                                    ( 7606),  -- PPP Dial-Up: Connected at %s bps - starting PPP
        trapTypeEnhDialFailure                                        ( 7607),  -- PPP Dial-Up: Unknown dialing failure
        trapTypeEnhDialDisconnected                                   ( 7608),  -- PPP Dial-Up: Link carrier lost
        trapTypeEnhPppduNegotiationFailed                             ( 7609),  -- PPP Dial-Up: PPP negotiation failed - disconnecting
        trapTypeEnhPppduIdleExceeded                                  ( 7610),  -- PPP Dial-Up: Idle time limit exceeded - disconnecting
        trapTypeEnhPppduIpcpFailed                                    ( 7611),  -- PPP Dial-Up: Failed to get IP address
        trapTypeEnhPppduIpcpUp                                        ( 7612),  -- PPP Dial-Up: Received new IP address
        trapTypeEnhPppduPppEst                                        ( 7613),  -- PPP Dial-Up: PPP link established
        trapTypeEnhPppduLinkDown                                      ( 7614),  -- PPP Dial-Up: PPP link down
        trapTypeEnhPppduLinkClosing                                   ( 7615),  -- PPP Dial-Up: Shutting down link
        trapTypeEnhDialModemStr                                       ( 7616),  -- PPP Dial-Up: Initialization : %s
        trapTypeEnhPppduUserDisconnect                                ( 7617),  -- PPP Dial-Up: User requested disconnect
        trapTypeEnhPppduUserConnect                                   ( 7618),  -- PPP Dial-Up: User requested connect
        trapTypeEnhDialCanceled                                       ( 7619),  -- PPP Dial-Up: Connect request canceled
        trapTypeEnhPppduNeedManualAction                              ( 7620),  -- PPP Dial-Up: Manual intervention needed. Check Primary Profile or Profile details
        trapTypeEnhWfoManualProfile                                   ( 7621),  -- PPP Dial-Up: Attempting dial-up but Primary Profile has a Manual Dial Type
        trapTypeEnhPppduAutoDetect                                    ( 7622),  -- "PPP Dial-Up: Startup without Ethernet cable, will try to dial on outbound traffic"
        trapTypeEnhPppduStartBy                                       ( 7623),  -- PPP Dial-Up: Dial initiated by %s
        trapTypeEnhPppduMaxConnExceeded                               ( 7624),  -- PPP Dial-Up: Maximum connection time exceeded - disconnecting
        trapTypeEnhPppduVpnDisabled                                   ( 7625),  -- PPP Dial-Up: The profile in use disabled VPN networking.
        trapTypeEnhPppduVpnEnabled                                    ( 7626),  -- PPP Dial-Up: VPN networking restored.
        trapTypeEnhPppduNoPeerIp                                      ( 7627),  -- "PPP Dial-Up: No peer IP address from Dial-Up ISP, local and remote IPs will be the same"
        trapTypeEnhNATDisabled                                        ( 7628),  -- Network Modem Mode Enabled: turning off NAT
        trapTypeEnhNATEnabled                                         ( 7629),  -- Network Modem Mode Disabled: re-enabling NAT
        trapTypeEnhDialupDuration                                     ( 7630),  -- PPP Dial-Up: Previous session was connected for %s
        trapTypeEnhMaxFailedDials                                     ( 7631),  -- Maximum sequential failed dial attempts (10) to a single dial-up number: %s
        trapTypeEnh30MinDialDelay                                     ( 7632),  -- Regulatory requirements prohibit %s from being re-dialed for 30 minutes
        trapTypeEnhPppduDialupNotAllowed                              ( 7633),  -- PPP Dial-Up: Dialing not allowed by schedule. %s
        trapTypeEnhPppduDialupDisconnectedOutOfSked                   ( 7634),  -- PPP Dial-Up: Connection disconnected as scheduled.
        trapTypeEnhPppduInvalidDnsServer                              ( 7635),  -- PPP Dial-Up: Invalid DNS IP address returned from Dial-Up ISP; overriding using dial-up profile settings
        trapTypeEnhChatStarted                                        ( 7636),  -- Chat started
        trapTypeEnhChatCompleted                                      ( 7637),  -- Chat completed
        trapTypeEnhChatWrote                                          ( 7638),  -- Chat wrote '%s'
        trapTypeEnhChatMsg                                            ( 7639),  -- Chat %s
        trapTypeEnhChatFailed                                         ( 7640),  -- Chat failed: %s
        trapTypeEnhDialupMsgDropped                                   ( 7641),  -- Unable to send message to dial-up task
        trapTypeEnhDataUsageWatermarkReached                          ( 7642),  -- WWAN Dial-up: %s.
        trapTypeEnhDataUsageOverlimit                                 ( 7643),  -- WWAN Dial-up: data usage limit reached for the '%s' billing cycle. Disconnecting the WWAN session.
        trapTypeEnhAutoDialFailedEthernetOnlyMode                     ( 7644),  -- %s auto-dial failed: Current Connection Model is configured as Ethernet Only
        trapTypeEnhWwanStartingPpp                                    ( 7645),  -- PPP Dial-Up: Starting PPP
        trapTypeEnhDODTriggeredByApp                                  ( 7646),  -- Dial-up: Session initiated by '%s'
        trapTypeEnhDODTriggeredByPkt                                  ( 7647),  -- Dial-up: Session initiated by data packet

-- ========== PPPoE ================================================

        trapTypeEnhPppoeStarting                                      ( 7801),  -- Starting PPPoE discovery
        trapTypeEnhPppoeLinkUp                                        ( 7802),  -- PPPoE LCP Link Up
        trapTypeEnhPppoeLinkDown                                      ( 7803),  -- PPPoE LCP Link Down
        trapTypeEnhPppoeLinkFin                                       ( 7804),  -- PPPoE  terminated
        trapTypeEnhPppoeNlUp                                          ( 7805),  -- PPPoE Network Connected
        trapTypeEnhPppoeNlDown                                        ( 7806),  -- PPPoE Network Disconnected
        trapTypeEnhPppoePads                                          ( 7807),  -- PPPoE discovery process complete
        trapTypeEnhPppoeChapAuthReq                                   ( 7808),  -- PPPoE starting CHAP Authentication
        trapTypeEnhPppoePapAuthReq                                    ( 7809),  -- PPPoE starting PAP Authentication
        trapTypeEnhPppoeChapAuthFail                                  ( 7810),  -- PPPoE CHAP Authentication Failed
        trapTypeEnhPppoePapAuthFail                                   ( 7811),  -- PPPoE PAP Authentication Failed
        trapTypeEnhPppoeAuthAck                                       ( 7812),  -- PPPoE PAP Authentication success.
        trapTypeEnhPppoeAuthNak                                       ( 7813),  -- PPPoE PAP Authentication Failed. Please verify PPPoE username and password
        trapTypeEnhPppoeTrafficTimeout                                ( 7814),  -- Disconnecting PPPoE due to traffic timeout
        trapTypeEnhPppoeLcpUnacked                                    ( 7815),  -- No response from ISP Disconnecting PPPoE.
        trapTypeEnhPPPPoENotReady                                     ( 7816),  -- PPPoE enabled but not ready
        trapTypeEnhReceivedPADO                                       ( 7817),  -- Received PPPoE Active Discovery Offer
        trapTypeEnhReceivedPADS                                       ( 7818),  -- Received PPPoE Active Discovery Session_confirmation
        trapTypeEnhSendingPADR                                        ( 7819),  -- Sending PPPoE Active Discovery Request
        trapTypeEnhPppoeLCPEchoRequestSent                            ( 7820),  -- Sending LCP Echo Request
        trapTypeEnhPppoeLCPEchoRequestRcvd                            ( 7821),  -- Received LCP Echo Request
        trapTypeEnhPppoeLCPEchoReplySent                              ( 7822),  -- Sending LCP Echo Reply
        trapTypeEnhPppoeLCPEchoReplyRcvd                              ( 7823),  -- Received LCP Echo Reply

-- ========== PPTP =================================================

        trapTypeEnhPptpCtrlConnStarting                               ( 8001),  -- PPTP Control Connection Negotiation Started
        trapTypeEnhPptpSessionStarting                                ( 8002),  -- PPTP Session Negotiation Started
        trapTypeEnhPptpMaxReTransExceed                               ( 8003),  -- PPTP Max Retransmission Exceeded
        trapTypeEnhPptpCtrlConnEstablished                            ( 8004),  -- PPTP Control Connection Established
        trapTypeEnhPptpTunnelDisconRem                                ( 8005),  -- PPTP Tunnel Disconnect from Remote
        trapTypeEnhPptpSessionSuccess                                 ( 8006),  -- PPTP Session Established
        trapTypeEnhPptpCallDisConnRem                                 ( 8007),  -- PPTP Session Disconnect from Remote
        trapTypeEnhPptpPPPStarts                                      ( 8008),  -- PPTP PPP Negotiation Started
        trapTypeEnhPptpLCPDown                                        ( 8009),  -- PPTP LCP Down
        trapTypeEnhPptpPPPUp                                          ( 8010),  -- PPTP PPP Session Up
        trapTypeEnhPptpNetDown                                        ( 8011),  -- PPTP PPP Down
        trapTypeEnhPptpPPPAuthFail                                    ( 8012),  -- PPTP PPP Authentication Failed
        trapTypeEnhPptpLCPUp                                          ( 8013),  -- PPTP LCP Up
        trapTypeEnhPptpUserDiscon                                     ( 8014),  -- PPTP Disconnect Initiated by the User
        trapTypeEnhPptpTrafficTimeout                                 ( 8015),  -- Disconnecting PPTP Tunnel due to traffic timeout
        trapTypeEnhPptpUserCon                                        ( 8016),  -- PPTP Connect Initiated by the User
        trapTypeEnhPptpPPPDown                                        ( 8017),  -- PPTP PPP link down
        trapTypeEnhPptpChapAuthReq                                    ( 8018),  -- PPTP starting CHAP Authentication
        trapTypeEnhPptpPapAuthReq                                     ( 8019),  -- PPTP starting PAP Authentication
        trapTypeEnhPptpChapAuthFail                                   ( 8020),  -- PPTP CHAP Authentication Failed.  Please verify PPTP username and password
        trapTypeEnhPptpPapAuthFail                                    ( 8021),  -- PPTP PAP Authentication Failed
        trapTypeEnhPptpAuthAck                                        ( 8022),  -- PPTP PAP Authentication success.
        trapTypeEnhPptpAuthNak                                        ( 8023),  -- PPTP PAP Authentication Failed. Please verify PPTP username and password
        trapTypeEnhPptpPPPlinkUp                                      ( 8024),  -- PPTP PPP Link Up
        trapTypeEnhPptpPPPlinkDown                                    ( 8025),  -- PPTP PPP Link down
        trapTypeEnhPptpPPPlinkFinished                                ( 8026),  -- PPTP PPP Link Finished
        trapTypeEnhPptpDisconEchoRq                                   ( 8027),  -- "No response from server to Echo Requests, disconnecting PPTP Tunnel"
        trapTypeEnhPptpDisconCtrlConnRq                               ( 8028),  -- No response from PPTP server to control connection requests
        trapTypeEnhPptpDisconCallRq                                   ( 8029),  -- No response from PPTP server to call requests
        trapTypeEnhPptpDisconCtrlConnRej                              ( 8030),  -- PPTP server rejected control connection
        trapTypeEnhPptpDisconCallRej                                  ( 8031),  -- PPTP server rejected the call request
        trapTypeEnhPptpServerDown                                     ( 8032),  -- "PPTP Server is not responding, check if the server is UP and running."
        trapTypeEnhPPTPNotReady                                       ( 8033),  -- PPTP  enabled but not ready
        trapTypeEnhPPTPDecodeFailed                                   ( 8034),  -- PPTP decode failure

-- ========== RADIUS ===============================================

        trapTypeEnhUserLoginRadiusFail                                ( 8201),  -- User login denied - RADIUS authentication failure
        trapTypeEnhUserLoginRadiusTimeout                             ( 8202),  -- User login denied - RADIUS server timeout
        trapTypeEnhUserLoginRadiusError                               ( 8203),  -- User login denied - RADIUS configuration error
        trapTypeEnhUserLoginFromWrongLocation                         ( 8204),  -- User login denied - User has no privileges for login from that location
        trapTypeEnhUserLoginRadiusProblem                             ( 8205),  -- User login denied - RADIUS communication problem
        trapTypeEnhUserLoginLdapFail                                  ( 8206),  -- User login denied - LDAP authentication failure
        trapTypeEnhUserLoginLdapTimeout                               ( 8207),  -- User login denied - LDAP server timeout
        trapTypeEnhUserLoginLdapError                                 ( 8208),  -- User login denied - LDAP server down or misconfigured
        trapTypeEnhUserLoginLdapProblem                               ( 8209),  -- User login denied - LDAP communication problem
        trapTypeEnhUserLoginLdapInvalidCredentials                    ( 8210),  -- User login denied - invalid credentials on LDAP server
        trapTypeEnhUserLoginLdapInsufficientAccess                    ( 8211),  -- User login denied - insufficient access on LDAP server
        trapTypeEnhUserLoginLdapSchemaMismatch                        ( 8212),  -- User login denied - LDAP schema mismatch
        trapTypeEnhUserLoginLdapCertName                              ( 8213),  -- Allowed LDAP server certificate with wrong host name
        trapTypeEnhUserLoginLdapResolveFail                           ( 8214),  -- User login denied - LDAP server name resolution failed
        trapTypeEnhUserLoginRadiusResolveFail                         ( 8215),  -- User login denied - RADIUS server name resolution failed
        trapTypeEnhUserLoginLdapBadServerCert                         ( 8216),  -- User login denied - LDAP server certificate not valid
        trapTypeEnhUserLoginLdapTLSError                              ( 8217),  -- User login denied - TLS or local certificate problem
        trapTypeEnhUserLoginLdapDirectoryMismatch                     ( 8218),  -- User login denied - LDAP directory mismatch

-- ========== RIP ==================================================

        trapTypeEnhLanRipModeOff                                      ( 8401),  -- RIP disabled on interface %s
        trapTypeEnhLanRipModeV1                                       ( 8402),  -- RIPv1 enabled on interface %s
        trapTypeEnhLanRipModeV2                                       ( 8403),  -- RIPv2 enabled on interface %s
        trapTypeEnhLanRipModeV2C                                      ( 8404),  -- RIPv2 compatibility (broadcast) mode enabled on interface %s
        trapTypeEnhDmzRipModeOff                                      ( 8405),  -- RIP disabled on DMZ interface
        trapTypeEnhDmzRipModeV1                                       ( 8406),  -- RIPv1 enabled on DMZ interface
        trapTypeEnhDmzRipModeV2                                       ( 8407),  -- RIPv2 enabled on DMZ interface
        trapTypeEnhDmzRipModeV2C                                      ( 8408),  -- RIPv2 compatibility (broadcast) mode enabled on DMZ interface
        trapTypeEnhWanRipModeOff                                      ( 8409),  -- RIP disabled on WAN interface
        trapTypeEnhWanRipModeV1                                       ( 8410),  -- RIPv1 enabled on WAN interface
        trapTypeEnhWanRipModeV2                                       ( 8411),  -- RIPv2 enabled on WAN interface
        trapTypeEnhWanRipModeV2C                                      ( 8412),  -- RIPv2 compatibility (broadcast) mode enabled on WAN interface
        trapTypeEnhRipWanOn                                           ( 8413),  -- RIP Broadcasts for LAN Network %s are being broadcast over dialup-connection

-- ========== Security Services ====================================

        trapTypeEnhLogNewListLoaded                                   ( 8601),  -- New URL List loaded
        trapTypeEnhLogNoNewListAvailable                              ( 8602),  -- No new URL List available
        trapTypeEnhLogProblemLoadingCheckSettings                     ( 8603),  -- Problem loading the URL List; check Filter settings
        trapTypeEnhLogProblemLoadingCheckDNS                          ( 8604),  -- Problem loading the URL List; check your DNS server
        trapTypeEnhAVAccessWithoutAgent                               ( 8605),  -- Access attempt from host without Anti-Virus agent installed
        trapTypeEnhAVAgentOutOfDate                                   ( 8606),  -- Anti-Virus agent out-of-date on host
        trapTypeEnhAVReceivedAlert                                    ( 8607),  -- Received AV Alert: %s
        trapTypeEnhAVExpiredMsg                                       ( 8608),  -- Received AV Alert: Your SonicWall Network Anti-Virus subscription has expired. %s
        trapTypeEnhCflUpdateApplianceNotRegistered                    ( 8609),  -- Problem loading the URL List; Appliance not registered.
        trapTypeEnhCflUpdateSubscriptionExpired                       ( 8610),  -- Problem loading the URL List; Subscription expired.
        trapTypeEnhCflUpdateErrorTransient                            ( 8611),  -- Problem loading the URL List; Try loading it again.
        trapTypeEnhCflUpdateErrorTransientAuto                        ( 8612),  -- Problem loading the URL List; Retrying later.
        trapTypeEnhCflUpdateErrorInternal                             ( 8613),  -- Problem loading the URL List; Flash write failure.
        trapTypeEnhCflApplianceCflExpired                             ( 8614),  -- The loaded content URL List has expired.
        trapTypeEnhCflSubscriptionExpiredEmailSubject                 ( 8615),  -- Content filter subscription expired.
        trapTypeEnhCflAutoBroken                                      ( 8616),  -- "CFL auto-download disabled, time problem detected"
        trapTypeEnhAvEnforcedLicensesExceeded                         ( 8617),  -- Anti-Virus Licenses Exceeded
        trapTypeEnhAVExpirationWarningMsg                             ( 8618),  -- Received AV Alert: Your SonicWall Network Anti-Virus subscription will expire in 7 days. %s
        trapTypeEnhCFSExpirationWarningMsg                            ( 8619),  -- Received CFS Alert: Your SonicWall Content Filtering subscription will expire in 7 days.
        trapTypeEnhCFSExpirationMsg                                   ( 8620),  -- Received CFS Alert: Your SonicWall Content Filtering subscription has expired.
        trapTypeEnhMafiaExpirationWarningMsg                          ( 8621),  -- Received E-Mail Filter Alert: Your SonicWall E-Mail Filtering subscription will expire in 7 days.
        trapTypeEnhMafiaExpirationMsg                                 ( 8622),  -- Received E-Mail Filter Alert: Your SonicWall E-Mail Filtering subscription has expired.
        trapTypeEnhDeaRegInc                                          ( 8623),  -- "<b>SonicWall Registration Update Needed:</b> Restore your existing security service subscriptions by clicking <a href=""/Security_Services/enable_services.html"">here</a>."
        trapTypeEnhIDPExpiredMsg                                      ( 8624),  -- Received IPS Alert: Your SonicWall Intrusion Prevention (IDP) subscription has expired.
        trapTypeEnhGSCNotCompliant                                    ( 8625),  -- Access attempt from host out of compliance with GSC policy
        trapTypeEnhGSCOutOfDate                                       ( 8626),  -- GSC policy out-of-date on host
        trapTypeEnhGSCAccessWithoutAgent                              ( 8627),  -- Access attempt from host without GSC installed
        trapTypeEnhGetfwinfo0                                         ( 8628),  -- Failed to synchronize license information with Licensing Server. Please see http://help.mysonicwall.com/licsyncfail.html (code: %s)
        trapTypeEnhGetfwinfo1                                         ( 8629),  -- unused/spare
        trapTypeEnhGetfwinfo2                                         ( 8630),  -- unused/spare
        trapTypeEnhAntiSpywareExpiredMsg                              ( 8631),  -- Anti-Spyware Service Expired
        trapTypeEnhAVGatewayAlert                                     ( 8632),  -- Gateway Anti-Virus Alert: %s
        trapTypeEnhAVGatewayExpiredMsg                                ( 8633),  -- Gateway Anti-Virus Service expired
        trapTypeEnhSecurityServicesMessage                            ( 8634),  -- %s
        trapTypeEnhAFExpiredMsg                                       ( 8635),  -- Received AF Alert: Your SonicWall Application Firewall (AF) subscription has expired.

-- ========== VOIP =================================================

        trapTypeEnhVoipCallConnect                                    ( 8801),  -- VoIP Call Connected
        trapTypeEnhVoipCallDisconnect                                 ( 8802),  -- VoIP Call Disconnected
        trapTypeEnhVoipAdmissionReject                                ( 8803),  -- H.323/RAS Admission Reject
        trapTypeEnhVoipAdmissionConfirm                               ( 8804),  -- H.323/RAS Admission Confirm
        trapTypeEnhVoipAdmissionRequest                               ( 8805),  -- H.323/RAS Admission Request
        trapTypeEnhVoipBandwidthReject                                ( 8806),  -- H.323/RAS Bandwidth Reject
        trapTypeEnhVoipDisengageConfirm                               ( 8807),  -- H.323/RAS Disengage Confirm
        trapTypeEnhVoipGatekeeperReject                               ( 8808),  -- H.323/RAS Gatekeeper Reject
        trapTypeEnhVoipLocationConfirm                                ( 8809),  -- H.323/RAS Location Confirm
        trapTypeEnhVoipLocationReject                                 ( 8810),  -- H.323/RAS Location Reject
        trapTypeEnhVoipRegistrationReject                             ( 8811),  -- H.323/RAS Registration Reject
        trapTypeEnhVoipSetup                                          ( 8812),  -- H.323/H.225 Setup
        trapTypeEnhVoipConnect                                        ( 8813),  -- H.323/H.225 Connect
        trapTypeEnhVoipAddress                                        ( 8814),  -- H.323/H.245 Address
        trapTypeEnhVoipEndSession                                     ( 8815),  -- H.323/H.245 End Session
        trapTypeEnhVoipEndpointAdded                                  ( 8816),  -- VoIP %s Endpoint added
        trapTypeEnhVoipEndpointRemoved                                ( 8817),  -- VoIP %s Endpoint removed
        trapTypeEnhVoipEndpointDenied                                 ( 8818),  -- VoIP %s Endpoint not added - configured 'public' endpoint limit reached
        trapTypeEnhVoipUnknownMessageResponse                         ( 8819),  -- H.323/RAS Unknown Message Response
        trapTypeEnhVoipDisengageReject                                ( 8820),  -- H.323/RAS Disengage Reject
        trapTypeEnhVoipUnregistrationReject                           ( 8821),  -- H.323/RAS Unregistration Reject
        trapTypeEnhVoipSipRequest                                     ( 8822),  -- SIP Request
        trapTypeEnhVoipSipResponse                                    ( 8823),  -- SIP Response
        trapTypeEnhVoipSipRegisterExpires                             ( 8824),  -- SIP Register expiration exceeds configured Signaling inactivity time out

-- ========== VPN ==================================================

        trapTypeEnhTCPStatSYN                                         ( 9001),  -- VPN TCP SYN
        trapTypeEnhTCPStatFIN                                         ( 9002),  -- VPN TCP FIN
        trapTypeEnhTCPStatPSH                                         ( 9003),  -- VPN TCP PSH
        trapTypeEnhIPsecTunnelStatus                                  ( 9004),  -- IPSecTunnel status changed
        trapTypeEnhVpnClean                                           ( 9005),  -- VPN Cleanup: Dynamic network settings change
        trapTypeEnhVpnBadSaCount                                      ( 9006),  -- VPN policy count received exceeds the limit; %s
        trapTypeEnhVpnRuleIsMissing                                   ( 9007),  -- Packet dropped. No firewall rule associated with VPN policy.

-- ========== VPN Client ===========================================

        trapTypeEnhXauthSuccess                                       ( 9201),  -- XAUTH Succeeded with VPN client
        trapTypeEnhXauthFailure                                       ( 9202),  -- "XAUTH Failed with VPN client, Authentication failure"
        trapTypeEnhXauthRadiusTimeout                                 ( 9203),  -- "XAUTH Failed with VPN client, Cannot Contact RADIUS Server"
        trapTypeEnhClientPolicyProvisioning                           ( 9204),  -- VPN Client Policy Provisioning
        trapTypeEnhVPNClientLicenseExceeded                           ( 9205),  -- Global VPN Client License Exceeded: Connection denied.
        trapTypeEnhBlockQuickModeWithDefaultKeyId                     ( 9206),  -- Blocked Quick Mode for Client using Default KeyId
        trapTypeEnhGlobalVPNClientNotAuthorized                       ( 9207),  -- Global VPN Client connection is not allowed. Appliance is not registered.
        trapTypeEnhClientVersionNotCompatible                         ( 9208),  -- Global VPN Client version cannot enforce personal firewall. Minimum Version required is 2.1
        trapTypeEnhDuplicateEntryInRelayTable                         ( 9209),  -- IKE Responder: IP Address already exists in the DHCP relay table. Client traffic not allowed.
        trapTypeEnhInvalidClientSetup                                 ( 9210),  -- IKE Responder: %s policy does not allow static IP for Virtual Adapter.

-- ========== VPN Ike ==============================================

        trapTypeEnhLogIkeProposalOK                                   ( 9401),  -- IKE Responder: Accepting IPSec proposal (Phase 2)
        trapTypeEnhLogIpsecProposalReject                             ( 9402),  -- IKE Responder: IPSec proposal does not match (Phase 2)
        trapTypeEnhLogIkeAddIPSecSA                                   ( 9403),  -- IKE negotiation complete. Adding IPSec SA. (Phase 2)
        trapTypeEnhLogIkeStartNegotiation                             ( 9404),  -- Starting IKE negotiation
        trapTypeEnhLogIkeDeleteSADstAddr                              ( 9405),  -- Deleting IPSec SA for destination
        trapTypeEnhLogIkeDeleteSASpi                                  ( 9406),  -- Deleting IPSec SA
        trapTypeEnhVpnStrSrcDst                                       ( 9407),  -- %s
        trapTypeEnhVpnDebug                                           ( 9408),  -- VPN Log Debug
        trapTypeEnhVpnNatTravPeerBehindNat                            ( 9409),  -- NAT Discovery : Peer IPSec Security Gateway behind a NAT/NAPT Device
        trapTypeEnhVpnNatTravWeBehindNat                              ( 9410),  -- NAT Discovery : Local IPSec Security Gateway behind a NAT/NAPT Device
        trapTypeEnhVpnNatTravNoNatDevicePresent                       ( 9411),  -- NAT Discovery :  No NAT/NAPT device detected between IPSec Security gateways
        trapTypeEnhVpnNatTravPeerNotSupportNatTraversal               ( 9412),  -- NAT Discovery : Peer IPSec Security Gateway doesn't support VPN NAT Traversal
        trapTypeEnhLogIkeProposalBadMode                              ( 9413),  -- IKE Responder: Mode %d - not tunnel mode
        trapTypeEnhLogIkeProposalPhase1IdMismatch                     ( 9414),  -- IKE Responder: No matching Phase 1 ID found for proposed remote network
        trapTypeEnhLogIkeProposalBadZeroRemAddr                       ( 9415),  -- IKE Responder: Proposed remote network is 0.0.0.0 but not DHCP relay nor default route
        trapTypeEnhLogIkeProposalNoRemNetMatch                        ( 9416),  -- IKE Responder: No match for proposed remote network address
        trapTypeEnhLogIkeProposalAddrWithDefGw                        ( 9417),  -- IKE Responder: Default LAN gateway is set but peer is not proposing to use this SA as a default route
        trapTypeEnhLogIkeProposalOutsideNotNatPub                     ( 9418),  -- IKE Responder: Tunnel terminates outside firewall but proposed local network is not NAT public address
        trapTypeEnhLogIkeProposalInsideNotLanDmz                      ( 9419),  -- IKE Responder: Tunnel terminates inside firewall but proposed local network is not inside firewall
        trapTypeEnhLogIkeProposalLanAddrOnDmz                         ( 9420),  -- IKE Responder: Tunnel terminates on DMZ but proposed local network is on LAN
        trapTypeEnhLogIkeProposalDmzAddrOnLan                         ( 9421),  -- IKE Responder: Tunnel terminates on LAN but proposed local network is on DMZ
        trapTypeEnhLogIkeProposalAhPfsMismatch                        ( 9422),  -- IKE Responder: AH Perfect Forward Secrecy mismatch
        trapTypeEnhLogIkeProposalEspPfsMismatch                       ( 9423),  -- IKE Responder: ESP Perfect Forward Secrecy mismatch
        trapTypeEnhLogIkeProposalAlgKeyMismatch                       ( 9424),  -- IKE Responder: Algorithms and/or keys do not match
        trapTypeEnhLogIkeProposalBadModeForXauth                      ( 9425),  -- IKE Responder: Mode %d - not transport mode. Xauth is required but not supported by peer.
        trapTypeEnhLogIkeProposalOutsideRemNotNat                     ( 9426),  -- IKE Responder: Tunnel terminates outside firewall but proposed remote network is not NAT public address
        trapTypeEnhLogIkeBeginInitiatorPh2                            ( 9427),  -- IKE Initiator: Start Quick Mode (Phase 2).
        trapTypeEnhIkeSaLifetimeExpired                               ( 9428),  -- IKE SA lifetime expired.
        trapTypeEnhStartMMIkeNegotiation                              ( 9429),  -- IKE Initiator: Start Main Mode negotiation (Phase 1)
        trapTypeEnhReceiveQMRequest                                   ( 9430),  -- IKE Responder: Received Quick Mode Request (Phase 2)
        trapTypeEnhInitMMPhase1Complete                               ( 9431),  -- IKE Initiator: Main Mode complete (Phase 1)
        trapTypeEnhInitAMPhase1Complete                               ( 9432),  -- IKE Initiator: Aggressive Mode complete (Phase 1).
        trapTypeEnhRespMMIkeRequest                                   ( 9433),  -- IKE Responder: Received Main Mode request (Phase 1)
        trapTypeEnhRespAMIkeRequest                                   ( 9434),  -- IKE Responder: Received Aggressive Mode request (Phase 1)
        trapTypeEnhRespMMPhase1Complete                               ( 9435),  -- IKE Responder: Main Mode complete (Phase 1)
        trapTypeEnhStartAMIkeNegotiation                              ( 9436),  -- IKE Initiator: Start Aggressive Mode negotiation (Phase 1)
        trapTypeEnhLogInitiatorIkeProposalOK                          ( 9437),  -- IKE Initiator: Accepting IPSec proposal (Phase 2)
        trapTypeEnhRespAMPhase1Complete                               ( 9438),  -- IKE Responder: Aggressive Mode complete (Phase 1)
        trapTypeEnhNoProposalChosen                                   ( 9439),  -- Received notify. NO_PROPOSAL_CHOSEN
        trapTypeEnhLogIkeProposalReject                               ( 9440),  -- IKE Responder: IKE proposal does not match (Phase 1)
        trapTypeEnhLogIkeAbort                                        ( 9441),  -- IKE negotiation aborted due to timeout
        trapTypeEnhDecryptFailedWithPsk                               ( 9442),  -- Failed payload verification after decryption; possible preshared key mismatch
        trapTypeEnhPayloadValidationFailed                            ( 9443),  -- Failed payload validation
        trapTypeEnhDropDuplicatePacket                                ( 9444),  -- Received packet retransmission. Drop duplicate packet
        trapTypeEnhSADisabled                                         ( 9445),  -- SA is disabled. Check VPN SA settings
        trapTypeEnhAuthFailed                                         ( 9446),  -- Received notify: ISAKMP_AUTH_FAILED
        trapTypeEnhHashFailed                                         ( 9447),  -- Computed hash does not match hash received from peer; preshared key mismatch
        trapTypeEnhPayloadMalformed                                   ( 9448),  -- Received notify: PAYLOAD_MALFORMED
        trapTypeEnhIpsecDeleteRequest                                 ( 9449),  -- Received IPSec SA delete request
        trapTypeEnhIkeDeleteRequest                                   ( 9450),  -- Received IKE SA delete request
        trapTypeEnhInvalidCookies                                     ( 9451),  -- Received notify: INVALID_COOKIES
        trapTypeEnhResponderLifetime                                  ( 9452),  -- Received notify: RESPONDER_LIFETIME
        trapTypeEnhNotifyInvalidSpi                                   ( 9453),  -- Received notify: INVALID_SPI
        trapTypeEnhLogIkeProposalBadZeroLocAddr                       ( 9454),  -- IKE Responder: Proposed local network is 0.0.0.0 but SA has no LAN Default Gateway
        trapTypeEnhAcceptingResponderLifetime                         ( 9455),  -- IKE Initiator: Accepting peer lifetime. (Phase 1)
        trapTypeEnhLogIkeProposalAddrWithOutDefGw                     ( 9456),  -- IKE Responder: Default LAN gateway is not set but peer is proposing to use this SA as a default route
        trapTypeEnhStartIkeNegSecGateway                              ( 9457),  -- IKE Initiator: Using secondary gateway to negotiate
        trapTypeEnhIkeInitIncorrectLocalAddr                          ( 9458),  -- IKE Initiator drop: Packet dest address does not match selected local interface address
        trapTypeEnhIkeRespIncorrectLocalAddr                          ( 9459),  -- IKE Responder drop: Packet dest address does not match selected local interface address
        trapTypeEnhHdrVerifyFailed                                    ( 9460),  -- Header verification failed
        trapTypeEnhUnencryptedWhileCryptoActive                       ( 9461),  -- Received unencrypted packet in crypto active state
        trapTypeEnhReceivedOnWrongPort                                ( 9462),  -- Received ISAKMP packet destined to port %s
        trapTypeEnhIKEDetailErrLog                                    ( 9463),  -- Payload processing failed
        trapTypeEnhVpnIkeIdMismatch                                   ( 9464),  -- IKE Responder: Proposed IKE ID mismatch
        trapTypeEnhInvalidPayload                                     ( 9465),  -- Received notify: INVALID_PAYLOAD
        trapTypeEnhIkeResponderAuthAlgoMismatch                       ( 9466),  -- IKE Responder: Phase 1 Authentication Method does not match
        trapTypeEnhIkeResponderEncAlgoMismatch                        ( 9467),  -- IKE Responder: Phase 1 encryption algorithm does not match
        trapTypeEnhIkeResponderEncAlgKeyLenMismatch                   ( 9468),  -- IKE Responder: Phase 1 encryption algorithm keylength does not match
        trapTypeEnhIkeResponderHashAlgMismatch                        ( 9469),  -- IKE Responder: Phase 1 hash algorithm does not match
        trapTypeEnhAPNoUserName                                       ( 9470),  -- IKE Responder: Phase 1 XAUTH required but policy has no user name
        trapTypeEnhAPNoUserPassword                                   ( 9471),  -- IKE Responder: Phase 1 XAUTH required but policy has no user password
        trapTypeEnhIkeResponderDHGroupMismatch                        ( 9472),  -- IKE Responder: Phase 1 DH Group does not match
        trapTypeEnhIkeResponderAHAuthAlgMismatch                      ( 9473),  -- IKE Responder: AH authentication algorithm does not match
        trapTypeEnhIkeResponderESPEncAlgMismatch                      ( 9474),  -- IKE Responder: ESP encryption algorithm does not match
        trapTypeEnhIkeResponderESPAuthAlgMismatch                     ( 9475),  -- IKE Responder: ESP authentication algorithm does not match
        trapTypeEnhIkeResponderAHAuthKeyLenMismatch                   ( 9476),  -- IKE Responder: AH authentication key length does not match
        trapTypeEnhIkeResponderESPEncKeyLenMismatch                   ( 9477),  -- IKE Responder: ESP encryption key length does not match
        trapTypeEnhIkeResponderESPAuthKeyLenMismatch                  ( 9478),  -- IKE Responder: ESP authentication key length does not match
        trapTypeEnhIkeResponderAHAuthKeyRoundsMismatch                ( 9479),  -- IKE Responder: AH authentication key rounds does not match
        trapTypeEnhIkeResponderESPEncKeyRoundsMismatch                ( 9480),  -- IKE Responder: ESP encryption key rounds does not match
        trapTypeEnhIkeResponderESPAuthKeyRoundsMismatch               ( 9481),  -- IKE Responder: ESP authentication key rounds does not match
        trapTypeEnhIkeResponderIPCompAlgoMismatch                     ( 9482),  -- IKE Responder: IP Compression algorithm does not match
        trapTypeEnhIkeInitiatorRemotePartyTO                          ( 9483),  -- IKE Initiator: Remote party timeout - Retransmitting IKE request.
        trapTypeEnhIkeResponderRemotePartyTO                          ( 9484),  -- IKE Responder: Remote party timeout - Retransmitting IKE request.
        trapTypeEnhIkeResponderProtocolMismatch                       ( 9485),  -- IKE Responder: IPsec protocol mismatch
        trapTypeEnhIkeInitiatorIDMismatch                             ( 9486),  -- IKE Initiator: Proposed IKE ID mismatch
        trapTypeEnhLogIpsecDstNetworkMismatch                         ( 9487),  -- IKE Responder: Peer's local network does not match VPN policy's <b>Destination Network</b>
        trapTypeEnhLogIpsecSrcNetworkMismatch                         ( 9488),  -- IKE Responder: Peer's destination network does not match VPN policy's <b>Local Network</b>
        trapTypeEnhLogRouteOverride                                   ( 9489),  -- IKE Responder: Route table overrides VPN policy
        trapTypeEnhLogIkeInitiatorProposalReject                      ( 9490),  -- IKE Initiator: IKE proposal does not match (Phase 1)
        trapTypeEnhIkeV2InitiatorStartSaInitRequest                   ( 9491),  -- IKEv2 Initiator: Send IKE_SA_INIT request
        trapTypeEnhIkeV2ResponderRcvdSaInitRequest                    ( 9492),  -- IKEv2 Responder: Received IKE_SA_INIT request
        trapTypeEnhIkeV2InitiatorStartAuthRequest                     ( 9493),  -- IKEv2 Initiator: Send IKE_AUTH request
        trapTypeEnhIkeV2ResponderRcvdAuthRequest                      ( 9494),  -- IKEv2 Responder: Received IKE_AUTH request
        trapTypeEnhIkeV2AuthenticationSuccessful                      ( 9495),  -- IKEv2 Authentication successful
        trapTypeEnhIkeV2AcceptPhase1Proposal                          ( 9496),  -- IKEv2 Accept IKE SA Proposal
        trapTypeEnhIkeV2AcceptPhase2Proposal                          ( 9497),  -- IKEv2 Accept IPsec SA Proposal
        trapTypeEnhIkeV2InitiatorStartCreateChildSa                   ( 9498),  -- IKEv2 Initiator: Send CREATE_CHILD_SA request
        trapTypeEnhIkeV2ResponderRcvdCreateChildSa                    ( 9499),  -- IKEv2 Responder: Received CREATE_CHILD_SA request
        trapTypeEnhIkeV2SendDeleteIkeRequest                          ( 9500),  -- IKEv2 Send delete IKE SA request
        trapTypeEnhIkeV2RcvdDeleteIkeRequest                          ( 9501),  -- IKEv2 Received delete IKE SA request
        trapTypeEnhIkeV2SendDeleteIpsecRequest                        ( 9502),  -- IKEv2 Send delete IPsec SA request
        trapTypeEnhIkeV2RcvdDeleteIpsecRequest                        ( 9503),  -- IKEv2 Received delete IPsec SA request
        trapTypeEnhIkeV2TSPayloadLocalNet                             ( 9504),  -- IKEv2 Responder: Peer's destination network does not match VPN policy's <b>Local Network</b>
        trapTypeEnhIkeV2TSPayloadDestinationNet                       ( 9505),  -- IKEv2 Responder: Peer's local network does not match VPN policy's <b>Destination Network</b>
        trapTypeEnhIkeV2PayloadProcessingError                        ( 9506),  -- IKEv2 Payload processing error
        trapTypeEnhIkeV2ExtraPayloadExists                            ( 9507),  -- IKEv2 Initiator: Negotiations failed. Extra payloads present.
        trapTypeEnhIkeV2NoRequiredPayloads                            ( 9508),  -- IKEv2 Initiator: Negotiations failed. Missing required payloads.
        trapTypeEnhIkeV2InputStateInvalid                             ( 9509),  -- IKEv2 Initiator: Negotiations failed. Invalid input state.
        trapTypeEnhIkeV2OuputStateInvalid                             ( 9510),  -- IKEv2 Initiator: Negotiations failed. Invalid output state.
        trapTypeEnhIkeV2ValidatePayloadFailed                         ( 9511),  -- IKEv2 Payload validation failed.
        trapTypeEnhIkeV2UnableToFindIkeSa                             ( 9512),  -- IKEv2 Unable to find IKE SA
        trapTypeEnhIkeV2DecryptPacketFailed                           ( 9513),  -- IKEv2 Decrypt packet failed
        trapTypeEnhIkeV2OutOfMemory                                   ( 9514),  -- IKEv2 Out of memory
        trapTypeEnhIkeV2PocessMsgQFailed                              ( 9515),  -- IKEv2 Process Message queue failed
        trapTypeEnhIkeV2InvalidState                                  ( 9516),  -- IKEv2 Invalid state
        trapTypeEnhIkeV2InvalidSpiSize                                ( 9517),  -- IKEv2 Invalid SPI size
        trapTypeEnhIkeV2VpnPolicyNotFound                             ( 9518),  -- IKEv2 VPN Policy not found
        trapTypeEnhIkeV2IpsecProtocolMismatch                         ( 9519),  -- IKEv2 IPsec proposal does not match
        trapTypeEnhIkeV2IpsecAttributesNotFound                       ( 9520),  -- IKEv2 IPsec attribute not found
        trapTypeEnhIkeV2IkeAttributesNotFound                         ( 9521),  -- IKEv2 IKE attribute not found
        trapTypeEnhIkeV2NegotiationAborted                            ( 9522),  -- IKEv2 Peer is not responding. Negotiation aborted.
        trapTypeEnhIkeV2InitiatorRemotePartyTO                        ( 9523),  -- IKEv2 Initiator: Remote party timeout - Retransmitting IKEv2 request.
        trapTypeEnhIkeV2InitiatorInitSaResponse                       ( 9524),  -- IKEv2 Initiator: Received IKE_SA_INT response
        trapTypeEnhIkeV2InitiatorIkeAuthResponse                      ( 9525),  -- IKEv2 Initiator: Received IKE_AUTH response
        trapTypeEnhIkeV2InitiatorCreateChildSaResponse                ( 9526),  -- IKEv2 Initiator: Received CREATE_CHILD_SA response
        trapTypeEnhIkeV2NegotiationComplete                           ( 9527),  -- IKEv2 negotiation complete
        trapTypeEnhIkeV2SendFailed                                    ( 9528),  -- IKEv2 Function sendto() failed to transmit packet.
        trapTypeEnhIkeV2InitiatorIDMismatch                           ( 9529),  -- IKEv2 Initiator: Proposed IKE ID mismatch
        trapTypeEnhIkeV2IkeProposalReject                             ( 9530),  -- IKEv2 IKE proposal does not match
        trapTypeEnhIkeV2NotifyStatusPayload                           ( 9531),  -- IKEv2 Received notify status payload
        trapTypeEnhIkeV2NotifyErrorPayload                            ( 9532),  -- IKEv2 Received notify error payload
        trapTypeEnhIkeV2NoNatDetectedBetweenPeers                     ( 9533),  -- IKEv2 No NAT device detected between negotiating peers
        trapTypeEnhIkeV2NatDetectedBetweenPeers                       ( 9534),  -- IKEv2 NAT device detected between negotiating peers
        trapTypeEnhIkeV2ResponderSendCreateChildSaResponse            ( 9535),  -- IKEv2 Responder: Send CREATE_CHILD_SA response
        trapTypeEnhIkeV2SendDeleteIkeResponse                         ( 9536),  -- IKEv2 Send delete IKE SA response
        trapTypeEnhIkeV2SendDeleteIpsecResponse                       ( 9537),  -- IKEv2 Send delete IPsec SA response
        trapTypeEnhIkeV2RcvdDeleteIkeResponse                         ( 9538),  -- IKEv2 Received delete IKE SA response
        trapTypeEnhIkeV2RcvdDeleteIpsecResponse                       ( 9539),  -- IKEv2 Received delete IPsec SA response

-- ========== VPN IPSec ============================================

        trapTypeEnhLogOutOfMemory                                     ( 9601),  -- Diagnostic Code E
        trapTypeEnhLogIpsecDynamicHostConnect                         ( 9602),  -- Dynamic IPSec client connected
        trapTypeEnhLogIllegalSpi                                      ( 9603),  -- Illegal IPSec SPI
        trapTypeEnhLogUnknownSpi                                      ( 9604),  -- Unknown IPSec SPI
        trapTypeEnhLogIpsecAuthFailure                                ( 9605),  -- IPSec Authentication Failed
        trapTypeEnhLogIpsecDecryptFailure                             ( 9606),  -- IPSec Decryption Failed
        trapTypeEnhLogIncompatibleSA                                  ( 9607),  -- Incompatible IPSec Security Association
        trapTypeEnhLogIllegalIpsecPeer                                ( 9608),  -- IPSec packet from or to an illegal host
        trapTypeEnhReplayDetected                                     ( 9609),  -- IPSec Replay Detected
        trapTypeEnhLogIllegalPktFromIpsecPeer                         ( 9610),  -- IPSec packet from an illegal host
        trapTypeEnhIpsecAHNatMaynotWork                               ( 9611),  -- NAT device may not support IPSec AH passthrough
        trapTypeEnhIpsecSaLifetimeExpired                             ( 9612),  -- IPSec SA lifetime expired.
        trapTypeEnhInvalidId                                          ( 9613),  -- Received notify: INVALID_ID_INFO
        trapTypeEnhIpsecEspDropped                                    ( 9614),  -- IPSec (ESP) packet dropped
        trapTypeEnhIpsecAhDropped                                     ( 9615),  -- IPSec (AH) packet dropped
        trapTypeEnhSimultIpsecEspConnDropped                          ( 9616),  -- IPSec (ESP) packet dropped; waiting for pending IPSec connection
        trapTypeEnhSimultIpsecAhConnDropped                           ( 9617),  -- IPSec (AH) packet dropped; waiting for pending IPSec connection
        trapTypeEnhLogIllegalDestination                              ( 9618),  -- Packet destination not in VPN Access list

-- ========== VPN PKI ==============================================

        trapTypeEnhCrlRequest                                         ( 9801),  -- Requesting CRL from
        trapTypeEnhCrlDownloadSuccess                                 ( 9802),  -- CRL loaded from
        trapTypeEnhCrlDownloadFailed                                  ( 9803),  -- Failed to get CRL from
        trapTypeEnhCrlFailNoMem                                       ( 9804),  -- Not enough memory to hold the CRL
        trapTypeEnhCrlFailTimedOut                                    ( 9805),  -- Connection timed out
        trapTypeEnhCrlFailNoConnect                                   ( 9806),  -- Cannot connect to the CRL server
        trapTypeEnhCrlFailNoReason                                    ( 9807),  -- Unknown reason
        trapTypeEnhCrlProcFail                                        ( 9808),  -- Failed to Process CRL from
        trapTypeEnhCrlBadFormat                                       ( 9809),  -- Bad CRL format
        trapTypeEnhCrlWrongIssuer                                     ( 9810),  -- Issuer match failed
        trapTypeEnhCrlCertRevoked                                     ( 9811),  -- Certificate on Revoked list(CRL)
        trapTypeEnhNoCertificate                                      ( 9812),  -- No Certificate for
        trapTypeEnhLogPkiGeneral                                      ( 9813),  -- PKI Error:
        trapTypeEnhPkeFailure                                         ( 9814),  -- PKI Failure
        trapTypeEnhPkeOutputLen                                       ( 9815),  -- PKI Failure: Output buffer too small
        trapTypeEnhPkeAlloc                                           ( 9816),  -- PKI Failure: Cannot alloc memory
        trapTypeEnhPkeEntityCertLimit                                 ( 9817),  -- "PKI Failure: Reached the limit for local certs, cant load any more"
        trapTypeEnhPkeImportFailed                                    ( 9818),  -- PKI Failure: Import failed
        trapTypeEnhPkeBadPassword                                     ( 9819),  -- PKI Failure: Incorrect admin password
        trapTypeEnhPkeCaCertLimit                                     ( 9820),  -- PKI Failure: CA certificates store exceeded. Cannot verify this Local Certificate
        trapTypeEnhPkeBadPkcs12Import                                 ( 9821),  -- PKI Failure: Improper file format. Please select PKCS#12 (*.p12) file
        trapTypeEnhPkeNonSonicId                                      ( 9822),  -- PKI Failure: Certificate's ID does not match this SonicWall
        trapTypeEnhPkePubPrivKeyMismatch                              ( 9823),  -- PKI Failure: public-private key mismatch
        trapTypeEnhPkeDupLocalCertName                                ( 9824),  -- PKI Failure: Duplicate local certificate name
        trapTypeEnhPkeDupLocalCert                                    ( 9825),  -- PKI Failure: Duplicate local certificate
        trapTypeEnhPkeNoCa                                            ( 9826),  -- PKI Failure: No CA certificates yet loaded
        trapTypeEnhPkeDataStoreCorrupt                                ( 9827),  -- PKI Failure: Internal error
        trapTypeEnhPkeNoResource                                      ( 9828),  -- "PKI Failure: Temporary memory shortage, try again"
        trapTypeEnhPkeChainCircular                                   ( 9829),  -- PKI Failure: The certificate chain is circular
        trapTypeEnhPkeChainIncomplete                                 ( 9830),  -- PKI Failure: The certificate chain is incomplete
        trapTypeEnhPkeChainNoRoot                                     ( 9831),  -- PKI Failure: The certificate chain has no root
        trapTypeEnhPkeAfterTime                                       ( 9832),  -- PKI Failure: The certificate or a certificate in the chain has expired
        trapTypeEnhPkeBeforeTime                                      ( 9833),  -- PKI Failure: The certificate or a certificate in the chain has a validity period in the future
        trapTypeEnhPkeBadDerCert                                      ( 9834),  -- PKI Failure: The certificate or a certificate in the chain is corrupt
        trapTypeEnhPkeBadSig                                          ( 9835),  -- PKI Failure: The certificate or a certificate in the chain has a bad signature
        trapTypeEnhPkeCouldNotValidateCert                            ( 9836),  -- PKI Failure: Loaded but could not verify certificate
        trapTypeEnhPkeCouldNotValidateChain                           ( 9837),  -- PKI Failure: Loaded the certificate but could not verify it's chain
        trapTypeEnhOcspRequestMsgSent                                 ( 9838),  -- OCSP sending request.
        trapTypeEnhOcspReqestMsgSendFailed                            ( 9839),  -- OCSP send request message failed.
        trapTypeEnhOcspReceiveResponseMsg                             ( 9840),  -- OCSP received response.
        trapTypeEnhOcspReceiveResponseMsgError                        ( 9841),  -- OCSP received response error.
        trapTypeEnhOcspURLResolveOK                                   ( 9842),  -- OCSP Resolved Domain Name.
        trapTypeEnhOcspURLResolveFailed                               ( 9843),  -- OCSP Failed to Resolve Domain Name.
        trapTypeEnhOcspInternalError                                  ( 9844),  -- OCSP Internal error handling received response.
        trapTypeEnhCrlExpired                                         ( 9845),  -- CRL has expired
        trapTypeEnhFailedToFindCert                                   ( 9846),  -- Failed to find certificate
        trapTypeEnhCRLMissing                                         ( 9847),  -- CRL missing - Issuer requires CRL checking.
        trapTypeEnhCRLValidationError                                 ( 9848),  -- CRL validation failure for Root Certificate
        trapTypeEnhCRLPathValidationError                             ( 9849),  -- Cannot Validate Issuer Path

-- ========== WAN Failover =========================================

        trapTypeEnhWanModeIs                                          (10001),  -- The network connection in use is %s
        trapTypeEnhWfoProbeFailed                                     (10002),  -- Probing failure on %s
        trapTypeEnhWfoManualSecProfile                                (10003),  -- PPP Dial-Up: Attempting dial-up but Alternate Profile has a Manual Dial Type
        trapTypeEnhWfoFailback                                        (10004),  -- WLB Failback initiated by %s
        trapTypeEnhWfoProbeSuccess                                    (10005),  -- Probing succeeded on %s
        trapTypeEnhWlbOnSpill                                         (10006),  -- "WLB Spill-over started, configured threshold exceeded"
        trapTypeEnhWlbOffSpill                                        (10007),  -- WLB Spill-over stopped
        trapTypeEnhWlbFailover                                        (10008),  -- WLB Failover in progress
        trapTypeEnhWlbResourceAvailable                               (10009),  -- WLB Resource is now available
        trapTypeEnhWlbResourceFailed                                  (10010),  -- WLB Resource failed

-- ========== Wireless =============================================

        trapTypeEnhWlanFirmwareUpdated                                (10201),  -- WLAN firmware image has been updated
        trapTypeEnhPktDropByWGuest                                    (10202),  -- Packet dropped by WLAN guest check
        trapTypeEnhPktDropByVpnTraversal                              (10203),  -- Packet dropped by WLAN vpn traversal check
        trapTypeEnhWlan80211bMgmt                                     (10204),  -- 802.11b Management
        trapTypeEnhWlanRecover                                        (10205),  -- WLAN recovery
        trapTypeEnhPktDropWanRestricted                               (10206),  -- Internet Access restricted to authorized users. Dropped packet received in the clear.
        trapTypeEnhWlanModeDHCPS                                      (10207),  -- "WLAN not in AP mode, DHCP server will not provide lease to clients on WLAN"
        trapTypeEnhWpaMicFailure                                      (10208),  -- WPA MIC Failure
        trapTypeEnhWpaRadiusTmout                                     (10209),  -- WPA Radius Server Timeout
        trapTypeEnhPktDropBySslvpnEnforcement                         (10210),  -- Packet dropped by WLAN SSL-VPN enforcement check
        trapTypeEnhSslvpnEnforcement                                  (10211),  -- SSL-VPN enforcement

-- ========== SonicPoint ===========================================

        trapTypeEnhSonicPointStatus                                   (10401),  -- SonicPoint Status
        trapTypeEnhSonicPointProvision                                (10402),  -- SonicPoint Provision
        trapTypeEnhWlanVapEnabled                                     (10403),  -- Virtual Access Point is enabled
        trapTypeEnhWlanVapDisabled                                    (10404),  -- Virtual Access Point is disabled

-- ========== Multicast ============================================

        trapTypeEnhMcastIgmpV2Join                                    (10601),  -- IGMP V2 client joined multicast Group : %s
        trapTypeEnhMcastIgmpV3Join                                    (10602),  -- IGMP V3 client joined multicast Group : %s
        trapTypeEnhMcastIgmpV3Membership                              (10603),  -- IGMP V3 Membership report received from interface %s
        trapTypeEnhMcastIgmpV2Membership                              (10604),  -- IGMP V2 Membership report received from interface %s
        trapTypeEnhMcastIgmpGeneralQuery                              (10605),  -- Router IGMP General query received on interface %s
        trapTypeEnhMcastIgmpMembershipQuery                           (10606),  -- Router IGMP Membership query  received on interface %s
        trapTypeEnhMcastIgmpLeaveGroup                                (10607),  -- IGMP Leave group message Received on interface %s
        trapTypeEnhMcastIgmpWrongChecksum                             (10608),  -- "IGMP  packet dropped, wrong checksum received on interface  %s"
        trapTypeEnhMcastEtherAddressWrong                             (10609),  -- "Multicast packet dropped, wrong MAC address receieved on interface : %s"
        trapTypeEnhMcastSrcBroadcast                                  (10610),  -- "Multicast packet dropped, Invalid src IP received on interface : %s"
        trapTypeEnhMcastIgmpPacketError                               (10611),  -- "IGMP packet dropped, decoding error "
        trapTypeEnhMcastIgmpNotHandled                                (10612),  -- IGMP Packet Not handled. Packet type : %s
        trapTypeEnhMcastIgmpUnsupportedRecordType                     (10613),  -- "IGMP V3 packet dropped, unsupported Record type : %s"
        trapTypeEnhMcastIgmpUnsupportedRecordTypeNotHandled           (10614),  -- IGMP V3 reord type : %s not Handled
        trapTypeEnhMcastUdpDropped                                    (10615),  -- "Multicast UDP packet dropped, no state entry"
        trapTypeEnhMcastTcpDropped                                    (10616),  -- Multicast TCP packet dropped
        trapTypeEnhMcastIgmpHashTimeout                               (10617),  -- "IGMP state table entry time out,deleting interface : %s for multicast address : %s"
        trapTypeEnhMcastIgmpVpnTimeout                                (10618),  -- "IGMP state table entry time out,deleting VPN  SPI :%s for Multicast address : %s"
        trapTypeEnhMcastRtpStatefulFailed                             (10619),  -- "Multicast UDP packet dropped, RTP stateful failed"
        trapTypeEnhMcastRtcpStatefulFailed                            (10620),  -- "Multicast UDP packet dropped, RTCP stateful failed"
        trapTypeEnhMcastDataApplicationNotSupported                   (10621),  -- Multicast application %s not supported
        trapTypeEnhMcastAddToPolicyList                               (10622),  -- "Adding to multicast policyList , interface : %s"
        trapTypeEnhMcstDeleteFromPolicyList                           (10623),  -- "Deleting from Multicast policy list, interface : %s"
        trapTypeEnhMcastVpnAddToPolicyList                            (10624),  -- "Adding to Multicast policyList , VPN SPI : %s"
        trapTypeEnhMcastVpnDeleteFromPolicyList                       (10625),  -- "Deleting from Multicast policy list, VPN SPI : %s"
        trapTypeEnhMcastIgmpRouterDetected                            (10626),  -- IGMP querier Router detected on interface %s
        trapTypeEnhMcastIgmpRouterDetectedVpn                         (10627),  -- "IGMP querier Router detected on VPN tunnel , SPI  %S"
        trapTypeEnhMcastAddressExceeded                               (10628),  -- Exceeded Max multicast address limit

-- ========== WLAN IDS =============================================

        trapTypeEnhWlanRogueAP                                        (10801),  -- Found Rogue Access Point
        trapTypeEnhWlanSeqCheck                                       (10802),  -- WLAN sequence number out of order
        trapTypeEnhWlanAssoFlood                                      (10803),  -- Association Flood from WLAN station
        trapTypeEnhWlanPassiveRogueAP                                 (10804),  -- Found Rogue Access Point
        trapTypeEnhWlanProbeCheck                                     (10805),  -- WLAN client null probing

-- ========== Legacy Modem Debug ===================================

-- ========== Modem Debug ==========================================

-- ========== PPP ==================================================

        trapTypeEnhPppAuthOk                                          (11401),  -- PPP: Authentication successful
        trapTypeEnhPppPapAuthFailed                                   (11402),  -- PPP: PAP Authentication failed - check username / password
        trapTypeEnhPppChapAuthFailed                                  (11403),  -- PPP: CHAP authentication failed - check username / password
        trapTypeEnhPppMschapAuthFailed                                (11404),  -- PPP: MS-CHAP authentication failed - check username / password
        trapTypeEnhPppMSChapStarting                                  (11405),  -- PPP: Starting MS-CHAP authentication
        trapTypeEnhPppChapStarting                                    (11406),  -- PPP: Starting CHAP authentication
        trapTypeEnhPppPapStarting                                     (11407),  -- PPP: Starting PAP authentication
        trapTypeEnhPPPDebugMsg                                        (11408),  -- PPP message: %s

-- ========== MsAD =================================================

        trapTypeEnhMsAdAgentNotRespond                                (11601),  -- ADConnector %s response timed-out; applying caching policy

-- ========== DDNS =================================================

        trapTypeEnhDDNSAbuse                                          (11801),  -- DDNS Failure: Provider %s
        trapTypeEnhDDNSInvalid                                        (11802),  -- DDNS Failure: Provider  %s
        trapTypeEnhDDNSLoginFailure                                   (11803),  -- DDNS Failure: Provider  %s
        trapTypeEnhDDNSUpdateSuccess                                  (11804),  -- DDNS Update success for domain %s
        trapTypeEnhDDNSAbuseImminent                                  (11805),  -- DDNS Warning: Provider %s
        trapTypeEnhDDNSTakenOffLine                                   (11806),  -- DDNS association %s taken Offline locally
        trapTypeEnhDDNSAdding                                         (11807),  -- DDNS association %s  added
        trapTypeEnhDDNSAssocEnabled                                   (11808),  -- DDNS association  %s  enabled
        trapTypeEnhDDNSAssocDisabled                                  (11809),  -- DDNS association  %s  disabled
        trapTypeEnhDDNSPutOnLine                                      (11810),  -- DDNS Association %s put on line
        trapTypeEnhDDNSAllAssocDeleted                                (11811),  -- All DDNS associations have been deleted
        trapTypeEnhDDNSDeactivated                                    (11812),  -- DDNS association %s deactivated
        trapTypeEnhDDNSAssocDeleted                                   (11813),  -- DDNS association %s deleted

-- ========== RBL ==================================================

        trapTypeEnhRblOutboundConnectionDropped                       (12001),  -- Outbound connection to RBL-listed SMTP server dropped
        trapTypeEnhRblInboundConnectionDropped                        (12002),  -- Inbound connection from RBL-listed SMTP server dropped
        trapTypeEnhRblHostIdentified                                  (12003),  -- SMTP server found on RBL blacklist
        trapTypeEnhRblNoValidDnsServers                               (12004),  -- No valid DNS server specified for RBL lookups

-- ========== ARS ==================================================

        trapTypeEnhARSInfoStr                                         (12201),  -- %s
        trapTypeEnhARSWarnStr                                         (12202),  -- %s
        trapTypeEnhARSDebugStr                                        (12203),  -- %s

-- ========== IP comp ==============================================

        trapTypeEnhIpcompInterruptErr                                 (12401),  -- IPcomp connection interrupt
        trapTypeEnhIpcompDropped                                      (12402),  -- IPcomp packet dropped
        trapTypeEnhSimultIpcompConnDropped                            (12403),  -- IPcomp packet dropped; waiting for pending IPcomp connection

-- ========== CIA ==================================================

        trapTypeEnhUserLoginCIATimeout                                (12601),  -- User login denied - CIA agent timeout
        trapTypeEnhUserLoginCIACfgErr                                 (12602),  -- User login denied - CIA configuration error
        trapTypeEnhUserLoginCIAProblem                                (12603),  -- User login denied - CIA communication problem
        trapTypeEnhUserLoginCIAResolveFail                            (12604),  -- User login denied - CIA agent name resolution failed
        trapTypeEnhUserLoginCIALongUserName                           (12605),  -- CIA returned user name too long
        trapTypeEnhUserLoginCIALongDomainName                         (12606),  -- CIA returned domain name too long
        trapTypeEnhUserLoginNoUserName                                (12607),  -- Agent returned no user name

-- ========== RF Management ========================================

-- ========== Dynamic Address Objects ==============================

-- ========== Application Firewall =================================

        trapTypeEnhAppFwAlert                                         (13201),  -- Application Firewall Alert: %s

-- ========== SSL-VPN ==============================================

-- ========== SonicPoint-N =========================================

        trapTypeEnhSonicPointNStatus                                  (13601),  -- SonicPointN Status
        trapTypeEnhSonicPointNProvision                               (13602),  -- SonicPointN Provision
        trapTypeEnhSonicPointNHWFailure                               (13603),  -- SonicPointN %s unexpected reboot.

-- ========== Anti-Spam ============================================

		trapTypeEnhAntiSpamEntityOperational                          (13801),  -- %s is operational.
		trapTypeEnhrAntiSpamEntityUnreachable                         (13802),  -- %s is unavailable.
		trapTypeEnhAntiSpamEnabled                                    (13803),  -- Anti-Spam service is enabled by administrator.
		trapTypeEnhAntiSpamDisabled                                   (13804),  -- Anti-Spam service is disabled by administrator.
		trapTypeEnhAntiSpamExpirationMsg                              (13805),  -- Your SonicWall Anti-Spam Service subscription has expired.
		trapTypeEnhAntiSpamConnLimitReached                           (13806),  -- SMTP connection limit is reached. Connection is dropped.
		trapTypeEnhAntispamStartupFailure                             (13807),  -- Anti-Spam Startup Failure - %s
		trapTypeEnhAntispamTeardownFailure                            (13808),  -- Anti-Spam Teardown Failure - %s
		trapTypeEnhAntispamOutboundConnectionDropped                  (13809),  -- Outbound connection to GRID-listed SMTP server dropped
		trapTypeEnhAntispamInboundConnectionDropped                   (13810),  -- Inbound connection from GRID-listed SMTP server dropped
		trapTypeEnhAntispamHostIdentified                             (13811),  -- SMTP server found on Reject List
		trapTypeEnhAntispamNoValidDnsServers                          (13812),  -- No valid DNS server specified for GRID lookups
		trapTypeEnhAntispamEmailRcvdFromMTA                           (13813),  -- Unprocessed email received from MTA on Inbound SMTP port
		trapTypeEnhAntispamProcessedEmailRcvd                         (13814),  -- Processed Email received from Email Security Service

-- ========== Network Monitor ======================================

        trapTypeEnhNetMonPolicyUp                                     (14001),  -- Network Monitor: Policy %s status is UP
        trapTypeEnhNetMonPolicyDown                                   (14002),  -- Network Monitor: Policy %s status is DOWN
        trapTypeEnhNetMonPolicyUnknown                                (14003),  -- Network Monitor: Policy %s status is UNKNOWN
        trapTypeEnhNetMonHostUnknown                                  (14004),  -- Network Monitor: Host %s status is UNKNOWN
        trapTypeEnhNetMonHostDown                                     (14005),  -- Network Monitor: Host %s is offline
        trapTypeEnhNetMonHostUp                                       (14006),  -- Network Monitor: Host %s is online

-- ========== DHCP Server ==========================================

-- ========== FTP ==================================================

-- ========== DPI SSL ==============================================

        trapTypeEnhDPISSLConCheck                                     (14601),  -- DPI-SSL Connection: %s

-- ========== Application Control ==================================

        trapTypeEnhACDetectionAlert                                   (15001),  -- Application Control Detection Alert: %s
        trapTypeEnhACPreventionAlert                                  (15002),  -- Application Control Prevention Alert: %s

-- ========== WAN Acceleration =====================================

        trapTypeEnhWxaDeviceUp	                                   	  (16001),  -- WAN Acceleration device %s is operational
        trapTypeEnhWxaDeviceDown	                                  (16002),  -- WAN Acceleration device %s is no longer operational
        trapTypeEnhWxaDeviceUsed	                                  (16003),  -- WAN Acceleration device %s is being used
        trapTypeEnhWxaDeviceUnused	                                  (16004),  -- WAN Acceleration device %s is no longer being used
        trapTypeEnhRemoteWxaProbeStop	                              (16005),  -- Remote WAN Acceleration device stopped responding to probes
        trapTypeEnhRemoteWxaProbeStart	                              (16006),  -- Remote WAN Acceleration device started responding to probes
        trapTypeEnhWxaLicenseExpired	                              (16007),   -- Your SonicWall WAN Acceleration Service subscription has expired.

-- ========== SonicOS Performance Monitoring =====================================

        trapTypeEnhSwMonLinkUtilHigh	                              (17001),  -- physical interface utilization is greater than 80% of the maximum rated tolerance(for the interface)for more than 10 seconds.
        trapTypeEnhSwMonCpuUtilHigh	                              	  (17002),  -- CPU reaches 80% utilization for more than 10 seconds.
        trapTypeEnhSwMonSessionUtilHigh								  (17003),  -- current session count is more than 50% of the supported maximum.
        trapTypeEnhSwMonThroughputUtilHigh							  (17004),  -- current dynamic NAT translation count is more than 50% of the configured maximum.
        trapTypeEnhSwMonNATTranslationUtilHigh						  (17005),   -- total firewall throughput is greater than 50% of the maximum rated tolerance for more than 10 seconds.

-- ========== SD-WAN ===============================================

        trapTypeEnhSdwanPspPathAvailable                              (18001),  -- SD-WAN PSP: %s
        trapTypeEnhSdwanPspPathAllRemoved                             (18002),  -- SD-WAN PSP: %s
        trapTypeEnhSdwanPspPathAdd                                    (18003),  -- SD-WAN PSP: %s
        trapTypeEnhSdwanPspPathRemove                                 (18004),  -- SD-WAN PSP: %s
        trapTypeEnhSdwanProbeAdded                                    (18005),  -- Performance Probe added : %s
        trapTypeEnhSdwanProbeDeleted                                  (18006),  -- Performance Probe deleted : %s
        trapTypeEnhSdwanProbeModified                                 (18007),  -- Performance Probe modified : %s
        trapTypeEnhSdwanPcoAdded                                      (18008),  -- Performance Class Object added : %s
        trapTypeEnhSdwanPcoDeleted                                    (18009),  -- Performance Class Object deleted : %s
        trapTypeEnhSdwanPcoModified                                   (18010),  -- Performance Class Object modified : %s
        trapTypeEnhSdwanPspAdd                                        (18011),  -- SD-WAN Path Selection Profile added :  %s
        trapTypeEnhSdwanPspMod                                        (18012),  -- SD-WAN Path Selection Profile modified :  %s
        trapTypeEnhSdwanPspDel                                        (18013),  -- SD-WAN Path Selection Profile deleted :  %s
        trapTypeEnhSdwanRouteAdd                                      (18014),  -- SD-WAN Route added :  %s
        trapTypeEnhSdwanRouteMod                                      (18015),  -- SD-WAN Route modified :  %s
        trapTypeEnhSdwanRouteDel                                      (18016),  -- SD-WAN Route deleted :  %s
        trapTypeEnhSdwanGrpAdd                                        (18017),  -- SD-WAN Group added %s
        trapTypeEnhSdwanGrpMod                                        (18018),  -- SD-WAN Group modified %s
        trapTypeEnhSdwanGrpDel                                        (18019),  -- SD-WAN Group deleted %s
        trapTypeEnhSdwanGrpMemAdd                                     (18020),  -- SD-WAN Group Member added %s
        trapTypeEnhSdwanGrpMemDel                                     (18021),  -- SD-WAN Group Member deleted %s
        trapTypeEnhSdwanGrpMemMod                                     (18022)   -- SD-WAN Group Member modified %s
	}

-- ****************************  Enterprise Specific Traps Information *******************************

sonicwallFwTrapInfo OBJECT IDENTIFIER ::= {sonicwallFwTrapModule 1}


-- ******************************************************************************************
--
-- The swTrapInfoTable
--
-- This table contains information that is
-- for the basic event on the firewall.
-- ******************************************************************************************

swTrapInfoTable OBJECT IDENTIFIER ::= { sonicwallFwTrapInfo 1 }

swTrapInfoTrapType OBJECT-TYPE
        SYNTAX     FwTrapType
        MAX-ACCESS accessible-for-notify
        STATUS     current
        DESCRIPTION
            "trap type ."
    ::= { swTrapInfoTable 1 }


swTrapInfoTrapDescription OBJECT-TYPE
		SYNTAX DisplayString
        MAX-ACCESS accessible-for-notify
        STATUS     current
        DESCRIPTION
            "The description of the trap. "
    ::= { swTrapInfoTable 2 }

swTrapInfoSrcIpAddress OBJECT-TYPE
		SYNTAX IpAddress
        MAX-ACCESS accessible-for-notify
        STATUS     current
        DESCRIPTION
            "The source ip address. "
    ::= { swTrapInfoTable 3 }

swTrapInfoDstIpAddress OBJECT-TYPE
		SYNTAX IpAddress
        MAX-ACCESS accessible-for-notify
        STATUS     current
        DESCRIPTION
            "The destination ip address. "
    ::= { swTrapInfoTable 4 }

swTrapInfoSrcPort OBJECT-TYPE
		SYNTAX INTEGER
        MAX-ACCESS accessible-for-notify
        STATUS     current
        DESCRIPTION
            "The destination port. "
    ::= { swTrapInfoTable 5 }

swTrapInfoDstPort OBJECT-TYPE
		SYNTAX INTEGER
        MAX-ACCESS accessible-for-notify
        STATUS     current
        DESCRIPTION
            "The destination port. "
    ::= { swTrapInfoTable 6 }

swTrapInfoSrcMacAddress OBJECT-TYPE
		SYNTAX MacAddress
        MAX-ACCESS accessible-for-notify
        STATUS     current
        DESCRIPTION
            "The source MAC address. "
    ::= { swTrapInfoTable 7 }

swTrapInfoDstMacAddress OBJECT-TYPE
		SYNTAX MacAddress
        MAX-ACCESS accessible-for-notify
        STATUS     current
        DESCRIPTION
            "The destination MAC address. "
    ::= { swTrapInfoTable 8 }

swTrapInfoIpType OBJECT-TYPE
		SYNTAX INTEGER
        MAX-ACCESS accessible-for-notify
        STATUS     current
        DESCRIPTION
            "The ip type. "
    ::= { swTrapInfoTable 9 }

swTrapInfoPrivMsg OBJECT-TYPE
		SYNTAX DisplayString
        MAX-ACCESS accessible-for-notify
        STATUS     current
        DESCRIPTION
            "The additional message. "
    ::= { swTrapInfoTable 10 }

swTrapInfoIpAddress OBJECT-TYPE
		SYNTAX IpAddress
        MAX-ACCESS accessible-for-notify
        STATUS     current
        DESCRIPTION
            "The ip address. "
    ::= { swTrapInfoTable 11 }

swTrapInfoSaName OBJECT-TYPE
		SYNTAX DisplayString
        MAX-ACCESS accessible-for-notify
        STATUS     current
        DESCRIPTION
            "Name of the SA. "
    ::= { swTrapInfoTable 12 }

swTrapInfoFwSrlNumber OBJECT-TYPE
		SYNTAX DisplayString
        MAX-ACCESS accessible-for-notify
        STATUS     current
        DESCRIPTION
            "Serial number of the firewall this trap is coming from. "
    ::= { swTrapInfoTable 13 }

swTrapInfoSaStatus OBJECT-TYPE
		SYNTAX INTEGER {
					up (1),
					down(0)
		}
        MAX-ACCESS accessible-for-notify
        STATUS     current
        DESCRIPTION
            "The status of the IPSec Tunnel. "
    ::= { swTrapInfoTable 14 }

swTrapInfoSrcAddrBegin OBJECT-TYPE
		SYNTAX IpAddress
    	MAX-ACCESS accessible-for-notify
		STATUS current
		DESCRIPTION
			"First address of the local network behind the firewall ( LAN side)."
	::= { swTrapInfoTable 15 }

swTrapInfoSrcAddrEnd OBJECT-TYPE
		SYNTAX IpAddress
    	MAX-ACCESS accessible-for-notify
		STATUS current
		DESCRIPTION
			"Last address of the local network. ( LAN side)."
	::= { swTrapInfoTable 16 }

swTrapInfoDstAddrBegin OBJECT-TYPE
		SYNTAX IpAddress
    	MAX-ACCESS accessible-for-notify
		STATUS current
		DESCRIPTION
			"First address of the remote network ."
	::= { swTrapInfoTable 17 }

swTrapInfoDstAddrEnd OBJECT-TYPE
		SYNTAX IpAddress
    	MAX-ACCESS accessible-for-notify
		STATUS current
		DESCRIPTION
			"Last address of the remote network."
	::= { swTrapInfoTable 18 }

swTrapInfoGateway OBJECT-TYPE
		SYNTAX IpAddress
    	MAX-ACCESS accessible-for-notify
		STATUS current
		DESCRIPTION
			"Address of the tunnel end point."
	::= { swTrapInfoTable 19 }

swTrapInfoIsDHCPCentral OBJECT-TYPE
		SYNTAX INTEGER
    	MAX-ACCESS accessible-for-notify
		STATUS current
		DESCRIPTION
			"If the Tunnel is a DHCP Central"
	::= { swTrapInfoTable 20 }

swTrapInfoSrcResolvedHostName OBJECT-TYPE
		SYNTAX DisplayString
        MAX-ACCESS accessible-for-notify
        STATUS     current
        DESCRIPTION
            "Source IP address' resolved host name. "
    ::= { swTrapInfoTable 21 }

swTrapInfoDstResolvedHostName OBJECT-TYPE
		SYNTAX DisplayString
        MAX-ACCESS accessible-for-notify
        STATUS     current
        DESCRIPTION
            "Destination IP address' resolved host name. "
    ::= { swTrapInfoTable 22 }

swTrapInfoSrcInterface OBJECT-TYPE
		SYNTAX Unsigned32
        MAX-ACCESS accessible-for-notify
        STATUS     current
        DESCRIPTION
            "Source interface "
    ::= { swTrapInfoTable 23 }

swTrapInfoDstInterface OBJECT-TYPE
		SYNTAX Unsigned32
        MAX-ACCESS accessible-for-notify
        STATUS     current
        DESCRIPTION
            "Destination interface "
    ::= { swTrapInfoTable 24 }

swTrapInfoClientUserName OBJECT-TYPE
		SYNTAX DisplayString
        MAX-ACCESS accessible-for-notify
        STATUS     current
        DESCRIPTION
            "Client User Name associated with the trap "
    ::= { swTrapInfoTable 25 }

-- ******************************************************************************************
--
-- sonicwall firewall trap group
--
-- This group defines the trap which sonicwall firewall generated
-- ******************************************************************************************

sonicwallFwTrapRoot OBJECT IDENTIFIER ::= {sonicwallFwTrapModule 2}


swFwTrapAttack NOTIFICATION-TYPE
        OBJECTS {
            swTrapInfoTrapType,
            swTrapInfoTrapDescription
        }
        STATUS current
        DESCRIPTION
            "This trap indicates that the firewall have detected a attack.
             The bound objects provide more detailed information about this problem."
    ::= { sonicwallFwTrapRoot 0 1 }

swFwTrapSysError NOTIFICATION-TYPE
        OBJECTS {
            swTrapInfoTrapType,
            swTrapInfoTrapDescription
        }
        STATUS current
        DESCRIPTION
            "This trap indicates that there is a system problem with the SonicWall appliance.
             The bound objects provide more detailed information about this problem."
    ::= { sonicwallFwTrapRoot 0 2 }

swFwTrapBlkWebSite NOTIFICATION-TYPE
        OBJECTS {
            swTrapInfoTrapType,
            swTrapInfoTrapDescription
        }
        STATUS current
        DESCRIPTION
            "This trap indicates that there is a web site was blocked by the firewall.
             The bound objects provide more detailed information about this problem."
    ::= { sonicwallFwTrapRoot 0 3}

swFwTrapIpsecTunnel NOTIFICATION-TYPE
        OBJECTS {
            swTrapInfoTrapType,
            swTrapInfoTrapDescription,
            swTrapInfoSaName,
            swTrapInfoFwSrlNumber,
            swTrapInfoSaStatus,
            swTrapInfoSrcAddrBegin,
			swTrapInfoSrcAddrEnd,
            swTrapInfoDstAddrBegin,
			swTrapInfoDstAddrEnd,
			swTrapInfoGateway,
			swTrapInfoIsDHCPCentral
        }
        STATUS current
        DESCRIPTION
            "This trap indicates that there has bee a change in the IPSec tunnel status along with
             the parameters required to indentify the tunnel ."
    ::= { sonicwallFwTrapRoot 0 4}

swFwTrapWlanIDS NOTIFICATION-TYPE
        OBJECTS {
            swTrapInfoTrapType,
            swTrapInfoTrapDescription
        }
        STATUS current
        DESCRIPTION
            "This trap indicates that there is a wireless intrusion detected by the firewall.
             The bound objects provide more detailed information about this problem."
    ::= { sonicwallFwTrapRoot 0 5}

swFwTrapSysEnv NOTIFICATION-TYPE
        OBJECTS {
            swTrapInfoTrapType,
            swTrapInfoTrapDescription
        }
        STATUS current
        DESCRIPTION
            "This trap indicates that there is a system environment problem detected by the firewall.
             The bound objects provide more detailed information about this problem."
    ::= { sonicwallFwTrapRoot 0 6}

--
-- New Traps (Enhanced 4.0 and up)
--

swFwTrapEnhNone NOTIFICATION-TYPE
        OBJECTS {
            swTrapInfoTrapType,
            swTrapInfoTrapDescription
        }
        STATUS current
        DESCRIPTION
            "This trap may be disabled at this time."
    ::= { sonicwallFwTrapRoot 0 100 }

swFwTrapEnhUnused NOTIFICATION-TYPE
        OBJECTS {
            swTrapInfoTrapType,
            swTrapInfoTrapDescription
        }
        STATUS current
        DESCRIPTION
            "This trap may be disabled at this time."
    ::= { sonicwallFwTrapRoot 0 101 }

swFwTrapEnhLegacySystemMaintenance NOTIFICATION-TYPE
        OBJECTS {
            swTrapInfoTrapType,
            swTrapInfoTrapDescription
        }
        STATUS current
        DESCRIPTION
            "This is a legacy trap for system maintenance."
    ::= { sonicwallFwTrapRoot 0 102 }

swFwTrapEnhLegacySystemErrors NOTIFICATION-TYPE
        OBJECTS {
            swTrapInfoTrapType,
            swTrapInfoTrapDescription
        }
        STATUS current
        DESCRIPTION
            "Please see description for swFwTrapSysError trap."
    ::= { sonicwallFwTrapRoot 0 103 }

swFwTrapEnhLegacyBlockedWebSites NOTIFICATION-TYPE
        OBJECTS {
            swTrapInfoTrapType,
            swTrapInfoTrapDescription
        }
        STATUS current
        DESCRIPTION
            "Please see description for swFwTrapBlkWebSite trap."
    ::= { sonicwallFwTrapRoot 0 104 }

swFwTrapEnhLegacyBlockedJavaEtc NOTIFICATION-TYPE
        OBJECTS {
            swTrapInfoTrapType,
            swTrapInfoTrapDescription
        }
        STATUS current
        DESCRIPTION
            "This is a legacy trap for blocked java and other blocked application activities."
    ::= { sonicwallFwTrapRoot 0 105 }

swFwTrapEnhLegacyUserActivity NOTIFICATION-TYPE
        OBJECTS {
            swTrapInfoTrapType,
            swTrapInfoTrapDescription
        }
        STATUS current
        DESCRIPTION
            "This is a legacy trap for user activities."
    ::= { sonicwallFwTrapRoot 0 106 }

swFwTrapEnhLegacyDeniedLanIp NOTIFICATION-TYPE
        OBJECTS {
            swTrapInfoTrapType,
            swTrapInfoTrapDescription
        }
        STATUS current
        DESCRIPTION
            "This is a legacy trap for denied LAN IP activities."
    ::= { sonicwallFwTrapRoot 0 107 }

swFwTrapEnhLegacyAttacks NOTIFICATION-TYPE
        OBJECTS {
            swTrapInfoTrapType,
            swTrapInfoTrapDescription
        }
        STATUS current
        DESCRIPTION
            "Please see description for swFwTrapAttack trap."
    ::= { sonicwallFwTrapRoot 0 108 }

swFwTrapEnhLegacyDroppedTcp NOTIFICATION-TYPE
        OBJECTS {
            swTrapInfoTrapType,
            swTrapInfoTrapDescription
        }
        STATUS current
        DESCRIPTION
            "This is a legacy trap for dropped TCP event."
    ::= { sonicwallFwTrapRoot 0 109 }

swFwTrapEnhLegacyDroppedUdp NOTIFICATION-TYPE
        OBJECTS {
            swTrapInfoTrapType,
            swTrapInfoTrapDescription
        }
        STATUS current
        DESCRIPTION
            "This is a legacy trap for dropped UDP event."
    ::= { sonicwallFwTrapRoot 0 110 }

swFwTrapEnhLegacyDroppedIcmp NOTIFICATION-TYPE
        OBJECTS {
            swTrapInfoTrapType,
            swTrapInfoTrapDescription
        }
        STATUS current
        DESCRIPTION
            "This is a legacy trap for dropped ICMP event."
    ::= { sonicwallFwTrapRoot 0 111 }

swFwTrapEnhLegacyNetworkDebug NOTIFICATION-TYPE
        OBJECTS {
            swTrapInfoTrapType,
            swTrapInfoTrapDescription
        }
        STATUS current
        DESCRIPTION
            "This is a legacy trap for network debug event."
    ::= { sonicwallFwTrapRoot 0 112 }

swFwTrapEnhLegacySystemEnvironment NOTIFICATION-TYPE
        OBJECTS {
            swTrapInfoTrapType,
            swTrapInfoTrapDescription
        }
        STATUS current
        DESCRIPTION
            "Please see description for swFwTrapSysEnv trap."
    ::= { sonicwallFwTrapRoot 0 113 }

swFwTrapEnhLegacyVpnTunnelStatus NOTIFICATION-TYPE
        OBJECTS {
            swTrapInfoTrapType,
            swTrapInfoTrapDescription,
            swTrapInfoSaName,
            swTrapInfoFwSrlNumber,
            swTrapInfoSaStatus,
            swTrapInfoSrcAddrBegin,
			swTrapInfoSrcAddrEnd,
            swTrapInfoDstAddrBegin,
			swTrapInfoDstAddrEnd,
			swTrapInfoGateway,
			swTrapInfoIsDHCPCentral
        }
        STATUS current
        DESCRIPTION
            "This is a legacy trap for VPN tunnel status."
    ::= { sonicwallFwTrapRoot 0 114 }

swFwTrapEnhLegacy80211bManagement NOTIFICATION-TYPE
        OBJECTS {
            swTrapInfoTrapType,
            swTrapInfoTrapDescription
        }
        STATUS current
        DESCRIPTION
            "This is a legacy trap for 802.11 management event."
    ::= { sonicwallFwTrapRoot 0 115 }

swFwTrapEnhAuthAccess NOTIFICATION-TYPE
        OBJECTS {
            swTrapInfoTrapType,
            swTrapInfoTrapDescription
        }
        STATUS current
        DESCRIPTION
            "This trap indicates an activity from log administrator, user and guest account.
             The bound objects provide more detailed information about this problem."
    ::= { sonicwallFwTrapRoot 0 116 }

swFwTrapEnhBootp NOTIFICATION-TYPE
        OBJECTS {
            swTrapInfoTrapType,
            swTrapInfoTrapDescription
        }
        STATUS current
        DESCRIPTION
            "This trap indicates an event happening from BOOTP.
             The bound objects provide more detailed information about this problem."
    ::= { sonicwallFwTrapRoot 0 117 }

swFwTrapEnhCrypt NOTIFICATION-TYPE
        OBJECTS {
            swTrapInfoTrapType,
            swTrapInfoTrapDescription
        }
        STATUS current
        DESCRIPTION
            "This trap indicates an event from crypto algorithm and hardware testing.
             The bound objects provide more detailed information about this problem."
    ::= { sonicwallFwTrapRoot 0 118 }

swFwTrapEnhDhcpc NOTIFICATION-TYPE
        OBJECTS {
            swTrapInfoTrapType,
            swTrapInfoTrapDescription
        }
        STATUS current
        DESCRIPTION
            "This trap indicates an event from DHCP Client protocol activity.
             The bound objects provide more detailed information about this problem."
    ::= { sonicwallFwTrapRoot 0 119 }

swFwTrapEnhDhcpr NOTIFICATION-TYPE
        OBJECTS {
            swTrapInfoTrapType,
            swTrapInfoTrapDescription
        }
        STATUS current
        DESCRIPTION
            "This trap indicates an event from DHCP central and gateway protocol activity.
             The bound objects provide more detailed information about this problem."
    ::= { sonicwallFwTrapRoot 0 120 }

swFwTrapEnhFwEvent NOTIFICATION-TYPE
        OBJECTS {
            swTrapInfoTrapType,
            swTrapInfoTrapDescription
        }
        STATUS current
        DESCRIPTION
            "This trap indicates an event from internal firewall activity.
             The bound objects provide more detailed information about this problem."
    ::= { sonicwallFwTrapRoot 0 121 }

swFwTrapEnhFwHardware NOTIFICATION-TYPE
        OBJECTS {
            swTrapInfoTrapType,
            swTrapInfoTrapDescription
        }
        STATUS current
        DESCRIPTION
            "This trap indicates an event from firewall hardware error.
             The bound objects provide more detailed information about this problem."
    ::= { sonicwallFwTrapRoot 0 122 }

swFwTrapEnhFwLogging NOTIFICATION-TYPE
        OBJECTS {
            swTrapInfoTrapType,
            swTrapInfoTrapDescription
        }
        STATUS current
        DESCRIPTION
            "This trap indicates a general firewall event or error.
             The bound objects provide more detailed information about this problem."
    ::= { sonicwallFwTrapRoot 0 123 }

swFwTrapEnhFwRule NOTIFICATION-TYPE
        OBJECTS {
            swTrapInfoTrapType,
            swTrapInfoTrapDescription
        }
        STATUS current
        DESCRIPTION
            "This trap indicates an event from a firewall rule modification.
             The bound objects provide more detailed information about this problem."
    ::= { sonicwallFwTrapRoot 0 124 }

swFwTrapEnhGms NOTIFICATION-TYPE
        OBJECTS {
            swTrapInfoTrapType,
            swTrapInfoTrapDescription
        }
        STATUS current
        DESCRIPTION
            "This trap indicates a GMS status event.
             The bound objects provide more detailed information about this problem."
    ::= { sonicwallFwTrapRoot 0 125 }

swFwTrapEnhHa NOTIFICATION-TYPE
        OBJECTS {
            swTrapInfoTrapType,
            swTrapInfoTrapDescription
        }
        STATUS current
        DESCRIPTION
            "This trap indicates an event from a high availability activity.
             The bound objects provide more detailed information about this problem."
    ::= { sonicwallFwTrapRoot 0 126 }

swFwTrapEnhIntrusionDetection NOTIFICATION-TYPE
        OBJECTS {
            swTrapInfoTrapType,
            swTrapInfoTrapDescription,
            swTrapInfoSrcIpAddress,
            swTrapInfoSrcPort,
            swTrapInfoSrcInterface,
            swTrapInfoSrcResolvedHostName,
            swTrapInfoDstIpAddress,
            swTrapInfoDstPort,
            swTrapInfoDstInterface,
            swTrapInfoDstResolvedHostName,
            swTrapInfoClientUserName
        }
        STATUS current
        DESCRIPTION
            "This trap indicates an event from an intrusion prevention activity.
             The bound objects provide more detailed information about this problem."
    ::= { sonicwallFwTrapRoot 0 127 }

swFwTrapEnhL2tpClient NOTIFICATION-TYPE
        OBJECTS {
            swTrapInfoTrapType,
            swTrapInfoTrapDescription
        }
        STATUS current
        DESCRIPTION
            "This trap indicates an event from an L2TP client activity.
             The bound objects provide more detailed information about this problem."
    ::= { sonicwallFwTrapRoot 0 128 }

swFwTrapEnhL2tpServer NOTIFICATION-TYPE
        OBJECTS {
            swTrapInfoTrapType,
            swTrapInfoTrapDescription
        }
        STATUS current
        DESCRIPTION
            "This trap indicates an event from an L2TP server activity.
             The bound objects provide more detailed information about this problem."
    ::= { sonicwallFwTrapRoot 0 129 }

swFwTrapEnhNetwork NOTIFICATION-TYPE
        OBJECTS {
            swTrapInfoTrapType,
            swTrapInfoTrapDescription,
            swTrapInfoSrcIpAddress,
            swTrapInfoSrcPort,
            swTrapInfoSrcInterface,
            swTrapInfoSrcResolvedHostName,
            swTrapInfoDstIpAddress,
            swTrapInfoDstPort,
            swTrapInfoDstInterface,
            swTrapInfoDstResolvedHostName,
            swTrapInfoClientUserName
        }
        STATUS current
        DESCRIPTION
            "This trap indicates an event from ARP, fragmentation or MTU activity.
             The bound objects provide more detailed information about this problem."
    ::= { sonicwallFwTrapRoot 0 130 }

swFwTrapEnhNetworkAccess NOTIFICATION-TYPE
        OBJECTS {
            swTrapInfoTrapType,
            swTrapInfoTrapDescription,
            swTrapInfoSrcIpAddress,
            swTrapInfoSrcPort,
            swTrapInfoSrcInterface,
            swTrapInfoSrcResolvedHostName,
            swTrapInfoDstIpAddress,
            swTrapInfoDstPort,
            swTrapInfoDstInterface,
            swTrapInfoDstResolvedHostName,
            swTrapInfoClientUserName
        }
        STATUS current
        DESCRIPTION
            "This trap indicates an event from network and firewall protocol access activity.
             The bound objects provide more detailed information about this problem."
    ::= { sonicwallFwTrapRoot 0 131 }

swFwTrapEnhNetworkTraffic NOTIFICATION-TYPE
        OBJECTS {
            swTrapInfoTrapType,
            swTrapInfoTrapDescription
        }
        STATUS current
        DESCRIPTION
            "This trap indicates a network traffic reporting event.
             The bound objects provide more detailed information about this problem."
    ::= { sonicwallFwTrapRoot 0 132 }

swFwTrapEnhPppDialUp NOTIFICATION-TYPE
        OBJECTS {
            swTrapInfoTrapType,
            swTrapInfoTrapDescription
        }
        STATUS current
        DESCRIPTION
            "This trap indicates an event from a PPP dial-up activity.
             The bound objects provide more detailed information about this problem."
    ::= { sonicwallFwTrapRoot 0 133 }

swFwTrapEnhPppoe NOTIFICATION-TYPE
        OBJECTS {
            swTrapInfoTrapType,
            swTrapInfoTrapDescription
        }
        STATUS current
        DESCRIPTION
            "This trap indicates an event from a PPPoE activity.
             The bound objects provide more detailed information about this problem."
    ::= { sonicwallFwTrapRoot 0 134 }

swFwTrapEnhPptp NOTIFICATION-TYPE
        OBJECTS {
            swTrapInfoTrapType,
            swTrapInfoTrapDescription
        }
        STATUS current
        DESCRIPTION
            "This trap indicates an event from a PPTP activity.
             The bound objects provide more detailed information about this problem."
    ::= { sonicwallFwTrapRoot 0 135 }

swFwTrapEnhRadius NOTIFICATION-TYPE
        OBJECTS {
            swTrapInfoTrapType,
            swTrapInfoTrapDescription
        }
        STATUS current
        DESCRIPTION
            "This trap indicates an event from a RADIUS or LDAP server activity.
             The bound objects provide more detailed information about this problem."
    ::= { sonicwallFwTrapRoot 0 136 }

swFwTrapEnhRip NOTIFICATION-TYPE
        OBJECTS {
            swTrapInfoTrapType,
            swTrapInfoTrapDescription
        }
        STATUS current
        DESCRIPTION
            "This trap indicates an event from a RIP activity.
             The bound objects provide more detailed information about this problem."
    ::= { sonicwallFwTrapRoot 0 137 }

swFwTrapEnhSecurityServices NOTIFICATION-TYPE
        OBJECTS {
            swTrapInfoTrapType,
            swTrapInfoTrapDescription,
            swTrapInfoSrcIpAddress,
            swTrapInfoSrcPort,
            swTrapInfoSrcInterface,
            swTrapInfoSrcResolvedHostName,
            swTrapInfoDstIpAddress,
            swTrapInfoDstPort,
            swTrapInfoDstInterface,
            swTrapInfoDstResolvedHostName,
            swTrapInfoClientUserName
        }
        STATUS current
        DESCRIPTION
            "This trap indicates an event from a security services activity.
             The bound objects provide more detailed information about this problem."
    ::= { sonicwallFwTrapRoot 0 138 }

swFwTrapEnhVoip NOTIFICATION-TYPE
        OBJECTS {
            swTrapInfoTrapType,
            swTrapInfoTrapDescription
        }
        STATUS current
        DESCRIPTION
            "This trap indicates an event from a VoIP H.323/RAS, H.323/H.225, and H.323/H.245 activity.
             The bound objects provide more detailed information about this problem."
    ::= { sonicwallFwTrapRoot 0 139 }

swFwTrapEnhVpn NOTIFICATION-TYPE
        OBJECTS {
            swTrapInfoTrapType,
            swTrapInfoTrapDescription
        }
        STATUS current
        DESCRIPTION
            "This trap indicates an event from a VPN activity.
             The bound objects provide more detailed information about this problem."
    ::= { sonicwallFwTrapRoot 0 140 }

swFwTrapEnhVpnClient NOTIFICATION-TYPE
        OBJECTS {
            swTrapInfoTrapType,
            swTrapInfoTrapDescription
        }
        STATUS current
        DESCRIPTION
            "This trap indicates an event from a VPN client activity.
             The bound objects provide more detailed information about this problem."
    ::= { sonicwallFwTrapRoot 0 141 }

swFwTrapEnhVpnIke NOTIFICATION-TYPE
        OBJECTS {
            swTrapInfoTrapType,
            swTrapInfoTrapDescription
        }
        STATUS current
        DESCRIPTION
            "This trap indicates an event from a VPN IKE activity.
             The bound objects provide more detailed information about this problem."
    ::= { sonicwallFwTrapRoot 0 142 }

swFwTrapEnhVpnIpsec NOTIFICATION-TYPE
        OBJECTS {
            swTrapInfoTrapType,
            swTrapInfoTrapDescription
        }
        STATUS current
        DESCRIPTION
            "This trap indicates an event from a VPN IPSec ctivity.
             The bound objects provide more detailed information about this problem."
    ::= { sonicwallFwTrapRoot 0 143 }

swFwTrapEnhVpnPki NOTIFICATION-TYPE
        OBJECTS {
            swTrapInfoTrapType,
            swTrapInfoTrapDescription
        }
        STATUS current
        DESCRIPTION
            "This trap indicates an event from a VPN PKI activity.
             The bound objects provide more detailed information about this problem."
    ::= { sonicwallFwTrapRoot 0 144 }

swFwTrapEnhWanFailover NOTIFICATION-TYPE
        OBJECTS {
            swTrapInfoTrapType,
            swTrapInfoTrapDescription
        }
        STATUS current
        DESCRIPTION
            "This trap indicates an event from a WAN failover activity.
             The bound objects provide more detailed information about this problem."
    ::= { sonicwallFwTrapRoot 0 145 }

swFwTrapEnhWireless NOTIFICATION-TYPE
        OBJECTS {
            swTrapInfoTrapType,
            swTrapInfoTrapDescription
        }
        STATUS current
        DESCRIPTION
            "This trap indicates an event from a wireless activity.
             The bound objects provide more detailed information about this problem."
    ::= { sonicwallFwTrapRoot 0 146 }

swFwTrapEnhSonicPoint NOTIFICATION-TYPE
        OBJECTS {
            swTrapInfoTrapType,
            swTrapInfoTrapDescription
        }
        STATUS current
        DESCRIPTION
            "This trap indicates an event from a SonicPoint activity.
             The bound objects provide more detailed information about this problem."
    ::= { sonicwallFwTrapRoot 0 147 }

swFwTrapEnhMcast NOTIFICATION-TYPE
        OBJECTS {
            swTrapInfoTrapType,
            swTrapInfoTrapDescription
        }
        STATUS current
        DESCRIPTION
            "This trap indicates an event from an IGMP activity.
             The bound objects provide more detailed information about this problem."
    ::= { sonicwallFwTrapRoot 0 148 }

swFwTrapEnhWlanIds NOTIFICATION-TYPE
        OBJECTS {
            swTrapInfoTrapType,
            swTrapInfoTrapDescription
        }
        STATUS current
        DESCRIPTION
            "This trap indicates an event from a WLAN IDS activity.
             The bound objects provide more detailed information about this problem."
    ::= { sonicwallFwTrapRoot 0 149 }

swFwTrapEnhLegacyModemDebug NOTIFICATION-TYPE
        OBJECTS {
            swTrapInfoTrapType,
            swTrapInfoTrapDescription
        }
        STATUS current
        DESCRIPTION
            "This is a legacy trap for modem debug."
    ::= { sonicwallFwTrapRoot 0 150 }

swFwTrapEnhModemDebug NOTIFICATION-TYPE
        OBJECTS {
            swTrapInfoTrapType,
            swTrapInfoTrapDescription
        }
        STATUS current
        DESCRIPTION
            "This trap indicates an event from modem debug.
             The bound objects provide more detailed information about this problem."
    ::= { sonicwallFwTrapRoot 0 151 }

swFwTrapEnhPpp NOTIFICATION-TYPE
        OBJECTS {
            swTrapInfoTrapType,
            swTrapInfoTrapDescription
        }
        STATUS current
        DESCRIPTION
            "This trap indicates an event from a generic PPP activity.
             The bound objects provide more detailed information about this problem."
    ::= { sonicwallFwTrapRoot 0 152 }

swFwTrapEnhMsAd NOTIFICATION-TYPE
        OBJECTS {
            swTrapInfoTrapType,
            swTrapInfoTrapDescription
        }
        STATUS current
        DESCRIPTION
            "This trap indicates an event from an MsAD activity.
             The bound objects provide more detailed information about this problem."
    ::= { sonicwallFwTrapRoot 0 153 }

swFwTrapEnhDdns NOTIFICATION-TYPE
        OBJECTS {
            swTrapInfoTrapType,
            swTrapInfoTrapDescription
        }
        STATUS current
        DESCRIPTION
            "This trap indicates an event from Dynamic DNS.
             The bound objects provide more detailed information about this problem."
    ::= { sonicwallFwTrapRoot 0 154 }

swFwTrapEnhRbl NOTIFICATION-TYPE
        OBJECTS {
            swTrapInfoTrapType,
            swTrapInfoTrapDescription
        }
        STATUS current
        DESCRIPTION
            "This trap indicates an event from a real-time black list activity.
             The bound objects provide more detailed information about this problem."
    ::= { sonicwallFwTrapRoot 0 155 }

swFwTrapEnhARS NOTIFICATION-TYPE
        OBJECTS {
            swTrapInfoTrapType,
            swTrapInfoTrapDescription
        }
        STATUS current
        DESCRIPTION
            "This trap may be disabled at this time."
    ::= { sonicwallFwTrapRoot 0 156 }

swFwTrapEnhIpcomp NOTIFICATION-TYPE
        OBJECTS {
            swTrapInfoTrapType,
            swTrapInfoTrapDescription
        }
        STATUS current
        DESCRIPTION
            "This trap indicates an event from an IP compression activity.
             The bound objects provide more detailed information about this problem."
    ::= { sonicwallFwTrapRoot 0 157 }

swFwTrapEnhCia NOTIFICATION-TYPE
        OBJECTS {
            swTrapInfoTrapType,
            swTrapInfoTrapDescription
        }
        STATUS current
        DESCRIPTION
            "This trap indicates an event from a CIA activity.
             The bound objects provide more detailed information about this problem."
    ::= { sonicwallFwTrapRoot 0 158 }

swFwTrapEnhRFManagement NOTIFICATION-TYPE
        OBJECTS {
            swTrapInfoTrapType,
            swTrapInfoTrapDescription
        }
        STATUS current
        DESCRIPTION
            "This trap indicates an event from an RF management activity.
             The bound objects provide more detailed information about this problem."
    ::= { sonicwallFwTrapRoot 0 159 }

swFwTrapEnhDynAddrObjs NOTIFICATION-TYPE
        OBJECTS {
            swTrapInfoTrapType,
            swTrapInfoTrapDescription
        }
        STATUS current
        DESCRIPTION
            "This trap indicates an event from a dynamic address object activity.
             The bound objects provide more detailed information about this problem."
    ::= { sonicwallFwTrapRoot 0 160 }

swFwTrapEnhApplicationFirewall NOTIFICATION-TYPE
        OBJECTS {
            swTrapInfoTrapType,
            swTrapInfoTrapDescription
        }
        STATUS current
        DESCRIPTION
            "This trap indicates an application firewall event."
    ::= { sonicwallFwTrapRoot 0 161 }

swFwTrapEnhSslvpn NOTIFICATION-TYPE
        OBJECTS {
            swTrapInfoTrapType,
            swTrapInfoTrapDescription
        }
        STATUS current
        DESCRIPTION
            "This trap indicates an SSL-VPN event."
    ::= { sonicwallFwTrapRoot 0 162 }

swFwTrapEnhSonicPointN NOTIFICATION-TYPE
        OBJECTS {
            swTrapInfoTrapType,
            swTrapInfoTrapDescription
        }
        STATUS current
        DESCRIPTION
            "This trap indicates a SonicPoint-N event."
    ::= { sonicwallFwTrapRoot 0 163 }

swFwTrapEnhAntispam NOTIFICATION-TYPE
        OBJECTS {
            swTrapInfoTrapType,
            swTrapInfoTrapDescription
        }
        STATUS current
        DESCRIPTION
            "This trap indicates an Anti-Spam event."
    ::= { sonicwallFwTrapRoot 0 164 }

swFwTrapEnhNetworkMonitor NOTIFICATION-TYPE
        OBJECTS {
            swTrapInfoTrapType,
            swTrapInfoTrapDescription
        }
        STATUS current
        DESCRIPTION
            "This trap indicates a Network Monitor event."
    ::= { sonicwallFwTrapRoot 0 165 }

swFwTrapEnhDhcpServer NOTIFICATION-TYPE
        OBJECTS {
            swTrapInfoTrapType,
            swTrapInfoTrapDescription
        }
        STATUS current
        DESCRIPTION
            "This trap indicates a DHCP Server event."
    ::= { sonicwallFwTrapRoot 0 166 }

swFwTrapEnhFtp NOTIFICATION-TYPE
        OBJECTS {
            swTrapInfoTrapType,
            swTrapInfoTrapDescription
        }
        STATUS current
        DESCRIPTION
            "This trap indicates a FTP event."
    ::= { sonicwallFwTrapRoot 0 167 }

swFwTrapEnhDPISSL NOTIFICATION-TYPE
        OBJECTS {
            swTrapInfoTrapType,
            swTrapInfoTrapDescription
        }
        STATUS current
        DESCRIPTION
            "This trap indicates a DPI SSL event."
    ::= { sonicwallFwTrapRoot 0 168 }

swFwTrapEnhApplicationControl NOTIFICATION-TYPE
        OBJECTS {
            swTrapInfoTrapType,
            swTrapInfoTrapDescription
        }
        STATUS current
        DESCRIPTION
            "This trap indicates an Application Control event."
    ::= { sonicwallFwTrapRoot 0 169 }

swFwTrapEnhWanAcceleration NOTIFICATION-TYPE
        OBJECTS {
            swTrapInfoTrapType,
            swTrapInfoTrapDescription
        }
        STATUS current
        DESCRIPTION
            "This trap indicates a WAN Acceleration event."
    ::= { sonicwallFwTrapRoot 0 170 }

END
