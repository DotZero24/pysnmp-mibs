-- *****************************************************************
-- Copyright (c) 2017 SonicWall Inc.
-- All rights reserved.
-- *****************************************************************

SONICWALL-SMA-APPLIANCE-SECURITY-HISTORY-MIB	DEFINITIONS ::= BEGIN
	IMPORTS
		sonicwallSMAAppliance
			FROM SONICWALL-SMA-MIB
		InternationalDisplayString
			FROM HOST-RESOURCES-MIB
		OBJECT-TYPE, Integer32,MODULE-IDENTITY
			FROM SNMPv2-SMI;

	sonicwallSecurityHistory MODULE-IDENTITY
			LAST-UPDATED       "201804090001Z"
			ORGANIZATION       "SonicWall"
			CONTACT-INFO
				"	SonicWall Inc.

					Tel: +1 408 745 9600
					Fax: +1 408 745 9300

				E-mail: support@sonicwall.com"
             DESCRIPTION        "This SonicWall MIB provides Security History Info"
        	::= {sonicwallSMAAppliance 4}

	numOfLoginDenials	OBJECT-TYPE
		SYNTAX			Integer32
		MAX-ACCESS	read-only
		STATUS			current
		DESCRIPTION	"The number of login denials in the last 24 hours"
		::=  {  sonicwallSecurityHistory  1  }

	lastLoginDenial	OBJECT IDENTIFIER
		::=  {  sonicwallSecurityHistory  2  }

	numOfAccessDenials	OBJECT-TYPE
		SYNTAX			Integer32
		MAX-ACCESS	read-only
		STATUS			current
		DESCRIPTION	"The number of access denials in the last 24 hours"
		::=  {  sonicwallSecurityHistory  3  }

	lastAccessDenial	OBJECT IDENTIFIER
		::=  {  sonicwallSecurityHistory  4  }

	lastLoginDeniedUser	OBJECT-TYPE
		SYNTAX			InternationalDisplayString
		MAX-ACCESS	read-only
		STATUS			current
		DESCRIPTION	"The last user who was denied authentication, shown in \
		                            the format user@realm."
		::=  {  lastLoginDenial  1  }

	lastLoginDeniedTime	OBJECT-TYPE
		SYNTAX			InternationalDisplayString
		MAX-ACCESS	read-only
		STATUS			current
		DESCRIPTION	"The time when the last user was denied authentication \
		                            in a string of the form Wed Jun 30 21:49:08 1993, in \
		                            the same timezone as appliance timezone."
		::=  {  lastLoginDenial  2  }

	lastAccessDeniedUser	OBJECT-TYPE
		SYNTAX			InternationalDisplayString
		MAX-ACCESS	read-only
		STATUS			current
		DESCRIPTION		"The last user who was denied access, shown in the \
		                            format user@realm."
		::=  {  lastAccessDenial  1  }

	lastAccessDeniedResource	OBJECT-TYPE
		SYNTAX			InternationalDisplayString
		MAX-ACCESS	read-only
		STATUS			current
		DESCRIPTION	"The resource which can be URL, host:port or host to \
		                            which access was denied."
		::=  {  lastAccessDenial  2  }

	lastAccessDeniedTime	OBJECT-TYPE
		SYNTAX			InternationalDisplayString
		MAX-ACCESS	read-only
		STATUS			current
		DESCRIPTION	"The time when the last user was denied access in a \
		                            string of the form Wed Jun 30 21:49:08 1993, in the \
		                            same timezone as appliance timezone."
		::=  {  lastAccessDenial  3  }

END
