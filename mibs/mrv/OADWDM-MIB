--  =======================================================================
--  File          : oadwdm.mib
--  Description   : Private MIB for Lambda Driver (DWDM/CWDM)
--
--  By            : Ilan Weber
--  Version       : Revision:   1.27
--  Original Date : September 20, 2001
--  Last Change   : Date:   October 28, 2012
--  =======================================================================
--
--
-- Copyright (c) 2001 MRV.  All Rights Reserved.
--
-- Reproduction of this document is authorized on condition that this
-- copyright notice is included.  This MRV SNMP MIB Specification
-- embodies MRV proprietary intellectual property.  MRV
-- retains all title and ownership in the specification, including any
-- revisions.
--
-- It is MRV's intent to encourage the widespread use of this
-- specification in connection with the management of MRV's
-- products. MRV grants vendor, end-users, and other interested
-- parties a non-exclusive license to use this specification in
-- connection with the management of MRV's products.
--
-- This specification is supplied "AS IS," and MRV makes no
-- warranty, either express or implied, as to the use, operation,
-- condition, or performance of the specification.
--
-- MRV retains the right to change this MIB without notification.
--
------------------------------------------------------------------------------
-- Object IDs for existing Lambda Driver devices
------------------------------------------------------------------------------
-- LD1600:    1.3.6.1.4.1.629.100.1.1
-- LD800:     1.3.6.1.4.1.629.100.2.1
-- LD400:     1.3.6.1.4.1.629.100.3.1
-- LD1600L:   1.3.6.1.4.1.629.100.4.1
-- LD400L:    1.3.6.1.4.1.629.100.5.1
-- LD200:     1.3.6.1.4.1.629.100.6.1
-- LD200L:    1.3.6.1.4.1.629.100.7.1
-- LD100G:    1.3.6.1.4.1.629.100.8.1
------------------------------------------------------------------------------
--

OADWDM-MIB DEFINITIONS ::= BEGIN

        IMPORTS
                oaDevTrapsPortsIfAlias  FROM OA-TRAP-MESSAGES-MIB
                Counter,
                enterprises             FROM RFC1155-SMI

                OBJECT-TYPE             FROM RFC-1212
                TRAP-TYPE               FROM RFC-1215
                DisplayString           FROM RFC1213-MIB;

------------------------------------------------------------------------------
-- Object Identifier Definition
------------------------------------------------------------------------------

oaccess                 OBJECT IDENTIFIER ::= { enterprises 6926 }
oaManagement            OBJECT IDENTIFIER ::= { oaccess 1 }

oaLambdaDriver          OBJECT IDENTIFIER ::= { oaManagement 41 }

------------------------------------------------------------------------------
-- GROUPS in    OADWDM-MIB
------------------------------------------------------------------------------

oaLdDevIdentify         OBJECT IDENTIFIER ::= { oaLambdaDriver 1 }
oaLdSlotsStatTable      OBJECT IDENTIFIER ::= { oaLambdaDriver 3 }
oaLdSlotEntitysStat     OBJECT IDENTIFIER ::= { oaLambdaDriver 4 }
oaLdRedundantOptic      OBJECT IDENTIFIER ::= { oaLambdaDriver 6 }
oaLdCardPortsStat       OBJECT IDENTIFIER ::= { oaLambdaDriver 8 }
oaLdAdcCardInfo         OBJECT IDENTIFIER ::= { oaLambdaDriver 9 }
oaLdCardChannelInfo     OBJECT IDENTIFIER ::= { oaLambdaDriver 11 }
oaLdOAmplifierInfo      OBJECT IDENTIFIER ::= { oaLambdaDriver 12 }
oaLdOcmCardInfo      	OBJECT IDENTIFIER ::= { oaLambdaDriver 13 }
oaLdRoadmInfo           OBJECT IDENTIFIER ::= { oaLambdaDriver 15 }
oaLdPortsCrossConnect   OBJECT IDENTIFIER ::= { oaLambdaDriver 16 }
oaLdOpticalMonitor      OBJECT IDENTIFIER ::= { oaLambdaDriver 17 }
oaLdDcmCardAttributes   OBJECT IDENTIFIER ::= { oaLambdaDriver 18 }

oaLdDevGenConfig        OBJECT IDENTIFIER ::= { oaLdDevIdentify 10 }
oaLdDevGenIdentify      OBJECT IDENTIFIER ::= { oaLdDevIdentify 11 }

------------------------------------------------------------------------------
-- Textual conventions
------------------------------------------------------------------------------

LambdaCh ::=  INTEGER
        {
         other    (1), ch21     (2), ch23     (3), ch25     (4),
         ch27     (5), ch29     (6), ch31     (7), ch33     (8),
         ch35     (9), ch37    (10), ch39    (11), ch41    (12),
         ch43    (13), ch45    (14), ch47    (15), ch49    (16),
         ch51    (17), ch53    (18), ch55    (19), ch57    (20),
         ch59    (21),
         wl1470  (31), wl1490  (32), wl1510  (33), wl1530  (34),
         wl1550  (35), wl1570  (36), wl1590  (37), wl1610  (38),
         wl1310  (39), wl1310sm  (40), wl1330  (41), wl1350  (42),
         wl1370  (43), wl1390  (44), wl1410  (45), wl1430  (46),
         wl1450  (47),
         ch20    (48), ch22    (49), ch24    (50), ch26    (51),
         ch28    (52), ch30    (53), ch32    (54), ch34    (55),
         ch36    (56), ch38    (57), ch40    (58), ch42    (59),
         ch44    (60), ch46    (61), ch48    (62), ch50    (63),
         ch52    (64), ch54    (65), ch56    (66), ch58    (67),
         ch60    (68),
         ch205   (69), ch225   (70), ch245   (71), ch265   (72),
         ch285   (73), ch305   (74), ch325   (75), ch345   (76),
         ch365   (77), ch385   (78), ch405   (79), ch425   (80),
         ch445   (81), ch465   (82), ch485   (83), ch505   (84),
         ch525   (85), ch545   (86), ch565   (87), ch585   (88),
         ch215   (89), ch235   (90), ch255   (91), ch275   (92),
         ch295   (93), ch315   (94), ch335   (95), ch355   (96),
         ch375   (97), ch395   (98), ch415   (99), ch435   (100),
         ch455  (101), ch475  (102), ch495  (103), ch515   (104),
         ch535  (105), ch555  (106), ch575  (107), ch595   (108)
        }
--        DESCRIPTION
--        "The Lambda Wavelength channel"

RateSelect ::=  INTEGER
        {
         other (1), oc3   (2), oc12  (3), oc48  (4), giga  (5),
         fiberChannel1062 (6), fiberChannel2125 (7), fastEthernet      (8),
         escon (9), stm1 (10), stm4 (11), stm16(12), bypass(13), e3   (14),
         e32  (15), ds3  (16), oc1  (17), ds3c (18), fddi  (19), e4   (20),
         dtv  (21), fiberChannel256 (22), ds4  (23), cmi   (24), hdtv (25),
         hdtv2(26), dtv2 (27), fiberChannel531 (28), ds5   (29), oc24 (30),
         ds5x (31), hdtv3(32), eth10giga(33), oc192(34), fiberChannel4250(35),
         stm64(36), otu2(37), sonetSdh10giga(38), fiberChannel10giga(39),
         fiberChannel8giga(40), tdm10giga(41), smpte292(42), eth10M(43), otu1(44),
         sdi143(45), sdi270(46), sdi360(47), sdi540(48), hdsdi(49),
         sdi3g(50), hd1001sdi(51), otu4(52), eth100g(53)
        }
--        DESCRIPTION
--        "Transponder Rate Select.
--         Indicates the transponder rate."

RateMode ::=  INTEGER
        {
         other (1), oc3 (2), oc3c (3), oc12au3 (4), oc12c (5), oc12au4 (6),
         fiberChannel1062 (7), fiberChannel2125 (8), oc48 (9), oc48c  (10),
         eth10giga (11), oc192 (12), stm64 (13), stm16 (14),
         fiberChannel10519 (15), eth10gigaWan (16), eth10gigaDi (17),
         eth100M (18), eth1giga (19), fiberChannel4250 (20), otu0 (21),
         otu1 (22), otu2 (23), sdi143 (24), sdi270 (25), sdi360 (26),
         hdsdi (27), sdi3g (28), otu3 (29), oc768 (30), stm256 (31),
         eth40giga (32), hd1001sdi (33), sdi177 (34), sdi540 (35), dvbasi (36),
         smpte292 (37), eth10M (38), escon (39), fiberChannel256 (40),
         fiberChannel531 (41), bypass(42), gm2-eth(43), gm2-fc(44), e3(45),
         cpri614 (46), cpri1228 (47), cpri2457 (48), cpri3072 (49), cpri4915 (50),
         fiberChannel8giga (51)
        }
--        DESCRIPTION
--        "Port Rate Mode.
--         other             - Unknown rate
--         oc3               - OC3
--         oc3c              - OC3 Concatenation
--         oc12au3           - OC12 Administrative Unit Level 3
--         oc12c             - OC12 Concatenation
--         oc12au4           - OC12 Administrative Unit Level 4
--         fiberChannel1062  - 1Giga Fibre Channel
--         fiberChannel2125  - 2Giga Fibre Channel
--         oc48              - OC48
--         oc48c             - OC48 Concatenation
--         eth10giga         - 10G Ethernet
--         oc192             - OC192
--         stm64             - STM64
--         stm16             - STM16
--         fiberChannel10519 - 10G Fibre Channel
--         eth10gigaWan      - 10G Ethernet WAN
--         eth10gigaDi 	     - 10G Ethernet with Frames Discard inhibition
--         eth100M           - 100M Ethernet
--         eth1giga          - 1G Ethernet
--         fiberChannel4250  - 4G Fibre Channel
--         otu0              - OTU-0
--         otu1              - OTU-1
--         otu2              - OTU-2
--         sdi143            - SDI 143Mbps
--         sdi270            - SDI 270Mbps
--         sdi360            - SDI 360Mbps
--         hdsdi             - HD SDI 1.485Gbps
--         sdi3g             - 3G SDI 2.97Gbps
--         otu3              - OTU-3
--         oc768             - OC768
--         stm256            - STM256
--         eth40giga         - 40G Ethernet
--         hdsdi             - HD1001 SDI 1.483Gbps
--         sdi177            - SDI 177Mbps
--         sdi540            - SDI 540Mbps
--         dvbasi            - DVB-ASI 270Mbps
--         smpte292          - Rate SMPTE 292Mbps
--         eth10M            - Rate 10base-X Ethernet
--         escon             - ESCON 200Mbps"
--         fiberChannel256   - 200M Fibre Channel
--         fiberChannel531   - 0.5G Fibre Channel
--         gm2-eth           - GM2 2x1GE
--         gm2-fc            - GM2 2xFibre Channel 1G
--         e3                - E3 34.368Mbps
--         cpri614           - CPRi 614Mbps
--         cpri1228          - CPRi 1228Mbps
--         cpri2457          - CPRi 2457Mbps
--         cpri3073          - CPRi 3072Mbps
--         cpri4915          - CPRi 4915Mbps"

------------------------------------------------------------------------------
-- OADWDM-MIB - define the oaLdDevIdentify
------------------------------------------------------------------------------

oaLdNSlots   OBJECT-TYPE
        SYNTAX  INTEGER
        ACCESS  read-only
        STATUS  mandatory
        DESCRIPTION
        "The number of slots in this device"
        ::= { oaLdDevIdentify 1 }

oaLdCardHardVers  OBJECT-TYPE
        SYNTAX  INTEGER
        ACCESS  read-only
        STATUS  mandatory
        DESCRIPTION
        "Hardware version of the agent card"
        ::= { oaLdDevIdentify 2 }

oaLdSoftVers  OBJECT-TYPE
        SYNTAX  INTEGER
        ACCESS  read-only
        STATUS  mandatory
        DESCRIPTION
        "Agent software version"
        ::= { oaLdDevIdentify 3 }

oaLdCreatinDate  OBJECT-TYPE
        SYNTAX  DisplayString
        ACCESS  read-only
        STATUS  mandatory
        DESCRIPTION
        "Agent software creation date and time"
        ::= { oaLdDevIdentify 4 }

oaLdDeviceType  OBJECT-TYPE
        SYNTAX  INTEGER
        {
         other       (1),
         ld800       (2),
         ld1600      (3),
         ld400       (4),
         ld800P      (5),
         ld1600L     (6),
         ld400L      (7),
         ld400P      (8),
         ld1600P     (9),
         ld200       (10),
         ld200L      (11),
         ld400i      (12),
         ld100G      (13),
         ld400iL     (14)
        }
        ACCESS  read-only
        STATUS  mandatory
        DESCRIPTION
        "Device type"
        ::= { oaLdDevIdentify 5 }

oaLdCardFpgaVers  OBJECT-TYPE
        SYNTAX  INTEGER
        ACCESS  read-only
        STATUS  mandatory
        DESCRIPTION
        "FPGA version of the agent card"
        ::= { oaLdDevIdentify 6 }

oaLdCardBackplaneVers  OBJECT-TYPE
        SYNTAX  INTEGER
        ACCESS  read-only
        STATUS  mandatory
        DESCRIPTION
        "Chassis backplane version.
         Value = -1 says, this object is not supported."
        ::= { oaLdDevIdentify 7 }

oaLdTrapsVer  OBJECT-TYPE
        SYNTAX  INTEGER
        ACCESS  read-write
        STATUS  mandatory
        DESCRIPTION
        "Traps format version.
         If this object is not suppoted or its value is 1,
         the traps version is the origin one,
         traps 15,17,20,23,25,27,28 and 29 are sent.
         If this object equals 2, then for each reason there is
         a 'normal' trap and an 'alarm' trap.
         If this object equals 3, then for each trap, connected to lambda interface,
         the interface descriptor is added."
        ::= { oaLdDevIdentify 8 }

oaLdCpuCardSerialNumber   OBJECT-TYPE
        SYNTAX  DisplayString (SIZE(10))
        ACCESS  read-only
        STATUS  mandatory
        DESCRIPTION
        "The CPU Card's Serial Number (10 digits)."
        ::= { oaLdDevIdentify 9 }

------------------------------------------------------------------------------
-- OADWDM-MIB - define the oaLdDevGenIdentify
------------------------------------------------------------------------------

oaLdCardBackplaneSN   OBJECT-TYPE
        SYNTAX  DisplayString (SIZE(10))
        ACCESS  read-only
        STATUS  mandatory
        DESCRIPTION
        "Chassis backplane's Serial Number (10 digits)."
        ::= { oaLdDevGenIdentify 1 }

oaLdSoftVersString  OBJECT-TYPE
        SYNTAX  DisplayString
        ACCESS  read-only
        STATUS  mandatory
        DESCRIPTION
        "Agent software version in string presentation"
        ::= { oaLdDevGenIdentify 2 }

oaLdCardBackplanePN   OBJECT-TYPE
        SYNTAX  DisplayString (SIZE (0..15))
        ACCESS  read-only
        STATUS  mandatory
        DESCRIPTION
        "Chassis backplane's Part Number (maximum 15 digits)."
        ::= { oaLdDevGenIdentify 3 }

oaLdCardIftableExtMode OBJECT-TYPE
        SYNTAX  INTEGER
        {
         other   (1),
         enable  (2),
         disable (3)
        }
        ACCESS  read-write
        STATUS  mandatory
        DESCRIPTION
        "Interface fTable extention mode."
        ::= { oaLdDevGenIdentify 4 }

---oaLdPowerBalancingizationMode OBJECT-TYPE
---        SYNTAX  INTEGER
---        {
---         other     (1),
---         manual    (2),
---         automatic (3)
---        }
---        ACCESS  read-write
---        STATUS  mandatory
---        DESCRIPTION
---        "Device power balancing mode."
---        ::= { oaLdDevGenIdentify 5 }

------------------------------------------------------------------------------
-- -OADWDM-MIB - define objects in the Device's Power Supplies Group
------------------------------------------------------------------------------

oaLdDevPS       OBJECT IDENTIFIER ::= { oaLdDevGenConfig 1 }

oaLdDevPSNumber OBJECT-TYPE
        SYNTAX  INTEGER
        ACCESS  read-only
        STATUS  mandatory
        DESCRIPTION
        "The number of Power Supplies in the corresponding Device.
         Value = 0 says, that Power Supply Table is not supported."
        ::= { oaLdDevPS 1 }

oaLdDevPSTable  OBJECT-TYPE
        SYNTAX  SEQUENCE OF OaLdDevPSEntry
        ACCESS  not-accessible
        STATUS  mandatory
        DESCRIPTION
        "This table shows all the Power Supplies modules,
         existing in the corresponding Device."
        ::= { oaLdDevPS 2 }

oaLdDevPSEntry  OBJECT-TYPE
        SYNTAX  OaLdDevPSEntry
        ACCESS  not-accessible
        STATUS  mandatory
        DESCRIPTION
        "The entries of the table."
        INDEX { oaLdDevPSIndex }
        ::= { oaLdDevPSTable 1 }

OaLdDevPSEntry ::= SEQUENCE
        {
         oaLdDevPSIndex         INTEGER,
         oaLdDevPSOperStatus    INTEGER,
         oaLdDevPSPartNumber    DisplayString,
         oaLdDevPSSerialNumber  DisplayString,
         oaLdDevPSHwRev         INTEGER
        }

oaLdDevPSIndex  OBJECT-TYPE
        SYNTAX  INTEGER
        ACCESS  read-only
        STATUS  mandatory
        DESCRIPTION
        "The index of the table,
         (MAX Value is equal to oaLdDevPSNumber)."
        ::= { oaLdDevPSEntry 1 }

oaLdDevPSOperStatus OBJECT-TYPE
        SYNTAX  INTEGER
        {
         none       (1),
         active     (2),
         notActive  (3)
        }
        ACCESS  read-only
        STATUS  mandatory
        DESCRIPTION
        "The Oper status of the Power Supply."
        ::= { oaLdDevPSEntry 5 }

oaLdDevPSPartNumber   OBJECT-TYPE
        SYNTAX  DisplayString (SIZE (0..15))
        ACCESS  read-only
        STATUS  mandatory
        DESCRIPTION
        "The Part Number of the Power Supply(maximum 15 symbols)."
        ::= { oaLdDevPSEntry 6 }

oaLdDevPSSerialNumber OBJECT-TYPE
        SYNTAX  DisplayString (SIZE(10))
        ACCESS  read-only
        STATUS  mandatory
        DESCRIPTION
        "The Serial Number of the Power Supply(10 digits)."
        ::= { oaLdDevPSEntry 7 }

oaLdDevPSHwRev OBJECT-TYPE
        SYNTAX  INTEGER
        ACCESS  read-only
        STATUS  mandatory
        DESCRIPTION
        "The Hardware Revision of the Power Supply."
        ::= { oaLdDevPSEntry 8 }

------------------------------------------------------------------------------
-- OADWDM-MIB - define objects in the Device's FAN Group
------------------------------------------------------------------------------

oaLdDevFAN          OBJECT IDENTIFIER ::= { oaLdDevGenConfig 3 }

oaLdDevFANsNumber   OBJECT-TYPE
        SYNTAX  INTEGER
        ACCESS  read-only
        STATUS  mandatory
        DESCRIPTION
        "The number of FANS in the corresponding Device.
         Value = 0 says, that FAN Table is not supported."
        ::= { oaLdDevFAN 1 }

oaLdDevFANTable OBJECT-TYPE
        SYNTAX  SEQUENCE OF OaLdDevFANEntry
        ACCESS  not-accessible
        STATUS  mandatory
        DESCRIPTION
        "This table shows all the FANs
         existing in the corresponding Device."
        ::= { oaLdDevFAN 2 }

oaLdDevFANEntry OBJECT-TYPE
        SYNTAX  OaLdDevFANEntry
        ACCESS  not-accessible
        STATUS  mandatory
        DESCRIPTION
        "The entries of the table."
        INDEX { oaLdDevFANIndex }
        ::= { oaLdDevFANTable 1 }

OaLdDevFANEntry ::= SEQUENCE
        {
         oaLdDevFANIndex        INTEGER,
         oaLdDevFANOperStatus   INTEGER
        }

oaLdDevFANIndex OBJECT-TYPE
        SYNTAX  INTEGER
        ACCESS  read-only
        STATUS  mandatory
        DESCRIPTION
        "The index of the table,
         (MAX Value is equal to oaLdDevFANsNumber)."
        ::= { oaLdDevFANEntry 1 }

oaLdDevFANOperStatus  OBJECT-TYPE
        SYNTAX  INTEGER
        {
         none       (1),
         active     (2),
         notActive  (3),
         fail       (4)
        }
        ACCESS  read-only
        STATUS  mandatory
        DESCRIPTION
        "The Oper status of the FAN."
        ::= { oaLdDevFANEntry 5 }

------------------------------------------------------------------------------
-- OADWDM-MIB - define objects in the Device's CPU Group
------------------------------------------------------------------------------

oaLdDevCPU       OBJECT IDENTIFIER ::= { oaLdDevGenConfig 4 }

oaLdDevCPUNumber OBJECT-TYPE
        SYNTAX  INTEGER
        ACCESS  read-only
        STATUS  mandatory
        DESCRIPTION
        "The number of CPU modules in the corresponding Device."
        ::= { oaLdDevCPU 1 }

oaLdDevCPUTable  OBJECT-TYPE
        SYNTAX  SEQUENCE OF OaLdDevCPUEntry
        ACCESS  not-accessible
        STATUS  mandatory
        DESCRIPTION
        "This table shows all the CPU modules,
         existing in the corresponding Device."
        ::= { oaLdDevCPU 10 }

oaLdDevCPUEntry  OBJECT-TYPE
        SYNTAX  OaLdDevCPUEntry
        ACCESS  not-accessible
        STATUS  mandatory
        DESCRIPTION
        "The entries of the table."
        INDEX { oaLdDevCPUIndex }
        ::= { oaLdDevCPUTable 1 }

OaLdDevCPUEntry ::= SEQUENCE
        {
         oaLdDevCPUIndex      INTEGER,
         oaLdDevCPUOperStatus INTEGER,
         oaLdDevCPUType       INTEGER,
         oaLdDevCPUHardVers      INTEGER,
         oaLdDevCPUFpgaVers      INTEGER,
         oaLdDevCPUSerialNumber  DisplayString,
         oaLdDevCPUBuildTime     DisplayString,
         oaLdDevCPUSoftVers      DisplayString,
         oaLdDevCPUBoardID       INTEGER,
         oaLdDevCPUBoardHardVers INTEGER
        }

oaLdDevCPUIndex  OBJECT-TYPE
        SYNTAX  INTEGER
        ACCESS  read-only
        STATUS  mandatory
        DESCRIPTION
        "The index of the table,
         (MAX Value is equal to oaLdDevCPUNumber)."
        ::= { oaLdDevCPUEntry 1 }

oaLdDevCPUOperStatus OBJECT-TYPE
        SYNTAX  INTEGER
        {
         other     (1),
         active    (2),
         standby   (3),
         reset     (4)
        }
        ACCESS  read-only
        STATUS  mandatory
        DESCRIPTION
        "The Operative status of the CPU module.
         active  - single CPU module or master CPU module in chassis with redundant CPU;
         standby - slave CPU module in chassis with redundant CPU;
         reset   - slave CPU module in shutdown mode."
        ::= { oaLdDevCPUEntry 2 }

oaLdDevCPUType OBJECT-TYPE
        SYNTAX  INTEGER
        {
         other  (1),
         mgtd   (2),
         mgtp   (3),
         mngt	(4)
        }
        ACCESS  read-only
        STATUS  mandatory
        DESCRIPTION
        "The HW Type of the CPU module.
         mgtd - regular agent module;
         mgtp - power agent module with additional HW features;
         mngt - KW based agent module."
        ::= { oaLdDevCPUEntry 3 }

oaLdDevCPUHardVers  OBJECT-TYPE
        SYNTAX  INTEGER
        ACCESS  read-only
        STATUS  mandatory
        DESCRIPTION
        "The CPU Card's hardware version."
        ::= { oaLdDevCPUEntry 4 }

oaLdDevCPUFpgaVers  OBJECT-TYPE
        SYNTAX  INTEGER
        ACCESS  read-only
        STATUS  mandatory
        DESCRIPTION
        "The CPU Card's FPGA version."
        ::= { oaLdDevCPUEntry 5 }

oaLdDevCPUSerialNumber   OBJECT-TYPE
        SYNTAX  DisplayString (SIZE(10))
        ACCESS  read-only
        STATUS  mandatory
        DESCRIPTION
        "The CPU Card's Serial Number (10 digits)."
        ::= { oaLdDevCPUEntry 6 }

oaLdDevCPUBuildTime  OBJECT-TYPE
        SYNTAX  DisplayString
        ACCESS  read-only
        STATUS  mandatory
        DESCRIPTION
        "Agent software creation date and time."
        ::= { oaLdDevCPUEntry 7 }

oaLdDevCPUSoftVers  OBJECT-TYPE
        SYNTAX  DisplayString
        ACCESS  read-only
        STATUS  mandatory
        DESCRIPTION
        "Agent software version."
        ::= { oaLdDevCPUEntry 8 }

oaLdDevCPUBoardID  OBJECT-TYPE
        SYNTAX  INTEGER
        ACCESS  read-only
        STATUS  mandatory
        DESCRIPTION
        "ID of CPU's base card"
        ::= { oaLdDevCPUEntry 9 }

oaLdDevCPUBoardHardVers  OBJECT-TYPE
        SYNTAX  INTEGER
        ACCESS  read-only
        STATUS  mandatory
        DESCRIPTION
        "Hardware version of CPU's base card"
        ::= { oaLdDevCPUEntry 10 }

------------------------------------------------------------------------------
-- OADWDM-MIB - define objects in the Device's CPU Redundant Group
------------------------------------------------------------------------------

oaLdDevRedundantCPU       OBJECT IDENTIFIER ::= { oaLdDevGenConfig 5 }

oaLdDevRedundantFeature OBJECT-TYPE
        SYNTAX  INTEGER
        {
         other   (1),
         enable  (2),
         disable (3)
        }
        ACCESS  read-write
        STATUS  mandatory
        DESCRIPTION
        "Set Redundant CPU feature on the next boot in the corresponding Device."
        ::= { oaLdDevRedundantCPU 1 }

oaLdDevRedundantMode OBJECT-TYPE
        SYNTAX  INTEGER
        {
         other   (1),
         enable  (2),
         disable (3)
        }
        ACCESS  read-write
        STATUS  mandatory
        DESCRIPTION
        "Set Redundant CPU mode in the corresponding Device."
        ::= { oaLdDevRedundantCPU 2 }

oaLdDevRedundantCommand OBJECT-TYPE
        SYNTAX  INTEGER
        {
         other           (1),
         forceSwitchOver (2),
         forceSync       (3)
        }
        ACCESS  read-write
        STATUS  mandatory
        DESCRIPTION
        "Force a command in the corresponding Device.
         forceSwitchOver - Force Standby CPU module to become Active;
         forceSync       - Force configuration sync with Standby system."
        ::= { oaLdDevRedundantCPU 3 }

oaLdDevRedundantPeerAdminStatus OBJECT-TYPE
        SYNTAX  INTEGER
        {
         other    (1),
         recover  (2),
         reboot   (3),
         shutdown (4)
        }
        ACCESS  read-write
        STATUS  mandatory
        DESCRIPTION
        "Force a  command to Slave (peer) CPU module in the corresponding Device.
         recover  - recover peer CPU module by hardware reset;
         reboot   - reboot peer CPU module;
         shutdown - shutdown peer CPU module and hold it in reset mode."
        ::= { oaLdDevRedundantCPU 4 }

------------------------------------------------------------------------------
-- OADWDM-MIB - define the Slots cards and status
------------------------------------------------------------------------------

oaLdCardsStatTable OBJECT-TYPE
        SYNTAX  SEQUENCE OF OaLdCardsStatEntry
        ACCESS  not-accessible
        STATUS  mandatory
        DESCRIPTION
        "A list of all the slots status objects"

        ::= { oaLdSlotsStatTable 1 }

oaLdCardsStatEntry  OBJECT-TYPE
        SYNTAX  OaLdCardsStatEntry
        ACCESS  not-accessible
        STATUS  mandatory
        DESCRIPTION
        "The slots status information."

        INDEX   { oaLdCardIndex }

        ::= { oaLdCardsStatTable 1 }

OaLdCardsStatEntry ::= SEQUENCE {

        oaLdCardIndex           INTEGER,
        oaLdCardType            INTEGER,
        oaLdCardRev             INTEGER,
        oaLdCardLambdaCh        LambdaCh,
        oaLdCardOptAccRx        INTEGER,
        oaLdCardOptDwdmRx       INTEGER,
        oaLdCardDwdmLaserTx     INTEGER,
        oaLdCardLaserTemp       INTEGER,
        oaLdCardAmbientTemp     INTEGER,
        oaLdCardRateSelect      RateSelect,
        oaLdCardRateMode        INTEGER,
        oaLdCardLaserMode       INTEGER,
        oaLdCardWdmRxPm         INTEGER,
        oaLdCardWdmTxPm         INTEGER,
        oaLdCardLoopBack        INTEGER,
        oaLdCardRedundantState  INTEGER,
        oaLdCardPrimaryState    INTEGER,
        oaLdCardFPGARev         INTEGER,
        oaLdCardPartNumber      DisplayString,
        oaLdCardSerialNumber    DisplayString,
        oaLdCardHwRev           INTEGER,
        oaLdCardOptAccTx        INTEGER,
        oaLdCardOptDwdmTx       INTEGER,
        oaLdCardTemp            INTEGER,
        oaLdCardSubType         INTEGER
       }

oaLdCardIndex  OBJECT-TYPE
        SYNTAX  INTEGER
        ACCESS  read-only
        STATUS  mandatory
        DESCRIPTION
        "The slot#. An index from 1 to The number of slots."
        ::= { oaLdCardsStatEntry 1 }


oaLdCardType   OBJECT-TYPE
        SYNTAX  INTEGER
        {
         other       (1),
         empty       (2),
         em2009dm    (3),
         em2009dh    (4),
         dw16mux     (5),
         dw16dmux    (6),
         cw8mux      (7),
         cw8dmux     (8),
         ld1600red   (9),
         ld1600mgt  (10),
         em2009cm   (11),
         em2009ch   (12),
         ld800red   (13),
         ld800mgt   (14),
         dw8mux     (15),
         dw8dmux    (16),
         em2009em   (17),
         oadm1      (18),
         oadm2      (19),
         oadm3      (20),
         oadm4      (21),
         em2009oe2  (22),
         em800srv   (23),
         em1600srv  (24),
         tmsfpc     (25),
         tmsfpd     (26),
         adc800     (27),
         adcd800    (28),
         w8MuxDmux  (29),
         w16MuxDmux (30),
         ld800redN  (31),
         ld1600redN (32),
         adc1600    (33),
         adcd1600   (34),
         em2009gm2  (35),
         em800oa    (36),
         em1600oa   (37),
         tm2sfp     (38),
         em2009fm2  (39),
         em2009e8gm (40),
         em2009t8gm (41),
         tme8gm     (42),
         tmt8gm     (43),
         tmgm2      (44),
         tmfm2      (45),
         tmdxfp     (46),
         em2009e3gm (47),
         em2009dsgm (48),
         tme3gm     (49),
         tmdsgm     (50),
         em800rbbs4 (51),
         em800mgtd  (52),
         em800dcm   (53),
         em800dcmd  (54),
         em1600dcm  (55),
         em1600dcmd (56),
         em800dsrv  (57),
         em800mp2   (58),
         em800roa   (59),
         em2009ftxm4(60),
         em2009ftxm8(61),
         em2009fxm4 (62),
         em2009fxm8 (63),
         tmftxm4    (64),
         tmftxm8    (65),
         tmfxm4     (66),
         tmfxm8     (67),
         em800oaid  (68),
         oadmxx     (69),
         em2009ocm4 (70),
         em2009ocm8 (71),
         tmocm4     (72),
         tmocm8     (73),
         em2009ftlm4(74),
         em2009ftlm8(75),
         em8MuxDmux (76),
         em16MuxDmux(77),
         em1600mgtd (78),
         tmdxfpMsa  (79),
         tmdxfpMsaTunable  (80),
         em2009fetxm4(81),
         em2009fetxm8(82),
         tmfetxm4    (83),
         tmfetxm8    (84),
         em2009em4   (85),
         tmd4gsfp    (86),
         tm2d4gsfp   (87),
         em1600Roadm (88),
         tmgm8d      (89),
         tmgm8cd     (90),
         tmgm8dTunable     (91),
         tmgm8cdTunable    (92),
         em1600Raman (93),
         bsxx        (94),
         em1600dsrv  (95),
         em16004cc10g      (96),
         em16008cc10g      (97),
         em800rbbs2  (98),
         em1600rbbs2 (99),
         b4oadmxx    (100),
         em1600oab22p (101),
         em1600oab22pm (102),
         em800oab22p   (103),
         em800oab22pm  (104),
         tm1600dxfpfx  (105),
         tm1600dxfpfxt (106),
         tm1600ocm48d  (107),
         tm1600ocm48dt (108),
         tmfcm8d (109),
         tmfcm8dt (110),
         tmfc2m4d (111),
         tmfc2m4dt (112),
         em16Mux40 (113),
         em16Dmux40 (114),
         em1600rbbs4 (115),
         tm1600dxfpcx  (116),
         tm1600dxfpcxt (117),
         em2009a4 (118),
         em1600oai21p (119),
         em1600oai21pm (120),
         em800oai21p   (121),
         em800oai21pm  (122),
         em2009eam2    (123),
         tm2sfppxfp    (124),
         em1600roadmw9 (125),
         tm2xfp        (126),
         opn1600c82    (127),
         add800        (128),
         addd800       (129),
         add1600       (130),
         addd1600      (131),
         em1600oaid    (132),
         em800oaDual   (133),
         em1600oaDual  (134),
         opn800s82     (135),
         opn1600s82    (136),
         tmgm8xfp      (137),
         tm2sfppxfpfc8 (138),
         tm2xfpf       (139),
         em1600mp2xx   (140),
         tm2xfpe       (141),
         em20094rs530  (142),
         em800dcmt     (143),
         em800dcmdt    (144),
         em1600dcmt    (145),
         em1600dcmdt   (146),
         tmdxfpfxt     (147),
         tmdxfpfxtDual (148),
         em2009Voa4    (149),
         em2009Voa8    (150),
         tmgm8dft      (151),
         tmfc1m8xfp    (152),
         tmfc2m4xfp    (153),
         tmocm48xfp    (154),
         tmgm8df       (155),
         em20098xfp    (156),
         em20098xfp2   (157),
         tm8a          (158),
         em800ocm      (159),
         tm2sfpenge    (160),
         tm40gt        (161),
         em100mngp     (162),
         em160016axfp2 (163),
         tm2sfpengel2  (164),
         tm2sfpxc      (165),
         tm10gm4t      (166),
         em1600wss2q   (167),
         em1600wss4d   (168),
         em800mngt     (169),
         em16Mux80     (170),
         em16Dmux80    (171),
         em16Mux40h    (172),
         em16Dmux40h   (173),
         em800tdcm     (174),
         em1600Raman12 (175),
         tm2xsfpfm     (176),
         em800mp2e2    (177),
         em800cin502   (178),
         tm6cfpf       (179),
         em1600mngt    (180)
         }
        ACCESS  read-only
        STATUS  mandatory
        DESCRIPTION
        "The Card's type"
        ::= { oaLdCardsStatEntry 2 }

oaLdCardRev   OBJECT-TYPE
        SYNTAX  INTEGER
        {
         other (1),
         rev1  (2),
         rev2  (3),
         rev3  (4),
         rev4  (5),
         rev5  (6),
         rev6  (7),
         rev7  (8)
        }
        ACCESS  read-only
        STATUS  mandatory
        DESCRIPTION
        "The Card's Revision"
        ::= { oaLdCardsStatEntry 3 }

oaLdCardLambdaCh   OBJECT-TYPE
        SYNTAX  LambdaCh
        ACCESS  read-only
        STATUS  mandatory
        DESCRIPTION
        "The Card's Lambda channel"
        ::= { oaLdCardsStatEntry 4 }

oaLdCardOptAccRx    OBJECT-TYPE
        SYNTAX  INTEGER
        {
         other (1),
         on    (2),
         off   (3)
        }
        ACCESS  read-only
        STATUS  mandatory
        DESCRIPTION
        "Slot optic access Rx indication.
         Indicates the optic access Receive status
         2 - Receive On
         3 - Receive Off"
        ::= { oaLdCardsStatEntry 5 }

oaLdCardOptDwdmRx    OBJECT-TYPE
        SYNTAX  INTEGER
        {
         other (1),
         on    (2),
         off   (3)
        }
        ACCESS  read-only
        STATUS  mandatory
        DESCRIPTION
        "Slot optic DWDM Rx indication.
         Indicates the optic DWDM Receive status
         2 - Receive On
         3 - Receive Off"
        ::= { oaLdCardsStatEntry 6 }

oaLdCardDwdmLaserTx    OBJECT-TYPE
        SYNTAX  INTEGER
        {
         other (1),
         ok    (2),
         fail  (3)
        }
        ACCESS  read-only
        STATUS  mandatory
        DESCRIPTION
        "Slot DWDM Laser Tx Fail indication.
         Indicates the DWDM Laser Transmit status
         2 - Transmit OK
         3 - Transmit Fail"
        ::= { oaLdCardsStatEntry 7 }

oaLdCardLaserTemp    OBJECT-TYPE
        SYNTAX  INTEGER
        {
         other  (1),
         normal (2),
         high   (3)
        }
        ACCESS  read-only
        STATUS  mandatory
        DESCRIPTION
        "Slot Laser Temperature indication.
         Indicates the Laser Temperature status
         2 - Temperature Normal
         3 - Temperature High"
        ::= { oaLdCardsStatEntry 8 }

oaLdCardAmbientTemp    OBJECT-TYPE
        SYNTAX  INTEGER
        {
         other  (1),
         normal (2),
         high   (3)
        }
        ACCESS  read-only
        STATUS  mandatory
        DESCRIPTION
        "Slot Ambient Temperature indication.
         Indicates the Ambient Temperature status
         2 - Temperature Normal
         3 - Temperature High"
        ::= { oaLdCardsStatEntry 9 }

oaLdCardRateSelect  OBJECT-TYPE
        SYNTAX  RateSelect
        ACCESS  read-write
        STATUS  mandatory
        DESCRIPTION
        "Transponder Rate Select.
         Indicates the transponder rate.
         oc48, stm16 and fiberChannel2125 are for card EM2009-CH
         and EM2009-DH only.
         sonetSdh10giga and fiberChannel10giga are for module TM2-SFPPXFP only."
        ::= { oaLdCardsStatEntry 10 }

oaLdCardRateMode    OBJECT-TYPE
        SYNTAX  INTEGER
        {
         other  (1),
         auto   (2),
         manual (3)
        }
        ACCESS  read-only
        STATUS  mandatory
        DESCRIPTION
        "Transponder Rate Mode.
         Indicates the transponder rate mode.
         2 - Automatic - Rate is set by software
         3 - Manual - Rate is set by DIP switches on board
         If manual, oaLdCardRateSelect can not be changed by software."
        ::= { oaLdCardsStatEntry 11 }

oaLdCardLaserMode    OBJECT-TYPE
        SYNTAX  INTEGER
        {
         other   (1),
         enable  (2),
         disable (3)
        }
        ACCESS  read-write
        STATUS  mandatory
        DESCRIPTION
        "Transponder Laser Mode.
         Indicates the transponder laser mode.
         2 - Enable  - Laser is enabled
         3 - Disable - Laser is disabled (can not transmit)"
        ::= { oaLdCardsStatEntry 12 }

oaLdCardWdmRxPm    OBJECT-TYPE
        SYNTAX  INTEGER
        ACCESS  read-only
        STATUS  mandatory
        DESCRIPTION
        "Transponder WDM receiver optical power.
         Indicates the optical power in dBm.
         To calculate the power use the equation  P(dBm)=oaLdCardWdmRxPm/2,
         when oaLdCardWdmRxPm is a signed number.
         (171) is returned when this feature is not supported"
        ::= { oaLdCardsStatEntry 15 }

oaLdCardWdmTxPm    OBJECT-TYPE
        SYNTAX  INTEGER
        ACCESS  read-only
        STATUS  mandatory
        DESCRIPTION
        "Transponder WDM transmitter optical power.
         Indicates the optical power in dBm.
         To calculate the power use the equation  P(dBm)=oaLdCardWdmTxPm/2,
         when oaLdCardWdmTxPm is a signed number.
         (171) is returned when this feature is not supported
         Note: For TM-DXFP card the optical power are in units of percent (%)"
        ::= { oaLdCardsStatEntry 16 }

oaLdCardLoopBack    OBJECT-TYPE
        SYNTAX  INTEGER
        {
         other            (1),
         normal           (2),
         loopback         (3),
         remoteLoopback   (4),
         localLoopback    (5)
        }
        ACCESS  read-write
        STATUS  mandatory
        DESCRIPTION
        "Transponder LoopBack state.
         Indicates the transponder LoopBack state.
         2 - normal         - Transponder card is in non-loopback state
         3 - loopback       - Transponder card is in loopback state
         4 - remoteLoopback - Transponder card is in remote loopback state
         5 - localLoopback  - Transponder card is in local loopback state
         Note: options 4 and 5 are available for TM-DXFP card."
        ::= { oaLdCardsStatEntry 17 }

oaLdCardRedundantState    OBJECT-TYPE
        SYNTAX  INTEGER
        {
         other     (1),
         normal    (2),
         redundant (3)
        }
        ACCESS  read-only
        STATUS  mandatory
        DESCRIPTION
        "Transponder Redundant Mode.
         Indicates the transponder redundant mode.
         2 - normal    - Transponder is in non-redundant mode
         3 - redundant - Transponder is in redundant mode"
        ::= { oaLdCardsStatEntry 18 }

oaLdCardPrimaryState    OBJECT-TYPE
        SYNTAX  INTEGER
        {
         other     (1),
         secondary (2),
         primary   (3)
        }
        ACCESS  read-write
        STATUS  mandatory
        DESCRIPTION
        "Transponder Primary/Secondary State.
         Indicates the transponder Primary/Secondary status.
         2 - secondary - Transponder is in secondary state and is not active
         3 - primary   - Transponder is in primary state and is active"
        ::= { oaLdCardsStatEntry 19 }

oaLdCardFPGARev   OBJECT-TYPE
        SYNTAX  INTEGER
        ACCESS  read-only
        STATUS  mandatory
        DESCRIPTION
        "The Card's FPGA Revision"
        ::= { oaLdCardsStatEntry 20 }

oaLdCardPartNumber   OBJECT-TYPE
        SYNTAX  DisplayString (SIZE (0..15))
        ACCESS  read-only
        STATUS  mandatory
        DESCRIPTION
        "The Card's Part Number (maximum 15 symbols)."
        ::= { oaLdCardsStatEntry 21 }

oaLdCardSerialNumber   OBJECT-TYPE
        SYNTAX  DisplayString (SIZE(10))
        ACCESS  read-only
        STATUS  mandatory
        DESCRIPTION
        "The Card's  Serial Number (10 digits)."
        ::= { oaLdCardsStatEntry 22 }

oaLdCardHwRev   OBJECT-TYPE
        SYNTAX  INTEGER
        ACCESS  read-only
        STATUS  mandatory
        DESCRIPTION
        "The Card's Hardware Revision"
        ::= { oaLdCardsStatEntry 23 }

oaLdCardOptAccTx    OBJECT-TYPE
        SYNTAX  INTEGER
        {
         other (1),
         on    (2),
         off   (3)
        }
        ACCESS  read-only
        STATUS  mandatory
        DESCRIPTION
        "Slot optic access Tx indication.
         Indicates the optic access Transmit status
         2 - Transmit On
         3 - Transmit Off"
        ::= { oaLdCardsStatEntry 24 }

oaLdCardOptDwdmTx    OBJECT-TYPE
        SYNTAX  INTEGER
        {
         other (1),
         on    (2),
         off   (3)
        }
        ACCESS  read-only
        STATUS  mandatory
        DESCRIPTION
        "Slot optic DWDM Tx indication.
         Indicates the optic DWDM Transmit status
         2 - Transmit On
         3 - Transmit Off"
        ::= { oaLdCardsStatEntry 25 }

oaLdCardTemp   OBJECT-TYPE
        SYNTAX  INTEGER
        ACCESS  read-only
        STATUS  mandatory
        DESCRIPTION
        "The Module Temperature (in units of 1/10 Degrees Celsius [0.1 C])"
        ::= { oaLdCardsStatEntry  26}

oaLdCardSubType OBJECT-TYPE
        SYNTAX  INTEGER
        {
         other     (1),
         regular   (2),
         enchanced (3)
        }
        ACCESS  read-only
        STATUS  mandatory
        DESCRIPTION
        "The Card's subtype"
        ::= { oaLdCardsStatEntry 27 }


------------------------------------------------------------------------------
-- OADWDM-MIB - define the Slot cards Entitys and their status
------------------------------------------------------------------------------

-- This table is for cards with more then one entity on it.
-- An entity can be a transponder.
-- For an example: Card TM2-SFP has two transponders on the same card.
--                 So, there is an entity for each transponder.

oaLdCardEntityStatTable OBJECT-TYPE
        SYNTAX  SEQUENCE OF OaLdCardEntityStatEntry
        ACCESS  not-accessible
        STATUS  mandatory
        DESCRIPTION
        "A list of all Entities in a slot and their status objects"

        ::= { oaLdSlotEntitysStat 1 }

oaLdCardEntityStatEntry  OBJECT-TYPE
        SYNTAX  OaLdCardEntityStatEntry
        ACCESS  not-accessible
        STATUS  mandatory
        DESCRIPTION
        "The slots Entity status information."

        INDEX   { oaLdCardEntityCardIndex, oaLdCardEntityEntityIndex }

        ::= { oaLdCardEntityStatTable 1 }

OaLdCardEntityStatEntry ::= SEQUENCE {

        oaLdCardEntityCardIndex       INTEGER,
        oaLdCardEntityEntityIndex     INTEGER,
        oaLdCardEntityWaveLength      INTEGER,
        oaLdCardEntityOptAccRx        INTEGER,
        oaLdCardEntityOptDwdmRx       INTEGER,
        oaLdCardEntityDwdmLaserTx     INTEGER,
        oaLdCardEntityLaserTemp       INTEGER,
        oaLdCardEntityAmbientTemp     INTEGER,
        oaLdCardEntityRateSelect      RateSelect,
        oaLdCardEntityRateMode        INTEGER,
        oaLdCardEntityLaserMode       INTEGER,
        oaLdCardEntityWdmRxPm         INTEGER,
        oaLdCardEntityWdmTxPm         INTEGER,
        oaLdCardEntityLoopBack        INTEGER,
        oaLdCardEntityRedundantState  INTEGER,
        oaLdCardEntityPrimaryState    INTEGER,
        oaLdCardEntityClockSource     INTEGER,
        oaLdCardEntityTransparency    INTEGER,
        oaLdCardEntityStandard	      INTEGER,
        oaLdCardEntityAccessLinState  INTEGER,
        oaLdCardEntityLineCoding      INTEGER,
        oaLdCardEntityUartBaudRate    INTEGER,
        oaLdCardEntityUartParity      INTEGER,
        oaLdCardEntityUartStopBit     INTEGER,
        oaLdCardEntityPmMode	      INTEGER,
        oaLdCardEntityWdmFecMode      INTEGER,
        oaLdCardEntityMinDispDist     INTEGER,
        oaLdCardEntityMaxDispDist     INTEGER,
        oaLdCardEntityDispDist        INTEGER,
        oaLdCardEntityCCMode          INTEGER,
        oaLdCardEntityOptAccTx        INTEGER,
        oaLdCardEntityOptDwdmTx       INTEGER,
        oaLdCardEntityEMCfgType       INTEGER,
        oaLdCardEntityEMCfgSide       INTEGER,
        oaLdCardEntityPreemptionMode  INTEGER,
        oaLdCardEntityActivePort      INTEGER,
        oaLdCardEntityOperationMode   INTEGER,
        oaLdCardEntityRedundantType   INTEGER,
        oaLdCardEntityOtu2MappingMode INTEGER,
        oaLdCardEntityTopologyMode    INTEGER,
        oaLdCardEntityDispDistAdmin   INTEGER,
        oaLdCardEntityChannelOffset   INTEGER,
        oaLdCardEntityTimingMode      INTEGER,
        oaLdCardEntityTdcmTuningStatus INTEGER,
        oaLdCardEntityRedModeActivePort INTEGER,
        oaLdCardEntityAutoShutdownMode INTEGER
       }

oaLdCardEntityCardIndex  OBJECT-TYPE
        SYNTAX  INTEGER
        ACCESS  read-only
        STATUS  mandatory
        DESCRIPTION
        "The slot#. An index from 1 to The number of slots."
        ::= { oaLdCardEntityStatEntry 1 }


oaLdCardEntityEntityIndex  OBJECT-TYPE
        SYNTAX  INTEGER
        ACCESS  read-only
        STATUS  mandatory
        DESCRIPTION
        "The entity#. An index from 1 to The number of entities."
        ::= { oaLdCardEntityStatEntry 2 }


oaLdCardEntityWaveLength   OBJECT-TYPE
        SYNTAX  INTEGER
        ACCESS  read-only
        STATUS  mandatory
        DESCRIPTION
        "The Card's entity laser wavelength (Lambda channel) in units of nm (Nanometer).
         Returns 0 when not applicable "
        ::= { oaLdCardEntityStatEntry 5 }

oaLdCardEntityOptAccRx    OBJECT-TYPE
        SYNTAX  INTEGER
        {
         other (1),
         on    (2),
         off   (3)
        }
        ACCESS  read-only
        STATUS  mandatory
        DESCRIPTION
        "Entity optic access Rx indication.
         Indicates the optic access Receive status
         2 - Receive On
         3 - Receive Off"
        ::= { oaLdCardEntityStatEntry 6 }

oaLdCardEntityOptDwdmRx    OBJECT-TYPE
        SYNTAX  INTEGER
        {
         other (1),
         on    (2),
         off   (3)
        }
        ACCESS  read-only
        STATUS  mandatory
        DESCRIPTION
        "Entity optic DWDM Rx indication.
         Indicates the optic DWDM Receive status
         2 - Receive On
         3 - Receive Off"
        ::= { oaLdCardEntityStatEntry 7 }

oaLdCardEntityDwdmLaserTx    OBJECT-TYPE
        SYNTAX  INTEGER
        {
         other (1),
         ok    (2),
         fail  (3)
        }
        ACCESS  read-only
        STATUS  mandatory
        DESCRIPTION
        "Entity DWDM Laser Tx Fail indication.
         Indicates the DWDM Laser Transmit status
         2 - Transmit OK
         3 - Transmit Fail"
        ::= { oaLdCardEntityStatEntry 8 }

oaLdCardEntityLaserTemp    OBJECT-TYPE
        SYNTAX  INTEGER
        {
         other  (1),
         normal (2),
         high   (3)
        }
        ACCESS  read-only
        STATUS  mandatory
        DESCRIPTION
        "Entity Laser Temperature indication.
         Indicates the Laser Temperature status
         2 - Temperature Normal
         3 - Temperature High"
        ::= { oaLdCardEntityStatEntry 9 }

oaLdCardEntityAmbientTemp    OBJECT-TYPE
        SYNTAX  INTEGER
        {
         other  (1),
         normal (2),
         high   (3)
        }
        ACCESS  read-only
        STATUS  mandatory
        DESCRIPTION
        "Entity Ambient Temperature indication.
         Indicates the Ambient Temperature status
         2 - Temperature Normal
         3 - Temperature High"
        ::= { oaLdCardEntityStatEntry 10 }

oaLdCardEntityRateSelect    OBJECT-TYPE
        SYNTAX  RateSelect
        ACCESS  read-write
        STATUS  mandatory
        DESCRIPTION
        "Transponder Rate Select.
         Indicates the transponder rate.
         oc48, stm16 and fiberChannel2125 are for card EM2009-CH
         and EM2009-DH only"
        ::= { oaLdCardEntityStatEntry 11 }

oaLdCardEntityRateMode    OBJECT-TYPE
        SYNTAX  INTEGER
        {
         other  (1),
         auto   (2),
         manual (3)
        }
        ACCESS  read-only
        STATUS  mandatory
        DESCRIPTION
        "Transponder Rate Mode.
         Indicates the transponder rate mode.
         2 - Automatic - Rate is set by software
         3 - Manual - Rate is set by DIP switches on board
         If manual, oaLdCardRateSelect can not be changed by software."
        ::= { oaLdCardEntityStatEntry 12 }

oaLdCardEntityLaserMode    OBJECT-TYPE
        SYNTAX  INTEGER
        {
         other   (1),
         enable  (2),
         disable (3)
        }
        ACCESS  read-write
        STATUS  mandatory
        DESCRIPTION
        "Transponder Laser Mode.
         Indicates the transponder laser mode.
         2 - Enable  - Laser is enabled
         3 - Disable - Laser is disabled (can not transmit)"
        ::= { oaLdCardEntityStatEntry 13 }

oaLdCardEntityWdmRxPm    OBJECT-TYPE
        SYNTAX  INTEGER
        ACCESS  read-only
        STATUS  mandatory
        DESCRIPTION
        "Transponder WDM receiver optical power.
         Indicates the optical power in units of 1/10 dBm.
         (oaLdCardEntityWdmRxPm is a signed number.)
         (999) is returned when this feature is not supported
         or irrelevant.
         (-999) is returned when signal is too low."
        ::= { oaLdCardEntityStatEntry 16 }

oaLdCardEntityWdmTxPm    OBJECT-TYPE
        SYNTAX  INTEGER
        ACCESS  read-only
        STATUS  mandatory
        DESCRIPTION
        "Transponder WDM transmitter optical power.
         Indicates the optical power in units of 1/10 dBm.
         (oaLdCardEntityWdmTxPm is a signed number.)
         (999) is returned when this feature is not supported
         or irrelevant.
         (-999) is returned when signal is too low."
        ::= { oaLdCardEntityStatEntry 17 }

oaLdCardEntityLoopBack    OBJECT-TYPE
        SYNTAX  INTEGER
        {
         other    (1),
         normal   (2),
         loopback (3),
         remoteLoopback (4),
         localLoopback  (5)
        }
        ACCESS  read-write
        STATUS  mandatory
        DESCRIPTION
        "Transponder LoopBack state.
         Indicates the transponder LoopBack state.
         2 - normal   - Transponder entity is in non-loopback state
         3 - loopback - Transponder entity is in loopback state
         4 - remoteLoopback - Transponder entity is in remote loopback state
         5 - localLoopback  - Transponder entity is in local loopback state
         Note: options 4 and 5 are available for TM2-D4G-SFP card."
        ::= { oaLdCardEntityStatEntry 18 }

oaLdCardEntityRedundantState    OBJECT-TYPE
        SYNTAX  INTEGER
        {
         other     (1),
         normal    (2),
         redundant (3)
        }
        ACCESS  read-only
        STATUS  mandatory
        DESCRIPTION
        "Transponder Redundant Mode.
         Indicates the transponder redundant mode.
         2 - normal    - Transponder is in non-redundant mode
         3 - redundant - Transponder is in redundant mode"
        ::= { oaLdCardEntityStatEntry 19 }

oaLdCardEntityPrimaryState    OBJECT-TYPE
        SYNTAX  INTEGER
        {
         other     (1),
         secondary (2),
         primary   (3)
        }
        ACCESS  read-write
        STATUS  mandatory
        DESCRIPTION
        "Transponder Primary/Secondary State.
         Indicates the transponder Primary/Secondary status.
         2 - secondary - Transponder is in secondary state and is not active
         3 - primary   - Transponder is in primary state and is active"
        ::= { oaLdCardEntityStatEntry 20 }

oaLdCardEntityClockSource    OBJECT-TYPE
        SYNTAX  INTEGER
        {
         other     (1),
         p1        (2),
         p2        (3),
         p3        (4),
         p4        (5),
         p5        (6),
         p6        (7),
         p7        (8),
         p8        (9),
         p9        (10)
        }
        ACCESS  read-write
        STATUS  mandatory
        DESCRIPTION
        "OCM Module Port Clock Source State.
         Indicates the Port Clock Source.
         2  - Port 1 - Module Clock Source is port 1
         3  - Port 2 - Module Clock Source is port 2
         4  - Port 3 - Module Clock Source is port 3
         5  - Port 4 - Module Clock Source is port 4
         6  - Port 5 - Module Clock Source is port 5 or Trunk port
                       according to module type
         7  - Port 6 - Module Clock Source is port 6
         8  - Port 7 - Module Clock Source is port 7
         9  - Port 8 - Module Clock Source is port 8
         10 - Port 9 - Module Clock Source is Trunk port"
        ::= { oaLdCardEntityStatEntry 21 }

oaLdCardEntityTransparency    OBJECT-TYPE
        SYNTAX  INTEGER
        {
         other         (1),
         transparent   (2),
         noTransparent (3)
        }
        ACCESS  read-write
        STATUS  mandatory
        DESCRIPTION
        "OCM Module Transparency State.
         Indicates the Module transparency state.
         2  - transparent    - Module is in transparency mode
         3  - no transparent - Module is in non transparency mode"
        ::= { oaLdCardEntityStatEntry 22 }

oaLdCardEntityStandard    OBJECT-TYPE
        SYNTAX  INTEGER
        {
         other         (1),
         sonet	       (2),
         sdh 	       (3)
        }
        ACCESS  read-write
        STATUS  mandatory
        DESCRIPTION
        "OCM Module Standard Mode.
         Indicates the Module Standard.
         2  - sonet - Module in SONET standard mode
         3  - sdh   - Module in SDH standard mode"
        ::= { oaLdCardEntityStatEntry 23 }

oaLdCardEntityAccessLinState    OBJECT-TYPE
        SYNTAX  INTEGER
        {
         other   (1),
         enable  (2),
         disable (3)
        }
        ACCESS  read-write
        STATUS  mandatory
        DESCRIPTION
        "Transponder LIN status.
         Indicates the transponder access LIN status.
         2 - Enable  - Access LIN is enabled
         3 - Disable - Access LIN is disabled"
        ::= { oaLdCardEntityStatEntry 24 }

oaLdCardEntityLineCoding    OBJECT-TYPE
        SYNTAX  INTEGER
        {
         other (1),
         b8zs  (2),
         ami   (3)
        }
        ACCESS  read-write
        STATUS  mandatory
        DESCRIPTION
        "Indicates the T1 cards Line Coding.
         2 - B8ZS - Bipolar 8-zero substitution encoding
         3 - AMI  - Alternate Mark Inversion encoding"
        ::= { oaLdCardEntityStatEntry 25 }

oaLdCardEntityUartBaudRate    OBJECT-TYPE
        SYNTAX  INTEGER
        {
         other      (1),
         baud1200   (2),
         baud2400   (3),
         baud4800   (4),
         baud9600   (5),
         baud19200  (6),
         baud38400  (7),
         baud57600  (8),
         baud115200 (9)
        }
        ACCESS  read-write
        STATUS  mandatory
        DESCRIPTION
        "Indicates the T1 cards UART Baud Rate configuration."
        ::= { oaLdCardEntityStatEntry 26 }

oaLdCardEntityUartParity    OBJECT-TYPE
        SYNTAX  INTEGER
        {
         other    (1),
         even     (2),
         odd      (3),
         noParity (4)
        }
        ACCESS  read-write
        STATUS  mandatory
        DESCRIPTION
        "Indicates the T1 cards UART Parity configuration."
        ::= { oaLdCardEntityStatEntry 27 }

oaLdCardEntityUartStopBit    OBJECT-TYPE
        SYNTAX  INTEGER
        {
         other     (1),
         stopBit1  (2),
         stopBit15 (3)
        }
        ACCESS  read-write
        STATUS  mandatory
        DESCRIPTION
        "Indicates the T1 cards UART Stop Bit configuration.
         1 - Stop Bit 1 x data bit,
         2 - Stop Bit 1.5 x data bit."
        ::= { oaLdCardEntityStatEntry 28 }

oaLdCardEntityPmMode    OBJECT-TYPE
        SYNTAX  INTEGER
        {
         other   (1),
         enable  (2),
         disable (3)
        }
        ACCESS  read-write
        STATUS  mandatory
        DESCRIPTION
        "Module Performance Monitoring Mode.
         Indicates the Module Performance Monitoring mode.
         2 - Enable  - PM is enabled
         3 - Disable - PM is disabled"
        ::= { oaLdCardEntityStatEntry 29 }

oaLdCardEntityWdmFecMode    OBJECT-TYPE
        SYNTAX  INTEGER
        {
         other   (1),
         g709	 (2),
         eFec    (3),
         byPass  (4),
         uFec    (5)
        }
        ACCESS  read-write
        STATUS  mandatory
        DESCRIPTION
        "The Forward Error Correction (FEC) mode which is used
         in the module.
         2 - g709 - Standard G.709 FEC mode.
         3 - eFec - Enhanced FEC proprietary mode.
         4 - byPass - Bypass FEC mode (no FEC).
         5 - uFec - Ultra FEC mode."
        ::= { oaLdCardEntityStatEntry 30 }

oaLdCardEntityMinDispDist OBJECT-TYPE
     SYNTAX	INTEGER
     UNITS  "ps/nm"
     ACCESS  read-only
     STATUS  mandatory
     DESCRIPTION
       "Minimum Dispersion distance of integrated TODC.
        (0) is returned when this feature is not supported
        Units: ps/nm"
     ::= {  oaLdCardEntityStatEntry 31 }

oaLdCardEntityMaxDispDist OBJECT-TYPE
     SYNTAX	INTEGER
     UNITS  "ps/nm"
     ACCESS  read-only
     STATUS  mandatory
     DESCRIPTION
       "Maximum Dispersion distance of integrated TODC.
        (0) is returned when this feature is not supported
        Units: ps/nm"
     ::= { oaLdCardEntityStatEntry 32 }

oaLdCardEntityDispDist OBJECT-TYPE
     SYNTAX	INTEGER
     UNITS  "ps/nm"
     ACCESS  read-write
     STATUS  mandatory
     DESCRIPTION
       "Dispersion distance of integrated TODC.
        Units: ps/nm"
     ::= { oaLdCardEntityStatEntry 33 }

oaLdCardEntityCCMode    OBJECT-TYPE
        SYNTAX  INTEGER
        {
         other        (1),
         dual1234     (2),
         dual1324     (3),
         dual1423     (4),
         protectRxMon (5),
         protectTxMon (6),
         multicast2   (7),
         multicast3   (8),
         multicast4   (9),
         loopback     (10)
        }
        ACCESS  read-write
        STATUS  mandatory
        DESCRIPTION
        "EM1600-4CC10G Module cross connection mode.
         dual1234 - Dual transponder mode, when port 1 <-> 2, port 3 <-> 4.
         dual1324 - Dual transponder mode, when port 1 <-> 3, port 2 <-> 4.
         dual1423 - Dual transponder mode, when port 1 <-> 4, port 2 <-> 3.
         protectRxMon - Protection with RX Monitor mode.
         protectTxMon - Protection with TX Monitor mode.
         multicast2 - Multicast mode, when port 2 is back.
         multicast3 - Multicast mode, when port 3 is back.
         multicast4 - Multicast mode, when port 4 is back.
         loopbackPerPort - Remote Loop Back for all ports mode"
        ::= { oaLdCardEntityStatEntry 34 }

oaLdCardEntityOptAccTx    OBJECT-TYPE
        SYNTAX  INTEGER
        {
         other (1),
         on    (2),
         off   (3)
        }
        ACCESS  read-only
        STATUS  mandatory
        DESCRIPTION
        "Entity optic access Tx indication.
         Indicates the optic access Transmit status
         2 - Transmit On
         3 - Transmit Off"
        ::= { oaLdCardEntityStatEntry 35 }

oaLdCardEntityOptDwdmTx    OBJECT-TYPE
        SYNTAX  INTEGER
        {
         other (1),
         on    (2),
         off   (3)
        }
        ACCESS  read-only
        STATUS  mandatory
        DESCRIPTION
        "Entity optic DWDM Tx indication.
         Indicates the optic DWDM Transmit status
         2 - Transmit On
         3 - Transmit Off"
        ::= { oaLdCardEntityStatEntry 36 }

oaLdCardEntityEMCfgType    OBJECT-TYPE
        SYNTAX  INTEGER
        {
         other   (1),
         typeI   (2),
         typeII  (3),
         typeIII (4),
         typeIV  (5),
         typeV   (6)
        }
        ACCESS  read-write
        STATUS  mandatory
        DESCRIPTION
        "Specifies the E&M Lead Signaling type."
        ::= { oaLdCardEntityStatEntry 37 }

oaLdCardEntityEMCfgSide    OBJECT-TYPE
        SYNTAX  INTEGER
        {
         other             (1),
         trunkCircuitSide  (2),
         signalingUnitSide (3)
        }
        ACCESS  read-write
        STATUS  mandatory
        DESCRIPTION
        "Specifies the side of the unit:
         trunkCircuitSide  - Trunk Circuit Side
         signalingUnitSide - Signaling Unit Side
         Usualy the PBX is the trunk circuit side and the
         telco, CO is the signaling unit side."
        ::= { oaLdCardEntityStatEntry 38 }

oaLdCardEntityPreemptionMode    OBJECT-TYPE
        SYNTAX  INTEGER
        {
         other        (1),
         port2        (2),
         port3        (3),
         noPreemption (4)
        }
        ACCESS  read-write
        STATUS  mandatory
        DESCRIPTION
        "EM1600-4CC10G Module preemption mode for TX or RX Protection cross connect.
         In two following preemption modes one of access ports has priority
         to be active in case of two links are ON.
         port2 - Port 2 has priority to be active if two links are ON for bith ports 2 and 3.
         port3 - Port 3 has priority to be active if two links are ON for bith ports 2 and 3.
         noPreemption - first linked port is active."
        ::= { oaLdCardEntityStatEntry 39 }

oaLdCardEntityActivePort    OBJECT-TYPE
        SYNTAX  INTEGER
        {
         other        (1),
         port2        (2),
         port3        (3),
         noActive     (4)
        }
        ACCESS  read-only
        STATUS  mandatory
        DESCRIPTION
        "EM1600-4CC10G Module actual active port for TX or RX Protection cross connect."
        ::= { oaLdCardEntityStatEntry 40 }

oaLdCardEntityOperationMode    OBJECT-TYPE
        SYNTAX  INTEGER
        {
         other           (1),
         normal          (2),
         yCableRedundant (3),
         repeater        (4),
         repeaterWan     (5),
         dualTransponder (6),
         broadcastUni    (7),
         crossTransponder(8),
         mux2WDM1Access  (9)
        }
        ACCESS  read-write
        STATUS  mandatory
        DESCRIPTION
        "other - Modue does not support this feature.
         normal- Normal operational mode.
         yCableRedundant - For TM2-XFP module redundancy mode.
         repeater    - For TM2-XFPF module - connects between the two WDM ports
                       for 10GE LAN repeater functionality.
         repeaterWan - For TM2-XFPF module - connects between the two WDM ports
                       for 10GE WAN repeater functionality.
         Next modes for module TM2-SFPXC:
         dualTransponder  - as regular Dual Transponder module.
         broadcastUni     - connects between WDM to three Access ports unidirectional.
         crossTransponder - connects as dual transponder between opposite WDM and Access ports.
         mux2WDM1Access   - connects between two WDM ports for mux to one Access port."
        ::= { oaLdCardEntityStatEntry 41 }

oaLdCardEntityRedundantType    OBJECT-TYPE
        SYNTAX  INTEGER
        {
         other                         (1),
         normal                        (2),
         dualSlotRedundancy            (3),
         singleSlotRedundancy          (4),
         singleSlotOneAccessRedundancy (5)
        }
        ACCESS  read-write
        STATUS  mandatory
        DESCRIPTION
        "Redundant operation mode, (applicable only for modules that support this features)
         other - Module does not support this feature,
         normal - No redundant mode,
         dualSlotRedundancy - Redundancy mode between the same entity of two sequential slots
                              (Y-cable connects both access ports at both slots),
         singleSlotRedundancy - Redundancy mode between two entities at the same module
                                (Y-cable connects both access ports in the same module),
         singleSlotOneAccessRedundancy - Redundancy mode between two entities at the same module
                                         (Y-cable is not needed)."
        ::= { oaLdCardEntityStatEntry 42 }

oaLdCardEntityOtu2MappingMode    OBJECT-TYPE
        SYNTAX  INTEGER
        {
         none                (1),
         basicMode           (2),
         extendedMode1       (3),
         extendedMode2       (4)
        }
        ACCESS  read-write
        STATUS  mandatory
        DESCRIPTION
        "For entities that enables mapping of clients into the OTN payload. The mode will indicate about
         the method of OTU-2 Line mapping. Based on that mode the user is able to build his services.
         none          - Module does not support this feature.
         basicMode     - The default mode. In this mode the output payload format is independently configured
                         based on user's request. All known clients are available.
         extendedMode1 - In this mode the output payload format is configured to Vcat 4xOTU-1 for GFP-T model.
                         The user is able to add fibre-channel and Eth-1G clients.
         extendedMode2 - In this mode the output payload format is configured to Vcat 4xOTU-1 for GFP-F model.
                         The user is able to add SDI (Video) and Ethernet clients."
        ::= { oaLdCardEntityStatEntry 43 }

oaLdCardEntityTopologyMode    OBJECT-TYPE
        SYNTAX  INTEGER
        {
         none             (1),
         pointToPoint     (2),
         linearADM        (3),
         ringUniDirection (4),
         ringBiDirection  (5)
        }
        ACCESS  read-write
        STATUS  mandatory
        DESCRIPTION
        ""
        ::= { oaLdCardEntityStatEntry 44 }

oaLdCardEntityDispDistAdmin OBJECT-TYPE
     SYNTAX	INTEGER
     UNITS  "ps/nm"
     ACCESS  read-write
     STATUS  mandatory
     DESCRIPTION
       "Administrative calibration factor for
        Dispersion distance of integrated TODC.
        Units: ps/nm"
     ::= { oaLdCardEntityStatEntry 45 }

oaLdCardEntityChannelOffset OBJECT-TYPE
     SYNTAX	INTEGER
     UNITS  "GHz"
     ACCESS  read-write
     STATUS  mandatory
     DESCRIPTION
       "ITU channel offset.
        Units: GHz"
     ::= { oaLdCardEntityStatEntry 46 }

oaLdCardEntityTimingMode    OBJECT-TYPE
        SYNTAX  INTEGER
        {
         none             (1),
         phaseMode        (2),
         fifoMode         (3)
        }
        ACCESS  read-write
        STATUS  mandatory
        DESCRIPTION
        "For entities that enables mapping of synchronous clients into the OTN payload.
         Timing mode will indicate how the clock will be recovered.
         none          - Module does not support this feature.
         phaseMode     - recovery mode based on phased mode,
         fifoMode      - recovery mode based on fifo mode"
        ::= { oaLdCardEntityStatEntry 47 }

oaLdCardEntityTdcmTuningStatus OBJECT-TYPE
     SYNTAX	INTEGER
     {
      other       (1),
      inProgress  (2),
      ok          (3)
     }
     ACCESS  read-only
     STATUS  mandatory
     DESCRIPTION
     "Current tuning status.
         inProgress - not all etalons reach their target temperature values
                      and some etalons are still tuning.
      ok         - all etalons reach their target temperature values."
     ::= { oaLdCardEntityStatEntry 48 }

oaLdCardEntityRedModeActivePort    OBJECT-TYPE
        SYNTAX  INTEGER
        ACCESS  read-write
        STATUS  mandatory
        DESCRIPTION
        "For entities that support single slot redundancy with one access port.
         Active port specifies which of the acess ports is active.
         For TM2_XSFPFM Port#2 indicatets the first access port and
         Port#3 the second access port."
        ::= { oaLdCardEntityStatEntry 49 }

oaLdCardEntityAutoShutdownMode    OBJECT-TYPE
        SYNTAX  INTEGER
        {
         other   (1),
         enable  (2),
         disable (3)
        }
        ACCESS  read-write
        STATUS  mandatory
        DESCRIPTION
        "Entity Auto Shutdown Mode.
         Indicates the entity Auto Shutdown (eye safe) mode.
         2 - Enable  - Auto Shutdown mode is enabled
         3 - Disable - Auto Shutdown mode is disabled."
        ::= { oaLdCardEntityStatEntry 50 }


------------------------------------------------------------------------------
-- OADWDM-MIB - define the Redundant Optical cards;
--              commands and status
------------------------------------------------------------------------------

oaLdRedundantOpticTable OBJECT-TYPE
        SYNTAX    SEQUENCE OF OaLdRedundantOpticEntry
        ACCESS    not-accessible
        STATUS    mandatory
        DESCRIPTION
        "Table of installed Lambda Driver Redundant Optical Cards"
        ::= {oaLdRedundantOptic 1}

oaLdRedundantOpticEntry OBJECT-TYPE
        SYNTAX    OaLdRedundantOpticEntry
        ACCESS    not-accessible
        STATUS    mandatory
        DESCRIPTION
        "Installed Lambda Driver Redundant Optical Cards"

        INDEX    { oaLdRedOptSlotNumber }

        ::= { oaLdRedundantOpticTable 1 }

OaLdRedundantOpticEntry ::= SEQUENCE {
        oaLdRedOptSlotNumber        INTEGER,
        oaLdRedOptSwitchPosition    INTEGER,
        oaLdRedOptLastCommand       INTEGER,
        oaLdRedOptPrimaryRx         INTEGER,
        oaLdRedOptSecondaryRx       INTEGER
       }

oaLdRedOptSlotNumber OBJECT-TYPE
        SYNTAX    INTEGER
        ACCESS    read-only
        STATUS    mandatory
        DESCRIPTION
        "The slot#. An index from 1 to The number of slots"
        ::= { oaLdRedundantOpticEntry 1 }

oaLdRedOptSwitchPosition OBJECT-TYPE
        SYNTAX    INTEGER
        {
         other           (1),
         primary         (2),
         secondary       (3)
        }
        ACCESS    read-write
        STATUS    mandatory
        DESCRIPTION
        "Switch Position:
         2 - Receive from Primary fiber.
         3 - Receive from Secondary fiber.
         Note:
              a command to set the switch to a non received fiber will be
              ignored."
        ::= { oaLdRedundantOpticEntry 2 }

oaLdRedOptLastCommand OBJECT-TYPE
        SYNTAX    INTEGER
        {
         other     (1),
         automatic (2),
         manual    (3)
        }
        ACCESS    read-only
        STATUS    mandatory
        DESCRIPTION
        "Indicates who issue the last command
         automatic - by hardware
         manual    - by software"
        ::= { oaLdRedundantOpticEntry 3 }

oaLdRedOptPrimaryRx OBJECT-TYPE
        SYNTAX    INTEGER
        {
         other (1),
         on    (2),
         off   (3)
        }
        ACCESS    read-only
        STATUS    mandatory
        DESCRIPTION
        "Indicates the Primary fiber Receive status
         2 - Receive On
         3 - Receive Off"
        ::= { oaLdRedundantOpticEntry 4 }

oaLdRedOptSecondaryRx OBJECT-TYPE
        SYNTAX    INTEGER
        {
         other (1),
         on    (2),
         off   (3)
        }
        ACCESS    read-only
        STATUS    mandatory
        DESCRIPTION
        "Indicates the Secondary fiber Receive status
         2 - Receive On
         3 - Receive Off"
        ::= { oaLdRedundantOpticEntry 5 }

------------------------------------------------------------------------------
-- OADWDM-MIB - define the card's ports Status;
------------------------------------------------------------------------------

oaLdCardPortsStatTable OBJECT-TYPE
        SYNTAX    SEQUENCE OF OaLdCardPortsStatEntry
        ACCESS    not-accessible
        STATUS    mandatory
        DESCRIPTION
        "Table of installed Lambda Driver Cards with more then one port"
        ::= {oaLdCardPortsStat 1}

oaLdCardPortsStatEntry OBJECT-TYPE
        SYNTAX    OaLdCardPortsStatEntry
        ACCESS    not-accessible
        STATUS    mandatory
        DESCRIPTION
        "Installed Lambda Driver Cards with more then one port"

        INDEX    { oaLdCardPortsSlotNumber, oaLdCardPortsPortNumber }

        ::= { oaLdCardPortsStatTable 1 }

OaLdCardPortsStatEntry ::= SEQUENCE {
        oaLdCardPortsSlotNumber       INTEGER,
        oaLdCardPortsPortNumber       INTEGER,
        oaLdCardPortsLink             INTEGER,
        oaLdCardPortsActivity         INTEGER,
        oaLdCardPortsWaveLength       INTEGER,
        oaLdCardPortsLoopBack         INTEGER,
        oaLdCardPortsCounters         INTEGER,
        oaLdCardPortsCounter1Low      Counter,
        oaLdCardPortsCounter1High     Counter,
        oaLdCardPortsCounter2Low      Counter,
        oaLdCardPortsCounter2High     Counter,
        oaLdCardPortsConnectorType    INTEGER,
        oaLdCardPortsConnectorSubType INTEGER,
        oaLdCardPortsRate             RateMode,
        oaLdCardPortsLineLength       INTEGER,
        oaLdCardPortsAccessLinState   INTEGER,
        oaLdCardPortsFlowControlMode  INTEGER,
        oaLdCardPortsDryContactStat   INTEGER,
        oaLdCardPortsPowerTuning      INTEGER,
        oaLdCardPortsMediaType        INTEGER,
        oaLdCardPortsEMCfgOperation   INTEGER,
        oaLdCardPortsEyemaxState      INTEGER,
        oaLdCardPortsEyemaxOperFactor INTEGER,
        oaLdCardPortsEyemaxAdminFactor INTEGER,
        oaLdCardPortsFefMode          INTEGER,
        oaLdCardPortsOdu1Index        INTEGER,
        oaLdCardPortsOdu1TsIndex      INTEGER,
        oaLdCardPortsPmMode           INTEGER,
        oaLdCardPortsFecMode          INTEGER,
        oaLdCardPortsLock             INTEGER,
        oaLdCardPortsLaserMode        INTEGER,
        oaLdCardPortsOdu1TsSize       INTEGER,
        oaLdCardPortsSpeed            INTEGER,
        oaLdCardPortsPriorityClockSource INTEGER,
        oaLdCardPortsActionMode       INTEGER,
        oaLdCardPortsOutputPortId     INTEGER,
        oaLdCardPortsGroupId          INTEGER,
        oaLdCardPortsChannelId        INTEGER,
        oaLdCardPortsAutoShutdownMode INTEGER,
        oaLdCardPortsEymxScnAmpFctr   INTEGER,
        oaLdCardPortsEymxScnAmpFctrMin INTEGER,
        oaLdCardPortsEymxScnAmpFctrMax INTEGER,
        oaLdCardPortsEymxScnDspComps  INTEGER,
        oaLdCardPortsEymxScnTreshold  INTEGER,
        oaLdCardPortsEymxScnOperComplt INTEGER,
        oaLdCardPortsEymxScnResult   DisplayString
       }

oaLdCardPortsSlotNumber OBJECT-TYPE
        SYNTAX    INTEGER
        ACCESS    read-only
        STATUS    mandatory
        DESCRIPTION
        "The slot#. An index from 1 to The number of slots"
        ::= { oaLdCardPortsStatEntry 1 }

oaLdCardPortsPortNumber OBJECT-TYPE
        SYNTAX    INTEGER
        ACCESS    read-only
        STATUS    mandatory
        DESCRIPTION
        "The port#. An index from 1 to The number of ports"
        ::= { oaLdCardPortsStatEntry 2 }

oaLdCardPortsLink OBJECT-TYPE
        SYNTAX    INTEGER
        {
         other     (1),
         on        (2),
         off       (3)
        }
        ACCESS    read-only
        STATUS    mandatory
        DESCRIPTION
        "Indicates the link status of the port
         2 - link on
         3 - link off"
        ::= { oaLdCardPortsStatEntry 3 }

oaLdCardPortsActivity OBJECT-TYPE
        SYNTAX    INTEGER
        {
         other     (1),
         on        (2),
         off       (3)
        }
        ACCESS    read-only
        STATUS    mandatory
        DESCRIPTION
        "Indicates the activety status of the port
         2 - activety on
         3 - activety off"
        ::= { oaLdCardPortsStatEntry 4 }

oaLdCardPortsWaveLength   OBJECT-TYPE
        SYNTAX  INTEGER
        ACCESS  read-only
        STATUS  mandatory
        DESCRIPTION
        "The port laser wavelength (Lambda channel) in units of nm (Nanometer).
         Returns 0 when not applicable "
        ::= { oaLdCardPortsStatEntry 6 }

oaLdCardPortsLoopBack OBJECT-TYPE
        SYNTAX  INTEGER
        {
         other                          (1),
         normal                         (2),
         remoteLoopback                 (3),
         localLoopback                  (4),
         lineLoopbackEnable             (5),
         diagnosticLoopbackEnable       (6)
        }
        ACCESS  read-write
        STATUS  mandatory
        DESCRIPTION
        "Transponder LoopBack state.
         Indicates the transponder LoopBack state.
         2 - normal             - Transponder card is in non-loopback state
         3 - remoteLoopback     - Transponder card is in remote loopback state
         4 - localLoopback      - Transponder card is in local loopback state
         5 - lineLoopbackEnable       - OCM module is in (LLEB)
                                        line loopback enable state
         6 - diagnosticLoopbackEnable - OCM module is in (DLEB)
                                        diagnostic loopback enablestate
         "
        ::= { oaLdCardPortsStatEntry 8 }

oaLdCardPortsCounters OBJECT-TYPE
        SYNTAX  INTEGER
        {
         notSupported  (1),
         supported     (2),
         clearCounters (3),
         extendedCounters (4)
        }
        ACCESS  read-write
        STATUS  mandatory
        DESCRIPTION
        "When read :
         1 - Counter feature is NOT supported
         2 - Counter feature is supported
         4 - Extended ethernet counters are supported
         When write:
         3 - Clear all port conters "
        ::= { oaLdCardPortsStatEntry 12 }

oaLdCardPortsCounter1Low OBJECT-TYPE
        SYNTAX  Counter
        ACCESS  read-only
        STATUS  mandatory
        DESCRIPTION
        "The number of bytes received at the port.
         This object returns the least significant 32 bits of a 64 bits counter.
         To calculate the actual counter reading, use the following formula:
         oaLdCardPortsCounter1High *  (2^32) + oaLdCardPortsCounter1Low."
        ::= { oaLdCardPortsStatEntry 14 }

oaLdCardPortsCounter1High OBJECT-TYPE
        SYNTAX  Counter
        ACCESS  read-only
        STATUS  mandatory
        DESCRIPTION
        "The number of bytes received at the port.
         This object returns the most significant 32 bits of a 64 bits counter.
         To calculate the actual counter reading, use the following formula:
         oaLdCardPortsCounter1High *  (2^32) + oaLdCardPortsCounter1Low."
        ::= { oaLdCardPortsStatEntry 15 }

oaLdCardPortsCounter2Low OBJECT-TYPE
        SYNTAX  Counter
        ACCESS  read-only
        STATUS  mandatory
        DESCRIPTION
        "The number of error bytes received at the port.
         This object returns the least significant 32 bits of a 64 bits counter.
         To calculate the actual counter reading, use the following formula:
         oaLdCardPortsCounter2High *  (2^32) + oaLdCardPortsCounter2Low."
        ::= { oaLdCardPortsStatEntry 17 }

oaLdCardPortsCounter2High OBJECT-TYPE
        SYNTAX  Counter
        ACCESS  read-only
        STATUS  mandatory
        DESCRIPTION
        "The number of error bytes received at the port.
         This object returns the most significant 32 bits of a 64 bits counter.
         To calculate the actual counter reading, use the following formula:
         oaLdCardPortsCounter2High *  (2^32) + oaLdCardPortsCounter2Low."
        ::= { oaLdCardPortsStatEntry 18 }

oaLdCardPortsConnectorType OBJECT-TYPE
        SYNTAX    INTEGER
        {
         other  (1),
         static (2),
         gbic   (3),
         sfp    (4),
         xfp    (5),
         xfpe   (6),
         cfp    (7)
        }
        ACCESS    read-only
        STATUS    mandatory
        DESCRIPTION
        "Port Connector Types:
         other - 1 - Unknown type of connector
         static- 2 - Not Changeable (fix) type of connector
         gbic  - 3 - GBIC type of connector
         sfp   - 4 - SFP  type of connector
         xfp   - 5 - XFP  type of connector
         xfpe  - 6 - XFPE type of connector
         cfp   - 7 - CFP  type of connector"
        ::= { oaLdCardPortsStatEntry 20 }

oaLdCardPortsConnectorSubType OBJECT-TYPE
        SYNTAX    INTEGER
        {
         other    (1),
         rj45     (2),
         sc       (3),
         lc       (4),
         mtrj     (5),
         vf       (6),
         mu       (7),
         miniCoax (8),
         mdiCx    (9),
         bnc      (10),
         mpo      (11)
        }
        ACCESS    read-only
        STATUS    mandatory
        DESCRIPTION
        "Port Connector Physical Sub Type:
         other   -1 - Unknown or N/A Connector's connectivity Type
         rj45    -2 - Copper RJ45
         sc      -3 - Regular Fibre Optic [FO]
         lc      -4 - LC
         mtrj    -5 - MT-RJ
         vf      -6 - VF
         mu      -7 - MU
         miniCoax-8 - mini Coaxical Connector
         mdiCx   -9 - SFF-8470 MDI Connector
         bnc     -10- BNC (Bayonet Neil-Concelman Connector)
         mpo     -11- MPO (Multiple-Fibre PushOn/Pull-off)"
        ::= { oaLdCardPortsStatEntry 21 }

oaLdCardPortsRate OBJECT-TYPE
        SYNTAX    RateMode
        ACCESS    read-write
        STATUS    mandatory
        DESCRIPTION
        ""
        ::= { oaLdCardPortsStatEntry 22 }

oaLdCardPortsLineLength OBJECT-TYPE
        SYNTAX    INTEGER
        {
         other        (1),
         from0to133   (2),
         from133to266 (3),
         from266to399 (4),
         from399to533 (5),
         from533to655 (6)
        }
        ACCESS    read-write
        STATUS    mandatory
        DESCRIPTION
        "T1 ports line length:
         other        - 1 - Unknown line length
         from0to133   - 2 - line length 0 - 133 ft. (0.6 dB)
         from133to266 - 3 - line length 133 - 266 ft. (1.2 dB)
         from266to399 - 4 - line length 266 - 399 ft. (1.8 dB)
         from399to533 - 5 - line length 399 - 533 ft. (2.4 dB)
         from533to655 - 6 - line length 533 - 655 ft. (3.0 dB)"
        ::= { oaLdCardPortsStatEntry 23 }

oaLdCardPortsAccessLinState    OBJECT-TYPE
        SYNTAX  INTEGER
        {
         other   (1),
         enable  (2),
         disable (3)
        }
        ACCESS  read-write
        STATUS  mandatory
        DESCRIPTION
        "Port LIN status.
         Indicates the Port access LIN status.
         2 - Enable  - Access LIN is enabled
         3 - Disable - Access LIN is disabled"
        ::= { oaLdCardPortsStatEntry 24 }

oaLdCardPortsFlowControlMode    OBJECT-TYPE
        SYNTAX  INTEGER
        {
         other   (1),
         enable  (2),
         disable (3)
        }
        ACCESS  read-write
        STATUS  mandatory
        DESCRIPTION
        "Module Flow Control Mode.
         Indicates the flow control mode for 10GbE access.
         2 - Enable  - Flow Control is enabled
         3 - Disable - Flow Control is disabled"
        ::= { oaLdCardPortsStatEntry 25 }

oaLdCardPortsDryContactStat  OBJECT-TYPE
        SYNTAX  INTEGER
        {
         other   (1),
         open    (2),
         close   (3)
        }
        ACCESS  read-only
        STATUS  mandatory
        DESCRIPTION
        "Port Dry Contact State.
         Indicates the Port Dry Contact State.
         2 - open  - Dry Contact is open
         3 - close - Dry Contact is close"
        ::= { oaLdCardPortsStatEntry 26 }

oaLdCardPortsPowerTuning  OBJECT-TYPE
        SYNTAX  INTEGER (-10..10)
        ACCESS  read-write
        STATUS  mandatory
        DESCRIPTION
        "Port Power Tuning in dB of the E&M signal.
         (20) is returned if this value is undefined."
        ::= { oaLdCardPortsStatEntry 27 }

oaLdCardPortsMediaType  OBJECT-TYPE
        SYNTAX  INTEGER
        {
         other   (1),
         copper  (2),
         fiber   (3)
        }
        ACCESS  read-only
        STATUS  mandatory
        DESCRIPTION
        "Type of Media."
        ::= { oaLdCardPortsStatEntry 28 }

oaLdCardPortsEMCfgOperation  OBJECT-TYPE
        SYNTAX  INTEGER
        {
         other     (1),
         twoWires  (2),
         fourWires (3)
        }
        ACCESS  read-write
        STATUS  mandatory
        DESCRIPTION
        "Specify the operation of the E&M signal.
         twoWires  - 2-wire operation.
         fourWires - 4-wire operation."
        ::= { oaLdCardPortsStatEntry 29 }

oaLdCardPortsEyemaxState    OBJECT-TYPE
        SYNTAX  INTEGER
        {
         other                 (1),
         disable               (2),
         enable                (3),
         scanning              (4),
         tracking              (5),
         calibrating           (6),
         stopTracking          (7)
        }
        ACCESS  read-write
        STATUS  mandatory
        DESCRIPTION
        "EyeMax state mode, (applicable only for ports that support this (EYEMAX) features)
         other - Port does not support this feature,
         disable - no Eyemax mode,
         scanning - start scan process,
         tracking - start tracking process,
         calibrating - set the 'oaLdCardPortsEyemaxAdminFactor' value into DAC,
         stopTracking - stop track process."
        ::= { oaLdCardPortsStatEntry 30 }

oaLdCardPortsEyemaxOperFactor    OBJECT-TYPE
        SYNTAX  INTEGER (0..100)
        UNITS  "percent"
        ACCESS  read-only
        STATUS  mandatory
        DESCRIPTION
        "EyeMax Operational Calibrate factor, This value represents current DAC output.
         When this feature is not supported (0) is returned.
         Units: percent."
        ::= { oaLdCardPortsStatEntry 31 }

oaLdCardPortsEyemaxAdminFactor    OBJECT-TYPE
        SYNTAX  INTEGER (0..100)
        UNITS  "percent"
        ACCESS  read-write
        STATUS  mandatory
        DESCRIPTION
        "EyeMax Administrative Calibration factor, This value is represents
         the value to be set into DAC.
         After scan operation it holds the optimal value that should be set into DAC.
         Users are able to set any value (0-100%) in order to change DAC outputs.
         (0) is returned when this feature is not supported
         Units: percent."
        ::= { oaLdCardPortsStatEntry 32 }

oaLdCardPortsFefMode    OBJECT-TYPE
        SYNTAX  INTEGER
        {
         other   (1),
         enable  (2),
         disable (3)
        }
        ACCESS  read-write
        STATUS  mandatory
        DESCRIPTION
        "Port Far End Failure (FEF) Detection mode.
         2 - Enable  - FEF is enabled
         3 - Disable - FEF is disabled"
        ::= { oaLdCardPortsStatEntry 33 }

oaLdCardPortsOdu1Index    OBJECT-TYPE
        SYNTAX  INTEGER (0..4)
        ACCESS  read-write
        STATUS  mandatory
        DESCRIPTION
        "For clients that mapped into the OTN payload.
         Indicates the index of the OPU-1 payload area.
         0 - not supported, or client is not configured.
         1 - Client mapped into OPU-1 #1 payload area.
         2 - Client mapped into OPU-1 #2 payload area.
         3 - Client mapped into OPU-1 #3 payload area.
         4 - Client mapped into OPU-1 #4 payload area."
        ::= { oaLdCardPortsStatEntry 34 }

oaLdCardPortsOdu1TsIndex    OBJECT-TYPE
        SYNTAX  INTEGER (0..16)
        ACCESS  read-write
        STATUS  mandatory
        DESCRIPTION
        "For clients that mapped into the OTN payload.
         Indicates the tributary slot index among the 16 tributary slots,
         of the OPU-1 payload area.
         0      - not supported, or client is not configured.
         [1-16] - Tributary slot index."
        ::= { oaLdCardPortsStatEntry 35 }

oaLdCardPortsPmMode    OBJECT-TYPE
        SYNTAX  INTEGER
        {
         other   (1),
         enable  (2),
         disable (3)
        }
        ACCESS  read-write
        STATUS  mandatory
        DESCRIPTION
        "Port Performance Monitoring Mode.
         Indicates the Port Performance Monitoring mode.
         2 - Enable  - PM is enabled for this port
         3 - Disable - PM is disabled for tthis port"
        ::= { oaLdCardPortsStatEntry 36 }

oaLdCardPortsFecMode    OBJECT-TYPE
        SYNTAX  INTEGER
        {
         other   (1),
         g709	 (2),
         eFec    (3),
         byPass  (4),
         g9751i4 (5),
         g9751i7 (6),
         hFec-7  (7),
         zeroFec (8)
        }
        ACCESS  read-write
        STATUS  mandatory
        DESCRIPTION
        "The Forward Error Correction (FEC) mode which is used
         in the selected port.
         2 - g709 - Standard G.709 FEC mode.
         3 - eFec - Enhanced FEC proprietary mode.
         4 - byPass - Bypass FEC mode (no FEC).
         5 - g9751i4 - G.975.1 Annex I.4 enhanced FEC.
         6 - g9751i7 - G.975.1 Annex I.7 enhanced FEC."
        ::= { oaLdCardPortsStatEntry 37 }

oaLdCardPortsLock    OBJECT-TYPE
        SYNTAX  INTEGER
        {
         other     (1),
         locked    (2),
         notlocked (3)
        }
        ACCESS  read-only
        STATUS  mandatory
        DESCRIPTION
        "Port PLL lock mode.
         2 - locked     - PLL was locked,
         3 - notlocked  - PLL was not locked"
        ::= { oaLdCardPortsStatEntry 38 }

oaLdCardPortsLaserMode    OBJECT-TYPE
        SYNTAX  INTEGER
        {
         other   (1),
         enable  (2),
         disable (3)
        }
        ACCESS  read-write
        STATUS  mandatory
        DESCRIPTION
        "Port Laser Mode.
         Indicates the port laser mode.
         2 - Enable  - Laser is enabled
         3 - Disable - Laser is disabled (can not transmit)"
        ::= { oaLdCardPortsStatEntry 39 }

oaLdCardPortsOdu1TsSize    OBJECT-TYPE
        SYNTAX  INTEGER
        ACCESS  read-only
        STATUS  mandatory
        DESCRIPTION
        "For clients that mapped into the OTN payload.
         Indicates the number of tributary slots that are occupied by the client's rate.
         0 - not supported, or client is not configured."
        ::= { oaLdCardPortsStatEntry 40 }

oaLdCardPortsSpeed    OBJECT-TYPE
        SYNTAX  INTEGER
        {
         other            (1),
         autoNegotiation  (2),
         force            (3)
        }
        ACCESS  read-write
        STATUS  mandatory
        DESCRIPTION
        "Ports speed mode."
        ::= { oaLdCardPortsStatEntry 41 }

oaLdCardPortsPriorityClockSource    OBJECT-TYPE
        SYNTAX  INTEGER
        ACCESS  read-write
        STATUS  mandatory
        DESCRIPTION
        "Defines the port's priority in relation to the clock source.
        1 defines the highest priority index and the last port index
        defines the least prioritized port.
        The highest priority port if available is used as the clock source,
        when it is not available the 2-nd highest available port would be used
        as the clock source."
        ::= { oaLdCardPortsStatEntry 42 }

oaLdCardPortsActionMode    OBJECT-TYPE
        SYNTAX  INTEGER
        {
         none        (1),
         add         (2),
         drop        (3),
         addAndDrop  (4)
        }
        ACCESS  read-write
        STATUS  mandatory
        DESCRIPTION
        ""
        ::= { oaLdCardPortsStatEntry 43 }

oaLdCardPortsOutputPortId  OBJECT-TYPE
        SYNTAX  INTEGER
        ACCESS  read-write
        STATUS  mandatory
        DESCRIPTION
        ""
        ::= { oaLdCardPortsStatEntry 44 }

oaLdCardPortsGroupId  OBJECT-TYPE
        SYNTAX  INTEGER
        ACCESS  read-write
        STATUS  mandatory
        DESCRIPTION
        ""
        ::= { oaLdCardPortsStatEntry 45 }

oaLdCardPortsChannelId  OBJECT-TYPE
        SYNTAX  INTEGER
        ACCESS  read-write
        STATUS  mandatory
        DESCRIPTION
        ""
        ::= { oaLdCardPortsStatEntry 46 }

oaLdCardPortsAutoShutdownMode    OBJECT-TYPE
        SYNTAX  INTEGER
        {
         other   (1),
         enable  (2),
         disable (3)
        }
        ACCESS  read-write
        STATUS  mandatory
        DESCRIPTION
        "Port Auto Shutdown Mode.
         Indicates the port Auto Shutdown (eye safe) mode.
         2 - Enable  - Auto Shutdown mode is enabled
         3 - Disable - Auto Shutdown mode is disabled."
        ::= { oaLdCardPortsStatEntry 47 }

oaLdCardPortsEymxScnAmpFctr    OBJECT-TYPE
        SYNTAX  INTEGER
        ACCESS  read-write
        STATUS  mandatory
        DESCRIPTION
        "Initialization value for Amlification Factor used
         in the Eyemax scanning operation in 0.1 units."
        ::= { oaLdCardPortsStatEntry 48 }

oaLdCardPortsEymxScnAmpFctrMin    OBJECT-TYPE
        SYNTAX  INTEGER
        ACCESS  read-only
        STATUS  mandatory
        DESCRIPTION
        "Minimum value that can be set for
         Initialization of the Amlification Factor used
         in the Eyemax scanning operation in 0.1 units."
        ::= { oaLdCardPortsStatEntry 49 }

oaLdCardPortsEymxScnAmpFctrMax    OBJECT-TYPE
        SYNTAX  INTEGER
        ACCESS  read-only
        STATUS  mandatory
        DESCRIPTION
        "Maximum value that can be set for
         Initialization of the Amlification Factor used
         in the Eyemax scanning operation in 0.1 units."
        ::= { oaLdCardPortsStatEntry 50 }

oaLdCardPortsEymxScnDspComps    OBJECT-TYPE
        SYNTAX  INTEGER
        ACCESS  read-write
        STATUS  mandatory
        DESCRIPTION
        "Initialization value for Dispersion Compensation
         used in the Eyemax scanning operation."
        ::= { oaLdCardPortsStatEntry 51 }

oaLdCardPortsEymxScnTreshold    OBJECT-TYPE
        SYNTAX  INTEGER (0..100)
        UNITS  "percent"
        ACCESS  read-write
        STATUS  mandatory
        DESCRIPTION
        "Initialization value for Rx threshold
         used in the Eyemax scanning operation."
        ::= { oaLdCardPortsStatEntry 52 }

oaLdCardPortsEymxScnOperComplt    OBJECT-TYPE
        SYNTAX  INTEGER (0..100)
        UNITS  "percent"
        ACCESS  read-only
        STATUS  mandatory
        DESCRIPTION
        "Indication how much of the scanning operation
         have been already completed (in percents 0 - 100)."
        ::= { oaLdCardPortsStatEntry 53 }

oaLdCardPortsEymxScnResult    OBJECT-TYPE
        SYNTAX  DisplayString
        ACCESS  read-only
        STATUS  mandatory
        DESCRIPTION
        "Indication if the scanning operation ended
         properly or finished with problems."
        ::= { oaLdCardPortsStatEntry 54 }

------------------------------------------------------------------------------
-- OADWDM-MIB - define the ADC / ADCD and MUX /
--              DMUX cards Lambda information
------------------------------------------------------------------------------

oaLdAdcCardInfoTable OBJECT-TYPE
        SYNTAX    SEQUENCE OF OaLdAdcCardInfoEntry
        ACCESS    not-accessible
        STATUS    mandatory
        DESCRIPTION
        "Table of installed Lambda Driver ADC / ADCD and MUX / DMUX Cards"
        ::= {oaLdAdcCardInfo 2}

oaLdAdcCardInfoEntry OBJECT-TYPE
        SYNTAX    OaLdAdcCardInfoEntry
        ACCESS    not-accessible
        STATUS    mandatory
        DESCRIPTION
        "Installed Lambda Driver ADC / ADCD and MUX / DMUX Cards"

        INDEX    { oaLdAdcCardSlotNumber }

        ::= { oaLdAdcCardInfoTable 1 }

OaLdAdcCardInfoEntry ::= SEQUENCE {
        oaLdAdcCardSlotNumber       INTEGER,
        oaLdAdcCardNumberOfPorts    INTEGER,
        oaLdAdcCardWdmWaveLength    INTEGER,
        oaLdAdcCardCardType         INTEGER,
        oaLdAdcCardSpacing          INTEGER,
        oaLdAdcCardSubBand          INTEGER,
        oaLdAdcCardChannelsPerPort  INTEGER
       }

oaLdAdcCardSlotNumber OBJECT-TYPE
        SYNTAX    INTEGER
        ACCESS    read-only
        STATUS    mandatory
        DESCRIPTION
        "The slot#. An index from 1 to The number of slots"
        ::= { oaLdAdcCardInfoEntry 1 }

oaLdAdcCardNumberOfPorts  OBJECT-TYPE
        SYNTAX  INTEGER
        ACCESS  read-only
        STATUS  mandatory
        DESCRIPTION
        "Number of ports at ADC / ADCD and MUX / DMUX card.
         For MUX / DMUX card the object returns the number of
         channels at card.
         Value = 0 says, that ADC / ADCD and MUX / DMUX cards
         Table is not supported."
        ::= { oaLdAdcCardInfoEntry 2 }

oaLdAdcCardWdmWaveLength OBJECT-TYPE
        SYNTAX  INTEGER
        {
         other     (1),
         cwdm      (2),
         dwdm      (3)
        }
        ACCESS  read-only
        STATUS  mandatory
        DESCRIPTION
        "WDM Wave Length at ADC / ADCD and MUX / DMUX card. (CWDM or DWDM)"
        ::= { oaLdAdcCardInfoEntry 3 }

oaLdAdcCardCardType OBJECT-TYPE
        SYNTAX  INTEGER
        {
         other     (1),
         adc       (2),
         adcd      (3),
         mux       (4),
         dmux      (5),
         muxDmux   (6)
        }
        ACCESS  read-only
        STATUS  mandatory
        DESCRIPTION
        "WDM Card Type."
        ::= { oaLdAdcCardInfoEntry 4 }

oaLdAdcCardSpacing OBJECT-TYPE
        SYNTAX  INTEGER
        {
         other     (1),
         g50       (2),
         g100      (3),
         g200      (4)
        }
        ACCESS  read-only
        STATUS  mandatory
        DESCRIPTION
        "MUX / DMUX card - steps in channel spacing (in GHz)
         according to ITU-T."
        ::= { oaLdAdcCardInfoEntry 5 }

oaLdAdcCardSubBand OBJECT-TYPE
        SYNTAX  INTEGER
        {
         other      (1),
         red        (2),
         blue       (3),
         redAndBlue (4)
        }
        ACCESS  read-only
        STATUS  mandatory
        DESCRIPTION
        "MUX / DMUX card sub-band.
         Note: according to oaLdAdcCardSpacing and oaLdAdcCardSubBand
         it is able to know each channel wavelength."
        ::= { oaLdAdcCardInfoEntry 6 }

oaLdAdcCardChannelsPerPort  OBJECT-TYPE
        SYNTAX  INTEGER
        ACCESS  read-only
        STATUS  mandatory
        DESCRIPTION
        "Number of channels per port at OADM-XX / BS-XX card.
         For ADC / ADCD / MUX / DMUX card the object returns 1."
        ::= { oaLdAdcCardInfoEntry 7 }

------------------------------------------------------------------------------
-- OADWDM-MIB - define the ADC / ADCD cards
--              Lambda Ports information
------------------------------------------------------------------------------

oaLdAdcCardPortsInfoTable OBJECT-TYPE
        SYNTAX    SEQUENCE OF OaLdAdcCardPortsInfoEntry
        ACCESS    not-accessible
        STATUS    mandatory
        DESCRIPTION
        "Table of installed Lambda Driver ADC and ADCD Cards"
        ::= {oaLdAdcCardInfo 4}

oaLdAdcCardPortsInfoEntry OBJECT-TYPE
        SYNTAX    OaLdAdcCardPortsInfoEntry
        ACCESS    not-accessible
        STATUS    mandatory
        DESCRIPTION
        "Installed Lambda Driver ADC and ADCD Cards"

        INDEX    { oaLdAdcCardPortsSlotNumber, oaLdAdcCardPortsPortNumber }

        ::= { oaLdAdcCardPortsInfoTable 1 }

OaLdAdcCardPortsInfoEntry ::= SEQUENCE {
        oaLdAdcCardPortsSlotNumber     INTEGER,
        oaLdAdcCardPortsPortNumber     INTEGER,
        oaLdAdcCardPortsLambdaCh       LambdaCh
       }

oaLdAdcCardPortsSlotNumber OBJECT-TYPE
        SYNTAX    INTEGER
        ACCESS    read-only
        STATUS    mandatory
        DESCRIPTION
        "The slot#. An index from 1 to The number of slots"
        ::= { oaLdAdcCardPortsInfoEntry 1 }

oaLdAdcCardPortsPortNumber OBJECT-TYPE
        SYNTAX    INTEGER
        ACCESS    read-only
        STATUS    mandatory
        DESCRIPTION
        "The port#. An index from 1 to The number of ports"
        ::= { oaLdAdcCardPortsInfoEntry 2 }

oaLdAdcCardPortsLambdaCh   OBJECT-TYPE
        SYNTAX  LambdaCh
        ACCESS  read-only
        STATUS  mandatory
        DESCRIPTION
        "The Card port's Lambda channel"
        ::= { oaLdAdcCardPortsInfoEntry 3 }

------------------------------------------------------------------------------
-- OADWDM-MIB - define the Card Channels information
------------------------------------------------------------------------------

oaLdCardChannelCfgTable OBJECT-TYPE
        SYNTAX    SEQUENCE OF OaLdCardChannelCfgEntry
        ACCESS    not-accessible
        STATUS    mandatory
        DESCRIPTION
        "Table of Lambda Driver Card Channels configuration."
        ::= {oaLdCardChannelInfo 2}

oaLdCardChannelCfgEntry OBJECT-TYPE
        SYNTAX    OaLdCardChannelCfgEntry
        ACCESS    not-accessible
        STATUS    mandatory
        DESCRIPTION
        "Lambda Driver Card Channels configuration Entry."

        INDEX    { oaLdCardChSlotId, oaLdCardChGroupId, oaLdCardChChannelId }

        ::= { oaLdCardChannelCfgTable 1 }

OaLdCardChannelCfgEntry ::= SEQUENCE {
        oaLdCardChSlotId        INTEGER,
        oaLdCardChGroupId       INTEGER,
        oaLdCardChChannelId     INTEGER,
        oaLdCardChOdu1Index     INTEGER,
        oaLdCardChOdu1TsIndex   INTEGER,
        oaLdCardChOdu1TsSize    INTEGER,
        oaLdCardChRate          RateMode
       }

oaLdCardChSlotId    OBJECT-TYPE
        SYNTAX    INTEGER
        ACCESS    read-only
        STATUS    mandatory
        DESCRIPTION
        "The slot#. An index from 1 to The number of slots."
        ::= { oaLdCardChannelCfgEntry 1 }

oaLdCardChGroupId    OBJECT-TYPE
        SYNTAX    INTEGER
        ACCESS    read-only
        STATUS    mandatory
        DESCRIPTION
        "."
        ::= { oaLdCardChannelCfgEntry 2 }

oaLdCardChChannelId    OBJECT-TYPE
        SYNTAX    INTEGER (1..64)
        ACCESS    read-only
        STATUS    mandatory
        DESCRIPTION
        "."
        ::= { oaLdCardChannelCfgEntry 3 }

oaLdCardChOdu1Index    OBJECT-TYPE
        SYNTAX  INTEGER (0..4)
        ACCESS  read-write
        STATUS  mandatory
        DESCRIPTION
        "For clients that mapped into the OTN payload.
         Indicates the index of the OPU-1 payload area.
         0 - not supported, or client is not configured.
         1 - Client mapped into OPU-1 #1 payload area.
         2 - Client mapped into OPU-1 #2 payload area.
         3 - Client mapped into OPU-1 #3 payload area.
         4 - Client mapped into OPU-1 #4 payload area."
        ::= { oaLdCardChannelCfgEntry 4 }

oaLdCardChOdu1TsIndex    OBJECT-TYPE
        SYNTAX  INTEGER (0..16)
        ACCESS  read-write
        STATUS  mandatory
        DESCRIPTION
        "For clients that mapped into the OTN payload.
         Indicates the tributary slot index among the 16 tributary slots,
         of the OPU-1 payload area.
         0      - not supported, or client is not configured.
         [1-16] - Tributary slot index."
        ::= { oaLdCardChannelCfgEntry 5 }

oaLdCardChOdu1TsSize    OBJECT-TYPE
        SYNTAX  INTEGER
        ACCESS  read-write
        STATUS  mandatory
        DESCRIPTION
        "For clients that mapped into the OTN payload.
         Indicates the number of tributary slots that are occupied by the client's rate.
         0 - not supported, or client is not configured."
        ::= { oaLdCardChannelCfgEntry 6 }

oaLdCardChRate OBJECT-TYPE
        SYNTAX    RateMode
        ACCESS    read-write
        STATUS    mandatory
        DESCRIPTION
        ""
        ::= { oaLdCardChannelCfgEntry 7 }

------------------------------------------------------------------------------
-- OADWDM-MIB - define the Optical Amplifier cards information
------------------------------------------------------------------------------

oaLdOAmplifierCardInfoTable OBJECT-TYPE
        SYNTAX    SEQUENCE OF OaLdOAmplifierCardInfoEntry
        ACCESS    not-accessible
        STATUS    mandatory
        DESCRIPTION
        "Table of installed Lambda Driver Optical Amplifier Cards"
        ::= {oaLdOAmplifierInfo 2}

oaLdOAmplifierCardInfoEntry OBJECT-TYPE
        SYNTAX    OaLdOAmplifierCardInfoEntry
        ACCESS    not-accessible
        STATUS    mandatory
        DESCRIPTION
        "Installed Lambda Driver Optical Amplifier Cards"

        INDEX    { oaLdOAmplifierCardSlotNumber }

        ::= { oaLdOAmplifierCardInfoTable 1 }

OaLdOAmplifierCardInfoEntry ::= SEQUENCE {
        oaLdOAmplifierCardSlotNumber        INTEGER,
        oaLdOAmplifierCardConfiguration     INTEGER,
        oaLdOAmplifierCardModuleType        INTEGER,
        oaLdOAmplifierCardHardwareVersion   DisplayString,
        oaLdOAmplifierCardSoftwareVersion   DisplayString,
        oaLdOAmplifierCardSerialNumber      DisplayString,
        oaLdOAmplifierCardTemperature       INTEGER,
        oaLdOAmplifierCardPSVoltage         INTEGER,
        oaLdOAmplifierCardPump1Current      INTEGER,
        oaLdOAmplifierCardPump1MaxCurrent   INTEGER,
        oaLdOAmplifierCardPump2Current      INTEGER,
        oaLdOAmplifierCardPump2MaxCurrent   INTEGER,
        oaLdOAmplifierCardInputPower        INTEGER,
        oaLdOAmplifierCardOutputPower       INTEGER,
        oaLdOAmplifierCardModuleGain        INTEGER,
        oaLdOAmplifierCardPump1Power        INTEGER,
        oaLdOAmplifierCardPump2Power        INTEGER,
        oaLdOAmplifierCardMaximumPower      INTEGER,
        oaLdOAmplifierCardRatedGain         INTEGER,
        oaLdOAmplifierCardAlarmStatus       OCTET STRING,
--
        oaLdOAmplifierCardAttributes        OCTET STRING,
--
        oaLdOAmplifierCardOperationMode     INTEGER,
        oaLdOAmplifierCardRunMode           INTEGER,
        oaLdOAmplifierCardAutoShutdownState INTEGER,
        oaLdOAmplifierCardInputThreshold    INTEGER,
        oaLdOAmplifierCardOutputThreshold   INTEGER,
        oaLdOAmplifierCardShutdownThreshold INTEGER,
        oaLdOAmplifierCardLowTempThreshold  INTEGER,
        oaLdOAmplifierCardHighTempThreshold INTEGER,
        oaLdOAmplifierCardPump1CurrentSet   INTEGER,
        oaLdOAmplifierCardPump2CurrentSet   INTEGER,
        oaLdOAmplifierCardOutputPowerSet    INTEGER,
        oaLdOAmplifierCardGainSet           INTEGER,
--
        oaLdOAmplifierCardPumpOutputPower   INTEGER,
        oaLdOAmplifierCardReflectedPower    INTEGER,
--
        oaLdOAmplifierCardBackReflRatio     INTEGER,
        oaLdOAmplifierCardBackReflThresh    INTEGER,
        oaLdOAmplifierCardAutoPowerReduction    INTEGER,
        oaLdOAmplifierCardOutputPumpPowerThresh INTEGER,
        oaLdOAmplifierCardCalibrationFactor INTEGER,
        oaLdOAmplifierCardTempAlarm         INTEGER,
        oaLdOAmplifierCardPump1Ratio        INTEGER
       }

oaLdOAmplifierCardSlotNumber OBJECT-TYPE
        SYNTAX    INTEGER
        ACCESS    read-only
        STATUS    mandatory
        DESCRIPTION
        "The slot#. An index from 1 to The number of slots"
        ::= { oaLdOAmplifierCardInfoEntry 1 }

oaLdOAmplifierCardConfiguration   OBJECT-TYPE
        SYNTAX  INTEGER
        {
         other      (1),
         singlePump (2),
         dualPump   (3),
         quadroPump (4)
        }
        ACCESS  read-only
        STATUS  mandatory
        DESCRIPTION
        "The Optical Amplifier Configuration"
        ::= { oaLdOAmplifierCardInfoEntry 2 }

oaLdOAmplifierCardModuleType   OBJECT-TYPE
        SYNTAX  INTEGER
        {
         other               (1),
         amplet              (2),
         bosterAmplifier     (3),
         lineAmplifier       (4),
         preAmplifier        (5),
         vgoaRamanAmplifier  (6),
         cBandRamanAmplifier (7)
        }
        ACCESS  read-only
        STATUS  mandatory
        DESCRIPTION
        "The Optical Amplifier Module Type"
        ::= { oaLdOAmplifierCardInfoEntry 3 }

oaLdOAmplifierCardHardwareVersion   OBJECT-TYPE
        SYNTAX  DisplayString (SIZE (0..16))
        ACCESS  read-only
        STATUS  mandatory
        DESCRIPTION
        "The Optical Amplifier Module Hardware Version"
        ::= { oaLdOAmplifierCardInfoEntry 4 }

oaLdOAmplifierCardSoftwareVersion   OBJECT-TYPE
        SYNTAX  DisplayString (SIZE (0..16))
        ACCESS  read-only
        STATUS  mandatory
        DESCRIPTION
        "The Optical Amplifier Module Software Version"
        ::= { oaLdOAmplifierCardInfoEntry 5 }

oaLdOAmplifierCardSerialNumber   OBJECT-TYPE
        SYNTAX  DisplayString (SIZE (0..16))
        ACCESS  read-only
        STATUS  mandatory
        DESCRIPTION
        "The Optical Amplifier Module Serial Number"
        ::= { oaLdOAmplifierCardInfoEntry 6 }

oaLdOAmplifierCardTemperature   OBJECT-TYPE
        SYNTAX  INTEGER
        ACCESS  read-only
        STATUS  mandatory
        DESCRIPTION
        "The Optical Amplifier Module Temperature
         (in units of 1/10 Degrees Celsius [0.1 C])"
        ::= { oaLdOAmplifierCardInfoEntry 7 }

oaLdOAmplifierCardPSVoltage   OBJECT-TYPE
        SYNTAX  INTEGER
        ACCESS  read-only
        STATUS  mandatory
        DESCRIPTION
        "The Optical Amplifier Power Supply Voltage
         (in units of 1/100 Volts [0.01 V])"
        ::= { oaLdOAmplifierCardInfoEntry 8 }

oaLdOAmplifierCardPump1Current   OBJECT-TYPE
        SYNTAX  INTEGER
        ACCESS  read-only
        STATUS  mandatory
        DESCRIPTION
        "The Optical Amplifier Pump 1 Current
         (in units of 1/10 milliamperes [0.1 mA])"
        ::= { oaLdOAmplifierCardInfoEntry 9 }

oaLdOAmplifierCardPump1MaxCurrent   OBJECT-TYPE
        SYNTAX  INTEGER
        ACCESS  read-only
        STATUS  mandatory
        DESCRIPTION
        "The Optical Amplifier Pump 1 Maximum Current
         (in units of 1/10 milliamperes [0.1 mA])"
        ::= { oaLdOAmplifierCardInfoEntry 10 }

oaLdOAmplifierCardPump2Current   OBJECT-TYPE
        SYNTAX  INTEGER
        ACCESS  read-only
        STATUS  mandatory
        DESCRIPTION
        "The Optical Amplifier Pump 2 Current
         (in units of 1/10 milliamperes [0.1 mA])"
        ::= { oaLdOAmplifierCardInfoEntry 11 }

oaLdOAmplifierCardPump2MaxCurrent   OBJECT-TYPE
        SYNTAX  INTEGER
        ACCESS  read-only
        STATUS  mandatory
        DESCRIPTION
        "The Optical Amplifier Pump 2 Maximum Current
         (in units of 1/10 milliamperes [0.1 mA])"
        ::= { oaLdOAmplifierCardInfoEntry 12 }

oaLdOAmplifierCardInputPower   OBJECT-TYPE
        SYNTAX  INTEGER
        ACCESS  read-only
        STATUS  mandatory
        DESCRIPTION
        "The Optical Amplifier Input Optical Power
         (in units of 1/100 [0.01 dBm])"
        ::= { oaLdOAmplifierCardInfoEntry 13 }

oaLdOAmplifierCardOutputPower   OBJECT-TYPE
        SYNTAX  INTEGER
        ACCESS  read-only
        STATUS  mandatory
        DESCRIPTION
        "The Optical Amplifier Output Optical Power
         (in units of 1/100 [0.01 dBm])"
        ::= { oaLdOAmplifierCardInfoEntry 14 }

oaLdOAmplifierCardModuleGain   OBJECT-TYPE
        SYNTAX  INTEGER
        ACCESS  read-only
        STATUS  mandatory
        DESCRIPTION
        "The Optical Amplifier Optical Module Gain
         (in units of 1/100 [0.01 dB])"
        ::= { oaLdOAmplifierCardInfoEntry 15 }

oaLdOAmplifierCardPump1Power   OBJECT-TYPE
        SYNTAX  INTEGER
        ACCESS  read-only
        STATUS  mandatory
        DESCRIPTION
        "The Optical Amplifier Pump 1 Power
         (in units of 1/100 milliwatts [0.01 mW])"
        ::= { oaLdOAmplifierCardInfoEntry 16 }

oaLdOAmplifierCardPump2Power   OBJECT-TYPE
        SYNTAX  INTEGER
        ACCESS  read-only
        STATUS  mandatory
        DESCRIPTION
        "The Optical Amplifier Pump 2 Power
         (in units of 1/100 milliwatts [0.01 mW])"
        ::= { oaLdOAmplifierCardInfoEntry 17 }

oaLdOAmplifierCardMaximumPower   OBJECT-TYPE
        SYNTAX  INTEGER
        ACCESS  read-only
        STATUS  mandatory
        DESCRIPTION
        "The Optical Amplifier Optical Maximum Power
         (in units of 1/100 [0.01 dBm])"
        ::= { oaLdOAmplifierCardInfoEntry 18 }

oaLdOAmplifierCardRatedGain   OBJECT-TYPE
        SYNTAX  INTEGER
        ACCESS  read-only
        STATUS  mandatory
        DESCRIPTION
        "The Optical Amplifier Optical Rated Gain
         (in units of 1/100 [0.01 dB])"
        ::= { oaLdOAmplifierCardInfoEntry 19 }

oaLdOAmplifierCardAlarmStatus   OBJECT-TYPE
        SYNTAX  OCTET STRING  (SIZE(2))
        ACCESS  read-only
        STATUS  mandatory
        DESCRIPTION
        "The Optical Amplifier Alarms.
         This object is organised as a bit map. Each bit represents an alarm.
         If the object is zero - no alarm is active.
         0x0000 ('0000 0000 0000 0000'B) - Normal (No alarm)
         0x0001 ('0000 0000 0000 0001'B) - Optical Input alarm
         0x0002 ('0000 0000 0000 0010'B) - Optical Output alarm
         0x0004 ('0000 0000 0000 0100'B) - Optical Input 2 (Back Reflection alarm for module EM800-OAR12)
         0x0008 ('0000 0000 0000 1000'B) - Module Temperature alarm
         0x0010 ('0000 0000 0001 0000'B) - Pump Temperature
         0x0020 ('0000 0000 0010 0000'B) - Pump Drive Current alarm
         0x0040 ('0000 0000 0100 0000'B) - Power Supply Voltage alarm
         0x0080 ('0000 0000 1000 0000'B) - Auto-shutdown
         0x0100 ('0000 0001 0000 0000'B) - Reflected Power High alarm
         Any combination of the bits represent the combination of the alarms"

        ::= { oaLdOAmplifierCardInfoEntry 20 }

oaLdOAmplifierCardAttributes   OBJECT-TYPE
        SYNTAX  OCTET STRING  (SIZE(2))
        ACCESS  read-only
        STATUS  mandatory
        DESCRIPTION
        "The Optical Amplifier Attributes.
         This object is organised as a bit map. Each bit represents one existed attribute.
          0x0000 ('0000 0000 0000 0000'B) - No additional attributes
          0x0001 ('0000 0000 0000 0001'B) - Dispersion attribute is on
          0x0002 ('0000 0000 0000 0010'B) - Mid Stage attribute is on
          0x0004 ('0000 0000 0000 0100'B) - Tunable Gain attribute is on
          0x0008 ('0000 0000 0000 1000'B) - High Power attribute is on
          0x0010 ('0000 0000 0001 0000'B) - Double slots module is on
         Other bitmasks are reserved.
         Any combination of the bits represent the combination of the attributes"

        ::= { oaLdOAmplifierCardInfoEntry 25 }

oaLdOAmplifierCardOperationMode   OBJECT-TYPE
        SYNTAX  INTEGER
        {
         other               (1),
         constantCurrent     (2),
         constantPumpPower   (3),
         constantOutputPower (4),
         constantGain        (5)
        }
        ACCESS  read-write
        STATUS  mandatory
        DESCRIPTION
        "The Optical Amplifier Operational Mode"
        ::= { oaLdOAmplifierCardInfoEntry 30 }

oaLdOAmplifierCardRunMode   OBJECT-TYPE
        SYNTAX  INTEGER
        {
         other         (1),
         start         (2),
         shutdownPower (3),
         eyeSafe       (4)
        }
        ACCESS  read-write
        STATUS  mandatory
        DESCRIPTION
        "The Optical Amplifier Run Mode"
        ::= { oaLdOAmplifierCardInfoEntry 31 }

oaLdOAmplifierCardAutoShutdownState   OBJECT-TYPE
        SYNTAX  INTEGER
        {
         other   (1),
         enable  (2),
         disable (3)
        }
        ACCESS  read-write
        STATUS  mandatory
        DESCRIPTION
        "The Optical Amplifier Auto Shutdown Status"
        ::= { oaLdOAmplifierCardInfoEntry 32 }

oaLdOAmplifierCardInputThreshold   OBJECT-TYPE
        SYNTAX  INTEGER
        ACCESS  read-write
        STATUS  mandatory
        DESCRIPTION
        "The Optical Amplifier Input Threshold
         (in units of 1/100 [0.01 dBm])"
        ::= { oaLdOAmplifierCardInfoEntry 33 }

oaLdOAmplifierCardOutputThreshold   OBJECT-TYPE
        SYNTAX  INTEGER
        ACCESS  read-write
        STATUS  mandatory
        DESCRIPTION
        "The Optical Amplifier Output Threshold
         (in units of 1/100 [0.01 dBm])"
        ::= { oaLdOAmplifierCardInfoEntry 34 }

oaLdOAmplifierCardShutdownThreshold   OBJECT-TYPE
        SYNTAX  INTEGER
        ACCESS  read-write
        STATUS  mandatory
        DESCRIPTION
        "The Optical Amplifier Shutdown Threshold
         (in units of 1/100 [0.01 dBm])"
        ::= { oaLdOAmplifierCardInfoEntry 35 }

oaLdOAmplifierCardLowTempThreshold   OBJECT-TYPE
        SYNTAX  INTEGER
        ACCESS  read-write
        STATUS  mandatory
        DESCRIPTION
        "The Optical Amplifier Low Temperature Threshold
         (in units of 1/10 Degrees Celsius [0.1 C])"
        ::= { oaLdOAmplifierCardInfoEntry 36 }

oaLdOAmplifierCardHighTempThreshold   OBJECT-TYPE
        SYNTAX  INTEGER
        ACCESS  read-write
        STATUS  mandatory
        DESCRIPTION
        "The Optical Amplifier High Temperature Threshold
         (in units of 1/10 Degrees Celsius [0.1 C])"
        ::= { oaLdOAmplifierCardInfoEntry 37 }

oaLdOAmplifierCardPump1CurrentSet   OBJECT-TYPE
        SYNTAX  INTEGER
        ACCESS  read-write
        STATUS  mandatory
        DESCRIPTION
        "The Optical Amplifier Pump 1 Current Setting
         (in units of 1/10 milliamperes [0.1 mA])"
        ::= { oaLdOAmplifierCardInfoEntry 38 }

oaLdOAmplifierCardPump2CurrentSet   OBJECT-TYPE
        SYNTAX  INTEGER
        ACCESS  read-write
        STATUS  mandatory
        DESCRIPTION
        "The Optical Amplifier Pump 2 Current Setting
        (in units of 1/10 milliamperes [0.1 mA])"
        ::= { oaLdOAmplifierCardInfoEntry 39 }

oaLdOAmplifierCardOutputPowerSet   OBJECT-TYPE
        SYNTAX  INTEGER
        ACCESS  read-write
        STATUS  mandatory
        DESCRIPTION
        "The Optical Amplifier Output Power Setting
         (in units of 1/100 [0.01 dBm])"
        ::= { oaLdOAmplifierCardInfoEntry 40 }

oaLdOAmplifierCardGainSet   OBJECT-TYPE
        SYNTAX  INTEGER
        ACCESS  read-write
        STATUS  mandatory
        DESCRIPTION
        "The Optical Amplifier Gain Setting
         (in units of 1/100 [0.01 dB]).
         For Raman12 module (EM800-OAR12) Estimated Raman Gain."
        ::= { oaLdOAmplifierCardInfoEntry 41 }

oaLdOAmplifierCardPumpOutputPower   OBJECT-TYPE
        SYNTAX  INTEGER
        ACCESS  read-only
        STATUS  mandatory
        DESCRIPTION
        "The C-Band Raman Amplifier Pump Output Power
         (in units of of 1/100 [0.01 dBm])"
        ::= { oaLdOAmplifierCardInfoEntry 42 }

oaLdOAmplifierCardReflectedPower   OBJECT-TYPE
        SYNTAX  INTEGER
        ACCESS  read-only
        STATUS  mandatory
        DESCRIPTION
        "The C-Band Raman Amplifier Reflected Pump Power
         (in units of 1/100 [0.01 dBm])"
        ::= { oaLdOAmplifierCardInfoEntry 43 }

oaLdOAmplifierCardBackReflRatio   OBJECT-TYPE
        SYNTAX  INTEGER
        ACCESS  read-only
        STATUS  mandatory
        DESCRIPTION
        "The Raman12 Back Reflection ratio between reflected and
         transmitted power (in units of 1/100 [0.01 dB])"
        ::= { oaLdOAmplifierCardInfoEntry 44 }

oaLdOAmplifierCardBackReflThresh   OBJECT-TYPE
        SYNTAX  INTEGER
        ACCESS  read-only
        STATUS  mandatory
        DESCRIPTION
        "The Raman12 Back Reflection Threshold
         (in units of 1/100 [0.01 dBm])"
        ::= { oaLdOAmplifierCardInfoEntry 45 }

oaLdOAmplifierCardAutoPowerReduction   OBJECT-TYPE
        SYNTAX  INTEGER
        {
         other   (1),
         enable  (2),
         disable (3)
        }
        ACCESS  read-only
        STATUS  mandatory
        DESCRIPTION
        "The Raman12 Auto Power Reduction (APR) Status
         in case of Back Reflection (BR) alarm.
         APR Enable means that the unit will mute its
         output power in case of BR alarm.
         APR Disable means that the unit will not mute its
         output power in case of BR alarm."
        ::= { oaLdOAmplifierCardInfoEntry 46 }

oaLdOAmplifierCardOutputPumpPowerThresh      OBJECT-TYPE
        SYNTAX  INTEGER
        ACCESS  read-write
        STATUS  mandatory
        DESCRIPTION
        "The Raman12 Output pump power Alarm Threshold
         (in units of 1/100 milliwatts [0.01 mW])"
        ::= { oaLdOAmplifierCardInfoEntry 47 }

oaLdOAmplifierCardCalibrationFactor      OBJECT-TYPE
        SYNTAX  INTEGER
        ACCESS  read-write
        STATUS  mandatory
        DESCRIPTION
        "The Raman12 calibration factor for Estimated Raman Gain.
         This coefficient is used to calculate the estimated Raman gain;
         default value = 0."
        ::= { oaLdOAmplifierCardInfoEntry 48 }

oaLdOAmplifierCardTempAlarm   OBJECT-TYPE
        SYNTAX  INTEGER
        {
         other   (1),
         enable  (2),
         disable (3)
        }
        ACCESS  read-write
        STATUS  mandatory
        DESCRIPTION
        "The Raman12 Shutdown status in case of module temperature alarm."
        ::= { oaLdOAmplifierCardInfoEntry 49 }

oaLdOAmplifierCardPump1Ratio      OBJECT-TYPE
        SYNTAX  INTEGER
        ACCESS  read-write
        STATUS  mandatory
        DESCRIPTION
        "The Raman12 pump 1 power ratio.
        Units: percent."
        ::= { oaLdOAmplifierCardInfoEntry 50 }

------------------------------------------------------------------------------
-- OADWDM-MIB - C-Band Raman Amplifier tables
--              Pumps Table
------------------------------------------------------------------------------
oaLdOAmplifierPumpInfoTable OBJECT-TYPE
        SYNTAX    SEQUENCE OF OaLdOAmplifierPumpInfoEntry
        ACCESS    not-accessible
        STATUS    mandatory
        DESCRIPTION
        "Table of installed Lambda Driver C-Band Raman Amplifier Pumps"
        ::= {oaLdOAmplifierInfo 3}

oaLdOAmplifierPumpInfoEntry OBJECT-TYPE
        SYNTAX    OaLdOAmplifierPumpInfoEntry
        ACCESS    not-accessible
        STATUS    mandatory
        DESCRIPTION
        "Installed Lambda Driver Optical Amplifier Pumps"

        INDEX    { oaLdOAmplifierCardSlotNumber, oaLdOAmplifierPumpNumber }

        ::= { oaLdOAmplifierPumpInfoTable 1 }

OaLdOAmplifierPumpInfoEntry ::= SEQUENCE {
         oaLdOAmplifierPumpNumber          INTEGER,
         oaLdOAmplifierPumpCurrent         INTEGER,
         oaLdOAmplifierPumpPower           INTEGER,
         oaLdOAmplifierPumpLaserTemp       INTEGER
        }

oaLdOAmplifierPumpNumber OBJECT-TYPE
        SYNTAX    INTEGER
        ACCESS    read-only
        STATUS    mandatory
        DESCRIPTION
        "The pump#. An index from 1 to The number of pumps"
        ::= { oaLdOAmplifierPumpInfoEntry  2}

oaLdOAmplifierPumpCurrent   OBJECT-TYPE
        SYNTAX  INTEGER
        ACCESS  read-only
        STATUS  mandatory
        DESCRIPTION
        "The C-Band Raman Amplifier Pump Drive Current
         (in units of mA)"
        ::= { oaLdOAmplifierPumpInfoEntry  3}

oaLdOAmplifierPumpPower   OBJECT-TYPE
        SYNTAX  INTEGER
        ACCESS  read-only
        STATUS  mandatory
        DESCRIPTION
        "The C-Band Raman Amplifier Pump Output Power
         (in units of mW)"
        ::= { oaLdOAmplifierPumpInfoEntry  4}

oaLdOAmplifierPumpLaserTemp   OBJECT-TYPE
        SYNTAX  INTEGER
        ACCESS  read-only
        STATUS  mandatory
        DESCRIPTION
        "The C-Band Raman Amplifier Pump Laser Temperature
         (in units of 1/10 [0.1 deg C])"
        ::= { oaLdOAmplifierPumpInfoEntry  5}

oaLdOAmplifierCompInterfaceCount OBJECT-TYPE
        SYNTAX    INTEGER
        ACCESS    read-only
        STATUS    mandatory
        DESCRIPTION
        "The number of modules in the system which are Optical Amplifier compatible."
        ::= {oaLdOAmplifierInfo 10}


------------------------------------------------------------------------------
-- OADWDM-MIB - defines the OCMs cards SONET/SDH ports status and
--              error counters.
------------------------------------------------------------------------------

oaLdOcmCardPortsInfoTable OBJECT-TYPE
        SYNTAX    SEQUENCE OF OaLdOcmCardPortsInfoEntry
        ACCESS    not-accessible
        STATUS    mandatory
        DESCRIPTION
        "Information table of installed OCM Cards"
        ::= {oaLdOcmCardInfo 2}

oaLdOcmCardPortsInfoEntry OBJECT-TYPE
        SYNTAX    OaLdOcmCardPortsInfoEntry
        ACCESS    not-accessible
        STATUS    mandatory
        DESCRIPTION
        "Installed OCM Cards"

        INDEX    { oaLdOcmCardPortsSlotNumber, oaLdOcmCardPortsPortNumber }

        ::= { oaLdOcmCardPortsInfoTable 1 }

OaLdOcmCardPortsInfoEntry ::= SEQUENCE {
        oaLdOcmCardPortsSlotNumber     INTEGER,
        oaLdOcmCardPortsPortNumber     INTEGER,
        oaLdOcmCardPortsSectionLof     INTEGER,
        oaLdOcmCardPortsSectionLos     INTEGER,
        oaLdOcmCardPortsSectionLoc     INTEGER,
        oaLdOcmCardPortsSectionB1      Counter,
        oaLdOcmCardPortsLineAis	       INTEGER,
        oaLdOcmCardPortsLineRdi        INTEGER,
        oaLdOcmCardPortsLineB2         Counter,
        oaLdOcmCardPortsLineFebe       Counter,
        oaLdOcmCardPortsPathAis        INTEGER,
        oaLdOcmCardPortsPathLop        INTEGER,
        oaLdOcmCardPortsPathB3         Counter,
        oaLdOcmCardPortsPathPse        Counter,
        oaLdOcmCardPortsPathNse        Counter
       }

oaLdOcmCardPortsSlotNumber OBJECT-TYPE
        SYNTAX    INTEGER
        ACCESS    read-only
        STATUS    mandatory
        DESCRIPTION
        "The slot#. An index from 1 to The number of slots"
        ::= { oaLdOcmCardPortsInfoEntry 1 }

oaLdOcmCardPortsPortNumber OBJECT-TYPE
        SYNTAX    INTEGER
        ACCESS    read-only
        STATUS    mandatory
        DESCRIPTION
        "The port#. An index from 1 to The number of ports"
        ::= { oaLdOcmCardPortsInfoEntry 2 }

oaLdOcmCardPortsSectionLof OBJECT-TYPE
        SYNTAX    INTEGER
        {
         other        (1),
         notSupported (2),
         on           (3),
         off          (4)
        }
        ACCESS  read-only
        STATUS    mandatory
        DESCRIPTION
        "Loss of Frame (LOF) indication."
        ::= { oaLdOcmCardPortsInfoEntry 3 }

oaLdOcmCardPortsSectionLos OBJECT-TYPE
        SYNTAX    INTEGER
        {
         other        (1),
         notSupported (2),
         on           (3),
         off          (4)
        }
        ACCESS  read-only
        STATUS    mandatory
        DESCRIPTION
        "Loss of Signal (LOS) indication."
        ::= { oaLdOcmCardPortsInfoEntry 4 }

oaLdOcmCardPortsSectionLoc OBJECT-TYPE
        SYNTAX    INTEGER
        {
         other        (1),
         notSupported (2),
         on           (3),
         off          (4)
        }
        ACCESS  read-only
        STATUS    mandatory
        DESCRIPTION
        "Loss of Clock (LOC) indication."
        ::= { oaLdOcmCardPortsInfoEntry 5 }

oaLdOcmCardPortsSectionB1 OBJECT-TYPE
        SYNTAX    Counter
        ACCESS    read-only
        STATUS    mandatory
        DESCRIPTION
        "B1 bytes monitoring for correct Bit Interleaved parity (BIP-8)
        values. BIP-8 is calculated over all bytes of each frame
        before descrambling."
        ::= { oaLdOcmCardPortsInfoEntry 6 }

oaLdOcmCardPortsLineAis OBJECT-TYPE
        SYNTAX    INTEGER
        {
         other        (1),
         notSupported (2),
         on           (3),
         off          (4)
        }
        ACCESS  read-only
        STATUS    mandatory
        DESCRIPTION
        "Line (AIS) - Alarm Indication Signal."
        ::= { oaLdOcmCardPortsInfoEntry 7 }

oaLdOcmCardPortsLineRdi OBJECT-TYPE
        SYNTAX    INTEGER
        {
         other        (1),
         notSupported (2),
         on           (3),
         off          (4)
        }
        ACCESS  read-only
        STATUS    mandatory
        DESCRIPTION
        "Line (RDI) - Remote Defect Indication. A returned signal to indicate upon
        LOS, LOF or AIS."
        ::= { oaLdOcmCardPortsInfoEntry 8 }

oaLdOcmCardPortsLineB2 OBJECT-TYPE
        SYNTAX    Counter
        ACCESS    read-only
        STATUS    mandatory
        DESCRIPTION
        "B2 bytes monitoring for correct Bit Interleaved parity (BIP-8)
        values. BIP-384 is calculated over all received data after descrambling."
        ::= { oaLdOcmCardPortsInfoEntry 9 }

oaLdOcmCardPortsLineFebe OBJECT-TYPE
        SYNTAX    Counter
        ACCESS    read-only
        STATUS    mandatory
        DESCRIPTION
        "Line FEBE (REI) - The number of B2 errors that were detected by the remote
        terminal in it's received signal."
        ::= { oaLdOcmCardPortsInfoEntry 10 }

oaLdOcmCardPortsPathAis OBJECT-TYPE
        SYNTAX    INTEGER
        {
         other        (1),
         notSupported (2),
         on           (3),
         off          (4)
        }
        ACCESS  read-only
        STATUS    mandatory
        DESCRIPTION
        "PATH (AIS) - PATH Alarm Indication Signal."
        ::= { oaLdOcmCardPortsInfoEntry 11 }

oaLdOcmCardPortsPathLop OBJECT-TYPE
        SYNTAX    INTEGER
        {
         other        (1),
         notSupported (2),
         on           (3),
         off          (4)
        }
        ACCESS  read-only
        STATUS    mandatory
        DESCRIPTION
        "PATH (LOP) - Loss Of Pointer. PATH indication of the pointer state."
        ::= { oaLdOcmCardPortsInfoEntry 12 }

oaLdOcmCardPortsPathB3 OBJECT-TYPE
        SYNTAX    Counter
        ACCESS    read-only
        STATUS    mandatory
        DESCRIPTION
        "B3 bytes monitoring for correct Bit Interleaved parity (BIP-8)
        values."
        ::= { oaLdOcmCardPortsInfoEntry 13 }

oaLdOcmCardPortsPathPse OBJECT-TYPE
        SYNTAX    Counter
        ACCESS    read-only
        STATUS    mandatory
        DESCRIPTION
        "This is an interperter justification counter that counts every
        positive justification."
        ::= { oaLdOcmCardPortsInfoEntry 14 }

oaLdOcmCardPortsPathNse OBJECT-TYPE
        SYNTAX    Counter
        ACCESS    read-only
        STATUS    mandatory
        DESCRIPTION
        "This is an interperter justification counter that counts every
        negative justification."
        ::= { oaLdOcmCardPortsInfoEntry 15 }

------------------------------------------------------------------------------
-- OADWDM-MIB - defines ROADM Modules
------------------------------------------------------------------------------

oaLdRoadmInfoTable OBJECT-TYPE
        SYNTAX    SEQUENCE OF OaLdRoadmInfoEntry
        ACCESS    not-accessible
        STATUS    mandatory
        DESCRIPTION
        "Table of installed Lambda Driver ROADM Modules"
        ::= {oaLdRoadmInfo 2}

oaLdRoadmInfoEntry OBJECT-TYPE
        SYNTAX    OaLdRoadmInfoEntry
        ACCESS    not-accessible
        STATUS    mandatory
        DESCRIPTION
        "Installed Lambda Driver ROADM Modules"

        INDEX    { oaLdRoadmSlotNumber }

        ::= { oaLdRoadmInfoTable 1 }

OaLdRoadmInfoEntry ::= SEQUENCE {
        oaLdRoadmSlotNumber             INTEGER,
        oaLdRoadmType                   INTEGER,
        oaLdRoadmDescription            DisplayString,
        oaLdRoadmSerialNumber           DisplayString,
        oaLdRoadmBoardVersion           DisplayString,
        oaLdRoadmFpgaVersion            DisplayString,
        oaLdRoadmBootVersion            DisplayString,
        oaLdRoadmMcVersion              DisplayString,
        oaLdRoadmDate                   DisplayString,
-- Status
        oaLdRoadmStatus                 INTEGER,
        oaLdRoadmComOutPortAdminStatus  INTEGER,
        oaLdRoadmFail                   INTEGER,
        oaLdRoadmTemperature            INTEGER,
        oaLdRoadmHeaterMode             INTEGER,
        oaLdRoadmHeaterTemperature      INTEGER,
        oaLdRoadmSpacing                INTEGER,
        oaLdRoadmNumberOfChPorts        INTEGER,
        oaLdRoadmPowerEqualization      INTEGER,
        oaLdRoadmZone2Temperature       INTEGER,
        oaLdRoadmZone3Temperature       INTEGER,
        oaLdRoadmNumberOfChannels       INTEGER,
        oaLdRoadmReconfigureSwitch      INTEGER,
        oaLdRoadmFirstChannel           INTEGER,
        oaLdRoadmLastChannel            INTEGER,
        oaLdRoadmDefaultConfiguration   INTEGER,
        oaLdRoadmPowerBalancingMode     INTEGER
       }

oaLdRoadmSlotNumber OBJECT-TYPE
        SYNTAX  INTEGER
        ACCESS  read-only
        STATUS  mandatory
        DESCRIPTION
        "The slot#. An index from 1 to The number of slots"
        ::= { oaLdRoadmInfoEntry 1 }

oaLdRoadmType OBJECT-TYPE
        SYNTAX  INTEGER
        ACCESS  read-only
        STATUS  mandatory
        DESCRIPTION
        "The ROADM module type
         each module type gets a unique id number"
        ::= { oaLdRoadmInfoEntry 2 }

oaLdRoadmDescription OBJECT-TYPE
        SYNTAX  DisplayString (SIZE (0..32))
        ACCESS  read-only
        STATUS  mandatory
        DESCRIPTION
        "The description of the ROADM module type"
        ::= { oaLdRoadmInfoEntry 3 }

oaLdRoadmSerialNumber OBJECT-TYPE
        SYNTAX  DisplayString (SIZE (0..32))
        ACCESS  read-only
        STATUS  mandatory
        DESCRIPTION
        "The ROADM module serial number"
        ::= { oaLdRoadmInfoEntry 4 }

oaLdRoadmBoardVersion OBJECT-TYPE
        SYNTAX  DisplayString (SIZE (0..32))
        ACCESS  read-only
        STATUS  mandatory
        DESCRIPTION
        "The ROADM module board version"
        ::= { oaLdRoadmInfoEntry 5 }

oaLdRoadmFpgaVersion OBJECT-TYPE
        SYNTAX  DisplayString (SIZE (0..32))
        ACCESS  read-only
        STATUS  mandatory
        DESCRIPTION
        "The ROADM module FPGA version"
        ::= { oaLdRoadmInfoEntry 6 }

oaLdRoadmBootVersion OBJECT-TYPE
        SYNTAX  DisplayString (SIZE (0..32))
        ACCESS  read-only
        STATUS  mandatory
        DESCRIPTION
        "The ROADM module Boot version"
        ::= { oaLdRoadmInfoEntry 7 }

oaLdRoadmMcVersion OBJECT-TYPE
        SYNTAX  DisplayString (SIZE (0..32))
        ACCESS  read-only
        STATUS  mandatory
        DESCRIPTION
        "The ROADM module MicroController code version"
        ::= { oaLdRoadmInfoEntry 8 }

oaLdRoadmDate OBJECT-TYPE
        SYNTAX  DisplayString (SIZE (0..32))
        ACCESS  read-only
        STATUS  mandatory
        DESCRIPTION
        "The ROADM module manufacture date"
        ::= { oaLdRoadmInfoEntry 9 }

oaLdRoadmStatus OBJECT-TYPE
        SYNTAX INTEGER
        {
         other          (1),
         initInProgress (2),
         operating      (3)
        }
        ACCESS  read-only
        STATUS  mandatory
        DESCRIPTION
        "The ROADM module status"
        ::= { oaLdRoadmInfoEntry 15 }

oaLdRoadmComOutPortAdminStatus OBJECT-TYPE
        SYNTAX  INTEGER
        {
         other          (1),
         normal         (2),
         disable        (3)
        }
        ACCESS  read-write
        STATUS  mandatory
        DESCRIPTION
        "The ROADM COM Output port admin status
         2 - Normal - all ports are configured
	     as their oaLdRoadmPortAdminState;
         3 - Disable - all ports are disabled."
        ::= { oaLdRoadmInfoEntry 16 }

oaLdRoadmFail OBJECT-TYPE
        SYNTAX  INTEGER
        {
         other          (1),
         ok             (2),
         fail           (3)
        }
        ACCESS  read-only
        STATUS  mandatory
        DESCRIPTION
        "The ROADM module fail status
         2 - Module works OK
         3 - Module fail"
        ::= { oaLdRoadmInfoEntry 17 }

oaLdRoadmTemperature OBJECT-TYPE
        SYNTAX  INTEGER
        ACCESS  read-only
        STATUS  mandatory
        DESCRIPTION
        "The ROADM module temperature or
         The WSS ROADM zone1 temperature.
         Units: 0.1 [C]"
        ::= { oaLdRoadmInfoEntry 18 }

oaLdRoadmHeaterMode OBJECT-TYPE
        SYNTAX  INTEGER
        {
         other          (1),
         operating      (2),
         disable        (3)
        }
        ACCESS  read-only
        STATUS  mandatory
        DESCRIPTION
        "The ROADM module AWG heater enable mode
         2 - AWG Heater On
         3 - AWG Heater Off"
        ::= { oaLdRoadmInfoEntry 19 }

oaLdRoadmHeaterTemperature OBJECT-TYPE
        SYNTAX  INTEGER
        ACCESS  read-only
        STATUS  mandatory
        DESCRIPTION
        "The ROADM module AWG heater temperature
         Units: 0.1 [C]"
        ::= { oaLdRoadmInfoEntry 20 }

oaLdRoadmSpacing OBJECT-TYPE
        SYNTAX  INTEGER
        {
         other    (1),
         s100     (2),
         s50      (3)
        }
        ACCESS  read-write
        STATUS  mandatory
        DESCRIPTION
        "The ROADM module channel spacing"
        ::= { oaLdRoadmInfoEntry 21 }

oaLdRoadmNumberOfChPorts OBJECT-TYPE
        SYNTAX  INTEGER
        ACCESS  read-only
        STATUS  mandatory
        DESCRIPTION
        "Number of channel ports at ROADM card."
        ::= { oaLdRoadmInfoEntry 22 }

oaLdRoadmPowerEqualization OBJECT-TYPE
        SYNTAX  INTEGER
        {
         done         (1),
         equalization (2)
        }
        ACCESS  read-write
        STATUS  mandatory
        DESCRIPTION
        "Makes procedure of automatic Power Equalization."
        ::= { oaLdRoadmInfoEntry 23 }

oaLdRoadmZone2Temperature OBJECT-TYPE
        SYNTAX  INTEGER
        ACCESS  read-only
        STATUS  mandatory
        DESCRIPTION
        "The WSS ROADM zone2 temperature
         Units: 0.1 [C]"
        ::= { oaLdRoadmInfoEntry 24 }

oaLdRoadmZone3Temperature OBJECT-TYPE
        SYNTAX  INTEGER
        ACCESS  read-only
        STATUS  mandatory
        DESCRIPTION
        "The WSS ROADM zone3 temperature
         Units: 0.1 [C]"
        ::= { oaLdRoadmInfoEntry 25 }

oaLdRoadmNumberOfChannels OBJECT-TYPE
        SYNTAX  INTEGER
        ACCESS  read-only
        STATUS  mandatory
        DESCRIPTION
        "Number of channels at ROADM card."
        ::= { oaLdRoadmInfoEntry 26 }

oaLdRoadmReconfigureSwitch OBJECT-TYPE
        SYNTAX  INTEGER
        {
         other       (1),
         done        (2),
         reconfigure (3)
        }
        ACCESS  read-write
        STATUS  mandatory
        DESCRIPTION
        "Makes procedure of implementing switch configuration on hardware."
        ::= { oaLdRoadmInfoEntry 27 }

oaLdRoadmFirstChannel OBJECT-TYPE
        SYNTAX  INTEGER
        ACCESS  read-only
        STATUS  mandatory
        DESCRIPTION
	"The value of the First Lambda Channel Number in the interval
         of possible Lambda Channels Numbers.
	 For the WSS ROADM Modules the value is equal to
         Lambda Channel Number multiplied by 1000.
	 Example: Lambda Channel Number 20 will apear as 20000.
	 For other ROADM Modules value equal to '0'"
	::= { oaLdRoadmInfoEntry 28 }

oaLdRoadmLastChannel OBJECT-TYPE
        SYNTAX  INTEGER
        ACCESS  read-only
        STATUS  mandatory
        DESCRIPTION
	"The value of the Last Lambda Channel Number in the interval
         of possible Lambda Channels Numbers.
	 For the WSS ROADM Modules the value is equal to
         Lambda Channel Number multiplied by 1000.
	 Example: Lambda Channel Number 20 will apear as 20000.
	 For other ROADM Modules value equal to '0'"
	::= { oaLdRoadmInfoEntry 29 }

oaLdRoadmDefaultConfiguration OBJECT-TYPE
        SYNTAX  INTEGER
        {
         other          (1),
         done           (2),
         restoreDefault (3)
        }
        ACCESS  read-write
        STATUS  mandatory
        DESCRIPTION
        "Restore default Port Channel Configuration for Module.
         Setting 'restoreDefault' for Modules EM1600-WSS2Q and EM1600-WSS4D
         will block all Channels configured on the Ports except those of
         external Wave Blockers."
        ::= { oaLdRoadmInfoEntry 30 }

oaLdRoadmPowerBalancingMode OBJECT-TYPE
     SYNTAX  INTEGER
     {
         other     (1),
         manual    (2),
         automatic (3)
     }
     ACCESS  read-write
     STATUS  mandatory
     DESCRIPTION
       "ROADM Module power balancing mode."
     ::= { oaLdRoadmInfoEntry 31 }

------------------------------------------------------------------------------
-- OADWDM-MIB - defines ROADM Modules Monitoring
------------------------------------------------------------------------------

oaLdRoadmMonitorTable OBJECT-TYPE
        SYNTAX    SEQUENCE OF OaLdRoadmMonitorEntry
        ACCESS    not-accessible
        STATUS    mandatory
        DESCRIPTION
        "Table of installed Lambda Driver ROADM Modules Monitoring"
        ::= {oaLdRoadmInfo 3}

oaLdRoadmMonitorEntry OBJECT-TYPE
        SYNTAX    OaLdRoadmMonitorEntry
        ACCESS    not-accessible
        STATUS    mandatory
        DESCRIPTION
        "Installed Lambda Driver ROADM Modules Monitoring"

        INDEX    { oaLdRoadmMonitorSlotNumber }

        ::= { oaLdRoadmMonitorTable 1 }

OaLdRoadmMonitorEntry ::= SEQUENCE {
        oaLdRoadmMonitorSlotNumber      INTEGER,
        oaLdRoadmMonitorComInputPower   INTEGER,
        oaLdRoadmMonitorComOutputPower  INTEGER,
        oaLdRoadmMonitorExpInputPower   INTEGER,
        oaLdRoadmMonitorExpOutputPower  INTEGER,
        oaLdRoadmMonitorDropOutputPower INTEGER
       }

oaLdRoadmMonitorSlotNumber OBJECT-TYPE
        SYNTAX  INTEGER
        ACCESS  read-only
        STATUS  mandatory
        DESCRIPTION
        "The slot#. An index from 1 to The number of slots"
        ::= { oaLdRoadmMonitorEntry 1 }

oaLdRoadmMonitorComInputPower OBJECT-TYPE
        SYNTAX  INTEGER
        ACCESS  read-only
        STATUS  mandatory
        DESCRIPTION
        "The ROADM module COM IN power
         Units: 0.1 [dBm]"
        ::= { oaLdRoadmMonitorEntry 2 }

oaLdRoadmMonitorComOutputPower OBJECT-TYPE
        SYNTAX  INTEGER
        ACCESS  read-only
        STATUS  mandatory
        DESCRIPTION
        "The ROADM module COM OUT power
         Units: 0.1 [dBm]"
        ::= { oaLdRoadmMonitorEntry 3 }

oaLdRoadmMonitorExpInputPower OBJECT-TYPE
        SYNTAX  INTEGER
        ACCESS  read-only
        STATUS  mandatory
        DESCRIPTION
        "The ROADM module Input power (EXP IN)
         Units: 0.1 [dBm]"
        ::= { oaLdRoadmMonitorEntry 4 }

oaLdRoadmMonitorExpOutputPower OBJECT-TYPE
        SYNTAX  INTEGER
        ACCESS  read-only
        STATUS  mandatory
        DESCRIPTION
        "The ROADM module EXP OUT power
         Units: 0.1 [dBm]"
        ::= { oaLdRoadmMonitorEntry 5 }

oaLdRoadmMonitorDropOutputPower OBJECT-TYPE
        SYNTAX  INTEGER
        ACCESS  read-only
        STATUS  mandatory
        DESCRIPTION
        "The ROADM module DROP OUT power
         Units: 0.1 [dBm]"
        ::= { oaLdRoadmMonitorEntry 6 }

------------------------------------------------------------------------------
-- OADWDM-MIB - defines ROADM Channels table
------------------------------------------------------------------------------
oaLdRoadmChannelTable OBJECT-TYPE
        SYNTAX    SEQUENCE OF OaLdRoadmChannelEntry
        ACCESS    not-accessible
        STATUS    mandatory
        DESCRIPTION
        "Table of installed Lambda Driver ROADM Modules Ports"
        ::= {oaLdRoadmInfo 4}

oaLdRoadmChannelEntry OBJECT-TYPE
        SYNTAX    OaLdRoadmChannelEntry
        ACCESS    not-accessible
        STATUS    mandatory
        DESCRIPTION
        "Installed Lambda Driver ROADM Modules Channels"

        INDEX    { oaLdRoadmChannelSlotNumber, oaLdRoadmChannelLambdaChannel, oaLdRoadmChannelPortNumber }
        ::= { oaLdRoadmChannelTable 1 }

OaLdRoadmChannelEntry ::= SEQUENCE {
        oaLdRoadmChannelSlotNumber        INTEGER,
        oaLdRoadmChannelLambdaChannel     INTEGER,
        oaLdRoadmChannelPortNumber        INTEGER,
        oaLdRoadmChannelWavelength        INTEGER,
        oaLdRoadmChannelDropPortNumber    INTEGER,
        oaLdRoadmChannelDropAttenuation   INTEGER,
        oaLdRoadmChannelConfigStatus      INTEGER,
-- Monitoring part
        oaLdRoadmChannelPower1            INTEGER,
        oaLdRoadmChannelPower2            INTEGER,
        oaLdRoadmChannelDropPeakFrequency INTEGER,
        oaLdRoadmChannelAddPeakFrequency  INTEGER,
-- Additional channel configuration

        oaLdRoadmChannelAddAttenuation    INTEGER,
        oaLdRoadmChannelGridFrequency     INTEGER,
        oaLdRoadmChannelSpacing           INTEGER
       }

oaLdRoadmChannelSlotNumber OBJECT-TYPE
        SYNTAX  INTEGER
        ACCESS  read-only
        STATUS  mandatory
        DESCRIPTION
        "The slot#. An index from 1 to The number of slots"
       ::= { oaLdRoadmChannelEntry 1 }

oaLdRoadmChannelLambdaChannel OBJECT-TYPE
        SYNTAX  INTEGER
        ACCESS  read-only
        STATUS  mandatory
        DESCRIPTION
        "The ROADM module Channel Lambda Channel Number multiplied by 1000.
         Example: channel 20 will apear as 20000."
        ::= { oaLdRoadmChannelEntry 2 }

oaLdRoadmChannelPortNumber OBJECT-TYPE
        SYNTAX  INTEGER
        ACCESS  read-only
        STATUS  mandatory
        DESCRIPTION
        "The port#. An index from 1 to The number of ports."
	::= { oaLdRoadmChannelEntry 3 }

oaLdRoadmChannelWavelength OBJECT-TYPE
        SYNTAX  INTEGER
        ACCESS  read-only
        STATUS  mandatory
        DESCRIPTION
        "The ROADM module Port Channel Wavelenth,
         Units: 0.01 Nano Meter[nm]"
        ::= { oaLdRoadmChannelEntry 4 }

oaLdRoadmChannelDropPortNumber OBJECT-TYPE
        SYNTAX  INTEGER
        ACCESS  read-write
        STATUS  mandatory
        DESCRIPTION
        "The number of Drop Port, connected to this Channel."
        ::= { oaLdRoadmChannelEntry 5 }

oaLdRoadmChannelDropAttenuation OBJECT-TYPE
        SYNTAX  INTEGER
        ACCESS  read-write
        STATUS  mandatory
        DESCRIPTION
        "The ROADM module port VOA Drop Attenuation,
         integer from 0 till 150, Units: 0.1 [dB]"
        ::= { oaLdRoadmChannelEntry 6 }

oaLdRoadmChannelConfigStatus OBJECT-TYPE
        SYNTAX  INTEGER
        {
         other          (1),
         virtual        (2),
         saved          (3)
        }
        ACCESS  read-only
        STATUS  mandatory
        DESCRIPTION
        "The status of ROADM module Channel.
         Set 'virtual' if configuration didn't save in HW."
        ::= { oaLdRoadmChannelEntry 7 }

oaLdRoadmChannelPower1 OBJECT-TYPE
        SYNTAX  INTEGER
        ACCESS  read-only
        STATUS  mandatory
        DESCRIPTION
        "The ROADM module Channel Power,
         (Drop Peak Power for module EM1600-WSS9,
         Com Output West or East Total Power for module EM1600-WSS2Q,
         Com Output Total Power for module EM1600-WSS4D)
         Units: 0.1 [dBm]"
        ::= { oaLdRoadmChannelEntry 8 }

oaLdRoadmChannelPower2 OBJECT-TYPE
        SYNTAX  INTEGER
        ACCESS  read-only
        STATUS  mandatory
        DESCRIPTION
        "The ROADM module Channel Power,
         (Add Peak Power for module EM1600-WSS9,
         Not applicable object for module EM1600-WSS2Q,
         Com Input Total Power for module EM1600-WSS4D)
         Units: 0.1 [dBm]"
        ::= { oaLdRoadmChannelEntry 9 }

oaLdRoadmChannelDropPeakFrequency OBJECT-TYPE
        SYNTAX  INTEGER
        ACCESS  read-only
        STATUS  mandatory
        DESCRIPTION
        "The ROADM module Channel Frequency, (Drop Peak Frequency)
         Units: 0.0001 [THz]"
        ::= { oaLdRoadmChannelEntry 10 }

oaLdRoadmChannelAddPeakFrequency OBJECT-TYPE
        SYNTAX  INTEGER
        ACCESS  read-only
        STATUS  mandatory
        DESCRIPTION
        "The ROADM module Channel Frequency, (Add Peak Frequency)
         Units: 0.0001 [THz]"
        ::= { oaLdRoadmChannelEntry 11 }

oaLdRoadmChannelAddAttenuation OBJECT-TYPE
        SYNTAX  INTEGER
        ACCESS  read-write
        STATUS  mandatory
        DESCRIPTION
        "The ROADM module port VOA Add Attenuation,
	 integer from 0 till 250, Units: 0.1 [dB]"
        ::= { oaLdRoadmChannelEntry 12 }

oaLdRoadmChannelGridFrequency OBJECT-TYPE
        SYNTAX  INTEGER
        ACCESS  read-only
        STATUS  mandatory
        DESCRIPTION
        "The ROADM module Channel Grid Frequency
         Units: 0.0001 [THz]"
        ::= { oaLdRoadmChannelEntry 13 }

oaLdRoadmChannelSpacing OBJECT-TYPE
        SYNTAX  INTEGER
        {
         other    (1),
         s100     (2),
         s50      (3)
        }
        ACCESS  read-only
        STATUS  mandatory
        DESCRIPTION
        "The ROADM Channel Spacing"
        ::= { oaLdRoadmChannelEntry 14 }

------------------------------------------------------------------------------
-- OADWDM-MIB - defines ROADM Modules Thresholds
------------------------------------------------------------------------------

oaLdRoadmThresholdTable OBJECT-TYPE
        SYNTAX    SEQUENCE OF OaLdRoadmThresholdEntry
        ACCESS    not-accessible
        STATUS    mandatory
        DESCRIPTION
        "Table of installed Lambda Driver ROADM Modules Thresholds"
        ::= {oaLdRoadmInfo 5}

oaLdRoadmThresholdEntry OBJECT-TYPE
        SYNTAX    OaLdRoadmThresholdEntry
        ACCESS    not-accessible
        STATUS    mandatory
        DESCRIPTION
        "Installed Lambda Driver ROADM Modules Thresholds"

        INDEX    { oaLdRoadmThresholdSlotNumber, oaLdRoadmThresholdIndex }

        ::= { oaLdRoadmThresholdTable 1 }

OaLdRoadmThresholdEntry ::= SEQUENCE {
        oaLdRoadmThresholdSlotNumber    INTEGER,
        oaLdRoadmThresholdIndex         INTEGER,
        oaLdRoadmThresholdAwgTemp       INTEGER,
        oaLdRoadmThresholdTemp          INTEGER,
        oaLdRoadmThresholdComInputPwr   INTEGER,
        oaLdRoadmThresholdComOutputPwr  INTEGER,
        oaLdRoadmThresholdExpInputPwr   INTEGER,
        oaLdRoadmThresholdExpOutputPwr  INTEGER,
        oaLdRoadmThresholdDropOutputPwr INTEGER
       }

oaLdRoadmThresholdSlotNumber OBJECT-TYPE
        SYNTAX  INTEGER
        ACCESS  read-only
        STATUS  mandatory
        DESCRIPTION
        "The slot#. An index from 1 to The number of slots"
        ::= { oaLdRoadmThresholdEntry 1 }

oaLdRoadmThresholdIndex OBJECT-TYPE
        SYNTAX  INTEGER
        {
         degradeLow             (1),
         degradeHigh            (2),
         failLow                (3),
         failHigh               (4),
         hysteresisDegradeLow   (5),
         hysteresisDegradeHigh  (6),
         hysteresisFailLow      (7),
         hysteresisFailHigh     (8),
         tRaise                 (9),
         tFall                  (10)
        }
        ACCESS  read-only
        STATUS  mandatory
        DESCRIPTION
        "The threshold index An index from 1 to The number of thresholds"
        ::= { oaLdRoadmThresholdEntry 2 }

oaLdRoadmThresholdAwgTemp OBJECT-TYPE
        SYNTAX  INTEGER
        ACCESS  read-only
        STATUS  mandatory
        DESCRIPTION
        "The ROADM module AWG temperature threshold
         Units: 0.1 [C]"
        ::= { oaLdRoadmThresholdEntry 3 }

oaLdRoadmThresholdTemp OBJECT-TYPE
        SYNTAX  INTEGER
        ACCESS  read-only
        STATUS  mandatory
        DESCRIPTION
        "The ROADM module temperature threshold
         Units: 0.1 [C]"
        ::= { oaLdRoadmThresholdEntry 4 }

oaLdRoadmThresholdComInputPwr OBJECT-TYPE
        SYNTAX  INTEGER
        ACCESS  read-only
        STATUS  mandatory
        DESCRIPTION
        "The ROADM module COM IN power threshold
         (demultiplexer channel output)
         Units: 0.1 [dBm]"
        ::= { oaLdRoadmThresholdEntry 5 }

oaLdRoadmThresholdComOutputPwr OBJECT-TYPE
        SYNTAX  INTEGER
        ACCESS  read-only
        STATUS  mandatory
        DESCRIPTION
        "The ROADM module COM OUT power threshold
         Units: 0.1 [dBm]"
        ::= { oaLdRoadmThresholdEntry 6 }

oaLdRoadmThresholdExpInputPwr OBJECT-TYPE
        SYNTAX  INTEGER
        ACCESS  read-only
        STATUS  mandatory
        DESCRIPTION
        "The ROADM module input power (EXT IN) threshold
         Units: 0.1 [dBm]"
        ::= { oaLdRoadmThresholdEntry 7 }

oaLdRoadmThresholdExpOutputPwr OBJECT-TYPE
        SYNTAX  INTEGER
        ACCESS  read-only
        STATUS  mandatory
        DESCRIPTION
        "The ROADM module EXP OUT power threshold
         Units: 0.1 [dBm]"
        ::= { oaLdRoadmThresholdEntry 8 }

oaLdRoadmThresholdDropOutputPwr OBJECT-TYPE
        SYNTAX  INTEGER
        ACCESS  read-only
        STATUS  mandatory
        DESCRIPTION
        "The ROADM module DROP OUT power threshold
         Units: 0.1 [dBm]"
        ::= { oaLdRoadmThresholdEntry 9 }

------------------------------------------------------------------------------
-- OADWDM-MIB - ROADM Module per Port Definitions
------------------------------------------------------------------------------

oaLdRoadmPortInfoTable OBJECT-TYPE
        SYNTAX    SEQUENCE OF OaLdRoadmPortInfoEntry
        ACCESS    not-accessible
        STATUS    mandatory
        DESCRIPTION
        "Table of installed Lambda Driver ROADM Modules Ports"
        ::= {oaLdRoadmInfo 6}

oaLdRoadmPortInfoEntry OBJECT-TYPE
        SYNTAX    OaLdRoadmPortInfoEntry
        ACCESS    not-accessible
        STATUS    mandatory
        DESCRIPTION
        "Installed Lambda Driver ROADM Modules Ports"

        INDEX    { oaLdRoadmPortSlotNumber, oaLdRoadmPortPortNumber }

        ::= { oaLdRoadmPortInfoTable 1 }

OaLdRoadmPortInfoEntry ::= SEQUENCE {
        oaLdRoadmPortSlotNumber         INTEGER,
        oaLdRoadmPortPortNumber         INTEGER,
        oaLdRoadmPortAdminState         INTEGER,
        oaLdRoadmPortServiceState       INTEGER,
-- Optical parameters
        oaLdRoadmPortPower              INTEGER,
--      oaLdRoadmPortVoaControlMode     INTEGER,
        oaLdRoadmPortVoaAttenuationAdd  INTEGER,
        oaLdRoadmPortVoaAttenuationPass INTEGER,
        oaLdRoadmPortVoaAttenuationDrop INTEGER,
        oaLdRoadmPortChannelWavelength  INTEGER,
        oaLdRoadmPortLambdaChannel      INTEGER,
        oaLdRoadmPortVoaMinAttenuation  INTEGER,
        oaLdRoadmPortVoaMaxAttenuation  INTEGER,
        oaLdRoadmPortName               DisplayString,
        oaLdRoadmPortPowerSupported     INTEGER,
        oaLdRoadmPortTotalPower         INTEGER,
        oaLdRoadmPortChanList           OCTET STRING,
        oaLdRoadmPortChanSrcPortList    OCTET STRING,
        oaLdRoadmPortBalancingAdminStatus  INTEGER,
        oaLdRoadmPortBalancingOperStatus   INTEGER,
        oaLdRoadmPortBalancingPower        INTEGER,
        oaLdRoadmPortBalancingMaxChnlsNum  INTEGER,
        oaLdRoadmPortBalancingPowerPerChnl INTEGER
       }

oaLdRoadmPortSlotNumber OBJECT-TYPE
        SYNTAX  INTEGER
        ACCESS  read-only
        STATUS  mandatory
        DESCRIPTION
        "The slot#. An index from 1 to The number of slots"
       ::= { oaLdRoadmPortInfoEntry 1 }

oaLdRoadmPortPortNumber OBJECT-TYPE
        SYNTAX  INTEGER
        ACCESS  read-only
        STATUS  mandatory
        DESCRIPTION
        "The port#. An index from 1 to The number of ports (channels)"
        ::= { oaLdRoadmPortInfoEntry 2 }

oaLdRoadmPortAdminState OBJECT-TYPE
        SYNTAX  INTEGER
        {
         other          (1),
         add            (2),
         pass           (3),
         dark           (4),
         drop           (5)
        }
        ACCESS  read-write
        STATUS  mandatory
        DESCRIPTION
        "The ROADM module administration state of the Port,
         Add, Pass through or Dark.
         Setting 'dark' for Modules EM1600-WSS2Q and EM1600-WSS4D
         will block all Channels configured on the Port."
        ::= { oaLdRoadmPortInfoEntry 3 }

oaLdRoadmPortServiceState OBJECT-TYPE
        SYNTAX  INTEGER
        {
         other          (1),
         add            (2),
         pass           (3),
         dark           (4),
         drop           (5)
        }
        ACCESS  read-only
        STATUS  mandatory
        DESCRIPTION
        "The ROADM module switch setting of the port,
         Add, Pass through or Dark"
        ::= { oaLdRoadmPortInfoEntry 4 }

oaLdRoadmPortPower OBJECT-TYPE
        SYNTAX  INTEGER
        ACCESS  read-only
        STATUS  mandatory
        DESCRIPTION
        "The ROADM module port input power
         (Multiplexer Input Power for module EM1600-ROADM40,
         Com Input Total Power for module EM1600-WSS4D).
         Units: 0.1 [dBm]"
        ::= { oaLdRoadmPortInfoEntry 5 }

-- oaLdRoadmPortVoaControlMode OBJECT-TYPE
--        SYNTAX  INTEGER
--        ACCESS  read-only
--        STATUS  mandatory
--        DESCRIPTION
--        "The ROADM module port VOA control mode
--         constant attenuation or constant output
--         currently not supported "
--        ::= { oaLdRoadmPortInfoEntry 6 }

oaLdRoadmPortVoaAttenuationAdd OBJECT-TYPE
        SYNTAX  INTEGER
        ACCESS  read-write
        STATUS  mandatory
        DESCRIPTION
        "The ROADM module port VOA add attenuation,
         integer from 0 till 250, Units: 0.1 [dB]"
        ::= { oaLdRoadmPortInfoEntry 7 }

oaLdRoadmPortVoaAttenuationPass OBJECT-TYPE
        SYNTAX  INTEGER
        ACCESS  read-write
        STATUS  mandatory
        DESCRIPTION
        "The ROADM module port VOA pass attenuation,
         integer from 0 till 250, Units: 0.1 [dB]"
        ::= { oaLdRoadmPortInfoEntry 8 }

oaLdRoadmPortVoaAttenuationDrop OBJECT-TYPE
        SYNTAX  INTEGER
        ACCESS  read-write
        STATUS  mandatory
        DESCRIPTION
        "The ROADM module port VOA drop attenuation,
         integer from 0 till 250, Units: 0.1 [dB]"
        ::= { oaLdRoadmPortInfoEntry 9 }

oaLdRoadmPortChannelWavelength OBJECT-TYPE
        SYNTAX  INTEGER
        ACCESS  read-write
        STATUS  mandatory
        DESCRIPTION
        "The ROADM module port channel wavelenth,
         Units: 0.01 Nano Meter[nm]"
        ::= { oaLdRoadmPortInfoEntry 10 }

oaLdRoadmPortLambdaChannel OBJECT-TYPE
        SYNTAX  INTEGER
        ACCESS  read-only
        STATUS  mandatory
        DESCRIPTION
        "The ROADM module port lambda channel number multiplied by 1000.
         Example: channel 20 will apear as 20000."
        ::= { oaLdRoadmPortInfoEntry 11 }

oaLdRoadmPortVoaMinAttenuation OBJECT-TYPE
        SYNTAX  INTEGER
        ACCESS  read-write
        STATUS  mandatory
        DESCRIPTION
        "The module port VOA minimum attenuation value,
         integer in Units: 0.1 [dB]"
        ::= { oaLdRoadmPortInfoEntry 12 }

oaLdRoadmPortVoaMaxAttenuation OBJECT-TYPE
        SYNTAX  INTEGER
        ACCESS  read-write
        STATUS  mandatory
        DESCRIPTION
        "The module port VOA maximum attenuation value,
         integer in Units: 0.1 [dB]"
        ::= { oaLdRoadmPortInfoEntry 13 }

oaLdRoadmPortName OBJECT-TYPE
        SYNTAX  DisplayString (SIZE(18))
        ACCESS  read-only
        STATUS  mandatory
        DESCRIPTION
        "Port Name string (as: Add-Drop West, ExpIn-ExpOut East, Com Out, WB1 In-Out etc.)"
        ::= { oaLdRoadmPortInfoEntry 14 }

oaLdRoadmPortPowerSupported OBJECT-TYPE
        SYNTAX    INTEGER
        {
         supported    (1),
         notSupported (2)
        }
        ACCESS  read-only
        STATUS    mandatory
        DESCRIPTION
        "Optical Power value exists for this port."
        ::= { oaLdRoadmPortInfoEntry 15 }

oaLdRoadmPortTotalPower OBJECT-TYPE
        SYNTAX  INTEGER
        ACCESS  read-only
        STATUS  mandatory
        DESCRIPTION
        "The ROADM module Port Total Power value.
         Units: 0.1 [dBm]"
        ::= { oaLdRoadmPortInfoEntry 16 }

oaLdRoadmPortChanList   OBJECT-TYPE
        SYNTAX  OCTET STRING  (SIZE(96))
        ACCESS  read-only
        STATUS  mandatory
        DESCRIPTION
        "List of Lambda Channels detected in the Port.
         Number of bytes in the Octet String is equal to the value
         of [oaLdRoadmNumberOfChannels].
         Each Byte in the Octet String includes information about
         existence of the Lambda Channel in the Port
         (0=does not exist, 1=exists)."
        ::= { oaLdRoadmPortInfoEntry 17 }

oaLdRoadmPortChanSrcPortList   OBJECT-TYPE
        SYNTAX  OCTET STRING  (SIZE(96))
        ACCESS  read-only
        STATUS  mandatory
        DESCRIPTION
        "List of Input Port Numbers which Lambda Channels were detected in the Port.
         Number of bytes in the Octet String is equal to the value
         of [oaLdRoadmNumberOfChannels].
         Each Byte in the Octet String includes Input Port Number or
         '0' for Output Port or other not relevant Ports."
        ::= { oaLdRoadmPortInfoEntry 18 }

oaLdRoadmPortBalancingAdminStatus OBJECT-TYPE
     SYNTAX  INTEGER
        {
         other      (1),
         balancing  (2),
         negate     (3)
        }
        ACCESS  read-write
        STATUS  mandatory
        DESCRIPTION
        "The ROADM module's port power balancing administrative status."
        ::= { oaLdRoadmPortInfoEntry 19 }

oaLdRoadmPortBalancingOperStatus OBJECT-TYPE
        SYNTAX  INTEGER
        {
         other       (1),
         inProgress  (2),
         done        (3),
         failed      (4)
        }
        ACCESS  read-only
        STATUS  mandatory
        DESCRIPTION
        "The ROADM module's port power balancing operative status."
        ::= { oaLdRoadmPortInfoEntry 20 }

oaLdRoadmPortBalancingPower OBJECT-TYPE
        SYNTAX  INTEGER
        ACCESS  read-write
        STATUS  mandatory
        DESCRIPTION
        "The ROADM module's port maximum COM OUT power.
         Units: 0.1 [dBm]"
        ::= { oaLdRoadmPortInfoEntry 21 }

oaLdRoadmPortBalancingMaxChnlsNum OBJECT-TYPE
        SYNTAX  INTEGER
        ACCESS  read-write
        STATUS  mandatory
        DESCRIPTION
        "The ROADM module's port maximum channels number for power balancing."
        ::= { oaLdRoadmPortInfoEntry 22 }

oaLdRoadmPortBalancingPowerPerChnl OBJECT-TYPE
        SYNTAX  INTEGER
        ACCESS  read-only
        STATUS  mandatory
        DESCRIPTION
        "The ROADM module's calculated maximum output power per channel.
         Units: 0.1 [dBm]"
        ::= { oaLdRoadmPortInfoEntry 23 }

------------------------------------------------------------------------------
-- OADWDM-MIB - ROADM Module per Port Thresholds Definitions
------------------------------------------------------------------------------

oaLdRoadmPortThresholdTable OBJECT-TYPE
        SYNTAX    SEQUENCE OF OaLdRoadmPortThresholdEntry
        ACCESS    not-accessible
        STATUS    mandatory
        DESCRIPTION
        "Table of installed Lambda Driver ROADM Modules Ports Threshold"
        ::= {oaLdRoadmInfo 7}

oaLdRoadmPortThresholdEntry OBJECT-TYPE
        SYNTAX    OaLdRoadmPortThresholdEntry
        ACCESS    not-accessible
        STATUS    mandatory
        DESCRIPTION
        "Installed Lambda Driver ROADM Modules Ports Threshold"

        INDEX    { oaLdRoadmPortThresholdSlotIndex,
                   oaLdRoadmPortThresholdPortIndex,
                   oaLdRoadmPortThresholdIndex }

        ::= { oaLdRoadmPortThresholdTable 1 }

OaLdRoadmPortThresholdEntry ::= SEQUENCE {
        oaLdRoadmPortThresholdSlotIndex  INTEGER,
        oaLdRoadmPortThresholdPortIndex  INTEGER,
        oaLdRoadmPortThresholdIndex      INTEGER,
        oaLdRoadmPortThresholdPwr        INTEGER
       }

oaLdRoadmPortThresholdSlotIndex OBJECT-TYPE
        SYNTAX  INTEGER
        ACCESS  read-only
        STATUS  mandatory
        DESCRIPTION
        "The slot#. An index from 1 to The number of slots"
       ::= { oaLdRoadmPortThresholdEntry 1 }

oaLdRoadmPortThresholdPortIndex OBJECT-TYPE
        SYNTAX  INTEGER
        ACCESS  read-only
        STATUS  mandatory
        DESCRIPTION
        "The port#. An index from 1 to The number of ports (channels)"
        ::= { oaLdRoadmPortThresholdEntry 2 }

oaLdRoadmPortThresholdIndex OBJECT-TYPE
        SYNTAX  INTEGER
        {
         degradeLow             (1),
         degradeHigh            (2),
         failLow                (3),
         failHigh               (4),
         hysteresisDegradeLow   (5),
         hysteresisDegradeHigh  (6),
         hysteresisFailLow      (7),
         hysteresisFailHigh     (8),
         tRaise                 (9),
         tFall                  (10)
        }
        ACCESS  read-only
        STATUS  mandatory
        DESCRIPTION
        "The threshold index An index from 1 to The number of thresholds"
        ::= { oaLdRoadmPortThresholdEntry 3 }

oaLdRoadmPortThresholdPwr OBJECT-TYPE
        SYNTAX  INTEGER
        ACCESS  read-only
        STATUS  mandatory
        DESCRIPTION
        "The ROADM module port power threshold,
         (multiplexer input power)
         Units: 0.1 [dBm]"
        ::= { oaLdRoadmPortThresholdEntry 4 }

------------------------------------------------------------------------------
-- OADWDM-MIB - define the card's ports cross connection
------------------------------------------------------------------------------

oaLdPortsCrossConnectTable OBJECT-TYPE
        SYNTAX    SEQUENCE OF OaLdPortsCrossConnectEntry
        ACCESS    not-accessible
        STATUS    mandatory
        DESCRIPTION
        "Table of installed Cross Connect Ports"
        ::= {oaLdPortsCrossConnect 1}

oaLdPortsCrossConnectEntry OBJECT-TYPE
        SYNTAX    OaLdPortsCrossConnectEntry
        ACCESS    not-accessible
        STATUS    mandatory
        DESCRIPTION
        "Installed Cross Connect Ports"

        INDEX    { oaLdPortsCrossConnectSlotNumber, oaLdPortsCrossConnectPortNumber }

        ::= { oaLdPortsCrossConnectTable 1 }

OaLdPortsCrossConnectEntry ::= SEQUENCE {
        oaLdPortsCrossConnectSlotNumber       INTEGER,
        oaLdPortsCrossConnectPortNumber       INTEGER,
        oaLdPortsCrossConnectNumber           INTEGER,
        oaLdPortsCrossConnectAction           INTEGER
       }

oaLdPortsCrossConnectSlotNumber OBJECT-TYPE
        SYNTAX    INTEGER
        ACCESS    read-only
        STATUS    mandatory
        DESCRIPTION
        "The Cross Connect module slot number."
        ::= { oaLdPortsCrossConnectEntry 1 }

oaLdPortsCrossConnectPortNumber OBJECT-TYPE
        SYNTAX    INTEGER
        ACCESS    read-only
        STATUS    mandatory
        DESCRIPTION
        "The port# from Cross Connect module."
        ::= { oaLdPortsCrossConnectEntry 2 }

oaLdPortsCrossConnectNumber OBJECT-TYPE
        SYNTAX    INTEGER
        ACCESS    read-write
        STATUS    mandatory
        DESCRIPTION
        "Number of port which is defined as connected with this port.
         The number is 0, if this port doesn't connected"
        ::= { oaLdPortsCrossConnectEntry 3 }

oaLdPortsCrossConnectAction OBJECT-TYPE
        SYNTAX    INTEGER
        {
         other      (1),
         connect    (2),
         disconnect (3)
        }
        ACCESS    read-write
        STATUS    mandatory
        DESCRIPTION
        "Action to connect or disconnect this port with number.
         Get always returns other. For set have to be together with object oaLdPortsCrossConnectNumber."
        ::= { oaLdPortsCrossConnectEntry 4 }

------------------------------------------------------------------------------
-- OADWDM-MIB - defines OCMC Module Ports Optical parameters
------------------------------------------------------------------------------

oaLdMeasurmentPointsTable OBJECT-TYPE
        SYNTAX    SEQUENCE OF OaLdMeasurmentPointsEntry
        ACCESS    not-accessible
        STATUS    mandatory
        DESCRIPTION
        "Table of optical peaks and Spectral points numbers."
        ::= {oaLdOpticalMonitor 1}

oaLdMeasurmentPointsEntry OBJECT-TYPE
        SYNTAX    OaLdMeasurmentPointsEntry
        ACCESS    not-accessible
        STATUS    mandatory
        DESCRIPTION
        "Table of optical peaks and Spectral points numbers."
        INDEX    { oaLdMeasurmentPointsSlotNumber, oaLdMeasurmentPointsPortNumber }
        ::= { oaLdMeasurmentPointsTable 1 }

OaLdMeasurmentPointsEntry ::= SEQUENCE {
        oaLdMeasurmentPointsSlotNumber   INTEGER,
        oaLdMeasurmentPointsPortNumber   INTEGER,
        oaLdPeaksNumber                  INTEGER,
        oaLdTotalBandPower               INTEGER
       }

oaLdMeasurmentPointsSlotNumber OBJECT-TYPE
        SYNTAX  INTEGER
        ACCESS  read-only
        STATUS  mandatory
        DESCRIPTION
        "The slot#. An index from 1 to The number of slots"
        ::= { oaLdMeasurmentPointsEntry 1 }

oaLdMeasurmentPointsPortNumber OBJECT-TYPE
        SYNTAX  INTEGER
        ACCESS  read-only
        STATUS  mandatory
        DESCRIPTION
        "The port#. An index from 1 to The number of ports."
        ::= { oaLdMeasurmentPointsEntry 2 }

oaLdPeaksNumber OBJECT-TYPE
        SYNTAX    INTEGER
        ACCESS    read-only
        STATUS    mandatory
        DESCRIPTION
        "The number of detected optical peaks."
        ::= {oaLdMeasurmentPointsEntry 3 }

oaLdTotalBandPower OBJECT-TYPE
        SYNTAX  INTEGER
        ACCESS  read-only
        STATUS  mandatory
        DESCRIPTION
        "The total band power. Units: 0.1 [dBm]"
        ::= {oaLdMeasurmentPointsEntry 4 }

------------------------------------------------------------------------------
-- OADWDM-MIB - defines OCMC Module Port Peaks Monitoring parameters
------------------------------------------------------------------------------

oaLdPeaksMonitorTable OBJECT-TYPE
        SYNTAX    SEQUENCE OF OaLdPeaksMonitorEntry
        ACCESS    not-accessible
        STATUS    mandatory
        DESCRIPTION
        "Table of Spectral optical Peaks Monitoring."
        ::= {oaLdOpticalMonitor 2}

oaLdPeaksMonitorEntry OBJECT-TYPE
        SYNTAX    OaLdPeaksMonitorEntry
        ACCESS    not-accessible
        STATUS    mandatory
        DESCRIPTION
        "Spectral optical Peaks Monitoring"
        INDEX    { oaLdPeaksMonitorSlotNumber, oaLdPeaksMonitorPortNumber, oaLdPeaksMonitorPeakNumber }
        ::= { oaLdPeaksMonitorTable 1 }

OaLdPeaksMonitorEntry ::= SEQUENCE {
        oaLdPeaksMonitorSlotNumber       INTEGER,
        oaLdPeaksMonitorPortNumber       INTEGER,
        oaLdPeaksMonitorPeakNumber       INTEGER,
        oaLdPeaksMonitorPeakFreq         INTEGER,
        oaLdPeaksMonitorPeakWavelength   INTEGER,
        oaLdPeaksMonitorPeakPower        INTEGER,
        oaLdPeaksMonitorTotalPower       INTEGER,
        oaLdPeaksMonitorOsnr             INTEGER,
        oaLdPeaksMonitorLeftValleyFreq   INTEGER,
        oaLdPeaksMonitorLeftValleyPower  INTEGER,
        oaLdPeaksMonitorRightValleyFreq  INTEGER,
        oaLdPeaksMonitorRightValleyPower INTEGER
       }

oaLdPeaksMonitorSlotNumber OBJECT-TYPE
        SYNTAX  INTEGER
        ACCESS  read-only
        STATUS  mandatory
        DESCRIPTION
        "The slot#. An index from 1 to The number of slots"
        ::= { oaLdPeaksMonitorEntry 1 }

oaLdPeaksMonitorPortNumber OBJECT-TYPE
        SYNTAX  INTEGER
        ACCESS  read-only
        STATUS  mandatory
        DESCRIPTION
        "The port#. An index from 1 to The number of ports."
        ::= { oaLdPeaksMonitorEntry 2 }

oaLdPeaksMonitorPeakNumber OBJECT-TYPE
        SYNTAX  INTEGER
        ACCESS  read-only
        STATUS  mandatory
        DESCRIPTION
        "The spectral peak#.
         An index from 1 to The number of measured spectral peaks."
        ::= { oaLdPeaksMonitorEntry 3 }

oaLdPeaksMonitorPeakFreq OBJECT-TYPE
        SYNTAX  INTEGER
        ACCESS  read-only
        STATUS  mandatory
        DESCRIPTION
        "The peak frequency. Units: 0.0001 [THz]."
        ::= { oaLdPeaksMonitorEntry 4 }

oaLdPeaksMonitorPeakWavelength OBJECT-TYPE
        SYNTAX  INTEGER
        ACCESS  read-only
        STATUS  mandatory
        DESCRIPTION
        "The peak wavelength. Units: 0.01 [nm]."
        ::= { oaLdPeaksMonitorEntry 5 }

oaLdPeaksMonitorPeakPower OBJECT-TYPE
        SYNTAX  INTEGER
        ACCESS  read-only
        STATUS  mandatory
        DESCRIPTION
        "The peak power. Units: 0.1 [dBm]"
        ::= { oaLdPeaksMonitorEntry 6 }

oaLdPeaksMonitorTotalPower OBJECT-TYPE
        SYNTAX  INTEGER
        ACCESS  read-only
        STATUS  mandatory
        DESCRIPTION
        "The total power. Units: 0.1 [dBm]"
        ::= { oaLdPeaksMonitorEntry 7 }

oaLdPeaksMonitorOsnr OBJECT-TYPE
        SYNTAX  INTEGER
        ACCESS  read-only
        STATUS  mandatory
        DESCRIPTION
        "The peak OSNR. Units: 0.1 [dB]"
        ::= { oaLdPeaksMonitorEntry 8 }

oaLdPeaksMonitorLeftValleyFreq OBJECT-TYPE
        SYNTAX  INTEGER
        ACCESS  read-only
        STATUS  mandatory
        DESCRIPTION
        "The peak Left valley Frequency. Units: 0.0001 [THz]."
        ::= { oaLdPeaksMonitorEntry 9 }

oaLdPeaksMonitorLeftValleyPower OBJECT-TYPE
        SYNTAX  INTEGER
        ACCESS  read-only
        STATUS  mandatory
        DESCRIPTION
        "The peak Left valley Power. Units: 0.1 [dBm]."
        ::= { oaLdPeaksMonitorEntry 10 }

oaLdPeaksMonitorRightValleyFreq OBJECT-TYPE
        SYNTAX  INTEGER
        ACCESS  read-only
        STATUS  mandatory
        DESCRIPTION
        "The peak Right valley Frequency. Units: 0.0001 [THz]."
        ::= { oaLdPeaksMonitorEntry 11 }

oaLdPeaksMonitorRightValleyPower OBJECT-TYPE
        SYNTAX  INTEGER
        ACCESS  read-only
        STATUS  mandatory
        DESCRIPTION
        "The peak Right valley Power. Units: 0.1 [dBm]."
        ::= { oaLdPeaksMonitorEntry 12 }

------------------------------------------------------------------------------
-- OADWDM-MIB - defines DCM Modules Additional parameters
------------------------------------------------------------------------------
oaLdDcmCardPortsTable OBJECT-TYPE
        SYNTAX    SEQUENCE OF OaLdDcmCardPortsTable
        ACCESS    not-accessible
        STATUS    mandatory
        DESCRIPTION
        "Table of installed DCM Cards"
        ::= {oaLdDcmCardAttributes 1}

oaLdDcmCardPortsEntry OBJECT-TYPE
        SYNTAX    OaLdDcmCardPortsTable
        ACCESS    not-accessible
        STATUS    mandatory
        DESCRIPTION
        "Installed DCM Cards"

        INDEX    { oaLdDcmCardPortsSlotNumber, oaLdDcmCardPortsPortNumber }

        ::= { oaLdDcmCardPortsTable 1 }

OaLdDcmCardPortsTable ::= SEQUENCE {
        oaLdDcmCardPortsSlotNumber    INTEGER,
        oaLdDcmCardPortsPortNumber    INTEGER,
        oaLdDcmCardPortsDistance      INTEGER,
        oaLdDcmCardPortsSpacing       INTEGER,
        oaLdDcmCardPortsRate          INTEGER
       }

oaLdDcmCardPortsSlotNumber OBJECT-TYPE
        SYNTAX    INTEGER
        ACCESS    read-only
        STATUS    mandatory
        DESCRIPTION
        "The slot#. An index from 1 to The number of DCM slots"
        ::= { oaLdDcmCardPortsEntry 1 }

oaLdDcmCardPortsPortNumber OBJECT-TYPE
        SYNTAX    INTEGER
        ACCESS    read-only
        STATUS    mandatory
        DESCRIPTION
        "The port#. An index from 1 to The number of ports"
        ::= { oaLdDcmCardPortsEntry 2 }

oaLdDcmCardPortsDistance OBJECT-TYPE
        SYNTAX    INTEGER
        ACCESS    read-only
        STATUS    mandatory
        DESCRIPTION
        "DCM module distance.
        Units: km"
        ::= { oaLdDcmCardPortsEntry 3 }

oaLdDcmCardPortsSpacing OBJECT-TYPE
        SYNTAX    INTEGER
        ACCESS    read-only
        STATUS    mandatory
        DESCRIPTION
        "DCM module spacing.
        Units: GHz"
        ::= { oaLdDcmCardPortsEntry 4 }

oaLdDcmCardPortsRate OBJECT-TYPE
        SYNTAX    INTEGER
        ACCESS    read-only
        STATUS    mandatory
        DESCRIPTION
    	"DCM module rate.
    	Units: Giga"
        ::= { oaLdDcmCardPortsEntry 5 }


------------------------------------------------------------------------------
-- TRAPS
------------------------------------------------------------------------------

    powerSupplyUpLD TRAP-TYPE
        ENTERPRISE  oaLambdaDriver
        VARIABLES { oaLdDevPSIndex }
        DESCRIPTION
            "The SNMP trap that is generated when
             power supply unit changes it's state from notActive to active"
              ::= 2

    powerSupplyDownLD TRAP-TYPE
        ENTERPRISE  oaLambdaDriver
        VARIABLES { oaLdDevPSIndex }
        DESCRIPTION
            "The SNMP trap that is generated when
             power supply unit changes it's state from active to notActive"
              ::= 3

    powerSupplyInLD TRAP-TYPE
        ENTERPRISE  oaLambdaDriver
        VARIABLES { oaLdDevPSIndex }
        DESCRIPTION
            "The SNMP trap that is generated when
             power supply unit is inserted into the chassis"
              ::= 4

    powerSupplyOutLD TRAP-TYPE
        ENTERPRISE  oaLambdaDriver
        VARIABLES { oaLdDevPSIndex }
        DESCRIPTION
            "The SNMP trap that is generated when
             power supply unit is taken out of the chassis"
              ::= 5

    fanUp TRAP-TYPE
        ENTERPRISE  oaLambdaDriver
        VARIABLES { oaLdDevFANIndex }
        DESCRIPTION
            "The SNMP trap that is generated when
             Fan unit changes it's state from notActive or fail to active"
              ::= 10

    fanDown TRAP-TYPE
        ENTERPRISE  oaLambdaDriver
        VARIABLES { oaLdDevFANIndex }
        DESCRIPTION
            "The SNMP trap that is generated when
             Fan unit changes it's state from active to notActive or fail"
              ::= 11

    switchPrimary TRAP-TYPE
        ENTERPRISE  oaLambdaDriver
        DESCRIPTION
            "The SNMP trap that is generated when
             optical switch on redundant card changes it's state
             from Secondary to Primary"
              ::= 12

    switchSecondary TRAP-TYPE
        ENTERPRISE  oaLambdaDriver
        DESCRIPTION
            "The SNMP trap that is generated when
             optical switch on redundant card changes it's state
             from Primary to Secondary"
              ::= 13

    configChangeIn TRAP-TYPE
        ENTERPRISE  oaLambdaDriver
        VARIABLES { oaLdCardIndex }
        DESCRIPTION
            "The SNMP trap that is generated when
             a card is inserted into the chassis"
              ::= 14

    transponderAccessRx TRAP-TYPE
        ENTERPRISE  oaLambdaDriver
        VARIABLES { oaLdCardIndex, oaLdCardOptAccRx}
        DESCRIPTION
            "The SNMP trap that is generated when
             a transponder card changes it's Access receive indication.
             Note: this trap is send only if oaLdTrapsVer is not supported"
              ::= 15

    transponderWdmRx TRAP-TYPE
        ENTERPRISE  oaLambdaDriver
        VARIABLES { oaLdCardIndex, oaLdCardOptDwdmRx }
        DESCRIPTION
            "The SNMP trap that is generated when
             a transponder card changes it's WDM receive indication.
             Note: this trap is send only if oaLdTrapsVer is not supported"
              ::= 17

    configChangeOut TRAP-TYPE
        ENTERPRISE  oaLambdaDriver
        VARIABLES { oaLdCardIndex }
        DESCRIPTION
            "The SNMP trap that is generated when
             a card is taken out of the chassis"
              ::= 19

    transponderCardLoopBack TRAP-TYPE
        ENTERPRISE  oaLambdaDriver
        VARIABLES { oaLdCardIndex, oaLdCardLoopBack }
        DESCRIPTION
            "The SNMP trap that is generated when
             a transponder card changes it's LoopBack state.
             Note: this trap is send only if oaLdTrapsVer is not supported"
              ::= 20

    redundantCardPrimaryRx TRAP-TYPE
        ENTERPRISE  oaLambdaDriver
        VARIABLES { oaLdRedOptSlotNumber, oaLdRedOptPrimaryRx }
        DESCRIPTION
            "The SNMP trap that is generated when
             on redundant card the Primary fiber Receive status is changed"
              ::= 21

    redundantCardSecondaryRx TRAP-TYPE
        ENTERPRISE  oaLambdaDriver
        VARIABLES { oaLdRedOptSlotNumber, oaLdRedOptSecondaryRx }
        DESCRIPTION
            "The SNMP trap that is generated when
             on redundant card the Secondary fiber Receive status is changed"
              ::= 22

    cardPortsLink TRAP-TYPE
        ENTERPRISE  oaLambdaDriver
        VARIABLES { oaLdCardPortsSlotNumber, oaLdCardPortsPortNumber, oaLdCardPortsLink }
        DESCRIPTION
            "The SNMP trap that is generated when
             the link status of a port at the card is changed.
             Note: this trap is send only if oaLdTrapsVer is not supported"
              ::= 23

    transponderEntityAccessRx TRAP-TYPE
        ENTERPRISE  oaLambdaDriver
        VARIABLES { oaLdCardEntityCardIndex, oaLdCardEntityEntityIndex, oaLdCardEntityOptAccRx}
        DESCRIPTION
            "The SNMP trap that is generated when
             a transponder at a card changes it's Access receive indication.
             Note: this trap is send only if oaLdTrapsVer is not supported"
              ::= 25

    transponderEntityWdmRx TRAP-TYPE
        ENTERPRISE  oaLambdaDriver
        VARIABLES { oaLdCardEntityCardIndex, oaLdCardEntityEntityIndex, oaLdCardEntityOptDwdmRx }
        DESCRIPTION
            "The SNMP trap that is generated when
             a transponder at a card changes it's WDM receive indication.
             Note: this trap is send only if oaLdTrapsVer is not supported"
              ::= 27

    transponderEntityLoopBack TRAP-TYPE
        ENTERPRISE  oaLambdaDriver
        VARIABLES { oaLdCardEntityCardIndex, oaLdCardEntityEntityIndex, oaLdCardEntityLoopBack }
        DESCRIPTION
            "The SNMP trap that is generated when
             a transponder entity changes it's LoopBack state.
             Note: this trap is send only if oaLdTrapsVer is not supported"
              ::= 28

    transponderCardPortsLoopBack TRAP-TYPE
        ENTERPRISE  oaLambdaDriver
        VARIABLES { oaLdCardPortsSlotNumber, oaLdCardPortsPortNumber, oaLdCardPortsLoopBack }
        DESCRIPTION
            "The SNMP trap that is generated when
             a transponder port changes it's LoopBack state.
             Note: this trap is send only if oaLdTrapsVer is not supported"
              ::= 29

   transponderAccessRxOn TRAP-TYPE
        ENTERPRISE  oaLambdaDriver
        VARIABLES { oaLdCardIndex, oaDevTrapsPortsIfAlias }
        DESCRIPTION
            "The SNMP trap that is generated when
             a transponder card changes it's Access receive indication to ON"
              ::= 30

   transponderAccessRxOff TRAP-TYPE
        ENTERPRISE  oaLambdaDriver
        VARIABLES { oaLdCardIndex, oaDevTrapsPortsIfAlias }
        DESCRIPTION
            "The SNMP trap that is generated when
             a transponder card changes it's Access receive indication to Off"
              ::= 31

    transponderWdmRxOn TRAP-TYPE
        ENTERPRISE  oaLambdaDriver
        VARIABLES { oaLdCardIndex, oaDevTrapsPortsIfAlias }
        DESCRIPTION
            "The SNMP trap that is generated when
             a transponder card changes it's WDM receive indication to On"
              ::= 32

    transponderWdmRxOff TRAP-TYPE
        ENTERPRISE  oaLambdaDriver
        VARIABLES { oaLdCardIndex, oaDevTrapsPortsIfAlias }
        DESCRIPTION
            "The SNMP trap that is generated when
             a transponder card changes it's WDM receive indication to Off"
              ::= 33

    transponderCardLoopBackLoop TRAP-TYPE
        ENTERPRISE  oaLambdaDriver
        VARIABLES { oaLdCardIndex, oaLdCardLoopBack, oaDevTrapsPortsIfAlias }
        DESCRIPTION
            "The SNMP trap that is generated when
             a transponder card changes it's LoopBack state to loop"
              ::= 34

    transponderCardLoopBackNormal TRAP-TYPE
        ENTERPRISE  oaLambdaDriver
        VARIABLES { oaLdCardIndex, oaLdCardLoopBack, oaDevTrapsPortsIfAlias }
        DESCRIPTION
            "The SNMP trap that is generated when
             a transponder card changes it's LoopBack state to normal"
              ::= 35

    cardPortsLinkOn TRAP-TYPE
        ENTERPRISE  oaLambdaDriver
        VARIABLES { oaLdCardPortsSlotNumber, oaLdCardPortsPortNumber, oaDevTrapsPortsIfAlias }
        DESCRIPTION
            "The SNMP trap that is generated when
             the link status of a port at the card is changed to On"
              ::= 36

   cardPortsLinkOff TRAP-TYPE
        ENTERPRISE  oaLambdaDriver
        VARIABLES { oaLdCardPortsSlotNumber, oaLdCardPortsPortNumber, oaDevTrapsPortsIfAlias }
        DESCRIPTION
            "The SNMP trap that is generated when
             the link status of a port at the card is changed to Off"
              ::= 37

    transponderEntityAccessRxOn TRAP-TYPE
        ENTERPRISE  oaLambdaDriver
        VARIABLES { oaLdCardEntityCardIndex, oaLdCardEntityEntityIndex, oaDevTrapsPortsIfAlias }
        DESCRIPTION
            "The SNMP trap that is generated when
             a transponder at a card changes it's Access receive indication to On"
              ::= 38

   transponderEntityAccessRxOff TRAP-TYPE
        ENTERPRISE  oaLambdaDriver
        VARIABLES { oaLdCardEntityCardIndex, oaLdCardEntityEntityIndex, oaDevTrapsPortsIfAlias }
        DESCRIPTION
            "The SNMP trap that is generated when
             a transponder at a card changes it's Access receive indication to Off"
              ::= 39

    transponderEntityWdmRxOn TRAP-TYPE
        ENTERPRISE  oaLambdaDriver
        VARIABLES { oaLdCardEntityCardIndex, oaLdCardEntityEntityIndex, oaDevTrapsPortsIfAlias }
        DESCRIPTION
            "The SNMP trap that is generated when
             a transponder at a card changes it's WDM receive indication to On"
              ::= 40

    transponderEntityWdmRxOff TRAP-TYPE
        ENTERPRISE  oaLambdaDriver
        VARIABLES { oaLdCardEntityCardIndex, oaLdCardEntityEntityIndex, oaDevTrapsPortsIfAlias }
        DESCRIPTION
            "The SNMP trap that is generated when
             a transponder at a card changes it's WDM receive indication to Off"
              ::= 41

    transponderEntityLoopBackLoop TRAP-TYPE
        ENTERPRISE  oaLambdaDriver
        VARIABLES { oaLdCardEntityCardIndex, oaLdCardEntityEntityIndex, oaLdCardEntityLoopBack, oaDevTrapsPortsIfAlias }
        DESCRIPTION
            "The SNMP trap that is generated when
             a transponder entity changes it's LoopBack state to loop"
              ::= 42

    transponderEntityLoopBackNormal TRAP-TYPE
        ENTERPRISE  oaLambdaDriver
        VARIABLES { oaLdCardEntityCardIndex, oaLdCardEntityEntityIndex, oaLdCardEntityLoopBack, oaDevTrapsPortsIfAlias }
        DESCRIPTION
            "The SNMP trap that is generated when
             a transponder entity changes it's LoopBack state to normal"
              ::= 43

    transponderCardPortsLoopBackLoop TRAP-TYPE
        ENTERPRISE  oaLambdaDriver
        VARIABLES { oaLdCardPortsSlotNumber, oaLdCardPortsPortNumber, oaLdCardPortsLoopBack, oaDevTrapsPortsIfAlias }
        DESCRIPTION
            "The SNMP trap that is generated when
             a transponder port changes it's LoopBack state to loop"
              ::= 44

    transponderCardPortsLoopBackNormal TRAP-TYPE
        ENTERPRISE  oaLambdaDriver
        VARIABLES { oaLdCardPortsSlotNumber, oaLdCardPortsPortNumber, oaLdCardPortsLoopBack, oaDevTrapsPortsIfAlias }
        DESCRIPTION
            "The SNMP trap that is generated when
             a transponder port changes it's LoopBack state to normal"
              ::= 45

    redCardPositionPrimary TRAP-TYPE
        ENTERPRISE  oaLambdaDriver
        VARIABLES { oaLdCardIndex }
        DESCRIPTION
            "The SNMP trap that is generated when
             optical switch on redundant card changes it's state
             from Secondary to Primary"
              ::= 46

    redCardPositionSecondary TRAP-TYPE
        ENTERPRISE  oaLambdaDriver
        VARIABLES { oaLdCardIndex }
        DESCRIPTION
            "The SNMP trap that is generated when
             optical switch on redundant card changes it's state
             from Primary to Secondary"
              ::= 47

    oaLdCardTemperatureNormal TRAP-TYPE
        ENTERPRISE  oaLambdaDriver
        VARIABLES { oaLdCardPortsSlotNumber }
        DESCRIPTION
            "The SNMP trap that is generated when Temperature
             of the card placed in the corresponding slot
             returned to Normal."
              ::= 48

    oaLdCardTemperatureHigh TRAP-TYPE
        ENTERPRISE  oaLambdaDriver
        VARIABLES { oaLdCardPortsSlotNumber }
        DESCRIPTION
            "The SNMP trap that is generated when Temperature
             of the card placed in the corresponding slot
             became too High."
              ::= 49

    oaLdOAmplifierInputAlarmOn TRAP-TYPE
        ENTERPRISE  oaLambdaDriver
        VARIABLES { oaLdCardPortsSlotNumber }
        DESCRIPTION
            "The SNMP trap that is generated when
             an Optical Amplifier Input Power exceeds its threshold value."
              ::= 50

    oaLdOAmplifierInputAlarmOff TRAP-TYPE
        ENTERPRISE  oaLambdaDriver
        VARIABLES { oaLdCardPortsSlotNumber }
        DESCRIPTION
            "The SNMP trap that is generated when
             an Optical Amplifier Input Power returns below its threshold value."
              ::= 51

    oaLdOAmplifierOutputAlarmOn TRAP-TYPE
        ENTERPRISE  oaLambdaDriver
        VARIABLES { oaLdCardPortsSlotNumber }
        DESCRIPTION
            "The SNMP trap that is generated when
             an Optical Amplifier Output Power exceeds its threshold value."
              ::= 52

    oaLdOAmplifierOutputAlarmOff TRAP-TYPE
        ENTERPRISE  oaLambdaDriver
        VARIABLES { oaLdCardPortsSlotNumber }
        DESCRIPTION
            "The SNMP trap that is generated when
             an Optical Amplifier Output Power returns below its threshold value."
              ::= 53

    oaLdOAmplifierModuleTempAlarmOn TRAP-TYPE
        ENTERPRISE  oaLambdaDriver
        VARIABLES { oaLdCardPortsSlotNumber }
        DESCRIPTION
            "The SNMP trap that is generated when
             an Optical Amplifier Module Temperature exceeds its threshold value."
              ::= 54

    oaLdOAmplifierModuleTempAlarmOff TRAP-TYPE
        ENTERPRISE  oaLambdaDriver
        VARIABLES { oaLdCardPortsSlotNumber }
        DESCRIPTION
            "The SNMP trap that is generated when
             an Optical Amplifier Module Temperature returns below its threshold value."
              ::= 55

    oaLdOAmplifierInput2AlarmOn TRAP-TYPE
        ENTERPRISE  oaLambdaDriver
        VARIABLES { oaLdCardPortsSlotNumber }
        DESCRIPTION
            "The SNMP trap that is generated when
             an Optical Amplifier Input2 Power exceeds its threshold value."
              ::= 56

    oaLdOAmplifierInput2AlarmOff TRAP-TYPE
        ENTERPRISE  oaLambdaDriver
        VARIABLES { oaLdCardPortsSlotNumber }
        DESCRIPTION
            "The SNMP trap that is generated when
             an Optical Amplifier Input2 Power returns below its threshold value."
              ::= 57

    oaLdOAmplifierPSAlarmOn TRAP-TYPE
        ENTERPRISE  oaLambdaDriver
        VARIABLES { oaLdCardPortsSlotNumber }
        DESCRIPTION
            "The SNMP trap that is generated when
             an Optical Amplifier PS Voltage Current exceeds its threshold value."
              ::= 58

    oaLdOAmplifierPSAlarmOff TRAP-TYPE
        ENTERPRISE  oaLambdaDriver
        VARIABLES { oaLdCardPortsSlotNumber }
        DESCRIPTION
            "The SNMP trap that is generated when
             an Optical Amplifier PS Voltage Current returns below its threshold value."
              ::= 59

    oaLdOAmplifierAutoShutdownAlarmOn TRAP-TYPE
        ENTERPRISE  oaLambdaDriver
        VARIABLES { oaLdCardPortsSlotNumber }
        DESCRIPTION
            "The SNMP trap that is generated when
             an Optical Amplifier Auto Shutdown exceeds its threshold value."
              ::= 60

    oaLdOAmplifierAutoShutdownAlarmOff TRAP-TYPE
        ENTERPRISE  oaLambdaDriver
        VARIABLES { oaLdCardPortsSlotNumber }
        DESCRIPTION
            "The SNMP trap that is generated when
             an Optical Amplifier Auto Shutdown returns below its threshold value."
              ::= 61

    oaLdOAmplifierPumpTempAlarmOn TRAP-TYPE
        ENTERPRISE  oaLambdaDriver
        VARIABLES { oaLdCardPortsSlotNumber }
        DESCRIPTION
            "The SNMP trap that is generated when
             an Optical Amplifier Pump Temperature exceeds its threshold value."
              ::= 62

    oaLdOAmplifierPumpTempAlarmOff TRAP-TYPE
        ENTERPRISE  oaLambdaDriver
        VARIABLES { oaLdCardPortsSlotNumber }
        DESCRIPTION
            "The SNMP trap that is generated when
             an Optical Amplifier Pump Temperature returns below its threshold value."
              ::= 63

    oaLdOAmplifierPumpDriveCurrentAlarmOn TRAP-TYPE
        ENTERPRISE  oaLambdaDriver
        VARIABLES { oaLdCardPortsSlotNumber }
        DESCRIPTION
            "The SNMP trap that is generated when
             an Optical Amplifier Pump Drive Current exceeds its threshold value."
              ::= 64

    oaLdOAmplifierPumpDriveCurrentAlarmOff TRAP-TYPE
        ENTERPRISE  oaLambdaDriver
        VARIABLES { oaLdCardPortsSlotNumber }
        DESCRIPTION
            "The SNMP trap that is generated when
             an Optical Amplifier Pump Drive Current returns below its threshold value."
              ::= 65

    oaLdRamanAmplifierReflectedAlarmOn TRAP-TYPE
        ENTERPRISE  oaLambdaDriver
        VARIABLES { oaLdCardPortsSlotNumber }
        DESCRIPTION
            "The SNMP trap that is generated when
             an Optical Raman Amplifier Reflected Power exceeds its threshold value."
              ::= 66

    oaLdRamanAmplifierReflectedAlarmOff TRAP-TYPE
        ENTERPRISE  oaLambdaDriver
        VARIABLES { oaLdCardPortsSlotNumber }
        DESCRIPTION
            "The SNMP trap that is generated when
             an Optical Raman Amplifier Reflected Power returns below its threshold value."
              ::= 67

    oaLdDevCPUForceSwitchoverCommandInvoked TRAP-TYPE
        ENTERPRISE  oaLambdaDriver
        DESCRIPTION
            "The SNMP trap that is generated when
             the command 'CPU Force Switchover is invoked."
              ::= 94

    oaLdFiberPrbsTestError TRAP-TYPE
        ENTERPRISE  oaLambdaDriver
        VARIABLES { oaLdCardIndex }
        DESCRIPTION
            "The SNMP trap that is generated when
             error is occurred during Fiber PRBS emulation test."
              ::= 95

    oaLdEMPortDryContactClosed TRAP-TYPE
        ENTERPRISE  oaLambdaDriver
        VARIABLES { oaLdCardPortsSlotNumber, oaLdCardPortsPortNumber, oaDevTrapsPortsIfAlias }
        DESCRIPTION
            "The SNMP trap that is generated when
             the Dry Contact of E&M port is closed."
              ::= 96

    oaLdEMPortDryContactOpened TRAP-TYPE
        ENTERPRISE  oaLambdaDriver
        VARIABLES { oaLdCardPortsSlotNumber, oaLdCardPortsPortNumber, oaDevTrapsPortsIfAlias }
        DESCRIPTION
            "The SNMP trap that is generated when
             the Dry Contact of E&M port is opened."
              ::= 97

    oaLdCardRestarted TRAP-TYPE
        ENTERPRISE  oaLambdaDriver
        VARIABLES { oaLdCardPortsSlotNumber }
        DESCRIPTION
            "The SNMP trap that is generated when
             card placed in the corresponding slot
             was restarted."
              ::= 163

   redundantCardPrimaryRxOn TRAP-TYPE
        ENTERPRISE  oaLambdaDriver
        VARIABLES { oaLdRedOptSlotNumber }
        DESCRIPTION
            "The SNMP trap that is generated when
             on redundant card the Primary fiber Receive status is changed to On"
              ::= 164

   redundantCardPrimaryRxOff TRAP-TYPE
        ENTERPRISE  oaLambdaDriver
        VARIABLES { oaLdRedOptSlotNumber }
        DESCRIPTION
            "The SNMP trap that is generated when
             on redundant card the Primary fiber Receive status is changed to Off"
              ::= 165

    redundantCardSecondaryRxOn TRAP-TYPE
        ENTERPRISE  oaLambdaDriver
        VARIABLES { oaLdRedOptSlotNumber }
        DESCRIPTION
            "The SNMP trap that is generated when
             on redundant card the Secondary fiber Receive status is changed to On"
              ::= 166

    redundantCardSecondaryRxOff TRAP-TYPE
        ENTERPRISE  oaLambdaDriver
        VARIABLES { oaLdRedOptSlotNumber }
        DESCRIPTION
            "The SNMP trap that is generated when
             on redundant card the Secondary fiber Receive status is changed Off"
              ::= 167

    cardPortsPrimaryClockSource TRAP-TYPE
        ENTERPRISE  oaLambdaDriver
        VARIABLES { oaLdCardEntityCardIndex, oaLdCardEntityEntityIndex, oaLdCardEntityClockSource , oaDevTrapsPortsIfAlias}
        DESCRIPTION
            "The SNMP trap that is generated when
             the module's clock source changed to the primary (user selected) port"
              ::= 168

    cardPortsNonPrimaryClockSource TRAP-TYPE
        ENTERPRISE  oaLambdaDriver
        VARIABLES { oaLdCardEntityCardIndex, oaLdCardEntityEntityIndex, oaLdCardEntityClockSource , oaDevTrapsPortsIfAlias}
        DESCRIPTION
            "The SNMP trap that is generated when
             the modules's clock source changed to a non-primary port"
              ::= 169

    eyemaxScanningStart TRAP-TYPE
        ENTERPRISE  oaLambdaDriver
        VARIABLES { oaLdCardPortsSlotNumber, oaLdCardPortsPortNumber, oaDevTrapsPortsIfAlias }
        DESCRIPTION
            "The SNMP trap that is generated when
             Eyemax Scanning is started on module or on port of module."
              ::= 170

    eyemaxScanningCompleted TRAP-TYPE
        ENTERPRISE  oaLambdaDriver
        VARIABLES { oaLdCardPortsSlotNumber, oaLdCardPortsPortNumber, oaDevTrapsPortsIfAlias }
        DESCRIPTION
            "The SNMP trap that is generated when
             Eyemax Scanning is completed on module or on port of module."
              ::= 171

    powerBalancingDone TRAP-TYPE
        ENTERPRISE  oaLambdaDriver
        VARIABLES { oaLdCardPortsSlotNumber, oaLdCardPortsPortNumber, oaDevTrapsPortsIfAlias }
        DESCRIPTION
            "The SNMP trap that is generated when
             Power Balancing process is successfully completed on port of module."
              ::= 172

    powerBalancingNegate TRAP-TYPE
        ENTERPRISE  oaLambdaDriver
        VARIABLES { oaLdCardPortsSlotNumber, oaLdCardPortsPortNumber, oaDevTrapsPortsIfAlias }
        DESCRIPTION
            "The SNMP trap that is generated when
             results of Power Balancing process are successfully negated on port of module."
              ::= 173

    rebootIsRequestedByUser TRAP-TYPE
        ENTERPRISE  oaLambdaDriver
        DESCRIPTION
            "The SNMP trap that is generated when the user initiates reboot process on device."
              ::= 174

END
