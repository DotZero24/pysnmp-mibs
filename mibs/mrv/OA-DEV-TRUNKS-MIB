--  =======================================================================
--  File        : oaTrunk.mib
--  Description : Private MIB for Device Trunk (Link Agregation) parameters
--  By          : Edna & Yakov
--  Version     : 0.2
--  Date        :
--  =======================================================================
--
--
-- Copyright (c) 2007 MRV.  All Rights Reserved.
--
--
-- Reproduction of this document is authorized on condition that this
-- copyright notice is included.  This MRV SNMP MIB Specification
-- embodies MRV's proprietary intellectual property.  MRV
-- retains all title and ownership in the specification, including any
-- revisions.
--
-- It is MRV's intent to encourage the widespread use of this
-- specification in connection with the management of MRV's
-- products. MRV grants vendor, end-users, and other interested
-- parties a non-exclusive license to use this specification in
-- connection with the management of MRV's products.
--
-- This specification is supplied "AS IS," and MRV makes no
-- warranty, either express or implied, as to the use, operation,
-- condition, or performance of the specification.
--
-- Copyright text courtesy of MRV
--
-- If you have any questions about this MIB, please call MRV
-- Technical Support Center at 1-800-858-7815 from inside USA or
-- 1-818-773-0900 from outside USA.
--
--
-- MRV retains the right to change this MIB without notification.
--

OA-DEV-TRUNKS-MIB DEFINITIONS ::= BEGIN

  IMPORTS
    MODULE-IDENTITY, OBJECT-TYPE, enterprises,
    Integer32 				         FROM SNMPv2-SMI    -- RFC2578
    MODULE-COMPLIANCE, OBJECT-GROUP              FROM SNMPv2-CONF   -- RFC2580
    DisplayString                                FROM SNMPv2-TC;    -- RFC2579

oaDeviceTrunks  MODULE-IDENTITY
    LAST-UPDATED "200712110000Z"  -- Dec 11, 2007
    ORGANIZATION "MRV Communications, Inc."
    CONTACT-INFO
        "Edna Ganon
         MRV Communication, Inc
         http://www.mrv.com
         Email:  eganon@mrv.com

         Inna Levin
         MRV Communication, Inc
         http://www.mrv.com
         Email:  ilevin@mrv.com

         Yakov Vaisman
         MRV Communication, Inc
         http://www.mrv.com
         Email:  yvaisman@mrv.com
        "

    DESCRIPTION
        "Supports information about
         Device Link Aggregation (Trunks)."

    -- Revision history

    REVISION "200712110000Z"  -- Dec 11, 2007
    DESCRIPTION
        "Revision 0.2: MIB Object [oaDevTrunkGrPortLogicalNumber] added."

    REVISION "200708020000Z"  -- Aug 2, 2007
    DESCRIPTION
        "Initial edition."

    ::= { nbDevGen 23 }

-- ************************************************************
-- MRV Object Identifier Definition
-- ************************************************************

nbase              OBJECT IDENTIFIER ::= { enterprises 629 }
nbSwitchG1         OBJECT IDENTIFIER ::= { nbase 1 }
nbSwitchG1Il       OBJECT IDENTIFIER ::= { nbSwitchG1 50}

-- GROUPS for General Device Configuration
nbDeviceConfig     OBJECT IDENTIFIER ::= { nbSwitchG1Il 11}
nbDevGen           OBJECT IDENTIFIER ::= { nbDeviceConfig 1 }

oaDevTrunkGen      OBJECT IDENTIFIER ::= { oaDeviceTrunks 1 }
oaDevTrunks        OBJECT IDENTIFIER ::= { oaDeviceTrunks 2 }

oaDevTrunkConformance   OBJECT IDENTIFIER ::= { oaDeviceTrunks 101 }

-- ************************************************************************
-- Objects for Device Events General group
-- ************************************************************************

oaDevTrunkGenSupport OBJECT-TYPE
    SYNTAX  INTEGER {
       notSupported (1),
       supported    (2)
    }
    MAX-ACCESS  read-only
    STATUS  current
    DESCRIPTION
    "Device  Link Aggregation (Trunk) feature support."

    ::= { oaDevTrunkGen 1 }

-- ************************************************************
-- Objects in the Device Link Aggregation (Trunk) Table
-- ************************************************************

oaDevTrunkGrNumber OBJECT-TYPE
    SYNTAX  Integer32
    MAX-ACCESS  read-only
    STATUS  current
    DESCRIPTION
    "Device Link Aggregations (Trunks) number in the Table."

    ::= { oaDevTrunks 1 }

oaDevTrunkGrTable         OBJECT-TYPE
    SYNTAX  SEQUENCE OF OaDevTrunkGrEntry
    MAX-ACCESS   not-accessible
    STATUS       current
    DESCRIPTION
    "This table configures Device Link Aggregation (Trunk)."

    ::= { oaDevTrunks 5 }

oaDevTrunkGrEntry OBJECT-TYPE
    SYNTAX       OaDevTrunkGrEntry
    MAX-ACCESS   not-accessible
    STATUS       current
    DESCRIPTION
    "Device Link Aggregation (Trunk) table entry."
    INDEX { oaDevTrunkGrId }

    ::= { oaDevTrunkGrTable 1 }

OaDevTrunkGrEntry ::= SEQUENCE {
    oaDevTrunkGrId                 Integer32,
    oaDevTrunkGrDescription        DisplayString,
    oaDevTrunkGrPortMembers        OCTET STRING,
    oaDevTrunkGrPortsNumber        Integer32,
    oaDevTrunkGrAdminStatus        INTEGER,
    oaDevTrunkGrPortLogicalNumber  Integer32
    }

oaDevTrunkGrId    OBJECT-TYPE
    SYNTAX Integer32 (1..2147483647)
    MAX-ACCESS   not-accessible
    STATUS  current
    DESCRIPTION
    "The index of the Trunks Table.
     Actual maximal number of Trunks is system dependent value."

    ::= { oaDevTrunkGrEntry 1 }

oaDevTrunkGrDescription    OBJECT-TYPE
    SYNTAX       DisplayString (SIZE (0..255))
    MAX-ACCESS   read-write
    STATUS       current
    DESCRIPTION
    "Trunk Description."

    ::= { oaDevTrunkGrEntry 2 }

oaDevTrunkGrPortMembers    OBJECT-TYPE
    SYNTAX     OCTET STRING (SIZE (0..32))
    MAX-ACCESS read-write
    STATUS     current
    DESCRIPTION
    "List of Ports making the Trunk [order: from first up to last].
     Each octet contains the corresponding number of Port."

    ::= { oaDevTrunkGrEntry 3 }

oaDevTrunkGrPortsNumber    OBJECT-TYPE
    SYNTAX Integer32
    MAX-ACCESS   read-only
    STATUS  current
    DESCRIPTION
    "Number of Ports in the Trunk."

    ::= { oaDevTrunkGrEntry 4 }

oaDevTrunkGrAdminStatus    OBJECT-TYPE
    SYNTAX       INTEGER {
       validId     (1),
       invalid     (2),
       validNoId   (3)
    }
    MAX-ACCESS   read-write
    STATUS  current
    DESCRIPTION
    "Controls creation/modification/invalidation of the Trunk entry.
     'validId'  - create new entry according to customer Trunk Id [SNMP GET/SET].
     'invalid'  - remove existing Trunk entry [SNMP SET].
     'validNoId'- create new entry without customer Trunk Id [SNMP SET]
                 (system will find the best compatible Id automatically)."

    ::= { oaDevTrunkGrEntry 5 }

oaDevTrunkGrPortLogicalNumber    OBJECT-TYPE
    SYNTAX Integer32
    MAX-ACCESS   read-only
    STATUS  current
    DESCRIPTION
    "The Trunks logical Port Number.
     Port Number = 132 + [oaDevTrunkGrId] ."

    ::= { oaDevTrunkGrEntry 6 }

-- *******************************************************************
--  Conformance Information
-- *******************************************************************

oaDevTrunkMIBCompliances  OBJECT IDENTIFIER ::= { oaDevTrunkConformance 1 }
oaDevTrunkMIBGroups       OBJECT IDENTIFIER ::= { oaDevTrunkConformance 2 }

-- *******************************************************************
--  Compliance Information
-- *******************************************************************

oaDevTrunkMIBCompliance   MODULE-COMPLIANCE
    STATUS current
    DESCRIPTION
    "The core compliance statement for all
     'oaDeviceTrunks' MIB implementations."

    MODULE -- this module

    MANDATORY-GROUPS {
                      oaDevTrunkMandatoryGroup
                     }

    ::= { oaDevTrunkMIBCompliances 1 }

-- ...................................................................
-- Conformance Groups
-- ...................................................................

oaDevTrunkMandatoryGroup  OBJECT-GROUP
    OBJECTS {
             oaDevTrunkGenSupport,
             oaDevTrunkGrNumber,

--             oaDevTrunkGrId,
             oaDevTrunkGrDescription,
             oaDevTrunkGrPortMembers,
             oaDevTrunkGrPortsNumber,
             oaDevTrunkGrAdminStatus,
             oaDevTrunkGrPortLogicalNumber
            }
    STATUS current
    DESCRIPTION
    "Mandatory objects for grouping of Device Trunk parameters."

    ::= { oaDevTrunkMIBGroups 1 }

END
