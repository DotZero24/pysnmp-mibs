--  ==========================================================================
--  File          : oaSonet.mib
--  Description   : Private MIB for Sonet (extension to Standard SONET MIB (RFC2558)
--
--  By            : Maoz Yona, Yakov Vaisman
--  Version       : Revision:   0.4
--  Original Date : July 15, 2008
--  Last Change   : Date:   April 14, 2011
--  ==========================================================================
--
--
-- Copyright (c) 2005 MRV.  All Rights Reserved.
--
-- Reproduction of this document is authorized on condition that this
-- copyright notice is included.  This MRV SNMP MIB Specification
-- embodies MRV proprietary intellectual property.  MRV
-- retains all title and ownership in the specification, including any
-- revisions.
--
-- It is MRV's intent to encourage the widespread use of this
-- specification in connection with the management of MRV's
-- products. MRV grants vendor, end-users, and other interested
-- parties a non-exclusive license to use this specification in
-- connection with the management of MRV's products.
--
-- This specification is supplied "AS IS," and MRV makes no
-- warranty, either express or implied, as to the use, operation,
-- condition, or performance of the specification.
--
-- MRV retains the right to change this MIB without notification.
--
OA-SONET-MIB DEFINITIONS ::= BEGIN

IMPORTS
        oaLdCardPortsSlotNumber,
        oaLdCardPortsPortNumber     FROM OADWDM-MIB
        oaDevTrapsPortsIfAlias      FROM OA-TRAP-MESSAGES-MIB
        MODULE-IDENTITY,
        NOTIFICATION-TYPE,
        enterprises, Integer32,
        OBJECT-TYPE, Unsigned32     FROM SNMPv2-SMI          -- RFC2578
        MODULE-COMPLIANCE,
        NOTIFICATION-GROUP,
        OBJECT-GROUP                FROM SNMPv2-CONF         -- RFC2580
        TruthValue                  FROM SNMPv2-TC           -- RFC2579
        PerfIntervalCount           FROM PerfHist-TC-MIB;    -- RFC3593

------------------------------------------------------------------------------
-- Object Identifier Definition
------------------------------------------------------------------------------

oaSonetMib   MODULE-IDENTITY
    LAST-UPDATED "200807150000Z" -- July 15, 2008
    ORGANIZATION "MRV Communications, Inc."
    CONTACT-INFO
    "Maoz Yona
     MRV Communication, Inc
     http://www.mrv.com
     Email:  myona@mrv.com
    "

    DESCRIPTION
    "This MIB is an extension to the standard SONET MIB (RFC2558)."

    -- Revision history

    REVISION "200807150000Z" -- July 15, 2008
    DESCRIPTION "Initial MIB Creation."

    ::= { oaManagement 81 }

-- ************************************************************
-- MIB place Definition
-- ************************************************************

oaccess                OBJECT IDENTIFIER ::= { enterprises 6926 }
oaManagement           OBJECT IDENTIFIER ::= { oaccess 1 }

oaSonetNotifications   OBJECT IDENTIFIER ::= { oaSonetMib 0 }
oaSonetSection         OBJECT IDENTIFIER ::= { oaSonetMib 1 }
oaSonetLine            OBJECT IDENTIFIER ::= { oaSonetMib 2 }
oaSonetGenParams       OBJECT IDENTIFIER ::= { oaSonetMib 4 }

-- ----------------------------------------------------------------
--
-- Sonet Section Alarm table
--
-- ----------------------------------------------------------------


oaSonetSecTcaTable OBJECT-TYPE
    SYNTAX  SEQUENCE OF OaSonetSecTcaEntry
    MAX-ACCESS  not-accessible
    STATUS  current
    DESCRIPTION
    "This table contains setting and reading the Thresholds Crossing
     Alarms (TCAs) of the SONET SECTION."
    ::= { oaSonetSection 1 }

oaSonetSecTcaEntry OBJECT-TYPE
    SYNTAX  OaSonetSecTcaEntry
    MAX-ACCESS  not-accessible
    STATUS  current
    DESCRIPTION
    "An entry in the alarm table. The entries exist for active sonet
     lines, with default threshold values. Thresholds may be configured
     for Errored Seconds (ES), Severely Errored Seconds (SES), Severely
     Errored Framing Seconds (SEFS) and Coding Violations (CV) for
     section layer sonet lines.
     Once these thresholds are exceeded, minor or major alarm is
     raised.
     Please refer RFC1595 for descriptions  of ES,SES,SEFS,CV"

    INDEX { oaSonetSecIfIndex }
    ::= { oaSonetSecTcaTable 1 }

OaSonetSecTcaEntry ::= SEQUENCE
    {
     oaSonetSecIfIndex          Integer32,
     oaSonetSec15MinESsTca      Unsigned32,
     oaSonetSecDayESsTca        Unsigned32,
     oaSonetSec15MinSESsTca     Unsigned32,
     oaSonetSecDaySESsTca       Unsigned32,
     oaSonetSec15MinSEFSsTca    Unsigned32,
     oaSonetSecDaySEFSsTca      Unsigned32,
     oaSonetSec15MinCVsTca      Unsigned32,
     oaSonetSecDayCVsTca        Unsigned32,
     oaSonetSec15MinUASsTca      Unsigned32,
     oaSonetSecDayUASsTca        Unsigned32
    }

oaSonetSecIfIndex OBJECT-TYPE
    SYNTAX  Integer32 (0..10000)
    MAX-ACCESS  accessible-for-notify
    STATUS  current
    DESCRIPTION
    "This object is the ifIndex, based on ifMib"
    ::= { oaSonetSecTcaEntry 1 }

oaSonetSec15MinESsTca OBJECT-TYPE
    SYNTAX  Unsigned32 (0..2147483647)
    MAX-ACCESS  read-write
    STATUS  current
    DESCRIPTION
    "This object indicates the threshold for Errored Seconds (ES),
     for the current 15-min interval, above which alarm is generated."
    REFERENCE
    " RFC2558 Section 3.5, GR-253-CORE "
    DEFVAL {60}
    ::= { oaSonetSecTcaEntry 2 }

oaSonetSecDayESsTca OBJECT-TYPE
    SYNTAX  Unsigned32 (0..2147483647)
    MAX-ACCESS  read-write
    STATUS  current
    DESCRIPTION
    "This object indicates the threshold for Errored Seconds (ES),
     for the 24-hour interval, above which alarm is generated. "
    REFERENCE
    " RFC2558 Section 3.5, GR-253-CORE "
    DEFVAL {600}
    ::= { oaSonetSecTcaEntry 3 }

oaSonetSec15MinSESsTca OBJECT-TYPE
    SYNTAX  Unsigned32 (0..2147483647)
    MAX-ACCESS  read-write
    STATUS  current
    DESCRIPTION
    "This object indicates the threshold for Severely Errored
     Seconds (SES) for the current 15-min interval,
     above which alarm is generated."
    REFERENCE
    " RFC2558 Section 3.5, GR-253-CORE "
    DEFVAL {3}
    ::= { oaSonetSecTcaEntry 4 }

oaSonetSecDaySESsTca OBJECT-TYPE
    SYNTAX  Unsigned32 (0..2147483647)
    MAX-ACCESS  read-write
    STATUS  current
    DESCRIPTION
    "This object indicates the threshold for Severely Errored
     Seconds (SES) for the 24-hour interval,
     above which alarm is generated."
    REFERENCE
    " RFC2558 Section 3.5, GR-253-CORE "
    DEFVAL {7}
    ::= { oaSonetSecTcaEntry 5 }

oaSonetSec15MinSEFSsTca OBJECT-TYPE
    SYNTAX  Unsigned32 (0..2147483647)
    MAX-ACCESS  read-write
    STATUS  current
    DESCRIPTION
    "This object indicates the threshold for Severely Errored
     Framing Seconds (SEFS), above which alarm is generated."
     REFERENCE
    " RFC2558 Section 3.5, GR-253-CORE "
    DEFVAL {75}
    ::= { oaSonetSecTcaEntry 6 }

oaSonetSecDaySEFSsTca OBJECT-TYPE
    SYNTAX  Unsigned32 (0..2147483647)
    MAX-ACCESS  read-write
    STATUS  current
    DESCRIPTION
    "This object indicates the threshold for Severely Errored
     Framing Seconds(SEFS) for the 24-hour interval,
     above which alarm is generated."
    REFERENCE
    " RFC2558 Section 3.5, GR-253-CORE "
    DEFVAL {750}
    ::= { oaSonetSecTcaEntry 7 }

oaSonetSec15MinCVsTca OBJECT-TYPE
    SYNTAX  Unsigned32 (0..2147483647)
    MAX-ACCESS  read-write
    STATUS  current
    DESCRIPTION
    "This object indicates the threshold for Coding Violations (CV),
     above which alarm is generated."
    REFERENCE
    " RFC2558 Section 3.5, GR-253-CORE "
    DEFVAL {75}
    ::= { oaSonetSecTcaEntry 8 }

oaSonetSecDayCVsTca OBJECT-TYPE
    SYNTAX  Unsigned32 (0..2147483647)
    MAX-ACCESS  read-write
    STATUS  current
    DESCRIPTION
    "This object indicates the threshold for Coding Violations (CV)
     for 24-hour interval, above which alarm is generated."
    REFERENCE
    " RFC2558 Section 3.5, GR-253-CORE "
    DEFVAL {750}
    ::= { oaSonetSecTcaEntry 9 }

oaSonetSec15MinUASsTca OBJECT-TYPE
    SYNTAX  Unsigned32 (0..2147483647)
    MAX-ACCESS  read-write
    STATUS  current
    DESCRIPTION
    "This object indicates the threshold for Unavailable Seconds (UAS),
     above which alarm is generated."
    REFERENCE
    " RFC2558 Section 3.5, GR-253-CORE "
    DEFVAL {15}
    ::= { oaSonetSecTcaEntry 10 }

oaSonetSecDayUASsTca OBJECT-TYPE
    SYNTAX  Unsigned32 (0..2147483647)
    MAX-ACCESS  read-write
    STATUS  current
    DESCRIPTION
    "This object indicates the threshold for Unavailable Seconds (UAS)
     for 24-hour interval, above which alarm is generated."
    REFERENCE
    " RFC2558 Section 3.5, GR-253-CORE "
    DEFVAL {20}
    ::= { oaSonetSecTcaEntry 11 }

-- ************************************************************
-- Objects in the Sonet Section Current Day Table
-- ************************************************************

oaSonetSecCurrDayTable OBJECT-TYPE
    SYNTAX  SEQUENCE OF OaSonetSecCurrDayEntry
    MAX-ACCESS  not-accessible
    STATUS  current
    DESCRIPTION
    "Contains sonet section related current 24-hour counters.
     A 24-hour interval starts at twelve midnight with
     reference to node time. In case of a manual change
     in node time all the counters in oaSonetSecCurr24HrTable
     table get reset to 0."
    ::= { oaSonetSection 2 }

oaSonetSecCurrDayEntry OBJECT-TYPE
    SYNTAX  OaSonetSecCurrDayEntry
    MAX-ACCESS  not-accessible
    STATUS  current
    DESCRIPTION
    "An entry in the current Day table. The entries exist for
     active sonet lines."
    INDEX { oaSonetSecCurrDayIfIndex }
    ::= { oaSonetSecCurrDayTable 1 }

OaSonetSecCurrDayEntry ::= SEQUENCE
    {
     oaSonetSecCurrDayIfIndex    Integer32,
     oaSonetSecCurrDayESs        PerfIntervalCount,
     oaSonetSecCurrDaySESs       PerfIntervalCount,
     oaSonetSecCurrDaySEFSs      PerfIntervalCount,
     oaSonetSecCurrDayCVs        PerfIntervalCount
    }

oaSonetSecCurrDayIfIndex OBJECT-TYPE
    SYNTAX  Integer32 (0..10000)
    MAX-ACCESS  not-accessible
    STATUS  current
    DESCRIPTION
    "This object is the ifIndex, based on ifMib"
    ::= { oaSonetSecCurrDayEntry 1 }

oaSonetSecCurrDayESs OBJECT-TYPE
    SYNTAX  PerfIntervalCount
    MAX-ACCESS  read-only
    STATUS  current
    DESCRIPTION
    "Number of Errored Seconds encountered in current 24-hour interval."
    REFERENCE
    " RFC2558 Section 3.5, GR-253-CORE"
    ::= { oaSonetSecCurrDayEntry 2 }

oaSonetSecCurrDaySESs OBJECT-TYPE
    SYNTAX  PerfIntervalCount
    MAX-ACCESS  read-only
    STATUS  current
    DESCRIPTION
    "Number of SESs encountered in current 24-hour interval."
    REFERENCE
    " RFC2558 Section 3.5, GR-253-CORE"
    ::= { oaSonetSecCurrDayEntry 3 }

oaSonetSecCurrDaySEFSs OBJECT-TYPE
    SYNTAX  PerfIntervalCount
    MAX-ACCESS  read-only
    STATUS  current
    DESCRIPTION
    "Number of SEFSs encountered in current 24-hour interval."
    REFERENCE
    " RFC2558 Section 3.5, GR-253-CORE"
    ::= { oaSonetSecCurrDayEntry 4 }

oaSonetSecCurrDayCVs OBJECT-TYPE
    SYNTAX  PerfIntervalCount
    MAX-ACCESS  read-only
    STATUS  current
    DESCRIPTION
    "Number of CVs encountered in current 24-hour interval."
    REFERENCE
    "RFC2558 Section 3.5, GR-253-CORE"
    ::= { oaSonetSecCurrDayEntry 5 }

-- ************************************************************
-- Objects in the Sonet Section Previous Day Table
-- ************************************************************

oaSonetSecPrevDayTable OBJECT-TYPE
    SYNTAX  SEQUENCE OF OaSonetSecPrevDayEntry
    MAX-ACCESS  not-accessible
    STATUS  current
    DESCRIPTION
    "Contains sonet section previous 24-hour counters.
     A 24-hour interval starts at twelve midnight with
     reference to node time. In case of a manual change
     in node time all the counters in oaSonetSecPrevDayTable
     table get reset to 0."
    ::= { oaSonetSection 3 }

oaSonetSecPrevDayEntry OBJECT-TYPE
    SYNTAX  OaSonetSecPrevDayEntry
    MAX-ACCESS  not-accessible
    STATUS  current
    DESCRIPTION
    "An entry in the previous day table. The entries exist for
     active sonet lines."
    INDEX { oaSonetSecPrevDayIfIndex }
    ::= { oaSonetSecPrevDayTable 1 }

OaSonetSecPrevDayEntry ::= SEQUENCE
    {
     oaSonetSecPrevDayIfIndex    Integer32,
     oaSonetSecPrevDayESs        PerfIntervalCount,
     oaSonetSecPrevDaySESs       PerfIntervalCount,
     oaSonetSecPrevDaySEFSs      PerfIntervalCount,
     oaSonetSecPrevDayCVs        PerfIntervalCount,
     oaSonetSecPrevDayValidData  TruthValue
    }

oaSonetSecPrevDayIfIndex OBJECT-TYPE
    SYNTAX  Integer32 (0..10000)
    MAX-ACCESS  not-accessible
    STATUS  current
    DESCRIPTION
    "This object is the ifIndex, based on ifMib"
    ::= { oaSonetSecPrevDayEntry 1 }

oaSonetSecPrevDayESs OBJECT-TYPE
    SYNTAX  PerfIntervalCount
    MAX-ACCESS  read-only
    STATUS  current
    DESCRIPTION
    "Number of Errored Seconds encountered in previous day interval."
    REFERENCE
    "RFC2558 Section 3.5, GR-253-CORE"
    ::= { oaSonetSecPrevDayEntry 2 }

oaSonetSecPrevDaySESs OBJECT-TYPE
    SYNTAX  PerfIntervalCount
    MAX-ACCESS  read-only
    STATUS  current
    DESCRIPTION
    "Number of SESs encountered in previous day interval."
     REFERENCE
    "RFC2558 Section 3.5, GR-253-CORE"
    ::= { oaSonetSecPrevDayEntry 3 }

oaSonetSecPrevDaySEFSs OBJECT-TYPE
    SYNTAX  PerfIntervalCount
    MAX-ACCESS  read-only
    STATUS  current
    DESCRIPTION
    "Number of SEFSs encountered in previous day interval."
    REFERENCE
    "RFC2558 Section 3.5,GR-253-CORE"
    ::= { oaSonetSecPrevDayEntry 4 }

oaSonetSecPrevDayCVs OBJECT-TYPE
    SYNTAX  PerfIntervalCount
    MAX-ACCESS  read-only
    STATUS  current
    DESCRIPTION
    "Number of CVs encountered in previous day interval."
    REFERENCE
    "RFC2558 Section 3.5, GR-253-CORE"
    ::= { oaSonetSecPrevDayEntry 5 }

 oaSonetSecPrevDayValidData OBJECT-TYPE
    SYNTAX  TruthValue
    MAX-ACCESS  read-only
    STATUS  current
    DESCRIPTION
    "This variable indicates if the data for this
     interval is valid."
    ::= { oaSonetSecPrevDayEntry 6 }

-- ************************************************************
-- Objects in the Line Alarms Table
-- ************************************************************

-- SONET/SDH Line Alarm  Table.
-- Changing any threshold will effect both the Near End and
-- Far End threshold.
-- ------------------------------------------------------------

oaSonetLineTcaTable OBJECT-TYPE
    SYNTAX  SEQUENCE OF OaSonetLineTcaEntry
    MAX-ACCESS  not-accessible
    STATUS  current
    DESCRIPTION
    "The SONET/SDH Line Alarm table. This table contains objects which are
     thresholds that the user can set. Once the threshold is exceeded,
     an alarm is flagged.Changing any threshold will affect  both
     the Near End and Far End(remote end of the line) threshold."
    ::= { oaSonetLine 1 }

oaSonetLineTcaEntry OBJECT-TYPE
    SYNTAX  OaSonetLineTcaEntry
    MAX-ACCESS  not-accessible
    STATUS  current
    DESCRIPTION
    "An entry in the SONET/SDH Line Alarm table.
     The entries may be created for an
     ifType value of sonet(39). Thresholds maybe specified for
     Errored Seconds (ES), Severely Errored Seconds (SES), Severely
     Errored Framing Seconds (SEFS), Coding Violations (CV) and
     Unavailable Seconds (UAS) for line layer of sonet lines.
     Once these thresholds are exceeded, minor or major alarm is
     raised.
     Please refer RFC1595 for descriptions  of ES,SES,CV,UAS"
    INDEX { oaSonetLineIfIndex }
    ::= { oaSonetLineTcaTable 1 }

OaSonetLineTcaEntry ::= SEQUENCE
    {
     oaSonetLineIfIndex          Integer32,
     oaSonetLine15MinESsTca      Unsigned32,
     oaSonetLineDayESsTca        Unsigned32,
     oaSonetLine15MinSESsTca     Unsigned32,
     oaSonetLineDaySESsTca       Unsigned32,
     oaSonetLine15MinCVsTca      Unsigned32,
     oaSonetLineDayCVsTca        Unsigned32,
     oaSonetLine15MinUASsTca     Unsigned32,
     oaSonetLineDayUASsTca       Unsigned32
    }

oaSonetLineIfIndex OBJECT-TYPE
    SYNTAX  Integer32 (0..10000)
    MAX-ACCESS  accessible-for-notify
    STATUS  current
    DESCRIPTION
    "This object is the ifIndex, based on ifMib"
    ::= { oaSonetLineTcaEntry 1 }

oaSonetLine15MinESsTca OBJECT-TYPE
    SYNTAX  Unsigned32 (0..2147483647)
    MAX-ACCESS  read-write
    STATUS  current
    DESCRIPTION
    "This object indicates the threshold for Errored Seconds (ES)
     for the current 15-min interval, above which alarm is
     generated.
     This threshold is the same for Far End and Near End. "
    REFERENCE
    " RFC2558 Section 3.5, GR-253-CORE "
    DEFVAL {60}
    ::= { oaSonetLineTcaEntry 2 }

oaSonetLineDayESsTca OBJECT-TYPE
    SYNTAX  Unsigned32 (0..2147483647)
    MAX-ACCESS  read-write
    STATUS  current
    DESCRIPTION
    "This object indicates the threshold for Errored Seconds (ES)
     for the 24-hour interval, above which alarm is generated.
     This threshold is the same for Far End and Near End. "
    REFERENCE
    " RFC2558 Section 3.5, GR-253-CORE "
    DEFVAL {600}
    ::= { oaSonetLineTcaEntry 3 }

oaSonetLine15MinSESsTca OBJECT-TYPE
    SYNTAX  Unsigned32 (0..2147483647)
    MAX-ACCESS  read-write
    STATUS  current
    DESCRIPTION
    "This is the Severely Errored Seconds (SES) threshold
     for the current 15-min interval,
     above which alarm is generated.
     This threshold is the same for Far End and Near End."
    REFERENCE
    " RFC2558 Section 3.5, GR-253-CORE "
    DEFVAL {3}
    ::= { oaSonetLineTcaEntry 4 }

oaSonetLineDaySESsTca OBJECT-TYPE
    SYNTAX  Unsigned32 (0..2147483647)
    MAX-ACCESS  read-write
    STATUS  current
    DESCRIPTION
    "This is the Severely Errored Seconds (SES) threshold
     for the 24-hour interval, above which alarm is generated.
     This threshold is the same for Far End and Near End."
    REFERENCE
    " RFC2558 Section 3.5, GR-253-CORE "
    DEFVAL {7}
    ::= { oaSonetLineTcaEntry 5 }

oaSonetLine15MinCVsTca OBJECT-TYPE
    SYNTAX  Unsigned32 (0..2147483647)
    MAX-ACCESS  read-write
    STATUS  current
    DESCRIPTION
    "This is the Coding Violations (CV) threshold for the current
     15-min interval, above which alarm is generated.
     This threshold is the same for Far End and Near End."
    REFERENCE
    " RFC2558 Section 3.5, GR-253-CORE "
    DEFVAL {75}
    ::= { oaSonetLineTcaEntry 6 }

oaSonetLineDayCVsTca OBJECT-TYPE
    SYNTAX  Unsigned32 (0..2147483647)
    MAX-ACCESS  read-write
    STATUS  current
    DESCRIPTION
    "This is the Coding Violations (CV) threshold for the
     24-hour interval, above which alarm is generated.
     This threshold is the same for Far End and Near End."
    REFERENCE
    " RFC2558 Section 3.5, GR-253-CORE "
    DEFVAL {750}
    ::= { oaSonetLineTcaEntry 7 }

oaSonetLine15MinUASsTca OBJECT-TYPE
    SYNTAX  Unsigned32 (0..2147483647)
    MAX-ACCESS  read-write
    STATUS  current
    DESCRIPTION
    "This is the Unavailable Seconds (UAS) threshold for the current
     15-min, above which alarm is generated.
     This threshold is the same for Far End and Near End. "
    REFERENCE
    " RFC2558 Section 3.5, GR-253-CORE "
    DEFVAL {10}
    ::= { oaSonetLineTcaEntry 8 }

oaSonetLineDayUASsTca OBJECT-TYPE
    SYNTAX  Unsigned32 (0..2147483647)
    MAX-ACCESS  read-write
    STATUS  current
    DESCRIPTION
    "This is the Unavailable Seconds (UAS) threshold for the
     24-hour interval above which alarm is generated.
     This threshold is the same for Far End and Near End. "
    REFERENCE
    " RFC2558 Section 3.5, GR-253-CORE "
    DEFVAL {10}
    ::= { oaSonetLineTcaEntry 9 }

-- ************************************************************
-- Objects indicating the Mib status.
-- ************************************************************

oaSonetMibImplementRevision	 OBJECT-TYPE
    SYNTAX      Integer32
    MAX-ACCESS  read-only
    STATUS      current
    DESCRIPTION
    "The value of this Object will increment according to
     each MIB implementation in the Agent."
    ::= { oaSonetGenParams 2 }

-- ************************************************************
-- Objects in the Sonet Line Current 24-hour period Table
-- ************************************************************

oaSonetLineCurrDayTable OBJECT-TYPE
    SYNTAX  SEQUENCE OF OaSonetLineCurrDayEntry
    MAX-ACCESS  not-accessible
    STATUS  current
    DESCRIPTION
    "Contains sonet line related current 24-hour counters.
     A 24-hour interval starts at twelve midnight with
     reference to node time. In case of a manual change
     in node time all the counters in oaSonetLineCurrDayTable
     table get reset to 0."
    ::= { oaSonetLine 2 }

oaSonetLineCurrDayEntry OBJECT-TYPE
    SYNTAX  OaSonetLineCurrDayEntry
    MAX-ACCESS  not-accessible
    STATUS  current
    DESCRIPTION
    "An entry in the current 24-hour table. The entries exist for
     active sonet lines."
    INDEX { oaSonetLineCurrDayIfIndex }
    ::= { oaSonetLineCurrDayTable 1 }

OaSonetLineCurrDayEntry ::= SEQUENCE
    {
     oaSonetLineCurrDayIfIndex   Integer32,
     oaSonetNELineCurrDayESs     PerfIntervalCount,
     oaSonetNELineCurrDaySESs    PerfIntervalCount,
     oaSonetNELineCurrDayCVs     PerfIntervalCount,
     oaSonetNELineCurrDayUASs    PerfIntervalCount,
     oaSonetFELineCurrDayESs     PerfIntervalCount,
     oaSonetFELineCurrDaySESs    PerfIntervalCount,
     oaSonetFELineCurrDayCVs     PerfIntervalCount,
     oaSonetFELineCurrDayUASs    PerfIntervalCount
    }

oaSonetLineCurrDayIfIndex OBJECT-TYPE
    SYNTAX  Integer32 (0..10000)
    MAX-ACCESS  not-accessible
    STATUS  current
    DESCRIPTION
    "This object is the ifIndex, based on ifMib"
    ::= { oaSonetLineCurrDayEntry 1 }

oaSonetNELineCurrDayESs OBJECT-TYPE
    SYNTAX  PerfIntervalCount
    MAX-ACCESS  read-only
    STATUS  current
    DESCRIPTION
    "Number of Errored Seconds encountered in current 24-hour interval."
    REFERENCE
    " RFC2558 Section 3.5, GR-253-CORE"
    ::= { oaSonetLineCurrDayEntry 2 }

oaSonetNELineCurrDaySESs OBJECT-TYPE
    SYNTAX  PerfIntervalCount
    MAX-ACCESS  read-only
    STATUS  current
    DESCRIPTION
    "Number of SESs encountered in current 24-hour interval."
    REFERENCE
    " RFC2558 Section 3.5, GR-253-CORE"
    ::= { oaSonetLineCurrDayEntry 3 }

oaSonetNELineCurrDayCVs OBJECT-TYPE
    SYNTAX  PerfIntervalCount
    MAX-ACCESS  read-only
    STATUS  current
    DESCRIPTION
    "Number of CVs encountered in current 24-hour interval."
    REFERENCE
    " RFC2558 Section 3.5, GR-253-CORE"
    ::= { oaSonetLineCurrDayEntry 4 }

oaSonetNELineCurrDayUASs OBJECT-TYPE
    SYNTAX  PerfIntervalCount
    MAX-ACCESS  read-only
    STATUS  current
    DESCRIPTION
    "Number of UASs encountered in current 24-hour interval."
    REFERENCE
    " RFC2558 Section 3.5, GR-253-CORE"
    ::= { oaSonetLineCurrDayEntry 5 }


oaSonetFELineCurrDayESs OBJECT-TYPE
    SYNTAX  PerfIntervalCount
    MAX-ACCESS  read-only
    STATUS  current
    DESCRIPTION
    "Number of far end Errored Seconds encountered in current
     24-hour interval."
    REFERENCE
    " RFC2558 Section 3.5, GR-253-CORE"
    ::= { oaSonetLineCurrDayEntry 6 }

oaSonetFELineCurrDaySESs OBJECT-TYPE
    SYNTAX  PerfIntervalCount
    MAX-ACCESS  read-only
    STATUS  current
    DESCRIPTION
    "Number of far end SESs encountered in current 24-hour interval."
    REFERENCE
    " RFC2558 Section 3.5, GR-253-CORE"
    ::= { oaSonetLineCurrDayEntry 7 }

oaSonetFELineCurrDayCVs OBJECT-TYPE
    SYNTAX  PerfIntervalCount
    MAX-ACCESS  read-only
    STATUS  current
    DESCRIPTION
    "Number of far end CVs encountered in current 24-hour interval."
    REFERENCE
    " RFC2558 Section 3.5, GR-253-CORE"
    ::= { oaSonetLineCurrDayEntry 8 }

oaSonetFELineCurrDayUASs OBJECT-TYPE
    SYNTAX  PerfIntervalCount
    MAX-ACCESS  read-only
    STATUS  current
    DESCRIPTION
    "Number of far end UASs encountered in current 24-hour interval."
    REFERENCE
    " RFC2558 Section 3.5, GR-253-CORE"
    ::= { oaSonetLineCurrDayEntry 9 }

-- ************************************************************
-- Objects in the Sonet Line Previous 24-hour period Table
-- ************************************************************

oaSonetLinePrevDayTable OBJECT-TYPE
    SYNTAX  SEQUENCE OF OaSonetLinePrevDayEntry
    MAX-ACCESS  not-accessible
    STATUS  current
    DESCRIPTION
    "Contains sonet line previous 24-hour counters.
     A 24-hour interval starts at twelve midnight with
     reference to node time. In case of a manual change
     in node time all the counters in oaSonetLinePrevDayTable
     table get reset to 0."
    ::= { oaSonetLine 3 }

oaSonetLinePrevDayEntry OBJECT-TYPE
    SYNTAX  OaSonetLinePrevDayEntry
    MAX-ACCESS  not-accessible
    STATUS  current
    DESCRIPTION
    "An entry in the current 24-hour table. The entries exist for
    active sonet lines."
    INDEX   { oaSonetLinePrevDayIfIndex }
    ::= { oaSonetLinePrevDayTable 1 }

OaSonetLinePrevDayEntry ::= SEQUENCE
    {
     oaSonetLinePrevDayIfIndex   Integer32,
     oaSonetNELinePrevDayESs     PerfIntervalCount,
     oaSonetNELinePrevDaySESs    PerfIntervalCount,
     oaSonetNELinePrevDayCVs     PerfIntervalCount,
     oaSonetNELinePrevDayUASs    PerfIntervalCount,
     oaSonetFELinePrevDayESs     PerfIntervalCount,
     oaSonetFELinePrevDaySESs    PerfIntervalCount,
     oaSonetFELinePrevDayCVs     PerfIntervalCount,
     oaSonetFELinePrevDayUASs    PerfIntervalCount,
     oaSonetLinePrevDayValidData TruthValue
    }

oaSonetLinePrevDayIfIndex OBJECT-TYPE
    SYNTAX  Integer32 (0..10000)
    MAX-ACCESS  not-accessible
    STATUS  current
    DESCRIPTION
    "This object is the ifIndex, based on ifMib"
    ::= { oaSonetLinePrevDayEntry 1 }

oaSonetNELinePrevDayESs OBJECT-TYPE
    SYNTAX  PerfIntervalCount
    MAX-ACCESS  read-only
    STATUS  current
    DESCRIPTION
    "Number of Errored Seconds encountered in previous 24-hour interval."
    REFERENCE
    " RFC2558 Section 3.5, GR-253-CORE"
    ::= { oaSonetLinePrevDayEntry 2 }

oaSonetNELinePrevDaySESs OBJECT-TYPE
    SYNTAX  PerfIntervalCount
    MAX-ACCESS  read-only
    STATUS  current
    DESCRIPTION
    "Number of SESs encountered in previous 24-hour interval."
    REFERENCE
    " RFC2558 Section 3.5, GR-253-CORE"
    ::= { oaSonetLinePrevDayEntry 3 }

oaSonetNELinePrevDayCVs OBJECT-TYPE
    SYNTAX  PerfIntervalCount
    MAX-ACCESS  read-only
    STATUS  current
    DESCRIPTION
    "Number of CVs encountered in previous 24-hour interval."
    REFERENCE
    "RFC2558 Section 3.5, GR-253-CORE"
    ::= { oaSonetLinePrevDayEntry 4 }

oaSonetNELinePrevDayUASs OBJECT-TYPE
    SYNTAX  PerfIntervalCount
    MAX-ACCESS  read-only
    STATUS  current
    DESCRIPTION
    "Number of UASs encountered in previous 24-hour interval."
    REFERENCE
    " RFC2558 Section 3.5, GR-253-CORE"
    ::= { oaSonetLinePrevDayEntry 5 }

oaSonetFELinePrevDayESs OBJECT-TYPE
    SYNTAX  PerfIntervalCount
    MAX-ACCESS  read-only
    STATUS  current
    DESCRIPTION
    "Number of far end Errored Seconds encountered in previous
     24-hour interval."
    REFERENCE
    " RFC2558 Section 3.5, GR-253-CORE"
    ::= { oaSonetLinePrevDayEntry 6 }

oaSonetFELinePrevDaySESs OBJECT-TYPE
    SYNTAX  PerfIntervalCount
    MAX-ACCESS  read-only
    STATUS  current
    DESCRIPTION
    "Number of far end SESs encountered in previous 24-hour interval."
    REFERENCE
    "RFC2558 Section 3.5, GR-253-CORE"
    ::= { oaSonetLinePrevDayEntry 7 }

oaSonetFELinePrevDayCVs OBJECT-TYPE
    SYNTAX  PerfIntervalCount
    MAX-ACCESS  read-only
    STATUS  current
    DESCRIPTION
    "Number of far end CVs encountered in previous 24-hour interval."
    REFERENCE
    "RFC2558 Section 3.5,GR-253-CORE"
    ::= { oaSonetLinePrevDayEntry 8 }

oaSonetFELinePrevDayUASs OBJECT-TYPE
    SYNTAX  PerfIntervalCount
    MAX-ACCESS  read-only
    STATUS  current
    DESCRIPTION
    "Number of far end UASs encountered in previous 24-hour interval."
    REFERENCE
    "RFC2558 Section 3.5, GR-253-CORE"
    ::= { oaSonetLinePrevDayEntry 9 }

 oaSonetLinePrevDayValidData OBJECT-TYPE
    SYNTAX  TruthValue
    MAX-ACCESS  read-only
    STATUS  current
    DESCRIPTION
    "This variable indicates if the data for this
    interval is valid."
    ::= { oaSonetLinePrevDayEntry 10 }

-- *******************************************************************
--  Conformance Information
-- *******************************************************************

oaSonetMIBConformance OBJECT IDENTIFIER ::= { oaSonetMib 3 }
oaSonetMIBGroups      OBJECT IDENTIFIER ::= { oaSonetMIBConformance 1 }
oaSonetMIBCompliances OBJECT IDENTIFIER ::= { oaSonetMIBConformance 2 }

oaSonetMIBCompliance MODULE-COMPLIANCE
    STATUS current
    DESCRIPTION
    "The Compliance statement for oaSonetMIB group."

    MODULE -- this module

    MANDATORY-GROUPS {
                      oaSonetSecTcaGroup,
                      oaSonetLineTcaGroup,
                      oaSonetSecCurrDayGroup,
                      oaSonetSecPrevDayGroup,
                      oaSonetNELineCurrDayGroup,
                      oaSonetNELinePrevDayGroup,
                      oaSonetGenParamsGroup
                     }

    GROUP oaSonetFELineCurrDayGroup
    DESCRIPTION
    "Implementation of this group is optional. To be supported
     if far end line tables in standard sonet MIB are supported."

    GROUP oaSonetFELinePrevDayGroup
    DESCRIPTION
    "Implementation of this group is optional. To be supported
     if far end path tables in standard sonet MIB are supported."

    ::= {oaSonetMIBCompliances 1}

-- ...................................................................
-- Conformance Groups
-- ...................................................................

oaSonetSecTcaGroup OBJECT-GROUP
    OBJECTS {
             oaSonetSecIfIndex,
             oaSonetSec15MinESsTca,
             oaSonetSecDayESsTca,
             oaSonetSec15MinSESsTca,
             oaSonetSecDaySESsTca,
             oaSonetSec15MinSEFSsTca,
             oaSonetSecDaySEFSsTca,
             oaSonetSec15MinCVsTca,
             oaSonetSecDayCVsTca,
             oaSonetSec15MinUASsTca,
             oaSonetSecDayUASsTca
            }
    STATUS current
    DESCRIPTION
    " These are objects related to oaSonetSection TCA group."
    ::= { oaSonetMIBGroups 1}

oaSonetLineTcaGroup OBJECT-GROUP
    OBJECTS {
             oaSonetLineIfIndex,
             oaSonetLine15MinESsTca,
             oaSonetLineDayESsTca,
             oaSonetLine15MinSESsTca,
             oaSonetLineDaySESsTca,
             oaSonetLine15MinCVsTca,
             oaSonetLineDayCVsTca,
             oaSonetLine15MinUASsTca,
             oaSonetLineDayUASsTca
            }
    STATUS current
    DESCRIPTION
    "These are objects related to oaSonetLine TCA group."
    ::= { oaSonetMIBGroups 2}

oaSonetSecCurrDayGroup OBJECT-GROUP
    OBJECTS {
             oaSonetSecCurrDayESs,
             oaSonetSecCurrDaySESs,
             oaSonetSecCurrDaySEFSs,
             oaSonetSecCurrDayCVs
            }
    STATUS current
    DESCRIPTION
    " These are objects related to oaSonetSection Current DAY group."
    ::= { oaSonetMIBGroups 3}

oaSonetSecPrevDayGroup OBJECT-GROUP
    OBJECTS {
             oaSonetSecPrevDayESs,
             oaSonetSecPrevDaySESs,
             oaSonetSecPrevDaySEFSs,
             oaSonetSecPrevDayCVs,
             oaSonetSecPrevDayValidData
            }
    STATUS current
    DESCRIPTION
    " These are objects related to oaSonetSection Previous Day group."
    ::= { oaSonetMIBGroups 4}

oaSonetNELineCurrDayGroup OBJECT-GROUP
    OBJECTS {
             oaSonetNELineCurrDayESs,
             oaSonetNELineCurrDaySESs,
             oaSonetNELineCurrDayCVs,
             oaSonetNELineCurrDayUASs
            }
    STATUS current
    DESCRIPTION
    "These are objects related to oaSonetLine (Near-End) Current DAY group."
    ::= { oaSonetMIBGroups 5}

oaSonetNELinePrevDayGroup OBJECT-GROUP
    OBJECTS {
             oaSonetNELinePrevDayESs,
             oaSonetNELinePrevDaySESs,
             oaSonetNELinePrevDayCVs,
             oaSonetNELinePrevDayUASs,
             oaSonetLinePrevDayValidData
            }
    STATUS current
    DESCRIPTION
    "These are objects related to oaSonetLine (Near-End) Previous DAY group."
    ::= { oaSonetMIBGroups 6}

oaSonetFELineCurrDayGroup OBJECT-GROUP
    OBJECTS {
             oaSonetFELineCurrDayESs,
             oaSonetFELineCurrDaySESs,
             oaSonetFELineCurrDayCVs,
             oaSonetFELineCurrDayUASs
            }
    STATUS current
    DESCRIPTION
    "These are objects related to oaSonetLine (Far-End) Current DAY group."
    ::= { oaSonetMIBGroups 7}

oaSonetFELinePrevDayGroup OBJECT-GROUP
    OBJECTS {
             oaSonetFELinePrevDayESs,
             oaSonetFELinePrevDaySESs,
             oaSonetFELinePrevDayCVs,
             oaSonetFELinePrevDayUASs,
             oaSonetLinePrevDayValidData
            }
    STATUS current
    DESCRIPTION
    "These are objects related to oaSonetLine (Near-End) Previous DAY group."
    ::= { oaSonetMIBGroups 8}

 oaSonetSecTcaNotificationsGroup   NOTIFICATION-GROUP
    NOTIFICATIONS {
             oaSonetSec15MinESsOn,
             oaSonetSec15MinESsOff,
             oaSonetSec15MinSESsOn,
             oaSonetSec15MinSESsOff,
             oaSonetSec15MinSEFSsOn,
             oaSonetSec15MinSEFSsOff,
             oaSonetSec15MinCVsOn,
             oaSonetSec15MinCVsOff,
             oaSonetSecCurrDayESsOn,
             oaSonetSecCurrDayESsOff,
             oaSonetSecCurrDaySESsOn,
             oaSonetSecCurrDaySESsOff,
             oaSonetSecCurrDaySEFSsOn,
             oaSonetSecCurrDaySEFSsOff,
             oaSonetSecCurrDayCVsOn,
             oaSonetSecCurrDayCVsOff
            }
    STATUS  current
    DESCRIPTION
    "The Sonet Section notifications which are required
     to be supported by implementations of this MIB."
    ::= { oaSonetMIBGroups 9 }

 oaSonetNELineTcaNotifGroup   NOTIFICATION-GROUP
    NOTIFICATIONS {
             oaSonetNELine15MinESsOn,
             oaSonetNELine15MinESsOff,
             oaSonetNELine15MinSESsOn,
             oaSonetNELine15MinSESsOff,
             oaSonetNELine15MinCVsOn,
             oaSonetNELine15MinCVsOff,
             oaSonetNELine15MinUASsOn,
             oaSonetNELine15MinUASsOff,
             oaSonetNELineCurrDayESsOn,
             oaSonetNELineCurrDayESsOff,
             oaSonetNELineCurrDaySESsOn,
             oaSonetNELineCurrDaySESsOff,
             oaSonetNELineCurrDayCVsOn,
             oaSonetNELineCurrDayCVsOff,
             oaSonetNELineCurrDayUASsOn,
             oaSonetNELineCurrDayUASsOff
            }
    STATUS  current
    DESCRIPTION
    "The Sonet Near-End Line notifications which are required
     to be supported by implementations of this MIB."
    ::= { oaSonetMIBGroups 10 }

 oaSonetFELineTcaNotifGroup   NOTIFICATION-GROUP
    NOTIFICATIONS {
             oaSonetFELine15MinESsOn,
             oaSonetFELine15MinESsOff,
             oaSonetFELine15MinSESsOn,
             oaSonetFELine15MinSESsOff,
             oaSonetFELine15MinCVsOn,
             oaSonetFELine15MinCVsOff,
             oaSonetFELine15MinUASsOn,
             oaSonetFELine15MinUASsOff,
             oaSonetFELineCurrDayESsOn,
             oaSonetFELineCurrDayESsOff,
             oaSonetFELineCurrDaySESsOn,
             oaSonetFELineCurrDaySESsOff,
             oaSonetFELineCurrDayCVsOn,
             oaSonetFELineCurrDayCVsOff,
             oaSonetFELineCurrDayUASsOn,
             oaSonetFELineCurrDayUASsOff
            }
    STATUS  current
    DESCRIPTION
    "The Sonet Far-End Line notifications which are required
     to be supported by implementations of this MIB."
    ::= { oaSonetMIBGroups 11 }

 oaSonetSecNotificationsGroup   NOTIFICATION-GROUP
    NOTIFICATIONS {
             oaSonetSecLosAlarmOn,
             oaSonetSecLosAlarmOff
            }
    STATUS  current
    DESCRIPTION
    "The Sonet SECTION notifications which are required
     to be supported by implementations of this MIB."
    ::= { oaSonetMIBGroups 12 }

 oaSonetLineNotificationsGroup   NOTIFICATION-GROUP
    NOTIFICATIONS {
             oaSonetLineAisAlarmOn,
             oaSonetLineAisAlarmOff,
             oaSonetLineRdiAlarmOn,
             oaSonetLineRdiAlarmOff
            }
    STATUS  current
    DESCRIPTION
    "The Sonet Line notifications which are required
     to be supported by implementations of this MIB."
    ::= { oaSonetMIBGroups 13 }

 oaOtuLineNotificationsGroup   NOTIFICATION-GROUP
    NOTIFICATIONS {
             oaSonetLineSideOtuLosAlarmOn,
             oaSonetLineSideOtuLosAlarmOff,
             oaSonetLineSideOtuAisAlarmOn,
             oaSonetLineSideOtuAisAlarmOff,
             oaSonetLineSideOtuIaeAlarmOn,
             oaSonetLineSideOtuIaeAlarmOff
            }
    STATUS  current
    DESCRIPTION
    "The OTU Line notifications which are required
     to be supported by implementations of this MIB."
    ::= { oaSonetMIBGroups 14 }

 oaSonetGenParamsGroup   OBJECT-GROUP
    OBJECTS {
	     oaSonetMibImplementRevision
            }
    STATUS current
    DESCRIPTION
    "These are objects related to oaSonetGenParams group."
    ::= { oaSonetMIBGroups 15}

-- *******************************************************************
--  Notification Definition section
-- *******************************************************************

oaSonetSec15MinESsOn NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     the Section ES counter for the 15-min interval
     has crossed the TCA value."
    ::= { oaSonetNotifications 99 }

oaSonetSec15MinESsOff NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     the Section ES counter for the 15-min interval
     has not crossed the TCA value."
    ::= { oaSonetNotifications 100 }

oaSonetSec15MinSESsOn NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     the Section SES counter for the 15-min interval
     has crossed the TCA value."
    ::= { oaSonetNotifications 104 }

oaSonetSec15MinSESsOff NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     the Section SES counter for the 15-min interval
     has not crossed the TCA value."
    ::= { oaSonetNotifications 105 }

oaSonetSec15MinSEFSsOn NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     the Section SEFS counter for the 15-min interval
     has crossed the TCA value."
    ::= { oaSonetNotifications 106 }

oaSonetSec15MinSEFSsOff NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     the Section SEFS counter for the 15-min interval
     has not crossed the TCA value."
    ::= { oaSonetNotifications 107 }

oaSonetSec15MinCVsOn NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     the Section CV counter for the 15-min interval
     has crossed the TCA value."
    ::= { oaSonetNotifications 108 }

oaSonetSec15MinCVsOff NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     the Section CV counter for the 15-min interval
     has not crossed the TCA value."
    ::= { oaSonetNotifications 109 }

oaSonetSecCurrDayESsOn NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     the Section ES counter for the 24-hour interval
     has crossed the TCA value."
    ::= { oaSonetNotifications 110 }

oaSonetSecCurrDayESsOff NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     the Section ES counter for the 24-hour interval
     has not crossed the TCA value."
    ::= { oaSonetNotifications 111 }

oaSonetSecCurrDaySESsOn NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     the Section SES counter for the 24-hour interval
     has crossed the TCA value."
    ::= { oaSonetNotifications 112 }

oaSonetSecCurrDaySESsOff NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     the Section SES counter for the 24-hour interval
     has not crossed the TCA value."
    ::= { oaSonetNotifications 113 }

oaSonetSecCurrDaySEFSsOn NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     the Section SEFS counter for the 24-hour interval
     has crossed the TCA value."
    ::= { oaSonetNotifications 114 }

oaSonetSecCurrDaySEFSsOff NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     the Section SEFS counter for the 24-hour interval
     has not crossed the TCA value."
    ::= { oaSonetNotifications 115 }

oaSonetSecCurrDayCVsOn NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     the Section CV counter for the 24-hour interval
     has crossed the TCA value."
    ::= { oaSonetNotifications 116 }

oaSonetSecCurrDayCVsOff NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     the Section CV counter for the 24-hour interval
     has not crossed the TCA value."
    ::= { oaSonetNotifications 117 }

oaSonetNELine15MinESsOn NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the NE Line ES counter for the 15-min interval
     has crossed the TCA value."
    ::= { oaSonetNotifications 118 }

oaSonetNELine15MinESsOff NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the NE Line ES counter for the 15-min interval
     has not crossed the TCA value."
    ::= { oaSonetNotifications 119 }

oaSonetNELine15MinSESsOn NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the NE Line SES counter for the 15-min interval
     has crossed the TCA value."
    ::= { oaSonetNotifications 120 }

oaSonetNELine15MinSESsOff NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the NE Line SES counter for the 15-min interval
     has not crossed the TCA value."
    ::= { oaSonetNotifications 121 }

oaSonetNELine15MinCVsOn NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the NE Line CV counter for the 15-min interval
     has crossed the TCA value."
    ::= { oaSonetNotifications 122 }

oaSonetNELine15MinCVsOff NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the NE Line CV counter for the 15-min interval
     has not crossed the TCA value."
    ::= { oaSonetNotifications 123 }

oaSonetNELine15MinUASsOn NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the NE Line UAS counter for the 15-min interval
     has crossed the TCA value."
    ::= { oaSonetNotifications 124 }

oaSonetNELine15MinUASsOff NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the NE Line UAS counter for the 15-min interval
     has not crossed the TCA value."
    ::= { oaSonetNotifications 125 }

oaSonetFELine15MinESsOn NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the FE Line ES counter for the 15-min interval
     has crossed the TCA value."
    ::= { oaSonetNotifications 126 }

oaSonetFELine15MinESsOff NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the FE Line ES counter for the 15-min interval
     has not crossed the TCA value."
    ::= { oaSonetNotifications 127 }

oaSonetFELine15MinSESsOn NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the FE Line SES counter for the 15-min interval
     has crossed the TCA value."
    ::= { oaSonetNotifications 128 }

oaSonetFELine15MinSESsOff NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the FE Line SES counter for the 15-min interval
     has not crossed the TCA value."
    ::= { oaSonetNotifications 129 }

oaSonetFELine15MinCVsOn NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the FE Line CV counter for the 15-min interval
     has crossed the TCA value."
    ::= { oaSonetNotifications 130 }

oaSonetFELine15MinCVsOff NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the FE Line CV counter for the 15-min interval
     has not crossed the TCA value."
    ::= { oaSonetNotifications 131 }

oaSonetFELine15MinUASsOn NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the FE Line UAS counter for the 15-min interval
     has crossed the TCA value."
    ::= { oaSonetNotifications 132 }

oaSonetFELine15MinUASsOff NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the FE Line UAS counter for the 15-min interval
     has not crossed the TCA value."
    ::= { oaSonetNotifications 133 }

oaSonetNELineCurrDayESsOn NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the NE Line ES counter for the 24-hour interval
     has crossed the TCA value."
    ::= { oaSonetNotifications 134 }

oaSonetNELineCurrDayESsOff NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the NE Line ES counter for the 24-hour interval
     has not crossed the TCA value."
    ::= { oaSonetNotifications 135 }

oaSonetNELineCurrDaySESsOn NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the NE Line SES counter for the 24-hour interval
     has crossed the TCA value."
    ::= { oaSonetNotifications 136 }

oaSonetNELineCurrDaySESsOff NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the NE Line SES counter for the 24-hour interval
     has not crossed the TCA value."
    ::= { oaSonetNotifications 137 }

oaSonetNELineCurrDayCVsOn NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the NE Line CV counter for the 24-hour interval
     has crossed the TCA value."
    ::= { oaSonetNotifications 138 }

oaSonetNELineCurrDayCVsOff NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the NE Line CV counter for the 24-hour interval
     has crossed the TCA value."
    ::= { oaSonetNotifications 139 }

oaSonetNELineCurrDayUASsOn NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the NE Line UAS counter for the 24-hour interval  -- Yakov (UAS instead of CV)
     has not crossed the TCA value."
    ::= { oaSonetNotifications 140 }

oaSonetNELineCurrDayUASsOff NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the NE Line UAS counter for the 24-hour interval
     has crossed the TCA value."
    ::= { oaSonetNotifications 141 }

oaSonetFELineCurrDayESsOn NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the FE Line ES counter for the 24-hour interval
     has crossed the TCA value."
    ::= { oaSonetNotifications 142 }

oaSonetFELineCurrDayESsOff NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the FE Line ES counter for the 24-hour interval
     has not crossed the TCA value."
    ::= { oaSonetNotifications 143 }

oaSonetFELineCurrDaySESsOn NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the FE Line SES counter for the 24-hour interval
     has crossed the TCA value."
    ::= { oaSonetNotifications 144 }

oaSonetFELineCurrDaySESsOff NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the FE Line SES counter for the 24-hour interval
     has not crossed the TCA value."
    ::= { oaSonetNotifications 145 }

oaSonetFELineCurrDayCVsOn NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the FE Line CV counter for the 24-hour interval
     has crossed the TCA value."
    ::= { oaSonetNotifications 146 }

oaSonetFELineCurrDayCVsOff NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the FE Line CV counter for the 24-hour interval
     has crossed the TCA value."
    ::= { oaSonetNotifications 147 }

oaSonetFELineCurrDayUASsOn NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the FE Line CV counter for the 24-hour interval
     has not crossed the TCA value."
    ::= { oaSonetNotifications 148 }

oaSonetFELineCurrDayUASsOff NOTIFICATION-TYPE
    OBJECTS {
             oaLdCardPortsSlotNumber,
             oaLdCardPortsPortNumber,
             oaSonetLineIfIndex,
             oaDevTrapsPortsIfAlias
            }
    STATUS  current
    DESCRIPTION
    "The SNMP trap that is generated when
     the FE Line UAS counter for the 24-hour interval
     has crossed the TCA value."
    ::= { oaSonetNotifications 149 }

oaSonetSecLosAlarmOn NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     Section LOS indication is set."
    ::= { oaSonetNotifications 151 }

oaSonetSecLosAlarmOff NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     Section LOS indication is reset."
    ::= { oaSonetNotifications 152 }

oaSonetLineAisAlarmOn NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     Line AIS indication is set."
    ::= { oaSonetNotifications 153 }

oaSonetLineAisAlarmOff NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     Line AIS indication is reset."
    ::= { oaSonetNotifications 154 }

oaSonetLineRdiAlarmOn NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     Line RDI indication is set."
    ::= { oaSonetNotifications 155 }

oaSonetLineRdiAlarmOff NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     Line RDI indication is reset."
    ::= { oaSonetNotifications 156 }

oaSonetLineSideOtuLosAlarmOn NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     LOS indication is set on the OTU Line side."
    ::= { oaSonetNotifications 157 }

oaSonetLineSideOtuLosAlarmOff NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     LOS indication is reset on the OTU Line side."
    ::= { oaSonetNotifications 158 }

oaSonetLineSideOtuAisAlarmOn NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     AIS indication is set on the OTU Line side."
    ::= { oaSonetNotifications 159 }

oaSonetLineSideOtuAisAlarmOff NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     AIS indication is reset on the OTU Line side."
    ::= { oaSonetNotifications 160 }

oaSonetLineSideOtuIaeAlarmOn NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     IAE indication is set on the OTU Line side."
    ::= { oaSonetNotifications 161 }

oaSonetLineSideOtuIaeAlarmOff NOTIFICATION-TYPE
    OBJECTS {
             oaLdCardPortsSlotNumber,
             oaLdCardPortsPortNumber,
             oaSonetSecIfIndex,
             oaDevTrapsPortsIfAlias
            }
    STATUS  current
    DESCRIPTION
    "The SNMP trap that is generated when
     Line IAE indication is reset on the OTU Line side."
    ::= { oaSonetNotifications 162 }
END
