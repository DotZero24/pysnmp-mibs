--  =======================================================================
--  File        : nbSched.mib
--  Description : Private MIB support the functionality of scheduling
--                management actions
--  By          : Alex

-- Copyright (c) 2008 MRV.  All Rights Reserved.
--
--
-- Reproduction of this document is authorized on condition that this
-- copyright notice is included.  This MRV SNMP MIB Specification
-- embodies MRV's proprietary intellectual property.  MRV
-- retains all title and ownership in the specification, including any
-- revisions.
--
-- It is MRV's intent to encourage the widespread use of this
-- specification in connection with the management of MRV's
-- products. MRV grants vendor, end-users, and other interested
-- parties a non-exclusive license to use this specification in
-- connection with the management of MRV's products.
--
-- This specification is supplied "AS IS," and MRV makes no
-- warranty, either express or implied, as to the use, operation,
-- condition, or performance of the specification.
--
-- Copyright text courtesy of MRV
--
-- If you have any questions about this MIB, please call MRV
-- Technical Support Center at 1-800-858-7815 from inside USA or
-- 1-818-773-0900 from outside USA.
--
--
-- MRV retains the right to change this MIB without notification.

OA-SCHED-MIB DEFINITIONS ::= BEGIN

        IMPORTS
                MODULE-IDENTITY, OBJECT-TYPE,
                enterprises, Unsigned32                       FROM SNMPv2-SMI
                TEXTUAL-CONVENTION, RowStatus,
                DisplayString, TruthValue                     FROM SNMPv2-TC
                nbSwitchG1Il                                  FROM OS-COMMON-TC-MIB
                MODULE-COMPLIANCE, OBJECT-GROUP               FROM SNMPv2-CONF;

nbSched        MODULE-IDENTITY
                LAST-UPDATED "200801070000Z"
                ORGANIZATION "MRV Communications, Inc."
                CONTACT-INFO
                   "Alex Rozin
                    MRV Communication, Inc
                    http://www.mrv.com
                    Email:  ARozin@mrv.com"
                DESCRIPTION
                    "Scheduler MIB."
                REVISION "200801070000Z"
                DESCRIPTION
                    "Initial edition."
                ::= { nbSwitchG1Il 18 }

-- ************************************************************
-- MIB place Definition
-- ************************************************************

nbSchedConformance    OBJECT IDENTIFIER ::= { nbSched 100 }
nbSchedMIBCompliances OBJECT IDENTIFIER ::= { nbSchedConformance 1 }
nbSchedMIBGroups      OBJECT IDENTIFIER ::= { nbSchedConformance 2 }

-- ************************************************************
-- Textual converions
-- ************************************************************

SchedCommandType ::= TEXTUAL-CONVENTION
    STATUS      current
    DESCRIPTION
       "Indicates the type of the scheduling command."
    REFERENCE
       "."
    SYNTAX      INTEGER {
                  cli   (1),
                  shell (2)
                }



nbSchedTable OBJECT-TYPE
    SYNTAX      SEQUENCE OF NbSchedEntry
    MAX-ACCESS  not-accessible
    STATUS      current
    DESCRIPTION
       "Scheduler configuration table."
    REFERENCE
       "."
    ::= { nbSched 1 }

nbSchedEntry OBJECT-TYPE
    SYNTAX      NbSchedEntry
    MAX-ACCESS  not-accessible
    STATUS      current
    DESCRIPTION
       "Contains configuration of Scheduler."
    INDEX { nbSchedIndex }
    ::= { nbSchedTable 1 }

NbSchedEntry ::= SEQUENCE {
      nbSchedIndex                 Unsigned32,

      nbSchedStartMinute           Unsigned32,
      nbSchedStartHour             Unsigned32,
      nbSchedStartDay              Unsigned32,
      nbSchedStartMonth            Unsigned32,
      nbSchedStartWeekday          Unsigned32,

      nbSchedEndMinute             Unsigned32,
      nbSchedEndHour               Unsigned32,
      nbSchedEndDay                Unsigned32,
      nbSchedEndMonth              Unsigned32,
      nbSchedEndWeekday            Unsigned32,

      nbSchedNumberOfTimes         Unsigned32,
      nbSchedInterval              Unsigned32,
      nbSchedIsNow                 TruthValue,
      nbSchedNotify                TruthValue,
      nbSchedCmdType               SchedCommandType,
      nbSchedCommand               DisplayString,
      nbSchedRemark                DisplayString,

      nbSchedIsCompleted           TruthValue,
      nbSchedRowStatus             RowStatus
    }

nbSchedIndex    OBJECT-TYPE
    SYNTAX      Unsigned32 (1..65535|65536)
    MAX-ACCESS  not-accessible
    STATUS      current
    DESCRIPTION
       "Index of the entry. If SET operation comes with the index 65536, new
       entry is created with authomaticaly selected index."
    REFERENCE
       "802.1ag clauses 3.19 and 19.2.1"
    ::= { nbSchedEntry 1 }

nbSchedStartMinute   OBJECT-TYPE
    SYNTAX           Unsigned32 (0..59|99)
    MAX-ACCESS       read-write
    STATUS           current
    DESCRIPTION
       "."
    REFERENCE
       "."
    ::= { nbSchedEntry 4 }

nbSchedStartHour     OBJECT-TYPE
    SYNTAX           Unsigned32 (0..23|99)
    MAX-ACCESS       read-write
    STATUS           current
    DESCRIPTION
       "."
    REFERENCE
       "."
    ::= { nbSchedEntry 5 }

nbSchedStartDay      OBJECT-TYPE
    SYNTAX           Unsigned32 (1..31|99)
    MAX-ACCESS       read-write
    STATUS           current
    DESCRIPTION
       "."
    REFERENCE
       "."
    ::= { nbSchedEntry 6 }

nbSchedStartMonth    OBJECT-TYPE
    SYNTAX           Unsigned32 (1..12|99)
    MAX-ACCESS       read-write
    STATUS           current
    DESCRIPTION
       "."
    REFERENCE
       "."
    ::= { nbSchedEntry 7 }

nbSchedStartWeekday  OBJECT-TYPE
    SYNTAX           Unsigned32 (0..6|99)
    MAX-ACCESS       read-write
    STATUS           current
    DESCRIPTION
       "."
    REFERENCE
       "."
    ::= { nbSchedEntry 8 }

nbSchedEndMinute   OBJECT-TYPE
    SYNTAX         Unsigned32 (0..59|99)
    MAX-ACCESS     read-write
    STATUS         current
    DESCRIPTION
       "."
    REFERENCE
       "."
    ::= { nbSchedEntry 10 }

nbSchedEndHour       OBJECT-TYPE
    SYNTAX           Unsigned32 (0..23|99)
    MAX-ACCESS       read-write
    STATUS           current
    DESCRIPTION
       "."
    REFERENCE
       "."
    ::= { nbSchedEntry 11 }

nbSchedEndDay        OBJECT-TYPE
    SYNTAX           Unsigned32 (1..31|99)
    MAX-ACCESS       read-write
    STATUS           current
    DESCRIPTION
       "."
    REFERENCE
       "."
    ::= { nbSchedEntry 12 }

nbSchedEndMonth      OBJECT-TYPE
    SYNTAX           Unsigned32 (1..12|99)
    MAX-ACCESS       read-write
    STATUS           current
    DESCRIPTION
       "."
    REFERENCE
       "."
    ::= { nbSchedEntry 13 }

nbSchedEndWeekday    OBJECT-TYPE
    SYNTAX           Unsigned32 (0..6|99)
    MAX-ACCESS       read-write
    STATUS           current
    DESCRIPTION
       "."
    REFERENCE
       "."
    ::= { nbSchedEntry 14 }

nbSchedNumberOfTimes  OBJECT-TYPE
    SYNTAX            Unsigned32 (1..527040)
    MAX-ACCESS        read-write
    STATUS            current
    DESCRIPTION
       "."
    REFERENCE
       "."
    ::= { nbSchedEntry 20 }

nbSchedInterval       OBJECT-TYPE
    SYNTAX            Unsigned32 (1..527040)
    MAX-ACCESS        read-write
    STATUS            current
    DESCRIPTION
       "."
    REFERENCE
       "."
    ::= { nbSchedEntry 21 }

nbSchedIsNow          OBJECT-TYPE
    SYNTAX            TruthValue
    MAX-ACCESS        read-write
    STATUS            current
    DESCRIPTION
       "."
    REFERENCE
       "."
    ::= { nbSchedEntry 22 }

nbSchedNotify         OBJECT-TYPE
    SYNTAX            TruthValue
    MAX-ACCESS        read-write
    STATUS            current
    DESCRIPTION
       "."
    REFERENCE
       "."
    ::= { nbSchedEntry 23 }

nbSchedCmdType        OBJECT-TYPE
    SYNTAX            SchedCommandType
    MAX-ACCESS        read-write
    STATUS            current
    DESCRIPTION
       "."
    REFERENCE
       "."
    ::= { nbSchedEntry 24 }

nbSchedCommand        OBJECT-TYPE
    SYNTAX            DisplayString (SIZE (2..132))
    MAX-ACCESS        read-write
    STATUS            current
    DESCRIPTION
       "."
    REFERENCE
       "."
    ::= { nbSchedEntry 25 }

nbSchedRemark         OBJECT-TYPE
    SYNTAX            DisplayString (SIZE (2..132))
    MAX-ACCESS        read-write
    STATUS            current
    DESCRIPTION
       "."
    REFERENCE
       "."
    ::= { nbSchedEntry 26 }


nbSchedIsCompleted    OBJECT-TYPE
    SYNTAX            TruthValue
    MAX-ACCESS        read-only
    STATUS            current
    DESCRIPTION
       "."
    REFERENCE
       "."
    ::= { nbSchedEntry 27 }

nbSchedRowStatus      OBJECT-TYPE
    SYNTAX            RowStatus
    MAX-ACCESS        read-write
    STATUS            current
    DESCRIPTION
       "."
    REFERENCE
       "."
    ::= { nbSchedEntry 28 }


-- *******************************************************************
--  Conformance Information
-- *******************************************************************

nbSchedMIBCompliance MODULE-COMPLIANCE
    STATUS current
    DESCRIPTION
        "The core compliance statement for all the implementations."

    MODULE -- this module
        MANDATORY-GROUPS {
                          nbSchedMandatoryGroup
                         }

    ::= { nbSchedMIBCompliances 1 }

-- ...................................................................
-- Conformance Groups
-- ...................................................................

nbSchedMandatoryGroup  OBJECT-GROUP
    OBJECTS {
            nbSchedStartMinute,
            nbSchedStartHour,
            nbSchedStartDay,
            nbSchedStartMonth,
            nbSchedStartWeekday,
            nbSchedEndMinute,
            nbSchedEndHour,
            nbSchedEndDay,
            nbSchedEndMonth,
            nbSchedEndWeekday,
            nbSchedNumberOfTimes,
            nbSchedInterval,
            nbSchedIsNow,
            nbSchedNotify,
            nbSchedCmdType,
            nbSchedCommand,
            nbSchedRemark,
            nbSchedIsCompleted,
            nbSchedRowStatus
            }
    STATUS current
    DESCRIPTION
        "."

    ::= { nbSchedMIBGroups 1 }


END
