--  =======================================================================
--  File        : mrv-priv-traps.mib
--  Description : Private MIB for Linux Router
--  By          : Alex Rozin
--  Supports private traps, that are reflection of standrd ones

-- Copyright (c) 2006 MRV.  All Rights Reserved.
--
--
-- Reproduction of this document is authorized on condition that this
-- copyright notice is included.  This MRV SNMP MIB Specification
-- embodies MRV's proprietary intellectual property.  MRV
-- retains all title and ownership in the specification, including any
-- revisions.
--
-- It is MRV's intent to encourage the widespread use of this
-- specification in connection with the management of MRV's
-- products. MRV grants vendor, end-users, and other interested
-- parties a non-exclusive license to use this specification in
-- connection with the management of MRV's products.
--
-- This specification is supplied "AS IS," and MRV makes no
-- warranty, either express or implied, as to the use, operation,
-- condition, or performance of the specification.
--
-- Copyright text courtesy of MRV
--
-- If you have any questions about this MIB, please call MRV
-- Technical Support Center at 1-800-858-7815 from inside USA or
-- 1-818-773-0900 from outside USA.
--
--
-- MRV retains the right to change this MIB without notification.

MRV-PRIV-TRAPS-MIB DEFINITIONS ::= BEGIN

IMPORTS
    MODULE-IDENTITY, OBJECT-TYPE, enterprises,
    NOTIFICATION-TYPE, Integer32, Unsigned32     FROM SNMPv2-SMI
    MODULE-COMPLIANCE, NOTIFICATION-GROUP,
    OBJECT-GROUP                                 FROM SNMPv2-CONF
    DisplayString, TEXTUAL-CONVENTION            FROM SNMPv2-TC;


nbPrivTraps  MODULE-IDENTITY
    LAST-UPDATED "200602220000Z"
    ORGANIZATION "MRV Communications, Inc."
    CONTACT-INFO
        "Alex Rozin
         MRV Communication, Inc
         http://www.mrv.com
         Email:  ARozin@mrv.com"
    DESCRIPTION
        "Supports information about device identifiaction."

    -- Revision history

    REVISION "200602220000Z"
    DESCRIPTION
        "Initial edition."
    ::= { nbSwitchG1Il 21 }

-- ************************************************************
-- MIB place Definition
-- ************************************************************

nbase                  OBJECT IDENTIFIER ::= { enterprises 629 }
nbSwitchG1             OBJECT IDENTIFIER ::= { nbase 1 }
nbSwitchG1Il           OBJECT IDENTIFIER ::= { nbSwitchG1 50}
mrvPrivateTraps        OBJECT IDENTIFIER ::= { nbPrivTraps 3}
mrvTrapParameters      OBJECT IDENTIFIER ::= { mrvPrivateTraps 1 }
mrvPrivateGenTraps     OBJECT IDENTIFIER ::= { mrvPrivateTraps 6}
mrvPrivateSpecTraps    OBJECT IDENTIFIER ::= { mrvPrivateTraps 7}

mrvPrivateTrapsConformance    OBJECT IDENTIFIER ::= { nbPrivTraps 100 }
mrvPrivateTrapsMIBCompliances OBJECT IDENTIFIER ::= { mrvPrivateTrapsConformance 1 }
mrvPrivateTrapsMIBGroups      OBJECT IDENTIFIER ::= { mrvPrivateTrapsConformance 2 }

-- ************************************************************
-- Textual conventions
-- ************************************************************

TCEventClass ::= TEXTUAL-CONVENTION
    STATUS          current
    DESCRIPTION
            "The categories of which events are classified by."
    SYNTAX          INTEGER {
                      serviceAffecting(1),
                      nonServiceAffecting (2)
                    }

TCEventLevel ::= TEXTUAL-CONVENTION
    STATUS          current
    DESCRIPTION
            "The severity level of events."
    SYNTAX          INTEGER {
                      critical(1),
                      major(2),
                      minor(3),
                      info(4),
                      clear(5)
                    }

NbEthOamMepId ::= TEXTUAL-CONVENTION
    DISPLAY-HINT "d"
    STATUS      current
    DESCRIPTION
       "Maintenance association End Point Identifier (MEPID): A small
        integer, unique over a given Maintenance Association,
        identifying a specific MEP."
    REFERENCE
       "802.1ag clauses 3.19 and 19.2.1"
    SYNTAX      Unsigned32 (1..4095)

NbEthOamMDLevel ::= TEXTUAL-CONVENTION
    DISPLAY-HINT "d"
    STATUS      current
    DESCRIPTION
       "Integer identifying the Maintenance Domain Level (MD Level).
        Higher numbers correspond to higher Maintenance Domains,
        those with the greatest physical reach, with the highest
        values for customers' CFM PDUs.  Lower numbers correspond
        to lower Maintenance Domains, those with more limited
        physical reach, with the lowest values for CFM PDUs
        protecting single bridges or physical links.
       "
    REFERENCE
       "802.1ag clauses 18.3, 21.4.1"
    SYNTAX      Integer32 (0..7)

NbEthOamCcmHighestDefectPri ::= TEXTUAL-CONVENTION
    STATUS      current
    DESCRIPTION
       "Copied from Dot1agCfmHighestDefectPri of dot1ag.mib.
        An enumerated value, equal to the contents of the variable
        highestDefect (20.33.9 and Table 20-1), indicating the
        highest-priority defect that has been present since the MEP
        Fault Notification Generator State Machine was last in the
        FNG_RESET state, either:

        none(0)           no defects since FNG_RESET
        defRDICCM(1)      DefRDICCM
        defMACstatus(2)   DefMACstatus
        defRemoteCCM(3)   DefRemoteCCM
        defErrorCCM(4)    DefErrorCCM
        defXconCCM(5)     DefXconCCM

        The value 0 is used for no defects so that additional higher
        priority values can be added, if needed, at a later time, and
        so that these values correspond with those in
        Dot1agCfmLowestAlarmPri.
       "
    REFERENCE
       "802.1ag clause 20.1.2, 12.14.7.7.2:c and 20.33.9"
    SYNTAX      INTEGER {
                  none              (0),
                  defRDICCM         (1),
                  defMACstatus      (2),
                  defRemoteCCM      (3),
                  defErrorCCM       (4),
                  defXconCCM        (5)
                }


-- ************************************************************
-- Trap parameters
-- ************************************************************


mrvElementID OBJECT-TYPE
    SYNTAX          DisplayString
    MAX-ACCESS      read-only
    STATUS          current
    DESCRIPTION
            "String description contains the element name (hostname) to identify the element."
    ::= { mrvTrapParameters 2 }

mrvPortIndex OBJECT-TYPE
    SYNTAX          Integer32 (1..65535)
    MAX-ACCESS      read-only
    STATUS          current
    DESCRIPTION
            "The port index of the event that generated the trap."
    ::= { mrvTrapParameters 5 }


mrvEventDescription OBJECT-TYPE
    SYNTAX          DisplayString
    MAX-ACCESS      read-only
    STATUS          current
    DESCRIPTION
            "A description of the event that generated the trap."
    ::= { mrvTrapParameters 7 }

mrvEventClass OBJECT-TYPE
    SYNTAX          TCEventClass
    MAX-ACCESS      read-only
    STATUS          current
    DESCRIPTION
            "The category of the event that generated the trap."
    ::= { mrvTrapParameters 8 }

mrvEventLevel OBJECT-TYPE
    SYNTAX          TCEventLevel
    MAX-ACCESS      read-only
    STATUS          current
    DESCRIPTION
            "The severity level of the event that generated the trap."
    ::= { mrvTrapParameters 9 }


mrvDevPSIndex		OBJECT-TYPE
		SYNTAX      Integer32
		MAX-ACCESS  read-only
		STATUS      current
		DESCRIPTION
		 "The index of the table,
		  (MAX Value is equal to nbsDevPSNumber)."
		::= { mrvTrapParameters 10 }

mrvDevFANIndex		OBJECT-TYPE
		SYNTAX      Integer32
		MAX-ACCESS  read-only
		STATUS      current
		DESCRIPTION
		 "The index of the table,
		  (MAX Value is equal to nbsDevFANsNumber)."
		::= { mrvTrapParameters 11 }

mrvEthOamMdLevel OBJECT-TYPE
    SYNTAX      NbEthOamMDLevel
    MAX-ACCESS  read-only
    STATUS      current
    DESCRIPTION
       "MD Level of the Maintenance Point."
    REFERENCE
       "802.1ag clause 12.14.2.1.2:b"
    ::= { mrvTrapParameters 12 }

mrvEthOamMaIndex OBJECT-TYPE
    SYNTAX      Unsigned32(1..4294967295)
    MAX-ACCESS  read-only
    STATUS      current
    DESCRIPTION
       "The Maintenance Association index."
    REFERENCE
       "."
    ::= { mrvTrapParameters 13 }


mrvEthOamMepIdentifier OBJECT-TYPE
    SYNTAX      NbEthOamMepId
    MAX-ACCESS  read-only
    STATUS      current
    DESCRIPTION
       "Source MEP for the Loopback test"
    REFERENCE
       "."
    ::= { mrvTrapParameters 14 }

mrvEthOamTrapCcmHighestPrDefect OBJECT-TYPE
    SYNTAX      NbEthOamCcmHighestDefectPri
    MAX-ACCESS  read-only
    STATUS      current
    DESCRIPTION
       "Copied from dot1agCfmMepHighestPrDefect of dot1ag.mib.
        The highest priority defect that has been present since the
        MEPs Fault Notification Generator State Machine was last in
        the FNG_RESET state.  "
    REFERENCE
       "802.1ag clause 12.14.7.1.3:n  20.33.9 and Table 21-1"
    ::= { mrvTrapParameters 15 }

mrvDevLosGrActivePortNumber OBJECT-TYPE
    SYNTAX     Integer32
    MAX-ACCESS read-write
    STATUS	   current
    DESCRIPTION
    "The number of Active port in the corresponding Group."
    ::= { mrvTrapParameters 16 }


mrvDevLosGrPrimaryPort OBJECT-TYPE
    SYNTAX       Integer32 (0..256)
    MAX-ACCESS   read-write
    STATUS       current
    DESCRIPTION
    "The number of the Primary Port from the Ports Group Members list."
    ::= { mrvTrapParameters 17 }


mrvDevLosGrSecondaryPort OBJECT-TYPE
    SYNTAX Integer32 (0..256)
    MAX-ACCESS   read-only
    STATUS  current
    DESCRIPTION
    "The number of the Secondary Port from the Ports Group Members list."
    ::= { mrvTrapParameters 18 }

mrvDevLosGrActionCause OBJECT-TYPE
    SYNTAX  INTEGER {
       noAction           (1),
       portLinkUp         (2),
       portLinkDown       (3),
       agRMepDiscardEvent (4),
       agRMepNoConnEvent  (5),
       agRMepAliveEvent   (6),
       activePortAdminSet (7)
    }
    MAX-ACCESS read-only
    STATUS	current
    DESCRIPTION
    "The causes of last LOS action are:
     [portLinkDown] - port [oaDevLosGrActivePortNumber] is active because
                    other Group member port became Link Down now.
     [portLinkUp]   - port [oaDevLosGrActivePortNumber] is active because
                    it became Link Up now.
     [agRMepDiscardEvent] - port [oaDevLosGrActivePortNumber] is active because
                    other Group member port received 'Remote Mep Discard Event'.
     [agRMepNoConnEvent] - port [oaDevLosGrActivePortNumber] is active because
                    other Group member port received 'No connection to Remote Mep Event'.
     [agRMepAliveEvent] - port [oaDevLosGrActivePortNumber] is active because
                    it received 'Remote Mep Alive Event'.
     [activePortAdminSet] - port [oaDevLosGrActivePortNumber] is active because
                    of administrative setting."
    ::= { mrvTrapParameters 19 }

mrvPortLinSlavePorts OBJECT-TYPE
    SYNTAX     OCTET STRING (SIZE (0..255))
    MAX-ACCESS read-write
    STATUS     current
    DESCRIPTION
    "List of Slave Ports in the Link Reflection (LIN) entry.
     Each octet contains the corresponding number of Port or Trunk
     [order: from first up to last].
     Trunks appear in the List of Ports with the value equal to
     ( 132 + [oaDevTrunkGrId] )."
    ::= { mrvTrapParameters 20 }

mrvPortLinActionCause OBJECT-TYPE
    SYNTAX             INTEGER {
       noAction           (1),
       portLinkUp         (2),
       portLinkDown       (3),
       agRMepDiscardEvent (4),
       agRMepNoConnEvent  (5),
       agRMepAliveEvent   (6)
    }
    MAX-ACCESS read-only
    STATUS	current
    DESCRIPTION
    "The causes of last LIN action are:
     [portLinkDown] - Slave Ports [oaPortLinSlavePorts] are Down because
                      the Master port [oaPortLinId] became Down now.
     [portLinkUp]   -  Slave Ports [oaPortLinSlavePorts] are Up because
                      the Master port [oaPortLinId] became Up now.
     [agRMepDiscardEvent] - Slave Ports [oaPortLinSlavePorts] are Down because
                      the Master port [oaPortLinId] received 'Remote Mep Discard Event'.
     [agRMepNoConnEvent] - Slave Ports [oaPortLinSlavePorts] are Down because
                      the Master port [oaPortLinId] received 'No connection to Remote Mep Event'.
     [agRMepAliveEvent] - Slave Ports [oaPortLinSlavePorts] are Up because
                      the Master port [oaPortLinId] received 'Remote Mep Alive Event'."
    ::= { mrvTrapParameters 21 }



-- ************************************************************
-- Traps (notifications)
-- ************************************************************

-- *******************************************************************
--  Generic traps (reflection of RFCs 3418 and 2863
-- *******************************************************************

mrvPrivateGenTrapPrefix OBJECT IDENTIFIER ::= { mrvPrivateGenTraps 0 }

mrvColdStart NOTIFICATION-TYPE
    OBJECTS         {
                      mrvElementID,
                      mrvEventDescription, -- "NE restarted and reinitializing with altered configuration"
                      mrvEventLevel,       -- critical(1)
                      mrvEventClass        -- serviceAffecting(1)
                    }
    STATUS  current
    DESCRIPTION
            "This trap signifies that the SNMP entity, acting
            in an agent role, is reinitializing itself and that its
            configuration may have been altered."
    ::= { mrvPrivateGenTrapPrefix 1 }

mrvWarmStart NOTIFICATION-TYPE
    OBJECTS         {
                      mrvElementID,
                      mrvEventDescription, -- "NE restarted and reinitializing with altered configuration"
                      mrvEventLevel,       -- critical(1)
                      mrvEventClass        -- serviceAffecting(1)
                    }
    STATUS  current
    DESCRIPTION
            "This trap signifies that the SNMP entity, acting
            in an agent role, is reinitializing itself such that its
            configuration is unaltered."
    ::= { mrvPrivateGenTrapPrefix 2 }

mrvPortLinkDown NOTIFICATION-TYPE
    OBJECTS         {
                      mrvElementID,
                      mrvEventDescription, -- "SNMP agent communication link changed state - down"
                      mrvEventLevel,       -- critical(1)
                      mrvEventClass,       -- serviceAffecting(1)
                      mrvPortIndex         -- MRV will always send the save value like ifIndex
                    }
    STATUS          current
    DESCRIPTION
            "A mrvPortLinkDown trap signifies that the SNMP entity, acting in
            agent role, has detected that the ifOperStatus object for
            of its communication links is about to enter the down
            from some other state (but not from the notPresent).
            This other state is indicated by the included value of ifOperStatus."
    ::= { mrvPrivateGenTrapPrefix 3 }

mrvPortLinkUp   NOTIFICATION-TYPE
    OBJECTS         {
                      mrvElementID,
                      mrvEventDescription, -- "SNMP agent communication link changed state - up"
                      mrvEventLevel,       -- clear(5)
                      mrvEventClass,       -- serviceAffecting(1)
                      mrvPortIndex         -- MRV will always send the save value like ifIndex
                    }
    STATUS          current
    DESCRIPTION
            "A mrvPortLinkUp trap signifies that the SNMP entity, acting in an
            role, has detected that the ifOperStatus object for
            of its communication links left the down state and
            transitioned into some other state (but not into the
            notPresent state). This other state is indicated by the
            included value of ifOperStatus."
    ::= { mrvPrivateGenTrapPrefix 4 }

mrvAuthenticationFailure NOTIFICATION-TYPE
    OBJECTS         {
                      mrvElementID,
                      mrvEventDescription, -- "Access via SNMP failed"
                      mrvEventLevel,       -- minor(3)
                      mrvEventClass        -- nonServiceAffecting(1)
                    }
    STATUS  current
    DESCRIPTION
            "An authenticationFailure trap signifies that the SNMP
            entity, acting in an agent role, has received a protocol
            message that is not properly authenticated.  While all
            implementations of the SNMP must be capable of generating
            this trap, the snmpEnableAuthenTraps object indicates
            whether this trap will be generated."
    ::= { mrvPrivateGenTrapPrefix 5 }

-- *******************************************************************
--  Specific traps
-- *******************************************************************

mrvPrivateSpecTrapPrefix OBJECT IDENTIFIER ::= { mrvPrivateSpecTraps 0 }

mrvPowerSupplyUp NOTIFICATION-TYPE
    OBJECTS         {
                      mrvElementID,
                      mrvEventDescription, -- "Power Supply Up"
                      mrvEventLevel,       -- clear(5)
                      mrvEventClass,       -- nonServiceAffecting(1)
                      mrvDevPSIndex
                    }
    STATUS  current
    DESCRIPTION
            "The SNMP trap that is generated when
    		 power supply unit changes it's state from notActive to active"
    ::= { mrvPrivateSpecTrapPrefix 1 }

mrvPowerSupplyDown NOTIFICATION-TYPE
    OBJECTS         {
                      mrvElementID,
                      mrvEventDescription, -- "Power Supply Down"
                      mrvEventLevel,       -- minor(3)
                      mrvEventClass,       -- nonServiceAffecting(1)
                      mrvDevPSIndex
                    }
    STATUS  current
    DESCRIPTION
            "The SNMP trap that is generated when
    		 power supply unit changes it's state from active to notActive"
    ::= { mrvPrivateSpecTrapPrefix 2 }

mrvFANUnitUp       NOTIFICATION-TYPE
    OBJECTS         {
                      mrvElementID,
                      mrvEventDescription, -- "FAN Active"
                      mrvEventLevel,       -- clear(5)
                      mrvEventClass,       -- nonServiceAffecting(1)
                      mrvDevFANIndex
                    }
    STATUS  current
    DESCRIPTION
            "The SNMP trap that is generated when
    		 FAN unit changes it's state from notActive to active"
    ::= { mrvPrivateSpecTrapPrefix 3 }

mrvFANUnitDown    NOTIFICATION-TYPE
    OBJECTS         {
                      mrvElementID,
                      mrvEventDescription, -- "FAN Failure"
                      mrvEventLevel,       -- minor(3)
                      mrvEventClass,       -- nonServiceAffecting(1)
                      mrvDevFANIndex
                    }
    STATUS  current
    DESCRIPTION
            "The SNMP trap that is generated when
    		 FAN unit changes it's state from active to notActive"
    ::= { mrvPrivateSpecTrapPrefix 4 }

mrvDeviceTemperatureNormal NOTIFICATION-TYPE
    OBJECTS         {
                      mrvElementID,
                      mrvEventDescription, -- "Device Temperature Normal"
                      mrvEventLevel,       -- clear(5)
                      mrvEventClass        -- nonServiceAffecting(1)
                    }
    STATUS  current
    DESCRIPTION
            "The SNMP trap that is generated when
    		 Device Temperature changes it's state from High to Normal"
    ::= { mrvPrivateSpecTrapPrefix 5 }

mrvDeviceTemperatureHigh NOTIFICATION-TYPE
    OBJECTS         {
                      mrvElementID,
                      mrvEventDescription, -- "Device Temperature too high"
                      mrvEventLevel,       -- major(2)
                      mrvEventClass        -- nonServiceAffecting(1)
                    }
    STATUS  current
    DESCRIPTION
            "The SNMP trap that is generated when
    		 Device Temperature changes it's state from Normal to High"
    ::= { mrvPrivateSpecTrapPrefix 6 }

mrvDot1agCfmFault NOTIFICATION-TYPE
    OBJECTS         {
                      mrvElementID,
                      mrvEventDescription, -- "Continuity Check Failed"
                      mrvEventLevel,       -- critical(1)
                      mrvEventClass,       -- serviceAffecting(1)
                      mrvEthOamMdLevel,
                      mrvEthOamMaIndex,
                      mrvEthOamMepIdentifier,
                      mrvEthOamTrapCcmHighestPrDefect
                    }
    STATUS  current
    DESCRIPTION
            "A MEP has a persistent defect condition. A notification
            (fault alarm) is sent to the management entity with the OID
            of the MEP that has detected the fault"
    REFERENCE
            "802.1ag clause 12.14.7.7"
    ::= { mrvPrivateSpecTrapPrefix 7 }

mrvDot1agCfmRecovery NOTIFICATION-TYPE
    OBJECTS         {
                      mrvElementID,
                      mrvEventDescription, -- "Continuity Recovery"
                      mrvEventLevel,       -- clear(5)
                      mrvEventClass,       -- serviceAffecting(1)
                      mrvEthOamMdLevel,
                      mrvEthOamMaIndex,
                      mrvEthOamMepIdentifier,
                      mrvEthOamTrapCcmHighestPrDefect
                    }
    STATUS  current
    DESCRIPTION
            "A MEP has a persistent defect condition. A notification
            (recovery alarm) is sent to the management entity with the OID
            of the MEP that has detected the recovery after a fault."
    REFERENCE
            "802.1ag clause 12.14.7.7"
    ::= { mrvPrivateSpecTrapPrefix 8 }

mrvPortProtectionBackup NOTIFICATION-TYPE
    OBJECTS         {
                      mrvElementID,
                      mrvEventDescription, -- "Traffic switced to backup"
                      mrvEventLevel,       -- major(2)
                      mrvEventClass,       -- serviceAffecting(1)
                      mrvDevLosGrActivePortNumber,
                      mrvDevLosGrPrimaryPort,
                      mrvDevLosGrSecondaryPort,
                      mrvDevLosGrActionCause
                    }
    STATUS  current
    DESCRIPTION
            "The SNMP trap that is generated when one of the Ports in the LOS Group
             became Active.
             For example: port A and port B are the members of the LOS Group while
             port A is a primary port and port B is the secondary port."
    ::= { mrvPrivateSpecTrapPrefix 9 }

mrvPortProtectionPrimary NOTIFICATION-TYPE
    OBJECTS         {
                      mrvElementID,
                      mrvEventDescription, -- "Traffic restored to port"
                      mrvEventLevel,       -- clear(5)
                      mrvEventClass,       -- serviceAffecting(1)
                      mrvDevLosGrActivePortNumber,
                      mrvDevLosGrPrimaryPort,
                      mrvDevLosGrSecondaryPort,
                      mrvDevLosGrActionCause
                    }
    STATUS  current
    DESCRIPTION
            "The SNMP trap that is generated when one of the Ports in the LOS Group
             became Active.
             For example: port A and port B are the members of the LOS Group while
             port A is a primary port and port B is the secondary port."
    ::= { mrvPrivateSpecTrapPrefix 10 }

mrvPortReflectionLinkDown NOTIFICATION-TYPE
    OBJECTS         {
                      mrvElementID,
                      mrvEventDescription, -- "Port down due to link reflection"
                      mrvEventLevel,       -- major(2)
                      mrvEventClass,       -- serviceAffecting(1)
                      mrvPortIndex,
                      mrvPortLinSlavePorts,
                      mrvPortLinActionCause
                    }
    STATUS  current
    DESCRIPTION
            "The SNMP trap that is generated when Dependent ports
             [mrvPortLinSlavePorts] Link State became Down as result of
             link reflection only.
             It should not be sent, when port became Down by
             physical disconnection or CLI command 'port state disable' -
             unlike standard LinkDown.
             In the case of [mrvPortLinSymmetricStatus]='nonSymmetric'
             the Dependent ports are indeed the LIN Slave ports.
             But in the case of [mrvPortLinSymmetricStatus]='symmetric'
             the Dependent ports list has only one port which can be
             Master port or Slave port, because in this case these both
             ports are equivalent."
    ::= { mrvPrivateSpecTrapPrefix 11 }

mrvPortReflectionLinkUp NOTIFICATION-TYPE
    OBJECTS         {
                      mrvElementID,
                      mrvEventDescription, -- "Port up due to link reflection"
                      mrvEventLevel,       -- clear(5)
                      mrvEventClass,       -- serviceAffecting(1)
                      mrvPortIndex,
                      mrvPortLinSlavePorts,
                      mrvPortLinActionCause
                    }
    STATUS  current
    DESCRIPTION
            "The SNMP trap that is generated when Dependent ports
             [mrvPortLinSlavePorts] Link State became Up.
             as result of link reflection only.
             It should not be sent, when port became Up by
             physical connection or CLI command 'port state enable' -
             unlike standard LinkUp.
             In the case of [mrvPortLinSymmetricStatus]='nonSymmetric'
             the Dependent ports are indeed the LIN Slave ports.
             But in the case of [mrvPortLinSymmetricStatus]='symmetric'
             the Dependent ports list has only one port which can be
             Master port or Slave port, because in this case these both
             ports are equivalent."
    ::= { mrvPrivateSpecTrapPrefix 12 }

-- *******************************************************************
--  Conformance Information
-- *******************************************************************

mrvPrivateTrapsMIBCompliance MODULE-COMPLIANCE
    STATUS current
    DESCRIPTION
        "The core compliance statement for all the implementations."

    MODULE -- this module
        MANDATORY-GROUPS {
                          mrvPrivateTrapsMandatoryGroup,
                          mrvPrivateTrapsNotifGrp
                         }

    ::= { mrvPrivateTrapsMIBCompliances 1 }

-- ...................................................................
-- Conformance Groups
-- ...................................................................

mrvPrivateTrapsMandatoryGroup  OBJECT-GROUP
    OBJECTS {
       mrvPortIndex,
       mrvEventDescription,
       mrvEventClass,
       mrvEventLevel,
       mrvElementID,
       mrvDevPSIndex,
       mrvDevFANIndex,
       mrvEthOamMdLevel,
       mrvEthOamMaIndex,
       mrvEthOamMepIdentifier,
       mrvEthOamTrapCcmHighestPrDefect,
       mrvDevLosGrActivePortNumber,
       mrvDevLosGrPrimaryPort,
       mrvDevLosGrSecondaryPort,
       mrvDevLosGrActionCause,
       mrvPortLinSlavePorts,
       mrvPortLinActionCause
    }
    STATUS current
    DESCRIPTION
        "."

    ::= { mrvPrivateTrapsMIBGroups 1 }


mrvPrivateTrapsNotifGrp NOTIFICATION-GROUP
   NOTIFICATIONS {
             mrvColdStart,
             mrvWarmStart,
             mrvPortLinkUp, mrvPortLinkDown,
             mrvAuthenticationFailure,
             mrvPowerSupplyUp, mrvPowerSupplyDown,
             mrvFANUnitUp, mrvFANUnitDown,
             mrvDeviceTemperatureNormal, mrvDeviceTemperatureHigh,
             mrvDot1agCfmFault, mrvDot1agCfmRecovery,
             mrvPortProtectionBackup, mrvPortProtectionPrimary,
             mrvPortReflectionLinkDown, mrvPortReflectionLinkUp
          }
   STATUS        current
   DESCRIPTION
       "The notification which are required to be supported by
       implementations of this MIB."
   ::= { mrvPrivateTrapsMIBGroups 2 }


END
