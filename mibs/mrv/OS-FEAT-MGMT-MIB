--  =======================================================================
--  File        : osfaetMgmt.mib
--  Description : Private MIB abstract featues management support
--  By          : Alex

-- Copyright (c) 2008 MRV.  All Rights Reserved.
--
--
-- Reproduction of this document is authorized on condition that this
-- copyright notice is included.  This MRV SNMP MIB Specification
-- embodies MRV's proprietary intellectual property.  MRV
-- retains all title and ownership in the specification, including any
-- revisions.
--
-- It is MRV's intent to encourage the widespread use of this
-- specification in connection with the management of MRV's
-- products. MRV grants vendor, end-users, and other interested
-- parties a non-exclusive license to use this specification in
-- connection with the management of MRV's products.
--
-- This specification is supplied "AS IS," and MRV makes no
-- warranty, either express or implied, as to the use, operation,
-- condition, or performance of the specification.
--
-- Copyright text courtesy of MRV
--
-- If you have any questions about this MIB, please call MRV
-- Technical Support Center at 1-800-858-7815 from inside USA or
-- 1-818-773-0900 from outside USA.
--
--
-- MRV retains the right to change this MIB without notification.

OS-FEAT-MGMT-MIB DEFINITIONS ::= BEGIN

IMPORTS
                MODULE-IDENTITY, OBJECT-TYPE,
                Unsigned32                                    FROM SNMPv2-SMI
                oaOptiSwitch                                  FROM OS-COMMON-TC-MIB
                MODULE-COMPLIANCE, OBJECT-GROUP               FROM SNMPv2-CONF;

osFeatMgmt      MODULE-IDENTITY
                LAST-UPDATED "201010260000Z"
                ORGANIZATION "MRV Communications, Inc."
                CONTACT-INFO
                   "Alex Rozin
                    MRV Communication, Inc
                    http://www.mrv.com
                    Email:  ARozin@mrv.com"
                DESCRIPTION
                    "This MIB allows to configurate tag actions in Ethernet
                    Provision services."
                REVISION     "201010260000Z"
                DESCRIPTION
                    "Initial edition."
                ::= { oaOptiSwitch 21 }

-- ************************************************************
-- MIB place Definition
-- ************************************************************

osFeatMgmtObjects           OBJECT IDENTIFIER ::= { osFeatMgmt 1 }
osFeatMgmtConformance       OBJECT IDENTIFIER ::= { osFeatMgmt 100 }
osFeatMgmtMIBCompliances    OBJECT IDENTIFIER ::= { osFeatMgmtConformance 1 }
osFeatMgmtMIBGroups         OBJECT IDENTIFIER ::= { osFeatMgmtConformance 2 }

--3456789a123456789b123456789c123456789d123456789e123456789f123456789g123456789

-- ************************************************************
-- The osFeatMgmtTable Table
-- ************************************************************
osFeatMgmtTable  OBJECT-TYPE
    SYNTAX       SEQUENCE OF OsFeatMgmtEntry
    MAX-ACCESS   not-accessible
    STATUS       current
    DESCRIPTION
        "Features management."
    REFERENCE
       "."
    ::= { osFeatMgmtObjects 3 }

osFeatMgmtEntry   OBJECT-TYPE
    SYNTAX       OsFeatMgmtEntry
    MAX-ACCESS   not-accessible
    STATUS       current
    DESCRIPTION
       "Contains an entry of the table."
    INDEX { osFeatMgmtId }
    ::= { osFeatMgmtTable 1 }

OsFeatMgmtEntry ::= SEQUENCE {
      osFeatMgmtId     INTEGER,
      osFeatMgmtStatus INTEGER,
      osFeatMgmtParam  Unsigned32,
      osFeatMgmtKey    OCTET STRING
}

osFeatMgmtId     OBJECT-TYPE
    SYNTAX       INTEGER {
                   os940rTL10Gports (1)
                 }
    MAX-ACCESS   not-accessible
    STATUS       current
    DESCRIPTION
        "Feature ID"
    ::= { osFeatMgmtEntry 1 }

osFeatMgmtStatus OBJECT-TYPE
    SYNTAX       INTEGER {
                   other  (0),
                   deny   (1),
                   permit (2)
                 }
    MAX-ACCESS   read-write
    STATUS       current
    DESCRIPTION
        "Status of the feature."
    ::= { osFeatMgmtEntry 2 }

osFeatMgmtParam  OBJECT-TYPE
    SYNTAX       Unsigned32
    MAX-ACCESS   read-write
    STATUS       current
    DESCRIPTION
        "Status of the feature."
    ::= { osFeatMgmtEntry 3 }


osFeatMgmtKey    OBJECT-TYPE
    SYNTAX       OCTET STRING (SIZE(16))
    MAX-ACCESS   read-write
    STATUS       current
    DESCRIPTION
        "Status of the feature."
    ::= { osFeatMgmtEntry 4 }

-- *******************************************************************
--  Conformance Information
-- *******************************************************************

osFeatMgmtMIBCompliance MODULE-COMPLIANCE
    STATUS current
    DESCRIPTION
        "The core compliance statement for all the implementations."

    MODULE -- this module
        MANDATORY-GROUPS {
                          osFeatMgmtMandatoryGroup
                         }

    ::= { osFeatMgmtMIBCompliances 1 }

-- ...................................................................
-- Conformance Groups
-- ...................................................................
osFeatMgmtMandatoryGroup  OBJECT-GROUP
    OBJECTS {
      osFeatMgmtStatus,
      osFeatMgmtParam,
      osFeatMgmtKey
            }
    STATUS current
    DESCRIPTION
        "."

    ::= { osFeatMgmtMIBGroups 1 }


END
