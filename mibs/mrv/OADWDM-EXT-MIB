--  =======================================================================
--  File          : Oadwdm_ext.mib
--  Description   : Extended Private MIB for LambdaDriver (DWDM/CWDM)
--
--  By            : Olga Bronshteyn
--  Version       : Revision:   1.00
--  Original Date : June 28, 2009
--  Last Change   : Date:   July 1, 2009
--  =======================================================================
--
--
-- Copyright (c) 2001 MRV.  All Rights Reserved.
--
-- Reproduction of this document is authorized on condition that this
-- copyright notice is included.  This MRV SNMP MIB Specification
-- embodies MRV proprietary intellectual property.  MRV
-- retains all title and ownership in the specification, including any
-- revisions.
--
-- It is MRV's intent to encourage the widespread use of this
-- specification in connection with the management of MRV's
-- products. MRV grants vendor, end-users, and other interested
-- parties a non-exclusive license to use this specification in
-- connection with the management of MRV's products.
--
-- This specification is supplied "AS IS," and MRV makes no
-- warranty, either express or implied, as to the use, operation,
-- condition, or performance of the specification.
--
-- MRV retains the right to change this MIB without notification.
--
OADWDM-EXT-MIB DEFINITIONS ::= BEGIN

        IMPORTS
                enterprises,
                OBJECT-TYPE             FROM SNMPv2-SMI
                Integer32, Counter32,
                Counter64		FROM SNMPv2-SMI
                MODULE-IDENTITY         FROM SNMPv2-SMI
                MODULE-COMPLIANCE,
                OBJECT-GROUP            FROM SNMPv2-CONF;

oaLambdaDriver   MODULE-IDENTITY
        LAST-UPDATED "200907010000Z" -- 1 July, 2009
        ORGANIZATION "MRV Communications"
        CONTACT-INFO "For technical support, please contact your service
                      channel."
        DESCRIPTION
              "This MIB defines extended objects for LambdaDriver."
        REVISION "200906280000Z" -- 28 june, 2009
            DESCRIPTION "Initial MIB Creation."
         ::= { oaManagement 41 }

------------------------------------------------------------------------------
-- Object Identifier Definition
------------------------------------------------------------------------------

oaccess                   OBJECT IDENTIFIER ::= { enterprises 6926 }
oaManagement              OBJECT IDENTIFIER ::= { oaccess 1 }

------------------------------------------------------------------------------
-- GROUPS in    OADWDM-EXT-MIB
------------------------------------------------------------------------------

oaLdPortsCntr             OBJECT IDENTIFIER ::= { oaLambdaDriver 10 }

oaLdPortsCntrConformance  OBJECT IDENTIFIER ::= { oaLambdaDriver 100 }

------------------------------------------------------------------------------
-- OADWDM-EXT-MIB - defines the Ports Ethernet counters.
------------------------------------------------------------------------------

oaLdPortsCntrTable OBJECT-TYPE
        SYNTAX SEQUENCE OF OaLdPortsCntrEntry
        MAX-ACCESS not-accessible
        STATUS current
        DESCRIPTION
        "Information table of Port Ethernet Counters."
        ::= {oaLdPortsCntr 2}

oaLdPortsCntrEntry OBJECT-TYPE
        SYNTAX    OaLdPortsCntrEntry
        MAX-ACCESS not-accessible
        STATUS current
        DESCRIPTION
        "Port Ethernet Counters."
        INDEX { oaLdPortsCntrSlotNumber, oaLdPortsCntrPortNumber }

        ::= { oaLdPortsCntrTable 1 }

OaLdPortsCntrEntry ::= SEQUENCE {
        oaLdPortsCntrSlotNumber     Integer32,
        oaLdPortsCntrPortNumber     Integer32,
        oaLdPortsCntrSyncErrs       Counter32,
        oaLdPortsCntrCrcErrs        Counter32,
        oaLdPortsCntrInRateBits     Integer32,
        oaLdPortsCntrOutRateBits    Integer32,
        oaLdPortsCntrCodeViols      Counter32,
        oaLdPortsCntrInPkts         Counter64,
        oaLdPortsCntrOutPkts        Counter64,
        oaLdPortsCntrInOctets       Counter64,
        oaLdPortsCntrOutOctets      Counter64
}

oaLdPortsCntrSlotNumber OBJECT-TYPE
        SYNTAX    Integer32 (1..24)
        MAX-ACCESS not-accessible
        STATUS current
        DESCRIPTION
        "The slot#. An index from 1 to The number of slots."
        ::= { oaLdPortsCntrEntry 1 }

oaLdPortsCntrPortNumber OBJECT-TYPE
        SYNTAX    Integer32 (1..40)
        MAX-ACCESS not-accessible
        STATUS current
        DESCRIPTION
        "The port#. An index from 1 to The number of ports."
        ::= { oaLdPortsCntrEntry 2 }

oaLdPortsCntrSyncErrs OBJECT-TYPE
        SYNTAX    Counter32
        MAX-ACCESS    read-only
        STATUS  current
        DESCRIPTION
        "The number of SYNC error occured in the port."
        ::= { oaLdPortsCntrEntry 3 }

oaLdPortsCntrCrcErrs OBJECT-TYPE
        SYNTAX    Counter32
        MAX-ACCESS    read-only
        STATUS    current
        DESCRIPTION
        "The number of CRC error occured in the port."
        ::= { oaLdPortsCntrEntry 4 }

oaLdPortsCntrInRateBits OBJECT-TYPE
        SYNTAX    Integer32
        MAX-ACCESS    read-only
        STATUS    current
        DESCRIPTION
        "The Bit Rate measured on received traffic in bits per second."
        ::= { oaLdPortsCntrEntry 5 }

oaLdPortsCntrOutRateBits OBJECT-TYPE
        SYNTAX    Integer32
        MAX-ACCESS    read-only
        STATUS    current
        DESCRIPTION
        "The Bit Rate measured on transmitted traffic in bits per second."
        ::= { oaLdPortsCntrEntry 6 }

oaLdPortsCntrCodeViols OBJECT-TYPE
        SYNTAX    Counter32
        MAX-ACCESS    read-only
        STATUS    current
        DESCRIPTION
        "The number of Code Violation occured in the port."
        ::= { oaLdPortsCntrEntry 7 }

oaLdPortsCntrInPkts OBJECT-TYPE
        SYNTAX    Counter64
        MAX-ACCESS    read-only
        STATUS    current
        DESCRIPTION
        "The total number of packets received on the port."
        ::= { oaLdPortsCntrEntry 8 }

oaLdPortsCntrOutPkts OBJECT-TYPE
        SYNTAX    Counter64
        MAX-ACCESS    read-only
        STATUS    current
        DESCRIPTION
        "The total number of packets transmitted out of the port."
        ::= { oaLdPortsCntrEntry 9 }

oaLdPortsCntrInOctets OBJECT-TYPE
        SYNTAX    Counter64
        MAX-ACCESS    read-only
        STATUS    current
        DESCRIPTION
        "The total number of bytes received on the port."
        ::= { oaLdPortsCntrEntry 10 }

oaLdPortsCntrOutOctets OBJECT-TYPE
        SYNTAX    Counter64
        MAX-ACCESS    read-only
        STATUS    current
        DESCRIPTION
        "The total number of bytes transmitted out of the port."
        ::= { oaLdPortsCntrEntry 11 }

------------------------------------------------------------------------------
-- conformance information
------------------------------------------------------------------------------

oaLdPortsCntrGroups       OBJECT IDENTIFIER ::= { oaLdPortsCntrConformance 1 }
oaLdPortsCntrCompliances  OBJECT IDENTIFIER ::= { oaLdPortsCntrConformance 2 }

------------------------------------------------------------------------------
-- compliance statements
------------------------------------------------------------------------------

oaLdPortsCntrCompliance   MODULE-COMPLIANCE
    STATUS  current
    DESCRIPTION
            "The compliance statement for extended objects of LambdaDriver."

    MODULE  -- this module
        MANDATORY-GROUPS {
                          oaLdPortsCntrGroup
                         }

    ::= { oaLdPortsCntrCompliances 1 }

------------------------------------------------------------------------------
-- units of conformance
------------------------------------------------------------------------------

oaLdPortsCntrGroup OBJECT-GROUP
    OBJECTS { oaLdPortsCntrSyncErrs,
              oaLdPortsCntrCrcErrs,
              oaLdPortsCntrInRateBits,
              oaLdPortsCntrOutRateBits,
              oaLdPortsCntrCodeViols,
              oaLdPortsCntrInPkts,
              oaLdPortsCntrOutPkts,
              oaLdPortsCntrInOctets,
              oaLdPortsCntrOutOctets }
    STATUS  current
    DESCRIPTION
            "A collection of objects providing information
             for LambdaDriver Port Ethernet Counters."
    ::= { oaLdPortsCntrGroups 1 }

END
