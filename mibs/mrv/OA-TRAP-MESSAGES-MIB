--  =======================================================================
--  File        : oatrpmsg.mib
--  Description : Private MIB for Device TRAPs Descriptions.
--  By          : Maoz & Yakov
--  Version     : 0.1
--  Date        : October 30, 2007
--  =======================================================================

-- Copyright (c) 2005 MRV.  All Rights Reserved.
--
--
-- Reproduction of this document is authorized on condition that this
-- copyright notice is included.  This MRV SNMP MIB Specification
-- embodies MRV's proprietary intellectual property.  MRV
-- retains all title and ownership in the specification, including any
-- revisions.
--
-- It is MRV's intent to encourage the widespread use of this
-- specification in connection with the management of MRV's
-- products. MRV grants vendor, end-users, and other interested
-- parties a non-exclusive license to use this specification in
-- connection with the management of MRV's products.
--
-- This specification is supplied "AS IS," and MRV makes no
-- warranty, either express or implied, as to the use, operation,
-- condition, or performance of the specification.
--
-- Copyright text courtesy of MRV
--
-- If you have any questions about this MIB, please call MRV
-- Technical Support Center at 1-800-858-7815 from inside USA or
-- 1-818-773-0900 from outside USA.
--
--
-- MRV retains the right to change this MIB without notification.

OA-TRAP-MESSAGES-MIB DEFINITIONS ::= BEGIN

IMPORTS
    MODULE-IDENTITY, OBJECT-TYPE,
    enterprises,Integer32, NOTIFICATION-TYPE     FROM SNMPv2-SMI    -- RFC2578
    MODULE-COMPLIANCE, OBJECT-GROUP,
    NOTIFICATION-GROUP                           FROM SNMPv2-CONF   -- RFC2580
    DisplayString                                FROM SNMPv2-TC;    -- RFC2579

nbDeviceTrapMessages  MODULE-IDENTITY
    LAST-UPDATED "200710300000Z"  -- Oct 30, 2007
    ORGANIZATION "MRV Communications, Inc."
    CONTACT-INFO
        "Maoz Yona
         MRV Communication, Inc
         http://www.mrv.com
         Email:  myona@mrv.com

         Yakov Vaisman
         MRV Communication, Inc
         http://www.mrv.com
         Email:  yvaisman@mrv.com
        "

    DESCRIPTION
        "Device TRAPs messages descriptions."

    -- Revision history

    REVISION "200710300000Z"  -- Oct 30, 2007
    DESCRIPTION
        "Initial edition."
    ::= { nbDevGen 27 }

-- ************************************************************
-- MIB place Definition
-- ************************************************************

nbase                    OBJECT IDENTIFIER ::= { enterprises 629 }
nbSwitchG1               OBJECT IDENTIFIER ::= { nbase 1 }
nbSwitchG1Il             OBJECT IDENTIFIER ::= { nbSwitchG1 50}

-- GROUPS for General Device Configuration
nbDeviceConfig           OBJECT IDENTIFIER ::= { nbSwitchG1Il 11}
nbDevGen                 OBJECT IDENTIFIER ::= { nbDeviceConfig 1 }


oaDevTrapsNotifications  OBJECT IDENTIFIER ::= { nbDeviceTrapMessages 0 }
oaDevTrapsGen            OBJECT IDENTIFIER ::= { nbDeviceTrapMessages 1 }
oaDevTrapsPorts          OBJECT IDENTIFIER ::= { nbDeviceTrapMessages 5 }

oaDevTrapsConformance    OBJECT IDENTIFIER ::= { nbDeviceTrapMessages 101 }

-- ************************************************************
-- Objects in the Trap Messages General Group
-- ************************************************************

oaDevTrapsGenSupport OBJECT-TYPE
    SYNTAX  INTEGER {
       notSupported (1),
       supported    (2)
    }
    MAX-ACCESS  read-only
    STATUS  current
    DESCRIPTION
    "Trap message descriptions feature support."
    ::= { oaDevTrapsGen 1 }

-- ************************************************************
-- Objects in the Device Port Trap Messages Group
-- ************************************************************

oaDevTrapsPortsTable    OBJECT-TYPE
    SYNTAX       SEQUENCE OF OaDevTrapsPortsEntry
    MAX-ACCESS   not-accessible
    STATUS       current
    DESCRIPTION
    "Table contains the Interface parameters
     given in the Slot / Port convention."
    ::= { oaDevTrapsPorts 3 }

oaDevTrapsPortsEntry    OBJECT-TYPE
    SYNTAX       OaDevTrapsPortsEntry
    MAX-ACCESS   not-accessible
    STATUS       current
    DESCRIPTION
        "."
    INDEX { oaDevTrapsPortsIfIndex }
    ::= { oaDevTrapsPortsTable 1 }

OaDevTrapsPortsEntry ::= SEQUENCE {
    oaDevTrapsPortsIfIndex         Integer32,
    oaDevTrapsPortsSlotNumber      Integer32,
    oaDevTrapsPortsSlotPortNumber  Integer32,
    oaDevTrapsPortsIfAlias         DisplayString
    }

oaDevTrapsPortsIfIndex     OBJECT-TYPE
    SYNTAX  Integer32 (1..2147483647)
    MAX-ACCESS  accessible-for-notify
    STATUS      current
    DESCRIPTION
    "A unique value of Device Intrerface.
     Same as [ifIndex] value."
    ::= { oaDevTrapsPortsEntry 1 }

oaDevTrapsPortsSlotNumber       OBJECT-TYPE
    SYNTAX       Integer32 (1..256)
    MAX-ACCESS   read-only
    STATUS       current
    DESCRIPTION
    "A sequential value of Slot
     corresponding Interface belons to."
    ::= { oaDevTrapsPortsEntry 2 }

oaDevTrapsPortsSlotPortNumber       OBJECT-TYPE
    SYNTAX       Integer32 (1..256)
    MAX-ACCESS   read-only
    STATUS       current
    DESCRIPTION
    "A sequential value of Port in the Slot
     corresponding Interface belons to."
    ::= { oaDevTrapsPortsEntry 3 }

oaDevTrapsPortsIfAlias   OBJECT-TYPE
    SYNTAX       DisplayString (SIZE (0..64))
    MAX-ACCESS   read-only
    STATUS       current
    DESCRIPTION
    "A string including the Interface Alias/Description.
     Same as [ifAlias] value."
    ::= { oaDevTrapsPortsEntry 4 }

-- *******************************************************************
--  Conformance Information
-- *******************************************************************

oaDevTrapsMIBCompliances  OBJECT IDENTIFIER ::= { oaDevTrapsConformance 1 }
oaDevTrapsMIBGroups       OBJECT IDENTIFIER ::= { oaDevTrapsConformance 2 }

oaDevTrapsMIBCompliance MODULE-COMPLIANCE
    STATUS current
    DESCRIPTION
    "The core compliance statement for all [nbDeviceTrapMessages] implementations."

    MODULE -- this module

        MANDATORY-GROUPS {
                          oaDevTrapsGenGroup,
                          oaDevTrapsPortsGroup,
                          oaDevTrapsPortsNotificationGroup
                         }
    ::= { oaDevTrapsMIBCompliances 1 }

-- ...................................................................
-- Conformance Groups
-- ...................................................................

oaDevTrapsGenGroup  OBJECT-GROUP
    OBJECTS {
             oaDevTrapsGenSupport
            }
    STATUS  current
    DESCRIPTION
    "Optional objects for grouping of Device TRAPs General parameters."
    ::= { oaDevTrapsMIBGroups 1 }

oaDevTrapsPortsGroup  OBJECT-GROUP
    OBJECTS {
             oaDevTrapsPortsIfIndex,
             oaDevTrapsPortsSlotNumber,
             oaDevTrapsPortsSlotPortNumber,
             oaDevTrapsPortsIfAlias
            }
    STATUS  current
    DESCRIPTION
    "Optional objects for grouping of Device TRAPs Ports parameters."
    ::= { oaDevTrapsMIBGroups 2 }

 oaDevTrapsPortsNotificationGroup   NOTIFICATION-GROUP
    NOTIFICATIONS {
             oaDevTrapsLinkDown,
             oaDevTrapsLinkUp
            }
    STATUS  current
    DESCRIPTION
    "The notifications which are required to be supported by
     implementations of this MIB."
    ::= { oaDevTrapsMIBGroups 3 }

-- *******************************************************************
--  Notification Definitions section
-- *******************************************************************

oaDevTrapsLinkDown NOTIFICATION-TYPE
    OBJECTS {
             oaDevTrapsPortsIfIndex,
             oaDevTrapsPortsSlotNumber,
             oaDevTrapsPortsSlotPortNumber,
             oaDevTrapsPortsIfAlias
            }
    STATUS  current
    DESCRIPTION
            "The SNMP trap that is generated when
             link status of the interface became down."
    ::= { oaDevTrapsNotifications 203 }

oaDevTrapsLinkUp NOTIFICATION-TYPE
    OBJECTS {
             oaDevTrapsPortsIfIndex,
             oaDevTrapsPortsSlotNumber,
             oaDevTrapsPortsSlotPortNumber,
             oaDevTrapsPortsIfAlias
            }
    STATUS  current
    DESCRIPTION
            "The SNMP trap that is generated when
             link status of the interface became up."
    ::= { oaDevTrapsNotifications 204 }

END
