--  =======================================================================
--  File        : OS-PWE3-ICCP-MIB.mib
--  Description : Private MIB for Inter-Chassis Communication Protocol for L2VPN PE Pwe3Iccp
--  By          : Yoram Shechori
--
-- Copyright (c) 2014 MRV.  All Rights Reserved.
--
--
-- Reproduction of this document is authorized on condition that this
-- copyright notice is included.  This MRV SNMP MIB Specification
-- embodies MRV's proprietary intellectual property.  MRV
-- retains all title and ownership in the specification, including any
-- revisions.
--
-- It is MRV's intent to encourage the widespread use of this
-- specification in connection with the management of MRV's
-- products. MRV grants vendor, end-users, and other interested
-- parties a non-exclusive license to use this specification in
-- connection with the management of MRV's products.
--
-- This specification is supplied "AS IS," and MRV makes no
-- warranty, either express or implied, as to the use, operation,
-- condition, or performance of the specification.
--
-- Copyright text courtesy of MRV
--
-- If you have any questions about this MIB, please call MRV
-- Technical Support Center at 1-800-858-7815 from inside USA or
-- 1-818-773-0900 from outside USA.
--
--
-- MRV retains the right to change this MIB without notification.
--
-- OS-PWE3-ICCP-MIB.my
-- MIB generated by MG-SOFT Visual MIB Builder 2013 (64-bit) Version 9.0  Build 760
-- Sunday, July 06, 2014 at 14:07:18
--

	OS-PWE3-ICCP-MIB DEFINITIONS ::= BEGIN

		IMPORTS
			OBJECT-GROUP, MODULE-COMPLIANCE, NOTIFICATION-GROUP
				FROM SNMPv2-CONF
			enterprises, Integer32, Unsigned32, OBJECT-TYPE,
			MODULE-IDENTITY, NOTIFICATION-TYPE
				FROM SNMPv2-SMI
            InetAddressType, InetAddress
                FROM INET-ADDRESS-MIB           -- RFC2851
			MacAddress, RowStatus, DisplayString, TEXTUAL-CONVENTION
				FROM SNMPv2-TC;


		-- 1.3.6.1.4.1.6926.2.29
		osPwe3Iccp MODULE-IDENTITY
			LAST-UPDATED "201407061300Z"		-- July 06, 2014 at 13:00 GMT
			ORGANIZATION
				"MRV Communications, Inc."
			CONTACT-INFO
				"Yoram Shechori
				MRV Communication, Inc
				http://www.mrv.com
				Email: yshechori@mrv.com"
			DESCRIPTION
				"MRV MIB for Redundancy support
				This MIB covers the support for ICCP and MCLACP as define by
				draft-ietf-pwe3-iccp
				"
			REVISION "201407061300Z"		-- July 06, 2014 at 13:00 GMT
			DESCRIPTION
				"Initial version"
			::= { oaOptiSwitch 29 }



--
-- Textual conventions
--

		AdminState ::= TEXTUAL-CONVENTION
			STATUS current
			DESCRIPTION
				"Description."
			SYNTAX INTEGER
				{
				up(1),
				down(2)
				}

        BfdStatus ::= TEXTUAL-CONVENTION
            STATUS current
            DESCRIPTION
               "Description."
            SYNTAX INTEGER
                {
                disable(0),
                enable(1)
                }


		IccpStatus ::= TEXTUAL-CONVENTION
			STATUS current
			DESCRIPTION
				"   -NON EXISTENT: This state is the starting point for the state
				   machine.It indicates that no ICCP connection exists and that
				   there's no LDP session established between the PEs.

				   -INITIALIZED: This state indicates that an LDP session exists between
				   the PEs but LDP ICCP Capabilitiy have not yet been exchanged between
				   them.

				   -CAPSENT: This state indicates that an LDP session exists between the
				   PEs and that the local PE has avertized LDP ICCP Capability to its
				   peer.

				   -CAPREC: This state indicates that an LDP session exists between the
				   PEs and that the local PE has both received and avertized LDP ICCP
				   Capability from/to its peer.

				   -CONNECTING: This state indicates that the local PE has initiated
				   an ICCP connection to its peer, and is awaiting its response.

				   -OPERATIONAL: This state indicates that the ICCP connection is
				   operational."
			REFERENCE
				"draft-ietf-pwe3-iccp-16.txt
				4.2.1. ICCP Connection State Machine"
			SYNTAX INTEGER
				{
				nonExistent(0),
				initialized(1),
				capSent(2),
				capRecv(3),
				connecting(4),
				operational(5)
				}

		MlacpStatus ::= TEXTUAL-CONVENTION
			STATUS current
			DESCRIPTION
				"   -NON EXISTENT: This state indicates that the Application Connection
				   does not exist since there is no ICCP connection between the PEs.

				   -RESET: This state indicates that an ICCP connection is operational
				   between the PEs, but that the Application Connection has not been
				   initialized yet or has been resent.

				   -CONNSENT: This state indicates that the local PE has requested
				   initiation of an Application Connection with its peer, but has not
				   received a response yet.

				   -CONNREC: This state indicates that the local PE has received a
				   request to initiate an Application Connection from its peer but has
				   not responded yet.

				   -CONNECTING: This state indicates that the local PE has transmitted
				   to its peer an Application Connection message with the A-bit set
				   to 1, and is awaiting the peer's response

				   -OPERATIONAL: This state indicates that the Application Connection is
				   operational."
			REFERENCE
				"draft-ietf-pwe3-iccp-16.txt
				4.4.2. Application Connection State Machine"
			SYNTAX INTEGER
				{
				nonExistent(0),
				reset(1),
				connSent(2),
				connRecv(3),
				connecting(4),
				operational(5)
				}


--
-- Node definitions
--

		-- 1.3.6.1.4.1.6926
		oaccess OBJECT IDENTIFIER ::= { enterprises 6926 }


		-- 1.3.6.1.4.1.6926.2
		oaOptiSwitch OBJECT IDENTIFIER ::= { oaccess 2 }


		-- 1.3.6.1.4.1.6926.2.29.0
		osPwe3IccpNotifications OBJECT IDENTIFIER ::= { osPwe3Iccp 0 }


		-- 1.3.6.1.4.1.6926.2.29.0.1
		osPwe3IccpRGUp NOTIFICATION-TYPE
			OBJECTS { osPwe3IccpRGStatus }
			STATUS current
			DESCRIPTION
				"osPwe3IccpRGStatus becomes operational(5)."
			::= { osPwe3IccpNotifications 1 }


		-- 1.3.6.1.4.1.6926.2.29.0.2
		osPwe3IccpRGDown NOTIFICATION-TYPE
			OBJECTS { osPwe3IccpRGStatus }
			STATUS current
			DESCRIPTION
				"osPwe3IccpRGStatus changed from operational(5) to any other state."
			::= { osPwe3IccpNotifications 2 }


		-- 1.3.6.1.4.1.6926.2.29.0.3
		osPwe3IccpMlacpUp NOTIFICATION-TYPE
			OBJECTS { osPwe3IccpMlacpStatus }
			STATUS current
			DESCRIPTION
				"osPwe3IccpMlacpStatus becomes operational(5)."
			::= { osPwe3IccpNotifications 3 }


		-- 1.3.6.1.4.1.6926.2.29.0.4
		osPwe3IccpMlacpDown NOTIFICATION-TYPE
			OBJECTS { osPwe3IccpMlacpStatus }
			STATUS current
			DESCRIPTION
				"osPwe3IccpMlacpStatus changed from operational(5) to any other state."
			::= { osPwe3IccpNotifications 4 }

        -- 1.3.6.1.4.1.6926.2.29.0.5
		osPwe3IccpMlacpAggChange NOTIFICATION-TYPE
			OBJECTS { osPwe3IccpMlacpAggActiveRole, osPwe3IccpMlacpAggSwCause }
			STATUS current
			DESCRIPTION
				"osPwe3IccpMlacpAggActiveRole changed."
			::= { osPwe3IccpNotifications 5 }




		-- 1.3.6.1.4.1.6926.2.29.1
		osPwe3IccpObjects OBJECT IDENTIFIER ::= { osPwe3Iccp 1 }


		-- 1.3.6.1.4.1.6926.2.29.1.1
		osPwe3IccpGen OBJECT IDENTIFIER ::= { osPwe3IccpObjects 1 }


		-- 1.3.6.1.4.1.6926.2.29.1.1.1
		osPwe3IccpSupport OBJECT-TYPE
			SYNTAX INTEGER
				{
				notSupported(1),
				supported(2)
				}
			MAX-ACCESS read-only
			STATUS current
			DESCRIPTION
				"Indicates that this MIB is supported"
			::= { osPwe3IccpGen 1 }


		-- 1.3.6.1.4.1.6926.2.29.1.2
		osPwe3IccpRGTable OBJECT-TYPE
			SYNTAX SEQUENCE OF OsPwe3IccpRGEntry
			MAX-ACCESS not-accessible
			STATUS current
			DESCRIPTION
				"Table of ICCP Redundancy Groups"
			::= { osPwe3IccpObjects 2 }


		-- 1.3.6.1.4.1.6926.2.29.1.2.1
		osPwe3IccpRGEntry OBJECT-TYPE
			SYNTAX OsPwe3IccpRGEntry
			MAX-ACCESS not-accessible
			STATUS current
			DESCRIPTION
				"ICCP Redundancy Group Entry"
			INDEX { osPwe3IccpRGIndex }
			::= { osPwe3IccpRGTable 1 }

		OsPwe3IccpRGEntry ::=
			SEQUENCE {
				osPwe3IccpRGIndex
					Unsigned32,
				osPwe3IccpRGSenderName
					DisplayString,
               osPwe3IccpRGPeerAddrType
                    InetAddressType,
				osPwe3IccpRGPeerAddr
					InetAddress,
				osPwe3IccpRGStatus
					IccpStatus,
                osPwe3IccpRGBfdRef
                    BfdStatus,
                osPwe3IccpRGLastError
                    DisplayString,
				osPwe3IccpRGRowStatus
					RowStatus
			 }

		-- 1.3.6.1.4.1.6926.2.29.1.2.1.1
		osPwe3IccpRGIndex OBJECT-TYPE
			SYNTAX Unsigned32 (1..65535)
			MAX-ACCESS not-accessible
			STATUS current
			DESCRIPTION
				"ICCP Redundancy Group Index (must be the same as define in the peer node)"
			::= { osPwe3IccpRGEntry 1 }


		-- 1.3.6.1.4.1.6926.2.29.1.2.1.2
		osPwe3IccpRGSenderName OBJECT-TYPE
			SYNTAX DisplayString (SIZE (0..80))
			MAX-ACCESS read-write
			STATUS current
			DESCRIPTION
				"The name of the node to be advertise by the ICCP protocol"
			REFERENCE
				"draft-ietf-pwe3-iccp-16.txt
				6.2.1. ICC Sender Name TLV"
            DEFVAL { "" }
			::= { osPwe3IccpRGEntry 2 }


		-- 1.3.6.1.4.1.6926.2.29.1.2.1.3
        osPwe3IccpRGPeerAddrType OBJECT-TYPE
			SYNTAX InetAddressType
			MAX-ACCESS read-write
			STATUS current
			DESCRIPTION
				"Peer node IP address type for establishment of RG"
            DEFVAL { ipv4 }
			::= { osPwe3IccpRGEntry 3 }

		-- 1.3.6.1.4.1.6926.2.29.1.2.1.4
		osPwe3IccpRGPeerAddr OBJECT-TYPE
			SYNTAX InetAddress
			MAX-ACCESS read-write
			STATUS current
			DESCRIPTION
				"Peer node IP address for establishment of RG"
            DEFVAL { '00000000'H }
			::= { osPwe3IccpRGEntry 4 }


		-- 1.3.6.1.4.1.6926.2.29.1.2.1.5
		osPwe3IccpRGStatus OBJECT-TYPE
			SYNTAX IccpStatus
			MAX-ACCESS read-only
			STATUS current
			DESCRIPTION
				"   -NON EXISTENT: This state is the starting point for the state
				   machine.It indicates that no ICCP connection exists and that
				   there's no LDP session established between the PEs.

				   -INITIALIZED: This state indicates that an LDP session exists between
				   the PEs but LDP ICCP Capabilitiy have not yet been exchanged between
				   them.

				   -CAPSENT: This state indicates that an LDP session exists between the
				   PEs and that the local PE has avertized LDP ICCP Capability to its
				   peer.

				   -CAPREC: This state indicates that an LDP session exists between the
				   PEs and that the local PE has both received and avertized LDP ICCP
				   Capability from/to its peer.

				   -CONNECTING: This state indicates that the local PE has initiated
				   an ICCP connection to its peer, and is awaiting its response.

				   -OPERATIONAL: This state indicates that the ICCP connection is
				   operational."
			REFERENCE
				"draft-ietf-pwe3-iccp-16.txt
				4.2.1. ICCP Connection State Machine"
			::= { osPwe3IccpRGEntry 5 }

		-- 1.3.6.1.4.1.6926.2.29.1.2.1.6
        osPwe3IccpRGBfdRef OBJECT-TYPE
			SYNTAX BfdStatus
			MAX-ACCESS read-write
			STATUS current
			DESCRIPTION
                "Reference index to BFD session monitoring the connectivity with the peer node.
				CLI command : liveliness bfd"
			DEFVAL { 0 }
			::= { osPwe3IccpRGEntry 6 }

        -- 1.3.6.1.4.1.6926.2.29.1.3.1.89
        osPwe3IccpRGLastError OBJECT-TYPE
            SYNTAX           DisplayString (SIZE (0..160))
            MAX-ACCESS       read-only
            STATUS           current
            DESCRIPTION
               "Last configuration error description."
			::= { osPwe3IccpRGEntry 89 }



		-- 1.3.6.1.4.1.6926.2.29.1.2.1.90
		osPwe3IccpRGRowStatus OBJECT-TYPE
			SYNTAX RowStatus
			MAX-ACCESS read-write
			STATUS current
			DESCRIPTION
				"Description."
            DEFVAL { notInService }
			::= { osPwe3IccpRGEntry 90 }


		-- 1.3.6.1.4.1.6926.2.29.1.3
		osPwe3IccpMlacpAppTable OBJECT-TYPE
			SYNTAX SEQUENCE OF OsPwe3IccpMlacpAppEntry
			MAX-ACCESS not-accessible
			STATUS current
			DESCRIPTION
				"Description."
			::= { osPwe3IccpObjects 3 }


		-- 1.3.6.1.4.1.6926.2.29.1.3.1
		osPwe3IccpMlacpAppEntry OBJECT-TYPE
			SYNTAX OsPwe3IccpMlacpAppEntry
			MAX-ACCESS not-accessible
			STATUS current
			DESCRIPTION
				"Description."
			INDEX { osPwe3IccpMlacpIndex }
			::= { osPwe3IccpMlacpAppTable 1 }


		OsPwe3IccpMlacpAppEntry ::=
			SEQUENCE {
				osPwe3IccpMlacpIndex
					Unsigned32,
				osPwe3IccpMlacpChassisId
					Unsigned32,
				osPwe3IccpMlacpSystemMac
					MacAddress,
				osPwe3IccpMlacpSystemPriority
					Unsigned32,
                osPwe3IccpMlacpLastError
                    DisplayString,
				osPwe3IccpMlacpStatus
					MlacpStatus,
				osPwe3IccpMlacpRowStatus
					RowStatus
			 }

		-- 1.3.6.1.4.1.6926.2.29.1.3.1.1
		osPwe3IccpMlacpIndex OBJECT-TYPE
			SYNTAX Unsigned32 (1..65535)
			MAX-ACCESS not-accessible
			STATUS current
			DESCRIPTION
				"Index of the mlacp application instance, must be equal to the ICCP RG index (osPwe3IccpRGIndex) to be used."
			::= { osPwe3IccpMlacpAppEntry 1 }


		-- 1.3.6.1.4.1.6926.2.29.1.3.1.2
		osPwe3IccpMlacpChassisId OBJECT-TYPE
			SYNTAX Unsigned32 (0..65535)
			MAX-ACCESS read-write
			STATUS current
			DESCRIPTION
				"Chassis ID to be published by LACP of the trunk conencted to the mlacp"
			::= { osPwe3IccpMlacpAppEntry 2 }


		-- 1.3.6.1.4.1.6926.2.29.1.3.1.3
		osPwe3IccpMlacpSystemMac OBJECT-TYPE
			SYNTAX MacAddress
			MAX-ACCESS read-write
			STATUS current
			DESCRIPTION
				"Assigns the common System MAC to be used for MC-LAG"
            DEFVAL { '000000000000'H }
			::= { osPwe3IccpMlacpAppEntry 3 }


		-- 1.3.6.1.4.1.6926.2.29.1.3.1.4
		osPwe3IccpMlacpSystemPriority OBJECT-TYPE
			SYNTAX Unsigned32 (1..65535)
			MAX-ACCESS read-write
			STATUS current
			DESCRIPTION
				"Assigns the system Priority as defined by LACP"
			REFERENCE
				"802.1AX section 5.3.2"
			DEFVAL { 32768 }
			::= { osPwe3IccpMlacpAppEntry 4 }

		-- 1.3.6.1.4.1.6926.2.29.1.3.1.5
        osPwe3IccpMlacpLastError OBJECT-TYPE
            SYNTAX           DisplayString (SIZE (0..160))
            MAX-ACCESS       read-only
            STATUS           current
            DESCRIPTION
               "Last configuration error description."
			::= { osPwe3IccpMlacpAppEntry 5 }

		-- 1.3.6.1.4.1.6926.2.29.1.3.1.6
		osPwe3IccpMlacpStatus OBJECT-TYPE
			SYNTAX MlacpStatus
			MAX-ACCESS read-only
			STATUS current
			DESCRIPTION
				"mlacp session status"
			REFERENCE
				"draft-ietf-pwe3-iccp-16.txt
				4.4.2. Application Connection State Machine"
			::= { osPwe3IccpMlacpAppEntry 6 }


		-- 1.3.6.1.4.1.6926.2.29.1.3.1.7
		osPwe3IccpMlacpRowStatus OBJECT-TYPE
			SYNTAX RowStatus
			MAX-ACCESS read-write
			STATUS current
			DESCRIPTION
				"Description."
            DEFVAL { notInService }
			::= { osPwe3IccpMlacpAppEntry 7 }


		-- 1.3.6.1.4.1.6926.2.29.1.4
		osPwe3IccpMlacpAggTable OBJECT-TYPE
			SYNTAX SEQUENCE OF OsPwe3IccpMlacpAggEntry
			MAX-ACCESS not-accessible
			STATUS current
			DESCRIPTION
				"Table of mlacp aggregators"
			::= { osPwe3IccpObjects 4 }


		-- 1.3.6.1.4.1.6926.2.29.1.4.1
		osPwe3IccpMlacpAggEntry OBJECT-TYPE
			SYNTAX OsPwe3IccpMlacpAggEntry
			MAX-ACCESS not-accessible
			STATUS current
			DESCRIPTION
				"Description."
			INDEX { osPwe3IccpMlacpAggIndex }
			::= { osPwe3IccpMlacpAggTable 1 }


		OsPwe3IccpMlacpAggEntry ::=
			SEQUENCE {
				osPwe3IccpMlacpAggIndex
					Unsigned32,
				osPwe3IccpMlacpAggIccpIndex
					Unsigned32,
				osPwe3IccpMlacpAggMode
					INTEGER,
				osPwe3IccpMlacpAggRole
					INTEGER,
				osPwe3IccpMlacpAggActiveRole
					INTEGER,
				osPwe3IccpMlacpAggRevertive
					Integer32,
				osPwe3IccpMlacpAggThreshold
					Integer32,
                osPwe3IccpMlacpAggCommand
                    INTEGER,
                osPwe3IccpMlacpAggSwCause
                    INTEGER,
                osPwe3IccpMlacpAggLastError
                    DisplayString,
				osPwe3IccpMlacpAggRowStatus
					RowStatus
			 }

		-- 1.3.6.1.4.1.6926.2.29.1.4.1.1
		osPwe3IccpMlacpAggIndex OBJECT-TYPE
			SYNTAX Unsigned32 (1..128)
			MAX-ACCESS not-accessible
			STATUS current
			DESCRIPTION
				"mlacp Aggregator ID - must be the same index as the trunk index (osPortTrunkId) defined in osPortTrunkTable"
			::= { osPwe3IccpMlacpAggEntry 1 }


		-- 1.3.6.1.4.1.6926.2.29.1.4.1.2
		osPwe3IccpMlacpAggIccpIndex OBJECT-TYPE
			SYNTAX Unsigned32 (0|1..65535)
			MAX-ACCESS read-write
			STATUS current
			DESCRIPTION
				"ICCP RG index - osPwe3IccpRGIndex"
			DEFVAL { 0 }
			::= { osPwe3IccpMlacpAggEntry 2 }


		-- 1.3.6.1.4.1.6926.2.29.1.4.1.3
		osPwe3IccpMlacpAggMode OBJECT-TYPE
			SYNTAX INTEGER
				{
                undefined    (0),
				activeStandby(1),
				activeActive (2)
				}
			MAX-ACCESS read-write
			STATUS current
			DESCRIPTION
				"mlacp mode as either active-standby or active-active
				first release does not support active-active"
			DEFVAL { undefined }
			::= { osPwe3IccpMlacpAggEntry 3 }


		-- 1.3.6.1.4.1.6926.2.29.1.4.1.4
		osPwe3IccpMlacpAggRole OBJECT-TYPE
			SYNTAX INTEGER
				{
                undefined (0),
				active    (1),
				standby   (2)
				}
			MAX-ACCESS read-write
			STATUS current
			DESCRIPTION
				"Define the node default mode as either active or standby"
			DEFVAL { undefined }
			::= { osPwe3IccpMlacpAggEntry 4 }


		-- 1.3.6.1.4.1.6926.2.29.1.4.1.5
		osPwe3IccpMlacpAggActiveRole OBJECT-TYPE
			SYNTAX INTEGER
				{
                undefined (0),
				active(1),
				standby(2)
				}
			MAX-ACCESS read-only
			STATUS current
			DESCRIPTION
				"Retrieve the node current mode as either active or standby"
			::= { osPwe3IccpMlacpAggEntry 5 }


		-- 1.3.6.1.4.1.6926.2.29.1.4.1.6
		osPwe3IccpMlacpAggRevertive OBJECT-TYPE
			SYNTAX Integer32 (-1..3600)
			MAX-ACCESS read-write
			STATUS current
			DESCRIPTION
				"Enables revertive switchover and configures the holdoff timer
				-1 - Non Revertive
				0-3600 - Revertive, time in seconds"
            DEFVAL { -1 }
			::= { osPwe3IccpMlacpAggEntry 6 }


		-- 1.3.6.1.4.1.6926.2.29.1.4.1.7
		osPwe3IccpMlacpAggThreshold OBJECT-TYPE
			SYNTAX Integer32 (0..100)
			UNITS "Precentage"
			MAX-ACCESS read-write
			STATUS current
			DESCRIPTION
				"Define the prectage of links in the trunk to initiate a failover:
				i.e. if the trunk has 4 links and the value is set to 50,
				only when more than 2 links will fail it will trigger the switching to the other RG PE to become active"
			::= { osPwe3IccpMlacpAggEntry 7 }

        -- 1.3.6.1.4.1.6926.2.29.1.4.1.8
		osPwe3IccpMlacpAggCommand OBJECT-TYPE
			SYNTAX INTEGER
				{
				none(1),                -- "no force-switch"
				forceSwitch(2),         -- "force-switch"
				revertSwitch(3)         -- "manual-revert"
				}
			MAX-ACCESS read-write
			STATUS current
			DESCRIPTION
				"This object manual controls the behavior of the aggergator,
				The command will be accepted only when mlacp-aggr is configured as osPwe3IccpMlacpAggRole active(1)

				 none -         normal operation of the mlacp-aggr
				 forceSwitch -  Force traffic to move away from the active node
				                as if there is a failure, traffic will not revert to the active
				                node as long as this command is set
				 revertSwitch - Revert back to Active node
				                Post failure-recovery the expected behavior is to revert back to the active node
				                The revert will happen after the timer has expired
				                To manualy switch back to the active node (in case of non-revert or before
				                revert time has expired) issue this command.
				                The value will be automatically set back to none(1) by
				                the device upon execution of the revert command."
			DEFVAL { none }
			::= { osPwe3IccpMlacpAggEntry 8 }

		-- 1.3.6.1.4.1.6926.2.29.1.3.1.9
        osPwe3IccpMlacpAggSwCause OBJECT-TYPE
            SYNTAX           INTEGER {
                               undefined (0),
                               local     (1),
                               remote    (2),
                               acFail    (3),
                               force     (4),
                               reverting (5)
                             }
            MAX-ACCESS       read-only
            STATUS           current
            DESCRIPTION
               "The cause of the last switchower."
			::= { osPwe3IccpMlacpAggEntry 9 }

		-- 1.3.6.1.4.1.6926.2.29.1.3.1.89
        osPwe3IccpMlacpAggLastError OBJECT-TYPE
            SYNTAX           DisplayString (SIZE (0..160))
            MAX-ACCESS       read-only
            STATUS           current
            DESCRIPTION
               "Last configuration error description."
			::= { osPwe3IccpMlacpAggEntry 89 }


		-- 1.3.6.1.4.1.6926.2.29.1.4.1.90
		osPwe3IccpMlacpAggRowStatus OBJECT-TYPE
			SYNTAX           RowStatus
			MAX-ACCESS       read-write
			STATUS           current
			DESCRIPTION
				"Description."
            DEFVAL { notInService }
			::= { osPwe3IccpMlacpAggEntry 90 }


		-- 1.3.6.1.4.1.6926.2.29.2
		osPwe3IccpConf OBJECT IDENTIFIER ::= { osPwe3Iccp 2 }


		-- 1.3.6.1.4.1.6926.2.29.2.1
		osPwe3IccpGroups OBJECT IDENTIFIER ::= { osPwe3IccpConf 1 }


		-- 1.3.6.1.4.1.6926.2.29.2.1.1
		osPwe3IccpNotificationGroup NOTIFICATION-GROUP
			NOTIFICATIONS { osPwe3IccpRGUp, osPwe3IccpRGDown, osPwe3IccpMlacpUp, osPwe3IccpMlacpDown, osPwe3IccpMlacpAggChange }
			STATUS current
			DESCRIPTION
				"Description."
			::= { osPwe3IccpGroups 1 }


		-- 1.3.6.1.4.1.6926.2.29.2.1.2
		osPwe3IccpGenGroup OBJECT-GROUP
			OBJECTS { osPwe3IccpSupport }
			STATUS current
			DESCRIPTION
				"Description."
			::= { osPwe3IccpGroups 2 }


		-- 1.3.6.1.4.1.6926.2.29.2.1.3
		osPwe3IccpRGGroup OBJECT-GROUP
			OBJECTS { osPwe3IccpRGSenderName, osPwe3IccpRGPeerAddrType, osPwe3IccpRGPeerAddr,
                      osPwe3IccpRGStatus, osPwe3IccpRGBfdRef,
                      osPwe3IccpRGLastError, osPwe3IccpRGRowStatus }
			STATUS current
			DESCRIPTION
				"1st revision of MRV Redundancy MIB"
			::= { osPwe3IccpGroups 3 }


		-- 1.3.6.1.4.1.6926.2.29.2.1.4
		osPwe3IccpMlacpAggGroup OBJECT-GROUP
			OBJECTS { osPwe3IccpMlacpAggIccpIndex, osPwe3IccpMlacpAggMode, osPwe3IccpMlacpAggRevertive,
                      osPwe3IccpMlacpAggRowStatus, osPwe3IccpMlacpAggThreshold, osPwe3IccpMlacpAggCommand,
				      osPwe3IccpMlacpAggRole, osPwe3IccpMlacpAggActiveRole, osPwe3IccpMlacpAggSwCause, osPwe3IccpMlacpAggLastError }
			STATUS current
			DESCRIPTION
				"Description."
			::= { osPwe3IccpGroups 4 }


		-- 1.3.6.1.4.1.6926.2.29.2.1.5
		osPwe3IccpMlacpAppGroup OBJECT-GROUP
			OBJECTS { osPwe3IccpMlacpChassisId, osPwe3IccpMlacpSystemMac, osPwe3IccpMlacpSystemPriority,
                      osPwe3IccpMlacpLastError, osPwe3IccpMlacpStatus, osPwe3IccpMlacpRowStatus
				 }
			STATUS current
			DESCRIPTION
				"Description."
			::= { osPwe3IccpGroups 5 }


		-- 1.3.6.1.4.1.6926.2.29.2.2
		osPwe3IccpCompliances OBJECT IDENTIFIER ::= { osPwe3IccpConf 2 }


		-- 1.3.6.1.4.1.6926.2.29.2.2.1
		osPwe3IccpModuleCompliance MODULE-COMPLIANCE
			STATUS current
			DESCRIPTION
				"Description."
			MODULE -- this module
				MANDATORY-GROUPS { osPwe3IccpGenGroup, osPwe3IccpRGGroup, osPwe3IccpMlacpAggGroup, osPwe3IccpMlacpAppGroup, osPwe3IccpNotificationGroup
					 }
			::= { osPwe3IccpCompliances 1 }



	END
