--
-- Copyright (C) 2000-2005 Webscreen Technology Ltd
-- Copyright (C) 2005-2013 Webscreen Systems Ltd
-- Copyright (C) 2013-2014 Juniper Networks, Inc.
--
-- For a manager to use it, it must be copied to /usr/share/snmp/mibs as
-- DDOSSECURE4-MIB.txt
-- and MIBS must be defined as "+DDOSSECURE4-MIB" in the environment

-- * ddossecure4

DDOSSECURE4-MIB DEFINITIONS ::= BEGIN

IMPORTS
    MODULE-IDENTITY, OBJECT-TYPE, OBJECT-IDENTITY, NOTIFICATION-TYPE,
    enterprises, Gauge32, IpAddress, Integer32, Counter32, Counter64
        FROM SNMPv2-SMI

    TEXTUAL-CONVENTION, DisplayString,
    TruthValue, TimeInterval, DateAndTime
        FROM SNMPv2-TC

    MODULE-COMPLIANCE, OBJECT-GROUP, NOTIFICATION-GROUP
        FROM SNMPv2-CONF

    InetAddress, InetAddressType
        FROM INET-ADDRESS-MIB;

ddossecure4MIB MODULE-IDENTITY
    LAST-UPDATED
        "201404250000Z"  -- April 25, 2014
    ORGANIZATION
        "Juniper Networks, Inc."
    CONTACT-INFO
	"postal:     Juniper Technical Assistance Center
	             Juniper Networks, Inc.
	             1194 N. Mathilda Avenue
	             Sunnyvale, CA 94089
	             USA
	 email:      support@juniper.net"
    DESCRIPTION
        "The DDoS Secure MIB version 4."
    REVISION
        "201404250000Z"  -- April 25, 2014
    DESCRIPTION
        "Update variable names to reflect current naming"
    REVISION
        "201311010000Z"  -- November 01, 2013
    DESCRIPTION
        "We are now Juniper.  Replace Webscreen with DDoS Secure as appropriate"
    REVISION
        "201202170000Z"  -- February 17, 2012
    DESCRIPTION
        "Fix confusion over bits and bytes."
    REVISION
        "201109260000Z"  -- September 26, 2011
    DESCRIPTION
        "Current revision for code releases 3.2.4-2 / 4.0.2-2 or later.
         Support for ipv4 and ipv6.
         Complete tree re-organization.
         This MIB replaces version 3."
    ::= { enterprises webscreen-technology(11068) products(1) 4 }

jddsAppliance OBJECT IDENTIFIER ::= { ddossecure4MIB 4 }

jddsPortal OBJECT IDENTIFIER ::= { ddossecure4MIB 5 }

jddsProtected OBJECT IDENTIFIER ::= { ddossecure4MIB 6 }

jddsGatewayInternet OBJECT IDENTIFIER ::= { ddossecure4MIB 7 }

jddsGatewayProtected  OBJECT IDENTIFIER ::= { ddossecure4MIB 8 }

DefenseType ::= TEXTUAL-CONVENTION
    STATUS      current
    DESCRIPTION
       "Type of Attack"
    SYNTAX INTEGER {
	bandWidth(1),
	flood(2),
	blockedProtocol(3),
	blockedState(4),
	ipAttack(5),
	tcpAttack(6),
	udpAttack(7),
	icmpAttack(8),
	otherIpAttack(9),
	fragmentAttack(10),
	badIpPacket(11),
	badTcpPacket(12),
	badUdpPacket(13),
	badIcmpPacket(14),
	badOtherIpPacket(15),
	overloadedProtectedIP(16)
	}

Direction ::= TEXTUAL-CONVENTION
    STATUS      current
    DESCRIPTION
       "Packet direction"
    SYNTAX INTEGER {
	outbound(1),
	inbound(2)
	}

LocalIndex ::= TEXTUAL-CONVENTION
    DISPLAY-HINT "d"
    STATUS       current
    DESCRIPTION
            "A unique value, greater than zero, for each entry."
    SYNTAX       Integer32 (1..2147483647)


-- ### Appliance settings ###


apConfig OBJECT IDENTIFIER ::= { jddsAppliance 1 }


apInterfaces OBJECT IDENTIFIER ::= { apConfig 1 }


apManagement OBJECT IDENTIFIER ::= { apInterfaces 1 }

apMgmtIfIpAddress OBJECT-TYPE
    SYNTAX      IpAddress
    MAX-ACCESS  read-only
    STATUS      current
    DESCRIPTION
        "IP address of the appliance management interface"
    ::= { apManagement 1 }

apMgmtIfNetmask OBJECT-TYPE
    SYNTAX      IpAddress
    MAX-ACCESS  read-only
    STATUS      current
    DESCRIPTION
        "Netmask of the appliance management interface"
    ::= { apManagement 2 }

apMgmtIfGwIpAddress OBJECT-TYPE
    SYNTAX      IpAddress
    MAX-ACCESS  read-only
    STATUS      current
    DESCRIPTION
        "Gateway IP address of the appliance management interface"
    ::= { apManagement 3 }

apMgmtIfLinkMode OBJECT-TYPE
    SYNTAX      DisplayString
    MAX-ACCESS  read-only
    STATUS      current
    DESCRIPTION
        "Speed and duplex of the appliance management interface"
    ::= { apManagement 4 }

apMgmtIfLinkFC OBJECT-TYPE
    SYNTAX      DisplayString
    MAX-ACCESS  read-only
    STATUS      current
    DESCRIPTION
        "Flow Control configuration of the appliance management interface"
    ::= { apManagement 5 }

apMgmtIfName OBJECT-TYPE
    SYNTAX      DisplayString
    MAX-ACCESS  read-only
    STATUS      current
    DESCRIPTION
        "Underlying interface name of the appliance management interface"
    ::= { apManagement 6 }


apInternet OBJECT IDENTIFIER ::= { apInterfaces 2 }

apIntIfLinkMode OBJECT-TYPE
    SYNTAX      DisplayString
    MAX-ACCESS  read-only
    STATUS      current
    DESCRIPTION
        "Speed and duplex of the appliance internet interface"
    ::= { apInternet 1 }

apIntIfLinkFC OBJECT-TYPE
    SYNTAX      DisplayString
    MAX-ACCESS  read-only
    STATUS      current
    DESCRIPTION
        "Flow Control configuration of the appliance internet interface"
    ::= { apInternet 2 }

apIntIfName OBJECT-TYPE
    SYNTAX      DisplayString
    MAX-ACCESS  read-only
    STATUS      current
    DESCRIPTION
        "Underlying interface name(s) of the appliance internet interface"
    ::= { apInternet 3 }


apProtectedInterface OBJECT IDENTIFIER ::= { apInterfaces 3 }

apProtIfLinkMode OBJECT-TYPE
    SYNTAX      DisplayString
    MAX-ACCESS  read-only
    STATUS      current
    DESCRIPTION
        "Speed and duplex of the appliance Protected Interface"
    ::= { apProtectedInterface 1 }

apProtIfLinkFC OBJECT-TYPE
    SYNTAX      DisplayString
    MAX-ACCESS  read-only
    STATUS      current
    DESCRIPTION
        "Flow Control configuration of the appliance Protected Interface"
    ::= { apProtectedInterface 2 }

apProtIfName OBJECT-TYPE
    SYNTAX      DisplayString
    MAX-ACCESS  read-only
    STATUS      current
    DESCRIPTION
        "Underlying interface name(s) of the appliance Protected Interface"
    ::= { apProtectedInterface 3 }


apDataShare OBJECT IDENTIFIER ::= { apInterfaces 4 }

apDataIfIpAddress OBJECT-TYPE
    SYNTAX      IpAddress
    MAX-ACCESS  read-only
    STATUS      current
    DESCRIPTION
        "IP address of the appliance data share interface"
    ::= { apDataShare 1 }

apDataIfNetmask OBJECT-TYPE
    SYNTAX      IpAddress
    MAX-ACCESS  read-only
    STATUS      current
    DESCRIPTION
        "Netmask of the appliance data share interface"
    ::= { apDataShare 2 }

apDataIfLinkMode OBJECT-TYPE
    SYNTAX      DisplayString
    MAX-ACCESS  read-only
    STATUS      current
    DESCRIPTION
        "Speed and duplex of the appliance data share interface"
    ::= { apDataShare 3 }

apDataIfLinkFC OBJECT-TYPE
    SYNTAX      DisplayString
    MAX-ACCESS  read-only
    STATUS      current
    DESCRIPTION
        "Flow Control configuration of the appliance data share interface"
    ::= { apDataShare 4 }

apDataIfName OBJECT-TYPE
    SYNTAX      DisplayString
    MAX-ACCESS  read-only
    STATUS      current
    DESCRIPTION
        "Underlying interface name of the appliance data share interface"
    ::= { apDataShare 5 }


-- ****         apAccess


apAccess OBJECT IDENTIFIER ::= { apConfig 2 }

apUserTable OBJECT-TYPE
    SYNTAX SEQUENCE OF ApUserEntry
    MAX-ACCESS  not-accessible
    STATUS      current
    DESCRIPTION
        "Table of user entries with permission on appliance"
    ::= { apAccess 1 }

apUserEntry OBJECT-TYPE
    SYNTAX      ApUserEntry
    MAX-ACCESS  not-accessible
    STATUS      current
    DESCRIPTION
        "A row consisting of a record for a particular user"
    INDEX { apUserId }
    ::= { apUserTable 1 }

ApUserEntry ::= SEQUENCE {
    apUserId              LocalIndex,
    apUserName            DisplayString,
    apUserPermissions     DisplayString
}

apUserId OBJECT-TYPE
    SYNTAX      LocalIndex
    MAX-ACCESS	not-accessible
    STATUS      current
    DESCRIPTION
        "Unique ID number for this user"
    ::= { apUserEntry 1 }

apUserName OBJECT-TYPE
    SYNTAX      DisplayString
    MAX-ACCESS  read-only
    STATUS      current
    DESCRIPTION
        "The name associated with this user"
    ::= { apUserEntry 2 }

apUserPermissions OBJECT-TYPE
    SYNTAX      DisplayString
    MAX-ACCESS  read-only
    STATUS      current
    DESCRIPTION
        "The permissions associated with this user"
    ::= { apUserEntry 3 }

-- *****            snmp

apSnmpAccessIpList OBJECT-TYPE
    SYNTAX      DisplayString
    MAX-ACCESS  read-only
    STATUS      current
    DESCRIPTION
        "Comma-separated list of IP addresses allowed to make SNMP queries"
    ::= { apAccess 3 }

apHttpsAccessIpList OBJECT-TYPE
    SYNTAX      DisplayString
    MAX-ACCESS  read-only
    STATUS      current
    DESCRIPTION
        "Comma-separated list of IP addresses allowed to connect via HTTPS"
    ::= { apAccess 4 }

apSshAccessIpList OBJECT-TYPE
    SYNTAX      DisplayString
    MAX-ACCESS  read-only
    STATUS      current
    DESCRIPTION
        "Comma-separated list of IP addresses allowed to connect via SSH"
    ::= { apAccess 5 }


apLogging OBJECT IDENTIFIER ::= { apConfig 3 }

apSyslogServer OBJECT-TYPE
    SYNTAX      DisplayString
    MAX-ACCESS  read-only
    STATUS      current
    DESCRIPTION
        "ASCII comma-separated list of IP addresses to receive remote syslog for appliance logs"
    ::= { apLogging 1 }

apSyslogFacility OBJECT-TYPE
    SYNTAX      DisplayString
    MAX-ACCESS  read-only
    STATUS      current
    DESCRIPTION
        "Syslog facility name for appliance logs"
    ::= { apLogging 2 }

apSyslogPriority OBJECT-TYPE
    SYNTAX      DisplayString
    MAX-ACCESS  read-only
    STATUS      current
    DESCRIPTION
        "Syslog priority name for appliance logs"
    ::= { apLogging 3 }

apWebtrendsServer OBJECT-TYPE
    SYNTAX      DisplayString
    MAX-ACCESS  read-only
    STATUS      current
    DESCRIPTION
        "ASCII comma-separated list of IP addresses to receive remote webtrends logs"
    ::= { apLogging 4 }

apWebtrendsFacility OBJECT-TYPE
    SYNTAX      DisplayString
    MAX-ACCESS  read-only
    STATUS      current
    DESCRIPTION
        "Webtrends facility name"
    ::= { apLogging 5 }

apWebtrendsPriority OBJECT-TYPE
    SYNTAX      DisplayString
    MAX-ACCESS  read-only
    STATUS      current
    DESCRIPTION
        "Webtrends priority name"
    ::= { apLogging 6 }


apCreateIncidentsThreshold OBJECT IDENTIFIER ::= { apLogging 7 }

apBandwidthCreateThresh OBJECT-TYPE
    SYNTAX      TruthValue
    MAX-ACCESS  read-only
    STATUS      current
    DESCRIPTION
        "Create Incident threshold enabled on/off for bandwidth defense info"
    ::= { apCreateIncidentsThreshold 1 }

apBandwidthCreateThreshRate OBJECT-TYPE
    SYNTAX      Gauge32
    MAX-ACCESS  read-only
    STATUS      current
    DESCRIPTION
        "Create Incident threshold rate for bandwidth defense info"
    ::= { apCreateIncidentsThreshold 2 }

apFloodCreateThresh OBJECT-TYPE
    SYNTAX      TruthValue
    MAX-ACCESS  read-only
    STATUS      current
    DESCRIPTION
        "Create Incident threshold enabled on/off for flood defense info"
    ::= { apCreateIncidentsThreshold 3 }

apFloodCreateThreshRate OBJECT-TYPE
    SYNTAX      Gauge32
    MAX-ACCESS  read-only
    STATUS      current
    DESCRIPTION
        "Create Incident threshold rate for flood defense info"
    ::= { apCreateIncidentsThreshold 4 }

apBlockedProtoCreateThresh OBJECT-TYPE
    SYNTAX      TruthValue
    MAX-ACCESS  read-only
    STATUS      current
    DESCRIPTION
        "Create Incident threshold enabled on/off for blocked Protocol defense info"
    ::= { apCreateIncidentsThreshold 5 }

apBlockedProtoCreateThreshRate OBJECT-TYPE
    SYNTAX      Gauge32
    MAX-ACCESS  read-only
    STATUS      current
    DESCRIPTION
        "Create Incident threshold rate for blocked Protocol defense info"
    ::= { apCreateIncidentsThreshold 6 }

apBlockedStateCreateThresh OBJECT-TYPE
    SYNTAX      TruthValue
    MAX-ACCESS  read-only
    STATUS      current
    DESCRIPTION
        "Create Incident threshold enabled on/off for blocked state defense info"
    ::= { apCreateIncidentsThreshold 7 }

apBlockedStateCreateThreshRate OBJECT-TYPE
    SYNTAX      Gauge32
    MAX-ACCESS  read-only
    STATUS      current
    DESCRIPTION
        "Create Incident threshold rate for blocked state defense info"
    ::= { apCreateIncidentsThreshold 8 }

apIpAttackCreateThresh OBJECT-TYPE
    SYNTAX      TruthValue
    MAX-ACCESS  read-only
    STATUS      current
    DESCRIPTION
        "Create Incident threshold enabled on/off for IP Attack defense info"
    ::= { apCreateIncidentsThreshold 9 }

apIpAttackCreateThreshRate OBJECT-TYPE
    SYNTAX      Gauge32
    MAX-ACCESS  read-only
    STATUS      current
    DESCRIPTION
        "Create Incident threshold rate for IP Attack defense info"
    ::= { apCreateIncidentsThreshold 10 }

apTcpAttackCreateThresh OBJECT-TYPE
    SYNTAX      TruthValue
    MAX-ACCESS  read-only
    STATUS      current
    DESCRIPTION
        "Create Incident threshold enabled on/off for TCP Attack defense info"
    ::= { apCreateIncidentsThreshold 11 }

apTcpAttackCreateThreshRate OBJECT-TYPE
    SYNTAX      Gauge32
    MAX-ACCESS  read-only
    STATUS      current
    DESCRIPTION
        "Create Incident threshold rate for TCP Attack defense info"
    ::= { apCreateIncidentsThreshold 12 }

apUdpAttackCreateThresh OBJECT-TYPE
    SYNTAX      TruthValue
    MAX-ACCESS  read-only
    STATUS      current
    DESCRIPTION
        "Create Incident threshold enabled on/off for UDP Attack defense info"
    ::= { apCreateIncidentsThreshold 13 }

apUdpAttackCreateThreshRate OBJECT-TYPE
    SYNTAX      Gauge32
    MAX-ACCESS  read-only
    STATUS      current
    DESCRIPTION
        "Create Incident threshold rate for UDP Attack defense info"
    ::= { apCreateIncidentsThreshold 14 }

apIcmpAttackCreateThresh OBJECT-TYPE
    SYNTAX      TruthValue
    MAX-ACCESS  read-only
    STATUS      current
    DESCRIPTION
        "Create Incident threshold enabled on/off for ICMP Attack defense info"
    ::= { apCreateIncidentsThreshold 15 }

apIcmpAttackCreateThreshRate OBJECT-TYPE
    SYNTAX      Gauge32
    MAX-ACCESS  read-only
    STATUS      current
    DESCRIPTION
        "Create Incident threshold rate for ICMP Attack defense info"
    ::= { apCreateIncidentsThreshold 16 }

apOtherIpAttackCreateThresh OBJECT-TYPE
    SYNTAX      TruthValue
    MAX-ACCESS  read-only
    STATUS      current
    DESCRIPTION
        "Create Incident threshold enabled on/off for other IP Attack defense info"
    ::= { apCreateIncidentsThreshold 17 }

apOtherIpAttackCreateThreshRate OBJECT-TYPE
    SYNTAX      Gauge32
    MAX-ACCESS  read-only
    STATUS      current
    DESCRIPTION
        "Create Incident threshold rate for other IP Attack defense info"
    ::= { apCreateIncidentsThreshold 18 }

apFragAttackCreateThresh OBJECT-TYPE
    SYNTAX      TruthValue
    MAX-ACCESS  read-only
    STATUS      current
    DESCRIPTION
        "Create Incident threshold enabled on/off for fragment Attack defense info"
    ::= { apCreateIncidentsThreshold 19 }

apFragAttackCreateThreshRate OBJECT-TYPE
    SYNTAX      Gauge32
    MAX-ACCESS  read-only
    STATUS      current
    DESCRIPTION
        "Create Incident threshold rate for fragment Attack defense info"
    ::= { apCreateIncidentsThreshold 20 }

apBadIpCreateThresh OBJECT-TYPE
    SYNTAX      TruthValue
    MAX-ACCESS  read-only
    STATUS      current
    DESCRIPTION
        "Create Incident threshold enabled on/off for bad IP defense info"
    ::= { apCreateIncidentsThreshold 21 }

apBadIpCreateThreshRate OBJECT-TYPE
    SYNTAX      Gauge32
    MAX-ACCESS  read-only
    STATUS      current
    DESCRIPTION
        "Create Incident threshold rate for bad IP defense info"
    ::= { apCreateIncidentsThreshold 22 }

apBadTcpCreateThresh OBJECT-TYPE
    SYNTAX      TruthValue
    MAX-ACCESS  read-only
    STATUS      current
    DESCRIPTION
        "Create Incident threshold enabled on/off for bad TCP defense info"
    ::= { apCreateIncidentsThreshold 23 }

apBadTcpCreateThreshRate OBJECT-TYPE
    SYNTAX      Gauge32
    MAX-ACCESS  read-only
    STATUS      current
    DESCRIPTION
        "Create Incident threshold rate for bad TCP defense info"
    ::= { apCreateIncidentsThreshold 24 }

apBadUdpCreateThresh OBJECT-TYPE
    SYNTAX      TruthValue
    MAX-ACCESS  read-only
    STATUS      current
    DESCRIPTION
        "Create Incident threshold enabled on/off for bad UDP defense info"
    ::= { apCreateIncidentsThreshold 25 }

apBadUdpCreateThreshRate OBJECT-TYPE
    SYNTAX      Gauge32
    MAX-ACCESS  read-only
    STATUS      current
    DESCRIPTION
        "Create Incident threshold rate for bad UDP defense info"
    ::= { apCreateIncidentsThreshold 26 }

apBadIcmpCreateThresh OBJECT-TYPE
    SYNTAX      TruthValue
    MAX-ACCESS  read-only
    STATUS      current
    DESCRIPTION
        "Create Incident threshold enabled on/off for bad ICMP defense info"
    ::= { apCreateIncidentsThreshold 27 }

apBadIcmpCreateThreshRate OBJECT-TYPE
    SYNTAX      Gauge32
    MAX-ACCESS  read-only
    STATUS      current
    DESCRIPTION
        "Create Incident threshold rate for bad ICMP defense info"
    ::= { apCreateIncidentsThreshold 28 }

apBadOtherIpCreateThresh OBJECT-TYPE
    SYNTAX      TruthValue
    MAX-ACCESS  read-only
    STATUS      current
    DESCRIPTION
        "Create Incident threshold enabled on/off for bad other IP defense info"
    ::= { apCreateIncidentsThreshold 29 }

apBadOtherIpCreateThreshRate OBJECT-TYPE
    SYNTAX      Gauge32
    MAX-ACCESS  read-only
    STATUS      current
    DESCRIPTION
        "Create Incident threshold rate for bad other IP defense info"
    ::= { apCreateIncidentsThreshold 30 }

apOverloadedIpCreateThresh OBJECT-TYPE
    SYNTAX      TruthValue
    MAX-ACCESS  read-only
    STATUS      current
    DESCRIPTION
        "Create Incident threshold enabled on/off for overloaded protected IP info"
    ::= { apCreateIncidentsThreshold 31 }

apOverloadedIpCreateThreshRate OBJECT-TYPE
    SYNTAX      Gauge32
    MAX-ACCESS  read-only
    STATUS      current
    DESCRIPTION
        "Create Incident threshold rate for overloaded protected IP info"
    ::= { apCreateIncidentsThreshold 32 }


apViewIncidentsThresholds OBJECT IDENTIFIER ::= { apLogging 8 }

apBandwidthViewThresh OBJECT-TYPE
    SYNTAX      TruthValue
    MAX-ACCESS  read-only
    STATUS      current
    DESCRIPTION
        "View Incidents threshold enabled on/off for bandwidth defense info"
    ::= { apViewIncidentsThresholds 1 }

apBandwidthViewThreshRate OBJECT-TYPE
    SYNTAX      Gauge32
    MAX-ACCESS  read-only
    STATUS      current
    DESCRIPTION
        "View Incidents threshold rate for bandwidth defense info"
    ::= { apViewIncidentsThresholds 2 }

apFloodViewThresh OBJECT-TYPE
    SYNTAX      TruthValue
    MAX-ACCESS  read-only
    STATUS      current
    DESCRIPTION
        "View Incidents threshold enabled on/off for flood defense info"
    ::= { apViewIncidentsThresholds 3 }

apFloodViewThreshRate OBJECT-TYPE
    SYNTAX      Gauge32
    MAX-ACCESS  read-only
    STATUS      current
    DESCRIPTION
        "View Incidents threshold rate for flood defense info"
    ::= { apViewIncidentsThresholds 4 }

apBlockedProtoViewThresh OBJECT-TYPE
    SYNTAX      TruthValue
    MAX-ACCESS  read-only
    STATUS      current
    DESCRIPTION
        "View Incidents threshold enabled on/off for blocked Protocol defense info"
    ::= { apViewIncidentsThresholds 5 }

apBlockedProtoViewThreshRate OBJECT-TYPE
    SYNTAX      Gauge32
    MAX-ACCESS  read-only
    STATUS      current
    DESCRIPTION
        "View Incidents threshold rate for blocked Protocol defense info"
    ::= { apViewIncidentsThresholds 6 }

apBlockedStateViewThresh OBJECT-TYPE
    SYNTAX      TruthValue
    MAX-ACCESS  read-only
    STATUS      current
    DESCRIPTION
        "View Incidents threshold enabled on/off for blocked state defense info"
    ::= { apViewIncidentsThresholds 7 }

apBlockedStateViewThreshRate OBJECT-TYPE
    SYNTAX      Gauge32
    MAX-ACCESS  read-only
    STATUS      current
    DESCRIPTION
        "View Incidents threshold rate for blocked state defense info"
    ::= { apViewIncidentsThresholds 8 }

apIpAttackViewThresh OBJECT-TYPE
    SYNTAX      TruthValue
    MAX-ACCESS  read-only
    STATUS      current
    DESCRIPTION
        "View Incidents threshold enabled on/off for IP Attack defense info"
    ::= { apViewIncidentsThresholds 9 }

apIpAttackViewThreshRate OBJECT-TYPE
    SYNTAX      Gauge32
    MAX-ACCESS  read-only
    STATUS      current
    DESCRIPTION
        "View Incidents threshold rate for IP Attack defense info"
    ::= { apViewIncidentsThresholds 10 }

apTcpAttackViewThresh OBJECT-TYPE
    SYNTAX      TruthValue
    MAX-ACCESS  read-only
    STATUS      current
    DESCRIPTION
        "View Incidents threshold enabled on/off for TCP Attack defense info"
    ::= { apViewIncidentsThresholds 11 }

apTcpAttackViewThreshRate OBJECT-TYPE
    SYNTAX      Gauge32
    MAX-ACCESS  read-only
    STATUS      current
    DESCRIPTION
        "View Incidents threshold rate for TCP Attack defense info"
    ::= { apViewIncidentsThresholds 12 }

apUdpAttackViewThresh OBJECT-TYPE
    SYNTAX      TruthValue
    MAX-ACCESS  read-only
    STATUS      current
    DESCRIPTION
        "View Incidents threshold enabled on/off for UDP Attack defense info"
    ::= { apViewIncidentsThresholds 13 }

apUdpAttackViewThreshRate OBJECT-TYPE
    SYNTAX      Gauge32
    MAX-ACCESS  read-only
    STATUS      current
    DESCRIPTION
        "View Incidents threshold rate for UDP Attack defense info"
    ::= { apViewIncidentsThresholds 14 }

apIcmpAttackViewThresh OBJECT-TYPE
    SYNTAX      TruthValue
    MAX-ACCESS  read-only
    STATUS      current
    DESCRIPTION
        "View Incidents threshold enabled on/off for ICMP Attack defense info"
    ::= { apViewIncidentsThresholds 15 }

apIcmpAttackViewThreshRate OBJECT-TYPE
    SYNTAX      Gauge32
    MAX-ACCESS  read-only
    STATUS      current
    DESCRIPTION
        "View Incidents threshold rate for ICMP Attack defense info"
    ::= { apViewIncidentsThresholds 16 }

apOtherIpAttackViewThresh OBJECT-TYPE
    SYNTAX      TruthValue
    MAX-ACCESS  read-only
    STATUS      current
    DESCRIPTION
        "View Incidents threshold enabled on/off for other IP Attack defense info"
    ::= { apViewIncidentsThresholds 17 }

apOtherIpAttackViewThreshRate OBJECT-TYPE
    SYNTAX      Gauge32
    MAX-ACCESS  read-only
    STATUS      current
    DESCRIPTION
        "View Incidents threshold rate for other IP Attack defense info"
    ::= { apViewIncidentsThresholds 18 }

apFragAttackViewThresh OBJECT-TYPE
    SYNTAX      TruthValue
    MAX-ACCESS  read-only
    STATUS      current
    DESCRIPTION
        "View Incidents threshold enabled on/off for fragment Attack defense info"
    ::= { apViewIncidentsThresholds 19 }

apFragAttackViewThreshRate OBJECT-TYPE
    SYNTAX      Gauge32
    MAX-ACCESS  read-only
    STATUS      current
    DESCRIPTION
        "View Incidents threshold rate for fragment Attack defense info"
    ::= { apViewIncidentsThresholds 20 }

apBadIpViewThresh OBJECT-TYPE
    SYNTAX      TruthValue
    MAX-ACCESS  read-only
    STATUS      current
    DESCRIPTION
        "View Incidents threshold enabled on/off for bad IP defense info"
    ::= { apViewIncidentsThresholds 21 }

apBadIpViewThreshRate OBJECT-TYPE
    SYNTAX      Gauge32
    MAX-ACCESS  read-only
    STATUS      current
    DESCRIPTION
        "View Incidents threshold rate for bad IP defense info"
    ::= { apViewIncidentsThresholds 22 }

apBadTcpViewThresh OBJECT-TYPE
    SYNTAX      TruthValue
    MAX-ACCESS  read-only
    STATUS      current
    DESCRIPTION
        "View Incidents threshold enabled on/off for bad TCP defense info"
    ::= { apViewIncidentsThresholds 23 }

apBadTcpViewThreshRate OBJECT-TYPE
    SYNTAX      Gauge32
    MAX-ACCESS  read-only
    STATUS      current
    DESCRIPTION
        "View Incidents threshold rate for bad TCP defense info"
    ::= { apViewIncidentsThresholds 24 }

apBadUdpViewThresh OBJECT-TYPE
    SYNTAX      TruthValue
    MAX-ACCESS  read-only
    STATUS      current
    DESCRIPTION
        "View Incidents threshold enabled on/off for bad UDP defense info"
    ::= { apViewIncidentsThresholds 25 }

apBadUdpViewThreshRate OBJECT-TYPE
    SYNTAX      Gauge32
    MAX-ACCESS  read-only
    STATUS      current
    DESCRIPTION
        "View Incidents threshold rate for bad UDP defense info"
    ::= { apViewIncidentsThresholds 26 }

apBadIcmpViewThresh OBJECT-TYPE
    SYNTAX      TruthValue
    MAX-ACCESS  read-only
    STATUS      current
    DESCRIPTION
        "View Incidents threshold enabled on/off for bad ICMP defense info"
    ::= { apViewIncidentsThresholds 27 }

apBadIcmpViewThreshRate OBJECT-TYPE
    SYNTAX      Gauge32
    MAX-ACCESS  read-only
    STATUS      current
    DESCRIPTION
        "View Incidents threshold rate for bad ICMP defense info"
    ::= { apViewIncidentsThresholds 28 }

apBadOtherIpViewThresh OBJECT-TYPE
    SYNTAX      TruthValue
    MAX-ACCESS  read-only
    STATUS      current
    DESCRIPTION
        "View Incidents threshold enabled on/off for bad other IP defense info"
    ::= { apViewIncidentsThresholds 29 }

apBadOtherIpViewThreshRate OBJECT-TYPE
    SYNTAX      Gauge32
    MAX-ACCESS  read-only
    STATUS      current
    DESCRIPTION
        "View Incidents threshold rate for bad other IP defense info"
    ::= { apViewIncidentsThresholds 30 }

apOverloadedIpViewThresh OBJECT-TYPE
    SYNTAX      TruthValue
    MAX-ACCESS  read-only
    STATUS      current
    DESCRIPTION
        "View Incidents threshold enabled on/off for overloaded protected IP info"
    ::= { apViewIncidentsThresholds 31 }

apOverloadedIpViewThreshRate OBJECT-TYPE
    SYNTAX      Gauge32
    MAX-ACCESS  read-only
    STATUS      current
    DESCRIPTION
        "View Incidents threshold rate for overloaded protected IP info"
    ::= { apViewIncidentsThresholds 32 }


apWOffenderLogThreshold OBJECT IDENTIFIER ::= { apLogging 9 }

apBandwidthOffThresh OBJECT-TYPE
    SYNTAX      TruthValue
    MAX-ACCESS  read-only
    STATUS      current
    DESCRIPTION
        "Worst Offenders logging threshold enabled on/off for bandwidth defense info"
    ::= { apWOffenderLogThreshold 1 }

apBandwidthOffThreshRate OBJECT-TYPE
    SYNTAX      Gauge32
    MAX-ACCESS  read-only
    STATUS      current
    DESCRIPTION
        "Worst Offenders logging threshold rate for bandwidth defense info"
    ::= { apWOffenderLogThreshold 2 }

apFloodOffThresh OBJECT-TYPE
    SYNTAX      TruthValue
    MAX-ACCESS  read-only
    STATUS      current
    DESCRIPTION
        "Worst Offenders logging threshold enabled on/off for flood defense info"
    ::= { apWOffenderLogThreshold 3 }

apFloodOffThreshRate OBJECT-TYPE
    SYNTAX      Gauge32
    MAX-ACCESS  read-only
    STATUS      current
    DESCRIPTION
        "Worst Offenders logging threshold rate for flood defense info"
    ::= { apWOffenderLogThreshold 4 }

apBlockedProtoOffThresh OBJECT-TYPE
    SYNTAX      TruthValue
    MAX-ACCESS  read-only
    STATUS      current
    DESCRIPTION
        "Worst Offenders logging threshold enabled on/off for blocked Protocol defense info"
    ::= { apWOffenderLogThreshold 5 }

apBlockedProtoOffThreshRate OBJECT-TYPE
    SYNTAX      Gauge32
    MAX-ACCESS  read-only
    STATUS      current
    DESCRIPTION
        "Worst Offenders logging threshold rate for blocked Protocol defense info"
    ::= { apWOffenderLogThreshold 6 }

apBlockedStateOffThresh OBJECT-TYPE
    SYNTAX      TruthValue
    MAX-ACCESS  read-only
    STATUS      current
    DESCRIPTION
        "Worst Offenders logging threshold enabled on/off for blocked state defense info"
    ::= { apWOffenderLogThreshold 7 }

apBlockedStateOffThreshRate OBJECT-TYPE
    SYNTAX      Gauge32
    MAX-ACCESS  read-only
    STATUS      current
    DESCRIPTION
        "Worst Offenders logging threshold rate for blocked state defense info"
    ::= { apWOffenderLogThreshold 8 }

apIpAttackOffThresh OBJECT-TYPE
    SYNTAX      TruthValue
    MAX-ACCESS  read-only
    STATUS      current
    DESCRIPTION
        "Worst Offenders logging threshold enabled on/off for IP Attack defense info"
    ::= { apWOffenderLogThreshold 9 }

apIpAttackOffThreshRate OBJECT-TYPE
    SYNTAX      Gauge32
    MAX-ACCESS  read-only
    STATUS      current
    DESCRIPTION
        "Worst Offenders logging threshold rate for IP Attack defense info"
    ::= { apWOffenderLogThreshold 10 }

apTcpAttackOffThresh OBJECT-TYPE
    SYNTAX      TruthValue
    MAX-ACCESS  read-only
    STATUS      current
    DESCRIPTION
        "Worst Offenders logging threshold enabled on/off for TCP Attack defense info"
    ::= { apWOffenderLogThreshold 11 }

apTcpAttackOffThreshRate OBJECT-TYPE
    SYNTAX      Gauge32
    MAX-ACCESS  read-only
    STATUS      current
    DESCRIPTION
        "Worst Offenders logging threshold rate for TCP Attack defense info"
    ::= { apWOffenderLogThreshold 12 }

apUdpAttackOffThresh OBJECT-TYPE
    SYNTAX      TruthValue
    MAX-ACCESS  read-only
    STATUS      current
    DESCRIPTION
        "Worst Offenders logging threshold enabled on/off for UDP Attack defense info"
    ::= { apWOffenderLogThreshold 13 }

apUdpAttackOffThreshRate OBJECT-TYPE
    SYNTAX      Gauge32
    MAX-ACCESS  read-only
    STATUS      current
    DESCRIPTION
        "Worst Offenders logging threshold rate for UDP Attack defense info"
    ::= { apWOffenderLogThreshold 14 }

apIcmpAttackOffThresh OBJECT-TYPE
    SYNTAX      TruthValue
    MAX-ACCESS  read-only
    STATUS      current
    DESCRIPTION
        "Worst Offenders logging threshold enabled on/off for ICMP Attack defense info"
    ::= { apWOffenderLogThreshold 15 }

apIcmpAttackOffThreshRate OBJECT-TYPE
    SYNTAX      Gauge32
    MAX-ACCESS  read-only
    STATUS      current
    DESCRIPTION
        "Worst Offenders logging threshold rate for ICMP Attack defense info"
    ::= { apWOffenderLogThreshold 16 }

apOtherIpAttackOffThresh OBJECT-TYPE
    SYNTAX      TruthValue
    MAX-ACCESS  read-only
    STATUS      current
    DESCRIPTION
        "Worst Offenders logging threshold enabled on/off for other IP Attack defense info"
    ::= { apWOffenderLogThreshold 17 }

apOtherIpAttackOffThreshRate OBJECT-TYPE
    SYNTAX      Gauge32
    MAX-ACCESS  read-only
    STATUS      current
    DESCRIPTION
        "Worst Offenders logging threshold rate for other IP Attack defense info"
    ::= { apWOffenderLogThreshold 18 }

apFragAttackOffThresh OBJECT-TYPE
    SYNTAX      TruthValue
    MAX-ACCESS  read-only
    STATUS      current
    DESCRIPTION
        "Worst Offenders logging threshold enabled on/off for fragment Attack defense info"
    ::= { apWOffenderLogThreshold 19 }

apFragAttackOffThreshRate OBJECT-TYPE
    SYNTAX      Gauge32
    MAX-ACCESS  read-only
    STATUS      current
    DESCRIPTION
        "Worst Offenders logging threshold rate for fragment Attack defense info"
    ::= { apWOffenderLogThreshold 20 }

apBadIpOffThresh OBJECT-TYPE
    SYNTAX      TruthValue
    MAX-ACCESS  read-only
    STATUS      current
    DESCRIPTION
        "Worst Offenders logging threshold enabled on/off for bad IP defense info"
    ::= { apWOffenderLogThreshold 21 }

apBadIpOffThreshRate OBJECT-TYPE
    SYNTAX      Gauge32
    MAX-ACCESS  read-only
    STATUS      current
    DESCRIPTION
        "Worst Offenders logging threshold rate for bad IP defense info"
    ::= { apWOffenderLogThreshold 22 }

apBadTcpOffThresh OBJECT-TYPE
    SYNTAX      TruthValue
    MAX-ACCESS  read-only
    STATUS      current
    DESCRIPTION
        "Worst Offenders logging threshold enabled on/off for bad TCP defense info"
    ::= { apWOffenderLogThreshold 23 }

apBadTcpOffThreshRate OBJECT-TYPE
    SYNTAX      Gauge32
    MAX-ACCESS  read-only
    STATUS      current
    DESCRIPTION
        "Worst Offenders logging threshold rate for bad TCP defense info"
    ::= { apWOffenderLogThreshold 24 }

apBadUdpOffThresh OBJECT-TYPE
    SYNTAX      TruthValue
    MAX-ACCESS  read-only
    STATUS      current
    DESCRIPTION
        "Worst Offenders logging threshold enabled on/off for bad UDP defense info"
    ::= { apWOffenderLogThreshold 25 }

apBadUdpOffThreshRate OBJECT-TYPE
    SYNTAX      Gauge32
    MAX-ACCESS  read-only
    STATUS      current
    DESCRIPTION
        "Worst Offenders logging threshold rate for bad UDP defense info"
    ::= { apWOffenderLogThreshold 26 }

apBadIcmpOffThresh OBJECT-TYPE
    SYNTAX      TruthValue
    MAX-ACCESS  read-only
    STATUS      current
    DESCRIPTION
        "Worst Offenders logging threshold enabled on/off for bad ICMP defense info"
    ::= { apWOffenderLogThreshold 27 }

apBadIcmpOffThreshRate OBJECT-TYPE
    SYNTAX      Gauge32
    MAX-ACCESS  read-only
    STATUS      current
    DESCRIPTION
        "Worst Offenders logging threshold rate for bad ICMP defense info"
    ::= { apWOffenderLogThreshold 28 }

apBadOtherIpOffThresh OBJECT-TYPE
    SYNTAX      TruthValue
    MAX-ACCESS  read-only
    STATUS      current
    DESCRIPTION
        "Offenders logging threshold enabled on/off for bad other IP defense info"
    ::= { apWOffenderLogThreshold 29 }

apBadOtherIpOffThreshRate OBJECT-TYPE
    SYNTAX      Gauge32
    MAX-ACCESS  read-only
    STATUS      current
    DESCRIPTION
        "Worst Offenders logging threshold rate for bad other IP defense info"
    ::= { apWOffenderLogThreshold 30 }

apOverloadedIpOffThresh OBJECT-TYPE
    SYNTAX      TruthValue
    MAX-ACCESS  read-only
    STATUS      current
    DESCRIPTION
        "Worst Offenders logging threshold enabled on/off for overloaded protected IP info"
    ::= { apWOffenderLogThreshold 31 }

apOverloadedIpOffThreshRate OBJECT-TYPE
    SYNTAX      Gauge32
    MAX-ACCESS  read-only
    STATUS      current
    DESCRIPTION
        "Worst Offenders logging threshold rate for overloaded protected IP info"
    ::= { apWOffenderLogThreshold 32 }


apIncidentAlertThreshold OBJECT IDENTIFIER ::= { apLogging 10 }

apBandwidthAlertThresh OBJECT-TYPE
    SYNTAX      TruthValue
    MAX-ACCESS  read-only
    STATUS      current
    DESCRIPTION
        "Incident Alert threshold enabled on/off for bandwidth defense info"
    ::= { apIncidentAlertThreshold 1 }

apBandwidthAlertThreshRate OBJECT-TYPE
    SYNTAX      Gauge32
    MAX-ACCESS  read-only
    STATUS      current
    DESCRIPTION
        "Incident Alert threshold rate for bandwidth defense info"
    ::= { apIncidentAlertThreshold 2 }

apFloodAlertThresh OBJECT-TYPE
    SYNTAX      TruthValue
    MAX-ACCESS  read-only
    STATUS      current
    DESCRIPTION
        "Incident Alert threshold enabled on/off for flood defense info"
    ::= { apIncidentAlertThreshold 3 }

apFloodAlertThreshRate OBJECT-TYPE
    SYNTAX      Gauge32
    MAX-ACCESS  read-only
    STATUS      current
    DESCRIPTION
        "Incident Alert threshold rate for flood defense info"
    ::= { apIncidentAlertThreshold 4 }

apBlockedProtoAlertThresh OBJECT-TYPE
    SYNTAX      TruthValue
    MAX-ACCESS  read-only
    STATUS      current
    DESCRIPTION
        "Incident Alert threshold enabled on/off for blocked Protocol defense info"
    ::= { apIncidentAlertThreshold 5 }

apBlockedProtoAlertThreshRate OBJECT-TYPE
    SYNTAX      Gauge32
    MAX-ACCESS  read-only
    STATUS      current
    DESCRIPTION
        "Incident Alert threshold rate for blocked Protocol defense info"
    ::= { apIncidentAlertThreshold 6 }

apBlockedStateAlertThresh OBJECT-TYPE
    SYNTAX      TruthValue
    MAX-ACCESS  read-only
    STATUS      current
    DESCRIPTION
        "Incident Alert threshold enabled on/off for blocked state defense info"
    ::= { apIncidentAlertThreshold 7 }

apBlockedStateAlertThreshRate OBJECT-TYPE
    SYNTAX      Gauge32
    MAX-ACCESS  read-only
    STATUS      current
    DESCRIPTION
        "Incident Alert threshold rate for blocked state defense info"
    ::= { apIncidentAlertThreshold 8 }

apIpAttackAlertThresh OBJECT-TYPE
    SYNTAX      TruthValue
    MAX-ACCESS  read-only
    STATUS      current
    DESCRIPTION
        "Incident Alert threshold enabled on/off for IP Attack defense info"
    ::= { apIncidentAlertThreshold 9 }

apIpAttackAlertThreshRate OBJECT-TYPE
    SYNTAX      Gauge32
    MAX-ACCESS  read-only
    STATUS      current
    DESCRIPTION
        "Incident Alert threshold rate for IP Attack defense info"
    ::= { apIncidentAlertThreshold 10 }

apTcpAttackAlertThresh OBJECT-TYPE
    SYNTAX      TruthValue
    MAX-ACCESS  read-only
    STATUS      current
    DESCRIPTION
        "Incident Alert threshold enabled on/off for TCP Attack defense info"
    ::= { apIncidentAlertThreshold 11 }

apTcpAttackAlertThreshRate OBJECT-TYPE
    SYNTAX      Gauge32
    MAX-ACCESS  read-only
    STATUS      current
    DESCRIPTION
        "Incident Alert threshold rate for TCP Attack defense info"
    ::= { apIncidentAlertThreshold 12 }

apUdpAttackAlertThresh OBJECT-TYPE
    SYNTAX      TruthValue
    MAX-ACCESS  read-only
    STATUS      current
    DESCRIPTION
        "Incident Alert threshold enabled on/off for UDP Attack defense info"
    ::= { apIncidentAlertThreshold 13 }

apUdpAttackAlertThreshRate OBJECT-TYPE
    SYNTAX      Gauge32
    MAX-ACCESS  read-only
    STATUS      current
    DESCRIPTION
        "Incident Alert threshold rate for UDP Attack defense info"
    ::= { apIncidentAlertThreshold 14 }

apIcmpAttackAlertThresh OBJECT-TYPE
    SYNTAX      TruthValue
    MAX-ACCESS  read-only
    STATUS      current
    DESCRIPTION
        "Incident Alert threshold enabled on/off for ICMP Attack defense info"
    ::= { apIncidentAlertThreshold 15 }

apIcmpAttackAlertThreshRate OBJECT-TYPE
    SYNTAX      Gauge32
    MAX-ACCESS  read-only
    STATUS      current
    DESCRIPTION
        "Incident Alert threshold rate for ICMP Attack defense info"
    ::= { apIncidentAlertThreshold 16 }

apOtherIpAttackAlertThresh OBJECT-TYPE
    SYNTAX      TruthValue
    MAX-ACCESS  read-only
    STATUS      current
    DESCRIPTION
        "Incident Alert threshold enabled on/off for other IP Attack defense info"
    ::= { apIncidentAlertThreshold 17 }

apOtherIpAttackAlertThreshRate OBJECT-TYPE
    SYNTAX      Gauge32
    MAX-ACCESS  read-only
    STATUS      current
    DESCRIPTION
        "Incident Alert threshold rate for other IP Attack defense info"
    ::= { apIncidentAlertThreshold 18 }

apFragAttackAlertThresh OBJECT-TYPE
    SYNTAX      TruthValue
    MAX-ACCESS  read-only
    STATUS      current
    DESCRIPTION
        "Incident Alert threshold enabled on/off for fragment Attack defense info"
    ::= { apIncidentAlertThreshold 19 }

apFragAttackAlertThreshRate OBJECT-TYPE
    SYNTAX      Gauge32
    MAX-ACCESS  read-only
    STATUS      current
    DESCRIPTION
        "Incident Alert threshold rate for fragment Attack defense info"
    ::= { apIncidentAlertThreshold 20 }

apBadIpAlertThresh OBJECT-TYPE
    SYNTAX      TruthValue
    MAX-ACCESS  read-only
    STATUS      current
    DESCRIPTION
        "Incident Alert threshold enabled on/off for bad IP defense info"
    ::= { apIncidentAlertThreshold 21 }

apBadIpAlertThreshRate OBJECT-TYPE
    SYNTAX      Gauge32
    MAX-ACCESS  read-only
    STATUS      current
    DESCRIPTION
        "Incident Alert threshold rate for bad IP defense info"
    ::= { apIncidentAlertThreshold 22 }

apBadTcpAlertThresh OBJECT-TYPE
    SYNTAX      TruthValue
    MAX-ACCESS  read-only
    STATUS      current
    DESCRIPTION
        "Incident Alert threshold enabled on/off for bad TCP defense info"
    ::= { apIncidentAlertThreshold 23 }

apBadTcpAlertThreshRate OBJECT-TYPE
    SYNTAX      Gauge32
    MAX-ACCESS  read-only
    STATUS      current
    DESCRIPTION
        "Incident Alert threshold rate for bad TCP defense info"
    ::= { apIncidentAlertThreshold 24 }

apBadUdpAlertThresh OBJECT-TYPE
    SYNTAX      TruthValue
    MAX-ACCESS  read-only
    STATUS      current
    DESCRIPTION
        "Incident Alert threshold enabled on/off for bad UDP defense info"
    ::= { apIncidentAlertThreshold 25 }

apBadUdpAlertThreshRate OBJECT-TYPE
    SYNTAX      Gauge32
    MAX-ACCESS  read-only
    STATUS      current
    DESCRIPTION
        "Incident Alert threshold rate for bad UDP defense info"
    ::= { apIncidentAlertThreshold 26 }

apBadIcmpAlertThresh OBJECT-TYPE
    SYNTAX      TruthValue
    MAX-ACCESS  read-only
    STATUS      current
    DESCRIPTION
        "Incident Alert threshold enabled on/off for bad ICMP defense info"
    ::= { apIncidentAlertThreshold 27 }

apBadIcmpAlertThreshRate OBJECT-TYPE
    SYNTAX      Gauge32
    MAX-ACCESS  read-only
    STATUS      current
    DESCRIPTION
        "Incident Alert threshold rate for bad ICMP defense info"
    ::= { apIncidentAlertThreshold 28 }

apBadOtherIpAlertThresh OBJECT-TYPE
    SYNTAX      TruthValue
    MAX-ACCESS  read-only
    STATUS      current
    DESCRIPTION
        "Incident Alert threshold enabled on/off for bad other IP defense info"
    ::= { apIncidentAlertThreshold 29 }

apBadOtherIpAlertThreshRate OBJECT-TYPE
    SYNTAX      Gauge32
    MAX-ACCESS  read-only
    STATUS      current
    DESCRIPTION
        "Incident Alert threshold rate for bad other IP defense info"
    ::= { apIncidentAlertThreshold 30 }

apOverloadedIpAlertThresh OBJECT-TYPE
    SYNTAX      TruthValue
    MAX-ACCESS  read-only
    STATUS      current
    DESCRIPTION
        "Incident Alert threshold enabled on/off for overloaded protected IP info"
    ::= { apIncidentAlertThreshold 31 }

apOverloadedIpAlertThreshRate OBJECT-TYPE
    SYNTAX      Gauge32
    MAX-ACCESS  read-only
    STATUS      current
    DESCRIPTION
        "Incident Alert threshold rate for overloaded protected IP info"
    ::= { apIncidentAlertThreshold 32 }

apMail OBJECT IDENTIFIER ::= { apConfig 4 }

apMailServer OBJECT-TYPE
    SYNTAX      IpAddress
    MAX-ACCESS  read-only
    STATUS      current
    DESCRIPTION
        "IP address of SMTP email server for appliance"
    ::= { apMail 1 }

apMailFrom OBJECT-TYPE
    SYNTAX      DisplayString
    MAX-ACCESS  read-only
    STATUS      current
    DESCRIPTION
        "eMail address appliance messages should appear to be from"
    ::= { apMail 2 }

apMailSubject OBJECT-TYPE
    SYNTAX      DisplayString
    MAX-ACCESS  read-only
    STATUS      current
    DESCRIPTION
        "eMail subject appliance messages should display (no longer used)"
    ::= { apMail 3 }

apMailToList OBJECT-TYPE
    SYNTAX      DisplayString
    MAX-ACCESS  read-only
    STATUS      current
    DESCRIPTION
        "Semicolon-separated list of recipients for appliance messages"
    ::= { apMail 4 }

apMailDailyStats OBJECT-TYPE
    SYNTAX      TruthValue
    MAX-ACCESS  read-only
    STATUS      current
    DESCRIPTION
        "True if daily statistics are to be mailed"
    ::= { apMail 5 }

apMailAlerts OBJECT-TYPE
    SYNTAX      TruthValue
    MAX-ACCESS  read-only
    STATUS      current
    DESCRIPTION
        "True if mail alerts are to be sent"
    ::= { apMail 6 }

apMailAlertInterval OBJECT-TYPE
    SYNTAX      Gauge32
    MAX-ACCESS  read-only
    STATUS      current
    DESCRIPTION
        "Minimum interval between email alerts (in minutes)"
    ::= { apMail 7 }


apDebugConfig OBJECT IDENTIFIER ::= { apConfig 5 }

apDebugBandwidthFlag OBJECT-TYPE
    SYNTAX      TruthValue
    MAX-ACCESS  read-only
    STATUS      current
    DESCRIPTION
        "TRUE if logging bandwidth Attacks"
    ::= { apDebugConfig 1 }

apDebugFloodFlag OBJECT-TYPE
    SYNTAX      TruthValue
    MAX-ACCESS  read-only
    STATUS      current
    DESCRIPTION
        "TRUE if logging floods"
    ::= { apDebugConfig 2 }

apDebugBlockedProtocolFlag OBJECT-TYPE
    SYNTAX      TruthValue
    MAX-ACCESS  read-only
    STATUS      current
    DESCRIPTION
        "TRUE if logging packets with Blocked Protocols"
    ::= { apDebugConfig 3 }

apDebugBlockedStateFlag OBJECT-TYPE
    SYNTAX      TruthValue
    MAX-ACCESS  read-only
    STATUS      current
    DESCRIPTION
        "TRUE if logging packets with Blocked States"
    ::= { apDebugConfig 4 }

apDebugIpAttackFlag OBJECT-TYPE
    SYNTAX      TruthValue
    MAX-ACCESS  read-only
    STATUS      current
    DESCRIPTION
        "TRUE if logging IP Attacks"
    ::= { apDebugConfig 5 }

apDebugTcpAttackFlag OBJECT-TYPE
    SYNTAX      TruthValue
    MAX-ACCESS  read-only
    STATUS      current
    DESCRIPTION
        "TRUE if logging TCP Attacks"
    ::= { apDebugConfig 6 }

apDebugUdpAttackFlag OBJECT-TYPE
    SYNTAX      TruthValue
    MAX-ACCESS  read-only
    STATUS      current
    DESCRIPTION
        "TRUE if logging UDP Attacks"
    ::= { apDebugConfig 7 }

apDebugIcmpAttackFlag OBJECT-TYPE
    SYNTAX      TruthValue
    MAX-ACCESS  read-only
    STATUS      current
    DESCRIPTION
        "TRUE if logging ICMP Attacks"
    ::= { apDebugConfig 8 }

apDebugOtherIpAttackFlag OBJECT-TYPE
    SYNTAX      TruthValue
    MAX-ACCESS  read-only
    STATUS      current
    DESCRIPTION
        "TRUE if logging other IP Protocol Attacks"
    ::= { apDebugConfig 9 }

apDebugFragmentAttackFlag OBJECT-TYPE
    SYNTAX      TruthValue
    MAX-ACCESS  read-only
    STATUS      current
    DESCRIPTION
        "TRUE if logging fragment Attacks"
    ::= { apDebugConfig 10 }

apDebugBadIpPacketFlag OBJECT-TYPE
    SYNTAX      TruthValue
    MAX-ACCESS  read-only
    STATUS      current
    DESCRIPTION
        "TRUE if logging bad IP packets"
    ::= { apDebugConfig 11 }

apDebugBadTcpPacketFlag OBJECT-TYPE
    SYNTAX      TruthValue
    MAX-ACCESS  read-only
    STATUS      current
    DESCRIPTION
        "TRUE if logging bad TCP packets"
    ::= { apDebugConfig 12 }

apDebugBadUdpPacketFlag OBJECT-TYPE
    SYNTAX      TruthValue
    MAX-ACCESS  read-only
    STATUS      current
    DESCRIPTION
        "TRUE if logging bad UDP packets"
    ::= { apDebugConfig 13 }

apDebugBadIcmpFlag OBJECT-TYPE
    SYNTAX      TruthValue
    MAX-ACCESS  read-only
    STATUS      current
    DESCRIPTION
        "TRUE if logging bad ICMP packets"
    ::= { apDebugConfig 14 }

apDebugBadOtherIpFlag OBJECT-TYPE
    SYNTAX      TruthValue
    MAX-ACCESS  read-only
    STATUS      current
    DESCRIPTION
        "TRUE if logging bad Other IP Protocol packets"
    ::= { apDebugConfig 15 }

apDebugOverloadProtectedIpFlag OBJECT-TYPE
    SYNTAX      TruthValue
    MAX-ACCESS  read-only
    STATUS      current
    DESCRIPTION
        "TRUE if logging stalled protected IPs"
    ::= { apDebugConfig 16 }

apOperationMode OBJECT-TYPE
    SYNTAX      DisplayString
    MAX-ACCESS  read-only
    STATUS      current
    DESCRIPTION
        "Current operating mode of the DDoS Secure device"
    ::= { apConfig 6 }

apNtpServerList OBJECT-TYPE
    SYNTAX      DisplayString
    MAX-ACCESS  read-only
    STATUS      current
    DESCRIPTION
        "Comma-separated list of NTP servers for appliance"
    ::= { apConfig 7 }

apTimeZone OBJECT-TYPE
    SYNTAX      DisplayString
    MAX-ACCESS  read-only
    STATUS      current
    DESCRIPTION
        "Time zone (as a string, e.g. Europe/London)"
    ::= { apConfig 8 }

apProtectedIpNetwork OBJECT-TYPE
    SYNTAX      DisplayString
    MAX-ACCESS  read-only
    STATUS      current
    DESCRIPTION
        "All the protected IP network(s) on the DDoS Secure Appliance"
    ::= { apConfig 9 }

apSnmp OBJECT IDENTIFIER ::= { apConfig 10 }

apSnmpRoCommunity OBJECT-TYPE
    SYNTAX      DisplayString
    MAX-ACCESS  read-only
    STATUS      current
    DESCRIPTION
        "Read-only community string"
    ::= { apSnmp 1 }

apSnmpTrapCommunity OBJECT-TYPE
    SYNTAX      DisplayString
    MAX-ACCESS  read-only
    STATUS      current
    DESCRIPTION
        "Read-only community string"
    ::= { apSnmp 2 }

apSnmpTrapIpAddressList OBJECT-TYPE
    SYNTAX      DisplayString
    MAX-ACCESS  read-only
    STATUS      current
    DESCRIPTION
        "ASCII comma-separated list of IP addresses to receive SNMP traps"
    ::= { apSnmp 3 }

apAutoBlackList OBJECT IDENTIFIER ::= { apConfig 11 }

apAutoblockEnable OBJECT-TYPE
    SYNTAX      TruthValue
    MAX-ACCESS  read-only
    STATUS      current
    DESCRIPTION
        "Enables autoblocking of clients when a worst offender
	 exceeds the autoblockRate threshold"
    ::= { apAutoBlackList 1 }

apAutoblockRateT1 OBJECT-TYPE
    SYNTAX      Gauge32
    MAX-ACCESS  read-only
    STATUS      current
    DESCRIPTION
        "Packet rate/sec above which worst offending clients (type 1) are autoblocked,
	 if autoblocking is enabled"
    ::= { apAutoBlackList 2 }

apAutoblockRateT2 OBJECT-TYPE
    SYNTAX      Gauge32
    MAX-ACCESS  read-only
    STATUS      current
    DESCRIPTION
        "Packet rate/sec above which worst offending clients (type 2) are autoblocked,
	 if autoblocking is enabled"
    ::= { apAutoBlackList 3 }

apProtectedIpAutodetect OBJECT-TYPE
    SYNTAX      TruthValue
    MAX-ACCESS  read-only
    STATUS      current
    DESCRIPTION
        "If true, unconfigured IPs amd MACs are autodetected on the protected interface
	 (and default protection parameters are applied)"
    ::= { apConfig 12 }

apTrackIndeterminate OBJECT-TYPE
    SYNTAX      TruthValue
    MAX-ACCESS  read-only
    STATUS      current
    DESCRIPTION
        "Track state on indeterminate addresses on protected interface"
    ::= { apConfig 13 }

-- ### Protection configuration settings ###

prConfigTable OBJECT-TYPE
    SYNTAX      SEQUENCE OF PrConfigEntry
    MAX-ACCESS	not-accessible
    STATUS	current
    DESCRIPTION
	"The configuration of each IP or MAC address
	 protected by the DDoS Secure"
    ::= { jddsProtected 1 }

prConfigEntry OBJECT-TYPE
    SYNTAX   PrConfigEntry
    MAX-ACCESS	not-accessible
    STATUS      current
    DESCRIPTION
	"The protection configuration for an individual address on the protected interface"
    INDEX       { prConfigInetAddressType, prConfigInetAddress }
    ::= { prConfigTable 1 }

PrConfigEntry ::= SEQUENCE {
    prConfigInetAddressType
	InetAddressType,
    prConfigInetAddress
	InetAddress,
    prHostName
	DisplayString,
    prTcpBacklog
	Gauge32,
    prMaxConnections
	Gauge32,
    prMaxConnectionRate
	Gauge32,
    prInFilterName
        DisplayString,
    prOutFilterName
        DisplayString,
    prSendTcpRejects
        TruthValue,
    prTrackSoap
        TruthValue,
    prOperationMode
        DisplayString,
    prMaxGets
	Gauge32,
    prFragsDisabled
	TruthValue
}

prConfigInetAddressType OBJECT-TYPE
    SYNTAX      InetAddressType
    MAX-ACCESS  not-accessible
    STATUS      current
    DESCRIPTION
	"The protected IP address type IPv4 or IPv6"
     ::= { prConfigEntry 1 }

prConfigInetAddress OBJECT-TYPE
    SYNTAX      InetAddress (SIZE (0..47))
    MAX-ACCESS  not-accessible
    STATUS      current
    DESCRIPTION
	"The protected IP address"
     ::= { prConfigEntry 2 }

prHostName OBJECT-TYPE
    SYNTAX      DisplayString
    MAX-ACCESS  read-only
    STATUS      current
    DESCRIPTION
	"Host name associated with the protected IP"
     ::= { prConfigEntry 3 }

prTcpBacklog OBJECT-TYPE
    SYNTAX      Gauge32
    MAX-ACCESS  read-only
    STATUS      current
    DESCRIPTION
	"Max number of half-open TCP connections"
     ::= { prConfigEntry 4 }

prMaxConnections OBJECT-TYPE
    SYNTAX      Gauge32
    MAX-ACCESS  read-only
    STATUS      current
    DESCRIPTION
	"Max number of open TCP connections"
     ::= { prConfigEntry 5 }

prMaxConnectionRate OBJECT-TYPE
    SYNTAX      Gauge32
    MAX-ACCESS  read-only
    STATUS      current
    DESCRIPTION
	"Max rate of opening new TCP connections"
     ::= { prConfigEntry 6 }

prInFilterName OBJECT-TYPE
    SYNTAX      DisplayString
    MAX-ACCESS  read-only
    STATUS      current
    DESCRIPTION
	"Input filter name associated with the protected IP"
     ::= { prConfigEntry 7 }

prOutFilterName OBJECT-TYPE
    SYNTAX      DisplayString
    MAX-ACCESS  read-only
    STATUS      current
    DESCRIPTION
	"Output filter name associated with the protected IP"
     ::= { prConfigEntry 8 }

prSendTcpRejects OBJECT-TYPE
    SYNTAX      TruthValue
    MAX-ACCESS  read-only
    STATUS      current
    DESCRIPTION
        "TRUE if TCP rejects are to be sent"
    ::= { prConfigEntry 9 }

prTrackSoap OBJECT-TYPE
    SYNTAX      TruthValue
    MAX-ACCESS  read-only
    STATUS      current
    DESCRIPTION
        "TRUE if SOAP Headers are to be tracked"
    ::= { prConfigEntry 10 }

prOperationMode OBJECT-TYPE
    SYNTAX      DisplayString
    MAX-ACCESS  read-only
    STATUS      current
    DESCRIPTION
        "Current operating mode of the protected IP"
    ::= { prConfigEntry 11 }

prMaxGets OBJECT-TYPE
    SYNTAX      Gauge32
    MAX-ACCESS  read-only
    STATUS      current
    DESCRIPTION
	"Max number of outstanding GET requests"
     ::= { prConfigEntry 12 }

prFragsDisabled OBJECT-TYPE
    SYNTAX      TruthValue
    MAX-ACCESS  read-only
    STATUS      current
    DESCRIPTION
        "TRUE if packet fragmentation is not allowed"
    ::= { prConfigEntry 13 }


-- ### Gateway internet-side settings ###

gwInternetConfigTable OBJECT-TYPE
    SYNTAX      SEQUENCE OF GwInternetConfigEntry
    MAX-ACCESS	not-accessible
    STATUS	current
    DESCRIPTION
	"The configuration of each internet-side gateway
	 protected by the DDoS Secure"
    ::= { jddsGatewayInternet 1 }

gwInternetConfigEntry OBJECT-TYPE
    SYNTAX      GwInternetConfigEntry
    MAX-ACCESS	not-accessible
    STATUS      current
    DESCRIPTION
	"The configuration of an individual internet-side gateway"
    INDEX       { gwInternetConfigIndex }
    ::= { gwInternetConfigTable 1 }

GwInternetConfigEntry ::= SEQUENCE {
    gwInternetConfigIndex
	LocalIndex,
    gwInternetConfigMacAddress
	DisplayString,
    gwInternetConfigToSpeedBps
	Gauge32,
    gwInternetConfigToRatePps
	Gauge32
}

gwInternetConfigIndex OBJECT-TYPE
    SYNTAX      LocalIndex
    MAX-ACCESS  not-accessible
    STATUS      current
    DESCRIPTION
        "Unique gateway internet index"
    ::= { gwInternetConfigEntry 1 }

gwInternetConfigMacAddress OBJECT-TYPE
    SYNTAX      DisplayString
    MAX-ACCESS  read-only
    STATUS      current
    DESCRIPTION
	"MAC address of the internet-side gateway"
     ::= { gwInternetConfigEntry 2 }

gwInternetConfigToSpeedBps OBJECT-TYPE
    SYNTAX      Gauge32
    MAX-ACCESS  read-only
    STATUS      current
    DESCRIPTION
	"Max speed to internet-side gateway allowed in bits/sec"
     ::= { gwInternetConfigEntry 3 }

gwInternetConfigToRatePps OBJECT-TYPE
    SYNTAX      Gauge32
    MAX-ACCESS  read-only
    STATUS      current
    DESCRIPTION
	"Max rate to internet-side gateway allowed in packets/sec"
     ::= { gwInternetConfigEntry 4 }


-- ### Gateway protected-side settings ###

gwProtectedConfigTable OBJECT-TYPE
    SYNTAX      SEQUENCE OF GwProtectedConfigEntry
    MAX-ACCESS	not-accessible
    STATUS	current
    DESCRIPTION
	"The configuration of each protected-side gateway
	 protected by the DDoS Secure"
    ::= { jddsGatewayProtected 1 }

gwProtectedConfigEntry OBJECT-TYPE
    SYNTAX      GwProtectedConfigEntry
    MAX-ACCESS	not-accessible
    STATUS      current
    DESCRIPTION
	"The configuration of an individual protected-side gateway"
    INDEX       { gwProtectedConfigIndex }
    ::= { gwProtectedConfigTable 1 }

GwProtectedConfigEntry ::= SEQUENCE {
    gwProtectedConfigIndex
	LocalIndex,
    gwProtectedConfigMacAddress
	DisplayString,
    gwProtectedConfigToSpeedBps
	Gauge32,
    gwProtectedConfigToRatePps
	Gauge32
}

gwProtectedConfigIndex OBJECT-TYPE
    SYNTAX      LocalIndex
    MAX-ACCESS  not-accessible
    STATUS      current
    DESCRIPTION
        "Unique protected-side gateway index"
    ::= { gwProtectedConfigEntry 1 }

gwProtectedConfigMacAddress OBJECT-TYPE
    SYNTAX      DisplayString
    MAX-ACCESS  read-only
    STATUS      current
    DESCRIPTION
	"MAC address of the protected-side gateway"
     ::= { gwProtectedConfigEntry 2 }

gwProtectedConfigToSpeedBps OBJECT-TYPE
    SYNTAX      Gauge32
    MAX-ACCESS  read-only
    STATUS      current
    DESCRIPTION
	"Max speed to protected-side gateway allowed in bits/sec"
     ::= { gwProtectedConfigEntry 3 }

gwProtectedConfigToRatePps OBJECT-TYPE
    SYNTAX      Gauge32
    MAX-ACCESS  read-only
    STATUS      current
    DESCRIPTION
	"Max speed to protected-side gateway allowed in packets/sec"
     ::= { gwProtectedConfigEntry 4 }


apState OBJECT IDENTIFIER ::= { jddsAppliance 2 }

apDefenseFlags OBJECT IDENTIFIER ::= { apState 1 }

apBandwidth OBJECT-TYPE
    SYNTAX      TruthValue
    MAX-ACCESS  read-only
    STATUS      current
    DESCRIPTION
        "TRUE if appliance is currently using bandwidth defense"
    ::= { apDefenseFlags 1 }

apFlood OBJECT-TYPE
    SYNTAX      TruthValue
    MAX-ACCESS  read-only
    STATUS      current
    DESCRIPTION
        "TRUE if appliance is currently using flood defense"
    ::= { apDefenseFlags 2 }

apBlockedProtocol OBJECT-TYPE
    SYNTAX      TruthValue
    MAX-ACCESS  read-only
    STATUS      current
    DESCRIPTION
        "TRUE if appliance is currently using blocked Protocol defense"
    ::= { apDefenseFlags 3 }

apBlockedState OBJECT-TYPE
    SYNTAX      TruthValue
    MAX-ACCESS  read-only
    STATUS      current
    DESCRIPTION
        "TRUE if appliance is currently using blocked state defense"
    ::= { apDefenseFlags 4 }

apIpAttack OBJECT-TYPE
    SYNTAX      TruthValue
    MAX-ACCESS  read-only
    STATUS      current
    DESCRIPTION
        "TRUE if appliance is currently using IP Attack defense"
    ::= { apDefenseFlags 5 }

apTcpAttack OBJECT-TYPE
    SYNTAX      TruthValue
    MAX-ACCESS  read-only
    STATUS      current
    DESCRIPTION
        "TRUE if appliance is currently using TCP Attack defense"
    ::= { apDefenseFlags 6 }

apUdpAttack OBJECT-TYPE
    SYNTAX      TruthValue
    MAX-ACCESS  read-only
    STATUS      current
    DESCRIPTION
        "TRUE if appliance is currently using UDP Attack defense"
    ::= { apDefenseFlags 7 }

apIcmpAttack OBJECT-TYPE
    SYNTAX      TruthValue
    MAX-ACCESS  read-only
    STATUS      current
    DESCRIPTION
        "TRUE if appliance is currently using ICMP Attack defense"
    ::= { apDefenseFlags 8 }

apOtherIpAttack OBJECT-TYPE
    SYNTAX      TruthValue
    MAX-ACCESS  read-only
    STATUS      current
    DESCRIPTION
        "TRUE if appliance is currently using other IP Attack defense"
    ::= { apDefenseFlags 9 }

apFragAttack OBJECT-TYPE
    SYNTAX      TruthValue
    MAX-ACCESS  read-only
    STATUS      current
    DESCRIPTION
        "TRUE if appliance is currently using fragment Attack defense"
    ::= { apDefenseFlags 10 }

apBadIp OBJECT-TYPE
    SYNTAX      TruthValue
    MAX-ACCESS  read-only
    STATUS      current
    DESCRIPTION
        "TRUE if appliance is currently using bad IP defense"
    ::= { apDefenseFlags 11 }

apBadTcp OBJECT-TYPE
    SYNTAX      TruthValue
    MAX-ACCESS  read-only
    STATUS      current
    DESCRIPTION
        "TRUE if appliance is currently using bad TCP defense"
    ::= { apDefenseFlags 12 }

apBadUdp OBJECT-TYPE
    SYNTAX      TruthValue
    MAX-ACCESS  read-only
    STATUS      current
    DESCRIPTION
        "TRUE if appliance is currently using bad UDP defense"
    ::= { apDefenseFlags 13 }

apBadIcmp OBJECT-TYPE
    SYNTAX      TruthValue
    MAX-ACCESS  read-only
    STATUS      current
    DESCRIPTION
        "TRUE if appliance is currently using bad ICMP defense"
    ::= { apDefenseFlags 14 }

apBadOtherIp OBJECT-TYPE
    SYNTAX      TruthValue
    MAX-ACCESS  read-only
    STATUS      current
    DESCRIPTION
        "TRUE if appliance is currently using bad other IP defense"
    ::= { apDefenseFlags 15 }

apOverloadedIp OBJECT-TYPE
    SYNTAX      TruthValue
    MAX-ACCESS  read-only
    STATUS      current
    DESCRIPTION
        "TRUE if appliance is currently experiencing an overloaded protected IP"
    ::= { apDefenseFlags 16 }

apTcpStates OBJECT IDENTIFIER ::= { apState 2 }

apInSyn OBJECT-TYPE
    SYNTAX      Counter32
    MAX-ACCESS  read-only
    STATUS      current
    DESCRIPTION
        "state tally: client connection requests inbound"
    ::= { apTcpStates 1 }

apOutSyn OBJECT-TYPE
    SYNTAX      Counter32
    MAX-ACCESS  read-only
    STATUS      current
    DESCRIPTION
        "state tally: client connection requests outbound"
    ::= { apTcpStates 2 }

apInSynAck OBJECT-TYPE
    SYNTAX      Counter32
    MAX-ACCESS  read-only
    STATUS      current
    DESCRIPTION
        "state tally: protected IP responses to client connection requests inbound"
    ::= { apTcpStates 3 }

apOutSynAck OBJECT-TYPE
    SYNTAX      Counter32
    MAX-ACCESS  read-only
    STATUS      current
    DESCRIPTION
        "state tally: protected IP responses to client connection requests outbound"
    ::= { apTcpStates 4 }

apInSynSyn OBJECT-TYPE
    SYNTAX      Counter32
    MAX-ACCESS  read-only
    STATUS      current
    DESCRIPTION
        "state tally: client and protected IP crossed SYNs on inbound connection"
    ::= { apTcpStates 5 }

apOutSynSyn OBJECT-TYPE
    SYNTAX      Counter32
    MAX-ACCESS  read-only
    STATUS      current
    DESCRIPTION
        "state tally: client and protected IP crossed SYNs on outbound connection"
    ::= { apTcpStates 6 }

apInEst OBJECT-TYPE
    SYNTAX      Counter32
    MAX-ACCESS  read-only
    STATUS      current
    DESCRIPTION
        "state tally: client-protected IP connections established inbound"
    ::= { apTcpStates 7 }

apOutEst OBJECT-TYPE
    SYNTAX      Counter32
    MAX-ACCESS  read-only
    STATUS      current
    DESCRIPTION
        "state tally: client-protected IP connections established outbound"
    ::= { apTcpStates 8 }

apInFin1Src OBJECT-TYPE
    SYNTAX      Counter32
    MAX-ACCESS  read-only
    STATUS      current
    DESCRIPTION
        "state tally: client FINs sent inbound"
    ::= { apTcpStates 9 }

apOutFin1Src OBJECT-TYPE
    SYNTAX      Counter32
    MAX-ACCESS  read-only
    STATUS      current
    DESCRIPTION
        "state tally: client FINs sent outbound"
    ::= { apTcpStates 10 }

apInFin2Src OBJECT-TYPE
    SYNTAX      Counter32
    MAX-ACCESS  read-only
    STATUS      current
    DESCRIPTION
        "state tally: protected IP ACKed FINs inbound"
    ::= { apTcpStates 11 }

apOutFin2Src OBJECT-TYPE
    SYNTAX      Counter32
    MAX-ACCESS  read-only
    STATUS      current
    DESCRIPTION
        "state tally: protected IP ACKed FINs outbound"
    ::= { apTcpStates 12 }

apInFin3Src OBJECT-TYPE
    SYNTAX      Counter32
    MAX-ACCESS  read-only
    STATUS      current
    DESCRIPTION
        "state tally: client and protected IP sent FINs inbound"
    ::= { apTcpStates 13 }

apOutFin3Src OBJECT-TYPE
    SYNTAX      Counter32
    MAX-ACCESS  read-only
    STATUS      current
    DESCRIPTION
        "state tally: client and protected IP sent FINs outbound"
    ::= { apTcpStates 14 }

apInFinFin OBJECT-TYPE
    SYNTAX      Counter32
    MAX-ACCESS  read-only
    STATUS      current
    DESCRIPTION
        "state tally: client and protected IP crossed un-ACKed FINs inbound"
    ::= { apTcpStates 15 }

apOutFinFin OBJECT-TYPE
    SYNTAX      Counter32
    MAX-ACCESS  read-only
    STATUS      current
    DESCRIPTION
        "state tally: client and protected IP crossed un-ACKed FINs outbound"
    ::= { apTcpStates 16 }

apInFin1Dst OBJECT-TYPE
    SYNTAX      Counter32
    MAX-ACCESS  read-only
    STATUS      current
    DESCRIPTION
        "state tally: protected IP FINs sent inbound"
    ::= { apTcpStates 17 }

apOutFin1Dst OBJECT-TYPE
    SYNTAX      Counter32
    MAX-ACCESS  read-only
    STATUS      current
    DESCRIPTION
        "state tally: protected IP FINs sent outbound"
    ::= { apTcpStates 18 }

apInFin2Dst OBJECT-TYPE
    SYNTAX      Counter32
    MAX-ACCESS  read-only
    STATUS      current
    DESCRIPTION
        "state tally: protected IP ACKed FINs inbound"
    ::= { apTcpStates 19 }

apOutFin2Dst OBJECT-TYPE
    SYNTAX      Counter32
    MAX-ACCESS  read-only
    STATUS      current
    DESCRIPTION
        "state tally: client ACKed FINs outbound"
    ::= { apTcpStates 20 }

apInFin3Dst OBJECT-TYPE
    SYNTAX      Counter32
    MAX-ACCESS  read-only
    STATUS      current
    DESCRIPTION
        "state tally: protected IP and client sent FINs inbound"
    ::= { apTcpStates 21 }

apOutFin3Dst OBJECT-TYPE
    SYNTAX      Counter32
    MAX-ACCESS  read-only
    STATUS      current
    DESCRIPTION
        "state tally: protected IP and client sent FINs outbound"
    ::= { apTcpStates 22 }

apInCls OBJECT-TYPE
    SYNTAX      Counter32
    MAX-ACCESS  read-only
    STATUS      current
    DESCRIPTION
        "state tally: closed connections inbound"
    ::= { apTcpStates 23 }

apOutCls OBJECT-TYPE
    SYNTAX      Counter32
    MAX-ACCESS  read-only
    STATUS      current
    DESCRIPTION
        "state tally: closed connections outbound"
    ::= { apTcpStates 24 }

apInRst OBJECT-TYPE
    SYNTAX      Counter32
    MAX-ACCESS  read-only
    STATUS      current
    DESCRIPTION
        "state tally: resets sent on inbound connection"
    ::= { apTcpStates 25 }

apOutRst OBJECT-TYPE
    SYNTAX      Counter32
    MAX-ACCESS  read-only
    STATUS      current
    DESCRIPTION
        "state tally: resets sent on outbound connection"
    ::= { apTcpStates 26 }

apInRstCls OBJECT-TYPE
    SYNTAX      Counter32
    MAX-ACCESS  read-only
    STATUS      current
    DESCRIPTION
        "state tally: resets sent on inbound connection"
    ::= { apTcpStates 27 }

apOutRstCls OBJECT-TYPE
    SYNTAX      Counter32
    MAX-ACCESS  read-only
    STATUS      current
    DESCRIPTION
        "state tally: resets sent on outbound connection"
    ::= { apTcpStates 28 }

apInUnknown OBJECT-TYPE
    SYNTAX      Counter32
    MAX-ACCESS  read-only
    STATUS      current
    DESCRIPTION
        "state tally: unknown states inbound"
    ::= { apTcpStates 29 }

apOutUnknown OBJECT-TYPE
    SYNTAX      Counter32
    MAX-ACCESS  read-only
    STATUS      current
    DESCRIPTION
        "state tally: unknown states outbound"
    ::= { apTcpStates 30 }

apInAck OBJECT-TYPE
    SYNTAX      Counter32
    MAX-ACCESS  read-only
    STATUS      current
    DESCRIPTION
        "state tally: three way handshake completed inbound"
    ::= { apTcpStates 31 }

apOutAck OBJECT-TYPE
    SYNTAX      Counter32
    MAX-ACCESS  read-only
    STATUS      current
    DESCRIPTION
        "state tally: three way handshake completed outbound"
    ::= { apTcpStates 32 }

apInPendAck OBJECT-TYPE
    SYNTAX      Counter32
    MAX-ACCESS  read-only
    STATUS      current
    DESCRIPTION
        "state tally: protected IP has not acknowledged any data inbound"
    ::= { apTcpStates 33 }

apOutPendAck OBJECT-TYPE
    SYNTAX      Counter32
    MAX-ACCESS  read-only
    STATUS      current
    DESCRIPTION
        "state tally: protected IP has not acknowledged any data outbound"
    ::= { apTcpStates 34 }

apInGet OBJECT-TYPE
    SYNTAX      Counter32
    MAX-ACCESS  read-only
    STATUS      current
    DESCRIPTION
        "state tally: protected IP in GET State"
    ::= { apTcpStates 35 }

apOutGet OBJECT-TYPE
    SYNTAX      Counter32
    MAX-ACCESS  read-only
    STATUS      current
    DESCRIPTION
        "state tally: protected IP in GET State"
    ::= { apTcpStates 36 }

apInGets OBJECT-TYPE
    SYNTAX      Counter32
    MAX-ACCESS  read-only
    STATUS      current
    DESCRIPTION
        "state tally: the number of established TCP sessions processing a GET"
    ::= { apTcpStates 37 }

apOutGets OBJECT-TYPE
    SYNTAX      Counter32
    MAX-ACCESS  read-only
    STATUS      current
    DESCRIPTION
        "state tally: the number of established TCP sessions processing a GET"
    ::= { apTcpStates 38 }

apInTotalBpsAvg OBJECT-TYPE
    SYNTAX      Gauge32
    MAX-ACCESS  read-only
    STATUS      current
    DESCRIPTION
	"Average number of input bits per second"
    ::= { apTcpStates 901 }

apOutTotalBpsAvg OBJECT-TYPE
    SYNTAX      Gauge32
    MAX-ACCESS  read-only
    STATUS      current
    DESCRIPTION
	"Average number of output bits per second"
    ::= { apTcpStates 902 }

apInTotalPpsAvg OBJECT-TYPE
    SYNTAX      Gauge32
    MAX-ACCESS  read-only
    STATUS      current
    DESCRIPTION
	"Average packets/sec traffic rate inbound since last restart or reset"
    ::= { apTcpStates 903 }

apOutTotalPpsAvg OBJECT-TYPE
    SYNTAX      Gauge32
    MAX-ACCESS  read-only
    STATUS      current
    DESCRIPTION
	"Average packets/sec traffic rate outbound since last restart or reset"
    ::= { apTcpStates 904 }

apInSmallPpsAvg OBJECT-TYPE
    SYNTAX      Gauge32
    MAX-ACCESS  read-only
    STATUS      current
    DESCRIPTION
	"Averaged inbound packets (256 bytes or less) per second processed. Dropped data is not included"
    ::= { apTcpStates 905 }

apOutSmallPpsAvg OBJECT-TYPE
    SYNTAX      Gauge32
    MAX-ACCESS  read-only
    STATUS      current
    DESCRIPTION
	"Averaged outbound packets (256 bytes or less) per second processed. Dropped data is not included"
    ::= { apTcpStates 906 }

apInMediumPpsAvg OBJECT-TYPE
    SYNTAX      Gauge32
    MAX-ACCESS  read-only
    STATUS      current
    DESCRIPTION
	"Averaged inbound packets (1024 bytes or less, but greater than 256 bytes) per second. Dropped data is not included"
    ::= { apTcpStates 907 }

apOutMediumPpsAvg OBJECT-TYPE
    SYNTAX      Gauge32
    MAX-ACCESS  read-only
    STATUS      current
    DESCRIPTION
	"Averaged outbound packets (1024 bytes or less, but greater than 256 bytes) per second. Dropped data is not included"
    ::= { apTcpStates 908 }

apInLargePpsAvg OBJECT-TYPE
    SYNTAX      Gauge32
    MAX-ACCESS  read-only
    STATUS      current
    DESCRIPTION
	"Averaged inbound packets (greater than 1024 bytes) per second. Dropped data is not included"
    ::= { apTcpStates 909 }

apOutLargePpsAvg OBJECT-TYPE
    SYNTAX      Gauge32
    MAX-ACCESS  read-only
    STATUS      current
    DESCRIPTION
	"Averaged outbound packets (greater than 1024 bytes) per second. Dropped data is not included"
    ::= { apTcpStates 910 }

apInDroppedBpsAvg OBJECT-TYPE
    SYNTAX      Gauge32
    MAX-ACCESS  read-only
    STATUS      current
    DESCRIPTION
	"Average number of input bits Dropped per second"
    ::= { apTcpStates 911 }

apOutDroppedBpsAvg OBJECT-TYPE
    SYNTAX      Gauge32
    MAX-ACCESS  read-only
    STATUS      current
    DESCRIPTION
	"Average number of output bits Dropped per second"
    ::= { apTcpStates 912 }

apInDroppedPpsAvg OBJECT-TYPE
    SYNTAX      Gauge32
    MAX-ACCESS  read-only
    STATUS      current
    DESCRIPTION
	"Average number of input packets Dropped per second"
    ::= { apTcpStates 913 }

apOutDroppedPpsAvg OBJECT-TYPE
    SYNTAX      Gauge32
    MAX-ACCESS  read-only
    STATUS      current
    DESCRIPTION
	"Averaged number of output packets Dropped per second"
    ::= { apTcpStates 914 }

apInCharmDroppedBpsAvg OBJECT-TYPE
    SYNTAX      Gauge32
    MAX-ACCESS  read-only
    STATUS      current
    DESCRIPTION
	"Averaged inbound bits per second dropped by heuristic detection"
    ::= { apTcpStates 915 }

apOutCharmDroppedBpsAvg OBJECT-TYPE
    SYNTAX      Gauge32
    MAX-ACCESS  read-only
    STATUS      current
    DESCRIPTION
	"Averaged outbound bits per second dropped by heuristic detection"
    ::= { apTcpStates 916 }

apInFilteredBwthPercentAvg OBJECT-TYPE
    SYNTAX      Gauge32
    MAX-ACCESS  read-only
    STATUS      current
    DESCRIPTION
	"Averaged inbound dropped bandwidth divided by the actual bandwidth"
    ::= { apTcpStates 917 }

apOutFilteredBwthPercentAvg OBJECT-TYPE
    SYNTAX      Gauge32
    MAX-ACCESS  read-only
    STATUS      current
    DESCRIPTION
	"Averaged outbound dropped bandwidth divided by the actual bandwidth"
    ::= { apTcpStates 918 }

apInSynbacklogtallyAvg OBJECT-TYPE
    SYNTAX      Gauge32
    MAX-ACCESS  read-only
    STATUS      current
    DESCRIPTION
	"Averaged number of partially open TCP connections inbound"
    ::= { apTcpStates 919 }

apOutSynbacklogtallyAvg OBJECT-TYPE
    SYNTAX      Gauge32
    MAX-ACCESS  read-only
    STATUS      current
    DESCRIPTION
	"Averaged number of partially open TCP connections outbound"
    ::= { apTcpStates 920 }

apInConnectionAvg OBJECT-TYPE
    SYNTAX      Gauge32
    MAX-ACCESS  read-only
    STATUS      current
    DESCRIPTION
	"Averaged number of inbound TCP connections"
    ::= { apTcpStates 921 }

apOutConnectionAvg OBJECT-TYPE
    SYNTAX      Gauge32
    MAX-ACCESS  read-only
    STATUS      current
    DESCRIPTION
	"Averaged number of outbound TCP connections"
    ::= { apTcpStates 922 }

apInConnreqAvg OBJECT-TYPE
    SYNTAX      Gauge32
    MAX-ACCESS  read-only
    STATUS      current
    DESCRIPTION
	"Averaged number of inbound TCP connection requests"
    ::= { apTcpStates 923 }

apOutConnreqAvg OBJECT-TYPE
    SYNTAX      Gauge32
    MAX-ACCESS  read-only
    STATUS      current
    DESCRIPTION
	"Averaged number of outbound TCP connection requests"
    ::= { apTcpStates 924 }

apInActiveHttpGetsAvg OBJECT-TYPE
    SYNTAX      Gauge32
    MAX-ACCESS  read-only
    STATUS      current
    DESCRIPTION
	"Averaged number of inbound HTTP page requests being processed"
    ::= { apTcpStates 925 }

apOutActiveHttpGetsAvg OBJECT-TYPE
    SYNTAX      Gauge32
    MAX-ACCESS  read-only
    STATUS      current
    DESCRIPTION
	"Averaged number of outbound HTTP page requests being processed"
    ::= { apTcpStates 926 }

apInProtectBwthPktsAvg OBJECT-TYPE
    SYNTAX      Gauge32
    MAX-ACCESS  read-only
    STATUS      current
    DESCRIPTION
	"Averaged inbound protected bandwifth"
    ::= { apTcpStates 927 }

apOutProtectBwthPktsAvg OBJECT-TYPE
    SYNTAX      Gauge32
    MAX-ACCESS  read-only
    STATUS      current
    DESCRIPTION
	"Averaged outbound protected bandwifth"
    ::= { apTcpStates 928 }

apInFloodPktsAvg OBJECT-TYPE
    SYNTAX      Gauge32
    MAX-ACCESS  read-only
    STATUS      current
    DESCRIPTION
	"Averaged number of inbound packets causing flooding"
    ::= { apTcpStates 929 }

apOutFloodPktsAvg OBJECT-TYPE
    SYNTAX      Gauge32
    MAX-ACCESS  read-only
    STATUS      current
    DESCRIPTION
	"Averaged number of outbound packets causing flooding"
    ::= { apTcpStates 930 }

apInBlockedProtocolPktsAvg OBJECT-TYPE
    SYNTAX      Gauge32
    MAX-ACCESS  read-only
    STATUS      current
    DESCRIPTION
	"Averaged number of inbound IP packets dropped by filter "
    ::= { apTcpStates 931 }

apOutBlockedProtocolPktsAvg OBJECT-TYPE
    SYNTAX      Gauge32
    MAX-ACCESS  read-only
    STATUS      current
    DESCRIPTION
	"Averaged number of outbound IP packets dropped by filter"
    ::= { apTcpStates 932 }

apInBlockedStatePktsAvg OBJECT-TYPE
    SYNTAX      Gauge32
    MAX-ACCESS  read-only
    STATUS      current
    DESCRIPTION
	"Averaged number of inbound IP packets dropped due to incorrect state"
    ::= { apTcpStates 933 }

apOutBlockedStatePktsAvg OBJECT-TYPE
    SYNTAX      Gauge32
    MAX-ACCESS  read-only
    STATUS      current
    DESCRIPTION
	"Averaged number of outbound IP packets dropped due to incorrect state"
    ::= { apTcpStates 934 }

apInIpAttackPktsAvg OBJECT-TYPE
    SYNTAX      Gauge32
    MAX-ACCESS  read-only
    STATUS      current
    DESCRIPTION
	"Averaged number of inbound IP packets in an IP Attack"
    ::= { apTcpStates 935 }

apOutIpAttackPktsAvg OBJECT-TYPE
    SYNTAX      Gauge32
    MAX-ACCESS  read-only
    STATUS      current
    DESCRIPTION
	"Averaged number of outbound IP packets in an IP Attack"
    ::= { apTcpStates 936 }

apInTcpAttackPktsAvg OBJECT-TYPE
    SYNTAX      Gauge32
    MAX-ACCESS  read-only
    STATUS      current
    DESCRIPTION
	"Averaged number of inbound IP packets in a TCP Attack"
    ::= { apTcpStates 937 }

apOutTcpAttackPktsAvg OBJECT-TYPE
    SYNTAX      Gauge32
    MAX-ACCESS  read-only
    STATUS      current
    DESCRIPTION
	"Averaged number of outbound IP packets in a TCP Attack"
    ::= { apTcpStates 938 }

apInUdpAttackPktsAvg OBJECT-TYPE
    SYNTAX      Gauge32
    MAX-ACCESS  read-only
    STATUS      current
    DESCRIPTION
	"Averaged number of inbound IP packets in a UDP Attack"
    ::= { apTcpStates 939 }

apOutUdpAttackPktsAvg OBJECT-TYPE
    SYNTAX      Gauge32
    MAX-ACCESS  read-only
    STATUS      current
    DESCRIPTION
	"Averaged number of outbound IP packets in a UDP Attack"
    ::= { apTcpStates 940 }

apInIcmpAttackPktsAvg OBJECT-TYPE
    SYNTAX      Gauge32
    MAX-ACCESS  read-only
    STATUS      current
    DESCRIPTION
	"Averaged number of inbound IP packets in a ICMP Attack"
    ::= { apTcpStates 941 }

apOutIcmpAttackPktsAvg OBJECT-TYPE
    SYNTAX      Gauge32
    MAX-ACCESS  read-only
    STATUS      current
    DESCRIPTION
	"Averaged number of outbound IP packets in a ICMP Attack"
    ::= { apTcpStates 942 }

apInOtherIpAttackPktsAvg OBJECT-TYPE
    SYNTAX      Gauge32
    MAX-ACCESS  read-only
    STATUS      current
    DESCRIPTION
	"Averaged number of inbound IP packets in an IP Attack using other protocols"
    ::= { apTcpStates 943 }

apOutOtherIpAttackPktsAvg OBJECT-TYPE
    SYNTAX      Gauge32
    MAX-ACCESS  read-only
    STATUS      current
    DESCRIPTION
	"Averaged number of outbound IP packets in an IP Attack using other protocols"
    ::= { apTcpStates 944 }

apInFragmentAttackPktsAvg OBJECT-TYPE
    SYNTAX      Gauge32
    MAX-ACCESS  read-only
    STATUS      current
    DESCRIPTION
	"Averaged number of inbound IP packets in an Fragmentation Attack"
    ::= { apTcpStates 945 }

apOutFragmentAttackPktsAvg OBJECT-TYPE
    SYNTAX      Gauge32
    MAX-ACCESS  read-only
    STATUS      current
    DESCRIPTION
	"Averaged number of outbound IP packets in an Fragmentation Attack"
    ::= { apTcpStates 946 }

apInBadipPktsAvg OBJECT-TYPE
    SYNTAX      Gauge32
    MAX-ACCESS  read-only
    STATUS      current
    DESCRIPTION
	"Averaged number of inbound IP packets with malformed IP Headers"
    ::= { apTcpStates 947 }

apOutBadipPktsAvg OBJECT-TYPE
    SYNTAX      Gauge32
    MAX-ACCESS  read-only
    STATUS      current
    DESCRIPTION
	"Averaged number of outbound IP packets with malformed IP Headers"
    ::= { apTcpStates 948 }

apInBadTcpPktsAvg OBJECT-TYPE
    SYNTAX      Gauge32
    MAX-ACCESS  read-only
    STATUS      current
    DESCRIPTION
	"Averaged number of inbound IP packets with bad TCP protocol/state"
    ::= { apTcpStates 949 }

apOutBadTcpPktsAvg OBJECT-TYPE
    SYNTAX      Gauge32
    MAX-ACCESS  read-only
    STATUS      current
    DESCRIPTION
	"Averaged number of outbound IP packets with bad TCP protocol/state"
    ::= { apTcpStates 950 }

apInBadUdpPktsAvg OBJECT-TYPE
    SYNTAX      Gauge32
    MAX-ACCESS  read-only
    STATUS      current
    DESCRIPTION
	"Averaged number of inbound UDP packets with malformed header or missing data"
    ::= { apTcpStates 951 }

apOutBadUdpPktsAvg OBJECT-TYPE
    SYNTAX      Gauge32
    MAX-ACCESS  read-only
    STATUS      current
    DESCRIPTION
	"Averaged number of outbound UDP packets with malformed header or missing data"
    ::= { apTcpStates 952 }

apInBadIcmpPktsAvg OBJECT-TYPE
    SYNTAX      Gauge32
    MAX-ACCESS  read-only
    STATUS      current
    DESCRIPTION
	"Averaged number of inbound ICMP packets with malformed header"
    ::= { apTcpStates 953 }

apOutBadIcmpPktsAvg OBJECT-TYPE
    SYNTAX      Gauge32
    MAX-ACCESS  read-only
    STATUS      current
    DESCRIPTION
	"Averaged number of outbound ICMP packets with malformed header"
    ::= { apTcpStates 954 }

apInBadOtherIpPktsAvg OBJECT-TYPE
    SYNTAX      Gauge32
    MAX-ACCESS  read-only
    STATUS      current
    DESCRIPTION
	"Averaged number of inbound IP packets of other protocol with malformed header"
    ::= { apTcpStates 955 }

apOutBadOtherIpPktsAvg OBJECT-TYPE
    SYNTAX      Gauge32
    MAX-ACCESS  read-only
    STATUS      current
    DESCRIPTION
	"Averaged number of outbound IP packets of other protocol with malformed header"
    ::= { apTcpStates 956 }

apInOverloadedAvg OBJECT-TYPE
    SYNTAX      Gauge32
    MAX-ACCESS  read-only
    STATUS      current
    DESCRIPTION
	"Averaged number of inbound packets overloading the protected IPs"
    ::= { apTcpStates 957 }

apOutOverloadedAvg OBJECT-TYPE
    SYNTAX      Gauge32
    MAX-ACCESS  read-only
    STATUS      current
    DESCRIPTION
	"Averaged number of outbound packets overloading the protected IPs"
    ::= { apTcpStates 958 }

apInLatencyAvg OBJECT-TYPE
    SYNTAX      Gauge32
    MAX-ACCESS  read-only
    STATUS      current
    DESCRIPTION
	"Averaged inbound Latency"
    ::= { apTcpStates 959 }

apOutLatencyAvg OBJECT-TYPE
    SYNTAX      Gauge32
    MAX-ACCESS  read-only
    STATUS      current
    DESCRIPTION
	"Averaged outbound Latency"
    ::= { apTcpStates 960 }

apInSmallPpsMax OBJECT-TYPE
    SYNTAX      Gauge32
    MAX-ACCESS  read-only
    STATUS      current
    DESCRIPTION
	"Peak inbound packets (256 bytes or less) per second processed. Dropped data is not included"
    ::= { apTcpStates 1001 }

apOutSmallPpsMax OBJECT-TYPE
    SYNTAX      Gauge32
    MAX-ACCESS  read-only
    STATUS      current
    DESCRIPTION
	"Peak outbound packets (256 bytes or less) per second processed. Dropped data is not included"
    ::= { apTcpStates 1002 }

apInMediumPpsMax OBJECT-TYPE
    SYNTAX      Gauge32
    MAX-ACCESS  read-only
    STATUS      current
    DESCRIPTION
	"Peak inbound packets (1024 bytes or less, but greater than 256 bytes) per second. Dropped data is not included"
    ::= { apTcpStates 1003 }

apOutMediumPpsMax OBJECT-TYPE
    SYNTAX      Gauge32
    MAX-ACCESS  read-only
    STATUS      current
    DESCRIPTION
	"Peak outbound packets (1024 bytes or less, but greater than 256 bytes) per second. Dropped data is not included"
    ::= { apTcpStates 1004 }

apInLargePpsMax OBJECT-TYPE
    SYNTAX      Gauge32
    MAX-ACCESS  read-only
    STATUS      current
    DESCRIPTION
	"Peak inbound packets (greater than 1024 bytes) per second. Dropped data is not included"
    ::= { apTcpStates 1005 }

apOutLargePpsMax OBJECT-TYPE
    SYNTAX      Gauge32
    MAX-ACCESS  read-only
    STATUS      current
    DESCRIPTION
	"Peak outbound packets (greater than 1024 bytes) per second. Dropped data is not included"
    ::= { apTcpStates 1006 }

apInFilteredBwthPercentMax OBJECT-TYPE
    SYNTAX      Gauge32
    MAX-ACCESS  read-only
    STATUS      current
    DESCRIPTION
	"Peak inbound dropped bandwidth divided by the actual bandwidth"
    ::= { apTcpStates 1007 }

apOutFilteredBwthPercentMax OBJECT-TYPE
    SYNTAX      Gauge32
    MAX-ACCESS  read-only
    STATUS      current
    DESCRIPTION
	"Peak outbound dropped bandwidth divided by the actual bandwidth"
    ::= { apTcpStates 1008 }

apInSynbacklogtallyMax OBJECT-TYPE
    SYNTAX      Gauge32
    MAX-ACCESS  read-only
    STATUS      current
    DESCRIPTION
	"Peak number of partially open TCP connections inbound"
    ::= { apTcpStates 1009 }

apOutSynbacklogtallyMax OBJECT-TYPE
    SYNTAX      Gauge32
    MAX-ACCESS  read-only
    STATUS      current
    DESCRIPTION
	"Peak number of partially open TCP connections outbound"
    ::= { apTcpStates 1010 }

apInConnectionMax OBJECT-TYPE
    SYNTAX      Gauge32
    MAX-ACCESS  read-only
    STATUS      current
    DESCRIPTION
	"Peak number of inbound TCP connections"
    ::= { apTcpStates 1011 }

apOutConnectionMax OBJECT-TYPE
    SYNTAX      Gauge32
    MAX-ACCESS  read-only
    STATUS      current
    DESCRIPTION
	"Peak number of outbound TCP connections"
    ::= { apTcpStates 1012 }

apInConnreqMax OBJECT-TYPE
    SYNTAX 	Gauge32
    MAX-ACCESS  read-only
    STATUS      current
    DESCRIPTION
	"Peak number of inbound TCP connection requests"
    ::= { apTcpStates 1013 }

apOutConnreqMax OBJECT-TYPE
    SYNTAX	Gauge32
    MAX-ACCESS  read-only
    STATUS      current
    DESCRIPTION
	"Peak number of outbound TCP connection requests"
    ::= { apTcpStates 1014 }

apInActiveHttpGetsMax OBJECT-TYPE
    SYNTAX	Gauge32
    MAX-ACCESS  read-only
    STATUS      current
    DESCRIPTION
	"Peak number of inbound HTTP page requests being processed"
    ::= { apTcpStates 1015 }

apOutActiveHttpGetsMax OBJECT-TYPE
    SYNTAX      Gauge32
    MAX-ACCESS  read-only
    STATUS      current
    DESCRIPTION
	"Peak number of outbound HTTP page requests being processed"
    ::= { apTcpStates 1016 }

apInProtectBwthPktsMax OBJECT-TYPE
    SYNTAX      Gauge32
    MAX-ACCESS  read-only
    STATUS      current
    DESCRIPTION
	"Peak inbound protected bandwifth"
    ::= { apTcpStates 1017 }

apOutProtectBwthPktsMax OBJECT-TYPE
    SYNTAX      Gauge32
    MAX-ACCESS  read-only
    STATUS      current
    DESCRIPTION
	"Peak outbound protected bandwifth"
    ::= { apTcpStates 1018 }

apInFloodPktsMax OBJECT-TYPE
    SYNTAX      Gauge32
    MAX-ACCESS  read-only
    STATUS      current
    DESCRIPTION
	"Peak number of inbound packets causing flooding"
    ::= { apTcpStates 1019 }

apOutFloodPktsMax OBJECT-TYPE
    SYNTAX      Gauge32
    MAX-ACCESS  read-only
    STATUS      current
    DESCRIPTION
	"Peak number of outbound packets causing flooding"
    ::= { apTcpStates 1020 }

apInBlockedProtocolPktsMax OBJECT-TYPE
    SYNTAX      Gauge32
    MAX-ACCESS  read-only
    STATUS      current
    DESCRIPTION
	"Peak number of inbound IP packets dropped by filter "
    ::= { apTcpStates 1021 }

apOutBlockedProtocolPktsMax OBJECT-TYPE
    SYNTAX      Gauge32
    MAX-ACCESS  read-only
    STATUS      current
    DESCRIPTION
	"Peak number of outbound IP packets dropped by filter"
    ::= { apTcpStates 1022 }

apInBlockedStatePktsMax OBJECT-TYPE
    SYNTAX      Gauge32
    MAX-ACCESS  read-only
    STATUS      current
    DESCRIPTION
	"Peak number of inbound IP packets dropped due to incorrect state"
    ::= { apTcpStates 1023 }

apOutBlockedStatePktsMax OBJECT-TYPE
    SYNTAX      Gauge32
    MAX-ACCESS  read-only
    STATUS      current
    DESCRIPTION
	"Peak number of outbound IP packets dropped due to incorrect state"
    ::= { apTcpStates 1024 }

apInIpAttackPktsMax OBJECT-TYPE
    SYNTAX      Gauge32
    MAX-ACCESS  read-only
    STATUS      current
    DESCRIPTION
	"Peak number of inbound IP packets in an IP Attack"
    ::= { apTcpStates 1025 }

apOutIpAttackPktsMax OBJECT-TYPE
    SYNTAX      Gauge32
    MAX-ACCESS  read-only
    STATUS      current
    DESCRIPTION
	"Peak number of outbound IP packets in an IP Attack"
    ::= { apTcpStates 1026 }

apInTcpAttackPktsMax OBJECT-TYPE
    SYNTAX      Gauge32
    MAX-ACCESS  read-only
    STATUS      current
    DESCRIPTION
	"Peak number of inbound IP packets in a TCP Attack"
    ::= { apTcpStates 1027 }

apOutTcpAttackPktsMax OBJECT-TYPE
    SYNTAX      Gauge32
    MAX-ACCESS  read-only
    STATUS      current
    DESCRIPTION
	"Peak number of outbound IP packets in a TCP Attack"
    ::= { apTcpStates 1028 }

apInUdpAttackPktsMax OBJECT-TYPE
    SYNTAX      Gauge32
    MAX-ACCESS  read-only
    STATUS      current
    DESCRIPTION
	"Peak number of inbound IP packets in a UDP Attack"
    ::= { apTcpStates 1029 }

apOutUdpAttackPktsMax OBJECT-TYPE
    SYNTAX      Gauge32
    MAX-ACCESS  read-only
    STATUS      current
    DESCRIPTION
	"Peak number of outbound IP packets in a UDP Attack"
    ::= { apTcpStates 1030 }

apInIcmpAttackPktsMax OBJECT-TYPE
    SYNTAX      Gauge32
    MAX-ACCESS  read-only
    STATUS      current
    DESCRIPTION
	"Peak number of inbound IP packets in a ICMP Attack"
    ::= { apTcpStates 1031 }

apOutIcmpAttackPktsMax OBJECT-TYPE
    SYNTAX      Gauge32
    MAX-ACCESS  read-only
    STATUS      current
    DESCRIPTION
	"Peak number of outbound IP packets in a ICMP Attack"
    ::= { apTcpStates 1032 }

apInOtherIpAttackPktsMax OBJECT-TYPE
    SYNTAX      Gauge32
    MAX-ACCESS  read-only
    STATUS      current
    DESCRIPTION
	"Peak number of inbound IP packets in an IP Attack using other protocols"
    ::= { apTcpStates 1033 }

apOutOtherIpAttackPktsMax OBJECT-TYPE
    SYNTAX      Gauge32
    MAX-ACCESS  read-only
    STATUS      current
    DESCRIPTION
	"Peak number of outbound IP packets in an IP Attack using other protocols"
    ::= { apTcpStates 1034 }

apInFragmentAttackPktsMax OBJECT-TYPE
    SYNTAX      Gauge32
    MAX-ACCESS  read-only
    STATUS      current
    DESCRIPTION
	"Peak number of inbound IP packets in an Fragmentation Attack"
    ::= { apTcpStates 1035 }

apOutFragmentAttackPktsMax OBJECT-TYPE
    SYNTAX      Gauge32
    MAX-ACCESS  read-only
    STATUS      current
    DESCRIPTION
	"Peak number of outbound IP packets in an Fragmentation Attack"
    ::= { apTcpStates 1036 }

apInBadipPktsMax OBJECT-TYPE
    SYNTAX      Gauge32
    MAX-ACCESS  read-only
    STATUS      current
    DESCRIPTION
	"Peak number of inbound IP packets with malformed IP Headers"
    ::= { apTcpStates 1037 }

apOutBadipPktsMax OBJECT-TYPE
    SYNTAX      Gauge32
    MAX-ACCESS  read-only
    STATUS      current
    DESCRIPTION
	"Peak number of outbound IP packets with malformed IP Headers"
    ::= { apTcpStates 1038 }

apInBadTcpPktsMax OBJECT-TYPE
    SYNTAX      Gauge32
    MAX-ACCESS  read-only
    STATUS      current
    DESCRIPTION
	"Peak number of inbound IP packets with bad TCP protocol/state"
    ::= { apTcpStates 1039 }

apOutBadTcpPktsMax OBJECT-TYPE
    SYNTAX      Gauge32
    MAX-ACCESS  read-only
    STATUS      current
    DESCRIPTION
	"Peak number of outbound IP packets with bad TCP protocol/state"
    ::= { apTcpStates 1040 }

apInBadUdpPktsMax OBJECT-TYPE
    SYNTAX      Gauge32
    MAX-ACCESS  read-only
    STATUS      current
    DESCRIPTION
	"Peak number of inbound UDP packets with malformed header or missing data"
    ::= { apTcpStates 1041 }

apOutBadUdpPktsMax OBJECT-TYPE
    SYNTAX      Gauge32
    MAX-ACCESS  read-only
    STATUS      current
    DESCRIPTION
	"Peak number of outbound UDP packets with malformed header or missing data"
    ::= { apTcpStates 1042 }

apInBadIcmpPktsMax OBJECT-TYPE
    SYNTAX      Gauge32
    MAX-ACCESS  read-only
    STATUS      current
    DESCRIPTION
	"Peak number of inbound ICMP packets with malformed header"
    ::= { apTcpStates 1043 }

apOutBadIcmpPktsMax OBJECT-TYPE
    SYNTAX      Gauge32
    MAX-ACCESS  read-only
    STATUS      current
    DESCRIPTION
	"Peak number of outbound ICMP packets with malformed header"
    ::= { apTcpStates 1044 }

apInBadOtherIpPktsMax OBJECT-TYPE
    SYNTAX      Gauge32
    MAX-ACCESS  read-only
    STATUS      current
    DESCRIPTION
	"Peak number of inbound IP packets of other protocol with malformed header"
    ::= { apTcpStates 1045 }

apOutBadOtherIpPktsMax OBJECT-TYPE
    SYNTAX      Gauge32
    MAX-ACCESS  read-only
    STATUS      current
    DESCRIPTION
	"Peak number of outbound IP packets of other protocol with malformed header"
    ::= { apTcpStates 1046 }

apInOverloadedMax OBJECT-TYPE
    SYNTAX      Gauge32
    MAX-ACCESS  read-only
    STATUS      current
    DESCRIPTION
	"Peak number of inbound packets overloading the protected IPs"
    ::= { apTcpStates 1047 }

apOutOverloadedMax OBJECT-TYPE
    SYNTAX      Gauge32
    MAX-ACCESS  read-only
    STATUS      current
    DESCRIPTION
	"Peak number of outbound packets overloading the protected IPs"
    ::= { apTcpStates 1048 }

apInLatencyMax OBJECT-TYPE
    SYNTAX      Gauge32
    MAX-ACCESS  read-only
    STATUS      current
    DESCRIPTION
	"Peak inbound Latency"
    ::= { apTcpStates 1049 }

apOutLatencyMax OBJECT-TYPE
    SYNTAX      Gauge32
    MAX-ACCESS  read-only
    STATUS      current
    DESCRIPTION
	"Peak outbound Latency"
    ::= { apTcpStates 1050 }

apIfStates OBJECT IDENTIFIER ::= { apState 3 }

apMgmtIfLinkModeState OBJECT-TYPE
    SYNTAX      DisplayString
    MAX-ACCESS  read-only
    STATUS      current
    DESCRIPTION
        "Speed and duplex of the appliance management interface"
    ::= { apIfStates 1 }

apIntIfLinkModeState OBJECT-TYPE
    SYNTAX      DisplayString
    MAX-ACCESS  read-only
    STATUS      current
    DESCRIPTION
        "Speed and duplex of the appliance internet interface"
    ::= { apIfStates 2 }

apProtIfLinkModeState OBJECT-TYPE
    SYNTAX      DisplayString
    MAX-ACCESS  read-only
    STATUS      current
    DESCRIPTION
        "Speed and duplex of the appliance Protected Interface"
    ::= { apIfStates 3 }

apMgmtIfLinkFCState OBJECT-TYPE
    SYNTAX      DisplayString
    MAX-ACCESS  read-only
    STATUS      current
    DESCRIPTION
        "Flow Control setting of the appliance management interface"
    ::= { apIfStates 4 }

apIntIfLinkFCState OBJECT-TYPE
    SYNTAX      DisplayString
    MAX-ACCESS  read-only
    STATUS      current
    DESCRIPTION
        "Flow Control setting of the appliance internet interface"
    ::= { apIfStates 5 }

apProtIfLinkFCState OBJECT-TYPE
    SYNTAX      DisplayString
    MAX-ACCESS  read-only
    STATUS      current
    DESCRIPTION
        "Flow Control setting of the appliance Protected Interface"
    ::= { apIfStates 6 }


apHighAvailabilityInfo OBJECT IDENTIFIER ::= { apState 4 }

apHaState OBJECT-TYPE
    SYNTAX INTEGER {
	unknown(1),
	probe(2),
	standby(3),
	active(4),
	cripple(5),
	standalone(6),
	activesec(7)
    }
    MAX-ACCESS  read-only
    STATUS      current
    DESCRIPTION
        "Current high availability state"
    ::= { apHighAvailabilityInfo 1 }

apHaPartnerList OBJECT-TYPE
    SYNTAX      DisplayString
    MAX-ACCESS  read-only
    STATUS      current
    DESCRIPTION
        "Comma-separated list of redundant (fail-over) partners"
    ::= { apHighAvailabilityInfo 2 }

apHaPartnerTime OBJECT-TYPE
    SYNTAX      TimeInterval
    MAX-ACCESS  read-only
    STATUS      current
    DESCRIPTION
        "Elapsed time since last redundant partner contact"
    ::= { apHighAvailabilityInfo 3 }

apStalledFlag OBJECT-TYPE
    SYNTAX      TruthValue
    MAX-ACCESS  read-only
    STATUS      current
    DESCRIPTION
        "TRUE if DDoS Secure engine stalled"
    ::= { apState 5 }

apOutputErrorIIFlag OBJECT-TYPE
    SYNTAX      TruthValue
    MAX-ACCESS  read-only
    STATUS      current
    DESCRIPTION
        "TRUE if DDoS Secure is having trouble transmitting packets over Internet Interface"
    ::= { apState 6 }

apOutputErrorPIFlag OBJECT-TYPE
    SYNTAX      TruthValue
    MAX-ACCESS  read-only
    STATUS      current
    DESCRIPTION
        "TRUE if DDoS Secure is having trouble transmitting packet over Protected Interfaces"
    ::= { apState 7 }

apOutputErrorMIFlag OBJECT-TYPE
    SYNTAX      TruthValue
    MAX-ACCESS  read-only
    STATUS      current
    DESCRIPTION
        "TRUE if DDoS Secure is having trouble transmitting packet over Management Interfaces"
    ::= { apState 8 }

apNewConfigFlag OBJECT-TYPE
    SYNTAX      TruthValue
    MAX-ACCESS  read-only
    STATUS      current
    DESCRIPTION
        "TRUE if DDoS Secure configuration has just been updated"
    ::= { apState 9 }

apNotLicensedFlag OBJECT-TYPE
    SYNTAX      TruthValue
    MAX-ACCESS  read-only
    STATUS      current
    DESCRIPTION
        "TRUE if DDoS Secure has not yet been authorized for use"
    ::= { apState 10 }

apMacTableFullFlag OBJECT-TYPE
    SYNTAX      TruthValue
    MAX-ACCESS  read-only
    STATUS      current
    DESCRIPTION
        "TRUE if DDoS Secure's internal MAC table space is full"
    ::= { apState 11 }

apProtectedTableFullFlag OBJECT-TYPE
    SYNTAX      TruthValue
    MAX-ACCESS  read-only
    STATUS      current
    DESCRIPTION
        "TRUE if DDoS Secure's internal protected IP table space is full"
    ::= { apState 12 }

apIncidentTableFullFlag OBJECT-TYPE
    SYNTAX      TruthValue
    MAX-ACCESS  read-only
    STATUS      current
    DESCRIPTION
        "TRUE if DDoS Secure's internal incident table space is full"
    ::= { apState 13 }

apTcpTableFullFlag OBJECT-TYPE
    SYNTAX      TruthValue
    MAX-ACCESS  read-only
    STATUS      current
    DESCRIPTION
        "TRUE if DDoS Secure's internal TCP table space is full"
    ::= { apState 14 }

apUdpTableFullFlag OBJECT-TYPE
    SYNTAX      TruthValue
    MAX-ACCESS  read-only
    STATUS      current
    DESCRIPTION
        "TRUE if DDoS Secure's internal UDP table space is full"
    ::= { apState 15 }

apIcmpTableFullFlag OBJECT-TYPE
    SYNTAX      TruthValue
    MAX-ACCESS  read-only
    STATUS      current
    DESCRIPTION
        "TRUE if DDoS Secure's internal ICMP table space is full"
    ::= { apState 16 }

apOtherIpTableFullFlag OBJECT-TYPE
    SYNTAX      TruthValue
    MAX-ACCESS  read-only
    STATUS      current
    DESCRIPTION
        "TRUE if DDoS Secure's internal other IP table space is full"
    ::= { apState 17 }

apFragTableFullFlag OBJECT-TYPE
    SYNTAX      TruthValue
    MAX-ACCESS  read-only
    STATUS      current
    DESCRIPTION
        "TRUE if DDoS Secure's internal fragment table space is full"
    ::= { apState 18 }

apFtpTableFullFlag OBJECT-TYPE
    SYNTAX      TruthValue
    MAX-ACCESS  read-only
    STATUS      current
    DESCRIPTION
        "TRUE if DDoS Secure's internal ftp tracking table space is full"
    ::= { apState 19 }

apBlockedTableFullFlag OBJECT-TYPE
    SYNTAX      TruthValue
    MAX-ACCESS  read-only
    STATUS      current
    DESCRIPTION
        "TRUE if DDoS Secure's internal blocked ip table space is full"
    ::= { apState 20 }

apShortCircuitFlag OBJECT-TYPE
    SYNTAX      TruthValue
    MAX-ACCESS  read-only
    STATUS      current
    DESCRIPTION
        "TRUE if DDoS Secure has detected an external link between
         the Internet and Protected Interfaces"
    ::= { apState 21 }

apInternetIfDisconnectedFlag OBJECT-TYPE
    SYNTAX      TruthValue
    MAX-ACCESS  read-only
    STATUS      current
    DESCRIPTION
        "TRUE if DDoS Secure has detected that the Internet interface
         has been disconnected"
    ::= { apState 22 }

apProtectedIfDisconnectedFlag OBJECT-TYPE
    SYNTAX      TruthValue
    MAX-ACCESS  read-only
    STATUS      current
    DESCRIPTION
        "TRUE if DDoS Secure has detected that the Protected interface
         has been disconnected"
    ::= { apState 23 }

apMgmtIfDisconnectedFlag OBJECT-TYPE
    SYNTAX      TruthValue
    MAX-ACCESS  read-only
    STATUS      current
    DESCRIPTION
        "TRUE if DDoS Secure has detected that the Management interface
         has been disconnected"
    ::= { apState 24 }

apUpgradingFlag OBJECT-TYPE
    SYNTAX      TruthValue
    MAX-ACCESS  read-only
    STATUS      current
    DESCRIPTION
        "TRUE if DDoS Secure is in the process of a software upgrade"
    ::= { apState 25 }

apProtectedIfTrafficFlag OBJECT-TYPE
    SYNTAX      TruthValue
    MAX-ACCESS  read-only
    STATUS      current
    DESCRIPTION
        "TRUE if DDoS Secure detects traffic on the Protected interface
         while in Analyze-Tap mode"
    ::= { apState 26 }

apRoutingLoopFlag OBJECT-TYPE
    SYNTAX      TruthValue
    MAX-ACCESS  read-only
    STATUS      current
    DESCRIPTION
        "TRUE if DDoS Secure detects apossible alternate network path
         around the appliance"
    ::= { apState 27 }

apOfflineFlag OBJECT-TYPE
    SYNTAX      TruthValue
    MAX-ACCESS  read-only
    STATUS      current
    DESCRIPTION
        "TRUE if the DDoS Secure engine is no longer running, a brief
         state during DDoS Secure restart sequence"
    ::= { apState 28 }

apStateLearningFlag OBJECT-TYPE
    SYNTAX      TruthValue
    MAX-ACCESS  read-only
    STATUS      current
    DESCRIPTION
        "TRUE if DDoS Secure is in state learning mode"
    ::= { apState 29 }

apSupportExpiredFlag OBJECT-TYPE
    SYNTAX      TruthValue
    MAX-ACCESS  read-only
    STATUS      current
    DESCRIPTION
        "TRUE if DDoS Secure's support period has expired"
    ::= { apState 30 }

apSevereLoadingFlag OBJECT-TYPE
    SYNTAX      TruthValue
    MAX-ACCESS  read-only
    STATUS      current
    DESCRIPTION
        "TRUE if DDoS Secure detects that packets have been Dropped due
         to heavy loading"
    ::= { apState 31 }

apMacMisconfiguredFlag OBJECT-TYPE
    SYNTAX      TruthValue
    MAX-ACCESS  read-only
    STATUS      current
    DESCRIPTION
        "TRUE if DDoS Secure detects that a ethernet address configured
         for one interface is detected on another interface"
    ::= { apState 32 }

apIfMisconfiguredFlag OBJECT-TYPE
    SYNTAX      TruthValue
    MAX-ACCESS  read-only
    STATUS      current
    DESCRIPTION
        "TRUE if the Internet and Protected interfaces are configured
	differently, and a Fail-Safe card is installed"
    ::= { apState 33 }

apInternetIfLinkDownFlag OBJECT-TYPE
    SYNTAX      TruthValue
    MAX-ACCESS  read-only
    STATUS      current
    DESCRIPTION
        "TRUE if DDoS Secure has detected that one of the links on the Internet interface
         has been disconnected"
    ::= { apState 34 }

apProtectedIfLinkDownFlag OBJECT-TYPE
    SYNTAX      TruthValue
    MAX-ACCESS  read-only
    STATUS      current
    DESCRIPTION
        "TRUE if DDoS Secure has detected that one of the links on the protected IP interface
         has been disconnected"
    ::= { apState 35 }

apDatashareIfDisconnectedFlag OBJECT-TYPE
    SYNTAX      TruthValue
    MAX-ACCESS  read-only
    STATUS      current
    DESCRIPTION
        "TRUE if DDoS Secure has detected that the Data Share interface
         has been disconnected"
    ::= { apState 36 }

apDiskFailingFlag OBJECT-TYPE
    SYNTAX      TruthValue
    MAX-ACCESS  read-only
    STATUS      current
    DESCRIPTION
        "TRUE if DDoS Secure has a disk failing"
    ::= { apState 37 }

apPsuFailingFlag OBJECT-TYPE
    SYNTAX      TruthValue
    MAX-ACCESS  read-only
    STATUS      current
    DESCRIPTION
        "TRUE if DDoS Secure has a PSU failing"
    ::= { apState 38 }

apFanFailingFlag OBJECT-TYPE
    SYNTAX      TruthValue
    MAX-ACCESS  read-only
    STATUS      current
    DESCRIPTION
        "TRUE if DDoS Secure has a Fan failing"
    ::= { apState 39 }

apConfigXferFailFlag OBJECT-TYPE
    SYNTAX      TruthValue
    MAX-ACCESS  read-only
    STATUS      current
    DESCRIPTION
        "TRUE if DDoS Secure has failed to transfer a confuguration"
    ::= { apState 40 }

apMissingRequiredPartnerFlag OBJECT-TYPE
    SYNTAX      TruthValue
    MAX-ACCESS  read-only
    STATUS      current
    DESCRIPTION
        "TRUE if a required partner is not active"
    ::= { apState 41 }

apBgpMisconfiguredIpFlag OBJECT-TYPE
    SYNTAX      TruthValue
    MAX-ACCESS  read-only
    STATUS      current
    DESCRIPTION
        "TRUE if BGP traffic detected to undefined protected IP"
    ::= { apState 42 }


apStats OBJECT IDENTIFIER ::= { jddsAppliance 3 }


apSessionTallies OBJECT IDENTIFIER ::= { apStats 1 }

apInTcpConnTally OBJECT-TYPE
    SYNTAX      Gauge32
    MAX-ACCESS  read-only
    STATUS      current
    DESCRIPTION
        "Current number of established TCP sessions across appliance originated by an internet-side client"
    ::= { apSessionTallies 1 }

apOutTcpConnTally OBJECT-TYPE
    SYNTAX      Gauge32
    MAX-ACCESS  read-only
    STATUS      current
    DESCRIPTION
        "Current number of established TCP sessions across appliance originated by a protected IPs"
    ::= { apSessionTallies 2 }

apInSynBacklogTally OBJECT-TYPE
    SYNTAX      Gauge32
    MAX-ACCESS  read-only
    STATUS      current
    DESCRIPTION
        "Current number of half open (not yet established) TCP sessions originated by an internet-side client"
    ::= { apSessionTallies 3 }

apUdpSessionTally OBJECT-TYPE
    SYNTAX      Gauge32
    MAX-ACCESS  read-only
    STATUS      current
    DESCRIPTION
        "Current number of UDP sessions across appliance"
    ::= { apSessionTallies 4 }

apIcmpSessionTally OBJECT-TYPE
    SYNTAX      Gauge32
    MAX-ACCESS  read-only
    STATUS      current
    DESCRIPTION
        "Current number of ICMP sessions across appliance"
    ::= { apSessionTallies 5 }

apOtherIpSessionTally OBJECT-TYPE
    SYNTAX      Gauge32
    MAX-ACCESS  read-only
    STATUS      current
    DESCRIPTION
        "Current number of other IP sessions across appliance"
    ::= { apSessionTallies 6 }


apSummaryBytes OBJECT IDENTIFIER ::= { apStats 3 }

apInTotalBytesCnt OBJECT-TYPE
    SYNTAX      Counter64
    MAX-ACCESS  read-only
    STATUS      current
    DESCRIPTION
        "Total number of bytes seen inbound by DDoS Secure"
    ::= { apSummaryBytes 1 }

apOutTotalBytesCnt OBJECT-TYPE
    SYNTAX      Counter64
    MAX-ACCESS  read-only
    STATUS      current
    DESCRIPTION
        "Total number of bytes seen outbound by DDoS Secure"
    ::= { apSummaryBytes 2 }

apInDroppedBytesCnt OBJECT-TYPE
    SYNTAX      Counter64
    MAX-ACCESS  read-only
    STATUS      current
    DESCRIPTION
        "Total number of bytes Dropped inbound by DDoS Secure"
    ::= { apSummaryBytes 3 }

apOutDroppedBytesCnt OBJECT-TYPE
    SYNTAX      Counter64
    MAX-ACCESS  read-only
    STATUS      current
    DESCRIPTION
        "Total number of bytes Dropped outbound by DDoS Secure"
    ::= { apSummaryBytes 4 }

apInCharmDroppedBytesCnt OBJECT-TYPE
    SYNTAX      Counter64
    MAX-ACCESS  read-only
    STATUS      current
    DESCRIPTION
        "Total number of bytes Dropped inbound using CHARM heuristics"
    ::= { apSummaryBytes 5 }

apOutCharmDroppedBytesCnt OBJECT-TYPE
    SYNTAX      Counter64
    MAX-ACCESS  read-only
    STATUS      current
    DESCRIPTION
        "Total number of bytes Dropped outbound using CHARM heuristics"
    ::= { apSummaryBytes 6 }


apSummaryPpsRates OBJECT IDENTIFIER ::= { apStats 4 }

apInTotalPpsMax OBJECT-TYPE
    SYNTAX      Gauge32
    MAX-ACCESS  read-only
    STATUS      current
    DESCRIPTION
        "Peak aggregate packets/sec traffic rate inbound since last
         restart or reset"
    ::= { apSummaryPpsRates 1 }

apOutTotalPpsMax OBJECT-TYPE
    SYNTAX      Gauge32
    MAX-ACCESS  read-only
    STATUS      current
    DESCRIPTION
        "Peak aggregate packets/sec traffic rate outbound since last
         restart or reset"
    ::= { apSummaryPpsRates 2 }

apInDroppedPpsMax OBJECT-TYPE
    SYNTAX      Gauge32
    MAX-ACCESS  read-only
    STATUS      current
    DESCRIPTION
        "Peak packets/sec Drop rate inbound by DDoS Secure since last
         restart or reset"
    ::= { apSummaryPpsRates 3 }

apOutDroppedPpsMax OBJECT-TYPE
    SYNTAX      Gauge32
    MAX-ACCESS  read-only
    STATUS      current
    DESCRIPTION
        "Peak packets/sec Drop rate outbound by DDoS Secure since last
         restart or reset"
    ::= { apSummaryPpsRates 4 }


apSummaryBpsRates OBJECT IDENTIFIER ::= { apStats 5 }

apInTotalBpsMax OBJECT-TYPE
    SYNTAX      Gauge32
    MAX-ACCESS  read-only
    STATUS      current
    DESCRIPTION
        "Peak aggregate bits per second traffic rate inbound since last
         restart or reset"
    ::= { apSummaryBpsRates 1 }

apOutTotalBpsMax OBJECT-TYPE
    SYNTAX      Gauge32
    MAX-ACCESS  read-only
    STATUS      current
    DESCRIPTION
        "Peak aggregate bits per second traffic rate outbound since last
         restart or reset"
    ::= { apSummaryBpsRates 2 }

apInDroppedBpsMax OBJECT-TYPE
    SYNTAX      Gauge32
    MAX-ACCESS  read-only
    STATUS      current
    DESCRIPTION
        "Peak bits per second Drop rate inbound by DDoS Secure since last
         restart or reset"
    ::= { apSummaryBpsRates 3 }

apOutDroppedBpsMax OBJECT-TYPE
    SYNTAX      Gauge32
    MAX-ACCESS  read-only
    STATUS      current
    DESCRIPTION
        "Peak bits per second Drop rate outbound by DDoS Secure since last
         restart or reset"
    ::= { apSummaryBpsRates 4 }

apInCharmDroppedBpsMax OBJECT-TYPE
    SYNTAX      Gauge32
    MAX-ACCESS  read-only
    STATUS      current
    DESCRIPTION
        "Peak bits per second Drop rate inbound using CHARM heuristics since
         last restart or reset"
    ::= { apSummaryBpsRates 5 }

apOutCharmDroppedBpsMax OBJECT-TYPE
    SYNTAX      Gauge32
    MAX-ACCESS  read-only
    STATUS      current
    DESCRIPTION
        "Peak bits per second Drop rate outbound using CHARM heuristics since
         last restart or reset"
    ::= { apSummaryBpsRates 6 }


apAttackPkts OBJECT IDENTIFIER ::= { apStats 6 }

apInProtectBwthPktsCnt OBJECT-TYPE
    SYNTAX      Counter32
    MAX-ACCESS  read-only
    STATUS      current
    DESCRIPTION
        "Total number of packets identified inbound in protect bandwidth defense"
    ::= { apAttackPkts 1 }

apOutProtectBwthPktsCnt OBJECT-TYPE
    SYNTAX      Counter32
    MAX-ACCESS  read-only
    STATUS      current
    DESCRIPTION
        "Total number of packets identified outbound in protect bandwidth defense"
    ::= { apAttackPkts 2 }

apInFloodPktsCnt OBJECT-TYPE
    SYNTAX      Counter32
    MAX-ACCESS  read-only
    STATUS      current
    DESCRIPTION
        "Total number of packets identified inbound in flood defense"
    ::= { apAttackPkts 3 }

apOutFloodPktsCnt OBJECT-TYPE
    SYNTAX      Counter32
    MAX-ACCESS  read-only
    STATUS      current
    DESCRIPTION
        "Total number of packets identified outbound in flood defense"
    ::= { apAttackPkts 4 }

apInBlockedProtocolPktsCnt OBJECT-TYPE
    SYNTAX      Counter32
    MAX-ACCESS  read-only
    STATUS      current
    DESCRIPTION
        "Total number of packets identified inbound in blocked Protocol defense"
    ::= { apAttackPkts 5 }

apOutBlockedProtocolPktsCnt OBJECT-TYPE
    SYNTAX      Counter32
    MAX-ACCESS  read-only
    STATUS      current
    DESCRIPTION
        "Total number of packets identified outbound in blocked Protocol defense"
    ::= { apAttackPkts 6 }

apInBlockedStatePktsCnt OBJECT-TYPE
    SYNTAX      Counter32
    MAX-ACCESS  read-only
    STATUS      current
    DESCRIPTION
        "Total number of packets identified inbound in blocked state defense"
    ::= { apAttackPkts 7 }

apOutBlockedStatePktsCnt OBJECT-TYPE
    SYNTAX      Counter32
    MAX-ACCESS  read-only
    STATUS      current
    DESCRIPTION
        "Total number of packets identified outbound in blocked state defense"
    ::= { apAttackPkts 8 }

apInIpAttackPktsCnt OBJECT-TYPE
    SYNTAX      Counter32
    MAX-ACCESS  read-only
    STATUS      current
    DESCRIPTION
        "Total number of packets identified inbound in IP Attack defense"
    ::= { apAttackPkts 9 }

apOutIpAttackPktsCnt OBJECT-TYPE
    SYNTAX      Counter32
    MAX-ACCESS  read-only
    STATUS      current
    DESCRIPTION
        "Total number of packets identified outbound in IP Attack defense"
    ::= { apAttackPkts 10 }

apInTcpAttackPktsCnt OBJECT-TYPE
    SYNTAX      Counter32
    MAX-ACCESS  read-only
    STATUS      current
    DESCRIPTION
        "Total number of packets identified inbound in TCP Attack defense"
    ::= { apAttackPkts 11 }

apOutTcpAttackPktsCnt OBJECT-TYPE
    SYNTAX      Counter32
    MAX-ACCESS  read-only
    STATUS      current
    DESCRIPTION
        "Total number of packets identified outbound in TCP Attack defense"
    ::= { apAttackPkts 12 }

apInUdpAttackPktsCnt OBJECT-TYPE
    SYNTAX      Counter32
    MAX-ACCESS  read-only
    STATUS      current
    DESCRIPTION
        "Total number of packets identified inbound in UDP Attack defense"
    ::= { apAttackPkts 13 }

apOutUdpAttackPktsCnt OBJECT-TYPE
    SYNTAX      Counter32
    MAX-ACCESS  read-only
    STATUS      current
    DESCRIPTION
        "Total number of packets identified outbound in UDP Attack defense"
    ::= { apAttackPkts 14 }

apInIcmpAttackPktsCnt OBJECT-TYPE
    SYNTAX      Counter32
    MAX-ACCESS  read-only
    STATUS      current
    DESCRIPTION
        "Total number of packets identified inbound in ICMP Attack defense"
    ::= { apAttackPkts 15 }

apOutIcmpAttackPktsCnt OBJECT-TYPE
    SYNTAX      Counter32
    MAX-ACCESS  read-only
    STATUS      current
    DESCRIPTION
        "Total number of packets identified outbound in ICMP Attack defense"
    ::= { apAttackPkts 16 }

apInOtherIpAttackPktsCnt OBJECT-TYPE
    SYNTAX      Counter32
    MAX-ACCESS  read-only
    STATUS      current
    DESCRIPTION
        "Total number of packets identified inbound in other IP Attack defense"
    ::= { apAttackPkts 17 }

apOutOtherIpAttackPktsCnt OBJECT-TYPE
    SYNTAX      Counter32
    MAX-ACCESS  read-only
    STATUS      current
    DESCRIPTION
        "Total number of packets identified outbound in other IP Attack defense"
    ::= { apAttackPkts 18 }

apInFragmentAttackPktsCnt OBJECT-TYPE
    SYNTAX      Counter32
    MAX-ACCESS  read-only
    STATUS      current
    DESCRIPTION
        "Total number of packets identified inbound in fragment Attack defense"
    ::= { apAttackPkts 19 }

apOutFragmentAttackPktsCnt OBJECT-TYPE
    SYNTAX      Counter32
    MAX-ACCESS  read-only
    STATUS      current
    DESCRIPTION
        "Total number of packets identified outbound in fragment Attack defense"
    ::= { apAttackPkts 20 }

apInBadIpPktsCnt OBJECT-TYPE
    SYNTAX      Counter32
    MAX-ACCESS  read-only
    STATUS      current
    DESCRIPTION
        "Total number of packets identified inbound in bad IP defense"
    ::= { apAttackPkts 21 }

apOutBadIpPktsCnt OBJECT-TYPE
    SYNTAX      Counter32
    MAX-ACCESS  read-only
    STATUS      current
    DESCRIPTION
        "Total number of packets identified outbound in bad IP defense"
    ::= { apAttackPkts 22 }

apInBadTcpPktsCnt OBJECT-TYPE
    SYNTAX      Counter32
    MAX-ACCESS  read-only
    STATUS      current
    DESCRIPTION
        "Total number of packets identified inbound in bad TCP defense"
    ::= { apAttackPkts 23 }

apOutBadTcpPktsCnt OBJECT-TYPE
    SYNTAX      Counter32
    MAX-ACCESS  read-only
    STATUS      current
    DESCRIPTION
        "Total number of packets identified outbound in bad TCP defense"
    ::= { apAttackPkts 24 }

apInBadUdpPktsCnt OBJECT-TYPE
    SYNTAX      Counter32
    MAX-ACCESS  read-only
    STATUS      current
    DESCRIPTION
        "Total number of packets identified inbound in bad UDP defense"
    ::= { apAttackPkts 25 }

apOutBadUdpPktsCnt OBJECT-TYPE
    SYNTAX      Counter32
    MAX-ACCESS  read-only
    STATUS      current
    DESCRIPTION
        "Total number of packets identified outbound in bad UDP defense"
    ::= { apAttackPkts 26 }

apInBadIcmpPktsCnt OBJECT-TYPE
    SYNTAX      Counter32
    MAX-ACCESS  read-only
    STATUS      current
    DESCRIPTION
        "Total number of packets identified inbound in bad ICMP defense"
    ::= { apAttackPkts 27 }

apOutBadIcmpPktsCnt OBJECT-TYPE
    SYNTAX      Counter32
    MAX-ACCESS  read-only
    STATUS      current
    DESCRIPTION
        "Total number of packets identified outbound in bad ICMP defense"
    ::= { apAttackPkts 28 }

apInBadOtherIpPktsCnt OBJECT-TYPE
    SYNTAX      Counter32
    MAX-ACCESS  read-only
    STATUS      current
    DESCRIPTION
        "Total number of packets identified inbound in bad other IP defense"
    ::= { apAttackPkts 29 }

apOutBadOtherIpPktsCnt OBJECT-TYPE
    SYNTAX      Counter32
    MAX-ACCESS  read-only
    STATUS      current
    DESCRIPTION
        "Total number of packets identified outbound in bad other IP defense"
    ::= { apAttackPkts 30 }

apInTotalPpsCnt OBJECT-TYPE
    SYNTAX      Counter32
    MAX-ACCESS  read-only
    STATUS      current
    DESCRIPTION
	"Total packets/sec traffic rate inbound since last restart or reset"
    ::= { apAttackPkts 33 }

apOutTotalPpsCnt OBJECT-TYPE
    SYNTAX      Counter32
    MAX-ACCESS  read-only
    STATUS      current
    DESCRIPTION
	"Total packets/sec traffic rate outbound since last
         restart or reset"
    ::= { apAttackPkts 34 }

apInSmallPpsCnt OBJECT-TYPE
    SYNTAX      Counter32
    MAX-ACCESS  read-only
    STATUS      current
    DESCRIPTION
	"Total inbound packets (256 bytes or less) per second processed. Dropped data is not included"
    ::= { apAttackPkts 35 }

apOutSmallPpsCnt OBJECT-TYPE
    SYNTAX      Counter32
    MAX-ACCESS  read-only
    STATUS      current
    DESCRIPTION
	"Total outbound packets (256 bytes or less) per second processed. Dropped data is not included"
    ::= { apAttackPkts 36 }

apInMediumPpsCnt OBJECT-TYPE
    SYNTAX      Counter32
    MAX-ACCESS  read-only
    STATUS      current
    DESCRIPTION
	"Total inbound packets (1024 bytes or less, but greater than 256 bytes) per second. Dropped data is not included"
    ::= { apAttackPkts 37 }

apOutMediumPpsCnt OBJECT-TYPE
    SYNTAX      Counter32
    MAX-ACCESS  read-only
    STATUS      current
    DESCRIPTION
	"Total outbound packets (1024 bytes or less, but greater than 256 bytes) per second. Dropped data is not included"
    ::= { apAttackPkts 38 }

apInLargePpsCnt OBJECT-TYPE
    SYNTAX      Counter32
    MAX-ACCESS  read-only
    STATUS      current
    DESCRIPTION
	"Total inbound packets (greater than 1024 bytes) per second. Dropped data is not included"
    ::= { apAttackPkts 39 }

apOutLargePpsCnt OBJECT-TYPE
    SYNTAX      Counter32
    MAX-ACCESS  read-only
    STATUS      current
    DESCRIPTION
	"Total outbound packets (greater than 1024 bytes) per second. Dropped data is not included"
    ::= { apAttackPkts 40 }

apInDroppedPpsCnt OBJECT-TYPE
    SYNTAX      Counter32
    MAX-ACCESS  read-only
    STATUS      current
    DESCRIPTION
	"Total number of input packets Dropped per second"
    ::= { apAttackPkts 43 }

apOutDroppedPpsCnt OBJECT-TYPE
    SYNTAX      Counter32
    MAX-ACCESS  read-only
    STATUS      current
    DESCRIPTION
	"Total number of output packets Dropped per second"
     ::= { apAttackPkts 44 }

apInFilteredBwthPercentCnt OBJECT-TYPE
    SYNTAX      Counter32
    MAX-ACCESS  read-only
    STATUS      current
    DESCRIPTION
	"Total inbound dropped bandwidth divided by the actual bandwidth"
    ::= { apAttackPkts 45 }

apOutFilteredBwthPercentCnt OBJECT-TYPE
    SYNTAX      Counter32
    MAX-ACCESS  read-only
    STATUS      current
    DESCRIPTION
	"Total outbound dropped bandwidth divided by the actual bandwidth"
    ::= { apAttackPkts 46 }

apInConnreqCnt OBJECT-TYPE
    SYNTAX      Counter32
    MAX-ACCESS  read-only
    STATUS      current
    DESCRIPTION
	"Total number of inbound TCP connection requests"
    ::= { apAttackPkts 47 }

apOutConnreqCnt OBJECT-TYPE
    SYNTAX      Counter32
    MAX-ACCESS  read-only
    STATUS      current
    DESCRIPTION
	"Total number of outbound TCP connection requests"
    ::= { apAttackPkts 48 }

apInOverloadedCnt OBJECT-TYPE
    SYNTAX      Counter32
    MAX-ACCESS  read-only
    STATUS      current
    DESCRIPTION
	"Total number of inbound packets overloading the protected IPs"
    ::= { apAttackPkts 49 }

apOutOverloadedCnt OBJECT-TYPE
    SYNTAX      Counter32
    MAX-ACCESS  read-only
    STATUS      current
    DESCRIPTION
	"Total number of outbound packets overloading the protected IPs"
    ::= { apAttackPkts 50 }

apWorstOffenderTable OBJECT-TYPE
    SYNTAX SEQUENCE OF ApWorstOffenderEntry
    MAX-ACCESS  not-accessible
    STATUS      current
    DESCRIPTION
        "Table of worst offender statistics"
    ::= { apStats 7 }

apWorstOffenderEntry OBJECT-TYPE
    SYNTAX      ApWorstOffenderEntry
    MAX-ACCESS  not-accessible
    STATUS      current
    DESCRIPTION
        "A row consisting of a worst offender for a given reason and their statistics"
    INDEX       { apWorstOffenderInetAddressType, apWorstOffenderInetAddress, apWorstOffenderReason }
    ::= { apWorstOffenderTable 1 }

ApWorstOffenderEntry ::= SEQUENCE {
    apWorstOffenderInetAddressType
	InetAddressType,
    apWorstOffenderInetAddress
	InetAddress,
    apWorstOffenderReason
	DefenseType,
    apWorstOffenderLastTime
	DateAndTime,
    apWorstOffenderCount
	Counter32
}

apWorstOffenderInetAddressType OBJECT-TYPE
    SYNTAX InetAddressType
    MAX-ACCESS  not-accessible
    STATUS      current
    DESCRIPTION
        "IP address type of the offender"
    ::= {apWorstOffenderEntry 1}


apWorstOffenderInetAddress OBJECT-TYPE
    SYNTAX InetAddress (SIZE (0..47))
    MAX-ACCESS	not-accessible
    STATUS	current
    DESCRIPTION
	"IP Address of offender"
    ::= {apWorstOffenderEntry 2}

apWorstOffenderReason OBJECT-TYPE
    SYNTAX DefenseType
    MAX-ACCESS	not-accessible
    STATUS	current
    DESCRIPTION
	"Type of Attack"
    ::= {apWorstOffenderEntry 3}

apWorstOffenderLastTime OBJECT-TYPE
    SYNTAX DateAndTime
    MAX-ACCESS	read-only
    STATUS	current
    DESCRIPTION
	"Time of latest Attack (of given type)"
    ::= {apWorstOffenderEntry 4}

apWorstOffenderCount OBJECT-TYPE
    SYNTAX Counter32
    MAX-ACCESS	read-only
    STATUS	current
    DESCRIPTION
	"Total number of offenses (of given type)"
    ::= {apWorstOffenderEntry 5}

apLogFileTable OBJECT-TYPE
    SYNTAX SEQUENCE OF ApLogFileEntry
    MAX-ACCESS  not-accessible
    STATUS      current
    DESCRIPTION
        "Table of log file entries"
    ::= { jddsAppliance 4 }

apLogFileEntry OBJECT-TYPE
    SYNTAX      ApLogFileEntry
    MAX-ACCESS  not-accessible
    STATUS      current
    DESCRIPTION
        "A row consisting of a record from a log file"
    INDEX { apLogFileRecordNumber }
    ::= { apLogFileTable 1 }

ApLogFileEntry ::= SEQUENCE {
    apLogFileRecordNumber
       LocalIndex,
    apLogFileRecord
       DisplayString
}

apLogFileRecordNumber OBJECT-TYPE
    SYNTAX      LocalIndex
    MAX-ACCESS  not-accessible
    STATUS      current
    DESCRIPTION
        "Unique log file record number"
    ::= { apLogFileEntry 1 }

apLogFileRecord OBJECT-TYPE
    SYNTAX      DisplayString
    MAX-ACCESS  read-only
    STATUS      current
    DESCRIPTION
        "Specific log file entry"
    ::= { apLogFileEntry 2 }

apIncidentTable OBJECT-TYPE
    SYNTAX SEQUENCE OF ApIncidentEntry
    MAX-ACCESS  not-accessible
    STATUS      current
    DESCRIPTION
        "Table of incident entries"
    ::= { jddsAppliance 5 }

apIncidentEntry OBJECT-TYPE
    SYNTAX   ApIncidentEntry
    MAX-ACCESS  not-accessible
    STATUS      current
    DESCRIPTION
        "A row consisting of an incident record"
    INDEX { apIncidentYear,
            apIncidentMonth,
            apIncidentDay,
            apIncidentNumber }
    ::= {apIncidentTable 1 }

ApIncidentEntry ::= SEQUENCE {
 apIncidentYear
       LocalIndex,
 apIncidentMonth
       LocalIndex,
 apIncidentDay
       LocalIndex,
 apIncidentNumber
       LocalIndex,
 apIncidentStart
       DateAndTime,
 apIncidentAddress
       DisplayString,
 apIncidentType
       DisplayString,
 apIncidentDirection
       Direction,
 apIncidentPeakRate
       Gauge32,
 apIncidentDropped
       Gauge32
}

apIncidentYear OBJECT-TYPE
    SYNTAX      LocalIndex
    MAX-ACCESS  not-accessible
    STATUS      current
    DESCRIPTION
        "Incident record year"
    ::= {apIncidentEntry 1 }

apIncidentMonth OBJECT-TYPE
    SYNTAX      LocalIndex
    MAX-ACCESS  not-accessible
    STATUS      current
    DESCRIPTION
        "Incident record month"
    ::= {apIncidentEntry 2 }

apIncidentDay OBJECT-TYPE
    SYNTAX      LocalIndex
    MAX-ACCESS  not-accessible
    STATUS      current
    DESCRIPTION
        "Incident record day of month"
    ::= {apIncidentEntry 3 }

apIncidentNumber OBJECT-TYPE
    SYNTAX      LocalIndex
    MAX-ACCESS  not-accessible
    STATUS      current
    DESCRIPTION
        "Unique (for the day) incident record number"
    ::= {apIncidentEntry 4 }

apIncidentStart OBJECT-TYPE
    SYNTAX      DateAndTime
    MAX-ACCESS  read-only
    STATUS      current
    DESCRIPTION
        "Incident start time"
    ::= {apIncidentEntry 5 }

apIncidentAddress OBJECT-TYPE
    SYNTAX      DisplayString
    MAX-ACCESS  read-only
    STATUS      current
    DESCRIPTION
        "Appliance, Portal and Protected Incident IP or MAC address, This could be an outbound MAC incident"
    ::= {apIncidentEntry 6 }

apIncidentType OBJECT-TYPE
    SYNTAX      DisplayString
    MAX-ACCESS  read-only
    STATUS      current
    DESCRIPTION
        "Incident defense type (and subtype)"
    ::= {apIncidentEntry 7 }

apIncidentDirection OBJECT-TYPE
    SYNTAX      Direction
    MAX-ACCESS  read-only
    STATUS      current
    DESCRIPTION
        "Incident direction"
    ::= {apIncidentEntry 8 }

apIncidentPeakRate OBJECT-TYPE
    SYNTAX      Gauge32
    MAX-ACCESS  read-only
    STATUS      current
    DESCRIPTION
        "Peak packets/s during this incident"
    ::= {apIncidentEntry 9 }

apIncidentDropped OBJECT-TYPE
    SYNTAX      Gauge32
    MAX-ACCESS  read-only
    STATUS      current
    DESCRIPTION
        "No of packets Dropped as part of this incident"
    ::= {apIncidentEntry 10 }

-- End of Appliance settings


-- **  poStatsTable
poStatsTable OBJECT-TYPE
    SYNTAX SEQUENCE OF PoStatsEntry
    MAX-ACCESS  not-accessible
    STATUS      current
    DESCRIPTION
        "Table of portal statistics"
    ::= { jddsPortal 3 }

poStatsEntry OBJECT-TYPE
    SYNTAX     PoStatsEntry
    MAX-ACCESS  not-accessible
    STATUS      current
    DESCRIPTION
        "A row associated with a specific portal"
    INDEX { poStatsIndex }
    ::= { poStatsTable 1 }

PoStatsEntry ::= SEQUENCE {
   poStatsIndex
	LocalIndex,
   poPortalName
	DisplayString,
   poInTotalBpsAvg
	Gauge32,
   poOutTotalBpsAvg
	Gauge32,
   poInTotalPpsAvg
	Gauge32,
   poOutTotalPpsAvg
	Gauge32,
   poInSmallPpsAvg
	Gauge32,
   poOutSmallPpsAvg
	Gauge32,
   poInMediumPpsAvg
	Gauge32,
   poOutMediumPpsAvg
	Gauge32,
   poInLargePpsAvg
	Gauge32,
   poOutLargePpsAvg
	Gauge32,
   poInDroppedBpsAvg
	Gauge32,
   poOutDroppedBpsAvg
	Gauge32,
   poInDroppedPpsAvg
	Gauge32,
   poOutDroppedPpsAvg
	Gauge32,
   poInCharmDroppedBpsAvg
	Gauge32,
   poOutCharmDroppedBpsAvg
	Gauge32,
   poInFilteredBwthPercentAvg
	Gauge32,
   poOutFilteredBwthPercentAvg
	Gauge32,
   poInSynbacklogtallyAvg
	Gauge32,
   poOutSynbacklogtallyAvg
	Gauge32,
   poInConnectionAvg
	Gauge32,
   poOutConnectionAvg
	Gauge32,
   poInConnreqAvg
	Gauge32,
   poOutConnreqAvg
	Gauge32,
   poInActiveHttpGetsAvg
	Gauge32,
   poOutActiveHttpGetsAvg
	Gauge32,
   poInProtectBwthPktsAvg
	Gauge32,
   poOutProtectBwthPktsAvg
	Gauge32,
   poInFloodPktsAvg
	Gauge32,
   poOutFloodPktsAvg
	Gauge32,
   poInBlockedProtocolPktsAvg
	Gauge32,
   poOutBlockedProtocolPktsAvg
	Gauge32,
   poInBlockedStatePktsAvg
	Gauge32,
   poOutBlockedStatePktsAvg
	Gauge32,
   poInIpAttackPktsAvg
	Gauge32,
   poOutIpAttackPktsAvg
	Gauge32,
   poInTcpAttackPktsAvg
	Gauge32,
   poOutTcpAttackPktsAvg
	Gauge32,
   poInUdpAttackPktsAvg
	Gauge32,
   poOutUdpAttackPktsAvg
	Gauge32,
   poInIcmpAttackPktsAvg
	Gauge32,
   poOutIcmpAttackPktsAvg
	Gauge32,
   poInOtherIpAttackPktsAvg
	Gauge32,
   poOutOtherIpAttackPktsAvg
	Gauge32,
   poInFragmentAttackPktsAvg
	Gauge32,
   poOutFragmentAttackPktsAvg
	Gauge32,
   poInBadipPktsAvg
	Gauge32,
   poOutBadipPktsAvg
	Gauge32,
   poInBadTcpPktsAvg
	Gauge32,
   poOutBadTcpPktsAvg
	Gauge32,
   poInBadUdpPktsAvg
	Gauge32,
   poOutBadUdpPktsAvg
	Gauge32,
   poInBadIcmpPktsAvg
	Gauge32,
   poOutBadIcmpPktsAvg
	Gauge32,
   poInBadOtherIpPktsAvg
	Gauge32,
   poOutBadOtherIpPktsAvg
	Gauge32,
   poInOverloadedAvg
	Gauge32,
   poOutOverloadedAvg
	Gauge32,
   poInLatencyAvg
	Gauge32,
   poOutLatencyAvg
	Gauge32,
   poInTotalBpsMax
	Gauge32,
   poOutTotalBpsMax
	Gauge32,
   poInTotalPpsMax
	Gauge32,
   poOutTotalPpsMax
	Gauge32,
   poInSmallPpsMax
	Gauge32,
   poOutSmallPpsMax
	Gauge32,
   poInMediumPpsMax
	Gauge32,
   poOutMediumPpsMax
	Gauge32,
   poInLargePpsMax
	Gauge32,
   poOutLargePpsMax
	Gauge32,
   poInDroppedBpsMax
	Gauge32,
   poOutDroppedBpsMax
	Gauge32,
   poInDroppedPpsMax
	Gauge32,
   poOutDroppedPpsMax
	Gauge32,
   poInCharmDroppedBpsMax
	Gauge32,
   poOutCharmDroppedBpsMax
	Gauge32,
   poInFilteredBwthPercentMax
	Gauge32,
   poOutFilteredBwthPercentMax
	Gauge32,
   poInSynbacklogtallyMax
	Gauge32,
   poOutSynbacklogtallyMax
	Gauge32,
   poInConnectionMax
	Gauge32,
   poOutConnectionMax
	Gauge32,
   poInConnreqMax
	Gauge32,
   poOutConnreqMax
	Gauge32,
   poInActiveHttpGetsMax
	Gauge32,
   poOutActiveHttpGetsMax
	Gauge32,
   poInProtectBwthPktsMax
	Gauge32,
   poOutProtectBwthPktsMax
	Gauge32,
   poInFloodPktsMax
	Gauge32,
   poOutFloodPktsMax
	Gauge32,
   poInBlockedProtocolPktsMax
	Gauge32,
   poOutBlockedProtocolPktsMax
	Gauge32,
   poInBlockedStatePktsMax
	Gauge32,
   poOutBlockedStatePktsMax
	Gauge32,
   poInIpAttackPktsMax
	Gauge32,
   poOutIpAttackPktsMax
	Gauge32,
   poInTcpAttackPktsMax
	Gauge32,
   poOutTcpAttackPktsMax
	Gauge32,
   poInUdpAttackPktsMax
	Gauge32,
   poOutUdpAttackPktsMax
	Gauge32,
   poInIcmpAttackPktsMax
	Gauge32,
   poOutIcmpAttackPktsMax
	Gauge32,
   poInOtherIpAttackPktsMax
	Gauge32,
   poOutOtherIpAttackPktsMax
	Gauge32,
   poInFragmentAttackPktsMax
	Gauge32,
   poOutFragmentAttackPktsMax
	Gauge32,
   poInBadipPktsMax
	Gauge32,
   poOutBadipPktsMax
	Gauge32,
   poInBadTcpPktsMax
	Gauge32,
   poOutBadTcpPktsMax
	Gauge32,
   poInBadUdpPktsMax
	Gauge32,
   poOutBadUdpPktsMax
	Gauge32,
   poInBadIcmpPktsMax
	Gauge32,
   poOutBadIcmpPktsMax
	Gauge32,
   poInBadOtherIpPktsMax
	Gauge32,
   poOutBadOtherIpPktsMax
	Gauge32,
   poInOverloadedMax
	Gauge32,
   poOutOverloadedMax
	Gauge32,
   poInLatencyMax
	Gauge32,
   poOutLatencyMax
	Gauge32,
   poInTotalBytesCnt
	Counter64,
   poOutTotalBytesCnt
	Counter64,
   poInDroppedBytesCnt
	Counter64,
   poOutDroppedBytesCnt
	Counter64,
   poInCharmDroppedBytesCnt
	Counter64,
   poOutCharmDroppedBytesCnt
	Counter64,
   poInTotalPpsCnt
      	Counter32,
   poOutTotalPpsCnt
      	Counter32,
   poInSmallPpsCnt
      	Counter32,
   poOutSmallPpsCnt
      	Counter32,
   poInMediumPpsCnt
      	Counter32,
   poOutMediumPpsCnt
      	Counter32,
   poInLargePpsCnt
      	Counter32,
   poOutLargePpsCnt
      	Counter32,
   poInDroppedPpsCnt
      	Counter32,
   poOutDroppedPpsCnt
      	Counter32,
   poInFilteredBwthPercentCnt
      	Counter32,
   poOutFilteredBwthPercentCnt
      	Counter32,
   poInConnreqCnt
      	Counter32,
   poOutConnreqCnt
   	Counter32
}

 poStatsIndex OBJECT-TYPE
    SYNTAX      LocalIndex
    MAX-ACCESS  not-accessible
    STATUS      current
    DESCRIPTION
        "Index to Portal Statistics"
   ::= { poStatsEntry 1 }

 poPortalName OBJECT-TYPE
    SYNTAX      DisplayString
    MAX-ACCESS  read-only
    STATUS      current
    DESCRIPTION
        "The name associated with this portal"
    ::= { poStatsEntry 2 }

poInTotalBpsAvg OBJECT-TYPE
    SYNTAX      Gauge32
    MAX-ACCESS  read-only
    STATUS      current
    DESCRIPTION
	"Average number of input bits per second"
    ::= { poStatsEntry 901 }

poOutTotalBpsAvg OBJECT-TYPE
    SYNTAX      Gauge32
    MAX-ACCESS  read-only
    STATUS      current
    DESCRIPTION
	"Average number of output bits per second"
    ::= { poStatsEntry 902 }

poInTotalPpsAvg OBJECT-TYPE
    SYNTAX      Gauge32
    MAX-ACCESS  read-only
    STATUS      current
    DESCRIPTION
	"Average packets/sec traffic rate inbound since last restart or reset"
    ::= { poStatsEntry 903 }

poOutTotalPpsAvg OBJECT-TYPE
    SYNTAX      Gauge32
    MAX-ACCESS  read-only
    STATUS      current
    DESCRIPTION
	"Average packets/sec traffic rate outbound since last restart or reset"
    ::= { poStatsEntry 904 }

poInSmallPpsAvg OBJECT-TYPE
    SYNTAX      Gauge32
    MAX-ACCESS  read-only
    STATUS      current
    DESCRIPTION
	"Averaged inbound packets (256 bytes or less) per second processed. Dropped data is not included"
    ::= { poStatsEntry 905 }

poOutSmallPpsAvg OBJECT-TYPE
    SYNTAX      Gauge32
    MAX-ACCESS  read-only
    STATUS      current
    DESCRIPTION
	"Averaged outbound packets (256 bytes or less) per second processed. Dropped data is not included"
    ::= { poStatsEntry 906 }

poInMediumPpsAvg OBJECT-TYPE
    SYNTAX      Gauge32
    MAX-ACCESS  read-only
    STATUS      current
    DESCRIPTION
	"Averaged inbound packets (1024 bytes or less, but greater than 256 bytes) per second. Dropped data is not included"
    ::= { poStatsEntry 907 }

poOutMediumPpsAvg OBJECT-TYPE
    SYNTAX      Gauge32
    MAX-ACCESS  read-only
    STATUS      current
    DESCRIPTION
	"Averaged outbound packets (1024 bytes or less, but greater than 256 bytes) per second. Dropped data is not included"
    ::= { poStatsEntry 908 }

poInLargePpsAvg OBJECT-TYPE
    SYNTAX      Gauge32
    MAX-ACCESS  read-only
    STATUS      current
    DESCRIPTION
	"Averaged inbound packets (greater than 1024 bytes) per second. Dropped data is not included"
    ::= { poStatsEntry 909 }

poOutLargePpsAvg OBJECT-TYPE
    SYNTAX      Gauge32
    MAX-ACCESS  read-only
    STATUS      current
    DESCRIPTION
	"Averaged outbound packets (greater than 1024 bytes) per second. Dropped data is not included"
    ::= { poStatsEntry 910 }

poInDroppedBpsAvg OBJECT-TYPE
    SYNTAX      Gauge32
    MAX-ACCESS  read-only
    STATUS      current
    DESCRIPTION
	"Average number of input bits Dropped per second"
    ::= { poStatsEntry 911 }

poOutDroppedBpsAvg OBJECT-TYPE
    SYNTAX      Gauge32
    MAX-ACCESS  read-only
    STATUS      current
    DESCRIPTION
	"Average number of output bits Dropped per second"
    ::= { poStatsEntry 912 }

poInDroppedPpsAvg OBJECT-TYPE
    SYNTAX      Gauge32
    MAX-ACCESS  read-only
    STATUS      current
    DESCRIPTION
	"Average number of input packets Dropped per second"
    ::= { poStatsEntry 913 }

poOutDroppedPpsAvg OBJECT-TYPE
    SYNTAX      Gauge32
    MAX-ACCESS  read-only
    STATUS      current
    DESCRIPTION
	"Averaged number of output packets Dropped per second"
    ::= { poStatsEntry 914 }

poInCharmDroppedBpsAvg OBJECT-TYPE
    SYNTAX      Gauge32
    MAX-ACCESS  read-only
    STATUS      current
    DESCRIPTION
	"Averaged inbound bits per second dropped by heuristic detection"
    ::= { poStatsEntry 915 }

poOutCharmDroppedBpsAvg OBJECT-TYPE
    SYNTAX      Gauge32
    MAX-ACCESS  read-only
    STATUS      current
    DESCRIPTION
	"Averaged outbound bits per second dropped by heuristic detection"
    ::= { poStatsEntry 916 }

poInFilteredBwthPercentAvg OBJECT-TYPE
    SYNTAX      Gauge32
    MAX-ACCESS  read-only
    STATUS      current
    DESCRIPTION
	"Averaged inbound dropped bandwidth divided by the actual bandwidth"
    ::= { poStatsEntry 917 }

poOutFilteredBwthPercentAvg OBJECT-TYPE
    SYNTAX      Gauge32
    MAX-ACCESS  read-only
    STATUS      current
    DESCRIPTION
	"Averaged outbound dropped bandwidth divided by the actual bandwidth"
    ::= { poStatsEntry 918 }

poInSynbacklogtallyAvg OBJECT-TYPE
    SYNTAX      Gauge32
    MAX-ACCESS  read-only
    STATUS      current
    DESCRIPTION
	"Averaged number of partially open TCP connections inbound"
    ::= { poStatsEntry 919 }

poOutSynbacklogtallyAvg OBJECT-TYPE
    SYNTAX      Gauge32
    MAX-ACCESS  read-only
    STATUS      current
    DESCRIPTION
	"Averaged number of partially open TCP connections outbound"
    ::= { poStatsEntry 920 }

poInConnectionAvg OBJECT-TYPE
    SYNTAX      Gauge32
    MAX-ACCESS  read-only
    STATUS      current
    DESCRIPTION
	"Averaged number of inbound TCP connections"
    ::= { poStatsEntry 921 }

poOutConnectionAvg OBJECT-TYPE
    SYNTAX      Gauge32
    MAX-ACCESS  read-only
    STATUS      current
    DESCRIPTION
	"Averaged number of outbound TCP connections"
    ::= { poStatsEntry 922 }

poInConnreqAvg OBJECT-TYPE
    SYNTAX      Gauge32
    MAX-ACCESS  read-only
    STATUS      current
    DESCRIPTION
	"Averaged number of inbound TCP connection requests"
    ::= { poStatsEntry 923 }

poOutConnreqAvg OBJECT-TYPE
    SYNTAX      Gauge32
    MAX-ACCESS  read-only
    STATUS      current
    DESCRIPTION
	"Averaged number of outbound TCP connection requests"
    ::= { poStatsEntry 924 }

poInActiveHttpGetsAvg OBJECT-TYPE
    SYNTAX      Gauge32
    MAX-ACCESS  read-only
    STATUS      current
    DESCRIPTION
	"Averaged number of inbound HTTP page requests being processed"
    ::= { poStatsEntry 925 }

poOutActiveHttpGetsAvg OBJECT-TYPE
    SYNTAX      Gauge32
    MAX-ACCESS  read-only
    STATUS      current
    DESCRIPTION
	"Averaged number of outbound HTTP page requests being processed"
    ::= { poStatsEntry 926 }

poInProtectBwthPktsAvg OBJECT-TYPE
    SYNTAX      Gauge32
    MAX-ACCESS  read-only
    STATUS      current
    DESCRIPTION
	"Averaged inbound protected bandwifth"
    ::= { poStatsEntry 927 }

poOutProtectBwthPktsAvg OBJECT-TYPE
    SYNTAX      Gauge32
    MAX-ACCESS  read-only
    STATUS      current
    DESCRIPTION
	"Averaged outbound protected bandwifth"
    ::= { poStatsEntry 928 }

poInFloodPktsAvg OBJECT-TYPE
    SYNTAX      Gauge32
    MAX-ACCESS  read-only
    STATUS      current
    DESCRIPTION
	"Averaged number of inbound packets causing flooding"
    ::= { poStatsEntry 929 }

poOutFloodPktsAvg OBJECT-TYPE
    SYNTAX      Gauge32
    MAX-ACCESS  read-only
    STATUS      current
    DESCRIPTION
	"Averaged number of outbound packets causing flooding"
    ::= { poStatsEntry 930 }

poInBlockedProtocolPktsAvg OBJECT-TYPE
    SYNTAX      Gauge32
    MAX-ACCESS  read-only
    STATUS      current
    DESCRIPTION
	"Averaged number of inbound IP packets dropped by filter "
    ::= { poStatsEntry 931 }

poOutBlockedProtocolPktsAvg OBJECT-TYPE
    SYNTAX      Gauge32
    MAX-ACCESS  read-only
    STATUS      current
    DESCRIPTION
	"Averaged number of outbound IP packets dropped by filter"
    ::= { poStatsEntry 932 }

poInBlockedStatePktsAvg OBJECT-TYPE
    SYNTAX      Gauge32
    MAX-ACCESS  read-only
    STATUS      current
    DESCRIPTION
	"Averaged number of inbound IP packets dropped due to incorrect state"
    ::= { poStatsEntry 933 }

poOutBlockedStatePktsAvg OBJECT-TYPE
    SYNTAX      Gauge32
    MAX-ACCESS  read-only
    STATUS      current
    DESCRIPTION
	"Averaged number of outbound IP packets dropped due to incorrect state"
    ::= { poStatsEntry 934 }

poInIpAttackPktsAvg OBJECT-TYPE
    SYNTAX      Gauge32
    MAX-ACCESS  read-only
    STATUS      current
    DESCRIPTION
	"Averaged number of inbound IP packets in an IP Attack"
    ::= { poStatsEntry 935 }

poOutIpAttackPktsAvg OBJECT-TYPE
    SYNTAX      Gauge32
    MAX-ACCESS  read-only
    STATUS      current
    DESCRIPTION
	"Averaged number of outbound IP packets in an IP Attack"
    ::= { poStatsEntry 936 }

poInTcpAttackPktsAvg OBJECT-TYPE
    SYNTAX      Gauge32
    MAX-ACCESS  read-only
    STATUS      current
    DESCRIPTION
	"Averaged number of inbound IP packets in a TCP Attack"
    ::= { poStatsEntry 937 }

poOutTcpAttackPktsAvg OBJECT-TYPE
    SYNTAX      Gauge32
    MAX-ACCESS  read-only
    STATUS      current
    DESCRIPTION
	"Averaged number of outbound IP packets in a TCP Attack"
    ::= { poStatsEntry 938 }

poInUdpAttackPktsAvg OBJECT-TYPE
    SYNTAX      Gauge32
    MAX-ACCESS  read-only
    STATUS      current
    DESCRIPTION
	"Averaged number of inbound IP packets in a UDP Attack"
    ::= { poStatsEntry 939 }

poOutUdpAttackPktsAvg OBJECT-TYPE
    SYNTAX      Gauge32
    MAX-ACCESS  read-only
    STATUS      current
    DESCRIPTION
	"Averaged number of outbound IP packets in a UDP Attack"
    ::= { poStatsEntry 940 }

poInIcmpAttackPktsAvg OBJECT-TYPE
    SYNTAX      Gauge32
    MAX-ACCESS  read-only
    STATUS      current
    DESCRIPTION
	"Averaged number of inbound IP packets in a ICMP Attack"
    ::= { poStatsEntry 941 }

poOutIcmpAttackPktsAvg OBJECT-TYPE
    SYNTAX      Gauge32
    MAX-ACCESS  read-only
    STATUS      current
    DESCRIPTION
	"Averaged number of outbound IP packets in a ICMP Attack"
    ::= { poStatsEntry 942 }

poInOtherIpAttackPktsAvg OBJECT-TYPE
    SYNTAX      Gauge32
    MAX-ACCESS  read-only
    STATUS      current
    DESCRIPTION
	"Averaged number of inbound IP packets in an IP Attack using other protocols"
    ::= { poStatsEntry 943 }

poOutOtherIpAttackPktsAvg OBJECT-TYPE
    SYNTAX      Gauge32
    MAX-ACCESS  read-only
    STATUS      current
    DESCRIPTION
	"Averaged number of outbound IP packets in an IP Attack using other protocols"
    ::= { poStatsEntry 944 }

poInFragmentAttackPktsAvg OBJECT-TYPE
    SYNTAX      Gauge32
    MAX-ACCESS  read-only
    STATUS      current
    DESCRIPTION
	"Averaged number of inbound IP packets in an Fragmentation Attack"
    ::= { poStatsEntry 945 }

poOutFragmentAttackPktsAvg OBJECT-TYPE
    SYNTAX      Gauge32
    MAX-ACCESS  read-only
    STATUS      current
    DESCRIPTION
	"Averaged number of outbound IP packets in an Fragmentation Attack"
    ::= { poStatsEntry 946 }

poInBadipPktsAvg OBJECT-TYPE
    SYNTAX      Gauge32
    MAX-ACCESS  read-only
    STATUS      current
    DESCRIPTION
	"Averaged number of inbound IP packets with malformed IP Headers"
    ::= { poStatsEntry 947 }

poOutBadipPktsAvg OBJECT-TYPE
    SYNTAX      Gauge32
    MAX-ACCESS  read-only
    STATUS      current
    DESCRIPTION
	"Averaged number of outbound IP packets with malformed IP Headers"
    ::= { poStatsEntry 948 }

poInBadTcpPktsAvg OBJECT-TYPE
    SYNTAX      Gauge32
    MAX-ACCESS  read-only
    STATUS      current
    DESCRIPTION
	"Averaged number of inbound IP packets with bad TCP protocol/state"
    ::= { poStatsEntry 949 }

poOutBadTcpPktsAvg OBJECT-TYPE
    SYNTAX      Gauge32
    MAX-ACCESS  read-only
    STATUS      current
    DESCRIPTION
	"Averaged number of outbound IP packets with bad TCP protocol/state"
    ::= { poStatsEntry 950 }

poInBadUdpPktsAvg OBJECT-TYPE
    SYNTAX      Gauge32
    MAX-ACCESS  read-only
    STATUS      current
    DESCRIPTION
	"Averaged number of inbound UDP packets with malformed header or missing data"
    ::= { poStatsEntry 951 }

poOutBadUdpPktsAvg OBJECT-TYPE
    SYNTAX      Gauge32
    MAX-ACCESS  read-only
    STATUS      current
    DESCRIPTION
	"Averaged number of outbound UDP packets with malformed header or missing data"
    ::= { poStatsEntry 952 }

poInBadIcmpPktsAvg OBJECT-TYPE
    SYNTAX      Gauge32
    MAX-ACCESS  read-only
    STATUS      current
    DESCRIPTION
	"Averaged number of inbound ICMP packets with malformed header"
    ::= { poStatsEntry 953 }

poOutBadIcmpPktsAvg OBJECT-TYPE
    SYNTAX      Gauge32
    MAX-ACCESS  read-only
    STATUS      current
    DESCRIPTION
	"Averaged number of outbound ICMP packets with malformed header"
    ::= { poStatsEntry 954 }

poInBadOtherIpPktsAvg OBJECT-TYPE
    SYNTAX      Gauge32
    MAX-ACCESS  read-only
    STATUS      current
    DESCRIPTION
	"Averaged number of inbound IP packets of other protocol with malformed header"
    ::= { poStatsEntry 955 }

poOutBadOtherIpPktsAvg OBJECT-TYPE
    SYNTAX      Gauge32
    MAX-ACCESS  read-only
    STATUS      current
    DESCRIPTION
	"Averaged number of outbound IP packets of other protocol with malformed header"
    ::= { poStatsEntry 956 }

poInOverloadedAvg OBJECT-TYPE
    SYNTAX      Gauge32
    MAX-ACCESS  read-only
    STATUS      current
    DESCRIPTION
	"Averaged number of inbound packets overloading the protected IP"
    ::= { poStatsEntry 957 }

poOutOverloadedAvg OBJECT-TYPE
    SYNTAX      Gauge32
    MAX-ACCESS  read-only
    STATUS      current
    DESCRIPTION
	"Averaged number of outbound packets overloading the protected IP"
    ::= { poStatsEntry 958 }

poInLatencyAvg OBJECT-TYPE
    SYNTAX      Gauge32
    MAX-ACCESS  read-only
    STATUS      current
    DESCRIPTION
	"Averaged inbound Latency"
    ::= { poStatsEntry 959 }

poOutLatencyAvg OBJECT-TYPE
    SYNTAX      Gauge32
    MAX-ACCESS  read-only
    STATUS      current
    DESCRIPTION
	"Averaged outbound Latency"
    ::= { poStatsEntry 960 }

poInTotalBpsMax OBJECT-TYPE
    SYNTAX      Gauge32
    MAX-ACCESS  read-only
    STATUS      current
    DESCRIPTION
	"Peak number of input bits per second"
    ::= { poStatsEntry 1001 }

poOutTotalBpsMax OBJECT-TYPE
    SYNTAX      Gauge32
    MAX-ACCESS  read-only
    STATUS      current
    DESCRIPTION
	"Peak number of output bits per second"
    ::= { poStatsEntry 1002 }

poInTotalPpsMax OBJECT-TYPE
    SYNTAX      Gauge32
    MAX-ACCESS  read-only
    STATUS      current
    DESCRIPTION
	"Peak packets/sec traffic rate inbound since last restart or reset"
    ::= { poStatsEntry 1003 }

poOutTotalPpsMax OBJECT-TYPE
    SYNTAX      Gauge32
    MAX-ACCESS  read-only
    STATUS      current
    DESCRIPTION
	"Peak packets/sec traffic rate outbound since last
         restart or reset"
    ::= { poStatsEntry 1004 }

poInSmallPpsMax OBJECT-TYPE
    SYNTAX      Gauge32
    MAX-ACCESS  read-only
    STATUS      current
    DESCRIPTION
	"Peak inbound packets (256 bytes or less) per second processed. Dropped data is not included"
    ::= { poStatsEntry 1005 }

poOutSmallPpsMax OBJECT-TYPE
    SYNTAX      Gauge32
    MAX-ACCESS  read-only
    STATUS      current
    DESCRIPTION
	"Peak outbound packets (256 bytes or less) per second processed. Dropped data is not included"
    ::= { poStatsEntry 1006 }

poInMediumPpsMax OBJECT-TYPE
    SYNTAX      Gauge32
    MAX-ACCESS  read-only
    STATUS      current
    DESCRIPTION
	"Peak inbound packets (1024 bytes or less, but greater than 256 bytes) per second. Dropped data is not included"
    ::= { poStatsEntry 1007 }

poOutMediumPpsMax OBJECT-TYPE
    SYNTAX      Gauge32
    MAX-ACCESS  read-only
    STATUS      current
    DESCRIPTION
	"Peak outbound packets (1024 bytes or less, but greater than 256 bytes) per second. Dropped data is not included"
    ::= { poStatsEntry 1008 }

poInLargePpsMax OBJECT-TYPE
    SYNTAX      Gauge32
    MAX-ACCESS  read-only
    STATUS      current
    DESCRIPTION
	"Peak inbound packets (greater than 1024 bytes) per second. Dropped data is not included"
    ::= { poStatsEntry 1009 }

poOutLargePpsMax OBJECT-TYPE
    SYNTAX      Gauge32
    MAX-ACCESS  read-only
    STATUS      current
    DESCRIPTION
	"Peak outbound packets (greater than 1024 bytes) per second. Dropped data is not included"
    ::= { poStatsEntry 1010 }

poInDroppedBpsMax OBJECT-TYPE
    SYNTAX      Gauge32
    MAX-ACCESS  read-only
    STATUS      current
    DESCRIPTION
	"Average number of input bits Dropped per second"
    ::= { poStatsEntry 1011 }

poOutDroppedBpsMax OBJECT-TYPE
    SYNTAX      Gauge32
    MAX-ACCESS  read-only
    STATUS      current
    DESCRIPTION
	"Average number of output bits Dropped per second"
    ::= { poStatsEntry 1012 }

poInDroppedPpsMax OBJECT-TYPE
    SYNTAX      Gauge32
    MAX-ACCESS  read-only
    STATUS      current
    DESCRIPTION
	"Average number of input packets Dropped per second"
    ::= { poStatsEntry 1013 }

poOutDroppedPpsMax OBJECT-TYPE
    SYNTAX      Gauge32
    MAX-ACCESS  read-only
    STATUS      current
    DESCRIPTION
	"Peak number of output packets Dropped per second"
    ::= { poStatsEntry 1014 }

poInCharmDroppedBpsMax OBJECT-TYPE
    SYNTAX      Gauge32
    MAX-ACCESS  read-only
    STATUS      current
    DESCRIPTION
	"Peak inbound bits per second dropped by heuristic detection"
    ::= { poStatsEntry 1015 }

poOutCharmDroppedBpsMax OBJECT-TYPE
    SYNTAX      Gauge32
    MAX-ACCESS  read-only
    STATUS      current
    DESCRIPTION
	"Peak outbound bits per second dropped by heuristic detection"
    ::= { poStatsEntry 1016 }

poInFilteredBwthPercentMax OBJECT-TYPE
    SYNTAX      Gauge32
    MAX-ACCESS  read-only
    STATUS      current
    DESCRIPTION
	"Peak inbound dropped bandwidth divided by the actual bandwidth"
    ::= { poStatsEntry 1017 }

poOutFilteredBwthPercentMax OBJECT-TYPE
    SYNTAX      Gauge32
    MAX-ACCESS  read-only
    STATUS      current
    DESCRIPTION
	"Peak outbound dropped bandwidth divided by the actual bandwidth"
    ::= { poStatsEntry 1018 }

poInSynbacklogtallyMax OBJECT-TYPE
    SYNTAX      Gauge32
    MAX-ACCESS  read-only
    STATUS      current
    DESCRIPTION
	"Peak number of partially open TCP connections inbound"
    ::= { poStatsEntry 1019 }

poOutSynbacklogtallyMax OBJECT-TYPE
    SYNTAX      Gauge32
    MAX-ACCESS  read-only
    STATUS      current
    DESCRIPTION
	"Peak number of partially open TCP connections outbound"
    ::= { poStatsEntry 1020 }

poInConnectionMax OBJECT-TYPE
    SYNTAX      Gauge32
    MAX-ACCESS  read-only
    STATUS      current
    DESCRIPTION
	"Peak number of inbound TCP connections"
    ::= { poStatsEntry 1021 }

poOutConnectionMax OBJECT-TYPE
    SYNTAX      Gauge32
    MAX-ACCESS  read-only
    STATUS      current
    DESCRIPTION
	"Peak number of outbound TCP connections"
    ::= { poStatsEntry 1022 }

poInConnreqMax OBJECT-TYPE
    SYNTAX      Gauge32
    MAX-ACCESS  read-only
    STATUS      current
    DESCRIPTION
	"Peak number of inbound TCP connection requests"
    ::= { poStatsEntry 1023 }

poOutConnreqMax OBJECT-TYPE
    SYNTAX	Gauge32
    MAX-ACCESS  read-only
    STATUS      current
    DESCRIPTION
	"Peak number of outbound TCP connection requests"
    ::= { poStatsEntry 1024 }

poInActiveHttpGetsMax OBJECT-TYPE
    SYNTAX      Gauge32
    MAX-ACCESS  read-only
    STATUS      current
    DESCRIPTION
	"Peak number of inbound HTTP page requests being processed"
    ::= { poStatsEntry 1025 }

poOutActiveHttpGetsMax OBJECT-TYPE
    SYNTAX      Gauge32
    MAX-ACCESS  read-only
    STATUS      current
    DESCRIPTION
	"Peak number of outbound HTTP page requests being processed"
    ::= { poStatsEntry 1026 }

poInProtectBwthPktsMax OBJECT-TYPE
    SYNTAX      Gauge32
    MAX-ACCESS  read-only
    STATUS      current
    DESCRIPTION
	"Peak inbound protected bandwifth"
    ::= { poStatsEntry 1027 }

poOutProtectBwthPktsMax OBJECT-TYPE
    SYNTAX      Gauge32
    MAX-ACCESS  read-only
    STATUS      current
    DESCRIPTION
	"Peak outbound protected bandwifth"
    ::= { poStatsEntry 1028 }

poInFloodPktsMax OBJECT-TYPE
    SYNTAX      Gauge32
    MAX-ACCESS  read-only
    STATUS      current
    DESCRIPTION
	"Peak number of inbound packets causing flooding"
    ::= { poStatsEntry 1029 }

poOutFloodPktsMax OBJECT-TYPE
    SYNTAX      Gauge32
    MAX-ACCESS  read-only
    STATUS      current
    DESCRIPTION
	"Peak number of outbound packets causing flooding"
    ::= { poStatsEntry 1030 }

poInBlockedProtocolPktsMax OBJECT-TYPE
    SYNTAX      Gauge32
    MAX-ACCESS  read-only
    STATUS      current
    DESCRIPTION
	"Peak number of inbound IP packets dropped by filter "
    ::= { poStatsEntry 1031 }

poOutBlockedProtocolPktsMax OBJECT-TYPE
    SYNTAX      Gauge32
    MAX-ACCESS  read-only
    STATUS      current
    DESCRIPTION
	"Peak number of outbound IP packets dropped by filter"
    ::= { poStatsEntry 1032 }

poInBlockedStatePktsMax OBJECT-TYPE
    SYNTAX      Gauge32
    MAX-ACCESS  read-only
    STATUS      current
    DESCRIPTION
	"Peak number of inbound IP packets dropped due to incorrect state"
    ::= { poStatsEntry 1033 }

poOutBlockedStatePktsMax OBJECT-TYPE
    SYNTAX      Gauge32
    MAX-ACCESS  read-only
    STATUS      current
    DESCRIPTION
	"Peak number of outbound IP packets dropped due to incorrect state"
    ::= { poStatsEntry 1034 }

poInIpAttackPktsMax OBJECT-TYPE
    SYNTAX      Gauge32
    MAX-ACCESS  read-only
    STATUS      current
    DESCRIPTION
	"Peak number of inbound IP packets in an IP Attack"
    ::= { poStatsEntry 1035 }

poOutIpAttackPktsMax OBJECT-TYPE
    SYNTAX      Gauge32
    MAX-ACCESS  read-only
    STATUS      current
    DESCRIPTION
	"Peak number of outbound IP packets in an IP Attack"
    ::= { poStatsEntry 1036 }

poInTcpAttackPktsMax OBJECT-TYPE
    SYNTAX      Gauge32
    MAX-ACCESS  read-only
    STATUS      current
    DESCRIPTION
	"Peak number of inbound IP packets in a TCP Attack"
    ::= { poStatsEntry 1037 }

poOutTcpAttackPktsMax OBJECT-TYPE
    SYNTAX      Gauge32
    MAX-ACCESS  read-only
    STATUS      current
    DESCRIPTION
	"Peak number of outbound IP packets in a TCP Attack"
    ::= { poStatsEntry 1038 }

poInUdpAttackPktsMax OBJECT-TYPE
    SYNTAX      Gauge32
    MAX-ACCESS  read-only
    STATUS      current
    DESCRIPTION
	"Peak number of inbound IP packets in a UDP Attack"
    ::= { poStatsEntry 1039 }

poOutUdpAttackPktsMax OBJECT-TYPE
    SYNTAX      Gauge32
    MAX-ACCESS  read-only
    STATUS      current
    DESCRIPTION
	"Peak number of outbound IP packets in a UDP Attack"
    ::= { poStatsEntry 1040 }

poInIcmpAttackPktsMax OBJECT-TYPE
    SYNTAX      Gauge32
    MAX-ACCESS  read-only
    STATUS      current
    DESCRIPTION
	"Peak number of inbound IP packets in a ICMP Attack"
    ::= { poStatsEntry 1041 }

poOutIcmpAttackPktsMax OBJECT-TYPE
    SYNTAX      Gauge32
    MAX-ACCESS  read-only
    STATUS      current
    DESCRIPTION
	"Peak number of outbound IP packets in a ICMP Attack"
    ::= { poStatsEntry 1042 }

poInOtherIpAttackPktsMax OBJECT-TYPE
    SYNTAX      Gauge32
    MAX-ACCESS  read-only
    STATUS      current
    DESCRIPTION
	"Peak number of inbound IP packets in an IP Attack using other protocols"
    ::= { poStatsEntry 1043 }

poOutOtherIpAttackPktsMax OBJECT-TYPE
    SYNTAX      Gauge32
    MAX-ACCESS  read-only
    STATUS      current
    DESCRIPTION
	"Peak number of outbound IP packets in an IP Attack using other protocols"
    ::= { poStatsEntry 1044 }

poInFragmentAttackPktsMax OBJECT-TYPE
    SYNTAX      Gauge32
    MAX-ACCESS  read-only
    STATUS      current
    DESCRIPTION
	"Peak number of inbound IP packets in an Fragmentation Attack"
    ::= { poStatsEntry 1045 }

poOutFragmentAttackPktsMax OBJECT-TYPE
    SYNTAX      Gauge32
    MAX-ACCESS  read-only
    STATUS      current
    DESCRIPTION
	"Peak number of outbound IP packets in an Fragmentation Attack"
    ::= { poStatsEntry 1046 }

poInBadipPktsMax OBJECT-TYPE
    SYNTAX      Gauge32
    MAX-ACCESS  read-only
    STATUS      current
    DESCRIPTION
	"Peak number of inbound IP packets with malformed IP Headers"
    ::= { poStatsEntry 1047 }

poOutBadipPktsMax OBJECT-TYPE
    SYNTAX      Gauge32
    MAX-ACCESS  read-only
    STATUS      current
    DESCRIPTION
	"Peak number of outbound IP packets with malformed IP Headers"
    ::= { poStatsEntry 1048 }

poInBadTcpPktsMax OBJECT-TYPE
    SYNTAX      Gauge32
    MAX-ACCESS  read-only
    STATUS      current
    DESCRIPTION
	"Peak number of inbound IP packets with bad TCP protocol/state"
    ::= { poStatsEntry 1049 }

poOutBadTcpPktsMax OBJECT-TYPE
    SYNTAX      Gauge32
    MAX-ACCESS  read-only
    STATUS      current
    DESCRIPTION
	"Peak number of outbound IP packets with bad TCP protocol/state"
    ::= { poStatsEntry 1050 }

poInBadUdpPktsMax OBJECT-TYPE
    SYNTAX      Gauge32
    MAX-ACCESS  read-only
    STATUS      current
    DESCRIPTION
	"Peak number of inbound UDP packets with malformed header or missing data"
    ::= { poStatsEntry 1051 }

poOutBadUdpPktsMax OBJECT-TYPE
    SYNTAX      Gauge32
    MAX-ACCESS  read-only
    STATUS      current
    DESCRIPTION
	"Peak number of outbound UDP packets with malformed header or missing data"
    ::= { poStatsEntry 1052 }

poInBadIcmpPktsMax OBJECT-TYPE
    SYNTAX      Gauge32
    MAX-ACCESS  read-only
    STATUS      current
    DESCRIPTION
	"Peak number of inbound ICMP packets with malformed header"
    ::= { poStatsEntry 1053 }

poOutBadIcmpPktsMax OBJECT-TYPE
    SYNTAX      Gauge32
    MAX-ACCESS  read-only
    STATUS      current
    DESCRIPTION
	"Peak number of outbound ICMP packets with malformed header"
    ::= { poStatsEntry 1054 }

poInBadOtherIpPktsMax OBJECT-TYPE
    SYNTAX      Gauge32
    MAX-ACCESS  read-only
    STATUS      current
    DESCRIPTION
	"Peak number of inbound IP packets of other protocol with malformed header"
    ::= { poStatsEntry 1055 }

poOutBadOtherIpPktsMax OBJECT-TYPE
    SYNTAX      Gauge32
    MAX-ACCESS  read-only
    STATUS      current
    DESCRIPTION
	"Peak number of outbound IP packets of other protocol with malformed header"
    ::= { poStatsEntry 1056 }

poInOverloadedMax OBJECT-TYPE
    SYNTAX      Gauge32
    MAX-ACCESS  read-only
    STATUS      current
    DESCRIPTION
	"Peak number of inbound packets overloading the protected IP"
    ::= { poStatsEntry 1057 }

poOutOverloadedMax OBJECT-TYPE
    SYNTAX      Gauge32
    MAX-ACCESS  read-only
    STATUS      current
    DESCRIPTION
	"Peak number of outbound packets overloading the protected IP"
    ::= { poStatsEntry 1058 }

poInLatencyMax OBJECT-TYPE
    SYNTAX      Gauge32
    MAX-ACCESS  read-only
    STATUS      current
    DESCRIPTION
	"Peak inbound Latency"
    ::= { poStatsEntry 1059 }

poOutLatencyMax OBJECT-TYPE
    SYNTAX      Gauge32
    MAX-ACCESS  read-only
    STATUS      current
    DESCRIPTION
	"Peak outbound Latency"
    ::= { poStatsEntry 1060 }

poInTotalBytesCnt OBJECT-TYPE
    SYNTAX      Counter64
    MAX-ACCESS  read-only
    STATUS      current
    DESCRIPTION
        "Total number of bytes seen inbound by DDoS Secure"
    ::= { poStatsEntry 1101 }

poOutTotalBytesCnt OBJECT-TYPE
    SYNTAX      Counter64
    MAX-ACCESS  read-only
    STATUS      current
    DESCRIPTION
        "Total number of bytes seen outbound by DDoS Secure"
    ::= { poStatsEntry 1102 }

poInDroppedBytesCnt OBJECT-TYPE
    SYNTAX      Counter64
    MAX-ACCESS  read-only
    STATUS      current
    DESCRIPTION
        "Total number of bytes Dropped inbound by DDoS Secure"
    ::= { poStatsEntry 1103 }

poOutDroppedBytesCnt OBJECT-TYPE
    SYNTAX      Counter64
    MAX-ACCESS  read-only
    STATUS      current
    DESCRIPTION
        "Total number of bytes Dropped outbound by DDoS Secure"
    ::= { poStatsEntry 1104 }

poInCharmDroppedBytesCnt OBJECT-TYPE
    SYNTAX      Counter64
    MAX-ACCESS  read-only
    STATUS      current
    DESCRIPTION
        "Total number of bytes Dropped inbound using CHARM heuristics"
    ::= { poStatsEntry 1105 }

poOutCharmDroppedBytesCnt OBJECT-TYPE
    SYNTAX      Counter64
    MAX-ACCESS  read-only
    STATUS      current
    DESCRIPTION
        "Total number of bytes Dropped outbound using CHARM heuristics"
    ::= { poStatsEntry 1106 }

poInTotalPpsCnt OBJECT-TYPE
    SYNTAX      Counter32
    MAX-ACCESS  read-only
    STATUS      current
    DESCRIPTION
	"Total packets/sec traffic rate inbound since last restart or reset"
    ::= { poStatsEntry 1109 }

poOutTotalPpsCnt OBJECT-TYPE
    SYNTAX      Counter32
    MAX-ACCESS  read-only
    STATUS      current
    DESCRIPTION
	"Total packets/sec traffic rate outbound since last
         restart or reset"
    ::= { poStatsEntry 1110 }

poInSmallPpsCnt OBJECT-TYPE
    SYNTAX      Counter32
    MAX-ACCESS  read-only
    STATUS      current
    DESCRIPTION
	"Total inbound packets (256 bytes or less) per second processed. Dropped data is not included"
    ::= { poStatsEntry 1111 }

poOutSmallPpsCnt OBJECT-TYPE
    SYNTAX      Counter32
    MAX-ACCESS  read-only
    STATUS      current
    DESCRIPTION
	"Total outbound packets (256 bytes or less) per second processed. Dropped data is not included"
    ::= { poStatsEntry 1112 }

poInMediumPpsCnt OBJECT-TYPE
    SYNTAX      Counter32
    MAX-ACCESS  read-only
    STATUS      current
    DESCRIPTION
	"Total inbound packets (1024 bytes or less, but greater than 256 bytes) per second. Dropped data is not included"
    ::= { poStatsEntry 1113 }

poOutMediumPpsCnt OBJECT-TYPE
    SYNTAX      Counter32
    MAX-ACCESS  read-only
    STATUS      current
    DESCRIPTION
	"Total outbound packets (1024 bytes or less, but greater than 256 bytes) per second. Dropped data is not included"
    ::= { poStatsEntry 1114 }

poInLargePpsCnt OBJECT-TYPE
    SYNTAX      Counter32
    MAX-ACCESS  read-only
    STATUS      current
    DESCRIPTION
	"Total inbound packets (greater than 1024 bytes) per second. Dropped data is not included"
    ::= { poStatsEntry 1115 }

poOutLargePpsCnt OBJECT-TYPE
    SYNTAX      Counter32
    MAX-ACCESS  read-only
    STATUS      current
    DESCRIPTION
	"Total outbound packets (greater than 1024 bytes) per second. Dropped data is not included"
    ::= { poStatsEntry 1116 }

poInDroppedPpsCnt OBJECT-TYPE
    SYNTAX      Counter32
    MAX-ACCESS  read-only
    STATUS      current
    DESCRIPTION
	"Total number of input packets Dropped per second"
    ::= { poStatsEntry 1119 }

poOutDroppedPpsCnt OBJECT-TYPE
    SYNTAX      Counter32
    MAX-ACCESS  read-only
    STATUS      current
    DESCRIPTION
	"Total number of output packets Dropped per second"
     ::= { poStatsEntry 1120 }

poInFilteredBwthPercentCnt OBJECT-TYPE
    SYNTAX      Counter32
    MAX-ACCESS  read-only
    STATUS      current
    DESCRIPTION
	"Total inbound dropped bandwidth divided by the actual bandwidth"
    ::= { poStatsEntry 1121 }

poOutFilteredBwthPercentCnt OBJECT-TYPE
    SYNTAX      Counter32
    MAX-ACCESS  read-only
    STATUS      current
    DESCRIPTION
	"Total outbound dropped bandwidth divided by the actual bandwidth"
    ::= { poStatsEntry 1122 }

poInConnreqCnt OBJECT-TYPE
    SYNTAX      Counter32
    MAX-ACCESS  read-only
    STATUS      current
    DESCRIPTION
	"Total number of inbound TCP connection requests"
    ::= { poStatsEntry 1123 }

poOutConnreqCnt OBJECT-TYPE
    SYNTAX      Counter32
    MAX-ACCESS  read-only
    STATUS      current
    DESCRIPTION
	"Total number of outbound TCP connection requests"
    ::= { poStatsEntry 1124 }

poIncidentTable OBJECT-TYPE
    SYNTAX SEQUENCE OF PoIncidentEntry
    MAX-ACCESS  not-accessible
    STATUS      current
    DESCRIPTION
        "Table of portal incident entries"
    ::= { jddsPortal 5 }

poIncidentEntry OBJECT-TYPE
    SYNTAX   PoIncidentEntry
    MAX-ACCESS  not-accessible
    STATUS      current
    DESCRIPTION
        "A row consisting of an incident record for a specific portal"
    INDEX { poIncidentYear,
            poIncidentMonth,
            poIncidentDay,
            poIncidentNumber}
    ::= {poIncidentTable 1 }

PoIncidentEntry ::= SEQUENCE {
    poIncidentYear
       LocalIndex,
    poIncidentMonth
       LocalIndex,
    poIncidentDay
       LocalIndex,
    poIncidentNumber
       LocalIndex,
    poIncidentPortalName
       DisplayString,
    poIncidentStart
       DateAndTime,
    poIncidentAddress
       DisplayString,
    poIncidentType
       DisplayString,
    poIncidentDirection
       Direction,
    poIncidentPeakRate
       Gauge32,
    poIncidentDropped
       Gauge32
}

poIncidentYear OBJECT-TYPE
    SYNTAX      LocalIndex
    MAX-ACCESS  not-accessible
    STATUS      current
    DESCRIPTION
        "Incident record year"
    ::= {poIncidentEntry 1 }

poIncidentMonth OBJECT-TYPE
    SYNTAX      LocalIndex
    MAX-ACCESS  not-accessible
    STATUS      current
    DESCRIPTION
        "Incident record month"
    ::= {poIncidentEntry 2 }

poIncidentDay OBJECT-TYPE
    SYNTAX      LocalIndex
    MAX-ACCESS  not-accessible
    STATUS      current
    DESCRIPTION
        "Incident record day of month"
    ::= {poIncidentEntry 3 }

poIncidentNumber OBJECT-TYPE
    SYNTAX      LocalIndex
    MAX-ACCESS  not-accessible
    STATUS      current
    DESCRIPTION
        "Unique (for the day) incident record number"
    ::= {poIncidentEntry 4 }

poIncidentPortalName OBJECT-TYPE
    SYNTAX      DisplayString
    MAX-ACCESS  read-only
    STATUS      current
    DESCRIPTION
        "The name associated with this portal"
    ::= { poIncidentEntry 5 }

poIncidentStart OBJECT-TYPE
    SYNTAX      DateAndTime
    MAX-ACCESS  read-only
    STATUS      current
    DESCRIPTION
        "Incident start time"
    ::= {poIncidentEntry 6 }

poIncidentAddress OBJECT-TYPE
    SYNTAX      DisplayString
    MAX-ACCESS  read-only
    STATUS      current
    DESCRIPTION
        "Portal or Protected address affected by the incident. IP or MAC Address "
    ::= {poIncidentEntry 7 }

poIncidentType OBJECT-TYPE
    SYNTAX      DisplayString
    MAX-ACCESS  read-only
    STATUS      current
    DESCRIPTION
        "Incident defense type (and subtype)"
    ::= {poIncidentEntry 8 }

poIncidentDirection OBJECT-TYPE
    SYNTAX      Direction
    MAX-ACCESS  read-only
    STATUS      current
    DESCRIPTION
        "Incident direction"
    ::= {poIncidentEntry 9 }

poIncidentPeakRate OBJECT-TYPE
    SYNTAX      Gauge32
    MAX-ACCESS  read-only
    STATUS      current
    DESCRIPTION
        "Peak packets/s during this incident"
    ::= {poIncidentEntry 10 }

poIncidentDropped OBJECT-TYPE
    SYNTAX      Gauge32
    MAX-ACCESS  read-only
    STATUS      current
    DESCRIPTION
        "No of packets Dropped as part of this incident"
    ::= {poIncidentEntry 11 }


-- ### Portal Filter settings ###

poFiltersTable OBJECT-TYPE
    SYNTAX SEQUENCE OF PoFiltersEntry
    MAX-ACCESS  not-accessible
    STATUS      current
    DESCRIPTION
        "Table of filter configurations"
    ::= { jddsPortal 6 }

poFiltersEntry OBJECT-TYPE
    SYNTAX      PoFiltersEntry
    MAX-ACCESS  not-accessible
    STATUS      current
    DESCRIPTION
        "A row associated with a specific portal filter"
    INDEX { poFilterIndex }
    ::= { poFiltersTable 1 }

PoFiltersEntry ::= SEQUENCE {
    poFilterIndex
       LocalIndex,
    poFilterName
       DisplayString,
    poTcpPortsList
       DisplayString,
    poUdpPortsList
       DisplayString,
    poIcmpTypesList
       DisplayString,
    poIpProtocolsList
       DisplayString
}

poFilterIndex OBJECT-TYPE
    SYNTAX      LocalIndex
    MAX-ACCESS  not-accessible
    STATUS      current
    DESCRIPTION
        "Unique filter index"
    ::= { poFiltersEntry 1 }

poFilterName OBJECT-TYPE
    SYNTAX      DisplayString
    MAX-ACCESS  read-only
    STATUS      current
    DESCRIPTION
        "Identifying filter name"
    ::= { poFiltersEntry 2 }

poTcpPortsList OBJECT-TYPE
    SYNTAX      DisplayString
    MAX-ACCESS  read-only
    STATUS      current
    DESCRIPTION
        "Comma separated list of TCP ports to allow"
    ::= { poFiltersEntry 3 }

poUdpPortsList OBJECT-TYPE
    SYNTAX      DisplayString
    MAX-ACCESS  read-only
    STATUS      current
    DESCRIPTION
        "Comma separated list of UDP ports to allow"
    ::= { poFiltersEntry 4 }

poIcmpTypesList OBJECT-TYPE
    SYNTAX      DisplayString
    MAX-ACCESS  read-only
    STATUS      current
    DESCRIPTION
        "Comma separated list of ICMP types to allow"
    ::= { poFiltersEntry 5 }

poIpProtocolsList OBJECT-TYPE
    SYNTAX      DisplayString
    MAX-ACCESS  read-only
    STATUS      current
    DESCRIPTION
        "Comma separated list of other IP Protocols to allow"
    ::= { poFiltersEntry 6 }

-- ### protected IP Statistics ###

-- **   prStatsTable
prStatsTable OBJECT-TYPE
    SYNTAX SEQUENCE OF PrStatsEntry
    MAX-ACCESS  not-accessible
    STATUS      current
    DESCRIPTION
        "Table of protected IP statistics"
    ::= { jddsProtected 3 }


prStatsEntry OBJECT-TYPE
    SYNTAX      PrStatsEntry
    MAX-ACCESS  not-accessible
    STATUS      current
    DESCRIPTION
        "A row associated with a specific protected IP"
    INDEX {  prInetAddressType,
             prInetAddress }
    ::= { prStatsTable 1 }

PrStatsEntry ::= SEQUENCE {
   prInetAddressType
	InetAddressType,
   prInetAddress
	InetAddress,
   prBandwidth
	TruthValue,
   prFlood
	TruthValue,
   prBlockedProtocol
	TruthValue,
   prBlockedState
	TruthValue,
   prIpAttack
	TruthValue,
   prTcpAttack
	TruthValue,
   prUdpAttack
	TruthValue,
   prIcmpAttack
	TruthValue,
   prOtherIpAttack
	TruthValue,
   prFragAttack
	TruthValue,
   prBadIp
	TruthValue,
   prBadTcp
	TruthValue,
   prBadUdp
	TruthValue,
   prBadIcmp
	TruthValue,
   prBadOtherIp
	TruthValue,
   prOverloaded
	TruthValue,
   prInSyn
	Gauge32,
   prOutSyn
	Gauge32,
   prInSynAck
	Gauge32,
   prOutSynAck
	Gauge32,
   prInSynSyn
	Gauge32,
   prOutSynSyn
	Gauge32,
   prInAck
	Gauge32,
   prOutAck
	Gauge32,
   prInPendAck
	Gauge32,
   prOutPendAck
	Gauge32,
   prInGet
	Gauge32,
   prOutGet
	Gauge32,
   prInEst
	Gauge32,
   prOutEst
	Gauge32,
   prInFin1Src
	Gauge32,
   prOutFin1Src
	Gauge32,
   prInFin2Src
	Gauge32,
   prOutFin2Src
	Gauge32,
   prInFin3Src
	Gauge32,
   prOutFin3Src
	Gauge32,
   prInFinFin
	Gauge32,
   prOutFinFin
	Gauge32,
   prInFin1Dst
	Gauge32,
   prOutFin1Dst
	Gauge32,
   prInFin2Dst
	Gauge32,
   prOutFin2Dst
	Gauge32,
   prInFin3Dst
	Gauge32,
   prOutFin3Dst
	Gauge32,
   prInCls
	Gauge32,
   prOutCls
	Gauge32,
   prInRst
	Gauge32,
   prOutRst
	Gauge32,
   prInRstCls
	Gauge32,
   prOutRstCls
	Gauge32,
   prInUnknown
	Gauge32,
   prOutUnknown
	Gauge32,
   prInGets
	Gauge32,
   prOutGets
	Gauge32,
   prOverloadedFlag
	TruthValue,
   prInTcpConnTally
	Counter32,
   prOutTcpConnTally
	Counter32,
   prInSynBacklogTally
	Counter32,
   prInTotalBytesCnt
	Counter64,
   prOutTotalBytesCnt
	Counter64,
   prInDroppedBytesCnt
	Counter64,
   prOutDroppedBytesCnt
	Counter64,
   prInCharmDroppedBytesCnt
	Counter64,
   prOutCharmDroppedBytesCnt
	Counter64,
   prInTotalPpsMax
	Gauge32,
   prOutTotalPpsMax
	Gauge32,
   prInDroppedPpsMax
	Gauge32,
   prOutDroppedPpsMax
	Gauge32,
   prInTotalBpsMax
	Gauge32,
   prOutTotalBpsMax
	Gauge32,
   prInDroppedBpsMax
	Gauge32,
   prOutDroppedBpsMax
	Gauge32,
   prInCharmDroppedBpsMax
	Gauge32,
   prOutCharmDroppedBpsMax
	Gauge32,
   prInProtectBwthPktsCnt
	Counter32,
   prOutProtectBwthPktsCnt
	Counter32,
   prInFloodPktsCnt
	Counter32,
   prOutFloodPktsCnt
	Counter32,
   prInBlockedProtocolPktsCnt
	Counter32,
   prOutBlockedProtocolPktsCnt
	Counter32,
   prInBlockedStatePktsCnt
	Counter32,
   prOutBlockedStatePktsCnt
	Counter32,
   prInIpAttackPktsCnt
	Counter32,
   prOutIpAttackPktsCnt
	Counter32,
   prInTcpAttackPktsCnt
	Counter32,
   prOutTcpAttackPktsCnt
	Counter32,
   prInUdpAttackPktsCnt
	Counter32,
   prOutUdpAttackPktsCnt
	Counter32,
   prInIcmpAttackPktsCnt
	Counter32,
   prOutIcmpAttackPktsCnt
	Counter32,
   prInOtherIpAttackPktsCnt
	Counter32,
   prOutOtherIpAttackPktsCnt
	Counter32,
   prInFragmentAttackPktsCnt
	Counter32,
   prOutFragmentAttackPktsCnt
	Counter32,
   prInBadIpPktsCnt
	Counter32,
   prOutBadIpPktsCnt
	Counter32,
   prInBadTcpPktsCnt
	Counter32,
   prOutBadTcpPktsCnt
	Counter32,
   prInBadUdpPktsCnt
	Counter32,
   prOutBadUdpPktsCnt
	Counter32,
   prInBadIcmpPktsCnt
	Counter32,
   prOutBadIcmpPktsCnt
	Counter32,
   prInBadOtherIpPktsCnt
	Counter32,
   prOutBadOtherIpPktsCnt
	Counter32,
   prInTotalBpsAvg
	Gauge32,
   prOutTotalBpsAvg
	Gauge32,
   prInTotalPpsAvg
	Gauge32,
   prOutTotalPpsAvg
	Gauge32,
   prInSmallPpsAvg
	Gauge32,
   prOutSmallPpsAvg
	Gauge32,
   prInMediumPpsAvg
	Gauge32,
   prOutMediumPpsAvg
	Gauge32,
   prInLargePpsAvg
	Gauge32,
   prOutLargePpsAvg
	Gauge32,
   prInDroppedBpsAvg
	Gauge32,
   prOutDroppedBpsAvg
	Gauge32,
   prInDroppedPpsAvg
	Gauge32,
   prOutDroppedPpsAvg
	Gauge32,
   prInCharmDroppedBpsAvg
	Gauge32,
   prOutCharmDroppedBpsAvg
	Gauge32,
   prInFilteredBwthPercentAvg
	Gauge32,
   prOutFilteredBwthPercentAvg
	Gauge32,
   prInSynbacklogtallyAvg
	Gauge32,
   prOutSynbacklogtallyAvg
	Gauge32,
   prInConnectionAvg
	Gauge32,
   prOutConnectionAvg
	Gauge32,
   prInConnreqAvg
	Gauge32,
   prOutConnreqAvg
	Gauge32,
   prInActiveHttpGetsAvg
	Gauge32,
   prOutActiveHttpGetsAvg
	Gauge32,
   prInProtectBwthPktsAvg
	Gauge32,
   prOutProtectBwthPktsAvg
	Gauge32,
   prInFloodPktsAvg
	Gauge32,
   prOutFloodPktsAvg
	Gauge32,
   prInBlockedProtocolPktsAvg
	Gauge32,
   prOutBlockedProtocolPktsAvg
	Gauge32,
   prInBlockedStatePktsAvg
	Gauge32,
   prOutBlockedStatePktsAvg
	Gauge32,
   prInIpAttackPktsAvg
	Gauge32,
   prOutIpAttackPktsAvg
	Gauge32,
   prInTcpAttackPktsAvg
	Gauge32,
   prOutTcpAttackPktsAvg
	Gauge32,
   prInUdpAttackPktsAvg
	Gauge32,
   prOutUdpAttackPktsAvg
	Gauge32,
   prInIcmpAttackPktsAvg
	Gauge32,
   prOutIcmpAttackPktsAvg
	Gauge32,
   prInOtherIpAttackPktsAvg
	Gauge32,
   prOutOtherIpAttackPktsAvg
	Gauge32,
   prInFragmentAttackPktsAvg
	Gauge32,
   prOutFragmentAttackPktsAvg
	Gauge32,
   prInBadipPktsAvg
	Gauge32,
   prOutBadipPktsAvg
	Gauge32,
   prInBadTcpPktsAvg
	Gauge32,
   prOutBadTcpPktsAvg
	Gauge32,
   prInBadUdpPktsAvg
	Gauge32,
   prOutBadUdpPktsAvg
	Gauge32,
   prInBadIcmpPktsAvg
	Gauge32,
   prOutBadIcmpPktsAvg
	Gauge32,
   prInBadOtherIpPktsAvg
	Gauge32,
   prOutBadOtherIpPktsAvg
	Gauge32,
   prInOverloadedAvg
	Gauge32,
   prOutOverloadedAvg
	Gauge32,
   prInLatencyAvg
	Gauge32,
   prOutLatencyAvg
	Gauge32,
   prInSmallPpsMax
	Gauge32,
   prOutSmallPpsMax
	Gauge32,
   prInMediumPpsMax
	Gauge32,
   prOutMediumPpsMax
	Gauge32,
   prInLargePpsMax
	Gauge32,
   prOutLargePpsMax
	Gauge32,
   prInFilteredBwthPercentMax
	Gauge32,
   prOutFilteredBwthPercentMax
	Gauge32,
   prInSynbacklogtallyMax
	Gauge32,
   prOutSynbacklogtallyMax
	Gauge32,
   prInConnectionMax
	Gauge32,
   prOutConnectionMax
	Gauge32,
   prInConnreqMax
	Gauge32,
   prOutConnreqMax
	Gauge32,
   prInActiveHttpGetsMax
	Gauge32,
   prOutActiveHttpGetsMax
	Gauge32,
   prInProtectBwthPktsMax
	Gauge32,
   prOutProtectBwthPktsMax
	Gauge32,
   prInFloodPktsMax
	Gauge32,
   prOutFloodPktsMax
	Gauge32,
   prInBlockedProtocolPktsMax
	Gauge32,
   prOutBlockedProtocolPktsMax
	Gauge32,
   prInBlockedStatePktsMax
	Gauge32,
   prOutBlockedStatePktsMax
	Gauge32,
   prInIpAttackPktsMax
	Gauge32,
   prOutIpAttackPktsMax
	Gauge32,
   prInTcpAttackPktsMax
	Gauge32,
   prOutTcpAttackPktsMax
	Gauge32,
   prInUdpAttackPktsMax
	Gauge32,
   prOutUdpAttackPktsMax
	Gauge32,
   prInIcmpAttackPktsMax
	Gauge32,
   prOutIcmpAttackPktsMax
	Gauge32,
   prInOtherIpAttackPktsMax
	Gauge32,
   prOutOtherIpAttackPktsMax
	Gauge32,
   prInFragmentAttackPktsMax
	Gauge32,
   prOutFragmentAttackPktsMax
	Gauge32,
   prInBadipPktsMax
	Gauge32,
   prOutBadipPktsMax
	Gauge32,
   prInBadTcpPktsMax
	Gauge32,
   prOutBadTcpPktsMax
	Gauge32,
   prInBadUdpPktsMax
	Gauge32,
   prOutBadUdpPktsMax
	Gauge32,
   prInBadIcmpPktsMax
	Gauge32,
   prOutBadIcmpPktsMax
	Gauge32,
   prInBadOtherIpPktsMax
	Gauge32,
   prOutBadOtherIpPktsMax
	Gauge32,
   prInOverloadedMax
	Gauge32,
   prOutOverloadedMax
	Gauge32,
   prInLatencyMax
	Gauge32,
   prOutLatencyMax
	Gauge32
}


prInetAddressType OBJECT-TYPE
    SYNTAX      InetAddressType
    MAX-ACCESS  not-accessible
    STATUS      current
    DESCRIPTION
	"Type of IP address a specific protected IP"
     ::= { prStatsEntry 1 }

prInetAddress OBJECT-TYPE
    SYNTAX      InetAddress (SIZE (0..47))
    MAX-ACCESS  not-accessible
    STATUS      current
    DESCRIPTION
	"IP address of a specific protected IP"
     ::= { prStatsEntry 2 }

prBandwidth OBJECT-TYPE
    SYNTAX      TruthValue
    MAX-ACCESS  read-only
    STATUS      current
    DESCRIPTION
	"TRUE if defending bandwidth"
     ::= { prStatsEntry 101 }

prFlood OBJECT-TYPE
    SYNTAX      TruthValue
    MAX-ACCESS  read-only
    STATUS      current
    DESCRIPTION
	"TRUE if defending against floods"
     ::= { prStatsEntry 102 }

prBlockedProtocol OBJECT-TYPE
    SYNTAX      TruthValue
    MAX-ACCESS  read-only
    STATUS      current
    DESCRIPTION
	"TRUE if defending against Connection floods"
     ::= { prStatsEntry 103 }

prBlockedState OBJECT-TYPE
    SYNTAX      TruthValue
    MAX-ACCESS  read-only
    STATUS      current
    DESCRIPTION
	"TRUE if defending against Connection floods"
     ::= { prStatsEntry 104 }

prIpAttack OBJECT-TYPE
    SYNTAX      TruthValue
    MAX-ACCESS  read-only
    STATUS      current
    DESCRIPTION
	"TRUE if defending against IP Attack"
     ::= { prStatsEntry 105 }

prTcpAttack OBJECT-TYPE
    SYNTAX      TruthValue
    MAX-ACCESS  read-only
    STATUS      current
    DESCRIPTION
	"TRUE if defending against TCP Attack"
     ::= { prStatsEntry 106 }

prUdpAttack OBJECT-TYPE
    SYNTAX      TruthValue
    MAX-ACCESS  read-only
    STATUS      current
    DESCRIPTION
	"TRUE if defending against UDP Attack"
     ::= { prStatsEntry 107 }

prIcmpAttack OBJECT-TYPE
    SYNTAX      TruthValue
    MAX-ACCESS  read-only
    STATUS      current
    DESCRIPTION
	"TRUE if defending against ICMP Attack"
     ::= { prStatsEntry 108 }

prOtherIpAttack OBJECT-TYPE
    SYNTAX      TruthValue
    MAX-ACCESS  read-only
    STATUS      current
    DESCRIPTION
	"TRUE if defending against Other IP Protocol Attack"
     ::= { prStatsEntry 109 }

prFragAttack OBJECT-TYPE
    SYNTAX      TruthValue
    MAX-ACCESS  read-only
    STATUS      current
    DESCRIPTION
	"TRUE if defending against Fragment Attack"
     ::= { prStatsEntry 110 }

prBadIp OBJECT-TYPE
    SYNTAX      TruthValue
    MAX-ACCESS  read-only
    STATUS      current
    DESCRIPTION
	"TRUE if defending against Bad IP packets"
     ::= { prStatsEntry 111 }

prBadTcp OBJECT-TYPE
    SYNTAX      TruthValue
    MAX-ACCESS  read-only
    STATUS      current
    DESCRIPTION
	"TRUE if defending against Bad TCP packets"
     ::= { prStatsEntry 112 }

prBadUdp OBJECT-TYPE
    SYNTAX      TruthValue
    MAX-ACCESS  read-only
    STATUS      current
    DESCRIPTION
	"TRUE if defending against Bad UDP packets"
     ::= { prStatsEntry 113 }

prBadIcmp OBJECT-TYPE
    SYNTAX      TruthValue
    MAX-ACCESS  read-only
    STATUS      current
    DESCRIPTION
	"TRUE if defending against Bad ICMP packets"
     ::= { prStatsEntry 114 }

prBadOtherIp OBJECT-TYPE
    SYNTAX      TruthValue
    MAX-ACCESS  read-only
    STATUS      current
    DESCRIPTION
	"TRUE if defending against Bad other IP Protocol packets"
     ::= { prStatsEntry 115 }

prOverloaded OBJECT-TYPE
    SYNTAX      TruthValue
    MAX-ACCESS  read-only
    STATUS      current
    DESCRIPTION
	"TRUE if protected IP is overloaded"
     ::= { prStatsEntry 116 }

prInSyn OBJECT-TYPE
    SYNTAX      Gauge32
    MAX-ACCESS  read-only
    STATUS      current
    DESCRIPTION
	"Count of TCP connections in given state"
     ::= { prStatsEntry 201 }

prOutSyn OBJECT-TYPE
    SYNTAX      Gauge32
    MAX-ACCESS  read-only
    STATUS      current
    DESCRIPTION
	"Count of TCP connections in given state"
     ::= { prStatsEntry 202 }

prInSynAck OBJECT-TYPE
    SYNTAX      Gauge32
    MAX-ACCESS  read-only
    STATUS      current
    DESCRIPTION
	"Count of TCP connections in given state"
     ::= { prStatsEntry 203 }

prOutSynAck OBJECT-TYPE
    SYNTAX      Gauge32
    MAX-ACCESS  read-only
    STATUS      current
    DESCRIPTION
	"Count of TCP connections in given state"
     ::= { prStatsEntry 204 }

prInSynSyn OBJECT-TYPE
    SYNTAX      Gauge32
    MAX-ACCESS  read-only
    STATUS      current
    DESCRIPTION
	"Count of TCP connections in given state"
     ::= { prStatsEntry 205 }

prOutSynSyn OBJECT-TYPE
    SYNTAX      Gauge32
    MAX-ACCESS  read-only
    STATUS      current
    DESCRIPTION
	"Count of TCP connections in given state"
     ::= { prStatsEntry 206 }

prInAck OBJECT-TYPE
    SYNTAX      Gauge32
    MAX-ACCESS  read-only
    STATUS      current
    DESCRIPTION
	"Count of TCP connections in given state"
    ::= { prStatsEntry 207 }

prOutAck OBJECT-TYPE
    SYNTAX      Gauge32
    MAX-ACCESS  read-only
    STATUS      current
    DESCRIPTION
	"Count of TCP connections in given state"
    ::= { prStatsEntry 208 }

prInPendAck OBJECT-TYPE
    SYNTAX      Gauge32
    MAX-ACCESS  read-only
    STATUS      current
    DESCRIPTION
	"Count of TCP connections in given state"
    ::= { prStatsEntry 209 }

prOutPendAck OBJECT-TYPE
    SYNTAX      Gauge32
    MAX-ACCESS  read-only
    STATUS      current
    DESCRIPTION
	"Count of TCP connections in given state"
    ::= { prStatsEntry 210 }

prInGet OBJECT-TYPE
    SYNTAX      Gauge32
    MAX-ACCESS  read-only
    STATUS      current
    DESCRIPTION
	"Count of TCP connections in given state"
    ::= { prStatsEntry 211 }

prOutGet OBJECT-TYPE
    SYNTAX      Gauge32
    MAX-ACCESS  read-only
    STATUS      current
    DESCRIPTION
	"Count of TCP connections in given state"
    ::= { prStatsEntry 212 }

prInEst OBJECT-TYPE
    SYNTAX      Gauge32
    MAX-ACCESS  read-only
    STATUS      current
    DESCRIPTION
	"Count of TCP connections in given state"
     ::= { prStatsEntry 213 }

prOutEst OBJECT-TYPE
    SYNTAX      Gauge32
    MAX-ACCESS  read-only
    STATUS      current
    DESCRIPTION
	"Count of TCP connections in given state"
     ::= { prStatsEntry 214 }

prInFin1Src OBJECT-TYPE
    SYNTAX      Gauge32
    MAX-ACCESS  read-only
    STATUS      current
    DESCRIPTION
	"Count of TCP connections in given state"
     ::= { prStatsEntry 215 }

prOutFin1Src OBJECT-TYPE
    SYNTAX      Gauge32
    MAX-ACCESS  read-only
    STATUS      current
    DESCRIPTION
	"Count of TCP connections in given state"
     ::= { prStatsEntry 216 }

prInFin2Src OBJECT-TYPE
    SYNTAX      Gauge32
    MAX-ACCESS  read-only
    STATUS      current
    DESCRIPTION
	"Count of TCP connections in given state"
     ::= { prStatsEntry 217 }

prOutFin2Src OBJECT-TYPE
    SYNTAX      Gauge32
    MAX-ACCESS  read-only
    STATUS      current
    DESCRIPTION
	"Count of TCP connections in given state"
     ::= { prStatsEntry 218 }

prInFin3Src OBJECT-TYPE
    SYNTAX      Gauge32
    MAX-ACCESS  read-only
    STATUS      current
    DESCRIPTION
	"Count of TCP connections in given state"
     ::= { prStatsEntry 219 }

prOutFin3Src OBJECT-TYPE
    SYNTAX      Gauge32
    MAX-ACCESS  read-only
    STATUS      current
    DESCRIPTION
	"Count of TCP connections in given state"
     ::= { prStatsEntry 220 }

prInFinFin OBJECT-TYPE
    SYNTAX      Gauge32
    MAX-ACCESS  read-only
    STATUS      current
    DESCRIPTION
	"Count of TCP connections in given state"
     ::= { prStatsEntry 221 }

prOutFinFin OBJECT-TYPE
    SYNTAX      Gauge32
    MAX-ACCESS  read-only
    STATUS      current
    DESCRIPTION
	"Count of TCP connections in given state"
     ::= { prStatsEntry 222 }

prInFin1Dst OBJECT-TYPE
    SYNTAX      Gauge32
    MAX-ACCESS  read-only
    STATUS      current
    DESCRIPTION
	"Count of TCP connections in given state"
     ::= { prStatsEntry 223 }

prOutFin1Dst OBJECT-TYPE
    SYNTAX      Gauge32
    MAX-ACCESS  read-only
    STATUS      current
    DESCRIPTION
	"Count of TCP connections in given state"
     ::= { prStatsEntry 224 }

prInFin2Dst OBJECT-TYPE
    SYNTAX      Gauge32
    MAX-ACCESS  read-only
    STATUS      current
    DESCRIPTION
	"Count of TCP connections in given state"
     ::= { prStatsEntry 225 }

prOutFin2Dst OBJECT-TYPE
    SYNTAX      Gauge32
    MAX-ACCESS  read-only
    STATUS      current
    DESCRIPTION
	"Count of TCP connections in given state"
     ::= { prStatsEntry 226 }

prInFin3Dst OBJECT-TYPE
    SYNTAX      Gauge32
    MAX-ACCESS  read-only
    STATUS      current
    DESCRIPTION
	"Count of TCP connections in given state"
     ::= { prStatsEntry 227 }

prOutFin3Dst OBJECT-TYPE
    SYNTAX      Gauge32
    MAX-ACCESS  read-only
    STATUS      current
    DESCRIPTION
	"Count of TCP connections in given state"
     ::= { prStatsEntry 228 }

prInCls OBJECT-TYPE
    SYNTAX      Gauge32
    MAX-ACCESS  read-only
    STATUS      current
    DESCRIPTION
	"Count of TCP connections in given state"
     ::= { prStatsEntry 229 }

prOutCls OBJECT-TYPE
    SYNTAX      Gauge32
    MAX-ACCESS  read-only
    STATUS      current
    DESCRIPTION
	"Count of TCP connections in given state"
     ::= { prStatsEntry 230 }

prInRst OBJECT-TYPE
    SYNTAX      Gauge32
    MAX-ACCESS  read-only
    STATUS      current
    DESCRIPTION
	"Count of TCP connections in given state"
     ::= { prStatsEntry 231 }

prOutRst OBJECT-TYPE
    SYNTAX      Gauge32
    MAX-ACCESS  read-only
    STATUS      current
    DESCRIPTION
	"Count of TCP connections in given state"
     ::= { prStatsEntry 232 }

prInRstCls OBJECT-TYPE
    SYNTAX      Gauge32
    MAX-ACCESS  read-only
    STATUS      current
    DESCRIPTION
	"Count of TCP connections in given state"
     ::= { prStatsEntry 233 }

prOutRstCls OBJECT-TYPE
    SYNTAX      Gauge32
    MAX-ACCESS  read-only
    STATUS      current
    DESCRIPTION
	"Count of TCP connections in given state"
     ::= { prStatsEntry 234 }

prInUnknown OBJECT-TYPE
    SYNTAX      Gauge32
    MAX-ACCESS  read-only
    STATUS      current
    DESCRIPTION
	"Count of TCP connections in given state"
     ::= { prStatsEntry 235 }

prOutUnknown OBJECT-TYPE
    SYNTAX      Gauge32
    MAX-ACCESS  read-only
    STATUS      current
    DESCRIPTION
	"Count of TCP connections in given state"
     ::= { prStatsEntry 236 }

prInGets OBJECT-TYPE
    SYNTAX      Gauge32
    MAX-ACCESS  read-only
    STATUS      current
    DESCRIPTION
	"Count of inbound TCP connections to this protected IP processing GETS"
    ::= { prStatsEntry 237 }

prOutGets OBJECT-TYPE
    SYNTAX      Gauge32
    MAX-ACCESS  read-only
    STATUS      current
    DESCRIPTION
	"Count of outbound TCP connections from this protected IP processing GETS"
    ::= { prStatsEntry 238 }

prOverloadedFlag OBJECT-TYPE
    SYNTAX      TruthValue
    MAX-ACCESS  read-only
    STATUS      current
    DESCRIPTION
        "TRUE if protected IP overloaded"
    ::= { prStatsEntry 301 }

prInTcpConnTally OBJECT-TYPE
    SYNTAX Counter32
    MAX-ACCESS  read-only
    STATUS      current
    DESCRIPTION
	"Number of current TCP connections to protected IP originated by a client"
     ::= { prStatsEntry 401 }

prOutTcpConnTally OBJECT-TYPE
    SYNTAX Counter32
    MAX-ACCESS  read-only
    STATUS      current
    DESCRIPTION
	"Number of current TCP connections to protected IP originated by the protected IP itself"
     ::= { prStatsEntry 402 }

prInSynBacklogTally OBJECT-TYPE
    SYNTAX Counter32
    MAX-ACCESS  read-only
    STATUS      current
    DESCRIPTION
	"Current protected IP SYN backlog"
     ::= { prStatsEntry 403 }

prInTotalBytesCnt OBJECT-TYPE
    SYNTAX Counter64
    MAX-ACCESS  read-only
    STATUS      current
    DESCRIPTION
	"Total number of input bytes seen"
     ::= { prStatsEntry 501 }

prOutTotalBytesCnt OBJECT-TYPE
    SYNTAX Counter64
    MAX-ACCESS  read-only
    STATUS      current
    DESCRIPTION
	"Total number of output bytes seen"
     ::= { prStatsEntry 502 }

prInDroppedBytesCnt OBJECT-TYPE
    SYNTAX Counter64
    MAX-ACCESS  read-only
    STATUS      current
    DESCRIPTION
	"Total number of input bytes Dropped"
     ::= { prStatsEntry 503 }

prOutDroppedBytesCnt OBJECT-TYPE
    SYNTAX Counter64
    MAX-ACCESS  read-only
    STATUS      current
    DESCRIPTION
	"Total number of output bytes Dropped"
     ::= { prStatsEntry 504 }

prInCharmDroppedBytesCnt OBJECT-TYPE
    SYNTAX Counter64
    MAX-ACCESS  read-only
    STATUS      current
    DESCRIPTION
	"Number of input bytes Dropped through lack of charm"
     ::= { prStatsEntry 505 }

prOutCharmDroppedBytesCnt OBJECT-TYPE
    SYNTAX Counter64
    MAX-ACCESS  read-only
    STATUS      current
    DESCRIPTION
	"Number of output bytes Dropped through lack of charm"
     ::= { prStatsEntry 506 }

prInTotalPpsMax OBJECT-TYPE
    SYNTAX      Gauge32
    MAX-ACCESS  read-only
    STATUS      current
    DESCRIPTION
	"Maximum number of input packets per second"
     ::= { prStatsEntry 601 }

prOutTotalPpsMax OBJECT-TYPE
    SYNTAX      Gauge32
    MAX-ACCESS  read-only
    STATUS      current
    DESCRIPTION
	"Maximum number of output packets per second"
     ::= { prStatsEntry 602 }

prInDroppedPpsMax OBJECT-TYPE
    SYNTAX      Gauge32
    MAX-ACCESS  read-only
    STATUS      current
    DESCRIPTION
	"Maximum number of input packets Dropped per second"
     ::= { prStatsEntry 603 }

prOutDroppedPpsMax OBJECT-TYPE
    SYNTAX      Gauge32
    MAX-ACCESS  read-only
    STATUS      current
    DESCRIPTION
	"Maximum number of output packets Dropped per second"
     ::= { prStatsEntry 604 }

prInTotalBpsMax OBJECT-TYPE
    SYNTAX      Gauge32
    MAX-ACCESS  read-only
    STATUS      current
    DESCRIPTION
	"Maximum number of input bits per second"
     ::= { prStatsEntry 701 }

prOutTotalBpsMax OBJECT-TYPE
    SYNTAX      Gauge32
    MAX-ACCESS  read-only
    STATUS      current
    DESCRIPTION
	"Maximum number of output bits per second"
     ::= { prStatsEntry 702 }

prInDroppedBpsMax OBJECT-TYPE
    SYNTAX      Gauge32
    MAX-ACCESS  read-only
    STATUS      current
    DESCRIPTION
	"Maximum number of input bits Dropped per second"
     ::= { prStatsEntry 703 }

prOutDroppedBpsMax OBJECT-TYPE
    SYNTAX      Gauge32
    MAX-ACCESS  read-only
    STATUS      current
    DESCRIPTION
	"Maximum number of output bits Dropped per second"
     ::= { prStatsEntry 704 }

prInCharmDroppedBpsMax OBJECT-TYPE
    SYNTAX      Gauge32
    MAX-ACCESS  read-only
    STATUS      current
    DESCRIPTION
	"Maximum number of input bits Dropped per second through lack of charm"
     ::= { prStatsEntry 705 }

prOutCharmDroppedBpsMax OBJECT-TYPE
    SYNTAX      Gauge32
    MAX-ACCESS  read-only
    STATUS      current
    DESCRIPTION
	"Maximum number of output bits Dropped per second through lack of charm"
     ::= { prStatsEntry 706 }

prInProtectBwthPktsCnt OBJECT-TYPE
    SYNTAX Counter32
    MAX-ACCESS  read-only
    STATUS      current
    DESCRIPTION
	"Number of input packets Dropped through bandwidth protection"
     ::= { prStatsEntry 801 }

prOutProtectBwthPktsCnt OBJECT-TYPE
    SYNTAX Counter32
    MAX-ACCESS  read-only
    STATUS      current
    DESCRIPTION
	"Number of output packets Dropped through bandwidth protection"
     ::= { prStatsEntry 802 }

prInFloodPktsCnt OBJECT-TYPE
    SYNTAX Counter32
    MAX-ACCESS  read-only
    STATUS      current
    DESCRIPTION
	"Number of input packets Dropped through flood protection"
     ::= { prStatsEntry 803 }

prOutFloodPktsCnt OBJECT-TYPE
    SYNTAX Counter32
    MAX-ACCESS  read-only
    STATUS      current
    DESCRIPTION
	"Number of output packets Dropped through flood protection"
     ::= { prStatsEntry 804 }

prInBlockedProtocolPktsCnt OBJECT-TYPE
    SYNTAX Counter32
    MAX-ACCESS  read-only
    STATUS      current
    DESCRIPTION
	"Number of input packets Dropped through blocked Protocol protection"
     ::= { prStatsEntry 805 }

prOutBlockedProtocolPktsCnt OBJECT-TYPE
    SYNTAX Counter32
    MAX-ACCESS  read-only
    STATUS      current
    DESCRIPTION
	"Number of output packets Dropped through blocked Protocol protection"
     ::= { prStatsEntry 806 }

prInBlockedStatePktsCnt OBJECT-TYPE
    SYNTAX Counter32
    MAX-ACCESS  read-only
    STATUS      current
    DESCRIPTION
	"Number of input packets Dropped through blocked state protection"
     ::= { prStatsEntry 807 }

prOutBlockedStatePktsCnt OBJECT-TYPE
    SYNTAX Counter32
    MAX-ACCESS  read-only
    STATUS      current
    DESCRIPTION
	"Number of output packets Dropped through blocked state protection"
     ::= { prStatsEntry 808 }

prInIpAttackPktsCnt OBJECT-TYPE
    SYNTAX Counter32
    MAX-ACCESS  read-only
    STATUS      current
    DESCRIPTION
	"Number of input packets Dropped through IP Attack"
     ::= { prStatsEntry 809 }

prOutIpAttackPktsCnt OBJECT-TYPE
    SYNTAX Counter32
    MAX-ACCESS  read-only
    STATUS      current
    DESCRIPTION
	"Number of output packets Dropped through IP Attack"
     ::= { prStatsEntry 810 }

prInTcpAttackPktsCnt OBJECT-TYPE
    SYNTAX Counter32
    MAX-ACCESS  read-only
    STATUS      current
    DESCRIPTION
	"Number of input packets Dropped through TCP Attack"
     ::= { prStatsEntry 811 }

prOutTcpAttackPktsCnt OBJECT-TYPE
    SYNTAX Counter32
    MAX-ACCESS  read-only
    STATUS      current
    DESCRIPTION
	"Number of output packets Dropped through TCP Attack"
     ::= { prStatsEntry 812 }

prInUdpAttackPktsCnt OBJECT-TYPE
    SYNTAX Counter32
    MAX-ACCESS  read-only
    STATUS      current
    DESCRIPTION
	"Number of input packets Dropped through UDP Attack"
     ::= { prStatsEntry 813 }

prOutUdpAttackPktsCnt OBJECT-TYPE
    SYNTAX Counter32
    MAX-ACCESS  read-only
    STATUS      current
    DESCRIPTION
	"Number of output packets Dropped through UDP Attack"
     ::= { prStatsEntry 814 }

prInIcmpAttackPktsCnt OBJECT-TYPE
    SYNTAX Counter32
    MAX-ACCESS  read-only
    STATUS      current
    DESCRIPTION
	"Number of input packets Dropped through ICMP Attack"
     ::= { prStatsEntry 815 }

prOutIcmpAttackPktsCnt OBJECT-TYPE
    SYNTAX Counter32
    MAX-ACCESS  read-only
    STATUS      current
    DESCRIPTION
	"Number of output packets Dropped through ICMP Attack"
     ::= { prStatsEntry 816 }

prInOtherIpAttackPktsCnt OBJECT-TYPE
    SYNTAX Counter32
    MAX-ACCESS  read-only
    STATUS      current
    DESCRIPTION
	"Number of input packets Dropped through Other IP Protocol Attack"
     ::= { prStatsEntry 817 }

prOutOtherIpAttackPktsCnt OBJECT-TYPE
    SYNTAX Counter32
    MAX-ACCESS  read-only
    STATUS      current
    DESCRIPTION
	"Number of output packets Dropped through Other IP Protocol Attack"
     ::= { prStatsEntry 818 }

prInFragmentAttackPktsCnt OBJECT-TYPE
    SYNTAX Counter32
    MAX-ACCESS  read-only
    STATUS      current
    DESCRIPTION
	"Number of input packets Dropped through fragment Attack protection"
     ::= { prStatsEntry 819 }

prOutFragmentAttackPktsCnt OBJECT-TYPE
    SYNTAX Counter32
    MAX-ACCESS  read-only
    STATUS      current
    DESCRIPTION
	"Number of output packets Dropped through fragment Attack protection"
     ::= { prStatsEntry 820 }

prInBadIpPktsCnt OBJECT-TYPE
    SYNTAX Counter32
    MAX-ACCESS  read-only
    STATUS      current
    DESCRIPTION
	"Number of input packets Dropped through bad IP packet protection"
     ::= { prStatsEntry 821 }

prOutBadIpPktsCnt OBJECT-TYPE
    SYNTAX Counter32
    MAX-ACCESS  read-only
    STATUS      current
    DESCRIPTION
	"Number of output packets Dropped through bad IP packet protection"
     ::= { prStatsEntry 822 }

prInBadTcpPktsCnt OBJECT-TYPE
    SYNTAX Counter32
    MAX-ACCESS  read-only
    STATUS      current
    DESCRIPTION
	"Number of input packets Dropped through bad TCP packet protection"
     ::= { prStatsEntry 823 }

prOutBadTcpPktsCnt OBJECT-TYPE
    SYNTAX Counter32
    MAX-ACCESS  read-only
    STATUS      current
    DESCRIPTION
	"Number of output packets Dropped through bad TCP packet protection"
     ::= { prStatsEntry 824 }

prInBadUdpPktsCnt OBJECT-TYPE
    SYNTAX Counter32
    MAX-ACCESS  read-only
    STATUS      current
    DESCRIPTION
	"Number of input packets Dropped through bad UDP packet protection"
     ::= { prStatsEntry 825 }

prOutBadUdpPktsCnt OBJECT-TYPE
    SYNTAX Counter32
    MAX-ACCESS  read-only
    STATUS      current
    DESCRIPTION
	"Number of output packets Dropped through bad UDP packet protection"
     ::= { prStatsEntry 826 }

prInBadIcmpPktsCnt OBJECT-TYPE
    SYNTAX Counter32
    MAX-ACCESS  read-only
    STATUS      current
    DESCRIPTION
	"Number of input packets Dropped through bad ICMP packet protection"
     ::= { prStatsEntry 827 }

prOutBadIcmpPktsCnt OBJECT-TYPE
    SYNTAX Counter32
    MAX-ACCESS  read-only
    STATUS      current
    DESCRIPTION
	"Number of output packets Dropped through bad ICMP packet protection"
     ::= { prStatsEntry 828 }

prInBadOtherIpPktsCnt OBJECT-TYPE
    SYNTAX Counter32
    MAX-ACCESS  read-only
    STATUS      current
    DESCRIPTION
	"Number of input packets Dropped through bad Other IP Protocol packet protection"
     ::= { prStatsEntry 829 }

prOutBadOtherIpPktsCnt OBJECT-TYPE
    SYNTAX Counter32
    MAX-ACCESS  read-only
    STATUS      current
    DESCRIPTION
	"Number of output packets Dropped through bad Other IP Protocol packet protection"
     ::= { prStatsEntry 830 }

 prInTotalBpsAvg OBJECT-TYPE
    SYNTAX      Gauge32
    MAX-ACCESS  read-only
    STATUS      current
    DESCRIPTION
	"Average number of input bits per second"
    ::= { prStatsEntry 901 }

prOutTotalBpsAvg OBJECT-TYPE
    SYNTAX      Gauge32
    MAX-ACCESS  read-only
    STATUS      current
    DESCRIPTION
	"Average number of output bits per second"
    ::= { prStatsEntry 902 }

prInTotalPpsAvg OBJECT-TYPE
    SYNTAX      Gauge32
    MAX-ACCESS  read-only
    STATUS      current
    DESCRIPTION
	"Average packets/sec traffic rate inbound since last restart or reset"
    ::= { prStatsEntry 903 }

prOutTotalPpsAvg OBJECT-TYPE
    SYNTAX      Gauge32
    MAX-ACCESS  read-only
    STATUS      current
    DESCRIPTION
	"Average packets/sec traffic rate outbound since last restart or reset"
    ::= { prStatsEntry 904 }

prInSmallPpsAvg OBJECT-TYPE
    SYNTAX      Gauge32
    MAX-ACCESS  read-only
    STATUS      current
    DESCRIPTION
	"Averaged inbound packets (256 bytes or less) per second processed. Dropped data is not included"
    ::= { prStatsEntry 905 }

prOutSmallPpsAvg OBJECT-TYPE
    SYNTAX      Gauge32
    MAX-ACCESS  read-only
    STATUS      current
    DESCRIPTION
	"Averaged outbound packets (256 bytes or less) per second processed. Dropped data is not included"
    ::= { prStatsEntry 906 }

prInMediumPpsAvg OBJECT-TYPE
    SYNTAX      Gauge32
    MAX-ACCESS  read-only
    STATUS      current
    DESCRIPTION
	"Averaged inbound packets (1024 bytes or less, but greater than 256 bytes) per second. Dropped data is not included"
    ::= { prStatsEntry 907 }

prOutMediumPpsAvg OBJECT-TYPE
    SYNTAX      Gauge32
    MAX-ACCESS  read-only
    STATUS      current
    DESCRIPTION
	"Averaged outbound packets (1024 bytes or less, but greater than 256 bytes) per second. Dropped data is not included"
    ::= { prStatsEntry 908 }

prInLargePpsAvg OBJECT-TYPE
    SYNTAX      Gauge32
    MAX-ACCESS  read-only
    STATUS      current
    DESCRIPTION
	"Averaged inbound packets (greater than 1024 bytes) per second. Dropped data is not included"
    ::= { prStatsEntry 909 }

prOutLargePpsAvg OBJECT-TYPE
    SYNTAX      Gauge32
    MAX-ACCESS  read-only
    STATUS      current
    DESCRIPTION
	"Averaged outbound packets (greater than 1024 bytes) per second. Dropped data is not included"
    ::= { prStatsEntry 910 }

prInDroppedBpsAvg OBJECT-TYPE
    SYNTAX      Gauge32
    MAX-ACCESS  read-only
    STATUS      current
    DESCRIPTION
	"Average number of input bits Dropped per second"
    ::= { prStatsEntry 911 }

prOutDroppedBpsAvg OBJECT-TYPE
    SYNTAX      Gauge32
    MAX-ACCESS  read-only
    STATUS      current
    DESCRIPTION
	"Average number of output bits Dropped per second"
    ::= { prStatsEntry 912 }

prInDroppedPpsAvg OBJECT-TYPE
    SYNTAX      Gauge32
    MAX-ACCESS  read-only
    STATUS      current
    DESCRIPTION
	"Average number of input packets Dropped per second"
    ::= { prStatsEntry 913 }

prOutDroppedPpsAvg OBJECT-TYPE
    SYNTAX      Gauge32
    MAX-ACCESS  read-only
    STATUS      current
    DESCRIPTION
	"Averaged number of output packets Dropped per second"
    ::= { prStatsEntry 914 }

prInCharmDroppedBpsAvg OBJECT-TYPE
    SYNTAX      Gauge32
    MAX-ACCESS  read-only
    STATUS      current
    DESCRIPTION
	"Averaged inbound bits per second dropped by heuristic detection"
    ::= { prStatsEntry 915 }

prOutCharmDroppedBpsAvg OBJECT-TYPE
    SYNTAX      Gauge32
    MAX-ACCESS  read-only
    STATUS      current
    DESCRIPTION
	"Averaged outbound bits per second dropped by heuristic detection"
    ::= { prStatsEntry 916 }

prInFilteredBwthPercentAvg OBJECT-TYPE
    SYNTAX      Gauge32
    MAX-ACCESS  read-only
    STATUS      current
    DESCRIPTION
	"Averaged inbound dropped bandwidth divided by the actual bandwidth"
    ::= { prStatsEntry 917 }

prOutFilteredBwthPercentAvg OBJECT-TYPE
    SYNTAX      Gauge32
    MAX-ACCESS  read-only
    STATUS      current
    DESCRIPTION
	"Averaged outbound dropped bandwidth divided by the actual bandwidth"
    ::= { prStatsEntry 918 }

prInSynbacklogtallyAvg OBJECT-TYPE
    SYNTAX      Gauge32
    MAX-ACCESS  read-only
    STATUS      current
    DESCRIPTION
	"Averaged number of partially open TCP connections inbound"
    ::= { prStatsEntry 919 }

prOutSynbacklogtallyAvg OBJECT-TYPE
    SYNTAX      Gauge32
    MAX-ACCESS  read-only
    STATUS      current
    DESCRIPTION
	"Averaged number of partially open TCP connections outbound"
    ::= { prStatsEntry 920 }

prInConnectionAvg OBJECT-TYPE
    SYNTAX      Gauge32
    MAX-ACCESS  read-only
    STATUS      current
    DESCRIPTION
	"Averaged number of inbound TCP connections"
    ::= { prStatsEntry 921 }

prOutConnectionAvg OBJECT-TYPE
    SYNTAX      Gauge32
    MAX-ACCESS  read-only
    STATUS      current
    DESCRIPTION
	"Averaged number of outbound TCP connections"
    ::= { prStatsEntry 922 }

prInConnreqAvg OBJECT-TYPE
    SYNTAX      Gauge32
    MAX-ACCESS  read-only
    STATUS      current
    DESCRIPTION
	"Averaged number of inbound TCP connection requests"
    ::= { prStatsEntry 923 }

prOutConnreqAvg OBJECT-TYPE
    SYNTAX      Gauge32
    MAX-ACCESS  read-only
    STATUS      current
    DESCRIPTION
	"Averaged number of outbound TCP connection requests"
    ::= { prStatsEntry 924 }

prInActiveHttpGetsAvg OBJECT-TYPE
    SYNTAX      Gauge32
    MAX-ACCESS  read-only
    STATUS      current
    DESCRIPTION
	"Averaged number of inbound HTTP page requests being processed"
    ::= { prStatsEntry 925 }

prOutActiveHttpGetsAvg OBJECT-TYPE
    SYNTAX      Gauge32
    MAX-ACCESS  read-only
    STATUS      current
    DESCRIPTION
	"Averaged number of outbound HTTP page requests being processed"
    ::= { prStatsEntry 926 }

prInProtectBwthPktsAvg OBJECT-TYPE
    SYNTAX      Gauge32
    MAX-ACCESS  read-only
    STATUS      current
    DESCRIPTION
	"Averaged inbound protected bandwifth"
    ::= { prStatsEntry 927 }

prOutProtectBwthPktsAvg OBJECT-TYPE
    SYNTAX      Gauge32
    MAX-ACCESS  read-only
    STATUS      current
    DESCRIPTION
	"Averaged outbound protected bandwifth"
    ::= { prStatsEntry 928 }

prInFloodPktsAvg OBJECT-TYPE
    SYNTAX      Gauge32
    MAX-ACCESS  read-only
    STATUS      current
    DESCRIPTION
	"Averaged number of inbound packets causing flooding"
    ::= { prStatsEntry 929 }

prOutFloodPktsAvg OBJECT-TYPE
    SYNTAX      Gauge32
    MAX-ACCESS  read-only
    STATUS      current
    DESCRIPTION
	"Averaged number of outbound packets causing flooding"
    ::= { prStatsEntry 930 }

prInBlockedProtocolPktsAvg OBJECT-TYPE
    SYNTAX      Gauge32
    MAX-ACCESS  read-only
    STATUS      current
    DESCRIPTION
	"Averaged number of inbound IP packets dropped by filter "
    ::= { prStatsEntry 931 }

prOutBlockedProtocolPktsAvg OBJECT-TYPE
    SYNTAX      Gauge32
    MAX-ACCESS  read-only
    STATUS      current
    DESCRIPTION
	"Averaged number of outbound IP packets dropped by filter"
    ::= { prStatsEntry 932 }

prInBlockedStatePktsAvg OBJECT-TYPE
    SYNTAX      Gauge32
    MAX-ACCESS  read-only
    STATUS      current
    DESCRIPTION
	"Averaged number of inbound IP packets dropped due to incorrect state"
    ::= { prStatsEntry 933 }

prOutBlockedStatePktsAvg OBJECT-TYPE
    SYNTAX      Gauge32
    MAX-ACCESS  read-only
    STATUS      current
    DESCRIPTION
	"Averaged number of outbound IP packets dropped due to incorrect state"
    ::= { prStatsEntry 934 }

prInIpAttackPktsAvg OBJECT-TYPE
    SYNTAX      Gauge32
    MAX-ACCESS  read-only
    STATUS      current
    DESCRIPTION
	"Averaged number of inbound IP packets in an IP Attack"
    ::= { prStatsEntry 935 }

prOutIpAttackPktsAvg OBJECT-TYPE
    SYNTAX      Gauge32
    MAX-ACCESS  read-only
    STATUS      current
    DESCRIPTION
	"Averaged number of outbound IP packets in an IP Attack"
    ::= { prStatsEntry 936 }

prInTcpAttackPktsAvg OBJECT-TYPE
    SYNTAX      Gauge32
    MAX-ACCESS  read-only
    STATUS      current
    DESCRIPTION
	"Averaged number of inbound IP packets in a TCP Attack"
    ::= { prStatsEntry 937 }

prOutTcpAttackPktsAvg OBJECT-TYPE
    SYNTAX      Gauge32
    MAX-ACCESS  read-only
    STATUS      current
    DESCRIPTION
	"Averaged number of outbound IP packets in a TCP Attack"
    ::= { prStatsEntry 938 }

prInUdpAttackPktsAvg OBJECT-TYPE
    SYNTAX      Gauge32
    MAX-ACCESS  read-only
    STATUS      current
    DESCRIPTION
	"Averaged number of inbound IP packets in a UDP Attack"
    ::= { prStatsEntry 939 }

prOutUdpAttackPktsAvg OBJECT-TYPE
    SYNTAX      Gauge32
    MAX-ACCESS  read-only
    STATUS      current
    DESCRIPTION
	"Averaged number of outbound IP packets in a UDP Attack"
    ::= { prStatsEntry 940 }

prInIcmpAttackPktsAvg OBJECT-TYPE
    SYNTAX      Gauge32
    MAX-ACCESS  read-only
    STATUS      current
    DESCRIPTION
	"Averaged number of inbound IP packets in a ICMP Attack"
    ::= { prStatsEntry 941 }

prOutIcmpAttackPktsAvg OBJECT-TYPE
    SYNTAX      Gauge32
    MAX-ACCESS  read-only
    STATUS      current
    DESCRIPTION
	"Averaged number of outbound IP packets in a ICMP Attack"
    ::= { prStatsEntry 942 }

prInOtherIpAttackPktsAvg OBJECT-TYPE
    SYNTAX      Gauge32
    MAX-ACCESS  read-only
    STATUS      current
    DESCRIPTION
	"Averaged number of inbound IP packets in an IP Attack using other protocols"
    ::= { prStatsEntry 943 }

prOutOtherIpAttackPktsAvg OBJECT-TYPE
    SYNTAX      Gauge32
    MAX-ACCESS  read-only
    STATUS      current
    DESCRIPTION
	"Averaged number of outbound IP packets in an IP Attack using other protocols"
    ::= { prStatsEntry 944 }

prInFragmentAttackPktsAvg OBJECT-TYPE
    SYNTAX      Gauge32
    MAX-ACCESS  read-only
    STATUS      current
    DESCRIPTION
	"Averaged number of inbound IP packets in an Fragmentation Attack"
    ::= { prStatsEntry 945 }

prOutFragmentAttackPktsAvg OBJECT-TYPE
    SYNTAX      Gauge32
    MAX-ACCESS  read-only
    STATUS      current
    DESCRIPTION
	"Averaged number of outbound IP packets in an Fragmentation Attack"
    ::= { prStatsEntry 946 }

prInBadipPktsAvg OBJECT-TYPE
    SYNTAX      Gauge32
    MAX-ACCESS  read-only
    STATUS      current
    DESCRIPTION
	"Averaged number of inbound IP packets with malformed IP Headers"
    ::= { prStatsEntry 947 }

prOutBadipPktsAvg OBJECT-TYPE
    SYNTAX      Gauge32
    MAX-ACCESS  read-only
    STATUS      current
    DESCRIPTION
	"Averaged number of outbound IP packets with malformed IP Headers"
    ::= { prStatsEntry 948 }

prInBadTcpPktsAvg OBJECT-TYPE
    SYNTAX      Gauge32
    MAX-ACCESS  read-only
    STATUS      current
    DESCRIPTION
	"Averaged number of inbound IP packets with bad TCP protocol/state"
    ::= { prStatsEntry 949 }

prOutBadTcpPktsAvg OBJECT-TYPE
    SYNTAX      Gauge32
    MAX-ACCESS  read-only
    STATUS      current
    DESCRIPTION
	"Averaged number of outbound IP packets with bad TCP protocol/state"
    ::= { prStatsEntry 950 }

prInBadUdpPktsAvg OBJECT-TYPE
    SYNTAX      Gauge32
    MAX-ACCESS  read-only
    STATUS      current
    DESCRIPTION
	"Averaged number of inbound UDP packets with malformed header or missing data"
    ::= { prStatsEntry 951 }

prOutBadUdpPktsAvg OBJECT-TYPE
    SYNTAX      Gauge32
    MAX-ACCESS  read-only
    STATUS      current
    DESCRIPTION
	"Averaged number of outbound UDP packets with malformed header or missing data"
    ::= { prStatsEntry 952 }

prInBadIcmpPktsAvg OBJECT-TYPE
    SYNTAX      Gauge32
    MAX-ACCESS  read-only
    STATUS      current
    DESCRIPTION
	"Averaged number of inbound ICMP packets with malformed header"
    ::= { prStatsEntry 953 }

prOutBadIcmpPktsAvg OBJECT-TYPE
    SYNTAX      Gauge32
    MAX-ACCESS  read-only
    STATUS      current
    DESCRIPTION
	"Averaged number of outbound ICMP packets with malformed header"
    ::= { prStatsEntry 954 }

prInBadOtherIpPktsAvg OBJECT-TYPE
    SYNTAX      Gauge32
    MAX-ACCESS  read-only
    STATUS      current
    DESCRIPTION
	"Averaged number of inbound IP packets of other protocol with malformed header"
    ::= { prStatsEntry 955 }

prOutBadOtherIpPktsAvg OBJECT-TYPE
    SYNTAX      Gauge32
    MAX-ACCESS  read-only
    STATUS      current
    DESCRIPTION
	"Averaged number of outbound IP packets of other protocol with malformed header"
    ::= { prStatsEntry 956 }

prInOverloadedAvg OBJECT-TYPE
    SYNTAX      Gauge32
    MAX-ACCESS  read-only
    STATUS      current
    DESCRIPTION
	"Averaged number of inbound packets overloading the protected IP"
    ::= { prStatsEntry 957 }

prOutOverloadedAvg OBJECT-TYPE
    SYNTAX      Gauge32
    MAX-ACCESS  read-only
    STATUS      current
    DESCRIPTION
	"Averaged number of outbound packets overloading the protected IP"
    ::= { prStatsEntry 958 }

prInLatencyAvg OBJECT-TYPE
    SYNTAX      Gauge32
    MAX-ACCESS  read-only
    STATUS      current
    DESCRIPTION
	"Averaged inbound Latency"
    ::= { prStatsEntry 959 }

prOutLatencyAvg OBJECT-TYPE
    SYNTAX      Gauge32
    MAX-ACCESS  read-only
    STATUS      current
    DESCRIPTION
	"Averaged outbound Latency"
    ::= { prStatsEntry 960 }

prInSmallPpsMax OBJECT-TYPE
    SYNTAX      Gauge32
    MAX-ACCESS  read-only
    STATUS      current
    DESCRIPTION
	"Peak inbound packets (256 bytes or less) per second processed. Dropped data is not included"
    ::= { prStatsEntry 1001 }

prOutSmallPpsMax OBJECT-TYPE
    SYNTAX      Gauge32
    MAX-ACCESS  read-only
    STATUS      current
    DESCRIPTION
	"Peak outbound packets (256 bytes or less) per second processed. Dropped data is not included"
    ::= { prStatsEntry 1002 }

prInMediumPpsMax OBJECT-TYPE
    SYNTAX      Gauge32
    MAX-ACCESS  read-only
    STATUS      current
    DESCRIPTION
	"Peak inbound packets (1024 bytes or less, but greater than 256 bytes) per second. Dropped data is not included"
    ::= { prStatsEntry 1003 }

prOutMediumPpsMax OBJECT-TYPE
    SYNTAX      Gauge32
    MAX-ACCESS  read-only
    STATUS      current
    DESCRIPTION
	"Peak outbound packets (1024 bytes or less, but greater than 256 bytes) per second. Dropped data is not included"
    ::= { prStatsEntry 1004 }

prInLargePpsMax OBJECT-TYPE
    SYNTAX      Gauge32
    MAX-ACCESS  read-only
    STATUS      current
    DESCRIPTION
	"Peak inbound packets (greater than 1024 bytes) per second. Dropped data is not included"
    ::= { prStatsEntry 1005 }

prOutLargePpsMax OBJECT-TYPE
    SYNTAX      Gauge32
    MAX-ACCESS  read-only
    STATUS      current
    DESCRIPTION
	"Peak outbound packets (greater than 1024 bytes) per second. Dropped data is not included"
    ::= { prStatsEntry 1006 }

prInFilteredBwthPercentMax OBJECT-TYPE
    SYNTAX      Gauge32
    MAX-ACCESS  read-only
    STATUS      current
    DESCRIPTION
	"Peak inbound dropped bandwidth divided by the actual bandwidth"
    ::= { prStatsEntry 1007 }

prOutFilteredBwthPercentMax OBJECT-TYPE
    SYNTAX      Gauge32
    MAX-ACCESS  read-only
    STATUS      current
    DESCRIPTION
	"Peak outbound dropped bandwidth divided by the actual bandwidth"
    ::= { prStatsEntry 1008 }

prInSynbacklogtallyMax OBJECT-TYPE
    SYNTAX      Gauge32
    MAX-ACCESS  read-only
    STATUS      current
    DESCRIPTION
	"Peak number of partially open TCP connections inbound"
    ::= { prStatsEntry 1009 }

prOutSynbacklogtallyMax OBJECT-TYPE
    SYNTAX      Gauge32
    MAX-ACCESS  read-only
    STATUS      current
    DESCRIPTION
	"Peak number of partially open TCP connections outbound"
    ::= { prStatsEntry 1010 }

prInConnectionMax OBJECT-TYPE
    SYNTAX      Gauge32
    MAX-ACCESS  read-only
    STATUS      current
    DESCRIPTION
	"Peak number of inbound TCP connections"
    ::= { prStatsEntry 1011 }

prOutConnectionMax OBJECT-TYPE
    SYNTAX      Gauge32
    MAX-ACCESS  read-only
    STATUS      current
    DESCRIPTION
	"Peak number of outbound TCP connections"
    ::= { prStatsEntry 1012 }

prInConnreqMax OBJECT-TYPE
    SYNTAX      Gauge32
    MAX-ACCESS  read-only
    STATUS      current
    DESCRIPTION
	"Peak number of inbound TCP connection requests"
    ::= { prStatsEntry 1013 }

prOutConnreqMax OBJECT-TYPE
    SYNTAX	Gauge32
    MAX-ACCESS  read-only
    STATUS      current
    DESCRIPTION
	"Peak number of outbound TCP connection requests"
    ::= { prStatsEntry 1014 }

prInActiveHttpGetsMax OBJECT-TYPE
    SYNTAX      Gauge32
    MAX-ACCESS  read-only
    STATUS      current
    DESCRIPTION
	"Peak number of inbound HTTP page requests being processed"
    ::= { prStatsEntry 1015 }

prOutActiveHttpGetsMax OBJECT-TYPE
    SYNTAX      Gauge32
    MAX-ACCESS  read-only
    STATUS      current
    DESCRIPTION
	"Peak number of outbound HTTP page requests being processed"
    ::= { prStatsEntry 1016 }

prInProtectBwthPktsMax OBJECT-TYPE
    SYNTAX      Gauge32
    MAX-ACCESS  read-only
    STATUS      current
    DESCRIPTION
	"Peak inbound protected bandwifth"
    ::= { prStatsEntry 1017 }

prOutProtectBwthPktsMax OBJECT-TYPE
    SYNTAX      Gauge32
    MAX-ACCESS  read-only
    STATUS      current
    DESCRIPTION
	"Peak outbound protected bandwifth"
    ::= { prStatsEntry 1018 }

prInFloodPktsMax OBJECT-TYPE
    SYNTAX      Gauge32
    MAX-ACCESS  read-only
    STATUS      current
    DESCRIPTION
	"Peak number of inbound packets causing flooding"
    ::= { prStatsEntry 1019 }

prOutFloodPktsMax OBJECT-TYPE
    SYNTAX      Gauge32
    MAX-ACCESS  read-only
    STATUS      current
    DESCRIPTION
	"Peak number of outbound packets causing flooding"
    ::= { prStatsEntry 1020 }

prInBlockedProtocolPktsMax OBJECT-TYPE
    SYNTAX      Gauge32
    MAX-ACCESS  read-only
    STATUS      current
    DESCRIPTION
	"Peak number of inbound IP packets dropped by filter "
    ::= { prStatsEntry 1021 }

prOutBlockedProtocolPktsMax OBJECT-TYPE
    SYNTAX      Gauge32
    MAX-ACCESS  read-only
    STATUS      current
    DESCRIPTION
	"Peak number of outbound IP packets dropped by filter"
    ::= { prStatsEntry 1022 }

prInBlockedStatePktsMax OBJECT-TYPE
    SYNTAX      Gauge32
    MAX-ACCESS  read-only
    STATUS      current
    DESCRIPTION
	"Peak number of inbound IP packets dropped due to incorrect state"
    ::= { prStatsEntry 1023 }

prOutBlockedStatePktsMax OBJECT-TYPE
    SYNTAX      Gauge32
    MAX-ACCESS  read-only
    STATUS      current
    DESCRIPTION
	"Peak number of outbound IP packets dropped due to incorrect state"
    ::= { prStatsEntry 1024 }

prInIpAttackPktsMax OBJECT-TYPE
    SYNTAX      Gauge32
    MAX-ACCESS  read-only
    STATUS      current
    DESCRIPTION
	"Peak number of inbound IP packets in an IP Attack"
    ::= { prStatsEntry 1025 }

prOutIpAttackPktsMax OBJECT-TYPE
    SYNTAX      Gauge32
    MAX-ACCESS  read-only
    STATUS      current
    DESCRIPTION
	"Peak number of outbound IP packets in an IP Attack"
    ::= { prStatsEntry 1026 }

prInTcpAttackPktsMax OBJECT-TYPE
    SYNTAX      Gauge32
    MAX-ACCESS  read-only
    STATUS      current
    DESCRIPTION
	"Peak number of inbound IP packets in a TCP Attack"
    ::= { prStatsEntry 1027 }

prOutTcpAttackPktsMax OBJECT-TYPE
    SYNTAX      Gauge32
    MAX-ACCESS  read-only
    STATUS      current
    DESCRIPTION
	"Peak number of outbound IP packets in a TCP Attack"
    ::= { prStatsEntry 1028 }

prInUdpAttackPktsMax OBJECT-TYPE
    SYNTAX      Gauge32
    MAX-ACCESS  read-only
    STATUS      current
    DESCRIPTION
	"Peak number of inbound IP packets in a UDP Attack"
    ::= { prStatsEntry 1029 }

prOutUdpAttackPktsMax OBJECT-TYPE
    SYNTAX      Gauge32
    MAX-ACCESS  read-only
    STATUS      current
    DESCRIPTION
	"Peak number of outbound IP packets in a UDP Attack"
    ::= { prStatsEntry 1030 }

prInIcmpAttackPktsMax OBJECT-TYPE
    SYNTAX      Gauge32
    MAX-ACCESS  read-only
    STATUS      current
    DESCRIPTION
	"Peak number of inbound IP packets in a ICMP Attack"
    ::= { prStatsEntry 1031 }

prOutIcmpAttackPktsMax OBJECT-TYPE
    SYNTAX      Gauge32
    MAX-ACCESS  read-only
    STATUS      current
    DESCRIPTION
	"Peak number of outbound IP packets in a ICMP Attack"
    ::= { prStatsEntry 1032 }

prInOtherIpAttackPktsMax OBJECT-TYPE
    SYNTAX      Gauge32
    MAX-ACCESS  read-only
    STATUS      current
    DESCRIPTION
	"Peak number of inbound IP packets in an IP Attack using other protocols"
    ::= { prStatsEntry 1033 }

prOutOtherIpAttackPktsMax OBJECT-TYPE
    SYNTAX      Gauge32
    MAX-ACCESS  read-only
    STATUS      current
    DESCRIPTION
	"Peak number of outbound IP packets in an IP Attack using other protocols"
    ::= { prStatsEntry 1034 }

prInFragmentAttackPktsMax OBJECT-TYPE
    SYNTAX      Gauge32
    MAX-ACCESS  read-only
    STATUS      current
    DESCRIPTION
	"Peak number of inbound IP packets in an Fragmentation Attack"
    ::= { prStatsEntry 1035 }

prOutFragmentAttackPktsMax OBJECT-TYPE
    SYNTAX      Gauge32
    MAX-ACCESS  read-only
    STATUS      current
    DESCRIPTION
	"Peak number of outbound IP packets in an Fragmentation Attack"
    ::= { prStatsEntry 1036 }

prInBadipPktsMax OBJECT-TYPE
    SYNTAX      Gauge32
    MAX-ACCESS  read-only
    STATUS      current
    DESCRIPTION
	"Peak number of inbound IP packets with malformed IP Headers"
    ::= { prStatsEntry 1037 }

prOutBadipPktsMax OBJECT-TYPE
    SYNTAX      Gauge32
    MAX-ACCESS  read-only
    STATUS      current
    DESCRIPTION
	"Peak number of outbound IP packets with malformed IP Headers"
    ::= { prStatsEntry 1038 }

prInBadTcpPktsMax OBJECT-TYPE
    SYNTAX      Gauge32
    MAX-ACCESS  read-only
    STATUS      current
    DESCRIPTION
	"Peak number of inbound IP packets with bad TCP protocol/state"
    ::= { prStatsEntry 1039 }

prOutBadTcpPktsMax OBJECT-TYPE
    SYNTAX      Gauge32
    MAX-ACCESS  read-only
    STATUS      current
    DESCRIPTION
	"Peak number of outbound IP packets with bad TCP protocol/state"
    ::= { prStatsEntry 1040 }

prInBadUdpPktsMax OBJECT-TYPE
    SYNTAX      Gauge32
    MAX-ACCESS  read-only
    STATUS      current
    DESCRIPTION
	"Peak number of inbound UDP packets with malformed header or missing data"
    ::= { prStatsEntry 1041 }

prOutBadUdpPktsMax OBJECT-TYPE
    SYNTAX      Gauge32
    MAX-ACCESS  read-only
    STATUS      current
    DESCRIPTION
	"Peak number of outbound UDP packets with malformed header or missing data"
    ::= { prStatsEntry 1042 }

prInBadIcmpPktsMax OBJECT-TYPE
    SYNTAX      Gauge32
    MAX-ACCESS  read-only
    STATUS      current
    DESCRIPTION
	"Peak number of inbound ICMP packets with malformed header"
    ::= { prStatsEntry 1043 }

prOutBadIcmpPktsMax OBJECT-TYPE
    SYNTAX      Gauge32
    MAX-ACCESS  read-only
    STATUS      current
    DESCRIPTION
	"Peak number of outbound ICMP packets with malformed header"
    ::= { prStatsEntry 1044 }

prInBadOtherIpPktsMax OBJECT-TYPE
    SYNTAX      Gauge32
    MAX-ACCESS  read-only
    STATUS      current
    DESCRIPTION
	"Peak number of inbound IP packets of other protocol with malformed header"
    ::= { prStatsEntry 1045 }

prOutBadOtherIpPktsMax OBJECT-TYPE
    SYNTAX      Gauge32
    MAX-ACCESS  read-only
    STATUS      current
    DESCRIPTION
	"Peak number of outbound IP packets of other protocol with malformed header"
    ::= { prStatsEntry 1046 }

prInOverloadedMax OBJECT-TYPE
    SYNTAX      Gauge32
    MAX-ACCESS  read-only
    STATUS      current
    DESCRIPTION
	"Peak number of inbound packets overloading the protected IP"
    ::= { prStatsEntry 1047 }

prOutOverloadedMax OBJECT-TYPE
    SYNTAX      Gauge32
    MAX-ACCESS  read-only
    STATUS      current
    DESCRIPTION
	"Peak number of outbound packets overloading the protected IP"
    ::= { prStatsEntry 1048 }

prInLatencyMax OBJECT-TYPE
    SYNTAX      Gauge32
    MAX-ACCESS  read-only
    STATUS      current
    DESCRIPTION
	"Peak inbound Latency"
    ::= { prStatsEntry 1049 }

prOutLatencyMax OBJECT-TYPE
    SYNTAX      Gauge32
    MAX-ACCESS  read-only
    STATUS      current
    DESCRIPTION
	"Peak outbound Latency"
    ::= { prStatsEntry 1050 }

-- end of protected IP status section

-- ### protected IP Incident section

prIncidentTable OBJECT-TYPE
    SYNTAX SEQUENCE OF PrIncidentEntry
    MAX-ACCESS  not-accessible
    STATUS      current
    DESCRIPTION
        "Table of portal incident entries"
    ::= { jddsProtected 5 }

prIncidentEntry OBJECT-TYPE
    SYNTAX   PrIncidentEntry
    MAX-ACCESS  not-accessible
    STATUS      current
    DESCRIPTION
        "A row consisting of an incident record"
    INDEX { prIncidentYear,
            prIncidentMonth,
            prIncidentDay,
            prIncidentNumber,
            prIncidentInetAddressType,
            prIncidentInetAddress}
    ::= {prIncidentTable 1 }

PrIncidentEntry ::= SEQUENCE {
    prIncidentYear
       LocalIndex,
    prIncidentMonth
       LocalIndex,
    prIncidentDay
       LocalIndex,
    prIncidentNumber
       LocalIndex,
    prIncidentInetAddressType
	InetAddressType,
    prIncidentInetAddress
	InetAddress,
    prIncidentStart
       DateAndTime,
    prIncidentAddress
       DisplayString,
    prIncidentType
       DisplayString,
    prIncidentDirection
       Direction,
    prIncidentPeakRate
       Gauge32,
    prIncidentDropped
       Gauge32
}

prIncidentYear OBJECT-TYPE
    SYNTAX      LocalIndex
    MAX-ACCESS  not-accessible
    STATUS      current
    DESCRIPTION
        "Incident record year"
    ::= { prIncidentEntry 1 }

prIncidentMonth OBJECT-TYPE
    SYNTAX      LocalIndex
    MAX-ACCESS  not-accessible
    STATUS      current
    DESCRIPTION
        "Incident record month"
    ::= { prIncidentEntry 2 }

prIncidentDay OBJECT-TYPE
    SYNTAX      LocalIndex
    MAX-ACCESS  not-accessible
    STATUS      current
    DESCRIPTION
        "Incident record day of month"
    ::= { prIncidentEntry 3 }

prIncidentNumber OBJECT-TYPE
    SYNTAX      LocalIndex
    MAX-ACCESS  not-accessible
    STATUS      current
    DESCRIPTION
        "Unique (for the day) incident record number"
    ::= { prIncidentEntry 4 }

prIncidentInetAddressType OBJECT-TYPE
    SYNTAX      InetAddressType
    MAX-ACCESS  not-accessible
    STATUS      current
    DESCRIPTION
	"Type of IP address a specific protected IP"
     ::= { prIncidentEntry 5 }

prIncidentInetAddress OBJECT-TYPE
    SYNTAX      InetAddress (SIZE (0..47))
    MAX-ACCESS  not-accessible
    STATUS      current
    DESCRIPTION
	"IP address of a specific protected IP"
     ::= { prIncidentEntry 6 }

prIncidentStart OBJECT-TYPE
    SYNTAX      DateAndTime
    MAX-ACCESS  read-only
    STATUS      current
    DESCRIPTION
        "Incident start time"
    ::= { prIncidentEntry 7 }

prIncidentAddress OBJECT-TYPE
    SYNTAX      DisplayString
    MAX-ACCESS  read-only
    STATUS      current
    DESCRIPTION
        "Incident protected IP IP or MAC address"
    ::= { prIncidentEntry 8 }

prIncidentType OBJECT-TYPE
    SYNTAX      DisplayString
    MAX-ACCESS  read-only
    STATUS      current
    DESCRIPTION
        "Incident defense type (and subtype)"
    ::= { prIncidentEntry 9 }

prIncidentDirection OBJECT-TYPE
    SYNTAX      Direction
    MAX-ACCESS  read-only
    STATUS      current
    DESCRIPTION
        "Incident direction"
    ::= { prIncidentEntry 10 }

prIncidentPeakRate OBJECT-TYPE
    SYNTAX      Gauge32
    MAX-ACCESS  read-only
    STATUS      current
    DESCRIPTION
        "Peak packets/s during this incident"
    ::= { prIncidentEntry 11 }

prIncidentDropped OBJECT-TYPE
    SYNTAX      Gauge32
    MAX-ACCESS  read-only
    STATUS      current
    DESCRIPTION
        "No of packets Dropped as part of this incident"
    ::= { prIncidentEntry 12 }

-- ### end of protected IP incident section ###


-- ### Gateway statistics ###

gwInternetStatsTable OBJECT-TYPE
    SYNTAX SEQUENCE OF GwInternetStatsEntry
    MAX-ACCESS  not-accessible
    STATUS      current
    DESCRIPTION
        "Table of internet-side gateway statistics"
    ::= { jddsGatewayInternet 3 }

gwInternetStatsEntry OBJECT-TYPE
    SYNTAX      GwInternetStatsEntry
    MAX-ACCESS  not-accessible
    STATUS      current
    DESCRIPTION
        "A row associated with a specific gateway"
    INDEX { gwInternetStatsIndex }
    ::= { gwInternetStatsTable 1 }

GwInternetStatsEntry ::= SEQUENCE {
    gwInternetStatsIndex
	LocalIndex,
    gwInternetMacAddress
	DisplayString,
    gwInternetIpAddress
	DisplayString,
    gwInternetInTotalBytesCnt
	Counter64,
    gwInternetOutTotalBytesCnt
	Counter64,
    gwInternetInDroppedBytesCnt
	Counter64,
    gwInternetOutDroppedBytesCnt
	Counter64,
    gwInternetInTotalPpsMax
	Gauge32,
    gwInternetOutTotalPpsMax
	Gauge32,
    gwInternetInDroppedPpsMax
	Gauge32,
    gwInternetOutDroppedPpsMax
	Gauge32,
    gwInternetInTotalBpsMax
	Gauge32,
    gwInternetOutTotalBpsMax
	Gauge32,
    gwInternetInDroppedBpsMax
	Gauge32,
    gwInternetOutDroppedBpsMax
	Gauge32
}

gwInternetStatsIndex OBJECT-TYPE
    SYNTAX      LocalIndex
    MAX-ACCESS  not-accessible
    STATUS      current
    DESCRIPTION
        "Unique gw internet index"
    ::= { gwInternetStatsEntry 1 }

gwInternetMacAddress OBJECT-TYPE
    SYNTAX      DisplayString
    MAX-ACCESS  read-only
    STATUS      current
    DESCRIPTION
        "MAC address of a specific protected internet-side gateway"
    ::= { gwInternetStatsEntry 2 }

gwInternetIpAddress OBJECT-TYPE
    SYNTAX      DisplayString
    MAX-ACCESS  read-only
    STATUS      current
    DESCRIPTION
        "IP address of a specific protected internet-side gateway"
    ::= { gwInternetStatsEntry 3 }

gwInternetInTotalBytesCnt OBJECT-TYPE
    SYNTAX Counter64
    MAX-ACCESS  read-only
    STATUS      current
    DESCRIPTION
	"Total number of input bytes seen"
     ::= { gwInternetStatsEntry 101 }

gwInternetOutTotalBytesCnt OBJECT-TYPE
    SYNTAX Counter64
    MAX-ACCESS  read-only
    STATUS      current
    DESCRIPTION
	"Total number of output bytes seen"
     ::= { gwInternetStatsEntry 102 }

gwInternetInDroppedBytesCnt OBJECT-TYPE
    SYNTAX Counter64
    MAX-ACCESS  read-only
    STATUS      current
    DESCRIPTION
	"Total number of input bytes Dropped"
     ::= { gwInternetStatsEntry 103 }

gwInternetOutDroppedBytesCnt OBJECT-TYPE
    SYNTAX Counter64
    MAX-ACCESS  read-only
    STATUS      current
    DESCRIPTION
	"Total number of output bytes Dropped"
     ::= { gwInternetStatsEntry 104 }

gwInternetInTotalPpsMax OBJECT-TYPE
    SYNTAX      Gauge32
    MAX-ACCESS  read-only
    STATUS      current
    DESCRIPTION
	"Maximum number of input packets per second"
     ::= { gwInternetStatsEntry 201 }

gwInternetOutTotalPpsMax OBJECT-TYPE
    SYNTAX      Gauge32
    MAX-ACCESS  read-only
    STATUS      current
    DESCRIPTION
	"Maximum number of output packets per second"
     ::= { gwInternetStatsEntry 202 }

gwInternetInDroppedPpsMax OBJECT-TYPE
    SYNTAX      Gauge32
    MAX-ACCESS  read-only
    STATUS      current
    DESCRIPTION
	"Maximum number of input packets Dropped per second"
     ::= { gwInternetStatsEntry 203 }

gwInternetOutDroppedPpsMax OBJECT-TYPE
    SYNTAX      Gauge32
    MAX-ACCESS  read-only
    STATUS      current
    DESCRIPTION
	"Maximum number of output packets Dropped per second"
     ::= { gwInternetStatsEntry 204 }

gwInternetInTotalBpsMax OBJECT-TYPE
    SYNTAX      Gauge32
    MAX-ACCESS  read-only
    STATUS      current
    DESCRIPTION
	"Maximum number of input bits per second"
     ::= { gwInternetStatsEntry 301 }

gwInternetOutTotalBpsMax OBJECT-TYPE
    SYNTAX      Gauge32
    MAX-ACCESS  read-only
    STATUS      current
    DESCRIPTION
	"Maximum number of output bits per second"
     ::= { gwInternetStatsEntry 302 }

gwInternetInDroppedBpsMax OBJECT-TYPE
    SYNTAX      Gauge32
    MAX-ACCESS  read-only
    STATUS      current
    DESCRIPTION
	"Maximum number of input bits Dropped per second"
     ::= { gwInternetStatsEntry 303 }

gwInternetOutDroppedBpsMax OBJECT-TYPE
    SYNTAX      Gauge32
    MAX-ACCESS  read-only
    STATUS      current
    DESCRIPTION
	"Maximum number of output bits Dropped per second"
     ::= { gwInternetStatsEntry 304 }

gwProtectedStatsTable OBJECT-TYPE
    SYNTAX SEQUENCE OF GwProtectedStatsEntry
    MAX-ACCESS  not-accessible
    STATUS      current
    DESCRIPTION
        "Table of protected-side gateway statistics"
    ::= { jddsGatewayProtected 3 }

gwProtectedStatsEntry OBJECT-TYPE
    SYNTAX      GwProtectedStatsEntry
    MAX-ACCESS  not-accessible
    STATUS      current
    DESCRIPTION
        "A row associated with a specific protected IP side gateway"
    INDEX { gwProtectedIndex }
    ::= { gwProtectedStatsTable 1 }

GwProtectedStatsEntry ::= SEQUENCE {
    gwProtectedIndex
	LocalIndex,
    gwProtectedMacAddress
	DisplayString,
    gwProtectedIpAddress
	DisplayString,
    gwProtectedInTotalBytesCnt
	Counter64,
    gwProtectedOutTotalBytesCnt
	Counter64,
    gwProtectedInDroppedBytesCnt
	Counter64,
    gwProtectedOutDroppedBytesCnt
	Counter64,
    gwProtectedInTotalPpsMax
	Gauge32,
    gwProtectedOutTotalPpsMax
	Gauge32,
    gwProtectedInDroppedPpsMax
	Gauge32,
    gwProtectedOutDroppedPpsMax
	Gauge32,
    gwProtectedInTotalBpsMax
	Gauge32,
    gwProtectedOutTotalBpsMax
	Gauge32,
    gwProtectedInDroppedBpsMax
	Gauge32,
    gwProtectedOutDroppedBpsMax
	Gauge32
}

gwProtectedIndex OBJECT-TYPE
    SYNTAX      LocalIndex
    MAX-ACCESS  not-accessible
    STATUS      current
    DESCRIPTION
        "Unique protected gateway index"
    ::= { gwProtectedStatsEntry 1 }

gwProtectedMacAddress OBJECT-TYPE
    SYNTAX      DisplayString
    MAX-ACCESS  read-only
    STATUS      current
    DESCRIPTION
        "MAC address of a specific protected-side gateway"
    ::= { gwProtectedStatsEntry 2 }

gwProtectedIpAddress OBJECT-TYPE
    SYNTAX      DisplayString
    MAX-ACCESS  read-only
    STATUS      current
    DESCRIPTION
        "IP address of a specific protected-side gateway"
    ::= { gwProtectedStatsEntry 3 }

gwProtectedInTotalBytesCnt OBJECT-TYPE
    SYNTAX Counter64
    MAX-ACCESS  read-only
    STATUS      current
    DESCRIPTION
	"Total number of input bytes seen"
     ::= { gwProtectedStatsEntry 101 }

gwProtectedOutTotalBytesCnt OBJECT-TYPE
    SYNTAX Counter64
    MAX-ACCESS  read-only
    STATUS      current
    DESCRIPTION
	"Total number of output bytes seen"
     ::= { gwProtectedStatsEntry 102 }

gwProtectedInDroppedBytesCnt OBJECT-TYPE
    SYNTAX Counter64
    MAX-ACCESS  read-only
    STATUS      current
    DESCRIPTION
	"Total number of input bytes Dropped"
     ::= { gwProtectedStatsEntry 103 }

gwProtectedOutDroppedBytesCnt OBJECT-TYPE
    SYNTAX Counter64
    MAX-ACCESS  read-only
    STATUS      current
    DESCRIPTION
	"Total number of output bytes Dropped"
     ::= { gwProtectedStatsEntry 104 }

gwProtectedInTotalPpsMax OBJECT-TYPE
    SYNTAX      Gauge32
    MAX-ACCESS  read-only
    STATUS      current
    DESCRIPTION
	"Maximum number of input packets per second"
     ::= { gwProtectedStatsEntry 201 }

gwProtectedOutTotalPpsMax OBJECT-TYPE
    SYNTAX      Gauge32
    MAX-ACCESS  read-only
    STATUS      current
    DESCRIPTION
	"Maximum number of output packets per second"
     ::= { gwProtectedStatsEntry 202 }

gwProtectedInDroppedPpsMax OBJECT-TYPE
    SYNTAX      Gauge32
    MAX-ACCESS  read-only
    STATUS      current
    DESCRIPTION
	"Maximum number of input packets Dropped per second"
     ::= { gwProtectedStatsEntry 203 }

gwProtectedOutDroppedPpsMax OBJECT-TYPE
    SYNTAX      Gauge32
    MAX-ACCESS  read-only
    STATUS      current
    DESCRIPTION
	"Maximum number of output packets Dropped per second"
     ::= { gwProtectedStatsEntry 204 }

gwProtectedInTotalBpsMax OBJECT-TYPE
    SYNTAX      Gauge32
    MAX-ACCESS  read-only
    STATUS      current
    DESCRIPTION
	"Maximum number of input bits per second"
     ::= { gwProtectedStatsEntry 301 }

gwProtectedOutTotalBpsMax OBJECT-TYPE
    SYNTAX      Gauge32
    MAX-ACCESS  read-only
    STATUS      current
    DESCRIPTION
	"Maximum number of output bits per second"
     ::= { gwProtectedStatsEntry 302 }

gwProtectedInDroppedBpsMax OBJECT-TYPE
    SYNTAX      Gauge32
    MAX-ACCESS  read-only
    STATUS      current
    DESCRIPTION
	"Maximum number of input bits Dropped per second"
     ::= { gwProtectedStatsEntry 303 }

gwProtectedOutDroppedBpsMax OBJECT-TYPE
    SYNTAX      Gauge32
    MAX-ACCESS  read-only
    STATUS      current
    DESCRIPTION
	"Maximum number of output bits Dropped per second"
     ::= { gwProtectedStatsEntry 304 }


-- End of Gateway statistics

ddossecureEvents OBJECT-IDENTITY
    STATUS	current
    DESCRIPTION
	"Definition point for DDoS Secure notifications"
    ::= {ddossecure4MIB 0}

prBandwidthLimitOn NOTIFICATION-TYPE
    OBJECTS     { prHostName, prBandwidth }
    STATUS	current
    DESCRIPTION
	"Rate limiting traffic by bandwidth. Tracked by protected IP / portal."
    ::= {ddossecureEvents 2011}

prBandwidthLimitOff NOTIFICATION-TYPE
    OBJECTS     { prHostName, prBandwidth }
    STATUS	current
    DESCRIPTION
	"No longer rate limiting traffic by bandwidth."
    ::= {ddossecureEvents 2012}

prPacketLimitOn NOTIFICATION-TYPE
    OBJECTS     { prHostName, prFlood }
    STATUS	current
    DESCRIPTION
	"Rate limiting traffic by packet rate."
    ::= {ddossecureEvents 2021}

prPacketLimitOff NOTIFICATION-TYPE
    OBJECTS     { prHostName, prFlood }
    STATUS	current
    DESCRIPTION
	"No longer rate limiting traffic by packet rate."
    ::= {ddossecureEvents 2022}

prBlockedProtocolBlackListIpOn NOTIFICATION-TYPE
    OBJECTS     { prHostName, prBlockedProtocol }
    STATUS	current
    DESCRIPTION
	"Dropping traffic not expressly permitted. Tracked by protected IP."
    ::= {ddossecureEvents 2031}

prBlockedProtocolBlackListIpOff NOTIFICATION-TYPE
    OBJECTS     { prHostName, prBlockedProtocol }
    STATUS	current
    DESCRIPTION
	"No longer Dropping traffic not expressly permitted."
    ::= {ddossecureEvents 2032}

prBlockedProtocolIcmpTypeOn NOTIFICATION-TYPE
    OBJECTS     { prHostName, prBlockedProtocol }
    STATUS	current
    DESCRIPTION
	"Dropping traffic not expressly permitted. Tracked by protected IP."
    ::= {ddossecureEvents 2041}

prBlockedProtocolIcmpTypeOff NOTIFICATION-TYPE
    OBJECTS     { prHostName, prBlockedProtocol }
    STATUS	current
    DESCRIPTION
	"No longer Dropping traffic not expressly permitted."
    ::= {ddossecureEvents 2042}

prBlockedProtocolPortOn NOTIFICATION-TYPE
    OBJECTS     { prHostName, prBlockedProtocol }
    STATUS	current
    DESCRIPTION
	"Dropping traffic not expressly permitted. Tracked by protected IP."
    ::= {ddossecureEvents 2051}

prBlockedProtocolPortOff NOTIFICATION-TYPE
    OBJECTS     { prHostName, prBlockedProtocol }
    STATUS	current
    DESCRIPTION
	"No longer Dropping traffic not expressly permitted."
    ::= {ddossecureEvents 2052}

prBlockedProtocolOtherOn NOTIFICATION-TYPE
    OBJECTS     { prHostName, prBlockedProtocol }
    STATUS	current
    DESCRIPTION
	"Dropping traffic not expressly permitted. Tracked by protected IP."
    ::= {ddossecureEvents 2061}

prBlockedProtocolOtherOff NOTIFICATION-TYPE
    OBJECTS     { prHostName, prBlockedProtocol }
    STATUS	current
    DESCRIPTION
	"No longer Dropping traffic not expressly permitted."
    ::= {ddossecureEvents 2062}

prUnknownSessionIcmpRespOn NOTIFICATION-TYPE
    OBJECTS     { prHostName, prBlockedState }
    STATUS	current
    DESCRIPTION
	"Dropping TCP traffic that is out of state. Tracked by protected IP."
    ::= {ddossecureEvents 2081}

prUnknownSessionIcmpRespOff NOTIFICATION-TYPE
    OBJECTS     { prHostName, prBlockedState }
    STATUS	current
    DESCRIPTION
	"No longer Dropping TCP traffic that is out of state."
    ::= {ddossecureEvents 2082}

prUnknownSessionIcmpDiagRespOn NOTIFICATION-TYPE
    OBJECTS     { prHostName, prBlockedState }
    STATUS	current
    DESCRIPTION
	"Dropping TCP traffic that is out of state. Tracked by protected IP."
    ::= {ddossecureEvents 2091}

prUnknownSessionIcmpDiagRespOff NOTIFICATION-TYPE
    OBJECTS     { prHostName, prBlockedState }
    STATUS	current
    DESCRIPTION
	"No longer Dropping TCP traffic that is out of state."
    ::= {ddossecureEvents 2092}

prUnknownSessionNoStateOn NOTIFICATION-TYPE
    OBJECTS     { prHostName, prBlockedState }
    STATUS	current
    DESCRIPTION
	"Dropping TCP traffic that is out of state. Tracked by protected IP."
    ::= {ddossecureEvents 2101}

prUnknownSessionNoStateOff NOTIFICATION-TYPE
    OBJECTS     { prHostName, prBlockedState }
    STATUS	current
    DESCRIPTION
	"No longer Dropping TCP traffic that is out of state."
    ::= {ddossecureEvents 2102}

prUnknownSessionInvalidStateOn NOTIFICATION-TYPE
    OBJECTS     { prHostName, prBlockedState }
    STATUS	current
    DESCRIPTION
	"Dropping TCP traffic that is out of state. Tracked by protected IP."
    ::= {ddossecureEvents 2111}

prUnknownSessionInvalidStateOff NOTIFICATION-TYPE
    OBJECTS     { prHostName, prBlockedState }
    STATUS	current
    DESCRIPTION
	"No longer Dropping TCP traffic that is out of state."
    ::= {ddossecureEvents 2112}

prTcpAttackRstOn NOTIFICATION-TYPE
    OBJECTS     { prHostName, prTcpAttack }
    STATUS	current
    DESCRIPTION
	"Dropping TCP packets causing stress. Tracked by protected IP."
    ::= {ddossecureEvents 2121}

prTcpAttackRstOff NOTIFICATION-TYPE
    OBJECTS     { prHostName, prTcpAttack }
    STATUS	current
    DESCRIPTION
	"No longer Dropping TCP packets causing stress."
    ::= {ddossecureEvents 2122}

prIpAttackLandOn NOTIFICATION-TYPE
    OBJECTS     { prHostName, prIpAttack }
    STATUS	current
    DESCRIPTION
	"Dropping IP packets causing stress. Tracked by protected IP."
    ::= {ddossecureEvents 2131}

prIpAttackLandOff NOTIFICATION-TYPE
    OBJECTS     { prHostName, prIpAttack }
    STATUS	current
    DESCRIPTION
	"No longer Dropping IP packets causing stress."
    ::= {ddossecureEvents 2132}

prTcpAttackSynAckToOn NOTIFICATION-TYPE
    OBJECTS     { prHostName, prTcpAttack }
    STATUS	current
    DESCRIPTION
	"Dropping TCP packets causing stress. Tracked by protected IP."
    ::= {ddossecureEvents 2141}

prTcpAttackSynAckToOff NOTIFICATION-TYPE
    OBJECTS     { prHostName, prTcpAttack }
    STATUS	current
    DESCRIPTION
	"No longer Dropping TCP packets causing stress."
    ::= {ddossecureEvents 2142}

prBlockedProtocolCountryOn NOTIFICATION-TYPE
    OBJECTS     { prHostName, prBlockedProtocol }
    STATUS	current
    DESCRIPTION
	"This IP address is part of a blocked country or network"
    ::= {ddossecureEvents 2151}

prBlockedProtocolCountryOff NOTIFICATION-TYPE
    OBJECTS     { prHostName, prBlockedProtocol }
    STATUS	current
    DESCRIPTION
	"This IP address is no longer part of a blocked country or network."
    ::= {ddossecureEvents 2152}

prTcpAttackSynFloodOn NOTIFICATION-TYPE
    OBJECTS     { prHostName, prTcpAttack }
    STATUS	current
    DESCRIPTION
	"Receiving SYN packets at a rate higher than it can handle. Tracked by protected IP."
    ::= {ddossecureEvents 2161}

prTcpAttackSynFloodOff NOTIFICATION-TYPE
    OBJECTS     { prHostName, prTcpAttack }
    STATUS	current
    DESCRIPTION
	"No longer receiving a SYN flood."
    ::= {ddossecureEvents 2162}

prTcpAttackConnFloodOn NOTIFICATION-TYPE
    OBJECTS     { prHostName, prTcpAttack }
    STATUS	current
    DESCRIPTION
	"Reached concurrent connection configured limit. Tracked by protected IP."
    ::= {ddossecureEvents 2171}

prTcpAttackConnFloodOff NOTIFICATION-TYPE
    OBJECTS     { prHostName, prTcpAttack }
    STATUS	current
    DESCRIPTION
	"No longer above the concurrent connection configured limit"
    ::= {ddossecureEvents 2172}

prTcpAttackTableFullOn NOTIFICATION-TYPE
    OBJECTS     { prHostName, prTcpAttack }
    STATUS	current
    DESCRIPTION
	"Internal state table for TCP connections is full. Tracked by protected IP."
    ::= {ddossecureEvents 2181}

prTcpAttackTableFullOff NOTIFICATION-TYPE
    OBJECTS     { prHostName, prTcpAttack }
    STATUS	current
    DESCRIPTION
	"Internal state table for TCP connections is no longer full."
    ::= {ddossecureEvents 2182}

prBadTcpFastAckOn NOTIFICATION-TYPE
    OBJECTS     { prHostName, prBadTcp }
    STATUS	current
    DESCRIPTION
	"Identical ACKs repeated at a rate greater than 10 per second. Tracked by protected IP."
    ::= {ddossecureEvents 2191}

prBadTcpFastAckOff NOTIFICATION-TYPE
    OBJECTS     { prHostName, prBadTcp }
    STATUS	current
    DESCRIPTION
	"No longer seeing identical ACKs repeated at a rate greater than 10 per second. Tracked by protected IP."
    ::= {ddossecureEvents 2192}

prTcpAttackHttpFloodOn NOTIFICATION-TYPE
    OBJECTS     { prHostName, prTcpAttack }
    STATUS	current
    DESCRIPTION
	"The protected IP has reached its concurrent GET/HEAD configured limit. Tracked by protected IP."
    ::= {ddossecureEvents 2201}

prTcpAttackHttpFloodOff NOTIFICATION-TYPE
    OBJECTS     { prHostName, prTcpAttack }
    STATUS	current
    DESCRIPTION
	"Dropped below the concurrent GET/HEAD configured limit."
    ::= {ddossecureEvents 2202}

prUdpAttackTableFullOn NOTIFICATION-TYPE
    OBJECTS     { prHostName, prUdpAttack }
    STATUS	current
    DESCRIPTION
	"Internal state table for UDP connections is full. Tracked by protected IP."
    ::= {ddossecureEvents 2211}

prUdpAttackTableFullOff NOTIFICATION-TYPE
    OBJECTS     { prHostName, prUdpAttack }
    STATUS	current
    DESCRIPTION
	"Internal state table for UDP connections is no longer full."
    ::= {ddossecureEvents 2212}

prTcpAttackHttpTimeoutOn NOTIFICATION-TYPE
    OBJECTS     { prHostName, prTcpAttack }
    STATUS	current
    DESCRIPTION
	"No response to a GET or HEAD request in a timely manner. Tracked by protected IP."
    ::= {ddossecureEvents 2231}

prTcpAttackHttpTimeoutOff NOTIFICATION-TYPE
    OBJECTS     { prHostName, prTcpAttack }
    STATUS	current
    DESCRIPTION
	"protected IP is now responding to a GET or HEAD request in a timely manner."
    ::= {ddossecureEvents 2232}

prIcmpAttackRepeatsOn NOTIFICATION-TYPE
    OBJECTS     { prHostName, prIcmpAttack }
    STATUS	current
    DESCRIPTION
	"Dropping ICMP packets causing stress. Tracked by protected IP."
    ::= {ddossecureEvents 2241}

prIcmpAttackRepeatsOff NOTIFICATION-TYPE
    OBJECTS     { prHostName, prIcmpAttack }
    STATUS	current
    DESCRIPTION
	"No longer Dropping ICMP packets causing stress. Tracked by protected IP."
    ::= {ddossecureEvents 2242}

prIcmpAttackTableFullOn NOTIFICATION-TYPE
    OBJECTS     { prHostName, prIcmpAttack }
    STATUS	current
    DESCRIPTION
	"Dropping ICMP packets causing stress. Tracked by protected IP."
    ::= {ddossecureEvents 2251}

prIcmpAttackTableFullOff NOTIFICATION-TYPE
    OBJECTS     { prHostName, prIcmpAttack }
    STATUS	current
    DESCRIPTION
	"No longer Dropping ICMP packets causing stress. Tracked by protected IP."
    ::= {ddossecureEvents 2252}

prOtherIpAttackTableFullOn NOTIFICATION-TYPE
    OBJECTS     { prHostName, prOtherIpAttack }
    STATUS	current
    DESCRIPTION
	"Dropping Other IP packets causing stress. Tracked by protected IP."
    ::= {ddossecureEvents 2271}

prOtherIpAttackTableFullOff NOTIFICATION-TYPE
    OBJECTS     { prHostName, prOtherIpAttack }
    STATUS	current
    DESCRIPTION
	"No longer Dropping Other IP packets causing stress."
    ::= {ddossecureEvents 2272}

prFragAttackPingOfDeathOn NOTIFICATION-TYPE
    OBJECTS     { prHostName, prFragAttack }
    STATUS	current
    DESCRIPTION
	"Dropping packet fragments that are causing stress. Assembled packet are longer than 65535 bytes. Tracked by protected IP."
    ::= {ddossecureEvents 2291}

prFragAttackPingOfDeathOff NOTIFICATION-TYPE
    OBJECTS     { prHostName, prFragAttack }
    STATUS	current
    DESCRIPTION
	"No longer Dropping packet fragments that are causing stress, Assembled packet are less than 65535 bytes. Tracked by protected IP."
    ::= {ddossecureEvents 2292}

prFragAttackHeadOverlayOn NOTIFICATION-TYPE
    OBJECTS     { prHostName, prFragAttack }
    STATUS	current
    DESCRIPTION
	"Dropping packet fragments that are causing stress. Tracked by protected IP."
    ::= {ddossecureEvents 2301}

prFragAttackHeadOverlayOff NOTIFICATION-TYPE
    OBJECTS     { prHostName, prFragAttack }
    STATUS	current
    DESCRIPTION
	"No longer Dropping packet fragments that are causing stress. Tracked by protected IP."
    ::= {ddossecureEvents 2302}

prFragAttackTableFullOn NOTIFICATION-TYPE
    OBJECTS     { prHostName, prFragAttack }
    STATUS	current
    DESCRIPTION
	"Dropping packet fragments that are causing stress. Internal state table for fragments is full. Tracked by protected IP."
    ::= {ddossecureEvents 2311}

prFragAttackTableFullOff NOTIFICATION-TYPE
    OBJECTS     { prHostName, prFragAttack }
    STATUS	current
    DESCRIPTION
	"No longer Dropping packet fragments that are causing stress, Internal state table for fragments is no longer full. Tracked by protected IP."
    ::= {ddossecureEvents 2312}

prFragAttackSmallSizeOn NOTIFICATION-TYPE
    OBJECTS     { prHostName, prFragAttack }
    STATUS	current
    DESCRIPTION
	"Dropping packet fragments that are causing stress. Initial TCP fragment is smaller than header. Tracked by protected IP."
    ::= {ddossecureEvents 2321}

prFragAttackSmallSizeOff NOTIFICATION-TYPE
    OBJECTS     { prHostName, prFragAttack }
    STATUS	current
    DESCRIPTION
	"No longer Dropping packet fragments that are causing stress, Header is within Initial TCP fragment size. Tracked by protected IP."
    ::= {ddossecureEvents 2322}

prFragAttackNoFragsAllowedOn NOTIFICATION-TYPE
    OBJECTS     { prHostName, prFragAttack }
    STATUS	current
    DESCRIPTION
	"Dropping packet fragments that are causing stress. Fragmentation has been disabled in the Filter. Tracked by protected IP."
    ::= {ddossecureEvents 2331}

prFragAttackNoFragsAllowedOff NOTIFICATION-TYPE
    OBJECTS     { prHostName, prFragAttack }
    STATUS	current
    DESCRIPTION
	"No longer Dropping packet fragments that are causing stress, Fragmentation has been reenabled in the Filter. Tracked by protected IP."
    ::= {ddossecureEvents 2332}

prBadIpSrcAddrOn NOTIFICATION-TYPE
    OBJECTS     { prHostName, prBadIp }
    STATUS	current
    DESCRIPTION
	"Dropping IP packets that do not match RFCs. Invalid Source Address. Tracked by protected IP."
    ::= {ddossecureEvents 2341}

prBadIpSrcAddrOff NOTIFICATION-TYPE
    OBJECTS     { prHostName, prBadIp }
    STATUS	current
    DESCRIPTION
	"No longer Dropping IP packets that do not match RFCs. Source Address now valid"
    ::= {ddossecureEvents 2342}

prBadIpHeaderOn NOTIFICATION-TYPE
    OBJECTS     { prHostName, prBadIp }
    STATUS	current
    DESCRIPTION
	"Dropping IP packets that do not match RFCs. Header malformed. Tracked by protected IP."
    ::= {ddossecureEvents 2351}

prBadIpHeaderOff NOTIFICATION-TYPE
    OBJECTS     { prHostName, prBadIp }
    STATUS	current
    DESCRIPTION
	"No longer Dropping IP packets that do not match RFCs. Header no longer malformed."
    ::= {ddossecureEvents 2352}

prBadIpOptionOn NOTIFICATION-TYPE
    OBJECTS     { prHostName, prBadIp }
    STATUS	current
    DESCRIPTION
	"Dropping IP packets that do not match RFCs. Invalid option field or field length. Tracked by protected IP."
    ::= {ddossecureEvents 2361}

prBadIpOptionOff NOTIFICATION-TYPE
    OBJECTS     { prHostName, prBadIp }
    STATUS	current
    DESCRIPTION
	"No longer Dropping IP packets that do not match RFCs. Option field or field length now valid."
    ::= {ddossecureEvents 2362}

prBadIpSizeOn NOTIFICATION-TYPE
    OBJECTS     { prHostName, prBadIp }
    STATUS	current
    DESCRIPTION
	"Dropping IP packets that do not match RFCs. Invalid length field. Tracked by protected IP."
    ::= {ddossecureEvents 2371}

prBadIpSizeOff NOTIFICATION-TYPE
    OBJECTS     { prHostName, prBadIp }
    STATUS	current
    DESCRIPTION
	"No longer Dropping IP packets that do not match RFCs. Length field now valid."
    ::= {ddossecureEvents 2372}

prBlockedProtocolTmpBlackListOn NOTIFICATION-TYPE
    OBJECTS     { prHostName, prBlockedProtocol }
    STATUS	current
    DESCRIPTION
	"Dropping IP packets that have been temporarily black-listed. Tracked by protected IP."
    ::= {ddossecureEvents 2381}

prBlockedProtocolTmpBlackListOff NOTIFICATION-TYPE
    OBJECTS     { prHostName, prBlockedProtocol }
    STATUS	current
    DESCRIPTION
	"No longer Dropping IP packets that have been temporarily black-listed."
    ::= {ddossecureEvents 2382}

prBadTcpFlagsOn NOTIFICATION-TYPE
    OBJECTS     { prHostName, prBadTcp }
    STATUS	current
    DESCRIPTION
	"Dropping TCP packets that do not match RFCs. Invalid TCP flag combinations. Tracked by protected IP."
    ::= {ddossecureEvents 2391}

prBadTcpFlagsOff NOTIFICATION-TYPE
    OBJECTS     { prHostName, prBadTcp }
    STATUS	current
    DESCRIPTION
	"No longer Dropping TCP packets that do not match RFCs. TCP flag combinations now valid."
    ::= {ddossecureEvents 2392}

prBadTcpMalformedOn NOTIFICATION-TYPE
    OBJECTS     { prHostName, prBadTcp }
    STATUS	current
    DESCRIPTION
	"Dropping TCP packets that do not match RFCs. Format of TCP Header invalid. Tracked by protected IP."
    ::= {ddossecureEvents 2401}

prBadTcpMalformedOff NOTIFICATION-TYPE
    OBJECTS     { prHostName, prBadTcp }
    STATUS	current
    DESCRIPTION
	"No longer Dropping TCP packets that do not match RFCs. Format of TCP Header now valid."
    ::= {ddossecureEvents 2402}

prBadTcpOptionOn NOTIFICATION-TYPE
    OBJECTS     { prHostName, prBadTcp }
    STATUS	current
    DESCRIPTION
	"Dropping TCP packets that do not match RFCs. Invalid TCP option field. Tracked by protected IP."
    ::= {ddossecureEvents 2411}

prBadTcpOptionOff NOTIFICATION-TYPE
    OBJECTS     { prHostName, prBadTcp }
    STATUS	current
    DESCRIPTION
	"No longer Dropping TCP packets that do not match RFCs. TCP option field now valid."
    ::= {ddossecureEvents 2412}

prBlockedProtocolDnsOn NOTIFICATION-TYPE
    OBJECTS     { prHostName, prBlockedProtocol }
    STATUS	current
    DESCRIPTION
	"Dropping DNS requests that have been black-listed. Tracked by protected IP."
    ::= {ddossecureEvents 2421}

prBlockedProtocolDnsOff NOTIFICATION-TYPE
    OBJECTS     { prHostName, prBlockedProtocol }
    STATUS	current
    DESCRIPTION
	"No longer Dropping DNS requests that have been black-listed."
    ::= {ddossecureEvents 2422}

prBadUdpNoDataOn NOTIFICATION-TYPE
    OBJECTS     { prHostName, prBadUdp }
    STATUS	current
    DESCRIPTION
	"Dropping UDP packets that do not match RFCs. UDP packet contains no data. Tracked by protected IP."
    ::= {ddossecureEvents 2431}

prBadUdpNoDataOff NOTIFICATION-TYPE
    OBJECTS     { prHostName, prBadUdp }
    STATUS	current
    DESCRIPTION
	"No longer Dropping UDP packets that do not match RFCs. UDP packet now contain data."
    ::= {ddossecureEvents 2432}

prBadUdpMalformedOn NOTIFICATION-TYPE
    OBJECTS     { prHostName, prBadUdp }
    STATUS	current
    DESCRIPTION
	"Dropping UDP packets that do not match RFCs. UDP header malformed. Tracked by protected IP."
    ::= {ddossecureEvents 2441}

prBadUdpMalformedOff  NOTIFICATION-TYPE
    OBJECTS     { prHostName, prBadUdp }
    STATUS	current
    DESCRIPTION
	"No longer Dropping UDP packets that do not match RFCs. UDP header no longer malformed."
    ::= {ddossecureEvents 2442}

prBlockedProtocolAsOn NOTIFICATION-TYPE
    OBJECTS     { prHostName, prBlockedProtocol }
    STATUS	current
    DESCRIPTION
	"Dropping AS requests that have been black-listed. Tracked by protected IP."
    ::= {ddossecureEvents 2451}

prBlockedProtocolAsOff NOTIFICATION-TYPE
    OBJECTS     { prHostName, prBlockedProtocol }
    STATUS	current
    DESCRIPTION
	"No longer Dropping AS requests that have been black-listed."
    ::= {ddossecureEvents 2452}

ptTcpAttackHttpRateFloodOn NOTIFICATION-TYPE
    OBJECTS     { prHostName, prTcpAttack }
    STATUS	current
    DESCRIPTION
	"Dropping TCP packets causing stress. HTTP requests rate exceeds configured threshold. Tracked by protected IP."
    ::= {ddossecureEvents 2461}

ptTcpAttackHttpRateFloodOff NOTIFICATION-TYPE
    OBJECTS     { prHostName, prTcpAttack }
    STATUS	current
    DESCRIPTION
	"No longer Dropping TCP packets causing stress. HTTP requests rate now below configured threshold."
    ::= {ddossecureEvents 2462}

prBadIcmpMalformedOn NOTIFICATION-TYPE
    OBJECTS     { prHostName, prBadIcmp }
    STATUS	current
    DESCRIPTION
	"Dropping ICMP packets that do not match RFCs. ICMP header malformed (length, options etc). Tracked by protected IP."
    ::= {ddossecureEvents 2471}

prBadIcmpMalformedOff NOTIFICATION-TYPE
    OBJECTS     { prHostName, prBadIcmp }
    STATUS	current
    DESCRIPTION
	"No longer Dropping ICMP packets that do not match RFCs. ICMP header no longer malformed."
    ::= {ddossecureEvents 2472}

prBlockedProtocolUrlOn NOTIFICATION-TYPE
    OBJECTS     { prHostName, prBlockedProtocol }
    STATUS	current
    DESCRIPTION
	"Dropping URL requests that have been black-listed. Tracked by protected IP."
    ::= {ddossecureEvents 2481}

prBlockedProtocolUrlOff NOTIFICATION-TYPE
    OBJECTS     { prHostName, prBlockedProtocol }
    STATUS	current
    DESCRIPTION
	"No longer Dropping URL requests that have been black-listed."
    ::= {ddossecureEvents 2482}

prBadOtherIpProtocolOn NOTIFICATION-TYPE
    OBJECTS     { prHostName, prBadOtherIp }
    STATUS	current
    DESCRIPTION
	"Dropping Other IP packets that do not match RFCs. Invalid IP protocol number. Tracked by protected IP."
    ::= {ddossecureEvents 2501}

prBadOtherIpProtocolOff NOTIFICATION-TYPE
    OBJECTS     { prHostName, prBadOtherIp }
    STATUS	current
    DESCRIPTION
	"No longer Dropping Other IP packets that do not match RFCs. IP protocol number now valid."
    ::= {ddossecureEvents 2502}

prBadOtherIpLengthOn NOTIFICATION-TYPE
    OBJECTS     { prHostName, prBadOtherIp }
    STATUS	current
    DESCRIPTION
	"Dropping Other IP packets that do not match RFCs. IP packet too short to contain IP Protocol header. Tracked by protected IP."
    ::= {ddossecureEvents 2511}

prBadOtherIpLengthOff NOTIFICATION-TYPE
    OBJECTS     { prHostName, prBadOtherIp }
    STATUS	current
    DESCRIPTION
	"No longer Dropping Other IP packets that do not match RFCs. IP packet no longer too short to contain IP Protocol header."
    ::= {ddossecureEvents 2512}

prTcpAttackHttpIncompleteOn NOTIFICATION-TYPE
    OBJECTS     { prHostName, prBadOtherIp }
    STATUS	current
    DESCRIPTION
	"Reporting incomplete HTTP requests. Tracked by protected IP."
    ::= {ddossecureEvents 2521}

prTcpAttackHttpIncompleteOff NOTIFICATION-TYPE
    OBJECTS     { prHostName, prBadOtherIp }
    STATUS	current
    DESCRIPTION
	"No longer Reporting incomplete HTTP requests."
    ::= {ddossecureEvents 2522}

prOverloadedStallOn NOTIFICATION-TYPE
    OBJECTS     { prHostName, prOverloaded }
    STATUS	current
    DESCRIPTION
	"Detected overloaded protected IP. The protected IP has stopped responding to anything. Tracked by protected IP."
    ::= {ddossecureEvents 2531}

prOverloadedStallOff NOTIFICATION-TYPE
    OBJECTS     { prHostName, prOverloaded }
    STATUS	current
    DESCRIPTION
	"No longer detected overloaded protected IP. The protected IP is now responding."
    ::= {ddossecureEvents 2532}

prFragAttackTimeOutOn NOTIFICATION-TYPE
    OBJECTS     { prHostName, prFragAttack }
    STATUS	current
    DESCRIPTION
	"Dropping packet fragments that are causing stress. Fragments taking too long. Tracked by protected IP."
    ::= {ddossecureEvents 2541}

prFragAttackTimeOutOff NOTIFICATION-TYPE
    OBJECTS     { prHostName, prFragAttack }
    STATUS	current
    DESCRIPTION
	"No longer Dropping packet fragments that are causing stress, Fragments no longer timing out. Tracked by protected IP."
    ::= {ddossecureEvents 2542}

prFragAttackRepeatsOn NOTIFICATION-TYPE
    OBJECTS     { prHostName, prFragAttack }
    STATUS	current
    DESCRIPTION
	"Dropping packet fragments that are causing stress. Fragment Repeats. Tracked by protected IP."
    ::= {ddossecureEvents 2551}

prFragAttackRepeatsOff NOTIFICATION-TYPE
    OBJECTS     { prHostName, prFragAttack }
    STATUS	current
    DESCRIPTION
	"No longer Dropping packet fragments that are causing stress, Fragment no longer Repeats. Tracked by protected IP."
    ::= {ddossecureEvents 2552}

prFragAttackBadLengthOn NOTIFICATION-TYPE
    OBJECTS     { prHostName, prFragAttack }
    STATUS	current
    DESCRIPTION
	"Dropping packet fragments that are causing stress. Invalid fragment length in IP header. Tracked by protected IP."
    ::= {ddossecureEvents 2561}

prFragAttackBadLengthOff NOTIFICATION-TYPE
    OBJECTS     { prHostName, prFragAttack }
    STATUS	current
    DESCRIPTION
	"No longer Dropping packet fragments that are causing stress, Fragment length in IP header now valid. Tracked by protected IP."
    ::= {ddossecureEvents 2562}

prOverloadedBacklogOn NOTIFICATION-TYPE
    OBJECTS     { prHostName, prOverloaded }
    STATUS	current
    DESCRIPTION
	"The protected IP cannot keep up with new TCP connections and is not responding to some SYN requests. Tracked by protected IP."
    ::= {ddossecureEvents 2681}

prOverloadedBacklogOff NOTIFICATION-TYPE
    OBJECTS     { prHostName, prOverloaded }
    STATUS	current
    DESCRIPTION
	"No longer detected overloaded protected IP."
    ::= {ddossecureEvents 2682}

prBlockedProtocolAddressOn NOTIFICATION-TYPE
    OBJECTS     { prHostName, prBlockedProtocol }
    STATUS	current
    DESCRIPTION
	"Blocking protocol as Destination of inbound IP packet, or source of outbound IP packet is not a protected IP address. Tracked by protected IP."
    ::= {ddossecureEvents 2691}

prBlockedProtocolAddressOff NOTIFICATION-TYPE
    OBJECTS     { prHostName, prBlockedProtocol }
    STATUS	current
    DESCRIPTION
	"no longer blocking packets not containing protected IP address."
    ::= {ddossecureEvents 2692}

prTcpAttackNoDataOn NOTIFICATION-TYPE
    OBJECTS     { prHostName, prTcpAttack }
    STATUS	current
    DESCRIPTION
	"Dropping TCP packets causing stress.  Tracked by protected IP."
    ::= {ddossecureEvents 2701}

prTcpAttackNoDataOff NOTIFICATION-TYPE
    OBJECTS     { prHostName, prTcpAttack }
    STATUS	current
    DESCRIPTION
	"No longer Dropping TCP packets causing stress. "
    ::= {ddossecureEvents 2702}

prTcpAttackNoServerDataOn NOTIFICATION-TYPE
    OBJECTS     { prHostName, prTcpAttack }
    STATUS	current
    DESCRIPTION
	"Dropping TCP packets causing stress.  Tracked by protected IP."
    ::= {ddossecureEvents 2711}

prTcpAttackNoServerDataOff NOTIFICATION-TYPE
    OBJECTS     { prHostName, prTcpAttack }
    STATUS	current
    DESCRIPTION
	"No longer Dropping TCP packets causing stress. "
    ::= {ddossecureEvents 2712}

prTcpAttackConnRateFloodOn NOTIFICATION-TYPE
    OBJECTS     { prHostName, prTcpAttack }
    STATUS	current
    DESCRIPTION
	"Dropping TCP packets as the protected IP is receiving connection requests at a rate higher than it is configured for. Tracked by protected IP."
    ::= {ddossecureEvents 2721}

prTcpAttackConnRateFloodOff NOTIFICATION-TYPE
    OBJECTS     { prHostName, prTcpAttack }
    STATUS	current
    DESCRIPTION
	"No longer Dropping TCP packets as the protected IP is receiving connection requests at or below the configured rate."
    ::= {ddossecureEvents 2722}

prOverloadedThreadsOn NOTIFICATION-TYPE
    OBJECTS     { prHostName, prOverloaded }
    STATUS	current
    DESCRIPTION
	"Detected overloaded protected IP. The protected IP is not acknowledging data requests. Tracked by protected IP."
    ::= {ddossecureEvents 2731}

prOverloadedThreadsOff NOTIFICATION-TYPE
    OBJECTS     { prHostName, prOverloaded }
    STATUS	current
    DESCRIPTION
	"No longer detected overloaded protected IP. The protected IP is now acknowledging data requests."
    ::= {ddossecureEvents 2732}

prBadIpReflectedRouteOn NOTIFICATION-TYPE
    OBJECTS     { prHostName, prBadIp }
    STATUS	current
    DESCRIPTION
	"Dropping IP packets that do not match RFCs. Same packet seen both sides of DDoS Secure. Tracked by protected IP."
    ::= {ddossecureEvents 2741}

prBadIpReflectedRouteOff NOTIFICATION-TYPE
    OBJECTS     { prHostName, prBadIp }
    STATUS	current
    DESCRIPTION
	"No longer Dropping IP packets that do not match RFCs. No longer seeing same packet on both sides of DDoS Secure."
    ::= {ddossecureEvents 2742}

prTcpAttackPortScanOn NOTIFICATION-TYPE
    OBJECTS     { prHostName, prTcpAttack }
    STATUS	current
    DESCRIPTION
	"Dropping TCP packets as the protected IP is receiving connection requests at a rate higher than it is configured for. Tracked by protected IP."
    ::= {ddossecureEvents 2771}

prTcpAttackPortScanOff NOTIFICATION-TYPE
    OBJECTS     { prHostName, prTcpAttack }
    STATUS	current
    DESCRIPTION
	"No longer Dropping TCP packets as the protected IP is receiving connection requests at or below the configured rate."
    ::= {ddossecureEvents 2772}

prTcpAttackSmallWindowOn NOTIFICATION-TYPE
    OBJECTS     { prHostName, prTcpAttack }
    STATUS	current
    DESCRIPTION
	"Dropping TCP packets as the protected IP is receiving connection requests at a rate higher than it is configured for. Tracked by protected IP."
    ::= {ddossecureEvents 2781}

prTcpAttackSmallWindowOff NOTIFICATION-TYPE
    OBJECTS     { prHostName, prTcpAttack }
    STATUS	current
    DESCRIPTION
	"No longer Dropping TCP packets as the protected IP is receiving connection requests at or below the configured rate."
    ::= {ddossecureEvents 2782}

prTcpAttackClientAbortOn NOTIFICATION-TYPE
    OBJECTS     { prHostName, prTcpAttack }
    STATUS	current
    DESCRIPTION
	"Dropping TCP packets as client aborted connection after request. Tracked by protected IP."
    ::= {ddossecureEvents 2791}

prTcpAttackClientAbortOff NOTIFICATION-TYPE
    OBJECTS     { prHostName, prTcpAttack }
    STATUS	current
    DESCRIPTION
	"No longer dropping TCP packets as client aborted connection after request."
    ::= {ddossecureEvents 2792}

prBlockedProtocolSipOn NOTIFICATION-TYPE
    OBJECTS     { prHostName, prBlockedProtocol }
    STATUS	current
    DESCRIPTION
	"Dropping SIP requests that have been black-listed. Tracked by protected IP."
    ::= {ddossecureEvents 2811}

prBlockedProtocolSipOff NOTIFICATION-TYPE
    OBJECTS     { prHostName, prBlockedProtocol }
    STATUS	current
    DESCRIPTION
	"No longer Dropping SIP requests that have been black-listed."
    ::= {ddossecureEvents 2812}

prTcpAttackUrlRateLimitOn NOTIFICATION-TYPE
    OBJECTS     { prHostName, prTcpAttack }
    STATUS	current
    DESCRIPTION
	"Rate Limiting URL requests. Tracked by protected IP."
    ::= {ddossecureEvents 2821}

prTcpAttackUrlRateLimitOff NOTIFICATION-TYPE
    OBJECTS     { prHostName, prTcpAttack }
    STATUS	current
    DESCRIPTION
	"No longer Rate Limiting URL requests."
    ::= {ddossecureEvents 2822}

prUdpAttackDnsRateLimitOn NOTIFICATION-TYPE
    OBJECTS     { prHostName, prUdpAttack }
    STATUS	current
    DESCRIPTION
	"Rate Limiting DNS requests. Tracked by protected IP."
    ::= {ddossecureEvents 2831}

prUdpAttackDnsRateLimitOff NOTIFICATION-TYPE
    OBJECTS     { prHostName, prUdpAttack }
    STATUS	current
    DESCRIPTION
	"No longer Rate Limiting DNS requests."
    ::= {ddossecureEvents 2832}

prUdpAttackSipRateLimitOn NOTIFICATION-TYPE
    OBJECTS     { prHostName, prUdpAttack }
    STATUS	current
    DESCRIPTION
	"Rate Limiting SIP requests. Tracked by protected IP."
    ::= {ddossecureEvents 2841}

prUdpAttackSipRateLimitOff NOTIFICATION-TYPE
    OBJECTS     { prHostName, prUdpAttack }
    STATUS	current
    DESCRIPTION
	"No longer Rate Limiting SIP requests."
    ::= {ddossecureEvents 2842}

prBadTcpChecksumOn NOTIFICATION-TYPE
    OBJECTS     { prHostName, prBadTcp }
    STATUS	current
    DESCRIPTION
	"Dropping TCP packets that do not match RFCs. Invalid Checksum. Tracked by protected IP."
    ::= {ddossecureEvents 2851}

prBadTcpChecksumOff NOTIFICATION-TYPE
    OBJECTS     { prHostName, prBadTcp }
    STATUS	current
    DESCRIPTION
	"No longer Dropping TCP packets that do not match RFCs. Checksum now valid."
    ::= {ddossecureEvents 2852}

prTcpAttackHttpFormatOn NOTIFICATION-TYPE
    OBJECTS     { prHostName, prTcpAttack }
    STATUS	current
    DESCRIPTION
	"Dropping HTTP packets that do not match RFCs. Invalid Format. Tracked by protected IP."
    ::= {ddossecureEvents 2861}

prTcpAttackHttpFormatOff NOTIFICATION-TYPE
    OBJECTS     { prHostName, prBadTcp }
    STATUS	current
    DESCRIPTION
	"No longer Dropping HTTP packets that do not match RFCs. Format now valid."
    ::= {ddossecureEvents 2862}

prUnknownSessionReflectiveOn NOTIFICATION-TYPE
    OBJECTS     { prHostName, prBlockedState }
    STATUS	current
    DESCRIPTION
	"Dropping unknown traffic that is out of state. Tracked by protected IP."
    ::= {ddossecureEvents 2871}

prUnknownSessionReflectiveOff NOTIFICATION-TYPE
    OBJECTS     { prHostName, prBlockedState }
    STATUS	current
    DESCRIPTION
	"No longer Dropping unknown traffic that is out of state."
    ::= {ddossecureEvents 2872}


prBandwidthOn NOTIFICATION-TYPE
    OBJECTS     { prHostName, prBandwidth }
    STATUS	current
    DESCRIPTION
	"Rate limiting traffic by bandwidth. Tracked by protected IP / portal."
    ::= {ddossecureEvents 1011}

prBandwidthOff NOTIFICATION-TYPE
    OBJECTS     { prHostName, prBandwidth }
    STATUS	current
    DESCRIPTION
	"No longer rate limiting traffic by bandwidth."
    ::= {ddossecureEvents 1012}

prFloodOn NOTIFICATION-TYPE
    OBJECTS     { prHostName, prFlood }
    STATUS	current
    DESCRIPTION
	"Rate limiting traffic by packet rate."
    ::= {ddossecureEvents 1021}

prFloodOff NOTIFICATION-TYPE
    OBJECTS     { prHostName, prFlood }
    STATUS	current
    DESCRIPTION
	"No longer rate limiting traffic by packet rate."
    ::= {ddossecureEvents 1022}

prBlockedProtocolOn NOTIFICATION-TYPE
    OBJECTS     { prHostName, prBlockedProtocol }
    STATUS	current
    DESCRIPTION
	"Dropping traffic not expressly permitted. Tracked by protected IP."
    ::= {ddossecureEvents 1031}

prBlockedProtocolOff NOTIFICATION-TYPE
    OBJECTS     { prHostName, prBlockedProtocol }
    STATUS	current
    DESCRIPTION
	"No longer Dropping traffic not expressly permitted."
    ::= {ddossecureEvents 1032}

prBlockedStateOn NOTIFICATION-TYPE
    OBJECTS     { prHostName, prBlockedState }
    STATUS	current
    DESCRIPTION
	"Dropping TCP traffic that is out of state. Tracked by protected IP."
    ::= {ddossecureEvents 1041}

prBlockedStateOff NOTIFICATION-TYPE
    OBJECTS     { prHostName, prBlockedState }
    STATUS	current
    DESCRIPTION
	"No longer Dropping TCP traffic that is out of state."
    ::= {ddossecureEvents 1042}

prIpAttackOn NOTIFICATION-TYPE
    OBJECTS     { prHostName, prIpAttack }
    STATUS	current
    DESCRIPTION
	"Dropping IP packets causing stress. Tracked by protected IP."
    ::= {ddossecureEvents 1051}

prIpAttackOff NOTIFICATION-TYPE
    OBJECTS     { prHostName, prIpAttack }
    STATUS	current
    DESCRIPTION
	"No longer Dropping IP packets causing stress."
    ::= {ddossecureEvents 1052}

prTcpAttackOn NOTIFICATION-TYPE
    OBJECTS     { prHostName, prTcpAttack }
    STATUS	current
    DESCRIPTION
	"Dropping TCP packets causing stress. Tracked by protected IP."
    ::= {ddossecureEvents 1061}

prTcpAttackOff NOTIFICATION-TYPE
    OBJECTS     { prHostName, prTcpAttack }
    STATUS	current
    DESCRIPTION
	"No longer Dropping TCP packets causing stress."
    ::= {ddossecureEvents 1062}

prUdpAttackOn NOTIFICATION-TYPE
    OBJECTS     { prHostName, prUdpAttack }
    STATUS	current
    DESCRIPTION
	"Dropping UDP packets causing stress. Tracked by protected IP."
    ::= {ddossecureEvents 1071}

prUdpAttackOff NOTIFICATION-TYPE
    OBJECTS     { prHostName, prUdpAttack }
    STATUS	current
    DESCRIPTION
	"No longer Dropping UDP packets causing stress."
    ::= {ddossecureEvents 1072}

prIcmpAttackOn NOTIFICATION-TYPE
    OBJECTS     { prHostName, prIcmpAttack }
    STATUS	current
    DESCRIPTION
	"Dropping ICMP packets causing stress. Tracked by protected IP."
    ::= {ddossecureEvents 1081}

prIcmpAttackOff NOTIFICATION-TYPE
    OBJECTS     { prHostName, prIcmpAttack }
    STATUS	current
    DESCRIPTION
	"No longer Dropping ICMP packets causing stress. Tracked by protected IP."
    ::= {ddossecureEvents 1082}

prOtherIpAttackOn NOTIFICATION-TYPE
    OBJECTS     { prHostName, prOtherIpAttack }
    STATUS	current
    DESCRIPTION
	"Dropping Other IP packets causing stress. Tracked by protected IP."
    ::= {ddossecureEvents 1091}

prOtherIpAttackOff NOTIFICATION-TYPE
    OBJECTS     { prHostName, prOtherIpAttack }
    STATUS	current
    DESCRIPTION
	"No longer Dropping Other IP packets causing stress."
    ::= {ddossecureEvents 1092}

prFragAttackOn NOTIFICATION-TYPE
    OBJECTS     { prHostName, prFragAttack }
    STATUS	current
    DESCRIPTION
	"Dropping packet fragments that are causing stress. Tracked by protected IP."
    ::= {ddossecureEvents 1101}

prFragAttackOff NOTIFICATION-TYPE
    OBJECTS     { prHostName, prFragAttack }
    STATUS	current
    DESCRIPTION
	"No longer Dropping packet fragments that are causing stress. Tracked by protected IP."
    ::= {ddossecureEvents 1102}

prBadIpOn NOTIFICATION-TYPE
    OBJECTS     { prHostName, prBadIp }
    STATUS	current
    DESCRIPTION
	"Dropping IP packets that do not match RFCs. Tracked by protected IP."
    ::= {ddossecureEvents 1111}

prBadIpOff NOTIFICATION-TYPE
    OBJECTS     { prHostName, prBadIp }
    STATUS	current
    DESCRIPTION
	"No longer Dropping IP packets that do not match RFCs."
    ::= {ddossecureEvents 1112}

prBadTcpOn NOTIFICATION-TYPE
    OBJECTS     { prHostName, prBadTcp }
    STATUS	current
    DESCRIPTION
	"Dropping TCP Packets that do not match RFCs. Tracked by protected IP."
    ::= {ddossecureEvents 1121}

prBadTcpOff NOTIFICATION-TYPE
    OBJECTS     { prHostName, prBadTcp }
    STATUS	current
    DESCRIPTION
	"No longer Dropping TCP Packets that do not match RFCs. Tracked by protected IP."
    ::= {ddossecureEvents 1122}

prBadUdpOn NOTIFICATION-TYPE
    OBJECTS     { prHostName, prBadUdp }
    STATUS	current
    DESCRIPTION
	"Dropping UDP packets that do not match RFCs. Tracked by protected IP."
    ::= {ddossecureEvents 1131}

prBadUdpOff NOTIFICATION-TYPE
    OBJECTS     { prHostName, prBadUdp }
    STATUS	current
    DESCRIPTION
	"No longer Dropping UDP packets that do not match RFCs."
    ::= {ddossecureEvents 1132}

prBadIcmpOn NOTIFICATION-TYPE
    OBJECTS     { prHostName, prBadIcmp }
    STATUS	current
    DESCRIPTION
	"Dropping ICMP packets that do not match RFCs. Tracked by protected IP."
    ::= {ddossecureEvents 1141}

prBadIcmpOff NOTIFICATION-TYPE
    OBJECTS     { prHostName, prBadIcmp }
    STATUS	current
    DESCRIPTION
	"No longer Dropping ICMP packets that do not match RFCs."
    ::= {ddossecureEvents 1142}

prBadOtherIpOn NOTIFICATION-TYPE
    OBJECTS     { prHostName, prBadOtherIp }
    STATUS	current
    DESCRIPTION
	"Dropping Other IP packets that do not match RFCs. Tracked by protected IP."
    ::= {ddossecureEvents 1151}

prBadOtherIpOff NOTIFICATION-TYPE
    OBJECTS     { prHostName, prBadOtherIp }
    STATUS	current
    DESCRIPTION
	"No longer Dropping Other IP packets that do not match RFCs."
    ::= {ddossecureEvents 1152}

prOverloadedOn NOTIFICATION-TYPE
    OBJECTS     { prHostName, prOverloaded }
    STATUS	current
    DESCRIPTION
	"Detected overloaded protected IP. Tracked by protected IP."
    ::= {ddossecureEvents 1161}

prOverloadedOff NOTIFICATION-TYPE
    OBJECTS     { prHostName, prOverloaded }
    STATUS	current
    DESCRIPTION
	"No longer detected overloaded protected IP."
    ::= {ddossecureEvents 1162}

apHaStateMode NOTIFICATION-TYPE
    OBJECTS     { apHaState }
    STATUS	current
    DESCRIPTION
	"Current High Availability state."
    ::= {ddossecureEvents 2000}

apOutputErrorIIFlagOn NOTIFICATION-TYPE
    OBJECTS     { apOutputErrorIIFlag }
    STATUS	current
    DESCRIPTION
	"DDoS Secure is having trouble transmitting packets on the Internet Interface.  This could be because a downstream link is saturated, or a duplex speed mismatch."
    ::= {ddossecureEvents 3011}

apOutputErrorIIFlagOff NOTIFICATION-TYPE
    OBJECTS     { apOutputErrorIIFlag }
    STATUS	current
    DESCRIPTION
	"DDoS Secure has stopped having trouble transmitting packets on the Internet Interface."
    ::= {ddossecureEvents 3012}

apOutputErrorPIFlagOn NOTIFICATION-TYPE
    OBJECTS     { apOutputErrorPIFlag }
    STATUS	current
    DESCRIPTION
	"DDoS Secure is having trouble transmitting packets on the Protected Interface.  This could be because a downstream link is saturated, or a duplex speed mismatch."
    ::= {ddossecureEvents 3021}

apOutputErrorPIFlagOff NOTIFICATION-TYPE
    OBJECTS     { apOutputErrorPIFlag }
    STATUS	current
    DESCRIPTION
	"DDoS Secure has stopped having trouble transmitting packets on the Protected Interface."
    ::= {ddossecureEvents 3022}

apOutputErrorMIFlagOn NOTIFICATION-TYPE
    OBJECTS     { apOutputErrorMIFlag }
    STATUS	current
    DESCRIPTION
	"DDoS Secure is having trouble transmitting packets on the Management Interface.  This could be because a downstream link is saturated, or a duplex speed mismatch."
    ::= {ddossecureEvents 3031}

apOutputErrorMIFlagOff NOTIFICATION-TYPE
    OBJECTS     { apOutputErrorMIFlag }
    STATUS	current
    DESCRIPTION
	"DDoS Secure has stopped having trouble transmitting packets on the Management Interface."
    ::= {ddossecureEvents 3032}

apNewConfigFlagOn NOTIFICATION-TYPE
    OBJECTS     { apNewConfigFlag }
    STATUS	current
    DESCRIPTION
	"DDoS Secure is processing a new configuration."
    ::= {ddossecureEvents 3041}

apNewConfigFlagOff NOTIFICATION-TYPE
    OBJECTS     { apNewConfigFlag }
    STATUS	current
    DESCRIPTION
	"DDoS Secure has finished processing a new configuration."
    ::= {ddossecureEvents 3042}

apNotLicensedFlagOn NOTIFICATION-TYPE
    OBJECTS     { apNotLicensedFlag }
    STATUS	current
    DESCRIPTION
	"DDoS Secure is not licensed."
    ::= {ddossecureEvents 3051}

apNotLicensedFlagOff NOTIFICATION-TYPE
    OBJECTS     { apNotLicensedFlag }
    STATUS	current
    DESCRIPTION
	"DDoS Secure is now licensed."
    ::= {ddossecureEvents 3052}

apMacTableFullFlagOn NOTIFICATION-TYPE
    OBJECTS     { apMacTableFullFlag }
    STATUS	current
    DESCRIPTION
	"Mac Address table is full."
    ::= {ddossecureEvents 3061}

apMacTableFullFlagOff NOTIFICATION-TYPE
    OBJECTS     { apMacTableFullFlag }
    STATUS	current
    DESCRIPTION
	"Mac Address table is no longer full."
    ::= {ddossecureEvents 3062}

apProtectedTableFullFlagOn NOTIFICATION-TYPE
    OBJECTS     { apProtectedTableFullFlag }
    STATUS	current
    DESCRIPTION
	"protected IP table is full."
    ::= {ddossecureEvents 3071}

apProtectedTableFullFlagOff NOTIFICATION-TYPE
    OBJECTS     { apProtectedTableFullFlag }
    STATUS	current
    DESCRIPTION
	"protected IP table is no longer full."
    ::= {ddossecureEvents 3072}

apIncidentTableFullFlagOn NOTIFICATION-TYPE
    OBJECTS     { apIncidentTableFullFlag }
    STATUS	current
    DESCRIPTION
	"Incident table is full."
    ::= {ddossecureEvents 3081}

apIncidentTableFullFlagOff NOTIFICATION-TYPE
    OBJECTS     { apIncidentTableFullFlag }
    STATUS	current
    DESCRIPTION
	"Incident table is no longer full."
    ::= {ddossecureEvents 3082}

apTcpTableFullFlagOn NOTIFICATION-TYPE
    OBJECTS     { apTcpTableFullFlag }
    STATUS	current
    DESCRIPTION
	"TCP table is full."
    ::= {ddossecureEvents 3091}

apTcpTableFullFlagOff NOTIFICATION-TYPE
    OBJECTS     { apTcpTableFullFlag }
    STATUS	current
    DESCRIPTION
	"TCP table is no longer full."
    ::= {ddossecureEvents 3092}

apUdpTableFullFlagOn NOTIFICATION-TYPE
    OBJECTS     { apUdpTableFullFlag }
    STATUS	current
    DESCRIPTION
	"UDP table is full."
    ::= {ddossecureEvents 3101}

apUdpTableFullFlagOff NOTIFICATION-TYPE
    OBJECTS     { apUdpTableFullFlag }
    STATUS	current
    DESCRIPTION
	"UDP table is no longer full."
    ::= {ddossecureEvents 3102}

apIcmpTableFullFlagOn NOTIFICATION-TYPE
    OBJECTS     { apIcmpTableFullFlag }
    STATUS	current
    DESCRIPTION
	"ICMP table is full."
    ::= {ddossecureEvents 3111}

apIcmpTableFullFlagOff NOTIFICATION-TYPE
    OBJECTS     { apIcmpTableFullFlag }
    STATUS	current
    DESCRIPTION
	"ICMP table is no longer full."
    ::= {ddossecureEvents 3112}

apOtherIpTableFullFlagOn NOTIFICATION-TYPE
    OBJECTS     { apOtherIpTableFullFlag }
    STATUS	current
    DESCRIPTION
	"Other IP table is full."
    ::= {ddossecureEvents 3121}

apOtherIpTableFullFlagOff NOTIFICATION-TYPE
    OBJECTS     { apOtherIpTableFullFlag }
    STATUS	current
    DESCRIPTION
	"Other IP table is no longer full."
    ::= {ddossecureEvents 3122}

apFragTableFullFlagOn NOTIFICATION-TYPE
    OBJECTS     { apFragTableFullFlag }
    STATUS	current
    DESCRIPTION
	"Fragment table is full."
    ::= {ddossecureEvents 3131}

apFragTableFullFlagOff NOTIFICATION-TYPE
    OBJECTS     { apFragTableFullFlag }
    STATUS	current
    DESCRIPTION
	"Fragment table is no longer full."
    ::= {ddossecureEvents 3132}

apFtpTableFullFlagOn NOTIFICATION-TYPE
    OBJECTS     { apFtpTableFullFlag }
    STATUS	current
    DESCRIPTION
	"FTP ftp table is full."
    ::= {ddossecureEvents 3141}

apFtpTableFullFlagOff NOTIFICATION-TYPE
    OBJECTS     { apFtpTableFullFlag }
    STATUS	current
    DESCRIPTION
	"FTP ftp table is no longer full."
    ::= {ddossecureEvents 3142}

apBlockedTableFullFlagOn NOTIFICATION-TYPE
    OBJECTS     { apBlockedTableFullFlag }
    STATUS	current
    DESCRIPTION
	"Blocked IP table is full."
    ::= {ddossecureEvents 3151}

apBlockedTableFullFlagOff NOTIFICATION-TYPE
    OBJECTS     { apBlockedTableFullFlag }
    STATUS	current
    DESCRIPTION
	"Blocked IP table is no longer full."
    ::= {ddossecureEvents 3152}

apShortCircuitFlagOn NOTIFICATION-TYPE
    OBJECTS     { apShortCircuitFlag }
    STATUS	current
    DESCRIPTION
	"Traffic is bypassing DDoS Secure (Source MAC address is seen on both sides of the DDoS Secure)."
    ::= {ddossecureEvents 3161}

apShortCircuitFlagOff NOTIFICATION-TYPE
    OBJECTS     { apShortCircuitFlag }
    STATUS	current
    DESCRIPTION
	"Traffic is no longer bypassing DDoS Secure."
    ::= {ddossecureEvents 3162}

apInternetIfDisconnectedFlagOn NOTIFICATION-TYPE
    OBJECTS     { apInternetIfDisconnectedFlag }
    STATUS	current
    DESCRIPTION
	"Internet interface is not connected."
    ::= {ddossecureEvents 3171}

apInternetIfDisconnectedFlagOff NOTIFICATION-TYPE
    OBJECTS     { apInternetIfDisconnectedFlag }
    STATUS	current
    DESCRIPTION
	"Internet interface is now connected."
    ::= {ddossecureEvents 3172}

apProtectedIfDisconnectedFlagOn NOTIFICATION-TYPE
    OBJECTS     { apProtectedIfDisconnectedFlag }
    STATUS	current
    DESCRIPTION
	"Protected Interface is not connected."
    ::= {ddossecureEvents 3181}

apProtectedIfDisconnectedFlagOff NOTIFICATION-TYPE
    OBJECTS     { apProtectedIfDisconnectedFlag }
    STATUS	current
    DESCRIPTION
	"Protected Interface is now connected."
    ::= {ddossecureEvents 3182}

apMgmtIfDisconnectedFlagOn NOTIFICATION-TYPE
    OBJECTS     { apMgmtIfDisconnectedFlag }
    STATUS	current
    DESCRIPTION
	"Management interface is not connected."
    ::= {ddossecureEvents 3191}

apMgmtIfDisconnectedFlagOff NOTIFICATION-TYPE
    OBJECTS     { apMgmtIfDisconnectedFlag }
    STATUS	current
    DESCRIPTION
	"Management interface is now connected."
    ::= {ddossecureEvents 3192}

apUpgradingFlagOn NOTIFICATION-TYPE
    OBJECTS     { apUpgradingFlag }
    STATUS	current
    DESCRIPTION
	"DDoS Secure software is being upgraded."
    ::= {ddossecureEvents 3201}

apUpgradingFlagOff NOTIFICATION-TYPE
    OBJECTS     { apUpgradingFlag }
    STATUS	current
    DESCRIPTION
	"DDoS Secure software upgrade finished."
    ::= {ddossecureEvents 3202}

apProtectedIfTrafficFlagOn NOTIFICATION-TYPE
    OBJECTS     { apProtectedIfTrafficFlag }
    STATUS	current
    DESCRIPTION
	"Unexpected traffic seen on Protected Interface in TAP mode."
    ::= {ddossecureEvents 3211}

apProtectedIfTrafficFlagOff NOTIFICATION-TYPE
    OBJECTS     { apProtectedIfTrafficFlag }
    STATUS	current
    DESCRIPTION
	"Unexpected traffic no longer seen on Protected Interface in TAP mode."
    ::= {ddossecureEvents 3212}

apRoutingLoopFlagOn NOTIFICATION-TYPE
    OBJECTS     { apRoutingLoopFlag }
    STATUS	current
    DESCRIPTION
	"Routing Loop detected."
    ::= {ddossecureEvents 3221}

apRoutingLoopFlagOff NOTIFICATION-TYPE
    OBJECTS     { apRoutingLoopFlag }
    STATUS	current
    DESCRIPTION
	"Routing Loop no longer detected."
    ::= {ddossecureEvents 3222}

apOfflineFlagOn NOTIFICATION-TYPE
    OBJECTS     { apOfflineFlag }
    STATUS	current
    DESCRIPTION
	"DDoS Secure is Offline."
    ::= {ddossecureEvents 3231}

apOfflineFlagOff NOTIFICATION-TYPE
    OBJECTS     { apOfflineFlag }
    STATUS	current
    DESCRIPTION
	"DDoS Secure is no longer Offline."
    ::= {ddossecureEvents 3232}

apStateLearningFlagOn NOTIFICATION-TYPE
    OBJECTS     { apStateLearningFlag }
    STATUS	current
    DESCRIPTION
	"DDoS Secure is in State learning phase."
    ::= {ddossecureEvents 3241}

apStateLearningFlagOff NOTIFICATION-TYPE
    OBJECTS     { apStateLearningFlag }
    STATUS	current
    DESCRIPTION
	"DDoS Secure is no longer in State learning phase."
    ::= {ddossecureEvents 3242}

apSupportExpiredFlagOn NOTIFICATION-TYPE
    OBJECTS     { apSupportExpiredFlag }
    STATUS	current
    DESCRIPTION
	"Support License has expired."
    ::= {ddossecureEvents 3251}

apSupportExpiredFlagOff NOTIFICATION-TYPE
    OBJECTS     { apSupportExpiredFlag }
    STATUS	current
    DESCRIPTION
	"Support License is now valid."
    ::= {ddossecureEvents 3252}

apSevereLoadingFlagOn NOTIFICATION-TYPE
    OBJECTS     { apSevereLoadingFlag }
    STATUS	current
    DESCRIPTION
	"Appliance is severely loaded."
    ::= {ddossecureEvents 3261}

apSevereLoadingFlagOff NOTIFICATION-TYPE
    OBJECTS     { apSevereLoadingFlag }
    STATUS	current
    DESCRIPTION
	"Appliance is no longer severely loaded."
    ::= {ddossecureEvents 3262}

apMacMisconfiguredFlagOn NOTIFICATION-TYPE
    OBJECTS     { apMacMisconfiguredFlag }
    STATUS	current
    DESCRIPTION
	"MAC address is configured for one side of the DDoS Secure, but seen on the other side."
    ::= {ddossecureEvents 3271}

apMacMisconfiguredFlagOff NOTIFICATION-TYPE
    OBJECTS     { apMacMisconfiguredFlag }
    STATUS	current
    DESCRIPTION
	"No MACaddresses misconfigured."
    ::= {ddossecureEvents 3272}

apIfMisconfiguredFlagOn NOTIFICATION-TYPE
    OBJECTS     { apIfMisconfiguredFlag }
    STATUS	current
    DESCRIPTION
	"Protected and Internet speeds are not configured identically.  Bypass cards only."
    ::= {ddossecureEvents 3281}

apIfMisconfiguredFlagOff NOTIFICATION-TYPE
    OBJECTS     { apIfMisconfiguredFlag }
    STATUS	current
    DESCRIPTION
	"Protected and Internet speeds are configured identically.  Bypass cards only."
    ::= {ddossecureEvents 3282}

apInternetIfLinkDownFlagOn NOTIFICATION-TYPE
    OBJECTS     { apInternetIfLinkDownFlag }
    STATUS	current
    DESCRIPTION
	"One or more Internet sub-links are down."
    ::= {ddossecureEvents 3291}

apInternetIfLinkDownFlagOff NOTIFICATION-TYPE
    OBJECTS     { apInternetIfLinkDownFlag }
    STATUS	current
    DESCRIPTION
	"All Internet sub-links are up."
    ::= {ddossecureEvents 3292}

apProtectedIfLinkDownFlagOn NOTIFICATION-TYPE
    OBJECTS     { apProtectedIfLinkDownFlag }
    STATUS	current
    DESCRIPTION
	"One or more Protected sub-links are down."
    ::= {ddossecureEvents 3301}

apProtectedIfLinkDownFlagOff NOTIFICATION-TYPE
    OBJECTS     { apProtectedIfLinkDownFlag }
    STATUS	current
    DESCRIPTION
	"All Protected sub-links are up."
    ::= {ddossecureEvents 3302}

apDatashareIfDisconnectedFlagOn NOTIFICATION-TYPE
    OBJECTS     { apDatashareIfDisconnectedFlag }
    STATUS	current
    DESCRIPTION
	"Data Share interface is not connected."
    ::= {ddossecureEvents 3311}

apDatashareIfDisconnectedFlagOff NOTIFICATION-TYPE
    OBJECTS     { apDatashareIfDisconnectedFlag }
    STATUS	current
    DESCRIPTION
	"Data Share interface is now connected."
    ::= {ddossecureEvents 3312}

apDiskFailingOn NOTIFICATION-TYPE
    OBJECTS     { apDiskFailingFlag }
    STATUS	current
    DESCRIPTION
	"A disk is failing."
    ::= {ddossecureEvents 3321}

apDiskFailingOff NOTIFICATION-TYPE
    OBJECTS     { apDiskFailingFlag }
    STATUS	current
    DESCRIPTION
	"Disk failure no longer detected."
    ::= {ddossecureEvents 3322}

apPsuFailingFlagOn NOTIFICATION-TYPE
    OBJECTS     { apPsuFailingFlag }
    STATUS	current
    DESCRIPTION
	"A Power Supply Unit is failing."
    ::= {ddossecureEvents 3331}

apPsuFailingFlagOff NOTIFICATION-TYPE
    OBJECTS     { apPsuFailingFlag }
    STATUS	current
    DESCRIPTION
	"A Power Supply Unit is no longer failing."
    ::= {ddossecureEvents 3332}

apFanFailingFlagOn NOTIFICATION-TYPE
    OBJECTS     { apFanFailingFlag }
    STATUS	current
    DESCRIPTION
	"A Fan is failing."
    ::= {ddossecureEvents 3341}

apFanFailingFlagOff NOTIFICATION-TYPE
    OBJECTS     { apFanFailingFlag }
    STATUS	current
    DESCRIPTION
	"A Fan is no longer failing."
    ::= {ddossecureEvents 3342}

apConfigXferFailFlagOn NOTIFICATION-TYPE
    OBJECTS     { apConfigXferFailFlag }
    STATUS	current
    DESCRIPTION
	"Configuration Transfer failed."
    ::= {ddossecureEvents 3351}

apConfigXferFailFlagOff NOTIFICATION-TYPE
    OBJECTS     { apConfigXferFailFlag }
    STATUS	current
    DESCRIPTION
	"Configuration Transfer failed report finished."
    ::= {ddossecureEvents 3352}

apMissingRequiredPartnerFlagOn NOTIFICATION-TYPE
    OBJECTS     { apMissingRequiredPartnerFlag }
    STATUS	current
    DESCRIPTION
	"Missing Required Partner found."
    ::= {ddossecureEvents 3361}

apMissingRequiredPartnerFlagOff NOTIFICATION-TYPE
    OBJECTS     { apMissingRequiredPartnerFlag }
    STATUS	current
    DESCRIPTION
	"All Required Partners active."
    ::= {ddossecureEvents 3362}

apBgpMisconfiguredIpFlagOn NOTIFICATION-TYPE
    OBJECTS     { apBgpMisconfiguredIpFlag }
    STATUS	current
    DESCRIPTION
        "BGP traffic detected to undefined protected IP"
    ::= {ddossecureEvents 3371}

apBgpMisconfiguredIpFlagOff NOTIFICATION-TYPE
    OBJECTS     { apBgpMisconfiguredIpFlag }
    STATUS	current
    DESCRIPTION
        "BGP traffic no longer detected to undefined protected IP"
    ::= {ddossecureEvents 3372}


-- Old definitions

apOutputErrorIIEvent NOTIFICATION-TYPE
    OBJECTS     { apOutputErrorIIFlag }
    STATUS	deprecated
    DESCRIPTION
	"DDoS Secure is having trouble transmitting packets on the Internet Interface.  This could be because a downstream link is saturated, or a duplex speed mismatch."
    ::= {ddossecureEvents 1}

apOutputErrorPIEvent NOTIFICATION-TYPE
    OBJECTS     { apOutputErrorPIFlag }
    STATUS	deprecated
    DESCRIPTION
	"DDoS Secure is having trouble transmitting packets on the Protected Interface.  This could be because a downstream link is saturated, or a duplex speed mismatch."
    ::= {ddossecureEvents 2}

apOutputErrorMIEvent NOTIFICATION-TYPE
    OBJECTS     { apOutputErrorMIFlag }
    STATUS	deprecated
    DESCRIPTION
	"DDoS Secure is having trouble transmitting packets on the Management Interface.  This could be because a downstream link is saturated, or a duplex speed mismatch."
    ::= {ddossecureEvents 3}

apNewConfigEvent NOTIFICATION-TYPE
    OBJECTS     { apNewConfigFlag }
    STATUS	deprecated
    DESCRIPTION
	"DDoS Secure is processing a new configuration"
    ::= {ddossecureEvents 4}

apNotLicensedEvent NOTIFICATION-TYPE
    OBJECTS     { apNotLicensedFlag }
    STATUS	deprecated
    DESCRIPTION
	"DDoS Secure is not licensed"
    ::= {ddossecureEvents 5}

apMacTableFullEvent NOTIFICATION-TYPE
    OBJECTS     { apMacTableFullFlag }
    STATUS	deprecated
    DESCRIPTION
	"Mac Address table is full"
    ::= {ddossecureEvents 6}

apProtectedTableFullEvent NOTIFICATION-TYPE
    OBJECTS     { apProtectedTableFullFlag }
    STATUS	deprecated
    DESCRIPTION
	"Protected IP table is full"
    ::= {ddossecureEvents 7}

apIncidentTableFullEvent NOTIFICATION-TYPE
    OBJECTS     { apIncidentTableFullFlag }
    STATUS	deprecated
    DESCRIPTION
	"Incident table is full"
    ::= {ddossecureEvents 8}

apTcpTableFullEvent NOTIFICATION-TYPE
    OBJECTS     { apTcpTableFullFlag }
    STATUS	deprecated
    DESCRIPTION
	"TCP table is full"
    ::= {ddossecureEvents 9}

apUdpTableFullEvent NOTIFICATION-TYPE
    OBJECTS     { apUdpTableFullFlag }
    STATUS	deprecated
    DESCRIPTION
	"UDP table is full"
    ::= {ddossecureEvents 10}

apIcmpTableFullEvent NOTIFICATION-TYPE
    OBJECTS     { apIcmpTableFullFlag }
    STATUS	deprecated
    DESCRIPTION
	"ICMP table is full"
    ::= {ddossecureEvents 11}

apOtherIpTableFullEvent NOTIFICATION-TYPE
    OBJECTS     { apOtherIpTableFullFlag }
    STATUS	deprecated
    DESCRIPTION
	"Other IP table is full"
    ::= {ddossecureEvents 12}

apFragTableFullEvent NOTIFICATION-TYPE
    OBJECTS     { apFragTableFullFlag }
    STATUS	deprecated
    DESCRIPTION
	"Fragment table is full"
    ::= {ddossecureEvents 13}

apFtpTableFullEvent NOTIFICATION-TYPE
    OBJECTS     { apFtpTableFullFlag }
    STATUS	deprecated
    DESCRIPTION
	"FTP ftp table is full"
    ::= {ddossecureEvents 14}

apBlockedTableFullEvent NOTIFICATION-TYPE
    OBJECTS     { apBlockedTableFullFlag }
    STATUS	deprecated
    DESCRIPTION
	"Blocked IP table is full"
    ::= {ddossecureEvents 15}

apShortCircuitEvent NOTIFICATION-TYPE
    OBJECTS     { apShortCircuitFlag }
    STATUS	deprecated
    DESCRIPTION
	"Seeing same source MAC address both sides of the DDoS Secure"
    ::= {ddossecureEvents 16}

apInternetIfDisconnectedEvent NOTIFICATION-TYPE
    OBJECTS     { apInternetIfDisconnectedFlag }
    STATUS	deprecated
    DESCRIPTION
	"Internet interface is not connected"
    ::= {ddossecureEvents 17}

apProtectedIfDisconnectedEvent NOTIFICATION-TYPE
    OBJECTS     { apProtectedIfDisconnectedFlag }
    STATUS	deprecated
    DESCRIPTION
	"Protected Interface is not connected"
    ::= {ddossecureEvents 18}

apMgmtIfDisconnectedEvent NOTIFICATION-TYPE
    OBJECTS     { apMgmtIfDisconnectedFlag }
    STATUS	deprecated
    DESCRIPTION
	"Management interface is not connected"
    ::= {ddossecureEvents 19}

apUpgradingEvent NOTIFICATION-TYPE
    OBJECTS     { apUpgradingFlag }
    STATUS	deprecated
    DESCRIPTION
	"DDoS Secure software is being upgraded"
    ::= {ddossecureEvents 20}

apProtectedIfTrafficEvent NOTIFICATION-TYPE
    OBJECTS     { apProtectedIfTrafficFlag }
    STATUS	deprecated
    DESCRIPTION
	"Unexpected traffic seen on Protected Interface in TAP mode"
    ::= {ddossecureEvents 21}

apRoutingLoopEvent NOTIFICATION-TYPE
    OBJECTS     { apRoutingLoopFlag }
    STATUS	deprecated
    DESCRIPTION
	"Routing Loop detected"
    ::= {ddossecureEvents 22}

apOfflineEvent NOTIFICATION-TYPE
    OBJECTS     { apOfflineFlag }
    STATUS	deprecated
    DESCRIPTION
	"DDoS Secure is Offline"
    ::= {ddossecureEvents 23}

apStateLearningEvent NOTIFICATION-TYPE
    OBJECTS     { apStateLearningFlag }
    STATUS	deprecated
    DESCRIPTION
	"DDoS Secure is State learning"
    ::= {ddossecureEvents 24}

apSupportExpiredEvent NOTIFICATION-TYPE
    OBJECTS     { apSupportExpiredFlag }
    STATUS	deprecated
    DESCRIPTION
	"Support License has expired"
    ::= {ddossecureEvents 25}

apSevereLoadingEvent NOTIFICATION-TYPE
    OBJECTS     { apSevereLoadingFlag }
    STATUS	deprecated
    DESCRIPTION
	"Appliance is severely loaded"
    ::= {ddossecureEvents 26}

apMacMisconfiguredEvent NOTIFICATION-TYPE
    OBJECTS     { apMacMisconfiguredFlag }
    STATUS	deprecated
    DESCRIPTION
	"MAC address configured for wrong side of DDoS Secure"
    ::= {ddossecureEvents 27}

apIfMisconfiguredEvent NOTIFICATION-TYPE
    OBJECTS     { apIfMisconfiguredFlag }
    STATUS	deprecated
    DESCRIPTION
	"Protected / Internet interface speed mismatch"
    ::= {ddossecureEvents 28}

apInternetIfLinkDownEvent NOTIFICATION-TYPE
    OBJECTS     { apInternetIfLinkDownFlag }
    STATUS	deprecated
    DESCRIPTION
	"One or more Internet sub-links are down"
    ::= {ddossecureEvents 29}

apProtectedIfLinkDownEvent NOTIFICATION-TYPE
    OBJECTS     { apProtectedIfLinkDownFlag }
    STATUS	deprecated
    DESCRIPTION
	"One or more Protected sub-links are down"
    ::= {ddossecureEvents 30}

apDatashareIfDisconnectedEvent NOTIFICATION-TYPE
    OBJECTS     { apDatashareIfDisconnectedFlag }
    STATUS	deprecated
    DESCRIPTION
	"Data Share interface is not connected"
    ::= {ddossecureEvents 31}

apHaStateEvent NOTIFICATION-TYPE
    OBJECTS     { apHaState }
    STATUS	deprecated
    DESCRIPTION
	"Current High Availability state"
    ::= {ddossecureEvents 35}

prBandwidthEvent NOTIFICATION-TYPE
    OBJECTS     { prBandwidth }
    STATUS	deprecated
    DESCRIPTION
	"Rate limiting traffic by bandwidth"
    ::= {ddossecureEvents 40}

prFloodEvent NOTIFICATION-TYPE
    OBJECTS     { prFlood }
    STATUS	deprecated
    DESCRIPTION
	"Rate limiting traffic by packet rate"
    ::= {ddossecureEvents 41}

prBlockedProtocolEvent NOTIFICATION-TYPE
    OBJECTS     { prBlockedProtocol }
    STATUS	deprecated
    DESCRIPTION
	"Dropping traffic not expressly permitted"
    ::= {ddossecureEvents 42}

prBlockedStateEvent NOTIFICATION-TYPE
    OBJECTS     { prBlockedState }
    STATUS	deprecated
    DESCRIPTION
	"Dropping TCP traffic that is out of state"
    ::= {ddossecureEvents 43}

prIpAttackEvent NOTIFICATION-TYPE
    OBJECTS     { prIpAttack }
    STATUS	deprecated
    DESCRIPTION
	"Dropping IP packets causing stress"
    ::= {ddossecureEvents 44}

prTcpAttackEvent NOTIFICATION-TYPE
    OBJECTS     { prTcpAttack }
    STATUS	deprecated
    DESCRIPTION
	"Dropping TCP packets causing stress"
    ::= {ddossecureEvents 45}

prUdpAttackEvent NOTIFICATION-TYPE
    OBJECTS     { prUdpAttack }
    STATUS	deprecated
    DESCRIPTION
	"Dropping UDP packets causing stress"
    ::= {ddossecureEvents 46}

prIcmpAttackEvent NOTIFICATION-TYPE
    OBJECTS     { prIcmpAttack }
    STATUS	deprecated
    DESCRIPTION
	"Dropping ICMP packets causing stress"
    ::= {ddossecureEvents 47}

prOtherIpAttackEvent NOTIFICATION-TYPE
    OBJECTS     { prOtherIpAttack }
    STATUS	deprecated
    DESCRIPTION
	"Dropping Other IP packets causing stress"
    ::= {ddossecureEvents 48}

prFragAttackEvent NOTIFICATION-TYPE
    OBJECTS     { prFragAttack }
    STATUS	deprecated
    DESCRIPTION
	"Dropping packet fragments that are causing stress"
    ::= {ddossecureEvents 49}

prBadIpEvent NOTIFICATION-TYPE
    OBJECTS     { prBadIp }
    STATUS	deprecated
    DESCRIPTION
	"Dropping IP packets that do not match RFCs"
    ::= {ddossecureEvents 50}

prBadTcpEvent NOTIFICATION-TYPE
    OBJECTS     { prBadTcp }
    STATUS	deprecated
    DESCRIPTION
	"Dropping TCP Packets that do not match RFCs"
    ::= {ddossecureEvents 51}

prBadUdpEvent NOTIFICATION-TYPE
    OBJECTS     { prBadUdp }
    STATUS	deprecated
    DESCRIPTION
	"Dropping UDP packets that do not match RFCs"
    ::= {ddossecureEvents 52}

prBadIcmpEvent NOTIFICATION-TYPE
    OBJECTS     { prBadIcmp }
    STATUS	deprecated
    DESCRIPTION
	"Dropping ICMP packets that do not match RFCs"
    ::= {ddossecureEvents 53}

prBadOtherIpEvent NOTIFICATION-TYPE
    OBJECTS     { prBadOtherIp }
    STATUS	deprecated
    DESCRIPTION
	"Dropping Other IP packets that do not match RFCs"
    ::= {ddossecureEvents 54}

prOverloadedEvent NOTIFICATION-TYPE
    OBJECTS     { prOverloaded }
    STATUS	deprecated
    DESCRIPTION
	"Detected overloaded protected IP"
    ::= {ddossecureEvents 55}

-- Conformance information

   ddossecure4MIBConformance OBJECT IDENTIFIER ::= { ddossecure4MIB 9 }

   ddossecure4MIBCompliances OBJECT IDENTIFIER ::= { ddossecure4MIBConformance 1 }
   ddossecure4MIBGroups      OBJECT IDENTIFIER ::= { ddossecure4MIBConformance 2 }


   ddossecure4MIBCompliance MODULE-COMPLIANCE

   STATUS current
   DESCRIPTION "Compliance Statement"
   MODULE
   MANDATORY-GROUPS {
	apCfgGroup,
	gwGroup,
	apIncidentGroup,
	apDebugGroup,
	apGroup,
	poGroup,
	prGroup,
	prCfgGroup,
	gwCfgGroup,
	apEventObjectGroup,
	apRatesGroup,
	poFilterCfgGroup,
	apLinkStatusGroup,
	apLogGroup,
	apHaCfgGroup,
	prNotificationGroup
   }

   ::= { ddossecure4MIBCompliances 1 }

   ddossecure4MIBComplianceDep MODULE-COMPLIANCE

   STATUS deprecated
   DESCRIPTION "Compliance Statement"
   MODULE
   MANDATORY-GROUPS {
	deprecatedNotificationGroup
   }

   ::= { ddossecure4MIBCompliances 2 }


-- units of conformance

apCfgGroup OBJECT-GROUP
    OBJECTS {
	apMgmtIfIpAddress,
	apMgmtIfNetmask,
	apMgmtIfGwIpAddress,
	apMgmtIfLinkMode,
	apMgmtIfLinkFC,
	apMgmtIfName,
	apIntIfLinkMode,
	apIntIfLinkFC,
	apIntIfName,
	apProtIfLinkMode,
	apProtIfLinkFC,
	apProtIfName,
	apDataIfIpAddress,
	apDataIfNetmask,
	apDataIfLinkMode,
	apDataIfLinkFC,
	apDataIfName,
	apUserName,
	apUserPermissions,
	apSnmpRoCommunity,
	apSnmpTrapCommunity,
	apSnmpTrapIpAddressList,
	apSnmpAccessIpList,
	apHttpsAccessIpList,
	apSshAccessIpList,
	apSyslogServer,
	apSyslogFacility,
	apSyslogPriority,
	apWebtrendsServer,
	apWebtrendsFacility,
	apWebtrendsPriority,
	apMailServer,
	apMailFrom,
	apMailSubject,
	apMailToList,
	apMailDailyStats,
	apMailAlerts,
	apMailAlertInterval,
	apOperationMode,
	apNtpServerList,
	apTimeZone,
	apProtectedIpNetwork,
	apAutoblockEnable,
	apAutoblockRateT1,
	apProtectedIpAutodetect,
	apTrackIndeterminate,
	apAutoblockRateT2
    }
    STATUS current
    DESCRIPTION "Appliance Configuration Group."
    ::= { ddossecure4MIBGroups 1 }

gwGroup OBJECT-GROUP
    OBJECTS {
	gwInternetMacAddress,
	gwInternetIpAddress,
	gwInternetInTotalBytesCnt,
	gwInternetOutTotalBytesCnt,
	gwInternetInDroppedBytesCnt,
	gwInternetOutDroppedBytesCnt,
	gwInternetInTotalPpsMax,
	gwInternetOutTotalPpsMax,
	gwInternetInDroppedPpsMax,
	gwInternetOutDroppedPpsMax,
	gwInternetInTotalBpsMax,
	gwInternetOutTotalBpsMax,
	gwInternetInDroppedBpsMax,
	gwInternetOutDroppedBpsMax,
	gwProtectedMacAddress,
	gwProtectedIpAddress,
	gwProtectedInTotalBytesCnt,
	gwProtectedOutTotalBytesCnt,
	gwProtectedInDroppedBytesCnt,
	gwProtectedOutDroppedBytesCnt,
	gwProtectedInTotalPpsMax,
	gwProtectedOutTotalPpsMax,
	gwProtectedInDroppedPpsMax,
	gwProtectedOutDroppedPpsMax,
	gwProtectedInTotalBpsMax,
	gwProtectedOutTotalBpsMax,
	gwProtectedInDroppedBpsMax,
	gwProtectedOutDroppedBpsMax
    }
    STATUS current
    DESCRIPTION "Gateway Statistics Group."
    ::= { ddossecure4MIBGroups 2 }

apIncidentGroup OBJECT-GROUP
    OBJECTS {
	apBandwidthCreateThresh,
	apBandwidthCreateThreshRate,
	apFloodCreateThresh,
	apFloodCreateThreshRate,
	apBlockedProtoCreateThresh,
	apBlockedProtoCreateThreshRate,
	apBlockedStateCreateThresh,
	apBlockedStateCreateThreshRate,
	apIpAttackCreateThresh,
	apIpAttackCreateThreshRate,
	apTcpAttackCreateThresh,
	apTcpAttackCreateThreshRate,
	apUdpAttackCreateThresh,
	apUdpAttackCreateThreshRate,
	apIcmpAttackCreateThresh,
	apIcmpAttackCreateThreshRate,
	apOtherIpAttackCreateThresh,
	apOtherIpAttackCreateThreshRate,
	apFragAttackCreateThresh,
	apFragAttackCreateThreshRate,
	apBadIpCreateThresh,
	apBadIpCreateThreshRate,
	apBadTcpCreateThresh,
	apBadTcpCreateThreshRate,
	apBadUdpCreateThresh,
	apBadUdpCreateThreshRate,
	apBadIcmpCreateThresh,
	apBadIcmpCreateThreshRate,
	apBadOtherIpCreateThresh,
	apBadOtherIpCreateThreshRate,
	apOverloadedIpCreateThresh,
	apOverloadedIpCreateThreshRate,
	apBandwidthViewThresh,
	apBandwidthViewThreshRate,
	apFloodViewThresh,
	apFloodViewThreshRate,
	apBlockedProtoViewThresh,
	apBlockedProtoViewThreshRate,
	apBlockedStateViewThresh,
	apBlockedStateViewThreshRate,
	apIpAttackViewThresh,
	apIpAttackViewThreshRate,
	apTcpAttackViewThresh,
	apTcpAttackViewThreshRate,
	apUdpAttackViewThresh,
	apUdpAttackViewThreshRate,
	apIcmpAttackViewThresh,
	apIcmpAttackViewThreshRate,
	apOtherIpAttackViewThresh,
	apOtherIpAttackViewThreshRate,
	apFragAttackViewThresh,
	apFragAttackViewThreshRate,
	apBadIpViewThresh,
	apBadIpViewThreshRate,
	apBadTcpViewThresh,
	apBadTcpViewThreshRate,
	apBadUdpViewThresh,
	apBadUdpViewThreshRate,
	apBadIcmpViewThresh,
	apBadIcmpViewThreshRate,
	apBadOtherIpViewThresh,
	apBadOtherIpViewThreshRate,
	apOverloadedIpViewThresh,
	apOverloadedIpViewThreshRate,
	apBandwidthOffThresh,
	apBandwidthOffThreshRate,
	apFloodOffThresh,
	apFloodOffThreshRate,
	apBlockedProtoOffThresh,
	apBlockedProtoOffThreshRate,
	apBlockedStateOffThresh,
	apBlockedStateOffThreshRate,
	apIpAttackOffThresh,
	apIpAttackOffThreshRate,
	apTcpAttackOffThresh,
	apTcpAttackOffThreshRate,
	apUdpAttackOffThresh,
	apUdpAttackOffThreshRate,
	apIcmpAttackOffThresh,
	apIcmpAttackOffThreshRate,
	apOtherIpAttackOffThresh,
	apOtherIpAttackOffThreshRate,
	apFragAttackOffThresh,
	apFragAttackOffThreshRate,
	apBadIpOffThresh,
	apBadIpOffThreshRate,
	apBadTcpOffThresh,
	apBadTcpOffThreshRate,
	apBadUdpOffThresh,
	apBadUdpOffThreshRate,
	apBadIcmpOffThresh,
	apBadIcmpOffThreshRate,
	apBadOtherIpOffThresh,
	apBadOtherIpOffThreshRate,
	apOverloadedIpOffThresh,
	apOverloadedIpOffThreshRate,
	apBandwidthAlertThresh,
	apBandwidthAlertThreshRate,
	apFloodAlertThresh,
	apFloodAlertThreshRate,
	apBlockedProtoAlertThresh,
	apBlockedProtoAlertThreshRate,
	apBlockedStateAlertThresh,
	apBlockedStateAlertThreshRate,
	apIpAttackAlertThresh,
	apIpAttackAlertThreshRate,
	apTcpAttackAlertThresh,
	apTcpAttackAlertThreshRate,
	apUdpAttackAlertThresh,
	apUdpAttackAlertThreshRate,
	apIcmpAttackAlertThresh,
	apIcmpAttackAlertThreshRate,
	apOtherIpAttackAlertThresh,
	apOtherIpAttackAlertThreshRate,
	apFragAttackAlertThresh,
	apFragAttackAlertThreshRate,
	apBadIpAlertThresh,
	apBadIpAlertThreshRate,
	apBadTcpAlertThresh,
	apBadTcpAlertThreshRate,
	apBadUdpAlertThresh,
	apBadUdpAlertThreshRate,
	apBadIcmpAlertThresh,
	apBadIcmpAlertThreshRate,
	apBadOtherIpAlertThresh,
	apBadOtherIpAlertThreshRate,
	apOverloadedIpAlertThresh,
	apOverloadedIpAlertThreshRate
    }
    STATUS current
    DESCRIPTION "Appliance Threshold Configuration Group."
    ::= { ddossecure4MIBGroups 3 }

apDebugGroup OBJECT-GROUP
    OBJECTS {
	apDebugBandwidthFlag,
	apDebugFloodFlag,
	apDebugBlockedProtocolFlag,
	apDebugBlockedStateFlag,
	apDebugIpAttackFlag,
	apDebugTcpAttackFlag,
	apDebugUdpAttackFlag,
	apDebugIcmpAttackFlag,
	apDebugOtherIpAttackFlag,
	apDebugFragmentAttackFlag,
	apDebugBadIpPacketFlag,
	apDebugBadTcpPacketFlag,
	apDebugBadUdpPacketFlag,
	apDebugBadIcmpFlag,
	apDebugBadOtherIpFlag,
	apDebugOverloadProtectedIpFlag
    }
    STATUS current
    DESCRIPTION "Appliance Logging Debug Group."
    ::= { ddossecure4MIBGroups 4 }

apGroup OBJECT-GROUP
    OBJECTS {
	apBandwidth,
	apFlood,
	apBlockedProtocol,
	apBlockedState,
	apIpAttack,
	apTcpAttack,
	apUdpAttack,
	apIcmpAttack,
	apOtherIpAttack,
	apFragAttack,
	apBadIp,
	apBadTcp,
	apBadUdp,
	apBadIcmp,
	apBadOtherIp,
	apOverloadedIp,
	apInSyn,
	apOutSyn,
	apInSynAck,
	apOutSynAck,
	apInSynSyn,
	apOutSynSyn,
	apInEst,
	apOutEst,
	apInFin1Src,
	apOutFin1Src,
	apInFin2Src,
	apOutFin2Src,
	apInFin3Src,
	apOutFin3Src,
	apInFinFin,
	apOutFinFin,
	apInFin1Dst,
	apOutFin1Dst,
	apInFin2Dst,
	apOutFin2Dst,
	apInFin3Dst,
	apOutFin3Dst,
	apInCls,
	apOutCls,
	apInRst,
	apOutRst,
	apInRstCls,
	apOutRstCls,
	apInUnknown,
	apOutUnknown,
	apInAck,
	apOutAck,
	apInPendAck,
	apOutPendAck,
	apInGet,
	apOutGet,
	apInGets,
	apOutGets,
	apInTotalBpsAvg,
	apOutTotalBpsAvg,
	apInTotalPpsAvg,
	apOutTotalPpsAvg,
	apInSmallPpsAvg,
	apOutSmallPpsAvg,
	apInMediumPpsAvg,
	apOutMediumPpsAvg,
	apInLargePpsAvg,
	apOutLargePpsAvg,
	apInDroppedBpsAvg,
	apOutDroppedBpsAvg,
	apInDroppedPpsAvg,
	apOutDroppedPpsAvg,
	apInCharmDroppedBpsAvg,
	apOutCharmDroppedBpsAvg,
	apInFilteredBwthPercentAvg,
	apOutFilteredBwthPercentAvg,
	apInSynbacklogtallyAvg,
	apOutSynbacklogtallyAvg,
	apInConnectionAvg,
	apOutConnectionAvg,
	apInConnreqAvg,
	apOutConnreqAvg,
	apInActiveHttpGetsAvg,
	apOutActiveHttpGetsAvg,
	apInProtectBwthPktsAvg,
	apOutProtectBwthPktsAvg,
	apInFloodPktsAvg,
	apOutFloodPktsAvg,
	apInBlockedProtocolPktsAvg,
	apOutBlockedProtocolPktsAvg,
	apInBlockedStatePktsAvg,
	apOutBlockedStatePktsAvg,
	apInIpAttackPktsAvg,
	apOutIpAttackPktsAvg,
	apInTcpAttackPktsAvg,
	apOutTcpAttackPktsAvg,
	apInUdpAttackPktsAvg,
	apOutUdpAttackPktsAvg,
	apInIcmpAttackPktsAvg,
	apOutIcmpAttackPktsAvg,
	apInOtherIpAttackPktsAvg,
	apOutOtherIpAttackPktsAvg,
	apInFragmentAttackPktsAvg,
	apOutFragmentAttackPktsAvg,
	apInBadipPktsAvg,
	apOutBadipPktsAvg,
	apInBadTcpPktsAvg,
	apOutBadTcpPktsAvg,
	apInBadUdpPktsAvg,
	apOutBadUdpPktsAvg,
	apInBadIcmpPktsAvg,
	apOutBadIcmpPktsAvg,
	apInBadOtherIpPktsAvg,
	apOutBadOtherIpPktsAvg,
	apInOverloadedAvg,
	apOutOverloadedAvg,
	apInLatencyAvg,
	apOutLatencyAvg,
	apInSmallPpsMax,
	apOutSmallPpsMax,
	apInMediumPpsMax,
	apOutMediumPpsMax,
	apInLargePpsMax,
	apOutLargePpsMax,
	apInCharmDroppedBpsMax,
	apOutCharmDroppedBpsMax,
	apInFilteredBwthPercentMax,
	apOutFilteredBwthPercentMax,
	apInSynbacklogtallyMax,
	apOutSynbacklogtallyMax,
	apInConnectionMax,
	apOutConnectionMax,
	apInConnreqMax,
	apOutConnreqMax,
	apInActiveHttpGetsMax,
	apOutActiveHttpGetsMax,
	apInProtectBwthPktsMax,
	apOutProtectBwthPktsMax,
	apInFloodPktsMax,
	apOutFloodPktsMax,
	apInBlockedProtocolPktsMax,
	apOutBlockedProtocolPktsMax,
	apInBlockedStatePktsMax,
	apOutBlockedStatePktsMax,
	apInIpAttackPktsMax,
	apOutIpAttackPktsMax,
	apInTcpAttackPktsMax,
	apOutTcpAttackPktsMax,
	apInUdpAttackPktsMax,
	apOutUdpAttackPktsMax,
	apInIcmpAttackPktsMax,
	apOutIcmpAttackPktsMax,
	apInOtherIpAttackPktsMax,
	apOutOtherIpAttackPktsMax,
	apInFragmentAttackPktsMax,
	apOutFragmentAttackPktsMax,
	apInBadipPktsMax,
	apOutBadipPktsMax,
	apInBadTcpPktsMax,
	apOutBadTcpPktsMax,
	apInBadUdpPktsMax,
	apOutBadUdpPktsMax,
	apInBadIcmpPktsMax,
	apOutBadIcmpPktsMax,
	apInBadOtherIpPktsMax,
	apOutBadOtherIpPktsMax,
	apInOverloadedMax,
	apOutOverloadedMax,
	apInLatencyMax,
	apOutLatencyMax,
	apStalledFlag,
	apOfflineFlag,
	apInTcpConnTally,
	apOutTcpConnTally,
	apInSynBacklogTally,
	apUdpSessionTally,
	apIcmpSessionTally,
	apOtherIpSessionTally,
	apIncidentStart,
	apIncidentAddress,
	apIncidentType,
	apIncidentDirection,
	apIncidentPeakRate,
	apIncidentDropped
    }
    STATUS current
    DESCRIPTION "Appliance Statistics Group."
    ::= { ddossecure4MIBGroups 5 }

prGroup OBJECT-GROUP
    OBJECTS {
	prBandwidth,
	prFlood,
	prBlockedProtocol,
	prBlockedState,
	prIpAttack,
	prTcpAttack,
	prUdpAttack,
	prIcmpAttack,
	prOtherIpAttack,
	prFragAttack,
	prBadIp,
	prBadTcp,
	prBadUdp,
	prBadIcmp,
	prBadOtherIp,
	prOverloaded,
	prInSyn,
	prOutSyn,
	prInSynAck,
	prOutSynAck,
	prInSynSyn,
	prOutSynSyn,
	prInEst,
	prOutEst,
	prInFin1Src,
	prOutFin1Src,
	prInFin2Src,
	prOutFin2Src,
	prInFin3Src,
	prOutFin3Src,
	prInFinFin,
	prOutFinFin,
	prInFin1Dst,
	prOutFin1Dst,
	prInFin2Dst,
	prOutFin2Dst,
	prInFin3Dst,
	prOutFin3Dst,
	prInCls,
	prOutCls,
	prInRst,
	prOutRst,
	prInRstCls,
	prOutRstCls,
	prInUnknown,
	prOutUnknown,
	prInAck,
	prOutAck,
	prInPendAck,
	prOutPendAck,
	prInGet,
	prOutGet,
	prInGets,
	prOutGets,
	prOverloadedFlag,
	prInTcpConnTally,
	prOutTcpConnTally,
	prInSynBacklogTally,
	prInTotalBytesCnt,
	prOutTotalBytesCnt,
	prInDroppedBytesCnt,
	prOutDroppedBytesCnt,
	prInCharmDroppedBytesCnt,
	prOutCharmDroppedBytesCnt,
	prInTotalPpsMax,
	prOutTotalPpsMax,
	prInDroppedPpsMax,
	prOutDroppedPpsMax,
	prInTotalBpsMax,
	prOutTotalBpsMax,
	prInDroppedBpsMax,
	prOutDroppedBpsMax,
	prInCharmDroppedBpsMax,
	prOutCharmDroppedBpsMax,
	prInProtectBwthPktsCnt,
	prOutProtectBwthPktsCnt,
	prInFloodPktsCnt,
	prOutFloodPktsCnt,
	prInBlockedProtocolPktsCnt,
	prOutBlockedProtocolPktsCnt,
	prInBlockedStatePktsCnt,
	prOutBlockedStatePktsCnt,
	prInIpAttackPktsCnt,
	prOutIpAttackPktsCnt,
	prInTcpAttackPktsCnt,
	prOutTcpAttackPktsCnt,
	prInUdpAttackPktsCnt,
	prOutUdpAttackPktsCnt,
	prInIcmpAttackPktsCnt,
	prOutIcmpAttackPktsCnt,
	prInOtherIpAttackPktsCnt,
	prOutOtherIpAttackPktsCnt,
	prInFragmentAttackPktsCnt,
	prOutFragmentAttackPktsCnt,
	prInBadIpPktsCnt,
	prOutBadIpPktsCnt,
	prInBadTcpPktsCnt,
	prOutBadTcpPktsCnt,
	prInBadUdpPktsCnt,
	prOutBadUdpPktsCnt,
	prInBadIcmpPktsCnt,
	prOutBadIcmpPktsCnt,
	prInBadOtherIpPktsCnt,
	prOutBadOtherIpPktsCnt,
	prInTotalBpsAvg,
	prOutTotalBpsAvg,
	prInTotalPpsAvg,
	prOutTotalPpsAvg,
	prInSmallPpsAvg,
	prOutSmallPpsAvg,
	prInMediumPpsAvg,
	prOutMediumPpsAvg,
	prInLargePpsAvg,
	prOutLargePpsAvg,
	prInDroppedBpsAvg,
	prOutDroppedBpsAvg,
	prInDroppedPpsAvg,
	prOutDroppedPpsAvg,
	prInCharmDroppedBpsAvg,
	prOutCharmDroppedBpsAvg,
	prInFilteredBwthPercentAvg,
	prOutFilteredBwthPercentAvg,
	prInSynbacklogtallyAvg,
	prOutSynbacklogtallyAvg,
	prInConnectionAvg,
	prOutConnectionAvg,
	prInConnreqAvg,
	prOutConnreqAvg,
	prInActiveHttpGetsAvg,
	prOutActiveHttpGetsAvg,
	prInProtectBwthPktsAvg,
	prOutProtectBwthPktsAvg,
	prInFloodPktsAvg,
	prOutFloodPktsAvg,
	prInBlockedProtocolPktsAvg,
	prOutBlockedProtocolPktsAvg,
	prInBlockedStatePktsAvg,
	prOutBlockedStatePktsAvg,
	prInIpAttackPktsAvg,
	prOutIpAttackPktsAvg,
	prInTcpAttackPktsAvg,
	prOutTcpAttackPktsAvg,
	prInUdpAttackPktsAvg,
	prOutUdpAttackPktsAvg,
	prInIcmpAttackPktsAvg,
	prOutIcmpAttackPktsAvg,
	prInOtherIpAttackPktsAvg,
	prOutOtherIpAttackPktsAvg,
	prInFragmentAttackPktsAvg,
	prOutFragmentAttackPktsAvg,
	prInBadipPktsAvg,
	prOutBadipPktsAvg,
	prInBadTcpPktsAvg,
	prOutBadTcpPktsAvg,
	prInBadUdpPktsAvg,
	prOutBadUdpPktsAvg,
	prInBadIcmpPktsAvg,
	prOutBadIcmpPktsAvg,
	prInBadOtherIpPktsAvg,
	prOutBadOtherIpPktsAvg,
	prInOverloadedAvg,
	prOutOverloadedAvg,
	prInLatencyAvg,
	prOutLatencyAvg,
	prInTotalBpsMax,
	prOutTotalBpsMax,
	prInTotalPpsMax,
	prOutTotalPpsMax,
	prInSmallPpsMax,
	prOutSmallPpsMax,
	prInMediumPpsMax,
	prOutMediumPpsMax,
	prInLargePpsMax,
	prOutLargePpsMax,
	prInDroppedBpsMax,
	prOutDroppedBpsMax,
	prInDroppedPpsMax,
	prOutDroppedPpsMax,
	prInCharmDroppedBpsMax,
	prOutCharmDroppedBpsMax,
	prInFilteredBwthPercentMax,
	prOutFilteredBwthPercentMax,
	prInSynbacklogtallyMax,
	prOutSynbacklogtallyMax,
	prInConnectionMax,
	prOutConnectionMax,
	prInConnreqMax,
	prOutConnreqMax,
	prInActiveHttpGetsMax,
	prOutActiveHttpGetsMax,
	prInProtectBwthPktsMax,
	prOutProtectBwthPktsMax,
	prInFloodPktsMax,
	prOutFloodPktsMax,
	prInBlockedProtocolPktsMax,
	prOutBlockedProtocolPktsMax,
	prInBlockedStatePktsMax,
	prOutBlockedStatePktsMax,
	prInIpAttackPktsMax,
	prOutIpAttackPktsMax,
	prInTcpAttackPktsMax,
	prOutTcpAttackPktsMax,
	prInUdpAttackPktsMax,
	prOutUdpAttackPktsMax,
	prInIcmpAttackPktsMax,
	prOutIcmpAttackPktsMax,
	prInOtherIpAttackPktsMax,
	prOutOtherIpAttackPktsMax,
	prInFragmentAttackPktsMax,
	prOutFragmentAttackPktsMax,
	prInBadipPktsMax,
	prOutBadipPktsMax,
	prInBadTcpPktsMax,
	prOutBadTcpPktsMax,
	prInBadUdpPktsMax,
	prOutBadUdpPktsMax,
	prInBadIcmpPktsMax,
	prOutBadIcmpPktsMax,
	prInBadOtherIpPktsMax,
	prOutBadOtherIpPktsMax,
	prInOverloadedMax,
	prOutOverloadedMax,
	prInLatencyMax,
	prOutLatencyMax,
	prIncidentStart,
	prIncidentAddress,
	prIncidentType,
	prIncidentDirection,
	prIncidentPeakRate,
	prIncidentDropped
    }
    STATUS current
    DESCRIPTION "Protected Statistics Group."
    ::= { ddossecure4MIBGroups 6 }

prCfgGroup OBJECT-GROUP
    OBJECTS {
	prHostName,
	prTcpBacklog,
	prMaxConnections,
	prMaxConnectionRate,
	prInFilterName,
	prOutFilterName,
	prSendTcpRejects,
	prTrackSoap,
	prOperationMode,
	prMaxGets,
	prFragsDisabled
    }
    STATUS current
    DESCRIPTION "protected IP Configuration Group."
    ::= { ddossecure4MIBGroups 7 }

gwCfgGroup OBJECT-GROUP
    OBJECTS {
	gwInternetConfigMacAddress,
	gwInternetConfigToSpeedBps,
	gwInternetConfigToRatePps,
	gwProtectedConfigMacAddress,
	gwProtectedConfigToSpeedBps,
	gwProtectedConfigToRatePps
    }
    STATUS current
    DESCRIPTION "Gateway Configuration Group."
    ::= { ddossecure4MIBGroups 8 }

apEventObjectGroup OBJECT-GROUP
    OBJECTS {
	apOutputErrorIIFlag,
	apOutputErrorPIFlag,
	apOutputErrorMIFlag,
	apNewConfigFlag,
	apNotLicensedFlag,
	apMacTableFullFlag,
	apProtectedTableFullFlag,
	apIncidentTableFullFlag,
	apTcpTableFullFlag,
	apUdpTableFullFlag,
	apIcmpTableFullFlag,
	apOtherIpTableFullFlag,
	apFragTableFullFlag,
	apFtpTableFullFlag,
	apBlockedTableFullFlag,
	apShortCircuitFlag,
	apInternetIfDisconnectedFlag,
	apProtectedIfDisconnectedFlag,
	apMgmtIfDisconnectedFlag,
	apUpgradingFlag,
	apProtectedIfTrafficFlag,
	apRoutingLoopFlag,
	apStateLearningFlag,
	apSupportExpiredFlag,
	apSevereLoadingFlag,
	apMacMisconfiguredFlag,
	apIfMisconfiguredFlag,
	apInternetIfLinkDownFlag,
	apProtectedIfLinkDownFlag,
	apDatashareIfDisconnectedFlag,
	apDiskFailingFlag,
	apPsuFailingFlag,
	apFanFailingFlag,
	apConfigXferFailFlag,
	apMissingRequiredPartnerFlag,
	apBgpMisconfiguredIpFlag
    }
    STATUS current
    DESCRIPTION "Appliance State Flag Group."
    ::= { ddossecure4MIBGroups 9 }

apRatesGroup OBJECT-GROUP
    OBJECTS {
	apInTotalBytesCnt,
	apOutTotalBytesCnt,
	apInDroppedBytesCnt,
	apOutDroppedBytesCnt,
	apInCharmDroppedBytesCnt,
	apOutCharmDroppedBytesCnt,
	apInTotalPpsMax,
	apOutTotalPpsMax,
	apInDroppedPpsMax,
	apOutDroppedPpsMax,
	apInTotalBpsMax,
	apOutTotalBpsMax,
	apInDroppedBpsMax,
	apOutDroppedBpsMax,
	apInCharmDroppedBpsMax,
	apOutCharmDroppedBpsMax,
	apInProtectBwthPktsCnt,
	apOutProtectBwthPktsCnt,
	apInFloodPktsCnt,
	apOutFloodPktsCnt,
	apInBlockedProtocolPktsCnt,
	apOutBlockedProtocolPktsCnt,
	apInBlockedStatePktsCnt,
	apOutBlockedStatePktsCnt,
	apInIpAttackPktsCnt,
	apOutIpAttackPktsCnt,
	apInTcpAttackPktsCnt,
	apOutTcpAttackPktsCnt,
	apInUdpAttackPktsCnt,
	apOutUdpAttackPktsCnt,
	apInIcmpAttackPktsCnt,
	apOutIcmpAttackPktsCnt,
	apInOtherIpAttackPktsCnt,
	apOutOtherIpAttackPktsCnt,
	apInFragmentAttackPktsCnt,
	apOutFragmentAttackPktsCnt,
	apInBadIpPktsCnt,
	apOutBadIpPktsCnt,
	apInBadTcpPktsCnt,
	apOutBadTcpPktsCnt,
	apInBadUdpPktsCnt,
	apOutBadUdpPktsCnt,
	apInBadIcmpPktsCnt,
	apOutBadIcmpPktsCnt,
	apInBadOtherIpPktsCnt,
	apOutBadOtherIpPktsCnt,
	apInTotalBytesCnt,
	apOutTotalBytesCnt,
	apInTotalPpsCnt,
	apOutTotalPpsCnt,
	apInSmallPpsCnt,
	apOutSmallPpsCnt,
	apInMediumPpsCnt,
	apOutMediumPpsCnt,
	apInLargePpsCnt,
	apOutLargePpsCnt,
	apInDroppedBytesCnt,
	apOutDroppedBytesCnt,
	apInDroppedPpsCnt,
	apOutDroppedPpsCnt,
	apInFilteredBwthPercentCnt,
	apOutFilteredBwthPercentCnt,
	apInConnreqCnt,
	apOutConnreqCnt,
	apInOverloadedCnt,
	apOutOverloadedCnt
    }
    STATUS current
    DESCRIPTION "Configuration Group."
    ::= { ddossecure4MIBGroups 10 }

poFilterCfgGroup OBJECT-GROUP
    OBJECTS {
	poFilterName,
	poTcpPortsList,
	poUdpPortsList,
	poIcmpTypesList,
	poIpProtocolsList
    }
    STATUS current
    DESCRIPTION "Configuration Group."
    ::= { ddossecure4MIBGroups 11 }

apLinkStatusGroup OBJECT-GROUP
    OBJECTS {
	apMgmtIfLinkModeState,
	apIntIfLinkModeState,
	apMgmtIfLinkFCState,
	apIntIfLinkFCState,
	apProtIfLinkModeState,
	apProtIfLinkFCState
    }
    STATUS current
    DESCRIPTION "Configuration Group."
    ::= { ddossecure4MIBGroups 12 }

apLogGroup OBJECT-GROUP
    OBJECTS {
	apWorstOffenderLastTime,
	apWorstOffenderCount,
	apLogFileRecord
    }
    STATUS current
    DESCRIPTION "Configuration Group."
    ::= { ddossecure4MIBGroups 13 }

apHaCfgGroup OBJECT-GROUP
    OBJECTS {
	apHaState,
	apHaPartnerList,
	apHaPartnerTime
    }
    STATUS current
    DESCRIPTION "Configuration Group."
    ::= { ddossecure4MIBGroups 14 }

poGroup OBJECT-GROUP
    OBJECTS {
    	poPortalName,
	poInTotalBpsAvg,
	poOutTotalBpsAvg,
	poInTotalPpsAvg,
	poOutTotalPpsAvg,
	poInSmallPpsAvg,
	poOutSmallPpsAvg,
	poInMediumPpsAvg,
	poOutMediumPpsAvg,
	poInLargePpsAvg,
	poOutLargePpsAvg,
	poInDroppedBpsAvg,
	poOutDroppedBpsAvg,
	poInDroppedPpsAvg,
	poOutDroppedPpsAvg,
	poInCharmDroppedBpsAvg,
	poOutCharmDroppedBpsAvg,
	poInFilteredBwthPercentAvg,
	poOutFilteredBwthPercentAvg,
	poInSynbacklogtallyAvg,
	poOutSynbacklogtallyAvg,
	poInConnectionAvg,
	poOutConnectionAvg,
	poInConnreqAvg,
	poOutConnreqAvg,
	poInActiveHttpGetsAvg,
	poOutActiveHttpGetsAvg,
	poInProtectBwthPktsAvg,
	poOutProtectBwthPktsAvg,
	poInFloodPktsAvg,
	poOutFloodPktsAvg,
	poInBlockedProtocolPktsAvg,
	poOutBlockedProtocolPktsAvg,
	poInBlockedStatePktsAvg,
	poOutBlockedStatePktsAvg,
	poInIpAttackPktsAvg,
	poOutIpAttackPktsAvg,
	poInTcpAttackPktsAvg,
	poOutTcpAttackPktsAvg,
	poInUdpAttackPktsAvg,
	poOutUdpAttackPktsAvg,
	poInIcmpAttackPktsAvg,
	poOutIcmpAttackPktsAvg,
	poInOtherIpAttackPktsAvg,
	poOutOtherIpAttackPktsAvg,
	poInFragmentAttackPktsAvg,
	poOutFragmentAttackPktsAvg,
	poInBadipPktsAvg,
	poOutBadipPktsAvg,
	poInBadTcpPktsAvg,
	poOutBadTcpPktsAvg,
	poInBadUdpPktsAvg,
	poOutBadUdpPktsAvg,
	poInBadIcmpPktsAvg,
	poOutBadIcmpPktsAvg,
	poInBadOtherIpPktsAvg,
	poOutBadOtherIpPktsAvg,
	poInOverloadedAvg,
	poOutOverloadedAvg,
	poInLatencyAvg,
	poOutLatencyAvg,
	poInTotalBpsMax,
	poOutTotalBpsMax,
	poInTotalPpsMax,
	poOutTotalPpsMax,
	poInSmallPpsMax,
	poOutSmallPpsMax,
	poInMediumPpsMax,
	poOutMediumPpsMax,
	poInLargePpsMax,
	poOutLargePpsMax,
	poInDroppedBpsMax,
	poOutDroppedBpsMax,
	poInDroppedPpsMax,
	poOutDroppedPpsMax,
	poInCharmDroppedBpsMax,
	poOutCharmDroppedBpsMax,
	poInFilteredBwthPercentMax,
	poOutFilteredBwthPercentMax,
	poInSynbacklogtallyMax,
	poOutSynbacklogtallyMax,
	poInConnectionMax,
	poOutConnectionMax,
	poInConnreqMax,
	poOutConnreqMax,
	poInActiveHttpGetsMax,
	poOutActiveHttpGetsMax,
	poInProtectBwthPktsMax,
	poOutProtectBwthPktsMax,
	poInFloodPktsMax,
	poOutFloodPktsMax,
	poInBlockedProtocolPktsMax,
	poOutBlockedProtocolPktsMax,
	poInBlockedStatePktsMax,
	poOutBlockedStatePktsMax,
	poInIpAttackPktsMax,
	poOutIpAttackPktsMax,
	poInTcpAttackPktsMax,
	poOutTcpAttackPktsMax,
	poInUdpAttackPktsMax,
	poOutUdpAttackPktsMax,
	poInIcmpAttackPktsMax,
	poOutIcmpAttackPktsMax,
	poInOtherIpAttackPktsMax,
	poOutOtherIpAttackPktsMax,
	poInFragmentAttackPktsMax,
	poOutFragmentAttackPktsMax,
	poInBadipPktsMax,
	poOutBadipPktsMax,
	poInBadTcpPktsMax,
	poOutBadTcpPktsMax,
	poInBadUdpPktsMax,
	poOutBadUdpPktsMax,
	poInBadIcmpPktsMax,
	poOutBadIcmpPktsMax,
	poInBadOtherIpPktsMax,
	poOutBadOtherIpPktsMax,
	poInOverloadedMax,
	poOutOverloadedMax,
	poInLatencyMax,
	poOutLatencyMax,
	poInTotalBytesCnt,
	poOutTotalBytesCnt,
	poInDroppedBytesCnt,
	poOutDroppedBytesCnt,
	poInCharmDroppedBytesCnt,
	poOutCharmDroppedBytesCnt,
	poInTotalPpsCnt,
	poOutTotalPpsCnt,
	poInSmallPpsCnt,
	poOutSmallPpsCnt,
	poInMediumPpsCnt,
	poOutMediumPpsCnt,
	poInLargePpsCnt,
	poOutLargePpsCnt,
	poInDroppedPpsCnt,
	poOutDroppedPpsCnt,
	poInFilteredBwthPercentCnt,
	poOutFilteredBwthPercentCnt,
	poInConnreqCnt,
	poOutConnreqCnt,
	poIncidentPortalName,
	poIncidentStart,
	poIncidentAddress,
	poIncidentType,
	poIncidentDirection,
	poIncidentPeakRate,
	poIncidentDropped
    }
    STATUS current
    DESCRIPTION "Configuration Group."
    ::= { ddossecure4MIBGroups 15 }

prNotificationGroup NOTIFICATION-GROUP
    NOTIFICATIONS {
	prBandwidthOn,
	prBandwidthOff,
	prFloodOn,
	prFloodOff,
	prBlockedProtocolOn,
	prBlockedProtocolOff,
	prBlockedStateOn,
	prBlockedStateOff,
	prIpAttackOn,
	prIpAttackOff,
	prTcpAttackOn,
	prTcpAttackOff,
	prUdpAttackOn,
	prUdpAttackOff,
	prIcmpAttackOn,
	prIcmpAttackOff,
	prOtherIpAttackOn,
	prOtherIpAttackOff,
	prFragAttackOn,
	prFragAttackOff,
	prBadIpOn,
	prBadIpOff,
	prBadTcpOn,
	prBadTcpOff,
	prBadUdpOn,
	prBadUdpOff,
	prBadIcmpOn,
	prBadIcmpOff,
	prBadOtherIpOn,
	prBadOtherIpOff,
	prOverloadedOn,
	prOverloadedOff,
	apHaStateMode,
	apOutputErrorIIFlagOn,
	apOutputErrorIIFlagOff,
	apOutputErrorPIFlagOn,
	apOutputErrorPIFlagOff,
	apOutputErrorMIFlagOn,
	apOutputErrorMIFlagOff,
	apNewConfigFlagOn,
	apNewConfigFlagOff,
	apNotLicensedFlagOn,
	apNotLicensedFlagOff,
	apMacTableFullFlagOn,
	apMacTableFullFlagOff,
	apProtectedTableFullFlagOn,
	apProtectedTableFullFlagOff,
	apIncidentTableFullFlagOn,
	apIncidentTableFullFlagOff,
	apTcpTableFullFlagOn,
	apTcpTableFullFlagOff,
	apUdpTableFullFlagOn,
	apUdpTableFullFlagOff,
	apIcmpTableFullFlagOn,
	apIcmpTableFullFlagOff,
	apOtherIpTableFullFlagOn,
	apOtherIpTableFullFlagOff,
	apFragTableFullFlagOn,
	apFragTableFullFlagOff,
	apFtpTableFullFlagOn,
	apFtpTableFullFlagOff,
	apBlockedTableFullFlagOn,
	apBlockedTableFullFlagOff,
	apShortCircuitFlagOn,
	apShortCircuitFlagOff,
	apInternetIfDisconnectedFlagOn,
	apInternetIfDisconnectedFlagOff,
	apProtectedIfDisconnectedFlagOn,
	apProtectedIfDisconnectedFlagOff,
	apMgmtIfDisconnectedFlagOn,
	apMgmtIfDisconnectedFlagOff,
	apUpgradingFlagOn,
	apUpgradingFlagOff,
	apProtectedIfTrafficFlagOn,
	apProtectedIfTrafficFlagOff,
	apRoutingLoopFlagOn,
	apRoutingLoopFlagOff,
	apOfflineFlagOn,
	apOfflineFlagOff,
	apStateLearningFlagOn,
	apStateLearningFlagOff,
	apSupportExpiredFlagOn,
	apSupportExpiredFlagOff,
	apSevereLoadingFlagOn,
	apSevereLoadingFlagOff,
	apMacMisconfiguredFlagOn,
	apMacMisconfiguredFlagOff,
	apIfMisconfiguredFlagOn,
	apIfMisconfiguredFlagOff,
	apInternetIfLinkDownFlagOn,
	apInternetIfLinkDownFlagOff,
	apProtectedIfLinkDownFlagOn,
	apProtectedIfLinkDownFlagOff,
	apDatashareIfDisconnectedFlagOn,
	apDatashareIfDisconnectedFlagOff,
	apDiskFailingOn,
	apDiskFailingOff,
	apPsuFailingFlagOn,
	apPsuFailingFlagOff,
	apFanFailingFlagOn,
	apFanFailingFlagOff,
	apConfigXferFailFlagOn,
	apConfigXferFailFlagOff,
	apMissingRequiredPartnerFlagOn,
	apMissingRequiredPartnerFlagOff,
	apBgpMisconfiguredIpFlagOn,
	apBgpMisconfiguredIpFlagOff,
	prBandwidthLimitOn,
	prBandwidthLimitOff,
	prPacketLimitOn,
	prPacketLimitOff,
	prBlockedProtocolBlackListIpOn,
	prBlockedProtocolBlackListIpOff,
	prBlockedProtocolIcmpTypeOn,
	prBlockedProtocolIcmpTypeOff,
	prBlockedProtocolPortOn,
	prBlockedProtocolPortOff,
	prBlockedProtocolOtherOn,
	prBlockedProtocolOtherOff,
	prUnknownSessionIcmpRespOn,
	prUnknownSessionIcmpRespOff,
	prUnknownSessionIcmpDiagRespOn,
	prUnknownSessionIcmpDiagRespOff,
	prUnknownSessionNoStateOn,
	prUnknownSessionNoStateOff,
	prUnknownSessionInvalidStateOn,
	prUnknownSessionInvalidStateOff,
	prTcpAttackRstOn,
	prTcpAttackRstOff,
	prIpAttackLandOn,
	prIpAttackLandOff,
	prTcpAttackSynAckToOn,
	prTcpAttackSynAckToOff,
	prBlockedProtocolCountryOn,
	prBlockedProtocolCountryOff,
	prTcpAttackSynFloodOn,
	prTcpAttackSynFloodOff,
	prTcpAttackConnFloodOn,
	prTcpAttackConnFloodOff,
	prTcpAttackTableFullOn,
	prTcpAttackTableFullOff,
	prBadTcpFastAckOn,
	prBadTcpFastAckOff,
	prTcpAttackHttpFloodOn,
	prTcpAttackHttpFloodOff,
	prUdpAttackTableFullOn,
	prUdpAttackTableFullOff,
	prTcpAttackHttpTimeoutOn,
	prTcpAttackHttpTimeoutOff,
	prIcmpAttackRepeatsOn,
	prIcmpAttackRepeatsOff,
	prIcmpAttackTableFullOn,
	prIcmpAttackTableFullOff,
	prOtherIpAttackTableFullOn,
	prOtherIpAttackTableFullOff,
	prFragAttackPingOfDeathOn,
	prFragAttackPingOfDeathOff,
	prFragAttackHeadOverlayOn,
	prFragAttackHeadOverlayOff,
	prFragAttackTableFullOn,
	prFragAttackTableFullOff,
	prFragAttackSmallSizeOn,
	prFragAttackSmallSizeOff,
	prFragAttackNoFragsAllowedOn,
	prFragAttackNoFragsAllowedOff,
	prBadIpSrcAddrOn,
	prBadIpSrcAddrOff,
	prBadIpHeaderOn,
	prBadIpHeaderOff,
	prBadIpOptionOn,
	prBadIpOptionOff,
	prBadIpSizeOn,
	prBadIpSizeOff,
	prBlockedProtocolTmpBlackListOn,
	prBlockedProtocolTmpBlackListOff,
	prBadTcpFlagsOn,
	prBadTcpFlagsOff,
	prBadTcpMalformedOn,
	prBadTcpMalformedOff,
	prBadTcpOptionOn,
	prBadTcpOptionOff,
	prBlockedProtocolDnsOn,
	prBlockedProtocolDnsOff,
	prBadUdpNoDataOn,
	prBadUdpNoDataOff,
	prBadUdpMalformedOn,
	prBadUdpMalformedOff,
	prBlockedProtocolAsOn,
	prBlockedProtocolAsOff,
	ptTcpAttackHttpRateFloodOn,
	ptTcpAttackHttpRateFloodOff,
	prBadIcmpMalformedOn,
	prBadIcmpMalformedOff,
	prBlockedProtocolUrlOn,
	prBlockedProtocolUrlOff,
	prBadOtherIpProtocolOn,
	prBadOtherIpProtocolOff,
	prBadOtherIpLengthOn,
	prBadOtherIpLengthOff,
	prTcpAttackHttpIncompleteOn,
	prTcpAttackHttpIncompleteOff,
	prOverloadedStallOn,
	prOverloadedStallOff,
	prFragAttackTimeOutOn,
	prFragAttackTimeOutOff,
	prFragAttackRepeatsOn,
	prFragAttackRepeatsOff,
	prFragAttackBadLengthOn,
	prFragAttackBadLengthOff,
	prOverloadedBacklogOn,
	prOverloadedBacklogOff,
	prBlockedProtocolAddressOn,
	prBlockedProtocolAddressOff,
	prTcpAttackNoDataOn,
	prTcpAttackNoDataOff,
	prTcpAttackNoServerDataOn,
	prTcpAttackNoServerDataOff,
	prTcpAttackConnRateFloodOn,
	prTcpAttackConnRateFloodOff,
	prOverloadedThreadsOn,
	prOverloadedThreadsOff,
	prBadIpReflectedRouteOn,
	prBadIpReflectedRouteOff,
	prTcpAttackPortScanOn,
	prTcpAttackPortScanOff,
	prTcpAttackSmallWindowOn,
	prTcpAttackSmallWindowOff,
	prTcpAttackClientAbortOn,
	prTcpAttackClientAbortOff,
	prBlockedProtocolSipOn,
	prBlockedProtocolSipOff,
	prTcpAttackUrlRateLimitOn,
	prTcpAttackUrlRateLimitOff,
	prUdpAttackDnsRateLimitOn,
	prUdpAttackDnsRateLimitOff,
	prUdpAttackSipRateLimitOn,
	prUdpAttackSipRateLimitOff,
	prBadTcpChecksumOn,
	prBadTcpChecksumOff,
	prTcpAttackHttpFormatOn,
	prTcpAttackHttpFormatOff,
	prUnknownSessionReflectiveOn,
	prUnknownSessionReflectiveOff
    }
    STATUS current
    DESCRIPTION "Notification Group."
    ::= { ddossecure4MIBGroups 100 }

deprecatedNotificationGroup NOTIFICATION-GROUP
    NOTIFICATIONS {
	apOutputErrorIIEvent,
	apOutputErrorPIEvent,
	apOutputErrorMIEvent,
	apNewConfigEvent,
	apNotLicensedEvent,
	apMacTableFullEvent,
	apProtectedTableFullEvent,
	apIncidentTableFullEvent,
	apTcpTableFullEvent,
	apUdpTableFullEvent,
	apIcmpTableFullEvent,
	apOtherIpTableFullEvent,
	apFragTableFullEvent,
	apFtpTableFullEvent,
	apBlockedTableFullEvent,
	apShortCircuitEvent,
	apInternetIfDisconnectedEvent,
	apProtectedIfDisconnectedEvent,
	apMgmtIfDisconnectedEvent,
	apUpgradingEvent,
	apProtectedIfTrafficEvent,
	apRoutingLoopEvent,
	apOfflineEvent,
	apStateLearningEvent,
	apSupportExpiredEvent,
	apSevereLoadingEvent,
	apMacMisconfiguredEvent,
	apIfMisconfiguredEvent,
	apInternetIfLinkDownEvent,
	apProtectedIfLinkDownEvent,
	apDatashareIfDisconnectedEvent,
	apHaStateEvent,
	prBandwidthEvent,
	prFloodEvent,
	prBlockedProtocolEvent,
	prBlockedStateEvent,
	prIpAttackEvent,
	prTcpAttackEvent,
	prUdpAttackEvent,
	prIcmpAttackEvent,
	prOtherIpAttackEvent,
	prFragAttackEvent,
	prBadIpEvent,
	prBadTcpEvent,
	prBadUdpEvent,
	prBadIcmpEvent,
	prBadOtherIpEvent,
	prOverloadedEvent
    }
    STATUS deprecated
    DESCRIPTION "Notification Group."
    ::= { ddossecure4MIBGroups 101 }

END
