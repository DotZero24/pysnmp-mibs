--
-- Juniper Mobile Gateway GTP objects MIB.
--
-- Copyright (c) 2010-2013, Juniper Networks, Inc.
-- All rights reserved.
--
-- The contents of this document are subject to change without notice.
--

JUNIPER-MOBILE-GATEWAY-GTP-MIB DEFINITIONS ::= BEGIN

IMPORTS
    Counter64, IpAddress, Integer32, Counter32, Unsigned32,
    NOTIFICATION-TYPE, MODULE-IDENTITY,OBJECT-TYPE
        FROM SNMPv2-SMI

    TEXTUAL-CONVENTION, DisplayString, RowStatus, TruthValue
        FROM SNMPv2-TC

    Ipv6AddressPrefix, Ipv6AddressIfIdentifier, Ipv6Address
        FROM IPV6-TC

    InetAddressType, InetAddress, InetPortNumber, InetAddressPrefixLength
        FROM INET-ADDRESS-MIB

    EnabledStatus
        FROM JUNIPER-MIMSTP-MIB

    jnxMobileGatewayPgwGgsn
        FROM JUNIPER-MBG-SMI

    jnxMbgGwIndex, jnxMbgGwName
        FROM JUNIPER-MOBILE-GATEWAYS;

--
-- Module Identity for GPRS Tunneling Protocol
-- GTPC generally refers to Control Path of the GTP protocol and
-- GTPU generally refers to the Data Path of the GTP Protocol
--

jnxMbgPgwGtpMib MODULE-IDENTITY
    LAST-UPDATED "201101281200Z" -- Jan 28, 2011, 12:00:00 UTC
    ORGANIZATION "Juniper Networks, Inc."
    CONTACT-INFO
        "Juniper Technical Assistance Center
         Juniper Networks, Inc.
         1133 Innovation Way
         Sunnyvale, CA 94089
         E-mail: support@juniper.net"
    DESCRIPTION
        "This module defines some sample objects pertaining to GTP protocol."
    REVISION "201101281200Z" -- Jan 28, 2011, 12:00:00 UTC
    DESCRIPTION "Initial version"

    ::= { jnxMobileGatewayPgwGgsn 2 }

jnxMbgPgwGtpNotifications  OBJECT IDENTIFIER ::=
                                    { jnxMbgPgwGtpMib 0 }
jnxMbgPgwGtpObjects     OBJECT IDENTIFIER ::=
                                    { jnxMbgPgwGtpMib 1 }

--
-- Global Statistics Table : Gateway level statistics
--

jnxMbgPgwGtpCGlbStatsTable OBJECT-TYPE
    SYNTAX SEQUENCE OF JnxMbgPgwGtpGlbStatsEntry
    MAX-ACCESS  not-accessible
    STATUS      current
    DESCRIPTION
        "Each entry corresponds to a Gateway level GTP Control statistic"
  ::= { jnxMbgPgwGtpObjects 10 }

jnxMbgPgwGtpGlbStatsEntry OBJECT-TYPE
    SYNTAX      JnxMbgPgwGtpGlbStatsEntry
    MAX-ACCESS  not-accessible
    STATUS      current
    DESCRIPTION
        "A specification of the GTPC Global Statistics Table ."
    INDEX     { jnxMbgGwIndex}
    ::= { jnxMbgPgwGtpCGlbStatsTable 1}

JnxMbgPgwGtpGlbStatsEntry ::= SEQUENCE {
    jnxMbgPgwRxPacketsDropped       Counter64,
    jnxMbgPgwPacketAllocFail        Counter64,
    jnxMbgPgwPacketSendFail         Counter64,
    jnxMbgPgwIPVerErrRx             Counter64,
    jnxMbgPgwIPProtoErrRx           Counter64,
    jnxMbgPgwGTPPortErrRx           Counter64,
    jnxMbgPgwGTPUnknVerRx           Counter64,
    jnxMbgPgwPcktLenErrRx           Counter64,
    jnxMbgPgwUnknMsgRx              Counter64,
    jnxMbgPgwV2ProtocolErrRx        Counter64,
    jnxMbgPgwV2UnSupportedMsgRx     Counter64,
    jnxMbgPgwV2T3RespTmrExpRx       Counter64,
    jnxMbgPgwV2GlbNumMsgRx          Counter64,
    jnxMbgPgwV2GlbNumMsgTx          Counter64,
    jnxMbgPgwV2GlbNumBytesRx        Counter64,
    jnxMbgPgwV2GlbNumBytesTx        Counter64,
    jnxMbgPgwV2GlbEchoReqRx         Counter64,
    jnxMbgPgwV2GlbEchoReqTx         Counter64,
    jnxMbgPgwV2GlbEchoRespRx        Counter64,
    jnxMbgPgwV2GlbEchoRespTx        Counter64,
    jnxMbgPgwV2VerNotSupRx          Counter64,
    jnxMbgPgwV2VerNotSupTx          Counter64,
    jnxMbgPgwV2CreateSessReqRx      Counter64,
    jnxMbgPgwV2CreateSessReqTx      Counter64,
    jnxMbgPgwV2CreateSessRspRx      Counter64,
    jnxMbgPgwV2CreateSessRspTx      Counter64,
    jnxMbgPgwV2ModBrReqRx           Counter64,
    jnxMbgPgwV2ModBrReqTx           Counter64,
    jnxMbgPgwV2ModBrRspRx           Counter64,
    jnxMbgPgwV2ModBrRspTx           Counter64,
    jnxMbgPgwV2DelSessReqRx         Counter64,
    jnxMbgPgwV2DelSessReqTx         Counter64,
    jnxMbgPgwV2DelSessRspRx         Counter64,
    jnxMbgPgwV2DelSessRspTx         Counter64,
    jnxMbgPgwV2CrtBrReqRx           Counter64,
    jnxMbgPgwV2CrtBrReqTx           Counter64,
    jnxMbgPgwV2CrtBrRspRx           Counter64,
    jnxMbgPgwV2CrtBrRspTx           Counter64,
    jnxMbgPgwV2UpdBrReqRx           Counter64,
    jnxMbgPgwV2UpdBrReqTx           Counter64,
    jnxMbgPgwV2UpdBrRspRx           Counter64,
    jnxMbgPgwV2UpdBrRspTx           Counter64,
    jnxMbgPgwV2DelBrReqRx           Counter64,
    jnxMbgPgwV2DelBrReqTx           Counter64,
    jnxMbgPgwV2DelBrRspRx           Counter64,
    jnxMbgPgwV2DelBrRspTx           Counter64,
    jnxMbgPgwV2DelConnSetReqRx      Counter64,
    jnxMbgPgwV2DelConnSetReqTx      Counter64,
    jnxMbgPgwV2DelConnSetRspRx      Counter64,
    jnxMbgPgwV2DelConnSetRspTx      Counter64,
    jnxMbgPgwV2UpdConnSetReqRx      Counter64,
    jnxMbgPgwV2UpdConnSetReqTx      Counter64,
    jnxMbgPgwV2UpdConnSetRspRx      Counter64,
    jnxMbgPgwV2UpdConnSetRspTx      Counter64,
    jnxMbgPgwV2ModBrCmdRx           Counter64,
    jnxMbgPgwV2ModBrCmdTx           Counter64,
    jnxMbgPgwV2ModBrFlrIndRx        Counter64,
    jnxMbgPgwV2ModBrFlrIndTx        Counter64,
    jnxMbgPgwV2DelBrCmdRx           Counter64,
    jnxMbgPgwV2DelBrCmdTx           Counter64,
    jnxMbgPgwV2DelBrFlrIndRx        Counter64,
    jnxMbgPgwV2DelBrFlrIndTx        Counter64,
    jnxMbgPgwV2BrResCmdRx           Counter64,
    jnxMbgPgwV2BrResCmdTx           Counter64,
    jnxMbgPgwV2BrResFlrIndRx        Counter64,
    jnxMbgPgwV2BrResFlrIndTx        Counter64,
    jnxMbgPgwV2RelAcsBrReqRx        Counter64,
    jnxMbgPgwV2RelAcsBrReqTx        Counter64,
    jnxMbgPgwV2RelAcsBrRespRx       Counter64,
    jnxMbgPgwV2RelAcsBrRespTx       Counter64,
    jnxMbgPgwV2CrIndTunReqRx        Counter64,
    jnxMbgPgwV2CrIndTunReqTx        Counter64,
    jnxMbgPgwV2CrIndTunRespRx       Counter64,
    jnxMbgPgwV2CrIndTunRespTx       Counter64,
    jnxMbgPgwV2DelIndTunReqRx       Counter64,
    jnxMbgPgwV2DelIndTunReqTx       Counter64,
    jnxMbgPgwV2DelIndTunRespRx      Counter64,
    jnxMbgPgwV2DelIndTunRespTx      Counter64,
    jnxMbgPgwV2DlDataNotifRx        Counter64,
    jnxMbgPgwV2DlDataNotifTx        Counter64,
    jnxMbgPgwV2DlDataAckRx          Counter64,
    jnxMbgPgwV2DlDataAckTx          Counter64,
    jnxMbgPgwV2DlDataNotiFlrIndRx   Counter64,
    jnxMbgPgwV2DlDataNotiFlrIndTx   Counter64,
    jnxMbgPgwV2StopPagingIndRx      Counter64,
    jnxMbgPgwV2StopPagingIndTx      Counter64,
    jnxMbgPgwV2ICsPageRx            Counter64,
    jnxMbgPgwV2ICsPageTx            Counter64,
    jnxMbgPgwV2ICsReqAcceptRx       Counter64,
    jnxMbgPgwV2ICsReqAcceptTx       Counter64,
    jnxMbgPgwV2ICsAcceptPartRx      Counter64,
    jnxMbgPgwV2ICsAcceptPartTx      Counter64,
    jnxMbgPgwV2ICsNewPTNPrefRx      Counter64,
    jnxMbgPgwV2ICsNewPTNPrefTx      Counter64,
    jnxMbgPgwV2ICsNewPTSIAdbrRx     Counter64,
    jnxMbgPgwV2ICsNewPTSIAdbrTx     Counter64,
    jnxMbgPgwV2ICsCtxNotFndRx       Counter64,
    jnxMbgPgwV2ICsCtxNotFndTx       Counter64,
    jnxMbgPgwV2ICsInvMsgFmtRx       Counter64,
    jnxMbgPgwV2ICsInvMsgFmtTx       Counter64,
    jnxMbgPgwV2ICsVerNotSuppRx      Counter64,
    jnxMbgPgwV2ICsVerNotSuppTx      Counter64,
    jnxMbgPgwV2ICsInvLenRx          Counter64,
    jnxMbgPgwV2ICsInvLenTx          Counter64,
    jnxMbgPgwV2ICsServNotSuppRx     Counter64,
    jnxMbgPgwV2ICsServNotSuppTx     Counter64,
    jnxMbgPgwV2ICsManIEIncorrRx     Counter64,
    jnxMbgPgwV2ICsManIEIncorrTx     Counter64,
    jnxMbgPgwV2ICsManIEMissRx       Counter64,
    jnxMbgPgwV2ICsManIEMissTx       Counter64,
    jnxMbgPgwV2ICsOptIEIncorrRx     Counter64,
    jnxMbgPgwV2ICsOptIEIncorrTx     Counter64,
    jnxMbgPgwV2ICsSysFailRx         Counter64,
    jnxMbgPgwV2ICsSysFailTx         Counter64,
    jnxMbgPgwV2ICsNoResRx           Counter64,
    jnxMbgPgwV2ICsNoResTx           Counter64,
    jnxMbgPgwV2ICsTFTSMANTErRx      Counter64,
    jnxMbgPgwV2ICsTFTSMANTErTx      Counter64,
    jnxMbgPgwV2ICsTFTSysErrRx       Counter64,
    jnxMbgPgwV2ICsTFTSysErrTx       Counter64,
    jnxMbgPgwV2ICsPkFltManErrRx     Counter64,
    jnxMbgPgwV2ICsPkFltManErrTx     Counter64,
    jnxMbgPgwV2ICsPkFltSynErrRx     Counter64,
    jnxMbgPgwV2ICsPkFltSynErrTx     Counter64,
    jnxMbgPgwV2ICsMisUnknAPNRx      Counter64,
    jnxMbgPgwV2ICsMisUnknAPNTx      Counter64,
    jnxMbgPgwV2ICsUnexpRptIERx      Counter64,
    jnxMbgPgwV2ICsUnexpRptIETx      Counter64,
    jnxMbgPgwV2ICsGREKeyNtFdRx      Counter64,
    jnxMbgPgwV2ICsGREKeyNtFdTx      Counter64,
    jnxMbgPgwV2ICsRelocFailRx       Counter64,
    jnxMbgPgwV2ICsRelocFailTx       Counter64,
    jnxMbgPgwV2ICsDeniedINRatRx     Counter64,
    jnxMbgPgwV2ICsDeniedINRatTx     Counter64,
    jnxMbgPgwV2ICsPTNotSuppRx       Counter64,
    jnxMbgPgwV2ICsPTNotSuppTx       Counter64,
    jnxMbgPgwV2ICsAllDynAdOccRx     Counter64,
    jnxMbgPgwV2ICsAllDynAdOccTx     Counter64,
    jnxMbgPgwV2ICsNOTFTUECTXRx      Counter64,
    jnxMbgPgwV2ICsNOTFTUECTXTx      Counter64,
    jnxMbgPgwV2ICsProtoNtSupRx      Counter64,
    jnxMbgPgwV2ICsProtoNtSupTx      Counter64,
    jnxMbgPgwV2ICsUENotRespRx       Counter64,
    jnxMbgPgwV2ICsUENotRespTx       Counter64,
    jnxMbgPgwV2ICsUERefusesRx       Counter64,
    jnxMbgPgwV2ICsUERefusesTx       Counter64,
    jnxMbgPgwV2ICsServDeniedRx      Counter64,
    jnxMbgPgwV2ICsServDeniedTx      Counter64,
    jnxMbgPgwV2ICsUnabPageUERx      Counter64,
    jnxMbgPgwV2ICsUnabPageUETx      Counter64,
    jnxMbgPgwV2ICsNoMemRx           Counter64,
    jnxMbgPgwV2ICsNoMemTx           Counter64,
    jnxMbgPgwV2ICsUserAUTHFlRx      Counter64,
    jnxMbgPgwV2ICsUserAUTHFlTx      Counter64,
    jnxMbgPgwV2ICsAPNAcsDenRx       Counter64,
    jnxMbgPgwV2ICsAPNAcsDenTx       Counter64,
    jnxMbgPgwV2ICsReqRejRx          Counter64,
    jnxMbgPgwV2ICsReqRejTx          Counter64,
    jnxMbgPgwV2ICsPTMSISigMMRx      Counter64,
    jnxMbgPgwV2ICsPTMSISigMMTx      Counter64,
    jnxMbgPgwV2ICsIMSINotKnRx       Counter64,
    jnxMbgPgwV2ICsIMSINotKnTx       Counter64,
    jnxMbgPgwV2ICsCondIEMsRx        Counter64,
    jnxMbgPgwV2ICsCondIEMsTx        Counter64,
    jnxMbgPgwV2ICsAPNResTIncRx      Counter64,
    jnxMbgPgwV2ICsAPNResTIncTx      Counter64,
    jnxMbgPgwV2ICsUnknownRx         Counter64,
    jnxMbgPgwV2ICsUnknownTx         Counter64,
    jnxMbgPgwV1ProtocolErrRx        Counter64,
    jnxMbgPgwV1UnSupportedMsgRx     Counter64,
    jnxMbgPgwV1T3RespTmrExpRx       Counter64,
    jnxMbgPgwV1GlbNumMsgRx          Counter64,
    jnxMbgPgwV1GlbNumMsgTx          Counter64,
    jnxMbgPgwV1GlbNumBytesRx        Counter64,
    jnxMbgPgwV1GlbNumBytesTx        Counter64,
    jnxMbgPgwV1GlbEchoReqRx         Counter64,
    jnxMbgPgwV1GlbEchoReqTx         Counter64,
    jnxMbgPgwV1GlbEchoRespRx        Counter64,
    jnxMbgPgwV1GlbEchoRespTx        Counter64,
    jnxMbgPgwV1VerNotSupRx          Counter64,
    jnxMbgPgwV1VerNotSupTx          Counter64,
    jnxMbgPgwV1CrtPdpCxtReqRx       Counter64,
    jnxMbgPgwV1CrtPdpCxtReqTx       Counter64,
    jnxMbgPgwV1CrtPdpCxtRspRx       Counter64,
    jnxMbgPgwV1CrtPdpCxtRspTx       Counter64,
    jnxMbgPgwV1UpdPdpCxtReqRx       Counter64,
    jnxMbgPgwV1UpdPdpCxtReqTx       Counter64,
    jnxMbgPgwV1UpdPdpCxtRspRx       Counter64,
    jnxMbgPgwV1UpdPdpCxtRspTx       Counter64,
    jnxMbgPgwV1DelPdpCxtReqRx       Counter64,
    jnxMbgPgwV1DelPdpCxtReqTx       Counter64,
    jnxMbgPgwV1DelPdpCxtRspRx       Counter64,
    jnxMbgPgwV1DelPdpCxtRspTx       Counter64,
    jnxMbgPgwV1CrtAAPdpCxtReqRx     Counter64,
    jnxMbgPgwV1CrtAAPdpCxtReqTx     Counter64,
    jnxMbgPgwV1CrtAAPdpCxtRspRx     Counter64,
    jnxMbgPgwV1CrtAAPdpCxtRspTx     Counter64,
    jnxMbgPgwV1DelAAPdpCxtReqRx     Counter64,
    jnxMbgPgwV1DelAAPdpCxtReqTx     Counter64,
    jnxMbgPgwV1DelAAPdpCxtRspRx     Counter64,
    jnxMbgPgwV1DelAAPdpCxtRspTx     Counter64,
    jnxMbgPgwV1ErrorIndRx           Counter64,
    jnxMbgPgwV1ErrorIndTx           Counter64,
    jnxMbgPgwV1NotifReqRx           Counter64,
    jnxMbgPgwV1NotifReqTx           Counter64,
    jnxMbgPgwV1NotifRspRx           Counter64,
    jnxMbgPgwV1NotifRspTx           Counter64,
    jnxMbgPgwV1NotifRejReqRx        Counter64,
    jnxMbgPgwV1NotifRejReqTx        Counter64,
    jnxMbgPgwV1NotifRejRspRx        Counter64,
    jnxMbgPgwV1NotifRejRspTx        Counter64,
    jnxMbgPgwV1RtInfReqRx           Counter64,
    jnxMbgPgwV1RtInfReqTx           Counter64,
    jnxMbgPgwV1RtInfRspRx           Counter64,
    jnxMbgPgwV1RtInfRspTx           Counter64,
    jnxMbgPgwV1FailRptReqRx         Counter64,
    jnxMbgPgwV1FailRptReqTx         Counter64,
    jnxMbgPgwV1FailRptRspRx         Counter64,
    jnxMbgPgwV1FailRptRspTx         Counter64,
    jnxMbgPgwV1NotMSPresReqRx       Counter64,
    jnxMbgPgwV1NotMSPresReqTx       Counter64,
    jnxMbgPgwV1NotMSPresRspRx       Counter64,
    jnxMbgPgwV1NotMSPresRspTx       Counter64,
    jnxMbgPgwV1ICsReqAcceptedRx     Counter64,
    jnxMbgPgwV1ICsReqAcceptedTx     Counter64,
    jnxMbgPgwV1ICsNonExistRx        Counter64,
    jnxMbgPgwV1ICsNonExistTx        Counter64,
    jnxMbgPgwV1ICsInvMsgFmtRx       Counter64,
    jnxMbgPgwV1ICsInvMsgFmtTx       Counter64,
    jnxMbgPgwV1ICsIMSINotKnownRx    Counter64,
    jnxMbgPgwV1ICsIMSINotKnownTx    Counter64,
    jnxMbgPgwV1ICsMSGRPSDetachRx    Counter64,
    jnxMbgPgwV1ICsMSGRPSDetachTx    Counter64,
    jnxMbgPgwV1ICsMSNotGRPSRespRx   Counter64,
    jnxMbgPgwV1ICsMSNotGRPSRespTx   Counter64,
    jnxMbgPgwV1ICsMSRefusesRx       Counter64,
    jnxMbgPgwV1ICsMSRefusesTx       Counter64,
    jnxMbgPgwV1ICsVerNotSuppRx      Counter64,
    jnxMbgPgwV1ICsVerNotSuppTx      Counter64,
    jnxMbgPgwV1ICsNoResRx           Counter64,
    jnxMbgPgwV1ICsNoResTx           Counter64,
    jnxMbgPgwV1ICsServNotSuppRx     Counter64,
    jnxMbgPgwV1ICsServNotSuppTx     Counter64,
    jnxMbgPgwV1ICsManIEIncrtRx      Counter64,
    jnxMbgPgwV1ICsManIEIncrtTx      Counter64,
    jnxMbgPgwV1ICsManIEMissRx       Counter64,
    jnxMbgPgwV1ICsManIEMissTx       Counter64,
    jnxMbgPgwV1ICsOptIEIncrtRx      Counter64,
    jnxMbgPgwV1ICsOptIEIncrtTx      Counter64,
    jnxMbgPgwV1ICsSysFailRx         Counter64,
    jnxMbgPgwV1ICsSysFailTx         Counter64,
    jnxMbgPgwV1ICsRoamRestrictRx    Counter64,
    jnxMbgPgwV1ICsRoamRestrictTx    Counter64,
    jnxMbgPgwV1ICsPTMSISigMMRx      Counter64,
    jnxMbgPgwV1ICsPTMSISigMMTx      Counter64,
    jnxMbgPgwV1ICsGPRSConnSuppRx    Counter64,
    jnxMbgPgwV1ICsGPRSConnSuppTx    Counter64,
    jnxMbgPgwV1ICsAuthFailRx        Counter64,
    jnxMbgPgwV1ICsAuthFailTx        Counter64,
    jnxMbgPgwV1ICsUserAuthFailRx    Counter64,
    jnxMbgPgwV1ICsUserAuthFailTx    Counter64,
    jnxMbgPgwV1ICsCtxNotFndRx       Counter64,
    jnxMbgPgwV1ICsCtxNotFndTx       Counter64,
    jnxMbgPgwV1ICsAllDynPDPAdRx     Counter64,
    jnxMbgPgwV1ICsAllDynPDPAdTx     Counter64,
    jnxMbgPgwV1ICsNoMemRx           Counter64,
    jnxMbgPgwV1ICsNoMemTx           Counter64,
    jnxMbgPgwV1ICsRelocFailRx       Counter64,
    jnxMbgPgwV1ICsRelocFailTx       Counter64,
    jnxMbgPgwV1ICsUnkManExhdrRx     Counter64,
    jnxMbgPgwV1ICsUnkManExhdrTx     Counter64,
    jnxMbgPgwV1ICsSMANTTFTEr1Rx     Counter64,
    jnxMbgPgwV1ICsSMANTTFTEr1Tx     Counter64,
    jnxMbgPgwV1ICsSYNTFTErr2Rx      Counter64,
    jnxMbgPgwV1ICsSYNTFTErr2Tx      Counter64,
    jnxMbgPgwV1ICsSMNTPkFlEr1Rx     Counter64,
    jnxMbgPgwV1ICsSMNTPkFlEr1Tx     Counter64,
    jnxMbgPgwV1ICsSYNPkFlErr2Rx     Counter64,
    jnxMbgPgwV1ICsSYNPkFlErr2Tx     Counter64,
    jnxMbgPgwV1ICsMissUnknAPNRx     Counter64,
    jnxMbgPgwV1ICsMissUnknAPNTx     Counter64,
    jnxMbgPgwV1ICsUnknPDPAdRx       Counter64,
    jnxMbgPgwV1ICsUnknPDPAdTx       Counter64,
    jnxMbgPgwV1ICsNoTFTCtxExRx      Counter64,
    jnxMbgPgwV1ICsNoTFTCtxExTx      Counter64,
    jnxMbgPgwV0ProtocolErrRx        Counter64,
    jnxMbgPgwV0UnSupportedMsgRx     Counter64,
    jnxMbgPgwV0T3RespTmrExpRx       Counter64,
    jnxMbgPgwV0GlbNumMsgRx          Counter64,
    jnxMbgPgwV0GlbNumMsgTx          Counter64,
    jnxMbgPgwV0GlbNumBytesRx        Counter64,
    jnxMbgPgwV0GlbNumBytesTx        Counter64,
    jnxMbgPgwV0GlbEchoReqRx         Counter64,
    jnxMbgPgwV0GlbEchoReqTx         Counter64,
    jnxMbgPgwV0GlbEchoRespRx        Counter64,
    jnxMbgPgwV0GlbEchoRespTx        Counter64,
    jnxMbgPgwV0GlbVerNotSupRx       Counter64,
    jnxMbgPgwV0GlbVerNotSupTx       Counter64,
    jnxMbgPgwV0GlbCrtPdpCxtReqRx    Counter64,
    jnxMbgPgwV0GlbCrtPdpCxtReqTx    Counter64,
    jnxMbgPgwV0GlbCrtPdpCxtRspRx    Counter64,
    jnxMbgPgwV0GlbCrtPdpCxtRspTx    Counter64,
    jnxMbgPgwV0GlbUpdPdpCxtReqRx    Counter64,
    jnxMbgPgwV0GlbUpdPdpCxtReqTx    Counter64,
    jnxMbgPgwV0GlbUpdPdpCxtRspRx    Counter64,
    jnxMbgPgwV0GlbUpdPdpCxtRspTx    Counter64,
    jnxMbgPgwV0GlbDelPdpCxtReqRx    Counter64,
    jnxMbgPgwV0GlbDelPdpCxtReqTx    Counter64,
    jnxMbgPgwV0GlbDelPdpCxtRspRx    Counter64,
    jnxMbgPgwV0GlbDelPdpCxtRspTx    Counter64,
    jnxMbgPgwV0GlbCrtAAPdpCxtReqRx  Counter64,
    jnxMbgPgwV0GlbCrtAAPdpCxtReqTx  Counter64,
    jnxMbgPgwV0GlbCrtAAPdpCxtRspRx  Counter64,
    jnxMbgPgwV0GlbCrtAAPdpCxtRspTx  Counter64,
    jnxMbgPgwV0GlbDelAAPdpCxtReqRx  Counter64,
    jnxMbgPgwV0GlbDelAAPdpCxtReqTx  Counter64,
    jnxMbgPgwV0GlbDelAAPdpCxtRspRx  Counter64,
    jnxMbgPgwV0GlbDelAAPdpCxtRspTx  Counter64,
    jnxMbgPgwV0GlbErrorIndRx        Counter64,
    jnxMbgPgwV0GlbErrorIndTx        Counter64,
    jnxMbgPgwV0GlbNotifReqRx        Counter64,
    jnxMbgPgwV0GlbNotifReqTx        Counter64,
    jnxMbgPgwV0GlbNotifRspRx        Counter64,
    jnxMbgPgwV0GlbNotifRspTx        Counter64,
    jnxMbgPgwV0GlbNotifRejReqRx     Counter64,
    jnxMbgPgwV0GlbNotifRejReqTx     Counter64,
    jnxMbgPgwV0GlbNotifRejRspRx     Counter64,
    jnxMbgPgwV0GlbNotifRejRspTx     Counter64,
    jnxMbgPgwV0GlbRtInfReqRx        Counter64,
    jnxMbgPgwV0GlbRtInfReqTx        Counter64,
    jnxMbgPgwV0GlbRtInfRspRx        Counter64,
    jnxMbgPgwV0GlbRtInfRspTx        Counter64,
    jnxMbgPgwV0GlbFailRptReqRx      Counter64,
    jnxMbgPgwV0GlbFailRptReqTx      Counter64,
    jnxMbgPgwV0GlbFailRptRspRx      Counter64,
    jnxMbgPgwV0GlbFailRptRspTx      Counter64,
    jnxMbgPgwV0GlbNotMSPresReqRx    Counter64,
    jnxMbgPgwV0GlbNotMSPresReqTx    Counter64,
    jnxMbgPgwV0GlbNotMSPresRspRx    Counter64,
    jnxMbgPgwV0GlbNotMSPresRspTx    Counter64,
    jnxMbgPgwV0ICsReqAcceptedRx     Counter64,
    jnxMbgPgwV0ICsReqAcceptedTx     Counter64,
    jnxMbgPgwV0ICsNonExistRx        Counter64,
    jnxMbgPgwV0ICsNonExistTx        Counter64,
    jnxMbgPgwV0ICsInvMsgFmtRx       Counter64,
    jnxMbgPgwV0ICsInvMsgFmtTx       Counter64,
    jnxMbgPgwV0ICsIMSINotKnownRx    Counter64,
    jnxMbgPgwV0ICsIMSINotKnownTx    Counter64,
    jnxMbgPgwV0ICsMSGRPSDetachRx    Counter64,
    jnxMbgPgwV0ICsMSGRPSDetachTx    Counter64,
    jnxMbgPgwV0ICsMSNotGRPSRespRx   Counter64,
    jnxMbgPgwV0ICsMSNotGRPSRespTx   Counter64,
    jnxMbgPgwV0ICsMSRefusesRx       Counter64,
    jnxMbgPgwV0ICsMSRefusesTx       Counter64,
    jnxMbgPgwV0ICsVerNotSuppRx      Counter64,
    jnxMbgPgwV0ICsVerNotSuppTx      Counter64,
    jnxMbgPgwV0ICsNoResRx           Counter64,
    jnxMbgPgwV0ICsNoResTx           Counter64,
    jnxMbgPgwV0ICsServNotSuppRx     Counter64,
    jnxMbgPgwV0ICsServNotSuppTx     Counter64,
    jnxMbgPgwV0ICsManIEIncrtRx      Counter64,
    jnxMbgPgwV0ICsManIEIncrtTx      Counter64,
    jnxMbgPgwV0ICsManIEMissRx       Counter64,
    jnxMbgPgwV0ICsManIEMissTx       Counter64,
    jnxMbgPgwV0ICsOptIEIncrtRx      Counter64,
    jnxMbgPgwV0ICsOptIEIncrtTx      Counter64,
    jnxMbgPgwV0ICsSysFailRx         Counter64,
    jnxMbgPgwV0ICsSysFailTx         Counter64,
    jnxMbgPgwV0ICsRoamRestrictRx    Counter64,
    jnxMbgPgwV0ICsRoamRestrictTx    Counter64,
    jnxMbgPgwV0ICsPTMSISigMMRx      Counter64,
    jnxMbgPgwV0ICsPTMSISigMMTx      Counter64,
    jnxMbgPgwV0ICsGPRSConnSuppRx    Counter64,
    jnxMbgPgwV0ICsGPRSConnSuppTx    Counter64,
    jnxMbgPgwV0ICsAuthFailRx        Counter64,
    jnxMbgPgwV0ICsAuthFailTx        Counter64,
    jnxMbgPgwV0ICsUserAuthFailRx    Counter64,
    jnxMbgPgwV0ICsUserAuthFailTx    Counter64,
    jnxMbgPgwGtpV2ICsLclDetRx       Counter64,
    jnxMbgPgwGtpV2ICsLclDetTx       Counter64,
    jnxMbgPgwGtpV2ICsCmpDetRx       Counter64,
    jnxMbgPgwGtpV2ICsCmpDetTx       Counter64,
    jnxMbgPgwGtpV2ICsRATChgRx       Counter64,
    jnxMbgPgwGtpV2ICsRATChgTx       Counter64,
    jnxMbgPgwGtpV2ICsISRDeactRx     Counter64,
    jnxMbgPgwGtpV2ICsISRDeactTx     Counter64,
    jnxMbgPgwGtpV2ICsEIFRNCEnRx     Counter64,
    jnxMbgPgwGtpV2ICsEIFRNCEnTx     Counter64,
    jnxMbgPgwGtpV2ICsSemErTADRx     Counter64,
    jnxMbgPgwGtpV2ICsSemErTADTx     Counter64,
    jnxMbgPgwGtpV2ICsSynErTADRx     Counter64,
    jnxMbgPgwGtpV2ICsSynErTADTx     Counter64,
    jnxMbgPgwGtpV2ICsRMValRcvRx     Counter64,
    jnxMbgPgwGtpV2ICsRMValRcvTx     Counter64,
    jnxMbgPgwGtpV2ICsRPrNtRspRx     Counter64,
    jnxMbgPgwGtpV2ICsRPrNtRspTx     Counter64,
    jnxMbgPgwGtpV2ICsColNWReqRx     Counter64,
    jnxMbgPgwGtpV2ICsColNWReqTx     Counter64,
    jnxMbgPgwGtpV2ICsUnPgUESusRx    Counter64,
    jnxMbgPgwGtpV2ICsUnPgUESusTx    Counter64,
    jnxMbgPgwGtpV2ICsInvTotLenRx    Counter64,
    jnxMbgPgwGtpV2ICsInvTotLenTx    Counter64,
    jnxMbgPgwGtpV2ICsDtForNtSupRx   Counter64,
    jnxMbgPgwGtpV2ICsDtForNtSupTx   Counter64,
    jnxMbgPgwGtpV2ICsInReFRePrRx    Counter64,
    jnxMbgPgwGtpV2ICsInReFRePrTx    Counter64,
    jnxMbgPgwGtpV2ICsInvPrRx        Counter64,
    jnxMbgPgwGtpV2ICsInvPrTx        Counter64,
    jnxMbgPgwV1InitPdpCxtReqRx      Counter64,
    jnxMbgPgwV1InitPdpCxtReqTx      Counter64,
    jnxMbgPgwV1InitPdpCxtRspRx      Counter64,
    jnxMbgPgwV1InitPdpCxtRspTx      Counter64,
    jnxMbgPgwV2SuspNotifRx          Counter64,
    jnxMbgPgwV2SuspNotifTx          Counter64,
    jnxMbgPgwV2SuspAckRx            Counter64,
    jnxMbgPgwV2SuspAckTx            Counter64,
    jnxMbgPgwV2ResumeNotifRx        Counter64,
    jnxMbgPgwV2ResumeNotifTx        Counter64,
    jnxMbgPgwV2ResumeAckRx          Counter64,
    jnxMbgPgwV2ResumeAckTx          Counter64,
    jnxMbgPgwV2PiggybackMsgRx       Counter64,
    jnxMbgPgwV2PiggybackMsgTx       Counter64
}

jnxMbgPgwRxPacketsDropped  OBJECT-TYPE
    SYNTAX      Counter64
    MAX-ACCESS  read-only
    STATUS      current
    DESCRIPTION
    "Number of Received GTP Packets Dropped by the Gateway."
    ::= { jnxMbgPgwGtpGlbStatsEntry 1 }

jnxMbgPgwPacketAllocFail  OBJECT-TYPE
    SYNTAX      Counter64
    MAX-ACCESS  read-only
    STATUS      current
    DESCRIPTION
    "Number of Packet allocation failures in the Gateway."
    ::= { jnxMbgPgwGtpGlbStatsEntry 2 }

jnxMbgPgwPacketSendFail OBJECT-TYPE
    SYNTAX      Counter64
    MAX-ACCESS  read-only
    STATUS      current
    DESCRIPTION
    "Number of GTP Packet Send failures in the Gateway."
    ::= { jnxMbgPgwGtpGlbStatsEntry 3 }

jnxMbgPgwIPVerErrRx OBJECT-TYPE
    SYNTAX      Counter64
    MAX-ACCESS  read-only
    STATUS      current
    DESCRIPTION
    "Number of IP Version Error Packets Received."
    ::= { jnxMbgPgwGtpGlbStatsEntry 4 }

jnxMbgPgwIPProtoErrRx OBJECT-TYPE
    SYNTAX      Counter64
    MAX-ACCESS  read-only
    STATUS      current
    DESCRIPTION
    "Number of  IP Protocol Error packets Received."
    ::= { jnxMbgPgwGtpGlbStatsEntry 5 }

jnxMbgPgwGTPPortErrRx OBJECT-TYPE
    SYNTAX      Counter64
    MAX-ACCESS  read-only
    STATUS      current
    DESCRIPTION
    "Number of  Port Error Packets Received."
    ::= { jnxMbgPgwGtpGlbStatsEntry 6 }

jnxMbgPgwGTPUnknVerRx OBJECT-TYPE
    SYNTAX      Counter64
    MAX-ACCESS  read-only
    STATUS      current
    DESCRIPTION
    "Number of  Unknown Version Packets Received."
    ::= { jnxMbgPgwGtpGlbStatsEntry 7 }

jnxMbgPgwPcktLenErrRx OBJECT-TYPE
    SYNTAX      Counter64
    MAX-ACCESS  read-only
    STATUS      current
    DESCRIPTION
    "Number of Packet Length Error Packets Received."
    ::= { jnxMbgPgwGtpGlbStatsEntry 8 }

jnxMbgPgwUnknMsgRx OBJECT-TYPE
    SYNTAX      Counter64
    MAX-ACCESS  read-only
    STATUS      current
    DESCRIPTION
    "Number of  Unknown Messages Received."
    ::= { jnxMbgPgwGtpGlbStatsEntry 9 }

jnxMbgPgwV2ProtocolErrRx  OBJECT-TYPE
    SYNTAX      Counter64
    MAX-ACCESS  read-only
    STATUS      current
    DESCRIPTION
    "Number of GTPv2 Protocol Errors Received."
    ::= { jnxMbgPgwGtpGlbStatsEntry 10 }

jnxMbgPgwV2UnSupportedMsgRx  OBJECT-TYPE
    SYNTAX      Counter64
    MAX-ACCESS  read-only
    STATUS      current
    DESCRIPTION
    "Number of GTPv2 Unsupported Messages received."
    ::= { jnxMbgPgwGtpGlbStatsEntry 11 }

jnxMbgPgwV2T3RespTmrExpRx  OBJECT-TYPE
    SYNTAX      Counter64
    MAX-ACCESS  read-only
    STATUS      current
    DESCRIPTION
    "GTP V2 Number of T3 timer expiries Received."
    ::= { jnxMbgPgwGtpGlbStatsEntry 12 }

jnxMbgPgwV2GlbNumMsgRx  OBJECT-TYPE
    SYNTAX      Counter64
    MAX-ACCESS  read-only
    STATUS      current
    DESCRIPTION
    "Number of GTPv2 messages received."
    ::= { jnxMbgPgwGtpGlbStatsEntry 13 }

jnxMbgPgwV2GlbNumMsgTx  OBJECT-TYPE
    SYNTAX      Counter64
    MAX-ACCESS  read-only
    STATUS      current
    DESCRIPTION
    "Number of GTPV2 messages sent."
    ::= { jnxMbgPgwGtpGlbStatsEntry 14 }

jnxMbgPgwV2GlbNumBytesRx  OBJECT-TYPE
    SYNTAX      Counter64
    MAX-ACCESS  read-only
    STATUS      current
    DESCRIPTION
    "Number of GTPv2 bytes received."
    ::= { jnxMbgPgwGtpGlbStatsEntry 15 }

jnxMbgPgwV2GlbNumBytesTx  OBJECT-TYPE
    SYNTAX      Counter64
    MAX-ACCESS  read-only
    STATUS      current
    DESCRIPTION
    "Number of GTPV2 bytes sent."
    ::= { jnxMbgPgwGtpGlbStatsEntry 16 }

jnxMbgPgwV2GlbEchoReqRx  OBJECT-TYPE
    SYNTAX      Counter64
    MAX-ACCESS  read-only
    STATUS      current
    DESCRIPTION
    "Number of GTP V2 Echo Request received."
    ::= { jnxMbgPgwGtpGlbStatsEntry 19 }

jnxMbgPgwV2GlbEchoReqTx  OBJECT-TYPE
    SYNTAX      Counter64
    MAX-ACCESS  read-only
    STATUS      current
    DESCRIPTION
    "Number of GTP V2 Echo Request Sent."
    ::= { jnxMbgPgwGtpGlbStatsEntry 20 }

jnxMbgPgwV2GlbEchoRespRx  OBJECT-TYPE
    SYNTAX      Counter64
    MAX-ACCESS  read-only
    STATUS      current
    DESCRIPTION
    "Number of GTP V2 Echo Response received."
    ::= { jnxMbgPgwGtpGlbStatsEntry 21 }

jnxMbgPgwV2GlbEchoRespTx  OBJECT-TYPE
    SYNTAX      Counter64
    MAX-ACCESS  read-only
    STATUS      current
    DESCRIPTION
    "Number of GTP V2 Echo Response Sent."
    ::= { jnxMbgPgwGtpGlbStatsEntry 22 }

jnxMbgPgwV2VerNotSupRx OBJECT-TYPE
    SYNTAX      Counter64
    MAX-ACCESS  read-only
    STATUS      current
    DESCRIPTION
    "Number of GTP V2 Version Not supported messages received"
    ::= { jnxMbgPgwGtpGlbStatsEntry 23 }

jnxMbgPgwV2VerNotSupTx OBJECT-TYPE
    SYNTAX      Counter64
    MAX-ACCESS  read-only
    STATUS      current
    DESCRIPTION
    "Number of GTP V2 version not supported messages Sent."
    ::= { jnxMbgPgwGtpGlbStatsEntry 24 }

jnxMbgPgwV2CreateSessReqRx  OBJECT-TYPE
    SYNTAX      Counter64
    MAX-ACCESS  read-only
    STATUS      current
    DESCRIPTION
    "Number of GTP V2 Create Session Requests received."
    ::= { jnxMbgPgwGtpGlbStatsEntry 25 }

jnxMbgPgwV2CreateSessReqTx  OBJECT-TYPE
    SYNTAX      Counter64
    MAX-ACCESS  read-only
    STATUS      current
    DESCRIPTION
    "Number of GTP V2 Create Session Requests Sent."
    ::= { jnxMbgPgwGtpGlbStatsEntry 26 }

jnxMbgPgwV2CreateSessRspRx  OBJECT-TYPE
    SYNTAX      Counter64
    MAX-ACCESS  read-only
    STATUS      current
    DESCRIPTION
    "Number of GTP V2 Create Session Responses received."
    ::= { jnxMbgPgwGtpGlbStatsEntry 27 }

jnxMbgPgwV2CreateSessRspTx  OBJECT-TYPE
    SYNTAX      Counter64
    MAX-ACCESS  read-only
    STATUS      current
    DESCRIPTION
    "Number of GTP V2 Create Session Responses Sent."
    ::= { jnxMbgPgwGtpGlbStatsEntry 28 }

jnxMbgPgwV2ModBrReqRx  OBJECT-TYPE
    SYNTAX      Counter64
    MAX-ACCESS  read-only
    STATUS      current
    DESCRIPTION
    "Number of GTP V2 Modify Bearer Requests received."
    ::= { jnxMbgPgwGtpGlbStatsEntry 29 }

jnxMbgPgwV2ModBrReqTx  OBJECT-TYPE
    SYNTAX      Counter64
    MAX-ACCESS  read-only
    STATUS      current
    DESCRIPTION
    "Number of GTP V2 Modify Bearer Requests Sent."
    ::= { jnxMbgPgwGtpGlbStatsEntry 30 }

jnxMbgPgwV2ModBrRspRx  OBJECT-TYPE
    SYNTAX      Counter64
    MAX-ACCESS  read-only
    STATUS      current
    DESCRIPTION
    "Number of GTP V2 Modify Bearer Responses received."
    ::= { jnxMbgPgwGtpGlbStatsEntry 31 }

jnxMbgPgwV2ModBrRspTx  OBJECT-TYPE
    SYNTAX      Counter64
    MAX-ACCESS  read-only
    STATUS      current
    DESCRIPTION
    "Number of GTP V2 Modify Bearer Responses Sent."
    ::= { jnxMbgPgwGtpGlbStatsEntry 32 }

jnxMbgPgwV2DelSessReqRx  OBJECT-TYPE
    SYNTAX      Counter64
    MAX-ACCESS  read-only
    STATUS      current
    DESCRIPTION
    "Number of GTP V2 Delete Session Requests received."
    ::= { jnxMbgPgwGtpGlbStatsEntry 33 }

jnxMbgPgwV2DelSessReqTx  OBJECT-TYPE
    SYNTAX      Counter64
    MAX-ACCESS  read-only
    STATUS      current
    DESCRIPTION
    "Number of GTP V2 Delete Session Requests Sent."
    ::= { jnxMbgPgwGtpGlbStatsEntry 34 }

jnxMbgPgwV2DelSessRspRx  OBJECT-TYPE
    SYNTAX      Counter64
    MAX-ACCESS  read-only
    STATUS      current
    DESCRIPTION
    "Number of GTP V2 Delete Session Responses received."
    ::= { jnxMbgPgwGtpGlbStatsEntry 35 }

jnxMbgPgwV2DelSessRspTx  OBJECT-TYPE
    SYNTAX      Counter64
    MAX-ACCESS  read-only
    STATUS      current
    DESCRIPTION
    "Number of GTP V2 Delete Session Responses Sent."
    ::= { jnxMbgPgwGtpGlbStatsEntry 36 }

jnxMbgPgwV2CrtBrReqRx  OBJECT-TYPE
    SYNTAX      Counter64
    MAX-ACCESS  read-only
    STATUS      current
    DESCRIPTION
    "Number of GTP V2 Create Bearer Requests received."
    ::= { jnxMbgPgwGtpGlbStatsEntry 37 }

jnxMbgPgwV2CrtBrReqTx  OBJECT-TYPE
    SYNTAX      Counter64
    MAX-ACCESS  read-only
    STATUS      current
    DESCRIPTION
    "Number of GTP V2 Create Bearer Requests Sent."
    ::= { jnxMbgPgwGtpGlbStatsEntry 38 }

jnxMbgPgwV2CrtBrRspRx  OBJECT-TYPE
    SYNTAX      Counter64
    MAX-ACCESS  read-only
    STATUS      current
    DESCRIPTION
    "Number of GTP V2 Create Bearer Responses received."
    ::= { jnxMbgPgwGtpGlbStatsEntry 39 }

jnxMbgPgwV2CrtBrRspTx  OBJECT-TYPE
    SYNTAX      Counter64
    MAX-ACCESS  read-only
    STATUS      current
    DESCRIPTION
    "Number of GTP V2 Create Bearer Responses Sent."
    ::= { jnxMbgPgwGtpGlbStatsEntry 40 }

jnxMbgPgwV2UpdBrReqRx  OBJECT-TYPE
    SYNTAX      Counter64
    MAX-ACCESS  read-only
    STATUS      current
    DESCRIPTION
    "Number of GTP V2 Update Bearer Requests received."
    ::= { jnxMbgPgwGtpGlbStatsEntry 41 }

jnxMbgPgwV2UpdBrReqTx  OBJECT-TYPE
    SYNTAX      Counter64
    MAX-ACCESS  read-only
    STATUS      current
    DESCRIPTION
    "Number of GTP V2 Update Bearer Requests Sent."
    ::= { jnxMbgPgwGtpGlbStatsEntry 42 }

jnxMbgPgwV2UpdBrRspRx  OBJECT-TYPE
    SYNTAX      Counter64
    MAX-ACCESS  read-only
    STATUS      current
    DESCRIPTION
    "Number of GTP V2 Update Bearer Responses received."
    ::= { jnxMbgPgwGtpGlbStatsEntry 43 }

jnxMbgPgwV2UpdBrRspTx  OBJECT-TYPE
    SYNTAX      Counter64
    MAX-ACCESS  read-only
    STATUS      current
    DESCRIPTION
    "Number of GTP V2 Update Bearer Responses Sent."
    ::= { jnxMbgPgwGtpGlbStatsEntry 44 }

jnxMbgPgwV2DelBrReqRx  OBJECT-TYPE
    SYNTAX      Counter64
    MAX-ACCESS  read-only
    STATUS      current
    DESCRIPTION
    "Number of GTP V2 Delete Bearer Requests received."
    ::= { jnxMbgPgwGtpGlbStatsEntry 45 }

jnxMbgPgwV2DelBrReqTx  OBJECT-TYPE
    SYNTAX      Counter64
    MAX-ACCESS  read-only
    STATUS      current
    DESCRIPTION
    "Number of GTP V2 Delete Bearer Requests Sent."
    ::= { jnxMbgPgwGtpGlbStatsEntry 46 }

jnxMbgPgwV2DelBrRspRx  OBJECT-TYPE
    SYNTAX      Counter64
    MAX-ACCESS  read-only
    STATUS      current
    DESCRIPTION
    "Number of GTP V2 Delete Bearer Responses received."
    ::= { jnxMbgPgwGtpGlbStatsEntry 47 }

jnxMbgPgwV2DelBrRspTx  OBJECT-TYPE
    SYNTAX      Counter64
    MAX-ACCESS  read-only
    STATUS      current
    DESCRIPTION
    "Number of GTP V2 Delete Bearer Responses Sent."
    ::= { jnxMbgPgwGtpGlbStatsEntry 48 }

jnxMbgPgwV2DelConnSetReqRx  OBJECT-TYPE
    SYNTAX      Counter64
    MAX-ACCESS  read-only
    STATUS      current
    DESCRIPTION
    "Number of GTP V2 Delete PDN connection set Requests received."
    ::= { jnxMbgPgwGtpGlbStatsEntry 49 }

jnxMbgPgwV2DelConnSetReqTx  OBJECT-TYPE
    SYNTAX      Counter64
    MAX-ACCESS  read-only
    STATUS      current
    DESCRIPTION
    "Number of GTP V2 Delete PDN connection set Requests Sent."
    ::= { jnxMbgPgwGtpGlbStatsEntry 50 }

jnxMbgPgwV2DelConnSetRspRx  OBJECT-TYPE
    SYNTAX      Counter64
    MAX-ACCESS  read-only
    STATUS      current
    DESCRIPTION
    "Number of GTP V2 Delete PDN connection set Responses received."
    ::= { jnxMbgPgwGtpGlbStatsEntry 51 }

jnxMbgPgwV2DelConnSetRspTx  OBJECT-TYPE
    SYNTAX      Counter64
    MAX-ACCESS  read-only
    STATUS      current
    DESCRIPTION
    "Number of GTP V2 Delete PDN connection set Responses Sent."
    ::= { jnxMbgPgwGtpGlbStatsEntry 52 }

jnxMbgPgwV2UpdConnSetReqRx  OBJECT-TYPE
    SYNTAX      Counter64
    MAX-ACCESS  read-only
    STATUS      current
    DESCRIPTION
    "Number of GTP V2 Update Connection set Request received."
    ::= { jnxMbgPgwGtpGlbStatsEntry 53 }

jnxMbgPgwV2UpdConnSetReqTx  OBJECT-TYPE
    SYNTAX      Counter64
    MAX-ACCESS  read-only
    STATUS      current
    DESCRIPTION
    "Number of GTP V2 Update Connection set Requests Sent."
    ::= { jnxMbgPgwGtpGlbStatsEntry 54 }

jnxMbgPgwV2UpdConnSetRspRx  OBJECT-TYPE
    SYNTAX      Counter64
    MAX-ACCESS  read-only
    STATUS      current
    DESCRIPTION
    "Number of GTP V2 Update Connetion set Responses received."
    ::= { jnxMbgPgwGtpGlbStatsEntry 55 }

jnxMbgPgwV2UpdConnSetRspTx  OBJECT-TYPE
    SYNTAX      Counter64
    MAX-ACCESS  read-only
    STATUS      current
    DESCRIPTION
    "Number of GTP V2 Update Connection set Responses Sent."
    ::= { jnxMbgPgwGtpGlbStatsEntry 56 }

jnxMbgPgwV2ModBrCmdRx  OBJECT-TYPE
    SYNTAX      Counter64
    MAX-ACCESS  read-only
    STATUS      current
    DESCRIPTION
    "Number of GTP V2 Modify Bearer Command received."
    ::= { jnxMbgPgwGtpGlbStatsEntry 57 }

jnxMbgPgwV2ModBrCmdTx  OBJECT-TYPE
    SYNTAX      Counter64
    MAX-ACCESS  read-only
    STATUS      current
    DESCRIPTION
    "Number of GTP V2 Modify Bearer Command Sent."
    ::= { jnxMbgPgwGtpGlbStatsEntry 58 }

jnxMbgPgwV2ModBrFlrIndRx  OBJECT-TYPE
    SYNTAX      Counter64
    MAX-ACCESS  read-only
    STATUS      current
    DESCRIPTION
    "Number of GTP V2 Modify Bearer Failure received."
    ::= { jnxMbgPgwGtpGlbStatsEntry 59 }

jnxMbgPgwV2ModBrFlrIndTx  OBJECT-TYPE
    SYNTAX      Counter64
    MAX-ACCESS  read-only
    STATUS      current
    DESCRIPTION
    "Number of GTP V2 Modify Bearer Failure Sent."
    ::= { jnxMbgPgwGtpGlbStatsEntry 60 }

jnxMbgPgwV2DelBrCmdRx  OBJECT-TYPE
    SYNTAX      Counter64
    MAX-ACCESS  read-only
    STATUS      current
    DESCRIPTION
    "Number of GTP V2 Delete Bearer Command received."
    ::= { jnxMbgPgwGtpGlbStatsEntry 61 }

jnxMbgPgwV2DelBrCmdTx  OBJECT-TYPE
    SYNTAX      Counter64
    MAX-ACCESS  read-only
    STATUS      current
    DESCRIPTION
    "Number of GTP V2 Delete Bearer Command Sent."
    ::= { jnxMbgPgwGtpGlbStatsEntry 62 }

jnxMbgPgwV2DelBrFlrIndRx  OBJECT-TYPE
    SYNTAX      Counter64
    MAX-ACCESS  read-only
    STATUS      current
    DESCRIPTION
    "Number of GTP V2 Delete Bearer Failure received."
    ::= { jnxMbgPgwGtpGlbStatsEntry 63 }

jnxMbgPgwV2DelBrFlrIndTx  OBJECT-TYPE
    SYNTAX      Counter64
    MAX-ACCESS  read-only
    STATUS      current
    DESCRIPTION
    "Number of GTP V2 Delete Bearer Failure Sent."
    ::= { jnxMbgPgwGtpGlbStatsEntry 64 }

jnxMbgPgwV2BrResCmdRx  OBJECT-TYPE
    SYNTAX      Counter64
    MAX-ACCESS  read-only
    STATUS      current
    DESCRIPTION
    "Number of GTP V2 Bearer Response Command received."
    ::= { jnxMbgPgwGtpGlbStatsEntry 65 }

jnxMbgPgwV2BrResCmdTx  OBJECT-TYPE
    SYNTAX      Counter64
    MAX-ACCESS  read-only
    STATUS      current
    DESCRIPTION
    "Number of GTP V2 Bearer Response Command Sent."
    ::= { jnxMbgPgwGtpGlbStatsEntry 66 }

jnxMbgPgwV2BrResFlrIndRx  OBJECT-TYPE
    SYNTAX      Counter64
    MAX-ACCESS  read-only
    STATUS      current
    DESCRIPTION
    "Number of GTP V2 Bearer Resource Failure received."
    ::= { jnxMbgPgwGtpGlbStatsEntry 67 }

jnxMbgPgwV2BrResFlrIndTx  OBJECT-TYPE
    SYNTAX      Counter64
    MAX-ACCESS  read-only
    STATUS      current
    DESCRIPTION
    "Number of GTP V2 Bearer Resource Failure Sent."
    ::= { jnxMbgPgwGtpGlbStatsEntry 68 }

jnxMbgPgwV2RelAcsBrReqRx OBJECT-TYPE
    SYNTAX      Counter64
    MAX-ACCESS  read-only
    STATUS      obsolete
    DESCRIPTION
    "Number of GTP V2 Release Access Bearer Requests received."
    ::= { jnxMbgPgwGtpGlbStatsEntry 69 }

jnxMbgPgwV2RelAcsBrReqTx OBJECT-TYPE
    SYNTAX      Counter64
    MAX-ACCESS  read-only
    STATUS      obsolete
    DESCRIPTION
    "Number of GTP V2 Release Access Bearer Requests Sent."
    ::= { jnxMbgPgwGtpGlbStatsEntry 70 }

jnxMbgPgwV2RelAcsBrRespRx OBJECT-TYPE
    SYNTAX      Counter64
    MAX-ACCESS  read-only
    STATUS      obsolete
    DESCRIPTION
    "Number of GTP V2 Release Access Bearer Responses received."
    ::= { jnxMbgPgwGtpGlbStatsEntry 71 }

jnxMbgPgwV2RelAcsBrRespTx OBJECT-TYPE
    SYNTAX      Counter64
    MAX-ACCESS  read-only
    STATUS      obsolete
    DESCRIPTION
    "Number of GTP V2 Release Access Bearer Responses Sent."
    ::= { jnxMbgPgwGtpGlbStatsEntry 72 }

jnxMbgPgwV2CrIndTunReqRx OBJECT-TYPE
    SYNTAX      Counter64
    MAX-ACCESS  read-only
    STATUS      obsolete
    DESCRIPTION
    "Number of GTP V2 Create Indirect Tunnel Forward Requests Received"
    ::= { jnxMbgPgwGtpGlbStatsEntry 73 }

jnxMbgPgwV2CrIndTunReqTx OBJECT-TYPE
    SYNTAX      Counter64
    MAX-ACCESS  read-only
    STATUS      obsolete
    DESCRIPTION
    "Number of GTP V2 Create Indirect Tunnel Forward Requests Sent"
    ::= { jnxMbgPgwGtpGlbStatsEntry 74 }

jnxMbgPgwV2CrIndTunRespRx  OBJECT-TYPE
    SYNTAX      Counter64
    MAX-ACCESS  read-only
    STATUS      obsolete
    DESCRIPTION
    "Number of GTP V2 Create Indirect Tunnel Forward Responses Received"
    ::= { jnxMbgPgwGtpGlbStatsEntry 75 }

jnxMbgPgwV2CrIndTunRespTx  OBJECT-TYPE
    SYNTAX      Counter64
    MAX-ACCESS  read-only
    STATUS      obsolete
    DESCRIPTION
    "Number of GTP V2 Create Indirect Tunnel Forward Responses Sent"
    ::= { jnxMbgPgwGtpGlbStatsEntry 76 }

jnxMbgPgwV2DelIndTunReqRx OBJECT-TYPE
    SYNTAX      Counter64
    MAX-ACCESS  read-only
    STATUS      obsolete
    DESCRIPTION
    "Number of GTP V2 Delete Indirect Tunnel Forward Request Received"
    ::= { jnxMbgPgwGtpGlbStatsEntry 77 }

jnxMbgPgwV2DelIndTunReqTx OBJECT-TYPE
    SYNTAX      Counter64
    MAX-ACCESS  read-only
    STATUS      obsolete
    DESCRIPTION
    "Number of GTP V2 Delete Indirect Tunnel Forward Requests Sent."
    ::= { jnxMbgPgwGtpGlbStatsEntry 78 }

jnxMbgPgwV2DelIndTunRespRx  OBJECT-TYPE
    SYNTAX      Counter64
    MAX-ACCESS  read-only
    STATUS      obsolete
    DESCRIPTION
    "Number of GTP V2 Delete Indirect Tunnel Forward Responses Received"
    ::= { jnxMbgPgwGtpGlbStatsEntry 79 }

jnxMbgPgwV2DelIndTunRespTx  OBJECT-TYPE
    SYNTAX      Counter64
    MAX-ACCESS  read-only
    STATUS      obsolete
    DESCRIPTION
    "Number of GTP V2 Delete Indirect Tunnel Forward Responses Sent."
    ::= { jnxMbgPgwGtpGlbStatsEntry 80 }

jnxMbgPgwV2DlDataNotifRx  OBJECT-TYPE
    SYNTAX      Counter64
    MAX-ACCESS  read-only
    STATUS      obsolete
    DESCRIPTION
    "Number of GTP V2 Downlink Data Notify received."
    ::= { jnxMbgPgwGtpGlbStatsEntry 81 }

jnxMbgPgwV2DlDataNotifTx  OBJECT-TYPE
    SYNTAX      Counter64
    MAX-ACCESS  read-only
    STATUS      obsolete
    DESCRIPTION
    "Number of GTP V2 Downlink Data Notify Sent."
    ::= { jnxMbgPgwGtpGlbStatsEntry 82 }

jnxMbgPgwV2DlDataAckRx  OBJECT-TYPE
    SYNTAX      Counter64
    MAX-ACCESS  read-only
    STATUS      obsolete
    DESCRIPTION
    "Number of GTP V2 Downlink Data Notify Acknowledgements received."
    ::= { jnxMbgPgwGtpGlbStatsEntry 83 }

jnxMbgPgwV2DlDataAckTx  OBJECT-TYPE
    SYNTAX      Counter64
    MAX-ACCESS  read-only
    STATUS      obsolete
    DESCRIPTION
    "Number of GTP V2 Downlink Data Notify Acknowledgements Sent."
    ::= { jnxMbgPgwGtpGlbStatsEntry 84 }

jnxMbgPgwV2DlDataNotiFlrIndRx  OBJECT-TYPE
    SYNTAX      Counter64
    MAX-ACCESS  read-only
    STATUS      obsolete
    DESCRIPTION
    "Number of GTP V2 Downlink Data Notification failures received."
    ::= { jnxMbgPgwGtpGlbStatsEntry 85 }

jnxMbgPgwV2DlDataNotiFlrIndTx  OBJECT-TYPE
    SYNTAX      Counter64
    MAX-ACCESS  read-only
    STATUS      obsolete
    DESCRIPTION
    "Number of GTP V2 Downlink Data Notification failures Sent."
    ::= { jnxMbgPgwGtpGlbStatsEntry 86 }

jnxMbgPgwV2StopPagingIndRx OBJECT-TYPE
    SYNTAX      Counter64
    MAX-ACCESS  read-only
    STATUS      obsolete
    DESCRIPTION
    "Number of GTP V2 Stop Paging Indication Messages Received."
    ::= { jnxMbgPgwGtpGlbStatsEntry 87 }

jnxMbgPgwV2StopPagingIndTx  OBJECT-TYPE
    SYNTAX      Counter64
    MAX-ACCESS  read-only
    STATUS      obsolete
    DESCRIPTION
    "Number of GTP V2 Stop Paging Indicaton messages Transmitted"
    ::= { jnxMbgPgwGtpGlbStatsEntry 88 }

jnxMbgPgwV2ICsPageRx  OBJECT-TYPE
    SYNTAX      Counter64
    MAX-ACCESS  read-only
    STATUS      obsolete
    DESCRIPTION
    "Number of GTPV2 packets received with cause Page."
    ::= { jnxMbgPgwGtpGlbStatsEntry 89 }

jnxMbgPgwV2ICsPageTx  OBJECT-TYPE
    SYNTAX      Counter64
    MAX-ACCESS  read-only
    STATUS      obsolete
    DESCRIPTION
    "Number of GTPV2 packets sent with cause Page."
    ::= { jnxMbgPgwGtpGlbStatsEntry 90 }

jnxMbgPgwV2ICsReqAcceptRx  OBJECT-TYPE
    SYNTAX      Counter64
    MAX-ACCESS  read-only
    STATUS      current
    DESCRIPTION
    "Number of GTPV2 packets received with cause Request Accept."
    ::= { jnxMbgPgwGtpGlbStatsEntry 91 }

jnxMbgPgwV2ICsReqAcceptTx  OBJECT-TYPE
    SYNTAX      Counter64
    MAX-ACCESS  read-only
    STATUS      current
    DESCRIPTION
    "Number of GTPV2 packets sent with cause Request Accept messsges sent."
    ::= { jnxMbgPgwGtpGlbStatsEntry 92 }

jnxMbgPgwV2ICsAcceptPartRx  OBJECT-TYPE
    SYNTAX      Counter64
    MAX-ACCESS  read-only
    STATUS      current
    DESCRIPTION
    "Number of GTPV2 packets received with cause Accept Partial messages receive."
    ::= { jnxMbgPgwGtpGlbStatsEntry 93 }

jnxMbgPgwV2ICsAcceptPartTx  OBJECT-TYPE
    SYNTAX      Counter64
    MAX-ACCESS  read-only
    STATUS      current
    DESCRIPTION
    "Number of GTPV2 packets sent with cause Accept Partial."
    ::= { jnxMbgPgwGtpGlbStatsEntry 94 }

jnxMbgPgwV2ICsNewPTNPrefRx  OBJECT-TYPE
    SYNTAX      Counter64
    MAX-ACCESS  read-only
    STATUS      current
    DESCRIPTION
    "Number of GTPV2 packets received with cause New PDN type due to Network Preference."
    ::= { jnxMbgPgwGtpGlbStatsEntry 95 }

jnxMbgPgwV2ICsNewPTNPrefTx  OBJECT-TYPE
    SYNTAX      Counter64
    MAX-ACCESS  read-only
    STATUS      current
    DESCRIPTION
    "Number of GTPV2 packets sent with cause New PDN type due to Network Preference."
    ::= { jnxMbgPgwGtpGlbStatsEntry 96 }


jnxMbgPgwV2ICsNewPTSIAdbrRx  OBJECT-TYPE
    SYNTAX      Counter64
    MAX-ACCESS  read-only
    STATUS      current
    DESCRIPTION
    "Number of GTPV2 packets received with cause New PDN type due to Single Address Bearer."
    ::= { jnxMbgPgwGtpGlbStatsEntry 97 }

jnxMbgPgwV2ICsNewPTSIAdbrTx  OBJECT-TYPE
    SYNTAX      Counter64
    MAX-ACCESS  read-only
    STATUS      current
    DESCRIPTION
    "Number of GTPV2 packets sent with cause New PDN type due to Single Address Bearer."
    ::= { jnxMbgPgwGtpGlbStatsEntry 98 }

jnxMbgPgwV2ICsCtxNotFndRx  OBJECT-TYPE
    SYNTAX      Counter64
    MAX-ACCESS  read-only
    STATUS      current
    DESCRIPTION
    "Number of  GTPV2 packets received with cause Context not found."
    ::= { jnxMbgPgwGtpGlbStatsEntry 99 }

jnxMbgPgwV2ICsCtxNotFndTx  OBJECT-TYPE
    SYNTAX      Counter64
    MAX-ACCESS  read-only
    STATUS      current
    DESCRIPTION
    "Number of GTPV2 packets sent with cause Context not found."
    ::= { jnxMbgPgwGtpGlbStatsEntry 100 }

jnxMbgPgwV2ICsInvMsgFmtRx  OBJECT-TYPE
    SYNTAX      Counter64
    MAX-ACCESS  read-only
    STATUS      current
    DESCRIPTION
    "Number of GTPV2 packets received with cause Invalid Message Format."
    ::= { jnxMbgPgwGtpGlbStatsEntry 101 }

jnxMbgPgwV2ICsInvMsgFmtTx  OBJECT-TYPE
    SYNTAX      Counter64
    MAX-ACCESS  read-only
    STATUS      current
    DESCRIPTION
    "Number of GTPV2 packets sent with cause Invalid Message Format."
    ::= { jnxMbgPgwGtpGlbStatsEntry 102 }

jnxMbgPgwV2ICsVerNotSuppRx  OBJECT-TYPE
    SYNTAX      Counter64
    MAX-ACCESS  read-only
    STATUS      current
    DESCRIPTION
    "Number of GTPV2 packets received with cause Version not Supported."
    ::= { jnxMbgPgwGtpGlbStatsEntry 103 }

jnxMbgPgwV2ICsVerNotSuppTx  OBJECT-TYPE
    SYNTAX      Counter64
    MAX-ACCESS  read-only
    STATUS      current
    DESCRIPTION
    "Number of GTPV2 packets sent with cause Version not Supported."
    ::= { jnxMbgPgwGtpGlbStatsEntry 104 }

jnxMbgPgwV2ICsInvLenRx  OBJECT-TYPE
    SYNTAX      Counter64
    MAX-ACCESS  read-only
    STATUS      current
    DESCRIPTION
    "Number of GTPV2 packets received with cause Invalid Length."
    ::= { jnxMbgPgwGtpGlbStatsEntry 105 }

jnxMbgPgwV2ICsInvLenTx  OBJECT-TYPE
    SYNTAX      Counter64
    MAX-ACCESS  read-only
    STATUS      current
    DESCRIPTION
    "Number of GTPV2 packets sent with cause Invalid Length."
    ::= { jnxMbgPgwGtpGlbStatsEntry 106 }

jnxMbgPgwV2ICsServNotSuppRx  OBJECT-TYPE
    SYNTAX      Counter64
    MAX-ACCESS  read-only
    STATUS      current
    DESCRIPTION
    "Number of GTPV2 packets received with cause Service Not supported."
    ::= { jnxMbgPgwGtpGlbStatsEntry 107 }

jnxMbgPgwV2ICsServNotSuppTx  OBJECT-TYPE
    SYNTAX      Counter64
    MAX-ACCESS  read-only
    STATUS      current
    DESCRIPTION
    "Number of GTPV2 packets sent with cause Service Not supported."
    ::= { jnxMbgPgwGtpGlbStatsEntry 108 }

jnxMbgPgwV2ICsManIEIncorrRx  OBJECT-TYPE
    SYNTAX      Counter64
    MAX-ACCESS  read-only
    STATUS      current
    DESCRIPTION
    "Number of GTPV2 packets received with cause Mandatory IE incorrect."
    ::= { jnxMbgPgwGtpGlbStatsEntry 109 }

jnxMbgPgwV2ICsManIEIncorrTx  OBJECT-TYPE
    SYNTAX      Counter64
    MAX-ACCESS  read-only
    STATUS      current
    DESCRIPTION
    "Number of GTPV2 packets sent with cause Mandatory IE incorrect."
    ::= { jnxMbgPgwGtpGlbStatsEntry 110 }

jnxMbgPgwV2ICsManIEMissRx  OBJECT-TYPE
    SYNTAX      Counter64
    MAX-ACCESS  read-only
    STATUS      current
    DESCRIPTION
    "Number of GTPV2 packets received with cause Mandatory IE Missing."
    ::= { jnxMbgPgwGtpGlbStatsEntry 111 }

jnxMbgPgwV2ICsManIEMissTx  OBJECT-TYPE
    SYNTAX      Counter64
    MAX-ACCESS  read-only
    STATUS      current
    DESCRIPTION
    "Number of GTPV2 packets sent with cause Mandatory IE Missing."
    ::= { jnxMbgPgwGtpGlbStatsEntry 112 }

jnxMbgPgwV2ICsOptIEIncorrRx  OBJECT-TYPE
    SYNTAX      Counter64
    MAX-ACCESS  read-only
    STATUS      current
    DESCRIPTION
    "Number of GTPV2 packets received with cause Optional IE Incorrect."
    ::= { jnxMbgPgwGtpGlbStatsEntry 113 }

jnxMbgPgwV2ICsOptIEIncorrTx  OBJECT-TYPE
    SYNTAX      Counter64
    MAX-ACCESS  read-only
    STATUS      current
    DESCRIPTION
    "Number of GTPV2 packets sent with cause Optional IE Incorrect."
    ::= { jnxMbgPgwGtpGlbStatsEntry 114 }

jnxMbgPgwV2ICsSysFailRx  OBJECT-TYPE
    SYNTAX      Counter64
    MAX-ACCESS  read-only
    STATUS      current
    DESCRIPTION
    "Number of GTPV2 packets received with cause System Failure."
    ::= { jnxMbgPgwGtpGlbStatsEntry 115 }

jnxMbgPgwV2ICsSysFailTx  OBJECT-TYPE
    SYNTAX      Counter64
    MAX-ACCESS  read-only
    STATUS      current
    DESCRIPTION
    "Number of GTPV2 packets sent with cause System Failure."
    ::= { jnxMbgPgwGtpGlbStatsEntry 116 }

jnxMbgPgwV2ICsNoResRx  OBJECT-TYPE
    SYNTAX      Counter64
    MAX-ACCESS  read-only
    STATUS      current
    DESCRIPTION
    "Number of GTPV2 packets received with cause No Resource."
    ::= { jnxMbgPgwGtpGlbStatsEntry 117 }

jnxMbgPgwV2ICsNoResTx  OBJECT-TYPE
    SYNTAX      Counter64
    MAX-ACCESS  read-only
    STATUS      current
    DESCRIPTION
    "Number of GTPV2 packets sent with cause No Resource."
    ::= { jnxMbgPgwGtpGlbStatsEntry 118 }

jnxMbgPgwV2ICsTFTSMANTErRx  OBJECT-TYPE
    SYNTAX      Counter64
    MAX-ACCESS  read-only
    STATUS      current
    DESCRIPTION
    "Number of GTPV2 packets received with cause TFT Symantic Error."
    ::= { jnxMbgPgwGtpGlbStatsEntry 119 }

jnxMbgPgwV2ICsTFTSMANTErTx  OBJECT-TYPE
    SYNTAX      Counter64
    MAX-ACCESS  read-only
    STATUS      current
    DESCRIPTION
    "Number of GTPV2 packets sent with cause TFT Symantic Error."
    ::= { jnxMbgPgwGtpGlbStatsEntry 120 }

jnxMbgPgwV2ICsTFTSysErrRx  OBJECT-TYPE
    SYNTAX      Counter64
    MAX-ACCESS  read-only
    STATUS      current
    DESCRIPTION
    "Number of GTPV2 packets received with cause TFT System Error."
    ::= { jnxMbgPgwGtpGlbStatsEntry 121 }

jnxMbgPgwV2ICsTFTSysErrTx  OBJECT-TYPE
    SYNTAX      Counter64
    MAX-ACCESS  read-only
    STATUS      current
    DESCRIPTION
    "Number of GTPV2 packets sent with cause TFT System Error."
    ::= { jnxMbgPgwGtpGlbStatsEntry 122 }

jnxMbgPgwV2ICsPkFltManErrRx  OBJECT-TYPE
    SYNTAX      Counter64
    MAX-ACCESS  read-only
    STATUS      current
    DESCRIPTION
    "Number of GTPV2 packets received with cause Packet Filter Symantic Error."
    ::= { jnxMbgPgwGtpGlbStatsEntry 123 }

jnxMbgPgwV2ICsPkFltManErrTx  OBJECT-TYPE
    SYNTAX      Counter64
    MAX-ACCESS  read-only
    STATUS      current
    DESCRIPTION
    "Number of GTPV2 packets sent with cause Packet Filter Symantic Error."
    ::= { jnxMbgPgwGtpGlbStatsEntry 124 }

jnxMbgPgwV2ICsPkFltSynErrRx  OBJECT-TYPE
    SYNTAX      Counter64
    MAX-ACCESS  read-only
    STATUS      current
    DESCRIPTION
    "Number of GTPV2 packets received with cause Packet Filter Syntax Error."
    ::= { jnxMbgPgwGtpGlbStatsEntry 125 }

jnxMbgPgwV2ICsPkFltSynErrTx  OBJECT-TYPE
    SYNTAX      Counter64
    MAX-ACCESS  read-only
    STATUS      current
    DESCRIPTION
    "Number of GTPV2 packets sent with cause Packet Filter Syntax Error."
    ::= { jnxMbgPgwGtpGlbStatsEntry 126 }

jnxMbgPgwV2ICsMisUnknAPNRx  OBJECT-TYPE
    SYNTAX      Counter64
    MAX-ACCESS  read-only
    STATUS      current
    DESCRIPTION
    "Number of GTPV2 packets received with cause Unknown APN."
    ::= { jnxMbgPgwGtpGlbStatsEntry 127 }

jnxMbgPgwV2ICsMisUnknAPNTx  OBJECT-TYPE
    SYNTAX      Counter64
    MAX-ACCESS  read-only
    STATUS      current
    DESCRIPTION
    "Number of GTPV2 packets sent with cause Unknown APN."
    ::= { jnxMbgPgwGtpGlbStatsEntry 128 }

jnxMbgPgwV2ICsUnexpRptIERx  OBJECT-TYPE
    SYNTAX      Counter64
    MAX-ACCESS  read-only
    STATUS      current
    DESCRIPTION
    "Number of GTPV2 packets received with cause Unexpected Repeated IE."
    ::= { jnxMbgPgwGtpGlbStatsEntry 129 }

jnxMbgPgwV2ICsUnexpRptIETx  OBJECT-TYPE
    SYNTAX      Counter64
    MAX-ACCESS  read-only
    STATUS      current
    DESCRIPTION
    "Number of GTPV2 packets sent with cause Unexpected Repeated IE."
    ::= { jnxMbgPgwGtpGlbStatsEntry 130 }

jnxMbgPgwV2ICsGREKeyNtFdRx  OBJECT-TYPE
    SYNTAX      Counter64
    MAX-ACCESS  read-only
    STATUS      current
    DESCRIPTION
    "Number of GTPV2 packets received with cause GRE Key Not Found."
    ::= { jnxMbgPgwGtpGlbStatsEntry 131 }

jnxMbgPgwV2ICsGREKeyNtFdTx  OBJECT-TYPE
    SYNTAX      Counter64
    MAX-ACCESS  read-only
    STATUS      current
    DESCRIPTION
    "Number of GTPV2 packets sent with cause GRE Key Not Found."
    ::= { jnxMbgPgwGtpGlbStatsEntry 132 }

jnxMbgPgwV2ICsRelocFailRx  OBJECT-TYPE
    SYNTAX      Counter64
    MAX-ACCESS  read-only
    STATUS      current
    DESCRIPTION
    "Number of GTPV2 packets received with cause Relocation Failed."
    ::= { jnxMbgPgwGtpGlbStatsEntry 133 }

jnxMbgPgwV2ICsRelocFailTx  OBJECT-TYPE
    SYNTAX      Counter64
    MAX-ACCESS  read-only
    STATUS      current
    DESCRIPTION
    "Number of GTPV2 packets sent with cause Relocation Failed."
    ::= { jnxMbgPgwGtpGlbStatsEntry 134 }

jnxMbgPgwV2ICsDeniedINRatRx  OBJECT-TYPE
    SYNTAX      Counter64
    MAX-ACCESS  read-only
    STATUS      current
    DESCRIPTION
    "Number of GTPV2 packets received with cause Denied in RAT."
    ::= { jnxMbgPgwGtpGlbStatsEntry 135 }

jnxMbgPgwV2ICsDeniedINRatTx  OBJECT-TYPE
    SYNTAX      Counter64
    MAX-ACCESS  read-only
    STATUS      current
    DESCRIPTION
    "Number of GTPV2 packets sent with cause Denied in RAT."
    ::= { jnxMbgPgwGtpGlbStatsEntry 136 }

jnxMbgPgwV2ICsPTNotSuppRx  OBJECT-TYPE
    SYNTAX      Counter64
    MAX-ACCESS  read-only
    STATUS      current
    DESCRIPTION
    "Number of GTPV2 packets received with cause PDN Type Not Supported."
    ::= { jnxMbgPgwGtpGlbStatsEntry 137 }

jnxMbgPgwV2ICsPTNotSuppTx  OBJECT-TYPE
    SYNTAX      Counter64
    MAX-ACCESS  read-only
    STATUS      current
    DESCRIPTION
    "Number of GTPV2 packets sent with cause PDN Type Not Supported."
    ::= { jnxMbgPgwGtpGlbStatsEntry 138 }

jnxMbgPgwV2ICsAllDynAdOccRx  OBJECT-TYPE
    SYNTAX      Counter64
    MAX-ACCESS  read-only
    STATUS      current
    DESCRIPTION
    "Number of GTPV2 packets received with cause Allocated Dynamic Address Occupied."
    ::= { jnxMbgPgwGtpGlbStatsEntry 139 }

jnxMbgPgwV2ICsAllDynAdOccTx  OBJECT-TYPE
    SYNTAX      Counter64
    MAX-ACCESS  read-only
    STATUS      current
    DESCRIPTION
    "Number of GTPV2 packets sent with cause Allocated Dynamic Address Occupied."
    ::= { jnxMbgPgwGtpGlbStatsEntry 140 }

jnxMbgPgwV2ICsNOTFTUECTXRx  OBJECT-TYPE
    SYNTAX      Counter64
    MAX-ACCESS  read-only
    STATUS      current
    DESCRIPTION
    "Number of GTPV2 packets received with cause UE Context Without TFT Exists."
    ::= { jnxMbgPgwGtpGlbStatsEntry 141 }

jnxMbgPgwV2ICsNOTFTUECTXTx  OBJECT-TYPE
    SYNTAX      Counter64
    MAX-ACCESS  read-only
    STATUS      current
    DESCRIPTION
    "Number of GTPV2 packets sent with cause UE Context Without TFT Exists."
    ::= { jnxMbgPgwGtpGlbStatsEntry 142 }

jnxMbgPgwV2ICsProtoNtSupRx  OBJECT-TYPE
    SYNTAX      Counter64
    MAX-ACCESS  read-only
    STATUS      current
    DESCRIPTION
    "Number of GTPV2 packets received with cause Protocol Not Supported."
    ::= { jnxMbgPgwGtpGlbStatsEntry 143 }

jnxMbgPgwV2ICsProtoNtSupTx  OBJECT-TYPE
    SYNTAX      Counter64
    MAX-ACCESS  read-only
    STATUS      current
    DESCRIPTION
    "Number of GTPV2 packets sent with cause Protocol Not Supported."
    ::= { jnxMbgPgwGtpGlbStatsEntry 144 }

jnxMbgPgwV2ICsUENotRespRx  OBJECT-TYPE
    SYNTAX      Counter64
    MAX-ACCESS  read-only
    STATUS      current
    DESCRIPTION
    "Number of GTPV2 packets received with cause UE Not Responding."
    ::= { jnxMbgPgwGtpGlbStatsEntry 145 }

jnxMbgPgwV2ICsUENotRespTx  OBJECT-TYPE
    SYNTAX      Counter64
    MAX-ACCESS  read-only
    STATUS      current
    DESCRIPTION
    "Number of GTPV2 packets sent with cause UE Not Responding."
    ::= { jnxMbgPgwGtpGlbStatsEntry 146 }

jnxMbgPgwV2ICsUERefusesRx  OBJECT-TYPE
    SYNTAX      Counter64
    MAX-ACCESS  read-only
    STATUS      current
    DESCRIPTION
    "Number of GTPV2 packets received with cause UE Refuses."
    ::= { jnxMbgPgwGtpGlbStatsEntry 147 }

jnxMbgPgwV2ICsUERefusesTx  OBJECT-TYPE
    SYNTAX      Counter64
    MAX-ACCESS  read-only
    STATUS      current
    DESCRIPTION
    "Number of GTPV2 packets sent with cause UE Refuses."
    ::= { jnxMbgPgwGtpGlbStatsEntry 148 }

jnxMbgPgwV2ICsServDeniedRx  OBJECT-TYPE
    SYNTAX      Counter64
    MAX-ACCESS  read-only
    STATUS      current
    DESCRIPTION
    "Number of GTPV2 packets received with cause Service Denied."
    ::= { jnxMbgPgwGtpGlbStatsEntry 149 }

jnxMbgPgwV2ICsServDeniedTx  OBJECT-TYPE
    SYNTAX      Counter64
    MAX-ACCESS  read-only
    STATUS      current
    DESCRIPTION
    "Number of GTPV2 packets sent with cause Service Denied."
    ::= { jnxMbgPgwGtpGlbStatsEntry 150 }

jnxMbgPgwV2ICsUnabPageUERx  OBJECT-TYPE
    SYNTAX      Counter64
    MAX-ACCESS  read-only
    STATUS      current
    DESCRIPTION
    "Number of GTPV2 packets received with cause Unable to Page UE."
    ::= { jnxMbgPgwGtpGlbStatsEntry 151 }

jnxMbgPgwV2ICsUnabPageUETx  OBJECT-TYPE
    SYNTAX      Counter64
    MAX-ACCESS  read-only
    STATUS      current
    DESCRIPTION
    "Number of GTPV2 packets sent with cause Unable to Page UE."
    ::= { jnxMbgPgwGtpGlbStatsEntry 152 }

jnxMbgPgwV2ICsNoMemRx  OBJECT-TYPE
    SYNTAX      Counter64
    MAX-ACCESS  read-only
    STATUS      current
    DESCRIPTION
    "Number of GTPV2 packets received with cause No Memory."
    ::= { jnxMbgPgwGtpGlbStatsEntry 153 }

jnxMbgPgwV2ICsNoMemTx  OBJECT-TYPE
    SYNTAX      Counter64
    MAX-ACCESS  read-only
    STATUS      current
    DESCRIPTION
    "Number of GTPV2 packets sent with cause No Memory."
    ::= { jnxMbgPgwGtpGlbStatsEntry 154 }

jnxMbgPgwV2ICsUserAUTHFlRx  OBJECT-TYPE
    SYNTAX      Counter64
    MAX-ACCESS  read-only
    STATUS      current
    DESCRIPTION
    "Number of GTPV2 packets received with cause User AUTH Failed."
    ::= { jnxMbgPgwGtpGlbStatsEntry 155 }

jnxMbgPgwV2ICsUserAUTHFlTx  OBJECT-TYPE
    SYNTAX      Counter64
    MAX-ACCESS  read-only
    STATUS      current
    DESCRIPTION
    "Number of GTPV2 packets sent with cause User AUTH Failed."
    ::= { jnxMbgPgwGtpGlbStatsEntry 156 }

jnxMbgPgwV2ICsAPNAcsDenRx  OBJECT-TYPE
    SYNTAX      Counter64
    MAX-ACCESS  read-only
    STATUS      current
    DESCRIPTION
    "Number of GTPV2 packets received with cause APN Access Denied."
    ::= { jnxMbgPgwGtpGlbStatsEntry 157 }

jnxMbgPgwV2ICsAPNAcsDenTx  OBJECT-TYPE
    SYNTAX      Counter64
    MAX-ACCESS  read-only
    STATUS      current
    DESCRIPTION
    "Number of GTPV2 packets sent with cause APN Access Denied."
    ::= { jnxMbgPgwGtpGlbStatsEntry 158 }

jnxMbgPgwV2ICsReqRejRx  OBJECT-TYPE
    SYNTAX      Counter64
    MAX-ACCESS  read-only
    STATUS      current
    DESCRIPTION
    "Number of GTPV2 packets received with cause Request Rejected."
    ::= { jnxMbgPgwGtpGlbStatsEntry 159 }

jnxMbgPgwV2ICsReqRejTx  OBJECT-TYPE
    SYNTAX      Counter64
    MAX-ACCESS  read-only
    STATUS      current
    DESCRIPTION
    "Number of GTPV2 packets sent with cause Request Rejected."
    ::= { jnxMbgPgwGtpGlbStatsEntry 160 }

jnxMbgPgwV2ICsPTMSISigMMRx OBJECT-TYPE
     SYNTAX      Counter64
     MAX-ACCESS  read-only
     STATUS      current
     DESCRIPTION
     "Number of GTPV2 packets received with cause P-TMSI Signature Mismatc."
    ::= { jnxMbgPgwGtpGlbStatsEntry 161 }

jnxMbgPgwV2ICsPTMSISigMMTx OBJECT-TYPE
     SYNTAX      Counter64
     MAX-ACCESS  read-only
     STATUS      current
     DESCRIPTION
     "Number of GTPV2 packets sent with cause P-TMSI Signature Mismatch"
    ::= { jnxMbgPgwGtpGlbStatsEntry 162 }

jnxMbgPgwV2ICsIMSINotKnRx OBJECT-TYPE
      SYNTAX      Counter64
      MAX-ACCESS  read-only
      STATUS      current
      DESCRIPTION
      "Number of GTPV2 packets received with cause IMSI Not Known."
    ::= { jnxMbgPgwGtpGlbStatsEntry 163 }

jnxMbgPgwV2ICsIMSINotKnTx OBJECT-TYPE
      SYNTAX      Counter64
      MAX-ACCESS  read-only
      STATUS      current
      DESCRIPTION
      "Number of GTPV2 packets sent with cause IMSI Not Known."
    ::= { jnxMbgPgwGtpGlbStatsEntry 164 }

jnxMbgPgwV2ICsCondIEMsRx OBJECT-TYPE
       SYNTAX      Counter64
       MAX-ACCESS  read-only
       STATUS      current
       DESCRIPTION
       "Number of GTPV2 packets received with cause Conditional IE Missing."
     ::= { jnxMbgPgwGtpGlbStatsEntry 165 }

jnxMbgPgwV2ICsCondIEMsTx OBJECT-TYPE
       SYNTAX      Counter64
       MAX-ACCESS  read-only
       STATUS      current
       DESCRIPTION
       "Number of GTPV2 packets sent with cause Conditional IE Missing."
     ::= { jnxMbgPgwGtpGlbStatsEntry 166 }

jnxMbgPgwV2ICsAPNResTIncRx OBJECT-TYPE
        SYNTAX      Counter64
        MAX-ACCESS  read-only
        STATUS      current
        DESCRIPTION
        "Number of GTPV2 packets received with cause APN Restriction Type Incompatible"
     ::= { jnxMbgPgwGtpGlbStatsEntry 167 }

jnxMbgPgwV2ICsAPNResTIncTx OBJECT-TYPE
        SYNTAX      Counter64
        MAX-ACCESS  read-only
        STATUS      current
        DESCRIPTION
        "Number of GTPV2 packets sent with cause APN Restriction Type Incompatible"
     ::= { jnxMbgPgwGtpGlbStatsEntry 168 }

jnxMbgPgwV2ICsUnknownRx OBJECT-TYPE
         SYNTAX      Counter64
         MAX-ACCESS  read-only
         STATUS      current
         DESCRIPTION
         "Number of GTPV2 packets received with cause Unknown"
     ::= { jnxMbgPgwGtpGlbStatsEntry 169 }

jnxMbgPgwV2ICsUnknownTx OBJECT-TYPE
         SYNTAX      Counter64
         MAX-ACCESS  read-only
         STATUS      current
         DESCRIPTION
         "Number of GTPV2 packets sent with cause Unknown"
     ::= { jnxMbgPgwGtpGlbStatsEntry 170 }

jnxMbgPgwV1ProtocolErrRx  OBJECT-TYPE
    SYNTAX      Counter64
    MAX-ACCESS  read-only
    STATUS      current
    DESCRIPTION
    "Number of GTPv2 Protocol Errors Received."
    ::= { jnxMbgPgwGtpGlbStatsEntry 171 }

jnxMbgPgwV1UnSupportedMsgRx  OBJECT-TYPE
    SYNTAX      Counter64
    MAX-ACCESS  read-only
    STATUS      current
    DESCRIPTION
    "Number of GTPv2 Unsupported Messages received."
    ::= { jnxMbgPgwGtpGlbStatsEntry 172 }

jnxMbgPgwV1T3RespTmrExpRx  OBJECT-TYPE
    SYNTAX      Counter64
    MAX-ACCESS  read-only
    STATUS      current
    DESCRIPTION
    "Number of GTP V1 T3 timer expiries Received."
    ::= { jnxMbgPgwGtpGlbStatsEntry 173 }

jnxMbgPgwV1GlbNumMsgRx  OBJECT-TYPE
    SYNTAX      Counter64
    MAX-ACCESS  read-only
    STATUS      current
    DESCRIPTION
    "Number of GTPv1 messages received."
    ::= { jnxMbgPgwGtpGlbStatsEntry 174 }

jnxMbgPgwV1GlbNumMsgTx  OBJECT-TYPE
    SYNTAX      Counter64
    MAX-ACCESS  read-only
    STATUS      current
    DESCRIPTION
    "Number of GTP V1 messages sent."
    ::= { jnxMbgPgwGtpGlbStatsEntry 175 }

jnxMbgPgwV1GlbNumBytesRx  OBJECT-TYPE
    SYNTAX      Counter64
    MAX-ACCESS  read-only
    STATUS      current
    DESCRIPTION
    "Number of GTPv1 bytes received."
    ::= { jnxMbgPgwGtpGlbStatsEntry 176 }

jnxMbgPgwV1GlbNumBytesTx  OBJECT-TYPE
    SYNTAX      Counter64
    MAX-ACCESS  read-only
    STATUS      current
    DESCRIPTION
    "Number of GTP V1 bytes sent."
    ::= { jnxMbgPgwGtpGlbStatsEntry 177 }

jnxMbgPgwV1GlbEchoReqRx  OBJECT-TYPE
    SYNTAX      Counter64
    MAX-ACCESS  read-only
    STATUS      current
    DESCRIPTION
    "Number of GTP V1 Echo Requests received."
    ::= { jnxMbgPgwGtpGlbStatsEntry 178 }

jnxMbgPgwV1GlbEchoReqTx  OBJECT-TYPE
    SYNTAX      Counter64
    MAX-ACCESS  read-only
    STATUS      current
    DESCRIPTION
    "Number of GTP V1 Echo Requests Sent."
    ::= { jnxMbgPgwGtpGlbStatsEntry 179 }

jnxMbgPgwV1GlbEchoRespRx  OBJECT-TYPE
    SYNTAX      Counter64
    MAX-ACCESS  read-only
    STATUS      current
    DESCRIPTION
    "Number of GTP V1 Echo Responses received."
    ::= { jnxMbgPgwGtpGlbStatsEntry 180 }

jnxMbgPgwV1GlbEchoRespTx  OBJECT-TYPE
    SYNTAX      Counter64
    MAX-ACCESS  read-only
    STATUS      current
    DESCRIPTION
    "Number of GTP V1 Echo Responses Sent."
    ::= { jnxMbgPgwGtpGlbStatsEntry 181 }

jnxMbgPgwV1VerNotSupRx OBJECT-TYPE
    SYNTAX      Counter64
    MAX-ACCESS  read-only
    STATUS      current
    DESCRIPTION
    "Number of GTP V1 Version Not supported messages received"
    ::= { jnxMbgPgwGtpGlbStatsEntry 182 }

jnxMbgPgwV1VerNotSupTx OBJECT-TYPE
    SYNTAX      Counter64
    MAX-ACCESS  read-only
    STATUS      current
    DESCRIPTION
    "Number of GTP V1 version not supported messages Sent."
    ::= { jnxMbgPgwGtpGlbStatsEntry 183 }

jnxMbgPgwV1CrtPdpCxtReqRx   OBJECT-TYPE
    SYNTAX      Counter64
    MAX-ACCESS  read-only
    STATUS      current
    DESCRIPTION
    "Number of GTP V1 Create PDP Context Requests Received."
    ::= { jnxMbgPgwGtpGlbStatsEntry 184 }

jnxMbgPgwV1CrtPdpCxtReqTx   OBJECT-TYPE
    SYNTAX      Counter64
    MAX-ACCESS  read-only
    STATUS      current
    DESCRIPTION
    "Number of GTP V1 Create PDP Context Requests Sent."
    ::= { jnxMbgPgwGtpGlbStatsEntry 185 }

jnxMbgPgwV1CrtPdpCxtRspRx   OBJECT-TYPE
    SYNTAX      Counter64
    MAX-ACCESS  read-only
    STATUS      current
    DESCRIPTION
    "Number of GTP V1 Create PDP Context Responses Received."
    ::= { jnxMbgPgwGtpGlbStatsEntry 186 }

jnxMbgPgwV1CrtPdpCxtRspTx   OBJECT-TYPE
    SYNTAX      Counter64
    MAX-ACCESS  read-only
    STATUS      current
    DESCRIPTION
    "Number of GTP V1 Create PDP Context Responses Sent."
    ::= { jnxMbgPgwGtpGlbStatsEntry 187 }

jnxMbgPgwV1UpdPdpCxtReqRx   OBJECT-TYPE
    SYNTAX      Counter64
    MAX-ACCESS  read-only
    STATUS      current
    DESCRIPTION
    "Number of GTP V1 Update PDP Context Requests Received."
    ::= { jnxMbgPgwGtpGlbStatsEntry 188 }

jnxMbgPgwV1UpdPdpCxtReqTx   OBJECT-TYPE
    SYNTAX      Counter64
    MAX-ACCESS  read-only
    STATUS      current
    DESCRIPTION
    "Number of GTP V1 Update PDP Context Requests Sent."
    ::= { jnxMbgPgwGtpGlbStatsEntry 189 }

jnxMbgPgwV1UpdPdpCxtRspRx   OBJECT-TYPE
    SYNTAX      Counter64
    MAX-ACCESS  read-only
    STATUS      current
    DESCRIPTION
    "Number of GTP V1 Update PDP Context Responses Received."
    ::= { jnxMbgPgwGtpGlbStatsEntry 190 }

jnxMbgPgwV1UpdPdpCxtRspTx   OBJECT-TYPE
    SYNTAX      Counter64
    MAX-ACCESS  read-only
    STATUS      current
    DESCRIPTION
    "Number of GTP V1 Update PDP Context Responses Sent."
    ::= { jnxMbgPgwGtpGlbStatsEntry 191 }

jnxMbgPgwV1DelPdpCxtReqRx   OBJECT-TYPE
    SYNTAX      Counter64
    MAX-ACCESS  read-only
    STATUS      current
    DESCRIPTION
    "Number of GTP V1 Delete PDP Context Requests Received."
    ::= { jnxMbgPgwGtpGlbStatsEntry 192 }

jnxMbgPgwV1DelPdpCxtReqTx   OBJECT-TYPE
    SYNTAX      Counter64
    MAX-ACCESS  read-only
    STATUS      current
    DESCRIPTION
    "Number of GTP V1 Delete PDP Context Requests Sent."
    ::= { jnxMbgPgwGtpGlbStatsEntry 193 }

jnxMbgPgwV1DelPdpCxtRspRx   OBJECT-TYPE
    SYNTAX      Counter64
    MAX-ACCESS  read-only
    STATUS      current
    DESCRIPTION
    "Number of GTP V1 Delete PDP Context Responses Received."
    ::= { jnxMbgPgwGtpGlbStatsEntry 194 }

jnxMbgPgwV1DelPdpCxtRspTx   OBJECT-TYPE
    SYNTAX      Counter64
    MAX-ACCESS  read-only
    STATUS      current
    DESCRIPTION
    "Number of GTP V1 Delete PDP Context Responses Sent."
    ::= { jnxMbgPgwGtpGlbStatsEntry 195 }

jnxMbgPgwV1CrtAAPdpCxtReqRx   OBJECT-TYPE
    SYNTAX      Counter64
    MAX-ACCESS  read-only
    STATUS      current
    DESCRIPTION
    "Number of GTP V1 Create AA PDP Context Requests Received."
    ::= { jnxMbgPgwGtpGlbStatsEntry 196 }

jnxMbgPgwV1CrtAAPdpCxtReqTx   OBJECT-TYPE
    SYNTAX      Counter64
    MAX-ACCESS  read-only
    STATUS      current
    DESCRIPTION
    "Number of GTP V1 Create AA PDP Context Requests Sent."
    ::= { jnxMbgPgwGtpGlbStatsEntry 197 }

jnxMbgPgwV1CrtAAPdpCxtRspRx   OBJECT-TYPE
    SYNTAX      Counter64
    MAX-ACCESS  read-only
    STATUS      current
    DESCRIPTION
    "Number of GTP V1 Create AA PDP Context Responses Received."
    ::= { jnxMbgPgwGtpGlbStatsEntry 198 }

jnxMbgPgwV1CrtAAPdpCxtRspTx   OBJECT-TYPE
    SYNTAX      Counter64
    MAX-ACCESS  read-only
    STATUS      current
    DESCRIPTION
    "Number of GTP V1 Create AA PDP Context Responses Sent."
    ::= { jnxMbgPgwGtpGlbStatsEntry 199 }

jnxMbgPgwV1DelAAPdpCxtReqRx   OBJECT-TYPE
    SYNTAX      Counter64
    MAX-ACCESS  read-only
    STATUS      current
    DESCRIPTION
    "Number of GTP V1 Delete AA PDP Context Requests Received."
    ::= { jnxMbgPgwGtpGlbStatsEntry 200 }

jnxMbgPgwV1DelAAPdpCxtReqTx   OBJECT-TYPE
    SYNTAX      Counter64
    MAX-ACCESS  read-only
    STATUS      current
    DESCRIPTION
    "Number of GTP V1 Delete AA PDP Context Requests Sent."
    ::= { jnxMbgPgwGtpGlbStatsEntry 201 }

jnxMbgPgwV1DelAAPdpCxtRspRx   OBJECT-TYPE
    SYNTAX      Counter64
    MAX-ACCESS  read-only
    STATUS      current
    DESCRIPTION
    "Number of GTP V1 Delete AA PDP Context Responses Received."
    ::= { jnxMbgPgwGtpGlbStatsEntry 202 }

jnxMbgPgwV1DelAAPdpCxtRspTx   OBJECT-TYPE
    SYNTAX      Counter64
    MAX-ACCESS  read-only
    STATUS      current
    DESCRIPTION
    "Number of GTP V1 Delete AA PDP Context Responses Sent."
    ::= { jnxMbgPgwGtpGlbStatsEntry 203 }

jnxMbgPgwV1ErrorIndRx   OBJECT-TYPE
    SYNTAX      Counter64
    MAX-ACCESS  read-only
    STATUS      current
    DESCRIPTION
    "Number of GTP V1 Error Indication Received."
    ::= { jnxMbgPgwGtpGlbStatsEntry 204 }

jnxMbgPgwV1ErrorIndTx   OBJECT-TYPE
    SYNTAX      Counter64
    MAX-ACCESS  read-only
    STATUS      current
    DESCRIPTION
    "Number of GTP V1 Error Indication Sent."
    ::= { jnxMbgPgwGtpGlbStatsEntry 205 }

jnxMbgPgwV1NotifReqRx   OBJECT-TYPE
    SYNTAX      Counter64
    MAX-ACCESS  read-only
    STATUS      current
    DESCRIPTION
    "Number of GTP V1 Notify Requests Received."
    ::= { jnxMbgPgwGtpGlbStatsEntry 206 }

jnxMbgPgwV1NotifReqTx   OBJECT-TYPE
    SYNTAX      Counter64
    MAX-ACCESS  read-only
    STATUS      current
    DESCRIPTION
    "Number of GTP V1 Notify Requests Sent."
    ::= { jnxMbgPgwGtpGlbStatsEntry 207 }

jnxMbgPgwV1NotifRspRx   OBJECT-TYPE
    SYNTAX      Counter64
    MAX-ACCESS  read-only
    STATUS      current
    DESCRIPTION
    "Number of GTP V1 Notify Responses Received."
    ::= { jnxMbgPgwGtpGlbStatsEntry 208 }

jnxMbgPgwV1NotifRspTx   OBJECT-TYPE
    SYNTAX      Counter64
    MAX-ACCESS  read-only
    STATUS      current
    DESCRIPTION
    "Number of GTP V1 Notify Responses Sent."
    ::= { jnxMbgPgwGtpGlbStatsEntry 209 }

jnxMbgPgwV1NotifRejReqRx   OBJECT-TYPE
    SYNTAX      Counter64
    MAX-ACCESS  read-only
    STATUS      current
    DESCRIPTION
    "Number of GTP V1 Notify Reject Requests Received."
    ::= { jnxMbgPgwGtpGlbStatsEntry 210 }

jnxMbgPgwV1NotifRejReqTx   OBJECT-TYPE
    SYNTAX      Counter64
    MAX-ACCESS  read-only
    STATUS      current
    DESCRIPTION
    "Number of GTP V1 Notify Reject Requests Sent."
    ::= { jnxMbgPgwGtpGlbStatsEntry 211 }

jnxMbgPgwV1NotifRejRspRx   OBJECT-TYPE
    SYNTAX      Counter64
    MAX-ACCESS  read-only
    STATUS      current
    DESCRIPTION
    "Number of GTP V1 Notify Reject Responses Received."
    ::= { jnxMbgPgwGtpGlbStatsEntry 212 }

jnxMbgPgwV1NotifRejRspTx   OBJECT-TYPE
    SYNTAX      Counter64
    MAX-ACCESS  read-only
    STATUS      current
    DESCRIPTION
    "Number of GTP V1 Notify Reject Responses Sent."
    ::= { jnxMbgPgwGtpGlbStatsEntry 213 }

jnxMbgPgwV1RtInfReqRx   OBJECT-TYPE
    SYNTAX      Counter64
    MAX-ACCESS  read-only
    STATUS      current
    DESCRIPTION
    "Number of GTP V1 Routing Information Requests Received."
    ::= { jnxMbgPgwGtpGlbStatsEntry 214 }

jnxMbgPgwV1RtInfReqTx   OBJECT-TYPE
    SYNTAX      Counter64
    MAX-ACCESS  read-only
    STATUS      current
    DESCRIPTION
    "Number of GTP V1 Routing Information Requests Sent."
    ::= { jnxMbgPgwGtpGlbStatsEntry 215 }

jnxMbgPgwV1RtInfRspRx   OBJECT-TYPE
    SYNTAX      Counter64
    MAX-ACCESS  read-only
    STATUS      current
    DESCRIPTION
    "Number of GTP V1 Routing Information Responses Received."
    ::= { jnxMbgPgwGtpGlbStatsEntry 216 }

jnxMbgPgwV1RtInfRspTx   OBJECT-TYPE
    SYNTAX      Counter64
    MAX-ACCESS  read-only
    STATUS      current
    DESCRIPTION
    "Number of GTP V1 Routing Information Responses Sent."
    ::= { jnxMbgPgwGtpGlbStatsEntry 217 }

jnxMbgPgwV1FailRptReqRx   OBJECT-TYPE
    SYNTAX      Counter64
    MAX-ACCESS  read-only
    STATUS      current
    DESCRIPTION
    "Number of GTP V1 Fail Repeat Requests Received."
    ::= { jnxMbgPgwGtpGlbStatsEntry 218 }

jnxMbgPgwV1FailRptReqTx   OBJECT-TYPE
    SYNTAX      Counter64
    MAX-ACCESS  read-only
    STATUS      current
    DESCRIPTION
    "Number of GTP V1 Fail Repeat Requests Sent."
    ::= { jnxMbgPgwGtpGlbStatsEntry 219 }

jnxMbgPgwV1FailRptRspRx   OBJECT-TYPE
    SYNTAX      Counter64
    MAX-ACCESS  read-only
    STATUS      current
    DESCRIPTION
    "Number of GTP V1 Fail Repeat Responses Received."
    ::= { jnxMbgPgwGtpGlbStatsEntry 220 }

jnxMbgPgwV1FailRptRspTx   OBJECT-TYPE
    SYNTAX      Counter64
    MAX-ACCESS  read-only
    STATUS      current
    DESCRIPTION
    "Number of GTP V1 Fail Repeat Responses Sent."
    ::= { jnxMbgPgwGtpGlbStatsEntry 221 }

jnxMbgPgwV1NotMSPresReqRx   OBJECT-TYPE
    SYNTAX      Counter64
    MAX-ACCESS  read-only
    STATUS      current
    DESCRIPTION
    "Number of GTP V1 MS Not Present Request Received."
    ::= { jnxMbgPgwGtpGlbStatsEntry 222 }

jnxMbgPgwV1NotMSPresReqTx   OBJECT-TYPE
    SYNTAX      Counter64
    MAX-ACCESS  read-only
    STATUS      current
    DESCRIPTION
    "Number of GTP V1 MS Not Present Request Sent."
    ::= { jnxMbgPgwGtpGlbStatsEntry 223 }

jnxMbgPgwV1NotMSPresRspRx   OBJECT-TYPE
    SYNTAX      Counter64
    MAX-ACCESS  read-only
    STATUS      current
    DESCRIPTION
    "Number of GTP V1 MS Not Present Responses Received."
    ::= { jnxMbgPgwGtpGlbStatsEntry 224 }

jnxMbgPgwV1NotMSPresRspTx   OBJECT-TYPE
    SYNTAX      Counter64
    MAX-ACCESS  read-only
    STATUS      current
    DESCRIPTION
    "Number of GTP V1 MS Not Present Responses Sent."
    ::= { jnxMbgPgwGtpGlbStatsEntry 225 }

jnxMbgPgwV1ICsReqAcceptedRx   OBJECT-TYPE
    SYNTAX      Counter64
    MAX-ACCESS  read-only
    STATUS      current
    DESCRIPTION
    "Number of GTPV1 packets received with cause Request Accepted."
    ::= { jnxMbgPgwGtpGlbStatsEntry 226 }

jnxMbgPgwV1ICsReqAcceptedTx   OBJECT-TYPE
    SYNTAX      Counter64
    MAX-ACCESS  read-only
    STATUS      current
    DESCRIPTION
    "Number of GTPV1 packets sent with cause Request Accepted."
    ::= { jnxMbgPgwGtpGlbStatsEntry 227 }

jnxMbgPgwV1ICsNonExistRx   OBJECT-TYPE
    SYNTAX      Counter64
    MAX-ACCESS  read-only
    STATUS      current
    DESCRIPTION
    "Number of GTPV1 packets received with cause Non Existant."
    ::= { jnxMbgPgwGtpGlbStatsEntry 228 }

jnxMbgPgwV1ICsNonExistTx   OBJECT-TYPE
    SYNTAX      Counter64
    MAX-ACCESS  read-only
    STATUS      current
    DESCRIPTION
    "Number of GTPV1 packets sent with cause Non Existant."
    ::= { jnxMbgPgwGtpGlbStatsEntry 229 }

jnxMbgPgwV1ICsInvMsgFmtRx   OBJECT-TYPE
    SYNTAX      Counter64
    MAX-ACCESS  read-only
    STATUS      current
    DESCRIPTION
    "Number of GTPV1 packets received with cause Invalid Mesage Format."
    ::= { jnxMbgPgwGtpGlbStatsEntry 230 }

jnxMbgPgwV1ICsInvMsgFmtTx   OBJECT-TYPE
    SYNTAX      Counter64
    MAX-ACCESS  read-only
    STATUS      current
    DESCRIPTION
    "Number of GTPV1 packets sent with cause Invalid Mesage Format."
    ::= { jnxMbgPgwGtpGlbStatsEntry 231 }

jnxMbgPgwV1ICsIMSINotKnownRx   OBJECT-TYPE
    SYNTAX      Counter64
    MAX-ACCESS  read-only
    STATUS      current
    DESCRIPTION
    "Number of GTPV1 packets received with cause IMSI Not Known."
    ::= { jnxMbgPgwGtpGlbStatsEntry 232 }


jnxMbgPgwV1ICsIMSINotKnownTx   OBJECT-TYPE
    SYNTAX      Counter64
    MAX-ACCESS  read-only
    STATUS      current
    DESCRIPTION
    "Number of GTPV1 packets sent with cause IMSI Not Known."
    ::= { jnxMbgPgwGtpGlbStatsEntry 233 }

jnxMbgPgwV1ICsMSGRPSDetachRx   OBJECT-TYPE
    SYNTAX      Counter64
    MAX-ACCESS  read-only
    STATUS      current
    DESCRIPTION
    "Number of GTPV1 packets received with cause MS GPRS Detached."
    ::= { jnxMbgPgwGtpGlbStatsEntry 234 }

jnxMbgPgwV1ICsMSGRPSDetachTx   OBJECT-TYPE
    SYNTAX      Counter64
    MAX-ACCESS  read-only
    STATUS      current
    DESCRIPTION
    "Number of GTPV1 packets sent with cause MS GPRS Detached."
    ::= { jnxMbgPgwGtpGlbStatsEntry 235 }

jnxMbgPgwV1ICsMSNotGRPSRespRx   OBJECT-TYPE
    SYNTAX      Counter64
    MAX-ACCESS  read-only
    STATUS      current
    DESCRIPTION
    "Number of GTPV1 packets received with cause MS No GPRS Response."
    ::= { jnxMbgPgwGtpGlbStatsEntry 236 }

jnxMbgPgwV1ICsMSNotGRPSRespTx   OBJECT-TYPE
    SYNTAX      Counter64
    MAX-ACCESS  read-only
    STATUS      current
    DESCRIPTION
    "Number of GTPV1 packets sent with cause MS No GPRS Response."
    ::= { jnxMbgPgwGtpGlbStatsEntry 237 }

jnxMbgPgwV1ICsMSRefusesRx   OBJECT-TYPE
    SYNTAX      Counter64
    MAX-ACCESS  read-only
    STATUS      current
    DESCRIPTION
    "Number of GTPV1 packets received with cause MS Refues."
    ::= { jnxMbgPgwGtpGlbStatsEntry 238 }

jnxMbgPgwV1ICsMSRefusesTx   OBJECT-TYPE
    SYNTAX      Counter64
    MAX-ACCESS  read-only
    STATUS      current
    DESCRIPTION
    "Number of GTPV1 packets sent with cause MS Refues."
    ::= { jnxMbgPgwGtpGlbStatsEntry 239 }

jnxMbgPgwV1ICsVerNotSuppRx   OBJECT-TYPE
    SYNTAX      Counter64
    MAX-ACCESS  read-only
    STATUS      current
    DESCRIPTION
    "Number of GTPV1 packets received with cause Version Not Supported."
    ::= { jnxMbgPgwGtpGlbStatsEntry 240 }

jnxMbgPgwV1ICsVerNotSuppTx   OBJECT-TYPE
    SYNTAX      Counter64
    MAX-ACCESS  read-only
    STATUS      current
    DESCRIPTION
    "Number of GTPV1 packets sent with cause Version Not Supported."
    ::= { jnxMbgPgwGtpGlbStatsEntry 241 }

jnxMbgPgwV1ICsNoResRx   OBJECT-TYPE
    SYNTAX      Counter64
    MAX-ACCESS  read-only
    STATUS      current
    DESCRIPTION
    "Number of GTPV1 packets received with cause No Response."
    ::= { jnxMbgPgwGtpGlbStatsEntry 242 }

jnxMbgPgwV1ICsNoResTx   OBJECT-TYPE
    SYNTAX      Counter64
    MAX-ACCESS  read-only
    STATUS      current
    DESCRIPTION
    "Number of GTPV1 packets sent with cause No Response."
    ::= { jnxMbgPgwGtpGlbStatsEntry 243 }

jnxMbgPgwV1ICsServNotSuppRx   OBJECT-TYPE
    SYNTAX      Counter64
    MAX-ACCESS  read-only
    STATUS      current
    DESCRIPTION
    "Number of GTPV1 packets received with cause Service Not Supported."
    ::= { jnxMbgPgwGtpGlbStatsEntry 244 }

jnxMbgPgwV1ICsServNotSuppTx   OBJECT-TYPE
    SYNTAX      Counter64
    MAX-ACCESS  read-only
    STATUS      current
    DESCRIPTION
    "Number of GTPV1 packets sent with cause Service Not Supported."
    ::= { jnxMbgPgwGtpGlbStatsEntry 245 }

jnxMbgPgwV1ICsManIEIncrtRx   OBJECT-TYPE
    SYNTAX      Counter64
    MAX-ACCESS  read-only
    STATUS      current
    DESCRIPTION
    "Number of GTPV1 packets received with cause Mandatory IE incorrect."
    ::= { jnxMbgPgwGtpGlbStatsEntry 246 }

jnxMbgPgwV1ICsManIEIncrtTx   OBJECT-TYPE
    SYNTAX      Counter64
    MAX-ACCESS  read-only
    STATUS      current
    DESCRIPTION
    "Number of GTPV1 packets sent with cause Mandatory IE incorrect."
    ::= { jnxMbgPgwGtpGlbStatsEntry 247 }

jnxMbgPgwV1ICsManIEMissRx   OBJECT-TYPE
    SYNTAX      Counter64
    MAX-ACCESS  read-only
    STATUS      current
    DESCRIPTION
    "Number of GTPV1 packets received with cause Mandatory IE Missing."
    ::= { jnxMbgPgwGtpGlbStatsEntry 248 }

jnxMbgPgwV1ICsManIEMissTx   OBJECT-TYPE
    SYNTAX      Counter64
    MAX-ACCESS  read-only
    STATUS      current
    DESCRIPTION
    "Number of GTPV1 packets sent with cause Mandatory IE Missing."
    ::= { jnxMbgPgwGtpGlbStatsEntry 249 }

jnxMbgPgwV1ICsOptIEIncrtRx   OBJECT-TYPE
    SYNTAX      Counter64
    MAX-ACCESS  read-only
    STATUS      current
    DESCRIPTION
    "Number of GTPV1 packets received with cause Optional IE incorrect."
    ::= { jnxMbgPgwGtpGlbStatsEntry 250 }

jnxMbgPgwV1ICsOptIEIncrtTx   OBJECT-TYPE
    SYNTAX      Counter64
    MAX-ACCESS  read-only
    STATUS      current
    DESCRIPTION
    "Number of GTPV1 packets sent with cause Optional IE incorrect."
    ::= { jnxMbgPgwGtpGlbStatsEntry 251 }

jnxMbgPgwV1ICsSysFailRx   OBJECT-TYPE
    SYNTAX      Counter64
    MAX-ACCESS  read-only
    STATUS      current
    DESCRIPTION
    "Number of GTPV1 packets received with cause System Failure."
    ::= { jnxMbgPgwGtpGlbStatsEntry 252 }

jnxMbgPgwV1ICsSysFailTx   OBJECT-TYPE
    SYNTAX      Counter64
    MAX-ACCESS  read-only
    STATUS      current
    DESCRIPTION
    "Number of GTPV1 packets sent with cause System Failure."
    ::= { jnxMbgPgwGtpGlbStatsEntry 253 }

jnxMbgPgwV1ICsRoamRestrictRx   OBJECT-TYPE
    SYNTAX      Counter64
    MAX-ACCESS  read-only
    STATUS      current
    DESCRIPTION
    "Number of GTPV1 packets received with cause Roaming Restricted."
    ::= { jnxMbgPgwGtpGlbStatsEntry 254 }

jnxMbgPgwV1ICsRoamRestrictTx   OBJECT-TYPE
    SYNTAX      Counter64
    MAX-ACCESS  read-only
    STATUS      current
    DESCRIPTION
    "Number of GTPV1 packets sent with cause Roaming Restricted."
    ::= { jnxMbgPgwGtpGlbStatsEntry 255 }

jnxMbgPgwV1ICsPTMSISigMMRx   OBJECT-TYPE
    SYNTAX      Counter64
    MAX-ACCESS  read-only
    STATUS      current
    DESCRIPTION
    "Number of GTPV1 packets received with cause PTMSI Signature Mismatch."
    ::= { jnxMbgPgwGtpGlbStatsEntry 256 }

jnxMbgPgwV1ICsPTMSISigMMTx   OBJECT-TYPE
    SYNTAX      Counter64
    MAX-ACCESS  read-only
    STATUS      current
    DESCRIPTION
    "Number of GTPV1 packets sent with cause PTMSI Signature Mismatch."
    ::= { jnxMbgPgwGtpGlbStatsEntry 257 }

jnxMbgPgwV1ICsGPRSConnSuppRx   OBJECT-TYPE
    SYNTAX      Counter64
    MAX-ACCESS  read-only
    STATUS      current
    DESCRIPTION
    "Number of GTPV1 packets received with cause GPRS Connection Supported."
    ::= { jnxMbgPgwGtpGlbStatsEntry 258 }

jnxMbgPgwV1ICsGPRSConnSuppTx   OBJECT-TYPE
    SYNTAX      Counter64
    MAX-ACCESS  read-only
    STATUS      current
    DESCRIPTION
    "Number of GTPV1 packets sent with cause GPRS Connection Supported."
    ::= { jnxMbgPgwGtpGlbStatsEntry 259 }

jnxMbgPgwV1ICsAuthFailRx   OBJECT-TYPE
    SYNTAX      Counter64
    MAX-ACCESS  read-only
    STATUS      current
    DESCRIPTION
    "Number of GTPV1 packets received with cause Auth Failure."
    ::= { jnxMbgPgwGtpGlbStatsEntry 260 }

jnxMbgPgwV1ICsAuthFailTx   OBJECT-TYPE
    SYNTAX      Counter64
    MAX-ACCESS  read-only
    STATUS      current
    DESCRIPTION
    "Number of GTPV1 packets sent with cause Auth Failure."
    ::= { jnxMbgPgwGtpGlbStatsEntry 261 }

jnxMbgPgwV1ICsUserAuthFailRx   OBJECT-TYPE
    SYNTAX      Counter64
    MAX-ACCESS  read-only
    STATUS      current
    DESCRIPTION
    "Number of GTPV1 packets received with cause User Auth Failure."
    ::= { jnxMbgPgwGtpGlbStatsEntry 262 }

jnxMbgPgwV1ICsUserAuthFailTx   OBJECT-TYPE
    SYNTAX      Counter64
    MAX-ACCESS  read-only
    STATUS      current
    DESCRIPTION
    "Number of GTPV1 packets sent with cause User Auth Failure."
    ::= { jnxMbgPgwGtpGlbStatsEntry 263 }

jnxMbgPgwV1ICsCtxNotFndRx   OBJECT-TYPE
    SYNTAX      Counter64
    MAX-ACCESS  read-only
    STATUS      current
    DESCRIPTION
    "Number of GTPV1 packets received with cause Context Not Found."
    ::= { jnxMbgPgwGtpGlbStatsEntry 264 }

jnxMbgPgwV1ICsCtxNotFndTx   OBJECT-TYPE
    SYNTAX      Counter64
    MAX-ACCESS  read-only
    STATUS      current
    DESCRIPTION
    "Number of GTPV1 packets sent with cause Context Not Found."
    ::= { jnxMbgPgwGtpGlbStatsEntry 265 }

jnxMbgPgwV1ICsAllDynPDPAdRx   OBJECT-TYPE
    SYNTAX      Counter64
    MAX-ACCESS  read-only
    STATUS      current
    DESCRIPTION
    "Number of GTPV1 packets received with cause Allow Dynamic PDP Address."
    ::= { jnxMbgPgwGtpGlbStatsEntry 266 }

jnxMbgPgwV1ICsAllDynPDPAdTx   OBJECT-TYPE
    SYNTAX      Counter64
    MAX-ACCESS  read-only
    STATUS      current
    DESCRIPTION
    "Number of GTPV1 packets sent with cause Allow Dynamic PDP Address."
    ::= { jnxMbgPgwGtpGlbStatsEntry 267 }

jnxMbgPgwV1ICsNoMemRx   OBJECT-TYPE
    SYNTAX      Counter64
    MAX-ACCESS  read-only
    STATUS      current
    DESCRIPTION
    "Number of GTPV1 packets received with cause No Memory."
    ::= { jnxMbgPgwGtpGlbStatsEntry 268 }

jnxMbgPgwV1ICsNoMemTx   OBJECT-TYPE
    SYNTAX      Counter64
    MAX-ACCESS  read-only
    STATUS      current
    DESCRIPTION
    "Number of GTPV1 packets sent with cause No Memory."
    ::= { jnxMbgPgwGtpGlbStatsEntry 269 }

jnxMbgPgwV1ICsRelocFailRx   OBJECT-TYPE
    SYNTAX      Counter64
    MAX-ACCESS  read-only
    STATUS      current
    DESCRIPTION
    "Number of GTPV1 packets received with cause Relocation Failed."
    ::= { jnxMbgPgwGtpGlbStatsEntry 270 }

jnxMbgPgwV1ICsRelocFailTx   OBJECT-TYPE
    SYNTAX      Counter64
    MAX-ACCESS  read-only
    STATUS      current
    DESCRIPTION
    "Number of GTPV1 packets sent with cause Relocation Failed."
    ::= { jnxMbgPgwGtpGlbStatsEntry 271 }

jnxMbgPgwV1ICsUnkManExhdrRx   OBJECT-TYPE
    SYNTAX      Counter64
    MAX-ACCESS  read-only
    STATUS      current
    DESCRIPTION
    "Number of GTPV1 packets received with cause Unknown Mandatory Extension Header."
    ::= { jnxMbgPgwGtpGlbStatsEntry 272 }

jnxMbgPgwV1ICsUnkManExhdrTx   OBJECT-TYPE
    SYNTAX      Counter64
    MAX-ACCESS  read-only
    STATUS      current
    DESCRIPTION
    "Number of GTPV1 packets sent with cause Unknown Mandatory Extension Header."
    ::= { jnxMbgPgwGtpGlbStatsEntry 273 }

jnxMbgPgwV1ICsSMANTTFTEr1Rx   OBJECT-TYPE
    SYNTAX      Counter64
    MAX-ACCESS  read-only
    STATUS      current
    DESCRIPTION
    "Number of GTPV1 packets received with cause Mandatory TFT Error."
    ::= { jnxMbgPgwGtpGlbStatsEntry 274 }

jnxMbgPgwV1ICsSMANTTFTEr1Tx   OBJECT-TYPE
    SYNTAX      Counter64
    MAX-ACCESS  read-only
    STATUS      current
    DESCRIPTION
    "Number of GTPV1 packets sent with cause Mandatory TFT Error."
    ::= { jnxMbgPgwGtpGlbStatsEntry 275 }

jnxMbgPgwV1ICsSYNTFTErr2Rx   OBJECT-TYPE
    SYNTAX      Counter64
    MAX-ACCESS  read-only
    STATUS      current
    DESCRIPTION
    "Number of GTPV1 packets received with cause Mandatory TFT Error."
    ::= { jnxMbgPgwGtpGlbStatsEntry 276 }

jnxMbgPgwV1ICsSYNTFTErr2Tx   OBJECT-TYPE
    SYNTAX      Counter64
    MAX-ACCESS  read-only
    STATUS      current
    DESCRIPTION
    "Number of GTPV1 packets sent with cause Mandatory TFT Error."
    ::= { jnxMbgPgwGtpGlbStatsEntry 277 }

jnxMbgPgwV1ICsSMNTPkFlEr1Rx   OBJECT-TYPE
    SYNTAX      Counter64
    MAX-ACCESS  read-only
    STATUS      current
    DESCRIPTION
    "Number of GTPV1 packets received with cause Mandatory Packet Filter Error."
    ::= { jnxMbgPgwGtpGlbStatsEntry 278 }

jnxMbgPgwV1ICsSMNTPkFlEr1Tx   OBJECT-TYPE
    SYNTAX      Counter64
    MAX-ACCESS  read-only
    STATUS      current
    DESCRIPTION
    "Number of GTPV1 packets sent with cause Mandatory Packet Filter Error."
    ::= { jnxMbgPgwGtpGlbStatsEntry 279 }

jnxMbgPgwV1ICsSYNPkFlErr2Rx   OBJECT-TYPE
    SYNTAX      Counter64
    MAX-ACCESS  read-only
    STATUS      current
    DESCRIPTION
    "Number of GTPV1 packets received with cause Mandatory Packet Filter Error."
    ::= { jnxMbgPgwGtpGlbStatsEntry 280 }

jnxMbgPgwV1ICsSYNPkFlErr2Tx   OBJECT-TYPE
    SYNTAX      Counter64
    MAX-ACCESS  read-only
    STATUS      current
    DESCRIPTION
    "Number of GTPV1 packets sent with cause Mandatory Packet Filter Error."
    ::= { jnxMbgPgwGtpGlbStatsEntry 281 }

jnxMbgPgwV1ICsMissUnknAPNRx   OBJECT-TYPE
    SYNTAX      Counter64
    MAX-ACCESS  read-only
    STATUS      current
    DESCRIPTION
    "Number of GTPV1 packets received with cause Unknowkn APN missing."
    ::= { jnxMbgPgwGtpGlbStatsEntry 282 }

jnxMbgPgwV1ICsMissUnknAPNTx   OBJECT-TYPE
    SYNTAX      Counter64
    MAX-ACCESS  read-only
    STATUS      current
    DESCRIPTION
    "Number of GTPV1 packets sent with cause Unknowkn APN missing."
    ::= { jnxMbgPgwGtpGlbStatsEntry 283 }

jnxMbgPgwV1ICsUnknPDPAdRx   OBJECT-TYPE
    SYNTAX      Counter64
    MAX-ACCESS  read-only
    STATUS      current
    DESCRIPTION
    "Number of GTPV1 packets received with cause Unknowkn PDP Address."
    ::= { jnxMbgPgwGtpGlbStatsEntry 284 }

jnxMbgPgwV1ICsUnknPDPAdTx   OBJECT-TYPE
    SYNTAX      Counter64
    MAX-ACCESS  read-only
    STATUS      current
    DESCRIPTION
    "Number of GTPV1 packets sent with cause Unknowkn PDP Address."
    ::= { jnxMbgPgwGtpGlbStatsEntry 285 }

jnxMbgPgwV1ICsNoTFTCtxExRx   OBJECT-TYPE
    SYNTAX      Counter64
    MAX-ACCESS  read-only
    STATUS      current
    DESCRIPTION
    "Number of GTPV1 packets received with cause No TFT Context Exists."
    ::= { jnxMbgPgwGtpGlbStatsEntry 286 }

jnxMbgPgwV1ICsNoTFTCtxExTx   OBJECT-TYPE
    SYNTAX      Counter64
    MAX-ACCESS  read-only
    STATUS      current
    DESCRIPTION
    "Number of GTPV1 packets sent with cause No TFT Context Exists."
    ::= { jnxMbgPgwGtpGlbStatsEntry 287 }

jnxMbgPgwV0ProtocolErrRx  OBJECT-TYPE
    SYNTAX      Counter64
    MAX-ACCESS  read-only
    STATUS      current
    DESCRIPTION
    "Number of GTPv0 Protocol Errors Received."
    ::= { jnxMbgPgwGtpGlbStatsEntry 288 }

jnxMbgPgwV0UnSupportedMsgRx  OBJECT-TYPE
    SYNTAX      Counter64
    MAX-ACCESS  read-only
    STATUS      current
    DESCRIPTION
    "Number of GTPv0 Unsupported Messages received."
    ::= { jnxMbgPgwGtpGlbStatsEntry 289 }

jnxMbgPgwV0T3RespTmrExpRx  OBJECT-TYPE
    SYNTAX      Counter64
    MAX-ACCESS  read-only
    STATUS      current
    DESCRIPTION
    "Number of GTP V0 T3 timer expiries Received."
    ::= { jnxMbgPgwGtpGlbStatsEntry 290 }

jnxMbgPgwV0GlbNumMsgRx  OBJECT-TYPE
    SYNTAX      Counter64
    MAX-ACCESS  read-only
    STATUS      current
    DESCRIPTION
    "Number of GTPv0 messages received."
    ::= { jnxMbgPgwGtpGlbStatsEntry 291 }

jnxMbgPgwV0GlbNumMsgTx  OBJECT-TYPE
    SYNTAX      Counter64
    MAX-ACCESS  read-only
    STATUS      current
    DESCRIPTION
    "Number of GTP V0 messages sent."
    ::= { jnxMbgPgwGtpGlbStatsEntry 292 }

jnxMbgPgwV0GlbNumBytesRx  OBJECT-TYPE
    SYNTAX      Counter64
    MAX-ACCESS  read-only
    STATUS      current
    DESCRIPTION
    "Number of GTPv0 bytes received."
    ::= { jnxMbgPgwGtpGlbStatsEntry 293 }

jnxMbgPgwV0GlbNumBytesTx  OBJECT-TYPE
    SYNTAX      Counter64
    MAX-ACCESS  read-only
    STATUS      current
    DESCRIPTION
    "Number of GTP V0 bytes sent."
    ::= { jnxMbgPgwGtpGlbStatsEntry 294 }

jnxMbgPgwV0GlbEchoReqRx  OBJECT-TYPE
    SYNTAX      Counter64
    MAX-ACCESS  read-only
    STATUS      current
    DESCRIPTION
   "Number of GTP V0 Echo Requests received."
    ::= { jnxMbgPgwGtpGlbStatsEntry 295 }

jnxMbgPgwV0GlbEchoReqTx  OBJECT-TYPE
    SYNTAX      Counter64
    MAX-ACCESS  read-only
    STATUS      current
    DESCRIPTION
    "Number of GTP V0 Echo Requests Sent."
    ::= { jnxMbgPgwGtpGlbStatsEntry 296 }

jnxMbgPgwV0GlbEchoRespRx  OBJECT-TYPE
    SYNTAX      Counter64
    MAX-ACCESS  read-only
    STATUS      current
    DESCRIPTION
    "Number of GTP V0 Echo Responses received."
    ::= { jnxMbgPgwGtpGlbStatsEntry 297 }

jnxMbgPgwV0GlbEchoRespTx  OBJECT-TYPE
    SYNTAX      Counter64
    MAX-ACCESS  read-only
    STATUS      current
    DESCRIPTION
    "Number of GTP V0 Echo Responses Sent."
    ::= { jnxMbgPgwGtpGlbStatsEntry 298 }

jnxMbgPgwV0GlbVerNotSupRx OBJECT-TYPE
    SYNTAX      Counter64
    MAX-ACCESS  read-only
    STATUS      current
    DESCRIPTION
    "Number of GTP V0 Version Not supported messages received"
    ::= { jnxMbgPgwGtpGlbStatsEntry 299 }

jnxMbgPgwV0GlbVerNotSupTx OBJECT-TYPE
    SYNTAX      Counter64
    MAX-ACCESS  read-only
    STATUS      current
    DESCRIPTION
    "Number of GTP V0 version not supported messages Sent."
    ::= { jnxMbgPgwGtpGlbStatsEntry 300 }

jnxMbgPgwV0GlbCrtPdpCxtReqRx   OBJECT-TYPE
    SYNTAX      Counter64
    MAX-ACCESS  read-only
    STATUS      current
    DESCRIPTION
    "Number of GTP V0 Create PDP Context Requests Received."
    ::= { jnxMbgPgwGtpGlbStatsEntry 301 }

jnxMbgPgwV0GlbCrtPdpCxtReqTx   OBJECT-TYPE
    SYNTAX      Counter64
    MAX-ACCESS  read-only
    STATUS      current
    DESCRIPTION
    "Number of GTP V0 Create PDP Context Requests Sent."
    ::= { jnxMbgPgwGtpGlbStatsEntry 302 }

jnxMbgPgwV0GlbCrtPdpCxtRspRx   OBJECT-TYPE
    SYNTAX      Counter64
    MAX-ACCESS  read-only
    STATUS      current
    DESCRIPTION
    "Number of GTP V0 Create PDP Context Responses Received."
    ::= { jnxMbgPgwGtpGlbStatsEntry 303 }

jnxMbgPgwV0GlbCrtPdpCxtRspTx   OBJECT-TYPE
    SYNTAX      Counter64
    MAX-ACCESS  read-only
    STATUS      current
    DESCRIPTION
    "Number of GTP V0 Create PDP Context Responses Sent."
    ::= { jnxMbgPgwGtpGlbStatsEntry 304 }

jnxMbgPgwV0GlbUpdPdpCxtReqRx   OBJECT-TYPE
    SYNTAX      Counter64
    MAX-ACCESS  read-only
    STATUS      current
    DESCRIPTION
    "Number of GTP V0 Update PDP Context Requests Received."
    ::= { jnxMbgPgwGtpGlbStatsEntry 305 }

jnxMbgPgwV0GlbUpdPdpCxtReqTx   OBJECT-TYPE
    SYNTAX      Counter64
    MAX-ACCESS  read-only
    STATUS      current
    DESCRIPTION
    "Number of GTP V0 Update PDP Context Requests Sent."
    ::= { jnxMbgPgwGtpGlbStatsEntry 306 }

jnxMbgPgwV0GlbUpdPdpCxtRspRx   OBJECT-TYPE
    SYNTAX      Counter64
    MAX-ACCESS  read-only
    STATUS      current
    DESCRIPTION
    "Number of GTP V0 Update PDP Context Responses Received."
    ::= { jnxMbgPgwGtpGlbStatsEntry 307 }

jnxMbgPgwV0GlbUpdPdpCxtRspTx   OBJECT-TYPE
    SYNTAX      Counter64
    MAX-ACCESS  read-only
    STATUS      current
    DESCRIPTION
    "Number of GTP V0 Update PDP Context Responses Sent."
    ::= { jnxMbgPgwGtpGlbStatsEntry 308 }

jnxMbgPgwV0GlbDelPdpCxtReqRx   OBJECT-TYPE
    SYNTAX      Counter64
    MAX-ACCESS  read-only
    STATUS      current
    DESCRIPTION
    "Number of GTP V0 Delete PDP Context Requests Received."
    ::= { jnxMbgPgwGtpGlbStatsEntry 309 }

jnxMbgPgwV0GlbDelPdpCxtReqTx   OBJECT-TYPE
    SYNTAX      Counter64
    MAX-ACCESS  read-only
    STATUS      current
    DESCRIPTION
    "Number of GTP V0 Delete PDP Context Requests Sent."
    ::= { jnxMbgPgwGtpGlbStatsEntry 310 }

jnxMbgPgwV0GlbDelPdpCxtRspRx   OBJECT-TYPE
    SYNTAX      Counter64
    MAX-ACCESS  read-only
    STATUS      current
    DESCRIPTION
    "Number of GTP V0 Delete PDP Context Responses Received."
    ::= { jnxMbgPgwGtpGlbStatsEntry 311 }

jnxMbgPgwV0GlbDelPdpCxtRspTx   OBJECT-TYPE
    SYNTAX      Counter64
    MAX-ACCESS  read-only
    STATUS      current
    DESCRIPTION
    "Number of GTP V0 Delete PDP Context Responses Sent."
    ::= { jnxMbgPgwGtpGlbStatsEntry 312 }

jnxMbgPgwV0GlbCrtAAPdpCxtReqRx   OBJECT-TYPE
    SYNTAX      Counter64
    MAX-ACCESS  read-only
    STATUS      current
    DESCRIPTION
    "Number of GTP V0 Create AA PDP Context Requests Received."
    ::= { jnxMbgPgwGtpGlbStatsEntry 313 }

jnxMbgPgwV0GlbCrtAAPdpCxtReqTx   OBJECT-TYPE
    SYNTAX      Counter64
    MAX-ACCESS  read-only
    STATUS      current
    DESCRIPTION
    "Number of GTP V0 Create AA PDP Context Requests Sent."
    ::= { jnxMbgPgwGtpGlbStatsEntry 314 }

jnxMbgPgwV0GlbCrtAAPdpCxtRspRx   OBJECT-TYPE
    SYNTAX      Counter64
    MAX-ACCESS  read-only
    STATUS      current
    DESCRIPTION
    "Number of GTP V0 Create AA PDP Context Responses Received."
    ::= { jnxMbgPgwGtpGlbStatsEntry 315 }

jnxMbgPgwV0GlbCrtAAPdpCxtRspTx   OBJECT-TYPE
    SYNTAX      Counter64
    MAX-ACCESS  read-only
    STATUS      current
    DESCRIPTION
    "Number of GTP V0 Create AA PDP Context Responses Sent."
    ::= { jnxMbgPgwGtpGlbStatsEntry 316 }

jnxMbgPgwV0GlbDelAAPdpCxtReqRx   OBJECT-TYPE
    SYNTAX      Counter64
    MAX-ACCESS  read-only
    STATUS      current
    DESCRIPTION
    "Number of GTP V0 Delete AA PDP Context Requests Received."
    ::= { jnxMbgPgwGtpGlbStatsEntry 317 }

jnxMbgPgwV0GlbDelAAPdpCxtReqTx   OBJECT-TYPE
    SYNTAX      Counter64
    MAX-ACCESS  read-only
    STATUS      current
    DESCRIPTION
    "Number of GTP V0 Delete AA PDP Context Requests Sent."
    ::= { jnxMbgPgwGtpGlbStatsEntry 318 }

jnxMbgPgwV0GlbDelAAPdpCxtRspRx   OBJECT-TYPE
    SYNTAX      Counter64
    MAX-ACCESS  read-only
    STATUS      current
    DESCRIPTION
    "Number of GTP V0 Delete AA PDP Context Responses Received."
    ::= { jnxMbgPgwGtpGlbStatsEntry 319 }

jnxMbgPgwV0GlbDelAAPdpCxtRspTx   OBJECT-TYPE
    SYNTAX      Counter64
    MAX-ACCESS  read-only
    STATUS      current
    DESCRIPTION
    "Number of GTP V0 Delete AA PDP Context Responses Sent."
    ::= { jnxMbgPgwGtpGlbStatsEntry 320 }

jnxMbgPgwV0GlbErrorIndRx   OBJECT-TYPE
    SYNTAX      Counter64
    MAX-ACCESS  read-only
    STATUS      current
    DESCRIPTION
    "Number of GTP V0 Error Indication messages Received."
    ::= { jnxMbgPgwGtpGlbStatsEntry 321 }

jnxMbgPgwV0GlbErrorIndTx   OBJECT-TYPE
    SYNTAX      Counter64
    MAX-ACCESS  read-only
    STATUS      current
    DESCRIPTION
    "Number of GTP V0 Error Indication messages Sent."
    ::= { jnxMbgPgwGtpGlbStatsEntry 322 }

jnxMbgPgwV0GlbNotifReqRx   OBJECT-TYPE
    SYNTAX      Counter64
    MAX-ACCESS  read-only
    STATUS      current
    DESCRIPTION
    "Number of GTP V0 Notify Requests Received."
    ::= { jnxMbgPgwGtpGlbStatsEntry 323 }

jnxMbgPgwV0GlbNotifReqTx   OBJECT-TYPE
    SYNTAX      Counter64
    MAX-ACCESS  read-only
    STATUS      current
    DESCRIPTION
    "Number of GTP V0 Notify Requests Sent."
    ::= { jnxMbgPgwGtpGlbStatsEntry 324 }

jnxMbgPgwV0GlbNotifRspRx   OBJECT-TYPE
    SYNTAX      Counter64
    MAX-ACCESS  read-only
    STATUS      current
    DESCRIPTION
    "Number of GTP V0 Notify Responses Received."
    ::= { jnxMbgPgwGtpGlbStatsEntry 325 }

jnxMbgPgwV0GlbNotifRspTx   OBJECT-TYPE
    SYNTAX      Counter64
    MAX-ACCESS  read-only
    STATUS      current
    DESCRIPTION
    "Number of GTP V0 Notify Responses Sent."
    ::= { jnxMbgPgwGtpGlbStatsEntry 326 }

jnxMbgPgwV0GlbNotifRejReqRx   OBJECT-TYPE
    SYNTAX      Counter64
    MAX-ACCESS  read-only
    STATUS      current
    DESCRIPTION
    "Number of GTP V0 Notify Reject Requests Received."
    ::= { jnxMbgPgwGtpGlbStatsEntry 327 }

jnxMbgPgwV0GlbNotifRejReqTx   OBJECT-TYPE
    SYNTAX      Counter64
    MAX-ACCESS  read-only
    STATUS      current
    DESCRIPTION
    "Number of GTP V0 Notify Reject Requests Sent."
    ::= { jnxMbgPgwGtpGlbStatsEntry 328 }

jnxMbgPgwV0GlbNotifRejRspRx   OBJECT-TYPE
    SYNTAX      Counter64
    MAX-ACCESS  read-only
    STATUS      current
    DESCRIPTION
    "Number of GTP V0 Notify Reject Responses Received."
    ::= { jnxMbgPgwGtpGlbStatsEntry 329 }

jnxMbgPgwV0GlbNotifRejRspTx   OBJECT-TYPE
    SYNTAX      Counter64
    MAX-ACCESS  read-only
    STATUS      current
    DESCRIPTION
    "Number of GTP V0 Notify Reject Responses Sent."
    ::= { jnxMbgPgwGtpGlbStatsEntry 330 }

jnxMbgPgwV0GlbRtInfReqRx   OBJECT-TYPE
    SYNTAX      Counter64
    MAX-ACCESS  read-only
    STATUS      current
    DESCRIPTION
    "Number of GTP V0 Routing Information Requests Received."
    ::= { jnxMbgPgwGtpGlbStatsEntry 331 }

jnxMbgPgwV0GlbRtInfReqTx   OBJECT-TYPE
    SYNTAX      Counter64
    MAX-ACCESS  read-only
    STATUS      current
    DESCRIPTION
    "Number of GTP V0 Routing Information Requests Sent."
    ::= { jnxMbgPgwGtpGlbStatsEntry 332 }

jnxMbgPgwV0GlbRtInfRspRx   OBJECT-TYPE
    SYNTAX      Counter64
    MAX-ACCESS  read-only
    STATUS      current
    DESCRIPTION
    "Number of GTP V0 Routing Information Responses Received."
    ::= { jnxMbgPgwGtpGlbStatsEntry 333 }

jnxMbgPgwV0GlbRtInfRspTx   OBJECT-TYPE
    SYNTAX      Counter64
    MAX-ACCESS  read-only
    STATUS      current
    DESCRIPTION
    "Number of GTP V0 Routing Information Responses Sent."
    ::= { jnxMbgPgwGtpGlbStatsEntry 334 }

jnxMbgPgwV0GlbFailRptReqRx   OBJECT-TYPE
    SYNTAX      Counter64
    MAX-ACCESS  read-only
    STATUS      current
    DESCRIPTION
    "Number of GTP V0 Fail Repeat Requests Received."
    ::= { jnxMbgPgwGtpGlbStatsEntry 335 }

jnxMbgPgwV0GlbFailRptReqTx   OBJECT-TYPE
    SYNTAX      Counter64
    MAX-ACCESS  read-only
    STATUS      current
    DESCRIPTION
    "Number of GTP V0 Fail Repeat Requests Sent."
    ::= { jnxMbgPgwGtpGlbStatsEntry 336 }

jnxMbgPgwV0GlbFailRptRspRx   OBJECT-TYPE
    SYNTAX      Counter64
    MAX-ACCESS  read-only
    STATUS      current
    DESCRIPTION
    "Number of GTP V0 Fail Repeat Responses Received."
    ::= { jnxMbgPgwGtpGlbStatsEntry 337 }

jnxMbgPgwV0GlbFailRptRspTx   OBJECT-TYPE
    SYNTAX      Counter64
    MAX-ACCESS  read-only
    STATUS      current
    DESCRIPTION
    "Number of GTP V0 Fail Repeat Responses Sent."
    ::= { jnxMbgPgwGtpGlbStatsEntry 338 }

jnxMbgPgwV0GlbNotMSPresReqRx   OBJECT-TYPE
    SYNTAX      Counter64
    MAX-ACCESS  read-only
    STATUS      current
    DESCRIPTION
    "Number of GTP V0 MS Not Present Requests Received."
    ::= { jnxMbgPgwGtpGlbStatsEntry 339 }

jnxMbgPgwV0GlbNotMSPresReqTx   OBJECT-TYPE
    SYNTAX      Counter64
    MAX-ACCESS  read-only
    STATUS      current
    DESCRIPTION
    "Number of GTP V0 MS Not Present Requests Sent."
    ::= { jnxMbgPgwGtpGlbStatsEntry 340 }

jnxMbgPgwV0GlbNotMSPresRspRx   OBJECT-TYPE
    SYNTAX      Counter64
    MAX-ACCESS  read-only
    STATUS      current
    DESCRIPTION
    "Number of GTP V0 MS Not Present Responses Received."
    ::= { jnxMbgPgwGtpGlbStatsEntry 341 }

jnxMbgPgwV0GlbNotMSPresRspTx   OBJECT-TYPE
    SYNTAX      Counter64
    MAX-ACCESS  read-only
    STATUS      current
    DESCRIPTION
    "Number of GTP V0 MS Not Present Responses Sent."
    ::= { jnxMbgPgwGtpGlbStatsEntry 342 }

jnxMbgPgwV0ICsReqAcceptedRx   OBJECT-TYPE
    SYNTAX      Counter64
    MAX-ACCESS  read-only
    STATUS      current
    DESCRIPTION
    "Number of GTPV0 packets received with cause Request Accepted."
    ::= { jnxMbgPgwGtpGlbStatsEntry 343 }

jnxMbgPgwV0ICsReqAcceptedTx   OBJECT-TYPE
    SYNTAX      Counter64
    MAX-ACCESS  read-only
    STATUS      current
    DESCRIPTION
    "Number of GTPV0 packets sent with cause Request Accepted."
    ::= { jnxMbgPgwGtpGlbStatsEntry 344 }

jnxMbgPgwV0ICsNonExistRx   OBJECT-TYPE
    SYNTAX      Counter64
    MAX-ACCESS  read-only
    STATUS      current
    DESCRIPTION
    "Number of GTPV0 packets received with cause Non Existant ."
    ::= { jnxMbgPgwGtpGlbStatsEntry 345 }

jnxMbgPgwV0ICsNonExistTx   OBJECT-TYPE
    SYNTAX      Counter64
    MAX-ACCESS  read-only
    STATUS      current
    DESCRIPTION
    "Number of GTPV0 packets sent with cause Non Existant."
    ::= { jnxMbgPgwGtpGlbStatsEntry 346 }

jnxMbgPgwV0ICsInvMsgFmtRx   OBJECT-TYPE
    SYNTAX      Counter64
    MAX-ACCESS  read-only
    STATUS      current
    DESCRIPTION
    "Number of GTPV0 packets received with cause Invalid Mesage Format."
    ::= { jnxMbgPgwGtpGlbStatsEntry 347 }

jnxMbgPgwV0ICsInvMsgFmtTx   OBJECT-TYPE
    SYNTAX      Counter64
    MAX-ACCESS  read-only
    STATUS      current
    DESCRIPTION
    "Number of GTPV0 packets sent with cause Invalid Mesage Format."
    ::= { jnxMbgPgwGtpGlbStatsEntry 348 }

jnxMbgPgwV0ICsIMSINotKnownRx   OBJECT-TYPE
    SYNTAX      Counter64
    MAX-ACCESS  read-only
    STATUS      current
    DESCRIPTION
    "Number of GTPV0 packets received with cause IMSI Not Known."
    ::= { jnxMbgPgwGtpGlbStatsEntry 349 }


jnxMbgPgwV0ICsIMSINotKnownTx   OBJECT-TYPE
    SYNTAX      Counter64
    MAX-ACCESS  read-only
    STATUS      current
    DESCRIPTION
    "Number of GTPV0 packets sent with cause IMSI Not Known."
    ::= { jnxMbgPgwGtpGlbStatsEntry 350 }

jnxMbgPgwV0ICsMSGRPSDetachRx   OBJECT-TYPE
    SYNTAX      Counter64
    MAX-ACCESS  read-only
    STATUS      current
    DESCRIPTION
    "Number of GTPV0 packets received with cause MS GPRS Detached."
    ::= { jnxMbgPgwGtpGlbStatsEntry 351 }

jnxMbgPgwV0ICsMSGRPSDetachTx   OBJECT-TYPE
    SYNTAX      Counter64
    MAX-ACCESS  read-only
    STATUS      current
    DESCRIPTION
    "Number of GTPV0 packets sent with cause MS GPRS Detached."
    ::= { jnxMbgPgwGtpGlbStatsEntry 352 }

jnxMbgPgwV0ICsMSNotGRPSRespRx   OBJECT-TYPE
    SYNTAX      Counter64
    MAX-ACCESS  read-only
    STATUS      current
    DESCRIPTION
    "Number of GTPV0 packets received with cause MS No GPRS Response."
    ::= { jnxMbgPgwGtpGlbStatsEntry 353 }

jnxMbgPgwV0ICsMSNotGRPSRespTx   OBJECT-TYPE
    SYNTAX      Counter64
    MAX-ACCESS  read-only
    STATUS      current
    DESCRIPTION
    "Number of GTPV0 packets sent with cause MS No GPRS Response."
    ::= { jnxMbgPgwGtpGlbStatsEntry 354 }

jnxMbgPgwV0ICsMSRefusesRx   OBJECT-TYPE
    SYNTAX      Counter64
    MAX-ACCESS  read-only
    STATUS      current
    DESCRIPTION
    "Number of GTPV0 packets received with cause MS Refues."
    ::= { jnxMbgPgwGtpGlbStatsEntry 355 }

jnxMbgPgwV0ICsMSRefusesTx   OBJECT-TYPE
    SYNTAX      Counter64
    MAX-ACCESS  read-only
    STATUS      current
    DESCRIPTION
    "Number of GTPV0 packets sent with cause MS Refues."
    ::= { jnxMbgPgwGtpGlbStatsEntry 356 }

jnxMbgPgwV0ICsVerNotSuppRx   OBJECT-TYPE
    SYNTAX      Counter64
    MAX-ACCESS  read-only
    STATUS      current
    DESCRIPTION
    "Number of GTPV0 packets received with cause Version Not Supported."
    ::= { jnxMbgPgwGtpGlbStatsEntry 357 }

jnxMbgPgwV0ICsVerNotSuppTx   OBJECT-TYPE
    SYNTAX      Counter64
    MAX-ACCESS  read-only
    STATUS      current
    DESCRIPTION
    "Number of GTPV0 packets sent with cause Version Not Supported."
    ::= { jnxMbgPgwGtpGlbStatsEntry 358 }

jnxMbgPgwV0ICsNoResRx   OBJECT-TYPE
    SYNTAX      Counter64
    MAX-ACCESS  read-only
    STATUS      current
    DESCRIPTION
    "Number of GTPV0 packets received with cause No Response."
    ::= { jnxMbgPgwGtpGlbStatsEntry 359 }

jnxMbgPgwV0ICsNoResTx   OBJECT-TYPE
    SYNTAX      Counter64
    MAX-ACCESS  read-only
    STATUS      current
    DESCRIPTION
    "Number of GTPV0 packets sent with cause No Response."
    ::= { jnxMbgPgwGtpGlbStatsEntry 360 }

jnxMbgPgwV0ICsServNotSuppRx   OBJECT-TYPE
    SYNTAX      Counter64
    MAX-ACCESS  read-only
    STATUS      current
    DESCRIPTION
    "Number of GTPV0 packets received with cause Service Not Supported."
    ::= { jnxMbgPgwGtpGlbStatsEntry 361 }

jnxMbgPgwV0ICsServNotSuppTx   OBJECT-TYPE
    SYNTAX      Counter64
    MAX-ACCESS  read-only
    STATUS      current
    DESCRIPTION
    "Number of GTPV0 packets sent with cause Service Not Supported."
    ::= { jnxMbgPgwGtpGlbStatsEntry 362 }

jnxMbgPgwV0ICsManIEIncrtRx   OBJECT-TYPE
    SYNTAX      Counter64
    MAX-ACCESS  read-only
    STATUS      current
    DESCRIPTION
    "Number of GTPV0 packets received with cause Mandatory IE incorrect."
    ::= { jnxMbgPgwGtpGlbStatsEntry 363 }

jnxMbgPgwV0ICsManIEIncrtTx   OBJECT-TYPE
    SYNTAX      Counter64
    MAX-ACCESS  read-only
    STATUS      current
    DESCRIPTION
    "Number of GTPV0 packets sent with cause Mandatory IE incorrect."
    ::= { jnxMbgPgwGtpGlbStatsEntry 364 }

jnxMbgPgwV0ICsManIEMissRx   OBJECT-TYPE
    SYNTAX      Counter64
    MAX-ACCESS  read-only
    STATUS      current
    DESCRIPTION
    "Number of GTPV0 packets received with cause Mandatory IE Missing."
    ::= { jnxMbgPgwGtpGlbStatsEntry 365 }

jnxMbgPgwV0ICsManIEMissTx   OBJECT-TYPE
    SYNTAX      Counter64
    MAX-ACCESS  read-only
    STATUS      current
    DESCRIPTION
    "Number of GTPV0 packets sent with cause Mandatory IE Missing."
    ::= { jnxMbgPgwGtpGlbStatsEntry 366 }

jnxMbgPgwV0ICsOptIEIncrtRx   OBJECT-TYPE
    SYNTAX      Counter64
    MAX-ACCESS  read-only
    STATUS      current
    DESCRIPTION
    "Number of GTPV0 packets received with cause Optional IE incorrect."
    ::= { jnxMbgPgwGtpGlbStatsEntry 367 }

jnxMbgPgwV0ICsOptIEIncrtTx   OBJECT-TYPE
    SYNTAX      Counter64
    MAX-ACCESS  read-only
    STATUS      current
    DESCRIPTION
    "Number of GTPV0 packets sent with cause Optional IE incorrect."
    ::= { jnxMbgPgwGtpGlbStatsEntry 368 }

jnxMbgPgwV0ICsSysFailRx   OBJECT-TYPE
    SYNTAX      Counter64
    MAX-ACCESS  read-only
    STATUS      current
    DESCRIPTION
    "Number of GTPV0 packets received with cause System Failure."
    ::= { jnxMbgPgwGtpGlbStatsEntry 369 }

jnxMbgPgwV0ICsSysFailTx   OBJECT-TYPE
    SYNTAX      Counter64
    MAX-ACCESS  read-only
    STATUS      current
    DESCRIPTION
    "Number of GTPV0 packets sent with cause System Failure."
    ::= { jnxMbgPgwGtpGlbStatsEntry 370 }

jnxMbgPgwV0ICsRoamRestrictRx   OBJECT-TYPE
    SYNTAX      Counter64
    MAX-ACCESS  read-only
    STATUS      current
    DESCRIPTION
    "Number of GTPV0 packets received with cause Roaming Restricted."
    ::= { jnxMbgPgwGtpGlbStatsEntry 371 }

jnxMbgPgwV0ICsRoamRestrictTx   OBJECT-TYPE
    SYNTAX      Counter64
    MAX-ACCESS  read-only
    STATUS      current
    DESCRIPTION
    "Number of GTPV0 packets sent with cause Roaming Restricted."
    ::= { jnxMbgPgwGtpGlbStatsEntry 372 }

jnxMbgPgwV0ICsPTMSISigMMRx   OBJECT-TYPE
    SYNTAX      Counter64
    MAX-ACCESS  read-only
    STATUS      current
    DESCRIPTION
    "Number of GTPV0 packets received with cause PTMSI Signature Mismatch."
    ::= { jnxMbgPgwGtpGlbStatsEntry 373 }

jnxMbgPgwV0ICsPTMSISigMMTx   OBJECT-TYPE
    SYNTAX      Counter64
    MAX-ACCESS  read-only
    STATUS      current
    DESCRIPTION
    "Number of GTPV0 packets sent with cause PTMSI Signature Mismatch."
    ::= { jnxMbgPgwGtpGlbStatsEntry 374 }

jnxMbgPgwV0ICsGPRSConnSuppRx   OBJECT-TYPE
    SYNTAX      Counter64
    MAX-ACCESS  read-only
    STATUS      current
    DESCRIPTION
    "Number of GTPV0 packets received with cause GPRS Connection Supported."
    ::= { jnxMbgPgwGtpGlbStatsEntry 375 }

jnxMbgPgwV0ICsGPRSConnSuppTx   OBJECT-TYPE
    SYNTAX      Counter64
    MAX-ACCESS  read-only
    STATUS      current
    DESCRIPTION
    "Number of GTPV0 packets sent with cause GPRS Connection Supported."
    ::= { jnxMbgPgwGtpGlbStatsEntry 376 }

jnxMbgPgwV0ICsAuthFailRx   OBJECT-TYPE
    SYNTAX      Counter64
    MAX-ACCESS  read-only
    STATUS      current
    DESCRIPTION
    "Number of GTPV0 packets received with cause Auth Failure."
    ::= { jnxMbgPgwGtpGlbStatsEntry 377 }

jnxMbgPgwV0ICsAuthFailTx   OBJECT-TYPE
    SYNTAX      Counter64
    MAX-ACCESS  read-only
    STATUS      current
    DESCRIPTION
    "Number of GTPV0 packets sent with cause Auth Failure."
    ::= { jnxMbgPgwGtpGlbStatsEntry 378 }

jnxMbgPgwV0ICsUserAuthFailRx   OBJECT-TYPE
    SYNTAX      Counter64
    MAX-ACCESS  read-only
    STATUS      current
    DESCRIPTION
    "Number of GTPV0 packets received with cause User Auth Failure."
    ::= { jnxMbgPgwGtpGlbStatsEntry 379 }

jnxMbgPgwV0ICsUserAuthFailTx   OBJECT-TYPE
    SYNTAX      Counter64
    MAX-ACCESS  read-only
    STATUS      current
    DESCRIPTION
    "Number of GTPV0 packets sent with cause User Auth Failure."
    ::= { jnxMbgPgwGtpGlbStatsEntry 380 }

jnxMbgPgwGtpV2ICsLclDetRx OBJECT-TYPE
         SYNTAX      Counter64
         MAX-ACCESS  read-only
         STATUS      current
         DESCRIPTION
         "Number of GTP packets received with cause Local Detach."
     ::= { jnxMbgPgwGtpGlbStatsEntry 381 }

jnxMbgPgwGtpV2ICsLclDetTx OBJECT-TYPE
         SYNTAX      Counter64
         MAX-ACCESS  read-only
         STATUS      current
         DESCRIPTION
         "Number of GTP packets sent with cause Local Detach."
     ::= { jnxMbgPgwGtpGlbStatsEntry 382 }

jnxMbgPgwGtpV2ICsCmpDetRx OBJECT-TYPE
         SYNTAX      Counter64
         MAX-ACCESS  read-only
         STATUS      current
         DESCRIPTION
         "Number of GTP packets received with cause Complete Detach."
     ::= { jnxMbgPgwGtpGlbStatsEntry 383 }

jnxMbgPgwGtpV2ICsCmpDetTx OBJECT-TYPE
         SYNTAX      Counter64
         MAX-ACCESS  read-only
         STATUS      current
         DESCRIPTION
         "Number of GTP packets sent with cause Complete Detach."
     ::= { jnxMbgPgwGtpGlbStatsEntry 384 }

jnxMbgPgwGtpV2ICsRATChgRx OBJECT-TYPE
         SYNTAX      Counter64
         MAX-ACCESS  read-only
         STATUS      current
         DESCRIPTION
         "Number of GTP packets received with cause RAT changed from 3GPP to non 3GPP."
     ::= { jnxMbgPgwGtpGlbStatsEntry 385 }

jnxMbgPgwGtpV2ICsRATChgTx OBJECT-TYPE
         SYNTAX      Counter64
         MAX-ACCESS  read-only
         STATUS      current
         DESCRIPTION
         "Number of GTP packets sent with cause RAT changed from 3GPP to non 3GPP."
     ::= { jnxMbgPgwGtpGlbStatsEntry 386 }

jnxMbgPgwGtpV2ICsISRDeactRx OBJECT-TYPE
         SYNTAX      Counter64
         MAX-ACCESS  read-only
         STATUS      current
         DESCRIPTION
         "Number of GTP packets received with cause ISR Deactivated."
     ::= { jnxMbgPgwGtpGlbStatsEntry 387 }

jnxMbgPgwGtpV2ICsISRDeactTx OBJECT-TYPE
         SYNTAX      Counter64
         MAX-ACCESS  read-only
         STATUS      current
         DESCRIPTION
         "Number of GTP packets sent with cause ISR Deactivated."
     ::= { jnxMbgPgwGtpGlbStatsEntry 388 }

jnxMbgPgwGtpV2ICsEIFRNCEnRx OBJECT-TYPE
         SYNTAX      Counter64
         MAX-ACCESS  read-only
         STATUS      current
         DESCRIPTION
         "Number of GTP packets received with cause Error Indication from RNC eNodeB."
     ::= { jnxMbgPgwGtpGlbStatsEntry 389 }

jnxMbgPgwGtpV2ICsEIFRNCEnTx OBJECT-TYPE
         SYNTAX      Counter64
         MAX-ACCESS  read-only
         STATUS      current
         DESCRIPTION
         "Number of GTP packets sent with cause Error Indication from RNC eNodeB."
     ::= { jnxMbgPgwGtpGlbStatsEntry 390 }

jnxMbgPgwGtpV2ICsSemErTADRx OBJECT-TYPE
         SYNTAX      Counter64
         MAX-ACCESS  read-only
         STATUS      current
         DESCRIPTION
         "Number of GTP packets received with cause Semantic Error in TAD Operation."
     ::= { jnxMbgPgwGtpGlbStatsEntry 391 }

jnxMbgPgwGtpV2ICsSemErTADTx OBJECT-TYPE
         SYNTAX      Counter64
         MAX-ACCESS  read-only
         STATUS      current
         DESCRIPTION
         "Number of GTP packets sent with cause Semantic Error in TAD Operation."
     ::= { jnxMbgPgwGtpGlbStatsEntry 392 }

jnxMbgPgwGtpV2ICsSynErTADRx OBJECT-TYPE
         SYNTAX      Counter64
         MAX-ACCESS  read-only
         STATUS      current
         DESCRIPTION
         "Number of GTP packets received with cause Syntactic Error in TAD Operation."
     ::= { jnxMbgPgwGtpGlbStatsEntry 393 }

jnxMbgPgwGtpV2ICsSynErTADTx OBJECT-TYPE
         SYNTAX      Counter64
         MAX-ACCESS  read-only
         STATUS      current
         DESCRIPTION
         "Number of GTP packets sent with cause Syntactic Error in TAD Operation."
     ::= { jnxMbgPgwGtpGlbStatsEntry 394 }

jnxMbgPgwGtpV2ICsRMValRcvRx OBJECT-TYPE
         SYNTAX      Counter64
         MAX-ACCESS  read-only
         STATUS      current
         DESCRIPTION
         "Number of GTP packets received with cause Reserved Message Value Received."
     ::= { jnxMbgPgwGtpGlbStatsEntry 395 }

jnxMbgPgwGtpV2ICsRMValRcvTx OBJECT-TYPE
         SYNTAX      Counter64
         MAX-ACCESS  read-only
         STATUS      current
         DESCRIPTION
         "Number of GTP packets sent with cause Reserved Message Value Received."
     ::= { jnxMbgPgwGtpGlbStatsEntry 396 }

jnxMbgPgwGtpV2ICsRPrNtRspRx OBJECT-TYPE
         SYNTAX      Counter64
         MAX-ACCESS  read-only
         STATUS      current
         DESCRIPTION
         "Number of GTP packets received with cause Remote peer not responding."
     ::= { jnxMbgPgwGtpGlbStatsEntry 397 }

jnxMbgPgwGtpV2ICsRPrNtRspTx OBJECT-TYPE
         SYNTAX      Counter64
         MAX-ACCESS  read-only
         STATUS      current
         DESCRIPTION
         "Number of GTP packets sent with cause Remote peer not responding."
     ::= { jnxMbgPgwGtpGlbStatsEntry 398 }

jnxMbgPgwGtpV2ICsColNWReqRx OBJECT-TYPE
         SYNTAX      Counter64
         MAX-ACCESS  read-only
         STATUS      current
         DESCRIPTION
         "Number of GTP packets received with cause Collision with network initiated request."
     ::= { jnxMbgPgwGtpGlbStatsEntry 399 }

jnxMbgPgwGtpV2ICsColNWReqTx OBJECT-TYPE
         SYNTAX      Counter64
         MAX-ACCESS  read-only
         STATUS      current
         DESCRIPTION
         "Number of GTP packets sent with cause Collision with network initiated request."
     ::= { jnxMbgPgwGtpGlbStatsEntry 400 }

jnxMbgPgwGtpV2ICsUnPgUESusRx OBJECT-TYPE
         SYNTAX      Counter64
         MAX-ACCESS  read-only
         STATUS      current
         DESCRIPTION
         "Number of GTP packets received with cause Unable to page UE due to suspension."
     ::= { jnxMbgPgwGtpGlbStatsEntry 401 }

jnxMbgPgwGtpV2ICsUnPgUESusTx OBJECT-TYPE
         SYNTAX      Counter64
         MAX-ACCESS  read-only
         STATUS      current
         DESCRIPTION
         "Number of GTP packets sent with cause Unable to page UE due to suspension."
     ::= { jnxMbgPgwGtpGlbStatsEntry 402 }

jnxMbgPgwGtpV2ICsInvTotLenRx OBJECT-TYPE
         SYNTAX      Counter64
         MAX-ACCESS  read-only
         STATUS      current
         DESCRIPTION
         "Number of GTP packets received with cause Invalid total len."
     ::= { jnxMbgPgwGtpGlbStatsEntry 403 }

jnxMbgPgwGtpV2ICsInvTotLenTx OBJECT-TYPE
         SYNTAX      Counter64
         MAX-ACCESS  read-only
         STATUS      current
         DESCRIPTION
         "Number of GTP packets sent with cause Invalid total len."
     ::= { jnxMbgPgwGtpGlbStatsEntry 404 }

jnxMbgPgwGtpV2ICsDtForNtSupRx OBJECT-TYPE
         SYNTAX      Counter64
         MAX-ACCESS  read-only
         STATUS      current
         DESCRIPTION
         "Number of GTP packets received with cause Data forwarding not supported."
     ::= { jnxMbgPgwGtpGlbStatsEntry 405 }

jnxMbgPgwGtpV2ICsDtForNtSupTx OBJECT-TYPE
         SYNTAX      Counter64
         MAX-ACCESS  read-only
         STATUS      current
         DESCRIPTION
         "Number of GTP packets sent with cause Data forwarding not supported."
     ::= { jnxMbgPgwGtpGlbStatsEntry 406 }

jnxMbgPgwGtpV2ICsInReFRePrRx OBJECT-TYPE
         SYNTAX      Counter64
         MAX-ACCESS  read-only
         STATUS      current
         DESCRIPTION
         "Number of GTP packets received with cause Invalid Reply from Remote peer."
     ::= { jnxMbgPgwGtpGlbStatsEntry 407 }

jnxMbgPgwGtpV2ICsInReFRePrTx OBJECT-TYPE
         SYNTAX      Counter64
         MAX-ACCESS  read-only
         STATUS      current
         DESCRIPTION
         "Number of GTP packets sent with cause Invalid Reply from Remote peer."
     ::= { jnxMbgPgwGtpGlbStatsEntry 408 }

jnxMbgPgwGtpV2ICsInvPrRx OBJECT-TYPE
         SYNTAX      Counter64
         MAX-ACCESS  read-only
         STATUS      current
         DESCRIPTION
         "Number of GTP packets received with cause Invalid peer."
     ::= { jnxMbgPgwGtpGlbStatsEntry 409 }

jnxMbgPgwGtpV2ICsInvPrTx OBJECT-TYPE
         SYNTAX      Counter64
         MAX-ACCESS  read-only
         STATUS      current
         DESCRIPTION
         "Number of GTP packets sent with cause Invalid peer."
     ::= { jnxMbgPgwGtpGlbStatsEntry 410 }

jnxMbgPgwV1InitPdpCxtReqRx   OBJECT-TYPE
    SYNTAX      Counter64
    MAX-ACCESS  read-only
    STATUS      current
    DESCRIPTION
    "Number of GTP V1 Initiate PDP Context Requests Received."
    ::= { jnxMbgPgwGtpGlbStatsEntry 411 }

jnxMbgPgwV1InitPdpCxtReqTx   OBJECT-TYPE
    SYNTAX      Counter64
    MAX-ACCESS  read-only
    STATUS      current
    DESCRIPTION
    "Number of GTP V1 Initiate PDP Context Requests Send."
    ::= { jnxMbgPgwGtpGlbStatsEntry 412 }

jnxMbgPgwV1InitPdpCxtRspRx   OBJECT-TYPE
    SYNTAX      Counter64
    MAX-ACCESS  read-only
    STATUS      current
    DESCRIPTION
    "Number of GTP V1 Initiate PDP Context Response Received."
    ::= { jnxMbgPgwGtpGlbStatsEntry 413 }

jnxMbgPgwV1InitPdpCxtRspTx   OBJECT-TYPE
    SYNTAX      Counter64
    MAX-ACCESS  read-only
    STATUS      current
    DESCRIPTION
    "Number of GTP V1 Initiate PDP Context Response Send."
    ::= { jnxMbgPgwGtpGlbStatsEntry 414 }

jnxMbgPgwV2SuspNotifRx OBJECT-TYPE
         SYNTAX      Counter64
         MAX-ACCESS  read-only
         STATUS      current
         DESCRIPTION
         "Number of GTPv2 Suspend Notification messages received."
     ::= { jnxMbgPgwGtpGlbStatsEntry 415 }

jnxMbgPgwV2SuspNotifTx OBJECT-TYPE
         SYNTAX      Counter64
         MAX-ACCESS  read-only
         STATUS      current
         DESCRIPTION
         "Number of GTPv2 Suspend Notification messages sent."
     ::= { jnxMbgPgwGtpGlbStatsEntry 416 }

jnxMbgPgwV2SuspAckRx OBJECT-TYPE
         SYNTAX      Counter64
         MAX-ACCESS  read-only
         STATUS      current
         DESCRIPTION
         "Number of GTPv2 Suspend Acknowledgement messages received."
     ::= { jnxMbgPgwGtpGlbStatsEntry 417 }

jnxMbgPgwV2SuspAckTx OBJECT-TYPE
         SYNTAX      Counter64
         MAX-ACCESS  read-only
         STATUS      current
         DESCRIPTION
         "Number of GTPv2 Suspend Acknowledgement messages sent."
     ::= { jnxMbgPgwGtpGlbStatsEntry 418 }

jnxMbgPgwV2ResumeNotifRx OBJECT-TYPE
         SYNTAX      Counter64
         MAX-ACCESS  read-only
         STATUS      current
         DESCRIPTION
         "Number of GTPv2 Resume Notification messages received."
     ::= { jnxMbgPgwGtpGlbStatsEntry 419 }

jnxMbgPgwV2ResumeNotifTx OBJECT-TYPE
         SYNTAX      Counter64
         MAX-ACCESS  read-only
         STATUS      current
         DESCRIPTION
         "Number of GTPv2 Resume Notification messages sent."
     ::= { jnxMbgPgwGtpGlbStatsEntry 420 }

jnxMbgPgwV2ResumeAckRx OBJECT-TYPE
         SYNTAX      Counter64
         MAX-ACCESS  read-only
         STATUS      current
         DESCRIPTION
         "Number of GTPv2 Resume Acknowledgement messages received."
     ::= { jnxMbgPgwGtpGlbStatsEntry 421 }

jnxMbgPgwV2ResumeAckTx OBJECT-TYPE
         SYNTAX      Counter64
         MAX-ACCESS  read-only
         STATUS      current
         DESCRIPTION
         "Number of GTPv2 Resume Acknowledgement messages sent."
     ::= { jnxMbgPgwGtpGlbStatsEntry 422 }

jnxMbgPgwV2PiggybackMsgRx OBJECT-TYPE
         SYNTAX      Counter64
         MAX-ACCESS  read-only
         STATUS      current
         DESCRIPTION
         "Number of GTPv2 S5 Piggyback messages received."
     ::= { jnxMbgPgwGtpGlbStatsEntry 423 }

jnxMbgPgwV2PiggybackMsgTx OBJECT-TYPE
         SYNTAX      Counter64
         MAX-ACCESS  read-only
         STATUS      current
         DESCRIPTION
         "Number of GTPv2 S5 Piggyback messages sent."
     ::= { jnxMbgPgwGtpGlbStatsEntry 424 }

--
-- Peer Statistics Table: Peer leve statistics
--

jnxMbgPgwGtpCPerPeerStatsTable OBJECT-TYPE
    SYNTAX SEQUENCE OF JnxMbgPgwGtpPerPeerStatsEntry
    MAX-ACCESS  not-accessible
    STATUS      current
    DESCRIPTION
        "Each entry corresponds to a Peer level GTP Control statistic."
  ::= { jnxMbgPgwGtpObjects 9 }

jnxMbgPgwGtpPerPeerStatsEntry OBJECT-TYPE
    SYNTAX      JnxMbgPgwGtpPerPeerStatsEntry
    MAX-ACCESS  not-accessible
    STATUS      current
    DESCRIPTION
        "A specification of the GTPC peer statistics Group."
    INDEX     { jnxMbgGwIndex,
                jnxMbgPgwPPGtpRmtAddr,
                jnxMbgPgwPPGtpLclAddr,
                jnxMbgPgwPPGtpRtgInst }
    ::= { jnxMbgPgwGtpCPerPeerStatsTable 1}

JnxMbgPgwGtpPerPeerStatsEntry ::= SEQUENCE {
    jnxMbgPgwPPGtpRmtAddr           IpAddress,
    jnxMbgPgwPPGtpLclAddr           IpAddress,
    jnxMbgPgwPPGtpRtgInst           Unsigned32,
    jnxMbgPgwPPRxPacketsDropped     Counter64,
    jnxMbgPgwPPPacketAllocFail      Counter64,
    jnxMbgPgwPPPacketSendFail       Counter64,
    jnxMbgPgwPPIPVerErrRx           Counter64,
    jnxMbgPgwPPIPProtoErrRx         Counter64,
    jnxMbgPgwPPGTPPortErrRx         Counter64,
    jnxMbgPgwPPGTPUnknVerRx         Counter64,
    jnxMbgPgwPPPcktLenErrRx         Counter64,
    jnxMbgPgwPPUnknMsgRx            Counter64,
    jnxMbgPgwPPProtocolErrRx        Counter64,
    jnxMbgPgwPPV2UnSupportedMsgRx   Counter64,
    jnxMbgPgwPPV2T3RespTmrExpRx     Counter64,
    jnxMbgPgwPPV2GlbNumMsgRx        Counter64,
    jnxMbgPgwPPV2GlbNumMsgTx        Counter64,
    jnxMbgPgwPPV2GlbNumBytesRx      Counter64,
    jnxMbgPgwPPV2GlbNumBytesTx      Counter64,
    jnxMbgPgwPPV2GlbEchoReqRx       Counter64,
    jnxMbgPgwPPV2GlbEchoReqTx       Counter64,
    jnxMbgPgwPPV2GlbEchoRespRx      Counter64,
    jnxMbgPgwPPV2GlbEchoRespTx      Counter64,
    jnxMbgPgwPPV2VerNotSupRx        Counter64,
    jnxMbgPgwPPV2VerNotSupTx        Counter64,
    jnxMbgPgwPPV2CreateSessReqRx    Counter64,
    jnxMbgPgwPPV2CreateSessReqTx    Counter64,
    jnxMbgPgwPPV2CreateSessRspRx    Counter64,
    jnxMbgPgwPPV2CreateSessRspTx    Counter64,
    jnxMbgPgwPPV2ModBrReqRx         Counter64,
    jnxMbgPgwPPV2ModBrReqTx         Counter64,
    jnxMbgPgwPPV2ModBrRspRx         Counter64,
    jnxMbgPgwPPV2ModBrRspTx         Counter64,
    jnxMbgPgwPPV2DelSessReqRx       Counter64,
    jnxMbgPgwPPV2DelSessReqTx       Counter64,
    jnxMbgPgwPPV2DelSessRspRx       Counter64,
    jnxMbgPgwPPV2DelSessRspTx       Counter64,
    jnxMbgPgwPPV2CrtBrReqRx         Counter64,
    jnxMbgPgwPPV2CrtBrReqTx         Counter64,
    jnxMbgPgwPPV2CrtBrRspRx         Counter64,
    jnxMbgPgwPPV2CrtBrRspTx         Counter64,
    jnxMbgPgwPPV2UpdBrReqRx         Counter64,
    jnxMbgPgwPPV2UpdBrReqTx         Counter64,
    jnxMbgPgwPPV2UpdBrRspRx         Counter64,
    jnxMbgPgwPPV2UpdBrRspTx         Counter64,
    jnxMbgPgwPPV2DelBrReqRx         Counter64,
    jnxMbgPgwPPV2DelBrReqTx         Counter64,
    jnxMbgPgwPPV2DelBrRspRx         Counter64,
    jnxMbgPgwPPV2DelBrRspTx         Counter64,
    jnxMbgPgwPPV2DelConnSetReqRx    Counter64,
    jnxMbgPgwPPV2DelConnSetReqTx    Counter64,
    jnxMbgPgwPPV2DelConnSetRspRx    Counter64,
    jnxMbgPgwPPV2DelConnSetRspTx    Counter64,
    jnxMbgPgwPPV2UpdConnSetReqRx    Counter64,
    jnxMbgPgwPPV2UpdConnSetReqTx    Counter64,
    jnxMbgPgwPPV2UpdConnSetRspRx    Counter64,
    jnxMbgPgwPPV2UpdConnSetRspTx    Counter64,
    jnxMbgPgwPPV2ModBrCmdRx         Counter64,
    jnxMbgPgwPPV2ModBrCmdTx         Counter64,
    jnxMbgPgwPPV2ModBrFlrIndRx      Counter64,
    jnxMbgPgwPPV2ModBrFlrIndTx      Counter64,
    jnxMbgPgwPPV2DelBrCmdRx         Counter64,
    jnxMbgPgwPPV2DelBrCmdTx         Counter64,
    jnxMbgPgwPPV2DelBrFlrIndRx      Counter64,
    jnxMbgPgwPPV2DelBrFlrIndTx      Counter64,
    jnxMbgPgwPPV2BrResCmdRx         Counter64,
    jnxMbgPgwPPV2BrResCmdTx         Counter64,
    jnxMbgPgwPPV2BrResFlrIndRx      Counter64,
    jnxMbgPgwPPV2BrResFlrIndTx      Counter64,
    jnxMbgPgwPPV2RelAcsBrReqRx      Counter64,
    jnxMbgPgwPPV2RelAcsBrReqTx      Counter64,
    jnxMbgPgwPPV2RelAcsBrRespRx     Counter64,
    jnxMbgPgwPPV2RelAcsBrRespTx     Counter64,
    jnxMbgPgwPPV2CrIndTunReqRx      Counter64,
    jnxMbgPgwPPV2CrIndTunReqTx      Counter64,
    jnxMbgPgwPPV2CrIndTunRespRx     Counter64,
    jnxMbgPgwPPV2CrIndTunRespTx     Counter64,
    jnxMbgPgwPPV2DelIndTunReqRx     Counter64,
    jnxMbgPgwPPV2DelIndTunReqTx     Counter64,
    jnxMbgPgwPPV2DelIndTunRespRx    Counter64,
    jnxMbgPgwPPV2DelIndTunRespTx    Counter64,
    jnxMbgPgwPPV2DlDataNotifRx      Counter64,
    jnxMbgPgwPPV2DlDataNotifTx      Counter64,
    jnxMbgPgwPPV2DlDataAckRx        Counter64,
    jnxMbgPgwPPV2DlDataAckTx        Counter64,
    jnxMbgPgwPPV2DlDataNotiFlrIndRx Counter64,
    jnxMbgPgwPPV2DlDataNotiFlrIndTx Counter64,
    jnxMbgPgwPPV2StopPagingIndRx    Counter64,
    jnxMbgPgwPPV2StopPagingIndTx    Counter64,
    jnxMbgPgwPPV2ICsPageRx          Counter64,
    jnxMbgPgwPPV2ICsPageTx          Counter64,
    jnxMbgPgwPPV2ICsReqAcceptRx     Counter64,
    jnxMbgPgwPPV2ICsReqAcceptTx     Counter64,
    jnxMbgPgwPPV2ICsAcceptPartRx    Counter64,
    jnxMbgPgwPPV2ICsAcceptPartTx    Counter64,
    jnxMbgPgwPPV2ICsNewPTNPrefRx    Counter64,
    jnxMbgPgwPPV2ICsNewPTNPrefTx    Counter64,
    jnxMbgPgwPPV2ICsNewPTSIAdbrRx   Counter64,
    jnxMbgPgwPPV2ICsNewPTSIAdbrTx   Counter64,
    jnxMbgPgwPPV2ICsCtxNotFndRx     Counter64,
    jnxMbgPgwPPV2ICsCtxNotFndTx     Counter64,
    jnxMbgPgwPPV2ICsInvMsgFmtRx     Counter64,
    jnxMbgPgwPPV2ICsInvMsgFmtTx     Counter64,
    jnxMbgPgwPPV2ICsVerNotSuppRx    Counter64,
    jnxMbgPgwPPV2ICsVerNotSuppTx    Counter64,
    jnxMbgPgwPPV2ICsInvLenRx        Counter64,
    jnxMbgPgwPPV2ICsInvLenTx        Counter64,
    jnxMbgPgwPPV2ICsServNotSuppRx   Counter64,
    jnxMbgPgwPPV2ICsServNotSuppTx   Counter64,
    jnxMbgPgwPPV2ICsManIEIncorrRx   Counter64,
    jnxMbgPgwPPV2ICsManIEIncorrTx   Counter64,
    jnxMbgPgwPPV2ICsManIEMissRx     Counter64,
    jnxMbgPgwPPV2ICsManIEMissTx     Counter64,
    jnxMbgPgwPPV2ICsOptIEIncorrRx   Counter64,
    jnxMbgPgwPPV2ICsOptIEIncorrTx   Counter64,
    jnxMbgPgwPPV2ICsSysFailRx       Counter64,
    jnxMbgPgwPPV2ICsSysFailTx       Counter64,
    jnxMbgPgwPPV2ICsNoResRx         Counter64,
    jnxMbgPgwPPV2ICsNoResTx         Counter64,
    jnxMbgPgwPPV2ICsTFTSMANTErRx    Counter64,
    jnxMbgPgwPPV2ICsTFTSMANTErTx    Counter64,
    jnxMbgPgwPPV2ICsTFTSysErrRx     Counter64,
    jnxMbgPgwPPV2ICsTFTSysErrTx     Counter64,
    jnxMbgPgwPPV2ICsPkFltManErrRx   Counter64,
    jnxMbgPgwPPV2ICsPkFltManErrTx   Counter64,
    jnxMbgPgwPPV2ICsPkFltSynErrRx   Counter64,
    jnxMbgPgwPPV2ICsPkFltSynErrTx   Counter64,
    jnxMbgPgwPPV2ICsMisUnknAPNRx    Counter64,
    jnxMbgPgwPPV2ICsMisUnknAPNTx    Counter64,
    jnxMbgPgwPPV2ICsUnexpRptIERx    Counter64,
    jnxMbgPgwPPV2ICsUnexpRptIETx    Counter64,
    jnxMbgPgwPPV2ICsGREKeyNtFdRx    Counter64,
    jnxMbgPgwPPV2ICsGREKeyNtFdTx    Counter64,
    jnxMbgPgwPPV2ICsRelocFailRx     Counter64,
    jnxMbgPgwPPV2ICsRelocFailTx     Counter64,
    jnxMbgPgwPPV2ICsDeniedINRatRx   Counter64,
    jnxMbgPgwPPV2ICsDeniedINRatTx   Counter64,
    jnxMbgPgwPPV2ICsPTNotSuppRx     Counter64,
    jnxMbgPgwPPV2ICsPTNotSuppTx     Counter64,
    jnxMbgPgwPPV2ICsAllDynAdOccRx   Counter64,
    jnxMbgPgwPPV2ICsAllDynAdOccTx   Counter64,
    jnxMbgPgwPPV2ICsNOTFTUECTXRx    Counter64,
    jnxMbgPgwPPV2ICsNOTFTUECTXTx    Counter64,
    jnxMbgPgwPPV2ICsProtoNtSupRx    Counter64,
    jnxMbgPgwPPV2ICsProtoNtSupTx    Counter64,
    jnxMbgPgwPPV2ICsUENotRespRx     Counter64,
    jnxMbgPgwPPV2ICsUENotRespTx     Counter64,
    jnxMbgPgwPPV2ICsUERefusesRx     Counter64,
    jnxMbgPgwPPV2ICsUERefusesTx     Counter64,
    jnxMbgPgwPPV2ICsServDeniedRx    Counter64,
    jnxMbgPgwPPV2ICsServDeniedTx    Counter64,
    jnxMbgPgwPPV2ICsUnabPageUERx    Counter64,
    jnxMbgPgwPPV2ICsUnabPageUETx    Counter64,
    jnxMbgPgwPPV2ICsNoMemRx         Counter64,
    jnxMbgPgwPPV2ICsNoMemTx         Counter64,
    jnxMbgPgwPPV2ICsUserAUTHFlRx    Counter64,
    jnxMbgPgwPPV2ICsUserAUTHFlTx    Counter64,
    jnxMbgPgwPPV2ICsAPNAcsDenRx     Counter64,
    jnxMbgPgwPPV2ICsAPNAcsDenTx     Counter64,
    jnxMbgPgwPPV2ICsReqRejRx        Counter64,
    jnxMbgPgwPPV2ICsReqRejTx        Counter64,
    jnxMbgPgwPPV2ICsPTMSISigMMRx    Counter64,
    jnxMbgPgwPPV2ICsPTMSISigMMTx    Counter64,
    jnxMbgPgwPPV2ICsIMSINotKnRx     Counter64,
    jnxMbgPgwPPV2ICsIMSINotKnTx     Counter64,
    jnxMbgPgwPPV2ICsCondIEMsRx      Counter64,
    jnxMbgPgwPPV2ICsCondIEMsTx      Counter64,
    jnxMbgPgwPPV2ICsAPNResTIncRx    Counter64,
    jnxMbgPgwPPV2ICsAPNResTIncTx    Counter64,
    jnxMbgPgwPPV2ICsUnknownRx       Counter64,
    jnxMbgPgwPPV2ICsUnknownTx       Counter64,
    jnxMbgPgwPPV1ProtocolErrRx      Counter64,
    jnxMbgPgwPPV1UnSupportedMsgRx   Counter64,
    jnxMbgPgwPPV1T3RespTmrExpRx     Counter64,
    jnxMbgPgwPPV1GlbNumMsgRx        Counter64,
    jnxMbgPgwPPV1GlbNumMsgTx        Counter64,
    jnxMbgPgwPPV1GlbNumBytesRx      Counter64,
    jnxMbgPgwPPV1GlbNumBytesTx      Counter64,
    jnxMbgPgwPPV1GlbEchoReqRx       Counter64,
    jnxMbgPgwPPV1GlbEchoReqTx       Counter64,
    jnxMbgPgwPPV1GlbEchoRespRx      Counter64,
    jnxMbgPgwPPV1GlbEchoRespTx      Counter64,
    jnxMbgPgwPPV1VerNotSupRx        Counter64,
    jnxMbgPgwPPV1VerNotSupTx        Counter64,
    jnxMbgPgwPPV1CrtPdpCxtReqRx     Counter64,
    jnxMbgPgwPPV1CrtPdpCxtReqTx     Counter64,
    jnxMbgPgwPPV1CrtPdpCxtRspRx     Counter64,
    jnxMbgPgwPPV1CrtPdpCxtRspTx     Counter64,
    jnxMbgPgwPPV1UpdPdpCxtReqRx     Counter64,
    jnxMbgPgwPPV1UpdPdpCxtReqTx     Counter64,
    jnxMbgPgwPPV1UpdPdpCxtRspRx     Counter64,
    jnxMbgPgwPPV1UpdPdpCxtRspTx     Counter64,
    jnxMbgPgwPPV1DelPdpCxtReqRx     Counter64,
    jnxMbgPgwPPV1DelPdpCxtReqTx     Counter64,
    jnxMbgPgwPPV1DelPdpCxtRspRx     Counter64,
    jnxMbgPgwPPV1DelPdpCxtRspTx     Counter64,
    jnxMbgPgwPPV1CrtAAPdpCxtReqRx   Counter64,
    jnxMbgPgwPPV1CrtAAPdpCxtReqTx   Counter64,
    jnxMbgPgwPPV1CrtAAPdpCxtRspRx   Counter64,
    jnxMbgPgwPPV1CrtAAPdpCxtRspTx   Counter64,
    jnxMbgPgwPPV1DelAAPdpCxtReqRx   Counter64,
    jnxMbgPgwPPV1DelAAPdpCxtReqTx   Counter64,
    jnxMbgPgwPPV1DelAAPdpCxtRspRx   Counter64,
    jnxMbgPgwPPV1DelAAPdpCxtRspTx   Counter64,
    jnxMbgPgwPPV1ErrorIndRx         Counter64,
    jnxMbgPgwPPV1ErrorIndTx         Counter64,
    jnxMbgPgwPPV1NotifReqRx         Counter64,
    jnxMbgPgwPPV1NotifReqTx         Counter64,
    jnxMbgPgwPPV1NotifRspRx         Counter64,
    jnxMbgPgwPPV1NotifRspTx         Counter64,
    jnxMbgPgwPPV1NotifRejReqRx      Counter64,
    jnxMbgPgwPPV1NotifRejReqTx      Counter64,
    jnxMbgPgwPPV1NotifRejRspRx      Counter64,
    jnxMbgPgwPPV1NotifRejRspTx      Counter64,
    jnxMbgPgwPPV1RtInfReqRx         Counter64,
    jnxMbgPgwPPV1RtInfReqTx         Counter64,
    jnxMbgPgwPPV1RtInfRspRx         Counter64,
    jnxMbgPgwPPV1RtInfRspTx         Counter64,
    jnxMbgPgwPPV1FailRptReqRx       Counter64,
    jnxMbgPgwPPV1FailRptReqTx       Counter64,
    jnxMbgPgwPPV1FailRptRspRx       Counter64,
    jnxMbgPgwPPV1FailRptRspTx       Counter64,
    jnxMbgPgwPPV1NotMSPresReqRx     Counter64,
    jnxMbgPgwPPV1NotMSPresReqTx     Counter64,
    jnxMbgPgwPPV1NotMSPresRspRx     Counter64,
    jnxMbgPgwPPV1NotMSPresRspTx     Counter64,
    jnxMbgPgwPPV1ICsReqAcceptedRx   Counter64,
    jnxMbgPgwPPV1ICsReqAcceptedTx   Counter64,
    jnxMbgPgwPPV1ICsNonExistRx      Counter64,
    jnxMbgPgwPPV1ICsNonExistTx      Counter64,
    jnxMbgPgwPPV1ICsInvMsgFmtRx     Counter64,
    jnxMbgPgwPPV1ICsInvMsgFmtTx     Counter64,
    jnxMbgPgwPPV1ICsIMSINotKnownRx  Counter64,
    jnxMbgPgwPPV1ICsIMSINotKnownTx  Counter64,
    jnxMbgPgwPPV1ICsMSGRPSDetachRx  Counter64,
    jnxMbgPgwPPV1ICsMSGRPSDetachTx  Counter64,
    jnxMbgPgwPPV1ICsMSNotGRPSRespRx Counter64,
    jnxMbgPgwPPV1ICsMSNotGRPSRespTx Counter64,
    jnxMbgPgwPPV1ICsMSRefusesRx     Counter64,
    jnxMbgPgwPPV1ICsMSRefusesTx     Counter64,
    jnxMbgPgwPPV1ICsVerNotSuppRx    Counter64,
    jnxMbgPgwPPV1ICsVerNotSuppTx    Counter64,
    jnxMbgPgwPPV1ICsNoResRx         Counter64,
    jnxMbgPgwPPV1ICsNoResTx         Counter64,
    jnxMbgPgwPPV1ICsServNotSuppRx   Counter64,
    jnxMbgPgwPPV1ICsServNotSuppTx   Counter64,
    jnxMbgPgwPPV1ICsManIEIncrtRx    Counter64,
    jnxMbgPgwPPV1ICsManIEIncrtTx    Counter64,
    jnxMbgPgwPPV1ICsManIEMissRx     Counter64,
    jnxMbgPgwPPV1ICsManIEMissTx     Counter64,
    jnxMbgPgwPPV1ICsOptIEIncrtRx    Counter64,
    jnxMbgPgwPPV1ICsOptIEIncrtTx    Counter64,
    jnxMbgPgwPPV1ICsSysFailRx       Counter64,
    jnxMbgPgwPPV1ICsSysFailTx       Counter64,
    jnxMbgPgwPPV1ICsRoamRestrictRx  Counter64,
    jnxMbgPgwPPV1ICsRoamRestrictTx  Counter64,
    jnxMbgPgwPPV1ICsPTMSISigMMRx    Counter64,
    jnxMbgPgwPPV1ICsPTMSISigMMTx    Counter64,
    jnxMbgPgwPPV1ICsGPRSConnSuppRx  Counter64,
    jnxMbgPgwPPV1ICsGPRSConnSuppTx  Counter64,
    jnxMbgPgwPPV1ICsAuthFailRx      Counter64,
    jnxMbgPgwPPV1ICsAuthFailTx      Counter64,
    jnxMbgPgwPPV1ICsUserAuthFailRx  Counter64,
    jnxMbgPgwPPV1ICsUserAuthFailTx  Counter64,
    jnxMbgPgwPPV1ICsCtxNotFndRx     Counter64,
    jnxMbgPgwPPV1ICsCtxNotFndTx     Counter64,
    jnxMbgPgwPPV1ICsAllDynPDPAdRx   Counter64,
    jnxMbgPgwPPV1ICsAllDynPDPAdTx   Counter64,
    jnxMbgPgwPPV1ICsNoMemRx         Counter64,
    jnxMbgPgwPPV1ICsNoMemTx         Counter64,
    jnxMbgPgwPPV1ICsRelocFailRx     Counter64,
    jnxMbgPgwPPV1ICsRelocFailTx     Counter64,
    jnxMbgPgwPPV1ICsUnkManExhdrRx   Counter64,
    jnxMbgPgwPPV1ICsUnkManExhdrTx   Counter64,
    jnxMbgPgwPPV1ICsSMANTTFTEr1Rx   Counter64,
    jnxMbgPgwPPV1ICsSMANTTFTEr1Tx   Counter64,
    jnxMbgPgwPPV1ICsSYNTFTErr2Rx    Counter64,
    jnxMbgPgwPPV1ICsSYNTFTErr2Tx    Counter64,
    jnxMbgPgwPPV1ICsSMNTPkFlEr1Rx   Counter64,
    jnxMbgPgwPPV1ICsSMNTPkFlEr1Tx   Counter64,
    jnxMbgPgwPPV1ICsSYNPkFlErr2Rx   Counter64,
    jnxMbgPgwPPV1ICsSYNPkFlErr2Tx   Counter64,
    jnxMbgPgwPPV1ICsMissUnknAPNRx   Counter64,
    jnxMbgPgwPPV1ICsMissUnknAPNTx   Counter64,
    jnxMbgPgwPPV1ICsUnknPDPAdRx     Counter64,
    jnxMbgPgwPPV1ICsUnknPDPAdTx     Counter64,
    jnxMbgPgwPPV1ICsNoTFTCtxExRx    Counter64,
    jnxMbgPgwPPV1ICsNoTFTCtxExTx    Counter64,
    jnxMbgPgwPPV0ProtocolErrRx      Counter64,
    jnxMbgPgwPPV0UnSupportedMsgRx   Counter64,
    jnxMbgPgwPPV0T3RespTmrExpRx     Counter64,
    jnxMbgPgwPPV0GlbNumMsgRx        Counter64,
    jnxMbgPgwPPV0GlbNumMsgTx        Counter64,
    jnxMbgPgwPPV0GlbNumBytesRx      Counter64,
    jnxMbgPgwPPV0GlbNumBytesTx      Counter64,
    jnxMbgPgwPPV0GlbEchoReqRx       Counter64,
    jnxMbgPgwPPV0GlbEchoReqTx       Counter64,
    jnxMbgPgwPPV0GlbEchoRespRx      Counter64,
    jnxMbgPgwPPV0GlbEchoRespTx      Counter64,
    jnxMbgPgwPPV0GlbVerNotSupRx     Counter64,
    jnxMbgPgwPPV0GlbVerNotSupTx     Counter64,
    jnxMbgPgwPPV0GlbCrtPdpCxtReqRx  Counter64,
    jnxMbgPgwPPV0GlbCrtPdpCxtReqTx  Counter64,
    jnxMbgPgwPPV0GlbCrtPdpCxtRspRx  Counter64,
    jnxMbgPgwPPV0GlbCrtPdpCxtRspTx  Counter64,
    jnxMbgPgwPPV0GlbUpdPdpCxtReqRx  Counter64,
    jnxMbgPgwPPV0GlbUpdPdpCxtReqTx  Counter64,
    jnxMbgPgwPPV0GlbUpdPdpCxtRspRx  Counter64,
    jnxMbgPgwPPV0GlbUpdPdpCxtRspTx  Counter64,
    jnxMbgPgwPPV0GlbDelPdpCxtReqRx  Counter64,
    jnxMbgPgwPPV0GlbDelPdpCxtReqTx  Counter64,
    jnxMbgPgwPPV0GlbDelPdpCxtRspRx  Counter64,
    jnxMbgPgwPPV0GlbDelPdpCxtRspTx  Counter64,
    jnxMbgPgwPPV0GlbCrAAPdpCxtReqRx Counter64,
    jnxMbgPgwPPV0GlbCrAAPdpCxtReqTx Counter64,
    jnxMbgPgwPPV0GlbCrAAPdpCxtRspRx Counter64,
    jnxMbgPgwPPV0GlbCrAAPdpCxtRspTx Counter64,
    jnxMbgPgwPPV0GlbDlAAPdpCxtReqRx Counter64,
    jnxMbgPgwPPV0GlbDlAAPdpCxtReqTx Counter64,
    jnxMbgPgwPPV0GlbDlAAPdpCxtRspRx Counter64,
    jnxMbgPgwPPV0GlbDlAAPdpCxtRspTx Counter64,
    jnxMbgPgwPPV0GlbErrorIndRx      Counter64,
    jnxMbgPgwPPV0GlbErrorIndTx      Counter64,
    jnxMbgPgwPPV0GlbNotifReqRx      Counter64,
    jnxMbgPgwPPV0GlbNotifReqTx      Counter64,
    jnxMbgPgwPPV0GlbNotifRspRx      Counter64,
    jnxMbgPgwPPV0GlbNotifRspTx      Counter64,
    jnxMbgPgwPPV0GlbNotifRejReqRx   Counter64,
    jnxMbgPgwPPV0GlbNotifRejReqTx   Counter64,
    jnxMbgPgwPPV0GlbNotifRejRspRx   Counter64,
    jnxMbgPgwPPV0GlbNotifRejRspTx   Counter64,
    jnxMbgPgwPPV0GlbRtInfReqRx      Counter64,
    jnxMbgPgwPPV0GlbRtInfReqTx      Counter64,
    jnxMbgPgwPPV0GlbRtInfRspRx      Counter64,
    jnxMbgPgwPPV0GlbRtInfRspTx      Counter64,
    jnxMbgPgwPPV0GlbFailRptReqRx    Counter64,
    jnxMbgPgwPPV0GlbFailRptReqTx    Counter64,
    jnxMbgPgwPPV0GlbFailRptRspRx    Counter64,
    jnxMbgPgwPPV0GlbFailRptRspTx    Counter64,
    jnxMbgPgwPPV0GlbNotMSPresReqRx  Counter64,
    jnxMbgPgwPPV0GlbNotMSPresReqTx  Counter64,
    jnxMbgPgwPPV0GlbNotMSPresRspRx  Counter64,
    jnxMbgPgwPPV0GlbNotMSPresRspTx  Counter64,
    jnxMbgPgwPPV0ICsReqAcceptedRx   Counter64,
    jnxMbgPgwPPV0ICsReqAcceptedTx   Counter64,
    jnxMbgPgwPPV0ICsNonExistRx      Counter64,
    jnxMbgPgwPPV0ICsNonExistTx      Counter64,
    jnxMbgPgwPPV0ICsInvMsgFmtRx     Counter64,
    jnxMbgPgwPPV0ICsInvMsgFmtTx     Counter64,
    jnxMbgPgwPPV0ICsIMSINotKnownRx  Counter64,
    jnxMbgPgwPPV0ICsIMSINotKnownTx  Counter64,
    jnxMbgPgwPPV0ICsMSGRPSDetachRx  Counter64,
    jnxMbgPgwPPV0ICsMSGRPSDetachTx  Counter64,
    jnxMbgPgwPPV0ICsMSNotGRPSRespRx Counter64,
    jnxMbgPgwPPV0ICsMSNotGRPSRespTx Counter64,
    jnxMbgPgwPPV0ICsMSRefusesRx     Counter64,
    jnxMbgPgwPPV0ICsMSRefusesTx     Counter64,
    jnxMbgPgwPPV0ICsVerNotSuppRx    Counter64,
    jnxMbgPgwPPV0ICsVerNotSuppTx    Counter64,
    jnxMbgPgwPPV0ICsNoResRx         Counter64,
    jnxMbgPgwPPV0ICsNoResTx         Counter64,
    jnxMbgPgwPPV0ICsServNotSuppRx   Counter64,
    jnxMbgPgwPPV0ICsServNotSuppTx   Counter64,
    jnxMbgPgwPPV0ICsManIEIncrtRx    Counter64,
    jnxMbgPgwPPV0ICsManIEIncrtTx    Counter64,
    jnxMbgPgwPPV0ICsManIEMissRx     Counter64,
    jnxMbgPgwPPV0ICsManIEMissTx     Counter64,
    jnxMbgPgwPPV0ICsOptIEIncrtRx    Counter64,
    jnxMbgPgwPPV0ICsOptIEIncrtTx    Counter64,
    jnxMbgPgwPPV0ICsSysFailRx       Counter64,
    jnxMbgPgwPPV0ICsSysFailTx       Counter64,
    jnxMbgPgwPPV0ICsRoamRestrictRx  Counter64,
    jnxMbgPgwPPV0ICsRoamRestrictTx  Counter64,
    jnxMbgPgwPPV0ICsPTMSISigMMRx    Counter64,
    jnxMbgPgwPPV0ICsPTMSISigMMTx    Counter64,
    jnxMbgPgwPPV0ICsGPRSConnSuppRx  Counter64,
    jnxMbgPgwPPV0ICsGPRSConnSuppTx  Counter64,
    jnxMbgPgwPPV0ICsAuthFailRx      Counter64,
    jnxMbgPgwPPV0ICsAuthFailTx      Counter64,
    jnxMbgPgwPPV0ICsUserAuthFailRx  Counter64,
    jnxMbgPgwPPV0ICsUserAuthFailTx  Counter64,
    jnxMbgPgwPPGtpV2ICsLclDetRx     Counter64,
    jnxMbgPgwPPGtpV2ICsLclDetTx     Counter64,
    jnxMbgPgwPPGtpV2ICsCmpDetRx     Counter64,
    jnxMbgPgwPPGtpV2ICsCmpDetTx     Counter64,
    jnxMbgPgwPPGtpV2ICsRATChgRx     Counter64,
    jnxMbgPgwPPGtpV2ICsRATChgTx     Counter64,
    jnxMbgPgwPPGtpV2ICsISRDeactRx   Counter64,
    jnxMbgPgwPPGtpV2ICsISRDeactTx   Counter64,
    jnxMbgPgwPPGtpV2ICsEIFRNCEnRx   Counter64,
    jnxMbgPgwPPGtpV2ICsEIFRNCEnTx   Counter64,
    jnxMbgPgwPPGtpV2ICsSemErTADRx   Counter64,
    jnxMbgPgwPPGtpV2ICsSemErTADTx   Counter64,
    jnxMbgPgwPPGtpV2ICsSynErTADRx   Counter64,
    jnxMbgPgwPPGtpV2ICsSynErTADTx   Counter64,
    jnxMbgPgwPPGtpV2ICsRMValRcvRx   Counter64,
    jnxMbgPgwPPGtpV2ICsRMValRcvTx   Counter64,
    jnxMbgPgwPPGtpV2ICsRPrNtRspRx   Counter64,
    jnxMbgPgwPPGtpV2ICsRPrNtRspTx   Counter64,
    jnxMbgPgwPPGtpV2ICsColNWReqRx   Counter64,
    jnxMbgPgwPPGtpV2ICsColNWReqTx   Counter64,
    jnxMbgPgwPPGtpV2ICsUnPgUESusRx  Counter64,
    jnxMbgPgwPPGtpV2ICsUnPgUESusTx  Counter64,
    jnxMbgPgwPPGtpV2ICsInvTotLenRx  Counter64,
    jnxMbgPgwPPGtpV2ICsInvTotLenTx  Counter64,
    jnxMbgPgwPPGtpV2ICsDtForNtSupRx Counter64,
    jnxMbgPgwPPGtpV2ICsDtForNtSupTx Counter64,
    jnxMbgPgwPPGtpV2ICsInReFRePrRx  Counter64,
    jnxMbgPgwPPGtpV2ICsInReFRePrTx  Counter64,
    jnxMbgPgwPPGtpV2ICsInvPrRx      Counter64,
    jnxMbgPgwPPGtpV2ICsInvPrTx      Counter64,
    jnxMbgPgwPPV1InitPdpCxtReqRx    Counter64,
    jnxMbgPgwPPV1InitPdpCxtReqTx    Counter64,
    jnxMbgPgwPPV1InitPdpCxtRspRx    Counter64,
    jnxMbgPgwPPV1InitPdpCxtRspTx    Counter64,
    jnxMbgPgwPPV2SuspNotifRx        Counter64,
    jnxMbgPgwPPV2SuspNotifTx        Counter64,
    jnxMbgPgwPPV2SuspAckRx          Counter64,
    jnxMbgPgwPPV2SuspAckTx          Counter64,
    jnxMbgPgwPPV2ResumeNotifRx      Counter64,
    jnxMbgPgwPPV2ResumeNotifTx      Counter64,
    jnxMbgPgwPPV2ResumeAckRx        Counter64,
    jnxMbgPgwPPV2ResumeAckTx        Counter64,
    jnxMbgPgwPPV2PiggybackMsgRx     Counter64,
    jnxMbgPgwPPV2PiggybackMsgTx     Counter64
}

jnxMbgPgwPPGtpRmtAddr OBJECT-TYPE
    SYNTAX      IpAddress
    MAX-ACCESS  not-accessible
    STATUS      current
    DESCRIPTION
        "The Remote IP address of this GTP entry."
    ::= { jnxMbgPgwGtpPerPeerStatsEntry 1 }

jnxMbgPgwPPGtpLclAddr OBJECT-TYPE
    SYNTAX      IpAddress
    MAX-ACCESS  not-accessible
    STATUS      current
    DESCRIPTION
        "The Local IP address of this GTP entry."
    ::= { jnxMbgPgwGtpPerPeerStatsEntry 2 }

jnxMbgPgwPPGtpRtgInst OBJECT-TYPE
    SYNTAX      Unsigned32
    MAX-ACCESS  not-accessible
    STATUS      current
    DESCRIPTION
        "The Routing Instance for this Peer."
    ::= { jnxMbgPgwGtpPerPeerStatsEntry 3 }

jnxMbgPgwPPRxPacketsDropped  OBJECT-TYPE
    SYNTAX      Counter64
    MAX-ACCESS  read-only
    STATUS      current
    DESCRIPTION
    "Number of Received GTP Packets Dropped."
    ::= { jnxMbgPgwGtpPerPeerStatsEntry 4 }

jnxMbgPgwPPPacketAllocFail  OBJECT-TYPE
    SYNTAX      Counter64
    MAX-ACCESS  read-only
    STATUS      current
    DESCRIPTION
    "Number of Packet allocation failures."
    ::= { jnxMbgPgwGtpPerPeerStatsEntry 5 }

jnxMbgPgwPPPacketSendFail OBJECT-TYPE
    SYNTAX      Counter64
    MAX-ACCESS  read-only
    STATUS      current
    DESCRIPTION
    "Number of Packet Send failures."
    ::= { jnxMbgPgwGtpPerPeerStatsEntry 6 }

jnxMbgPgwPPIPVerErrRx OBJECT-TYPE
    SYNTAX      Counter64
    MAX-ACCESS  read-only
    STATUS      current
    DESCRIPTION
    "Number of IP Version Error Packets Received."
    ::= { jnxMbgPgwGtpPerPeerStatsEntry 7 }

jnxMbgPgwPPIPProtoErrRx OBJECT-TYPE
    SYNTAX      Counter64
    MAX-ACCESS  read-only
    STATUS      current
    DESCRIPTION
    "Number of  IP Protocol Error packets Received."
    ::= { jnxMbgPgwGtpPerPeerStatsEntry 8 }

jnxMbgPgwPPGTPPortErrRx OBJECT-TYPE
    SYNTAX      Counter64
    MAX-ACCESS  read-only
    STATUS      current
    DESCRIPTION
    "Number of  Port Error Packets Received."
    ::= { jnxMbgPgwGtpPerPeerStatsEntry 9 }

jnxMbgPgwPPGTPUnknVerRx OBJECT-TYPE
    SYNTAX      Counter64
    MAX-ACCESS  read-only
    STATUS      current
    DESCRIPTION
    "Number of  Unknown Version Packets Received."
    ::= { jnxMbgPgwGtpPerPeerStatsEntry 10 }

jnxMbgPgwPPPcktLenErrRx OBJECT-TYPE
    SYNTAX      Counter64
    MAX-ACCESS  read-only
    STATUS      current
    DESCRIPTION
    "Number of Packet Length Error Packets Received."
    ::= { jnxMbgPgwGtpPerPeerStatsEntry 11 }

jnxMbgPgwPPUnknMsgRx OBJECT-TYPE
    SYNTAX      Counter64
    MAX-ACCESS  read-only
    STATUS      current
    DESCRIPTION
    "Number of  Unknown Messages Received."
    ::= { jnxMbgPgwGtpPerPeerStatsEntry 12 }

jnxMbgPgwPPProtocolErrRx  OBJECT-TYPE
    SYNTAX      Counter64
    MAX-ACCESS  read-only
    STATUS      current
    DESCRIPTION
    "Number of GTPv2 Protocol Errors Received."
    ::= { jnxMbgPgwGtpPerPeerStatsEntry 13 }

jnxMbgPgwPPV2UnSupportedMsgRx  OBJECT-TYPE
    SYNTAX      Counter64
    MAX-ACCESS  read-only
    STATUS      current
    DESCRIPTION
    "Number of GTPv2 Unsupported Messages received."
    ::= { jnxMbgPgwGtpPerPeerStatsEntry 14 }

jnxMbgPgwPPV2T3RespTmrExpRx  OBJECT-TYPE
    SYNTAX      Counter64
    MAX-ACCESS  read-only
    STATUS      current
    DESCRIPTION
    "Number of GTP V2 Number of T3 timer expiries Received."
    ::= { jnxMbgPgwGtpPerPeerStatsEntry 15 }

jnxMbgPgwPPV2GlbNumMsgRx  OBJECT-TYPE
    SYNTAX      Counter64
    MAX-ACCESS  read-only
    STATUS      current
    DESCRIPTION
    "Number of GTPv2 messages received."
    ::= { jnxMbgPgwGtpPerPeerStatsEntry 16 }

jnxMbgPgwPPV2GlbNumMsgTx  OBJECT-TYPE
    SYNTAX      Counter64
    MAX-ACCESS  read-only
    STATUS      current
    DESCRIPTION
    "Number of GTP V2 messages sent."
    ::= { jnxMbgPgwGtpPerPeerStatsEntry 17 }

jnxMbgPgwPPV2GlbNumBytesRx  OBJECT-TYPE
    SYNTAX      Counter64
    MAX-ACCESS  read-only
    STATUS      current
    DESCRIPTION
    "Number of GTPv2 bytes received."
    ::= { jnxMbgPgwGtpPerPeerStatsEntry 18 }

jnxMbgPgwPPV2GlbNumBytesTx  OBJECT-TYPE
    SYNTAX      Counter64
    MAX-ACCESS  read-only
    STATUS      current
    DESCRIPTION
    "Number of GTP V2 bytes sent."
    ::= { jnxMbgPgwGtpPerPeerStatsEntry 19 }

jnxMbgPgwPPV2GlbEchoReqRx  OBJECT-TYPE
    SYNTAX      Counter64
    MAX-ACCESS  read-only
    STATUS      current
    DESCRIPTION
    "Number of GTP V2 Echo Requests received."
    ::= { jnxMbgPgwGtpPerPeerStatsEntry 20 }

jnxMbgPgwPPV2GlbEchoReqTx  OBJECT-TYPE
    SYNTAX      Counter64
    MAX-ACCESS  read-only
    STATUS      current
    DESCRIPTION
    "Number of GTP V2 Echo Requests Sent."
    ::= { jnxMbgPgwGtpPerPeerStatsEntry 21 }

jnxMbgPgwPPV2GlbEchoRespRx  OBJECT-TYPE
    SYNTAX      Counter64
    MAX-ACCESS  read-only
    STATUS      current
    DESCRIPTION
    "Number of GTP V2 Echo Responses received."
    ::= { jnxMbgPgwGtpPerPeerStatsEntry 22 }

jnxMbgPgwPPV2GlbEchoRespTx  OBJECT-TYPE
    SYNTAX      Counter64
    MAX-ACCESS  read-only
    STATUS      current
    DESCRIPTION
    "Number of GTP V2 Echo Responses Sent."
    ::= { jnxMbgPgwGtpPerPeerStatsEntry 23 }

jnxMbgPgwPPV2VerNotSupRx OBJECT-TYPE
    SYNTAX      Counter64
    MAX-ACCESS  read-only
    STATUS      current
    DESCRIPTION
    "Number of GTP V2 Version Not supported messages received"
    ::= { jnxMbgPgwGtpPerPeerStatsEntry 24 }

jnxMbgPgwPPV2VerNotSupTx OBJECT-TYPE
    SYNTAX      Counter64
    MAX-ACCESS  read-only
    STATUS      current
    DESCRIPTION
    "Number of GTP V2 Number of version not supported messages Sent."
    ::= { jnxMbgPgwGtpPerPeerStatsEntry 25 }

jnxMbgPgwPPV2CreateSessReqRx  OBJECT-TYPE
    SYNTAX      Counter64
    MAX-ACCESS  read-only
    STATUS      current
    DESCRIPTION
    "Number of GTP V2 Create Session Requests received."
    ::= { jnxMbgPgwGtpPerPeerStatsEntry 26 }

jnxMbgPgwPPV2CreateSessReqTx  OBJECT-TYPE
    SYNTAX      Counter64
    MAX-ACCESS  read-only
    STATUS      current
    DESCRIPTION
    "Number of GTP V2 Create Session Requests Sent."
    ::= { jnxMbgPgwGtpPerPeerStatsEntry 27 }

jnxMbgPgwPPV2CreateSessRspRx  OBJECT-TYPE
    SYNTAX      Counter64
    MAX-ACCESS  read-only
    STATUS      current
    DESCRIPTION
    "Number of GTP V2 Create Session Responses received."
    ::= { jnxMbgPgwGtpPerPeerStatsEntry 28 }

jnxMbgPgwPPV2CreateSessRspTx  OBJECT-TYPE
    SYNTAX      Counter64
    MAX-ACCESS  read-only
    STATUS      current
    DESCRIPTION
    "Number of GTP V2 Create Session Responses Sent."
    ::= { jnxMbgPgwGtpPerPeerStatsEntry 29 }

jnxMbgPgwPPV2ModBrReqRx  OBJECT-TYPE
    SYNTAX      Counter64
    MAX-ACCESS  read-only
    STATUS      current
    DESCRIPTION
    "Number of GTP V2 Modify Bearer Requests received."
    ::= { jnxMbgPgwGtpPerPeerStatsEntry 30 }

jnxMbgPgwPPV2ModBrReqTx  OBJECT-TYPE
    SYNTAX      Counter64
    MAX-ACCESS  read-only
    STATUS      current
    DESCRIPTION
    "Number of GTP V2 Modify Bearer Requests Sent."
    ::= { jnxMbgPgwGtpPerPeerStatsEntry 31 }

jnxMbgPgwPPV2ModBrRspRx  OBJECT-TYPE
    SYNTAX      Counter64
    MAX-ACCESS  read-only
    STATUS      current
    DESCRIPTION
    "Number of GTP V2 Modify Bearer Responses received."
    ::= { jnxMbgPgwGtpPerPeerStatsEntry 32 }

jnxMbgPgwPPV2ModBrRspTx  OBJECT-TYPE
    SYNTAX      Counter64
    MAX-ACCESS  read-only
    STATUS      current
    DESCRIPTION
    "Number of GTP V2 Modify Bearer Responses Sent."
    ::= { jnxMbgPgwGtpPerPeerStatsEntry 33 }

jnxMbgPgwPPV2DelSessReqRx  OBJECT-TYPE
    SYNTAX      Counter64
    MAX-ACCESS  read-only
    STATUS      current
    DESCRIPTION
    "Number of GTP V2 Delete Session Requests received."
    ::= { jnxMbgPgwGtpPerPeerStatsEntry 34 }

jnxMbgPgwPPV2DelSessReqTx  OBJECT-TYPE
    SYNTAX      Counter64
    MAX-ACCESS  read-only
    STATUS      current
    DESCRIPTION
    "Number of GTP V2 Delete Session Requests Sent."
    ::= { jnxMbgPgwGtpPerPeerStatsEntry 35 }

jnxMbgPgwPPV2DelSessRspRx  OBJECT-TYPE
    SYNTAX      Counter64
    MAX-ACCESS  read-only
    STATUS      current
    DESCRIPTION
    "Number of GTP V2 Delete Session Responses received."
    ::= { jnxMbgPgwGtpPerPeerStatsEntry 36 }

jnxMbgPgwPPV2DelSessRspTx  OBJECT-TYPE
    SYNTAX      Counter64
    MAX-ACCESS  read-only
    STATUS      current
    DESCRIPTION
    "Number of GTP V2 Delete Session Responses Sent."
    ::= { jnxMbgPgwGtpPerPeerStatsEntry 37 }

jnxMbgPgwPPV2CrtBrReqRx  OBJECT-TYPE
    SYNTAX      Counter64
    MAX-ACCESS  read-only
    STATUS      current
    DESCRIPTION
    "Number of GTP V2 Create Bearer Requests received."
    ::= { jnxMbgPgwGtpPerPeerStatsEntry 38 }

jnxMbgPgwPPV2CrtBrReqTx  OBJECT-TYPE
    SYNTAX      Counter64
    MAX-ACCESS  read-only
    STATUS      current
    DESCRIPTION
    "Number of GTP V2 Create Bearer Requests Sent."
    ::= { jnxMbgPgwGtpPerPeerStatsEntry 39 }

jnxMbgPgwPPV2CrtBrRspRx  OBJECT-TYPE
    SYNTAX      Counter64
    MAX-ACCESS  read-only
    STATUS      current
    DESCRIPTION
    "Number of GTP V2 Create Bearer Responses received."
    ::= { jnxMbgPgwGtpPerPeerStatsEntry 40 }

jnxMbgPgwPPV2CrtBrRspTx  OBJECT-TYPE
    SYNTAX      Counter64
    MAX-ACCESS  read-only
    STATUS      current
    DESCRIPTION
    "Number of GTP V2 Create Bearer Responses Sent."
    ::= { jnxMbgPgwGtpPerPeerStatsEntry 41 }

jnxMbgPgwPPV2UpdBrReqRx  OBJECT-TYPE
    SYNTAX      Counter64
    MAX-ACCESS  read-only
    STATUS      current
    DESCRIPTION
    "Number of GTP V2 Update Bearer Requests received."
    ::= { jnxMbgPgwGtpPerPeerStatsEntry 42 }

jnxMbgPgwPPV2UpdBrReqTx  OBJECT-TYPE
    SYNTAX      Counter64
    MAX-ACCESS  read-only
    STATUS      current
    DESCRIPTION
    "Number of GTP V2 Update Bearer Requests Sent."
    ::= { jnxMbgPgwGtpPerPeerStatsEntry 43 }

jnxMbgPgwPPV2UpdBrRspRx  OBJECT-TYPE
    SYNTAX      Counter64
    MAX-ACCESS  read-only
    STATUS      current
    DESCRIPTION
    "Number of GTP V2 Update Bearer Responses received."
    ::= { jnxMbgPgwGtpPerPeerStatsEntry 44 }

jnxMbgPgwPPV2UpdBrRspTx  OBJECT-TYPE
    SYNTAX      Counter64
    MAX-ACCESS  read-only
    STATUS      current
    DESCRIPTION
    "Number of GTP V2 Update Bearer Responses Sent."
    ::= { jnxMbgPgwGtpPerPeerStatsEntry 45 }

jnxMbgPgwPPV2DelBrReqRx  OBJECT-TYPE
    SYNTAX      Counter64
    MAX-ACCESS  read-only
    STATUS      current
    DESCRIPTION
    "Number of GTP V2 Delete Bearer Requests received."
    ::= { jnxMbgPgwGtpPerPeerStatsEntry 46 }

jnxMbgPgwPPV2DelBrReqTx  OBJECT-TYPE
    SYNTAX      Counter64
    MAX-ACCESS  read-only
    STATUS      current
    DESCRIPTION
    "Number of GTP V2 Delete Bearer Requests Sent."
    ::= { jnxMbgPgwGtpPerPeerStatsEntry 47 }

jnxMbgPgwPPV2DelBrRspRx  OBJECT-TYPE
    SYNTAX      Counter64
    MAX-ACCESS  read-only
    STATUS      current
    DESCRIPTION
    "Number of GTP V2 Delete Bearer Responses received."
    ::= { jnxMbgPgwGtpPerPeerStatsEntry 48 }

jnxMbgPgwPPV2DelBrRspTx  OBJECT-TYPE
    SYNTAX      Counter64
    MAX-ACCESS  read-only
    STATUS      current
    DESCRIPTION
    "Number of GTP V2 Delete Bearer Responses Sent."
    ::= { jnxMbgPgwGtpPerPeerStatsEntry 49 }
jnxMbgPgwPPV2DelConnSetReqRx  OBJECT-TYPE
    SYNTAX      Counter64
    MAX-ACCESS  read-only
    STATUS      current
    DESCRIPTION
    "GTP V2 Delete PDN connection set Requests received."
    ::= { jnxMbgPgwGtpPerPeerStatsEntry 50 }

jnxMbgPgwPPV2DelConnSetReqTx  OBJECT-TYPE
    SYNTAX      Counter64
    MAX-ACCESS  read-only
    STATUS      current
    DESCRIPTION
    "GTP V2 Delete PDN connection set Requests Sent."
    ::= { jnxMbgPgwGtpPerPeerStatsEntry 51 }

jnxMbgPgwPPV2DelConnSetRspRx  OBJECT-TYPE
    SYNTAX      Counter64
    MAX-ACCESS  read-only
    STATUS      current
    DESCRIPTION
    "GTP V2 Delete PDN connection set Responses received."
    ::= { jnxMbgPgwGtpPerPeerStatsEntry 52 }

jnxMbgPgwPPV2DelConnSetRspTx  OBJECT-TYPE
    SYNTAX      Counter64
    MAX-ACCESS  read-only
    STATUS      current
    DESCRIPTION
    "GTP V2 Delete PDN connection set Responses Sent."
    ::= { jnxMbgPgwGtpPerPeerStatsEntry 53 }

jnxMbgPgwPPV2UpdConnSetReqRx  OBJECT-TYPE
    SYNTAX      Counter64
    MAX-ACCESS  read-only
    STATUS      current
    DESCRIPTION
    "GTP V2 Update Connection set Requests received."
    ::= { jnxMbgPgwGtpPerPeerStatsEntry 54 }

jnxMbgPgwPPV2UpdConnSetReqTx  OBJECT-TYPE
    SYNTAX      Counter64
    MAX-ACCESS  read-only
    STATUS      current
    DESCRIPTION
    "GTP V2 Update Connection set Requests Sent."
    ::= { jnxMbgPgwGtpPerPeerStatsEntry 55 }

jnxMbgPgwPPV2UpdConnSetRspRx  OBJECT-TYPE
    SYNTAX      Counter64
    MAX-ACCESS  read-only
    STATUS      current
    DESCRIPTION
    "GTP V2 Update Connecton set Responses received."
    ::= { jnxMbgPgwGtpPerPeerStatsEntry 56 }

jnxMbgPgwPPV2UpdConnSetRspTx  OBJECT-TYPE
    SYNTAX      Counter64
    MAX-ACCESS  read-only
    STATUS      current
    DESCRIPTION
    "GTP V2 Update Connection set Responses Sent."
    ::= { jnxMbgPgwGtpPerPeerStatsEntry 57 }

jnxMbgPgwPPV2ModBrCmdRx  OBJECT-TYPE
    SYNTAX      Counter64
    MAX-ACCESS  read-only
    STATUS      current
    DESCRIPTION
    "Number of GTP V2 Modify Bearer Command received."
    ::= { jnxMbgPgwGtpPerPeerStatsEntry 58 }

jnxMbgPgwPPV2ModBrCmdTx  OBJECT-TYPE
    SYNTAX      Counter64
    MAX-ACCESS  read-only
    STATUS      current
    DESCRIPTION
    "Number of GTP V2 Modify Bearer Command Sent."
    ::= { jnxMbgPgwGtpPerPeerStatsEntry 59 }

jnxMbgPgwPPV2ModBrFlrIndRx  OBJECT-TYPE
    SYNTAX      Counter64
    MAX-ACCESS  read-only
    STATUS      current
    DESCRIPTION
    "Number of GTP V2 Modify Bearer Failure received."
    ::= { jnxMbgPgwGtpPerPeerStatsEntry 60 }

jnxMbgPgwPPV2ModBrFlrIndTx  OBJECT-TYPE
    SYNTAX      Counter64
    MAX-ACCESS  read-only
    STATUS      current
    DESCRIPTION
    "Number of GTP V2 Modify Bearer Failure Sent."
    ::= { jnxMbgPgwGtpPerPeerStatsEntry 61 }

jnxMbgPgwPPV2DelBrCmdRx  OBJECT-TYPE
    SYNTAX      Counter64
    MAX-ACCESS  read-only
    STATUS      current
    DESCRIPTION
    "Number of GTP V2 Delete Bearer Command received."
    ::= { jnxMbgPgwGtpPerPeerStatsEntry 62 }

jnxMbgPgwPPV2DelBrCmdTx  OBJECT-TYPE
    SYNTAX      Counter64
    MAX-ACCESS  read-only
    STATUS      current
    DESCRIPTION
    "Number of GTP V2 Delete Bearer Command Sent."
    ::= { jnxMbgPgwGtpPerPeerStatsEntry 63 }

jnxMbgPgwPPV2DelBrFlrIndRx  OBJECT-TYPE
    SYNTAX      Counter64
    MAX-ACCESS  read-only
    STATUS      current
    DESCRIPTION
    "Number of GTP V2 Delete Bearer Failure received."
    ::= { jnxMbgPgwGtpPerPeerStatsEntry 64 }

jnxMbgPgwPPV2DelBrFlrIndTx  OBJECT-TYPE
    SYNTAX      Counter64
    MAX-ACCESS  read-only
    STATUS      current
    DESCRIPTION
    "Number of GTP V2 Delete Bearer Failure Sent."
    ::= { jnxMbgPgwGtpPerPeerStatsEntry 65 }

jnxMbgPgwPPV2BrResCmdRx  OBJECT-TYPE
    SYNTAX      Counter64
    MAX-ACCESS  read-only
    STATUS      current
    DESCRIPTION
    "Number of GTP V2 Bearer Response Command received."
    ::= { jnxMbgPgwGtpPerPeerStatsEntry 66 }

jnxMbgPgwPPV2BrResCmdTx  OBJECT-TYPE
    SYNTAX      Counter64
    MAX-ACCESS  read-only
    STATUS      current
    DESCRIPTION
    "Number of GTP V2 Bearer Response Command Sent."
    ::= { jnxMbgPgwGtpPerPeerStatsEntry 67 }

jnxMbgPgwPPV2BrResFlrIndRx  OBJECT-TYPE
    SYNTAX      Counter64
    MAX-ACCESS  read-only
    STATUS      current
    DESCRIPTION
    "Number of GTP V2 Bearer Resource Failure received."
    ::= { jnxMbgPgwGtpPerPeerStatsEntry 68 }

jnxMbgPgwPPV2BrResFlrIndTx  OBJECT-TYPE
    SYNTAX      Counter64
    MAX-ACCESS  read-only
    STATUS      current
    DESCRIPTION
    "Number of GTP V2 Bearer Resource Failure Sent."
    ::= { jnxMbgPgwGtpPerPeerStatsEntry 69 }

jnxMbgPgwPPV2RelAcsBrReqRx OBJECT-TYPE
    SYNTAX      Counter64
    MAX-ACCESS  read-only
    STATUS      obsolete
    DESCRIPTION
    "Number of GTP V2 Release Access Bearer Requests received."
    ::= { jnxMbgPgwGtpPerPeerStatsEntry 70 }

jnxMbgPgwPPV2RelAcsBrReqTx OBJECT-TYPE
    SYNTAX      Counter64
    MAX-ACCESS  read-only
    STATUS      obsolete
    DESCRIPTION
    "Number of GTP V2 Release Access Bearer Requests sent."
    ::= { jnxMbgPgwGtpPerPeerStatsEntry 71 }

jnxMbgPgwPPV2RelAcsBrRespRx OBJECT-TYPE
    SYNTAX      Counter64
    MAX-ACCESS  read-only
    STATUS      obsolete
    DESCRIPTION
    "Number of GTP V2 Release Access Bearer Response received."
    ::= { jnxMbgPgwGtpPerPeerStatsEntry 72 }

jnxMbgPgwPPV2RelAcsBrRespTx OBJECT-TYPE
    SYNTAX      Counter64
    MAX-ACCESS  read-only
    STATUS      obsolete
    DESCRIPTION
    "Number of GTP V2 Release Access Bearer Response sent."
    ::= { jnxMbgPgwGtpPerPeerStatsEntry 73 }

jnxMbgPgwPPV2CrIndTunReqRx OBJECT-TYPE
    SYNTAX      Counter64
    MAX-ACCESS  read-only
    STATUS      obsolete
    DESCRIPTION
    "Number of GTP V2 Create Indirect Tunnel Forward Requests Received"
    ::= { jnxMbgPgwGtpPerPeerStatsEntry 74 }

jnxMbgPgwPPV2CrIndTunReqTx OBJECT-TYPE
    SYNTAX      Counter64
    MAX-ACCESS  read-only
    STATUS      obsolete
    DESCRIPTION
    "Number of GTP V2 Create Indirect Tunnel Forward Requests sent"
    ::= { jnxMbgPgwGtpPerPeerStatsEntry 75 }

jnxMbgPgwPPV2CrIndTunRespRx  OBJECT-TYPE
    SYNTAX      Counter64
    MAX-ACCESS  read-only
    STATUS      obsolete
    DESCRIPTION
    "Number of GTP V2 Create Indirect Tunnel Forward Responses Received"
    ::= { jnxMbgPgwGtpPerPeerStatsEntry 76 }

jnxMbgPgwPPV2CrIndTunRespTx  OBJECT-TYPE
    SYNTAX      Counter64
    MAX-ACCESS  read-only
    STATUS      obsolete
    DESCRIPTION
    "Number of GTP V2 Create Indirect Tunnel Forward Responses sent"
    ::= { jnxMbgPgwGtpPerPeerStatsEntry 77 }

jnxMbgPgwPPV2DelIndTunReqRx OBJECT-TYPE
    SYNTAX      Counter64
    MAX-ACCESS  read-only
    STATUS      obsolete
    DESCRIPTION
    "Number of GTP V2 Delete Indirect Tunnel Forward Requests Received"
    ::= { jnxMbgPgwGtpPerPeerStatsEntry 78 }

jnxMbgPgwPPV2DelIndTunReqTx OBJECT-TYPE
    SYNTAX      Counter64
    MAX-ACCESS  read-only
    STATUS      obsolete
    DESCRIPTION
    "Number of GTP V2 Delete Indirect Tunnel Forward Requests sent."
    ::= { jnxMbgPgwGtpPerPeerStatsEntry 79 }

jnxMbgPgwPPV2DelIndTunRespRx  OBJECT-TYPE
    SYNTAX      Counter64
    MAX-ACCESS  read-only
    STATUS      obsolete
    DESCRIPTION
    "Number of GTP V2 Delete Indirect Tunnel Forward Responses Received"
    ::= { jnxMbgPgwGtpPerPeerStatsEntry 80 }

jnxMbgPgwPPV2DelIndTunRespTx  OBJECT-TYPE
    SYNTAX      Counter64
    MAX-ACCESS  read-only
    STATUS      obsolete
    DESCRIPTION
    "Number of GTP V2 Delete Indirect Tunnel Forward Responses sent."
    ::= { jnxMbgPgwGtpPerPeerStatsEntry 81 }

jnxMbgPgwPPV2DlDataNotifRx  OBJECT-TYPE
    SYNTAX      Counter64
    MAX-ACCESS  read-only
    STATUS      obsolete
    DESCRIPTION
    "Number of GTP V2 Downlink Data Notify received."
    ::= { jnxMbgPgwGtpPerPeerStatsEntry 82 }

jnxMbgPgwPPV2DlDataNotifTx  OBJECT-TYPE
    SYNTAX      Counter64
    MAX-ACCESS  read-only
    STATUS      obsolete
    DESCRIPTION
    "Number of GTP V2 Downlink Data Notify Sent."
    ::= { jnxMbgPgwGtpPerPeerStatsEntry 83 }

jnxMbgPgwPPV2DlDataAckRx  OBJECT-TYPE
    SYNTAX      Counter64
    MAX-ACCESS  read-only
    STATUS      obsolete
    DESCRIPTION
    "Number of GTP V2 Downlink Data Notify Acknowledgements received."
    ::= { jnxMbgPgwGtpPerPeerStatsEntry 84 }

jnxMbgPgwPPV2DlDataAckTx  OBJECT-TYPE
    SYNTAX      Counter64
    MAX-ACCESS  read-only
    STATUS      obsolete
    DESCRIPTION
    "Number of GTP V2 Downlink Data Notify Acknowledgements Sent."
    ::= { jnxMbgPgwGtpPerPeerStatsEntry 85 }

jnxMbgPgwPPV2DlDataNotiFlrIndRx  OBJECT-TYPE
    SYNTAX      Counter64
    MAX-ACCESS  read-only
    STATUS      obsolete
    DESCRIPTION
    "Number of GTP V2 Downlink Data Notification fail received."
    ::= { jnxMbgPgwGtpPerPeerStatsEntry 86 }

jnxMbgPgwPPV2DlDataNotiFlrIndTx  OBJECT-TYPE
    SYNTAX      Counter64
    MAX-ACCESS  read-only
    STATUS      obsolete
    DESCRIPTION
    "Number of GTP V2 Downlink Data Notification fail Sent."
    ::= { jnxMbgPgwGtpPerPeerStatsEntry 87 }

jnxMbgPgwPPV2StopPagingIndRx OBJECT-TYPE
    SYNTAX      Counter64
    MAX-ACCESS  read-only
    STATUS      obsolete
    DESCRIPTION
    "Number of GTP V2 Stop Paging Indication Messages Received."
    ::= { jnxMbgPgwGtpPerPeerStatsEntry 88 }

jnxMbgPgwPPV2StopPagingIndTx  OBJECT-TYPE
    SYNTAX      Counter64
    MAX-ACCESS  read-only
    STATUS      obsolete
    DESCRIPTION
    "Number of GTP V2 Stop Paging Indicaton messages sent"
    ::= { jnxMbgPgwGtpPerPeerStatsEntry 89 }

jnxMbgPgwPPV2ICsPageRx  OBJECT-TYPE
    SYNTAX      Counter64
    MAX-ACCESS  read-only
    STATUS      obsolete
    DESCRIPTION
    "Number of GTPV2 packets received with cause Page."
    ::= { jnxMbgPgwGtpPerPeerStatsEntry 90 }

jnxMbgPgwPPV2ICsPageTx  OBJECT-TYPE
    SYNTAX      Counter64
    MAX-ACCESS  read-only
    STATUS      obsolete
    DESCRIPTION
    "Number of GTPV2 packets sent with cause Page."
    ::= { jnxMbgPgwGtpPerPeerStatsEntry 91 }

jnxMbgPgwPPV2ICsReqAcceptRx  OBJECT-TYPE
    SYNTAX      Counter64
    MAX-ACCESS  read-only
    STATUS      current
    DESCRIPTION
    "Number of GTPV2 packets received with cause Request Accept."
    ::= { jnxMbgPgwGtpPerPeerStatsEntry 92 }

jnxMbgPgwPPV2ICsReqAcceptTx  OBJECT-TYPE
    SYNTAX      Counter64
    MAX-ACCESS  read-only
    STATUS      current
    DESCRIPTION
    "Number of GTPV2 packets sent with cause Request Accept."
    ::= { jnxMbgPgwGtpPerPeerStatsEntry 93 }

jnxMbgPgwPPV2ICsAcceptPartRx  OBJECT-TYPE
    SYNTAX      Counter64
    MAX-ACCESS  read-only
    STATUS      current
    DESCRIPTION
    "Number of GTPV2 packets received with cause Accept Partial."
    ::= { jnxMbgPgwGtpPerPeerStatsEntry 94 }

jnxMbgPgwPPV2ICsAcceptPartTx  OBJECT-TYPE
    SYNTAX      Counter64
    MAX-ACCESS  read-only
    STATUS      current
    DESCRIPTION
    "Number of GTPV2 packets sent with cause Accept Partial."
    ::= { jnxMbgPgwGtpPerPeerStatsEntry 95 }

jnxMbgPgwPPV2ICsNewPTNPrefRx  OBJECT-TYPE
    SYNTAX      Counter64
    MAX-ACCESS  read-only
    STATUS      current
    DESCRIPTION
    "Number of GTPV2 packets received with cause New PDN type due to Network Preference."
    ::= { jnxMbgPgwGtpPerPeerStatsEntry 96 }

jnxMbgPgwPPV2ICsNewPTNPrefTx  OBJECT-TYPE
    SYNTAX      Counter64
    MAX-ACCESS  read-only
    STATUS      current
    DESCRIPTION
    "Number of GTPV2 packets sent with cause New PDN type due to Network Preference."
    ::= { jnxMbgPgwGtpPerPeerStatsEntry 97 }


jnxMbgPgwPPV2ICsNewPTSIAdbrRx  OBJECT-TYPE
    SYNTAX      Counter64
    MAX-ACCESS  read-only
    STATUS      current
    DESCRIPTION
    "Number of GTPV2 packets received with cause New PDN type due to Single Address Bearer."
    ::= { jnxMbgPgwGtpPerPeerStatsEntry 98 }

jnxMbgPgwPPV2ICsNewPTSIAdbrTx  OBJECT-TYPE
    SYNTAX      Counter64
    MAX-ACCESS  read-only
    STATUS      current
    DESCRIPTION
    "Number of GTPV2 packets sent with cause New PDN type due to Single Address Bearer."
    ::= { jnxMbgPgwGtpPerPeerStatsEntry 99 }

jnxMbgPgwPPV2ICsCtxNotFndRx  OBJECT-TYPE
    SYNTAX      Counter64
    MAX-ACCESS  read-only
    STATUS      current
    DESCRIPTION
    "Number of GTPV2 packets received with cause Context not found ."
    ::= { jnxMbgPgwGtpPerPeerStatsEntry 100 }

jnxMbgPgwPPV2ICsCtxNotFndTx  OBJECT-TYPE
    SYNTAX      Counter64
    MAX-ACCESS  read-only
    STATUS      current
    DESCRIPTION
    "Number of GTPV2 packets sent with cause Context not found."
    ::= { jnxMbgPgwGtpPerPeerStatsEntry 101 }

jnxMbgPgwPPV2ICsInvMsgFmtRx  OBJECT-TYPE
    SYNTAX      Counter64
    MAX-ACCESS  read-only
    STATUS      current
    DESCRIPTION
    "Number of GTPV2 packets received with cause Invalid Message Format."
    ::= { jnxMbgPgwGtpPerPeerStatsEntry 102 }

jnxMbgPgwPPV2ICsInvMsgFmtTx  OBJECT-TYPE
    SYNTAX      Counter64
    MAX-ACCESS  read-only
    STATUS      current
    DESCRIPTION
    "Number of GTPV2 packets sent with cause Invalid Message Format."
    ::= { jnxMbgPgwGtpPerPeerStatsEntry 103 }

jnxMbgPgwPPV2ICsVerNotSuppRx  OBJECT-TYPE
    SYNTAX      Counter64
    MAX-ACCESS  read-only
    STATUS      current
    DESCRIPTION
    "Number of GTPV2 packets received with cause Version not Supported."
    ::= { jnxMbgPgwGtpPerPeerStatsEntry 104 }

jnxMbgPgwPPV2ICsVerNotSuppTx  OBJECT-TYPE
    SYNTAX      Counter64
    MAX-ACCESS  read-only
    STATUS      current
    DESCRIPTION
    "Number of GTPV2 packets sent with cause Version not Supported."
    ::= { jnxMbgPgwGtpPerPeerStatsEntry 105 }

jnxMbgPgwPPV2ICsInvLenRx  OBJECT-TYPE
    SYNTAX      Counter64
    MAX-ACCESS  read-only
    STATUS      current
    DESCRIPTION
    "Number of GTPV2 packets received with cause Invalid Length."
    ::= { jnxMbgPgwGtpPerPeerStatsEntry 106 }

jnxMbgPgwPPV2ICsInvLenTx  OBJECT-TYPE
    SYNTAX      Counter64
    MAX-ACCESS  read-only
    STATUS      current
    DESCRIPTION
    "Number of GTPV2 packets sent with cause Invalid Length."
    ::= { jnxMbgPgwGtpPerPeerStatsEntry 107 }

jnxMbgPgwPPV2ICsServNotSuppRx  OBJECT-TYPE
    SYNTAX      Counter64
    MAX-ACCESS  read-only
    STATUS      current
    DESCRIPTION
    "Number of GTPV2 packets received with cause Service Not supported."
    ::= { jnxMbgPgwGtpPerPeerStatsEntry 108 }

jnxMbgPgwPPV2ICsServNotSuppTx  OBJECT-TYPE
    SYNTAX      Counter64
    MAX-ACCESS  read-only
    STATUS      current
    DESCRIPTION
    "Number of GTPV2 packets sent with cause Service Not supported."
    ::= { jnxMbgPgwGtpPerPeerStatsEntry 109 }

jnxMbgPgwPPV2ICsManIEIncorrRx  OBJECT-TYPE
    SYNTAX      Counter64
    MAX-ACCESS  read-only
    STATUS      current
    DESCRIPTION
    "Number of GTPV2 packets received with cause Mandatory IE incorrect."
    ::= { jnxMbgPgwGtpPerPeerStatsEntry 110 }

jnxMbgPgwPPV2ICsManIEIncorrTx  OBJECT-TYPE
    SYNTAX      Counter64
    MAX-ACCESS  read-only
    STATUS      current
    DESCRIPTION
    "Number of GTPV2 packets sent with cause Mandatory IE incorrect."
    ::= { jnxMbgPgwGtpPerPeerStatsEntry 111 }

jnxMbgPgwPPV2ICsManIEMissRx  OBJECT-TYPE
    SYNTAX      Counter64
    MAX-ACCESS  read-only
    STATUS      current
    DESCRIPTION
    "Number of GTPV2 packets received with cause Mandatory IE Missing."
    ::= { jnxMbgPgwGtpPerPeerStatsEntry 112 }

jnxMbgPgwPPV2ICsManIEMissTx  OBJECT-TYPE
    SYNTAX      Counter64
    MAX-ACCESS  read-only
    STATUS      current
    DESCRIPTION
    "Number of GTPV2 packets sent with cause Mandatory IE Missing."
    ::= { jnxMbgPgwGtpPerPeerStatsEntry 113 }

jnxMbgPgwPPV2ICsOptIEIncorrRx  OBJECT-TYPE
    SYNTAX      Counter64
    MAX-ACCESS  read-only
    STATUS      current
    DESCRIPTION
    "Number of GTPV2 packets received with cause Optional IE Incorrect."
    ::= { jnxMbgPgwGtpPerPeerStatsEntry 114 }

jnxMbgPgwPPV2ICsOptIEIncorrTx  OBJECT-TYPE
    SYNTAX      Counter64
    MAX-ACCESS  read-only
    STATUS      current
    DESCRIPTION
    "Number of GTPV2 packets sent with cause Optional IE Incorrect."
    ::= { jnxMbgPgwGtpPerPeerStatsEntry 115 }

jnxMbgPgwPPV2ICsSysFailRx  OBJECT-TYPE
    SYNTAX      Counter64
    MAX-ACCESS  read-only
    STATUS      current
    DESCRIPTION
    "Number of GTPV2 packets received with cause System Failure."
    ::= { jnxMbgPgwGtpPerPeerStatsEntry 116 }

jnxMbgPgwPPV2ICsSysFailTx  OBJECT-TYPE
    SYNTAX      Counter64
    MAX-ACCESS  read-only
    STATUS      current
    DESCRIPTION
    "Number of GTPV2 packets sent with cause System Failure."
    ::= { jnxMbgPgwGtpPerPeerStatsEntry 117 }

jnxMbgPgwPPV2ICsNoResRx  OBJECT-TYPE
    SYNTAX      Counter64
    MAX-ACCESS  read-only
    STATUS      current
    DESCRIPTION
    "Number of GTPV2 packets received with cause No Resource."
    ::= { jnxMbgPgwGtpPerPeerStatsEntry 118 }

jnxMbgPgwPPV2ICsNoResTx  OBJECT-TYPE
    SYNTAX      Counter64
    MAX-ACCESS  read-only
    STATUS      current
    DESCRIPTION
    "Number of GTPV2 packets sent with cause No Resource."
    ::= { jnxMbgPgwGtpPerPeerStatsEntry 119 }

jnxMbgPgwPPV2ICsTFTSMANTErRx  OBJECT-TYPE
    SYNTAX      Counter64
    MAX-ACCESS  read-only
    STATUS      current
    DESCRIPTION
    "Number of GTPV2 packets received with cause TFT Symantic Error."
    ::= { jnxMbgPgwGtpPerPeerStatsEntry 120 }

jnxMbgPgwPPV2ICsTFTSMANTErTx  OBJECT-TYPE
    SYNTAX      Counter64
    MAX-ACCESS  read-only
    STATUS      current
    DESCRIPTION
    "Number of GTPV2 packets sent with cause TFT Symantic Error."
    ::= { jnxMbgPgwGtpPerPeerStatsEntry 121 }

jnxMbgPgwPPV2ICsTFTSysErrRx  OBJECT-TYPE
    SYNTAX      Counter64
    MAX-ACCESS  read-only
    STATUS      current
    DESCRIPTION
    "Number of GTPV2 packets received with cause TFT System Error."
    ::= { jnxMbgPgwGtpPerPeerStatsEntry 122 }

jnxMbgPgwPPV2ICsTFTSysErrTx  OBJECT-TYPE
    SYNTAX      Counter64
    MAX-ACCESS  read-only
    STATUS      current
    DESCRIPTION
    "Number of GTPV2 packets sent with cause TFT System Error."
    ::= { jnxMbgPgwGtpPerPeerStatsEntry 123 }

jnxMbgPgwPPV2ICsPkFltManErrRx  OBJECT-TYPE
    SYNTAX      Counter64
    MAX-ACCESS  read-only
    STATUS      current
    DESCRIPTION
    "Number of GTPV2 packets received with cause Packet Filter Symantic Error."
    ::= { jnxMbgPgwGtpPerPeerStatsEntry 124 }

jnxMbgPgwPPV2ICsPkFltManErrTx  OBJECT-TYPE
    SYNTAX      Counter64
    MAX-ACCESS  read-only
    STATUS      current
    DESCRIPTION
    "Number of GTPV2 packets sent with cause Packet Filter Symantic Error."
    ::= { jnxMbgPgwGtpPerPeerStatsEntry 125 }

jnxMbgPgwPPV2ICsPkFltSynErrRx  OBJECT-TYPE
    SYNTAX      Counter64
    MAX-ACCESS  read-only
    STATUS      current
    DESCRIPTION
    "Number of GTPV2 packets received with cause Packet Filter Syntax Error."
    ::= { jnxMbgPgwGtpPerPeerStatsEntry 126 }

jnxMbgPgwPPV2ICsPkFltSynErrTx  OBJECT-TYPE
    SYNTAX      Counter64
    MAX-ACCESS  read-only
    STATUS      current
    DESCRIPTION
    "Number of GTPV2 packets sent with cause Packet Filter Syntax Error."
    ::= { jnxMbgPgwGtpPerPeerStatsEntry 127 }

jnxMbgPgwPPV2ICsMisUnknAPNRx  OBJECT-TYPE
    SYNTAX      Counter64
    MAX-ACCESS  read-only
    STATUS      current
    DESCRIPTION
    "Number of GTPV2 packets received with cause Unknown APN."
    ::= { jnxMbgPgwGtpPerPeerStatsEntry 128 }

jnxMbgPgwPPV2ICsMisUnknAPNTx  OBJECT-TYPE
    SYNTAX      Counter64
    MAX-ACCESS  read-only
    STATUS      current
    DESCRIPTION
    "Number of GTPV2 packets sent with cause Unknown APN."
    ::= { jnxMbgPgwGtpPerPeerStatsEntry 129 }

jnxMbgPgwPPV2ICsUnexpRptIERx  OBJECT-TYPE
    SYNTAX      Counter64
    MAX-ACCESS  read-only
    STATUS      current
    DESCRIPTION
    "Number of GTPV2 packets received with cause Unexpected Repeated IE."
    ::= { jnxMbgPgwGtpPerPeerStatsEntry 130 }

jnxMbgPgwPPV2ICsUnexpRptIETx  OBJECT-TYPE
    SYNTAX      Counter64
    MAX-ACCESS  read-only
    STATUS      current
    DESCRIPTION
    "Number of GTPV2 packets sent with cause Unexpected Repeated IE."
    ::= { jnxMbgPgwGtpPerPeerStatsEntry 131 }

jnxMbgPgwPPV2ICsGREKeyNtFdRx  OBJECT-TYPE
    SYNTAX      Counter64
    MAX-ACCESS  read-only
    STATUS      current
    DESCRIPTION
    "Number of GTPV2 packets received with cause GRE Key Not Found."
    ::= { jnxMbgPgwGtpPerPeerStatsEntry 132 }

jnxMbgPgwPPV2ICsGREKeyNtFdTx  OBJECT-TYPE
    SYNTAX      Counter64
    MAX-ACCESS  read-only
    STATUS      current
    DESCRIPTION
    "Number of GTPV2 packets sent with cause GRE Key Not Found."
    ::= { jnxMbgPgwGtpPerPeerStatsEntry 133 }

jnxMbgPgwPPV2ICsRelocFailRx  OBJECT-TYPE
    SYNTAX      Counter64
    MAX-ACCESS  read-only
    STATUS      current
    DESCRIPTION
    "Number of GTPV2 packets received with cause Relocation Failed."
    ::= { jnxMbgPgwGtpPerPeerStatsEntry 134 }

jnxMbgPgwPPV2ICsRelocFailTx  OBJECT-TYPE
    SYNTAX      Counter64
    MAX-ACCESS  read-only
    STATUS      current
    DESCRIPTION
    "Number of GTPV2 packets sent with cause Relocation Failed."
    ::= { jnxMbgPgwGtpPerPeerStatsEntry 135 }

jnxMbgPgwPPV2ICsDeniedINRatRx  OBJECT-TYPE
    SYNTAX      Counter64
    MAX-ACCESS  read-only
    STATUS      current
    DESCRIPTION
    "Number of GTPV2 packets received with cause Denied in RAT."
    ::= { jnxMbgPgwGtpPerPeerStatsEntry 136 }

jnxMbgPgwPPV2ICsDeniedINRatTx  OBJECT-TYPE
    SYNTAX      Counter64
    MAX-ACCESS  read-only
    STATUS      current
    DESCRIPTION
    "Number of GTPV2 packets sent with cause Denied in RAT."
    ::= { jnxMbgPgwGtpPerPeerStatsEntry 137 }

jnxMbgPgwPPV2ICsPTNotSuppRx  OBJECT-TYPE
    SYNTAX      Counter64
    MAX-ACCESS  read-only
    STATUS      current
    DESCRIPTION
    "Number of GTPV2 packets received with cause PDN Type Not Supported."
    ::= { jnxMbgPgwGtpPerPeerStatsEntry 138 }

jnxMbgPgwPPV2ICsPTNotSuppTx  OBJECT-TYPE
    SYNTAX      Counter64
    MAX-ACCESS  read-only
    STATUS      current
    DESCRIPTION
    "Number of GTPV2 packets sent with cause PDN Type Not Supported."
    ::= { jnxMbgPgwGtpPerPeerStatsEntry 139 }

jnxMbgPgwPPV2ICsAllDynAdOccRx  OBJECT-TYPE
    SYNTAX      Counter64
    MAX-ACCESS  read-only
    STATUS      current
    DESCRIPTION
    "Number of GTPV2 packets received with cause Allocated Dynamic Address Occupied."
    ::= { jnxMbgPgwGtpPerPeerStatsEntry 140 }

jnxMbgPgwPPV2ICsAllDynAdOccTx  OBJECT-TYPE
    SYNTAX      Counter64
    MAX-ACCESS  read-only
    STATUS      current
    DESCRIPTION
    "Number of GTPV2 packets sent with cause Allocated Dynamic Address Occupied."
    ::= { jnxMbgPgwGtpPerPeerStatsEntry 141 }

jnxMbgPgwPPV2ICsNOTFTUECTXRx  OBJECT-TYPE
    SYNTAX      Counter64
    MAX-ACCESS  read-only
    STATUS      current
    DESCRIPTION
    "Number of GTPV2 packets received with cause UE Context Without TFT Exists."
    ::= { jnxMbgPgwGtpPerPeerStatsEntry 142 }

jnxMbgPgwPPV2ICsNOTFTUECTXTx  OBJECT-TYPE
    SYNTAX      Counter64
    MAX-ACCESS  read-only
    STATUS      current
    DESCRIPTION
    "Number of GTPV2 packets sent with cause UE Context Without TFT Exists."
    ::= { jnxMbgPgwGtpPerPeerStatsEntry 143 }

jnxMbgPgwPPV2ICsProtoNtSupRx  OBJECT-TYPE
    SYNTAX      Counter64
    MAX-ACCESS  read-only
    STATUS      current
    DESCRIPTION
    "Number of GTPV2 packets received with cause Protocol Not Supported."
    ::= { jnxMbgPgwGtpPerPeerStatsEntry 144 }

jnxMbgPgwPPV2ICsProtoNtSupTx  OBJECT-TYPE
    SYNTAX      Counter64
    MAX-ACCESS  read-only
    STATUS      current
    DESCRIPTION
    "Number of GTPV2 packets sent with cause Protocol Not Supported."
    ::= { jnxMbgPgwGtpPerPeerStatsEntry 145 }

jnxMbgPgwPPV2ICsUENotRespRx  OBJECT-TYPE
    SYNTAX      Counter64
    MAX-ACCESS  read-only
    STATUS      current
    DESCRIPTION
    "Number of GTPV2 packets received with cause UE Not Responding."
    ::= { jnxMbgPgwGtpPerPeerStatsEntry 146 }

jnxMbgPgwPPV2ICsUENotRespTx  OBJECT-TYPE
    SYNTAX      Counter64
    MAX-ACCESS  read-only
    STATUS      current
    DESCRIPTION
    "Number of GTPV2 packets sent with cause UE Not Responding."
    ::= { jnxMbgPgwGtpPerPeerStatsEntry 147 }

jnxMbgPgwPPV2ICsUERefusesRx  OBJECT-TYPE
    SYNTAX      Counter64
    MAX-ACCESS  read-only
    STATUS      current
    DESCRIPTION
    "Number of GTPV2 packets received with cause UE Refuses."
    ::= { jnxMbgPgwGtpPerPeerStatsEntry 148 }

jnxMbgPgwPPV2ICsUERefusesTx  OBJECT-TYPE
    SYNTAX      Counter64
    MAX-ACCESS  read-only
    STATUS      current
    DESCRIPTION
    "Number of GTPV2 packets sent with cause UE Refuses."
    ::= { jnxMbgPgwGtpPerPeerStatsEntry 149 }

jnxMbgPgwPPV2ICsServDeniedRx  OBJECT-TYPE
    SYNTAX      Counter64
    MAX-ACCESS  read-only
    STATUS      current
    DESCRIPTION
    "Number of GTPV2 packets received with cause Service Denied."
    ::= { jnxMbgPgwGtpPerPeerStatsEntry 150 }

jnxMbgPgwPPV2ICsServDeniedTx  OBJECT-TYPE
    SYNTAX      Counter64
    MAX-ACCESS  read-only
    STATUS      current
    DESCRIPTION
    "Number of GTPV2 packets sent with cause Service Denied."
    ::= { jnxMbgPgwGtpPerPeerStatsEntry 151 }

jnxMbgPgwPPV2ICsUnabPageUERx  OBJECT-TYPE
    SYNTAX      Counter64
    MAX-ACCESS  read-only
    STATUS      current
    DESCRIPTION
    "Number of GTPV2 packets received with cause Unable to Page UE."
    ::= { jnxMbgPgwGtpPerPeerStatsEntry 152 }

jnxMbgPgwPPV2ICsUnabPageUETx  OBJECT-TYPE
    SYNTAX      Counter64
    MAX-ACCESS  read-only
    STATUS      current
    DESCRIPTION
    "Number of GTPV2 packets sent with cause Unable to Page UE."
    ::= { jnxMbgPgwGtpPerPeerStatsEntry 153 }

jnxMbgPgwPPV2ICsNoMemRx  OBJECT-TYPE
    SYNTAX      Counter64
    MAX-ACCESS  read-only
    STATUS      current
    DESCRIPTION
    "Number of GTPV2 packets received with cause No Memory."
    ::= { jnxMbgPgwGtpPerPeerStatsEntry 154 }

jnxMbgPgwPPV2ICsNoMemTx  OBJECT-TYPE
    SYNTAX      Counter64
    MAX-ACCESS  read-only
    STATUS      current
    DESCRIPTION
    "Number of GTPV2 packets sent with cause No Memory."
    ::= { jnxMbgPgwGtpPerPeerStatsEntry 155 }

jnxMbgPgwPPV2ICsUserAUTHFlRx  OBJECT-TYPE
    SYNTAX      Counter64
    MAX-ACCESS  read-only
    STATUS      current
    DESCRIPTION
    "Number of GTPV2 packets received with cause User AUTH Failed."
    ::= { jnxMbgPgwGtpPerPeerStatsEntry 156 }

jnxMbgPgwPPV2ICsUserAUTHFlTx  OBJECT-TYPE
    SYNTAX      Counter64
    MAX-ACCESS  read-only
    STATUS      current
    DESCRIPTION
    "Number of GTPV2 packets sent with cause User AUTH Failed."
    ::= { jnxMbgPgwGtpPerPeerStatsEntry 157 }

jnxMbgPgwPPV2ICsAPNAcsDenRx  OBJECT-TYPE
    SYNTAX      Counter64
    MAX-ACCESS  read-only
    STATUS      current
    DESCRIPTION
    "Number of GTPV2 packets received with cause APN Access Denied."
    ::= { jnxMbgPgwGtpPerPeerStatsEntry 158 }

jnxMbgPgwPPV2ICsAPNAcsDenTx  OBJECT-TYPE
    SYNTAX      Counter64
    MAX-ACCESS  read-only
    STATUS      current
    DESCRIPTION
    "Number of GTPV2 packets sent with cause APN Access Denied."
    ::= { jnxMbgPgwGtpPerPeerStatsEntry 159 }

jnxMbgPgwPPV2ICsReqRejRx  OBJECT-TYPE
    SYNTAX      Counter64
    MAX-ACCESS  read-only
    STATUS      current
    DESCRIPTION
    "Number of GTPV2 packets received with cause Request Rejected."
    ::= { jnxMbgPgwGtpPerPeerStatsEntry 160 }

jnxMbgPgwPPV2ICsReqRejTx  OBJECT-TYPE
    SYNTAX      Counter64
    MAX-ACCESS  read-only
    STATUS      current
    DESCRIPTION
    "Number of GTPV2 packets sent with cause Request Rejected."
    ::= { jnxMbgPgwGtpPerPeerStatsEntry 161 }

jnxMbgPgwPPV2ICsPTMSISigMMRx OBJECT-TYPE
     SYNTAX      Counter64
     MAX-ACCESS  read-only
     STATUS      current
     DESCRIPTION
     "Number of GTPV2 packets received with cause P-TMSI Signature Mismatch"
    ::= { jnxMbgPgwGtpPerPeerStatsEntry 162 }

jnxMbgPgwPPV2ICsPTMSISigMMTx OBJECT-TYPE
     SYNTAX      Counter64
     MAX-ACCESS  read-only
     STATUS      current
     DESCRIPTION
     "Number of GTPV2 packets sent with cause P-TMSI Signature Mismatch."
    ::= { jnxMbgPgwGtpPerPeerStatsEntry 163 }

jnxMbgPgwPPV2ICsIMSINotKnRx OBJECT-TYPE
      SYNTAX      Counter64
      MAX-ACCESS  read-only
      STATUS      current
      DESCRIPTION
      "Number of GTPV2 packets received with cause IMSI Not Known."
    ::= { jnxMbgPgwGtpPerPeerStatsEntry 164 }

jnxMbgPgwPPV2ICsIMSINotKnTx OBJECT-TYPE
      SYNTAX      Counter64
      MAX-ACCESS  read-only
      STATUS      current
      DESCRIPTION
      "Number of GTPV2 packets sent with cause IMSI Not Known."
    ::= { jnxMbgPgwGtpPerPeerStatsEntry 165 }

jnxMbgPgwPPV2ICsCondIEMsRx OBJECT-TYPE
       SYNTAX      Counter64
       MAX-ACCESS  read-only
       STATUS      current
       DESCRIPTION
       "Number of GTPV2 packets received with cause Conditional IE Missing."
     ::= { jnxMbgPgwGtpPerPeerStatsEntry 166 }

jnxMbgPgwPPV2ICsCondIEMsTx OBJECT-TYPE
       SYNTAX      Counter64
       MAX-ACCESS  read-only
       STATUS      current
       DESCRIPTION
       "Number of GTPV2 packets sent with cause Conditional IE Missing."
     ::= { jnxMbgPgwGtpPerPeerStatsEntry 167 }

jnxMbgPgwPPV2ICsAPNResTIncRx OBJECT-TYPE
        SYNTAX      Counter64
        MAX-ACCESS  read-only
        STATUS      current
        DESCRIPTION
        "Number of GTPV2 packets received with cause APN Restriction Type Incompatible msgs received"
     ::= { jnxMbgPgwGtpPerPeerStatsEntry 168 }

jnxMbgPgwPPV2ICsAPNResTIncTx OBJECT-TYPE
        SYNTAX      Counter64
        MAX-ACCESS  read-only
        STATUS      current
        DESCRIPTION
        "Number of GTPV2 packets sent with cause APN Restriction Type Incompatible msgs sent."
     ::= { jnxMbgPgwGtpPerPeerStatsEntry 169 }

jnxMbgPgwPPV2ICsUnknownRx OBJECT-TYPE
         SYNTAX      Counter64
         MAX-ACCESS  read-only
         STATUS      current
         DESCRIPTION
         "Number of GTPV2 packets received with cause Unknown."
     ::= { jnxMbgPgwGtpPerPeerStatsEntry 170 }

jnxMbgPgwPPV2ICsUnknownTx OBJECT-TYPE
         SYNTAX      Counter64
         MAX-ACCESS  read-only
         STATUS      current
         DESCRIPTION
         "Number of GTPV2 packets sent with cause Unknown."
     ::= { jnxMbgPgwGtpPerPeerStatsEntry 171 }

jnxMbgPgwPPV1ProtocolErrRx  OBJECT-TYPE
    SYNTAX      Counter64
    MAX-ACCESS  read-only
    STATUS      current
    DESCRIPTION
    "Number of GTPv1 Protocol Errors Received."
    ::= { jnxMbgPgwGtpPerPeerStatsEntry 172 }

jnxMbgPgwPPV1UnSupportedMsgRx  OBJECT-TYPE
    SYNTAX      Counter64
    MAX-ACCESS  read-only
    STATUS      current
    DESCRIPTION
    "Number of GTPv1 Unsupported Messages received."
    ::= { jnxMbgPgwGtpPerPeerStatsEntry 173 }

jnxMbgPgwPPV1T3RespTmrExpRx  OBJECT-TYPE
    SYNTAX      Counter64
    MAX-ACCESS  read-only
    STATUS      current
    DESCRIPTION
    "Number of GTP V1 T3 timer expiries Received."
    ::= { jnxMbgPgwGtpPerPeerStatsEntry 174 }

jnxMbgPgwPPV1GlbNumMsgRx  OBJECT-TYPE
    SYNTAX      Counter64
    MAX-ACCESS  read-only
    STATUS      current
    DESCRIPTION
    "Number of GTPv1 messages received."
    ::= { jnxMbgPgwGtpPerPeerStatsEntry 175 }

jnxMbgPgwPPV1GlbNumMsgTx  OBJECT-TYPE
    SYNTAX      Counter64
    MAX-ACCESS  read-only
    STATUS      current
    DESCRIPTION
    "Number of GTP V1 messages sent."
    ::= { jnxMbgPgwGtpPerPeerStatsEntry 176 }

jnxMbgPgwPPV1GlbNumBytesRx  OBJECT-TYPE
    SYNTAX      Counter64
    MAX-ACCESS  read-only
    STATUS      current
    DESCRIPTION
    "Number of GTPv1 bytes received."
    ::= { jnxMbgPgwGtpPerPeerStatsEntry 177 }

jnxMbgPgwPPV1GlbNumBytesTx  OBJECT-TYPE
    SYNTAX      Counter64
    MAX-ACCESS  read-only
    STATUS      current
    DESCRIPTION
    "Number of GTPV1 bytes sent."
    ::= { jnxMbgPgwGtpPerPeerStatsEntry 178 }

jnxMbgPgwPPV1GlbEchoReqRx  OBJECT-TYPE
    SYNTAX      Counter64
    MAX-ACCESS  read-only
    STATUS      current
    DESCRIPTION
    "Number of GTP V1 Echo Requests received."
    ::= { jnxMbgPgwGtpPerPeerStatsEntry 179 }

jnxMbgPgwPPV1GlbEchoReqTx  OBJECT-TYPE
    SYNTAX      Counter64
    MAX-ACCESS  read-only
    STATUS      current
    DESCRIPTION
    "Number of GTP V1 Echo Requests Sent."
    ::= { jnxMbgPgwGtpPerPeerStatsEntry 180 }

jnxMbgPgwPPV1GlbEchoRespRx  OBJECT-TYPE
    SYNTAX      Counter64
    MAX-ACCESS  read-only
    STATUS      current
    DESCRIPTION
    "Number of GTP V1 Echo Responses received."
    ::= { jnxMbgPgwGtpPerPeerStatsEntry 181 }

jnxMbgPgwPPV1GlbEchoRespTx  OBJECT-TYPE
    SYNTAX      Counter64
    MAX-ACCESS  read-only
    STATUS      current
    DESCRIPTION
    "Number of GTP V1 Echo Responses Sent."
    ::= { jnxMbgPgwGtpPerPeerStatsEntry 182 }

jnxMbgPgwPPV1VerNotSupRx OBJECT-TYPE
    SYNTAX      Counter64
    MAX-ACCESS  read-only
    STATUS      current
    DESCRIPTION
    "Number of GTP V1 Version Not supported messages received"
    ::= { jnxMbgPgwGtpPerPeerStatsEntry 183 }

jnxMbgPgwPPV1VerNotSupTx OBJECT-TYPE
    SYNTAX      Counter64
    MAX-ACCESS  read-only
    STATUS      current
    DESCRIPTION
    "Number of GTP V1 Number of version not supported messages sent."
    ::= { jnxMbgPgwGtpPerPeerStatsEntry 184 }

jnxMbgPgwPPV1CrtPdpCxtReqRx   OBJECT-TYPE
    SYNTAX      Counter64
    MAX-ACCESS  read-only
    STATUS      current
    DESCRIPTION
    "Number of GTP V1 Create PDP Context Requests Received."
    ::= { jnxMbgPgwGtpPerPeerStatsEntry 185 }

jnxMbgPgwPPV1CrtPdpCxtReqTx   OBJECT-TYPE
    SYNTAX      Counter64
    MAX-ACCESS  read-only
    STATUS      current
    DESCRIPTION
    "Number of GTP V1 Create PDP Context Requests Sent."
    ::= { jnxMbgPgwGtpPerPeerStatsEntry 186 }

jnxMbgPgwPPV1CrtPdpCxtRspRx   OBJECT-TYPE
    SYNTAX      Counter64
    MAX-ACCESS  read-only
    STATUS      current
    DESCRIPTION
    "Number of GTP V1 Create PDP Context Responses Received."
    ::= { jnxMbgPgwGtpPerPeerStatsEntry 187 }

jnxMbgPgwPPV1CrtPdpCxtRspTx   OBJECT-TYPE
    SYNTAX      Counter64
    MAX-ACCESS  read-only
    STATUS      current
    DESCRIPTION
    "Number of GTP V1 Create PDP Context Responses Sent."
    ::= { jnxMbgPgwGtpPerPeerStatsEntry 188 }

jnxMbgPgwPPV1UpdPdpCxtReqRx   OBJECT-TYPE
    SYNTAX      Counter64
    MAX-ACCESS  read-only
    STATUS      current
    DESCRIPTION
    "Number of GTP V1 Update PDP Context Requests Received."
    ::= { jnxMbgPgwGtpPerPeerStatsEntry 189 }

jnxMbgPgwPPV1UpdPdpCxtReqTx   OBJECT-TYPE
    SYNTAX      Counter64
    MAX-ACCESS  read-only
    STATUS      current
    DESCRIPTION
    "Number of GTP V1 Update PDP Context Requests Sent."
    ::= { jnxMbgPgwGtpPerPeerStatsEntry 190 }

jnxMbgPgwPPV1UpdPdpCxtRspRx   OBJECT-TYPE
    SYNTAX      Counter64
    MAX-ACCESS  read-only
    STATUS      current
    DESCRIPTION
    "Number of GTP V1 Update PDP Context Responses Received."
    ::= { jnxMbgPgwGtpPerPeerStatsEntry 191 }

jnxMbgPgwPPV1UpdPdpCxtRspTx   OBJECT-TYPE
    SYNTAX      Counter64
    MAX-ACCESS  read-only
    STATUS      current
    DESCRIPTION
    "Number of GTP V1 Update PDP Context Responses Sent."
    ::= { jnxMbgPgwGtpPerPeerStatsEntry 192 }

jnxMbgPgwPPV1DelPdpCxtReqRx   OBJECT-TYPE
    SYNTAX      Counter64
    MAX-ACCESS  read-only
    STATUS      current
    DESCRIPTION
    "Number of GTP V1 Delete PDP Context Requests Received."
    ::= { jnxMbgPgwGtpPerPeerStatsEntry 193 }

jnxMbgPgwPPV1DelPdpCxtReqTx   OBJECT-TYPE
    SYNTAX      Counter64
    MAX-ACCESS  read-only
    STATUS      current
    DESCRIPTION
    "Number of GTP V1 Delete PDP Context Requests Sent."
    ::= { jnxMbgPgwGtpPerPeerStatsEntry 194 }

jnxMbgPgwPPV1DelPdpCxtRspRx   OBJECT-TYPE
    SYNTAX      Counter64
    MAX-ACCESS  read-only
    STATUS      current
    DESCRIPTION
    "Number of GTP V1 Delete PDP Context Responses Received."
    ::= { jnxMbgPgwGtpPerPeerStatsEntry 195 }

jnxMbgPgwPPV1DelPdpCxtRspTx   OBJECT-TYPE
    SYNTAX      Counter64
    MAX-ACCESS  read-only
    STATUS      current
    DESCRIPTION
    "Number of GTP V1 Delete PDP Context Responses Sent."
    ::= { jnxMbgPgwGtpPerPeerStatsEntry 196 }

jnxMbgPgwPPV1CrtAAPdpCxtReqRx   OBJECT-TYPE
    SYNTAX      Counter64
    MAX-ACCESS  read-only
    STATUS      current
    DESCRIPTION
    "Number of GTP V1 Create AA PDP Context Requests Received."
    ::= { jnxMbgPgwGtpPerPeerStatsEntry 197 }

jnxMbgPgwPPV1CrtAAPdpCxtReqTx   OBJECT-TYPE
    SYNTAX      Counter64
    MAX-ACCESS  read-only
    STATUS      current
    DESCRIPTION
    "Number of GTP V1 Create AA PDP Context Requests Sent."
    ::= { jnxMbgPgwGtpPerPeerStatsEntry 198 }

jnxMbgPgwPPV1CrtAAPdpCxtRspRx   OBJECT-TYPE
    SYNTAX      Counter64
    MAX-ACCESS  read-only
    STATUS      current
    DESCRIPTION
    "Number of GTP V1 Create AA PDP Context Responses Received."
    ::= { jnxMbgPgwGtpPerPeerStatsEntry 199 }

jnxMbgPgwPPV1CrtAAPdpCxtRspTx   OBJECT-TYPE
    SYNTAX      Counter64
    MAX-ACCESS  read-only
    STATUS      current
    DESCRIPTION
    "Number of GTP V1 Create AA PDP Context Responses Sent."
    ::= { jnxMbgPgwGtpPerPeerStatsEntry 200 }

jnxMbgPgwPPV1DelAAPdpCxtReqRx   OBJECT-TYPE
    SYNTAX      Counter64
    MAX-ACCESS  read-only
    STATUS      current
    DESCRIPTION
    "Number of GTP V1 Delete AA PDP Context Requests Received."
    ::= { jnxMbgPgwGtpPerPeerStatsEntry 201 }

jnxMbgPgwPPV1DelAAPdpCxtReqTx   OBJECT-TYPE
    SYNTAX      Counter64
    MAX-ACCESS  read-only
    STATUS      current
    DESCRIPTION
    "Number of GTP V1 Delete AA PDP Context Requests Sent."
    ::= { jnxMbgPgwGtpPerPeerStatsEntry 202 }

jnxMbgPgwPPV1DelAAPdpCxtRspRx   OBJECT-TYPE
    SYNTAX      Counter64
    MAX-ACCESS  read-only
    STATUS      current
    DESCRIPTION
    "Number of GTP V1 Delete AA PDP Context Responses Received."
    ::= { jnxMbgPgwGtpPerPeerStatsEntry 203 }

jnxMbgPgwPPV1DelAAPdpCxtRspTx   OBJECT-TYPE
    SYNTAX      Counter64
    MAX-ACCESS  read-only
    STATUS      current
    DESCRIPTION
    "Number of GTP V1 Delete AA PDP Context Responses Sent."
    ::= { jnxMbgPgwGtpPerPeerStatsEntry 204 }

jnxMbgPgwPPV1ErrorIndRx   OBJECT-TYPE
    SYNTAX      Counter64
    MAX-ACCESS  read-only
    STATUS      current
    DESCRIPTION
    "Number of GTP V1 Error Indication Received."
    ::= { jnxMbgPgwGtpPerPeerStatsEntry 205 }

jnxMbgPgwPPV1ErrorIndTx   OBJECT-TYPE
    SYNTAX      Counter64
    MAX-ACCESS  read-only
    STATUS      current
    DESCRIPTION
    "Number of GTP V1 Error Indication Sent."
    ::= { jnxMbgPgwGtpPerPeerStatsEntry 206 }

jnxMbgPgwPPV1NotifReqRx   OBJECT-TYPE
    SYNTAX      Counter64
    MAX-ACCESS  read-only
    STATUS      current
    DESCRIPTION
    "Number of GTP V1 Notify Requests Received."
    ::= { jnxMbgPgwGtpPerPeerStatsEntry 207 }

jnxMbgPgwPPV1NotifReqTx   OBJECT-TYPE
    SYNTAX      Counter64
    MAX-ACCESS  read-only
    STATUS      current
    DESCRIPTION
    "Number of GTP V1 Notify Requests Sent."
    ::= { jnxMbgPgwGtpPerPeerStatsEntry 208 }

jnxMbgPgwPPV1NotifRspRx   OBJECT-TYPE
    SYNTAX      Counter64
    MAX-ACCESS  read-only
    STATUS      current
    DESCRIPTION
    "Number of GTP V1 Notify Responses Received."
    ::= { jnxMbgPgwGtpPerPeerStatsEntry 209 }

jnxMbgPgwPPV1NotifRspTx   OBJECT-TYPE
    SYNTAX      Counter64
    MAX-ACCESS  read-only
    STATUS      current
    DESCRIPTION
    "Number of GTP V1 Notify Responses Sent."
    ::= { jnxMbgPgwGtpPerPeerStatsEntry 210 }

jnxMbgPgwPPV1NotifRejReqRx   OBJECT-TYPE
    SYNTAX      Counter64
    MAX-ACCESS  read-only
    STATUS      current
    DESCRIPTION
    "Number of GTP V1 Notify Reject Requests Received."
    ::= { jnxMbgPgwGtpPerPeerStatsEntry 211 }

jnxMbgPgwPPV1NotifRejReqTx   OBJECT-TYPE
    SYNTAX      Counter64
    MAX-ACCESS  read-only
    STATUS      current
    DESCRIPTION
    "Number of GTP V1 Notify Reject Requests Sent."
    ::= { jnxMbgPgwGtpPerPeerStatsEntry 212 }

jnxMbgPgwPPV1NotifRejRspRx   OBJECT-TYPE
    SYNTAX      Counter64
    MAX-ACCESS  read-only
    STATUS      current
    DESCRIPTION
    "Number of GTP V1 Notify Reject Responses Received."
    ::= { jnxMbgPgwGtpPerPeerStatsEntry 213 }

jnxMbgPgwPPV1NotifRejRspTx   OBJECT-TYPE
    SYNTAX      Counter64
    MAX-ACCESS  read-only
    STATUS      current
    DESCRIPTION
    "Number of GTP V1 Notify Reject Responses Sent."
    ::= { jnxMbgPgwGtpPerPeerStatsEntry 214 }

jnxMbgPgwPPV1RtInfReqRx   OBJECT-TYPE
    SYNTAX      Counter64
    MAX-ACCESS  read-only
    STATUS      current
    DESCRIPTION
    "Number of GTP V1 Routing Information Requests Received."
    ::= { jnxMbgPgwGtpPerPeerStatsEntry 215 }

jnxMbgPgwPPV1RtInfReqTx   OBJECT-TYPE
    SYNTAX      Counter64
    MAX-ACCESS  read-only
    STATUS      current
    DESCRIPTION
    "Number of GTP V1 Routing Information Requests Sent."
    ::= { jnxMbgPgwGtpPerPeerStatsEntry 216 }

jnxMbgPgwPPV1RtInfRspRx   OBJECT-TYPE
    SYNTAX      Counter64
    MAX-ACCESS  read-only
    STATUS      current
    DESCRIPTION
    "Number of GTP V1 Routing Information Responses Received."
    ::= { jnxMbgPgwGtpPerPeerStatsEntry 217 }

jnxMbgPgwPPV1RtInfRspTx   OBJECT-TYPE
    SYNTAX      Counter64
    MAX-ACCESS  read-only
    STATUS      current
    DESCRIPTION
    "Number of GTP V1 Routing Information Responses Sent."
    ::= { jnxMbgPgwGtpPerPeerStatsEntry 218 }

jnxMbgPgwPPV1FailRptReqRx   OBJECT-TYPE
    SYNTAX      Counter64
    MAX-ACCESS  read-only
    STATUS      current
    DESCRIPTION
    "Number of GTP V1 Fail Repeat Requests Received."
    ::= { jnxMbgPgwGtpPerPeerStatsEntry 219 }

jnxMbgPgwPPV1FailRptReqTx   OBJECT-TYPE
    SYNTAX      Counter64
    MAX-ACCESS  read-only
    STATUS      current
    DESCRIPTION
    "Number of GTP V1 Fail Repeat Requests Sent."
    ::= { jnxMbgPgwGtpPerPeerStatsEntry 220 }

jnxMbgPgwPPV1FailRptRspRx   OBJECT-TYPE
    SYNTAX      Counter64
    MAX-ACCESS  read-only
    STATUS      current
    DESCRIPTION
    "Number of GTP V1 Fail Repeat Responses Received."
    ::= { jnxMbgPgwGtpPerPeerStatsEntry 221 }

jnxMbgPgwPPV1FailRptRspTx   OBJECT-TYPE
    SYNTAX      Counter64
    MAX-ACCESS  read-only
    STATUS      current
    DESCRIPTION
    "Number of GTP V1 Fail Repeat Responses Sent."
    ::= { jnxMbgPgwGtpPerPeerStatsEntry 222 }

jnxMbgPgwPPV1NotMSPresReqRx   OBJECT-TYPE
    SYNTAX      Counter64
    MAX-ACCESS  read-only
    STATUS      current
    DESCRIPTION
    "Number of GTP V1 MS Not Present Request Received."
    ::= { jnxMbgPgwGtpPerPeerStatsEntry 223 }

jnxMbgPgwPPV1NotMSPresReqTx   OBJECT-TYPE
    SYNTAX      Counter64
    MAX-ACCESS  read-only
    STATUS      current
    DESCRIPTION
    "Number of GTP V1 MS Not Present Request Sent."
    ::= { jnxMbgPgwGtpPerPeerStatsEntry 224 }

jnxMbgPgwPPV1NotMSPresRspRx   OBJECT-TYPE
    SYNTAX      Counter64
    MAX-ACCESS  read-only
    STATUS      current
    DESCRIPTION
    "Number of GTP V1 MS Not Present Responses Received."
    ::= { jnxMbgPgwGtpPerPeerStatsEntry 225 }

jnxMbgPgwPPV1NotMSPresRspTx   OBJECT-TYPE
    SYNTAX      Counter64
    MAX-ACCESS  read-only
    STATUS      current
    DESCRIPTION
    "Number of GTP V1 MS Not Present Responses Sent."
    ::= { jnxMbgPgwGtpPerPeerStatsEntry 226 }

jnxMbgPgwPPV1ICsReqAcceptedRx   OBJECT-TYPE
    SYNTAX      Counter64
    MAX-ACCESS  read-only
    STATUS      current
    DESCRIPTION
    "Number of GTPV1 packets received with cause Request Accepted."
    ::= { jnxMbgPgwGtpPerPeerStatsEntry 227 }

jnxMbgPgwPPV1ICsReqAcceptedTx   OBJECT-TYPE
    SYNTAX      Counter64
    MAX-ACCESS  read-only
    STATUS      current
    DESCRIPTION
    "Number of GTPV1 packets sent with cause Request Accepted."
    ::= { jnxMbgPgwGtpPerPeerStatsEntry 228 }

jnxMbgPgwPPV1ICsNonExistRx   OBJECT-TYPE
    SYNTAX      Counter64
    MAX-ACCESS  read-only
    STATUS      current
    DESCRIPTION
    "Number of GTPV1 packets received with cause Non Existant."
    ::= { jnxMbgPgwGtpPerPeerStatsEntry 229 }

jnxMbgPgwPPV1ICsNonExistTx   OBJECT-TYPE
    SYNTAX      Counter64
    MAX-ACCESS  read-only
    STATUS      current
    DESCRIPTION
    "Number of GTPV1 packets sent with cause Non Existant."
    ::= { jnxMbgPgwGtpPerPeerStatsEntry 230 }

jnxMbgPgwPPV1ICsInvMsgFmtRx   OBJECT-TYPE
    SYNTAX      Counter64
    MAX-ACCESS  read-only
    STATUS      current
    DESCRIPTION
    "Number of GTPV1 packets received with cause Invalid Mesage Format."
    ::= { jnxMbgPgwGtpPerPeerStatsEntry 231 }

jnxMbgPgwPPV1ICsInvMsgFmtTx   OBJECT-TYPE
    SYNTAX      Counter64
    MAX-ACCESS  read-only
    STATUS      current
    DESCRIPTION
    "Number of GTPV1 packets sent with cause Invalid Mesage Format."
    ::= { jnxMbgPgwGtpPerPeerStatsEntry 232 }

jnxMbgPgwPPV1ICsIMSINotKnownRx   OBJECT-TYPE
    SYNTAX      Counter64
    MAX-ACCESS  read-only
    STATUS      current
    DESCRIPTION
    "Number of GTPV1 packets received with cause IMSI Not Known."
    ::= { jnxMbgPgwGtpPerPeerStatsEntry 233 }


jnxMbgPgwPPV1ICsIMSINotKnownTx   OBJECT-TYPE
    SYNTAX      Counter64
    MAX-ACCESS  read-only
    STATUS      current
    DESCRIPTION
    "Number of GTPV1 packets sent with cause IMSI Not Known."
    ::= { jnxMbgPgwGtpPerPeerStatsEntry 234 }

jnxMbgPgwPPV1ICsMSGRPSDetachRx   OBJECT-TYPE
    SYNTAX      Counter64
    MAX-ACCESS  read-only
    STATUS      current
    DESCRIPTION
    "Number of GTPV1 packets received with cause MS GPRS Detached."
    ::= { jnxMbgPgwGtpPerPeerStatsEntry 235 }

jnxMbgPgwPPV1ICsMSGRPSDetachTx   OBJECT-TYPE
    SYNTAX      Counter64
    MAX-ACCESS  read-only
    STATUS      current
    DESCRIPTION
    "Number of GTPV1 packets sent with cause MS GPRS Detached."
    ::= { jnxMbgPgwGtpPerPeerStatsEntry 236 }

jnxMbgPgwPPV1ICsMSNotGRPSRespRx   OBJECT-TYPE
    SYNTAX      Counter64
    MAX-ACCESS  read-only
    STATUS      current
    DESCRIPTION
    "Number of GTPV1 packets received with cause MS No GPRS Response."
    ::= { jnxMbgPgwGtpPerPeerStatsEntry 237 }

jnxMbgPgwPPV1ICsMSNotGRPSRespTx   OBJECT-TYPE
    SYNTAX      Counter64
    MAX-ACCESS  read-only
    STATUS      current
    DESCRIPTION
    "Number of GTPV1 packets sent with cause MS No GPRS Response."
    ::= { jnxMbgPgwGtpPerPeerStatsEntry 238 }

jnxMbgPgwPPV1ICsMSRefusesRx   OBJECT-TYPE
    SYNTAX      Counter64
    MAX-ACCESS  read-only
    STATUS      current
    DESCRIPTION
    "Number of GTPV1 packets received with cause MS Refues."
    ::= { jnxMbgPgwGtpPerPeerStatsEntry 239 }

jnxMbgPgwPPV1ICsMSRefusesTx   OBJECT-TYPE
    SYNTAX      Counter64
    MAX-ACCESS  read-only
    STATUS      current
    DESCRIPTION
    "Number of GTPV1 packets sent with cause MS Refues."
    ::= { jnxMbgPgwGtpPerPeerStatsEntry 240 }

jnxMbgPgwPPV1ICsVerNotSuppRx   OBJECT-TYPE
    SYNTAX      Counter64
    MAX-ACCESS  read-only
    STATUS      current
    DESCRIPTION
    "Number of GTPV1 packets received with cause Version Not Supported."
    ::= { jnxMbgPgwGtpPerPeerStatsEntry 241 }

jnxMbgPgwPPV1ICsVerNotSuppTx   OBJECT-TYPE
    SYNTAX      Counter64
    MAX-ACCESS  read-only
    STATUS      current
    DESCRIPTION
    "Number of GTPV1 packets sent with cause Version Not Supported."
    ::= { jnxMbgPgwGtpPerPeerStatsEntry 242 }

jnxMbgPgwPPV1ICsNoResRx   OBJECT-TYPE
    SYNTAX      Counter64
    MAX-ACCESS  read-only
    STATUS      current
    DESCRIPTION
    "Number of GTPV1 packets received with cause No Response."
    ::= { jnxMbgPgwGtpPerPeerStatsEntry 243 }

jnxMbgPgwPPV1ICsNoResTx   OBJECT-TYPE
    SYNTAX      Counter64
    MAX-ACCESS  read-only
    STATUS      current
    DESCRIPTION
    "Number of GTPV1 packets sent with cause No Response."
    ::= { jnxMbgPgwGtpPerPeerStatsEntry 244 }

jnxMbgPgwPPV1ICsServNotSuppRx   OBJECT-TYPE
    SYNTAX      Counter64
    MAX-ACCESS  read-only
    STATUS      current
    DESCRIPTION
    "Number of GTPV1 packets received with cause Service Not Supported."
    ::= { jnxMbgPgwGtpPerPeerStatsEntry 245 }

jnxMbgPgwPPV1ICsServNotSuppTx   OBJECT-TYPE
    SYNTAX      Counter64
    MAX-ACCESS  read-only
    STATUS      current
    DESCRIPTION
    "Number of GTPV1 packets sent with cause Service Not Supported."
    ::= { jnxMbgPgwGtpPerPeerStatsEntry 246 }

jnxMbgPgwPPV1ICsManIEIncrtRx   OBJECT-TYPE
    SYNTAX      Counter64
    MAX-ACCESS  read-only
    STATUS      current
    DESCRIPTION
    "Number of GTPV1 packets received with cause Mandatory IE incorrect."
    ::= { jnxMbgPgwGtpPerPeerStatsEntry 247 }

jnxMbgPgwPPV1ICsManIEIncrtTx   OBJECT-TYPE
    SYNTAX      Counter64
    MAX-ACCESS  read-only
    STATUS      current
    DESCRIPTION
    "Number of GTPV1 packets sent with cause Mandatory IE incorrect."
    ::= { jnxMbgPgwGtpPerPeerStatsEntry 248 }

jnxMbgPgwPPV1ICsManIEMissRx   OBJECT-TYPE
    SYNTAX      Counter64
    MAX-ACCESS  read-only
    STATUS      current
    DESCRIPTION
    "Number of GTPV1 packets received with cause Mandatory IE Missing."
    ::= { jnxMbgPgwGtpPerPeerStatsEntry 249 }

jnxMbgPgwPPV1ICsManIEMissTx   OBJECT-TYPE
    SYNTAX      Counter64
    MAX-ACCESS  read-only
    STATUS      current
    DESCRIPTION
    "Number of GTPV1 packets sent with cause Mandatory IE Missing."
    ::= { jnxMbgPgwGtpPerPeerStatsEntry 250 }

jnxMbgPgwPPV1ICsOptIEIncrtRx   OBJECT-TYPE
    SYNTAX      Counter64
    MAX-ACCESS  read-only
    STATUS      current
    DESCRIPTION
    "Number of GTPV1 packets received with cause Optional IE incorrect."
    ::= { jnxMbgPgwGtpPerPeerStatsEntry 251 }

jnxMbgPgwPPV1ICsOptIEIncrtTx   OBJECT-TYPE
    SYNTAX      Counter64
    MAX-ACCESS  read-only
    STATUS      current
    DESCRIPTION
    "Number of GTPV1 packets sent with cause Optional IE incorrect."
    ::= { jnxMbgPgwGtpPerPeerStatsEntry 252 }

jnxMbgPgwPPV1ICsSysFailRx   OBJECT-TYPE
    SYNTAX      Counter64
    MAX-ACCESS  read-only
    STATUS      current
    DESCRIPTION
    "Number of GTPV1 packets received with cause System Failure."
    ::= { jnxMbgPgwGtpPerPeerStatsEntry 253 }

jnxMbgPgwPPV1ICsSysFailTx   OBJECT-TYPE
    SYNTAX      Counter64
    MAX-ACCESS  read-only
    STATUS      current
    DESCRIPTION
    "Number of GTPV1 packets sent with cause System Failure."
    ::= { jnxMbgPgwGtpPerPeerStatsEntry 254 }

jnxMbgPgwPPV1ICsRoamRestrictRx   OBJECT-TYPE
    SYNTAX      Counter64
    MAX-ACCESS  read-only
    STATUS      current
    DESCRIPTION
    "Number of GTPV1 packets received with cause Roaming Restricted."
    ::= { jnxMbgPgwGtpPerPeerStatsEntry 255 }

jnxMbgPgwPPV1ICsRoamRestrictTx   OBJECT-TYPE
    SYNTAX      Counter64
    MAX-ACCESS  read-only
    STATUS      current
    DESCRIPTION
    "Number of GTPV1 packets sent with cause Roaming Restricted."
    ::= { jnxMbgPgwGtpPerPeerStatsEntry 256 }

jnxMbgPgwPPV1ICsPTMSISigMMRx   OBJECT-TYPE
    SYNTAX      Counter64
    MAX-ACCESS  read-only
    STATUS      current
    DESCRIPTION
    "Number of GTPV1 packets received with cause PTMSI Signature Mismatch."
    ::= { jnxMbgPgwGtpPerPeerStatsEntry 257 }

jnxMbgPgwPPV1ICsPTMSISigMMTx   OBJECT-TYPE
    SYNTAX      Counter64
    MAX-ACCESS  read-only
    STATUS      current
    DESCRIPTION
    "Number of GTPV1 packets sent with cause PTMSI Signature Mismatch."
    ::= { jnxMbgPgwGtpPerPeerStatsEntry 258 }

jnxMbgPgwPPV1ICsGPRSConnSuppRx   OBJECT-TYPE
    SYNTAX      Counter64
    MAX-ACCESS  read-only
    STATUS      current
    DESCRIPTION
    "Number of GTPV1 packets received with cause GPRS Connection Supported."
    ::= { jnxMbgPgwGtpPerPeerStatsEntry 259 }

jnxMbgPgwPPV1ICsGPRSConnSuppTx   OBJECT-TYPE
    SYNTAX      Counter64
    MAX-ACCESS  read-only
    STATUS      current
    DESCRIPTION
    "Number of GTPV1 packets sent with cause GPRS Connection Supported."
    ::= { jnxMbgPgwGtpPerPeerStatsEntry 260 }

jnxMbgPgwPPV1ICsAuthFailRx   OBJECT-TYPE
    SYNTAX      Counter64
    MAX-ACCESS  read-only
    STATUS      current
    DESCRIPTION
    "Number of GTPV1 packets received with cause Auth Failure."
    ::= { jnxMbgPgwGtpPerPeerStatsEntry 261 }

jnxMbgPgwPPV1ICsAuthFailTx   OBJECT-TYPE
    SYNTAX      Counter64
    MAX-ACCESS  read-only
    STATUS      current
    DESCRIPTION
    "Number of GTPV1 packets sent with cause Auth Failure."
    ::= { jnxMbgPgwGtpPerPeerStatsEntry 262 }

jnxMbgPgwPPV1ICsUserAuthFailRx   OBJECT-TYPE
    SYNTAX      Counter64
    MAX-ACCESS  read-only
    STATUS      current
    DESCRIPTION
    "Number of GTPV1 packets received with cause User Auth Failure."
    ::= { jnxMbgPgwGtpPerPeerStatsEntry 263 }

jnxMbgPgwPPV1ICsUserAuthFailTx   OBJECT-TYPE
    SYNTAX      Counter64
    MAX-ACCESS  read-only
    STATUS      current
    DESCRIPTION
    "Number of GTPV1 packets sent with cause User Auth Failure."
    ::= { jnxMbgPgwGtpPerPeerStatsEntry 264 }

jnxMbgPgwPPV1ICsCtxNotFndRx   OBJECT-TYPE
    SYNTAX      Counter64
    MAX-ACCESS  read-only
    STATUS      current
    DESCRIPTION
    "Number of GTPV1 packets received with cause Context Not Found."
    ::= { jnxMbgPgwGtpPerPeerStatsEntry 265 }

jnxMbgPgwPPV1ICsCtxNotFndTx   OBJECT-TYPE
    SYNTAX      Counter64
    MAX-ACCESS  read-only
    STATUS      current
    DESCRIPTION
    "Number of GTPV1 packets sent with cause Context Not Found."
    ::= { jnxMbgPgwGtpPerPeerStatsEntry 266 }

jnxMbgPgwPPV1ICsAllDynPDPAdRx   OBJECT-TYPE
    SYNTAX      Counter64
    MAX-ACCESS  read-only
    STATUS      current
    DESCRIPTION
    "Number of GTPV1 packets received with cause Allow Dynamic PDP Address."
    ::= { jnxMbgPgwGtpPerPeerStatsEntry 267 }

jnxMbgPgwPPV1ICsAllDynPDPAdTx   OBJECT-TYPE
    SYNTAX      Counter64
    MAX-ACCESS  read-only
    STATUS      current
    DESCRIPTION
    "Number of GTPV1 packets sent with cause Allow Dynamic PDP Address."
    ::= { jnxMbgPgwGtpPerPeerStatsEntry 268 }

jnxMbgPgwPPV1ICsNoMemRx   OBJECT-TYPE
    SYNTAX      Counter64
    MAX-ACCESS  read-only
    STATUS      current
    DESCRIPTION
    "Number of GTPV1 packets received with cause No Memory."
    ::= { jnxMbgPgwGtpPerPeerStatsEntry 269 }

jnxMbgPgwPPV1ICsNoMemTx   OBJECT-TYPE
    SYNTAX      Counter64
    MAX-ACCESS  read-only
    STATUS      current
    DESCRIPTION
    "Number of GTPV1 packets sent with cause No Memory."
    ::= { jnxMbgPgwGtpPerPeerStatsEntry 270 }

jnxMbgPgwPPV1ICsRelocFailRx   OBJECT-TYPE
    SYNTAX      Counter64
    MAX-ACCESS  read-only
    STATUS      current
    DESCRIPTION
    "Number of GTPV1 packets received with cause Relocation Failed."
    ::= { jnxMbgPgwGtpPerPeerStatsEntry 271 }

jnxMbgPgwPPV1ICsRelocFailTx   OBJECT-TYPE
    SYNTAX      Counter64
    MAX-ACCESS  read-only
    STATUS      current
    DESCRIPTION
    "Number of GTPV1 packets sent with cause Relocation Failed."
    ::= { jnxMbgPgwGtpPerPeerStatsEntry 272 }

jnxMbgPgwPPV1ICsUnkManExhdrRx   OBJECT-TYPE
    SYNTAX      Counter64
    MAX-ACCESS  read-only
    STATUS      current
    DESCRIPTION
    "Number of GTPV1 packets received with cause Unknown Mandatory Extension Header."
    ::= { jnxMbgPgwGtpPerPeerStatsEntry 273 }

jnxMbgPgwPPV1ICsUnkManExhdrTx   OBJECT-TYPE
    SYNTAX      Counter64
    MAX-ACCESS  read-only
    STATUS      current
    DESCRIPTION
    "Number of GTPV1 packets sent with cause Unknown Mandatory Extension Header."
    ::= { jnxMbgPgwGtpPerPeerStatsEntry 274 }

jnxMbgPgwPPV1ICsSMANTTFTEr1Rx   OBJECT-TYPE
    SYNTAX      Counter64
    MAX-ACCESS  read-only
    STATUS      current
    DESCRIPTION
    "Number of GTPV1 packets received with cause Mandatory TFT Error."
    ::= { jnxMbgPgwGtpPerPeerStatsEntry 275 }

jnxMbgPgwPPV1ICsSMANTTFTEr1Tx   OBJECT-TYPE
    SYNTAX      Counter64
    MAX-ACCESS  read-only
    STATUS      current
    DESCRIPTION
    "Number of GTPV1 packets sent with cause Mandatory TFT Error."
    ::= { jnxMbgPgwGtpPerPeerStatsEntry 276 }

jnxMbgPgwPPV1ICsSYNTFTErr2Rx   OBJECT-TYPE
    SYNTAX      Counter64
    MAX-ACCESS  read-only
    STATUS      current
    DESCRIPTION
    "Number of GTPV1 packets received with cause Mandatory TFT Error."
    ::= { jnxMbgPgwGtpPerPeerStatsEntry 277 }

jnxMbgPgwPPV1ICsSYNTFTErr2Tx   OBJECT-TYPE
    SYNTAX      Counter64
    MAX-ACCESS  read-only
    STATUS      current
    DESCRIPTION
    "Number of GTPV1 packets sent with cause Mandatory TFT Error."
    ::= { jnxMbgPgwGtpPerPeerStatsEntry 278 }

jnxMbgPgwPPV1ICsSMNTPkFlEr1Rx   OBJECT-TYPE
    SYNTAX      Counter64
    MAX-ACCESS  read-only
    STATUS      current
    DESCRIPTION
    "Number of GTPV1 packets received with cause Mandatory Packet Filter Error."
    ::= { jnxMbgPgwGtpPerPeerStatsEntry 279 }

jnxMbgPgwPPV1ICsSMNTPkFlEr1Tx   OBJECT-TYPE
    SYNTAX      Counter64
    MAX-ACCESS  read-only
    STATUS      current
    DESCRIPTION
    "Number of GTPV1 packets sent with cause Mandatory Packet Filter Error."
    ::= { jnxMbgPgwGtpPerPeerStatsEntry 280 }

jnxMbgPgwPPV1ICsSYNPkFlErr2Rx   OBJECT-TYPE
    SYNTAX      Counter64
    MAX-ACCESS  read-only
    STATUS      current
    DESCRIPTION
    "Number of GTPV1 packets received with cause Mandatory Packet Filter Error."
    ::= { jnxMbgPgwGtpPerPeerStatsEntry 281 }

jnxMbgPgwPPV1ICsSYNPkFlErr2Tx   OBJECT-TYPE
    SYNTAX      Counter64
    MAX-ACCESS  read-only
    STATUS      current
    DESCRIPTION
    "Number of GTPV1 packets sent with cause Mandatory Packet Filter Error."
    ::= { jnxMbgPgwGtpPerPeerStatsEntry 282 }

jnxMbgPgwPPV1ICsMissUnknAPNRx   OBJECT-TYPE
    SYNTAX      Counter64
    MAX-ACCESS  read-only
    STATUS      current
    DESCRIPTION
    "Number of GTPV1 packets received with cause Unknowkn APN missing."
    ::= { jnxMbgPgwGtpPerPeerStatsEntry 283 }

jnxMbgPgwPPV1ICsMissUnknAPNTx   OBJECT-TYPE
    SYNTAX      Counter64
    MAX-ACCESS  read-only
    STATUS      current
    DESCRIPTION
    "Number of GTPV1 packets sent with cause Unknowkn APN missing."
    ::= { jnxMbgPgwGtpPerPeerStatsEntry 284 }

jnxMbgPgwPPV1ICsUnknPDPAdRx   OBJECT-TYPE
    SYNTAX      Counter64
    MAX-ACCESS  read-only
    STATUS      current
    DESCRIPTION
    "Number of GTPV1 packets received with cause Unknowkn PDP Address."
    ::= { jnxMbgPgwGtpPerPeerStatsEntry 285 }

jnxMbgPgwPPV1ICsUnknPDPAdTx   OBJECT-TYPE
    SYNTAX      Counter64
    MAX-ACCESS  read-only
    STATUS      current
    DESCRIPTION
    "Number of GTPV1 packets sent with cause Unknowkn PDP Address."
    ::= { jnxMbgPgwGtpPerPeerStatsEntry 286 }

jnxMbgPgwPPV1ICsNoTFTCtxExRx   OBJECT-TYPE
    SYNTAX      Counter64
    MAX-ACCESS  read-only
    STATUS      current
    DESCRIPTION
    "Number of GTPV1 packets received with cause No TFT Context Exists."
    ::= { jnxMbgPgwGtpPerPeerStatsEntry 287 }

jnxMbgPgwPPV1ICsNoTFTCtxExTx   OBJECT-TYPE
    SYNTAX      Counter64
    MAX-ACCESS  read-only
    STATUS      current
    DESCRIPTION
    "Number of GTPV1 packets sent with cause No TFT Context Exists."
    ::= { jnxMbgPgwGtpPerPeerStatsEntry 288 }

jnxMbgPgwPPV0ProtocolErrRx  OBJECT-TYPE
    SYNTAX      Counter64
    MAX-ACCESS  read-only
    STATUS      current
    DESCRIPTION
    "Number of GTPv0 Protocol Errors Received."
    ::= { jnxMbgPgwGtpPerPeerStatsEntry 289 }

jnxMbgPgwPPV0UnSupportedMsgRx  OBJECT-TYPE
    SYNTAX      Counter64
    MAX-ACCESS  read-only
    STATUS      current
    DESCRIPTION
    "Number of GTP V0 Unsupported Messages received."
    ::= { jnxMbgPgwGtpPerPeerStatsEntry 290 }

jnxMbgPgwPPV0T3RespTmrExpRx  OBJECT-TYPE
    SYNTAX      Counter64
    MAX-ACCESS  read-only
    STATUS      current
    DESCRIPTION
    "Number of GTP V0 T3 timer expiries Received."
    ::= { jnxMbgPgwGtpPerPeerStatsEntry 291 }

jnxMbgPgwPPV0GlbNumMsgRx  OBJECT-TYPE
    SYNTAX      Counter64
    MAX-ACCESS  read-only
    STATUS      current
    DESCRIPTION
    "Number of GTPv0 messages received."
    ::= { jnxMbgPgwGtpPerPeerStatsEntry 292 }

jnxMbgPgwPPV0GlbNumMsgTx  OBJECT-TYPE
    SYNTAX      Counter64
    MAX-ACCESS  read-only
    STATUS      current
    DESCRIPTION
    "Number of GTP V0 messages sent."
    ::= { jnxMbgPgwGtpPerPeerStatsEntry 293 }

jnxMbgPgwPPV0GlbNumBytesRx  OBJECT-TYPE
    SYNTAX      Counter64
    MAX-ACCESS  read-only
    STATUS      current
    DESCRIPTION
    "Number of GTP V0 bytes received."
    ::= { jnxMbgPgwGtpPerPeerStatsEntry 294 }

jnxMbgPgwPPV0GlbNumBytesTx  OBJECT-TYPE
    SYNTAX      Counter64
    MAX-ACCESS  read-only
    STATUS      current
    DESCRIPTION
    "Number of GTP V0 bytes sent."
    ::= { jnxMbgPgwGtpPerPeerStatsEntry 295 }

jnxMbgPgwPPV0GlbEchoReqRx  OBJECT-TYPE
    SYNTAX      Counter64
    MAX-ACCESS  read-only
    STATUS      current
    DESCRIPTION
   "Number of GTP V0 Echo Request received."
    ::= { jnxMbgPgwGtpPerPeerStatsEntry 296 }

jnxMbgPgwPPV0GlbEchoReqTx  OBJECT-TYPE
    SYNTAX      Counter64
    MAX-ACCESS  read-only
    STATUS      current
    DESCRIPTION
    "Number of GTP V0 Echo Request Sent."
    ::= { jnxMbgPgwGtpPerPeerStatsEntry 297 }

jnxMbgPgwPPV0GlbEchoRespRx  OBJECT-TYPE
    SYNTAX      Counter64
    MAX-ACCESS  read-only
    STATUS      current
    DESCRIPTION
    "Number of GTP V0 Echo Response received."
    ::= { jnxMbgPgwGtpPerPeerStatsEntry 298 }

jnxMbgPgwPPV0GlbEchoRespTx  OBJECT-TYPE
    SYNTAX      Counter64
    MAX-ACCESS  read-only
    STATUS      current
    DESCRIPTION
    "Number of GTP V0 Echo Response Sent."
    ::= { jnxMbgPgwGtpPerPeerStatsEntry 299 }

jnxMbgPgwPPV0GlbVerNotSupRx OBJECT-TYPE
    SYNTAX      Counter64
    MAX-ACCESS  read-only
    STATUS      current
    DESCRIPTION
    "Number of GTP V0 Version Not supported messages received"
    ::= { jnxMbgPgwGtpPerPeerStatsEntry 300 }

jnxMbgPgwPPV0GlbVerNotSupTx OBJECT-TYPE
    SYNTAX      Counter64
    MAX-ACCESS  read-only
    STATUS      current
    DESCRIPTION
    "Number of GTP V0 Number of version not supported messages sent."
    ::= { jnxMbgPgwGtpPerPeerStatsEntry 301 }

jnxMbgPgwPPV0GlbCrtPdpCxtReqRx   OBJECT-TYPE
    SYNTAX      Counter64
    MAX-ACCESS  read-only
    STATUS      current
    DESCRIPTION
    "Number of GTP V0 Create PDP Context Requests Received."
    ::= { jnxMbgPgwGtpPerPeerStatsEntry 302 }

jnxMbgPgwPPV0GlbCrtPdpCxtReqTx   OBJECT-TYPE
    SYNTAX      Counter64
    MAX-ACCESS  read-only
    STATUS      current
    DESCRIPTION
    "Number of GTP V0 Create PDP Context Requests Sent."
    ::= { jnxMbgPgwGtpPerPeerStatsEntry 303 }

jnxMbgPgwPPV0GlbCrtPdpCxtRspRx   OBJECT-TYPE
    SYNTAX      Counter64
    MAX-ACCESS  read-only
    STATUS      current
    DESCRIPTION
    "Number of GTP V0 Create PDP Context Responses Received."
    ::= { jnxMbgPgwGtpPerPeerStatsEntry 304 }

jnxMbgPgwPPV0GlbCrtPdpCxtRspTx   OBJECT-TYPE
    SYNTAX      Counter64
    MAX-ACCESS  read-only
    STATUS      current
    DESCRIPTION
    "Number of GTP V0 Create PDP Context Responses Sent."
    ::= { jnxMbgPgwGtpPerPeerStatsEntry 305 }

jnxMbgPgwPPV0GlbUpdPdpCxtReqRx   OBJECT-TYPE
    SYNTAX      Counter64
    MAX-ACCESS  read-only
    STATUS      current
    DESCRIPTION
    "Number of GTP V0 Update PDP Context Requests Received."
    ::= { jnxMbgPgwGtpPerPeerStatsEntry 306 }

jnxMbgPgwPPV0GlbUpdPdpCxtReqTx   OBJECT-TYPE
    SYNTAX      Counter64
    MAX-ACCESS  read-only
    STATUS      current
    DESCRIPTION
    "Number of GTP V0 Update PDP Context Requests Sent."
    ::= { jnxMbgPgwGtpPerPeerStatsEntry 307 }

jnxMbgPgwPPV0GlbUpdPdpCxtRspRx   OBJECT-TYPE
    SYNTAX      Counter64
    MAX-ACCESS  read-only
    STATUS      current
    DESCRIPTION
    "Number of GTP V0 Update PDP Context Responses Received."
    ::= { jnxMbgPgwGtpPerPeerStatsEntry 308 }

jnxMbgPgwPPV0GlbUpdPdpCxtRspTx   OBJECT-TYPE
    SYNTAX      Counter64
    MAX-ACCESS  read-only
    STATUS      current
    DESCRIPTION
    "Number of GTP V0 Update PDP Context Responses Sent."
    ::= { jnxMbgPgwGtpPerPeerStatsEntry 309 }

jnxMbgPgwPPV0GlbDelPdpCxtReqRx   OBJECT-TYPE
    SYNTAX      Counter64
    MAX-ACCESS  read-only
    STATUS      current
    DESCRIPTION
    "Number of GTP V0 Delete PDP Context Requests Received."
    ::= { jnxMbgPgwGtpPerPeerStatsEntry 310 }

jnxMbgPgwPPV0GlbDelPdpCxtReqTx   OBJECT-TYPE
    SYNTAX      Counter64
    MAX-ACCESS  read-only
    STATUS      current
    DESCRIPTION
    "Number of GTP V0 Delete PDP Context Requests Sent."
    ::= { jnxMbgPgwGtpPerPeerStatsEntry 311 }

jnxMbgPgwPPV0GlbDelPdpCxtRspRx   OBJECT-TYPE
    SYNTAX      Counter64
    MAX-ACCESS  read-only
    STATUS      current
    DESCRIPTION
    "Number of GTP V0 Delete PDP Context Responses Received."
    ::= { jnxMbgPgwGtpPerPeerStatsEntry 312 }

jnxMbgPgwPPV0GlbDelPdpCxtRspTx   OBJECT-TYPE
    SYNTAX      Counter64
    MAX-ACCESS  read-only
    STATUS      current
    DESCRIPTION
    "Number of GTP V0 Delete PDP Context Responses Sent."
    ::= { jnxMbgPgwGtpPerPeerStatsEntry 313 }

jnxMbgPgwPPV0GlbCrAAPdpCxtReqRx   OBJECT-TYPE
    SYNTAX      Counter64
    MAX-ACCESS  read-only
    STATUS      current
    DESCRIPTION
    "Number of GTP V0 Create AA PDP Context Requests Received."
    ::= { jnxMbgPgwGtpPerPeerStatsEntry 314 }

jnxMbgPgwPPV0GlbCrAAPdpCxtReqTx   OBJECT-TYPE
    SYNTAX      Counter64
    MAX-ACCESS  read-only
    STATUS      current
    DESCRIPTION
    "Number of GTP V0 Create AA PDP Context Requests Sent."
    ::= { jnxMbgPgwGtpPerPeerStatsEntry 315 }

jnxMbgPgwPPV0GlbCrAAPdpCxtRspRx   OBJECT-TYPE
    SYNTAX      Counter64
    MAX-ACCESS  read-only
    STATUS      current
    DESCRIPTION
    "Number of GTP V0 Create AA PDP Context Responses Received."
    ::= { jnxMbgPgwGtpPerPeerStatsEntry 316 }

jnxMbgPgwPPV0GlbCrAAPdpCxtRspTx   OBJECT-TYPE
    SYNTAX      Counter64
    MAX-ACCESS  read-only
    STATUS      current
    DESCRIPTION
    "Number of GTP V0 Create AA PDP Context Responses Sent."
    ::= { jnxMbgPgwGtpPerPeerStatsEntry 317 }

jnxMbgPgwPPV0GlbDlAAPdpCxtReqRx   OBJECT-TYPE
    SYNTAX      Counter64
    MAX-ACCESS  read-only
    STATUS      current
    DESCRIPTION
    "Number of GTP V0 Delete AA PDP Context Requests Received."
    ::= { jnxMbgPgwGtpPerPeerStatsEntry 318 }

jnxMbgPgwPPV0GlbDlAAPdpCxtReqTx   OBJECT-TYPE
    SYNTAX      Counter64
    MAX-ACCESS  read-only
    STATUS      current
    DESCRIPTION
    "Number of GTP V0 Delete AA PDP Context Requests Sent."
    ::= { jnxMbgPgwGtpPerPeerStatsEntry 319 }

jnxMbgPgwPPV0GlbDlAAPdpCxtRspRx   OBJECT-TYPE
    SYNTAX      Counter64
    MAX-ACCESS  read-only
    STATUS      current
    DESCRIPTION
    "Number of GTP V0 Delete AA PDP Context Responses Received."
    ::= { jnxMbgPgwGtpPerPeerStatsEntry 320 }

jnxMbgPgwPPV0GlbDlAAPdpCxtRspTx   OBJECT-TYPE
    SYNTAX      Counter64
    MAX-ACCESS  read-only
    STATUS      current
    DESCRIPTION
    "Number of GTP V0 Delete AA PDP Context Responses Sent."
    ::= { jnxMbgPgwGtpPerPeerStatsEntry 321 }

jnxMbgPgwPPV0GlbErrorIndRx   OBJECT-TYPE
    SYNTAX      Counter64
    MAX-ACCESS  read-only
    STATUS      current
    DESCRIPTION
    "Number of GTP V0 Error Indication Received."
    ::= { jnxMbgPgwGtpPerPeerStatsEntry 322 }

jnxMbgPgwPPV0GlbErrorIndTx   OBJECT-TYPE
    SYNTAX      Counter64
    MAX-ACCESS  read-only
    STATUS      current
    DESCRIPTION
    "Number of GTP V0 Error Indication Sent."
    ::= { jnxMbgPgwGtpPerPeerStatsEntry 323 }

jnxMbgPgwPPV0GlbNotifReqRx   OBJECT-TYPE
    SYNTAX      Counter64
    MAX-ACCESS  read-only
    STATUS      current
    DESCRIPTION
    "Number of GTP V0 Notify Requests Received."
    ::= { jnxMbgPgwGtpPerPeerStatsEntry 324 }

jnxMbgPgwPPV0GlbNotifReqTx   OBJECT-TYPE
    SYNTAX      Counter64
    MAX-ACCESS  read-only
    STATUS      current
    DESCRIPTION
    "Number of GTP V0 Notify Requests Sent."
    ::= { jnxMbgPgwGtpPerPeerStatsEntry 325 }

jnxMbgPgwPPV0GlbNotifRspRx   OBJECT-TYPE
    SYNTAX      Counter64
    MAX-ACCESS  read-only
    STATUS      current
    DESCRIPTION
    "Number of GTP V0 Notify Responses Received."
    ::= { jnxMbgPgwGtpPerPeerStatsEntry 326 }

jnxMbgPgwPPV0GlbNotifRspTx   OBJECT-TYPE
    SYNTAX      Counter64
    MAX-ACCESS  read-only
    STATUS      current
    DESCRIPTION
    "Number of GTP V0 Notify Responses Sent."
    ::= { jnxMbgPgwGtpPerPeerStatsEntry 327 }

jnxMbgPgwPPV0GlbNotifRejReqRx   OBJECT-TYPE
    SYNTAX      Counter64
    MAX-ACCESS  read-only
    STATUS      current
    DESCRIPTION
    "Number of GTP V0 Notify Reject Requests Received."
    ::= { jnxMbgPgwGtpPerPeerStatsEntry 328 }

jnxMbgPgwPPV0GlbNotifRejReqTx   OBJECT-TYPE
    SYNTAX      Counter64
    MAX-ACCESS  read-only
    STATUS      current
    DESCRIPTION
    "Number of GTP V0 Notify Reject Requests Sent."
    ::= { jnxMbgPgwGtpPerPeerStatsEntry 329 }

jnxMbgPgwPPV0GlbNotifRejRspRx   OBJECT-TYPE
    SYNTAX      Counter64
    MAX-ACCESS  read-only
    STATUS      current
    DESCRIPTION
    "Number of GTP V0 Notify Reject Responses Received."
    ::= { jnxMbgPgwGtpPerPeerStatsEntry 330 }

jnxMbgPgwPPV0GlbNotifRejRspTx   OBJECT-TYPE
    SYNTAX      Counter64
    MAX-ACCESS  read-only
    STATUS      current
    DESCRIPTION
    "Number of GTP V0 Notify Reject Responses Sent."
    ::= { jnxMbgPgwGtpPerPeerStatsEntry 331 }

jnxMbgPgwPPV0GlbRtInfReqRx   OBJECT-TYPE
    SYNTAX      Counter64
    MAX-ACCESS  read-only
    STATUS      current
    DESCRIPTION
    "Number of GTP V0 Routing Information Requests Received."
    ::= { jnxMbgPgwGtpPerPeerStatsEntry 332 }

jnxMbgPgwPPV0GlbRtInfReqTx   OBJECT-TYPE
    SYNTAX      Counter64
    MAX-ACCESS  read-only
    STATUS      current
    DESCRIPTION
    "Number of GTP V0 Routing Information Requests Sent."
    ::= { jnxMbgPgwGtpPerPeerStatsEntry 333 }

jnxMbgPgwPPV0GlbRtInfRspRx   OBJECT-TYPE
    SYNTAX      Counter64
    MAX-ACCESS  read-only
    STATUS      current
    DESCRIPTION
    "Number of GTP V0 Routing Information Responses Received."
    ::= { jnxMbgPgwGtpPerPeerStatsEntry 334 }

jnxMbgPgwPPV0GlbRtInfRspTx   OBJECT-TYPE
    SYNTAX      Counter64
    MAX-ACCESS  read-only
    STATUS      current
    DESCRIPTION
    "Number of GTP V0 Routing Information Responses Sent."
    ::= { jnxMbgPgwGtpPerPeerStatsEntry 335 }

jnxMbgPgwPPV0GlbFailRptReqRx   OBJECT-TYPE
    SYNTAX      Counter64
    MAX-ACCESS  read-only
    STATUS      current
    DESCRIPTION
    "Number of GTP V0 Fail Repeat Requests Received."
    ::= { jnxMbgPgwGtpPerPeerStatsEntry 336 }

jnxMbgPgwPPV0GlbFailRptReqTx   OBJECT-TYPE
    SYNTAX      Counter64
    MAX-ACCESS  read-only
    STATUS      current
    DESCRIPTION
    "Number of GTP V0 Fail Repeat Requests Sent."
    ::= { jnxMbgPgwGtpPerPeerStatsEntry 337 }

jnxMbgPgwPPV0GlbFailRptRspRx   OBJECT-TYPE
    SYNTAX      Counter64
    MAX-ACCESS  read-only
    STATUS      current
    DESCRIPTION
    "Number of GTP V0 Fail Repeat Responses Received."
    ::= { jnxMbgPgwGtpPerPeerStatsEntry 338 }

jnxMbgPgwPPV0GlbFailRptRspTx   OBJECT-TYPE
    SYNTAX      Counter64
    MAX-ACCESS  read-only
    STATUS      current
    DESCRIPTION
    "Number of GTP V0 Fail Repeat Responses Sent."
    ::= { jnxMbgPgwGtpPerPeerStatsEntry 339 }

jnxMbgPgwPPV0GlbNotMSPresReqRx   OBJECT-TYPE
    SYNTAX      Counter64
    MAX-ACCESS  read-only
    STATUS      current
    DESCRIPTION
    "Number of GTP V0 MS Not Present Request Received."
    ::= { jnxMbgPgwGtpPerPeerStatsEntry 340 }

jnxMbgPgwPPV0GlbNotMSPresReqTx   OBJECT-TYPE
    SYNTAX      Counter64
    MAX-ACCESS  read-only
    STATUS      current
    DESCRIPTION
    "Number of GTP V0 MS Not Present Request Sent."
    ::= { jnxMbgPgwGtpPerPeerStatsEntry 341 }

jnxMbgPgwPPV0GlbNotMSPresRspRx   OBJECT-TYPE
    SYNTAX      Counter64
    MAX-ACCESS  read-only
    STATUS      current
    DESCRIPTION
    "Number of GTP V0 MS Not Present Responses Received."
    ::= { jnxMbgPgwGtpPerPeerStatsEntry 342 }

jnxMbgPgwPPV0GlbNotMSPresRspTx   OBJECT-TYPE
    SYNTAX      Counter64
    MAX-ACCESS  read-only
    STATUS      current
    DESCRIPTION
    "Number of GTP V0 MS Not Present Responses Sent."
    ::= { jnxMbgPgwGtpPerPeerStatsEntry 343 }

jnxMbgPgwPPV0ICsReqAcceptedRx   OBJECT-TYPE
    SYNTAX      Counter64
    MAX-ACCESS  read-only
    STATUS      current
    DESCRIPTION
    "Number of GTPV0 packets received with cause Request Accepted."
    ::= { jnxMbgPgwGtpPerPeerStatsEntry 344 }

jnxMbgPgwPPV0ICsReqAcceptedTx   OBJECT-TYPE
    SYNTAX      Counter64
    MAX-ACCESS  read-only
    STATUS      current
    DESCRIPTION
    "Number of GTPV0 packets sent with cause Request Accepted."
    ::= { jnxMbgPgwGtpPerPeerStatsEntry 345 }

jnxMbgPgwPPV0ICsNonExistRx   OBJECT-TYPE
    SYNTAX      Counter64
    MAX-ACCESS  read-only
    STATUS      current
    DESCRIPTION
    "Number of GTPV0 packets received with cause Non Existant."
    ::= { jnxMbgPgwGtpPerPeerStatsEntry 346 }

jnxMbgPgwPPV0ICsNonExistTx   OBJECT-TYPE
    SYNTAX      Counter64
    MAX-ACCESS  read-only
    STATUS      current
    DESCRIPTION
    "Number of GTPV0 packets sent with cause Non Existant."
    ::= { jnxMbgPgwGtpPerPeerStatsEntry 347 }

jnxMbgPgwPPV0ICsInvMsgFmtRx   OBJECT-TYPE
    SYNTAX      Counter64
    MAX-ACCESS  read-only
    STATUS      current
    DESCRIPTION
    "Number of GTPV0 packets received with cause Invalid Mesage Format."
    ::= { jnxMbgPgwGtpPerPeerStatsEntry 348 }

jnxMbgPgwPPV0ICsInvMsgFmtTx   OBJECT-TYPE
    SYNTAX      Counter64
    MAX-ACCESS  read-only
    STATUS      current
    DESCRIPTION
    "Number of GTPV0 packets sent with cause Invalid Mesage Format."
    ::= { jnxMbgPgwGtpPerPeerStatsEntry 349 }

jnxMbgPgwPPV0ICsIMSINotKnownRx   OBJECT-TYPE
    SYNTAX      Counter64
    MAX-ACCESS  read-only
    STATUS      current
    DESCRIPTION
    "Number of GTPV0 packets received with cause IMSI Not Known."
    ::= { jnxMbgPgwGtpPerPeerStatsEntry 350 }


jnxMbgPgwPPV0ICsIMSINotKnownTx   OBJECT-TYPE
    SYNTAX      Counter64
    MAX-ACCESS  read-only
    STATUS      current
    DESCRIPTION
    "Number of GTPV0 packets sent with cause IMSI Not Known."
    ::= { jnxMbgPgwGtpPerPeerStatsEntry 351 }

jnxMbgPgwPPV0ICsMSGRPSDetachRx   OBJECT-TYPE
    SYNTAX      Counter64
    MAX-ACCESS  read-only
    STATUS      current
    DESCRIPTION
    "Number of GTPV0 packets received with cause MS GPRS Detached."
    ::= { jnxMbgPgwGtpPerPeerStatsEntry 352 }

jnxMbgPgwPPV0ICsMSGRPSDetachTx   OBJECT-TYPE
    SYNTAX      Counter64
    MAX-ACCESS  read-only
    STATUS      current
    DESCRIPTION
    "Number of GTPV0 packets sent with cause MS GPRS Detached."
    ::= { jnxMbgPgwGtpPerPeerStatsEntry 353 }

jnxMbgPgwPPV0ICsMSNotGRPSRespRx   OBJECT-TYPE
    SYNTAX      Counter64
    MAX-ACCESS  read-only
    STATUS      current
    DESCRIPTION
    "Number of GTPV0 packets received with cause MS No GPRS Response."
    ::= { jnxMbgPgwGtpPerPeerStatsEntry 354 }

jnxMbgPgwPPV0ICsMSNotGRPSRespTx   OBJECT-TYPE
    SYNTAX      Counter64
    MAX-ACCESS  read-only
    STATUS      current
    DESCRIPTION
    "Number of GTPV0 packets sent with cause MS No GPRS Response."
    ::= { jnxMbgPgwGtpPerPeerStatsEntry 355 }

jnxMbgPgwPPV0ICsMSRefusesRx   OBJECT-TYPE
    SYNTAX      Counter64
    MAX-ACCESS  read-only
    STATUS      current
    DESCRIPTION
    "Number of GTPV0 packets received with cause MS Refues."
    ::= { jnxMbgPgwGtpPerPeerStatsEntry 356 }

jnxMbgPgwPPV0ICsMSRefusesTx   OBJECT-TYPE
    SYNTAX      Counter64
    MAX-ACCESS  read-only
    STATUS      current
    DESCRIPTION
    "Number of GTPV0 packets sent with cause MS Refues."
    ::= { jnxMbgPgwGtpPerPeerStatsEntry 357 }

jnxMbgPgwPPV0ICsVerNotSuppRx   OBJECT-TYPE
    SYNTAX      Counter64
    MAX-ACCESS  read-only
    STATUS      current
    DESCRIPTION
    "Number of GTPV0 packets received with cause Version Not Supported."
    ::= { jnxMbgPgwGtpPerPeerStatsEntry 358 }

jnxMbgPgwPPV0ICsVerNotSuppTx   OBJECT-TYPE
    SYNTAX      Counter64
    MAX-ACCESS  read-only
    STATUS      current
    DESCRIPTION
    "Number of GTPV0 packets sent with cause Version Not Supported."
    ::= { jnxMbgPgwGtpPerPeerStatsEntry 359 }

jnxMbgPgwPPV0ICsNoResRx   OBJECT-TYPE
    SYNTAX      Counter64
    MAX-ACCESS  read-only
    STATUS      current
    DESCRIPTION
    "Number of GTPV0 packets received with cause No Response."
    ::= { jnxMbgPgwGtpPerPeerStatsEntry 360 }

jnxMbgPgwPPV0ICsNoResTx   OBJECT-TYPE
    SYNTAX      Counter64
    MAX-ACCESS  read-only
    STATUS      current
    DESCRIPTION
    "Number of GTPV0 packets sent with cause No Response."
    ::= { jnxMbgPgwGtpPerPeerStatsEntry 361 }

jnxMbgPgwPPV0ICsServNotSuppRx   OBJECT-TYPE
    SYNTAX      Counter64
    MAX-ACCESS  read-only
    STATUS      current
    DESCRIPTION
    "Number of GTPV0 packets received with cause Service Not Supported."
    ::= { jnxMbgPgwGtpPerPeerStatsEntry 362 }

jnxMbgPgwPPV0ICsServNotSuppTx   OBJECT-TYPE
    SYNTAX      Counter64
    MAX-ACCESS  read-only
    STATUS      current
    DESCRIPTION
    "Number of GTPV0 packets sent with cause Service Not Supported."
    ::= { jnxMbgPgwGtpPerPeerStatsEntry 363 }

jnxMbgPgwPPV0ICsManIEIncrtRx   OBJECT-TYPE
    SYNTAX      Counter64
    MAX-ACCESS  read-only
    STATUS      current
    DESCRIPTION
    "Number of GTPV0 packets received with cause Mandatory IE incorrect."
    ::= { jnxMbgPgwGtpPerPeerStatsEntry 364 }

jnxMbgPgwPPV0ICsManIEIncrtTx   OBJECT-TYPE
    SYNTAX      Counter64
    MAX-ACCESS  read-only
    STATUS      current
    DESCRIPTION
    "Number of GTPV0 packets sent with cause Mandatory IE incorrect."
    ::= { jnxMbgPgwGtpPerPeerStatsEntry 365 }

jnxMbgPgwPPV0ICsManIEMissRx   OBJECT-TYPE
    SYNTAX      Counter64
    MAX-ACCESS  read-only
    STATUS      current
    DESCRIPTION
    "Number of GTPV0 packets received with cause Mandatory IE Missing."
    ::= { jnxMbgPgwGtpPerPeerStatsEntry 366 }

jnxMbgPgwPPV0ICsManIEMissTx   OBJECT-TYPE
    SYNTAX      Counter64
    MAX-ACCESS  read-only
    STATUS      current
    DESCRIPTION
    "Number of GTPV0 packets sent with cause Mandatory IE Missing."
    ::= { jnxMbgPgwGtpPerPeerStatsEntry 367 }

jnxMbgPgwPPV0ICsOptIEIncrtRx   OBJECT-TYPE
    SYNTAX      Counter64
    MAX-ACCESS  read-only
    STATUS      current
    DESCRIPTION
    "Number of GTPV0 packets received with cause Optional IE incorrect."
    ::= { jnxMbgPgwGtpPerPeerStatsEntry 368 }

jnxMbgPgwPPV0ICsOptIEIncrtTx   OBJECT-TYPE
    SYNTAX      Counter64
    MAX-ACCESS  read-only
    STATUS      current
    DESCRIPTION
    "Number of GTPV0 packets sent with cause Optional IE incorrect."
    ::= { jnxMbgPgwGtpPerPeerStatsEntry 369 }

jnxMbgPgwPPV0ICsSysFailRx   OBJECT-TYPE
    SYNTAX      Counter64
    MAX-ACCESS  read-only
    STATUS      current
    DESCRIPTION
    "Number of GTPV0 packets received with cause System Failure."
    ::= { jnxMbgPgwGtpPerPeerStatsEntry 370 }

jnxMbgPgwPPV0ICsSysFailTx   OBJECT-TYPE
    SYNTAX      Counter64
    MAX-ACCESS  read-only
    STATUS      current
    DESCRIPTION
    "Number of GTPV0 packets sent with cause System Failure."
    ::= { jnxMbgPgwGtpPerPeerStatsEntry 371 }

jnxMbgPgwPPV0ICsRoamRestrictRx   OBJECT-TYPE
    SYNTAX      Counter64
    MAX-ACCESS  read-only
    STATUS      current
    DESCRIPTION
    "Number of GTPV0 packets received with cause Roaming Restricted."
    ::= { jnxMbgPgwGtpPerPeerStatsEntry 372 }

jnxMbgPgwPPV0ICsRoamRestrictTx   OBJECT-TYPE
    SYNTAX      Counter64
    MAX-ACCESS  read-only
    STATUS      current
    DESCRIPTION
    "Number of GTPV0 packets sent with cause Roaming Restricted."
    ::= { jnxMbgPgwGtpPerPeerStatsEntry 373 }

jnxMbgPgwPPV0ICsPTMSISigMMRx   OBJECT-TYPE
    SYNTAX      Counter64
    MAX-ACCESS  read-only
    STATUS      current
    DESCRIPTION
    "Number of GTPV0 packets received with cause PTMSI Signature Mismatch."
    ::= { jnxMbgPgwGtpPerPeerStatsEntry 374 }

jnxMbgPgwPPV0ICsPTMSISigMMTx   OBJECT-TYPE
    SYNTAX      Counter64
    MAX-ACCESS  read-only
    STATUS      current
    DESCRIPTION
    "Number of GTPV0 packets sent with cause PTMSI Signature Mismatch."
    ::= { jnxMbgPgwGtpPerPeerStatsEntry 375 }

jnxMbgPgwPPV0ICsGPRSConnSuppRx   OBJECT-TYPE
    SYNTAX      Counter64
    MAX-ACCESS  read-only
    STATUS      current
    DESCRIPTION
    "Number of GTPV0 packets received with cause GPRS Connection Supported."
    ::= { jnxMbgPgwGtpPerPeerStatsEntry 376 }

jnxMbgPgwPPV0ICsGPRSConnSuppTx   OBJECT-TYPE
    SYNTAX      Counter64
    MAX-ACCESS  read-only
    STATUS      current
    DESCRIPTION
    "Number of GTPV0 packets sent with cause GPRS Connection Supported."
    ::= { jnxMbgPgwGtpPerPeerStatsEntry 377 }

jnxMbgPgwPPV0ICsAuthFailRx   OBJECT-TYPE
    SYNTAX      Counter64
    MAX-ACCESS  read-only
    STATUS      current
    DESCRIPTION
    "Number of GTPV0 packets received with cause Auth Failure."
    ::= { jnxMbgPgwGtpPerPeerStatsEntry 378 }

jnxMbgPgwPPV0ICsAuthFailTx   OBJECT-TYPE
    SYNTAX      Counter64
    MAX-ACCESS  read-only
    STATUS      current
    DESCRIPTION
    "Number of GTPV0 packets sent with cause Auth Failure."
    ::= { jnxMbgPgwGtpPerPeerStatsEntry 379 }

jnxMbgPgwPPV0ICsUserAuthFailRx   OBJECT-TYPE
    SYNTAX      Counter64
    MAX-ACCESS  read-only
    STATUS      current
    DESCRIPTION
    "Number of GTPV0 packets received with cause User Auth Failure."
    ::= { jnxMbgPgwGtpPerPeerStatsEntry 380 }

jnxMbgPgwPPV0ICsUserAuthFailTx   OBJECT-TYPE
    SYNTAX      Counter64
    MAX-ACCESS  read-only
    STATUS      current
    DESCRIPTION
    "Number of GTPV0 packets sent with cause User Auth Failure."
    ::= { jnxMbgPgwGtpPerPeerStatsEntry 381 }

jnxMbgPgwPPGtpV2ICsLclDetRx OBJECT-TYPE
         SYNTAX      Counter64
         MAX-ACCESS  read-only
         STATUS      current
         DESCRIPTION
         "Number of GTP packets received with cause Local Detach."
     ::= { jnxMbgPgwGtpPerPeerStatsEntry 382 }

jnxMbgPgwPPGtpV2ICsLclDetTx OBJECT-TYPE
         SYNTAX      Counter64
         MAX-ACCESS  read-only
         STATUS      current
         DESCRIPTION
         "Number of GTP packets sent with cause Local Detach."
     ::= { jnxMbgPgwGtpPerPeerStatsEntry 383 }

jnxMbgPgwPPGtpV2ICsCmpDetRx OBJECT-TYPE
         SYNTAX      Counter64
         MAX-ACCESS  read-only
         STATUS      current
         DESCRIPTION
         "Number of GTP packets received with cause Complete Detach."
     ::= { jnxMbgPgwGtpPerPeerStatsEntry 384 }

jnxMbgPgwPPGtpV2ICsCmpDetTx OBJECT-TYPE
         SYNTAX      Counter64
         MAX-ACCESS  read-only
         STATUS      current
         DESCRIPTION
         "Number of GTP packets sent with cause Complete Detach."
     ::= { jnxMbgPgwGtpPerPeerStatsEntry 385 }

jnxMbgPgwPPGtpV2ICsRATChgRx OBJECT-TYPE
         SYNTAX      Counter64
         MAX-ACCESS  read-only
         STATUS      current
         DESCRIPTION
         "Number of GTP packets received with cause RAT changed from 3GPP to non 3GPP."
     ::= { jnxMbgPgwGtpPerPeerStatsEntry 386 }

jnxMbgPgwPPGtpV2ICsRATChgTx OBJECT-TYPE
         SYNTAX      Counter64
         MAX-ACCESS  read-only
         STATUS      current
         DESCRIPTION
         "Number of GTP packets sent with cause RAT changed from 3GPP to non 3GPP."
     ::= { jnxMbgPgwGtpPerPeerStatsEntry 387 }

jnxMbgPgwPPGtpV2ICsISRDeactRx OBJECT-TYPE
         SYNTAX      Counter64
         MAX-ACCESS  read-only
         STATUS      current
         DESCRIPTION
         "Number of GTP packets received with cause ISR Deactivated."
     ::= { jnxMbgPgwGtpPerPeerStatsEntry 388 }

jnxMbgPgwPPGtpV2ICsISRDeactTx OBJECT-TYPE
         SYNTAX      Counter64
         MAX-ACCESS  read-only
         STATUS      current
         DESCRIPTION
         "Number of GTP packets sent with cause ISR Deactivated."
     ::= { jnxMbgPgwGtpPerPeerStatsEntry 389 }

jnxMbgPgwPPGtpV2ICsEIFRNCEnRx OBJECT-TYPE
         SYNTAX      Counter64
         MAX-ACCESS  read-only
         STATUS      current
         DESCRIPTION
         "Number of GTP packets received with cause Error Indication from RNC eNodeB."
     ::= { jnxMbgPgwGtpPerPeerStatsEntry 390 }

jnxMbgPgwPPGtpV2ICsEIFRNCEnTx OBJECT-TYPE
         SYNTAX      Counter64
         MAX-ACCESS  read-only
         STATUS      current
         DESCRIPTION
         "Number of GTP packets sent with cause Error Indication from RNC eNodeB."
     ::= { jnxMbgPgwGtpPerPeerStatsEntry 391 }

jnxMbgPgwPPGtpV2ICsSemErTADRx OBJECT-TYPE
         SYNTAX      Counter64
         MAX-ACCESS  read-only
         STATUS      current
         DESCRIPTION
         "Number of GTP packets received with cause Semantic Error in TAD Operation."
     ::= { jnxMbgPgwGtpPerPeerStatsEntry 392 }

jnxMbgPgwPPGtpV2ICsSemErTADTx OBJECT-TYPE
         SYNTAX      Counter64
         MAX-ACCESS  read-only
         STATUS      current
         DESCRIPTION
         "Number of GTP packets sent with cause Semantic Error in TAD Operation."
     ::= { jnxMbgPgwGtpPerPeerStatsEntry 393 }

jnxMbgPgwPPGtpV2ICsSynErTADRx OBJECT-TYPE
         SYNTAX      Counter64
         MAX-ACCESS  read-only
         STATUS      current
         DESCRIPTION
         "Number of GTP packets received with cause Syntactic Error in TAD Operation."
     ::= { jnxMbgPgwGtpPerPeerStatsEntry 394 }

jnxMbgPgwPPGtpV2ICsSynErTADTx OBJECT-TYPE
         SYNTAX      Counter64
         MAX-ACCESS  read-only
         STATUS      current
         DESCRIPTION
         "Number of GTP packets sent with cause Syntactic Error in TAD Operation."
     ::= { jnxMbgPgwGtpPerPeerStatsEntry 395 }

jnxMbgPgwPPGtpV2ICsRMValRcvRx OBJECT-TYPE
         SYNTAX      Counter64
         MAX-ACCESS  read-only
         STATUS      current
         DESCRIPTION
         "Number of GTP packets received with cause Reserved Message Value Received."
     ::= { jnxMbgPgwGtpPerPeerStatsEntry 396 }

jnxMbgPgwPPGtpV2ICsRMValRcvTx OBJECT-TYPE
         SYNTAX      Counter64
         MAX-ACCESS  read-only
         STATUS      current
         DESCRIPTION
         "Number of GTP packets sent with cause Reserved Message Value Received."
     ::= { jnxMbgPgwGtpPerPeerStatsEntry 397 }

jnxMbgPgwPPGtpV2ICsRPrNtRspRx OBJECT-TYPE
         SYNTAX      Counter64
         MAX-ACCESS  read-only
         STATUS      current
         DESCRIPTION
         "Number of GTP packets received with cause Remote peer not responding."
     ::= { jnxMbgPgwGtpPerPeerStatsEntry 398 }

jnxMbgPgwPPGtpV2ICsRPrNtRspTx OBJECT-TYPE
         SYNTAX      Counter64
         MAX-ACCESS  read-only
         STATUS      current
         DESCRIPTION
         "Number of GTP packets sent with cause Remote peer not responding."
     ::= { jnxMbgPgwGtpPerPeerStatsEntry 399 }

jnxMbgPgwPPGtpV2ICsColNWReqRx OBJECT-TYPE
         SYNTAX      Counter64
         MAX-ACCESS  read-only
         STATUS      current
         DESCRIPTION
         "Number of GTP packets received with cause Collision with network initiated request."
     ::= { jnxMbgPgwGtpPerPeerStatsEntry 400 }

jnxMbgPgwPPGtpV2ICsColNWReqTx OBJECT-TYPE
         SYNTAX      Counter64
         MAX-ACCESS  read-only
         STATUS      current
         DESCRIPTION
         "Number of GTP packets sent with cause Collision with network initiated request."
     ::= { jnxMbgPgwGtpPerPeerStatsEntry 401 }

jnxMbgPgwPPGtpV2ICsUnPgUESusRx OBJECT-TYPE
         SYNTAX      Counter64
         MAX-ACCESS  read-only
         STATUS      current
         DESCRIPTION
         "Number of GTP packets received with cause Unable to page UE due to suspension."
     ::= { jnxMbgPgwGtpPerPeerStatsEntry 402 }

jnxMbgPgwPPGtpV2ICsUnPgUESusTx OBJECT-TYPE
         SYNTAX      Counter64
         MAX-ACCESS  read-only
         STATUS      current
         DESCRIPTION
         "Number of GTP packets sent with cause Unable to page UE due to suspension."
     ::= { jnxMbgPgwGtpPerPeerStatsEntry 403 }

jnxMbgPgwPPGtpV2ICsInvTotLenRx OBJECT-TYPE
         SYNTAX      Counter64
         MAX-ACCESS  read-only
         STATUS      current
         DESCRIPTION
         "Number of GTP packets received with cause Invalid total len."
     ::= { jnxMbgPgwGtpPerPeerStatsEntry 404 }

jnxMbgPgwPPGtpV2ICsInvTotLenTx OBJECT-TYPE
         SYNTAX      Counter64
         MAX-ACCESS  read-only
         STATUS      current
         DESCRIPTION
         "Number of GTP packets sent with cause Invalid total len."
     ::= { jnxMbgPgwGtpPerPeerStatsEntry 405 }

jnxMbgPgwPPGtpV2ICsDtForNtSupRx OBJECT-TYPE
         SYNTAX      Counter64
         MAX-ACCESS  read-only
         STATUS      current
         DESCRIPTION
         "Number of GTP packets received with cause Data forwarding not supported."
     ::= { jnxMbgPgwGtpPerPeerStatsEntry 406 }

jnxMbgPgwPPGtpV2ICsDtForNtSupTx OBJECT-TYPE
         SYNTAX      Counter64
         MAX-ACCESS  read-only
         STATUS      current
         DESCRIPTION
         "Number of GTP packets sent with cause Data forwarding not supported."
     ::= { jnxMbgPgwGtpPerPeerStatsEntry 407 }

jnxMbgPgwPPGtpV2ICsInReFRePrRx OBJECT-TYPE
         SYNTAX      Counter64
         MAX-ACCESS  read-only
         STATUS      current
         DESCRIPTION
         "Number of GTP packets received with cause Invalid Reply from Remote peer."
     ::= { jnxMbgPgwGtpPerPeerStatsEntry 408 }

jnxMbgPgwPPGtpV2ICsInReFRePrTx OBJECT-TYPE
         SYNTAX      Counter64
         MAX-ACCESS  read-only
         STATUS      current
         DESCRIPTION
         "Number of GTP packets sent with cause Invalid Reply from Remote peer."
     ::= { jnxMbgPgwGtpPerPeerStatsEntry 409 }

jnxMbgPgwPPGtpV2ICsInvPrRx OBJECT-TYPE
         SYNTAX      Counter64
         MAX-ACCESS  read-only
         STATUS      current
         DESCRIPTION
         "Number of GTP packets received with cause Invalid peer."
     ::= { jnxMbgPgwGtpPerPeerStatsEntry 410 }

jnxMbgPgwPPGtpV2ICsInvPrTx OBJECT-TYPE
         SYNTAX      Counter64
         MAX-ACCESS  read-only
         STATUS      current
         DESCRIPTION
         "Number of GTP packets sent with cause Invalid peer."
     ::= { jnxMbgPgwGtpPerPeerStatsEntry 411 }

jnxMbgPgwPPV1InitPdpCxtReqRx   OBJECT-TYPE
    SYNTAX      Counter64
    MAX-ACCESS  read-only
    STATUS      current
    DESCRIPTION
    "Number of GTP V1 Initiated PDP Context Requests Received."
    ::= { jnxMbgPgwGtpPerPeerStatsEntry 412 }

jnxMbgPgwPPV1InitPdpCxtReqTx   OBJECT-TYPE
    SYNTAX      Counter64
    MAX-ACCESS  read-only
    STATUS      current
    DESCRIPTION
    "Number of GTP V1 Initiated PDP Context Requests Sent."
    ::= { jnxMbgPgwGtpPerPeerStatsEntry 413 }

jnxMbgPgwPPV1InitPdpCxtRspRx   OBJECT-TYPE
    SYNTAX      Counter64
    MAX-ACCESS  read-only
    STATUS      current
    DESCRIPTION
    "Number of GTP V1 Initiated PDP Context Response Received."
    ::= { jnxMbgPgwGtpPerPeerStatsEntry 414 }

jnxMbgPgwPPV1InitPdpCxtRspTx   OBJECT-TYPE
    SYNTAX      Counter64
    MAX-ACCESS  read-only
    STATUS      current
    DESCRIPTION
    "Number of GTP V1 Initiated PDP Context Response Sent."
    ::= { jnxMbgPgwGtpPerPeerStatsEntry 415 }

jnxMbgPgwPPV2SuspNotifRx OBJECT-TYPE
         SYNTAX      Counter64
         MAX-ACCESS  read-only
         STATUS      current
         DESCRIPTION
         "Number of GTPv2 Suspend Notification messages received."
     ::= { jnxMbgPgwGtpPerPeerStatsEntry 416 }

jnxMbgPgwPPV2SuspNotifTx OBJECT-TYPE
         SYNTAX      Counter64
         MAX-ACCESS  read-only
         STATUS      current
         DESCRIPTION
         "Number of GTPv2 Suspend Notification messages sent."
     ::= { jnxMbgPgwGtpPerPeerStatsEntry 417 }

jnxMbgPgwPPV2SuspAckRx OBJECT-TYPE
         SYNTAX      Counter64
         MAX-ACCESS  read-only
         STATUS      current
         DESCRIPTION
         "Number of GTPv2 Suspend Acknowledgement messages received."
     ::= { jnxMbgPgwGtpPerPeerStatsEntry 418 }

jnxMbgPgwPPV2SuspAckTx OBJECT-TYPE
         SYNTAX      Counter64
         MAX-ACCESS  read-only
         STATUS      current
         DESCRIPTION
         "Number of GTPv2 Suspend Acknowledgement messages sent."
     ::= { jnxMbgPgwGtpPerPeerStatsEntry 419 }

jnxMbgPgwPPV2ResumeNotifRx OBJECT-TYPE
         SYNTAX      Counter64
         MAX-ACCESS  read-only
         STATUS      current
         DESCRIPTION
         "Number of GTPv2 Resume Notification messages received."
     ::= { jnxMbgPgwGtpPerPeerStatsEntry 420 }

jnxMbgPgwPPV2ResumeNotifTx OBJECT-TYPE
         SYNTAX      Counter64
         MAX-ACCESS  read-only
         STATUS      current
         DESCRIPTION
         "Number of GTPv2 Resume Notification messages sent."
     ::= { jnxMbgPgwGtpPerPeerStatsEntry 421 }

jnxMbgPgwPPV2ResumeAckRx OBJECT-TYPE
         SYNTAX      Counter64
         MAX-ACCESS  read-only
         STATUS      current
         DESCRIPTION
         "Number of GTPv2 Resume Acknowledgement messages received."
     ::= { jnxMbgPgwGtpPerPeerStatsEntry 422 }

jnxMbgPgwPPV2ResumeAckTx OBJECT-TYPE
         SYNTAX      Counter64
         MAX-ACCESS  read-only
         STATUS      current
         DESCRIPTION
         "Number of GTPv2 Resume Acknowledgement messages sent."
     ::= { jnxMbgPgwGtpPerPeerStatsEntry 423 }

jnxMbgPgwPPV2PiggybackMsgRx OBJECT-TYPE
         SYNTAX      Counter64
         MAX-ACCESS  read-only
         STATUS      current
         DESCRIPTION
         "Number of GTPv2 Piggyback messages received."
     ::= { jnxMbgPgwGtpPerPeerStatsEntry 424 }

jnxMbgPgwPPV2PiggybackMsgTx OBJECT-TYPE
         SYNTAX      Counter64
         MAX-ACCESS  read-only
         STATUS      current
         DESCRIPTION
         "Number of GTPv2 Piggyback messages sent."
     ::= { jnxMbgPgwGtpPerPeerStatsEntry 425 }

--
-- GTP Object for showing GTP Interface Statistics
--
jnxMbgPgwGtpIfStatsTable  OBJECT-TYPE
    SYNTAX SEQUENCE OF JnxMbgPgwGtpIfStatsEntry
    MAX-ACCESS  not-accessible
    STATUS      current
    DESCRIPTION
        "Each entry corresponds to an interface level GTP statistic."
    ::= { jnxMbgPgwGtpObjects 11 }

jnxMbgPgwGtpIfStatsEntry OBJECT-TYPE
    SYNTAX      JnxMbgPgwGtpIfStatsEntry
    MAX-ACCESS  not-accessible
    STATUS      current
    DESCRIPTION
        "A specification of the GTP interface level control Statistics."
    INDEX     { jnxMbgGwIndex,
                jnxMbgPgwIfIndex }
    ::= { jnxMbgPgwGtpIfStatsTable 1}

JnxMbgPgwGtpIfStatsEntry ::= SEQUENCE {
    jnxMbgPgwIfIndex                Unsigned32,
    jnxMbgPgwIfType                 DisplayString,
    jnxMbgPgwIfRxPacketsDropped     Counter64,
    jnxMbgPgwIfPacketAllocFail      Counter64,
    jnxMbgPgwIfPacketSendFail       Counter64,
    jnxMbgPgwIfIPVerErrRx           Counter64,
    jnxMbgPgwIfIPProtoErrRx         Counter64,
    jnxMbgPgwIfGTPPortErrRx         Counter64,
    jnxMbgPgwIfGTPUnknVerRx         Counter64,
    jnxMbgPgwIfPcktLenErrRx         Counter64,
    jnxMbgPgwIfUnknMsgRx            Counter64,
    jnxMbgPgwIfV2ProtocolErrRx      Counter64,
    jnxMbgPgwIfV2UnSupportedMsgRx   Counter64,
    jnxMbgPgwIfV2T3RespTmrExpRx     Counter64,
    jnxMbgPgwIfV2GlbNumMsgRx        Counter64,
    jnxMbgPgwIfV2GlbNumMsgTx        Counter64,
    jnxMbgPgwIfV2GlbNumBytesRx      Counter64,
    jnxMbgPgwIfV2GlbNumBytesTx      Counter64,
    jnxMbgPgwIfV2GlbEchoReqRx       Counter64,
    jnxMbgPgwIfV2GlbEchoReqTx       Counter64,
    jnxMbgPgwIfV2GlbEchoRespRx      Counter64,
    jnxMbgPgwIfV2GlbEchoRespTx      Counter64,
    jnxMbgPgwIfV2VerNotSupRx        Counter64,
    jnxMbgPgwIfV2VerNotSupTx        Counter64,
    jnxMbgPgwIfV2CreateSessReqRx    Counter64,
    jnxMbgPgwIfV2CreateSessReqTx    Counter64,
    jnxMbgPgwIfV2CreateSessRspRx    Counter64,
    jnxMbgPgwIfV2CreateSessRspTx    Counter64,
    jnxMbgPgwIfV2ModBrReqRx         Counter64,
    jnxMbgPgwIfV2ModBrReqTx         Counter64,
    jnxMbgPgwIfV2ModBrRspRx         Counter64,
    jnxMbgPgwIfV2ModBrRspTx         Counter64,
    jnxMbgPgwIfV2DelSessReqRx       Counter64,
    jnxMbgPgwIfV2DelSessReqTx       Counter64,
    jnxMbgPgwIfV2DelSessRspRx       Counter64,
    jnxMbgPgwIfV2DelSessRspTx       Counter64,
    jnxMbgPgwIfV2CrtBrReqRx         Counter64,
    jnxMbgPgwIfV2CrtBrReqTx         Counter64,
    jnxMbgPgwIfV2CrtBrRspRx         Counter64,
    jnxMbgPgwIfV2CrtBrRspTx         Counter64,
    jnxMbgPgwIfV2UpdBrReqRx         Counter64,
    jnxMbgPgwIfV2UpdBrReqTx         Counter64,
    jnxMbgPgwIfV2UpdBrRspRx         Counter64,
    jnxMbgPgwIfV2UpdBrRspTx         Counter64,
    jnxMbgPgwIfV2DelBrReqRx         Counter64,
    jnxMbgPgwIfV2DelBrReqTx         Counter64,
    jnxMbgPgwIfV2DelBrRspRx         Counter64,
    jnxMbgPgwIfV2DelBrRspTx         Counter64,
    jnxMbgPgwIfV2DelConnSetReqRx    Counter64,
    jnxMbgPgwIfV2DelConnSetReqTx    Counter64,
    jnxMbgPgwIfV2DelConnSetRspRx    Counter64,
    jnxMbgPgwIfV2DelConnSetRspTx    Counter64,
    jnxMbgPgwIfV2UpdConnSetReqRx    Counter64,
    jnxMbgPgwIfV2UpdConnSetReqTx    Counter64,
    jnxMbgPgwIfV2UpdConnSetRspRx    Counter64,
    jnxMbgPgwIfV2UpdConnSetRspTx    Counter64,
    jnxMbgPgwIfV2ModBrCmdRx         Counter64,
    jnxMbgPgwIfV2ModBrCmdTx         Counter64,
    jnxMbgPgwIfV2ModBrFlrIndRx      Counter64,
    jnxMbgPgwIfV2ModBrFlrIndTx      Counter64,
    jnxMbgPgwIfV2DelBrCmdRx         Counter64,
    jnxMbgPgwIfV2DelBrCmdTx         Counter64,
    jnxMbgPgwIfV2DelBrFlrIndRx      Counter64,
    jnxMbgPgwIfV2DelBrFlrIndTx      Counter64,
    jnxMbgPgwIfV2BrResCmdRx         Counter64,
    jnxMbgPgwIfV2BrResCmdTx         Counter64,
    jnxMbgPgwIfV2BrResFlrIndRx      Counter64,
    jnxMbgPgwIfV2BrResFlrIndTx      Counter64,
    jnxMbgPgwIfV2ICsReqAcceptRx     Counter64,
    jnxMbgPgwIfV2ICsReqAcceptTx     Counter64,
    jnxMbgPgwIfV2ICsAcceptPartRx    Counter64,
    jnxMbgPgwIfV2ICsAcceptPartTx    Counter64,
    jnxMbgPgwIfV2ICsNewPTNPrefRx    Counter64,
    jnxMbgPgwIfV2ICsNewPTNPrefTx    Counter64,
    jnxMbgPgwIfV2ICsNewPTSIAdbrRx   Counter64,
    jnxMbgPgwIfV2ICsNewPTSIAdbrTx   Counter64,
    jnxMbgPgwIfV2ICsCtxNotFndRx     Counter64,
    jnxMbgPgwIfV2ICsCtxNotFndTx     Counter64,
    jnxMbgPgwIfV2ICsInvMsgFmtRx     Counter64,
    jnxMbgPgwIfV2ICsInvMsgFmtTx     Counter64,
    jnxMbgPgwIfV2ICsVerNotSuppRx    Counter64,
    jnxMbgPgwIfV2ICsVerNotSuppTx    Counter64,
    jnxMbgPgwIfV2ICsInvLenRx        Counter64,
    jnxMbgPgwIfV2ICsInvLenTx        Counter64,
    jnxMbgPgwIfV2ICsServNotSuppRx   Counter64,
    jnxMbgPgwIfV2ICsServNotSuppTx   Counter64,
    jnxMbgPgwIfV2ICsManIEIncorrRx   Counter64,
    jnxMbgPgwIfV2ICsManIEIncorrTx   Counter64,
    jnxMbgPgwIfV2ICsManIEMissRx     Counter64,
    jnxMbgPgwIfV2ICsManIEMissTx     Counter64,
    jnxMbgPgwIfV2ICsOptIEIncorrRx   Counter64,
    jnxMbgPgwIfV2ICsOptIEIncorrTx   Counter64,
    jnxMbgPgwIfV2ICsSysFailRx       Counter64,
    jnxMbgPgwIfV2ICsSysFailTx       Counter64,
    jnxMbgPgwIfV2ICsNoResRx         Counter64,
    jnxMbgPgwIfV2ICsNoResTx         Counter64,
    jnxMbgPgwIfV2ICsTFTSMANTErRx    Counter64,
    jnxMbgPgwIfV2ICsTFTSMANTErTx    Counter64,
    jnxMbgPgwIfV2ICsTFTSysErrRx     Counter64,
    jnxMbgPgwIfV2ICsTFTSysErrTx     Counter64,
    jnxMbgPgwIfV2ICsPkFltManErrRx   Counter64,
    jnxMbgPgwIfV2ICsPkFltManErrTx   Counter64,
    jnxMbgPgwIfV2ICsPkFltSynErrRx   Counter64,
    jnxMbgPgwIfV2ICsPkFltSynErrTx   Counter64,
    jnxMbgPgwIfV2ICsMisUnknAPNRx    Counter64,
    jnxMbgPgwIfV2ICsMisUnknAPNTx    Counter64,
    jnxMbgPgwIfV2ICsUnexpRptIERx    Counter64,
    jnxMbgPgwIfV2ICsUnexpRptIETx    Counter64,
    jnxMbgPgwIfV2ICsGREKeyNtFdRx    Counter64,
    jnxMbgPgwIfV2ICsGREKeyNtFdTx    Counter64,
    jnxMbgPgwIfV2ICsRelocFailRx     Counter64,
    jnxMbgPgwIfV2ICsRelocFailTx     Counter64,
    jnxMbgPgwIfV2ICsDeniedINRatRx   Counter64,
    jnxMbgPgwIfV2ICsDeniedINRatTx   Counter64,
    jnxMbgPgwIfV2ICsPTNotSuppRx     Counter64,
    jnxMbgPgwIfV2ICsPTNotSuppTx     Counter64,
    jnxMbgPgwIfV2ICsAllDynAdOccRx   Counter64,
    jnxMbgPgwIfV2ICsAllDynAdOccTx   Counter64,
    jnxMbgPgwIfV2ICsNOTFTUECTXRx    Counter64,
    jnxMbgPgwIfV2ICsNOTFTUECTXTx    Counter64,
    jnxMbgPgwIfV2ICsProtoNtSupRx    Counter64,
    jnxMbgPgwIfV2ICsProtoNtSupTx    Counter64,
    jnxMbgPgwIfV2ICsUENotRespRx     Counter64,
    jnxMbgPgwIfV2ICsUENotRespTx     Counter64,
    jnxMbgPgwIfV2ICsUERefusesRx     Counter64,
    jnxMbgPgwIfV2ICsUERefusesTx     Counter64,
    jnxMbgPgwIfV2ICsServDeniedRx    Counter64,
    jnxMbgPgwIfV2ICsServDeniedTx    Counter64,
    jnxMbgPgwIfV2ICsUnabPageUERx    Counter64,
    jnxMbgPgwIfV2ICsUnabPageUETx    Counter64,
    jnxMbgPgwIfV2ICsNoMemRx         Counter64,
    jnxMbgPgwIfV2ICsNoMemTx         Counter64,
    jnxMbgPgwIfV2ICsUserAUTHFlRx    Counter64,
    jnxMbgPgwIfV2ICsUserAUTHFlTx    Counter64,
    jnxMbgPgwIfV2ICsAPNAcsDenRx     Counter64,
    jnxMbgPgwIfV2ICsAPNAcsDenTx     Counter64,
    jnxMbgPgwIfV2ICsReqRejRx        Counter64,
    jnxMbgPgwIfV2ICsReqRejTx        Counter64,
    jnxMbgPgwIfV2ICsPTMSISigMMRx    Counter64,
    jnxMbgPgwIfV2ICsPTMSISigMMTx    Counter64,
    jnxMbgPgwIfV2ICsIMSINotKnRx     Counter64,
    jnxMbgPgwIfV2ICsIMSINotKnTx     Counter64,
    jnxMbgPgwIfV2ICsCondIEMsRx      Counter64,
    jnxMbgPgwIfV2ICsCondIEMsTx      Counter64,
    jnxMbgPgwIfV2ICsAPNResTIncRx    Counter64,
    jnxMbgPgwIfV2ICsAPNResTIncTx    Counter64,
    jnxMbgPgwIfV2ICsUnknownRx       Counter64,
    jnxMbgPgwIfV2ICsUnknownTx       Counter64,
    jnxMbgPgwIfV1ProtocolErrRx      Counter64,
    jnxMbgPgwIfV1UnSupportedMsgRx   Counter64,
    jnxMbgPgwIfV1T3RespTmrExpRx     Counter64,
    jnxMbgPgwIfV1GlbNumMsgRx        Counter64,
    jnxMbgPgwIfV1GlbNumMsgTx        Counter64,
    jnxMbgPgwIfV1GlbNumBytesRx      Counter64,
    jnxMbgPgwIfV1GlbNumBytesTx      Counter64,
    jnxMbgPgwIfV1GlbEchoReqRx       Counter64,
    jnxMbgPgwIfV1GlbEchoReqTx       Counter64,
    jnxMbgPgwIfV1GlbEchoRespRx      Counter64,
    jnxMbgPgwIfV1GlbEchoRespTx      Counter64,
    jnxMbgPgwIfV1VerNotSupRx        Counter64,
    jnxMbgPgwIfV1VerNotSupTx        Counter64,
    jnxMbgPgwIfV1CrtPdpCxtReqRx     Counter64,
    jnxMbgPgwIfV1CrtPdpCxtReqTx     Counter64,
    jnxMbgPgwIfV1CrtPdpCxtRspRx     Counter64,
    jnxMbgPgwIfV1CrtPdpCxtRspTx     Counter64,
    jnxMbgPgwIfV1UpdPdpCxtReqRx     Counter64,
    jnxMbgPgwIfV1UpdPdpCxtReqTx     Counter64,
    jnxMbgPgwIfV1UpdPdpCxtRspRx     Counter64,
    jnxMbgPgwIfV1UpdPdpCxtRspTx     Counter64,
    jnxMbgPgwIfV1DelPdpCxtReqRx     Counter64,
    jnxMbgPgwIfV1DelPdpCxtReqTx     Counter64,
    jnxMbgPgwIfV1DelPdpCxtRspRx     Counter64,
    jnxMbgPgwIfV1DelPdpCxtRspTx     Counter64,
    jnxMbgPgwIfV1CrtAAPdpCxtReqRx   Counter64,
    jnxMbgPgwIfV1CrtAAPdpCxtReqTx   Counter64,
    jnxMbgPgwIfV1CrtAAPdpCxtRspRx   Counter64,
    jnxMbgPgwIfV1CrtAAPdpCxtRspTx   Counter64,
    jnxMbgPgwIfV1DelAAPdpCxtReqRx   Counter64,
    jnxMbgPgwIfV1DelAAPdpCxtReqTx   Counter64,
    jnxMbgPgwIfV1DelAAPdpCxtRspRx   Counter64,
    jnxMbgPgwIfV1DelAAPdpCxtRspTx   Counter64,
    jnxMbgPgwIfV1ErrorIndRx         Counter64,
    jnxMbgPgwIfV1ErrorIndTx         Counter64,
    jnxMbgPgwIfV1NotifReqRx         Counter64,
    jnxMbgPgwIfV1NotifReqTx         Counter64,
    jnxMbgPgwIfV1NotifRspRx         Counter64,
    jnxMbgPgwIfV1NotifRspTx         Counter64,
    jnxMbgPgwIfV1NotifRejReqRx      Counter64,
    jnxMbgPgwIfV1NotifRejReqTx      Counter64,
    jnxMbgPgwIfV1NotifRejRspRx      Counter64,
    jnxMbgPgwIfV1NotifRejRspTx      Counter64,
    jnxMbgPgwIfV1RtInfReqRx         Counter64,
    jnxMbgPgwIfV1RtInfReqTx         Counter64,
    jnxMbgPgwIfV1RtInfRspRx         Counter64,
    jnxMbgPgwIfV1RtInfRspTx         Counter64,
    jnxMbgPgwIfV1FailRptReqRx       Counter64,
    jnxMbgPgwIfV1FailRptReqTx       Counter64,
    jnxMbgPgwIfV1FailRptRspRx       Counter64,
    jnxMbgPgwIfV1FailRptRspTx       Counter64,
    jnxMbgPgwIfV1NotMSPresReqRx     Counter64,
    jnxMbgPgwIfV1NotMSPresReqTx     Counter64,
    jnxMbgPgwIfV1NotMSPresRspRx     Counter64,
    jnxMbgPgwIfV1NotMSPresRspTx     Counter64,
    jnxMbgPgwIfV1ICsReqAcceptedRx   Counter64,
    jnxMbgPgwIfV1ICsReqAcceptedTx   Counter64,
    jnxMbgPgwIfV1ICsNonExistRx      Counter64,
    jnxMbgPgwIfV1ICsNonExistTx      Counter64,
    jnxMbgPgwIfV1ICsInvMsgFmtRx     Counter64,
    jnxMbgPgwIfV1ICsInvMsgFmtTx     Counter64,
    jnxMbgPgwIfV1ICsIMSINotKnownRx  Counter64,
    jnxMbgPgwIfV1ICsIMSINotKnownTx  Counter64,
    jnxMbgPgwIfV1ICsMSGRPSDetachRx  Counter64,
    jnxMbgPgwIfV1ICsMSGRPSDetachTx  Counter64,
    jnxMbgPgwIfV1ICsMSNotGRPSRespRx Counter64,
    jnxMbgPgwIfV1ICsMSNotGRPSRespTx Counter64,
    jnxMbgPgwIfV1ICsMSRefusesRx     Counter64,
    jnxMbgPgwIfV1ICsMSRefusesTx     Counter64,
    jnxMbgPgwIfV1ICsVerNotSuppRx    Counter64,
    jnxMbgPgwIfV1ICsVerNotSuppTx    Counter64,
    jnxMbgPgwIfV1ICsNoResRx         Counter64,
    jnxMbgPgwIfV1ICsNoResTx         Counter64,
    jnxMbgPgwIfV1ICsServNotSuppRx   Counter64,
    jnxMbgPgwIfV1ICsServNotSuppTx   Counter64,
    jnxMbgPgwIfV1ICsManIEIncrtRx    Counter64,
    jnxMbgPgwIfV1ICsManIEIncrtTx    Counter64,
    jnxMbgPgwIfV1ICsManIEMissRx     Counter64,
    jnxMbgPgwIfV1ICsManIEMissTx     Counter64,
    jnxMbgPgwIfV1ICsOptIEIncrtRx    Counter64,
    jnxMbgPgwIfV1ICsOptIEIncrtTx    Counter64,
    jnxMbgPgwIfV1ICsSysFailRx       Counter64,
    jnxMbgPgwIfV1ICsSysFailTx       Counter64,
    jnxMbgPgwIfV1ICsRoamRestrictRx  Counter64,
    jnxMbgPgwIfV1ICsRoamRestrictTx  Counter64,
    jnxMbgPgwIfV1ICsPTMSISigMMRx    Counter64,
    jnxMbgPgwIfV1ICsPTMSISigMMTx    Counter64,
    jnxMbgPgwIfV1ICsGPRSConnSuppRx  Counter64,
    jnxMbgPgwIfV1ICsGPRSConnSuppTx  Counter64,
    jnxMbgPgwIfV1ICsAuthFailRx      Counter64,
    jnxMbgPgwIfV1ICsAuthFailTx      Counter64,
    jnxMbgPgwIfV1ICsUserAuthFailRx  Counter64,
    jnxMbgPgwIfV1ICsUserAuthFailTx  Counter64,
    jnxMbgPgwIfV1ICsCtxNotFndRx     Counter64,
    jnxMbgPgwIfV1ICsCtxNotFndTx     Counter64,
    jnxMbgPgwIfV1ICsAllDynPDPAdRx   Counter64,
    jnxMbgPgwIfV1ICsAllDynPDPAdTx   Counter64,
    jnxMbgPgwIfV1ICsNoMemRx         Counter64,
    jnxMbgPgwIfV1ICsNoMemTx         Counter64,
    jnxMbgPgwIfV1ICsRelocFailRx     Counter64,
    jnxMbgPgwIfV1ICsRelocFailTx     Counter64,
    jnxMbgPgwIfV1ICsUnkManExhdrRx   Counter64,
    jnxMbgPgwIfV1ICsUnkManExhdrTx   Counter64,
    jnxMbgPgwIfV1ICsSMANTTFTEr1Rx   Counter64,
    jnxMbgPgwIfV1ICsSMANTTFTEr1Tx   Counter64,
    jnxMbgPgwIfV1ICsSYNTFTErr2Rx    Counter64,
    jnxMbgPgwIfV1ICsSYNTFTErr2Tx    Counter64,
    jnxMbgPgwIfV1ICsSMNTPkFlEr1Rx   Counter64,
    jnxMbgPgwIfV1ICsSMNTPkFlEr1Tx   Counter64,
    jnxMbgPgwIfV1ICsSYNPkFlErr2Rx   Counter64,
    jnxMbgPgwIfV1ICsSYNPkFlErr2Tx   Counter64,
    jnxMbgPgwIfV1ICsMissUnknAPNRx   Counter64,
    jnxMbgPgwIfV1ICsMissUnknAPNTx   Counter64,
    jnxMbgPgwIfV1ICsUnknPDPAdRx     Counter64,
    jnxMbgPgwIfV1ICsUnknPDPAdTx     Counter64,
    jnxMbgPgwIfV1ICsNoTFTCtxExRx    Counter64,
    jnxMbgPgwIfV1ICsNoTFTCtxExTx    Counter64,
    jnxMbgPgwIfV0ProtocolErrRx      Counter64,
    jnxMbgPgwIfV0UnSupportedMsgRx   Counter64,
    jnxMbgPgwIfV0T3RespTmrExpRx     Counter64,
    jnxMbgPgwIfV0GlbNumMsgRx        Counter64,
    jnxMbgPgwIfV0GlbNumMsgTx        Counter64,
    jnxMbgPgwIfV0GlbNumBytesRx      Counter64,
    jnxMbgPgwIfV0GlbNumBytesTx      Counter64,
    jnxMbgPgwIfV0GlbEchoReqRx       Counter64,
    jnxMbgPgwIfV0GlbEchoReqTx       Counter64,
    jnxMbgPgwIfV0GlbEchoRespRx      Counter64,
    jnxMbgPgwIfV0GlbEchoRespTx      Counter64,
    jnxMbgPgwIfV0GlbVerNotSupRx     Counter64,
    jnxMbgPgwIfV0GlbVerNotSupTx     Counter64,
    jnxMbgPgwIfV0GlbCrtPdpCxtReqRx  Counter64,
    jnxMbgPgwIfV0GlbCrtPdpCxtReqTx  Counter64,
    jnxMbgPgwIfV0GlbCrtPdpCxtRspRx  Counter64,
    jnxMbgPgwIfV0GlbCrtPdpCxtRspTx  Counter64,
    jnxMbgPgwIfV0GlbUpdPdpCxtReqRx  Counter64,
    jnxMbgPgwIfV0GlbUpdPdpCxtReqTx  Counter64,
    jnxMbgPgwIfV0GlbUpdPdpCxtRspRx  Counter64,
    jnxMbgPgwIfV0GlbUpdPdpCxtRspTx  Counter64,
    jnxMbgPgwIfV0GlbDelPdpCxtReqRx  Counter64,
    jnxMbgPgwIfV0GlbDelPdpCxtReqTx  Counter64,
    jnxMbgPgwIfV0GlbDelPdpCxtRspRx  Counter64,
    jnxMbgPgwIfV0GlbDelPdpCxtRspTx  Counter64,
    jnxMbgPgwIfV0GlbCrtAAPdpCxtRqRx Counter64,
    jnxMbgPgwIfV0GlbCrtAAPdpCxtRqTx Counter64,
    jnxMbgPgwIfV0GlbCrtAAPdpCxtRpRx Counter64,
    jnxMbgPgwIfV0GlbCrtAAPdpCxtRpTx Counter64,
    jnxMbgPgwIfV0GlbDelAAPdpCxtRqRx Counter64,
    jnxMbgPgwIfV0GlbDelAAPdpCxtRqTx Counter64,
    jnxMbgPgwIfV0GlbDelAAPdpCxtRpRx Counter64,
    jnxMbgPgwIfV0GlbDelAAPdpCxtRpTx Counter64,
    jnxMbgPgwIfV0GlbErrorIndRx      Counter64,
    jnxMbgPgwIfV0GlbErrorIndTx      Counter64,
    jnxMbgPgwIfV0GlbNotifReqRx      Counter64,
    jnxMbgPgwIfV0GlbNotifReqTx      Counter64,
    jnxMbgPgwIfV0GlbNotifRspRx      Counter64,
    jnxMbgPgwIfV0GlbNotifRspTx      Counter64,
    jnxMbgPgwIfV0GlbNotifRejReqRx   Counter64,
    jnxMbgPgwIfV0GlbNotifRejReqTx   Counter64,
    jnxMbgPgwIfV0GlbNotifRejRspRx   Counter64,
    jnxMbgPgwIfV0GlbNotifRejRspTx   Counter64,
    jnxMbgPgwIfV0GlbRtInfReqRx      Counter64,
    jnxMbgPgwIfV0GlbRtInfReqTx      Counter64,
    jnxMbgPgwIfV0GlbRtInfRspRx      Counter64,
    jnxMbgPgwIfV0GlbRtInfRspTx      Counter64,
    jnxMbgPgwIfV0GlbFailRptReqRx    Counter64,
    jnxMbgPgwIfV0GlbFailRptReqTx    Counter64,
    jnxMbgPgwIfV0GlbFailRptRspRx    Counter64,
    jnxMbgPgwIfV0GlbFailRptRspTx    Counter64,
    jnxMbgPgwIfV0GlbNotMSPresReqRx  Counter64,
    jnxMbgPgwIfV0GlbNotMSPresReqTx  Counter64,
    jnxMbgPgwIfV0GlbNotMSPresRspRx  Counter64,
    jnxMbgPgwIfV0GlbNotMSPresRspTx  Counter64,
    jnxMbgPgwIfV0ICsReqAcceptedRx   Counter64,
    jnxMbgPgwIfV0ICsReqAcceptedTx   Counter64,
    jnxMbgPgwIfV0ICsNonExistRx      Counter64,
    jnxMbgPgwIfV0ICsNonExistTx      Counter64,
    jnxMbgPgwIfV0ICsInvMsgFmtRx     Counter64,
    jnxMbgPgwIfV0ICsInvMsgFmtTx     Counter64,
    jnxMbgPgwIfV0ICsIMSINotKnownRx  Counter64,
    jnxMbgPgwIfV0ICsIMSINotKnownTx  Counter64,
    jnxMbgPgwIfV0ICsMSGRPSDetachRx  Counter64,
    jnxMbgPgwIfV0ICsMSGRPSDetachTx  Counter64,
    jnxMbgPgwIfV0ICsMSNotGRPSRespRx Counter64,
    jnxMbgPgwIfV0ICsMSNotGRPSRespTx Counter64,
    jnxMbgPgwIfV0ICsMSRefusesRx     Counter64,
    jnxMbgPgwIfV0ICsMSRefusesTx     Counter64,
    jnxMbgPgwIfV0ICsVerNotSuppRx    Counter64,
    jnxMbgPgwIfV0ICsVerNotSuppTx    Counter64,
    jnxMbgPgwIfV0ICsNoResRx         Counter64,
    jnxMbgPgwIfV0ICsNoResTx         Counter64,
    jnxMbgPgwIfV0ICsServNotSuppRx   Counter64,
    jnxMbgPgwIfV0ICsServNotSuppTx   Counter64,
    jnxMbgPgwIfV0ICsManIEIncrtRx    Counter64,
    jnxMbgPgwIfV0ICsManIEIncrtTx    Counter64,
    jnxMbgPgwIfV0ICsManIEMissRx     Counter64,
    jnxMbgPgwIfV0ICsManIEMissTx     Counter64,
    jnxMbgPgwIfV0ICsOptIEIncrtRx    Counter64,
    jnxMbgPgwIfV0ICsOptIEIncrtTx    Counter64,
    jnxMbgPgwIfV0ICsSysFailRx       Counter64,
    jnxMbgPgwIfV0ICsSysFailTx       Counter64,
    jnxMbgPgwIfV0ICsRoamRestrictRx  Counter64,
    jnxMbgPgwIfV0ICsRoamRestrictTx  Counter64,
    jnxMbgPgwIfV0ICsPTMSISigMMRx    Counter64,
    jnxMbgPgwIfV0ICsPTMSISigMMTx    Counter64,
    jnxMbgPgwIfV0ICsGPRSConnSuppRx  Counter64,
    jnxMbgPgwIfV0ICsGPRSConnSuppTx  Counter64,
    jnxMbgPgwIfV0ICsAuthFailRx      Counter64,
    jnxMbgPgwIfV0ICsAuthFailTx      Counter64,
    jnxMbgPgwIfV0ICsUserAuthFailRx  Counter64,
    jnxMbgPgwIfV0ICsUserAuthFailTx  Counter64,
    jnxMbgPgwIfGtpV2ICsLclDetRx     Counter64,
    jnxMbgPgwIfGtpV2ICsLclDetTx     Counter64,
    jnxMbgPgwIfGtpV2ICsCmpDetRx     Counter64,
    jnxMbgPgwIfGtpV2ICsCmpDetTx     Counter64,
    jnxMbgPgwIfGtpV2ICsRATChgRx     Counter64,
    jnxMbgPgwIfGtpV2ICsRATChgTx     Counter64,
    jnxMbgPgwIfGtpV2ICsISRDeactRx   Counter64,
    jnxMbgPgwIfGtpV2ICsISRDeactTx   Counter64,
    jnxMbgPgwIfGtpV2ICsEIFRNCEnRx   Counter64,
    jnxMbgPgwIfGtpV2ICsEIFRNCEnTx   Counter64,
    jnxMbgPgwIfGtpV2ICsSemErTADRx   Counter64,
    jnxMbgPgwIfGtpV2ICsSemErTADTx   Counter64,
    jnxMbgPgwIfGtpV2ICsSynErTADRx   Counter64,
    jnxMbgPgwIfGtpV2ICsSynErTADTx   Counter64,
    jnxMbgPgwIfGtpV2ICsRMValRcvRx   Counter64,
    jnxMbgPgwIfGtpV2ICsRMValRcvTx   Counter64,
    jnxMbgPgwIfGtpV2ICsRPrNtRspRx   Counter64,
    jnxMbgPgwIfGtpV2ICsRPrNtRspTx   Counter64,
    jnxMbgPgwIfGtpV2ICsColNWReqRx   Counter64,
    jnxMbgPgwIfGtpV2ICsColNWReqTx   Counter64,
    jnxMbgPgwIfGtpV2ICsUnPgUESusRx  Counter64,
    jnxMbgPgwIfGtpV2ICsUnPgUESusTx  Counter64,
    jnxMbgPgwIfGtpV2ICsInvTotLenRx  Counter64,
    jnxMbgPgwIfGtpV2ICsInvTotLenTx  Counter64,
    jnxMbgPgwIfGtpV2ICsDtForNtSupRx Counter64,
    jnxMbgPgwIfGtpV2ICsDtForNtSupTx Counter64,
    jnxMbgPgwIfGtpV2ICsInReFRePrRx  Counter64,
    jnxMbgPgwIfGtpV2ICsInReFRePrTx  Counter64,
    jnxMbgPgwIfGtpV2ICsInvPrRx      Counter64,
    jnxMbgPgwIfGtpV2ICsInvPrTx      Counter64,
    jnxMbgPgwIfV1InitPdpCxtReqRx    Counter64,
    jnxMbgPgwIfV1InitPdpCxtReqTx    Counter64,
    jnxMbgPgwIfV1InitPdpCxtRspRx    Counter64,
    jnxMbgPgwIfV1InitPdpCxtRspTx    Counter64,
    jnxMbgPgwIfV2SuspNotifRx        Counter64,
    jnxMbgPgwIfV2SuspNotifTx        Counter64,
    jnxMbgPgwIfV2SuspAckRx          Counter64,
    jnxMbgPgwIfV2SuspAckTx          Counter64,
    jnxMbgPgwIfV2ResumeNotifRx      Counter64,
    jnxMbgPgwIfV2ResumeNotifTx      Counter64,
    jnxMbgPgwIfV2ResumeAckRx        Counter64,
    jnxMbgPgwIfV2ResumeAckTx        Counter64,
    jnxMbgPgwIfV2PiggybackMsgRx     Counter64,
    jnxMbgPgwIfV2PiggybackMsgTx     Counter64
}

jnxMbgPgwIfIndex OBJECT-TYPE
    SYNTAX      Unsigned32
    MAX-ACCESS  not-accessible
    STATUS      current
    DESCRIPTION
    "GTP Interface Index"
    ::= { jnxMbgPgwGtpIfStatsEntry 1 }

jnxMbgPgwIfType OBJECT-TYPE
    SYNTAX      DisplayString
    MAX-ACCESS  read-only
    STATUS      current
    DESCRIPTION
    "Interface Name."
    ::= { jnxMbgPgwGtpIfStatsEntry 2 }

jnxMbgPgwIfRxPacketsDropped  OBJECT-TYPE
    SYNTAX      Counter64
    MAX-ACCESS  read-only
    STATUS      current
    DESCRIPTION
    "Number of Received GTP Packets Dropped by the Gateway."
    ::= { jnxMbgPgwGtpIfStatsEntry 3 }

jnxMbgPgwIfPacketAllocFail  OBJECT-TYPE
    SYNTAX      Counter64
    MAX-ACCESS  read-only
    STATUS      current
    DESCRIPTION
    "Number of Packet allocation failures in the Gateway."
    ::= { jnxMbgPgwGtpIfStatsEntry 4 }

jnxMbgPgwIfPacketSendFail OBJECT-TYPE
    SYNTAX      Counter64
    MAX-ACCESS  read-only
    STATUS      current
    DESCRIPTION
    "Number of GTP Packet Send failures in the Gateway."
    ::= { jnxMbgPgwGtpIfStatsEntry 5 }

jnxMbgPgwIfIPVerErrRx OBJECT-TYPE
    SYNTAX      Counter64
    MAX-ACCESS  read-only
    STATUS      current
    DESCRIPTION
    "Number of IP Version Error Packets Received."
    ::= { jnxMbgPgwGtpIfStatsEntry 6 }

jnxMbgPgwIfIPProtoErrRx OBJECT-TYPE
    SYNTAX      Counter64
    MAX-ACCESS  read-only
    STATUS      current
    DESCRIPTION
    "Number of  IP Protocol Error packets Received."
    ::= { jnxMbgPgwGtpIfStatsEntry 7 }

jnxMbgPgwIfGTPPortErrRx OBJECT-TYPE
    SYNTAX      Counter64
    MAX-ACCESS  read-only
    STATUS      current
    DESCRIPTION
    "Number of  Port Error Packets Received."
    ::= { jnxMbgPgwGtpIfStatsEntry 8 }

jnxMbgPgwIfGTPUnknVerRx OBJECT-TYPE
    SYNTAX      Counter64
    MAX-ACCESS  read-only
    STATUS      current
    DESCRIPTION
    "Number of  Unknown Version Packets Received."
    ::= { jnxMbgPgwGtpIfStatsEntry 9 }

jnxMbgPgwIfPcktLenErrRx OBJECT-TYPE
    SYNTAX      Counter64
    MAX-ACCESS  read-only
    STATUS      current
    DESCRIPTION
    "Number of Packet Length Error Packets Received."
    ::= { jnxMbgPgwGtpIfStatsEntry 10 }

jnxMbgPgwIfUnknMsgRx OBJECT-TYPE
    SYNTAX      Counter64
    MAX-ACCESS  read-only
    STATUS      current
    DESCRIPTION
    "Number of  Unknown Messages Received."
    ::= { jnxMbgPgwGtpIfStatsEntry 11 }

jnxMbgPgwIfV2ProtocolErrRx  OBJECT-TYPE
    SYNTAX      Counter64
    MAX-ACCESS  read-only
    STATUS      current
    DESCRIPTION
    "Number of GTPv2 Protocol Errors Received."
    ::= { jnxMbgPgwGtpIfStatsEntry 12 }

jnxMbgPgwIfV2UnSupportedMsgRx  OBJECT-TYPE
    SYNTAX      Counter64
    MAX-ACCESS  read-only
    STATUS      current
    DESCRIPTION
    "Number of GTPv2 Unsupported Messages received."
    ::= { jnxMbgPgwGtpIfStatsEntry 13 }

jnxMbgPgwIfV2T3RespTmrExpRx  OBJECT-TYPE
    SYNTAX      Counter64
    MAX-ACCESS  read-only
    STATUS      current
    DESCRIPTION
    "GTP V2 Number of T3 timer expiries Received."
    ::= { jnxMbgPgwGtpIfStatsEntry 14 }

jnxMbgPgwIfV2GlbNumMsgRx  OBJECT-TYPE
    SYNTAX      Counter64
    MAX-ACCESS  read-only
    STATUS      current
    DESCRIPTION
    "Number of GTPv2 messages received."
    ::= { jnxMbgPgwGtpIfStatsEntry 15 }

jnxMbgPgwIfV2GlbNumMsgTx  OBJECT-TYPE
    SYNTAX      Counter64
    MAX-ACCESS  read-only
    STATUS      current
    DESCRIPTION
    "Number of GTPV2 messages sent."
    ::= { jnxMbgPgwGtpIfStatsEntry 16 }

jnxMbgPgwIfV2GlbNumBytesRx  OBJECT-TYPE
    SYNTAX      Counter64
    MAX-ACCESS  read-only
    STATUS      current
    DESCRIPTION
    "Number of GTPv2 bytes received."
    ::= { jnxMbgPgwGtpIfStatsEntry 17 }

jnxMbgPgwIfV2GlbNumBytesTx  OBJECT-TYPE
    SYNTAX      Counter64
    MAX-ACCESS  read-only
    STATUS      current
    DESCRIPTION
    "Number of GTPV2 bytes sent."
    ::= { jnxMbgPgwGtpIfStatsEntry 18 }

jnxMbgPgwIfV2GlbEchoReqRx  OBJECT-TYPE
    SYNTAX      Counter64
    MAX-ACCESS  read-only
    STATUS      current
    DESCRIPTION
    "Number of GTP V2 Echo Request received."
    ::= { jnxMbgPgwGtpIfStatsEntry 19 }

jnxMbgPgwIfV2GlbEchoReqTx  OBJECT-TYPE
    SYNTAX      Counter64
    MAX-ACCESS  read-only
    STATUS      current
    DESCRIPTION
    "Number of GTP V2 Echo Request Sent."
    ::= { jnxMbgPgwGtpIfStatsEntry 20 }

jnxMbgPgwIfV2GlbEchoRespRx  OBJECT-TYPE
    SYNTAX      Counter64
    MAX-ACCESS  read-only
    STATUS      current
    DESCRIPTION
    "Number of GTP V2 Echo Response received."
    ::= { jnxMbgPgwGtpIfStatsEntry 21 }

jnxMbgPgwIfV2GlbEchoRespTx  OBJECT-TYPE
    SYNTAX      Counter64
    MAX-ACCESS  read-only
    STATUS      current
    DESCRIPTION
    "Number of GTP V2 Echo Response Sent."
    ::= { jnxMbgPgwGtpIfStatsEntry 22 }

jnxMbgPgwIfV2VerNotSupRx OBJECT-TYPE
    SYNTAX      Counter64
    MAX-ACCESS  read-only
    STATUS      current
    DESCRIPTION
    "Number of GTP V2 Version Not supported messages received"
    ::= { jnxMbgPgwGtpIfStatsEntry 23 }

jnxMbgPgwIfV2VerNotSupTx OBJECT-TYPE
    SYNTAX      Counter64
    MAX-ACCESS  read-only
    STATUS      current
    DESCRIPTION
    "Number of GTP V2 version not supported messages Sent."
    ::= { jnxMbgPgwGtpIfStatsEntry 24 }

jnxMbgPgwIfV2CreateSessReqRx  OBJECT-TYPE
    SYNTAX      Counter64
    MAX-ACCESS  read-only
    STATUS      current
    DESCRIPTION
    "Number of GTP V2 Create Session Requests received."
    ::= { jnxMbgPgwGtpIfStatsEntry 25 }

jnxMbgPgwIfV2CreateSessReqTx  OBJECT-TYPE
    SYNTAX      Counter64
    MAX-ACCESS  read-only
    STATUS      current
    DESCRIPTION
    "Number of GTP V2 Create Session Requests Sent."
    ::= { jnxMbgPgwGtpIfStatsEntry 26 }

jnxMbgPgwIfV2CreateSessRspRx  OBJECT-TYPE
    SYNTAX      Counter64
    MAX-ACCESS  read-only
    STATUS      current
    DESCRIPTION
    "Number of GTP V2 Create Session Responses received."
    ::= { jnxMbgPgwGtpIfStatsEntry 27 }

jnxMbgPgwIfV2CreateSessRspTx  OBJECT-TYPE
    SYNTAX      Counter64
    MAX-ACCESS  read-only
    STATUS      current
    DESCRIPTION
    "Number of GTP V2 Create Session Responses Sent."
    ::= { jnxMbgPgwGtpIfStatsEntry 28 }

jnxMbgPgwIfV2ModBrReqRx  OBJECT-TYPE
    SYNTAX      Counter64
    MAX-ACCESS  read-only
    STATUS      current
    DESCRIPTION
    "Number of GTP V2 Modify Bearer Requests received."
    ::= { jnxMbgPgwGtpIfStatsEntry 29 }

jnxMbgPgwIfV2ModBrReqTx  OBJECT-TYPE
    SYNTAX      Counter64
    MAX-ACCESS  read-only
    STATUS      current
    DESCRIPTION
    "Number of GTP V2 Modify Bearer Requests Sent."
    ::= { jnxMbgPgwGtpIfStatsEntry 30 }

jnxMbgPgwIfV2ModBrRspRx  OBJECT-TYPE
    SYNTAX      Counter64
    MAX-ACCESS  read-only
    STATUS      current
    DESCRIPTION
    "Number of GTP V2 Modify Bearer Responses received."
    ::= { jnxMbgPgwGtpIfStatsEntry 31 }

jnxMbgPgwIfV2ModBrRspTx  OBJECT-TYPE
    SYNTAX      Counter64
    MAX-ACCESS  read-only
    STATUS      current
    DESCRIPTION
    "Number of GTP V2 Modify Bearer Responses Sent."
    ::= { jnxMbgPgwGtpIfStatsEntry 32 }

jnxMbgPgwIfV2DelSessReqRx  OBJECT-TYPE
    SYNTAX      Counter64
    MAX-ACCESS  read-only
    STATUS      current
    DESCRIPTION
    "Number of GTP V2 Delete Session Requests received."
    ::= { jnxMbgPgwGtpIfStatsEntry 33 }

jnxMbgPgwIfV2DelSessReqTx  OBJECT-TYPE
    SYNTAX      Counter64
    MAX-ACCESS  read-only
    STATUS      current
    DESCRIPTION
    "Number of GTP V2 Delete Session Requests Sent."
    ::= { jnxMbgPgwGtpIfStatsEntry 34 }

jnxMbgPgwIfV2DelSessRspRx  OBJECT-TYPE
    SYNTAX      Counter64
    MAX-ACCESS  read-only
    STATUS      current
    DESCRIPTION
    "Number of GTP V2 Delete Session Responses received."
    ::= { jnxMbgPgwGtpIfStatsEntry 35 }

jnxMbgPgwIfV2DelSessRspTx  OBJECT-TYPE
    SYNTAX      Counter64
    MAX-ACCESS  read-only
    STATUS      current
    DESCRIPTION
    "Number of GTP V2 Delete Session Responses Sent."
    ::= { jnxMbgPgwGtpIfStatsEntry 36 }

jnxMbgPgwIfV2CrtBrReqRx  OBJECT-TYPE
    SYNTAX      Counter64
    MAX-ACCESS  read-only
    STATUS      current
    DESCRIPTION
    "Number of GTP V2 Create Bearer Requests received."
    ::= { jnxMbgPgwGtpIfStatsEntry 37 }

jnxMbgPgwIfV2CrtBrReqTx  OBJECT-TYPE
    SYNTAX      Counter64
    MAX-ACCESS  read-only
    STATUS      current
    DESCRIPTION
    "Number of GTP V2 Create Bearer Requests Sent."
    ::= { jnxMbgPgwGtpIfStatsEntry 38 }

jnxMbgPgwIfV2CrtBrRspRx  OBJECT-TYPE
    SYNTAX      Counter64
    MAX-ACCESS  read-only
    STATUS      current
    DESCRIPTION
    "Number of GTP V2 Create Bearer Responses received."
    ::= { jnxMbgPgwGtpIfStatsEntry 39 }

jnxMbgPgwIfV2CrtBrRspTx  OBJECT-TYPE
    SYNTAX      Counter64
    MAX-ACCESS  read-only
    STATUS      current
    DESCRIPTION
    "Number of GTP V2 Create Bearer Responses Sent."
    ::= { jnxMbgPgwGtpIfStatsEntry 40 }

jnxMbgPgwIfV2UpdBrReqRx  OBJECT-TYPE
    SYNTAX      Counter64
    MAX-ACCESS  read-only
    STATUS      current
    DESCRIPTION
    "Number of GTP V2 Update Bearer Requests received."
    ::= { jnxMbgPgwGtpIfStatsEntry 41 }

jnxMbgPgwIfV2UpdBrReqTx  OBJECT-TYPE
    SYNTAX      Counter64
    MAX-ACCESS  read-only
    STATUS      current
    DESCRIPTION
    "Number of GTP V2 Update Bearer Requests Sent."
    ::= { jnxMbgPgwGtpIfStatsEntry 42 }

jnxMbgPgwIfV2UpdBrRspRx  OBJECT-TYPE
    SYNTAX      Counter64
    MAX-ACCESS  read-only
    STATUS      current
    DESCRIPTION
    "Number of GTP V2 Update Bearer Responses received."
    ::= { jnxMbgPgwGtpIfStatsEntry 43 }

jnxMbgPgwIfV2UpdBrRspTx  OBJECT-TYPE
    SYNTAX      Counter64
    MAX-ACCESS  read-only
    STATUS      current
    DESCRIPTION
    "Number of GTP V2 Update Bearer Responses Sent."
    ::= { jnxMbgPgwGtpIfStatsEntry 44 }

jnxMbgPgwIfV2DelBrReqRx  OBJECT-TYPE
    SYNTAX      Counter64
    MAX-ACCESS  read-only
    STATUS      current
    DESCRIPTION
    "Number of GTP V2 Delete Bearer Requests received."
    ::= { jnxMbgPgwGtpIfStatsEntry 45 }

jnxMbgPgwIfV2DelBrReqTx  OBJECT-TYPE
    SYNTAX      Counter64
    MAX-ACCESS  read-only
    STATUS      current
    DESCRIPTION
    "Number of GTP V2 Delete Bearer Requests Sent."
    ::= { jnxMbgPgwGtpIfStatsEntry 46 }

jnxMbgPgwIfV2DelBrRspRx  OBJECT-TYPE
    SYNTAX      Counter64
    MAX-ACCESS  read-only
    STATUS      current
    DESCRIPTION
    "Number of GTP V2 Delete Bearer Responses received."
    ::= { jnxMbgPgwGtpIfStatsEntry 47 }

jnxMbgPgwIfV2DelBrRspTx  OBJECT-TYPE
    SYNTAX      Counter64
    MAX-ACCESS  read-only
    STATUS      current
    DESCRIPTION
    "Number of GTP V2 Delete Bearer Responses Sent."
    ::= { jnxMbgPgwGtpIfStatsEntry 48 }

jnxMbgPgwIfV2DelConnSetReqRx  OBJECT-TYPE
    SYNTAX      Counter64
    MAX-ACCESS  read-only
    STATUS      current
    DESCRIPTION
    "Number of GTP V2 Delete PDN connection set Requests received."
    ::= { jnxMbgPgwGtpIfStatsEntry 49 }

jnxMbgPgwIfV2DelConnSetReqTx  OBJECT-TYPE
    SYNTAX      Counter64
    MAX-ACCESS  read-only
    STATUS      current
    DESCRIPTION
    "Number of GTP V2 Delete PDN connection set Requests Sent."
    ::= { jnxMbgPgwGtpIfStatsEntry 50 }

jnxMbgPgwIfV2DelConnSetRspRx  OBJECT-TYPE
    SYNTAX      Counter64
    MAX-ACCESS  read-only
    STATUS      current
    DESCRIPTION
    "Number of GTP V2 Delete PDN connection set Responses received."
    ::= { jnxMbgPgwGtpIfStatsEntry 51 }

jnxMbgPgwIfV2DelConnSetRspTx  OBJECT-TYPE
    SYNTAX      Counter64
    MAX-ACCESS  read-only
    STATUS      current
    DESCRIPTION
    "Number of GTP V2 Delete PDN connection set Responses Sent."
    ::= { jnxMbgPgwGtpIfStatsEntry 52 }

jnxMbgPgwIfV2UpdConnSetReqRx  OBJECT-TYPE
    SYNTAX      Counter64
    MAX-ACCESS  read-only
    STATUS      current
    DESCRIPTION
    "Number of GTP V2 Update Connection set Request received."
    ::= { jnxMbgPgwGtpIfStatsEntry 53 }

jnxMbgPgwIfV2UpdConnSetReqTx  OBJECT-TYPE
    SYNTAX      Counter64
    MAX-ACCESS  read-only
    STATUS      current
    DESCRIPTION
    "Number of GTP V2 Update Connection set Requests Sent."
    ::= { jnxMbgPgwGtpIfStatsEntry 54 }

jnxMbgPgwIfV2UpdConnSetRspRx  OBJECT-TYPE
    SYNTAX      Counter64
    MAX-ACCESS  read-only
    STATUS      current
    DESCRIPTION
    "Number of GTP V2 Update Connetion set Responses received."
    ::= { jnxMbgPgwGtpIfStatsEntry 55 }

jnxMbgPgwIfV2UpdConnSetRspTx  OBJECT-TYPE
    SYNTAX      Counter64
    MAX-ACCESS  read-only
    STATUS      current
    DESCRIPTION
    "Number of GTP V2 Update Connection set Responses Sent."
    ::= { jnxMbgPgwGtpIfStatsEntry 56 }

jnxMbgPgwIfV2ModBrCmdRx  OBJECT-TYPE
    SYNTAX      Counter64
    MAX-ACCESS  read-only
    STATUS      current
    DESCRIPTION
    "Number of GTP V2 Modify Bearer Command received."
    ::= { jnxMbgPgwGtpIfStatsEntry 57 }

jnxMbgPgwIfV2ModBrCmdTx  OBJECT-TYPE
    SYNTAX      Counter64
    MAX-ACCESS  read-only
    STATUS      current
    DESCRIPTION
    "Number of GTP V2 Modify Bearer Command Sent."
    ::= { jnxMbgPgwGtpIfStatsEntry 58 }

jnxMbgPgwIfV2ModBrFlrIndRx  OBJECT-TYPE
    SYNTAX      Counter64
    MAX-ACCESS  read-only
    STATUS      current
    DESCRIPTION
    "Number of GTP V2 Modify Bearer Failure received."
    ::= { jnxMbgPgwGtpIfStatsEntry 59 }

jnxMbgPgwIfV2ModBrFlrIndTx  OBJECT-TYPE
    SYNTAX      Counter64
    MAX-ACCESS  read-only
    STATUS      current
    DESCRIPTION
    "Number of GTP V2 Modify Bearer Failure Sent."
    ::= { jnxMbgPgwGtpIfStatsEntry 60 }

jnxMbgPgwIfV2DelBrCmdRx  OBJECT-TYPE
    SYNTAX      Counter64
    MAX-ACCESS  read-only
    STATUS      current
    DESCRIPTION
    "Number of GTP V2 Delete Bearer Command received."
    ::= { jnxMbgPgwGtpIfStatsEntry 61 }

jnxMbgPgwIfV2DelBrCmdTx  OBJECT-TYPE
    SYNTAX      Counter64
    MAX-ACCESS  read-only
    STATUS      current
    DESCRIPTION
    "Number of GTP V2 Delete Bearer Command Sent."
    ::= { jnxMbgPgwGtpIfStatsEntry 62 }

jnxMbgPgwIfV2DelBrFlrIndRx  OBJECT-TYPE
    SYNTAX      Counter64
    MAX-ACCESS  read-only
    STATUS      current
    DESCRIPTION
    "Number of GTP V2 Delete Bearer Failure received."
    ::= { jnxMbgPgwGtpIfStatsEntry 63 }

jnxMbgPgwIfV2DelBrFlrIndTx  OBJECT-TYPE
    SYNTAX      Counter64
    MAX-ACCESS  read-only
    STATUS      current
    DESCRIPTION
    "Number of GTP V2 Delete Bearer Failure Sent."
    ::= { jnxMbgPgwGtpIfStatsEntry 64 }

jnxMbgPgwIfV2BrResCmdRx  OBJECT-TYPE
    SYNTAX      Counter64
    MAX-ACCESS  read-only
    STATUS      current
    DESCRIPTION
    "Number of GTP V2 Bearer Response Command received."
    ::= { jnxMbgPgwGtpIfStatsEntry 65 }

jnxMbgPgwIfV2BrResCmdTx  OBJECT-TYPE
    SYNTAX      Counter64
    MAX-ACCESS  read-only
    STATUS      current
    DESCRIPTION
    "Number of GTP V2 Bearer Response Command Sent."
    ::= { jnxMbgPgwGtpIfStatsEntry 66 }

jnxMbgPgwIfV2BrResFlrIndRx  OBJECT-TYPE
    SYNTAX      Counter64
    MAX-ACCESS  read-only
    STATUS      current
    DESCRIPTION
    "Number of GTP V2 Bearer Resource Failure received."
    ::= { jnxMbgPgwGtpIfStatsEntry 67 }

jnxMbgPgwIfV2BrResFlrIndTx  OBJECT-TYPE
    SYNTAX      Counter64
    MAX-ACCESS  read-only
    STATUS      current
    DESCRIPTION
    "Number of GTP V2 Bearer Resource Failure Sent."
    ::= { jnxMbgPgwGtpIfStatsEntry 68 }

jnxMbgPgwIfV2ICsReqAcceptRx  OBJECT-TYPE
    SYNTAX      Counter64
    MAX-ACCESS  read-only
    STATUS      current
    DESCRIPTION
    "Number of GTPV2 packets received with cause Request Accept."
    ::= { jnxMbgPgwGtpIfStatsEntry 69 }

jnxMbgPgwIfV2ICsReqAcceptTx  OBJECT-TYPE
    SYNTAX      Counter64
    MAX-ACCESS  read-only
    STATUS      current
    DESCRIPTION
    "Number of GTPV2 packets sent with cause Request Accept messsges sent."
    ::= { jnxMbgPgwGtpIfStatsEntry 70 }

jnxMbgPgwIfV2ICsAcceptPartRx  OBJECT-TYPE
    SYNTAX      Counter64
    MAX-ACCESS  read-only
    STATUS      current
    DESCRIPTION
    "Number of GTPV2 packets received with cause Accept Partial messages receive."
    ::= { jnxMbgPgwGtpIfStatsEntry 71 }

jnxMbgPgwIfV2ICsAcceptPartTx  OBJECT-TYPE
    SYNTAX      Counter64
    MAX-ACCESS  read-only
    STATUS      current
    DESCRIPTION
    "Number of GTPV2 packets sent with cause Accept Partial."
    ::= { jnxMbgPgwGtpIfStatsEntry 72 }

jnxMbgPgwIfV2ICsNewPTNPrefRx  OBJECT-TYPE
    SYNTAX      Counter64
    MAX-ACCESS  read-only
    STATUS      current
    DESCRIPTION
    "Number of GTPV2 packets received with cause New PDN type due to Network Preference."
    ::= { jnxMbgPgwGtpIfStatsEntry 73 }

jnxMbgPgwIfV2ICsNewPTNPrefTx  OBJECT-TYPE
    SYNTAX      Counter64
    MAX-ACCESS  read-only
    STATUS      current
    DESCRIPTION
    "Number of GTPV2 packets sent with cause New PDN type due to Network Preference."
    ::= { jnxMbgPgwGtpIfStatsEntry 74 }


jnxMbgPgwIfV2ICsNewPTSIAdbrRx  OBJECT-TYPE
    SYNTAX      Counter64
    MAX-ACCESS  read-only
    STATUS      current
    DESCRIPTION
    "Number of GTPV2 packets received with cause New PDN type due to Single Address Bearer."
    ::= { jnxMbgPgwGtpIfStatsEntry 75 }

jnxMbgPgwIfV2ICsNewPTSIAdbrTx  OBJECT-TYPE
    SYNTAX      Counter64
    MAX-ACCESS  read-only
    STATUS      current
    DESCRIPTION
    "Number of GTPV2 packets sent with cause New PDN type due to Single Address Bearer."
    ::= { jnxMbgPgwGtpIfStatsEntry 76 }

jnxMbgPgwIfV2ICsCtxNotFndRx  OBJECT-TYPE
    SYNTAX      Counter64
    MAX-ACCESS  read-only
    STATUS      current
    DESCRIPTION
    "Number of  GTPV2 packets received with cause Context not found."
    ::= { jnxMbgPgwGtpIfStatsEntry 77 }

jnxMbgPgwIfV2ICsCtxNotFndTx  OBJECT-TYPE
    SYNTAX      Counter64
    MAX-ACCESS  read-only
    STATUS      current
    DESCRIPTION
    "Number of GTPV2 packets sent with cause Context not found."
    ::= { jnxMbgPgwGtpIfStatsEntry 78 }

jnxMbgPgwIfV2ICsInvMsgFmtRx  OBJECT-TYPE
    SYNTAX      Counter64
    MAX-ACCESS  read-only
    STATUS      current
    DESCRIPTION
    "Number of GTPV2 packets received with cause Invalid Message Format."
    ::= { jnxMbgPgwGtpIfStatsEntry 79 }

jnxMbgPgwIfV2ICsInvMsgFmtTx  OBJECT-TYPE
    SYNTAX      Counter64
    MAX-ACCESS  read-only
    STATUS      current
    DESCRIPTION
    "Number of GTPV2 packets sent with cause Invalid Message Format."
    ::= { jnxMbgPgwGtpIfStatsEntry 80 }

jnxMbgPgwIfV2ICsVerNotSuppRx  OBJECT-TYPE
    SYNTAX      Counter64
    MAX-ACCESS  read-only
    STATUS      current
    DESCRIPTION
    "Number of GTPV2 packets received with cause Version not Supported."
    ::= { jnxMbgPgwGtpIfStatsEntry 81 }

jnxMbgPgwIfV2ICsVerNotSuppTx  OBJECT-TYPE
    SYNTAX      Counter64
    MAX-ACCESS  read-only
    STATUS      current
    DESCRIPTION
    "Number of GTPV2 packets sent with cause Version not Supported."
    ::= { jnxMbgPgwGtpIfStatsEntry 82 }

jnxMbgPgwIfV2ICsInvLenRx  OBJECT-TYPE
    SYNTAX      Counter64
    MAX-ACCESS  read-only
    STATUS      current
    DESCRIPTION
    "Number of GTPV2 packets received with cause Invalid Length."
    ::= { jnxMbgPgwGtpIfStatsEntry 83 }

jnxMbgPgwIfV2ICsInvLenTx  OBJECT-TYPE
    SYNTAX      Counter64
    MAX-ACCESS  read-only
    STATUS      current
    DESCRIPTION
    "Number of GTPV2 packets sent with cause Invalid Length."
    ::= { jnxMbgPgwGtpIfStatsEntry 84 }

jnxMbgPgwIfV2ICsServNotSuppRx  OBJECT-TYPE
    SYNTAX      Counter64
    MAX-ACCESS  read-only
    STATUS      current
    DESCRIPTION
    "Number of GTPV2 packets received with cause Service Not supported."
    ::= { jnxMbgPgwGtpIfStatsEntry 85 }

jnxMbgPgwIfV2ICsServNotSuppTx  OBJECT-TYPE
    SYNTAX      Counter64
    MAX-ACCESS  read-only
    STATUS      current
    DESCRIPTION
    "Number of GTPV2 packets sent with cause Service Not supported."
    ::= { jnxMbgPgwGtpIfStatsEntry 86 }

jnxMbgPgwIfV2ICsManIEIncorrRx  OBJECT-TYPE
    SYNTAX      Counter64
    MAX-ACCESS  read-only
    STATUS      current
    DESCRIPTION
    "Number of GTPV2 packets received with cause Mandatory IE incorrect."
    ::= { jnxMbgPgwGtpIfStatsEntry 87 }

jnxMbgPgwIfV2ICsManIEIncorrTx  OBJECT-TYPE
    SYNTAX      Counter64
    MAX-ACCESS  read-only
    STATUS      current
    DESCRIPTION
    "Number of GTPV2 packets sent with cause Mandatory IE incorrect."
    ::= { jnxMbgPgwGtpIfStatsEntry 88 }

jnxMbgPgwIfV2ICsManIEMissRx  OBJECT-TYPE
    SYNTAX      Counter64
    MAX-ACCESS  read-only
    STATUS      current
    DESCRIPTION
    "Number of GTPV2 packets received with cause Mandatory IE Missing."
    ::= { jnxMbgPgwGtpIfStatsEntry 89 }

jnxMbgPgwIfV2ICsManIEMissTx  OBJECT-TYPE
    SYNTAX      Counter64
    MAX-ACCESS  read-only
    STATUS      current
    DESCRIPTION
    "Number of GTPV2 packets sent with cause Mandatory IE Missing."
    ::= { jnxMbgPgwGtpIfStatsEntry 90 }

jnxMbgPgwIfV2ICsOptIEIncorrRx  OBJECT-TYPE
    SYNTAX      Counter64
    MAX-ACCESS  read-only
    STATUS      current
    DESCRIPTION
    "Number of GTPV2 packets received with cause Optional IE Incorrect."
    ::= { jnxMbgPgwGtpIfStatsEntry 91 }

jnxMbgPgwIfV2ICsOptIEIncorrTx  OBJECT-TYPE
    SYNTAX      Counter64
    MAX-ACCESS  read-only
    STATUS      current
    DESCRIPTION
    "Number of GTPV2 packets sent with cause Optional IE Incorrect."
    ::= { jnxMbgPgwGtpIfStatsEntry 92 }

jnxMbgPgwIfV2ICsSysFailRx  OBJECT-TYPE
    SYNTAX      Counter64
    MAX-ACCESS  read-only
    STATUS      current
    DESCRIPTION
    "Number of GTPV2 packets received with cause System Failure."
    ::= { jnxMbgPgwGtpIfStatsEntry 93 }

jnxMbgPgwIfV2ICsSysFailTx  OBJECT-TYPE
    SYNTAX      Counter64
    MAX-ACCESS  read-only
    STATUS      current
    DESCRIPTION
    "Number of GTPV2 packets sent with cause System Failure."
    ::= { jnxMbgPgwGtpIfStatsEntry 94 }

jnxMbgPgwIfV2ICsNoResRx  OBJECT-TYPE
    SYNTAX      Counter64
    MAX-ACCESS  read-only
    STATUS      current
    DESCRIPTION
    "Number of GTPV2 packets received with cause No Resource."
    ::= { jnxMbgPgwGtpIfStatsEntry 95 }

jnxMbgPgwIfV2ICsNoResTx  OBJECT-TYPE
    SYNTAX      Counter64
    MAX-ACCESS  read-only
    STATUS      current
    DESCRIPTION
    "Number of GTPV2 packets sent with cause No Resource."
    ::= { jnxMbgPgwGtpIfStatsEntry 96 }

jnxMbgPgwIfV2ICsTFTSMANTErRx  OBJECT-TYPE
    SYNTAX      Counter64
    MAX-ACCESS  read-only
    STATUS      current
    DESCRIPTION
    "Number of GTPV2 packets received with cause TFT Symantic Error."
    ::= { jnxMbgPgwGtpIfStatsEntry 97 }

jnxMbgPgwIfV2ICsTFTSMANTErTx  OBJECT-TYPE
    SYNTAX      Counter64
    MAX-ACCESS  read-only
    STATUS      current
    DESCRIPTION
    "Number of GTPV2 packets sent with cause TFT Symantic Error."
    ::= { jnxMbgPgwGtpIfStatsEntry 98 }

jnxMbgPgwIfV2ICsTFTSysErrRx  OBJECT-TYPE
    SYNTAX      Counter64
    MAX-ACCESS  read-only
    STATUS      current
    DESCRIPTION
    "Number of GTPV2 packets received with cause TFT System Error."
    ::= { jnxMbgPgwGtpIfStatsEntry 99 }

jnxMbgPgwIfV2ICsTFTSysErrTx  OBJECT-TYPE
    SYNTAX      Counter64
    MAX-ACCESS  read-only
    STATUS      current
    DESCRIPTION
    "Number of GTPV2 packets sent with cause TFT System Error."
    ::= { jnxMbgPgwGtpIfStatsEntry 100 }

jnxMbgPgwIfV2ICsPkFltManErrRx  OBJECT-TYPE
    SYNTAX      Counter64
    MAX-ACCESS  read-only
    STATUS      current
    DESCRIPTION
    "Number of GTPV2 packets received with cause Packet Filter Symantic Error."
    ::= { jnxMbgPgwGtpIfStatsEntry 101 }

jnxMbgPgwIfV2ICsPkFltManErrTx  OBJECT-TYPE
    SYNTAX      Counter64
    MAX-ACCESS  read-only
    STATUS      current
    DESCRIPTION
    "Number of GTPV2 packets sent with cause Packet Filter Symantic Error."
    ::= { jnxMbgPgwGtpIfStatsEntry 102 }

jnxMbgPgwIfV2ICsPkFltSynErrRx  OBJECT-TYPE
    SYNTAX      Counter64
    MAX-ACCESS  read-only
    STATUS      current
    DESCRIPTION
    "Number of GTPV2 packets received with cause Packet Filter Syntax Error."
    ::= { jnxMbgPgwGtpIfStatsEntry 103 }

jnxMbgPgwIfV2ICsPkFltSynErrTx  OBJECT-TYPE
    SYNTAX      Counter64
    MAX-ACCESS  read-only
    STATUS      current
    DESCRIPTION
    "Number of GTPV2 packets sent with cause Packet Filter Syntax Error."
    ::= { jnxMbgPgwGtpIfStatsEntry 104 }

jnxMbgPgwIfV2ICsMisUnknAPNRx  OBJECT-TYPE
    SYNTAX      Counter64
    MAX-ACCESS  read-only
    STATUS      current
    DESCRIPTION
    "Number of GTPV2 packets received with cause Unknown APN."
    ::= { jnxMbgPgwGtpIfStatsEntry 105 }

jnxMbgPgwIfV2ICsMisUnknAPNTx  OBJECT-TYPE
    SYNTAX      Counter64
    MAX-ACCESS  read-only
    STATUS      current
    DESCRIPTION
    "Number of GTPV2 packets sent with cause Unknown APN."
    ::= { jnxMbgPgwGtpIfStatsEntry 106 }

jnxMbgPgwIfV2ICsUnexpRptIERx  OBJECT-TYPE
    SYNTAX      Counter64
    MAX-ACCESS  read-only
    STATUS      current
    DESCRIPTION
    "Number of GTPV2 packets received with cause Unexpected Repeated IE."
    ::= { jnxMbgPgwGtpIfStatsEntry 107 }

jnxMbgPgwIfV2ICsUnexpRptIETx  OBJECT-TYPE
    SYNTAX      Counter64
    MAX-ACCESS  read-only
    STATUS      current
    DESCRIPTION
    "Number of GTPV2 packets sent with cause Unexpected Repeated IE."
    ::= { jnxMbgPgwGtpIfStatsEntry 108 }

jnxMbgPgwIfV2ICsGREKeyNtFdRx  OBJECT-TYPE
    SYNTAX      Counter64
    MAX-ACCESS  read-only
    STATUS      current
    DESCRIPTION
    "Number of GTPV2 packets received with cause GRE Key Not Found."
    ::= { jnxMbgPgwGtpIfStatsEntry 109 }

jnxMbgPgwIfV2ICsGREKeyNtFdTx  OBJECT-TYPE
    SYNTAX      Counter64
    MAX-ACCESS  read-only
    STATUS      current
    DESCRIPTION
    "Number of GTPV2 packets sent with cause GRE Key Not Found."
    ::= { jnxMbgPgwGtpIfStatsEntry 110 }

jnxMbgPgwIfV2ICsRelocFailRx  OBJECT-TYPE
    SYNTAX      Counter64
    MAX-ACCESS  read-only
    STATUS      current
    DESCRIPTION
    "Number of GTPV2 packets received with cause Relocation Failed."
    ::= { jnxMbgPgwGtpIfStatsEntry 111 }

jnxMbgPgwIfV2ICsRelocFailTx  OBJECT-TYPE
    SYNTAX      Counter64
    MAX-ACCESS  read-only
    STATUS      current
    DESCRIPTION
    "Number of GTPV2 packets sent with cause Relocation Failed."
    ::= { jnxMbgPgwGtpIfStatsEntry 112 }

jnxMbgPgwIfV2ICsDeniedINRatRx  OBJECT-TYPE
    SYNTAX      Counter64
    MAX-ACCESS  read-only
    STATUS      current
    DESCRIPTION
    "Number of GTPV2 packets received with cause Denied in RAT."
    ::= { jnxMbgPgwGtpIfStatsEntry 113 }

jnxMbgPgwIfV2ICsDeniedINRatTx  OBJECT-TYPE
    SYNTAX      Counter64
    MAX-ACCESS  read-only
    STATUS      current
    DESCRIPTION
    "Number of GTPV2 packets sent with cause Denied in RAT."
    ::= { jnxMbgPgwGtpIfStatsEntry 114 }

jnxMbgPgwIfV2ICsPTNotSuppRx  OBJECT-TYPE
    SYNTAX      Counter64
    MAX-ACCESS  read-only
    STATUS      current
    DESCRIPTION
    "Number of GTPV2 packets received with cause PDN Type Not Supported."
    ::= { jnxMbgPgwGtpIfStatsEntry 115 }

jnxMbgPgwIfV2ICsPTNotSuppTx  OBJECT-TYPE
    SYNTAX      Counter64
    MAX-ACCESS  read-only
    STATUS      current
    DESCRIPTION
    "Number of GTPV2 packets sent with cause PDN Type Not Supported."
    ::= { jnxMbgPgwGtpIfStatsEntry 116 }

jnxMbgPgwIfV2ICsAllDynAdOccRx  OBJECT-TYPE
    SYNTAX      Counter64
    MAX-ACCESS  read-only
    STATUS      current
    DESCRIPTION
    "Number of GTPV2 packets received with cause Allocated Dynamic Address Occupied."
    ::= { jnxMbgPgwGtpIfStatsEntry 117 }

jnxMbgPgwIfV2ICsAllDynAdOccTx  OBJECT-TYPE
    SYNTAX      Counter64
    MAX-ACCESS  read-only
    STATUS      current
    DESCRIPTION
    "Number of GTPV2 packets sent with cause Allocated Dynamic Address Occupied."
    ::= { jnxMbgPgwGtpIfStatsEntry 118 }

jnxMbgPgwIfV2ICsNOTFTUECTXRx  OBJECT-TYPE
    SYNTAX      Counter64
    MAX-ACCESS  read-only
    STATUS      current
    DESCRIPTION
    "Number of GTPV2 packets received with cause UE Context Without TFT Exists."
    ::= { jnxMbgPgwGtpIfStatsEntry 119 }

jnxMbgPgwIfV2ICsNOTFTUECTXTx  OBJECT-TYPE
    SYNTAX      Counter64
    MAX-ACCESS  read-only
    STATUS      current
    DESCRIPTION
    "Number of GTPV2 packets sent with cause UE Context Without TFT Exists."
    ::= { jnxMbgPgwGtpIfStatsEntry 120 }

jnxMbgPgwIfV2ICsProtoNtSupRx  OBJECT-TYPE
    SYNTAX      Counter64
    MAX-ACCESS  read-only
    STATUS      current
    DESCRIPTION
    "Number of GTPV2 packets received with cause Protocol Not Supported."
    ::= { jnxMbgPgwGtpIfStatsEntry 121 }

jnxMbgPgwIfV2ICsProtoNtSupTx  OBJECT-TYPE
    SYNTAX      Counter64
    MAX-ACCESS  read-only
    STATUS      current
    DESCRIPTION
    "Number of GTPV2 packets sent with cause Protocol Not Supported."
    ::= { jnxMbgPgwGtpIfStatsEntry 122 }

jnxMbgPgwIfV2ICsUENotRespRx  OBJECT-TYPE
    SYNTAX      Counter64
    MAX-ACCESS  read-only
    STATUS      current
    DESCRIPTION
    "Number of GTPV2 packets received with cause UE Not Responding."
    ::= { jnxMbgPgwGtpIfStatsEntry 123 }

jnxMbgPgwIfV2ICsUENotRespTx  OBJECT-TYPE
    SYNTAX      Counter64
    MAX-ACCESS  read-only
    STATUS      current
    DESCRIPTION
    "Number of GTPV2 packets sent with cause UE Not Responding."
    ::= { jnxMbgPgwGtpIfStatsEntry 124 }

jnxMbgPgwIfV2ICsUERefusesRx  OBJECT-TYPE
    SYNTAX      Counter64
    MAX-ACCESS  read-only
    STATUS      current
    DESCRIPTION
    "Number of GTPV2 packets received with cause UE Refuses."
    ::= { jnxMbgPgwGtpIfStatsEntry 125 }

jnxMbgPgwIfV2ICsUERefusesTx  OBJECT-TYPE
    SYNTAX      Counter64
    MAX-ACCESS  read-only
    STATUS      current
    DESCRIPTION
    "Number of GTPV2 packets sent with cause UE Refuses."
    ::= { jnxMbgPgwGtpIfStatsEntry 126 }

jnxMbgPgwIfV2ICsServDeniedRx  OBJECT-TYPE
    SYNTAX      Counter64
    MAX-ACCESS  read-only
    STATUS      current
    DESCRIPTION
    "Number of GTPV2 packets received with cause Service Denied."
    ::= { jnxMbgPgwGtpIfStatsEntry 127 }

jnxMbgPgwIfV2ICsServDeniedTx  OBJECT-TYPE
    SYNTAX      Counter64
    MAX-ACCESS  read-only
    STATUS      current
    DESCRIPTION
    "Number of GTPV2 packets sent with cause Service Denied."
    ::= { jnxMbgPgwGtpIfStatsEntry 128 }

jnxMbgPgwIfV2ICsUnabPageUERx  OBJECT-TYPE
    SYNTAX      Counter64
    MAX-ACCESS  read-only
    STATUS      current
    DESCRIPTION
    "Number of GTPV2 packets received with cause Unable to Page UE."
    ::= { jnxMbgPgwGtpIfStatsEntry 129 }

jnxMbgPgwIfV2ICsUnabPageUETx  OBJECT-TYPE
    SYNTAX      Counter64
    MAX-ACCESS  read-only
    STATUS      current
    DESCRIPTION
    "Number of GTPV2 packets sent with cause Unable to Page UE."
    ::= { jnxMbgPgwGtpIfStatsEntry 130 }

jnxMbgPgwIfV2ICsNoMemRx  OBJECT-TYPE
    SYNTAX      Counter64
    MAX-ACCESS  read-only
    STATUS      current
    DESCRIPTION
    "Number of GTPV2 packets received with cause No Memory."
    ::= { jnxMbgPgwGtpIfStatsEntry 131 }

jnxMbgPgwIfV2ICsNoMemTx  OBJECT-TYPE
    SYNTAX      Counter64
    MAX-ACCESS  read-only
    STATUS      current
    DESCRIPTION
    "Number of GTPV2 packets sent with cause No Memory."
    ::= { jnxMbgPgwGtpIfStatsEntry 132 }

jnxMbgPgwIfV2ICsUserAUTHFlRx  OBJECT-TYPE
    SYNTAX      Counter64
    MAX-ACCESS  read-only
    STATUS      current
    DESCRIPTION
    "Number of GTPV2 packets received with cause User AUTH Failed."
    ::= { jnxMbgPgwGtpIfStatsEntry 133 }

jnxMbgPgwIfV2ICsUserAUTHFlTx  OBJECT-TYPE
    SYNTAX      Counter64
    MAX-ACCESS  read-only
    STATUS      current
    DESCRIPTION
    "Number of GTPV2 packets sent with cause User AUTH Failed."
    ::= { jnxMbgPgwGtpIfStatsEntry 134 }

jnxMbgPgwIfV2ICsAPNAcsDenRx  OBJECT-TYPE
    SYNTAX      Counter64
    MAX-ACCESS  read-only
    STATUS      current
    DESCRIPTION
    "Number of GTPV2 packets received with cause APN Access Denied."
    ::= { jnxMbgPgwGtpIfStatsEntry 135 }

jnxMbgPgwIfV2ICsAPNAcsDenTx  OBJECT-TYPE
    SYNTAX      Counter64
    MAX-ACCESS  read-only
    STATUS      current
    DESCRIPTION
    "Number of GTPV2 packets sent with cause APN Access Denied."
    ::= { jnxMbgPgwGtpIfStatsEntry 136 }

jnxMbgPgwIfV2ICsReqRejRx  OBJECT-TYPE
    SYNTAX      Counter64
    MAX-ACCESS  read-only
    STATUS      current
    DESCRIPTION
    "Number of GTPV2 packets received with cause Request Rejected."
    ::= { jnxMbgPgwGtpIfStatsEntry 137 }

jnxMbgPgwIfV2ICsReqRejTx  OBJECT-TYPE
    SYNTAX      Counter64
    MAX-ACCESS  read-only
    STATUS      current
    DESCRIPTION
    "Number of GTPV2 packets sent with cause Request Rejected."
    ::= { jnxMbgPgwGtpIfStatsEntry 138 }

jnxMbgPgwIfV2ICsPTMSISigMMRx OBJECT-TYPE
     SYNTAX      Counter64
     MAX-ACCESS  read-only
     STATUS      current
     DESCRIPTION
     "Number of GTPV2 packets received with cause P-TMSI Signature Mismatc."
    ::= { jnxMbgPgwGtpIfStatsEntry 139 }

jnxMbgPgwIfV2ICsPTMSISigMMTx OBJECT-TYPE
     SYNTAX      Counter64
     MAX-ACCESS  read-only
     STATUS      current
     DESCRIPTION
     "Number of GTPV2 packets sent with cause P-TMSI Signature Mismatch"
    ::= { jnxMbgPgwGtpIfStatsEntry 140 }

jnxMbgPgwIfV2ICsIMSINotKnRx OBJECT-TYPE
      SYNTAX      Counter64
      MAX-ACCESS  read-only
      STATUS      current
      DESCRIPTION
      "Number of GTPV2 packets received with cause IMSI Not Known."
    ::= { jnxMbgPgwGtpIfStatsEntry 141 }

jnxMbgPgwIfV2ICsIMSINotKnTx OBJECT-TYPE
      SYNTAX      Counter64
      MAX-ACCESS  read-only
      STATUS      current
      DESCRIPTION
      "Number of GTPV2 packets sent with cause IMSI Not Known."
    ::= { jnxMbgPgwGtpIfStatsEntry 142 }

jnxMbgPgwIfV2ICsCondIEMsRx OBJECT-TYPE
       SYNTAX      Counter64
       MAX-ACCESS  read-only
       STATUS      current
       DESCRIPTION
       "Number of GTPV2 packets received with cause Conditional IE Missing."
     ::= { jnxMbgPgwGtpIfStatsEntry 143 }

jnxMbgPgwIfV2ICsCondIEMsTx OBJECT-TYPE
       SYNTAX      Counter64
       MAX-ACCESS  read-only
       STATUS      current
       DESCRIPTION
       "Number of GTPV2 packets sent with cause Conditional IE Missing."
     ::= { jnxMbgPgwGtpIfStatsEntry 144 }

jnxMbgPgwIfV2ICsAPNResTIncRx OBJECT-TYPE
        SYNTAX      Counter64
        MAX-ACCESS  read-only
        STATUS      current
        DESCRIPTION
        "Number of GTPV2 packets received with cause APN Restriction Type Incompatible"
     ::= { jnxMbgPgwGtpIfStatsEntry 145 }

jnxMbgPgwIfV2ICsAPNResTIncTx OBJECT-TYPE
        SYNTAX      Counter64
        MAX-ACCESS  read-only
        STATUS      current
        DESCRIPTION
        "Number of GTPV2 packets sent with cause APN Restriction Type Incompatible"
     ::= { jnxMbgPgwGtpIfStatsEntry 146 }

jnxMbgPgwIfV2ICsUnknownRx OBJECT-TYPE
         SYNTAX      Counter64
         MAX-ACCESS  read-only
         STATUS      current
         DESCRIPTION
         "Number of GTPV2 packets received with cause Unknown"
     ::= { jnxMbgPgwGtpIfStatsEntry 147 }

jnxMbgPgwIfV2ICsUnknownTx OBJECT-TYPE
         SYNTAX      Counter64
         MAX-ACCESS  read-only
         STATUS      current
         DESCRIPTION
         "Number of GTPV2 packets sent with cause Unknown"
     ::= { jnxMbgPgwGtpIfStatsEntry 148 }

jnxMbgPgwIfV1ProtocolErrRx  OBJECT-TYPE
    SYNTAX      Counter64
    MAX-ACCESS  read-only
    STATUS      current
    DESCRIPTION
    "Number of GTPv2 Protocol Errors Received."
    ::= { jnxMbgPgwGtpIfStatsEntry 149 }

jnxMbgPgwIfV1UnSupportedMsgRx  OBJECT-TYPE
    SYNTAX      Counter64
    MAX-ACCESS  read-only
    STATUS      current
    DESCRIPTION
    "Number of GTPv2 Unsupported Messages received."
    ::= { jnxMbgPgwGtpIfStatsEntry 150 }

jnxMbgPgwIfV1T3RespTmrExpRx  OBJECT-TYPE
    SYNTAX      Counter64
    MAX-ACCESS  read-only
    STATUS      current
    DESCRIPTION
    "Number of GTP V1 T3 timer expiries Received."
    ::= { jnxMbgPgwGtpIfStatsEntry 151 }

jnxMbgPgwIfV1GlbNumMsgRx  OBJECT-TYPE
    SYNTAX      Counter64
    MAX-ACCESS  read-only
    STATUS      current
    DESCRIPTION
    "Number of GTPv1 messages received."
    ::= { jnxMbgPgwGtpIfStatsEntry 152 }

jnxMbgPgwIfV1GlbNumMsgTx  OBJECT-TYPE
    SYNTAX      Counter64
    MAX-ACCESS  read-only
    STATUS      current
    DESCRIPTION
    "Number of GTP V1 messages sent."
    ::= { jnxMbgPgwGtpIfStatsEntry 153 }

jnxMbgPgwIfV1GlbNumBytesRx  OBJECT-TYPE
    SYNTAX      Counter64
    MAX-ACCESS  read-only
    STATUS      current
    DESCRIPTION
    "Number of GTPv1 bytes received."
    ::= { jnxMbgPgwGtpIfStatsEntry 154 }

jnxMbgPgwIfV1GlbNumBytesTx  OBJECT-TYPE
    SYNTAX      Counter64
    MAX-ACCESS  read-only
    STATUS      current
    DESCRIPTION
    "Number of GTP V1 bytes sent."
    ::= { jnxMbgPgwGtpIfStatsEntry 155 }

jnxMbgPgwIfV1GlbEchoReqRx  OBJECT-TYPE
    SYNTAX      Counter64
    MAX-ACCESS  read-only
    STATUS      current
    DESCRIPTION
    "Number of GTP V1 Echo Requests received."
    ::= { jnxMbgPgwGtpIfStatsEntry 156 }

jnxMbgPgwIfV1GlbEchoReqTx  OBJECT-TYPE
    SYNTAX      Counter64
    MAX-ACCESS  read-only
    STATUS      current
    DESCRIPTION
    "Number of GTP V1 Echo Requests Sent."
    ::= { jnxMbgPgwGtpIfStatsEntry 157 }

jnxMbgPgwIfV1GlbEchoRespRx  OBJECT-TYPE
    SYNTAX      Counter64
    MAX-ACCESS  read-only
    STATUS      current
    DESCRIPTION
    "Number of GTP V1 Echo Responses received."
    ::= { jnxMbgPgwGtpIfStatsEntry 158 }

jnxMbgPgwIfV1GlbEchoRespTx  OBJECT-TYPE
    SYNTAX      Counter64
    MAX-ACCESS  read-only
    STATUS      current
    DESCRIPTION
    "Number of GTP V1 Echo Responses Sent."
    ::= { jnxMbgPgwGtpIfStatsEntry 159 }

jnxMbgPgwIfV1VerNotSupRx OBJECT-TYPE
    SYNTAX      Counter64
    MAX-ACCESS  read-only
    STATUS      current
    DESCRIPTION
    "Number of GTP V1 Version Not supported messages received"
    ::= { jnxMbgPgwGtpIfStatsEntry 160 }

jnxMbgPgwIfV1VerNotSupTx OBJECT-TYPE
    SYNTAX      Counter64
    MAX-ACCESS  read-only
    STATUS      current
    DESCRIPTION
    "Number of GTP V1 version not supported messages Sent."
    ::= { jnxMbgPgwGtpIfStatsEntry 161 }

jnxMbgPgwIfV1CrtPdpCxtReqRx   OBJECT-TYPE
    SYNTAX      Counter64
    MAX-ACCESS  read-only
    STATUS      current
    DESCRIPTION
    "Number of GTP V1 Create PDP Context Requests Received."
    ::= { jnxMbgPgwGtpIfStatsEntry 162 }

jnxMbgPgwIfV1CrtPdpCxtReqTx   OBJECT-TYPE
    SYNTAX      Counter64
    MAX-ACCESS  read-only
    STATUS      current
    DESCRIPTION
    "Number of GTP V1 Create PDP Context Requests Sent."
    ::= { jnxMbgPgwGtpIfStatsEntry 163 }

jnxMbgPgwIfV1CrtPdpCxtRspRx   OBJECT-TYPE
    SYNTAX      Counter64
    MAX-ACCESS  read-only
    STATUS      current
    DESCRIPTION
    "Number of GTP V1 Create PDP Context Responses Received."
    ::= { jnxMbgPgwGtpIfStatsEntry 164 }

jnxMbgPgwIfV1CrtPdpCxtRspTx   OBJECT-TYPE
    SYNTAX      Counter64
    MAX-ACCESS  read-only
    STATUS      current
    DESCRIPTION
    "Number of GTP V1 Create PDP Context Responses Sent."
    ::= { jnxMbgPgwGtpIfStatsEntry 165 }

jnxMbgPgwIfV1UpdPdpCxtReqRx   OBJECT-TYPE
    SYNTAX      Counter64
    MAX-ACCESS  read-only
    STATUS      current
    DESCRIPTION
    "Number of GTP V1 Update PDP Context Requests Received."
    ::= { jnxMbgPgwGtpIfStatsEntry 166 }

jnxMbgPgwIfV1UpdPdpCxtReqTx   OBJECT-TYPE
    SYNTAX      Counter64
    MAX-ACCESS  read-only
    STATUS      current
    DESCRIPTION
    "Number of GTP V1 Update PDP Context Requests Sent."
    ::= { jnxMbgPgwGtpIfStatsEntry 167 }

jnxMbgPgwIfV1UpdPdpCxtRspRx   OBJECT-TYPE
    SYNTAX      Counter64
    MAX-ACCESS  read-only
    STATUS      current
    DESCRIPTION
    "Number of GTP V1 Update PDP Context Responses Received."
    ::= { jnxMbgPgwGtpIfStatsEntry 168 }

jnxMbgPgwIfV1UpdPdpCxtRspTx   OBJECT-TYPE
    SYNTAX      Counter64
    MAX-ACCESS  read-only
    STATUS      current
    DESCRIPTION
    "Number of GTP V1 Update PDP Context Responses Sent."
    ::= { jnxMbgPgwGtpIfStatsEntry 169 }

jnxMbgPgwIfV1DelPdpCxtReqRx   OBJECT-TYPE
    SYNTAX      Counter64
    MAX-ACCESS  read-only
    STATUS      current
    DESCRIPTION
    "Number of GTP V1 Delete PDP Context Requests Received."
    ::= { jnxMbgPgwGtpIfStatsEntry 170 }

jnxMbgPgwIfV1DelPdpCxtReqTx   OBJECT-TYPE
    SYNTAX      Counter64
    MAX-ACCESS  read-only
    STATUS      current
    DESCRIPTION
    "Number of GTP V1 Delete PDP Context Requests Sent."
    ::= { jnxMbgPgwGtpIfStatsEntry 171 }

jnxMbgPgwIfV1DelPdpCxtRspRx   OBJECT-TYPE
    SYNTAX      Counter64
    MAX-ACCESS  read-only
    STATUS      current
    DESCRIPTION
    "Number of GTP V1 Delete PDP Context Responses Received."
    ::= { jnxMbgPgwGtpIfStatsEntry 172 }

jnxMbgPgwIfV1DelPdpCxtRspTx   OBJECT-TYPE
    SYNTAX      Counter64
    MAX-ACCESS  read-only
    STATUS      current
    DESCRIPTION
    "Number of GTP V1 Delete PDP Context Responses Sent."
    ::= { jnxMbgPgwGtpIfStatsEntry 173 }

jnxMbgPgwIfV1CrtAAPdpCxtReqRx   OBJECT-TYPE
    SYNTAX      Counter64
    MAX-ACCESS  read-only
    STATUS      current
    DESCRIPTION
    "Number of GTP V1 Create AA PDP Context Requests Received."
    ::= { jnxMbgPgwGtpIfStatsEntry 174 }

jnxMbgPgwIfV1CrtAAPdpCxtReqTx   OBJECT-TYPE
    SYNTAX      Counter64
    MAX-ACCESS  read-only
    STATUS      current
    DESCRIPTION
    "Number of GTP V1 Create AA PDP Context Requests Sent."
    ::= { jnxMbgPgwGtpIfStatsEntry 175 }

jnxMbgPgwIfV1CrtAAPdpCxtRspRx   OBJECT-TYPE
    SYNTAX      Counter64
    MAX-ACCESS  read-only
    STATUS      current
    DESCRIPTION
    "Number of GTP V1 Create AA PDP Context Responses Received."
    ::= { jnxMbgPgwGtpIfStatsEntry 176 }

jnxMbgPgwIfV1CrtAAPdpCxtRspTx   OBJECT-TYPE
    SYNTAX      Counter64
    MAX-ACCESS  read-only
    STATUS      current
    DESCRIPTION
    "Number of GTP V1 Create AA PDP Context Responses Sent."
    ::= { jnxMbgPgwGtpIfStatsEntry 177 }

jnxMbgPgwIfV1DelAAPdpCxtReqRx   OBJECT-TYPE
    SYNTAX      Counter64
    MAX-ACCESS  read-only
    STATUS      current
    DESCRIPTION
    "Number of GTP V1 Delete AA PDP Context Requests Received."
    ::= { jnxMbgPgwGtpIfStatsEntry 178 }

jnxMbgPgwIfV1DelAAPdpCxtReqTx   OBJECT-TYPE
    SYNTAX      Counter64
    MAX-ACCESS  read-only
    STATUS      current
    DESCRIPTION
    "Number of GTP V1 Delete AA PDP Context Requests Sent."
    ::= { jnxMbgPgwGtpIfStatsEntry 179 }

jnxMbgPgwIfV1DelAAPdpCxtRspRx   OBJECT-TYPE
    SYNTAX      Counter64
    MAX-ACCESS  read-only
    STATUS      current
    DESCRIPTION
    "Number of GTP V1 Delete AA PDP Context Responses Received."
    ::= { jnxMbgPgwGtpIfStatsEntry 180 }

jnxMbgPgwIfV1DelAAPdpCxtRspTx   OBJECT-TYPE
    SYNTAX      Counter64
    MAX-ACCESS  read-only
    STATUS      current
    DESCRIPTION
    "Number of GTP V1 Delete AA PDP Context Responses Sent."
    ::= { jnxMbgPgwGtpIfStatsEntry 181 }

jnxMbgPgwIfV1ErrorIndRx   OBJECT-TYPE
    SYNTAX      Counter64
    MAX-ACCESS  read-only
    STATUS      current
    DESCRIPTION
    "Number of GTP V1 Error Indication Received."
    ::= { jnxMbgPgwGtpIfStatsEntry 182 }

jnxMbgPgwIfV1ErrorIndTx   OBJECT-TYPE
    SYNTAX      Counter64
    MAX-ACCESS  read-only
    STATUS      current
    DESCRIPTION
    "Number of GTP V1 Error Indication Sent."
    ::= { jnxMbgPgwGtpIfStatsEntry 183 }

jnxMbgPgwIfV1NotifReqRx   OBJECT-TYPE
    SYNTAX      Counter64
    MAX-ACCESS  read-only
    STATUS      current
    DESCRIPTION
    "Number of GTP V1 Notify Requests Received."
    ::= { jnxMbgPgwGtpIfStatsEntry 184 }

jnxMbgPgwIfV1NotifReqTx   OBJECT-TYPE
    SYNTAX      Counter64
    MAX-ACCESS  read-only
    STATUS      current
    DESCRIPTION
    "Number of GTP V1 Notify Requests Sent."
    ::= { jnxMbgPgwGtpIfStatsEntry 185 }

jnxMbgPgwIfV1NotifRspRx   OBJECT-TYPE
    SYNTAX      Counter64
    MAX-ACCESS  read-only
    STATUS      current
    DESCRIPTION
    "Number of GTP V1 Notify Responses Received."
    ::= { jnxMbgPgwGtpIfStatsEntry 186 }

jnxMbgPgwIfV1NotifRspTx   OBJECT-TYPE
    SYNTAX      Counter64
    MAX-ACCESS  read-only
    STATUS      current
    DESCRIPTION
    "Number of GTP V1 Notify Responses Sent."
    ::= { jnxMbgPgwGtpIfStatsEntry 187 }

jnxMbgPgwIfV1NotifRejReqRx   OBJECT-TYPE
    SYNTAX      Counter64
    MAX-ACCESS  read-only
    STATUS      current
    DESCRIPTION
    "Number of GTP V1 Notify Reject Requests Received."
    ::= { jnxMbgPgwGtpIfStatsEntry 188 }

jnxMbgPgwIfV1NotifRejReqTx   OBJECT-TYPE
    SYNTAX      Counter64
    MAX-ACCESS  read-only
    STATUS      current
    DESCRIPTION
    "Number of GTP V1 Notify Reject Requests Sent."
    ::= { jnxMbgPgwGtpIfStatsEntry 189 }

jnxMbgPgwIfV1NotifRejRspRx   OBJECT-TYPE
    SYNTAX      Counter64
    MAX-ACCESS  read-only
    STATUS      current
    DESCRIPTION
    "Number of GTP V1 Notify Reject Responses Received."
    ::= { jnxMbgPgwGtpIfStatsEntry 190 }

jnxMbgPgwIfV1NotifRejRspTx   OBJECT-TYPE
    SYNTAX      Counter64
    MAX-ACCESS  read-only
    STATUS      current
    DESCRIPTION
    "Number of GTP V1 Notify Reject Responses Sent."
    ::= { jnxMbgPgwGtpIfStatsEntry 191 }

jnxMbgPgwIfV1RtInfReqRx   OBJECT-TYPE
    SYNTAX      Counter64
    MAX-ACCESS  read-only
    STATUS      current
    DESCRIPTION
    "Number of GTP V1 Routing Information Requests Received."
    ::= { jnxMbgPgwGtpIfStatsEntry 192 }

jnxMbgPgwIfV1RtInfReqTx   OBJECT-TYPE
    SYNTAX      Counter64
    MAX-ACCESS  read-only
    STATUS      current
    DESCRIPTION
    "Number of GTP V1 Routing Information Requests Sent."
    ::= { jnxMbgPgwGtpIfStatsEntry 193 }

jnxMbgPgwIfV1RtInfRspRx   OBJECT-TYPE
    SYNTAX      Counter64
    MAX-ACCESS  read-only
    STATUS      current
    DESCRIPTION
    "Number of GTP V1 Routing Information Responses Received."
    ::= { jnxMbgPgwGtpIfStatsEntry 194 }

jnxMbgPgwIfV1RtInfRspTx   OBJECT-TYPE
    SYNTAX      Counter64
    MAX-ACCESS  read-only
    STATUS      current
    DESCRIPTION
    "Number of GTP V1 Routing Information Responses Sent."
    ::= { jnxMbgPgwGtpIfStatsEntry 195 }

jnxMbgPgwIfV1FailRptReqRx   OBJECT-TYPE
    SYNTAX      Counter64
    MAX-ACCESS  read-only
    STATUS      current
    DESCRIPTION
    "Number of GTP V1 Fail Repeat Requests Received."
    ::= { jnxMbgPgwGtpIfStatsEntry 196 }

jnxMbgPgwIfV1FailRptReqTx   OBJECT-TYPE
    SYNTAX      Counter64
    MAX-ACCESS  read-only
    STATUS      current
    DESCRIPTION
    "Number of GTP V1 Fail Repeat Requests Sent."
    ::= { jnxMbgPgwGtpIfStatsEntry 197 }

jnxMbgPgwIfV1FailRptRspRx   OBJECT-TYPE
    SYNTAX      Counter64
    MAX-ACCESS  read-only
    STATUS      current
    DESCRIPTION
    "Number of GTP V1 Fail Repeat Responses Received."
    ::= { jnxMbgPgwGtpIfStatsEntry 198 }

jnxMbgPgwIfV1FailRptRspTx   OBJECT-TYPE
    SYNTAX      Counter64
    MAX-ACCESS  read-only
    STATUS      current
    DESCRIPTION
    "Number of GTP V1 Fail Repeat Responses Sent."
    ::= { jnxMbgPgwGtpIfStatsEntry 199 }

jnxMbgPgwIfV1NotMSPresReqRx   OBJECT-TYPE
    SYNTAX      Counter64
    MAX-ACCESS  read-only
    STATUS      current
    DESCRIPTION
    "Number of GTP V1 MS Not Present Request Received."
    ::= { jnxMbgPgwGtpIfStatsEntry 200 }

jnxMbgPgwIfV1NotMSPresReqTx   OBJECT-TYPE
    SYNTAX      Counter64
    MAX-ACCESS  read-only
    STATUS      current
    DESCRIPTION
    "Number of GTP V1 MS Not Present Request Sent."
    ::= { jnxMbgPgwGtpIfStatsEntry 201 }

jnxMbgPgwIfV1NotMSPresRspRx   OBJECT-TYPE
    SYNTAX      Counter64
    MAX-ACCESS  read-only
    STATUS      current
    DESCRIPTION
    "Number of GTP V1 MS Not Present Responses Received."
    ::= { jnxMbgPgwGtpIfStatsEntry 202 }

jnxMbgPgwIfV1NotMSPresRspTx   OBJECT-TYPE
    SYNTAX      Counter64
    MAX-ACCESS  read-only
    STATUS      current
    DESCRIPTION
    "Number of GTP V1 MS Not Present Responses Sent."
    ::= { jnxMbgPgwGtpIfStatsEntry 203 }

jnxMbgPgwIfV1ICsReqAcceptedRx   OBJECT-TYPE
    SYNTAX      Counter64
    MAX-ACCESS  read-only
    STATUS      current
    DESCRIPTION
    "Number of GTPV1 packets received with cause Request Accepted."
    ::= { jnxMbgPgwGtpIfStatsEntry 204 }

jnxMbgPgwIfV1ICsReqAcceptedTx   OBJECT-TYPE
    SYNTAX      Counter64
    MAX-ACCESS  read-only
    STATUS      current
    DESCRIPTION
    "Number of GTPV1 packets sent with cause Request Accepted."
    ::= { jnxMbgPgwGtpIfStatsEntry 205 }

jnxMbgPgwIfV1ICsNonExistRx   OBJECT-TYPE
    SYNTAX      Counter64
    MAX-ACCESS  read-only
    STATUS      current
    DESCRIPTION
    "Number of GTPV1 packets received with cause Non Existant."
    ::= { jnxMbgPgwGtpIfStatsEntry 206 }

jnxMbgPgwIfV1ICsNonExistTx   OBJECT-TYPE
    SYNTAX      Counter64
    MAX-ACCESS  read-only
    STATUS      current
    DESCRIPTION
    "Number of GTPV1 packets sent with cause Non Existant."
    ::= { jnxMbgPgwGtpIfStatsEntry 207 }

jnxMbgPgwIfV1ICsInvMsgFmtRx   OBJECT-TYPE
    SYNTAX      Counter64
    MAX-ACCESS  read-only
    STATUS      current
    DESCRIPTION
    "Number of GTPV1 packets received with cause Invalid Mesage Format."
    ::= { jnxMbgPgwGtpIfStatsEntry 208 }

jnxMbgPgwIfV1ICsInvMsgFmtTx   OBJECT-TYPE
    SYNTAX      Counter64
    MAX-ACCESS  read-only
    STATUS      current
    DESCRIPTION
    "Number of GTPV1 packets sent with cause Invalid Mesage Format."
    ::= { jnxMbgPgwGtpIfStatsEntry 209 }

jnxMbgPgwIfV1ICsIMSINotKnownRx   OBJECT-TYPE
    SYNTAX      Counter64
    MAX-ACCESS  read-only
    STATUS      current
    DESCRIPTION
    "Number of GTPV1 packets received with cause IMSI Not Known."
    ::= { jnxMbgPgwGtpIfStatsEntry 210 }


jnxMbgPgwIfV1ICsIMSINotKnownTx   OBJECT-TYPE
    SYNTAX      Counter64
    MAX-ACCESS  read-only
    STATUS      current
    DESCRIPTION
    "Number of GTPV1 packets sent with cause IMSI Not Known."
    ::= { jnxMbgPgwGtpIfStatsEntry 211 }

jnxMbgPgwIfV1ICsMSGRPSDetachRx   OBJECT-TYPE
    SYNTAX      Counter64
    MAX-ACCESS  read-only
    STATUS      current
    DESCRIPTION
    "Number of GTPV1 packets received with cause MS GPRS Detached."
    ::= { jnxMbgPgwGtpIfStatsEntry 212 }

jnxMbgPgwIfV1ICsMSGRPSDetachTx   OBJECT-TYPE
    SYNTAX      Counter64
    MAX-ACCESS  read-only
    STATUS      current
    DESCRIPTION
    "Number of GTPV1 packets sent with cause MS GPRS Detached."
    ::= { jnxMbgPgwGtpIfStatsEntry 213 }

jnxMbgPgwIfV1ICsMSNotGRPSRespRx   OBJECT-TYPE
    SYNTAX      Counter64
    MAX-ACCESS  read-only
    STATUS      current
    DESCRIPTION
    "Number of GTPV1 packets received with cause MS No GPRS Response."
    ::= { jnxMbgPgwGtpIfStatsEntry 214 }

jnxMbgPgwIfV1ICsMSNotGRPSRespTx   OBJECT-TYPE
    SYNTAX      Counter64
    MAX-ACCESS  read-only
    STATUS      current
    DESCRIPTION
    "Number of GTPV1 packets sent with cause MS No GPRS Response."
    ::= { jnxMbgPgwGtpIfStatsEntry 215 }

jnxMbgPgwIfV1ICsMSRefusesRx   OBJECT-TYPE
    SYNTAX      Counter64
    MAX-ACCESS  read-only
    STATUS      current
    DESCRIPTION
    "Number of GTPV1 packets received with cause MS Refues."
    ::= { jnxMbgPgwGtpIfStatsEntry 216 }

jnxMbgPgwIfV1ICsMSRefusesTx   OBJECT-TYPE
    SYNTAX      Counter64
    MAX-ACCESS  read-only
    STATUS      current
    DESCRIPTION
    "Number of GTPV1 packets sent with cause MS Refues."
    ::= { jnxMbgPgwGtpIfStatsEntry 217 }

jnxMbgPgwIfV1ICsVerNotSuppRx   OBJECT-TYPE
    SYNTAX      Counter64
    MAX-ACCESS  read-only
    STATUS      current
    DESCRIPTION
    "Number of GTPV1 packets received with cause Version Not Supported."
    ::= { jnxMbgPgwGtpIfStatsEntry 218 }

jnxMbgPgwIfV1ICsVerNotSuppTx   OBJECT-TYPE
    SYNTAX      Counter64
    MAX-ACCESS  read-only
    STATUS      current
    DESCRIPTION
    "Number of GTPV1 packets sent with cause Version Not Supported."
    ::= { jnxMbgPgwGtpIfStatsEntry 219 }

jnxMbgPgwIfV1ICsNoResRx   OBJECT-TYPE
    SYNTAX      Counter64
    MAX-ACCESS  read-only
    STATUS      current
    DESCRIPTION
    "Number of GTPV1 packets received with cause No Response."
    ::= { jnxMbgPgwGtpIfStatsEntry 220 }

jnxMbgPgwIfV1ICsNoResTx   OBJECT-TYPE
    SYNTAX      Counter64
    MAX-ACCESS  read-only
    STATUS      current
    DESCRIPTION
    "Number of GTPV1 packets sent with cause No Response."
    ::= { jnxMbgPgwGtpIfStatsEntry 221 }

jnxMbgPgwIfV1ICsServNotSuppRx   OBJECT-TYPE
    SYNTAX      Counter64
    MAX-ACCESS  read-only
    STATUS      current
    DESCRIPTION
    "Number of GTPV1 packets received with cause Service Not Supported."
    ::= { jnxMbgPgwGtpIfStatsEntry 222 }

jnxMbgPgwIfV1ICsServNotSuppTx   OBJECT-TYPE
    SYNTAX      Counter64
    MAX-ACCESS  read-only
    STATUS      current
    DESCRIPTION
    "Number of GTPV1 packets sent with cause Service Not Supported."
    ::= { jnxMbgPgwGtpIfStatsEntry 223 }

jnxMbgPgwIfV1ICsManIEIncrtRx   OBJECT-TYPE
    SYNTAX      Counter64
    MAX-ACCESS  read-only
    STATUS      current
    DESCRIPTION
    "Number of GTPV1 packets received with cause Mandatory IE incorrect."
    ::= { jnxMbgPgwGtpIfStatsEntry 224 }

jnxMbgPgwIfV1ICsManIEIncrtTx   OBJECT-TYPE
    SYNTAX      Counter64
    MAX-ACCESS  read-only
    STATUS      current
    DESCRIPTION
    "Number of GTPV1 packets sent with cause Mandatory IE incorrect."
    ::= { jnxMbgPgwGtpIfStatsEntry 225 }

jnxMbgPgwIfV1ICsManIEMissRx   OBJECT-TYPE
    SYNTAX      Counter64
    MAX-ACCESS  read-only
    STATUS      current
    DESCRIPTION
    "Number of GTPV1 packets received with cause Mandatory IE Missing."
    ::= { jnxMbgPgwGtpIfStatsEntry 226 }

jnxMbgPgwIfV1ICsManIEMissTx   OBJECT-TYPE
    SYNTAX      Counter64
    MAX-ACCESS  read-only
    STATUS      current
    DESCRIPTION
    "Number of GTPV1 packets sent with cause Mandatory IE Missing."
    ::= { jnxMbgPgwGtpIfStatsEntry 227 }

jnxMbgPgwIfV1ICsOptIEIncrtRx   OBJECT-TYPE
    SYNTAX      Counter64
    MAX-ACCESS  read-only
    STATUS      current
    DESCRIPTION
    "Number of GTPV1 packets received with cause Optional IE incorrect."
    ::= { jnxMbgPgwGtpIfStatsEntry 228 }

jnxMbgPgwIfV1ICsOptIEIncrtTx   OBJECT-TYPE
    SYNTAX      Counter64
    MAX-ACCESS  read-only
    STATUS      current
    DESCRIPTION
    "Number of GTPV1 packets sent with cause Optional IE incorrect."
    ::= { jnxMbgPgwGtpIfStatsEntry 229 }

jnxMbgPgwIfV1ICsSysFailRx   OBJECT-TYPE
    SYNTAX      Counter64
    MAX-ACCESS  read-only
    STATUS      current
    DESCRIPTION
    "Number of GTPV1 packets received with cause System Failure."
    ::= { jnxMbgPgwGtpIfStatsEntry 230 }

jnxMbgPgwIfV1ICsSysFailTx   OBJECT-TYPE
    SYNTAX      Counter64
    MAX-ACCESS  read-only
    STATUS      current
    DESCRIPTION
    "Number of GTPV1 packets sent with cause System Failure."
    ::= { jnxMbgPgwGtpIfStatsEntry 231 }

jnxMbgPgwIfV1ICsRoamRestrictRx   OBJECT-TYPE
    SYNTAX      Counter64
    MAX-ACCESS  read-only
    STATUS      current
    DESCRIPTION
    "Number of GTPV1 packets received with cause Roaming Restricted."
    ::= { jnxMbgPgwGtpIfStatsEntry 232 }

jnxMbgPgwIfV1ICsRoamRestrictTx   OBJECT-TYPE
    SYNTAX      Counter64
    MAX-ACCESS  read-only
    STATUS      current
    DESCRIPTION
    "Number of GTPV1 packets sent with cause Roaming Restricted."
    ::= { jnxMbgPgwGtpIfStatsEntry 233 }

jnxMbgPgwIfV1ICsPTMSISigMMRx   OBJECT-TYPE
    SYNTAX      Counter64
    MAX-ACCESS  read-only
    STATUS      current
    DESCRIPTION
    "Number of GTPV1 packets received with cause PTMSI Signature Mismatch."
    ::= { jnxMbgPgwGtpIfStatsEntry 234 }

jnxMbgPgwIfV1ICsPTMSISigMMTx   OBJECT-TYPE
    SYNTAX      Counter64
    MAX-ACCESS  read-only
    STATUS      current
    DESCRIPTION
    "Number of GTPV1 packets sent with cause PTMSI Signature Mismatch."
    ::= { jnxMbgPgwGtpIfStatsEntry 235 }

jnxMbgPgwIfV1ICsGPRSConnSuppRx   OBJECT-TYPE
    SYNTAX      Counter64
    MAX-ACCESS  read-only
    STATUS      current
    DESCRIPTION
    "Number of GTPV1 packets received with cause GPRS Connection Supported."
    ::= { jnxMbgPgwGtpIfStatsEntry 236 }

jnxMbgPgwIfV1ICsGPRSConnSuppTx   OBJECT-TYPE
    SYNTAX      Counter64
    MAX-ACCESS  read-only
    STATUS      current
    DESCRIPTION
    "Number of GTPV1 packets sent with cause GPRS Connection Supported."
    ::= { jnxMbgPgwGtpIfStatsEntry 237 }

jnxMbgPgwIfV1ICsAuthFailRx   OBJECT-TYPE
    SYNTAX      Counter64
    MAX-ACCESS  read-only
    STATUS      current
    DESCRIPTION
    "Number of GTPV1 packets received with cause Auth Failure."
    ::= { jnxMbgPgwGtpIfStatsEntry 238 }

jnxMbgPgwIfV1ICsAuthFailTx   OBJECT-TYPE
    SYNTAX      Counter64
    MAX-ACCESS  read-only
    STATUS      current
    DESCRIPTION
    "Number of GTPV1 packets sent with cause Auth Failure."
    ::= { jnxMbgPgwGtpIfStatsEntry 239 }

jnxMbgPgwIfV1ICsUserAuthFailRx   OBJECT-TYPE
    SYNTAX      Counter64
    MAX-ACCESS  read-only
    STATUS      current
    DESCRIPTION
    "Number of GTPV1 packets received with cause User Auth Failure."
    ::= { jnxMbgPgwGtpIfStatsEntry 240 }

jnxMbgPgwIfV1ICsUserAuthFailTx   OBJECT-TYPE
    SYNTAX      Counter64
    MAX-ACCESS  read-only
    STATUS      current
    DESCRIPTION
    "Number of GTPV1 packets sent with cause User Auth Failure."
    ::= { jnxMbgPgwGtpIfStatsEntry 241 }

jnxMbgPgwIfV1ICsCtxNotFndRx   OBJECT-TYPE
    SYNTAX      Counter64
    MAX-ACCESS  read-only
    STATUS      current
    DESCRIPTION
    "Number of GTPV1 packets received with cause Context Not Found."
    ::= { jnxMbgPgwGtpIfStatsEntry 242 }

jnxMbgPgwIfV1ICsCtxNotFndTx   OBJECT-TYPE
    SYNTAX      Counter64
    MAX-ACCESS  read-only
    STATUS      current
    DESCRIPTION
    "Number of GTPV1 packets sent with cause Context Not Found."
    ::= { jnxMbgPgwGtpIfStatsEntry 243 }

jnxMbgPgwIfV1ICsAllDynPDPAdRx   OBJECT-TYPE
    SYNTAX      Counter64
    MAX-ACCESS  read-only
    STATUS      current
    DESCRIPTION
    "Number of GTPV1 packets received with cause Allow Dynamic PDP Address."
    ::= { jnxMbgPgwGtpIfStatsEntry 244 }

jnxMbgPgwIfV1ICsAllDynPDPAdTx   OBJECT-TYPE
    SYNTAX      Counter64
    MAX-ACCESS  read-only
    STATUS      current
    DESCRIPTION
    "Number of GTPV1 packets sent with cause Allow Dynamic PDP Address."
    ::= { jnxMbgPgwGtpIfStatsEntry 245 }

jnxMbgPgwIfV1ICsNoMemRx   OBJECT-TYPE
    SYNTAX      Counter64
    MAX-ACCESS  read-only
    STATUS      current
    DESCRIPTION
    "Number of GTPV1 packets received with cause No Memory."
    ::= { jnxMbgPgwGtpIfStatsEntry 246 }

jnxMbgPgwIfV1ICsNoMemTx   OBJECT-TYPE
    SYNTAX      Counter64
    MAX-ACCESS  read-only
    STATUS      current
    DESCRIPTION
    "Number of GTPV1 packets sent with cause No Memory."
    ::= { jnxMbgPgwGtpIfStatsEntry 247 }

jnxMbgPgwIfV1ICsRelocFailRx   OBJECT-TYPE
    SYNTAX      Counter64
    MAX-ACCESS  read-only
    STATUS      current
    DESCRIPTION
    "Number of GTPV1 packets received with cause Relocation Failed."
    ::= { jnxMbgPgwGtpIfStatsEntry 248 }

jnxMbgPgwIfV1ICsRelocFailTx   OBJECT-TYPE
    SYNTAX      Counter64
    MAX-ACCESS  read-only
    STATUS      current
    DESCRIPTION
    "Number of GTPV1 packets sent with cause Relocation Failed."
    ::= { jnxMbgPgwGtpIfStatsEntry 249 }

jnxMbgPgwIfV1ICsUnkManExhdrRx   OBJECT-TYPE
    SYNTAX      Counter64
    MAX-ACCESS  read-only
    STATUS      current
    DESCRIPTION
    "Number of GTPV1 packets received with cause Unknown Mandatory Extension Header."
    ::= { jnxMbgPgwGtpIfStatsEntry 250 }

jnxMbgPgwIfV1ICsUnkManExhdrTx   OBJECT-TYPE
    SYNTAX      Counter64
    MAX-ACCESS  read-only
    STATUS      current
    DESCRIPTION
    "Number of GTPV1 packets sent with cause Unknown Mandatory Extension Header."
    ::= { jnxMbgPgwGtpIfStatsEntry 251 }

jnxMbgPgwIfV1ICsSMANTTFTEr1Rx   OBJECT-TYPE
    SYNTAX      Counter64
    MAX-ACCESS  read-only
    STATUS      current
    DESCRIPTION
    "Number of GTPV1 packets received with cause Mandatory TFT Error."
    ::= { jnxMbgPgwGtpIfStatsEntry 252 }

jnxMbgPgwIfV1ICsSMANTTFTEr1Tx   OBJECT-TYPE
    SYNTAX      Counter64
    MAX-ACCESS  read-only
    STATUS      current
    DESCRIPTION
    "Number of GTPV1 packets sent with cause Mandatory TFT Error."
    ::= { jnxMbgPgwGtpIfStatsEntry 253 }

jnxMbgPgwIfV1ICsSYNTFTErr2Rx   OBJECT-TYPE
    SYNTAX      Counter64
    MAX-ACCESS  read-only
    STATUS      current
    DESCRIPTION
    "Number of GTPV1 packets received with cause Mandatory TFT Error."
    ::= { jnxMbgPgwGtpIfStatsEntry 254 }

jnxMbgPgwIfV1ICsSYNTFTErr2Tx   OBJECT-TYPE
    SYNTAX      Counter64
    MAX-ACCESS  read-only
    STATUS      current
    DESCRIPTION
    "Number of GTPV1 packets sent with cause Mandatory TFT Error."
    ::= { jnxMbgPgwGtpIfStatsEntry 255 }

jnxMbgPgwIfV1ICsSMNTPkFlEr1Rx   OBJECT-TYPE
    SYNTAX      Counter64
    MAX-ACCESS  read-only
    STATUS      current
    DESCRIPTION
    "Number of GTPV1 packets received with cause Mandatory Packet Filter Error."
    ::= { jnxMbgPgwGtpIfStatsEntry 256 }

jnxMbgPgwIfV1ICsSMNTPkFlEr1Tx   OBJECT-TYPE
    SYNTAX      Counter64
    MAX-ACCESS  read-only
    STATUS      current
    DESCRIPTION
    "Number of GTPV1 packets sent with cause Mandatory Packet Filter Error."
    ::= { jnxMbgPgwGtpIfStatsEntry 257 }

jnxMbgPgwIfV1ICsSYNPkFlErr2Rx   OBJECT-TYPE
    SYNTAX      Counter64
    MAX-ACCESS  read-only
    STATUS      current
    DESCRIPTION
    "Number of GTPV1 packets received with cause Mandatory Packet Filter Error."
    ::= { jnxMbgPgwGtpIfStatsEntry 258 }

jnxMbgPgwIfV1ICsSYNPkFlErr2Tx   OBJECT-TYPE
    SYNTAX      Counter64
    MAX-ACCESS  read-only
    STATUS      current
    DESCRIPTION
    "Number of GTPV1 packets sent with cause Mandatory Packet Filter Error."
    ::= { jnxMbgPgwGtpIfStatsEntry 259 }

jnxMbgPgwIfV1ICsMissUnknAPNRx   OBJECT-TYPE
    SYNTAX      Counter64
    MAX-ACCESS  read-only
    STATUS      current
    DESCRIPTION
    "Number of GTPV1 packets received with cause Unknowkn APN missing."
    ::= { jnxMbgPgwGtpIfStatsEntry 260 }

jnxMbgPgwIfV1ICsMissUnknAPNTx   OBJECT-TYPE
    SYNTAX      Counter64
    MAX-ACCESS  read-only
    STATUS      current
    DESCRIPTION
    "Number of GTPV1 packets sent with cause Unknowkn APN missing."
    ::= { jnxMbgPgwGtpIfStatsEntry 261 }

jnxMbgPgwIfV1ICsUnknPDPAdRx   OBJECT-TYPE
    SYNTAX      Counter64
    MAX-ACCESS  read-only
    STATUS      current
    DESCRIPTION
    "Number of GTPV1 packets received with cause Unknowkn PDP Address."
    ::= { jnxMbgPgwGtpIfStatsEntry 262 }

jnxMbgPgwIfV1ICsUnknPDPAdTx   OBJECT-TYPE
    SYNTAX      Counter64
    MAX-ACCESS  read-only
    STATUS      current
    DESCRIPTION
    "Number of GTPV1 packets sent with cause Unknowkn PDP Address."
    ::= { jnxMbgPgwGtpIfStatsEntry 263 }

jnxMbgPgwIfV1ICsNoTFTCtxExRx   OBJECT-TYPE
    SYNTAX      Counter64
    MAX-ACCESS  read-only
    STATUS      current
    DESCRIPTION
    "Number of GTPV1 packets received with cause No TFT Context Exists."
    ::= { jnxMbgPgwGtpIfStatsEntry 264 }

jnxMbgPgwIfV1ICsNoTFTCtxExTx   OBJECT-TYPE
    SYNTAX      Counter64
    MAX-ACCESS  read-only
    STATUS      current
    DESCRIPTION
    "Number of GTPV1 packets sent with cause No TFT Context Exists."
    ::= { jnxMbgPgwGtpIfStatsEntry 265 }

jnxMbgPgwIfV0ProtocolErrRx  OBJECT-TYPE
    SYNTAX      Counter64
    MAX-ACCESS  read-only
    STATUS      current
    DESCRIPTION
    "Number of GTPv0 Protocol Errors Received."
    ::= { jnxMbgPgwGtpIfStatsEntry 266 }

jnxMbgPgwIfV0UnSupportedMsgRx  OBJECT-TYPE
    SYNTAX      Counter64
    MAX-ACCESS  read-only
    STATUS      current
    DESCRIPTION
    "Number of GTPv0 Unsupported Messages received."
    ::= { jnxMbgPgwGtpIfStatsEntry 267 }

jnxMbgPgwIfV0T3RespTmrExpRx  OBJECT-TYPE
    SYNTAX      Counter64
    MAX-ACCESS  read-only
    STATUS      current
    DESCRIPTION
    "Number of GTP V0 T3 timer expiries Received."
    ::= { jnxMbgPgwGtpIfStatsEntry 268 }

jnxMbgPgwIfV0GlbNumMsgRx  OBJECT-TYPE
    SYNTAX      Counter64
    MAX-ACCESS  read-only
    STATUS      current
    DESCRIPTION
    "Number of GTPv0 messages received."
    ::= { jnxMbgPgwGtpIfStatsEntry 269 }

jnxMbgPgwIfV0GlbNumMsgTx  OBJECT-TYPE
    SYNTAX      Counter64
    MAX-ACCESS  read-only
    STATUS      current
    DESCRIPTION
    "Number of GTP V0 messages sent."
    ::= { jnxMbgPgwGtpIfStatsEntry 270 }

jnxMbgPgwIfV0GlbNumBytesRx  OBJECT-TYPE
    SYNTAX      Counter64
    MAX-ACCESS  read-only
    STATUS      current
    DESCRIPTION
    "Number of GTPv0 bytes received."
    ::= { jnxMbgPgwGtpIfStatsEntry 271 }

jnxMbgPgwIfV0GlbNumBytesTx  OBJECT-TYPE
    SYNTAX      Counter64
    MAX-ACCESS  read-only
    STATUS      current
    DESCRIPTION
    "Number of GTP V0 bytes sent."
    ::= { jnxMbgPgwGtpIfStatsEntry 272 }

jnxMbgPgwIfV0GlbEchoReqRx  OBJECT-TYPE
    SYNTAX      Counter64
    MAX-ACCESS  read-only
    STATUS      current
    DESCRIPTION
   "Number of GTP V0 Echo Requests received."
    ::= { jnxMbgPgwGtpIfStatsEntry 273 }

jnxMbgPgwIfV0GlbEchoReqTx  OBJECT-TYPE
    SYNTAX      Counter64
    MAX-ACCESS  read-only
    STATUS      current
    DESCRIPTION
    "Number of GTP V0 Echo Requests Sent."
    ::= { jnxMbgPgwGtpIfStatsEntry 274 }

jnxMbgPgwIfV0GlbEchoRespRx  OBJECT-TYPE
    SYNTAX      Counter64
    MAX-ACCESS  read-only
    STATUS      current
    DESCRIPTION
    "Number of GTP V0 Echo Responses received."
    ::= { jnxMbgPgwGtpIfStatsEntry 275 }

jnxMbgPgwIfV0GlbEchoRespTx  OBJECT-TYPE
    SYNTAX      Counter64
    MAX-ACCESS  read-only
    STATUS      current
    DESCRIPTION
    "Number of GTP V0 Echo Responses Sent."
    ::= { jnxMbgPgwGtpIfStatsEntry 276 }

jnxMbgPgwIfV0GlbVerNotSupRx OBJECT-TYPE
    SYNTAX      Counter64
    MAX-ACCESS  read-only
    STATUS      current
    DESCRIPTION
    "Number of GTP V0 Version Not supported messages received"
    ::= { jnxMbgPgwGtpIfStatsEntry 277 }

jnxMbgPgwIfV0GlbVerNotSupTx OBJECT-TYPE
    SYNTAX      Counter64
    MAX-ACCESS  read-only
    STATUS      current
    DESCRIPTION
    "Number of GTP V0 version not supported messages Sent."
    ::= { jnxMbgPgwGtpIfStatsEntry 278 }

jnxMbgPgwIfV0GlbCrtPdpCxtReqRx   OBJECT-TYPE
    SYNTAX      Counter64
    MAX-ACCESS  read-only
    STATUS      current
    DESCRIPTION
    "Number of GTP V0 Create PDP Context Requests Received."
    ::= { jnxMbgPgwGtpIfStatsEntry 279 }

jnxMbgPgwIfV0GlbCrtPdpCxtReqTx   OBJECT-TYPE
    SYNTAX      Counter64
    MAX-ACCESS  read-only
    STATUS      current
    DESCRIPTION
    "Number of GTP V0 Create PDP Context Requests Sent."
    ::= { jnxMbgPgwGtpIfStatsEntry 280 }

jnxMbgPgwIfV0GlbCrtPdpCxtRspRx   OBJECT-TYPE
    SYNTAX      Counter64
    MAX-ACCESS  read-only
    STATUS      current
    DESCRIPTION
    "Number of GTP V0 Create PDP Context Responses Received."
    ::= { jnxMbgPgwGtpIfStatsEntry 281 }

jnxMbgPgwIfV0GlbCrtPdpCxtRspTx   OBJECT-TYPE
    SYNTAX      Counter64
    MAX-ACCESS  read-only
    STATUS      current
    DESCRIPTION
    "Number of GTP V0 Create PDP Context Responses Sent."
    ::= { jnxMbgPgwGtpIfStatsEntry 282 }

jnxMbgPgwIfV0GlbUpdPdpCxtReqRx   OBJECT-TYPE
    SYNTAX      Counter64
    MAX-ACCESS  read-only
    STATUS      current
    DESCRIPTION
    "Number of GTP V0 Update PDP Context Requests Received."
    ::= { jnxMbgPgwGtpIfStatsEntry 283 }

jnxMbgPgwIfV0GlbUpdPdpCxtReqTx   OBJECT-TYPE
    SYNTAX      Counter64
    MAX-ACCESS  read-only
    STATUS      current
    DESCRIPTION
    "Number of GTP V0 Update PDP Context Requests Sent."
    ::= { jnxMbgPgwGtpIfStatsEntry 284 }

jnxMbgPgwIfV0GlbUpdPdpCxtRspRx   OBJECT-TYPE
    SYNTAX      Counter64
    MAX-ACCESS  read-only
    STATUS      current
    DESCRIPTION
    "Number of GTP V0 Update PDP Context Responses Received."
    ::= { jnxMbgPgwGtpIfStatsEntry 285 }

jnxMbgPgwIfV0GlbUpdPdpCxtRspTx   OBJECT-TYPE
    SYNTAX      Counter64
    MAX-ACCESS  read-only
    STATUS      current
    DESCRIPTION
    "Number of GTP V0 Update PDP Context Responses Sent."
    ::= { jnxMbgPgwGtpIfStatsEntry 286 }

jnxMbgPgwIfV0GlbDelPdpCxtReqRx   OBJECT-TYPE
    SYNTAX      Counter64
    MAX-ACCESS  read-only
    STATUS      current
    DESCRIPTION
    "Number of GTP V0 Delete PDP Context Requests Received."
    ::= { jnxMbgPgwGtpIfStatsEntry 287 }

jnxMbgPgwIfV0GlbDelPdpCxtReqTx   OBJECT-TYPE
    SYNTAX      Counter64
    MAX-ACCESS  read-only
    STATUS      current
    DESCRIPTION
    "Number of GTP V0 Delete PDP Context Requests Sent."
    ::= { jnxMbgPgwGtpIfStatsEntry 288 }

jnxMbgPgwIfV0GlbDelPdpCxtRspRx   OBJECT-TYPE
    SYNTAX      Counter64
    MAX-ACCESS  read-only
    STATUS      current
    DESCRIPTION
    "Number of GTP V0 Delete PDP Context Responses Received."
    ::= { jnxMbgPgwGtpIfStatsEntry 289 }

jnxMbgPgwIfV0GlbDelPdpCxtRspTx   OBJECT-TYPE
    SYNTAX      Counter64
    MAX-ACCESS  read-only
    STATUS      current
    DESCRIPTION
    "Number of GTP V0 Delete PDP Context Responses Sent."
    ::= { jnxMbgPgwGtpIfStatsEntry 290 }

jnxMbgPgwIfV0GlbCrtAAPdpCxtRqRx   OBJECT-TYPE
    SYNTAX      Counter64
    MAX-ACCESS  read-only
    STATUS      current
    DESCRIPTION
    "Number of GTP V0 Create AA PDP Context Requests Received."
    ::= { jnxMbgPgwGtpIfStatsEntry 291 }

jnxMbgPgwIfV0GlbCrtAAPdpCxtRqTx   OBJECT-TYPE
    SYNTAX      Counter64
    MAX-ACCESS  read-only
    STATUS      current
    DESCRIPTION
    "Number of GTP V0 Create AA PDP Context Requests Sent."
    ::= { jnxMbgPgwGtpIfStatsEntry 292 }

jnxMbgPgwIfV0GlbCrtAAPdpCxtRpRx   OBJECT-TYPE
    SYNTAX      Counter64
    MAX-ACCESS  read-only
    STATUS      current
    DESCRIPTION
    "Number of GTP V0 Create AA PDP Context Responses Received."
    ::= { jnxMbgPgwGtpIfStatsEntry 293 }

jnxMbgPgwIfV0GlbCrtAAPdpCxtRpTx   OBJECT-TYPE
    SYNTAX      Counter64
    MAX-ACCESS  read-only
    STATUS      current
    DESCRIPTION
    "Number of GTP V0 Create AA PDP Context Responses Sent."
    ::= { jnxMbgPgwGtpIfStatsEntry 294 }

jnxMbgPgwIfV0GlbDelAAPdpCxtRqRx   OBJECT-TYPE
    SYNTAX      Counter64
    MAX-ACCESS  read-only
    STATUS      current
    DESCRIPTION
    "Number of GTP V0 Delete AA PDP Context Requests Received."
    ::= { jnxMbgPgwGtpIfStatsEntry 295 }

jnxMbgPgwIfV0GlbDelAAPdpCxtRqTx   OBJECT-TYPE
    SYNTAX      Counter64
    MAX-ACCESS  read-only
    STATUS      current
    DESCRIPTION
    "Number of GTP V0 Delete AA PDP Context Requests Sent."
    ::= { jnxMbgPgwGtpIfStatsEntry 296 }

jnxMbgPgwIfV0GlbDelAAPdpCxtRpRx   OBJECT-TYPE
    SYNTAX      Counter64
    MAX-ACCESS  read-only
    STATUS      current
    DESCRIPTION
    "Number of GTP V0 Delete AA PDP Context Responses Received."
    ::= { jnxMbgPgwGtpIfStatsEntry 297 }

jnxMbgPgwIfV0GlbDelAAPdpCxtRpTx   OBJECT-TYPE
    SYNTAX      Counter64
    MAX-ACCESS  read-only
    STATUS      current
    DESCRIPTION
    "Number of GTP V0 Delete AA PDP Context Responses Sent."
    ::= { jnxMbgPgwGtpIfStatsEntry 298 }

jnxMbgPgwIfV0GlbErrorIndRx   OBJECT-TYPE
    SYNTAX      Counter64
    MAX-ACCESS  read-only
    STATUS      current
    DESCRIPTION
    "Number of GTP V0 Error Indication messages Received."
    ::= { jnxMbgPgwGtpIfStatsEntry 299 }

jnxMbgPgwIfV0GlbErrorIndTx   OBJECT-TYPE
    SYNTAX      Counter64
    MAX-ACCESS  read-only
    STATUS      current
    DESCRIPTION
    "Number of GTP V0 Error Indication messages Sent."
    ::= { jnxMbgPgwGtpIfStatsEntry 300 }

jnxMbgPgwIfV0GlbNotifReqRx   OBJECT-TYPE
    SYNTAX      Counter64
    MAX-ACCESS  read-only
    STATUS      current
    DESCRIPTION
    "Number of GTP V0 Notify Requests Received."
    ::= { jnxMbgPgwGtpIfStatsEntry 301 }

jnxMbgPgwIfV0GlbNotifReqTx   OBJECT-TYPE
    SYNTAX      Counter64
    MAX-ACCESS  read-only
    STATUS      current
    DESCRIPTION
    "Number of GTP V0 Notify Requests Sent."
    ::= { jnxMbgPgwGtpIfStatsEntry 302 }

jnxMbgPgwIfV0GlbNotifRspRx   OBJECT-TYPE
    SYNTAX      Counter64
    MAX-ACCESS  read-only
    STATUS      current
    DESCRIPTION
    "Number of GTP V0 Notify Responses Received."
    ::= { jnxMbgPgwGtpIfStatsEntry 303 }

jnxMbgPgwIfV0GlbNotifRspTx   OBJECT-TYPE
    SYNTAX      Counter64
    MAX-ACCESS  read-only
    STATUS      current
    DESCRIPTION
    "Number of GTP V0 Notify Responses Sent."
    ::= { jnxMbgPgwGtpIfStatsEntry 304 }

jnxMbgPgwIfV0GlbNotifRejReqRx   OBJECT-TYPE
    SYNTAX      Counter64
    MAX-ACCESS  read-only
    STATUS      current
    DESCRIPTION
    "Number of GTP V0 Notify Reject Requests Received."
    ::= { jnxMbgPgwGtpIfStatsEntry 305 }

jnxMbgPgwIfV0GlbNotifRejReqTx   OBJECT-TYPE
    SYNTAX      Counter64
    MAX-ACCESS  read-only
    STATUS      current
    DESCRIPTION
    "Number of GTP V0 Notify Reject Requests Sent."
    ::= { jnxMbgPgwGtpIfStatsEntry 306 }

jnxMbgPgwIfV0GlbNotifRejRspRx   OBJECT-TYPE
    SYNTAX      Counter64
    MAX-ACCESS  read-only
    STATUS      current
    DESCRIPTION
    "Number of GTP V0 Notify Reject Responses Received."
    ::= { jnxMbgPgwGtpIfStatsEntry 307 }

jnxMbgPgwIfV0GlbNotifRejRspTx   OBJECT-TYPE
    SYNTAX      Counter64
    MAX-ACCESS  read-only
    STATUS      current
    DESCRIPTION
    "Number of GTP V0 Notify Reject Responses Sent."
    ::= { jnxMbgPgwGtpIfStatsEntry 308 }

jnxMbgPgwIfV0GlbRtInfReqRx   OBJECT-TYPE
    SYNTAX      Counter64
    MAX-ACCESS  read-only
    STATUS      current
    DESCRIPTION
    "Number of GTP V0 Routing Information Requests Received."
    ::= { jnxMbgPgwGtpIfStatsEntry 309 }

jnxMbgPgwIfV0GlbRtInfReqTx   OBJECT-TYPE
    SYNTAX      Counter64
    MAX-ACCESS  read-only
    STATUS      current
    DESCRIPTION
    "Number of GTP V0 Routing Information Requests Sent."
    ::= { jnxMbgPgwGtpIfStatsEntry 310 }

jnxMbgPgwIfV0GlbRtInfRspRx   OBJECT-TYPE
    SYNTAX      Counter64
    MAX-ACCESS  read-only
    STATUS      current
    DESCRIPTION
    "Number of GTP V0 Routing Information Responses Received."
    ::= { jnxMbgPgwGtpIfStatsEntry 311 }

jnxMbgPgwIfV0GlbRtInfRspTx   OBJECT-TYPE
    SYNTAX      Counter64
    MAX-ACCESS  read-only
    STATUS      current
    DESCRIPTION
    "Number of GTP V0 Routing Information Responses Sent."
    ::= { jnxMbgPgwGtpIfStatsEntry 312 }

jnxMbgPgwIfV0GlbFailRptReqRx   OBJECT-TYPE
    SYNTAX      Counter64
    MAX-ACCESS  read-only
    STATUS      current
    DESCRIPTION
    "Number of GTP V0 Fail Repeat Requests Received."
    ::= { jnxMbgPgwGtpIfStatsEntry 313 }

jnxMbgPgwIfV0GlbFailRptReqTx   OBJECT-TYPE
    SYNTAX      Counter64
    MAX-ACCESS  read-only
    STATUS      current
    DESCRIPTION
    "Number of GTP V0 Fail Repeat Requests Sent."
    ::= { jnxMbgPgwGtpIfStatsEntry 314 }

jnxMbgPgwIfV0GlbFailRptRspRx   OBJECT-TYPE
    SYNTAX      Counter64
    MAX-ACCESS  read-only
    STATUS      current
    DESCRIPTION
    "Number of GTP V0 Fail Repeat Responses Received."
    ::= { jnxMbgPgwGtpIfStatsEntry 315 }

jnxMbgPgwIfV0GlbFailRptRspTx   OBJECT-TYPE
    SYNTAX      Counter64
    MAX-ACCESS  read-only
    STATUS      current
    DESCRIPTION
    "Number of GTP V0 Fail Repeat Responses Sent."
    ::= { jnxMbgPgwGtpIfStatsEntry 316 }

jnxMbgPgwIfV0GlbNotMSPresReqRx   OBJECT-TYPE
    SYNTAX      Counter64
    MAX-ACCESS  read-only
    STATUS      current
    DESCRIPTION
    "Number of GTP V0 MS Not Present Requests Received."
    ::= { jnxMbgPgwGtpIfStatsEntry 317 }

jnxMbgPgwIfV0GlbNotMSPresReqTx   OBJECT-TYPE
    SYNTAX      Counter64
    MAX-ACCESS  read-only
    STATUS      current
    DESCRIPTION
    "Number of GTP V0 MS Not Present Requests Sent."
    ::= { jnxMbgPgwGtpIfStatsEntry 318 }

jnxMbgPgwIfV0GlbNotMSPresRspRx   OBJECT-TYPE
    SYNTAX      Counter64
    MAX-ACCESS  read-only
    STATUS      current
    DESCRIPTION
    "Number of GTP V0 MS Not Present Responses Received."
    ::= { jnxMbgPgwGtpIfStatsEntry 319 }

jnxMbgPgwIfV0GlbNotMSPresRspTx   OBJECT-TYPE
    SYNTAX      Counter64
    MAX-ACCESS  read-only
    STATUS      current
    DESCRIPTION
    "Number of GTP V0 MS Not Present Responses Sent."
    ::= { jnxMbgPgwGtpIfStatsEntry 320 }

jnxMbgPgwIfV0ICsReqAcceptedRx   OBJECT-TYPE
    SYNTAX      Counter64
    MAX-ACCESS  read-only
    STATUS      current
    DESCRIPTION
    "Number of GTPV0 packets received with cause Request Accepted."
    ::= { jnxMbgPgwGtpIfStatsEntry 321 }

jnxMbgPgwIfV0ICsReqAcceptedTx   OBJECT-TYPE
    SYNTAX      Counter64
    MAX-ACCESS  read-only
    STATUS      current
    DESCRIPTION
    "Number of GTPV0 packets sent with cause Request Accepted."
    ::= { jnxMbgPgwGtpIfStatsEntry 322 }

jnxMbgPgwIfV0ICsNonExistRx   OBJECT-TYPE
    SYNTAX      Counter64
    MAX-ACCESS  read-only
    STATUS      current
    DESCRIPTION
    "Number of GTPV0 packets received with cause Non Existant ."
    ::= { jnxMbgPgwGtpIfStatsEntry 323 }

jnxMbgPgwIfV0ICsNonExistTx   OBJECT-TYPE
    SYNTAX      Counter64
    MAX-ACCESS  read-only
    STATUS      current
    DESCRIPTION
    "Number of GTPV0 packets sent with cause Non Existant."
    ::= { jnxMbgPgwGtpIfStatsEntry 324 }

jnxMbgPgwIfV0ICsInvMsgFmtRx   OBJECT-TYPE
    SYNTAX      Counter64
    MAX-ACCESS  read-only
    STATUS      current
    DESCRIPTION
    "Number of GTPV0 packets received with cause Invalid Mesage Format."
    ::= { jnxMbgPgwGtpIfStatsEntry 325 }

jnxMbgPgwIfV0ICsInvMsgFmtTx   OBJECT-TYPE
    SYNTAX      Counter64
    MAX-ACCESS  read-only
    STATUS      current
    DESCRIPTION
    "Number of GTPV0 packets sent with cause Invalid Mesage Format."
    ::= { jnxMbgPgwGtpIfStatsEntry 326 }

jnxMbgPgwIfV0ICsIMSINotKnownRx   OBJECT-TYPE
    SYNTAX      Counter64
    MAX-ACCESS  read-only
    STATUS      current
    DESCRIPTION
    "Number of GTPV0 packets received with cause IMSI Not Known."
    ::= { jnxMbgPgwGtpIfStatsEntry 327 }


jnxMbgPgwIfV0ICsIMSINotKnownTx   OBJECT-TYPE
    SYNTAX      Counter64
    MAX-ACCESS  read-only
    STATUS      current
    DESCRIPTION
    "Number of GTPV0 packets sent with cause IMSI Not Known."
    ::= { jnxMbgPgwGtpIfStatsEntry 328 }

jnxMbgPgwIfV0ICsMSGRPSDetachRx   OBJECT-TYPE
    SYNTAX      Counter64
    MAX-ACCESS  read-only
    STATUS      current
    DESCRIPTION
    "Number of GTPV0 packets received with cause MS GPRS Detached."
    ::= { jnxMbgPgwGtpIfStatsEntry 329 }

jnxMbgPgwIfV0ICsMSGRPSDetachTx   OBJECT-TYPE
    SYNTAX      Counter64
    MAX-ACCESS  read-only
    STATUS      current
    DESCRIPTION
    "Number of GTPV0 packets sent with cause MS GPRS Detached."
    ::= { jnxMbgPgwGtpIfStatsEntry 330 }

jnxMbgPgwIfV0ICsMSNotGRPSRespRx   OBJECT-TYPE
    SYNTAX      Counter64
    MAX-ACCESS  read-only
    STATUS      current
    DESCRIPTION
    "Number of GTPV0 packets received with cause MS No GPRS Response."
    ::= { jnxMbgPgwGtpIfStatsEntry 331 }

jnxMbgPgwIfV0ICsMSNotGRPSRespTx   OBJECT-TYPE
    SYNTAX      Counter64
    MAX-ACCESS  read-only
    STATUS      current
    DESCRIPTION
    "Number of GTPV0 packets sent with cause MS No GPRS Response."
    ::= { jnxMbgPgwGtpIfStatsEntry 332 }

jnxMbgPgwIfV0ICsMSRefusesRx   OBJECT-TYPE
    SYNTAX      Counter64
    MAX-ACCESS  read-only
    STATUS      current
    DESCRIPTION
    "Number of GTPV0 packets received with cause MS Refues."
    ::= { jnxMbgPgwGtpIfStatsEntry 333 }

jnxMbgPgwIfV0ICsMSRefusesTx   OBJECT-TYPE
    SYNTAX      Counter64
    MAX-ACCESS  read-only
    STATUS      current
    DESCRIPTION
    "Number of GTPV0 packets sent with cause MS Refues."
    ::= { jnxMbgPgwGtpIfStatsEntry 334 }

jnxMbgPgwIfV0ICsVerNotSuppRx   OBJECT-TYPE
    SYNTAX      Counter64
    MAX-ACCESS  read-only
    STATUS      current
    DESCRIPTION
    "Number of GTPV0 packets received with cause Version Not Supported."
    ::= { jnxMbgPgwGtpIfStatsEntry 335 }

jnxMbgPgwIfV0ICsVerNotSuppTx   OBJECT-TYPE
    SYNTAX      Counter64
    MAX-ACCESS  read-only
    STATUS      current
    DESCRIPTION
    "Number of GTPV0 packets sent with cause Version Not Supported."
    ::= { jnxMbgPgwGtpIfStatsEntry 336 }

jnxMbgPgwIfV0ICsNoResRx   OBJECT-TYPE
    SYNTAX      Counter64
    MAX-ACCESS  read-only
    STATUS      current
    DESCRIPTION
    "Number of GTPV0 packets received with cause No Response."
    ::= { jnxMbgPgwGtpIfStatsEntry 337 }

jnxMbgPgwIfV0ICsNoResTx   OBJECT-TYPE
    SYNTAX      Counter64
    MAX-ACCESS  read-only
    STATUS      current
    DESCRIPTION
    "Number of GTPV0 packets sent with cause No Response."
    ::= { jnxMbgPgwGtpIfStatsEntry 338 }

jnxMbgPgwIfV0ICsServNotSuppRx   OBJECT-TYPE
    SYNTAX      Counter64
    MAX-ACCESS  read-only
    STATUS      current
    DESCRIPTION
    "Number of GTPV0 packets received with cause Service Not Supported."
    ::= { jnxMbgPgwGtpIfStatsEntry 339 }

jnxMbgPgwIfV0ICsServNotSuppTx   OBJECT-TYPE
    SYNTAX      Counter64
    MAX-ACCESS  read-only
    STATUS      current
    DESCRIPTION
    "Number of GTPV0 packets sent with cause Service Not Supported."
    ::= { jnxMbgPgwGtpIfStatsEntry 340 }

jnxMbgPgwIfV0ICsManIEIncrtRx   OBJECT-TYPE
    SYNTAX      Counter64
    MAX-ACCESS  read-only
    STATUS      current
    DESCRIPTION
    "Number of GTPV0 packets received with cause Mandatory IE incorrect."
    ::= { jnxMbgPgwGtpIfStatsEntry 341 }

jnxMbgPgwIfV0ICsManIEIncrtTx   OBJECT-TYPE
    SYNTAX      Counter64
    MAX-ACCESS  read-only
    STATUS      current
    DESCRIPTION
    "Number of GTPV0 packets sent with cause Mandatory IE incorrect."
    ::= { jnxMbgPgwGtpIfStatsEntry 342 }

jnxMbgPgwIfV0ICsManIEMissRx   OBJECT-TYPE
    SYNTAX      Counter64
    MAX-ACCESS  read-only
    STATUS      current
    DESCRIPTION
    "Number of GTPV0 packets received with cause Mandatory IE Missing."
    ::= { jnxMbgPgwGtpIfStatsEntry 343 }

jnxMbgPgwIfV0ICsManIEMissTx   OBJECT-TYPE
    SYNTAX      Counter64
    MAX-ACCESS  read-only
    STATUS      current
    DESCRIPTION
    "Number of GTPV0 packets sent with cause Mandatory IE Missing."
    ::= { jnxMbgPgwGtpIfStatsEntry 344 }

jnxMbgPgwIfV0ICsOptIEIncrtRx   OBJECT-TYPE
    SYNTAX      Counter64
    MAX-ACCESS  read-only
    STATUS      current
    DESCRIPTION
    "Number of GTPV0 packets received with cause Optional IE incorrect."
    ::= { jnxMbgPgwGtpIfStatsEntry 345 }

jnxMbgPgwIfV0ICsOptIEIncrtTx   OBJECT-TYPE
    SYNTAX      Counter64
    MAX-ACCESS  read-only
    STATUS      current
    DESCRIPTION
    "Number of GTPV0 packets sent with cause Optional IE incorrect."
    ::= { jnxMbgPgwGtpIfStatsEntry 346 }

jnxMbgPgwIfV0ICsSysFailRx   OBJECT-TYPE
    SYNTAX      Counter64
    MAX-ACCESS  read-only
    STATUS      current
    DESCRIPTION
    "Number of GTPV0 packets received with cause System Failure."
    ::= { jnxMbgPgwGtpIfStatsEntry 347 }

jnxMbgPgwIfV0ICsSysFailTx   OBJECT-TYPE
    SYNTAX      Counter64
    MAX-ACCESS  read-only
    STATUS      current
    DESCRIPTION
    "Number of GTPV0 packets sent with cause System Failure."
    ::= { jnxMbgPgwGtpIfStatsEntry 348 }

jnxMbgPgwIfV0ICsRoamRestrictRx   OBJECT-TYPE
    SYNTAX      Counter64
    MAX-ACCESS  read-only
    STATUS      current
    DESCRIPTION
    "Number of GTPV0 packets received with cause Roaming Restricted."
    ::= { jnxMbgPgwGtpIfStatsEntry 349 }

jnxMbgPgwIfV0ICsRoamRestrictTx   OBJECT-TYPE
    SYNTAX      Counter64
    MAX-ACCESS  read-only
    STATUS      current
    DESCRIPTION
    "Number of GTPV0 packets sent with cause Roaming Restricted."
    ::= { jnxMbgPgwGtpIfStatsEntry 350 }

jnxMbgPgwIfV0ICsPTMSISigMMRx   OBJECT-TYPE
    SYNTAX      Counter64
    MAX-ACCESS  read-only
    STATUS      current
    DESCRIPTION
    "Number of GTPV0 packets received with cause PTMSI Signature Mismatch."
    ::= { jnxMbgPgwGtpIfStatsEntry 351 }

jnxMbgPgwIfV0ICsPTMSISigMMTx   OBJECT-TYPE
    SYNTAX      Counter64
    MAX-ACCESS  read-only
    STATUS      current
    DESCRIPTION
    "Number of GTPV0 packets sent with cause PTMSI Signature Mismatch."
    ::= { jnxMbgPgwGtpIfStatsEntry 352 }

jnxMbgPgwIfV0ICsGPRSConnSuppRx   OBJECT-TYPE
    SYNTAX      Counter64
    MAX-ACCESS  read-only
    STATUS      current
    DESCRIPTION
    "Number of GTPV0 packets received with cause GPRS Connection Supported."
    ::= { jnxMbgPgwGtpIfStatsEntry 353 }

jnxMbgPgwIfV0ICsGPRSConnSuppTx   OBJECT-TYPE
    SYNTAX      Counter64
    MAX-ACCESS  read-only
    STATUS      current
    DESCRIPTION
    "Number of GTPV0 packets sent with cause GPRS Connection Supported."
    ::= { jnxMbgPgwGtpIfStatsEntry 354 }

jnxMbgPgwIfV0ICsAuthFailRx   OBJECT-TYPE
    SYNTAX      Counter64
    MAX-ACCESS  read-only
    STATUS      current
    DESCRIPTION
    "Number of GTPV0 packets received with cause Auth Failure."
    ::= { jnxMbgPgwGtpIfStatsEntry 355 }

jnxMbgPgwIfV0ICsAuthFailTx   OBJECT-TYPE
    SYNTAX      Counter64
    MAX-ACCESS  read-only
    STATUS      current
    DESCRIPTION
    "Number of GTPV0 packets sent with cause Auth Failure."
    ::= { jnxMbgPgwGtpIfStatsEntry 356 }

jnxMbgPgwIfV0ICsUserAuthFailRx   OBJECT-TYPE
    SYNTAX      Counter64
    MAX-ACCESS  read-only
    STATUS      current
    DESCRIPTION
    "Number of GTPV0 packets received with cause User Auth Failure."
    ::= { jnxMbgPgwGtpIfStatsEntry 357 }

jnxMbgPgwIfV0ICsUserAuthFailTx   OBJECT-TYPE
    SYNTAX      Counter64
    MAX-ACCESS  read-only
    STATUS      current
    DESCRIPTION
    "Number of GTPV0 packets sent with cause User Auth Failure."
    ::= { jnxMbgPgwGtpIfStatsEntry 358 }

jnxMbgPgwIfGtpV2ICsLclDetRx OBJECT-TYPE
         SYNTAX      Counter64
         MAX-ACCESS  read-only
         STATUS      current
         DESCRIPTION
         "Number of GTP packets received with cause Local Detach."
     ::= { jnxMbgPgwGtpIfStatsEntry 359 }

jnxMbgPgwIfGtpV2ICsLclDetTx OBJECT-TYPE
         SYNTAX      Counter64
         MAX-ACCESS  read-only
         STATUS      current
         DESCRIPTION
         "Number of GTP packets sent with cause Local Detach."
     ::= { jnxMbgPgwGtpIfStatsEntry 360 }

jnxMbgPgwIfGtpV2ICsCmpDetRx OBJECT-TYPE
         SYNTAX      Counter64
         MAX-ACCESS  read-only
         STATUS      current
         DESCRIPTION
         "Number of GTP packets received with cause Complete Detach."
     ::= { jnxMbgPgwGtpIfStatsEntry 361 }

jnxMbgPgwIfGtpV2ICsCmpDetTx OBJECT-TYPE
         SYNTAX      Counter64
         MAX-ACCESS  read-only
         STATUS      current
         DESCRIPTION
         "Number of GTP packets sent with cause Complete Detach."
     ::= { jnxMbgPgwGtpIfStatsEntry 362 }

jnxMbgPgwIfGtpV2ICsRATChgRx OBJECT-TYPE
         SYNTAX      Counter64
         MAX-ACCESS  read-only
         STATUS      current
         DESCRIPTION
         "Number of GTP packets received with cause RAT changed from 3GPP to non 3GPP."
     ::= { jnxMbgPgwGtpIfStatsEntry 363 }

jnxMbgPgwIfGtpV2ICsRATChgTx OBJECT-TYPE
         SYNTAX      Counter64
         MAX-ACCESS  read-only
         STATUS      current
         DESCRIPTION
         "Number of GTP packets sent with cause RAT changed from 3GPP to non 3GPP."
     ::= { jnxMbgPgwGtpIfStatsEntry 364 }

jnxMbgPgwIfGtpV2ICsISRDeactRx OBJECT-TYPE
         SYNTAX      Counter64
         MAX-ACCESS  read-only
         STATUS      current
         DESCRIPTION
         "Number of GTP packets received with cause ISR Deactivated."
     ::= { jnxMbgPgwGtpIfStatsEntry 365 }

jnxMbgPgwIfGtpV2ICsISRDeactTx OBJECT-TYPE
         SYNTAX      Counter64
         MAX-ACCESS  read-only
         STATUS      current
         DESCRIPTION
         "Number of GTP packets sent with cause ISR Deactivated."
     ::= { jnxMbgPgwGtpIfStatsEntry 366 }

jnxMbgPgwIfGtpV2ICsEIFRNCEnRx OBJECT-TYPE
         SYNTAX      Counter64
         MAX-ACCESS  read-only
         STATUS      current
         DESCRIPTION
         "Number of GTP packets received with cause Error Indication from RNC eNodeB."
     ::= { jnxMbgPgwGtpIfStatsEntry 367 }

jnxMbgPgwIfGtpV2ICsEIFRNCEnTx OBJECT-TYPE
         SYNTAX      Counter64
         MAX-ACCESS  read-only
         STATUS      current
         DESCRIPTION
         "Number of GTP packets sent with cause Error Indication from RNC eNodeB."
     ::= { jnxMbgPgwGtpIfStatsEntry 368 }

jnxMbgPgwIfGtpV2ICsSemErTADRx OBJECT-TYPE
         SYNTAX      Counter64
         MAX-ACCESS  read-only
         STATUS      current
         DESCRIPTION
         "Number of GTP packets received with cause Semantic Error in TAD Operation."
     ::= { jnxMbgPgwGtpIfStatsEntry 369 }

jnxMbgPgwIfGtpV2ICsSemErTADTx OBJECT-TYPE
         SYNTAX      Counter64
         MAX-ACCESS  read-only
         STATUS      current
         DESCRIPTION
         "Number of GTP packets sent with cause Semantic Error in TAD Operation."
     ::= { jnxMbgPgwGtpIfStatsEntry 370 }

jnxMbgPgwIfGtpV2ICsSynErTADRx OBJECT-TYPE
         SYNTAX      Counter64
         MAX-ACCESS  read-only
         STATUS      current
         DESCRIPTION
         "Number of GTP packets received with cause Syntactic Error in TAD Operation."
     ::= { jnxMbgPgwGtpIfStatsEntry 371 }

jnxMbgPgwIfGtpV2ICsSynErTADTx OBJECT-TYPE
         SYNTAX      Counter64
         MAX-ACCESS  read-only
         STATUS      current
         DESCRIPTION
         "Number of GTP packets sent with cause Syntactic Error in TAD Operation."
     ::= { jnxMbgPgwGtpIfStatsEntry 372 }

jnxMbgPgwIfGtpV2ICsRMValRcvRx OBJECT-TYPE
         SYNTAX      Counter64
         MAX-ACCESS  read-only
         STATUS      current
         DESCRIPTION
         "Number of GTP packets received with cause Reserved Message Value Received."
     ::= { jnxMbgPgwGtpIfStatsEntry 373 }

jnxMbgPgwIfGtpV2ICsRMValRcvTx OBJECT-TYPE
         SYNTAX      Counter64
         MAX-ACCESS  read-only
         STATUS      current
         DESCRIPTION
         "Number of GTP packets sent with cause Reserved Message Value Received."
     ::= { jnxMbgPgwGtpIfStatsEntry 374 }

jnxMbgPgwIfGtpV2ICsRPrNtRspRx OBJECT-TYPE
         SYNTAX      Counter64
         MAX-ACCESS  read-only
         STATUS      current
         DESCRIPTION
         "Number of GTP packets received with cause Remote peer not responding."
     ::= { jnxMbgPgwGtpIfStatsEntry 375 }

jnxMbgPgwIfGtpV2ICsRPrNtRspTx OBJECT-TYPE
         SYNTAX      Counter64
         MAX-ACCESS  read-only
         STATUS      current
         DESCRIPTION
         "Number of GTP packets sent with cause Remote peer not responding."
     ::= { jnxMbgPgwGtpIfStatsEntry 376 }

jnxMbgPgwIfGtpV2ICsColNWReqRx OBJECT-TYPE
         SYNTAX      Counter64
         MAX-ACCESS  read-only
         STATUS      current
         DESCRIPTION
         "Number of GTP packets received with cause Collision with network initiated request."
     ::= { jnxMbgPgwGtpIfStatsEntry 377 }

jnxMbgPgwIfGtpV2ICsColNWReqTx OBJECT-TYPE
         SYNTAX      Counter64
         MAX-ACCESS  read-only
         STATUS      current
         DESCRIPTION
         "Number of GTP packets sent with cause Collision with network initiated request."
     ::= { jnxMbgPgwGtpIfStatsEntry 378 }

jnxMbgPgwIfGtpV2ICsUnPgUESusRx OBJECT-TYPE
         SYNTAX      Counter64
         MAX-ACCESS  read-only
         STATUS      current
         DESCRIPTION
         "Number of GTP packets received with cause Unable to page UE due to suspension."
     ::= { jnxMbgPgwGtpIfStatsEntry 379 }

jnxMbgPgwIfGtpV2ICsUnPgUESusTx OBJECT-TYPE
         SYNTAX      Counter64
         MAX-ACCESS  read-only
         STATUS      current
         DESCRIPTION
         "Number of GTP packets sent with cause Unable to page UE due to suspension."
     ::= { jnxMbgPgwGtpIfStatsEntry 380 }

jnxMbgPgwIfGtpV2ICsInvTotLenRx OBJECT-TYPE
         SYNTAX      Counter64
         MAX-ACCESS  read-only
         STATUS      current
         DESCRIPTION
         "Number of GTP packets received with cause Invalid total len."
     ::= { jnxMbgPgwGtpIfStatsEntry 381 }

jnxMbgPgwIfGtpV2ICsInvTotLenTx OBJECT-TYPE
         SYNTAX      Counter64
         MAX-ACCESS  read-only
         STATUS      current
         DESCRIPTION
         "Number of GTP packets sent with cause Invalid total len."
     ::= { jnxMbgPgwGtpIfStatsEntry 382 }

jnxMbgPgwIfGtpV2ICsDtForNtSupRx OBJECT-TYPE
         SYNTAX      Counter64
         MAX-ACCESS  read-only
         STATUS      current
         DESCRIPTION
         "Number of GTP packets received with cause Data forwarding not supported."
     ::= { jnxMbgPgwGtpIfStatsEntry 383 }

jnxMbgPgwIfGtpV2ICsDtForNtSupTx OBJECT-TYPE
         SYNTAX      Counter64
         MAX-ACCESS  read-only
         STATUS      current
         DESCRIPTION
         "Number of GTP packets sent with cause Data forwarding not supported."
     ::= { jnxMbgPgwGtpIfStatsEntry 384 }

jnxMbgPgwIfGtpV2ICsInReFRePrRx OBJECT-TYPE
         SYNTAX      Counter64
         MAX-ACCESS  read-only
         STATUS      current
         DESCRIPTION
         "Number of GTP packets received with cause Invalid Reply from Remote peer."
     ::= { jnxMbgPgwGtpIfStatsEntry 385 }

jnxMbgPgwIfGtpV2ICsInReFRePrTx OBJECT-TYPE
         SYNTAX      Counter64
         MAX-ACCESS  read-only
         STATUS      current
         DESCRIPTION
         "Number of GTP packets sent with cause Invalid Reply from Remote peer."
     ::= { jnxMbgPgwGtpIfStatsEntry 386 }

jnxMbgPgwIfGtpV2ICsInvPrRx OBJECT-TYPE
         SYNTAX      Counter64
         MAX-ACCESS  read-only
         STATUS      current
         DESCRIPTION
         "Number of GTP packets received with cause Invalid peer."
     ::= { jnxMbgPgwGtpIfStatsEntry 387 }

jnxMbgPgwIfGtpV2ICsInvPrTx OBJECT-TYPE
         SYNTAX      Counter64
         MAX-ACCESS  read-only
         STATUS      current
         DESCRIPTION
         "Number of GTP packets sent with cause Invalid peer."
     ::= { jnxMbgPgwGtpIfStatsEntry 388 }

jnxMbgPgwIfV1InitPdpCxtReqRx   OBJECT-TYPE
    SYNTAX      Counter64
    MAX-ACCESS  read-only
    STATUS      current
    DESCRIPTION
    "Number of GTP V1 Initiated PDP Context Requests Received."
    ::= { jnxMbgPgwGtpIfStatsEntry 389 }

jnxMbgPgwIfV1InitPdpCxtReqTx   OBJECT-TYPE
    SYNTAX      Counter64
    MAX-ACCESS  read-only
    STATUS      current
    DESCRIPTION
    "Number of GTP V1 Initiated PDP Context Requests Sent."
    ::= { jnxMbgPgwGtpIfStatsEntry 390 }

jnxMbgPgwIfV1InitPdpCxtRspRx   OBJECT-TYPE
    SYNTAX      Counter64
    MAX-ACCESS  read-only
    STATUS      current
    DESCRIPTION
    "Number of GTP V1 Initiated PDP Context Response Received."
    ::= { jnxMbgPgwGtpIfStatsEntry 391 }

jnxMbgPgwIfV1InitPdpCxtRspTx   OBJECT-TYPE
    SYNTAX      Counter64
    MAX-ACCESS  read-only
    STATUS      current
    DESCRIPTION
    "Number of GTP V1 Initiated PDP Context Response Sent."
    ::= { jnxMbgPgwGtpIfStatsEntry 392 }

jnxMbgPgwIfV2SuspNotifRx OBJECT-TYPE
         SYNTAX      Counter64
         MAX-ACCESS  read-only
         STATUS      current
         DESCRIPTION
         "Number of GTPv2 Suspend Notification messages received."
     ::= { jnxMbgPgwGtpIfStatsEntry 393 }

jnxMbgPgwIfV2SuspNotifTx OBJECT-TYPE
         SYNTAX      Counter64
         MAX-ACCESS  read-only
         STATUS      current
         DESCRIPTION
         "Number of GTPv2 Suspend Notification messages sent."
     ::= { jnxMbgPgwGtpIfStatsEntry 394 }

jnxMbgPgwIfV2SuspAckRx OBJECT-TYPE
         SYNTAX      Counter64
         MAX-ACCESS  read-only
         STATUS      current
         DESCRIPTION
         "Number of GTPv2 Suspend Acknowledgement messages received."
     ::= { jnxMbgPgwGtpIfStatsEntry 395 }

jnxMbgPgwIfV2SuspAckTx OBJECT-TYPE
         SYNTAX      Counter64
         MAX-ACCESS  read-only
         STATUS      current
         DESCRIPTION
         "Number of GTPv2 Suspend Acknowledgement messages sent."
     ::= { jnxMbgPgwGtpIfStatsEntry 396 }

jnxMbgPgwIfV2ResumeNotifRx OBJECT-TYPE
         SYNTAX      Counter64
         MAX-ACCESS  read-only
         STATUS      current
         DESCRIPTION
         "Number of GTPv2 Resume Notification messages received."
     ::= { jnxMbgPgwGtpIfStatsEntry 397 }

jnxMbgPgwIfV2ResumeNotifTx OBJECT-TYPE
         SYNTAX      Counter64
         MAX-ACCESS  read-only
         STATUS      current
         DESCRIPTION
         "Number of GTPv2 Resume Notification messages sent."
     ::= { jnxMbgPgwGtpIfStatsEntry 398 }

jnxMbgPgwIfV2ResumeAckRx OBJECT-TYPE
         SYNTAX      Counter64
         MAX-ACCESS  read-only
         STATUS      current
         DESCRIPTION
         "Number of GTPv2 Resume Acknowledgement messages received."
     ::= { jnxMbgPgwGtpIfStatsEntry 399 }

jnxMbgPgwIfV2ResumeAckTx OBJECT-TYPE
         SYNTAX      Counter64
         MAX-ACCESS  read-only
         STATUS      current
         DESCRIPTION
         "Number of GTPv2 Resume Acknowledgement messages sent."
     ::= { jnxMbgPgwGtpIfStatsEntry 400 }

jnxMbgPgwIfV2PiggybackMsgRx OBJECT-TYPE
         SYNTAX      Counter64
         MAX-ACCESS  read-only
         STATUS      current
         DESCRIPTION
         "Number of GTPv2 Piggyback messages received."
     ::= { jnxMbgPgwGtpIfStatsEntry 401 }

jnxMbgPgwIfV2PiggybackMsgTx OBJECT-TYPE
         SYNTAX      Counter64
         MAX-ACCESS  read-only
         STATUS      current
         DESCRIPTION
         "Number of GTPv2 Piggyback messages sent."
     ::= { jnxMbgPgwGtpIfStatsEntry 402 }

--
-- GTP Object for showing GTP Global Config Parameters
--
jnxMbgPgwGtpCGlblCfgGroup      OBJECT IDENTIFIER ::=
                                              { jnxMbgPgwGtpObjects 1 }

--
-- GTP Object for showing GTP Gn and GP Config Parameters
--

jnxMbgPgwGtpCGnGpGlblCfgGroup  OBJECT IDENTIFIER ::=
                                              { jnxMbgPgwGtpObjects 2 }

--
-- GTP Object for showing GTP S5 and S8 Config Parameters
--

jnxMbgPgwGtpCS5S8GlblCfgGroup  OBJECT IDENTIFIER ::=
                                              { jnxMbgPgwGtpObjects 3 }

--
-- GTP Object for showing GTP Version 2 Statistics
--
jnxMbgPgwGtpV2Stats                 OBJECT IDENTIFIER ::=
                                              { jnxMbgPgwGtpObjects 4 }

--
-- GTP Object for showing GTP Version 1 Statistics
--

jnxMbgPgwGtpV1Stats                 OBJECT IDENTIFIER ::=
                                              { jnxMbgPgwGtpObjects 5 }
--
-- GTP Object for showing GTP Version 0 Statistics
--

jnxMbgPgwGtpV0Stats                 OBJECT IDENTIFIER ::=
                                              { jnxMbgPgwGtpObjects 8 }
--
-- GtpC Global Configuration Group elements.
--

jnxMbgPgwGtpGWName   OBJECT-TYPE
    SYNTAX      DisplayString
    MAX-ACCESS  read-only
    STATUS      deprecated
    DESCRIPTION
    "Gateway Name."
    ::= { jnxMbgPgwGtpCGlblCfgGroup 1 }


jnxMbgPgwGtpPeerHistory   OBJECT-TYPE
    SYNTAX      Unsigned32
    MAX-ACCESS  read-only
    STATUS      deprecated
    DESCRIPTION
    "Number of Peers to be retained in history."
    ::= { jnxMbgPgwGtpCGlblCfgGroup 2 }


jnxMbgPgwGtpN3Reqs   OBJECT-TYPE
    SYNTAX      Unsigned32
    MAX-ACCESS  read-only
    STATUS      deprecated
    DESCRIPTION
    "Number of N3 Requests."
    ::= { jnxMbgPgwGtpCGlblCfgGroup 3 }


jnxMbgPgwGtpT3Resp   OBJECT-TYPE
    SYNTAX      Unsigned32
    MAX-ACCESS  read-only
    STATUS      deprecated
    DESCRIPTION
    "Number of T3 Responses."
    ::= { jnxMbgPgwGtpCGlblCfgGroup 4 }


jnxMbgPgwGtpCtrlEchIntr   OBJECT-TYPE
    SYNTAX      Unsigned32
    MAX-ACCESS  read-only
    STATUS      deprecated
    DESCRIPTION
    "GTPC Echo Interval in seconds."
    ::= { jnxMbgPgwGtpCGlblCfgGroup 5 }


jnxMbgPgwGtpCtrlNoPathMgmt   OBJECT-TYPE
    SYNTAX      Unsigned32
    MAX-ACCESS  read-only
    STATUS      deprecated
    DESCRIPTION
    "Detremine if Control Path Management is Enabled."
    ::= { jnxMbgPgwGtpCGlblCfgGroup 6 }


jnxMbgPgwGtpCtrlIfName   OBJECT-TYPE
    SYNTAX      DisplayString
    MAX-ACCESS  read-only
    STATUS      deprecated
    DESCRIPTION
    "GTPC Interface Name."
    ::= { jnxMbgPgwGtpCGlblCfgGroup 7 }


jnxMbgPgwGtpCtrlIfRtbId   OBJECT-TYPE
    SYNTAX      Unsigned32
    MAX-ACCESS  read-only
    STATUS      deprecated
    DESCRIPTION
    "GTP Control RTB ID."
    ::= { jnxMbgPgwGtpCGlblCfgGroup 8 }


jnxMbgPgwGtpCtrlIPv4Addr   OBJECT-TYPE
    SYNTAX      InetAddress ( SIZE (4) )
    MAX-ACCESS  read-only
    STATUS      deprecated
    DESCRIPTION
    "GTPC Local IPv4 Address."
    ::= { jnxMbgPgwGtpCGlblCfgGroup 9 }


jnxMbgPgwGtpCtrlIPv6Addr   OBJECT-TYPE
    SYNTAX      InetAddress ( SIZE (16) )
    MAX-ACCESS  read-only
    STATUS      deprecated
    DESCRIPTION
    "GTPC Local IPv6 Address, if absent returns NULL."
    ::= { jnxMbgPgwGtpCGlblCfgGroup 10 }


jnxMbgPgwGtpDataN3Reqs   OBJECT-TYPE
    SYNTAX      Unsigned32
    MAX-ACCESS  read-only
    STATUS      deprecated
    DESCRIPTION
    "Number of Datapath N3 Requests."
    ::= { jnxMbgPgwGtpCGlblCfgGroup 11 }


jnxMbgPgwGtpDataT3Resp   OBJECT-TYPE
    SYNTAX      Unsigned32
    MAX-ACCESS  read-only
    STATUS      deprecated
    DESCRIPTION
    "Number of Datapath T3 Responses."
    ::= { jnxMbgPgwGtpCGlblCfgGroup 12 }


jnxMbgPgwGtpDataEchIntr   OBJECT-TYPE
    SYNTAX      Unsigned32
    MAX-ACCESS  read-only
    STATUS      deprecated
    DESCRIPTION
    "GTPU Echo Interval in seconds."
    ::= { jnxMbgPgwGtpCGlblCfgGroup 13 }


jnxMbgPgwGtpDataNoPathMgmt   OBJECT-TYPE
    SYNTAX      Unsigned32
    MAX-ACCESS  read-only
    STATUS      deprecated
    DESCRIPTION
    "Determine if Datapath Path Management is enabled."
    ::= { jnxMbgPgwGtpCGlblCfgGroup 14 }


jnxMbgPgwGtpDataIfName   OBJECT-TYPE
    SYNTAX      DisplayString
    MAX-ACCESS  read-only
    STATUS      deprecated
    DESCRIPTION
    "GTPU datapath Interface Name."
    ::= { jnxMbgPgwGtpCGlblCfgGroup 15 }


jnxMbgPgwGtpDataIfRtbId   OBJECT-TYPE
    SYNTAX      Unsigned32
    MAX-ACCESS  read-only
    STATUS      deprecated
    DESCRIPTION
    "GTP Datapath RTB Id."
    ::= { jnxMbgPgwGtpCGlblCfgGroup 16 }


jnxMbgPgwGtpDataIPv4Addr   OBJECT-TYPE
    SYNTAX      InetAddress ( SIZE (4) )
    MAX-ACCESS  read-only
    STATUS      deprecated
    DESCRIPTION
    "GTPU Local IPv4 Address."
    ::= { jnxMbgPgwGtpCGlblCfgGroup 17 }


jnxMbgPgwGtpDataIPv6Addr   OBJECT-TYPE
    SYNTAX      InetAddress ( SIZE (16) )
    MAX-ACCESS  read-only
    STATUS      deprecated
    DESCRIPTION
    "GTPU Local IPv6 Address, if absent returns NULL."
    ::= { jnxMbgPgwGtpCGlblCfgGroup 18 }

--
-- GTP V2 Stats Elements.
--

jnxMbgPgwV2NumMsgRx  OBJECT-TYPE
    SYNTAX      Counter64
    MAX-ACCESS  read-only
    STATUS      deprecated
    DESCRIPTION
    "Number of GTPv2 messages received."
    ::= { jnxMbgPgwGtpV2Stats 1 }


jnxMbgPgwV2NumBytesRx  OBJECT-TYPE
    SYNTAX      Counter64
    MAX-ACCESS  read-only
    STATUS      deprecated
    DESCRIPTION
    "Number of GTPv2 bytes received."
    ::= { jnxMbgPgwGtpV2Stats 2 }


jnxMbgPgwUnSupportedMsg  OBJECT-TYPE
    SYNTAX      Counter64
    MAX-ACCESS  read-only
    STATUS      deprecated
    DESCRIPTION
    "Number of GTPv2 Unsupported Messages received."
    ::= { jnxMbgPgwGtpV2Stats 3 }


jnxMbgPgwProtocolErr  OBJECT-TYPE
    SYNTAX      Counter64
    MAX-ACCESS  read-only
    STATUS      deprecated
    DESCRIPTION
    "Number of GTPv2 Protocol Errors."
    ::= { jnxMbgPgwGtpV2Stats 4 }


jnxMbgPgwT3RespTmrExp  OBJECT-TYPE
    SYNTAX      Counter64
    MAX-ACCESS  read-only
    STATUS      deprecated
    DESCRIPTION
    "GTP V2 Number of T3 timer expiries."
    ::= { jnxMbgPgwGtpV2Stats 5 }


jnxMbgPgwmsgRedirectRX  OBJECT-TYPE
    SYNTAX      Counter64
    MAX-ACCESS  read-only
    STATUS      deprecated
    DESCRIPTION
    "GTP V2 Number of received message redirected to SPs for error handling received."
    ::= { jnxMbgPgwGtpV2Stats 6 }


jnxMbgPgwmsgRedirectTX  OBJECT-TYPE
    SYNTAX      Counter64
    MAX-ACCESS  read-only
    STATUS      deprecated
    DESCRIPTION
    "Number of GTP V2 sent messages redirected to SPs for error handling sent."
    ::= { jnxMbgPgwGtpV2Stats 7 }


jnxMbgPgwCreateSessReqRx  OBJECT-TYPE
    SYNTAX      Counter64
    MAX-ACCESS  read-only
    STATUS      deprecated
    DESCRIPTION
    "Number of GTP V2 Create Session Requests received."
    ::= { jnxMbgPgwGtpV2Stats 8 }


jnxMbgPgwCreateSessRspRx  OBJECT-TYPE
    SYNTAX      Counter64
    MAX-ACCESS  read-only
    STATUS      deprecated
    DESCRIPTION
    "Number of GTP V2 Create Session Responses received."
    ::= { jnxMbgPgwGtpV2Stats 9 }


jnxMbgPgwModBrReqRx  OBJECT-TYPE
    SYNTAX      Counter64
    MAX-ACCESS  read-only
    STATUS      deprecated
    DESCRIPTION
    "Number of GTP V2 Modify Bearer Requests received."
    ::= { jnxMbgPgwGtpV2Stats 10 }


jnxMbgPgwModBrRspRx  OBJECT-TYPE
    SYNTAX      Counter64
    MAX-ACCESS  read-only
    STATUS      deprecated
    DESCRIPTION
    "Number of GTP V2 Modify Bearer Responses received."
    ::= { jnxMbgPgwGtpV2Stats 11 }


jnxMbgPgwDelSessReqRx  OBJECT-TYPE
    SYNTAX      Counter64
    MAX-ACCESS  read-only
    STATUS      deprecated
    DESCRIPTION
    "Number of GTP V2 Delete Session Requests received."
    ::= { jnxMbgPgwGtpV2Stats 12 }


jnxMbgPgwDelSessRspRx  OBJECT-TYPE
    SYNTAX      Counter64
    MAX-ACCESS  read-only
    STATUS      deprecated
    DESCRIPTION
    "Number of GTP V2 Delete Session Responses received."
    ::= { jnxMbgPgwGtpV2Stats 13 }


jnxMbgPgwCngNotifReqRx  OBJECT-TYPE
    SYNTAX      Counter64
    MAX-ACCESS  read-only
    STATUS      deprecated
    DESCRIPTION
    "Number of GTP V2 CNG Notify Requests received."
    ::= { jnxMbgPgwGtpV2Stats 14 }


jnxMbgPgwCngNotifRspRx  OBJECT-TYPE
    SYNTAX      Counter64
    MAX-ACCESS  read-only
    STATUS      deprecated
    DESCRIPTION
    "Number of GTP V2 CNG Notify Responses received."
    ::= { jnxMbgPgwGtpV2Stats 15 }


jnxMbgPgwModBrCmdRx  OBJECT-TYPE
    SYNTAX      Counter64
    MAX-ACCESS  read-only
    STATUS      deprecated
    DESCRIPTION
    "Number of GTP V2 Modify Bearer Command received."
    ::= { jnxMbgPgwGtpV2Stats 16 }


jnxMbgPgwModBrFlrIndRx  OBJECT-TYPE
    SYNTAX      Counter64
    MAX-ACCESS  read-only
    STATUS      deprecated
    DESCRIPTION
    "Number of GTP V2 Modify Bearer Failure received."
    ::= { jnxMbgPgwGtpV2Stats 17 }


jnxMbgPgwDelBrCmdRx  OBJECT-TYPE
    SYNTAX      Counter64
    MAX-ACCESS  read-only
    STATUS      deprecated
    DESCRIPTION
    "Number of GTP V2 Delete Bearer Command received."
    ::= { jnxMbgPgwGtpV2Stats 18 }


jnxMbgPgwDelBrFlrIndRx  OBJECT-TYPE
    SYNTAX      Counter64
    MAX-ACCESS  read-only
    STATUS      deprecated
    DESCRIPTION
    "Number of GTP V2 Delete Bearer Failure received."
    ::= { jnxMbgPgwGtpV2Stats 19 }


jnxMbgPgwBrResCmdRx  OBJECT-TYPE
    SYNTAX      Counter64
    MAX-ACCESS  read-only
    STATUS      deprecated
    DESCRIPTION
    "Number of GTP V2 Bearer Response Command received."
    ::= { jnxMbgPgwGtpV2Stats 20 }


jnxMbgPgwBrResFlrIndRx  OBJECT-TYPE
    SYNTAX      Counter64
    MAX-ACCESS  read-only
    STATUS      deprecated
    DESCRIPTION
    "Number of GTP V2 Bearer Resource Failure. received."
    ::= { jnxMbgPgwGtpV2Stats 21 }


jnxMbgPgwDlDataNotiFlrIndRx  OBJECT-TYPE
    SYNTAX      Counter64
    MAX-ACCESS  read-only
    STATUS      deprecated
    DESCRIPTION
    "GTP V2 Downlink Data Notification fail received."
    ::= { jnxMbgPgwGtpV2Stats 22 }


jnxMbgPgwTraceSessActRx  OBJECT-TYPE
    SYNTAX      Counter64
    MAX-ACCESS  read-only
    STATUS      deprecated
    DESCRIPTION
    "GTP V2 Trace Session Activate received."
    ::= { jnxMbgPgwGtpV2Stats 23 }


jnxMbgPgwTraceSessDeactRx  OBJECT-TYPE
    SYNTAX      Counter64
    MAX-ACCESS  read-only
    STATUS      deprecated
    DESCRIPTION
    "GTP V2 Trace Session De-activate received."
    ::= { jnxMbgPgwGtpV2Stats 24 }


jnxMbgPgwCrtBrReqRx  OBJECT-TYPE
    SYNTAX      Counter64
    MAX-ACCESS  read-only
    STATUS      deprecated
    DESCRIPTION
    "Number of GTP V2 Create Bearer Requests received."
    ::= { jnxMbgPgwGtpV2Stats 25 }


jnxMbgPgwCrtBrRspRx  OBJECT-TYPE
    SYNTAX      Counter64
    MAX-ACCESS  read-only
    STATUS      deprecated
    DESCRIPTION
    "Number of GTP V2 Create Bearer Response received."
    ::= { jnxMbgPgwGtpV2Stats 26 }


jnxMbgPgwUpdBrReqRx  OBJECT-TYPE
    SYNTAX      Counter64
    MAX-ACCESS  read-only
    STATUS      deprecated
    DESCRIPTION
    "Number of GTP V2 Update Bearer Request received."
    ::= { jnxMbgPgwGtpV2Stats 27 }


jnxMbgPgwUpdBrRspRx  OBJECT-TYPE
    SYNTAX      Counter64
    MAX-ACCESS  read-only
    STATUS      deprecated
    DESCRIPTION
    "Number of GTP V2 Update Bearer Response received."
    ::= { jnxMbgPgwGtpV2Stats 28 }


jnxMbgPgwDelBrReqRx  OBJECT-TYPE
    SYNTAX      Counter64
    MAX-ACCESS  read-only
    STATUS      deprecated
    DESCRIPTION
    "Number of GTP V2 Delete Bearer Request received."
    ::= { jnxMbgPgwGtpV2Stats 29 }


jnxMbgPgwDelBrRspRx  OBJECT-TYPE
    SYNTAX      Counter64
    MAX-ACCESS  read-only
    STATUS      deprecated
    DESCRIPTION
    "Number of GTP V2 Delete Bearer Response received."
    ::= { jnxMbgPgwGtpV2Stats 30 }


jnxMbgPgwDelConnSetReqRx  OBJECT-TYPE
    SYNTAX      Counter64
    MAX-ACCESS  read-only
    STATUS      deprecated
    DESCRIPTION
    "GTP V2 Delete PDN conn set Request received."
    ::= { jnxMbgPgwGtpV2Stats 31 }


jnxMbgPgwDelConnSetRspRx  OBJECT-TYPE
    SYNTAX      Counter64
    MAX-ACCESS  read-only
    STATUS      deprecated
    DESCRIPTION
    "GTP V2 Delete PDN conn set Response received."
    ::= { jnxMbgPgwGtpV2Stats 32 }


jnxMbgPgwDlDataNotifRx  OBJECT-TYPE
    SYNTAX      Counter64
    MAX-ACCESS  read-only
    STATUS      deprecated
    DESCRIPTION
    "GTP V2 Downlink Data Notify received."
    ::= { jnxMbgPgwGtpV2Stats 33 }


jnxMbgPgwDlDataAckRx  OBJECT-TYPE
    SYNTAX      Counter64
    MAX-ACCESS  read-only
    STATUS      deprecated
    DESCRIPTION
    "GTP V2 Downlink Data Notify Acknowledgement received."
    ::= { jnxMbgPgwGtpV2Stats 34 }


jnxMbgPgwUpdConnSetReqRx  OBJECT-TYPE
    SYNTAX      Counter64
    MAX-ACCESS  read-only
    STATUS      deprecated
    DESCRIPTION
    "GTP V2 Update Connset Request received."
    ::= { jnxMbgPgwGtpV2Stats 35 }


jnxMbgPgwUpdConnSetRspRx  OBJECT-TYPE
    SYNTAX      Counter64
    MAX-ACCESS  read-only
    STATUS      deprecated
    DESCRIPTION
    "GTP V2 Update Connset Response received."
    ::= { jnxMbgPgwGtpV2Stats 36 }


jnxMbgPgwV2EchoReqRx  OBJECT-TYPE
    SYNTAX      Counter64
    MAX-ACCESS  read-only
    STATUS      deprecated
    DESCRIPTION
    "GTP V2 Echo Request received."
    ::= { jnxMbgPgwGtpV2Stats 37 }


jnxMbgPgwV2EchoRespRx  OBJECT-TYPE
    SYNTAX      Counter64
    MAX-ACCESS  read-only
    STATUS      deprecated
    DESCRIPTION
    "GTP V2 Echo Response received."
    ::= { jnxMbgPgwGtpV2Stats 38 }


jnxMbgPgwGtpV2ICsPage  OBJECT-TYPE
    SYNTAX      Counter64
    MAX-ACCESS  read-only
    STATUS      deprecated
    DESCRIPTION
    "GTP Cause Page."
    ::= { jnxMbgPgwGtpV2Stats 39 }


jnxMbgPgwGtpV2ICsReqAccept  OBJECT-TYPE
    SYNTAX      Counter64
    MAX-ACCESS  read-only
    STATUS      deprecated
    DESCRIPTION
    "GTP Cause Request Accept."
    ::= { jnxMbgPgwGtpV2Stats 40 }


jnxMbgPgwGtpV2ICsAcceptPart  OBJECT-TYPE
    SYNTAX      Counter64
    MAX-ACCESS  read-only
    STATUS      deprecated
    DESCRIPTION
    "GTP Cause Accept Partial."
    ::= { jnxMbgPgwGtpV2Stats 41 }


jnxMbgPgwGtpV2ICsNewPTSubLT  OBJECT-TYPE
    SYNTAX      Counter64
    MAX-ACCESS  read-only
    STATUS      deprecated
    DESCRIPTION
    "GTP Cause New PDN type due to Subscriber LImit."
    ::= { jnxMbgPgwGtpV2Stats 42 }


jnxMbgPgwGtpV2ICsNewPTNPref  OBJECT-TYPE
    SYNTAX      Counter64
    MAX-ACCESS  read-only
    STATUS      deprecated
    DESCRIPTION
    "GTP Cause New PDN type due to Network Preference"
    ::= { jnxMbgPgwGtpV2Stats 43 }


jnxMbgPgwGtpV2ICsNewPTSIAddrbr  OBJECT-TYPE
    SYNTAX      Counter64
    MAX-ACCESS  read-only
    STATUS      deprecated
    DESCRIPTION
    "GTP Cause New PDN type due to Single Address Bearer."
    ::= { jnxMbgPgwGtpV2Stats 44 }


jnxMbgPgwGtpV2ICsCtxNotFnd  OBJECT-TYPE
    SYNTAX      Counter64
    MAX-ACCESS  read-only
    STATUS      deprecated
    DESCRIPTION
    "GTP Cause Context not found."
    ::= { jnxMbgPgwGtpV2Stats 45 }


jnxMbgPgwGtpV2ICsInvMsgFmt  OBJECT-TYPE
    SYNTAX      Counter64
    MAX-ACCESS  read-only
    STATUS      deprecated
    DESCRIPTION
    "GTP Cause Invalid Message Format."
    ::= { jnxMbgPgwGtpV2Stats 46 }


jnxMbgPgwGtpV2ICsVerNotSupp  OBJECT-TYPE
    SYNTAX      Counter64
    MAX-ACCESS  read-only
    STATUS      deprecated
    DESCRIPTION
    "GTP Cause Version not Supported."
    ::= { jnxMbgPgwGtpV2Stats 47 }


jnxMbgPgwGtpV2ICsInvLen  OBJECT-TYPE
    SYNTAX      Counter64
    MAX-ACCESS  read-only
    STATUS      deprecated
    DESCRIPTION
    "GTP Cause Invalid Length."
    ::= { jnxMbgPgwGtpV2Stats 48 }


jnxMbgPgwGtpV2ICsServNotSupp  OBJECT-TYPE
    SYNTAX      Counter64
    MAX-ACCESS  read-only
    STATUS      deprecated
    DESCRIPTION
    "GTP Cause Service Not supported."
    ::= { jnxMbgPgwGtpV2Stats 49 }


jnxMbgPgwGtpV2ICsManIEIncorr  OBJECT-TYPE
    SYNTAX      Counter64
    MAX-ACCESS  read-only
    STATUS      deprecated
    DESCRIPTION
    "GTP Cause Mandatory IE incorrect."
    ::= { jnxMbgPgwGtpV2Stats 50 }


jnxMbgPgwGtpV2ICsManIEMiss  OBJECT-TYPE
    SYNTAX      Counter64
    MAX-ACCESS  read-only
    STATUS      deprecated
    DESCRIPTION
    "GTP Cause Mandatory IE Missing."
    ::= { jnxMbgPgwGtpV2Stats 51 }


jnxMbgPgwGtpV2ICsOptIEIncorr  OBJECT-TYPE
    SYNTAX      Counter64
    MAX-ACCESS  read-only
    STATUS      deprecated
    DESCRIPTION
    "GTP Cause Optional IE Incorrect."
    ::= { jnxMbgPgwGtpV2Stats 52 }


jnxMbgPgwGtpV2ICsSysFail  OBJECT-TYPE
    SYNTAX      Counter64
    MAX-ACCESS  read-only
    STATUS      deprecated
    DESCRIPTION
    "GTP Cause System Failure."
    ::= { jnxMbgPgwGtpV2Stats 53 }


jnxMbgPgwGtpV2ICsNoRes  OBJECT-TYPE
    SYNTAX      Counter64
    MAX-ACCESS  read-only
    STATUS      deprecated
    DESCRIPTION
    "GTP Cause No Resource."
    ::= { jnxMbgPgwGtpV2Stats 54 }


jnxMbgPgwGtpV2ICsTFTSMANTErr  OBJECT-TYPE
    SYNTAX      Counter64
    MAX-ACCESS  read-only
    STATUS      deprecated
    DESCRIPTION
    "GTP Cause TFT Symantic Error."
    ::= { jnxMbgPgwGtpV2Stats 55 }


jnxMbgPgwGtpV2ICsTFTSysErr  OBJECT-TYPE
    SYNTAX      Counter64
    MAX-ACCESS  read-only
    STATUS      deprecated
    DESCRIPTION
    "GTP Cause TFT System Error."
    ::= { jnxMbgPgwGtpV2Stats 56 }


jnxMbgPgwGtpV2ICsPktFltrsMantErr  OBJECT-TYPE
    SYNTAX      Counter64
    MAX-ACCESS  read-only
    STATUS      deprecated
    DESCRIPTION
    "GTP Cause Packet Filter Symantic Error."
    ::= { jnxMbgPgwGtpV2Stats 57 }


jnxMbgPgwGtpV2ICsPktFltrSynErr  OBJECT-TYPE
    SYNTAX      Counter64
    MAX-ACCESS  read-only
    STATUS      deprecated
    DESCRIPTION
    "GTP Cause Packet Filter Syntax Error."
    ::= { jnxMbgPgwGtpV2Stats 58 }


jnxMbgPgwGtpV2ICsMissUnkownAPN  OBJECT-TYPE
    SYNTAX      Counter64
    MAX-ACCESS  read-only
    STATUS      deprecated
    DESCRIPTION
    "GTP Cause Unknown APN."
    ::= { jnxMbgPgwGtpV2Stats 59 }


jnxMbgPgwGtpV2ICsUnexpRepeatIE  OBJECT-TYPE
    SYNTAX      Counter64
    MAX-ACCESS  read-only
    STATUS      deprecated
    DESCRIPTION
    "GTP Cause Unexpected Repeated IE."
    ::= { jnxMbgPgwGtpV2Stats 60 }


jnxMbgPgwGtpV2ICsGREKeyNotFnd  OBJECT-TYPE
    SYNTAX      Counter64
    MAX-ACCESS  read-only
    STATUS      deprecated
    DESCRIPTION
    "GTP Cause GRE Key Not Found."
    ::= { jnxMbgPgwGtpV2Stats 61 }


jnxMbgPgwGtpV2ICsRelocFail  OBJECT-TYPE
    SYNTAX      Counter64
    MAX-ACCESS  read-only
    STATUS      deprecated
    DESCRIPTION
    "GTP Cause Relocation Failed."
    ::= { jnxMbgPgwGtpV2Stats 62 }


jnxMbgPgwGtpV2ICsDeniedINRat  OBJECT-TYPE
    SYNTAX      Counter64
    MAX-ACCESS  read-only
    STATUS      deprecated
    DESCRIPTION
    "GTP Cause Denied in RAT."
    ::= { jnxMbgPgwGtpV2Stats 63 }


jnxMbgPgwGtpV2ICsPTNotSupp  OBJECT-TYPE
    SYNTAX      Counter64
    MAX-ACCESS  read-only
    STATUS      deprecated
    DESCRIPTION
    "GTP Cause PDN Type Not Supported."
    ::= { jnxMbgPgwGtpV2Stats 64 }


jnxMbgPgwGtpV2ICsAllDynAddrOcc  OBJECT-TYPE
    SYNTAX      Counter64
    MAX-ACCESS  read-only
    STATUS      deprecated
    DESCRIPTION
    "GTP Cause Allocated Dynamic Address Occupied."
    ::= { jnxMbgPgwGtpV2Stats 65 }


jnxMbgPgwGtpV2ICsNOTFTUECTXEXIS  OBJECT-TYPE
    SYNTAX      Counter64
    MAX-ACCESS  read-only
    STATUS      deprecated
    DESCRIPTION
    "GTP Cause UE Context Without TFT Exists."
    ::= { jnxMbgPgwGtpV2Stats 66 }


jnxMbgPgwGtpV2ICsProtoNotSupp  OBJECT-TYPE
    SYNTAX      Counter64
    MAX-ACCESS  read-only
    STATUS      deprecated
    DESCRIPTION
    "GTP Cause Protocol Not Supported."
    ::= { jnxMbgPgwGtpV2Stats 67 }


jnxMbgPgwGtpV2ICsUENotResp  OBJECT-TYPE
    SYNTAX      Counter64
    MAX-ACCESS  read-only
    STATUS      deprecated
    DESCRIPTION
    "GTP Cause UE Not Responding."
    ::= { jnxMbgPgwGtpV2Stats 68 }


jnxMbgPgwGtpV2ICsUERefuses  OBJECT-TYPE
    SYNTAX      Counter64
    MAX-ACCESS  read-only
    STATUS      deprecated
    DESCRIPTION
    "GTP Cause UE Refuses."
    ::= { jnxMbgPgwGtpV2Stats 69 }


jnxMbgPgwGtpV2ICsServDenied  OBJECT-TYPE
    SYNTAX      Counter64
    MAX-ACCESS  read-only
    STATUS      deprecated
    DESCRIPTION
    "GTP Cause Service Denied."
    ::= { jnxMbgPgwGtpV2Stats 70 }


jnxMbgPgwGtpV2ICsUnablePageUE  OBJECT-TYPE
    SYNTAX      Counter64
    MAX-ACCESS  read-only
    STATUS      deprecated
    DESCRIPTION
    "GTP Cause Unable to Page UE."
    ::= { jnxMbgPgwGtpV2Stats 71 }


jnxMbgPgwGtpV2ICsNoMem  OBJECT-TYPE
    SYNTAX      Counter64
    MAX-ACCESS  read-only
    STATUS      deprecated
    DESCRIPTION
    "GTP Cause No Memory."
    ::= { jnxMbgPgwGtpV2Stats 72 }


jnxMbgPgwGtpV2ICsUserAUTHFail  OBJECT-TYPE
    SYNTAX      Counter64
    MAX-ACCESS  read-only
    STATUS      deprecated
    DESCRIPTION
    "GTP Cause User AUTH Failed."
    ::= { jnxMbgPgwGtpV2Stats 73 }


jnxMbgPgwGtpV2ICsAPNAccessDenied  OBJECT-TYPE
    SYNTAX      Counter64
    MAX-ACCESS  read-only
    STATUS      deprecated
    DESCRIPTION
    "GTP Cause APN Access Denied."
    ::= { jnxMbgPgwGtpV2Stats 74 }


jnxMbgPgwGtpV2ICsReqRej  OBJECT-TYPE
    SYNTAX      Counter64
    MAX-ACCESS  read-only
    STATUS      deprecated
    DESCRIPTION
    "GTP Cause Request Rejected."
    ::= { jnxMbgPgwGtpV2Stats 75 }

jnxMbgPgwV2NumMsgTx  OBJECT-TYPE
    SYNTAX      Counter64
    MAX-ACCESS  read-only
    STATUS      deprecated
    DESCRIPTION
    "Number of V2 messages sent."
    ::= { jnxMbgPgwGtpV2Stats 76 }


jnxMbgPgwV2NumBytesTx  OBJECT-TYPE
    SYNTAX      Counter64
    MAX-ACCESS  read-only
    STATUS      deprecated
    DESCRIPTION
    "Number of V2 bytes sent."
    ::= { jnxMbgPgwGtpV2Stats 77 }

jnxMbgPgwCreateSessReqTx  OBJECT-TYPE
    SYNTAX      Counter64
    MAX-ACCESS  read-only
    STATUS      deprecated
    DESCRIPTION
    "Number of GTP V2 Create Session Requests Sent."
    ::= { jnxMbgPgwGtpV2Stats 78 }


jnxMbgPgwCreateSessRspTx  OBJECT-TYPE
    SYNTAX      Counter64
    MAX-ACCESS  read-only
    STATUS      deprecated
    DESCRIPTION
    "Number of GTP V2 Create Session Responses Sent."
    ::= { jnxMbgPgwGtpV2Stats 79 }


jnxMbgPgwModBrReqTx  OBJECT-TYPE
    SYNTAX      Counter64
    MAX-ACCESS  read-only
    STATUS      deprecated
    DESCRIPTION
    "Number of GTP V2 Modify Bearer Requests Sent."
    ::= { jnxMbgPgwGtpV2Stats 80 }


jnxMbgPgwModBrRspTx  OBJECT-TYPE
    SYNTAX      Counter64
    MAX-ACCESS  read-only
    STATUS      deprecated
    DESCRIPTION
    "Number of GTP V2 Modify Bearer Responses Sent."
    ::= { jnxMbgPgwGtpV2Stats 81 }


jnxMbgPgwDelSessReqTx  OBJECT-TYPE
    SYNTAX      Counter64
    MAX-ACCESS  read-only
    STATUS      deprecated
    DESCRIPTION
    "Number of GTP V2 Delete Session Requests Sent."
    ::= { jnxMbgPgwGtpV2Stats 82 }


jnxMbgPgwDelSessRspTx  OBJECT-TYPE
    SYNTAX      Counter64
    MAX-ACCESS  read-only
    STATUS      deprecated
    DESCRIPTION
    "Number of GTP V2 Delete Session Responses Sent."
    ::= { jnxMbgPgwGtpV2Stats 83 }


jnxMbgPgwCngNotifReqTx  OBJECT-TYPE
    SYNTAX      Counter64
    MAX-ACCESS  read-only
    STATUS      deprecated
    DESCRIPTION
    "Number of GTP V2 CNG Notify Requests Sent."
    ::= { jnxMbgPgwGtpV2Stats 84 }


jnxMbgPgwCngNotifRspTx  OBJECT-TYPE
    SYNTAX      Counter64
    MAX-ACCESS  read-only
    STATUS      deprecated
    DESCRIPTION
    "Number of GTP V2 CNG Notify Responses Sent."
    ::= { jnxMbgPgwGtpV2Stats 85 }


jnxMbgPgwModBrCmdTx  OBJECT-TYPE
    SYNTAX      Counter64
    MAX-ACCESS  read-only
    STATUS      deprecated
    DESCRIPTION
    "Number of GTP V2 Modify Bearer Command Sent."
    ::= { jnxMbgPgwGtpV2Stats 86 }


jnxMbgPgwModBrFlrIndTx  OBJECT-TYPE
    SYNTAX      Counter64
    MAX-ACCESS  read-only
    STATUS      deprecated
    DESCRIPTION
    "Number of GTP V2 Modify Bearer Failure Sent."
    ::= { jnxMbgPgwGtpV2Stats 87 }


jnxMbgPgwDelBrCmdTx  OBJECT-TYPE
    SYNTAX      Counter64
    MAX-ACCESS  read-only
    STATUS      deprecated
    DESCRIPTION
    "Number of GTP V2 Delete Bearer Command Sent."
    ::= { jnxMbgPgwGtpV2Stats 88 }


jnxMbgPgwDelBrFlrIndTx  OBJECT-TYPE
    SYNTAX      Counter64
    MAX-ACCESS  read-only
    STATUS      deprecated
    DESCRIPTION
    "Number of GTP V2 Delete Bearer Failure Sent."
    ::= { jnxMbgPgwGtpV2Stats 89 }


jnxMbgPgwBrResCmdTx  OBJECT-TYPE
    SYNTAX      Counter64
    MAX-ACCESS  read-only
    STATUS      deprecated
    DESCRIPTION
    "Number of GTP V2 Bearer Response Command Sent."
    ::= { jnxMbgPgwGtpV2Stats 90 }


jnxMbgPgwBrResFlrIndTx  OBJECT-TYPE
    SYNTAX      Counter64
    MAX-ACCESS  read-only
    STATUS      deprecated
    DESCRIPTION
    "Number of GTP V2 Bearer Resource Failure. Sent."
    ::= { jnxMbgPgwGtpV2Stats 91 }


jnxMbgPgwDlDataNotiFlrIndTx  OBJECT-TYPE
    SYNTAX      Counter64
    MAX-ACCESS  read-only
    STATUS      deprecated
    DESCRIPTION
    "GTP V2 Downlink Data Notification fail Sent."
    ::= { jnxMbgPgwGtpV2Stats 92 }


jnxMbgPgwTraceSessActTx  OBJECT-TYPE
    SYNTAX      Counter64
    MAX-ACCESS  read-only
    STATUS      deprecated
    DESCRIPTION
    "GTP V2 Trace Session Activate Sent."
    ::= { jnxMbgPgwGtpV2Stats 93 }


jnxMbgPgwTraceSessDeactTx  OBJECT-TYPE
    SYNTAX      Counter64
    MAX-ACCESS  read-only
    STATUS      deprecated
    DESCRIPTION
    "GTP V2 Trace Session De-activate Sent."
    ::= { jnxMbgPgwGtpV2Stats 94 }


jnxMbgPgwCrtBrReqTx  OBJECT-TYPE
    SYNTAX      Counter64
    MAX-ACCESS  read-only
    STATUS      deprecated
    DESCRIPTION
    "Number of GTP V2 Create Bearer Requests Sent."
    ::= { jnxMbgPgwGtpV2Stats 95 }


jnxMbgPgwCrtBrRspTx  OBJECT-TYPE
    SYNTAX      Counter64
    MAX-ACCESS  read-only
    STATUS      deprecated
    DESCRIPTION
    "Number of GTP V2 Create Bearer Response Sent."
    ::= { jnxMbgPgwGtpV2Stats 96 }


jnxMbgPgwUpdBrReqTx  OBJECT-TYPE
    SYNTAX      Counter64
    MAX-ACCESS  read-only
    STATUS      deprecated
    DESCRIPTION
    "Number of GTP V2 Update Bearer Request Sent."
    ::= { jnxMbgPgwGtpV2Stats 97 }


jnxMbgPgwUpdBrRspTx  OBJECT-TYPE
    SYNTAX      Counter64
    MAX-ACCESS  read-only
    STATUS      deprecated
    DESCRIPTION
    "Number of GTP V2 Update Bearer Response Sent."
    ::= { jnxMbgPgwGtpV2Stats 98 }


jnxMbgPgwDelBrReqTx  OBJECT-TYPE
    SYNTAX      Counter64
    MAX-ACCESS  read-only
    STATUS      deprecated
    DESCRIPTION
    "Number of GTP V2 Delete Bearer Request Sent."
    ::= { jnxMbgPgwGtpV2Stats 99 }


jnxMbgPgwDelBrRspTx  OBJECT-TYPE
    SYNTAX      Counter64
    MAX-ACCESS  read-only
    STATUS      deprecated
    DESCRIPTION
    "Number of GTP V2 Delete Bearer Response Sent."
    ::= { jnxMbgPgwGtpV2Stats 100 }


jnxMbgPgwDelConnSetReqTx  OBJECT-TYPE
    SYNTAX      Counter64
    MAX-ACCESS  read-only
    STATUS      deprecated
    DESCRIPTION
    "GTP V2 Delete PDN conn set Request Sent."
    ::= { jnxMbgPgwGtpV2Stats 101 }


jnxMbgPgwDelConnSetRspTx  OBJECT-TYPE
    SYNTAX      Counter64
    MAX-ACCESS  read-only
    STATUS      deprecated
    DESCRIPTION
    "GTP V2 Delete PDN conn set Response Sent."
    ::= { jnxMbgPgwGtpV2Stats 102 }


jnxMbgPgwDlDataNotifTx  OBJECT-TYPE
    SYNTAX      Counter64
    MAX-ACCESS  read-only
    STATUS      deprecated
    DESCRIPTION
    "GTP V2 Downlink Data Notify Sent."
    ::= { jnxMbgPgwGtpV2Stats 103 }


jnxMbgPgwDlDataAckTx  OBJECT-TYPE
    SYNTAX      Counter64
    MAX-ACCESS  read-only
    STATUS      deprecated
    DESCRIPTION
    "GTP V2 Downlink Data Notify Acknowledgement Sent."
    ::= { jnxMbgPgwGtpV2Stats 104 }


jnxMbgPgwUpdConnSetReqTx  OBJECT-TYPE
    SYNTAX      Counter64
    MAX-ACCESS  read-only
    STATUS      deprecated
    DESCRIPTION
    "GTP V2 Update Connset Request Sent."
    ::= { jnxMbgPgwGtpV2Stats 105 }


jnxMbgPgwUpdConnSetRspTx  OBJECT-TYPE
    SYNTAX      Counter64
    MAX-ACCESS  read-only
    STATUS      deprecated
    DESCRIPTION
    "GTP V2 Update Connset Response Sent."
    ::= { jnxMbgPgwGtpV2Stats 106 }


jnxMbgPgwV2EchoReqTx  OBJECT-TYPE
    SYNTAX      Counter64
    MAX-ACCESS  read-only
    STATUS      deprecated
    DESCRIPTION
    "GTP V2 Echo Request Sent."
    ::= { jnxMbgPgwGtpV2Stats 107 }


jnxMbgPgwV2EchoRespTx  OBJECT-TYPE
    SYNTAX      Counter64
    MAX-ACCESS  read-only
    STATUS      deprecated
    DESCRIPTION
    "GTP V2 Echo Response Sent."
    ::= { jnxMbgPgwGtpV2Stats 108 }

--
-- GtpC Gn Gp Global Configuration Group elements.
--

jnxMbgPgwGtpCGnGpGWName   OBJECT-TYPE
    SYNTAX      DisplayString
    MAX-ACCESS  read-only
    STATUS      deprecated
    DESCRIPTION
    "Gateway Name."
    ::= { jnxMbgPgwGtpCGnGpGlblCfgGroup 1 }


jnxMbgPgwGtpCGnGpPeerHistory   OBJECT-TYPE
    SYNTAX      Unsigned32
    MAX-ACCESS  read-only
    STATUS      deprecated
    DESCRIPTION
    "Number of Peers to be retained in history."
    ::= { jnxMbgPgwGtpCGnGpGlblCfgGroup 2 }


jnxMbgPgwGtpCGnGpN3Reqs   OBJECT-TYPE
    SYNTAX      Unsigned32
    MAX-ACCESS  read-only
    STATUS      deprecated
    DESCRIPTION
    "Number of N3 Requests."
    ::= { jnxMbgPgwGtpCGnGpGlblCfgGroup 3 }


jnxMbgPgwGtpCGnGpT3Resp   OBJECT-TYPE
    SYNTAX      Unsigned32
    MAX-ACCESS  read-only
    STATUS      deprecated
    DESCRIPTION
    "Number of T3 Responses."
    ::= { jnxMbgPgwGtpCGnGpGlblCfgGroup 4 }


jnxMbgPgwGtpCGnGpCtrlEchIntr   OBJECT-TYPE
    SYNTAX      Unsigned32
    MAX-ACCESS  read-only
    STATUS      deprecated
    DESCRIPTION
    "GTPC Echo Interval in seconds."
    ::= { jnxMbgPgwGtpCGnGpGlblCfgGroup 5 }


jnxMbgPgwGtpCGnGpCtrlNoPathMgmt   OBJECT-TYPE
    SYNTAX      Unsigned32
    MAX-ACCESS  read-only
    STATUS      deprecated
    DESCRIPTION
    "Control Path Management Enabled."
    ::= { jnxMbgPgwGtpCGnGpGlblCfgGroup 6 }


jnxMbgPgwGtpCGnGpCtrlIfName   OBJECT-TYPE
    SYNTAX      DisplayString
    MAX-ACCESS  read-only
    STATUS      deprecated
    DESCRIPTION
    "GTPC Interface Name."
    ::= { jnxMbgPgwGtpCGnGpGlblCfgGroup 7 }


jnxMbgPgwGtpCGnGpCtrlIfRtbId   OBJECT-TYPE
    SYNTAX      Unsigned32
    MAX-ACCESS  read-only
    STATUS      deprecated
    DESCRIPTION
    "GTP Control RTB ID."
    ::= { jnxMbgPgwGtpCGnGpGlblCfgGroup 8 }


jnxMbgPgwGtpCGnGpCtrlIPv4Addr   OBJECT-TYPE
    SYNTAX      InetAddress ( SIZE (4) )
    MAX-ACCESS  read-only
    STATUS      deprecated
    DESCRIPTION
    "GTPC Local IPv4 Address."
    ::= { jnxMbgPgwGtpCGnGpGlblCfgGroup 9 }


jnxMbgPgwGtpCGnGpCtrlIPv6Addr   OBJECT-TYPE
    SYNTAX      InetAddress ( SIZE (16) )
    MAX-ACCESS  read-only
    STATUS      deprecated
    DESCRIPTION
    "GTPC Local IPv6 Address."
    ::= { jnxMbgPgwGtpCGnGpGlblCfgGroup 10 }


jnxMbgPgwGtpCGnGpDataN3Reqs   OBJECT-TYPE
    SYNTAX      Unsigned32
    MAX-ACCESS  read-only
    STATUS      deprecated
    DESCRIPTION
    "Number of Datapath N3 Requests."
    ::= { jnxMbgPgwGtpCGnGpGlblCfgGroup 11 }


jnxMbgPgwGtpCGnGpDataT3Resp   OBJECT-TYPE
    SYNTAX      Unsigned32
    MAX-ACCESS  read-only
    STATUS      deprecated
    DESCRIPTION
    "Number of Datapath T3 Responses."
    ::= { jnxMbgPgwGtpCGnGpGlblCfgGroup 12 }


jnxMbgPgwGtpCGnGpDataEchIntr   OBJECT-TYPE
    SYNTAX      Unsigned32
    MAX-ACCESS  read-only
    STATUS      deprecated
    DESCRIPTION
    "GTPU Echo Interval in seconds."
    ::= { jnxMbgPgwGtpCGnGpGlblCfgGroup 13 }


jnxMbgPgwGtpCGnGpDataNoPathMgmt   OBJECT-TYPE
    SYNTAX      Unsigned32
    MAX-ACCESS  read-only
    STATUS      deprecated
    DESCRIPTION
    "Datapath Path Management enabled."
    ::= { jnxMbgPgwGtpCGnGpGlblCfgGroup 14 }


jnxMbgPgwGtpCGnGpDataIfName   OBJECT-TYPE
    SYNTAX      DisplayString
    MAX-ACCESS  read-only
    STATUS      deprecated
    DESCRIPTION
    "GTPU datapath Interface Name."
    ::= { jnxMbgPgwGtpCGnGpGlblCfgGroup 15 }


jnxMbgPgwGtpCGnGpDataIfRtbId   OBJECT-TYPE
    SYNTAX      Unsigned32
    MAX-ACCESS  read-only
    STATUS      deprecated
    DESCRIPTION
    "GTP Datapath RTB Id."
    ::= { jnxMbgPgwGtpCGnGpGlblCfgGroup 16 }


jnxMbgPgwGtpCGnGpDataIPv4Addr   OBJECT-TYPE
    SYNTAX      InetAddress ( SIZE (4) )
    MAX-ACCESS  read-only
    STATUS      deprecated
    DESCRIPTION
    "GTPU Local IPv4 Address."
    ::= { jnxMbgPgwGtpCGnGpGlblCfgGroup 17 }


jnxMbgPgwGtpCGnGpDataIPv6Addr   OBJECT-TYPE
    SYNTAX      InetAddress ( SIZE (16) )
    MAX-ACCESS  read-only
    STATUS      deprecated
    DESCRIPTION
    "GTPU Local IPv6 Address."
    ::= { jnxMbgPgwGtpCGnGpGlblCfgGroup 18 }

--
-- GtpC s5 s8 Global Configuration Group elements.
--

jnxMbgPgwGtpCS5S8GWName   OBJECT-TYPE
    SYNTAX      DisplayString
    MAX-ACCESS  read-only
    STATUS      deprecated
    DESCRIPTION
    "Gateway Name."
    ::= { jnxMbgPgwGtpCS5S8GlblCfgGroup 1 }


jnxMbgPgwGtpCS5S8PeerHistory   OBJECT-TYPE
    SYNTAX      Unsigned32
    MAX-ACCESS  read-only
    STATUS      deprecated
    DESCRIPTION
    "Number of Peers to be retained in history."
    ::= { jnxMbgPgwGtpCS5S8GlblCfgGroup 2 }


jnxMbgPgwGtpCS5S8N3Reqs   OBJECT-TYPE
    SYNTAX      Unsigned32
    MAX-ACCESS  read-only
    STATUS      deprecated
    DESCRIPTION
    "Number of N3 Requests."
    ::= { jnxMbgPgwGtpCS5S8GlblCfgGroup 3 }


jnxMbgPgwGtpCS5S8T3Resp   OBJECT-TYPE
    SYNTAX      Unsigned32
    MAX-ACCESS  read-only
    STATUS      deprecated
    DESCRIPTION
    "Number of T3 Responses."
    ::= { jnxMbgPgwGtpCS5S8GlblCfgGroup 4 }


jnxMbgPgwGtpCS5S8CtrlEchIntr   OBJECT-TYPE
    SYNTAX      Unsigned32
    MAX-ACCESS  read-only
    STATUS      deprecated
    DESCRIPTION
    "GTPC Echo Interval in seconds."
    ::= { jnxMbgPgwGtpCS5S8GlblCfgGroup 5 }


jnxMbgPgwGtpCS5S8CtrlNoPathMgmt   OBJECT-TYPE
    SYNTAX      Unsigned32
    MAX-ACCESS  read-only
    STATUS      deprecated
    DESCRIPTION
    "Control Path Management Enabled."
    ::= { jnxMbgPgwGtpCS5S8GlblCfgGroup 6 }


jnxMbgPgwGtpCS5S8CtrlIfName   OBJECT-TYPE
    SYNTAX      DisplayString
    MAX-ACCESS  read-only
    STATUS      deprecated
    DESCRIPTION
    "GTPC Interface Name."
    ::= { jnxMbgPgwGtpCS5S8GlblCfgGroup 7 }


jnxMbgPgwGtpCS5S8CtrlIfRtbId   OBJECT-TYPE
    SYNTAX      Unsigned32
    MAX-ACCESS  read-only
    STATUS      deprecated
    DESCRIPTION
    "GTP Control RTB ID."
    ::= { jnxMbgPgwGtpCS5S8GlblCfgGroup 8 }


jnxMbgPgwGtpCS5S8CtrlIPv4Addr   OBJECT-TYPE
    SYNTAX      InetAddress ( SIZE (4) )
    MAX-ACCESS  read-only
    STATUS      deprecated
    DESCRIPTION
    "GTPC Local IPv4 Address."
    ::= { jnxMbgPgwGtpCS5S8GlblCfgGroup 9 }


jnxMbgPgwGtpCS5S8CtrlIPv6Addr   OBJECT-TYPE
    SYNTAX      InetAddress ( SIZE (16) )
    MAX-ACCESS  read-only
    STATUS      deprecated
    DESCRIPTION
    "GTPC Local IPv6 Address."
    ::= { jnxMbgPgwGtpCS5S8GlblCfgGroup 10 }


jnxMbgPgwGtpCS5S8DataN3Reqs   OBJECT-TYPE
    SYNTAX      Unsigned32
    MAX-ACCESS  read-only
    STATUS      deprecated
    DESCRIPTION
    "Number of Datapath N3 Requests."
    ::= { jnxMbgPgwGtpCS5S8GlblCfgGroup 11 }


jnxMbgPgwGtpCS5S8DataT3Resp   OBJECT-TYPE
    SYNTAX      Unsigned32
    MAX-ACCESS  read-only
    STATUS      deprecated
    DESCRIPTION
    "Number of Datapath T3 Responses."
    ::= { jnxMbgPgwGtpCS5S8GlblCfgGroup 12 }


jnxMbgPgwGtpCS5S8DataEchIntr   OBJECT-TYPE
    SYNTAX      Unsigned32
    MAX-ACCESS  read-only
    STATUS      deprecated
    DESCRIPTION
    "GTPU Echo Interval in seconds."
    ::= { jnxMbgPgwGtpCS5S8GlblCfgGroup 13 }


jnxMbgPgwGtpCS5S8DataNoPathMgmt   OBJECT-TYPE
    SYNTAX      Unsigned32
    MAX-ACCESS  read-only
    STATUS      deprecated
    DESCRIPTION
    "Datapath Path Management enabled."
    ::= { jnxMbgPgwGtpCS5S8GlblCfgGroup 14 }


jnxMbgPgwGtpCS5S8DataIfName   OBJECT-TYPE
    SYNTAX      DisplayString
    MAX-ACCESS  read-only
    STATUS      deprecated
    DESCRIPTION
    "GTPU datapath Interface Name."
    ::= { jnxMbgPgwGtpCS5S8GlblCfgGroup 15 }


jnxMbgPgwGtpCS5S8DataIfRtbId   OBJECT-TYPE
    SYNTAX      Unsigned32
    MAX-ACCESS  read-only
    STATUS      deprecated
    DESCRIPTION
    "GTP Datapath RTB Id."
    ::= { jnxMbgPgwGtpCS5S8GlblCfgGroup 16 }


jnxMbgPgwGtpCS5S8DataIPv4Addr   OBJECT-TYPE
    SYNTAX      InetAddress ( SIZE (4) )
    MAX-ACCESS  read-only
    STATUS      deprecated
    DESCRIPTION
    "GTPU Local IPv4 Address."
    ::= { jnxMbgPgwGtpCS5S8GlblCfgGroup 17 }


jnxMbgPgwGtpCS5S8DataIPv6Addr   OBJECT-TYPE
    SYNTAX      InetAddress ( SIZE (16) )
    MAX-ACCESS  read-only
    STATUS      deprecated
    DESCRIPTION
    "GTPU Local IPv6 Address."
    ::= { jnxMbgPgwGtpCS5S8GlblCfgGroup 18 }

--
-- GTP V0 Stats elements
--

jnxMbgPgwV0NumMsgRx   OBJECT-TYPE
    SYNTAX      Counter64
    MAX-ACCESS  read-only
    STATUS      deprecated
    DESCRIPTION
    "Number Of GTP V0 Messages Rx."
    ::= { jnxMbgPgwGtpV0Stats 1 }


jnxMbgPgwV0NumBytesRx   OBJECT-TYPE
    SYNTAX      Counter64
    MAX-ACCESS  read-only
    STATUS      deprecated
    DESCRIPTION
    "Number of GTP V0 Bytes Rx."
    ::= { jnxMbgPgwGtpV0Stats 2 }


jnxMbgPgwV0UnSupportedMsg   OBJECT-TYPE
    SYNTAX      Counter64
    MAX-ACCESS  read-only
    STATUS      deprecated
    DESCRIPTION
    "Unsupported Messages."
    ::= { jnxMbgPgwGtpV0Stats 3 }


jnxMbgPgwV0ProtErr   OBJECT-TYPE
    SYNTAX      Counter64
    MAX-ACCESS  read-only
    STATUS      deprecated
    DESCRIPTION
    "GTP V0 Protocol Errors."
    ::= { jnxMbgPgwGtpV0Stats 4 }


jnxMbgPgwV0T3RespTmrExp   OBJECT-TYPE
    SYNTAX      Counter64
    MAX-ACCESS  read-only
    STATUS      deprecated
    DESCRIPTION
    "GTP V0 T3 Response Timer Expiries."
    ::= { jnxMbgPgwGtpV0Stats 5 }


jnxMbgPgwV0MsgRedirectRx   OBJECT-TYPE
    SYNTAX      Counter64
    MAX-ACCESS  read-only
    STATUS      deprecated
    DESCRIPTION
    "GTP V0 Rx Message Redirected."
    ::= { jnxMbgPgwGtpV0Stats 6 }


jnxMbgPgwV0MsgRedirectTx   OBJECT-TYPE
    SYNTAX      Counter64
    MAX-ACCESS  read-only
    STATUS      deprecated
    DESCRIPTION
    "GTP V0 Tx Message Redirected."
    ::= { jnxMbgPgwGtpV0Stats 7 }


jnxMbgPgwV0SuppExtHdrNot   OBJECT-TYPE
    SYNTAX      Counter64
    MAX-ACCESS  read-only
    STATUS      deprecated
    DESCRIPTION
    "GTP V0 Extension Header Not Supported."
    ::= { jnxMbgPgwGtpV0Stats 8 }


jnxMbgPgwV0EchoReqRx   OBJECT-TYPE
    SYNTAX      Counter64
    MAX-ACCESS  read-only
    STATUS      deprecated
    DESCRIPTION
    "GTP V0 Echo Requests Received."
    ::= { jnxMbgPgwGtpV0Stats 9 }


jnxMbgPgwV0EchoRespRx   OBJECT-TYPE
    SYNTAX      Counter64
    MAX-ACCESS  read-only
    STATUS      deprecated
    DESCRIPTION
    "GTP V0 Echo Responses Received."
    ::= { jnxMbgPgwGtpV0Stats 10 }


jnxMbgPgwV0CrtPdpCxtReqRx   OBJECT-TYPE
    SYNTAX      Counter64
    MAX-ACCESS  read-only
    STATUS      deprecated
    DESCRIPTION
    "GTP V0 Create PDP Context Requests Received."
    ::= { jnxMbgPgwGtpV0Stats 11 }


jnxMbgPgwV0CrtPdpCxtRspRx   OBJECT-TYPE
    SYNTAX      Counter64
    MAX-ACCESS  read-only
    STATUS      deprecated
    DESCRIPTION
    "GTP V0 Create PDP Context Responses Received."
    ::= { jnxMbgPgwGtpV0Stats 12 }


jnxMbgPgwV0UpdPdpCxtReqRx   OBJECT-TYPE
    SYNTAX      Counter64
    MAX-ACCESS  read-only
    STATUS      deprecated
    DESCRIPTION
    "GTP V0 Update PDP Context Requests Received."
    ::= { jnxMbgPgwGtpV0Stats 13 }


jnxMbgPgwV0UpdPdpCxtRspRx   OBJECT-TYPE
    SYNTAX      Counter64
    MAX-ACCESS  read-only
    STATUS      deprecated
    DESCRIPTION
    "GTP V0 Update PDP Context Responses Received."
    ::= { jnxMbgPgwGtpV0Stats 14 }


jnxMbgPgwV0DelPdpCxtReqRx   OBJECT-TYPE
    SYNTAX      Counter64
    MAX-ACCESS  read-only
    STATUS      deprecated
    DESCRIPTION
    "GTP V0 Delete PDP Context Requests Received."
    ::= { jnxMbgPgwGtpV0Stats 15 }


jnxMbgPgwV0DelPdpCxtRspRx   OBJECT-TYPE
    SYNTAX      Counter64
    MAX-ACCESS  read-only
    STATUS      deprecated
    DESCRIPTION
    "GTP V0 Delete PDP Context Responses Received."
    ::= { jnxMbgPgwGtpV0Stats 16 }


jnxMbgPgwV0CrtAAPdpCxtReqRx   OBJECT-TYPE
    SYNTAX      Counter64
    MAX-ACCESS  read-only
    STATUS      deprecated
    DESCRIPTION
    "GTP V0 Create AA PDP Context Requests Received."
    ::= { jnxMbgPgwGtpV0Stats 17 }


jnxMbgPgwV0CrtAAPdpCxtRspRx   OBJECT-TYPE
    SYNTAX      Counter64
    MAX-ACCESS  read-only
    STATUS      deprecated
    DESCRIPTION
    "GTP V0 Create AA PDP Context Responses Received."
    ::= { jnxMbgPgwGtpV0Stats 18 }


jnxMbgPgwV0DelAAPdpCxtReqRx   OBJECT-TYPE
    SYNTAX      Counter64
    MAX-ACCESS  read-only
    STATUS      deprecated
    DESCRIPTION
    "GTP V0 Delete AA PDP Context Requests Received."
    ::= { jnxMbgPgwGtpV0Stats 19 }


jnxMbgPgwV0DelAAPdpCxtRspRx   OBJECT-TYPE
    SYNTAX      Counter64
    MAX-ACCESS  read-only
    STATUS      deprecated
    DESCRIPTION
    "GTP V0 Delete AA PDP Context Responses Received."
    ::= { jnxMbgPgwGtpV0Stats 20 }


jnxMbgPgwV0ErrorIndRx   OBJECT-TYPE
    SYNTAX      Counter64
    MAX-ACCESS  read-only
    STATUS      deprecated
    DESCRIPTION
    "GTP V0 Error Indication Received."
    ::= { jnxMbgPgwGtpV0Stats 21 }


jnxMbgPgwV0NotifReqRx   OBJECT-TYPE
    SYNTAX      Counter64
    MAX-ACCESS  read-only
    STATUS      deprecated
    DESCRIPTION
    "GTP V0 Notify Requests Received."
    ::= { jnxMbgPgwGtpV0Stats 22 }


jnxMbgPgwV0NotifRspRx   OBJECT-TYPE
    SYNTAX      Counter64
    MAX-ACCESS  read-only
    STATUS      deprecated
    DESCRIPTION
    "GTP V0 Notify Responses Received."
    ::= { jnxMbgPgwGtpV0Stats 23 }


jnxMbgPgwV0NotifRejReqRx   OBJECT-TYPE
    SYNTAX      Counter64
    MAX-ACCESS  read-only
    STATUS      deprecated
    DESCRIPTION
    "GTP V0 Notify Reject Requests Received."
    ::= { jnxMbgPgwGtpV0Stats 24 }


jnxMbgPgwV0NotifRejRspRx   OBJECT-TYPE
    SYNTAX      Counter64
    MAX-ACCESS  read-only
    STATUS      deprecated
    DESCRIPTION
    "GTP V0 Notify Reject Responses Received."
    ::= { jnxMbgPgwGtpV0Stats 25 }


jnxMbgPgwV0RtInfReqRx   OBJECT-TYPE
    SYNTAX      Counter64
    MAX-ACCESS  read-only
    STATUS      deprecated
    DESCRIPTION
    "GTP V0 Routing Information Requests Received."
    ::= { jnxMbgPgwGtpV0Stats 26 }


jnxMbgPgwV0RtInfRspRx   OBJECT-TYPE
    SYNTAX      Counter64
    MAX-ACCESS  read-only
    STATUS      deprecated
    DESCRIPTION
    "GTP V0 Routing Information Responses Received."
    ::= { jnxMbgPgwGtpV0Stats 27 }


jnxMbgPgwV0FailRptReqRx   OBJECT-TYPE
    SYNTAX      Counter64
    MAX-ACCESS  read-only
    STATUS      deprecated
    DESCRIPTION
    "GTP V0 Fail Repeat Requests Received."
    ::= { jnxMbgPgwGtpV0Stats 28 }


jnxMbgPgwV0FailRptRspRx   OBJECT-TYPE
    SYNTAX      Counter64
    MAX-ACCESS  read-only
    STATUS      deprecated
    DESCRIPTION
    "GTP V0 Fail Repeat Responses Received."
    ::= { jnxMbgPgwGtpV0Stats 29 }


jnxMbgPgwV0NotMSPresReqRx   OBJECT-TYPE
    SYNTAX      Counter64
    MAX-ACCESS  read-only
    STATUS      deprecated
    DESCRIPTION
    "GTP V0 MS Not Present Request Received."
    ::= { jnxMbgPgwGtpV0Stats 30 }


jnxMbgPgwV0NotMSPresRspRx   OBJECT-TYPE
    SYNTAX      Counter64
    MAX-ACCESS  read-only
    STATUS      deprecated
    DESCRIPTION
    "GTP V0 MS Not Present Responses Received."
    ::= { jnxMbgPgwGtpV0Stats 31 }


jnxMbgPgwGTPV0ICsReqAccepted   OBJECT-TYPE
    SYNTAX      Counter64
    MAX-ACCESS  read-only
    STATUS      deprecated
    DESCRIPTION
    "GTP Cause Request Accepted."
    ::= { jnxMbgPgwGtpV0Stats 32 }


jnxMbgPgwGTPV0ICsNonExist   OBJECT-TYPE
    SYNTAX      Counter64
    MAX-ACCESS  read-only
    STATUS      deprecated
    DESCRIPTION
    "GTP Cause Non Existant."
    ::= { jnxMbgPgwGtpV0Stats 33 }


jnxMbgPgwGTPV0ICsInvMsgFmt   OBJECT-TYPE
    SYNTAX      Counter64
    MAX-ACCESS  read-only
    STATUS      deprecated
    DESCRIPTION
    "GTP Cause Invalid Mesage Format."
    ::= { jnxMbgPgwGtpV0Stats 34 }


jnxMbgPgwGTPV0ICsIMSINotKnown   OBJECT-TYPE
    SYNTAX      Counter64
    MAX-ACCESS  read-only
    STATUS      deprecated
    DESCRIPTION
    "GTP Cause IMSI Not Known."
    ::= { jnxMbgPgwGtpV0Stats 35 }


jnxMbgPgwGTPV0ICsMSGRPSDetach   OBJECT-TYPE
    SYNTAX      Counter64
    MAX-ACCESS  read-only
    STATUS      deprecated
    DESCRIPTION
    "GTP Cause MS GPRS Detached."
    ::= { jnxMbgPgwGtpV0Stats 36 }


jnxMbgPgwGTPV0ICsMSNotGRPSResp   OBJECT-TYPE
    SYNTAX      Counter64
    MAX-ACCESS  read-only
    STATUS      deprecated
    DESCRIPTION
    "GTP Cause MS No GPRS Response."
    ::= { jnxMbgPgwGtpV0Stats 37 }


jnxMbgPgwGTPV0ICsMSRefuses   OBJECT-TYPE
    SYNTAX      Counter64
    MAX-ACCESS  read-only
    STATUS      deprecated
    DESCRIPTION
    "GTP Cause MS Refues."
    ::= { jnxMbgPgwGtpV0Stats 38 }


jnxMbgPgwGTPV0ICsVerNotSupp   OBJECT-TYPE
    SYNTAX      Counter64
    MAX-ACCESS  read-only
    STATUS      deprecated
    DESCRIPTION
    "GTP Cause Version Not Supported."
    ::= { jnxMbgPgwGtpV0Stats 39 }


jnxMbgPgwGTPV0ICsNoRes   OBJECT-TYPE
    SYNTAX      Counter64
    MAX-ACCESS  read-only
    STATUS      deprecated
    DESCRIPTION
    "GTP Cause No Response."
    ::= { jnxMbgPgwGtpV0Stats 40 }


jnxMbgPgwGTPV0ICsServNotSupp   OBJECT-TYPE
    SYNTAX      Counter64
    MAX-ACCESS  read-only
    STATUS      deprecated
    DESCRIPTION
    "GTP Cause Service Not Supported."
    ::= { jnxMbgPgwGtpV0Stats 41 }


jnxMbgPgwGTPV0ICsManIEIncrt   OBJECT-TYPE
    SYNTAX      Counter64
    MAX-ACCESS  read-only
    STATUS      deprecated
    DESCRIPTION
    "GTP Cause Mandatory IE incorrect."
    ::= { jnxMbgPgwGtpV0Stats 42 }


jnxMbgPgwGTPV0ICsManIEMiss   OBJECT-TYPE
    SYNTAX      Counter64
    MAX-ACCESS  read-only
    STATUS      deprecated
    DESCRIPTION
    "GTP Cause Mandatory IE Missing."
    ::= { jnxMbgPgwGtpV0Stats 43 }


jnxMbgPgwGTPV0ICsOptIEIncrt   OBJECT-TYPE
    SYNTAX      Counter64
    MAX-ACCESS  read-only
    STATUS      deprecated
    DESCRIPTION
    "GTP Cause Optional IE incorrect."
    ::= { jnxMbgPgwGtpV0Stats 44 }


jnxMbgPgwGTPV0ICsSysFail   OBJECT-TYPE
    SYNTAX      Counter64
    MAX-ACCESS  read-only
    STATUS      deprecated
    DESCRIPTION
    "GTP Cause System Failure."
    ::= { jnxMbgPgwGtpV0Stats 45 }


jnxMbgPgwGTPV0ICsRoamRestrict   OBJECT-TYPE
    SYNTAX      Counter64
    MAX-ACCESS  read-only
    STATUS      deprecated
    DESCRIPTION
    "GTP Cause Roaming Restricted."
    ::= { jnxMbgPgwGtpV0Stats 46 }


jnxMbgPgwGTPV0ICsPTMSISigMismatch   OBJECT-TYPE
    SYNTAX      Counter64
    MAX-ACCESS  read-only
    STATUS      deprecated
    DESCRIPTION
    "GTP Cause PTMSI Signature Mismatch."
    ::= { jnxMbgPgwGtpV0Stats 47 }


jnxMbgPgwGTPV0ICsGPRSConnSupp   OBJECT-TYPE
    SYNTAX      Counter64
    MAX-ACCESS  read-only
    STATUS      deprecated
    DESCRIPTION
    "GTP Cause GPRS Connection Supported."
    ::= { jnxMbgPgwGtpV0Stats 48 }


jnxMbgPgwGTPV0ICsAuthFail   OBJECT-TYPE
    SYNTAX      Counter64
    MAX-ACCESS  read-only
    STATUS      deprecated
    DESCRIPTION
    "GTP Cause Auth Failure."
    ::= { jnxMbgPgwGtpV0Stats 49 }


jnxMbgPgwGTPV0ICsUserAuthFail   OBJECT-TYPE
    SYNTAX      Counter64
    MAX-ACCESS  read-only
    STATUS      deprecated
    DESCRIPTION
    "GTP Cause User Auth Failure."
    ::= { jnxMbgPgwGtpV0Stats 50 }

jnxMbgPgwV0NumMsgTx   OBJECT-TYPE
    SYNTAX      Counter64
    MAX-ACCESS  read-only
    STATUS      deprecated
    DESCRIPTION
    "Number Of Messages Tx."
    ::= { jnxMbgPgwGtpV0Stats 51 }


jnxMbgPgwV0NumBytesTx   OBJECT-TYPE
    SYNTAX      Counter64
    MAX-ACCESS  read-only
    STATUS      deprecated
    DESCRIPTION
    "Number of Bytes Tx."
    ::= { jnxMbgPgwGtpV0Stats 52 }


jnxMbgPgwV0EchoReqTx   OBJECT-TYPE
    SYNTAX      Counter64
    MAX-ACCESS  read-only
    STATUS      deprecated
    DESCRIPTION
    "GTP V0 Echo Requests Sent."
    ::= { jnxMbgPgwGtpV0Stats 53 }


jnxMbgPgwV0EchoRespTx   OBJECT-TYPE
    SYNTAX      Counter64
    MAX-ACCESS  read-only
    STATUS      deprecated
    DESCRIPTION
    "GTP V0 Echo Responses Sent."
    ::= { jnxMbgPgwGtpV0Stats 54 }


jnxMbgPgwV0CrtPdpCxtReqTx   OBJECT-TYPE
    SYNTAX      Counter64
    MAX-ACCESS  read-only
    STATUS      deprecated
    DESCRIPTION
    "GTP V0 Create PDP Context Requests Sent."
    ::= { jnxMbgPgwGtpV0Stats 55 }


jnxMbgPgwV0CrtPdpCxtRspTx   OBJECT-TYPE
    SYNTAX      Counter64
    MAX-ACCESS  read-only
    STATUS      deprecated
    DESCRIPTION
    "GTP V0 Create PDP Context Responses Sent."
    ::= { jnxMbgPgwGtpV0Stats 56 }


jnxMbgPgwV0UpdPdpCxtReqTx   OBJECT-TYPE
    SYNTAX      Counter64
    MAX-ACCESS  read-only
    STATUS      deprecated
    DESCRIPTION
    "GTP V0 Update PDP Context Requests Sent."
    ::= { jnxMbgPgwGtpV0Stats 57 }


jnxMbgPgwV0UpdPdpCxtRspTx   OBJECT-TYPE
    SYNTAX      Counter64
    MAX-ACCESS  read-only
    STATUS      deprecated
    DESCRIPTION
    "GTP V0 Update PDP Context Responses Sent."
    ::= { jnxMbgPgwGtpV0Stats 58 }


jnxMbgPgwV0DelPdpCxtReqTx   OBJECT-TYPE
    SYNTAX      Counter64
    MAX-ACCESS  read-only
    STATUS      deprecated
    DESCRIPTION
    "GTP V0 Delete PDP Context Requests Sent."
    ::= { jnxMbgPgwGtpV0Stats 59 }


jnxMbgPgwV0DelPdpCxtRspTx   OBJECT-TYPE
    SYNTAX      Counter64
    MAX-ACCESS  read-only
    STATUS      deprecated
    DESCRIPTION
    "GTP V0 Delete PDP Context Responses Sent."
    ::= { jnxMbgPgwGtpV0Stats 60 }


jnxMbgPgwV0CrtAAPdpCxtReqTx   OBJECT-TYPE
    SYNTAX      Counter64
    MAX-ACCESS  read-only
    STATUS      deprecated
    DESCRIPTION
    "GTP V0 Create AA PDP Context Requests Sent."
    ::= { jnxMbgPgwGtpV0Stats 61 }


jnxMbgPgwV0CrtAAPdpCxtRspTx   OBJECT-TYPE
    SYNTAX      Counter64
    MAX-ACCESS  read-only
    STATUS      deprecated
    DESCRIPTION
    "GTP V0 Create AA PDP Context Responses Sent."
    ::= { jnxMbgPgwGtpV0Stats 62 }


jnxMbgPgwV0DelAAPdpCxtReqTx   OBJECT-TYPE
    SYNTAX      Counter64
    MAX-ACCESS  read-only
    STATUS      deprecated
    DESCRIPTION
    "GTP V0 Delete AA PDP Context Requests Sent."
    ::= { jnxMbgPgwGtpV0Stats 63 }


jnxMbgPgwV0DelAAPdpCxtRspTx   OBJECT-TYPE
    SYNTAX      Counter64
    MAX-ACCESS  read-only
    STATUS      deprecated
    DESCRIPTION
    "GTP V0 Delete AA PDP Context Responses Sent."
    ::= { jnxMbgPgwGtpV0Stats 64 }


jnxMbgPgwV0ErrorIndTx   OBJECT-TYPE
    SYNTAX      Counter64
    MAX-ACCESS  read-only
    STATUS      deprecated
    DESCRIPTION
    "GTP V0 Error Indication Sent."
    ::= { jnxMbgPgwGtpV0Stats 65 }


jnxMbgPgwV0NotifReqTx   OBJECT-TYPE
    SYNTAX      Counter64
    MAX-ACCESS  read-only
    STATUS      deprecated
    DESCRIPTION
    "GTP V0 Notify Requests Sent."
    ::= { jnxMbgPgwGtpV0Stats 66 }


jnxMbgPgwV0NotifRspTx   OBJECT-TYPE
    SYNTAX      Counter64
    MAX-ACCESS  read-only
    STATUS      deprecated
    DESCRIPTION
    "GTP V0 Notify Responses Sent."
    ::= { jnxMbgPgwGtpV0Stats 67 }


jnxMbgPgwV0NotifRejReqTx   OBJECT-TYPE
    SYNTAX      Counter64
    MAX-ACCESS  read-only
    STATUS      deprecated
    DESCRIPTION
    "GTP V0 Notify Reject Requests Sent."
    ::= { jnxMbgPgwGtpV0Stats 68 }


jnxMbgPgwV0NotifRejRspTx   OBJECT-TYPE
    SYNTAX      Counter64
    MAX-ACCESS  read-only
    STATUS      deprecated
    DESCRIPTION
    "GTP V0 Notify Reject Responses Sent."
    ::= { jnxMbgPgwGtpV0Stats 69 }


jnxMbgPgwV0RtInfReqTx   OBJECT-TYPE
    SYNTAX      Counter64
    MAX-ACCESS  read-only
    STATUS      deprecated
    DESCRIPTION
    "GTP V0 Routing Information Requests Sent."
    ::= { jnxMbgPgwGtpV0Stats 70 }


jnxMbgPgwV0RtInfRspTx   OBJECT-TYPE
    SYNTAX      Counter64
    MAX-ACCESS  read-only
    STATUS      deprecated
    DESCRIPTION
    "GTP V0 Routing Information Responses Sent."
    ::= { jnxMbgPgwGtpV0Stats 71 }


jnxMbgPgwV0FailRptReqTx   OBJECT-TYPE
    SYNTAX      Counter64
    MAX-ACCESS  read-only
    STATUS      deprecated
    DESCRIPTION
    "GTP V0 Fail Repeat Requests Sent."
    ::= { jnxMbgPgwGtpV0Stats 72 }


jnxMbgPgwV0FailRptRspTx   OBJECT-TYPE
    SYNTAX      Counter64
    MAX-ACCESS  read-only
    STATUS      deprecated
    DESCRIPTION
    "GTP V0 Fail Repeat Responses Sent."
    ::= { jnxMbgPgwGtpV0Stats 73 }


jnxMbgPgwV0NotMSPresReqTx   OBJECT-TYPE
    SYNTAX      Counter64
    MAX-ACCESS  read-only
    STATUS      deprecated
    DESCRIPTION
    "GTP V0 MS Not Present Request Sent."
    ::= { jnxMbgPgwGtpV0Stats 74 }


jnxMbgPgwV0NotMSPresRspTx   OBJECT-TYPE
    SYNTAX      Counter64
    MAX-ACCESS  read-only
    STATUS      deprecated
    DESCRIPTION
    "GTP V0 MS Not Present Responses Sent."
    ::= { jnxMbgPgwGtpV0Stats 75 }

--
-- GTP V1 Stats elements
--

jnxMbgPgwV1NumMsgRx   OBJECT-TYPE
    SYNTAX      Counter64
    MAX-ACCESS  read-only
    STATUS      deprecated
    DESCRIPTION
    "Number Of GTP V1 Messages Rx."
    ::= { jnxMbgPgwGtpV1Stats 1 }


jnxMbgPgwV1NumBytesRx   OBJECT-TYPE
    SYNTAX      Counter64
    MAX-ACCESS  read-only
    STATUS      deprecated
    DESCRIPTION
    "Number of GTP V1 Bytes Rx."
    ::= { jnxMbgPgwGtpV1Stats 2 }


jnxMbgPgwV1UnSupportedMsg   OBJECT-TYPE
    SYNTAX      Counter64
    MAX-ACCESS  read-only
    STATUS      deprecated
    DESCRIPTION
    "Unsupported Messages."
    ::= { jnxMbgPgwGtpV1Stats 3 }


jnxMbgPgwProtErr   OBJECT-TYPE
    SYNTAX      Counter64
    MAX-ACCESS  read-only
    STATUS      deprecated
    DESCRIPTION
    "GTP V1 Protocol Errors."
    ::= { jnxMbgPgwGtpV1Stats 4 }


jnxMbgPgwV1T3RespTmrExp   OBJECT-TYPE
    SYNTAX      Counter64
    MAX-ACCESS  read-only
    STATUS      deprecated
    DESCRIPTION
    "GTP V1 T3 Response Timer Expiries."
    ::= { jnxMbgPgwGtpV1Stats 5 }


jnxMbgPgwMsgRedirectRx   OBJECT-TYPE
    SYNTAX      Counter64
    MAX-ACCESS  read-only
    STATUS      deprecated
    DESCRIPTION
    "GTP V1 Rx Message Redirected."
    ::= { jnxMbgPgwGtpV1Stats 6 }


jnxMbgPgwMsgRedirectTx   OBJECT-TYPE
    SYNTAX      Counter64
    MAX-ACCESS  read-only
    STATUS      deprecated
    DESCRIPTION
    "GTP V1 Tx Message Redirected."
    ::= { jnxMbgPgwGtpV1Stats 7 }


jnxMbgPgwSuppExtHdrNot   OBJECT-TYPE
    SYNTAX      Counter64
    MAX-ACCESS  read-only
    STATUS      deprecated
    DESCRIPTION
    "GTP V1 Extension Header Not Supported."
    ::= { jnxMbgPgwGtpV1Stats 8 }


jnxMbgPgwV1EchoReqRx   OBJECT-TYPE
    SYNTAX      Counter64
    MAX-ACCESS  read-only
    STATUS      deprecated
    DESCRIPTION
    "GTP V1 Echo Requests Received."
    ::= { jnxMbgPgwGtpV1Stats 9 }


jnxMbgPgwV1EchoRespRx   OBJECT-TYPE
    SYNTAX      Counter64
    MAX-ACCESS  read-only
    STATUS      deprecated
    DESCRIPTION
    "GTP V1 Echo Responses Received."
    ::= { jnxMbgPgwGtpV1Stats 10 }


jnxMbgPgwCrtPdpCxtReqRx   OBJECT-TYPE
    SYNTAX      Counter64
    MAX-ACCESS  read-only
    STATUS      deprecated
    DESCRIPTION
    "GTP V1 Create PDP Context Requests Received."
    ::= { jnxMbgPgwGtpV1Stats 11 }


jnxMbgPgwCrtPdpCxtRspRx   OBJECT-TYPE
    SYNTAX      Counter64
    MAX-ACCESS  read-only
    STATUS      deprecated
    DESCRIPTION
    "GTP V1 Create PDP Context Responses Received."
    ::= { jnxMbgPgwGtpV1Stats 12 }


jnxMbgPgwUpdPdpCxtReqRx   OBJECT-TYPE
    SYNTAX      Counter64
    MAX-ACCESS  read-only
    STATUS      deprecated
    DESCRIPTION
    "GTP V1 Update PDP Context Requests Received."
    ::= { jnxMbgPgwGtpV1Stats 13 }


jnxMbgPgwUpdPdpCxtRspRx   OBJECT-TYPE
    SYNTAX      Counter64
    MAX-ACCESS  read-only
    STATUS      deprecated
    DESCRIPTION
    "GTP V1 Update PDP Context Responses Received."
    ::= { jnxMbgPgwGtpV1Stats 14 }


jnxMbgPgwDelPdpCxtReqRx   OBJECT-TYPE
    SYNTAX      Counter64
    MAX-ACCESS  read-only
    STATUS      deprecated
    DESCRIPTION
    "GTP V1 Delete PDP Context Requests Received."
    ::= { jnxMbgPgwGtpV1Stats 15 }


jnxMbgPgwDelPdpCxtRspRx   OBJECT-TYPE
    SYNTAX      Counter64
    MAX-ACCESS  read-only
    STATUS      deprecated
    DESCRIPTION
    "GTP V1 Delete PDP Context Responses Received."
    ::= { jnxMbgPgwGtpV1Stats 16 }


jnxMbgPgwCrtAAPdpCxtReqRx   OBJECT-TYPE
    SYNTAX      Counter64
    MAX-ACCESS  read-only
    STATUS      deprecated
    DESCRIPTION
    "GTP V1 Create AA PDP Context Requests Received."
    ::= { jnxMbgPgwGtpV1Stats 17 }


jnxMbgPgwCrtAAPdpCxtRspRx   OBJECT-TYPE
    SYNTAX      Counter64
    MAX-ACCESS  read-only
    STATUS      deprecated
    DESCRIPTION
    "GTP V1 Create AA PDP Context Responses Received."
    ::= { jnxMbgPgwGtpV1Stats 18 }


jnxMbgPgwDelAAPdpCxtReqRx   OBJECT-TYPE
    SYNTAX      Counter64
    MAX-ACCESS  read-only
    STATUS      deprecated
    DESCRIPTION
    "GTP V1 Delete AA PDP Context Requests Received."
    ::= { jnxMbgPgwGtpV1Stats 19 }


jnxMbgPgwDelAAPdpCxtRspRx   OBJECT-TYPE
    SYNTAX      Counter64
    MAX-ACCESS  read-only
    STATUS      deprecated
    DESCRIPTION
    "GTP V1 Delete AA PDP Context Responses Received."
    ::= { jnxMbgPgwGtpV1Stats 20 }


jnxMbgPgwErrorIndRx   OBJECT-TYPE
    SYNTAX      Counter64
    MAX-ACCESS  read-only
    STATUS      deprecated
    DESCRIPTION
    "GTP V1 Error Indication Received."
    ::= { jnxMbgPgwGtpV1Stats 21 }


jnxMbgPgwNotifReqRx   OBJECT-TYPE
    SYNTAX      Counter64
    MAX-ACCESS  read-only
    STATUS      deprecated
    DESCRIPTION
    "GTP V1 Notify Requests Received."
    ::= { jnxMbgPgwGtpV1Stats 22 }


jnxMbgPgwNotifRspRx   OBJECT-TYPE
    SYNTAX      Counter64
    MAX-ACCESS  read-only
    STATUS      deprecated
    DESCRIPTION
    "GTP V1 Notify Responses Received."
    ::= { jnxMbgPgwGtpV1Stats 23 }


jnxMbgPgwNotifRejReqRx   OBJECT-TYPE
    SYNTAX      Counter64
    MAX-ACCESS  read-only
    STATUS      deprecated
    DESCRIPTION
    "GTP V1 Notify Reject Requests Received."
    ::= { jnxMbgPgwGtpV1Stats 24 }


jnxMbgPgwNotifRejRspRx   OBJECT-TYPE
    SYNTAX      Counter64
    MAX-ACCESS  read-only
    STATUS      deprecated
    DESCRIPTION
    "GTP V1 Notify Reject Responses Received."
    ::= { jnxMbgPgwGtpV1Stats 25 }


jnxMbgPgwRtInfReqRx   OBJECT-TYPE
    SYNTAX      Counter64
    MAX-ACCESS  read-only
    STATUS      deprecated
    DESCRIPTION
    "GTP V1 Routing Information Requests Received."
    ::= { jnxMbgPgwGtpV1Stats 26 }


jnxMbgPgwRtInfRspRx   OBJECT-TYPE
    SYNTAX      Counter64
    MAX-ACCESS  read-only
    STATUS      deprecated
    DESCRIPTION
    "GTP V1 Routing Information Responses Received."
    ::= { jnxMbgPgwGtpV1Stats 27 }


jnxMbgPgwFailRptReqRx   OBJECT-TYPE
    SYNTAX      Counter64
    MAX-ACCESS  read-only
    STATUS      deprecated
    DESCRIPTION
    "GTP V1 Fail Repeat Requests Received."
    ::= { jnxMbgPgwGtpV1Stats 28 }


jnxMbgPgwFailRptRspRx   OBJECT-TYPE
    SYNTAX      Counter64
    MAX-ACCESS  read-only
    STATUS      deprecated
    DESCRIPTION
    "GTP V1 Fail Repeat Responses Received."
    ::= { jnxMbgPgwGtpV1Stats 29 }


jnxMbgPgwNotMSPresReqRx   OBJECT-TYPE
    SYNTAX      Counter64
    MAX-ACCESS  read-only
    STATUS      deprecated
    DESCRIPTION
    "GTP V1 MS Not Present Request Received."
    ::= { jnxMbgPgwGtpV1Stats 30 }


jnxMbgPgwNotMSPresRspRx   OBJECT-TYPE
    SYNTAX      Counter64
    MAX-ACCESS  read-only
    STATUS      deprecated
    DESCRIPTION
    "GTP V1 MS Not Present Responses Received."
    ::= { jnxMbgPgwGtpV1Stats 31 }


jnxMbgPgwGTPICsReqAccepted   OBJECT-TYPE
    SYNTAX      Counter64
    MAX-ACCESS  read-only
    STATUS      deprecated
    DESCRIPTION
    "GTP Cause Request Accepted."
    ::= { jnxMbgPgwGtpV1Stats 32 }


jnxMbgPgwGTPICsNonExist   OBJECT-TYPE
    SYNTAX      Counter64
    MAX-ACCESS  read-only
    STATUS      deprecated
    DESCRIPTION
    "GTP Cause Non Existant."
    ::= { jnxMbgPgwGtpV1Stats 33 }


jnxMbgPgwGTPICsInvMsgFmt   OBJECT-TYPE
    SYNTAX      Counter64
    MAX-ACCESS  read-only
    STATUS      deprecated
    DESCRIPTION
    "GTP Cause Invalid Mesage Format."
    ::= { jnxMbgPgwGtpV1Stats 34 }


jnxMbgPgwGTPICsIMSINotKnown   OBJECT-TYPE
    SYNTAX      Counter64
    MAX-ACCESS  read-only
    STATUS      deprecated
    DESCRIPTION
    "GTP Cause IMSI Not Known."
    ::= { jnxMbgPgwGtpV1Stats 35 }


jnxMbgPgwGTPICsMSGRPSDetach   OBJECT-TYPE
    SYNTAX      Counter64
    MAX-ACCESS  read-only
    STATUS      deprecated
    DESCRIPTION
    "GTP Cause MS GPRS Detached."
    ::= { jnxMbgPgwGtpV1Stats 36 }


jnxMbgPgwGTPICsMSNotGRPSResp   OBJECT-TYPE
    SYNTAX      Counter64
    MAX-ACCESS  read-only
    STATUS      deprecated
    DESCRIPTION
    "GTP Cause MS No GPRS Response."
    ::= { jnxMbgPgwGtpV1Stats 37 }


jnxMbgPgwGTPICsMSRefuses   OBJECT-TYPE
    SYNTAX      Counter64
    MAX-ACCESS  read-only
    STATUS      deprecated
    DESCRIPTION
    "GTP Cause MS Refues."
    ::= { jnxMbgPgwGtpV1Stats 38 }


jnxMbgPgwGTPICsVerNotSupp   OBJECT-TYPE
    SYNTAX      Counter64
    MAX-ACCESS  read-only
    STATUS      deprecated
    DESCRIPTION
    "GTP Cause Version Not Supported."
    ::= { jnxMbgPgwGtpV1Stats 39 }


jnxMbgPgwGTPICsNoRes   OBJECT-TYPE
    SYNTAX      Counter64
    MAX-ACCESS  read-only
    STATUS      deprecated
    DESCRIPTION
    "GTP Cause No Response."
    ::= { jnxMbgPgwGtpV1Stats 40 }


jnxMbgPgwGTPICsServNotSupp   OBJECT-TYPE
    SYNTAX      Counter64
    MAX-ACCESS  read-only
    STATUS      deprecated
    DESCRIPTION
    "GTP Cause Service Not Supported."
    ::= { jnxMbgPgwGtpV1Stats 41 }


jnxMbgPgwGTPICsManIEIncrt   OBJECT-TYPE
    SYNTAX      Counter64
    MAX-ACCESS  read-only
    STATUS      deprecated
    DESCRIPTION
    "GTP Cause Mandatory IE incorrect."
    ::= { jnxMbgPgwGtpV1Stats 42 }


jnxMbgPgwGTPICsManIEMiss   OBJECT-TYPE
    SYNTAX      Counter64
    MAX-ACCESS  read-only
    STATUS      deprecated
    DESCRIPTION
    "GTP Cause Mandatory IE Missing."
    ::= { jnxMbgPgwGtpV1Stats 43 }


jnxMbgPgwGTPICsOptIEIncrt   OBJECT-TYPE
    SYNTAX      Counter64
    MAX-ACCESS  read-only
    STATUS      deprecated
    DESCRIPTION
    "GTP Cause Optional IE incorrect."
    ::= { jnxMbgPgwGtpV1Stats 44 }


jnxMbgPgwGTPICsSysFail   OBJECT-TYPE
    SYNTAX      Counter64
    MAX-ACCESS  read-only
    STATUS      deprecated
    DESCRIPTION
    "GTP Cause System Failure."
    ::= { jnxMbgPgwGtpV1Stats 45 }


jnxMbgPgwGTPICsRoamRestrict   OBJECT-TYPE
    SYNTAX      Counter64
    MAX-ACCESS  read-only
    STATUS      deprecated
    DESCRIPTION
    "GTP Cause Roaming Restricted."
    ::= { jnxMbgPgwGtpV1Stats 46 }


jnxMbgPgwGTPICsPTMSISigMismatch   OBJECT-TYPE
    SYNTAX      Counter64
    MAX-ACCESS  read-only
    STATUS      deprecated
    DESCRIPTION
    "GTP Cause PTMSI Signature Mismatch."
    ::= { jnxMbgPgwGtpV1Stats 47 }


jnxMbgPgwGTPICsGPRSConnSupp   OBJECT-TYPE
    SYNTAX      Counter64
    MAX-ACCESS  read-only
    STATUS      deprecated
    DESCRIPTION
    "GTP Cause GPRS Connection Supported."
    ::= { jnxMbgPgwGtpV1Stats 48 }


jnxMbgPgwGTPICsAuthFail   OBJECT-TYPE
    SYNTAX      Counter64
    MAX-ACCESS  read-only
    STATUS      deprecated
    DESCRIPTION
    "GTP Cause Auth Failure."
    ::= { jnxMbgPgwGtpV1Stats 49 }


jnxMbgPgwGTPICsUserAuthFail   OBJECT-TYPE
    SYNTAX      Counter64
    MAX-ACCESS  read-only
    STATUS      deprecated
    DESCRIPTION
    "GTP Cause User Auth Failure."
    ::= { jnxMbgPgwGtpV1Stats 50 }


jnxMbgPgwGTPV1ICsCtxNotFnd   OBJECT-TYPE
    SYNTAX      Counter64
    MAX-ACCESS  read-only
    STATUS      deprecated
    DESCRIPTION
    "GTP Cause Context Not Found."
    ::= { jnxMbgPgwGtpV1Stats 51 }


jnxMbgPgwGTPV1ICsAllDynPDPAddr   OBJECT-TYPE
    SYNTAX      Counter64
    MAX-ACCESS  read-only
    STATUS      deprecated
    DESCRIPTION
    "GTP Cause Allow Dynamic PDP Address."
    ::= { jnxMbgPgwGtpV1Stats 52 }


jnxMbgPgwGTPV1ICsNoMem   OBJECT-TYPE
    SYNTAX      Counter64
    MAX-ACCESS  read-only
    STATUS      deprecated
    DESCRIPTION
    "GTP Cause No Memory."
    ::= { jnxMbgPgwGtpV1Stats 53 }


jnxMbgPgwGTPV1ICsRelocFail   OBJECT-TYPE
    SYNTAX      Counter64
    MAX-ACCESS  read-only
    STATUS      deprecated
    DESCRIPTION
    "GTP Cause Relocation Failed."
    ::= { jnxMbgPgwGtpV1Stats 54 }


jnxMbgPgwGTPV1ICsUnkManExthdr   OBJECT-TYPE
    SYNTAX      Counter64
    MAX-ACCESS  read-only
    STATUS      deprecated
    DESCRIPTION
    "GTP Cause Unknown Mandatory Extension Header."
    ::= { jnxMbgPgwGtpV1Stats 55 }


jnxMbgPgwGTPV1ICsSMANTTFTErr1   OBJECT-TYPE
    SYNTAX      Counter64
    MAX-ACCESS  read-only
    STATUS      deprecated
    DESCRIPTION
    "GTP Cause Mandatory TFT Error."
    ::= { jnxMbgPgwGtpV1Stats 56 }


jnxMbgPgwGTPV1ICsSYNTFTErr2   OBJECT-TYPE
    SYNTAX      Counter64
    MAX-ACCESS  read-only
    STATUS      deprecated
    DESCRIPTION
    "GTP Cause Mandatory TFT Error."
    ::= { jnxMbgPgwGtpV1Stats 57 }


jnxMbgPgwGTPV1ICsSMNTPktFltrErr1   OBJECT-TYPE
    SYNTAX      Counter64
    MAX-ACCESS  read-only
    STATUS      deprecated
    DESCRIPTION
    "GTP Cause Mandatory Packet Filter Error."
    ::= { jnxMbgPgwGtpV1Stats 58 }


jnxMbgPgwGTPV1ICsSYNPktFltrErr2   OBJECT-TYPE
    SYNTAX      Counter64
    MAX-ACCESS  read-only
    STATUS      deprecated
    DESCRIPTION
    "GTP Cause Mandatory Packet Filter Error."
    ::= { jnxMbgPgwGtpV1Stats 59 }


jnxMbgPgwGTPV1ICsMissUnknownAPN   OBJECT-TYPE
    SYNTAX      Counter64
    MAX-ACCESS  read-only
    STATUS      deprecated
    DESCRIPTION
    "GTP Cause Unknowkn APN missing."
    ::= { jnxMbgPgwGtpV1Stats 60 }


jnxMbgPgwGTPV1ICsUnknownPDPAddr   OBJECT-TYPE
    SYNTAX      Counter64
    MAX-ACCESS  read-only
    STATUS      deprecated
    DESCRIPTION
    "GTP Cause Unknowkn PDP Address."
    ::= { jnxMbgPgwGtpV1Stats 61 }


jnxMbgPgwGTPV1ICsNoTFTCtxExist   OBJECT-TYPE
    SYNTAX      Counter64
    MAX-ACCESS  read-only
    STATUS      deprecated
    DESCRIPTION
    "GTP Cause No TFT Context Exists."
    ::= { jnxMbgPgwGtpV1Stats 62 }

jnxMbgPgwV1NumMsgTx   OBJECT-TYPE
    SYNTAX      Counter64
    MAX-ACCESS  read-only
    STATUS      deprecated
    DESCRIPTION
    "Number Of Messages Tx."
    ::= { jnxMbgPgwGtpV1Stats 63 }


jnxMbgPgwV1NumBytesTx   OBJECT-TYPE
    SYNTAX      Counter64
    MAX-ACCESS  read-only
    STATUS      deprecated
    DESCRIPTION
    "Number of Bytes Tx."
    ::= { jnxMbgPgwGtpV1Stats 64 }


jnxMbgPgwV1EchoReqTx   OBJECT-TYPE
    SYNTAX      Counter64
    MAX-ACCESS  read-only
    STATUS      deprecated
    DESCRIPTION
    "GTP V1 Echo Requests Sent."
    ::= { jnxMbgPgwGtpV1Stats 65 }


jnxMbgPgwV1EchoRespTx   OBJECT-TYPE
    SYNTAX      Counter64
    MAX-ACCESS  read-only
    STATUS      deprecated
    DESCRIPTION
    "GTP V1 Echo Responses Sent."
    ::= { jnxMbgPgwGtpV1Stats 66 }


jnxMbgPgwCrtPdpCxtReqTx   OBJECT-TYPE
    SYNTAX      Counter64
    MAX-ACCESS  read-only
    STATUS      deprecated
    DESCRIPTION
    "GTP V1 Create PDP Context Requests Sent."
    ::= { jnxMbgPgwGtpV1Stats 67 }


jnxMbgPgwCrtPdpCxtRspTx   OBJECT-TYPE
    SYNTAX      Counter64
    MAX-ACCESS  read-only
    STATUS      deprecated
    DESCRIPTION
    "GTP V1 Create PDP Context Responses Sent."
    ::= { jnxMbgPgwGtpV1Stats 68 }


jnxMbgPgwUpdPdpCxtReqTx   OBJECT-TYPE
    SYNTAX      Counter64
    MAX-ACCESS  read-only
    STATUS      deprecated
    DESCRIPTION
    "GTP V1 Update PDP Context Requests Sent."
    ::= { jnxMbgPgwGtpV1Stats 69 }


jnxMbgPgwUpdPdpCxtRspTx   OBJECT-TYPE
    SYNTAX      Counter64
    MAX-ACCESS  read-only
    STATUS      deprecated
    DESCRIPTION
    "GTP V1 Update PDP Context Responses Sent."
    ::= { jnxMbgPgwGtpV1Stats 70 }


jnxMbgPgwDelPdpCxtReqTx   OBJECT-TYPE
    SYNTAX      Counter64
    MAX-ACCESS  read-only
    STATUS      deprecated
    DESCRIPTION
    "GTP V1 Delete PDP Context Requests Sent."
    ::= { jnxMbgPgwGtpV1Stats 71 }


jnxMbgPgwDelPdpCxtRspTx   OBJECT-TYPE
    SYNTAX      Counter64
    MAX-ACCESS  read-only
    STATUS      deprecated
    DESCRIPTION
    "GTP V1 Delete PDP Context Responses Sent."
    ::= { jnxMbgPgwGtpV1Stats 72 }


jnxMbgPgwCrtAAPdpCxtReqTx   OBJECT-TYPE
    SYNTAX      Counter64
    MAX-ACCESS  read-only
    STATUS      deprecated
    DESCRIPTION
    "GTP V1 Create AA PDP Context Requests Sent."
    ::= { jnxMbgPgwGtpV1Stats 73 }


jnxMbgPgwCrtAAPdpCxtRspTx   OBJECT-TYPE
    SYNTAX      Counter64
    MAX-ACCESS  read-only
    STATUS      deprecated
    DESCRIPTION
    "GTP V1 Create AA PDP Context Responses Sent."
    ::= { jnxMbgPgwGtpV1Stats 74 }


jnxMbgPgwDelAAPdpCxtReqTx   OBJECT-TYPE
    SYNTAX      Counter64
    MAX-ACCESS  read-only
    STATUS      deprecated
    DESCRIPTION
    "GTP V1 Delete AA PDP Context Requests Sent."
    ::= { jnxMbgPgwGtpV1Stats 75 }


jnxMbgPgwDelAAPdpCxtRspTx   OBJECT-TYPE
    SYNTAX      Counter64
    MAX-ACCESS  read-only
    STATUS      deprecated
    DESCRIPTION
    "GTP V1 Delete AA PDP Context Responses Sent."
    ::= { jnxMbgPgwGtpV1Stats 76 }


jnxMbgPgwErrorIndTx   OBJECT-TYPE
    SYNTAX      Counter64
    MAX-ACCESS  read-only
    STATUS      deprecated
    DESCRIPTION
    "GTP V1 Error Indication Sent."
    ::= { jnxMbgPgwGtpV1Stats 77 }


jnxMbgPgwNotifReqTx   OBJECT-TYPE
    SYNTAX      Counter64
    MAX-ACCESS  read-only
    STATUS      deprecated
    DESCRIPTION
    "GTP V1 Notify Requests Sent."
    ::= { jnxMbgPgwGtpV1Stats 78 }


jnxMbgPgwNotifRspTx   OBJECT-TYPE
    SYNTAX      Counter64
    MAX-ACCESS  read-only
    STATUS      deprecated
    DESCRIPTION
    "GTP V1 Notify Responses Sent."
    ::= { jnxMbgPgwGtpV1Stats 79 }


jnxMbgPgwNotifRejReqTx   OBJECT-TYPE
    SYNTAX      Counter64
    MAX-ACCESS  read-only
    STATUS      deprecated
    DESCRIPTION
    "GTP V1 Notify Reject Requests Sent."
    ::= { jnxMbgPgwGtpV1Stats 80 }


jnxMbgPgwNotifRejRspTx   OBJECT-TYPE
    SYNTAX      Counter64
    MAX-ACCESS  read-only
    STATUS      deprecated
    DESCRIPTION
    "GTP V1 Notify Reject Responses Sent."
    ::= { jnxMbgPgwGtpV1Stats 81 }


jnxMbgPgwRtInfReqTx   OBJECT-TYPE
    SYNTAX      Counter64
    MAX-ACCESS  read-only
    STATUS      deprecated
    DESCRIPTION
    "GTP V1 Routing Information Requests Sent."
    ::= { jnxMbgPgwGtpV1Stats 82 }


jnxMbgPgwRtInfRspTx   OBJECT-TYPE
    SYNTAX      Counter64
    MAX-ACCESS  read-only
    STATUS      deprecated
    DESCRIPTION
    "GTP V1 Routing Information Responses Sent."
    ::= { jnxMbgPgwGtpV1Stats 83 }


jnxMbgPgwFailRptReqTx   OBJECT-TYPE
    SYNTAX      Counter64
    MAX-ACCESS  read-only
    STATUS      deprecated
    DESCRIPTION
    "GTP V1 Fail Repeat Requests Sent."
    ::= { jnxMbgPgwGtpV1Stats 84 }


jnxMbgPgwFailRptRspTx   OBJECT-TYPE
    SYNTAX      Counter64
    MAX-ACCESS  read-only
    STATUS      deprecated
    DESCRIPTION
    "GTP V1 Fail Repeat Responses Sent."
    ::= { jnxMbgPgwGtpV1Stats 85 }


jnxMbgPgwNotMSPresReqTx   OBJECT-TYPE
    SYNTAX      Counter64
    MAX-ACCESS  read-only
    STATUS      deprecated
    DESCRIPTION
    "GTP V1 MS Not Present Request Sent."
    ::= { jnxMbgPgwGtpV1Stats 86 }


jnxMbgPgwNotMSPresRspTx   OBJECT-TYPE
    SYNTAX      Counter64
    MAX-ACCESS  read-only
    STATUS      deprecated
    DESCRIPTION
    "GTP V1 MS Not Present Responses Sent."
    ::= { jnxMbgPgwGtpV1Stats 87 }

--
-- GTP peer table to store stats.
-- The table is indexed by remote address, local address and routing instance
--

jnxMbgPgwGtpPeerStatsTable OBJECT-TYPE
    SYNTAX SEQUENCE OF JnxMbgPgwGtpPeerEntry
    MAX-ACCESS  not-accessible
    STATUS      deprecated
    DESCRIPTION
        "Each entry corresponds to a GTP Peer discovered."
    ::= { jnxMbgPgwGtpObjects 6 }

jnxMbgPgwGtpPeerEntry OBJECT-TYPE
    SYNTAX      JnxMbgPgwGtpPeerEntry
    MAX-ACCESS  not-accessible
    STATUS      deprecated
    DESCRIPTION
        "A specification of the GTP peer node connected to the GW."
    INDEX     { jnxMbgPgwGtpPeerRmtAddr,
                jnxMbgPgwGtpPeerLclAddr,
                jnxMbgPgwGtpPeerRtgInst }
    ::= { jnxMbgPgwGtpPeerStatsTable 1}

JnxMbgPgwGtpPeerEntry ::= SEQUENCE {
    jnxMbgPgwGtpPeerRmtAddr      IpAddress,
    jnxMbgPgwGtpPeerLclAddr      IpAddress,
    jnxMbgPgwGtpPeerRtgInst      Unsigned32,
    jnxMbgPgwGtpDropCounter      Counter64,
    jnxMbgPgwGtpPktAllocFail     Counter64,
    jnxMbgPgwGtpPktSendFail      Counter64,
    jnxMbgPgwGtpIPVerErrRx       Counter64,
    jnxMbgPgwGtpIPProtoErrRx     Counter64,
    jnxMbgPgwGtpPktLenErrRx      Counter64,
    jnxMbgPgwGtpUnkMsgRx         Counter64,
    jnxMbgPgwGtpMemAllocFailed   Counter64
}

jnxMbgPgwGtpPeerRmtAddr OBJECT-TYPE
    SYNTAX      IpAddress
    MAX-ACCESS  not-accessible
    STATUS      deprecated
    DESCRIPTION
        "The Remote IP address of this GTP entry."
    ::= { jnxMbgPgwGtpPeerEntry 1 }

jnxMbgPgwGtpPeerLclAddr OBJECT-TYPE
    SYNTAX      IpAddress
    MAX-ACCESS  not-accessible
    STATUS      deprecated
    DESCRIPTION
        "The Local IP address of this GTP entry."
    ::= { jnxMbgPgwGtpPeerEntry 2 }

jnxMbgPgwGtpPeerRtgInst OBJECT-TYPE
    SYNTAX      Unsigned32
    MAX-ACCESS  not-accessible
    STATUS      deprecated
    DESCRIPTION
        "The Routing Instance for this Peer."
    ::= { jnxMbgPgwGtpPeerEntry 3 }

jnxMbgPgwGtpDropCounter OBJECT-TYPE
    SYNTAX      Counter64
    MAX-ACCESS  read-only
    STATUS      deprecated
    DESCRIPTION
        "Message Drop Counter."
    ::= { jnxMbgPgwGtpPeerEntry 4 }

jnxMbgPgwGtpPktAllocFail OBJECT-TYPE
    SYNTAX      Counter64
    MAX-ACCESS  read-only
    STATUS      deprecated
    DESCRIPTION
        "Packet allocation failure count."
    ::= { jnxMbgPgwGtpPeerEntry 5 }

jnxMbgPgwGtpPktSendFail OBJECT-TYPE
    SYNTAX      Counter64
    MAX-ACCESS  read-only
    STATUS      deprecated
    DESCRIPTION
        "Packet sending failure count."
    ::= { jnxMbgPgwGtpPeerEntry 6 }

jnxMbgPgwGtpIPVerErrRx OBJECT-TYPE
    SYNTAX      Counter64
    MAX-ACCESS  read-only
    STATUS      deprecated
    DESCRIPTION
        "Rx Packet IP Version Error."
    ::= { jnxMbgPgwGtpPeerEntry 7 }

jnxMbgPgwGtpIPProtoErrRx OBJECT-TYPE
    SYNTAX      Counter64
    MAX-ACCESS  read-only
    STATUS      deprecated
    DESCRIPTION
        "Rx Packet IP Protocol Error."
    ::= { jnxMbgPgwGtpPeerEntry 8 }

jnxMbgPgwGtpPktLenErrRx OBJECT-TYPE
    SYNTAX      Counter64
    MAX-ACCESS  read-only
    STATUS      deprecated
    DESCRIPTION
        "Rx Packet Length Error."
    ::= { jnxMbgPgwGtpPeerEntry 9 }

jnxMbgPgwGtpUnkMsgRx OBJECT-TYPE
    SYNTAX      Counter64
    MAX-ACCESS  read-only
    STATUS      deprecated
    DESCRIPTION
        "Unknown Message Count."
    ::= { jnxMbgPgwGtpPeerEntry 10 }

jnxMbgPgwGtpMemAllocFailed OBJECT-TYPE
    SYNTAX      Counter64
    MAX-ACCESS  read-only
    STATUS      deprecated
    DESCRIPTION
        "Memory Allocation Failed."
    ::= { jnxMbgPgwGtpPeerEntry 11 }

jnxMbgPgwGtpNotificationVars   OBJECT IDENTIFIER ::= {
                                             jnxMbgPgwGtpObjects 7 }
jnxMbgPgwGtpPeerName OBJECT-TYPE
    SYNTAX      DisplayString
    MAX-ACCESS  accessible-for-notify
    STATUS      current
    DESCRIPTION
    "GTP Peer Name/IP"
   ::= { jnxMbgPgwGtpNotificationVars 1 }

jnxMbgPgwGtpAlarmThrshld OBJECT-TYPE
    SYNTAX        INTEGER {
                      thresholdlow     (0),
                      thresholdhigh    (1)
    }
    MAX-ACCESS    accessible-for-notify
    STATUS        deprecated
    DESCRIPTION
    "Alarm threshold::
     0: MOBILED_ALARM_THRESHOLD_LOW
     1: MOBILED_ALARM_THRESHOLD_HIGH"
   ::= { jnxMbgPgwGtpNotificationVars 2 }

jnxMbgPgwGtpAlarmState OBJECT-TYPE
    SYNTAX        INTEGER {
                      alarmcleared    (0),
                      alarmraised     (1)
    }
    MAX-ACCESS    accessible-for-notify
    STATUS        deprecated
    DESCRIPTION
    "Alarm state::
     0: MOBILED_ALARM_CLEARED
     1: MOBILED_ALARM_RAISED"
   ::= { jnxMbgPgwGtpNotificationVars 3 }

jnxMbgPgwGtpAlarmStatCounter OBJECT-TYPE
    SYNTAX      Unsigned32
    MAX-ACCESS    accessible-for-notify
    STATUS        current
    DESCRIPTION
    "Current Value of (Alarm) Statistics Counter
     eg: in jnxMbgPgwGtpPrDNTPerPrAlrmActv it spefies the number
         of times peer is down with in the monitoring interval"
   ::= { jnxMbgPgwGtpNotificationVars 4 }

jnxMbgPgwGtpInterfaceType OBJECT-TYPE
    SYNTAX      DisplayString
    MAX-ACCESS  accessible-for-notify
    STATUS      current
    DESCRIPTION
    "GTP Interface Type which can be one of gn/gp/S5/S8"
   ::= { jnxMbgPgwGtpNotificationVars 5 }

jnxMbgPgwGtpGwName OBJECT-TYPE
    SYNTAX      DisplayString
    MAX-ACCESS  accessible-for-notify
    STATUS      current
    DESCRIPTION
        "A string that indicates the gateway name"
    ::= { jnxMbgPgwGtpNotificationVars 6 }

jnxMbgPgwGtpGwIndex OBJECT-TYPE
    SYNTAX      Unsigned32
    MAX-ACCESS  accessible-for-notify
    STATUS      current
    DESCRIPTION
        "Current Gateway ID value"
    ::= { jnxMbgPgwGtpNotificationVars 7 }

jnxMbgPgwGtpPeerGWUpNotif NOTIFICATION-TYPE
     OBJECTS          { jnxMbgPgwGtpPeerName }
     STATUS      deprecated
     DESCRIPTION
     "GTPC Peer UP Notification"
    ::= { jnxMbgPgwGtpNotifications 1 }

jnxMbgPgwGtpPeerDownNotif NOTIFICATION-TYPE
    OBJECTS          { jnxMbgPgwGtpPeerName }
    STATUS      deprecated
    DESCRIPTION
     "GTPC Peer Down Notification"
    ::= { jnxMbgPgwGtpNotifications 2 }

jnxMbgPgwGtpPeerDNThresPerPeerNotif NOTIFICATION-TYPE
    OBJECTS     { jnxMbgPgwGtpPeerName,
              jnxMbgPgwGtpAlarmState,
              jnxMbgPgwGtpAlarmStatCounter }
    STATUS          deprecated
    DESCRIPTION
        "Per Peer Threshold For The
         Number of GTP Peer Down."
    ::= { jnxMbgPgwGtpNotifications 3 }

jnxMbgPgwGtpPeerGwUpNotify NOTIFICATION-TYPE
     OBJECTS          { jnxMbgPgwGtpGwIndex,
                        jnxMbgPgwGtpGwName,
                        jnxMbgPgwGtpInterfaceType,
                        jnxMbgPgwGtpPeerName }
     STATUS      current
     DESCRIPTION
     "GTPC Peer UP Notification. This trap is sent when a new peer is added
       or an existing peer goes down and comes back up."
    ::= { jnxMbgPgwGtpNotifications 4 }

jnxMbgPgwGtpPeerGwDnNotify NOTIFICATION-TYPE
    OBJECTS          { jnxMbgPgwGtpGwIndex,
                        jnxMbgPgwGtpGwName,
                       jnxMbgPgwGtpInterfaceType,
                       jnxMbgPgwGtpPeerName }
    STATUS      current
    DESCRIPTION
     "GTPC Peer Down Notification. This trap is sent when a peer connection
      goes down."
    ::= { jnxMbgPgwGtpNotifications 5 }

jnxMbgPgwGtpPrDnTPerPrAlrmActv NOTIFICATION-TYPE
    OBJECTS     { jnxMbgPgwGtpGwIndex,
                        jnxMbgPgwGtpGwName,
                  jnxMbgPgwGtpInterfaceType,
                  jnxMbgPgwGtpPeerName,
                  jnxMbgPgwGtpAlarmStatCounter }
    STATUS          current
    DESCRIPTION
        "Peer down Threshold trap Active. This is sent when a peer connection
         flaps for more than a higher threshold number of times with in a
         monitor interval."
    ::= { jnxMbgPgwGtpNotifications 6 }

jnxMbgPgwGtpPrDnTPerPrAlrmClr NOTIFICATION-TYPE
    OBJECTS     { jnxMbgPgwGtpGwIndex,
                        jnxMbgPgwGtpGwName,
                  jnxMbgPgwGtpInterfaceType,
                  jnxMbgPgwGtpPeerName,
                  jnxMbgPgwGtpAlarmStatCounter }
    STATUS          current
    DESCRIPTION
        "Peer down Threshold trap Cleared. This is sent when the number of
         times a peer connection flaps in a monitor interval come down below
         the lower threshold."
    ::= { jnxMbgPgwGtpNotifications 7 }

END
