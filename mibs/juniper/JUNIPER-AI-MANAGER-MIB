--
-- Juniper Enterprise Specific MIB: Advanced Insight Manager MIB
--
-- Copyright (c) 2007, Juniper Networks, Inc.
-- All rights reserved.
--
-- The contents of this document are subject to change without notice.
--


JUNIPER-AI-MANAGER-MIB DEFINITIONS ::= BEGIN

IMPORTS
    MODULE-IDENTITY, OBJECT-TYPE, NOTIFICATION-TYPE
        FROM SNMPv2-SMI
    DisplayString
        FROM SNMPv2-TC
    jnxAdvancedInsightMgr
        FROM JUNIPER-SMI;

jnxAIManager MODULE-IDENTITY

    LAST-UPDATED "200710090000Z"
    ORGANIZATION "Juniper Networks, Inc."
    CONTACT-INFO
            "        Juniper Technical Assistance Center
		     Juniper Networks, Inc.
		     1194 N. Mathilda Avenue
		     Sunnyvale, CA 94089
		     E-mail: support@juniper.net"

    DESCRIPTION
            "The MIB modules representing Juniper Networks'
	    implementation of enterprise specific MIBs
	    supported by a single SNMP agent."
    REVISION    "200710090000Z" -- 09-Oct-07
    DESCRIPTION
            "Added Advanced Insight Manager identification objects."

    ::= { jnxAdvancedInsightMgr 1 }


-- Juniper Advanced Insight Manager MIB
--

-- Top level objects

    jnxAIMDescr OBJECT-TYPE
	SYNTAX		DisplayString (SIZE (0..63))
	MAX-ACCESS	read-only
	STATUS		current
	DESCRIPTION
	        "Description of Advanced Insight notification."
	::= { jnxAIManager 1 }

    jnxAIMHostName OBJECT-TYPE
	SYNTAX		DisplayString (SIZE (0..63))
	MAX-ACCESS	read-only
	STATUS		current
	DESCRIPTION
		"Device associated with Advanced Insight
		notification."
	::= { jnxAIManager 2 }

    jnxAIMOrganization OBJECT-TYPE
	SYNTAX		DisplayString (SIZE (0..63))
	MAX-ACCESS	read-only
	STATUS		current
	DESCRIPTION
		"Organization associated with Advanced Insight
		notification."
	::= { jnxAIManager 3 }

    jnxAIMIncidentHostID OBJECT-TYPE
	SYNTAX		DisplayString (SIZE (0..63))
	MAX-ACCESS	read-only
	STATUS		current
	DESCRIPTION
		"HostID of incident associated with Advanced
		Insight notification."
	::= { jnxAIManager 4 }

    jnxAIMCaseID OBJECT-TYPE
	SYNTAX		DisplayString (SIZE (0..63))
	MAX-ACCESS	read-only
	STATUS		current
	DESCRIPTION
		"CaseID (assigned by Juniper) associated with
		Advanced Insight notification."
	::= { jnxAIManager 5 }

    jnxAIMIssueDate OBJECT-TYPE
	SYNTAX		DisplayString (SIZE (0..63))
	MAX-ACCESS	read-only
	STATUS		current
	DESCRIPTION
		"Issue Date of the intelligence message associated
		with Advanced Insight notification."
	::= { jnxAIManager 6 }

	jnxAIMIPAddress OBJECT-TYPE
	SYNTAX		DisplayString (SIZE (0..63))
	MAX-ACCESS	read-only
	STATUS		current
	DESCRIPTION
		"IPAddress of device associated with Advanced
		Insight notification."
	::= { jnxAIManager 7 }

	jnxAIMSerialNumber OBJECT-TYPE
	SYNTAX		DisplayString (SIZE (0..63))
	MAX-ACCESS	read-only
	STATUS		current
	DESCRIPTION
		"SerailNumber of device associated with Advanced
		Insight notification."
	::= { jnxAIManager 8 }

	jnxAIMPartNumber OBJECT-TYPE
	SYNTAX		DisplayString (SIZE (0..63))
	MAX-ACCESS	read-only
	STATUS		current
	DESCRIPTION
		"part number of device associated with Advanced
		Insight notification."
	::= { jnxAIManager 9 }

	jnxAIMContractAgreementNumber OBJECT-TYPE
	SYNTAX		DisplayString (SIZE (0..63))
	MAX-ACCESS	read-only
	STATUS		current
	DESCRIPTION
		"Contract Agreement Number."
	::= { jnxAIManager 10 }

	jnxAIMContractAgreementStatus OBJECT-TYPE
	SYNTAX		DisplayString (SIZE (0..63))
	MAX-ACCESS	read-only
	STATUS		current
	DESCRIPTION
		"Contract Agreement Status."
	::= { jnxAIManager 11 }

	jnxAIMContractSKU OBJECT-TYPE
	SYNTAX		DisplayString (SIZE (0..63))
	MAX-ACCESS	read-only
	STATUS		current
	DESCRIPTION
		"Contract SKU."
	::= { jnxAIManager 12 }

	jnxAIMContractSKUType OBJECT-TYPE
	SYNTAX		DisplayString (SIZE (0..63))
	MAX-ACCESS	read-only
	STATUS		current
	DESCRIPTION
		"Contract SKU Type."
	::= { jnxAIManager 13 }

	jnxAIMContractStartDate OBJECT-TYPE
	SYNTAX		DisplayString (SIZE (0..63))
	MAX-ACCESS	read-only
	STATUS		current
	DESCRIPTION
		"Contract Start Date."
	::= { jnxAIManager 14 }

	jnxAIMContractEndDate OBJECT-TYPE
	SYNTAX		DisplayString (SIZE (0..63))
	MAX-ACCESS	read-only
	STATUS		current
	DESCRIPTION
		"Contract End Date."
	::= { jnxAIManager 15 }

    jnxAIMProduct OBJECT-TYPE
	SYNTAX		DisplayString (SIZE (0..63))
	MAX-ACCESS	read-only
	STATUS		current
	DESCRIPTION
		"Product."
	::= { jnxAIManager 16 }

	jnxAIMPlatform OBJECT-TYPE
	SYNTAX		DisplayString (SIZE (0..63))
	MAX-ACCESS	read-only
	STATUS		current
	DESCRIPTION
		"Platform."
	::= { jnxAIManager 17 }

	jnxAIMJunosVersion OBJECT-TYPE
	SYNTAX		DisplayString (SIZE (0..63))
	MAX-ACCESS	read-only
	STATUS		current
	DESCRIPTION
		"Junos Version."
	::= { jnxAIManager 18 }

	jnxAIMScriptVersion OBJECT-TYPE
	SYNTAX		DisplayString (SIZE (0..63))
	MAX-ACCESS	read-only
	STATUS		current
	DESCRIPTION
		"AI Script Version."
	::= { jnxAIManager 19 }

	jnxAIMExposureMsg OBJECT-TYPE
	SYNTAX		DisplayString (SIZE (0..63))
	MAX-ACCESS	read-only
	STATUS		current
	DESCRIPTION
		"Exposure Message."
	::= { jnxAIManager 20 }

	jnxAIMExposureIssueDate OBJECT-TYPE
	SYNTAX		DisplayString (SIZE (0..63))
	MAX-ACCESS	read-only
	STATUS		current
	DESCRIPTION
		"Exposure Issue Date."
	::= { jnxAIManager 21 }

	jnxAIMExposurePRNumber OBJECT-TYPE
	SYNTAX		DisplayString (SIZE (0..63))
	MAX-ACCESS	read-only
	STATUS		current
	DESCRIPTION
		"Exposure PR Number."
	::= { jnxAIManager 22 }

	jnxAIMExposureLink OBJECT-TYPE
	SYNTAX		DisplayString (SIZE (0..63))
	MAX-ACCESS	read-only
	STATUS		current
	DESCRIPTION
		"Exposure Link."
	::= { jnxAIManager 23 }

	jnxAIMLastIJMBReceivedTime OBJECT-TYPE
	SYNTAX		DisplayString (SIZE (0..63))
	MAX-ACCESS	read-only
	STATUS		current
	DESCRIPTION
		"Last IJMB received time."
	::= { jnxAIManager 24 }

	jnxAIMDeviceState OBJECT-TYPE
	SYNTAX		DisplayString (SIZE (0..63))
	MAX-ACCESS	read-only
	STATUS		current
	DESCRIPTION
		"State of the connected member device"
	::= { jnxAIManager 25 }

	jnxAIMBIOSState OBJECT-TYPE
	SYNTAX		DisplayString (SIZE (0..63))
	MAX-ACCESS	read-only
	STATUS		current
	DESCRIPTION
		"BIOS State of the device"
	::= { jnxAIManager 26 }

	jnxAIMDaysToExpireForPartnerCert OBJECT-TYPE
	SYNTAX		DisplayString (SIZE (0..63))
	MAX-ACCESS	read-only
	STATUS		current
	DESCRIPTION
		"Days to expire for partner certificate"
	::= { jnxAIManager 27 }

	jnxAIMExpDateTimePartnerCert OBJECT-TYPE
	SYNTAX		DisplayString (SIZE (0..63))
	MAX-ACCESS	read-only
	STATUS		current
	DESCRIPTION
		"Date and time of expire of partner certificate"
	::= { jnxAIManager 28 }

	jnxAIMPHDExpectedDeviceSlot OBJECT-TYPE
	SYNTAX		DisplayString (SIZE (0..63))
	MAX-ACCESS	read-only
	STATUS		current
	DESCRIPTION
		"Expected time slot for PHD on the device"
	::= { jnxAIManager 29 }

	jnxAIMPHDExpectedSNSlot OBJECT-TYPE
	SYNTAX		DisplayString (SIZE (0..63))
	MAX-ACCESS	read-only
	STATUS		current
	DESCRIPTION
		"Expected time slot for PHD in Service Now"
	::= { jnxAIManager 30 }

	jnxAIMPHDReceivedTime OBJECT-TYPE
	SYNTAX		DisplayString (SIZE (0..63))
	MAX-ACCESS	read-only
	STATUS		current
	DESCRIPTION
		"Received time slot for PHD on the device"
	::= { jnxAIManager 31 }

	jnxAIMPHDFailureType OBJECT-TYPE
	SYNTAX		DisplayString (SIZE (0..63))
	MAX-ACCESS	read-only
	STATUS		current
	DESCRIPTION
		"Type of failure of PHD. Ex: Missed or Invalid PHD"
	::= { jnxAIManager 32 }

	jnxAIMObjectId OBJECT-TYPE
	SYNTAX		DisplayString (SIZE (0..63))
	MAX-ACCESS	read-only
	STATUS		current
	DESCRIPTION
		"Database Id associated with Advanced
		Insight notification."
	::= { jnxAIManager 33 }

--
-- definition of Advanced Insight Manager traps
--

jnxAIManagerNotifications  OBJECT IDENTIFIER ::= { jnxAIManager 0 }


    jnxAIMNewIncidentDetected NOTIFICATION-TYPE
	OBJECTS		{ jnxAIMDescr,
			  jnxAIMHostName,
			  jnxAIMOrganization,
			  jnxAIMIncidentHostID,
			  jnxAIMIPAddress,
			  jnxAIMObjectId }
	STATUS		current
	DESCRIPTION
		"A jnxAIMNewIncidentDetected trap signifies that
		a new incident has been detected."
	::= { jnxAIManagerNotifications 1 }

    jnxAIMIncidentReportedToJuniper NOTIFICATION-TYPE
	OBJECTS		{ jnxAIMDescr,
			  jnxAIMHostName,
			  jnxAIMOrganization,
			  jnxAIMIncidentHostID,
			  jnxAIMIPAddress }
	STATUS		current
	DESCRIPTION
		"A jnxAIMIncidentReportedToJuniper trap signifies
		that an incident has been reported to Juniper."
	::= { jnxAIManagerNotifications 2 }

    jnxAIMCaseIDAssigned NOTIFICATION-TYPE
	OBJECTS		{ jnxAIMDescr,
			  jnxAIMHostName,
			  jnxAIMOrganization,
			  jnxAIMIncidentHostID,
			  jnxAIMCaseID,
			  jnxAIMIPAddress }
	STATUS		current
	DESCRIPTION
		"A jnxAIMCaseIDAssigned trap signifies that an
		incident has been assigned CaseID."
	::= { jnxAIManagerNotifications 3 }

    jnxAIMCaseUpdated NOTIFICATION-TYPE
	OBJECTS		{ jnxAIMDescr,
			  jnxAIMHostName,
			  jnxAIMOrganization,
			  jnxAIMIncidentHostID,
			  jnxAIMCaseID,
			  jnxAIMIPAddress }
	STATUS		current
	DESCRIPTION
		"A jnxAIMCaseUpdated trap signifies that
		a case has been updated."
	::= { jnxAIManagerNotifications 4 }

    jnxAIMNewIntelligenceMessage NOTIFICATION-TYPE
	OBJECTS		{ jnxAIMDescr,
			  jnxAIMOrganization,
			  jnxAIMIssueDate,
			  jnxAIMObjectId }
	STATUS		current
	DESCRIPTION
		"A jnxAIMNewIntelligenceMessage trap signifies
		that a new intelligence message has been received."
	::= { jnxAIManagerNotifications 5 }

	jnxAIMNewEOLMatch NOTIFICATION-TYPE
	OBJECTS		{ jnxAIMDescr,
			  jnxAIMHostName,
			  jnxAIMIPAddress }
	STATUS		current
	DESCRIPTION
		"A jnxAIMNewEOLMatch trap signifies that
		a new EOL match for a Device has been detected."
	::= { jnxAIManagerNotifications 6 }

	jnxAIMNewPBNArrival NOTIFICATION-TYPE
	OBJECTS		{ jnxAIMDescr,
			  jnxAIMHostName,
			  jnxAIMIPAddress }
	STATUS		current
	DESCRIPTION
		"A jnxAIMNewPBNArrival trap signifies that
		a new PBN has arrived."
	::= { jnxAIManagerNotifications 7 }

	jnxAIMNewPBNMatch NOTIFICATION-TYPE
	OBJECTS		{ jnxAIMDescr}
	STATUS		current
	DESCRIPTION
		"A jnxAIMNewPBNMatch trap signifies that
		a new PBN match for a Device has been detected."
	::= { jnxAIManagerNotifications 8 }

	jnxAIMContractExpiry NOTIFICATION-TYPE
	OBJECTS		{ jnxAIMDescr,
	          jnxAIMHostName,
			  jnxAIMSerialNumber,
			  jnxAIMPartNumber,
			  jnxAIMContractAgreementNumber,
			  jnxAIMContractAgreementStatus,
			  jnxAIMContractSKU,
			  jnxAIMContractSKUType,
			  jnxAIMContractStartDate,
			  jnxAIMContractEndDate,
			  jnxAIMIPAddress }
	STATUS		current
	DESCRIPTION
		"A jnxAIMContractExpiry trap signifies that
		a contarct for a serial number is going to expire in the next 60 days."
	::= { jnxAIManagerNotifications 9 }

	jnxAIMNewExposure NOTIFICATION-TYPE
	OBJECTS		{ jnxAIMDescr,
	          jnxAIMHostName,
			  jnxAIMProduct,
			  jnxAIMPlatform,
			  jnxAIMJunosVersion,
			  jnxAIMScriptVersion,
			  jnxAIMExposureMsg,
			  jnxAIMExposureIssueDate,
			  jnxAIMExposurePRNumber,
			  jnxAIMExposureLink,
			  jnxAIMIPAddress }
	STATUS		current
	DESCRIPTION
		"A jnxAIMNewExposure trap signifies that
		a new exposure for a device has been detected."
	::= { jnxAIManagerNotifications 10 }

   jnxAIMIncidentWithoutShiptoAddress NOTIFICATION-TYPE
	OBJECTS		{ jnxAIMDescr,
			  jnxAIMHostName,
			  jnxAIMOrganization,
			  jnxAIMIncidentHostID,
			  jnxAIMIPAddress }
	STATUS		current
	DESCRIPTION
		"A jnxAIMIncidentWithoutShiptoAddress trap signifies
		that an incident has been reported to Juniper without ship to address."
	::= { jnxAIManagerNotifications 11 }

	jnxAIMSwitchToAutoCollectionOfIJMB NOTIFICATION-TYPE
	OBJECTS		{ jnxAIMDescr,
	          jnxAIMHostName,
			  jnxAIMProduct,
			  jnxAIMPlatform,
			  jnxAIMSerialNumber,
			  jnxAIMLastIJMBReceivedTime }
	STATUS		current
	DESCRIPTION
		"A jnxAIMSwitchToAutoCollectionOfIJMB trap signifies that
		Service Now has switched to auto collection of IJMB for a device."
	::= { jnxAIManagerNotifications 12 }

	jnxAIMConnectedMemberDeviceActions NOTIFICATION-TYPE
	OBJECTS		{ jnxAIMDescr,
              jnxAIMOrganization,
              jnxAIMHostName,
			  jnxAIMIPAddress,
			  jnxAIMSerialNumber,
			  jnxAIMDeviceState}
	STATUS		current
	DESCRIPTION
		"A jnxAIMConnectedMemberDeviceActions trap signifies that
		connected member devices have been added in partner proxy or
		deleted in connected member."
	::= { jnxAIManagerNotifications 13 }

	jnxAIMDeviceBIOSState NOTIFICATION-TYPE
	OBJECTS		{ jnxAIMDescr,
              jnxAIMOrganization,
              jnxAIMHostName,
			  jnxAIMIPAddress,
			  jnxAIMSerialNumber,
			  jnxAIMBIOSState}
	STATUS		current
	DESCRIPTION
		"A jnxAIMDeviceBIOSState trap signifies that
		BIOS state of a device is either a success, failure
		or both."
	::= { jnxAIManagerNotifications 14 }

	jnxAIMPartnerCertExpiry NOTIFICATION-TYPE
	OBJECTS		{ jnxAIMDaysToExpireForPartnerCert,
              		jnxAIMExpDateTimePartnerCert}
	STATUS		current
	DESCRIPTION
		"A jnxAIMPartnerCertExpiry trap notifies the user about the expiry of the Partner certificate. "
	::= { jnxAIManagerNotifications 15 }

	jnxAIMPartnerCertExpired NOTIFICATION-TYPE
	OBJECTS		{jnxAIMExpDateTimePartnerCert}
	STATUS		current
	DESCRIPTION
		"A jnxAIMPartnerCertExpired trap notifies the user after the expiry of the Partner certificate. "
	::= { jnxAIManagerNotifications 16 }

	jnxAIMPHDCollectionFailure NOTIFICATION-TYPE
	OBJECTS		{jnxAIMDescr, jnxAIMHostName, jnxAIMIPAddress, jnxAIMPHDFailureType, jnxAIMPHDReceivedTime, jnxAIMPHDExpectedDeviceSlot, jnxAIMPHDExpectedSNSlot}
	STATUS		current
	DESCRIPTION
		"A jnxAIMPHDCollectionFailure trap notifies the PHD collection failure. "
	::= { jnxAIManagerNotifications 17 }

END
