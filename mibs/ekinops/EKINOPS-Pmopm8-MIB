-- *****************************************************************
-- EKINOPS-Pmopm8.TXT:  MIB
--
--MIB Part Number:3MI00215AAAA
--MIB Version:02
--
-- Copyright (c) 2014 by Ekinops
-- All rights reserved.
--
-- *****************************************************************

EKINOPS-Pmopm8-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

modulePmopm8 MODULE-IDENTITY
        LAST-UPDATED "201605230000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.net"
        DESCRIPTION
          "MIB for managing Ekinops modules"
	REVISION "201407280000Z"
	DESCRIPTION
	  "Initial Version."


	REVISION "201605230000Z"
	DESCRIPTION
	  "New AlarmType – synthesisAlarm (12)"
        ::= { ekinops 66 }



--- *****************************************************
---     LEAF LEVEL 2
--- *****************************************************


pmopm8alarms OBJECT IDENTIFIER ::= { modulePmopm8 2 }
pmopm8AlmOther OBJECT IDENTIFIER ::= { pmopm8alarms 1 }
pmopm8AlmOtherNurg OBJECT IDENTIFIER ::= { pmopm8AlmOther 1 }
pmopm8AlmOtherUrg OBJECT IDENTIFIER ::= { pmopm8AlmOther 2 }
pmopm8AlmOtherCrit OBJECT IDENTIFIER ::= { pmopm8AlmOther 3 }

pmopm8AlmClient OBJECT IDENTIFIER ::= { pmopm8alarms 2 }
pmopm8AlmClientNurg OBJECT IDENTIFIER ::= { pmopm8AlmClient 1 }
pmopm8AlmClientUrg OBJECT IDENTIFIER ::= { pmopm8AlmClient 2 }
pmopm8AlmClientCrit OBJECT IDENTIFIER ::= { pmopm8AlmClient 3 }

pmopm8AlmLine OBJECT IDENTIFIER ::= { pmopm8alarms 3 }
pmopm8AlmLineNurg OBJECT IDENTIFIER ::= { pmopm8AlmLine 1 }
pmopm8AlmLineUrg OBJECT IDENTIFIER ::= { pmopm8AlmLine 2 }
pmopm8AlmLineCrit OBJECT IDENTIFIER ::= { pmopm8AlmLine 3 }



pmopm8measures OBJECT IDENTIFIER ::= { modulePmopm8 3 }
pmopm8MesrOther OBJECT IDENTIFIER ::= { pmopm8measures 1 }
pmopm8MesrClient OBJECT IDENTIFIER ::= { pmopm8measures 2 }
pmopm8MesrLine OBJECT IDENTIFIER ::= { pmopm8measures 3 }




pmopm8controlsWrite OBJECT IDENTIFIER ::= { modulePmopm8 6 }
pmopm8CtrlOther OBJECT IDENTIFIER ::= { pmopm8controlsWrite 1 }
pmopm8CtrlClient OBJECT IDENTIFIER ::= { pmopm8controlsWrite 2 }
pmopm8CtrlLine OBJECT IDENTIFIER ::= { pmopm8controlsWrite 3 }

pmopm8ri OBJECT IDENTIFIER ::= { modulePmopm8 7 }
pmopm8riTable OBJECT IDENTIFIER ::= { pmopm8ri 1 }

pmopm8download OBJECT IDENTIFIER ::= { modulePmopm8 8 }
pmopm8DwlOther OBJECT IDENTIFIER ::= { pmopm8download 1 }
pmopm8DwlClient OBJECT IDENTIFIER ::= { pmopm8download 2 }
pmopm8DwlLine OBJECT IDENTIFIER ::= { pmopm8download 3 }


pmopm8Config OBJECT IDENTIFIER ::= { modulePmopm8 9 }

pmopm8traps OBJECT IDENTIFIER ::= { modulePmopm8 10 }




--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************


Pmopm8Grid ::= TEXTUAL-CONVENTION
    STATUS      current
    DESCRIPTION "Different grids on the modules"
    SYNTAX INTEGER {
		grid200(200),
		grid100(100),
		grid50(50)
           }

Pmopm8MultiRate ::= TEXTUAL-CONVENTION
    STATUS      current
    DESCRIPTION "different values for a client port"
    SYNTAX INTEGER

Pmopm8OtxChannel ::= TEXTUAL-CONVENTION
    STATUS      current
    DESCRIPTION "different values for a client port"
    SYNTAX INTEGER

Pmopm8AdjustValue ::= TEXTUAL-CONVENTION
    STATUS      current
    DESCRIPTION "different values for a client port"
    SYNTAX INTEGER

Pmopm8OtxMode ::= TEXTUAL-CONVENTION
    STATUS      current
    DESCRIPTION "different values for a client port"
    SYNTAX INTEGER

--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pmopm8RinvReloadInventory OBJECT-TYPE
  SYNTAX EkiOnOff
  MAX-ACCESS read-write
  STATUS current
  DESCRIPTION
        "Reload the inventory: This OID triggers an
         inventory reload."
  ::= { pmopm8ri 2 }

pmopm8RinvHwPlatform OBJECT-TYPE
  SYNTAX DisplayString
  MAX-ACCESS read-only
  STATUS current
  DESCRIPTION
        "HW platform description: This OID contains the
         description of the Hardware platform."
  ::= { pmopm8ri 3 }

pmopm8RinvModulePlatform OBJECT-TYPE
  SYNTAX DisplayString
  MAX-ACCESS read-only
  STATUS current
  DESCRIPTION
        "Module platform description: This OID contains the
         description of the Module."
  ::= { pmopm8ri 4 }

pmopm8RinvSwPlatform OBJECT-TYPE
  SYNTAX DisplayString
  MAX-ACCESS read-only
  STATUS current
  DESCRIPTION
        "SW platform description: This OID contains the
         description of the Software platform."
  ::= { pmopm8ri 5 }

pmopm8RinvGwPlatform OBJECT-TYPE
  SYNTAX DisplayString
  MAX-ACCESS read-only
  STATUS current
  DESCRIPTION
        "GW platform desciption: This OID contains the
         description of the Gateware platform."
  ::= { pmopm8ri 6 }


pmopm8RinvSfpTable OBJECT-TYPE
      SYNTAX  SEQUENCE OF Pmopm8RinvSfpEntry
      MAX-ACCESS  not-accessible
      STATUS  current
      DESCRIPTION
              "List of the SFPs on the selected module"
      ::= { pmopm8riTable 1 }

pmopm8RinvSfpEntry OBJECT-TYPE
        SYNTAX  Pmopm8RinvSfpEntry
        MAX-ACCESS  not-accessible
        STATUS  current
        DESCRIPTION
              "Row definition for the SFP table"
        INDEX   { pmopm8RinvSfpIndex }
        ::= { pmopm8RinvSfpTable 1 }



Pmopm8RinvSfpEntry::=
        SEQUENCE {
          pmopm8RinvSfpIndex
              Integer32,
          pmopm8Rinvsfp
              DisplayString
        }


    pmopm8RinvSfpIndex OBJECT-TYPE
        SYNTAX  Integer32(1..16)
        MAX-ACCESS  read-only
        STATUS  current
        DESCRIPTION
              "Index for SFP table"
        ::= { pmopm8RinvSfpEntry 1 }


    pmopm8Rinvsfp OBJECT-TYPE
        SYNTAX  DisplayString
        MAX-ACCESS  read-only
        STATUS  current
        DESCRIPTION
              "Inventory for the SFP: This OID contains the inventory for the SFP"
        ::= { pmopm8RinvSfpEntry 2 }




pmopm8RinvLineTable OBJECT-TYPE
      SYNTAX  SEQUENCE OF Pmopm8RinvLineEntry
      MAX-ACCESS  not-accessible
      STATUS  current
      DESCRIPTION
              "List of the XFPs on the selected module"
      ::= { pmopm8riTable 2 }

pmopm8RinvLineEntry OBJECT-TYPE
        SYNTAX  Pmopm8RinvLineEntry
        MAX-ACCESS  not-accessible
        STATUS  current
        DESCRIPTION
              "Row definition for the XFP table"
        INDEX   { pmopm8RinvLineIndex }
        ::= { pmopm8RinvLineTable 1 }



Pmopm8RinvLineEntry::=
        SEQUENCE {
          pmopm8RinvLineIndex
              Integer32,
          pmopm8RinvxfpLine
              DisplayString
        }


    pmopm8RinvLineIndex OBJECT-TYPE
        SYNTAX  Integer32(1..16)
        MAX-ACCESS  read-only
        STATUS  current
        DESCRIPTION
              "Index for XFP table"
        ::= { pmopm8RinvLineEntry 1 }


    pmopm8RinvxfpLine OBJECT-TYPE
        SYNTAX  DisplayString
        MAX-ACCESS  read-only
        STATUS  current
        DESCRIPTION
              "Inventory for the XFP: This OID contains the inventory for the XFP"
        ::= { pmopm8RinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pmopm8AlmsynthAlm0 OBJECT IDENTIFIER ::= { pmopm8AlmOtherCrit 0 }




pmopm8AlmDefFuseB OBJECT-TYPE
	  SYNTAX EkiOnOff
	  MAX-ACCESS read-only
	  STATUS current
	  DESCRIPTION
        "
        Fuse B Fail :This OID indicates
        that the fuse of the power input
        B is in fail condition  <Help>
          Status of the Fuse B <Condtype>
        DEF_FUSE_B <Probcause> powerProblem
        (36) <Alarmtype> equipmentAlarm
        (5) <Polarity> (2)
        "
	  ::= { pmopm8AlmsynthAlm0 16 }



pmopm8AlmDefFuseA OBJECT-TYPE
	  SYNTAX EkiOnOff
	  MAX-ACCESS read-only
	  STATUS current
	  DESCRIPTION
        "
        Fuse A Fail :This OID indicates
        that the fuse of the power input
        A is in fail condition  <Help>
          Status of the Fuse A <Condtype>
        DEF_FUSE_A <Probcause> powerProblem
        (36) <Alarmtype> equipmentAlarm
        (5) <Polarity> (2)
        "
	  ::= { pmopm8AlmsynthAlm0 15 }



pmopm8AlmModGlobFail OBJECT-TYPE
	  SYNTAX EkiOnOff
	  MAX-ACCESS read-only
	  STATUS current
	  DESCRIPTION
        "
        Module Failure :This OID is set
        on detection of a failure originating
        from the PM <Condtype> MOD_GLOB_FAIL
        <Probcause> equipmentMalfunction
        (16) <Alarmtype> synthesisAlarm
        (12)  <Polarity> (2)
        "
	  ::= { pmopm8AlmsynthAlm0 9 }



--- *****************************************************
---     LEAF for the synthAlm2 article
--- *****************************************************
pmopm8AlmsynthAlm2 OBJECT IDENTIFIER ::= { pmopm8AlmOtherNurg 2 }




pmopm8AlmCorrelatOff OBJECT-TYPE
	  SYNTAX EkiOnOff
	  MAX-ACCESS read-only
	  STATUS current
	  DESCRIPTION
        "
        Not Used : <Condtype> CORRELAT_OFF
        <Probcause> other (1) <Alarmtype>
        other (1) <Polarity> (2)
        "
	  ::= { pmopm8AlmsynthAlm2 4 }



pmopm8AlmConfTableLoad OBJECT-TYPE
	  SYNTAX EkiOnOff
	  MAX-ACCESS read-only
	  STATUS current
	  DESCRIPTION
        "
        PM Configuration Load : <Condtype>
        CONF_TABLE_LOAD <Probcause> other
        (1) <Alarmtype> other (1) <Polarity>
        (2)
        "
	  ::= { pmopm8AlmsynthAlm2 3 }



pmopm8AlmInvUpload OBJECT-TYPE
	  SYNTAX EkiOnOff
	  MAX-ACCESS read-only
	  STATUS current
	  DESCRIPTION
        "
        Inventory Upload : <Condtype>
         INV_UPLOAD <Probcause> other (1)
        <Alarmtype> other (1) <Polarity>
        (2)
        "
	  ::= { pmopm8AlmsynthAlm2 2 }



pmopm8AlmConfTableSave OBJECT-TYPE
	  SYNTAX EkiOnOff
	  MAX-ACCESS read-only
	  STATUS current
	  DESCRIPTION
        "
        PM Configuration Save : <Condtype>
        CONF_TABLE_SAVE <Probcause> other
        (1) <Alarmtype> other (1) <Polarity>
        (2)
        "
	  ::= { pmopm8AlmsynthAlm2 1 }



--- *********************************************************
---     TABLE for the pmopm8AlmsynthAlmPort articles
--- *********************************************************

pmopm8AlmsynthAlmPortTable OBJECT-TYPE
	SYNTAX  SEQUENCE OF Pmopm8AlmsynthAlmPortEntry
	MAX-ACCESS not-accessible
	STATUS current
	DESCRIPTION
        "
        List of pmopm8AlmsynthAlmPort
         Article
        "
	::= { pmopm8AlmClientCrit 8 }


pmopm8AlmsynthAlmPortEntry OBJECT-TYPE
	SYNTAX Pmopm8AlmsynthAlmPortEntry
	MAX-ACCESS not-accessible
	STATUS current
	DESCRIPTION
        "
        Row definition for the pmopm8AlmsynthAlmPort
        table
        "
	INDEX   { pmopm8AlmsynthAlmPortIndex }
	::= { pmopm8AlmsynthAlmPortTable 1 }


Pmopm8AlmsynthAlmPortEntry ::=
	SEQUENCE {
	pmopm8AlmsynthAlmPortIndex
		INTEGER,
	pmopm8AlmSpectrumInvalidDataPortn
		EkiOnOff,
	pmopm8AlmSpectrumOosPortn
		EkiOnOff,
	pmopm8AlmSpectrumAbsentPortn
		EkiOnOff
	}


pmopm8AlmsynthAlmPortIndex OBJECT-TYPE
	SYNTAX  INTEGER(0..128)
	MAX-ACCESS  read-only
	STATUS current
	DESCRIPTION
        "
        Index definition for the pmopm8AlmsynthAlmPort
        table
        "
	::= { pmopm8AlmsynthAlmPortEntry 1 }


pmopm8AlmSpectrumInvalidDataPortn OBJECT-TYPE
	SYNTAX  EkiOnOff
	MAX-ACCESS read-only
	STATUS current
	DESCRIPTION
        "
        Spectrum Data Invalid :This OID
        indicates the data retreived by
        the OPM are invalid. Check the
         input power of the Spectrum port
        Is lower than 8.5dBm.<Help> This
        alarm indicates the data retreived
        by the OPM are invalid. Check the
        input power of the Spectrum port
        Is lower than 8.5dBm. <Condtype>
        SPECTRUM_INVALID_DATA_1 <Probcause>
        inputOutputDeviceError(24) <Alarmtype>
        equipmentAlarm (5) <Polarity> (2)
        "
	::= { pmopm8AlmsynthAlmPortEntry 4 }


pmopm8AlmSpectrumOosPortn OBJECT-TYPE
	SYNTAX  EkiOnOff
	MAX-ACCESS read-only
	STATUS current
	DESCRIPTION
        "
        Spectrum In Service :This OID
         indicates that the Optical Power
        Monitoring is In Service or Out
        of Service <Help> This status indicates
        if the Optical Power Monitoring
        is in service <Condtype> SPECTRUM_OOS_1
        <Probcause> informationalStatus(1000)
        <Alarmtype> other (1) <Polarity>
        (2)
        "
	::= { pmopm8AlmsynthAlmPortEntry 3 }


pmopm8AlmSpectrumAbsentPortn OBJECT-TYPE
	SYNTAX  EkiOnOff
	MAX-ACCESS read-only
	STATUS current
	DESCRIPTION
        "
        Spectrum Absent :This OID indicates
        there is no spectrum detected on
        the Optical Power Monitoring input<Help>
        This alarm indicates there is no
        spectrum detected on the Optical
        Power Monitoring input <Condtype>
        SPECTRUM_ABSENT_1 <Probcause> inputOutputDeviceError
        (24) <Alarmtype> equipmentAlarm
        (5) <Polarity> (2)
        "
	::= { pmopm8AlmsynthAlmPortEntry 2 }


--- *********************************************************
---     TABLE for the pmopm8Almchannel1Port articles
--- *********************************************************

pmopm8Almchannel1PortTable OBJECT-TYPE
	SYNTAX  SEQUENCE OF Pmopm8Almchannel1PortEntry
	MAX-ACCESS not-accessible
	STATUS current
	DESCRIPTION
        "
        List of pmopm8Almchannel1Port
         Article
        "
	::= { pmopm8AlmClientCrit 16 }


pmopm8Almchannel1PortEntry OBJECT-TYPE
	SYNTAX Pmopm8Almchannel1PortEntry
	MAX-ACCESS not-accessible
	STATUS current
	DESCRIPTION
        "
        Row definition for the pmopm8Almchannel1Port
        table
        "
	INDEX   { pmopm8Almchannel1PortIndex }
	::= { pmopm8Almchannel1PortTable 1 }


Pmopm8Almchannel1PortEntry ::=
	SEQUENCE {
	pmopm8Almchannel1PortIndex
		INTEGER,
	pmopm8AlmChannel1OosPortn
		EkiOnOff,
	pmopm8AlmChannel1PowerHighPortn
		EkiOnOff,
	pmopm8AlmChannel1PowerLowPortn
		EkiOnOff,
	pmopm8AlmChannel1BalancedPortn
		EkiOnOff,
	pmopm8AlmChannel1MismatchPortn
		EkiOnOff,
	pmopm8AlmChannel1AbsentPortn
		EkiOnOff
	}


pmopm8Almchannel1PortIndex OBJECT-TYPE
	SYNTAX  INTEGER(0..128)
	MAX-ACCESS  read-only
	STATUS current
	DESCRIPTION
        "
        Index definition for the pmopm8Almchannel1Port
        table
        "
	::= { pmopm8Almchannel1PortEntry 1 }


pmopm8AlmChannel1OosPortn OBJECT-TYPE
	SYNTAX  EkiOnOff
	MAX-ACCESS read-only
	STATUS current
	DESCRIPTION
        "
        In Service :This OID indicates
        that the channel is out of service
         <Help> This alarm indicates that
        the channel is in service <Condtype>
        CHANNEL1_OOS_1 <Probcause> informationalStatus(1000)
        <Alarmtype> other (1) <Polarity>
        (2)
        "
	::= { pmopm8Almchannel1PortEntry 7 }


pmopm8AlmChannel1PowerHighPortn OBJECT-TYPE
	SYNTAX  EkiOnOff
	MAX-ACCESS read-only
	STATUS current
	DESCRIPTION
        "
        Power High :This OID indicates
        that the power of the channel is
        higher than the configured threshold<Help>
        This alarm indicates that the power
        of the channel is higher than the
        configured threshold <Condtype>
        CHANNEL1_POWER_HIGH_1 <Probcause>
        degradedSignal (13) <Alarmtype>
        equipmentAlarm <Polarity> (2)
        "
	::= { pmopm8Almchannel1PortEntry 6 }


pmopm8AlmChannel1PowerLowPortn OBJECT-TYPE
	SYNTAX  EkiOnOff
	MAX-ACCESS read-only
	STATUS current
	DESCRIPTION
        "
        Power Low :This OID indicates
         that the power of the channel
         is lower than the configured threshold<Help>
        This alarm indicates that the power
        of the channel is lower than the
        configured threshold <Condtype>
        CHANNEL1_POWER_LOW_1 <Probcause>
        degradedSignal (13) <Alarmtype>
        equipmentAlarm <Polarity> (2)
        "
	::= { pmopm8Almchannel1PortEntry 5 }


pmopm8AlmChannel1BalancedPortn OBJECT-TYPE
	SYNTAX  EkiOnOff
	MAX-ACCESS read-only
	STATUS current
	DESCRIPTION
        "
        Balanced :This OID indicates that
        an in service channel is balanced
        by the Ekinops auto turn up application<Help>
        This status indicates that an in
        service channel is balanced by
         the Ekinops auto turn up application
        <Condtype> CHANNEL1_BALANCED_1
         <Probcause> informationalStatus(1000)
        <Alarmtype> other (1) <Polarity>
        (2)
        "
	::= { pmopm8Almchannel1PortEntry 4 }


pmopm8AlmChannel1MismatchPortn OBJECT-TYPE
	SYNTAX  EkiOnOff
	MAX-ACCESS read-only
	STATUS current
	DESCRIPTION
        "
        Mismatch :This OID indicates that
        an out of service channel is detected
        on the Optical Power Monitoring
        input<Help> This alarm indicates
        that an out of service channel
         is detected on the Optical Power
        Monitoring input <Condtype> CHANNEL1_MISMATCH_1
        <Probcause> unexpectedInformation
        (75) <Alarmtype> equipmentAlarm
        <Polarity> (2)
        "
	::= { pmopm8Almchannel1PortEntry 3 }


pmopm8AlmChannel1AbsentPortn OBJECT-TYPE
	SYNTAX  EkiOnOff
	MAX-ACCESS read-only
	STATUS current
	DESCRIPTION
        "
        Absent :This OID indicates that
        an in service channel is absent
        on the Optical Power Monitoring
        input<Help> This alarm indicates
        that an in service channel is absent
        on the Optical Power Monitoring
        input <Condtype> CHANNEL1_ABSENT_1
        <Probcause> informationMissing
         (65) <Alarmtype> equipmentAlarm
        (5) <Polarity> (2)
        "
	::= { pmopm8Almchannel1PortEntry 2 }


--- *********************************************************
---     TABLE for the pmopm8Almchannel2Port articles
--- *********************************************************

pmopm8Almchannel2PortTable OBJECT-TYPE
	SYNTAX  SEQUENCE OF Pmopm8Almchannel2PortEntry
	MAX-ACCESS not-accessible
	STATUS current
	DESCRIPTION
        "
        List of pmopm8Almchannel2Port
         Article
        "
	::= { pmopm8AlmClientCrit 24 }


pmopm8Almchannel2PortEntry OBJECT-TYPE
	SYNTAX Pmopm8Almchannel2PortEntry
	MAX-ACCESS not-accessible
	STATUS current
	DESCRIPTION
        "
        Row definition for the pmopm8Almchannel2Port
        table
        "
	INDEX   { pmopm8Almchannel2PortIndex }
	::= { pmopm8Almchannel2PortTable 1 }


Pmopm8Almchannel2PortEntry ::=
	SEQUENCE {
	pmopm8Almchannel2PortIndex
		INTEGER,
	pmopm8AlmChannel2OosPortn
		EkiOnOff,
	pmopm8AlmChannel2PowerHighPortn
		EkiOnOff,
	pmopm8AlmChannel2PowerLowPortn
		EkiOnOff,
	pmopm8AlmChannel2BalancedPortn
		EkiOnOff,
	pmopm8AlmChannel2MismatchPortn
		EkiOnOff,
	pmopm8AlmChannel2AbsentPortn
		EkiOnOff
	}


pmopm8Almchannel2PortIndex OBJECT-TYPE
	SYNTAX  INTEGER(0..128)
	MAX-ACCESS  read-only
	STATUS current
	DESCRIPTION
        "
        Index definition for the pmopm8Almchannel2Port
        table
        "
	::= { pmopm8Almchannel2PortEntry 1 }


pmopm8AlmChannel2OosPortn OBJECT-TYPE
	SYNTAX  EkiOnOff
	MAX-ACCESS read-only
	STATUS current
	DESCRIPTION
        "
        Channel Out Of Service 2 :This
        OID indicates that the channel
         is out of service  <Help> This
        alarm indicates that the channel
        is in service <Condtype> CHANNEL2_OOS_1
        <Probcause> informationalStatus(1000)
        <Alarmtype> other (1) <Polarity>
        (2)
        "
	::= { pmopm8Almchannel2PortEntry 7 }


pmopm8AlmChannel2PowerHighPortn OBJECT-TYPE
	SYNTAX  EkiOnOff
	MAX-ACCESS read-only
	STATUS current
	DESCRIPTION
        "
        Channel Power High 2 :This OID
        indicates that the power of the
        channel is higher than the configured
        threshold<Help> This alarm indicates
        that the power of the channel is
        higher than the configured threshold
        <Condtype> CHANNEL2_POWER_HIGH_1
        <Probcause> degradedSignal (13)
        <Alarmtype> equipmentAlarm <Polarity>
        (2)
        "
	::= { pmopm8Almchannel2PortEntry 6 }


pmopm8AlmChannel2PowerLowPortn OBJECT-TYPE
	SYNTAX  EkiOnOff
	MAX-ACCESS read-only
	STATUS current
	DESCRIPTION
        "
        Channel Power Low 2 :This OID
         indicates that the power of the
        channel is lower than the configured
        threshold<Help> This alarm indicates
        that the power of the channel is
        lower than the configured threshold
        <Condtype> CHANNEL2_POWER_LOW_1
        <Probcause> degradedSignal (13)
        <Alarmtype> equipmentAlarm <Polarity>
        (2)
        "
	::= { pmopm8Almchannel2PortEntry 5 }


pmopm8AlmChannel2BalancedPortn OBJECT-TYPE
	SYNTAX  EkiOnOff
	MAX-ACCESS read-only
	STATUS current
	DESCRIPTION
        "
        Channel Balanced 2 :This OID indicates
        that an in service channel is balanced
        by the Ekinops auto turn up application<Help>
        This status indicates that an in
        service channel is balanced by
         the Ekinops auto turn up application
        <Condtype> CHANNEL2_BALANCED_1
         <Probcause> informationalStatus(1000)
        <Alarmtype> other (1) <Polarity>
        (2)
        "
	::= { pmopm8Almchannel2PortEntry 4 }


pmopm8AlmChannel2MismatchPortn OBJECT-TYPE
	SYNTAX  EkiOnOff
	MAX-ACCESS read-only
	STATUS current
	DESCRIPTION
        "
        Channel Mismatch 2 :This OID indicates
        that an out of service channel
         is detected on the Optical Power
        Monitoring input<Help> This alarm
        indicates that an out of service
        channel is detected on the Optical
        Power Monitoring input <Condtype>
        CHANNEL2_MISMATCH_1 <Probcause>
        unexpectedInformation (75) <Alarmtype>
        equipmentAlarm <Polarity> (2)
        "
	::= { pmopm8Almchannel2PortEntry 3 }


pmopm8AlmChannel2AbsentPortn OBJECT-TYPE
	SYNTAX  EkiOnOff
	MAX-ACCESS read-only
	STATUS current
	DESCRIPTION
        "
        Channel Absent 2 :This OID indicates
        that an in service channel is absent
        on the Optical Power Monitoring
        input<Help> This alarm indicates
        that an in service channel is absent
        on the Optical Power Monitoring
        input <Condtype> CHANNEL2_ABSENT_1
        <Probcause> informationMissing
         (65) <Alarmtype> equipmentAlarm
        (5) <Polarity> (2)
        "
	::= { pmopm8Almchannel2PortEntry 2 }


--- *********************************************************
---     TABLE for the pmopm8Almchannel3Port articles
--- *********************************************************

pmopm8Almchannel3PortTable OBJECT-TYPE
	SYNTAX  SEQUENCE OF Pmopm8Almchannel3PortEntry
	MAX-ACCESS not-accessible
	STATUS current
	DESCRIPTION
        "
        List of pmopm8Almchannel3Port
         Article
        "
	::= { pmopm8AlmClientCrit 32 }


pmopm8Almchannel3PortEntry OBJECT-TYPE
	SYNTAX Pmopm8Almchannel3PortEntry
	MAX-ACCESS not-accessible
	STATUS current
	DESCRIPTION
        "
        Row definition for the pmopm8Almchannel3Port
        table
        "
	INDEX   { pmopm8Almchannel3PortIndex }
	::= { pmopm8Almchannel3PortTable 1 }


Pmopm8Almchannel3PortEntry ::=
	SEQUENCE {
	pmopm8Almchannel3PortIndex
		INTEGER,
	pmopm8AlmChannel3OosPortn
		EkiOnOff,
	pmopm8AlmChannel3PowerHighPortn
		EkiOnOff,
	pmopm8AlmChannel3PowerLowPortn
		EkiOnOff,
	pmopm8AlmChannel3BalancedPortn
		EkiOnOff,
	pmopm8AlmChannel3MismatchPortn
		EkiOnOff,
	pmopm8AlmChannel3AbsentPortn
		EkiOnOff
	}


pmopm8Almchannel3PortIndex OBJECT-TYPE
	SYNTAX  INTEGER(0..128)
	MAX-ACCESS  read-only
	STATUS current
	DESCRIPTION
        "
        Index definition for the pmopm8Almchannel3Port
        table
        "
	::= { pmopm8Almchannel3PortEntry 1 }


pmopm8AlmChannel3OosPortn OBJECT-TYPE
	SYNTAX  EkiOnOff
	MAX-ACCESS read-only
	STATUS current
	DESCRIPTION
        "
        Channel Out Of Service 3 :This
        OID indicates that the channel
         is out of service  <Help> This
        alarm indicates that the channel
        is in service <Condtype> CHANNEL3_OOS_1
        <Probcause> informationalStatus(1000)
        <Alarmtype> other (1) <Polarity>
        (2)
        "
	::= { pmopm8Almchannel3PortEntry 7 }


pmopm8AlmChannel3PowerHighPortn OBJECT-TYPE
	SYNTAX  EkiOnOff
	MAX-ACCESS read-only
	STATUS current
	DESCRIPTION
        "
        Channel Power High 3 :This OID
        indicates that the power of the
        channel is higher than the configured
        threshold<Help> This alarm indicates
        that the power of the channel is
        higher than the configured threshold
        <Condtype> CHANNEL3_POWER_HIGH_1
        <Probcause> degradedSignal (13)
        <Alarmtype> equipmentAlarm <Polarity>
        (2)
        "
	::= { pmopm8Almchannel3PortEntry 6 }


pmopm8AlmChannel3PowerLowPortn OBJECT-TYPE
	SYNTAX  EkiOnOff
	MAX-ACCESS read-only
	STATUS current
	DESCRIPTION
        "
        Channel Power Low 3 :This OID
         indicates that the power of the
        channel is lower than the configured
        threshold<Help> This alarm indicates
        that the power of the channel is
        lower than the configured threshold
        <Condtype> CHANNEL3_POWER_LOW_1
        <Probcause> degradedSignal (13)
        <Alarmtype> equipmentAlarm <Polarity>
        (2)
        "
	::= { pmopm8Almchannel3PortEntry 5 }


pmopm8AlmChannel3BalancedPortn OBJECT-TYPE
	SYNTAX  EkiOnOff
	MAX-ACCESS read-only
	STATUS current
	DESCRIPTION
        "
        Channel Balanced 3 :This OID indicates
        that an in service channel is balanced
        by the Ekinops auto turn up application<Help>
        This status indicates that an in
        service channel is balanced by
         the Ekinops auto turn up application
        <Condtype> CHANNEL3_BALANCED_1
         <Probcause> informationalStatus(1000)
        <Alarmtype> other (1) <Polarity>
        (2)
        "
	::= { pmopm8Almchannel3PortEntry 4 }


pmopm8AlmChannel3MismatchPortn OBJECT-TYPE
	SYNTAX  EkiOnOff
	MAX-ACCESS read-only
	STATUS current
	DESCRIPTION
        "
        Channel Mismatch 3 :This OID indicates
        that an out of service channel
         is detected on the Optical Power
        Monitoring input<Help> This alarm
        indicates that an out of service
        channel is detected on the Optical
        Power Monitoring input <Condtype>
        CHANNEL3_MISMATCH_1 <Probcause>
        unexpectedInformation (75) <Alarmtype>
        equipmentAlarm <Polarity> (2)
        "
	::= { pmopm8Almchannel3PortEntry 3 }


pmopm8AlmChannel3AbsentPortn OBJECT-TYPE
	SYNTAX  EkiOnOff
	MAX-ACCESS read-only
	STATUS current
	DESCRIPTION
        "
        Channel Absent 3 :This OID indicates
        that an in service channel is absent
        on the Optical Power Monitoring
        input<Help> This alarm indicates
        that an in service channel is absent
        on the Optical Power Monitoring
        input <Condtype> CHANNEL3_ABSENT_1
        <Probcause> informationMissing
         (65) <Alarmtype> equipmentAlarm
        (5) <Polarity> (2)
        "
	::= { pmopm8Almchannel3PortEntry 2 }


--- *********************************************************
---     TABLE for the pmopm8Almchannel4Port articles
--- *********************************************************

pmopm8Almchannel4PortTable OBJECT-TYPE
	SYNTAX  SEQUENCE OF Pmopm8Almchannel4PortEntry
	MAX-ACCESS not-accessible
	STATUS current
	DESCRIPTION
        "
        List of pmopm8Almchannel4Port
         Article
        "
	::= { pmopm8AlmClientCrit 40 }


pmopm8Almchannel4PortEntry OBJECT-TYPE
	SYNTAX Pmopm8Almchannel4PortEntry
	MAX-ACCESS not-accessible
	STATUS current
	DESCRIPTION
        "
        Row definition for the pmopm8Almchannel4Port
        table
        "
	INDEX   { pmopm8Almchannel4PortIndex }
	::= { pmopm8Almchannel4PortTable 1 }


Pmopm8Almchannel4PortEntry ::=
	SEQUENCE {
	pmopm8Almchannel4PortIndex
		INTEGER,
	pmopm8AlmChannel4OosPortn
		EkiOnOff,
	pmopm8AlmChannel4PowerHighPortn
		EkiOnOff,
	pmopm8AlmChannel4PowerLowPortn
		EkiOnOff,
	pmopm8AlmChannel4BalancedPortn
		EkiOnOff,
	pmopm8AlmChannel4MismatchPortn
		EkiOnOff,
	pmopm8AlmChannel4AbsentPortn
		EkiOnOff
	}


pmopm8Almchannel4PortIndex OBJECT-TYPE
	SYNTAX  INTEGER(0..128)
	MAX-ACCESS  read-only
	STATUS current
	DESCRIPTION
        "
        Index definition for the pmopm8Almchannel4Port
        table
        "
	::= { pmopm8Almchannel4PortEntry 1 }


pmopm8AlmChannel4OosPortn OBJECT-TYPE
	SYNTAX  EkiOnOff
	MAX-ACCESS read-only
	STATUS current
	DESCRIPTION
        "
        Channel Out Of Service 4 :This
        OID indicates that the channel
         is out of service  <Help> This
        alarm indicates that the channel
        is in service <Condtype> CHANNEL4_OOS_1
        <Probcause> informationalStatus(1000)
        <Alarmtype> other (1) <Polarity>
        (2)
        "
	::= { pmopm8Almchannel4PortEntry 7 }


pmopm8AlmChannel4PowerHighPortn OBJECT-TYPE
	SYNTAX  EkiOnOff
	MAX-ACCESS read-only
	STATUS current
	DESCRIPTION
        "
        Channel Power High 4 :This OID
        indicates that the power of the
        channel is higher than the configured
        threshold<Help> This alarm indicates
        that the power of the channel is
        higher than the configured threshold
        <Condtype> CHANNEL4_POWER_HIGH_1
        <Probcause> degradedSignal (13)
        <Alarmtype> equipmentAlarm <Polarity>
        (2)
        "
	::= { pmopm8Almchannel4PortEntry 6 }


pmopm8AlmChannel4PowerLowPortn OBJECT-TYPE
	SYNTAX  EkiOnOff
	MAX-ACCESS read-only
	STATUS current
	DESCRIPTION
        "
        Channel Power Low 4 :This OID
         indicates that the power of the
        channel is lower than the configured
        threshold<Help> This alarm indicates
        that the power of the channel is
        lower than the configured threshold
        <Condtype> CHANNEL4_POWER_LOW_1
        <Probcause> degradedSignal (13)
        <Alarmtype> equipmentAlarm <Polarity>
        (2)
        "
	::= { pmopm8Almchannel4PortEntry 5 }


pmopm8AlmChannel4BalancedPortn OBJECT-TYPE
	SYNTAX  EkiOnOff
	MAX-ACCESS read-only
	STATUS current
	DESCRIPTION
        "
        Channel Balanced 4 :This OID indicates
        that an in service channel is balanced
        by the Ekinops auto turn up application<Help>
        This status indicates that an in
        service channel is balanced by
         the Ekinops auto turn up application
        <Condtype> CHANNEL4_BALANCED_1
         <Probcause> informationalStatus(1000)
        <Alarmtype> other (1) <Polarity>
        (2)
        "
	::= { pmopm8Almchannel4PortEntry 4 }


pmopm8AlmChannel4MismatchPortn OBJECT-TYPE
	SYNTAX  EkiOnOff
	MAX-ACCESS read-only
	STATUS current
	DESCRIPTION
        "
        Channel Mismatch 4 :This OID indicates
        that an out of service channel
         is detected on the Optical Power
        Monitoring input<Help> This alarm
        indicates that an out of service
        channel is detected on the Optical
        Power Monitoring input <Condtype>
        CHANNEL4_MISMATCH_1 <Probcause>
        unexpectedInformation (75) <Alarmtype>
        equipmentAlarm <Polarity> (2)
        "
	::= { pmopm8Almchannel4PortEntry 3 }


pmopm8AlmChannel4AbsentPortn OBJECT-TYPE
	SYNTAX  EkiOnOff
	MAX-ACCESS read-only
	STATUS current
	DESCRIPTION
        "
        Channel Absent 4 :This OID indicates
        that an in service channel is absent
        on the Optical Power Monitoring
        input<Help> This alarm indicates
        that an in service channel is absent
        on the Optical Power Monitoring
        input <Condtype> CHANNEL4_ABSENT_1
        <Probcause> informationMissing
         (65) <Alarmtype> equipmentAlarm
        (5) <Polarity> (2)
        "
	::= { pmopm8Almchannel4PortEntry 2 }


--- *********************************************************
---     TABLE for the pmopm8Almchannel5Port articles
--- *********************************************************

pmopm8Almchannel5PortTable OBJECT-TYPE
	SYNTAX  SEQUENCE OF Pmopm8Almchannel5PortEntry
	MAX-ACCESS not-accessible
	STATUS current
	DESCRIPTION
        "
        List of pmopm8Almchannel5Port
         Article
        "
	::= { pmopm8AlmClientCrit 48 }


pmopm8Almchannel5PortEntry OBJECT-TYPE
	SYNTAX Pmopm8Almchannel5PortEntry
	MAX-ACCESS not-accessible
	STATUS current
	DESCRIPTION
        "
        Row definition for the pmopm8Almchannel5Port
        table
        "
	INDEX   { pmopm8Almchannel5PortIndex }
	::= { pmopm8Almchannel5PortTable 1 }


Pmopm8Almchannel5PortEntry ::=
	SEQUENCE {
	pmopm8Almchannel5PortIndex
		INTEGER,
	pmopm8AlmChannel5OosPortn
		EkiOnOff,
	pmopm8AlmChannel5PowerHighPortn
		EkiOnOff,
	pmopm8AlmChannel5PowerLowPortn
		EkiOnOff,
	pmopm8AlmChannel5BalancedPortn
		EkiOnOff,
	pmopm8AlmChannel5MismatchPortn
		EkiOnOff,
	pmopm8AlmChannel5AbsentPortn
		EkiOnOff
	}


pmopm8Almchannel5PortIndex OBJECT-TYPE
	SYNTAX  INTEGER(0..128)
	MAX-ACCESS  read-only
	STATUS current
	DESCRIPTION
        "
        Index definition for the pmopm8Almchannel5Port
        table
        "
	::= { pmopm8Almchannel5PortEntry 1 }


pmopm8AlmChannel5OosPortn OBJECT-TYPE
	SYNTAX  EkiOnOff
	MAX-ACCESS read-only
	STATUS current
	DESCRIPTION
        "
        Channel Out Of Service 5 :This
        OID indicates that the channel
         is out of service  <Help> This
        alarm indicates that the channel
        is in service <Condtype> CHANNEL5_OOS_1
        <Probcause> informationalStatus(1000)
        <Alarmtype> other (1) <Polarity>
        (2)
        "
	::= { pmopm8Almchannel5PortEntry 7 }


pmopm8AlmChannel5PowerHighPortn OBJECT-TYPE
	SYNTAX  EkiOnOff
	MAX-ACCESS read-only
	STATUS current
	DESCRIPTION
        "
        Channel Power High 5 :This OID
        indicates that the power of the
        channel is higher than the configured
        threshold<Help> This alarm indicates
        that the power of the channel is
        higher than the configured threshold
        <Condtype> CHANNEL5_POWER_HIGH_1
        <Probcause> degradedSignal (13)
        <Alarmtype> equipmentAlarm <Polarity>
        (2)
        "
	::= { pmopm8Almchannel5PortEntry 6 }


pmopm8AlmChannel5PowerLowPortn OBJECT-TYPE
	SYNTAX  EkiOnOff
	MAX-ACCESS read-only
	STATUS current
	DESCRIPTION
        "
        Channel Power Low 5 :This OID
         indicates that the power of the
        channel is lower than the configured
        threshold<Help> This alarm indicates
        that the power of the channel is
        lower than the configured threshold
        <Condtype> CHANNEL5_POWER_LOW_1
        <Probcause> degradedSignal (13)
        <Alarmtype> equipmentAlarm <Polarity>
        (2)
        "
	::= { pmopm8Almchannel5PortEntry 5 }


pmopm8AlmChannel5BalancedPortn OBJECT-TYPE
	SYNTAX  EkiOnOff
	MAX-ACCESS read-only
	STATUS current
	DESCRIPTION
        "
        Channel Balanced 5 :This OID indicates
        that an in service channel is balanced
        by the Ekinops auto turn up application<Help>
        This status indicates that an in
        service channel is balanced by
         the Ekinops auto turn up application
        <Condtype> CHANNEL5_BALANCED_1
         <Probcause> informationalStatus(1000)
        <Alarmtype> other (1) <Polarity>
        (2)
        "
	::= { pmopm8Almchannel5PortEntry 4 }


pmopm8AlmChannel5MismatchPortn OBJECT-TYPE
	SYNTAX  EkiOnOff
	MAX-ACCESS read-only
	STATUS current
	DESCRIPTION
        "
        Channel Mismatch 5 :This OID indicates
        that an out of service channel
         is detected on the Optical Power
        Monitoring input<Help> This alarm
        indicates that an out of service
        channel is detected on the Optical
        Power Monitoring input <Condtype>
        CHANNEL5_MISMATCH_1 <Probcause>
        unexpectedInformation (75) <Alarmtype>
        equipmentAlarm <Polarity> (2)
        "
	::= { pmopm8Almchannel5PortEntry 3 }


pmopm8AlmChannel5AbsentPortn OBJECT-TYPE
	SYNTAX  EkiOnOff
	MAX-ACCESS read-only
	STATUS current
	DESCRIPTION
        "
        Channel Absent 5 :This OID indicates
        that an in service channel is absent
        on the Optical Power Monitoring
        input<Help> This alarm indicates
        that an in service channel is absent
        on the Optical Power Monitoring
        input <Condtype> CHANNEL5_ABSENT_1
        <Probcause> informationMissing
         (65) <Alarmtype> equipmentAlarm
        (5) <Polarity> (2)
        "
	::= { pmopm8Almchannel5PortEntry 2 }


--- *********************************************************
---     TABLE for the pmopm8Almchannel6Port articles
--- *********************************************************

pmopm8Almchannel6PortTable OBJECT-TYPE
	SYNTAX  SEQUENCE OF Pmopm8Almchannel6PortEntry
	MAX-ACCESS not-accessible
	STATUS current
	DESCRIPTION
        "
        List of pmopm8Almchannel6Port
         Article
        "
	::= { pmopm8AlmClientCrit 56 }


pmopm8Almchannel6PortEntry OBJECT-TYPE
	SYNTAX Pmopm8Almchannel6PortEntry
	MAX-ACCESS not-accessible
	STATUS current
	DESCRIPTION
        "
        Row definition for the pmopm8Almchannel6Port
        table
        "
	INDEX   { pmopm8Almchannel6PortIndex }
	::= { pmopm8Almchannel6PortTable 1 }


Pmopm8Almchannel6PortEntry ::=
	SEQUENCE {
	pmopm8Almchannel6PortIndex
		INTEGER,
	pmopm8AlmChannel6OosPortn
		EkiOnOff,
	pmopm8AlmChannel6PowerHighPortn
		EkiOnOff,
	pmopm8AlmChannel6PowerLowPortn
		EkiOnOff,
	pmopm8AlmChannel6BalancedPortn
		EkiOnOff,
	pmopm8AlmChannel6MismatchPortn
		EkiOnOff,
	pmopm8AlmChannel6AbsentPortn
		EkiOnOff
	}


pmopm8Almchannel6PortIndex OBJECT-TYPE
	SYNTAX  INTEGER(0..128)
	MAX-ACCESS  read-only
	STATUS current
	DESCRIPTION
        "
        Index definition for the pmopm8Almchannel6Port
        table
        "
	::= { pmopm8Almchannel6PortEntry 1 }


pmopm8AlmChannel6OosPortn OBJECT-TYPE
	SYNTAX  EkiOnOff
	MAX-ACCESS read-only
	STATUS current
	DESCRIPTION
        "
        Channel Out Of Service 6 :This
        OID indicates that the channel
         is out of service  <Help> This
        alarm indicates that the channel
        is in service <Condtype> CHANNEL6_OOS_1
        <Probcause> informationalStatus(1000)
        <Alarmtype> other (1) <Polarity>
        (2)
        "
	::= { pmopm8Almchannel6PortEntry 7 }


pmopm8AlmChannel6PowerHighPortn OBJECT-TYPE
	SYNTAX  EkiOnOff
	MAX-ACCESS read-only
	STATUS current
	DESCRIPTION
        "
        Channel Power High 6 :This OID
        indicates that the power of the
        channel is higher than the configured
        threshold<Help> This alarm indicates
        that the power of the channel is
        higher than the configured threshold
        <Condtype> CHANNEL6_POWER_HIGH_1
        <Probcause> degradedSignal (13)
        <Alarmtype> equipmentAlarm <Polarity>
        (2)
        "
	::= { pmopm8Almchannel6PortEntry 6 }


pmopm8AlmChannel6PowerLowPortn OBJECT-TYPE
	SYNTAX  EkiOnOff
	MAX-ACCESS read-only
	STATUS current
	DESCRIPTION
        "
        Channel Power Low 6 :This OID
         indicates that the power of the
        channel is lower than the configured
        threshold<Help> This alarm indicates
        that the power of the channel is
        lower than the configured threshold
        <Condtype> CHANNEL6_POWER_LOW_1
        <Probcause> degradedSignal (13)
        <Alarmtype> equipmentAlarm <Polarity>
        (2)
        "
	::= { pmopm8Almchannel6PortEntry 5 }


pmopm8AlmChannel6BalancedPortn OBJECT-TYPE
	SYNTAX  EkiOnOff
	MAX-ACCESS read-only
	STATUS current
	DESCRIPTION
        "
        Channel Balanced 6 :This OID indicates
        that an in service channel is balanced
        by the Ekinops auto turn up application<Help>
        This status indicates that an in
        service channel is balanced by
         the Ekinops auto turn up application
        <Condtype> CHANNEL6_BALANCED_1
         <Probcause> informationalStatus(1000)
        <Alarmtype> other (1) <Polarity>
        (2)
        "
	::= { pmopm8Almchannel6PortEntry 4 }


pmopm8AlmChannel6MismatchPortn OBJECT-TYPE
	SYNTAX  EkiOnOff
	MAX-ACCESS read-only
	STATUS current
	DESCRIPTION
        "
        Channel Mismatch 6 :This OID indicates
        that an out of service channel
         is detected on the Optical Power
        Monitoring input<Help> This alarm
        indicates that an out of service
        channel is detected on the Optical
        Power Monitoring input <Condtype>
        CHANNEL6_MISMATCH_1 <Probcause>
        unexpectedInformation (75) <Alarmtype>
        equipmentAlarm <Polarity> (2)
        "
	::= { pmopm8Almchannel6PortEntry 3 }


pmopm8AlmChannel6AbsentPortn OBJECT-TYPE
	SYNTAX  EkiOnOff
	MAX-ACCESS read-only
	STATUS current
	DESCRIPTION
        "
        Channel Absent 6 :This OID indicates
        that an in service channel is absent
        on the Optical Power Monitoring
        input<Help> This alarm indicates
        that an in service channel is absent
        on the Optical Power Monitoring
        input <Condtype> CHANNEL6_ABSENT_1
        <Probcause> informationMissing
         (65) <Alarmtype> equipmentAlarm
        (5) <Polarity> (2)
        "
	::= { pmopm8Almchannel6PortEntry 2 }


--- *********************************************************
---     TABLE for the pmopm8Almchannel7Port articles
--- *********************************************************

pmopm8Almchannel7PortTable OBJECT-TYPE
	SYNTAX  SEQUENCE OF Pmopm8Almchannel7PortEntry
	MAX-ACCESS not-accessible
	STATUS current
	DESCRIPTION
        "
        List of pmopm8Almchannel7Port
         Article
        "
	::= { pmopm8AlmClientCrit 64 }


pmopm8Almchannel7PortEntry OBJECT-TYPE
	SYNTAX Pmopm8Almchannel7PortEntry
	MAX-ACCESS not-accessible
	STATUS current
	DESCRIPTION
        "
        Row definition for the pmopm8Almchannel7Port
        table
        "
	INDEX   { pmopm8Almchannel7PortIndex }
	::= { pmopm8Almchannel7PortTable 1 }


Pmopm8Almchannel7PortEntry ::=
	SEQUENCE {
	pmopm8Almchannel7PortIndex
		INTEGER,
	pmopm8AlmChannel7OosPortn
		EkiOnOff,
	pmopm8AlmChannel7PowerHighPortn
		EkiOnOff,
	pmopm8AlmChannel7PowerLowPortn
		EkiOnOff,
	pmopm8AlmChannel7BalancedPortn
		EkiOnOff,
	pmopm8AlmChannel7MismatchPortn
		EkiOnOff,
	pmopm8AlmChannel7AbsentPortn
		EkiOnOff
	}


pmopm8Almchannel7PortIndex OBJECT-TYPE
	SYNTAX  INTEGER(0..128)
	MAX-ACCESS  read-only
	STATUS current
	DESCRIPTION
        "
        Index definition for the pmopm8Almchannel7Port
        table
        "
	::= { pmopm8Almchannel7PortEntry 1 }


pmopm8AlmChannel7OosPortn OBJECT-TYPE
	SYNTAX  EkiOnOff
	MAX-ACCESS read-only
	STATUS current
	DESCRIPTION
        "
        Channel Out Of Service 7 :This
        OID indicates that the channel
         is out of service  <Help> This
        alarm indicates that the channel
        is in service <Condtype> CHANNEL7_OOS_1
        <Probcause> informationalStatus(1000)
        <Alarmtype> other (1) <Polarity>
        (2)
        "
	::= { pmopm8Almchannel7PortEntry 7 }


pmopm8AlmChannel7PowerHighPortn OBJECT-TYPE
	SYNTAX  EkiOnOff
	MAX-ACCESS read-only
	STATUS current
	DESCRIPTION
        "
        Channel Power High 7 :This OID
        indicates that the power of the
        channel is higher than the configured
        threshold<Help> This alarm indicates
        that the power of the channel is
        higher than the configured threshold
        <Condtype> CHANNEL7_POWER_HIGH_1
        <Probcause> degradedSignal (13)
        <Alarmtype> equipmentAlarm <Polarity>
        (2)
        "
	::= { pmopm8Almchannel7PortEntry 6 }


pmopm8AlmChannel7PowerLowPortn OBJECT-TYPE
	SYNTAX  EkiOnOff
	MAX-ACCESS read-only
	STATUS current
	DESCRIPTION
        "
        Channel Power Low 7 :This OID
         indicates that the power of the
        channel is lower than the configured
        threshold<Help> This alarm indicates
        that the power of the channel is
        lower than the configured threshold
        <Condtype> CHANNEL7_POWER_LOW_1
        <Probcause> degradedSignal (13)
        <Alarmtype> equipmentAlarm <Polarity>
        (2)
        "
	::= { pmopm8Almchannel7PortEntry 5 }


pmopm8AlmChannel7BalancedPortn OBJECT-TYPE
	SYNTAX  EkiOnOff
	MAX-ACCESS read-only
	STATUS current
	DESCRIPTION
        "
        Channel Balanced 7 :This OID indicates
        that an in service channel is balanced
        by the Ekinops auto turn up application<Help>
        This status indicates that an in
        service channel is balanced by
         the Ekinops auto turn up application
        <Condtype> CHANNEL7_BALANCED_1
         <Probcause> informationalStatus(1000)
        <Alarmtype> other (1) <Polarity>
        (2)
        "
	::= { pmopm8Almchannel7PortEntry 4 }


pmopm8AlmChannel7MismatchPortn OBJECT-TYPE
	SYNTAX  EkiOnOff
	MAX-ACCESS read-only
	STATUS current
	DESCRIPTION
        "
        Channel Mismatch 7 :This OID indicates
        that an out of service channel
         is detected on the Optical Power
        Monitoring input<Help> This alarm
        indicates that an out of service
        channel is detected on the Optical
        Power Monitoring input <Condtype>
        CHANNEL7_MISMATCH_1 <Probcause>
        unexpectedInformation (75) <Alarmtype>
        equipmentAlarm <Polarity> (2)
        "
	::= { pmopm8Almchannel7PortEntry 3 }


pmopm8AlmChannel7AbsentPortn OBJECT-TYPE
	SYNTAX  EkiOnOff
	MAX-ACCESS read-only
	STATUS current
	DESCRIPTION
        "
        Channel Absent 7 :This OID indicates
        that an in service channel is absent
        on the Optical Power Monitoring
        input<Help> This alarm indicates
        that an in service channel is absent
        on the Optical Power Monitoring
        input <Condtype> CHANNEL7_ABSENT_1
        <Probcause> informationMissing
         (65) <Alarmtype> equipmentAlarm
        (5) <Polarity> (2)
        "
	::= { pmopm8Almchannel7PortEntry 2 }


--- *********************************************************
---     TABLE for the pmopm8Almchannel8Port articles
--- *********************************************************

pmopm8Almchannel8PortTable OBJECT-TYPE
	SYNTAX  SEQUENCE OF Pmopm8Almchannel8PortEntry
	MAX-ACCESS not-accessible
	STATUS current
	DESCRIPTION
        "
        List of pmopm8Almchannel8Port
         Article
        "
	::= { pmopm8AlmClientCrit 72 }


pmopm8Almchannel8PortEntry OBJECT-TYPE
	SYNTAX Pmopm8Almchannel8PortEntry
	MAX-ACCESS not-accessible
	STATUS current
	DESCRIPTION
        "
        Row definition for the pmopm8Almchannel8Port
        table
        "
	INDEX   { pmopm8Almchannel8PortIndex }
	::= { pmopm8Almchannel8PortTable 1 }


Pmopm8Almchannel8PortEntry ::=
	SEQUENCE {
	pmopm8Almchannel8PortIndex
		INTEGER,
	pmopm8AlmChannel8OosPortn
		EkiOnOff,
	pmopm8AlmChannel8PowerHighPortn
		EkiOnOff,
	pmopm8AlmChannel8PowerLowPortn
		EkiOnOff,
	pmopm8AlmChannel8BalancedPortn
		EkiOnOff,
	pmopm8AlmChannel8MismatchPortn
		EkiOnOff,
	pmopm8AlmChannel8AbsentPortn
		EkiOnOff
	}


pmopm8Almchannel8PortIndex OBJECT-TYPE
	SYNTAX  INTEGER(0..128)
	MAX-ACCESS  read-only
	STATUS current
	DESCRIPTION
        "
        Index definition for the pmopm8Almchannel8Port
        table
        "
	::= { pmopm8Almchannel8PortEntry 1 }


pmopm8AlmChannel8OosPortn OBJECT-TYPE
	SYNTAX  EkiOnOff
	MAX-ACCESS read-only
	STATUS current
	DESCRIPTION
        "
        Channel Out Of Service 8 :This
        OID indicates that the channel
         is out of service  <Help> This
        alarm indicates that the channel
        is in service <Condtype> CHANNEL8_OOS_1
        <Probcause> informationalStatus(1000)
        <Alarmtype> other (1) <Polarity>
        (2)
        "
	::= { pmopm8Almchannel8PortEntry 7 }


pmopm8AlmChannel8PowerHighPortn OBJECT-TYPE
	SYNTAX  EkiOnOff
	MAX-ACCESS read-only
	STATUS current
	DESCRIPTION
        "
        Channel Power High 8 :This OID
        indicates that the power of the
        channel is higher than the configured
        threshold<Help> This alarm indicates
        that the power of the channel is
        higher than the configured threshold
        <Condtype> CHANNEL8_POWER_HIGH_1
        <Probcause> degradedSignal (13)
        <Alarmtype> equipmentAlarm <Polarity>
        (2)
        "
	::= { pmopm8Almchannel8PortEntry 6 }


pmopm8AlmChannel8PowerLowPortn OBJECT-TYPE
	SYNTAX  EkiOnOff
	MAX-ACCESS read-only
	STATUS current
	DESCRIPTION
        "
        Channel Power Low 8 :This OID
         indicates that the power of the
        channel is lower than the configured
        threshold<Help> This alarm indicates
        that the power of the channel is
        lower than the configured threshold
        <Condtype> CHANNEL8_POWER_LOW_1
        <Probcause> degradedSignal (13)
        <Alarmtype> equipmentAlarm <Polarity>
        (2)
        "
	::= { pmopm8Almchannel8PortEntry 5 }


pmopm8AlmChannel8BalancedPortn OBJECT-TYPE
	SYNTAX  EkiOnOff
	MAX-ACCESS read-only
	STATUS current
	DESCRIPTION
        "
        Channel Balanced 8 :This OID indicates
        that an in service channel is balanced
        by the Ekinops auto turn up application<Help>
        This status indicates that an in
        service channel is balanced by
         the Ekinops auto turn up application
        <Condtype> CHANNEL8_BALANCED_1
         <Probcause> informationalStatus(1000)
        <Alarmtype> other (1) <Polarity>
        (2)
        "
	::= { pmopm8Almchannel8PortEntry 4 }


pmopm8AlmChannel8MismatchPortn OBJECT-TYPE
	SYNTAX  EkiOnOff
	MAX-ACCESS read-only
	STATUS current
	DESCRIPTION
        "
        Channel Mismatch 8 :This OID indicates
        that an out of service channel
         is detected on the Optical Power
        Monitoring input<Help> This alarm
        indicates that an out of service
        channel is detected on the Optical
        Power Monitoring input <Condtype>
        CHANNEL8_MISMATCH_1 <Probcause>
        unexpectedInformation (75) <Alarmtype>
        equipmentAlarm <Polarity> (2)
        "
	::= { pmopm8Almchannel8PortEntry 3 }


pmopm8AlmChannel8AbsentPortn OBJECT-TYPE
	SYNTAX  EkiOnOff
	MAX-ACCESS read-only
	STATUS current
	DESCRIPTION
        "
        Channel Absent 8 :This OID indicates
        that an in service channel is absent
        on the Optical Power Monitoring
        input<Help> This alarm indicates
        that an in service channel is absent
        on the Optical Power Monitoring
        input <Condtype> CHANNEL8_ABSENT_1
        <Probcause> informationMissing
         (65) <Alarmtype> equipmentAlarm
        (5) <Polarity> (2)
        "
	::= { pmopm8Almchannel8PortEntry 2 }


--- *********************************************************
---     TABLE for the pmopm8Almchannel9Port articles
--- *********************************************************

pmopm8Almchannel9PortTable OBJECT-TYPE
	SYNTAX  SEQUENCE OF Pmopm8Almchannel9PortEntry
	MAX-ACCESS not-accessible
	STATUS current
	DESCRIPTION
        "
        List of pmopm8Almchannel9Port
         Article
        "
	::= { pmopm8AlmClientCrit 80 }


pmopm8Almchannel9PortEntry OBJECT-TYPE
	SYNTAX Pmopm8Almchannel9PortEntry
	MAX-ACCESS not-accessible
	STATUS current
	DESCRIPTION
        "
        Row definition for the pmopm8Almchannel9Port
        table
        "
	INDEX   { pmopm8Almchannel9PortIndex }
	::= { pmopm8Almchannel9PortTable 1 }


Pmopm8Almchannel9PortEntry ::=
	SEQUENCE {
	pmopm8Almchannel9PortIndex
		INTEGER,
	pmopm8AlmChannel9OosPortn
		EkiOnOff,
	pmopm8AlmChannel9PowerHighPortn
		EkiOnOff,
	pmopm8AlmChannel9PowerLowPortn
		EkiOnOff,
	pmopm8AlmChannel9BalancedPortn
		EkiOnOff,
	pmopm8AlmChannel9MismatchPortn
		EkiOnOff,
	pmopm8AlmChannel9AbsentPortn
		EkiOnOff
	}


pmopm8Almchannel9PortIndex OBJECT-TYPE
	SYNTAX  INTEGER(0..128)
	MAX-ACCESS  read-only
	STATUS current
	DESCRIPTION
        "
        Index definition for the pmopm8Almchannel9Port
        table
        "
	::= { pmopm8Almchannel9PortEntry 1 }


pmopm8AlmChannel9OosPortn OBJECT-TYPE
	SYNTAX  EkiOnOff
	MAX-ACCESS read-only
	STATUS current
	DESCRIPTION
        "
        Channel Out Of Service 9 :This
        OID indicates that the channel
         is out of service  <Help> This
        alarm indicates that the channel
        is in service <Condtype> CHANNEL9_OOS_1
        <Probcause> informationalStatus(1000)
        <Alarmtype> other (1) <Polarity>
        (2)
        "
	::= { pmopm8Almchannel9PortEntry 7 }


pmopm8AlmChannel9PowerHighPortn OBJECT-TYPE
	SYNTAX  EkiOnOff
	MAX-ACCESS read-only
	STATUS current
	DESCRIPTION
        "
        Channel Power High 9 :This OID
        indicates that the power of the
        channel is higher than the configured
        threshold<Help> This alarm indicates
        that the power of the channel is
        higher than the configured threshold
        <Condtype> CHANNEL9_POWER_HIGH_1
        <Probcause> degradedSignal (13)
        <Alarmtype> equipmentAlarm <Polarity>
        (2)
        "
	::= { pmopm8Almchannel9PortEntry 6 }


pmopm8AlmChannel9PowerLowPortn OBJECT-TYPE
	SYNTAX  EkiOnOff
	MAX-ACCESS read-only
	STATUS current
	DESCRIPTION
        "
        Channel Power Low 9 :This OID
         indicates that the power of the
        channel is lower than the configured
        threshold<Help> This alarm indicates
        that the power of the channel is
        lower than the configured threshold
        <Condtype> CHANNEL9_POWER_LOW_1
        <Probcause> degradedSignal (13)
        <Alarmtype> equipmentAlarm <Polarity>
        (2)
        "
	::= { pmopm8Almchannel9PortEntry 5 }


pmopm8AlmChannel9BalancedPortn OBJECT-TYPE
	SYNTAX  EkiOnOff
	MAX-ACCESS read-only
	STATUS current
	DESCRIPTION
        "
        Channel Balanced 9 :This OID indicates
        that an in service channel is balanced
        by the Ekinops auto turn up application<Help>
        This status indicates that an in
        service channel is balanced by
         the Ekinops auto turn up application
        <Condtype> CHANNEL9_BALANCED_1
         <Probcause> informationalStatus(1000)
        <Alarmtype> other (1) <Polarity>
        (2)
        "
	::= { pmopm8Almchannel9PortEntry 4 }


pmopm8AlmChannel9MismatchPortn OBJECT-TYPE
	SYNTAX  EkiOnOff
	MAX-ACCESS read-only
	STATUS current
	DESCRIPTION
        "
        Channel Mismatch 9 :This OID indicates
        that an out of service channel
         is detected on the Optical Power
        Monitoring input<Help> This alarm
        indicates that an out of service
        channel is detected on the Optical
        Power Monitoring input <Condtype>
        CHANNEL9_MISMATCH_1 <Probcause>
        unexpectedInformation (75) <Alarmtype>
        equipmentAlarm <Polarity> (2)
        "
	::= { pmopm8Almchannel9PortEntry 3 }


pmopm8AlmChannel9AbsentPortn OBJECT-TYPE
	SYNTAX  EkiOnOff
	MAX-ACCESS read-only
	STATUS current
	DESCRIPTION
        "
        Channel Absent 9 :This OID indicates
        that an in service channel is absent
        on the Optical Power Monitoring
        input<Help> This alarm indicates
        that an in service channel is absent
        on the Optical Power Monitoring
        input <Condtype> CHANNEL9_ABSENT_1
        <Probcause> informationMissing
         (65) <Alarmtype> equipmentAlarm
        (5) <Polarity> (2)
        "
	::= { pmopm8Almchannel9PortEntry 2 }


--- *********************************************************
---     TABLE for the pmopm8Almchannel10Port articles
--- *********************************************************

pmopm8Almchannel10PortTable OBJECT-TYPE
	SYNTAX  SEQUENCE OF Pmopm8Almchannel10PortEntry
	MAX-ACCESS not-accessible
	STATUS current
	DESCRIPTION
        "
        List of pmopm8Almchannel10Port
        Article
        "
	::= { pmopm8AlmClientCrit 88 }


pmopm8Almchannel10PortEntry OBJECT-TYPE
	SYNTAX Pmopm8Almchannel10PortEntry
	MAX-ACCESS not-accessible
	STATUS current
	DESCRIPTION
        "
        Row definition for the pmopm8Almchannel10Port
        table
        "
	INDEX   { pmopm8Almchannel10PortIndex }
	::= { pmopm8Almchannel10PortTable 1 }


Pmopm8Almchannel10PortEntry ::=
	SEQUENCE {
	pmopm8Almchannel10PortIndex
		INTEGER,
	pmopm8AlmChannel10OosPortn
		EkiOnOff,
	pmopm8AlmChannel10PowerHighPortn
		EkiOnOff,
	pmopm8AlmChannel10PowerLowPortn
		EkiOnOff,
	pmopm8AlmChannel10BalancedPortn
		EkiOnOff,
	pmopm8AlmChannel10MismatchPortn
		EkiOnOff,
	pmopm8AlmChannel10AbsentPortn
		EkiOnOff
	}


pmopm8Almchannel10PortIndex OBJECT-TYPE
	SYNTAX  INTEGER(0..128)
	MAX-ACCESS  read-only
	STATUS current
	DESCRIPTION
        "
        Index definition for the pmopm8Almchannel10Port
        table
        "
	::= { pmopm8Almchannel10PortEntry 1 }


pmopm8AlmChannel10OosPortn OBJECT-TYPE
	SYNTAX  EkiOnOff
	MAX-ACCESS read-only
	STATUS current
	DESCRIPTION
        "
        Channel Out Of Service 10 :This
        OID indicates that the channel
         is out of service  <Help> This
        alarm indicates that the channel
        is in service <Condtype> CHANNEL10_OOS_1
        <Probcause> informationalStatus(1000)
        <Alarmtype> other (1) <Polarity>
        (2)
        "
	::= { pmopm8Almchannel10PortEntry 7 }


pmopm8AlmChannel10PowerHighPortn OBJECT-TYPE
	SYNTAX  EkiOnOff
	MAX-ACCESS read-only
	STATUS current
	DESCRIPTION
        "
        Channel Power High 10 :This OID
        indicates that the power of the
        channel is higher than the configured
        threshold<Help> This alarm indicates
        that the power of the channel is
        higher than the configured threshold
        <Condtype> CHANNEL10_POWER_HIGH_1
        <Probcause> degradedSignal (13)
        <Alarmtype> equipmentAlarm <Polarity>
        (2)
        "
	::= { pmopm8Almchannel10PortEntry 6 }


pmopm8AlmChannel10PowerLowPortn OBJECT-TYPE
	SYNTAX  EkiOnOff
	MAX-ACCESS read-only
	STATUS current
	DESCRIPTION
        "
        Channel Power Low 10 :This OID
        indicates that the power of the
        channel is lower than the configured
        threshold<Help> This alarm indicates
        that the power of the channel is
        lower than the configured threshold
        <Condtype> CHANNEL10_POWER_LOW_1
        <Probcause> degradedSignal (13)
        <Alarmtype> equipmentAlarm <Polarity>
        (2)
        "
	::= { pmopm8Almchannel10PortEntry 5 }


pmopm8AlmChannel10BalancedPortn OBJECT-TYPE
	SYNTAX  EkiOnOff
	MAX-ACCESS read-only
	STATUS current
	DESCRIPTION
        "
        Channel Balanced 10 :This OID
         indicates that an in service channel
        is balanced by the Ekinops auto
        turn up application<Help> This
         status indicates that an in service
        channel is balanced by the Ekinops
        auto turn up application <Condtype>
        CHANNEL10_BALANCED_1 <Probcause>
        informationalStatus(1000) <Alarmtype>
        other (1) <Polarity> (2)
        "
	::= { pmopm8Almchannel10PortEntry 4 }


pmopm8AlmChannel10MismatchPortn OBJECT-TYPE
	SYNTAX  EkiOnOff
	MAX-ACCESS read-only
	STATUS current
	DESCRIPTION
        "
        Channel Mismatch 10 :This OID
         indicates that an out of service
        channel is detected on the Optical
        Power Monitoring input<Help> This
        alarm indicates that an out of
         service channel is detected on
        the Optical Power Monitoring input
        <Condtype> CHANNEL10_MISMATCH_1
        <Probcause> unexpectedInformation
        (75) <Alarmtype> equipmentAlarm
        <Polarity> (2)
        "
	::= { pmopm8Almchannel10PortEntry 3 }


pmopm8AlmChannel10AbsentPortn OBJECT-TYPE
	SYNTAX  EkiOnOff
	MAX-ACCESS read-only
	STATUS current
	DESCRIPTION
        "
        Channel Absent 10 :This OID indicates
        that an in service channel is absent
        on the Optical Power Monitoring
        input<Help> This alarm indicates
        that an in service channel is absent
        on the Optical Power Monitoring
        input <Condtype> CHANNEL10_ABSENT_1
        <Probcause> informationMissing
         (65) <Alarmtype> equipmentAlarm
        (5) <Polarity> (2)
        "
	::= { pmopm8Almchannel10PortEntry 2 }


--- *********************************************************
---     TABLE for the pmopm8Almchannel11Port articles
--- *********************************************************

pmopm8Almchannel11PortTable OBJECT-TYPE
	SYNTAX  SEQUENCE OF Pmopm8Almchannel11PortEntry
	MAX-ACCESS not-accessible
	STATUS current
	DESCRIPTION
        "
        List of pmopm8Almchannel11Port
        Article
        "
	::= { pmopm8AlmClientCrit 96 }


pmopm8Almchannel11PortEntry OBJECT-TYPE
	SYNTAX Pmopm8Almchannel11PortEntry
	MAX-ACCESS not-accessible
	STATUS current
	DESCRIPTION
        "
        Row definition for the pmopm8Almchannel11Port
        table
        "
	INDEX   { pmopm8Almchannel11PortIndex }
	::= { pmopm8Almchannel11PortTable 1 }


Pmopm8Almchannel11PortEntry ::=
	SEQUENCE {
	pmopm8Almchannel11PortIndex
		INTEGER,
	pmopm8AlmChannel11OosPortn
		EkiOnOff,
	pmopm8AlmChannel11PowerHighPortn
		EkiOnOff,
	pmopm8AlmChannel11PowerLowPortn
		EkiOnOff,
	pmopm8AlmChannel11BalancedPortn
		EkiOnOff,
	pmopm8AlmChannel11MismatchPortn
		EkiOnOff,
	pmopm8AlmChannel11AbsentPortn
		EkiOnOff
	}


pmopm8Almchannel11PortIndex OBJECT-TYPE
	SYNTAX  INTEGER(0..128)
	MAX-ACCESS  read-only
	STATUS current
	DESCRIPTION
        "
        Index definition for the pmopm8Almchannel11Port
        table
        "
	::= { pmopm8Almchannel11PortEntry 1 }


pmopm8AlmChannel11OosPortn OBJECT-TYPE
	SYNTAX  EkiOnOff
	MAX-ACCESS read-only
	STATUS current
	DESCRIPTION
        "
        Channel Out Of Service 11 :This
        OID indicates that the channel
         is out of service  <Help> This
        alarm indicates that the channel
        is in service <Condtype> CHANNEL11_OOS_1
        <Probcause> informationalStatus(1000)
        <Alarmtype> other (1) <Polarity>
        (2)
        "
	::= { pmopm8Almchannel11PortEntry 7 }


pmopm8AlmChannel11PowerHighPortn OBJECT-TYPE
	SYNTAX  EkiOnOff
	MAX-ACCESS read-only
	STATUS current
	DESCRIPTION
        "
        Channel Power High 11 :This OID
        indicates that the power of the
        channel is higher than the configured
        threshold<Help> This alarm indicates
        that the power of the channel is
        higher than the configured threshold
        <Condtype> CHANNEL11_POWER_HIGH_1
        <Probcause> degradedSignal (13)
        <Alarmtype> equipmentAlarm <Polarity>
        (2)
        "
	::= { pmopm8Almchannel11PortEntry 6 }


pmopm8AlmChannel11PowerLowPortn OBJECT-TYPE
	SYNTAX  EkiOnOff
	MAX-ACCESS read-only
	STATUS current
	DESCRIPTION
        "
        Channel Power Low 11 :This OID
        indicates that the power of the
        channel is lower than the configured
        threshold<Help> This alarm indicates
        that the power of the channel is
        lower than the configured threshold
        <Condtype> CHANNEL11_POWER_LOW_1
        <Probcause> degradedSignal (13)
        <Alarmtype> equipmentAlarm <Polarity>
        (2)
        "
	::= { pmopm8Almchannel11PortEntry 5 }


pmopm8AlmChannel11BalancedPortn OBJECT-TYPE
	SYNTAX  EkiOnOff
	MAX-ACCESS read-only
	STATUS current
	DESCRIPTION
        "
        Channel Balanced 11 :This OID
         indicates that an in service channel
        is balanced by the Ekinops auto
        turn up application<Help> This
         status indicates that an in service
        channel is balanced by the Ekinops
        auto turn up application <Condtype>
        CHANNEL11_BALANCED_1 <Probcause>
        informationalStatus(1000) <Alarmtype>
        other (1) <Polarity> (2)
        "
	::= { pmopm8Almchannel11PortEntry 4 }


pmopm8AlmChannel11MismatchPortn OBJECT-TYPE
	SYNTAX  EkiOnOff
	MAX-ACCESS read-only
	STATUS current
	DESCRIPTION
        "
        Channel Mismatch 11 :This OID
         indicates that an out of service
        channel is detected on the Optical
        Power Monitoring input<Help> This
        alarm indicates that an out of
         service channel is detected on
        the Optical Power Monitoring input
        <Condtype> CHANNEL11_MISMATCH_1
        <Probcause> unexpectedInformation
        (75) <Alarmtype> equipmentAlarm
        <Polarity> (2)
        "
	::= { pmopm8Almchannel11PortEntry 3 }


pmopm8AlmChannel11AbsentPortn OBJECT-TYPE
	SYNTAX  EkiOnOff
	MAX-ACCESS read-only
	STATUS current
	DESCRIPTION
        "
        Channel Absent 11 :This OID indicates
        that an in service channel is absent
        on the Optical Power Monitoring
        input<Help> This alarm indicates
        that an in service channel is absent
        on the Optical Power Monitoring
        input <Condtype> CHANNEL11_ABSENT_1
        <Probcause> informationMissing
         (65) <Alarmtype> equipmentAlarm
        (5) <Polarity> (2)
        "
	::= { pmopm8Almchannel11PortEntry 2 }


--- *********************************************************
---     TABLE for the pmopm8Almchannel12Port articles
--- *********************************************************

pmopm8Almchannel12PortTable OBJECT-TYPE
	SYNTAX  SEQUENCE OF Pmopm8Almchannel12PortEntry
	MAX-ACCESS not-accessible
	STATUS current
	DESCRIPTION
        "
        List of pmopm8Almchannel12Port
        Article
        "
	::= { pmopm8AlmClientCrit 104 }


pmopm8Almchannel12PortEntry OBJECT-TYPE
	SYNTAX Pmopm8Almchannel12PortEntry
	MAX-ACCESS not-accessible
	STATUS current
	DESCRIPTION
        "
        Row definition for the pmopm8Almchannel12Port
        table
        "
	INDEX   { pmopm8Almchannel12PortIndex }
	::= { pmopm8Almchannel12PortTable 1 }


Pmopm8Almchannel12PortEntry ::=
	SEQUENCE {
	pmopm8Almchannel12PortIndex
		INTEGER,
	pmopm8AlmChannel12OosPortn
		EkiOnOff,
	pmopm8AlmChannel12PowerHighPortn
		EkiOnOff,
	pmopm8AlmChannel12PowerLowPortn
		EkiOnOff,
	pmopm8AlmChannel12BalancedPortn
		EkiOnOff,
	pmopm8AlmChannel12MismatchPortn
		EkiOnOff,
	pmopm8AlmChannel12AbsentPortn
		EkiOnOff
	}


pmopm8Almchannel12PortIndex OBJECT-TYPE
	SYNTAX  INTEGER(0..128)
	MAX-ACCESS  read-only
	STATUS current
	DESCRIPTION
        "
        Index definition for the pmopm8Almchannel12Port
        table
        "
	::= { pmopm8Almchannel12PortEntry 1 }


pmopm8AlmChannel12OosPortn OBJECT-TYPE
	SYNTAX  EkiOnOff
	MAX-ACCESS read-only
	STATUS current
	DESCRIPTION
        "
        Channel Out Of Service 12 :This
        OID indicates that the channel
         is out of service  <Help> This
        alarm indicates that the channel
        is in service <Condtype> CHANNEL12_OOS_1
        <Probcause> informationalStatus(1000)
        <Alarmtype> other (1) <Polarity>
        (2)
        "
	::= { pmopm8Almchannel12PortEntry 7 }


pmopm8AlmChannel12PowerHighPortn OBJECT-TYPE
	SYNTAX  EkiOnOff
	MAX-ACCESS read-only
	STATUS current
	DESCRIPTION
        "
        Channel Power High 12 :This OID
        indicates that the power of the
        channel is higher than the configured
        threshold<Help> This alarm indicates
        that the power of the channel is
        higher than the configured threshold
        <Condtype> CHANNEL12_POWER_HIGH_1
        <Probcause> degradedSignal (13)
        <Alarmtype> equipmentAlarm <Polarity>
        (2)
        "
	::= { pmopm8Almchannel12PortEntry 6 }


pmopm8AlmChannel12PowerLowPortn OBJECT-TYPE
	SYNTAX  EkiOnOff
	MAX-ACCESS read-only
	STATUS current
	DESCRIPTION
        "
        Channel Power Low 12 :This OID
        indicates that the power of the
        channel is lower than the configured
        threshold<Help> This alarm indicates
        that the power of the channel is
        lower than the configured threshold
        <Condtype> CHANNEL12_POWER_LOW_1
        <Probcause> degradedSignal (13)
        <Alarmtype> equipmentAlarm <Polarity>
        (2)
        "
	::= { pmopm8Almchannel12PortEntry 5 }


pmopm8AlmChannel12BalancedPortn OBJECT-TYPE
	SYNTAX  EkiOnOff
	MAX-ACCESS read-only
	STATUS current
	DESCRIPTION
        "
        Channel Balanced 12 :This OID
         indicates that an in service channel
        is balanced by the Ekinops auto
        turn up application<Help> This
         status indicates that an in service
        channel is balanced by the Ekinops
        auto turn up application <Condtype>
        CHANNEL12_BALANCED_1 <Probcause>
        informationalStatus(1000) <Alarmtype>
        other (1) <Polarity> (2)
        "
	::= { pmopm8Almchannel12PortEntry 4 }


pmopm8AlmChannel12MismatchPortn OBJECT-TYPE
	SYNTAX  EkiOnOff
	MAX-ACCESS read-only
	STATUS current
	DESCRIPTION
        "
        Channel Mismatch 12 :This OID
         indicates that an out of service
        channel is detected on the Optical
        Power Monitoring input<Help> This
        alarm indicates that an out of
         service channel is detected on
        the Optical Power Monitoring input
        <Condtype> CHANNEL12_MISMATCH_1
        <Probcause> unexpectedInformation
        (75) <Alarmtype> equipmentAlarm
        <Polarity> (2)
        "
	::= { pmopm8Almchannel12PortEntry 3 }


pmopm8AlmChannel12AbsentPortn OBJECT-TYPE
	SYNTAX  EkiOnOff
	MAX-ACCESS read-only
	STATUS current
	DESCRIPTION
        "
        Channel Absent 12 :This OID indicates
        that an in service channel is absent
        on the Optical Power Monitoring
        input<Help> This alarm indicates
        that an in service channel is absent
        on the Optical Power Monitoring
        input <Condtype> CHANNEL12_ABSENT_1
        <Probcause> informationMissing
         (65) <Alarmtype> equipmentAlarm
        (5) <Polarity> (2)
        "
	::= { pmopm8Almchannel12PortEntry 2 }


--- *********************************************************
---     TABLE for the pmopm8Almchannel13Port articles
--- *********************************************************

pmopm8Almchannel13PortTable OBJECT-TYPE
	SYNTAX  SEQUENCE OF Pmopm8Almchannel13PortEntry
	MAX-ACCESS not-accessible
	STATUS current
	DESCRIPTION
        "
        List of pmopm8Almchannel13Port
        Article
        "
	::= { pmopm8AlmClientCrit 112 }


pmopm8Almchannel13PortEntry OBJECT-TYPE
	SYNTAX Pmopm8Almchannel13PortEntry
	MAX-ACCESS not-accessible
	STATUS current
	DESCRIPTION
        "
        Row definition for the pmopm8Almchannel13Port
        table
        "
	INDEX   { pmopm8Almchannel13PortIndex }
	::= { pmopm8Almchannel13PortTable 1 }


Pmopm8Almchannel13PortEntry ::=
	SEQUENCE {
	pmopm8Almchannel13PortIndex
		INTEGER,
	pmopm8AlmChannel13OosPortn
		EkiOnOff,
	pmopm8AlmChannel13PowerHighPortn
		EkiOnOff,
	pmopm8AlmChannel13PowerLowPortn
		EkiOnOff,
	pmopm8AlmChannel13BalancedPortn
		EkiOnOff,
	pmopm8AlmChannel13MismatchPortn
		EkiOnOff,
	pmopm8AlmChannel13AbsentPortn
		EkiOnOff
	}


pmopm8Almchannel13PortIndex OBJECT-TYPE
	SYNTAX  INTEGER(0..128)
	MAX-ACCESS  read-only
	STATUS current
	DESCRIPTION
        "
        Index definition for the pmopm8Almchannel13Port
        table
        "
	::= { pmopm8Almchannel13PortEntry 1 }


pmopm8AlmChannel13OosPortn OBJECT-TYPE
	SYNTAX  EkiOnOff
	MAX-ACCESS read-only
	STATUS current
	DESCRIPTION
        "
        Channel Out Of Service 13 :This
        OID indicates that the channel
         is out of service  <Help> This
        alarm indicates that the channel
        is in service <Condtype> CHANNEL13_OOS_1
        <Probcause> informationalStatus(1000)
        <Alarmtype> other (1) <Polarity>
        (2)
        "
	::= { pmopm8Almchannel13PortEntry 7 }


pmopm8AlmChannel13PowerHighPortn OBJECT-TYPE
	SYNTAX  EkiOnOff
	MAX-ACCESS read-only
	STATUS current
	DESCRIPTION
        "
        Channel Power High 13 :This OID
        indicates that the power of the
        channel is higher than the configured
        threshold<Help> This alarm indicates
        that the power of the channel is
        higher than the configured threshold
        <Condtype> CHANNEL13_POWER_HIGH_1
        <Probcause> degradedSignal (13)
        <Alarmtype> equipmentAlarm <Polarity>
        (2)
        "
	::= { pmopm8Almchannel13PortEntry 6 }


pmopm8AlmChannel13PowerLowPortn OBJECT-TYPE
	SYNTAX  EkiOnOff
	MAX-ACCESS read-only
	STATUS current
	DESCRIPTION
        "
        Channel Power Low 13 :This OID
        indicates that the power of the
        channel is lower than the configured
        threshold<Help> This alarm indicates
        that the power of the channel is
        lower than the configured threshold
        <Condtype> CHANNEL13_POWER_LOW_1
        <Probcause> degradedSignal (13)
        <Alarmtype> equipmentAlarm <Polarity>
        (2)
        "
	::= { pmopm8Almchannel13PortEntry 5 }


pmopm8AlmChannel13BalancedPortn OBJECT-TYPE
	SYNTAX  EkiOnOff
	MAX-ACCESS read-only
	STATUS current
	DESCRIPTION
        "
        Channel Balanced 13 :This OID
         indicates that an in service channel
        is balanced by the Ekinops auto
        turn up application<Help> This
         status indicates that an in service
        channel is balanced by the Ekinops
        auto turn up application <Condtype>
        CHANNEL13_BALANCED_1 <Probcause>
        informationalStatus(1000) <Alarmtype>
        other (1) <Polarity> (2)
        "
	::= { pmopm8Almchannel13PortEntry 4 }


pmopm8AlmChannel13MismatchPortn OBJECT-TYPE
	SYNTAX  EkiOnOff
	MAX-ACCESS read-only
	STATUS current
	DESCRIPTION
        "
        Channel Mismatch 13 :This OID
         indicates that an out of service
        channel is detected on the Optical
        Power Monitoring input<Help> This
        alarm indicates that an out of
         service channel is detected on
        the Optical Power Monitoring input
        <Condtype> CHANNEL13_MISMATCH_1
        <Probcause> unexpectedInformation
        (75) <Alarmtype> equipmentAlarm
        <Polarity> (2)
        "
	::= { pmopm8Almchannel13PortEntry 3 }


pmopm8AlmChannel13AbsentPortn OBJECT-TYPE
	SYNTAX  EkiOnOff
	MAX-ACCESS read-only
	STATUS current
	DESCRIPTION
        "
        Channel Absent 13 :This OID indicates
        that an in service channel is absent
        on the Optical Power Monitoring
        input<Help> This alarm indicates
        that an in service channel is absent
        on the Optical Power Monitoring
        input <Condtype> CHANNEL13_ABSENT_1
        <Probcause> informationMissing
         (65) <Alarmtype> equipmentAlarm
        (5) <Polarity> (2)
        "
	::= { pmopm8Almchannel13PortEntry 2 }


--- *********************************************************
---     TABLE for the pmopm8Almchannel14Port articles
--- *********************************************************

pmopm8Almchannel14PortTable OBJECT-TYPE
	SYNTAX  SEQUENCE OF Pmopm8Almchannel14PortEntry
	MAX-ACCESS not-accessible
	STATUS current
	DESCRIPTION
        "
        List of pmopm8Almchannel14Port
        Article
        "
	::= { pmopm8AlmClientCrit 120 }


pmopm8Almchannel14PortEntry OBJECT-TYPE
	SYNTAX Pmopm8Almchannel14PortEntry
	MAX-ACCESS not-accessible
	STATUS current
	DESCRIPTION
        "
        Row definition for the pmopm8Almchannel14Port
        table
        "
	INDEX   { pmopm8Almchannel14PortIndex }
	::= { pmopm8Almchannel14PortTable 1 }


Pmopm8Almchannel14PortEntry ::=
	SEQUENCE {
	pmopm8Almchannel14PortIndex
		INTEGER,
	pmopm8AlmChannel14OosPortn
		EkiOnOff,
	pmopm8AlmChannel14PowerHighPortn
		EkiOnOff,
	pmopm8AlmChannel14PowerLowPortn
		EkiOnOff,
	pmopm8AlmChannel14BalancedPortn
		EkiOnOff,
	pmopm8AlmChannel14MismatchPortn
		EkiOnOff,
	pmopm8AlmChannel14AbsentPortn
		EkiOnOff
	}


pmopm8Almchannel14PortIndex OBJECT-TYPE
	SYNTAX  INTEGER(0..128)
	MAX-ACCESS  read-only
	STATUS current
	DESCRIPTION
        "
        Index definition for the pmopm8Almchannel14Port
        table
        "
	::= { pmopm8Almchannel14PortEntry 1 }


pmopm8AlmChannel14OosPortn OBJECT-TYPE
	SYNTAX  EkiOnOff
	MAX-ACCESS read-only
	STATUS current
	DESCRIPTION
        "
        Channel Out Of Service 14 :This
        OID indicates that the channel
         is out of service  <Help> This
        alarm indicates that the channel
        is in service <Condtype> CHANNEL14_OOS_1
        <Probcause> informationalStatus(1000)
        <Alarmtype> other (1) <Polarity>
        (2)
        "
	::= { pmopm8Almchannel14PortEntry 7 }


pmopm8AlmChannel14PowerHighPortn OBJECT-TYPE
	SYNTAX  EkiOnOff
	MAX-ACCESS read-only
	STATUS current
	DESCRIPTION
        "
        Channel Power High 14 :This OID
        indicates that the power of the
        channel is higher than the configured
        threshold<Help> This alarm indicates
        that the power of the channel is
        higher than the configured threshold
        <Condtype> CHANNEL14_POWER_HIGH_1
        <Probcause> degradedSignal (13)
        <Alarmtype> equipmentAlarm <Polarity>
        (2)
        "
	::= { pmopm8Almchannel14PortEntry 6 }


pmopm8AlmChannel14PowerLowPortn OBJECT-TYPE
	SYNTAX  EkiOnOff
	MAX-ACCESS read-only
	STATUS current
	DESCRIPTION
        "
        Channel Power Low 14 :This OID
        indicates that the power of the
        channel is lower than the configured
        threshold<Help> This alarm indicates
        that the power of the channel is
        lower than the configured threshold
        <Condtype> CHANNEL14_POWER_LOW_1
        <Probcause> degradedSignal (13)
        <Alarmtype> equipmentAlarm <Polarity>
        (2)
        "
	::= { pmopm8Almchannel14PortEntry 5 }


pmopm8AlmChannel14BalancedPortn OBJECT-TYPE
	SYNTAX  EkiOnOff
	MAX-ACCESS read-only
	STATUS current
	DESCRIPTION
        "
        Channel Balanced 14 :This OID
         indicates that an in service channel
        is balanced by the Ekinops auto
        turn up application<Help> This
         status indicates that an in service
        channel is balanced by the Ekinops
        auto turn up application <Condtype>
        CHANNEL14_BALANCED_1 <Probcause>
        informationalStatus(1000) <Alarmtype>
        other (1) <Polarity> (2)
        "
	::= { pmopm8Almchannel14PortEntry 4 }


pmopm8AlmChannel14MismatchPortn OBJECT-TYPE
	SYNTAX  EkiOnOff
	MAX-ACCESS read-only
	STATUS current
	DESCRIPTION
        "
        Channel Mismatch 14 :This OID
         indicates that an out of service
        channel is detected on the Optical
        Power Monitoring input<Help> This
        alarm indicates that an out of
         service channel is detected on
        the Optical Power Monitoring input
        <Condtype> CHANNEL14_MISMATCH_1
        <Probcause> unexpectedInformation
        (75) <Alarmtype> equipmentAlarm
        <Polarity> (2)
        "
	::= { pmopm8Almchannel14PortEntry 3 }


pmopm8AlmChannel14AbsentPortn OBJECT-TYPE
	SYNTAX  EkiOnOff
	MAX-ACCESS read-only
	STATUS current
	DESCRIPTION
        "
        Channel Absent 14 :This OID indicates
        that an in service channel is absent
        on the Optical Power Monitoring
        input<Help> This alarm indicates
        that an in service channel is absent
        on the Optical Power Monitoring
        input <Condtype> CHANNEL14_ABSENT_1
        <Probcause> informationMissing
         (65) <Alarmtype> equipmentAlarm
        (5) <Polarity> (2)
        "
	::= { pmopm8Almchannel14PortEntry 2 }


--- *********************************************************
---     TABLE for the pmopm8Almchannel15Port articles
--- *********************************************************

pmopm8Almchannel15PortTable OBJECT-TYPE
	SYNTAX  SEQUENCE OF Pmopm8Almchannel15PortEntry
	MAX-ACCESS not-accessible
	STATUS current
	DESCRIPTION
        "
        List of pmopm8Almchannel15Port
        Article
        "
	::= { pmopm8AlmClientCrit 128 }


pmopm8Almchannel15PortEntry OBJECT-TYPE
	SYNTAX Pmopm8Almchannel15PortEntry
	MAX-ACCESS not-accessible
	STATUS current
	DESCRIPTION
        "
        Row definition for the pmopm8Almchannel15Port
        table
        "
	INDEX   { pmopm8Almchannel15PortIndex }
	::= { pmopm8Almchannel15PortTable 1 }


Pmopm8Almchannel15PortEntry ::=
	SEQUENCE {
	pmopm8Almchannel15PortIndex
		INTEGER,
	pmopm8AlmChannel15OosPortn
		EkiOnOff,
	pmopm8AlmChannel15PowerHighPortn
		EkiOnOff,
	pmopm8AlmChannel15PowerLowPortn
		EkiOnOff,
	pmopm8AlmChannel15BalancedPortn
		EkiOnOff,
	pmopm8AlmChannel15MismatchPortn
		EkiOnOff,
	pmopm8AlmChannel15AbsentPortn
		EkiOnOff
	}


pmopm8Almchannel15PortIndex OBJECT-TYPE
	SYNTAX  INTEGER(0..128)
	MAX-ACCESS  read-only
	STATUS current
	DESCRIPTION
        "
        Index definition for the pmopm8Almchannel15Port
        table
        "
	::= { pmopm8Almchannel15PortEntry 1 }


pmopm8AlmChannel15OosPortn OBJECT-TYPE
	SYNTAX  EkiOnOff
	MAX-ACCESS read-only
	STATUS current
	DESCRIPTION
        "
        Channel Out Of Service 15 :This
        OID indicates that the channel
         is out of service  <Help> This
        alarm indicates that the channel
        is in service <Condtype> CHANNEL15_OOS_1
        <Probcause> informationalStatus(1000)
        <Alarmtype> other (1) <Polarity>
        (2)
        "
	::= { pmopm8Almchannel15PortEntry 7 }


pmopm8AlmChannel15PowerHighPortn OBJECT-TYPE
	SYNTAX  EkiOnOff
	MAX-ACCESS read-only
	STATUS current
	DESCRIPTION
        "
        Channel Power High 15 :This OID
        indicates that the power of the
        channel is higher than the configured
        threshold<Help> This alarm indicates
        that the power of the channel is
        higher than the configured threshold
        <Condtype> CHANNEL15_POWER_HIGH_1
        <Probcause> degradedSignal (13)
        <Alarmtype> equipmentAlarm <Polarity>
        (2)
        "
	::= { pmopm8Almchannel15PortEntry 6 }


pmopm8AlmChannel15PowerLowPortn OBJECT-TYPE
	SYNTAX  EkiOnOff
	MAX-ACCESS read-only
	STATUS current
	DESCRIPTION
        "
        Channel Power Low 15 :This OID
        indicates that the power of the
        channel is lower than the configured
        threshold<Help> This alarm indicates
        that the power of the channel is
        lower than the configured threshold
        <Condtype> CHANNEL15_POWER_LOW_1
        <Probcause> degradedSignal (13)
        <Alarmtype> equipmentAlarm <Polarity>
        (2)
        "
	::= { pmopm8Almchannel15PortEntry 5 }


pmopm8AlmChannel15BalancedPortn OBJECT-TYPE
	SYNTAX  EkiOnOff
	MAX-ACCESS read-only
	STATUS current
	DESCRIPTION
        "
        Channel Balanced 15 :This OID
         indicates that an in service channel
        is balanced by the Ekinops auto
        turn up application<Help> This
         status indicates that an in service
        channel is balanced by the Ekinops
        auto turn up application <Condtype>
        CHANNEL15_BALANCED_1 <Probcause>
        informationalStatus(1000) <Alarmtype>
        other (1) <Polarity> (2)
        "
	::= { pmopm8Almchannel15PortEntry 4 }


pmopm8AlmChannel15MismatchPortn OBJECT-TYPE
	SYNTAX  EkiOnOff
	MAX-ACCESS read-only
	STATUS current
	DESCRIPTION
        "
        Channel Mismatch 15 :This OID
         indicates that an out of service
        channel is detected on the Optical
        Power Monitoring input<Help> This
        alarm indicates that an out of
         service channel is detected on
        the Optical Power Monitoring input
        <Condtype> CHANNEL15_MISMATCH_1
        <Probcause> unexpectedInformation
        (75) <Alarmtype> equipmentAlarm
        <Polarity> (2)
        "
	::= { pmopm8Almchannel15PortEntry 3 }


pmopm8AlmChannel15AbsentPortn OBJECT-TYPE
	SYNTAX  EkiOnOff
	MAX-ACCESS read-only
	STATUS current
	DESCRIPTION
        "
        Channel Absent 15 :This OID indicates
        that an in service channel is absent
        on the Optical Power Monitoring
        input<Help> This alarm indicates
        that an in service channel is absent
        on the Optical Power Monitoring
        input <Condtype> CHANNEL15_ABSENT_1
        <Probcause> informationMissing
         (65) <Alarmtype> equipmentAlarm
        (5) <Polarity> (2)
        "
	::= { pmopm8Almchannel15PortEntry 2 }


--- *********************************************************
---     TABLE for the pmopm8Almchannel16Port articles
--- *********************************************************

pmopm8Almchannel16PortTable OBJECT-TYPE
	SYNTAX  SEQUENCE OF Pmopm8Almchannel16PortEntry
	MAX-ACCESS not-accessible
	STATUS current
	DESCRIPTION
        "
        List of pmopm8Almchannel16Port
        Article
        "
	::= { pmopm8AlmClientCrit 136 }


pmopm8Almchannel16PortEntry OBJECT-TYPE
	SYNTAX Pmopm8Almchannel16PortEntry
	MAX-ACCESS not-accessible
	STATUS current
	DESCRIPTION
        "
        Row definition for the pmopm8Almchannel16Port
        table
        "
	INDEX   { pmopm8Almchannel16PortIndex }
	::= { pmopm8Almchannel16PortTable 1 }


Pmopm8Almchannel16PortEntry ::=
	SEQUENCE {
	pmopm8Almchannel16PortIndex
		INTEGER,
	pmopm8AlmChannel16OosPortn
		EkiOnOff,
	pmopm8AlmChannel16PowerHighPortn
		EkiOnOff,
	pmopm8AlmChannel16PowerLowPortn
		EkiOnOff,
	pmopm8AlmChannel16BalancedPortn
		EkiOnOff,
	pmopm8AlmChannel16MismatchPortn
		EkiOnOff,
	pmopm8AlmChannel16AbsentPortn
		EkiOnOff
	}


pmopm8Almchannel16PortIndex OBJECT-TYPE
	SYNTAX  INTEGER(0..128)
	MAX-ACCESS  read-only
	STATUS current
	DESCRIPTION
        "
        Index definition for the pmopm8Almchannel16Port
        table
        "
	::= { pmopm8Almchannel16PortEntry 1 }


pmopm8AlmChannel16OosPortn OBJECT-TYPE
	SYNTAX  EkiOnOff
	MAX-ACCESS read-only
	STATUS current
	DESCRIPTION
        "
        Channel Out Of Service 16 :This
        OID indicates that the channel
         is out of service  <Help> This
        alarm indicates that the channel
        is in service <Condtype> CHANNEL16_OOS_1
        <Probcause> informationalStatus(1000)
        <Alarmtype> other (1) <Polarity>
        (2)
        "
	::= { pmopm8Almchannel16PortEntry 7 }


pmopm8AlmChannel16PowerHighPortn OBJECT-TYPE
	SYNTAX  EkiOnOff
	MAX-ACCESS read-only
	STATUS current
	DESCRIPTION
        "
        Channel Power High 16 :This OID
        indicates that the power of the
        channel is higher than the configured
        threshold<Help> This alarm indicates
        that the power of the channel is
        higher than the configured threshold
        <Condtype> CHANNEL16_POWER_HIGH_1
        <Probcause> degradedSignal (13)
        <Alarmtype> equipmentAlarm <Polarity>
        (2)
        "
	::= { pmopm8Almchannel16PortEntry 6 }


pmopm8AlmChannel16PowerLowPortn OBJECT-TYPE
	SYNTAX  EkiOnOff
	MAX-ACCESS read-only
	STATUS current
	DESCRIPTION
        "
        Channel Power Low 16 :This OID
        indicates that the power of the
        channel is lower than the configured
        threshold<Help> This alarm indicates
        that the power of the channel is
        lower than the configured threshold
        <Condtype> CHANNEL16_POWER_LOW_1
        <Probcause> degradedSignal (13)
        <Alarmtype> equipmentAlarm <Polarity>
        (2)
        "
	::= { pmopm8Almchannel16PortEntry 5 }


pmopm8AlmChannel16BalancedPortn OBJECT-TYPE
	SYNTAX  EkiOnOff
	MAX-ACCESS read-only
	STATUS current
	DESCRIPTION
        "
        Channel Balanced 16 :This OID
         indicates that an in service channel
        is balanced by the Ekinops auto
        turn up application<Help> This
         status indicates that an in service
        channel is balanced by the Ekinops
        auto turn up application <Condtype>
        CHANNEL16_BALANCED_1 <Probcause>
        informationalStatus(1000) <Alarmtype>
        other (1) <Polarity> (2)
        "
	::= { pmopm8Almchannel16PortEntry 4 }


pmopm8AlmChannel16MismatchPortn OBJECT-TYPE
	SYNTAX  EkiOnOff
	MAX-ACCESS read-only
	STATUS current
	DESCRIPTION
        "
        Channel Mismatch 16 :This OID
         indicates that an out of service
        channel is detected on the Optical
        Power Monitoring input<Help> This
        alarm indicates that an out of
         service channel is detected on
        the Optical Power Monitoring input
        <Condtype> CHANNEL16_MISMATCH_1
        <Probcause> unexpectedInformation
        (75) <Alarmtype> equipmentAlarm
        <Polarity> (2)
        "
	::= { pmopm8Almchannel16PortEntry 3 }


pmopm8AlmChannel16AbsentPortn OBJECT-TYPE
	SYNTAX  EkiOnOff
	MAX-ACCESS read-only
	STATUS current
	DESCRIPTION
        "
        Channel Absent 16 :This OID indicates
        that an in service channel is absent
        on the Optical Power Monitoring
        input<Help> This alarm indicates
        that an in service channel is absent
        on the Optical Power Monitoring
        input <Condtype> CHANNEL16_ABSENT_1
        <Probcause> informationMissing
         (65) <Alarmtype> equipmentAlarm
        (5) <Polarity> (2)
        "
	::= { pmopm8Almchannel16PortEntry 2 }


--- *********************************************************
---     TABLE for the pmopm8Almchannel17Port articles
--- *********************************************************

pmopm8Almchannel17PortTable OBJECT-TYPE
	SYNTAX  SEQUENCE OF Pmopm8Almchannel17PortEntry
	MAX-ACCESS not-accessible
	STATUS current
	DESCRIPTION
        "
        List of pmopm8Almchannel17Port
        Article
        "
	::= { pmopm8AlmClientCrit 144 }


pmopm8Almchannel17PortEntry OBJECT-TYPE
	SYNTAX Pmopm8Almchannel17PortEntry
	MAX-ACCESS not-accessible
	STATUS current
	DESCRIPTION
        "
        Row definition for the pmopm8Almchannel17Port
        table
        "
	INDEX   { pmopm8Almchannel17PortIndex }
	::= { pmopm8Almchannel17PortTable 1 }


Pmopm8Almchannel17PortEntry ::=
	SEQUENCE {
	pmopm8Almchannel17PortIndex
		INTEGER,
	pmopm8AlmChannel17OosPortn
		EkiOnOff,
	pmopm8AlmChannel17PowerHighPortn
		EkiOnOff,
	pmopm8AlmChannel17PowerLowPortn
		EkiOnOff,
	pmopm8AlmChannel17BalancedPortn
		EkiOnOff,
	pmopm8AlmChannel17MismatchPortn
		EkiOnOff,
	pmopm8AlmChannel17AbsentPortn
		EkiOnOff
	}


pmopm8Almchannel17PortIndex OBJECT-TYPE
	SYNTAX  INTEGER(0..128)
	MAX-ACCESS  read-only
	STATUS current
	DESCRIPTION
        "
        Index definition for the pmopm8Almchannel17Port
        table
        "
	::= { pmopm8Almchannel17PortEntry 1 }


pmopm8AlmChannel17OosPortn OBJECT-TYPE
	SYNTAX  EkiOnOff
	MAX-ACCESS read-only
	STATUS current
	DESCRIPTION
        "
        Channel Out Of Service 17 :This
        OID indicates that the channel
         is out of service  <Help> This
        alarm indicates that the channel
        is in service <Condtype> CHANNEL17_OOS_1
        <Probcause> informationalStatus(1000)
        <Alarmtype> other (1) <Polarity>
        (2)
        "
	::= { pmopm8Almchannel17PortEntry 7 }


pmopm8AlmChannel17PowerHighPortn OBJECT-TYPE
	SYNTAX  EkiOnOff
	MAX-ACCESS read-only
	STATUS current
	DESCRIPTION
        "
        Channel Power High 17 :This OID
        indicates that the power of the
        channel is higher than the configured
        threshold<Help> This alarm indicates
        that the power of the channel is
        higher than the configured threshold
        <Condtype> CHANNEL17_POWER_HIGH_1
        <Probcause> degradedSignal (13)
        <Alarmtype> equipmentAlarm <Polarity>
        (2)
        "
	::= { pmopm8Almchannel17PortEntry 6 }


pmopm8AlmChannel17PowerLowPortn OBJECT-TYPE
	SYNTAX  EkiOnOff
	MAX-ACCESS read-only
	STATUS current
	DESCRIPTION
        "
        Channel Power Low 17 :This OID
        indicates that the power of the
        channel is lower than the configured
        threshold<Help> This alarm indicates
        that the power of the channel is
        lower than the configured threshold
        <Condtype> CHANNEL17_POWER_LOW_1
        <Probcause> degradedSignal (13)
        <Alarmtype> equipmentAlarm <Polarity>
        (2)
        "
	::= { pmopm8Almchannel17PortEntry 5 }


pmopm8AlmChannel17BalancedPortn OBJECT-TYPE
	SYNTAX  EkiOnOff
	MAX-ACCESS read-only
	STATUS current
	DESCRIPTION
        "
        Channel Balanced 17 :This OID
         indicates that an in service channel
        is balanced by the Ekinops auto
        turn up application<Help> This
         status indicates that an in service
        channel is balanced by the Ekinops
        auto turn up application <Condtype>
        CHANNEL17_BALANCED_1 <Probcause>
        informationalStatus(1000) <Alarmtype>
        other (1) <Polarity> (2)
        "
	::= { pmopm8Almchannel17PortEntry 4 }


pmopm8AlmChannel17MismatchPortn OBJECT-TYPE
	SYNTAX  EkiOnOff
	MAX-ACCESS read-only
	STATUS current
	DESCRIPTION
        "
        Channel Mismatch 17 :This OID
         indicates that an out of service
        channel is detected on the Optical
        Power Monitoring input<Help> This
        alarm indicates that an out of
         service channel is detected on
        the Optical Power Monitoring input
        <Condtype> CHANNEL17_MISMATCH_1
        <Probcause> unexpectedInformation
        (75) <Alarmtype> equipmentAlarm
        <Polarity> (2)
        "
	::= { pmopm8Almchannel17PortEntry 3 }


pmopm8AlmChannel17AbsentPortn OBJECT-TYPE
	SYNTAX  EkiOnOff
	MAX-ACCESS read-only
	STATUS current
	DESCRIPTION
        "
        Channel Absent 17 :This OID indicates
        that an in service channel is absent
        on the Optical Power Monitoring
        input<Help> This alarm indicates
        that an in service channel is absent
        on the Optical Power Monitoring
        input <Condtype> CHANNEL17_ABSENT_1
        <Probcause> informationMissing
         (65) <Alarmtype> equipmentAlarm
        (5) <Polarity> (2)
        "
	::= { pmopm8Almchannel17PortEntry 2 }


--- *********************************************************
---     TABLE for the pmopm8Almchannel18Port articles
--- *********************************************************

pmopm8Almchannel18PortTable OBJECT-TYPE
	SYNTAX  SEQUENCE OF Pmopm8Almchannel18PortEntry
	MAX-ACCESS not-accessible
	STATUS current
	DESCRIPTION
        "
        List of pmopm8Almchannel18Port
        Article
        "
	::= { pmopm8AlmClientCrit 152 }


pmopm8Almchannel18PortEntry OBJECT-TYPE
	SYNTAX Pmopm8Almchannel18PortEntry
	MAX-ACCESS not-accessible
	STATUS current
	DESCRIPTION
        "
        Row definition for the pmopm8Almchannel18Port
        table
        "
	INDEX   { pmopm8Almchannel18PortIndex }
	::= { pmopm8Almchannel18PortTable 1 }


Pmopm8Almchannel18PortEntry ::=
	SEQUENCE {
	pmopm8Almchannel18PortIndex
		INTEGER,
	pmopm8AlmChannel18OosPortn
		EkiOnOff,
	pmopm8AlmChannel18PowerHighPortn
		EkiOnOff,
	pmopm8AlmChannel18PowerLowPortn
		EkiOnOff,
	pmopm8AlmChannel18BalancedPortn
		EkiOnOff,
	pmopm8AlmChannel18MismatchPortn
		EkiOnOff,
	pmopm8AlmChannel18AbsentPortn
		EkiOnOff
	}


pmopm8Almchannel18PortIndex OBJECT-TYPE
	SYNTAX  INTEGER(0..128)
	MAX-ACCESS  read-only
	STATUS current
	DESCRIPTION
        "
        Index definition for the pmopm8Almchannel18Port
        table
        "
	::= { pmopm8Almchannel18PortEntry 1 }


pmopm8AlmChannel18OosPortn OBJECT-TYPE
	SYNTAX  EkiOnOff
	MAX-ACCESS read-only
	STATUS current
	DESCRIPTION
        "
        Channel Out Of Service 18 :This
        OID indicates that the channel
         is out of service  <Help> This
        alarm indicates that the channel
        is in service <Condtype> CHANNEL18_OOS_1
        <Probcause> informationalStatus(1000)
        <Alarmtype> other (1) <Polarity>
        (2)
        "
	::= { pmopm8Almchannel18PortEntry 7 }


pmopm8AlmChannel18PowerHighPortn OBJECT-TYPE
	SYNTAX  EkiOnOff
	MAX-ACCESS read-only
	STATUS current
	DESCRIPTION
        "
        Channel Power High 18 :This OID
        indicates that the power of the
        channel is higher than the configured
        threshold<Help> This alarm indicates
        that the power of the channel is
        higher than the configured threshold
        <Condtype> CHANNEL18_POWER_HIGH_1
        <Probcause> degradedSignal (13)
        <Alarmtype> equipmentAlarm <Polarity>
        (2)
        "
	::= { pmopm8Almchannel18PortEntry 6 }


pmopm8AlmChannel18PowerLowPortn OBJECT-TYPE
	SYNTAX  EkiOnOff
	MAX-ACCESS read-only
	STATUS current
	DESCRIPTION
        "
        Channel Power Low 18 :This OID
        indicates that the power of the
        channel is lower than the configured
        threshold<Help> This alarm indicates
        that the power of the channel is
        lower than the configured threshold
        <Condtype> CHANNEL18_POWER_LOW_1
        <Probcause> degradedSignal (13)
        <Alarmtype> equipmentAlarm <Polarity>
        (2)
        "
	::= { pmopm8Almchannel18PortEntry 5 }


pmopm8AlmChannel18BalancedPortn OBJECT-TYPE
	SYNTAX  EkiOnOff
	MAX-ACCESS read-only
	STATUS current
	DESCRIPTION
        "
        Channel Balanced 18 :This OID
         indicates that an in service channel
        is balanced by the Ekinops auto
        turn up application<Help> This
         status indicates that an in service
        channel is balanced by the Ekinops
        auto turn up application <Condtype>
        CHANNEL18_BALANCED_1 <Probcause>
        informationalStatus(1000) <Alarmtype>
        other (1) <Polarity> (2)
        "
	::= { pmopm8Almchannel18PortEntry 4 }


pmopm8AlmChannel18MismatchPortn OBJECT-TYPE
	SYNTAX  EkiOnOff
	MAX-ACCESS read-only
	STATUS current
	DESCRIPTION
        "
        Channel Mismatch 18 :This OID
         indicates that an out of service
        channel is detected on the Optical
        Power Monitoring input<Help> This
        alarm indicates that an out of
         service channel is detected on
        the Optical Power Monitoring input
        <Condtype> CHANNEL18_MISMATCH_1
        <Probcause> unexpectedInformation
        (75) <Alarmtype> equipmentAlarm
        <Polarity> (2)
        "
	::= { pmopm8Almchannel18PortEntry 3 }


pmopm8AlmChannel18AbsentPortn OBJECT-TYPE
	SYNTAX  EkiOnOff
	MAX-ACCESS read-only
	STATUS current
	DESCRIPTION
        "
        Channel Absent 18 :This OID indicates
        that an in service channel is absent
        on the Optical Power Monitoring
        input<Help> This alarm indicates
        that an in service channel is absent
        on the Optical Power Monitoring
        input <Condtype> CHANNEL18_ABSENT_1
        <Probcause> informationMissing
         (65) <Alarmtype> equipmentAlarm
        (5) <Polarity> (2)
        "
	::= { pmopm8Almchannel18PortEntry 2 }


--- *********************************************************
---     TABLE for the pmopm8Almchannel19Port articles
--- *********************************************************

pmopm8Almchannel19PortTable OBJECT-TYPE
	SYNTAX  SEQUENCE OF Pmopm8Almchannel19PortEntry
	MAX-ACCESS not-accessible
	STATUS current
	DESCRIPTION
        "
        List of pmopm8Almchannel19Port
        Article
        "
	::= { pmopm8AlmClientCrit 160 }


pmopm8Almchannel19PortEntry OBJECT-TYPE
	SYNTAX Pmopm8Almchannel19PortEntry
	MAX-ACCESS not-accessible
	STATUS current
	DESCRIPTION
        "
        Row definition for the pmopm8Almchannel19Port
        table
        "
	INDEX   { pmopm8Almchannel19PortIndex }
	::= { pmopm8Almchannel19PortTable 1 }


Pmopm8Almchannel19PortEntry ::=
	SEQUENCE {
	pmopm8Almchannel19PortIndex
		INTEGER,
	pmopm8AlmChannel19OosPortn
		EkiOnOff,
	pmopm8AlmChannel19PowerHighPortn
		EkiOnOff,
	pmopm8AlmChannel19PowerLowPortn
		EkiOnOff,
	pmopm8AlmChannel19BalancedPortn
		EkiOnOff,
	pmopm8AlmChannel19MismatchPortn
		EkiOnOff,
	pmopm8AlmChannel19AbsentPortn
		EkiOnOff
	}


pmopm8Almchannel19PortIndex OBJECT-TYPE
	SYNTAX  INTEGER(0..128)
	MAX-ACCESS  read-only
	STATUS current
	DESCRIPTION
        "
        Index definition for the pmopm8Almchannel19Port
        table
        "
	::= { pmopm8Almchannel19PortEntry 1 }


pmopm8AlmChannel19OosPortn OBJECT-TYPE
	SYNTAX  EkiOnOff
	MAX-ACCESS read-only
	STATUS current
	DESCRIPTION
        "
        Channel Out Of Service 19 :This
        OID indicates that the channel
         is out of service  <Help> This
        alarm indicates that the channel
        is in service <Condtype> CHANNEL19_OOS_1
        <Probcause> informationalStatus(1000)
        <Alarmtype> other (1) <Polarity>
        (2)
        "
	::= { pmopm8Almchannel19PortEntry 7 }


pmopm8AlmChannel19PowerHighPortn OBJECT-TYPE
	SYNTAX  EkiOnOff
	MAX-ACCESS read-only
	STATUS current
	DESCRIPTION
        "
        Channel Power High 19 :This OID
        indicates that the power of the
        channel is higher than the configured
        threshold<Help> This alarm indicates
        that the power of the channel is
        higher than the configured threshold
        <Condtype> CHANNEL19_POWER_HIGH_1
        <Probcause> degradedSignal (13)
        <Alarmtype> equipmentAlarm <Polarity>
        (2)
        "
	::= { pmopm8Almchannel19PortEntry 6 }


pmopm8AlmChannel19PowerLowPortn OBJECT-TYPE
	SYNTAX  EkiOnOff
	MAX-ACCESS read-only
	STATUS current
	DESCRIPTION
        "
        Channel Power Low 19 :This OID
        indicates that the power of the
        channel is lower than the configured
        threshold<Help> This alarm indicates
        that the power of the channel is
        lower than the configured threshold
        <Condtype> CHANNEL19_POWER_LOW_1
        <Probcause> degradedSignal (13)
        <Alarmtype> equipmentAlarm <Polarity>
        (2)
        "
	::= { pmopm8Almchannel19PortEntry 5 }


pmopm8AlmChannel19BalancedPortn OBJECT-TYPE
	SYNTAX  EkiOnOff
	MAX-ACCESS read-only
	STATUS current
	DESCRIPTION
        "
        Channel Balanced 19 :This OID
         indicates that an in service channel
        is balanced by the Ekinops auto
        turn up application<Help> This
         status indicates that an in service
        channel is balanced by the Ekinops
        auto turn up application <Condtype>
        CHANNEL19_BALANCED_1 <Probcause>
        informationalStatus(1000) <Alarmtype>
        other (1) <Polarity> (2)
        "
	::= { pmopm8Almchannel19PortEntry 4 }


pmopm8AlmChannel19MismatchPortn OBJECT-TYPE
	SYNTAX  EkiOnOff
	MAX-ACCESS read-only
	STATUS current
	DESCRIPTION
        "
        Channel Mismatch 19 :This OID
         indicates that an out of service
        channel is detected on the Optical
        Power Monitoring input<Help> This
        alarm indicates that an out of
         service channel is detected on
        the Optical Power Monitoring input
        <Condtype> CHANNEL19_MISMATCH_1
        <Probcause> unexpectedInformation
        (75) <Alarmtype> equipmentAlarm
        <Polarity> (2)
        "
	::= { pmopm8Almchannel19PortEntry 3 }


pmopm8AlmChannel19AbsentPortn OBJECT-TYPE
	SYNTAX  EkiOnOff
	MAX-ACCESS read-only
	STATUS current
	DESCRIPTION
        "
        Channel Absent 19 :This OID indicates
        that an in service channel is absent
        on the Optical Power Monitoring
        input<Help> This alarm indicates
        that an in service channel is absent
        on the Optical Power Monitoring
        input <Condtype> CHANNEL19_ABSENT_1
        <Probcause> informationMissing
         (65) <Alarmtype> equipmentAlarm
        (5) <Polarity> (2)
        "
	::= { pmopm8Almchannel19PortEntry 2 }


--- *********************************************************
---     TABLE for the pmopm8Almchannel20Port articles
--- *********************************************************

pmopm8Almchannel20PortTable OBJECT-TYPE
	SYNTAX  SEQUENCE OF Pmopm8Almchannel20PortEntry
	MAX-ACCESS not-accessible
	STATUS current
	DESCRIPTION
        "
        List of pmopm8Almchannel20Port
        Article
        "
	::= { pmopm8AlmClientCrit 168 }


pmopm8Almchannel20PortEntry OBJECT-TYPE
	SYNTAX Pmopm8Almchannel20PortEntry
	MAX-ACCESS not-accessible
	STATUS current
	DESCRIPTION
        "
        Row definition for the pmopm8Almchannel20Port
        table
        "
	INDEX   { pmopm8Almchannel20PortIndex }
	::= { pmopm8Almchannel20PortTable 1 }


Pmopm8Almchannel20PortEntry ::=
	SEQUENCE {
	pmopm8Almchannel20PortIndex
		INTEGER,
	pmopm8AlmChannel20OosPortn
		EkiOnOff,
	pmopm8AlmChannel20PowerHighPortn
		EkiOnOff,
	pmopm8AlmChannel20PowerLowPortn
		EkiOnOff,
	pmopm8AlmChannel20BalancedPortn
		EkiOnOff,
	pmopm8AlmChannel20MismatchPortn
		EkiOnOff,
	pmopm8AlmChannel20AbsentPortn
		EkiOnOff
	}


pmopm8Almchannel20PortIndex OBJECT-TYPE
	SYNTAX  INTEGER(0..128)
	MAX-ACCESS  read-only
	STATUS current
	DESCRIPTION
        "
        Index definition for the pmopm8Almchannel20Port
        table
        "
	::= { pmopm8Almchannel20PortEntry 1 }


pmopm8AlmChannel20OosPortn OBJECT-TYPE
	SYNTAX  EkiOnOff
	MAX-ACCESS read-only
	STATUS current
	DESCRIPTION
        "
        Channel Out Of Service 20 :This
        OID indicates that the channel
         is out of service  <Help> This
        alarm indicates that the channel
        is in service <Condtype> CHANNEL20_OOS_1
        <Probcause> informationalStatus(1000)
        <Alarmtype> other (1) <Polarity>
        (2)
        "
	::= { pmopm8Almchannel20PortEntry 7 }


pmopm8AlmChannel20PowerHighPortn OBJECT-TYPE
	SYNTAX  EkiOnOff
	MAX-ACCESS read-only
	STATUS current
	DESCRIPTION
        "
        Channel Power High 20 :This OID
        indicates that the power of the
        channel is higher than the configured
        threshold<Help> This alarm indicates
        that the power of the channel is
        higher than the configured threshold
        <Condtype> CHANNEL20_POWER_HIGH_1
        <Probcause> degradedSignal (13)
        <Alarmtype> equipmentAlarm <Polarity>
        (2)
        "
	::= { pmopm8Almchannel20PortEntry 6 }


pmopm8AlmChannel20PowerLowPortn OBJECT-TYPE
	SYNTAX  EkiOnOff
	MAX-ACCESS read-only
	STATUS current
	DESCRIPTION
        "
        Channel Power Low 20 :This OID
        indicates that the power of the
        channel is lower than the configured
        threshold<Help> This alarm indicates
        that the power of the channel is
        lower than the configured threshold
        <Condtype> CHANNEL20_POWER_LOW_1
        <Probcause> degradedSignal (13)
        <Alarmtype> equipmentAlarm <Polarity>
        (2)
        "
	::= { pmopm8Almchannel20PortEntry 5 }


pmopm8AlmChannel20BalancedPortn OBJECT-TYPE
	SYNTAX  EkiOnOff
	MAX-ACCESS read-only
	STATUS current
	DESCRIPTION
        "
        Channel Balanced 20 :This OID
         indicates that an in service channel
        is balanced by the Ekinops auto
        turn up application<Help> This
         status indicates that an in service
        channel is balanced by the Ekinops
        auto turn up application <Condtype>
        CHANNEL20_BALANCED_1 <Probcause>
        informationalStatus(1000) <Alarmtype>
        other (1) <Polarity> (2)
        "
	::= { pmopm8Almchannel20PortEntry 4 }


pmopm8AlmChannel20MismatchPortn OBJECT-TYPE
	SYNTAX  EkiOnOff
	MAX-ACCESS read-only
	STATUS current
	DESCRIPTION
        "
        Channel Mismatch 20 :This OID
         indicates that an out of service
        channel is detected on the Optical
        Power Monitoring input<Help> This
        alarm indicates that an out of
         service channel is detected on
        the Optical Power Monitoring input
        <Condtype> CHANNEL20_MISMATCH_1
        <Probcause> unexpectedInformation
        (75) <Alarmtype> equipmentAlarm
        <Polarity> (2)
        "
	::= { pmopm8Almchannel20PortEntry 3 }


pmopm8AlmChannel20AbsentPortn OBJECT-TYPE
	SYNTAX  EkiOnOff
	MAX-ACCESS read-only
	STATUS current
	DESCRIPTION
        "
        Channel Absent 20 :This OID indicates
        that an in service channel is absent
        on the Optical Power Monitoring
        input<Help> This alarm indicates
        that an in service channel is absent
        on the Optical Power Monitoring
        input <Condtype> CHANNEL20_ABSENT_1
        <Probcause> informationMissing
         (65) <Alarmtype> equipmentAlarm
        (5) <Polarity> (2)
        "
	::= { pmopm8Almchannel20PortEntry 2 }


--- *********************************************************
---     TABLE for the pmopm8Almchannel21Port articles
--- *********************************************************

pmopm8Almchannel21PortTable OBJECT-TYPE
	SYNTAX  SEQUENCE OF Pmopm8Almchannel21PortEntry
	MAX-ACCESS not-accessible
	STATUS current
	DESCRIPTION
        "
        List of pmopm8Almchannel21Port
        Article
        "
	::= { pmopm8AlmClientCrit 176 }


pmopm8Almchannel21PortEntry OBJECT-TYPE
	SYNTAX Pmopm8Almchannel21PortEntry
	MAX-ACCESS not-accessible
	STATUS current
	DESCRIPTION
        "
        Row definition for the pmopm8Almchannel21Port
        table
        "
	INDEX   { pmopm8Almchannel21PortIndex }
	::= { pmopm8Almchannel21PortTable 1 }


Pmopm8Almchannel21PortEntry ::=
	SEQUENCE {
	pmopm8Almchannel21PortIndex
		INTEGER,
	pmopm8AlmChannel21OosPortn
		EkiOnOff,
	pmopm8AlmChannel21PowerHighPortn
		EkiOnOff,
	pmopm8AlmChannel21PowerLowPortn
		EkiOnOff,
	pmopm8AlmChannel21BalancedPortn
		EkiOnOff,
	pmopm8AlmChannel21MismatchPortn
		EkiOnOff,
	pmopm8AlmChannel21AbsentPortn
		EkiOnOff
	}


pmopm8Almchannel21PortIndex OBJECT-TYPE
	SYNTAX  INTEGER(0..128)
	MAX-ACCESS  read-only
	STATUS current
	DESCRIPTION
        "
        Index definition for the pmopm8Almchannel21Port
        table
        "
	::= { pmopm8Almchannel21PortEntry 1 }


pmopm8AlmChannel21OosPortn OBJECT-TYPE
	SYNTAX  EkiOnOff
	MAX-ACCESS read-only
	STATUS current
	DESCRIPTION
        "
        Channel Out Of Service 21 :This
        OID indicates that the channel
         is out of service  <Help> This
        alarm indicates that the channel
        is in service <Condtype> CHANNEL21_OOS_1
        <Probcause> informationalStatus(1000)
        <Alarmtype> other (1) <Polarity>
        (2)
        "
	::= { pmopm8Almchannel21PortEntry 7 }


pmopm8AlmChannel21PowerHighPortn OBJECT-TYPE
	SYNTAX  EkiOnOff
	MAX-ACCESS read-only
	STATUS current
	DESCRIPTION
        "
        Channel Power High 21 :This OID
        indicates that the power of the
        channel is higher than the configured
        threshold<Help> This alarm indicates
        that the power of the channel is
        higher than the configured threshold
        <Condtype> CHANNEL21_POWER_HIGH_1
        <Probcause> degradedSignal (13)
        <Alarmtype> equipmentAlarm <Polarity>
        (2)
        "
	::= { pmopm8Almchannel21PortEntry 6 }


pmopm8AlmChannel21PowerLowPortn OBJECT-TYPE
	SYNTAX  EkiOnOff
	MAX-ACCESS read-only
	STATUS current
	DESCRIPTION
        "
        Channel Power Low 21 :This OID
        indicates that the power of the
        channel is lower than the configured
        threshold<Help> This alarm indicates
        that the power of the channel is
        lower than the configured threshold
        <Condtype> CHANNEL21_POWER_LOW_1
        <Probcause> degradedSignal (13)
        <Alarmtype> equipmentAlarm <Polarity>
        (2)
        "
	::= { pmopm8Almchannel21PortEntry 5 }


pmopm8AlmChannel21BalancedPortn OBJECT-TYPE
	SYNTAX  EkiOnOff
	MAX-ACCESS read-only
	STATUS current
	DESCRIPTION
        "
        Channel Balanced 21 :This OID
         indicates that an in service channel
        is balanced by the Ekinops auto
        turn up application<Help> This
         status indicates that an in service
        channel is balanced by the Ekinops
        auto turn up application <Condtype>
        CHANNEL21_BALANCED_1 <Probcause>
        informationalStatus(1000) <Alarmtype>
        other (1) <Polarity> (2)
        "
	::= { pmopm8Almchannel21PortEntry 4 }


pmopm8AlmChannel21MismatchPortn OBJECT-TYPE
	SYNTAX  EkiOnOff
	MAX-ACCESS read-only
	STATUS current
	DESCRIPTION
        "
        Channel Mismatch 21 :This OID
         indicates that an out of service
        channel is detected on the Optical
        Power Monitoring input<Help> This
        alarm indicates that an out of
         service channel is detected on
        the Optical Power Monitoring input
        <Condtype> CHANNEL21_MISMATCH_1
        <Probcause> unexpectedInformation
        (75) <Alarmtype> equipmentAlarm
        <Polarity> (2)
        "
	::= { pmopm8Almchannel21PortEntry 3 }


pmopm8AlmChannel21AbsentPortn OBJECT-TYPE
	SYNTAX  EkiOnOff
	MAX-ACCESS read-only
	STATUS current
	DESCRIPTION
        "
        Channel Absent 21 :This OID indicates
        that an in service channel is absent
        on the Optical Power Monitoring
        input<Help> This alarm indicates
        that an in service channel is absent
        on the Optical Power Monitoring
        input <Condtype> CHANNEL21_ABSENT_1
        <Probcause> informationMissing
         (65) <Alarmtype> equipmentAlarm
        (5) <Polarity> (2)
        "
	::= { pmopm8Almchannel21PortEntry 2 }


--- *********************************************************
---     TABLE for the pmopm8Almchannel22Port articles
--- *********************************************************

pmopm8Almchannel22PortTable OBJECT-TYPE
	SYNTAX  SEQUENCE OF Pmopm8Almchannel22PortEntry
	MAX-ACCESS not-accessible
	STATUS current
	DESCRIPTION
        "
        List of pmopm8Almchannel22Port
        Article
        "
	::= { pmopm8AlmClientCrit 184 }


pmopm8Almchannel22PortEntry OBJECT-TYPE
	SYNTAX Pmopm8Almchannel22PortEntry
	MAX-ACCESS not-accessible
	STATUS current
	DESCRIPTION
        "
        Row definition for the pmopm8Almchannel22Port
        table
        "
	INDEX   { pmopm8Almchannel22PortIndex }
	::= { pmopm8Almchannel22PortTable 1 }


Pmopm8Almchannel22PortEntry ::=
	SEQUENCE {
	pmopm8Almchannel22PortIndex
		INTEGER,
	pmopm8AlmChannel22OosPortn
		EkiOnOff,
	pmopm8AlmChannel22PowerHighPortn
		EkiOnOff,
	pmopm8AlmChannel22PowerLowPortn
		EkiOnOff,
	pmopm8AlmChannel22BalancedPortn
		EkiOnOff,
	pmopm8AlmChannel22MismatchPortn
		EkiOnOff,
	pmopm8AlmChannel22AbsentPortn
		EkiOnOff
	}


pmopm8Almchannel22PortIndex OBJECT-TYPE
	SYNTAX  INTEGER(0..128)
	MAX-ACCESS  read-only
	STATUS current
	DESCRIPTION
        "
        Index definition for the pmopm8Almchannel22Port
        table
        "
	::= { pmopm8Almchannel22PortEntry 1 }


pmopm8AlmChannel22OosPortn OBJECT-TYPE
	SYNTAX  EkiOnOff
	MAX-ACCESS read-only
	STATUS current
	DESCRIPTION
        "
        Channel Out Of Service 22 :This
        OID indicates that the channel
         is out of service  <Help> This
        alarm indicates that the channel
        is in service <Condtype> CHANNEL22_OOS_1
        <Probcause> informationalStatus(1000)
        <Alarmtype> other (1) <Polarity>
        (2)
        "
	::= { pmopm8Almchannel22PortEntry 7 }


pmopm8AlmChannel22PowerHighPortn OBJECT-TYPE
	SYNTAX  EkiOnOff
	MAX-ACCESS read-only
	STATUS current
	DESCRIPTION
        "
        Channel Power High 22 :This OID
        indicates that the power of the
        channel is higher than the configured
        threshold<Help> This alarm indicates
        that the power of the channel is
        higher than the configured threshold
        <Condtype> CHANNEL22_POWER_HIGH_1
        <Probcause> degradedSignal (13)
        <Alarmtype> equipmentAlarm <Polarity>
        (2)
        "
	::= { pmopm8Almchannel22PortEntry 6 }


pmopm8AlmChannel22PowerLowPortn OBJECT-TYPE
	SYNTAX  EkiOnOff
	MAX-ACCESS read-only
	STATUS current
	DESCRIPTION
        "
        Channel Power Low 22 :This OID
        indicates that the power of the
        channel is lower than the configured
        threshold<Help> This alarm indicates
        that the power of the channel is
        lower than the configured threshold
        <Condtype> CHANNEL22_POWER_LOW_1
        <Probcause> degradedSignal (13)
        <Alarmtype> equipmentAlarm <Polarity>
        (2)
        "
	::= { pmopm8Almchannel22PortEntry 5 }


pmopm8AlmChannel22BalancedPortn OBJECT-TYPE
	SYNTAX  EkiOnOff
	MAX-ACCESS read-only
	STATUS current
	DESCRIPTION
        "
        Channel Balanced 22 :This OID
         indicates that an in service channel
        is balanced by the Ekinops auto
        turn up application<Help> This
         status indicates that an in service
        channel is balanced by the Ekinops
        auto turn up application <Condtype>
        CHANNEL22_BALANCED_1 <Probcause>
        informationalStatus(1000) <Alarmtype>
        other (1) <Polarity> (2)
        "
	::= { pmopm8Almchannel22PortEntry 4 }


pmopm8AlmChannel22MismatchPortn OBJECT-TYPE
	SYNTAX  EkiOnOff
	MAX-ACCESS read-only
	STATUS current
	DESCRIPTION
        "
        Channel Mismatch 22 :This OID
         indicates that an out of service
        channel is detected on the Optical
        Power Monitoring input<Help> This
        alarm indicates that an out of
         service channel is detected on
        the Optical Power Monitoring input
        <Condtype> CHANNEL22_MISMATCH_1
        <Probcause> unexpectedInformation
        (75) <Alarmtype> equipmentAlarm
        <Polarity> (2)
        "
	::= { pmopm8Almchannel22PortEntry 3 }


pmopm8AlmChannel22AbsentPortn OBJECT-TYPE
	SYNTAX  EkiOnOff
	MAX-ACCESS read-only
	STATUS current
	DESCRIPTION
        "
        Channel Absent 22 :This OID indicates
        that an in service channel is absent
        on the Optical Power Monitoring
        input<Help> This alarm indicates
        that an in service channel is absent
        on the Optical Power Monitoring
        input <Condtype> CHANNEL22_ABSENT_1
        <Probcause> informationMissing
         (65) <Alarmtype> equipmentAlarm
        (5) <Polarity> (2)
        "
	::= { pmopm8Almchannel22PortEntry 2 }


--- *********************************************************
---     TABLE for the pmopm8Almchannel23Port articles
--- *********************************************************

pmopm8Almchannel23PortTable OBJECT-TYPE
	SYNTAX  SEQUENCE OF Pmopm8Almchannel23PortEntry
	MAX-ACCESS not-accessible
	STATUS current
	DESCRIPTION
        "
        List of pmopm8Almchannel23Port
        Article
        "
	::= { pmopm8AlmClientCrit 192 }


pmopm8Almchannel23PortEntry OBJECT-TYPE
	SYNTAX Pmopm8Almchannel23PortEntry
	MAX-ACCESS not-accessible
	STATUS current
	DESCRIPTION
        "
        Row definition for the pmopm8Almchannel23Port
        table
        "
	INDEX   { pmopm8Almchannel23PortIndex }
	::= { pmopm8Almchannel23PortTable 1 }


Pmopm8Almchannel23PortEntry ::=
	SEQUENCE {
	pmopm8Almchannel23PortIndex
		INTEGER,
	pmopm8AlmChannel23OosPortn
		EkiOnOff,
	pmopm8AlmChannel23PowerHighPortn
		EkiOnOff,
	pmopm8AlmChannel23PowerLowPortn
		EkiOnOff,
	pmopm8AlmChannel23BalancedPortn
		EkiOnOff,
	pmopm8AlmChannel23MismatchPortn
		EkiOnOff,
	pmopm8AlmChannel23AbsentPortn
		EkiOnOff
	}


pmopm8Almchannel23PortIndex OBJECT-TYPE
	SYNTAX  INTEGER(0..128)
	MAX-ACCESS  read-only
	STATUS current
	DESCRIPTION
        "
        Index definition for the pmopm8Almchannel23Port
        table
        "
	::= { pmopm8Almchannel23PortEntry 1 }


pmopm8AlmChannel23OosPortn OBJECT-TYPE
	SYNTAX  EkiOnOff
	MAX-ACCESS read-only
	STATUS current
	DESCRIPTION
        "
        Channel Out Of Service 23 :This
        OID indicates that the channel
         is out of service  <Help> This
        alarm indicates that the channel
        is in service <Condtype> CHANNEL23_OOS_1
        <Probcause> informationalStatus(1000)
        <Alarmtype> other (1) <Polarity>
        (2)
        "
	::= { pmopm8Almchannel23PortEntry 7 }


pmopm8AlmChannel23PowerHighPortn OBJECT-TYPE
	SYNTAX  EkiOnOff
	MAX-ACCESS read-only
	STATUS current
	DESCRIPTION
        "
        Channel Power High 23 :This OID
        indicates that the power of the
        channel is higher than the configured
        threshold<Help> This alarm indicates
        that the power of the channel is
        higher than the configured threshold
        <Condtype> CHANNEL23_POWER_HIGH_1
        <Probcause> degradedSignal (13)
        <Alarmtype> equipmentAlarm <Polarity>
        (2)
        "
	::= { pmopm8Almchannel23PortEntry 6 }


pmopm8AlmChannel23PowerLowPortn OBJECT-TYPE
	SYNTAX  EkiOnOff
	MAX-ACCESS read-only
	STATUS current
	DESCRIPTION
        "
        Channel Power Low 23 :This OID
        indicates that the power of the
        channel is lower than the configured
        threshold<Help> This alarm indicates
        that the power of the channel is
        lower than the configured threshold
        <Condtype> CHANNEL23_POWER_LOW_1
        <Probcause> degradedSignal (13)
        <Alarmtype> equipmentAlarm <Polarity>
        (2)
        "
	::= { pmopm8Almchannel23PortEntry 5 }


pmopm8AlmChannel23BalancedPortn OBJECT-TYPE
	SYNTAX  EkiOnOff
	MAX-ACCESS read-only
	STATUS current
	DESCRIPTION
        "
        Channel Balanced 23 :This OID
         indicates that an in service channel
        is balanced by the Ekinops auto
        turn up application<Help> This
         status indicates that an in service
        channel is balanced by the Ekinops
        auto turn up application <Condtype>
        CHANNEL23_BALANCED_1 <Probcause>
        informationalStatus(1000) <Alarmtype>
        other (1) <Polarity> (2)
        "
	::= { pmopm8Almchannel23PortEntry 4 }


pmopm8AlmChannel23MismatchPortn OBJECT-TYPE
	SYNTAX  EkiOnOff
	MAX-ACCESS read-only
	STATUS current
	DESCRIPTION
        "
        Channel Mismatch 23 :This OID
         indicates that an out of service
        channel is detected on the Optical
        Power Monitoring input<Help> This
        alarm indicates that an out of
         service channel is detected on
        the Optical Power Monitoring input
        <Condtype> CHANNEL23_MISMATCH_1
        <Probcause> unexpectedInformation
        (75) <Alarmtype> equipmentAlarm
        <Polarity> (2)
        "
	::= { pmopm8Almchannel23PortEntry 3 }


pmopm8AlmChannel23AbsentPortn OBJECT-TYPE
	SYNTAX  EkiOnOff
	MAX-ACCESS read-only
	STATUS current
	DESCRIPTION
        "
        Channel Absent 23 :This OID indicates
        that an in service channel is absent
        on the Optical Power Monitoring
        input<Help> This alarm indicates
        that an in service channel is absent
        on the Optical Power Monitoring
        input <Condtype> CHANNEL23_ABSENT_1
        <Probcause> informationMissing
         (65) <Alarmtype> equipmentAlarm
        (5) <Polarity> (2)
        "
	::= { pmopm8Almchannel23PortEntry 2 }


--- *********************************************************
---     TABLE for the pmopm8Almchannel24Port articles
--- *********************************************************

pmopm8Almchannel24PortTable OBJECT-TYPE
	SYNTAX  SEQUENCE OF Pmopm8Almchannel24PortEntry
	MAX-ACCESS not-accessible
	STATUS current
	DESCRIPTION
        "
        List of pmopm8Almchannel24Port
        Article
        "
	::= { pmopm8AlmClientCrit 200 }


pmopm8Almchannel24PortEntry OBJECT-TYPE
	SYNTAX Pmopm8Almchannel24PortEntry
	MAX-ACCESS not-accessible
	STATUS current
	DESCRIPTION
        "
        Row definition for the pmopm8Almchannel24Port
        table
        "
	INDEX   { pmopm8Almchannel24PortIndex }
	::= { pmopm8Almchannel24PortTable 1 }


Pmopm8Almchannel24PortEntry ::=
	SEQUENCE {
	pmopm8Almchannel24PortIndex
		INTEGER,
	pmopm8AlmChannel24OosPortn
		EkiOnOff,
	pmopm8AlmChannel24PowerHighPortn
		EkiOnOff,
	pmopm8AlmChannel24PowerLowPortn
		EkiOnOff,
	pmopm8AlmChannel24BalancedPortn
		EkiOnOff,
	pmopm8AlmChannel24MismatchPortn
		EkiOnOff,
	pmopm8AlmChannel24AbsentPortn
		EkiOnOff
	}


pmopm8Almchannel24PortIndex OBJECT-TYPE
	SYNTAX  INTEGER(0..128)
	MAX-ACCESS  read-only
	STATUS current
	DESCRIPTION
        "
        Index definition for the pmopm8Almchannel24Port
        table
        "
	::= { pmopm8Almchannel24PortEntry 1 }


pmopm8AlmChannel24OosPortn OBJECT-TYPE
	SYNTAX  EkiOnOff
	MAX-ACCESS read-only
	STATUS current
	DESCRIPTION
        "
        Channel Out Of Service 24 :This
        OID indicates that the channel
         is out of service  <Help> This
        alarm indicates that the channel
        is in service <Condtype> CHANNEL24_OOS_1
        <Probcause> informationalStatus(1000)
        <Alarmtype> other (1) <Polarity>
        (2)
        "
	::= { pmopm8Almchannel24PortEntry 7 }


pmopm8AlmChannel24PowerHighPortn OBJECT-TYPE
	SYNTAX  EkiOnOff
	MAX-ACCESS read-only
	STATUS current
	DESCRIPTION
        "
        Channel Power High 24 :This OID
        indicates that the power of the
        channel is higher than the configured
        threshold<Help> This alarm indicates
        that the power of the channel is
        higher than the configured threshold
        <Condtype> CHANNEL24_POWER_HIGH_1
        <Probcause> degradedSignal (13)
        <Alarmtype> equipmentAlarm <Polarity>
        (2)
        "
	::= { pmopm8Almchannel24PortEntry 6 }


pmopm8AlmChannel24PowerLowPortn OBJECT-TYPE
	SYNTAX  EkiOnOff
	MAX-ACCESS read-only
	STATUS current
	DESCRIPTION
        "
        Channel Power Low 24 :This OID
        indicates that the power of the
        channel is lower than the configured
        threshold<Help> This alarm indicates
        that the power of the channel is
        lower than the configured threshold
        <Condtype> CHANNEL24_POWER_LOW_1
        <Probcause> degradedSignal (13)
        <Alarmtype> equipmentAlarm <Polarity>
        (2)
        "
	::= { pmopm8Almchannel24PortEntry 5 }


pmopm8AlmChannel24BalancedPortn OBJECT-TYPE
	SYNTAX  EkiOnOff
	MAX-ACCESS read-only
	STATUS current
	DESCRIPTION
        "
        Channel Balanced 24 :This OID
         indicates that an in service channel
        is balanced by the Ekinops auto
        turn up application<Help> This
         status indicates that an in service
        channel is balanced by the Ekinops
        auto turn up application <Condtype>
        CHANNEL24_BALANCED_1 <Probcause>
        informationalStatus(1000) <Alarmtype>
        other (1) <Polarity> (2)
        "
	::= { pmopm8Almchannel24PortEntry 4 }


pmopm8AlmChannel24MismatchPortn OBJECT-TYPE
	SYNTAX  EkiOnOff
	MAX-ACCESS read-only
	STATUS current
	DESCRIPTION
        "
        Channel Mismatch 24 :This OID
         indicates that an out of service
        channel is detected on the Optical
        Power Monitoring input<Help> This
        alarm indicates that an out of
         service channel is detected on
        the Optical Power Monitoring input
        <Condtype> CHANNEL24_MISMATCH_1
        <Probcause> unexpectedInformation
        (75) <Alarmtype> equipmentAlarm
        <Polarity> (2)
        "
	::= { pmopm8Almchannel24PortEntry 3 }


pmopm8AlmChannel24AbsentPortn OBJECT-TYPE
	SYNTAX  EkiOnOff
	MAX-ACCESS read-only
	STATUS current
	DESCRIPTION
        "
        Channel Absent 24 :This OID indicates
        that an in service channel is absent
        on the Optical Power Monitoring
        input<Help> This alarm indicates
        that an in service channel is absent
        on the Optical Power Monitoring
        input <Condtype> CHANNEL24_ABSENT_1
        <Probcause> informationMissing
         (65) <Alarmtype> equipmentAlarm
        (5) <Polarity> (2)
        "
	::= { pmopm8Almchannel24PortEntry 2 }


--- *********************************************************
---     TABLE for the pmopm8Almchannel25Port articles
--- *********************************************************

pmopm8Almchannel25PortTable OBJECT-TYPE
	SYNTAX  SEQUENCE OF Pmopm8Almchannel25PortEntry
	MAX-ACCESS not-accessible
	STATUS current
	DESCRIPTION
        "
        List of pmopm8Almchannel25Port
        Article
        "
	::= { pmopm8AlmClientCrit 208 }


pmopm8Almchannel25PortEntry OBJECT-TYPE
	SYNTAX Pmopm8Almchannel25PortEntry
	MAX-ACCESS not-accessible
	STATUS current
	DESCRIPTION
        "
        Row definition for the pmopm8Almchannel25Port
        table
        "
	INDEX   { pmopm8Almchannel25PortIndex }
	::= { pmopm8Almchannel25PortTable 1 }


Pmopm8Almchannel25PortEntry ::=
	SEQUENCE {
	pmopm8Almchannel25PortIndex
		INTEGER,
	pmopm8AlmChannel25OosPortn
		EkiOnOff,
	pmopm8AlmChannel25PowerHighPortn
		EkiOnOff,
	pmopm8AlmChannel25PowerLowPortn
		EkiOnOff,
	pmopm8AlmChannel25BalancedPortn
		EkiOnOff,
	pmopm8AlmChannel25MismatchPortn
		EkiOnOff,
	pmopm8AlmChannel25AbsentPortn
		EkiOnOff
	}


pmopm8Almchannel25PortIndex OBJECT-TYPE
	SYNTAX  INTEGER(0..128)
	MAX-ACCESS  read-only
	STATUS current
	DESCRIPTION
        "
        Index definition for the pmopm8Almchannel25Port
        table
        "
	::= { pmopm8Almchannel25PortEntry 1 }


pmopm8AlmChannel25OosPortn OBJECT-TYPE
	SYNTAX  EkiOnOff
	MAX-ACCESS read-only
	STATUS current
	DESCRIPTION
        "
        Channel Out Of Service 25 :This
        OID indicates that the channel
         is out of service  <Help> This
        alarm indicates that the channel
        is in service <Condtype> CHANNEL25_OOS_1
        <Probcause> informationalStatus(1000)
        <Alarmtype> other (1) <Polarity>
        (2)
        "
	::= { pmopm8Almchannel25PortEntry 7 }


pmopm8AlmChannel25PowerHighPortn OBJECT-TYPE
	SYNTAX  EkiOnOff
	MAX-ACCESS read-only
	STATUS current
	DESCRIPTION
        "
        Channel Power High 25 :This OID
        indicates that the power of the
        channel is higher than the configured
        threshold<Help> This alarm indicates
        that the power of the channel is
        higher than the configured threshold
        <Condtype> CHANNEL25_POWER_HIGH_1
        <Probcause> degradedSignal (13)
        <Alarmtype> equipmentAlarm <Polarity>
        (2)
        "
	::= { pmopm8Almchannel25PortEntry 6 }


pmopm8AlmChannel25PowerLowPortn OBJECT-TYPE
	SYNTAX  EkiOnOff
	MAX-ACCESS read-only
	STATUS current
	DESCRIPTION
        "
        Channel Power Low 25 :This OID
        indicates that the power of the
        channel is lower than the configured
        threshold<Help> This alarm indicates
        that the power of the channel is
        lower than the configured threshold
        <Condtype> CHANNEL25_POWER_LOW_1
        <Probcause> degradedSignal (13)
        <Alarmtype> equipmentAlarm <Polarity>
        (2)
        "
	::= { pmopm8Almchannel25PortEntry 5 }


pmopm8AlmChannel25BalancedPortn OBJECT-TYPE
	SYNTAX  EkiOnOff
	MAX-ACCESS read-only
	STATUS current
	DESCRIPTION
        "
        Channel Balanced 25 :This OID
         indicates that an in service channel
        is balanced by the Ekinops auto
        turn up application<Help> This
         status indicates that an in service
        channel is balanced by the Ekinops
        auto turn up application <Condtype>
        CHANNEL25_BALANCED_1 <Probcause>
        informationalStatus(1000) <Alarmtype>
        other (1) <Polarity> (2)
        "
	::= { pmopm8Almchannel25PortEntry 4 }


pmopm8AlmChannel25MismatchPortn OBJECT-TYPE
	SYNTAX  EkiOnOff
	MAX-ACCESS read-only
	STATUS current
	DESCRIPTION
        "
        Channel Mismatch 25 :This OID
         indicates that an out of service
        channel is detected on the Optical
        Power Monitoring input<Help> This
        alarm indicates that an out of
         service channel is detected on
        the Optical Power Monitoring input
        <Condtype> CHANNEL25_MISMATCH_1
        <Probcause> unexpectedInformation
        (75) <Alarmtype> equipmentAlarm
        <Polarity> (2)
        "
	::= { pmopm8Almchannel25PortEntry 3 }


pmopm8AlmChannel25AbsentPortn OBJECT-TYPE
	SYNTAX  EkiOnOff
	MAX-ACCESS read-only
	STATUS current
	DESCRIPTION
        "
        Channel Absent 25 :This OID indicates
        that an in service channel is absent
        on the Optical Power Monitoring
        input<Help> This alarm indicates
        that an in service channel is absent
        on the Optical Power Monitoring
        input <Condtype> CHANNEL25_ABSENT_1
        <Probcause> informationMissing
         (65) <Alarmtype> equipmentAlarm
        (5) <Polarity> (2)
        "
	::= { pmopm8Almchannel25PortEntry 2 }


--- *********************************************************
---     TABLE for the pmopm8Almchannel26Port articles
--- *********************************************************

pmopm8Almchannel26PortTable OBJECT-TYPE
	SYNTAX  SEQUENCE OF Pmopm8Almchannel26PortEntry
	MAX-ACCESS not-accessible
	STATUS current
	DESCRIPTION
        "
        List of pmopm8Almchannel26Port
        Article
        "
	::= { pmopm8AlmClientCrit 216 }


pmopm8Almchannel26PortEntry OBJECT-TYPE
	SYNTAX Pmopm8Almchannel26PortEntry
	MAX-ACCESS not-accessible
	STATUS current
	DESCRIPTION
        "
        Row definition for the pmopm8Almchannel26Port
        table
        "
	INDEX   { pmopm8Almchannel26PortIndex }
	::= { pmopm8Almchannel26PortTable 1 }


Pmopm8Almchannel26PortEntry ::=
	SEQUENCE {
	pmopm8Almchannel26PortIndex
		INTEGER,
	pmopm8AlmChannel26OosPortn
		EkiOnOff,
	pmopm8AlmChannel26PowerHighPortn
		EkiOnOff,
	pmopm8AlmChannel26PowerLowPortn
		EkiOnOff,
	pmopm8AlmChannel26BalancedPortn
		EkiOnOff,
	pmopm8AlmChannel26MismatchPortn
		EkiOnOff,
	pmopm8AlmChannel26AbsentPortn
		EkiOnOff
	}


pmopm8Almchannel26PortIndex OBJECT-TYPE
	SYNTAX  INTEGER(0..128)
	MAX-ACCESS  read-only
	STATUS current
	DESCRIPTION
        "
        Index definition for the pmopm8Almchannel26Port
        table
        "
	::= { pmopm8Almchannel26PortEntry 1 }


pmopm8AlmChannel26OosPortn OBJECT-TYPE
	SYNTAX  EkiOnOff
	MAX-ACCESS read-only
	STATUS current
	DESCRIPTION
        "
        Channel Out Of Service 26 :This
        OID indicates that the channel
         is out of service  <Help> This
        alarm indicates that the channel
        is in service <Condtype> CHANNEL26_OOS_1
        <Probcause> informationalStatus(1000)
        <Alarmtype> other (1) <Polarity>
        (2)
        "
	::= { pmopm8Almchannel26PortEntry 7 }


pmopm8AlmChannel26PowerHighPortn OBJECT-TYPE
	SYNTAX  EkiOnOff
	MAX-ACCESS read-only
	STATUS current
	DESCRIPTION
        "
        Channel Power High 26 :This OID
        indicates that the power of the
        channel is higher than the configured
        threshold<Help> This alarm indicates
        that the power of the channel is
        higher than the configured threshold
        <Condtype> CHANNEL26_POWER_HIGH_1
        <Probcause> degradedSignal (13)
        <Alarmtype> equipmentAlarm <Polarity>
        (2)
        "
	::= { pmopm8Almchannel26PortEntry 6 }


pmopm8AlmChannel26PowerLowPortn OBJECT-TYPE
	SYNTAX  EkiOnOff
	MAX-ACCESS read-only
	STATUS current
	DESCRIPTION
        "
        Channel Power Low 26 :This OID
        indicates that the power of the
        channel is lower than the configured
        threshold<Help> This alarm indicates
        that the power of the channel is
        lower than the configured threshold
        <Condtype> CHANNEL26_POWER_LOW_1
        <Probcause> degradedSignal (13)
        <Alarmtype> equipmentAlarm <Polarity>
        (2)
        "
	::= { pmopm8Almchannel26PortEntry 5 }


pmopm8AlmChannel26BalancedPortn OBJECT-TYPE
	SYNTAX  EkiOnOff
	MAX-ACCESS read-only
	STATUS current
	DESCRIPTION
        "
        Channel Balanced 26 :This OID
         indicates that an in service channel
        is balanced by the Ekinops auto
        turn up application<Help> This
         status indicates that an in service
        channel is balanced by the Ekinops
        auto turn up application <Condtype>
        CHANNEL26_BALANCED_1 <Probcause>
        informationalStatus(1000) <Alarmtype>
        other (1) <Polarity> (2)
        "
	::= { pmopm8Almchannel26PortEntry 4 }


pmopm8AlmChannel26MismatchPortn OBJECT-TYPE
	SYNTAX  EkiOnOff
	MAX-ACCESS read-only
	STATUS current
	DESCRIPTION
        "
        Channel Mismatch 26 :This OID
         indicates that an out of service
        channel is detected on the Optical
        Power Monitoring input<Help> This
        alarm indicates that an out of
         service channel is detected on
        the Optical Power Monitoring input
        <Condtype> CHANNEL26_MISMATCH_1
        <Probcause> unexpectedInformation
        (75) <Alarmtype> equipmentAlarm
        <Polarity> (2)
        "
	::= { pmopm8Almchannel26PortEntry 3 }


pmopm8AlmChannel26AbsentPortn OBJECT-TYPE
	SYNTAX  EkiOnOff
	MAX-ACCESS read-only
	STATUS current
	DESCRIPTION
        "
        Channel Absent 26 :This OID indicates
        that an in service channel is absent
        on the Optical Power Monitoring
        input<Help> This alarm indicates
        that an in service channel is absent
        on the Optical Power Monitoring
        input <Condtype> CHANNEL26_ABSENT_1
        <Probcause> informationMissing
         (65) <Alarmtype> equipmentAlarm
        (5) <Polarity> (2)
        "
	::= { pmopm8Almchannel26PortEntry 2 }


--- *********************************************************
---     TABLE for the pmopm8Almchannel27Port articles
--- *********************************************************

pmopm8Almchannel27PortTable OBJECT-TYPE
	SYNTAX  SEQUENCE OF Pmopm8Almchannel27PortEntry
	MAX-ACCESS not-accessible
	STATUS current
	DESCRIPTION
        "
        List of pmopm8Almchannel27Port
        Article
        "
	::= { pmopm8AlmClientCrit 224 }


pmopm8Almchannel27PortEntry OBJECT-TYPE
	SYNTAX Pmopm8Almchannel27PortEntry
	MAX-ACCESS not-accessible
	STATUS current
	DESCRIPTION
        "
        Row definition for the pmopm8Almchannel27Port
        table
        "
	INDEX   { pmopm8Almchannel27PortIndex }
	::= { pmopm8Almchannel27PortTable 1 }


Pmopm8Almchannel27PortEntry ::=
	SEQUENCE {
	pmopm8Almchannel27PortIndex
		INTEGER,
	pmopm8AlmChannel27OosPortn
		EkiOnOff,
	pmopm8AlmChannel27PowerHighPortn
		EkiOnOff,
	pmopm8AlmChannel27PowerLowPortn
		EkiOnOff,
	pmopm8AlmChannel27BalancedPortn
		EkiOnOff,
	pmopm8AlmChannel27MismatchPortn
		EkiOnOff,
	pmopm8AlmChannel27AbsentPortn
		EkiOnOff
	}


pmopm8Almchannel27PortIndex OBJECT-TYPE
	SYNTAX  INTEGER(0..128)
	MAX-ACCESS  read-only
	STATUS current
	DESCRIPTION
        "
        Index definition for the pmopm8Almchannel27Port
        table
        "
	::= { pmopm8Almchannel27PortEntry 1 }


pmopm8AlmChannel27OosPortn OBJECT-TYPE
	SYNTAX  EkiOnOff
	MAX-ACCESS read-only
	STATUS current
	DESCRIPTION
        "
        Channel Out Of Service 27 :This
        OID indicates that the channel
         is out of service  <Help> This
        alarm indicates that the channel
        is in service <Condtype> CHANNEL27_OOS_1
        <Probcause> informationalStatus(1000)
        <Alarmtype> other (1) <Polarity>
        (2)
        "
	::= { pmopm8Almchannel27PortEntry 7 }


pmopm8AlmChannel27PowerHighPortn OBJECT-TYPE
	SYNTAX  EkiOnOff
	MAX-ACCESS read-only
	STATUS current
	DESCRIPTION
        "
        Channel Power High 27 :This OID
        indicates that the power of the
        channel is higher than the configured
        threshold<Help> This alarm indicates
        that the power of the channel is
        higher than the configured threshold
        <Condtype> CHANNEL27_POWER_HIGH_1
        <Probcause> degradedSignal (13)
        <Alarmtype> equipmentAlarm <Polarity>
        (2)
        "
	::= { pmopm8Almchannel27PortEntry 6 }


pmopm8AlmChannel27PowerLowPortn OBJECT-TYPE
	SYNTAX  EkiOnOff
	MAX-ACCESS read-only
	STATUS current
	DESCRIPTION
        "
        Channel Power Low 27 :This OID
        indicates that the power of the
        channel is lower than the configured
        threshold<Help> This alarm indicates
        that the power of the channel is
        lower than the configured threshold
        <Condtype> CHANNEL27_POWER_LOW_1
        <Probcause> degradedSignal (13)
        <Alarmtype> equipmentAlarm <Polarity>
        (2)
        "
	::= { pmopm8Almchannel27PortEntry 5 }


pmopm8AlmChannel27BalancedPortn OBJECT-TYPE
	SYNTAX  EkiOnOff
	MAX-ACCESS read-only
	STATUS current
	DESCRIPTION
        "
        Channel Balanced 27 :This OID
         indicates that an in service channel
        is balanced by the Ekinops auto
        turn up application<Help> This
         status indicates that an in service
        channel is balanced by the Ekinops
        auto turn up application <Condtype>
        CHANNEL27_BALANCED_1 <Probcause>
        informationalStatus(1000) <Alarmtype>
        other (1) <Polarity> (2)
        "
	::= { pmopm8Almchannel27PortEntry 4 }


pmopm8AlmChannel27MismatchPortn OBJECT-TYPE
	SYNTAX  EkiOnOff
	MAX-ACCESS read-only
	STATUS current
	DESCRIPTION
        "
        Channel Mismatch 27 :This OID
         indicates that an out of service
        channel is detected on the Optical
        Power Monitoring input<Help> This
        alarm indicates that an out of
         service channel is detected on
        the Optical Power Monitoring input
        <Condtype> CHANNEL27_MISMATCH_1
        <Probcause> unexpectedInformation
        (75) <Alarmtype> equipmentAlarm
        <Polarity> (2)
        "
	::= { pmopm8Almchannel27PortEntry 3 }


pmopm8AlmChannel27AbsentPortn OBJECT-TYPE
	SYNTAX  EkiOnOff
	MAX-ACCESS read-only
	STATUS current
	DESCRIPTION
        "
        Channel Absent 27 :This OID indicates
        that an in service channel is absent
        on the Optical Power Monitoring
        input<Help> This alarm indicates
        that an in service channel is absent
        on the Optical Power Monitoring
        input <Condtype> CHANNEL27_ABSENT_1
        <Probcause> informationMissing
         (65) <Alarmtype> equipmentAlarm
        (5) <Polarity> (2)
        "
	::= { pmopm8Almchannel27PortEntry 2 }


--- *********************************************************
---     TABLE for the pmopm8Almchannel28Port articles
--- *********************************************************

pmopm8Almchannel28PortTable OBJECT-TYPE
	SYNTAX  SEQUENCE OF Pmopm8Almchannel28PortEntry
	MAX-ACCESS not-accessible
	STATUS current
	DESCRIPTION
        "
        List of pmopm8Almchannel28Port
        Article
        "
	::= { pmopm8AlmClientCrit 232 }


pmopm8Almchannel28PortEntry OBJECT-TYPE
	SYNTAX Pmopm8Almchannel28PortEntry
	MAX-ACCESS not-accessible
	STATUS current
	DESCRIPTION
        "
        Row definition for the pmopm8Almchannel28Port
        table
        "
	INDEX   { pmopm8Almchannel28PortIndex }
	::= { pmopm8Almchannel28PortTable 1 }


Pmopm8Almchannel28PortEntry ::=
	SEQUENCE {
	pmopm8Almchannel28PortIndex
		INTEGER,
	pmopm8AlmChannel28OosPortn
		EkiOnOff,
	pmopm8AlmChannel28PowerHighPortn
		EkiOnOff,
	pmopm8AlmChannel28PowerLowPortn
		EkiOnOff,
	pmopm8AlmChannel28BalancedPortn
		EkiOnOff,
	pmopm8AlmChannel28MismatchPortn
		EkiOnOff,
	pmopm8AlmChannel28AbsentPortn
		EkiOnOff
	}


pmopm8Almchannel28PortIndex OBJECT-TYPE
	SYNTAX  INTEGER(0..128)
	MAX-ACCESS  read-only
	STATUS current
	DESCRIPTION
        "
        Index definition for the pmopm8Almchannel28Port
        table
        "
	::= { pmopm8Almchannel28PortEntry 1 }


pmopm8AlmChannel28OosPortn OBJECT-TYPE
	SYNTAX  EkiOnOff
	MAX-ACCESS read-only
	STATUS current
	DESCRIPTION
        "
        Channel Out Of Service 28 :This
        OID indicates that the channel
         is out of service  <Help> This
        alarm indicates that the channel
        is in service <Condtype> CHANNEL28_OOS_1
        <Probcause> informationalStatus(1000)
        <Alarmtype> other (1) <Polarity>
        (2)
        "
	::= { pmopm8Almchannel28PortEntry 7 }


pmopm8AlmChannel28PowerHighPortn OBJECT-TYPE
	SYNTAX  EkiOnOff
	MAX-ACCESS read-only
	STATUS current
	DESCRIPTION
        "
        Channel Power High 28 :This OID
        indicates that the power of the
        channel is higher than the configured
        threshold<Help> This alarm indicates
        that the power of the channel is
        higher than the configured threshold
        <Condtype> CHANNEL28_POWER_HIGH_1
        <Probcause> degradedSignal (13)
        <Alarmtype> equipmentAlarm <Polarity>
        (2)
        "
	::= { pmopm8Almchannel28PortEntry 6 }


pmopm8AlmChannel28PowerLowPortn OBJECT-TYPE
	SYNTAX  EkiOnOff
	MAX-ACCESS read-only
	STATUS current
	DESCRIPTION
        "
        Channel Power Low 28 :This OID
        indicates that the power of the
        channel is lower than the configured
        threshold<Help> This alarm indicates
        that the power of the channel is
        lower than the configured threshold
        <Condtype> CHANNEL28_POWER_LOW_1
        <Probcause> degradedSignal (13)
        <Alarmtype> equipmentAlarm <Polarity>
        (2)
        "
	::= { pmopm8Almchannel28PortEntry 5 }


pmopm8AlmChannel28BalancedPortn OBJECT-TYPE
	SYNTAX  EkiOnOff
	MAX-ACCESS read-only
	STATUS current
	DESCRIPTION
        "
        Channel Balanced 28 :This OID
         indicates that an in service channel
        is balanced by the Ekinops auto
        turn up application<Help> This
         status indicates that an in service
        channel is balanced by the Ekinops
        auto turn up application <Condtype>
        CHANNEL28_BALANCED_1 <Probcause>
        informationalStatus(1000) <Alarmtype>
        other (1) <Polarity> (2)
        "
	::= { pmopm8Almchannel28PortEntry 4 }


pmopm8AlmChannel28MismatchPortn OBJECT-TYPE
	SYNTAX  EkiOnOff
	MAX-ACCESS read-only
	STATUS current
	DESCRIPTION
        "
        Channel Mismatch 28 :This OID
         indicates that an out of service
        channel is detected on the Optical
        Power Monitoring input<Help> This
        alarm indicates that an out of
         service channel is detected on
        the Optical Power Monitoring input
        <Condtype> CHANNEL28_MISMATCH_1
        <Probcause> unexpectedInformation
        (75) <Alarmtype> equipmentAlarm
        <Polarity> (2)
        "
	::= { pmopm8Almchannel28PortEntry 3 }


pmopm8AlmChannel28AbsentPortn OBJECT-TYPE
	SYNTAX  EkiOnOff
	MAX-ACCESS read-only
	STATUS current
	DESCRIPTION
        "
        Channel Absent 28 :This OID indicates
        that an in service channel is absent
        on the Optical Power Monitoring
        input<Help> This alarm indicates
        that an in service channel is absent
        on the Optical Power Monitoring
        input <Condtype> CHANNEL28_ABSENT_1
        <Probcause> informationMissing
         (65) <Alarmtype> equipmentAlarm
        (5) <Polarity> (2)
        "
	::= { pmopm8Almchannel28PortEntry 2 }


--- *********************************************************
---     TABLE for the pmopm8Almchannel29Port articles
--- *********************************************************

pmopm8Almchannel29PortTable OBJECT-TYPE
	SYNTAX  SEQUENCE OF Pmopm8Almchannel29PortEntry
	MAX-ACCESS not-accessible
	STATUS current
	DESCRIPTION
        "
        List of pmopm8Almchannel29Port
        Article
        "
	::= { pmopm8AlmClientCrit 240 }


pmopm8Almchannel29PortEntry OBJECT-TYPE
	SYNTAX Pmopm8Almchannel29PortEntry
	MAX-ACCESS not-accessible
	STATUS current
	DESCRIPTION
        "
        Row definition for the pmopm8Almchannel29Port
        table
        "
	INDEX   { pmopm8Almchannel29PortIndex }
	::= { pmopm8Almchannel29PortTable 1 }


Pmopm8Almchannel29PortEntry ::=
	SEQUENCE {
	pmopm8Almchannel29PortIndex
		INTEGER,
	pmopm8AlmChannel29OosPortn
		EkiOnOff,
	pmopm8AlmChannel29PowerHighPortn
		EkiOnOff,
	pmopm8AlmChannel29PowerLowPortn
		EkiOnOff,
	pmopm8AlmChannel29BalancedPortn
		EkiOnOff,
	pmopm8AlmChannel29MismatchPortn
		EkiOnOff,
	pmopm8AlmChannel29AbsentPortn
		EkiOnOff
	}


pmopm8Almchannel29PortIndex OBJECT-TYPE
	SYNTAX  INTEGER(0..128)
	MAX-ACCESS  read-only
	STATUS current
	DESCRIPTION
        "
        Index definition for the pmopm8Almchannel29Port
        table
        "
	::= { pmopm8Almchannel29PortEntry 1 }


pmopm8AlmChannel29OosPortn OBJECT-TYPE
	SYNTAX  EkiOnOff
	MAX-ACCESS read-only
	STATUS current
	DESCRIPTION
        "
        Channel Out Of Service 29 :This
        OID indicates that the channel
         is out of service  <Help> This
        alarm indicates that the channel
        is in service <Condtype> CHANNEL29_OOS_1
        <Probcause> informationalStatus(1000)
        <Alarmtype> other (1) <Polarity>
        (2)
        "
	::= { pmopm8Almchannel29PortEntry 7 }


pmopm8AlmChannel29PowerHighPortn OBJECT-TYPE
	SYNTAX  EkiOnOff
	MAX-ACCESS read-only
	STATUS current
	DESCRIPTION
        "
        Channel Power High 29 :This OID
        indicates that the power of the
        channel is higher than the configured
        threshold<Help> This alarm indicates
        that the power of the channel is
        higher than the configured threshold
        <Condtype> CHANNEL29_POWER_HIGH_1
        <Probcause> degradedSignal (13)
        <Alarmtype> equipmentAlarm <Polarity>
        (2)
        "
	::= { pmopm8Almchannel29PortEntry 6 }


pmopm8AlmChannel29PowerLowPortn OBJECT-TYPE
	SYNTAX  EkiOnOff
	MAX-ACCESS read-only
	STATUS current
	DESCRIPTION
        "
        Channel Power Low 29 :This OID
        indicates that the power of the
        channel is lower than the configured
        threshold<Help> This alarm indicates
        that the power of the channel is
        lower than the configured threshold
        <Condtype> CHANNEL29_POWER_LOW_1
        <Probcause> degradedSignal (13)
        <Alarmtype> equipmentAlarm <Polarity>
        (2)
        "
	::= { pmopm8Almchannel29PortEntry 5 }


pmopm8AlmChannel29BalancedPortn OBJECT-TYPE
	SYNTAX  EkiOnOff
	MAX-ACCESS read-only
	STATUS current
	DESCRIPTION
        "
        Channel Balanced 29 :This OID
         indicates that an in service channel
        is balanced by the Ekinops auto
        turn up application<Help> This
         status indicates that an in service
        channel is balanced by the Ekinops
        auto turn up application <Condtype>
        CHANNEL29_BALANCED_1 <Probcause>
        informationalStatus(1000) <Alarmtype>
        other (1) <Polarity> (2)
        "
	::= { pmopm8Almchannel29PortEntry 4 }


pmopm8AlmChannel29MismatchPortn OBJECT-TYPE
	SYNTAX  EkiOnOff
	MAX-ACCESS read-only
	STATUS current
	DESCRIPTION
        "
        Channel Mismatch 29 :This OID
         indicates that an out of service
        channel is detected on the Optical
        Power Monitoring input<Help> This
        alarm indicates that an out of
         service channel is detected on
        the Optical Power Monitoring input
        <Condtype> CHANNEL29_MISMATCH_1
        <Probcause> unexpectedInformation
        (75) <Alarmtype> equipmentAlarm
        <Polarity> (2)
        "
	::= { pmopm8Almchannel29PortEntry 3 }


pmopm8AlmChannel29AbsentPortn OBJECT-TYPE
	SYNTAX  EkiOnOff
	MAX-ACCESS read-only
	STATUS current
	DESCRIPTION
        "
        Channel Absent 29 :This OID indicates
        that an in service channel is absent
        on the Optical Power Monitoring
        input<Help> This alarm indicates
        that an in service channel is absent
        on the Optical Power Monitoring
        input <Condtype> CHANNEL29_ABSENT_1
        <Probcause> informationMissing
         (65) <Alarmtype> equipmentAlarm
        (5) <Polarity> (2)
        "
	::= { pmopm8Almchannel29PortEntry 2 }


--- *********************************************************
---     TABLE for the pmopm8Almchannel30Port articles
--- *********************************************************

pmopm8Almchannel30PortTable OBJECT-TYPE
	SYNTAX  SEQUENCE OF Pmopm8Almchannel30PortEntry
	MAX-ACCESS not-accessible
	STATUS current
	DESCRIPTION
        "
        List of pmopm8Almchannel30Port
        Article
        "
	::= { pmopm8AlmClientCrit 248 }


pmopm8Almchannel30PortEntry OBJECT-TYPE
	SYNTAX Pmopm8Almchannel30PortEntry
	MAX-ACCESS not-accessible
	STATUS current
	DESCRIPTION
        "
        Row definition for the pmopm8Almchannel30Port
        table
        "
	INDEX   { pmopm8Almchannel30PortIndex }
	::= { pmopm8Almchannel30PortTable 1 }


Pmopm8Almchannel30PortEntry ::=
	SEQUENCE {
	pmopm8Almchannel30PortIndex
		INTEGER,
	pmopm8AlmChannel30OosPortn
		EkiOnOff,
	pmopm8AlmChannel30PowerHighPortn
		EkiOnOff,
	pmopm8AlmChannel30PowerLowPortn
		EkiOnOff,
	pmopm8AlmChannel30BalancedPortn
		EkiOnOff,
	pmopm8AlmChannel30MismatchPortn
		EkiOnOff,
	pmopm8AlmChannel30AbsentPortn
		EkiOnOff
	}


pmopm8Almchannel30PortIndex OBJECT-TYPE
	SYNTAX  INTEGER(0..128)
	MAX-ACCESS  read-only
	STATUS current
	DESCRIPTION
        "
        Index definition for the pmopm8Almchannel30Port
        table
        "
	::= { pmopm8Almchannel30PortEntry 1 }


pmopm8AlmChannel30OosPortn OBJECT-TYPE
	SYNTAX  EkiOnOff
	MAX-ACCESS read-only
	STATUS current
	DESCRIPTION
        "
        Channel Out Of Service 30 :This
        OID indicates that the channel
         is out of service  <Help> This
        alarm indicates that the channel
        is in service <Condtype> CHANNEL30_OOS_1
        <Probcause> informationalStatus(1000)
        <Alarmtype> other (1) <Polarity>
        (2)
        "
	::= { pmopm8Almchannel30PortEntry 7 }


pmopm8AlmChannel30PowerHighPortn OBJECT-TYPE
	SYNTAX  EkiOnOff
	MAX-ACCESS read-only
	STATUS current
	DESCRIPTION
        "
        Channel Power High 30 :This OID
        indicates that the power of the
        channel is higher than the configured
        threshold<Help> This alarm indicates
        that the power of the channel is
        higher than the configured threshold
        <Condtype> CHANNEL30_POWER_HIGH_1
        <Probcause> degradedSignal (13)
        <Alarmtype> equipmentAlarm <Polarity>
        (2)
        "
	::= { pmopm8Almchannel30PortEntry 6 }


pmopm8AlmChannel30PowerLowPortn OBJECT-TYPE
	SYNTAX  EkiOnOff
	MAX-ACCESS read-only
	STATUS current
	DESCRIPTION
        "
        Channel Power Low 30 :This OID
        indicates that the power of the
        channel is lower than the configured
        threshold<Help> This alarm indicates
        that the power of the channel is
        lower than the configured threshold
        <Condtype> CHANNEL30_POWER_LOW_1
        <Probcause> degradedSignal (13)
        <Alarmtype> equipmentAlarm <Polarity>
        (2)
        "
	::= { pmopm8Almchannel30PortEntry 5 }


pmopm8AlmChannel30BalancedPortn OBJECT-TYPE
	SYNTAX  EkiOnOff
	MAX-ACCESS read-only
	STATUS current
	DESCRIPTION
        "
        Channel Balanced 30 :This OID
         indicates that an in service channel
        is balanced by the Ekinops auto
        turn up application<Help> This
         status indicates that an in service
        channel is balanced by the Ekinops
        auto turn up application <Condtype>
        CHANNEL30_BALANCED_1 <Probcause>
        informationalStatus(1000) <Alarmtype>
        other (1) <Polarity> (2)
        "
	::= { pmopm8Almchannel30PortEntry 4 }


pmopm8AlmChannel30MismatchPortn OBJECT-TYPE
	SYNTAX  EkiOnOff
	MAX-ACCESS read-only
	STATUS current
	DESCRIPTION
        "
        Channel Mismatch 30 :This OID
         indicates that an out of service
        channel is detected on the Optical
        Power Monitoring input<Help> This
        alarm indicates that an out of
         service channel is detected on
        the Optical Power Monitoring input
        <Condtype> CHANNEL30_MISMATCH_1
        <Probcause> unexpectedInformation
        (75) <Alarmtype> equipmentAlarm
        <Polarity> (2)
        "
	::= { pmopm8Almchannel30PortEntry 3 }


pmopm8AlmChannel30AbsentPortn OBJECT-TYPE
	SYNTAX  EkiOnOff
	MAX-ACCESS read-only
	STATUS current
	DESCRIPTION
        "
        Channel Absent 30 :This OID indicates
        that an in service channel is absent
        on the Optical Power Monitoring
        input<Help> This alarm indicates
        that an in service channel is absent
        on the Optical Power Monitoring
        input <Condtype> CHANNEL30_ABSENT_1
        <Probcause> informationMissing
         (65) <Alarmtype> equipmentAlarm
        (5) <Polarity> (2)
        "
	::= { pmopm8Almchannel30PortEntry 2 }


--- *********************************************************
---     TABLE for the pmopm8Almchannel31Port articles
--- *********************************************************

pmopm8Almchannel31PortTable OBJECT-TYPE
	SYNTAX  SEQUENCE OF Pmopm8Almchannel31PortEntry
	MAX-ACCESS not-accessible
	STATUS current
	DESCRIPTION
        "
        List of pmopm8Almchannel31Port
        Article
        "
	::= { pmopm8AlmClientCrit 256 }


pmopm8Almchannel31PortEntry OBJECT-TYPE
	SYNTAX Pmopm8Almchannel31PortEntry
	MAX-ACCESS not-accessible
	STATUS current
	DESCRIPTION
        "
        Row definition for the pmopm8Almchannel31Port
        table
        "
	INDEX   { pmopm8Almchannel31PortIndex }
	::= { pmopm8Almchannel31PortTable 1 }


Pmopm8Almchannel31PortEntry ::=
	SEQUENCE {
	pmopm8Almchannel31PortIndex
		INTEGER,
	pmopm8AlmChannel31OosPortn
		EkiOnOff,
	pmopm8AlmChannel31PowerHighPortn
		EkiOnOff,
	pmopm8AlmChannel31PowerLowPortn
		EkiOnOff,
	pmopm8AlmChannel31BalancedPortn
		EkiOnOff,
	pmopm8AlmChannel31MismatchPortn
		EkiOnOff,
	pmopm8AlmChannel31AbsentPortn
		EkiOnOff
	}


pmopm8Almchannel31PortIndex OBJECT-TYPE
	SYNTAX  INTEGER(0..128)
	MAX-ACCESS  read-only
	STATUS current
	DESCRIPTION
        "
        Index definition for the pmopm8Almchannel31Port
        table
        "
	::= { pmopm8Almchannel31PortEntry 1 }


pmopm8AlmChannel31OosPortn OBJECT-TYPE
	SYNTAX  EkiOnOff
	MAX-ACCESS read-only
	STATUS current
	DESCRIPTION
        "
        Channel Out Of Service 31 :This
        OID indicates that the channel
         is out of service  <Help> This
        alarm indicates that the channel
        is in service <Condtype> CHANNEL31_OOS_1
        <Probcause> informationalStatus(1000)
        <Alarmtype> other (1) <Polarity>
        (2)
        "
	::= { pmopm8Almchannel31PortEntry 7 }


pmopm8AlmChannel31PowerHighPortn OBJECT-TYPE
	SYNTAX  EkiOnOff
	MAX-ACCESS read-only
	STATUS current
	DESCRIPTION
        "
        Channel Power High 31 :This OID
        indicates that the power of the
        channel is higher than the configured
        threshold<Help> This alarm indicates
        that the power of the channel is
        higher than the configured threshold
        <Condtype> CHANNEL31_POWER_HIGH_1
        <Probcause> degradedSignal (13)
        <Alarmtype> equipmentAlarm <Polarity>
        (2)
        "
	::= { pmopm8Almchannel31PortEntry 6 }


pmopm8AlmChannel31PowerLowPortn OBJECT-TYPE
	SYNTAX  EkiOnOff
	MAX-ACCESS read-only
	STATUS current
	DESCRIPTION
        "
        Channel Power Low 31 :This OID
        indicates that the power of the
        channel is lower than the configured
        threshold<Help> This alarm indicates
        that the power of the channel is
        lower than the configured threshold
        <Condtype> CHANNEL31_POWER_LOW_1
        <Probcause> degradedSignal (13)
        <Alarmtype> equipmentAlarm <Polarity>
        (2)
        "
	::= { pmopm8Almchannel31PortEntry 5 }


pmopm8AlmChannel31BalancedPortn OBJECT-TYPE
	SYNTAX  EkiOnOff
	MAX-ACCESS read-only
	STATUS current
	DESCRIPTION
        "
        Channel Balanced 31 :This OID
         indicates that an in service channel
        is balanced by the Ekinops auto
        turn up application<Help> This
         status indicates that an in service
        channel is balanced by the Ekinops
        auto turn up application <Condtype>
        CHANNEL31_BALANCED_1 <Probcause>
        informationalStatus(1000) <Alarmtype>
        other (1) <Polarity> (2)
        "
	::= { pmopm8Almchannel31PortEntry 4 }


pmopm8AlmChannel31MismatchPortn OBJECT-TYPE
	SYNTAX  EkiOnOff
	MAX-ACCESS read-only
	STATUS current
	DESCRIPTION
        "
        Channel Mismatch 31 :This OID
         indicates that an out of service
        channel is detected on the Optical
        Power Monitoring input<Help> This
        alarm indicates that an out of
         service channel is detected on
        the Optical Power Monitoring input
        <Condtype> CHANNEL31_MISMATCH_1
        <Probcause> unexpectedInformation
        (75) <Alarmtype> equipmentAlarm
        <Polarity> (2)
        "
	::= { pmopm8Almchannel31PortEntry 3 }


pmopm8AlmChannel31AbsentPortn OBJECT-TYPE
	SYNTAX  EkiOnOff
	MAX-ACCESS read-only
	STATUS current
	DESCRIPTION
        "
        Channel Absent 31 :This OID indicates
        that an in service channel is absent
        on the Optical Power Monitoring
        input<Help> This alarm indicates
        that an in service channel is absent
        on the Optical Power Monitoring
        input <Condtype> CHANNEL31_ABSENT_1
        <Probcause> informationMissing
         (65) <Alarmtype> equipmentAlarm
        (5) <Polarity> (2)
        "
	::= { pmopm8Almchannel31PortEntry 2 }


--- *********************************************************
---     TABLE for the pmopm8Almchannel32Port articles
--- *********************************************************

pmopm8Almchannel32PortTable OBJECT-TYPE
	SYNTAX  SEQUENCE OF Pmopm8Almchannel32PortEntry
	MAX-ACCESS not-accessible
	STATUS current
	DESCRIPTION
        "
        List of pmopm8Almchannel32Port
        Article
        "
	::= { pmopm8AlmClientCrit 264 }


pmopm8Almchannel32PortEntry OBJECT-TYPE
	SYNTAX Pmopm8Almchannel32PortEntry
	MAX-ACCESS not-accessible
	STATUS current
	DESCRIPTION
        "
        Row definition for the pmopm8Almchannel32Port
        table
        "
	INDEX   { pmopm8Almchannel32PortIndex }
	::= { pmopm8Almchannel32PortTable 1 }


Pmopm8Almchannel32PortEntry ::=
	SEQUENCE {
	pmopm8Almchannel32PortIndex
		INTEGER,
	pmopm8AlmChannel32OosPortn
		EkiOnOff,
	pmopm8AlmChannel32PowerHighPortn
		EkiOnOff,
	pmopm8AlmChannel32PowerLowPortn
		EkiOnOff,
	pmopm8AlmChannel32BalancedPortn
		EkiOnOff,
	pmopm8AlmChannel32MismatchPortn
		EkiOnOff,
	pmopm8AlmChannel32AbsentPortn
		EkiOnOff
	}


pmopm8Almchannel32PortIndex OBJECT-TYPE
	SYNTAX  INTEGER(0..128)
	MAX-ACCESS  read-only
	STATUS current
	DESCRIPTION
        "
        Index definition for the pmopm8Almchannel32Port
        table
        "
	::= { pmopm8Almchannel32PortEntry 1 }


pmopm8AlmChannel32OosPortn OBJECT-TYPE
	SYNTAX  EkiOnOff
	MAX-ACCESS read-only
	STATUS current
	DESCRIPTION
        "
        Channel Out Of Service 32 :This
        OID indicates that the channel
         is out of service  <Help> This
        alarm indicates that the channel
        is in service <Condtype> CHANNEL32_OOS_1
        <Probcause> informationalStatus(1000)
        <Alarmtype> other (1) <Polarity>
        (2)
        "
	::= { pmopm8Almchannel32PortEntry 7 }


pmopm8AlmChannel32PowerHighPortn OBJECT-TYPE
	SYNTAX  EkiOnOff
	MAX-ACCESS read-only
	STATUS current
	DESCRIPTION
        "
        Channel Power High 32 :This OID
        indicates that the power of the
        channel is higher than the configured
        threshold<Help> This alarm indicates
        that the power of the channel is
        higher than the configured threshold
        <Condtype> CHANNEL32_POWER_HIGH_1
        <Probcause> degradedSignal (13)
        <Alarmtype> equipmentAlarm <Polarity>
        (2)
        "
	::= { pmopm8Almchannel32PortEntry 6 }


pmopm8AlmChannel32PowerLowPortn OBJECT-TYPE
	SYNTAX  EkiOnOff
	MAX-ACCESS read-only
	STATUS current
	DESCRIPTION
        "
        Channel Power Low 32 :This OID
        indicates that the power of the
        channel is lower than the configured
        threshold<Help> This alarm indicates
        that the power of the channel is
        lower than the configured threshold
        <Condtype> CHANNEL32_POWER_LOW_1
        <Probcause> degradedSignal (13)
        <Alarmtype> equipmentAlarm <Polarity>
        (2)
        "
	::= { pmopm8Almchannel32PortEntry 5 }


pmopm8AlmChannel32BalancedPortn OBJECT-TYPE
	SYNTAX  EkiOnOff
	MAX-ACCESS read-only
	STATUS current
	DESCRIPTION
        "
        Channel Balanced 32 :This OID
         indicates that an in service channel
        is balanced by the Ekinops auto
        turn up application<Help> This
         status indicates that an in service
        channel is balanced by the Ekinops
        auto turn up application <Condtype>
        CHANNEL32_BALANCED_1 <Probcause>
        informationalStatus(1000) <Alarmtype>
        other (1) <Polarity> (2)
        "
	::= { pmopm8Almchannel32PortEntry 4 }


pmopm8AlmChannel32MismatchPortn OBJECT-TYPE
	SYNTAX  EkiOnOff
	MAX-ACCESS read-only
	STATUS current
	DESCRIPTION
        "
        Channel Mismatch 32 :This OID
         indicates that an out of service
        channel is detected on the Optical
        Power Monitoring input<Help> This
        alarm indicates that an out of
         service channel is detected on
        the Optical Power Monitoring input
        <Condtype> CHANNEL32_MISMATCH_1
        <Probcause> unexpectedInformation
        (75) <Alarmtype> equipmentAlarm
        <Polarity> (2)
        "
	::= { pmopm8Almchannel32PortEntry 3 }


pmopm8AlmChannel32AbsentPortn OBJECT-TYPE
	SYNTAX  EkiOnOff
	MAX-ACCESS read-only
	STATUS current
	DESCRIPTION
        "
        Channel Absent 32 :This OID indicates
        that an in service channel is absent
        on the Optical Power Monitoring
        input<Help> This alarm indicates
        that an in service channel is absent
        on the Optical Power Monitoring
        input <Condtype> CHANNEL32_ABSENT_1
        <Probcause> informationMissing
         (65) <Alarmtype> equipmentAlarm
        (5) <Polarity> (2)
        "
	::= { pmopm8Almchannel32PortEntry 2 }


--- *********************************************************
---     TABLE for the pmopm8Almchannel33Port articles
--- *********************************************************

pmopm8Almchannel33PortTable OBJECT-TYPE
	SYNTAX  SEQUENCE OF Pmopm8Almchannel33PortEntry
	MAX-ACCESS not-accessible
	STATUS current
	DESCRIPTION
        "
        List of pmopm8Almchannel33Port
        Article
        "
	::= { pmopm8AlmClientCrit 272 }


pmopm8Almchannel33PortEntry OBJECT-TYPE
	SYNTAX Pmopm8Almchannel33PortEntry
	MAX-ACCESS not-accessible
	STATUS current
	DESCRIPTION
        "
        Row definition for the pmopm8Almchannel33Port
        table
        "
	INDEX   { pmopm8Almchannel33PortIndex }
	::= { pmopm8Almchannel33PortTable 1 }


Pmopm8Almchannel33PortEntry ::=
	SEQUENCE {
	pmopm8Almchannel33PortIndex
		INTEGER,
	pmopm8AlmChannel33OosPortn
		EkiOnOff,
	pmopm8AlmChannel33PowerHighPortn
		EkiOnOff,
	pmopm8AlmChannel33PowerLowPortn
		EkiOnOff,
	pmopm8AlmChannel33BalancedPortn
		EkiOnOff,
	pmopm8AlmChannel33MismatchPortn
		EkiOnOff,
	pmopm8AlmChannel33AbsentPortn
		EkiOnOff
	}


pmopm8Almchannel33PortIndex OBJECT-TYPE
	SYNTAX  INTEGER(0..128)
	MAX-ACCESS  read-only
	STATUS current
	DESCRIPTION
        "
        Index definition for the pmopm8Almchannel33Port
        table
        "
	::= { pmopm8Almchannel33PortEntry 1 }


pmopm8AlmChannel33OosPortn OBJECT-TYPE
	SYNTAX  EkiOnOff
	MAX-ACCESS read-only
	STATUS current
	DESCRIPTION
        "
        Channel Out Of Service 33 :This
        OID indicates that the channel
         is out of service  <Help> This
        alarm indicates that the channel
        is in service <Condtype> CHANNEL33_OOS_1
        <Probcause> informationalStatus(1000)
        <Alarmtype> other (1) <Polarity>
        (2)
        "
	::= { pmopm8Almchannel33PortEntry 7 }


pmopm8AlmChannel33PowerHighPortn OBJECT-TYPE
	SYNTAX  EkiOnOff
	MAX-ACCESS read-only
	STATUS current
	DESCRIPTION
        "
        Channel Power High 33 :This OID
        indicates that the power of the
        channel is higher than the configured
        threshold<Help> This alarm indicates
        that the power of the channel is
        higher than the configured threshold
        <Condtype> CHANNEL33_POWER_HIGH_1
        <Probcause> degradedSignal (13)
        <Alarmtype> equipmentAlarm <Polarity>
        (2)
        "
	::= { pmopm8Almchannel33PortEntry 6 }


pmopm8AlmChannel33PowerLowPortn OBJECT-TYPE
	SYNTAX  EkiOnOff
	MAX-ACCESS read-only
	STATUS current
	DESCRIPTION
        "
        Channel Power Low 33 :This OID
        indicates that the power of the
        channel is lower than the configured
        threshold<Help> This alarm indicates
        that the power of the channel is
        lower than the configured threshold
        <Condtype> CHANNEL33_POWER_LOW_1
        <Probcause> degradedSignal (13)
        <Alarmtype> equipmentAlarm <Polarity>
        (2)
        "
	::= { pmopm8Almchannel33PortEntry 5 }


pmopm8AlmChannel33BalancedPortn OBJECT-TYPE
	SYNTAX  EkiOnOff
	MAX-ACCESS read-only
	STATUS current
	DESCRIPTION
        "
        Channel Balanced 33 :This OID
         indicates that an in service channel
        is balanced by the Ekinops auto
        turn up application<Help> This
         status indicates that an in service
        channel is balanced by the Ekinops
        auto turn up application <Condtype>
        CHANNEL33_BALANCED_1 <Probcause>
        informationalStatus(1000) <Alarmtype>
        other (1) <Polarity> (2)
        "
	::= { pmopm8Almchannel33PortEntry 4 }


pmopm8AlmChannel33MismatchPortn OBJECT-TYPE
	SYNTAX  EkiOnOff
	MAX-ACCESS read-only
	STATUS current
	DESCRIPTION
        "
        Channel Mismatch 33 :This OID
         indicates that an out of service
        channel is detected on the Optical
        Power Monitoring input<Help> This
        alarm indicates that an out of
         service channel is detected on
        the Optical Power Monitoring input
        <Condtype> CHANNEL33_MISMATCH_1
        <Probcause> unexpectedInformation
        (75) <Alarmtype> equipmentAlarm
        <Polarity> (2)
        "
	::= { pmopm8Almchannel33PortEntry 3 }


pmopm8AlmChannel33AbsentPortn OBJECT-TYPE
	SYNTAX  EkiOnOff
	MAX-ACCESS read-only
	STATUS current
	DESCRIPTION
        "
        Channel Absent 33 :This OID indicates
        that an in service channel is absent
        on the Optical Power Monitoring
        input<Help> This alarm indicates
        that an in service channel is absent
        on the Optical Power Monitoring
        input <Condtype> CHANNEL33_ABSENT_1
        <Probcause> informationMissing
         (65) <Alarmtype> equipmentAlarm
        (5) <Polarity> (2)
        "
	::= { pmopm8Almchannel33PortEntry 2 }


--- *********************************************************
---     TABLE for the pmopm8Almchannel34Port articles
--- *********************************************************

pmopm8Almchannel34PortTable OBJECT-TYPE
	SYNTAX  SEQUENCE OF Pmopm8Almchannel34PortEntry
	MAX-ACCESS not-accessible
	STATUS current
	DESCRIPTION
        "
        List of pmopm8Almchannel34Port
        Article
        "
	::= { pmopm8AlmClientCrit 280 }


pmopm8Almchannel34PortEntry OBJECT-TYPE
	SYNTAX Pmopm8Almchannel34PortEntry
	MAX-ACCESS not-accessible
	STATUS current
	DESCRIPTION
        "
        Row definition for the pmopm8Almchannel34Port
        table
        "
	INDEX   { pmopm8Almchannel34PortIndex }
	::= { pmopm8Almchannel34PortTable 1 }


Pmopm8Almchannel34PortEntry ::=
	SEQUENCE {
	pmopm8Almchannel34PortIndex
		INTEGER,
	pmopm8AlmChannel34OosPortn
		EkiOnOff,
	pmopm8AlmChannel34PowerHighPortn
		EkiOnOff,
	pmopm8AlmChannel34PowerLowPortn
		EkiOnOff,
	pmopm8AlmChannel34BalancedPortn
		EkiOnOff,
	pmopm8AlmChannel34MismatchPortn
		EkiOnOff,
	pmopm8AlmChannel34AbsentPortn
		EkiOnOff
	}


pmopm8Almchannel34PortIndex OBJECT-TYPE
	SYNTAX  INTEGER(0..128)
	MAX-ACCESS  read-only
	STATUS current
	DESCRIPTION
        "
        Index definition for the pmopm8Almchannel34Port
        table
        "
	::= { pmopm8Almchannel34PortEntry 1 }


pmopm8AlmChannel34OosPortn OBJECT-TYPE
	SYNTAX  EkiOnOff
	MAX-ACCESS read-only
	STATUS current
	DESCRIPTION
        "
        Channel Out Of Service 34 :This
        OID indicates that the channel
         is out of service  <Help> This
        alarm indicates that the channel
        is in service <Condtype> CHANNEL34_OOS_1
        <Probcause> informationalStatus(1000)
        <Alarmtype> other (1) <Polarity>
        (2)
        "
	::= { pmopm8Almchannel34PortEntry 7 }


pmopm8AlmChannel34PowerHighPortn OBJECT-TYPE
	SYNTAX  EkiOnOff
	MAX-ACCESS read-only
	STATUS current
	DESCRIPTION
        "
        Channel Power High 34 :This OID
        indicates that the power of the
        channel is higher than the configured
        threshold<Help> This alarm indicates
        that the power of the channel is
        higher than the configured threshold
        <Condtype> CHANNEL34_POWER_HIGH_1
        <Probcause> degradedSignal (13)
        <Alarmtype> equipmentAlarm <Polarity>
        (2)
        "
	::= { pmopm8Almchannel34PortEntry 6 }


pmopm8AlmChannel34PowerLowPortn OBJECT-TYPE
	SYNTAX  EkiOnOff
	MAX-ACCESS read-only
	STATUS current
	DESCRIPTION
        "
        Channel Power Low 34 :This OID
        indicates that the power of the
        channel is lower than the configured
        threshold<Help> This alarm indicates
        that the power of the channel is
        lower than the configured threshold
        <Condtype> CHANNEL34_POWER_LOW_1
        <Probcause> degradedSignal (13)
        <Alarmtype> equipmentAlarm <Polarity>
        (2)
        "
	::= { pmopm8Almchannel34PortEntry 5 }


pmopm8AlmChannel34BalancedPortn OBJECT-TYPE
	SYNTAX  EkiOnOff
	MAX-ACCESS read-only
	STATUS current
	DESCRIPTION
        "
        Channel Balanced 34 :This OID
         indicates that an in service channel
        is balanced by the Ekinops auto
        turn up application<Help> This
         status indicates that an in service
        channel is balanced by the Ekinops
        auto turn up application <Condtype>
        CHANNEL34_BALANCED_1 <Probcause>
        informationalStatus(1000) <Alarmtype>
        other (1) <Polarity> (2)
        "
	::= { pmopm8Almchannel34PortEntry 4 }


pmopm8AlmChannel34MismatchPortn OBJECT-TYPE
	SYNTAX  EkiOnOff
	MAX-ACCESS read-only
	STATUS current
	DESCRIPTION
        "
        Channel Mismatch 34 :This OID
         indicates that an out of service
        channel is detected on the Optical
        Power Monitoring input<Help> This
        alarm indicates that an out of
         service channel is detected on
        the Optical Power Monitoring input
        <Condtype> CHANNEL34_MISMATCH_1
        <Probcause> unexpectedInformation
        (75) <Alarmtype> equipmentAlarm
        <Polarity> (2)
        "
	::= { pmopm8Almchannel34PortEntry 3 }


pmopm8AlmChannel34AbsentPortn OBJECT-TYPE
	SYNTAX  EkiOnOff
	MAX-ACCESS read-only
	STATUS current
	DESCRIPTION
        "
        Channel Absent 34 :This OID indicates
        that an in service channel is absent
        on the Optical Power Monitoring
        input<Help> This alarm indicates
        that an in service channel is absent
        on the Optical Power Monitoring
        input <Condtype> CHANNEL34_ABSENT_1
        <Probcause> informationMissing
         (65) <Alarmtype> equipmentAlarm
        (5) <Polarity> (2)
        "
	::= { pmopm8Almchannel34PortEntry 2 }


--- *********************************************************
---     TABLE for the pmopm8Almchannel35Port articles
--- *********************************************************

pmopm8Almchannel35PortTable OBJECT-TYPE
	SYNTAX  SEQUENCE OF Pmopm8Almchannel35PortEntry
	MAX-ACCESS not-accessible
	STATUS current
	DESCRIPTION
        "
        List of pmopm8Almchannel35Port
        Article
        "
	::= { pmopm8AlmClientCrit 288 }


pmopm8Almchannel35PortEntry OBJECT-TYPE
	SYNTAX Pmopm8Almchannel35PortEntry
	MAX-ACCESS not-accessible
	STATUS current
	DESCRIPTION
        "
        Row definition for the pmopm8Almchannel35Port
        table
        "
	INDEX   { pmopm8Almchannel35PortIndex }
	::= { pmopm8Almchannel35PortTable 1 }


Pmopm8Almchannel35PortEntry ::=
	SEQUENCE {
	pmopm8Almchannel35PortIndex
		INTEGER,
	pmopm8AlmChannel35OosPortn
		EkiOnOff,
	pmopm8AlmChannel35PowerHighPortn
		EkiOnOff,
	pmopm8AlmChannel35PowerLowPortn
		EkiOnOff,
	pmopm8AlmChannel35BalancedPortn
		EkiOnOff,
	pmopm8AlmChannel35MismatchPortn
		EkiOnOff,
	pmopm8AlmChannel35AbsentPortn
		EkiOnOff
	}


pmopm8Almchannel35PortIndex OBJECT-TYPE
	SYNTAX  INTEGER(0..128)
	MAX-ACCESS  read-only
	STATUS current
	DESCRIPTION
        "
        Index definition for the pmopm8Almchannel35Port
        table
        "
	::= { pmopm8Almchannel35PortEntry 1 }


pmopm8AlmChannel35OosPortn OBJECT-TYPE
	SYNTAX  EkiOnOff
	MAX-ACCESS read-only
	STATUS current
	DESCRIPTION
        "
        Channel Out Of Service 35 :This
        OID indicates that the channel
         is out of service  <Help> This
        alarm indicates that the channel
        is in service <Condtype> CHANNEL35_OOS_1
        <Probcause> informationalStatus(1000)
        <Alarmtype> other (1) <Polarity>
        (2)
        "
	::= { pmopm8Almchannel35PortEntry 7 }


pmopm8AlmChannel35PowerHighPortn OBJECT-TYPE
	SYNTAX  EkiOnOff
	MAX-ACCESS read-only
	STATUS current
	DESCRIPTION
        "
        Channel Power High 35 :This OID
        indicates that the power of the
        channel is higher than the configured
        threshold<Help> This alarm indicates
        that the power of the channel is
        higher than the configured threshold
        <Condtype> CHANNEL35_POWER_HIGH_1
        <Probcause> degradedSignal (13)
        <Alarmtype> equipmentAlarm <Polarity>
        (2)
        "
	::= { pmopm8Almchannel35PortEntry 6 }


pmopm8AlmChannel35PowerLowPortn OBJECT-TYPE
	SYNTAX  EkiOnOff
	MAX-ACCESS read-only
	STATUS current
	DESCRIPTION
        "
        Channel Power Low 35 :This OID
        indicates that the power of the
        channel is lower than the configured
        threshold<Help> This alarm indicates
        that the power of the channel is
        lower than the configured threshold
        <Condtype> CHANNEL35_POWER_LOW_1
        <Probcause> degradedSignal (13)
        <Alarmtype> equipmentAlarm <Polarity>
        (2)
        "
	::= { pmopm8Almchannel35PortEntry 5 }


pmopm8AlmChannel35BalancedPortn OBJECT-TYPE
	SYNTAX  EkiOnOff
	MAX-ACCESS read-only
	STATUS current
	DESCRIPTION
        "
        Channel Balanced 35 :This OID
         indicates that an in service channel
        is balanced by the Ekinops auto
        turn up application<Help> This
         status indicates that an in service
        channel is balanced by the Ekinops
        auto turn up application <Condtype>
        CHANNEL35_BALANCED_1 <Probcause>
        informationalStatus(1000) <Alarmtype>
        other (1) <Polarity> (2)
        "
	::= { pmopm8Almchannel35PortEntry 4 }


pmopm8AlmChannel35MismatchPortn OBJECT-TYPE
	SYNTAX  EkiOnOff
	MAX-ACCESS read-only
	STATUS current
	DESCRIPTION
        "
        Channel Mismatch 35 :This OID
         indicates that an out of service
        channel is detected on the Optical
        Power Monitoring input<Help> This
        alarm indicates that an out of
         service channel is detected on
        the Optical Power Monitoring input
        <Condtype> CHANNEL35_MISMATCH_1
        <Probcause> unexpectedInformation
        (75) <Alarmtype> equipmentAlarm
        <Polarity> (2)
        "
	::= { pmopm8Almchannel35PortEntry 3 }


pmopm8AlmChannel35AbsentPortn OBJECT-TYPE
	SYNTAX  EkiOnOff
	MAX-ACCESS read-only
	STATUS current
	DESCRIPTION
        "
        Channel Absent 35 :This OID indicates
        that an in service channel is absent
        on the Optical Power Monitoring
        input<Help> This alarm indicates
        that an in service channel is absent
        on the Optical Power Monitoring
        input <Condtype> CHANNEL35_ABSENT_1
        <Probcause> informationMissing
         (65) <Alarmtype> equipmentAlarm
        (5) <Polarity> (2)
        "
	::= { pmopm8Almchannel35PortEntry 2 }


--- *********************************************************
---     TABLE for the pmopm8Almchannel36Port articles
--- *********************************************************

pmopm8Almchannel36PortTable OBJECT-TYPE
	SYNTAX  SEQUENCE OF Pmopm8Almchannel36PortEntry
	MAX-ACCESS not-accessible
	STATUS current
	DESCRIPTION
        "
        List of pmopm8Almchannel36Port
        Article
        "
	::= { pmopm8AlmClientCrit 296 }


pmopm8Almchannel36PortEntry OBJECT-TYPE
	SYNTAX Pmopm8Almchannel36PortEntry
	MAX-ACCESS not-accessible
	STATUS current
	DESCRIPTION
        "
        Row definition for the pmopm8Almchannel36Port
        table
        "
	INDEX   { pmopm8Almchannel36PortIndex }
	::= { pmopm8Almchannel36PortTable 1 }


Pmopm8Almchannel36PortEntry ::=
	SEQUENCE {
	pmopm8Almchannel36PortIndex
		INTEGER,
	pmopm8AlmChannel36OosPortn
		EkiOnOff,
	pmopm8AlmChannel36PowerHighPortn
		EkiOnOff,
	pmopm8AlmChannel36PowerLowPortn
		EkiOnOff,
	pmopm8AlmChannel36BalancedPortn
		EkiOnOff,
	pmopm8AlmChannel36MismatchPortn
		EkiOnOff,
	pmopm8AlmChannel36AbsentPortn
		EkiOnOff
	}


pmopm8Almchannel36PortIndex OBJECT-TYPE
	SYNTAX  INTEGER(0..128)
	MAX-ACCESS  read-only
	STATUS current
	DESCRIPTION
        "
        Index definition for the pmopm8Almchannel36Port
        table
        "
	::= { pmopm8Almchannel36PortEntry 1 }


pmopm8AlmChannel36OosPortn OBJECT-TYPE
	SYNTAX  EkiOnOff
	MAX-ACCESS read-only
	STATUS current
	DESCRIPTION
        "
        Channel Out Of Service 36 :This
        OID indicates that the channel
         is out of service  <Help> This
        alarm indicates that the channel
        is in service <Condtype> CHANNEL36_OOS_1
        <Probcause> informationalStatus(1000)
        <Alarmtype> other (1) <Polarity>
        (2)
        "
	::= { pmopm8Almchannel36PortEntry 7 }


pmopm8AlmChannel36PowerHighPortn OBJECT-TYPE
	SYNTAX  EkiOnOff
	MAX-ACCESS read-only
	STATUS current
	DESCRIPTION
        "
        Channel Power High 36 :This OID
        indicates that the power of the
        channel is higher than the configured
        threshold<Help> This alarm indicates
        that the power of the channel is
        higher than the configured threshold
        <Condtype> CHANNEL36_POWER_HIGH_1
        <Probcause> degradedSignal (13)
        <Alarmtype> equipmentAlarm <Polarity>
        (2)
        "
	::= { pmopm8Almchannel36PortEntry 6 }


pmopm8AlmChannel36PowerLowPortn OBJECT-TYPE
	SYNTAX  EkiOnOff
	MAX-ACCESS read-only
	STATUS current
	DESCRIPTION
        "
        Channel Power Low 36 :This OID
        indicates that the power of the
        channel is lower than the configured
        threshold<Help> This alarm indicates
        that the power of the channel is
        lower than the configured threshold
        <Condtype> CHANNEL36_POWER_LOW_1
        <Probcause> degradedSignal (13)
        <Alarmtype> equipmentAlarm <Polarity>
        (2)
        "
	::= { pmopm8Almchannel36PortEntry 5 }


pmopm8AlmChannel36BalancedPortn OBJECT-TYPE
	SYNTAX  EkiOnOff
	MAX-ACCESS read-only
	STATUS current
	DESCRIPTION
        "
        Channel Balanced 36 :This OID
         indicates that an in service channel
        is balanced by the Ekinops auto
        turn up application<Help> This
         status indicates that an in service
        channel is balanced by the Ekinops
        auto turn up application <Condtype>
        CHANNEL36_BALANCED_1 <Probcause>
        informationalStatus(1000) <Alarmtype>
        other (1) <Polarity> (2)
        "
	::= { pmopm8Almchannel36PortEntry 4 }


pmopm8AlmChannel36MismatchPortn OBJECT-TYPE
	SYNTAX  EkiOnOff
	MAX-ACCESS read-only
	STATUS current
	DESCRIPTION
        "
        Channel Mismatch 36 :This OID
         indicates that an out of service
        channel is detected on the Optical
        Power Monitoring input<Help> This
        alarm indicates that an out of
         service channel is detected on
        the Optical Power Monitoring input
        <Condtype> CHANNEL36_MISMATCH_1
        <Probcause> unexpectedInformation
        (75) <Alarmtype> equipmentAlarm
        <Polarity> (2)
        "
	::= { pmopm8Almchannel36PortEntry 3 }


pmopm8AlmChannel36AbsentPortn OBJECT-TYPE
	SYNTAX  EkiOnOff
	MAX-ACCESS read-only
	STATUS current
	DESCRIPTION
        "
        Channel Absent 36 :This OID indicates
        that an in service channel is absent
        on the Optical Power Monitoring
        input<Help> This alarm indicates
        that an in service channel is absent
        on the Optical Power Monitoring
        input <Condtype> CHANNEL36_ABSENT_1
        <Probcause> informationMissing
         (65) <Alarmtype> equipmentAlarm
        (5) <Polarity> (2)
        "
	::= { pmopm8Almchannel36PortEntry 2 }


--- *********************************************************
---     TABLE for the pmopm8Almchannel37Port articles
--- *********************************************************

pmopm8Almchannel37PortTable OBJECT-TYPE
	SYNTAX  SEQUENCE OF Pmopm8Almchannel37PortEntry
	MAX-ACCESS not-accessible
	STATUS current
	DESCRIPTION
        "
        List of pmopm8Almchannel37Port
        Article
        "
	::= { pmopm8AlmClientCrit 304 }


pmopm8Almchannel37PortEntry OBJECT-TYPE
	SYNTAX Pmopm8Almchannel37PortEntry
	MAX-ACCESS not-accessible
	STATUS current
	DESCRIPTION
        "
        Row definition for the pmopm8Almchannel37Port
        table
        "
	INDEX   { pmopm8Almchannel37PortIndex }
	::= { pmopm8Almchannel37PortTable 1 }


Pmopm8Almchannel37PortEntry ::=
	SEQUENCE {
	pmopm8Almchannel37PortIndex
		INTEGER,
	pmopm8AlmChannel37OosPortn
		EkiOnOff,
	pmopm8AlmChannel37PowerHighPortn
		EkiOnOff,
	pmopm8AlmChannel37PowerLowPortn
		EkiOnOff,
	pmopm8AlmChannel37BalancedPortn
		EkiOnOff,
	pmopm8AlmChannel37MismatchPortn
		EkiOnOff,
	pmopm8AlmChannel37AbsentPortn
		EkiOnOff
	}


pmopm8Almchannel37PortIndex OBJECT-TYPE
	SYNTAX  INTEGER(0..128)
	MAX-ACCESS  read-only
	STATUS current
	DESCRIPTION
        "
        Index definition for the pmopm8Almchannel37Port
        table
        "
	::= { pmopm8Almchannel37PortEntry 1 }


pmopm8AlmChannel37OosPortn OBJECT-TYPE
	SYNTAX  EkiOnOff
	MAX-ACCESS read-only
	STATUS current
	DESCRIPTION
        "
        Channel Out Of Service 37 :This
        OID indicates that the channel
         is out of service  <Help> This
        alarm indicates that the channel
        is in service <Condtype> CHANNEL37_OOS_1
        <Probcause> informationalStatus(1000)
        <Alarmtype> other (1) <Polarity>
        (2)
        "
	::= { pmopm8Almchannel37PortEntry 7 }


pmopm8AlmChannel37PowerHighPortn OBJECT-TYPE
	SYNTAX  EkiOnOff
	MAX-ACCESS read-only
	STATUS current
	DESCRIPTION
        "
        Channel Power High 37 :This OID
        indicates that the power of the
        channel is higher than the configured
        threshold<Help> This alarm indicates
        that the power of the channel is
        higher than the configured threshold
        <Condtype> CHANNEL37_POWER_HIGH_1
        <Probcause> degradedSignal (13)
        <Alarmtype> equipmentAlarm <Polarity>
        (2)
        "
	::= { pmopm8Almchannel37PortEntry 6 }


pmopm8AlmChannel37PowerLowPortn OBJECT-TYPE
	SYNTAX  EkiOnOff
	MAX-ACCESS read-only
	STATUS current
	DESCRIPTION
        "
        Channel Power Low 37 :This OID
        indicates that the power of the
        channel is lower than the configured
        threshold<Help> This alarm indicates
        that the power of the channel is
        lower than the configured threshold
        <Condtype> CHANNEL37_POWER_LOW_1
        <Probcause> degradedSignal (13)
        <Alarmtype> equipmentAlarm <Polarity>
        (2)
        "
	::= { pmopm8Almchannel37PortEntry 5 }


pmopm8AlmChannel37BalancedPortn OBJECT-TYPE
	SYNTAX  EkiOnOff
	MAX-ACCESS read-only
	STATUS current
	DESCRIPTION
        "
        Channel Balanced 37 :This OID
         indicates that an in service channel
        is balanced by the Ekinops auto
        turn up application<Help> This
         status indicates that an in service
        channel is balanced by the Ekinops
        auto turn up application <Condtype>
        CHANNEL37_BALANCED_1 <Probcause>
        informationalStatus(1000) <Alarmtype>
        other (1) <Polarity> (2)
        "
	::= { pmopm8Almchannel37PortEntry 4 }


pmopm8AlmChannel37MismatchPortn OBJECT-TYPE
	SYNTAX  EkiOnOff
	MAX-ACCESS read-only
	STATUS current
	DESCRIPTION
        "
        Channel Mismatch 37 :This OID
         indicates that an out of service
        channel is detected on the Optical
        Power Monitoring input<Help> This
        alarm indicates that an out of
         service channel is detected on
        the Optical Power Monitoring input
        <Condtype> CHANNEL37_MISMATCH_1
        <Probcause> unexpectedInformation
        (75) <Alarmtype> equipmentAlarm
        <Polarity> (2)
        "
	::= { pmopm8Almchannel37PortEntry 3 }


pmopm8AlmChannel37AbsentPortn OBJECT-TYPE
	SYNTAX  EkiOnOff
	MAX-ACCESS read-only
	STATUS current
	DESCRIPTION
        "
        Channel Absent 37 :This OID indicates
        that an in service channel is absent
        on the Optical Power Monitoring
        input<Help> This alarm indicates
        that an in service channel is absent
        on the Optical Power Monitoring
        input <Condtype> CHANNEL37_ABSENT_1
        <Probcause> informationMissing
         (65) <Alarmtype> equipmentAlarm
        (5) <Polarity> (2)
        "
	::= { pmopm8Almchannel37PortEntry 2 }


--- *********************************************************
---     TABLE for the pmopm8Almchannel38Port articles
--- *********************************************************

pmopm8Almchannel38PortTable OBJECT-TYPE
	SYNTAX  SEQUENCE OF Pmopm8Almchannel38PortEntry
	MAX-ACCESS not-accessible
	STATUS current
	DESCRIPTION
        "
        List of pmopm8Almchannel38Port
        Article
        "
	::= { pmopm8AlmClientCrit 312 }


pmopm8Almchannel38PortEntry OBJECT-TYPE
	SYNTAX Pmopm8Almchannel38PortEntry
	MAX-ACCESS not-accessible
	STATUS current
	DESCRIPTION
        "
        Row definition for the pmopm8Almchannel38Port
        table
        "
	INDEX   { pmopm8Almchannel38PortIndex }
	::= { pmopm8Almchannel38PortTable 1 }


Pmopm8Almchannel38PortEntry ::=
	SEQUENCE {
	pmopm8Almchannel38PortIndex
		INTEGER,
	pmopm8AlmChannel38OosPortn
		EkiOnOff,
	pmopm8AlmChannel38PowerHighPortn
		EkiOnOff,
	pmopm8AlmChannel38PowerLowPortn
		EkiOnOff,
	pmopm8AlmChannel38BalancedPortn
		EkiOnOff,
	pmopm8AlmChannel38MismatchPortn
		EkiOnOff,
	pmopm8AlmChannel38AbsentPortn
		EkiOnOff
	}


pmopm8Almchannel38PortIndex OBJECT-TYPE
	SYNTAX  INTEGER(0..128)
	MAX-ACCESS  read-only
	STATUS current
	DESCRIPTION
        "
        Index definition for the pmopm8Almchannel38Port
        table
        "
	::= { pmopm8Almchannel38PortEntry 1 }


pmopm8AlmChannel38OosPortn OBJECT-TYPE
	SYNTAX  EkiOnOff
	MAX-ACCESS read-only
	STATUS current
	DESCRIPTION
        "
        Channel Out Of Service 38 :This
        OID indicates that the channel
         is out of service  <Help> This
        alarm indicates that the channel
        is in service <Condtype> CHANNEL38_OOS_1
        <Probcause> informationalStatus(1000)
        <Alarmtype> other (1) <Polarity>
        (2)
        "
	::= { pmopm8Almchannel38PortEntry 7 }


pmopm8AlmChannel38PowerHighPortn OBJECT-TYPE
	SYNTAX  EkiOnOff
	MAX-ACCESS read-only
	STATUS current
	DESCRIPTION
        "
        Channel Power High 38 :This OID
        indicates that the power of the
        channel is higher than the configured
        threshold<Help> This alarm indicates
        that the power of the channel is
        higher than the configured threshold
        <Condtype> CHANNEL38_POWER_HIGH_1
        <Probcause> degradedSignal (13)
        <Alarmtype> equipmentAlarm <Polarity>
        (2)
        "
	::= { pmopm8Almchannel38PortEntry 6 }


pmopm8AlmChannel38PowerLowPortn OBJECT-TYPE
	SYNTAX  EkiOnOff
	MAX-ACCESS read-only
	STATUS current
	DESCRIPTION
        "
        Channel Power Low 38 :This OID
        indicates that the power of the
        channel is lower than the configured
        threshold<Help> This alarm indicates
        that the power of the channel is
        lower than the configured threshold
        <Condtype> CHANNEL38_POWER_LOW_1
        <Probcause> degradedSignal (13)
        <Alarmtype> equipmentAlarm <Polarity>
        (2)
        "
	::= { pmopm8Almchannel38PortEntry 5 }


pmopm8AlmChannel38BalancedPortn OBJECT-TYPE
	SYNTAX  EkiOnOff
	MAX-ACCESS read-only
	STATUS current
	DESCRIPTION
        "
        Channel Balanced 38 :This OID
         indicates that an in service channel
        is balanced by the Ekinops auto
        turn up application<Help> This
         status indicates that an in service
        channel is balanced by the Ekinops
        auto turn up application <Condtype>
        CHANNEL38_BALANCED_1 <Probcause>
        informationalStatus(1000) <Alarmtype>
        other (1) <Polarity> (2)
        "
	::= { pmopm8Almchannel38PortEntry 4 }


pmopm8AlmChannel38MismatchPortn OBJECT-TYPE
	SYNTAX  EkiOnOff
	MAX-ACCESS read-only
	STATUS current
	DESCRIPTION
        "
        Channel Mismatch 38 :This OID
         indicates that an out of service
        channel is detected on the Optical
        Power Monitoring input<Help> This
        alarm indicates that an out of
         service channel is detected on
        the Optical Power Monitoring input
        <Condtype> CHANNEL38_MISMATCH_1
        <Probcause> unexpectedInformation
        (75) <Alarmtype> equipmentAlarm
        <Polarity> (2)
        "
	::= { pmopm8Almchannel38PortEntry 3 }


pmopm8AlmChannel38AbsentPortn OBJECT-TYPE
	SYNTAX  EkiOnOff
	MAX-ACCESS read-only
	STATUS current
	DESCRIPTION
        "
        Channel Absent 38 :This OID indicates
        that an in service channel is absent
        on the Optical Power Monitoring
        input<Help> This alarm indicates
        that an in service channel is absent
        on the Optical Power Monitoring
        input <Condtype> CHANNEL38_ABSENT_1
        <Probcause> informationMissing
         (65) <Alarmtype> equipmentAlarm
        (5) <Polarity> (2)
        "
	::= { pmopm8Almchannel38PortEntry 2 }


--- *********************************************************
---     TABLE for the pmopm8Almchannel39Port articles
--- *********************************************************

pmopm8Almchannel39PortTable OBJECT-TYPE
	SYNTAX  SEQUENCE OF Pmopm8Almchannel39PortEntry
	MAX-ACCESS not-accessible
	STATUS current
	DESCRIPTION
        "
        List of pmopm8Almchannel39Port
        Article
        "
	::= { pmopm8AlmClientCrit 320 }


pmopm8Almchannel39PortEntry OBJECT-TYPE
	SYNTAX Pmopm8Almchannel39PortEntry
	MAX-ACCESS not-accessible
	STATUS current
	DESCRIPTION
        "
        Row definition for the pmopm8Almchannel39Port
        table
        "
	INDEX   { pmopm8Almchannel39PortIndex }
	::= { pmopm8Almchannel39PortTable 1 }


Pmopm8Almchannel39PortEntry ::=
	SEQUENCE {
	pmopm8Almchannel39PortIndex
		INTEGER,
	pmopm8AlmChannel39OosPortn
		EkiOnOff,
	pmopm8AlmChannel39PowerHighPortn
		EkiOnOff,
	pmopm8AlmChannel39PowerLowPortn
		EkiOnOff,
	pmopm8AlmChannel39BalancedPortn
		EkiOnOff,
	pmopm8AlmChannel39MismatchPortn
		EkiOnOff,
	pmopm8AlmChannel39AbsentPortn
		EkiOnOff
	}


pmopm8Almchannel39PortIndex OBJECT-TYPE
	SYNTAX  INTEGER(0..128)
	MAX-ACCESS  read-only
	STATUS current
	DESCRIPTION
        "
        Index definition for the pmopm8Almchannel39Port
        table
        "
	::= { pmopm8Almchannel39PortEntry 1 }


pmopm8AlmChannel39OosPortn OBJECT-TYPE
	SYNTAX  EkiOnOff
	MAX-ACCESS read-only
	STATUS current
	DESCRIPTION
        "
        Channel Out Of Service 39 :This
        OID indicates that the channel
         is out of service  <Help> This
        alarm indicates that the channel
        is in service <Condtype> CHANNEL39_OOS_1
        <Probcause> informationalStatus(1000)
        <Alarmtype> other (1) <Polarity>
        (2)
        "
	::= { pmopm8Almchannel39PortEntry 7 }


pmopm8AlmChannel39PowerHighPortn OBJECT-TYPE
	SYNTAX  EkiOnOff
	MAX-ACCESS read-only
	STATUS current
	DESCRIPTION
        "
        Channel Power High 39 :This OID
        indicates that the power of the
        channel is higher than the configured
        threshold<Help> This alarm indicates
        that the power of the channel is
        higher than the configured threshold
        <Condtype> CHANNEL39_POWER_HIGH_1
        <Probcause> degradedSignal (13)
        <Alarmtype> equipmentAlarm <Polarity>
        (2)
        "
	::= { pmopm8Almchannel39PortEntry 6 }


pmopm8AlmChannel39PowerLowPortn OBJECT-TYPE
	SYNTAX  EkiOnOff
	MAX-ACCESS read-only
	STATUS current
	DESCRIPTION
        "
        Channel Power Low 39 :This OID
        indicates that the power of the
        channel is lower than the configured
        threshold<Help> This alarm indicates
        that the power of the channel is
        lower than the configured threshold
        <Condtype> CHANNEL39_POWER_LOW_1
        <Probcause> degradedSignal (13)
        <Alarmtype> equipmentAlarm <Polarity>
        (2)
        "
	::= { pmopm8Almchannel39PortEntry 5 }


pmopm8AlmChannel39BalancedPortn OBJECT-TYPE
	SYNTAX  EkiOnOff
	MAX-ACCESS read-only
	STATUS current
	DESCRIPTION
        "
        Channel Balanced 39 :This OID
         indicates that an in service channel
        is balanced by the Ekinops auto
        turn up application<Help> This
         status indicates that an in service
        channel is balanced by the Ekinops
        auto turn up application <Condtype>
        CHANNEL39_BALANCED_1 <Probcause>
        informationalStatus(1000) <Alarmtype>
        other (1) <Polarity> (2)
        "
	::= { pmopm8Almchannel39PortEntry 4 }


pmopm8AlmChannel39MismatchPortn OBJECT-TYPE
	SYNTAX  EkiOnOff
	MAX-ACCESS read-only
	STATUS current
	DESCRIPTION
        "
        Channel Mismatch 39 :This OID
         indicates that an out of service
        channel is detected on the Optical
        Power Monitoring input<Help> This
        alarm indicates that an out of
         service channel is detected on
        the Optical Power Monitoring input
        <Condtype> CHANNEL39_MISMATCH_1
        <Probcause> unexpectedInformation
        (75) <Alarmtype> equipmentAlarm
        <Polarity> (2)
        "
	::= { pmopm8Almchannel39PortEntry 3 }


pmopm8AlmChannel39AbsentPortn OBJECT-TYPE
	SYNTAX  EkiOnOff
	MAX-ACCESS read-only
	STATUS current
	DESCRIPTION
        "
        Channel Absent 39 :This OID indicates
        that an in service channel is absent
        on the Optical Power Monitoring
        input<Help> This alarm indicates
        that an in service channel is absent
        on the Optical Power Monitoring
        input <Condtype> CHANNEL39_ABSENT_1
        <Probcause> informationMissing
         (65) <Alarmtype> equipmentAlarm
        (5) <Polarity> (2)
        "
	::= { pmopm8Almchannel39PortEntry 2 }


--- *********************************************************
---     TABLE for the pmopm8Almchannel40Port articles
--- *********************************************************

pmopm8Almchannel40PortTable OBJECT-TYPE
	SYNTAX  SEQUENCE OF Pmopm8Almchannel40PortEntry
	MAX-ACCESS not-accessible
	STATUS current
	DESCRIPTION
        "
        List of pmopm8Almchannel40Port
        Article
        "
	::= { pmopm8AlmClientCrit 328 }


pmopm8Almchannel40PortEntry OBJECT-TYPE
	SYNTAX Pmopm8Almchannel40PortEntry
	MAX-ACCESS not-accessible
	STATUS current
	DESCRIPTION
        "
        Row definition for the pmopm8Almchannel40Port
        table
        "
	INDEX   { pmopm8Almchannel40PortIndex }
	::= { pmopm8Almchannel40PortTable 1 }


Pmopm8Almchannel40PortEntry ::=
	SEQUENCE {
	pmopm8Almchannel40PortIndex
		INTEGER,
	pmopm8AlmChannel40OosPortn
		EkiOnOff,
	pmopm8AlmChannel40PowerHighPortn
		EkiOnOff,
	pmopm8AlmChannel40PowerLowPortn
		EkiOnOff,
	pmopm8AlmChannel40BalancedPortn
		EkiOnOff,
	pmopm8AlmChannel40MismatchPortn
		EkiOnOff,
	pmopm8AlmChannel40AbsentPortn
		EkiOnOff
	}


pmopm8Almchannel40PortIndex OBJECT-TYPE
	SYNTAX  INTEGER(0..128)
	MAX-ACCESS  read-only
	STATUS current
	DESCRIPTION
        "
        Index definition for the pmopm8Almchannel40Port
        table
        "
	::= { pmopm8Almchannel40PortEntry 1 }


pmopm8AlmChannel40OosPortn OBJECT-TYPE
	SYNTAX  EkiOnOff
	MAX-ACCESS read-only
	STATUS current
	DESCRIPTION
        "
        Channel Out Of Service 40 :This
        OID indicates that the channel
         is out of service  <Help> This
        alarm indicates that the channel
        is in service <Condtype> CHANNEL40_OOS_1
        <Probcause> informationalStatus(1000)
        <Alarmtype> other (1) <Polarity>
        (2)
        "
	::= { pmopm8Almchannel40PortEntry 7 }


pmopm8AlmChannel40PowerHighPortn OBJECT-TYPE
	SYNTAX  EkiOnOff
	MAX-ACCESS read-only
	STATUS current
	DESCRIPTION
        "
        Channel Power High 40 :This OID
        indicates that the power of the
        channel is higher than the configured
        threshold<Help> This alarm indicates
        that the power of the channel is
        higher than the configured threshold
        <Condtype> CHANNEL40_POWER_HIGH_1
        <Probcause> degradedSignal (13)
        <Alarmtype> equipmentAlarm <Polarity>
        (2)
        "
	::= { pmopm8Almchannel40PortEntry 6 }


pmopm8AlmChannel40PowerLowPortn OBJECT-TYPE
	SYNTAX  EkiOnOff
	MAX-ACCESS read-only
	STATUS current
	DESCRIPTION
        "
        Channel Power Low 40 :This OID
        indicates that the power of the
        channel is lower than the configured
        threshold<Help> This alarm indicates
        that the power of the channel is
        lower than the configured threshold
        <Condtype> CHANNEL40_POWER_LOW_1
        <Probcause> degradedSignal (13)
        <Alarmtype> equipmentAlarm <Polarity>
        (2)
        "
	::= { pmopm8Almchannel40PortEntry 5 }


pmopm8AlmChannel40BalancedPortn OBJECT-TYPE
	SYNTAX  EkiOnOff
	MAX-ACCESS read-only
	STATUS current
	DESCRIPTION
        "
        Channel Balanced 40 :This OID
         indicates that an in service channel
        is balanced by the Ekinops auto
        turn up application<Help> This
         status indicates that an in service
        channel is balanced by the Ekinops
        auto turn up application <Condtype>
        CHANNEL40_BALANCED_1 <Probcause>
        informationalStatus(1000) <Alarmtype>
        other (1) <Polarity> (2)
        "
	::= { pmopm8Almchannel40PortEntry 4 }


pmopm8AlmChannel40MismatchPortn OBJECT-TYPE
	SYNTAX  EkiOnOff
	MAX-ACCESS read-only
	STATUS current
	DESCRIPTION
        "
        Channel Mismatch 40 :This OID
         indicates that an out of service
        channel is detected on the Optical
        Power Monitoring input<Help> This
        alarm indicates that an out of
         service channel is detected on
        the Optical Power Monitoring input
        <Condtype> CHANNEL40_MISMATCH_1
        <Probcause> unexpectedInformation
        (75) <Alarmtype> equipmentAlarm
        <Polarity> (2)
        "
	::= { pmopm8Almchannel40PortEntry 3 }


pmopm8AlmChannel40AbsentPortn OBJECT-TYPE
	SYNTAX  EkiOnOff
	MAX-ACCESS read-only
	STATUS current
	DESCRIPTION
        "
        Channel Absent 40 :This OID indicates
        that an in service channel is absent
        on the Optical Power Monitoring
        input<Help> This alarm indicates
        that an in service channel is absent
        on the Optical Power Monitoring
        input <Condtype> CHANNEL40_ABSENT_1
        <Probcause> informationMissing
         (65) <Alarmtype> equipmentAlarm
        (5) <Polarity> (2)
        "
	::= { pmopm8Almchannel40PortEntry 2 }


--- *********************************************************
---     TABLE for the pmopm8Almchannel41Port articles
--- *********************************************************

pmopm8Almchannel41PortTable OBJECT-TYPE
	SYNTAX  SEQUENCE OF Pmopm8Almchannel41PortEntry
	MAX-ACCESS not-accessible
	STATUS current
	DESCRIPTION
        "
        List of pmopm8Almchannel41Port
        Article
        "
	::= { pmopm8AlmClientCrit 336 }


pmopm8Almchannel41PortEntry OBJECT-TYPE
	SYNTAX Pmopm8Almchannel41PortEntry
	MAX-ACCESS not-accessible
	STATUS current
	DESCRIPTION
        "
        Row definition for the pmopm8Almchannel41Port
        table
        "
	INDEX   { pmopm8Almchannel41PortIndex }
	::= { pmopm8Almchannel41PortTable 1 }


Pmopm8Almchannel41PortEntry ::=
	SEQUENCE {
	pmopm8Almchannel41PortIndex
		INTEGER,
	pmopm8AlmChannel41OosPortn
		EkiOnOff,
	pmopm8AlmChannel41PowerHighPortn
		EkiOnOff,
	pmopm8AlmChannel41PowerLowPortn
		EkiOnOff,
	pmopm8AlmChannel41BalancedPortn
		EkiOnOff,
	pmopm8AlmChannel41MismatchPortn
		EkiOnOff,
	pmopm8AlmChannel41AbsentPortn
		EkiOnOff
	}


pmopm8Almchannel41PortIndex OBJECT-TYPE
	SYNTAX  INTEGER(0..128)
	MAX-ACCESS  read-only
	STATUS current
	DESCRIPTION
        "
        Index definition for the pmopm8Almchannel41Port
        table
        "
	::= { pmopm8Almchannel41PortEntry 1 }


pmopm8AlmChannel41OosPortn OBJECT-TYPE
	SYNTAX  EkiOnOff
	MAX-ACCESS read-only
	STATUS current
	DESCRIPTION
        "
        Channel Out Of Service 41 :This
        OID indicates that the channel
         is out of service  <Help> This
        alarm indicates that the channel
        is in service <Condtype> CHANNEL41_OOS_1
        <Probcause> informationalStatus(1000)
        <Alarmtype> other (1) <Polarity>
        (2)
        "
	::= { pmopm8Almchannel41PortEntry 7 }


pmopm8AlmChannel41PowerHighPortn OBJECT-TYPE
	SYNTAX  EkiOnOff
	MAX-ACCESS read-only
	STATUS current
	DESCRIPTION
        "
        Channel Power High 41 :This OID
        indicates that the power of the
        channel is higher than the configured
        threshold<Help> This alarm indicates
        that the power of the channel is
        higher than the configured threshold
        <Condtype> CHANNEL41_POWER_HIGH_1
        <Probcause> degradedSignal (13)
        <Alarmtype> equipmentAlarm <Polarity>
        (2)
        "
	::= { pmopm8Almchannel41PortEntry 6 }


pmopm8AlmChannel41PowerLowPortn OBJECT-TYPE
	SYNTAX  EkiOnOff
	MAX-ACCESS read-only
	STATUS current
	DESCRIPTION
        "
        Channel Power Low 41 :This OID
        indicates that the power of the
        channel is lower than the configured
        threshold<Help> This alarm indicates
        that the power of the channel is
        lower than the configured threshold
        <Condtype> CHANNEL41_POWER_LOW_1
        <Probcause> degradedSignal (13)
        <Alarmtype> equipmentAlarm <Polarity>
        (2)
        "
	::= { pmopm8Almchannel41PortEntry 5 }


pmopm8AlmChannel41BalancedPortn OBJECT-TYPE
	SYNTAX  EkiOnOff
	MAX-ACCESS read-only
	STATUS current
	DESCRIPTION
        "
        Channel Balanced 41 :This OID
         indicates that an in service channel
        is balanced by the Ekinops auto
        turn up application<Help> This
         status indicates that an in service
        channel is balanced by the Ekinops
        auto turn up application <Condtype>
        CHANNEL41_BALANCED_1 <Probcause>
        informationalStatus(1000) <Alarmtype>
        other (1) <Polarity> (2)
        "
	::= { pmopm8Almchannel41PortEntry 4 }


pmopm8AlmChannel41MismatchPortn OBJECT-TYPE
	SYNTAX  EkiOnOff
	MAX-ACCESS read-only
	STATUS current
	DESCRIPTION
        "
        Channel Mismatch 41 :This OID
         indicates that an out of service
        channel is detected on the Optical
        Power Monitoring input<Help> This
        alarm indicates that an out of
         service channel is detected on
        the Optical Power Monitoring input
        <Condtype> CHANNEL41_MISMATCH_1
        <Probcause> unexpectedInformation
        (75) <Alarmtype> equipmentAlarm
        <Polarity> (2)
        "
	::= { pmopm8Almchannel41PortEntry 3 }


pmopm8AlmChannel41AbsentPortn OBJECT-TYPE
	SYNTAX  EkiOnOff
	MAX-ACCESS read-only
	STATUS current
	DESCRIPTION
        "
        Channel Absent 41 :This OID indicates
        that an in service channel is absent
        on the Optical Power Monitoring
        input<Help> This alarm indicates
        that an in service channel is absent
        on the Optical Power Monitoring
        input <Condtype> CHANNEL41_ABSENT_1
        <Probcause> informationMissing
         (65) <Alarmtype> equipmentAlarm
        (5) <Polarity> (2)
        "
	::= { pmopm8Almchannel41PortEntry 2 }


--- *********************************************************
---     TABLE for the pmopm8Almchannel42Port articles
--- *********************************************************

pmopm8Almchannel42PortTable OBJECT-TYPE
	SYNTAX  SEQUENCE OF Pmopm8Almchannel42PortEntry
	MAX-ACCESS not-accessible
	STATUS current
	DESCRIPTION
        "
        List of pmopm8Almchannel42Port
        Article
        "
	::= { pmopm8AlmClientCrit 344 }


pmopm8Almchannel42PortEntry OBJECT-TYPE
	SYNTAX Pmopm8Almchannel42PortEntry
	MAX-ACCESS not-accessible
	STATUS current
	DESCRIPTION
        "
        Row definition for the pmopm8Almchannel42Port
        table
        "
	INDEX   { pmopm8Almchannel42PortIndex }
	::= { pmopm8Almchannel42PortTable 1 }


Pmopm8Almchannel42PortEntry ::=
	SEQUENCE {
	pmopm8Almchannel42PortIndex
		INTEGER,
	pmopm8AlmChannel42OosPortn
		EkiOnOff,
	pmopm8AlmChannel42PowerHighPortn
		EkiOnOff,
	pmopm8AlmChannel42PowerLowPortn
		EkiOnOff,
	pmopm8AlmChannel42BalancedPortn
		EkiOnOff,
	pmopm8AlmChannel42MismatchPortn
		EkiOnOff,
	pmopm8AlmChannel42AbsentPortn
		EkiOnOff
	}


pmopm8Almchannel42PortIndex OBJECT-TYPE
	SYNTAX  INTEGER(0..128)
	MAX-ACCESS  read-only
	STATUS current
	DESCRIPTION
        "
        Index definition for the pmopm8Almchannel42Port
        table
        "
	::= { pmopm8Almchannel42PortEntry 1 }


pmopm8AlmChannel42OosPortn OBJECT-TYPE
	SYNTAX  EkiOnOff
	MAX-ACCESS read-only
	STATUS current
	DESCRIPTION
        "
        Channel Out Of Service 42 :This
        OID indicates that the channel
         is out of service  <Help> This
        alarm indicates that the channel
        is in service <Condtype> CHANNEL42_OOS_1
        <Probcause> informationalStatus(1000)
        <Alarmtype> other (1) <Polarity>
        (2)
        "
	::= { pmopm8Almchannel42PortEntry 7 }


pmopm8AlmChannel42PowerHighPortn OBJECT-TYPE
	SYNTAX  EkiOnOff
	MAX-ACCESS read-only
	STATUS current
	DESCRIPTION
        "
        Channel Power High 42 :This OID
        indicates that the power of the
        channel is higher than the configured
        threshold<Help> This alarm indicates
        that the power of the channel is
        higher than the configured threshold
        <Condtype> CHANNEL42_POWER_HIGH_1
        <Probcause> degradedSignal (13)
        <Alarmtype> equipmentAlarm <Polarity>
        (2)
        "
	::= { pmopm8Almchannel42PortEntry 6 }


pmopm8AlmChannel42PowerLowPortn OBJECT-TYPE
	SYNTAX  EkiOnOff
	MAX-ACCESS read-only
	STATUS current
	DESCRIPTION
        "
        Channel Power Low 42 :This OID
        indicates that the power of the
        channel is lower than the configured
        threshold<Help> This alarm indicates
        that the power of the channel is
        lower than the configured threshold
        <Condtype> CHANNEL42_POWER_LOW_1
        <Probcause> degradedSignal (13)
        <Alarmtype> equipmentAlarm <Polarity>
        (2)
        "
	::= { pmopm8Almchannel42PortEntry 5 }


pmopm8AlmChannel42BalancedPortn OBJECT-TYPE
	SYNTAX  EkiOnOff
	MAX-ACCESS read-only
	STATUS current
	DESCRIPTION
        "
        Channel Balanced 42 :This OID
         indicates that an in service channel
        is balanced by the Ekinops auto
        turn up application<Help> This
         status indicates that an in service
        channel is balanced by the Ekinops
        auto turn up application <Condtype>
        CHANNEL42_BALANCED_1 <Probcause>
        informationalStatus(1000) <Alarmtype>
        other (1) <Polarity> (2)
        "
	::= { pmopm8Almchannel42PortEntry 4 }


pmopm8AlmChannel42MismatchPortn OBJECT-TYPE
	SYNTAX  EkiOnOff
	MAX-ACCESS read-only
	STATUS current
	DESCRIPTION
        "
        Channel Mismatch 42 :This OID
         indicates that an out of service
        channel is detected on the Optical
        Power Monitoring input<Help> This
        alarm indicates that an out of
         service channel is detected on
        the Optical Power Monitoring input
        <Condtype> CHANNEL42_MISMATCH_1
        <Probcause> unexpectedInformation
        (75) <Alarmtype> equipmentAlarm
        <Polarity> (2)
        "
	::= { pmopm8Almchannel42PortEntry 3 }


pmopm8AlmChannel42AbsentPortn OBJECT-TYPE
	SYNTAX  EkiOnOff
	MAX-ACCESS read-only
	STATUS current
	DESCRIPTION
        "
        Channel Absent 42 :This OID indicates
        that an in service channel is absent
        on the Optical Power Monitoring
        input<Help> This alarm indicates
        that an in service channel is absent
        on the Optical Power Monitoring
        input <Condtype> CHANNEL42_ABSENT_1
        <Probcause> informationMissing
         (65) <Alarmtype> equipmentAlarm
        (5) <Polarity> (2)
        "
	::= { pmopm8Almchannel42PortEntry 2 }


--- *********************************************************
---     TABLE for the pmopm8Almchannel43Port articles
--- *********************************************************

pmopm8Almchannel43PortTable OBJECT-TYPE
	SYNTAX  SEQUENCE OF Pmopm8Almchannel43PortEntry
	MAX-ACCESS not-accessible
	STATUS current
	DESCRIPTION
        "
        List of pmopm8Almchannel43Port
        Article
        "
	::= { pmopm8AlmClientCrit 352 }


pmopm8Almchannel43PortEntry OBJECT-TYPE
	SYNTAX Pmopm8Almchannel43PortEntry
	MAX-ACCESS not-accessible
	STATUS current
	DESCRIPTION
        "
        Row definition for the pmopm8Almchannel43Port
        table
        "
	INDEX   { pmopm8Almchannel43PortIndex }
	::= { pmopm8Almchannel43PortTable 1 }


Pmopm8Almchannel43PortEntry ::=
	SEQUENCE {
	pmopm8Almchannel43PortIndex
		INTEGER,
	pmopm8AlmChannel43OosPortn
		EkiOnOff,
	pmopm8AlmChannel43PowerHighPortn
		EkiOnOff,
	pmopm8AlmChannel43PowerLowPortn
		EkiOnOff,
	pmopm8AlmChannel43BalancedPortn
		EkiOnOff,
	pmopm8AlmChannel43MismatchPortn
		EkiOnOff,
	pmopm8AlmChannel43AbsentPortn
		EkiOnOff
	}


pmopm8Almchannel43PortIndex OBJECT-TYPE
	SYNTAX  INTEGER(0..128)
	MAX-ACCESS  read-only
	STATUS current
	DESCRIPTION
        "
        Index definition for the pmopm8Almchannel43Port
        table
        "
	::= { pmopm8Almchannel43PortEntry 1 }


pmopm8AlmChannel43OosPortn OBJECT-TYPE
	SYNTAX  EkiOnOff
	MAX-ACCESS read-only
	STATUS current
	DESCRIPTION
        "
        Channel Out Of Service 43 :This
        OID indicates that the channel
         is out of service  <Help> This
        alarm indicates that the channel
        is in service <Condtype> CHANNEL43_OOS_1
        <Probcause> informationalStatus(1000)
        <Alarmtype> other (1) <Polarity>
        (2)
        "
	::= { pmopm8Almchannel43PortEntry 7 }


pmopm8AlmChannel43PowerHighPortn OBJECT-TYPE
	SYNTAX  EkiOnOff
	MAX-ACCESS read-only
	STATUS current
	DESCRIPTION
        "
        Channel Power High 43 :This OID
        indicates that the power of the
        channel is higher than the configured
        threshold<Help> This alarm indicates
        that the power of the channel is
        higher than the configured threshold
        <Condtype> CHANNEL43_POWER_HIGH_1
        <Probcause> degradedSignal (13)
        <Alarmtype> equipmentAlarm <Polarity>
        (2)
        "
	::= { pmopm8Almchannel43PortEntry 6 }


pmopm8AlmChannel43PowerLowPortn OBJECT-TYPE
	SYNTAX  EkiOnOff
	MAX-ACCESS read-only
	STATUS current
	DESCRIPTION
        "
        Channel Power Low 43 :This OID
        indicates that the power of the
        channel is lower than the configured
        threshold<Help> This alarm indicates
        that the power of the channel is
        lower than the configured threshold
        <Condtype> CHANNEL43_POWER_LOW_1
        <Probcause> degradedSignal (13)
        <Alarmtype> equipmentAlarm <Polarity>
        (2)
        "
	::= { pmopm8Almchannel43PortEntry 5 }


pmopm8AlmChannel43BalancedPortn OBJECT-TYPE
	SYNTAX  EkiOnOff
	MAX-ACCESS read-only
	STATUS current
	DESCRIPTION
        "
        Channel Balanced 43 :This OID
         indicates that an in service channel
        is balanced by the Ekinops auto
        turn up application<Help> This
         status indicates that an in service
        channel is balanced by the Ekinops
        auto turn up application <Condtype>
        CHANNEL43_BALANCED_1 <Probcause>
        informationalStatus(1000) <Alarmtype>
        other (1) <Polarity> (2)
        "
	::= { pmopm8Almchannel43PortEntry 4 }


pmopm8AlmChannel43MismatchPortn OBJECT-TYPE
	SYNTAX  EkiOnOff
	MAX-ACCESS read-only
	STATUS current
	DESCRIPTION
        "
        Channel Mismatch 43 :This OID
         indicates that an out of service
        channel is detected on the Optical
        Power Monitoring input<Help> This
        alarm indicates that an out of
         service channel is detected on
        the Optical Power Monitoring input
        <Condtype> CHANNEL43_MISMATCH_1
        <Probcause> unexpectedInformation
        (75) <Alarmtype> equipmentAlarm
        <Polarity> (2)
        "
	::= { pmopm8Almchannel43PortEntry 3 }


pmopm8AlmChannel43AbsentPortn OBJECT-TYPE
	SYNTAX  EkiOnOff
	MAX-ACCESS read-only
	STATUS current
	DESCRIPTION
        "
        Channel Absent 43 :This OID indicates
        that an in service channel is absent
        on the Optical Power Monitoring
        input<Help> This alarm indicates
        that an in service channel is absent
        on the Optical Power Monitoring
        input <Condtype> CHANNEL43_ABSENT_1
        <Probcause> informationMissing
         (65) <Alarmtype> equipmentAlarm
        (5) <Polarity> (2)
        "
	::= { pmopm8Almchannel43PortEntry 2 }


--- *********************************************************
---     TABLE for the pmopm8Almchannel44Port articles
--- *********************************************************

pmopm8Almchannel44PortTable OBJECT-TYPE
	SYNTAX  SEQUENCE OF Pmopm8Almchannel44PortEntry
	MAX-ACCESS not-accessible
	STATUS current
	DESCRIPTION
        "
        List of pmopm8Almchannel44Port
        Article
        "
	::= { pmopm8AlmClientCrit 360 }


pmopm8Almchannel44PortEntry OBJECT-TYPE
	SYNTAX Pmopm8Almchannel44PortEntry
	MAX-ACCESS not-accessible
	STATUS current
	DESCRIPTION
        "
        Row definition for the pmopm8Almchannel44Port
        table
        "
	INDEX   { pmopm8Almchannel44PortIndex }
	::= { pmopm8Almchannel44PortTable 1 }


Pmopm8Almchannel44PortEntry ::=
	SEQUENCE {
	pmopm8Almchannel44PortIndex
		INTEGER,
	pmopm8AlmChannel44OosPortn
		EkiOnOff,
	pmopm8AlmChannel44PowerHighPortn
		EkiOnOff,
	pmopm8AlmChannel44PowerLowPortn
		EkiOnOff,
	pmopm8AlmChannel44BalancedPortn
		EkiOnOff,
	pmopm8AlmChannel44MismatchPortn
		EkiOnOff,
	pmopm8AlmChannel44AbsentPortn
		EkiOnOff
	}


pmopm8Almchannel44PortIndex OBJECT-TYPE
	SYNTAX  INTEGER(0..128)
	MAX-ACCESS  read-only
	STATUS current
	DESCRIPTION
        "
        Index definition for the pmopm8Almchannel44Port
        table
        "
	::= { pmopm8Almchannel44PortEntry 1 }


pmopm8AlmChannel44OosPortn OBJECT-TYPE
	SYNTAX  EkiOnOff
	MAX-ACCESS read-only
	STATUS current
	DESCRIPTION
        "
        Channel Out Of Service 44 :This
        OID indicates that the channel
         is out of service  <Help> This
        alarm indicates that the channel
        is in service <Condtype> CHANNEL44_OOS_1
        <Probcause> informationalStatus(1000)
        <Alarmtype> other (1) <Polarity>
        (2)
        "
	::= { pmopm8Almchannel44PortEntry 7 }


pmopm8AlmChannel44PowerHighPortn OBJECT-TYPE
	SYNTAX  EkiOnOff
	MAX-ACCESS read-only
	STATUS current
	DESCRIPTION
        "
        Channel Power High 44 :This OID
        indicates that the power of the
        channel is higher than the configured
        threshold<Help> This alarm indicates
        that the power of the channel is
        higher than the configured threshold
        <Condtype> CHANNEL44_POWER_HIGH_1
        <Probcause> degradedSignal (13)
        <Alarmtype> equipmentAlarm <Polarity>
        (2)
        "
	::= { pmopm8Almchannel44PortEntry 6 }


pmopm8AlmChannel44PowerLowPortn OBJECT-TYPE
	SYNTAX  EkiOnOff
	MAX-ACCESS read-only
	STATUS current
	DESCRIPTION
        "
        Channel Power Low 44 :This OID
        indicates that the power of the
        channel is lower than the configured
        threshold<Help> This alarm indicates
        that the power of the channel is
        lower than the configured threshold
        <Condtype> CHANNEL44_POWER_LOW_1
        <Probcause> degradedSignal (13)
        <Alarmtype> equipmentAlarm <Polarity>
        (2)
        "
	::= { pmopm8Almchannel44PortEntry 5 }


pmopm8AlmChannel44BalancedPortn OBJECT-TYPE
	SYNTAX  EkiOnOff
	MAX-ACCESS read-only
	STATUS current
	DESCRIPTION
        "
        Channel Balanced 44 :This OID
         indicates that an in service channel
        is balanced by the Ekinops auto
        turn up application<Help> This
         status indicates that an in service
        channel is balanced by the Ekinops
        auto turn up application <Condtype>
        CHANNEL44_BALANCED_1 <Probcause>
        informationalStatus(1000) <Alarmtype>
        other (1) <Polarity> (2)
        "
	::= { pmopm8Almchannel44PortEntry 4 }


pmopm8AlmChannel44MismatchPortn OBJECT-TYPE
	SYNTAX  EkiOnOff
	MAX-ACCESS read-only
	STATUS current
	DESCRIPTION
        "
        Channel Mismatch 44 :This OID
         indicates that an out of service
        channel is detected on the Optical
        Power Monitoring input<Help> This
        alarm indicates that an out of
         service channel is detected on
        the Optical Power Monitoring input
        <Condtype> CHANNEL44_MISMATCH_1
        <Probcause> unexpectedInformation
        (75) <Alarmtype> equipmentAlarm
        <Polarity> (2)
        "
	::= { pmopm8Almchannel44PortEntry 3 }


pmopm8AlmChannel44AbsentPortn OBJECT-TYPE
	SYNTAX  EkiOnOff
	MAX-ACCESS read-only
	STATUS current
	DESCRIPTION
        "
        Channel Absent 44 :This OID indicates
        that an in service channel is absent
        on the Optical Power Monitoring
        input<Help> This alarm indicates
        that an in service channel is absent
        on the Optical Power Monitoring
        input <Condtype> CHANNEL44_ABSENT_1
        <Probcause> informationMissing
         (65) <Alarmtype> equipmentAlarm
        (5) <Polarity> (2)
        "
	::= { pmopm8Almchannel44PortEntry 2 }


--- *********************************************************
---     TABLE for the pmopm8Almchannel45Port articles
--- *********************************************************

pmopm8Almchannel45PortTable OBJECT-TYPE
	SYNTAX  SEQUENCE OF Pmopm8Almchannel45PortEntry
	MAX-ACCESS not-accessible
	STATUS current
	DESCRIPTION
        "
        List of pmopm8Almchannel45Port
        Article
        "
	::= { pmopm8AlmClientCrit 368 }


pmopm8Almchannel45PortEntry OBJECT-TYPE
	SYNTAX Pmopm8Almchannel45PortEntry
	MAX-ACCESS not-accessible
	STATUS current
	DESCRIPTION
        "
        Row definition for the pmopm8Almchannel45Port
        table
        "
	INDEX   { pmopm8Almchannel45PortIndex }
	::= { pmopm8Almchannel45PortTable 1 }


Pmopm8Almchannel45PortEntry ::=
	SEQUENCE {
	pmopm8Almchannel45PortIndex
		INTEGER,
	pmopm8AlmChannel45OosPortn
		EkiOnOff,
	pmopm8AlmChannel45PowerHighPortn
		EkiOnOff,
	pmopm8AlmChannel45PowerLowPortn
		EkiOnOff,
	pmopm8AlmChannel45BalancedPortn
		EkiOnOff,
	pmopm8AlmChannel45MismatchPortn
		EkiOnOff,
	pmopm8AlmChannel45AbsentPortn
		EkiOnOff
	}


pmopm8Almchannel45PortIndex OBJECT-TYPE
	SYNTAX  INTEGER(0..128)
	MAX-ACCESS  read-only
	STATUS current
	DESCRIPTION
        "
        Index definition for the pmopm8Almchannel45Port
        table
        "
	::= { pmopm8Almchannel45PortEntry 1 }


pmopm8AlmChannel45OosPortn OBJECT-TYPE
	SYNTAX  EkiOnOff
	MAX-ACCESS read-only
	STATUS current
	DESCRIPTION
        "
        Channel Out Of Service 45 :This
        OID indicates that the channel
         is out of service  <Help> This
        alarm indicates that the channel
        is in service <Condtype> CHANNEL45_OOS_1
        <Probcause> informationalStatus(1000)
        <Alarmtype> other (1) <Polarity>
        (2)
        "
	::= { pmopm8Almchannel45PortEntry 7 }


pmopm8AlmChannel45PowerHighPortn OBJECT-TYPE
	SYNTAX  EkiOnOff
	MAX-ACCESS read-only
	STATUS current
	DESCRIPTION
        "
        Channel Power High 45 :This OID
        indicates that the power of the
        channel is higher than the configured
        threshold<Help> This alarm indicates
        that the power of the channel is
        higher than the configured threshold
        <Condtype> CHANNEL45_POWER_HIGH_1
        <Probcause> degradedSignal (13)
        <Alarmtype> equipmentAlarm <Polarity>
        (2)
        "
	::= { pmopm8Almchannel45PortEntry 6 }


pmopm8AlmChannel45PowerLowPortn OBJECT-TYPE
	SYNTAX  EkiOnOff
	MAX-ACCESS read-only
	STATUS current
	DESCRIPTION
        "
        Channel Power Low 45 :This OID
        indicates that the power of the
        channel is lower than the configured
        threshold<Help> This alarm indicates
        that the power of the channel is
        lower than the configured threshold
        <Condtype> CHANNEL45_POWER_LOW_1
        <Probcause> degradedSignal (13)
        <Alarmtype> equipmentAlarm <Polarity>
        (2)
        "
	::= { pmopm8Almchannel45PortEntry 5 }


pmopm8AlmChannel45BalancedPortn OBJECT-TYPE
	SYNTAX  EkiOnOff
	MAX-ACCESS read-only
	STATUS current
	DESCRIPTION
        "
        Channel Balanced 45 :This OID
         indicates that an in service channel
        is balanced by the Ekinops auto
        turn up application<Help> This
         status indicates that an in service
        channel is balanced by the Ekinops
        auto turn up application <Condtype>
        CHANNEL45_BALANCED_1 <Probcause>
        informationalStatus(1000) <Alarmtype>
        other (1) <Polarity> (2)
        "
	::= { pmopm8Almchannel45PortEntry 4 }


pmopm8AlmChannel45MismatchPortn OBJECT-TYPE
	SYNTAX  EkiOnOff
	MAX-ACCESS read-only
	STATUS current
	DESCRIPTION
        "
        Channel Mismatch 45 :This OID
         indicates that an out of service
        channel is detected on the Optical
        Power Monitoring input<Help> This
        alarm indicates that an out of
         service channel is detected on
        the Optical Power Monitoring input
        <Condtype> CHANNEL45_MISMATCH_1
        <Probcause> unexpectedInformation
        (75) <Alarmtype> equipmentAlarm
        <Polarity> (2)
        "
	::= { pmopm8Almchannel45PortEntry 3 }


pmopm8AlmChannel45AbsentPortn OBJECT-TYPE
	SYNTAX  EkiOnOff
	MAX-ACCESS read-only
	STATUS current
	DESCRIPTION
        "
        Channel Absent 45 :This OID indicates
        that an in service channel is absent
        on the Optical Power Monitoring
        input<Help> This alarm indicates
        that an in service channel is absent
        on the Optical Power Monitoring
        input <Condtype> CHANNEL45_ABSENT_1
        <Probcause> informationMissing
         (65) <Alarmtype> equipmentAlarm
        (5) <Polarity> (2)
        "
	::= { pmopm8Almchannel45PortEntry 2 }


--- *********************************************************
---     TABLE for the pmopm8Almchannel46Port articles
--- *********************************************************

pmopm8Almchannel46PortTable OBJECT-TYPE
	SYNTAX  SEQUENCE OF Pmopm8Almchannel46PortEntry
	MAX-ACCESS not-accessible
	STATUS current
	DESCRIPTION
        "
        List of pmopm8Almchannel46Port
        Article
        "
	::= { pmopm8AlmClientCrit 376 }


pmopm8Almchannel46PortEntry OBJECT-TYPE
	SYNTAX Pmopm8Almchannel46PortEntry
	MAX-ACCESS not-accessible
	STATUS current
	DESCRIPTION
        "
        Row definition for the pmopm8Almchannel46Port
        table
        "
	INDEX   { pmopm8Almchannel46PortIndex }
	::= { pmopm8Almchannel46PortTable 1 }


Pmopm8Almchannel46PortEntry ::=
	SEQUENCE {
	pmopm8Almchannel46PortIndex
		INTEGER,
	pmopm8AlmChannel46OosPortn
		EkiOnOff,
	pmopm8AlmChannel46PowerHighPortn
		EkiOnOff,
	pmopm8AlmChannel46PowerLowPortn
		EkiOnOff,
	pmopm8AlmChannel46BalancedPortn
		EkiOnOff,
	pmopm8AlmChannel46MismatchPortn
		EkiOnOff,
	pmopm8AlmChannel46AbsentPortn
		EkiOnOff
	}


pmopm8Almchannel46PortIndex OBJECT-TYPE
	SYNTAX  INTEGER(0..128)
	MAX-ACCESS  read-only
	STATUS current
	DESCRIPTION
        "
        Index definition for the pmopm8Almchannel46Port
        table
        "
	::= { pmopm8Almchannel46PortEntry 1 }


pmopm8AlmChannel46OosPortn OBJECT-TYPE
	SYNTAX  EkiOnOff
	MAX-ACCESS read-only
	STATUS current
	DESCRIPTION
        "
        Channel Out Of Service 46 :This
        OID indicates that the channel
         is out of service  <Help> This
        alarm indicates that the channel
        is in service <Condtype> CHANNEL46_OOS_1
        <Probcause> informationalStatus(1000)
        <Alarmtype> other (1) <Polarity>
        (2)
        "
	::= { pmopm8Almchannel46PortEntry 7 }


pmopm8AlmChannel46PowerHighPortn OBJECT-TYPE
	SYNTAX  EkiOnOff
	MAX-ACCESS read-only
	STATUS current
	DESCRIPTION
        "
        Channel Power High 46 :This OID
        indicates that the power of the
        channel is higher than the configured
        threshold<Help> This alarm indicates
        that the power of the channel is
        higher than the configured threshold
        <Condtype> CHANNEL46_POWER_HIGH_1
        <Probcause> degradedSignal (13)
        <Alarmtype> equipmentAlarm <Polarity>
        (2)
        "
	::= { pmopm8Almchannel46PortEntry 6 }


pmopm8AlmChannel46PowerLowPortn OBJECT-TYPE
	SYNTAX  EkiOnOff
	MAX-ACCESS read-only
	STATUS current
	DESCRIPTION
        "
        Channel Power Low 46 :This OID
        indicates that the power of the
        channel is lower than the configured
        threshold<Help> This alarm indicates
        that the power of the channel is
        lower than the configured threshold
        <Condtype> CHANNEL46_POWER_LOW_1
        <Probcause> degradedSignal (13)
        <Alarmtype> equipmentAlarm <Polarity>
        (2)
        "
	::= { pmopm8Almchannel46PortEntry 5 }


pmopm8AlmChannel46BalancedPortn OBJECT-TYPE
	SYNTAX  EkiOnOff
	MAX-ACCESS read-only
	STATUS current
	DESCRIPTION
        "
        Channel Balanced 46 :This OID
         indicates that an in service channel
        is balanced by the Ekinops auto
        turn up application<Help> This
         status indicates that an in service
        channel is balanced by the Ekinops
        auto turn up application <Condtype>
        CHANNEL46_BALANCED_1 <Probcause>
        informationalStatus(1000) <Alarmtype>
        other (1) <Polarity> (2)
        "
	::= { pmopm8Almchannel46PortEntry 4 }


pmopm8AlmChannel46MismatchPortn OBJECT-TYPE
	SYNTAX  EkiOnOff
	MAX-ACCESS read-only
	STATUS current
	DESCRIPTION
        "
        Channel Mismatch 46 :This OID
         indicates that an out of service
        channel is detected on the Optical
        Power Monitoring input<Help> This
        alarm indicates that an out of
         service channel is detected on
        the Optical Power Monitoring input
        <Condtype> CHANNEL46_MISMATCH_1
        <Probcause> unexpectedInformation
        (75) <Alarmtype> equipmentAlarm
        <Polarity> (2)
        "
	::= { pmopm8Almchannel46PortEntry 3 }


pmopm8AlmChannel46AbsentPortn OBJECT-TYPE
	SYNTAX  EkiOnOff
	MAX-ACCESS read-only
	STATUS current
	DESCRIPTION
        "
        Channel Absent 46 :This OID indicates
        that an in service channel is absent
        on the Optical Power Monitoring
        input<Help> This alarm indicates
        that an in service channel is absent
        on the Optical Power Monitoring
        input <Condtype> CHANNEL46_ABSENT_1
        <Probcause> informationMissing
         (65) <Alarmtype> equipmentAlarm
        (5) <Polarity> (2)
        "
	::= { pmopm8Almchannel46PortEntry 2 }


--- *********************************************************
---     TABLE for the pmopm8Almchannel47Port articles
--- *********************************************************

pmopm8Almchannel47PortTable OBJECT-TYPE
	SYNTAX  SEQUENCE OF Pmopm8Almchannel47PortEntry
	MAX-ACCESS not-accessible
	STATUS current
	DESCRIPTION
        "
        List of pmopm8Almchannel47Port
        Article
        "
	::= { pmopm8AlmClientCrit 384 }


pmopm8Almchannel47PortEntry OBJECT-TYPE
	SYNTAX Pmopm8Almchannel47PortEntry
	MAX-ACCESS not-accessible
	STATUS current
	DESCRIPTION
        "
        Row definition for the pmopm8Almchannel47Port
        table
        "
	INDEX   { pmopm8Almchannel47PortIndex }
	::= { pmopm8Almchannel47PortTable 1 }


Pmopm8Almchannel47PortEntry ::=
	SEQUENCE {
	pmopm8Almchannel47PortIndex
		INTEGER,
	pmopm8AlmChannel47OosPortn
		EkiOnOff,
	pmopm8AlmChannel47PowerHighPortn
		EkiOnOff,
	pmopm8AlmChannel47PowerLowPortn
		EkiOnOff,
	pmopm8AlmChannel47BalancedPortn
		EkiOnOff,
	pmopm8AlmChannel47MismatchPortn
		EkiOnOff,
	pmopm8AlmChannel47AbsentPortn
		EkiOnOff
	}


pmopm8Almchannel47PortIndex OBJECT-TYPE
	SYNTAX  INTEGER(0..128)
	MAX-ACCESS  read-only
	STATUS current
	DESCRIPTION
        "
        Index definition for the pmopm8Almchannel47Port
        table
        "
	::= { pmopm8Almchannel47PortEntry 1 }


pmopm8AlmChannel47OosPortn OBJECT-TYPE
	SYNTAX  EkiOnOff
	MAX-ACCESS read-only
	STATUS current
	DESCRIPTION
        "
        Channel Out Of Service 47 :This
        OID indicates that the channel
         is out of service  <Help> This
        alarm indicates that the channel
        is in service <Condtype> CHANNEL47_OOS_1
        <Probcause> informationalStatus(1000)
        <Alarmtype> other (1) <Polarity>
        (2)
        "
	::= { pmopm8Almchannel47PortEntry 7 }


pmopm8AlmChannel47PowerHighPortn OBJECT-TYPE
	SYNTAX  EkiOnOff
	MAX-ACCESS read-only
	STATUS current
	DESCRIPTION
        "
        Channel Power High 47 :This OID
        indicates that the power of the
        channel is higher than the configured
        threshold<Help> This alarm indicates
        that the power of the channel is
        higher than the configured threshold
        <Condtype> CHANNEL47_POWER_HIGH_1
        <Probcause> degradedSignal (13)
        <Alarmtype> equipmentAlarm <Polarity>
        (2)
        "
	::= { pmopm8Almchannel47PortEntry 6 }


pmopm8AlmChannel47PowerLowPortn OBJECT-TYPE
	SYNTAX  EkiOnOff
	MAX-ACCESS read-only
	STATUS current
	DESCRIPTION
        "
        Channel Power Low 47 :This OID
        indicates that the power of the
        channel is lower than the configured
        threshold<Help> This alarm indicates
        that the power of the channel is
        lower than the configured threshold
        <Condtype> CHANNEL47_POWER_LOW_1
        <Probcause> degradedSignal (13)
        <Alarmtype> equipmentAlarm <Polarity>
        (2)
        "
	::= { pmopm8Almchannel47PortEntry 5 }


pmopm8AlmChannel47BalancedPortn OBJECT-TYPE
	SYNTAX  EkiOnOff
	MAX-ACCESS read-only
	STATUS current
	DESCRIPTION
        "
        Channel Balanced 47 :This OID
         indicates that an in service channel
        is balanced by the Ekinops auto
        turn up application<Help> This
         status indicates that an in service
        channel is balanced by the Ekinops
        auto turn up application <Condtype>
        CHANNEL47_BALANCED_1 <Probcause>
        informationalStatus(1000) <Alarmtype>
        other (1) <Polarity> (2)
        "
	::= { pmopm8Almchannel47PortEntry 4 }


pmopm8AlmChannel47MismatchPortn OBJECT-TYPE
	SYNTAX  EkiOnOff
	MAX-ACCESS read-only
	STATUS current
	DESCRIPTION
        "
        Channel Mismatch 47 :This OID
         indicates that an out of service
        channel is detected on the Optical
        Power Monitoring input<Help> This
        alarm indicates that an out of
         service channel is detected on
        the Optical Power Monitoring input
        <Condtype> CHANNEL47_MISMATCH_1
        <Probcause> unexpectedInformation
        (75) <Alarmtype> equipmentAlarm
        <Polarity> (2)
        "
	::= { pmopm8Almchannel47PortEntry 3 }


pmopm8AlmChannel47AbsentPortn OBJECT-TYPE
	SYNTAX  EkiOnOff
	MAX-ACCESS read-only
	STATUS current
	DESCRIPTION
        "
        Channel Absent 47 :This OID indicates
        that an in service channel is absent
        on the Optical Power Monitoring
        input<Help> This alarm indicates
        that an in service channel is absent
        on the Optical Power Monitoring
        input <Condtype> CHANNEL47_ABSENT_1
        <Probcause> informationMissing
         (65) <Alarmtype> equipmentAlarm
        (5) <Polarity> (2)
        "
	::= { pmopm8Almchannel47PortEntry 2 }


--- *********************************************************
---     TABLE for the pmopm8Almchannel48Port articles
--- *********************************************************

pmopm8Almchannel48PortTable OBJECT-TYPE
	SYNTAX  SEQUENCE OF Pmopm8Almchannel48PortEntry
	MAX-ACCESS not-accessible
	STATUS current
	DESCRIPTION
        "
        List of pmopm8Almchannel48Port
        Article
        "
	::= { pmopm8AlmClientCrit 392 }


pmopm8Almchannel48PortEntry OBJECT-TYPE
	SYNTAX Pmopm8Almchannel48PortEntry
	MAX-ACCESS not-accessible
	STATUS current
	DESCRIPTION
        "
        Row definition for the pmopm8Almchannel48Port
        table
        "
	INDEX   { pmopm8Almchannel48PortIndex }
	::= { pmopm8Almchannel48PortTable 1 }


Pmopm8Almchannel48PortEntry ::=
	SEQUENCE {
	pmopm8Almchannel48PortIndex
		INTEGER,
	pmopm8AlmChannel48OosPortn
		EkiOnOff,
	pmopm8AlmChannel48PowerHighPortn
		EkiOnOff,
	pmopm8AlmChannel48PowerLowPortn
		EkiOnOff,
	pmopm8AlmChannel48BalancedPortn
		EkiOnOff,
	pmopm8AlmChannel48MismatchPortn
		EkiOnOff,
	pmopm8AlmChannel48AbsentPortn
		EkiOnOff
	}


pmopm8Almchannel48PortIndex OBJECT-TYPE
	SYNTAX  INTEGER(0..128)
	MAX-ACCESS  read-only
	STATUS current
	DESCRIPTION
        "
        Index definition for the pmopm8Almchannel48Port
        table
        "
	::= { pmopm8Almchannel48PortEntry 1 }


pmopm8AlmChannel48OosPortn OBJECT-TYPE
	SYNTAX  EkiOnOff
	MAX-ACCESS read-only
	STATUS current
	DESCRIPTION
        "
        Channel Out Of Service 48 :This
        OID indicates that the channel
         is out of service  <Help> This
        alarm indicates that the channel
        is in service <Condtype> CHANNEL48_OOS_1
        <Probcause> informationalStatus(1000)
        <Alarmtype> other (1) <Polarity>
        (2)
        "
	::= { pmopm8Almchannel48PortEntry 7 }


pmopm8AlmChannel48PowerHighPortn OBJECT-TYPE
	SYNTAX  EkiOnOff
	MAX-ACCESS read-only
	STATUS current
	DESCRIPTION
        "
        Channel Power High 48 :This OID
        indicates that the power of the
        channel is higher than the configured
        threshold<Help> This alarm indicates
        that the power of the channel is
        higher than the configured threshold
        <Condtype> CHANNEL48_POWER_HIGH_1
        <Probcause> degradedSignal (13)
        <Alarmtype> equipmentAlarm <Polarity>
        (2)
        "
	::= { pmopm8Almchannel48PortEntry 6 }


pmopm8AlmChannel48PowerLowPortn OBJECT-TYPE
	SYNTAX  EkiOnOff
	MAX-ACCESS read-only
	STATUS current
	DESCRIPTION
        "
        Channel Power Low 48 :This OID
        indicates that the power of the
        channel is lower than the configured
        threshold<Help> This alarm indicates
        that the power of the channel is
        lower than the configured threshold
        <Condtype> CHANNEL48_POWER_LOW_1
        <Probcause> degradedSignal (13)
        <Alarmtype> equipmentAlarm <Polarity>
        (2)
        "
	::= { pmopm8Almchannel48PortEntry 5 }


pmopm8AlmChannel48BalancedPortn OBJECT-TYPE
	SYNTAX  EkiOnOff
	MAX-ACCESS read-only
	STATUS current
	DESCRIPTION
        "
        Channel Balanced 48 :This OID
         indicates that an in service channel
        is balanced by the Ekinops auto
        turn up application<Help> This
         status indicates that an in service
        channel is balanced by the Ekinops
        auto turn up application <Condtype>
        CHANNEL48_BALANCED_1 <Probcause>
        informationalStatus(1000) <Alarmtype>
        other (1) <Polarity> (2)
        "
	::= { pmopm8Almchannel48PortEntry 4 }


pmopm8AlmChannel48MismatchPortn OBJECT-TYPE
	SYNTAX  EkiOnOff
	MAX-ACCESS read-only
	STATUS current
	DESCRIPTION
        "
        Channel Mismatch 48 :This OID
         indicates that an out of service
        channel is detected on the Optical
        Power Monitoring input<Help> This
        alarm indicates that an out of
         service channel is detected on
        the Optical Power Monitoring input
        <Condtype> CHANNEL48_MISMATCH_1
        <Probcause> unexpectedInformation
        (75) <Alarmtype> equipmentAlarm
        <Polarity> (2)
        "
	::= { pmopm8Almchannel48PortEntry 3 }


pmopm8AlmChannel48AbsentPortn OBJECT-TYPE
	SYNTAX  EkiOnOff
	MAX-ACCESS read-only
	STATUS current
	DESCRIPTION
        "
        Channel Absent 48 :This OID indicates
        that an in service channel is absent
        on the Optical Power Monitoring
        input<Help> This alarm indicates
        that an in service channel is absent
        on the Optical Power Monitoring
        input <Condtype> CHANNEL48_ABSENT_1
        <Probcause> informationMissing
         (65) <Alarmtype> equipmentAlarm
        (5) <Polarity> (2)
        "
	::= { pmopm8Almchannel48PortEntry 2 }


--- *********************************************************
---     TABLE for the pmopm8Almchannel49Port articles
--- *********************************************************

pmopm8Almchannel49PortTable OBJECT-TYPE
	SYNTAX  SEQUENCE OF Pmopm8Almchannel49PortEntry
	MAX-ACCESS not-accessible
	STATUS current
	DESCRIPTION
        "
        List of pmopm8Almchannel49Port
        Article
        "
	::= { pmopm8AlmClientCrit 400 }


pmopm8Almchannel49PortEntry OBJECT-TYPE
	SYNTAX Pmopm8Almchannel49PortEntry
	MAX-ACCESS not-accessible
	STATUS current
	DESCRIPTION
        "
        Row definition for the pmopm8Almchannel49Port
        table
        "
	INDEX   { pmopm8Almchannel49PortIndex }
	::= { pmopm8Almchannel49PortTable 1 }


Pmopm8Almchannel49PortEntry ::=
	SEQUENCE {
	pmopm8Almchannel49PortIndex
		INTEGER,
	pmopm8AlmChannel49OosPortn
		EkiOnOff,
	pmopm8AlmChannel49PowerHighPortn
		EkiOnOff,
	pmopm8AlmChannel49PowerLowPortn
		EkiOnOff,
	pmopm8AlmChannel49BalancedPortn
		EkiOnOff,
	pmopm8AlmChannel49MismatchPortn
		EkiOnOff,
	pmopm8AlmChannel49AbsentPortn
		EkiOnOff
	}


pmopm8Almchannel49PortIndex OBJECT-TYPE
	SYNTAX  INTEGER(0..128)
	MAX-ACCESS  read-only
	STATUS current
	DESCRIPTION
        "
        Index definition for the pmopm8Almchannel49Port
        table
        "
	::= { pmopm8Almchannel49PortEntry 1 }


pmopm8AlmChannel49OosPortn OBJECT-TYPE
	SYNTAX  EkiOnOff
	MAX-ACCESS read-only
	STATUS current
	DESCRIPTION
        "
        Channel Out Of Service 49 :This
        OID indicates that the channel
         is out of service  <Help> This
        alarm indicates that the channel
        is in service <Condtype> CHANNEL49_OOS_1
        <Probcause> informationalStatus(1000)
        <Alarmtype> other (1) <Polarity>
        (2)
        "
	::= { pmopm8Almchannel49PortEntry 7 }


pmopm8AlmChannel49PowerHighPortn OBJECT-TYPE
	SYNTAX  EkiOnOff
	MAX-ACCESS read-only
	STATUS current
	DESCRIPTION
        "
        Channel Power High 49 :This OID
        indicates that the power of the
        channel is higher than the configured
        threshold<Help> This alarm indicates
        that the power of the channel is
        higher than the configured threshold
        <Condtype> CHANNEL49_POWER_HIGH_1
        <Probcause> degradedSignal (13)
        <Alarmtype> equipmentAlarm <Polarity>
        (2)
        "
	::= { pmopm8Almchannel49PortEntry 6 }


pmopm8AlmChannel49PowerLowPortn OBJECT-TYPE
	SYNTAX  EkiOnOff
	MAX-ACCESS read-only
	STATUS current
	DESCRIPTION
        "
        Channel Power Low 49 :This OID
        indicates that the power of the
        channel is lower than the configured
        threshold<Help> This alarm indicates
        that the power of the channel is
        lower than the configured threshold
        <Condtype> CHANNEL49_POWER_LOW_1
        <Probcause> degradedSignal (13)
        <Alarmtype> equipmentAlarm <Polarity>
        (2)
        "
	::= { pmopm8Almchannel49PortEntry 5 }


pmopm8AlmChannel49BalancedPortn OBJECT-TYPE
	SYNTAX  EkiOnOff
	MAX-ACCESS read-only
	STATUS current
	DESCRIPTION
        "
        Channel Balanced 49 :This OID
         indicates that an in service channel
        is balanced by the Ekinops auto
        turn up application<Help> This
         status indicates that an in service
        channel is balanced by the Ekinops
        auto turn up application <Condtype>
        CHANNEL49_BALANCED_1 <Probcause>
        informationalStatus(1000) <Alarmtype>
        other (1) <Polarity> (2)
        "
	::= { pmopm8Almchannel49PortEntry 4 }


pmopm8AlmChannel49MismatchPortn OBJECT-TYPE
	SYNTAX  EkiOnOff
	MAX-ACCESS read-only
	STATUS current
	DESCRIPTION
        "
        Channel Mismatch 49 :This OID
         indicates that an out of service
        channel is detected on the Optical
        Power Monitoring input<Help> This
        alarm indicates that an out of
         service channel is detected on
        the Optical Power Monitoring input
        <Condtype> CHANNEL49_MISMATCH_1
        <Probcause> unexpectedInformation
        (75) <Alarmtype> equipmentAlarm
        <Polarity> (2)
        "
	::= { pmopm8Almchannel49PortEntry 3 }


pmopm8AlmChannel49AbsentPortn OBJECT-TYPE
	SYNTAX  EkiOnOff
	MAX-ACCESS read-only
	STATUS current
	DESCRIPTION
        "
        Channel Absent 49 :This OID indicates
        that an in service channel is absent
        on the Optical Power Monitoring
        input<Help> This alarm indicates
        that an in service channel is absent
        on the Optical Power Monitoring
        input <Condtype> CHANNEL49_ABSENT_1
        <Probcause> informationMissing
         (65) <Alarmtype> equipmentAlarm
        (5) <Polarity> (2)
        "
	::= { pmopm8Almchannel49PortEntry 2 }


--- *********************************************************
---     TABLE for the pmopm8Almchannel50Port articles
--- *********************************************************

pmopm8Almchannel50PortTable OBJECT-TYPE
	SYNTAX  SEQUENCE OF Pmopm8Almchannel50PortEntry
	MAX-ACCESS not-accessible
	STATUS current
	DESCRIPTION
        "
        List of pmopm8Almchannel50Port
        Article
        "
	::= { pmopm8AlmClientCrit 408 }


pmopm8Almchannel50PortEntry OBJECT-TYPE
	SYNTAX Pmopm8Almchannel50PortEntry
	MAX-ACCESS not-accessible
	STATUS current
	DESCRIPTION
        "
        Row definition for the pmopm8Almchannel50Port
        table
        "
	INDEX   { pmopm8Almchannel50PortIndex }
	::= { pmopm8Almchannel50PortTable 1 }


Pmopm8Almchannel50PortEntry ::=
	SEQUENCE {
	pmopm8Almchannel50PortIndex
		INTEGER,
	pmopm8AlmChannel50OosPortn
		EkiOnOff,
	pmopm8AlmChannel50PowerHighPortn
		EkiOnOff,
	pmopm8AlmChannel50PowerLowPortn
		EkiOnOff,
	pmopm8AlmChannel50BalancedPortn
		EkiOnOff,
	pmopm8AlmChannel50MismatchPortn
		EkiOnOff,
	pmopm8AlmChannel50AbsentPortn
		EkiOnOff
	}


pmopm8Almchannel50PortIndex OBJECT-TYPE
	SYNTAX  INTEGER(0..128)
	MAX-ACCESS  read-only
	STATUS current
	DESCRIPTION
        "
        Index definition for the pmopm8Almchannel50Port
        table
        "
	::= { pmopm8Almchannel50PortEntry 1 }


pmopm8AlmChannel50OosPortn OBJECT-TYPE
	SYNTAX  EkiOnOff
	MAX-ACCESS read-only
	STATUS current
	DESCRIPTION
        "
        Channel Out Of Service 50 :This
        OID indicates that the channel
         is out of service  <Help> This
        alarm indicates that the channel
        is in service <Condtype> CHANNEL50_OOS_1
        <Probcause> informationalStatus(1000)
        <Alarmtype> other (1) <Polarity>
        (2)
        "
	::= { pmopm8Almchannel50PortEntry 7 }


pmopm8AlmChannel50PowerHighPortn OBJECT-TYPE
	SYNTAX  EkiOnOff
	MAX-ACCESS read-only
	STATUS current
	DESCRIPTION
        "
        Channel Power High 50 :This OID
        indicates that the power of the
        channel is higher than the configured
        threshold<Help> This alarm indicates
        that the power of the channel is
        higher than the configured threshold
        <Condtype> CHANNEL50_POWER_HIGH_1
        <Probcause> degradedSignal (13)
        <Alarmtype> equipmentAlarm <Polarity>
        (2)
        "
	::= { pmopm8Almchannel50PortEntry 6 }


pmopm8AlmChannel50PowerLowPortn OBJECT-TYPE
	SYNTAX  EkiOnOff
	MAX-ACCESS read-only
	STATUS current
	DESCRIPTION
        "
        Channel Power Low 50 :This OID
        indicates that the power of the
        channel is lower than the configured
        threshold<Help> This alarm indicates
        that the power of the channel is
        lower than the configured threshold
        <Condtype> CHANNEL50_POWER_LOW_1
        <Probcause> degradedSignal (13)
        <Alarmtype> equipmentAlarm <Polarity>
        (2)
        "
	::= { pmopm8Almchannel50PortEntry 5 }


pmopm8AlmChannel50BalancedPortn OBJECT-TYPE
	SYNTAX  EkiOnOff
	MAX-ACCESS read-only
	STATUS current
	DESCRIPTION
        "
        Channel Balanced 50 :This OID
         indicates that an in service channel
        is balanced by the Ekinops auto
        turn up application<Help> This
         status indicates that an in service
        channel is balanced by the Ekinops
        auto turn up application <Condtype>
        CHANNEL50_BALANCED_1 <Probcause>
        informationalStatus(1000) <Alarmtype>
        other (1) <Polarity> (2)
        "
	::= { pmopm8Almchannel50PortEntry 4 }


pmopm8AlmChannel50MismatchPortn OBJECT-TYPE
	SYNTAX  EkiOnOff
	MAX-ACCESS read-only
	STATUS current
	DESCRIPTION
        "
        Channel Mismatch 50 :This OID
         indicates that an out of service
        channel is detected on the Optical
        Power Monitoring input<Help> This
        alarm indicates that an out of
         service channel is detected on
        the Optical Power Monitoring input
        <Condtype> CHANNEL50_MISMATCH_1
        <Probcause> unexpectedInformation
        (75) <Alarmtype> equipmentAlarm
        <Polarity> (2)
        "
	::= { pmopm8Almchannel50PortEntry 3 }


pmopm8AlmChannel50AbsentPortn OBJECT-TYPE
	SYNTAX  EkiOnOff
	MAX-ACCESS read-only
	STATUS current
	DESCRIPTION
        "
        Channel Absent 50 :This OID indicates
        that an in service channel is absent
        on the Optical Power Monitoring
        input<Help> This alarm indicates
        that an in service channel is absent
        on the Optical Power Monitoring
        input <Condtype> CHANNEL50_ABSENT_1
        <Probcause> informationMissing
         (65) <Alarmtype> equipmentAlarm
        (5) <Polarity> (2)
        "
	::= { pmopm8Almchannel50PortEntry 2 }


--- *********************************************************
---     TABLE for the pmopm8Almchannel51Port articles
--- *********************************************************

pmopm8Almchannel51PortTable OBJECT-TYPE
	SYNTAX  SEQUENCE OF Pmopm8Almchannel51PortEntry
	MAX-ACCESS not-accessible
	STATUS current
	DESCRIPTION
        "
        List of pmopm8Almchannel51Port
        Article
        "
	::= { pmopm8AlmClientCrit 416 }


pmopm8Almchannel51PortEntry OBJECT-TYPE
	SYNTAX Pmopm8Almchannel51PortEntry
	MAX-ACCESS not-accessible
	STATUS current
	DESCRIPTION
        "
        Row definition for the pmopm8Almchannel51Port
        table
        "
	INDEX   { pmopm8Almchannel51PortIndex }
	::= { pmopm8Almchannel51PortTable 1 }


Pmopm8Almchannel51PortEntry ::=
	SEQUENCE {
	pmopm8Almchannel51PortIndex
		INTEGER,
	pmopm8AlmChannel51OosPortn
		EkiOnOff,
	pmopm8AlmChannel51PowerHighPortn
		EkiOnOff,
	pmopm8AlmChannel51PowerLowPortn
		EkiOnOff,
	pmopm8AlmChannel51BalancedPortn
		EkiOnOff,
	pmopm8AlmChannel51MismatchPortn
		EkiOnOff,
	pmopm8AlmChannel51AbsentPortn
		EkiOnOff
	}


pmopm8Almchannel51PortIndex OBJECT-TYPE
	SYNTAX  INTEGER(0..128)
	MAX-ACCESS  read-only
	STATUS current
	DESCRIPTION
        "
        Index definition for the pmopm8Almchannel51Port
        table
        "
	::= { pmopm8Almchannel51PortEntry 1 }


pmopm8AlmChannel51OosPortn OBJECT-TYPE
	SYNTAX  EkiOnOff
	MAX-ACCESS read-only
	STATUS current
	DESCRIPTION
        "
        Channel Out Of Service 51 :This
        OID indicates that the channel
         is out of service  <Help> This
        alarm indicates that the channel
        is in service <Condtype> CHANNEL51_OOS_1
        <Probcause> informationalStatus(1000)
        <Alarmtype> other (1) <Polarity>
        (2)
        "
	::= { pmopm8Almchannel51PortEntry 7 }


pmopm8AlmChannel51PowerHighPortn OBJECT-TYPE
	SYNTAX  EkiOnOff
	MAX-ACCESS read-only
	STATUS current
	DESCRIPTION
        "
        Channel Power High 51 :This OID
        indicates that the power of the
        channel is higher than the configured
        threshold<Help> This alarm indicates
        that the power of the channel is
        higher than the configured threshold
        <Condtype> CHANNEL51_POWER_HIGH_1
        <Probcause> degradedSignal (13)
        <Alarmtype> equipmentAlarm <Polarity>
        (2)
        "
	::= { pmopm8Almchannel51PortEntry 6 }


pmopm8AlmChannel51PowerLowPortn OBJECT-TYPE
	SYNTAX  EkiOnOff
	MAX-ACCESS read-only
	STATUS current
	DESCRIPTION
        "
        Channel Power Low 51 :This OID
        indicates that the power of the
        channel is lower than the configured
        threshold<Help> This alarm indicates
        that the power of the channel is
        lower than the configured threshold
        <Condtype> CHANNEL51_POWER_LOW_1
        <Probcause> degradedSignal (13)
        <Alarmtype> equipmentAlarm <Polarity>
        (2)
        "
	::= { pmopm8Almchannel51PortEntry 5 }


pmopm8AlmChannel51BalancedPortn OBJECT-TYPE
	SYNTAX  EkiOnOff
	MAX-ACCESS read-only
	STATUS current
	DESCRIPTION
        "
        Channel Balanced 51 :This OID
         indicates that an in service channel
        is balanced by the Ekinops auto
        turn up application<Help> This
         status indicates that an in service
        channel is balanced by the Ekinops
        auto turn up application <Condtype>
        CHANNEL51_BALANCED_1 <Probcause>
        informationalStatus(1000) <Alarmtype>
        other (1) <Polarity> (2)
        "
	::= { pmopm8Almchannel51PortEntry 4 }


pmopm8AlmChannel51MismatchPortn OBJECT-TYPE
	SYNTAX  EkiOnOff
	MAX-ACCESS read-only
	STATUS current
	DESCRIPTION
        "
        Channel Mismatch 51 :This OID
         indicates that an out of service
        channel is detected on the Optical
        Power Monitoring input<Help> This
        alarm indicates that an out of
         service channel is detected on
        the Optical Power Monitoring input
        <Condtype> CHANNEL51_MISMATCH_1
        <Probcause> unexpectedInformation
        (75) <Alarmtype> equipmentAlarm
        <Polarity> (2)
        "
	::= { pmopm8Almchannel51PortEntry 3 }


pmopm8AlmChannel51AbsentPortn OBJECT-TYPE
	SYNTAX  EkiOnOff
	MAX-ACCESS read-only
	STATUS current
	DESCRIPTION
        "
        Channel Absent 51 :This OID indicates
        that an in service channel is absent
        on the Optical Power Monitoring
        input<Help> This alarm indicates
        that an in service channel is absent
        on the Optical Power Monitoring
        input <Condtype> CHANNEL51_ABSENT_1
        <Probcause> informationMissing
         (65) <Alarmtype> equipmentAlarm
        (5) <Polarity> (2)
        "
	::= { pmopm8Almchannel51PortEntry 2 }


--- *********************************************************
---     TABLE for the pmopm8Almchannel52Port articles
--- *********************************************************

pmopm8Almchannel52PortTable OBJECT-TYPE
	SYNTAX  SEQUENCE OF Pmopm8Almchannel52PortEntry
	MAX-ACCESS not-accessible
	STATUS current
	DESCRIPTION
        "
        List of pmopm8Almchannel52Port
        Article
        "
	::= { pmopm8AlmClientCrit 424 }


pmopm8Almchannel52PortEntry OBJECT-TYPE
	SYNTAX Pmopm8Almchannel52PortEntry
	MAX-ACCESS not-accessible
	STATUS current
	DESCRIPTION
        "
        Row definition for the pmopm8Almchannel52Port
        table
        "
	INDEX   { pmopm8Almchannel52PortIndex }
	::= { pmopm8Almchannel52PortTable 1 }


Pmopm8Almchannel52PortEntry ::=
	SEQUENCE {
	pmopm8Almchannel52PortIndex
		INTEGER,
	pmopm8AlmChannel52OosPortn
		EkiOnOff,
	pmopm8AlmChannel52PowerHighPortn
		EkiOnOff,
	pmopm8AlmChannel52PowerLowPortn
		EkiOnOff,
	pmopm8AlmChannel52BalancedPortn
		EkiOnOff,
	pmopm8AlmChannel52MismatchPortn
		EkiOnOff,
	pmopm8AlmChannel52AbsentPortn
		EkiOnOff
	}


pmopm8Almchannel52PortIndex OBJECT-TYPE
	SYNTAX  INTEGER(0..128)
	MAX-ACCESS  read-only
	STATUS current
	DESCRIPTION
        "
        Index definition for the pmopm8Almchannel52Port
        table
        "
	::= { pmopm8Almchannel52PortEntry 1 }


pmopm8AlmChannel52OosPortn OBJECT-TYPE
	SYNTAX  EkiOnOff
	MAX-ACCESS read-only
	STATUS current
	DESCRIPTION
        "
        Channel Out Of Service 52 :This
        OID indicates that the channel
         is out of service  <Help> This
        alarm indicates that the channel
        is in service <Condtype> CHANNEL52_OOS_1
        <Probcause> informationalStatus(1000)
        <Alarmtype> other (1) <Polarity>
        (2)
        "
	::= { pmopm8Almchannel52PortEntry 7 }


pmopm8AlmChannel52PowerHighPortn OBJECT-TYPE
	SYNTAX  EkiOnOff
	MAX-ACCESS read-only
	STATUS current
	DESCRIPTION
        "
        Channel Power High 52 :This OID
        indicates that the power of the
        channel is higher than the configured
        threshold<Help> This alarm indicates
        that the power of the channel is
        higher than the configured threshold
        <Condtype> CHANNEL52_POWER_HIGH_1
        <Probcause> degradedSignal (13)
        <Alarmtype> equipmentAlarm <Polarity>
        (2)
        "
	::= { pmopm8Almchannel52PortEntry 6 }


pmopm8AlmChannel52PowerLowPortn OBJECT-TYPE
	SYNTAX  EkiOnOff
	MAX-ACCESS read-only
	STATUS current
	DESCRIPTION
        "
        Channel Power Low 52 :This OID
        indicates that the power of the
        channel is lower than the configured
        threshold<Help> This alarm indicates
        that the power of the channel is
        lower than the configured threshold
        <Condtype> CHANNEL52_POWER_LOW_1
        <Probcause> degradedSignal (13)
        <Alarmtype> equipmentAlarm <Polarity>
        (2)
        "
	::= { pmopm8Almchannel52PortEntry 5 }


pmopm8AlmChannel52BalancedPortn OBJECT-TYPE
	SYNTAX  EkiOnOff
	MAX-ACCESS read-only
	STATUS current
	DESCRIPTION
        "
        Channel Balanced 52 :This OID
         indicates that an in service channel
        is balanced by the Ekinops auto
        turn up application<Help> This
         status indicates that an in service
        channel is balanced by the Ekinops
        auto turn up application <Condtype>
        CHANNEL52_BALANCED_1 <Probcause>
        informationalStatus(1000) <Alarmtype>
        other (1) <Polarity> (2)
        "
	::= { pmopm8Almchannel52PortEntry 4 }


pmopm8AlmChannel52MismatchPortn OBJECT-TYPE
	SYNTAX  EkiOnOff
	MAX-ACCESS read-only
	STATUS current
	DESCRIPTION
        "
        Channel Mismatch 52 :This OID
         indicates that an out of service
        channel is detected on the Optical
        Power Monitoring input<Help> This
        alarm indicates that an out of
         service channel is detected on
        the Optical Power Monitoring input
        <Condtype> CHANNEL52_MISMATCH_1
        <Probcause> unexpectedInformation
        (75) <Alarmtype> equipmentAlarm
        <Polarity> (2)
        "
	::= { pmopm8Almchannel52PortEntry 3 }


pmopm8AlmChannel52AbsentPortn OBJECT-TYPE
	SYNTAX  EkiOnOff
	MAX-ACCESS read-only
	STATUS current
	DESCRIPTION
        "
        Channel Absent 52 :This OID indicates
        that an in service channel is absent
        on the Optical Power Monitoring
        input<Help> This alarm indicates
        that an in service channel is absent
        on the Optical Power Monitoring
        input <Condtype> CHANNEL52_ABSENT_1
        <Probcause> informationMissing
         (65) <Alarmtype> equipmentAlarm
        (5) <Polarity> (2)
        "
	::= { pmopm8Almchannel52PortEntry 2 }


--- *********************************************************
---     TABLE for the pmopm8Almchannel53Port articles
--- *********************************************************

pmopm8Almchannel53PortTable OBJECT-TYPE
	SYNTAX  SEQUENCE OF Pmopm8Almchannel53PortEntry
	MAX-ACCESS not-accessible
	STATUS current
	DESCRIPTION
        "
        List of pmopm8Almchannel53Port
        Article
        "
	::= { pmopm8AlmClientCrit 432 }


pmopm8Almchannel53PortEntry OBJECT-TYPE
	SYNTAX Pmopm8Almchannel53PortEntry
	MAX-ACCESS not-accessible
	STATUS current
	DESCRIPTION
        "
        Row definition for the pmopm8Almchannel53Port
        table
        "
	INDEX   { pmopm8Almchannel53PortIndex }
	::= { pmopm8Almchannel53PortTable 1 }


Pmopm8Almchannel53PortEntry ::=
	SEQUENCE {
	pmopm8Almchannel53PortIndex
		INTEGER,
	pmopm8AlmChannel53OosPortn
		EkiOnOff,
	pmopm8AlmChannel53PowerHighPortn
		EkiOnOff,
	pmopm8AlmChannel53PowerLowPortn
		EkiOnOff,
	pmopm8AlmChannel53BalancedPortn
		EkiOnOff,
	pmopm8AlmChannel53MismatchPortn
		EkiOnOff,
	pmopm8AlmChannel53AbsentPortn
		EkiOnOff
	}


pmopm8Almchannel53PortIndex OBJECT-TYPE
	SYNTAX  INTEGER(0..128)
	MAX-ACCESS  read-only
	STATUS current
	DESCRIPTION
        "
        Index definition for the pmopm8Almchannel53Port
        table
        "
	::= { pmopm8Almchannel53PortEntry 1 }


pmopm8AlmChannel53OosPortn OBJECT-TYPE
	SYNTAX  EkiOnOff
	MAX-ACCESS read-only
	STATUS current
	DESCRIPTION
        "
        Channel Out Of Service 53 :This
        OID indicates that the channel
         is out of service  <Help> This
        alarm indicates that the channel
        is in service <Condtype> CHANNEL53_OOS_1
        <Probcause> informationalStatus(1000)
        <Alarmtype> other (1) <Polarity>
        (2)
        "
	::= { pmopm8Almchannel53PortEntry 7 }


pmopm8AlmChannel53PowerHighPortn OBJECT-TYPE
	SYNTAX  EkiOnOff
	MAX-ACCESS read-only
	STATUS current
	DESCRIPTION
        "
        Channel Power High 53 :This OID
        indicates that the power of the
        channel is higher than the configured
        threshold<Help> This alarm indicates
        that the power of the channel is
        higher than the configured threshold
        <Condtype> CHANNEL53_POWER_HIGH_1
        <Probcause> degradedSignal (13)
        <Alarmtype> equipmentAlarm <Polarity>
        (2)
        "
	::= { pmopm8Almchannel53PortEntry 6 }


pmopm8AlmChannel53PowerLowPortn OBJECT-TYPE
	SYNTAX  EkiOnOff
	MAX-ACCESS read-only
	STATUS current
	DESCRIPTION
        "
        Channel Power Low 53 :This OID
        indicates that the power of the
        channel is lower than the configured
        threshold<Help> This alarm indicates
        that the power of the channel is
        lower than the configured threshold
        <Condtype> CHANNEL53_POWER_LOW_1
        <Probcause> degradedSignal (13)
        <Alarmtype> equipmentAlarm <Polarity>
        (2)
        "
	::= { pmopm8Almchannel53PortEntry 5 }


pmopm8AlmChannel53BalancedPortn OBJECT-TYPE
	SYNTAX  EkiOnOff
	MAX-ACCESS read-only
	STATUS current
	DESCRIPTION
        "
        Channel Balanced 53 :This OID
         indicates that an in service channel
        is balanced by the Ekinops auto
        turn up application<Help> This
         status indicates that an in service
        channel is balanced by the Ekinops
        auto turn up application <Condtype>
        CHANNEL53_BALANCED_1 <Probcause>
        informationalStatus(1000) <Alarmtype>
        other (1) <Polarity> (2)
        "
	::= { pmopm8Almchannel53PortEntry 4 }


pmopm8AlmChannel53MismatchPortn OBJECT-TYPE
	SYNTAX  EkiOnOff
	MAX-ACCESS read-only
	STATUS current
	DESCRIPTION
        "
        Channel Mismatch 53 :This OID
         indicates that an out of service
        channel is detected on the Optical
        Power Monitoring input<Help> This
        alarm indicates that an out of
         service channel is detected on
        the Optical Power Monitoring input
        <Condtype> CHANNEL53_MISMATCH_1
        <Probcause> unexpectedInformation
        (75) <Alarmtype> equipmentAlarm
        <Polarity> (2)
        "
	::= { pmopm8Almchannel53PortEntry 3 }


pmopm8AlmChannel53AbsentPortn OBJECT-TYPE
	SYNTAX  EkiOnOff
	MAX-ACCESS read-only
	STATUS current
	DESCRIPTION
        "
        Channel Absent 53 :This OID indicates
        that an in service channel is absent
        on the Optical Power Monitoring
        input<Help> This alarm indicates
        that an in service channel is absent
        on the Optical Power Monitoring
        input <Condtype> CHANNEL53_ABSENT_1
        <Probcause> informationMissing
         (65) <Alarmtype> equipmentAlarm
        (5) <Polarity> (2)
        "
	::= { pmopm8Almchannel53PortEntry 2 }


--- *********************************************************
---     TABLE for the pmopm8Almchannel54Port articles
--- *********************************************************

pmopm8Almchannel54PortTable OBJECT-TYPE
	SYNTAX  SEQUENCE OF Pmopm8Almchannel54PortEntry
	MAX-ACCESS not-accessible
	STATUS current
	DESCRIPTION
        "
        List of pmopm8Almchannel54Port
        Article
        "
	::= { pmopm8AlmClientCrit 440 }


pmopm8Almchannel54PortEntry OBJECT-TYPE
	SYNTAX Pmopm8Almchannel54PortEntry
	MAX-ACCESS not-accessible
	STATUS current
	DESCRIPTION
        "
        Row definition for the pmopm8Almchannel54Port
        table
        "
	INDEX   { pmopm8Almchannel54PortIndex }
	::= { pmopm8Almchannel54PortTable 1 }


Pmopm8Almchannel54PortEntry ::=
	SEQUENCE {
	pmopm8Almchannel54PortIndex
		INTEGER,
	pmopm8AlmChannel54OosPortn
		EkiOnOff,
	pmopm8AlmChannel54PowerHighPortn
		EkiOnOff,
	pmopm8AlmChannel54PowerLowPortn
		EkiOnOff,
	pmopm8AlmChannel54BalancedPortn
		EkiOnOff,
	pmopm8AlmChannel54MismatchPortn
		EkiOnOff,
	pmopm8AlmChannel54AbsentPortn
		EkiOnOff
	}


pmopm8Almchannel54PortIndex OBJECT-TYPE
	SYNTAX  INTEGER(0..128)
	MAX-ACCESS  read-only
	STATUS current
	DESCRIPTION
        "
        Index definition for the pmopm8Almchannel54Port
        table
        "
	::= { pmopm8Almchannel54PortEntry 1 }


pmopm8AlmChannel54OosPortn OBJECT-TYPE
	SYNTAX  EkiOnOff
	MAX-ACCESS read-only
	STATUS current
	DESCRIPTION
        "
        Channel Out Of Service 54 :This
        OID indicates that the channel
         is out of service  <Help> This
        alarm indicates that the channel
        is in service <Condtype> CHANNEL54_OOS_1
        <Probcause> informationalStatus(1000)
        <Alarmtype> other (1) <Polarity>
        (2)
        "
	::= { pmopm8Almchannel54PortEntry 7 }


pmopm8AlmChannel54PowerHighPortn OBJECT-TYPE
	SYNTAX  EkiOnOff
	MAX-ACCESS read-only
	STATUS current
	DESCRIPTION
        "
        Channel Power High 54 :This OID
        indicates that the power of the
        channel is higher than the configured
        threshold<Help> This alarm indicates
        that the power of the channel is
        higher than the configured threshold
        <Condtype> CHANNEL54_POWER_HIGH_1
        <Probcause> degradedSignal (13)
        <Alarmtype> equipmentAlarm <Polarity>
        (2)
        "
	::= { pmopm8Almchannel54PortEntry 6 }


pmopm8AlmChannel54PowerLowPortn OBJECT-TYPE
	SYNTAX  EkiOnOff
	MAX-ACCESS read-only
	STATUS current
	DESCRIPTION
        "
        Channel Power Low 54 :This OID
        indicates that the power of the
        channel is lower than the configured
        threshold<Help> This alarm indicates
        that the power of the channel is
        lower than the configured threshold
        <Condtype> CHANNEL54_POWER_LOW_1
        <Probcause> degradedSignal (13)
        <Alarmtype> equipmentAlarm <Polarity>
        (2)
        "
	::= { pmopm8Almchannel54PortEntry 5 }


pmopm8AlmChannel54BalancedPortn OBJECT-TYPE
	SYNTAX  EkiOnOff
	MAX-ACCESS read-only
	STATUS current
	DESCRIPTION
        "
        Channel Balanced 54 :This OID
         indicates that an in service channel
        is balanced by the Ekinops auto
        turn up application<Help> This
         status indicates that an in service
        channel is balanced by the Ekinops
        auto turn up application <Condtype>
        CHANNEL54_BALANCED_1 <Probcause>
        informationalStatus(1000) <Alarmtype>
        other (1) <Polarity> (2)
        "
	::= { pmopm8Almchannel54PortEntry 4 }


pmopm8AlmChannel54MismatchPortn OBJECT-TYPE
	SYNTAX  EkiOnOff
	MAX-ACCESS read-only
	STATUS current
	DESCRIPTION
        "
        Channel Mismatch 54 :This OID
         indicates that an out of service
        channel is detected on the Optical
        Power Monitoring input<Help> This
        alarm indicates that an out of
         service channel is detected on
        the Optical Power Monitoring input
        <Condtype> CHANNEL54_MISMATCH_1
        <Probcause> unexpectedInformation
        (75) <Alarmtype> equipmentAlarm
        <Polarity> (2)
        "
	::= { pmopm8Almchannel54PortEntry 3 }


pmopm8AlmChannel54AbsentPortn OBJECT-TYPE
	SYNTAX  EkiOnOff
	MAX-ACCESS read-only
	STATUS current
	DESCRIPTION
        "
        Channel Absent 54 :This OID indicates
        that an in service channel is absent
        on the Optical Power Monitoring
        input<Help> This alarm indicates
        that an in service channel is absent
        on the Optical Power Monitoring
        input <Condtype> CHANNEL54_ABSENT_1
        <Probcause> informationMissing
         (65) <Alarmtype> equipmentAlarm
        (5) <Polarity> (2)
        "
	::= { pmopm8Almchannel54PortEntry 2 }


--- *********************************************************
---     TABLE for the pmopm8Almchannel55Port articles
--- *********************************************************

pmopm8Almchannel55PortTable OBJECT-TYPE
	SYNTAX  SEQUENCE OF Pmopm8Almchannel55PortEntry
	MAX-ACCESS not-accessible
	STATUS current
	DESCRIPTION
        "
        List of pmopm8Almchannel55Port
        Article
        "
	::= { pmopm8AlmClientCrit 448 }


pmopm8Almchannel55PortEntry OBJECT-TYPE
	SYNTAX Pmopm8Almchannel55PortEntry
	MAX-ACCESS not-accessible
	STATUS current
	DESCRIPTION
        "
        Row definition for the pmopm8Almchannel55Port
        table
        "
	INDEX   { pmopm8Almchannel55PortIndex }
	::= { pmopm8Almchannel55PortTable 1 }


Pmopm8Almchannel55PortEntry ::=
	SEQUENCE {
	pmopm8Almchannel55PortIndex
		INTEGER,
	pmopm8AlmChannel55OosPortn
		EkiOnOff,
	pmopm8AlmChannel55PowerHighPortn
		EkiOnOff,
	pmopm8AlmChannel55PowerLowPortn
		EkiOnOff,
	pmopm8AlmChannel55BalancedPortn
		EkiOnOff,
	pmopm8AlmChannel55MismatchPortn
		EkiOnOff,
	pmopm8AlmChannel55AbsentPortn
		EkiOnOff
	}


pmopm8Almchannel55PortIndex OBJECT-TYPE
	SYNTAX  INTEGER(0..128)
	MAX-ACCESS  read-only
	STATUS current
	DESCRIPTION
        "
        Index definition for the pmopm8Almchannel55Port
        table
        "
	::= { pmopm8Almchannel55PortEntry 1 }


pmopm8AlmChannel55OosPortn OBJECT-TYPE
	SYNTAX  EkiOnOff
	MAX-ACCESS read-only
	STATUS current
	DESCRIPTION
        "
        Channel Out Of Service 55 :This
        OID indicates that the channel
         is out of service  <Help> This
        alarm indicates that the channel
        is in service <Condtype> CHANNEL55_OOS_1
        <Probcause> informationalStatus(1000)
        <Alarmtype> other (1) <Polarity>
        (2)
        "
	::= { pmopm8Almchannel55PortEntry 7 }


pmopm8AlmChannel55PowerHighPortn OBJECT-TYPE
	SYNTAX  EkiOnOff
	MAX-ACCESS read-only
	STATUS current
	DESCRIPTION
        "
        Channel Power High 55 :This OID
        indicates that the power of the
        channel is higher than the configured
        threshold<Help> This alarm indicates
        that the power of the channel is
        higher than the configured threshold
        <Condtype> CHANNEL55_POWER_HIGH_1
        <Probcause> degradedSignal (13)
        <Alarmtype> equipmentAlarm <Polarity>
        (2)
        "
	::= { pmopm8Almchannel55PortEntry 6 }


pmopm8AlmChannel55PowerLowPortn OBJECT-TYPE
	SYNTAX  EkiOnOff
	MAX-ACCESS read-only
	STATUS current
	DESCRIPTION
        "
        Channel Power Low 55 :This OID
        indicates that the power of the
        channel is lower than the configured
        threshold<Help> This alarm indicates
        that the power of the channel is
        lower than the configured threshold
        <Condtype> CHANNEL55_POWER_LOW_1
        <Probcause> degradedSignal (13)
        <Alarmtype> equipmentAlarm <Polarity>
        (2)
        "
	::= { pmopm8Almchannel55PortEntry 5 }


pmopm8AlmChannel55BalancedPortn OBJECT-TYPE
	SYNTAX  EkiOnOff
	MAX-ACCESS read-only
	STATUS current
	DESCRIPTION
        "
        Channel Balanced 55 :This OID
         indicates that an in service channel
        is balanced by the Ekinops auto
        turn up application<Help> This
         status indicates that an in service
        channel is balanced by the Ekinops
        auto turn up application <Condtype>
        CHANNEL55_BALANCED_1 <Probcause>
        informationalStatus(1000) <Alarmtype>
        other (1) <Polarity> (2)
        "
	::= { pmopm8Almchannel55PortEntry 4 }


pmopm8AlmChannel55MismatchPortn OBJECT-TYPE
	SYNTAX  EkiOnOff
	MAX-ACCESS read-only
	STATUS current
	DESCRIPTION
        "
        Channel Mismatch 55 :This OID
         indicates that an out of service
        channel is detected on the Optical
        Power Monitoring input<Help> This
        alarm indicates that an out of
         service channel is detected on
        the Optical Power Monitoring input
        <Condtype> CHANNEL55_MISMATCH_1
        <Probcause> unexpectedInformation
        (75) <Alarmtype> equipmentAlarm
        <Polarity> (2)
        "
	::= { pmopm8Almchannel55PortEntry 3 }


pmopm8AlmChannel55AbsentPortn OBJECT-TYPE
	SYNTAX  EkiOnOff
	MAX-ACCESS read-only
	STATUS current
	DESCRIPTION
        "
        Channel Absent 55 :This OID indicates
        that an in service channel is absent
        on the Optical Power Monitoring
        input<Help> This alarm indicates
        that an in service channel is absent
        on the Optical Power Monitoring
        input <Condtype> CHANNEL55_ABSENT_1
        <Probcause> informationMissing
         (65) <Alarmtype> equipmentAlarm
        (5) <Polarity> (2)
        "
	::= { pmopm8Almchannel55PortEntry 2 }


--- *********************************************************
---     TABLE for the pmopm8Almchannel56Port articles
--- *********************************************************

pmopm8Almchannel56PortTable OBJECT-TYPE
	SYNTAX  SEQUENCE OF Pmopm8Almchannel56PortEntry
	MAX-ACCESS not-accessible
	STATUS current
	DESCRIPTION
        "
        List of pmopm8Almchannel56Port
        Article
        "
	::= { pmopm8AlmClientCrit 456 }


pmopm8Almchannel56PortEntry OBJECT-TYPE
	SYNTAX Pmopm8Almchannel56PortEntry
	MAX-ACCESS not-accessible
	STATUS current
	DESCRIPTION
        "
        Row definition for the pmopm8Almchannel56Port
        table
        "
	INDEX   { pmopm8Almchannel56PortIndex }
	::= { pmopm8Almchannel56PortTable 1 }


Pmopm8Almchannel56PortEntry ::=
	SEQUENCE {
	pmopm8Almchannel56PortIndex
		INTEGER,
	pmopm8AlmChannel56OosPortn
		EkiOnOff,
	pmopm8AlmChannel56PowerHighPortn
		EkiOnOff,
	pmopm8AlmChannel56PowerLowPortn
		EkiOnOff,
	pmopm8AlmChannel56BalancedPortn
		EkiOnOff,
	pmopm8AlmChannel56MismatchPortn
		EkiOnOff,
	pmopm8AlmChannel56AbsentPortn
		EkiOnOff
	}


pmopm8Almchannel56PortIndex OBJECT-TYPE
	SYNTAX  INTEGER(0..128)
	MAX-ACCESS  read-only
	STATUS current
	DESCRIPTION
        "
        Index definition for the pmopm8Almchannel56Port
        table
        "
	::= { pmopm8Almchannel56PortEntry 1 }


pmopm8AlmChannel56OosPortn OBJECT-TYPE
	SYNTAX  EkiOnOff
	MAX-ACCESS read-only
	STATUS current
	DESCRIPTION
        "
        Channel Out Of Service 56 :This
        OID indicates that the channel
         is out of service  <Help> This
        alarm indicates that the channel
        is in service <Condtype> CHANNEL56_OOS_1
        <Probcause> informationalStatus(1000)
        <Alarmtype> other (1) <Polarity>
        (2)
        "
	::= { pmopm8Almchannel56PortEntry 7 }


pmopm8AlmChannel56PowerHighPortn OBJECT-TYPE
	SYNTAX  EkiOnOff
	MAX-ACCESS read-only
	STATUS current
	DESCRIPTION
        "
        Channel Power High 56 :This OID
        indicates that the power of the
        channel is higher than the configured
        threshold<Help> This alarm indicates
        that the power of the channel is
        higher than the configured threshold
        <Condtype> CHANNEL56_POWER_HIGH_1
        <Probcause> degradedSignal (13)
        <Alarmtype> equipmentAlarm <Polarity>
        (2)
        "
	::= { pmopm8Almchannel56PortEntry 6 }


pmopm8AlmChannel56PowerLowPortn OBJECT-TYPE
	SYNTAX  EkiOnOff
	MAX-ACCESS read-only
	STATUS current
	DESCRIPTION
        "
        Channel Power Low 56 :This OID
        indicates that the power of the
        channel is lower than the configured
        threshold<Help> This alarm indicates
        that the power of the channel is
        lower than the configured threshold
        <Condtype> CHANNEL56_POWER_LOW_1
        <Probcause> degradedSignal (13)
        <Alarmtype> equipmentAlarm <Polarity>
        (2)
        "
	::= { pmopm8Almchannel56PortEntry 5 }


pmopm8AlmChannel56BalancedPortn OBJECT-TYPE
	SYNTAX  EkiOnOff
	MAX-ACCESS read-only
	STATUS current
	DESCRIPTION
        "
        Channel Balanced 56 :This OID
         indicates that an in service channel
        is balanced by the Ekinops auto
        turn up application<Help> This
         status indicates that an in service
        channel is balanced by the Ekinops
        auto turn up application <Condtype>
        CHANNEL56_BALANCED_1 <Probcause>
        informationalStatus(1000) <Alarmtype>
        other (1) <Polarity> (2)
        "
	::= { pmopm8Almchannel56PortEntry 4 }


pmopm8AlmChannel56MismatchPortn OBJECT-TYPE
	SYNTAX  EkiOnOff
	MAX-ACCESS read-only
	STATUS current
	DESCRIPTION
        "
        Channel Mismatch 56 :This OID
         indicates that an out of service
        channel is detected on the Optical
        Power Monitoring input<Help> This
        alarm indicates that an out of
         service channel is detected on
        the Optical Power Monitoring input
        <Condtype> CHANNEL56_MISMATCH_1
        <Probcause> unexpectedInformation
        (75) <Alarmtype> equipmentAlarm
        <Polarity> (2)
        "
	::= { pmopm8Almchannel56PortEntry 3 }


pmopm8AlmChannel56AbsentPortn OBJECT-TYPE
	SYNTAX  EkiOnOff
	MAX-ACCESS read-only
	STATUS current
	DESCRIPTION
        "
        Channel Absent 56 :This OID indicates
        that an in service channel is absent
        on the Optical Power Monitoring
        input<Help> This alarm indicates
        that an in service channel is absent
        on the Optical Power Monitoring
        input <Condtype> CHANNEL56_ABSENT_1
        <Probcause> informationMissing
         (65) <Alarmtype> equipmentAlarm
        (5) <Polarity> (2)
        "
	::= { pmopm8Almchannel56PortEntry 2 }


--- *********************************************************
---     TABLE for the pmopm8Almchannel57Port articles
--- *********************************************************

pmopm8Almchannel57PortTable OBJECT-TYPE
	SYNTAX  SEQUENCE OF Pmopm8Almchannel57PortEntry
	MAX-ACCESS not-accessible
	STATUS current
	DESCRIPTION
        "
        List of pmopm8Almchannel57Port
        Article
        "
	::= { pmopm8AlmClientCrit 464 }


pmopm8Almchannel57PortEntry OBJECT-TYPE
	SYNTAX Pmopm8Almchannel57PortEntry
	MAX-ACCESS not-accessible
	STATUS current
	DESCRIPTION
        "
        Row definition for the pmopm8Almchannel57Port
        table
        "
	INDEX   { pmopm8Almchannel57PortIndex }
	::= { pmopm8Almchannel57PortTable 1 }


Pmopm8Almchannel57PortEntry ::=
	SEQUENCE {
	pmopm8Almchannel57PortIndex
		INTEGER,
	pmopm8AlmChannel57OosPortn
		EkiOnOff,
	pmopm8AlmChannel57PowerHighPortn
		EkiOnOff,
	pmopm8AlmChannel57PowerLowPortn
		EkiOnOff,
	pmopm8AlmChannel57BalancedPortn
		EkiOnOff,
	pmopm8AlmChannel57MismatchPortn
		EkiOnOff,
	pmopm8AlmChannel57AbsentPortn
		EkiOnOff
	}


pmopm8Almchannel57PortIndex OBJECT-TYPE
	SYNTAX  INTEGER(0..128)
	MAX-ACCESS  read-only
	STATUS current
	DESCRIPTION
        "
        Index definition for the pmopm8Almchannel57Port
        table
        "
	::= { pmopm8Almchannel57PortEntry 1 }


pmopm8AlmChannel57OosPortn OBJECT-TYPE
	SYNTAX  EkiOnOff
	MAX-ACCESS read-only
	STATUS current
	DESCRIPTION
        "
        Channel Out Of Service 57 :This
        OID indicates that the channel
         is out of service  <Help> This
        alarm indicates that the channel
        is in service <Condtype> CHANNEL57_OOS_1
        <Probcause> informationalStatus(1000)
        <Alarmtype> other (1) <Polarity>
        (2)
        "
	::= { pmopm8Almchannel57PortEntry 7 }


pmopm8AlmChannel57PowerHighPortn OBJECT-TYPE
	SYNTAX  EkiOnOff
	MAX-ACCESS read-only
	STATUS current
	DESCRIPTION
        "
        Channel Power High 57 :This OID
        indicates that the power of the
        channel is higher than the configured
        threshold<Help> This alarm indicates
        that the power of the channel is
        higher than the configured threshold
        <Condtype> CHANNEL57_POWER_HIGH_1
        <Probcause> degradedSignal (13)
        <Alarmtype> equipmentAlarm <Polarity>
        (2)
        "
	::= { pmopm8Almchannel57PortEntry 6 }


pmopm8AlmChannel57PowerLowPortn OBJECT-TYPE
	SYNTAX  EkiOnOff
	MAX-ACCESS read-only
	STATUS current
	DESCRIPTION
        "
        Channel Power Low 57 :This OID
        indicates that the power of the
        channel is lower than the configured
        threshold<Help> This alarm indicates
        that the power of the channel is
        lower than the configured threshold
        <Condtype> CHANNEL57_POWER_LOW_1
        <Probcause> degradedSignal (13)
        <Alarmtype> equipmentAlarm <Polarity>
        (2)
        "
	::= { pmopm8Almchannel57PortEntry 5 }


pmopm8AlmChannel57BalancedPortn OBJECT-TYPE
	SYNTAX  EkiOnOff
	MAX-ACCESS read-only
	STATUS current
	DESCRIPTION
        "
        Channel Balanced 57 :This OID
         indicates that an in service channel
        is balanced by the Ekinops auto
        turn up application<Help> This
         status indicates that an in service
        channel is balanced by the Ekinops
        auto turn up application <Condtype>
        CHANNEL57_BALANCED_1 <Probcause>
        informationalStatus(1000) <Alarmtype>
        other (1) <Polarity> (2)
        "
	::= { pmopm8Almchannel57PortEntry 4 }


pmopm8AlmChannel57MismatchPortn OBJECT-TYPE
	SYNTAX  EkiOnOff
	MAX-ACCESS read-only
	STATUS current
	DESCRIPTION
        "
        Channel Mismatch 57 :This OID
         indicates that an out of service
        channel is detected on the Optical
        Power Monitoring input<Help> This
        alarm indicates that an out of
         service channel is detected on
        the Optical Power Monitoring input
        <Condtype> CHANNEL57_MISMATCH_1
        <Probcause> unexpectedInformation
        (75) <Alarmtype> equipmentAlarm
        <Polarity> (2)
        "
	::= { pmopm8Almchannel57PortEntry 3 }


pmopm8AlmChannel57AbsentPortn OBJECT-TYPE
	SYNTAX  EkiOnOff
	MAX-ACCESS read-only
	STATUS current
	DESCRIPTION
        "
        Channel Absent 57 :This OID indicates
        that an in service channel is absent
        on the Optical Power Monitoring
        input<Help> This alarm indicates
        that an in service channel is absent
        on the Optical Power Monitoring
        input <Condtype> CHANNEL57_ABSENT_1
        <Probcause> informationMissing
         (65) <Alarmtype> equipmentAlarm
        (5) <Polarity> (2)
        "
	::= { pmopm8Almchannel57PortEntry 2 }


--- *********************************************************
---     TABLE for the pmopm8Almchannel58Port articles
--- *********************************************************

pmopm8Almchannel58PortTable OBJECT-TYPE
	SYNTAX  SEQUENCE OF Pmopm8Almchannel58PortEntry
	MAX-ACCESS not-accessible
	STATUS current
	DESCRIPTION
        "
        List of pmopm8Almchannel58Port
        Article
        "
	::= { pmopm8AlmClientCrit 472 }


pmopm8Almchannel58PortEntry OBJECT-TYPE
	SYNTAX Pmopm8Almchannel58PortEntry
	MAX-ACCESS not-accessible
	STATUS current
	DESCRIPTION
        "
        Row definition for the pmopm8Almchannel58Port
        table
        "
	INDEX   { pmopm8Almchannel58PortIndex }
	::= { pmopm8Almchannel58PortTable 1 }


Pmopm8Almchannel58PortEntry ::=
	SEQUENCE {
	pmopm8Almchannel58PortIndex
		INTEGER,
	pmopm8AlmChannel58OosPortn
		EkiOnOff,
	pmopm8AlmChannel58PowerHighPortn
		EkiOnOff,
	pmopm8AlmChannel58PowerLowPortn
		EkiOnOff,
	pmopm8AlmChannel58BalancedPortn
		EkiOnOff,
	pmopm8AlmChannel58MismatchPortn
		EkiOnOff,
	pmopm8AlmChannel58AbsentPortn
		EkiOnOff
	}


pmopm8Almchannel58PortIndex OBJECT-TYPE
	SYNTAX  INTEGER(0..128)
	MAX-ACCESS  read-only
	STATUS current
	DESCRIPTION
        "
        Index definition for the pmopm8Almchannel58Port
        table
        "
	::= { pmopm8Almchannel58PortEntry 1 }


pmopm8AlmChannel58OosPortn OBJECT-TYPE
	SYNTAX  EkiOnOff
	MAX-ACCESS read-only
	STATUS current
	DESCRIPTION
        "
        Channel Out Of Service 58 :This
        OID indicates that the channel
         is out of service  <Help> This
        alarm indicates that the channel
        is in service <Condtype> CHANNEL58_OOS_1
        <Probcause> informationalStatus(1000)
        <Alarmtype> other (1) <Polarity>
        (2)
        "
	::= { pmopm8Almchannel58PortEntry 7 }


pmopm8AlmChannel58PowerHighPortn OBJECT-TYPE
	SYNTAX  EkiOnOff
	MAX-ACCESS read-only
	STATUS current
	DESCRIPTION
        "
        Channel Power High 58 :This OID
        indicates that the power of the
        channel is higher than the configured
        threshold<Help> This alarm indicates
        that the power of the channel is
        higher than the configured threshold
        <Condtype> CHANNEL58_POWER_HIGH_1
        <Probcause> degradedSignal (13)
        <Alarmtype> equipmentAlarm <Polarity>
        (2)
        "
	::= { pmopm8Almchannel58PortEntry 6 }


pmopm8AlmChannel58PowerLowPortn OBJECT-TYPE
	SYNTAX  EkiOnOff
	MAX-ACCESS read-only
	STATUS current
	DESCRIPTION
        "
        Channel Power Low 58 :This OID
        indicates that the power of the
        channel is lower than the configured
        threshold<Help> This alarm indicates
        that the power of the channel is
        lower than the configured threshold
        <Condtype> CHANNEL58_POWER_LOW_1
        <Probcause> degradedSignal (13)
        <Alarmtype> equipmentAlarm <Polarity>
        (2)
        "
	::= { pmopm8Almchannel58PortEntry 5 }


pmopm8AlmChannel58BalancedPortn OBJECT-TYPE
	SYNTAX  EkiOnOff
	MAX-ACCESS read-only
	STATUS current
	DESCRIPTION
        "
        Channel Balanced 58 :This OID
         indicates that an in service channel
        is balanced by the Ekinops auto
        turn up application<Help> This
         status indicates that an in service
        channel is balanced by the Ekinops
        auto turn up application <Condtype>
        CHANNEL58_BALANCED_1 <Probcause>
        informationalStatus(1000) <Alarmtype>
        other (1) <Polarity> (2)
        "
	::= { pmopm8Almchannel58PortEntry 4 }


pmopm8AlmChannel58MismatchPortn OBJECT-TYPE
	SYNTAX  EkiOnOff
	MAX-ACCESS read-only
	STATUS current
	DESCRIPTION
        "
        Channel Mismatch 58 :This OID
         indicates that an out of service
        channel is detected on the Optical
        Power Monitoring input<Help> This
        alarm indicates that an out of
         service channel is detected on
        the Optical Power Monitoring input
        <Condtype> CHANNEL58_MISMATCH_1
        <Probcause> unexpectedInformation
        (75) <Alarmtype> equipmentAlarm
        <Polarity> (2)
        "
	::= { pmopm8Almchannel58PortEntry 3 }


pmopm8AlmChannel58AbsentPortn OBJECT-TYPE
	SYNTAX  EkiOnOff
	MAX-ACCESS read-only
	STATUS current
	DESCRIPTION
        "
        Channel Absent 58 :This OID indicates
        that an in service channel is absent
        on the Optical Power Monitoring
        input<Help> This alarm indicates
        that an in service channel is absent
        on the Optical Power Monitoring
        input <Condtype> CHANNEL58_ABSENT_1
        <Probcause> informationMissing
         (65) <Alarmtype> equipmentAlarm
        (5) <Polarity> (2)
        "
	::= { pmopm8Almchannel58PortEntry 2 }


--- *********************************************************
---     TABLE for the pmopm8Almchannel59Port articles
--- *********************************************************

pmopm8Almchannel59PortTable OBJECT-TYPE
	SYNTAX  SEQUENCE OF Pmopm8Almchannel59PortEntry
	MAX-ACCESS not-accessible
	STATUS current
	DESCRIPTION
        "
        List of pmopm8Almchannel59Port
        Article
        "
	::= { pmopm8AlmClientCrit 480 }


pmopm8Almchannel59PortEntry OBJECT-TYPE
	SYNTAX Pmopm8Almchannel59PortEntry
	MAX-ACCESS not-accessible
	STATUS current
	DESCRIPTION
        "
        Row definition for the pmopm8Almchannel59Port
        table
        "
	INDEX   { pmopm8Almchannel59PortIndex }
	::= { pmopm8Almchannel59PortTable 1 }


Pmopm8Almchannel59PortEntry ::=
	SEQUENCE {
	pmopm8Almchannel59PortIndex
		INTEGER,
	pmopm8AlmChannel59OosPortn
		EkiOnOff,
	pmopm8AlmChannel59PowerHighPortn
		EkiOnOff,
	pmopm8AlmChannel59PowerLowPortn
		EkiOnOff,
	pmopm8AlmChannel59BalancedPortn
		EkiOnOff,
	pmopm8AlmChannel59MismatchPortn
		EkiOnOff,
	pmopm8AlmChannel59AbsentPortn
		EkiOnOff
	}


pmopm8Almchannel59PortIndex OBJECT-TYPE
	SYNTAX  INTEGER(0..128)
	MAX-ACCESS  read-only
	STATUS current
	DESCRIPTION
        "
        Index definition for the pmopm8Almchannel59Port
        table
        "
	::= { pmopm8Almchannel59PortEntry 1 }


pmopm8AlmChannel59OosPortn OBJECT-TYPE
	SYNTAX  EkiOnOff
	MAX-ACCESS read-only
	STATUS current
	DESCRIPTION
        "
        Channel Out Of Service 59 :This
        OID indicates that the channel
         is out of service  <Help> This
        alarm indicates that the channel
        is in service <Condtype> CHANNEL59_OOS_1
        <Probcause> informationalStatus(1000)
        <Alarmtype> other (1) <Polarity>
        (2)
        "
	::= { pmopm8Almchannel59PortEntry 7 }


pmopm8AlmChannel59PowerHighPortn OBJECT-TYPE
	SYNTAX  EkiOnOff
	MAX-ACCESS read-only
	STATUS current
	DESCRIPTION
        "
        Channel Power High 59 :This OID
        indicates that the power of the
        channel is higher than the configured
        threshold<Help> This alarm indicates
        that the power of the channel is
        higher than the configured threshold
        <Condtype> CHANNEL59_POWER_HIGH_1
        <Probcause> degradedSignal (13)
        <Alarmtype> equipmentAlarm <Polarity>
        (2)
        "
	::= { pmopm8Almchannel59PortEntry 6 }


pmopm8AlmChannel59PowerLowPortn OBJECT-TYPE
	SYNTAX  EkiOnOff
	MAX-ACCESS read-only
	STATUS current
	DESCRIPTION
        "
        Channel Power Low 59 :This OID
        indicates that the power of the
        channel is lower than the configured
        threshold<Help> This alarm indicates
        that the power of the channel is
        lower than the configured threshold
        <Condtype> CHANNEL59_POWER_LOW_1
        <Probcause> degradedSignal (13)
        <Alarmtype> equipmentAlarm <Polarity>
        (2)
        "
	::= { pmopm8Almchannel59PortEntry 5 }


pmopm8AlmChannel59BalancedPortn OBJECT-TYPE
	SYNTAX  EkiOnOff
	MAX-ACCESS read-only
	STATUS current
	DESCRIPTION
        "
        Channel Balanced 59 :This OID
         indicates that an in service channel
        is balanced by the Ekinops auto
        turn up application<Help> This
         status indicates that an in service
        channel is balanced by the Ekinops
        auto turn up application <Condtype>
        CHANNEL59_BALANCED_1 <Probcause>
        informationalStatus(1000) <Alarmtype>
        other (1) <Polarity> (2)
        "
	::= { pmopm8Almchannel59PortEntry 4 }


pmopm8AlmChannel59MismatchPortn OBJECT-TYPE
	SYNTAX  EkiOnOff
	MAX-ACCESS read-only
	STATUS current
	DESCRIPTION
        "
        Channel Mismatch 59 :This OID
         indicates that an out of service
        channel is detected on the Optical
        Power Monitoring input<Help> This
        alarm indicates that an out of
         service channel is detected on
        the Optical Power Monitoring input
        <Condtype> CHANNEL59_MISMATCH_1
        <Probcause> unexpectedInformation
        (75) <Alarmtype> equipmentAlarm
        <Polarity> (2)
        "
	::= { pmopm8Almchannel59PortEntry 3 }


pmopm8AlmChannel59AbsentPortn OBJECT-TYPE
	SYNTAX  EkiOnOff
	MAX-ACCESS read-only
	STATUS current
	DESCRIPTION
        "
        Channel Absent 59 :This OID indicates
        that an in service channel is absent
        on the Optical Power Monitoring
        input<Help> This alarm indicates
        that an in service channel is absent
        on the Optical Power Monitoring
        input <Condtype> CHANNEL59_ABSENT_1
        <Probcause> informationMissing
         (65) <Alarmtype> equipmentAlarm
        (5) <Polarity> (2)
        "
	::= { pmopm8Almchannel59PortEntry 2 }


--- *********************************************************
---     TABLE for the pmopm8Almchannel60Port articles
--- *********************************************************

pmopm8Almchannel60PortTable OBJECT-TYPE
	SYNTAX  SEQUENCE OF Pmopm8Almchannel60PortEntry
	MAX-ACCESS not-accessible
	STATUS current
	DESCRIPTION
        "
        List of pmopm8Almchannel60Port
        Article
        "
	::= { pmopm8AlmClientCrit 488 }


pmopm8Almchannel60PortEntry OBJECT-TYPE
	SYNTAX Pmopm8Almchannel60PortEntry
	MAX-ACCESS not-accessible
	STATUS current
	DESCRIPTION
        "
        Row definition for the pmopm8Almchannel60Port
        table
        "
	INDEX   { pmopm8Almchannel60PortIndex }
	::= { pmopm8Almchannel60PortTable 1 }


Pmopm8Almchannel60PortEntry ::=
	SEQUENCE {
	pmopm8Almchannel60PortIndex
		INTEGER,
	pmopm8AlmChannel60OosPortn
		EkiOnOff,
	pmopm8AlmChannel60PowerHighPortn
		EkiOnOff,
	pmopm8AlmChannel60PowerLowPortn
		EkiOnOff,
	pmopm8AlmChannel60BalancedPortn
		EkiOnOff,
	pmopm8AlmChannel60MismatchPortn
		EkiOnOff,
	pmopm8AlmChannel60AbsentPortn
		EkiOnOff
	}


pmopm8Almchannel60PortIndex OBJECT-TYPE
	SYNTAX  INTEGER(0..128)
	MAX-ACCESS  read-only
	STATUS current
	DESCRIPTION
        "
        Index definition for the pmopm8Almchannel60Port
        table
        "
	::= { pmopm8Almchannel60PortEntry 1 }


pmopm8AlmChannel60OosPortn OBJECT-TYPE
	SYNTAX  EkiOnOff
	MAX-ACCESS read-only
	STATUS current
	DESCRIPTION
        "
        Channel Out Of Service 60 :This
        OID indicates that the channel
         is out of service  <Help> This
        alarm indicates that the channel
        is in service <Condtype> CHANNEL60_OOS_1
        <Probcause> informationalStatus(1000)
        <Alarmtype> other (1) <Polarity>
        (2)
        "
	::= { pmopm8Almchannel60PortEntry 7 }


pmopm8AlmChannel60PowerHighPortn OBJECT-TYPE
	SYNTAX  EkiOnOff
	MAX-ACCESS read-only
	STATUS current
	DESCRIPTION
        "
        Channel Power High 60 :This OID
        indicates that the power of the
        channel is higher than the configured
        threshold<Help> This alarm indicates
        that the power of the channel is
        higher than the configured threshold
        <Condtype> CHANNEL60_POWER_HIGH_1
        <Probcause> degradedSignal (13)
        <Alarmtype> equipmentAlarm <Polarity>
        (2)
        "
	::= { pmopm8Almchannel60PortEntry 6 }


pmopm8AlmChannel60PowerLowPortn OBJECT-TYPE
	SYNTAX  EkiOnOff
	MAX-ACCESS read-only
	STATUS current
	DESCRIPTION
        "
        Channel Power Low 60 :This OID
        indicates that the power of the
        channel is lower than the configured
        threshold<Help> This alarm indicates
        that the power of the channel is
        lower than the configured threshold
        <Condtype> CHANNEL60_POWER_LOW_1
        <Probcause> degradedSignal (13)
        <Alarmtype> equipmentAlarm <Polarity>
        (2)
        "
	::= { pmopm8Almchannel60PortEntry 5 }


pmopm8AlmChannel60BalancedPortn OBJECT-TYPE
	SYNTAX  EkiOnOff
	MAX-ACCESS read-only
	STATUS current
	DESCRIPTION
        "
        Channel Balanced 60 :This OID
         indicates that an in service channel
        is balanced by the Ekinops auto
        turn up application<Help> This
         status indicates that an in service
        channel is balanced by the Ekinops
        auto turn up application <Condtype>
        CHANNEL60_BALANCED_1 <Probcause>
        informationalStatus(1000) <Alarmtype>
        other (1) <Polarity> (2)
        "
	::= { pmopm8Almchannel60PortEntry 4 }


pmopm8AlmChannel60MismatchPortn OBJECT-TYPE
	SYNTAX  EkiOnOff
	MAX-ACCESS read-only
	STATUS current
	DESCRIPTION
        "
        Channel Mismatch 60 :This OID
         indicates that an out of service
        channel is detected on the Optical
        Power Monitoring input<Help> This
        alarm indicates that an out of
         service channel is detected on
        the Optical Power Monitoring input
        <Condtype> CHANNEL60_MISMATCH_1
        <Probcause> unexpectedInformation
        (75) <Alarmtype> equipmentAlarm
        <Polarity> (2)
        "
	::= { pmopm8Almchannel60PortEntry 3 }


pmopm8AlmChannel60AbsentPortn OBJECT-TYPE
	SYNTAX  EkiOnOff
	MAX-ACCESS read-only
	STATUS current
	DESCRIPTION
        "
        Channel Absent 60 :This OID indicates
        that an in service channel is absent
        on the Optical Power Monitoring
        input<Help> This alarm indicates
        that an in service channel is absent
        on the Optical Power Monitoring
        input <Condtype> CHANNEL60_ABSENT_1
        <Probcause> informationMissing
         (65) <Alarmtype> equipmentAlarm
        (5) <Polarity> (2)
        "
	::= { pmopm8Almchannel60PortEntry 2 }


--- *********************************************************
---     TABLE for the pmopm8Almchannel61Port articles
--- *********************************************************

pmopm8Almchannel61PortTable OBJECT-TYPE
	SYNTAX  SEQUENCE OF Pmopm8Almchannel61PortEntry
	MAX-ACCESS not-accessible
	STATUS current
	DESCRIPTION
        "
        List of pmopm8Almchannel61Port
        Article
        "
	::= { pmopm8AlmClientCrit 496 }


pmopm8Almchannel61PortEntry OBJECT-TYPE
	SYNTAX Pmopm8Almchannel61PortEntry
	MAX-ACCESS not-accessible
	STATUS current
	DESCRIPTION
        "
        Row definition for the pmopm8Almchannel61Port
        table
        "
	INDEX   { pmopm8Almchannel61PortIndex }
	::= { pmopm8Almchannel61PortTable 1 }


Pmopm8Almchannel61PortEntry ::=
	SEQUENCE {
	pmopm8Almchannel61PortIndex
		INTEGER,
	pmopm8AlmChannel61OosPortn
		EkiOnOff,
	pmopm8AlmChannel61PowerHighPortn
		EkiOnOff,
	pmopm8AlmChannel61PowerLowPortn
		EkiOnOff,
	pmopm8AlmChannel61BalancedPortn
		EkiOnOff,
	pmopm8AlmChannel61MismatchPortn
		EkiOnOff,
	pmopm8AlmChannel61AbsentPortn
		EkiOnOff
	}


pmopm8Almchannel61PortIndex OBJECT-TYPE
	SYNTAX  INTEGER(0..128)
	MAX-ACCESS  read-only
	STATUS current
	DESCRIPTION
        "
        Index definition for the pmopm8Almchannel61Port
        table
        "
	::= { pmopm8Almchannel61PortEntry 1 }


pmopm8AlmChannel61OosPortn OBJECT-TYPE
	SYNTAX  EkiOnOff
	MAX-ACCESS read-only
	STATUS current
	DESCRIPTION
        "
        Channel Out Of Service 61 :This
        OID indicates that the channel
         is out of service  <Help> This
        alarm indicates that the channel
        is in service <Condtype> CHANNEL61_OOS_1
        <Probcause> informationalStatus(1000)
        <Alarmtype> other (1) <Polarity>
        (2)
        "
	::= { pmopm8Almchannel61PortEntry 7 }


pmopm8AlmChannel61PowerHighPortn OBJECT-TYPE
	SYNTAX  EkiOnOff
	MAX-ACCESS read-only
	STATUS current
	DESCRIPTION
        "
        Channel Power High 61 :This OID
        indicates that the power of the
        channel is higher than the configured
        threshold<Help> This alarm indicates
        that the power of the channel is
        higher than the configured threshold
        <Condtype> CHANNEL61_POWER_HIGH_1
        <Probcause> degradedSignal (13)
        <Alarmtype> equipmentAlarm <Polarity>
        (2)
        "
	::= { pmopm8Almchannel61PortEntry 6 }


pmopm8AlmChannel61PowerLowPortn OBJECT-TYPE
	SYNTAX  EkiOnOff
	MAX-ACCESS read-only
	STATUS current
	DESCRIPTION
        "
        Channel Power Low 61 :This OID
        indicates that the power of the
        channel is lower than the configured
        threshold<Help> This alarm indicates
        that the power of the channel is
        lower than the configured threshold
        <Condtype> CHANNEL61_POWER_LOW_1
        <Probcause> degradedSignal (13)
        <Alarmtype> equipmentAlarm <Polarity>
        (2)
        "
	::= { pmopm8Almchannel61PortEntry 5 }


pmopm8AlmChannel61BalancedPortn OBJECT-TYPE
	SYNTAX  EkiOnOff
	MAX-ACCESS read-only
	STATUS current
	DESCRIPTION
        "
        Channel Balanced 61 :This OID
         indicates that an in service channel
        is balanced by the Ekinops auto
        turn up application<Help> This
         status indicates that an in service
        channel is balanced by the Ekinops
        auto turn up application <Condtype>
        CHANNEL61_BALANCED_1 <Probcause>
        informationalStatus(1000) <Alarmtype>
        other (1) <Polarity> (2)
        "
	::= { pmopm8Almchannel61PortEntry 4 }


pmopm8AlmChannel61MismatchPortn OBJECT-TYPE
	SYNTAX  EkiOnOff
	MAX-ACCESS read-only
	STATUS current
	DESCRIPTION
        "
        Channel Mismatch 61 :This OID
         indicates that an out of service
        channel is detected on the Optical
        Power Monitoring input<Help> This
        alarm indicates that an out of
         service channel is detected on
        the Optical Power Monitoring input
        <Condtype> CHANNEL61_MISMATCH_1
        <Probcause> unexpectedInformation
        (75) <Alarmtype> equipmentAlarm
        <Polarity> (2)
        "
	::= { pmopm8Almchannel61PortEntry 3 }


pmopm8AlmChannel61AbsentPortn OBJECT-TYPE
	SYNTAX  EkiOnOff
	MAX-ACCESS read-only
	STATUS current
	DESCRIPTION
        "
        Channel Absent 61 :This OID indicates
        that an in service channel is absent
        on the Optical Power Monitoring
        input<Help> This alarm indicates
        that an in service channel is absent
        on the Optical Power Monitoring
        input <Condtype> CHANNEL61_ABSENT_1
        <Probcause> informationMissing
         (65) <Alarmtype> equipmentAlarm
        (5) <Polarity> (2)
        "
	::= { pmopm8Almchannel61PortEntry 2 }


--- *********************************************************
---     TABLE for the pmopm8Almchannel62Port articles
--- *********************************************************

pmopm8Almchannel62PortTable OBJECT-TYPE
	SYNTAX  SEQUENCE OF Pmopm8Almchannel62PortEntry
	MAX-ACCESS not-accessible
	STATUS current
	DESCRIPTION
        "
        List of pmopm8Almchannel62Port
        Article
        "
	::= { pmopm8AlmClientCrit 504 }


pmopm8Almchannel62PortEntry OBJECT-TYPE
	SYNTAX Pmopm8Almchannel62PortEntry
	MAX-ACCESS not-accessible
	STATUS current
	DESCRIPTION
        "
        Row definition for the pmopm8Almchannel62Port
        table
        "
	INDEX   { pmopm8Almchannel62PortIndex }
	::= { pmopm8Almchannel62PortTable 1 }


Pmopm8Almchannel62PortEntry ::=
	SEQUENCE {
	pmopm8Almchannel62PortIndex
		INTEGER,
	pmopm8AlmChannel62OosPortn
		EkiOnOff,
	pmopm8AlmChannel62PowerHighPortn
		EkiOnOff,
	pmopm8AlmChannel62PowerLowPortn
		EkiOnOff,
	pmopm8AlmChannel62BalancedPortn
		EkiOnOff,
	pmopm8AlmChannel62MismatchPortn
		EkiOnOff,
	pmopm8AlmChannel62AbsentPortn
		EkiOnOff
	}


pmopm8Almchannel62PortIndex OBJECT-TYPE
	SYNTAX  INTEGER(0..128)
	MAX-ACCESS  read-only
	STATUS current
	DESCRIPTION
        "
        Index definition for the pmopm8Almchannel62Port
        table
        "
	::= { pmopm8Almchannel62PortEntry 1 }


pmopm8AlmChannel62OosPortn OBJECT-TYPE
	SYNTAX  EkiOnOff
	MAX-ACCESS read-only
	STATUS current
	DESCRIPTION
        "
        Channel Out Of Service 62 :This
        OID indicates that the channel
         is out of service  <Help> This
        alarm indicates that the channel
        is in service <Condtype> CHANNEL62_OOS_1
        <Probcause> informationalStatus(1000)
        <Alarmtype> other (1) <Polarity>
        (2)
        "
	::= { pmopm8Almchannel62PortEntry 7 }


pmopm8AlmChannel62PowerHighPortn OBJECT-TYPE
	SYNTAX  EkiOnOff
	MAX-ACCESS read-only
	STATUS current
	DESCRIPTION
        "
        Channel Power High 62 :This OID
        indicates that the power of the
        channel is higher than the configured
        threshold<Help> This alarm indicates
        that the power of the channel is
        higher than the configured threshold
        <Condtype> CHANNEL62_POWER_HIGH_1
        <Probcause> degradedSignal (13)
        <Alarmtype> equipmentAlarm <Polarity>
        (2)
        "
	::= { pmopm8Almchannel62PortEntry 6 }


pmopm8AlmChannel62PowerLowPortn OBJECT-TYPE
	SYNTAX  EkiOnOff
	MAX-ACCESS read-only
	STATUS current
	DESCRIPTION
        "
        Channel Power Low 62 :This OID
        indicates that the power of the
        channel is lower than the configured
        threshold<Help> This alarm indicates
        that the power of the channel is
        lower than the configured threshold
        <Condtype> CHANNEL62_POWER_LOW_1
        <Probcause> degradedSignal (13)
        <Alarmtype> equipmentAlarm <Polarity>
        (2)
        "
	::= { pmopm8Almchannel62PortEntry 5 }


pmopm8AlmChannel62BalancedPortn OBJECT-TYPE
	SYNTAX  EkiOnOff
	MAX-ACCESS read-only
	STATUS current
	DESCRIPTION
        "
        Channel Balanced 62 :This OID
         indicates that an in service channel
        is balanced by the Ekinops auto
        turn up application<Help> This
         status indicates that an in service
        channel is balanced by the Ekinops
        auto turn up application <Condtype>
        CHANNEL62_BALANCED_1 <Probcause>
        informationalStatus(1000) <Alarmtype>
        other (1) <Polarity> (2)
        "
	::= { pmopm8Almchannel62PortEntry 4 }


pmopm8AlmChannel62MismatchPortn OBJECT-TYPE
	SYNTAX  EkiOnOff
	MAX-ACCESS read-only
	STATUS current
	DESCRIPTION
        "
        Channel Mismatch 62 :This OID
         indicates that an out of service
        channel is detected on the Optical
        Power Monitoring input<Help> This
        alarm indicates that an out of
         service channel is detected on
        the Optical Power Monitoring input
        <Condtype> CHANNEL62_MISMATCH_1
        <Probcause> unexpectedInformation
        (75) <Alarmtype> equipmentAlarm
        <Polarity> (2)
        "
	::= { pmopm8Almchannel62PortEntry 3 }


pmopm8AlmChannel62AbsentPortn OBJECT-TYPE
	SYNTAX  EkiOnOff
	MAX-ACCESS read-only
	STATUS current
	DESCRIPTION
        "
        Channel Absent 62 :This OID indicates
        that an in service channel is absent
        on the Optical Power Monitoring
        input<Help> This alarm indicates
        that an in service channel is absent
        on the Optical Power Monitoring
        input <Condtype> CHANNEL62_ABSENT_1
        <Probcause> informationMissing
         (65) <Alarmtype> equipmentAlarm
        (5) <Polarity> (2)
        "
	::= { pmopm8Almchannel62PortEntry 2 }


--- *********************************************************
---     TABLE for the pmopm8Almchannel63Port articles
--- *********************************************************

pmopm8Almchannel63PortTable OBJECT-TYPE
	SYNTAX  SEQUENCE OF Pmopm8Almchannel63PortEntry
	MAX-ACCESS not-accessible
	STATUS current
	DESCRIPTION
        "
        List of pmopm8Almchannel63Port
        Article
        "
	::= { pmopm8AlmClientCrit 512 }


pmopm8Almchannel63PortEntry OBJECT-TYPE
	SYNTAX Pmopm8Almchannel63PortEntry
	MAX-ACCESS not-accessible
	STATUS current
	DESCRIPTION
        "
        Row definition for the pmopm8Almchannel63Port
        table
        "
	INDEX   { pmopm8Almchannel63PortIndex }
	::= { pmopm8Almchannel63PortTable 1 }


Pmopm8Almchannel63PortEntry ::=
	SEQUENCE {
	pmopm8Almchannel63PortIndex
		INTEGER,
	pmopm8AlmChannel63OosPortn
		EkiOnOff,
	pmopm8AlmChannel63PowerHighPortn
		EkiOnOff,
	pmopm8AlmChannel63PowerLowPortn
		EkiOnOff,
	pmopm8AlmChannel63BalancedPortn
		EkiOnOff,
	pmopm8AlmChannel63MismatchPortn
		EkiOnOff,
	pmopm8AlmChannel63AbsentPortn
		EkiOnOff
	}


pmopm8Almchannel63PortIndex OBJECT-TYPE
	SYNTAX  INTEGER(0..128)
	MAX-ACCESS  read-only
	STATUS current
	DESCRIPTION
        "
        Index definition for the pmopm8Almchannel63Port
        table
        "
	::= { pmopm8Almchannel63PortEntry 1 }


pmopm8AlmChannel63OosPortn OBJECT-TYPE
	SYNTAX  EkiOnOff
	MAX-ACCESS read-only
	STATUS current
	DESCRIPTION
        "
        Channel Out Of Service 63 :This
        OID indicates that the channel
         is out of service  <Help> This
        alarm indicates that the channel
        is in service <Condtype> CHANNEL63_OOS_1
        <Probcause> informationalStatus(1000)
        <Alarmtype> other (1) <Polarity>
        (2)
        "
	::= { pmopm8Almchannel63PortEntry 7 }


pmopm8AlmChannel63PowerHighPortn OBJECT-TYPE
	SYNTAX  EkiOnOff
	MAX-ACCESS read-only
	STATUS current
	DESCRIPTION
        "
        Channel Power High 63 :This OID
        indicates that the power of the
        channel is higher than the configured
        threshold<Help> This alarm indicates
        that the power of the channel is
        higher than the configured threshold
        <Condtype> CHANNEL63_POWER_HIGH_1
        <Probcause> degradedSignal (13)
        <Alarmtype> equipmentAlarm <Polarity>
        (2)
        "
	::= { pmopm8Almchannel63PortEntry 6 }


pmopm8AlmChannel63PowerLowPortn OBJECT-TYPE
	SYNTAX  EkiOnOff
	MAX-ACCESS read-only
	STATUS current
	DESCRIPTION
        "
        Channel Power Low 63 :This OID
        indicates that the power of the
        channel is lower than the configured
        threshold<Help> This alarm indicates
        that the power of the channel is
        lower than the configured threshold
        <Condtype> CHANNEL63_POWER_LOW_1
        <Probcause> degradedSignal (13)
        <Alarmtype> equipmentAlarm <Polarity>
        (2)
        "
	::= { pmopm8Almchannel63PortEntry 5 }


pmopm8AlmChannel63BalancedPortn OBJECT-TYPE
	SYNTAX  EkiOnOff
	MAX-ACCESS read-only
	STATUS current
	DESCRIPTION
        "
        Channel Balanced 63 :This OID
         indicates that an in service channel
        is balanced by the Ekinops auto
        turn up application<Help> This
         status indicates that an in service
        channel is balanced by the Ekinops
        auto turn up application <Condtype>
        CHANNEL63_BALANCED_1 <Probcause>
        informationalStatus(1000) <Alarmtype>
        other (1) <Polarity> (2)
        "
	::= { pmopm8Almchannel63PortEntry 4 }


pmopm8AlmChannel63MismatchPortn OBJECT-TYPE
	SYNTAX  EkiOnOff
	MAX-ACCESS read-only
	STATUS current
	DESCRIPTION
        "
        Channel Mismatch 63 :This OID
         indicates that an out of service
        channel is detected on the Optical
        Power Monitoring input<Help> This
        alarm indicates that an out of
         service channel is detected on
        the Optical Power Monitoring input
        <Condtype> CHANNEL63_MISMATCH_1
        <Probcause> unexpectedInformation
        (75) <Alarmtype> equipmentAlarm
        <Polarity> (2)
        "
	::= { pmopm8Almchannel63PortEntry 3 }


pmopm8AlmChannel63AbsentPortn OBJECT-TYPE
	SYNTAX  EkiOnOff
	MAX-ACCESS read-only
	STATUS current
	DESCRIPTION
        "
        Channel Absent 63 :This OID indicates
        that an in service channel is absent
        on the Optical Power Monitoring
        input<Help> This alarm indicates
        that an in service channel is absent
        on the Optical Power Monitoring
        input <Condtype> CHANNEL63_ABSENT_1
        <Probcause> informationMissing
         (65) <Alarmtype> equipmentAlarm
        (5) <Polarity> (2)
        "
	::= { pmopm8Almchannel63PortEntry 2 }


--- *********************************************************
---     TABLE for the pmopm8Almchannel64Port articles
--- *********************************************************

pmopm8Almchannel64PortTable OBJECT-TYPE
	SYNTAX  SEQUENCE OF Pmopm8Almchannel64PortEntry
	MAX-ACCESS not-accessible
	STATUS current
	DESCRIPTION
        "
        List of pmopm8Almchannel64Port
        Article
        "
	::= { pmopm8AlmClientCrit 520 }


pmopm8Almchannel64PortEntry OBJECT-TYPE
	SYNTAX Pmopm8Almchannel64PortEntry
	MAX-ACCESS not-accessible
	STATUS current
	DESCRIPTION
        "
        Row definition for the pmopm8Almchannel64Port
        table
        "
	INDEX   { pmopm8Almchannel64PortIndex }
	::= { pmopm8Almchannel64PortTable 1 }


Pmopm8Almchannel64PortEntry ::=
	SEQUENCE {
	pmopm8Almchannel64PortIndex
		INTEGER,
	pmopm8AlmChannel64OosPortn
		EkiOnOff,
	pmopm8AlmChannel64PowerHighPortn
		EkiOnOff,
	pmopm8AlmChannel64PowerLowPortn
		EkiOnOff,
	pmopm8AlmChannel64BalancedPortn
		EkiOnOff,
	pmopm8AlmChannel64MismatchPortn
		EkiOnOff,
	pmopm8AlmChannel64AbsentPortn
		EkiOnOff
	}


pmopm8Almchannel64PortIndex OBJECT-TYPE
	SYNTAX  INTEGER(0..128)
	MAX-ACCESS  read-only
	STATUS current
	DESCRIPTION
        "
        Index definition for the pmopm8Almchannel64Port
        table
        "
	::= { pmopm8Almchannel64PortEntry 1 }


pmopm8AlmChannel64OosPortn OBJECT-TYPE
	SYNTAX  EkiOnOff
	MAX-ACCESS read-only
	STATUS current
	DESCRIPTION
        "
        Channel Out Of Service 64 :This
        OID indicates that the channel
         is out of service  <Help> This
        alarm indicates that the channel
        is in service <Condtype> CHANNEL64_OOS_1
        <Probcause> informationalStatus(1000)
        <Alarmtype> other (1) <Polarity>
        (2)
        "
	::= { pmopm8Almchannel64PortEntry 7 }


pmopm8AlmChannel64PowerHighPortn OBJECT-TYPE
	SYNTAX  EkiOnOff
	MAX-ACCESS read-only
	STATUS current
	DESCRIPTION
        "
        Channel Power High 64 :This OID
        indicates that the power of the
        channel is higher than the configured
        threshold<Help> This alarm indicates
        that the power of the channel is
        higher than the configured threshold
        <Condtype> CHANNEL64_POWER_HIGH_1
        <Probcause> degradedSignal (13)
        <Alarmtype> equipmentAlarm <Polarity>
        (2)
        "
	::= { pmopm8Almchannel64PortEntry 6 }


pmopm8AlmChannel64PowerLowPortn OBJECT-TYPE
	SYNTAX  EkiOnOff
	MAX-ACCESS read-only
	STATUS current
	DESCRIPTION
        "
        Channel Power Low 64 :This OID
        indicates that the power of the
        channel is lower than the configured
        threshold<Help> This alarm indicates
        that the power of the channel is
        lower than the configured threshold
        <Condtype> CHANNEL64_POWER_LOW_1
        <Probcause> degradedSignal (13)
        <Alarmtype> equipmentAlarm <Polarity>
        (2)
        "
	::= { pmopm8Almchannel64PortEntry 5 }


pmopm8AlmChannel64BalancedPortn OBJECT-TYPE
	SYNTAX  EkiOnOff
	MAX-ACCESS read-only
	STATUS current
	DESCRIPTION
        "
        Channel Balanced 64 :This OID
         indicates that an in service channel
        is balanced by the Ekinops auto
        turn up application<Help> This
         status indicates that an in service
        channel is balanced by the Ekinops
        auto turn up application <Condtype>
        CHANNEL64_BALANCED_1 <Probcause>
        informationalStatus(1000) <Alarmtype>
        other (1) <Polarity> (2)
        "
	::= { pmopm8Almchannel64PortEntry 4 }


pmopm8AlmChannel64MismatchPortn OBJECT-TYPE
	SYNTAX  EkiOnOff
	MAX-ACCESS read-only
	STATUS current
	DESCRIPTION
        "
        Channel Mismatch 64 :This OID
         indicates that an out of service
        channel is detected on the Optical
        Power Monitoring input<Help> This
        alarm indicates that an out of
         service channel is detected on
        the Optical Power Monitoring input
        <Condtype> CHANNEL64_MISMATCH_1
        <Probcause> unexpectedInformation
        (75) <Alarmtype> equipmentAlarm
        <Polarity> (2)
        "
	::= { pmopm8Almchannel64PortEntry 3 }


pmopm8AlmChannel64AbsentPortn OBJECT-TYPE
	SYNTAX  EkiOnOff
	MAX-ACCESS read-only
	STATUS current
	DESCRIPTION
        "
        Channel Absent 64 :This OID indicates
        that an in service channel is absent
        on the Optical Power Monitoring
        input<Help> This alarm indicates
        that an in service channel is absent
        on the Optical Power Monitoring
        input <Condtype> CHANNEL64_ABSENT_1
        <Probcause> informationMissing
         (65) <Alarmtype> equipmentAlarm
        (5) <Polarity> (2)
        "
	::= { pmopm8Almchannel64PortEntry 2 }


--- *********************************************************
---     TABLE for the pmopm8Almchannel65Port articles
--- *********************************************************

pmopm8Almchannel65PortTable OBJECT-TYPE
	SYNTAX  SEQUENCE OF Pmopm8Almchannel65PortEntry
	MAX-ACCESS not-accessible
	STATUS current
	DESCRIPTION
        "
        List of pmopm8Almchannel65Port
        Article
        "
	::= { pmopm8AlmClientCrit 528 }


pmopm8Almchannel65PortEntry OBJECT-TYPE
	SYNTAX Pmopm8Almchannel65PortEntry
	MAX-ACCESS not-accessible
	STATUS current
	DESCRIPTION
        "
        Row definition for the pmopm8Almchannel65Port
        table
        "
	INDEX   { pmopm8Almchannel65PortIndex }
	::= { pmopm8Almchannel65PortTable 1 }


Pmopm8Almchannel65PortEntry ::=
	SEQUENCE {
	pmopm8Almchannel65PortIndex
		INTEGER,
	pmopm8AlmChannel65OosPortn
		EkiOnOff,
	pmopm8AlmChannel65PowerHighPortn
		EkiOnOff,
	pmopm8AlmChannel65PowerLowPortn
		EkiOnOff,
	pmopm8AlmChannel65BalancedPortn
		EkiOnOff,
	pmopm8AlmChannel65MismatchPortn
		EkiOnOff,
	pmopm8AlmChannel65AbsentPortn
		EkiOnOff
	}


pmopm8Almchannel65PortIndex OBJECT-TYPE
	SYNTAX  INTEGER(0..128)
	MAX-ACCESS  read-only
	STATUS current
	DESCRIPTION
        "
        Index definition for the pmopm8Almchannel65Port
        table
        "
	::= { pmopm8Almchannel65PortEntry 1 }


pmopm8AlmChannel65OosPortn OBJECT-TYPE
	SYNTAX  EkiOnOff
	MAX-ACCESS read-only
	STATUS current
	DESCRIPTION
        "
        Channel Out Of Service 65 :This
        OID indicates that the channel
         is out of service  <Help> This
        alarm indicates that the channel
        is in service <Condtype> CHANNEL65_OOS_1
        <Probcause> informationalStatus(1000)
        <Alarmtype> other (1) <Polarity>
        (2)
        "
	::= { pmopm8Almchannel65PortEntry 7 }


pmopm8AlmChannel65PowerHighPortn OBJECT-TYPE
	SYNTAX  EkiOnOff
	MAX-ACCESS read-only
	STATUS current
	DESCRIPTION
        "
        Channel Power High 65 :This OID
        indicates that the power of the
        channel is higher than the configured
        threshold<Help> This alarm indicates
        that the power of the channel is
        higher than the configured threshold
        <Condtype> CHANNEL65_POWER_HIGH_1
        <Probcause> degradedSignal (13)
        <Alarmtype> equipmentAlarm <Polarity>
        (2)
        "
	::= { pmopm8Almchannel65PortEntry 6 }


pmopm8AlmChannel65PowerLowPortn OBJECT-TYPE
	SYNTAX  EkiOnOff
	MAX-ACCESS read-only
	STATUS current
	DESCRIPTION
        "
        Channel Power Low 65 :This OID
        indicates that the power of the
        channel is lower than the configured
        threshold<Help> This alarm indicates
        that the power of the channel is
        lower than the configured threshold
        <Condtype> CHANNEL65_POWER_LOW_1
        <Probcause> degradedSignal (13)
        <Alarmtype> equipmentAlarm <Polarity>
        (2)
        "
	::= { pmopm8Almchannel65PortEntry 5 }


pmopm8AlmChannel65BalancedPortn OBJECT-TYPE
	SYNTAX  EkiOnOff
	MAX-ACCESS read-only
	STATUS current
	DESCRIPTION
        "
        Channel Balanced 65 :This OID
         indicates that an in service channel
        is balanced by the Ekinops auto
        turn up application<Help> This
         status indicates that an in service
        channel is balanced by the Ekinops
        auto turn up application <Condtype>
        CHANNEL65_BALANCED_1 <Probcause>
        informationalStatus(1000) <Alarmtype>
        other (1) <Polarity> (2)
        "
	::= { pmopm8Almchannel65PortEntry 4 }


pmopm8AlmChannel65MismatchPortn OBJECT-TYPE
	SYNTAX  EkiOnOff
	MAX-ACCESS read-only
	STATUS current
	DESCRIPTION
        "
        Channel Mismatch 65 :This OID
         indicates that an out of service
        channel is detected on the Optical
        Power Monitoring input<Help> This
        alarm indicates that an out of
         service channel is detected on
        the Optical Power Monitoring input
        <Condtype> CHANNEL65_MISMATCH_1
        <Probcause> unexpectedInformation
        (75) <Alarmtype> equipmentAlarm
        <Polarity> (2)
        "
	::= { pmopm8Almchannel65PortEntry 3 }


pmopm8AlmChannel65AbsentPortn OBJECT-TYPE
	SYNTAX  EkiOnOff
	MAX-ACCESS read-only
	STATUS current
	DESCRIPTION
        "
        Channel Absent 65 :This OID indicates
        that an in service channel is absent
        on the Optical Power Monitoring
        input<Help> This alarm indicates
        that an in service channel is absent
        on the Optical Power Monitoring
        input <Condtype> CHANNEL65_ABSENT_1
        <Probcause> informationMissing
         (65) <Alarmtype> equipmentAlarm
        (5) <Polarity> (2)
        "
	::= { pmopm8Almchannel65PortEntry 2 }


--- *********************************************************
---     TABLE for the pmopm8Almchannel66Port articles
--- *********************************************************

pmopm8Almchannel66PortTable OBJECT-TYPE
	SYNTAX  SEQUENCE OF Pmopm8Almchannel66PortEntry
	MAX-ACCESS not-accessible
	STATUS current
	DESCRIPTION
        "
        List of pmopm8Almchannel66Port
        Article
        "
	::= { pmopm8AlmClientCrit 536 }


pmopm8Almchannel66PortEntry OBJECT-TYPE
	SYNTAX Pmopm8Almchannel66PortEntry
	MAX-ACCESS not-accessible
	STATUS current
	DESCRIPTION
        "
        Row definition for the pmopm8Almchannel66Port
        table
        "
	INDEX   { pmopm8Almchannel66PortIndex }
	::= { pmopm8Almchannel66PortTable 1 }


Pmopm8Almchannel66PortEntry ::=
	SEQUENCE {
	pmopm8Almchannel66PortIndex
		INTEGER,
	pmopm8AlmChannel66OosPortn
		EkiOnOff,
	pmopm8AlmChannel66PowerHighPortn
		EkiOnOff,
	pmopm8AlmChannel66PowerLowPortn
		EkiOnOff,
	pmopm8AlmChannel66BalancedPortn
		EkiOnOff,
	pmopm8AlmChannel66MismatchPortn
		EkiOnOff,
	pmopm8AlmChannel66AbsentPortn
		EkiOnOff
	}


pmopm8Almchannel66PortIndex OBJECT-TYPE
	SYNTAX  INTEGER(0..128)
	MAX-ACCESS  read-only
	STATUS current
	DESCRIPTION
        "
        Index definition for the pmopm8Almchannel66Port
        table
        "
	::= { pmopm8Almchannel66PortEntry 1 }


pmopm8AlmChannel66OosPortn OBJECT-TYPE
	SYNTAX  EkiOnOff
	MAX-ACCESS read-only
	STATUS current
	DESCRIPTION
        "
        Channel Out Of Service 66 :This
        OID indicates that the channel
         is out of service  <Help> This
        alarm indicates that the channel
        is in service <Condtype> CHANNEL66_OOS_1
        <Probcause> informationalStatus(1000)
        <Alarmtype> other (1) <Polarity>
        (2)
        "
	::= { pmopm8Almchannel66PortEntry 7 }


pmopm8AlmChannel66PowerHighPortn OBJECT-TYPE
	SYNTAX  EkiOnOff
	MAX-ACCESS read-only
	STATUS current
	DESCRIPTION
        "
        Channel Power High 66 :This OID
        indicates that the power of the
        channel is higher than the configured
        threshold<Help> This alarm indicates
        that the power of the channel is
        higher than the configured threshold
        <Condtype> CHANNEL66_POWER_HIGH_1
        <Probcause> degradedSignal (13)
        <Alarmtype> equipmentAlarm <Polarity>
        (2)
        "
	::= { pmopm8Almchannel66PortEntry 6 }


pmopm8AlmChannel66PowerLowPortn OBJECT-TYPE
	SYNTAX  EkiOnOff
	MAX-ACCESS read-only
	STATUS current
	DESCRIPTION
        "
        Channel Power Low 66 :This OID
        indicates that the power of the
        channel is lower than the configured
        threshold<Help> This alarm indicates
        that the power of the channel is
        lower than the configured threshold
        <Condtype> CHANNEL66_POWER_LOW_1
        <Probcause> degradedSignal (13)
        <Alarmtype> equipmentAlarm <Polarity>
        (2)
        "
	::= { pmopm8Almchannel66PortEntry 5 }


pmopm8AlmChannel66BalancedPortn OBJECT-TYPE
	SYNTAX  EkiOnOff
	MAX-ACCESS read-only
	STATUS current
	DESCRIPTION
        "
        Channel Balanced 66 :This OID
         indicates that an in service channel
        is balanced by the Ekinops auto
        turn up application<Help> This
         status indicates that an in service
        channel is balanced by the Ekinops
        auto turn up application <Condtype>
        CHANNEL66_BALANCED_1 <Probcause>
        informationalStatus(1000) <Alarmtype>
        other (1) <Polarity> (2)
        "
	::= { pmopm8Almchannel66PortEntry 4 }


pmopm8AlmChannel66MismatchPortn OBJECT-TYPE
	SYNTAX  EkiOnOff
	MAX-ACCESS read-only
	STATUS current
	DESCRIPTION
        "
        Channel Mismatch 66 :This OID
         indicates that an out of service
        channel is detected on the Optical
        Power Monitoring input<Help> This
        alarm indicates that an out of
         service channel is detected on
        the Optical Power Monitoring input
        <Condtype> CHANNEL66_MISMATCH_1
        <Probcause> unexpectedInformation
        (75) <Alarmtype> equipmentAlarm
        <Polarity> (2)
        "
	::= { pmopm8Almchannel66PortEntry 3 }


pmopm8AlmChannel66AbsentPortn OBJECT-TYPE
	SYNTAX  EkiOnOff
	MAX-ACCESS read-only
	STATUS current
	DESCRIPTION
        "
        Channel Absent 66 :This OID indicates
        that an in service channel is absent
        on the Optical Power Monitoring
        input<Help> This alarm indicates
        that an in service channel is absent
        on the Optical Power Monitoring
        input <Condtype> CHANNEL66_ABSENT_1
        <Probcause> informationMissing
         (65) <Alarmtype> equipmentAlarm
        (5) <Polarity> (2)
        "
	::= { pmopm8Almchannel66PortEntry 2 }


--- *********************************************************
---     TABLE for the pmopm8Almchannel67Port articles
--- *********************************************************

pmopm8Almchannel67PortTable OBJECT-TYPE
	SYNTAX  SEQUENCE OF Pmopm8Almchannel67PortEntry
	MAX-ACCESS not-accessible
	STATUS current
	DESCRIPTION
        "
        List of pmopm8Almchannel67Port
        Article
        "
	::= { pmopm8AlmClientCrit 544 }


pmopm8Almchannel67PortEntry OBJECT-TYPE
	SYNTAX Pmopm8Almchannel67PortEntry
	MAX-ACCESS not-accessible
	STATUS current
	DESCRIPTION
        "
        Row definition for the pmopm8Almchannel67Port
        table
        "
	INDEX   { pmopm8Almchannel67PortIndex }
	::= { pmopm8Almchannel67PortTable 1 }


Pmopm8Almchannel67PortEntry ::=
	SEQUENCE {
	pmopm8Almchannel67PortIndex
		INTEGER,
	pmopm8AlmChannel67OosPortn
		EkiOnOff,
	pmopm8AlmChannel67PowerHighPortn
		EkiOnOff,
	pmopm8AlmChannel67PowerLowPortn
		EkiOnOff,
	pmopm8AlmChannel67BalancedPortn
		EkiOnOff,
	pmopm8AlmChannel67MismatchPortn
		EkiOnOff,
	pmopm8AlmChannel67AbsentPortn
		EkiOnOff
	}


pmopm8Almchannel67PortIndex OBJECT-TYPE
	SYNTAX  INTEGER(0..128)
	MAX-ACCESS  read-only
	STATUS current
	DESCRIPTION
        "
        Index definition for the pmopm8Almchannel67Port
        table
        "
	::= { pmopm8Almchannel67PortEntry 1 }


pmopm8AlmChannel67OosPortn OBJECT-TYPE
	SYNTAX  EkiOnOff
	MAX-ACCESS read-only
	STATUS current
	DESCRIPTION
        "
        Channel Out Of Service 67 :This
        OID indicates that the channel
         is out of service  <Help> This
        alarm indicates that the channel
        is in service <Condtype> CHANNEL67_OOS_1
        <Probcause> informationalStatus(1000)
        <Alarmtype> other (1) <Polarity>
        (2)
        "
	::= { pmopm8Almchannel67PortEntry 7 }


pmopm8AlmChannel67PowerHighPortn OBJECT-TYPE
	SYNTAX  EkiOnOff
	MAX-ACCESS read-only
	STATUS current
	DESCRIPTION
        "
        Channel Power High 67 :This OID
        indicates that the power of the
        channel is higher than the configured
        threshold<Help> This alarm indicates
        that the power of the channel is
        higher than the configured threshold
        <Condtype> CHANNEL67_POWER_HIGH_1
        <Probcause> degradedSignal (13)
        <Alarmtype> equipmentAlarm <Polarity>
        (2)
        "
	::= { pmopm8Almchannel67PortEntry 6 }


pmopm8AlmChannel67PowerLowPortn OBJECT-TYPE
	SYNTAX  EkiOnOff
	MAX-ACCESS read-only
	STATUS current
	DESCRIPTION
        "
        Channel Power Low 67 :This OID
        indicates that the power of the
        channel is lower than the configured
        threshold<Help> This alarm indicates
        that the power of the channel is
        lower than the configured threshold
        <Condtype> CHANNEL67_POWER_LOW_1
        <Probcause> degradedSignal (13)
        <Alarmtype> equipmentAlarm <Polarity>
        (2)
        "
	::= { pmopm8Almchannel67PortEntry 5 }


pmopm8AlmChannel67BalancedPortn OBJECT-TYPE
	SYNTAX  EkiOnOff
	MAX-ACCESS read-only
	STATUS current
	DESCRIPTION
        "
        Channel Balanced 67 :This OID
         indicates that an in service channel
        is balanced by the Ekinops auto
        turn up application<Help> This
         status indicates that an in service
        channel is balanced by the Ekinops
        auto turn up application <Condtype>
        CHANNEL67_BALANCED_1 <Probcause>
        informationalStatus(1000) <Alarmtype>
        other (1) <Polarity> (2)
        "
	::= { pmopm8Almchannel67PortEntry 4 }


pmopm8AlmChannel67MismatchPortn OBJECT-TYPE
	SYNTAX  EkiOnOff
	MAX-ACCESS read-only
	STATUS current
	DESCRIPTION
        "
        Channel Mismatch 67 :This OID
         indicates that an out of service
        channel is detected on the Optical
        Power Monitoring input<Help> This
        alarm indicates that an out of
         service channel is detected on
        the Optical Power Monitoring input
        <Condtype> CHANNEL67_MISMATCH_1
        <Probcause> unexpectedInformation
        (75) <Alarmtype> equipmentAlarm
        <Polarity> (2)
        "
	::= { pmopm8Almchannel67PortEntry 3 }


pmopm8AlmChannel67AbsentPortn OBJECT-TYPE
	SYNTAX  EkiOnOff
	MAX-ACCESS read-only
	STATUS current
	DESCRIPTION
        "
        Channel Absent 67 :This OID indicates
        that an in service channel is absent
        on the Optical Power Monitoring
        input<Help> This alarm indicates
        that an in service channel is absent
        on the Optical Power Monitoring
        input <Condtype> CHANNEL67_ABSENT_1
        <Probcause> informationMissing
         (65) <Alarmtype> equipmentAlarm
        (5) <Polarity> (2)
        "
	::= { pmopm8Almchannel67PortEntry 2 }


--- *********************************************************
---     TABLE for the pmopm8Almchannel68Port articles
--- *********************************************************

pmopm8Almchannel68PortTable OBJECT-TYPE
	SYNTAX  SEQUENCE OF Pmopm8Almchannel68PortEntry
	MAX-ACCESS not-accessible
	STATUS current
	DESCRIPTION
        "
        List of pmopm8Almchannel68Port
        Article
        "
	::= { pmopm8AlmClientCrit 552 }


pmopm8Almchannel68PortEntry OBJECT-TYPE
	SYNTAX Pmopm8Almchannel68PortEntry
	MAX-ACCESS not-accessible
	STATUS current
	DESCRIPTION
        "
        Row definition for the pmopm8Almchannel68Port
        table
        "
	INDEX   { pmopm8Almchannel68PortIndex }
	::= { pmopm8Almchannel68PortTable 1 }


Pmopm8Almchannel68PortEntry ::=
	SEQUENCE {
	pmopm8Almchannel68PortIndex
		INTEGER,
	pmopm8AlmChannel68OosPortn
		EkiOnOff,
	pmopm8AlmChannel68PowerHighPortn
		EkiOnOff,
	pmopm8AlmChannel68PowerLowPortn
		EkiOnOff,
	pmopm8AlmChannel68BalancedPortn
		EkiOnOff,
	pmopm8AlmChannel68MismatchPortn
		EkiOnOff,
	pmopm8AlmChannel68AbsentPortn
		EkiOnOff
	}


pmopm8Almchannel68PortIndex OBJECT-TYPE
	SYNTAX  INTEGER(0..128)
	MAX-ACCESS  read-only
	STATUS current
	DESCRIPTION
        "
        Index definition for the pmopm8Almchannel68Port
        table
        "
	::= { pmopm8Almchannel68PortEntry 1 }


pmopm8AlmChannel68OosPortn OBJECT-TYPE
	SYNTAX  EkiOnOff
	MAX-ACCESS read-only
	STATUS current
	DESCRIPTION
        "
        Channel Out Of Service 68 :This
        OID indicates that the channel
         is out of service  <Help> This
        alarm indicates that the channel
        is in service <Condtype> CHANNEL68_OOS_1
        <Probcause> informationalStatus(1000)
        <Alarmtype> other (1) <Polarity>
        (2)
        "
	::= { pmopm8Almchannel68PortEntry 7 }


pmopm8AlmChannel68PowerHighPortn OBJECT-TYPE
	SYNTAX  EkiOnOff
	MAX-ACCESS read-only
	STATUS current
	DESCRIPTION
        "
        Channel Power High 68 :This OID
        indicates that the power of the
        channel is higher than the configured
        threshold<Help> This alarm indicates
        that the power of the channel is
        higher than the configured threshold
        <Condtype> CHANNEL68_POWER_HIGH_1
        <Probcause> degradedSignal (13)
        <Alarmtype> equipmentAlarm <Polarity>
        (2)
        "
	::= { pmopm8Almchannel68PortEntry 6 }


pmopm8AlmChannel68PowerLowPortn OBJECT-TYPE
	SYNTAX  EkiOnOff
	MAX-ACCESS read-only
	STATUS current
	DESCRIPTION
        "
        Channel Power Low 68 :This OID
        indicates that the power of the
        channel is lower than the configured
        threshold<Help> This alarm indicates
        that the power of the channel is
        lower than the configured threshold
        <Condtype> CHANNEL68_POWER_LOW_1
        <Probcause> degradedSignal (13)
        <Alarmtype> equipmentAlarm <Polarity>
        (2)
        "
	::= { pmopm8Almchannel68PortEntry 5 }


pmopm8AlmChannel68BalancedPortn OBJECT-TYPE
	SYNTAX  EkiOnOff
	MAX-ACCESS read-only
	STATUS current
	DESCRIPTION
        "
        Channel Balanced 68 :This OID
         indicates that an in service channel
        is balanced by the Ekinops auto
        turn up application<Help> This
         status indicates that an in service
        channel is balanced by the Ekinops
        auto turn up application <Condtype>
        CHANNEL68_BALANCED_1 <Probcause>
        informationalStatus(1000) <Alarmtype>
        other (1) <Polarity> (2)
        "
	::= { pmopm8Almchannel68PortEntry 4 }


pmopm8AlmChannel68MismatchPortn OBJECT-TYPE
	SYNTAX  EkiOnOff
	MAX-ACCESS read-only
	STATUS current
	DESCRIPTION
        "
        Channel Mismatch 68 :This OID
         indicates that an out of service
        channel is detected on the Optical
        Power Monitoring input<Help> This
        alarm indicates that an out of
         service channel is detected on
        the Optical Power Monitoring input
        <Condtype> CHANNEL68_MISMATCH_1
        <Probcause> unexpectedInformation
        (75) <Alarmtype> equipmentAlarm
        <Polarity> (2)
        "
	::= { pmopm8Almchannel68PortEntry 3 }


pmopm8AlmChannel68AbsentPortn OBJECT-TYPE
	SYNTAX  EkiOnOff
	MAX-ACCESS read-only
	STATUS current
	DESCRIPTION
        "
        Channel Absent 68 :This OID indicates
        that an in service channel is absent
        on the Optical Power Monitoring
        input<Help> This alarm indicates
        that an in service channel is absent
        on the Optical Power Monitoring
        input <Condtype> CHANNEL68_ABSENT_1
        <Probcause> informationMissing
         (65) <Alarmtype> equipmentAlarm
        (5) <Polarity> (2)
        "
	::= { pmopm8Almchannel68PortEntry 2 }


--- *********************************************************
---     TABLE for the pmopm8Almchannel69Port articles
--- *********************************************************

pmopm8Almchannel69PortTable OBJECT-TYPE
	SYNTAX  SEQUENCE OF Pmopm8Almchannel69PortEntry
	MAX-ACCESS not-accessible
	STATUS current
	DESCRIPTION
        "
        List of pmopm8Almchannel69Port
        Article
        "
	::= { pmopm8AlmClientCrit 560 }


pmopm8Almchannel69PortEntry OBJECT-TYPE
	SYNTAX Pmopm8Almchannel69PortEntry
	MAX-ACCESS not-accessible
	STATUS current
	DESCRIPTION
        "
        Row definition for the pmopm8Almchannel69Port
        table
        "
	INDEX   { pmopm8Almchannel69PortIndex }
	::= { pmopm8Almchannel69PortTable 1 }


Pmopm8Almchannel69PortEntry ::=
	SEQUENCE {
	pmopm8Almchannel69PortIndex
		INTEGER,
	pmopm8AlmChannel69OosPortn
		EkiOnOff,
	pmopm8AlmChannel69PowerHighPortn
		EkiOnOff,
	pmopm8AlmChannel69PowerLowPortn
		EkiOnOff,
	pmopm8AlmChannel69BalancedPortn
		EkiOnOff,
	pmopm8AlmChannel69MismatchPortn
		EkiOnOff,
	pmopm8AlmChannel69AbsentPortn
		EkiOnOff
	}


pmopm8Almchannel69PortIndex OBJECT-TYPE
	SYNTAX  INTEGER(0..128)
	MAX-ACCESS  read-only
	STATUS current
	DESCRIPTION
        "
        Index definition for the pmopm8Almchannel69Port
        table
        "
	::= { pmopm8Almchannel69PortEntry 1 }


pmopm8AlmChannel69OosPortn OBJECT-TYPE
	SYNTAX  EkiOnOff
	MAX-ACCESS read-only
	STATUS current
	DESCRIPTION
        "
        Channel Out Of Service 69 :This
        OID indicates that the channel
         is out of service  <Help> This
        alarm indicates that the channel
        is in service <Condtype> CHANNEL69_OOS_1
        <Probcause> informationalStatus(1000)
        <Alarmtype> other (1) <Polarity>
        (2)
        "
	::= { pmopm8Almchannel69PortEntry 7 }


pmopm8AlmChannel69PowerHighPortn OBJECT-TYPE
	SYNTAX  EkiOnOff
	MAX-ACCESS read-only
	STATUS current
	DESCRIPTION
        "
        Channel Power High 69 :This OID
        indicates that the power of the
        channel is higher than the configured
        threshold<Help> This alarm indicates
        that the power of the channel is
        higher than the configured threshold
        <Condtype> CHANNEL69_POWER_HIGH_1
        <Probcause> degradedSignal (13)
        <Alarmtype> equipmentAlarm <Polarity>
        (2)
        "
	::= { pmopm8Almchannel69PortEntry 6 }


pmopm8AlmChannel69PowerLowPortn OBJECT-TYPE
	SYNTAX  EkiOnOff
	MAX-ACCESS read-only
	STATUS current
	DESCRIPTION
        "
        Channel Power Low 69 :This OID
        indicates that the power of the
        channel is lower than the configured
        threshold<Help> This alarm indicates
        that the power of the channel is
        lower than the configured threshold
        <Condtype> CHANNEL69_POWER_LOW_1
        <Probcause> degradedSignal (13)
        <Alarmtype> equipmentAlarm <Polarity>
        (2)
        "
	::= { pmopm8Almchannel69PortEntry 5 }


pmopm8AlmChannel69BalancedPortn OBJECT-TYPE
	SYNTAX  EkiOnOff
	MAX-ACCESS read-only
	STATUS current
	DESCRIPTION
        "
        Channel Balanced 69 :This OID
         indicates that an in service channel
        is balanced by the Ekinops auto
        turn up application<Help> This
         status indicates that an in service
        channel is balanced by the Ekinops
        auto turn up application <Condtype>
        CHANNEL69_BALANCED_1 <Probcause>
        informationalStatus(1000) <Alarmtype>
        other (1) <Polarity> (2)
        "
	::= { pmopm8Almchannel69PortEntry 4 }


pmopm8AlmChannel69MismatchPortn OBJECT-TYPE
	SYNTAX  EkiOnOff
	MAX-ACCESS read-only
	STATUS current
	DESCRIPTION
        "
        Channel Mismatch 69 :This OID
         indicates that an out of service
        channel is detected on the Optical
        Power Monitoring input<Help> This
        alarm indicates that an out of
         service channel is detected on
        the Optical Power Monitoring input
        <Condtype> CHANNEL69_MISMATCH_1
        <Probcause> unexpectedInformation
        (75) <Alarmtype> equipmentAlarm
        <Polarity> (2)
        "
	::= { pmopm8Almchannel69PortEntry 3 }


pmopm8AlmChannel69AbsentPortn OBJECT-TYPE
	SYNTAX  EkiOnOff
	MAX-ACCESS read-only
	STATUS current
	DESCRIPTION
        "
        Channel Absent 69 :This OID indicates
        that an in service channel is absent
        on the Optical Power Monitoring
        input<Help> This alarm indicates
        that an in service channel is absent
        on the Optical Power Monitoring
        input <Condtype> CHANNEL69_ABSENT_1
        <Probcause> informationMissing
         (65) <Alarmtype> equipmentAlarm
        (5) <Polarity> (2)
        "
	::= { pmopm8Almchannel69PortEntry 2 }


--- *********************************************************
---     TABLE for the pmopm8Almchannel70Port articles
--- *********************************************************

pmopm8Almchannel70PortTable OBJECT-TYPE
	SYNTAX  SEQUENCE OF Pmopm8Almchannel70PortEntry
	MAX-ACCESS not-accessible
	STATUS current
	DESCRIPTION
        "
        List of pmopm8Almchannel70Port
        Article
        "
	::= { pmopm8AlmClientCrit 568 }


pmopm8Almchannel70PortEntry OBJECT-TYPE
	SYNTAX Pmopm8Almchannel70PortEntry
	MAX-ACCESS not-accessible
	STATUS current
	DESCRIPTION
        "
        Row definition for the pmopm8Almchannel70Port
        table
        "
	INDEX   { pmopm8Almchannel70PortIndex }
	::= { pmopm8Almchannel70PortTable 1 }


Pmopm8Almchannel70PortEntry ::=
	SEQUENCE {
	pmopm8Almchannel70PortIndex
		INTEGER,
	pmopm8AlmChannel70OosPortn
		EkiOnOff,
	pmopm8AlmChannel70PowerHighPortn
		EkiOnOff,
	pmopm8AlmChannel70PowerLowPortn
		EkiOnOff,
	pmopm8AlmChannel70BalancedPortn
		EkiOnOff,
	pmopm8AlmChannel70MismatchPortn
		EkiOnOff,
	pmopm8AlmChannel70AbsentPortn
		EkiOnOff
	}


pmopm8Almchannel70PortIndex OBJECT-TYPE
	SYNTAX  INTEGER(0..128)
	MAX-ACCESS  read-only
	STATUS current
	DESCRIPTION
        "
        Index definition for the pmopm8Almchannel70Port
        table
        "
	::= { pmopm8Almchannel70PortEntry 1 }


pmopm8AlmChannel70OosPortn OBJECT-TYPE
	SYNTAX  EkiOnOff
	MAX-ACCESS read-only
	STATUS current
	DESCRIPTION
        "
        Channel Out Of Service 70 :This
        OID indicates that the channel
         is out of service  <Help> This
        alarm indicates that the channel
        is in service <Condtype> CHANNEL70_OOS_1
        <Probcause> informationalStatus(1000)
        <Alarmtype> other (1) <Polarity>
        (2)
        "
	::= { pmopm8Almchannel70PortEntry 7 }


pmopm8AlmChannel70PowerHighPortn OBJECT-TYPE
	SYNTAX  EkiOnOff
	MAX-ACCESS read-only
	STATUS current
	DESCRIPTION
        "
        Channel Power High 70 :This OID
        indicates that the power of the
        channel is higher than the configured
        threshold<Help> This alarm indicates
        that the power of the channel is
        higher than the configured threshold
        <Condtype> CHANNEL70_POWER_HIGH_1
        <Probcause> degradedSignal (13)
        <Alarmtype> equipmentAlarm <Polarity>
        (2)
        "
	::= { pmopm8Almchannel70PortEntry 6 }


pmopm8AlmChannel70PowerLowPortn OBJECT-TYPE
	SYNTAX  EkiOnOff
	MAX-ACCESS read-only
	STATUS current
	DESCRIPTION
        "
        Channel Power Low 70 :This OID
        indicates that the power of the
        channel is lower than the configured
        threshold<Help> This alarm indicates
        that the power of the channel is
        lower than the configured threshold
        <Condtype> CHANNEL70_POWER_LOW_1
        <Probcause> degradedSignal (13)
        <Alarmtype> equipmentAlarm <Polarity>
        (2)
        "
	::= { pmopm8Almchannel70PortEntry 5 }


pmopm8AlmChannel70BalancedPortn OBJECT-TYPE
	SYNTAX  EkiOnOff
	MAX-ACCESS read-only
	STATUS current
	DESCRIPTION
        "
        Channel Balanced 70 :This OID
         indicates that an in service channel
        is balanced by the Ekinops auto
        turn up application<Help> This
         status indicates that an in service
        channel is balanced by the Ekinops
        auto turn up application <Condtype>
        CHANNEL70_BALANCED_1 <Probcause>
        informationalStatus(1000) <Alarmtype>
        other (1) <Polarity> (2)
        "
	::= { pmopm8Almchannel70PortEntry 4 }


pmopm8AlmChannel70MismatchPortn OBJECT-TYPE
	SYNTAX  EkiOnOff
	MAX-ACCESS read-only
	STATUS current
	DESCRIPTION
        "
        Channel Mismatch 70 :This OID
         indicates that an out of service
        channel is detected on the Optical
        Power Monitoring input<Help> This
        alarm indicates that an out of
         service channel is detected on
        the Optical Power Monitoring input
        <Condtype> CHANNEL70_MISMATCH_1
        <Probcause> unexpectedInformation
        (75) <Alarmtype> equipmentAlarm
        <Polarity> (2)
        "
	::= { pmopm8Almchannel70PortEntry 3 }


pmopm8AlmChannel70AbsentPortn OBJECT-TYPE
	SYNTAX  EkiOnOff
	MAX-ACCESS read-only
	STATUS current
	DESCRIPTION
        "
        Channel Absent 70 :This OID indicates
        that an in service channel is absent
        on the Optical Power Monitoring
        input<Help> This alarm indicates
        that an in service channel is absent
        on the Optical Power Monitoring
        input <Condtype> CHANNEL70_ABSENT_1
        <Probcause> informationMissing
         (65) <Alarmtype> equipmentAlarm
        (5) <Polarity> (2)
        "
	::= { pmopm8Almchannel70PortEntry 2 }


--- *********************************************************
---     TABLE for the pmopm8Almchannel71Port articles
--- *********************************************************

pmopm8Almchannel71PortTable OBJECT-TYPE
	SYNTAX  SEQUENCE OF Pmopm8Almchannel71PortEntry
	MAX-ACCESS not-accessible
	STATUS current
	DESCRIPTION
        "
        List of pmopm8Almchannel71Port
        Article
        "
	::= { pmopm8AlmClientCrit 576 }


pmopm8Almchannel71PortEntry OBJECT-TYPE
	SYNTAX Pmopm8Almchannel71PortEntry
	MAX-ACCESS not-accessible
	STATUS current
	DESCRIPTION
        "
        Row definition for the pmopm8Almchannel71Port
        table
        "
	INDEX   { pmopm8Almchannel71PortIndex }
	::= { pmopm8Almchannel71PortTable 1 }


Pmopm8Almchannel71PortEntry ::=
	SEQUENCE {
	pmopm8Almchannel71PortIndex
		INTEGER,
	pmopm8AlmChannel71OosPortn
		EkiOnOff,
	pmopm8AlmChannel71PowerHighPortn
		EkiOnOff,
	pmopm8AlmChannel71PowerLowPortn
		EkiOnOff,
	pmopm8AlmChannel71BalancedPortn
		EkiOnOff,
	pmopm8AlmChannel71MismatchPortn
		EkiOnOff,
	pmopm8AlmChannel71AbsentPortn
		EkiOnOff
	}


pmopm8Almchannel71PortIndex OBJECT-TYPE
	SYNTAX  INTEGER(0..128)
	MAX-ACCESS  read-only
	STATUS current
	DESCRIPTION
        "
        Index definition for the pmopm8Almchannel71Port
        table
        "
	::= { pmopm8Almchannel71PortEntry 1 }


pmopm8AlmChannel71OosPortn OBJECT-TYPE
	SYNTAX  EkiOnOff
	MAX-ACCESS read-only
	STATUS current
	DESCRIPTION
        "
        Channel Out Of Service 71 :This
        OID indicates that the channel
         is out of service  <Help> This
        alarm indicates that the channel
        is in service <Condtype> CHANNEL71_OOS_1
        <Probcause> informationalStatus(1000)
        <Alarmtype> other (1) <Polarity>
        (2)
        "
	::= { pmopm8Almchannel71PortEntry 7 }


pmopm8AlmChannel71PowerHighPortn OBJECT-TYPE
	SYNTAX  EkiOnOff
	MAX-ACCESS read-only
	STATUS current
	DESCRIPTION
        "
        Channel Power High 71 :This OID
        indicates that the power of the
        channel is higher than the configured
        threshold<Help> This alarm indicates
        that the power of the channel is
        higher than the configured threshold
        <Condtype> CHANNEL71_POWER_HIGH_1
        <Probcause> degradedSignal (13)
        <Alarmtype> equipmentAlarm <Polarity>
        (2)
        "
	::= { pmopm8Almchannel71PortEntry 6 }


pmopm8AlmChannel71PowerLowPortn OBJECT-TYPE
	SYNTAX  EkiOnOff
	MAX-ACCESS read-only
	STATUS current
	DESCRIPTION
        "
        Channel Power Low 71 :This OID
        indicates that the power of the
        channel is lower than the configured
        threshold<Help> This alarm indicates
        that the power of the channel is
        lower than the configured threshold
        <Condtype> CHANNEL71_POWER_LOW_1
        <Probcause> degradedSignal (13)
        <Alarmtype> equipmentAlarm <Polarity>
        (2)
        "
	::= { pmopm8Almchannel71PortEntry 5 }


pmopm8AlmChannel71BalancedPortn OBJECT-TYPE
	SYNTAX  EkiOnOff
	MAX-ACCESS read-only
	STATUS current
	DESCRIPTION
        "
        Channel Balanced 71 :This OID
         indicates that an in service channel
        is balanced by the Ekinops auto
        turn up application<Help> This
         status indicates that an in service
        channel is balanced by the Ekinops
        auto turn up application <Condtype>
        CHANNEL71_BALANCED_1 <Probcause>
        informationalStatus(1000) <Alarmtype>
        other (1) <Polarity> (2)
        "
	::= { pmopm8Almchannel71PortEntry 4 }


pmopm8AlmChannel71MismatchPortn OBJECT-TYPE
	SYNTAX  EkiOnOff
	MAX-ACCESS read-only
	STATUS current
	DESCRIPTION
        "
        Channel Mismatch 71 :This OID
         indicates that an out of service
        channel is detected on the Optical
        Power Monitoring input<Help> This
        alarm indicates that an out of
         service channel is detected on
        the Optical Power Monitoring input
        <Condtype> CHANNEL71_MISMATCH_1
        <Probcause> unexpectedInformation
        (75) <Alarmtype> equipmentAlarm
        <Polarity> (2)
        "
	::= { pmopm8Almchannel71PortEntry 3 }


pmopm8AlmChannel71AbsentPortn OBJECT-TYPE
	SYNTAX  EkiOnOff
	MAX-ACCESS read-only
	STATUS current
	DESCRIPTION
        "
        Channel Absent 71 :This OID indicates
        that an in service channel is absent
        on the Optical Power Monitoring
        input<Help> This alarm indicates
        that an in service channel is absent
        on the Optical Power Monitoring
        input <Condtype> CHANNEL71_ABSENT_1
        <Probcause> informationMissing
         (65) <Alarmtype> equipmentAlarm
        (5) <Polarity> (2)
        "
	::= { pmopm8Almchannel71PortEntry 2 }


--- *********************************************************
---     TABLE for the pmopm8Almchannel72Port articles
--- *********************************************************

pmopm8Almchannel72PortTable OBJECT-TYPE
	SYNTAX  SEQUENCE OF Pmopm8Almchannel72PortEntry
	MAX-ACCESS not-accessible
	STATUS current
	DESCRIPTION
        "
        List of pmopm8Almchannel72Port
        Article
        "
	::= { pmopm8AlmClientCrit 584 }


pmopm8Almchannel72PortEntry OBJECT-TYPE
	SYNTAX Pmopm8Almchannel72PortEntry
	MAX-ACCESS not-accessible
	STATUS current
	DESCRIPTION
        "
        Row definition for the pmopm8Almchannel72Port
        table
        "
	INDEX   { pmopm8Almchannel72PortIndex }
	::= { pmopm8Almchannel72PortTable 1 }


Pmopm8Almchannel72PortEntry ::=
	SEQUENCE {
	pmopm8Almchannel72PortIndex
		INTEGER,
	pmopm8AlmChannel72OosPortn
		EkiOnOff,
	pmopm8AlmChannel72PowerHighPortn
		EkiOnOff,
	pmopm8AlmChannel72PowerLowPortn
		EkiOnOff,
	pmopm8AlmChannel72BalancedPortn
		EkiOnOff,
	pmopm8AlmChannel72MismatchPortn
		EkiOnOff,
	pmopm8AlmChannel72AbsentPortn
		EkiOnOff
	}


pmopm8Almchannel72PortIndex OBJECT-TYPE
	SYNTAX  INTEGER(0..128)
	MAX-ACCESS  read-only
	STATUS current
	DESCRIPTION
        "
        Index definition for the pmopm8Almchannel72Port
        table
        "
	::= { pmopm8Almchannel72PortEntry 1 }


pmopm8AlmChannel72OosPortn OBJECT-TYPE
	SYNTAX  EkiOnOff
	MAX-ACCESS read-only
	STATUS current
	DESCRIPTION
        "
        Channel Out Of Service 72 :This
        OID indicates that the channel
         is out of service  <Help> This
        alarm indicates that the channel
        is in service <Condtype> CHANNEL72_OOS_1
        <Probcause> informationalStatus(1000)
        <Alarmtype> other (1) <Polarity>
        (2)
        "
	::= { pmopm8Almchannel72PortEntry 7 }


pmopm8AlmChannel72PowerHighPortn OBJECT-TYPE
	SYNTAX  EkiOnOff
	MAX-ACCESS read-only
	STATUS current
	DESCRIPTION
        "
        Channel Power High 72 :This OID
        indicates that the power of the
        channel is higher than the configured
        threshold<Help> This alarm indicates
        that the power of the channel is
        higher than the configured threshold
        <Condtype> CHANNEL72_POWER_HIGH_1
        <Probcause> degradedSignal (13)
        <Alarmtype> equipmentAlarm <Polarity>
        (2)
        "
	::= { pmopm8Almchannel72PortEntry 6 }


pmopm8AlmChannel72PowerLowPortn OBJECT-TYPE
	SYNTAX  EkiOnOff
	MAX-ACCESS read-only
	STATUS current
	DESCRIPTION
        "
        Channel Power Low 72 :This OID
        indicates that the power of the
        channel is lower than the configured
        threshold<Help> This alarm indicates
        that the power of the channel is
        lower than the configured threshold
        <Condtype> CHANNEL72_POWER_LOW_1
        <Probcause> degradedSignal (13)
        <Alarmtype> equipmentAlarm <Polarity>
        (2)
        "
	::= { pmopm8Almchannel72PortEntry 5 }


pmopm8AlmChannel72BalancedPortn OBJECT-TYPE
	SYNTAX  EkiOnOff
	MAX-ACCESS read-only
	STATUS current
	DESCRIPTION
        "
        Channel Balanced 72 :This OID
         indicates that an in service channel
        is balanced by the Ekinops auto
        turn up application<Help> This
         status indicates that an in service
        channel is balanced by the Ekinops
        auto turn up application <Condtype>
        CHANNEL72_BALANCED_1 <Probcause>
        informationalStatus(1000) <Alarmtype>
        other (1) <Polarity> (2)
        "
	::= { pmopm8Almchannel72PortEntry 4 }


pmopm8AlmChannel72MismatchPortn OBJECT-TYPE
	SYNTAX  EkiOnOff
	MAX-ACCESS read-only
	STATUS current
	DESCRIPTION
        "
        Channel Mismatch 72 :This OID
         indicates that an out of service
        channel is detected on the Optical
        Power Monitoring input<Help> This
        alarm indicates that an out of
         service channel is detected on
        the Optical Power Monitoring input
        <Condtype> CHANNEL72_MISMATCH_1
        <Probcause> unexpectedInformation
        (75) <Alarmtype> equipmentAlarm
        <Polarity> (2)
        "
	::= { pmopm8Almchannel72PortEntry 3 }


pmopm8AlmChannel72AbsentPortn OBJECT-TYPE
	SYNTAX  EkiOnOff
	MAX-ACCESS read-only
	STATUS current
	DESCRIPTION
        "
        Channel Absent 72 :This OID indicates
        that an in service channel is absent
        on the Optical Power Monitoring
        input<Help> This alarm indicates
        that an in service channel is absent
        on the Optical Power Monitoring
        input <Condtype> CHANNEL72_ABSENT_1
        <Probcause> informationMissing
         (65) <Alarmtype> equipmentAlarm
        (5) <Polarity> (2)
        "
	::= { pmopm8Almchannel72PortEntry 2 }


--- *********************************************************
---     TABLE for the pmopm8Almchannel73Port articles
--- *********************************************************

pmopm8Almchannel73PortTable OBJECT-TYPE
	SYNTAX  SEQUENCE OF Pmopm8Almchannel73PortEntry
	MAX-ACCESS not-accessible
	STATUS current
	DESCRIPTION
        "
        List of pmopm8Almchannel73Port
        Article
        "
	::= { pmopm8AlmClientCrit 592 }


pmopm8Almchannel73PortEntry OBJECT-TYPE
	SYNTAX Pmopm8Almchannel73PortEntry
	MAX-ACCESS not-accessible
	STATUS current
	DESCRIPTION
        "
        Row definition for the pmopm8Almchannel73Port
        table
        "
	INDEX   { pmopm8Almchannel73PortIndex }
	::= { pmopm8Almchannel73PortTable 1 }


Pmopm8Almchannel73PortEntry ::=
	SEQUENCE {
	pmopm8Almchannel73PortIndex
		INTEGER,
	pmopm8AlmChannel73OosPortn
		EkiOnOff,
	pmopm8AlmChannel73PowerHighPortn
		EkiOnOff,
	pmopm8AlmChannel73PowerLowPortn
		EkiOnOff,
	pmopm8AlmChannel73BalancedPortn
		EkiOnOff,
	pmopm8AlmChannel73MismatchPortn
		EkiOnOff,
	pmopm8AlmChannel73AbsentPortn
		EkiOnOff
	}


pmopm8Almchannel73PortIndex OBJECT-TYPE
	SYNTAX  INTEGER(0..128)
	MAX-ACCESS  read-only
	STATUS current
	DESCRIPTION
        "
        Index definition for the pmopm8Almchannel73Port
        table
        "
	::= { pmopm8Almchannel73PortEntry 1 }


pmopm8AlmChannel73OosPortn OBJECT-TYPE
	SYNTAX  EkiOnOff
	MAX-ACCESS read-only
	STATUS current
	DESCRIPTION
        "
        Channel Out Of Service 73 :This
        OID indicates that the channel
         is out of service  <Help> This
        alarm indicates that the channel
        is in service <Condtype> CHANNEL73_OOS_1
        <Probcause> informationalStatus(1000)
        <Alarmtype> other (1) <Polarity>
        (2)
        "
	::= { pmopm8Almchannel73PortEntry 7 }


pmopm8AlmChannel73PowerHighPortn OBJECT-TYPE
	SYNTAX  EkiOnOff
	MAX-ACCESS read-only
	STATUS current
	DESCRIPTION
        "
        Channel Power High 73 :This OID
        indicates that the power of the
        channel is higher than the configured
        threshold<Help> This alarm indicates
        that the power of the channel is
        higher than the configured threshold
        <Condtype> CHANNEL73_POWER_HIGH_1
        <Probcause> degradedSignal (13)
        <Alarmtype> equipmentAlarm <Polarity>
        (2)
        "
	::= { pmopm8Almchannel73PortEntry 6 }


pmopm8AlmChannel73PowerLowPortn OBJECT-TYPE
	SYNTAX  EkiOnOff
	MAX-ACCESS read-only
	STATUS current
	DESCRIPTION
        "
        Channel Power Low 73 :This OID
        indicates that the power of the
        channel is lower than the configured
        threshold<Help> This alarm indicates
        that the power of the channel is
        lower than the configured threshold
        <Condtype> CHANNEL73_POWER_LOW_1
        <Probcause> degradedSignal (13)
        <Alarmtype> equipmentAlarm <Polarity>
        (2)
        "
	::= { pmopm8Almchannel73PortEntry 5 }


pmopm8AlmChannel73BalancedPortn OBJECT-TYPE
	SYNTAX  EkiOnOff
	MAX-ACCESS read-only
	STATUS current
	DESCRIPTION
        "
        Channel Balanced 73 :This OID
         indicates that an in service channel
        is balanced by the Ekinops auto
        turn up application<Help> This
         status indicates that an in service
        channel is balanced by the Ekinops
        auto turn up application <Condtype>
        CHANNEL73_BALANCED_1 <Probcause>
        informationalStatus(1000) <Alarmtype>
        other (1) <Polarity> (2)
        "
	::= { pmopm8Almchannel73PortEntry 4 }


pmopm8AlmChannel73MismatchPortn OBJECT-TYPE
	SYNTAX  EkiOnOff
	MAX-ACCESS read-only
	STATUS current
	DESCRIPTION
        "
        Channel Mismatch 73 :This OID
         indicates that an out of service
        channel is detected on the Optical
        Power Monitoring input<Help> This
        alarm indicates that an out of
         service channel is detected on
        the Optical Power Monitoring input
        <Condtype> CHANNEL73_MISMATCH_1
        <Probcause> unexpectedInformation
        (75) <Alarmtype> equipmentAlarm
        <Polarity> (2)
        "
	::= { pmopm8Almchannel73PortEntry 3 }


pmopm8AlmChannel73AbsentPortn OBJECT-TYPE
	SYNTAX  EkiOnOff
	MAX-ACCESS read-only
	STATUS current
	DESCRIPTION
        "
        Channel Absent 73 :This OID indicates
        that an in service channel is absent
        on the Optical Power Monitoring
        input<Help> This alarm indicates
        that an in service channel is absent
        on the Optical Power Monitoring
        input <Condtype> CHANNEL73_ABSENT_1
        <Probcause> informationMissing
         (65) <Alarmtype> equipmentAlarm
        (5) <Polarity> (2)
        "
	::= { pmopm8Almchannel73PortEntry 2 }


--- *********************************************************
---     TABLE for the pmopm8Almchannel74Port articles
--- *********************************************************

pmopm8Almchannel74PortTable OBJECT-TYPE
	SYNTAX  SEQUENCE OF Pmopm8Almchannel74PortEntry
	MAX-ACCESS not-accessible
	STATUS current
	DESCRIPTION
        "
        List of pmopm8Almchannel74Port
        Article
        "
	::= { pmopm8AlmClientCrit 600 }


pmopm8Almchannel74PortEntry OBJECT-TYPE
	SYNTAX Pmopm8Almchannel74PortEntry
	MAX-ACCESS not-accessible
	STATUS current
	DESCRIPTION
        "
        Row definition for the pmopm8Almchannel74Port
        table
        "
	INDEX   { pmopm8Almchannel74PortIndex }
	::= { pmopm8Almchannel74PortTable 1 }


Pmopm8Almchannel74PortEntry ::=
	SEQUENCE {
	pmopm8Almchannel74PortIndex
		INTEGER,
	pmopm8AlmChannel74OosPortn
		EkiOnOff,
	pmopm8AlmChannel74PowerHighPortn
		EkiOnOff,
	pmopm8AlmChannel74PowerLowPortn
		EkiOnOff,
	pmopm8AlmChannel74BalancedPortn
		EkiOnOff,
	pmopm8AlmChannel74MismatchPortn
		EkiOnOff,
	pmopm8AlmChannel74AbsentPortn
		EkiOnOff
	}


pmopm8Almchannel74PortIndex OBJECT-TYPE
	SYNTAX  INTEGER(0..128)
	MAX-ACCESS  read-only
	STATUS current
	DESCRIPTION
        "
        Index definition for the pmopm8Almchannel74Port
        table
        "
	::= { pmopm8Almchannel74PortEntry 1 }


pmopm8AlmChannel74OosPortn OBJECT-TYPE
	SYNTAX  EkiOnOff
	MAX-ACCESS read-only
	STATUS current
	DESCRIPTION
        "
        Channel Out Of Service 74 :This
        OID indicates that the channel
         is out of service  <Help> This
        alarm indicates that the channel
        is in service <Condtype> CHANNEL74_OOS_1
        <Probcause> informationalStatus(1000)
        <Alarmtype> other (1) <Polarity>
        (2)
        "
	::= { pmopm8Almchannel74PortEntry 7 }


pmopm8AlmChannel74PowerHighPortn OBJECT-TYPE
	SYNTAX  EkiOnOff
	MAX-ACCESS read-only
	STATUS current
	DESCRIPTION
        "
        Channel Power High 74 :This OID
        indicates that the power of the
        channel is higher than the configured
        threshold<Help> This alarm indicates
        that the power of the channel is
        higher than the configured threshold
        <Condtype> CHANNEL74_POWER_HIGH_1
        <Probcause> degradedSignal (13)
        <Alarmtype> equipmentAlarm <Polarity>
        (2)
        "
	::= { pmopm8Almchannel74PortEntry 6 }


pmopm8AlmChannel74PowerLowPortn OBJECT-TYPE
	SYNTAX  EkiOnOff
	MAX-ACCESS read-only
	STATUS current
	DESCRIPTION
        "
        Channel Power Low 74 :This OID
        indicates that the power of the
        channel is lower than the configured
        threshold<Help> This alarm indicates
        that the power of the channel is
        lower than the configured threshold
        <Condtype> CHANNEL74_POWER_LOW_1
        <Probcause> degradedSignal (13)
        <Alarmtype> equipmentAlarm <Polarity>
        (2)
        "
	::= { pmopm8Almchannel74PortEntry 5 }


pmopm8AlmChannel74BalancedPortn OBJECT-TYPE
	SYNTAX  EkiOnOff
	MAX-ACCESS read-only
	STATUS current
	DESCRIPTION
        "
        Channel Balanced 74 :This OID
         indicates that an in service channel
        is balanced by the Ekinops auto
        turn up application<Help> This
         status indicates that an in service
        channel is balanced by the Ekinops
        auto turn up application <Condtype>
        CHANNEL74_BALANCED_1 <Probcause>
        informationalStatus(1000) <Alarmtype>
        other (1) <Polarity> (2)
        "
	::= { pmopm8Almchannel74PortEntry 4 }


pmopm8AlmChannel74MismatchPortn OBJECT-TYPE
	SYNTAX  EkiOnOff
	MAX-ACCESS read-only
	STATUS current
	DESCRIPTION
        "
        Channel Mismatch 74 :This OID
         indicates that an out of service
        channel is detected on the Optical
        Power Monitoring input<Help> This
        alarm indicates that an out of
         service channel is detected on
        the Optical Power Monitoring input
        <Condtype> CHANNEL74_MISMATCH_1
        <Probcause> unexpectedInformation
        (75) <Alarmtype> equipmentAlarm
        <Polarity> (2)
        "
	::= { pmopm8Almchannel74PortEntry 3 }


pmopm8AlmChannel74AbsentPortn OBJECT-TYPE
	SYNTAX  EkiOnOff
	MAX-ACCESS read-only
	STATUS current
	DESCRIPTION
        "
        Channel Absent 74 :This OID indicates
        that an in service channel is absent
        on the Optical Power Monitoring
        input<Help> This alarm indicates
        that an in service channel is absent
        on the Optical Power Monitoring
        input <Condtype> CHANNEL74_ABSENT_1
        <Probcause> informationMissing
         (65) <Alarmtype> equipmentAlarm
        (5) <Polarity> (2)
        "
	::= { pmopm8Almchannel74PortEntry 2 }


--- *********************************************************
---     TABLE for the pmopm8Almchannel75Port articles
--- *********************************************************

pmopm8Almchannel75PortTable OBJECT-TYPE
	SYNTAX  SEQUENCE OF Pmopm8Almchannel75PortEntry
	MAX-ACCESS not-accessible
	STATUS current
	DESCRIPTION
        "
        List of pmopm8Almchannel75Port
        Article
        "
	::= { pmopm8AlmClientCrit 608 }


pmopm8Almchannel75PortEntry OBJECT-TYPE
	SYNTAX Pmopm8Almchannel75PortEntry
	MAX-ACCESS not-accessible
	STATUS current
	DESCRIPTION
        "
        Row definition for the pmopm8Almchannel75Port
        table
        "
	INDEX   { pmopm8Almchannel75PortIndex }
	::= { pmopm8Almchannel75PortTable 1 }


Pmopm8Almchannel75PortEntry ::=
	SEQUENCE {
	pmopm8Almchannel75PortIndex
		INTEGER,
	pmopm8AlmChannel75OosPortn
		EkiOnOff,
	pmopm8AlmChannel75PowerHighPortn
		EkiOnOff,
	pmopm8AlmChannel75PowerLowPortn
		EkiOnOff,
	pmopm8AlmChannel75BalancedPortn
		EkiOnOff,
	pmopm8AlmChannel75MismatchPortn
		EkiOnOff,
	pmopm8AlmChannel75AbsentPortn
		EkiOnOff
	}


pmopm8Almchannel75PortIndex OBJECT-TYPE
	SYNTAX  INTEGER(0..128)
	MAX-ACCESS  read-only
	STATUS current
	DESCRIPTION
        "
        Index definition for the pmopm8Almchannel75Port
        table
        "
	::= { pmopm8Almchannel75PortEntry 1 }


pmopm8AlmChannel75OosPortn OBJECT-TYPE
	SYNTAX  EkiOnOff
	MAX-ACCESS read-only
	STATUS current
	DESCRIPTION
        "
        Channel Out Of Service 75 :This
        OID indicates that the channel
         is out of service  <Help> This
        alarm indicates that the channel
        is in service <Condtype> CHANNEL75_OOS_1
        <Probcause> informationalStatus(1000)
        <Alarmtype> other (1) <Polarity>
        (2)
        "
	::= { pmopm8Almchannel75PortEntry 7 }


pmopm8AlmChannel75PowerHighPortn OBJECT-TYPE
	SYNTAX  EkiOnOff
	MAX-ACCESS read-only
	STATUS current
	DESCRIPTION
        "
        Channel Power High 75 :This OID
        indicates that the power of the
        channel is higher than the configured
        threshold<Help> This alarm indicates
        that the power of the channel is
        higher than the configured threshold
        <Condtype> CHANNEL75_POWER_HIGH_1
        <Probcause> degradedSignal (13)
        <Alarmtype> equipmentAlarm <Polarity>
        (2)
        "
	::= { pmopm8Almchannel75PortEntry 6 }


pmopm8AlmChannel75PowerLowPortn OBJECT-TYPE
	SYNTAX  EkiOnOff
	MAX-ACCESS read-only
	STATUS current
	DESCRIPTION
        "
        Channel Power Low 75 :This OID
        indicates that the power of the
        channel is lower than the configured
        threshold<Help> This alarm indicates
        that the power of the channel is
        lower than the configured threshold
        <Condtype> CHANNEL75_POWER_LOW_1
        <Probcause> degradedSignal (13)
        <Alarmtype> equipmentAlarm <Polarity>
        (2)
        "
	::= { pmopm8Almchannel75PortEntry 5 }


pmopm8AlmChannel75BalancedPortn OBJECT-TYPE
	SYNTAX  EkiOnOff
	MAX-ACCESS read-only
	STATUS current
	DESCRIPTION
        "
        Channel Balanced 75 :This OID
         indicates that an in service channel
        is balanced by the Ekinops auto
        turn up application<Help> This
         status indicates that an in service
        channel is balanced by the Ekinops
        auto turn up application <Condtype>
        CHANNEL75_BALANCED_1 <Probcause>
        informationalStatus(1000) <Alarmtype>
        other (1) <Polarity> (2)
        "
	::= { pmopm8Almchannel75PortEntry 4 }


pmopm8AlmChannel75MismatchPortn OBJECT-TYPE
	SYNTAX  EkiOnOff
	MAX-ACCESS read-only
	STATUS current
	DESCRIPTION
        "
        Channel Mismatch 75 :This OID
         indicates that an out of service
        channel is detected on the Optical
        Power Monitoring input<Help> This
        alarm indicates that an out of
         service channel is detected on
        the Optical Power Monitoring input
        <Condtype> CHANNEL75_MISMATCH_1
        <Probcause> unexpectedInformation
        (75) <Alarmtype> equipmentAlarm
        <Polarity> (2)
        "
	::= { pmopm8Almchannel75PortEntry 3 }


pmopm8AlmChannel75AbsentPortn OBJECT-TYPE
	SYNTAX  EkiOnOff
	MAX-ACCESS read-only
	STATUS current
	DESCRIPTION
        "
        Channel Absent 75 :This OID indicates
        that an in service channel is absent
        on the Optical Power Monitoring
        input<Help> This alarm indicates
        that an in service channel is absent
        on the Optical Power Monitoring
        input <Condtype> CHANNEL75_ABSENT_1
        <Probcause> informationMissing
         (65) <Alarmtype> equipmentAlarm
        (5) <Polarity> (2)
        "
	::= { pmopm8Almchannel75PortEntry 2 }


--- *********************************************************
---     TABLE for the pmopm8Almchannel76Port articles
--- *********************************************************

pmopm8Almchannel76PortTable OBJECT-TYPE
	SYNTAX  SEQUENCE OF Pmopm8Almchannel76PortEntry
	MAX-ACCESS not-accessible
	STATUS current
	DESCRIPTION
        "
        List of pmopm8Almchannel76Port
        Article
        "
	::= { pmopm8AlmClientCrit 616 }


pmopm8Almchannel76PortEntry OBJECT-TYPE
	SYNTAX Pmopm8Almchannel76PortEntry
	MAX-ACCESS not-accessible
	STATUS current
	DESCRIPTION
        "
        Row definition for the pmopm8Almchannel76Port
        table
        "
	INDEX   { pmopm8Almchannel76PortIndex }
	::= { pmopm8Almchannel76PortTable 1 }


Pmopm8Almchannel76PortEntry ::=
	SEQUENCE {
	pmopm8Almchannel76PortIndex
		INTEGER,
	pmopm8AlmChannel76OosPortn
		EkiOnOff,
	pmopm8AlmChannel76PowerHighPortn
		EkiOnOff,
	pmopm8AlmChannel76PowerLowPortn
		EkiOnOff,
	pmopm8AlmChannel76BalancedPortn
		EkiOnOff,
	pmopm8AlmChannel76MismatchPortn
		EkiOnOff,
	pmopm8AlmChannel76AbsentPortn
		EkiOnOff
	}


pmopm8Almchannel76PortIndex OBJECT-TYPE
	SYNTAX  INTEGER(0..128)
	MAX-ACCESS  read-only
	STATUS current
	DESCRIPTION
        "
        Index definition for the pmopm8Almchannel76Port
        table
        "
	::= { pmopm8Almchannel76PortEntry 1 }


pmopm8AlmChannel76OosPortn OBJECT-TYPE
	SYNTAX  EkiOnOff
	MAX-ACCESS read-only
	STATUS current
	DESCRIPTION
        "
        Channel Out Of Service 76 :This
        OID indicates that the channel
         is out of service  <Help> This
        alarm indicates that the channel
        is in service <Condtype> CHANNEL76_OOS_1
        <Probcause> informationalStatus(1000)
        <Alarmtype> other (1) <Polarity>
        (2)
        "
	::= { pmopm8Almchannel76PortEntry 7 }


pmopm8AlmChannel76PowerHighPortn OBJECT-TYPE
	SYNTAX  EkiOnOff
	MAX-ACCESS read-only
	STATUS current
	DESCRIPTION
        "
        Channel Power High 76 :This OID
        indicates that the power of the
        channel is higher than the configured
        threshold<Help> This alarm indicates
        that the power of the channel is
        higher than the configured threshold
        <Condtype> CHANNEL76_POWER_HIGH_1
        <Probcause> degradedSignal (13)
        <Alarmtype> equipmentAlarm <Polarity>
        (2)
        "
	::= { pmopm8Almchannel76PortEntry 6 }


pmopm8AlmChannel76PowerLowPortn OBJECT-TYPE
	SYNTAX  EkiOnOff
	MAX-ACCESS read-only
	STATUS current
	DESCRIPTION
        "
        Channel Power Low 76 :This OID
        indicates that the power of the
        channel is lower than the configured
        threshold<Help> This alarm indicates
        that the power of the channel is
        lower than the configured threshold
        <Condtype> CHANNEL76_POWER_LOW_1
        <Probcause> degradedSignal (13)
        <Alarmtype> equipmentAlarm <Polarity>
        (2)
        "
	::= { pmopm8Almchannel76PortEntry 5 }


pmopm8AlmChannel76BalancedPortn OBJECT-TYPE
	SYNTAX  EkiOnOff
	MAX-ACCESS read-only
	STATUS current
	DESCRIPTION
        "
        Channel Balanced 76 :This OID
         indicates that an in service channel
        is balanced by the Ekinops auto
        turn up application<Help> This
         status indicates that an in service
        channel is balanced by the Ekinops
        auto turn up application <Condtype>
        CHANNEL76_BALANCED_1 <Probcause>
        informationalStatus(1000) <Alarmtype>
        other (1) <Polarity> (2)
        "
	::= { pmopm8Almchannel76PortEntry 4 }


pmopm8AlmChannel76MismatchPortn OBJECT-TYPE
	SYNTAX  EkiOnOff
	MAX-ACCESS read-only
	STATUS current
	DESCRIPTION
        "
        Channel Mismatch 76 :This OID
         indicates that an out of service
        channel is detected on the Optical
        Power Monitoring input<Help> This
        alarm indicates that an out of
         service channel is detected on
        the Optical Power Monitoring input
        <Condtype> CHANNEL76_MISMATCH_1
        <Probcause> unexpectedInformation
        (75) <Alarmtype> equipmentAlarm
        <Polarity> (2)
        "
	::= { pmopm8Almchannel76PortEntry 3 }


pmopm8AlmChannel76AbsentPortn OBJECT-TYPE
	SYNTAX  EkiOnOff
	MAX-ACCESS read-only
	STATUS current
	DESCRIPTION
        "
        Channel Absent 76 :This OID indicates
        that an in service channel is absent
        on the Optical Power Monitoring
        input<Help> This alarm indicates
        that an in service channel is absent
        on the Optical Power Monitoring
        input <Condtype> CHANNEL76_ABSENT_1
        <Probcause> informationMissing
         (65) <Alarmtype> equipmentAlarm
        (5) <Polarity> (2)
        "
	::= { pmopm8Almchannel76PortEntry 2 }


--- *********************************************************
---     TABLE for the pmopm8Almchannel77Port articles
--- *********************************************************

pmopm8Almchannel77PortTable OBJECT-TYPE
	SYNTAX  SEQUENCE OF Pmopm8Almchannel77PortEntry
	MAX-ACCESS not-accessible
	STATUS current
	DESCRIPTION
        "
        List of pmopm8Almchannel77Port
        Article
        "
	::= { pmopm8AlmClientCrit 624 }


pmopm8Almchannel77PortEntry OBJECT-TYPE
	SYNTAX Pmopm8Almchannel77PortEntry
	MAX-ACCESS not-accessible
	STATUS current
	DESCRIPTION
        "
        Row definition for the pmopm8Almchannel77Port
        table
        "
	INDEX   { pmopm8Almchannel77PortIndex }
	::= { pmopm8Almchannel77PortTable 1 }


Pmopm8Almchannel77PortEntry ::=
	SEQUENCE {
	pmopm8Almchannel77PortIndex
		INTEGER,
	pmopm8AlmChannel77OosPortn
		EkiOnOff,
	pmopm8AlmChannel77PowerHighPortn
		EkiOnOff,
	pmopm8AlmChannel77PowerLowPortn
		EkiOnOff,
	pmopm8AlmChannel77BalancedPortn
		EkiOnOff,
	pmopm8AlmChannel77MismatchPortn
		EkiOnOff,
	pmopm8AlmChannel77AbsentPortn
		EkiOnOff
	}


pmopm8Almchannel77PortIndex OBJECT-TYPE
	SYNTAX  INTEGER(0..128)
	MAX-ACCESS  read-only
	STATUS current
	DESCRIPTION
        "
        Index definition for the pmopm8Almchannel77Port
        table
        "
	::= { pmopm8Almchannel77PortEntry 1 }


pmopm8AlmChannel77OosPortn OBJECT-TYPE
	SYNTAX  EkiOnOff
	MAX-ACCESS read-only
	STATUS current
	DESCRIPTION
        "
        Channel Out Of Service 77 :This
        OID indicates that the channel
         is out of service  <Help> This
        alarm indicates that the channel
        is in service <Condtype> CHANNEL77_OOS_1
        <Probcause> informationalStatus(1000)
        <Alarmtype> other (1) <Polarity>
        (2)
        "
	::= { pmopm8Almchannel77PortEntry 7 }


pmopm8AlmChannel77PowerHighPortn OBJECT-TYPE
	SYNTAX  EkiOnOff
	MAX-ACCESS read-only
	STATUS current
	DESCRIPTION
        "
        Channel Power High 77 :This OID
        indicates that the power of the
        channel is higher than the configured
        threshold<Help> This alarm indicates
        that the power of the channel is
        higher than the configured threshold
        <Condtype> CHANNEL77_POWER_HIGH_1
        <Probcause> degradedSignal (13)
        <Alarmtype> equipmentAlarm <Polarity>
        (2)
        "
	::= { pmopm8Almchannel77PortEntry 6 }


pmopm8AlmChannel77PowerLowPortn OBJECT-TYPE
	SYNTAX  EkiOnOff
	MAX-ACCESS read-only
	STATUS current
	DESCRIPTION
        "
        Channel Power Low 77 :This OID
        indicates that the power of the
        channel is lower than the configured
        threshold<Help> This alarm indicates
        that the power of the channel is
        lower than the configured threshold
        <Condtype> CHANNEL77_POWER_LOW_1
        <Probcause> degradedSignal (13)
        <Alarmtype> equipmentAlarm <Polarity>
        (2)
        "
	::= { pmopm8Almchannel77PortEntry 5 }


pmopm8AlmChannel77BalancedPortn OBJECT-TYPE
	SYNTAX  EkiOnOff
	MAX-ACCESS read-only
	STATUS current
	DESCRIPTION
        "
        Channel Balanced 77 :This OID
         indicates that an in service channel
        is balanced by the Ekinops auto
        turn up application<Help> This
         status indicates that an in service
        channel is balanced by the Ekinops
        auto turn up application <Condtype>
        CHANNEL77_BALANCED_1 <Probcause>
        informationalStatus(1000) <Alarmtype>
        other (1) <Polarity> (2)
        "
	::= { pmopm8Almchannel77PortEntry 4 }


pmopm8AlmChannel77MismatchPortn OBJECT-TYPE
	SYNTAX  EkiOnOff
	MAX-ACCESS read-only
	STATUS current
	DESCRIPTION
        "
        Channel Mismatch 77 :This OID
         indicates that an out of service
        channel is detected on the Optical
        Power Monitoring input<Help> This
        alarm indicates that an out of
         service channel is detected on
        the Optical Power Monitoring input
        <Condtype> CHANNEL77_MISMATCH_1
        <Probcause> unexpectedInformation
        (75) <Alarmtype> equipmentAlarm
        <Polarity> (2)
        "
	::= { pmopm8Almchannel77PortEntry 3 }


pmopm8AlmChannel77AbsentPortn OBJECT-TYPE
	SYNTAX  EkiOnOff
	MAX-ACCESS read-only
	STATUS current
	DESCRIPTION
        "
        Channel Absent 77 :This OID indicates
        that an in service channel is absent
        on the Optical Power Monitoring
        input<Help> This alarm indicates
        that an in service channel is absent
        on the Optical Power Monitoring
        input <Condtype> CHANNEL77_ABSENT_1
        <Probcause> informationMissing
         (65) <Alarmtype> equipmentAlarm
        (5) <Polarity> (2)
        "
	::= { pmopm8Almchannel77PortEntry 2 }


--- *********************************************************
---     TABLE for the pmopm8Almchannel78Port articles
--- *********************************************************

pmopm8Almchannel78PortTable OBJECT-TYPE
	SYNTAX  SEQUENCE OF Pmopm8Almchannel78PortEntry
	MAX-ACCESS not-accessible
	STATUS current
	DESCRIPTION
        "
        List of pmopm8Almchannel78Port
        Article
        "
	::= { pmopm8AlmClientCrit 632 }


pmopm8Almchannel78PortEntry OBJECT-TYPE
	SYNTAX Pmopm8Almchannel78PortEntry
	MAX-ACCESS not-accessible
	STATUS current
	DESCRIPTION
        "
        Row definition for the pmopm8Almchannel78Port
        table
        "
	INDEX   { pmopm8Almchannel78PortIndex }
	::= { pmopm8Almchannel78PortTable 1 }


Pmopm8Almchannel78PortEntry ::=
	SEQUENCE {
	pmopm8Almchannel78PortIndex
		INTEGER,
	pmopm8AlmChannel78OosPortn
		EkiOnOff,
	pmopm8AlmChannel78PowerHighPortn
		EkiOnOff,
	pmopm8AlmChannel78PowerLowPortn
		EkiOnOff,
	pmopm8AlmChannel78BalancedPortn
		EkiOnOff,
	pmopm8AlmChannel78MismatchPortn
		EkiOnOff,
	pmopm8AlmChannel78AbsentPortn
		EkiOnOff
	}


pmopm8Almchannel78PortIndex OBJECT-TYPE
	SYNTAX  INTEGER(0..128)
	MAX-ACCESS  read-only
	STATUS current
	DESCRIPTION
        "
        Index definition for the pmopm8Almchannel78Port
        table
        "
	::= { pmopm8Almchannel78PortEntry 1 }


pmopm8AlmChannel78OosPortn OBJECT-TYPE
	SYNTAX  EkiOnOff
	MAX-ACCESS read-only
	STATUS current
	DESCRIPTION
        "
        Channel Out Of Service 78 :This
        OID indicates that the channel
         is out of service  <Help> This
        alarm indicates that the channel
        is in service <Condtype> CHANNEL78_OOS_1
        <Probcause> informationalStatus(1000)
        <Alarmtype> other (1) <Polarity>
        (2)
        "
	::= { pmopm8Almchannel78PortEntry 7 }


pmopm8AlmChannel78PowerHighPortn OBJECT-TYPE
	SYNTAX  EkiOnOff
	MAX-ACCESS read-only
	STATUS current
	DESCRIPTION
        "
        Channel Power High 78 :This OID
        indicates that the power of the
        channel is higher than the configured
        threshold<Help> This alarm indicates
        that the power of the channel is
        higher than the configured threshold
        <Condtype> CHANNEL78_POWER_HIGH_1
        <Probcause> degradedSignal (13)
        <Alarmtype> equipmentAlarm <Polarity>
        (2)
        "
	::= { pmopm8Almchannel78PortEntry 6 }


pmopm8AlmChannel78PowerLowPortn OBJECT-TYPE
	SYNTAX  EkiOnOff
	MAX-ACCESS read-only
	STATUS current
	DESCRIPTION
        "
        Channel Power Low 78 :This OID
        indicates that the power of the
        channel is lower than the configured
        threshold<Help> This alarm indicates
        that the power of the channel is
        lower than the configured threshold
        <Condtype> CHANNEL78_POWER_LOW_1
        <Probcause> degradedSignal (13)
        <Alarmtype> equipmentAlarm <Polarity>
        (2)
        "
	::= { pmopm8Almchannel78PortEntry 5 }


pmopm8AlmChannel78BalancedPortn OBJECT-TYPE
	SYNTAX  EkiOnOff
	MAX-ACCESS read-only
	STATUS current
	DESCRIPTION
        "
        Channel Balanced 78 :This OID
         indicates that an in service channel
        is balanced by the Ekinops auto
        turn up application<Help> This
         status indicates that an in service
        channel is balanced by the Ekinops
        auto turn up application <Condtype>
        CHANNEL78_BALANCED_1 <Probcause>
        informationalStatus(1000) <Alarmtype>
        other (1) <Polarity> (2)
        "
	::= { pmopm8Almchannel78PortEntry 4 }


pmopm8AlmChannel78MismatchPortn OBJECT-TYPE
	SYNTAX  EkiOnOff
	MAX-ACCESS read-only
	STATUS current
	DESCRIPTION
        "
        Channel Mismatch 78 :This OID
         indicates that an out of service
        channel is detected on the Optical
        Power Monitoring input<Help> This
        alarm indicates that an out of
         service channel is detected on
        the Optical Power Monitoring input
        <Condtype> CHANNEL78_MISMATCH_1
        <Probcause> unexpectedInformation
        (75) <Alarmtype> equipmentAlarm
        <Polarity> (2)
        "
	::= { pmopm8Almchannel78PortEntry 3 }


pmopm8AlmChannel78AbsentPortn OBJECT-TYPE
	SYNTAX  EkiOnOff
	MAX-ACCESS read-only
	STATUS current
	DESCRIPTION
        "
        Channel Absent 78 :This OID indicates
        that an in service channel is absent
        on the Optical Power Monitoring
        input<Help> This alarm indicates
        that an in service channel is absent
        on the Optical Power Monitoring
        input <Condtype> CHANNEL78_ABSENT_1
        <Probcause> informationMissing
         (65) <Alarmtype> equipmentAlarm
        (5) <Polarity> (2)
        "
	::= { pmopm8Almchannel78PortEntry 2 }


--- *********************************************************
---     TABLE for the pmopm8Almchannel79Port articles
--- *********************************************************

pmopm8Almchannel79PortTable OBJECT-TYPE
	SYNTAX  SEQUENCE OF Pmopm8Almchannel79PortEntry
	MAX-ACCESS not-accessible
	STATUS current
	DESCRIPTION
        "
        List of pmopm8Almchannel79Port
        Article
        "
	::= { pmopm8AlmClientCrit 640 }


pmopm8Almchannel79PortEntry OBJECT-TYPE
	SYNTAX Pmopm8Almchannel79PortEntry
	MAX-ACCESS not-accessible
	STATUS current
	DESCRIPTION
        "
        Row definition for the pmopm8Almchannel79Port
        table
        "
	INDEX   { pmopm8Almchannel79PortIndex }
	::= { pmopm8Almchannel79PortTable 1 }


Pmopm8Almchannel79PortEntry ::=
	SEQUENCE {
	pmopm8Almchannel79PortIndex
		INTEGER,
	pmopm8AlmChannel79OosPortn
		EkiOnOff,
	pmopm8AlmChannel79PowerHighPortn
		EkiOnOff,
	pmopm8AlmChannel79PowerLowPortn
		EkiOnOff,
	pmopm8AlmChannel79BalancedPortn
		EkiOnOff,
	pmopm8AlmChannel79MismatchPortn
		EkiOnOff,
	pmopm8AlmChannel79AbsentPortn
		EkiOnOff
	}


pmopm8Almchannel79PortIndex OBJECT-TYPE
	SYNTAX  INTEGER(0..128)
	MAX-ACCESS  read-only
	STATUS current
	DESCRIPTION
        "
        Index definition for the pmopm8Almchannel79Port
        table
        "
	::= { pmopm8Almchannel79PortEntry 1 }


pmopm8AlmChannel79OosPortn OBJECT-TYPE
	SYNTAX  EkiOnOff
	MAX-ACCESS read-only
	STATUS current
	DESCRIPTION
        "
        Channel Out Of Service 79 :This
        OID indicates that the channel
         is out of service  <Help> This
        alarm indicates that the channel
        is in service <Condtype> CHANNEL79_OOS_1
        <Probcause> informationalStatus(1000)
        <Alarmtype> other (1) <Polarity>
        (2)
        "
	::= { pmopm8Almchannel79PortEntry 7 }


pmopm8AlmChannel79PowerHighPortn OBJECT-TYPE
	SYNTAX  EkiOnOff
	MAX-ACCESS read-only
	STATUS current
	DESCRIPTION
        "
        Channel Power High 79 :This OID
        indicates that the power of the
        channel is higher than the configured
        threshold<Help> This alarm indicates
        that the power of the channel is
        higher than the configured threshold
        <Condtype> CHANNEL79_POWER_HIGH_1
        <Probcause> degradedSignal (13)
        <Alarmtype> equipmentAlarm <Polarity>
        (2)
        "
	::= { pmopm8Almchannel79PortEntry 6 }


pmopm8AlmChannel79PowerLowPortn OBJECT-TYPE
	SYNTAX  EkiOnOff
	MAX-ACCESS read-only
	STATUS current
	DESCRIPTION
        "
        Channel Power Low 79 :This OID
        indicates that the power of the
        channel is lower than the configured
        threshold<Help> This alarm indicates
        that the power of the channel is
        lower than the configured threshold
        <Condtype> CHANNEL79_POWER_LOW_1
        <Probcause> degradedSignal (13)
        <Alarmtype> equipmentAlarm <Polarity>
        (2)
        "
	::= { pmopm8Almchannel79PortEntry 5 }


pmopm8AlmChannel79BalancedPortn OBJECT-TYPE
	SYNTAX  EkiOnOff
	MAX-ACCESS read-only
	STATUS current
	DESCRIPTION
        "
        Channel Balanced 79 :This OID
         indicates that an in service channel
        is balanced by the Ekinops auto
        turn up application<Help> This
         status indicates that an in service
        channel is balanced by the Ekinops
        auto turn up application <Condtype>
        CHANNEL79_BALANCED_1 <Probcause>
        informationalStatus(1000) <Alarmtype>
        other (1) <Polarity> (2)
        "
	::= { pmopm8Almchannel79PortEntry 4 }


pmopm8AlmChannel79MismatchPortn OBJECT-TYPE
	SYNTAX  EkiOnOff
	MAX-ACCESS read-only
	STATUS current
	DESCRIPTION
        "
        Channel Mismatch 79 :This OID
         indicates that an out of service
        channel is detected on the Optical
        Power Monitoring input<Help> This
        alarm indicates that an out of
         service channel is detected on
        the Optical Power Monitoring input
        <Condtype> CHANNEL79_MISMATCH_1
        <Probcause> unexpectedInformation
        (75) <Alarmtype> equipmentAlarm
        <Polarity> (2)
        "
	::= { pmopm8Almchannel79PortEntry 3 }


pmopm8AlmChannel79AbsentPortn OBJECT-TYPE
	SYNTAX  EkiOnOff
	MAX-ACCESS read-only
	STATUS current
	DESCRIPTION
        "
        Channel Absent 79 :This OID indicates
        that an in service channel is absent
        on the Optical Power Monitoring
        input<Help> This alarm indicates
        that an in service channel is absent
        on the Optical Power Monitoring
        input <Condtype> CHANNEL79_ABSENT_1
        <Probcause> informationMissing
         (65) <Alarmtype> equipmentAlarm
        (5) <Polarity> (2)
        "
	::= { pmopm8Almchannel79PortEntry 2 }


--- *********************************************************
---     TABLE for the pmopm8Almchannel80Port articles
--- *********************************************************

pmopm8Almchannel80PortTable OBJECT-TYPE
	SYNTAX  SEQUENCE OF Pmopm8Almchannel80PortEntry
	MAX-ACCESS not-accessible
	STATUS current
	DESCRIPTION
        "
        List of pmopm8Almchannel80Port
        Article
        "
	::= { pmopm8AlmClientCrit 648 }


pmopm8Almchannel80PortEntry OBJECT-TYPE
	SYNTAX Pmopm8Almchannel80PortEntry
	MAX-ACCESS not-accessible
	STATUS current
	DESCRIPTION
        "
        Row definition for the pmopm8Almchannel80Port
        table
        "
	INDEX   { pmopm8Almchannel80PortIndex }
	::= { pmopm8Almchannel80PortTable 1 }


Pmopm8Almchannel80PortEntry ::=
	SEQUENCE {
	pmopm8Almchannel80PortIndex
		INTEGER,
	pmopm8AlmChannel80OosPortn
		EkiOnOff,
	pmopm8AlmChannel80PowerHighPortn
		EkiOnOff,
	pmopm8AlmChannel80PowerLowPortn
		EkiOnOff,
	pmopm8AlmChannel80BalancedPortn
		EkiOnOff,
	pmopm8AlmChannel80MismatchPortn
		EkiOnOff,
	pmopm8AlmChannel80AbsentPortn
		EkiOnOff
	}


pmopm8Almchannel80PortIndex OBJECT-TYPE
	SYNTAX  INTEGER(0..128)
	MAX-ACCESS  read-only
	STATUS current
	DESCRIPTION
        "
        Index definition for the pmopm8Almchannel80Port
        table
        "
	::= { pmopm8Almchannel80PortEntry 1 }


pmopm8AlmChannel80OosPortn OBJECT-TYPE
	SYNTAX  EkiOnOff
	MAX-ACCESS read-only
	STATUS current
	DESCRIPTION
        "
        Channel Out Of Service 80 :This
        OID indicates that the channel
         is out of service  <Help> This
        alarm indicates that the channel
        is in service <Condtype> CHANNEL80_OOS_1
        <Probcause> informationalStatus(1000)
        <Alarmtype> other (1) <Polarity>
        (2)
        "
	::= { pmopm8Almchannel80PortEntry 7 }


pmopm8AlmChannel80PowerHighPortn OBJECT-TYPE
	SYNTAX  EkiOnOff
	MAX-ACCESS read-only
	STATUS current
	DESCRIPTION
        "
        Channel Power High 80 :This OID
        indicates that the power of the
        channel is higher than the configured
        threshold<Help> This alarm indicates
        that the power of the channel is
        higher than the configured threshold
        <Condtype> CHANNEL80_POWER_HIGH_1
        <Probcause> degradedSignal (13)
        <Alarmtype> equipmentAlarm <Polarity>
        (2)
        "
	::= { pmopm8Almchannel80PortEntry 6 }


pmopm8AlmChannel80PowerLowPortn OBJECT-TYPE
	SYNTAX  EkiOnOff
	MAX-ACCESS read-only
	STATUS current
	DESCRIPTION
        "
        Channel Power Low 80 :This OID
        indicates that the power of the
        channel is lower than the configured
        threshold<Help> This alarm indicates
        that the power of the channel is
        lower than the configured threshold
        <Condtype> CHANNEL80_POWER_LOW_1
        <Probcause> degradedSignal (13)
        <Alarmtype> equipmentAlarm <Polarity>
        (2)
        "
	::= { pmopm8Almchannel80PortEntry 5 }


pmopm8AlmChannel80BalancedPortn OBJECT-TYPE
	SYNTAX  EkiOnOff
	MAX-ACCESS read-only
	STATUS current
	DESCRIPTION
        "
        Channel Balanced 80 :This OID
         indicates that an in service channel
        is balanced by the Ekinops auto
        turn up application<Help> This
         status indicates that an in service
        channel is balanced by the Ekinops
        auto turn up application <Condtype>
        CHANNEL80_BALANCED_1 <Probcause>
        informationalStatus(1000) <Alarmtype>
        other (1) <Polarity> (2)
        "
	::= { pmopm8Almchannel80PortEntry 4 }


pmopm8AlmChannel80MismatchPortn OBJECT-TYPE
	SYNTAX  EkiOnOff
	MAX-ACCESS read-only
	STATUS current
	DESCRIPTION
        "
        Channel Mismatch 80 :This OID
         indicates that an out of service
        channel is detected on the Optical
        Power Monitoring input<Help> This
        alarm indicates that an out of
         service channel is detected on
        the Optical Power Monitoring input
        <Condtype> CHANNEL80_MISMATCH_1
        <Probcause> unexpectedInformation
        (75) <Alarmtype> equipmentAlarm
        <Polarity> (2)
        "
	::= { pmopm8Almchannel80PortEntry 3 }


pmopm8AlmChannel80AbsentPortn OBJECT-TYPE
	SYNTAX  EkiOnOff
	MAX-ACCESS read-only
	STATUS current
	DESCRIPTION
        "
        Channel Absent 80 :This OID indicates
        that an in service channel is absent
        on the Optical Power Monitoring
        input<Help> This alarm indicates
        that an in service channel is absent
        on the Optical Power Monitoring
        input <Condtype> CHANNEL80_ABSENT_1
        <Probcause> informationMissing
         (65) <Alarmtype> equipmentAlarm
        (5) <Polarity> (2)
        "
	::= { pmopm8Almchannel80PortEntry 2 }


--- *********************************************************
---     TABLE for the pmopm8Almchannel81Port articles
--- *********************************************************

pmopm8Almchannel81PortTable OBJECT-TYPE
	SYNTAX  SEQUENCE OF Pmopm8Almchannel81PortEntry
	MAX-ACCESS not-accessible
	STATUS current
	DESCRIPTION
        "
        List of pmopm8Almchannel81Port
        Article
        "
	::= { pmopm8AlmClientCrit 656 }


pmopm8Almchannel81PortEntry OBJECT-TYPE
	SYNTAX Pmopm8Almchannel81PortEntry
	MAX-ACCESS not-accessible
	STATUS current
	DESCRIPTION
        "
        Row definition for the pmopm8Almchannel81Port
        table
        "
	INDEX   { pmopm8Almchannel81PortIndex }
	::= { pmopm8Almchannel81PortTable 1 }


Pmopm8Almchannel81PortEntry ::=
	SEQUENCE {
	pmopm8Almchannel81PortIndex
		INTEGER,
	pmopm8AlmChannel81OosPortn
		EkiOnOff,
	pmopm8AlmChannel81PowerHighPortn
		EkiOnOff,
	pmopm8AlmChannel81PowerLowPortn
		EkiOnOff,
	pmopm8AlmChannel81BalancedPortn
		EkiOnOff,
	pmopm8AlmChannel81MismatchPortn
		EkiOnOff,
	pmopm8AlmChannel81AbsentPortn
		EkiOnOff
	}


pmopm8Almchannel81PortIndex OBJECT-TYPE
	SYNTAX  INTEGER(0..128)
	MAX-ACCESS  read-only
	STATUS current
	DESCRIPTION
        "
        Index definition for the pmopm8Almchannel81Port
        table
        "
	::= { pmopm8Almchannel81PortEntry 1 }


pmopm8AlmChannel81OosPortn OBJECT-TYPE
	SYNTAX  EkiOnOff
	MAX-ACCESS read-only
	STATUS current
	DESCRIPTION
        "
        Channel Out Of Service 81 :This
        OID indicates that the channel
         is out of service  <Help> This
        alarm indicates that the channel
        is in service <Condtype> CHANNEL81_OOS_1
        <Probcause> informationalStatus(1000)
        <Alarmtype> other (1) <Polarity>
        (2)
        "
	::= { pmopm8Almchannel81PortEntry 7 }


pmopm8AlmChannel81PowerHighPortn OBJECT-TYPE
	SYNTAX  EkiOnOff
	MAX-ACCESS read-only
	STATUS current
	DESCRIPTION
        "
        Channel Power High 81 :This OID
        indicates that the power of the
        channel is higher than the configured
        threshold<Help> This alarm indicates
        that the power of the channel is
        higher than the configured threshold
        <Condtype> CHANNEL81_POWER_HIGH_1
        <Probcause> degradedSignal (13)
        <Alarmtype> equipmentAlarm <Polarity>
        (2)
        "
	::= { pmopm8Almchannel81PortEntry 6 }


pmopm8AlmChannel81PowerLowPortn OBJECT-TYPE
	SYNTAX  EkiOnOff
	MAX-ACCESS read-only
	STATUS current
	DESCRIPTION
        "
        Channel Power Low 81 :This OID
        indicates that the power of the
        channel is lower than the configured
        threshold<Help> This alarm indicates
        that the power of the channel is
        lower than the configured threshold
        <Condtype> CHANNEL81_POWER_LOW_1
        <Probcause> degradedSignal (13)
        <Alarmtype> equipmentAlarm <Polarity>
        (2)
        "
	::= { pmopm8Almchannel81PortEntry 5 }


pmopm8AlmChannel81BalancedPortn OBJECT-TYPE
	SYNTAX  EkiOnOff
	MAX-ACCESS read-only
	STATUS current
	DESCRIPTION
        "
        Channel Balanced 81 :This OID
         indicates that an in service channel
        is balanced by the Ekinops auto
        turn up application<Help> This
         status indicates that an in service
        channel is balanced by the Ekinops
        auto turn up application <Condtype>
        CHANNEL81_BALANCED_1 <Probcause>
        informationalStatus(1000) <Alarmtype>
        other (1) <Polarity> (2)
        "
	::= { pmopm8Almchannel81PortEntry 4 }


pmopm8AlmChannel81MismatchPortn OBJECT-TYPE
	SYNTAX  EkiOnOff
	MAX-ACCESS read-only
	STATUS current
	DESCRIPTION
        "
        Channel Mismatch 81 :This OID
         indicates that an out of service
        channel is detected on the Optical
        Power Monitoring input<Help> This
        alarm indicates that an out of
         service channel is detected on
        the Optical Power Monitoring input
        <Condtype> CHANNEL81_MISMATCH_1
        <Probcause> unexpectedInformation
        (75) <Alarmtype> equipmentAlarm
        <Polarity> (2)
        "
	::= { pmopm8Almchannel81PortEntry 3 }


pmopm8AlmChannel81AbsentPortn OBJECT-TYPE
	SYNTAX  EkiOnOff
	MAX-ACCESS read-only
	STATUS current
	DESCRIPTION
        "
        Channel Absent 81 :This OID indicates
        that an in service channel is absent
        on the Optical Power Monitoring
        input<Help> This alarm indicates
        that an in service channel is absent
        on the Optical Power Monitoring
        input <Condtype> CHANNEL81_ABSENT_1
        <Probcause> informationMissing
         (65) <Alarmtype> equipmentAlarm
        (5) <Polarity> (2)
        "
	::= { pmopm8Almchannel81PortEntry 2 }


--- *********************************************************
---     TABLE for the pmopm8Almchannel82Port articles
--- *********************************************************

pmopm8Almchannel82PortTable OBJECT-TYPE
	SYNTAX  SEQUENCE OF Pmopm8Almchannel82PortEntry
	MAX-ACCESS not-accessible
	STATUS current
	DESCRIPTION
        "
        List of pmopm8Almchannel82Port
        Article
        "
	::= { pmopm8AlmClientCrit 664 }


pmopm8Almchannel82PortEntry OBJECT-TYPE
	SYNTAX Pmopm8Almchannel82PortEntry
	MAX-ACCESS not-accessible
	STATUS current
	DESCRIPTION
        "
        Row definition for the pmopm8Almchannel82Port
        table
        "
	INDEX   { pmopm8Almchannel82PortIndex }
	::= { pmopm8Almchannel82PortTable 1 }


Pmopm8Almchannel82PortEntry ::=
	SEQUENCE {
	pmopm8Almchannel82PortIndex
		INTEGER,
	pmopm8AlmChannel82OosPortn
		EkiOnOff,
	pmopm8AlmChannel82PowerHighPortn
		EkiOnOff,
	pmopm8AlmChannel82PowerLowPortn
		EkiOnOff,
	pmopm8AlmChannel82BalancedPortn
		EkiOnOff,
	pmopm8AlmChannel82MismatchPortn
		EkiOnOff,
	pmopm8AlmChannel82AbsentPortn
		EkiOnOff
	}


pmopm8Almchannel82PortIndex OBJECT-TYPE
	SYNTAX  INTEGER(0..128)
	MAX-ACCESS  read-only
	STATUS current
	DESCRIPTION
        "
        Index definition for the pmopm8Almchannel82Port
        table
        "
	::= { pmopm8Almchannel82PortEntry 1 }


pmopm8AlmChannel82OosPortn OBJECT-TYPE
	SYNTAX  EkiOnOff
	MAX-ACCESS read-only
	STATUS current
	DESCRIPTION
        "
        Channel Out Of Service 82 :This
        OID indicates that the channel
         is out of service  <Help> This
        alarm indicates that the channel
        is in service <Condtype> CHANNEL82_OOS_1
        <Probcause> informationalStatus(1000)
        <Alarmtype> other (1) <Polarity>
        (2)
        "
	::= { pmopm8Almchannel82PortEntry 7 }


pmopm8AlmChannel82PowerHighPortn OBJECT-TYPE
	SYNTAX  EkiOnOff
	MAX-ACCESS read-only
	STATUS current
	DESCRIPTION
        "
        Channel Power High 82 :This OID
        indicates that the power of the
        channel is higher than the configured
        threshold<Help> This alarm indicates
        that the power of the channel is
        higher than the configured threshold
        <Condtype> CHANNEL82_POWER_HIGH_1
        <Probcause> degradedSignal (13)
        <Alarmtype> equipmentAlarm <Polarity>
        (2)
        "
	::= { pmopm8Almchannel82PortEntry 6 }


pmopm8AlmChannel82PowerLowPortn OBJECT-TYPE
	SYNTAX  EkiOnOff
	MAX-ACCESS read-only
	STATUS current
	DESCRIPTION
        "
        Channel Power Low 82 :This OID
        indicates that the power of the
        channel is lower than the configured
        threshold<Help> This alarm indicates
        that the power of the channel is
        lower than the configured threshold
        <Condtype> CHANNEL82_POWER_LOW_1
        <Probcause> degradedSignal (13)
        <Alarmtype> equipmentAlarm <Polarity>
        (2)
        "
	::= { pmopm8Almchannel82PortEntry 5 }


pmopm8AlmChannel82BalancedPortn OBJECT-TYPE
	SYNTAX  EkiOnOff
	MAX-ACCESS read-only
	STATUS current
	DESCRIPTION
        "
        Channel Balanced 82 :This OID
         indicates that an in service channel
        is balanced by the Ekinops auto
        turn up application<Help> This
         status indicates that an in service
        channel is balanced by the Ekinops
        auto turn up application <Condtype>
        CHANNEL82_BALANCED_1 <Probcause>
        informationalStatus(1000) <Alarmtype>
        other (1) <Polarity> (2)
        "
	::= { pmopm8Almchannel82PortEntry 4 }


pmopm8AlmChannel82MismatchPortn OBJECT-TYPE
	SYNTAX  EkiOnOff
	MAX-ACCESS read-only
	STATUS current
	DESCRIPTION
        "
        Channel Mismatch 82 :This OID
         indicates that an out of service
        channel is detected on the Optical
        Power Monitoring input<Help> This
        alarm indicates that an out of
         service channel is detected on
        the Optical Power Monitoring input
        <Condtype> CHANNEL82_MISMATCH_1
        <Probcause> unexpectedInformation
        (75) <Alarmtype> equipmentAlarm
        <Polarity> (2)
        "
	::= { pmopm8Almchannel82PortEntry 3 }


pmopm8AlmChannel82AbsentPortn OBJECT-TYPE
	SYNTAX  EkiOnOff
	MAX-ACCESS read-only
	STATUS current
	DESCRIPTION
        "
        Channel Absent 82 :This OID indicates
        that an in service channel is absent
        on the Optical Power Monitoring
        input<Help> This alarm indicates
        that an in service channel is absent
        on the Optical Power Monitoring
        input <Condtype> CHANNEL82_ABSENT_1
        <Probcause> informationMissing
         (65) <Alarmtype> equipmentAlarm
        (5) <Polarity> (2)
        "
	::= { pmopm8Almchannel82PortEntry 2 }


--- *********************************************************
---     TABLE for the pmopm8Almchannel83Port articles
--- *********************************************************

pmopm8Almchannel83PortTable OBJECT-TYPE
	SYNTAX  SEQUENCE OF Pmopm8Almchannel83PortEntry
	MAX-ACCESS not-accessible
	STATUS current
	DESCRIPTION
        "
        List of pmopm8Almchannel83Port
        Article
        "
	::= { pmopm8AlmClientCrit 672 }


pmopm8Almchannel83PortEntry OBJECT-TYPE
	SYNTAX Pmopm8Almchannel83PortEntry
	MAX-ACCESS not-accessible
	STATUS current
	DESCRIPTION
        "
        Row definition for the pmopm8Almchannel83Port
        table
        "
	INDEX   { pmopm8Almchannel83PortIndex }
	::= { pmopm8Almchannel83PortTable 1 }


Pmopm8Almchannel83PortEntry ::=
	SEQUENCE {
	pmopm8Almchannel83PortIndex
		INTEGER,
	pmopm8AlmChannel83OosPortn
		EkiOnOff,
	pmopm8AlmChannel83PowerHighPortn
		EkiOnOff,
	pmopm8AlmChannel83PowerLowPortn
		EkiOnOff,
	pmopm8AlmChannel83BalancedPortn
		EkiOnOff,
	pmopm8AlmChannel83MismatchPortn
		EkiOnOff,
	pmopm8AlmChannel83AbsentPortn
		EkiOnOff
	}


pmopm8Almchannel83PortIndex OBJECT-TYPE
	SYNTAX  INTEGER(0..128)
	MAX-ACCESS  read-only
	STATUS current
	DESCRIPTION
        "
        Index definition for the pmopm8Almchannel83Port
        table
        "
	::= { pmopm8Almchannel83PortEntry 1 }


pmopm8AlmChannel83OosPortn OBJECT-TYPE
	SYNTAX  EkiOnOff
	MAX-ACCESS read-only
	STATUS current
	DESCRIPTION
        "
        Channel Out Of Service 83 :This
        OID indicates that the channel
         is out of service  <Help> This
        alarm indicates that the channel
        is in service <Condtype> CHANNEL83_OOS_1
        <Probcause> informationalStatus(1000)
        <Alarmtype> other (1) <Polarity>
        (2)
        "
	::= { pmopm8Almchannel83PortEntry 7 }


pmopm8AlmChannel83PowerHighPortn OBJECT-TYPE
	SYNTAX  EkiOnOff
	MAX-ACCESS read-only
	STATUS current
	DESCRIPTION
        "
        Channel Power High 83 :This OID
        indicates that the power of the
        channel is higher than the configured
        threshold<Help> This alarm indicates
        that the power of the channel is
        higher than the configured threshold
        <Condtype> CHANNEL83_POWER_HIGH_1
        <Probcause> degradedSignal (13)
        <Alarmtype> equipmentAlarm <Polarity>
        (2)
        "
	::= { pmopm8Almchannel83PortEntry 6 }


pmopm8AlmChannel83PowerLowPortn OBJECT-TYPE
	SYNTAX  EkiOnOff
	MAX-ACCESS read-only
	STATUS current
	DESCRIPTION
        "
        Channel Power Low 83 :This OID
        indicates that the power of the
        channel is lower than the configured
        threshold<Help> This alarm indicates
        that the power of the channel is
        lower than the configured threshold
        <Condtype> CHANNEL83_POWER_LOW_1
        <Probcause> degradedSignal (13)
        <Alarmtype> equipmentAlarm <Polarity>
        (2)
        "
	::= { pmopm8Almchannel83PortEntry 5 }


pmopm8AlmChannel83BalancedPortn OBJECT-TYPE
	SYNTAX  EkiOnOff
	MAX-ACCESS read-only
	STATUS current
	DESCRIPTION
        "
        Channel Balanced 83 :This OID
         indicates that an in service channel
        is balanced by the Ekinops auto
        turn up application<Help> This
         status indicates that an in service
        channel is balanced by the Ekinops
        auto turn up application <Condtype>
        CHANNEL83_BALANCED_1 <Probcause>
        informationalStatus(1000) <Alarmtype>
        other (1) <Polarity> (2)
        "
	::= { pmopm8Almchannel83PortEntry 4 }


pmopm8AlmChannel83MismatchPortn OBJECT-TYPE
	SYNTAX  EkiOnOff
	MAX-ACCESS read-only
	STATUS current
	DESCRIPTION
        "
        Channel Mismatch 83 :This OID
         indicates that an out of service
        channel is detected on the Optical
        Power Monitoring input<Help> This
        alarm indicates that an out of
         service channel is detected on
        the Optical Power Monitoring input
        <Condtype> CHANNEL83_MISMATCH_1
        <Probcause> unexpectedInformation
        (75) <Alarmtype> equipmentAlarm
        <Polarity> (2)
        "
	::= { pmopm8Almchannel83PortEntry 3 }


pmopm8AlmChannel83AbsentPortn OBJECT-TYPE
	SYNTAX  EkiOnOff
	MAX-ACCESS read-only
	STATUS current
	DESCRIPTION
        "
        Channel Absent 83 :This OID indicates
        that an in service channel is absent
        on the Optical Power Monitoring
        input<Help> This alarm indicates
        that an in service channel is absent
        on the Optical Power Monitoring
        input <Condtype> CHANNEL83_ABSENT_1
        <Probcause> informationMissing
         (65) <Alarmtype> equipmentAlarm
        (5) <Polarity> (2)
        "
	::= { pmopm8Almchannel83PortEntry 2 }


--- *********************************************************
---     TABLE for the pmopm8Almchannel84Port articles
--- *********************************************************

pmopm8Almchannel84PortTable OBJECT-TYPE
	SYNTAX  SEQUENCE OF Pmopm8Almchannel84PortEntry
	MAX-ACCESS not-accessible
	STATUS current
	DESCRIPTION
        "
        List of pmopm8Almchannel84Port
        Article
        "
	::= { pmopm8AlmClientCrit 680 }


pmopm8Almchannel84PortEntry OBJECT-TYPE
	SYNTAX Pmopm8Almchannel84PortEntry
	MAX-ACCESS not-accessible
	STATUS current
	DESCRIPTION
        "
        Row definition for the pmopm8Almchannel84Port
        table
        "
	INDEX   { pmopm8Almchannel84PortIndex }
	::= { pmopm8Almchannel84PortTable 1 }


Pmopm8Almchannel84PortEntry ::=
	SEQUENCE {
	pmopm8Almchannel84PortIndex
		INTEGER,
	pmopm8AlmChannel84OosPortn
		EkiOnOff,
	pmopm8AlmChannel84PowerHighPortn
		EkiOnOff,
	pmopm8AlmChannel84PowerLowPortn
		EkiOnOff,
	pmopm8AlmChannel84BalancedPortn
		EkiOnOff,
	pmopm8AlmChannel84MismatchPortn
		EkiOnOff,
	pmopm8AlmChannel84AbsentPortn
		EkiOnOff
	}


pmopm8Almchannel84PortIndex OBJECT-TYPE
	SYNTAX  INTEGER(0..128)
	MAX-ACCESS  read-only
	STATUS current
	DESCRIPTION
        "
        Index definition for the pmopm8Almchannel84Port
        table
        "
	::= { pmopm8Almchannel84PortEntry 1 }


pmopm8AlmChannel84OosPortn OBJECT-TYPE
	SYNTAX  EkiOnOff
	MAX-ACCESS read-only
	STATUS current
	DESCRIPTION
        "
        Channel Out Of Service 84 :This
        OID indicates that the channel
         is out of service  <Help> This
        alarm indicates that the channel
        is in service <Condtype> CHANNEL84_OOS_1
        <Probcause> informationalStatus(1000)
        <Alarmtype> other (1) <Polarity>
        (2)
        "
	::= { pmopm8Almchannel84PortEntry 7 }


pmopm8AlmChannel84PowerHighPortn OBJECT-TYPE
	SYNTAX  EkiOnOff
	MAX-ACCESS read-only
	STATUS current
	DESCRIPTION
        "
        Channel Power High 84 :This OID
        indicates that the power of the
        channel is higher than the configured
        threshold<Help> This alarm indicates
        that the power of the channel is
        higher than the configured threshold
        <Condtype> CHANNEL84_POWER_HIGH_1
        <Probcause> degradedSignal (13)
        <Alarmtype> equipmentAlarm <Polarity>
        (2)
        "
	::= { pmopm8Almchannel84PortEntry 6 }


pmopm8AlmChannel84PowerLowPortn OBJECT-TYPE
	SYNTAX  EkiOnOff
	MAX-ACCESS read-only
	STATUS current
	DESCRIPTION
        "
        Channel Power Low 84 :This OID
        indicates that the power of the
        channel is lower than the configured
        threshold<Help> This alarm indicates
        that the power of the channel is
        lower than the configured threshold
        <Condtype> CHANNEL84_POWER_LOW_1
        <Probcause> degradedSignal (13)
        <Alarmtype> equipmentAlarm <Polarity>
        (2)
        "
	::= { pmopm8Almchannel84PortEntry 5 }


pmopm8AlmChannel84BalancedPortn OBJECT-TYPE
	SYNTAX  EkiOnOff
	MAX-ACCESS read-only
	STATUS current
	DESCRIPTION
        "
        Channel Balanced 84 :This OID
         indicates that an in service channel
        is balanced by the Ekinops auto
        turn up application<Help> This
         status indicates that an in service
        channel is balanced by the Ekinops
        auto turn up application <Condtype>
        CHANNEL84_BALANCED_1 <Probcause>
        informationalStatus(1000) <Alarmtype>
        other (1) <Polarity> (2)
        "
	::= { pmopm8Almchannel84PortEntry 4 }


pmopm8AlmChannel84MismatchPortn OBJECT-TYPE
	SYNTAX  EkiOnOff
	MAX-ACCESS read-only
	STATUS current
	DESCRIPTION
        "
        Channel Mismatch 84 :This OID
         indicates that an out of service
        channel is detected on the Optical
        Power Monitoring input<Help> This
        alarm indicates that an out of
         service channel is detected on
        the Optical Power Monitoring input
        <Condtype> CHANNEL84_MISMATCH_1
        <Probcause> unexpectedInformation
        (75) <Alarmtype> equipmentAlarm
        <Polarity> (2)
        "
	::= { pmopm8Almchannel84PortEntry 3 }


pmopm8AlmChannel84AbsentPortn OBJECT-TYPE
	SYNTAX  EkiOnOff
	MAX-ACCESS read-only
	STATUS current
	DESCRIPTION
        "
        Channel Absent 84 :This OID indicates
        that an in service channel is absent
        on the Optical Power Monitoring
        input<Help> This alarm indicates
        that an in service channel is absent
        on the Optical Power Monitoring
        input <Condtype> CHANNEL84_ABSENT_1
        <Probcause> informationMissing
         (65) <Alarmtype> equipmentAlarm
        (5) <Polarity> (2)
        "
	::= { pmopm8Almchannel84PortEntry 2 }


--- *********************************************************
---     TABLE for the pmopm8Almchannel85Port articles
--- *********************************************************

pmopm8Almchannel85PortTable OBJECT-TYPE
	SYNTAX  SEQUENCE OF Pmopm8Almchannel85PortEntry
	MAX-ACCESS not-accessible
	STATUS current
	DESCRIPTION
        "
        List of pmopm8Almchannel85Port
        Article
        "
	::= { pmopm8AlmClientCrit 688 }


pmopm8Almchannel85PortEntry OBJECT-TYPE
	SYNTAX Pmopm8Almchannel85PortEntry
	MAX-ACCESS not-accessible
	STATUS current
	DESCRIPTION
        "
        Row definition for the pmopm8Almchannel85Port
        table
        "
	INDEX   { pmopm8Almchannel85PortIndex }
	::= { pmopm8Almchannel85PortTable 1 }


Pmopm8Almchannel85PortEntry ::=
	SEQUENCE {
	pmopm8Almchannel85PortIndex
		INTEGER,
	pmopm8AlmChannel85OosPortn
		EkiOnOff,
	pmopm8AlmChannel85PowerHighPortn
		EkiOnOff,
	pmopm8AlmChannel85PowerLowPortn
		EkiOnOff,
	pmopm8AlmChannel85BalancedPortn
		EkiOnOff,
	pmopm8AlmChannel85MismatchPortn
		EkiOnOff,
	pmopm8AlmChannel85AbsentPortn
		EkiOnOff
	}


pmopm8Almchannel85PortIndex OBJECT-TYPE
	SYNTAX  INTEGER(0..128)
	MAX-ACCESS  read-only
	STATUS current
	DESCRIPTION
        "
        Index definition for the pmopm8Almchannel85Port
        table
        "
	::= { pmopm8Almchannel85PortEntry 1 }


pmopm8AlmChannel85OosPortn OBJECT-TYPE
	SYNTAX  EkiOnOff
	MAX-ACCESS read-only
	STATUS current
	DESCRIPTION
        "
        Channel Out Of Service 85 :This
        OID indicates that the channel
         is out of service  <Help> This
        alarm indicates that the channel
        is in service <Condtype> CHANNEL85_OOS_1
        <Probcause> informationalStatus(1000)
        <Alarmtype> other (1) <Polarity>
        (2)
        "
	::= { pmopm8Almchannel85PortEntry 7 }


pmopm8AlmChannel85PowerHighPortn OBJECT-TYPE
	SYNTAX  EkiOnOff
	MAX-ACCESS read-only
	STATUS current
	DESCRIPTION
        "
        Channel Power High 85 :This OID
        indicates that the power of the
        channel is higher than the configured
        threshold<Help> This alarm indicates
        that the power of the channel is
        higher than the configured threshold
        <Condtype> CHANNEL85_POWER_HIGH_1
        <Probcause> degradedSignal (13)
        <Alarmtype> equipmentAlarm <Polarity>
        (2)
        "
	::= { pmopm8Almchannel85PortEntry 6 }


pmopm8AlmChannel85PowerLowPortn OBJECT-TYPE
	SYNTAX  EkiOnOff
	MAX-ACCESS read-only
	STATUS current
	DESCRIPTION
        "
        Channel Power Low 85 :This OID
        indicates that the power of the
        channel is lower than the configured
        threshold<Help> This alarm indicates
        that the power of the channel is
        lower than the configured threshold
        <Condtype> CHANNEL85_POWER_LOW_1
        <Probcause> degradedSignal (13)
        <Alarmtype> equipmentAlarm <Polarity>
        (2)
        "
	::= { pmopm8Almchannel85PortEntry 5 }


pmopm8AlmChannel85BalancedPortn OBJECT-TYPE
	SYNTAX  EkiOnOff
	MAX-ACCESS read-only
	STATUS current
	DESCRIPTION
        "
        Channel Balanced 85 :This OID
         indicates that an in service channel
        is balanced by the Ekinops auto
        turn up application<Help> This
         status indicates that an in service
        channel is balanced by the Ekinops
        auto turn up application <Condtype>
        CHANNEL85_BALANCED_1 <Probcause>
        informationalStatus(1000) <Alarmtype>
        other (1) <Polarity> (2)
        "
	::= { pmopm8Almchannel85PortEntry 4 }


pmopm8AlmChannel85MismatchPortn OBJECT-TYPE
	SYNTAX  EkiOnOff
	MAX-ACCESS read-only
	STATUS current
	DESCRIPTION
        "
        Channel Mismatch 85 :This OID
         indicates that an out of service
        channel is detected on the Optical
        Power Monitoring input<Help> This
        alarm indicates that an out of
         service channel is detected on
        the Optical Power Monitoring input
        <Condtype> CHANNEL85_MISMATCH_1
        <Probcause> unexpectedInformation
        (75) <Alarmtype> equipmentAlarm
        <Polarity> (2)
        "
	::= { pmopm8Almchannel85PortEntry 3 }


pmopm8AlmChannel85AbsentPortn OBJECT-TYPE
	SYNTAX  EkiOnOff
	MAX-ACCESS read-only
	STATUS current
	DESCRIPTION
        "
        Channel Absent 85 :This OID indicates
        that an in service channel is absent
        on the Optical Power Monitoring
        input<Help> This alarm indicates
        that an in service channel is absent
        on the Optical Power Monitoring
        input <Condtype> CHANNEL85_ABSENT_1
        <Probcause> informationMissing
         (65) <Alarmtype> equipmentAlarm
        (5) <Polarity> (2)
        "
	::= { pmopm8Almchannel85PortEntry 2 }


--- *********************************************************
---     TABLE for the pmopm8Almchannel86Port articles
--- *********************************************************

pmopm8Almchannel86PortTable OBJECT-TYPE
	SYNTAX  SEQUENCE OF Pmopm8Almchannel86PortEntry
	MAX-ACCESS not-accessible
	STATUS current
	DESCRIPTION
        "
        List of pmopm8Almchannel86Port
        Article
        "
	::= { pmopm8AlmClientCrit 696 }


pmopm8Almchannel86PortEntry OBJECT-TYPE
	SYNTAX Pmopm8Almchannel86PortEntry
	MAX-ACCESS not-accessible
	STATUS current
	DESCRIPTION
        "
        Row definition for the pmopm8Almchannel86Port
        table
        "
	INDEX   { pmopm8Almchannel86PortIndex }
	::= { pmopm8Almchannel86PortTable 1 }


Pmopm8Almchannel86PortEntry ::=
	SEQUENCE {
	pmopm8Almchannel86PortIndex
		INTEGER,
	pmopm8AlmChannel86OosPortn
		EkiOnOff,
	pmopm8AlmChannel86PowerHighPortn
		EkiOnOff,
	pmopm8AlmChannel86PowerLowPortn
		EkiOnOff,
	pmopm8AlmChannel86BalancedPortn
		EkiOnOff,
	pmopm8AlmChannel86MismatchPortn
		EkiOnOff,
	pmopm8AlmChannel86AbsentPortn
		EkiOnOff
	}


pmopm8Almchannel86PortIndex OBJECT-TYPE
	SYNTAX  INTEGER(0..128)
	MAX-ACCESS  read-only
	STATUS current
	DESCRIPTION
        "
        Index definition for the pmopm8Almchannel86Port
        table
        "
	::= { pmopm8Almchannel86PortEntry 1 }


pmopm8AlmChannel86OosPortn OBJECT-TYPE
	SYNTAX  EkiOnOff
	MAX-ACCESS read-only
	STATUS current
	DESCRIPTION
        "
        Channel Out Of Service 86 :This
        OID indicates that the channel
         is out of service  <Help> This
        alarm indicates that the channel
        is in service <Condtype> CHANNEL86_OOS_1
        <Probcause> informationalStatus(1000)
        <Alarmtype> other (1) <Polarity>
        (2)
        "
	::= { pmopm8Almchannel86PortEntry 7 }


pmopm8AlmChannel86PowerHighPortn OBJECT-TYPE
	SYNTAX  EkiOnOff
	MAX-ACCESS read-only
	STATUS current
	DESCRIPTION
        "
        Channel Power High 86 :This OID
        indicates that the power of the
        channel is higher than the configured
        threshold<Help> This alarm indicates
        that the power of the channel is
        higher than the configured threshold
        <Condtype> CHANNEL86_POWER_HIGH_1
        <Probcause> degradedSignal (13)
        <Alarmtype> equipmentAlarm <Polarity>
        (2)
        "
	::= { pmopm8Almchannel86PortEntry 6 }


pmopm8AlmChannel86PowerLowPortn OBJECT-TYPE
	SYNTAX  EkiOnOff
	MAX-ACCESS read-only
	STATUS current
	DESCRIPTION
        "
        Channel Power Low 86 :This OID
        indicates that the power of the
        channel is lower than the configured
        threshold<Help> This alarm indicates
        that the power of the channel is
        lower than the configured threshold
        <Condtype> CHANNEL86_POWER_LOW_1
        <Probcause> degradedSignal (13)
        <Alarmtype> equipmentAlarm <Polarity>
        (2)
        "
	::= { pmopm8Almchannel86PortEntry 5 }


pmopm8AlmChannel86BalancedPortn OBJECT-TYPE
	SYNTAX  EkiOnOff
	MAX-ACCESS read-only
	STATUS current
	DESCRIPTION
        "
        Channel Balanced 86 :This OID
         indicates that an in service channel
        is balanced by the Ekinops auto
        turn up application<Help> This
         status indicates that an in service
        channel is balanced by the Ekinops
        auto turn up application <Condtype>
        CHANNEL86_BALANCED_1 <Probcause>
        informationalStatus(1000) <Alarmtype>
        other (1) <Polarity> (2)
        "
	::= { pmopm8Almchannel86PortEntry 4 }


pmopm8AlmChannel86MismatchPortn OBJECT-TYPE
	SYNTAX  EkiOnOff
	MAX-ACCESS read-only
	STATUS current
	DESCRIPTION
        "
        Channel Mismatch 86 :This OID
         indicates that an out of service
        channel is detected on the Optical
        Power Monitoring input<Help> This
        alarm indicates that an out of
         service channel is detected on
        the Optical Power Monitoring input
        <Condtype> CHANNEL86_MISMATCH_1
        <Probcause> unexpectedInformation
        (75) <Alarmtype> equipmentAlarm
        <Polarity> (2)
        "
	::= { pmopm8Almchannel86PortEntry 3 }


pmopm8AlmChannel86AbsentPortn OBJECT-TYPE
	SYNTAX  EkiOnOff
	MAX-ACCESS read-only
	STATUS current
	DESCRIPTION
        "
        Channel Absent 86 :This OID indicates
        that an in service channel is absent
        on the Optical Power Monitoring
        input<Help> This alarm indicates
        that an in service channel is absent
        on the Optical Power Monitoring
        input <Condtype> CHANNEL86_ABSENT_1
        <Probcause> informationMissing
         (65) <Alarmtype> equipmentAlarm
        (5) <Polarity> (2)
        "
	::= { pmopm8Almchannel86PortEntry 2 }


--- *********************************************************
---     TABLE for the pmopm8Almchannel87Port articles
--- *********************************************************

pmopm8Almchannel87PortTable OBJECT-TYPE
	SYNTAX  SEQUENCE OF Pmopm8Almchannel87PortEntry
	MAX-ACCESS not-accessible
	STATUS current
	DESCRIPTION
        "
        List of pmopm8Almchannel87Port
        Article
        "
	::= { pmopm8AlmClientCrit 704 }


pmopm8Almchannel87PortEntry OBJECT-TYPE
	SYNTAX Pmopm8Almchannel87PortEntry
	MAX-ACCESS not-accessible
	STATUS current
	DESCRIPTION
        "
        Row definition for the pmopm8Almchannel87Port
        table
        "
	INDEX   { pmopm8Almchannel87PortIndex }
	::= { pmopm8Almchannel87PortTable 1 }


Pmopm8Almchannel87PortEntry ::=
	SEQUENCE {
	pmopm8Almchannel87PortIndex
		INTEGER,
	pmopm8AlmChannel87OosPortn
		EkiOnOff,
	pmopm8AlmChannel87PowerHighPortn
		EkiOnOff,
	pmopm8AlmChannel87PowerLowPortn
		EkiOnOff,
	pmopm8AlmChannel87BalancedPortn
		EkiOnOff,
	pmopm8AlmChannel87MismatchPortn
		EkiOnOff,
	pmopm8AlmChannel87AbsentPortn
		EkiOnOff
	}


pmopm8Almchannel87PortIndex OBJECT-TYPE
	SYNTAX  INTEGER(0..128)
	MAX-ACCESS  read-only
	STATUS current
	DESCRIPTION
        "
        Index definition for the pmopm8Almchannel87Port
        table
        "
	::= { pmopm8Almchannel87PortEntry 1 }


pmopm8AlmChannel87OosPortn OBJECT-TYPE
	SYNTAX  EkiOnOff
	MAX-ACCESS read-only
	STATUS current
	DESCRIPTION
        "
        Channel Out Of Service 87 :This
        OID indicates that the channel
         is out of service  <Help> This
        alarm indicates that the channel
        is in service <Condtype> CHANNEL87_OOS_1
        <Probcause> informationalStatus(1000)
        <Alarmtype> other (1) <Polarity>
        (2)
        "
	::= { pmopm8Almchannel87PortEntry 7 }


pmopm8AlmChannel87PowerHighPortn OBJECT-TYPE
	SYNTAX  EkiOnOff
	MAX-ACCESS read-only
	STATUS current
	DESCRIPTION
        "
        Channel Power High 87 :This OID
        indicates that the power of the
        channel is higher than the configured
        threshold<Help> This alarm indicates
        that the power of the channel is
        higher than the configured threshold
        <Condtype> CHANNEL87_POWER_HIGH_1
        <Probcause> degradedSignal (13)
        <Alarmtype> equipmentAlarm <Polarity>
        (2)
        "
	::= { pmopm8Almchannel87PortEntry 6 }


pmopm8AlmChannel87PowerLowPortn OBJECT-TYPE
	SYNTAX  EkiOnOff
	MAX-ACCESS read-only
	STATUS current
	DESCRIPTION
        "
        Channel Power Low 87 :This OID
        indicates that the power of the
        channel is lower than the configured
        threshold<Help> This alarm indicates
        that the power of the channel is
        lower than the configured threshold
        <Condtype> CHANNEL87_POWER_LOW_1
        <Probcause> degradedSignal (13)
        <Alarmtype> equipmentAlarm <Polarity>
        (2)
        "
	::= { pmopm8Almchannel87PortEntry 5 }


pmopm8AlmChannel87BalancedPortn OBJECT-TYPE
	SYNTAX  EkiOnOff
	MAX-ACCESS read-only
	STATUS current
	DESCRIPTION
        "
        Channel Balanced 87 :This OID
         indicates that an in service channel
        is balanced by the Ekinops auto
        turn up application<Help> This
         status indicates that an in service
        channel is balanced by the Ekinops
        auto turn up application <Condtype>
        CHANNEL87_BALANCED_1 <Probcause>
        informationalStatus(1000) <Alarmtype>
        other (1) <Polarity> (2)
        "
	::= { pmopm8Almchannel87PortEntry 4 }


pmopm8AlmChannel87MismatchPortn OBJECT-TYPE
	SYNTAX  EkiOnOff
	MAX-ACCESS read-only
	STATUS current
	DESCRIPTION
        "
        Channel Mismatch 87 :This OID
         indicates that an out of service
        channel is detected on the Optical
        Power Monitoring input<Help> This
        alarm indicates that an out of
         service channel is detected on
        the Optical Power Monitoring input
        <Condtype> CHANNEL87_MISMATCH_1
        <Probcause> unexpectedInformation
        (75) <Alarmtype> equipmentAlarm
        <Polarity> (2)
        "
	::= { pmopm8Almchannel87PortEntry 3 }


pmopm8AlmChannel87AbsentPortn OBJECT-TYPE
	SYNTAX  EkiOnOff
	MAX-ACCESS read-only
	STATUS current
	DESCRIPTION
        "
        Channel Absent 87 :This OID indicates
        that an in service channel is absent
        on the Optical Power Monitoring
        input<Help> This alarm indicates
        that an in service channel is absent
        on the Optical Power Monitoring
        input <Condtype> CHANNEL87_ABSENT_1
        <Probcause> informationMissing
         (65) <Alarmtype> equipmentAlarm
        (5) <Polarity> (2)
        "
	::= { pmopm8Almchannel87PortEntry 2 }


--- *********************************************************
---     TABLE for the pmopm8Almchannel88Port articles
--- *********************************************************

pmopm8Almchannel88PortTable OBJECT-TYPE
	SYNTAX  SEQUENCE OF Pmopm8Almchannel88PortEntry
	MAX-ACCESS not-accessible
	STATUS current
	DESCRIPTION
        "
        List of pmopm8Almchannel88Port
        Article
        "
	::= { pmopm8AlmClientCrit 712 }


pmopm8Almchannel88PortEntry OBJECT-TYPE
	SYNTAX Pmopm8Almchannel88PortEntry
	MAX-ACCESS not-accessible
	STATUS current
	DESCRIPTION
        "
        Row definition for the pmopm8Almchannel88Port
        table
        "
	INDEX   { pmopm8Almchannel88PortIndex }
	::= { pmopm8Almchannel88PortTable 1 }


Pmopm8Almchannel88PortEntry ::=
	SEQUENCE {
	pmopm8Almchannel88PortIndex
		INTEGER,
	pmopm8AlmChannel88OosPortn
		EkiOnOff,
	pmopm8AlmChannel88PowerHighPortn
		EkiOnOff,
	pmopm8AlmChannel88PowerLowPortn
		EkiOnOff,
	pmopm8AlmChannel88BalancedPortn
		EkiOnOff,
	pmopm8AlmChannel88MismatchPortn
		EkiOnOff,
	pmopm8AlmChannel88AbsentPortn
		EkiOnOff
	}


pmopm8Almchannel88PortIndex OBJECT-TYPE
	SYNTAX  INTEGER(0..128)
	MAX-ACCESS  read-only
	STATUS current
	DESCRIPTION
        "
        Index definition for the pmopm8Almchannel88Port
        table
        "
	::= { pmopm8Almchannel88PortEntry 1 }


pmopm8AlmChannel88OosPortn OBJECT-TYPE
	SYNTAX  EkiOnOff
	MAX-ACCESS read-only
	STATUS current
	DESCRIPTION
        "
        Channel Out Of Service 88 :This
        OID indicates that the channel
         is out of service  <Help> This
        alarm indicates that the channel
        is in service <Condtype> CHANNEL88_OOS_1
        <Probcause> informationalStatus(1000)
        <Alarmtype> other (1) <Polarity>
        (2)
        "
	::= { pmopm8Almchannel88PortEntry 7 }


pmopm8AlmChannel88PowerHighPortn OBJECT-TYPE
	SYNTAX  EkiOnOff
	MAX-ACCESS read-only
	STATUS current
	DESCRIPTION
        "
        Channel Power High 88 :This OID
        indicates that the power of the
        channel is higher than the configured
        threshold<Help> This alarm indicates
        that the power of the channel is
        higher than the configured threshold
        <Condtype> CHANNEL88_POWER_HIGH_1
        <Probcause> degradedSignal (13)
        <Alarmtype> equipmentAlarm <Polarity>
        (2)
        "
	::= { pmopm8Almchannel88PortEntry 6 }


pmopm8AlmChannel88PowerLowPortn OBJECT-TYPE
	SYNTAX  EkiOnOff
	MAX-ACCESS read-only
	STATUS current
	DESCRIPTION
        "
        Channel Power Low 88 :This OID
        indicates that the power of the
        channel is lower than the configured
        threshold<Help> This alarm indicates
        that the power of the channel is
        lower than the configured threshold
        <Condtype> CHANNEL88_POWER_LOW_1
        <Probcause> degradedSignal (13)
        <Alarmtype> equipmentAlarm <Polarity>
        (2)
        "
	::= { pmopm8Almchannel88PortEntry 5 }


pmopm8AlmChannel88BalancedPortn OBJECT-TYPE
	SYNTAX  EkiOnOff
	MAX-ACCESS read-only
	STATUS current
	DESCRIPTION
        "
        Channel Balanced 88 :This OID
         indicates that an in service channel
        is balanced by the Ekinops auto
        turn up application<Help> This
         status indicates that an in service
        channel is balanced by the Ekinops
        auto turn up application <Condtype>
        CHANNEL88_BALANCED_1 <Probcause>
        informationalStatus(1000) <Alarmtype>
        other (1) <Polarity> (2)
        "
	::= { pmopm8Almchannel88PortEntry 4 }


pmopm8AlmChannel88MismatchPortn OBJECT-TYPE
	SYNTAX  EkiOnOff
	MAX-ACCESS read-only
	STATUS current
	DESCRIPTION
        "
        Channel Mismatch 88 :This OID
         indicates that an out of service
        channel is detected on the Optical
        Power Monitoring input<Help> This
        alarm indicates that an out of
         service channel is detected on
        the Optical Power Monitoring input
        <Condtype> CHANNEL88_MISMATCH_1
        <Probcause> unexpectedInformation
        (75) <Alarmtype> equipmentAlarm
        <Polarity> (2)
        "
	::= { pmopm8Almchannel88PortEntry 3 }


pmopm8AlmChannel88AbsentPortn OBJECT-TYPE
	SYNTAX  EkiOnOff
	MAX-ACCESS read-only
	STATUS current
	DESCRIPTION
        "
        Channel Absent 88 :This OID indicates
        that an in service channel is absent
        on the Optical Power Monitoring
        input<Help> This alarm indicates
        that an in service channel is absent
        on the Optical Power Monitoring
        input <Condtype> CHANNEL88_ABSENT_1
        <Probcause> informationMissing
         (65) <Alarmtype> equipmentAlarm
        (5) <Polarity> (2)
        "
	::= { pmopm8Almchannel88PortEntry 2 }


--- *********************************************************
---     TABLE for the pmopm8Almchannel89Port articles
--- *********************************************************

pmopm8Almchannel89PortTable OBJECT-TYPE
	SYNTAX  SEQUENCE OF Pmopm8Almchannel89PortEntry
	MAX-ACCESS not-accessible
	STATUS current
	DESCRIPTION
        "
        List of pmopm8Almchannel89Port
        Article
        "
	::= { pmopm8AlmClientCrit 720 }


pmopm8Almchannel89PortEntry OBJECT-TYPE
	SYNTAX Pmopm8Almchannel89PortEntry
	MAX-ACCESS not-accessible
	STATUS current
	DESCRIPTION
        "
        Row definition for the pmopm8Almchannel89Port
        table
        "
	INDEX   { pmopm8Almchannel89PortIndex }
	::= { pmopm8Almchannel89PortTable 1 }


Pmopm8Almchannel89PortEntry ::=
	SEQUENCE {
	pmopm8Almchannel89PortIndex
		INTEGER,
	pmopm8AlmChannel89OosPortn
		EkiOnOff,
	pmopm8AlmChannel89PowerHighPortn
		EkiOnOff,
	pmopm8AlmChannel89PowerLowPortn
		EkiOnOff,
	pmopm8AlmChannel89BalancedPortn
		EkiOnOff,
	pmopm8AlmChannel89MismatchPortn
		EkiOnOff,
	pmopm8AlmChannel89AbsentPortn
		EkiOnOff
	}


pmopm8Almchannel89PortIndex OBJECT-TYPE
	SYNTAX  INTEGER(0..128)
	MAX-ACCESS  read-only
	STATUS current
	DESCRIPTION
        "
        Index definition for the pmopm8Almchannel89Port
        table
        "
	::= { pmopm8Almchannel89PortEntry 1 }


pmopm8AlmChannel89OosPortn OBJECT-TYPE
	SYNTAX  EkiOnOff
	MAX-ACCESS read-only
	STATUS current
	DESCRIPTION
        "
        Channel Out Of Service 89 :This
        OID indicates that the channel
         is out of service  <Help> This
        alarm indicates that the channel
        is in service <Condtype> CHANNEL89_OOS_1
        <Probcause> informationalStatus(1000)
        <Alarmtype> other (1) <Polarity>
        (2)
        "
	::= { pmopm8Almchannel89PortEntry 7 }


pmopm8AlmChannel89PowerHighPortn OBJECT-TYPE
	SYNTAX  EkiOnOff
	MAX-ACCESS read-only
	STATUS current
	DESCRIPTION
        "
        Channel Power High 89 :This OID
        indicates that the power of the
        channel is higher than the configured
        threshold<Help> This alarm indicates
        that the power of the channel is
        higher than the configured threshold
        <Condtype> CHANNEL89_POWER_HIGH_1
        <Probcause> degradedSignal (13)
        <Alarmtype> equipmentAlarm <Polarity>
        (2)
        "
	::= { pmopm8Almchannel89PortEntry 6 }


pmopm8AlmChannel89PowerLowPortn OBJECT-TYPE
	SYNTAX  EkiOnOff
	MAX-ACCESS read-only
	STATUS current
	DESCRIPTION
        "
        Channel Power Low 89 :This OID
        indicates that the power of the
        channel is lower than the configured
        threshold<Help> This alarm indicates
        that the power of the channel is
        lower than the configured threshold
        <Condtype> CHANNEL89_POWER_LOW_1
        <Probcause> degradedSignal (13)
        <Alarmtype> equipmentAlarm <Polarity>
        (2)
        "
	::= { pmopm8Almchannel89PortEntry 5 }


pmopm8AlmChannel89BalancedPortn OBJECT-TYPE
	SYNTAX  EkiOnOff
	MAX-ACCESS read-only
	STATUS current
	DESCRIPTION
        "
        Channel Balanced 89 :This OID
         indicates that an in service channel
        is balanced by the Ekinops auto
        turn up application<Help> This
         status indicates that an in service
        channel is balanced by the Ekinops
        auto turn up application <Condtype>
        CHANNEL89_BALANCED_1 <Probcause>
        informationalStatus(1000) <Alarmtype>
        other (1) <Polarity> (2)
        "
	::= { pmopm8Almchannel89PortEntry 4 }


pmopm8AlmChannel89MismatchPortn OBJECT-TYPE
	SYNTAX  EkiOnOff
	MAX-ACCESS read-only
	STATUS current
	DESCRIPTION
        "
        Channel Mismatch 89 :This OID
         indicates that an out of service
        channel is detected on the Optical
        Power Monitoring input<Help> This
        alarm indicates that an out of
         service channel is detected on
        the Optical Power Monitoring input
        <Condtype> CHANNEL89_MISMATCH_1
        <Probcause> unexpectedInformation
        (75) <Alarmtype> equipmentAlarm
        <Polarity> (2)
        "
	::= { pmopm8Almchannel89PortEntry 3 }


pmopm8AlmChannel89AbsentPortn OBJECT-TYPE
	SYNTAX  EkiOnOff
	MAX-ACCESS read-only
	STATUS current
	DESCRIPTION
        "
        Channel Absent 89 :This OID indicates
        that an in service channel is absent
        on the Optical Power Monitoring
        input<Help> This alarm indicates
        that an in service channel is absent
        on the Optical Power Monitoring
        input <Condtype> CHANNEL89_ABSENT_1
        <Probcause> informationMissing
         (65) <Alarmtype> equipmentAlarm
        (5) <Polarity> (2)
        "
	::= { pmopm8Almchannel89PortEntry 2 }


--- *********************************************************
---     TABLE for the pmopm8Almchannel90Port articles
--- *********************************************************

pmopm8Almchannel90PortTable OBJECT-TYPE
	SYNTAX  SEQUENCE OF Pmopm8Almchannel90PortEntry
	MAX-ACCESS not-accessible
	STATUS current
	DESCRIPTION
        "
        List of pmopm8Almchannel90Port
        Article
        "
	::= { pmopm8AlmClientCrit 728 }


pmopm8Almchannel90PortEntry OBJECT-TYPE
	SYNTAX Pmopm8Almchannel90PortEntry
	MAX-ACCESS not-accessible
	STATUS current
	DESCRIPTION
        "
        Row definition for the pmopm8Almchannel90Port
        table
        "
	INDEX   { pmopm8Almchannel90PortIndex }
	::= { pmopm8Almchannel90PortTable 1 }


Pmopm8Almchannel90PortEntry ::=
	SEQUENCE {
	pmopm8Almchannel90PortIndex
		INTEGER,
	pmopm8AlmChannel90OosPortn
		EkiOnOff,
	pmopm8AlmChannel90PowerHighPortn
		EkiOnOff,
	pmopm8AlmChannel90PowerLowPortn
		EkiOnOff,
	pmopm8AlmChannel90BalancedPortn
		EkiOnOff,
	pmopm8AlmChannel90MismatchPortn
		EkiOnOff,
	pmopm8AlmChannel90AbsentPortn
		EkiOnOff
	}


pmopm8Almchannel90PortIndex OBJECT-TYPE
	SYNTAX  INTEGER(0..128)
	MAX-ACCESS  read-only
	STATUS current
	DESCRIPTION
        "
        Index definition for the pmopm8Almchannel90Port
        table
        "
	::= { pmopm8Almchannel90PortEntry 1 }


pmopm8AlmChannel90OosPortn OBJECT-TYPE
	SYNTAX  EkiOnOff
	MAX-ACCESS read-only
	STATUS current
	DESCRIPTION
        "
        Channel Out Of Service 90 :This
        OID indicates that the channel
         is out of service  <Help> This
        alarm indicates that the channel
        is in service <Condtype> CHANNEL90_OOS_1
        <Probcause> informationalStatus(1000)
        <Alarmtype> other (1) <Polarity>
        (2)
        "
	::= { pmopm8Almchannel90PortEntry 7 }


pmopm8AlmChannel90PowerHighPortn OBJECT-TYPE
	SYNTAX  EkiOnOff
	MAX-ACCESS read-only
	STATUS current
	DESCRIPTION
        "
        Channel Power High 90 :This OID
        indicates that the power of the
        channel is higher than the configured
        threshold<Help> This alarm indicates
        that the power of the channel is
        higher than the configured threshold
        <Condtype> CHANNEL90_POWER_HIGH_1
        <Probcause> degradedSignal (13)
        <Alarmtype> equipmentAlarm <Polarity>
        (2)
        "
	::= { pmopm8Almchannel90PortEntry 6 }


pmopm8AlmChannel90PowerLowPortn OBJECT-TYPE
	SYNTAX  EkiOnOff
	MAX-ACCESS read-only
	STATUS current
	DESCRIPTION
        "
        Channel Power Low 90 :This OID
        indicates that the power of the
        channel is lower than the configured
        threshold<Help> This alarm indicates
        that the power of the channel is
        lower than the configured threshold
        <Condtype> CHANNEL90_POWER_LOW_1
        <Probcause> degradedSignal (13)
        <Alarmtype> equipmentAlarm <Polarity>
        (2)
        "
	::= { pmopm8Almchannel90PortEntry 5 }


pmopm8AlmChannel90BalancedPortn OBJECT-TYPE
	SYNTAX  EkiOnOff
	MAX-ACCESS read-only
	STATUS current
	DESCRIPTION
        "
        Channel Balanced 90 :This OID
         indicates that an in service channel
        is balanced by the Ekinops auto
        turn up application<Help> This
         status indicates that an in service
        channel is balanced by the Ekinops
        auto turn up application <Condtype>
        CHANNEL90_BALANCED_1 <Probcause>
        informationalStatus(1000) <Alarmtype>
        other (1) <Polarity> (2)
        "
	::= { pmopm8Almchannel90PortEntry 4 }


pmopm8AlmChannel90MismatchPortn OBJECT-TYPE
	SYNTAX  EkiOnOff
	MAX-ACCESS read-only
	STATUS current
	DESCRIPTION
        "
        Channel Mismatch 90 :This OID
         indicates that an out of service
        channel is detected on the Optical
        Power Monitoring input<Help> This
        alarm indicates that an out of
         service channel is detected on
        the Optical Power Monitoring input
        <Condtype> CHANNEL90_MISMATCH_1
        <Probcause> unexpectedInformation
        (75) <Alarmtype> equipmentAlarm
        <Polarity> (2)
        "
	::= { pmopm8Almchannel90PortEntry 3 }


pmopm8AlmChannel90AbsentPortn OBJECT-TYPE
	SYNTAX  EkiOnOff
	MAX-ACCESS read-only
	STATUS current
	DESCRIPTION
        "
        Channel Absent 90 :This OID indicates
        that an in service channel is absent
        on the Optical Power Monitoring
        input<Help> This alarm indicates
        that an in service channel is absent
        on the Optical Power Monitoring
        input <Condtype> CHANNEL90_ABSENT_1
        <Probcause> informationMissing
         (65) <Alarmtype> equipmentAlarm
        (5) <Polarity> (2)
        "
	::= { pmopm8Almchannel90PortEntry 2 }


--- *********************************************************
---     TABLE for the pmopm8Almchannel91Port articles
--- *********************************************************

pmopm8Almchannel91PortTable OBJECT-TYPE
	SYNTAX  SEQUENCE OF Pmopm8Almchannel91PortEntry
	MAX-ACCESS not-accessible
	STATUS current
	DESCRIPTION
        "
        List of pmopm8Almchannel91Port
        Article
        "
	::= { pmopm8AlmClientCrit 736 }


pmopm8Almchannel91PortEntry OBJECT-TYPE
	SYNTAX Pmopm8Almchannel91PortEntry
	MAX-ACCESS not-accessible
	STATUS current
	DESCRIPTION
        "
        Row definition for the pmopm8Almchannel91Port
        table
        "
	INDEX   { pmopm8Almchannel91PortIndex }
	::= { pmopm8Almchannel91PortTable 1 }


Pmopm8Almchannel91PortEntry ::=
	SEQUENCE {
	pmopm8Almchannel91PortIndex
		INTEGER,
	pmopm8AlmChannel91OosPortn
		EkiOnOff,
	pmopm8AlmChannel91PowerHighPortn
		EkiOnOff,
	pmopm8AlmChannel91PowerLowPortn
		EkiOnOff,
	pmopm8AlmChannel91BalancedPortn
		EkiOnOff,
	pmopm8AlmChannel91MismatchPortn
		EkiOnOff,
	pmopm8AlmChannel91AbsentPortn
		EkiOnOff
	}


pmopm8Almchannel91PortIndex OBJECT-TYPE
	SYNTAX  INTEGER(0..128)
	MAX-ACCESS  read-only
	STATUS current
	DESCRIPTION
        "
        Index definition for the pmopm8Almchannel91Port
        table
        "
	::= { pmopm8Almchannel91PortEntry 1 }


pmopm8AlmChannel91OosPortn OBJECT-TYPE
	SYNTAX  EkiOnOff
	MAX-ACCESS read-only
	STATUS current
	DESCRIPTION
        "
        Channel Out Of Service 91 :This
        OID indicates that the channel
         is out of service  <Help> This
        alarm indicates that the channel
        is in service <Condtype> CHANNEL91_OOS_1
        <Probcause> informationalStatus(1000)
        <Alarmtype> other (1) <Polarity>
        (2)
        "
	::= { pmopm8Almchannel91PortEntry 7 }


pmopm8AlmChannel91PowerHighPortn OBJECT-TYPE
	SYNTAX  EkiOnOff
	MAX-ACCESS read-only
	STATUS current
	DESCRIPTION
        "
        Channel Power High 91 :This OID
        indicates that the power of the
        channel is higher than the configured
        threshold<Help> This alarm indicates
        that the power of the channel is
        higher than the configured threshold
        <Condtype> CHANNEL91_POWER_HIGH_1
        <Probcause> degradedSignal (13)
        <Alarmtype> equipmentAlarm <Polarity>
        (2)
        "
	::= { pmopm8Almchannel91PortEntry 6 }


pmopm8AlmChannel91PowerLowPortn OBJECT-TYPE
	SYNTAX  EkiOnOff
	MAX-ACCESS read-only
	STATUS current
	DESCRIPTION
        "
        Channel Power Low 91 :This OID
        indicates that the power of the
        channel is lower than the configured
        threshold<Help> This alarm indicates
        that the power of the channel is
        lower than the configured threshold
        <Condtype> CHANNEL91_POWER_LOW_1
        <Probcause> degradedSignal (13)
        <Alarmtype> equipmentAlarm <Polarity>
        (2)
        "
	::= { pmopm8Almchannel91PortEntry 5 }


pmopm8AlmChannel91BalancedPortn OBJECT-TYPE
	SYNTAX  EkiOnOff
	MAX-ACCESS read-only
	STATUS current
	DESCRIPTION
        "
        Channel Balanced 91 :This OID
         indicates that an in service channel
        is balanced by the Ekinops auto
        turn up application<Help> This
         status indicates that an in service
        channel is balanced by the Ekinops
        auto turn up application <Condtype>
        CHANNEL91_BALANCED_1 <Probcause>
        informationalStatus(1000) <Alarmtype>
        other (1) <Polarity> (2)
        "
	::= { pmopm8Almchannel91PortEntry 4 }


pmopm8AlmChannel91MismatchPortn OBJECT-TYPE
	SYNTAX  EkiOnOff
	MAX-ACCESS read-only
	STATUS current
	DESCRIPTION
        "
        Channel Mismatch 91 :This OID
         indicates that an out of service
        channel is detected on the Optical
        Power Monitoring input<Help> This
        alarm indicates that an out of
         service channel is detected on
        the Optical Power Monitoring input
        <Condtype> CHANNEL91_MISMATCH_1
        <Probcause> unexpectedInformation
        (75) <Alarmtype> equipmentAlarm
        <Polarity> (2)
        "
	::= { pmopm8Almchannel91PortEntry 3 }


pmopm8AlmChannel91AbsentPortn OBJECT-TYPE
	SYNTAX  EkiOnOff
	MAX-ACCESS read-only
	STATUS current
	DESCRIPTION
        "
        Channel Absent 91 :This OID indicates
        that an in service channel is absent
        on the Optical Power Monitoring
        input<Help> This alarm indicates
        that an in service channel is absent
        on the Optical Power Monitoring
        input <Condtype> CHANNEL91_ABSENT_1
        <Probcause> informationMissing
         (65) <Alarmtype> equipmentAlarm
        (5) <Polarity> (2)
        "
	::= { pmopm8Almchannel91PortEntry 2 }


--- *********************************************************
---     TABLE for the pmopm8Almchannel92Port articles
--- *********************************************************

pmopm8Almchannel92PortTable OBJECT-TYPE
	SYNTAX  SEQUENCE OF Pmopm8Almchannel92PortEntry
	MAX-ACCESS not-accessible
	STATUS current
	DESCRIPTION
        "
        List of pmopm8Almchannel92Port
        Article
        "
	::= { pmopm8AlmClientCrit 744 }


pmopm8Almchannel92PortEntry OBJECT-TYPE
	SYNTAX Pmopm8Almchannel92PortEntry
	MAX-ACCESS not-accessible
	STATUS current
	DESCRIPTION
        "
        Row definition for the pmopm8Almchannel92Port
        table
        "
	INDEX   { pmopm8Almchannel92PortIndex }
	::= { pmopm8Almchannel92PortTable 1 }


Pmopm8Almchannel92PortEntry ::=
	SEQUENCE {
	pmopm8Almchannel92PortIndex
		INTEGER,
	pmopm8AlmChannel92OosPortn
		EkiOnOff,
	pmopm8AlmChannel92PowerHighPortn
		EkiOnOff,
	pmopm8AlmChannel92PowerLowPortn
		EkiOnOff,
	pmopm8AlmChannel92BalancedPortn
		EkiOnOff,
	pmopm8AlmChannel92MismatchPortn
		EkiOnOff,
	pmopm8AlmChannel92AbsentPortn
		EkiOnOff
	}


pmopm8Almchannel92PortIndex OBJECT-TYPE
	SYNTAX  INTEGER(0..128)
	MAX-ACCESS  read-only
	STATUS current
	DESCRIPTION
        "
        Index definition for the pmopm8Almchannel92Port
        table
        "
	::= { pmopm8Almchannel92PortEntry 1 }


pmopm8AlmChannel92OosPortn OBJECT-TYPE
	SYNTAX  EkiOnOff
	MAX-ACCESS read-only
	STATUS current
	DESCRIPTION
        "
        Channel Out Of Service 92 :This
        OID indicates that the channel
         is out of service  <Help> This
        alarm indicates that the channel
        is in service <Condtype> CHANNEL92_OOS_1
        <Probcause> informationalStatus(1000)
        <Alarmtype> other (1) <Polarity>
        (2)
        "
	::= { pmopm8Almchannel92PortEntry 7 }


pmopm8AlmChannel92PowerHighPortn OBJECT-TYPE
	SYNTAX  EkiOnOff
	MAX-ACCESS read-only
	STATUS current
	DESCRIPTION
        "
        Channel Power High 92 :This OID
        indicates that the power of the
        channel is higher than the configured
        threshold<Help> This alarm indicates
        that the power of the channel is
        higher than the configured threshold
        <Condtype> CHANNEL92_POWER_HIGH_1
        <Probcause> degradedSignal (13)
        <Alarmtype> equipmentAlarm <Polarity>
        (2)
        "
	::= { pmopm8Almchannel92PortEntry 6 }


pmopm8AlmChannel92PowerLowPortn OBJECT-TYPE
	SYNTAX  EkiOnOff
	MAX-ACCESS read-only
	STATUS current
	DESCRIPTION
        "
        Channel Power Low 92 :This OID
        indicates that the power of the
        channel is lower than the configured
        threshold<Help> This alarm indicates
        that the power of the channel is
        lower than the configured threshold
        <Condtype> CHANNEL92_POWER_LOW_1
        <Probcause> degradedSignal (13)
        <Alarmtype> equipmentAlarm <Polarity>
        (2)
        "
	::= { pmopm8Almchannel92PortEntry 5 }


pmopm8AlmChannel92BalancedPortn OBJECT-TYPE
	SYNTAX  EkiOnOff
	MAX-ACCESS read-only
	STATUS current
	DESCRIPTION
        "
        Channel Balanced 92 :This OID
         indicates that an in service channel
        is balanced by the Ekinops auto
        turn up application<Help> This
         status indicates that an in service
        channel is balanced by the Ekinops
        auto turn up application <Condtype>
        CHANNEL92_BALANCED_1 <Probcause>
        informationalStatus(1000) <Alarmtype>
        other (1) <Polarity> (2)
        "
	::= { pmopm8Almchannel92PortEntry 4 }


pmopm8AlmChannel92MismatchPortn OBJECT-TYPE
	SYNTAX  EkiOnOff
	MAX-ACCESS read-only
	STATUS current
	DESCRIPTION
        "
        Channel Mismatch 92 :This OID
         indicates that an out of service
        channel is detected on the Optical
        Power Monitoring input<Help> This
        alarm indicates that an out of
         service channel is detected on
        the Optical Power Monitoring input
        <Condtype> CHANNEL92_MISMATCH_1
        <Probcause> unexpectedInformation
        (75) <Alarmtype> equipmentAlarm
        <Polarity> (2)
        "
	::= { pmopm8Almchannel92PortEntry 3 }


pmopm8AlmChannel92AbsentPortn OBJECT-TYPE
	SYNTAX  EkiOnOff
	MAX-ACCESS read-only
	STATUS current
	DESCRIPTION
        "
        Channel Absent 92 :This OID indicates
        that an in service channel is absent
        on the Optical Power Monitoring
        input<Help> This alarm indicates
        that an in service channel is absent
        on the Optical Power Monitoring
        input <Condtype> CHANNEL92_ABSENT_1
        <Probcause> informationMissing
         (65) <Alarmtype> equipmentAlarm
        (5) <Polarity> (2)
        "
	::= { pmopm8Almchannel92PortEntry 2 }


--- *********************************************************
---     TABLE for the pmopm8Almchannel93Port articles
--- *********************************************************

pmopm8Almchannel93PortTable OBJECT-TYPE
	SYNTAX  SEQUENCE OF Pmopm8Almchannel93PortEntry
	MAX-ACCESS not-accessible
	STATUS current
	DESCRIPTION
        "
        List of pmopm8Almchannel93Port
        Article
        "
	::= { pmopm8AlmClientCrit 752 }


pmopm8Almchannel93PortEntry OBJECT-TYPE
	SYNTAX Pmopm8Almchannel93PortEntry
	MAX-ACCESS not-accessible
	STATUS current
	DESCRIPTION
        "
        Row definition for the pmopm8Almchannel93Port
        table
        "
	INDEX   { pmopm8Almchannel93PortIndex }
	::= { pmopm8Almchannel93PortTable 1 }


Pmopm8Almchannel93PortEntry ::=
	SEQUENCE {
	pmopm8Almchannel93PortIndex
		INTEGER,
	pmopm8AlmChannel93OosPortn
		EkiOnOff,
	pmopm8AlmChannel93PowerHighPortn
		EkiOnOff,
	pmopm8AlmChannel93PowerLowPortn
		EkiOnOff,
	pmopm8AlmChannel93BalancedPortn
		EkiOnOff,
	pmopm8AlmChannel93MismatchPortn
		EkiOnOff,
	pmopm8AlmChannel93AbsentPortn
		EkiOnOff
	}


pmopm8Almchannel93PortIndex OBJECT-TYPE
	SYNTAX  INTEGER(0..128)
	MAX-ACCESS  read-only
	STATUS current
	DESCRIPTION
        "
        Index definition for the pmopm8Almchannel93Port
        table
        "
	::= { pmopm8Almchannel93PortEntry 1 }


pmopm8AlmChannel93OosPortn OBJECT-TYPE
	SYNTAX  EkiOnOff
	MAX-ACCESS read-only
	STATUS current
	DESCRIPTION
        "
        Channel Out Of Service 93 :This
        OID indicates that the channel
         is out of service  <Help> This
        alarm indicates that the channel
        is in service <Condtype> CHANNEL93_OOS_1
        <Probcause> informationalStatus(1000)
        <Alarmtype> other (1) <Polarity>
        (2)
        "
	::= { pmopm8Almchannel93PortEntry 7 }


pmopm8AlmChannel93PowerHighPortn OBJECT-TYPE
	SYNTAX  EkiOnOff
	MAX-ACCESS read-only
	STATUS current
	DESCRIPTION
        "
        Channel Power High 93 :This OID
        indicates that the power of the
        channel is higher than the configured
        threshold<Help> This alarm indicates
        that the power of the channel is
        higher than the configured threshold
        <Condtype> CHANNEL93_POWER_HIGH_1
        <Probcause> degradedSignal (13)
        <Alarmtype> equipmentAlarm <Polarity>
        (2)
        "
	::= { pmopm8Almchannel93PortEntry 6 }


pmopm8AlmChannel93PowerLowPortn OBJECT-TYPE
	SYNTAX  EkiOnOff
	MAX-ACCESS read-only
	STATUS current
	DESCRIPTION
        "
        Channel Power Low 93 :This OID
        indicates that the power of the
        channel is lower than the configured
        threshold<Help> This alarm indicates
        that the power of the channel is
        lower than the configured threshold
        <Condtype> CHANNEL93_POWER_LOW_1
        <Probcause> degradedSignal (13)
        <Alarmtype> equipmentAlarm <Polarity>
        (2)
        "
	::= { pmopm8Almchannel93PortEntry 5 }


pmopm8AlmChannel93BalancedPortn OBJECT-TYPE
	SYNTAX  EkiOnOff
	MAX-ACCESS read-only
	STATUS current
	DESCRIPTION
        "
        Channel Balanced 93 :This OID
         indicates that an in service channel
        is balanced by the Ekinops auto
        turn up application<Help> This
         status indicates that an in service
        channel is balanced by the Ekinops
        auto turn up application <Condtype>
        CHANNEL93_BALANCED_1 <Probcause>
        informationalStatus(1000) <Alarmtype>
        other (1) <Polarity> (2)
        "
	::= { pmopm8Almchannel93PortEntry 4 }


pmopm8AlmChannel93MismatchPortn OBJECT-TYPE
	SYNTAX  EkiOnOff
	MAX-ACCESS read-only
	STATUS current
	DESCRIPTION
        "
        Channel Mismatch 93 :This OID
         indicates that an out of service
        channel is detected on the Optical
        Power Monitoring input<Help> This
        alarm indicates that an out of
         service channel is detected on
        the Optical Power Monitoring input
        <Condtype> CHANNEL93_MISMATCH_1
        <Probcause> unexpectedInformation
        (75) <Alarmtype> equipmentAlarm
        <Polarity> (2)
        "
	::= { pmopm8Almchannel93PortEntry 3 }


pmopm8AlmChannel93AbsentPortn OBJECT-TYPE
	SYNTAX  EkiOnOff
	MAX-ACCESS read-only
	STATUS current
	DESCRIPTION
        "
        Channel Absent 93 :This OID indicates
        that an in service channel is absent
        on the Optical Power Monitoring
        input<Help> This alarm indicates
        that an in service channel is absent
        on the Optical Power Monitoring
        input <Condtype> CHANNEL93_ABSENT_1
        <Probcause> informationMissing
         (65) <Alarmtype> equipmentAlarm
        (5) <Polarity> (2)
        "
	::= { pmopm8Almchannel93PortEntry 2 }


--- *********************************************************
---     TABLE for the pmopm8Almchannel94Port articles
--- *********************************************************

pmopm8Almchannel94PortTable OBJECT-TYPE
	SYNTAX  SEQUENCE OF Pmopm8Almchannel94PortEntry
	MAX-ACCESS not-accessible
	STATUS current
	DESCRIPTION
        "
        List of pmopm8Almchannel94Port
        Article
        "
	::= { pmopm8AlmClientCrit 760 }


pmopm8Almchannel94PortEntry OBJECT-TYPE
	SYNTAX Pmopm8Almchannel94PortEntry
	MAX-ACCESS not-accessible
	STATUS current
	DESCRIPTION
        "
        Row definition for the pmopm8Almchannel94Port
        table
        "
	INDEX   { pmopm8Almchannel94PortIndex }
	::= { pmopm8Almchannel94PortTable 1 }


Pmopm8Almchannel94PortEntry ::=
	SEQUENCE {
	pmopm8Almchannel94PortIndex
		INTEGER,
	pmopm8AlmChannel94OosPortn
		EkiOnOff,
	pmopm8AlmChannel94PowerHighPortn
		EkiOnOff,
	pmopm8AlmChannel94PowerLowPortn
		EkiOnOff,
	pmopm8AlmChannel94BalancedPortn
		EkiOnOff,
	pmopm8AlmChannel94MismatchPortn
		EkiOnOff,
	pmopm8AlmChannel94AbsentPortn
		EkiOnOff
	}


pmopm8Almchannel94PortIndex OBJECT-TYPE
	SYNTAX  INTEGER(0..128)
	MAX-ACCESS  read-only
	STATUS current
	DESCRIPTION
        "
        Index definition for the pmopm8Almchannel94Port
        table
        "
	::= { pmopm8Almchannel94PortEntry 1 }


pmopm8AlmChannel94OosPortn OBJECT-TYPE
	SYNTAX  EkiOnOff
	MAX-ACCESS read-only
	STATUS current
	DESCRIPTION
        "
        Channel Out Of Service 94 :This
        OID indicates that the channel
         is out of service  <Help> This
        alarm indicates that the channel
        is in service <Condtype> CHANNEL94_OOS_1
        <Probcause> informationalStatus(1000)
        <Alarmtype> other (1) <Polarity>
        (2)
        "
	::= { pmopm8Almchannel94PortEntry 7 }


pmopm8AlmChannel94PowerHighPortn OBJECT-TYPE
	SYNTAX  EkiOnOff
	MAX-ACCESS read-only
	STATUS current
	DESCRIPTION
        "
        Channel Power High 94 :This OID
        indicates that the power of the
        channel is higher than the configured
        threshold<Help> This alarm indicates
        that the power of the channel is
        higher than the configured threshold
        <Condtype> CHANNEL94_POWER_HIGH_1
        <Probcause> degradedSignal (13)
        <Alarmtype> equipmentAlarm <Polarity>
        (2)
        "
	::= { pmopm8Almchannel94PortEntry 6 }


pmopm8AlmChannel94PowerLowPortn OBJECT-TYPE
	SYNTAX  EkiOnOff
	MAX-ACCESS read-only
	STATUS current
	DESCRIPTION
        "
        Channel Power Low 94 :This OID
        indicates that the power of the
        channel is lower than the configured
        threshold<Help> This alarm indicates
        that the power of the channel is
        lower than the configured threshold
        <Condtype> CHANNEL94_POWER_LOW_1
        <Probcause> degradedSignal (13)
        <Alarmtype> equipmentAlarm <Polarity>
        (2)
        "
	::= { pmopm8Almchannel94PortEntry 5 }


pmopm8AlmChannel94BalancedPortn OBJECT-TYPE
	SYNTAX  EkiOnOff
	MAX-ACCESS read-only
	STATUS current
	DESCRIPTION
        "
        Channel Balanced 94 :This OID
         indicates that an in service channel
        is balanced by the Ekinops auto
        turn up application<Help> This
         status indicates that an in service
        channel is balanced by the Ekinops
        auto turn up application <Condtype>
        CHANNEL94_BALANCED_1 <Probcause>
        informationalStatus(1000) <Alarmtype>
        other (1) <Polarity> (2)
        "
	::= { pmopm8Almchannel94PortEntry 4 }


pmopm8AlmChannel94MismatchPortn OBJECT-TYPE
	SYNTAX  EkiOnOff
	MAX-ACCESS read-only
	STATUS current
	DESCRIPTION
        "
        Channel Mismatch 94 :This OID
         indicates that an out of service
        channel is detected on the Optical
        Power Monitoring input<Help> This
        alarm indicates that an out of
         service channel is detected on
        the Optical Power Monitoring input
        <Condtype> CHANNEL94_MISMATCH_1
        <Probcause> unexpectedInformation
        (75) <Alarmtype> equipmentAlarm
        <Polarity> (2)
        "
	::= { pmopm8Almchannel94PortEntry 3 }


pmopm8AlmChannel94AbsentPortn OBJECT-TYPE
	SYNTAX  EkiOnOff
	MAX-ACCESS read-only
	STATUS current
	DESCRIPTION
        "
        Channel Absent 94 :This OID indicates
        that an in service channel is absent
        on the Optical Power Monitoring
        input<Help> This alarm indicates
        that an in service channel is absent
        on the Optical Power Monitoring
        input <Condtype> CHANNEL94_ABSENT_1
        <Probcause> informationMissing
         (65) <Alarmtype> equipmentAlarm
        (5) <Polarity> (2)
        "
	::= { pmopm8Almchannel94PortEntry 2 }


--- *********************************************************
---     TABLE for the pmopm8Almchannel95Port articles
--- *********************************************************

pmopm8Almchannel95PortTable OBJECT-TYPE
	SYNTAX  SEQUENCE OF Pmopm8Almchannel95PortEntry
	MAX-ACCESS not-accessible
	STATUS current
	DESCRIPTION
        "
        List of pmopm8Almchannel95Port
        Article
        "
	::= { pmopm8AlmClientCrit 768 }


pmopm8Almchannel95PortEntry OBJECT-TYPE
	SYNTAX Pmopm8Almchannel95PortEntry
	MAX-ACCESS not-accessible
	STATUS current
	DESCRIPTION
        "
        Row definition for the pmopm8Almchannel95Port
        table
        "
	INDEX   { pmopm8Almchannel95PortIndex }
	::= { pmopm8Almchannel95PortTable 1 }


Pmopm8Almchannel95PortEntry ::=
	SEQUENCE {
	pmopm8Almchannel95PortIndex
		INTEGER,
	pmopm8AlmChannel95OosPortn
		EkiOnOff,
	pmopm8AlmChannel95PowerHighPortn
		EkiOnOff,
	pmopm8AlmChannel95PowerLowPortn
		EkiOnOff,
	pmopm8AlmChannel95BalancedPortn
		EkiOnOff,
	pmopm8AlmChannel95MismatchPortn
		EkiOnOff,
	pmopm8AlmChannel95AbsentPortn
		EkiOnOff
	}


pmopm8Almchannel95PortIndex OBJECT-TYPE
	SYNTAX  INTEGER(0..128)
	MAX-ACCESS  read-only
	STATUS current
	DESCRIPTION
        "
        Index definition for the pmopm8Almchannel95Port
        table
        "
	::= { pmopm8Almchannel95PortEntry 1 }


pmopm8AlmChannel95OosPortn OBJECT-TYPE
	SYNTAX  EkiOnOff
	MAX-ACCESS read-only
	STATUS current
	DESCRIPTION
        "
        Channel Out Of Service 95 :This
        OID indicates that the channel
         is out of service  <Help> This
        alarm indicates that the channel
        is in service <Condtype> CHANNEL95_OOS_1
        <Probcause> informationalStatus(1000)
        <Alarmtype> other (1) <Polarity>
        (2)
        "
	::= { pmopm8Almchannel95PortEntry 7 }


pmopm8AlmChannel95PowerHighPortn OBJECT-TYPE
	SYNTAX  EkiOnOff
	MAX-ACCESS read-only
	STATUS current
	DESCRIPTION
        "
        Channel Power High 95 :This OID
        indicates that the power of the
        channel is higher than the configured
        threshold<Help> This alarm indicates
        that the power of the channel is
        higher than the configured threshold
        <Condtype> CHANNEL95_POWER_HIGH_1
        <Probcause> degradedSignal (13)
        <Alarmtype> equipmentAlarm <Polarity>
        (2)
        "
	::= { pmopm8Almchannel95PortEntry 6 }


pmopm8AlmChannel95PowerLowPortn OBJECT-TYPE
	SYNTAX  EkiOnOff
	MAX-ACCESS read-only
	STATUS current
	DESCRIPTION
        "
        Channel Power Low 95 :This OID
        indicates that the power of the
        channel is lower than the configured
        threshold<Help> This alarm indicates
        that the power of the channel is
        lower than the configured threshold
        <Condtype> CHANNEL95_POWER_LOW_1
        <Probcause> degradedSignal (13)
        <Alarmtype> equipmentAlarm <Polarity>
        (2)
        "
	::= { pmopm8Almchannel95PortEntry 5 }


pmopm8AlmChannel95BalancedPortn OBJECT-TYPE
	SYNTAX  EkiOnOff
	MAX-ACCESS read-only
	STATUS current
	DESCRIPTION
        "
        Channel Balanced 95 :This OID
         indicates that an in service channel
        is balanced by the Ekinops auto
        turn up application<Help> This
         status indicates that an in service
        channel is balanced by the Ekinops
        auto turn up application <Condtype>
        CHANNEL95_BALANCED_1 <Probcause>
        informationalStatus(1000) <Alarmtype>
        other (1) <Polarity> (2)
        "
	::= { pmopm8Almchannel95PortEntry 4 }


pmopm8AlmChannel95MismatchPortn OBJECT-TYPE
	SYNTAX  EkiOnOff
	MAX-ACCESS read-only
	STATUS current
	DESCRIPTION
        "
        Channel Mismatch 95 :This OID
         indicates that an out of service
        channel is detected on the Optical
        Power Monitoring input<Help> This
        alarm indicates that an out of
         service channel is detected on
        the Optical Power Monitoring input
        <Condtype> CHANNEL95_MISMATCH_1
        <Probcause> unexpectedInformation
        (75) <Alarmtype> equipmentAlarm
        <Polarity> (2)
        "
	::= { pmopm8Almchannel95PortEntry 3 }


pmopm8AlmChannel95AbsentPortn OBJECT-TYPE
	SYNTAX  EkiOnOff
	MAX-ACCESS read-only
	STATUS current
	DESCRIPTION
        "
        Channel Absent 95 :This OID indicates
        that an in service channel is absent
        on the Optical Power Monitoring
        input<Help> This alarm indicates
        that an in service channel is absent
        on the Optical Power Monitoring
        input <Condtype> CHANNEL95_ABSENT_1
        <Probcause> informationMissing
         (65) <Alarmtype> equipmentAlarm
        (5) <Polarity> (2)
        "
	::= { pmopm8Almchannel95PortEntry 2 }


--- *********************************************************
---     TABLE for the pmopm8Almchannel96Port articles
--- *********************************************************

pmopm8Almchannel96PortTable OBJECT-TYPE
	SYNTAX  SEQUENCE OF Pmopm8Almchannel96PortEntry
	MAX-ACCESS not-accessible
	STATUS current
	DESCRIPTION
        "
        List of pmopm8Almchannel96Port
        Article
        "
	::= { pmopm8AlmClientCrit 776 }


pmopm8Almchannel96PortEntry OBJECT-TYPE
	SYNTAX Pmopm8Almchannel96PortEntry
	MAX-ACCESS not-accessible
	STATUS current
	DESCRIPTION
        "
        Row definition for the pmopm8Almchannel96Port
        table
        "
	INDEX   { pmopm8Almchannel96PortIndex }
	::= { pmopm8Almchannel96PortTable 1 }


Pmopm8Almchannel96PortEntry ::=
	SEQUENCE {
	pmopm8Almchannel96PortIndex
		INTEGER,
	pmopm8AlmChannel96OosPortn
		EkiOnOff,
	pmopm8AlmChannel96PowerHighPortn
		EkiOnOff,
	pmopm8AlmChannel96PowerLowPortn
		EkiOnOff,
	pmopm8AlmChannel96BalancedPortn
		EkiOnOff,
	pmopm8AlmChannel96MismatchPortn
		EkiOnOff,
	pmopm8AlmChannel96AbsentPortn
		EkiOnOff
	}


pmopm8Almchannel96PortIndex OBJECT-TYPE
	SYNTAX  INTEGER(0..128)
	MAX-ACCESS  read-only
	STATUS current
	DESCRIPTION
        "
        Index definition for the pmopm8Almchannel96Port
        table
        "
	::= { pmopm8Almchannel96PortEntry 1 }


pmopm8AlmChannel96OosPortn OBJECT-TYPE
	SYNTAX  EkiOnOff
	MAX-ACCESS read-only
	STATUS current
	DESCRIPTION
        "
        Channel Out Of Service 96 :This
        OID indicates that the channel
         is out of service  <Help> This
        alarm indicates that the channel
        is in service <Condtype> CHANNEL96_OOS_1
        <Probcause> informationalStatus(1000)
        <Alarmtype> other (1) <Polarity>
        (2)
        "
	::= { pmopm8Almchannel96PortEntry 7 }


pmopm8AlmChannel96PowerHighPortn OBJECT-TYPE
	SYNTAX  EkiOnOff
	MAX-ACCESS read-only
	STATUS current
	DESCRIPTION
        "
        Channel Power High 96 :This OID
        indicates that the power of the
        channel is higher than the configured
        threshold<Help> This alarm indicates
        that the power of the channel is
        higher than the configured threshold
        <Condtype> CHANNEL96_POWER_HIGH_1
        <Probcause> degradedSignal (13)
        <Alarmtype> equipmentAlarm <Polarity>
        (2)
        "
	::= { pmopm8Almchannel96PortEntry 6 }


pmopm8AlmChannel96PowerLowPortn OBJECT-TYPE
	SYNTAX  EkiOnOff
	MAX-ACCESS read-only
	STATUS current
	DESCRIPTION
        "
        Channel Power Low 96 :This OID
        indicates that the power of the
        channel is lower than the configured
        threshold<Help> This alarm indicates
        that the power of the channel is
        lower than the configured threshold
        <Condtype> CHANNEL96_POWER_LOW_1
        <Probcause> degradedSignal (13)
        <Alarmtype> equipmentAlarm <Polarity>
        (2)
        "
	::= { pmopm8Almchannel96PortEntry 5 }


pmopm8AlmChannel96BalancedPortn OBJECT-TYPE
	SYNTAX  EkiOnOff
	MAX-ACCESS read-only
	STATUS current
	DESCRIPTION
        "
        Channel Balanced 96 :This OID
         indicates that an in service channel
        is balanced by the Ekinops auto
        turn up application<Help> This
         status indicates that an in service
        channel is balanced by the Ekinops
        auto turn up application <Condtype>
        CHANNEL96_BALANCED_1 <Probcause>
        informationalStatus(1000) <Alarmtype>
        other (1) <Polarity> (2)
        "
	::= { pmopm8Almchannel96PortEntry 4 }


pmopm8AlmChannel96MismatchPortn OBJECT-TYPE
	SYNTAX  EkiOnOff
	MAX-ACCESS read-only
	STATUS current
	DESCRIPTION
        "
        Channel Mismatch 96 :This OID
         indicates that an out of service
        channel is detected on the Optical
        Power Monitoring input<Help> This
        alarm indicates that an out of
         service channel is detected on
        the Optical Power Monitoring input
        <Condtype> CHANNEL96_MISMATCH_1
        <Probcause> unexpectedInformation
        (75) <Alarmtype> equipmentAlarm
        <Polarity> (2)
        "
	::= { pmopm8Almchannel96PortEntry 3 }


pmopm8AlmChannel96AbsentPortn OBJECT-TYPE
	SYNTAX  EkiOnOff
	MAX-ACCESS read-only
	STATUS current
	DESCRIPTION
        "
        Channel Absent 96 :This OID indicates
        that an in service channel is absent
        on the Optical Power Monitoring
        input<Help> This alarm indicates
        that an in service channel is absent
        on the Optical Power Monitoring
        input <Condtype> CHANNEL96_ABSENT_1
        <Probcause> informationMissing
         (65) <Alarmtype> equipmentAlarm
        (5) <Polarity> (2)
        "
	::= { pmopm8Almchannel96PortEntry 2 }







--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pmopm8CtrlconfMgnt1 OBJECT IDENTIFIER ::= { pmopm8CtrlOther 1 }




pmopm8CtrlConf2Clear1 OBJECT-TYPE
	  SYNTAX EkiOnOff
	  MAX-ACCESS read-write
	  STATUS current
	  DESCRIPTION
        "
        Clear Configuration Tables :This
        OID clears the configuration tables
        from configuration2 in the flash.
         <Help>  This control restores
         the default configuration of the
        module
        "
	  ::= { pmopm8CtrlconfMgnt1 14 }



pmopm8CtrlConf2Flash1 OBJECT-TYPE
	  SYNTAX EkiOnOff
	  MAX-ACCESS read-write
	  STATUS current
	  DESCRIPTION
        "
        Write Configuration Tables :This
        OID saves the current configuration
        of the PM as configuration2 in
         the flash.  <Help>  This control
        saves the customer configuration
        on the module
        "
	  ::= { pmopm8CtrlconfMgnt1 10 }



pmopm8CtrlConf2Load1 OBJECT-TYPE
	  SYNTAX EkiOnOff
	  MAX-ACCESS read-write
	  STATUS current
	  DESCRIPTION
        "
        Load Configuration Tables Set
         Nb 2 :When set this OID enables
        loading from flash configuration2
        into the PM.
        "
	  ::= { pmopm8CtrlconfMgnt1 2 }



pmopm8CtrlConf1Load1 OBJECT-TYPE
	  SYNTAX EkiOnOff
	  MAX-ACCESS read-write
	  STATUS current
	  DESCRIPTION
        "
        Load Configuration Tables Set
         Nb 1 :When set this OID enables
        loading from flash configuration1
        into the PM.
        "
	  ::= { pmopm8CtrlconfMgnt1 1 }



--- *****************************************************
---     LEAF for the synth4 article
--- *****************************************************
pmopm8Ctrlsynth4 OBJECT IDENTIFIER ::= { pmopm8CtrlOther 4 }




pmopm8CtrlCorrelatOff OBJECT-TYPE
	  SYNTAX EkiOnOff
	  MAX-ACCESS read-write
	  STATUS current
	  DESCRIPTION
        "
        Disable Alarm Correlation :This
        OID disables the alarm correlation
        in the PM.
        "
	  ::= { pmopm8Ctrlsynth4 2 }



pmopm8CtrlCorrelatOn OBJECT-TYPE
	  SYNTAX EkiOnOff
	  MAX-ACCESS read-write
	  STATUS current
	  DESCRIPTION
        "
        Enable Alarm Correlation :This
        OID enables the alarm correlation
        in the PM.
        "
	  ::= { pmopm8Ctrlsynth4 1 }



--- *****************************************************
---     LEAF for the swMgnt article
--- *****************************************************
pmopm8CtrlswMgnt OBJECT IDENTIFIER ::= { pmopm8CtrlOther 5 }




pmopm8CtrlLoadSwBank2 OBJECT-TYPE
	  SYNTAX EkiOnOff
	  MAX-ACCESS read-write
	  STATUS current
	  DESCRIPTION
        "
        Set Software Nb 2 As Active :This
        OID, when set, loads the SW from
        bank2 into the PM. It must be followed
        by a reset.  <Help>  This controls
        selects the second SW bank as the
        active bank for the next module
        reset
        "
	  ::= { pmopm8CtrlswMgnt 6 }



pmopm8CtrlLoadSwBank1 OBJECT-TYPE
	  SYNTAX EkiOnOff
	  MAX-ACCESS read-write
	  STATUS current
	  DESCRIPTION
        "
        Set Software Nb 1 As Active :This
        OID, when set, loads the SW from
        bank1 into the PM. It must be followed
        by a reset.  <Help>  This controls
        selects the first SW bank as the
        active bank for the next module
        reset
        "
	  ::= { pmopm8CtrlswMgnt 5 }



pmopm8CtrlWarmReset OBJECT-TYPE
	  SYNTAX EkiOnOff
	  MAX-ACCESS read-write
	  STATUS current
	  DESCRIPTION
        "
        PM Warm Reset :This OID, when
         set, causes a warm reset of the
        PM. This reset is not traffic affecting,
        and the configuration of PM remains
        unchanged.  <Help>  This control
        initiates a warm reset of the module.
        "
	  ::= { pmopm8CtrlswMgnt 3 }



pmopm8CtrlColdReset OBJECT-TYPE
	  SYNTAX EkiOnOff
	  MAX-ACCESS read-write
	  STATUS current
	  DESCRIPTION
        "
        PM Cold Reset :This OID, when
         set, causes a cold reset of the
        PM. This reset is traffic affecting,
        and the configuration of PM is
         reloaded on start-up.  <Help>
          This control initiates a cold
        reset of the module.
        "
	  ::= { pmopm8CtrlswMgnt 2 }



--- *****************************************************
---     LEAF for the gwMgnt article
--- *****************************************************
pmopm8CtrlgwMgnt OBJECT IDENTIFIER ::= { pmopm8CtrlOther 6 }




pmopm8CtrlLoadGwBank4 OBJECT-TYPE
	  SYNTAX EkiOnOff
	  MAX-ACCESS read-write
	  STATUS current
	  DESCRIPTION
        "
        Set Gateware Nb 4 As Active :This
        OID, when set, loads the GW from
        bank4 (Flash) into the PM. It is
        followed by an automatic gateware
        cold reset.
        "
	  ::= { pmopm8CtrlgwMgnt 8 }



pmopm8CtrlLoadGwBank3 OBJECT-TYPE
	  SYNTAX EkiOnOff
	  MAX-ACCESS read-write
	  STATUS current
	  DESCRIPTION
        "
        Set Gateware Nb 3 As Active :This
        OID, when set, loads the GW from
        bank3 (Flash) into the PM. It is
        followed by an automatic gateware
        cold reset.  <Help>  This controls
        initiates a cold reset of the module
        and select the third GW bank as
        the active bank
        "
	  ::= { pmopm8CtrlgwMgnt 7 }



pmopm8CtrlLoadGwBank2 OBJECT-TYPE
	  SYNTAX EkiOnOff
	  MAX-ACCESS read-write
	  STATUS current
	  DESCRIPTION
        "
        Set Gateware Nb 2 As Active :This
        OID, when set, loads the GW from
        bank2 (Flash) into the PM. It is
        followed by an automatic gateware
        cold reset.
        "
	  ::= { pmopm8CtrlgwMgnt 6 }



pmopm8CtrlLoadGwBank1 OBJECT-TYPE
	  SYNTAX EkiOnOff
	  MAX-ACCESS read-write
	  STATUS current
	  DESCRIPTION
        "
        Set Gateware Nb 1 As Active :This
        OID, when set, loads the GW from
        bank1 (Flash) into the PM. It is
        followed by an automatic gateware
        cold reset.  <Help>  This controls
        initiates a cold reset of the module
        and select the first GW bank as
        the active bank
        "
	  ::= { pmopm8CtrlgwMgnt 5 }



pmopm8CtrlCurrentGwReset OBJECT-TYPE
	  SYNTAX EkiOnOff
	  MAX-ACCESS read-write
	  STATUS current
	  DESCRIPTION
        "
        Active Gateware Reset :This OID,
        when set, resets the active gateware.
        It is traffic affecting.
        "
	  ::= { pmopm8CtrlgwMgnt 1 }



--- *********************************************************
---     TABLE for the pmopm8Ctrlcalibration articles
--- *********************************************************

pmopm8CtrlcalibrationTable OBJECT-TYPE
	SYNTAX  SEQUENCE OF Pmopm8CtrlcalibrationEntry
	MAX-ACCESS not-accessible
	STATUS current
	DESCRIPTION
        "
        List of pmopm8Ctrlcalibration
         Article
        "
	::= { pmopm8CtrlClient 16 }


pmopm8CtrlcalibrationEntry OBJECT-TYPE
	SYNTAX Pmopm8CtrlcalibrationEntry
	MAX-ACCESS not-accessible
	STATUS current
	DESCRIPTION
        "
        Row definition for the pmopm8Ctrlcalibration
        table
        "
	INDEX   { pmopm8CtrlcalibrationIndex }
	::= { pmopm8CtrlcalibrationTable 1 }


Pmopm8CtrlcalibrationEntry ::=
	SEQUENCE {
	pmopm8CtrlcalibrationIndex
		INTEGER,
	pmopm8CtrlcalibrationPortn
		EkiState
	}


pmopm8CtrlcalibrationIndex OBJECT-TYPE
	SYNTAX  INTEGER(0..128)
	MAX-ACCESS  read-only
	STATUS current
	DESCRIPTION
        "
        Index definition for the pmopm8Ctrlcalibration
        table
        "
	::= { pmopm8CtrlcalibrationEntry 1 }


pmopm8CtrlcalibrationPortn OBJECT-TYPE
	SYNTAX  EkiState
	MAX-ACCESS read-write
	STATUS current
	DESCRIPTION
        "
        Port Calibration :This OID initiates
        the OPM input calibration to define
        automatically the OPM offset value.
         <Help>  This parameter initiates
        the OPM input calibration to define
        automatically the OPM offset value.
        "
	::= { pmopm8CtrlcalibrationEntry 2 }


--- *********************************************************
---     TABLE for the pmopm8CtrlspectrumAutodiscovery articles
--- *********************************************************

pmopm8CtrlspectrumAutodiscoveryTable OBJECT-TYPE
	SYNTAX  SEQUENCE OF Pmopm8CtrlspectrumAutodiscoveryEntry
	MAX-ACCESS not-accessible
	STATUS current
	DESCRIPTION
        "
        List of pmopm8CtrlspectrumAutodiscovery
        Article
        "
	::= { pmopm8CtrlClient 17 }


pmopm8CtrlspectrumAutodiscoveryEntry OBJECT-TYPE
	SYNTAX Pmopm8CtrlspectrumAutodiscoveryEntry
	MAX-ACCESS not-accessible
	STATUS current
	DESCRIPTION
        "
        Row definition for the pmopm8CtrlspectrumAutodiscovery
        table
        "
	INDEX   { pmopm8CtrlspectrumAutodiscoveryIndex }
	::= { pmopm8CtrlspectrumAutodiscoveryTable 1 }


Pmopm8CtrlspectrumAutodiscoveryEntry ::=
	SEQUENCE {
	pmopm8CtrlspectrumAutodiscoveryIndex
		INTEGER,
	pmopm8CtrlspectrumAutodiscoveryPortn
		EkiState
	}


pmopm8CtrlspectrumAutodiscoveryIndex OBJECT-TYPE
	SYNTAX  INTEGER(0..128)
	MAX-ACCESS  read-only
	STATUS current
	DESCRIPTION
        "
        Index definition for the pmopm8CtrlspectrumAutodiscovery
        table
        "
	::= { pmopm8CtrlspectrumAutodiscoveryEntry 1 }


pmopm8CtrlspectrumAutodiscoveryPortn OBJECT-TYPE
	SYNTAX  EkiState
	MAX-ACCESS read-write
	STATUS current
	DESCRIPTION
        "
        Spectrum Auto Discovery :This
         OID initiates the OPM scanning
        to define automatically the channels
        to monitor  <Help>  This parameter
        initiates the automatic configuration
        of the thresholds (for each channel)
        using the user-defined delta.
        "
	::= { pmopm8CtrlspectrumAutodiscoveryEntry 2 }


--- *********************************************************
---     TABLE for the pmopm8CtrlthresholdsAutoconfig articles
--- *********************************************************

pmopm8CtrlthresholdsAutoconfigTable OBJECT-TYPE
	SYNTAX  SEQUENCE OF Pmopm8CtrlthresholdsAutoconfigEntry
	MAX-ACCESS not-accessible
	STATUS current
	DESCRIPTION
        "
        List of pmopm8CtrlthresholdsAutoconfig
        Article
        "
	::= { pmopm8CtrlClient 18 }


pmopm8CtrlthresholdsAutoconfigEntry OBJECT-TYPE
	SYNTAX Pmopm8CtrlthresholdsAutoconfigEntry
	MAX-ACCESS not-accessible
	STATUS current
	DESCRIPTION
        "
        Row definition for the pmopm8CtrlthresholdsAutoconfig
        table
        "
	INDEX   { pmopm8CtrlthresholdsAutoconfigIndex }
	::= { pmopm8CtrlthresholdsAutoconfigTable 1 }


Pmopm8CtrlthresholdsAutoconfigEntry ::=
	SEQUENCE {
	pmopm8CtrlthresholdsAutoconfigIndex
		INTEGER,
	pmopm8CtrlthresholdsAutoconfigPortn
		EkiState
	}


pmopm8CtrlthresholdsAutoconfigIndex OBJECT-TYPE
	SYNTAX  INTEGER(0..128)
	MAX-ACCESS  read-only
	STATUS current
	DESCRIPTION
        "
        Index definition for the pmopm8CtrlthresholdsAutoconfig
        table
        "
	::= { pmopm8CtrlthresholdsAutoconfigEntry 1 }


pmopm8CtrlthresholdsAutoconfigPortn OBJECT-TYPE
	SYNTAX  EkiState
	MAX-ACCESS read-write
	STATUS current
	DESCRIPTION
        "
        Thresholds Auto Configuration
         :This OID initiates the automatic
        configuration of the thresholds
        (for each channel) using the user-defined
        delta.<Help> This parameter initiates
        the automatic configuration of
         the thresholds (for each channel)
        using the user-defined delta.
        "
	::= { pmopm8CtrlthresholdsAutoconfigEntry 2 }


--- *********************************************************
---     TABLE for the pmopm8CtrlpowerLossDelta articles
--- *********************************************************

pmopm8CtrlpowerLossDeltaTable OBJECT-TYPE
	SYNTAX  SEQUENCE OF Pmopm8CtrlpowerLossDeltaEntry
	MAX-ACCESS not-accessible
	STATUS current
	DESCRIPTION
        "
        List of pmopm8CtrlpowerLossDelta
        Article
        "
	::= { pmopm8CtrlClient 32 }


pmopm8CtrlpowerLossDeltaEntry OBJECT-TYPE
	SYNTAX Pmopm8CtrlpowerLossDeltaEntry
	MAX-ACCESS not-accessible
	STATUS current
	DESCRIPTION
        "
        Row definition for the pmopm8CtrlpowerLossDelta
        table
        "
	INDEX   { pmopm8CtrlpowerLossDeltaIndex }
	::= { pmopm8CtrlpowerLossDeltaTable 1 }


Pmopm8CtrlpowerLossDeltaEntry ::=
	SEQUENCE {
	pmopm8CtrlpowerLossDeltaIndex
		INTEGER,
	pmopm8CtrlpowerLossDeltaPortn
		INTEGER
	}


pmopm8CtrlpowerLossDeltaIndex OBJECT-TYPE
	SYNTAX  INTEGER(0..128)
	MAX-ACCESS  read-only
	STATUS current
	DESCRIPTION
        "
        Index definition for the pmopm8CtrlpowerLossDelta
        table
        "
	::= { pmopm8CtrlpowerLossDeltaEntry 1 }


pmopm8CtrlpowerLossDeltaPortn OBJECT-TYPE
	SYNTAX  INTEGER (0..65535)
	MAX-ACCESS read-write
	STATUS current
	DESCRIPTION
        "
        Power Loss Delta :This OID defines
        the delta to use to define the
         channel absence threshold  (AV=InvQ8(Delta))
        (Unit = dB)<Help> This parameter
        defines the delta to use to defined
        the channel absence threshold
        "
	::= { pmopm8CtrlpowerLossDeltaEntry 2 }


--- *********************************************************
---     TABLE for the pmopm8CtrlpowerHighDelta articles
--- *********************************************************

pmopm8CtrlpowerHighDeltaTable OBJECT-TYPE
	SYNTAX  SEQUENCE OF Pmopm8CtrlpowerHighDeltaEntry
	MAX-ACCESS not-accessible
	STATUS current
	DESCRIPTION
        "
        List of pmopm8CtrlpowerHighDelta
        Article
        "
	::= { pmopm8CtrlClient 40 }


pmopm8CtrlpowerHighDeltaEntry OBJECT-TYPE
	SYNTAX Pmopm8CtrlpowerHighDeltaEntry
	MAX-ACCESS not-accessible
	STATUS current
	DESCRIPTION
        "
        Row definition for the pmopm8CtrlpowerHighDelta
        table
        "
	INDEX   { pmopm8CtrlpowerHighDeltaIndex }
	::= { pmopm8CtrlpowerHighDeltaTable 1 }


Pmopm8CtrlpowerHighDeltaEntry ::=
	SEQUENCE {
	pmopm8CtrlpowerHighDeltaIndex
		INTEGER,
	pmopm8CtrlpowerHighDeltaPortn
		INTEGER
	}


pmopm8CtrlpowerHighDeltaIndex OBJECT-TYPE
	SYNTAX  INTEGER(0..128)
	MAX-ACCESS  read-only
	STATUS current
	DESCRIPTION
        "
        Index definition for the pmopm8CtrlpowerHighDelta
        table
        "
	::= { pmopm8CtrlpowerHighDeltaEntry 1 }


pmopm8CtrlpowerHighDeltaPortn OBJECT-TYPE
	SYNTAX  INTEGER (0..65535)
	MAX-ACCESS read-write
	STATUS current
	DESCRIPTION
        "
        Power High Delta :This OID defines
        the delta to use to define the
         channel absence threshold  (AV=InvQ8(Delta))
        (Unit = dB)<Help> This parameter
        defines the delta to use to defined
        the channel power high threshold
        "
	::= { pmopm8CtrlpowerHighDeltaEntry 2 }


--- *********************************************************
---     TABLE for the pmopm8CtrlpowerLowDelta articles
--- *********************************************************

pmopm8CtrlpowerLowDeltaTable OBJECT-TYPE
	SYNTAX  SEQUENCE OF Pmopm8CtrlpowerLowDeltaEntry
	MAX-ACCESS not-accessible
	STATUS current
	DESCRIPTION
        "
        List of pmopm8CtrlpowerLowDelta
        Article
        "
	::= { pmopm8CtrlClient 48 }


pmopm8CtrlpowerLowDeltaEntry OBJECT-TYPE
	SYNTAX Pmopm8CtrlpowerLowDeltaEntry
	MAX-ACCESS not-accessible
	STATUS current
	DESCRIPTION
        "
        Row definition for the pmopm8CtrlpowerLowDelta
        table
        "
	INDEX   { pmopm8CtrlpowerLowDeltaIndex }
	::= { pmopm8CtrlpowerLowDeltaTable 1 }


Pmopm8CtrlpowerLowDeltaEntry ::=
	SEQUENCE {
	pmopm8CtrlpowerLowDeltaIndex
		INTEGER,
	pmopm8CtrlpowerLowDeltaPortn
		INTEGER
	}


pmopm8CtrlpowerLowDeltaIndex OBJECT-TYPE
	SYNTAX  INTEGER(0..128)
	MAX-ACCESS  read-only
	STATUS current
	DESCRIPTION
        "
        Index definition for the pmopm8CtrlpowerLowDelta
        table
        "
	::= { pmopm8CtrlpowerLowDeltaEntry 1 }


pmopm8CtrlpowerLowDeltaPortn OBJECT-TYPE
	SYNTAX  INTEGER (0..65535)
	MAX-ACCESS read-write
	STATUS current
	DESCRIPTION
        "
        Power Low Delta :This OID defines
        the delta to use to define the
         channel absence threshold  (AV=InvQ8(Delta))
        (Unit = dB)<Help> This parameter
        defines the delta to use to defined
        the channel power low threshold
        "
	::= { pmopm8CtrlpowerLowDeltaEntry 2 }


--- *********************************************************
---     TABLE for the pmopm8CtrlinputPowerRef articles
--- *********************************************************

pmopm8CtrlinputPowerRefTable OBJECT-TYPE
	SYNTAX  SEQUENCE OF Pmopm8CtrlinputPowerRefEntry
	MAX-ACCESS not-accessible
	STATUS current
	DESCRIPTION
        "
        List of pmopm8CtrlinputPowerRef
        Article
        "
	::= { pmopm8CtrlClient 64 }


pmopm8CtrlinputPowerRefEntry OBJECT-TYPE
	SYNTAX Pmopm8CtrlinputPowerRefEntry
	MAX-ACCESS not-accessible
	STATUS current
	DESCRIPTION
        "
        Row definition for the pmopm8CtrlinputPowerRef
        table
        "
	INDEX   { pmopm8CtrlinputPowerRefIndex }
	::= { pmopm8CtrlinputPowerRefTable 1 }


Pmopm8CtrlinputPowerRefEntry ::=
	SEQUENCE {
	pmopm8CtrlinputPowerRefIndex
		INTEGER,
	pmopm8CtrlinputPowerRefPortn
		INTEGER
	}


pmopm8CtrlinputPowerRefIndex OBJECT-TYPE
	SYNTAX  INTEGER(0..128)
	MAX-ACCESS  read-only
	STATUS current
	DESCRIPTION
        "
        Index definition for the pmopm8CtrlinputPowerRef
        table
        "
	::= { pmopm8CtrlinputPowerRefEntry 1 }


pmopm8CtrlinputPowerRefPortn OBJECT-TYPE
	SYNTAX  INTEGER (0..65535)
	MAX-ACCESS read-write
	STATUS current
	DESCRIPTION
        "
        Input Power Reference :This OID
        defines the input power reference
        used to calibrate the OPM input
        power.   (AV=InvQ8(Power)) (Unit
        = dBm)<Help> This parameter defines
        the input power reference used
         to calibrate the OPM input power.
        "
	::= { pmopm8CtrlinputPowerRefEntry 2 }


--- *****************************************************
---     LEAF for the ledTest article
--- *****************************************************
pmopm8CtrlledTest OBJECT IDENTIFIER ::= { pmopm8CtrlOther 192 }




pmopm8CtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { pmopm8CtrlledTest 3 }



pmopm8CtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { pmopm8CtrlledTest 2 }



pmopm8CtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { pmopm8CtrlledTest 1 }








--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



--- *********************************************************
---     TABLE for the pmopm8Mesrchannel1 articles
--- *********************************************************

pmopm8Mesrchannel1Table OBJECT-TYPE
	SYNTAX  SEQUENCE OF Pmopm8Mesrchannel1Entry
	MAX-ACCESS not-accessible
	STATUS current
	DESCRIPTION
        "
        List of pmopm8Mesrchannel1 Article
        "
	::= { pmopm8MesrClient 16 }


pmopm8Mesrchannel1Entry OBJECT-TYPE
	SYNTAX Pmopm8Mesrchannel1Entry
	MAX-ACCESS not-accessible
	STATUS current
	DESCRIPTION
        "
        Row definition for the pmopm8Mesrchannel1
        table
        "
	INDEX   { pmopm8Mesrchannel1Index }
	::= { pmopm8Mesrchannel1Table 1 }


Pmopm8Mesrchannel1Entry ::=
	SEQUENCE {
	pmopm8Mesrchannel1Index
		INTEGER,
	pmopm8Mesrchannel1Portn
		INTEGER
	}


pmopm8Mesrchannel1Index OBJECT-TYPE
	SYNTAX  INTEGER(0..128)
	MAX-ACCESS  read-only
	STATUS current
	DESCRIPTION
        "
        Index definition for the pmopm8Mesrchannel1
        table
        "
	::= { pmopm8Mesrchannel1Entry 1 }


pmopm8Mesrchannel1Portn OBJECT-TYPE
	SYNTAX  INTEGER (0..65535)
	MAX-ACCESS read-only
	STATUS current
	DESCRIPTION
        "
        Channel Power :This OID indicates
        the channel power  (Power =Q8(Number
        format)) (Unit = dBm)  <Help> This
        measure indicates the channel power
        "
	::= { pmopm8Mesrchannel1Entry 2 }


--- *********************************************************
---     TABLE for the pmopm8Mesrchannel2 articles
--- *********************************************************

pmopm8Mesrchannel2Table OBJECT-TYPE
	SYNTAX  SEQUENCE OF Pmopm8Mesrchannel2Entry
	MAX-ACCESS not-accessible
	STATUS current
	DESCRIPTION
        "
        List of pmopm8Mesrchannel2 Article
        "
	::= { pmopm8MesrClient 24 }


pmopm8Mesrchannel2Entry OBJECT-TYPE
	SYNTAX Pmopm8Mesrchannel2Entry
	MAX-ACCESS not-accessible
	STATUS current
	DESCRIPTION
        "
        Row definition for the pmopm8Mesrchannel2
        table
        "
	INDEX   { pmopm8Mesrchannel2Index }
	::= { pmopm8Mesrchannel2Table 1 }


Pmopm8Mesrchannel2Entry ::=
	SEQUENCE {
	pmopm8Mesrchannel2Index
		INTEGER,
	pmopm8Mesrchannel2Portn
		INTEGER
	}


pmopm8Mesrchannel2Index OBJECT-TYPE
	SYNTAX  INTEGER(0..128)
	MAX-ACCESS  read-only
	STATUS current
	DESCRIPTION
        "
        Index definition for the pmopm8Mesrchannel2
        table
        "
	::= { pmopm8Mesrchannel2Entry 1 }


pmopm8Mesrchannel2Portn OBJECT-TYPE
	SYNTAX  INTEGER (0..65535)
	MAX-ACCESS read-only
	STATUS current
	DESCRIPTION
        "
        Channel2 Power :This OID indicates
        the channel power  (Power =Q8(Number
        format)) (Unit = dBm)  <Help> This
        measure indicates the channel power
        "
	::= { pmopm8Mesrchannel2Entry 2 }


--- *********************************************************
---     TABLE for the pmopm8Mesrchannel3 articles
--- *********************************************************

pmopm8Mesrchannel3Table OBJECT-TYPE
	SYNTAX  SEQUENCE OF Pmopm8Mesrchannel3Entry
	MAX-ACCESS not-accessible
	STATUS current
	DESCRIPTION
        "
        List of pmopm8Mesrchannel3 Article
        "
	::= { pmopm8MesrClient 32 }


pmopm8Mesrchannel3Entry OBJECT-TYPE
	SYNTAX Pmopm8Mesrchannel3Entry
	MAX-ACCESS not-accessible
	STATUS current
	DESCRIPTION
        "
        Row definition for the pmopm8Mesrchannel3
        table
        "
	INDEX   { pmopm8Mesrchannel3Index }
	::= { pmopm8Mesrchannel3Table 1 }


Pmopm8Mesrchannel3Entry ::=
	SEQUENCE {
	pmopm8Mesrchannel3Index
		INTEGER,
	pmopm8Mesrchannel3Portn
		INTEGER
	}


pmopm8Mesrchannel3Index OBJECT-TYPE
	SYNTAX  INTEGER(0..128)
	MAX-ACCESS  read-only
	STATUS current
	DESCRIPTION
        "
        Index definition for the pmopm8Mesrchannel3
        table
        "
	::= { pmopm8Mesrchannel3Entry 1 }


pmopm8Mesrchannel3Portn OBJECT-TYPE
	SYNTAX  INTEGER (0..65535)
	MAX-ACCESS read-only
	STATUS current
	DESCRIPTION
        "
        Channel3 Power :This OID indicates
        the channel power  (Power =Q8(Number
        format)) (Unit = dBm)  <Help> This
        measure indicates the channel power
        "
	::= { pmopm8Mesrchannel3Entry 2 }


--- *********************************************************
---     TABLE for the pmopm8Mesrchannel4 articles
--- *********************************************************

pmopm8Mesrchannel4Table OBJECT-TYPE
	SYNTAX  SEQUENCE OF Pmopm8Mesrchannel4Entry
	MAX-ACCESS not-accessible
	STATUS current
	DESCRIPTION
        "
        List of pmopm8Mesrchannel4 Article
        "
	::= { pmopm8MesrClient 40 }


pmopm8Mesrchannel4Entry OBJECT-TYPE
	SYNTAX Pmopm8Mesrchannel4Entry
	MAX-ACCESS not-accessible
	STATUS current
	DESCRIPTION
        "
        Row definition for the pmopm8Mesrchannel4
        table
        "
	INDEX   { pmopm8Mesrchannel4Index }
	::= { pmopm8Mesrchannel4Table 1 }


Pmopm8Mesrchannel4Entry ::=
	SEQUENCE {
	pmopm8Mesrchannel4Index
		INTEGER,
	pmopm8Mesrchannel4Portn
		INTEGER
	}


pmopm8Mesrchannel4Index OBJECT-TYPE
	SYNTAX  INTEGER(0..128)
	MAX-ACCESS  read-only
	STATUS current
	DESCRIPTION
        "
        Index definition for the pmopm8Mesrchannel4
        table
        "
	::= { pmopm8Mesrchannel4Entry 1 }


pmopm8Mesrchannel4Portn OBJECT-TYPE
	SYNTAX  INTEGER (0..65535)
	MAX-ACCESS read-only
	STATUS current
	DESCRIPTION
        "
        Channel4 Power :This OID indicates
        the channel power  (Power =Q8(Number
        format)) (Unit = dBm)  <Help> This
        measure indicates the channel power
        "
	::= { pmopm8Mesrchannel4Entry 2 }


--- *********************************************************
---     TABLE for the pmopm8Mesrchannel5 articles
--- *********************************************************

pmopm8Mesrchannel5Table OBJECT-TYPE
	SYNTAX  SEQUENCE OF Pmopm8Mesrchannel5Entry
	MAX-ACCESS not-accessible
	STATUS current
	DESCRIPTION
        "
        List of pmopm8Mesrchannel5 Article
        "
	::= { pmopm8MesrClient 48 }


pmopm8Mesrchannel5Entry OBJECT-TYPE
	SYNTAX Pmopm8Mesrchannel5Entry
	MAX-ACCESS not-accessible
	STATUS current
	DESCRIPTION
        "
        Row definition for the pmopm8Mesrchannel5
        table
        "
	INDEX   { pmopm8Mesrchannel5Index }
	::= { pmopm8Mesrchannel5Table 1 }


Pmopm8Mesrchannel5Entry ::=
	SEQUENCE {
	pmopm8Mesrchannel5Index
		INTEGER,
	pmopm8Mesrchannel5Portn
		INTEGER
	}


pmopm8Mesrchannel5Index OBJECT-TYPE
	SYNTAX  INTEGER(0..128)
	MAX-ACCESS  read-only
	STATUS current
	DESCRIPTION
        "
        Index definition for the pmopm8Mesrchannel5
        table
        "
	::= { pmopm8Mesrchannel5Entry 1 }


pmopm8Mesrchannel5Portn OBJECT-TYPE
	SYNTAX  INTEGER (0..65535)
	MAX-ACCESS read-only
	STATUS current
	DESCRIPTION
        "
        Channel5 Power :This OID indicates
        the channel power  (Power =Q8(Number
        format)) (Unit = dBm)  <Help> This
        measure indicates the channel power
        "
	::= { pmopm8Mesrchannel5Entry 2 }


--- *********************************************************
---     TABLE for the pmopm8Mesrchannel6 articles
--- *********************************************************

pmopm8Mesrchannel6Table OBJECT-TYPE
	SYNTAX  SEQUENCE OF Pmopm8Mesrchannel6Entry
	MAX-ACCESS not-accessible
	STATUS current
	DESCRIPTION
        "
        List of pmopm8Mesrchannel6 Article
        "
	::= { pmopm8MesrClient 56 }


pmopm8Mesrchannel6Entry OBJECT-TYPE
	SYNTAX Pmopm8Mesrchannel6Entry
	MAX-ACCESS not-accessible
	STATUS current
	DESCRIPTION
        "
        Row definition for the pmopm8Mesrchannel6
        table
        "
	INDEX   { pmopm8Mesrchannel6Index }
	::= { pmopm8Mesrchannel6Table 1 }


Pmopm8Mesrchannel6Entry ::=
	SEQUENCE {
	pmopm8Mesrchannel6Index
		INTEGER,
	pmopm8Mesrchannel6Portn
		INTEGER
	}


pmopm8Mesrchannel6Index OBJECT-TYPE
	SYNTAX  INTEGER(0..128)
	MAX-ACCESS  read-only
	STATUS current
	DESCRIPTION
        "
        Index definition for the pmopm8Mesrchannel6
        table
        "
	::= { pmopm8Mesrchannel6Entry 1 }


pmopm8Mesrchannel6Portn OBJECT-TYPE
	SYNTAX  INTEGER (0..65535)
	MAX-ACCESS read-only
	STATUS current
	DESCRIPTION
        "
        Channel6 Power :This OID indicates
        the channel power  (Power =Q8(Number
        format)) (Unit = dBm)  <Help> This
        measure indicates the channel power
        "
	::= { pmopm8Mesrchannel6Entry 2 }


--- *********************************************************
---     TABLE for the pmopm8Mesrchannel7 articles
--- *********************************************************

pmopm8Mesrchannel7Table OBJECT-TYPE
	SYNTAX  SEQUENCE OF Pmopm8Mesrchannel7Entry
	MAX-ACCESS not-accessible
	STATUS current
	DESCRIPTION
        "
        List of pmopm8Mesrchannel7 Article
        "
	::= { pmopm8MesrClient 64 }


pmopm8Mesrchannel7Entry OBJECT-TYPE
	SYNTAX Pmopm8Mesrchannel7Entry
	MAX-ACCESS not-accessible
	STATUS current
	DESCRIPTION
        "
        Row definition for the pmopm8Mesrchannel7
        table
        "
	INDEX   { pmopm8Mesrchannel7Index }
	::= { pmopm8Mesrchannel7Table 1 }


Pmopm8Mesrchannel7Entry ::=
	SEQUENCE {
	pmopm8Mesrchannel7Index
		INTEGER,
	pmopm8Mesrchannel7Portn
		INTEGER
	}


pmopm8Mesrchannel7Index OBJECT-TYPE
	SYNTAX  INTEGER(0..128)
	MAX-ACCESS  read-only
	STATUS current
	DESCRIPTION
        "
        Index definition for the pmopm8Mesrchannel7
        table
        "
	::= { pmopm8Mesrchannel7Entry 1 }


pmopm8Mesrchannel7Portn OBJECT-TYPE
	SYNTAX  INTEGER (0..65535)
	MAX-ACCESS read-only
	STATUS current
	DESCRIPTION
        "
        Channel7 Power :This OID indicates
        the channel power  (Power =Q8(Number
        format)) (Unit = dBm)  <Help> This
        measure indicates the channel power
        "
	::= { pmopm8Mesrchannel7Entry 2 }


--- *********************************************************
---     TABLE for the pmopm8Mesrchannel8 articles
--- *********************************************************

pmopm8Mesrchannel8Table OBJECT-TYPE
	SYNTAX  SEQUENCE OF Pmopm8Mesrchannel8Entry
	MAX-ACCESS not-accessible
	STATUS current
	DESCRIPTION
        "
        List of pmopm8Mesrchannel8 Article
        "
	::= { pmopm8MesrClient 72 }


pmopm8Mesrchannel8Entry OBJECT-TYPE
	SYNTAX Pmopm8Mesrchannel8Entry
	MAX-ACCESS not-accessible
	STATUS current
	DESCRIPTION
        "
        Row definition for the pmopm8Mesrchannel8
        table
        "
	INDEX   { pmopm8Mesrchannel8Index }
	::= { pmopm8Mesrchannel8Table 1 }


Pmopm8Mesrchannel8Entry ::=
	SEQUENCE {
	pmopm8Mesrchannel8Index
		INTEGER,
	pmopm8Mesrchannel8Portn
		INTEGER
	}


pmopm8Mesrchannel8Index OBJECT-TYPE
	SYNTAX  INTEGER(0..128)
	MAX-ACCESS  read-only
	STATUS current
	DESCRIPTION
        "
        Index definition for the pmopm8Mesrchannel8
        table
        "
	::= { pmopm8Mesrchannel8Entry 1 }


pmopm8Mesrchannel8Portn OBJECT-TYPE
	SYNTAX  INTEGER (0..65535)
	MAX-ACCESS read-only
	STATUS current
	DESCRIPTION
        "
        Channel8 Power :This OID indicates
        the channel power  (Power =Q8(Number
        format)) (Unit = dBm)  <Help> This
        measure indicates the channel power
        "
	::= { pmopm8Mesrchannel8Entry 2 }


--- *********************************************************
---     TABLE for the pmopm8Mesrchannel9 articles
--- *********************************************************

pmopm8Mesrchannel9Table OBJECT-TYPE
	SYNTAX  SEQUENCE OF Pmopm8Mesrchannel9Entry
	MAX-ACCESS not-accessible
	STATUS current
	DESCRIPTION
        "
        List of pmopm8Mesrchannel9 Article
        "
	::= { pmopm8MesrClient 80 }


pmopm8Mesrchannel9Entry OBJECT-TYPE
	SYNTAX Pmopm8Mesrchannel9Entry
	MAX-ACCESS not-accessible
	STATUS current
	DESCRIPTION
        "
        Row definition for the pmopm8Mesrchannel9
        table
        "
	INDEX   { pmopm8Mesrchannel9Index }
	::= { pmopm8Mesrchannel9Table 1 }


Pmopm8Mesrchannel9Entry ::=
	SEQUENCE {
	pmopm8Mesrchannel9Index
		INTEGER,
	pmopm8Mesrchannel9Portn
		INTEGER
	}


pmopm8Mesrchannel9Index OBJECT-TYPE
	SYNTAX  INTEGER(0..128)
	MAX-ACCESS  read-only
	STATUS current
	DESCRIPTION
        "
        Index definition for the pmopm8Mesrchannel9
        table
        "
	::= { pmopm8Mesrchannel9Entry 1 }


pmopm8Mesrchannel9Portn OBJECT-TYPE
	SYNTAX  INTEGER (0..65535)
	MAX-ACCESS read-only
	STATUS current
	DESCRIPTION
        "
        Channel9 Power :This OID indicates
        the channel power  (Power =Q8(Number
        format)) (Unit = dBm)  <Help> This
        measure indicates the channel power
        "
	::= { pmopm8Mesrchannel9Entry 2 }


--- *********************************************************
---     TABLE for the pmopm8Mesrchannel10 articles
--- *********************************************************

pmopm8Mesrchannel10Table OBJECT-TYPE
	SYNTAX  SEQUENCE OF Pmopm8Mesrchannel10Entry
	MAX-ACCESS not-accessible
	STATUS current
	DESCRIPTION
        "
        List of pmopm8Mesrchannel10 Article
        "
	::= { pmopm8MesrClient 88 }


pmopm8Mesrchannel10Entry OBJECT-TYPE
	SYNTAX Pmopm8Mesrchannel10Entry
	MAX-ACCESS not-accessible
	STATUS current
	DESCRIPTION
        "
        Row definition for the pmopm8Mesrchannel10
        table
        "
	INDEX   { pmopm8Mesrchannel10Index }
	::= { pmopm8Mesrchannel10Table 1 }


Pmopm8Mesrchannel10Entry ::=
	SEQUENCE {
	pmopm8Mesrchannel10Index
		INTEGER,
	pmopm8Mesrchannel10Portn
		INTEGER
	}


pmopm8Mesrchannel10Index OBJECT-TYPE
	SYNTAX  INTEGER(0..128)
	MAX-ACCESS  read-only
	STATUS current
	DESCRIPTION
        "
        Index definition for the pmopm8Mesrchannel10
        table
        "
	::= { pmopm8Mesrchannel10Entry 1 }


pmopm8Mesrchannel10Portn OBJECT-TYPE
	SYNTAX  INTEGER (0..65535)
	MAX-ACCESS read-only
	STATUS current
	DESCRIPTION
        "
        Channel10 Power :This OID indicates
        the channel power  (Power =Q8(Number
        format)) (Unit = dBm)  <Help> This
        measure indicates the channel power
        "
	::= { pmopm8Mesrchannel10Entry 2 }


--- *********************************************************
---     TABLE for the pmopm8Mesrchannel11 articles
--- *********************************************************

pmopm8Mesrchannel11Table OBJECT-TYPE
	SYNTAX  SEQUENCE OF Pmopm8Mesrchannel11Entry
	MAX-ACCESS not-accessible
	STATUS current
	DESCRIPTION
        "
        List of pmopm8Mesrchannel11 Article
        "
	::= { pmopm8MesrClient 96 }


pmopm8Mesrchannel11Entry OBJECT-TYPE
	SYNTAX Pmopm8Mesrchannel11Entry
	MAX-ACCESS not-accessible
	STATUS current
	DESCRIPTION
        "
        Row definition for the pmopm8Mesrchannel11
        table
        "
	INDEX   { pmopm8Mesrchannel11Index }
	::= { pmopm8Mesrchannel11Table 1 }


Pmopm8Mesrchannel11Entry ::=
	SEQUENCE {
	pmopm8Mesrchannel11Index
		INTEGER,
	pmopm8Mesrchannel11Portn
		INTEGER
	}


pmopm8Mesrchannel11Index OBJECT-TYPE
	SYNTAX  INTEGER(0..128)
	MAX-ACCESS  read-only
	STATUS current
	DESCRIPTION
        "
        Index definition for the pmopm8Mesrchannel11
        table
        "
	::= { pmopm8Mesrchannel11Entry 1 }


pmopm8Mesrchannel11Portn OBJECT-TYPE
	SYNTAX  INTEGER (0..65535)
	MAX-ACCESS read-only
	STATUS current
	DESCRIPTION
        "
        Channel11 Power :This OID indicates
        the channel power  (Power =Q8(Number
        format)) (Unit = dBm)  <Help> This
        measure indicates the channel power
        "
	::= { pmopm8Mesrchannel11Entry 2 }


--- *********************************************************
---     TABLE for the pmopm8Mesrchannel12 articles
--- *********************************************************

pmopm8Mesrchannel12Table OBJECT-TYPE
	SYNTAX  SEQUENCE OF Pmopm8Mesrchannel12Entry
	MAX-ACCESS not-accessible
	STATUS current
	DESCRIPTION
        "
        List of pmopm8Mesrchannel12 Article
        "
	::= { pmopm8MesrClient 104 }


pmopm8Mesrchannel12Entry OBJECT-TYPE
	SYNTAX Pmopm8Mesrchannel12Entry
	MAX-ACCESS not-accessible
	STATUS current
	DESCRIPTION
        "
        Row definition for the pmopm8Mesrchannel12
        table
        "
	INDEX   { pmopm8Mesrchannel12Index }
	::= { pmopm8Mesrchannel12Table 1 }


Pmopm8Mesrchannel12Entry ::=
	SEQUENCE {
	pmopm8Mesrchannel12Index
		INTEGER,
	pmopm8Mesrchannel12Portn
		INTEGER
	}


pmopm8Mesrchannel12Index OBJECT-TYPE
	SYNTAX  INTEGER(0..128)
	MAX-ACCESS  read-only
	STATUS current
	DESCRIPTION
        "
        Index definition for the pmopm8Mesrchannel12
        table
        "
	::= { pmopm8Mesrchannel12Entry 1 }


pmopm8Mesrchannel12Portn OBJECT-TYPE
	SYNTAX  INTEGER (0..65535)
	MAX-ACCESS read-only
	STATUS current
	DESCRIPTION
        "
        Channel12 Power :This OID indicates
        the channel power  (Power =Q8(Number
        format)) (Unit = dBm)  <Help> This
        measure indicates the channel power
        "
	::= { pmopm8Mesrchannel12Entry 2 }


--- *********************************************************
---     TABLE for the pmopm8Mesrchannel13 articles
--- *********************************************************

pmopm8Mesrchannel13Table OBJECT-TYPE
	SYNTAX  SEQUENCE OF Pmopm8Mesrchannel13Entry
	MAX-ACCESS not-accessible
	STATUS current
	DESCRIPTION
        "
        List of pmopm8Mesrchannel13 Article
        "
	::= { pmopm8MesrClient 112 }


pmopm8Mesrchannel13Entry OBJECT-TYPE
	SYNTAX Pmopm8Mesrchannel13Entry
	MAX-ACCESS not-accessible
	STATUS current
	DESCRIPTION
        "
        Row definition for the pmopm8Mesrchannel13
        table
        "
	INDEX   { pmopm8Mesrchannel13Index }
	::= { pmopm8Mesrchannel13Table 1 }


Pmopm8Mesrchannel13Entry ::=
	SEQUENCE {
	pmopm8Mesrchannel13Index
		INTEGER,
	pmopm8Mesrchannel13Portn
		INTEGER
	}


pmopm8Mesrchannel13Index OBJECT-TYPE
	SYNTAX  INTEGER(0..128)
	MAX-ACCESS  read-only
	STATUS current
	DESCRIPTION
        "
        Index definition for the pmopm8Mesrchannel13
        table
        "
	::= { pmopm8Mesrchannel13Entry 1 }


pmopm8Mesrchannel13Portn OBJECT-TYPE
	SYNTAX  INTEGER (0..65535)
	MAX-ACCESS read-only
	STATUS current
	DESCRIPTION
        "
        Channel13 Power :This OID indicates
        the channel power  (Power =Q8(Number
        format)) (Unit = dBm)  <Help> This
        measure indicates the channel power
        "
	::= { pmopm8Mesrchannel13Entry 2 }


--- *********************************************************
---     TABLE for the pmopm8Mesrchannel14 articles
--- *********************************************************

pmopm8Mesrchannel14Table OBJECT-TYPE
	SYNTAX  SEQUENCE OF Pmopm8Mesrchannel14Entry
	MAX-ACCESS not-accessible
	STATUS current
	DESCRIPTION
        "
        List of pmopm8Mesrchannel14 Article
        "
	::= { pmopm8MesrClient 120 }


pmopm8Mesrchannel14Entry OBJECT-TYPE
	SYNTAX Pmopm8Mesrchannel14Entry
	MAX-ACCESS not-accessible
	STATUS current
	DESCRIPTION
        "
        Row definition for the pmopm8Mesrchannel14
        table
        "
	INDEX   { pmopm8Mesrchannel14Index }
	::= { pmopm8Mesrchannel14Table 1 }


Pmopm8Mesrchannel14Entry ::=
	SEQUENCE {
	pmopm8Mesrchannel14Index
		INTEGER,
	pmopm8Mesrchannel14Portn
		INTEGER
	}


pmopm8Mesrchannel14Index OBJECT-TYPE
	SYNTAX  INTEGER(0..128)
	MAX-ACCESS  read-only
	STATUS current
	DESCRIPTION
        "
        Index definition for the pmopm8Mesrchannel14
        table
        "
	::= { pmopm8Mesrchannel14Entry 1 }


pmopm8Mesrchannel14Portn OBJECT-TYPE
	SYNTAX  INTEGER (0..65535)
	MAX-ACCESS read-only
	STATUS current
	DESCRIPTION
        "
        Channel14 Power :This OID indicates
        the channel power  (Power =Q8(Number
        format)) (Unit = dBm)  <Help> This
        measure indicates the channel power
        "
	::= { pmopm8Mesrchannel14Entry 2 }


--- *********************************************************
---     TABLE for the pmopm8Mesrchannel15 articles
--- *********************************************************

pmopm8Mesrchannel15Table OBJECT-TYPE
	SYNTAX  SEQUENCE OF Pmopm8Mesrchannel15Entry
	MAX-ACCESS not-accessible
	STATUS current
	DESCRIPTION
        "
        List of pmopm8Mesrchannel15 Article
        "
	::= { pmopm8MesrClient 128 }


pmopm8Mesrchannel15Entry OBJECT-TYPE
	SYNTAX Pmopm8Mesrchannel15Entry
	MAX-ACCESS not-accessible
	STATUS current
	DESCRIPTION
        "
        Row definition for the pmopm8Mesrchannel15
        table
        "
	INDEX   { pmopm8Mesrchannel15Index }
	::= { pmopm8Mesrchannel15Table 1 }


Pmopm8Mesrchannel15Entry ::=
	SEQUENCE {
	pmopm8Mesrchannel15Index
		INTEGER,
	pmopm8Mesrchannel15Portn
		INTEGER
	}


pmopm8Mesrchannel15Index OBJECT-TYPE
	SYNTAX  INTEGER(0..128)
	MAX-ACCESS  read-only
	STATUS current
	DESCRIPTION
        "
        Index definition for the pmopm8Mesrchannel15
        table
        "
	::= { pmopm8Mesrchannel15Entry 1 }


pmopm8Mesrchannel15Portn OBJECT-TYPE
	SYNTAX  INTEGER (0..65535)
	MAX-ACCESS read-only
	STATUS current
	DESCRIPTION
        "
        Channel15 Power :This OID indicates
        the channel power  (Power =Q8(Number
        format)) (Unit = dBm)  <Help> This
        measure indicates the channel power
        "
	::= { pmopm8Mesrchannel15Entry 2 }


--- *********************************************************
---     TABLE for the pmopm8Mesrchannel16 articles
--- *********************************************************

pmopm8Mesrchannel16Table OBJECT-TYPE
	SYNTAX  SEQUENCE OF Pmopm8Mesrchannel16Entry
	MAX-ACCESS not-accessible
	STATUS current
	DESCRIPTION
        "
        List of pmopm8Mesrchannel16 Article
        "
	::= { pmopm8MesrClient 136 }


pmopm8Mesrchannel16Entry OBJECT-TYPE
	SYNTAX Pmopm8Mesrchannel16Entry
	MAX-ACCESS not-accessible
	STATUS current
	DESCRIPTION
        "
        Row definition for the pmopm8Mesrchannel16
        table
        "
	INDEX   { pmopm8Mesrchannel16Index }
	::= { pmopm8Mesrchannel16Table 1 }


Pmopm8Mesrchannel16Entry ::=
	SEQUENCE {
	pmopm8Mesrchannel16Index
		INTEGER,
	pmopm8Mesrchannel16Portn
		INTEGER
	}


pmopm8Mesrchannel16Index OBJECT-TYPE
	SYNTAX  INTEGER(0..128)
	MAX-ACCESS  read-only
	STATUS current
	DESCRIPTION
        "
        Index definition for the pmopm8Mesrchannel16
        table
        "
	::= { pmopm8Mesrchannel16Entry 1 }


pmopm8Mesrchannel16Portn OBJECT-TYPE
	SYNTAX  INTEGER (0..65535)
	MAX-ACCESS read-only
	STATUS current
	DESCRIPTION
        "
        Channel16 Power :This OID indicates
        the channel power  (Power =Q8(Number
        format)) (Unit = dBm)  <Help> This
        measure indicates the channel power
        "
	::= { pmopm8Mesrchannel16Entry 2 }


--- *********************************************************
---     TABLE for the pmopm8Mesrchannel17 articles
--- *********************************************************

pmopm8Mesrchannel17Table OBJECT-TYPE
	SYNTAX  SEQUENCE OF Pmopm8Mesrchannel17Entry
	MAX-ACCESS not-accessible
	STATUS current
	DESCRIPTION
        "
        List of pmopm8Mesrchannel17 Article
        "
	::= { pmopm8MesrClient 144 }


pmopm8Mesrchannel17Entry OBJECT-TYPE
	SYNTAX Pmopm8Mesrchannel17Entry
	MAX-ACCESS not-accessible
	STATUS current
	DESCRIPTION
        "
        Row definition for the pmopm8Mesrchannel17
        table
        "
	INDEX   { pmopm8Mesrchannel17Index }
	::= { pmopm8Mesrchannel17Table 1 }


Pmopm8Mesrchannel17Entry ::=
	SEQUENCE {
	pmopm8Mesrchannel17Index
		INTEGER,
	pmopm8Mesrchannel17Portn
		INTEGER
	}


pmopm8Mesrchannel17Index OBJECT-TYPE
	SYNTAX  INTEGER(0..128)
	MAX-ACCESS  read-only
	STATUS current
	DESCRIPTION
        "
        Index definition for the pmopm8Mesrchannel17
        table
        "
	::= { pmopm8Mesrchannel17Entry 1 }


pmopm8Mesrchannel17Portn OBJECT-TYPE
	SYNTAX  INTEGER (0..65535)
	MAX-ACCESS read-only
	STATUS current
	DESCRIPTION
        "
        Channel17 Power :This OID indicates
        the channel power  (Power =Q8(Number
        format)) (Unit = dBm)  <Help> This
        measure indicates the channel power
        "
	::= { pmopm8Mesrchannel17Entry 2 }


--- *********************************************************
---     TABLE for the pmopm8Mesrchannel18 articles
--- *********************************************************

pmopm8Mesrchannel18Table OBJECT-TYPE
	SYNTAX  SEQUENCE OF Pmopm8Mesrchannel18Entry
	MAX-ACCESS not-accessible
	STATUS current
	DESCRIPTION
        "
        List of pmopm8Mesrchannel18 Article
        "
	::= { pmopm8MesrClient 152 }


pmopm8Mesrchannel18Entry OBJECT-TYPE
	SYNTAX Pmopm8Mesrchannel18Entry
	MAX-ACCESS not-accessible
	STATUS current
	DESCRIPTION
        "
        Row definition for the pmopm8Mesrchannel18
        table
        "
	INDEX   { pmopm8Mesrchannel18Index }
	::= { pmopm8Mesrchannel18Table 1 }


Pmopm8Mesrchannel18Entry ::=
	SEQUENCE {
	pmopm8Mesrchannel18Index
		INTEGER,
	pmopm8Mesrchannel18Portn
		INTEGER
	}


pmopm8Mesrchannel18Index OBJECT-TYPE
	SYNTAX  INTEGER(0..128)
	MAX-ACCESS  read-only
	STATUS current
	DESCRIPTION
        "
        Index definition for the pmopm8Mesrchannel18
        table
        "
	::= { pmopm8Mesrchannel18Entry 1 }


pmopm8Mesrchannel18Portn OBJECT-TYPE
	SYNTAX  INTEGER (0..65535)
	MAX-ACCESS read-only
	STATUS current
	DESCRIPTION
        "
        Channel18 Power :This OID indicates
        the channel power  (Power =Q8(Number
        format)) (Unit = dBm)  <Help> This
        measure indicates the channel power
        "
	::= { pmopm8Mesrchannel18Entry 2 }


--- *********************************************************
---     TABLE for the pmopm8Mesrchannel19 articles
--- *********************************************************

pmopm8Mesrchannel19Table OBJECT-TYPE
	SYNTAX  SEQUENCE OF Pmopm8Mesrchannel19Entry
	MAX-ACCESS not-accessible
	STATUS current
	DESCRIPTION
        "
        List of pmopm8Mesrchannel19 Article
        "
	::= { pmopm8MesrClient 160 }


pmopm8Mesrchannel19Entry OBJECT-TYPE
	SYNTAX Pmopm8Mesrchannel19Entry
	MAX-ACCESS not-accessible
	STATUS current
	DESCRIPTION
        "
        Row definition for the pmopm8Mesrchannel19
        table
        "
	INDEX   { pmopm8Mesrchannel19Index }
	::= { pmopm8Mesrchannel19Table 1 }


Pmopm8Mesrchannel19Entry ::=
	SEQUENCE {
	pmopm8Mesrchannel19Index
		INTEGER,
	pmopm8Mesrchannel19Portn
		INTEGER
	}


pmopm8Mesrchannel19Index OBJECT-TYPE
	SYNTAX  INTEGER(0..128)
	MAX-ACCESS  read-only
	STATUS current
	DESCRIPTION
        "
        Index definition for the pmopm8Mesrchannel19
        table
        "
	::= { pmopm8Mesrchannel19Entry 1 }


pmopm8Mesrchannel19Portn OBJECT-TYPE
	SYNTAX  INTEGER (0..65535)
	MAX-ACCESS read-only
	STATUS current
	DESCRIPTION
        "
        Channel19 Power :This OID indicates
        the channel power  (Power =Q8(Number
        format)) (Unit = dBm)  <Help> This
        measure indicates the channel power
        "
	::= { pmopm8Mesrchannel19Entry 2 }


--- *********************************************************
---     TABLE for the pmopm8Mesrchannel20 articles
--- *********************************************************

pmopm8Mesrchannel20Table OBJECT-TYPE
	SYNTAX  SEQUENCE OF Pmopm8Mesrchannel20Entry
	MAX-ACCESS not-accessible
	STATUS current
	DESCRIPTION
        "
        List of pmopm8Mesrchannel20 Article
        "
	::= { pmopm8MesrClient 168 }


pmopm8Mesrchannel20Entry OBJECT-TYPE
	SYNTAX Pmopm8Mesrchannel20Entry
	MAX-ACCESS not-accessible
	STATUS current
	DESCRIPTION
        "
        Row definition for the pmopm8Mesrchannel20
        table
        "
	INDEX   { pmopm8Mesrchannel20Index }
	::= { pmopm8Mesrchannel20Table 1 }


Pmopm8Mesrchannel20Entry ::=
	SEQUENCE {
	pmopm8Mesrchannel20Index
		INTEGER,
	pmopm8Mesrchannel20Portn
		INTEGER
	}


pmopm8Mesrchannel20Index OBJECT-TYPE
	SYNTAX  INTEGER(0..128)
	MAX-ACCESS  read-only
	STATUS current
	DESCRIPTION
        "
        Index definition for the pmopm8Mesrchannel20
        table
        "
	::= { pmopm8Mesrchannel20Entry 1 }


pmopm8Mesrchannel20Portn OBJECT-TYPE
	SYNTAX  INTEGER (0..65535)
	MAX-ACCESS read-only
	STATUS current
	DESCRIPTION
        "
        Channel20 Power :This OID indicates
        the channel power  (Power =Q8(Number
        format)) (Unit = dBm)  <Help> This
        measure indicates the channel power
        "
	::= { pmopm8Mesrchannel20Entry 2 }


--- *********************************************************
---     TABLE for the pmopm8Mesrchannel21 articles
--- *********************************************************

pmopm8Mesrchannel21Table OBJECT-TYPE
	SYNTAX  SEQUENCE OF Pmopm8Mesrchannel21Entry
	MAX-ACCESS not-accessible
	STATUS current
	DESCRIPTION
        "
        List of pmopm8Mesrchannel21 Article
        "
	::= { pmopm8MesrClient 176 }


pmopm8Mesrchannel21Entry OBJECT-TYPE
	SYNTAX Pmopm8Mesrchannel21Entry
	MAX-ACCESS not-accessible
	STATUS current
	DESCRIPTION
        "
        Row definition for the pmopm8Mesrchannel21
        table
        "
	INDEX   { pmopm8Mesrchannel21Index }
	::= { pmopm8Mesrchannel21Table 1 }


Pmopm8Mesrchannel21Entry ::=
	SEQUENCE {
	pmopm8Mesrchannel21Index
		INTEGER,
	pmopm8Mesrchannel21Portn
		INTEGER
	}


pmopm8Mesrchannel21Index OBJECT-TYPE
	SYNTAX  INTEGER(0..128)
	MAX-ACCESS  read-only
	STATUS current
	DESCRIPTION
        "
        Index definition for the pmopm8Mesrchannel21
        table
        "
	::= { pmopm8Mesrchannel21Entry 1 }


pmopm8Mesrchannel21Portn OBJECT-TYPE
	SYNTAX  INTEGER (0..65535)
	MAX-ACCESS read-only
	STATUS current
	DESCRIPTION
        "
        Channel21 Power :This OID indicates
        the channel power  (Power =Q8(Number
        format)) (Unit = dBm)  <Help> This
        measure indicates the channel power
        "
	::= { pmopm8Mesrchannel21Entry 2 }


--- *********************************************************
---     TABLE for the pmopm8Mesrchannel22 articles
--- *********************************************************

pmopm8Mesrchannel22Table OBJECT-TYPE
	SYNTAX  SEQUENCE OF Pmopm8Mesrchannel22Entry
	MAX-ACCESS not-accessible
	STATUS current
	DESCRIPTION
        "
        List of pmopm8Mesrchannel22 Article
        "
	::= { pmopm8MesrClient 184 }


pmopm8Mesrchannel22Entry OBJECT-TYPE
	SYNTAX Pmopm8Mesrchannel22Entry
	MAX-ACCESS not-accessible
	STATUS current
	DESCRIPTION
        "
        Row definition for the pmopm8Mesrchannel22
        table
        "
	INDEX   { pmopm8Mesrchannel22Index }
	::= { pmopm8Mesrchannel22Table 1 }


Pmopm8Mesrchannel22Entry ::=
	SEQUENCE {
	pmopm8Mesrchannel22Index
		INTEGER,
	pmopm8Mesrchannel22Portn
		INTEGER
	}


pmopm8Mesrchannel22Index OBJECT-TYPE
	SYNTAX  INTEGER(0..128)
	MAX-ACCESS  read-only
	STATUS current
	DESCRIPTION
        "
        Index definition for the pmopm8Mesrchannel22
        table
        "
	::= { pmopm8Mesrchannel22Entry 1 }


pmopm8Mesrchannel22Portn OBJECT-TYPE
	SYNTAX  INTEGER (0..65535)
	MAX-ACCESS read-only
	STATUS current
	DESCRIPTION
        "
        Channel22 Power :This OID indicates
        the channel power  (Power =Q8(Number
        format)) (Unit = dBm)  <Help> This
        measure indicates the channel power
        "
	::= { pmopm8Mesrchannel22Entry 2 }


--- *********************************************************
---     TABLE for the pmopm8Mesrchannel23 articles
--- *********************************************************

pmopm8Mesrchannel23Table OBJECT-TYPE
	SYNTAX  SEQUENCE OF Pmopm8Mesrchannel23Entry
	MAX-ACCESS not-accessible
	STATUS current
	DESCRIPTION
        "
        List of pmopm8Mesrchannel23 Article
        "
	::= { pmopm8MesrClient 192 }


pmopm8Mesrchannel23Entry OBJECT-TYPE
	SYNTAX Pmopm8Mesrchannel23Entry
	MAX-ACCESS not-accessible
	STATUS current
	DESCRIPTION
        "
        Row definition for the pmopm8Mesrchannel23
        table
        "
	INDEX   { pmopm8Mesrchannel23Index }
	::= { pmopm8Mesrchannel23Table 1 }


Pmopm8Mesrchannel23Entry ::=
	SEQUENCE {
	pmopm8Mesrchannel23Index
		INTEGER,
	pmopm8Mesrchannel23Portn
		INTEGER
	}


pmopm8Mesrchannel23Index OBJECT-TYPE
	SYNTAX  INTEGER(0..128)
	MAX-ACCESS  read-only
	STATUS current
	DESCRIPTION
        "
        Index definition for the pmopm8Mesrchannel23
        table
        "
	::= { pmopm8Mesrchannel23Entry 1 }


pmopm8Mesrchannel23Portn OBJECT-TYPE
	SYNTAX  INTEGER (0..65535)
	MAX-ACCESS read-only
	STATUS current
	DESCRIPTION
        "
        Channel23 Power :This OID indicates
        the channel power  (Power =Q8(Number
        format)) (Unit = dBm)  <Help> This
        measure indicates the channel power
        "
	::= { pmopm8Mesrchannel23Entry 2 }


--- *********************************************************
---     TABLE for the pmopm8Mesrchannel24 articles
--- *********************************************************

pmopm8Mesrchannel24Table OBJECT-TYPE
	SYNTAX  SEQUENCE OF Pmopm8Mesrchannel24Entry
	MAX-ACCESS not-accessible
	STATUS current
	DESCRIPTION
        "
        List of pmopm8Mesrchannel24 Article
        "
	::= { pmopm8MesrClient 200 }


pmopm8Mesrchannel24Entry OBJECT-TYPE
	SYNTAX Pmopm8Mesrchannel24Entry
	MAX-ACCESS not-accessible
	STATUS current
	DESCRIPTION
        "
        Row definition for the pmopm8Mesrchannel24
        table
        "
	INDEX   { pmopm8Mesrchannel24Index }
	::= { pmopm8Mesrchannel24Table 1 }


Pmopm8Mesrchannel24Entry ::=
	SEQUENCE {
	pmopm8Mesrchannel24Index
		INTEGER,
	pmopm8Mesrchannel24Portn
		INTEGER
	}


pmopm8Mesrchannel24Index OBJECT-TYPE
	SYNTAX  INTEGER(0..128)
	MAX-ACCESS  read-only
	STATUS current
	DESCRIPTION
        "
        Index definition for the pmopm8Mesrchannel24
        table
        "
	::= { pmopm8Mesrchannel24Entry 1 }


pmopm8Mesrchannel24Portn OBJECT-TYPE
	SYNTAX  INTEGER (0..65535)
	MAX-ACCESS read-only
	STATUS current
	DESCRIPTION
        "
        Channel24 Power :This OID indicates
        the channel power  (Power =Q8(Number
        format)) (Unit = dBm)  <Help> This
        measure indicates the channel power
        "
	::= { pmopm8Mesrchannel24Entry 2 }


--- *********************************************************
---     TABLE for the pmopm8Mesrchannel25 articles
--- *********************************************************

pmopm8Mesrchannel25Table OBJECT-TYPE
	SYNTAX  SEQUENCE OF Pmopm8Mesrchannel25Entry
	MAX-ACCESS not-accessible
	STATUS current
	DESCRIPTION
        "
        List of pmopm8Mesrchannel25 Article
        "
	::= { pmopm8MesrClient 208 }


pmopm8Mesrchannel25Entry OBJECT-TYPE
	SYNTAX Pmopm8Mesrchannel25Entry
	MAX-ACCESS not-accessible
	STATUS current
	DESCRIPTION
        "
        Row definition for the pmopm8Mesrchannel25
        table
        "
	INDEX   { pmopm8Mesrchannel25Index }
	::= { pmopm8Mesrchannel25Table 1 }


Pmopm8Mesrchannel25Entry ::=
	SEQUENCE {
	pmopm8Mesrchannel25Index
		INTEGER,
	pmopm8Mesrchannel25Portn
		INTEGER
	}


pmopm8Mesrchannel25Index OBJECT-TYPE
	SYNTAX  INTEGER(0..128)
	MAX-ACCESS  read-only
	STATUS current
	DESCRIPTION
        "
        Index definition for the pmopm8Mesrchannel25
        table
        "
	::= { pmopm8Mesrchannel25Entry 1 }


pmopm8Mesrchannel25Portn OBJECT-TYPE
	SYNTAX  INTEGER (0..65535)
	MAX-ACCESS read-only
	STATUS current
	DESCRIPTION
        "
        Channel25 Power :This OID indicates
        the channel power  (Power =Q8(Number
        format)) (Unit = dBm)  <Help> This
        measure indicates the channel power
        "
	::= { pmopm8Mesrchannel25Entry 2 }


--- *********************************************************
---     TABLE for the pmopm8Mesrchannel26 articles
--- *********************************************************

pmopm8Mesrchannel26Table OBJECT-TYPE
	SYNTAX  SEQUENCE OF Pmopm8Mesrchannel26Entry
	MAX-ACCESS not-accessible
	STATUS current
	DESCRIPTION
        "
        List of pmopm8Mesrchannel26 Article
        "
	::= { pmopm8MesrClient 216 }


pmopm8Mesrchannel26Entry OBJECT-TYPE
	SYNTAX Pmopm8Mesrchannel26Entry
	MAX-ACCESS not-accessible
	STATUS current
	DESCRIPTION
        "
        Row definition for the pmopm8Mesrchannel26
        table
        "
	INDEX   { pmopm8Mesrchannel26Index }
	::= { pmopm8Mesrchannel26Table 1 }


Pmopm8Mesrchannel26Entry ::=
	SEQUENCE {
	pmopm8Mesrchannel26Index
		INTEGER,
	pmopm8Mesrchannel26Portn
		INTEGER
	}


pmopm8Mesrchannel26Index OBJECT-TYPE
	SYNTAX  INTEGER(0..128)
	MAX-ACCESS  read-only
	STATUS current
	DESCRIPTION
        "
        Index definition for the pmopm8Mesrchannel26
        table
        "
	::= { pmopm8Mesrchannel26Entry 1 }


pmopm8Mesrchannel26Portn OBJECT-TYPE
	SYNTAX  INTEGER (0..65535)
	MAX-ACCESS read-only
	STATUS current
	DESCRIPTION
        "
        Channel26 Power :This OID indicates
        the channel power  (Power =Q8(Number
        format)) (Unit = dBm)  <Help> This
        measure indicates the channel power
        "
	::= { pmopm8Mesrchannel26Entry 2 }


--- *********************************************************
---     TABLE for the pmopm8Mesrchannel27 articles
--- *********************************************************

pmopm8Mesrchannel27Table OBJECT-TYPE
	SYNTAX  SEQUENCE OF Pmopm8Mesrchannel27Entry
	MAX-ACCESS not-accessible
	STATUS current
	DESCRIPTION
        "
        List of pmopm8Mesrchannel27 Article
        "
	::= { pmopm8MesrClient 224 }


pmopm8Mesrchannel27Entry OBJECT-TYPE
	SYNTAX Pmopm8Mesrchannel27Entry
	MAX-ACCESS not-accessible
	STATUS current
	DESCRIPTION
        "
        Row definition for the pmopm8Mesrchannel27
        table
        "
	INDEX   { pmopm8Mesrchannel27Index }
	::= { pmopm8Mesrchannel27Table 1 }


Pmopm8Mesrchannel27Entry ::=
	SEQUENCE {
	pmopm8Mesrchannel27Index
		INTEGER,
	pmopm8Mesrchannel27Portn
		INTEGER
	}


pmopm8Mesrchannel27Index OBJECT-TYPE
	SYNTAX  INTEGER(0..128)
	MAX-ACCESS  read-only
	STATUS current
	DESCRIPTION
        "
        Index definition for the pmopm8Mesrchannel27
        table
        "
	::= { pmopm8Mesrchannel27Entry 1 }


pmopm8Mesrchannel27Portn OBJECT-TYPE
	SYNTAX  INTEGER (0..65535)
	MAX-ACCESS read-only
	STATUS current
	DESCRIPTION
        "
        Channel27 Power :This OID indicates
        the channel power  (Power =Q8(Number
        format)) (Unit = dBm)  <Help> This
        measure indicates the channel power
        "
	::= { pmopm8Mesrchannel27Entry 2 }


--- *********************************************************
---     TABLE for the pmopm8Mesrchannel28 articles
--- *********************************************************

pmopm8Mesrchannel28Table OBJECT-TYPE
	SYNTAX  SEQUENCE OF Pmopm8Mesrchannel28Entry
	MAX-ACCESS not-accessible
	STATUS current
	DESCRIPTION
        "
        List of pmopm8Mesrchannel28 Article
        "
	::= { pmopm8MesrClient 232 }


pmopm8Mesrchannel28Entry OBJECT-TYPE
	SYNTAX Pmopm8Mesrchannel28Entry
	MAX-ACCESS not-accessible
	STATUS current
	DESCRIPTION
        "
        Row definition for the pmopm8Mesrchannel28
        table
        "
	INDEX   { pmopm8Mesrchannel28Index }
	::= { pmopm8Mesrchannel28Table 1 }


Pmopm8Mesrchannel28Entry ::=
	SEQUENCE {
	pmopm8Mesrchannel28Index
		INTEGER,
	pmopm8Mesrchannel28Portn
		INTEGER
	}


pmopm8Mesrchannel28Index OBJECT-TYPE
	SYNTAX  INTEGER(0..128)
	MAX-ACCESS  read-only
	STATUS current
	DESCRIPTION
        "
        Index definition for the pmopm8Mesrchannel28
        table
        "
	::= { pmopm8Mesrchannel28Entry 1 }


pmopm8Mesrchannel28Portn OBJECT-TYPE
	SYNTAX  INTEGER (0..65535)
	MAX-ACCESS read-only
	STATUS current
	DESCRIPTION
        "
        Channel28 Power :This OID indicates
        the channel power  (Power =Q8(Number
        format)) (Unit = dBm)  <Help> This
        measure indicates the channel power
        "
	::= { pmopm8Mesrchannel28Entry 2 }


--- *********************************************************
---     TABLE for the pmopm8Mesrchannel29 articles
--- *********************************************************

pmopm8Mesrchannel29Table OBJECT-TYPE
	SYNTAX  SEQUENCE OF Pmopm8Mesrchannel29Entry
	MAX-ACCESS not-accessible
	STATUS current
	DESCRIPTION
        "
        List of pmopm8Mesrchannel29 Article
        "
	::= { pmopm8MesrClient 240 }


pmopm8Mesrchannel29Entry OBJECT-TYPE
	SYNTAX Pmopm8Mesrchannel29Entry
	MAX-ACCESS not-accessible
	STATUS current
	DESCRIPTION
        "
        Row definition for the pmopm8Mesrchannel29
        table
        "
	INDEX   { pmopm8Mesrchannel29Index }
	::= { pmopm8Mesrchannel29Table 1 }


Pmopm8Mesrchannel29Entry ::=
	SEQUENCE {
	pmopm8Mesrchannel29Index
		INTEGER,
	pmopm8Mesrchannel29Portn
		INTEGER
	}


pmopm8Mesrchannel29Index OBJECT-TYPE
	SYNTAX  INTEGER(0..128)
	MAX-ACCESS  read-only
	STATUS current
	DESCRIPTION
        "
        Index definition for the pmopm8Mesrchannel29
        table
        "
	::= { pmopm8Mesrchannel29Entry 1 }


pmopm8Mesrchannel29Portn OBJECT-TYPE
	SYNTAX  INTEGER (0..65535)
	MAX-ACCESS read-only
	STATUS current
	DESCRIPTION
        "
        Channel29 Power :This OID indicates
        the channel power  (Power =Q8(Number
        format)) (Unit = dBm)  <Help> This
        measure indicates the channel power
        "
	::= { pmopm8Mesrchannel29Entry 2 }


--- *********************************************************
---     TABLE for the pmopm8Mesrchannel30 articles
--- *********************************************************

pmopm8Mesrchannel30Table OBJECT-TYPE
	SYNTAX  SEQUENCE OF Pmopm8Mesrchannel30Entry
	MAX-ACCESS not-accessible
	STATUS current
	DESCRIPTION
        "
        List of pmopm8Mesrchannel30 Article
        "
	::= { pmopm8MesrClient 248 }


pmopm8Mesrchannel30Entry OBJECT-TYPE
	SYNTAX Pmopm8Mesrchannel30Entry
	MAX-ACCESS not-accessible
	STATUS current
	DESCRIPTION
        "
        Row definition for the pmopm8Mesrchannel30
        table
        "
	INDEX   { pmopm8Mesrchannel30Index }
	::= { pmopm8Mesrchannel30Table 1 }


Pmopm8Mesrchannel30Entry ::=
	SEQUENCE {
	pmopm8Mesrchannel30Index
		INTEGER,
	pmopm8Mesrchannel30Portn
		INTEGER
	}


pmopm8Mesrchannel30Index OBJECT-TYPE
	SYNTAX  INTEGER(0..128)
	MAX-ACCESS  read-only
	STATUS current
	DESCRIPTION
        "
        Index definition for the pmopm8Mesrchannel30
        table
        "
	::= { pmopm8Mesrchannel30Entry 1 }


pmopm8Mesrchannel30Portn OBJECT-TYPE
	SYNTAX  INTEGER (0..65535)
	MAX-ACCESS read-only
	STATUS current
	DESCRIPTION
        "
        Channel30 Power :This OID indicates
        the channel power  (Power =Q8(Number
        format)) (Unit = dBm)  <Help> This
        measure indicates the channel power
        "
	::= { pmopm8Mesrchannel30Entry 2 }


--- *********************************************************
---     TABLE for the pmopm8Mesrchannel31 articles
--- *********************************************************

pmopm8Mesrchannel31Table OBJECT-TYPE
	SYNTAX  SEQUENCE OF Pmopm8Mesrchannel31Entry
	MAX-ACCESS not-accessible
	STATUS current
	DESCRIPTION
        "
        List of pmopm8Mesrchannel31 Article
        "
	::= { pmopm8MesrClient 256 }


pmopm8Mesrchannel31Entry OBJECT-TYPE
	SYNTAX Pmopm8Mesrchannel31Entry
	MAX-ACCESS not-accessible
	STATUS current
	DESCRIPTION
        "
        Row definition for the pmopm8Mesrchannel31
        table
        "
	INDEX   { pmopm8Mesrchannel31Index }
	::= { pmopm8Mesrchannel31Table 1 }


Pmopm8Mesrchannel31Entry ::=
	SEQUENCE {
	pmopm8Mesrchannel31Index
		INTEGER,
	pmopm8Mesrchannel31Portn
		INTEGER
	}


pmopm8Mesrchannel31Index OBJECT-TYPE
	SYNTAX  INTEGER(0..128)
	MAX-ACCESS  read-only
	STATUS current
	DESCRIPTION
        "
        Index definition for the pmopm8Mesrchannel31
        table
        "
	::= { pmopm8Mesrchannel31Entry 1 }


pmopm8Mesrchannel31Portn OBJECT-TYPE
	SYNTAX  INTEGER (0..65535)
	MAX-ACCESS read-only
	STATUS current
	DESCRIPTION
        "
        Channel31 Power :This OID indicates
        the channel power  (Power =Q8(Number
        format)) (Unit = dBm)  <Help> This
        measure indicates the channel power
        "
	::= { pmopm8Mesrchannel31Entry 2 }


--- *********************************************************
---     TABLE for the pmopm8Mesrchannel32 articles
--- *********************************************************

pmopm8Mesrchannel32Table OBJECT-TYPE
	SYNTAX  SEQUENCE OF Pmopm8Mesrchannel32Entry
	MAX-ACCESS not-accessible
	STATUS current
	DESCRIPTION
        "
        List of pmopm8Mesrchannel32 Article
        "
	::= { pmopm8MesrClient 264 }


pmopm8Mesrchannel32Entry OBJECT-TYPE
	SYNTAX Pmopm8Mesrchannel32Entry
	MAX-ACCESS not-accessible
	STATUS current
	DESCRIPTION
        "
        Row definition for the pmopm8Mesrchannel32
        table
        "
	INDEX   { pmopm8Mesrchannel32Index }
	::= { pmopm8Mesrchannel32Table 1 }


Pmopm8Mesrchannel32Entry ::=
	SEQUENCE {
	pmopm8Mesrchannel32Index
		INTEGER,
	pmopm8Mesrchannel32Portn
		INTEGER
	}


pmopm8Mesrchannel32Index OBJECT-TYPE
	SYNTAX  INTEGER(0..128)
	MAX-ACCESS  read-only
	STATUS current
	DESCRIPTION
        "
        Index definition for the pmopm8Mesrchannel32
        table
        "
	::= { pmopm8Mesrchannel32Entry 1 }


pmopm8Mesrchannel32Portn OBJECT-TYPE
	SYNTAX  INTEGER (0..65535)
	MAX-ACCESS read-only
	STATUS current
	DESCRIPTION
        "
        Channel32 Power :This OID indicates
        the channel power  (Power =Q8(Number
        format)) (Unit = dBm)  <Help> This
        measure indicates the channel power
        "
	::= { pmopm8Mesrchannel32Entry 2 }


--- *********************************************************
---     TABLE for the pmopm8Mesrchannel33 articles
--- *********************************************************

pmopm8Mesrchannel33Table OBJECT-TYPE
	SYNTAX  SEQUENCE OF Pmopm8Mesrchannel33Entry
	MAX-ACCESS not-accessible
	STATUS current
	DESCRIPTION
        "
        List of pmopm8Mesrchannel33 Article
        "
	::= { pmopm8MesrClient 272 }


pmopm8Mesrchannel33Entry OBJECT-TYPE
	SYNTAX Pmopm8Mesrchannel33Entry
	MAX-ACCESS not-accessible
	STATUS current
	DESCRIPTION
        "
        Row definition for the pmopm8Mesrchannel33
        table
        "
	INDEX   { pmopm8Mesrchannel33Index }
	::= { pmopm8Mesrchannel33Table 1 }


Pmopm8Mesrchannel33Entry ::=
	SEQUENCE {
	pmopm8Mesrchannel33Index
		INTEGER,
	pmopm8Mesrchannel33Portn
		INTEGER
	}


pmopm8Mesrchannel33Index OBJECT-TYPE
	SYNTAX  INTEGER(0..128)
	MAX-ACCESS  read-only
	STATUS current
	DESCRIPTION
        "
        Index definition for the pmopm8Mesrchannel33
        table
        "
	::= { pmopm8Mesrchannel33Entry 1 }


pmopm8Mesrchannel33Portn OBJECT-TYPE
	SYNTAX  INTEGER (0..65535)
	MAX-ACCESS read-only
	STATUS current
	DESCRIPTION
        "
        Channel33 Power :This OID indicates
        the channel power  (Power =Q8(Number
        format)) (Unit = dBm)  <Help> This
        measure indicates the channel power
        "
	::= { pmopm8Mesrchannel33Entry 2 }


--- *********************************************************
---     TABLE for the pmopm8Mesrchannel34 articles
--- *********************************************************

pmopm8Mesrchannel34Table OBJECT-TYPE
	SYNTAX  SEQUENCE OF Pmopm8Mesrchannel34Entry
	MAX-ACCESS not-accessible
	STATUS current
	DESCRIPTION
        "
        List of pmopm8Mesrchannel34 Article
        "
	::= { pmopm8MesrClient 280 }


pmopm8Mesrchannel34Entry OBJECT-TYPE
	SYNTAX Pmopm8Mesrchannel34Entry
	MAX-ACCESS not-accessible
	STATUS current
	DESCRIPTION
        "
        Row definition for the pmopm8Mesrchannel34
        table
        "
	INDEX   { pmopm8Mesrchannel34Index }
	::= { pmopm8Mesrchannel34Table 1 }


Pmopm8Mesrchannel34Entry ::=
	SEQUENCE {
	pmopm8Mesrchannel34Index
		INTEGER,
	pmopm8Mesrchannel34Portn
		INTEGER
	}


pmopm8Mesrchannel34Index OBJECT-TYPE
	SYNTAX  INTEGER(0..128)
	MAX-ACCESS  read-only
	STATUS current
	DESCRIPTION
        "
        Index definition for the pmopm8Mesrchannel34
        table
        "
	::= { pmopm8Mesrchannel34Entry 1 }


pmopm8Mesrchannel34Portn OBJECT-TYPE
	SYNTAX  INTEGER (0..65535)
	MAX-ACCESS read-only
	STATUS current
	DESCRIPTION
        "
        Channel34 Power :This OID indicates
        the channel power  (Power =Q8(Number
        format)) (Unit = dBm)  <Help> This
        measure indicates the channel power
        "
	::= { pmopm8Mesrchannel34Entry 2 }


--- *********************************************************
---     TABLE for the pmopm8Mesrchannel35 articles
--- *********************************************************

pmopm8Mesrchannel35Table OBJECT-TYPE
	SYNTAX  SEQUENCE OF Pmopm8Mesrchannel35Entry
	MAX-ACCESS not-accessible
	STATUS current
	DESCRIPTION
        "
        List of pmopm8Mesrchannel35 Article
        "
	::= { pmopm8MesrClient 288 }


pmopm8Mesrchannel35Entry OBJECT-TYPE
	SYNTAX Pmopm8Mesrchannel35Entry
	MAX-ACCESS not-accessible
	STATUS current
	DESCRIPTION
        "
        Row definition for the pmopm8Mesrchannel35
        table
        "
	INDEX   { pmopm8Mesrchannel35Index }
	::= { pmopm8Mesrchannel35Table 1 }


Pmopm8Mesrchannel35Entry ::=
	SEQUENCE {
	pmopm8Mesrchannel35Index
		INTEGER,
	pmopm8Mesrchannel35Portn
		INTEGER
	}


pmopm8Mesrchannel35Index OBJECT-TYPE
	SYNTAX  INTEGER(0..128)
	MAX-ACCESS  read-only
	STATUS current
	DESCRIPTION
        "
        Index definition for the pmopm8Mesrchannel35
        table
        "
	::= { pmopm8Mesrchannel35Entry 1 }


pmopm8Mesrchannel35Portn OBJECT-TYPE
	SYNTAX  INTEGER (0..65535)
	MAX-ACCESS read-only
	STATUS current
	DESCRIPTION
        "
        Channel35 Power :This OID indicates
        the channel power  (Power =Q8(Number
        format)) (Unit = dBm)  <Help> This
        measure indicates the channel power
        "
	::= { pmopm8Mesrchannel35Entry 2 }


--- *********************************************************
---     TABLE for the pmopm8Mesrchannel36 articles
--- *********************************************************

pmopm8Mesrchannel36Table OBJECT-TYPE
	SYNTAX  SEQUENCE OF Pmopm8Mesrchannel36Entry
	MAX-ACCESS not-accessible
	STATUS current
	DESCRIPTION
        "
        List of pmopm8Mesrchannel36 Article
        "
	::= { pmopm8MesrClient 296 }


pmopm8Mesrchannel36Entry OBJECT-TYPE
	SYNTAX Pmopm8Mesrchannel36Entry
	MAX-ACCESS not-accessible
	STATUS current
	DESCRIPTION
        "
        Row definition for the pmopm8Mesrchannel36
        table
        "
	INDEX   { pmopm8Mesrchannel36Index }
	::= { pmopm8Mesrchannel36Table 1 }


Pmopm8Mesrchannel36Entry ::=
	SEQUENCE {
	pmopm8Mesrchannel36Index
		INTEGER,
	pmopm8Mesrchannel36Portn
		INTEGER
	}


pmopm8Mesrchannel36Index OBJECT-TYPE
	SYNTAX  INTEGER(0..128)
	MAX-ACCESS  read-only
	STATUS current
	DESCRIPTION
        "
        Index definition for the pmopm8Mesrchannel36
        table
        "
	::= { pmopm8Mesrchannel36Entry 1 }


pmopm8Mesrchannel36Portn OBJECT-TYPE
	SYNTAX  INTEGER (0..65535)
	MAX-ACCESS read-only
	STATUS current
	DESCRIPTION
        "
        Channel36 Power :This OID indicates
        the channel power  (Power =Q8(Number
        format)) (Unit = dBm)  <Help> This
        measure indicates the channel power
        "
	::= { pmopm8Mesrchannel36Entry 2 }


--- *********************************************************
---     TABLE for the pmopm8Mesrchannel37 articles
--- *********************************************************

pmopm8Mesrchannel37Table OBJECT-TYPE
	SYNTAX  SEQUENCE OF Pmopm8Mesrchannel37Entry
	MAX-ACCESS not-accessible
	STATUS current
	DESCRIPTION
        "
        List of pmopm8Mesrchannel37 Article
        "
	::= { pmopm8MesrClient 304 }


pmopm8Mesrchannel37Entry OBJECT-TYPE
	SYNTAX Pmopm8Mesrchannel37Entry
	MAX-ACCESS not-accessible
	STATUS current
	DESCRIPTION
        "
        Row definition for the pmopm8Mesrchannel37
        table
        "
	INDEX   { pmopm8Mesrchannel37Index }
	::= { pmopm8Mesrchannel37Table 1 }


Pmopm8Mesrchannel37Entry ::=
	SEQUENCE {
	pmopm8Mesrchannel37Index
		INTEGER,
	pmopm8Mesrchannel37Portn
		INTEGER
	}


pmopm8Mesrchannel37Index OBJECT-TYPE
	SYNTAX  INTEGER(0..128)
	MAX-ACCESS  read-only
	STATUS current
	DESCRIPTION
        "
        Index definition for the pmopm8Mesrchannel37
        table
        "
	::= { pmopm8Mesrchannel37Entry 1 }


pmopm8Mesrchannel37Portn OBJECT-TYPE
	SYNTAX  INTEGER (0..65535)
	MAX-ACCESS read-only
	STATUS current
	DESCRIPTION
        "
        Channel37 Power :This OID indicates
        the channel power  (Power =Q8(Number
        format)) (Unit = dBm)  <Help> This
        measure indicates the channel power
        "
	::= { pmopm8Mesrchannel37Entry 2 }


--- *********************************************************
---     TABLE for the pmopm8Mesrchannel38 articles
--- *********************************************************

pmopm8Mesrchannel38Table OBJECT-TYPE
	SYNTAX  SEQUENCE OF Pmopm8Mesrchannel38Entry
	MAX-ACCESS not-accessible
	STATUS current
	DESCRIPTION
        "
        List of pmopm8Mesrchannel38 Article
        "
	::= { pmopm8MesrClient 312 }


pmopm8Mesrchannel38Entry OBJECT-TYPE
	SYNTAX Pmopm8Mesrchannel38Entry
	MAX-ACCESS not-accessible
	STATUS current
	DESCRIPTION
        "
        Row definition for the pmopm8Mesrchannel38
        table
        "
	INDEX   { pmopm8Mesrchannel38Index }
	::= { pmopm8Mesrchannel38Table 1 }


Pmopm8Mesrchannel38Entry ::=
	SEQUENCE {
	pmopm8Mesrchannel38Index
		INTEGER,
	pmopm8Mesrchannel38Portn
		INTEGER
	}


pmopm8Mesrchannel38Index OBJECT-TYPE
	SYNTAX  INTEGER(0..128)
	MAX-ACCESS  read-only
	STATUS current
	DESCRIPTION
        "
        Index definition for the pmopm8Mesrchannel38
        table
        "
	::= { pmopm8Mesrchannel38Entry 1 }


pmopm8Mesrchannel38Portn OBJECT-TYPE
	SYNTAX  INTEGER (0..65535)
	MAX-ACCESS read-only
	STATUS current
	DESCRIPTION
        "
        Channel38 Power :This OID indicates
        the channel power  (Power =Q8(Number
        format)) (Unit = dBm)  <Help> This
        measure indicates the channel power
        "
	::= { pmopm8Mesrchannel38Entry 2 }


--- *********************************************************
---     TABLE for the pmopm8Mesrchannel39 articles
--- *********************************************************

pmopm8Mesrchannel39Table OBJECT-TYPE
	SYNTAX  SEQUENCE OF Pmopm8Mesrchannel39Entry
	MAX-ACCESS not-accessible
	STATUS current
	DESCRIPTION
        "
        List of pmopm8Mesrchannel39 Article
        "
	::= { pmopm8MesrClient 320 }


pmopm8Mesrchannel39Entry OBJECT-TYPE
	SYNTAX Pmopm8Mesrchannel39Entry
	MAX-ACCESS not-accessible
	STATUS current
	DESCRIPTION
        "
        Row definition for the pmopm8Mesrchannel39
        table
        "
	INDEX   { pmopm8Mesrchannel39Index }
	::= { pmopm8Mesrchannel39Table 1 }


Pmopm8Mesrchannel39Entry ::=
	SEQUENCE {
	pmopm8Mesrchannel39Index
		INTEGER,
	pmopm8Mesrchannel39Portn
		INTEGER
	}


pmopm8Mesrchannel39Index OBJECT-TYPE
	SYNTAX  INTEGER(0..128)
	MAX-ACCESS  read-only
	STATUS current
	DESCRIPTION
        "
        Index definition for the pmopm8Mesrchannel39
        table
        "
	::= { pmopm8Mesrchannel39Entry 1 }


pmopm8Mesrchannel39Portn OBJECT-TYPE
	SYNTAX  INTEGER (0..65535)
	MAX-ACCESS read-only
	STATUS current
	DESCRIPTION
        "
        Channel39 Power :This OID indicates
        the channel power  (Power =Q8(Number
        format)) (Unit = dBm)  <Help> This
        measure indicates the channel power
        "
	::= { pmopm8Mesrchannel39Entry 2 }


--- *********************************************************
---     TABLE for the pmopm8Mesrchannel40 articles
--- *********************************************************

pmopm8Mesrchannel40Table OBJECT-TYPE
	SYNTAX  SEQUENCE OF Pmopm8Mesrchannel40Entry
	MAX-ACCESS not-accessible
	STATUS current
	DESCRIPTION
        "
        List of pmopm8Mesrchannel40 Article
        "
	::= { pmopm8MesrClient 328 }


pmopm8Mesrchannel40Entry OBJECT-TYPE
	SYNTAX Pmopm8Mesrchannel40Entry
	MAX-ACCESS not-accessible
	STATUS current
	DESCRIPTION
        "
        Row definition for the pmopm8Mesrchannel40
        table
        "
	INDEX   { pmopm8Mesrchannel40Index }
	::= { pmopm8Mesrchannel40Table 1 }


Pmopm8Mesrchannel40Entry ::=
	SEQUENCE {
	pmopm8Mesrchannel40Index
		INTEGER,
	pmopm8Mesrchannel40Portn
		INTEGER
	}


pmopm8Mesrchannel40Index OBJECT-TYPE
	SYNTAX  INTEGER(0..128)
	MAX-ACCESS  read-only
	STATUS current
	DESCRIPTION
        "
        Index definition for the pmopm8Mesrchannel40
        table
        "
	::= { pmopm8Mesrchannel40Entry 1 }


pmopm8Mesrchannel40Portn OBJECT-TYPE
	SYNTAX  INTEGER (0..65535)
	MAX-ACCESS read-only
	STATUS current
	DESCRIPTION
        "
        Channel40 Power :This OID indicates
        the channel power  (Power =Q8(Number
        format)) (Unit = dBm)  <Help> This
        measure indicates the channel power
        "
	::= { pmopm8Mesrchannel40Entry 2 }


--- *********************************************************
---     TABLE for the pmopm8Mesrchannel41 articles
--- *********************************************************

pmopm8Mesrchannel41Table OBJECT-TYPE
	SYNTAX  SEQUENCE OF Pmopm8Mesrchannel41Entry
	MAX-ACCESS not-accessible
	STATUS current
	DESCRIPTION
        "
        List of pmopm8Mesrchannel41 Article
        "
	::= { pmopm8MesrClient 336 }


pmopm8Mesrchannel41Entry OBJECT-TYPE
	SYNTAX Pmopm8Mesrchannel41Entry
	MAX-ACCESS not-accessible
	STATUS current
	DESCRIPTION
        "
        Row definition for the pmopm8Mesrchannel41
        table
        "
	INDEX   { pmopm8Mesrchannel41Index }
	::= { pmopm8Mesrchannel41Table 1 }


Pmopm8Mesrchannel41Entry ::=
	SEQUENCE {
	pmopm8Mesrchannel41Index
		INTEGER,
	pmopm8Mesrchannel41Portn
		INTEGER
	}


pmopm8Mesrchannel41Index OBJECT-TYPE
	SYNTAX  INTEGER(0..128)
	MAX-ACCESS  read-only
	STATUS current
	DESCRIPTION
        "
        Index definition for the pmopm8Mesrchannel41
        table
        "
	::= { pmopm8Mesrchannel41Entry 1 }


pmopm8Mesrchannel41Portn OBJECT-TYPE
	SYNTAX  INTEGER (0..65535)
	MAX-ACCESS read-only
	STATUS current
	DESCRIPTION
        "
        Channel41 Power :This OID indicates
        the channel power  (Power =Q8(Number
        format)) (Unit = dBm)  <Help> This
        measure indicates the channel power
        "
	::= { pmopm8Mesrchannel41Entry 2 }


--- *********************************************************
---     TABLE for the pmopm8Mesrchannel42 articles
--- *********************************************************

pmopm8Mesrchannel42Table OBJECT-TYPE
	SYNTAX  SEQUENCE OF Pmopm8Mesrchannel42Entry
	MAX-ACCESS not-accessible
	STATUS current
	DESCRIPTION
        "
        List of pmopm8Mesrchannel42 Article
        "
	::= { pmopm8MesrClient 344 }


pmopm8Mesrchannel42Entry OBJECT-TYPE
	SYNTAX Pmopm8Mesrchannel42Entry
	MAX-ACCESS not-accessible
	STATUS current
	DESCRIPTION
        "
        Row definition for the pmopm8Mesrchannel42
        table
        "
	INDEX   { pmopm8Mesrchannel42Index }
	::= { pmopm8Mesrchannel42Table 1 }


Pmopm8Mesrchannel42Entry ::=
	SEQUENCE {
	pmopm8Mesrchannel42Index
		INTEGER,
	pmopm8Mesrchannel42Portn
		INTEGER
	}


pmopm8Mesrchannel42Index OBJECT-TYPE
	SYNTAX  INTEGER(0..128)
	MAX-ACCESS  read-only
	STATUS current
	DESCRIPTION
        "
        Index definition for the pmopm8Mesrchannel42
        table
        "
	::= { pmopm8Mesrchannel42Entry 1 }


pmopm8Mesrchannel42Portn OBJECT-TYPE
	SYNTAX  INTEGER (0..65535)
	MAX-ACCESS read-only
	STATUS current
	DESCRIPTION
        "
        Channel42 Power :This OID indicates
        the channel power  (Power =Q8(Number
        format)) (Unit = dBm)  <Help> This
        measure indicates the channel power
        "
	::= { pmopm8Mesrchannel42Entry 2 }


--- *********************************************************
---     TABLE for the pmopm8Mesrchannel43 articles
--- *********************************************************

pmopm8Mesrchannel43Table OBJECT-TYPE
	SYNTAX  SEQUENCE OF Pmopm8Mesrchannel43Entry
	MAX-ACCESS not-accessible
	STATUS current
	DESCRIPTION
        "
        List of pmopm8Mesrchannel43 Article
        "
	::= { pmopm8MesrClient 352 }


pmopm8Mesrchannel43Entry OBJECT-TYPE
	SYNTAX Pmopm8Mesrchannel43Entry
	MAX-ACCESS not-accessible
	STATUS current
	DESCRIPTION
        "
        Row definition for the pmopm8Mesrchannel43
        table
        "
	INDEX   { pmopm8Mesrchannel43Index }
	::= { pmopm8Mesrchannel43Table 1 }


Pmopm8Mesrchannel43Entry ::=
	SEQUENCE {
	pmopm8Mesrchannel43Index
		INTEGER,
	pmopm8Mesrchannel43Portn
		INTEGER
	}


pmopm8Mesrchannel43Index OBJECT-TYPE
	SYNTAX  INTEGER(0..128)
	MAX-ACCESS  read-only
	STATUS current
	DESCRIPTION
        "
        Index definition for the pmopm8Mesrchannel43
        table
        "
	::= { pmopm8Mesrchannel43Entry 1 }


pmopm8Mesrchannel43Portn OBJECT-TYPE
	SYNTAX  INTEGER (0..65535)
	MAX-ACCESS read-only
	STATUS current
	DESCRIPTION
        "
        Channel43 Power :This OID indicates
        the channel power  (Power =Q8(Number
        format)) (Unit = dBm)  <Help> This
        measure indicates the channel power
        "
	::= { pmopm8Mesrchannel43Entry 2 }


--- *********************************************************
---     TABLE for the pmopm8Mesrchannel44 articles
--- *********************************************************

pmopm8Mesrchannel44Table OBJECT-TYPE
	SYNTAX  SEQUENCE OF Pmopm8Mesrchannel44Entry
	MAX-ACCESS not-accessible
	STATUS current
	DESCRIPTION
        "
        List of pmopm8Mesrchannel44 Article
        "
	::= { pmopm8MesrClient 360 }


pmopm8Mesrchannel44Entry OBJECT-TYPE
	SYNTAX Pmopm8Mesrchannel44Entry
	MAX-ACCESS not-accessible
	STATUS current
	DESCRIPTION
        "
        Row definition for the pmopm8Mesrchannel44
        table
        "
	INDEX   { pmopm8Mesrchannel44Index }
	::= { pmopm8Mesrchannel44Table 1 }


Pmopm8Mesrchannel44Entry ::=
	SEQUENCE {
	pmopm8Mesrchannel44Index
		INTEGER,
	pmopm8Mesrchannel44Portn
		INTEGER
	}


pmopm8Mesrchannel44Index OBJECT-TYPE
	SYNTAX  INTEGER(0..128)
	MAX-ACCESS  read-only
	STATUS current
	DESCRIPTION
        "
        Index definition for the pmopm8Mesrchannel44
        table
        "
	::= { pmopm8Mesrchannel44Entry 1 }


pmopm8Mesrchannel44Portn OBJECT-TYPE
	SYNTAX  INTEGER (0..65535)
	MAX-ACCESS read-only
	STATUS current
	DESCRIPTION
        "
        Channel44 Power :This OID indicates
        the channel power  (Power =Q8(Number
        format)) (Unit = dBm)  <Help> This
        measure indicates the channel power
        "
	::= { pmopm8Mesrchannel44Entry 2 }


--- *********************************************************
---     TABLE for the pmopm8Mesrchannel45 articles
--- *********************************************************

pmopm8Mesrchannel45Table OBJECT-TYPE
	SYNTAX  SEQUENCE OF Pmopm8Mesrchannel45Entry
	MAX-ACCESS not-accessible
	STATUS current
	DESCRIPTION
        "
        List of pmopm8Mesrchannel45 Article
        "
	::= { pmopm8MesrClient 368 }


pmopm8Mesrchannel45Entry OBJECT-TYPE
	SYNTAX Pmopm8Mesrchannel45Entry
	MAX-ACCESS not-accessible
	STATUS current
	DESCRIPTION
        "
        Row definition for the pmopm8Mesrchannel45
        table
        "
	INDEX   { pmopm8Mesrchannel45Index }
	::= { pmopm8Mesrchannel45Table 1 }


Pmopm8Mesrchannel45Entry ::=
	SEQUENCE {
	pmopm8Mesrchannel45Index
		INTEGER,
	pmopm8Mesrchannel45Portn
		INTEGER
	}


pmopm8Mesrchannel45Index OBJECT-TYPE
	SYNTAX  INTEGER(0..128)
	MAX-ACCESS  read-only
	STATUS current
	DESCRIPTION
        "
        Index definition for the pmopm8Mesrchannel45
        table
        "
	::= { pmopm8Mesrchannel45Entry 1 }


pmopm8Mesrchannel45Portn OBJECT-TYPE
	SYNTAX  INTEGER (0..65535)
	MAX-ACCESS read-only
	STATUS current
	DESCRIPTION
        "
        Channel45 Power :This OID indicates
        the channel power  (Power =Q8(Number
        format)) (Unit = dBm)  <Help> This
        measure indicates the channel power
        "
	::= { pmopm8Mesrchannel45Entry 2 }


--- *********************************************************
---     TABLE for the pmopm8Mesrchannel46 articles
--- *********************************************************

pmopm8Mesrchannel46Table OBJECT-TYPE
	SYNTAX  SEQUENCE OF Pmopm8Mesrchannel46Entry
	MAX-ACCESS not-accessible
	STATUS current
	DESCRIPTION
        "
        List of pmopm8Mesrchannel46 Article
        "
	::= { pmopm8MesrClient 376 }


pmopm8Mesrchannel46Entry OBJECT-TYPE
	SYNTAX Pmopm8Mesrchannel46Entry
	MAX-ACCESS not-accessible
	STATUS current
	DESCRIPTION
        "
        Row definition for the pmopm8Mesrchannel46
        table
        "
	INDEX   { pmopm8Mesrchannel46Index }
	::= { pmopm8Mesrchannel46Table 1 }


Pmopm8Mesrchannel46Entry ::=
	SEQUENCE {
	pmopm8Mesrchannel46Index
		INTEGER,
	pmopm8Mesrchannel46Portn
		INTEGER
	}


pmopm8Mesrchannel46Index OBJECT-TYPE
	SYNTAX  INTEGER(0..128)
	MAX-ACCESS  read-only
	STATUS current
	DESCRIPTION
        "
        Index definition for the pmopm8Mesrchannel46
        table
        "
	::= { pmopm8Mesrchannel46Entry 1 }


pmopm8Mesrchannel46Portn OBJECT-TYPE
	SYNTAX  INTEGER (0..65535)
	MAX-ACCESS read-only
	STATUS current
	DESCRIPTION
        "
        Channel46 Power :This OID indicates
        the channel power  (Power =Q8(Number
        format)) (Unit = dBm)  <Help> This
        measure indicates the channel power
        "
	::= { pmopm8Mesrchannel46Entry 2 }


--- *********************************************************
---     TABLE for the pmopm8Mesrchannel47 articles
--- *********************************************************

pmopm8Mesrchannel47Table OBJECT-TYPE
	SYNTAX  SEQUENCE OF Pmopm8Mesrchannel47Entry
	MAX-ACCESS not-accessible
	STATUS current
	DESCRIPTION
        "
        List of pmopm8Mesrchannel47 Article
        "
	::= { pmopm8MesrClient 384 }


pmopm8Mesrchannel47Entry OBJECT-TYPE
	SYNTAX Pmopm8Mesrchannel47Entry
	MAX-ACCESS not-accessible
	STATUS current
	DESCRIPTION
        "
        Row definition for the pmopm8Mesrchannel47
        table
        "
	INDEX   { pmopm8Mesrchannel47Index }
	::= { pmopm8Mesrchannel47Table 1 }


Pmopm8Mesrchannel47Entry ::=
	SEQUENCE {
	pmopm8Mesrchannel47Index
		INTEGER,
	pmopm8Mesrchannel47Portn
		INTEGER
	}


pmopm8Mesrchannel47Index OBJECT-TYPE
	SYNTAX  INTEGER(0..128)
	MAX-ACCESS  read-only
	STATUS current
	DESCRIPTION
        "
        Index definition for the pmopm8Mesrchannel47
        table
        "
	::= { pmopm8Mesrchannel47Entry 1 }


pmopm8Mesrchannel47Portn OBJECT-TYPE
	SYNTAX  INTEGER (0..65535)
	MAX-ACCESS read-only
	STATUS current
	DESCRIPTION
        "
        Channel47 Power :This OID indicates
        the channel power  (Power =Q8(Number
        format)) (Unit = dBm)  <Help> This
        measure indicates the channel power
        "
	::= { pmopm8Mesrchannel47Entry 2 }


--- *********************************************************
---     TABLE for the pmopm8Mesrchannel48 articles
--- *********************************************************

pmopm8Mesrchannel48Table OBJECT-TYPE
	SYNTAX  SEQUENCE OF Pmopm8Mesrchannel48Entry
	MAX-ACCESS not-accessible
	STATUS current
	DESCRIPTION
        "
        List of pmopm8Mesrchannel48 Article
        "
	::= { pmopm8MesrClient 392 }


pmopm8Mesrchannel48Entry OBJECT-TYPE
	SYNTAX Pmopm8Mesrchannel48Entry
	MAX-ACCESS not-accessible
	STATUS current
	DESCRIPTION
        "
        Row definition for the pmopm8Mesrchannel48
        table
        "
	INDEX   { pmopm8Mesrchannel48Index }
	::= { pmopm8Mesrchannel48Table 1 }


Pmopm8Mesrchannel48Entry ::=
	SEQUENCE {
	pmopm8Mesrchannel48Index
		INTEGER,
	pmopm8Mesrchannel48Portn
		INTEGER
	}


pmopm8Mesrchannel48Index OBJECT-TYPE
	SYNTAX  INTEGER(0..128)
	MAX-ACCESS  read-only
	STATUS current
	DESCRIPTION
        "
        Index definition for the pmopm8Mesrchannel48
        table
        "
	::= { pmopm8Mesrchannel48Entry 1 }


pmopm8Mesrchannel48Portn OBJECT-TYPE
	SYNTAX  INTEGER (0..65535)
	MAX-ACCESS read-only
	STATUS current
	DESCRIPTION
        "
        Channel48 Power :This OID indicates
        the channel power  (Power =Q8(Number
        format)) (Unit = dBm)  <Help> This
        measure indicates the channel power
        "
	::= { pmopm8Mesrchannel48Entry 2 }


--- *********************************************************
---     TABLE for the pmopm8Mesrchannel49 articles
--- *********************************************************

pmopm8Mesrchannel49Table OBJECT-TYPE
	SYNTAX  SEQUENCE OF Pmopm8Mesrchannel49Entry
	MAX-ACCESS not-accessible
	STATUS current
	DESCRIPTION
        "
        List of pmopm8Mesrchannel49 Article
        "
	::= { pmopm8MesrClient 400 }


pmopm8Mesrchannel49Entry OBJECT-TYPE
	SYNTAX Pmopm8Mesrchannel49Entry
	MAX-ACCESS not-accessible
	STATUS current
	DESCRIPTION
        "
        Row definition for the pmopm8Mesrchannel49
        table
        "
	INDEX   { pmopm8Mesrchannel49Index }
	::= { pmopm8Mesrchannel49Table 1 }


Pmopm8Mesrchannel49Entry ::=
	SEQUENCE {
	pmopm8Mesrchannel49Index
		INTEGER,
	pmopm8Mesrchannel49Portn
		INTEGER
	}


pmopm8Mesrchannel49Index OBJECT-TYPE
	SYNTAX  INTEGER(0..128)
	MAX-ACCESS  read-only
	STATUS current
	DESCRIPTION
        "
        Index definition for the pmopm8Mesrchannel49
        table
        "
	::= { pmopm8Mesrchannel49Entry 1 }


pmopm8Mesrchannel49Portn OBJECT-TYPE
	SYNTAX  INTEGER (0..65535)
	MAX-ACCESS read-only
	STATUS current
	DESCRIPTION
        "
        Channel49 Power :This OID indicates
        the channel power  (Power =Q8(Number
        format)) (Unit = dBm)  <Help> This
        measure indicates the channel power
        "
	::= { pmopm8Mesrchannel49Entry 2 }


--- *********************************************************
---     TABLE for the pmopm8Mesrchannel50 articles
--- *********************************************************

pmopm8Mesrchannel50Table OBJECT-TYPE
	SYNTAX  SEQUENCE OF Pmopm8Mesrchannel50Entry
	MAX-ACCESS not-accessible
	STATUS current
	DESCRIPTION
        "
        List of pmopm8Mesrchannel50 Article
        "
	::= { pmopm8MesrClient 408 }


pmopm8Mesrchannel50Entry OBJECT-TYPE
	SYNTAX Pmopm8Mesrchannel50Entry
	MAX-ACCESS not-accessible
	STATUS current
	DESCRIPTION
        "
        Row definition for the pmopm8Mesrchannel50
        table
        "
	INDEX   { pmopm8Mesrchannel50Index }
	::= { pmopm8Mesrchannel50Table 1 }


Pmopm8Mesrchannel50Entry ::=
	SEQUENCE {
	pmopm8Mesrchannel50Index
		INTEGER,
	pmopm8Mesrchannel50Portn
		INTEGER
	}


pmopm8Mesrchannel50Index OBJECT-TYPE
	SYNTAX  INTEGER(0..128)
	MAX-ACCESS  read-only
	STATUS current
	DESCRIPTION
        "
        Index definition for the pmopm8Mesrchannel50
        table
        "
	::= { pmopm8Mesrchannel50Entry 1 }


pmopm8Mesrchannel50Portn OBJECT-TYPE
	SYNTAX  INTEGER (0..65535)
	MAX-ACCESS read-only
	STATUS current
	DESCRIPTION
        "
        Channel50 Power :This OID indicates
        the channel power  (Power =Q8(Number
        format)) (Unit = dBm)  <Help> This
        measure indicates the channel power
        "
	::= { pmopm8Mesrchannel50Entry 2 }


--- *********************************************************
---     TABLE for the pmopm8Mesrchannel51 articles
--- *********************************************************

pmopm8Mesrchannel51Table OBJECT-TYPE
	SYNTAX  SEQUENCE OF Pmopm8Mesrchannel51Entry
	MAX-ACCESS not-accessible
	STATUS current
	DESCRIPTION
        "
        List of pmopm8Mesrchannel51 Article
        "
	::= { pmopm8MesrClient 416 }


pmopm8Mesrchannel51Entry OBJECT-TYPE
	SYNTAX Pmopm8Mesrchannel51Entry
	MAX-ACCESS not-accessible
	STATUS current
	DESCRIPTION
        "
        Row definition for the pmopm8Mesrchannel51
        table
        "
	INDEX   { pmopm8Mesrchannel51Index }
	::= { pmopm8Mesrchannel51Table 1 }


Pmopm8Mesrchannel51Entry ::=
	SEQUENCE {
	pmopm8Mesrchannel51Index
		INTEGER,
	pmopm8Mesrchannel51Portn
		INTEGER
	}


pmopm8Mesrchannel51Index OBJECT-TYPE
	SYNTAX  INTEGER(0..128)
	MAX-ACCESS  read-only
	STATUS current
	DESCRIPTION
        "
        Index definition for the pmopm8Mesrchannel51
        table
        "
	::= { pmopm8Mesrchannel51Entry 1 }


pmopm8Mesrchannel51Portn OBJECT-TYPE
	SYNTAX  INTEGER (0..65535)
	MAX-ACCESS read-only
	STATUS current
	DESCRIPTION
        "
        Channel51 Power :This OID indicates
        the channel power  (Power =Q8(Number
        format)) (Unit = dBm)  <Help> This
        measure indicates the channel power
        "
	::= { pmopm8Mesrchannel51Entry 2 }


--- *********************************************************
---     TABLE for the pmopm8Mesrchannel52 articles
--- *********************************************************

pmopm8Mesrchannel52Table OBJECT-TYPE
	SYNTAX  SEQUENCE OF Pmopm8Mesrchannel52Entry
	MAX-ACCESS not-accessible
	STATUS current
	DESCRIPTION
        "
        List of pmopm8Mesrchannel52 Article
        "
	::= { pmopm8MesrClient 424 }


pmopm8Mesrchannel52Entry OBJECT-TYPE
	SYNTAX Pmopm8Mesrchannel52Entry
	MAX-ACCESS not-accessible
	STATUS current
	DESCRIPTION
        "
        Row definition for the pmopm8Mesrchannel52
        table
        "
	INDEX   { pmopm8Mesrchannel52Index }
	::= { pmopm8Mesrchannel52Table 1 }


Pmopm8Mesrchannel52Entry ::=
	SEQUENCE {
	pmopm8Mesrchannel52Index
		INTEGER,
	pmopm8Mesrchannel52Portn
		INTEGER
	}


pmopm8Mesrchannel52Index OBJECT-TYPE
	SYNTAX  INTEGER(0..128)
	MAX-ACCESS  read-only
	STATUS current
	DESCRIPTION
        "
        Index definition for the pmopm8Mesrchannel52
        table
        "
	::= { pmopm8Mesrchannel52Entry 1 }


pmopm8Mesrchannel52Portn OBJECT-TYPE
	SYNTAX  INTEGER (0..65535)
	MAX-ACCESS read-only
	STATUS current
	DESCRIPTION
        "
        Channel52 Power :This OID indicates
        the channel power  (Power =Q8(Number
        format)) (Unit = dBm)  <Help> This
        measure indicates the channel power
        "
	::= { pmopm8Mesrchannel52Entry 2 }


--- *********************************************************
---     TABLE for the pmopm8Mesrchannel53 articles
--- *********************************************************

pmopm8Mesrchannel53Table OBJECT-TYPE
	SYNTAX  SEQUENCE OF Pmopm8Mesrchannel53Entry
	MAX-ACCESS not-accessible
	STATUS current
	DESCRIPTION
        "
        List of pmopm8Mesrchannel53 Article
        "
	::= { pmopm8MesrClient 432 }


pmopm8Mesrchannel53Entry OBJECT-TYPE
	SYNTAX Pmopm8Mesrchannel53Entry
	MAX-ACCESS not-accessible
	STATUS current
	DESCRIPTION
        "
        Row definition for the pmopm8Mesrchannel53
        table
        "
	INDEX   { pmopm8Mesrchannel53Index }
	::= { pmopm8Mesrchannel53Table 1 }


Pmopm8Mesrchannel53Entry ::=
	SEQUENCE {
	pmopm8Mesrchannel53Index
		INTEGER,
	pmopm8Mesrchannel53Portn
		INTEGER
	}


pmopm8Mesrchannel53Index OBJECT-TYPE
	SYNTAX  INTEGER(0..128)
	MAX-ACCESS  read-only
	STATUS current
	DESCRIPTION
        "
        Index definition for the pmopm8Mesrchannel53
        table
        "
	::= { pmopm8Mesrchannel53Entry 1 }


pmopm8Mesrchannel53Portn OBJECT-TYPE
	SYNTAX  INTEGER (0..65535)
	MAX-ACCESS read-only
	STATUS current
	DESCRIPTION
        "
        Channel53 Power :This OID indicates
        the channel power  (Power =Q8(Number
        format)) (Unit = dBm)  <Help> This
        measure indicates the channel power
        "
	::= { pmopm8Mesrchannel53Entry 2 }


--- *********************************************************
---     TABLE for the pmopm8Mesrchannel54 articles
--- *********************************************************

pmopm8Mesrchannel54Table OBJECT-TYPE
	SYNTAX  SEQUENCE OF Pmopm8Mesrchannel54Entry
	MAX-ACCESS not-accessible
	STATUS current
	DESCRIPTION
        "
        List of pmopm8Mesrchannel54 Article
        "
	::= { pmopm8MesrClient 440 }


pmopm8Mesrchannel54Entry OBJECT-TYPE
	SYNTAX Pmopm8Mesrchannel54Entry
	MAX-ACCESS not-accessible
	STATUS current
	DESCRIPTION
        "
        Row definition for the pmopm8Mesrchannel54
        table
        "
	INDEX   { pmopm8Mesrchannel54Index }
	::= { pmopm8Mesrchannel54Table 1 }


Pmopm8Mesrchannel54Entry ::=
	SEQUENCE {
	pmopm8Mesrchannel54Index
		INTEGER,
	pmopm8Mesrchannel54Portn
		INTEGER
	}


pmopm8Mesrchannel54Index OBJECT-TYPE
	SYNTAX  INTEGER(0..128)
	MAX-ACCESS  read-only
	STATUS current
	DESCRIPTION
        "
        Index definition for the pmopm8Mesrchannel54
        table
        "
	::= { pmopm8Mesrchannel54Entry 1 }


pmopm8Mesrchannel54Portn OBJECT-TYPE
	SYNTAX  INTEGER (0..65535)
	MAX-ACCESS read-only
	STATUS current
	DESCRIPTION
        "
        Channel54 Power :This OID indicates
        the channel power  (Power =Q8(Number
        format)) (Unit = dBm)  <Help> This
        measure indicates the channel power
        "
	::= { pmopm8Mesrchannel54Entry 2 }


--- *********************************************************
---     TABLE for the pmopm8Mesrchannel55 articles
--- *********************************************************

pmopm8Mesrchannel55Table OBJECT-TYPE
	SYNTAX  SEQUENCE OF Pmopm8Mesrchannel55Entry
	MAX-ACCESS not-accessible
	STATUS current
	DESCRIPTION
        "
        List of pmopm8Mesrchannel55 Article
        "
	::= { pmopm8MesrClient 448 }


pmopm8Mesrchannel55Entry OBJECT-TYPE
	SYNTAX Pmopm8Mesrchannel55Entry
	MAX-ACCESS not-accessible
	STATUS current
	DESCRIPTION
        "
        Row definition for the pmopm8Mesrchannel55
        table
        "
	INDEX   { pmopm8Mesrchannel55Index }
	::= { pmopm8Mesrchannel55Table 1 }


Pmopm8Mesrchannel55Entry ::=
	SEQUENCE {
	pmopm8Mesrchannel55Index
		INTEGER,
	pmopm8Mesrchannel55Portn
		INTEGER
	}


pmopm8Mesrchannel55Index OBJECT-TYPE
	SYNTAX  INTEGER(0..128)
	MAX-ACCESS  read-only
	STATUS current
	DESCRIPTION
        "
        Index definition for the pmopm8Mesrchannel55
        table
        "
	::= { pmopm8Mesrchannel55Entry 1 }


pmopm8Mesrchannel55Portn OBJECT-TYPE
	SYNTAX  INTEGER (0..65535)
	MAX-ACCESS read-only
	STATUS current
	DESCRIPTION
        "
        Channel55 Power :This OID indicates
        the channel power  (Power =Q8(Number
        format)) (Unit = dBm)  <Help> This
        measure indicates the channel power
        "
	::= { pmopm8Mesrchannel55Entry 2 }


--- *********************************************************
---     TABLE for the pmopm8Mesrchannel56 articles
--- *********************************************************

pmopm8Mesrchannel56Table OBJECT-TYPE
	SYNTAX  SEQUENCE OF Pmopm8Mesrchannel56Entry
	MAX-ACCESS not-accessible
	STATUS current
	DESCRIPTION
        "
        List of pmopm8Mesrchannel56 Article
        "
	::= { pmopm8MesrClient 456 }


pmopm8Mesrchannel56Entry OBJECT-TYPE
	SYNTAX Pmopm8Mesrchannel56Entry
	MAX-ACCESS not-accessible
	STATUS current
	DESCRIPTION
        "
        Row definition for the pmopm8Mesrchannel56
        table
        "
	INDEX   { pmopm8Mesrchannel56Index }
	::= { pmopm8Mesrchannel56Table 1 }


Pmopm8Mesrchannel56Entry ::=
	SEQUENCE {
	pmopm8Mesrchannel56Index
		INTEGER,
	pmopm8Mesrchannel56Portn
		INTEGER
	}


pmopm8Mesrchannel56Index OBJECT-TYPE
	SYNTAX  INTEGER(0..128)
	MAX-ACCESS  read-only
	STATUS current
	DESCRIPTION
        "
        Index definition for the pmopm8Mesrchannel56
        table
        "
	::= { pmopm8Mesrchannel56Entry 1 }


pmopm8Mesrchannel56Portn OBJECT-TYPE
	SYNTAX  INTEGER (0..65535)
	MAX-ACCESS read-only
	STATUS current
	DESCRIPTION
        "
        Channel56 Power :This OID indicates
        the channel power  (Power =Q8(Number
        format)) (Unit = dBm)  <Help> This
        measure indicates the channel power
        "
	::= { pmopm8Mesrchannel56Entry 2 }


--- *********************************************************
---     TABLE for the pmopm8Mesrchannel57 articles
--- *********************************************************

pmopm8Mesrchannel57Table OBJECT-TYPE
	SYNTAX  SEQUENCE OF Pmopm8Mesrchannel57Entry
	MAX-ACCESS not-accessible
	STATUS current
	DESCRIPTION
        "
        List of pmopm8Mesrchannel57 Article
        "
	::= { pmopm8MesrClient 464 }


pmopm8Mesrchannel57Entry OBJECT-TYPE
	SYNTAX Pmopm8Mesrchannel57Entry
	MAX-ACCESS not-accessible
	STATUS current
	DESCRIPTION
        "
        Row definition for the pmopm8Mesrchannel57
        table
        "
	INDEX   { pmopm8Mesrchannel57Index }
	::= { pmopm8Mesrchannel57Table 1 }


Pmopm8Mesrchannel57Entry ::=
	SEQUENCE {
	pmopm8Mesrchannel57Index
		INTEGER,
	pmopm8Mesrchannel57Portn
		INTEGER
	}


pmopm8Mesrchannel57Index OBJECT-TYPE
	SYNTAX  INTEGER(0..128)
	MAX-ACCESS  read-only
	STATUS current
	DESCRIPTION
        "
        Index definition for the pmopm8Mesrchannel57
        table
        "
	::= { pmopm8Mesrchannel57Entry 1 }


pmopm8Mesrchannel57Portn OBJECT-TYPE
	SYNTAX  INTEGER (0..65535)
	MAX-ACCESS read-only
	STATUS current
	DESCRIPTION
        "
        Channel57 Power :This OID indicates
        the channel power  (Power =Q8(Number
        format)) (Unit = dBm)  <Help> This
        measure indicates the channel power
        "
	::= { pmopm8Mesrchannel57Entry 2 }


--- *********************************************************
---     TABLE for the pmopm8Mesrchannel58 articles
--- *********************************************************

pmopm8Mesrchannel58Table OBJECT-TYPE
	SYNTAX  SEQUENCE OF Pmopm8Mesrchannel58Entry
	MAX-ACCESS not-accessible
	STATUS current
	DESCRIPTION
        "
        List of pmopm8Mesrchannel58 Article
        "
	::= { pmopm8MesrClient 472 }


pmopm8Mesrchannel58Entry OBJECT-TYPE
	SYNTAX Pmopm8Mesrchannel58Entry
	MAX-ACCESS not-accessible
	STATUS current
	DESCRIPTION
        "
        Row definition for the pmopm8Mesrchannel58
        table
        "
	INDEX   { pmopm8Mesrchannel58Index }
	::= { pmopm8Mesrchannel58Table 1 }


Pmopm8Mesrchannel58Entry ::=
	SEQUENCE {
	pmopm8Mesrchannel58Index
		INTEGER,
	pmopm8Mesrchannel58Portn
		INTEGER
	}


pmopm8Mesrchannel58Index OBJECT-TYPE
	SYNTAX  INTEGER(0..128)
	MAX-ACCESS  read-only
	STATUS current
	DESCRIPTION
        "
        Index definition for the pmopm8Mesrchannel58
        table
        "
	::= { pmopm8Mesrchannel58Entry 1 }


pmopm8Mesrchannel58Portn OBJECT-TYPE
	SYNTAX  INTEGER (0..65535)
	MAX-ACCESS read-only
	STATUS current
	DESCRIPTION
        "
        Channel58 Power :This OID indicates
        the channel power  (Power =Q8(Number
        format)) (Unit = dBm)  <Help> This
        measure indicates the channel power
        "
	::= { pmopm8Mesrchannel58Entry 2 }


--- *********************************************************
---     TABLE for the pmopm8Mesrchannel59 articles
--- *********************************************************

pmopm8Mesrchannel59Table OBJECT-TYPE
	SYNTAX  SEQUENCE OF Pmopm8Mesrchannel59Entry
	MAX-ACCESS not-accessible
	STATUS current
	DESCRIPTION
        "
        List of pmopm8Mesrchannel59 Article
        "
	::= { pmopm8MesrClient 480 }


pmopm8Mesrchannel59Entry OBJECT-TYPE
	SYNTAX Pmopm8Mesrchannel59Entry
	MAX-ACCESS not-accessible
	STATUS current
	DESCRIPTION
        "
        Row definition for the pmopm8Mesrchannel59
        table
        "
	INDEX   { pmopm8Mesrchannel59Index }
	::= { pmopm8Mesrchannel59Table 1 }


Pmopm8Mesrchannel59Entry ::=
	SEQUENCE {
	pmopm8Mesrchannel59Index
		INTEGER,
	pmopm8Mesrchannel59Portn
		INTEGER
	}


pmopm8Mesrchannel59Index OBJECT-TYPE
	SYNTAX  INTEGER(0..128)
	MAX-ACCESS  read-only
	STATUS current
	DESCRIPTION
        "
        Index definition for the pmopm8Mesrchannel59
        table
        "
	::= { pmopm8Mesrchannel59Entry 1 }


pmopm8Mesrchannel59Portn OBJECT-TYPE
	SYNTAX  INTEGER (0..65535)
	MAX-ACCESS read-only
	STATUS current
	DESCRIPTION
        "
        Channel59 Power :This OID indicates
        the channel power  (Power =Q8(Number
        format)) (Unit = dBm)  <Help> This
        measure indicates the channel power
        "
	::= { pmopm8Mesrchannel59Entry 2 }


--- *********************************************************
---     TABLE for the pmopm8Mesrchannel60 articles
--- *********************************************************

pmopm8Mesrchannel60Table OBJECT-TYPE
	SYNTAX  SEQUENCE OF Pmopm8Mesrchannel60Entry
	MAX-ACCESS not-accessible
	STATUS current
	DESCRIPTION
        "
        List of pmopm8Mesrchannel60 Article
        "
	::= { pmopm8MesrClient 488 }


pmopm8Mesrchannel60Entry OBJECT-TYPE
	SYNTAX Pmopm8Mesrchannel60Entry
	MAX-ACCESS not-accessible
	STATUS current
	DESCRIPTION
        "
        Row definition for the pmopm8Mesrchannel60
        table
        "
	INDEX   { pmopm8Mesrchannel60Index }
	::= { pmopm8Mesrchannel60Table 1 }


Pmopm8Mesrchannel60Entry ::=
	SEQUENCE {
	pmopm8Mesrchannel60Index
		INTEGER,
	pmopm8Mesrchannel60Portn
		INTEGER
	}


pmopm8Mesrchannel60Index OBJECT-TYPE
	SYNTAX  INTEGER(0..128)
	MAX-ACCESS  read-only
	STATUS current
	DESCRIPTION
        "
        Index definition for the pmopm8Mesrchannel60
        table
        "
	::= { pmopm8Mesrchannel60Entry 1 }


pmopm8Mesrchannel60Portn OBJECT-TYPE
	SYNTAX  INTEGER (0..65535)
	MAX-ACCESS read-only
	STATUS current
	DESCRIPTION
        "
        Channel60 Power :This OID indicates
        the channel power  (Power =Q8(Number
        format)) (Unit = dBm)  <Help> This
        measure indicates the channel power
        "
	::= { pmopm8Mesrchannel60Entry 2 }


--- *********************************************************
---     TABLE for the pmopm8Mesrchannel61 articles
--- *********************************************************

pmopm8Mesrchannel61Table OBJECT-TYPE
	SYNTAX  SEQUENCE OF Pmopm8Mesrchannel61Entry
	MAX-ACCESS not-accessible
	STATUS current
	DESCRIPTION
        "
        List of pmopm8Mesrchannel61 Article
        "
	::= { pmopm8MesrClient 496 }


pmopm8Mesrchannel61Entry OBJECT-TYPE
	SYNTAX Pmopm8Mesrchannel61Entry
	MAX-ACCESS not-accessible
	STATUS current
	DESCRIPTION
        "
        Row definition for the pmopm8Mesrchannel61
        table
        "
	INDEX   { pmopm8Mesrchannel61Index }
	::= { pmopm8Mesrchannel61Table 1 }


Pmopm8Mesrchannel61Entry ::=
	SEQUENCE {
	pmopm8Mesrchannel61Index
		INTEGER,
	pmopm8Mesrchannel61Portn
		INTEGER
	}


pmopm8Mesrchannel61Index OBJECT-TYPE
	SYNTAX  INTEGER(0..128)
	MAX-ACCESS  read-only
	STATUS current
	DESCRIPTION
        "
        Index definition for the pmopm8Mesrchannel61
        table
        "
	::= { pmopm8Mesrchannel61Entry 1 }


pmopm8Mesrchannel61Portn OBJECT-TYPE
	SYNTAX  INTEGER (0..65535)
	MAX-ACCESS read-only
	STATUS current
	DESCRIPTION
        "
        Channel61 Power :This OID indicates
        the channel power  (Power =Q8(Number
        format)) (Unit = dBm)  <Help> This
        measure indicates the channel power
        "
	::= { pmopm8Mesrchannel61Entry 2 }


--- *********************************************************
---     TABLE for the pmopm8Mesrchannel62 articles
--- *********************************************************

pmopm8Mesrchannel62Table OBJECT-TYPE
	SYNTAX  SEQUENCE OF Pmopm8Mesrchannel62Entry
	MAX-ACCESS not-accessible
	STATUS current
	DESCRIPTION
        "
        List of pmopm8Mesrchannel62 Article
        "
	::= { pmopm8MesrClient 504 }


pmopm8Mesrchannel62Entry OBJECT-TYPE
	SYNTAX Pmopm8Mesrchannel62Entry
	MAX-ACCESS not-accessible
	STATUS current
	DESCRIPTION
        "
        Row definition for the pmopm8Mesrchannel62
        table
        "
	INDEX   { pmopm8Mesrchannel62Index }
	::= { pmopm8Mesrchannel62Table 1 }


Pmopm8Mesrchannel62Entry ::=
	SEQUENCE {
	pmopm8Mesrchannel62Index
		INTEGER,
	pmopm8Mesrchannel62Portn
		INTEGER
	}


pmopm8Mesrchannel62Index OBJECT-TYPE
	SYNTAX  INTEGER(0..128)
	MAX-ACCESS  read-only
	STATUS current
	DESCRIPTION
        "
        Index definition for the pmopm8Mesrchannel62
        table
        "
	::= { pmopm8Mesrchannel62Entry 1 }


pmopm8Mesrchannel62Portn OBJECT-TYPE
	SYNTAX  INTEGER (0..65535)
	MAX-ACCESS read-only
	STATUS current
	DESCRIPTION
        "
        Channel62 Power :This OID indicates
        the channel power  (Power =Q8(Number
        format)) (Unit = dBm)  <Help> This
        measure indicates the channel power
        "
	::= { pmopm8Mesrchannel62Entry 2 }


--- *********************************************************
---     TABLE for the pmopm8Mesrchannel63 articles
--- *********************************************************

pmopm8Mesrchannel63Table OBJECT-TYPE
	SYNTAX  SEQUENCE OF Pmopm8Mesrchannel63Entry
	MAX-ACCESS not-accessible
	STATUS current
	DESCRIPTION
        "
        List of pmopm8Mesrchannel63 Article
        "
	::= { pmopm8MesrClient 512 }


pmopm8Mesrchannel63Entry OBJECT-TYPE
	SYNTAX Pmopm8Mesrchannel63Entry
	MAX-ACCESS not-accessible
	STATUS current
	DESCRIPTION
        "
        Row definition for the pmopm8Mesrchannel63
        table
        "
	INDEX   { pmopm8Mesrchannel63Index }
	::= { pmopm8Mesrchannel63Table 1 }


Pmopm8Mesrchannel63Entry ::=
	SEQUENCE {
	pmopm8Mesrchannel63Index
		INTEGER,
	pmopm8Mesrchannel63Portn
		INTEGER
	}


pmopm8Mesrchannel63Index OBJECT-TYPE
	SYNTAX  INTEGER(0..128)
	MAX-ACCESS  read-only
	STATUS current
	DESCRIPTION
        "
        Index definition for the pmopm8Mesrchannel63
        table
        "
	::= { pmopm8Mesrchannel63Entry 1 }


pmopm8Mesrchannel63Portn OBJECT-TYPE
	SYNTAX  INTEGER (0..65535)
	MAX-ACCESS read-only
	STATUS current
	DESCRIPTION
        "
        Channel63 Power :This OID indicates
        the channel power  (Power =Q8(Number
        format)) (Unit = dBm)  <Help> This
        measure indicates the channel power
        "
	::= { pmopm8Mesrchannel63Entry 2 }


--- *********************************************************
---     TABLE for the pmopm8Mesrchannel64 articles
--- *********************************************************

pmopm8Mesrchannel64Table OBJECT-TYPE
	SYNTAX  SEQUENCE OF Pmopm8Mesrchannel64Entry
	MAX-ACCESS not-accessible
	STATUS current
	DESCRIPTION
        "
        List of pmopm8Mesrchannel64 Article
        "
	::= { pmopm8MesrClient 520 }


pmopm8Mesrchannel64Entry OBJECT-TYPE
	SYNTAX Pmopm8Mesrchannel64Entry
	MAX-ACCESS not-accessible
	STATUS current
	DESCRIPTION
        "
        Row definition for the pmopm8Mesrchannel64
        table
        "
	INDEX   { pmopm8Mesrchannel64Index }
	::= { pmopm8Mesrchannel64Table 1 }


Pmopm8Mesrchannel64Entry ::=
	SEQUENCE {
	pmopm8Mesrchannel64Index
		INTEGER,
	pmopm8Mesrchannel64Portn
		INTEGER
	}


pmopm8Mesrchannel64Index OBJECT-TYPE
	SYNTAX  INTEGER(0..128)
	MAX-ACCESS  read-only
	STATUS current
	DESCRIPTION
        "
        Index definition for the pmopm8Mesrchannel64
        table
        "
	::= { pmopm8Mesrchannel64Entry 1 }


pmopm8Mesrchannel64Portn OBJECT-TYPE
	SYNTAX  INTEGER (0..65535)
	MAX-ACCESS read-only
	STATUS current
	DESCRIPTION
        "
        Channel64 Power :This OID indicates
        the channel power  (Power =Q8(Number
        format)) (Unit = dBm)  <Help> This
        measure indicates the channel power
        "
	::= { pmopm8Mesrchannel64Entry 2 }


--- *********************************************************
---     TABLE for the pmopm8Mesrchannel65 articles
--- *********************************************************

pmopm8Mesrchannel65Table OBJECT-TYPE
	SYNTAX  SEQUENCE OF Pmopm8Mesrchannel65Entry
	MAX-ACCESS not-accessible
	STATUS current
	DESCRIPTION
        "
        List of pmopm8Mesrchannel65 Article
        "
	::= { pmopm8MesrClient 528 }


pmopm8Mesrchannel65Entry OBJECT-TYPE
	SYNTAX Pmopm8Mesrchannel65Entry
	MAX-ACCESS not-accessible
	STATUS current
	DESCRIPTION
        "
        Row definition for the pmopm8Mesrchannel65
        table
        "
	INDEX   { pmopm8Mesrchannel65Index }
	::= { pmopm8Mesrchannel65Table 1 }


Pmopm8Mesrchannel65Entry ::=
	SEQUENCE {
	pmopm8Mesrchannel65Index
		INTEGER,
	pmopm8Mesrchannel65Portn
		INTEGER
	}


pmopm8Mesrchannel65Index OBJECT-TYPE
	SYNTAX  INTEGER(0..128)
	MAX-ACCESS  read-only
	STATUS current
	DESCRIPTION
        "
        Index definition for the pmopm8Mesrchannel65
        table
        "
	::= { pmopm8Mesrchannel65Entry 1 }


pmopm8Mesrchannel65Portn OBJECT-TYPE
	SYNTAX  INTEGER (0..65535)
	MAX-ACCESS read-only
	STATUS current
	DESCRIPTION
        "
        Channel65 Power :This OID indicates
        the channel power  (Power =Q8(Number
        format)) (Unit = dBm)  <Help> This
        measure indicates the channel power
        "
	::= { pmopm8Mesrchannel65Entry 2 }


--- *********************************************************
---     TABLE for the pmopm8Mesrchannel66 articles
--- *********************************************************

pmopm8Mesrchannel66Table OBJECT-TYPE
	SYNTAX  SEQUENCE OF Pmopm8Mesrchannel66Entry
	MAX-ACCESS not-accessible
	STATUS current
	DESCRIPTION
        "
        List of pmopm8Mesrchannel66 Article
        "
	::= { pmopm8MesrClient 536 }


pmopm8Mesrchannel66Entry OBJECT-TYPE
	SYNTAX Pmopm8Mesrchannel66Entry
	MAX-ACCESS not-accessible
	STATUS current
	DESCRIPTION
        "
        Row definition for the pmopm8Mesrchannel66
        table
        "
	INDEX   { pmopm8Mesrchannel66Index }
	::= { pmopm8Mesrchannel66Table 1 }


Pmopm8Mesrchannel66Entry ::=
	SEQUENCE {
	pmopm8Mesrchannel66Index
		INTEGER,
	pmopm8Mesrchannel66Portn
		INTEGER
	}


pmopm8Mesrchannel66Index OBJECT-TYPE
	SYNTAX  INTEGER(0..128)
	MAX-ACCESS  read-only
	STATUS current
	DESCRIPTION
        "
        Index definition for the pmopm8Mesrchannel66
        table
        "
	::= { pmopm8Mesrchannel66Entry 1 }


pmopm8Mesrchannel66Portn OBJECT-TYPE
	SYNTAX  INTEGER (0..65535)
	MAX-ACCESS read-only
	STATUS current
	DESCRIPTION
        "
        Channel66 Power :This OID indicates
        the channel power  (Power =Q8(Number
        format)) (Unit = dBm)  <Help> This
        measure indicates the channel power
        "
	::= { pmopm8Mesrchannel66Entry 2 }


--- *********************************************************
---     TABLE for the pmopm8Mesrchannel67 articles
--- *********************************************************

pmopm8Mesrchannel67Table OBJECT-TYPE
	SYNTAX  SEQUENCE OF Pmopm8Mesrchannel67Entry
	MAX-ACCESS not-accessible
	STATUS current
	DESCRIPTION
        "
        List of pmopm8Mesrchannel67 Article
        "
	::= { pmopm8MesrClient 544 }


pmopm8Mesrchannel67Entry OBJECT-TYPE
	SYNTAX Pmopm8Mesrchannel67Entry
	MAX-ACCESS not-accessible
	STATUS current
	DESCRIPTION
        "
        Row definition for the pmopm8Mesrchannel67
        table
        "
	INDEX   { pmopm8Mesrchannel67Index }
	::= { pmopm8Mesrchannel67Table 1 }


Pmopm8Mesrchannel67Entry ::=
	SEQUENCE {
	pmopm8Mesrchannel67Index
		INTEGER,
	pmopm8Mesrchannel67Portn
		INTEGER
	}


pmopm8Mesrchannel67Index OBJECT-TYPE
	SYNTAX  INTEGER(0..128)
	MAX-ACCESS  read-only
	STATUS current
	DESCRIPTION
        "
        Index definition for the pmopm8Mesrchannel67
        table
        "
	::= { pmopm8Mesrchannel67Entry 1 }


pmopm8Mesrchannel67Portn OBJECT-TYPE
	SYNTAX  INTEGER (0..65535)
	MAX-ACCESS read-only
	STATUS current
	DESCRIPTION
        "
        Channel67 Power :This OID indicates
        the channel power  (Power =Q8(Number
        format)) (Unit = dBm)  <Help> This
        measure indicates the channel power
        "
	::= { pmopm8Mesrchannel67Entry 2 }


--- *********************************************************
---     TABLE for the pmopm8Mesrchannel68 articles
--- *********************************************************

pmopm8Mesrchannel68Table OBJECT-TYPE
	SYNTAX  SEQUENCE OF Pmopm8Mesrchannel68Entry
	MAX-ACCESS not-accessible
	STATUS current
	DESCRIPTION
        "
        List of pmopm8Mesrchannel68 Article
        "
	::= { pmopm8MesrClient 552 }


pmopm8Mesrchannel68Entry OBJECT-TYPE
	SYNTAX Pmopm8Mesrchannel68Entry
	MAX-ACCESS not-accessible
	STATUS current
	DESCRIPTION
        "
        Row definition for the pmopm8Mesrchannel68
        table
        "
	INDEX   { pmopm8Mesrchannel68Index }
	::= { pmopm8Mesrchannel68Table 1 }


Pmopm8Mesrchannel68Entry ::=
	SEQUENCE {
	pmopm8Mesrchannel68Index
		INTEGER,
	pmopm8Mesrchannel68Portn
		INTEGER
	}


pmopm8Mesrchannel68Index OBJECT-TYPE
	SYNTAX  INTEGER(0..128)
	MAX-ACCESS  read-only
	STATUS current
	DESCRIPTION
        "
        Index definition for the pmopm8Mesrchannel68
        table
        "
	::= { pmopm8Mesrchannel68Entry 1 }


pmopm8Mesrchannel68Portn OBJECT-TYPE
	SYNTAX  INTEGER (0..65535)
	MAX-ACCESS read-only
	STATUS current
	DESCRIPTION
        "
        Channel68 Power :This OID indicates
        the channel power  (Power =Q8(Number
        format)) (Unit = dBm)  <Help> This
        measure indicates the channel power
        "
	::= { pmopm8Mesrchannel68Entry 2 }


--- *********************************************************
---     TABLE for the pmopm8Mesrchannel69 articles
--- *********************************************************

pmopm8Mesrchannel69Table OBJECT-TYPE
	SYNTAX  SEQUENCE OF Pmopm8Mesrchannel69Entry
	MAX-ACCESS not-accessible
	STATUS current
	DESCRIPTION
        "
        List of pmopm8Mesrchannel69 Article
        "
	::= { pmopm8MesrClient 560 }


pmopm8Mesrchannel69Entry OBJECT-TYPE
	SYNTAX Pmopm8Mesrchannel69Entry
	MAX-ACCESS not-accessible
	STATUS current
	DESCRIPTION
        "
        Row definition for the pmopm8Mesrchannel69
        table
        "
	INDEX   { pmopm8Mesrchannel69Index }
	::= { pmopm8Mesrchannel69Table 1 }


Pmopm8Mesrchannel69Entry ::=
	SEQUENCE {
	pmopm8Mesrchannel69Index
		INTEGER,
	pmopm8Mesrchannel69Portn
		INTEGER
	}


pmopm8Mesrchannel69Index OBJECT-TYPE
	SYNTAX  INTEGER(0..128)
	MAX-ACCESS  read-only
	STATUS current
	DESCRIPTION
        "
        Index definition for the pmopm8Mesrchannel69
        table
        "
	::= { pmopm8Mesrchannel69Entry 1 }


pmopm8Mesrchannel69Portn OBJECT-TYPE
	SYNTAX  INTEGER (0..65535)
	MAX-ACCESS read-only
	STATUS current
	DESCRIPTION
        "
        Channel69 Power :This OID indicates
        the channel power  (Power =Q8(Number
        format)) (Unit = dBm)  <Help> This
        measure indicates the channel power
        "
	::= { pmopm8Mesrchannel69Entry 2 }


--- *********************************************************
---     TABLE for the pmopm8Mesrchannel70 articles
--- *********************************************************

pmopm8Mesrchannel70Table OBJECT-TYPE
	SYNTAX  SEQUENCE OF Pmopm8Mesrchannel70Entry
	MAX-ACCESS not-accessible
	STATUS current
	DESCRIPTION
        "
        List of pmopm8Mesrchannel70 Article
        "
	::= { pmopm8MesrClient 568 }


pmopm8Mesrchannel70Entry OBJECT-TYPE
	SYNTAX Pmopm8Mesrchannel70Entry
	MAX-ACCESS not-accessible
	STATUS current
	DESCRIPTION
        "
        Row definition for the pmopm8Mesrchannel70
        table
        "
	INDEX   { pmopm8Mesrchannel70Index }
	::= { pmopm8Mesrchannel70Table 1 }


Pmopm8Mesrchannel70Entry ::=
	SEQUENCE {
	pmopm8Mesrchannel70Index
		INTEGER,
	pmopm8Mesrchannel70Portn
		INTEGER
	}


pmopm8Mesrchannel70Index OBJECT-TYPE
	SYNTAX  INTEGER(0..128)
	MAX-ACCESS  read-only
	STATUS current
	DESCRIPTION
        "
        Index definition for the pmopm8Mesrchannel70
        table
        "
	::= { pmopm8Mesrchannel70Entry 1 }


pmopm8Mesrchannel70Portn OBJECT-TYPE
	SYNTAX  INTEGER (0..65535)
	MAX-ACCESS read-only
	STATUS current
	DESCRIPTION
        "
        Channel70 Power :This OID indicates
        the channel power  (Power =Q8(Number
        format)) (Unit = dBm)  <Help> This
        measure indicates the channel power
        "
	::= { pmopm8Mesrchannel70Entry 2 }


--- *********************************************************
---     TABLE for the pmopm8Mesrchannel71 articles
--- *********************************************************

pmopm8Mesrchannel71Table OBJECT-TYPE
	SYNTAX  SEQUENCE OF Pmopm8Mesrchannel71Entry
	MAX-ACCESS not-accessible
	STATUS current
	DESCRIPTION
        "
        List of pmopm8Mesrchannel71 Article
        "
	::= { pmopm8MesrClient 576 }


pmopm8Mesrchannel71Entry OBJECT-TYPE
	SYNTAX Pmopm8Mesrchannel71Entry
	MAX-ACCESS not-accessible
	STATUS current
	DESCRIPTION
        "
        Row definition for the pmopm8Mesrchannel71
        table
        "
	INDEX   { pmopm8Mesrchannel71Index }
	::= { pmopm8Mesrchannel71Table 1 }


Pmopm8Mesrchannel71Entry ::=
	SEQUENCE {
	pmopm8Mesrchannel71Index
		INTEGER,
	pmopm8Mesrchannel71Portn
		INTEGER
	}


pmopm8Mesrchannel71Index OBJECT-TYPE
	SYNTAX  INTEGER(0..128)
	MAX-ACCESS  read-only
	STATUS current
	DESCRIPTION
        "
        Index definition for the pmopm8Mesrchannel71
        table
        "
	::= { pmopm8Mesrchannel71Entry 1 }


pmopm8Mesrchannel71Portn OBJECT-TYPE
	SYNTAX  INTEGER (0..65535)
	MAX-ACCESS read-only
	STATUS current
	DESCRIPTION
        "
        Channel71 Power :This OID indicates
        the channel power  (Power =Q8(Number
        format)) (Unit = dBm)  <Help> This
        measure indicates the channel power
        "
	::= { pmopm8Mesrchannel71Entry 2 }


--- *********************************************************
---     TABLE for the pmopm8Mesrchannel72 articles
--- *********************************************************

pmopm8Mesrchannel72Table OBJECT-TYPE
	SYNTAX  SEQUENCE OF Pmopm8Mesrchannel72Entry
	MAX-ACCESS not-accessible
	STATUS current
	DESCRIPTION
        "
        List of pmopm8Mesrchannel72 Article
        "
	::= { pmopm8MesrClient 584 }


pmopm8Mesrchannel72Entry OBJECT-TYPE
	SYNTAX Pmopm8Mesrchannel72Entry
	MAX-ACCESS not-accessible
	STATUS current
	DESCRIPTION
        "
        Row definition for the pmopm8Mesrchannel72
        table
        "
	INDEX   { pmopm8Mesrchannel72Index }
	::= { pmopm8Mesrchannel72Table 1 }


Pmopm8Mesrchannel72Entry ::=
	SEQUENCE {
	pmopm8Mesrchannel72Index
		INTEGER,
	pmopm8Mesrchannel72Portn
		INTEGER
	}


pmopm8Mesrchannel72Index OBJECT-TYPE
	SYNTAX  INTEGER(0..128)
	MAX-ACCESS  read-only
	STATUS current
	DESCRIPTION
        "
        Index definition for the pmopm8Mesrchannel72
        table
        "
	::= { pmopm8Mesrchannel72Entry 1 }


pmopm8Mesrchannel72Portn OBJECT-TYPE
	SYNTAX  INTEGER (0..65535)
	MAX-ACCESS read-only
	STATUS current
	DESCRIPTION
        "
        Channel72 Power :This OID indicates
        the channel power  (Power =Q8(Number
        format)) (Unit = dBm)  <Help> This
        measure indicates the channel power
        "
	::= { pmopm8Mesrchannel72Entry 2 }


--- *********************************************************
---     TABLE for the pmopm8Mesrchannel73 articles
--- *********************************************************

pmopm8Mesrchannel73Table OBJECT-TYPE
	SYNTAX  SEQUENCE OF Pmopm8Mesrchannel73Entry
	MAX-ACCESS not-accessible
	STATUS current
	DESCRIPTION
        "
        List of pmopm8Mesrchannel73 Article
        "
	::= { pmopm8MesrClient 592 }


pmopm8Mesrchannel73Entry OBJECT-TYPE
	SYNTAX Pmopm8Mesrchannel73Entry
	MAX-ACCESS not-accessible
	STATUS current
	DESCRIPTION
        "
        Row definition for the pmopm8Mesrchannel73
        table
        "
	INDEX   { pmopm8Mesrchannel73Index }
	::= { pmopm8Mesrchannel73Table 1 }


Pmopm8Mesrchannel73Entry ::=
	SEQUENCE {
	pmopm8Mesrchannel73Index
		INTEGER,
	pmopm8Mesrchannel73Portn
		INTEGER
	}


pmopm8Mesrchannel73Index OBJECT-TYPE
	SYNTAX  INTEGER(0..128)
	MAX-ACCESS  read-only
	STATUS current
	DESCRIPTION
        "
        Index definition for the pmopm8Mesrchannel73
        table
        "
	::= { pmopm8Mesrchannel73Entry 1 }


pmopm8Mesrchannel73Portn OBJECT-TYPE
	SYNTAX  INTEGER (0..65535)
	MAX-ACCESS read-only
	STATUS current
	DESCRIPTION
        "
        Channel73 Power :This OID indicates
        the channel power  (Power =Q8(Number
        format)) (Unit = dBm)  <Help> This
        measure indicates the channel power
        "
	::= { pmopm8Mesrchannel73Entry 2 }


--- *********************************************************
---     TABLE for the pmopm8Mesrchannel74 articles
--- *********************************************************

pmopm8Mesrchannel74Table OBJECT-TYPE
	SYNTAX  SEQUENCE OF Pmopm8Mesrchannel74Entry
	MAX-ACCESS not-accessible
	STATUS current
	DESCRIPTION
        "
        List of pmopm8Mesrchannel74 Article
        "
	::= { pmopm8MesrClient 600 }


pmopm8Mesrchannel74Entry OBJECT-TYPE
	SYNTAX Pmopm8Mesrchannel74Entry
	MAX-ACCESS not-accessible
	STATUS current
	DESCRIPTION
        "
        Row definition for the pmopm8Mesrchannel74
        table
        "
	INDEX   { pmopm8Mesrchannel74Index }
	::= { pmopm8Mesrchannel74Table 1 }


Pmopm8Mesrchannel74Entry ::=
	SEQUENCE {
	pmopm8Mesrchannel74Index
		INTEGER,
	pmopm8Mesrchannel74Portn
		INTEGER
	}


pmopm8Mesrchannel74Index OBJECT-TYPE
	SYNTAX  INTEGER(0..128)
	MAX-ACCESS  read-only
	STATUS current
	DESCRIPTION
        "
        Index definition for the pmopm8Mesrchannel74
        table
        "
	::= { pmopm8Mesrchannel74Entry 1 }


pmopm8Mesrchannel74Portn OBJECT-TYPE
	SYNTAX  INTEGER (0..65535)
	MAX-ACCESS read-only
	STATUS current
	DESCRIPTION
        "
        Channel74 Power :This OID indicates
        the channel power  (Power =Q8(Number
        format)) (Unit = dBm)  <Help> This
        measure indicates the channel power
        "
	::= { pmopm8Mesrchannel74Entry 2 }


--- *********************************************************
---     TABLE for the pmopm8Mesrchannel75 articles
--- *********************************************************

pmopm8Mesrchannel75Table OBJECT-TYPE
	SYNTAX  SEQUENCE OF Pmopm8Mesrchannel75Entry
	MAX-ACCESS not-accessible
	STATUS current
	DESCRIPTION
        "
        List of pmopm8Mesrchannel75 Article
        "
	::= { pmopm8MesrClient 608 }


pmopm8Mesrchannel75Entry OBJECT-TYPE
	SYNTAX Pmopm8Mesrchannel75Entry
	MAX-ACCESS not-accessible
	STATUS current
	DESCRIPTION
        "
        Row definition for the pmopm8Mesrchannel75
        table
        "
	INDEX   { pmopm8Mesrchannel75Index }
	::= { pmopm8Mesrchannel75Table 1 }


Pmopm8Mesrchannel75Entry ::=
	SEQUENCE {
	pmopm8Mesrchannel75Index
		INTEGER,
	pmopm8Mesrchannel75Portn
		INTEGER
	}


pmopm8Mesrchannel75Index OBJECT-TYPE
	SYNTAX  INTEGER(0..128)
	MAX-ACCESS  read-only
	STATUS current
	DESCRIPTION
        "
        Index definition for the pmopm8Mesrchannel75
        table
        "
	::= { pmopm8Mesrchannel75Entry 1 }


pmopm8Mesrchannel75Portn OBJECT-TYPE
	SYNTAX  INTEGER (0..65535)
	MAX-ACCESS read-only
	STATUS current
	DESCRIPTION
        "
        Channel75 Power :This OID indicates
        the channel power  (Power =Q8(Number
        format)) (Unit = dBm)  <Help> This
        measure indicates the channel power
        "
	::= { pmopm8Mesrchannel75Entry 2 }


--- *********************************************************
---     TABLE for the pmopm8Mesrchannel76 articles
--- *********************************************************

pmopm8Mesrchannel76Table OBJECT-TYPE
	SYNTAX  SEQUENCE OF Pmopm8Mesrchannel76Entry
	MAX-ACCESS not-accessible
	STATUS current
	DESCRIPTION
        "
        List of pmopm8Mesrchannel76 Article
        "
	::= { pmopm8MesrClient 616 }


pmopm8Mesrchannel76Entry OBJECT-TYPE
	SYNTAX Pmopm8Mesrchannel76Entry
	MAX-ACCESS not-accessible
	STATUS current
	DESCRIPTION
        "
        Row definition for the pmopm8Mesrchannel76
        table
        "
	INDEX   { pmopm8Mesrchannel76Index }
	::= { pmopm8Mesrchannel76Table 1 }


Pmopm8Mesrchannel76Entry ::=
	SEQUENCE {
	pmopm8Mesrchannel76Index
		INTEGER,
	pmopm8Mesrchannel76Portn
		INTEGER
	}


pmopm8Mesrchannel76Index OBJECT-TYPE
	SYNTAX  INTEGER(0..128)
	MAX-ACCESS  read-only
	STATUS current
	DESCRIPTION
        "
        Index definition for the pmopm8Mesrchannel76
        table
        "
	::= { pmopm8Mesrchannel76Entry 1 }


pmopm8Mesrchannel76Portn OBJECT-TYPE
	SYNTAX  INTEGER (0..65535)
	MAX-ACCESS read-only
	STATUS current
	DESCRIPTION
        "
        Channel76 Power :This OID indicates
        the channel power  (Power =Q8(Number
        format)) (Unit = dBm)  <Help> This
        measure indicates the channel power
        "
	::= { pmopm8Mesrchannel76Entry 2 }


--- *********************************************************
---     TABLE for the pmopm8Mesrchannel77 articles
--- *********************************************************

pmopm8Mesrchannel77Table OBJECT-TYPE
	SYNTAX  SEQUENCE OF Pmopm8Mesrchannel77Entry
	MAX-ACCESS not-accessible
	STATUS current
	DESCRIPTION
        "
        List of pmopm8Mesrchannel77 Article
        "
	::= { pmopm8MesrClient 624 }


pmopm8Mesrchannel77Entry OBJECT-TYPE
	SYNTAX Pmopm8Mesrchannel77Entry
	MAX-ACCESS not-accessible
	STATUS current
	DESCRIPTION
        "
        Row definition for the pmopm8Mesrchannel77
        table
        "
	INDEX   { pmopm8Mesrchannel77Index }
	::= { pmopm8Mesrchannel77Table 1 }


Pmopm8Mesrchannel77Entry ::=
	SEQUENCE {
	pmopm8Mesrchannel77Index
		INTEGER,
	pmopm8Mesrchannel77Portn
		INTEGER
	}


pmopm8Mesrchannel77Index OBJECT-TYPE
	SYNTAX  INTEGER(0..128)
	MAX-ACCESS  read-only
	STATUS current
	DESCRIPTION
        "
        Index definition for the pmopm8Mesrchannel77
        table
        "
	::= { pmopm8Mesrchannel77Entry 1 }


pmopm8Mesrchannel77Portn OBJECT-TYPE
	SYNTAX  INTEGER (0..65535)
	MAX-ACCESS read-only
	STATUS current
	DESCRIPTION
        "
        Channel77 Power :This OID indicates
        the channel power  (Power =Q8(Number
        format)) (Unit = dBm)  <Help> This
        measure indicates the channel power
        "
	::= { pmopm8Mesrchannel77Entry 2 }


--- *********************************************************
---     TABLE for the pmopm8Mesrchannel78 articles
--- *********************************************************

pmopm8Mesrchannel78Table OBJECT-TYPE
	SYNTAX  SEQUENCE OF Pmopm8Mesrchannel78Entry
	MAX-ACCESS not-accessible
	STATUS current
	DESCRIPTION
        "
        List of pmopm8Mesrchannel78 Article
        "
	::= { pmopm8MesrClient 632 }


pmopm8Mesrchannel78Entry OBJECT-TYPE
	SYNTAX Pmopm8Mesrchannel78Entry
	MAX-ACCESS not-accessible
	STATUS current
	DESCRIPTION
        "
        Row definition for the pmopm8Mesrchannel78
        table
        "
	INDEX   { pmopm8Mesrchannel78Index }
	::= { pmopm8Mesrchannel78Table 1 }


Pmopm8Mesrchannel78Entry ::=
	SEQUENCE {
	pmopm8Mesrchannel78Index
		INTEGER,
	pmopm8Mesrchannel78Portn
		INTEGER
	}


pmopm8Mesrchannel78Index OBJECT-TYPE
	SYNTAX  INTEGER(0..128)
	MAX-ACCESS  read-only
	STATUS current
	DESCRIPTION
        "
        Index definition for the pmopm8Mesrchannel78
        table
        "
	::= { pmopm8Mesrchannel78Entry 1 }


pmopm8Mesrchannel78Portn OBJECT-TYPE
	SYNTAX  INTEGER (0..65535)
	MAX-ACCESS read-only
	STATUS current
	DESCRIPTION
        "
        Channel78 Power :This OID indicates
        the channel power  (Power =Q8(Number
        format)) (Unit = dBm)  <Help> This
        measure indicates the channel power
        "
	::= { pmopm8Mesrchannel78Entry 2 }


--- *********************************************************
---     TABLE for the pmopm8Mesrchannel79 articles
--- *********************************************************

pmopm8Mesrchannel79Table OBJECT-TYPE
	SYNTAX  SEQUENCE OF Pmopm8Mesrchannel79Entry
	MAX-ACCESS not-accessible
	STATUS current
	DESCRIPTION
        "
        List of pmopm8Mesrchannel79 Article
        "
	::= { pmopm8MesrClient 640 }


pmopm8Mesrchannel79Entry OBJECT-TYPE
	SYNTAX Pmopm8Mesrchannel79Entry
	MAX-ACCESS not-accessible
	STATUS current
	DESCRIPTION
        "
        Row definition for the pmopm8Mesrchannel79
        table
        "
	INDEX   { pmopm8Mesrchannel79Index }
	::= { pmopm8Mesrchannel79Table 1 }


Pmopm8Mesrchannel79Entry ::=
	SEQUENCE {
	pmopm8Mesrchannel79Index
		INTEGER,
	pmopm8Mesrchannel79Portn
		INTEGER
	}


pmopm8Mesrchannel79Index OBJECT-TYPE
	SYNTAX  INTEGER(0..128)
	MAX-ACCESS  read-only
	STATUS current
	DESCRIPTION
        "
        Index definition for the pmopm8Mesrchannel79
        table
        "
	::= { pmopm8Mesrchannel79Entry 1 }


pmopm8Mesrchannel79Portn OBJECT-TYPE
	SYNTAX  INTEGER (0..65535)
	MAX-ACCESS read-only
	STATUS current
	DESCRIPTION
        "
        Channel79 Power :This OID indicates
        the channel power  (Power =Q8(Number
        format)) (Unit = dBm)  <Help> This
        measure indicates the channel power
        "
	::= { pmopm8Mesrchannel79Entry 2 }


--- *********************************************************
---     TABLE for the pmopm8Mesrchannel80 articles
--- *********************************************************

pmopm8Mesrchannel80Table OBJECT-TYPE
	SYNTAX  SEQUENCE OF Pmopm8Mesrchannel80Entry
	MAX-ACCESS not-accessible
	STATUS current
	DESCRIPTION
        "
        List of pmopm8Mesrchannel80 Article
        "
	::= { pmopm8MesrClient 648 }


pmopm8Mesrchannel80Entry OBJECT-TYPE
	SYNTAX Pmopm8Mesrchannel80Entry
	MAX-ACCESS not-accessible
	STATUS current
	DESCRIPTION
        "
        Row definition for the pmopm8Mesrchannel80
        table
        "
	INDEX   { pmopm8Mesrchannel80Index }
	::= { pmopm8Mesrchannel80Table 1 }


Pmopm8Mesrchannel80Entry ::=
	SEQUENCE {
	pmopm8Mesrchannel80Index
		INTEGER,
	pmopm8Mesrchannel80Portn
		INTEGER
	}


pmopm8Mesrchannel80Index OBJECT-TYPE
	SYNTAX  INTEGER(0..128)
	MAX-ACCESS  read-only
	STATUS current
	DESCRIPTION
        "
        Index definition for the pmopm8Mesrchannel80
        table
        "
	::= { pmopm8Mesrchannel80Entry 1 }


pmopm8Mesrchannel80Portn OBJECT-TYPE
	SYNTAX  INTEGER (0..65535)
	MAX-ACCESS read-only
	STATUS current
	DESCRIPTION
        "
        Channel80 Power :This OID indicates
        the channel power  (Power =Q8(Number
        format)) (Unit = dBm)  <Help> This
        measure indicates the channel power
        "
	::= { pmopm8Mesrchannel80Entry 2 }


--- *********************************************************
---     TABLE for the pmopm8Mesrchannel81 articles
--- *********************************************************

pmopm8Mesrchannel81Table OBJECT-TYPE
	SYNTAX  SEQUENCE OF Pmopm8Mesrchannel81Entry
	MAX-ACCESS not-accessible
	STATUS current
	DESCRIPTION
        "
        List of pmopm8Mesrchannel81 Article
        "
	::= { pmopm8MesrClient 656 }


pmopm8Mesrchannel81Entry OBJECT-TYPE
	SYNTAX Pmopm8Mesrchannel81Entry
	MAX-ACCESS not-accessible
	STATUS current
	DESCRIPTION
        "
        Row definition for the pmopm8Mesrchannel81
        table
        "
	INDEX   { pmopm8Mesrchannel81Index }
	::= { pmopm8Mesrchannel81Table 1 }


Pmopm8Mesrchannel81Entry ::=
	SEQUENCE {
	pmopm8Mesrchannel81Index
		INTEGER,
	pmopm8Mesrchannel81Portn
		INTEGER
	}


pmopm8Mesrchannel81Index OBJECT-TYPE
	SYNTAX  INTEGER(0..128)
	MAX-ACCESS  read-only
	STATUS current
	DESCRIPTION
        "
        Index definition for the pmopm8Mesrchannel81
        table
        "
	::= { pmopm8Mesrchannel81Entry 1 }


pmopm8Mesrchannel81Portn OBJECT-TYPE
	SYNTAX  INTEGER (0..65535)
	MAX-ACCESS read-only
	STATUS current
	DESCRIPTION
        "
        Channel81 Power :This OID indicates
        the channel power  (Power =Q8(Number
        format)) (Unit = dBm)  <Help> This
        measure indicates the channel power
        "
	::= { pmopm8Mesrchannel81Entry 2 }


--- *********************************************************
---     TABLE for the pmopm8Mesrchannel82 articles
--- *********************************************************

pmopm8Mesrchannel82Table OBJECT-TYPE
	SYNTAX  SEQUENCE OF Pmopm8Mesrchannel82Entry
	MAX-ACCESS not-accessible
	STATUS current
	DESCRIPTION
        "
        List of pmopm8Mesrchannel82 Article
        "
	::= { pmopm8MesrClient 664 }


pmopm8Mesrchannel82Entry OBJECT-TYPE
	SYNTAX Pmopm8Mesrchannel82Entry
	MAX-ACCESS not-accessible
	STATUS current
	DESCRIPTION
        "
        Row definition for the pmopm8Mesrchannel82
        table
        "
	INDEX   { pmopm8Mesrchannel82Index }
	::= { pmopm8Mesrchannel82Table 1 }


Pmopm8Mesrchannel82Entry ::=
	SEQUENCE {
	pmopm8Mesrchannel82Index
		INTEGER,
	pmopm8Mesrchannel82Portn
		INTEGER
	}


pmopm8Mesrchannel82Index OBJECT-TYPE
	SYNTAX  INTEGER(0..128)
	MAX-ACCESS  read-only
	STATUS current
	DESCRIPTION
        "
        Index definition for the pmopm8Mesrchannel82
        table
        "
	::= { pmopm8Mesrchannel82Entry 1 }


pmopm8Mesrchannel82Portn OBJECT-TYPE
	SYNTAX  INTEGER (0..65535)
	MAX-ACCESS read-only
	STATUS current
	DESCRIPTION
        "
        Channel82 Power :This OID indicates
        the channel power  (Power =Q8(Number
        format)) (Unit = dBm)  <Help> This
        measure indicates the channel power
        "
	::= { pmopm8Mesrchannel82Entry 2 }


--- *********************************************************
---     TABLE for the pmopm8Mesrchannel83 articles
--- *********************************************************

pmopm8Mesrchannel83Table OBJECT-TYPE
	SYNTAX  SEQUENCE OF Pmopm8Mesrchannel83Entry
	MAX-ACCESS not-accessible
	STATUS current
	DESCRIPTION
        "
        List of pmopm8Mesrchannel83 Article
        "
	::= { pmopm8MesrClient 672 }


pmopm8Mesrchannel83Entry OBJECT-TYPE
	SYNTAX Pmopm8Mesrchannel83Entry
	MAX-ACCESS not-accessible
	STATUS current
	DESCRIPTION
        "
        Row definition for the pmopm8Mesrchannel83
        table
        "
	INDEX   { pmopm8Mesrchannel83Index }
	::= { pmopm8Mesrchannel83Table 1 }


Pmopm8Mesrchannel83Entry ::=
	SEQUENCE {
	pmopm8Mesrchannel83Index
		INTEGER,
	pmopm8Mesrchannel83Portn
		INTEGER
	}


pmopm8Mesrchannel83Index OBJECT-TYPE
	SYNTAX  INTEGER(0..128)
	MAX-ACCESS  read-only
	STATUS current
	DESCRIPTION
        "
        Index definition for the pmopm8Mesrchannel83
        table
        "
	::= { pmopm8Mesrchannel83Entry 1 }


pmopm8Mesrchannel83Portn OBJECT-TYPE
	SYNTAX  INTEGER (0..65535)
	MAX-ACCESS read-only
	STATUS current
	DESCRIPTION
        "
        Channel83 Power :This OID indicates
        the channel power  (Power =Q8(Number
        format)) (Unit = dBm)  <Help> This
        measure indicates the channel power
        "
	::= { pmopm8Mesrchannel83Entry 2 }


--- *********************************************************
---     TABLE for the pmopm8Mesrchannel84 articles
--- *********************************************************

pmopm8Mesrchannel84Table OBJECT-TYPE
	SYNTAX  SEQUENCE OF Pmopm8Mesrchannel84Entry
	MAX-ACCESS not-accessible
	STATUS current
	DESCRIPTION
        "
        List of pmopm8Mesrchannel84 Article
        "
	::= { pmopm8MesrClient 680 }


pmopm8Mesrchannel84Entry OBJECT-TYPE
	SYNTAX Pmopm8Mesrchannel84Entry
	MAX-ACCESS not-accessible
	STATUS current
	DESCRIPTION
        "
        Row definition for the pmopm8Mesrchannel84
        table
        "
	INDEX   { pmopm8Mesrchannel84Index }
	::= { pmopm8Mesrchannel84Table 1 }


Pmopm8Mesrchannel84Entry ::=
	SEQUENCE {
	pmopm8Mesrchannel84Index
		INTEGER,
	pmopm8Mesrchannel84Portn
		INTEGER
	}


pmopm8Mesrchannel84Index OBJECT-TYPE
	SYNTAX  INTEGER(0..128)
	MAX-ACCESS  read-only
	STATUS current
	DESCRIPTION
        "
        Index definition for the pmopm8Mesrchannel84
        table
        "
	::= { pmopm8Mesrchannel84Entry 1 }


pmopm8Mesrchannel84Portn OBJECT-TYPE
	SYNTAX  INTEGER (0..65535)
	MAX-ACCESS read-only
	STATUS current
	DESCRIPTION
        "
        Channel84 Power :This OID indicates
        the channel power  (Power =Q8(Number
        format)) (Unit = dBm)  <Help> This
        measure indicates the channel power
        "
	::= { pmopm8Mesrchannel84Entry 2 }


--- *********************************************************
---     TABLE for the pmopm8Mesrchannel85 articles
--- *********************************************************

pmopm8Mesrchannel85Table OBJECT-TYPE
	SYNTAX  SEQUENCE OF Pmopm8Mesrchannel85Entry
	MAX-ACCESS not-accessible
	STATUS current
	DESCRIPTION
        "
        List of pmopm8Mesrchannel85 Article
        "
	::= { pmopm8MesrClient 688 }


pmopm8Mesrchannel85Entry OBJECT-TYPE
	SYNTAX Pmopm8Mesrchannel85Entry
	MAX-ACCESS not-accessible
	STATUS current
	DESCRIPTION
        "
        Row definition for the pmopm8Mesrchannel85
        table
        "
	INDEX   { pmopm8Mesrchannel85Index }
	::= { pmopm8Mesrchannel85Table 1 }


Pmopm8Mesrchannel85Entry ::=
	SEQUENCE {
	pmopm8Mesrchannel85Index
		INTEGER,
	pmopm8Mesrchannel85Portn
		INTEGER
	}


pmopm8Mesrchannel85Index OBJECT-TYPE
	SYNTAX  INTEGER(0..128)
	MAX-ACCESS  read-only
	STATUS current
	DESCRIPTION
        "
        Index definition for the pmopm8Mesrchannel85
        table
        "
	::= { pmopm8Mesrchannel85Entry 1 }


pmopm8Mesrchannel85Portn OBJECT-TYPE
	SYNTAX  INTEGER (0..65535)
	MAX-ACCESS read-only
	STATUS current
	DESCRIPTION
        "
        Channel85 Power :This OID indicates
        the channel power  (Power =Q8(Number
        format)) (Unit = dBm)  <Help> This
        measure indicates the channel power
        "
	::= { pmopm8Mesrchannel85Entry 2 }


--- *********************************************************
---     TABLE for the pmopm8Mesrchannel86 articles
--- *********************************************************

pmopm8Mesrchannel86Table OBJECT-TYPE
	SYNTAX  SEQUENCE OF Pmopm8Mesrchannel86Entry
	MAX-ACCESS not-accessible
	STATUS current
	DESCRIPTION
        "
        List of pmopm8Mesrchannel86 Article
        "
	::= { pmopm8MesrClient 696 }


pmopm8Mesrchannel86Entry OBJECT-TYPE
	SYNTAX Pmopm8Mesrchannel86Entry
	MAX-ACCESS not-accessible
	STATUS current
	DESCRIPTION
        "
        Row definition for the pmopm8Mesrchannel86
        table
        "
	INDEX   { pmopm8Mesrchannel86Index }
	::= { pmopm8Mesrchannel86Table 1 }


Pmopm8Mesrchannel86Entry ::=
	SEQUENCE {
	pmopm8Mesrchannel86Index
		INTEGER,
	pmopm8Mesrchannel86Portn
		INTEGER
	}


pmopm8Mesrchannel86Index OBJECT-TYPE
	SYNTAX  INTEGER(0..128)
	MAX-ACCESS  read-only
	STATUS current
	DESCRIPTION
        "
        Index definition for the pmopm8Mesrchannel86
        table
        "
	::= { pmopm8Mesrchannel86Entry 1 }


pmopm8Mesrchannel86Portn OBJECT-TYPE
	SYNTAX  INTEGER (0..65535)
	MAX-ACCESS read-only
	STATUS current
	DESCRIPTION
        "
        Channel86 Power :This OID indicates
        the channel power  (Power =Q8(Number
        format)) (Unit = dBm)  <Help> This
        measure indicates the channel power
        "
	::= { pmopm8Mesrchannel86Entry 2 }


--- *********************************************************
---     TABLE for the pmopm8Mesrchannel87 articles
--- *********************************************************

pmopm8Mesrchannel87Table OBJECT-TYPE
	SYNTAX  SEQUENCE OF Pmopm8Mesrchannel87Entry
	MAX-ACCESS not-accessible
	STATUS current
	DESCRIPTION
        "
        List of pmopm8Mesrchannel87 Article
        "
	::= { pmopm8MesrClient 704 }


pmopm8Mesrchannel87Entry OBJECT-TYPE
	SYNTAX Pmopm8Mesrchannel87Entry
	MAX-ACCESS not-accessible
	STATUS current
	DESCRIPTION
        "
        Row definition for the pmopm8Mesrchannel87
        table
        "
	INDEX   { pmopm8Mesrchannel87Index }
	::= { pmopm8Mesrchannel87Table 1 }


Pmopm8Mesrchannel87Entry ::=
	SEQUENCE {
	pmopm8Mesrchannel87Index
		INTEGER,
	pmopm8Mesrchannel87Portn
		INTEGER
	}


pmopm8Mesrchannel87Index OBJECT-TYPE
	SYNTAX  INTEGER(0..128)
	MAX-ACCESS  read-only
	STATUS current
	DESCRIPTION
        "
        Index definition for the pmopm8Mesrchannel87
        table
        "
	::= { pmopm8Mesrchannel87Entry 1 }


pmopm8Mesrchannel87Portn OBJECT-TYPE
	SYNTAX  INTEGER (0..65535)
	MAX-ACCESS read-only
	STATUS current
	DESCRIPTION
        "
        Channel87 Power :This OID indicates
        the channel power  (Power =Q8(Number
        format)) (Unit = dBm)  <Help> This
        measure indicates the channel power
        "
	::= { pmopm8Mesrchannel87Entry 2 }


--- *********************************************************
---     TABLE for the pmopm8Mesrchannel88 articles
--- *********************************************************

pmopm8Mesrchannel88Table OBJECT-TYPE
	SYNTAX  SEQUENCE OF Pmopm8Mesrchannel88Entry
	MAX-ACCESS not-accessible
	STATUS current
	DESCRIPTION
        "
        List of pmopm8Mesrchannel88 Article
        "
	::= { pmopm8MesrClient 712 }


pmopm8Mesrchannel88Entry OBJECT-TYPE
	SYNTAX Pmopm8Mesrchannel88Entry
	MAX-ACCESS not-accessible
	STATUS current
	DESCRIPTION
        "
        Row definition for the pmopm8Mesrchannel88
        table
        "
	INDEX   { pmopm8Mesrchannel88Index }
	::= { pmopm8Mesrchannel88Table 1 }


Pmopm8Mesrchannel88Entry ::=
	SEQUENCE {
	pmopm8Mesrchannel88Index
		INTEGER,
	pmopm8Mesrchannel88Portn
		INTEGER
	}


pmopm8Mesrchannel88Index OBJECT-TYPE
	SYNTAX  INTEGER(0..128)
	MAX-ACCESS  read-only
	STATUS current
	DESCRIPTION
        "
        Index definition for the pmopm8Mesrchannel88
        table
        "
	::= { pmopm8Mesrchannel88Entry 1 }


pmopm8Mesrchannel88Portn OBJECT-TYPE
	SYNTAX  INTEGER (0..65535)
	MAX-ACCESS read-only
	STATUS current
	DESCRIPTION
        "
        Channel88 Power :This OID indicates
        the channel power  (Power =Q8(Number
        format)) (Unit = dBm)  <Help> This
        measure indicates the channel power
        "
	::= { pmopm8Mesrchannel88Entry 2 }


--- *********************************************************
---     TABLE for the pmopm8Mesrchannel89 articles
--- *********************************************************

pmopm8Mesrchannel89Table OBJECT-TYPE
	SYNTAX  SEQUENCE OF Pmopm8Mesrchannel89Entry
	MAX-ACCESS not-accessible
	STATUS current
	DESCRIPTION
        "
        List of pmopm8Mesrchannel89 Article
        "
	::= { pmopm8MesrClient 720 }


pmopm8Mesrchannel89Entry OBJECT-TYPE
	SYNTAX Pmopm8Mesrchannel89Entry
	MAX-ACCESS not-accessible
	STATUS current
	DESCRIPTION
        "
        Row definition for the pmopm8Mesrchannel89
        table
        "
	INDEX   { pmopm8Mesrchannel89Index }
	::= { pmopm8Mesrchannel89Table 1 }


Pmopm8Mesrchannel89Entry ::=
	SEQUENCE {
	pmopm8Mesrchannel89Index
		INTEGER,
	pmopm8Mesrchannel89Portn
		INTEGER
	}


pmopm8Mesrchannel89Index OBJECT-TYPE
	SYNTAX  INTEGER(0..128)
	MAX-ACCESS  read-only
	STATUS current
	DESCRIPTION
        "
        Index definition for the pmopm8Mesrchannel89
        table
        "
	::= { pmopm8Mesrchannel89Entry 1 }


pmopm8Mesrchannel89Portn OBJECT-TYPE
	SYNTAX  INTEGER (0..65535)
	MAX-ACCESS read-only
	STATUS current
	DESCRIPTION
        "
        Channel89 Power :This OID indicates
        the channel power  (Power =Q8(Number
        format)) (Unit = dBm)  <Help> This
        measure indicates the channel power
        "
	::= { pmopm8Mesrchannel89Entry 2 }


--- *********************************************************
---     TABLE for the pmopm8Mesrchannel90 articles
--- *********************************************************

pmopm8Mesrchannel90Table OBJECT-TYPE
	SYNTAX  SEQUENCE OF Pmopm8Mesrchannel90Entry
	MAX-ACCESS not-accessible
	STATUS current
	DESCRIPTION
        "
        List of pmopm8Mesrchannel90 Article
        "
	::= { pmopm8MesrClient 728 }


pmopm8Mesrchannel90Entry OBJECT-TYPE
	SYNTAX Pmopm8Mesrchannel90Entry
	MAX-ACCESS not-accessible
	STATUS current
	DESCRIPTION
        "
        Row definition for the pmopm8Mesrchannel90
        table
        "
	INDEX   { pmopm8Mesrchannel90Index }
	::= { pmopm8Mesrchannel90Table 1 }


Pmopm8Mesrchannel90Entry ::=
	SEQUENCE {
	pmopm8Mesrchannel90Index
		INTEGER,
	pmopm8Mesrchannel90Portn
		INTEGER
	}


pmopm8Mesrchannel90Index OBJECT-TYPE
	SYNTAX  INTEGER(0..128)
	MAX-ACCESS  read-only
	STATUS current
	DESCRIPTION
        "
        Index definition for the pmopm8Mesrchannel90
        table
        "
	::= { pmopm8Mesrchannel90Entry 1 }


pmopm8Mesrchannel90Portn OBJECT-TYPE
	SYNTAX  INTEGER (0..65535)
	MAX-ACCESS read-only
	STATUS current
	DESCRIPTION
        "
        Channel90 Power :This OID indicates
        the channel power  (Power =Q8(Number
        format)) (Unit = dBm)  <Help> This
        measure indicates the channel power
        "
	::= { pmopm8Mesrchannel90Entry 2 }


--- *********************************************************
---     TABLE for the pmopm8Mesrchannel91 articles
--- *********************************************************

pmopm8Mesrchannel91Table OBJECT-TYPE
	SYNTAX  SEQUENCE OF Pmopm8Mesrchannel91Entry
	MAX-ACCESS not-accessible
	STATUS current
	DESCRIPTION
        "
        List of pmopm8Mesrchannel91 Article
        "
	::= { pmopm8MesrClient 736 }


pmopm8Mesrchannel91Entry OBJECT-TYPE
	SYNTAX Pmopm8Mesrchannel91Entry
	MAX-ACCESS not-accessible
	STATUS current
	DESCRIPTION
        "
        Row definition for the pmopm8Mesrchannel91
        table
        "
	INDEX   { pmopm8Mesrchannel91Index }
	::= { pmopm8Mesrchannel91Table 1 }


Pmopm8Mesrchannel91Entry ::=
	SEQUENCE {
	pmopm8Mesrchannel91Index
		INTEGER,
	pmopm8Mesrchannel91Portn
		INTEGER
	}


pmopm8Mesrchannel91Index OBJECT-TYPE
	SYNTAX  INTEGER(0..128)
	MAX-ACCESS  read-only
	STATUS current
	DESCRIPTION
        "
        Index definition for the pmopm8Mesrchannel91
        table
        "
	::= { pmopm8Mesrchannel91Entry 1 }


pmopm8Mesrchannel91Portn OBJECT-TYPE
	SYNTAX  INTEGER (0..65535)
	MAX-ACCESS read-only
	STATUS current
	DESCRIPTION
        "
        Channel91 Power :This OID indicates
        the channel power  (Power =Q8(Number
        format)) (Unit = dBm)  <Help> This
        measure indicates the channel power
        "
	::= { pmopm8Mesrchannel91Entry 2 }


--- *********************************************************
---     TABLE for the pmopm8Mesrchannel92 articles
--- *********************************************************

pmopm8Mesrchannel92Table OBJECT-TYPE
	SYNTAX  SEQUENCE OF Pmopm8Mesrchannel92Entry
	MAX-ACCESS not-accessible
	STATUS current
	DESCRIPTION
        "
        List of pmopm8Mesrchannel92 Article
        "
	::= { pmopm8MesrClient 744 }


pmopm8Mesrchannel92Entry OBJECT-TYPE
	SYNTAX Pmopm8Mesrchannel92Entry
	MAX-ACCESS not-accessible
	STATUS current
	DESCRIPTION
        "
        Row definition for the pmopm8Mesrchannel92
        table
        "
	INDEX   { pmopm8Mesrchannel92Index }
	::= { pmopm8Mesrchannel92Table 1 }


Pmopm8Mesrchannel92Entry ::=
	SEQUENCE {
	pmopm8Mesrchannel92Index
		INTEGER,
	pmopm8Mesrchannel92Portn
		INTEGER
	}


pmopm8Mesrchannel92Index OBJECT-TYPE
	SYNTAX  INTEGER(0..128)
	MAX-ACCESS  read-only
	STATUS current
	DESCRIPTION
        "
        Index definition for the pmopm8Mesrchannel92
        table
        "
	::= { pmopm8Mesrchannel92Entry 1 }


pmopm8Mesrchannel92Portn OBJECT-TYPE
	SYNTAX  INTEGER (0..65535)
	MAX-ACCESS read-only
	STATUS current
	DESCRIPTION
        "
        Channel92 Power :This OID indicates
        the channel power  (Power =Q8(Number
        format)) (Unit = dBm)  <Help> This
        measure indicates the channel power
        "
	::= { pmopm8Mesrchannel92Entry 2 }


--- *********************************************************
---     TABLE for the pmopm8Mesrchannel93 articles
--- *********************************************************

pmopm8Mesrchannel93Table OBJECT-TYPE
	SYNTAX  SEQUENCE OF Pmopm8Mesrchannel93Entry
	MAX-ACCESS not-accessible
	STATUS current
	DESCRIPTION
        "
        List of pmopm8Mesrchannel93 Article
        "
	::= { pmopm8MesrClient 752 }


pmopm8Mesrchannel93Entry OBJECT-TYPE
	SYNTAX Pmopm8Mesrchannel93Entry
	MAX-ACCESS not-accessible
	STATUS current
	DESCRIPTION
        "
        Row definition for the pmopm8Mesrchannel93
        table
        "
	INDEX   { pmopm8Mesrchannel93Index }
	::= { pmopm8Mesrchannel93Table 1 }


Pmopm8Mesrchannel93Entry ::=
	SEQUENCE {
	pmopm8Mesrchannel93Index
		INTEGER,
	pmopm8Mesrchannel93Portn
		INTEGER
	}


pmopm8Mesrchannel93Index OBJECT-TYPE
	SYNTAX  INTEGER(0..128)
	MAX-ACCESS  read-only
	STATUS current
	DESCRIPTION
        "
        Index definition for the pmopm8Mesrchannel93
        table
        "
	::= { pmopm8Mesrchannel93Entry 1 }


pmopm8Mesrchannel93Portn OBJECT-TYPE
	SYNTAX  INTEGER (0..65535)
	MAX-ACCESS read-only
	STATUS current
	DESCRIPTION
        "
        Channel93 Power :This OID indicates
        the channel power  (Power =Q8(Number
        format)) (Unit = dBm)  <Help> This
        measure indicates the channel power
        "
	::= { pmopm8Mesrchannel93Entry 2 }


--- *********************************************************
---     TABLE for the pmopm8Mesrchannel94 articles
--- *********************************************************

pmopm8Mesrchannel94Table OBJECT-TYPE
	SYNTAX  SEQUENCE OF Pmopm8Mesrchannel94Entry
	MAX-ACCESS not-accessible
	STATUS current
	DESCRIPTION
        "
        List of pmopm8Mesrchannel94 Article
        "
	::= { pmopm8MesrClient 760 }


pmopm8Mesrchannel94Entry OBJECT-TYPE
	SYNTAX Pmopm8Mesrchannel94Entry
	MAX-ACCESS not-accessible
	STATUS current
	DESCRIPTION
        "
        Row definition for the pmopm8Mesrchannel94
        table
        "
	INDEX   { pmopm8Mesrchannel94Index }
	::= { pmopm8Mesrchannel94Table 1 }


Pmopm8Mesrchannel94Entry ::=
	SEQUENCE {
	pmopm8Mesrchannel94Index
		INTEGER,
	pmopm8Mesrchannel94Portn
		INTEGER
	}


pmopm8Mesrchannel94Index OBJECT-TYPE
	SYNTAX  INTEGER(0..128)
	MAX-ACCESS  read-only
	STATUS current
	DESCRIPTION
        "
        Index definition for the pmopm8Mesrchannel94
        table
        "
	::= { pmopm8Mesrchannel94Entry 1 }


pmopm8Mesrchannel94Portn OBJECT-TYPE
	SYNTAX  INTEGER (0..65535)
	MAX-ACCESS read-only
	STATUS current
	DESCRIPTION
        "
        Channel94 Power :This OID indicates
        the channel power  (Power =Q8(Number
        format)) (Unit = dBm)  <Help> This
        measure indicates the channel power
        "
	::= { pmopm8Mesrchannel94Entry 2 }


--- *********************************************************
---     TABLE for the pmopm8Mesrchannel95 articles
--- *********************************************************

pmopm8Mesrchannel95Table OBJECT-TYPE
	SYNTAX  SEQUENCE OF Pmopm8Mesrchannel95Entry
	MAX-ACCESS not-accessible
	STATUS current
	DESCRIPTION
        "
        List of pmopm8Mesrchannel95 Article
        "
	::= { pmopm8MesrClient 768 }


pmopm8Mesrchannel95Entry OBJECT-TYPE
	SYNTAX Pmopm8Mesrchannel95Entry
	MAX-ACCESS not-accessible
	STATUS current
	DESCRIPTION
        "
        Row definition for the pmopm8Mesrchannel95
        table
        "
	INDEX   { pmopm8Mesrchannel95Index }
	::= { pmopm8Mesrchannel95Table 1 }


Pmopm8Mesrchannel95Entry ::=
	SEQUENCE {
	pmopm8Mesrchannel95Index
		INTEGER,
	pmopm8Mesrchannel95Portn
		INTEGER
	}


pmopm8Mesrchannel95Index OBJECT-TYPE
	SYNTAX  INTEGER(0..128)
	MAX-ACCESS  read-only
	STATUS current
	DESCRIPTION
        "
        Index definition for the pmopm8Mesrchannel95
        table
        "
	::= { pmopm8Mesrchannel95Entry 1 }


pmopm8Mesrchannel95Portn OBJECT-TYPE
	SYNTAX  INTEGER (0..65535)
	MAX-ACCESS read-only
	STATUS current
	DESCRIPTION
        "
        Channel95 Power :This OID indicates
        the channel power  (Power =Q8(Number
        format)) (Unit = dBm)  <Help> This
        measure indicates the channel power
        "
	::= { pmopm8Mesrchannel95Entry 2 }


--- *********************************************************
---     TABLE for the pmopm8Mesrchannel96 articles
--- *********************************************************

pmopm8Mesrchannel96Table OBJECT-TYPE
	SYNTAX  SEQUENCE OF Pmopm8Mesrchannel96Entry
	MAX-ACCESS not-accessible
	STATUS current
	DESCRIPTION
        "
        List of pmopm8Mesrchannel96 Article
        "
	::= { pmopm8MesrClient 776 }


pmopm8Mesrchannel96Entry OBJECT-TYPE
	SYNTAX Pmopm8Mesrchannel96Entry
	MAX-ACCESS not-accessible
	STATUS current
	DESCRIPTION
        "
        Row definition for the pmopm8Mesrchannel96
        table
        "
	INDEX   { pmopm8Mesrchannel96Index }
	::= { pmopm8Mesrchannel96Table 1 }


Pmopm8Mesrchannel96Entry ::=
	SEQUENCE {
	pmopm8Mesrchannel96Index
		INTEGER,
	pmopm8Mesrchannel96Portn
		INTEGER
	}


pmopm8Mesrchannel96Index OBJECT-TYPE
	SYNTAX  INTEGER(0..128)
	MAX-ACCESS  read-only
	STATUS current
	DESCRIPTION
        "
        Index definition for the pmopm8Mesrchannel96
        table
        "
	::= { pmopm8Mesrchannel96Entry 1 }


pmopm8Mesrchannel96Portn OBJECT-TYPE
	SYNTAX  INTEGER (0..65535)
	MAX-ACCESS read-only
	STATUS current
	DESCRIPTION
        "
        Channel96 Power :This OID indicates
        the channel power  (Power =Q8(Number
        format)) (Unit = dBm)  <Help> This
        measure indicates the channel power
        "
	::= { pmopm8Mesrchannel96Entry 2 }


--- *********************************************************
---     TABLE for the pmopm8MesrportInputPwr articles
--- *********************************************************

pmopm8MesrportInputPwrTable OBJECT-TYPE
	SYNTAX  SEQUENCE OF Pmopm8MesrportInputPwrEntry
	MAX-ACCESS not-accessible
	STATUS current
	DESCRIPTION
        "
        List of pmopm8MesrportInputPwr
        Article
        "
	::= { pmopm8MesrClient 784 }


pmopm8MesrportInputPwrEntry OBJECT-TYPE
	SYNTAX Pmopm8MesrportInputPwrEntry
	MAX-ACCESS not-accessible
	STATUS current
	DESCRIPTION
        "
        Row definition for the pmopm8MesrportInputPwr
        table
        "
	INDEX   { pmopm8MesrportInputPwrIndex }
	::= { pmopm8MesrportInputPwrTable 1 }


Pmopm8MesrportInputPwrEntry ::=
	SEQUENCE {
	pmopm8MesrportInputPwrIndex
		INTEGER,
	pmopm8MesrportInputPwrPortn
		INTEGER
	}


pmopm8MesrportInputPwrIndex OBJECT-TYPE
	SYNTAX  INTEGER(0..128)
	MAX-ACCESS  read-only
	STATUS current
	DESCRIPTION
        "
        Index definition for the pmopm8MesrportInputPwr
        table
        "
	::= { pmopm8MesrportInputPwrEntry 1 }


pmopm8MesrportInputPwrPortn OBJECT-TYPE
	SYNTAX  INTEGER (0..65535)
	MAX-ACCESS read-only
	STATUS current
	DESCRIPTION
        "
        OPM Port Input Power :This OID
        indicates the total input power
        on the OPM port (Power =Q8(Number
        format)) (Unit = dBm)  <Help> This
        measure indicates the total input
        power on the OPM port
        "
	::= { pmopm8MesrportInputPwrEntry 2 }


--- *********************************************************
---     TABLE for the pmopm8MesrchannelMaxPwr articles
--- *********************************************************

pmopm8MesrchannelMaxPwrTable OBJECT-TYPE
	SYNTAX  SEQUENCE OF Pmopm8MesrchannelMaxPwrEntry
	MAX-ACCESS not-accessible
	STATUS current
	DESCRIPTION
        "
        List of pmopm8MesrchannelMaxPwr
        Article
        "
	::= { pmopm8MesrClient 792 }


pmopm8MesrchannelMaxPwrEntry OBJECT-TYPE
	SYNTAX Pmopm8MesrchannelMaxPwrEntry
	MAX-ACCESS not-accessible
	STATUS current
	DESCRIPTION
        "
        Row definition for the pmopm8MesrchannelMaxPwr
        table
        "
	INDEX   { pmopm8MesrchannelMaxPwrIndex }
	::= { pmopm8MesrchannelMaxPwrTable 1 }


Pmopm8MesrchannelMaxPwrEntry ::=
	SEQUENCE {
	pmopm8MesrchannelMaxPwrIndex
		INTEGER,
	pmopm8MesrchannelMaxPwrPortn
		INTEGER
	}


pmopm8MesrchannelMaxPwrIndex OBJECT-TYPE
	SYNTAX  INTEGER(0..128)
	MAX-ACCESS  read-only
	STATUS current
	DESCRIPTION
        "
        Index definition for the pmopm8MesrchannelMaxPwr
        table
        "
	::= { pmopm8MesrchannelMaxPwrEntry 1 }


pmopm8MesrchannelMaxPwrPortn OBJECT-TYPE
	SYNTAX  INTEGER (0..65535)
	MAX-ACCESS read-only
	STATUS current
	DESCRIPTION
        "
        Channel Maximum Power :This OID
        indicates the maximum channel power
        on the OPM input port (Power =Q8(Number
        format)) (Unit = dBm)  <Help> This
        measure indicates the maximum channel
        power on the OPM input port
        "
	::= { pmopm8MesrchannelMaxPwrEntry 2 }


--- *********************************************************
---     TABLE for the pmopm8MesrchannelMinPwr articles
--- *********************************************************

pmopm8MesrchannelMinPwrTable OBJECT-TYPE
	SYNTAX  SEQUENCE OF Pmopm8MesrchannelMinPwrEntry
	MAX-ACCESS not-accessible
	STATUS current
	DESCRIPTION
        "
        List of pmopm8MesrchannelMinPwr
        Article
        "
	::= { pmopm8MesrClient 800 }


pmopm8MesrchannelMinPwrEntry OBJECT-TYPE
	SYNTAX Pmopm8MesrchannelMinPwrEntry
	MAX-ACCESS not-accessible
	STATUS current
	DESCRIPTION
        "
        Row definition for the pmopm8MesrchannelMinPwr
        table
        "
	INDEX   { pmopm8MesrchannelMinPwrIndex }
	::= { pmopm8MesrchannelMinPwrTable 1 }


Pmopm8MesrchannelMinPwrEntry ::=
	SEQUENCE {
	pmopm8MesrchannelMinPwrIndex
		INTEGER,
	pmopm8MesrchannelMinPwrPortn
		INTEGER
	}


pmopm8MesrchannelMinPwrIndex OBJECT-TYPE
	SYNTAX  INTEGER(0..128)
	MAX-ACCESS  read-only
	STATUS current
	DESCRIPTION
        "
        Index definition for the pmopm8MesrchannelMinPwr
        table
        "
	::= { pmopm8MesrchannelMinPwrEntry 1 }


pmopm8MesrchannelMinPwrPortn OBJECT-TYPE
	SYNTAX  INTEGER (0..65535)
	MAX-ACCESS read-only
	STATUS current
	DESCRIPTION
        "
        Channel Minimum Power :This OID
        indicates the minimum channel power
        on the OPM input port (Power =Q8(Number
        format)) (Unit = dBm)  <Help> This
        measure indicates the minimum channel
        power on the OPM input port
        "
	::= { pmopm8MesrchannelMinPwrEntry 2 }


--- *****************************************************
---     LEAF for the opmTemp article
--- *****************************************************

pmopm8MesropmTemp OBJECT-TYPE
	  SYNTAX Unsigned32 (0..65535)
	  MAX-ACCESS read-only
	  STATUS current
	  DESCRIPTION
        "
        PM OPM Temperature :This OID indicates
        the temperature of the PM OPM
         (Temperature = AV/256) (Unit =
        C)<Help> This measure indicates
        the temperature of the PM OPM
        "
	  ::= { pmopm8MesrOther 808 }








--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pmopm8DwlrestartProcess OBJECT IDENTIFIER ::= { pmopm8DwlOther 0 }




pmopm8DwlColdRestartProcessed OBJECT-TYPE
	  SYNTAX EkiOnOff
	  MAX-ACCESS read-only
	  STATUS current
	  DESCRIPTION
        "
        Cold Restart :This OID indicates
        that the module last restart was
        a Cold RESTART
        "
	  ::= { pmopm8DwlrestartProcess 2 }



pmopm8DwlWarmRestartProcessed OBJECT-TYPE
	  SYNTAX EkiOnOff
	  MAX-ACCESS read-only
	  STATUS current
	  DESCRIPTION
        "
        Warm Restart :This OID indicates
        that the module last restart was
        a Warm RESTART
        "
	  ::= { pmopm8DwlrestartProcess 1 }



--- *****************************************************
---     LEAF for the swBanksUsed article
--- *****************************************************
pmopm8DwlswBanksUsed OBJECT IDENTIFIER ::= { pmopm8DwlOther 1 }




pmopm8DwlSwBank2Notempty OBJECT-TYPE
	  SYNTAX EkiOnOff
	  MAX-ACCESS read-only
	  STATUS current
	  DESCRIPTION
        "
        SW bank 2 loaded :This OID indicates
        a software is loaded in SW bank
        2  <Help>  This status indicates
        if the SW bank 2 contains SW package
        "
	  ::= { pmopm8DwlswBanksUsed 6 }



pmopm8DwlSwBank1Notempty OBJECT-TYPE
	  SYNTAX EkiOnOff
	  MAX-ACCESS read-only
	  STATUS current
	  DESCRIPTION
        "
        SW bank 1 loaded :This OID indicates
        a software is loaded in SW bank
        1  <Help>  This status indicates
        if the SW bank 1 contains SW package
        "
	  ::= { pmopm8DwlswBanksUsed 5 }



pmopm8DwlSwBank2Used OBJECT-TYPE
	  SYNTAX EkiOnOff
	  MAX-ACCESS read-only
	  STATUS current
	  DESCRIPTION
        "
        SW bank 2 active :This OID indicates
        the module is working on SW bank
        2  <Help>  This status indicates
        if the SW bank 2 is active or standby
        "
	  ::= { pmopm8DwlswBanksUsed 2 }



pmopm8DwlSwBank1Used OBJECT-TYPE
	  SYNTAX EkiOnOff
	  MAX-ACCESS read-only
	  STATUS current
	  DESCRIPTION
        "
        SW bank 1 active :This OID indicates
        the module is working on SW bank
        1  <Help>  This status indicates
        if the SW bank 1 is active or standby
        "
	  ::= { pmopm8DwlswBanksUsed 1 }



--- *****************************************************
---     LEAF for the gwBanksUsed article
--- *****************************************************
pmopm8DwlgwBanksUsed OBJECT IDENTIFIER ::= { pmopm8DwlOther 2 }




pmopm8DwlGwBank4Notempty OBJECT-TYPE
	  SYNTAX EkiOnOff
	  MAX-ACCESS read-only
	  STATUS current
	  DESCRIPTION
        "
        GW bank 4 loaded :This OID indicates
        a gateware is loaded in GW bank
        4
        "
	  ::= { pmopm8DwlgwBanksUsed 8 }



pmopm8DwlGwBank3Notempty OBJECT-TYPE
	  SYNTAX EkiOnOff
	  MAX-ACCESS read-only
	  STATUS current
	  DESCRIPTION
        "
        GW bank 3 loaded :This OID indicates
        a gateware is loaded in GW bank
        3  <Help>  This status indicates
        if the GW bank 3 contains GW package
        "
	  ::= { pmopm8DwlgwBanksUsed 7 }



pmopm8DwlGwBank2Notempty OBJECT-TYPE
	  SYNTAX EkiOnOff
	  MAX-ACCESS read-only
	  STATUS current
	  DESCRIPTION
        "
        GW bank 2 loaded :This OID indicates
        a gateware is loaded in GW bank
        2
        "
	  ::= { pmopm8DwlgwBanksUsed 6 }



pmopm8DwlGwBank1Notempty OBJECT-TYPE
	  SYNTAX EkiOnOff
	  MAX-ACCESS read-only
	  STATUS current
	  DESCRIPTION
        "
        GW bank 1 loaded :This OID indicates
        a gateware is loaded in GW bank
        1  <Help>  This status indicates
        if the GW bank 1 contains GW package
        "
	  ::= { pmopm8DwlgwBanksUsed 5 }



pmopm8DwlGwBank4Used OBJECT-TYPE
	  SYNTAX EkiOnOff
	  MAX-ACCESS read-only
	  STATUS current
	  DESCRIPTION
        "
        GW bank 4 active :This OID indicates
        the module is working on GW bank
        4
        "
	  ::= { pmopm8DwlgwBanksUsed 4 }



pmopm8DwlGwBank3Used OBJECT-TYPE
	  SYNTAX EkiOnOff
	  MAX-ACCESS read-only
	  STATUS current
	  DESCRIPTION
        "
        GW bank 3 active :This OID indicates
        the module is working on GW bank
        3  <Help>  This status indicates
        if the GW bank 3 is active or standby
        "
	  ::= { pmopm8DwlgwBanksUsed 3 }



pmopm8DwlGwBank2Used OBJECT-TYPE
	  SYNTAX EkiOnOff
	  MAX-ACCESS read-only
	  STATUS current
	  DESCRIPTION
        "
        GW bank 2 active :This OID indicates
        the module is working on GW bank
        2
        "
	  ::= { pmopm8DwlgwBanksUsed 2 }



pmopm8DwlGwBank1Used OBJECT-TYPE
	  SYNTAX EkiOnOff
	  MAX-ACCESS read-only
	  STATUS current
	  DESCRIPTION
        "
        GW bank 1 active :This OID indicates
        the module is working on GW bank
        1  <Help>  This status indicates
        if the GW bank 1 is active or standby
        "
	  ::= { pmopm8DwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group lsd
--- *****************************************************

pmopm8CfgLsd OBJECT IDENTIFIER ::= { pmopm8Config 1 }



--- *****************************************************
---     LEAF for the table 0012
--- *****************************************************

pmopm8tableclientcaiscsf OBJECT IDENTIFIER ::= { pmopm8CfgLsd 1 }



--- *****************************************************
---     LEAF for the table Group startup
--- *****************************************************

pmopm8CfgStartup OBJECT IDENTIFIER ::= { pmopm8Config 2 }



--- *****************************************************
---     LEAF for the table 0005
--- *****************************************************

pmopm8tableother OBJECT IDENTIFIER ::= { pmopm8CfgStartup 1 }



pmopm8CfgcomponentType OBJECT-TYPE
	  SYNTAX Unsigned32 (0..65536)
	  MAX-ACCESS read-only
	  STATUS current
	  DESCRIPTION
        "
        Component parameters :This OID
        defines the component parameters
        "
	  ::= { pmopm8tableother 2 }



pmopm8Cfgmiscellaneous OBJECT-TYPE
	  SYNTAX Unsigned32 (0..65536)
	  MAX-ACCESS read-only
	  STATUS current
	  DESCRIPTION
        "
        Miscellaneous default settings
        :This OID defines the miscellaneous
        parameters
        "
	  ::= { pmopm8tableother 3 }



pmopm8CfgfirstChannel OBJECT-TYPE
	  SYNTAX Unsigned32 (0..65536)
	  MAX-ACCESS read-only
	  STATUS current
	  DESCRIPTION
        "
        Number of the first channel of
        the component :This OID defines
        the first channel number of the
        PMOPM
        "
	  ::= { pmopm8tableother 4 }



pmopm8CfglastChannel OBJECT-TYPE
	  SYNTAX Unsigned32 (0..65536)
	  MAX-ACCESS read-only
	  STATUS current
	  DESCRIPTION
        "
        Number of the last channel of
         the component :This OID defines
        the last channel number of the
         PMOPM
        "
	  ::= { pmopm8tableother 5 }



pmopm8Cfggrid OBJECT-TYPE
	  SYNTAX Unsigned32 (0..65536)
	  MAX-ACCESS read-only
	  STATUS current
	  DESCRIPTION
        "
        Grid value of the component :This
        OID defines the grid of the PMOPM
        "
	  ::= { pmopm8tableother 6 }



--- *****************************************************
---     LEAF for the table 2110
--- *****************************************************

pmopm8CfgClientStartupOosTable OBJECT-TYPE
	SYNTAX  SEQUENCE OF Pmopm8CfgClientStartupOosEntry
	MAX-ACCESS not-accessible
	STATUS current
	DESCRIPTION
        "
        List of  Article
        "
	::= { pmopm8CfgStartup 2 }


pmopm8CfgClientStartupOosEntry OBJECT-TYPE
	SYNTAX Pmopm8CfgClientStartupOosEntry
	MAX-ACCESS not-accessible
	STATUS current
	DESCRIPTION
        "
        Row definition for the startup
        table
        "
	INDEX   { pmopm8CfgClientStartupOosIndex }
	::= { pmopm8CfgClientStartupOosTable 1 }


Pmopm8CfgClientStartupOosEntry ::=
	SEQUENCE {
	pmopm8CfgClientStartupOosIndex
		INTEGER,
	pmopm8CfgSpectrumOosPortn
		Unsigned32,
	pmopm8CfgSpectrumOffsetPortn
		Unsigned32,
	pmopm8CfgCh1Ch16OosPortn
		Unsigned32,
	pmopm8CfgCh17Ch32OosPortn
		Unsigned32,
	pmopm8CfgCh33Ch48OosPortn
		Unsigned32,
	pmopm8CfgCh49Ch64OosPortn
		Unsigned32,
	pmopm8CfgCh65Ch80OosPortn
		Unsigned32,
	pmopm8CfgCh81Ch96OosPortn
		Unsigned32
	}


pmopm8CfgClientStartupOosIndex OBJECT-TYPE
	SYNTAX  INTEGER(0..128)
	MAX-ACCESS  read-only
	STATUS current
	DESCRIPTION
        "
        Index definition for the clientStartupOos
        table
        "
	::= { pmopm8CfgClientStartupOosEntry 1 }


pmopm8CfgSpectrumOosPortn OBJECT-TYPE
	SYNTAX  Unsigned32 (0..65536)
	MAX-ACCESS read-write
	STATUS current
	DESCRIPTION
        "
        Default Settings on Spectrum OOS
        :This OID sets the OPM input port
        out of service
        "
	::= { pmopm8CfgClientStartupOosEntry 3 }


pmopm8CfgSpectrumOffsetPortn OBJECT-TYPE
	SYNTAX  Unsigned32 (0..65536)
	MAX-ACCESS read-write
	STATUS current
	DESCRIPTION
        "
        Default Settings on Spectrum Offset
        :This OID defines a negative offset
        for the OPM input port
        "
	::= { pmopm8CfgClientStartupOosEntry 4 }


pmopm8CfgCh1Ch16OosPortn OBJECT-TYPE
	SYNTAX  Unsigned32 (0..65536)
	MAX-ACCESS read-write
	STATUS current
	DESCRIPTION
        "
        Default Settings on Channel OOS
        :This OID sets the channel out
         of service
        "
	::= { pmopm8CfgClientStartupOosEntry 5 }


pmopm8CfgCh17Ch32OosPortn OBJECT-TYPE
	SYNTAX  Unsigned32 (0..65536)
	MAX-ACCESS read-write
	STATUS current
	DESCRIPTION
        "
        Default Settings on Channel OOS
        :This OID sets the channel out
         of service
        "
	::= { pmopm8CfgClientStartupOosEntry 6 }


pmopm8CfgCh33Ch48OosPortn OBJECT-TYPE
	SYNTAX  Unsigned32 (0..65536)
	MAX-ACCESS read-write
	STATUS current
	DESCRIPTION
        "
        Default Settings on Channel OOS
        :This OID sets the channel out
         of service
        "
	::= { pmopm8CfgClientStartupOosEntry 7 }


pmopm8CfgCh49Ch64OosPortn OBJECT-TYPE
	SYNTAX  Unsigned32 (0..65536)
	MAX-ACCESS read-write
	STATUS current
	DESCRIPTION
        "
        Default Settings on Channel OOS
        :This OID sets the channel out
         of service
        "
	::= { pmopm8CfgClientStartupOosEntry 8 }


pmopm8CfgCh65Ch80OosPortn OBJECT-TYPE
	SYNTAX  Unsigned32 (0..65536)
	MAX-ACCESS read-write
	STATUS current
	DESCRIPTION
        "
        Default Settings on Channel OOS
        :This OID sets the channel out
         of service
        "
	::= { pmopm8CfgClientStartupOosEntry 9 }


pmopm8CfgCh81Ch96OosPortn OBJECT-TYPE
	SYNTAX  Unsigned32 (0..65536)
	MAX-ACCESS read-write
	STATUS current
	DESCRIPTION
        "
        Default Settings on Channel OOS
        :This OID sets the channel out
         of service
        "
	::= { pmopm8CfgClientStartupOosEntry 10 }


--- *****************************************************
---     LEAF for the table 2111
--- *****************************************************

pmopm8CfgClientStartupBalanceTable OBJECT-TYPE
	SYNTAX  SEQUENCE OF Pmopm8CfgClientStartupBalanceEntry
	MAX-ACCESS not-accessible
	STATUS current
	DESCRIPTION
        "
        List of  Article
        "
	::= { pmopm8CfgStartup 3 }


pmopm8CfgClientStartupBalanceEntry OBJECT-TYPE
	SYNTAX Pmopm8CfgClientStartupBalanceEntry
	MAX-ACCESS not-accessible
	STATUS current
	DESCRIPTION
        "
        Row definition for the startup
        table
        "
	INDEX   { pmopm8CfgClientStartupBalanceIndex }
	::= { pmopm8CfgClientStartupBalanceTable 1 }


Pmopm8CfgClientStartupBalanceEntry ::=
	SEQUENCE {
	pmopm8CfgClientStartupBalanceIndex
		INTEGER,
	pmopm8CfgCh1Ch16BalancePortn
		Unsigned32,
	pmopm8CfgCh17Ch32BalancePortn
		Unsigned32,
	pmopm8CfgCh33Ch48BalancePortn
		Unsigned32,
	pmopm8CfgCh49Ch64BalancePortn
		Unsigned32,
	pmopm8CfgCh65Ch80BalancePortn
		Unsigned32,
	pmopm8CfgCh81Ch96BalancePortn
		Unsigned32
	}


pmopm8CfgClientStartupBalanceIndex OBJECT-TYPE
	SYNTAX  INTEGER(0..128)
	MAX-ACCESS  read-only
	STATUS current
	DESCRIPTION
        "
        Index definition for the clientStartupBalance
        table
        "
	::= { pmopm8CfgClientStartupBalanceEntry 1 }


pmopm8CfgCh1Ch16BalancePortn OBJECT-TYPE
	SYNTAX  Unsigned32 (0..65536)
	MAX-ACCESS read-write
	STATUS current
	DESCRIPTION
        "
        Default Settings on Balance :This
        OID is used by the Ekinops auto
        turn up application to tag the
         channel as balanced
        "
	::= { pmopm8CfgClientStartupBalanceEntry 3 }


pmopm8CfgCh17Ch32BalancePortn OBJECT-TYPE
	SYNTAX  Unsigned32 (0..65536)
	MAX-ACCESS read-write
	STATUS current
	DESCRIPTION
        "
        Default Settings on Balance :This
        OID is used by the Ekinops auto
        turn up application to tag the
         channel as balanced
        "
	::= { pmopm8CfgClientStartupBalanceEntry 4 }


pmopm8CfgCh33Ch48BalancePortn OBJECT-TYPE
	SYNTAX  Unsigned32 (0..65536)
	MAX-ACCESS read-write
	STATUS current
	DESCRIPTION
        "
        Default Settings on Balance :This
        OID is used by the Ekinops auto
        turn up application to tag the
         channel as balanced
        "
	::= { pmopm8CfgClientStartupBalanceEntry 5 }


pmopm8CfgCh49Ch64BalancePortn OBJECT-TYPE
	SYNTAX  Unsigned32 (0..65536)
	MAX-ACCESS read-write
	STATUS current
	DESCRIPTION
        "
        Default Settings on Balance :This
        OID is used by the Ekinops auto
        turn up application to tag the
         channel as balanced
        "
	::= { pmopm8CfgClientStartupBalanceEntry 6 }


pmopm8CfgCh65Ch80BalancePortn OBJECT-TYPE
	SYNTAX  Unsigned32 (0..65536)
	MAX-ACCESS read-write
	STATUS current
	DESCRIPTION
        "
        Default Settings on Balance :This
        OID is used by the Ekinops auto
        turn up application to tag the
         channel as balanced
        "
	::= { pmopm8CfgClientStartupBalanceEntry 7 }


pmopm8CfgCh81Ch96BalancePortn OBJECT-TYPE
	SYNTAX  Unsigned32 (0..65536)
	MAX-ACCESS read-write
	STATUS current
	DESCRIPTION
        "
        Default Settings on Balance :This
        OID is used by the Ekinops auto
        turn up application to tag the
         channel as balanced
        "
	::= { pmopm8CfgClientStartupBalanceEntry 8 }


--- *****************************************************
---     LEAF for the table 2112
--- *****************************************************

pmopm8CfgClientStartupAbsthreshTable OBJECT-TYPE
	SYNTAX  SEQUENCE OF Pmopm8CfgClientStartupAbsthreshEntry
	MAX-ACCESS not-accessible
	STATUS current
	DESCRIPTION
        "
        List of  Article
        "
	::= { pmopm8CfgStartup 4 }


pmopm8CfgClientStartupAbsthreshEntry OBJECT-TYPE
	SYNTAX Pmopm8CfgClientStartupAbsthreshEntry
	MAX-ACCESS not-accessible
	STATUS current
	DESCRIPTION
        "
        Row definition for the startup
        table
        "
	INDEX   { pmopm8CfgClientStartupAbsthreshIndex }
	::= { pmopm8CfgClientStartupAbsthreshTable 1 }


Pmopm8CfgClientStartupAbsthreshEntry ::=
	SEQUENCE {
	pmopm8CfgClientStartupAbsthreshIndex
		INTEGER,
	pmopm8CfgChannel1AbsthreshPortn
		Unsigned32,
	pmopm8CfgChannel2AbsthreshPortn
		Unsigned32,
	pmopm8CfgChannel3AbsthreshPortn
		Unsigned32,
	pmopm8CfgChannel4AbsthreshPortn
		Unsigned32,
	pmopm8CfgChannel5AbsthreshPortn
		Unsigned32,
	pmopm8CfgChannel6AbsthreshPortn
		Unsigned32,
	pmopm8CfgChannel7AbsthreshPortn
		Unsigned32,
	pmopm8CfgChannel8AbsthreshPortn
		Unsigned32,
	pmopm8CfgChannel9AbsthreshPortn
		Unsigned32,
	pmopm8CfgChannel10AbsthreshPortn
		Unsigned32,
	pmopm8CfgChannel11AbsthreshPortn
		Unsigned32,
	pmopm8CfgChannel12AbsthreshPortn
		Unsigned32,
	pmopm8CfgChannel13AbsthreshPortn
		Unsigned32,
	pmopm8CfgChannel14AbsthreshPortn
		Unsigned32,
	pmopm8CfgChannel15AbsthreshPortn
		Unsigned32,
	pmopm8CfgChannel16AbsthreshPortn
		Unsigned32,
	pmopm8CfgChannel17AbsthreshPortn
		Unsigned32,
	pmopm8CfgChannel18AbsthreshPortn
		Unsigned32,
	pmopm8CfgChannel19AbsthreshPortn
		Unsigned32,
	pmopm8CfgChannel20AbsthreshPortn
		Unsigned32,
	pmopm8CfgChannel21AbsthreshPortn
		Unsigned32,
	pmopm8CfgChannel22AbsthreshPortn
		Unsigned32,
	pmopm8CfgChannel23AbsthreshPortn
		Unsigned32,
	pmopm8CfgChannel24AbsthreshPortn
		Unsigned32,
	pmopm8CfgChannel25AbsthreshPortn
		Unsigned32,
	pmopm8CfgChannel26AbsthreshPortn
		Unsigned32,
	pmopm8CfgChannel27AbsthreshPortn
		Unsigned32,
	pmopm8CfgChannel28AbsthreshPortn
		Unsigned32,
	pmopm8CfgChannel29AbsthreshPortn
		Unsigned32,
	pmopm8CfgChannel30AbsthreshPortn
		Unsigned32,
	pmopm8CfgChannel31AbsthreshPortn
		Unsigned32,
	pmopm8CfgChannel32AbsthreshPortn
		Unsigned32,
	pmopm8CfgChannel33AbsthreshPortn
		Unsigned32,
	pmopm8CfgChannel34AbsthreshPortn
		Unsigned32,
	pmopm8CfgChannel35AbsthreshPortn
		Unsigned32,
	pmopm8CfgChannel36AbsthreshPortn
		Unsigned32,
	pmopm8CfgChannel37AbsthreshPortn
		Unsigned32,
	pmopm8CfgChannel38AbsthreshPortn
		Unsigned32,
	pmopm8CfgChannel39AbsthreshPortn
		Unsigned32,
	pmopm8CfgChannel40AbsthreshPortn
		Unsigned32,
	pmopm8CfgChannel41AbsthreshPortn
		Unsigned32,
	pmopm8CfgChannel42AbsthreshPortn
		Unsigned32,
	pmopm8CfgChannel43AbsthreshPortn
		Unsigned32,
	pmopm8CfgChannel44AbsthreshPortn
		Unsigned32,
	pmopm8CfgChannel45AbsthreshPortn
		Unsigned32,
	pmopm8CfgChannel46AbsthreshPortn
		Unsigned32,
	pmopm8CfgChannel47AbsthreshPortn
		Unsigned32,
	pmopm8CfgChannel48AbsthreshPortn
		Unsigned32,
	pmopm8CfgChannel49AbsthreshPortn
		Unsigned32,
	pmopm8CfgChannel50AbsthreshPortn
		Unsigned32,
	pmopm8CfgChannel51AbsthreshPortn
		Unsigned32,
	pmopm8CfgChannel52AbsthreshPortn
		Unsigned32,
	pmopm8CfgChannel53AbsthreshPortn
		Unsigned32,
	pmopm8CfgChannel54AbsthreshPortn
		Unsigned32,
	pmopm8CfgChannel55AbsthreshPortn
		Unsigned32,
	pmopm8CfgChannel56AbsthreshPortn
		Unsigned32,
	pmopm8CfgChannel57AbsthreshPortn
		Unsigned32,
	pmopm8CfgChannel58AbsthreshPortn
		Unsigned32,
	pmopm8CfgChannel59AbsthreshPortn
		Unsigned32,
	pmopm8CfgChannel60AbsthreshPortn
		Unsigned32,
	pmopm8CfgChannel61AbsthreshPortn
		Unsigned32,
	pmopm8CfgChannel62AbsthreshPortn
		Unsigned32,
	pmopm8CfgChannel63AbsthreshPortn
		Unsigned32,
	pmopm8CfgChannel64AbsthreshPortn
		Unsigned32,
	pmopm8CfgChannel65AbsthreshPortn
		Unsigned32,
	pmopm8CfgChannel66AbsthreshPortn
		Unsigned32,
	pmopm8CfgChannel67AbsthreshPortn
		Unsigned32,
	pmopm8CfgChannel68AbsthreshPortn
		Unsigned32,
	pmopm8CfgChannel69AbsthreshPortn
		Unsigned32,
	pmopm8CfgChannel70AbsthreshPortn
		Unsigned32,
	pmopm8CfgChannel71AbsthreshPortn
		Unsigned32,
	pmopm8CfgChannel72AbsthreshPortn
		Unsigned32,
	pmopm8CfgChannel73AbsthreshPortn
		Unsigned32,
	pmopm8CfgChannel74AbsthreshPortn
		Unsigned32,
	pmopm8CfgChannel75AbsthreshPortn
		Unsigned32,
	pmopm8CfgChannel76AbsthreshPortn
		Unsigned32,
	pmopm8CfgChannel77AbsthreshPortn
		Unsigned32,
	pmopm8CfgChannel78AbsthreshPortn
		Unsigned32,
	pmopm8CfgChannel79AbsthreshPortn
		Unsigned32,
	pmopm8CfgChannel80AbsthreshPortn
		Unsigned32,
	pmopm8CfgChannel81AbsthreshPortn
		Unsigned32,
	pmopm8CfgChannel82AbsthreshPortn
		Unsigned32,
	pmopm8CfgChannel83AbsthreshPortn
		Unsigned32,
	pmopm8CfgChannel84AbsthreshPortn
		Unsigned32,
	pmopm8CfgChannel85AbsthreshPortn
		Unsigned32,
	pmopm8CfgChannel86AbsthreshPortn
		Unsigned32,
	pmopm8CfgChannel87AbsthreshPortn
		Unsigned32,
	pmopm8CfgChannel88AbsthreshPortn
		Unsigned32,
	pmopm8CfgChannel89AbsthreshPortn
		Unsigned32,
	pmopm8CfgChannel90AbsthreshPortn
		Unsigned32,
	pmopm8CfgChannel91AbsthreshPortn
		Unsigned32,
	pmopm8CfgChannel92AbsthreshPortn
		Unsigned32,
	pmopm8CfgChannel93AbsthreshPortn
		Unsigned32,
	pmopm8CfgChannel94AbsthreshPortn
		Unsigned32,
	pmopm8CfgChannel95AbsthreshPortn
		Unsigned32,
	pmopm8CfgChannel96AbsthreshPortn
		Unsigned32
	}


pmopm8CfgClientStartupAbsthreshIndex OBJECT-TYPE
	SYNTAX  INTEGER(0..128)
	MAX-ACCESS  read-only
	STATUS current
	DESCRIPTION
        "
        Index definition for the clientStartupAbsthresh
        table
        "
	::= { pmopm8CfgClientStartupAbsthreshEntry 1 }


pmopm8CfgChannel1AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 3 }


pmopm8CfgChannel2AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 4 }


pmopm8CfgChannel3AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 5 }


pmopm8CfgChannel4AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 6 }


pmopm8CfgChannel5AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 7 }


pmopm8CfgChannel6AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 8 }


pmopm8CfgChannel7AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 9 }


pmopm8CfgChannel8AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 10 }


pmopm8CfgChannel9AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 11 }


pmopm8CfgChannel10AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 12 }


pmopm8CfgChannel11AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 13 }


pmopm8CfgChannel12AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 14 }


pmopm8CfgChannel13AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 15 }


pmopm8CfgChannel14AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 16 }


pmopm8CfgChannel15AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 17 }


pmopm8CfgChannel16AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 18 }


pmopm8CfgChannel17AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 19 }


pmopm8CfgChannel18AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 20 }


pmopm8CfgChannel19AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 21 }


pmopm8CfgChannel20AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 22 }


pmopm8CfgChannel21AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 23 }


pmopm8CfgChannel22AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 24 }


pmopm8CfgChannel23AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 25 }


pmopm8CfgChannel24AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 26 }


pmopm8CfgChannel25AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 27 }


pmopm8CfgChannel26AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 28 }


pmopm8CfgChannel27AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 29 }


pmopm8CfgChannel28AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 30 }


pmopm8CfgChannel29AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 31 }


pmopm8CfgChannel30AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 32 }


pmopm8CfgChannel31AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 33 }


pmopm8CfgChannel32AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 34 }


pmopm8CfgChannel33AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 35 }


pmopm8CfgChannel34AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 36 }


pmopm8CfgChannel35AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 37 }


pmopm8CfgChannel36AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 38 }


pmopm8CfgChannel37AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 39 }


pmopm8CfgChannel38AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 40 }


pmopm8CfgChannel39AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 41 }


pmopm8CfgChannel40AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 42 }


pmopm8CfgChannel41AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 43 }


pmopm8CfgChannel42AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 44 }


pmopm8CfgChannel43AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 45 }


pmopm8CfgChannel44AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 46 }


pmopm8CfgChannel45AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 47 }


pmopm8CfgChannel46AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 48 }


pmopm8CfgChannel47AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 49 }


pmopm8CfgChannel48AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 50 }


pmopm8CfgChannel49AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 51 }


pmopm8CfgChannel50AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 52 }


pmopm8CfgChannel51AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 53 }


pmopm8CfgChannel52AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 54 }


pmopm8CfgChannel53AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 55 }


pmopm8CfgChannel54AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 56 }


pmopm8CfgChannel55AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 57 }


pmopm8CfgChannel56AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 58 }


pmopm8CfgChannel57AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 59 }


pmopm8CfgChannel58AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 60 }


pmopm8CfgChannel59AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 61 }


pmopm8CfgChannel60AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 62 }


pmopm8CfgChannel61AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 63 }


pmopm8CfgChannel62AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 64 }


pmopm8CfgChannel63AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 65 }


pmopm8CfgChannel64AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 66 }


pmopm8CfgChannel65AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 67 }


pmopm8CfgChannel66AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 68 }


pmopm8CfgChannel67AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 69 }


pmopm8CfgChannel68AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 70 }


pmopm8CfgChannel69AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 71 }


pmopm8CfgChannel70AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 72 }


pmopm8CfgChannel71AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 73 }


pmopm8CfgChannel72AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 74 }


pmopm8CfgChannel73AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 75 }


pmopm8CfgChannel74AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 76 }


pmopm8CfgChannel75AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 77 }


pmopm8CfgChannel76AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 78 }


pmopm8CfgChannel77AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 79 }


pmopm8CfgChannel78AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 80 }


pmopm8CfgChannel79AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 81 }


pmopm8CfgChannel80AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 82 }


pmopm8CfgChannel81AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 83 }


pmopm8CfgChannel82AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 84 }


pmopm8CfgChannel83AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 85 }


pmopm8CfgChannel84AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 86 }


pmopm8CfgChannel85AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 87 }


pmopm8CfgChannel86AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 88 }


pmopm8CfgChannel87AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 89 }


pmopm8CfgChannel88AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 90 }


pmopm8CfgChannel89AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 91 }


pmopm8CfgChannel90AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 92 }


pmopm8CfgChannel91AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 93 }


pmopm8CfgChannel92AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 94 }


pmopm8CfgChannel93AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 95 }


pmopm8CfgChannel94AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 96 }


pmopm8CfgChannel95AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 97 }


pmopm8CfgChannel96AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm8CfgClientStartupAbsthreshEntry 98 }


--- *****************************************************
---     LEAF for the table 2113
--- *****************************************************

pmopm8CfgClientStartupPwrHighTable OBJECT-TYPE
	SYNTAX  SEQUENCE OF Pmopm8CfgClientStartupPwrHighEntry
	MAX-ACCESS not-accessible
	STATUS current
	DESCRIPTION
        "
        List of  Article
        "
	::= { pmopm8CfgStartup 5 }


pmopm8CfgClientStartupPwrHighEntry OBJECT-TYPE
	SYNTAX Pmopm8CfgClientStartupPwrHighEntry
	MAX-ACCESS not-accessible
	STATUS current
	DESCRIPTION
        "
        Row definition for the startup
        table
        "
	INDEX   { pmopm8CfgClientStartupPwrHighIndex }
	::= { pmopm8CfgClientStartupPwrHighTable 1 }


Pmopm8CfgClientStartupPwrHighEntry ::=
	SEQUENCE {
	pmopm8CfgClientStartupPwrHighIndex
		INTEGER,
	pmopm8CfgChannel1PwrhighPortn
		Unsigned32,
	pmopm8CfgChannel2PwrhighPortn
		Unsigned32,
	pmopm8CfgChannel3PwrhighPortn
		Unsigned32,
	pmopm8CfgChannel4PwrhighPortn
		Unsigned32,
	pmopm8CfgChannel5PwrhighPortn
		Unsigned32,
	pmopm8CfgChannel6PwrhighPortn
		Unsigned32,
	pmopm8CfgChannel7PwrhighPortn
		Unsigned32,
	pmopm8CfgChannel8PwrhighPortn
		Unsigned32,
	pmopm8CfgChannel9PwrhighPortn
		Unsigned32,
	pmopm8CfgChannel10PwrhighPortn
		Unsigned32,
	pmopm8CfgChannel11PwrhighPortn
		Unsigned32,
	pmopm8CfgChannel12PwrhighPortn
		Unsigned32,
	pmopm8CfgChannel13PwrhighPortn
		Unsigned32,
	pmopm8CfgChannel14PwrhighPortn
		Unsigned32,
	pmopm8CfgChannel15PwrhighPortn
		Unsigned32,
	pmopm8CfgChannel16PwrhighPortn
		Unsigned32,
	pmopm8CfgChannel17PwrhighPortn
		Unsigned32,
	pmopm8CfgChannel18PwrhighPortn
		Unsigned32,
	pmopm8CfgChannel19PwrhighPortn
		Unsigned32,
	pmopm8CfgChannel20PwrhighPortn
		Unsigned32,
	pmopm8CfgChannel21PwrhighPortn
		Unsigned32,
	pmopm8CfgChannel22PwrhighPortn
		Unsigned32,
	pmopm8CfgChannel23PwrhighPortn
		Unsigned32,
	pmopm8CfgChannel24PwrhighPortn
		Unsigned32,
	pmopm8CfgChannel25PwrhighPortn
		Unsigned32,
	pmopm8CfgChannel26PwrhighPortn
		Unsigned32,
	pmopm8CfgChannel27PwrhighPortn
		Unsigned32,
	pmopm8CfgChannel28PwrhighPortn
		Unsigned32,
	pmopm8CfgChannel29PwrhighPortn
		Unsigned32,
	pmopm8CfgChannel30PwrhighPortn
		Unsigned32,
	pmopm8CfgChannel31PwrhighPortn
		Unsigned32,
	pmopm8CfgChannel32PwrhighPortn
		Unsigned32,
	pmopm8CfgChannel33PwrhighPortn
		Unsigned32,
	pmopm8CfgChannel34PwrhighPortn
		Unsigned32,
	pmopm8CfgChannel35PwrhighPortn
		Unsigned32,
	pmopm8CfgChannel36PwrhighPortn
		Unsigned32,
	pmopm8CfgChannel37PwrhighPortn
		Unsigned32,
	pmopm8CfgChannel38PwrhighPortn
		Unsigned32,
	pmopm8CfgChannel39PwrhighPortn
		Unsigned32,
	pmopm8CfgChannel40PwrhighPortn
		Unsigned32,
	pmopm8CfgChannel41PwrhighPortn
		Unsigned32,
	pmopm8CfgChannel42PwrhighPortn
		Unsigned32,
	pmopm8CfgChannel43PwrhighPortn
		Unsigned32,
	pmopm8CfgChannel44PwrhighPortn
		Unsigned32,
	pmopm8CfgChannel45PwrhighPortn
		Unsigned32,
	pmopm8CfgChannel46PwrhighPortn
		Unsigned32,
	pmopm8CfgChannel47PwrhighPortn
		Unsigned32,
	pmopm8CfgChannel48PwrhighPortn
		Unsigned32,
	pmopm8CfgChannel49PwrhighPortn
		Unsigned32,
	pmopm8CfgChannel50PwrhighPortn
		Unsigned32,
	pmopm8CfgChannel51PwrhighPortn
		Unsigned32,
	pmopm8CfgChannel52PwrhighPortn
		Unsigned32,
	pmopm8CfgChannel53PwrhighPortn
		Unsigned32,
	pmopm8CfgChannel54PwrhighPortn
		Unsigned32,
	pmopm8CfgChannel55PwrhighPortn
		Unsigned32,
	pmopm8CfgChannel56PwrhighPortn
		Unsigned32,
	pmopm8CfgChannel57PwrhighPortn
		Unsigned32,
	pmopm8CfgChannel58PwrhighPortn
		Unsigned32,
	pmopm8CfgChannel59PwrhighPortn
		Unsigned32,
	pmopm8CfgChannel60PwrhighPortn
		Unsigned32,
	pmopm8CfgChannel61PwrhighPortn
		Unsigned32,
	pmopm8CfgChannel62PwrhighPortn
		Unsigned32,
	pmopm8CfgChannel63PwrhighPortn
		Unsigned32,
	pmopm8CfgChannel64PwrhighPortn
		Unsigned32,
	pmopm8CfgChannel65PwrhighPortn
		Unsigned32,
	pmopm8CfgChannel66PwrhighPortn
		Unsigned32,
	pmopm8CfgChannel67PwrhighPortn
		Unsigned32,
	pmopm8CfgChannel68PwrhighPortn
		Unsigned32,
	pmopm8CfgChannel69PwrhighPortn
		Unsigned32,
	pmopm8CfgChannel70PwrhighPortn
		Unsigned32,
	pmopm8CfgChannel71PwrhighPortn
		Unsigned32,
	pmopm8CfgChannel72PwrhighPortn
		Unsigned32,
	pmopm8CfgChannel73PwrhighPortn
		Unsigned32,
	pmopm8CfgChannel74PwrhighPortn
		Unsigned32,
	pmopm8CfgChannel75PwrhighPortn
		Unsigned32,
	pmopm8CfgChannel76PwrhighPortn
		Unsigned32,
	pmopm8CfgChannel77PwrhighPortn
		Unsigned32,
	pmopm8CfgChannel78PwrhighPortn
		Unsigned32,
	pmopm8CfgChannel79PwrhighPortn
		Unsigned32,
	pmopm8CfgChannel80PwrhighPortn
		Unsigned32,
	pmopm8CfgChannel81PwrhighPortn
		Unsigned32,
	pmopm8CfgChannel82PwrhighPortn
		Unsigned32,
	pmopm8CfgChannel83PwrhighPortn
		Unsigned32,
	pmopm8CfgChannel84PwrhighPortn
		Unsigned32,
	pmopm8CfgChannel85PwrhighPortn
		Unsigned32,
	pmopm8CfgChannel86PwrhighPortn
		Unsigned32,
	pmopm8CfgChannel87PwrhighPortn
		Unsigned32,
	pmopm8CfgChannel88PwrhighPortn
		Unsigned32,
	pmopm8CfgChannel89PwrhighPortn
		Unsigned32,
	pmopm8CfgChannel90PwrhighPortn
		Unsigned32,
	pmopm8CfgChannel91PwrhighPortn
		Unsigned32,
	pmopm8CfgChannel92PwrhighPortn
		Unsigned32,
	pmopm8CfgChannel93PwrhighPortn
		Unsigned32,
	pmopm8CfgChannel94PwrhighPortn
		Unsigned32,
	pmopm8CfgChannel95PwrhighPortn
		Unsigned32,
	pmopm8CfgChannel96PwrhighPortn
		Unsigned32
	}


pmopm8CfgClientStartupPwrHighIndex OBJECT-TYPE
	SYNTAX  INTEGER(0..128)
	MAX-ACCESS  read-only
	STATUS current
	DESCRIPTION
        "
        Index definition for the clientStartupPwrHigh
        table
        "
	::= { pmopm8CfgClientStartupPwrHighEntry 1 }


pmopm8CfgChannel1PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 3 }


pmopm8CfgChannel2PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 4 }


pmopm8CfgChannel3PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 5 }


pmopm8CfgChannel4PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 6 }


pmopm8CfgChannel5PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 7 }


pmopm8CfgChannel6PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 8 }


pmopm8CfgChannel7PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 9 }


pmopm8CfgChannel8PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 10 }


pmopm8CfgChannel9PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 11 }


pmopm8CfgChannel10PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 12 }


pmopm8CfgChannel11PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 13 }


pmopm8CfgChannel12PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 14 }


pmopm8CfgChannel13PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 15 }


pmopm8CfgChannel14PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 16 }


pmopm8CfgChannel15PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 17 }


pmopm8CfgChannel16PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 18 }


pmopm8CfgChannel17PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 19 }


pmopm8CfgChannel18PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 20 }


pmopm8CfgChannel19PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 21 }


pmopm8CfgChannel20PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 22 }


pmopm8CfgChannel21PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 23 }


pmopm8CfgChannel22PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 24 }


pmopm8CfgChannel23PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 25 }


pmopm8CfgChannel24PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 26 }


pmopm8CfgChannel25PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 27 }


pmopm8CfgChannel26PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 28 }


pmopm8CfgChannel27PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 29 }


pmopm8CfgChannel28PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 30 }


pmopm8CfgChannel29PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 31 }


pmopm8CfgChannel30PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 32 }


pmopm8CfgChannel31PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 33 }


pmopm8CfgChannel32PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 34 }


pmopm8CfgChannel33PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 35 }


pmopm8CfgChannel34PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 36 }


pmopm8CfgChannel35PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 37 }


pmopm8CfgChannel36PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 38 }


pmopm8CfgChannel37PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 39 }


pmopm8CfgChannel38PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 40 }


pmopm8CfgChannel39PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 41 }


pmopm8CfgChannel40PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 42 }


pmopm8CfgChannel41PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 43 }


pmopm8CfgChannel42PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 44 }


pmopm8CfgChannel43PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 45 }


pmopm8CfgChannel44PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 46 }


pmopm8CfgChannel45PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 47 }


pmopm8CfgChannel46PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 48 }


pmopm8CfgChannel47PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 49 }


pmopm8CfgChannel48PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 50 }


pmopm8CfgChannel49PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 51 }


pmopm8CfgChannel50PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 52 }


pmopm8CfgChannel51PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 53 }


pmopm8CfgChannel52PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 54 }


pmopm8CfgChannel53PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 55 }


pmopm8CfgChannel54PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 56 }


pmopm8CfgChannel55PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 57 }


pmopm8CfgChannel56PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 58 }


pmopm8CfgChannel57PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 59 }


pmopm8CfgChannel58PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 60 }


pmopm8CfgChannel59PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 61 }


pmopm8CfgChannel60PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 62 }


pmopm8CfgChannel61PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 63 }


pmopm8CfgChannel62PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 64 }


pmopm8CfgChannel63PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 65 }


pmopm8CfgChannel64PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 66 }


pmopm8CfgChannel65PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 67 }


pmopm8CfgChannel66PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 68 }


pmopm8CfgChannel67PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 69 }


pmopm8CfgChannel68PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 70 }


pmopm8CfgChannel69PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 71 }


pmopm8CfgChannel70PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 72 }


pmopm8CfgChannel71PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 73 }


pmopm8CfgChannel72PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 74 }


pmopm8CfgChannel73PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 75 }


pmopm8CfgChannel74PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 76 }


pmopm8CfgChannel75PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 77 }


pmopm8CfgChannel76PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 78 }


pmopm8CfgChannel77PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 79 }


pmopm8CfgChannel78PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 80 }


pmopm8CfgChannel79PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 81 }


pmopm8CfgChannel80PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 82 }


pmopm8CfgChannel81PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 83 }


pmopm8CfgChannel82PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 84 }


pmopm8CfgChannel83PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 85 }


pmopm8CfgChannel84PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 86 }


pmopm8CfgChannel85PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 87 }


pmopm8CfgChannel86PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 88 }


pmopm8CfgChannel87PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 89 }


pmopm8CfgChannel88PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 90 }


pmopm8CfgChannel89PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 91 }


pmopm8CfgChannel90PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 92 }


pmopm8CfgChannel91PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 93 }


pmopm8CfgChannel92PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 94 }


pmopm8CfgChannel93PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 95 }


pmopm8CfgChannel94PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 96 }


pmopm8CfgChannel95PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 97 }


pmopm8CfgChannel96PwrhighPortn OBJECT-TYPE
	SYNTAX  Unsigned32 (0..65536)
	MAX-ACCESS read-write
	STATUS current
	DESCRIPTION
        "
        Default Settings on Max Power
         :This OID defines the threshold
        to rise a channel power high
        "
	::= { pmopm8CfgClientStartupPwrHighEntry 98 }


--- *****************************************************
---     LEAF for the table 2114
--- *****************************************************

pmopm8CfgClientStartupPwrLowTable OBJECT-TYPE
	SYNTAX  SEQUENCE OF Pmopm8CfgClientStartupPwrLowEntry
	MAX-ACCESS not-accessible
	STATUS current
	DESCRIPTION
        "
        List of  Article
        "
	::= { pmopm8CfgStartup 6 }


pmopm8CfgClientStartupPwrLowEntry OBJECT-TYPE
	SYNTAX Pmopm8CfgClientStartupPwrLowEntry
	MAX-ACCESS not-accessible
	STATUS current
	DESCRIPTION
        "
        Row definition for the startup
        table
        "
	INDEX   { pmopm8CfgClientStartupPwrLowIndex }
	::= { pmopm8CfgClientStartupPwrLowTable 1 }


Pmopm8CfgClientStartupPwrLowEntry ::=
	SEQUENCE {
	pmopm8CfgClientStartupPwrLowIndex
		INTEGER,
	pmopm8CfgChannel1PwrlowPortn
		Unsigned32,
	pmopm8CfgChannel2PwrlowPortn
		Unsigned32,
	pmopm8CfgChannel3PwrlowPortn
		Unsigned32,
	pmopm8CfgChannel4PwrlowPortn
		Unsigned32,
	pmopm8CfgChannel5PwrlowPortn
		Unsigned32,
	pmopm8CfgChannel6PwrlowPortn
		Unsigned32,
	pmopm8CfgChannel7PwrlowPortn
		Unsigned32,
	pmopm8CfgChannel8PwrlowPortn
		Unsigned32,
	pmopm8CfgChannel9PwrlowPortn
		Unsigned32,
	pmopm8CfgChannel10PwrlowPortn
		Unsigned32,
	pmopm8CfgChannel11PwrlowPortn
		Unsigned32,
	pmopm8CfgChannel12PwrlowPortn
		Unsigned32,
	pmopm8CfgChannel13PwrlowPortn
		Unsigned32,
	pmopm8CfgChannel14PwrlowPortn
		Unsigned32,
	pmopm8CfgChannel15PwrlowPortn
		Unsigned32,
	pmopm8CfgChannel16PwrlowPortn
		Unsigned32,
	pmopm8CfgChannel17PwrlowPortn
		Unsigned32,
	pmopm8CfgChannel18PwrlowPortn
		Unsigned32,
	pmopm8CfgChannel19PwrlowPortn
		Unsigned32,
	pmopm8CfgChannel20PwrlowPortn
		Unsigned32,
	pmopm8CfgChannel21PwrlowPortn
		Unsigned32,
	pmopm8CfgChannel22PwrlowPortn
		Unsigned32,
	pmopm8CfgChannel23PwrlowPortn
		Unsigned32,
	pmopm8CfgChannel24PwrlowPortn
		Unsigned32,
	pmopm8CfgChannel25PwrlowPortn
		Unsigned32,
	pmopm8CfgChannel26PwrlowPortn
		Unsigned32,
	pmopm8CfgChannel27PwrlowPortn
		Unsigned32,
	pmopm8CfgChannel28PwrlowPortn
		Unsigned32,
	pmopm8CfgChannel29PwrlowPortn
		Unsigned32,
	pmopm8CfgChannel30PwrlowPortn
		Unsigned32,
	pmopm8CfgChannel31PwrlowPortn
		Unsigned32,
	pmopm8CfgChannel32PwrlowPortn
		Unsigned32,
	pmopm8CfgChannel33PwrlowPortn
		Unsigned32,
	pmopm8CfgChannel34PwrlowPortn
		Unsigned32,
	pmopm8CfgChannel35PwrlowPortn
		Unsigned32,
	pmopm8CfgChannel36PwrlowPortn
		Unsigned32,
	pmopm8CfgChannel37PwrlowPortn
		Unsigned32,
	pmopm8CfgChannel38PwrlowPortn
		Unsigned32,
	pmopm8CfgChannel39PwrlowPortn
		Unsigned32,
	pmopm8CfgChannel40PwrlowPortn
		Unsigned32,
	pmopm8CfgChannel41PwrlowPortn
		Unsigned32,
	pmopm8CfgChannel42PwrlowPortn
		Unsigned32,
	pmopm8CfgChannel43PwrlowPortn
		Unsigned32,
	pmopm8CfgChannel44PwrlowPortn
		Unsigned32,
	pmopm8CfgChannel45PwrlowPortn
		Unsigned32,
	pmopm8CfgChannel46PwrlowPortn
		Unsigned32,
	pmopm8CfgChannel47PwrlowPortn
		Unsigned32,
	pmopm8CfgChannel48PwrlowPortn
		Unsigned32,
	pmopm8CfgChannel49PwrlowPortn
		Unsigned32,
	pmopm8CfgChannel50PwrlowPortn
		Unsigned32,
	pmopm8CfgChannel51PwrlowPortn
		Unsigned32,
	pmopm8CfgChannel52PwrlowPortn
		Unsigned32,
	pmopm8CfgChannel53PwrlowPortn
		Unsigned32,
	pmopm8CfgChannel54PwrlowPortn
		Unsigned32,
	pmopm8CfgChannel55PwrlowPortn
		Unsigned32,
	pmopm8CfgChannel56PwrlowPortn
		Unsigned32,
	pmopm8CfgChannel57PwrlowPortn
		Unsigned32,
	pmopm8CfgChannel58PwrlowPortn
		Unsigned32,
	pmopm8CfgChannel59PwrlowPortn
		Unsigned32,
	pmopm8CfgChannel60PwrlowPortn
		Unsigned32,
	pmopm8CfgChannel61PwrlowPortn
		Unsigned32,
	pmopm8CfgChannel62PwrlowPortn
		Unsigned32,
	pmopm8CfgChannel63PwrlowPortn
		Unsigned32,
	pmopm8CfgChannel64PwrlowPortn
		Unsigned32,
	pmopm8CfgChannel65PwrlowPortn
		Unsigned32,
	pmopm8CfgChannel66PwrlowPortn
		Unsigned32,
	pmopm8CfgChannel67PwrlowPortn
		Unsigned32,
	pmopm8CfgChannel68PwrlowPortn
		Unsigned32,
	pmopm8CfgChannel69PwrlowPortn
		Unsigned32,
	pmopm8CfgChannel70PwrlowPortn
		Unsigned32,
	pmopm8CfgChannel71PwrlowPortn
		Unsigned32,
	pmopm8CfgChannel72PwrlowPortn
		Unsigned32,
	pmopm8CfgChannel73PwrlowPortn
		Unsigned32,
	pmopm8CfgChannel74PwrlowPortn
		Unsigned32,
	pmopm8CfgChannel75PwrlowPortn
		Unsigned32,
	pmopm8CfgChannel76PwrlowPortn
		Unsigned32,
	pmopm8CfgChannel77PwrlowPortn
		Unsigned32,
	pmopm8CfgChannel78PwrlowPortn
		Unsigned32,
	pmopm8CfgChannel79PwrlowPortn
		Unsigned32,
	pmopm8CfgChannel80PwrlowPortn
		Unsigned32,
	pmopm8CfgChannel81PwrlowPortn
		Unsigned32,
	pmopm8CfgChannel82PwrlowPortn
		Unsigned32,
	pmopm8CfgChannel83PwrlowPortn
		Unsigned32,
	pmopm8CfgChannel84PwrlowPortn
		Unsigned32,
	pmopm8CfgChannel85PwrlowPortn
		Unsigned32,
	pmopm8CfgChannel86PwrlowPortn
		Unsigned32,
	pmopm8CfgChannel87PwrlowPortn
		Unsigned32,
	pmopm8CfgChannel88PwrlowPortn
		Unsigned32,
	pmopm8CfgChannel89PwrlowPortn
		Unsigned32,
	pmopm8CfgChannel90PwrlowPortn
		Unsigned32,
	pmopm8CfgChannel91PwrlowPortn
		Unsigned32,
	pmopm8CfgChannel92PwrlowPortn
		Unsigned32,
	pmopm8CfgChannel93PwrlowPortn
		Unsigned32,
	pmopm8CfgChannel94PwrlowPortn
		Unsigned32,
	pmopm8CfgChannel95PwrlowPortn
		Unsigned32,
	pmopm8CfgChannel96PwrlowPortn
		Unsigned32
	}


pmopm8CfgClientStartupPwrLowIndex OBJECT-TYPE
	SYNTAX  INTEGER(0..128)
	MAX-ACCESS  read-only
	STATUS current
	DESCRIPTION
        "
        Index definition for the clientStartupPwrLow
        table
        "
	::= { pmopm8CfgClientStartupPwrLowEntry 1 }


pmopm8CfgChannel1PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 3 }


pmopm8CfgChannel2PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 4 }


pmopm8CfgChannel3PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 5 }


pmopm8CfgChannel4PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 6 }


pmopm8CfgChannel5PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 7 }


pmopm8CfgChannel6PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 8 }


pmopm8CfgChannel7PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 9 }


pmopm8CfgChannel8PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 10 }


pmopm8CfgChannel9PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 11 }


pmopm8CfgChannel10PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 12 }


pmopm8CfgChannel11PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 13 }


pmopm8CfgChannel12PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 14 }


pmopm8CfgChannel13PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 15 }


pmopm8CfgChannel14PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 16 }


pmopm8CfgChannel15PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 17 }


pmopm8CfgChannel16PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 18 }


pmopm8CfgChannel17PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 19 }


pmopm8CfgChannel18PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 20 }


pmopm8CfgChannel19PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 21 }


pmopm8CfgChannel20PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 22 }


pmopm8CfgChannel21PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 23 }


pmopm8CfgChannel22PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 24 }


pmopm8CfgChannel23PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 25 }


pmopm8CfgChannel24PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 26 }


pmopm8CfgChannel25PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 27 }


pmopm8CfgChannel26PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 28 }


pmopm8CfgChannel27PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 29 }


pmopm8CfgChannel28PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 30 }


pmopm8CfgChannel29PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 31 }


pmopm8CfgChannel30PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 32 }


pmopm8CfgChannel31PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 33 }


pmopm8CfgChannel32PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 34 }


pmopm8CfgChannel33PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 35 }


pmopm8CfgChannel34PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 36 }


pmopm8CfgChannel35PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 37 }


pmopm8CfgChannel36PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 38 }


pmopm8CfgChannel37PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 39 }


pmopm8CfgChannel38PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 40 }


pmopm8CfgChannel39PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 41 }


pmopm8CfgChannel40PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 42 }


pmopm8CfgChannel41PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 43 }


pmopm8CfgChannel42PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 44 }


pmopm8CfgChannel43PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 45 }


pmopm8CfgChannel44PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 46 }


pmopm8CfgChannel45PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 47 }


pmopm8CfgChannel46PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 48 }


pmopm8CfgChannel47PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 49 }


pmopm8CfgChannel48PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 50 }


pmopm8CfgChannel49PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 51 }


pmopm8CfgChannel50PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 52 }


pmopm8CfgChannel51PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 53 }


pmopm8CfgChannel52PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 54 }


pmopm8CfgChannel53PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 55 }


pmopm8CfgChannel54PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 56 }


pmopm8CfgChannel55PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 57 }


pmopm8CfgChannel56PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 58 }


pmopm8CfgChannel57PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 59 }


pmopm8CfgChannel58PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 60 }


pmopm8CfgChannel59PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 61 }


pmopm8CfgChannel60PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 62 }


pmopm8CfgChannel61PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 63 }


pmopm8CfgChannel62PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 64 }


pmopm8CfgChannel63PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 65 }


pmopm8CfgChannel64PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 66 }


pmopm8CfgChannel65PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 67 }


pmopm8CfgChannel66PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 68 }


pmopm8CfgChannel67PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 69 }


pmopm8CfgChannel68PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 70 }


pmopm8CfgChannel69PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 71 }


pmopm8CfgChannel70PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 72 }


pmopm8CfgChannel71PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 73 }


pmopm8CfgChannel72PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 74 }


pmopm8CfgChannel73PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 75 }


pmopm8CfgChannel74PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 76 }


pmopm8CfgChannel75PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 77 }


pmopm8CfgChannel76PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 78 }


pmopm8CfgChannel77PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 79 }


pmopm8CfgChannel78PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 80 }


pmopm8CfgChannel79PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 81 }


pmopm8CfgChannel80PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 82 }


pmopm8CfgChannel81PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 83 }


pmopm8CfgChannel82PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 84 }


pmopm8CfgChannel83PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 85 }


pmopm8CfgChannel84PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 86 }


pmopm8CfgChannel85PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 87 }


pmopm8CfgChannel86PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 88 }


pmopm8CfgChannel87PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 89 }


pmopm8CfgChannel88PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 90 }


pmopm8CfgChannel89PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 91 }


pmopm8CfgChannel90PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 92 }


pmopm8CfgChannel91PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 93 }


pmopm8CfgChannel92PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 94 }


pmopm8CfgChannel93PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 95 }


pmopm8CfgChannel94PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 96 }


pmopm8CfgChannel95PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 97 }


pmopm8CfgChannel96PwrlowPortn OBJECT-TYPE
	SYNTAX  Unsigned32 (0..65536)
	MAX-ACCESS read-write
	STATUS current
	DESCRIPTION
        "
        Default Settings on Min Power
         :This OID defines the threshold
        to rise a channel power low
        "
	::= { pmopm8CfgClientStartupPwrLowEntry 98 }


--- *****************************************************
---     LEAF for the table NO_VALUE
--- *****************************************************

pmopm8CfgLabelclientTable OBJECT-TYPE
	SYNTAX  SEQUENCE OF Pmopm8CfgLabelclientEntry
	MAX-ACCESS not-accessible
	STATUS current
	DESCRIPTION
        "
        List of  Article
        "
	::= { pmopm8CfgStartup 7 }


pmopm8CfgLabelclientEntry OBJECT-TYPE
	SYNTAX Pmopm8CfgLabelclientEntry
	MAX-ACCESS not-accessible
	STATUS current
	DESCRIPTION
        "
        Row definition for the startup
        table
        "
	INDEX   { pmopm8CfgLabelclientIndex }
	::= { pmopm8CfgLabelclientTable 1 }


Pmopm8CfgLabelclientEntry ::=
	SEQUENCE {
	pmopm8CfgLabelclientIndex
		INTEGER,
	pmopm8CfgLabelclientPortn
		DisplayString
	}


pmopm8CfgLabelclientIndex OBJECT-TYPE
	SYNTAX  INTEGER(0..128)
	MAX-ACCESS  read-only
	STATUS current
	DESCRIPTION
        "
        Index definition for the labelclient
        table
        "
	::= { pmopm8CfgLabelclientEntry 1 }


pmopm8CfgLabelclientPortn OBJECT-TYPE
	SYNTAX  DisplayString( SIZE(1..16))
	MAX-ACCESS read-write
	STATUS current
	DESCRIPTION
        "
        Default settings on the label
         of the Ports :
        "
	::= { pmopm8CfgLabelclientEntry 3 }


--- *****************************************************
---     LEAF for the table NO_VALUE
--- *****************************************************

pmopm8CfgLabellineTable OBJECT-TYPE
	SYNTAX  SEQUENCE OF Pmopm8CfgLabellineEntry
	MAX-ACCESS not-accessible
	STATUS current
	DESCRIPTION
        "
        List of  Article
        "
	::= { pmopm8CfgStartup 8 }


pmopm8CfgLabellineEntry OBJECT-TYPE
	SYNTAX Pmopm8CfgLabellineEntry
	MAX-ACCESS not-accessible
	STATUS current
	DESCRIPTION
        "
        Row definition for the startup
        table
        "
	INDEX   { pmopm8CfgLabellineIndex }
	::= { pmopm8CfgLabellineTable 1 }


Pmopm8CfgLabellineEntry ::=
	SEQUENCE {
	pmopm8CfgLabellineIndex
		INTEGER,
	pmopm8CfgLabellinePortn
		DisplayString
	}


pmopm8CfgLabellineIndex OBJECT-TYPE
	SYNTAX  INTEGER(0..128)
	MAX-ACCESS  read-only
	STATUS current
	DESCRIPTION
        "
        Index definition for the labelline
        table
        "
	::= { pmopm8CfgLabellineEntry 1 }


pmopm8CfgLabellinePortn OBJECT-TYPE
	SYNTAX  DisplayString( SIZE(1..16))
	MAX-ACCESS read-write
	STATUS current
	DESCRIPTION
        "
        Default settings on the label
         of the lines :
        "
	::= { pmopm8CfgLabellineEntry 3 }



pmopm8CfgWriteConfiguration  OBJECT-TYPE
	SYNTAX EkiOnOff
	MAX-ACCESS read-write
	STATUS current
	DESCRIPTION
	"Write configuration to module:This OID
	 writes the complete configuration to the module"
	::= { pmopm8Config 257 }






--- *****************************************************
---     TRAP OBJECTS
--- *****************************************************

pmopm8trapPortNumber OBJECT-TYPE
	SYNTAX INTEGER(1..64)
	MAX-ACCESS read-only
	STATUS current
	DESCRIPTION
	"Last port which generates a trap"
	::= { pmopm8traps 2 }

pmopm8trapLineNumber OBJECT-TYPE
	SYNTAX INTEGER(1..64)
	MAX-ACCESS read-only
	STATUS current
	DESCRIPTION
	"Last Line which generates a trap"
	::= { pmopm8traps 3 }

pmopm8trapBoardNumber OBJECT-TYPE
	SYNTAX INTEGER(1..64)
	MAX-ACCESS read-only
	STATUS current
	DESCRIPTION
	"Last module which generates a trap"
	::= { pmopm8traps 4 }







--- *****************************************************
---     CLIENT TRAPS
--- *****************************************************






--- *****************************************************
---     HW TRAPS
--- *****************************************************

pmopm8PowerTrapUrgentGoesOn NOTIFICATION-TYPE
	OBJECTS {pmopm8AlmDefFuseB, pmopm8AlmDefFuseA , pmopm8trapBoardNumber}
	STATUS current
	--&FILTNAME    "PMOPM Fuse A Fail ON"
	--&ACTIONS     { log, major }
	--&MATCH       { pmopm8AlmDefFuseB "*", pmopm8AlmDefFuseA "on", pmopm8trapBoardNumber "$3"}
	--&MESG        "Power Input A Fail on PMOPM in Slot $3 ($A)"

	--&FILTNAME    "PMOPM Fuse B Fail ON"
	--&ACTIONS     { log, major }
	--&MATCH       { pmopm8AlmDefFuseB "on", pmopm8AlmDefFuseA "*", pmopm8trapBoardNumber "$3"}
	--&MESG        "Power Input B Fail on PMOPM in Slot $3 ($A)"
	DESCRIPTION "Urgent power supply default is activated"
	::= { pmopm8traps 50 }

pmopm8PowerTrapUrgentGoesOff NOTIFICATION-TYPE
	OBJECTS {pmopm8AlmDefFuseB, pmopm8AlmDefFuseA , pmopm8trapBoardNumber}
	STATUS current
	--&FILTNAME    "PMOPM Fuse A&B Fail OFF"
	--&ACTIONS     { log, normal}
	--&CLEARS      { "PMOPM Fuse A Fail ON", "PMOPM Fuse B Fail ON" }
	--&MATCH       { pmopm8AlmDefFuseB "on", pmopm8AlmDefFuseA "on", pmopm8trapBoardNumber "$3"}
	--&MESG        "Power Inputs A and B Present on PMOPM in Slot $3 ($A)"

	DESCRIPTION "Urgent power supply default disappeared"
	::= { pmopm8traps 51 }






END
