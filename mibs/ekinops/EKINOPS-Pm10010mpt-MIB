-- *****************************************************************
-- EKINOPS-Pm10010mpt.TXT:  MIB
--
--MIB Part Number:3MI00031AACB
--MIB Version:03
--
-- Copyright (c) 2016 by Ekinops
-- All rights reserved.
--
-- *****************************************************************

EKINOPS-Pm10010mpt-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

modulePm10010mpt MODULE-IDENTITY
        LAST-UPDATED "201606020000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.fr"
        DESCRIPTION
          "Creation."

	REVISION "201402190000Z"
	DESCRIPTION
	  "Creation for PM 100G MPT"
	REVISION "201404010000Z"
	DESCRIPTION
	  "Probcause,AlarmType - NMS completion"
	REVISION "201404030000Z"
	DESCRIPTION
	  "Over Temp and Power Degrade monitoring"
	REVISION "201410140000Z"
	DESCRIPTION
	  "OSNR help completion"
	REVISION "201501230000Z"
	DESCRIPTION
	  "Labels cosmetic updates"
	REVISION "201507300000Z"
	DESCRIPTION
	  "Add Performance OIDs"
	REVISION "201510120000Z"
	DESCRIPTION
	  "OVL on SNMP-Object name on perf datacom"
	REVISION "201510210000Z"
	DESCRIPTION
	  "Add F0 objet"
	REVISION "201605020000Z"
	DESCRIPTION
	  "Datacom Perf SNMP objects corrections"
	REVISION "201605200000Z"
	DESCRIPTION
	  "New AlarmType – synthesisAlarm (12)"
	REVISION "201606020000Z"
	DESCRIPTION
	  "Capabilities objects of Table 5"
        ::= { ekinops 60 }



--- *****************************************************
---     LEAF LEVEL 2
--- *****************************************************


pm10010mptalarms OBJECT IDENTIFIER ::= { modulePm10010mpt 2 }
pm10010mptAlmOther OBJECT IDENTIFIER ::= { pm10010mptalarms 1 }
pm10010mptAlmOtherNurg OBJECT IDENTIFIER ::= { pm10010mptAlmOther 1 }
pm10010mptAlmOtherUrg OBJECT IDENTIFIER ::= { pm10010mptAlmOther 2 }
pm10010mptAlmOtherCrit OBJECT IDENTIFIER ::= { pm10010mptAlmOther 3 }

pm10010mptAlmClient OBJECT IDENTIFIER ::= { pm10010mptalarms 2 }
pm10010mptAlmClientNurg OBJECT IDENTIFIER ::= { pm10010mptAlmClient 1 }
pm10010mptAlmClientUrg OBJECT IDENTIFIER ::= { pm10010mptAlmClient 2 }
pm10010mptAlmClientCrit OBJECT IDENTIFIER ::= { pm10010mptAlmClient 3 }

pm10010mptAlmLine OBJECT IDENTIFIER ::= { pm10010mptalarms 3 }
pm10010mptAlmLineNurg OBJECT IDENTIFIER ::= { pm10010mptAlmLine 1 }
pm10010mptAlmLineUrg OBJECT IDENTIFIER ::= { pm10010mptAlmLine 2 }
pm10010mptAlmLineCrit OBJECT IDENTIFIER ::= { pm10010mptAlmLine 3 }





pm10010mptmeasures OBJECT IDENTIFIER ::= { modulePm10010mpt 3 }
pm10010mptMesrOther OBJECT IDENTIFIER ::= { pm10010mptmeasures 1 }
pm10010mptMesrClient OBJECT IDENTIFIER ::= { pm10010mptmeasures 2 }
pm10010mptMesrLine OBJECT IDENTIFIER ::= { pm10010mptmeasures 3 }




pm10010mptcounters OBJECT IDENTIFIER ::= { modulePm10010mpt 4 }
pm10010mptCntOther OBJECT IDENTIFIER ::= { pm10010mptcounters 1 }
pm10010mptCntClient OBJECT IDENTIFIER ::= { pm10010mptcounters 2 }
pm10010mptCntLine OBJECT IDENTIFIER ::= { pm10010mptcounters 3 }


pm10010mptcontrolsWrite OBJECT IDENTIFIER ::= { modulePm10010mpt 6 }
pm10010mptCtrlOther OBJECT IDENTIFIER ::= { pm10010mptcontrolsWrite 1 }
pm10010mptCtrlClient OBJECT IDENTIFIER ::= { pm10010mptcontrolsWrite 2 }
pm10010mptCtrlLine OBJECT IDENTIFIER ::= { pm10010mptcontrolsWrite 3 }

pm10010mptri OBJECT IDENTIFIER ::= { modulePm10010mpt 7 }
pm10010mptriTable OBJECT IDENTIFIER ::= { pm10010mptri 1 }

pm10010mptdownload OBJECT IDENTIFIER ::= { modulePm10010mpt 8 }
pm10010mptDwlOther OBJECT IDENTIFIER ::= { pm10010mptdownload 1 }
pm10010mptDwlClient OBJECT IDENTIFIER ::= { pm10010mptdownload 2 }
pm10010mptDwlLine OBJECT IDENTIFIER ::= { pm10010mptdownload 3 }


pm10010mptConfig OBJECT IDENTIFIER ::= { modulePm10010mpt 9 }

pm10010mpttraps OBJECT IDENTIFIER ::= { modulePm10010mpt 10 }



pm10010mptMonitoring OBJECT IDENTIFIER ::= { modulePm10010mpt 11}

pm10010mptMonOther OBJECT IDENTIFIER ::= { pm10010mptMonitoring 1 }
pm10010mptMonRmon OBJECT IDENTIFIER ::= { pm10010mptMonOther 3 }

pm10010mptMonClient OBJECT IDENTIFIER ::= { pm10010mptMonitoring 2 }
pm10010mptMonClientRmonCounter OBJECT IDENTIFIER ::= { pm10010mptMonClient 4 }


pm10010mptMonPerfOther OBJECT IDENTIFIER ::= { pm10010mptMonitoring 5 }
pm10010mptMonPerfSync OBJECT IDENTIFIER ::= { pm10010mptMonPerfOther 1 }
pm10010mptMonPerfTimeStamp OBJECT IDENTIFIER ::= { pm10010mptMonPerfOther 2 }


pm10010mptMonPerfClient OBJECT IDENTIFIER ::= { pm10010mptMonitoring 6 }

pm10010mptMonPerfLine OBJECT IDENTIFIER ::= { pm10010mptMonitoring 7 }



--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Pm10010mptMultiRate ::= TEXTUAL-CONVENTION
    STATUS      current
    DESCRIPTION "different rate for a client port"
    SYNTAX INTEGER {
		rate100Mhz(0),
		rate250Mhz(1),
		rate500Mhz(2),
		rate1Ghz(3)
           }

Pm10010mptOtxMode ::= TEXTUAL-CONVENTION
    STATUS      current
    DESCRIPTION "Different modes on OTX-TLH on client and line ports"
    SYNTAX INTEGER {
		otx80mode(1),
		otx60mode(2),
		otxadjustmode(4)
           }

Pm10010mptOtxGrid ::= TEXTUAL-CONVENTION
    STATUS      current
    DESCRIPTION "Different grids on OTX-TLH on client and line ports"
    SYNTAX INTEGER {
		otxgrid200(200),
		otxgrid100(100),
		otxgrid50(50)
           }

Pm10010mptAdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pm10010mptClientProtocol ::= TEXTUAL-CONVENTION
    STATUS      current
    DESCRIPTION "Different values on the protocol on the client ports"
    SYNTAX INTEGER {
		protocolclientvalue0(0),
		protocolclientvalue1(1),
		protocolclientvalue2(2),
		protocolclientvalue3(3),
		protocolclientvalue4(4),
		protocolclientvalue5(5),
		protocolclientvalue6(6),
		protocolclientvalue7(7),
		protocolclientvalue8(8)
           }

Pm10010mptProtocolMode ::= TEXTUAL-CONVENTION
    STATUS      current
    DESCRIPTION "Different values on the protocol mode"
    SYNTAX INTEGER {
		protocolmodevalue0(0),
		protocolmodevalue1(1),
		protocolmodevalue2(2),
		protocolmodevalue3(3)
           }

Pm10010mptOtxChannel ::= TEXTUAL-CONVENTION
    STATUS      current
    DESCRIPTION "Channel selection on transceiver Tx line ports"
    SYNTAX INTEGER

Pm10010mptOrxChannel ::= TEXTUAL-CONVENTION
    STATUS      current
    DESCRIPTION "Channel selection on transceiver Rx line ports"
    SYNTAX INTEGER

Rm10010ClientIgnoreTimer ::= TEXTUAL-CONVENTION
    STATUS      current
    DESCRIPTION "Different values on the ignore timer on the client ports"
    SYNTAX INTEGER {
		ignoretimerclientvalue0(0),
		ignoretimerclientvalue1(1),
		ignoretimerclientvalue2(2),
		ignoretimerclientvalue3(3),
		ignoretimerclientvalue4(4),
		ignoretimerclientvalue5(5),
		ignoretimerclientvalue6(6),
		ignoretimerclientvalue7(7),
		ignoretimerclientvalue8(8),
		ignoretimerclientvalue9(9),
		ignoretimerclientvalue10(10)
           }

--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm10010mptRinvReloadInventory OBJECT-TYPE
  SYNTAX EkiOnOff
  MAX-ACCESS read-write
  STATUS current
  DESCRIPTION
        "Reload the inventory: This OID triggers an
         inventory reload."
  ::= { pm10010mptri 2 }

pm10010mptRinvHwPlatform OBJECT-TYPE
  SYNTAX DisplayString
  MAX-ACCESS read-only
  STATUS current
  DESCRIPTION
        "HW platform description: This OID contains the
         description of the Hardware platform."
  ::= { pm10010mptri 3 }

pm10010mptRinvModulePlatform OBJECT-TYPE
  SYNTAX DisplayString
  MAX-ACCESS read-only
  STATUS current
  DESCRIPTION
        "Module platform description: This OID contains the
         description of the Module."
  ::= { pm10010mptri 4 }

pm10010mptRinvSwPlatform OBJECT-TYPE
  SYNTAX DisplayString
  MAX-ACCESS read-only
  STATUS current
  DESCRIPTION
        "SW platform description: This OID contains the
         description of the Software platform."
  ::= { pm10010mptri 5 }

pm10010mptRinvGwPlatform OBJECT-TYPE
  SYNTAX DisplayString
  MAX-ACCESS read-only
  STATUS current
  DESCRIPTION
        "GW platform desciption: This OID contains the
         description of the Gateware platform."
  ::= { pm10010mptri 6 }


pm10010mptRinvSfpTable OBJECT-TYPE
      SYNTAX  SEQUENCE OF Pm10010mptRinvSfpEntry
      MAX-ACCESS  not-accessible
      STATUS  current
      DESCRIPTION
              "List of the SFPs on the selected module"
      ::= { pm10010mptriTable 1 }

pm10010mptRinvSfpEntry OBJECT-TYPE
        SYNTAX  Pm10010mptRinvSfpEntry
        MAX-ACCESS  not-accessible
        STATUS  current
        DESCRIPTION
              "Row definition for the SFP table"
        INDEX   { pm10010mptRinvSfpIndex }
        ::= { pm10010mptRinvSfpTable 1 }



Pm10010mptRinvSfpEntry::=
        SEQUENCE {
          pm10010mptRinvSfpIndex
              Integer32,
          pm10010mptRinvsfp
              DisplayString
        }


    pm10010mptRinvSfpIndex OBJECT-TYPE
        SYNTAX  Integer32(1..16)
        MAX-ACCESS  read-only
        STATUS  current
        DESCRIPTION
              "Index for SFP table"
        ::= { pm10010mptRinvSfpEntry 1 }


    pm10010mptRinvsfp OBJECT-TYPE
        SYNTAX  DisplayString
        MAX-ACCESS  read-only
        STATUS  current
        DESCRIPTION
              "Inventory for the SFP: This OID contains the inventory for the SFP"
        ::= { pm10010mptRinvSfpEntry 2 }




pm10010mptRinvLineTable OBJECT-TYPE
      SYNTAX  SEQUENCE OF Pm10010mptRinvLineEntry
      MAX-ACCESS  not-accessible
      STATUS  current
      DESCRIPTION
              "List of the XFPs on the selected module"
      ::= { pm10010mptriTable 2 }

pm10010mptRinvLineEntry OBJECT-TYPE
        SYNTAX  Pm10010mptRinvLineEntry
        MAX-ACCESS  not-accessible
        STATUS  current
        DESCRIPTION
              "Row definition for the XFP table"
        INDEX   { pm10010mptRinvLineIndex }
        ::= { pm10010mptRinvLineTable 1 }



Pm10010mptRinvLineEntry::=
        SEQUENCE {
          pm10010mptRinvLineIndex
              Integer32,
          pm10010mptRinvxfpLine
              DisplayString
        }


    pm10010mptRinvLineIndex OBJECT-TYPE
        SYNTAX  Integer32(1..16)
        MAX-ACCESS  read-only
        STATUS  current
        DESCRIPTION
              "Index for XFP table"
        ::= { pm10010mptRinvLineEntry 1 }


    pm10010mptRinvxfpLine OBJECT-TYPE
        SYNTAX  DisplayString
        MAX-ACCESS  read-only
        STATUS  current
        DESCRIPTION
              "Inventory for the XFP: This OID contains the inventory for the XFP"
        ::= { pm10010mptRinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm10010mptAlmsynthAlm0 OBJECT IDENTIFIER ::= { pm10010mptAlmOtherCrit 0 }




pm10010mptAlmDefFuseB OBJECT-TYPE
	  SYNTAX EkiOnOff
	  MAX-ACCESS read-only
	  STATUS current
	  DESCRIPTION
        "
        Fuse B Fail :This OID indicates
        that the fuse of the power input
        B is in fail condition <Help> Status
        of the Fuse B <Condtype> DEF_FUSE_B
        <Probcause> powerProblem (36) <Alarmtype>
        equipmentAlarm (5) <Polarity> (2)
        "
	  ::= { pm10010mptAlmsynthAlm0 16 }



pm10010mptAlmDefFuseA OBJECT-TYPE
	  SYNTAX EkiOnOff
	  MAX-ACCESS read-only
	  STATUS current
	  DESCRIPTION
        "
        Fuse A Fail :This OID indicates
        that the fuse of the power input
        A is in fail condition <Help> Status
        of the Fuse A <Condtype> DEF_FUSE_A
        <Probcause> powerProblem (36) <Alarmtype>
        equipmentAlarm (5) <Polarity> (2)
        "
	  ::= { pm10010mptAlmsynthAlm0 15 }



pm10010mptAlmModGlobFail OBJECT-TYPE
	  SYNTAX EkiOnOff
	  MAX-ACCESS read-only
	  STATUS current
	  DESCRIPTION
        "
        Module Failure :This OID is set
        on detection of a failure originating
        from the RM <Help> This alarm is
        set on detection of a failure originating
        from the equipment <Condtype> MOD_GLOB_FAIL
        <Probcause> other (1) <Alarmtype>
        synthesisAlarm (12)  <Polarity>
        (2)
        "
	  ::= { pm10010mptAlmsynthAlm0 9 }



pm10010mptAlmFailFan OBJECT-TYPE
	  SYNTAX EkiOnOff
	  MAX-ACCESS read-only
	  STATUS current
	  DESCRIPTION
        "
        Fan Fail :This OID is at 1 when
        any fail occurs on the fan tray
        <Help> This alarm indicates that
        the Fan tray module is in a failure
        condition <Condtype> FAIL_FAN <Probcause>
        equipmentMalfunction (16) <Alarmtype>
        equipmentAlarm (5) <Polarity> (2)
        "
	  ::= { pm10010mptAlmsynthAlm0 2 }



--- *****************************************************
---     LEAF for the synthAlm2 article
--- *****************************************************
pm10010mptAlmsynthAlm2 OBJECT IDENTIFIER ::= { pm10010mptAlmOtherNurg 2 }




pm10010mptAlmMaintenanceOn OBJECT-TYPE
	  SYNTAX EkiOnOff
	  MAX-ACCESS read-only
	  STATUS current
	  DESCRIPTION
        "
        Maintenance Mode :This OID indicates
        that the RM is in maintenance mode.
        <Help> This alarm indicates that
        the maintenance mode is enabled
        on the PM <Condtype> MAINTENANCE_ON
        <Probcause> informationalStatus(1000)
        <Alarmtype> other (1) <Polarity>
        (2)
        "
	  ::= { pm10010mptAlmsynthAlm2 5 }



pm10010mptAlmCorrelatOff OBJECT-TYPE
	  SYNTAX EkiOnOff
	  MAX-ACCESS read-only
	  STATUS current
	  DESCRIPTION
        "
        Not Used :This OID, when set,
         indicates that alarm correlation
        is not being performed. <Condtype>
        CORRELAT_OFF <Probcause> informationalStatus(1000)
        <Alarmtype> other (1) <Polarity>
        (2)
        "
	  ::= { pm10010mptAlmsynthAlm2 4 }



pm10010mptAlmConfTableLoad OBJECT-TYPE
	  SYNTAX EkiOnOff
	  MAX-ACCESS read-only
	  STATUS current
	  DESCRIPTION
        "
        PM Configuration Load :This OID
         is at 1 during the loading of
         configuration tables in the modules
        RAM. <Condtype> CONF_TABLE_LOAD
        <Probcause> informationalStatus(1000)
        <Alarmtype> other (1) <Polarity>
        (2)
        "
	  ::= { pm10010mptAlmsynthAlm2 3 }



pm10010mptAlmInvUpload OBJECT-TYPE
	  SYNTAX EkiOnOff
	  MAX-ACCESS read-only
	  STATUS current
	  DESCRIPTION
        "
        Inventory Upload :This OID is
         at 1 during the uploading of PM
        inventory information. <Condtype>
        INV_UPLOAD <Probcause> informationalStatus(1000)
        <Alarmtype> other (1) <Polarity>
        (2)
        "
	  ::= { pm10010mptAlmsynthAlm2 2 }



pm10010mptAlmConfTableSave OBJECT-TYPE
	  SYNTAX EkiOnOff
	  MAX-ACCESS read-only
	  STATUS current
	  DESCRIPTION
        "
        PM Configuration Save :This OID
        is at 1 during the saving of a
         new configuration table in the
        module Flash memory. <Condtype>
        CONF_TABLE_SAVE <Probcause> informationalStatus(1000)
        <Alarmtype> other (1) <Polarity>
        (2)
        "
	  ::= { pm10010mptAlmsynthAlm2 1 }



--- *********************************************************
---     TABLE for the pm10010mptAlmsynthAlmPort articles
--- *********************************************************

pm10010mptAlmsynthAlmPortTable OBJECT-TYPE
	SYNTAX  SEQUENCE OF Pm10010mptAlmsynthAlmPortEntry
	MAX-ACCESS not-accessible
	STATUS current
	DESCRIPTION
        "
        List of pm10010mptAlmsynthAlmPort
        Article
        "
	::= { pm10010mptAlmClientCrit 8 }


pm10010mptAlmsynthAlmPortEntry OBJECT-TYPE
	SYNTAX Pm10010mptAlmsynthAlmPortEntry
	MAX-ACCESS not-accessible
	STATUS current
	DESCRIPTION
        "
        Row definition for the pm10010mptAlmsynthAlmPort
        table
        "
	INDEX   { pm10010mptAlmsynthAlmPortIndex }
	::= { pm10010mptAlmsynthAlmPortTable 1 }


Pm10010mptAlmsynthAlmPortEntry ::=
	SEQUENCE {
	pm10010mptAlmsynthAlmPortIndex
		INTEGER,
	pm10010mptAlmUpCsfPortn
		EkiOnOff,
	pm10010mptAlmFailAccPortn
		EkiOnOff,
	pm10010mptAlmIdleInsertedPortn
		EkiOnOff,
	pm10010mptAlmSfpDdmAlmPortn
		EkiOnOff,
	pm10010mptAlmSfpDdmWarningPortn
		EkiOnOff,
	pm10010mptAlmDwCaisPortn
		EkiOnOff,
	pm10010mptAlmClientRemoteOosPortn
		EkiOnOff,
	pm10010mptAlmClientLocalOosPortn
		EkiOnOff,
	pm10010mptAlmDwLsdPortn
		EkiOnOff,
	pm10010mptAlmHwFailAccPortn
		EkiOnOff,
	pm10010mptAlmDdmAbsentPortn
		EkiOnOff,
	pm10010mptAlmSfpAbsentPortn
		EkiOnOff
	}


pm10010mptAlmsynthAlmPortIndex OBJECT-TYPE
	SYNTAX  INTEGER(0..128)
	MAX-ACCESS  read-only
	STATUS current
	DESCRIPTION
        "
        Index definition for the pm10010mptAlmsynthAlmPort
        table
        "
	::= { pm10010mptAlmsynthAlmPortEntry 1 }


pm10010mptAlmUpCsfPortn OBJECT-TYPE
	SYNTAX  EkiOnOff
	MAX-ACCESS read-only
	STATUS current
	DESCRIPTION
        "
        Client Signal Fail Inserted :This
        OID indicates a CSF has been inserted
        in the upstream client port. <Help>
        This status indicates if a Client
        Signal Fail is currently inserted
        on the line signal for this client
        port <Condtype> UP_CSF_1 <Probcause>
        informationalStatus(1000) <Alarmtype>
        other (1) <Polarity> (2)
        "
	::= { pm10010mptAlmsynthAlmPortEntry 17 }


pm10010mptAlmFailAccPortn OBJECT-TYPE
	SYNTAX  EkiOnOff
	MAX-ACCESS read-only
	STATUS current
	DESCRIPTION
        "
        Client Access Fail :This OID indicates
        a failure on the Client port <Help>
        This alarm indicates a failure
         on the Client port <Condtype>
         FAIL_ACC_1 <Probcause> equipmentMalfunction
        (16) <Alarmtype> synthesisAlarm
        (12)  <Polarity> (2)
        "
	::= { pm10010mptAlmsynthAlmPortEntry 13 }


pm10010mptAlmIdleInsertedPortn OBJECT-TYPE
	SYNTAX  EkiOnOff
	MAX-ACCESS read-only
	STATUS current
	DESCRIPTION
        "
        Idle Inserted :This OID indicates
        the client output stream is replaced
        by IDLE<Help> This alarm indicates
        the client output stream is replaced
        by IDLE <Condtype> IDLE_INSERTED
        <Probcause> informationalStatus(1000)
        <Alarmtype> other (1) <Polarity>
        (2)
        "
	::= { pm10010mptAlmsynthAlmPortEntry 12 }


pm10010mptAlmSfpDdmAlmPortn OBJECT-TYPE
	SYNTAX  EkiOnOff
	MAX-ACCESS read-only
	STATUS current
	DESCRIPTION
        "
        Alarm On Client Trscv DDM :This
        OID indicates an alarm is being
        received from the Client Transceiver
        DDM <Help> This alarm indicates
        if a DDM Alarm has been detected
        on the client transceiver <Condtype>
        SFP_DDM_ALM_1 <Probcause> inputOutputDeviceError
        (24) <Alarmtype> synthesisAlarm
        (12)  <Polarity> (2)
        "
	::= { pm10010mptAlmsynthAlmPortEntry 11 }


pm10010mptAlmSfpDdmWarningPortn OBJECT-TYPE
	SYNTAX  EkiOnOff
	MAX-ACCESS read-only
	STATUS current
	DESCRIPTION
        "
        Warning On Client Trscv DDM :This
        OID indicates a warning is being
        received from the Client Transceiver
        DDM <Help> This alarm indicates
        if a DDM Warning has been detected
        on the client transceiver <Condtype>
        SFP_DDM_WARNING_1 <Probcause> inputOutputDeviceError
        (24) <Alarmtype> synthesisAlarm
        (12)  <Polarity> (2)
        "
	::= { pm10010mptAlmsynthAlmPortEntry 10 }


pm10010mptAlmDwCaisPortn OBJECT-TYPE
	SYNTAX  EkiOnOff
	MAX-ACCESS read-only
	STATUS current
	DESCRIPTION
        "
        Client AIS Inserted :This OID
         indicates a CAIS has been inserted
        on the output client port. <Help>
        This status indicates if a Client
        Alarm Indication Signal is currently
        inserted on the client interface
        <Condtype> DW_CAIS_1 <Probcause>
        informationalStatus(1000) <Alarmtype>
        other (1) <Polarity> (2)
        "
	::= { pm10010mptAlmsynthAlmPortEntry 9 }


pm10010mptAlmClientRemoteOosPortn OBJECT-TYPE
	SYNTAX  EkiOnOff
	MAX-ACCESS read-only
	STATUS current
	DESCRIPTION
        "
        Remote Client Port In Service
         :This OID indicates that the remote
        Client port is In Service (1) or
        Out of Service (2) <Help> This
         status indicates if the remote
        client port is in service <Condtype>
        CLIENT_REMOTE_OOS <Probcause> informationalStatus(1000)
        <Alarmtype> other (1) <Polarity>
        (2)
        "
	::= { pm10010mptAlmsynthAlmPortEntry 8 }


pm10010mptAlmClientLocalOosPortn OBJECT-TYPE
	SYNTAX  EkiOnOff
	MAX-ACCESS read-only
	STATUS current
	DESCRIPTION
        "
        Local Client Port In Service :This
        OID indicates that the local Client
        port is In Service (1) or Out of
        Service (2) <Help> This status
         indicates if the local client
         port is in service <Condtype>
         CLIENT_LOCAL_OOS <Probcause> informationalStatus(1000)
        <Alarmtype> other (1) <Polarity>
        (2)
        "
	::= { pm10010mptAlmsynthAlmPortEntry 7 }


pm10010mptAlmDwLsdPortn OBJECT-TYPE
	SYNTAX  EkiOnOff
	MAX-ACCESS read-only
	STATUS current
	DESCRIPTION
        "
        Client Trscv Laser Shutdown :This
        OID indicates the Client transceiver
        laser is shutdown <Help> This status
        indicates if the client transceiver
        laser is shutdown <Condtype> DW_LSD_1
        <Probcause> other (1) <Alarmtype>
        equipmentAlarm (5) <Polarity> (2)
        "
	::= { pm10010mptAlmsynthAlmPortEntry 6 }


pm10010mptAlmHwFailAccPortn OBJECT-TYPE
	SYNTAX  EkiOnOff
	MAX-ACCESS read-only
	STATUS current
	DESCRIPTION
        "
        Client HW Fail :This OID indicates
        a failure on client port, most
         probably caused by a HW issue.
        <Help> This alarm indicates a failure
        on client port, most probably caused
        by a HW issue. <Condtype> HW_FAIL_ACC_1
        <Probcause> equipmentMalfunction
        (16) <Alarmtype> synthesisAlarm
        (12)  <Polarity> (2)
        "
	::= { pm10010mptAlmsynthAlmPortEntry 5 }


pm10010mptAlmDdmAbsentPortn OBJECT-TYPE
	SYNTAX  EkiOnOff
	MAX-ACCESS read-only
	STATUS current
	DESCRIPTION
        "
        DDM Supported On Client Trscv
         :This OID indicates that the Client
        transceiver supports the Digital
        Diagnostic Monitoring function
         <Help> This status indicates if
        the client transceiver includes
        the DDM feature <Condtype> DDM_ABSENT_1
        <Probcause> informationalStatus(1000)
        <Alarmtype> other (1) <Polarity>
        (2)
        "
	::= { pm10010mptAlmsynthAlmPortEntry 3 }


pm10010mptAlmSfpAbsentPortn OBJECT-TYPE
	SYNTAX  EkiOnOff
	MAX-ACCESS read-only
	STATUS current
	DESCRIPTION
        "
        Client Optical Module Absent :This
        OID indicates that the Transceiver
        is not present in the client port.
        <Help> This alarm indicates if
         the client transceiver is not
         plugged <Condtype> SFP_ABSENT_1
        <Probcause> inputOutputDeviceError
        (24) <Alarmtype> equipmentAlarm
        (5) <Polarity> (2) <Event> ObjectCDINV
        "
	::= { pm10010mptAlmsynthAlmPortEntry 2 }


--- *********************************************************
---     TABLE for the pm10010mptAlmsynthAlmLine articles
--- *********************************************************

pm10010mptAlmsynthAlmLineTable OBJECT-TYPE
	SYNTAX  SEQUENCE OF Pm10010mptAlmsynthAlmLineEntry
	MAX-ACCESS not-accessible
	STATUS current
	DESCRIPTION
        "
        List of pm10010mptAlmsynthAlmLine
        Article
        "
	::= { pm10010mptAlmLineCrit 24 }


pm10010mptAlmsynthAlmLineEntry OBJECT-TYPE
	SYNTAX Pm10010mptAlmsynthAlmLineEntry
	MAX-ACCESS not-accessible
	STATUS current
	DESCRIPTION
        "
        Row definition for the pm10010mptAlmsynthAlmLine
        table
        "
	INDEX   { pm10010mptAlmsynthAlmLineIndex }
	::= { pm10010mptAlmsynthAlmLineTable 1 }


Pm10010mptAlmsynthAlmLineEntry ::=
	SEQUENCE {
	pm10010mptAlmsynthAlmLineIndex
		INTEGER,
	pm10010mptAlmLineActivePortn
		EkiOnOff,
	pm10010mptAlmLineFailPortn
		EkiOnOff,
	pm10010mptAlmLineDdmAlmPortn
		EkiOnOff,
	pm10010mptAlmLineDdmWarningPortn
		EkiOnOff,
	pm10010mptAlmUpRdiInsPortn
		EkiOnOff,
	pm10010mptAlmLineLocalOosPortn
		EkiOnOff,
	pm10010mptAlmXfpTxOffPortn
		EkiOnOff,
	pm10010mptAlmLineHwFailPortn
		EkiOnOff,
	pm10010mptAlmXfpInitNotComplPortn
		EkiOnOff,
	pm10010mptAlmXfpAbsentPortn
		EkiOnOff
	}


pm10010mptAlmsynthAlmLineIndex OBJECT-TYPE
	SYNTAX  INTEGER(0..128)
	MAX-ACCESS  read-only
	STATUS current
	DESCRIPTION
        "
        Index definition for the pm10010mptAlmsynthAlmLine
        table
        "
	::= { pm10010mptAlmsynthAlmLineEntry 1 }


pm10010mptAlmLineActivePortn OBJECT-TYPE
	SYNTAX  EkiOnOff
	MAX-ACCESS read-only
	STATUS current
	DESCRIPTION
        "
        Line Active :This OID indicates
        whether the line is active or standby.
        <Help> This status indicates whether
        the line is active or standby.
         <Condtype> LINE_ACTIVE <Probcause>
        informationalStatus(1000) <Alarmtype>
        other (1) <Polarity> (2)
        "
	::= { pm10010mptAlmsynthAlmLineEntry 17 }


pm10010mptAlmLineFailPortn OBJECT-TYPE
	SYNTAX  EkiOnOff
	MAX-ACCESS read-only
	STATUS current
	DESCRIPTION
        "
        Line Port Failure :This OID indicates
        a failure on the line port <Help>
        This alarm indicates a failure
         on the line port <Condtype> LINE_FAIL
        <Probcause> equipmentMalfunction
        (16) <Alarmtype> synthesisAlarm
        (12)  <Polarity> (2)
        "
	::= { pm10010mptAlmsynthAlmLineEntry 13 }


pm10010mptAlmLineDdmAlmPortn OBJECT-TYPE
	SYNTAX  EkiOnOff
	MAX-ACCESS read-only
	STATUS current
	DESCRIPTION
        "
        Alarm On Line Optical Module DDM
        :This OID indicates an alarm is
        present coming out of Line transceiver
        DDM <Help> This alarm indicates
        if a DDM Alarm has been detected
        on the line transceiver <Condtype>
        LINE_DDM_ALM <Probcause> inputOutputDeviceError
        (24) <Alarmtype> synthesisAlarm
        (12)  <Polarity> (2)
        "
	::= { pm10010mptAlmsynthAlmLineEntry 11 }


pm10010mptAlmLineDdmWarningPortn OBJECT-TYPE
	SYNTAX  EkiOnOff
	MAX-ACCESS read-only
	STATUS current
	DESCRIPTION
        "
        Warning On Line Optical Module
        DDM :This OID indicates a warning
        is present coming out of Line transceiver
        DDM <Help> This alarm indicates
        if a DDM Warning has been detected
        on the line transceiver <Condtype>
        LINE_DDM_WARNING <Probcause> inputOutputDeviceError
        (24) <Alarmtype> synthesisAlarm
        (12)  <Polarity> (2)
        "
	::= { pm10010mptAlmsynthAlmLineEntry 10 }


pm10010mptAlmUpRdiInsPortn OBJECT-TYPE
	SYNTAX  EkiOnOff
	MAX-ACCESS read-only
	STATUS current
	DESCRIPTION
        "
        MS-RDI/L-RDI Inserted On Line
         :This OID indicates an upstream
        MS-RDI/L-RDI has been inserted
         in the outgoing 10 Gb/s SDH/SONET
        signal. <Help> This status indicates
        if a MS-RDI/L-RDI is currently
         inserted on the line interface.
        <Condtype> UP_RDI_INS <Probcause>
        informationalStatus(1000) <Alarmtype>
        other (1) <Polarity> (2)
        "
	::= { pm10010mptAlmsynthAlmLineEntry 9 }


pm10010mptAlmLineLocalOosPortn OBJECT-TYPE
	SYNTAX  EkiOnOff
	MAX-ACCESS read-only
	STATUS current
	DESCRIPTION
        "
        Line Port In Service :This OID
        indicates that the Line port is
        In Service (1) of Out or Service
        (2) <Help> This status indicates
        if the line port is in service
         <Condtype> LINE_LOCAL_OOS <Probcause>
        informationalStatus(1000) <Alarmtype>
        other (1) <Polarity> (2)
        "
	::= { pm10010mptAlmsynthAlmLineEntry 7 }


pm10010mptAlmXfpTxOffPortn OBJECT-TYPE
	SYNTAX  EkiOnOff
	MAX-ACCESS read-only
	STATUS current
	DESCRIPTION
        "
        Line Trscv Laser Shutdown :This
        OID indicates the Line transceiver
        laser is shutdown <Help> This status
        indicates if the Line transceiver
        laser is shutdown <Condtype> XFP_TX_OFF
        <Probcause> other (1) <Alarmtype>
        equipmentAlarm (5) <Polarity> (2)
        "
	::= { pm10010mptAlmsynthAlmLineEntry 6 }


pm10010mptAlmLineHwFailPortn OBJECT-TYPE
	SYNTAX  EkiOnOff
	MAX-ACCESS read-only
	STATUS current
	DESCRIPTION
        "
        Line Port HW Failure :This OID
        indicates a failure on line port,
        most probably caused by a HW issue
        <Help> This alarm indicates a failure
        on line port, most probably caused
        by a HW issue <Condtype> LINE_HW_FAIL
        <Probcause> equipmentMalfunction
        (16) <Alarmtype> synthesisAlarm
        (12)  <Polarity> (2)
        "
	::= { pm10010mptAlmsynthAlmLineEntry 5 }


pm10010mptAlmXfpInitNotComplPortn OBJECT-TYPE
	SYNTAX  EkiOnOff
	MAX-ACCESS read-only
	STATUS current
	DESCRIPTION
        "
        Line Optical Module Ready :This
        OID indicates that the optical
         interface is not operational.
         <Help> This status indicates if
        the line transceiver has been correctly
        initialized <Condtype> XFP_INIT_NOT_COMPL
        <Probcause> equipmentMalfunction
        (16) <Alarmtype> equipmentAlarm
        (5) <Polarity> (2)
        "
	::= { pm10010mptAlmsynthAlmLineEntry 3 }


pm10010mptAlmXfpAbsentPortn OBJECT-TYPE
	SYNTAX  EkiOnOff
	MAX-ACCESS read-only
	STATUS current
	DESCRIPTION
        "
        Line Optical Module Absent :This
        OID indicates that the line optical
        interface is not present. <Help>
        This alarm indicates if the line
        transceiver is not plugged <Condtype>
        XFP_ABSENT <Probcause> inputOutputDeviceError
        (24) <Alarmtype> equipmentAlarm
        (5) <Polarity> (2)
        "
	::= { pm10010mptAlmsynthAlmLineEntry 2 }


--- *****************************************************
---     LEAF for the clientModuleState article
--- *****************************************************
pm10010mptAlmclientModuleState OBJECT IDENTIFIER ::= { pm10010mptAlmOtherCrit 40 }




pm10010mptAlmCfpHighPowerDown OBJECT-TYPE
	  SYNTAX EkiOnOff
	  MAX-ACCESS read-only
	  STATUS current
	  DESCRIPTION
        "
        Client Trscv High Power Down :This
        OID indicates the Client Trscv
         is entering Low Power state <Help>
        Status indicating the Client Trscv
        is entering Low Power state <Condtype>
        CFP_HIGH_POWER_DOWN <Probcause>
        informationalStatus(1000) <Alarmtype>
        other (1) <Polarity> (2)
        "
	  ::= { pm10010mptAlmclientModuleState 9 }



pm10010mptAlmCfpTxTurnOff OBJECT-TYPE
	  SYNTAX EkiOnOff
	  MAX-ACCESS read-only
	  STATUS current
	  DESCRIPTION
        "
        Client Trscv Laser Turn Off :This
        OID indicates the Client Trscv
         is turning off its laser <Help>
        Status indicating the Client Trscv
        is turning off its laser <Condtype>
        CFP_TX_TURN_OFF <Probcause> informationalStatus(1000)
        <Alarmtype> other (1) <Polarity>
        (2)
        "
	  ::= { pm10010mptAlmclientModuleState 8 }



pm10010mptAlmCfpFault OBJECT-TYPE
	  SYNTAX EkiOnOff
	  MAX-ACCESS read-only
	  STATUS current
	  DESCRIPTION
        "
        Client Trscv Fault :This OID indicates
        the Client Trscv is in Fault state
        <Help> Status indicating the Client
        Trscv is in Fault state <Condtype>
        CFP_FAULT <Probcause> informationalStatus(1000)
        <Alarmtype> other (1) <Polarity>
        (2)
        "
	  ::= { pm10010mptAlmclientModuleState 7 }



pm10010mptAlmCfpReady OBJECT-TYPE
	  SYNTAX EkiOnOff
	  MAX-ACCESS read-only
	  STATUS current
	  DESCRIPTION
        "
        Client Trscv Ready :This OID indicates
        the Client Trscv is ready to operate
        <Help> Status indicating the Client
        Trscv is ready to operate <Condtype>
        CFP_READY <Probcause> informationalStatus(1000)
        <Alarmtype> other (1) <Polarity>
        (2)
        "
	  ::= { pm10010mptAlmclientModuleState 6 }



pm10010mptAlmCfpTxTurnOn OBJECT-TYPE
	  SYNTAX EkiOnOff
	  MAX-ACCESS read-only
	  STATUS current
	  DESCRIPTION
        "
        Client Trscv Laser Turn On :This
        OID indicates the Client Trscv
         is turning on its laser <Help>
        Status indicating the Client Trscv
        is turning on its laser <Condtype>
        CFP_TX_TURN_ON <Probcause> informationalStatus(1000)
        <Alarmtype> other (1) <Polarity>
        (2)
        "
	  ::= { pm10010mptAlmclientModuleState 5 }



pm10010mptAlmCfpTxOff OBJECT-TYPE
	  SYNTAX EkiOnOff
	  MAX-ACCESS read-only
	  STATUS current
	  DESCRIPTION
        "
        Client Trscv Laser Shutdown :This
        OID indicates the Client Trscv
         Laser is OFF <Help> Status indicating
        the Client Trscv Laser is OFF <Condtype>
        CFP_TX_OFF <Probcause> informationalStatus(1000)
        <Alarmtype> other (1) <Polarity>
        (2)
        "
	  ::= { pm10010mptAlmclientModuleState 4 }



pm10010mptAlmCfpHighPowerUp OBJECT-TYPE
	  SYNTAX EkiOnOff
	  MAX-ACCESS read-only
	  STATUS current
	  DESCRIPTION
        "
        Client Trscv High Power Up :This
        OID indicates the Client Trscv
         is leaving Low Power state <Help>
        Status indicating the Client Trscv
        is leaving Low Power state <Condtype>
        CFP_HIGH_POWER_UP <Probcause> informationalStatus(1000)
        <Alarmtype> other (1) <Polarity>
        (2)
        "
	  ::= { pm10010mptAlmclientModuleState 3 }



pm10010mptAlmCfpLowPower OBJECT-TYPE
	  SYNTAX EkiOnOff
	  MAX-ACCESS read-only
	  STATUS current
	  DESCRIPTION
        "
        Client Trscv Low Power :This OID
        indicates the Client Trscv is in
        low power state <Help> Status indicating
        the Client Trscv is in low power
        state <Condtype> CFP_LOW_POWER
         <Probcause> informationalStatus(1000)
        <Alarmtype> other (1) <Polarity>
        (2)
        "
	  ::= { pm10010mptAlmclientModuleState 2 }



pm10010mptAlmCfpInitialize OBJECT-TYPE
	  SYNTAX EkiOnOff
	  MAX-ACCESS read-only
	  STATUS current
	  DESCRIPTION
        "
        Client Trscv Initialize :This
         OID indicates the Client Trscv
        initialization is in progress <Help>
        Status indicating the Client Trscv
        initialization is in progress <Condtype>
        CFP_INITIALIZE <Probcause> informationalStatus(1000)
        <Alarmtype> other (1) <Polarity>
        (2)
        "
	  ::= { pm10010mptAlmclientModuleState 1 }



--- *****************************************************
---     LEAF for the clientModuleGeneralStatus article
--- *****************************************************
pm10010mptAlmclientModuleGeneralStatus OBJECT IDENTIFIER ::= { pm10010mptAlmOtherCrit 41 }




pm10010mptAlmCfpHwInterlock OBJECT-TYPE
	  SYNTAX EkiOnOff
	  MAX-ACCESS read-only
	  STATUS current
	  DESCRIPTION
        "
        Client Trscv Hardware Interlock
        :This OID indicates the Client
         Trscv power is higher than the
        cooling capacity <Help> Alarm indicating
        the Client Trscv power is higher
        than the cooling capacity <Condtype>
        CFP_HW_INTERLOCK <Probcause> temperatureUnacceptable
        (51) <Alarmtype> equipmentAlarm
        (5) <Polarity> (2)
        "
	  ::= { pm10010mptAlmclientModuleGeneralStatus 14 }



pm10010mptAlmCfpLossOfRefclk OBJECT-TYPE
	  SYNTAX EkiOnOff
	  MAX-ACCESS read-only
	  STATUS current
	  DESCRIPTION
        "
        Client Trscv Loss Of Ref Clock
        :This OID indicates a Loss of Reference
        clock is detected on the Client
        Trscv <Help> Alarm indicating a
        Loss of Reference clock is detected
        on the Client Trscv <Condtype>
         CFP_LOSS_OF_REFCLK <Probcause>
        inputOutputDeviceError (24) <Alarmtype>
        equipmentAlarm (5) <Polarity> (2)
        "
	  ::= { pm10010mptAlmclientModuleGeneralStatus 11 }



pm10010mptAlmCfpTxJitterPllLol OBJECT-TYPE
	  SYNTAX EkiOnOff
	  MAX-ACCESS read-only
	  STATUS current
	  DESCRIPTION
        "
        Client Trscv Tx Jitter PLL Loss
        Of Lock :This OID indicates a Tx
        Jitter PLL Loss of Lock is dtected
        on the Client Trscv <Help> Alarm
        indicating a Tx Jitter PLL Loss
        of Lock is dtected on the Client
        Trscv <Condtype> CFP_TX_JITTER_PLL_LOL
        <Probcause> inputOutputDeviceError
        (24) <Alarmtype> equipmentAlarm
        (5) <Polarity> (2)
        "
	  ::= { pm10010mptAlmclientModuleGeneralStatus 10 }



pm10010mptAlmCfpTxCmuLol OBJECT-TYPE
	  SYNTAX EkiOnOff
	  MAX-ACCESS read-only
	  STATUS current
	  DESCRIPTION
        "
        Client Trscv CMU Loss Of Lock
         :This OID indicates a Clock Multiplier
        Unit Loss of Lock is detected on
        the Client Trscv <Help> Alarm indicating
        a Clock Multiplier Unit Loss of
        Lock is detected on the Client
         Trscv <Condtype> CFP_TX_CMU_LOL
        <Probcause> inputOutputDeviceError
        (24) <Alarmtype> equipmentAlarm
        (5) <Polarity> (2)
        "
	  ::= { pm10010mptAlmclientModuleGeneralStatus 9 }



pm10010mptAlmCfpTxLosf OBJECT-TYPE
	  SYNTAX EkiOnOff
	  MAX-ACCESS read-only
	  STATUS current
	  DESCRIPTION
        "
        Client Trscv Loss Of Signal Functionality
        :This OID indicates a Loss of Signal
        functionality is detected on the
        Client Trscv <Help> Alarm indicating
        a Loss of Signal functionality
         is detected on the Client Trscv
        <Condtype> CFP_TX_LOSF <Probcause>
        lossOfSignal (30) <Alarmtype> equipmentAlarm
        (5) <Polarity> (2)
        "
	  ::= { pm10010mptAlmclientModuleGeneralStatus 8 }



pm10010mptAlmCfpTxHostLol OBJECT-TYPE
	  SYNTAX EkiOnOff
	  MAX-ACCESS read-only
	  STATUS current
	  DESCRIPTION
        "
        Client Trscv Tx Host Loss Of Lock
        :This OID indicates of Loss of
         Lock is detected on the Client
        Trscv Tx Host interface <Help>
         Alarm indicating of Loss of Lock
        is detected on the Client Trscv
        Tx Host interface <Condtype> CFP_TX_HOST_LOL
        <Probcause> receiverFailure (42)
        <Alarmtype> equipmentAlarm (5)
         <Polarity> (2)
        "
	  ::= { pm10010mptAlmclientModuleGeneralStatus 7 }



pm10010mptAlmCfpRxLos OBJECT-TYPE
	  SYNTAX EkiOnOff
	  MAX-ACCESS read-only
	  STATUS current
	  DESCRIPTION
        "
        Client Trscv Loss Of Signal :This
        OID indicates a Loss of Signal
         is detected on the Client Trscv
        <Help> Alarm indicating a Loss
         of Signal is detected on the Client
        Trscv <Condtype> CFP_RX_LOS <Probcause>
        lossOfSignal (30) <Alarmtype> equipmentAlarm
        (5) <Polarity> (2)
        "
	  ::= { pm10010mptAlmclientModuleGeneralStatus 6 }



pm10010mptAlmCfpRxNetworkLol OBJECT-TYPE
	  SYNTAX EkiOnOff
	  MAX-ACCESS read-only
	  STATUS current
	  DESCRIPTION
        "
        Client Trscv Rx Network Loss Of
        Lock :This OID indicates of Loss
        of Lock is dected on the Client
        Trscv Rx Network interface <Help>
        Alarm indicating of Loss of Lock
        is dected on the Client Trscv Rx
        Network interface <Condtype> CFP_RX_NETWORK_LOL
        <Probcause> receiverFailure (42)
        <Alarmtype> equipmentAlarm (5)
         <Polarity> (2)
        "
	  ::= { pm10010mptAlmclientModuleGeneralStatus 5 }



pm10010mptAlmCfpOutOfAlignment OBJECT-TYPE
	  SYNTAX EkiOnOff
	  MAX-ACCESS read-only
	  STATUS current
	  DESCRIPTION
        "
        Client Trscv Out Of Alignment
         :This OID indicates an Out of
         alignment on the Client Trscv
         Host Interface <Help> Alarm indicating
        an Out of alignment on the Client
        Trscv Host Interface <Condtype>
        CFP_OUT_OF_ALIGNMENT <Probcause>
        receiverFailure (42) <Alarmtype>
        equipmentAlarm (5) <Polarity> (2)
        "
	  ::= { pm10010mptAlmclientModuleGeneralStatus 4 }



--- *****************************************************
---     LEAF for the clientGlobalAlarmSummary article
--- *****************************************************
pm10010mptAlmclientGlobalAlarmSummary OBJECT IDENTIFIER ::= { pm10010mptAlmOtherCrit 42 }




pm10010mptAlmCfpGlobAlarmAssertion  OBJECT-TYPE
	  SYNTAX EkiOnOff
	  MAX-ACCESS read-only
	  STATUS current
	  DESCRIPTION
        "
        Client Trscv Global Alarm :This
        OID indicates at least one  Fault
        or Status is detected on the Client
        Trscv module <Help> Synthesis alarm
        indicating at least one Alarm,
         Warning, Fault or Status is detected
        on the Client Trscv module <Condtype>
        CFP_GLOB_ALARM_ASSERTION  <Probcause>
        informationalStatus(1000) <Alarmtype>
        other (1) <Polarity> (2)
        "
	  ::= { pm10010mptAlmclientGlobalAlarmSummary 16 }



pm10010mptAlmCfpHostLaneFaultStatus  OBJECT-TYPE
	  SYNTAX EkiOnOff
	  MAX-ACCESS read-only
	  STATUS current
	  DESCRIPTION
        "
        Client Trscv Host Fault And Status
        :This OID indicates at least one
        Fault or Status is detected on
         the Client Trscv Host Interface
        <Help> Synthesis alarm indicating
        at least one Fault or Status is
        detected on the Client Trscv Host
        Interface <Condtype> CFP_HOST_LANE_FAULT_STATUS
         <Probcause> informationalStatus(1000)
        <Alarmtype> other (1) <Polarity>
        (2)
        "
	  ::= { pm10010mptAlmclientGlobalAlarmSummary 15 }



pm10010mptAlmCfpNetworkLaneFaultStatus  OBJECT-TYPE
	  SYNTAX EkiOnOff
	  MAX-ACCESS read-only
	  STATUS current
	  DESCRIPTION
        "
        Client Trscv Network Fault And
        Status :This OID indicates at least
        one Fault or Status is detected
        on the Client Trscv Network Interface
        <Help> Synthesis alarm indicating
        at least one Fault or Status is
        detected on the Client Trscv Network
        Interface <Condtype> CFP_NETWORK_LANE_FAULT_STATUS
         <Probcause> informationalStatus(1000)
        <Alarmtype> other (1) <Polarity>
        (2)
        "
	  ::= { pm10010mptAlmclientGlobalAlarmSummary 14 }



pm10010mptAlmCfpNetworkLaneAlarmWarning1 OBJECT-TYPE
	  SYNTAX EkiOnOff
	  MAX-ACCESS read-only
	  STATUS current
	  DESCRIPTION
        "
        Client Trscv Network Alarm And
        Warning 1 :This OID indicates at
        least one DDM  is detected on the
        Client Trscv Network Interface
         <Help> Synthesis alarm indicating
        at least one DDM Alarm or DDM Warning
        is detected on the Client Trscv
        Network Interface <Condtype> CFP_NETWORK_LANE_ALARM_WARNING_1
        <Probcause> informationalStatus(1000)
        <Alarmtype> other (1) <Polarity>
        (2)
        "
	  ::= { pm10010mptAlmclientGlobalAlarmSummary 13 }



pm10010mptAlmCfpModuleAlarmWarning2 OBJECT-TYPE
	  SYNTAX EkiOnOff
	  MAX-ACCESS read-only
	  STATUS current
	  DESCRIPTION
        "
        Client Trscv Module Alarm And
         Warning 2 :This OID indicates
         at least one DDM is detected on
        the Client Trscv module <Help>
         Synthesis alarm indicating at
         least one DDM Alarm or DDM Warning
        is detected on the Client Trscv
        module <Condtype> CFP_MODULE_ALARM_WARNING_2
        <Probcause> informationalStatus(1000)
        <Alarmtype> other (1) <Polarity>
        (2)
        "
	  ::= { pm10010mptAlmclientGlobalAlarmSummary 12 }



pm10010mptAlmCfpModuleAlarmWarning1  OBJECT-TYPE
	  SYNTAX EkiOnOff
	  MAX-ACCESS read-only
	  STATUS current
	  DESCRIPTION
        "
        Client Trscv Module Alarm And
         Warning 1 :This OID indicates
         at least one DDM  This OID is
         detected on the Client Trscv module
        <Help> Synthesis alarm indicating
        at least one DDM Alarm or DDM Warning
        is detected on the Client Trscv
        module <Condtype> CFP_MODULE_ALARM_WARNING_1
         <Probcause> informationalStatus(1000)
        <Alarmtype> other (1) <Polarity>
        (2)
        "
	  ::= { pm10010mptAlmclientGlobalAlarmSummary 11 }



pm10010mptAlmCfpModuleFault  OBJECT-TYPE
	  SYNTAX EkiOnOff
	  MAX-ACCESS read-only
	  STATUS current
	  DESCRIPTION
        "
        Client Trscv Module Fault :This
        OID indicates at least one Fault
        is detected on the Client Trscv
        module <Help> Synthesis alarm indicating
        at least one Fault is detected
         on the Client Trscv module <Condtype>
        CFP_MODULE_FAULT  <Probcause> informationalStatus(1000)
        <Alarmtype> other (1) <Polarity>
        (2)
        "
	  ::= { pm10010mptAlmclientGlobalAlarmSummary 10 }



pm10010mptAlmCfpModuleGeneralStatus  OBJECT-TYPE
	  SYNTAX EkiOnOff
	  MAX-ACCESS read-only
	  STATUS current
	  DESCRIPTION
        "
        Client Trscv General Status :This
        OID indicates the Client Trscv
         module general status <Help> Synthesis
        alarm indicating the Client Trscv
        module general status <Condtype>
        CFP_MODULE_GENERAL_STATUS  <Probcause>
        informationalStatus(1000) <Alarmtype>
        other (1) <Polarity> (2)
        "
	  ::= { pm10010mptAlmclientGlobalAlarmSummary 9 }



pm10010mptAlmCfpModuleState  OBJECT-TYPE
	  SYNTAX EkiOnOff
	  MAX-ACCESS read-only
	  STATUS current
	  DESCRIPTION
        "
        Client Trscv Module State :This
        OID indicates the Client Trscv
         module state <Help> Synthesis
         alarm indicating the Client Trscv
        module state <Condtype> CFP_MODULE_STATE
         <Probcause> informationalStatus(1000)
        <Alarmtype> other (1) <Polarity>
        (2)
        "
	  ::= { pm10010mptAlmclientGlobalAlarmSummary 8 }



pm10010mptAlmCfpNetworkLaneAlarmWarning2 OBJECT-TYPE
	  SYNTAX EkiOnOff
	  MAX-ACCESS read-only
	  STATUS current
	  DESCRIPTION
        "
        Client Trscv Network Alarm And
        Warning 2 :This OID indicates at
        least one DDM is detected on the
        Client Trscv Network Interface
         <Help> Synthesis alarm indicating
        at least one DDM Alarm or DDM Warning
        is detected on the Client Trscv
        Network Interface <Condtype> CFP_NETWORK_LANE_ALARM_WARNING_2
        <Probcause> informationalStatus(1000)
        <Alarmtype> other (1) <Polarity>
        (2)
        "
	  ::= { pm10010mptAlmclientGlobalAlarmSummary 7 }



pm10010mptAlmCfpSoftGlobAlarmTest  OBJECT-TYPE
	  SYNTAX EkiOnOff
	  MAX-ACCESS read-only
	  STATUS current
	  DESCRIPTION
        "
        Client Trscv Global Alarm SW Test
        :This OID indicates the Client
         Trscv Global Alarm This OID is
        raised by SW request for test purpose
        <Help> Status indicating the Client
        Trscv Global Alarm is raised by
        SW request for test purpose <Condtype>
        CFP_SOFT_GLOB_ALARM_TEST  <Probcause>
        informationalStatus(1000) <Alarmtype>
        other (1) <Polarity> (2)
        "
	  ::= { pm10010mptAlmclientGlobalAlarmSummary 1 }



--- *****************************************************
---     LEAF for the msaModuleState article
--- *****************************************************
pm10010mptAlmmsaModuleState OBJECT IDENTIFIER ::= { pm10010mptAlmOtherCrit 46 }




pm10010mptAlmMsaHighPowerDown OBJECT-TYPE
	  SYNTAX EkiOnOff
	  MAX-ACCESS read-only
	  STATUS current
	  DESCRIPTION
        "
        Line Trscv High Power Down :This
        OID indicates the Line Trscv is
        entering Low Power state <Help>
        Status indicating the Line Trscv
        is entering Low Power state <Condtype>
        MSA_HIGH_POWER_DOWN <Probcause>
        informationalStatus(1000) <Alarmtype>
        other (1) <Polarity> (2)
        "
	  ::= { pm10010mptAlmmsaModuleState 9 }



pm10010mptAlmMsaTxTurnOff OBJECT-TYPE
	  SYNTAX EkiOnOff
	  MAX-ACCESS read-only
	  STATUS current
	  DESCRIPTION
        "
        Line Trscv Laser Turn Off :This
        OID indicates the Line Trscv is
        turning off its laser <Help> Status
        indicating the Line Trscv is turning
        off its laser <Condtype> MSA_TX_TURN_OFF
        <Probcause> informationalStatus(1000)
        <Alarmtype> other (1) <Polarity>
        (2)
        "
	  ::= { pm10010mptAlmmsaModuleState 8 }



pm10010mptAlmMsaFault OBJECT-TYPE
	  SYNTAX EkiOnOff
	  MAX-ACCESS read-only
	  STATUS current
	  DESCRIPTION
        "
        Line Trscv Fault :This OID indicates
        the Line Trscv is in Fault state
        <Help> Status indicating the Line
        Trscv is in Fault state <Condtype>
        MSA_FAULT <Probcause> informationalStatus(1000)
        <Alarmtype> other (1) <Polarity>
        (2)
        "
	  ::= { pm10010mptAlmmsaModuleState 7 }



pm10010mptAlmMsaReady OBJECT-TYPE
	  SYNTAX EkiOnOff
	  MAX-ACCESS read-only
	  STATUS current
	  DESCRIPTION
        "
        Line Trscv Ready :This OID indicates
        the Line Trscv is ready to operate
        <Help> Status indicating the Line
        Trscv is ready to operate <Condtype>
        MSA_READY <Probcause> informationalStatus(1000)
        <Alarmtype> other (1) <Polarity>
        (2)
        "
	  ::= { pm10010mptAlmmsaModuleState 6 }



pm10010mptAlmMsaTxTurnOn OBJECT-TYPE
	  SYNTAX EkiOnOff
	  MAX-ACCESS read-only
	  STATUS current
	  DESCRIPTION
        "
        Line Trscv Laser Turn On :This
        OID indicates the Line Trscv is
        turning on its laser <Help> Status
        indicating the Line Trscv is turning
        on its laser <Condtype> MSA_TX_TURN_ON
        <Probcause> informationalStatus(1000)
        <Alarmtype> other (1) <Polarity>
        (2)
        "
	  ::= { pm10010mptAlmmsaModuleState 5 }



pm10010mptAlmMsaTxOff OBJECT-TYPE
	  SYNTAX EkiOnOff
	  MAX-ACCESS read-only
	  STATUS current
	  DESCRIPTION
        "
        Line Trscv Laser Shutdown :This
        OID indicates the Line Trscv Laser
        is OFF <Help> Status indicating
        the Line Trscv Laser is OFF <Condtype>
        MSA_TX_OFF <Probcause> informationalStatus(1000)
        <Alarmtype> other (1) <Polarity>
        (2)
        "
	  ::= { pm10010mptAlmmsaModuleState 4 }



pm10010mptAlmMsaHighPowerUp OBJECT-TYPE
	  SYNTAX EkiOnOff
	  MAX-ACCESS read-only
	  STATUS current
	  DESCRIPTION
        "
        Line Trscv High Power Up :This
        OID indicates the Line Trscv is
        leaving Low Power state <Help>
         Status indicating the Line Trscv
        is leaving Low Power state <Condtype>
        MSA_HIGH_POWER_UP <Probcause> informationalStatus(1000)
        <Alarmtype> other (1) <Polarity>
        (2)
        "
	  ::= { pm10010mptAlmmsaModuleState 3 }



pm10010mptAlmMsaLowPower OBJECT-TYPE
	  SYNTAX EkiOnOff
	  MAX-ACCESS read-only
	  STATUS current
	  DESCRIPTION
        "
        Line Trscv Low Power :This OID
        indicates the Line Trscv is in
         low power state <Help> Status
         indicating the Line Trscv is in
        low power state <Condtype> MSA_LOW_POWER
        <Probcause> informationalStatus(1000)
        <Alarmtype> other (1) <Polarity>
        (2)
        "
	  ::= { pm10010mptAlmmsaModuleState 2 }



pm10010mptAlmMsaInitialize OBJECT-TYPE
	  SYNTAX EkiOnOff
	  MAX-ACCESS read-only
	  STATUS current
	  DESCRIPTION
        "
        Line Trscv Initialize :This OID
        indicates the Line Trscv initialization
        is in progress <Help> Status indicating
        the Line Trscv initialization is
        in progress <Condtype> MSA_INITIALIZE
        <Probcause> informationalStatus(1000)
        <Alarmtype> other (1) <Polarity>
        (2)
        "
	  ::= { pm10010mptAlmmsaModuleState 1 }



--- *****************************************************
---     LEAF for the msaModuleGeneralStatus article
--- *****************************************************
pm10010mptAlmmsaModuleGeneralStatus OBJECT IDENTIFIER ::= { pm10010mptAlmOtherCrit 47 }




pm10010mptAlmMsaHwInterlock OBJECT-TYPE
	  SYNTAX EkiOnOff
	  MAX-ACCESS read-only
	  STATUS current
	  DESCRIPTION
        "
        Line Trscv Hardware Interlock
         :This OID indicates the Line Trscv
        power is higher than the cooling
        capacity <Help> Alarm indicating
        the Line Trscv power is higher
         than the cooling capacity <Condtype>
        MSA_HW_INTERLOCK <Probcause> temperatureUnacceptable
        (51) <Alarmtype> equipmentAlarm
        (5) <Polarity> (2)
        "
	  ::= { pm10010mptAlmmsaModuleGeneralStatus 14 }



pm10010mptAlmMsaLossOfRefclk OBJECT-TYPE
	  SYNTAX EkiOnOff
	  MAX-ACCESS read-only
	  STATUS current
	  DESCRIPTION
        "
        Line Trscv Loss Of Ref Clock :This
        OID indicates a Loss of Reference
        clock is detected on the Line Trscv
        <Help> Alarm indicating a Loss
         of Reference clock is detected
        on the Line Trscv <Condtype> MSA_LOSS_OF_REFCLK
        <Probcause> inputOutputDeviceError
        (24) <Alarmtype> equipmentAlarm
        (5) <Polarity> (2)
        "
	  ::= { pm10010mptAlmmsaModuleGeneralStatus 11 }



pm10010mptAlmMsaTxJitterPllLol OBJECT-TYPE
	  SYNTAX EkiOnOff
	  MAX-ACCESS read-only
	  STATUS current
	  DESCRIPTION
        "
        Line Trscv Tx Jitter PLL Loss
         Of Lock :This OID indicates a
         Tx Jitter PLL Loss of Lock is
         detected on the Line Trscv <Help>
        Alarm indicating a Tx Jitter PLL
        Loss of Lock is detected on the
        Line Trscv <Condtype> MSA_TX_JITTER_PLL_LOL
        <Probcause> inputOutputDeviceError
        (24) <Alarmtype> equipmentAlarm
        (5) <Polarity> (2)
        "
	  ::= { pm10010mptAlmmsaModuleGeneralStatus 10 }



pm10010mptAlmMsaTxCmuLol OBJECT-TYPE
	  SYNTAX EkiOnOff
	  MAX-ACCESS read-only
	  STATUS current
	  DESCRIPTION
        "
        Line Trscv CMU Loss Of Lock :This
        OID indicates a Clock Multiplier
        Unit Loss of Lock is detected on
        the Line Trscv <Help> Alarm indicating
        a Clock Multiplier Unit Loss of
        Lock is detected on the Line Trscv
        <Condtype> MSA_TX_CMU_LOL <Probcause>
        inputOutputDeviceError (24) <Alarmtype>
        equipmentAlarm (5) <Polarity> (2)
        "
	  ::= { pm10010mptAlmmsaModuleGeneralStatus 9 }



pm10010mptAlmMsaTxLosf OBJECT-TYPE
	  SYNTAX EkiOnOff
	  MAX-ACCESS read-only
	  STATUS current
	  DESCRIPTION
        "
        Line Trscv Loss Of Signal Functionality
        :This OID indicates a Loss of Signal
        functionality is detected on the
        Line Trscv <Help> Alarm indicating
        a Loss of Signal functionality
         is detected on the Line Trscv
         <Condtype> MSA_TX_LOSF <Probcause>
        lossOfSignal (30) <Alarmtype> equipmentAlarm
        (5) <Polarity> (2)
        "
	  ::= { pm10010mptAlmmsaModuleGeneralStatus 8 }



pm10010mptAlmMsaTxHostLol OBJECT-TYPE
	  SYNTAX EkiOnOff
	  MAX-ACCESS read-only
	  STATUS current
	  DESCRIPTION
        "
        Line Trscv Tx Host Loss Of Lock
        :This OID indicates of Loss of
         Lock is detected on the Line Trscv
        Tx Host interface <Help> Alarm
         indicating of Loss of Lock is
         detected on the Line Trscv Tx
         Host interface <Condtype> MSA_TX_HOST_LOL
        <Probcause> receiverFailure (42)
        <Alarmtype> equipmentAlarm (5)
         <Polarity> (2)
        "
	  ::= { pm10010mptAlmmsaModuleGeneralStatus 7 }



pm10010mptAlmMsaRxLos OBJECT-TYPE
	  SYNTAX EkiOnOff
	  MAX-ACCESS read-only
	  STATUS current
	  DESCRIPTION
        "
        Line Trscv Loss Of Signal :This
        OID indicates a Loss of Signal
         is detected on the Line Trscv
         <Help> Alarm indicating a Loss
        of Signal is detected on the Line
        Trscv <Condtype> MSA_RX_LOS <Probcause>
        lossOfSignal (30) <Alarmtype> equipmentAlarm
        (5) <Polarity> (2)
        "
	  ::= { pm10010mptAlmmsaModuleGeneralStatus 6 }



pm10010mptAlmMsaRxNetworkLol OBJECT-TYPE
	  SYNTAX EkiOnOff
	  MAX-ACCESS read-only
	  STATUS current
	  DESCRIPTION
        "
        Line Trscv Rx Network Loss Of
         Lock :This OID indicates of Loss
        of Lock is detected on the Line
        Trscv Rx Network interface <Help>
        Alarm indicating of Loss of Lock
        is detected on the Line Trscv Rx
        Network interface <Condtype> MSA_RX_NETWORK_LOL
        <Probcause> receiverFailure (42)
        <Alarmtype> equipmentAlarm (5)
         <Polarity> (2)
        "
	  ::= { pm10010mptAlmmsaModuleGeneralStatus 5 }



pm10010mptAlmMsaOutOfAlignment OBJECT-TYPE
	  SYNTAX EkiOnOff
	  MAX-ACCESS read-only
	  STATUS current
	  DESCRIPTION
        "
        Line Trscv Out Of Alignment :This
        OID indicates an Out of alignment
        on the Line Trscv Host Interface
        <Help> Alarm indicating an Out
         of alignment on the Line Trscv
        Host Interface <Condtype> MSA_OUT_OF_ALIGNMENT
        <Probcause> receiverFailure (42)
        <Alarmtype> equipmentAlarm (5)
         <Polarity> (2)
        "
	  ::= { pm10010mptAlmmsaModuleGeneralStatus 4 }



--- *****************************************************
---     LEAF for the msaGlobalAlarmSummary article
--- *****************************************************
pm10010mptAlmmsaGlobalAlarmSummary OBJECT IDENTIFIER ::= { pm10010mptAlmOtherCrit 48 }




pm10010mptAlmMsaGlobAlarmAssertion  OBJECT-TYPE
	  SYNTAX EkiOnOff
	  MAX-ACCESS read-only
	  STATUS current
	  DESCRIPTION
        "
        Line Trscv Global Alarm :This
         OID indicates at least one Fault
        or Status is detected on the Line
        Trscv module <Help> Synthesis alarm
        indicating at least one Alarm,
         Warning, Fault or Status is detected
        on the Line Trscv module <Condtype>
        MSA_GLOB_ALARM_ASSERTION  <Probcause>
        informationalStatus(1000) <Alarmtype>
        other (1) <Polarity> (2)
        "
	  ::= { pm10010mptAlmmsaGlobalAlarmSummary 16 }



pm10010mptAlmMsaHostLaneFaultStatus  OBJECT-TYPE
	  SYNTAX EkiOnOff
	  MAX-ACCESS read-only
	  STATUS current
	  DESCRIPTION
        "
        Line Trscv Host Fault And Status
        :This OID indicates at least one
        Fault or Status is detected on
         the Line Trscv Host Interface
         <Help> Synthesis alarm indicating
        at least one Fault or Status is
        detected on the Line Trscv Host
        Interface <Condtype> MSA_HOST_LANE_FAULT_STATUS
         <Probcause> informationalStatus(1000)
        <Alarmtype> other (1) <Polarity>
        (2)
        "
	  ::= { pm10010mptAlmmsaGlobalAlarmSummary 15 }



pm10010mptAlmMsaNetworkLaneFaultStatus  OBJECT-TYPE
	  SYNTAX EkiOnOff
	  MAX-ACCESS read-only
	  STATUS current
	  DESCRIPTION
        "
        Line Trscv Network Fault And Status
        :This OID indicates at least one
        Fault or Status is detected on
         the Line Trscv Network Interface
        <Help> Synthesis alarm indicating
        at least one Fault or Status is
        detected on the Line Trscv Network
        Interface <Condtype> MSA_NETWORK_LANE_FAULT_STATUS
         <Probcause> informationalStatus(1000)
        <Alarmtype> other (1) <Polarity>
        (2)
        "
	  ::= { pm10010mptAlmmsaGlobalAlarmSummary 14 }



pm10010mptAlmMsaNetworkLaneAlarmWarning1 OBJECT-TYPE
	  SYNTAX EkiOnOff
	  MAX-ACCESS read-only
	  STATUS current
	  DESCRIPTION
        "
        Line Trscv Network Alarm And Warning
        1 :This OID indicates at least
         one DDM is detected on the Line
        Trscv Network Interface <Help>
         Synthesis alarm indicating at
         least one DDM Alarm or DDM Warning
        is detected on the Line Trscv Network
        Interface <Condtype> MSA_NETWORK_LANE_ALARM_WARNING_1
        <Probcause> informationalStatus(1000)
        <Alarmtype> other (1) <Polarity>
        (2)
        "
	  ::= { pm10010mptAlmmsaGlobalAlarmSummary 13 }



pm10010mptAlmMsaModuleAlarmWarning2 OBJECT-TYPE
	  SYNTAX EkiOnOff
	  MAX-ACCESS read-only
	  STATUS current
	  DESCRIPTION
        "
        Line Trscv Module Alarm And Warning
        2 :This OID indicates at least
         one DDM is detected on the Line
        Trscv module <Help> Synthesis alarm
        indicating at least one DDM Alarm
        or DDM Warning is detected on the
        Line Trscv module <Condtype> MSA_MODULE_ALARM_WARNING_2
        <Probcause> informationalStatus(1000)
        <Alarmtype> other (1) <Polarity>
        (2)
        "
	  ::= { pm10010mptAlmmsaGlobalAlarmSummary 12 }



pm10010mptAlmMsaModuleAlarmWarning1  OBJECT-TYPE
	  SYNTAX EkiOnOff
	  MAX-ACCESS read-only
	  STATUS current
	  DESCRIPTION
        "
        Line Trscv Module Alarm And Warning
        1 :This OID indicates at least
         one DDM is detected on the Line
        Trscv module <Help> Synthesis alarm
        indicating at least one DDM Alarm
        or DDM Warning is detected on the
        Line Trscv module <Condtype> MSA_MODULE_ALARM_WARNING_1
         <Probcause> informationalStatus(1000)
        <Alarmtype> other (1) <Polarity>
        (2)
        "
	  ::= { pm10010mptAlmmsaGlobalAlarmSummary 11 }



pm10010mptAlmModuleFault  OBJECT-TYPE
	  SYNTAX EkiOnOff
	  MAX-ACCESS read-only
	  STATUS current
	  DESCRIPTION
        "
        Line Trscv Module Fault :This
         OID indicates at least one Fault
        is detected on the Line Trscv module
        <Help> Synthesis alarm indicating
        at least one Fault is detected
         on the Line Trscv module <Condtype>
        MODULE_FAULT  <Probcause> informationalStatus(1000)
        <Alarmtype> other (1) <Polarity>
        (2)
        "
	  ::= { pm10010mptAlmmsaGlobalAlarmSummary 10 }



pm10010mptAlmMsaModuleGeneralStatus  OBJECT-TYPE
	  SYNTAX EkiOnOff
	  MAX-ACCESS read-only
	  STATUS current
	  DESCRIPTION
        "
        Line Trscv General Status :This
        OID indicates the Line Trscv module
        general <Help> Synthesis alarm
         indicating the Line Trscv module
        general status <Condtype> MSA_MODULE_GENERAL_STATUS
         <Probcause> informationalStatus(1000)
        <Alarmtype> other (1) <Polarity>
        (2)
        "
	  ::= { pm10010mptAlmmsaGlobalAlarmSummary 9 }



pm10010mptAlmMsaModuleState  OBJECT-TYPE
	  SYNTAX EkiOnOff
	  MAX-ACCESS read-only
	  STATUS current
	  DESCRIPTION
        "
        Line Trscv Module State :This
         OID indicates the Line Trscv module
        state <Help> Synthesis alarm indicating
        the Line Trscv module state <Condtype>
        MSA_MODULE_STATE  <Probcause> informationalStatus(1000)
        <Alarmtype> other (1) <Polarity>
        (2)
        "
	  ::= { pm10010mptAlmmsaGlobalAlarmSummary 8 }



pm10010mptAlmMsaNetworkLaneAlarmWarning2 OBJECT-TYPE
	  SYNTAX EkiOnOff
	  MAX-ACCESS read-only
	  STATUS current
	  DESCRIPTION
        "
        Line Trscv Network Alarm And Warning
        2 :This OID indicates at least
         one DDM This OID is detected on
        the Line Trscv Network Interface
        <Help> Synthesis alarm indicating
        at least one DDM Alarm or DDM Warning
        is detected on the Line Trscv Network
        Interface <Condtype> MSA_NETWORK_LANE_ALARM_WARNING_2
        <Probcause> informationalStatus(1000)
        <Alarmtype> other (1) <Polarity>
        (2)
        "
	  ::= { pm10010mptAlmmsaGlobalAlarmSummary 7 }



pm10010mptAlmMsaNetworkHostAlarmStatus OBJECT-TYPE
	  SYNTAX EkiOnOff
	  MAX-ACCESS read-only
	  STATUS current
	  DESCRIPTION
        "
        Line Trscv Network/Host Alarm
         Status :This OID indicates the
        state of the Network and Host interface
        of the Line Trscv <Help> Synthesis
        alarm indicating the alarm state
        of the Network and Host interface
        of the Line Trscv <Condtype> MSA_NETWORK_HOST_ALARM_STATUS
        <Probcause> informationalStatus(1000)
        <Alarmtype> other (1) <Polarity>
        (2)
        "
	  ::= { pm10010mptAlmmsaGlobalAlarmSummary 6 }



pm10010mptAlmMsaSoftGlobAlarmTest  OBJECT-TYPE
	  SYNTAX EkiOnOff
	  MAX-ACCESS read-only
	  STATUS current
	  DESCRIPTION
        "
        Line Trscv Global Alarm SW Test
        :This OID indicates the Line Trscv
        Global alarm This OID is raised
        by SW request for test purpose
         <Help> Status indicating the Line
        Trscv Global Alarm is raised by
        SW request for test purpose <Condtype>
        MSA_SOFT_GLOB_ALARM_TEST  <Probcause>
        informationalStatus(1000) <Alarmtype>
        other (1) <Polarity> (2)
        "
	  ::= { pm10010mptAlmmsaGlobalAlarmSummary 1 }



--- *****************************************************
---     LEAF for the msaNetworkTxAlignment article
--- *****************************************************
pm10010mptAlmmsaNetworkTxAlignment OBJECT IDENTIFIER ::= { pm10010mptAlmOtherCrit 49 }




pm10010mptAlmNetTxLossOfAlignment OBJECT-TYPE
	  SYNTAX EkiOnOff
	  MAX-ACCESS read-only
	  STATUS current
	  DESCRIPTION
        "
        Line Trscv Network Tx Loss Of
         Alignment :This OID indicates
         a Tx Loss of Alignment is detected
        on the Line Trscv Network interface
        <Help> Alarm indicating a Tx Loss
        of Alignment is detected on the
        Line Trscv Network interface <Condtype>
        NET_TX_LOSS_OF_ALIGNMENT <Probcause>
        transmitterFailure (56) <Alarmtype>
        equipmentAlarm (5) <Polarity> (2)
        "
	  ::= { pm10010mptAlmmsaNetworkTxAlignment 16 }



pm10010mptAlmNetTxOutOfAlignment OBJECT-TYPE
	  SYNTAX EkiOnOff
	  MAX-ACCESS read-only
	  STATUS current
	  DESCRIPTION
        "
        Line Trscv Network Tx Out Of Alignment
        :This OID indicates a Tx Out of
        Alignment is detected on the Line
        Trscv Network interface <Help>
         Alarm indicating a Tx Out of Alignment
        is detected on the Line Trscv Network
        interface <Condtype> NET_TX_OUT_OF_ALIGNMENT
        <Probcause> transmitterFailure
         (56) <Alarmtype> equipmentAlarm
        (5) <Polarity> (2)
        "
	  ::= { pm10010mptAlmmsaNetworkTxAlignment 15 }



pm10010mptAlmNetTxCmuLockFault OBJECT-TYPE
	  SYNTAX EkiOnOff
	  MAX-ACCESS read-only
	  STATUS current
	  DESCRIPTION
        "
        Line Trscv Network Tx CMU Lock
        Fault :This OID indicates a Tx
         Clock Multiplier Unit Lock Fault
        is detected on the Line Trscv Network
        interface <Help> Alarm indicating
        a Tx Clock Multiplier Unit Lock
        Fault is detected on the Line Trscv
        Network interface <Condtype> NET_TX_CMU_LOCK_FAULT
        <Probcause> transmitterFailure
         (56) <Alarmtype> equipmentAlarm
        (5) <Polarity> (2)
        "
	  ::= { pm10010mptAlmmsaNetworkTxAlignment 14 }



pm10010mptAlmNetTxReferenceClockFault OBJECT-TYPE
	  SYNTAX EkiOnOff
	  MAX-ACCESS read-only
	  STATUS current
	  DESCRIPTION
        "
        Line Trscv Network Tx Ref Clock
        Fault :This OID indicates a Tx
         Reference Clock Fault is detected
        on the Line Trscv Network interface
        <Help> Alarm indicating a Tx Reference
        Clock Fault is detected on the
         Line Trscv Network interface <Condtype>
        NET_TX_REFERENCE_CLOCK_FAULT <Probcause>
        transmitterFailure (56) <Alarmtype>
        equipmentAlarm (5) <Polarity> (2)
        "
	  ::= { pm10010mptAlmmsaNetworkTxAlignment 13 }



pm10010mptAlmNetTxTimingFault OBJECT-TYPE
	  SYNTAX EkiOnOff
	  MAX-ACCESS read-only
	  STATUS current
	  DESCRIPTION
        "
        Line Trscv Network Tx Timing Fault
        :This OID indicates a Tx Timing
        Fault is detected on the Line Trscv
        Network interface <Help> Alarm
         indicating a Tx Timing Fault is
        detected on the Line Trscv Network
        interface <Condtype> NET_TX_TIMING_FAULT
        <Probcause> transmitterFailure
         (56) <Alarmtype> equipmentAlarm
        (5) <Polarity> (2)
        "
	  ::= { pm10010mptAlmmsaNetworkTxAlignment 12 }



--- *****************************************************
---     LEAF for the msaNetworkRxAlignment article
--- *****************************************************
pm10010mptAlmmsaNetworkRxAlignment OBJECT IDENTIFIER ::= { pm10010mptAlmOtherCrit 50 }




pm10010mptAlmNetRxModemSyncDetectFault OBJECT-TYPE
	  SYNTAX EkiOnOff
	  MAX-ACCESS read-only
	  STATUS current
	  DESCRIPTION
        "
        Line Trscv Network Rx Modem Sync
        Detect Fault :This OID indicates
        a Rx Modem Synchronisation Detection
        Fault is detected on the Line Trscv
        Network interface <Help> Alarm
         indicating a Rx Modem Synchronisation
        Detection Fault is detected on
         the Line Trscv Network interface
        <Condtype> NET_RX_MODEM_SYNC_DETECT_FAULT
        <Probcause> receiverFailure (42)
        <Alarmtype> equipmentAlarm (5)
         <Polarity> (2)
        "
	  ::= { pm10010mptAlmmsaNetworkRxAlignment 16 }



pm10010mptAlmNetRxModemLockFault OBJECT-TYPE
	  SYNTAX EkiOnOff
	  MAX-ACCESS read-only
	  STATUS current
	  DESCRIPTION
        "
        Line Trscv Network Rx Modem Lock
        Fault :This OID indicates a Rx
         Modem Lock Fault is detected on
        the Line Trscv Network interface
        <Help> Alarm indicating a Rx Modem
        Lock Fault is detected on the Line
        Trscv Network interface <Condtype>
        NET_RX_MODEM_LOCK_FAULT <Probcause>
        receiverFailure (42) <Alarmtype>
        equipmentAlarm (5) <Polarity> (2)
        "
	  ::= { pm10010mptAlmmsaNetworkRxAlignment 15 }



pm10010mptAlmNetRxLossOfAlignment OBJECT-TYPE
	  SYNTAX EkiOnOff
	  MAX-ACCESS read-only
	  STATUS current
	  DESCRIPTION
        "
        Line Trscv Network Rx Loss Of
         Alignment :This OID indicates
         a Rx Loss of Alignment is detected
        on the Line Trscv Network interface
        <Help> Alarm indicating a Rx Loss
        of Alignment is detected on the
        Line Trscv Network interface <Condtype>
        NET_RX_LOSS_OF_ALIGNMENT <Probcause>
        receiverFailure (42) <Alarmtype>
        equipmentAlarm (5) <Polarity> (2)
        "
	  ::= { pm10010mptAlmmsaNetworkRxAlignment 14 }



pm10010mptAlmNetRxOutOfAlignment OBJECT-TYPE
	  SYNTAX EkiOnOff
	  MAX-ACCESS read-only
	  STATUS current
	  DESCRIPTION
        "
        Line Trscv Network Rx Out Of Alignment
        :This OID indicates a Rx Out of
        Alignment is detected on the Line
        Trscv Network interface <Help>
         Alarm indicating a Rx Out of Alignment
        is detected on the Line Trscv Network
        interface <Condtype> NET_RX_OUT_OF_ALIGNMENT
        <Probcause> receiverFailure (42)
        <Alarmtype> equipmentAlarm (5)
         <Polarity> (2)
        "
	  ::= { pm10010mptAlmmsaNetworkRxAlignment 13 }



pm10010mptAlmNetRxTimingFault OBJECT-TYPE
	  SYNTAX EkiOnOff
	  MAX-ACCESS read-only
	  STATUS current
	  DESCRIPTION
        "
        Line Trscv Network Rx Timing Fault
        :This OID indicates a Rx Timing
        Fault is detected on the Line Trscv
        Network interface <Help> Alarm
         indicating a Rx Timing Fault is
        detected on the Line Trscv Network
        interface <Condtype> NET_RX_TIMING_FAULT
        <Probcause> receiverFailure (42)
        <Alarmtype> equipmentAlarm (5)
         <Polarity> (2)
        "
	  ::= { pm10010mptAlmmsaNetworkRxAlignment 12 }



--- *****************************************************
---     LEAF for the msaNetworkHostNetworkAlarmSummary article
--- *****************************************************
pm10010mptAlmmsaNetworkHostNetworkAlarmSummary OBJECT IDENTIFIER ::= { pm10010mptAlmOtherCrit 51 }




pm10010mptAlmHostTxOtnStatus OBJECT-TYPE
	  SYNTAX EkiOnOff
	  MAX-ACCESS read-only
	  STATUS current
	  DESCRIPTION
        "
        Line Trscv Host Tx OTN :This OID
        indicates a Tx OTN Fault is detected
        on the Line Trscv Host interface
        <Help> Synthesis Alarm indicating
        a Tx OTN Fault is detected on the
        Line Trscv Host interface <Condtype>
        HOST_TX_OTN_STATUS <Probcause>
         informationalStatus(1000) <Alarmtype>
        other (1) <Polarity> (2)
        "
	  ::= { pm10010mptAlmmsaNetworkHostNetworkAlarmSummary 16 }



pm10010mptAlmHostTxAlignment OBJECT-TYPE
	  SYNTAX EkiOnOff
	  MAX-ACCESS read-only
	  STATUS current
	  DESCRIPTION
        "
        Line Trscv Host Tx Alignment :This
        OID indicates a Tx Alignment Fault
        is detected on the Line Trscv Host
        interface <Help> Synthesis Alarm
        indicating a Tx Alignment Fault
        is detected on the Line Trscv Host
        interface <Condtype> HOST_TX_ALIGNMENT
        <Probcause> informationalStatus(1000)
        <Alarmtype> other (1) <Polarity>
        (2)
        "
	  ::= { pm10010mptAlmmsaNetworkHostNetworkAlarmSummary 15 }



pm10010mptAlmHostRxAlignment OBJECT-TYPE
	  SYNTAX EkiOnOff
	  MAX-ACCESS read-only
	  STATUS current
	  DESCRIPTION
        "
        Line Trscv Host Rx Alignment :This
        OID indicates a Rx Alignment Fault
        is detected on the Line Trscv Host
        interface <Help> Synthesis Alarm
        indicating a Rx Alignment Fault
        is detected on the Line Trscv Host
        interface <Condtype> HOST_RX_ALIGNMENT
        <Probcause> informationalStatus(1000)
        <Alarmtype> other (1) <Polarity>
        (2)
        "
	  ::= { pm10010mptAlmmsaNetworkHostNetworkAlarmSummary 14 }



pm10010mptAlmNetworkRxOtn OBJECT-TYPE
	  SYNTAX EkiOnOff
	  MAX-ACCESS read-only
	  STATUS current
	  DESCRIPTION
        "
        Line Trscv Network Rx OTN :This
        OID indicates a Rx OTN Fault is
        detected on the Line Trscv Network
        interface <Help> Synthesis Alarm
        indicating a Rx OTN Fault is detected
        on the Line Trscv Network interface
        <Condtype> NETWORK_RX_OTN <Probcause>
        informationalStatus(1000) <Alarmtype>
        other (1) <Polarity> (2)
        "
	  ::= { pm10010mptAlmmsaNetworkHostNetworkAlarmSummary 13 }



pm10010mptAlmNetworkRxAlignment OBJECT-TYPE
	  SYNTAX EkiOnOff
	  MAX-ACCESS read-only
	  STATUS current
	  DESCRIPTION
        "
        Line Trscv Network Rx Alignment
        :This OID indicates a Rx Alignment
        Fault is detected on the Line Trscv
        Network interface <Help> Synthesis
        Alarm indicating a Rx Alignment
        Fault is detected on the Line Trscv
        Network interface <Condtype> NETWORK_RX_ALIGNMENT
        <Probcause> informationalStatus(1000)
        <Alarmtype> other (1) <Polarity>
        (2)
        "
	  ::= { pm10010mptAlmmsaNetworkHostNetworkAlarmSummary 12 }



pm10010mptAlmNetworkTxAlignment OBJECT-TYPE
	  SYNTAX EkiOnOff
	  MAX-ACCESS read-only
	  STATUS current
	  DESCRIPTION
        "
        Line Trscv Network Tx Alignment
        :This OID indicates a Tx Alignment
        Fault is detected on the Line Trscv
        Network interface <Help> Synthesis
        Alarm indicating a Tx Alignment
        Fault is detected on the Line Trscv
        Network interface <Condtype> NETWORK_TX_ALIGNMENT
        <Probcause> informationalStatus(1000)
        <Alarmtype> other (1) <Polarity>
        (2)
        "
	  ::= { pm10010mptAlmmsaNetworkHostNetworkAlarmSummary 11 }



--- *****************************************************
---     LEAF for the msaHostTxAlignment article
--- *****************************************************
pm10010mptAlmmsaHostTxAlignment OBJECT IDENTIFIER ::= { pm10010mptAlmOtherCrit 52 }




pm10010mptAlmHostTxCdrLockFault OBJECT-TYPE
	  SYNTAX EkiOnOff
	  MAX-ACCESS read-only
	  STATUS current
	  DESCRIPTION
        "
        Line Trscv Host Tx CDR Lock Fault
        :This OID indicates a Tx Clock
         Data Recovery Lock Fault is detected
        on the Line Trscv Host interface
        <Help> Alarm indicating a Tx Clock
        Data Recovery Lock Fault is detected
        on the Line Trscv Host interface
        <Condtype> HOST_TX_CDR_LOCK_FAULT
        <Probcause> receiverFailure (42)
        <Alarmtype> equipmentAlarm (5)
         <Polarity> (2)
        "
	  ::= { pm10010mptAlmmsaHostTxAlignment 16 }



pm10010mptAlmHostTxLossOfAlignment OBJECT-TYPE
	  SYNTAX EkiOnOff
	  MAX-ACCESS read-only
	  STATUS current
	  DESCRIPTION
        "
        Line Trscv Host Tx Loss Of Alignment
        :This OID indicates a Tx Loss of
        Alignment is detected on the Line
        Trscv Host interface <Help> Alarm
        indicating a Tx Loss of Alignment
        is detected on the Line Trscv Host
        interface <Condtype> HOST_TX_LOSS_OF_ALIGNMENT
        <Probcause> receiverFailure (42)
        <Alarmtype> equipmentAlarm (5)
         <Polarity> (2)
        "
	  ::= { pm10010mptAlmmsaHostTxAlignment 15 }



pm10010mptAlmHostTxOutOfAlignment OBJECT-TYPE
	  SYNTAX EkiOnOff
	  MAX-ACCESS read-only
	  STATUS current
	  DESCRIPTION
        "
        Line Trscv Host Tx Out Of Alignment
        :This OID indicates a Tx Out of
        Alignment is detected on the Line
        Trscv Host interface <Help> Alarm
        indicating a Tx Out of Alignment
        is detected on the Line Trscv Host
        interface <Condtype> HOST_TX_OUT_OF_ALIGNMENT
        <Probcause> receiverFailure (42)
        <Alarmtype> equipmentAlarm (5)
         <Polarity> (2)
        "
	  ::= { pm10010mptAlmmsaHostTxAlignment 14 }



pm10010mptAlmHostTxDeskewLockFault OBJECT-TYPE
	  SYNTAX EkiOnOff
	  MAX-ACCESS read-only
	  STATUS current
	  DESCRIPTION
        "
        Line Trscv Host Tx Deskew Lock
        Fault :This OID indicates a Tx
         Deskew Lock Fault is detected
         on  the Line Trscv Host interface
        <Help> Alarm indicating a Tx Deskew
        Lock Fault is detected on  the
         Line Trscv Host interface <Condtype>
        HOST_TX_DESKEW_LOCK_FAULT <Probcause>
        receiverFailure (42) <Alarmtype>
        equipmentAlarm (5) <Polarity> (2)
        "
	  ::= { pm10010mptAlmmsaHostTxAlignment 13 }



--- *****************************************************
---     LEAF for the msaHostRxAlignment article
--- *****************************************************
pm10010mptAlmmsaHostRxAlignment OBJECT IDENTIFIER ::= { pm10010mptAlmOtherCrit 53 }




pm10010mptAlmHostRxLossOfAlignment OBJECT-TYPE
	  SYNTAX EkiOnOff
	  MAX-ACCESS read-only
	  STATUS current
	  DESCRIPTION
        "
        Line Trscv Host Rx Loss Of Alignment
        :This OID indicates a Rx Loss of
        Alignment is detected on the Line
        Trscv Host interface <Help> Alarm
        indicating a Rx Loss of Alignment
        is detected on the Line Trscv Host
        interface <Condtype> HOST_RX_LOSS_OF_ALIGNMENT
        <Probcause> transmitterFailure
         (56) <Alarmtype> equipmentAlarm
        (5) <Polarity> (2)
        "
	  ::= { pm10010mptAlmmsaHostRxAlignment 16 }



pm10010mptAlmHostRxOutOfAlignment OBJECT-TYPE
	  SYNTAX EkiOnOff
	  MAX-ACCESS read-only
	  STATUS current
	  DESCRIPTION
        "
        Line Trscv Host Rx Out Of Alignment
        :This OID indicates a Rx Out of
        Alignment is detected on the Line
        Trscv Host interface <Help> Alarm
        indicating a Rx Out of Alignment
        is detected on the Line Trscv Host
        interface <Condtype> HOST_RX_OUT_OF_ALIGNMENT
        <Probcause> transmitterFailure
         (56) <Alarmtype> equipmentAlarm
        (5) <Polarity> (2)
        "
	  ::= { pm10010mptAlmmsaHostRxAlignment 15 }



pm10010mptAlmHostRxCmuLockFault OBJECT-TYPE
	  SYNTAX EkiOnOff
	  MAX-ACCESS read-only
	  STATUS current
	  DESCRIPTION
        "
        Line Trscv Host Rx CMU Lock Fault
        :This OID indicates a Rx Clock
         Multiplier Unit Lock Fault is
         detected on the Line Trscv Host
        interface <Help> Alarm indicating
        a Rx Clock Multiplier Unit Lock
        Fault is detected on the Line Trscv
        Host interface <Condtype> HOST_RX_CMU_LOCK_FAULT
        <Probcause> transmitterFailure
         (56) <Alarmtype> equipmentAlarm
        (5) <Polarity> (2)
        "
	  ::= { pm10010mptAlmmsaHostRxAlignment 14 }



--- *********************************************************
---     TABLE for the pm10010mptAlmclientNetworkLaneAlarmWarning articles
--- *********************************************************

pm10010mptAlmclientNetworkLaneAlarmWarningTable OBJECT-TYPE
	SYNTAX  SEQUENCE OF Pm10010mptAlmclientNetworkLaneAlarmWarningEntry
	MAX-ACCESS not-accessible
	STATUS current
	DESCRIPTION
        "
        List of pm10010mptAlmclientNetworkLaneAlarmWarning
        Article
        "
	::= { pm10010mptAlmClientNurg 56 }


pm10010mptAlmclientNetworkLaneAlarmWarningEntry OBJECT-TYPE
	SYNTAX Pm10010mptAlmclientNetworkLaneAlarmWarningEntry
	MAX-ACCESS not-accessible
	STATUS current
	DESCRIPTION
        "
        Row definition for the pm10010mptAlmclientNetworkLaneAlarmWarning
        table
        "
	INDEX   { pm10010mptAlmclientNetworkLaneAlarmWarningIndex }
	::= { pm10010mptAlmclientNetworkLaneAlarmWarningTable 1 }


Pm10010mptAlmclientNetworkLaneAlarmWarningEntry ::=
	SEQUENCE {
	pm10010mptAlmclientNetworkLaneAlarmWarningIndex
		INTEGER,
	pm10010mptAlmClientBiasHighAlarmPortn
		EkiOnOff,
	pm10010mptAlmClientBiasHighWarningPortn
		EkiOnOff,
	pm10010mptAlmClientBiasLowWarningPortn
		EkiOnOff,
	pm10010mptAlmClientBiasLowAlarmPortn
		EkiOnOff,
	pm10010mptAlmClientTxPowerHighAlarmPortn
		EkiOnOff,
	pm10010mptAlmClientTxPowerHighWarningPortn
		EkiOnOff,
	pm10010mptAlmClientTxPowerLowWarningPortn
		EkiOnOff,
	pm10010mptAlmClientTxPowerLowAlarmPortn
		EkiOnOff,
	pm10010mptAlmClientLaserTempHighAlarmPortn
		EkiOnOff,
	pm10010mptAlmClientLaserTempHighWarningPortn
		EkiOnOff,
	pm10010mptAlmClientLaserTempLowWarningPortn
		EkiOnOff,
	pm10010mptAlmLaserTempLowAlarmPortn
		EkiOnOff,
	pm10010mptAlmClientRxPowerHighAlarmPortn
		EkiOnOff,
	pm10010mptAlmClientRxPowerHighWarningPortn
		EkiOnOff,
	pm10010mptAlmClientRxPowerLowWarningPortn
		EkiOnOff,
	pm10010mptAlmClientRxPowerLowAlarmPortn
		EkiOnOff
	}


pm10010mptAlmclientNetworkLaneAlarmWarningIndex OBJECT-TYPE
	SYNTAX  INTEGER(0..128)
	MAX-ACCESS  read-only
	STATUS current
	DESCRIPTION
        "
        Index definition for the pm10010mptAlmclientNetworkLaneAlarmWarning
        table
        "
	::= { pm10010mptAlmclientNetworkLaneAlarmWarningEntry 1 }


pm10010mptAlmClientBiasHighAlarmPortn OBJECT-TYPE
	SYNTAX  EkiOnOff
	MAX-ACCESS read-only
	STATUS current
	DESCRIPTION
        "
        Client Trscv Bias High Alarm :This
        OID indicates that the Trscv laser
        bias current is higher than the
        threshold value written in the
         Trscv EEPROM <Help> Alarm indicating
        that the Trscv laser bias current
        is higher than the threshold value
        written in the Trscv EEPROM <Condtype>
        CLIENT_BIAS_HIGH_ALARM <Probcause>
        transmitterFailure (56) <Alarmtype>
        equipmentAlarm (5) <Polarity> (2)
        "
	::= { pm10010mptAlmclientNetworkLaneAlarmWarningEntry 17 }


pm10010mptAlmClientBiasHighWarningPortn OBJECT-TYPE
	SYNTAX  EkiOnOff
	MAX-ACCESS read-only
	STATUS current
	DESCRIPTION
        "
        Client Trscv Bias High Warning
        :This OID indicates that the Trscv
        laser bias current is higher than
        the threshold value written in
         the Trscv EEPROM <Help> Warning
        indicating that the Trscv laser
        bias current is higher than the
        threshold value written in the
         Trscv EEPROM <Condtype> CLIENT_BIAS_HIGH_WARNING
        <Probcause> transmitterFailure
         (56) <Alarmtype> equipmentAlarm
        (5) <Polarity> (2)
        "
	::= { pm10010mptAlmclientNetworkLaneAlarmWarningEntry 16 }


pm10010mptAlmClientBiasLowWarningPortn OBJECT-TYPE
	SYNTAX  EkiOnOff
	MAX-ACCESS read-only
	STATUS current
	DESCRIPTION
        "
        Client Trscv Bias Low Warning
         :This OID indicates that the Trscv
        laser bias current is lower than
        the threshold value written in
         the Trscv EEPROM <Help> Warning
        indicating that the Trscv laser
        bias current is lower than the
         threshold value written in the
        Trscv EEPROM <Condtype> CLIENT_BIAS_LOW_WARNING
        <Probcause> transmitterFailure
         (56) <Alarmtype> equipmentAlarm
        (5) <Polarity> (2)
        "
	::= { pm10010mptAlmclientNetworkLaneAlarmWarningEntry 15 }


pm10010mptAlmClientBiasLowAlarmPortn OBJECT-TYPE
	SYNTAX  EkiOnOff
	MAX-ACCESS read-only
	STATUS current
	DESCRIPTION
        "
        Client Trscv Bias Low Alarm :This
        OID indicates that the Trscv laser
        bias current is lower than the
         threshold value written in the
        Trscv EEPROM <Help> Alarm indicating
        that the Trscv laser bias current
        is lower than the threshold value
        written in the Trscv EEPROM <Condtype>
        CLIENT_BIAS_LOW_ALARM <Probcause>
        transmitterFailure (56) <Alarmtype>
        equipmentAlarm (5) <Polarity> (2)
        "
	::= { pm10010mptAlmclientNetworkLaneAlarmWarningEntry 14 }


pm10010mptAlmClientTxPowerHighAlarmPortn OBJECT-TYPE
	SYNTAX  EkiOnOff
	MAX-ACCESS read-only
	STATUS current
	DESCRIPTION
        "
        Client Trscv Tx Power High Alarm
        :This OID indicates that the Trscv
        output power is higher than the
        threshold value written in the
         Trscv EEPROM <Help> Alarm indicating
        that the Trscv output power is
         higher than the threshold value
        written in the Trscv EEPROM <Condtype>
        CLIENT_TX_POWER_HIGH_ALARM <Probcause>
        transmitterFailure (56) <Alarmtype>
        equipmentAlarm (5) <Polarity> (2)
        "
	::= { pm10010mptAlmclientNetworkLaneAlarmWarningEntry 13 }


pm10010mptAlmClientTxPowerHighWarningPortn OBJECT-TYPE
	SYNTAX  EkiOnOff
	MAX-ACCESS read-only
	STATUS current
	DESCRIPTION
        "
        Client Trscv Tx Power High Warning
        :This OID indicates that the Trscv
        output power is higher than the
        threshold value written in the
         Trscv EEPROM <Help> Warning indicating
        that the Trscv output power is
         higher than the threshold value
        written in the Trscv EEPROM <Condtype>
        CLIENT_TX_POWER_HIGH_WARNING <Probcause>
        transmitterFailure (56) <Alarmtype>
        equipmentAlarm (5) <Polarity> (2)
        "
	::= { pm10010mptAlmclientNetworkLaneAlarmWarningEntry 12 }


pm10010mptAlmClientTxPowerLowWarningPortn OBJECT-TYPE
	SYNTAX  EkiOnOff
	MAX-ACCESS read-only
	STATUS current
	DESCRIPTION
        "
        Client Trscv Tx Power Low Warning
        :This OID indicates that the Trscv
        output power is lower than the
         threshold value written in the
        Trscv EEPROM <Help> Warning indicating
        that the Trscv output power is
         lower than the threshold value
        written in the Trscv EEPROM <Condtype>
        CLIENT_TX_POWER_LOW_WARNING <Probcause>
        transmitterFailure (56) <Alarmtype>
        equipmentAlarm (5) <Polarity> (2)
        "
	::= { pm10010mptAlmclientNetworkLaneAlarmWarningEntry 11 }


pm10010mptAlmClientTxPowerLowAlarmPortn OBJECT-TYPE
	SYNTAX  EkiOnOff
	MAX-ACCESS read-only
	STATUS current
	DESCRIPTION
        "
        Client Trscv Tx Power Low Alarm
        :This OID indicates that the Trscv
        output power is lower than the
         threshold value written in the
        Trscv EEPROM <Help> Alarm indicating
        that the Trscv output power is
         lower than the threshold value
        written in the Trscv EEPROM <Condtype>
        CLIENT_TX_POWER_LOW_ALARM <Probcause>
        transmitterFailure (56) <Alarmtype>
        equipmentAlarm (5) <Polarity> (2)
        "
	::= { pm10010mptAlmclientNetworkLaneAlarmWarningEntry 10 }


pm10010mptAlmClientLaserTempHighAlarmPortn OBJECT-TYPE
	SYNTAX  EkiOnOff
	MAX-ACCESS read-only
	STATUS current
	DESCRIPTION
        "
        Client Trscv Laser Temp High Alarm
        :This OID indicates that the Trscv
        Laser Temperature is higher than
        the threshold value written in
         the Trscv EEPROM <Help> Alarm
         indicating that the Trscv Laser
        Temperature is higher than the
         threshold value written in the
        Trscv EEPROM <Condtype> CLIENT_LASER_TEMP_HIGH_ALARM
        <Probcause> temperatureUnacceptable
        (51) <Alarmtype> equipmentAlarm
        (5) <Polarity> (2)
        "
	::= { pm10010mptAlmclientNetworkLaneAlarmWarningEntry 9 }


pm10010mptAlmClientLaserTempHighWarningPortn OBJECT-TYPE
	SYNTAX  EkiOnOff
	MAX-ACCESS read-only
	STATUS current
	DESCRIPTION
        "
        Client Trscv Laser Temp High Warning
        :This OID indicates that the Trscv
        Laser Temperature is higher than
        the threshold value written in
         the Trscv EEPROM <Help> Warning
        indicating that the Trscv Laser
        Temperature is higher than the
         threshold value written in the
        Trscv EEPROM <Condtype> CLIENT_LASER_TEMP_HIGH_WARNING
        <Probcause> temperatureUnacceptable
        (51) <Alarmtype> equipmentAlarm
        (5) <Polarity> (2)
        "
	::= { pm10010mptAlmclientNetworkLaneAlarmWarningEntry 8 }


pm10010mptAlmClientLaserTempLowWarningPortn OBJECT-TYPE
	SYNTAX  EkiOnOff
	MAX-ACCESS read-only
	STATUS current
	DESCRIPTION
        "
        Client Trscv Laser Temp Low Warning
        :This OID indicates that the Trscv
        Laser Temperature is lower than
        the threshold value written in
         the Trscv EEPROM <Help> Warning
        indicating that the Trscv Laser
        Temperature is lower than the threshold
        value written in the Trscv EEPROM
        <Condtype> CLIENT_LASER_TEMP_LOW_WARNING
        <Probcause> temperatureUnacceptable
        (51) <Alarmtype> equipmentAlarm
        (5) <Polarity> (2)
        "
	::= { pm10010mptAlmclientNetworkLaneAlarmWarningEntry 7 }


pm10010mptAlmLaserTempLowAlarmPortn OBJECT-TYPE
	SYNTAX  EkiOnOff
	MAX-ACCESS read-only
	STATUS current
	DESCRIPTION
        "
        Client Trscv Laser Temp Low Alarm
        :This OID indicates that the Trscv
        Laser Temperature is lower than
        the threshold value written in
         the Trscv EEPROM <Help> Alarm
         indicating that the Trscv Laser
        Temperature is lower than the threshold
        value written in the Trscv EEPROM
        <Condtype> LASER_TEMP_LOW_ALARM
        <Probcause> temperatureUnacceptable
        (51) <Alarmtype> equipmentAlarm
        (5) <Polarity> (2)
        "
	::= { pm10010mptAlmclientNetworkLaneAlarmWarningEntry 6 }


pm10010mptAlmClientRxPowerHighAlarmPortn OBJECT-TYPE
	SYNTAX  EkiOnOff
	MAX-ACCESS read-only
	STATUS current
	DESCRIPTION
        "
        Client Trscv Rx Power High Alarm
        :This OID indicates that the Trscv
        input power is higher than the
         threshold value written in the
        Trscv EEPROM <Help> Alarm indicating
        that the Trscv input power is higher
        than the threshold value written
        in the Trscv EEPROM <Condtype>
         CLIENT_RX_POWER_HIGH_ALARM <Probcause>
        receiveFailure (41) <Alarmtype>
        equipmentAlarm (5) <Polarity> (2)
        "
	::= { pm10010mptAlmclientNetworkLaneAlarmWarningEntry 5 }


pm10010mptAlmClientRxPowerHighWarningPortn OBJECT-TYPE
	SYNTAX  EkiOnOff
	MAX-ACCESS read-only
	STATUS current
	DESCRIPTION
        "
        Client Trscv Rx Power High Warning
        :This OID indicates that the Trscv
        input power is higher than the
         threshold value written in the
        Trscv EEPROM <Help> Warning indicating
        that the Trscv input power is higher
        than the threshold value written
        in the Trscv EEPROM <Condtype>
         CLIENT_RX_POWER_HIGH_WARNING <Probcause>
        receiveFailure (41) <Alarmtype>
        equipmentAlarm (5) <Polarity> (2)
        "
	::= { pm10010mptAlmclientNetworkLaneAlarmWarningEntry 4 }


pm10010mptAlmClientRxPowerLowWarningPortn OBJECT-TYPE
	SYNTAX  EkiOnOff
	MAX-ACCESS read-only
	STATUS current
	DESCRIPTION
        "
        Client Trscv Rx Power Low Warning
        :This OID indicates that the Trscv
        input power is lower than the threshold
        value written in the Trscv EEPROM
        <Help> Warning indicating that
         the Trscv input power is lower
        than the threshold value written
        in the Trscv EEPROM <Condtype>
         CLIENT_RX_POWER_LOW_WARNING <Probcause>
        receiveFailure (41) <Alarmtype>
        equipmentAlarm (5) <Polarity> (2)
        "
	::= { pm10010mptAlmclientNetworkLaneAlarmWarningEntry 3 }


pm10010mptAlmClientRxPowerLowAlarmPortn OBJECT-TYPE
	SYNTAX  EkiOnOff
	MAX-ACCESS read-only
	STATUS current
	DESCRIPTION
        "
        Client Trscv Rx Power Low Alarm
        :This OID indicates that the Trscv
        input power is lower than the threshold
        value written in the Trscv EEPROM
        <Help> Alarm indicating that the
        Trscv input power is lower than
        the threshold value written in
         the Trscv EEPROM <Condtype> CLIENT_RX_POWER_LOW_ALARM
        <Probcause> receiveFailure (41)
        <Alarmtype> equipmentAlarm (5)
         <Polarity> (2)
        "
	::= { pm10010mptAlmclientNetworkLaneAlarmWarningEntry 2 }


--- *********************************************************
---     TABLE for the pm10010mptAlmclientNetworkLaneFault articles
--- *********************************************************

pm10010mptAlmclientNetworkLaneFaultTable OBJECT-TYPE
	SYNTAX  SEQUENCE OF Pm10010mptAlmclientNetworkLaneFaultEntry
	MAX-ACCESS not-accessible
	STATUS current
	DESCRIPTION
        "
        List of pm10010mptAlmclientNetworkLaneFault
        Article
        "
	::= { pm10010mptAlmClientUrg 72 }


pm10010mptAlmclientNetworkLaneFaultEntry OBJECT-TYPE
	SYNTAX Pm10010mptAlmclientNetworkLaneFaultEntry
	MAX-ACCESS not-accessible
	STATUS current
	DESCRIPTION
        "
        Row definition for the pm10010mptAlmclientNetworkLaneFault
        table
        "
	INDEX   { pm10010mptAlmclientNetworkLaneFaultIndex }
	::= { pm10010mptAlmclientNetworkLaneFaultTable 1 }


Pm10010mptAlmclientNetworkLaneFaultEntry ::=
	SEQUENCE {
	pm10010mptAlmclientNetworkLaneFaultIndex
		INTEGER,
	pm10010mptAlmClientLaneTecFaultPortn
		EkiOnOff,
	pm10010mptAlmClientLaneWavelengthUnlockedPortn
		EkiOnOff,
	pm10010mptAlmClientLaneApdPowerSupplyPortn
		EkiOnOff,
	pm10010mptAlmClientLaneTxLosfPortn
		EkiOnOff,
	pm10010mptAlmClientLaneTxLolPortn
		EkiOnOff,
	pm10010mptAlmClientLaneRxLosPortn
		EkiOnOff,
	pm10010mptAlmClientLaneRxLolPortn
		EkiOnOff,
	pm10010mptAlmClientLaneRxFifoErrorPortn
		EkiOnOff
	}


pm10010mptAlmclientNetworkLaneFaultIndex OBJECT-TYPE
	SYNTAX  INTEGER(0..128)
	MAX-ACCESS  read-only
	STATUS current
	DESCRIPTION
        "
        Index definition for the pm10010mptAlmclientNetworkLaneFault
        table
        "
	::= { pm10010mptAlmclientNetworkLaneFaultEntry 1 }


pm10010mptAlmClientLaneTecFaultPortn OBJECT-TYPE
	SYNTAX  EkiOnOff
	MAX-ACCESS read-only
	STATUS current
	DESCRIPTION
        "
        Client Network Lane TEC Fault
         :This OID indicates a TEC Fault
        on the Client Trscv Network Lane
        <Help> Alarm indicating a TEC Fault
        on the Client Trscv Network Lane
        <Condtype> CLIENT_LANE_TEC_FAULT
        <Probcause> transmitterFailure
         (56) <Alarmtype> equipmentAlarm
        (5) <Polarity> (2)
        "
	::= { pm10010mptAlmclientNetworkLaneFaultEntry 17 }


pm10010mptAlmClientLaneWavelengthUnlockedPortn OBJECT-TYPE
	SYNTAX  EkiOnOff
	MAX-ACCESS read-only
	STATUS current
	DESCRIPTION
        "
        Client Network Lane Wavelength
        Unlock :This OID indicates a Wavelength
        unlock on the Client Trscv Network
        Lane <Help> Alarm indicating a
         Wavelength unlock on the Client
        Trscv Network Lane <Condtype> CLIENT_LANE_WAVELENGTH_UNLOCKED
        <Probcause> transmitterFailure
         (56) <Alarmtype> equipmentAlarm
        (5) <Polarity> (2)
        "
	::= { pm10010mptAlmclientNetworkLaneFaultEntry 16 }


pm10010mptAlmClientLaneApdPowerSupplyPortn OBJECT-TYPE
	SYNTAX  EkiOnOff
	MAX-ACCESS read-only
	STATUS current
	DESCRIPTION
        "
        Client Network Lane APD Power
         Supply :This OID indicates an
         APD Power supply failure on the
        Client Trscv Network Lane <Help>
        Alarm indicating an APD Power supply
        failure on the Client Trscv Network
        Lane <Condtype> CLIENT_LANE_APD_POWER_SUPPLY
        <Probcause> transmitterFailure
         (56) <Alarmtype> equipmentAlarm
        (5) <Polarity> (2)
        "
	::= { pm10010mptAlmclientNetworkLaneFaultEntry 15 }


pm10010mptAlmClientLaneTxLosfPortn OBJECT-TYPE
	SYNTAX  EkiOnOff
	MAX-ACCESS read-only
	STATUS current
	DESCRIPTION
        "
        Client Network Lane Tx Loss Of
        Signal Functionality :This OID
         indicates a Tx Loss of Signal
         Functionality on the Client Trscv
        Network Lane <Help> Alarm indicating
        a Tx Loss of Signal Functionality
        on the Client Trscv Network Lane
        <Condtype> CLIENT_LANE_TX_LOSF
         <Probcause> transmitterFailure
        (56) <Alarmtype> equipmentAlarm
        (5) <Polarity> (2)
        "
	::= { pm10010mptAlmclientNetworkLaneFaultEntry 9 }


pm10010mptAlmClientLaneTxLolPortn OBJECT-TYPE
	SYNTAX  EkiOnOff
	MAX-ACCESS read-only
	STATUS current
	DESCRIPTION
        "
        Client Network Lane Tx Loss Of
        Lock :This OID indicates a Tx Loss
        of Lock on the Client Trscv Network
        Lane <Help> Alarm indicating a
         Tx Loss of Lock on the Client
         Trscv Network Lane <Condtype>
         CLIENT_LANE_TX_LOL <Probcause>
        transmitterFailure (56) <Alarmtype>
        equipmentAlarm (5) <Polarity> (2)
        "
	::= { pm10010mptAlmclientNetworkLaneFaultEntry 8 }


pm10010mptAlmClientLaneRxLosPortn OBJECT-TYPE
	SYNTAX  EkiOnOff
	MAX-ACCESS read-only
	STATUS current
	DESCRIPTION
        "
        Client Network Lane Rx Loss Of
        Signal :This OID indicates a Rx
        Loss of Signal on the Client Trscv
        Network Lane <Help> Alarm indicating
        a Rx Loss of Signal on the Client
        Trscv Network Lane <Condtype> CLIENT_LANE_RX_LOS
        <Probcause> receiveFailure (41)
        <Alarmtype> physicalViolation (9)
        <Polarity> (2)
        "
	::= { pm10010mptAlmclientNetworkLaneFaultEntry 6 }


pm10010mptAlmClientLaneRxLolPortn OBJECT-TYPE
	SYNTAX  EkiOnOff
	MAX-ACCESS read-only
	STATUS current
	DESCRIPTION
        "
        Client Network Lane Rx Loss Of
        Lock :This OID indicates a Rx Loss
        of Lock on the Client Trscv Network
        Lane <Help> Alarm indicating a
         Rx Loss of Lock on the Client
         Trscv Network Lane <Condtype>
         CLIENT_LANE_RX_LOL <Probcause>
        receiverFailure (42) <Alarmtype>
        equipmentAlarm (5) <Polarity> (2)
        "
	::= { pm10010mptAlmclientNetworkLaneFaultEntry 5 }


pm10010mptAlmClientLaneRxFifoErrorPortn OBJECT-TYPE
	SYNTAX  EkiOnOff
	MAX-ACCESS read-only
	STATUS current
	DESCRIPTION
        "
        Client Network Lane Rx FIFO Error
        :This OID indicates a Rx FIFO Error
        on the Client Trscv Network Lane
        <Help> Alarm indicating a Rx FIFO
        Error on the Client Trscv Network
        Lane <Condtype> CLIENT_LANE_RX_FIFO_ERROR
        <Probcause> receiverFailure (42)
        <Alarmtype> equipmentAlarm (5)
         <Polarity> (2)
        "
	::= { pm10010mptAlmclientNetworkLaneFaultEntry 4 }


--- *********************************************************
---     TABLE for the pm10010mptAlmclientHostLaneFault articles
--- *********************************************************

pm10010mptAlmclientHostLaneFaultTable OBJECT-TYPE
	SYNTAX  SEQUENCE OF Pm10010mptAlmclientHostLaneFaultEntry
	MAX-ACCESS not-accessible
	STATUS current
	DESCRIPTION
        "
        List of pm10010mptAlmclientHostLaneFault
        Article
        "
	::= { pm10010mptAlmClientUrg 88 }


pm10010mptAlmclientHostLaneFaultEntry OBJECT-TYPE
	SYNTAX Pm10010mptAlmclientHostLaneFaultEntry
	MAX-ACCESS not-accessible
	STATUS current
	DESCRIPTION
        "
        Row definition for the pm10010mptAlmclientHostLaneFault
        table
        "
	INDEX   { pm10010mptAlmclientHostLaneFaultIndex }
	::= { pm10010mptAlmclientHostLaneFaultTable 1 }


Pm10010mptAlmclientHostLaneFaultEntry ::=
	SEQUENCE {
	pm10010mptAlmclientHostLaneFaultIndex
		INTEGER,
	pm10010mptAlmRfDetectedPortn
		EkiOnOff,
	pm10010mptAlmLfDetectedPortn
		EkiOnOff,
	pm10010mptAlmClientLaneTxFifoErrorPortn
		EkiOnOff,
	pm10010mptAlmClientTxHostLolPortn
		EkiOnOff,
	pm10010mptAlmClientCsfDetectedPortn
		EkiOnOff,
	pm10010mptAlmClientLanesNotAlignedPortn
		EkiOnOff,
	pm10010mptAlmClientLanes6466UnlockPortn
		EkiOnOff,
	pm10010mptAlmClientLanesMarkerUnlockPortn
		EkiOnOff,
	pm10010mptAlmClientInputLossOfSigPortn
		EkiOnOff,
	pm10010mptAlmClientLossOfSyncPortn
		EkiOnOff
	}


pm10010mptAlmclientHostLaneFaultIndex OBJECT-TYPE
	SYNTAX  INTEGER(0..128)
	MAX-ACCESS  read-only
	STATUS current
	DESCRIPTION
        "
        Index definition for the pm10010mptAlmclientHostLaneFault
        table
        "
	::= { pm10010mptAlmclientHostLaneFaultEntry 1 }


pm10010mptAlmRfDetectedPortn OBJECT-TYPE
	SYNTAX  EkiOnOff
	MAX-ACCESS read-only
	STATUS current
	DESCRIPTION
        "
        Remote Fault Signal Detected :This
        OID indicates a Remote Fault Signal
        is detected on the client input
        port<Help> This alarm indicates
        a Remote Fault Signal is detected
        on the client input port <Condtype>
        RF_DETECTED <Probcause> receiverFailure
        (42) <Alarmtype> equipmentAlarm
        (5) <Polarity> (2)
        "
	::= { pm10010mptAlmclientHostLaneFaultEntry 13 }


pm10010mptAlmLfDetectedPortn OBJECT-TYPE
	SYNTAX  EkiOnOff
	MAX-ACCESS read-only
	STATUS current
	DESCRIPTION
        "
        Local Fault Signal Detected :This
        OID indicates a Local Fault Signal
        is detected on the client input
        port<Help> This alarm indicates
        a Local Fault Signal is detected
        on the client input port <Condtype>
        LF_DETECTED <Probcause> receiverFailure
        (42) <Alarmtype> equipmentAlarm
        (5) <Polarity> (2)
        "
	::= { pm10010mptAlmclientHostLaneFaultEntry 12 }


pm10010mptAlmClientLaneTxFifoErrorPortn OBJECT-TYPE
	SYNTAX  EkiOnOff
	MAX-ACCESS read-only
	STATUS current
	DESCRIPTION
        "
        Client Host Lane Tx FIFO Error
        :This OID indicates a Tx FIFO Error
        on the Client Trscv Host Lane <Help>
        Alarm indicating a Tx FIFO Error
        on the Client Trscv Host Lane <Condtype>
        CLIENT_LANE_TX_FIFO_ERROR <Probcause>
        receiverFailure (42) <Alarmtype>
        equipmentAlarm (5) <Polarity> (2)
        "
	::= { pm10010mptAlmclientHostLaneFaultEntry 11 }


pm10010mptAlmClientTxHostLolPortn OBJECT-TYPE
	SYNTAX  EkiOnOff
	MAX-ACCESS read-only
	STATUS current
	DESCRIPTION
        "
        Client Host Lane Tx Loss Of Lock
        :This OID indicates a Tx Loss of
        Lock on the Client Trscv Host Lane
        <Help> Alarm indicating a Tx Loss
        of Lock on the Client Trscv Host
        Lane <Condtype> CLIENT_TX_HOST_LOL
        <Probcause> receiverFailure (42)
        <Alarmtype> equipmentAlarm (5)
         <Polarity> (2)
        "
	::= { pm10010mptAlmclientHostLaneFaultEntry 10 }


pm10010mptAlmClientCsfDetectedPortn OBJECT-TYPE
	SYNTAX  EkiOnOff
	MAX-ACCESS read-only
	STATUS current
	DESCRIPTION
        "
        Client Signal Fail Detected :This
        OID indicates that a CSF has been
        detected on client port in the
         downstream direction   <Help>
          This alarm indicates if a Client
        Signal Fail has been detected in
        the incoming line frame for this
        client port <Condtype> CLIENT_CSF_DETECTED
        <Probcause> receiveFailure (41)
        <Alarmtype> other(1) <Polarity>
        (2)
        "
	::= { pm10010mptAlmclientHostLaneFaultEntry 7 }


pm10010mptAlmClientLanesNotAlignedPortn OBJECT-TYPE
	SYNTAX  EkiOnOff
	MAX-ACCESS read-only
	STATUS current
	DESCRIPTION
        "
        Client Lanes Not Aligned :This
        OID indicates the Client lanes
         are not aligned <Help> Alarm indicating
        the Client lanes are not aligned
        <Condtype> CLIENT_LANES_NOT_ALIGNED
        <Probcause> receiveFailure (41)
        <Alarmtype> integrityViolation
         (7) <Polarity> (2)
        "
	::= { pm10010mptAlmclientHostLaneFaultEntry 6 }


pm10010mptAlmClientLanes6466UnlockPortn OBJECT-TYPE
	SYNTAX  EkiOnOff
	MAX-ACCESS read-only
	STATUS current
	DESCRIPTION
        "
        Client Lanes 64/66b Unlock :This
        OID indicates the Client 64/66b
        decoder is not lock <Help> Alarm
        indicating the Client 64/66b decoder
        is not lock <Condtype> CLIENT_LANES_64_66_UNLOCK
        <Probcause> receiveFailure (41)
        <Alarmtype> integrityViolation
         (7) <Polarity> (2)
        "
	::= { pm10010mptAlmclientHostLaneFaultEntry 5 }


pm10010mptAlmClientLanesMarkerUnlockPortn OBJECT-TYPE
	SYNTAX  EkiOnOff
	MAX-ACCESS read-only
	STATUS current
	DESCRIPTION
        "
        Client Lanes Marker Unlock :This
        OID indicates the Client lanes
         marker alignment is not lock <Help>
        Alarm indicating the Client lanes
        marker alignment is not lock <Condtype>
        CLIENT_LANES_MARKER_UNLOCK <Probcause>
        receiveFailure (41) <Alarmtype>
        integrityViolation (7) <Polarity>
        (2)
        "
	::= { pm10010mptAlmclientHostLaneFaultEntry 4 }


pm10010mptAlmClientInputLossOfSigPortn OBJECT-TYPE
	SYNTAX  EkiOnOff
	MAX-ACCESS read-only
	STATUS current
	DESCRIPTION
        "
        Client Input Loss Of Signal :This
        OID indicates a Loss of Signal
         is detected on the Client Trscv
        <Help> Alarm indicating a Loss
         of Signal is detected on the Client
        Trscv <Condtype> CLIENT_INPUT_LOSS_OF_SIG
        <Probcause> receiveFailure (41)
        <Alarmtype> physicalViolation (9)
        <Polarity> (2)
        "
	::= { pm10010mptAlmclientHostLaneFaultEntry 3 }


pm10010mptAlmClientLossOfSyncPortn OBJECT-TYPE
	SYNTAX  EkiOnOff
	MAX-ACCESS read-only
	STATUS current
	DESCRIPTION
        "
        Client Frame Alignment Loss :This
        OID indicates the module is not
        aligned with the incoming Client
        signal <Help> Alarm indicating
         the module is not aligned with
        the incoming client signal <Condtype>
        CLIENT_LOSS_OF_SYNC <Probcause>
        receiveFailure (41) <Alarmtype>
        integrityViolation (7) <Polarity>
        (2)
        "
	::= { pm10010mptAlmclientHostLaneFaultEntry 2 }


--- *********************************************************
---     TABLE for the pm10010mptAlmlineNetworkLaneAlarmWarning1 articles
--- *********************************************************

pm10010mptAlmlineNetworkLaneAlarmWarning1Table OBJECT-TYPE
	SYNTAX  SEQUENCE OF Pm10010mptAlmlineNetworkLaneAlarmWarning1Entry
	MAX-ACCESS not-accessible
	STATUS current
	DESCRIPTION
        "
        List of pm10010mptAlmlineNetworkLaneAlarmWarning1
        Article
        "
	::= { pm10010mptAlmLineNurg 104 }


pm10010mptAlmlineNetworkLaneAlarmWarning1Entry OBJECT-TYPE
	SYNTAX Pm10010mptAlmlineNetworkLaneAlarmWarning1Entry
	MAX-ACCESS not-accessible
	STATUS current
	DESCRIPTION
        "
        Row definition for the pm10010mptAlmlineNetworkLaneAlarmWarning1
        table
        "
	INDEX   { pm10010mptAlmlineNetworkLaneAlarmWarning1Index }
	::= { pm10010mptAlmlineNetworkLaneAlarmWarning1Table 1 }


Pm10010mptAlmlineNetworkLaneAlarmWarning1Entry ::=
	SEQUENCE {
	pm10010mptAlmlineNetworkLaneAlarmWarning1Index
		INTEGER,
	pm10010mptAlmLineBiasHighAlarmPortn
		EkiOnOff,
	pm10010mptAlmLineBiasHighWarningPortn
		EkiOnOff,
	pm10010mptAlmLineBiasLowWarningPortn
		EkiOnOff,
	pm10010mptAlmLineBiasLowAlarmPortn
		EkiOnOff,
	pm10010mptAlmLineTxPowerHighAlarmPortn
		EkiOnOff,
	pm10010mptAlmLineTxPowerHighWarningPortn
		EkiOnOff,
	pm10010mptAlmLineTxPowerLowWarningPortn
		EkiOnOff,
	pm10010mptAlmLineTxPowerLowAlarmPortn
		EkiOnOff,
	pm10010mptAlmLineLaserTempHighAlarmPortn
		EkiOnOff,
	pm10010mptAlmLineLaserTempHighWarningPortn
		EkiOnOff,
	pm10010mptAlmLineLaserTempLowWarningPortn
		EkiOnOff,
	pm10010mptAlmLineLaserTempLowAlarmPortn
		EkiOnOff,
	pm10010mptAlmLineRxPowerHighAlarmPortn
		EkiOnOff,
	pm10010mptAlmLineRxPowerHighWarningPortn
		EkiOnOff,
	pm10010mptAlmLineRxPowerLowWarningPortn
		EkiOnOff,
	pm10010mptAlmLineRxPowerLowAlarmPortn
		EkiOnOff
	}


pm10010mptAlmlineNetworkLaneAlarmWarning1Index OBJECT-TYPE
	SYNTAX  INTEGER(0..128)
	MAX-ACCESS  read-only
	STATUS current
	DESCRIPTION
        "
        Index definition for the pm10010mptAlmlineNetworkLaneAlarmWarning1
        table
        "
	::= { pm10010mptAlmlineNetworkLaneAlarmWarning1Entry 1 }


pm10010mptAlmLineBiasHighAlarmPortn OBJECT-TYPE
	SYNTAX  EkiOnOff
	MAX-ACCESS read-only
	STATUS current
	DESCRIPTION
        "
        Line Trscv Tx Bias High Alarm
         :This OID indicates that the Trscv
        laser bias current is higher than
        the threshold value written in
         the Trscv EEPROM <Help> Alarm
         indicating that the Trscv laser
        bias current is higher than the
        threshold value written in the
         Trscv EEPROM <Condtype> LINE_BIAS_HIGH_ALARM
        <Probcause> transmitterFailure
         (56) <Alarmtype> equipmentAlarm
        (5) <Polarity> (2)
        "
	::= { pm10010mptAlmlineNetworkLaneAlarmWarning1Entry 17 }


pm10010mptAlmLineBiasHighWarningPortn OBJECT-TYPE
	SYNTAX  EkiOnOff
	MAX-ACCESS read-only
	STATUS current
	DESCRIPTION
        "
        Line Trscv Tx Bias High Warning
        :This OID indicates that the Trscv
        laser bias current is higher than
        the threshold value written in
         the Trscv EEPROM <Help> Warning
        indicating that the Trscv laser
        bias current is higher than the
        threshold value written in the
         Trscv EEPROM <Condtype> LINE_BIAS_HIGH_WARNING
        <Probcause> transmitterFailure
         (56) <Alarmtype> equipmentAlarm
        (5) <Polarity> (2)
        "
	::= { pm10010mptAlmlineNetworkLaneAlarmWarning1Entry 16 }


pm10010mptAlmLineBiasLowWarningPortn OBJECT-TYPE
	SYNTAX  EkiOnOff
	MAX-ACCESS read-only
	STATUS current
	DESCRIPTION
        "
        Line Trscv Tx Bias Low Warning
        :This OID indicates that the Trscv
        laser bias current is lower than
        the threshold value written in
         the Trscv EEPROM <Help> Warning
        indicating that the Trscv laser
        bias current is lower than the
         threshold value written in the
        Trscv EEPROM <Condtype> LINE_BIAS_LOW_WARNING
        <Probcause> transmitterFailure
         (56) <Alarmtype> equipmentAlarm
        (5) <Polarity> (2)
        "
	::= { pm10010mptAlmlineNetworkLaneAlarmWarning1Entry 15 }


pm10010mptAlmLineBiasLowAlarmPortn OBJECT-TYPE
	SYNTAX  EkiOnOff
	MAX-ACCESS read-only
	STATUS current
	DESCRIPTION
        "
        Line Trscv Tx Bias Low Alarm :This
        OID indicates that the Trscv laser
        bias current is lower than the
         threshold value written in the
        Trscv EEPROM <Help> Alarm indicating
        that the Trscv laser bias current
        is lower than the threshold value
        written in the Trscv EEPROM <Condtype>
        LINE_BIAS_LOW_ALARM <Probcause>
        transmitterFailure (56) <Alarmtype>
        equipmentAlarm (5) <Polarity> (2)
        "
	::= { pm10010mptAlmlineNetworkLaneAlarmWarning1Entry 14 }


pm10010mptAlmLineTxPowerHighAlarmPortn OBJECT-TYPE
	SYNTAX  EkiOnOff
	MAX-ACCESS read-only
	STATUS current
	DESCRIPTION
        "
        Line Trscv Tx Power High Alarm
        :This OID indicates that the Trscv
        output power is higher than the
        threshold value written in the
         Trscv EEPROM <Help> Alarm indicating
        that the Trscv output power is
         higher than the threshold value
        written in the Trscv EEPROM <Condtype>
        LINE_TX_POWER_HIGH_ALARM <Probcause>
        transmitterFailure (56) <Alarmtype>
        equipmentAlarm (5) <Polarity> (2)
        "
	::= { pm10010mptAlmlineNetworkLaneAlarmWarning1Entry 13 }


pm10010mptAlmLineTxPowerHighWarningPortn OBJECT-TYPE
	SYNTAX  EkiOnOff
	MAX-ACCESS read-only
	STATUS current
	DESCRIPTION
        "
        Line Trscv Tx Power High Warning
        :This OID indicates that the Trscv
        output power is higher than the
        threshold value written in the
         Trscv EEPROM <Help> Warning indicating
        that the Trscv output power is
         higher than the threshold value
        written in the Trscv EEPROM <Condtype>
        LINE_TX_POWER_HIGH_WARNING <Probcause>
        transmitterFailure (56) <Alarmtype>
        equipmentAlarm (5) <Polarity> (2)
        "
	::= { pm10010mptAlmlineNetworkLaneAlarmWarning1Entry 12 }


pm10010mptAlmLineTxPowerLowWarningPortn OBJECT-TYPE
	SYNTAX  EkiOnOff
	MAX-ACCESS read-only
	STATUS current
	DESCRIPTION
        "
        Line Trscv Tx Power Low Warning
        :This OID indicates that the Trscv
        output power is lower than the
         threshold value written in the
        Trscv EEPROM <Help> Warning indicating
        that the Trscv output power is
         lower than the threshold value
        written in the Trscv EEPROM <Condtype>
        LINE_TX_POWER_LOW_WARNING <Probcause>
        transmitterFailure (56) <Alarmtype>
        equipmentAlarm (5) <Polarity> (2)
        "
	::= { pm10010mptAlmlineNetworkLaneAlarmWarning1Entry 11 }


pm10010mptAlmLineTxPowerLowAlarmPortn OBJECT-TYPE
	SYNTAX  EkiOnOff
	MAX-ACCESS read-only
	STATUS current
	DESCRIPTION
        "
        Line Trscv Tx Power Low Alarm
         :This OID indicates that the Trscv
        output power is lower than the
         threshold value written in the
        Trscv EEPROM <Help> Alarm indicating
        that the Trscv output power is
         lower than the threshold value
        written in the Trscv EEPROM <Condtype>
        LINE_TX_POWER_LOW_ALARM <Probcause>
        transmitterFailure (56) <Alarmtype>
        equipmentAlarm (5) <Polarity> (2)
        "
	::= { pm10010mptAlmlineNetworkLaneAlarmWarning1Entry 10 }


pm10010mptAlmLineLaserTempHighAlarmPortn OBJECT-TYPE
	SYNTAX  EkiOnOff
	MAX-ACCESS read-only
	STATUS current
	DESCRIPTION
        "
        Line Trscv Tx Laser Temp High
         Alarm :This OID indicates that
        the Trscv Tx Laser Temperature
         is higher than the threshold value
        written in the Trscv EEPROM <Help>
        Alarm indicating that the Trscv
        Tx Laser Temperature is higher
         than the threshold value written
        in the Trscv EEPROM <Condtype>
         LINE_LASER_TEMP_HIGH_ALARM <Probcause>
        temperatureUnacceptable (51) <Alarmtype>
        equipmentAlarm (5) <Polarity> (2)
        "
	::= { pm10010mptAlmlineNetworkLaneAlarmWarning1Entry 9 }


pm10010mptAlmLineLaserTempHighWarningPortn OBJECT-TYPE
	SYNTAX  EkiOnOff
	MAX-ACCESS read-only
	STATUS current
	DESCRIPTION
        "
        Line Trscv Tx Laser Temp High
         Warning :This OID indicates that
        the Trscv Tx Laser Temperature
         is higher than the threshold value
        written in the Trscv EEPROM <Help>
        Warning indicating that the Trscv
        Tx Laser Temperature is higher
         than the threshold value written
        in the Trscv EEPROM <Condtype>
         LINE_LASER_TEMP_HIGH_WARNING <Probcause>
        temperatureUnacceptable (51) <Alarmtype>
        equipmentAlarm (5) <Polarity> (2)
        "
	::= { pm10010mptAlmlineNetworkLaneAlarmWarning1Entry 8 }


pm10010mptAlmLineLaserTempLowWarningPortn OBJECT-TYPE
	SYNTAX  EkiOnOff
	MAX-ACCESS read-only
	STATUS current
	DESCRIPTION
        "
        Line Trscv Tx Laser Temp Low Warning
        :This OID indicates that the Trscv
        Tx Laser Temperature is lower than
        the threshold value written in
         the Trscv EEPROM <Help> Warning
        indicating that the Trscv Tx Laser
        Temperature is lower than the threshold
        value written in the Trscv EEPROM
        <Condtype> LINE_LASER_TEMP_LOW_WARNING
        <Probcause> temperatureUnacceptable
        (51) <Alarmtype> equipmentAlarm
        (5) <Polarity> (2)
        "
	::= { pm10010mptAlmlineNetworkLaneAlarmWarning1Entry 7 }


pm10010mptAlmLineLaserTempLowAlarmPortn OBJECT-TYPE
	SYNTAX  EkiOnOff
	MAX-ACCESS read-only
	STATUS current
	DESCRIPTION
        "
        Line Trscv Tx Laser Temp Low Alarm
        :This OID indicates that the Trscv
        Tx Laser Temperature is lower than
        the threshold value written in
         the Trscv EEPROM <Help> Alarm
         indicating that the Trscv Tx Laser
        Temperature is lower than the threshold
        value written in the Trscv EEPROM
        <Condtype> LINE_LASER_TEMP_LOW_ALARM
        <Probcause> temperatureUnacceptable
        (51) <Alarmtype> equipmentAlarm
        (5) <Polarity> (2)
        "
	::= { pm10010mptAlmlineNetworkLaneAlarmWarning1Entry 6 }


pm10010mptAlmLineRxPowerHighAlarmPortn OBJECT-TYPE
	SYNTAX  EkiOnOff
	MAX-ACCESS read-only
	STATUS current
	DESCRIPTION
        "
        Line Trscv Rx Power High Alarm
        :This OID indicates that the Trscv
        input power is higher than the
         threshold value written in the
        Trscv EEPROM <Help> Alarm indicating
        that the Trscv input power is higher
        than the threshold value written
        in the Trscv EEPROM <Condtype>
         LINE_RX_POWER_HIGH_ALARM <Probcause>
        receiveFailure (41) <Alarmtype>
        equipmentAlarm (5) <Polarity> (2)
        "
	::= { pm10010mptAlmlineNetworkLaneAlarmWarning1Entry 5 }


pm10010mptAlmLineRxPowerHighWarningPortn OBJECT-TYPE
	SYNTAX  EkiOnOff
	MAX-ACCESS read-only
	STATUS current
	DESCRIPTION
        "
        Line Trscv Rx Power High Warning
        :This OID indicates that the Trscv
        input power is higher than the
         threshold value written in the
        Trscv EEPROM <Help> Warning indicating
        that the Trscv input power is higher
        than the threshold value written
        in the Trscv EEPROM <Condtype>
         LINE_RX_POWER_HIGH_WARNING <Probcause>
        receiveFailure (41) <Alarmtype>
        equipmentAlarm (5) <Polarity> (2)
        "
	::= { pm10010mptAlmlineNetworkLaneAlarmWarning1Entry 4 }


pm10010mptAlmLineRxPowerLowWarningPortn OBJECT-TYPE
	SYNTAX  EkiOnOff
	MAX-ACCESS read-only
	STATUS current
	DESCRIPTION
        "
        Line Trscv Rx Power Low Warning
        :This OID indicates that the Trscv
        input power is lower than the threshold
        value written in the Trscv EEPROM
        <Help> Warning indicating that
         the Trscv input power is lower
        than the threshold value written
        in the Trscv EEPROM <Condtype>
         LINE_RX_POWER_LOW_WARNING <Probcause>
        receiveFailure (41) <Alarmtype>
        equipmentAlarm (5) <Polarity> (2)
        "
	::= { pm10010mptAlmlineNetworkLaneAlarmWarning1Entry 3 }


pm10010mptAlmLineRxPowerLowAlarmPortn OBJECT-TYPE
	SYNTAX  EkiOnOff
	MAX-ACCESS read-only
	STATUS current
	DESCRIPTION
        "
        Line Trscv Rx Power Low Alarm
         :This OID indicates that the Trscv
        input power is lower than the threshold
        value written in the Trscv EEPROM
        <Help> Alarm indicating that the
        Trscv input power is lower than
        the threshold value written in
         the Trscv EEPROM <Condtype> LINE_RX_POWER_LOW_ALARM
        <Probcause> receiveFailure (41)
        <Alarmtype> equipmentAlarm (5)
         <Polarity> (2)
        "
	::= { pm10010mptAlmlineNetworkLaneAlarmWarning1Entry 2 }


--- *********************************************************
---     TABLE for the pm10010mptAlmlineNetworkLaneAlarmWarning2 articles
--- *********************************************************

pm10010mptAlmlineNetworkLaneAlarmWarning2Table OBJECT-TYPE
	SYNTAX  SEQUENCE OF Pm10010mptAlmlineNetworkLaneAlarmWarning2Entry
	MAX-ACCESS not-accessible
	STATUS current
	DESCRIPTION
        "
        List of pm10010mptAlmlineNetworkLaneAlarmWarning2
        Article
        "
	::= { pm10010mptAlmLineNurg 120 }


pm10010mptAlmlineNetworkLaneAlarmWarning2Entry OBJECT-TYPE
	SYNTAX Pm10010mptAlmlineNetworkLaneAlarmWarning2Entry
	MAX-ACCESS not-accessible
	STATUS current
	DESCRIPTION
        "
        Row definition for the pm10010mptAlmlineNetworkLaneAlarmWarning2
        table
        "
	INDEX   { pm10010mptAlmlineNetworkLaneAlarmWarning2Index }
	::= { pm10010mptAlmlineNetworkLaneAlarmWarning2Table 1 }


Pm10010mptAlmlineNetworkLaneAlarmWarning2Entry ::=
	SEQUENCE {
	pm10010mptAlmlineNetworkLaneAlarmWarning2Index
		INTEGER,
	pm10010mptAlmRxLaserBiasHighAlarmPortn
		EkiOnOff,
	pm10010mptAlmRxLaserBiasHighWarningPortn
		EkiOnOff,
	pm10010mptAlmRxLaserBiasLowWarningPortn
		EkiOnOff,
	pm10010mptAlmRxLaserBiasLowAlarmPortn
		EkiOnOff,
	pm10010mptAlmRxLaserOutputHighAlarmPortn
		EkiOnOff,
	pm10010mptAlmRxLaserOutputHighWarningPortn
		EkiOnOff,
	pm10010mptAlmRxLaserOutputLowWarningPortn
		EkiOnOff,
	pm10010mptAlmRxLaserOutputLowAlarmPortn
		EkiOnOff,
	pm10010mptAlmRxLaserTempHighAlarmPortn
		EkiOnOff,
	pm10010mptAlmRxLaserTempHighWarningPortn
		EkiOnOff,
	pm10010mptAlmRxLaserTempLowWarningPortn
		EkiOnOff,
	pm10010mptAlmRxLaserTempLowAlarmPortn
		EkiOnOff,
	pm10010mptAlmTxModulatorBiasHighAlarmPortn
		EkiOnOff,
	pm10010mptAlmTxModulatorBiasHighWarningPortn
		EkiOnOff,
	pm10010mptAlmTxModulatorBiasLowWarningPortn
		EkiOnOff,
	pm10010mptAlmTxModulatorBiasLowAlarmPortn
		EkiOnOff
	}


pm10010mptAlmlineNetworkLaneAlarmWarning2Index OBJECT-TYPE
	SYNTAX  INTEGER(0..128)
	MAX-ACCESS  read-only
	STATUS current
	DESCRIPTION
        "
        Index definition for the pm10010mptAlmlineNetworkLaneAlarmWarning2
        table
        "
	::= { pm10010mptAlmlineNetworkLaneAlarmWarning2Entry 1 }


pm10010mptAlmRxLaserBiasHighAlarmPortn OBJECT-TYPE
	SYNTAX  EkiOnOff
	MAX-ACCESS read-only
	STATUS current
	DESCRIPTION
        "
        Line Trscv Rx Bias High Alarm
         :This OID indicates that the Trscv
        Rx laser bias current is higher
        than the threshold value written
        in the Trscv EEPROM <Help> Alarm
        indicating that the Trscv Rx laser
        bias current is higher than the
        threshold value written in the
         Trscv EEPROM <Condtype> RX_LASER_BIAS_HIGH_ALARM
        <Probcause> receiveFailure (41)
        <Alarmtype> equipmentAlarm (5)
         <Polarity> (2)
        "
	::= { pm10010mptAlmlineNetworkLaneAlarmWarning2Entry 17 }


pm10010mptAlmRxLaserBiasHighWarningPortn OBJECT-TYPE
	SYNTAX  EkiOnOff
	MAX-ACCESS read-only
	STATUS current
	DESCRIPTION
        "
        Line Trscv Rx Bias High Warning
        :This OID indicates that the Trscv
        Rx laser bias current is higher
        than the threshold value written
        in the Trscv EEPROM <Help> Warning
        indicating that the Trscv Rx laser
        bias current is higher than the
        threshold value written in the
         Trscv EEPROM <Condtype> RX_LASER_BIAS_HIGH_WARNING
        <Probcause> receiveFailure (41)
        <Alarmtype> equipmentAlarm (5)
         <Polarity> (2)
        "
	::= { pm10010mptAlmlineNetworkLaneAlarmWarning2Entry 16 }


pm10010mptAlmRxLaserBiasLowWarningPortn OBJECT-TYPE
	SYNTAX  EkiOnOff
	MAX-ACCESS read-only
	STATUS current
	DESCRIPTION
        "
        Line Trscv Rx Bias Low Warning
        :This OID indicates that the Trscv
        Rx laser bias current is lower
         than the threshold value written
        in the Trscv EEPROM <Help> Warning
        indicating that the Trscv Rx laser
        bias current is lower than the
         threshold value written in the
        Trscv EEPROM <Condtype> RX_LASER_BIAS_LOW_WARNING
        <Probcause> receiveFailure (41)
        <Alarmtype> equipmentAlarm (5)
         <Polarity> (2)
        "
	::= { pm10010mptAlmlineNetworkLaneAlarmWarning2Entry 15 }


pm10010mptAlmRxLaserBiasLowAlarmPortn OBJECT-TYPE
	SYNTAX  EkiOnOff
	MAX-ACCESS read-only
	STATUS current
	DESCRIPTION
        "
        Line Trscv Rx Bias Low Alarm :This
        OID indicates that the Trscv Rx
        laser bias current is lower than
        the threshold value written in
         the Trscv EEPROM <Help> Alarm
         indicating that the Trscv Rx laser
        bias current is lower than the
         threshold value written in the
        Trscv EEPROM <Condtype> RX_LASER_BIAS_LOW_ALARM
        <Probcause> receiveFailure (41)
        <Alarmtype> equipmentAlarm (5)
         <Polarity> (2)
        "
	::= { pm10010mptAlmlineNetworkLaneAlarmWarning2Entry 14 }


pm10010mptAlmRxLaserOutputHighAlarmPortn OBJECT-TYPE
	SYNTAX  EkiOnOff
	MAX-ACCESS read-only
	STATUS current
	DESCRIPTION
        "
        Line Trscv Rx Output Power High
        Alarm :This OID indicates that
         the Trscv Rx output power is higher
        than the threshold value written
        in the Trscv EEPROM <Help> Alarm
        indicating that the Trscv Rx output
        power is higher than the threshold
        value written in the Trscv EEPROM
        <Condtype> RX_LASER_OUTPUT_HIGH_ALARM
        <Probcause> receiveFailure (41)
        <Alarmtype> equipmentAlarm (5)
         <Polarity> (2)
        "
	::= { pm10010mptAlmlineNetworkLaneAlarmWarning2Entry 13 }


pm10010mptAlmRxLaserOutputHighWarningPortn OBJECT-TYPE
	SYNTAX  EkiOnOff
	MAX-ACCESS read-only
	STATUS current
	DESCRIPTION
        "
        Line Trscv Rx Output Power High
        Warning :This OID indicates that
        the Trscv Rx output power is higher
        than the threshold value written
        in the Trscv EEPROM <Help> Warning
        indicating that the Trscv Rx output
        power is higher than the threshold
        value written in the Trscv EEPROM
        <Condtype> RX_LASER_OUTPUT_HIGH_WARNING
        <Probcause> receiveFailure (41)
        <Alarmtype> equipmentAlarm (5)
         <Polarity> (2)
        "
	::= { pm10010mptAlmlineNetworkLaneAlarmWarning2Entry 12 }


pm10010mptAlmRxLaserOutputLowWarningPortn OBJECT-TYPE
	SYNTAX  EkiOnOff
	MAX-ACCESS read-only
	STATUS current
	DESCRIPTION
        "
        Line Trscv Rx Output Power Low
        Warning :This OID indicates that
        the Trscv Rx output power is lower
        than the threshold value written
        in the Trscv EEPROM <Help> Warning
        indicating that the Trscv Rx output
        power is lower than the threshold
        value written in the Trscv EEPROM
        <Condtype> RX_LASER_OUTPUT_LOW_WARNING
        <Probcause> receiveFailure (41)
        <Alarmtype> equipmentAlarm (5)
         <Polarity> (2)
        "
	::= { pm10010mptAlmlineNetworkLaneAlarmWarning2Entry 11 }


pm10010mptAlmRxLaserOutputLowAlarmPortn OBJECT-TYPE
	SYNTAX  EkiOnOff
	MAX-ACCESS read-only
	STATUS current
	DESCRIPTION
        "
        Line Trscv Rx Output Power Low
        Alarm :This OID indicates that
         the Trscv Rx output power is lower
        than the threshold value written
        in the Trscv EEPROM <Help> Alarm
        indicating that the Trscv Rx output
        power is lower than the threshold
        value written in the Trscv EEPROM
        <Condtype> RX_LASER_OUTPUT_LOW_ALARM
        <Probcause> receiveFailure (41)
        <Alarmtype> equipmentAlarm (5)
         <Polarity> (2)
        "
	::= { pm10010mptAlmlineNetworkLaneAlarmWarning2Entry 10 }


pm10010mptAlmRxLaserTempHighAlarmPortn OBJECT-TYPE
	SYNTAX  EkiOnOff
	MAX-ACCESS read-only
	STATUS current
	DESCRIPTION
        "
        Line Trscv Rx Laser Temp High
         Alarm :This OID indicates that
        the Trscv Rx Laser Temperature
         is higher than the threshold value
        written in the Trscv EEPROM <Help>
        Alarm indicating that the Trscv
        Rx Laser Temperature is higher
         than the threshold value written
        in the Trscv EEPROM <Condtype>
         RX_LASER_TEMP_HIGH_ALARM <Probcause>
        temperatureUnacceptable (51) <Alarmtype>
        equipmentAlarm (5) <Polarity> (2)
        "
	::= { pm10010mptAlmlineNetworkLaneAlarmWarning2Entry 9 }


pm10010mptAlmRxLaserTempHighWarningPortn OBJECT-TYPE
	SYNTAX  EkiOnOff
	MAX-ACCESS read-only
	STATUS current
	DESCRIPTION
        "
        Line Trscv Rx Laser Temp High
         Warning :This OID indicates that
        the Trscv Rx Laser Temperature
         is higher than the threshold value
        written in the Trscv EEPROM <Help>
        Warning indicating that the Trscv
        Rx Laser Temperature is higher
         than the threshold value written
        in the Trscv EEPROM <Condtype>
         RX_LASER_TEMP_HIGH_WARNING <Probcause>
        temperatureUnacceptable (51) <Alarmtype>
        equipmentAlarm (5) <Polarity> (2)
        "
	::= { pm10010mptAlmlineNetworkLaneAlarmWarning2Entry 8 }


pm10010mptAlmRxLaserTempLowWarningPortn OBJECT-TYPE
	SYNTAX  EkiOnOff
	MAX-ACCESS read-only
	STATUS current
	DESCRIPTION
        "
        Line Trscv Rx Laser Temp Low Warning
        :This OID indicates that the Trscv
        Rx Laser Temperature is lower than
        the threshold value written in
         the Trscv EEPROM <Help> Warning
        indicating that the Trscv Rx Laser
        Temperature is lower than the threshold
        value written in the Trscv EEPROM
        <Condtype> RX_LASER_TEMP_LOW_WARNING
        <Probcause> temperatureUnacceptable
        (51) <Alarmtype> equipmentAlarm
        (5) <Polarity> (2)
        "
	::= { pm10010mptAlmlineNetworkLaneAlarmWarning2Entry 7 }


pm10010mptAlmRxLaserTempLowAlarmPortn OBJECT-TYPE
	SYNTAX  EkiOnOff
	MAX-ACCESS read-only
	STATUS current
	DESCRIPTION
        "
        Line Trscv Rx Laser Temp Low Alarm
        :This OID indicates that the Trscv
        Rx Laser Temperature is lower than
        the threshold value written in
         the Trscv EEPROM <Help> Alarm
         indicating that the Trscv Rx Laser
        Temperature is lower than the threshold
        value written in the Trscv EEPROM
        <Condtype> RX_LASER_TEMP_LOW_ALARM
        <Probcause> temperatureUnacceptable
        (51) <Alarmtype> equipmentAlarm
        (5) <Polarity> (2)
        "
	::= { pm10010mptAlmlineNetworkLaneAlarmWarning2Entry 6 }


pm10010mptAlmTxModulatorBiasHighAlarmPortn OBJECT-TYPE
	SYNTAX  EkiOnOff
	MAX-ACCESS read-only
	STATUS current
	DESCRIPTION
        "
        Line Trscv Tx Modulator Bias High
        Alarm :This OID indicates that
         the Trscv Tx modulator bias current
        is higher than the threshold value
        written in the Trscv EEPROM <Help>
        Alarm indicating that the Trscv
        Tx modulator bias current is higher
        than the threshold value written
        in the Trscv EEPROM <Condtype>
         TX_MODULATOR_BIAS_HIGH_ALARM <Probcause>
        transmitterFailure (56) <Alarmtype>
        equipmentAlarm (5) <Polarity> (2)
        "
	::= { pm10010mptAlmlineNetworkLaneAlarmWarning2Entry 5 }


pm10010mptAlmTxModulatorBiasHighWarningPortn OBJECT-TYPE
	SYNTAX  EkiOnOff
	MAX-ACCESS read-only
	STATUS current
	DESCRIPTION
        "
        Line Trscv Tx Modulator Bias High
        Warning :This OID indicates that
        the Trscv Tx modulator bias current
        is higher than the threshold value
        written in the Trscv EEPROM <Help>
        Warning indicating that the Trscv
        Tx modulator bias current is higher
        than the threshold value written
        in the Trscv EEPROM <Condtype>
         TX_MODULATOR_BIAS_HIGH_WARNING
        <Probcause> transmitterFailure
         (56) <Alarmtype> equipmentAlarm
        (5) <Polarity> (2)
        "
	::= { pm10010mptAlmlineNetworkLaneAlarmWarning2Entry 4 }


pm10010mptAlmTxModulatorBiasLowWarningPortn OBJECT-TYPE
	SYNTAX  EkiOnOff
	MAX-ACCESS read-only
	STATUS current
	DESCRIPTION
        "
        Line Trscv Tx Modulator Bias Low
        Warning :This OID indicates that
        the Trscv Tx modulator bias current
        is lower than the threshold value
        written in the Trscv EEPROM <Help>
        Warning indicating that the Trscv
        Tx modulator bias current is lower
        than the threshold value written
        in the Trscv EEPROM <Condtype>
         TX_MODULATOR_BIAS_LOW_WARNING
         <Probcause> transmitterFailure
        (56) <Alarmtype> equipmentAlarm
        (5) <Polarity> (2)
        "
	::= { pm10010mptAlmlineNetworkLaneAlarmWarning2Entry 3 }


pm10010mptAlmTxModulatorBiasLowAlarmPortn OBJECT-TYPE
	SYNTAX  EkiOnOff
	MAX-ACCESS read-only
	STATUS current
	DESCRIPTION
        "
        Line Trscv Tx Modulator Bias Low
        Alarm :This OID indicates that
         the Trscv Tx modulator bias current
        is lower than the threshold value
        written in the Trscv EEPROM <Help>
        Alarm indicating that the Trscv
        Tx modulator bias current is lower
        than the threshold value written
        in the Trscv EEPROM <Condtype>
         TX_MODULATOR_BIAS_LOW_ALARM <Probcause>
        transmitterFailure (56) <Alarmtype>
        equipmentAlarm (5) <Polarity> (2)
        "
	::= { pm10010mptAlmlineNetworkLaneAlarmWarning2Entry 2 }


--- *********************************************************
---     TABLE for the pm10010mptAlmlineNetworkLaneFault articles
--- *********************************************************

pm10010mptAlmlineNetworkLaneFaultTable OBJECT-TYPE
	SYNTAX  SEQUENCE OF Pm10010mptAlmlineNetworkLaneFaultEntry
	MAX-ACCESS not-accessible
	STATUS current
	DESCRIPTION
        "
        List of pm10010mptAlmlineNetworkLaneFault
        Article
        "
	::= { pm10010mptAlmLineUrg 136 }


pm10010mptAlmlineNetworkLaneFaultEntry OBJECT-TYPE
	SYNTAX Pm10010mptAlmlineNetworkLaneFaultEntry
	MAX-ACCESS not-accessible
	STATUS current
	DESCRIPTION
        "
        Row definition for the pm10010mptAlmlineNetworkLaneFault
        table
        "
	INDEX   { pm10010mptAlmlineNetworkLaneFaultIndex }
	::= { pm10010mptAlmlineNetworkLaneFaultTable 1 }


Pm10010mptAlmlineNetworkLaneFaultEntry ::=
	SEQUENCE {
	pm10010mptAlmlineNetworkLaneFaultIndex
		INTEGER,
	pm10010mptAlmLineLaneTecFaultPortn
		EkiOnOff,
	pm10010mptAlmLineLaneWavelengthUnlockedPortn
		EkiOnOff,
	pm10010mptAlmLineLaneApdPowerSupplyPortn
		EkiOnOff,
	pm10010mptAlmLineLaneTxLosfPortn
		EkiOnOff,
	pm10010mptAlmLineLaneTxLolPortn
		EkiOnOff,
	pm10010mptAlmLineLaneRxLosPortn
		EkiOnOff,
	pm10010mptAlmLineLaneRxLolPortn
		EkiOnOff,
	pm10010mptAlmLineLaneRxFifoErrorPortn
		EkiOnOff,
	pm10010mptAlmLineLaneRxTecFaultPortn
		EkiOnOff
	}


pm10010mptAlmlineNetworkLaneFaultIndex OBJECT-TYPE
	SYNTAX  INTEGER(0..128)
	MAX-ACCESS  read-only
	STATUS current
	DESCRIPTION
        "
        Index definition for the pm10010mptAlmlineNetworkLaneFault
        table
        "
	::= { pm10010mptAlmlineNetworkLaneFaultEntry 1 }


pm10010mptAlmLineLaneTecFaultPortn OBJECT-TYPE
	SYNTAX  EkiOnOff
	MAX-ACCESS read-only
	STATUS current
	DESCRIPTION
        "
        Line Network Lane TEC Fault :This
        OID indicates a Tx TEC Fault on
        the Line Trscv Network Lane <Help>
        Alarm indicating a Tx TEC Fault
        on the Line Trscv Network Lane
         <Condtype> LINE_LANE_TEC_FAULT
        <Probcause> transmitterFailure
         (56) <Alarmtype> equipmentAlarm
        (5) <Polarity> (2)
        "
	::= { pm10010mptAlmlineNetworkLaneFaultEntry 17 }


pm10010mptAlmLineLaneWavelengthUnlockedPortn OBJECT-TYPE
	SYNTAX  EkiOnOff
	MAX-ACCESS read-only
	STATUS current
	DESCRIPTION
        "
        Line Network Lane Wavelength Unlock
        :This OID indicates a Wavelength
        unlock on the Line Trscv Network
        Lane <Help> Alarm indicating a
         Wavelength unlock on the Line
         Trscv Network Lane <Condtype>
         LINE_LANE_WAVELENGTH_UNLOCKED
         <Probcause> transmitterFailure
        (56) <Alarmtype> equipmentAlarm
        (5) <Polarity> (2)
        "
	::= { pm10010mptAlmlineNetworkLaneFaultEntry 16 }


pm10010mptAlmLineLaneApdPowerSupplyPortn OBJECT-TYPE
	SYNTAX  EkiOnOff
	MAX-ACCESS read-only
	STATUS current
	DESCRIPTION
        "
        Line Network Lane APD Power Supply
        :This OID indicates an APD Power
        supply failure on the Line Trscv
        Network Lane <Help> Alarm indicating
        an APD Power supply failure on
         the Line Trscv Network Lane <Condtype>
        LINE_LANE_APD_POWER_SUPPLY <Probcause>
        transmitterFailure (56) <Alarmtype>
        equipmentAlarm (5) <Polarity> (2)
        "
	::= { pm10010mptAlmlineNetworkLaneFaultEntry 15 }


pm10010mptAlmLineLaneTxLosfPortn OBJECT-TYPE
	SYNTAX  EkiOnOff
	MAX-ACCESS read-only
	STATUS current
	DESCRIPTION
        "
        Line Network Lane Tx Loss Of Signal
        Functionality :This OID indicates
        a Tx Loss of Signal Functionality
        on the Line Trscv Network Lane
         <Help> Alarm indicating a Tx Loss
        of Signal Functionality on the
         Line Trscv Network Lane <Condtype>
        LINE_LANE_TX_LOSF <Probcause> transmitterFailure
        (56) <Alarmtype> equipmentAlarm
        (5) <Polarity> (2)
        "
	::= { pm10010mptAlmlineNetworkLaneFaultEntry 9 }


pm10010mptAlmLineLaneTxLolPortn OBJECT-TYPE
	SYNTAX  EkiOnOff
	MAX-ACCESS read-only
	STATUS current
	DESCRIPTION
        "
        Line Network Lane Tx Loss Of Lock
        :This OID indicates a Tx Loss of
        Lock on the Line Trscv Network
         Lane <Help> Alarm indicating a
        Tx Loss of Lock on the Line Trscv
        Network Lane <Condtype> LINE_LANE_TX_LOL
        <Probcause> transmitterFailure
         (56) <Alarmtype> equipmentAlarm
        (5) <Polarity> (2)
        "
	::= { pm10010mptAlmlineNetworkLaneFaultEntry 8 }


pm10010mptAlmLineLaneRxLosPortn OBJECT-TYPE
	SYNTAX  EkiOnOff
	MAX-ACCESS read-only
	STATUS current
	DESCRIPTION
        "
        Line Network Lane Rx Loss Of Signal
        :This OID indicates a Rx Loss of
        Signal on the Line Trscv Network
        Lane <Help> Alarm indicating a
         Rx Loss of Signal on the Line
         Trscv Network Lane <Condtype>
         LINE_LANE_RX_LOS <Probcause> receiveFailure
        (41) <Alarmtype> physicalViolation
        (9) <Polarity> (2)
        "
	::= { pm10010mptAlmlineNetworkLaneFaultEntry 6 }


pm10010mptAlmLineLaneRxLolPortn OBJECT-TYPE
	SYNTAX  EkiOnOff
	MAX-ACCESS read-only
	STATUS current
	DESCRIPTION
        "
        Line Network Lane Rx Loss Of Lock
        :This OID indicates a Rx Loss of
        Lock on the Line Trscv Network
         Lane <Help> Alarm indicating a
        Rx Loss of Lock on the Line Trscv
        Network Lane <Condtype> LINE_LANE_RX_LOL
        <Probcause> receiverFailure (42)
        <Alarmtype> equipmentAlarm (5)
         <Polarity> (2)
        "
	::= { pm10010mptAlmlineNetworkLaneFaultEntry 5 }


pm10010mptAlmLineLaneRxFifoErrorPortn OBJECT-TYPE
	SYNTAX  EkiOnOff
	MAX-ACCESS read-only
	STATUS current
	DESCRIPTION
        "
        Line Network Lane Rx FIFO Error
        :This OID indicates a Rx FIFO Error
        on the Line Trscv Network Lane
         <Help> Alarm indicating a Rx FIFO
        Error on the Line Trscv Network
        Lane <Condtype> LINE_LANE_RX_FIFO_ERROR
        <Probcause> receiverFailure (42)
        <Alarmtype> equipmentAlarm (5)
         <Polarity> (2)
        "
	::= { pm10010mptAlmlineNetworkLaneFaultEntry 4 }


pm10010mptAlmLineLaneRxTecFaultPortn OBJECT-TYPE
	SYNTAX  EkiOnOff
	MAX-ACCESS read-only
	STATUS current
	DESCRIPTION
        "
        Line Network Lane Rx TEC Fault
        :This OID indicates a Rx TEC Fault
        on the Line Trscv Network Lane
         <Help> Alarm indicating a Rx TEC
        Fault on the Line Trscv Network
        Lane <Condtype> LINE_LANE_RX_TEC_FAULT
        <Probcause> receiverFailure (42)
        <Alarmtype> equipmentAlarm (5)
         <Polarity> (2)
        "
	::= { pm10010mptAlmlineNetworkLaneFaultEntry 3 }


--- *********************************************************
---     TABLE for the pm10010mptAlmlineHostLaneFault articles
--- *********************************************************

pm10010mptAlmlineHostLaneFaultTable OBJECT-TYPE
	SYNTAX  SEQUENCE OF Pm10010mptAlmlineHostLaneFaultEntry
	MAX-ACCESS not-accessible
	STATUS current
	DESCRIPTION
        "
        List of pm10010mptAlmlineHostLaneFault
        Article
        "
	::= { pm10010mptAlmLineUrg 152 }


pm10010mptAlmlineHostLaneFaultEntry OBJECT-TYPE
	SYNTAX Pm10010mptAlmlineHostLaneFaultEntry
	MAX-ACCESS not-accessible
	STATUS current
	DESCRIPTION
        "
        Row definition for the pm10010mptAlmlineHostLaneFault
        table
        "
	INDEX   { pm10010mptAlmlineHostLaneFaultIndex }
	::= { pm10010mptAlmlineHostLaneFaultTable 1 }


Pm10010mptAlmlineHostLaneFaultEntry ::=
	SEQUENCE {
	pm10010mptAlmlineHostLaneFaultIndex
		INTEGER,
	pm10010mptAlmLineTrxOverTempPortn
		EkiOnOff,
	pm10010mptAlmLinePowerDegradePortn
		EkiOnOff,
	pm10010mptAlmLineLaneTxFifoErrorPortn
		EkiOnOff,
	pm10010mptAlmLineTxHostLolPortn
		EkiOnOff,
	pm10010mptAlmLineSmIaeDetectedPortn
		EkiOnOff,
	pm10010mptAlmLineSmIaeInsertedPortn
		EkiOnOff,
	pm10010mptAlmLineSmBdiDetectedPortn
		EkiOnOff,
	pm10010mptAlmLineSmBdiInsertedPortn
		EkiOnOff,
	pm10010mptAlmLineLossOfFramePortn
		EkiOnOff,
	pm10010mptAlmLineInputLossOfSignalPortn
		EkiOnOff
	}


pm10010mptAlmlineHostLaneFaultIndex OBJECT-TYPE
	SYNTAX  INTEGER(0..128)
	MAX-ACCESS  read-only
	STATUS current
	DESCRIPTION
        "
        Index definition for the pm10010mptAlmlineHostLaneFault
        table
        "
	::= { pm10010mptAlmlineHostLaneFaultEntry 1 }


pm10010mptAlmLineTrxOverTempPortn OBJECT-TYPE
	SYNTAX  EkiOnOff
	MAX-ACCESS read-only
	STATUS current
	DESCRIPTION
        "
        Temperature Critical Level :This
        OID indicates the module temperature
        is too high triggering the power
        down protection mechanism <Help>
        This alarm indicates the module
        temperature is too high triggering
        the power down protection mechanism
        <Condtype> LINE_TRX_OVER_TEMP <Probcause>
        temperatureUnacceptable (51) <Alarmtype>
        equipmentAlarm (5) <Polarity> (2)
        "
	::= { pm10010mptAlmlineHostLaneFaultEntry 17 }


pm10010mptAlmLinePowerDegradePortn OBJECT-TYPE
	SYNTAX  EkiOnOff
	MAX-ACCESS read-only
	STATUS current
	DESCRIPTION
        "
        3V3 Power Degrade :This OID indicates
        the 3V3 power converter was in
         failure<Help> This alarm indicates
        the 3V3 power converter was in
         failure <Condtype> LINE_POWER_DEGRADE
        <Probcause> powerProblem (36) <Alarmtype>
        equipmentAlarm (5) <Polarity> (2)
        "
	::= { pm10010mptAlmlineHostLaneFaultEntry 16 }


pm10010mptAlmLineLaneTxFifoErrorPortn OBJECT-TYPE
	SYNTAX  EkiOnOff
	MAX-ACCESS read-only
	STATUS current
	DESCRIPTION
        "
        Line Host Lane Tx FIFO Error :This
        OID indicates a Tx FIFO Error on
        the Line Trscv Host Lane <Help>
        Alarm indicating a Tx FIFO Error
        on the Line Trscv Host Lane <Condtype>
        LINE_LANE_TX_FIFO_ERROR <Probcause>
        receiverFailure (42) <Alarmtype>
        equipmentAlarm (5) <Polarity> (2)
        "
	::= { pm10010mptAlmlineHostLaneFaultEntry 11 }


pm10010mptAlmLineTxHostLolPortn OBJECT-TYPE
	SYNTAX  EkiOnOff
	MAX-ACCESS read-only
	STATUS current
	DESCRIPTION
        "
        Line Host Lane Tx Loss Of Lock
        :This OID indicates a Tx Loss of
        Lock on the Line Trscv Host Lane
        <Help> Alarm indicating a Tx Loss
        of Lock on the Line Trscv Host
         Lane <Condtype> LINE_TX_HOST_LOL
        <Probcause> receiverFailure (42)
        <Alarmtype> equipmentAlarm (5)
         <Polarity> (2)
        "
	::= { pm10010mptAlmlineHostLaneFaultEntry 10 }


pm10010mptAlmLineSmIaeDetectedPortn OBJECT-TYPE
	SYNTAX  EkiOnOff
	MAX-ACCESS read-only
	STATUS current
	DESCRIPTION
        "
        Line SM IAE Detected :This OID
        indicates a SM Incoming Alignment
        Error is detected on the incoming
        Line signal <Help> Alarm indicating
        a SM Incoming Alignment Error is
        detected on the incoming Line signal
        <Condtype> LINE_SM_IAE_DETECTED
        <Probcause> receiveFailure (41)
        <Alarmtype> integrityViolation
         (7) <Polarity> (2)
        "
	::= { pm10010mptAlmlineHostLaneFaultEntry 7 }


pm10010mptAlmLineSmIaeInsertedPortn OBJECT-TYPE
	SYNTAX  EkiOnOff
	MAX-ACCESS read-only
	STATUS current
	DESCRIPTION
        "
        Line SM IAE Inserted :This OID
        indicates a SM Incoming Alignment
        Error is inserted on the outgoing
        Line signal <Help> Status indicating
        a SM Incoming Alignment Error is
        inserted on the outgoing Line signal
        <Condtype> LINE_SM_IAE_INSERTED
        <Probcause> informationalStatus(1000)
        <Alarmtype> other (1) <Polarity>
        (2)
        "
	::= { pm10010mptAlmlineHostLaneFaultEntry 6 }


pm10010mptAlmLineSmBdiDetectedPortn OBJECT-TYPE
	SYNTAX  EkiOnOff
	MAX-ACCESS read-only
	STATUS current
	DESCRIPTION
        "
        Line SM BDI Detected :This OID
        indicates a SM Backward Defect
         Indication is detected on the
         incoming Line signal <Help> Alarm
        indicating a SM Backward Defect
        Indication is detected on the incoming
        Line signal <Condtype> LINE_SM_BDI_DETECTED
        <Probcause> receiveFailure (41)
        <Alarmtype> integrityViolation
         (7) <Polarity> (2)
        "
	::= { pm10010mptAlmlineHostLaneFaultEntry 5 }


pm10010mptAlmLineSmBdiInsertedPortn OBJECT-TYPE
	SYNTAX  EkiOnOff
	MAX-ACCESS read-only
	STATUS current
	DESCRIPTION
        "
        Line SM BDI Inserted :This OID
        indicates a SM Backward Defect
         Indication is inserted on the
         outgoing Line signal <Help> Status
        indicating a SM Backward Defect
        Indication is inserted on the outgoing
        Line signal <Condtype> LINE_SM_BDI_INSERTED
        <Probcause> informationalStatus(1000)
        <Alarmtype> other (1) <Polarity>
        (2)
        "
	::= { pm10010mptAlmlineHostLaneFaultEntry 4 }


pm10010mptAlmLineLossOfFramePortn OBJECT-TYPE
	SYNTAX  EkiOnOff
	MAX-ACCESS read-only
	STATUS current
	DESCRIPTION
        "
        Line Loss Of Frame :This OID indicates
        the module is not aligned with
         the incoming Line signal <Help>
        Alarm indicating the module is
         not aligned with the incoming
         Line signal <Condtype> LINE_LOSS_OF_FRAME
        <Probcause> receiveFailure (41)
        <Alarmtype> integrityViolation
         (7) <Polarity> (2)
        "
	::= { pm10010mptAlmlineHostLaneFaultEntry 3 }


pm10010mptAlmLineInputLossOfSignalPortn OBJECT-TYPE
	SYNTAX  EkiOnOff
	MAX-ACCESS read-only
	STATUS current
	DESCRIPTION
        "
        Line Input Loss Of Signal :This
        OID indicates a Loss of Signal
         is detected on the Line Trscv
         <Help> Alarm indicating a Loss
        of Signal is detected on the Line
        Trscv <Condtype> LINE_INPUT_LOSS_OF_SIGNAL
        <Probcause> receiveFailure (41)
        <Alarmtype> physicalViolation (9)
        <Polarity> (2)
        "
	::= { pm10010mptAlmlineHostLaneFaultEntry 2 }


--- *********************************************************
---     TABLE for the pm10010mptAlmlineNetworkLaneRxOtn articles
--- *********************************************************

pm10010mptAlmlineNetworkLaneRxOtnTable OBJECT-TYPE
	SYNTAX  SEQUENCE OF Pm10010mptAlmlineNetworkLaneRxOtnEntry
	MAX-ACCESS not-accessible
	STATUS current
	DESCRIPTION
        "
        List of pm10010mptAlmlineNetworkLaneRxOtn
        Article
        "
	::= { pm10010mptAlmLineUrg 168 }


pm10010mptAlmlineNetworkLaneRxOtnEntry OBJECT-TYPE
	SYNTAX Pm10010mptAlmlineNetworkLaneRxOtnEntry
	MAX-ACCESS not-accessible
	STATUS current
	DESCRIPTION
        "
        Row definition for the pm10010mptAlmlineNetworkLaneRxOtn
        table
        "
	INDEX   { pm10010mptAlmlineNetworkLaneRxOtnIndex }
	::= { pm10010mptAlmlineNetworkLaneRxOtnTable 1 }


Pm10010mptAlmlineNetworkLaneRxOtnEntry ::=
	SEQUENCE {
	pm10010mptAlmlineNetworkLaneRxOtnIndex
		INTEGER,
	pm10010mptAlmLineRxOtnLofPortn
		EkiOnOff,
	pm10010mptAlmLineRxOtnOofPortn
		EkiOnOff,
	pm10010mptAlmLineRxOtnLomPortn
		EkiOnOff,
	pm10010mptAlmLineRxOtnOomPortn
		EkiOnOff,
	pm10010mptAlmLineRxOtnIaePortn
		EkiOnOff,
	pm10010mptAlmLineRxSmBdiPortn
		EkiOnOff,
	pm10010mptAlmLineRxOtnOtuAisPortn
		EkiOnOff,
	pm10010mptAlmLineRxOtnOduAisPortn
		EkiOnOff
	}


pm10010mptAlmlineNetworkLaneRxOtnIndex OBJECT-TYPE
	SYNTAX  INTEGER(0..128)
	MAX-ACCESS  read-only
	STATUS current
	DESCRIPTION
        "
        Index definition for the pm10010mptAlmlineNetworkLaneRxOtn
        table
        "
	::= { pm10010mptAlmlineNetworkLaneRxOtnEntry 1 }


pm10010mptAlmLineRxOtnLofPortn OBJECT-TYPE
	SYNTAX  EkiOnOff
	MAX-ACCESS read-only
	STATUS current
	DESCRIPTION
        "
        Line Network Rx LOF :This OID
         indicates a Loss of Frame is detected
        on the Rx Network interface of
         the Line Trscv <Help> Alarm indicating
        a Loss of Frame is detected on
         the Rx Network interface of the
        Line Trscv <Condtype> LINE_RX_OTN_LOF
        <Probcause> receiveFailure (41)
        <Alarmtype> equipmentAlarm (5)
         <Polarity> (2)
        "
	::= { pm10010mptAlmlineNetworkLaneRxOtnEntry 17 }


pm10010mptAlmLineRxOtnOofPortn OBJECT-TYPE
	SYNTAX  EkiOnOff
	MAX-ACCESS read-only
	STATUS current
	DESCRIPTION
        "
        Line Network Rx OOF :This OID
         indicates an Out of Frame is detected
        on the Rx Network interface of
         the Line Trscv <Help> Alarm indicating
        an Out of Frame is detected on
         the Rx Network interface of the
        Line Trscv <Condtype> LINE_RX_OTN_OOF
        <Probcause> receiveFailure (41)
        <Alarmtype> equipmentAlarm (5)
         <Polarity> (2)
        "
	::= { pm10010mptAlmlineNetworkLaneRxOtnEntry 16 }


pm10010mptAlmLineRxOtnLomPortn OBJECT-TYPE
	SYNTAX  EkiOnOff
	MAX-ACCESS read-only
	STATUS current
	DESCRIPTION
        "
        Line Network Rx LOM :This OID
         indicates a Loss of Multiframe
        is detected on the Rx Network interface
        of the Line Trscv <Help> Alarm
         indicating a Loss of Multiframe
        is detected on the Rx Network interface
        of the Line Trscv <Condtype> LINE_RX_OTN_LOM
        <Probcause> receiveFailure (41)
        <Alarmtype> equipmentAlarm (5)
         <Polarity> (2)
        "
	::= { pm10010mptAlmlineNetworkLaneRxOtnEntry 15 }


pm10010mptAlmLineRxOtnOomPortn OBJECT-TYPE
	SYNTAX  EkiOnOff
	MAX-ACCESS read-only
	STATUS current
	DESCRIPTION
        "
        Line Network Rx OOM :This OID
         indicates an Out of Multiframe
        is detected on the Rx Network interface
        of the Line Trscv <Help> Alarm
         indicating an Out of Multiframe
        is detected on the Rx Network interface
        of the Line Trscv <Condtype> LINE_RX_OTN_OOM
        <Probcause> receiveFailure (41)
        <Alarmtype> equipmentAlarm (5)
         <Polarity> (2)
        "
	::= { pm10010mptAlmlineNetworkLaneRxOtnEntry 14 }


pm10010mptAlmLineRxOtnIaePortn OBJECT-TYPE
	SYNTAX  EkiOnOff
	MAX-ACCESS read-only
	STATUS current
	DESCRIPTION
        "
        Line Network Rx IAE :This OID
         indicates an Incoming Alignment
        Error is detected on the Rx Network
        interface of the Line Trscv <Help>
        Alarm indicating an Incoming Alignment
        Error is detected on the Rx Network
        interface of the Line Trscv <Condtype>
        LINE_RX_OTN_IAE <Probcause> receiveFailure
        (41) <Alarmtype> equipmentAlarm
        (5) <Polarity> (2)
        "
	::= { pm10010mptAlmlineNetworkLaneRxOtnEntry 13 }


pm10010mptAlmLineRxSmBdiPortn OBJECT-TYPE
	SYNTAX  EkiOnOff
	MAX-ACCESS read-only
	STATUS current
	DESCRIPTION
        "
        Line Network Rx SM BDI :This OID
        indicates an SM Backward Defect
        Indication is detected on the Rx
        Network interface of the Line Trscv
        <Help> Alarm indicating an SM Backward
        Defect Indication is detected on
        the Rx Network interface of the
        Line Trscv <Condtype> LINE_RX_SM_BDI
        <Probcause> informationalStatus(1000)
        <Alarmtype> other (1) <Polarity>
        (2)
        "
	::= { pm10010mptAlmlineNetworkLaneRxOtnEntry 12 }


pm10010mptAlmLineRxOtnOtuAisPortn OBJECT-TYPE
	SYNTAX  EkiOnOff
	MAX-ACCESS read-only
	STATUS current
	DESCRIPTION
        "
        Line Network Rx OTU AIS :This
         OID indicates an OTU This OID
         Indication Signal is detected
         on the Rx Network interface of
        the Line Trscv <Help> Alarm indicating
        an OTU Alarm Indication Signal
         is detected on the Rx Network
         interface of the Line Trscv <Condtype>
        LINE_RX_OTN_OTU_AIS <Probcause>
        receiveFailure (41) <Alarmtype>
        equipmentAlarm (5) <Polarity> (2)
        "
	::= { pm10010mptAlmlineNetworkLaneRxOtnEntry 11 }


pm10010mptAlmLineRxOtnOduAisPortn OBJECT-TYPE
	SYNTAX  EkiOnOff
	MAX-ACCESS read-only
	STATUS current
	DESCRIPTION
        "
        Line Network Rx ODU AIS :This
         OID indicates an ODU This OID
         Indication Signal is detected
         on the Rx Network interface of
        the Line Trscv <Help> Alarm indicating
        an ODU Alarm Indication Signal
         is detected on the Rx Network
         interface of the Line Trscv <Condtype>
        LINE_RX_OTN_ODU_AIS <Probcause>
        receiveFailure (41) <Alarmtype>
        equipmentAlarm (5) <Polarity> (2)
        "
	::= { pm10010mptAlmlineNetworkLaneRxOtnEntry 10 }


--- *********************************************************
---     TABLE for the pm10010mptAlmlineHostLaneTxOtn articles
--- *********************************************************

pm10010mptAlmlineHostLaneTxOtnTable OBJECT-TYPE
	SYNTAX  SEQUENCE OF Pm10010mptAlmlineHostLaneTxOtnEntry
	MAX-ACCESS not-accessible
	STATUS current
	DESCRIPTION
        "
        List of pm10010mptAlmlineHostLaneTxOtn
        Article
        "
	::= { pm10010mptAlmLineUrg 184 }


pm10010mptAlmlineHostLaneTxOtnEntry OBJECT-TYPE
	SYNTAX Pm10010mptAlmlineHostLaneTxOtnEntry
	MAX-ACCESS not-accessible
	STATUS current
	DESCRIPTION
        "
        Row definition for the pm10010mptAlmlineHostLaneTxOtn
        table
        "
	INDEX   { pm10010mptAlmlineHostLaneTxOtnIndex }
	::= { pm10010mptAlmlineHostLaneTxOtnTable 1 }


Pm10010mptAlmlineHostLaneTxOtnEntry ::=
	SEQUENCE {
	pm10010mptAlmlineHostLaneTxOtnIndex
		INTEGER,
	pm10010mptAlmLineTxOtnLofPortn
		EkiOnOff,
	pm10010mptAlmLineTxOtnOofPortn
		EkiOnOff,
	pm10010mptAlmLineTxOtnLomPortn
		EkiOnOff,
	pm10010mptAlmLineTxOtnOomPortn
		EkiOnOff,
	pm10010mptAlmLineTxOtnIaePortn
		EkiOnOff,
	pm10010mptAlmLineTxSmBdiPortn
		EkiOnOff,
	pm10010mptAlmLineTxOtnOtuAisPortn
		EkiOnOff,
	pm10010mptAlmLineTxOtnOduAisPortn
		EkiOnOff
	}


pm10010mptAlmlineHostLaneTxOtnIndex OBJECT-TYPE
	SYNTAX  INTEGER(0..128)
	MAX-ACCESS  read-only
	STATUS current
	DESCRIPTION
        "
        Index definition for the pm10010mptAlmlineHostLaneTxOtn
        table
        "
	::= { pm10010mptAlmlineHostLaneTxOtnEntry 1 }


pm10010mptAlmLineTxOtnLofPortn OBJECT-TYPE
	SYNTAX  EkiOnOff
	MAX-ACCESS read-only
	STATUS current
	DESCRIPTION
        "
        Line Host Tx LOF :This OID indicates
        a Loss of Frame is detected on
         the Tx Host interface of the Line
        Trscv <Help> Alarm indicating a
        Loss of Frame is detected on the
        Tx Host interface of the Line Trscv
        <Condtype> LINE_TX_OTN_LOF <Probcause>
        receiveFailure (41) <Alarmtype>
        equipmentAlarm (5) <Polarity> (2)
        "
	::= { pm10010mptAlmlineHostLaneTxOtnEntry 17 }


pm10010mptAlmLineTxOtnOofPortn OBJECT-TYPE
	SYNTAX  EkiOnOff
	MAX-ACCESS read-only
	STATUS current
	DESCRIPTION
        "
        Line Host Tx OOF :This OID indicates
        an Out of Frame is detected on
         the Tx Host interface of the Line
        Trscv <Help> Alarm indicating an
        Out of Frame is detected on the
        Tx Host interface of the Line Trscv
        <Condtype> LINE_TX_OTN_OOF <Probcause>
        receiveFailure (41) <Alarmtype>
        equipmentAlarm (5) <Polarity> (2)
        "
	::= { pm10010mptAlmlineHostLaneTxOtnEntry 16 }


pm10010mptAlmLineTxOtnLomPortn OBJECT-TYPE
	SYNTAX  EkiOnOff
	MAX-ACCESS read-only
	STATUS current
	DESCRIPTION
        "
        Line Host Tx LOM :This OID indicates
        a Loss of Multiframe is detected
        on the Tx Host interface of the
        Line Trscv <Help> Alarm indicating
        a Loss of Multiframe is detected
        on the Tx Host interface of the
        Line Trscv <Condtype> LINE_TX_OTN_LOM
        <Probcause> receiveFailure (41)
        <Alarmtype> equipmentAlarm (5)
         <Polarity> (2)
        "
	::= { pm10010mptAlmlineHostLaneTxOtnEntry 15 }


pm10010mptAlmLineTxOtnOomPortn OBJECT-TYPE
	SYNTAX  EkiOnOff
	MAX-ACCESS read-only
	STATUS current
	DESCRIPTION
        "
        Line Host Tx OOM :This OID indicates
        an Out of Multiframe is detected
        on the Tx Host interface of the
        Line Trscv <Help> Alarm indicating
        an Out of Multiframe is detected
        on the Tx Host interface of the
        Line Trscv <Condtype> LINE_TX_OTN_OOM
        <Probcause> receiveFailure (41)
        <Alarmtype> equipmentAlarm (5)
         <Polarity> (2)
        "
	::= { pm10010mptAlmlineHostLaneTxOtnEntry 14 }


pm10010mptAlmLineTxOtnIaePortn OBJECT-TYPE
	SYNTAX  EkiOnOff
	MAX-ACCESS read-only
	STATUS current
	DESCRIPTION
        "
        Line Host Tx IAE :This OID indicates
        an Incoming Alignment Error is
         detected on the Tx Host interface
        of the Line Trscv <Help> Alarm
         indicating an Incoming Alignment
        Error is detected on the Tx Host
        interface of the Line Trscv <Condtype>
        LINE_TX_OTN_IAE <Probcause> receiveFailure
        (41) <Alarmtype> equipmentAlarm
        (5) <Polarity> (2)
        "
	::= { pm10010mptAlmlineHostLaneTxOtnEntry 13 }


pm10010mptAlmLineTxSmBdiPortn OBJECT-TYPE
	SYNTAX  EkiOnOff
	MAX-ACCESS read-only
	STATUS current
	DESCRIPTION
        "
        Line Host Tx SM BDI :This OID
         indicates an SM Backward Defect
        Indication is detected on the Tx
        Host interface of the Line Trscv
        <Help> Alarm indicating an SM Backward
        Defect Indication is detected on
        the Tx Host interface of the Line
        Trscv <Condtype> LINE_TX_SM_BDI
        <Probcause> informationalStatus(1000)
        <Alarmtype> other (1) <Polarity>
        (2)
        "
	::= { pm10010mptAlmlineHostLaneTxOtnEntry 12 }


pm10010mptAlmLineTxOtnOtuAisPortn OBJECT-TYPE
	SYNTAX  EkiOnOff
	MAX-ACCESS read-only
	STATUS current
	DESCRIPTION
        "
        Line Host Tx OTU AIS :This OID
        indicates an OTU This OID Indication
        Signal is detected on the Tx Host
        interface of the Line Trscv <Help>
        Alarm indicating an OTU Alarm Indication
        Signal is detected on the Tx Host
        interface of the Line Trscv <Condtype>
        LINE_TX_OTN_OTU_AIS <Probcause>
        receiveFailure (41) <Alarmtype>
        equipmentAlarm (5) <Polarity> (2)
        "
	::= { pm10010mptAlmlineHostLaneTxOtnEntry 11 }


pm10010mptAlmLineTxOtnOduAisPortn OBJECT-TYPE
	SYNTAX  EkiOnOff
	MAX-ACCESS read-only
	STATUS current
	DESCRIPTION
        "
        Line Host Tx ODU AIS :This OID
        indicates an ODU This OID Indication
        Signal is detected on the Tx Host
        interface of the Line Trscv <Help>
        Alarm indicating an ODU Alarm Indication
        Signal is detected on the Tx Host
        interface of the Line Trscv <Condtype>
        LINE_TX_OTN_ODU_AIS <Probcause>
        receiveFailure (41) <Alarmtype>
        equipmentAlarm (5) <Polarity> (2)
        "
	::= { pm10010mptAlmlineHostLaneTxOtnEntry 10 }


--- *********************************************************
---     TABLE for the pm10010mptAlmclientSfpAlmDdm articles
--- *********************************************************

pm10010mptAlmclientSfpAlmDdmTable OBJECT-TYPE
	SYNTAX  SEQUENCE OF Pm10010mptAlmclientSfpAlmDdmEntry
	MAX-ACCESS not-accessible
	STATUS current
	DESCRIPTION
        "
        List of pm10010mptAlmclientSfpAlmDdm
        Article
        "
	::= { pm10010mptAlmClientUrg 216 }


pm10010mptAlmclientSfpAlmDdmEntry OBJECT-TYPE
	SYNTAX Pm10010mptAlmclientSfpAlmDdmEntry
	MAX-ACCESS not-accessible
	STATUS current
	DESCRIPTION
        "
        Row definition for the pm10010mptAlmclientSfpAlmDdm
        table
        "
	INDEX   { pm10010mptAlmclientSfpAlmDdmIndex }
	::= { pm10010mptAlmclientSfpAlmDdmTable 1 }


Pm10010mptAlmclientSfpAlmDdmEntry ::=
	SEQUENCE {
	pm10010mptAlmclientSfpAlmDdmIndex
		INTEGER,
	pm10010mptAlmRxPwrHighAlaPortn
		EkiOnOff,
	pm10010mptAlmRxPwrLowAlaPortn
		EkiOnOff,
	pm10010mptAlmTempHighAlaPortn
		EkiOnOff,
	pm10010mptAlmTempLowAlaPortn
		EkiOnOff,
	pm10010mptAlmVccHighAlaPortn
		EkiOnOff,
	pm10010mptAlmVccLowAlaPortn
		EkiOnOff,
	pm10010mptAlmTxBiasHighAlaPortn
		EkiOnOff,
	pm10010mptAlmTxBiasLowAlaPortn
		EkiOnOff,
	pm10010mptAlmTxPwrHighAlaPortn
		EkiOnOff,
	pm10010mptAlmTxPwrLowAlaPortn
		EkiOnOff
	}


pm10010mptAlmclientSfpAlmDdmIndex OBJECT-TYPE
	SYNTAX  INTEGER(0..128)
	MAX-ACCESS  read-only
	STATUS current
	DESCRIPTION
        "
        Index definition for the pm10010mptAlmclientSfpAlmDdm
        table
        "
	::= { pm10010mptAlmclientSfpAlmDdmEntry 1 }


pm10010mptAlmRxPwrHighAlaPortn OBJECT-TYPE
	SYNTAX  EkiOnOff
	MAX-ACCESS read-only
	STATUS current
	DESCRIPTION
        "
        Client Trscv Rx Power High :This
        OID indicates that the Trscv input
        power of port is higher than the
        threshold value written in the
         Trscv EEPROM <Help> Alarm indicating
        that the Trscv input power of port
        is higher than the threshold value
        written in the Trscv EEPROM <Condtype>
        RX_PWR_HIGH_ALA_1 <Probcause> receiveFailure
        (41) <Alarmtype> equipmentAlarm
        (5) <Polarity> (2)
        "
	::= { pm10010mptAlmclientSfpAlmDdmEntry 17 }


pm10010mptAlmRxPwrLowAlaPortn OBJECT-TYPE
	SYNTAX  EkiOnOff
	MAX-ACCESS read-only
	STATUS current
	DESCRIPTION
        "
        Client Trscv Rx Power Low :This
        OID indicates that the Trscv input
        power of port is lower than the
        threshold value written in the
         Trscv EEPROM <Help> Alarm indicating
        that the Trscv input power of port
        is lower than the threshold value
        written in the Trscv EEPROM <Condtype>
        RX_PWR_LOW_ALA_1 <Probcause> receiveFailure
        (41) <Alarmtype> equipmentAlarm
        (5) <Polarity> (2)
        "
	::= { pm10010mptAlmclientSfpAlmDdmEntry 16 }


pm10010mptAlmTempHighAlaPortn OBJECT-TYPE
	SYNTAX  EkiOnOff
	MAX-ACCESS read-only
	STATUS current
	DESCRIPTION
        "
        Client Trscv Temp High :This OID
        indicates that the Trscv temperature
        of port is higher than the threshold
        value written in the Trscv EEPROM
        <Help> Alarm indicating that the
        Trscv temperature of port is higher
        than the threshold value written
        in the Trscv EEPROM <Condtype>
         TEMP_HIGH_ALA_1 <Probcause> temperatureUnacceptable
        (51) <Alarmtype> equipmentAlarm
        (5) <Polarity> (2)
        "
	::= { pm10010mptAlmclientSfpAlmDdmEntry 9 }


pm10010mptAlmTempLowAlaPortn OBJECT-TYPE
	SYNTAX  EkiOnOff
	MAX-ACCESS read-only
	STATUS current
	DESCRIPTION
        "
        Client Trscv Temp Low :This OID
        indicates that the Trscv temperature
        of port is lower than the threshold
        value written in the Trscv EEPROM
        <Help> Alarm indicating that the
        Trscv temperature of port is lower
        than the threshold value written
        in the Trscv EEPROM <Condtype>
         TEMP_LOW_ALA_1 <Probcause> temperatureUnacceptable
        (51) <Alarmtype> equipmentAlarm
        (5) <Polarity> (2)
        "
	::= { pm10010mptAlmclientSfpAlmDdmEntry 8 }


pm10010mptAlmVccHighAlaPortn OBJECT-TYPE
	SYNTAX  EkiOnOff
	MAX-ACCESS read-only
	STATUS current
	DESCRIPTION
        "
        Client Trscv Power Supply High
        :This OID indicates that the Trscv
        power supply of port is higher
         than the threshold value written
        in the Trscv EEPROM <Help> Alarm
        indicating that the Trscv power
        supply of port is higher than the
        threshold value written in the
         Trscv EEPROM <Condtype> VCC_HIGH_ALA_1
        <Probcause> powerProblem (36) <Alarmtype>
        equipmentAlarm (5) <Polarity> (2)
        "
	::= { pm10010mptAlmclientSfpAlmDdmEntry 7 }


pm10010mptAlmVccLowAlaPortn OBJECT-TYPE
	SYNTAX  EkiOnOff
	MAX-ACCESS read-only
	STATUS current
	DESCRIPTION
        "
        Client Trscv Power Supply Low
         :This OID indicates that the Trscv
        power supply of port is lower than
        the threshold value written in
         the Trscv EEPROM <Help> Alarm
         indicating that the Trscv power
        supply of port is lower than the
        threshold value written in the
         Trscv EEPROM <Condtype> VCC_LOW_ALA_1
        <Probcause> powerProblem (36) <Alarmtype>
        equipmentAlarm (5) <Polarity> (2)
        "
	::= { pm10010mptAlmclientSfpAlmDdmEntry 6 }


pm10010mptAlmTxBiasHighAlaPortn OBJECT-TYPE
	SYNTAX  EkiOnOff
	MAX-ACCESS read-only
	STATUS current
	DESCRIPTION
        "
        Client Trscv Bias High :This OID
        indicates that the Trscv laser
         bias current of port is higher
        than the threshold value written
        in the Trscv EEPROM <Help> Alarm
        indicating that the Trscv laser
        bias current of port is higher
         than the threshold value written
        in the Trscv EEPROM <Condtype>
         TX_BIAS_HIGH_ALA_1 <Probcause>
        transmitterFailure (56) <Alarmtype>
        equipmentAlarm (5) <Polarity> (2)
        "
	::= { pm10010mptAlmclientSfpAlmDdmEntry 5 }


pm10010mptAlmTxBiasLowAlaPortn OBJECT-TYPE
	SYNTAX  EkiOnOff
	MAX-ACCESS read-only
	STATUS current
	DESCRIPTION
        "
        Client Trscv Bias Low :This OID
        indicates that the Trscv laser
         bias current of port is lower
         than the threshold value written
        in the Trscv EEPROM <Help> Alarm
        indicating that the Trscv laser
        bias current of port is lower than
        the threshold value written in
         the Trscv EEPROM <Condtype> TX_BIAS_LOW_ALA_1
        <Probcause> transmitterFailure
         (56) <Alarmtype> equipmentAlarm
        (5) <Polarity> (2)
        "
	::= { pm10010mptAlmclientSfpAlmDdmEntry 4 }


pm10010mptAlmTxPwrHighAlaPortn OBJECT-TYPE
	SYNTAX  EkiOnOff
	MAX-ACCESS read-only
	STATUS current
	DESCRIPTION
        "
        Client Trscv Tx Power High :This
        OID indicates that the Trscv output
        power of port is higher than the
        threshold value written in the
         Trscv EEPROM <Help> Alarm indicating
        that the Trscv output power of
         port is higher than the threshold
        value written in the Trscv EEPROM
        <Condtype> TX_PWR_HIGH_ALA_1 <Probcause>
        transmitterFailure (56) <Alarmtype>
        equipmentAlarm (5) <Polarity> (2)
        "
	::= { pm10010mptAlmclientSfpAlmDdmEntry 3 }


pm10010mptAlmTxPwrLowAlaPortn OBJECT-TYPE
	SYNTAX  EkiOnOff
	MAX-ACCESS read-only
	STATUS current
	DESCRIPTION
        "
        Client Trscv Tx Power Low :This
        OID indicates that the Trscv output
        power of port is lower than the
        threshold value written in the
         Trscv EEPROM <Help> Alarm indicating
        that the Trscv output power of
         port is lower than the threshold
        value written in the Trscv EEPROM
        <Condtype> TX_PWR_LOW_ALA_1 <Probcause>
        transmitterFailure (56) <Alarmtype>
        equipmentAlarm (5) <Polarity> (2)
        "
	::= { pm10010mptAlmclientSfpAlmDdmEntry 2 }


--- *********************************************************
---     TABLE for the pm10010mptAlmclientSfpWarnDdm articles
--- *********************************************************

pm10010mptAlmclientSfpWarnDdmTable OBJECT-TYPE
	SYNTAX  SEQUENCE OF Pm10010mptAlmclientSfpWarnDdmEntry
	MAX-ACCESS not-accessible
	STATUS current
	DESCRIPTION
        "
        List of pm10010mptAlmclientSfpWarnDdm
        Article
        "
	::= { pm10010mptAlmClientNurg 232 }


pm10010mptAlmclientSfpWarnDdmEntry OBJECT-TYPE
	SYNTAX Pm10010mptAlmclientSfpWarnDdmEntry
	MAX-ACCESS not-accessible
	STATUS current
	DESCRIPTION
        "
        Row definition for the pm10010mptAlmclientSfpWarnDdm
        table
        "
	INDEX   { pm10010mptAlmclientSfpWarnDdmIndex }
	::= { pm10010mptAlmclientSfpWarnDdmTable 1 }


Pm10010mptAlmclientSfpWarnDdmEntry ::=
	SEQUENCE {
	pm10010mptAlmclientSfpWarnDdmIndex
		INTEGER,
	pm10010mptAlmRxPwrHighWngPortn
		EkiOnOff,
	pm10010mptAlmRxPwrLowWngPortn
		EkiOnOff,
	pm10010mptAlmTempHighWngPortn
		EkiOnOff,
	pm10010mptAlmTempLowWngPortn
		EkiOnOff,
	pm10010mptAlmVccHighWngPortn
		EkiOnOff,
	pm10010mptAlmVccLowWngPortn
		EkiOnOff,
	pm10010mptAlmTxBiasHighWngPortn
		EkiOnOff,
	pm10010mptAlmTxBiasLowWngPortn
		EkiOnOff,
	pm10010mptAlmTxPwrHighWngPortn
		EkiOnOff,
	pm10010mptAlmTxPwLowWngPortn
		EkiOnOff
	}


pm10010mptAlmclientSfpWarnDdmIndex OBJECT-TYPE
	SYNTAX  INTEGER(0..128)
	MAX-ACCESS  read-only
	STATUS current
	DESCRIPTION
        "
        Index definition for the pm10010mptAlmclientSfpWarnDdm
        table
        "
	::= { pm10010mptAlmclientSfpWarnDdmEntry 1 }


pm10010mptAlmRxPwrHighWngPortn OBJECT-TYPE
	SYNTAX  EkiOnOff
	MAX-ACCESS read-only
	STATUS current
	DESCRIPTION
        "
        Client Trscv Rx Power High Warning
        :This OID indicates that the Trscv
        input power is higher than the
         threshold value written in the
        Trscv EEPROM <Help> Warning indicating
        that the Trscv input power is higher
        than the threshold value written
        in the Trscv EEPROM <Condtype>
         RX_PWR_HIGH_WNG_1 <Probcause>
         receiveFailure (41) <Alarmtype>
        equipmentAlarm (5) <Polarity> (2)
        "
	::= { pm10010mptAlmclientSfpWarnDdmEntry 17 }


pm10010mptAlmRxPwrLowWngPortn OBJECT-TYPE
	SYNTAX  EkiOnOff
	MAX-ACCESS read-only
	STATUS current
	DESCRIPTION
        "
        Client Trscv Rx Power Low Warning
        :This OID indicates that the Trscv
        input power is lower than the threshold
        value written in the Trscv EEPROM
        <Help> Warning indicating that
         the Trscv input power is lower
        than the threshold value written
        in the Trscv EEPROM <Condtype>
         RX_PWR_LOW_WNG_1 <Probcause> receiveFailure
        (41) <Alarmtype> equipmentAlarm
        (5) <Polarity> (2)
        "
	::= { pm10010mptAlmclientSfpWarnDdmEntry 16 }


pm10010mptAlmTempHighWngPortn OBJECT-TYPE
	SYNTAX  EkiOnOff
	MAX-ACCESS read-only
	STATUS current
	DESCRIPTION
        "
        Client Trscv Temp High Warning
        :This OID indicates that the Trscv
        temperature is higher than the
         threshold value written in the
        Trscv EEPROM <Help> Warning indicating
        that the Trscv temperature is higher
        than the threshold value written
        in the Trscv EEPROM <Condtype>
         TEMP_HIGH_WNG_1 <Probcause> temperatureUnacceptable
        (51) <Alarmtype> equipmentAlarm
        (5) <Polarity> (2)
        "
	::= { pm10010mptAlmclientSfpWarnDdmEntry 9 }


pm10010mptAlmTempLowWngPortn OBJECT-TYPE
	SYNTAX  EkiOnOff
	MAX-ACCESS read-only
	STATUS current
	DESCRIPTION
        "
        Client Trscv Temp Low Warning
         :This OID indicates that the Trscv
        temperature is lower than the threshold
        value written in the Trscv EEPROM
        <Help> Warning indicating that
         the Trscv temperature is lower
        than the threshold value written
        in the Trscv EEPROM <Condtype>
         TEMP_LOW_WNG_1 <Probcause> temperatureUnacceptable
        (51) <Alarmtype> equipmentAlarm
        (5) <Polarity> (2)
        "
	::= { pm10010mptAlmclientSfpWarnDdmEntry 8 }


pm10010mptAlmVccHighWngPortn OBJECT-TYPE
	SYNTAX  EkiOnOff
	MAX-ACCESS read-only
	STATUS current
	DESCRIPTION
        "
        Client Trscv Power Supply High
        Warning :This OID indicates that
        the Trscv power supply is higher
        than the threshold value written
        in the Trscv EEPROM <Help> Warning
        indicating that the Trscv power
        supply is higher than the threshold
        value written in the Trscv EEPROM
        <Condtype> VCC_HIGH_WNG_1 <Probcause>
        powerProblem (36) <Alarmtype> equipmentAlarm
        (5) <Polarity> (2)
        "
	::= { pm10010mptAlmclientSfpWarnDdmEntry 7 }


pm10010mptAlmVccLowWngPortn OBJECT-TYPE
	SYNTAX  EkiOnOff
	MAX-ACCESS read-only
	STATUS current
	DESCRIPTION
        "
        Client Trscv Power Supply Low
         Warning :This OID indicates that
        the Trscv power supply is lower
        than the threshold value written
        in the Trscv EEPROM <Help> Warning
        indicating that the Trscv power
        supply is lower than the threshold
        value written in the Trscv EEPROM
        <Condtype> VCC_LOW_WNG_1 <Probcause>
        powerProblem (36) <Alarmtype> equipmentAlarm
        (5) <Polarity> (2)
        "
	::= { pm10010mptAlmclientSfpWarnDdmEntry 6 }


pm10010mptAlmTxBiasHighWngPortn OBJECT-TYPE
	SYNTAX  EkiOnOff
	MAX-ACCESS read-only
	STATUS current
	DESCRIPTION
        "
        Client Trscv Bias High Warning
        :This OID indicates that the Trscv
        laser bias current is higher than
        the threshold value written in
         the Trscv EEPROM <Help> Warning
        indicating that the Trscv laser
        bias current is higher than the
        threshold value written in the
         Trscv EEPROM <Condtype> TX_BIAS_HIGH_WNG_1
        <Probcause> transmitterFailure
         (56) <Alarmtype> equipmentAlarm
        (5) <Polarity> (2)
        "
	::= { pm10010mptAlmclientSfpWarnDdmEntry 5 }


pm10010mptAlmTxBiasLowWngPortn OBJECT-TYPE
	SYNTAX  EkiOnOff
	MAX-ACCESS read-only
	STATUS current
	DESCRIPTION
        "
        Client Trscv Bias Low Warning
         :This OID indicates that the Trscv
        laser bias current is lower than
        the threshold value written in
         the Trscv EEPROM <Help> Warning
        indicating that the Trscv laser
        bias current is lower than the
         threshold value written in the
        Trscv EEPROM <Condtype> TX_BIAS_LOW_WNG_1
        <Probcause> transmitterFailure
         (56) <Alarmtype> equipmentAlarm
        (5) <Polarity> (2)
        "
	::= { pm10010mptAlmclientSfpWarnDdmEntry 4 }


pm10010mptAlmTxPwrHighWngPortn OBJECT-TYPE
	SYNTAX  EkiOnOff
	MAX-ACCESS read-only
	STATUS current
	DESCRIPTION
        "
        Client Trscv Tx Power High Warning
        :This OID indicates that the Trscv
        output power is higher than the
        threshold value written in the
         Trscv EEPROM <Help> Warning indicating
        that the Trscv output power is
         higher than the threshold value
        written in the Trscv EEPROM <Condtype>
        TX_PWR_HIGH_WNG_1 <Probcause> transmitterFailure
        (56) <Alarmtype> equipmentAlarm
        (5) <Polarity> (2)
        "
	::= { pm10010mptAlmclientSfpWarnDdmEntry 3 }


pm10010mptAlmTxPwLowWngPortn OBJECT-TYPE
	SYNTAX  EkiOnOff
	MAX-ACCESS read-only
	STATUS current
	DESCRIPTION
        "
        Client Trscv Tx Power Low Warning
        :This OID indicates that the Trscv
        output power is lower than the
         threshold value written in the
        Trscv EEPROM <Help> Warning indicating
        that the Trscv output power is
         lower than the threshold value
        written in the Trscv EEPROM <Condtype>
        TX_PW_LOW_WNG_1 <Probcause> transmitterFailure
        (56) <Alarmtype> equipmentAlarm
        (5) <Polarity> (2)
        "
	::= { pm10010mptAlmclientSfpWarnDdmEntry 2 }







--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pm10010mptCtrlconfMgnt1 OBJECT IDENTIFIER ::= { pm10010mptCtrlOther 1 }




pm10010mptCtrlConf2Clear1 OBJECT-TYPE
	  SYNTAX EkiOnOff
	  MAX-ACCESS read-write
	  STATUS current
	  DESCRIPTION
        "
        Clear Configuration Tables :This
        OID clears the configuration tables
        from configuration2 in the flash.
         <Help>  This control restores
         the default configuration of the
        module
        "
	  ::= { pm10010mptCtrlconfMgnt1 14 }



pm10010mptCtrlConf2Flash1 OBJECT-TYPE
	  SYNTAX EkiOnOff
	  MAX-ACCESS read-write
	  STATUS current
	  DESCRIPTION
        "
        Write Configuration Tables :This
        OID saves the current configuration
        of the PM as configuration2 in
         the flash.  <Help>  This control
        saves the customer configuration
        on the module
        "
	  ::= { pm10010mptCtrlconfMgnt1 10 }



pm10010mptCtrlConf2Load1 OBJECT-TYPE
	  SYNTAX EkiOnOff
	  MAX-ACCESS read-write
	  STATUS current
	  DESCRIPTION
        "
        Load Configuration Tables Set
         Nb 2 :When set this OID enables
        loading from flash configuration2
        into the PM.
        "
	  ::= { pm10010mptCtrlconfMgnt1 2 }



pm10010mptCtrlConf1Load1 OBJECT-TYPE
	  SYNTAX EkiOnOff
	  MAX-ACCESS read-write
	  STATUS current
	  DESCRIPTION
        "
        Load Configuration Tables Set
         Nb 1 :When set this OID enables
        loading from flash configuration1
        into the PM.
        "
	  ::= { pm10010mptCtrlconfMgnt1 1 }



--- *****************************************************
---     LEAF for the synth4 article
--- *****************************************************
pm10010mptCtrlsynth4 OBJECT IDENTIFIER ::= { pm10010mptCtrlOther 4 }




pm10010mptCtrlCorrelatOff OBJECT-TYPE
	  SYNTAX EkiOnOff
	  MAX-ACCESS read-write
	  STATUS current
	  DESCRIPTION
        "
        Disable Alarm Correlation :This
        OID disables the alarm correlation
        in the PM.
        "
	  ::= { pm10010mptCtrlsynth4 2 }



pm10010mptCtrlCorrelatOn OBJECT-TYPE
	  SYNTAX EkiOnOff
	  MAX-ACCESS read-write
	  STATUS current
	  DESCRIPTION
        "
        Enable Alarm Correlation :This
        OID enables the alarm correlation
        in the PM.
        "
	  ::= { pm10010mptCtrlsynth4 1 }



--- *****************************************************
---     LEAF for the swMgnt article
--- *****************************************************
pm10010mptCtrlswMgnt OBJECT IDENTIFIER ::= { pm10010mptCtrlOther 5 }




pm10010mptCtrlLoadSwBank2 OBJECT-TYPE
	  SYNTAX EkiOnOff
	  MAX-ACCESS read-write
	  STATUS current
	  DESCRIPTION
        "
        Set Software Nb 2 As Active :This
        OID, when set, loads the SW from
        bank2 into the PM. It must be followed
        by a reset.  <Help>  This controls
        selects the second SW bank as the
        active bank for the next module
        reset
        "
	  ::= { pm10010mptCtrlswMgnt 6 }



pm10010mptCtrlLoadSwBank1 OBJECT-TYPE
	  SYNTAX EkiOnOff
	  MAX-ACCESS read-write
	  STATUS current
	  DESCRIPTION
        "
        Set Software Nb 1 As Active :This
        OID, when set, loads the SW from
        bank1 into the PM. It must be followed
        by a reset.  <Help>  This controls
        selects the first SW bank as the
        active bank for the next module
        reset
        "
	  ::= { pm10010mptCtrlswMgnt 5 }



pm10010mptCtrlWarmReset OBJECT-TYPE
	  SYNTAX EkiOnOff
	  MAX-ACCESS read-write
	  STATUS current
	  DESCRIPTION
        "
        PM Warm Reset :This OID, when
         set, causes a warm reset of the
        PM. This reset is not traffic affecting,
        and the configuration of PM remains
        unchanged.  <Help>  This control
        initiates a warm reset of the module.
        "
	  ::= { pm10010mptCtrlswMgnt 3 }



pm10010mptCtrlColdReset OBJECT-TYPE
	  SYNTAX EkiOnOff
	  MAX-ACCESS read-write
	  STATUS current
	  DESCRIPTION
        "
        PM Cold Reset :This OID, when
         set, causes a cold reset of the
        PM. This reset is traffic affecting,
        and the configuration of PM is
         reloaded on start-up.  <Help>
          This control initiates a cold
        reset of the module.
        "
	  ::= { pm10010mptCtrlswMgnt 2 }



--- *****************************************************
---     LEAF for the gwMgnt article
--- *****************************************************
pm10010mptCtrlgwMgnt OBJECT IDENTIFIER ::= { pm10010mptCtrlOther 6 }




pm10010mptCtrlLoadGwBank4 OBJECT-TYPE
	  SYNTAX EkiOnOff
	  MAX-ACCESS read-write
	  STATUS current
	  DESCRIPTION
        "
        Set Gateware Nb 4 As Active :This
        OID, when set, loads the GW from
        bank4 (Flash) into the PM. It is
        followed by an automatic gateware
        cold reset.
        "
	  ::= { pm10010mptCtrlgwMgnt 8 }



pm10010mptCtrlLoadGwBank3 OBJECT-TYPE
	  SYNTAX EkiOnOff
	  MAX-ACCESS read-write
	  STATUS current
	  DESCRIPTION
        "
        Set Gateware Nb 3 As Active :This
        OID, when set, loads the GW from
        bank3 (Flash) into the PM. It is
        followed by an automatic gateware
        cold reset.  <Help>  This controls
        initiates a cold reset of the module
        and select the third GW bank as
        the active bank
        "
	  ::= { pm10010mptCtrlgwMgnt 7 }



pm10010mptCtrlLoadGwBank2 OBJECT-TYPE
	  SYNTAX EkiOnOff
	  MAX-ACCESS read-write
	  STATUS current
	  DESCRIPTION
        "
        Set Gateware Nb 2 As Active :This
        OID, when set, loads the GW from
        bank2 (Flash) into the PM. It is
        followed by an automatic gateware
        cold reset.
        "
	  ::= { pm10010mptCtrlgwMgnt 6 }



pm10010mptCtrlLoadGwBank1 OBJECT-TYPE
	  SYNTAX EkiOnOff
	  MAX-ACCESS read-write
	  STATUS current
	  DESCRIPTION
        "
        Set Gateware Nb 1 As Active :This
        OID, when set, loads the GW from
        bank1 (Flash) into the PM. It is
        followed by an automatic gateware
        cold reset.  <Help>  This controls
        initiates a cold reset of the module
        and select the first GW bank as
        the active bank
        "
	  ::= { pm10010mptCtrlgwMgnt 5 }



pm10010mptCtrlCurrentGwReset OBJECT-TYPE
	  SYNTAX EkiOnOff
	  MAX-ACCESS read-write
	  STATUS current
	  DESCRIPTION
        "
        Active Gateware Reset :This OID,
        when set, resets the active gateware.
        It is traffic affecting.
        "
	  ::= { pm10010mptCtrlgwMgnt 1 }



--- *********************************************************
---     TABLE for the pm10010mptCtrlaccessLoop articles
--- *********************************************************

pm10010mptCtrlaccessLoopTable OBJECT-TYPE
	SYNTAX  SEQUENCE OF Pm10010mptCtrlaccessLoopEntry
	MAX-ACCESS not-accessible
	STATUS current
	DESCRIPTION
        "
        List of pm10010mptCtrlaccessLoop
        Article
        "
	::= { pm10010mptCtrlClient 16 }


pm10010mptCtrlaccessLoopEntry OBJECT-TYPE
	SYNTAX Pm10010mptCtrlaccessLoopEntry
	MAX-ACCESS not-accessible
	STATUS current
	DESCRIPTION
        "
        Row definition for the pm10010mptCtrlaccessLoop
        table
        "
	INDEX   { pm10010mptCtrlaccessLoopIndex }
	::= { pm10010mptCtrlaccessLoopTable 1 }


Pm10010mptCtrlaccessLoopEntry ::=
	SEQUENCE {
	pm10010mptCtrlaccessLoopIndex
		INTEGER,
	pm10010mptCtrlaccessLoopPortn
		EkiState
	}


pm10010mptCtrlaccessLoopIndex OBJECT-TYPE
	SYNTAX  INTEGER(0..128)
	MAX-ACCESS  read-only
	STATUS current
	DESCRIPTION
        "
        Index definition for the pm10010mptCtrlaccessLoop
        table
        "
	::= { pm10010mptCtrlaccessLoopEntry 1 }


pm10010mptCtrlaccessLoopPortn OBJECT-TYPE
	SYNTAX  EkiState
	MAX-ACCESS read-write
	STATUS current
	DESCRIPTION
        "
        Client Facility Loopback :This
        OID, when set at '1' puts the client
        port in loopback, looping the received
        10 Gb/s signal on the transmit
         10 Gb/s output.  <Help> This control
        enables the Out Loopback on the
        client port, looping the client
        input signal on the client output
        "
	::= { pm10010mptCtrlaccessLoopEntry 2 }


--- *********************************************************
---     TABLE for the pm10010mptCtrlclientLoopToLine articles
--- *********************************************************

pm10010mptCtrlclientLoopToLineTable OBJECT-TYPE
	SYNTAX  SEQUENCE OF Pm10010mptCtrlclientLoopToLineEntry
	MAX-ACCESS not-accessible
	STATUS current
	DESCRIPTION
        "
        List of pm10010mptCtrlclientLoopToLine
        Article
        "
	::= { pm10010mptCtrlClient 17 }


pm10010mptCtrlclientLoopToLineEntry OBJECT-TYPE
	SYNTAX Pm10010mptCtrlclientLoopToLineEntry
	MAX-ACCESS not-accessible
	STATUS current
	DESCRIPTION
        "
        Row definition for the pm10010mptCtrlclientLoopToLine
        table
        "
	INDEX   { pm10010mptCtrlclientLoopToLineIndex }
	::= { pm10010mptCtrlclientLoopToLineTable 1 }


Pm10010mptCtrlclientLoopToLineEntry ::=
	SEQUENCE {
	pm10010mptCtrlclientLoopToLineIndex
		INTEGER,
	pm10010mptCtrlclientLoopToLinePortn
		EkiState
	}


pm10010mptCtrlclientLoopToLineIndex OBJECT-TYPE
	SYNTAX  INTEGER(0..128)
	MAX-ACCESS  read-only
	STATUS current
	DESCRIPTION
        "
        Index definition for the pm10010mptCtrlclientLoopToLine
        table
        "
	::= { pm10010mptCtrlclientLoopToLineEntry 1 }


pm10010mptCtrlclientLoopToLinePortn OBJECT-TYPE
	SYNTAX  EkiState
	MAX-ACCESS read-write
	STATUS current
	DESCRIPTION
        "
        Client Terminal Loopback :This
        OID, when set, puts the client
         port in loop back, looping the
        10 Gb/s output signal on the 10
        Gb/s input.<Help> This control
         enables the In Loopback on the
        client port, looping the client
        output signal on the client input
        "
	::= { pm10010mptCtrlclientLoopToLineEntry 2 }


--- *********************************************************
---     TABLE for the pm10010mptCtrlcsfUpIns articles
--- *********************************************************

pm10010mptCtrlcsfUpInsTable OBJECT-TYPE
	SYNTAX  SEQUENCE OF Pm10010mptCtrlcsfUpInsEntry
	MAX-ACCESS not-accessible
	STATUS current
	DESCRIPTION
        "
        List of pm10010mptCtrlcsfUpIns
        Article
        "
	::= { pm10010mptCtrlClient 21 }


pm10010mptCtrlcsfUpInsEntry OBJECT-TYPE
	SYNTAX Pm10010mptCtrlcsfUpInsEntry
	MAX-ACCESS not-accessible
	STATUS current
	DESCRIPTION
        "
        Row definition for the pm10010mptCtrlcsfUpIns
        table
        "
	INDEX   { pm10010mptCtrlcsfUpInsIndex }
	::= { pm10010mptCtrlcsfUpInsTable 1 }


Pm10010mptCtrlcsfUpInsEntry ::=
	SEQUENCE {
	pm10010mptCtrlcsfUpInsIndex
		INTEGER,
	pm10010mptCtrlcsfUpInsPortn
		EkiState
	}


pm10010mptCtrlcsfUpInsIndex OBJECT-TYPE
	SYNTAX  INTEGER(0..128)
	MAX-ACCESS  read-only
	STATUS current
	DESCRIPTION
        "
        Index definition for the pm10010mptCtrlcsfUpIns
        table
        "
	::= { pm10010mptCtrlcsfUpInsEntry 1 }


pm10010mptCtrlcsfUpInsPortn OBJECT-TYPE
	SYNTAX  EkiState
	MAX-ACCESS read-write
	STATUS current
	DESCRIPTION
        "
        Client Signal Fail Insertion :This
        OID, when set, inserts  a client
        signal fail in the upstream client
        Port.  <Help>  This control inserts
        a Client Signal Fail for the client
        port
        "
	::= { pm10010mptCtrlcsfUpInsEntry 2 }


--- *********************************************************
---     TABLE for the pm10010mptCtrlcaisDwIns articles
--- *********************************************************

pm10010mptCtrlcaisDwInsTable OBJECT-TYPE
	SYNTAX  SEQUENCE OF Pm10010mptCtrlcaisDwInsEntry
	MAX-ACCESS not-accessible
	STATUS current
	DESCRIPTION
        "
        List of pm10010mptCtrlcaisDwIns
        Article
        "
	::= { pm10010mptCtrlClient 22 }


pm10010mptCtrlcaisDwInsEntry OBJECT-TYPE
	SYNTAX Pm10010mptCtrlcaisDwInsEntry
	MAX-ACCESS not-accessible
	STATUS current
	DESCRIPTION
        "
        Row definition for the pm10010mptCtrlcaisDwIns
        table
        "
	INDEX   { pm10010mptCtrlcaisDwInsIndex }
	::= { pm10010mptCtrlcaisDwInsTable 1 }


Pm10010mptCtrlcaisDwInsEntry ::=
	SEQUENCE {
	pm10010mptCtrlcaisDwInsIndex
		INTEGER,
	pm10010mptCtrlcaisDwInsPortn
		EkiState
	}


pm10010mptCtrlcaisDwInsIndex OBJECT-TYPE
	SYNTAX  INTEGER(0..128)
	MAX-ACCESS  read-only
	STATUS current
	DESCRIPTION
        "
        Index definition for the pm10010mptCtrlcaisDwIns
        table
        "
	::= { pm10010mptCtrlcaisDwInsEntry 1 }


pm10010mptCtrlcaisDwInsPortn OBJECT-TYPE
	SYNTAX  EkiState
	MAX-ACCESS read-write
	STATUS current
	DESCRIPTION
        "
        Client AIS Insertion :This OID,
        when set, inserts a client AIS
         on the downstream client Port.
         <Help>  This control inserts a
        Client AIS for the client port
        "
	::= { pm10010mptCtrlcaisDwInsEntry 2 }


--- *********************************************************
---     TABLE for the pm10010mptCtrlcommAccessLoop articles
--- *********************************************************

pm10010mptCtrlcommAccessLoopTable OBJECT-TYPE
	SYNTAX  SEQUENCE OF Pm10010mptCtrlcommAccessLoopEntry
	MAX-ACCESS not-accessible
	STATUS current
	DESCRIPTION
        "
        List of pm10010mptCtrlcommAccessLoop
        Article
        "
	::= { pm10010mptCtrlLine 64 }


pm10010mptCtrlcommAccessLoopEntry OBJECT-TYPE
	SYNTAX Pm10010mptCtrlcommAccessLoopEntry
	MAX-ACCESS not-accessible
	STATUS current
	DESCRIPTION
        "
        Row definition for the pm10010mptCtrlcommAccessLoop
        table
        "
	INDEX   { pm10010mptCtrlcommAccessLoopIndex }
	::= { pm10010mptCtrlcommAccessLoopTable 1 }


Pm10010mptCtrlcommAccessLoopEntry ::=
	SEQUENCE {
	pm10010mptCtrlcommAccessLoopIndex
		INTEGER,
	pm10010mptCtrlcommAccessLoopPortn
		EkiState
	}


pm10010mptCtrlcommAccessLoopIndex OBJECT-TYPE
	SYNTAX  INTEGER(0..128)
	MAX-ACCESS  read-only
	STATUS current
	DESCRIPTION
        "
        Index definition for the pm10010mptCtrlcommAccessLoop
        table
        "
	::= { pm10010mptCtrlcommAccessLoopEntry 1 }


pm10010mptCtrlcommAccessLoopPortn OBJECT-TYPE
	SYNTAX  EkiState
	MAX-ACCESS read-write
	STATUS current
	DESCRIPTION
        "
        Line Terminal Loopback :This OID,
        when set, puts the module in common
        access loop back, looping the 100
        Gb/s output signal on the 100 Gb/s
        input.<Help> This control enables
        the In Loopback on the line port,
        looping the 100 Gb/s output signal
        on the 100 Gb/s input
        "
	::= { pm10010mptCtrlcommAccessLoopEntry 2 }


--- *********************************************************
---     TABLE for the pm10010mptCtrllineLoop articles
--- *********************************************************

pm10010mptCtrllineLoopTable OBJECT-TYPE
	SYNTAX  SEQUENCE OF Pm10010mptCtrllineLoopEntry
	MAX-ACCESS not-accessible
	STATUS current
	DESCRIPTION
        "
        List of pm10010mptCtrllineLoop
        Article
        "
	::= { pm10010mptCtrlLine 66 }


pm10010mptCtrllineLoopEntry OBJECT-TYPE
	SYNTAX Pm10010mptCtrllineLoopEntry
	MAX-ACCESS not-accessible
	STATUS current
	DESCRIPTION
        "
        Row definition for the pm10010mptCtrllineLoop
        table
        "
	INDEX   { pm10010mptCtrllineLoopIndex }
	::= { pm10010mptCtrllineLoopTable 1 }


Pm10010mptCtrllineLoopEntry ::=
	SEQUENCE {
	pm10010mptCtrllineLoopIndex
		INTEGER,
	pm10010mptCtrllineLoopPortn
		EkiState
	}


pm10010mptCtrllineLoopIndex OBJECT-TYPE
	SYNTAX  INTEGER(0..128)
	MAX-ACCESS  read-only
	STATUS current
	DESCRIPTION
        "
        Index definition for the pm10010mptCtrllineLoop
        table
        "
	::= { pm10010mptCtrllineLoopEntry 1 }


pm10010mptCtrllineLoopPortn OBJECT-TYPE
	SYNTAX  EkiState
	MAX-ACCESS read-write
	STATUS current
	DESCRIPTION
        "
        Line Facility Loopback :This OID,
        when set at '1' puts the module
        in line loopback mode, looping
         the received 100 Gb/s signal on
        the transmit 100 Gb/s output. The
        Upstream part of the module is
         timed on the 100 Gb/s recovered
        clock in that case.<Help> This
         control enables the Out Loopback
        on the line port, looping the 100
        Gb/s input signal on the 100 Gb/s
        output
        "
	::= { pm10010mptCtrllineLoopEntry 2 }


--- *********************************************************
---     TABLE for the pm10010mptCtrlfecDisable articles
--- *********************************************************

pm10010mptCtrlfecDisableTable OBJECT-TYPE
	SYNTAX  SEQUENCE OF Pm10010mptCtrlfecDisableEntry
	MAX-ACCESS not-accessible
	STATUS current
	DESCRIPTION
        "
        List of pm10010mptCtrlfecDisable
        Article
        "
	::= { pm10010mptCtrlLine 69 }


pm10010mptCtrlfecDisableEntry OBJECT-TYPE
	SYNTAX Pm10010mptCtrlfecDisableEntry
	MAX-ACCESS not-accessible
	STATUS current
	DESCRIPTION
        "
        Row definition for the pm10010mptCtrlfecDisable
        table
        "
	INDEX   { pm10010mptCtrlfecDisableIndex }
	::= { pm10010mptCtrlfecDisableTable 1 }


Pm10010mptCtrlfecDisableEntry ::=
	SEQUENCE {
	pm10010mptCtrlfecDisableIndex
		INTEGER,
	pm10010mptCtrlfecDisablePortn
		EkiState
	}


pm10010mptCtrlfecDisableIndex OBJECT-TYPE
	SYNTAX  INTEGER(0..128)
	MAX-ACCESS  read-only
	STATUS current
	DESCRIPTION
        "
        Index definition for the pm10010mptCtrlfecDisable
        table
        "
	::= { pm10010mptCtrlfecDisableEntry 1 }


pm10010mptCtrlfecDisablePortn OBJECT-TYPE
	SYNTAX  EkiState
	MAX-ACCESS read-write
	STATUS current
	DESCRIPTION
        "
        Forward Error Correction Inhibition
        :This OID, when set, inhibits the
        Forward Error Correction feature
        on the line input  <Help>  This
        control enables/disables the Forward
        Error Correction on the line interface
        "
	::= { pm10010mptCtrlfecDisableEntry 2 }


--- *****************************************************
---     LEAF for the ledTest article
--- *****************************************************
pm10010mptCtrlledTest OBJECT IDENTIFIER ::= { pm10010mptCtrlOther 192 }




pm10010mptCtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { pm10010mptCtrlledTest 3 }



pm10010mptCtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { pm10010mptCtrlledTest 2 }



pm10010mptCtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { pm10010mptCtrlledTest 1 }



--- *****************************************************
---     LEAF for the initSwitchMarvell article
--- *****************************************************
pm10010mptCtrlinitSwitchMarvell OBJECT IDENTIFIER ::= { pm10010mptCtrlOther 201 }




pm10010mptCtrlInitSwitchMarvell OBJECT-TYPE
	  SYNTAX EkiOnOff
	  MAX-ACCESS read-write
	  STATUS current
	  DESCRIPTION
        "
        Switch Initialization :This OID
        operates an initialization of the
        switch managed through the module
         <Help>  This control activates
        an initialization of the switch
        managed through the module
        "
	  ::= { pm10010mptCtrlinitSwitchMarvell 1 }



--- *********************************************************
---     TABLE for the pm10010mptCtrlmsaLineLoop articles
--- *********************************************************

pm10010mptCtrlmsaLineLoopTable OBJECT-TYPE
	SYNTAX  SEQUENCE OF Pm10010mptCtrlmsaLineLoopEntry
	MAX-ACCESS not-accessible
	STATUS current
	DESCRIPTION
        "
        List of pm10010mptCtrlmsaLineLoop
        Article
        "
	::= { pm10010mptCtrlLine 209 }


pm10010mptCtrlmsaLineLoopEntry OBJECT-TYPE
	SYNTAX Pm10010mptCtrlmsaLineLoopEntry
	MAX-ACCESS not-accessible
	STATUS current
	DESCRIPTION
        "
        Row definition for the pm10010mptCtrlmsaLineLoop
        table
        "
	INDEX   { pm10010mptCtrlmsaLineLoopIndex }
	::= { pm10010mptCtrlmsaLineLoopTable 1 }


Pm10010mptCtrlmsaLineLoopEntry ::=
	SEQUENCE {
	pm10010mptCtrlmsaLineLoopIndex
		INTEGER,
	pm10010mptCtrlmsaLineLoopPortn
		EkiState
	}


pm10010mptCtrlmsaLineLoopIndex OBJECT-TYPE
	SYNTAX  INTEGER(0..128)
	MAX-ACCESS  read-only
	STATUS current
	DESCRIPTION
        "
        Index definition for the pm10010mptCtrlmsaLineLoop
        table
        "
	::= { pm10010mptCtrlmsaLineLoopEntry 1 }


pm10010mptCtrlmsaLineLoopPortn OBJECT-TYPE
	SYNTAX  EkiState
	MAX-ACCESS read-write
	STATUS current
	DESCRIPTION
        "
        MSA Line Loop :This OID operates
        a line loopback on the MSA Line
         <Help>  This control defines the
        line loop back of the line transceiver
        "
	::= { pm10010mptCtrlmsaLineLoopEntry 2 }


--- *********************************************************
---     TABLE for the pm10010mptCtrlmsaTxReset articles
--- *********************************************************

pm10010mptCtrlmsaTxResetTable OBJECT-TYPE
	SYNTAX  SEQUENCE OF Pm10010mptCtrlmsaTxResetEntry
	MAX-ACCESS not-accessible
	STATUS current
	DESCRIPTION
        "
        List of pm10010mptCtrlmsaTxReset
        Article
        "
	::= { pm10010mptCtrlLine 210 }


pm10010mptCtrlmsaTxResetEntry OBJECT-TYPE
	SYNTAX Pm10010mptCtrlmsaTxResetEntry
	MAX-ACCESS not-accessible
	STATUS current
	DESCRIPTION
        "
        Row definition for the pm10010mptCtrlmsaTxReset
        table
        "
	INDEX   { pm10010mptCtrlmsaTxResetIndex }
	::= { pm10010mptCtrlmsaTxResetTable 1 }


Pm10010mptCtrlmsaTxResetEntry ::=
	SEQUENCE {
	pm10010mptCtrlmsaTxResetIndex
		INTEGER,
	pm10010mptCtrlmsaTxResetPortn
		EkiState
	}


pm10010mptCtrlmsaTxResetIndex OBJECT-TYPE
	SYNTAX  INTEGER(0..128)
	MAX-ACCESS  read-only
	STATUS current
	DESCRIPTION
        "
        Index definition for the pm10010mptCtrlmsaTxReset
        table
        "
	::= { pm10010mptCtrlmsaTxResetEntry 1 }


pm10010mptCtrlmsaTxResetPortn OBJECT-TYPE
	SYNTAX  EkiState
	MAX-ACCESS read-write
	STATUS current
	DESCRIPTION
        "
        Line MSA TX Reset :This OID resets
        the TX portion of the MSA line
         module  <Help > This control
         initiates a reset of the transmitting
        side
        "
	::= { pm10010mptCtrlmsaTxResetEntry 2 }


--- *********************************************************
---     TABLE for the pm10010mptCtrlmsaRxReset articles
--- *********************************************************

pm10010mptCtrlmsaRxResetTable OBJECT-TYPE
	SYNTAX  SEQUENCE OF Pm10010mptCtrlmsaRxResetEntry
	MAX-ACCESS not-accessible
	STATUS current
	DESCRIPTION
        "
        List of pm10010mptCtrlmsaRxReset
        Article
        "
	::= { pm10010mptCtrlLine 211 }


pm10010mptCtrlmsaRxResetEntry OBJECT-TYPE
	SYNTAX Pm10010mptCtrlmsaRxResetEntry
	MAX-ACCESS not-accessible
	STATUS current
	DESCRIPTION
        "
        Row definition for the pm10010mptCtrlmsaRxReset
        table
        "
	INDEX   { pm10010mptCtrlmsaRxResetIndex }
	::= { pm10010mptCtrlmsaRxResetTable 1 }


Pm10010mptCtrlmsaRxResetEntry ::=
	SEQUENCE {
	pm10010mptCtrlmsaRxResetIndex
		INTEGER,
	pm10010mptCtrlmsaRxResetPortn
		EkiState
	}


pm10010mptCtrlmsaRxResetIndex OBJECT-TYPE
	SYNTAX  INTEGER(0..128)
	MAX-ACCESS  read-only
	STATUS current
	DESCRIPTION
        "
        Index definition for the pm10010mptCtrlmsaRxReset
        table
        "
	::= { pm10010mptCtrlmsaRxResetEntry 1 }


pm10010mptCtrlmsaRxResetPortn OBJECT-TYPE
	SYNTAX  EkiState
	MAX-ACCESS read-write
	STATUS current
	DESCRIPTION
        "
        Line MSA RX Reset :This OID resets
        the RX portion of the MSA line
         module  <Help > This control
         initiates a reset of the receiving
        side
        "
	::= { pm10010mptCtrlmsaRxResetEntry 2 }


--- *********************************************************
---     TABLE for the pm10010mptCtrlmsaShutdown articles
--- *********************************************************

pm10010mptCtrlmsaShutdownTable OBJECT-TYPE
	SYNTAX  SEQUENCE OF Pm10010mptCtrlmsaShutdownEntry
	MAX-ACCESS not-accessible
	STATUS current
	DESCRIPTION
        "
        List of pm10010mptCtrlmsaShutdown
        Article
        "
	::= { pm10010mptCtrlLine 212 }


pm10010mptCtrlmsaShutdownEntry OBJECT-TYPE
	SYNTAX Pm10010mptCtrlmsaShutdownEntry
	MAX-ACCESS not-accessible
	STATUS current
	DESCRIPTION
        "
        Row definition for the pm10010mptCtrlmsaShutdown
        table
        "
	INDEX   { pm10010mptCtrlmsaShutdownIndex }
	::= { pm10010mptCtrlmsaShutdownTable 1 }


Pm10010mptCtrlmsaShutdownEntry ::=
	SEQUENCE {
	pm10010mptCtrlmsaShutdownIndex
		INTEGER,
	pm10010mptCtrlmsaShutdownPortn
		EkiState
	}


pm10010mptCtrlmsaShutdownIndex OBJECT-TYPE
	SYNTAX  INTEGER(0..128)
	MAX-ACCESS  read-only
	STATUS current
	DESCRIPTION
        "
        Index definition for the pm10010mptCtrlmsaShutdown
        table
        "
	::= { pm10010mptCtrlmsaShutdownEntry 1 }


pm10010mptCtrlmsaShutdownPortn OBJECT-TYPE
	SYNTAX  EkiState
	MAX-ACCESS read-write
	STATUS current
	DESCRIPTION
        "
        Line MSA Shutdown :This OID enters
        a process to shutdown the MSA line
        module  <Help > This control  initiates
        a shutdown of the module
        "
	::= { pm10010mptCtrlmsaShutdownEntry 2 }


--- *****************************************************
---     LEAF for the resetCount article
--- *****************************************************
pm10010mptCtrlresetCount OBJECT IDENTIFIER ::= { pm10010mptCtrlOther 259 }




pm10010mptCtrlResetcount OBJECT-TYPE
	  SYNTAX EkiOnOff
	  MAX-ACCESS read-write
	  STATUS current
	  DESCRIPTION
        "
        Module Count Global Reset :This
        OID resets all the errors counters
        on the module  <Help > This control
         initiates a reset of the errors
        counters on the module
        "
	  ::= { pm10010mptCtrlresetCount 1 }



--- *****************************************************
---     LEAF for the resetRmon article
--- *****************************************************
pm10010mptCtrlresetRmon OBJECT IDENTIFIER ::= { pm10010mptCtrlOther 260 }




pm10010mptCtrlResetrmon OBJECT-TYPE
	  SYNTAX EkiOnOff
	  MAX-ACCESS read-write
	  STATUS current
	  DESCRIPTION
        "
        Module Rmon Global Reset :This
        OID resets all the Rmon counters
        on the module  <Help > This control
         initiates a reset of the Rmon
         counters on the module
        "
	  ::= { pm10010mptCtrlresetRmon 1 }



--- *****************************************************
---     LEAF for the resetMeasurements article
--- *****************************************************
pm10010mptCtrlresetMeasurements OBJECT IDENTIFIER ::= { pm10010mptCtrlOther 261 }




pm10010mptCtrlResetmeasurements OBJECT-TYPE
	  SYNTAX EkiOnOff
	  MAX-ACCESS read-write
	  STATUS current
	  DESCRIPTION
        "
        Management Meas Global Reset :This
        OID resets some measurements on
        the management  <Help > This control
         initiates a reset of some measurements
        on the management
        "
	  ::= { pm10010mptCtrlresetMeasurements 1 }



--- *********************************************************
---     TABLE for the pm10010mptCtrlclientResetAllCount articles
--- *********************************************************

pm10010mptCtrlclientResetAllCountTable OBJECT-TYPE
	SYNTAX  SEQUENCE OF Pm10010mptCtrlclientResetAllCountEntry
	MAX-ACCESS not-accessible
	STATUS current
	DESCRIPTION
        "
        List of pm10010mptCtrlclientResetAllCount
        Article
        "
	::= { pm10010mptCtrlClient 262 }


pm10010mptCtrlclientResetAllCountEntry OBJECT-TYPE
	SYNTAX Pm10010mptCtrlclientResetAllCountEntry
	MAX-ACCESS not-accessible
	STATUS current
	DESCRIPTION
        "
        Row definition for the pm10010mptCtrlclientResetAllCount
        table
        "
	INDEX   { pm10010mptCtrlclientResetAllCountIndex }
	::= { pm10010mptCtrlclientResetAllCountTable 1 }


Pm10010mptCtrlclientResetAllCountEntry ::=
	SEQUENCE {
	pm10010mptCtrlclientResetAllCountIndex
		INTEGER,
	pm10010mptCtrlclientResetAllCountsPortn
		EkiState
	}


pm10010mptCtrlclientResetAllCountIndex OBJECT-TYPE
	SYNTAX  INTEGER(0..128)
	MAX-ACCESS  read-only
	STATUS current
	DESCRIPTION
        "
        Index definition for the pm10010mptCtrlclientResetAllCount
        table
        "
	::= { pm10010mptCtrlclientResetAllCountEntry 1 }


pm10010mptCtrlclientResetAllCountsPortn OBJECT-TYPE
	SYNTAX  EkiState
	MAX-ACCESS read-write
	STATUS current
	DESCRIPTION
        "
        Client Counters Reset :This OID
        resets every counter on the client
        port  <Help>   This control operates
        a reset on the statistics current
        ,previous and history client port
        counters
        "
	::= { pm10010mptCtrlclientResetAllCountEntry 2 }


--- *********************************************************
---     TABLE for the pm10010mptCtrllineResetAllCount articles
--- *********************************************************

pm10010mptCtrllineResetAllCountTable OBJECT-TYPE
	SYNTAX  SEQUENCE OF Pm10010mptCtrllineResetAllCountEntry
	MAX-ACCESS not-accessible
	STATUS current
	DESCRIPTION
        "
        List of pm10010mptCtrllineResetAllCount
        Article
        "
	::= { pm10010mptCtrlLine 263 }


pm10010mptCtrllineResetAllCountEntry OBJECT-TYPE
	SYNTAX Pm10010mptCtrllineResetAllCountEntry
	MAX-ACCESS not-accessible
	STATUS current
	DESCRIPTION
        "
        Row definition for the pm10010mptCtrllineResetAllCount
        table
        "
	INDEX   { pm10010mptCtrllineResetAllCountIndex }
	::= { pm10010mptCtrllineResetAllCountTable 1 }


Pm10010mptCtrllineResetAllCountEntry ::=
	SEQUENCE {
	pm10010mptCtrllineResetAllCountIndex
		INTEGER,
	pm10010mptCtrllineResetAllCountsPortn
		EkiState
	}


pm10010mptCtrllineResetAllCountIndex OBJECT-TYPE
	SYNTAX  INTEGER(0..128)
	MAX-ACCESS  read-only
	STATUS current
	DESCRIPTION
        "
        Index definition for the pm10010mptCtrllineResetAllCount
        table
        "
	::= { pm10010mptCtrllineResetAllCountEntry 1 }


pm10010mptCtrllineResetAllCountsPortn OBJECT-TYPE
	SYNTAX  EkiState
	MAX-ACCESS read-write
	STATUS current
	DESCRIPTION
        "
        Line Counters Reset :This OID
         resets every counter on the line
        port  <Help>   This control operates
        a reset on the statistics current
        ,previous and history line port
        counters
        "
	::= { pm10010mptCtrllineResetAllCountEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pm10010mptCntclientInputErrorCounterLaneOne articles
--- *********************************************************

pm10010mptCntclientInputErrorCounterLaneOneTable OBJECT-TYPE
	SYNTAX  SEQUENCE OF Pm10010mptCntclientInputErrorCounterLaneOneEntry
	MAX-ACCESS not-accessible
	STATUS current
	DESCRIPTION
        "
        List of pm10010mptCntclientInputErrorCounterLaneOne
        Article
        "
	::= { pm10010mptCntClient 16 }


pm10010mptCntclientInputErrorCounterLaneOneEntry OBJECT-TYPE
	SYNTAX Pm10010mptCntclientInputErrorCounterLaneOneEntry
	MAX-ACCESS not-accessible
	STATUS current
	DESCRIPTION
        "
        Row definition for the pm10010mptCntclientInputErrorCounterLaneOne
        table
        "
	INDEX   { pm10010mptCntclientInputErrorCounterLaneOneIndex }
	::= { pm10010mptCntclientInputErrorCounterLaneOneTable 1 }


Pm10010mptCntclientInputErrorCounterLaneOneEntry ::=
	SEQUENCE {
	pm10010mptCntclientInputErrorCounterLaneOneIndex
		INTEGER,
	pm10010mptCntclientInputErrorCounterLaneOneValuePortn
		Counter32,
	pm10010mptCntclientInputErrorCounterLaneOneErrorPortn
		EkiOnOff,
	pm10010mptCntclientInputErrorCounterLaneOneOverloadPortn
		EkiOnOff
	}


pm10010mptCntclientInputErrorCounterLaneOneIndex OBJECT-TYPE
	SYNTAX  INTEGER(0..128)
	MAX-ACCESS  read-only
	STATUS current
	DESCRIPTION
        "
        Index definition for the pm10010mptCntclientInputErrorCounterLaneOne
        table
        "
	::= { pm10010mptCntclientInputErrorCounterLaneOneEntry 1 }


pm10010mptCntclientInputErrorCounterLaneOneValuePortn OBJECT-TYPE
	SYNTAX  Counter32
	MAX-ACCESS read-only
	STATUS current
	DESCRIPTION
        "
        Client_Input_Error_Counter_Lane1
        :This counter is incremented each
        time a coding violation is detected
        on the host lane of the client
         transceiver <Help> This counter
        is incremented each time a coding
        violation is detected on the host
        lane of the client transceiver
        "
	::= { pm10010mptCntclientInputErrorCounterLaneOneEntry 2 }


pm10010mptCntclientInputErrorCounterLaneOneErrorPortn OBJECT-TYPE
	SYNTAX  EkiOnOff
	MAX-ACCESS read-only
	STATUS current
	DESCRIPTION
        "
        Client Input Counter Error :This
        OID when set indicates the rate
        adaptation removal counter value
        is invalid on Port
        "
	::= { pm10010mptCntclientInputErrorCounterLaneOneEntry 3 }


pm10010mptCntclientInputErrorCounterLaneOneOverloadPortn OBJECT-TYPE
	SYNTAX  EkiOnOff
	MAX-ACCESS read-only
	STATUS current
	DESCRIPTION
        "
        Client Input Counter Overload
         :This OID when set indicates a
        rate adaptation removal counter
        overload on Port
        "
	::= { pm10010mptCntclientInputErrorCounterLaneOneEntry 4 }


--- *********************************************************
---     TABLE for the pm10010mptCntclientInputErrorCounterLaneTwo articles
--- *********************************************************

pm10010mptCntclientInputErrorCounterLaneTwoTable OBJECT-TYPE
	SYNTAX  SEQUENCE OF Pm10010mptCntclientInputErrorCounterLaneTwoEntry
	MAX-ACCESS not-accessible
	STATUS current
	DESCRIPTION
        "
        List of pm10010mptCntclientInputErrorCounterLaneTwo
        Article
        "
	::= { pm10010mptCntClient 32 }


pm10010mptCntclientInputErrorCounterLaneTwoEntry OBJECT-TYPE
	SYNTAX Pm10010mptCntclientInputErrorCounterLaneTwoEntry
	MAX-ACCESS not-accessible
	STATUS current
	DESCRIPTION
        "
        Row definition for the pm10010mptCntclientInputErrorCounterLaneTwo
        table
        "
	INDEX   { pm10010mptCntclientInputErrorCounterLaneTwoIndex }
	::= { pm10010mptCntclientInputErrorCounterLaneTwoTable 1 }


Pm10010mptCntclientInputErrorCounterLaneTwoEntry ::=
	SEQUENCE {
	pm10010mptCntclientInputErrorCounterLaneTwoIndex
		INTEGER,
	pm10010mptCntclientInputErrorCounterLaneTwoValuePortn
		Counter32,
	pm10010mptCntclientInputErrorCounterLaneTwoErrorPortn
		EkiOnOff,
	pm10010mptCntclientInputErrorCounterLaneTwoOverloadPortn
		EkiOnOff
	}


pm10010mptCntclientInputErrorCounterLaneTwoIndex OBJECT-TYPE
	SYNTAX  INTEGER(0..128)
	MAX-ACCESS  read-only
	STATUS current
	DESCRIPTION
        "
        Index definition for the pm10010mptCntclientInputErrorCounterLaneTwo
        table
        "
	::= { pm10010mptCntclientInputErrorCounterLaneTwoEntry 1 }


pm10010mptCntclientInputErrorCounterLaneTwoValuePortn OBJECT-TYPE
	SYNTAX  Counter32
	MAX-ACCESS read-only
	STATUS current
	DESCRIPTION
        "
        Client_Input_Error_Counter_Lane2
        :This counter is incremented each
        time a coding violation is detected
        on the host lane of the client
         transceiver <Help> This counter
        is incremented each time a coding
        violation is detected on the host
        lane of the client transceiver
        "
	::= { pm10010mptCntclientInputErrorCounterLaneTwoEntry 2 }


pm10010mptCntclientInputErrorCounterLaneTwoErrorPortn OBJECT-TYPE
	SYNTAX  EkiOnOff
	MAX-ACCESS read-only
	STATUS current
	DESCRIPTION
        "
        Client Input Counter Error :This
        OID when set indicates the client
        error counter value is invalid
         on Port
        "
	::= { pm10010mptCntclientInputErrorCounterLaneTwoEntry 3 }


pm10010mptCntclientInputErrorCounterLaneTwoOverloadPortn OBJECT-TYPE
	SYNTAX  EkiOnOff
	MAX-ACCESS read-only
	STATUS current
	DESCRIPTION
        "
        Client Input Counter Overload
         :This OID when set indicates a
        client input error counter overload
        on Port
        "
	::= { pm10010mptCntclientInputErrorCounterLaneTwoEntry 4 }


--- *********************************************************
---     TABLE for the pm10010mptCntclientInputErrorCounter articles
--- *********************************************************

pm10010mptCntclientInputErrorCounterTable OBJECT-TYPE
	SYNTAX  SEQUENCE OF Pm10010mptCntclientInputErrorCounterEntry
	MAX-ACCESS not-accessible
	STATUS current
	DESCRIPTION
        "
        List of pm10010mptCntclientInputErrorCounter
        Article
        "
	::= { pm10010mptCntClient 80 }


pm10010mptCntclientInputErrorCounterEntry OBJECT-TYPE
	SYNTAX Pm10010mptCntclientInputErrorCounterEntry
	MAX-ACCESS not-accessible
	STATUS current
	DESCRIPTION
        "
        Row definition for the pm10010mptCntclientInputErrorCounter
        table
        "
	INDEX   { pm10010mptCntclientInputErrorCounterIndex }
	::= { pm10010mptCntclientInputErrorCounterTable 1 }


Pm10010mptCntclientInputErrorCounterEntry ::=
	SEQUENCE {
	pm10010mptCntclientInputErrorCounterIndex
		INTEGER,
	pm10010mptCntclientInputErrorCounterValuePortn
		Counter32,
	pm10010mptCntclientInputErrorCounterErrorPortn
		EkiOnOff,
	pm10010mptCntclientInputErrorCounterOverloadPortn
		EkiOnOff
	}


pm10010mptCntclientInputErrorCounterIndex OBJECT-TYPE
	SYNTAX  INTEGER(0..128)
	MAX-ACCESS  read-only
	STATUS current
	DESCRIPTION
        "
        Index definition for the pm10010mptCntclientInputErrorCounter
        table
        "
	::= { pm10010mptCntclientInputErrorCounterEntry 1 }


pm10010mptCntclientInputErrorCounterValuePortn OBJECT-TYPE
	SYNTAX  Counter32
	MAX-ACCESS read-only
	STATUS current
	DESCRIPTION
        "
        Client Input Errors :This counter
        is increased each time a 10b/8b
        running disparity error is detected
        on the Client input stream  <Help>
         This counter gives the number
         of 10b/8b running disparity errors
        on the client port
        "
	::= { pm10010mptCntclientInputErrorCounterEntry 2 }


pm10010mptCntclientInputErrorCounterErrorPortn OBJECT-TYPE
	SYNTAX  EkiOnOff
	MAX-ACCESS read-only
	STATUS current
	DESCRIPTION
        "
        Client Counter Error :This OID
        when set indicates the client error
        counter value is invalid on Port
        "
	::= { pm10010mptCntclientInputErrorCounterEntry 3 }


pm10010mptCntclientInputErrorCounterOverloadPortn OBJECT-TYPE
	SYNTAX  EkiOnOff
	MAX-ACCESS read-only
	STATUS current
	DESCRIPTION
        "
        Client Counter Overload :This
         OID when set indicates a client
        input error counter overload on
        Port
        "
	::= { pm10010mptCntclientInputErrorCounterEntry 4 }


--- *********************************************************
---     TABLE for the pm10010mptCntclientCbipCounter articles
--- *********************************************************

pm10010mptCntclientCbipCounterTable OBJECT-TYPE
	SYNTAX  SEQUENCE OF Pm10010mptCntclientCbipCounterEntry
	MAX-ACCESS not-accessible
	STATUS current
	DESCRIPTION
        "
        List of pm10010mptCntclientCbipCounter
        Article
        "
	::= { pm10010mptCntClient 96 }


pm10010mptCntclientCbipCounterEntry OBJECT-TYPE
	SYNTAX Pm10010mptCntclientCbipCounterEntry
	MAX-ACCESS not-accessible
	STATUS current
	DESCRIPTION
        "
        Row definition for the pm10010mptCntclientCbipCounter
        table
        "
	INDEX   { pm10010mptCntclientCbipCounterIndex }
	::= { pm10010mptCntclientCbipCounterTable 1 }


Pm10010mptCntclientCbipCounterEntry ::=
	SEQUENCE {
	pm10010mptCntclientCbipCounterIndex
		INTEGER,
	pm10010mptCntclientCbipCounterValuePortn
		Counter32,
	pm10010mptCntclientCbipCounterErrorPortn
		EkiOnOff,
	pm10010mptCntclientCbipCounterOverloadPortn
		EkiOnOff
	}


pm10010mptCntclientCbipCounterIndex OBJECT-TYPE
	SYNTAX  INTEGER(0..128)
	MAX-ACCESS  read-only
	STATUS current
	DESCRIPTION
        "
        Index definition for the pm10010mptCntclientCbipCounter
        table
        "
	::= { pm10010mptCntclientCbipCounterEntry 1 }


pm10010mptCntclientCbipCounterValuePortn OBJECT-TYPE
	SYNTAX  Counter32
	MAX-ACCESS read-only
	STATUS current
	DESCRIPTION
        "
        Client Output Errors :This counter
        is incremented each time a CBIP
        parity error is detected on the
        Client output stream  <Help>  This
        counter gives the number of CBIP
        errors on the client port
        "
	::= { pm10010mptCntclientCbipCounterEntry 2 }


pm10010mptCntclientCbipCounterErrorPortn OBJECT-TYPE
	SYNTAX  EkiOnOff
	MAX-ACCESS read-only
	STATUS current
	DESCRIPTION
        "
        Client Counter Error :This OID
        when set indicates the CBIP error
        counter value is invalid on Port
        "
	::= { pm10010mptCntclientCbipCounterEntry 3 }


pm10010mptCntclientCbipCounterOverloadPortn OBJECT-TYPE
	SYNTAX  EkiOnOff
	MAX-ACCESS read-only
	STATUS current
	DESCRIPTION
        "
        Client CBIP Counter Overload :This
        OID when set indicates a CBIP error
        counter overload on Port
        "
	::= { pm10010mptCntclientCbipCounterEntry 4 }


--- *********************************************************
---     TABLE for the pm10010mptCntlocalLineSmBip8ErrorCounter articles
--- *********************************************************

pm10010mptCntlocalLineSmBip8ErrorCounterTable OBJECT-TYPE
	SYNTAX  SEQUENCE OF Pm10010mptCntlocalLineSmBip8ErrorCounterEntry
	MAX-ACCESS not-accessible
	STATUS current
	DESCRIPTION
        "
        List of pm10010mptCntlocalLineSmBip8ErrorCounter
        Article
        "
	::= { pm10010mptCntLine 192 }


pm10010mptCntlocalLineSmBip8ErrorCounterEntry OBJECT-TYPE
	SYNTAX Pm10010mptCntlocalLineSmBip8ErrorCounterEntry
	MAX-ACCESS not-accessible
	STATUS current
	DESCRIPTION
        "
        Row definition for the pm10010mptCntlocalLineSmBip8ErrorCounter
        table
        "
	INDEX   { pm10010mptCntlocalLineSmBip8ErrorCounterIndex }
	::= { pm10010mptCntlocalLineSmBip8ErrorCounterTable 1 }


Pm10010mptCntlocalLineSmBip8ErrorCounterEntry ::=
	SEQUENCE {
	pm10010mptCntlocalLineSmBip8ErrorCounterIndex
		INTEGER,
	pm10010mptCntlocalLineSmBip8ErrorCounterValuePortn
		Counter64,
	pm10010mptCntlocalLineSmBip8ErrorCounterErrorPortn
		EkiOnOff,
	pm10010mptCntlocalLineSmBip8ErrorCounterOverloadPortn
		EkiOnOff
	}


pm10010mptCntlocalLineSmBip8ErrorCounterIndex OBJECT-TYPE
	SYNTAX  INTEGER(0..128)
	MAX-ACCESS  read-only
	STATUS current
	DESCRIPTION
        "
        Index definition for the pm10010mptCntlocalLineSmBip8ErrorCounter
        table
        "
	::= { pm10010mptCntlocalLineSmBip8ErrorCounterEntry 1 }


pm10010mptCntlocalLineSmBip8ErrorCounterValuePortn OBJECT-TYPE
	SYNTAX  Counter64
	MAX-ACCESS read-only
	STATUS current
	DESCRIPTION
        "
        Line Input SM-BIP8 Errors :This
        OID gives the current Bit Error
        Rate (residual SM-BIP8 error) after
        FEC   <Help> This counter gives
        the current Bit Error Rate (residual
        SM-BIP8 error) after FEC
        "
	::= { pm10010mptCntlocalLineSmBip8ErrorCounterEntry 2 }


pm10010mptCntlocalLineSmBip8ErrorCounterErrorPortn OBJECT-TYPE
	SYNTAX  EkiOnOff
	MAX-ACCESS read-only
	STATUS current
	DESCRIPTION
        "
        Line Counter Error :This OID when
        set indicates the B1 error counter
        value is invalid on Port
        "
	::= { pm10010mptCntlocalLineSmBip8ErrorCounterEntry 3 }


pm10010mptCntlocalLineSmBip8ErrorCounterOverloadPortn OBJECT-TYPE
	SYNTAX  EkiOnOff
	MAX-ACCESS read-only
	STATUS current
	DESCRIPTION
        "
        Line Counter Overload :This OID
        when set indicates a B1 error counter
        overload on Port
        "
	::= { pm10010mptCntlocalLineSmBip8ErrorCounterEntry 4 }


--- *********************************************************
---     TABLE for the pm10010mptCntlocalLineFecCorrectedErrorsCounter articles
--- *********************************************************

pm10010mptCntlocalLineFecCorrectedErrorsCounterTable OBJECT-TYPE
	SYNTAX  SEQUENCE OF Pm10010mptCntlocalLineFecCorrectedErrorsCounterEntry
	MAX-ACCESS not-accessible
	STATUS current
	DESCRIPTION
        "
        List of pm10010mptCntlocalLineFecCorrectedErrorsCounter
        Article
        "
	::= { pm10010mptCntLine 193 }


pm10010mptCntlocalLineFecCorrectedErrorsCounterEntry OBJECT-TYPE
	SYNTAX Pm10010mptCntlocalLineFecCorrectedErrorsCounterEntry
	MAX-ACCESS not-accessible
	STATUS current
	DESCRIPTION
        "
        Row definition for the pm10010mptCntlocalLineFecCorrectedErrorsCounter
        table
        "
	INDEX   { pm10010mptCntlocalLineFecCorrectedErrorsCounterIndex }
	::= { pm10010mptCntlocalLineFecCorrectedErrorsCounterTable 1 }


Pm10010mptCntlocalLineFecCorrectedErrorsCounterEntry ::=
	SEQUENCE {
	pm10010mptCntlocalLineFecCorrectedErrorsCounterIndex
		INTEGER,
	pm10010mptCntlocalLineFecCorrectedErrorsCounterValuePortn
		Counter64,
	pm10010mptCntlocalLineFecCorrectedErrorsCounterErrorPortn
		EkiOnOff,
	pm10010mptCntlocalLineFecCorrectedErrorsCounterOverloadPortn
		EkiOnOff
	}


pm10010mptCntlocalLineFecCorrectedErrorsCounterIndex OBJECT-TYPE
	SYNTAX  INTEGER(0..128)
	MAX-ACCESS  read-only
	STATUS current
	DESCRIPTION
        "
        Index definition for the pm10010mptCntlocalLineFecCorrectedErrorsCounter
        table
        "
	::= { pm10010mptCntlocalLineFecCorrectedErrorsCounterEntry 1 }


pm10010mptCntlocalLineFecCorrectedErrorsCounterValuePortn OBJECT-TYPE
	SYNTAX  Counter64
	MAX-ACCESS read-only
	STATUS current
	DESCRIPTION
        "
        Line Input HD FEC Corrected Errors
        :This OID gives the current Bit
        Error Rate before the Hard Decision
        FEC  <Help> This counter gives
         the current Bit Error Rate before
        the Hard Decision FEC
        "
	::= { pm10010mptCntlocalLineFecCorrectedErrorsCounterEntry 2 }


pm10010mptCntlocalLineFecCorrectedErrorsCounterErrorPortn OBJECT-TYPE
	SYNTAX  EkiOnOff
	MAX-ACCESS read-only
	STATUS current
	DESCRIPTION
        "
        FEC Counter Error :This bit when
        set indicates the FEC corrected
        errors counter value is invalid
        on Line
        "
	::= { pm10010mptCntlocalLineFecCorrectedErrorsCounterEntry 3 }


pm10010mptCntlocalLineFecCorrectedErrorsCounterOverloadPortn OBJECT-TYPE
	SYNTAX  EkiOnOff
	MAX-ACCESS read-only
	STATUS current
	DESCRIPTION
        "
        FEC Counter Overload :This bit
        when set indicates a FEC corrected
        errors counter overload on Line
        "
	::= { pm10010mptCntlocalLineFecCorrectedErrorsCounterEntry 4 }


--- *********************************************************
---     TABLE for the pm10010mptCntremoteLineSmBip8ErrorCounter articles
--- *********************************************************

pm10010mptCntremoteLineSmBip8ErrorCounterTable OBJECT-TYPE
	SYNTAX  SEQUENCE OF Pm10010mptCntremoteLineSmBip8ErrorCounterEntry
	MAX-ACCESS not-accessible
	STATUS current
	DESCRIPTION
        "
        List of pm10010mptCntremoteLineSmBip8ErrorCounter
        Article
        "
	::= { pm10010mptCntLine 194 }


pm10010mptCntremoteLineSmBip8ErrorCounterEntry OBJECT-TYPE
	SYNTAX Pm10010mptCntremoteLineSmBip8ErrorCounterEntry
	MAX-ACCESS not-accessible
	STATUS current
	DESCRIPTION
        "
        Row definition for the pm10010mptCntremoteLineSmBip8ErrorCounter
        table
        "
	INDEX   { pm10010mptCntremoteLineSmBip8ErrorCounterIndex }
	::= { pm10010mptCntremoteLineSmBip8ErrorCounterTable 1 }


Pm10010mptCntremoteLineSmBip8ErrorCounterEntry ::=
	SEQUENCE {
	pm10010mptCntremoteLineSmBip8ErrorCounterIndex
		INTEGER,
	pm10010mptCntremoteLineSmBip8ErrorCounterValuePortn
		Counter64,
	pm10010mptCntremoteLineSmBip8ErrorCounterErrorPortn
		EkiOnOff,
	pm10010mptCntremoteLineSmBip8ErrorCounterOverloadPortn
		EkiOnOff
	}


pm10010mptCntremoteLineSmBip8ErrorCounterIndex OBJECT-TYPE
	SYNTAX  INTEGER(0..128)
	MAX-ACCESS  read-only
	STATUS current
	DESCRIPTION
        "
        Index definition for the pm10010mptCntremoteLineSmBip8ErrorCounter
        table
        "
	::= { pm10010mptCntremoteLineSmBip8ErrorCounterEntry 1 }


pm10010mptCntremoteLineSmBip8ErrorCounterValuePortn OBJECT-TYPE
	SYNTAX  Counter64
	MAX-ACCESS read-only
	STATUS current
	DESCRIPTION
        "
        Remote SM BIP8 :This OID gives
        the current Bit Error Rate (residual
        SM-BIP8 error) after FEC on the
        remote side  <Help> This counter
        gives the current Bit Error Rate
        (residual SM-BIP8 error) after
         FEC on the remote side
        "
	::= { pm10010mptCntremoteLineSmBip8ErrorCounterEntry 2 }


pm10010mptCntremoteLineSmBip8ErrorCounterErrorPortn OBJECT-TYPE
	SYNTAX  EkiOnOff
	MAX-ACCESS read-only
	STATUS current
	DESCRIPTION
        "
        Remote Counter Error :
        "
	::= { pm10010mptCntremoteLineSmBip8ErrorCounterEntry 3 }


pm10010mptCntremoteLineSmBip8ErrorCounterOverloadPortn OBJECT-TYPE
	SYNTAX  EkiOnOff
	MAX-ACCESS read-only
	STATUS current
	DESCRIPTION
        "
        Remote Counter Overload :
        "
	::= { pm10010mptCntremoteLineSmBip8ErrorCounterEntry 4 }


--- *********************************************************
---     TABLE for the pm10010mptCntlineDfrmTimCnt articles
--- *********************************************************

pm10010mptCntlineDfrmTimCntTable OBJECT-TYPE
	SYNTAX  SEQUENCE OF Pm10010mptCntlineDfrmTimCntEntry
	MAX-ACCESS not-accessible
	STATUS current
	DESCRIPTION
        "
        List of pm10010mptCntlineDfrmTimCnt
        Article
        "
	::= { pm10010mptCntLine 195 }


pm10010mptCntlineDfrmTimCntEntry OBJECT-TYPE
	SYNTAX Pm10010mptCntlineDfrmTimCntEntry
	MAX-ACCESS not-accessible
	STATUS current
	DESCRIPTION
        "
        Row definition for the pm10010mptCntlineDfrmTimCnt
        table
        "
	INDEX   { pm10010mptCntlineDfrmTimCntIndex }
	::= { pm10010mptCntlineDfrmTimCntTable 1 }


Pm10010mptCntlineDfrmTimCntEntry ::=
	SEQUENCE {
	pm10010mptCntlineDfrmTimCntIndex
		INTEGER,
	pm10010mptCntlineDfrmTimCntValuePortn
		Counter64,
	pm10010mptCntlineDfrmTimCntErrorPortn
		EkiOnOff,
	pm10010mptCntlineDfrmTimCntOverloadPortn
		EkiOnOff
	}


pm10010mptCntlineDfrmTimCntIndex OBJECT-TYPE
	SYNTAX  INTEGER(0..128)
	MAX-ACCESS  read-only
	STATUS current
	DESCRIPTION
        "
        Index definition for the pm10010mptCntlineDfrmTimCnt
        table
        "
	::= { pm10010mptCntlineDfrmTimCntEntry 1 }


pm10010mptCntlineDfrmTimCntValuePortn OBJECT-TYPE
	SYNTAX  Counter64
	MAX-ACCESS read-only
	STATUS current
	DESCRIPTION
        "
        Line Timer Counter :
        "
	::= { pm10010mptCntlineDfrmTimCntEntry 2 }


pm10010mptCntlineDfrmTimCntErrorPortn OBJECT-TYPE
	SYNTAX  EkiOnOff
	MAX-ACCESS read-only
	STATUS current
	DESCRIPTION
        "
        Line Counter Error :This OID when
        set indicates the deframer timer
        counter value is invalid on Port
        "
	::= { pm10010mptCntlineDfrmTimCntEntry 3 }


pm10010mptCntlineDfrmTimCntOverloadPortn OBJECT-TYPE
	SYNTAX  EkiOnOff
	MAX-ACCESS read-only
	STATUS current
	DESCRIPTION
        "
        Line Counter Overload :This OID
        when set indicates a deframer timer
        counter overload on Port
        "
	::= { pm10010mptCntlineDfrmTimCntEntry 4 }


--- *********************************************************
---     TABLE for the pm10010mptCntlocalLineTrscvFecCorrectedErrorCounter articles
--- *********************************************************

pm10010mptCntlocalLineTrscvFecCorrectedErrorCounterTable OBJECT-TYPE
	SYNTAX  SEQUENCE OF Pm10010mptCntlocalLineTrscvFecCorrectedErrorCounterEntry
	MAX-ACCESS not-accessible
	STATUS current
	DESCRIPTION
        "
        List of pm10010mptCntlocalLineTrscvFecCorrectedErrorCounter
        Article
        "
	::= { pm10010mptCntLine 196 }


pm10010mptCntlocalLineTrscvFecCorrectedErrorCounterEntry OBJECT-TYPE
	SYNTAX Pm10010mptCntlocalLineTrscvFecCorrectedErrorCounterEntry
	MAX-ACCESS not-accessible
	STATUS current
	DESCRIPTION
        "
        Row definition for the pm10010mptCntlocalLineTrscvFecCorrectedErrorCounter
        table
        "
	INDEX   { pm10010mptCntlocalLineTrscvFecCorrectedErrorCounterIndex }
	::= { pm10010mptCntlocalLineTrscvFecCorrectedErrorCounterTable 1 }


Pm10010mptCntlocalLineTrscvFecCorrectedErrorCounterEntry ::=
	SEQUENCE {
	pm10010mptCntlocalLineTrscvFecCorrectedErrorCounterIndex
		INTEGER,
	pm10010mptCntlocalLineTrscvFecCorrectedErrorCounterValuePortn
		Counter64,
	pm10010mptCntlocalLineTrscvFecCorrectedErrorCounterErrorPortn
		EkiOnOff,
	pm10010mptCntlocalLineTrscvFecCorrectedErrorCounterOverloadPortn
		EkiOnOff
	}


pm10010mptCntlocalLineTrscvFecCorrectedErrorCounterIndex OBJECT-TYPE
	SYNTAX  INTEGER(0..128)
	MAX-ACCESS  read-only
	STATUS current
	DESCRIPTION
        "
        Index definition for the pm10010mptCntlocalLineTrscvFecCorrectedErrorCounter
        table
        "
	::= { pm10010mptCntlocalLineTrscvFecCorrectedErrorCounterEntry 1 }


pm10010mptCntlocalLineTrscvFecCorrectedErrorCounterValuePortn OBJECT-TYPE
	SYNTAX  Counter64
	MAX-ACCESS read-only
	STATUS current
	DESCRIPTION
        "
        Line Input SD FEC Corrected Errors
        :This OID gives the current Bit
        Error Rate before the Soft Decision
        FEC  <Help> This counter gives
         the current Bit Error Rate before
        the Soft Decision FEC
        "
	::= { pm10010mptCntlocalLineTrscvFecCorrectedErrorCounterEntry 2 }


pm10010mptCntlocalLineTrscvFecCorrectedErrorCounterErrorPortn OBJECT-TYPE
	SYNTAX  EkiOnOff
	MAX-ACCESS read-only
	STATUS current
	DESCRIPTION
        "
        Line Counter Error :This OID when
        set indicates the deframer timer
        counter value is invalid on Port
        "
	::= { pm10010mptCntlocalLineTrscvFecCorrectedErrorCounterEntry 3 }


pm10010mptCntlocalLineTrscvFecCorrectedErrorCounterOverloadPortn OBJECT-TYPE
	SYNTAX  EkiOnOff
	MAX-ACCESS read-only
	STATUS current
	DESCRIPTION
        "
        Line Counter Overload :This OID
        when set indicates a deframer timer
        counter overload on Port
        "
	::= { pm10010mptCntlocalLineTrscvFecCorrectedErrorCounterEntry 4 }


--- *********************************************************
---     TABLE for the pm10010mptCntlocalLineTrscvFecUncorrectedErrorCounter articles
--- *********************************************************

pm10010mptCntlocalLineTrscvFecUncorrectedErrorCounterTable OBJECT-TYPE
	SYNTAX  SEQUENCE OF Pm10010mptCntlocalLineTrscvFecUncorrectedErrorCounterEntry
	MAX-ACCESS not-accessible
	STATUS current
	DESCRIPTION
        "
        List of pm10010mptCntlocalLineTrscvFecUncorrectedErrorCounter
        Article
        "
	::= { pm10010mptCntLine 197 }


pm10010mptCntlocalLineTrscvFecUncorrectedErrorCounterEntry OBJECT-TYPE
	SYNTAX Pm10010mptCntlocalLineTrscvFecUncorrectedErrorCounterEntry
	MAX-ACCESS not-accessible
	STATUS current
	DESCRIPTION
        "
        Row definition for the pm10010mptCntlocalLineTrscvFecUncorrectedErrorCounter
        table
        "
	INDEX   { pm10010mptCntlocalLineTrscvFecUncorrectedErrorCounterIndex }
	::= { pm10010mptCntlocalLineTrscvFecUncorrectedErrorCounterTable 1 }


Pm10010mptCntlocalLineTrscvFecUncorrectedErrorCounterEntry ::=
	SEQUENCE {
	pm10010mptCntlocalLineTrscvFecUncorrectedErrorCounterIndex
		INTEGER,
	pm10010mptCntlocalLineTrscvFecUncorrectedErrorCounterValuePortn
		Counter64,
	pm10010mptCntlocalLineTrscvFecUncorrectedErrorCounterErrorPortn
		EkiOnOff,
	pm10010mptCntlocalLineTrscvFecUncorrectedErrorCounterOverloadPortn
		EkiOnOff
	}


pm10010mptCntlocalLineTrscvFecUncorrectedErrorCounterIndex OBJECT-TYPE
	SYNTAX  INTEGER(0..128)
	MAX-ACCESS  read-only
	STATUS current
	DESCRIPTION
        "
        Index definition for the pm10010mptCntlocalLineTrscvFecUncorrectedErrorCounter
        table
        "
	::= { pm10010mptCntlocalLineTrscvFecUncorrectedErrorCounterEntry 1 }


pm10010mptCntlocalLineTrscvFecUncorrectedErrorCounterValuePortn OBJECT-TYPE
	SYNTAX  Counter64
	MAX-ACCESS read-only
	STATUS current
	DESCRIPTION
        "
        SD Uncorrected :This OID gives
        the current Bit Error Rate after
        the Soft Decision FEC (residual)
         <Help> This counter gives the
         current Bit Error Rate after the
        Soft Decision FEC (residual)
        "
	::= { pm10010mptCntlocalLineTrscvFecUncorrectedErrorCounterEntry 2 }


pm10010mptCntlocalLineTrscvFecUncorrectedErrorCounterErrorPortn OBJECT-TYPE
	SYNTAX  EkiOnOff
	MAX-ACCESS read-only
	STATUS current
	DESCRIPTION
        "
        Line Counter Error :This OID when
        set indicates the deframer timer
        counter value is invalid on Port
        "
	::= { pm10010mptCntlocalLineTrscvFecUncorrectedErrorCounterEntry 3 }


pm10010mptCntlocalLineTrscvFecUncorrectedErrorCounterOverloadPortn OBJECT-TYPE
	SYNTAX  EkiOnOff
	MAX-ACCESS read-only
	STATUS current
	DESCRIPTION
        "
        Line Counter Overload :This OID
        when set indicates a deframer timer
        counter overload on Port
        "
	::= { pm10010mptCntlocalLineTrscvFecUncorrectedErrorCounterEntry 4 }







--- *****************************************************
--- $$$$$$$$$$$$$$$$$$$$$$$$$$$$$$$$$$$$$$$$$$$$$$$$$$$$$
---     RMON - 64 bits COUNTERS
--- $$$$$$$$$$$$$$$$$$$$$$$$$$$$$$$$$$$$$$$$$$$$$$$$$$$$$
--- *****************************************************



--- *********************************************************
---     TABLE for the pm10010mptMonupRmonBytesCounterClientInput articles
--- *********************************************************

pm10010mptMonupRmonBytesCounterClientInputTable OBJECT-TYPE
	SYNTAX  SEQUENCE OF Pm10010mptMonupRmonBytesCounterClientInputEntry
	MAX-ACCESS not-accessible
	STATUS current
	DESCRIPTION
        "
        List of pm10010mptMonupRmonBytesCounterClientInput
        Article
        "
	::= { pm10010mptMonClientRmonCounter 16 }


pm10010mptMonupRmonBytesCounterClientInputEntry OBJECT-TYPE
	SYNTAX Pm10010mptMonupRmonBytesCounterClientInputEntry
	MAX-ACCESS not-accessible
	STATUS current
	DESCRIPTION
        "
        Row definition for the pm10010mptMonupRmonBytesCounterClientInput
        table
        "
	INDEX   { pm10010mptMonupRmonBytesCounterClientInputIndex }
	::= { pm10010mptMonupRmonBytesCounterClientInputTable 1 }


Pm10010mptMonupRmonBytesCounterClientInputEntry ::=
	SEQUENCE {
	pm10010mptMonupRmonBytesCounterClientInputIndex
		INTEGER,
	pm10010mptMonupRmonBytesCounterClientInputValuePortn
		Counter64,
	pm10010mptMonupRmonBytesCounterClientInputErrorPortn
		EkiOnOff,
	pm10010mptMonupRmonBytesCounterClientInputOverloadPortn
		EkiOnOff
	}


pm10010mptMonupRmonBytesCounterClientInputIndex OBJECT-TYPE
	SYNTAX  INTEGER(0..128)
	MAX-ACCESS  read-only
	STATUS current
	DESCRIPTION
        "
        Index definition for the pm10010mptMonupRmonBytesCounterClientInput
        table
        "
	::= { pm10010mptMonupRmonBytesCounterClientInputEntry 1 }


pm10010mptMonupRmonBytesCounterClientInputValuePortn OBJECT-TYPE
	SYNTAX  Counter64
	MAX-ACCESS read-only
	STATUS current
	DESCRIPTION
        "
        Client Input Bytes :This counter
        is increased each time a data byte
        is received on the client port
          <Help>  This counter gives the
        number of bytes received on the
        client port
        "
	::= { pm10010mptMonupRmonBytesCounterClientInputEntry 2 }


pm10010mptMonupRmonBytesCounterClientInputErrorPortn OBJECT-TYPE
	SYNTAX  EkiOnOff
	MAX-ACCESS read-only
	STATUS current
	DESCRIPTION
        "
        Bytes Counter Error :This OID
         when set indicates the Bytes counter
        value is invalid on client port
        "
	::= { pm10010mptMonupRmonBytesCounterClientInputEntry 3 }


pm10010mptMonupRmonBytesCounterClientInputOverloadPortn OBJECT-TYPE
	SYNTAX  EkiOnOff
	MAX-ACCESS read-only
	STATUS current
	DESCRIPTION
        "
        Bytes Counter Overload :This OID
        when set indicates a Bytes counter
        overload on client port
        "
	::= { pm10010mptMonupRmonBytesCounterClientInputEntry 4 }


--- *********************************************************
---     TABLE for the pm10010mptMonupRmonCrcErrorsCounterClientInput articles
--- *********************************************************

pm10010mptMonupRmonCrcErrorsCounterClientInputTable OBJECT-TYPE
	SYNTAX  SEQUENCE OF Pm10010mptMonupRmonCrcErrorsCounterClientInputEntry
	MAX-ACCESS not-accessible
	STATUS current
	DESCRIPTION
        "
        List of pm10010mptMonupRmonCrcErrorsCounterClientInput
        Article
        "
	::= { pm10010mptMonClientRmonCounter 32 }


pm10010mptMonupRmonCrcErrorsCounterClientInputEntry OBJECT-TYPE
	SYNTAX Pm10010mptMonupRmonCrcErrorsCounterClientInputEntry
	MAX-ACCESS not-accessible
	STATUS current
	DESCRIPTION
        "
        Row definition for the pm10010mptMonupRmonCrcErrorsCounterClientInput
        table
        "
	INDEX   { pm10010mptMonupRmonCrcErrorsCounterClientInputIndex }
	::= { pm10010mptMonupRmonCrcErrorsCounterClientInputTable 1 }


Pm10010mptMonupRmonCrcErrorsCounterClientInputEntry ::=
	SEQUENCE {
	pm10010mptMonupRmonCrcErrorsCounterClientInputIndex
		INTEGER,
	pm10010mptMonupRmonCrcErrorsCounterClientInputValuePortn
		Counter64,
	pm10010mptMonupRmonCrcErrorsCounterClientInputErrorPortn
		EkiOnOff,
	pm10010mptMonupRmonCrcErrorsCounterClientInputOverloadPortn
		EkiOnOff
	}


pm10010mptMonupRmonCrcErrorsCounterClientInputIndex OBJECT-TYPE
	SYNTAX  INTEGER(0..128)
	MAX-ACCESS  read-only
	STATUS current
	DESCRIPTION
        "
        Index definition for the pm10010mptMonupRmonCrcErrorsCounterClientInput
        table
        "
	::= { pm10010mptMonupRmonCrcErrorsCounterClientInputEntry 1 }


pm10010mptMonupRmonCrcErrorsCounterClientInputValuePortn OBJECT-TYPE
	SYNTAX  Counter64
	MAX-ACCESS read-only
	STATUS current
	DESCRIPTION
        "
        Client Input B1/CRC Errors :This
        counter is increased each time
         a B1/FCS error is detected on
         the client port  <Help>  This
         counter gives the number of B1/FCS
        Errors received on the client port
        "
	::= { pm10010mptMonupRmonCrcErrorsCounterClientInputEntry 2 }


pm10010mptMonupRmonCrcErrorsCounterClientInputErrorPortn OBJECT-TYPE
	SYNTAX  EkiOnOff
	MAX-ACCESS read-only
	STATUS current
	DESCRIPTION
        "
        B1/FCS Errors Counter Error :This
        OID when set indicates the B1/FCS
        Errors counter value is invalid
        on client port
        "
	::= { pm10010mptMonupRmonCrcErrorsCounterClientInputEntry 3 }


pm10010mptMonupRmonCrcErrorsCounterClientInputOverloadPortn OBJECT-TYPE
	SYNTAX  EkiOnOff
	MAX-ACCESS read-only
	STATUS current
	DESCRIPTION
        "
        B1/FCS Errors Counter Overload
        :This OID when set indicates a
         B1/FCS Errors counter overload
        on client port
        "
	::= { pm10010mptMonupRmonCrcErrorsCounterClientInputEntry 4 }


--- *********************************************************
---     TABLE for the pm10010mptMonupRmonPacketsCounterClientInput articles
--- *********************************************************

pm10010mptMonupRmonPacketsCounterClientInputTable OBJECT-TYPE
	SYNTAX  SEQUENCE OF Pm10010mptMonupRmonPacketsCounterClientInputEntry
	MAX-ACCESS not-accessible
	STATUS current
	DESCRIPTION
        "
        List of pm10010mptMonupRmonPacketsCounterClientInput
        Article
        "
	::= { pm10010mptMonClientRmonCounter 48 }


pm10010mptMonupRmonPacketsCounterClientInputEntry OBJECT-TYPE
	SYNTAX Pm10010mptMonupRmonPacketsCounterClientInputEntry
	MAX-ACCESS not-accessible
	STATUS current
	DESCRIPTION
        "
        Row definition for the pm10010mptMonupRmonPacketsCounterClientInput
        table
        "
	INDEX   { pm10010mptMonupRmonPacketsCounterClientInputIndex }
	::= { pm10010mptMonupRmonPacketsCounterClientInputTable 1 }


Pm10010mptMonupRmonPacketsCounterClientInputEntry ::=
	SEQUENCE {
	pm10010mptMonupRmonPacketsCounterClientInputIndex
		INTEGER,
	pm10010mptMonupRmonPacketsCounterClientInputValuePortn
		Counter64,
	pm10010mptMonupRmonPacketsCounterClientInputErrorPortn
		EkiOnOff,
	pm10010mptMonupRmonPacketsCounterClientInputOverloadPortn
		EkiOnOff
	}


pm10010mptMonupRmonPacketsCounterClientInputIndex OBJECT-TYPE
	SYNTAX  INTEGER(0..128)
	MAX-ACCESS  read-only
	STATUS current
	DESCRIPTION
        "
        Index definition for the pm10010mptMonupRmonPacketsCounterClientInput
        table
        "
	::= { pm10010mptMonupRmonPacketsCounterClientInputEntry 1 }


pm10010mptMonupRmonPacketsCounterClientInputValuePortn OBJECT-TYPE
	SYNTAX  Counter64
	MAX-ACCESS read-only
	STATUS current
	DESCRIPTION
        "
        Client Input Packets :This counter
        is increased each time a packet
        is received on the client port
          <Help>  This counter gives the
        number of packets received on the
        client port
        "
	::= { pm10010mptMonupRmonPacketsCounterClientInputEntry 2 }


pm10010mptMonupRmonPacketsCounterClientInputErrorPortn OBJECT-TYPE
	SYNTAX  EkiOnOff
	MAX-ACCESS read-only
	STATUS current
	DESCRIPTION
        "
        Packets Counter Error :This OID
        when set indicates the Packets
         counter value is invalid on client
        port
        "
	::= { pm10010mptMonupRmonPacketsCounterClientInputEntry 3 }


pm10010mptMonupRmonPacketsCounterClientInputOverloadPortn OBJECT-TYPE
	SYNTAX  EkiOnOff
	MAX-ACCESS read-only
	STATUS current
	DESCRIPTION
        "
        Packets Counter Overload :This
        OID when set indicates a Packets
        counter overload on client port
        "
	::= { pm10010mptMonupRmonPacketsCounterClientInputEntry 4 }


--- *********************************************************
---     TABLE for the pm10010mptMonupRmonBroadcastCounterClientInput articles
--- *********************************************************

pm10010mptMonupRmonBroadcastCounterClientInputTable OBJECT-TYPE
	SYNTAX  SEQUENCE OF Pm10010mptMonupRmonBroadcastCounterClientInputEntry
	MAX-ACCESS not-accessible
	STATUS current
	DESCRIPTION
        "
        List of pm10010mptMonupRmonBroadcastCounterClientInput
        Article
        "
	::= { pm10010mptMonClientRmonCounter 64 }


pm10010mptMonupRmonBroadcastCounterClientInputEntry OBJECT-TYPE
	SYNTAX Pm10010mptMonupRmonBroadcastCounterClientInputEntry
	MAX-ACCESS not-accessible
	STATUS current
	DESCRIPTION
        "
        Row definition for the pm10010mptMonupRmonBroadcastCounterClientInput
        table
        "
	INDEX   { pm10010mptMonupRmonBroadcastCounterClientInputIndex }
	::= { pm10010mptMonupRmonBroadcastCounterClientInputTable 1 }


Pm10010mptMonupRmonBroadcastCounterClientInputEntry ::=
	SEQUENCE {
	pm10010mptMonupRmonBroadcastCounterClientInputIndex
		INTEGER,
	pm10010mptMonupRmonBroadcastCounterClientInputValuePortn
		Counter64,
	pm10010mptMonupRmonBroadcastCounterClientInputErrorPortn
		EkiOnOff,
	pm10010mptMonupRmonBroadcastCounterClientInputOverloadPortn
		EkiOnOff
	}


pm10010mptMonupRmonBroadcastCounterClientInputIndex OBJECT-TYPE
	SYNTAX  INTEGER(0..128)
	MAX-ACCESS  read-only
	STATUS current
	DESCRIPTION
        "
        Index definition for the pm10010mptMonupRmonBroadcastCounterClientInput
        table
        "
	::= { pm10010mptMonupRmonBroadcastCounterClientInputEntry 1 }


pm10010mptMonupRmonBroadcastCounterClientInputValuePortn OBJECT-TYPE
	SYNTAX  Counter64
	MAX-ACCESS read-only
	STATUS current
	DESCRIPTION
        "
        Client Input Broadcast Packets
        :This counter is increased each
        time a broadcast packet is received
        on the client port  <Help>  This
        counter gives the number of Broadcast
        packets received on the client
         port
        "
	::= { pm10010mptMonupRmonBroadcastCounterClientInputEntry 2 }


pm10010mptMonupRmonBroadcastCounterClientInputErrorPortn OBJECT-TYPE
	SYNTAX  EkiOnOff
	MAX-ACCESS read-only
	STATUS current
	DESCRIPTION
        "
        Broadcast Counter Error :This
         OID when set indicates the Broadcast
        counter value is invalid on client
        port
        "
	::= { pm10010mptMonupRmonBroadcastCounterClientInputEntry 3 }


pm10010mptMonupRmonBroadcastCounterClientInputOverloadPortn OBJECT-TYPE
	SYNTAX  EkiOnOff
	MAX-ACCESS read-only
	STATUS current
	DESCRIPTION
        "
        Broadcast Counter Overload :This
        OID when set indicates a Broadcast
        counter overload on client port
        "
	::= { pm10010mptMonupRmonBroadcastCounterClientInputEntry 4 }


--- *********************************************************
---     TABLE for the pm10010mptMonupRmonMulticastCounterClientInput articles
--- *********************************************************

pm10010mptMonupRmonMulticastCounterClientInputTable OBJECT-TYPE
	SYNTAX  SEQUENCE OF Pm10010mptMonupRmonMulticastCounterClientInputEntry
	MAX-ACCESS not-accessible
	STATUS current
	DESCRIPTION
        "
        List of pm10010mptMonupRmonMulticastCounterClientInput
        Article
        "
	::= { pm10010mptMonClientRmonCounter 80 }


pm10010mptMonupRmonMulticastCounterClientInputEntry OBJECT-TYPE
	SYNTAX Pm10010mptMonupRmonMulticastCounterClientInputEntry
	MAX-ACCESS not-accessible
	STATUS current
	DESCRIPTION
        "
        Row definition for the pm10010mptMonupRmonMulticastCounterClientInput
        table
        "
	INDEX   { pm10010mptMonupRmonMulticastCounterClientInputIndex }
	::= { pm10010mptMonupRmonMulticastCounterClientInputTable 1 }


Pm10010mptMonupRmonMulticastCounterClientInputEntry ::=
	SEQUENCE {
	pm10010mptMonupRmonMulticastCounterClientInputIndex
		INTEGER,
	pm10010mptMonupRmonMulticastCounterClientInputValuePortn
		Counter64,
	pm10010mptMonupRmonMulticastCounterClientInputErrorPortn
		EkiOnOff,
	pm10010mptMonupRmonMulticastCounterClientInputOverloadPortn
		EkiOnOff
	}


pm10010mptMonupRmonMulticastCounterClientInputIndex OBJECT-TYPE
	SYNTAX  INTEGER(0..128)
	MAX-ACCESS  read-only
	STATUS current
	DESCRIPTION
        "
        Index definition for the pm10010mptMonupRmonMulticastCounterClientInput
        table
        "
	::= { pm10010mptMonupRmonMulticastCounterClientInputEntry 1 }


pm10010mptMonupRmonMulticastCounterClientInputValuePortn OBJECT-TYPE
	SYNTAX  Counter64
	MAX-ACCESS read-only
	STATUS current
	DESCRIPTION
        "
        Client Input Multicast Packets
        :This counter is increased each
        time a Multicast packet is received
        on the client port  <Help>  This
        counter gives the number of Multicast
        packets received on the client
         port
        "
	::= { pm10010mptMonupRmonMulticastCounterClientInputEntry 2 }


pm10010mptMonupRmonMulticastCounterClientInputErrorPortn OBJECT-TYPE
	SYNTAX  EkiOnOff
	MAX-ACCESS read-only
	STATUS current
	DESCRIPTION
        "
        Multicast Counter Error :This
         OID when set indicates the Multicast
        counter value is invalid on client
        port
        "
	::= { pm10010mptMonupRmonMulticastCounterClientInputEntry 3 }


pm10010mptMonupRmonMulticastCounterClientInputOverloadPortn OBJECT-TYPE
	SYNTAX  EkiOnOff
	MAX-ACCESS read-only
	STATUS current
	DESCRIPTION
        "
        Multicast Counter Overload :This
        OID when set indicates a Multicast
        counter overload on client port
        "
	::= { pm10010mptMonupRmonMulticastCounterClientInputEntry 4 }


--- *********************************************************
---     TABLE for the pm10010mptMonupRmonPauseFrameCounterClientInput articles
--- *********************************************************

pm10010mptMonupRmonPauseFrameCounterClientInputTable OBJECT-TYPE
	SYNTAX  SEQUENCE OF Pm10010mptMonupRmonPauseFrameCounterClientInputEntry
	MAX-ACCESS not-accessible
	STATUS current
	DESCRIPTION
        "
        List of pm10010mptMonupRmonPauseFrameCounterClientInput
        Article
        "
	::= { pm10010mptMonClientRmonCounter 96 }


pm10010mptMonupRmonPauseFrameCounterClientInputEntry OBJECT-TYPE
	SYNTAX Pm10010mptMonupRmonPauseFrameCounterClientInputEntry
	MAX-ACCESS not-accessible
	STATUS current
	DESCRIPTION
        "
        Row definition for the pm10010mptMonupRmonPauseFrameCounterClientInput
        table
        "
	INDEX   { pm10010mptMonupRmonPauseFrameCounterClientInputIndex }
	::= { pm10010mptMonupRmonPauseFrameCounterClientInputTable 1 }


Pm10010mptMonupRmonPauseFrameCounterClientInputEntry ::=
	SEQUENCE {
	pm10010mptMonupRmonPauseFrameCounterClientInputIndex
		INTEGER,
	pm10010mptMonupRmonPauseFrameCounterClientInputValuePortn
		Counter64,
	pm10010mptMonupRmonPauseFrameCounterClientInputErrorPortn
		EkiOnOff,
	pm10010mptMonupRmonPauseFrameCounterClientInputOverloadPortn
		EkiOnOff
	}


pm10010mptMonupRmonPauseFrameCounterClientInputIndex OBJECT-TYPE
	SYNTAX  INTEGER(0..128)
	MAX-ACCESS  read-only
	STATUS current
	DESCRIPTION
        "
        Index definition for the pm10010mptMonupRmonPauseFrameCounterClientInput
        table
        "
	::= { pm10010mptMonupRmonPauseFrameCounterClientInputEntry 1 }


pm10010mptMonupRmonPauseFrameCounterClientInputValuePortn OBJECT-TYPE
	SYNTAX  Counter64
	MAX-ACCESS read-only
	STATUS current
	DESCRIPTION
        "
        Client Input Pause Frames :This
        counter is increased each time
         a Pause frame is received on the
        client port  <Help>  This counter
        gives the number of Pause frames
        received on the client port
        "
	::= { pm10010mptMonupRmonPauseFrameCounterClientInputEntry 2 }


pm10010mptMonupRmonPauseFrameCounterClientInputErrorPortn OBJECT-TYPE
	SYNTAX  EkiOnOff
	MAX-ACCESS read-only
	STATUS current
	DESCRIPTION
        "
        Pause Counter Error :This OID
         when set indicates the Pause counter
        value is invalid on client port
        "
	::= { pm10010mptMonupRmonPauseFrameCounterClientInputEntry 3 }


pm10010mptMonupRmonPauseFrameCounterClientInputOverloadPortn OBJECT-TYPE
	SYNTAX  EkiOnOff
	MAX-ACCESS read-only
	STATUS current
	DESCRIPTION
        "
        Pause Counter Overload :This OID
        when set indicates a Pause counter
        overload on client port
        "
	::= { pm10010mptMonupRmonPauseFrameCounterClientInputEntry 4 }


--- *********************************************************
---     TABLE for the pm10010mptMonupRmonUnicastCounterClientInput articles
--- *********************************************************

pm10010mptMonupRmonUnicastCounterClientInputTable OBJECT-TYPE
	SYNTAX  SEQUENCE OF Pm10010mptMonupRmonUnicastCounterClientInputEntry
	MAX-ACCESS not-accessible
	STATUS current
	DESCRIPTION
        "
        List of pm10010mptMonupRmonUnicastCounterClientInput
        Article
        "
	::= { pm10010mptMonClientRmonCounter 160 }


pm10010mptMonupRmonUnicastCounterClientInputEntry OBJECT-TYPE
	SYNTAX Pm10010mptMonupRmonUnicastCounterClientInputEntry
	MAX-ACCESS not-accessible
	STATUS current
	DESCRIPTION
        "
        Row definition for the pm10010mptMonupRmonUnicastCounterClientInput
        table
        "
	INDEX   { pm10010mptMonupRmonUnicastCounterClientInputIndex }
	::= { pm10010mptMonupRmonUnicastCounterClientInputTable 1 }


Pm10010mptMonupRmonUnicastCounterClientInputEntry ::=
	SEQUENCE {
	pm10010mptMonupRmonUnicastCounterClientInputIndex
		INTEGER,
	pm10010mptMonupRmonUnicastCounterClientInputValuePortn
		Counter64,
	pm10010mptMonupRmonUnicastCounterClientInputErrorPortn
		EkiOnOff,
	pm10010mptMonupRmonUnicastCounterClientInputOverloadPortn
		EkiOnOff
	}


pm10010mptMonupRmonUnicastCounterClientInputIndex OBJECT-TYPE
	SYNTAX  INTEGER(0..128)
	MAX-ACCESS  read-only
	STATUS current
	DESCRIPTION
        "
        Index definition for the pm10010mptMonupRmonUnicastCounterClientInput
        table
        "
	::= { pm10010mptMonupRmonUnicastCounterClientInputEntry 1 }


pm10010mptMonupRmonUnicastCounterClientInputValuePortn OBJECT-TYPE
	SYNTAX  Counter64
	MAX-ACCESS read-only
	STATUS current
	DESCRIPTION
        "
        Client Input Unicast Packets :This
        counter is increased each time
         a Unicast packet is received on
        the client port  <Help>  This counter
        gives the number of Unicast packets
        received on the client port
        "
	::= { pm10010mptMonupRmonUnicastCounterClientInputEntry 2 }


pm10010mptMonupRmonUnicastCounterClientInputErrorPortn OBJECT-TYPE
	SYNTAX  EkiOnOff
	MAX-ACCESS read-only
	STATUS current
	DESCRIPTION
        "
        Unicast Counter Error :This OID
        when set indicates the Unicast
         counter value is invalid on client
        port
        "
	::= { pm10010mptMonupRmonUnicastCounterClientInputEntry 3 }


pm10010mptMonupRmonUnicastCounterClientInputOverloadPortn OBJECT-TYPE
	SYNTAX  EkiOnOff
	MAX-ACCESS read-only
	STATUS current
	DESCRIPTION
        "
        Unicast Counter Overload :This
        OID when set indicates a Unicast
        counter overload on client port
        "
	::= { pm10010mptMonupRmonUnicastCounterClientInputEntry 4 }


--- *********************************************************
---     TABLE for the pm10010mptMonupRmonNonunicastCounterClientInput articles
--- *********************************************************

pm10010mptMonupRmonNonunicastCounterClientInputTable OBJECT-TYPE
	SYNTAX  SEQUENCE OF Pm10010mptMonupRmonNonunicastCounterClientInputEntry
	MAX-ACCESS not-accessible
	STATUS current
	DESCRIPTION
        "
        List of pm10010mptMonupRmonNonunicastCounterClientInput
        Article
        "
	::= { pm10010mptMonClientRmonCounter 176 }


pm10010mptMonupRmonNonunicastCounterClientInputEntry OBJECT-TYPE
	SYNTAX Pm10010mptMonupRmonNonunicastCounterClientInputEntry
	MAX-ACCESS not-accessible
	STATUS current
	DESCRIPTION
        "
        Row definition for the pm10010mptMonupRmonNonunicastCounterClientInput
        table
        "
	INDEX   { pm10010mptMonupRmonNonunicastCounterClientInputIndex }
	::= { pm10010mptMonupRmonNonunicastCounterClientInputTable 1 }


Pm10010mptMonupRmonNonunicastCounterClientInputEntry ::=
	SEQUENCE {
	pm10010mptMonupRmonNonunicastCounterClientInputIndex
		INTEGER,
	pm10010mptMonupRmonNonunicastCounterClientInputValuePortn
		Counter64,
	pm10010mptMonupRmonNonunicastCounterClientInputErrorPortn
		EkiOnOff,
	pm10010mptMonupRmonNonunicastCounterClientInputOverloadPortn
		EkiOnOff
	}


pm10010mptMonupRmonNonunicastCounterClientInputIndex OBJECT-TYPE
	SYNTAX  INTEGER(0..128)
	MAX-ACCESS  read-only
	STATUS current
	DESCRIPTION
        "
        Index definition for the pm10010mptMonupRmonNonunicastCounterClientInput
        table
        "
	::= { pm10010mptMonupRmonNonunicastCounterClientInputEntry 1 }


pm10010mptMonupRmonNonunicastCounterClientInputValuePortn OBJECT-TYPE
	SYNTAX  Counter64
	MAX-ACCESS read-only
	STATUS current
	DESCRIPTION
        "
        Client Input Non Unicast Packets
        :This counter is increased each
        time a Non-Unicast packet is received
        on the client port  <Help>  This
        counter gives the number of Non-Unicast
        packets received on the client
         port
        "
	::= { pm10010mptMonupRmonNonunicastCounterClientInputEntry 2 }


pm10010mptMonupRmonNonunicastCounterClientInputErrorPortn OBJECT-TYPE
	SYNTAX  EkiOnOff
	MAX-ACCESS read-only
	STATUS current
	DESCRIPTION
        "
        Non Unicast Counter Error :This
        OID when set indicates the Non-Unicast
        counter value is invalid on client
        port
        "
	::= { pm10010mptMonupRmonNonunicastCounterClientInputEntry 3 }


pm10010mptMonupRmonNonunicastCounterClientInputOverloadPortn OBJECT-TYPE
	SYNTAX  EkiOnOff
	MAX-ACCESS read-only
	STATUS current
	DESCRIPTION
        "
        Non Unicast Counter Overload :This
        OID when set indicates a Non-Unicast
        counter overload on client port
        "
	::= { pm10010mptMonupRmonNonunicastCounterClientInputEntry 4 }


--- *********************************************************
---     TABLE for the pm10010mptMondownRmonBytesCounterClientOutput articles
--- *********************************************************

pm10010mptMondownRmonBytesCounterClientOutputTable OBJECT-TYPE
	SYNTAX  SEQUENCE OF Pm10010mptMondownRmonBytesCounterClientOutputEntry
	MAX-ACCESS not-accessible
	STATUS current
	DESCRIPTION
        "
        List of pm10010mptMondownRmonBytesCounterClientOutput
        Article
        "
	::= { pm10010mptMonClientRmonCounter 208 }


pm10010mptMondownRmonBytesCounterClientOutputEntry OBJECT-TYPE
	SYNTAX Pm10010mptMondownRmonBytesCounterClientOutputEntry
	MAX-ACCESS not-accessible
	STATUS current
	DESCRIPTION
        "
        Row definition for the pm10010mptMondownRmonBytesCounterClientOutput
        table
        "
	INDEX   { pm10010mptMondownRmonBytesCounterClientOutputIndex }
	::= { pm10010mptMondownRmonBytesCounterClientOutputTable 1 }


Pm10010mptMondownRmonBytesCounterClientOutputEntry ::=
	SEQUENCE {
	pm10010mptMondownRmonBytesCounterClientOutputIndex
		INTEGER,
	pm10010mptMondownRmonBytesCounterClientOutputValuePortn
		Counter64,
	pm10010mptMondownRmonBytesCounterClientOutputErrorPortn
		EkiOnOff,
	pm10010mptMondownRmonBytesCounterClientOutputOverloadPortn
		EkiOnOff
	}


pm10010mptMondownRmonBytesCounterClientOutputIndex OBJECT-TYPE
	SYNTAX  INTEGER(0..128)
	MAX-ACCESS  read-only
	STATUS current
	DESCRIPTION
        "
        Index definition for the pm10010mptMondownRmonBytesCounterClientOutput
        table
        "
	::= { pm10010mptMondownRmonBytesCounterClientOutputEntry 1 }


pm10010mptMondownRmonBytesCounterClientOutputValuePortn OBJECT-TYPE
	SYNTAX  Counter64
	MAX-ACCESS read-only
	STATUS current
	DESCRIPTION
        "
        Client Output Bytes :This counter
        is increased each time a data byte
        is transmitted on the client port
         <Help>  This counter gives the
        number of bytes transmitted on
         the client port
        "
	::= { pm10010mptMondownRmonBytesCounterClientOutputEntry 2 }


pm10010mptMondownRmonBytesCounterClientOutputErrorPortn OBJECT-TYPE
	SYNTAX  EkiOnOff
	MAX-ACCESS read-only
	STATUS current
	DESCRIPTION
        "
        Bytes Counter Error :This OID
         when set indicates the Bytes counter
        value is invalid on client port
        "
	::= { pm10010mptMondownRmonBytesCounterClientOutputEntry 3 }


pm10010mptMondownRmonBytesCounterClientOutputOverloadPortn OBJECT-TYPE
	SYNTAX  EkiOnOff
	MAX-ACCESS read-only
	STATUS current
	DESCRIPTION
        "
        Bytes Counter Overload :This OID
        when set indicates a Bytes counter
        overload on client port
        "
	::= { pm10010mptMondownRmonBytesCounterClientOutputEntry 4 }


--- *********************************************************
---     TABLE for the pm10010mptMondownRmonCrcErrorsCounterClientOutput articles
--- *********************************************************

pm10010mptMondownRmonCrcErrorsCounterClientOutputTable OBJECT-TYPE
	SYNTAX  SEQUENCE OF Pm10010mptMondownRmonCrcErrorsCounterClientOutputEntry
	MAX-ACCESS not-accessible
	STATUS current
	DESCRIPTION
        "
        List of pm10010mptMondownRmonCrcErrorsCounterClientOutput
        Article
        "
	::= { pm10010mptMonClientRmonCounter 224 }


pm10010mptMondownRmonCrcErrorsCounterClientOutputEntry OBJECT-TYPE
	SYNTAX Pm10010mptMondownRmonCrcErrorsCounterClientOutputEntry
	MAX-ACCESS not-accessible
	STATUS current
	DESCRIPTION
        "
        Row definition for the pm10010mptMondownRmonCrcErrorsCounterClientOutput
        table
        "
	INDEX   { pm10010mptMondownRmonCrcErrorsCounterClientOutputIndex }
	::= { pm10010mptMondownRmonCrcErrorsCounterClientOutputTable 1 }


Pm10010mptMondownRmonCrcErrorsCounterClientOutputEntry ::=
	SEQUENCE {
	pm10010mptMondownRmonCrcErrorsCounterClientOutputIndex
		INTEGER,
	pm10010mptMondownRmonCrcErrorsCounterClientOutputValuePortn
		Counter64,
	pm10010mptMondownRmonCrcErrorsCounterClientOutputErrorPortn
		EkiOnOff,
	pm10010mptMondownRmonCrcErrorsCounterClientOutputOverloadPortn
		EkiOnOff
	}


pm10010mptMondownRmonCrcErrorsCounterClientOutputIndex OBJECT-TYPE
	SYNTAX  INTEGER(0..128)
	MAX-ACCESS  read-only
	STATUS current
	DESCRIPTION
        "
        Index definition for the pm10010mptMondownRmonCrcErrorsCounterClientOutput
        table
        "
	::= { pm10010mptMondownRmonCrcErrorsCounterClientOutputEntry 1 }


pm10010mptMondownRmonCrcErrorsCounterClientOutputValuePortn OBJECT-TYPE
	SYNTAX  Counter64
	MAX-ACCESS read-only
	STATUS current
	DESCRIPTION
        "
        Client Output B1/CRC Errors :This
        counter is increased each time
         a B1/FCS error is detected on
         the transmit client port  <Help>
         This counter gives the number
         of B1/CRC Errors transmitted on
        the client port
        "
	::= { pm10010mptMondownRmonCrcErrorsCounterClientOutputEntry 2 }


pm10010mptMondownRmonCrcErrorsCounterClientOutputErrorPortn OBJECT-TYPE
	SYNTAX  EkiOnOff
	MAX-ACCESS read-only
	STATUS current
	DESCRIPTION
        "
        Output B1/CRC Errors Counter Error
        :This OID when set indicates the
        B1/FCS Errors counter value is
         invalid on client port
        "
	::= { pm10010mptMondownRmonCrcErrorsCounterClientOutputEntry 3 }


pm10010mptMondownRmonCrcErrorsCounterClientOutputOverloadPortn OBJECT-TYPE
	SYNTAX  EkiOnOff
	MAX-ACCESS read-only
	STATUS current
	DESCRIPTION
        "
        Output B1/CRC Errors Counter Overload
        :This OID when set indicates a
         B1/FCS Errors counter overload
        on client port
        "
	::= { pm10010mptMondownRmonCrcErrorsCounterClientOutputEntry 4 }


--- *********************************************************
---     TABLE for the pm10010mptMondownRmonPacketsCounterClientOutput articles
--- *********************************************************

pm10010mptMondownRmonPacketsCounterClientOutputTable OBJECT-TYPE
	SYNTAX  SEQUENCE OF Pm10010mptMondownRmonPacketsCounterClientOutputEntry
	MAX-ACCESS not-accessible
	STATUS current
	DESCRIPTION
        "
        List of pm10010mptMondownRmonPacketsCounterClientOutput
        Article
        "
	::= { pm10010mptMonClientRmonCounter 240 }


pm10010mptMondownRmonPacketsCounterClientOutputEntry OBJECT-TYPE
	SYNTAX Pm10010mptMondownRmonPacketsCounterClientOutputEntry
	MAX-ACCESS not-accessible
	STATUS current
	DESCRIPTION
        "
        Row definition for the pm10010mptMondownRmonPacketsCounterClientOutput
        table
        "
	INDEX   { pm10010mptMondownRmonPacketsCounterClientOutputIndex }
	::= { pm10010mptMondownRmonPacketsCounterClientOutputTable 1 }


Pm10010mptMondownRmonPacketsCounterClientOutputEntry ::=
	SEQUENCE {
	pm10010mptMondownRmonPacketsCounterClientOutputIndex
		INTEGER,
	pm10010mptMondownRmonPacketsCounterClientOutputValuePortn
		Counter64,
	pm10010mptMondownRmonPacketsCounterClientOutputErrorPortn
		EkiOnOff,
	pm10010mptMondownRmonPacketsCounterClientOutputOverloadPortn
		EkiOnOff
	}


pm10010mptMondownRmonPacketsCounterClientOutputIndex OBJECT-TYPE
	SYNTAX  INTEGER(0..128)
	MAX-ACCESS  read-only
	STATUS current
	DESCRIPTION
        "
        Index definition for the pm10010mptMondownRmonPacketsCounterClientOutput
        table
        "
	::= { pm10010mptMondownRmonPacketsCounterClientOutputEntry 1 }


pm10010mptMondownRmonPacketsCounterClientOutputValuePortn OBJECT-TYPE
	SYNTAX  Counter64
	MAX-ACCESS read-only
	STATUS current
	DESCRIPTION
        "
        Client Output Packets :This counter
        is increased each time a packet
        is transmitted on the client port
         <Help>  This counter gives the
        number of packets transmitted on
        the client port
        "
	::= { pm10010mptMondownRmonPacketsCounterClientOutputEntry 2 }


pm10010mptMondownRmonPacketsCounterClientOutputErrorPortn OBJECT-TYPE
	SYNTAX  EkiOnOff
	MAX-ACCESS read-only
	STATUS current
	DESCRIPTION
        "
        Packets Counter Error :This OID
        when set indicates the Packets
         counter value is invalid on client
        port
        "
	::= { pm10010mptMondownRmonPacketsCounterClientOutputEntry 3 }


pm10010mptMondownRmonPacketsCounterClientOutputOverloadPortn OBJECT-TYPE
	SYNTAX  EkiOnOff
	MAX-ACCESS read-only
	STATUS current
	DESCRIPTION
        "
        Packets Counter Overload :This
        OID when set indicates a Packets
        counter overload on client port
        "
	::= { pm10010mptMondownRmonPacketsCounterClientOutputEntry 4 }


--- *********************************************************
---     TABLE for the pm10010mptMondownRmonBroadcastCounterClientOutput articles
--- *********************************************************

pm10010mptMondownRmonBroadcastCounterClientOutputTable OBJECT-TYPE
	SYNTAX  SEQUENCE OF Pm10010mptMondownRmonBroadcastCounterClientOutputEntry
	MAX-ACCESS not-accessible
	STATUS current
	DESCRIPTION
        "
        List of pm10010mptMondownRmonBroadcastCounterClientOutput
        Article
        "
	::= { pm10010mptMonClientRmonCounter 256 }


pm10010mptMondownRmonBroadcastCounterClientOutputEntry OBJECT-TYPE
	SYNTAX Pm10010mptMondownRmonBroadcastCounterClientOutputEntry
	MAX-ACCESS not-accessible
	STATUS current
	DESCRIPTION
        "
        Row definition for the pm10010mptMondownRmonBroadcastCounterClientOutput
        table
        "
	INDEX   { pm10010mptMondownRmonBroadcastCounterClientOutputIndex }
	::= { pm10010mptMondownRmonBroadcastCounterClientOutputTable 1 }


Pm10010mptMondownRmonBroadcastCounterClientOutputEntry ::=
	SEQUENCE {
	pm10010mptMondownRmonBroadcastCounterClientOutputIndex
		INTEGER,
	pm10010mptMondownRmonBroadcastCounterClientOutputValuePortn
		Counter64,
	pm10010mptMondownRmonBroadcastCounterClientOutputErrorPortn
		EkiOnOff,
	pm10010mptMondownRmonBroadcastCounterClientOutputOverloadPortn
		EkiOnOff
	}


pm10010mptMondownRmonBroadcastCounterClientOutputIndex OBJECT-TYPE
	SYNTAX  INTEGER(0..128)
	MAX-ACCESS  read-only
	STATUS current
	DESCRIPTION
        "
        Index definition for the pm10010mptMondownRmonBroadcastCounterClientOutput
        table
        "
	::= { pm10010mptMondownRmonBroadcastCounterClientOutputEntry 1 }


pm10010mptMondownRmonBroadcastCounterClientOutputValuePortn OBJECT-TYPE
	SYNTAX  Counter64
	MAX-ACCESS read-only
	STATUS current
	DESCRIPTION
        "
        Client Output Broadcast Packets
        :This counter is increased each
        time a broadcast packet is transmitted
        on the client port  <Help>  This
        counter gives the number of Broadcast
        packets transmitted on the client
        port
        "
	::= { pm10010mptMondownRmonBroadcastCounterClientOutputEntry 2 }


pm10010mptMondownRmonBroadcastCounterClientOutputErrorPortn OBJECT-TYPE
	SYNTAX  EkiOnOff
	MAX-ACCESS read-only
	STATUS current
	DESCRIPTION
        "
        Broadcast Counter Error :This
         OID when set indicates the Broadcast
        counter value is invalid on client
        port
        "
	::= { pm10010mptMondownRmonBroadcastCounterClientOutputEntry 3 }


pm10010mptMondownRmonBroadcastCounterClientOutputOverloadPortn OBJECT-TYPE
	SYNTAX  EkiOnOff
	MAX-ACCESS read-only
	STATUS current
	DESCRIPTION
        "
        Broadcast Counter Overload :This
        OID when set indicates a Broadcast
        counter overload on client port
        "
	::= { pm10010mptMondownRmonBroadcastCounterClientOutputEntry 4 }


--- *********************************************************
---     TABLE for the pm10010mptMondownRmonMulticastCounterClientOutput articles
--- *********************************************************

pm10010mptMondownRmonMulticastCounterClientOutputTable OBJECT-TYPE
	SYNTAX  SEQUENCE OF Pm10010mptMondownRmonMulticastCounterClientOutputEntry
	MAX-ACCESS not-accessible
	STATUS current
	DESCRIPTION
        "
        List of pm10010mptMondownRmonMulticastCounterClientOutput
        Article
        "
	::= { pm10010mptMonClientRmonCounter 272 }


pm10010mptMondownRmonMulticastCounterClientOutputEntry OBJECT-TYPE
	SYNTAX Pm10010mptMondownRmonMulticastCounterClientOutputEntry
	MAX-ACCESS not-accessible
	STATUS current
	DESCRIPTION
        "
        Row definition for the pm10010mptMondownRmonMulticastCounterClientOutput
        table
        "
	INDEX   { pm10010mptMondownRmonMulticastCounterClientOutputIndex }
	::= { pm10010mptMondownRmonMulticastCounterClientOutputTable 1 }


Pm10010mptMondownRmonMulticastCounterClientOutputEntry ::=
	SEQUENCE {
	pm10010mptMondownRmonMulticastCounterClientOutputIndex
		INTEGER,
	pm10010mptMondownRmonMulticastCounterClientOutputValuePortn
		Counter64,
	pm10010mptMondownRmonMulticastCounterClientOutputErrorPortn
		EkiOnOff,
	pm10010mptMondownRmonMulticastCounterClientOutputOverloadPortn
		EkiOnOff
	}


pm10010mptMondownRmonMulticastCounterClientOutputIndex OBJECT-TYPE
	SYNTAX  INTEGER(0..128)
	MAX-ACCESS  read-only
	STATUS current
	DESCRIPTION
        "
        Index definition for the pm10010mptMondownRmonMulticastCounterClientOutput
        table
        "
	::= { pm10010mptMondownRmonMulticastCounterClientOutputEntry 1 }


pm10010mptMondownRmonMulticastCounterClientOutputValuePortn OBJECT-TYPE
	SYNTAX  Counter64
	MAX-ACCESS read-only
	STATUS current
	DESCRIPTION
        "
        Client Output Multicast Packets
        :This counter is increased each
        time a Multicast packet is transmitted
        on the client port  <Help>  This
        counter gives the number of Multicast
        packets transmitted on the client
        port
        "
	::= { pm10010mptMondownRmonMulticastCounterClientOutputEntry 2 }


pm10010mptMondownRmonMulticastCounterClientOutputErrorPortn OBJECT-TYPE
	SYNTAX  EkiOnOff
	MAX-ACCESS read-only
	STATUS current
	DESCRIPTION
        "
        Multicast Counter Error :This
         OID when set indicates the Multicast
        counter value is invalid on client
        port
        "
	::= { pm10010mptMondownRmonMulticastCounterClientOutputEntry 3 }


pm10010mptMondownRmonMulticastCounterClientOutputOverloadPortn OBJECT-TYPE
	SYNTAX  EkiOnOff
	MAX-ACCESS read-only
	STATUS current
	DESCRIPTION
        "
        Multicast Counter Overload :This
        OID when set indicates a Multicast
        counter overload on client port
        "
	::= { pm10010mptMondownRmonMulticastCounterClientOutputEntry 4 }


--- *********************************************************
---     TABLE for the pm10010mptMondownRmonPauseFrameCounterClientOutput articles
--- *********************************************************

pm10010mptMondownRmonPauseFrameCounterClientOutputTable OBJECT-TYPE
	SYNTAX  SEQUENCE OF Pm10010mptMondownRmonPauseFrameCounterClientOutputEntry
	MAX-ACCESS not-accessible
	STATUS current
	DESCRIPTION
        "
        List of pm10010mptMondownRmonPauseFrameCounterClientOutput
        Article
        "
	::= { pm10010mptMonClientRmonCounter 288 }


pm10010mptMondownRmonPauseFrameCounterClientOutputEntry OBJECT-TYPE
	SYNTAX Pm10010mptMondownRmonPauseFrameCounterClientOutputEntry
	MAX-ACCESS not-accessible
	STATUS current
	DESCRIPTION
        "
        Row definition for the pm10010mptMondownRmonPauseFrameCounterClientOutput
        table
        "
	INDEX   { pm10010mptMondownRmonPauseFrameCounterClientOutputIndex }
	::= { pm10010mptMondownRmonPauseFrameCounterClientOutputTable 1 }


Pm10010mptMondownRmonPauseFrameCounterClientOutputEntry ::=
	SEQUENCE {
	pm10010mptMondownRmonPauseFrameCounterClientOutputIndex
		INTEGER,
	pm10010mptMondownRmonPauseFrameCounterClientOutputValuePortn
		Counter64,
	pm10010mptMondownRmonPauseFrameCounterClientOutputErrorPortn
		EkiOnOff,
	pm10010mptMondownRmonPauseFrameCounterClientOutputOverloadPortn
		EkiOnOff
	}


pm10010mptMondownRmonPauseFrameCounterClientOutputIndex OBJECT-TYPE
	SYNTAX  INTEGER(0..128)
	MAX-ACCESS  read-only
	STATUS current
	DESCRIPTION
        "
        Index definition for the pm10010mptMondownRmonPauseFrameCounterClientOutput
        table
        "
	::= { pm10010mptMondownRmonPauseFrameCounterClientOutputEntry 1 }


pm10010mptMondownRmonPauseFrameCounterClientOutputValuePortn OBJECT-TYPE
	SYNTAX  Counter64
	MAX-ACCESS read-only
	STATUS current
	DESCRIPTION
        "
        Client Output Pause Frames :This
        counter is increased each time
         a Pause frame is transmitted on
        the client port  <Help>  This counter
        gives the number of Pause frames
        transmitted on the client port
        "
	::= { pm10010mptMondownRmonPauseFrameCounterClientOutputEntry 2 }


pm10010mptMondownRmonPauseFrameCounterClientOutputErrorPortn OBJECT-TYPE
	SYNTAX  EkiOnOff
	MAX-ACCESS read-only
	STATUS current
	DESCRIPTION
        "
        Pause Counter Error :This OID
         when set indicates the Pause counter
        value is invalid on client port
        "
	::= { pm10010mptMondownRmonPauseFrameCounterClientOutputEntry 3 }


pm10010mptMondownRmonPauseFrameCounterClientOutputOverloadPortn OBJECT-TYPE
	SYNTAX  EkiOnOff
	MAX-ACCESS read-only
	STATUS current
	DESCRIPTION
        "
        Pause Counter Overload :This OID
        when set indicates a Pause counter
        overload on client port
        "
	::= { pm10010mptMondownRmonPauseFrameCounterClientOutputEntry 4 }


--- *********************************************************
---     TABLE for the pm10010mptMondownRmonUnicastCounterClientOutput articles
--- *********************************************************

pm10010mptMondownRmonUnicastCounterClientOutputTable OBJECT-TYPE
	SYNTAX  SEQUENCE OF Pm10010mptMondownRmonUnicastCounterClientOutputEntry
	MAX-ACCESS not-accessible
	STATUS current
	DESCRIPTION
        "
        List of pm10010mptMondownRmonUnicastCounterClientOutput
        Article
        "
	::= { pm10010mptMonClientRmonCounter 352 }


pm10010mptMondownRmonUnicastCounterClientOutputEntry OBJECT-TYPE
	SYNTAX Pm10010mptMondownRmonUnicastCounterClientOutputEntry
	MAX-ACCESS not-accessible
	STATUS current
	DESCRIPTION
        "
        Row definition for the pm10010mptMondownRmonUnicastCounterClientOutput
        table
        "
	INDEX   { pm10010mptMondownRmonUnicastCounterClientOutputIndex }
	::= { pm10010mptMondownRmonUnicastCounterClientOutputTable 1 }


Pm10010mptMondownRmonUnicastCounterClientOutputEntry ::=
	SEQUENCE {
	pm10010mptMondownRmonUnicastCounterClientOutputIndex
		INTEGER,
	pm10010mptMondownRmonUnicastCounterClientOutputValuePortn
		Counter64,
	pm10010mptMondownRmonUnicastCounterClientOutputErrorPortn
		EkiOnOff,
	pm10010mptMondownRmonUnicastCounterClientOutputOverloadPortn
		EkiOnOff
	}


pm10010mptMondownRmonUnicastCounterClientOutputIndex OBJECT-TYPE
	SYNTAX  INTEGER(0..128)
	MAX-ACCESS  read-only
	STATUS current
	DESCRIPTION
        "
        Index definition for the pm10010mptMondownRmonUnicastCounterClientOutput
        table
        "
	::= { pm10010mptMondownRmonUnicastCounterClientOutputEntry 1 }


pm10010mptMondownRmonUnicastCounterClientOutputValuePortn OBJECT-TYPE
	SYNTAX  Counter64
	MAX-ACCESS read-only
	STATUS current
	DESCRIPTION
        "
        Client Output Unicast Packets
         :This counter is increased each
        time a Unicast packet is transmitted
        on the client port  <Help>  This
        counter gives the number of Unicast
        packets transmitted on the client
        port
        "
	::= { pm10010mptMondownRmonUnicastCounterClientOutputEntry 2 }


pm10010mptMondownRmonUnicastCounterClientOutputErrorPortn OBJECT-TYPE
	SYNTAX  EkiOnOff
	MAX-ACCESS read-only
	STATUS current
	DESCRIPTION
        "
        Unicast Counter Error :This OID
        when set indicates the Unicast
         counter value is invalid on client
        port
        "
	::= { pm10010mptMondownRmonUnicastCounterClientOutputEntry 3 }


pm10010mptMondownRmonUnicastCounterClientOutputOverloadPortn OBJECT-TYPE
	SYNTAX  EkiOnOff
	MAX-ACCESS read-only
	STATUS current
	DESCRIPTION
        "
        Unicast Counter Overload :This
        OID when set indicates a Unicast
        counter overload on client port
        "
	::= { pm10010mptMondownRmonUnicastCounterClientOutputEntry 4 }


--- *********************************************************
---     TABLE for the pm10010mptMondownRmonNonunicastCounterClientOutput articles
--- *********************************************************

pm10010mptMondownRmonNonunicastCounterClientOutputTable OBJECT-TYPE
	SYNTAX  SEQUENCE OF Pm10010mptMondownRmonNonunicastCounterClientOutputEntry
	MAX-ACCESS not-accessible
	STATUS current
	DESCRIPTION
        "
        List of pm10010mptMondownRmonNonunicastCounterClientOutput
        Article
        "
	::= { pm10010mptMonClientRmonCounter 368 }


pm10010mptMondownRmonNonunicastCounterClientOutputEntry OBJECT-TYPE
	SYNTAX Pm10010mptMondownRmonNonunicastCounterClientOutputEntry
	MAX-ACCESS not-accessible
	STATUS current
	DESCRIPTION
        "
        Row definition for the pm10010mptMondownRmonNonunicastCounterClientOutput
        table
        "
	INDEX   { pm10010mptMondownRmonNonunicastCounterClientOutputIndex }
	::= { pm10010mptMondownRmonNonunicastCounterClientOutputTable 1 }


Pm10010mptMondownRmonNonunicastCounterClientOutputEntry ::=
	SEQUENCE {
	pm10010mptMondownRmonNonunicastCounterClientOutputIndex
		INTEGER,
	pm10010mptMondownRmonNonunicastCounterClientOutputValuePortn
		Counter64,
	pm10010mptMondownRmonNonunicastCounterClientOutputErrorPortn
		EkiOnOff,
	pm10010mptMondownRmonNonunicastCounterClientOutputOverloadPortn
		EkiOnOff
	}


pm10010mptMondownRmonNonunicastCounterClientOutputIndex OBJECT-TYPE
	SYNTAX  INTEGER(0..128)
	MAX-ACCESS  read-only
	STATUS current
	DESCRIPTION
        "
        Index definition for the pm10010mptMondownRmonNonunicastCounterClientOutput
        table
        "
	::= { pm10010mptMondownRmonNonunicastCounterClientOutputEntry 1 }


pm10010mptMondownRmonNonunicastCounterClientOutputValuePortn OBJECT-TYPE
	SYNTAX  Counter64
	MAX-ACCESS read-only
	STATUS current
	DESCRIPTION
        "
        Client Output Non Unicast Packets
        :This counter is increased each
        time a Non-Unicast packet is transmitted
        on the client port  <Help>  This
        counter gives the number of Non-Unicast
        packets transmitted on the client
        port
        "
	::= { pm10010mptMondownRmonNonunicastCounterClientOutputEntry 2 }


pm10010mptMondownRmonNonunicastCounterClientOutputErrorPortn OBJECT-TYPE
	SYNTAX  EkiOnOff
	MAX-ACCESS read-only
	STATUS current
	DESCRIPTION
        "
        Non Unicast Counter Error :This
        OID when set indicates the Non-Unicast
        counter value is invalid on client
        port
        "
	::= { pm10010mptMondownRmonNonunicastCounterClientOutputEntry 3 }


pm10010mptMondownRmonNonunicastCounterClientOutputOverloadPortn OBJECT-TYPE
	SYNTAX  EkiOnOff
	MAX-ACCESS read-only
	STATUS current
	DESCRIPTION
        "
        Non Unicast Counter Overload :This
        OID when set indicates a Non-Unicast
        counter overload on client port
        "
	::= { pm10010mptMondownRmonNonunicastCounterClientOutputEntry 4 }







--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pm10010mptMesrsynth0 OBJECT-TYPE
	  SYNTAX EkiMeasureType
	  MAX-ACCESS read-only
	  STATUS deprecated
	  DESCRIPTION
        "
        Not Used :
        "
	  ::= { pm10010mptMesrOther 0 }



pm10010mptMesrsynth1 OBJECT-TYPE
	  SYNTAX EkiMeasureType
	  MAX-ACCESS read-only
	  STATUS deprecated
	  DESCRIPTION
        "
        Not Used :
        "
	  ::= { pm10010mptMesrOther 1 }



--- *****************************************************
---     LEAF for the pmIntervalNumber article
--- *****************************************************

pm10010mptMesrpmIntervalNumber OBJECT-TYPE
	  SYNTAX Unsigned32 (0..65535)
	  MAX-ACCESS read-only
	  STATUS current
	  DESCRIPTION
        "
        PM Interval Counter :
        "
	  ::= { pm10010mptMesrOther 7 }



--- *****************************************************
---     LEAF for the clientCfpTemp article
--- *****************************************************

pm10010mptMesrclientCfpTemp OBJECT-TYPE
	  SYNTAX Unsigned32 (0..65535)
	  MAX-ACCESS read-only
	  STATUS current
	  DESCRIPTION
        "
        Client Trscv Temperature :This
        OID gives the temperature value
        of the Client Transceiver, read
        from the DDM (Digital Diagnostic
        Monitoring) (Temperature = AV/256)
        (Unit = C) <Help> This Measure
         gives the temperature value of
        the Client Transceiver
        "
	  ::= { pm10010mptMesrClient 8 }



--- *****************************************************
---     LEAF for the clientCfp3v3Voltage article
--- *****************************************************

pm10010mptMesrclientCfp3v3Voltage OBJECT-TYPE
	  SYNTAX Unsigned32 (0..65535)
	  MAX-ACCESS read-only
	  STATUS current
	  DESCRIPTION
        "
        Client Trscv Voltage :This OID
        gives the 3V3 voltage value of
         the Client Transceiver, read from
        the DDM (Digital Diagnostic Monitoring)
         (Voltage = AV/1000) (Unit = V)
        <Help> This Measure gives the 3V3
        voltage value of the Client Transceiver
        "
	  ::= { pm10010mptMesrClient 9 }



--- *****************************************************
---     LEAF for the clientSoaBiasCurrent article
--- *****************************************************

pm10010mptMesrclientSoaBiasCurrent OBJECT-TYPE
	  SYNTAX Unsigned32 (0..65535)
	  MAX-ACCESS read-only
	  STATUS current
	  DESCRIPTION
        "
        Client Trscv SOA Bias :This OID
        gives the SOA bias value of the
        Client Transceiver, read from the
        DDM (Digital Diagnostic Monitoring)
         (Bias = AV/500) (Unit = mA) <Help>
        This Measure gives the SOA bias
        value of the Client Transceiver
        "
	  ::= { pm10010mptMesrClient 10 }



--- *****************************************************
---     LEAF for the lineMsaTemp article
--- *****************************************************

pm10010mptMesrlineMsaTemp OBJECT-TYPE
	  SYNTAX Unsigned32 (0..65535)
	  MAX-ACCESS read-only
	  STATUS current
	  DESCRIPTION
        "
        Line Trscv Temperature :This OID
        gives the temperature value of
         the Line Transceiver, read from
        the DDM (Digital Diagnostic Monitoring)
         (Temperature = AV/256) (Unit =
        C) <Help> This Measure gives the
        temperature value of the Line Transceiver.This
        temperature must remain below 95°C
        for proper operation
        "
	  ::= { pm10010mptMesrLine 12 }



--- *****************************************************
---     LEAF for the lineMsa3v3Voltage article
--- *****************************************************

pm10010mptMesrlineMsa3v3Voltage OBJECT-TYPE
	  SYNTAX Unsigned32 (0..65535)
	  MAX-ACCESS read-only
	  STATUS current
	  DESCRIPTION
        "
        Line Trscv Voltage :This OID gives
        the 3V3 voltage value of the Line
        Transceiver, read from the DDM
         (Digital Diagnostic Monitoring)
        (Voltage = AV/1000) (Unit = V)
         <Help> This Measure gives the
         3V3 voltage value of the Line
         Transceiver
        "
	  ::= { pm10010mptMesrLine 13 }



--- *****************************************************
---     LEAF for the lineSoaBiasCurrent article
--- *****************************************************

pm10010mptMesrlineSoaBiasCurrent OBJECT-TYPE
	  SYNTAX Unsigned32 (0..65535)
	  MAX-ACCESS read-only
	  STATUS current
	  DESCRIPTION
        "
        Line Trscv SOA Bias :This OID
         gives the SOA bias value of the
        Line Transceiver,read from the
         DDM (Digital Diagnostic Monitoring)
         (Bias = AV/500) (Unit = mA) <Help>
        This Measure gives the SOA bias
        value of the Line Transceiver
        "
	  ::= { pm10010mptMesrLine 14 }



--- *********************************************************
---     TABLE for the pm10010mptMesrclientNetTxTemp articles
--- *********************************************************

pm10010mptMesrclientNetTxTempTable OBJECT-TYPE
	SYNTAX  SEQUENCE OF Pm10010mptMesrclientNetTxTempEntry
	MAX-ACCESS not-accessible
	STATUS current
	DESCRIPTION
        "
        List of pm10010mptMesrclientNetTxTemp
        Article
        "
	::= { pm10010mptMesrClient 16 }


pm10010mptMesrclientNetTxTempEntry OBJECT-TYPE
	SYNTAX Pm10010mptMesrclientNetTxTempEntry
	MAX-ACCESS not-accessible
	STATUS current
	DESCRIPTION
        "
        Row definition for the pm10010mptMesrclientNetTxTemp
        table
        "
	INDEX   { pm10010mptMesrclientNetTxTempIndex }
	::= { pm10010mptMesrclientNetTxTempTable 1 }


Pm10010mptMesrclientNetTxTempEntry ::=
	SEQUENCE {
	pm10010mptMesrclientNetTxTempIndex
		INTEGER,
	pm10010mptMesrclientNetTxTempPortn
		INTEGER
	}


pm10010mptMesrclientNetTxTempIndex OBJECT-TYPE
	SYNTAX  INTEGER(0..128)
	MAX-ACCESS  read-only
	STATUS current
	DESCRIPTION
        "
        Index definition for the pm10010mptMesrclientNetTxTemp
        table
        "
	::= { pm10010mptMesrclientNetTxTempEntry 1 }


pm10010mptMesrclientNetTxTempPortn OBJECT-TYPE
	SYNTAX  INTEGER (0..65535)
	MAX-ACCESS read-only
	STATUS current
	DESCRIPTION
        "
        Client Trscv Temperature :This
        OID gives the Laser temperature
        value of the Client Transceiver,
        read from the DDM (Digital Diagnostic
        Monitoring) (Temperature = AV/256)
        (Unit = C) <Help> This Measure
         gives the Laser temperature value
        of the Client Transceiver
        "
	::= { pm10010mptMesrclientNetTxTempEntry 2 }


--- *********************************************************
---     TABLE for the pm10010mptMesrclientNetTxBias articles
--- *********************************************************

pm10010mptMesrclientNetTxBiasTable OBJECT-TYPE
	SYNTAX  SEQUENCE OF Pm10010mptMesrclientNetTxBiasEntry
	MAX-ACCESS not-accessible
	STATUS current
	DESCRIPTION
        "
        List of pm10010mptMesrclientNetTxBias
        Article
        "
	::= { pm10010mptMesrClient 32 }


pm10010mptMesrclientNetTxBiasEntry OBJECT-TYPE
	SYNTAX Pm10010mptMesrclientNetTxBiasEntry
	MAX-ACCESS not-accessible
	STATUS current
	DESCRIPTION
        "
        Row definition for the pm10010mptMesrclientNetTxBias
        table
        "
	INDEX   { pm10010mptMesrclientNetTxBiasIndex }
	::= { pm10010mptMesrclientNetTxBiasTable 1 }


Pm10010mptMesrclientNetTxBiasEntry ::=
	SEQUENCE {
	pm10010mptMesrclientNetTxBiasIndex
		INTEGER,
	pm10010mptMesrclientNetTxBiasPortn
		INTEGER
	}


pm10010mptMesrclientNetTxBiasIndex OBJECT-TYPE
	SYNTAX  INTEGER(0..128)
	MAX-ACCESS  read-only
	STATUS current
	DESCRIPTION
        "
        Index definition for the pm10010mptMesrclientNetTxBias
        table
        "
	::= { pm10010mptMesrclientNetTxBiasEntry 1 }


pm10010mptMesrclientNetTxBiasPortn OBJECT-TYPE
	SYNTAX  INTEGER (0..65535)
	MAX-ACCESS read-only
	STATUS current
	DESCRIPTION
        "
        Client Trscv Laser Bias :This
         OID gives the Laser bias value
        of the Client Transceiver, read
        from the DDM (Digital Diagnostic
        Monitoring) (Bias = AV/500) (Unit
        = mA) <Help> This Measure gives
        the Laser bias value of the Client
        Transceiver
        "
	::= { pm10010mptMesrclientNetTxBiasEntry 2 }


--- *********************************************************
---     TABLE for the pm10010mptMesrclientNetTxPwr articles
--- *********************************************************

pm10010mptMesrclientNetTxPwrTable OBJECT-TYPE
	SYNTAX  SEQUENCE OF Pm10010mptMesrclientNetTxPwrEntry
	MAX-ACCESS not-accessible
	STATUS current
	DESCRIPTION
        "
        List of pm10010mptMesrclientNetTxPwr
        Article
        "
	::= { pm10010mptMesrClient 48 }


pm10010mptMesrclientNetTxPwrEntry OBJECT-TYPE
	SYNTAX Pm10010mptMesrclientNetTxPwrEntry
	MAX-ACCESS not-accessible
	STATUS current
	DESCRIPTION
        "
        Row definition for the pm10010mptMesrclientNetTxPwr
        table
        "
	INDEX   { pm10010mptMesrclientNetTxPwrIndex }
	::= { pm10010mptMesrclientNetTxPwrTable 1 }


Pm10010mptMesrclientNetTxPwrEntry ::=
	SEQUENCE {
	pm10010mptMesrclientNetTxPwrIndex
		INTEGER,
	pm10010mptMesrclientNetTxPwrPortn
		INTEGER
	}


pm10010mptMesrclientNetTxPwrIndex OBJECT-TYPE
	SYNTAX  INTEGER(0..128)
	MAX-ACCESS  read-only
	STATUS current
	DESCRIPTION
        "
        Index definition for the pm10010mptMesrclientNetTxPwr
        table
        "
	::= { pm10010mptMesrclientNetTxPwrEntry 1 }


pm10010mptMesrclientNetTxPwrPortn OBJECT-TYPE
	SYNTAX  INTEGER (0..65535)
	MAX-ACCESS read-only
	STATUS current
	DESCRIPTION
        "
        Client Trscv Tx Power :This OID
        gives the transmit power value
         of the Client Transceiver, read
        from the DDM (Digital Diagnostic
        Monitoring) (Power = 10*log(AV)-40)
        (Unit = dBm) <Help> This Measure
        gives the transmit power value
         of the Client Transceiver
        "
	::= { pm10010mptMesrclientNetTxPwrEntry 2 }


--- *********************************************************
---     TABLE for the pm10010mptMesrclientNetRxPwr articles
--- *********************************************************

pm10010mptMesrclientNetRxPwrTable OBJECT-TYPE
	SYNTAX  SEQUENCE OF Pm10010mptMesrclientNetRxPwrEntry
	MAX-ACCESS not-accessible
	STATUS current
	DESCRIPTION
        "
        List of pm10010mptMesrclientNetRxPwr
        Article
        "
	::= { pm10010mptMesrClient 64 }


pm10010mptMesrclientNetRxPwrEntry OBJECT-TYPE
	SYNTAX Pm10010mptMesrclientNetRxPwrEntry
	MAX-ACCESS not-accessible
	STATUS current
	DESCRIPTION
        "
        Row definition for the pm10010mptMesrclientNetRxPwr
        table
        "
	INDEX   { pm10010mptMesrclientNetRxPwrIndex }
	::= { pm10010mptMesrclientNetRxPwrTable 1 }


Pm10010mptMesrclientNetRxPwrEntry ::=
	SEQUENCE {
	pm10010mptMesrclientNetRxPwrIndex
		INTEGER,
	pm10010mptMesrclientNetRxPwrPortn
		INTEGER
	}


pm10010mptMesrclientNetRxPwrIndex OBJECT-TYPE
	SYNTAX  INTEGER(0..128)
	MAX-ACCESS  read-only
	STATUS current
	DESCRIPTION
        "
        Index definition for the pm10010mptMesrclientNetRxPwr
        table
        "
	::= { pm10010mptMesrclientNetRxPwrEntry 1 }


pm10010mptMesrclientNetRxPwrPortn OBJECT-TYPE
	SYNTAX  INTEGER (0..65535)
	MAX-ACCESS read-only
	STATUS current
	DESCRIPTION
        "
        Client Trscv Rx Power :This OID
        gives the receive power value of
        the Client Transceiver, read in
        the DDM (Digital Diagnostic Monitoring)
        (Power = 10*log(AV)-40) (Unit =
        dBm) <Help> This Measure gives
         the receive power value of the
        Client Transceiver
        "
	::= { pm10010mptMesrclientNetRxPwrEntry 2 }


--- *********************************************************
---     TABLE for the pm10010mptMesrlineNetTxLaserOutputPwr articles
--- *********************************************************

pm10010mptMesrlineNetTxLaserOutputPwrTable OBJECT-TYPE
	SYNTAX  SEQUENCE OF Pm10010mptMesrlineNetTxLaserOutputPwrEntry
	MAX-ACCESS not-accessible
	STATUS current
	DESCRIPTION
        "
        List of pm10010mptMesrlineNetTxLaserOutputPwr
        Article
        "
	::= { pm10010mptMesrLine 80 }


pm10010mptMesrlineNetTxLaserOutputPwrEntry OBJECT-TYPE
	SYNTAX Pm10010mptMesrlineNetTxLaserOutputPwrEntry
	MAX-ACCESS not-accessible
	STATUS current
	DESCRIPTION
        "
        Row definition for the pm10010mptMesrlineNetTxLaserOutputPwr
        table
        "
	INDEX   { pm10010mptMesrlineNetTxLaserOutputPwrIndex }
	::= { pm10010mptMesrlineNetTxLaserOutputPwrTable 1 }


Pm10010mptMesrlineNetTxLaserOutputPwrEntry ::=
	SEQUENCE {
	pm10010mptMesrlineNetTxLaserOutputPwrIndex
		INTEGER,
	pm10010mptMesrlineNetTxLaserOutputPwrPortn
		INTEGER
	}


pm10010mptMesrlineNetTxLaserOutputPwrIndex OBJECT-TYPE
	SYNTAX  INTEGER(0..128)
	MAX-ACCESS  read-only
	STATUS current
	DESCRIPTION
        "
        Index definition for the pm10010mptMesrlineNetTxLaserOutputPwr
        table
        "
	::= { pm10010mptMesrlineNetTxLaserOutputPwrEntry 1 }


pm10010mptMesrlineNetTxLaserOutputPwrPortn OBJECT-TYPE
	SYNTAX  INTEGER (0..65535)
	MAX-ACCESS read-only
	STATUS current
	DESCRIPTION
        "
        Current Line Trscv Tx Power :This
        OID gives the Tx Laser transmit
        power value of the Line Transceiver,
        read in the DDM (Digital Diagnostic
        Monitoring) (Power = AV/100) (Unit
        = dBm) <Help> This Measure gives
        the Tx Laser transmit power value
        of the Line Transceiver
        "
	::= { pm10010mptMesrlineNetTxLaserOutputPwrEntry 2 }


--- *********************************************************
---     TABLE for the pm10010mptMesrlineNetTxLaserTemp articles
--- *********************************************************

pm10010mptMesrlineNetTxLaserTempTable OBJECT-TYPE
	SYNTAX  SEQUENCE OF Pm10010mptMesrlineNetTxLaserTempEntry
	MAX-ACCESS not-accessible
	STATUS current
	DESCRIPTION
        "
        List of pm10010mptMesrlineNetTxLaserTemp
        Article
        "
	::= { pm10010mptMesrLine 96 }


pm10010mptMesrlineNetTxLaserTempEntry OBJECT-TYPE
	SYNTAX Pm10010mptMesrlineNetTxLaserTempEntry
	MAX-ACCESS not-accessible
	STATUS current
	DESCRIPTION
        "
        Row definition for the pm10010mptMesrlineNetTxLaserTemp
        table
        "
	INDEX   { pm10010mptMesrlineNetTxLaserTempIndex }
	::= { pm10010mptMesrlineNetTxLaserTempTable 1 }


Pm10010mptMesrlineNetTxLaserTempEntry ::=
	SEQUENCE {
	pm10010mptMesrlineNetTxLaserTempIndex
		INTEGER,
	pm10010mptMesrlineNetTxLaserTempPortn
		INTEGER
	}


pm10010mptMesrlineNetTxLaserTempIndex OBJECT-TYPE
	SYNTAX  INTEGER(0..128)
	MAX-ACCESS  read-only
	STATUS current
	DESCRIPTION
        "
        Index definition for the pm10010mptMesrlineNetTxLaserTemp
        table
        "
	::= { pm10010mptMesrlineNetTxLaserTempEntry 1 }


pm10010mptMesrlineNetTxLaserTempPortn OBJECT-TYPE
	SYNTAX  INTEGER (0..65535)
	MAX-ACCESS read-only
	STATUS current
	DESCRIPTION
        "
        Current Line Trscv Tx Laser Temperature
        :This OID gives the Tx Laser Temperature
        value of the Line Transceiver,
         read from the DDM (Digital Diagnostic
        Monitoring) (Temperature = AV/256)
        (Unit = C) <Help> This Measure
         gives the Tx Laser Temperature
        value of the Line Transceiver
        "
	::= { pm10010mptMesrlineNetTxLaserTempEntry 2 }


--- *********************************************************
---     TABLE for the pm10010mptMesrlineNetTxBiasCurrent articles
--- *********************************************************

pm10010mptMesrlineNetTxBiasCurrentTable OBJECT-TYPE
	SYNTAX  SEQUENCE OF Pm10010mptMesrlineNetTxBiasCurrentEntry
	MAX-ACCESS not-accessible
	STATUS current
	DESCRIPTION
        "
        List of pm10010mptMesrlineNetTxBiasCurrent
        Article
        "
	::= { pm10010mptMesrLine 112 }


pm10010mptMesrlineNetTxBiasCurrentEntry OBJECT-TYPE
	SYNTAX Pm10010mptMesrlineNetTxBiasCurrentEntry
	MAX-ACCESS not-accessible
	STATUS current
	DESCRIPTION
        "
        Row definition for the pm10010mptMesrlineNetTxBiasCurrent
        table
        "
	INDEX   { pm10010mptMesrlineNetTxBiasCurrentIndex }
	::= { pm10010mptMesrlineNetTxBiasCurrentTable 1 }


Pm10010mptMesrlineNetTxBiasCurrentEntry ::=
	SEQUENCE {
	pm10010mptMesrlineNetTxBiasCurrentIndex
		INTEGER,
	pm10010mptMesrlineNetTxBiasCurrentPortn
		INTEGER
	}


pm10010mptMesrlineNetTxBiasCurrentIndex OBJECT-TYPE
	SYNTAX  INTEGER(0..128)
	MAX-ACCESS  read-only
	STATUS current
	DESCRIPTION
        "
        Index definition for the pm10010mptMesrlineNetTxBiasCurrent
        table
        "
	::= { pm10010mptMesrlineNetTxBiasCurrentEntry 1 }


pm10010mptMesrlineNetTxBiasCurrentPortn OBJECT-TYPE
	SYNTAX  INTEGER (0..65535)
	MAX-ACCESS read-only
	STATUS current
	DESCRIPTION
        "
        Current Line Trscv Tx Laser Bias
        :This OID gives the Tx Laser Bias
        value of the Line Transceiver,
         read from the DDM (Digital Diagnostic
        Monitoring) (Bias = AV/10) (Unit
        = mA) <Help> This Measure gives
        the Tx Laser Bias value of the
         Line Transceiver
        "
	::= { pm10010mptMesrlineNetTxBiasCurrentEntry 2 }


--- *********************************************************
---     TABLE for the pm10010mptMesrlineNetRxInputPwr articles
--- *********************************************************

pm10010mptMesrlineNetRxInputPwrTable OBJECT-TYPE
	SYNTAX  SEQUENCE OF Pm10010mptMesrlineNetRxInputPwrEntry
	MAX-ACCESS not-accessible
	STATUS current
	DESCRIPTION
        "
        List of pm10010mptMesrlineNetRxInputPwr
        Article
        "
	::= { pm10010mptMesrLine 128 }


pm10010mptMesrlineNetRxInputPwrEntry OBJECT-TYPE
	SYNTAX Pm10010mptMesrlineNetRxInputPwrEntry
	MAX-ACCESS not-accessible
	STATUS current
	DESCRIPTION
        "
        Row definition for the pm10010mptMesrlineNetRxInputPwr
        table
        "
	INDEX   { pm10010mptMesrlineNetRxInputPwrIndex }
	::= { pm10010mptMesrlineNetRxInputPwrTable 1 }


Pm10010mptMesrlineNetRxInputPwrEntry ::=
	SEQUENCE {
	pm10010mptMesrlineNetRxInputPwrIndex
		INTEGER,
	pm10010mptMesrlineNetRxInputPwrPortn
		INTEGER
	}


pm10010mptMesrlineNetRxInputPwrIndex OBJECT-TYPE
	SYNTAX  INTEGER(0..128)
	MAX-ACCESS  read-only
	STATUS current
	DESCRIPTION
        "
        Index definition for the pm10010mptMesrlineNetRxInputPwr
        table
        "
	::= { pm10010mptMesrlineNetRxInputPwrEntry 1 }


pm10010mptMesrlineNetRxInputPwrPortn OBJECT-TYPE
	SYNTAX  INTEGER (0..65535)
	MAX-ACCESS read-only
	STATUS current
	DESCRIPTION
        "
        Current Line Trscv Rx Power :This
        OID gives the Receive power value
        of the Line Transceiver, read in
        the DDM (Digital Diagnostic Monitoring)
        (Power = AV/100) (Unit = dBm) <Help>
        This Measure gives the Receive
         power value of the Line Transceiver
        "
	::= { pm10010mptMesrlineNetRxInputPwrEntry 2 }


--- *********************************************************
---     TABLE for the pm10010mptMesrlineResidualChromaticDisp articles
--- *********************************************************

pm10010mptMesrlineResidualChromaticDispTable OBJECT-TYPE
	SYNTAX  SEQUENCE OF Pm10010mptMesrlineResidualChromaticDispEntry
	MAX-ACCESS not-accessible
	STATUS current
	DESCRIPTION
        "
        List of pm10010mptMesrlineResidualChromaticDisp
        Article
        "
	::= { pm10010mptMesrLine 144 }


pm10010mptMesrlineResidualChromaticDispEntry OBJECT-TYPE
	SYNTAX Pm10010mptMesrlineResidualChromaticDispEntry
	MAX-ACCESS not-accessible
	STATUS current
	DESCRIPTION
        "
        Row definition for the pm10010mptMesrlineResidualChromaticDisp
        table
        "
	INDEX   { pm10010mptMesrlineResidualChromaticDispIndex }
	::= { pm10010mptMesrlineResidualChromaticDispTable 1 }


Pm10010mptMesrlineResidualChromaticDispEntry ::=
	SEQUENCE {
	pm10010mptMesrlineResidualChromaticDispIndex
		INTEGER,
	pm10010mptMesrlineResidualChromaticDispPortn
		INTEGER
	}


pm10010mptMesrlineResidualChromaticDispIndex OBJECT-TYPE
	SYNTAX  INTEGER(0..128)
	MAX-ACCESS  read-only
	STATUS current
	DESCRIPTION
        "
        Index definition for the pm10010mptMesrlineResidualChromaticDisp
        table
        "
	::= { pm10010mptMesrlineResidualChromaticDispEntry 1 }


pm10010mptMesrlineResidualChromaticDispPortn OBJECT-TYPE
	SYNTAX  INTEGER (0..65535)
	MAX-ACCESS read-only
	STATUS current
	DESCRIPTION
        "
        Current Residual Chromatic Dispersion
        :This OID gives the current Residual
        Chromatic Dispersion on the Line
        interface  (Unit = ps/nm)<Help>
        This measure gives the current
         Residual Chromatic Dispersion
         on the Line interface.
        "
	::= { pm10010mptMesrlineResidualChromaticDispEntry 2 }


--- *********************************************************
---     TABLE for the pm10010mptMesrlineDiffGroupDelay articles
--- *********************************************************

pm10010mptMesrlineDiffGroupDelayTable OBJECT-TYPE
	SYNTAX  SEQUENCE OF Pm10010mptMesrlineDiffGroupDelayEntry
	MAX-ACCESS not-accessible
	STATUS current
	DESCRIPTION
        "
        List of pm10010mptMesrlineDiffGroupDelay
        Article
        "
	::= { pm10010mptMesrLine 148 }


pm10010mptMesrlineDiffGroupDelayEntry OBJECT-TYPE
	SYNTAX Pm10010mptMesrlineDiffGroupDelayEntry
	MAX-ACCESS not-accessible
	STATUS current
	DESCRIPTION
        "
        Row definition for the pm10010mptMesrlineDiffGroupDelay
        table
        "
	INDEX   { pm10010mptMesrlineDiffGroupDelayIndex }
	::= { pm10010mptMesrlineDiffGroupDelayTable 1 }


Pm10010mptMesrlineDiffGroupDelayEntry ::=
	SEQUENCE {
	pm10010mptMesrlineDiffGroupDelayIndex
		INTEGER,
	pm10010mptMesrlineDiffGroupDelayPortn
		INTEGER
	}


pm10010mptMesrlineDiffGroupDelayIndex OBJECT-TYPE
	SYNTAX  INTEGER(0..128)
	MAX-ACCESS  read-only
	STATUS current
	DESCRIPTION
        "
        Index definition for the pm10010mptMesrlineDiffGroupDelay
        table
        "
	::= { pm10010mptMesrlineDiffGroupDelayEntry 1 }


pm10010mptMesrlineDiffGroupDelayPortn OBJECT-TYPE
	SYNTAX  INTEGER (0..65535)
	MAX-ACCESS read-only
	STATUS current
	DESCRIPTION
        "
        Current Differential Group Delay
        :This OID gives the current Differential
        Group Delay on the Line interface
          (Unit = ps)<Help> This measure
        gives the current Differential
         Group Delay on the Line interface.
        "
	::= { pm10010mptMesrlineDiffGroupDelayEntry 2 }


--- *********************************************************
---     TABLE for the pm10010mptMesrlineQFactor articles
--- *********************************************************

pm10010mptMesrlineQFactorTable OBJECT-TYPE
	SYNTAX  SEQUENCE OF Pm10010mptMesrlineQFactorEntry
	MAX-ACCESS not-accessible
	STATUS current
	DESCRIPTION
        "
        List of pm10010mptMesrlineQFactor
        Article
        "
	::= { pm10010mptMesrLine 152 }


pm10010mptMesrlineQFactorEntry OBJECT-TYPE
	SYNTAX Pm10010mptMesrlineQFactorEntry
	MAX-ACCESS not-accessible
	STATUS current
	DESCRIPTION
        "
        Row definition for the pm10010mptMesrlineQFactor
        table
        "
	INDEX   { pm10010mptMesrlineQFactorIndex }
	::= { pm10010mptMesrlineQFactorTable 1 }


Pm10010mptMesrlineQFactorEntry ::=
	SEQUENCE {
	pm10010mptMesrlineQFactorIndex
		INTEGER,
	pm10010mptMesrlineQFactorPortn
		INTEGER
	}


pm10010mptMesrlineQFactorIndex OBJECT-TYPE
	SYNTAX  INTEGER(0..128)
	MAX-ACCESS  read-only
	STATUS current
	DESCRIPTION
        "
        Index definition for the pm10010mptMesrlineQFactor
        table
        "
	::= { pm10010mptMesrlineQFactorEntry 1 }


pm10010mptMesrlineQFactorPortn OBJECT-TYPE
	SYNTAX  INTEGER (0..65535)
	MAX-ACCESS read-only
	STATUS current
	DESCRIPTION
        "
        Current Q Factor :This OID gives
        the current Q Factor on the Line
        interface   (Unit = dB) <Help>
         This measure gives the current
        Q Factor on the Line interface.
        "
	::= { pm10010mptMesrlineQFactorEntry 2 }


--- *********************************************************
---     TABLE for the pm10010mptMesrlineCarrierFreqOffset articles
--- *********************************************************

pm10010mptMesrlineCarrierFreqOffsetTable OBJECT-TYPE
	SYNTAX  SEQUENCE OF Pm10010mptMesrlineCarrierFreqOffsetEntry
	MAX-ACCESS not-accessible
	STATUS current
	DESCRIPTION
        "
        List of pm10010mptMesrlineCarrierFreqOffset
        Article
        "
	::= { pm10010mptMesrLine 156 }


pm10010mptMesrlineCarrierFreqOffsetEntry OBJECT-TYPE
	SYNTAX Pm10010mptMesrlineCarrierFreqOffsetEntry
	MAX-ACCESS not-accessible
	STATUS current
	DESCRIPTION
        "
        Row definition for the pm10010mptMesrlineCarrierFreqOffset
        table
        "
	INDEX   { pm10010mptMesrlineCarrierFreqOffsetIndex }
	::= { pm10010mptMesrlineCarrierFreqOffsetTable 1 }


Pm10010mptMesrlineCarrierFreqOffsetEntry ::=
	SEQUENCE {
	pm10010mptMesrlineCarrierFreqOffsetIndex
		INTEGER,
	pm10010mptMesrlineCarrierFreqOffsetPortn
		INTEGER
	}


pm10010mptMesrlineCarrierFreqOffsetIndex OBJECT-TYPE
	SYNTAX  INTEGER(0..128)
	MAX-ACCESS  read-only
	STATUS current
	DESCRIPTION
        "
        Index definition for the pm10010mptMesrlineCarrierFreqOffset
        table
        "
	::= { pm10010mptMesrlineCarrierFreqOffsetEntry 1 }


pm10010mptMesrlineCarrierFreqOffsetPortn OBJECT-TYPE
	SYNTAX  INTEGER (0..65535)
	MAX-ACCESS read-only
	STATUS current
	DESCRIPTION
        "
        Current Carrier Frequency Offset
        :This OID gives the current Carrier
        Frequency Offset on the Line interface
          (Unit = Mhz)<Help> This measure
        gives the current Carrier Frequency
        Offset on the Line interface.
        "
	::= { pm10010mptMesrlineCarrierFreqOffsetEntry 2 }


--- *********************************************************
---     TABLE for the pm10010mptMesrlineOsnr articles
--- *********************************************************

pm10010mptMesrlineOsnrTable OBJECT-TYPE
	SYNTAX  SEQUENCE OF Pm10010mptMesrlineOsnrEntry
	MAX-ACCESS not-accessible
	STATUS current
	DESCRIPTION
        "
        List of pm10010mptMesrlineOsnr
        Article
        "
	::= { pm10010mptMesrLine 160 }


pm10010mptMesrlineOsnrEntry OBJECT-TYPE
	SYNTAX Pm10010mptMesrlineOsnrEntry
	MAX-ACCESS not-accessible
	STATUS current
	DESCRIPTION
        "
        Row definition for the pm10010mptMesrlineOsnr
        table
        "
	INDEX   { pm10010mptMesrlineOsnrIndex }
	::= { pm10010mptMesrlineOsnrTable 1 }


Pm10010mptMesrlineOsnrEntry ::=
	SEQUENCE {
	pm10010mptMesrlineOsnrIndex
		INTEGER,
	pm10010mptMesrlineOsnrPortn
		INTEGER
	}


pm10010mptMesrlineOsnrIndex OBJECT-TYPE
	SYNTAX  INTEGER(0..128)
	MAX-ACCESS  read-only
	STATUS current
	DESCRIPTION
        "
        Index definition for the pm10010mptMesrlineOsnr
        table
        "
	::= { pm10010mptMesrlineOsnrEntry 1 }


pm10010mptMesrlineOsnrPortn OBJECT-TYPE
	SYNTAX  INTEGER (0..65535)
	MAX-ACCESS read-only
	STATUS current
	DESCRIPTION
        "
        Current OSNR :This OID gives the
        current OSNR on the Line interface
          (OSNR = AV/10) (Unit = dB) <Help>
        This measure gives the current
         OSNR on the Line interface.
        "
	::= { pm10010mptMesrlineOsnrEntry 2 }


--- *****************************************************
---     LEAF for the lineNetTxLaserOutputPwrAverage article
--- *****************************************************

pm10010mptMesrlineNetTxLaserOutputPwrAverage OBJECT-TYPE
	  SYNTAX Unsigned32 (0..65535)
	  MAX-ACCESS read-only
	  STATUS current
	  DESCRIPTION
        "
        Average Line Trscv Tx Power :This
        OID gives the average Tx Laser
         transmit power value among the
        network lanes of the Line Transceiver,
        read in the DDM (Digital Diagnostic
        Monitoring)  (Power = AV/100) (Unit
        = dBm) (Unit = dBm) <Help> This
        Measure gives the average Tx Laser
        transmit power value among the
         network lanes of the Line Transceiver
        "
	  ::= { pm10010mptMesrOther 180 }



--- *****************************************************
---     LEAF for the lineNetTxLaserTempAverage article
--- *****************************************************

pm10010mptMesrlineNetTxLaserTempAverage OBJECT-TYPE
	  SYNTAX Unsigned32 (0..65535)
	  MAX-ACCESS read-only
	  STATUS current
	  DESCRIPTION
        "
        Average Line Trscv Tx Laser Temperature
        :This OID gives the average Tx
         Laser Temperature value among
         the network lanes of the Line
         Transceiver, read from the DDM
        (Digital Diagnostic Monitoring)
        (Temperature = AV/256) (Unit =
         C) <Help> This Measure gives the
        average Tx Laser Temperature value
        among the network lanes of the
         Line Transceiver
        "
	  ::= { pm10010mptMesrOther 181 }



--- *****************************************************
---     LEAF for the lineNetTxBiasCurrentAverage article
--- *****************************************************

pm10010mptMesrlineNetTxBiasCurrentAverage OBJECT-TYPE
	  SYNTAX Unsigned32 (0..65535)
	  MAX-ACCESS read-only
	  STATUS current
	  DESCRIPTION
        "
        Average Line Trscv Tx Laser Bias
        :This OID gives the average Tx
         Laser Bias value among the network
        lanes of the Line Transceiver,
         read from the DDM (Digital Diagnostic
        Monitoring) (Bias = AV/10) (Unit
        = mA) <Help> This Measure gives
        the average Tx Laser Bias value
        among the network lanes of the
         Line Transceiver
        "
	  ::= { pm10010mptMesrOther 182 }



--- *****************************************************
---     LEAF for the lineNetRxInputPwrAverage article
--- *****************************************************

pm10010mptMesrlineNetRxInputPwrAverage OBJECT-TYPE
	  SYNTAX Unsigned32 (0..65535)
	  MAX-ACCESS read-only
	  STATUS current
	  DESCRIPTION
        "
        Average Line Trscv Rx Power :This
        OID gives the average Receive power
        value among the network lanes of
        the Line Transceiver, read in the
        DDM (Digital Diagnostic Monitoring)
        (Power = AV/100) (Unit = dBm) <Help>
        This Measure gives the average
         Receive power value among the
         network lanes of the Line Transceiver
        "
	  ::= { pm10010mptMesrOther 183 }



--- *****************************************************
---     LEAF for the lineResidualChromaticDispAverage article
--- *****************************************************

pm10010mptMesrlineResidualChromaticDispAverage OBJECT-TYPE
	  SYNTAX Unsigned32 (0..65535)
	  MAX-ACCESS read-only
	  STATUS current
	  DESCRIPTION
        "
        Average Residual Chromatic Dispersion
        :This OID gives the average Residual
        Chromatic Dispersion on the Line
        interface since the last measure
        reset <Help> This measure gives
        the average Residual Chromatic
         Dispersion on the Line interface
        since the last measure reset.
        "
	  ::= { pm10010mptMesrOther 184 }



--- *****************************************************
---     LEAF for the lineDiffGroupDelayAverage article
--- *****************************************************

pm10010mptMesrlineDiffGroupDelayAverage OBJECT-TYPE
	  SYNTAX Unsigned32 (0..65535)
	  MAX-ACCESS read-only
	  STATUS current
	  DESCRIPTION
        "
        Average Differential Group Delay
        :This OID gives the average Group
        Delay on the Line interface since
        the last measure reset <Help> This
        measure gives the average Differential
        Group Delay on the Line interface
        since the last measure reset.
        "
	  ::= { pm10010mptMesrOther 185 }



--- *****************************************************
---     LEAF for the lineQFactorAverage article
--- *****************************************************

pm10010mptMesrlineQFactorAverage OBJECT-TYPE
	  SYNTAX Unsigned32 (0..65535)
	  MAX-ACCESS read-only
	  STATUS current
	  DESCRIPTION
        "
        Average Q Factor :This OID gives
        the average Q Factor on the Line
        interface since the last measure
        reset <Help> This measure gives
        the average Q Factor on the Line
        interface since the last measure
        reset.
        "
	  ::= { pm10010mptMesrOther 186 }



--- *****************************************************
---     LEAF for the lineCarrierFreqOffsetAverage article
--- *****************************************************

pm10010mptMesrlineCarrierFreqOffsetAverage OBJECT-TYPE
	  SYNTAX Unsigned32 (0..65535)
	  MAX-ACCESS read-only
	  STATUS current
	  DESCRIPTION
        "
        Average Carrier Frequency Offset
        :This OID gives the average Carrier
        Frequency Offset on the Line interface
        since the last measure reset <Help>
        This measure gives the average
         Carrier Frequency Offset on the
        Line interface since the last measure
        reset
        "
	  ::= { pm10010mptMesrOther 187 }



--- *****************************************************
---     LEAF for the lineOsnrAverage article
--- *****************************************************

pm10010mptMesrlineOsnrAverage OBJECT-TYPE
	  SYNTAX Unsigned32 (0..65535)
	  MAX-ACCESS read-only
	  STATUS current
	  DESCRIPTION
        "
        Average OSNR :This OID gives the
        average OSNR on the Line interface
        since the last measure reset <Help>
        This measure gives the average
         OSNR on the Line interface since
        the last measure reset.
        "
	  ::= { pm10010mptMesrOther 188 }



--- *****************************************************
---     LEAF for the clientNetTxTempMin article
--- *****************************************************

pm10010mptMesrclientNetTxTempMin OBJECT-TYPE
	  SYNTAX Unsigned32 (0..65535)
	  MAX-ACCESS read-only
	  STATUS current
	  DESCRIPTION
        "
        Min Client Trscv Laser Temperature
        :This OID gives the minimum Laser
        temperature value among the network
        lanes of the Client Transceiver,
        read from the DDM (Digital Diagnostic
        Monitoring) (Temperature = AV/256)
        (Unit = C) <Help> This Measure
         gives the minimum Laser temperature
        value among the network lanes of
        the Client Transceiver
        "
	  ::= { pm10010mptMesrOther 192 }



--- *****************************************************
---     LEAF for the clientNetTxBiasMin article
--- *****************************************************

pm10010mptMesrclientNetTxBiasMin OBJECT-TYPE
	  SYNTAX Unsigned32 (0..65535)
	  MAX-ACCESS read-only
	  STATUS current
	  DESCRIPTION
        "
        Min Client Trscv Laser Bias :This
        OID gives the minimum Laser bias
        value among the network lanes of
        the Client Transceiver, read from
        the DDM (Digital Diagnostic Monitoring)
        (Bias = AV/500) (Unit = mA) <Help>
        This Measure gives the minimum
         Laser bias value among the network
        lanes of the Client Transceiver
        "
	  ::= { pm10010mptMesrOther 193 }



--- *****************************************************
---     LEAF for the clientNetTxPwrMin article
--- *****************************************************

pm10010mptMesrclientNetTxPwrMin OBJECT-TYPE
	  SYNTAX Unsigned32 (0..65535)
	  MAX-ACCESS read-only
	  STATUS current
	  DESCRIPTION
        "
        Min Client Trscv Tx Power :This
        OID gives the minimum transmit
         power value among the network
         lanes of the Client Transceiver,
        read from the DDM (Digital Diagnostic
        Monitoring) (Power = 10*log(AV)-40)
        (Unit = dBm) <Help> This Measure
        gives the minimum transmit power
        value among the network lanes of
        the Client Transceiver
        "
	  ::= { pm10010mptMesrOther 194 }



--- *****************************************************
---     LEAF for the clientNetRxPwrMin article
--- *****************************************************

pm10010mptMesrclientNetRxPwrMin OBJECT-TYPE
	  SYNTAX Unsigned32 (0..65535)
	  MAX-ACCESS read-only
	  STATUS current
	  DESCRIPTION
        "
        Min Client Trscv Rx Power :This
        OID gives the minimum receive power
        value among the network lanes of
        the Client Transceiver, read in
        the DDM (Digital Diagnostic Monitoring)
        (Power = 10*log(AV)-40) (Unit =
        dBm) <Help> This Measure gives
         the minimum receive power value
        among the network lanes of the
         Client Transceiver
        "
	  ::= { pm10010mptMesrOther 195 }



--- *****************************************************
---     LEAF for the lineNetTxLaserOutputPwrMin article
--- *****************************************************

pm10010mptMesrlineNetTxLaserOutputPwrMin OBJECT-TYPE
	  SYNTAX Unsigned32 (0..65535)
	  MAX-ACCESS read-only
	  STATUS current
	  DESCRIPTION
        "
        Min Line Trscv Tx Power :This
         OID gives the minimum Tx Laser
        transmit power value among the
         network lanes of the Line Transceiver,
        read in the DDM (Digital Diagnostic
        Monitoring)  (Power = AV/100) (Unit
        = dBm) (Unit = dBm) <Help> This
        Measure gives the minimum Tx Laser
        transmit power value among the
         network lanes of the Line Transceiver
        "
	  ::= { pm10010mptMesrOther 196 }



--- *****************************************************
---     LEAF for the lineNetTxLaserTempMin article
--- *****************************************************

pm10010mptMesrlineNetTxLaserTempMin OBJECT-TYPE
	  SYNTAX Unsigned32 (0..65535)
	  MAX-ACCESS read-only
	  STATUS current
	  DESCRIPTION
        "
        Min Line Trscv Tx Laser Temperature
        :This OID gives the minimum Tx
         Laser Temperature value among
         the network lanes of the Line
         Transceiver, read from the DDM
        (Digital Diagnostic Monitoring)
        (Temperature = AV/256) (Unit =
         C) <Help> This Measure gives the
        minimum Tx Laser Temperature value
        among the network lanes of the
         Line Transceiver
        "
	  ::= { pm10010mptMesrOther 197 }



--- *****************************************************
---     LEAF for the lineNetTxBiasCurrentMin article
--- *****************************************************

pm10010mptMesrlineNetTxBiasCurrentMin OBJECT-TYPE
	  SYNTAX Unsigned32 (0..65535)
	  MAX-ACCESS read-only
	  STATUS current
	  DESCRIPTION
        "
        Min Line Trscv Tx Laser Bias :This
        OID gives the minimum Tx Laser
         Bias value among the network lanes
        of the Line Transceiver, read from
        the DDM (Digital Diagnostic Monitoring)
        (Bias = AV/10) (Unit = mA) <Help>
        This Measure gives the minimum
         Tx Laser Bias value among the
         network lanes of the Line Transceiver
        "
	  ::= { pm10010mptMesrOther 198 }



--- *****************************************************
---     LEAF for the lineNetRxInputPwrMin article
--- *****************************************************

pm10010mptMesrlineNetRxInputPwrMin OBJECT-TYPE
	  SYNTAX Unsigned32 (0..65535)
	  MAX-ACCESS read-only
	  STATUS current
	  DESCRIPTION
        "
        Min Line Trscv Rx Power :This
         OID gives the minimum Receive
         power value among the network
         lanes of the Line Transceiver,
        read in the DDM (Digital Diagnostic
        Monitoring) (Power = AV/100) (Unit
        = dBm) <Help> This Measure gives
        the minimum Receive power value
        among the network lanes of the
         Line Transceiver
        "
	  ::= { pm10010mptMesrOther 199 }



--- *****************************************************
---     LEAF for the lineResidualChromaticDispMin article
--- *****************************************************

pm10010mptMesrlineResidualChromaticDispMin OBJECT-TYPE
	  SYNTAX Unsigned32 (0..65535)
	  MAX-ACCESS read-only
	  STATUS current
	  DESCRIPTION
        "
        Min Residual Chromatic Dispersion
        :This OID gives the minimum Residual
        Chromatic Dispersion on the Line
        interface since the last measure
        reset  (Unit = ps/nm)<Help> This
        measure gives the minimum Residual
        Chromatic Dispersion on the Line
        interface since the last measure
        reset.
        "
	  ::= { pm10010mptMesrOther 200 }



--- *****************************************************
---     LEAF for the lineDiffGroupDelayMin article
--- *****************************************************

pm10010mptMesrlineDiffGroupDelayMin OBJECT-TYPE
	  SYNTAX Unsigned32 (0..65535)
	  MAX-ACCESS read-only
	  STATUS current
	  DESCRIPTION
        "
        Min Differential Group Delay :This
        OID gives the minimum Differential
        Group Delay  on the Line interface
        since the last measure reset  (Unit
        = ps)<Help> This measure gives
         the minimum Differential Group
        Delay on the Line interface since
        the last measure reset.
        "
	  ::= { pm10010mptMesrOther 201 }



--- *****************************************************
---     LEAF for the lineQFactorMin article
--- *****************************************************

pm10010mptMesrlineQFactorMin OBJECT-TYPE
	  SYNTAX Unsigned32 (0..65535)
	  MAX-ACCESS read-only
	  STATUS current
	  DESCRIPTION
        "
        Min Q Factor :This OID gives the
        minimum Q Factor on the Line interface
        since the last measure reset  (Unit
        = dB)<Help> This measure gives
         the minimum Q Factor on the Line
        interface since the last measure
        reset.
        "
	  ::= { pm10010mptMesrOther 202 }



--- *****************************************************
---     LEAF for the lineCarrierFreqOffsetMin article
--- *****************************************************

pm10010mptMesrlineCarrierFreqOffsetMin OBJECT-TYPE
	  SYNTAX Unsigned32 (0..65535)
	  MAX-ACCESS read-only
	  STATUS current
	  DESCRIPTION
        "
        Min Carrier Frequency Offset :This
        OID gives the minimum Carrier Frequency
        Offset on the Line interface since
        the last measure reset  (Unit =
        Mhz)<Help> This measure gives the
        minimum Carrier Frequency Offset
        on the Line interface since the
        last measure reset
        "
	  ::= { pm10010mptMesrOther 203 }



--- *****************************************************
---     LEAF for the lineOsnrMin article
--- *****************************************************

pm10010mptMesrlineOsnrMin OBJECT-TYPE
	  SYNTAX Unsigned32 (0..65535)
	  MAX-ACCESS read-only
	  STATUS current
	  DESCRIPTION
        "
        Min OSNR :This OID gives the minimum
        OSNR on the Line interface since
        the last measure reset  (OSNR =
        AV/10) (Unit = dB)<Help> This measure
        gives the minimum OSNR on the Line
        interface since the last measure
        reset.
        "
	  ::= { pm10010mptMesrOther 204 }



--- *****************************************************
---     LEAF for the clientNetTxTempMax article
--- *****************************************************

pm10010mptMesrclientNetTxTempMax OBJECT-TYPE
	  SYNTAX Unsigned32 (0..65535)
	  MAX-ACCESS read-only
	  STATUS current
	  DESCRIPTION
        "
        Max Client Trscv Laser Temperature
        :This OID gives the maximum Laser
        temperature value among the network
        lanes of the Client Transceiver,
        read from the DDM (Digital Diagnostic
        Monitoring) (Temperature = AV/256)
        (Unit = C) <Help> This Measure
         gives the maximum Laser temperature
        value among the network lanes of
        the Client Transceiver
        "
	  ::= { pm10010mptMesrOther 208 }



--- *****************************************************
---     LEAF for the clientNetTxBiasMax article
--- *****************************************************

pm10010mptMesrclientNetTxBiasMax OBJECT-TYPE
	  SYNTAX Unsigned32 (0..65535)
	  MAX-ACCESS read-only
	  STATUS current
	  DESCRIPTION
        "
        Max Client Trscv Laser Bias :This
        OID gives the maximum Laser bias
        value among the network lanes of
        the Client Transceiver, read from
        the DDM (Digital Diagnostic Monitoring)
        (Bias = AV/500) (Unit = mA) <Help>
        This Measure gives the maximum
         Laser bias value among the network
        lanes of the Client Transceiver
        "
	  ::= { pm10010mptMesrOther 209 }



--- *****************************************************
---     LEAF for the clientNetTxPwrMax article
--- *****************************************************

pm10010mptMesrclientNetTxPwrMax OBJECT-TYPE
	  SYNTAX Unsigned32 (0..65535)
	  MAX-ACCESS read-only
	  STATUS current
	  DESCRIPTION
        "
        Max Client Trscv Tx Power :This
        OID gives the maximum transmit
         power value among the network
         lanes of the Client Transceiver,
        read from the DDM (Digital Diagnostic
        Monitoring) (Power = 10*log(AV)-40)
        (Unit = dBm) <Help> This Measure
        gives the maximum transmit power
        value among the network lanes of
        the Client Transceiver
        "
	  ::= { pm10010mptMesrOther 210 }



--- *****************************************************
---     LEAF for the clientNetRxPwrMax article
--- *****************************************************

pm10010mptMesrclientNetRxPwrMax OBJECT-TYPE
	  SYNTAX Unsigned32 (0..65535)
	  MAX-ACCESS read-only
	  STATUS current
	  DESCRIPTION
        "
        Max Client Trscv Rx Power :This
        OID gives the maximum receive power
        value among the network lanes of
        the Client Transceiver, read in
        the DDM (Digital Diagnostic Monitoring)
        (Power = 10*log(AV)-40) (Unit =
        dBm) <Help> This Measure gives
         the maximum receive power value
        among the network lanes of the
         Client Transceiver
        "
	  ::= { pm10010mptMesrOther 211 }



--- *****************************************************
---     LEAF for the lineNetTxLaserOutputPwrMax article
--- *****************************************************

pm10010mptMesrlineNetTxLaserOutputPwrMax OBJECT-TYPE
	  SYNTAX Unsigned32 (0..65535)
	  MAX-ACCESS read-only
	  STATUS current
	  DESCRIPTION
        "
        Max Line Trscv Tx Power :This
         OID gives the maximum Tx Laser
        transmit power value among the
         network lanes of the Line Transceiver,
        read in the DDM (Digital Diagnostic
        Monitoring) (Power = 10*log(AV)-40)
        (Unit = dBm) <Help> This Measure
        gives the maximum Tx Laser transmit
        power value among the network lanes
        of the Line Transceiver
        "
	  ::= { pm10010mptMesrOther 212 }



--- *****************************************************
---     LEAF for the lineNetTxLaserTempMax article
--- *****************************************************

pm10010mptMesrlineNetTxLaserTempMax OBJECT-TYPE
	  SYNTAX Unsigned32 (0..65535)
	  MAX-ACCESS read-only
	  STATUS current
	  DESCRIPTION
        "
        Max Line Trscv Tx Laser Temperature
        :This OID gives the maximum Tx
         Laser Temperature value among
         the network lanes of the Line
         Transceiver, read from the DDM
        (Digital Diagnostic Monitoring)
        (Temperature = AV/256) (Unit =
         C) <Help> This Measure gives the
        maximum Tx Laser Temperature value
        among the network lanes of the
         Line Transceiver
        "
	  ::= { pm10010mptMesrOther 213 }



--- *****************************************************
---     LEAF for the lineNetTxBiasCurrentMax article
--- *****************************************************

pm10010mptMesrlineNetTxBiasCurrentMax OBJECT-TYPE
	  SYNTAX Unsigned32 (0..65535)
	  MAX-ACCESS read-only
	  STATUS current
	  DESCRIPTION
        "
        Max Line Trscv Tx Laser Bias :This
        OID gives the maximum Tx Laser
         Bias value among the network lanes
        of the Line Transceiver, read from
        the DDM (Digital Diagnostic Monitoring)
        (Bias = AV/10) (Unit = mA) <Help>
        This Measure gives the maximum
         Tx Laser Bias value among the
         network lanes of the Line Transceiver
        "
	  ::= { pm10010mptMesrOther 214 }



--- *****************************************************
---     LEAF for the lineNetRxInputPwrMax article
--- *****************************************************

pm10010mptMesrlineNetRxInputPwrMax OBJECT-TYPE
	  SYNTAX Unsigned32 (0..65535)
	  MAX-ACCESS read-only
	  STATUS current
	  DESCRIPTION
        "
        Max Line Trscv Rx Power :This
         OID gives the maximum Receive
         power value among the network
         lanes of the Line Transceiver,
        read in the DDM (Digital Diagnostic
        Monitoring) (Power = 10*log(AV)-40)
        (Unit = dBm) <Help> This Measure
        gives the maximum Receive power
        value among the network lanes of
        the Line Transceiver
        "
	  ::= { pm10010mptMesrOther 215 }



--- *****************************************************
---     LEAF for the lineResidualChromaticDispMax article
--- *****************************************************

pm10010mptMesrlineResidualChromaticDispMax OBJECT-TYPE
	  SYNTAX Unsigned32 (0..65535)
	  MAX-ACCESS read-only
	  STATUS current
	  DESCRIPTION
        "
        Max Residual Chromatic Dispersion
        :This OID gives the maximum Residual
        Chromatic Dispersion on the Line
        interface since the last measure
        reset  (Unit = ps/nm)<Help> This
        measure gives the maximum Residual
        Chromatic Dispersion on the Line
        interface since the last measure
        reset.
        "
	  ::= { pm10010mptMesrOther 216 }



--- *****************************************************
---     LEAF for the lineDiffGroupDelayMax article
--- *****************************************************

pm10010mptMesrlineDiffGroupDelayMax OBJECT-TYPE
	  SYNTAX Unsigned32 (0..65535)
	  MAX-ACCESS read-only
	  STATUS current
	  DESCRIPTION
        "
        Max Differential Group Delay :This
        OID gives the maximum Differential
        Group Delay  on the Line interface
        since the last measure reset
         (Unit = ps)<Help> This measure
        gives the maximum Differential
         Group Delay on the Line interface
        since the last measure reset.
        "
	  ::= { pm10010mptMesrOther 217 }



--- *****************************************************
---     LEAF for the lineQFactorMax article
--- *****************************************************

pm10010mptMesrlineQFactorMax OBJECT-TYPE
	  SYNTAX Unsigned32 (0..65535)
	  MAX-ACCESS read-only
	  STATUS current
	  DESCRIPTION
        "
        Max Q Factor :This OID gives the
        maximum Q Factor on the Line interface
        since the last measure reset  (Unit
        = dB)<Help> This measure gives
         the maximum Q Factor on the Line
        interface since the last measure
        reset.
        "
	  ::= { pm10010mptMesrOther 218 }



--- *****************************************************
---     LEAF for the lineCarrierFreqOffsetMax article
--- *****************************************************

pm10010mptMesrlineCarrierFreqOffsetMax OBJECT-TYPE
	  SYNTAX Unsigned32 (0..65535)
	  MAX-ACCESS read-only
	  STATUS current
	  DESCRIPTION
        "
        Max Carrier Frequency Offset :This
        OID gives the maximum Carrier Frequency
        Offset on the Line interface since
        the last measure reset   (Unit
         = Mhz)<Help> This measure gives
        the maximum Carrier Frequency Offset
        on the Line interface since the
        last measure reset.
        "
	  ::= { pm10010mptMesrOther 219 }



--- *****************************************************
---     LEAF for the lineOsnrMax article
--- *****************************************************

pm10010mptMesrlineOsnrMax OBJECT-TYPE
	  SYNTAX Unsigned32 (0..65535)
	  MAX-ACCESS read-only
	  STATUS current
	  DESCRIPTION
        "
        Max OSNR :This OID gives the maximum
        OSNR on the Line interface since
        the last measure reset  (OSNR =
        AV/10) (Unit = dB)<Help> This measure
        gives the maximum OSNR on the Line
        interface since the last measure
        reset
        "
	  ::= { pm10010mptMesrOther 220 }








--- *****************************************************
--- $$$$$$$$$$$$$$$$$$$$$$$$$$$$$$$$$$$$$$$$$$$$$$$$$$$$$
---     PERFORMANCE
--- $$$$$$$$$$$$$$$$$$$$$$$$$$$$$$$$$$$$$$$$$$$$$$$$$$$$$
--- *****************************************************



--- *****************************************************
---     Leaf of the telecomInputClientCurrent15Stat
--- *****************************************************
--- *********************************************************
---     TABLE for the pm10010mptPerfTelecomInputClientCurrent15Stat articles
--- *********************************************************

pm10010mptPerfTelecomInputClientCurrent15StatTable OBJECT-TYPE
	SYNTAX  SEQUENCE OF Pm10010mptPerfTelecomInputClientCurrent15StatEntry
	MAX-ACCESS not-accessible
	STATUS current
	DESCRIPTION
        "
        List of pm10010mptPerfTelecomInputClientCurrent15Stat
        Article
        "
	::= { pm10010mptMonPerfClient 16 }


pm10010mptPerfTelecomInputClientCurrent15StatEntry OBJECT-TYPE
	SYNTAX Pm10010mptPerfTelecomInputClientCurrent15StatEntry
	MAX-ACCESS not-accessible
	STATUS current
	DESCRIPTION
        "
        Row definition for the pm10010mptPerfTelecomInputClientCurrent15Stat
        table
        "
	INDEX   { pm10010mptPerfTelecomInputClientCurrent15StatIndex }
	::= { pm10010mptPerfTelecomInputClientCurrent15StatTable 1 }


Pm10010mptPerfTelecomInputClientCurrent15StatEntry ::=
	SEQUENCE {
	pm10010mptPerfTelecomInputClientCurrent15StatIndex
		INTEGER,
	pm10010mptPerfTelecomInputClientCurrent15StatInvCvPortn
		EkiOnOff,
	pm10010mptPerfTelecomInputClientCurrent15StatCvValuePortn
		Unsigned32,
	pm10010mptPerfTelecomInputClientCurrent15StatInvEsPortn
		EkiOnOff,
	pm10010mptPerfTelecomInputClientCurrent15StatEsValuePortn
		Unsigned32,
	pm10010mptPerfTelecomInputClientCurrent15StatInvSesPortn
		EkiOnOff,
	pm10010mptPerfTelecomInputClientCurrent15StatSesValuePortn
		Unsigned32,
	pm10010mptPerfTelecomInputClientCurrent15StatInvSefsPortn
		EkiOnOff,
	pm10010mptPerfTelecomInputClientCurrent15StatSefsValuePortn
		Unsigned32,
	pm10010mptPerfTelecomInputClientCurrent15StatInvUasPortn
		EkiOnOff,
	pm10010mptPerfTelecomInputClientCurrent15StatUasValuePortn
		Unsigned32
	}


pm10010mptPerfTelecomInputClientCurrent15StatIndex OBJECT-TYPE
	SYNTAX  INTEGER(0..128)
	MAX-ACCESS  read-only
	STATUS current
	DESCRIPTION
        "
        Index definition for the pm10010mptPerfTelecomInputClientCurrent15Stat
        table
        "
	::= { pm10010mptPerfTelecomInputClientCurrent15StatEntry 1 }


pm10010mptPerfTelecomInputClientCurrent15StatInvCvPortn OBJECT-TYPE
	SYNTAX  EkiOnOff
	MAX-ACCESS read-only
	STATUS current
	DESCRIPTION
        "
        Current 15-min EBC counter inv.
        :This OID indicates that the current
        15-min Coding Violation counter
        is invalid
        "
	::= { pm10010mptPerfTelecomInputClientCurrent15StatEntry 2 }


pm10010mptPerfTelecomInputClientCurrent15StatCvValuePortn OBJECT-TYPE
	SYNTAX  Unsigned32
	MAX-ACCESS read-only
	STATUS current
	DESCRIPTION
        "
        Current 15-min EBC counter :This
        OID gives the current 15-min Coding
        Violation counter value
        "
	::= { pm10010mptPerfTelecomInputClientCurrent15StatEntry 3 }


pm10010mptPerfTelecomInputClientCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pm10010mptPerfTelecomInputClientCurrent15StatEntry 4 }


pm10010mptPerfTelecomInputClientCurrent15StatEsValuePortn OBJECT-TYPE
	SYNTAX  Unsigned32
	MAX-ACCESS read-only
	STATUS current
	DESCRIPTION
        "
        Current 15-min ES counter :This
        OID gives the current 15-min Errored
        Second counter value
        "
	::= { pm10010mptPerfTelecomInputClientCurrent15StatEntry 5 }


pm10010mptPerfTelecomInputClientCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pm10010mptPerfTelecomInputClientCurrent15StatEntry 6 }


pm10010mptPerfTelecomInputClientCurrent15StatSesValuePortn OBJECT-TYPE
	SYNTAX  Unsigned32
	MAX-ACCESS read-only
	STATUS current
	DESCRIPTION
        "
        Current 15-min SES counter :This
        OID gives the current 15-min severely
        Errored Second counter value
        "
	::= { pm10010mptPerfTelecomInputClientCurrent15StatEntry 7 }


pm10010mptPerfTelecomInputClientCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pm10010mptPerfTelecomInputClientCurrent15StatEntry 8 }


pm10010mptPerfTelecomInputClientCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pm10010mptPerfTelecomInputClientCurrent15StatEntry 9 }


pm10010mptPerfTelecomInputClientCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pm10010mptPerfTelecomInputClientCurrent15StatEntry 10 }


pm10010mptPerfTelecomInputClientCurrent15StatUasValuePortn OBJECT-TYPE
	SYNTAX  Unsigned32
	MAX-ACCESS read-only
	STATUS current
	DESCRIPTION
        "
        Current 15-min UAS counter :This
        OID gives the current 15-min UnAvailable
        Second counter value
        "
	::= { pm10010mptPerfTelecomInputClientCurrent15StatEntry 11 }


--- *****************************************************
---     Leaf of the telecomInputClientPast15Stat
--- *****************************************************
--- *********************************************************
---     TABLE for the pm10010mptPerfTelecomInputClientPast15StatHistory articles
--- *********************************************************

pm10010mptPerfTelecomInputClientPast15StatHistoryPort1Table OBJECT-TYPE
	SYNTAX  SEQUENCE OF Pm10010mptPerfTelecomInputClientPast15StatHistoryPort1Entry
	MAX-ACCESS not-accessible
	STATUS current
	DESCRIPTION
        "
        List of pm10010mptPerfTelecomInputClientPast15StatHistory
        Article
        "
	::= { pm10010mptMonPerfClient 32 }


pm10010mptPerfTelecomInputClientPast15StatHistoryPort1Entry OBJECT-TYPE
	SYNTAX Pm10010mptPerfTelecomInputClientPast15StatHistoryPort1Entry
	MAX-ACCESS not-accessible
	STATUS current
	DESCRIPTION
        "
        Row definition for the pm10010mptPerfTelecomInputClientPast15StatHistory
        table
        "
	INDEX   { pm10010mptPerfTelecomInputClientPast15StatHistoryPort1Index }
	::= { pm10010mptPerfTelecomInputClientPast15StatHistoryPort1Table 1 }


Pm10010mptPerfTelecomInputClientPast15StatHistoryPort1Entry ::=
	SEQUENCE {
	pm10010mptPerfTelecomInputClientPast15StatHistoryPort1Index
		INTEGER,
	pm10010mptPerfTelecomInputClientPast15StatHistoryInvCvPort1
		EkiOnOff,
	pm10010mptPerfTelecomInputClientPast15StatHistoryCvValuePort1
		Unsigned32,
	pm10010mptPerfTelecomInputClientPast15StatHistoryInvEsPort1
		EkiOnOff,
	pm10010mptPerfTelecomInputClientPast15StatHistoryEsValuePort1
		Unsigned32,
	pm10010mptPerfTelecomInputClientPast15StatHistoryInvSesPort1
		EkiOnOff,
	pm10010mptPerfTelecomInputClientPast15StatHistorySesValuePort1
		Unsigned32,
	pm10010mptPerfTelecomInputClientPast15StatHistoryInvSefsPort1
		EkiOnOff,
	pm10010mptPerfTelecomInputClientPast15StatHistorySefsValuePort1
		Unsigned32,
	pm10010mptPerfTelecomInputClientPast15StatHistoryInvUasPort1
		EkiOnOff,
	pm10010mptPerfTelecomInputClientPast15StatHistoryUasValuePort1
		Unsigned32
	}


pm10010mptPerfTelecomInputClientPast15StatHistoryPort1Index OBJECT-TYPE
	SYNTAX  INTEGER(0..128)
	MAX-ACCESS  read-only
	STATUS current
	DESCRIPTION
        "
        Index definition for the pm10010mptPerfTelecomInputClientPast15StatHistory
        table
        "
	::= { pm10010mptPerfTelecomInputClientPast15StatHistoryPort1Entry 1 }


pm10010mptPerfTelecomInputClientPast15StatHistoryInvCvPort1 OBJECT-TYPE
	SYNTAX  EkiOnOff
	MAX-ACCESS read-only
	STATUS current
	DESCRIPTION
        "
        Previous 15-min EBC counter inv.
        :This OID indicates that the previous
        15-min Coding Violation counter
        is invalid
        "
	::= { pm10010mptPerfTelecomInputClientPast15StatHistoryPort1Entry 2 }


pm10010mptPerfTelecomInputClientPast15StatHistoryCvValuePort1 OBJECT-TYPE
	SYNTAX  Unsigned32
	MAX-ACCESS read-only
	STATUS current
	DESCRIPTION
        "
        Previous 15-min EBC counter :This
        OID gives the previous 15-min Coding
        Violation counter value
        "
	::= { pm10010mptPerfTelecomInputClientPast15StatHistoryPort1Entry 3 }


pm10010mptPerfTelecomInputClientPast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pm10010mptPerfTelecomInputClientPast15StatHistoryPort1Entry 4 }


pm10010mptPerfTelecomInputClientPast15StatHistoryEsValuePort1 OBJECT-TYPE
	SYNTAX  Unsigned32
	MAX-ACCESS read-only
	STATUS current
	DESCRIPTION
        "
        Previous 15-min ES counter :This
        OID gives the previous 15-min Errored
        Second counter value
        "
	::= { pm10010mptPerfTelecomInputClientPast15StatHistoryPort1Entry 5 }


pm10010mptPerfTelecomInputClientPast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pm10010mptPerfTelecomInputClientPast15StatHistoryPort1Entry 6 }


pm10010mptPerfTelecomInputClientPast15StatHistorySesValuePort1 OBJECT-TYPE
	SYNTAX  Unsigned32
	MAX-ACCESS read-only
	STATUS current
	DESCRIPTION
        "
        Previous 15-min SES counter :This
        OID gives the previous 15-min severely
        Errored Second counter value
        "
	::= { pm10010mptPerfTelecomInputClientPast15StatHistoryPort1Entry 7 }


pm10010mptPerfTelecomInputClientPast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pm10010mptPerfTelecomInputClientPast15StatHistoryPort1Entry 8 }


pm10010mptPerfTelecomInputClientPast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pm10010mptPerfTelecomInputClientPast15StatHistoryPort1Entry 9 }


pm10010mptPerfTelecomInputClientPast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pm10010mptPerfTelecomInputClientPast15StatHistoryPort1Entry 10 }


pm10010mptPerfTelecomInputClientPast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pm10010mptPerfTelecomInputClientPast15StatHistoryPort1Entry 11 }


--- *****************************************************
---     Leaf of the telecomInputClientCurrent24Stat
--- *****************************************************
--- *********************************************************
---     TABLE for the pm10010mptPerfTelecomInputClientCurrent24Stat articles
--- *********************************************************

pm10010mptPerfTelecomInputClientCurrent24StatTable OBJECT-TYPE
	SYNTAX  SEQUENCE OF Pm10010mptPerfTelecomInputClientCurrent24StatEntry
	MAX-ACCESS not-accessible
	STATUS current
	DESCRIPTION
        "
        List of pm10010mptPerfTelecomInputClientCurrent24Stat
        Article
        "
	::= { pm10010mptMonPerfClient 48 }


pm10010mptPerfTelecomInputClientCurrent24StatEntry OBJECT-TYPE
	SYNTAX Pm10010mptPerfTelecomInputClientCurrent24StatEntry
	MAX-ACCESS not-accessible
	STATUS current
	DESCRIPTION
        "
        Row definition for the pm10010mptPerfTelecomInputClientCurrent24Stat
        table
        "
	INDEX   { pm10010mptPerfTelecomInputClientCurrent24StatIndex }
	::= { pm10010mptPerfTelecomInputClientCurrent24StatTable 1 }


Pm10010mptPerfTelecomInputClientCurrent24StatEntry ::=
	SEQUENCE {
	pm10010mptPerfTelecomInputClientCurrent24StatIndex
		INTEGER,
	pm10010mptPerfTelecomInputClientCurrent24StatInvCvPortn
		EkiOnOff,
	pm10010mptPerfTelecomInputClientCurrent24StatCvValuePortn
		Unsigned32,
	pm10010mptPerfTelecomInputClientCurrent24StatInvEsPortn
		EkiOnOff,
	pm10010mptPerfTelecomInputClientCurrent24StatEsValuePortn
		Unsigned32,
	pm10010mptPerfTelecomInputClientCurrent24StatInvSesPortn
		EkiOnOff,
	pm10010mptPerfTelecomInputClientCurrent24StatSesValuePortn
		Unsigned32,
	pm10010mptPerfTelecomInputClientCurrent24StatInvSefsPortn
		EkiOnOff,
	pm10010mptPerfTelecomInputClientCurrent24StatSefsValuePortn
		Unsigned32,
	pm10010mptPerfTelecomInputClientCurrent24StatInvUasPortn
		EkiOnOff,
	pm10010mptPerfTelecomInputClientCurrent24StatUasValuePortn
		Unsigned32
	}


pm10010mptPerfTelecomInputClientCurrent24StatIndex OBJECT-TYPE
	SYNTAX  INTEGER(0..128)
	MAX-ACCESS  read-only
	STATUS current
	DESCRIPTION
        "
        Index definition for the pm10010mptPerfTelecomInputClientCurrent24Stat
        table
        "
	::= { pm10010mptPerfTelecomInputClientCurrent24StatEntry 1 }


pm10010mptPerfTelecomInputClientCurrent24StatInvCvPortn OBJECT-TYPE
	SYNTAX  EkiOnOff
	MAX-ACCESS read-only
	STATUS current
	DESCRIPTION
        "
        Current 24-hours EBC counter inv.
        :This OID indicates that the current
        24-hours Coding Violation counter
        is invalid
        "
	::= { pm10010mptPerfTelecomInputClientCurrent24StatEntry 2 }


pm10010mptPerfTelecomInputClientCurrent24StatCvValuePortn OBJECT-TYPE
	SYNTAX  Unsigned32
	MAX-ACCESS read-only
	STATUS current
	DESCRIPTION
        "
        Current 24-hours EBC counter :This
        OID gives the current 24-hours
         Coding Violation counter value
        "
	::= { pm10010mptPerfTelecomInputClientCurrent24StatEntry 3 }


pm10010mptPerfTelecomInputClientCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pm10010mptPerfTelecomInputClientCurrent24StatEntry 4 }


pm10010mptPerfTelecomInputClientCurrent24StatEsValuePortn OBJECT-TYPE
	SYNTAX  Unsigned32
	MAX-ACCESS read-only
	STATUS current
	DESCRIPTION
        "
        Current 24-hours ES counter :This
        OID gives the current 24-hours
         Errored Second counter value
        "
	::= { pm10010mptPerfTelecomInputClientCurrent24StatEntry 5 }


pm10010mptPerfTelecomInputClientCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pm10010mptPerfTelecomInputClientCurrent24StatEntry 6 }


pm10010mptPerfTelecomInputClientCurrent24StatSesValuePortn OBJECT-TYPE
	SYNTAX  Unsigned32
	MAX-ACCESS read-only
	STATUS current
	DESCRIPTION
        "
        Current 24-hours SES counter :This
        OID gives the current 24-hours
         severely Errored Second counter
        value
        "
	::= { pm10010mptPerfTelecomInputClientCurrent24StatEntry 7 }


pm10010mptPerfTelecomInputClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pm10010mptPerfTelecomInputClientCurrent24StatEntry 8 }


pm10010mptPerfTelecomInputClientCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pm10010mptPerfTelecomInputClientCurrent24StatEntry 9 }


pm10010mptPerfTelecomInputClientCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pm10010mptPerfTelecomInputClientCurrent24StatEntry 10 }


pm10010mptPerfTelecomInputClientCurrent24StatUasValuePortn OBJECT-TYPE
	SYNTAX  Unsigned32
	MAX-ACCESS read-only
	STATUS current
	DESCRIPTION
        "
        Current 24-hours UAS counter :This
        OID gives the current 24-hours
         UnAvailable Second counter value
        "
	::= { pm10010mptPerfTelecomInputClientCurrent24StatEntry 11 }


--- *****************************************************
---     Leaf of the telecomInputClientPast24Stat
--- *****************************************************
--- *********************************************************
---     TABLE for the pm10010mptPerfTelecomInputClientPast24StatHistory articles
--- *********************************************************

pm10010mptPerfTelecomInputClientPast24StatHistoryPort1Table OBJECT-TYPE
	SYNTAX  SEQUENCE OF Pm10010mptPerfTelecomInputClientPast24StatHistoryPort1Entry
	MAX-ACCESS not-accessible
	STATUS current
	DESCRIPTION
        "
        List of pm10010mptPerfTelecomInputClientPast24StatHistory
        Article
        "
	::= { pm10010mptMonPerfClient 64 }


pm10010mptPerfTelecomInputClientPast24StatHistoryPort1Entry OBJECT-TYPE
	SYNTAX Pm10010mptPerfTelecomInputClientPast24StatHistoryPort1Entry
	MAX-ACCESS not-accessible
	STATUS current
	DESCRIPTION
        "
        Row definition for the pm10010mptPerfTelecomInputClientPast24StatHistory
        table
        "
	INDEX   { pm10010mptPerfTelecomInputClientPast24StatHistoryPort1Index }
	::= { pm10010mptPerfTelecomInputClientPast24StatHistoryPort1Table 1 }


Pm10010mptPerfTelecomInputClientPast24StatHistoryPort1Entry ::=
	SEQUENCE {
	pm10010mptPerfTelecomInputClientPast24StatHistoryPort1Index
		INTEGER,
	pm10010mptPerfTelecomInputClientPast24StatHistoryInvCvPort1
		EkiOnOff,
	pm10010mptPerfTelecomInputClientPast24StatHistoryCvValuePort1
		Unsigned32,
	pm10010mptPerfTelecomInputClientPast24StatHistoryInvEsPort1
		EkiOnOff,
	pm10010mptPerfTelecomInputClientPast24StatHistoryEsValuePort1
		Unsigned32,
	pm10010mptPerfTelecomInputClientPast24StatHistoryInvSesPort1
		EkiOnOff,
	pm10010mptPerfTelecomInputClientPast24StatHistorySesValuePort1
		Unsigned32,
	pm10010mptPerfTelecomInputClientPast24StatHistoryInvSefsPort1
		EkiOnOff,
	pm10010mptPerfTelecomInputClientPast24StatHistorySefsValuePort1
		Unsigned32,
	pm10010mptPerfTelecomInputClientPast24StatHistoryInvUasPort1
		EkiOnOff,
	pm10010mptPerfTelecomInputClientPast24StatHistoryUasValuePort1
		Unsigned32
	}


pm10010mptPerfTelecomInputClientPast24StatHistoryPort1Index OBJECT-TYPE
	SYNTAX  INTEGER(0..128)
	MAX-ACCESS  read-only
	STATUS current
	DESCRIPTION
        "
        Index definition for the pm10010mptPerfTelecomInputClientPast24StatHistory
        table
        "
	::= { pm10010mptPerfTelecomInputClientPast24StatHistoryPort1Entry 1 }


pm10010mptPerfTelecomInputClientPast24StatHistoryInvCvPort1 OBJECT-TYPE
	SYNTAX  EkiOnOff
	MAX-ACCESS read-only
	STATUS current
	DESCRIPTION
        "
        Previous 24-hours EBC counter
         inv. :This OID indicates that
         the previous 24-hours Coding Violation
        counter is invalid
        "
	::= { pm10010mptPerfTelecomInputClientPast24StatHistoryPort1Entry 2 }


pm10010mptPerfTelecomInputClientPast24StatHistoryCvValuePort1 OBJECT-TYPE
	SYNTAX  Unsigned32
	MAX-ACCESS read-only
	STATUS current
	DESCRIPTION
        "
        Previous 24-hours EBC counter
         :This OID gives the previous 24-hours
        Coding Violation counter value
        "
	::= { pm10010mptPerfTelecomInputClientPast24StatHistoryPort1Entry 3 }


pm10010mptPerfTelecomInputClientPast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pm10010mptPerfTelecomInputClientPast24StatHistoryPort1Entry 4 }


pm10010mptPerfTelecomInputClientPast24StatHistoryEsValuePort1 OBJECT-TYPE
	SYNTAX  Unsigned32
	MAX-ACCESS read-only
	STATUS current
	DESCRIPTION
        "
        Previous 24-hours ES counter :This
        OID gives the previous 24-hours
        Errored Second counter value
        "
	::= { pm10010mptPerfTelecomInputClientPast24StatHistoryPort1Entry 5 }


pm10010mptPerfTelecomInputClientPast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pm10010mptPerfTelecomInputClientPast24StatHistoryPort1Entry 6 }


pm10010mptPerfTelecomInputClientPast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pm10010mptPerfTelecomInputClientPast24StatHistoryPort1Entry 7 }


pm10010mptPerfTelecomInputClientPast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm10010mptPerfTelecomInputClientPast24StatHistoryPort1Entry 8 }


pm10010mptPerfTelecomInputClientPast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pm10010mptPerfTelecomInputClientPast24StatHistoryPort1Entry 9 }


pm10010mptPerfTelecomInputClientPast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pm10010mptPerfTelecomInputClientPast24StatHistoryPort1Entry 10 }


pm10010mptPerfTelecomInputClientPast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pm10010mptPerfTelecomInputClientPast24StatHistoryPort1Entry 11 }


--- *****************************************************
---     Leaf of the telecomOutputClientCurrent15Stat
--- *****************************************************
--- *********************************************************
---     TABLE for the pm10010mptPerfTelecomOutputClientCurrent15Stat articles
--- *********************************************************

pm10010mptPerfTelecomOutputClientCurrent15StatTable OBJECT-TYPE
	SYNTAX  SEQUENCE OF Pm10010mptPerfTelecomOutputClientCurrent15StatEntry
	MAX-ACCESS not-accessible
	STATUS current
	DESCRIPTION
        "
        List of pm10010mptPerfTelecomOutputClientCurrent15Stat
        Article
        "
	::= { pm10010mptMonPerfClient 80 }


pm10010mptPerfTelecomOutputClientCurrent15StatEntry OBJECT-TYPE
	SYNTAX Pm10010mptPerfTelecomOutputClientCurrent15StatEntry
	MAX-ACCESS not-accessible
	STATUS current
	DESCRIPTION
        "
        Row definition for the pm10010mptPerfTelecomOutputClientCurrent15Stat
        table
        "
	INDEX   { pm10010mptPerfTelecomOutputClientCurrent15StatIndex }
	::= { pm10010mptPerfTelecomOutputClientCurrent15StatTable 1 }


Pm10010mptPerfTelecomOutputClientCurrent15StatEntry ::=
	SEQUENCE {
	pm10010mptPerfTelecomOutputClientCurrent15StatIndex
		INTEGER,
	pm10010mptPerfTelecomOutputClientCurrent15StatInvCvPortn
		EkiOnOff,
	pm10010mptPerfTelecomOutputClientCurrent15StatCvValuePortn
		Unsigned32,
	pm10010mptPerfTelecomOutputClientCurrent15StatInvEsPortn
		EkiOnOff,
	pm10010mptPerfTelecomOutputClientCurrent15StatEsValuePortn
		Unsigned32,
	pm10010mptPerfTelecomOutputClientCurrent15StatInvSesPortn
		EkiOnOff,
	pm10010mptPerfTelecomOutputClientCurrent15StatSesValuePortn
		Unsigned32,
	pm10010mptPerfTelecomOutputClientCurrent15StatInvSefsPortn
		EkiOnOff,
	pm10010mptPerfTelecomOutputClientCurrent15StatSefsValuePortn
		Unsigned32,
	pm10010mptPerfTelecomOutputClientCurrent15StatInvUasPortn
		EkiOnOff,
	pm10010mptPerfTelecomOutputClientCurrent15StatUasValuePortn
		Unsigned32
	}


pm10010mptPerfTelecomOutputClientCurrent15StatIndex OBJECT-TYPE
	SYNTAX  INTEGER(0..128)
	MAX-ACCESS  read-only
	STATUS current
	DESCRIPTION
        "
        Index definition for the pm10010mptPerfTelecomOutputClientCurrent15Stat
        table
        "
	::= { pm10010mptPerfTelecomOutputClientCurrent15StatEntry 1 }


pm10010mptPerfTelecomOutputClientCurrent15StatInvCvPortn OBJECT-TYPE
	SYNTAX  EkiOnOff
	MAX-ACCESS read-only
	STATUS current
	DESCRIPTION
        "
        Current 15-min EBC counter inv.
        :This OID indicates that the current
        15-min Coding Violation counter
        is invalid
        "
	::= { pm10010mptPerfTelecomOutputClientCurrent15StatEntry 2 }


pm10010mptPerfTelecomOutputClientCurrent15StatCvValuePortn OBJECT-TYPE
	SYNTAX  Unsigned32
	MAX-ACCESS read-only
	STATUS current
	DESCRIPTION
        "
        Current 15-min EBC counter :This
        OID gives the current 15-min Coding
        Violation counter value
        "
	::= { pm10010mptPerfTelecomOutputClientCurrent15StatEntry 3 }


pm10010mptPerfTelecomOutputClientCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pm10010mptPerfTelecomOutputClientCurrent15StatEntry 4 }


pm10010mptPerfTelecomOutputClientCurrent15StatEsValuePortn OBJECT-TYPE
	SYNTAX  Unsigned32
	MAX-ACCESS read-only
	STATUS current
	DESCRIPTION
        "
        Current 15-min ES counter :This
        OID gives the current 15-min Errored
        Second counter value
        "
	::= { pm10010mptPerfTelecomOutputClientCurrent15StatEntry 5 }


pm10010mptPerfTelecomOutputClientCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pm10010mptPerfTelecomOutputClientCurrent15StatEntry 6 }


pm10010mptPerfTelecomOutputClientCurrent15StatSesValuePortn OBJECT-TYPE
	SYNTAX  Unsigned32
	MAX-ACCESS read-only
	STATUS current
	DESCRIPTION
        "
        Current 15-min SES counter :This
        OID gives the current 15-min severely
        Errored Second counter value
        "
	::= { pm10010mptPerfTelecomOutputClientCurrent15StatEntry 7 }


pm10010mptPerfTelecomOutputClientCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pm10010mptPerfTelecomOutputClientCurrent15StatEntry 8 }


pm10010mptPerfTelecomOutputClientCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pm10010mptPerfTelecomOutputClientCurrent15StatEntry 9 }


pm10010mptPerfTelecomOutputClientCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pm10010mptPerfTelecomOutputClientCurrent15StatEntry 10 }


pm10010mptPerfTelecomOutputClientCurrent15StatUasValuePortn OBJECT-TYPE
	SYNTAX  Unsigned32
	MAX-ACCESS read-only
	STATUS current
	DESCRIPTION
        "
        Current 15-min UAS counter :This
        OID gives the current 15-min UnAvailable
        Second counter value
        "
	::= { pm10010mptPerfTelecomOutputClientCurrent15StatEntry 11 }


--- *****************************************************
---     Leaf of the telecomOutputClientPast15Stat
--- *****************************************************
--- *********************************************************
---     TABLE for the pm10010mptPerfTelecomOutputClientPast15StatHistory articles
--- *********************************************************

pm10010mptPerfTelecomOutputClientPast15StatHistoryPort1Table OBJECT-TYPE
	SYNTAX  SEQUENCE OF Pm10010mptPerfTelecomOutputClientPast15StatHistoryPort1Entry
	MAX-ACCESS not-accessible
	STATUS current
	DESCRIPTION
        "
        List of pm10010mptPerfTelecomOutputClientPast15StatHistory
        Article
        "
	::= { pm10010mptMonPerfClient 96 }


pm10010mptPerfTelecomOutputClientPast15StatHistoryPort1Entry OBJECT-TYPE
	SYNTAX Pm10010mptPerfTelecomOutputClientPast15StatHistoryPort1Entry
	MAX-ACCESS not-accessible
	STATUS current
	DESCRIPTION
        "
        Row definition for the pm10010mptPerfTelecomOutputClientPast15StatHistory
        table
        "
	INDEX   { pm10010mptPerfTelecomOutputClientPast15StatHistoryPort1Index }
	::= { pm10010mptPerfTelecomOutputClientPast15StatHistoryPort1Table 1 }


Pm10010mptPerfTelecomOutputClientPast15StatHistoryPort1Entry ::=
	SEQUENCE {
	pm10010mptPerfTelecomOutputClientPast15StatHistoryPort1Index
		INTEGER,
	pm10010mptPerfTelecomOutputClientPast15StatHistoryInvCvPort1
		EkiOnOff,
	pm10010mptPerfTelecomOutputClientPast15StatHistoryCvValuePort1
		Unsigned32,
	pm10010mptPerfTelecomOutputClientPast15StatHistoryInvEsPort1
		EkiOnOff,
	pm10010mptPerfTelecomOutputClientPast15StatHistoryEsValuePort1
		Unsigned32,
	pm10010mptPerfTelecomOutputClientPast15StatHistoryInvSesPort1
		EkiOnOff,
	pm10010mptPerfTelecomOutputClientPast15StatHistorySesValuePort1
		Unsigned32,
	pm10010mptPerfTelecomOutputClientPast15StatHistoryInvSefsPort1
		EkiOnOff,
	pm10010mptPerfTelecomOutputClientPast15StatHistorySefsValuePort1
		Unsigned32,
	pm10010mptPerfTelecomOutputClientPast15StatHistoryInvUasPort1
		EkiOnOff,
	pm10010mptPerfTelecomOutputClientPast15StatHistoryUasValuePort1
		Unsigned32
	}


pm10010mptPerfTelecomOutputClientPast15StatHistoryPort1Index OBJECT-TYPE
	SYNTAX  INTEGER(0..128)
	MAX-ACCESS  read-only
	STATUS current
	DESCRIPTION
        "
        Index definition for the pm10010mptPerfTelecomOutputClientPast15StatHistory
        table
        "
	::= { pm10010mptPerfTelecomOutputClientPast15StatHistoryPort1Entry 1 }


pm10010mptPerfTelecomOutputClientPast15StatHistoryInvCvPort1 OBJECT-TYPE
	SYNTAX  EkiOnOff
	MAX-ACCESS read-only
	STATUS current
	DESCRIPTION
        "
        Previous 15-min EBC counter inv.
        :This OID indicates that the previous
        15-min Coding Violation counter
        is invalid
        "
	::= { pm10010mptPerfTelecomOutputClientPast15StatHistoryPort1Entry 2 }


pm10010mptPerfTelecomOutputClientPast15StatHistoryCvValuePort1 OBJECT-TYPE
	SYNTAX  Unsigned32
	MAX-ACCESS read-only
	STATUS current
	DESCRIPTION
        "
        Previous 15-min EBC counter :This
        OID gives the previous 15-min Coding
        Violation counter value
        "
	::= { pm10010mptPerfTelecomOutputClientPast15StatHistoryPort1Entry 3 }


pm10010mptPerfTelecomOutputClientPast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pm10010mptPerfTelecomOutputClientPast15StatHistoryPort1Entry 4 }


pm10010mptPerfTelecomOutputClientPast15StatHistoryEsValuePort1 OBJECT-TYPE
	SYNTAX  Unsigned32
	MAX-ACCESS read-only
	STATUS current
	DESCRIPTION
        "
        Previous 15-min ES counter :This
        OID gives the previous 15-min Errored
        Second counter value
        "
	::= { pm10010mptPerfTelecomOutputClientPast15StatHistoryPort1Entry 5 }


pm10010mptPerfTelecomOutputClientPast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pm10010mptPerfTelecomOutputClientPast15StatHistoryPort1Entry 6 }


pm10010mptPerfTelecomOutputClientPast15StatHistorySesValuePort1 OBJECT-TYPE
	SYNTAX  Unsigned32
	MAX-ACCESS read-only
	STATUS current
	DESCRIPTION
        "
        Previous 15-min SES counter :This
        OID gives the previous 15-min severely
        Errored Second counter value
        "
	::= { pm10010mptPerfTelecomOutputClientPast15StatHistoryPort1Entry 7 }


pm10010mptPerfTelecomOutputClientPast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pm10010mptPerfTelecomOutputClientPast15StatHistoryPort1Entry 8 }


pm10010mptPerfTelecomOutputClientPast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pm10010mptPerfTelecomOutputClientPast15StatHistoryPort1Entry 9 }


pm10010mptPerfTelecomOutputClientPast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pm10010mptPerfTelecomOutputClientPast15StatHistoryPort1Entry 10 }


pm10010mptPerfTelecomOutputClientPast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pm10010mptPerfTelecomOutputClientPast15StatHistoryPort1Entry 11 }


--- *****************************************************
---     Leaf of the telecomOutputClientCurrent24Stat
--- *****************************************************
--- *********************************************************
---     TABLE for the pm10010mptPerfTelecomOutputClientCurrent24Stat articles
--- *********************************************************

pm10010mptPerfTelecomOutputClientCurrent24StatTable OBJECT-TYPE
	SYNTAX  SEQUENCE OF Pm10010mptPerfTelecomOutputClientCurrent24StatEntry
	MAX-ACCESS not-accessible
	STATUS current
	DESCRIPTION
        "
        List of pm10010mptPerfTelecomOutputClientCurrent24Stat
        Article
        "
	::= { pm10010mptMonPerfClient 112 }


pm10010mptPerfTelecomOutputClientCurrent24StatEntry OBJECT-TYPE
	SYNTAX Pm10010mptPerfTelecomOutputClientCurrent24StatEntry
	MAX-ACCESS not-accessible
	STATUS current
	DESCRIPTION
        "
        Row definition for the pm10010mptPerfTelecomOutputClientCurrent24Stat
        table
        "
	INDEX   { pm10010mptPerfTelecomOutputClientCurrent24StatIndex }
	::= { pm10010mptPerfTelecomOutputClientCurrent24StatTable 1 }


Pm10010mptPerfTelecomOutputClientCurrent24StatEntry ::=
	SEQUENCE {
	pm10010mptPerfTelecomOutputClientCurrent24StatIndex
		INTEGER,
	pm10010mptPerfTelecomOutputClientCurrent24StatInvCvPortn
		EkiOnOff,
	pm10010mptPerfTelecomOutputClientCurrent24StatCvValuePortn
		Unsigned32,
	pm10010mptPerfTelecomOutputClientCurrent24StatInvEsPortn
		EkiOnOff,
	pm10010mptPerfTelecomOutputClientCurrent24StatEsValuePortn
		Unsigned32,
	pm10010mptPerfTelecomOutputClientCurrent24StatInvSesPortn
		EkiOnOff,
	pm10010mptPerfTelecomOutputClientCurrent24StatSesValuePortn
		Unsigned32,
	pm10010mptPerfTelecomOutputClientCurrent24StatInvSefsPortn
		EkiOnOff,
	pm10010mptPerfTelecomOutputClientCurrent24StatSefsValuePortn
		Unsigned32,
	pm10010mptPerfTelecomOutputClientCurrent24StatInvUasPortn
		EkiOnOff,
	pm10010mptPerfTelecomOutputClientCurrent24StatUasValuePortn
		Unsigned32
	}


pm10010mptPerfTelecomOutputClientCurrent24StatIndex OBJECT-TYPE
	SYNTAX  INTEGER(0..128)
	MAX-ACCESS  read-only
	STATUS current
	DESCRIPTION
        "
        Index definition for the pm10010mptPerfTelecomOutputClientCurrent24Stat
        table
        "
	::= { pm10010mptPerfTelecomOutputClientCurrent24StatEntry 1 }


pm10010mptPerfTelecomOutputClientCurrent24StatInvCvPortn OBJECT-TYPE
	SYNTAX  EkiOnOff
	MAX-ACCESS read-only
	STATUS current
	DESCRIPTION
        "
        Current 24-hours EBC counter inv.
        :This OID indicates that the current
        24-hours Coding Violation counter
        is invalid
        "
	::= { pm10010mptPerfTelecomOutputClientCurrent24StatEntry 2 }


pm10010mptPerfTelecomOutputClientCurrent24StatCvValuePortn OBJECT-TYPE
	SYNTAX  Unsigned32
	MAX-ACCESS read-only
	STATUS current
	DESCRIPTION
        "
        Current 24-hours EBC counter :This
        OID gives the current 24-hours
         Coding Violation counter value
        "
	::= { pm10010mptPerfTelecomOutputClientCurrent24StatEntry 3 }


pm10010mptPerfTelecomOutputClientCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pm10010mptPerfTelecomOutputClientCurrent24StatEntry 4 }


pm10010mptPerfTelecomOutputClientCurrent24StatEsValuePortn OBJECT-TYPE
	SYNTAX  Unsigned32
	MAX-ACCESS read-only
	STATUS current
	DESCRIPTION
        "
        Current 24-hours ES counter :This
        OID gives the current 24-hours
         Errored Second counter value
        "
	::= { pm10010mptPerfTelecomOutputClientCurrent24StatEntry 5 }


pm10010mptPerfTelecomOutputClientCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pm10010mptPerfTelecomOutputClientCurrent24StatEntry 6 }


pm10010mptPerfTelecomOutputClientCurrent24StatSesValuePortn OBJECT-TYPE
	SYNTAX  Unsigned32
	MAX-ACCESS read-only
	STATUS current
	DESCRIPTION
        "
        Current 24-hours SES counter :This
        OID gives the current 24-hours
         severely Errored Second counter
        value
        "
	::= { pm10010mptPerfTelecomOutputClientCurrent24StatEntry 7 }


pm10010mptPerfTelecomOutputClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pm10010mptPerfTelecomOutputClientCurrent24StatEntry 8 }


pm10010mptPerfTelecomOutputClientCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pm10010mptPerfTelecomOutputClientCurrent24StatEntry 9 }


pm10010mptPerfTelecomOutputClientCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pm10010mptPerfTelecomOutputClientCurrent24StatEntry 10 }


pm10010mptPerfTelecomOutputClientCurrent24StatUasValuePortn OBJECT-TYPE
	SYNTAX  Unsigned32
	MAX-ACCESS read-only
	STATUS current
	DESCRIPTION
        "
        Current 24-hours UAS counter :This
        OID gives the current 24-hours
         UnAvailable Second counter value
        "
	::= { pm10010mptPerfTelecomOutputClientCurrent24StatEntry 11 }


--- *****************************************************
---     Leaf of the telecomOutputClientPast24Stat
--- *****************************************************
--- *********************************************************
---     TABLE for the pm10010mptPerfTelecomOutputClientPast24StatHistory articles
--- *********************************************************

pm10010mptPerfTelecomOutputClientPast24StatHistoryPort1Table OBJECT-TYPE
	SYNTAX  SEQUENCE OF Pm10010mptPerfTelecomOutputClientPast24StatHistoryPort1Entry
	MAX-ACCESS not-accessible
	STATUS current
	DESCRIPTION
        "
        List of pm10010mptPerfTelecomOutputClientPast24StatHistory
        Article
        "
	::= { pm10010mptMonPerfClient 128 }


pm10010mptPerfTelecomOutputClientPast24StatHistoryPort1Entry OBJECT-TYPE
	SYNTAX Pm10010mptPerfTelecomOutputClientPast24StatHistoryPort1Entry
	MAX-ACCESS not-accessible
	STATUS current
	DESCRIPTION
        "
        Row definition for the pm10010mptPerfTelecomOutputClientPast24StatHistory
        table
        "
	INDEX   { pm10010mptPerfTelecomOutputClientPast24StatHistoryPort1Index }
	::= { pm10010mptPerfTelecomOutputClientPast24StatHistoryPort1Table 1 }


Pm10010mptPerfTelecomOutputClientPast24StatHistoryPort1Entry ::=
	SEQUENCE {
	pm10010mptPerfTelecomOutputClientPast24StatHistoryPort1Index
		INTEGER,
	pm10010mptPerfTelecomOutputClientPast24StatHistoryInvCvPort1
		EkiOnOff,
	pm10010mptPerfTelecomOutputClientPast24StatHistoryCvValuePort1
		Unsigned32,
	pm10010mptPerfTelecomOutputClientPast24StatHistoryInvEsPort1
		EkiOnOff,
	pm10010mptPerfTelecomOutputClientPast24StatHistoryEsValuePort1
		Unsigned32,
	pm10010mptPerfTelecomOutputClientPast24StatHistoryInvSesPort1
		EkiOnOff,
	pm10010mptPerfTelecomOutputClientPast24StatHistorySesValuePort1
		Unsigned32,
	pm10010mptPerfTelecomOutputClientPast24StatHistoryInvSefsPort1
		EkiOnOff,
	pm10010mptPerfTelecomOutputClientPast24StatHistorySefsValuePort1
		Unsigned32,
	pm10010mptPerfTelecomOutputClientPast24StatHistoryInvUasPort1
		EkiOnOff,
	pm10010mptPerfTelecomOutputClientPast24StatHistoryUasValuePort1
		Unsigned32
	}


pm10010mptPerfTelecomOutputClientPast24StatHistoryPort1Index OBJECT-TYPE
	SYNTAX  INTEGER(0..128)
	MAX-ACCESS  read-only
	STATUS current
	DESCRIPTION
        "
        Index definition for the pm10010mptPerfTelecomOutputClientPast24StatHistory
        table
        "
	::= { pm10010mptPerfTelecomOutputClientPast24StatHistoryPort1Entry 1 }


pm10010mptPerfTelecomOutputClientPast24StatHistoryInvCvPort1 OBJECT-TYPE
	SYNTAX  EkiOnOff
	MAX-ACCESS read-only
	STATUS current
	DESCRIPTION
        "
        Previous 24-hours EBC counter
         inv. :This OID indicates that
         the previous 24-hours Coding Violation
        counter is invalid
        "
	::= { pm10010mptPerfTelecomOutputClientPast24StatHistoryPort1Entry 2 }


pm10010mptPerfTelecomOutputClientPast24StatHistoryCvValuePort1 OBJECT-TYPE
	SYNTAX  Unsigned32
	MAX-ACCESS read-only
	STATUS current
	DESCRIPTION
        "
        Previous 24-hours EBC counter
         :This OID gives the previous 24-hours
        Coding Violation counter value
        "
	::= { pm10010mptPerfTelecomOutputClientPast24StatHistoryPort1Entry 3 }


pm10010mptPerfTelecomOutputClientPast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pm10010mptPerfTelecomOutputClientPast24StatHistoryPort1Entry 4 }


pm10010mptPerfTelecomOutputClientPast24StatHistoryEsValuePort1 OBJECT-TYPE
	SYNTAX  Unsigned32
	MAX-ACCESS read-only
	STATUS current
	DESCRIPTION
        "
        Previous 24-hours ES counter :This
        OID gives the previous 24-hours
        Errored Second counter value
        "
	::= { pm10010mptPerfTelecomOutputClientPast24StatHistoryPort1Entry 5 }


pm10010mptPerfTelecomOutputClientPast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pm10010mptPerfTelecomOutputClientPast24StatHistoryPort1Entry 6 }


pm10010mptPerfTelecomOutputClientPast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pm10010mptPerfTelecomOutputClientPast24StatHistoryPort1Entry 7 }


pm10010mptPerfTelecomOutputClientPast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm10010mptPerfTelecomOutputClientPast24StatHistoryPort1Entry 8 }


pm10010mptPerfTelecomOutputClientPast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pm10010mptPerfTelecomOutputClientPast24StatHistoryPort1Entry 9 }


pm10010mptPerfTelecomOutputClientPast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pm10010mptPerfTelecomOutputClientPast24StatHistoryPort1Entry 10 }


pm10010mptPerfTelecomOutputClientPast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pm10010mptPerfTelecomOutputClientPast24StatHistoryPort1Entry 11 }


--- *****************************************************
---     Leaf of the telecomLinePostFecCurrent15Stat
--- *****************************************************
--- *********************************************************
---     TABLE for the pm10010mptPerfTelecomLinePostFecCurrent15Stat articles
--- *********************************************************

pm10010mptPerfTelecomLinePostFecCurrent15StatTable OBJECT-TYPE
	SYNTAX  SEQUENCE OF Pm10010mptPerfTelecomLinePostFecCurrent15StatEntry
	MAX-ACCESS not-accessible
	STATUS current
	DESCRIPTION
        "
        List of pm10010mptPerfTelecomLinePostFecCurrent15Stat
        Article
        "
	::= { pm10010mptMonPerfLine 192 }


pm10010mptPerfTelecomLinePostFecCurrent15StatEntry OBJECT-TYPE
	SYNTAX Pm10010mptPerfTelecomLinePostFecCurrent15StatEntry
	MAX-ACCESS not-accessible
	STATUS current
	DESCRIPTION
        "
        Row definition for the pm10010mptPerfTelecomLinePostFecCurrent15Stat
        table
        "
	INDEX   { pm10010mptPerfTelecomLinePostFecCurrent15StatIndex }
	::= { pm10010mptPerfTelecomLinePostFecCurrent15StatTable 1 }


Pm10010mptPerfTelecomLinePostFecCurrent15StatEntry ::=
	SEQUENCE {
	pm10010mptPerfTelecomLinePostFecCurrent15StatIndex
		INTEGER,
	pm10010mptPerfTelecomLinePostFecCurrent15StatInvCvPortn
		EkiOnOff,
	pm10010mptPerfTelecomLinePostFecCurrent15StatCvValuePortn
		Unsigned32,
	pm10010mptPerfTelecomLinePostFecCurrent15StatInvEsPortn
		EkiOnOff,
	pm10010mptPerfTelecomLinePostFecCurrent15StatEsValuePortn
		Unsigned32,
	pm10010mptPerfTelecomLinePostFecCurrent15StatInvSesPortn
		EkiOnOff,
	pm10010mptPerfTelecomLinePostFecCurrent15StatSesValuePortn
		Unsigned32,
	pm10010mptPerfTelecomLinePostFecCurrent15StatInvSefsPortn
		EkiOnOff,
	pm10010mptPerfTelecomLinePostFecCurrent15StatSefsValuePortn
		Unsigned32,
	pm10010mptPerfTelecomLinePostFecCurrent15StatInvUasPortn
		EkiOnOff,
	pm10010mptPerfTelecomLinePostFecCurrent15StatUasValuePortn
		Unsigned32
	}


pm10010mptPerfTelecomLinePostFecCurrent15StatIndex OBJECT-TYPE
	SYNTAX  INTEGER(0..128)
	MAX-ACCESS  read-only
	STATUS current
	DESCRIPTION
        "
        Index definition for the pm10010mptPerfTelecomLinePostFecCurrent15Stat
        table
        "
	::= { pm10010mptPerfTelecomLinePostFecCurrent15StatEntry 1 }


pm10010mptPerfTelecomLinePostFecCurrent15StatInvCvPortn OBJECT-TYPE
	SYNTAX  EkiOnOff
	MAX-ACCESS read-only
	STATUS current
	DESCRIPTION
        "
        Current 15-min EBC counter inv.
        :This OID indicates that the current
        15-min Coding Violation counter
        is invalid
        "
	::= { pm10010mptPerfTelecomLinePostFecCurrent15StatEntry 2 }


pm10010mptPerfTelecomLinePostFecCurrent15StatCvValuePortn OBJECT-TYPE
	SYNTAX  Unsigned32
	MAX-ACCESS read-only
	STATUS current
	DESCRIPTION
        "
        Current 15-min EBC counter :This
        OID gives the current 15-min Coding
        Violation counter value
        "
	::= { pm10010mptPerfTelecomLinePostFecCurrent15StatEntry 3 }


pm10010mptPerfTelecomLinePostFecCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pm10010mptPerfTelecomLinePostFecCurrent15StatEntry 4 }


pm10010mptPerfTelecomLinePostFecCurrent15StatEsValuePortn OBJECT-TYPE
	SYNTAX  Unsigned32
	MAX-ACCESS read-only
	STATUS current
	DESCRIPTION
        "
        Current 15-min ES counter :This
        OID gives the current 15-min Errored
        Second counter value
        "
	::= { pm10010mptPerfTelecomLinePostFecCurrent15StatEntry 5 }


pm10010mptPerfTelecomLinePostFecCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pm10010mptPerfTelecomLinePostFecCurrent15StatEntry 6 }


pm10010mptPerfTelecomLinePostFecCurrent15StatSesValuePortn OBJECT-TYPE
	SYNTAX  Unsigned32
	MAX-ACCESS read-only
	STATUS current
	DESCRIPTION
        "
        Current 15-min SES counter :This
        OID gives the current 15-min severely
        Errored Second counter value
        "
	::= { pm10010mptPerfTelecomLinePostFecCurrent15StatEntry 7 }


pm10010mptPerfTelecomLinePostFecCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pm10010mptPerfTelecomLinePostFecCurrent15StatEntry 8 }


pm10010mptPerfTelecomLinePostFecCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pm10010mptPerfTelecomLinePostFecCurrent15StatEntry 9 }


pm10010mptPerfTelecomLinePostFecCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pm10010mptPerfTelecomLinePostFecCurrent15StatEntry 10 }


pm10010mptPerfTelecomLinePostFecCurrent15StatUasValuePortn OBJECT-TYPE
	SYNTAX  Unsigned32
	MAX-ACCESS read-only
	STATUS current
	DESCRIPTION
        "
        Current 15-min UAS counter :This
        OID gives the current 15-min UnAvailable
        Second counter value
        "
	::= { pm10010mptPerfTelecomLinePostFecCurrent15StatEntry 11 }


--- *****************************************************
---     Leaf of the telecomLinePostFecPast15Stat
--- *****************************************************
--- *********************************************************
---     TABLE for the pm10010mptPerfTelecomLinePostFecPast15StatHistory articles
--- *********************************************************

pm10010mptPerfTelecomLinePostFecPast15StatHistoryPort1Table OBJECT-TYPE
	SYNTAX  SEQUENCE OF Pm10010mptPerfTelecomLinePostFecPast15StatHistoryPort1Entry
	MAX-ACCESS not-accessible
	STATUS current
	DESCRIPTION
        "
        List of pm10010mptPerfTelecomLinePostFecPast15StatHistory
        Article
        "
	::= { pm10010mptMonPerfLine 193 }


pm10010mptPerfTelecomLinePostFecPast15StatHistoryPort1Entry OBJECT-TYPE
	SYNTAX Pm10010mptPerfTelecomLinePostFecPast15StatHistoryPort1Entry
	MAX-ACCESS not-accessible
	STATUS current
	DESCRIPTION
        "
        Row definition for the pm10010mptPerfTelecomLinePostFecPast15StatHistory
        table
        "
	INDEX   { pm10010mptPerfTelecomLinePostFecPast15StatHistoryPort1Index }
	::= { pm10010mptPerfTelecomLinePostFecPast15StatHistoryPort1Table 1 }


Pm10010mptPerfTelecomLinePostFecPast15StatHistoryPort1Entry ::=
	SEQUENCE {
	pm10010mptPerfTelecomLinePostFecPast15StatHistoryPort1Index
		INTEGER,
	pm10010mptPerfTelecomLinePostFecPast15StatHistoryInvCvPort1
		EkiOnOff,
	pm10010mptPerfTelecomLinePostFecPast15StatHistoryCvValuePort1
		Unsigned32,
	pm10010mptPerfTelecomLinePostFecPast15StatHistoryInvEsPort1
		EkiOnOff,
	pm10010mptPerfTelecomLinePostFecPast15StatHistoryEsValuePort1
		Unsigned32,
	pm10010mptPerfTelecomLinePostFecPast15StatHistoryInvSesPort1
		EkiOnOff,
	pm10010mptPerfTelecomLinePostFecPast15StatHistorySesValuePort1
		Unsigned32,
	pm10010mptPerfTelecomLinePostFecPast15StatHistoryInvSefsPort1
		EkiOnOff,
	pm10010mptPerfTelecomLinePostFecPast15StatHistorySefsValuePort1
		Unsigned32,
	pm10010mptPerfTelecomLinePostFecPast15StatHistoryInvUasPort1
		EkiOnOff,
	pm10010mptPerfTelecomLinePostFecPast15StatHistoryUasValuePort1
		Unsigned32
	}


pm10010mptPerfTelecomLinePostFecPast15StatHistoryPort1Index OBJECT-TYPE
	SYNTAX  INTEGER(0..128)
	MAX-ACCESS  read-only
	STATUS current
	DESCRIPTION
        "
        Index definition for the pm10010mptPerfTelecomLinePostFecPast15StatHistory
        table
        "
	::= { pm10010mptPerfTelecomLinePostFecPast15StatHistoryPort1Entry 1 }


pm10010mptPerfTelecomLinePostFecPast15StatHistoryInvCvPort1 OBJECT-TYPE
	SYNTAX  EkiOnOff
	MAX-ACCESS read-only
	STATUS current
	DESCRIPTION
        "
        Previous 15-min EBC counter inv.
        :This OID indicates that the previous
        15-min Coding Violation counter
        is invalid
        "
	::= { pm10010mptPerfTelecomLinePostFecPast15StatHistoryPort1Entry 2 }


pm10010mptPerfTelecomLinePostFecPast15StatHistoryCvValuePort1 OBJECT-TYPE
	SYNTAX  Unsigned32
	MAX-ACCESS read-only
	STATUS current
	DESCRIPTION
        "
        Previous 15-min EBC counter :This
        OID gives the previous 15-min Coding
        Violation counter value
        "
	::= { pm10010mptPerfTelecomLinePostFecPast15StatHistoryPort1Entry 3 }


pm10010mptPerfTelecomLinePostFecPast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pm10010mptPerfTelecomLinePostFecPast15StatHistoryPort1Entry 4 }


pm10010mptPerfTelecomLinePostFecPast15StatHistoryEsValuePort1 OBJECT-TYPE
	SYNTAX  Unsigned32
	MAX-ACCESS read-only
	STATUS current
	DESCRIPTION
        "
        Previous 15-min ES counter :This
        OID gives the previous 15-min Errored
        Second counter value
        "
	::= { pm10010mptPerfTelecomLinePostFecPast15StatHistoryPort1Entry 5 }


pm10010mptPerfTelecomLinePostFecPast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pm10010mptPerfTelecomLinePostFecPast15StatHistoryPort1Entry 6 }


pm10010mptPerfTelecomLinePostFecPast15StatHistorySesValuePort1 OBJECT-TYPE
	SYNTAX  Unsigned32
	MAX-ACCESS read-only
	STATUS current
	DESCRIPTION
        "
        Previous 15-min SES counter :This
        OID gives the previous 15-min severely
        Errored Second counter value
        "
	::= { pm10010mptPerfTelecomLinePostFecPast15StatHistoryPort1Entry 7 }


pm10010mptPerfTelecomLinePostFecPast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pm10010mptPerfTelecomLinePostFecPast15StatHistoryPort1Entry 8 }


pm10010mptPerfTelecomLinePostFecPast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pm10010mptPerfTelecomLinePostFecPast15StatHistoryPort1Entry 9 }


pm10010mptPerfTelecomLinePostFecPast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pm10010mptPerfTelecomLinePostFecPast15StatHistoryPort1Entry 10 }


pm10010mptPerfTelecomLinePostFecPast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pm10010mptPerfTelecomLinePostFecPast15StatHistoryPort1Entry 11 }


--- *****************************************************
---     Leaf of the telecomLinePostFecCurrent24Stat
--- *****************************************************
--- *********************************************************
---     TABLE for the pm10010mptPerfTelecomLinePostFecCurrent24Stat articles
--- *********************************************************

pm10010mptPerfTelecomLinePostFecCurrent24StatTable OBJECT-TYPE
	SYNTAX  SEQUENCE OF Pm10010mptPerfTelecomLinePostFecCurrent24StatEntry
	MAX-ACCESS not-accessible
	STATUS current
	DESCRIPTION
        "
        List of pm10010mptPerfTelecomLinePostFecCurrent24Stat
        Article
        "
	::= { pm10010mptMonPerfLine 194 }


pm10010mptPerfTelecomLinePostFecCurrent24StatEntry OBJECT-TYPE
	SYNTAX Pm10010mptPerfTelecomLinePostFecCurrent24StatEntry
	MAX-ACCESS not-accessible
	STATUS current
	DESCRIPTION
        "
        Row definition for the pm10010mptPerfTelecomLinePostFecCurrent24Stat
        table
        "
	INDEX   { pm10010mptPerfTelecomLinePostFecCurrent24StatIndex }
	::= { pm10010mptPerfTelecomLinePostFecCurrent24StatTable 1 }


Pm10010mptPerfTelecomLinePostFecCurrent24StatEntry ::=
	SEQUENCE {
	pm10010mptPerfTelecomLinePostFecCurrent24StatIndex
		INTEGER,
	pm10010mptPerfTelecomLinePostFecCurrent24StatInvCvPortn
		EkiOnOff,
	pm10010mptPerfTelecomLinePostFecCurrent24StatCvValuePortn
		Unsigned32,
	pm10010mptPerfTelecomLinePostFecCurrent24StatInvEsPortn
		EkiOnOff,
	pm10010mptPerfTelecomLinePostFecCurrent24StatEsValuePortn
		Unsigned32,
	pm10010mptPerfTelecomLinePostFecCurrent24StatInvSesPortn
		EkiOnOff,
	pm10010mptPerfTelecomLinePostFecCurrent24StatSesValuePortn
		Unsigned32,
	pm10010mptPerfTelecomLinePostFecCurrent24StatInvSefsPortn
		EkiOnOff,
	pm10010mptPerfTelecomLinePostFecCurrent24StatSefsValuePortn
		Unsigned32,
	pm10010mptPerfTelecomLinePostFecCurrent24StatInvUasPortn
		EkiOnOff,
	pm10010mptPerfTelecomLinePostFecCurrent24StatUasValuePortn
		Unsigned32
	}


pm10010mptPerfTelecomLinePostFecCurrent24StatIndex OBJECT-TYPE
	SYNTAX  INTEGER(0..128)
	MAX-ACCESS  read-only
	STATUS current
	DESCRIPTION
        "
        Index definition for the pm10010mptPerfTelecomLinePostFecCurrent24Stat
        table
        "
	::= { pm10010mptPerfTelecomLinePostFecCurrent24StatEntry 1 }


pm10010mptPerfTelecomLinePostFecCurrent24StatInvCvPortn OBJECT-TYPE
	SYNTAX  EkiOnOff
	MAX-ACCESS read-only
	STATUS current
	DESCRIPTION
        "
        Current 24-hours EBC counter inv.
        :This OID indicates that the current
        24-hours Coding Violation counter
        is invalid
        "
	::= { pm10010mptPerfTelecomLinePostFecCurrent24StatEntry 2 }


pm10010mptPerfTelecomLinePostFecCurrent24StatCvValuePortn OBJECT-TYPE
	SYNTAX  Unsigned32
	MAX-ACCESS read-only
	STATUS current
	DESCRIPTION
        "
        Current 24-hours EBC counter :This
        OID gives the current 24-hours
         Coding Violation counter value
        "
	::= { pm10010mptPerfTelecomLinePostFecCurrent24StatEntry 3 }


pm10010mptPerfTelecomLinePostFecCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pm10010mptPerfTelecomLinePostFecCurrent24StatEntry 4 }


pm10010mptPerfTelecomLinePostFecCurrent24StatEsValuePortn OBJECT-TYPE
	SYNTAX  Unsigned32
	MAX-ACCESS read-only
	STATUS current
	DESCRIPTION
        "
        Current 24-hours ES counter :This
        OID gives the current 24-hours
         Errored Second counter value
        "
	::= { pm10010mptPerfTelecomLinePostFecCurrent24StatEntry 5 }


pm10010mptPerfTelecomLinePostFecCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pm10010mptPerfTelecomLinePostFecCurrent24StatEntry 6 }


pm10010mptPerfTelecomLinePostFecCurrent24StatSesValuePortn OBJECT-TYPE
	SYNTAX  Unsigned32
	MAX-ACCESS read-only
	STATUS current
	DESCRIPTION
        "
        Current 24-hours SES counter :This
        OID gives the current 24-hours
         severely Errored Second counter
        value
        "
	::= { pm10010mptPerfTelecomLinePostFecCurrent24StatEntry 7 }


pm10010mptPerfTelecomLinePostFecCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pm10010mptPerfTelecomLinePostFecCurrent24StatEntry 8 }


pm10010mptPerfTelecomLinePostFecCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pm10010mptPerfTelecomLinePostFecCurrent24StatEntry 9 }


pm10010mptPerfTelecomLinePostFecCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pm10010mptPerfTelecomLinePostFecCurrent24StatEntry 10 }


pm10010mptPerfTelecomLinePostFecCurrent24StatUasValuePortn OBJECT-TYPE
	SYNTAX  Unsigned32
	MAX-ACCESS read-only
	STATUS current
	DESCRIPTION
        "
        Current 24-hours UAS counter :This
        OID gives the current 24-hours
         UnAvailable Second counter value
        "
	::= { pm10010mptPerfTelecomLinePostFecCurrent24StatEntry 11 }


--- *****************************************************
---     Leaf of the telecomLinePostFecPast24Stat
--- *****************************************************
--- *********************************************************
---     TABLE for the pm10010mptPerfTelecomLinePostFecPast24StatHistory articles
--- *********************************************************

pm10010mptPerfTelecomLinePostFecPast24StatHistoryPort1Table OBJECT-TYPE
	SYNTAX  SEQUENCE OF Pm10010mptPerfTelecomLinePostFecPast24StatHistoryPort1Entry
	MAX-ACCESS not-accessible
	STATUS current
	DESCRIPTION
        "
        List of pm10010mptPerfTelecomLinePostFecPast24StatHistory
        Article
        "
	::= { pm10010mptMonPerfLine 195 }


pm10010mptPerfTelecomLinePostFecPast24StatHistoryPort1Entry OBJECT-TYPE
	SYNTAX Pm10010mptPerfTelecomLinePostFecPast24StatHistoryPort1Entry
	MAX-ACCESS not-accessible
	STATUS current
	DESCRIPTION
        "
        Row definition for the pm10010mptPerfTelecomLinePostFecPast24StatHistory
        table
        "
	INDEX   { pm10010mptPerfTelecomLinePostFecPast24StatHistoryPort1Index }
	::= { pm10010mptPerfTelecomLinePostFecPast24StatHistoryPort1Table 1 }


Pm10010mptPerfTelecomLinePostFecPast24StatHistoryPort1Entry ::=
	SEQUENCE {
	pm10010mptPerfTelecomLinePostFecPast24StatHistoryPort1Index
		INTEGER,
	pm10010mptPerfTelecomLinePostFecPast24StatHistoryInvCvPort1
		EkiOnOff,
	pm10010mptPerfTelecomLinePostFecPast24StatHistoryCvValuePort1
		Unsigned32,
	pm10010mptPerfTelecomLinePostFecPast24StatHistoryInvEsPort1
		EkiOnOff,
	pm10010mptPerfTelecomLinePostFecPast24StatHistoryEsValuePort1
		Unsigned32,
	pm10010mptPerfTelecomLinePostFecPast24StatHistoryInvSesPort1
		EkiOnOff,
	pm10010mptPerfTelecomLinePostFecPast24StatHistorySesValuePort1
		Unsigned32,
	pm10010mptPerfTelecomLinePostFecPast24StatHistoryInvSefsPort1
		EkiOnOff,
	pm10010mptPerfTelecomLinePostFecPast24StatHistorySefsValuePort1
		Unsigned32,
	pm10010mptPerfTelecomLinePostFecPast24StatHistoryInvUasPort1
		EkiOnOff,
	pm10010mptPerfTelecomLinePostFecPast24StatHistoryUasValuePort1
		Unsigned32
	}


pm10010mptPerfTelecomLinePostFecPast24StatHistoryPort1Index OBJECT-TYPE
	SYNTAX  INTEGER(0..128)
	MAX-ACCESS  read-only
	STATUS current
	DESCRIPTION
        "
        Index definition for the pm10010mptPerfTelecomLinePostFecPast24StatHistory
        table
        "
	::= { pm10010mptPerfTelecomLinePostFecPast24StatHistoryPort1Entry 1 }


pm10010mptPerfTelecomLinePostFecPast24StatHistoryInvCvPort1 OBJECT-TYPE
	SYNTAX  EkiOnOff
	MAX-ACCESS read-only
	STATUS current
	DESCRIPTION
        "
        Previous 24-hours EBC counter
         inv. :This OID indicates that
         the previous 24-hours Coding Violation
        counter is invalid
        "
	::= { pm10010mptPerfTelecomLinePostFecPast24StatHistoryPort1Entry 2 }


pm10010mptPerfTelecomLinePostFecPast24StatHistoryCvValuePort1 OBJECT-TYPE
	SYNTAX  Unsigned32
	MAX-ACCESS read-only
	STATUS current
	DESCRIPTION
        "
        Previous 24-hours EBC counter
         :This OID gives the previous 24-hours
        Coding Violation counter value
        "
	::= { pm10010mptPerfTelecomLinePostFecPast24StatHistoryPort1Entry 3 }


pm10010mptPerfTelecomLinePostFecPast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pm10010mptPerfTelecomLinePostFecPast24StatHistoryPort1Entry 4 }


pm10010mptPerfTelecomLinePostFecPast24StatHistoryEsValuePort1 OBJECT-TYPE
	SYNTAX  Unsigned32
	MAX-ACCESS read-only
	STATUS current
	DESCRIPTION
        "
        Previous 24-hours ES counter :This
        OID gives the previous 24-hours
        Errored Second counter value
        "
	::= { pm10010mptPerfTelecomLinePostFecPast24StatHistoryPort1Entry 5 }


pm10010mptPerfTelecomLinePostFecPast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pm10010mptPerfTelecomLinePostFecPast24StatHistoryPort1Entry 6 }


pm10010mptPerfTelecomLinePostFecPast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pm10010mptPerfTelecomLinePostFecPast24StatHistoryPort1Entry 7 }


pm10010mptPerfTelecomLinePostFecPast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm10010mptPerfTelecomLinePostFecPast24StatHistoryPort1Entry 8 }


pm10010mptPerfTelecomLinePostFecPast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pm10010mptPerfTelecomLinePostFecPast24StatHistoryPort1Entry 9 }


pm10010mptPerfTelecomLinePostFecPast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pm10010mptPerfTelecomLinePostFecPast24StatHistoryPort1Entry 10 }


pm10010mptPerfTelecomLinePostFecPast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pm10010mptPerfTelecomLinePostFecPast24StatHistoryPort1Entry 11 }


--- *****************************************************
---     Leaf of the telecomBerLinePreFecCurrent15Stat
--- *****************************************************
--- *********************************************************
---     TABLE for the pm10010mptPerfTelecomBerLinePreFecCurrent15Stat articles
--- *********************************************************

pm10010mptPerfTelecomBerLinePreFecCurrent15StatTable OBJECT-TYPE
	SYNTAX  SEQUENCE OF Pm10010mptPerfTelecomBerLinePreFecCurrent15StatEntry
	MAX-ACCESS not-accessible
	STATUS current
	DESCRIPTION
        "
        List of pm10010mptPerfTelecomBerLinePreFecCurrent15Stat
        Article
        "
	::= { pm10010mptMonPerfLine 208 }


pm10010mptPerfTelecomBerLinePreFecCurrent15StatEntry OBJECT-TYPE
	SYNTAX Pm10010mptPerfTelecomBerLinePreFecCurrent15StatEntry
	MAX-ACCESS not-accessible
	STATUS current
	DESCRIPTION
        "
        Row definition for the pm10010mptPerfTelecomBerLinePreFecCurrent15Stat
        table
        "
	INDEX   { pm10010mptPerfTelecomBerLinePreFecCurrent15StatIndex }
	::= { pm10010mptPerfTelecomBerLinePreFecCurrent15StatTable 1 }


Pm10010mptPerfTelecomBerLinePreFecCurrent15StatEntry ::=
	SEQUENCE {
	pm10010mptPerfTelecomBerLinePreFecCurrent15StatIndex
		INTEGER,
	pm10010mptPerfTelecomBerLinePreFecCurrent15StatInvBerPortn
		EkiOnOff,
	pm10010mptPerfTelecomBerLinePreFecCurrent15StatBerValuePortn
		Unsigned32,
	pm10010mptPerfTelecomBerLinePreFecCurrent15StatInvMinBerPortn
		EkiOnOff,
	pm10010mptPerfTelecomBerLinePreFecCurrent15StatMinBerValuePortn
		Unsigned32,
	pm10010mptPerfTelecomBerLinePreFecCurrent15StatInvMaxBerPortn
		EkiOnOff,
	pm10010mptPerfTelecomBerLinePreFecCurrent15StatMaxBerValuePortn
		Unsigned32
	}


pm10010mptPerfTelecomBerLinePreFecCurrent15StatIndex OBJECT-TYPE
	SYNTAX  INTEGER(0..128)
	MAX-ACCESS  read-only
	STATUS current
	DESCRIPTION
        "
        Index definition for the pm10010mptPerfTelecomBerLinePreFecCurrent15Stat
        table
        "
	::= { pm10010mptPerfTelecomBerLinePreFecCurrent15StatEntry 1 }


pm10010mptPerfTelecomBerLinePreFecCurrent15StatInvBerPortn OBJECT-TYPE
	SYNTAX  EkiOnOff
	MAX-ACCESS read-only
	STATUS current
	DESCRIPTION
        "
        Current 15-min BER counter inv.
        :This OID indicates that the current
        15-min Coding Violation counter
        is invalid
        "
	::= { pm10010mptPerfTelecomBerLinePreFecCurrent15StatEntry 2 }


pm10010mptPerfTelecomBerLinePreFecCurrent15StatBerValuePortn OBJECT-TYPE
	SYNTAX  Unsigned32
	MAX-ACCESS read-only
	STATUS current
	DESCRIPTION
        "
        Current 15-min BER counter :This
        OID gives the current 15-min Coding
        Violation counter value
        "
	::= { pm10010mptPerfTelecomBerLinePreFecCurrent15StatEntry 3 }


pm10010mptPerfTelecomBerLinePreFecCurrent15StatInvMinBerPortn OBJECT-TYPE
	SYNTAX  EkiOnOff
	MAX-ACCESS read-only
	STATUS current
	DESCRIPTION
        "
        Current 15-min MinBER counter
         inv. :This OID indicates that
         the current 15-min Errored Second
        counter is invalid
        "
	::= { pm10010mptPerfTelecomBerLinePreFecCurrent15StatEntry 4 }


pm10010mptPerfTelecomBerLinePreFecCurrent15StatMinBerValuePortn OBJECT-TYPE
	SYNTAX  Unsigned32
	MAX-ACCESS read-only
	STATUS current
	DESCRIPTION
        "
        Current 15-min MinBER counter
         :This OID gives the current 15-min
        Errored Second counter value
        "
	::= { pm10010mptPerfTelecomBerLinePreFecCurrent15StatEntry 5 }


pm10010mptPerfTelecomBerLinePreFecCurrent15StatInvMaxBerPortn OBJECT-TYPE
	SYNTAX  EkiOnOff
	MAX-ACCESS read-only
	STATUS current
	DESCRIPTION
        "
        Current 15-min MaxBER counter
         inv. :This OID indicates that
         the current 15-min severely Errored
        Second counter is invalid
        "
	::= { pm10010mptPerfTelecomBerLinePreFecCurrent15StatEntry 6 }


pm10010mptPerfTelecomBerLinePreFecCurrent15StatMaxBerValuePortn OBJECT-TYPE
	SYNTAX  Unsigned32
	MAX-ACCESS read-only
	STATUS current
	DESCRIPTION
        "
        Current 15-min MaxBER counter
         :This OID gives the current 15-min
        severely Errored Second counter
        value
        "
	::= { pm10010mptPerfTelecomBerLinePreFecCurrent15StatEntry 7 }


--- *****************************************************
---     Leaf of the telecomBerLinePreFecPast15Stat
--- *****************************************************
--- *********************************************************
---     TABLE for the pm10010mptPerfTelecomBerLinePreFecPast15StatHistory articles
--- *********************************************************

pm10010mptPerfTelecomBerLinePreFecPast15StatHistoryPort1Table OBJECT-TYPE
	SYNTAX  SEQUENCE OF Pm10010mptPerfTelecomBerLinePreFecPast15StatHistoryPort1Entry
	MAX-ACCESS not-accessible
	STATUS current
	DESCRIPTION
        "
        List of pm10010mptPerfTelecomBerLinePreFecPast15StatHistory
        Article
        "
	::= { pm10010mptMonPerfLine 209 }


pm10010mptPerfTelecomBerLinePreFecPast15StatHistoryPort1Entry OBJECT-TYPE
	SYNTAX Pm10010mptPerfTelecomBerLinePreFecPast15StatHistoryPort1Entry
	MAX-ACCESS not-accessible
	STATUS current
	DESCRIPTION
        "
        Row definition for the pm10010mptPerfTelecomBerLinePreFecPast15StatHistory
        table
        "
	INDEX   { pm10010mptPerfTelecomBerLinePreFecPast15StatHistoryPort1Index }
	::= { pm10010mptPerfTelecomBerLinePreFecPast15StatHistoryPort1Table 1 }


Pm10010mptPerfTelecomBerLinePreFecPast15StatHistoryPort1Entry ::=
	SEQUENCE {
	pm10010mptPerfTelecomBerLinePreFecPast15StatHistoryPort1Index
		INTEGER,
	pm10010mptPerfTelecomBerLinePreFecPast15StatHistoryInvBerPort1
		EkiOnOff,
	pm10010mptPerfTelecomBerLinePreFecPast15StatHistoryBerValuePort1
		Unsigned32,
	pm10010mptPerfTelecomBerLinePreFecPast15StatHistoryInvMinBerPort1
		EkiOnOff,
	pm10010mptPerfTelecomBerLinePreFecPast15StatHistoryMinBerValuePort1
		Unsigned32,
	pm10010mptPerfTelecomBerLinePreFecPast15StatHistoryInvMaxBerPort1
		EkiOnOff,
	pm10010mptPerfTelecomBerLinePreFecPast15StatHistoryMaxBerValuePort1
		Unsigned32
	}


pm10010mptPerfTelecomBerLinePreFecPast15StatHistoryPort1Index OBJECT-TYPE
	SYNTAX  INTEGER(0..128)
	MAX-ACCESS  read-only
	STATUS current
	DESCRIPTION
        "
        Index definition for the pm10010mptPerfTelecomBerLinePreFecPast15StatHistory
        table
        "
	::= { pm10010mptPerfTelecomBerLinePreFecPast15StatHistoryPort1Entry 1 }


pm10010mptPerfTelecomBerLinePreFecPast15StatHistoryInvBerPort1 OBJECT-TYPE
	SYNTAX  EkiOnOff
	MAX-ACCESS read-only
	STATUS current
	DESCRIPTION
        "
        Previous 15-min BER counter inv.
        :This OID indicates that the previous
        15-min Coding Violation counter
        is invalid
        "
	::= { pm10010mptPerfTelecomBerLinePreFecPast15StatHistoryPort1Entry 2 }


pm10010mptPerfTelecomBerLinePreFecPast15StatHistoryBerValuePort1 OBJECT-TYPE
	SYNTAX  Unsigned32
	MAX-ACCESS read-only
	STATUS current
	DESCRIPTION
        "
        Previous 15-min BER counter :This
        OID gives the previous 15-min Coding
        Violation counter value
        "
	::= { pm10010mptPerfTelecomBerLinePreFecPast15StatHistoryPort1Entry 3 }


pm10010mptPerfTelecomBerLinePreFecPast15StatHistoryInvMinBerPort1 OBJECT-TYPE
	SYNTAX  EkiOnOff
	MAX-ACCESS read-only
	STATUS current
	DESCRIPTION
        "
        Previous 15-min MinBER counter
        inv. :This OID indicates that the
        previous 15-min Errored Second
         counter is invalid
        "
	::= { pm10010mptPerfTelecomBerLinePreFecPast15StatHistoryPort1Entry 4 }


pm10010mptPerfTelecomBerLinePreFecPast15StatHistoryMinBerValuePort1 OBJECT-TYPE
	SYNTAX  Unsigned32
	MAX-ACCESS read-only
	STATUS current
	DESCRIPTION
        "
        Previous 15-min MinBER counter
        :This OID gives the previous 15-min
        Errored Second counter value
        "
	::= { pm10010mptPerfTelecomBerLinePreFecPast15StatHistoryPort1Entry 5 }


pm10010mptPerfTelecomBerLinePreFecPast15StatHistoryInvMaxBerPort1 OBJECT-TYPE
	SYNTAX  EkiOnOff
	MAX-ACCESS read-only
	STATUS current
	DESCRIPTION
        "
        Previous 15-min MaxBER counter
        inv. :This OID indicates that the
        previous 15-min severely Errored
        Second counter is invalid
        "
	::= { pm10010mptPerfTelecomBerLinePreFecPast15StatHistoryPort1Entry 6 }


pm10010mptPerfTelecomBerLinePreFecPast15StatHistoryMaxBerValuePort1 OBJECT-TYPE
	SYNTAX  Unsigned32
	MAX-ACCESS read-only
	STATUS current
	DESCRIPTION
        "
        Previous 15-min MaxBER counter
        :This OID gives the previous 15-min
        severely Errored Second counter
        value
        "
	::= { pm10010mptPerfTelecomBerLinePreFecPast15StatHistoryPort1Entry 7 }


--- *****************************************************
---     Leaf of the telecomBerLinePreFecCurrent24Stat
--- *****************************************************
--- *********************************************************
---     TABLE for the pm10010mptPerfTelecomBerLinePreFecCurrent24Stat articles
--- *********************************************************

pm10010mptPerfTelecomBerLinePreFecCurrent24StatTable OBJECT-TYPE
	SYNTAX  SEQUENCE OF Pm10010mptPerfTelecomBerLinePreFecCurrent24StatEntry
	MAX-ACCESS not-accessible
	STATUS current
	DESCRIPTION
        "
        List of pm10010mptPerfTelecomBerLinePreFecCurrent24Stat
        Article
        "
	::= { pm10010mptMonPerfLine 210 }


pm10010mptPerfTelecomBerLinePreFecCurrent24StatEntry OBJECT-TYPE
	SYNTAX Pm10010mptPerfTelecomBerLinePreFecCurrent24StatEntry
	MAX-ACCESS not-accessible
	STATUS current
	DESCRIPTION
        "
        Row definition for the pm10010mptPerfTelecomBerLinePreFecCurrent24Stat
        table
        "
	INDEX   { pm10010mptPerfTelecomBerLinePreFecCurrent24StatIndex }
	::= { pm10010mptPerfTelecomBerLinePreFecCurrent24StatTable 1 }


Pm10010mptPerfTelecomBerLinePreFecCurrent24StatEntry ::=
	SEQUENCE {
	pm10010mptPerfTelecomBerLinePreFecCurrent24StatIndex
		INTEGER,
	pm10010mptPerfTelecomBerLinePreFecCurrent24StatInvBerPortn
		EkiOnOff,
	pm10010mptPerfTelecomBerLinePreFecCurrent24StatBerValuePortn
		Unsigned32,
	pm10010mptPerfTelecomBerLinePreFecCurrent24StatInvMinBerPortn
		EkiOnOff,
	pm10010mptPerfTelecomBerLinePreFecCurrent24StatMinBerValuePortn
		Unsigned32,
	pm10010mptPerfTelecomBerLinePreFecCurrent24StatInvMaxBerPortn
		EkiOnOff,
	pm10010mptPerfTelecomBerLinePreFecCurrent24StatMaxBerValuePortn
		Unsigned32
	}


pm10010mptPerfTelecomBerLinePreFecCurrent24StatIndex OBJECT-TYPE
	SYNTAX  INTEGER(0..128)
	MAX-ACCESS  read-only
	STATUS current
	DESCRIPTION
        "
        Index definition for the pm10010mptPerfTelecomBerLinePreFecCurrent24Stat
        table
        "
	::= { pm10010mptPerfTelecomBerLinePreFecCurrent24StatEntry 1 }


pm10010mptPerfTelecomBerLinePreFecCurrent24StatInvBerPortn OBJECT-TYPE
	SYNTAX  EkiOnOff
	MAX-ACCESS read-only
	STATUS current
	DESCRIPTION
        "
        Current 24-hours BER counter inv.
        :This OID indicates that the current
        24-hours Coding Violation counter
        is invalid
        "
	::= { pm10010mptPerfTelecomBerLinePreFecCurrent24StatEntry 2 }


pm10010mptPerfTelecomBerLinePreFecCurrent24StatBerValuePortn OBJECT-TYPE
	SYNTAX  Unsigned32
	MAX-ACCESS read-only
	STATUS current
	DESCRIPTION
        "
        Current 24-hours BER counter :This
        OID gives the current 24-hours
         Coding Violation counter value
        "
	::= { pm10010mptPerfTelecomBerLinePreFecCurrent24StatEntry 3 }


pm10010mptPerfTelecomBerLinePreFecCurrent24StatInvMinBerPortn OBJECT-TYPE
	SYNTAX  EkiOnOff
	MAX-ACCESS read-only
	STATUS current
	DESCRIPTION
        "
        Current 24-hoursMinBER counter
        inv. :This OID indicates that the
        current 24-hours Errored Second
        counter is invalid
        "
	::= { pm10010mptPerfTelecomBerLinePreFecCurrent24StatEntry 4 }


pm10010mptPerfTelecomBerLinePreFecCurrent24StatMinBerValuePortn OBJECT-TYPE
	SYNTAX  Unsigned32
	MAX-ACCESS read-only
	STATUS current
	DESCRIPTION
        "
        Current 24-hours MinBER counter
        :This OID gives the current 24-hours
        Errored Second counter value
        "
	::= { pm10010mptPerfTelecomBerLinePreFecCurrent24StatEntry 5 }


pm10010mptPerfTelecomBerLinePreFecCurrent24StatInvMaxBerPortn OBJECT-TYPE
	SYNTAX  EkiOnOff
	MAX-ACCESS read-only
	STATUS current
	DESCRIPTION
        "
        Current 24-hours MaxBER counter
        inv. :This OID indicates that the
        current 24-hours severely Errored
        Second counter is invalid
        "
	::= { pm10010mptPerfTelecomBerLinePreFecCurrent24StatEntry 6 }


pm10010mptPerfTelecomBerLinePreFecCurrent24StatMaxBerValuePortn OBJECT-TYPE
	SYNTAX  Unsigned32
	MAX-ACCESS read-only
	STATUS current
	DESCRIPTION
        "
        Current 24-hours MaxBER counter
        :This OID gives the current 24-hours
        severely Errored Second counter
        value
        "
	::= { pm10010mptPerfTelecomBerLinePreFecCurrent24StatEntry 7 }


--- *****************************************************
---     Leaf of the telecomBerLinePreFecPast24Stat
--- *****************************************************
--- *********************************************************
---     TABLE for the pm10010mptPerfTelecomBerLinePreFecPast24StatHistory articles
--- *********************************************************

pm10010mptPerfTelecomBerLinePreFecPast24StatHistoryPort1Table OBJECT-TYPE
	SYNTAX  SEQUENCE OF Pm10010mptPerfTelecomBerLinePreFecPast24StatHistoryPort1Entry
	MAX-ACCESS not-accessible
	STATUS current
	DESCRIPTION
        "
        List of pm10010mptPerfTelecomBerLinePreFecPast24StatHistory
        Article
        "
	::= { pm10010mptMonPerfLine 211 }


pm10010mptPerfTelecomBerLinePreFecPast24StatHistoryPort1Entry OBJECT-TYPE
	SYNTAX Pm10010mptPerfTelecomBerLinePreFecPast24StatHistoryPort1Entry
	MAX-ACCESS not-accessible
	STATUS current
	DESCRIPTION
        "
        Row definition for the pm10010mptPerfTelecomBerLinePreFecPast24StatHistory
        table
        "
	INDEX   { pm10010mptPerfTelecomBerLinePreFecPast24StatHistoryPort1Index }
	::= { pm10010mptPerfTelecomBerLinePreFecPast24StatHistoryPort1Table 1 }


Pm10010mptPerfTelecomBerLinePreFecPast24StatHistoryPort1Entry ::=
	SEQUENCE {
	pm10010mptPerfTelecomBerLinePreFecPast24StatHistoryPort1Index
		INTEGER,
	pm10010mptPerfTelecomBerLinePreFecPast24StatHistoryInvBerPort1
		EkiOnOff,
	pm10010mptPerfTelecomBerLinePreFecPast24StatHistoryBerValuePort1
		Unsigned32,
	pm10010mptPerfTelecomBerLinePreFecPast24StatHistoryInvMinBerPort1
		EkiOnOff,
	pm10010mptPerfTelecomBerLinePreFecPast24StatHistoryMinBerValuePort1
		Unsigned32,
	pm10010mptPerfTelecomBerLinePreFecPast24StatHistoryInvMaxBerPort1
		EkiOnOff,
	pm10010mptPerfTelecomBerLinePreFecPast24StatHistoryMaxBerValuePort1
		Unsigned32
	}


pm10010mptPerfTelecomBerLinePreFecPast24StatHistoryPort1Index OBJECT-TYPE
	SYNTAX  INTEGER(0..128)
	MAX-ACCESS  read-only
	STATUS current
	DESCRIPTION
        "
        Index definition for the pm10010mptPerfTelecomBerLinePreFecPast24StatHistory
        table
        "
	::= { pm10010mptPerfTelecomBerLinePreFecPast24StatHistoryPort1Entry 1 }


pm10010mptPerfTelecomBerLinePreFecPast24StatHistoryInvBerPort1 OBJECT-TYPE
	SYNTAX  EkiOnOff
	MAX-ACCESS read-only
	STATUS current
	DESCRIPTION
        "
        Previous 24-hours BER counter
         inv. :This OID indicates that
         the previous 24-hours Coding Violation
        counter is invalid
        "
	::= { pm10010mptPerfTelecomBerLinePreFecPast24StatHistoryPort1Entry 2 }


pm10010mptPerfTelecomBerLinePreFecPast24StatHistoryBerValuePort1 OBJECT-TYPE
	SYNTAX  Unsigned32
	MAX-ACCESS read-only
	STATUS current
	DESCRIPTION
        "
        Previous 24-hours BER counter
         :This OID gives the previous 24-hours
        Coding Violation counter value
        "
	::= { pm10010mptPerfTelecomBerLinePreFecPast24StatHistoryPort1Entry 3 }


pm10010mptPerfTelecomBerLinePreFecPast24StatHistoryInvMinBerPort1 OBJECT-TYPE
	SYNTAX  EkiOnOff
	MAX-ACCESS read-only
	STATUS current
	DESCRIPTION
        "
        Previous 24-hours MinBER counter
        inv. :This OID indicates that the
        previous 24-hours Errored Second
        counter is invalid
        "
	::= { pm10010mptPerfTelecomBerLinePreFecPast24StatHistoryPort1Entry 4 }


pm10010mptPerfTelecomBerLinePreFecPast24StatHistoryMinBerValuePort1 OBJECT-TYPE
	SYNTAX  Unsigned32
	MAX-ACCESS read-only
	STATUS current
	DESCRIPTION
        "
        Previous 24-hours MinBER counter
        :This OID gives the previous 24-hours
        Errored Second counter value
        "
	::= { pm10010mptPerfTelecomBerLinePreFecPast24StatHistoryPort1Entry 5 }


pm10010mptPerfTelecomBerLinePreFecPast24StatHistoryInvMaxBerPort1 OBJECT-TYPE
	SYNTAX  EkiOnOff
	MAX-ACCESS read-only
	STATUS current
	DESCRIPTION
        "
        Previous 24-hours MaxBER counter
        inv. :This OID indicates that the
        previous 24-hours severely Errored
        Second counter is invalid
        "
	::= { pm10010mptPerfTelecomBerLinePreFecPast24StatHistoryPort1Entry 6 }


pm10010mptPerfTelecomBerLinePreFecPast24StatHistoryMaxBerValuePort1 OBJECT-TYPE
	SYNTAX  Unsigned32
	MAX-ACCESS read-only
	STATUS current
	DESCRIPTION
        "
        Previous 24-hours MaxBER counter
        :This OID gives the previous 24-hours
        severely Errored Second counter
        value
        "
	::= { pm10010mptPerfTelecomBerLinePreFecPast24StatHistoryPort1Entry 7 }


--- *****************************************************
---     Leaf of the datacomClientCurrent15Stat
--- *****************************************************
--- *********************************************************
---     TABLE for the pm10010mptPerfDatacomClientCurrent15Stat articles
--- *********************************************************

pm10010mptPerfDatacomClientCurrent15StatTable OBJECT-TYPE
	SYNTAX  SEQUENCE OF Pm10010mptPerfDatacomClientCurrent15StatEntry
	MAX-ACCESS not-accessible
	STATUS current
	DESCRIPTION
        "
        List of pm10010mptPerfDatacomClientCurrent15Stat
        Article
        "
	::= { pm10010mptMonPerfClient 432 }


pm10010mptPerfDatacomClientCurrent15StatEntry OBJECT-TYPE
	SYNTAX Pm10010mptPerfDatacomClientCurrent15StatEntry
	MAX-ACCESS not-accessible
	STATUS current
	DESCRIPTION
        "
        Row definition for the pm10010mptPerfDatacomClientCurrent15Stat
        table
        "
	INDEX   { pm10010mptPerfDatacomClientCurrent15StatIndex }
	::= { pm10010mptPerfDatacomClientCurrent15StatTable 1 }


Pm10010mptPerfDatacomClientCurrent15StatEntry ::=
	SEQUENCE {
	pm10010mptPerfDatacomClientCurrent15StatIndex
		INTEGER,
	rm10010perfdatacomclientCurrent15StatOutPacketCountInvPortn
		EkiOnOff,
	rm10010perfdatacomclientCurrent15StatOutPacketCountPortn
		Counter64,
	rm10010perfdatacomclientCurrent15StatOutCrcCountInvPortn
		EkiOnOff,
	rm10010perfdatacomclientCurrent15StatOutCrcCountPortn
		Counter64,
	rm10010perfdatacomclientCurrent15StatInPacketCountInvPortn
		EkiOnOff,
	rm10010perfdatacomclientCurrent15StatInPacketCountPortn
		Counter64,
	rm10010perfdatacomclientCurrent15StatInCrcCountInvPortn
		EkiOnOff,
	rm10010perfdatacomclientCurrent15StatInCrcCountPortn
		Counter64
	}


pm10010mptPerfDatacomClientCurrent15StatIndex OBJECT-TYPE
	SYNTAX  INTEGER(0..128)
	MAX-ACCESS  read-only
	STATUS current
	DESCRIPTION
        "
        Index definition for the pm10010mptPerfDatacomClientCurrent15Stat
        table
        "
	::= { pm10010mptPerfDatacomClientCurrent15StatEntry 1 }


rm10010perfdatacomclientCurrent15StatOutPacketCountInvPortn OBJECT-TYPE
	SYNTAX  EkiOnOff
	MAX-ACCESS read-only
	STATUS current
	DESCRIPTION
        "
        Client Current 15-min Output Packet
        counter inv. :This OID indicates
        that the current 15-min Output
         Packets counter is invalid
        "
	::= { pm10010mptPerfDatacomClientCurrent15StatEntry 30 }


rm10010perfdatacomclientCurrent15StatOutPacketCountPortn OBJECT-TYPE
	SYNTAX  Counter64
	MAX-ACCESS read-only
	STATUS current
	DESCRIPTION
        "
        Client Current 15-min Output Packet
        counter :This OID gives the current
        15-min Output Packets counter value
        "
	::= { pm10010mptPerfDatacomClientCurrent15StatEntry 31 }


rm10010perfdatacomclientCurrent15StatOutCrcCountInvPortn OBJECT-TYPE
	SYNTAX  EkiOnOff
	MAX-ACCESS read-only
	STATUS current
	DESCRIPTION
        "
        Client Current 15-min Output CRC
        counter inv. :This OID indicates
        that the current 15-min Output
         CRC counter is invalid
        "
	::= { pm10010mptPerfDatacomClientCurrent15StatEntry 28 }


rm10010perfdatacomclientCurrent15StatOutCrcCountPortn OBJECT-TYPE
	SYNTAX  Counter64
	MAX-ACCESS read-only
	STATUS current
	DESCRIPTION
        "
        Client Current 15-min Output CRC
        counter :This OID gives the current
        15-min Output CRC counter value
        "
	::= { pm10010mptPerfDatacomClientCurrent15StatEntry 29 }


rm10010perfdatacomclientCurrent15StatInPacketCountInvPortn OBJECT-TYPE
	SYNTAX  EkiOnOff
	MAX-ACCESS read-only
	STATUS current
	DESCRIPTION
        "
        Client Current 15-min Input Packet
        counter inv. :This OID indicates
        that the current 15-min Input Packet
        counter is invalid
        "
	::= { pm10010mptPerfDatacomClientCurrent15StatEntry 6 }


rm10010perfdatacomclientCurrent15StatInPacketCountPortn OBJECT-TYPE
	SYNTAX  Counter64
	MAX-ACCESS read-only
	STATUS current
	DESCRIPTION
        "
        Client Current 15-min Input Packet
        counter :This OID gives the current
        15-min Input Packet counter value
        "
	::= { pm10010mptPerfDatacomClientCurrent15StatEntry 7 }


rm10010perfdatacomclientCurrent15StatInCrcCountInvPortn OBJECT-TYPE
	SYNTAX  EkiOnOff
	MAX-ACCESS read-only
	STATUS current
	DESCRIPTION
        "
        Client Current 15-min Input CRC
        counter inv. :This OID indicates
        that the current 15-min Input CRC
        counter is invalid
        "
	::= { pm10010mptPerfDatacomClientCurrent15StatEntry 4 }


rm10010perfdatacomclientCurrent15StatInCrcCountPortn OBJECT-TYPE
	SYNTAX  Counter64
	MAX-ACCESS read-only
	STATUS current
	DESCRIPTION
        "
        Client Current 15-min Input CRC
        counter :This OID gives the current
        15-min Input CRC counter value
        "
	::= { pm10010mptPerfDatacomClientCurrent15StatEntry 5 }


--- *****************************************************
---     Leaf of the datacomClientPast15Stat
--- *****************************************************
--- *********************************************************
---     TABLE for the pm10010mptPerfDatacomClientPast15StatHistory articles
--- *********************************************************

pm10010mptPerfDatacomClientPast15StatHistoryPort1Table OBJECT-TYPE
	SYNTAX  SEQUENCE OF Pm10010mptPerfDatacomClientPast15StatHistoryPort1Entry
	MAX-ACCESS not-accessible
	STATUS current
	DESCRIPTION
        "
        List of pm10010mptPerfDatacomClientPast15StatHistory
        Article
        "
	::= { pm10010mptMonPerfClient 448 }


pm10010mptPerfDatacomClientPast15StatHistoryPort1Entry OBJECT-TYPE
	SYNTAX Pm10010mptPerfDatacomClientPast15StatHistoryPort1Entry
	MAX-ACCESS not-accessible
	STATUS current
	DESCRIPTION
        "
        Row definition for the pm10010mptPerfDatacomClientPast15StatHistory
        table
        "
	INDEX   { pm10010mptPerfDatacomClientPast15StatHistoryPort1Index }
	::= { pm10010mptPerfDatacomClientPast15StatHistoryPort1Table 1 }


Pm10010mptPerfDatacomClientPast15StatHistoryPort1Entry ::=
	SEQUENCE {
	pm10010mptPerfDatacomClientPast15StatHistoryPort1Index
		INTEGER,
	rm10010perfdatacomclientPast15StatOutPacketCountInvPort1
		EkiOnOff,
	rm10010perfdatacomclientPast15StatOutPacketCountPort1
		Counter64,
	rm10010perfdatacomclientPast15StatOutCrcCountInvPort1
		EkiOnOff,
	rm10010perfdatacomclientPast15StatOutCrcCountPort1
		Counter64,
	rm10010perfdatacomclientPast15StatInPacketCountInvPort1
		EkiOnOff,
	rm10010perfdatacomclientPast15StatInPacketCountPort1
		Counter64,
	rm10010perfdatacomclientPast15StatInCrcCountInvPort1
		EkiOnOff,
	rm10010perfdatacomclientPast15StatInCrcCountPort1
		Counter64
	}


pm10010mptPerfDatacomClientPast15StatHistoryPort1Index OBJECT-TYPE
	SYNTAX  INTEGER(0..128)
	MAX-ACCESS  read-only
	STATUS current
	DESCRIPTION
        "
        Index definition for the pm10010mptPerfDatacomClientPast15StatHistory
        table
        "
	::= { pm10010mptPerfDatacomClientPast15StatHistoryPort1Entry 1 }


rm10010perfdatacomclientPast15StatOutPacketCountInvPort1 OBJECT-TYPE
	SYNTAX  EkiOnOff
	MAX-ACCESS read-only
	STATUS current
	DESCRIPTION
        "
        Client Past 15-min Output Packet
        counter inv. :This OID indicates
        that the past 15-min Output Packets
        counter is invalid
        "
	::= { pm10010mptPerfDatacomClientPast15StatHistoryPort1Entry 30 }


rm10010perfdatacomclientPast15StatOutPacketCountPort1 OBJECT-TYPE
	SYNTAX  Counter64
	MAX-ACCESS read-only
	STATUS current
	DESCRIPTION
        "
        Client Past 15-min Output Packet
        counter :This OID gives the past
        15-min Output Packets counter value
        "
	::= { pm10010mptPerfDatacomClientPast15StatHistoryPort1Entry 31 }


rm10010perfdatacomclientPast15StatOutCrcCountInvPort1 OBJECT-TYPE
	SYNTAX  EkiOnOff
	MAX-ACCESS read-only
	STATUS current
	DESCRIPTION
        "
        Client Past 15-min Output CRC
         counter inv. :This OID indicates
        that the past 15-min Output CRC
        counter is invalid
        "
	::= { pm10010mptPerfDatacomClientPast15StatHistoryPort1Entry 28 }


rm10010perfdatacomclientPast15StatOutCrcCountPort1 OBJECT-TYPE
	SYNTAX  Counter64
	MAX-ACCESS read-only
	STATUS current
	DESCRIPTION
        "
        Client Past 15-min Output CRC
         counter :This OID gives the past
        15-min Output CRC counter value
        "
	::= { pm10010mptPerfDatacomClientPast15StatHistoryPort1Entry 29 }


rm10010perfdatacomclientPast15StatInPacketCountInvPort1 OBJECT-TYPE
	SYNTAX  EkiOnOff
	MAX-ACCESS read-only
	STATUS current
	DESCRIPTION
        "
        Client Past 15-min Input Packet
        counter inv. :This OID indicates
        that the past 15-min Input Packet
        counter is invalid
        "
	::= { pm10010mptPerfDatacomClientPast15StatHistoryPort1Entry 6 }


rm10010perfdatacomclientPast15StatInPacketCountPort1 OBJECT-TYPE
	SYNTAX  Counter64
	MAX-ACCESS read-only
	STATUS current
	DESCRIPTION
        "
        Client Past 15-min Input Packet
        counter :This OID gives the past
        15-min Input Packet counter value
        "
	::= { pm10010mptPerfDatacomClientPast15StatHistoryPort1Entry 7 }


rm10010perfdatacomclientPast15StatInCrcCountInvPort1 OBJECT-TYPE
	SYNTAX  EkiOnOff
	MAX-ACCESS read-only
	STATUS current
	DESCRIPTION
        "
        Client Past 15-min Input CRC counter
        inv. :This OID indicates that the
        past 15-min Input CRC counter is
        invalid
        "
	::= { pm10010mptPerfDatacomClientPast15StatHistoryPort1Entry 4 }


rm10010perfdatacomclientPast15StatInCrcCountPort1 OBJECT-TYPE
	SYNTAX  Counter64
	MAX-ACCESS read-only
	STATUS current
	DESCRIPTION
        "
        Client Past 15-min Input CRC counter
        :This OID gives the past 15-min
        Input CRC counter value
        "
	::= { pm10010mptPerfDatacomClientPast15StatHistoryPort1Entry 5 }


--- *****************************************************
---     Leaf of the datacomClientCurrent24Stat
--- *****************************************************
--- *********************************************************
---     TABLE for the pm10010mptPerfDatacomClientCurrent24Stat articles
--- *********************************************************

pm10010mptPerfDatacomClientCurrent24StatTable OBJECT-TYPE
	SYNTAX  SEQUENCE OF Pm10010mptPerfDatacomClientCurrent24StatEntry
	MAX-ACCESS not-accessible
	STATUS current
	DESCRIPTION
        "
        List of pm10010mptPerfDatacomClientCurrent24Stat
        Article
        "
	::= { pm10010mptMonPerfClient 464 }


pm10010mptPerfDatacomClientCurrent24StatEntry OBJECT-TYPE
	SYNTAX Pm10010mptPerfDatacomClientCurrent24StatEntry
	MAX-ACCESS not-accessible
	STATUS current
	DESCRIPTION
        "
        Row definition for the pm10010mptPerfDatacomClientCurrent24Stat
        table
        "
	INDEX   { pm10010mptPerfDatacomClientCurrent24StatIndex }
	::= { pm10010mptPerfDatacomClientCurrent24StatTable 1 }


Pm10010mptPerfDatacomClientCurrent24StatEntry ::=
	SEQUENCE {
	pm10010mptPerfDatacomClientCurrent24StatIndex
		INTEGER,
	rm10010perfdatacomclientCurrent24StatOutPacketCountInvPortn
		EkiOnOff,
	rm10010perfdatacomclientCurrent24StatOutPacketCountPortn
		Counter64,
	rm10010perfdatacomclientCurrent24StatOutCrcCountInvPortn
		EkiOnOff,
	rm10010perfdatacomclientCurrent24StatOutCrcCountPortn
		Counter64,
	rm10010perfdatacomclientCurrent24StatInPacketCountInvPortn
		EkiOnOff,
	rm10010perfdatacomclientCurrent24StatInPacketCountPortn
		Counter64,
	rm10010perfdatacomclientCurrent24StatInCrcCountInvPortn
		EkiOnOff,
	rm10010perfdatacomclientCurrent24StatInCrcCountPortn
		Counter64
	}


pm10010mptPerfDatacomClientCurrent24StatIndex OBJECT-TYPE
	SYNTAX  INTEGER(0..128)
	MAX-ACCESS  read-only
	STATUS current
	DESCRIPTION
        "
        Index definition for the pm10010mptPerfDatacomClientCurrent24Stat
        table
        "
	::= { pm10010mptPerfDatacomClientCurrent24StatEntry 1 }


rm10010perfdatacomclientCurrent24StatOutPacketCountInvPortn OBJECT-TYPE
	SYNTAX  EkiOnOff
	MAX-ACCESS read-only
	STATUS current
	DESCRIPTION
        "
        Client Current 24-hours Output
        Packet counter inv. :This OID indicates
        that the current 24-hours Output
        Packets counter is invalid
        "
	::= { pm10010mptPerfDatacomClientCurrent24StatEntry 30 }


rm10010perfdatacomclientCurrent24StatOutPacketCountPortn OBJECT-TYPE
	SYNTAX  Counter64
	MAX-ACCESS read-only
	STATUS current
	DESCRIPTION
        "
        Client Current 24-hours Output
        Packet counter :This OID gives
         the current 24-hours Output Packets
        counter value
        "
	::= { pm10010mptPerfDatacomClientCurrent24StatEntry 31 }


rm10010perfdatacomclientCurrent24StatOutCrcCountInvPortn OBJECT-TYPE
	SYNTAX  EkiOnOff
	MAX-ACCESS read-only
	STATUS current
	DESCRIPTION
        "
        Client Current 24-hours Output
        CRC counter inv. :This OID indicates
        that the current 24-hours Output
        CRC counter is invalid
        "
	::= { pm10010mptPerfDatacomClientCurrent24StatEntry 28 }


rm10010perfdatacomclientCurrent24StatOutCrcCountPortn OBJECT-TYPE
	SYNTAX  Counter64
	MAX-ACCESS read-only
	STATUS current
	DESCRIPTION
        "
        Client Current 24-hours Output
        CRC counter :This OID gives the
        current 24-hours Output CRC counter
        value
        "
	::= { pm10010mptPerfDatacomClientCurrent24StatEntry 29 }


rm10010perfdatacomclientCurrent24StatInPacketCountInvPortn OBJECT-TYPE
	SYNTAX  EkiOnOff
	MAX-ACCESS read-only
	STATUS current
	DESCRIPTION
        "
        Client Current 24-hours Input
         Packet counter inv. :This OID
         indicates that the current 24-hours
        Input Packet counter is invalid
        "
	::= { pm10010mptPerfDatacomClientCurrent24StatEntry 6 }


rm10010perfdatacomclientCurrent24StatInPacketCountPortn OBJECT-TYPE
	SYNTAX  Counter64
	MAX-ACCESS read-only
	STATUS current
	DESCRIPTION
        "
        Client Current 24-hours Input
         Packet counter :This OID gives
        the current 24-hours Input Packet
        counter value
        "
	::= { pm10010mptPerfDatacomClientCurrent24StatEntry 7 }


rm10010perfdatacomclientCurrent24StatInCrcCountInvPortn OBJECT-TYPE
	SYNTAX  EkiOnOff
	MAX-ACCESS read-only
	STATUS current
	DESCRIPTION
        "
        Client Current 24-hours Input
         CRC counter inv. :This OID indicates
        that the current 24-hours Input
        CRC counter is invalid
        "
	::= { pm10010mptPerfDatacomClientCurrent24StatEntry 4 }


rm10010perfdatacomclientCurrent24StatInCrcCountPortn OBJECT-TYPE
	SYNTAX  Counter64
	MAX-ACCESS read-only
	STATUS current
	DESCRIPTION
        "
        Client Current 24-hours Input
         CRC counter :This OID gives the
        current 24-hours Input CRC counter
        value
        "
	::= { pm10010mptPerfDatacomClientCurrent24StatEntry 5 }


--- *****************************************************
---     Leaf of the datacomClientPast24Stat
--- *****************************************************
--- *********************************************************
---     TABLE for the pm10010mptPerfDatacomClientPast24StatHistory articles
--- *********************************************************

pm10010mptPerfDatacomClientPast24StatHistoryPort1Table OBJECT-TYPE
	SYNTAX  SEQUENCE OF Pm10010mptPerfDatacomClientPast24StatHistoryPort1Entry
	MAX-ACCESS not-accessible
	STATUS current
	DESCRIPTION
        "
        List of pm10010mptPerfDatacomClientPast24StatHistory
        Article
        "
	::= { pm10010mptMonPerfClient 480 }


pm10010mptPerfDatacomClientPast24StatHistoryPort1Entry OBJECT-TYPE
	SYNTAX Pm10010mptPerfDatacomClientPast24StatHistoryPort1Entry
	MAX-ACCESS not-accessible
	STATUS current
	DESCRIPTION
        "
        Row definition for the pm10010mptPerfDatacomClientPast24StatHistory
        table
        "
	INDEX   { pm10010mptPerfDatacomClientPast24StatHistoryPort1Index }
	::= { pm10010mptPerfDatacomClientPast24StatHistoryPort1Table 1 }


Pm10010mptPerfDatacomClientPast24StatHistoryPort1Entry ::=
	SEQUENCE {
	pm10010mptPerfDatacomClientPast24StatHistoryPort1Index
		INTEGER,
	rm10010perfdatacomclientPast24StatOutPacketCountInvPort1
		EkiOnOff,
	rm10010perfdatacomclientPast24StatOutPacketCountPort1
		Counter64,
	rm10010perfdatacomclientPast24StatOutCrcCountInvPort1
		EkiOnOff,
	rm10010perfdatacomclientPast24StatOutCrcCountPort1
		Counter64,
	rm10010perfdatacomclientPast24StatInPacketCountInvPort1
		EkiOnOff,
	rm10010perfdatacomclientPast24StatInPacketCountPort1
		Counter64,
	rm10010perfdatacomclientPast24StatInCrcCountInvPort1
		EkiOnOff,
	rm10010perfdatacomclientPast24StatInCrcCountPort1
		Counter64
	}


pm10010mptPerfDatacomClientPast24StatHistoryPort1Index OBJECT-TYPE
	SYNTAX  INTEGER(0..128)
	MAX-ACCESS  read-only
	STATUS current
	DESCRIPTION
        "
        Index definition for the pm10010mptPerfDatacomClientPast24StatHistory
        table
        "
	::= { pm10010mptPerfDatacomClientPast24StatHistoryPort1Entry 1 }


rm10010perfdatacomclientPast24StatOutPacketCountInvPort1 OBJECT-TYPE
	SYNTAX  EkiOnOff
	MAX-ACCESS read-only
	STATUS current
	DESCRIPTION
        "
        Client Past 24-hours Output Packet
        counter inv. :This OID indicates
        that the past 24-hours Output Packets
        counter is invalid
        "
	::= { pm10010mptPerfDatacomClientPast24StatHistoryPort1Entry 30 }


rm10010perfdatacomclientPast24StatOutPacketCountPort1 OBJECT-TYPE
	SYNTAX  Counter64
	MAX-ACCESS read-only
	STATUS current
	DESCRIPTION
        "
        Client Past 24-hours Output Packet
        counter :This OID gives the past
        24-hours Output Packets counter
        value
        "
	::= { pm10010mptPerfDatacomClientPast24StatHistoryPort1Entry 31 }


rm10010perfdatacomclientPast24StatOutCrcCountInvPort1 OBJECT-TYPE
	SYNTAX  EkiOnOff
	MAX-ACCESS read-only
	STATUS current
	DESCRIPTION
        "
        Client Past 24-hours Output CRC
        counter inv. :This OID indicates
        that the past 24-hours Output CRC
        counter is invalid
        "
	::= { pm10010mptPerfDatacomClientPast24StatHistoryPort1Entry 28 }


rm10010perfdatacomclientPast24StatOutCrcCountPort1 OBJECT-TYPE
	SYNTAX  Counter64
	MAX-ACCESS read-only
	STATUS current
	DESCRIPTION
        "
        Client Past 24-hours Output CRC
        counter :This OID gives the past
        24-hours Output CRC counter value
        "
	::= { pm10010mptPerfDatacomClientPast24StatHistoryPort1Entry 29 }


rm10010perfdatacomclientPast24StatInPacketCountInvPort1 OBJECT-TYPE
	SYNTAX  EkiOnOff
	MAX-ACCESS read-only
	STATUS current
	DESCRIPTION
        "
        Client Past 24-hours Input Packet
        counter inv. :This OID indicates
        that the past 24-hours Input Packet
        counter is invalid
        "
	::= { pm10010mptPerfDatacomClientPast24StatHistoryPort1Entry 6 }


rm10010perfdatacomclientPast24StatInPacketCountPort1 OBJECT-TYPE
	SYNTAX  Counter64
	MAX-ACCESS read-only
	STATUS current
	DESCRIPTION
        "
        Client Past 24-hours Input Packet
        counter :This OID gives the past
        24-hours Input Packet counter value
        "
	::= { pm10010mptPerfDatacomClientPast24StatHistoryPort1Entry 7 }


rm10010perfdatacomclientPast24StatInCrcCountInvPort1 OBJECT-TYPE
	SYNTAX  EkiOnOff
	MAX-ACCESS read-only
	STATUS current
	DESCRIPTION
        "
        Client Past 24-hours Input CRC
        counter inv. :This OID indicates
        that the past 24-hours Input CRC
        counter is invalid
        "
	::= { pm10010mptPerfDatacomClientPast24StatHistoryPort1Entry 4 }


rm10010perfdatacomclientPast24StatInCrcCountPort1 OBJECT-TYPE
	SYNTAX  Counter64
	MAX-ACCESS read-only
	STATUS current
	DESCRIPTION
        "
        Client Past 24-hours Input CRC
        counter :This OID gives the past
        24-hours Input CRC counter value
        "
	::= { pm10010mptPerfDatacomClientPast24StatHistoryPort1Entry 5 }



pm10010mptPerfEnable OBJECT-TYPE
	SYNTAX EkiOnOff
	MAX-ACCESS read-write
	STATUS current
	DESCRIPTION
        "
        Perf. Mon. Enable :This OID enables
        the Performance Monitoring application
        "
	::= { pm10010mptMonPerfSync 257 }


pm10010mptPerf15minSync OBJECT-TYPE
	SYNTAX EkiOnOff
	MAX-ACCESS read-write
	STATUS current
	DESCRIPTION
        "
        Perf. Mon. 15-min sync. :This
         OID must be used in external synchronisation
        mode only to send a 15-min synchronisation
        command
        "
	::= { pm10010mptMonPerfSync 259 }


pm10010mptPerf24hSync OBJECT-TYPE
	SYNTAX EkiOnOff
	MAX-ACCESS read-write
	STATUS current
	DESCRIPTION
        "
        Perf. Mon. 24-hours sync. :This
        OID must be used in external synchronisation
        mode only to send a 24-hours synchronisation
        command
        "
	::= { pm10010mptMonPerfSync 260 }


pm10010mptPerf15MinShort OBJECT-TYPE
	SYNTAX EkiOnOff
	MAX-ACCESS read-write
	STATUS current
	DESCRIPTION
        "
        15-min period is short :This OID
        indicates that the 15-min period
        lasts less than 890 seconds
        "
	::= { pm10010mptMonPerfTimeStamp 1 }


pm10010mptPerf15MinLong OBJECT-TYPE
	SYNTAX EkiOnOff
	MAX-ACCESS read-write
	STATUS current
	DESCRIPTION
        "
        15-min period is long :This OID
        indicates that the 15-min period
        lasts more than 910 seconds
        "
	::= { pm10010mptMonPerfTimeStamp 2 }


pm10010mptPerf24HoursShort OBJECT-TYPE
	SYNTAX Counter32
	MAX-ACCESS read-write
	STATUS current
	DESCRIPTION
        "
        24-hours period is short :This
        OID indicates that 24-hours period
        lasts less than 86390 seconds
        "
	::= { pm10010mptMonPerfTimeStamp 5 }


pm10010mptPerf24HoursLong OBJECT-TYPE
	SYNTAX Counter32
	MAX-ACCESS read-write
	STATUS current
	DESCRIPTION
        "
        24-hours period is long :This
         OID indicates that 24-hours period
        lasts more than 86410 seconds
        "
	::= { pm10010mptMonPerfTimeStamp 6 }


pm10010mptPerfCurrent15MinElapsedTime OBJECT-TYPE
	SYNTAX Counter32
	MAX-ACCESS read-write
	STATUS current
	DESCRIPTION
        "
        Current 15min period Elapsed Time
         :This OID gives the number of
         seconds elapsed in the current
        15-minutes period
        "
	::= { pm10010mptMonPerfTimeStamp 7 }


pm10010mptPerfCurrent24HoursElapsedTime OBJECT-TYPE
	SYNTAX Counter32
	MAX-ACCESS read-write
	STATUS current
	DESCRIPTION
        "
        Current 24hours period Elapsed
        Time :This OID gives the number
        of seconds elapsed in the current
        24-hours period
        "
	::= { pm10010mptMonPerfTimeStamp 8 }






--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pm10010mptDwlrestartProcess OBJECT IDENTIFIER ::= { pm10010mptDwlOther 0 }




pm10010mptDwlColdRestartProcessed OBJECT-TYPE
	  SYNTAX EkiOnOff
	  MAX-ACCESS read-only
	  STATUS current
	  DESCRIPTION
        "
        Cold Restart :This OID indicates
        that the module last restart was
        a Cold RESTART
        "
	  ::= { pm10010mptDwlrestartProcess 2 }



pm10010mptDwlWarmRestartProcessed OBJECT-TYPE
	  SYNTAX EkiOnOff
	  MAX-ACCESS read-only
	  STATUS current
	  DESCRIPTION
        "
        Warm Restart :This OID indicates
        that the module last restart was
        a Warm RESTART
        "
	  ::= { pm10010mptDwlrestartProcess 1 }



--- *****************************************************
---     LEAF for the swBanksUsed article
--- *****************************************************
pm10010mptDwlswBanksUsed OBJECT IDENTIFIER ::= { pm10010mptDwlOther 1 }




pm10010mptDwlSwBank2Notempty OBJECT-TYPE
	  SYNTAX EkiOnOff
	  MAX-ACCESS read-only
	  STATUS current
	  DESCRIPTION
        "
        SW bank 2 loaded :This OID indicates
        a software is loaded in SW bank
        2  <Help>  This status indicates
        if the SW bank 2 contains SW package
        "
	  ::= { pm10010mptDwlswBanksUsed 6 }



pm10010mptDwlSwBank1Notempty OBJECT-TYPE
	  SYNTAX EkiOnOff
	  MAX-ACCESS read-only
	  STATUS current
	  DESCRIPTION
        "
        SW bank 1 loaded :This OID indicates
        a software is loaded in SW bank
        1  <Help>  This status indicates
        if the SW bank 1 contains SW package
        "
	  ::= { pm10010mptDwlswBanksUsed 5 }



pm10010mptDwlSwBank2Used OBJECT-TYPE
	  SYNTAX EkiOnOff
	  MAX-ACCESS read-only
	  STATUS current
	  DESCRIPTION
        "
        SW bank 2 active :This OID indicates
        the module is working on SW bank
        2  <Help>  This status indicates
        if the SW bank 2 is active or standby
        "
	  ::= { pm10010mptDwlswBanksUsed 2 }



pm10010mptDwlSwBank1Used OBJECT-TYPE
	  SYNTAX EkiOnOff
	  MAX-ACCESS read-only
	  STATUS current
	  DESCRIPTION
        "
        SW bank 1 active :This OID indicates
        the module is working on SW bank
        1  <Help>  This status indicates
        if the SW bank 1 is active or standby
        "
	  ::= { pm10010mptDwlswBanksUsed 1 }



--- *****************************************************
---     LEAF for the gwBanksUsed article
--- *****************************************************
pm10010mptDwlgwBanksUsed OBJECT IDENTIFIER ::= { pm10010mptDwlOther 2 }




pm10010mptDwlGwBank4Notempty OBJECT-TYPE
	  SYNTAX EkiOnOff
	  MAX-ACCESS read-only
	  STATUS current
	  DESCRIPTION
        "
        GW bank 4 loaded :This OID indicates
        a gateware is loaded in GW bank
        4
        "
	  ::= { pm10010mptDwlgwBanksUsed 8 }



pm10010mptDwlGwBank3Notempty OBJECT-TYPE
	  SYNTAX EkiOnOff
	  MAX-ACCESS read-only
	  STATUS current
	  DESCRIPTION
        "
        GW bank 3 loaded :This OID indicates
        a gateware is loaded in GW bank
        3  <Help>  This status indicates
        if the GW bank 3 contains GW package
        "
	  ::= { pm10010mptDwlgwBanksUsed 7 }



pm10010mptDwlGwBank2Notempty OBJECT-TYPE
	  SYNTAX EkiOnOff
	  MAX-ACCESS read-only
	  STATUS current
	  DESCRIPTION
        "
        GW bank 2 loaded :This OID indicates
        a gateware is loaded in GW bank
        2
        "
	  ::= { pm10010mptDwlgwBanksUsed 6 }



pm10010mptDwlGwBank1Notempty OBJECT-TYPE
	  SYNTAX EkiOnOff
	  MAX-ACCESS read-only
	  STATUS current
	  DESCRIPTION
        "
        GW bank 1 loaded :This OID indicates
        a gateware is loaded in GW bank
        1  <Help>  This status indicates
        if the GW bank 1 contains GW package
        "
	  ::= { pm10010mptDwlgwBanksUsed 5 }



pm10010mptDwlGwBank4Used OBJECT-TYPE
	  SYNTAX EkiOnOff
	  MAX-ACCESS read-only
	  STATUS current
	  DESCRIPTION
        "
        GW bank 4 active :This OID indicates
        the module is working on GW bank
        4
        "
	  ::= { pm10010mptDwlgwBanksUsed 4 }



pm10010mptDwlGwBank3Used OBJECT-TYPE
	  SYNTAX EkiOnOff
	  MAX-ACCESS read-only
	  STATUS current
	  DESCRIPTION
        "
        GW bank 3 active :This OID indicates
        the module is working on GW bank
        3  <Help>  This status indicates
        if the GW bank 3 is active or standby
        "
	  ::= { pm10010mptDwlgwBanksUsed 3 }



pm10010mptDwlGwBank2Used OBJECT-TYPE
	  SYNTAX EkiOnOff
	  MAX-ACCESS read-only
	  STATUS current
	  DESCRIPTION
        "
        GW bank 2 active :This OID indicates
        the module is working on GW bank
        2
        "
	  ::= { pm10010mptDwlgwBanksUsed 2 }



pm10010mptDwlGwBank1Used OBJECT-TYPE
	  SYNTAX EkiOnOff
	  MAX-ACCESS read-only
	  STATUS current
	  DESCRIPTION
        "
        GW bank 1 active :This OID indicates
        the module is working on GW bank
        1  <Help>  This status indicates
        if the GW bank 1 is active or standby
        "
	  ::= { pm10010mptDwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pm10010mptCfgAccessCAisCsf OBJECT IDENTIFIER ::= { pm10010mptConfig 1 }



--- *****************************************************
---     LEAF for the table 0012
--- *****************************************************

pm10010mptCfgClientcaiscsfTable OBJECT-TYPE
	SYNTAX  SEQUENCE OF Pm10010mptCfgClientcaiscsfEntry
	MAX-ACCESS not-accessible
	STATUS current
	DESCRIPTION
        "
        List of  Article
        "
	::= { pm10010mptCfgAccessCAisCsf 1 }


pm10010mptCfgClientcaiscsfEntry OBJECT-TYPE
	SYNTAX Pm10010mptCfgClientcaiscsfEntry
	MAX-ACCESS not-accessible
	STATUS current
	DESCRIPTION
        "
        Row definition for the accessCAisCsf
        table
        "
	INDEX   { pm10010mptCfgClientcaiscsfIndex }
	::= { pm10010mptCfgClientcaiscsfTable 1 }


Pm10010mptCfgClientcaiscsfEntry ::=
	SEQUENCE {
	pm10010mptCfgClientcaiscsfIndex
		INTEGER,
	pm10010mptCfgReservePortn
		Unsigned32
	}


pm10010mptCfgClientcaiscsfIndex OBJECT-TYPE
	SYNTAX  INTEGER(0..128)
	MAX-ACCESS  read-only
	STATUS current
	DESCRIPTION
        "
        Index definition for the clientcaiscsf
        table
        "
	::= { pm10010mptCfgClientcaiscsfEntry 1 }


pm10010mptCfgReservePortn OBJECT-TYPE
	SYNTAX  Unsigned32 (0..65536)
	MAX-ACCESS read-write
	STATUS current
	DESCRIPTION
        "
        CAIS mode  on Client Port :This
        register enables/disables port
          laser shutdown on CAIS insertion
        condition
        "
	::= { pm10010mptCfgClientcaiscsfEntry 3 }


--- *****************************************************
---     LEAF for the table Group startup
--- *****************************************************

pm10010mptCfgStartup OBJECT IDENTIFIER ::= { pm10010mptConfig 2 }



--- *****************************************************
---     LEAF for the table 2110
--- *****************************************************

pm10010mptCfgClientStartupTable OBJECT-TYPE
	SYNTAX  SEQUENCE OF Pm10010mptCfgClientStartupEntry
	MAX-ACCESS not-accessible
	STATUS current
	DESCRIPTION
        "
        List of  Article
        "
	::= { pm10010mptCfgStartup 1 }


pm10010mptCfgClientStartupEntry OBJECT-TYPE
	SYNTAX Pm10010mptCfgClientStartupEntry
	MAX-ACCESS not-accessible
	STATUS current
	DESCRIPTION
        "
        Row definition for the startup
        table
        "
	INDEX   { pm10010mptCfgClientStartupIndex }
	::= { pm10010mptCfgClientStartupTable 1 }


Pm10010mptCfgClientStartupEntry ::=
	SEQUENCE {
	pm10010mptCfgClientStartupIndex
		INTEGER,
	pm10010mptCfgSystConfPortPortn
		Unsigned32,
	pm10010mptCfgNetConfPortPortn
		Unsigned32,
	pm10010mptCfgIgnoreTimePortn
		Unsigned32,
	pm10010mptCfgOptionsPortPortn
		Unsigned32
	}


pm10010mptCfgClientStartupIndex OBJECT-TYPE
	SYNTAX  INTEGER(0..128)
	MAX-ACCESS  read-only
	STATUS current
	DESCRIPTION
        "
        Index definition for the clientStartup
        table
        "
	::= { pm10010mptCfgClientStartupEntry 1 }


pm10010mptCfgSystConfPortPortn OBJECT-TYPE
	SYNTAX  Unsigned32 (0..65536)
	MAX-ACCESS read-write
	STATUS current
	DESCRIPTION
        "
        Default Settings on Client Port
        :This  register configures the
         default initialisation settings
        on the port.
        "
	::= { pm10010mptCfgClientStartupEntry 3 }


pm10010mptCfgNetConfPortPortn OBJECT-TYPE
	SYNTAX  Unsigned32 (0..65536)
	MAX-ACCESS read-write
	STATUS current
	DESCRIPTION
        "
        Default Settings on Client Port
        :This  register configures the
         default initialisation settings
        on the port.
        "
	::= { pm10010mptCfgClientStartupEntry 4 }


pm10010mptCfgIgnoreTimePortn OBJECT-TYPE
	SYNTAX  Unsigned32 (0..65536)
	MAX-ACCESS read-write
	STATUS current
	DESCRIPTION
        "
        Default Settings on Client Port
        :This  register configures the
         default initialisation settings
        on the port.
        "
	::= { pm10010mptCfgClientStartupEntry 6 }


pm10010mptCfgOptionsPortPortn OBJECT-TYPE
	SYNTAX  Unsigned32 (0..65536)
	MAX-ACCESS read-write
	STATUS current
	DESCRIPTION
        "
        Default Options on Client Port
        :This register configures the default
        options on the port.
        "
	::= { pm10010mptCfgClientStartupEntry 14 }


--- *****************************************************
---     LEAF for the table 2190
--- *****************************************************

pm10010mptCfgLineStartupTable OBJECT-TYPE
	SYNTAX  SEQUENCE OF Pm10010mptCfgLineStartupEntry
	MAX-ACCESS not-accessible
	STATUS current
	DESCRIPTION
        "
        List of  Article
        "
	::= { pm10010mptCfgStartup 2 }


pm10010mptCfgLineStartupEntry OBJECT-TYPE
	SYNTAX Pm10010mptCfgLineStartupEntry
	MAX-ACCESS not-accessible
	STATUS current
	DESCRIPTION
        "
        Row definition for the startup
        table
        "
	INDEX   { pm10010mptCfgLineStartupIndex }
	::= { pm10010mptCfgLineStartupTable 1 }


Pm10010mptCfgLineStartupEntry ::=
	SEQUENCE {
	pm10010mptCfgLineStartupIndex
		INTEGER,
	pm10010mptCfgSystConfLinePortn
		Unsigned32,
	pm10010mptCfgOptionsLinePortn
		Unsigned32
	}


pm10010mptCfgLineStartupIndex OBJECT-TYPE
	SYNTAX  INTEGER(0..128)
	MAX-ACCESS  read-only
	STATUS current
	DESCRIPTION
        "
        Index definition for the lineStartup
        table
        "
	::= { pm10010mptCfgLineStartupEntry 1 }


pm10010mptCfgSystConfLinePortn OBJECT-TYPE
	SYNTAX  Unsigned32 (0..65536)
	MAX-ACCESS read-write
	STATUS current
	DESCRIPTION
        "
        Default Settings on Line :This
        register configures the default
        initialisation settings on Line
        "
	::= { pm10010mptCfgLineStartupEntry 3 }


pm10010mptCfgOptionsLinePortn OBJECT-TYPE
	SYNTAX  Unsigned32 (0..65536)
	MAX-ACCESS read-write
	STATUS current
	DESCRIPTION
        "
        Default Options on Line :This
         register configures the default
        options on the line
        "
	::= { pm10010mptCfgLineStartupEntry 14 }


--- *****************************************************
---     LEAF for the table 21AB
--- *****************************************************

pm10010mptCfgXfpTable OBJECT-TYPE
	SYNTAX  SEQUENCE OF Pm10010mptCfgXfpEntry
	MAX-ACCESS not-accessible
	STATUS current
	DESCRIPTION
        "
        List of  Article
        "
	::= { pm10010mptCfgStartup 3 }


pm10010mptCfgXfpEntry OBJECT-TYPE
	SYNTAX Pm10010mptCfgXfpEntry
	MAX-ACCESS not-accessible
	STATUS current
	DESCRIPTION
        "
        Row definition for the startup
        table
        "
	INDEX   { pm10010mptCfgXfpIndex }
	::= { pm10010mptCfgXfpTable 1 }


Pm10010mptCfgXfpEntry ::=
	SEQUENCE {
	pm10010mptCfgXfpIndex
		INTEGER,
	pm10010mptCfgSystConfMsaLinePortn
		Unsigned32
	}


pm10010mptCfgXfpIndex OBJECT-TYPE
	SYNTAX  INTEGER(0..128)
	MAX-ACCESS  read-only
	STATUS current
	DESCRIPTION
        "
        Index definition for the xfp table
        "
	::= { pm10010mptCfgXfpEntry 1 }


pm10010mptCfgSystConfMsaLinePortn OBJECT-TYPE
	SYNTAX  Unsigned32 (0..65536)
	MAX-ACCESS read-write
	STATUS current
	DESCRIPTION
        "
        Default settings on MSA :This
         register configures the default
        initialisation settings on MSA
        "
	::= { pm10010mptCfgXfpEntry 3 }


--- *****************************************************
---     LEAF for the table Group labels
--- *****************************************************

pm10010mptCfgLabels OBJECT IDENTIFIER ::= { pm10010mptConfig 3 }



--- *****************************************************
---     LEAF for the table 0003
--- *****************************************************

pm10010mptCfgLabelclientTable OBJECT-TYPE
	SYNTAX  SEQUENCE OF Pm10010mptCfgLabelclientEntry
	MAX-ACCESS not-accessible
	STATUS current
	DESCRIPTION
        "
        List of  Article
        "
	::= { pm10010mptCfgLabels 1 }


pm10010mptCfgLabelclientEntry OBJECT-TYPE
	SYNTAX Pm10010mptCfgLabelclientEntry
	MAX-ACCESS not-accessible
	STATUS current
	DESCRIPTION
        "
        Row definition for the labels
         table
        "
	INDEX   { pm10010mptCfgLabelclientIndex }
	::= { pm10010mptCfgLabelclientTable 1 }


Pm10010mptCfgLabelclientEntry ::=
	SEQUENCE {
	pm10010mptCfgLabelclientIndex
		INTEGER,
	pm10010mptCfgLabelclientPortn
		DisplayString
	}


pm10010mptCfgLabelclientIndex OBJECT-TYPE
	SYNTAX  INTEGER(0..128)
	MAX-ACCESS  read-only
	STATUS current
	DESCRIPTION
        "
        Index definition for the labelclient
        table
        "
	::= { pm10010mptCfgLabelclientEntry 1 }


pm10010mptCfgLabelclientPortn OBJECT-TYPE
	SYNTAX  DisplayString( SIZE(1..16))
	MAX-ACCESS read-write
	STATUS current
	DESCRIPTION
        "
        Default settings on the label
         of the Ports :These registers
         configures the default initialisation
        settings of the labels of the ports.
        "
	::= { pm10010mptCfgLabelclientEntry 3 }


--- *****************************************************
---     LEAF for the table 0004
--- *****************************************************

pm10010mptCfgLabellineTable OBJECT-TYPE
	SYNTAX  SEQUENCE OF Pm10010mptCfgLabellineEntry
	MAX-ACCESS not-accessible
	STATUS current
	DESCRIPTION
        "
        List of  Article
        "
	::= { pm10010mptCfgLabels 2 }


pm10010mptCfgLabellineEntry OBJECT-TYPE
	SYNTAX Pm10010mptCfgLabellineEntry
	MAX-ACCESS not-accessible
	STATUS current
	DESCRIPTION
        "
        Row definition for the labels
         table
        "
	INDEX   { pm10010mptCfgLabellineIndex }
	::= { pm10010mptCfgLabellineTable 1 }


Pm10010mptCfgLabellineEntry ::=
	SEQUENCE {
	pm10010mptCfgLabellineIndex
		INTEGER,
	pm10010mptCfgLabellinePortn
		DisplayString
	}


pm10010mptCfgLabellineIndex OBJECT-TYPE
	SYNTAX  INTEGER(0..128)
	MAX-ACCESS  read-only
	STATUS current
	DESCRIPTION
        "
        Index definition for the labelline
        table
        "
	::= { pm10010mptCfgLabellineEntry 1 }


pm10010mptCfgLabellinePortn OBJECT-TYPE
	SYNTAX  DisplayString( SIZE(1..16))
	MAX-ACCESS read-write
	STATUS current
	DESCRIPTION
        "
        Default settings on the label
         of the lines :These registers
         configures the default initialisation
        settings of the labels of the lines.
        "
	::= { pm10010mptCfgLabellineEntry 3 }


--- *****************************************************
---     LEAF for the table Group startuptlh
--- *****************************************************

pm10010mptCfgStartuptlh OBJECT IDENTIFIER ::= { pm10010mptConfig 4 }



--- *****************************************************
---     LEAF for the table 25AB
--- *****************************************************

pm10010mptCfgOtxtlhTable OBJECT-TYPE
	SYNTAX  SEQUENCE OF Pm10010mptCfgOtxtlhEntry
	MAX-ACCESS not-accessible
	STATUS current
	DESCRIPTION
        "
        List of  Article
        "
	::= { pm10010mptCfgStartuptlh 1 }


pm10010mptCfgOtxtlhEntry OBJECT-TYPE
	SYNTAX Pm10010mptCfgOtxtlhEntry
	MAX-ACCESS not-accessible
	STATUS current
	DESCRIPTION
        "
        Row definition for the startuptlh
        table
        "
	INDEX   { pm10010mptCfgOtxtlhIndex }
	::= { pm10010mptCfgOtxtlhTable 1 }


Pm10010mptCfgOtxtlhEntry ::=
	SEQUENCE {
	pm10010mptCfgOtxtlhIndex
		INTEGER,
	pm10010mptCfgLinePwrLaserPortn
		Unsigned32,
	pm10010mptCfgLineFCurrentPortn
		Unsigned32,
	pm10010mptCfgLineGridCurrentPortn
		Unsigned32,
	pm10010mptCfgFPortn
		Unsigned32,
	pm10010mptCfgRxLineFCurrentPortn
		Unsigned32
	}


pm10010mptCfgOtxtlhIndex OBJECT-TYPE
	SYNTAX  INTEGER(0..128)
	MAX-ACCESS  read-only
	STATUS current
	DESCRIPTION
        "
        Index definition for the otxtlh
        table
        "
	::= { pm10010mptCfgOtxtlhEntry 1 }


pm10010mptCfgLinePwrLaserPortn OBJECT-TYPE
	SYNTAX  Unsigned32 (0..65536)
	MAX-ACCESS read-write
	STATUS current
	DESCRIPTION
        "
        Defaut Line output Power :This
        register configures the start-up
        output power of the Line tranceiver
         (Unit = dBm)
        "
	::= { pm10010mptCfgOtxtlhEntry 6 }


pm10010mptCfgLineFCurrentPortn OBJECT-TYPE
	SYNTAX  Unsigned32 (0..65536)
	MAX-ACCESS read-write
	STATUS current
	DESCRIPTION
        "
        Default Line transceiver Tx Channel
        :This register configures the start-up
        laser channel of the Line Tx transceiver
        "
	::= { pm10010mptCfgOtxtlhEntry 7 }


pm10010mptCfgLineGridCurrentPortn OBJECT-TYPE
	SYNTAX  Unsigned32 (0..65536)
	MAX-ACCESS read-write
	STATUS current
	DESCRIPTION
        "
        Default Line transceiver Grid
         :This register configures the
         start-up laser grid of the Line
        transceiver
        "
	::= { pm10010mptCfgOtxtlhEntry 8 }


pm10010mptCfgFPortn OBJECT-TYPE
	SYNTAX  Unsigned32 (0..65536)
	MAX-ACCESS read-write
	STATUS current
	DESCRIPTION
        "
        Default Line TRX lowest Freq :This
        register configures the start-up
        lowest frequency of the Line transceiver
        "
	::= { pm10010mptCfgOtxtlhEntry 9 }


pm10010mptCfgRxLineFCurrentPortn OBJECT-TYPE
	SYNTAX  Unsigned32 (0..65536)
	MAX-ACCESS read-write
	STATUS current
	DESCRIPTION
        "
        Default Line transceiver Rx Channel
        :This register configures the start-up
        laser channel of the Line Rx transceiver
        "
	::= { pm10010mptCfgOtxtlhEntry 10 }


--- *****************************************************
---     LEAF for the table Group other
--- *****************************************************

pm10010mptCfgOther OBJECT IDENTIFIER ::= { pm10010mptConfig 5 }



--- *****************************************************
---     LEAF for the table 2300
--- *****************************************************

pm10010mpttablemoduleOther OBJECT IDENTIFIER ::= { pm10010mptCfgOther 1 }



pm10010mptCfgmode OBJECT-TYPE
	  SYNTAX Unsigned32 (0..65536)
	  MAX-ACCESS read-write
	  STATUS current
	  DESCRIPTION
        "
        Default settings on Module :This
        register selects the configuration
        mode of the module
        "
	  ::= { pm10010mpttablemoduleOther 2 }



pm10010mptCfgfanLowSpeedThreshold OBJECT-TYPE
	  SYNTAX Unsigned32 (0..65536)
	  MAX-ACCESS read-write
	  STATUS current
	  DESCRIPTION
        "
        Default settings on Module :This
        register selects the speed threshold
        of the fan's
        "
	  ::= { pm10010mpttablemoduleOther 3 }



pm10010mptCfgfanHighSpeedThreshold OBJECT-TYPE
	  SYNTAX Unsigned32 (0..65536)
	  MAX-ACCESS read-write
	  STATUS current
	  DESCRIPTION
        "
        Default settings on Module :This
        register selects the speed threshold
        of the fan's
        "
	  ::= { pm10010mpttablemoduleOther 4 }



--- *****************************************************
---     LEAF for the table Group startuptablefive
--- *****************************************************

pm10010mptCfgStartuptablefive OBJECT IDENTIFIER ::= { pm10010mptConfig 6 }



--- *****************************************************
---     LEAF for the table 0005
--- *****************************************************

pm10010mptCfgOtxtlhcapabilitiesTable OBJECT-TYPE
	SYNTAX  SEQUENCE OF Pm10010mptCfgOtxtlhcapabilitiesEntry
	MAX-ACCESS not-accessible
	STATUS current
	DESCRIPTION
        "
        List of  Article
        "
	::= { pm10010mptCfgStartuptablefive 1 }


pm10010mptCfgOtxtlhcapabilitiesEntry OBJECT-TYPE
	SYNTAX Pm10010mptCfgOtxtlhcapabilitiesEntry
	MAX-ACCESS not-accessible
	STATUS current
	DESCRIPTION
        "
        Row definition for the startuptablefive
        table
        "
	INDEX   { pm10010mptCfgOtxtlhcapabilitiesIndex }
	::= { pm10010mptCfgOtxtlhcapabilitiesTable 1 }


Pm10010mptCfgOtxtlhcapabilitiesEntry ::=
	SEQUENCE {
	pm10010mptCfgOtxtlhcapabilitiesIndex
		INTEGER,
	pm10010mptCfgComponentTypePortn
		Unsigned32,
	pm10010mptCfgMiscellaneousPortn
		Unsigned32,
	pm10010mptCfgFirstChannelPortn
		Unsigned32,
	pm10010mptCfgLastChannelPortn
		Unsigned32,
	pm10010mptCfgGridPortn
		Unsigned32
	}


pm10010mptCfgOtxtlhcapabilitiesIndex OBJECT-TYPE
	SYNTAX  INTEGER(0..128)
	MAX-ACCESS  read-only
	STATUS current
	DESCRIPTION
        "
        Index definition for the otxtlhcapabilities
        table
        "
	::= { pm10010mptCfgOtxtlhcapabilitiesEntry 1 }


pm10010mptCfgComponentTypePortn OBJECT-TYPE
	SYNTAX  Unsigned32 (0..65536)
	MAX-ACCESS read-only
	STATUS current
	DESCRIPTION
        "
        Component parameters :This OID
        defines the component parameters
        "
	::= { pm10010mptCfgOtxtlhcapabilitiesEntry 3 }


pm10010mptCfgMiscellaneousPortn OBJECT-TYPE
	SYNTAX  Unsigned32 (0..65536)
	MAX-ACCESS read-only
	STATUS current
	DESCRIPTION
        "
        Miscellaneous default settings
        :This OID defines the miscellaneous
        parameters
        "
	::= { pm10010mptCfgOtxtlhcapabilitiesEntry 4 }


pm10010mptCfgFirstChannelPortn OBJECT-TYPE
	SYNTAX  Unsigned32 (0..65536)
	MAX-ACCESS read-only
	STATUS current
	DESCRIPTION
        "
        Number of the first channel of
        the component :This OID defines
        the first channel number of the
        PM
        "
	::= { pm10010mptCfgOtxtlhcapabilitiesEntry 5 }


pm10010mptCfgLastChannelPortn OBJECT-TYPE
	SYNTAX  Unsigned32 (0..65536)
	MAX-ACCESS read-only
	STATUS current
	DESCRIPTION
        "
        Number of the last channel of
         the component :This OID defines
        the last channel number of the
         PM
        "
	::= { pm10010mptCfgOtxtlhcapabilitiesEntry 6 }


pm10010mptCfgGridPortn OBJECT-TYPE
	SYNTAX  Unsigned32 (0..65536)
	MAX-ACCESS read-only
	STATUS current
	DESCRIPTION
        "
        Grid value of the component :This
        OID defines the grid of the PM
        "
	::= { pm10010mptCfgOtxtlhcapabilitiesEntry 7 }



pm10010mptCfgWriteConfiguration  OBJECT-TYPE
	SYNTAX EkiOnOff
	MAX-ACCESS read-write
	STATUS current
	DESCRIPTION
	"Write configuration to module:This OID
	 writes the complete configuration to the module"
	::= { pm10010mptConfig 257 }






--- *****************************************************
---     TRAP OBJECTS
--- *****************************************************

pm10010mpttrapPortNumber OBJECT-TYPE
	SYNTAX INTEGER(1..64)
	MAX-ACCESS read-only
	STATUS current
	DESCRIPTION
	"Last port which generates a trap"
	::= { pm10010mpttraps 2 }

pm10010mpttrapLineNumber OBJECT-TYPE
	SYNTAX INTEGER(1..64)
	MAX-ACCESS read-only
	STATUS current
	DESCRIPTION
	"Last Line which generates a trap"
	::= { pm10010mpttraps 3 }

pm10010mpttrapBoardNumber OBJECT-TYPE
	SYNTAX INTEGER(1..64)
	MAX-ACCESS read-only
	STATUS current
	DESCRIPTION
	"Last module which generates a trap"
	::= { pm10010mpttraps 4 }







--- *****************************************************
---     LINE TRAPS
--- *****************************************************

pm10010mptLineTrapNotUrgentGoesOn NOTIFICATION-TYPE
	OBJECTS {pm10010mptAlmLineDdmWarningPortn, pm10010mpttrapLineNumber, pm10010mpttrapBoardNumber}
	STATUS current
	--&FILTNAME    "PM10010MPT Line Not Urgent ON"
	--&ACTIONS     { log, minor }
	--&MATCH       { pm10010mptAlmLineDdmWarningPortn "on", pm10010mpttrapLineNumber "$2", pm10010mpttrapBoardNumber "$3"}
	--&MESG        "DDM Warning appears on Line Port $2 of PM10010MPT in Slot $3 ($A)"
	DESCRIPTION "Not urgent Line default is activated"
	::= { pm10010mpttraps 30 }

pm10010mptLineTrapNotUrgentGoesOff NOTIFICATION-TYPE
	OBJECTS {pm10010mptAlmLineDdmWarningPortn, pm10010mpttrapLineNumber, pm10010mpttrapBoardNumber}
	STATUS current
	--&FILTNAME    "PM10010MPT Line Not Urgent OFF"
	--&ACTIONS     { log, normal }
	--&CLEARS      { "PM10010MPT Line Not Urgent ON" }
	--&MATCH       { pm10010mptAlmLineDdmWarningPortn "on", pm10010mpttrapLineNumber "$2", pm10010mpttrapBoardNumber "$3"}
	--&MESG        "DDM Warning disappears on Line Port $2 of PM10010MPT in Slot $3 ($A)"
	DESCRIPTION "Not urgent Line default disappeared"
	::= { pm10010mpttraps 31 }

pm10010mptLineTrapUrgentGoesOn NOTIFICATION-TYPE
	OBJECTS {pm10010mptAlmLineDdmAlmPortn, pm10010mpttrapLineNumber, pm10010mpttrapBoardNumber}
	STATUS current
	--&FILTNAME    "PM10010MPT Line Urgent ON"
	--&ACTIONS     { log, major }
	--&MATCH       { pm10010mptAlmLineDdmAlmPortn "on", pm10010mpttrapLineNumber "$2", pm10010mpttrapBoardNumber "$3"}
	--&MESG        "DDM Alarm appears on Line Port $2 of PM10010MPT in Slot $3 ($A)"
	DESCRIPTION "Urgent Line default is activated"
	::= { pm10010mpttraps 32 }

pm10010mptLineTrapUrgentGoesOff NOTIFICATION-TYPE
	OBJECTS {pm10010mptAlmLineDdmAlmPortn, pm10010mpttrapLineNumber, pm10010mpttrapBoardNumber}
	STATUS current
	--&FILTNAME    "PM10010MPT Line Urgent OFF"
	--&ACTIONS     { log, normal }
	--&CLEARS      { "PM10010MPT Line Urgent ON" }
	--&MATCH       { pm10010mptAlmLineDdmAlmPortn "on", pm10010mpttrapLineNumber "$2", pm10010mpttrapBoardNumber "$3"}
	--&MESG        "DDM Alarm disappears on Line Port $2 of PM10010MPT in Slot $3 ($A)"
	DESCRIPTION "Urgent Line default disappeared"
	::= { pm10010mpttraps 33 }

pm10010mptLineTrapCritGoesOn NOTIFICATION-TYPE
	OBJECTS {pm10010mptAlmLineFailPortn , pm10010mptAlmLineHwFailPortn , pm10010mpttrapLineNumber, pm10010mpttrapBoardNumber}
	STATUS current
	--&FILTNAME    "PM10010MPT Line Fail ON"
	--&ACTIONS     { log, critical }
	--&MATCH       { pm10010mptAlmLineFailPortn "on", pm10010mptAlmLineHwFailPortn "*", pm10010mpttrapLineNumber "$3", pm10010mpttrapBoardNumber "$4"}
	--&MESG        "Line Port $3 Down on PM10010MPT in Slot $4 ($A)"

	--&FILTNAME    "PM10010MPT Line HW Fail ON (Hidden)"
	--&ACTIONS     { info }
	--&MATCH       { pm10010mptAlmLineFailPortn "*", pm10010mptAlmLineHwFailPortn "on", pm10010mpttrapLineNumber "$3", pm10010mpttrapBoardNumber "$4"}
	--&MESG        "Line Port $3 Down on PM10010MPT in Slot $4 ($A)"
	DESCRIPTION "Critical Line default is activated"
	::= { pm10010mpttraps 34 }

pm10010mptLineTrapCritGoesOff NOTIFICATION-TYPE
	OBJECTS {pm10010mptAlmLineFailPortn , pm10010mptAlmLineHwFailPortn , pm10010mpttrapLineNumber, pm10010mpttrapBoardNumber}
	STATUS current
	--&FILTNAME    "PM10010MPT Line Fail OFF"
	--&ACTIONS     { log,  normal }
	--&CLEARS      { "PM10010MPT Line Fail ON" }
	--&MATCH       { pm10010mptAlmLineFailPortn "on", pm10010mptAlmLineHwFailPortn "*", pm10010mpttrapLineNumber "$3", pm10010mpttrapBoardNumber "$4"}
	--&MESG        "Line Port $3 Up on PM10010MPT in Slot $4 ($A)"

	--&FILTNAME    "PM10010MPT Line HW Fail OFF (Hidden)"
	--&ACTIONS     { info }
	--&MATCH       { pm10010mptAlmLineFailPortn "*", pm10010mptAlmLineHwFailPortn "on", pm10010mpttrapLineNumber "$3", pm10010mpttrapBoardNumber "$4"}
	--&MESG        "Line Port $3 Up on PM10010MPT in Slot $4 ($A)"
	DESCRIPTION "Critical Line default disappeared"
	::= { pm10010mpttraps 35 }






--- *****************************************************
---     CLIENT TRAPS
--- *****************************************************

pm10010mptClientTrapNotUrgentGoesOn NOTIFICATION-TYPE
	OBJECTS {pm10010mptAlmSfpDdmWarningPortn, pm10010mpttrapPortNumber, pm10010mpttrapBoardNumber}
	STATUS current
		--&FILTNAME    "PM10010MPT Client Not Urgent ON"
		--&ACTIONS     { log, minor }
		--&MATCH       { pm10010mptAlmSfpDdmWarningPortn "on", pm10010mpttrapPortNumber "$2", pm10010mpttrapBoardNumber "$3"}
		--&MESG        "DDM Warning appears on Client Port $2 of PM10010MPT in Slot $3 ($A)"
	DESCRIPTION "Not urgent client default is activated"
	::= { pm10010mpttraps 40 }

pm10010mptClientTrapNotUrgentGoesOff NOTIFICATION-TYPE
	OBJECTS {pm10010mptAlmSfpDdmWarningPortn, pm10010mpttrapPortNumber, pm10010mpttrapBoardNumber}
	STATUS current
		--&FILTNAME    "PM10010MPT Client Not Urgent OFF"
		--&ACTIONS     { log, normal }
		--&CLEARS      { "PM10010MPT Client Not Urgent ON" }
		--&MATCH       { pm10010mptAlmSfpDdmWarningPortn "on", pm10010mpttrapPortNumber "$2", pm10010mpttrapBoardNumber "$3"}
		--&MESG        "DDM Warning appears on Client Port $2 of PM10010MPT in Slot $3 ($A)"
	DESCRIPTION "Not urgent client default disappeared"
	::= { pm10010mpttraps 41 }

pm10010mptClientTrapUrgentGoesOn NOTIFICATION-TYPE
	OBJECTS {pm10010mptAlmSfpDdmAlmPortn, pm10010mpttrapPortNumber, pm10010mpttrapBoardNumber}
	STATUS current
		--&FILTNAME    "PM10010MPT Client Urgent ON"
		--&ACTIONS     { log, major }
		--&MATCH       { pm10010mptAlmSfpDdmAlmPortn "on", pm10010mpttrapPortNumber "$2", pm10010mpttrapBoardNumber "$3"}
		--&MESG        "DDM Alarm appears on Client Port $2 of PM10010MPT in Slot $3 ($A)"
	DESCRIPTION "Urgent client default is activated"
	::= { pm10010mpttraps 42 }

pm10010mptClientTrapUrgentGoesOff NOTIFICATION-TYPE
	OBJECTS {pm10010mptAlmSfpDdmAlmPortn, pm10010mpttrapPortNumber, pm10010mpttrapBoardNumber}
	STATUS current
		--&FILTNAME    "PM10010MPT Client Urgent OFF"
		--&ACTIONS     { log, normal }
		--&CLEARS      { "PM10010MPT Client Urgent ON" }
		--&MATCH       { pm10010mptAlmSfpDdmAlmPortn "on", pm10010mpttrapPortNumber "$2", pm10010mpttrapBoardNumber "$3"}
		--&MESG        "DDM Alarm disappears on Client Port $2 of PM10010MPT in Slot $3 ($A)"
	DESCRIPTION "Urgent client default disappeared"
	::= { pm10010mpttraps 43 }

pm10010mptClientTrapCritGoesOn NOTIFICATION-TYPE
	OBJECTS {pm10010mptAlmFailAccPortn, pm10010mptAlmHwFailAccPortn, pm10010mpttrapPortNumber, pm10010mpttrapBoardNumber}
	STATUS current
		--&FILTNAME    "PM10010MPT Client Fail ON"
		--&ACTIONS     { log, critical }
		--&MATCH       { pm10010mptAlmFailAccPortn "on", pm10010mptAlmHwFailAccPortn "*", pm10010mpttrapPortNumber "$3", pm10010mpttrapBoardNumber "$4"}
		--&MESG        "Client Port $3 Down on PM10010MPT in Slot $4 ($A)"

		--&FILTNAME    "PM10010MPT Client HW Fail ON (Hidden)"
		--&ACTIONS     { info }
		--&MATCH       { pm10010mptAlmFailAccPortn "*", pm10010mptAlmHwFailAccPortn "on", pm10010mpttrapPortNumber "$3", pm10010mpttrapBoardNumber "$4"}
		--&MESG        "Client Port $3 Down on PM10010MPT in Slot $4 ($A)"
	DESCRIPTION "Critical client default is activated"
	::= { pm10010mpttraps 44 }

pm10010mptClientTrapCritGoesOff NOTIFICATION-TYPE
	OBJECTS {pm10010mptAlmFailAccPortn, pm10010mptAlmHwFailAccPortn, pm10010mpttrapPortNumber, pm10010mpttrapBoardNumber}
	STATUS current
		--&FILTNAME    "PM10010MPT Client Fail OFF"
		--&ACTIONS     { log, normal }
		--&CLEARS      { "PM10010MPT Client Fail ON" }
		--&MATCH       { pm10010mptAlmFailAccPortn "on", pm10010mptAlmHwFailAccPortn "*", pm10010mpttrapPortNumber "$3", pm10010mpttrapBoardNumber "$4"}
		--&MESG        "Client Port $3 Up on PM10010MPT in Slot $4 ($A)"

		--&FILTNAME    "PM10010MPT Client HW Fail OFF (Hidden)"
		--&ACTIONS     { info }
		--&MATCH       { pm10010mptAlmFailAccPortn "*", pm10010mptAlmHwFailAccPortn "on", pm10010mpttrapPortNumber "$3", pm10010mpttrapBoardNumber "$4"}
		--&MESG        "Client Port $3 Up on PM10010MPT in Slot $4 ($A)"
	DESCRIPTION "Critical client default disappeared"
	::= { pm10010mpttraps 45 }






--- *****************************************************
---     HW TRAPS
--- *****************************************************

pm10010mptPowerTrapUrgentGoesOn NOTIFICATION-TYPE
	OBJECTS {pm10010mptAlmDefFuseB, pm10010mptAlmDefFuseA , pm10010mpttrapBoardNumber}
	STATUS current
		--&FILTNAME    "PM10010MPT Fuse A Fail ON"
		--&ACTIONS     { log, major }
		--&MATCH       { pm10010mptAlmDefFuseB "*", pm10010mptAlmDefFuseA "on", pm10010mpttrapBoardNumber "$3"}
		--&MESG        "Power Input A Fail on PM10010MPT in Slot $3 ($A)"

		--&FILTNAME    "PM10010MPT Fuse B Fail ON"
		--&ACTIONS     { log, major }
		--&MATCH       { pm10010mptAlmDefFuseB "on", pm10010mptAlmDefFuseA "*", pm10010mpttrapBoardNumber "$3"}
		--&MESG        "Power Input B Fail on PM10010MPT in Slot $3 ($A)"
	DESCRIPTION "Urgent power supply default is activated"
	::= { pm10010mpttraps 50 }

pm10010mptPowerTrapUrgentGoesOff NOTIFICATION-TYPE
	OBJECTS {pm10010mptAlmDefFuseB, pm10010mptAlmDefFuseA , pm10010mpttrapBoardNumber}
	STATUS current
		--&FILTNAME    "PM10010MPT Fuse A&B Fail OFF"
		--&ACTIONS     { log, normal}
		--&CLEARS      { "PM10010MPT Fuse A Fail ON", "PM10010MPT Fuse B Fail ON" }
		--&MATCH       { pm10010mptAlmDefFuseB "on", pm10010mptAlmDefFuseA "on", pm10010mpttrapBoardNumber "$3"}
		--&MESG        "Power Inputs A and B Present on PM10010MPT in Slot $3 ($A)"
	DESCRIPTION "Urgent power supply default disappeared"
	::= { pm10010mpttraps 51 }






END
