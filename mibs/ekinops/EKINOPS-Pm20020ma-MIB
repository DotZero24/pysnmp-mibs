-- *****************************************************************
-- EKINOPS-Pm20020ma.TXT:  MIB
--
--MIB Part Number:3MI00035AAAE
--MIB Version:02
--
-- Copyright (c) 2017 by Ekinops
-- All rights reserved.
--
-- *****************************************************************

EKINOPS-Pm20020ma-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

modulePm20020ma MODULE-IDENTITY
        LAST-UPDATED "201703310000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.fr"
        DESCRIPTION
          "Creation."

	REVISION "201503190000Z"
	DESCRIPTION
	  "Creation for PM20020MA"
	REVISION "201601050000Z"
	DESCRIPTION
	  "Datacom Perf SNMP objects corrections"
	REVISION "201602290000Z"
	DESCRIPTION
	  "New Object type on INV"
	REVISION "201604200000Z"
	DESCRIPTION
	  "Label modif on a line counter"
	REVISION "201605200000Z"
	DESCRIPTION
	  "New AlarmType – synthesisAlarm (12)"
	REVISION "201606020000Z"
	DESCRIPTION
	  "Capabilities objects of Table 5"
	REVISION "201703310000Z"
	DESCRIPTION
	  "Module Modes"
        ::= { ekinops 69 }



--- *****************************************************
---     LEAF LEVEL 2
--- *****************************************************


pm20020maalarms OBJECT IDENTIFIER ::= { modulePm20020ma 2 }
pm20020maAlmOther OBJECT IDENTIFIER ::= { pm20020maalarms 1 }
pm20020maAlmOtherNurg OBJECT IDENTIFIER ::= { pm20020maAlmOther 1 }
pm20020maAlmOtherUrg OBJECT IDENTIFIER ::= { pm20020maAlmOther 2 }
pm20020maAlmOtherCrit OBJECT IDENTIFIER ::= { pm20020maAlmOther 3 }

pm20020maAlmClient OBJECT IDENTIFIER ::= { pm20020maalarms 2 }
pm20020maAlmClientNurg OBJECT IDENTIFIER ::= { pm20020maAlmClient 1 }
pm20020maAlmClientUrg OBJECT IDENTIFIER ::= { pm20020maAlmClient 2 }
pm20020maAlmClientCrit OBJECT IDENTIFIER ::= { pm20020maAlmClient 3 }

pm20020maAlmLine OBJECT IDENTIFIER ::= { pm20020maalarms 3 }
pm20020maAlmLineNurg OBJECT IDENTIFIER ::= { pm20020maAlmLine 1 }
pm20020maAlmLineUrg OBJECT IDENTIFIER ::= { pm20020maAlmLine 2 }
pm20020maAlmLineCrit OBJECT IDENTIFIER ::= { pm20020maAlmLine 3 }





pm20020mameasures OBJECT IDENTIFIER ::= { modulePm20020ma 3 }
pm20020maMesrOther OBJECT IDENTIFIER ::= { pm20020mameasures 1 }
pm20020maMesrClient OBJECT IDENTIFIER ::= { pm20020mameasures 2 }
pm20020maMesrLine OBJECT IDENTIFIER ::= { pm20020mameasures 3 }




pm20020macounters OBJECT IDENTIFIER ::= { modulePm20020ma 4 }
pm20020maCntOther OBJECT IDENTIFIER ::= { pm20020macounters 1 }
pm20020maCntClient OBJECT IDENTIFIER ::= { pm20020macounters 2 }
pm20020maCntLine OBJECT IDENTIFIER ::= { pm20020macounters 3 }


pm20020macontrolsWrite OBJECT IDENTIFIER ::= { modulePm20020ma 6 }
pm20020maCtrlOther OBJECT IDENTIFIER ::= { pm20020macontrolsWrite 1 }
pm20020maCtrlClient OBJECT IDENTIFIER ::= { pm20020macontrolsWrite 2 }
pm20020maCtrlLine OBJECT IDENTIFIER ::= { pm20020macontrolsWrite 3 }

pm20020mari OBJECT IDENTIFIER ::= { modulePm20020ma 7 }
pm20020mariTable OBJECT IDENTIFIER ::= { pm20020mari 1 }

pm20020madownload OBJECT IDENTIFIER ::= { modulePm20020ma 8 }
pm20020maDwlOther OBJECT IDENTIFIER ::= { pm20020madownload 1 }
pm20020maDwlClient OBJECT IDENTIFIER ::= { pm20020madownload 2 }
pm20020maDwlLine OBJECT IDENTIFIER ::= { pm20020madownload 3 }


pm20020maConfig OBJECT IDENTIFIER ::= { modulePm20020ma 9 }

pm20020matraps OBJECT IDENTIFIER ::= { modulePm20020ma 10 }



pm20020maMonitoring OBJECT IDENTIFIER ::= { modulePm20020ma 11}

pm20020maMonOther OBJECT IDENTIFIER ::= { pm20020maMonitoring 1 }
pm20020maMonRmon OBJECT IDENTIFIER ::= { pm20020maMonOther 3 }

pm20020maMonClient OBJECT IDENTIFIER ::= { pm20020maMonitoring 2 }
pm20020maMonClientRmonCounter OBJECT IDENTIFIER ::= { pm20020maMonClient 4 }


pm20020maMonPerfOther OBJECT IDENTIFIER ::= { pm20020maMonitoring 5 }
pm20020maMonPerfSync OBJECT IDENTIFIER ::= { pm20020maMonPerfOther 1 }
pm20020maMonPerfTimeStamp OBJECT IDENTIFIER ::= { pm20020maMonPerfOther 2 }


pm20020maMonPerfClient OBJECT IDENTIFIER ::= { pm20020maMonitoring 6 }

pm20020maMonPerfLine OBJECT IDENTIFIER ::= { pm20020maMonitoring 7 }



--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Pm20020maMultiRate ::= TEXTUAL-CONVENTION
    STATUS      current
    DESCRIPTION "different rate for a client port"
    SYNTAX INTEGER {
		rate100Mhz(0),
		rate250Mhz(1),
		rate500Mhz(2),
		rate1Ghz(3)
           }

Pm20020maOtxMode ::= TEXTUAL-CONVENTION
    STATUS      current
    DESCRIPTION "Different modes on OTX-TLH on client and line ports"
    SYNTAX INTEGER {
		otx80mode(1),
		otx60mode(2),
		otxadjustmode(4)
           }

Pm20020maOtxGrid ::= TEXTUAL-CONVENTION
    STATUS      current
    DESCRIPTION "Different grids on OTX-TLH on client and line ports"
    SYNTAX INTEGER {
		otxgrid200(200),
		otxgrid100(100),
		otxgrid50(50)
           }

Pm20020maAdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pm20020maClientProtocol ::= TEXTUAL-CONVENTION
    STATUS      current
    DESCRIPTION "Different values on the protocol on the client ports"
    SYNTAX INTEGER {
		protocolclientvalue0(0),
		protocolclientvalue1(1),
		protocolclientvalue2(2),
		protocolclientvalue3(3),
		protocolclientvalue4(4),
		protocolclientvalue5(5),
		protocolclientvalue6(6),
		protocolclientvalue7(7),
		protocolclientvalue8(8)
           }

Pm20020maProtocolMode ::= TEXTUAL-CONVENTION
    STATUS      current
    DESCRIPTION "Different values on the protocol mode"
    SYNTAX INTEGER {
		protocolmodevalue0(0),
		protocolmodevalue1(1),
		protocolmodevalue2(2),
		protocolmodevalue3(3)
           }

Pm20020maOtxChannel ::= TEXTUAL-CONVENTION
    STATUS      current
    DESCRIPTION "Channel selection on transceiver Tx line ports"
    SYNTAX INTEGER

Pm20020maOrxChannel ::= TEXTUAL-CONVENTION
    STATUS      current
    DESCRIPTION "Channel selection on transceiver Rx line ports"
    SYNTAX INTEGER

Pm20020maDccMode ::= TEXTUAL-CONVENTION
    STATUS      current
    DESCRIPTION "Mode for DCC"
    SYNTAX INTEGER {
		dccNo(0),
		dccLine1(1),
		dccLine2(2)
           }

Pm20020maModuleMode ::= TEXTUAL-CONVENTION
    STATUS      current
    DESCRIPTION "Mode for the  module"
    SYNTAX INTEGER {
		unusedmode(0),
		mode200gma(1),
		mode200gmr(2),
		mode100gulh(3)
           }

--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm20020maRinvReloadInventory OBJECT-TYPE
  SYNTAX EkiOnOff
  MAX-ACCESS read-write
  STATUS current
  DESCRIPTION
        "Reload the inventory: This OID triggers an
         inventory reload."
  ::= { pm20020mari 2 }

pm20020maRinvHwPlatform OBJECT-TYPE
  SYNTAX DisplayString
  MAX-ACCESS read-only
  STATUS current
  DESCRIPTION
        "HW platform description: This OID contains the
         description of the Hardware platform."
  ::= { pm20020mari 3 }

pm20020maRinvModulePlatform OBJECT-TYPE
  SYNTAX DisplayString
  MAX-ACCESS read-only
  STATUS current
  DESCRIPTION
        "Module platform description: This OID contains the
         description of the Module."
  ::= { pm20020mari 4 }

pm20020maRinvSwPlatform OBJECT-TYPE
  SYNTAX DisplayString
  MAX-ACCESS read-only
  STATUS current
  DESCRIPTION
        "SW platform description: This OID contains the
         description of the Software platform."
  ::= { pm20020mari 5 }

pm20020maRinvGwPlatform OBJECT-TYPE
  SYNTAX DisplayString
  MAX-ACCESS read-only
  STATUS current
  DESCRIPTION
        "GW platform description: This OID contains the
         description of the Gateware platform."
  ::= { pm20020mari 6 }


pm20020maRinvSfpTable OBJECT-TYPE
      SYNTAX  SEQUENCE OF Pm20020maRinvSfpEntry
      MAX-ACCESS  not-accessible
      STATUS  current
      DESCRIPTION
              "List of the SFPs on the selected module"
      ::= { pm20020mariTable 1 }

pm20020maRinvSfpEntry OBJECT-TYPE
        SYNTAX  Pm20020maRinvSfpEntry
        MAX-ACCESS  not-accessible
        STATUS  current
        DESCRIPTION
              "Row definition for the SFP table"
        INDEX   { pm20020maRinvSfpIndex }
        ::= { pm20020maRinvSfpTable 1 }



Pm20020maRinvSfpEntry::=
        SEQUENCE {
          pm20020maRinvSfpIndex
              Integer32,
          pm20020maRinvsfp
              DisplayString
        }


    pm20020maRinvSfpIndex OBJECT-TYPE
        SYNTAX  Integer32(1..16)
        MAX-ACCESS  read-only
        STATUS  current
        DESCRIPTION
              "Index for SFP table"
        ::= { pm20020maRinvSfpEntry 1 }


    pm20020maRinvsfp OBJECT-TYPE
        SYNTAX  DisplayString
        MAX-ACCESS  read-only
        STATUS  current
        DESCRIPTION
              "Inventory for the SFP: This OID contains the inventory for the SFP"
        ::= { pm20020maRinvSfpEntry 2 }




pm20020maRinvLineTable OBJECT-TYPE
      SYNTAX  SEQUENCE OF Pm20020maRinvLineEntry
      MAX-ACCESS  not-accessible
      STATUS  current
      DESCRIPTION
              "List of the XFPs on the selected module"
      ::= { pm20020mariTable 2 }

pm20020maRinvLineEntry OBJECT-TYPE
        SYNTAX  Pm20020maRinvLineEntry
        MAX-ACCESS  not-accessible
        STATUS  current
        DESCRIPTION
              "Row definition for the XFP table"
        INDEX   { pm20020maRinvLineIndex }
        ::= { pm20020maRinvLineTable 1 }



Pm20020maRinvLineEntry::=
        SEQUENCE {
          pm20020maRinvLineIndex
              Integer32,
          pm20020maRinvxfpLine
              DisplayString
        }


    pm20020maRinvLineIndex OBJECT-TYPE
        SYNTAX  Integer32(1..16)
        MAX-ACCESS  read-only
        STATUS  current
        DESCRIPTION
              "Index for XFP table"
        ::= { pm20020maRinvLineEntry 1 }


    pm20020maRinvxfpLine OBJECT-TYPE
        SYNTAX  DisplayString
        MAX-ACCESS  read-only
        STATUS  current
        DESCRIPTION
              "Inventory for the XFP: This OID contains the inventory for the XFP"
        ::= { pm20020maRinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm20020maAlmsynthAlm0 OBJECT IDENTIFIER ::= { pm20020maAlmOtherCrit 0 }




pm20020maAlmDefFuseB OBJECT-TYPE
	  SYNTAX EkiOnOff
	  MAX-ACCESS read-only
	  STATUS current
	  DESCRIPTION
        "
        Fuse B Fail :This OID indicates
        that the fuse of the power input
        B is in fail condition <Help> Status
        of the Fuse B <Condtype> DEF_FUSE_B
        <Probcause> powerProblem (36) <Alarmtype>
        equipmentAlarm (5) <Polarity> (2)
        "
	  ::= { pm20020maAlmsynthAlm0 16 }



pm20020maAlmDefFuseA OBJECT-TYPE
	  SYNTAX EkiOnOff
	  MAX-ACCESS read-only
	  STATUS current
	  DESCRIPTION
        "
        Fuse A Fail :This OID indicates
        that the fuse of the power input
        A is in fail condition <Help> Status
        of the Fuse A <Condtype> DEF_FUSE_A
        <Probcause> powerProblem (36) <Alarmtype>
        equipmentAlarm (5) <Polarity> (2)
        "
	  ::= { pm20020maAlmsynthAlm0 15 }



pm20020maAlmModGlobFail OBJECT-TYPE
	  SYNTAX EkiOnOff
	  MAX-ACCESS read-only
	  STATUS current
	  DESCRIPTION
        "
        Module Failure :This OID is set
        on detection of a failure originating
        from the RM <Help> This alarm is
        set on detection of a failure originating
        from the equipment <Condtype> MOD_GLOB_FAIL
        <Probcause> other (1) <Alarmtype>
        synthesisAlarm (12)  <Polarity>
        (2)
        "
	  ::= { pm20020maAlmsynthAlm0 9 }



pm20020maAlmFailFan OBJECT-TYPE
	  SYNTAX EkiOnOff
	  MAX-ACCESS read-only
	  STATUS current
	  DESCRIPTION
        "
        Fan Fail :This OID is at 1 when
        any fail occurs on the fan tray
        <Help> This alarm indicates that
        the Fan tray module is in a failure
        condition <Condtype> FAIL_FAN <Probcause>
        equipmentMalfunction (16) <Alarmtype>
        equipmentAlarm (5) <Polarity> (2)
        "
	  ::= { pm20020maAlmsynthAlm0 2 }



--- *****************************************************
---     LEAF for the synthAlm2 article
--- *****************************************************
pm20020maAlmsynthAlm2 OBJECT IDENTIFIER ::= { pm20020maAlmOtherNurg 2 }




pm20020maAlmMaintenanceOn OBJECT-TYPE
	  SYNTAX EkiOnOff
	  MAX-ACCESS read-only
	  STATUS current
	  DESCRIPTION
        "
        Maintenance Mode :This OID indicates
        that the RM is in maintenance mode.
        <Help> This alarm indicates that
        the maintenance mode is enabled
        on the PM <Condtype> MAINTENANCE_ON
        <Probcause> informationalStatus(1000)
        <Alarmtype> other (1) <Polarity>
        (2)
        "
	  ::= { pm20020maAlmsynthAlm2 5 }



pm20020maAlmCorrelatOff OBJECT-TYPE
	  SYNTAX EkiOnOff
	  MAX-ACCESS read-only
	  STATUS current
	  DESCRIPTION
        "
        Not Used :This OID, when set,
         indicates that alarm correlation
        is not being performed. <Condtype>
        CORRELAT_OFF <Probcause> informationalStatus(1000)
        <Alarmtype> other (1) <Polarity>
        (2)
        "
	  ::= { pm20020maAlmsynthAlm2 4 }



pm20020maAlmConfTableLoad OBJECT-TYPE
	  SYNTAX EkiOnOff
	  MAX-ACCESS read-only
	  STATUS current
	  DESCRIPTION
        "
        PM Configuration Load :This OID
         is at 1 during the loading of
         configuration tables in the modules
        RAM. <Condtype> CONF_TABLE_LOAD
        <Probcause> informationalStatus(1000)
        <Alarmtype> other (1) <Polarity>
        (2)
        "
	  ::= { pm20020maAlmsynthAlm2 3 }



pm20020maAlmInvUpload OBJECT-TYPE
	  SYNTAX EkiOnOff
	  MAX-ACCESS read-only
	  STATUS current
	  DESCRIPTION
        "
        Inventory Upload :This OID is
         at 1 during the uploading of PM
        inventory information. <Condtype>
        INV_UPLOAD <Probcause> informationalStatus(1000)
        <Alarmtype> other (1) <Polarity>
        (2)
        "
	  ::= { pm20020maAlmsynthAlm2 2 }



pm20020maAlmConfTableSave OBJECT-TYPE
	  SYNTAX EkiOnOff
	  MAX-ACCESS read-only
	  STATUS current
	  DESCRIPTION
        "
        PM Configuration Save :This OID
        is at 1 during the saving of a
         new configuration table in the
        module Flash memory. <Condtype>
        CONF_TABLE_SAVE <Probcause> informationalStatus(1000)
        <Alarmtype> other (1) <Polarity>
        (2)
        "
	  ::= { pm20020maAlmsynthAlm2 1 }



--- *********************************************************
---     TABLE for the pm20020maAlmsynthAlmPort articles
--- *********************************************************

pm20020maAlmsynthAlmPortTable OBJECT-TYPE
	SYNTAX  SEQUENCE OF Pm20020maAlmsynthAlmPortEntry
	MAX-ACCESS not-accessible
	STATUS current
	DESCRIPTION
        "
        List of pm20020maAlmsynthAlmPort
        Article
        "
	::= { pm20020maAlmClientCrit 8 }


pm20020maAlmsynthAlmPortEntry OBJECT-TYPE
	SYNTAX Pm20020maAlmsynthAlmPortEntry
	MAX-ACCESS not-accessible
	STATUS current
	DESCRIPTION
        "
        Row definition for the pm20020maAlmsynthAlmPort
        table
        "
	INDEX   { pm20020maAlmsynthAlmPortIndex }
	::= { pm20020maAlmsynthAlmPortTable 1 }


Pm20020maAlmsynthAlmPortEntry ::=
	SEQUENCE {
	pm20020maAlmsynthAlmPortIndex
		INTEGER,
	pm20020maAlmUpCsfPortn
		EkiOnOff,
	pm20020maAlmFailAccPortn
		EkiOnOff,
	pm20020maAlmSfpDdmAlmPortn
		EkiOnOff,
	pm20020maAlmSfpDdmWarningPortn
		EkiOnOff,
	pm20020maAlmDwCaisPortn
		EkiOnOff,
	pm20020maAlmClientRemoteOosPortn
		EkiOnOff,
	pm20020maAlmClientLocalOosPortn
		EkiOnOff,
	pm20020maAlmDwLsdPortn
		EkiOnOff,
	pm20020maAlmHwFailAccPortn
		EkiOnOff,
	pm20020maAlmDdmAbsentPortn
		EkiOnOff,
	pm20020maAlmSfpAbsentPortn
		EkiOnOff
	}


pm20020maAlmsynthAlmPortIndex OBJECT-TYPE
	SYNTAX  INTEGER(0..128)
	MAX-ACCESS  read-only
	STATUS current
	DESCRIPTION
        "
        Index definition for the pm20020maAlmsynthAlmPort
        table
        "
	::= { pm20020maAlmsynthAlmPortEntry 1 }


pm20020maAlmUpCsfPortn OBJECT-TYPE
	SYNTAX  EkiOnOff
	MAX-ACCESS read-only
	STATUS current
	DESCRIPTION
        "
        Client Signal Fail Inserted :This
        OID indicates a CSF has been inserted
        in the upstream client port. <Help>
        This status indicates if a Client
        Signal Fail is currently inserted
        on the line signal for this client
        port <Condtype> UP_CSF_1 <Probcause>
        informationalStatus(1000) <Alarmtype>
        other (1) <Polarity> (2)
        "
	::= { pm20020maAlmsynthAlmPortEntry 17 }


pm20020maAlmFailAccPortn OBJECT-TYPE
	SYNTAX  EkiOnOff
	MAX-ACCESS read-only
	STATUS current
	DESCRIPTION
        "
        Client Access Fail :This OID indicates
        a failure on the Client port <Help>
        This alarm indicates a failure
         on the Client port <Condtype>
         FAIL_ACC_1 <Probcause> equipmentMalfunction
        (16) <Alarmtype> synthesisAlarm
        (12)  <Polarity> (2)
        "
	::= { pm20020maAlmsynthAlmPortEntry 13 }


pm20020maAlmSfpDdmAlmPortn OBJECT-TYPE
	SYNTAX  EkiOnOff
	MAX-ACCESS read-only
	STATUS current
	DESCRIPTION
        "
        Alarm On Client Trscv DDM :This
        OID indicates an alarm is being
        received from the Client Transceiver
        DDM <Help> This alarm indicates
        if a DDM Alarm has been detected
        on the client transceiver <Condtype>
        SFP_DDM_ALM_1 <Probcause> inputOutputDeviceError
        (24) <Alarmtype> synthesisAlarm
        (12)  <Polarity> (2)
        "
	::= { pm20020maAlmsynthAlmPortEntry 11 }


pm20020maAlmSfpDdmWarningPortn OBJECT-TYPE
	SYNTAX  EkiOnOff
	MAX-ACCESS read-only
	STATUS current
	DESCRIPTION
        "
        Warning On Client Trscv DDM :This
        OID indicates a warning is being
        received from the Client Transceiver
        DDM <Help> This alarm indicates
        if a DDM Warning has been detected
        on the client transceiver <Condtype>
        SFP_DDM_WARNING_1 <Probcause> inputOutputDeviceError
        (24) <Alarmtype> synthesisAlarm
        (12)  <Polarity> (2)
        "
	::= { pm20020maAlmsynthAlmPortEntry 10 }


pm20020maAlmDwCaisPortn OBJECT-TYPE
	SYNTAX  EkiOnOff
	MAX-ACCESS read-only
	STATUS current
	DESCRIPTION
        "
        Client AIS Inserted :This OID
         indicates a CAIS has been inserted
        on the output client port. <Help>
        This status indicates if a Client
        Alarm Indication Signal is currently
        inserted on the client interface
        <Condtype> DW_CAIS_1 <Probcause>
        informationalStatus(1000) <Alarmtype>
        other (1) <Polarity> (2)
        "
	::= { pm20020maAlmsynthAlmPortEntry 9 }


pm20020maAlmClientRemoteOosPortn OBJECT-TYPE
	SYNTAX  EkiOnOff
	MAX-ACCESS read-only
	STATUS current
	DESCRIPTION
        "
        Remote Client Port In Service
         :This OID indicates that the remote
        Client port is In Service (1) or
        Out of Service (2) <Help> This
         status indicates if the remote
        client port is in service <Condtype>
        CLIENT_REMOTE_OOS <Probcause> informationalStatus(1000)
        <Alarmtype> other (1) <Polarity>
        (2)
        "
	::= { pm20020maAlmsynthAlmPortEntry 8 }


pm20020maAlmClientLocalOosPortn OBJECT-TYPE
	SYNTAX  EkiOnOff
	MAX-ACCESS read-only
	STATUS current
	DESCRIPTION
        "
        Local Client Port In Service :This
        OID indicates that the local Client
        port is In Service (1) or Out of
        Service (2) <Help> This status
         indicates if the local client
         port is in service <Condtype>
         CLIENT_LOCAL_OOS <Probcause> informationalStatus(1000)
        <Alarmtype> other (1) <Polarity>
        (2)
        "
	::= { pm20020maAlmsynthAlmPortEntry 7 }


pm20020maAlmDwLsdPortn OBJECT-TYPE
	SYNTAX  EkiOnOff
	MAX-ACCESS read-only
	STATUS current
	DESCRIPTION
        "
        Client Trscv Laser Shutdown :This
        OID indicates the Client transceiver
        laser is shutdown <Help> This status
        indicates if the client transceiver
        laser is shutdown <Condtype> DW_LSD_1
        <Probcause> other (1) <Alarmtype>
        equipmentAlarm (5) <Polarity> (2)
        "
	::= { pm20020maAlmsynthAlmPortEntry 6 }


pm20020maAlmHwFailAccPortn OBJECT-TYPE
	SYNTAX  EkiOnOff
	MAX-ACCESS read-only
	STATUS current
	DESCRIPTION
        "
        Client HW Fail :This OID indicates
        a failure on client port, most
         probably caused by a HW issue.
        <Help> This alarm indicates a failure
        on client port, most probably caused
        by a HW issue. <Condtype> HW_FAIL_ACC_1
        <Probcause> equipmentMalfunction
        (16) <Alarmtype> synthesisAlarm
        (12)  <Polarity> (2)
        "
	::= { pm20020maAlmsynthAlmPortEntry 5 }


pm20020maAlmDdmAbsentPortn OBJECT-TYPE
	SYNTAX  EkiOnOff
	MAX-ACCESS read-only
	STATUS current
	DESCRIPTION
        "
        DDM Supported On Client Trscv
         :This OID indicates that the Client
        transceiver supports the Digital
        Diagnostic Monitoring function
         <Help> This status indicates if
        the client transceiver includes
        the DDM feature <Condtype> DDM_ABSENT_1
        <Probcause> informationalStatus(1000)
        <Alarmtype> other (1) <Polarity>
        (2)
        "
	::= { pm20020maAlmsynthAlmPortEntry 3 }


pm20020maAlmSfpAbsentPortn OBJECT-TYPE
	SYNTAX  EkiOnOff
	MAX-ACCESS read-only
	STATUS current
	DESCRIPTION
        "
        Client Optical Module Absent :This
        OID indicates that the Transceiver
        is not present in the client port.
        <Help> This alarm indicates if
         the client transceiver is not
         plugged <Condtype> SFP_ABSENT_1
        <Probcause> inputOutputDeviceError
        (24) <Alarmtype> equipmentAlarm
        (5) <Polarity> (2) <Event> ObjectCDSingleClientInv
        "
	::= { pm20020maAlmsynthAlmPortEntry 2 }


--- *********************************************************
---     TABLE for the pm20020maAlmsynthAlmLine articles
--- *********************************************************

pm20020maAlmsynthAlmLineTable OBJECT-TYPE
	SYNTAX  SEQUENCE OF Pm20020maAlmsynthAlmLineEntry
	MAX-ACCESS not-accessible
	STATUS current
	DESCRIPTION
        "
        List of pm20020maAlmsynthAlmLine
        Article
        "
	::= { pm20020maAlmLineCrit 40 }


pm20020maAlmsynthAlmLineEntry OBJECT-TYPE
	SYNTAX Pm20020maAlmsynthAlmLineEntry
	MAX-ACCESS not-accessible
	STATUS current
	DESCRIPTION
        "
        Row definition for the pm20020maAlmsynthAlmLine
        table
        "
	INDEX   { pm20020maAlmsynthAlmLineIndex }
	::= { pm20020maAlmsynthAlmLineTable 1 }


Pm20020maAlmsynthAlmLineEntry ::=
	SEQUENCE {
	pm20020maAlmsynthAlmLineIndex
		INTEGER,
	pm20020maAlmLineActivePortn
		EkiOnOff,
	pm20020maAlmLineFailPortn
		EkiOnOff,
	pm20020maAlmLineDdmAlmPortn
		EkiOnOff,
	pm20020maAlmLineDdmWarningPortn
		EkiOnOff,
	pm20020maAlmUpRdiInsPortn
		EkiOnOff,
	pm20020maAlmLineLocalOosPortn
		EkiOnOff,
	pm20020maAlmXfpTxOffPortn
		EkiOnOff,
	pm20020maAlmLineHwFailPortn
		EkiOnOff,
	pm20020maAlmXfpInitNotComplPortn
		EkiOnOff,
	pm20020maAlmXfpAbsentPortn
		EkiOnOff
	}


pm20020maAlmsynthAlmLineIndex OBJECT-TYPE
	SYNTAX  INTEGER(0..128)
	MAX-ACCESS  read-only
	STATUS current
	DESCRIPTION
        "
        Index definition for the pm20020maAlmsynthAlmLine
        table
        "
	::= { pm20020maAlmsynthAlmLineEntry 1 }


pm20020maAlmLineActivePortn OBJECT-TYPE
	SYNTAX  EkiOnOff
	MAX-ACCESS read-only
	STATUS current
	DESCRIPTION
        "
        Line Active :This OID indicates
        whether the line is active or standby.
        <Help> This status indicates whether
        the line is active or standby.
         <Condtype> LINE_ACTIVE <Probcause>
        informationalStatus(1000) <Alarmtype>
        other (1) <Polarity> (2)
        "
	::= { pm20020maAlmsynthAlmLineEntry 17 }


pm20020maAlmLineFailPortn OBJECT-TYPE
	SYNTAX  EkiOnOff
	MAX-ACCESS read-only
	STATUS current
	DESCRIPTION
        "
        Line Port Failure :This OID indicates
        a failure on the line port <Help>
        This alarm indicates a failure
         on the line port <Condtype> LINE_FAIL
        <Probcause> equipmentMalfunction
        (16) <Alarmtype> synthesisAlarm
        (12)  <Polarity> (2)
        "
	::= { pm20020maAlmsynthAlmLineEntry 13 }


pm20020maAlmLineDdmAlmPortn OBJECT-TYPE
	SYNTAX  EkiOnOff
	MAX-ACCESS read-only
	STATUS current
	DESCRIPTION
        "
        Alarm On Line Optical Module DDM
        :This OID indicates an alarm is
        present coming out of Line transceiver
        DDM <Help> This alarm indicates
        if a DDM Alarm has been detected
        on the line transceiver <Condtype>
        LINE_DDM_ALM <Probcause> inputOutputDeviceError
        (24) <Alarmtype> synthesisAlarm
        (12)  <Polarity> (2)
        "
	::= { pm20020maAlmsynthAlmLineEntry 11 }


pm20020maAlmLineDdmWarningPortn OBJECT-TYPE
	SYNTAX  EkiOnOff
	MAX-ACCESS read-only
	STATUS current
	DESCRIPTION
        "
        Warning On Line Optical Module
        DDM :This OID indicates a warning
        is present coming out of Line transceiver
        DDM <Help> This alarm indicates
        if a DDM Warning has been detected
        on the line transceiver <Condtype>
        LINE_DDM_WARNING <Probcause> inputOutputDeviceError
        (24) <Alarmtype> synthesisAlarm
        (12)  <Polarity> (2)
        "
	::= { pm20020maAlmsynthAlmLineEntry 10 }


pm20020maAlmUpRdiInsPortn OBJECT-TYPE
	SYNTAX  EkiOnOff
	MAX-ACCESS read-only
	STATUS current
	DESCRIPTION
        "
        MS-RDI/L-RDI Inserted On Line
         :This OID indicates an upstream
        MS-RDI/L-RDI has been inserted
         in the outgoing 10 Gb/s SDH/SONET
        signal. <Help> This status indicates
        if a MS-RDI/L-RDI is currently
         inserted on the line interface.
        <Condtype> UP_RDI_INS <Probcause>
        informationalStatus(1000) <Alarmtype>
        other (1) <Polarity> (2)
        "
	::= { pm20020maAlmsynthAlmLineEntry 9 }


pm20020maAlmLineLocalOosPortn OBJECT-TYPE
	SYNTAX  EkiOnOff
	MAX-ACCESS read-only
	STATUS current
	DESCRIPTION
        "
        Line Port In Service :This OID
        indicates that the Line port is
        In Service (1) of Out or Service
        (2) <Help> This status indicates
        if the line port is in service
         <Condtype> LINE_LOCAL_OOS <Probcause>
        informationalStatus(1000) <Alarmtype>
        other (1) <Polarity> (2)
        "
	::= { pm20020maAlmsynthAlmLineEntry 7 }


pm20020maAlmXfpTxOffPortn OBJECT-TYPE
	SYNTAX  EkiOnOff
	MAX-ACCESS read-only
	STATUS current
	DESCRIPTION
        "
        Line Trscv Laser Shutdown :This
        OID indicates the Line transceiver
        laser is shutdown <Help> This status
        indicates if the Line transceiver
        laser is shutdown <Condtype> XFP_TX_OFF
        <Probcause> other (1) <Alarmtype>
        equipmentAlarm (5) <Polarity> (2)
        "
	::= { pm20020maAlmsynthAlmLineEntry 6 }


pm20020maAlmLineHwFailPortn OBJECT-TYPE
	SYNTAX  EkiOnOff
	MAX-ACCESS read-only
	STATUS current
	DESCRIPTION
        "
        Line Port HW Failure :This OID
        indicates a failure on line port,
        most probably caused by a HW issue
        <Help> This alarm indicates a failure
        on line port, most probably caused
        by a HW issue <Condtype> LINE_HW_FAIL
        <Probcause> equipmentMalfunction
        (16) <Alarmtype> synthesisAlarm
        (12)  <Polarity> (2)
        "
	::= { pm20020maAlmsynthAlmLineEntry 5 }


pm20020maAlmXfpInitNotComplPortn OBJECT-TYPE
	SYNTAX  EkiOnOff
	MAX-ACCESS read-only
	STATUS current
	DESCRIPTION
        "
        Line Optical Module Ready :This
        OID indicates that the optical
         interface is not operational.
         <Help> This status indicates if
        the line transceiver has been correctly
        initialized <Condtype> XFP_INIT_NOT_COMPL
        <Probcause> equipmentMalfunction
        (16) <Alarmtype> equipmentAlarm
        (5) <Polarity> (2)
        "
	::= { pm20020maAlmsynthAlmLineEntry 3 }


pm20020maAlmXfpAbsentPortn OBJECT-TYPE
	SYNTAX  EkiOnOff
	MAX-ACCESS read-only
	STATUS current
	DESCRIPTION
        "
        Line Optical Module Absent :This
        OID indicates that the line optical
        interface is not present. <Help>
        This alarm indicates if the line
        transceiver is not plugged <Condtype>
        XFP_ABSENT <Probcause> inputOutputDeviceError
        (24) <Alarmtype> equipmentAlarm
        (5) <Polarity> (2)
        "
	::= { pm20020maAlmsynthAlmLineEntry 2 }


--- *****************************************************
---     LEAF for the clientModuleState article
--- *****************************************************
pm20020maAlmclientModuleState OBJECT IDENTIFIER ::= { pm20020maAlmOtherCrit 72 }




pm20020maAlmCfpHighPowerDown OBJECT-TYPE
	  SYNTAX EkiOnOff
	  MAX-ACCESS read-only
	  STATUS current
	  DESCRIPTION
        "
        Client Trscv High Power Down :This
        OID indicates the Client Trscv
         is entering Low Power state <Help>
        Status indicating the Client Trscv
        is entering Low Power state <Condtype>
        CFP_HIGH_POWER_DOWN <Probcause>
        informationalStatus(1000) <Alarmtype>
        other (1) <Polarity> (2)
        "
	  ::= { pm20020maAlmclientModuleState 9 }



pm20020maAlmCfpTxTurnOff OBJECT-TYPE
	  SYNTAX EkiOnOff
	  MAX-ACCESS read-only
	  STATUS current
	  DESCRIPTION
        "
        Client Trscv Laser Turn Off :This
        OID indicates the Client Trscv
         is turning off its laser <Help>
        Status indicating the Client Trscv
        is turning off its laser <Condtype>
        CFP_TX_TURN_OFF <Probcause> informationalStatus(1000)
        <Alarmtype> other (1) <Polarity>
        (2)
        "
	  ::= { pm20020maAlmclientModuleState 8 }



pm20020maAlmCfpFault OBJECT-TYPE
	  SYNTAX EkiOnOff
	  MAX-ACCESS read-only
	  STATUS current
	  DESCRIPTION
        "
        Client Trscv Fault :This OID indicates
        the Client Trscv is in Fault state
        <Help> Status indicating the Client
        Trscv is in Fault state <Condtype>
        CFP_FAULT <Probcause> informationalStatus(1000)
        <Alarmtype> other (1) <Polarity>
        (2)
        "
	  ::= { pm20020maAlmclientModuleState 7 }



pm20020maAlmCfpReady OBJECT-TYPE
	  SYNTAX EkiOnOff
	  MAX-ACCESS read-only
	  STATUS current
	  DESCRIPTION
        "
        Client Trscv Ready :This OID indicates
        the Client Trscv is ready to operate
        <Help> Status indicating the Client
        Trscv is ready to operate <Condtype>
        CFP_READY <Probcause> informationalStatus(1000)
        <Alarmtype> other (1) <Polarity>
        (2)
        "
	  ::= { pm20020maAlmclientModuleState 6 }



pm20020maAlmCfpTxTurnOn OBJECT-TYPE
	  SYNTAX EkiOnOff
	  MAX-ACCESS read-only
	  STATUS current
	  DESCRIPTION
        "
        Client Trscv Laser Turn On :This
        OID indicates the Client Trscv
         is turning on its laser <Help>
        Status indicating the Client Trscv
        is turning on its laser <Condtype>
        CFP_TX_TURN_ON <Probcause> informationalStatus(1000)
        <Alarmtype> other (1) <Polarity>
        (2)
        "
	  ::= { pm20020maAlmclientModuleState 5 }



pm20020maAlmCfpTxOff OBJECT-TYPE
	  SYNTAX EkiOnOff
	  MAX-ACCESS read-only
	  STATUS current
	  DESCRIPTION
        "
        Client Trscv Laser Shutdown :This
        OID indicates the Client Trscv
         Laser is OFF <Help> Status indicating
        the Client Trscv Laser is OFF <Condtype>
        CFP_TX_OFF <Probcause> informationalStatus(1000)
        <Alarmtype> other (1) <Polarity>
        (2)
        "
	  ::= { pm20020maAlmclientModuleState 4 }



pm20020maAlmCfpHighPowerUp OBJECT-TYPE
	  SYNTAX EkiOnOff
	  MAX-ACCESS read-only
	  STATUS current
	  DESCRIPTION
        "
        Client Trscv High Power Up :This
        OID indicates the Client Trscv
         is leaving Low Power state <Help>
        Status indicating the Client Trscv
        is leaving Low Power state <Condtype>
        CFP_HIGH_POWER_UP <Probcause> informationalStatus(1000)
        <Alarmtype> other (1) <Polarity>
        (2)
        "
	  ::= { pm20020maAlmclientModuleState 3 }



pm20020maAlmCfpLowPower OBJECT-TYPE
	  SYNTAX EkiOnOff
	  MAX-ACCESS read-only
	  STATUS current
	  DESCRIPTION
        "
        Client Trscv Low Power :This OID
        indicates the Client Trscv is in
        low power state <Help> Status indicating
        the Client Trscv is in low power
        state <Condtype> CFP_LOW_POWER
         <Probcause> informationalStatus(1000)
        <Alarmtype> other (1) <Polarity>
        (2)
        "
	  ::= { pm20020maAlmclientModuleState 2 }



pm20020maAlmCfpInitialize OBJECT-TYPE
	  SYNTAX EkiOnOff
	  MAX-ACCESS read-only
	  STATUS current
	  DESCRIPTION
        "
        Client Trscv Initialize :This
         OID indicates the Client Trscv
        initialization is in progress <Help>
        Status indicating the Client Trscv
        initialization is in progress <Condtype>
        CFP_INITIALIZE <Probcause> informationalStatus(1000)
        <Alarmtype> other (1) <Polarity>
        (2)
        "
	  ::= { pm20020maAlmclientModuleState 1 }



--- *****************************************************
---     LEAF for the clientModuleGeneralStatus article
--- *****************************************************
pm20020maAlmclientModuleGeneralStatus OBJECT IDENTIFIER ::= { pm20020maAlmOtherCrit 73 }




pm20020maAlmCfpHwInterlock OBJECT-TYPE
	  SYNTAX EkiOnOff
	  MAX-ACCESS read-only
	  STATUS current
	  DESCRIPTION
        "
        Client Trscv Hardware Interlock
        :This OID indicates the Client
         Trscv power is higher than the
        cooling capacity <Help> Alarm indicating
        the Client Trscv power is higher
        than the cooling capacity <Condtype>
        CFP_HW_INTERLOCK <Probcause> temperatureUnacceptable
        (51) <Alarmtype> equipmentAlarm
        (5) <Polarity> (2)
        "
	  ::= { pm20020maAlmclientModuleGeneralStatus 14 }



pm20020maAlmCfpLossOfRefclk OBJECT-TYPE
	  SYNTAX EkiOnOff
	  MAX-ACCESS read-only
	  STATUS current
	  DESCRIPTION
        "
        Client Trscv Loss Of Ref Clock
        :This OID indicates a Loss of Reference
        clock is detected on the Client
        Trscv <Help> Alarm indicating a
        Loss of Reference clock is detected
        on the Client Trscv <Condtype>
         CFP_LOSS_OF_REFCLK <Probcause>
        inputOutputDeviceError (24) <Alarmtype>
        equipmentAlarm (5) <Polarity> (2)
        "
	  ::= { pm20020maAlmclientModuleGeneralStatus 11 }



pm20020maAlmCfpTxJitterPllLol OBJECT-TYPE
	  SYNTAX EkiOnOff
	  MAX-ACCESS read-only
	  STATUS current
	  DESCRIPTION
        "
        Client Trscv Tx Jitter PLL Loss
        Of Lock :This OID indicates a Tx
        Jitter PLL Loss of Lock is dtected
        on the Client Trscv <Help> Alarm
        indicating a Tx Jitter PLL Loss
        of Lock is dtected on the Client
        Trscv <Condtype> CFP_TX_JITTER_PLL_LOL
        <Probcause> inputOutputDeviceError
        (24) <Alarmtype> equipmentAlarm
        (5) <Polarity> (2)
        "
	  ::= { pm20020maAlmclientModuleGeneralStatus 10 }



pm20020maAlmCfpTxCmuLol OBJECT-TYPE
	  SYNTAX EkiOnOff
	  MAX-ACCESS read-only
	  STATUS current
	  DESCRIPTION
        "
        Client Trscv CMU Loss Of Lock
         :This OID indicates a Clock Multiplier
        Unit Loss of Lock is detected on
        the Client Trscv <Help> Alarm indicating
        a Clock Multiplier Unit Loss of
        Lock is detected on the Client
         Trscv <Condtype> CFP_TX_CMU_LOL
        <Probcause> inputOutputDeviceError
        (24) <Alarmtype> equipmentAlarm
        (5) <Polarity> (2)
        "
	  ::= { pm20020maAlmclientModuleGeneralStatus 9 }



pm20020maAlmCfpTxLosf OBJECT-TYPE
	  SYNTAX EkiOnOff
	  MAX-ACCESS read-only
	  STATUS current
	  DESCRIPTION
        "
        Client Trscv Loss Of Signal Functionality
        :This OID indicates a Loss of Signal
        functionality is detected on the
        Client Trscv <Help> Alarm indicating
        a Loss of Signal functionality
         is detected on the Client Trscv
        <Condtype> CFP_TX_LOSF <Probcause>
        lossOfSignal (30) <Alarmtype> equipmentAlarm
        (5) <Polarity> (2)
        "
	  ::= { pm20020maAlmclientModuleGeneralStatus 8 }



pm20020maAlmCfpTxHostLol OBJECT-TYPE
	  SYNTAX EkiOnOff
	  MAX-ACCESS read-only
	  STATUS current
	  DESCRIPTION
        "
        Client Trscv Tx Host Loss Of Lock
        :This OID indicates of Loss of
         Lock is detected on the Client
        Trscv Tx Host interface <Help>
         Alarm indicating of Loss of Lock
        is detected on the Client Trscv
        Tx Host interface <Condtype> CFP_TX_HOST_LOL
        <Probcause> receiverFailure (42)
        <Alarmtype> equipmentAlarm (5)
         <Polarity> (2)
        "
	  ::= { pm20020maAlmclientModuleGeneralStatus 7 }



pm20020maAlmCfpRxLos OBJECT-TYPE
	  SYNTAX EkiOnOff
	  MAX-ACCESS read-only
	  STATUS current
	  DESCRIPTION
        "
        Client Trscv Loss Of Signal :This
        OID indicates a Loss of Signal
         is detected on the Client Trscv
        <Help> Alarm indicating a Loss
         of Signal is detected on the Client
        Trscv <Condtype> CFP_RX_LOS <Probcause>
        lossOfSignal (30) <Alarmtype> equipmentAlarm
        (5) <Polarity> (2)
        "
	  ::= { pm20020maAlmclientModuleGeneralStatus 6 }



pm20020maAlmCfpRxNetworkLol OBJECT-TYPE
	  SYNTAX EkiOnOff
	  MAX-ACCESS read-only
	  STATUS current
	  DESCRIPTION
        "
        Client Trscv Rx Network Loss Of
        Lock :This OID indicates of Loss
        of Lock is dected on the Client
        Trscv Rx Network interface <Help>
        Alarm indicating of Loss of Lock
        is dected on the Client Trscv Rx
        Network interface <Condtype> CFP_RX_NETWORK_LOL
        <Probcause> receiverFailure (42)
        <Alarmtype> equipmentAlarm (5)
         <Polarity> (2)
        "
	  ::= { pm20020maAlmclientModuleGeneralStatus 5 }



pm20020maAlmCfpOutOfAlignment OBJECT-TYPE
	  SYNTAX EkiOnOff
	  MAX-ACCESS read-only
	  STATUS current
	  DESCRIPTION
        "
        Client Trscv Out Of Alignment
         :This OID indicates an Out of
         alignment on the Client Trscv
         Host Interface <Help> Alarm indicating
        an Out of alignment on the Client
        Trscv Host Interface <Condtype>
        CFP_OUT_OF_ALIGNMENT <Probcause>
        receiverFailure (42) <Alarmtype>
        equipmentAlarm (5) <Polarity> (2)
        "
	  ::= { pm20020maAlmclientModuleGeneralStatus 4 }



--- *****************************************************
---     LEAF for the clientGlobalAlarmSummary article
--- *****************************************************
pm20020maAlmclientGlobalAlarmSummary OBJECT IDENTIFIER ::= { pm20020maAlmOtherCrit 74 }




pm20020maAlmCfpGlobAlarmAssertion  OBJECT-TYPE
	  SYNTAX EkiOnOff
	  MAX-ACCESS read-only
	  STATUS current
	  DESCRIPTION
        "
        Client Trscv Global Alarm :This
        OID indicates at least one  Fault
        or Status is detected on the Client
        Trscv module <Help> Synthesis alarm
        indicating at least one Alarm,
         Warning, Fault or Status is detected
        on the Client Trscv module <Condtype>
        CFP_GLOB_ALARM_ASSERTION  <Probcause>
        informationalStatus(1000) <Alarmtype>
        other (1) <Polarity> (2)
        "
	  ::= { pm20020maAlmclientGlobalAlarmSummary 16 }



pm20020maAlmCfpHostLaneFaultStatus  OBJECT-TYPE
	  SYNTAX EkiOnOff
	  MAX-ACCESS read-only
	  STATUS current
	  DESCRIPTION
        "
        Client Trscv Host Fault And Status
        :This OID indicates at least one
        Fault or Status is detected on
         the Client Trscv Host Interface
        <Help> Synthesis alarm indicating
        at least one Fault or Status is
        detected on the Client Trscv Host
        Interface <Condtype> CFP_HOST_LANE_FAULT_STATUS
         <Probcause> informationalStatus(1000)
        <Alarmtype> other (1) <Polarity>
        (2)
        "
	  ::= { pm20020maAlmclientGlobalAlarmSummary 15 }



pm20020maAlmCfpNetworkLaneFaultStatus  OBJECT-TYPE
	  SYNTAX EkiOnOff
	  MAX-ACCESS read-only
	  STATUS current
	  DESCRIPTION
        "
        Client Trscv Network Fault And
        Status :This OID indicates at least
        one Fault or Status is detected
        on the Client Trscv Network Interface
        <Help> Synthesis alarm indicating
        at least one Fault or Status is
        detected on the Client Trscv Network
        Interface <Condtype> CFP_NETWORK_LANE_FAULT_STATUS
         <Probcause> informationalStatus(1000)
        <Alarmtype> other (1) <Polarity>
        (2)
        "
	  ::= { pm20020maAlmclientGlobalAlarmSummary 14 }



pm20020maAlmCfpNetworkLaneAlarmWarning1 OBJECT-TYPE
	  SYNTAX EkiOnOff
	  MAX-ACCESS read-only
	  STATUS current
	  DESCRIPTION
        "
        Client Trscv Network Alarm And
        Warning 1 :This OID indicates at
        least one DDM  is detected on the
        Client Trscv Network Interface
         <Help> Synthesis alarm indicating
        at least one DDM Alarm or DDM Warning
        is detected on the Client Trscv
        Network Interface <Condtype> CFP_NETWORK_LANE_ALARM_WARNING_1
        <Probcause> informationalStatus(1000)
        <Alarmtype> other (1) <Polarity>
        (2)
        "
	  ::= { pm20020maAlmclientGlobalAlarmSummary 13 }



pm20020maAlmCfpModuleAlarmWarning2 OBJECT-TYPE
	  SYNTAX EkiOnOff
	  MAX-ACCESS read-only
	  STATUS current
	  DESCRIPTION
        "
        Client Trscv Module Alarm And
         Warning 2 :This OID indicates
         at least one DDM is detected on
        the Client Trscv module <Help>
         Synthesis alarm indicating at
         least one DDM Alarm or DDM Warning
        is detected on the Client Trscv
        module <Condtype> CFP_MODULE_ALARM_WARNING_2
        <Probcause> informationalStatus(1000)
        <Alarmtype> other (1) <Polarity>
        (2)
        "
	  ::= { pm20020maAlmclientGlobalAlarmSummary 12 }



pm20020maAlmCfpModuleAlarmWarning1  OBJECT-TYPE
	  SYNTAX EkiOnOff
	  MAX-ACCESS read-only
	  STATUS current
	  DESCRIPTION
        "
        Client Trscv Module Alarm And
         Warning 1 :This OID indicates
         at least one DDM  This OID is
         detected on the Client Trscv module
        <Help> Synthesis alarm indicating
        at least one DDM Alarm or DDM Warning
        is detected on the Client Trscv
        module <Condtype> CFP_MODULE_ALARM_WARNING_1
         <Probcause> informationalStatus(1000)
        <Alarmtype> other (1) <Polarity>
        (2)
        "
	  ::= { pm20020maAlmclientGlobalAlarmSummary 11 }



pm20020maAlmCfpModuleFault  OBJECT-TYPE
	  SYNTAX EkiOnOff
	  MAX-ACCESS read-only
	  STATUS current
	  DESCRIPTION
        "
        Client Trscv Module Fault :This
        OID indicates at least one Fault
        is detected on the Client Trscv
        module <Help> Synthesis alarm indicating
        at least one Fault is detected
         on the Client Trscv module <Condtype>
        CFP_MODULE_FAULT  <Probcause> informationalStatus(1000)
        <Alarmtype> other (1) <Polarity>
        (2)
        "
	  ::= { pm20020maAlmclientGlobalAlarmSummary 10 }



pm20020maAlmCfpModuleGeneralStatus  OBJECT-TYPE
	  SYNTAX EkiOnOff
	  MAX-ACCESS read-only
	  STATUS current
	  DESCRIPTION
        "
        Client Trscv General Status :This
        OID indicates the Client Trscv
         module general status <Help> Synthesis
        alarm indicating the Client Trscv
        module general status <Condtype>
        CFP_MODULE_GENERAL_STATUS  <Probcause>
        informationalStatus(1000) <Alarmtype>
        other (1) <Polarity> (2)
        "
	  ::= { pm20020maAlmclientGlobalAlarmSummary 9 }



pm20020maAlmCfpModuleState  OBJECT-TYPE
	  SYNTAX EkiOnOff
	  MAX-ACCESS read-only
	  STATUS current
	  DESCRIPTION
        "
        Client Trscv Module State :This
        OID indicates the Client Trscv
         module state <Help> Synthesis
         alarm indicating the Client Trscv
        module state <Condtype> CFP_MODULE_STATE
         <Probcause> informationalStatus(1000)
        <Alarmtype> other (1) <Polarity>
        (2)
        "
	  ::= { pm20020maAlmclientGlobalAlarmSummary 8 }



pm20020maAlmCfpNetworkLaneAlarmWarning2 OBJECT-TYPE
	  SYNTAX EkiOnOff
	  MAX-ACCESS read-only
	  STATUS current
	  DESCRIPTION
        "
        Client Trscv Network Alarm And
        Warning 2 :This OID indicates at
        least one DDM is detected on the
        Client Trscv Network Interface
         <Help> Synthesis alarm indicating
        at least one DDM Alarm or DDM Warning
        is detected on the Client Trscv
        Network Interface <Condtype> CFP_NETWORK_LANE_ALARM_WARNING_2
        <Probcause> informationalStatus(1000)
        <Alarmtype> other (1) <Polarity>
        (2)
        "
	  ::= { pm20020maAlmclientGlobalAlarmSummary 7 }



pm20020maAlmCfpSoftGlobAlarmTest  OBJECT-TYPE
	  SYNTAX EkiOnOff
	  MAX-ACCESS read-only
	  STATUS current
	  DESCRIPTION
        "
        Client Trscv Global Alarm SW Test
        :This OID indicates the Client
         Trscv Global Alarm This OID is
        raised by SW request for test purpose
        <Help> Status indicating the Client
        Trscv Global Alarm is raised by
        SW request for test purpose <Condtype>
        CFP_SOFT_GLOB_ALARM_TEST  <Probcause>
        informationalStatus(1000) <Alarmtype>
        other (1) <Polarity> (2)
        "
	  ::= { pm20020maAlmclientGlobalAlarmSummary 1 }



--- *****************************************************
---     LEAF for the msaModuleState article
--- *****************************************************
pm20020maAlmmsaModuleState OBJECT IDENTIFIER ::= { pm20020maAlmOtherCrit 78 }




pm20020maAlmMsaHighPowerDown OBJECT-TYPE
	  SYNTAX EkiOnOff
	  MAX-ACCESS read-only
	  STATUS current
	  DESCRIPTION
        "
        Line Trscv High Power Down :This
        OID indicates the Line Trscv is
        entering Low Power state <Help>
        Status indicating the Line Trscv
        is entering Low Power state <Condtype>
        MSA_HIGH_POWER_DOWN <Probcause>
        informationalStatus(1000) <Alarmtype>
        other (1) <Polarity> (2)
        "
	  ::= { pm20020maAlmmsaModuleState 9 }



pm20020maAlmMsaTxTurnOff OBJECT-TYPE
	  SYNTAX EkiOnOff
	  MAX-ACCESS read-only
	  STATUS current
	  DESCRIPTION
        "
        Line Trscv Laser Turn Off :This
        OID indicates the Line Trscv is
        turning off its laser <Help> Status
        indicating the Line Trscv is turning
        off its laser <Condtype> MSA_TX_TURN_OFF
        <Probcause> informationalStatus(1000)
        <Alarmtype> other (1) <Polarity>
        (2)
        "
	  ::= { pm20020maAlmmsaModuleState 8 }



pm20020maAlmMsaFault OBJECT-TYPE
	  SYNTAX EkiOnOff
	  MAX-ACCESS read-only
	  STATUS current
	  DESCRIPTION
        "
        Line Trscv Fault :This OID indicates
        the Line Trscv is in Fault state
        <Help> Status indicating the Line
        Trscv is in Fault state <Condtype>
        MSA_FAULT <Probcause> informationalStatus(1000)
        <Alarmtype> other (1) <Polarity>
        (2)
        "
	  ::= { pm20020maAlmmsaModuleState 7 }



pm20020maAlmMsaReady OBJECT-TYPE
	  SYNTAX EkiOnOff
	  MAX-ACCESS read-only
	  STATUS current
	  DESCRIPTION
        "
        Line Trscv Ready :This OID indicates
        the Line Trscv is ready to operate
        <Help> Status indicating the Line
        Trscv is ready to operate <Condtype>
        MSA_READY <Probcause> informationalStatus(1000)
        <Alarmtype> other (1) <Polarity>
        (2)
        "
	  ::= { pm20020maAlmmsaModuleState 6 }



pm20020maAlmMsaTxTurnOn OBJECT-TYPE
	  SYNTAX EkiOnOff
	  MAX-ACCESS read-only
	  STATUS current
	  DESCRIPTION
        "
        Line Trscv Laser Turn On :This
        OID indicates the Line Trscv is
        turning on its laser <Help> Status
        indicating the Line Trscv is turning
        on its laser <Condtype> MSA_TX_TURN_ON
        <Probcause> informationalStatus(1000)
        <Alarmtype> other (1) <Polarity>
        (2)
        "
	  ::= { pm20020maAlmmsaModuleState 5 }



pm20020maAlmMsaTxOff OBJECT-TYPE
	  SYNTAX EkiOnOff
	  MAX-ACCESS read-only
	  STATUS current
	  DESCRIPTION
        "
        Line Trscv Laser Shutdown :This
        OID indicates the Line Trscv Laser
        is OFF <Help> Status indicating
        the Line Trscv Laser is OFF <Condtype>
        MSA_TX_OFF <Probcause> informationalStatus(1000)
        <Alarmtype> other (1) <Polarity>
        (2)
        "
	  ::= { pm20020maAlmmsaModuleState 4 }



pm20020maAlmMsaHighPowerUp OBJECT-TYPE
	  SYNTAX EkiOnOff
	  MAX-ACCESS read-only
	  STATUS current
	  DESCRIPTION
        "
        Line Trscv High Power Up :This
        OID indicates the Line Trscv is
        leaving Low Power state <Help>
         Status indicating the Line Trscv
        is leaving Low Power state <Condtype>
        MSA_HIGH_POWER_UP <Probcause> informationalStatus(1000)
        <Alarmtype> other (1) <Polarity>
        (2)
        "
	  ::= { pm20020maAlmmsaModuleState 3 }



pm20020maAlmMsaLowPower OBJECT-TYPE
	  SYNTAX EkiOnOff
	  MAX-ACCESS read-only
	  STATUS current
	  DESCRIPTION
        "
        Line Trscv Low Power :This OID
        indicates the Line Trscv is in
         low power state <Help> Status
         indicating the Line Trscv is in
        low power state <Condtype> MSA_LOW_POWER
        <Probcause> informationalStatus(1000)
        <Alarmtype> other (1) <Polarity>
        (2)
        "
	  ::= { pm20020maAlmmsaModuleState 2 }



pm20020maAlmMsaInitialize OBJECT-TYPE
	  SYNTAX EkiOnOff
	  MAX-ACCESS read-only
	  STATUS current
	  DESCRIPTION
        "
        Line Trscv Initialize :This OID
        indicates the Line Trscv initialization
        is in progress <Help> Status indicating
        the Line Trscv initialization is
        in progress <Condtype> MSA_INITIALIZE
        <Probcause> informationalStatus(1000)
        <Alarmtype> other (1) <Polarity>
        (2)
        "
	  ::= { pm20020maAlmmsaModuleState 1 }



--- *****************************************************
---     LEAF for the msaModuleGeneralStatus article
--- *****************************************************
pm20020maAlmmsaModuleGeneralStatus OBJECT IDENTIFIER ::= { pm20020maAlmOtherCrit 79 }




pm20020maAlmMsaHwInterlock OBJECT-TYPE
	  SYNTAX EkiOnOff
	  MAX-ACCESS read-only
	  STATUS current
	  DESCRIPTION
        "
        Line Trscv Hardware Interlock
         :This OID indicates the Line Trscv
        power is higher than the cooling
        capacity <Help> Alarm indicating
        the Line Trscv power is higher
         than the cooling capacity <Condtype>
        MSA_HW_INTERLOCK <Probcause> temperatureUnacceptable
        (51) <Alarmtype> equipmentAlarm
        (5) <Polarity> (2)
        "
	  ::= { pm20020maAlmmsaModuleGeneralStatus 14 }



pm20020maAlmMsaLossOfRefclk OBJECT-TYPE
	  SYNTAX EkiOnOff
	  MAX-ACCESS read-only
	  STATUS current
	  DESCRIPTION
        "
        Line Trscv Loss Of Ref Clock :This
        OID indicates a Loss of Reference
        clock is detected on the Line Trscv
        <Help> Alarm indicating a Loss
         of Reference clock is detected
        on the Line Trscv <Condtype> MSA_LOSS_OF_REFCLK
        <Probcause> inputOutputDeviceError
        (24) <Alarmtype> equipmentAlarm
        (5) <Polarity> (2)
        "
	  ::= { pm20020maAlmmsaModuleGeneralStatus 11 }



pm20020maAlmMsaTxJitterPllLol OBJECT-TYPE
	  SYNTAX EkiOnOff
	  MAX-ACCESS read-only
	  STATUS current
	  DESCRIPTION
        "
        Line Trscv Tx Jitter PLL Loss
         Of Lock :This OID indicates a
         Tx Jitter PLL Loss of Lock is
         detected on the Line Trscv <Help>
        Alarm indicating a Tx Jitter PLL
        Loss of Lock is detected on the
        Line Trscv <Condtype> MSA_TX_JITTER_PLL_LOL
        <Probcause> inputOutputDeviceError
        (24) <Alarmtype> equipmentAlarm
        (5) <Polarity> (2)
        "
	  ::= { pm20020maAlmmsaModuleGeneralStatus 10 }



pm20020maAlmMsaTxCmuLol OBJECT-TYPE
	  SYNTAX EkiOnOff
	  MAX-ACCESS read-only
	  STATUS current
	  DESCRIPTION
        "
        Line Trscv CMU Loss Of Lock :This
        OID indicates a Clock Multiplier
        Unit Loss of Lock is detected on
        the Line Trscv <Help> Alarm indicating
        a Clock Multiplier Unit Loss of
        Lock is detected on the Line Trscv
        <Condtype> MSA_TX_CMU_LOL <Probcause>
        inputOutputDeviceError (24) <Alarmtype>
        equipmentAlarm (5) <Polarity> (2)
        "
	  ::= { pm20020maAlmmsaModuleGeneralStatus 9 }



pm20020maAlmMsaTxLosf OBJECT-TYPE
	  SYNTAX EkiOnOff
	  MAX-ACCESS read-only
	  STATUS current
	  DESCRIPTION
        "
        Line Trscv Loss Of Signal Functionality
        :This OID indicates a Loss of Signal
        functionality is detected on the
        Line Trscv <Help> Alarm indicating
        a Loss of Signal functionality
         is detected on the Line Trscv
         <Condtype> MSA_TX_LOSF <Probcause>
        lossOfSignal (30) <Alarmtype> equipmentAlarm
        (5) <Polarity> (2)
        "
	  ::= { pm20020maAlmmsaModuleGeneralStatus 8 }



pm20020maAlmMsaTxHostLol OBJECT-TYPE
	  SYNTAX EkiOnOff
	  MAX-ACCESS read-only
	  STATUS current
	  DESCRIPTION
        "
        Line Trscv Tx Host Loss Of Lock
        :This OID indicates of Loss of
         Lock is detected on the Line Trscv
        Tx Host interface <Help> Alarm
         indicating of Loss of Lock is
         detected on the Line Trscv Tx
         Host interface <Condtype> MSA_TX_HOST_LOL
        <Probcause> receiverFailure (42)
        <Alarmtype> equipmentAlarm (5)
         <Polarity> (2)
        "
	  ::= { pm20020maAlmmsaModuleGeneralStatus 7 }



pm20020maAlmMsaRxLos OBJECT-TYPE
	  SYNTAX EkiOnOff
	  MAX-ACCESS read-only
	  STATUS current
	  DESCRIPTION
        "
        Line Trscv Loss Of Signal :This
        OID indicates a Loss of Signal
         is detected on the Line Trscv
         <Help> Alarm indicating a Loss
        of Signal is detected on the Line
        Trscv <Condtype> MSA_RX_LOS <Probcause>
        lossOfSignal (30) <Alarmtype> equipmentAlarm
        (5) <Polarity> (2)
        "
	  ::= { pm20020maAlmmsaModuleGeneralStatus 6 }



pm20020maAlmMsaRxNetworkLol OBJECT-TYPE
	  SYNTAX EkiOnOff
	  MAX-ACCESS read-only
	  STATUS current
	  DESCRIPTION
        "
        Line Trscv Rx Network Loss Of
         Lock :This OID indicates of Loss
        of Lock is detected on the Line
        Trscv Rx Network interface <Help>
        Alarm indicating of Loss of Lock
        is detected on the Line Trscv Rx
        Network interface <Condtype> MSA_RX_NETWORK_LOL
        <Probcause> receiverFailure (42)
        <Alarmtype> equipmentAlarm (5)
         <Polarity> (2)
        "
	  ::= { pm20020maAlmmsaModuleGeneralStatus 5 }



pm20020maAlmMsaOutOfAlignment OBJECT-TYPE
	  SYNTAX EkiOnOff
	  MAX-ACCESS read-only
	  STATUS current
	  DESCRIPTION
        "
        Line Trscv Out Of Alignment :This
        OID indicates an Out of alignment
        on the Line Trscv Host Interface
        <Help> Alarm indicating an Out
         of alignment on the Line Trscv
        Host Interface <Condtype> MSA_OUT_OF_ALIGNMENT
        <Probcause> receiverFailure (42)
        <Alarmtype> equipmentAlarm (5)
         <Polarity> (2)
        "
	  ::= { pm20020maAlmmsaModuleGeneralStatus 4 }



--- *****************************************************
---     LEAF for the msaGlobalAlarmSummary article
--- *****************************************************
pm20020maAlmmsaGlobalAlarmSummary OBJECT IDENTIFIER ::= { pm20020maAlmOtherCrit 80 }




pm20020maAlmMsaGlobAlarmAssertion  OBJECT-TYPE
	  SYNTAX EkiOnOff
	  MAX-ACCESS read-only
	  STATUS current
	  DESCRIPTION
        "
        Line Trscv Global Alarm :This
         OID indicates at least one Fault
        or Status is detected on the Line
        Trscv module <Help> Synthesis alarm
        indicating at least one Alarm,
         Warning, Fault or Status is detected
        on the Line Trscv module <Condtype>
        MSA_GLOB_ALARM_ASSERTION  <Probcause>
        informationalStatus(1000) <Alarmtype>
        other (1) <Polarity> (2)
        "
	  ::= { pm20020maAlmmsaGlobalAlarmSummary 16 }



pm20020maAlmMsaHostLaneFaultStatus  OBJECT-TYPE
	  SYNTAX EkiOnOff
	  MAX-ACCESS read-only
	  STATUS current
	  DESCRIPTION
        "
        Line Trscv Host Fault And Status
        :This OID indicates at least one
        Fault or Status is detected on
         the Line Trscv Host Interface
         <Help> Synthesis alarm indicating
        at least one Fault or Status is
        detected on the Line Trscv Host
        Interface <Condtype> MSA_HOST_LANE_FAULT_STATUS
         <Probcause> informationalStatus(1000)
        <Alarmtype> other (1) <Polarity>
        (2)
        "
	  ::= { pm20020maAlmmsaGlobalAlarmSummary 15 }



pm20020maAlmMsaNetworkLaneFaultStatus  OBJECT-TYPE
	  SYNTAX EkiOnOff
	  MAX-ACCESS read-only
	  STATUS current
	  DESCRIPTION
        "
        Line Trscv Network Fault And Status
        :This OID indicates at least one
        Fault or Status is detected on
         the Line Trscv Network Interface
        <Help> Synthesis alarm indicating
        at least one Fault or Status is
        detected on the Line Trscv Network
        Interface <Condtype> MSA_NETWORK_LANE_FAULT_STATUS
         <Probcause> informationalStatus(1000)
        <Alarmtype> other (1) <Polarity>
        (2)
        "
	  ::= { pm20020maAlmmsaGlobalAlarmSummary 14 }



pm20020maAlmMsaNetworkLaneAlarmWarning1 OBJECT-TYPE
	  SYNTAX EkiOnOff
	  MAX-ACCESS read-only
	  STATUS current
	  DESCRIPTION
        "
        Line Trscv Network Alarm And Warning
        1 :This OID indicates at least
         one DDM is detected on the Line
        Trscv Network Interface <Help>
         Synthesis alarm indicating at
         least one DDM Alarm or DDM Warning
        is detected on the Line Trscv Network
        Interface <Condtype> MSA_NETWORK_LANE_ALARM_WARNING_1
        <Probcause> informationalStatus(1000)
        <Alarmtype> other (1) <Polarity>
        (2)
        "
	  ::= { pm20020maAlmmsaGlobalAlarmSummary 13 }



pm20020maAlmMsaModuleAlarmWarning2 OBJECT-TYPE
	  SYNTAX EkiOnOff
	  MAX-ACCESS read-only
	  STATUS current
	  DESCRIPTION
        "
        Line Trscv Module Alarm And Warning
        2 :This OID indicates at least
         one DDM is detected on the Line
        Trscv module <Help> Synthesis alarm
        indicating at least one DDM Alarm
        or DDM Warning is detected on the
        Line Trscv module <Condtype> MSA_MODULE_ALARM_WARNING_2
        <Probcause> informationalStatus(1000)
        <Alarmtype> other (1) <Polarity>
        (2)
        "
	  ::= { pm20020maAlmmsaGlobalAlarmSummary 12 }



pm20020maAlmMsaModuleAlarmWarning1  OBJECT-TYPE
	  SYNTAX EkiOnOff
	  MAX-ACCESS read-only
	  STATUS current
	  DESCRIPTION
        "
        Line Trscv Module Alarm And Warning
        1 :This OID indicates at least
         one DDM is detected on the Line
        Trscv module <Help> Synthesis alarm
        indicating at least one DDM Alarm
        or DDM Warning is detected on the
        Line Trscv module <Condtype> MSA_MODULE_ALARM_WARNING_1
         <Probcause> informationalStatus(1000)
        <Alarmtype> other (1) <Polarity>
        (2)
        "
	  ::= { pm20020maAlmmsaGlobalAlarmSummary 11 }



pm20020maAlmModuleFault  OBJECT-TYPE
	  SYNTAX EkiOnOff
	  MAX-ACCESS read-only
	  STATUS current
	  DESCRIPTION
        "
        Line Trscv Module Fault :This
         OID indicates at least one Fault
        is detected on the Line Trscv module
        <Help> Synthesis alarm indicating
        at least one Fault is detected
         on the Line Trscv module <Condtype>
        MODULE_FAULT  <Probcause> informationalStatus(1000)
        <Alarmtype> other (1) <Polarity>
        (2)
        "
	  ::= { pm20020maAlmmsaGlobalAlarmSummary 10 }



pm20020maAlmMsaModuleGeneralStatus  OBJECT-TYPE
	  SYNTAX EkiOnOff
	  MAX-ACCESS read-only
	  STATUS current
	  DESCRIPTION
        "
        Line Trscv General Status :This
        OID indicates the Line Trscv module
        general <Help> Synthesis alarm
         indicating the Line Trscv module
        general status <Condtype> MSA_MODULE_GENERAL_STATUS
         <Probcause> informationalStatus(1000)
        <Alarmtype> other (1) <Polarity>
        (2)
        "
	  ::= { pm20020maAlmmsaGlobalAlarmSummary 9 }



pm20020maAlmMsaModuleState  OBJECT-TYPE
	  SYNTAX EkiOnOff
	  MAX-ACCESS read-only
	  STATUS current
	  DESCRIPTION
        "
        Line Trscv Module State :This
         OID indicates the Line Trscv module
        state <Help> Synthesis alarm indicating
        the Line Trscv module state <Condtype>
        MSA_MODULE_STATE  <Probcause> informationalStatus(1000)
        <Alarmtype> other (1) <Polarity>
        (2)
        "
	  ::= { pm20020maAlmmsaGlobalAlarmSummary 8 }



pm20020maAlmMsaNetworkLaneAlarmWarning2 OBJECT-TYPE
	  SYNTAX EkiOnOff
	  MAX-ACCESS read-only
	  STATUS current
	  DESCRIPTION
        "
        Line Trscv Network Alarm And Warning
        2 :This OID indicates at least
         one DDM This OID is detected on
        the Line Trscv Network Interface
        <Help> Synthesis alarm indicating
        at least one DDM Alarm or DDM Warning
        is detected on the Line Trscv Network
        Interface <Condtype> MSA_NETWORK_LANE_ALARM_WARNING_2
        <Probcause> informationalStatus(1000)
        <Alarmtype> other (1) <Polarity>
        (2)
        "
	  ::= { pm20020maAlmmsaGlobalAlarmSummary 7 }



pm20020maAlmMsaNetworkHostAlarmStatus OBJECT-TYPE
	  SYNTAX EkiOnOff
	  MAX-ACCESS read-only
	  STATUS current
	  DESCRIPTION
        "
        Line Trscv Network/Host Alarm
         Status :This OID indicates the
        state of the Network and Host interface
        of the Line Trscv <Help> Synthesis
        alarm indicating the alarm state
        of the Network and Host interface
        of the Line Trscv <Condtype> MSA_NETWORK_HOST_ALARM_STATUS
        <Probcause> informationalStatus(1000)
        <Alarmtype> other (1) <Polarity>
        (2)
        "
	  ::= { pm20020maAlmmsaGlobalAlarmSummary 6 }



pm20020maAlmMsaSoftGlobAlarmTest  OBJECT-TYPE
	  SYNTAX EkiOnOff
	  MAX-ACCESS read-only
	  STATUS current
	  DESCRIPTION
        "
        Line Trscv Global Alarm SW Test
        :This OID indicates the Line Trscv
        Global alarm This OID is raised
        by SW request for test purpose
         <Help> Status indicating the Line
        Trscv Global Alarm is raised by
        SW request for test purpose <Condtype>
        MSA_SOFT_GLOB_ALARM_TEST  <Probcause>
        informationalStatus(1000) <Alarmtype>
        other (1) <Polarity> (2)
        "
	  ::= { pm20020maAlmmsaGlobalAlarmSummary 1 }



--- *****************************************************
---     LEAF for the msaNetworkTxAlignment article
--- *****************************************************
pm20020maAlmmsaNetworkTxAlignment OBJECT IDENTIFIER ::= { pm20020maAlmOtherCrit 81 }




pm20020maAlmNetTxLossOfAlignment OBJECT-TYPE
	  SYNTAX EkiOnOff
	  MAX-ACCESS read-only
	  STATUS current
	  DESCRIPTION
        "
        Line Trscv Network Tx Loss Of
         Alignment :This OID indicates
         a Tx Loss of Alignment is detected
        on the Line Trscv Network interface
        <Help> Alarm indicating a Tx Loss
        of Alignment is detected on the
        Line Trscv Network interface <Condtype>
        NET_TX_LOSS_OF_ALIGNMENT <Probcause>
        transmitterFailure (56) <Alarmtype>
        equipmentAlarm (5) <Polarity> (2)
        "
	  ::= { pm20020maAlmmsaNetworkTxAlignment 16 }



pm20020maAlmNetTxOutOfAlignment OBJECT-TYPE
	  SYNTAX EkiOnOff
	  MAX-ACCESS read-only
	  STATUS current
	  DESCRIPTION
        "
        Line Trscv Network Tx Out Of Alignment
        :This OID indicates a Tx Out of
        Alignment is detected on the Line
        Trscv Network interface <Help>
         Alarm indicating a Tx Out of Alignment
        is detected on the Line Trscv Network
        interface <Condtype> NET_TX_OUT_OF_ALIGNMENT
        <Probcause> transmitterFailure
         (56) <Alarmtype> equipmentAlarm
        (5) <Polarity> (2)
        "
	  ::= { pm20020maAlmmsaNetworkTxAlignment 15 }



pm20020maAlmNetTxCmuLockFault OBJECT-TYPE
	  SYNTAX EkiOnOff
	  MAX-ACCESS read-only
	  STATUS current
	  DESCRIPTION
        "
        Line Trscv Network Tx CMU Lock
        Fault :This OID indicates a Tx
         Clock Multiplier Unit Lock Fault
        is detected on the Line Trscv Network
        interface <Help> Alarm indicating
        a Tx Clock Multiplier Unit Lock
        Fault is detected on the Line Trscv
        Network interface <Condtype> NET_TX_CMU_LOCK_FAULT
        <Probcause> transmitterFailure
         (56) <Alarmtype> equipmentAlarm
        (5) <Polarity> (2)
        "
	  ::= { pm20020maAlmmsaNetworkTxAlignment 14 }



pm20020maAlmNetTxReferenceClockFault OBJECT-TYPE
	  SYNTAX EkiOnOff
	  MAX-ACCESS read-only
	  STATUS current
	  DESCRIPTION
        "
        Line Trscv Network Tx Ref Clock
        Fault :This OID indicates a Tx
         Reference Clock Fault is detected
        on the Line Trscv Network interface
        <Help> Alarm indicating a Tx Reference
        Clock Fault is detected on the
         Line Trscv Network interface <Condtype>
        NET_TX_REFERENCE_CLOCK_FAULT <Probcause>
        transmitterFailure (56) <Alarmtype>
        equipmentAlarm (5) <Polarity> (2)
        "
	  ::= { pm20020maAlmmsaNetworkTxAlignment 13 }



pm20020maAlmNetTxTimingFault OBJECT-TYPE
	  SYNTAX EkiOnOff
	  MAX-ACCESS read-only
	  STATUS current
	  DESCRIPTION
        "
        Line Trscv Network Tx Timing Fault
        :This OID indicates a Tx Timing
        Fault is detected on the Line Trscv
        Network interface <Help> Alarm
         indicating a Tx Timing Fault is
        detected on the Line Trscv Network
        interface <Condtype> NET_TX_TIMING_FAULT
        <Probcause> transmitterFailure
         (56) <Alarmtype> equipmentAlarm
        (5) <Polarity> (2)
        "
	  ::= { pm20020maAlmmsaNetworkTxAlignment 12 }



--- *****************************************************
---     LEAF for the msaNetworkRxAlignment article
--- *****************************************************
pm20020maAlmmsaNetworkRxAlignment OBJECT IDENTIFIER ::= { pm20020maAlmOtherCrit 82 }




pm20020maAlmNetRxModemSyncDetectFault OBJECT-TYPE
	  SYNTAX EkiOnOff
	  MAX-ACCESS read-only
	  STATUS current
	  DESCRIPTION
        "
        Line Trscv Network Rx Modem Sync
        Detect Fault :This OID indicates
        a Rx Modem Synchronisation Detection
        Fault is detected on the Line Trscv
        Network interface <Help> Alarm
         indicating a Rx Modem Synchronisation
        Detection Fault is detected on
         the Line Trscv Network interface
        <Condtype> NET_RX_MODEM_SYNC_DETECT_FAULT
        <Probcause> receiverFailure (42)
        <Alarmtype> equipmentAlarm (5)
         <Polarity> (2)
        "
	  ::= { pm20020maAlmmsaNetworkRxAlignment 16 }



pm20020maAlmNetRxModemLockFault OBJECT-TYPE
	  SYNTAX EkiOnOff
	  MAX-ACCESS read-only
	  STATUS current
	  DESCRIPTION
        "
        Line Trscv Network Rx Modem Lock
        Fault :This OID indicates a Rx
         Modem Lock Fault is detected on
        the Line Trscv Network interface
        <Help> Alarm indicating a Rx Modem
        Lock Fault is detected on the Line
        Trscv Network interface <Condtype>
        NET_RX_MODEM_LOCK_FAULT <Probcause>
        receiverFailure (42) <Alarmtype>
        equipmentAlarm (5) <Polarity> (2)
        "
	  ::= { pm20020maAlmmsaNetworkRxAlignment 15 }



pm20020maAlmNetRxLossOfAlignment OBJECT-TYPE
	  SYNTAX EkiOnOff
	  MAX-ACCESS read-only
	  STATUS current
	  DESCRIPTION
        "
        Line Trscv Network Rx Loss Of
         Alignment :This OID indicates
         a Rx Loss of Alignment is detected
        on the Line Trscv Network interface
        <Help> Alarm indicating a Rx Loss
        of Alignment is detected on the
        Line Trscv Network interface <Condtype>
        NET_RX_LOSS_OF_ALIGNMENT <Probcause>
        receiverFailure (42) <Alarmtype>
        equipmentAlarm (5) <Polarity> (2)
        "
	  ::= { pm20020maAlmmsaNetworkRxAlignment 14 }



pm20020maAlmNetRxOutOfAlignment OBJECT-TYPE
	  SYNTAX EkiOnOff
	  MAX-ACCESS read-only
	  STATUS current
	  DESCRIPTION
        "
        Line Trscv Network Rx Out Of Alignment
        :This OID indicates a Rx Out of
        Alignment is detected on the Line
        Trscv Network interface <Help>
         Alarm indicating a Rx Out of Alignment
        is detected on the Line Trscv Network
        interface <Condtype> NET_RX_OUT_OF_ALIGNMENT
        <Probcause> receiverFailure (42)
        <Alarmtype> equipmentAlarm (5)
         <Polarity> (2)
        "
	  ::= { pm20020maAlmmsaNetworkRxAlignment 13 }



pm20020maAlmNetRxTimingFault OBJECT-TYPE
	  SYNTAX EkiOnOff
	  MAX-ACCESS read-only
	  STATUS current
	  DESCRIPTION
        "
        Line Trscv Network Rx Timing Fault
        :This OID indicates a Rx Timing
        Fault is detected on the Line Trscv
        Network interface <Help> Alarm
         indicating a Rx Timing Fault is
        detected on the Line Trscv Network
        interface <Condtype> NET_RX_TIMING_FAULT
        <Probcause> receiverFailure (42)
        <Alarmtype> equipmentAlarm (5)
         <Polarity> (2)
        "
	  ::= { pm20020maAlmmsaNetworkRxAlignment 12 }



--- *****************************************************
---     LEAF for the msaNetworkHostNetworkAlarmSummary article
--- *****************************************************
pm20020maAlmmsaNetworkHostNetworkAlarmSummary OBJECT IDENTIFIER ::= { pm20020maAlmOtherCrit 83 }




pm20020maAlmHostTxOtnStatus OBJECT-TYPE
	  SYNTAX EkiOnOff
	  MAX-ACCESS read-only
	  STATUS current
	  DESCRIPTION
        "
        Line Trscv Host Tx OTN :This OID
        indicates a Tx OTN Fault is detected
        on the Line Trscv Host interface
        <Help> Synthesis Alarm indicating
        a Tx OTN Fault is detected on the
        Line Trscv Host interface <Condtype>
        HOST_TX_OTN_STATUS <Probcause>
         informationalStatus(1000) <Alarmtype>
        other (1) <Polarity> (2)
        "
	  ::= { pm20020maAlmmsaNetworkHostNetworkAlarmSummary 16 }



pm20020maAlmHostTxAlignment OBJECT-TYPE
	  SYNTAX EkiOnOff
	  MAX-ACCESS read-only
	  STATUS current
	  DESCRIPTION
        "
        Line Trscv Host Tx Alignment :This
        OID indicates a Tx Alignment Fault
        is detected on the Line Trscv Host
        interface <Help> Synthesis Alarm
        indicating a Tx Alignment Fault
        is detected on the Line Trscv Host
        interface <Condtype> HOST_TX_ALIGNMENT
        <Probcause> informationalStatus(1000)
        <Alarmtype> other (1) <Polarity>
        (2)
        "
	  ::= { pm20020maAlmmsaNetworkHostNetworkAlarmSummary 15 }



pm20020maAlmHostRxAlignment OBJECT-TYPE
	  SYNTAX EkiOnOff
	  MAX-ACCESS read-only
	  STATUS current
	  DESCRIPTION
        "
        Line Trscv Host Rx Alignment :This
        OID indicates a Rx Alignment Fault
        is detected on the Line Trscv Host
        interface <Help> Synthesis Alarm
        indicating a Rx Alignment Fault
        is detected on the Line Trscv Host
        interface <Condtype> HOST_RX_ALIGNMENT
        <Probcause> informationalStatus(1000)
        <Alarmtype> other (1) <Polarity>
        (2)
        "
	  ::= { pm20020maAlmmsaNetworkHostNetworkAlarmSummary 14 }



pm20020maAlmNetworkRxOtn OBJECT-TYPE
	  SYNTAX EkiOnOff
	  MAX-ACCESS read-only
	  STATUS current
	  DESCRIPTION
        "
        Line Trscv Network Rx OTN :This
        OID indicates a Rx OTN Fault is
        detected on the Line Trscv Network
        interface <Help> Synthesis Alarm
        indicating a Rx OTN Fault is detected
        on the Line Trscv Network interface
        <Condtype> NETWORK_RX_OTN <Probcause>
        informationalStatus(1000) <Alarmtype>
        other (1) <Polarity> (2)
        "
	  ::= { pm20020maAlmmsaNetworkHostNetworkAlarmSummary 13 }



pm20020maAlmNetworkRxAlignment OBJECT-TYPE
	  SYNTAX EkiOnOff
	  MAX-ACCESS read-only
	  STATUS current
	  DESCRIPTION
        "
        Line Trscv Network Rx Alignment
        :This OID indicates a Rx Alignment
        Fault is detected on the Line Trscv
        Network interface <Help> Synthesis
        Alarm indicating a Rx Alignment
        Fault is detected on the Line Trscv
        Network interface <Condtype> NETWORK_RX_ALIGNMENT
        <Probcause> informationalStatus(1000)
        <Alarmtype> other (1) <Polarity>
        (2)
        "
	  ::= { pm20020maAlmmsaNetworkHostNetworkAlarmSummary 12 }



pm20020maAlmNetworkTxAlignment OBJECT-TYPE
	  SYNTAX EkiOnOff
	  MAX-ACCESS read-only
	  STATUS current
	  DESCRIPTION
        "
        Line Trscv Network Tx Alignment
        :This OID indicates a Tx Alignment
        Fault is detected on the Line Trscv
        Network interface <Help> Synthesis
        Alarm indicating a Tx Alignment
        Fault is detected on the Line Trscv
        Network interface <Condtype> NETWORK_TX_ALIGNMENT
        <Probcause> informationalStatus(1000)
        <Alarmtype> other (1) <Polarity>
        (2)
        "
	  ::= { pm20020maAlmmsaNetworkHostNetworkAlarmSummary 11 }



--- *****************************************************
---     LEAF for the msaHostTxAlignment article
--- *****************************************************
pm20020maAlmmsaHostTxAlignment OBJECT IDENTIFIER ::= { pm20020maAlmOtherCrit 84 }




pm20020maAlmHostTxCdrLockFault OBJECT-TYPE
	  SYNTAX EkiOnOff
	  MAX-ACCESS read-only
	  STATUS current
	  DESCRIPTION
        "
        Line Trscv Host Tx CDR Lock Fault
        :This OID indicates a Tx Clock
         Data Recovery Lock Fault is detected
        on the Line Trscv Host interface
        <Help> Alarm indicating a Tx Clock
        Data Recovery Lock Fault is detected
        on the Line Trscv Host interface
        <Condtype> HOST_TX_CDR_LOCK_FAULT
        <Probcause> receiverFailure (42)
        <Alarmtype> equipmentAlarm (5)
         <Polarity> (2)
        "
	  ::= { pm20020maAlmmsaHostTxAlignment 16 }



pm20020maAlmHostTxLossOfAlignment OBJECT-TYPE
	  SYNTAX EkiOnOff
	  MAX-ACCESS read-only
	  STATUS current
	  DESCRIPTION
        "
        Line Trscv Host Tx Loss Of Alignment
        :This OID indicates a Tx Loss of
        Alignment is detected on the Line
        Trscv Host interface <Help> Alarm
        indicating a Tx Loss of Alignment
        is detected on the Line Trscv Host
        interface <Condtype> HOST_TX_LOSS_OF_ALIGNMENT
        <Probcause> receiverFailure (42)
        <Alarmtype> equipmentAlarm (5)
         <Polarity> (2)
        "
	  ::= { pm20020maAlmmsaHostTxAlignment 15 }



pm20020maAlmHostTxOutOfAlignment OBJECT-TYPE
	  SYNTAX EkiOnOff
	  MAX-ACCESS read-only
	  STATUS current
	  DESCRIPTION
        "
        Line Trscv Host Tx Out Of Alignment
        :This OID indicates a Tx Out of
        Alignment is detected on the Line
        Trscv Host interface <Help> Alarm
        indicating a Tx Out of Alignment
        is detected on the Line Trscv Host
        interface <Condtype> HOST_TX_OUT_OF_ALIGNMENT
        <Probcause> receiverFailure (42)
        <Alarmtype> equipmentAlarm (5)
         <Polarity> (2)
        "
	  ::= { pm20020maAlmmsaHostTxAlignment 14 }



pm20020maAlmHostTxDeskewLockFault OBJECT-TYPE
	  SYNTAX EkiOnOff
	  MAX-ACCESS read-only
	  STATUS current
	  DESCRIPTION
        "
        Line Trscv Host Tx Deskew Lock
        Fault :This OID indicates a Tx
         Deskew Lock Fault is detected
         on  the Line Trscv Host interface
        <Help> Alarm indicating a Tx Deskew
        Lock Fault is detected on  the
         Line Trscv Host interface <Condtype>
        HOST_TX_DESKEW_LOCK_FAULT <Probcause>
        receiverFailure (42) <Alarmtype>
        equipmentAlarm (5) <Polarity> (2)
        "
	  ::= { pm20020maAlmmsaHostTxAlignment 13 }



--- *****************************************************
---     LEAF for the msaHostRxAlignment article
--- *****************************************************
pm20020maAlmmsaHostRxAlignment OBJECT IDENTIFIER ::= { pm20020maAlmOtherCrit 85 }




pm20020maAlmHostRxLossOfAlignment OBJECT-TYPE
	  SYNTAX EkiOnOff
	  MAX-ACCESS read-only
	  STATUS current
	  DESCRIPTION
        "
        Line Trscv Host Rx Loss Of Alignment
        :This OID indicates a Rx Loss of
        Alignment is detected on the Line
        Trscv Host interface <Help> Alarm
        indicating a Rx Loss of Alignment
        is detected on the Line Trscv Host
        interface <Condtype> HOST_RX_LOSS_OF_ALIGNMENT
        <Probcause> transmitterFailure
         (56) <Alarmtype> equipmentAlarm
        (5) <Polarity> (2)
        "
	  ::= { pm20020maAlmmsaHostRxAlignment 16 }



pm20020maAlmHostRxOutOfAlignment OBJECT-TYPE
	  SYNTAX EkiOnOff
	  MAX-ACCESS read-only
	  STATUS current
	  DESCRIPTION
        "
        Line Trscv Host Rx Out Of Alignment
        :This OID indicates a Rx Out of
        Alignment is detected on the Line
        Trscv Host interface <Help> Alarm
        indicating a Rx Out of Alignment
        is detected on the Line Trscv Host
        interface <Condtype> HOST_RX_OUT_OF_ALIGNMENT
        <Probcause> transmitterFailure
         (56) <Alarmtype> equipmentAlarm
        (5) <Polarity> (2)
        "
	  ::= { pm20020maAlmmsaHostRxAlignment 15 }



pm20020maAlmHostRxCmuLockFault OBJECT-TYPE
	  SYNTAX EkiOnOff
	  MAX-ACCESS read-only
	  STATUS current
	  DESCRIPTION
        "
        Line Trscv Host Rx CMU Lock Fault
        :This OID indicates a Rx Clock
         Multiplier Unit Lock Fault is
         detected on the Line Trscv Host
        interface <Help> Alarm indicating
        a Rx Clock Multiplier Unit Lock
        Fault is detected on the Line Trscv
        Host interface <Condtype> HOST_RX_CMU_LOCK_FAULT
        <Probcause> transmitterFailure
         (56) <Alarmtype> equipmentAlarm
        (5) <Polarity> (2)
        "
	  ::= { pm20020maAlmmsaHostRxAlignment 14 }



--- *********************************************************
---     TABLE for the pm20020maAlmclientNetworkLaneAlarmWarning articles
--- *********************************************************

pm20020maAlmclientNetworkLaneAlarmWarningTable OBJECT-TYPE
	SYNTAX  SEQUENCE OF Pm20020maAlmclientNetworkLaneAlarmWarningEntry
	MAX-ACCESS not-accessible
	STATUS current
	DESCRIPTION
        "
        List of pm20020maAlmclientNetworkLaneAlarmWarning
        Article
        "
	::= { pm20020maAlmClientNurg 88 }


pm20020maAlmclientNetworkLaneAlarmWarningEntry OBJECT-TYPE
	SYNTAX Pm20020maAlmclientNetworkLaneAlarmWarningEntry
	MAX-ACCESS not-accessible
	STATUS current
	DESCRIPTION
        "
        Row definition for the pm20020maAlmclientNetworkLaneAlarmWarning
        table
        "
	INDEX   { pm20020maAlmclientNetworkLaneAlarmWarningIndex }
	::= { pm20020maAlmclientNetworkLaneAlarmWarningTable 1 }


Pm20020maAlmclientNetworkLaneAlarmWarningEntry ::=
	SEQUENCE {
	pm20020maAlmclientNetworkLaneAlarmWarningIndex
		INTEGER,
	pm20020maAlmClientBiasHighAlarmPortn
		EkiOnOff,
	pm20020maAlmClientBiasHighWarningPortn
		EkiOnOff,
	pm20020maAlmClientBiasLowWarningPortn
		EkiOnOff,
	pm20020maAlmClientBiasLowAlarmPortn
		EkiOnOff,
	pm20020maAlmClientTxPowerHighAlarmPortn
		EkiOnOff,
	pm20020maAlmClientTxPowerHighWarningPortn
		EkiOnOff,
	pm20020maAlmClientTxPowerLowWarningPortn
		EkiOnOff,
	pm20020maAlmClientTxPowerLowAlarmPortn
		EkiOnOff,
	pm20020maAlmClientLaserTempHighAlarmPortn
		EkiOnOff,
	pm20020maAlmClientLaserTempHighWarningPortn
		EkiOnOff,
	pm20020maAlmClientLaserTempLowWarningPortn
		EkiOnOff,
	pm20020maAlmLaserTempLowAlarmPortn
		EkiOnOff,
	pm20020maAlmClientRxPowerHighAlarmPortn
		EkiOnOff,
	pm20020maAlmClientRxPowerHighWarningPortn
		EkiOnOff,
	pm20020maAlmClientRxPowerLowWarningPortn
		EkiOnOff,
	pm20020maAlmClientRxPowerLowAlarmPortn
		EkiOnOff
	}


pm20020maAlmclientNetworkLaneAlarmWarningIndex OBJECT-TYPE
	SYNTAX  INTEGER(0..128)
	MAX-ACCESS  read-only
	STATUS current
	DESCRIPTION
        "
        Index definition for the pm20020maAlmclientNetworkLaneAlarmWarning
        table
        "
	::= { pm20020maAlmclientNetworkLaneAlarmWarningEntry 1 }


pm20020maAlmClientBiasHighAlarmPortn OBJECT-TYPE
	SYNTAX  EkiOnOff
	MAX-ACCESS read-only
	STATUS current
	DESCRIPTION
        "
        Client Trscv Bias High Alarm :This
        OID indicates that the Trscv laser
        bias current is higher than the
        threshold value written in the
         Trscv EEPROM <Help> Alarm indicating
        that the Trscv laser bias current
        is higher than the threshold value
        written in the Trscv EEPROM <Condtype>
        CLIENT_BIAS_HIGH_ALARM <Probcause>
        transmitterFailure (56) <Alarmtype>
        equipmentAlarm (5) <Polarity> (2)
        "
	::= { pm20020maAlmclientNetworkLaneAlarmWarningEntry 17 }


pm20020maAlmClientBiasHighWarningPortn OBJECT-TYPE
	SYNTAX  EkiOnOff
	MAX-ACCESS read-only
	STATUS current
	DESCRIPTION
        "
        Client Trscv Bias High Warning
        :This OID indicates that the Trscv
        laser bias current is higher than
        the threshold value written in
         the Trscv EEPROM <Help> Warning
        indicating that the Trscv laser
        bias current is higher than the
        threshold value written in the
         Trscv EEPROM <Condtype> CLIENT_BIAS_HIGH_WARNING
        <Probcause> transmitterFailure
         (56) <Alarmtype> equipmentAlarm
        (5) <Polarity> (2)
        "
	::= { pm20020maAlmclientNetworkLaneAlarmWarningEntry 16 }


pm20020maAlmClientBiasLowWarningPortn OBJECT-TYPE
	SYNTAX  EkiOnOff
	MAX-ACCESS read-only
	STATUS current
	DESCRIPTION
        "
        Client Trscv Bias Low Warning
         :This OID indicates that the Trscv
        laser bias current is lower than
        the threshold value written in
         the Trscv EEPROM <Help> Warning
        indicating that the Trscv laser
        bias current is lower than the
         threshold value written in the
        Trscv EEPROM <Condtype> CLIENT_BIAS_LOW_WARNING
        <Probcause> transmitterFailure
         (56) <Alarmtype> equipmentAlarm
        (5) <Polarity> (2)
        "
	::= { pm20020maAlmclientNetworkLaneAlarmWarningEntry 15 }


pm20020maAlmClientBiasLowAlarmPortn OBJECT-TYPE
	SYNTAX  EkiOnOff
	MAX-ACCESS read-only
	STATUS current
	DESCRIPTION
        "
        Client Trscv Bias Low Alarm :This
        OID indicates that the Trscv laser
        bias current is lower than the
         threshold value written in the
        Trscv EEPROM <Help> Alarm indicating
        that the Trscv laser bias current
        is lower than the threshold value
        written in the Trscv EEPROM <Condtype>
        CLIENT_BIAS_LOW_ALARM <Probcause>
        transmitterFailure (56) <Alarmtype>
        equipmentAlarm (5) <Polarity> (2)
        "
	::= { pm20020maAlmclientNetworkLaneAlarmWarningEntry 14 }


pm20020maAlmClientTxPowerHighAlarmPortn OBJECT-TYPE
	SYNTAX  EkiOnOff
	MAX-ACCESS read-only
	STATUS current
	DESCRIPTION
        "
        Client Trscv Tx Power High Alarm
        :This OID indicates that the Trscv
        output power is higher than the
        threshold value written in the
         Trscv EEPROM <Help> Alarm indicating
        that the Trscv output power is
         higher than the threshold value
        written in the Trscv EEPROM <Condtype>
        CLIENT_TX_POWER_HIGH_ALARM <Probcause>
        transmitterFailure (56) <Alarmtype>
        equipmentAlarm (5) <Polarity> (2)
        "
	::= { pm20020maAlmclientNetworkLaneAlarmWarningEntry 13 }


pm20020maAlmClientTxPowerHighWarningPortn OBJECT-TYPE
	SYNTAX  EkiOnOff
	MAX-ACCESS read-only
	STATUS current
	DESCRIPTION
        "
        Client Trscv Tx Power High Warning
        :This OID indicates that the Trscv
        output power is higher than the
        threshold value written in the
         Trscv EEPROM <Help> Warning indicating
        that the Trscv output power is
         higher than the threshold value
        written in the Trscv EEPROM <Condtype>
        CLIENT_TX_POWER_HIGH_WARNING <Probcause>
        transmitterFailure (56) <Alarmtype>
        equipmentAlarm (5) <Polarity> (2)
        "
	::= { pm20020maAlmclientNetworkLaneAlarmWarningEntry 12 }


pm20020maAlmClientTxPowerLowWarningPortn OBJECT-TYPE
	SYNTAX  EkiOnOff
	MAX-ACCESS read-only
	STATUS current
	DESCRIPTION
        "
        Client Trscv Tx Power Low Warning
        :This OID indicates that the Trscv
        output power is lower than the
         threshold value written in the
        Trscv EEPROM <Help> Warning indicating
        that the Trscv output power is
         lower than the threshold value
        written in the Trscv EEPROM <Condtype>
        CLIENT_TX_POWER_LOW_WARNING <Probcause>
        transmitterFailure (56) <Alarmtype>
        equipmentAlarm (5) <Polarity> (2)
        "
	::= { pm20020maAlmclientNetworkLaneAlarmWarningEntry 11 }


pm20020maAlmClientTxPowerLowAlarmPortn OBJECT-TYPE
	SYNTAX  EkiOnOff
	MAX-ACCESS read-only
	STATUS current
	DESCRIPTION
        "
        Client Trscv Tx Power Low Alarm
        :This OID indicates that the Trscv
        output power is lower than the
         threshold value written in the
        Trscv EEPROM <Help> Alarm indicating
        that the Trscv output power is
         lower than the threshold value
        written in the Trscv EEPROM <Condtype>
        CLIENT_TX_POWER_LOW_ALARM <Probcause>
        transmitterFailure (56) <Alarmtype>
        equipmentAlarm (5) <Polarity> (2)
        "
	::= { pm20020maAlmclientNetworkLaneAlarmWarningEntry 10 }


pm20020maAlmClientLaserTempHighAlarmPortn OBJECT-TYPE
	SYNTAX  EkiOnOff
	MAX-ACCESS read-only
	STATUS current
	DESCRIPTION
        "
        Client Trscv Laser Temp High Alarm
        :This OID indicates that the Trscv
        Laser Temperature is higher than
        the threshold value written in
         the Trscv EEPROM <Help> Alarm
         indicating that the Trscv Laser
        Temperature is higher than the
         threshold value written in the
        Trscv EEPROM <Condtype> CLIENT_LASER_TEMP_HIGH_ALARM
        <Probcause> temperatureUnacceptable
        (51) <Alarmtype> equipmentAlarm
        (5) <Polarity> (2)
        "
	::= { pm20020maAlmclientNetworkLaneAlarmWarningEntry 9 }


pm20020maAlmClientLaserTempHighWarningPortn OBJECT-TYPE
	SYNTAX  EkiOnOff
	MAX-ACCESS read-only
	STATUS current
	DESCRIPTION
        "
        Client Trscv Laser Temp High Warning
        :This OID indicates that the Trscv
        Laser Temperature is higher than
        the threshold value written in
         the Trscv EEPROM <Help> Warning
        indicating that the Trscv Laser
        Temperature is higher than the
         threshold value written in the
        Trscv EEPROM <Condtype> CLIENT_LASER_TEMP_HIGH_WARNING
        <Probcause> temperatureUnacceptable
        (51) <Alarmtype> equipmentAlarm
        (5) <Polarity> (2)
        "
	::= { pm20020maAlmclientNetworkLaneAlarmWarningEntry 8 }


pm20020maAlmClientLaserTempLowWarningPortn OBJECT-TYPE
	SYNTAX  EkiOnOff
	MAX-ACCESS read-only
	STATUS current
	DESCRIPTION
        "
        Client Trscv Laser Temp Low Warning
        :This OID indicates that the Trscv
        Laser Temperature is lower than
        the threshold value written in
         the Trscv EEPROM <Help> Warning
        indicating that the Trscv Laser
        Temperature is lower than the threshold
        value written in the Trscv EEPROM
        <Condtype> CLIENT_LASER_TEMP_LOW_WARNING
        <Probcause> temperatureUnacceptable
        (51) <Alarmtype> equipmentAlarm
        (5) <Polarity> (2)
        "
	::= { pm20020maAlmclientNetworkLaneAlarmWarningEntry 7 }


pm20020maAlmLaserTempLowAlarmPortn OBJECT-TYPE
	SYNTAX  EkiOnOff
	MAX-ACCESS read-only
	STATUS current
	DESCRIPTION
        "
        Client Trscv Laser Temp Low Alarm
        :This OID indicates that the Trscv
        Laser Temperature is lower than
        the threshold value written in
         the Trscv EEPROM <Help> Alarm
         indicating that the Trscv Laser
        Temperature is lower than the threshold
        value written in the Trscv EEPROM
        <Condtype> LASER_TEMP_LOW_ALARM
        <Probcause> temperatureUnacceptable
        (51) <Alarmtype> equipmentAlarm
        (5) <Polarity> (2)
        "
	::= { pm20020maAlmclientNetworkLaneAlarmWarningEntry 6 }


pm20020maAlmClientRxPowerHighAlarmPortn OBJECT-TYPE
	SYNTAX  EkiOnOff
	MAX-ACCESS read-only
	STATUS current
	DESCRIPTION
        "
        Client Trscv Rx Power High Alarm
        :This OID indicates that the Trscv
        input power is higher than the
         threshold value written in the
        Trscv EEPROM <Help> Alarm indicating
        that the Trscv input power is higher
        than the threshold value written
        in the Trscv EEPROM <Condtype>
         CLIENT_RX_POWER_HIGH_ALARM <Probcause>
        receiveFailure (41) <Alarmtype>
        equipmentAlarm (5) <Polarity> (2)
        "
	::= { pm20020maAlmclientNetworkLaneAlarmWarningEntry 5 }


pm20020maAlmClientRxPowerHighWarningPortn OBJECT-TYPE
	SYNTAX  EkiOnOff
	MAX-ACCESS read-only
	STATUS current
	DESCRIPTION
        "
        Client Trscv Rx Power High Warning
        :This OID indicates that the Trscv
        input power is higher than the
         threshold value written in the
        Trscv EEPROM <Help> Warning indicating
        that the Trscv input power is higher
        than the threshold value written
        in the Trscv EEPROM <Condtype>
         CLIENT_RX_POWER_HIGH_WARNING <Probcause>
        receiveFailure (41) <Alarmtype>
        equipmentAlarm (5) <Polarity> (2)
        "
	::= { pm20020maAlmclientNetworkLaneAlarmWarningEntry 4 }


pm20020maAlmClientRxPowerLowWarningPortn OBJECT-TYPE
	SYNTAX  EkiOnOff
	MAX-ACCESS read-only
	STATUS current
	DESCRIPTION
        "
        Client Trscv Rx Power Low Warning
        :This OID indicates that the Trscv
        input power is lower than the threshold
        value written in the Trscv EEPROM
        <Help> Warning indicating that
         the Trscv input power is lower
        than the threshold value written
        in the Trscv EEPROM <Condtype>
         CLIENT_RX_POWER_LOW_WARNING <Probcause>
        receiveFailure (41) <Alarmtype>
        equipmentAlarm (5) <Polarity> (2)
        "
	::= { pm20020maAlmclientNetworkLaneAlarmWarningEntry 3 }


pm20020maAlmClientRxPowerLowAlarmPortn OBJECT-TYPE
	SYNTAX  EkiOnOff
	MAX-ACCESS read-only
	STATUS current
	DESCRIPTION
        "
        Client Trscv Rx Power Low Alarm
        :This OID indicates that the Trscv
        input power is lower than the threshold
        value written in the Trscv EEPROM
        <Help> Alarm indicating that the
        Trscv input power is lower than
        the threshold value written in
         the Trscv EEPROM <Condtype> CLIENT_RX_POWER_LOW_ALARM
        <Probcause> receiveFailure (41)
        <Alarmtype> equipmentAlarm (5)
         <Polarity> (2)
        "
	::= { pm20020maAlmclientNetworkLaneAlarmWarningEntry 2 }


--- *********************************************************
---     TABLE for the pm20020maAlmclientNetworkLaneFault articles
--- *********************************************************

pm20020maAlmclientNetworkLaneFaultTable OBJECT-TYPE
	SYNTAX  SEQUENCE OF Pm20020maAlmclientNetworkLaneFaultEntry
	MAX-ACCESS not-accessible
	STATUS current
	DESCRIPTION
        "
        List of pm20020maAlmclientNetworkLaneFault
        Article
        "
	::= { pm20020maAlmClientUrg 120 }


pm20020maAlmclientNetworkLaneFaultEntry OBJECT-TYPE
	SYNTAX Pm20020maAlmclientNetworkLaneFaultEntry
	MAX-ACCESS not-accessible
	STATUS current
	DESCRIPTION
        "
        Row definition for the pm20020maAlmclientNetworkLaneFault
        table
        "
	INDEX   { pm20020maAlmclientNetworkLaneFaultIndex }
	::= { pm20020maAlmclientNetworkLaneFaultTable 1 }


Pm20020maAlmclientNetworkLaneFaultEntry ::=
	SEQUENCE {
	pm20020maAlmclientNetworkLaneFaultIndex
		INTEGER,
	pm20020maAlmClientLaneTecFaultPortn
		EkiOnOff,
	pm20020maAlmClientLaneWavelengthUnlockedPortn
		EkiOnOff,
	pm20020maAlmClientLaneApdPowerSupplyPortn
		EkiOnOff,
	pm20020maAlmClientLaneTxLosfPortn
		EkiOnOff,
	pm20020maAlmClientLaneTxLolPortn
		EkiOnOff,
	pm20020maAlmClientLaneRxLosPortn
		EkiOnOff,
	pm20020maAlmClientLaneRxLolPortn
		EkiOnOff,
	pm20020maAlmClientLaneRxFifoErrorPortn
		EkiOnOff
	}


pm20020maAlmclientNetworkLaneFaultIndex OBJECT-TYPE
	SYNTAX  INTEGER(0..128)
	MAX-ACCESS  read-only
	STATUS current
	DESCRIPTION
        "
        Index definition for the pm20020maAlmclientNetworkLaneFault
        table
        "
	::= { pm20020maAlmclientNetworkLaneFaultEntry 1 }


pm20020maAlmClientLaneTecFaultPortn OBJECT-TYPE
	SYNTAX  EkiOnOff
	MAX-ACCESS read-only
	STATUS current
	DESCRIPTION
        "
        Client Network Lane TEC Fault
         :This OID indicates a TEC Fault
        on the Client Trscv Network Lane
        <Help> Alarm indicating a TEC Fault
        on the Client Trscv Network Lane
        <Condtype> CLIENT_LANE_TEC_FAULT
        <Probcause> transmitterFailure
         (56) <Alarmtype> equipmentAlarm
        (5) <Polarity> (2)
        "
	::= { pm20020maAlmclientNetworkLaneFaultEntry 17 }


pm20020maAlmClientLaneWavelengthUnlockedPortn OBJECT-TYPE
	SYNTAX  EkiOnOff
	MAX-ACCESS read-only
	STATUS current
	DESCRIPTION
        "
        Client Network Lane Wavelength
        Unlock :This OID indicates a Wavelength
        unlock on the Client Trscv Network
        Lane <Help> Alarm indicating a
         Wavelength unlock on the Client
        Trscv Network Lane <Condtype> CLIENT_LANE_WAVELENGTH_UNLOCKED
        <Probcause> transmitterFailure
         (56) <Alarmtype> equipmentAlarm
        (5) <Polarity> (2)
        "
	::= { pm20020maAlmclientNetworkLaneFaultEntry 16 }


pm20020maAlmClientLaneApdPowerSupplyPortn OBJECT-TYPE
	SYNTAX  EkiOnOff
	MAX-ACCESS read-only
	STATUS current
	DESCRIPTION
        "
        Client Network Lane APD Power
         Supply :This OID indicates an
         APD Power supply failure on the
        Client Trscv Network Lane <Help>
        Alarm indicating an APD Power supply
        failure on the Client Trscv Network
        Lane <Condtype> CLIENT_LANE_APD_POWER_SUPPLY
        <Probcause> transmitterFailure
         (56) <Alarmtype> equipmentAlarm
        (5) <Polarity> (2)
        "
	::= { pm20020maAlmclientNetworkLaneFaultEntry 15 }


pm20020maAlmClientLaneTxLosfPortn OBJECT-TYPE
	SYNTAX  EkiOnOff
	MAX-ACCESS read-only
	STATUS current
	DESCRIPTION
        "
        Client Network Lane Tx Loss Of
        Signal Functionality :This OID
         indicates a Tx Loss of Signal
         Functionality on the Client Trscv
        Network Lane <Help> Alarm indicating
        a Tx Loss of Signal Functionality
        on the Client Trscv Network Lane
        <Condtype> CLIENT_LANE_TX_LOSF
         <Probcause> transmitterFailure
        (56) <Alarmtype> equipmentAlarm
        (5) <Polarity> (2)
        "
	::= { pm20020maAlmclientNetworkLaneFaultEntry 9 }


pm20020maAlmClientLaneTxLolPortn OBJECT-TYPE
	SYNTAX  EkiOnOff
	MAX-ACCESS read-only
	STATUS current
	DESCRIPTION
        "
        Client Network Lane Tx Loss Of
        Lock :This OID indicates a Tx Loss
        of Lock on the Client Trscv Network
        Lane <Help> Alarm indicating a
         Tx Loss of Lock on the Client
         Trscv Network Lane <Condtype>
         CLIENT_LANE_TX_LOL <Probcause>
        transmitterFailure (56) <Alarmtype>
        equipmentAlarm (5) <Polarity> (2)
        "
	::= { pm20020maAlmclientNetworkLaneFaultEntry 8 }


pm20020maAlmClientLaneRxLosPortn OBJECT-TYPE
	SYNTAX  EkiOnOff
	MAX-ACCESS read-only
	STATUS current
	DESCRIPTION
        "
        Client Network Lane Rx Loss Of
        Signal :This OID indicates a Rx
        Loss of Signal on the Client Trscv
        Network Lane <Help> Alarm indicating
        a Rx Loss of Signal on the Client
        Trscv Network Lane <Condtype> CLIENT_LANE_RX_LOS
        <Probcause> receiveFailure (41)
        <Alarmtype> physicalViolation (9)
        <Polarity> (2)
        "
	::= { pm20020maAlmclientNetworkLaneFaultEntry 6 }


pm20020maAlmClientLaneRxLolPortn OBJECT-TYPE
	SYNTAX  EkiOnOff
	MAX-ACCESS read-only
	STATUS current
	DESCRIPTION
        "
        Client Network Lane Rx Loss Of
        Lock :This OID indicates a Rx Loss
        of Lock on the Client Trscv Network
        Lane <Help> Alarm indicating a
         Rx Loss of Lock on the Client
         Trscv Network Lane <Condtype>
         CLIENT_LANE_RX_LOL <Probcause>
        receiverFailure (42) <Alarmtype>
        equipmentAlarm (5) <Polarity> (2)
        "
	::= { pm20020maAlmclientNetworkLaneFaultEntry 5 }


pm20020maAlmClientLaneRxFifoErrorPortn OBJECT-TYPE
	SYNTAX  EkiOnOff
	MAX-ACCESS read-only
	STATUS current
	DESCRIPTION
        "
        Client Network Lane Rx FIFO Error
        :This OID indicates a Rx FIFO Error
        on the Client Trscv Network Lane
        <Help> Alarm indicating a Rx FIFO
        Error on the Client Trscv Network
        Lane <Condtype> CLIENT_LANE_RX_FIFO_ERROR
        <Probcause> receiverFailure (42)
        <Alarmtype> equipmentAlarm (5)
         <Polarity> (2)
        "
	::= { pm20020maAlmclientNetworkLaneFaultEntry 4 }


--- *********************************************************
---     TABLE for the pm20020maAlmclientHostLaneFault articles
--- *********************************************************

pm20020maAlmclientHostLaneFaultTable OBJECT-TYPE
	SYNTAX  SEQUENCE OF Pm20020maAlmclientHostLaneFaultEntry
	MAX-ACCESS not-accessible
	STATUS current
	DESCRIPTION
        "
        List of pm20020maAlmclientHostLaneFault
        Article
        "
	::= { pm20020maAlmClientUrg 152 }


pm20020maAlmclientHostLaneFaultEntry OBJECT-TYPE
	SYNTAX Pm20020maAlmclientHostLaneFaultEntry
	MAX-ACCESS not-accessible
	STATUS current
	DESCRIPTION
        "
        Row definition for the pm20020maAlmclientHostLaneFault
        table
        "
	INDEX   { pm20020maAlmclientHostLaneFaultIndex }
	::= { pm20020maAlmclientHostLaneFaultTable 1 }


Pm20020maAlmclientHostLaneFaultEntry ::=
	SEQUENCE {
	pm20020maAlmclientHostLaneFaultIndex
		INTEGER,
	pm20020maAlmClientLaneTxFifoErrorPortn
		EkiOnOff,
	pm20020maAlmClientTxHostLolPortn
		EkiOnOff,
	pm20020maAlmClientCsfDetectedPortn
		EkiOnOff,
	pm20020maAlmClientLanesNotAlignedPortn
		EkiOnOff,
	pm20020maAlmClientLanes6466UnlockPortn
		EkiOnOff,
	pm20020maAlmClientLanesMarkerUnlockPortn
		EkiOnOff,
	pm20020maAlmClientInputLossOfSigPortn
		EkiOnOff,
	pm20020maAlmClientLossOfSyncPortn
		EkiOnOff
	}


pm20020maAlmclientHostLaneFaultIndex OBJECT-TYPE
	SYNTAX  INTEGER(0..128)
	MAX-ACCESS  read-only
	STATUS current
	DESCRIPTION
        "
        Index definition for the pm20020maAlmclientHostLaneFault
        table
        "
	::= { pm20020maAlmclientHostLaneFaultEntry 1 }


pm20020maAlmClientLaneTxFifoErrorPortn OBJECT-TYPE
	SYNTAX  EkiOnOff
	MAX-ACCESS read-only
	STATUS current
	DESCRIPTION
        "
        Client Host Lane Tx FIFO Error
        :This OID indicates a Tx FIFO Error
        on the Client Trscv Host Lane <Help>
        Alarm indicating a Tx FIFO Error
        on the Client Trscv Host Lane <Condtype>
        CLIENT_LANE_TX_FIFO_ERROR <Probcause>
        receiverFailure (42) <Alarmtype>
        equipmentAlarm (5) <Polarity> (2)
        "
	::= { pm20020maAlmclientHostLaneFaultEntry 11 }


pm20020maAlmClientTxHostLolPortn OBJECT-TYPE
	SYNTAX  EkiOnOff
	MAX-ACCESS read-only
	STATUS current
	DESCRIPTION
        "
        Client Host Lane Tx Loss Of Lock
        :This OID indicates a Tx Loss of
        Lock on the Client Trscv Host Lane
        <Help> Alarm indicating a Tx Loss
        of Lock on the Client Trscv Host
        Lane <Condtype> CLIENT_TX_HOST_LOL
        <Probcause> receiverFailure (42)
        <Alarmtype> equipmentAlarm (5)
         <Polarity> (2)
        "
	::= { pm20020maAlmclientHostLaneFaultEntry 10 }


pm20020maAlmClientCsfDetectedPortn OBJECT-TYPE
	SYNTAX  EkiOnOff
	MAX-ACCESS read-only
	STATUS current
	DESCRIPTION
        "
        Client Signal Fail Detected :This
        OID indicates that a CSF has been
        detected on client port in the
         downstream direction   <Help>
          This alarm indicates if a Client
        Signal Fail has been detected in
        the incoming line frame for this
        client port <Condtype> CLIENT_CSF_DETECTED
        <Probcause> receiveFailure (41)
        <Alarmtype> other(1) <Polarity>
        (2)
        "
	::= { pm20020maAlmclientHostLaneFaultEntry 7 }


pm20020maAlmClientLanesNotAlignedPortn OBJECT-TYPE
	SYNTAX  EkiOnOff
	MAX-ACCESS read-only
	STATUS current
	DESCRIPTION
        "
        Client Lanes Not Aligned :This
        OID indicates the Client lanes
         are not aligned <Help> Alarm indicating
        the Client lanes are not aligned
        <Condtype> CLIENT_LANES_NOT_ALIGNED
        <Probcause> receiveFailure (41)
        <Alarmtype> integrityViolation
         (7) <Polarity> (2)
        "
	::= { pm20020maAlmclientHostLaneFaultEntry 6 }


pm20020maAlmClientLanes6466UnlockPortn OBJECT-TYPE
	SYNTAX  EkiOnOff
	MAX-ACCESS read-only
	STATUS current
	DESCRIPTION
        "
        Client Lanes 64/66b Unlock :This
        OID indicates the Client 64/66b
        decoder is not lock <Help> Alarm
        indicating the Client 64/66b decoder
        is not lock <Condtype> CLIENT_LANES_64_66_UNLOCK
        <Probcause> receiveFailure (41)
        <Alarmtype> integrityViolation
         (7) <Polarity> (2)
        "
	::= { pm20020maAlmclientHostLaneFaultEntry 5 }


pm20020maAlmClientLanesMarkerUnlockPortn OBJECT-TYPE
	SYNTAX  EkiOnOff
	MAX-ACCESS read-only
	STATUS current
	DESCRIPTION
        "
        Client Lanes Marker Unlock :This
        OID indicates the Client lanes
         marker alignment is not lock <Help>
        Alarm indicating the Client lanes
        marker alignment is not lock <Condtype>
        CLIENT_LANES_MARKER_UNLOCK <Probcause>
        receiveFailure (41) <Alarmtype>
        integrityViolation (7) <Polarity>
        (2)
        "
	::= { pm20020maAlmclientHostLaneFaultEntry 4 }


pm20020maAlmClientInputLossOfSigPortn OBJECT-TYPE
	SYNTAX  EkiOnOff
	MAX-ACCESS read-only
	STATUS current
	DESCRIPTION
        "
        Client Input Loss Of Signal :This
        OID indicates a Loss of Signal
         is detected on the Client Trscv
        <Help> Alarm indicating a Loss
         of Signal is detected on the Client
        Trscv <Condtype> CLIENT_INPUT_LOSS_OF_SIG
        <Probcause> receiveFailure (41)
        <Alarmtype> physicalViolation (9)
        <Polarity> (2)
        "
	::= { pm20020maAlmclientHostLaneFaultEntry 3 }


pm20020maAlmClientLossOfSyncPortn OBJECT-TYPE
	SYNTAX  EkiOnOff
	MAX-ACCESS read-only
	STATUS current
	DESCRIPTION
        "
        Client Frame Alignment Loss :This
        OID indicates the module is not
        aligned with the incoming Client
        signal <Help> Alarm indicating
         the module is not aligned with
        the incoming client signal <Condtype>
        CLIENT_LOSS_OF_SYNC <Probcause>
        receiveFailure (41) <Alarmtype>
        integrityViolation (7) <Polarity>
        (2)
        "
	::= { pm20020maAlmclientHostLaneFaultEntry 2 }


--- *********************************************************
---     TABLE for the pm20020maAlmlineNetworkLaneAlarmWarning1 articles
--- *********************************************************

pm20020maAlmlineNetworkLaneAlarmWarning1Table OBJECT-TYPE
	SYNTAX  SEQUENCE OF Pm20020maAlmlineNetworkLaneAlarmWarning1Entry
	MAX-ACCESS not-accessible
	STATUS current
	DESCRIPTION
        "
        List of pm20020maAlmlineNetworkLaneAlarmWarning1
        Article
        "
	::= { pm20020maAlmLineNurg 184 }


pm20020maAlmlineNetworkLaneAlarmWarning1Entry OBJECT-TYPE
	SYNTAX Pm20020maAlmlineNetworkLaneAlarmWarning1Entry
	MAX-ACCESS not-accessible
	STATUS current
	DESCRIPTION
        "
        Row definition for the pm20020maAlmlineNetworkLaneAlarmWarning1
        table
        "
	INDEX   { pm20020maAlmlineNetworkLaneAlarmWarning1Index }
	::= { pm20020maAlmlineNetworkLaneAlarmWarning1Table 1 }


Pm20020maAlmlineNetworkLaneAlarmWarning1Entry ::=
	SEQUENCE {
	pm20020maAlmlineNetworkLaneAlarmWarning1Index
		INTEGER,
	pm20020maAlmLineBiasHighAlarmPortn
		EkiOnOff,
	pm20020maAlmLineBiasHighWarningPortn
		EkiOnOff,
	pm20020maAlmLineBiasLowWarningPortn
		EkiOnOff,
	pm20020maAlmLineBiasLowAlarmPortn
		EkiOnOff,
	pm20020maAlmLineTxPowerHighAlarmPortn
		EkiOnOff,
	pm20020maAlmLineTxPowerHighWarningPortn
		EkiOnOff,
	pm20020maAlmLineTxPowerLowWarningPortn
		EkiOnOff,
	pm20020maAlmLineTxPowerLowAlarmPortn
		EkiOnOff,
	pm20020maAlmLineLaserTempHighAlarmPortn
		EkiOnOff,
	pm20020maAlmLineLaserTempHighWarningPortn
		EkiOnOff,
	pm20020maAlmLineLaserTempLowWarningPortn
		EkiOnOff,
	pm20020maAlmLineLaserTempLowAlarmPortn
		EkiOnOff,
	pm20020maAlmLineRxPowerHighAlarmPortn
		EkiOnOff,
	pm20020maAlmLineRxPowerHighWarningPortn
		EkiOnOff,
	pm20020maAlmLineRxPowerLowWarningPortn
		EkiOnOff,
	pm20020maAlmLineRxPowerLowAlarmPortn
		EkiOnOff
	}


pm20020maAlmlineNetworkLaneAlarmWarning1Index OBJECT-TYPE
	SYNTAX  INTEGER(0..128)
	MAX-ACCESS  read-only
	STATUS current
	DESCRIPTION
        "
        Index definition for the pm20020maAlmlineNetworkLaneAlarmWarning1
        table
        "
	::= { pm20020maAlmlineNetworkLaneAlarmWarning1Entry 1 }


pm20020maAlmLineBiasHighAlarmPortn OBJECT-TYPE
	SYNTAX  EkiOnOff
	MAX-ACCESS read-only
	STATUS current
	DESCRIPTION
        "
        Line Trscv Tx Bias High Alarm
         :This OID indicates that the Trscv
        laser bias current is higher than
        the threshold value written in
         the Trscv EEPROM <Help> Alarm
         indicating that the Trscv laser
        bias current is higher than the
        threshold value written in the
         Trscv EEPROM <Condtype> LINE_BIAS_HIGH_ALARM
        <Probcause> transmitterFailure
         (56) <Alarmtype> equipmentAlarm
        (5) <Polarity> (2)
        "
	::= { pm20020maAlmlineNetworkLaneAlarmWarning1Entry 17 }


pm20020maAlmLineBiasHighWarningPortn OBJECT-TYPE
	SYNTAX  EkiOnOff
	MAX-ACCESS read-only
	STATUS current
	DESCRIPTION
        "
        Line Trscv Tx Bias High Warning
        :This OID indicates that the Trscv
        laser bias current is higher than
        the threshold value written in
         the Trscv EEPROM <Help> Warning
        indicating that the Trscv laser
        bias current is higher than the
        threshold value written in the
         Trscv EEPROM <Condtype> LINE_BIAS_HIGH_WARNING
        <Probcause> transmitterFailure
         (56) <Alarmtype> equipmentAlarm
        (5) <Polarity> (2)
        "
	::= { pm20020maAlmlineNetworkLaneAlarmWarning1Entry 16 }


pm20020maAlmLineBiasLowWarningPortn OBJECT-TYPE
	SYNTAX  EkiOnOff
	MAX-ACCESS read-only
	STATUS current
	DESCRIPTION
        "
        Line Trscv Tx Bias Low Warning
        :This OID indicates that the Trscv
        laser bias current is lower than
        the threshold value written in
         the Trscv EEPROM <Help> Warning
        indicating that the Trscv laser
        bias current is lower than the
         threshold value written in the
        Trscv EEPROM <Condtype> LINE_BIAS_LOW_WARNING
        <Probcause> transmitterFailure
         (56) <Alarmtype> equipmentAlarm
        (5) <Polarity> (2)
        "
	::= { pm20020maAlmlineNetworkLaneAlarmWarning1Entry 15 }


pm20020maAlmLineBiasLowAlarmPortn OBJECT-TYPE
	SYNTAX  EkiOnOff
	MAX-ACCESS read-only
	STATUS current
	DESCRIPTION
        "
        Line Trscv Tx Bias Low Alarm :This
        OID indicates that the Trscv laser
        bias current is lower than the
         threshold value written in the
        Trscv EEPROM <Help> Alarm indicating
        that the Trscv laser bias current
        is lower than the threshold value
        written in the Trscv EEPROM <Condtype>
        LINE_BIAS_LOW_ALARM <Probcause>
        transmitterFailure (56) <Alarmtype>
        equipmentAlarm (5) <Polarity> (2)
        "
	::= { pm20020maAlmlineNetworkLaneAlarmWarning1Entry 14 }


pm20020maAlmLineTxPowerHighAlarmPortn OBJECT-TYPE
	SYNTAX  EkiOnOff
	MAX-ACCESS read-only
	STATUS current
	DESCRIPTION
        "
        Line Trscv Tx Power High Alarm
        :This OID indicates that the Trscv
        output power is higher than the
        threshold value written in the
         Trscv EEPROM <Help> Alarm indicating
        that the Trscv output power is
         higher than the threshold value
        written in the Trscv EEPROM <Condtype>
        LINE_TX_POWER_HIGH_ALARM <Probcause>
        transmitterFailure (56) <Alarmtype>
        equipmentAlarm (5) <Polarity> (2)
        "
	::= { pm20020maAlmlineNetworkLaneAlarmWarning1Entry 13 }


pm20020maAlmLineTxPowerHighWarningPortn OBJECT-TYPE
	SYNTAX  EkiOnOff
	MAX-ACCESS read-only
	STATUS current
	DESCRIPTION
        "
        Line Trscv Tx Power High Warning
        :This OID indicates that the Trscv
        output power is higher than the
        threshold value written in the
         Trscv EEPROM <Help> Warning indicating
        that the Trscv output power is
         higher than the threshold value
        written in the Trscv EEPROM <Condtype>
        LINE_TX_POWER_HIGH_WARNING <Probcause>
        transmitterFailure (56) <Alarmtype>
        equipmentAlarm (5) <Polarity> (2)
        "
	::= { pm20020maAlmlineNetworkLaneAlarmWarning1Entry 12 }


pm20020maAlmLineTxPowerLowWarningPortn OBJECT-TYPE
	SYNTAX  EkiOnOff
	MAX-ACCESS read-only
	STATUS current
	DESCRIPTION
        "
        Line Trscv Tx Power Low Warning
        :This OID indicates that the Trscv
        output power is lower than the
         threshold value written in the
        Trscv EEPROM <Help> Warning indicating
        that the Trscv output power is
         lower than the threshold value
        written in the Trscv EEPROM <Condtype>
        LINE_TX_POWER_LOW_WARNING <Probcause>
        transmitterFailure (56) <Alarmtype>
        equipmentAlarm (5) <Polarity> (2)
        "
	::= { pm20020maAlmlineNetworkLaneAlarmWarning1Entry 11 }


pm20020maAlmLineTxPowerLowAlarmPortn OBJECT-TYPE
	SYNTAX  EkiOnOff
	MAX-ACCESS read-only
	STATUS current
	DESCRIPTION
        "
        Line Trscv Tx Power Low Alarm
         :This OID indicates that the Trscv
        output power is lower than the
         threshold value written in the
        Trscv EEPROM <Help> Alarm indicating
        that the Trscv output power is
         lower than the threshold value
        written in the Trscv EEPROM <Condtype>
        LINE_TX_POWER_LOW_ALARM <Probcause>
        transmitterFailure (56) <Alarmtype>
        equipmentAlarm (5) <Polarity> (2)
        "
	::= { pm20020maAlmlineNetworkLaneAlarmWarning1Entry 10 }


pm20020maAlmLineLaserTempHighAlarmPortn OBJECT-TYPE
	SYNTAX  EkiOnOff
	MAX-ACCESS read-only
	STATUS current
	DESCRIPTION
        "
        Line Trscv Tx Laser Temp High
         Alarm :This OID indicates that
        the Trscv Tx Laser Temperature
         is higher than the threshold value
        written in the Trscv EEPROM <Help>
        Alarm indicating that the Trscv
        Tx Laser Temperature is higher
         than the threshold value written
        in the Trscv EEPROM <Condtype>
         LINE_LASER_TEMP_HIGH_ALARM <Probcause>
        temperatureUnacceptable (51) <Alarmtype>
        equipmentAlarm (5) <Polarity> (2)
        "
	::= { pm20020maAlmlineNetworkLaneAlarmWarning1Entry 9 }


pm20020maAlmLineLaserTempHighWarningPortn OBJECT-TYPE
	SYNTAX  EkiOnOff
	MAX-ACCESS read-only
	STATUS current
	DESCRIPTION
        "
        Line Trscv Tx Laser Temp High
         Warning :This OID indicates that
        the Trscv Tx Laser Temperature
         is higher than the threshold value
        written in the Trscv EEPROM <Help>
        Warning indicating that the Trscv
        Tx Laser Temperature is higher
         than the threshold value written
        in the Trscv EEPROM <Condtype>
         LINE_LASER_TEMP_HIGH_WARNING <Probcause>
        temperatureUnacceptable (51) <Alarmtype>
        equipmentAlarm (5) <Polarity> (2)
        "
	::= { pm20020maAlmlineNetworkLaneAlarmWarning1Entry 8 }


pm20020maAlmLineLaserTempLowWarningPortn OBJECT-TYPE
	SYNTAX  EkiOnOff
	MAX-ACCESS read-only
	STATUS current
	DESCRIPTION
        "
        Line Trscv Tx Laser Temp Low Warning
        :This OID indicates that the Trscv
        Tx Laser Temperature is lower than
        the threshold value written in
         the Trscv EEPROM <Help> Warning
        indicating that the Trscv Tx Laser
        Temperature is lower than the threshold
        value written in the Trscv EEPROM
        <Condtype> LINE_LASER_TEMP_LOW_WARNING
        <Probcause> temperatureUnacceptable
        (51) <Alarmtype> equipmentAlarm
        (5) <Polarity> (2)
        "
	::= { pm20020maAlmlineNetworkLaneAlarmWarning1Entry 7 }


pm20020maAlmLineLaserTempLowAlarmPortn OBJECT-TYPE
	SYNTAX  EkiOnOff
	MAX-ACCESS read-only
	STATUS current
	DESCRIPTION
        "
        Line Trscv Tx Laser Temp Low Alarm
        :This OID indicates that the Trscv
        Tx Laser Temperature is lower than
        the threshold value written in
         the Trscv EEPROM <Help> Alarm
         indicating that the Trscv Tx Laser
        Temperature is lower than the threshold
        value written in the Trscv EEPROM
        <Condtype> LINE_LASER_TEMP_LOW_ALARM
        <Probcause> temperatureUnacceptable
        (51) <Alarmtype> equipmentAlarm
        (5) <Polarity> (2)
        "
	::= { pm20020maAlmlineNetworkLaneAlarmWarning1Entry 6 }


pm20020maAlmLineRxPowerHighAlarmPortn OBJECT-TYPE
	SYNTAX  EkiOnOff
	MAX-ACCESS read-only
	STATUS current
	DESCRIPTION
        "
        Line Trscv Rx Power High Alarm
        :This OID indicates that the Trscv
        input power is higher than the
         threshold value written in the
        Trscv EEPROM <Help> Alarm indicating
        that the Trscv input power is higher
        than the threshold value written
        in the Trscv EEPROM <Condtype>
         LINE_RX_POWER_HIGH_ALARM <Probcause>
        receiveFailure (41) <Alarmtype>
        equipmentAlarm (5) <Polarity> (2)
        "
	::= { pm20020maAlmlineNetworkLaneAlarmWarning1Entry 5 }


pm20020maAlmLineRxPowerHighWarningPortn OBJECT-TYPE
	SYNTAX  EkiOnOff
	MAX-ACCESS read-only
	STATUS current
	DESCRIPTION
        "
        Line Trscv Rx Power High Warning
        :This OID indicates that the Trscv
        input power is higher than the
         threshold value written in the
        Trscv EEPROM <Help> Warning indicating
        that the Trscv input power is higher
        than the threshold value written
        in the Trscv EEPROM <Condtype>
         LINE_RX_POWER_HIGH_WARNING <Probcause>
        receiveFailure (41) <Alarmtype>
        equipmentAlarm (5) <Polarity> (2)
        "
	::= { pm20020maAlmlineNetworkLaneAlarmWarning1Entry 4 }


pm20020maAlmLineRxPowerLowWarningPortn OBJECT-TYPE
	SYNTAX  EkiOnOff
	MAX-ACCESS read-only
	STATUS current
	DESCRIPTION
        "
        Line Trscv Rx Power Low Warning
        :This OID indicates that the Trscv
        input power is lower than the threshold
        value written in the Trscv EEPROM
        <Help> Warning indicating that
         the Trscv input power is lower
        than the threshold value written
        in the Trscv EEPROM <Condtype>
         LINE_RX_POWER_LOW_WARNING <Probcause>
        receiveFailure (41) <Alarmtype>
        equipmentAlarm (5) <Polarity> (2)
        "
	::= { pm20020maAlmlineNetworkLaneAlarmWarning1Entry 3 }


pm20020maAlmLineRxPowerLowAlarmPortn OBJECT-TYPE
	SYNTAX  EkiOnOff
	MAX-ACCESS read-only
	STATUS current
	DESCRIPTION
        "
        Line Trscv Rx Power Low Alarm
         :This OID indicates that the Trscv
        input power is lower than the threshold
        value written in the Trscv EEPROM
        <Help> Alarm indicating that the
        Trscv input power is lower than
        the threshold value written in
         the Trscv EEPROM <Condtype> LINE_RX_POWER_LOW_ALARM
        <Probcause> receiveFailure (41)
        <Alarmtype> equipmentAlarm (5)
         <Polarity> (2)
        "
	::= { pm20020maAlmlineNetworkLaneAlarmWarning1Entry 2 }


--- *********************************************************
---     TABLE for the pm20020maAlmlineNetworkLaneAlarmWarning2 articles
--- *********************************************************

pm20020maAlmlineNetworkLaneAlarmWarning2Table OBJECT-TYPE
	SYNTAX  SEQUENCE OF Pm20020maAlmlineNetworkLaneAlarmWarning2Entry
	MAX-ACCESS not-accessible
	STATUS current
	DESCRIPTION
        "
        List of pm20020maAlmlineNetworkLaneAlarmWarning2
        Article
        "
	::= { pm20020maAlmLineNurg 188 }


pm20020maAlmlineNetworkLaneAlarmWarning2Entry OBJECT-TYPE
	SYNTAX Pm20020maAlmlineNetworkLaneAlarmWarning2Entry
	MAX-ACCESS not-accessible
	STATUS current
	DESCRIPTION
        "
        Row definition for the pm20020maAlmlineNetworkLaneAlarmWarning2
        table
        "
	INDEX   { pm20020maAlmlineNetworkLaneAlarmWarning2Index }
	::= { pm20020maAlmlineNetworkLaneAlarmWarning2Table 1 }


Pm20020maAlmlineNetworkLaneAlarmWarning2Entry ::=
	SEQUENCE {
	pm20020maAlmlineNetworkLaneAlarmWarning2Index
		INTEGER,
	pm20020maAlmRxLaserBiasHighAlarmPortn
		EkiOnOff,
	pm20020maAlmRxLaserBiasHighWarningPortn
		EkiOnOff,
	pm20020maAlmRxLaserBiasLowWarningPortn
		EkiOnOff,
	pm20020maAlmRxLaserBiasLowAlarmPortn
		EkiOnOff,
	pm20020maAlmRxLaserOutputHighAlarmPortn
		EkiOnOff,
	pm20020maAlmRxLaserOutputHighWarningPortn
		EkiOnOff,
	pm20020maAlmRxLaserOutputLowWarningPortn
		EkiOnOff,
	pm20020maAlmRxLaserOutputLowAlarmPortn
		EkiOnOff,
	pm20020maAlmRxLaserTempHighAlarmPortn
		EkiOnOff,
	pm20020maAlmRxLaserTempHighWarningPortn
		EkiOnOff,
	pm20020maAlmRxLaserTempLowWarningPortn
		EkiOnOff,
	pm20020maAlmRxLaserTempLowAlarmPortn
		EkiOnOff,
	pm20020maAlmTxModulatorBiasHighAlarmPortn
		EkiOnOff,
	pm20020maAlmTxModulatorBiasHighWarningPortn
		EkiOnOff,
	pm20020maAlmTxModulatorBiasLowWarningPortn
		EkiOnOff,
	pm20020maAlmTxModulatorBiasLowAlarmPortn
		EkiOnOff
	}


pm20020maAlmlineNetworkLaneAlarmWarning2Index OBJECT-TYPE
	SYNTAX  INTEGER(0..128)
	MAX-ACCESS  read-only
	STATUS current
	DESCRIPTION
        "
        Index definition for the pm20020maAlmlineNetworkLaneAlarmWarning2
        table
        "
	::= { pm20020maAlmlineNetworkLaneAlarmWarning2Entry 1 }


pm20020maAlmRxLaserBiasHighAlarmPortn OBJECT-TYPE
	SYNTAX  EkiOnOff
	MAX-ACCESS read-only
	STATUS current
	DESCRIPTION
        "
        Line Trscv Rx Bias High Alarm
         :This OID indicates that the Trscv
        Rx laser bias current is higher
        than the threshold value written
        in the Trscv EEPROM <Help> Alarm
        indicating that the Trscv Rx laser
        bias current is higher than the
        threshold value written in the
         Trscv EEPROM <Condtype> RX_LASER_BIAS_HIGH_ALARM
        <Probcause> receiveFailure (41)
        <Alarmtype> equipmentAlarm (5)
         <Polarity> (2)
        "
	::= { pm20020maAlmlineNetworkLaneAlarmWarning2Entry 17 }


pm20020maAlmRxLaserBiasHighWarningPortn OBJECT-TYPE
	SYNTAX  EkiOnOff
	MAX-ACCESS read-only
	STATUS current
	DESCRIPTION
        "
        Line Trscv Rx Bias High Warning
        :This OID indicates that the Trscv
        Rx laser bias current is higher
        than the threshold value written
        in the Trscv EEPROM <Help> Warning
        indicating that the Trscv Rx laser
        bias current is higher than the
        threshold value written in the
         Trscv EEPROM <Condtype> RX_LASER_BIAS_HIGH_WARNING
        <Probcause> receiveFailure (41)
        <Alarmtype> equipmentAlarm (5)
         <Polarity> (2)
        "
	::= { pm20020maAlmlineNetworkLaneAlarmWarning2Entry 16 }


pm20020maAlmRxLaserBiasLowWarningPortn OBJECT-TYPE
	SYNTAX  EkiOnOff
	MAX-ACCESS read-only
	STATUS current
	DESCRIPTION
        "
        Line Trscv Rx Bias Low Warning
        :This OID indicates that the Trscv
        Rx laser bias current is lower
         than the threshold value written
        in the Trscv EEPROM <Help> Warning
        indicating that the Trscv Rx laser
        bias current is lower than the
         threshold value written in the
        Trscv EEPROM <Condtype> RX_LASER_BIAS_LOW_WARNING
        <Probcause> receiveFailure (41)
        <Alarmtype> equipmentAlarm (5)
         <Polarity> (2)
        "
	::= { pm20020maAlmlineNetworkLaneAlarmWarning2Entry 15 }


pm20020maAlmRxLaserBiasLowAlarmPortn OBJECT-TYPE
	SYNTAX  EkiOnOff
	MAX-ACCESS read-only
	STATUS current
	DESCRIPTION
        "
        Line Trscv Rx Bias Low Alarm :This
        OID indicates that the Trscv Rx
        laser bias current is lower than
        the threshold value written in
         the Trscv EEPROM <Help> Alarm
         indicating that the Trscv Rx laser
        bias current is lower than the
         threshold value written in the
        Trscv EEPROM <Condtype> RX_LASER_BIAS_LOW_ALARM
        <Probcause> receiveFailure (41)
        <Alarmtype> equipmentAlarm (5)
         <Polarity> (2)
        "
	::= { pm20020maAlmlineNetworkLaneAlarmWarning2Entry 14 }


pm20020maAlmRxLaserOutputHighAlarmPortn OBJECT-TYPE
	SYNTAX  EkiOnOff
	MAX-ACCESS read-only
	STATUS current
	DESCRIPTION
        "
        Line Trscv Rx Output Power High
        Alarm :This OID indicates that
         the Trscv Rx output power is higher
        than the threshold value written
        in the Trscv EEPROM <Help> Alarm
        indicating that the Trscv Rx output
        power is higher than the threshold
        value written in the Trscv EEPROM
        <Condtype> RX_LASER_OUTPUT_HIGH_ALARM
        <Probcause> receiveFailure (41)
        <Alarmtype> equipmentAlarm (5)
         <Polarity> (2)
        "
	::= { pm20020maAlmlineNetworkLaneAlarmWarning2Entry 13 }


pm20020maAlmRxLaserOutputHighWarningPortn OBJECT-TYPE
	SYNTAX  EkiOnOff
	MAX-ACCESS read-only
	STATUS current
	DESCRIPTION
        "
        Line Trscv Rx Output Power High
        Warning :This OID indicates that
        the Trscv Rx output power is higher
        than the threshold value written
        in the Trscv EEPROM <Help> Warning
        indicating that the Trscv Rx output
        power is higher than the threshold
        value written in the Trscv EEPROM
        <Condtype> RX_LASER_OUTPUT_HIGH_WARNING
        <Probcause> receiveFailure (41)
        <Alarmtype> equipmentAlarm (5)
         <Polarity> (2)
        "
	::= { pm20020maAlmlineNetworkLaneAlarmWarning2Entry 12 }


pm20020maAlmRxLaserOutputLowWarningPortn OBJECT-TYPE
	SYNTAX  EkiOnOff
	MAX-ACCESS read-only
	STATUS current
	DESCRIPTION
        "
        Line Trscv Rx Output Power Low
        Warning :This OID indicates that
        the Trscv Rx output power is lower
        than the threshold value written
        in the Trscv EEPROM <Help> Warning
        indicating that the Trscv Rx output
        power is lower than the threshold
        value written in the Trscv EEPROM
        <Condtype> RX_LASER_OUTPUT_LOW_WARNING
        <Probcause> receiveFailure (41)
        <Alarmtype> equipmentAlarm (5)
         <Polarity> (2)
        "
	::= { pm20020maAlmlineNetworkLaneAlarmWarning2Entry 11 }


pm20020maAlmRxLaserOutputLowAlarmPortn OBJECT-TYPE
	SYNTAX  EkiOnOff
	MAX-ACCESS read-only
	STATUS current
	DESCRIPTION
        "
        Line Trscv Rx Output Power Low
        Alarm :This OID indicates that
         the Trscv Rx output power is lower
        than the threshold value written
        in the Trscv EEPROM <Help> Alarm
        indicating that the Trscv Rx output
        power is lower than the threshold
        value written in the Trscv EEPROM
        <Condtype> RX_LASER_OUTPUT_LOW_ALARM
        <Probcause> receiveFailure (41)
        <Alarmtype> equipmentAlarm (5)
         <Polarity> (2)
        "
	::= { pm20020maAlmlineNetworkLaneAlarmWarning2Entry 10 }


pm20020maAlmRxLaserTempHighAlarmPortn OBJECT-TYPE
	SYNTAX  EkiOnOff
	MAX-ACCESS read-only
	STATUS current
	DESCRIPTION
        "
        Line Trscv Rx Laser Temp High
         Alarm :This OID indicates that
        the Trscv Rx Laser Temperature
         is higher than the threshold value
        written in the Trscv EEPROM <Help>
        Alarm indicating that the Trscv
        Rx Laser Temperature is higher
         than the threshold value written
        in the Trscv EEPROM <Condtype>
         RX_LASER_TEMP_HIGH_ALARM <Probcause>
        temperatureUnacceptable (51) <Alarmtype>
        equipmentAlarm (5) <Polarity> (2)
        "
	::= { pm20020maAlmlineNetworkLaneAlarmWarning2Entry 9 }


pm20020maAlmRxLaserTempHighWarningPortn OBJECT-TYPE
	SYNTAX  EkiOnOff
	MAX-ACCESS read-only
	STATUS current
	DESCRIPTION
        "
        Line Trscv Rx Laser Temp High
         Warning :This OID indicates that
        the Trscv Rx Laser Temperature
         is higher than the threshold value
        written in the Trscv EEPROM <Help>
        Warning indicating that the Trscv
        Rx Laser Temperature is higher
         than the threshold value written
        in the Trscv EEPROM <Condtype>
         RX_LASER_TEMP_HIGH_WARNING <Probcause>
        temperatureUnacceptable (51) <Alarmtype>
        equipmentAlarm (5) <Polarity> (2)
        "
	::= { pm20020maAlmlineNetworkLaneAlarmWarning2Entry 8 }


pm20020maAlmRxLaserTempLowWarningPortn OBJECT-TYPE
	SYNTAX  EkiOnOff
	MAX-ACCESS read-only
	STATUS current
	DESCRIPTION
        "
        Line Trscv Rx Laser Temp Low Warning
        :This OID indicates that the Trscv
        Rx Laser Temperature is lower than
        the threshold value written in
         the Trscv EEPROM <Help> Warning
        indicating that the Trscv Rx Laser
        Temperature is lower than the threshold
        value written in the Trscv EEPROM
        <Condtype> RX_LASER_TEMP_LOW_WARNING
        <Probcause> temperatureUnacceptable
        (51) <Alarmtype> equipmentAlarm
        (5) <Polarity> (2)
        "
	::= { pm20020maAlmlineNetworkLaneAlarmWarning2Entry 7 }


pm20020maAlmRxLaserTempLowAlarmPortn OBJECT-TYPE
	SYNTAX  EkiOnOff
	MAX-ACCESS read-only
	STATUS current
	DESCRIPTION
        "
        Line Trscv Rx Laser Temp Low Alarm
        :This OID indicates that the Trscv
        Rx Laser Temperature is lower than
        the threshold value written in
         the Trscv EEPROM <Help> Alarm
         indicating that the Trscv Rx Laser
        Temperature is lower than the threshold
        value written in the Trscv EEPROM
        <Condtype> RX_LASER_TEMP_LOW_ALARM
        <Probcause> temperatureUnacceptable
        (51) <Alarmtype> equipmentAlarm
        (5) <Polarity> (2)
        "
	::= { pm20020maAlmlineNetworkLaneAlarmWarning2Entry 6 }


pm20020maAlmTxModulatorBiasHighAlarmPortn OBJECT-TYPE
	SYNTAX  EkiOnOff
	MAX-ACCESS read-only
	STATUS current
	DESCRIPTION
        "
        Line Trscv Tx Modulator Bias High
        Alarm :This OID indicates that
         the Trscv Tx modulator bias current
        is higher than the threshold value
        written in the Trscv EEPROM <Help>
        Alarm indicating that the Trscv
        Tx modulator bias current is higher
        than the threshold value written
        in the Trscv EEPROM <Condtype>
         TX_MODULATOR_BIAS_HIGH_ALARM <Probcause>
        transmitterFailure (56) <Alarmtype>
        equipmentAlarm (5) <Polarity> (2)
        "
	::= { pm20020maAlmlineNetworkLaneAlarmWarning2Entry 5 }


pm20020maAlmTxModulatorBiasHighWarningPortn OBJECT-TYPE
	SYNTAX  EkiOnOff
	MAX-ACCESS read-only
	STATUS current
	DESCRIPTION
        "
        Line Trscv Tx Modulator Bias High
        Warning :This OID indicates that
        the Trscv Tx modulator bias current
        is higher than the threshold value
        written in the Trscv EEPROM <Help>
        Warning indicating that the Trscv
        Tx modulator bias current is higher
        than the threshold value written
        in the Trscv EEPROM <Condtype>
         TX_MODULATOR_BIAS_HIGH_WARNING
        <Probcause> transmitterFailure
         (56) <Alarmtype> equipmentAlarm
        (5) <Polarity> (2)
        "
	::= { pm20020maAlmlineNetworkLaneAlarmWarning2Entry 4 }


pm20020maAlmTxModulatorBiasLowWarningPortn OBJECT-TYPE
	SYNTAX  EkiOnOff
	MAX-ACCESS read-only
	STATUS current
	DESCRIPTION
        "
        Line Trscv Tx Modulator Bias Low
        Warning :This OID indicates that
        the Trscv Tx modulator bias current
        is lower than the threshold value
        written in the Trscv EEPROM <Help>
        Warning indicating that the Trscv
        Tx modulator bias current is lower
        than the threshold value written
        in the Trscv EEPROM <Condtype>
         TX_MODULATOR_BIAS_LOW_WARNING
         <Probcause> transmitterFailure
        (56) <Alarmtype> equipmentAlarm
        (5) <Polarity> (2)
        "
	::= { pm20020maAlmlineNetworkLaneAlarmWarning2Entry 3 }


pm20020maAlmTxModulatorBiasLowAlarmPortn OBJECT-TYPE
	SYNTAX  EkiOnOff
	MAX-ACCESS read-only
	STATUS current
	DESCRIPTION
        "
        Line Trscv Tx Modulator Bias Low
        Alarm :This OID indicates that
         the Trscv Tx modulator bias current
        is lower than the threshold value
        written in the Trscv EEPROM <Help>
        Alarm indicating that the Trscv
        Tx modulator bias current is lower
        than the threshold value written
        in the Trscv EEPROM <Condtype>
         TX_MODULATOR_BIAS_LOW_ALARM <Probcause>
        transmitterFailure (56) <Alarmtype>
        equipmentAlarm (5) <Polarity> (2)
        "
	::= { pm20020maAlmlineNetworkLaneAlarmWarning2Entry 2 }


--- *********************************************************
---     TABLE for the pm20020maAlmlineNetworkLaneFault articles
--- *********************************************************

pm20020maAlmlineNetworkLaneFaultTable OBJECT-TYPE
	SYNTAX  SEQUENCE OF Pm20020maAlmlineNetworkLaneFaultEntry
	MAX-ACCESS not-accessible
	STATUS current
	DESCRIPTION
        "
        List of pm20020maAlmlineNetworkLaneFault
        Article
        "
	::= { pm20020maAlmLineUrg 192 }


pm20020maAlmlineNetworkLaneFaultEntry OBJECT-TYPE
	SYNTAX Pm20020maAlmlineNetworkLaneFaultEntry
	MAX-ACCESS not-accessible
	STATUS current
	DESCRIPTION
        "
        Row definition for the pm20020maAlmlineNetworkLaneFault
        table
        "
	INDEX   { pm20020maAlmlineNetworkLaneFaultIndex }
	::= { pm20020maAlmlineNetworkLaneFaultTable 1 }


Pm20020maAlmlineNetworkLaneFaultEntry ::=
	SEQUENCE {
	pm20020maAlmlineNetworkLaneFaultIndex
		INTEGER,
	pm20020maAlmLineLaneTecFaultPortn
		EkiOnOff,
	pm20020maAlmLineLaneWavelengthUnlockedPortn
		EkiOnOff,
	pm20020maAlmLineLaneApdPowerSupplyPortn
		EkiOnOff,
	pm20020maAlmLineLaneTxLosfPortn
		EkiOnOff,
	pm20020maAlmLineLaneTxLolPortn
		EkiOnOff,
	pm20020maAlmLineLaneRxLosPortn
		EkiOnOff,
	pm20020maAlmLineLaneRxLolPortn
		EkiOnOff,
	pm20020maAlmLineLaneRxFifoErrorPortn
		EkiOnOff,
	pm20020maAlmLineLaneRxTecFaultPortn
		EkiOnOff
	}


pm20020maAlmlineNetworkLaneFaultIndex OBJECT-TYPE
	SYNTAX  INTEGER(0..128)
	MAX-ACCESS  read-only
	STATUS current
	DESCRIPTION
        "
        Index definition for the pm20020maAlmlineNetworkLaneFault
        table
        "
	::= { pm20020maAlmlineNetworkLaneFaultEntry 1 }


pm20020maAlmLineLaneTecFaultPortn OBJECT-TYPE
	SYNTAX  EkiOnOff
	MAX-ACCESS read-only
	STATUS current
	DESCRIPTION
        "
        Line Network Lane TEC Fault :This
        OID indicates a Tx TEC Fault on
        the Line Trscv Network Lane <Help>
        Alarm indicating a Tx TEC Fault
        on the Line Trscv Network Lane
         <Condtype> LINE_LANE_TEC_FAULT
        <Probcause> transmitterFailure
         (56) <Alarmtype> equipmentAlarm
        (5) <Polarity> (2)
        "
	::= { pm20020maAlmlineNetworkLaneFaultEntry 17 }


pm20020maAlmLineLaneWavelengthUnlockedPortn OBJECT-TYPE
	SYNTAX  EkiOnOff
	MAX-ACCESS read-only
	STATUS current
	DESCRIPTION
        "
        Line Network Lane Wavelength Unlock
        :This OID indicates a Wavelength
        unlock on the Line Trscv Network
        Lane <Help> Alarm indicating a
         Wavelength unlock on the Line
         Trscv Network Lane <Condtype>
         LINE_LANE_WAVELENGTH_UNLOCKED
         <Probcause> transmitterFailure
        (56) <Alarmtype> equipmentAlarm
        (5) <Polarity> (2)
        "
	::= { pm20020maAlmlineNetworkLaneFaultEntry 16 }


pm20020maAlmLineLaneApdPowerSupplyPortn OBJECT-TYPE
	SYNTAX  EkiOnOff
	MAX-ACCESS read-only
	STATUS current
	DESCRIPTION
        "
        Line Network Lane APD Power Supply
        :This OID indicates an APD Power
        supply failure on the Line Trscv
        Network Lane <Help> Alarm indicating
        an APD Power supply failure on
         the Line Trscv Network Lane <Condtype>
        LINE_LANE_APD_POWER_SUPPLY <Probcause>
        transmitterFailure (56) <Alarmtype>
        equipmentAlarm (5) <Polarity> (2)
        "
	::= { pm20020maAlmlineNetworkLaneFaultEntry 15 }


pm20020maAlmLineLaneTxLosfPortn OBJECT-TYPE
	SYNTAX  EkiOnOff
	MAX-ACCESS read-only
	STATUS current
	DESCRIPTION
        "
        Line Network Lane Tx Loss Of Signal
        Functionality :This OID indicates
        a Tx Loss of Signal Functionality
        on the Line Trscv Network Lane
         <Help> Alarm indicating a Tx Loss
        of Signal Functionality on the
         Line Trscv Network Lane <Condtype>
        LINE_LANE_TX_LOSF <Probcause> transmitterFailure
        (56) <Alarmtype> equipmentAlarm
        (5) <Polarity> (2)
        "
	::= { pm20020maAlmlineNetworkLaneFaultEntry 9 }


pm20020maAlmLineLaneTxLolPortn OBJECT-TYPE
	SYNTAX  EkiOnOff
	MAX-ACCESS read-only
	STATUS current
	DESCRIPTION
        "
        Line Network Lane Tx Loss Of Lock
        :This OID indicates a Tx Loss of
        Lock on the Line Trscv Network
         Lane <Help> Alarm indicating a
        Tx Loss of Lock on the Line Trscv
        Network Lane <Condtype> LINE_LANE_TX_LOL
        <Probcause> transmitterFailure
         (56) <Alarmtype> equipmentAlarm
        (5) <Polarity> (2)
        "
	::= { pm20020maAlmlineNetworkLaneFaultEntry 8 }


pm20020maAlmLineLaneRxLosPortn OBJECT-TYPE
	SYNTAX  EkiOnOff
	MAX-ACCESS read-only
	STATUS current
	DESCRIPTION
        "
        Line Network Lane Rx Loss Of Signal
        :This OID indicates a Rx Loss of
        Signal on the Line Trscv Network
        Lane <Help> Alarm indicating a
         Rx Loss of Signal on the Line
         Trscv Network Lane <Condtype>
         LINE_LANE_RX_LOS <Probcause> receiveFailure
        (41) <Alarmtype> physicalViolation
        (9) <Polarity> (2)
        "
	::= { pm20020maAlmlineNetworkLaneFaultEntry 6 }


pm20020maAlmLineLaneRxLolPortn OBJECT-TYPE
	SYNTAX  EkiOnOff
	MAX-ACCESS read-only
	STATUS current
	DESCRIPTION
        "
        Line Network Lane Rx Loss Of Lock
        :This OID indicates a Rx Loss of
        Lock on the Line Trscv Network
         Lane <Help> Alarm indicating a
        Rx Loss of Lock on the Line Trscv
        Network Lane <Condtype> LINE_LANE_RX_LOL
        <Probcause> receiverFailure (42)
        <Alarmtype> equipmentAlarm (5)
         <Polarity> (2)
        "
	::= { pm20020maAlmlineNetworkLaneFaultEntry 5 }


pm20020maAlmLineLaneRxFifoErrorPortn OBJECT-TYPE
	SYNTAX  EkiOnOff
	MAX-ACCESS read-only
	STATUS current
	DESCRIPTION
        "
        Line Network Lane Rx FIFO Error
        :This OID indicates a Rx FIFO Error
        on the Line Trscv Network Lane
         <Help> Alarm indicating a Rx FIFO
        Error on the Line Trscv Network
        Lane <Condtype> LINE_LANE_RX_FIFO_ERROR
        <Probcause> receiverFailure (42)
        <Alarmtype> equipmentAlarm (5)
         <Polarity> (2)
        "
	::= { pm20020maAlmlineNetworkLaneFaultEntry 4 }


pm20020maAlmLineLaneRxTecFaultPortn OBJECT-TYPE
	SYNTAX  EkiOnOff
	MAX-ACCESS read-only
	STATUS current
	DESCRIPTION
        "
        Line Network Lane Rx TEC Fault
        :This OID indicates a Rx TEC Fault
        on the Line Trscv Network Lane
         <Help> Alarm indicating a Rx TEC
        Fault on the Line Trscv Network
        Lane <Condtype> LINE_LANE_RX_TEC_FAULT
        <Probcause> receiverFailure (42)
        <Alarmtype> equipmentAlarm (5)
         <Polarity> (2)
        "
	::= { pm20020maAlmlineNetworkLaneFaultEntry 3 }


--- *********************************************************
---     TABLE for the pm20020maAlmlineHostLaneFault articles
--- *********************************************************

pm20020maAlmlineHostLaneFaultTable OBJECT-TYPE
	SYNTAX  SEQUENCE OF Pm20020maAlmlineHostLaneFaultEntry
	MAX-ACCESS not-accessible
	STATUS current
	DESCRIPTION
        "
        List of pm20020maAlmlineHostLaneFault
        Article
        "
	::= { pm20020maAlmLineUrg 196 }


pm20020maAlmlineHostLaneFaultEntry OBJECT-TYPE
	SYNTAX Pm20020maAlmlineHostLaneFaultEntry
	MAX-ACCESS not-accessible
	STATUS current
	DESCRIPTION
        "
        Row definition for the pm20020maAlmlineHostLaneFault
        table
        "
	INDEX   { pm20020maAlmlineHostLaneFaultIndex }
	::= { pm20020maAlmlineHostLaneFaultTable 1 }


Pm20020maAlmlineHostLaneFaultEntry ::=
	SEQUENCE {
	pm20020maAlmlineHostLaneFaultIndex
		INTEGER,
	pm20020maAlmLineLaneTxFifoErrorPortn
		EkiOnOff,
	pm20020maAlmLineTxHostLolPortn
		EkiOnOff,
	pm20020maAlmLineSmIaeDetectedPortn
		EkiOnOff,
	pm20020maAlmLineSmIaeInsertedPortn
		EkiOnOff,
	pm20020maAlmLineSmBdiDetectedPortn
		EkiOnOff,
	pm20020maAlmLineSmBdiInsertedPortn
		EkiOnOff,
	pm20020maAlmLineLossOfFramePortn
		EkiOnOff,
	pm20020maAlmLineInputLossOfSignalPortn
		EkiOnOff
	}


pm20020maAlmlineHostLaneFaultIndex OBJECT-TYPE
	SYNTAX  INTEGER(0..128)
	MAX-ACCESS  read-only
	STATUS current
	DESCRIPTION
        "
        Index definition for the pm20020maAlmlineHostLaneFault
        table
        "
	::= { pm20020maAlmlineHostLaneFaultEntry 1 }


pm20020maAlmLineLaneTxFifoErrorPortn OBJECT-TYPE
	SYNTAX  EkiOnOff
	MAX-ACCESS read-only
	STATUS current
	DESCRIPTION
        "
        Line Host Lane Tx FIFO Error :This
        OID indicates a Tx FIFO Error on
        the Line Trscv Host Lane <Help>
        Alarm indicating a Tx FIFO Error
        on the Line Trscv Host Lane <Condtype>
        LINE_LANE_TX_FIFO_ERROR <Probcause>
        receiverFailure (42) <Alarmtype>
        equipmentAlarm (5) <Polarity> (2)
        "
	::= { pm20020maAlmlineHostLaneFaultEntry 11 }


pm20020maAlmLineTxHostLolPortn OBJECT-TYPE
	SYNTAX  EkiOnOff
	MAX-ACCESS read-only
	STATUS current
	DESCRIPTION
        "
        Line Host Lane Tx Loss Of Lock
        :This OID indicates a Tx Loss of
        Lock on the Line Trscv Host Lane
        <Help> Alarm indicating a Tx Loss
        of Lock on the Line Trscv Host
         Lane <Condtype> LINE_TX_HOST_LOL
        <Probcause> receiverFailure (42)
        <Alarmtype> equipmentAlarm (5)
         <Polarity> (2)
        "
	::= { pm20020maAlmlineHostLaneFaultEntry 10 }


pm20020maAlmLineSmIaeDetectedPortn OBJECT-TYPE
	SYNTAX  EkiOnOff
	MAX-ACCESS read-only
	STATUS current
	DESCRIPTION
        "
        Line SM IAE Detected :This OID
        indicates a SM Incoming Alignment
        Error is detected on the incoming
        Line signal <Help> Alarm indicating
        a SM Incoming Alignment Error is
        detected on the incoming Line signal
        <Condtype> LINE_SM_IAE_DETECTED
        <Probcause> receiveFailure (41)
        <Alarmtype> integrityViolation
         (7) <Polarity> (2)
        "
	::= { pm20020maAlmlineHostLaneFaultEntry 7 }


pm20020maAlmLineSmIaeInsertedPortn OBJECT-TYPE
	SYNTAX  EkiOnOff
	MAX-ACCESS read-only
	STATUS current
	DESCRIPTION
        "
        Line SM IAE Inserted :This OID
        indicates a SM Incoming Alignment
        Error is inserted on the outgoing
        Line signal <Help> Status indicating
        a SM Incoming Alignment Error is
        inserted on the outgoing Line signal
        <Condtype> LINE_SM_IAE_INSERTED
        <Probcause> informationalStatus(1000)
        <Alarmtype> other (1) <Polarity>
        (2)
        "
	::= { pm20020maAlmlineHostLaneFaultEntry 6 }


pm20020maAlmLineSmBdiDetectedPortn OBJECT-TYPE
	SYNTAX  EkiOnOff
	MAX-ACCESS read-only
	STATUS current
	DESCRIPTION
        "
        Line SM BDI Detected :This OID
        indicates a SM Backward Defect
         Indication is detected on the
         incoming Line signal <Help> Alarm
        indicating a SM Backward Defect
        Indication is detected on the incoming
        Line signal <Condtype> LINE_SM_BDI_DETECTED
        <Probcause> receiveFailure (41)
        <Alarmtype> integrityViolation
         (7) <Polarity> (2)
        "
	::= { pm20020maAlmlineHostLaneFaultEntry 5 }


pm20020maAlmLineSmBdiInsertedPortn OBJECT-TYPE
	SYNTAX  EkiOnOff
	MAX-ACCESS read-only
	STATUS current
	DESCRIPTION
        "
        Line SM BDI Inserted :This OID
        indicates a SM Backward Defect
         Indication is inserted on the
         outgoing Line signal <Help> Status
        indicating a SM Backward Defect
        Indication is inserted on the outgoing
        Line signal <Condtype> LINE_SM_BDI_INSERTED
        <Probcause> informationalStatus(1000)
        <Alarmtype> other (1) <Polarity>
        (2)
        "
	::= { pm20020maAlmlineHostLaneFaultEntry 4 }


pm20020maAlmLineLossOfFramePortn OBJECT-TYPE
	SYNTAX  EkiOnOff
	MAX-ACCESS read-only
	STATUS current
	DESCRIPTION
        "
        Line Loss Of Frame :This OID indicates
        the module is not aligned with
         the incoming Line signal <Help>
        Alarm indicating the module is
         not aligned with the incoming
         Line signal <Condtype> LINE_LOSS_OF_FRAME
        <Probcause> receiveFailure (41)
        <Alarmtype> integrityViolation
         (7) <Polarity> (2)
        "
	::= { pm20020maAlmlineHostLaneFaultEntry 3 }


pm20020maAlmLineInputLossOfSignalPortn OBJECT-TYPE
	SYNTAX  EkiOnOff
	MAX-ACCESS read-only
	STATUS current
	DESCRIPTION
        "
        Line Input Loss Of Signal :This
        OID indicates a Loss of Signal
         is detected on the Line Trscv
         <Help> Alarm indicating a Loss
        of Signal is detected on the Line
        Trscv <Condtype> LINE_INPUT_LOSS_OF_SIGNAL
        <Probcause> receiveFailure (41)
        <Alarmtype> physicalViolation (9)
        <Polarity> (2)
        "
	::= { pm20020maAlmlineHostLaneFaultEntry 2 }


--- *********************************************************
---     TABLE for the pm20020maAlmlineNetworkLaneRxOtn articles
--- *********************************************************

pm20020maAlmlineNetworkLaneRxOtnTable OBJECT-TYPE
	SYNTAX  SEQUENCE OF Pm20020maAlmlineNetworkLaneRxOtnEntry
	MAX-ACCESS not-accessible
	STATUS current
	DESCRIPTION
        "
        List of pm20020maAlmlineNetworkLaneRxOtn
        Article
        "
	::= { pm20020maAlmLineUrg 200 }


pm20020maAlmlineNetworkLaneRxOtnEntry OBJECT-TYPE
	SYNTAX Pm20020maAlmlineNetworkLaneRxOtnEntry
	MAX-ACCESS not-accessible
	STATUS current
	DESCRIPTION
        "
        Row definition for the pm20020maAlmlineNetworkLaneRxOtn
        table
        "
	INDEX   { pm20020maAlmlineNetworkLaneRxOtnIndex }
	::= { pm20020maAlmlineNetworkLaneRxOtnTable 1 }


Pm20020maAlmlineNetworkLaneRxOtnEntry ::=
	SEQUENCE {
	pm20020maAlmlineNetworkLaneRxOtnIndex
		INTEGER,
	pm20020maAlmLineRxOtnLofPortn
		EkiOnOff,
	pm20020maAlmLineRxOtnOofPortn
		EkiOnOff,
	pm20020maAlmLineRxOtnLomPortn
		EkiOnOff,
	pm20020maAlmLineRxOtnOomPortn
		EkiOnOff,
	pm20020maAlmLineRxOtnIaePortn
		EkiOnOff,
	pm20020maAlmLineRxSmBdiPortn
		EkiOnOff,
	pm20020maAlmLineRxOtnOtuAisPortn
		EkiOnOff,
	pm20020maAlmLineRxOtnOduAisPortn
		EkiOnOff
	}


pm20020maAlmlineNetworkLaneRxOtnIndex OBJECT-TYPE
	SYNTAX  INTEGER(0..128)
	MAX-ACCESS  read-only
	STATUS current
	DESCRIPTION
        "
        Index definition for the pm20020maAlmlineNetworkLaneRxOtn
        table
        "
	::= { pm20020maAlmlineNetworkLaneRxOtnEntry 1 }


pm20020maAlmLineRxOtnLofPortn OBJECT-TYPE
	SYNTAX  EkiOnOff
	MAX-ACCESS read-only
	STATUS current
	DESCRIPTION
        "
        Line Network Rx LOF :This OID
         indicates a Loss of Frame is detected
        on the Rx Network interface of
         the Line Trscv <Help> Alarm indicating
        a Loss of Frame is detected on
         the Rx Network interface of the
        Line Trscv <Condtype> LINE_RX_OTN_LOF
        <Probcause> receiveFailure (41)
        <Alarmtype> equipmentAlarm (5)
         <Polarity> (2)
        "
	::= { pm20020maAlmlineNetworkLaneRxOtnEntry 17 }


pm20020maAlmLineRxOtnOofPortn OBJECT-TYPE
	SYNTAX  EkiOnOff
	MAX-ACCESS read-only
	STATUS current
	DESCRIPTION
        "
        Line Network Rx OOF :This OID
         indicates an Out of Frame is detected
        on the Rx Network interface of
         the Line Trscv <Help> Alarm indicating
        an Out of Frame is detected on
         the Rx Network interface of the
        Line Trscv <Condtype> LINE_RX_OTN_OOF
        <Probcause> receiveFailure (41)
        <Alarmtype> equipmentAlarm (5)
         <Polarity> (2)
        "
	::= { pm20020maAlmlineNetworkLaneRxOtnEntry 16 }


pm20020maAlmLineRxOtnLomPortn OBJECT-TYPE
	SYNTAX  EkiOnOff
	MAX-ACCESS read-only
	STATUS current
	DESCRIPTION
        "
        Line Network Rx LOM :This OID
         indicates a Loss of Multiframe
        is detected on the Rx Network interface
        of the Line Trscv <Help> Alarm
         indicating a Loss of Multiframe
        is detected on the Rx Network interface
        of the Line Trscv <Condtype> LINE_RX_OTN_LOM
        <Probcause> receiveFailure (41)
        <Alarmtype> equipmentAlarm (5)
         <Polarity> (2)
        "
	::= { pm20020maAlmlineNetworkLaneRxOtnEntry 15 }


pm20020maAlmLineRxOtnOomPortn OBJECT-TYPE
	SYNTAX  EkiOnOff
	MAX-ACCESS read-only
	STATUS current
	DESCRIPTION
        "
        Line Network Rx OOM :This OID
         indicates an Out of Multiframe
        is detected on the Rx Network interface
        of the Line Trscv <Help> Alarm
         indicating an Out of Multiframe
        is detected on the Rx Network interface
        of the Line Trscv <Condtype> LINE_RX_OTN_OOM
        <Probcause> receiveFailure (41)
        <Alarmtype> equipmentAlarm (5)
         <Polarity> (2)
        "
	::= { pm20020maAlmlineNetworkLaneRxOtnEntry 14 }


pm20020maAlmLineRxOtnIaePortn OBJECT-TYPE
	SYNTAX  EkiOnOff
	MAX-ACCESS read-only
	STATUS current
	DESCRIPTION
        "
        Line Network Rx IAE :This OID
         indicates an Incoming Alignment
        Error is detected on the Rx Network
        interface of the Line Trscv <Help>
        Alarm indicating an Incoming Alignment
        Error is detected on the Rx Network
        interface of the Line Trscv <Condtype>
        LINE_RX_OTN_IAE <Probcause> receiveFailure
        (41) <Alarmtype> equipmentAlarm
        (5) <Polarity> (2)
        "
	::= { pm20020maAlmlineNetworkLaneRxOtnEntry 13 }


pm20020maAlmLineRxSmBdiPortn OBJECT-TYPE
	SYNTAX  EkiOnOff
	MAX-ACCESS read-only
	STATUS current
	DESCRIPTION
        "
        Line Network Rx SM BDI :This OID
        indicates an SM Backward Defect
        Indication is detected on the Rx
        Network interface of the Line Trscv
        <Help> Alarm indicating an SM Backward
        Defect Indication is detected on
        the Rx Network interface of the
        Line Trscv <Condtype> LINE_RX_SM_BDI
        <Probcause> informationalStatus(1000)
        <Alarmtype> other (1) <Polarity>
        (2)
        "
	::= { pm20020maAlmlineNetworkLaneRxOtnEntry 12 }


pm20020maAlmLineRxOtnOtuAisPortn OBJECT-TYPE
	SYNTAX  EkiOnOff
	MAX-ACCESS read-only
	STATUS current
	DESCRIPTION
        "
        Line Network Rx OTU AIS :This
         OID indicates an OTU This OID
         Indication Signal is detected
         on the Rx Network interface of
        the Line Trscv <Help> Alarm indicating
        an OTU Alarm Indication Signal
         is detected on the Rx Network
         interface of the Line Trscv <Condtype>
        LINE_RX_OTN_OTU_AIS <Probcause>
        receiveFailure (41) <Alarmtype>
        equipmentAlarm (5) <Polarity> (2)
        "
	::= { pm20020maAlmlineNetworkLaneRxOtnEntry 11 }


pm20020maAlmLineRxOtnOduAisPortn OBJECT-TYPE
	SYNTAX  EkiOnOff
	MAX-ACCESS read-only
	STATUS current
	DESCRIPTION
        "
        Line Network Rx ODU AIS :This
         OID indicates an ODU This OID
         Indication Signal is detected
         on the Rx Network interface of
        the Line Trscv <Help> Alarm indicating
        an ODU Alarm Indication Signal
         is detected on the Rx Network
         interface of the Line Trscv <Condtype>
        LINE_RX_OTN_ODU_AIS <Probcause>
        receiveFailure (41) <Alarmtype>
        equipmentAlarm (5) <Polarity> (2)
        "
	::= { pm20020maAlmlineNetworkLaneRxOtnEntry 10 }


--- *********************************************************
---     TABLE for the pm20020maAlmlineHostLaneTxOtn articles
--- *********************************************************

pm20020maAlmlineHostLaneTxOtnTable OBJECT-TYPE
	SYNTAX  SEQUENCE OF Pm20020maAlmlineHostLaneTxOtnEntry
	MAX-ACCESS not-accessible
	STATUS current
	DESCRIPTION
        "
        List of pm20020maAlmlineHostLaneTxOtn
        Article
        "
	::= { pm20020maAlmLineUrg 204 }


pm20020maAlmlineHostLaneTxOtnEntry OBJECT-TYPE
	SYNTAX Pm20020maAlmlineHostLaneTxOtnEntry
	MAX-ACCESS not-accessible
	STATUS current
	DESCRIPTION
        "
        Row definition for the pm20020maAlmlineHostLaneTxOtn
        table
        "
	INDEX   { pm20020maAlmlineHostLaneTxOtnIndex }
	::= { pm20020maAlmlineHostLaneTxOtnTable 1 }


Pm20020maAlmlineHostLaneTxOtnEntry ::=
	SEQUENCE {
	pm20020maAlmlineHostLaneTxOtnIndex
		INTEGER,
	pm20020maAlmLineTxOtnLofPortn
		EkiOnOff,
	pm20020maAlmLineTxOtnOofPortn
		EkiOnOff,
	pm20020maAlmLineTxOtnLomPortn
		EkiOnOff,
	pm20020maAlmLineTxOtnOomPortn
		EkiOnOff,
	pm20020maAlmLineTxOtnIaePortn
		EkiOnOff,
	pm20020maAlmLineTxSmBdiPortn
		EkiOnOff,
	pm20020maAlmLineTxOtnOtuAisPortn
		EkiOnOff,
	pm20020maAlmLineTxOtnOduAisPortn
		EkiOnOff
	}


pm20020maAlmlineHostLaneTxOtnIndex OBJECT-TYPE
	SYNTAX  INTEGER(0..128)
	MAX-ACCESS  read-only
	STATUS current
	DESCRIPTION
        "
        Index definition for the pm20020maAlmlineHostLaneTxOtn
        table
        "
	::= { pm20020maAlmlineHostLaneTxOtnEntry 1 }


pm20020maAlmLineTxOtnLofPortn OBJECT-TYPE
	SYNTAX  EkiOnOff
	MAX-ACCESS read-only
	STATUS current
	DESCRIPTION
        "
        Line Host Tx LOF :This OID indicates
        a Loss of Frame is detected on
         the Tx Host interface of the Line
        Trscv <Help> Alarm indicating a
        Loss of Frame is detected on the
        Tx Host interface of the Line Trscv
        <Condtype> LINE_TX_OTN_LOF <Probcause>
        receiveFailure (41) <Alarmtype>
        equipmentAlarm (5) <Polarity> (2)
        "
	::= { pm20020maAlmlineHostLaneTxOtnEntry 17 }


pm20020maAlmLineTxOtnOofPortn OBJECT-TYPE
	SYNTAX  EkiOnOff
	MAX-ACCESS read-only
	STATUS current
	DESCRIPTION
        "
        Line Host Tx OOF :This OID indicates
        an Out of Frame is detected on
         the Tx Host interface of the Line
        Trscv <Help> Alarm indicating an
        Out of Frame is detected on the
        Tx Host interface of the Line Trscv
        <Condtype> LINE_TX_OTN_OOF <Probcause>
        receiveFailure (41) <Alarmtype>
        equipmentAlarm (5) <Polarity> (2)
        "
	::= { pm20020maAlmlineHostLaneTxOtnEntry 16 }


pm20020maAlmLineTxOtnLomPortn OBJECT-TYPE
	SYNTAX  EkiOnOff
	MAX-ACCESS read-only
	STATUS current
	DESCRIPTION
        "
        Line Host Tx LOM :This OID indicates
        a Loss of Multiframe is detected
        on the Tx Host interface of the
        Line Trscv <Help> Alarm indicating
        a Loss of Multiframe is detected
        on the Tx Host interface of the
        Line Trscv <Condtype> LINE_TX_OTN_LOM
        <Probcause> receiveFailure (41)
        <Alarmtype> equipmentAlarm (5)
         <Polarity> (2)
        "
	::= { pm20020maAlmlineHostLaneTxOtnEntry 15 }


pm20020maAlmLineTxOtnOomPortn OBJECT-TYPE
	SYNTAX  EkiOnOff
	MAX-ACCESS read-only
	STATUS current
	DESCRIPTION
        "
        Line Host Tx OOM :This OID indicates
        an Out of Multiframe is detected
        on the Tx Host interface of the
        Line Trscv <Help> Alarm indicating
        an Out of Multiframe is detected
        on the Tx Host interface of the
        Line Trscv <Condtype> LINE_TX_OTN_OOM
        <Probcause> receiveFailure (41)
        <Alarmtype> equipmentAlarm (5)
         <Polarity> (2)
        "
	::= { pm20020maAlmlineHostLaneTxOtnEntry 14 }


pm20020maAlmLineTxOtnIaePortn OBJECT-TYPE
	SYNTAX  EkiOnOff
	MAX-ACCESS read-only
	STATUS current
	DESCRIPTION
        "
        Line Host Tx IAE :This OID indicates
        an Incoming Alignment Error is
         detected on the Tx Host interface
        of the Line Trscv <Help> Alarm
         indicating an Incoming Alignment
        Error is detected on the Tx Host
        interface of the Line Trscv <Condtype>
        LINE_TX_OTN_IAE <Probcause> receiveFailure
        (41) <Alarmtype> equipmentAlarm
        (5) <Polarity> (2)
        "
	::= { pm20020maAlmlineHostLaneTxOtnEntry 13 }


pm20020maAlmLineTxSmBdiPortn OBJECT-TYPE
	SYNTAX  EkiOnOff
	MAX-ACCESS read-only
	STATUS current
	DESCRIPTION
        "
        Line Host Tx SM BDI :This OID
         indicates an SM Backward Defect
        Indication is detected on the Tx
        Host interface of the Line Trscv
        <Help> Alarm indicating an SM Backward
        Defect Indication is detected on
        the Tx Host interface of the Line
        Trscv <Condtype> LINE_TX_SM_BDI
        <Probcause> informationalStatus(1000)
        <Alarmtype> other (1) <Polarity>
        (2)
        "
	::= { pm20020maAlmlineHostLaneTxOtnEntry 12 }


pm20020maAlmLineTxOtnOtuAisPortn OBJECT-TYPE
	SYNTAX  EkiOnOff
	MAX-ACCESS read-only
	STATUS current
	DESCRIPTION
        "
        Line Host Tx OTU AIS :This OID
        indicates an OTU This OID Indication
        Signal is detected on the Tx Host
        interface of the Line Trscv <Help>
        Alarm indicating an OTU Alarm Indication
        Signal is detected on the Tx Host
        interface of the Line Trscv <Condtype>
        LINE_TX_OTN_OTU_AIS <Probcause>
        receiveFailure (41) <Alarmtype>
        equipmentAlarm (5) <Polarity> (2)
        "
	::= { pm20020maAlmlineHostLaneTxOtnEntry 11 }


pm20020maAlmLineTxOtnOduAisPortn OBJECT-TYPE
	SYNTAX  EkiOnOff
	MAX-ACCESS read-only
	STATUS current
	DESCRIPTION
        "
        Line Host Tx ODU AIS :This OID
        indicates an ODU This OID Indication
        Signal is detected on the Tx Host
        interface of the Line Trscv <Help>
        Alarm indicating an ODU Alarm Indication
        Signal is detected on the Tx Host
        interface of the Line Trscv <Condtype>
        LINE_TX_OTN_ODU_AIS <Probcause>
        receiveFailure (41) <Alarmtype>
        equipmentAlarm (5) <Polarity> (2)
        "
	::= { pm20020maAlmlineHostLaneTxOtnEntry 10 }


--- *********************************************************
---     TABLE for the pm20020maAlmclientSfpAlmDdm articles
--- *********************************************************

pm20020maAlmclientSfpAlmDdmTable OBJECT-TYPE
	SYNTAX  SEQUENCE OF Pm20020maAlmclientSfpAlmDdmEntry
	MAX-ACCESS not-accessible
	STATUS current
	DESCRIPTION
        "
        List of pm20020maAlmclientSfpAlmDdm
        Article
        "
	::= { pm20020maAlmClientUrg 240 }


pm20020maAlmclientSfpAlmDdmEntry OBJECT-TYPE
	SYNTAX Pm20020maAlmclientSfpAlmDdmEntry
	MAX-ACCESS not-accessible
	STATUS current
	DESCRIPTION
        "
        Row definition for the pm20020maAlmclientSfpAlmDdm
        table
        "
	INDEX   { pm20020maAlmclientSfpAlmDdmIndex }
	::= { pm20020maAlmclientSfpAlmDdmTable 1 }


Pm20020maAlmclientSfpAlmDdmEntry ::=
	SEQUENCE {
	pm20020maAlmclientSfpAlmDdmIndex
		INTEGER,
	pm20020maAlmRxPwrHighAlaPortn
		EkiOnOff,
	pm20020maAlmRxPwrLowAlaPortn
		EkiOnOff,
	pm20020maAlmTempHighAlaPortn
		EkiOnOff,
	pm20020maAlmTempLowAlaPortn
		EkiOnOff,
	pm20020maAlmVccHighAlaPortn
		EkiOnOff,
	pm20020maAlmVccLowAlaPortn
		EkiOnOff,
	pm20020maAlmTxBiasHighAlaPortn
		EkiOnOff,
	pm20020maAlmTxBiasLowAlaPortn
		EkiOnOff,
	pm20020maAlmTxPwrHighAlaPortn
		EkiOnOff,
	pm20020maAlmTxPwrLowAlaPortn
		EkiOnOff
	}


pm20020maAlmclientSfpAlmDdmIndex OBJECT-TYPE
	SYNTAX  INTEGER(0..128)
	MAX-ACCESS  read-only
	STATUS current
	DESCRIPTION
        "
        Index definition for the pm20020maAlmclientSfpAlmDdm
        table
        "
	::= { pm20020maAlmclientSfpAlmDdmEntry 1 }


pm20020maAlmRxPwrHighAlaPortn OBJECT-TYPE
	SYNTAX  EkiOnOff
	MAX-ACCESS read-only
	STATUS current
	DESCRIPTION
        "
        Client Trscv Rx Power High :This
        OID indicates that the Trscv input
        power of port is higher than the
        threshold value written in the
         Trscv EEPROM <Help> Alarm indicating
        that the Trscv input power of port
        is higher than the threshold value
        written in the Trscv EEPROM <Condtype>
        RX_PWR_HIGH_ALA_1 <Probcause> receiveFailure
        (41) <Alarmtype> equipmentAlarm
        (5) <Polarity> (2)
        "
	::= { pm20020maAlmclientSfpAlmDdmEntry 17 }


pm20020maAlmRxPwrLowAlaPortn OBJECT-TYPE
	SYNTAX  EkiOnOff
	MAX-ACCESS read-only
	STATUS current
	DESCRIPTION
        "
        Client Trscv Rx Power Low :This
        OID indicates that the Trscv input
        power of port is lower than the
        threshold value written in the
         Trscv EEPROM <Help> Alarm indicating
        that the Trscv input power of port
        is lower than the threshold value
        written in the Trscv EEPROM <Condtype>
        RX_PWR_LOW_ALA_1 <Probcause> receiveFailure
        (41) <Alarmtype> equipmentAlarm
        (5) <Polarity> (2)
        "
	::= { pm20020maAlmclientSfpAlmDdmEntry 16 }


pm20020maAlmTempHighAlaPortn OBJECT-TYPE
	SYNTAX  EkiOnOff
	MAX-ACCESS read-only
	STATUS current
	DESCRIPTION
        "
        Client Trscv Temp High :This OID
        indicates that the Trscv temperature
        of port is higher than the threshold
        value written in the Trscv EEPROM
        <Help> Alarm indicating that the
        Trscv temperature of port is higher
        than the threshold value written
        in the Trscv EEPROM <Condtype>
         TEMP_HIGH_ALA_1 <Probcause> temperatureUnacceptable
        (51) <Alarmtype> equipmentAlarm
        (5) <Polarity> (2)
        "
	::= { pm20020maAlmclientSfpAlmDdmEntry 9 }


pm20020maAlmTempLowAlaPortn OBJECT-TYPE
	SYNTAX  EkiOnOff
	MAX-ACCESS read-only
	STATUS current
	DESCRIPTION
        "
        Client Trscv Temp Low :This OID
        indicates that the Trscv temperature
        of port is lower than the threshold
        value written in the Trscv EEPROM
        <Help> Alarm indicating that the
        Trscv temperature of port is lower
        than the threshold value written
        in the Trscv EEPROM <Condtype>
         TEMP_LOW_ALA_1 <Probcause> temperatureUnacceptable
        (51) <Alarmtype> equipmentAlarm
        (5) <Polarity> (2)
        "
	::= { pm20020maAlmclientSfpAlmDdmEntry 8 }


pm20020maAlmVccHighAlaPortn OBJECT-TYPE
	SYNTAX  EkiOnOff
	MAX-ACCESS read-only
	STATUS current
	DESCRIPTION
        "
        Client Trscv Power Supply High
        :This OID indicates that the Trscv
        power supply of port is higher
         than the threshold value written
        in the Trscv EEPROM <Help> Alarm
        indicating that the Trscv power
        supply of port is higher than the
        threshold value written in the
         Trscv EEPROM <Condtype> VCC_HIGH_ALA_1
        <Probcause> powerProblem (36) <Alarmtype>
        equipmentAlarm (5) <Polarity> (2)
        "
	::= { pm20020maAlmclientSfpAlmDdmEntry 7 }


pm20020maAlmVccLowAlaPortn OBJECT-TYPE
	SYNTAX  EkiOnOff
	MAX-ACCESS read-only
	STATUS current
	DESCRIPTION
        "
        Client Trscv Power Supply Low
         :This OID indicates that the Trscv
        power supply of port is lower than
        the threshold value written in
         the Trscv EEPROM <Help> Alarm
         indicating that the Trscv power
        supply of port is lower than the
        threshold value written in the
         Trscv EEPROM <Condtype> VCC_LOW_ALA_1
        <Probcause> powerProblem (36) <Alarmtype>
        equipmentAlarm (5) <Polarity> (2)
        "
	::= { pm20020maAlmclientSfpAlmDdmEntry 6 }


pm20020maAlmTxBiasHighAlaPortn OBJECT-TYPE
	SYNTAX  EkiOnOff
	MAX-ACCESS read-only
	STATUS current
	DESCRIPTION
        "
        Client Trscv Bias High :This OID
        indicates that the Trscv laser
         bias current of port is higher
        than the threshold value written
        in the Trscv EEPROM <Help> Alarm
        indicating that the Trscv laser
        bias current of port is higher
         than the threshold value written
        in the Trscv EEPROM <Condtype>
         TX_BIAS_HIGH_ALA_1 <Probcause>
        transmitterFailure (56) <Alarmtype>
        equipmentAlarm (5) <Polarity> (2)
        "
	::= { pm20020maAlmclientSfpAlmDdmEntry 5 }


pm20020maAlmTxBiasLowAlaPortn OBJECT-TYPE
	SYNTAX  EkiOnOff
	MAX-ACCESS read-only
	STATUS current
	DESCRIPTION
        "
        Client Trscv Bias Low :This OID
        indicates that the Trscv laser
         bias current of port is lower
         than the threshold value written
        in the Trscv EEPROM <Help> Alarm
        indicating that the Trscv laser
        bias current of port is lower than
        the threshold value written in
         the Trscv EEPROM <Condtype> TX_BIAS_LOW_ALA_1
        <Probcause> transmitterFailure
         (56) <Alarmtype> equipmentAlarm
        (5) <Polarity> (2)
        "
	::= { pm20020maAlmclientSfpAlmDdmEntry 4 }


pm20020maAlmTxPwrHighAlaPortn OBJECT-TYPE
	SYNTAX  EkiOnOff
	MAX-ACCESS read-only
	STATUS current
	DESCRIPTION
        "
        Client Trscv Tx Power High :This
        OID indicates that the Trscv output
        power of port is higher than the
        threshold value written in the
         Trscv EEPROM <Help> Alarm indicating
        that the Trscv output power of
         port is higher than the threshold
        value written in the Trscv EEPROM
        <Condtype> TX_PWR_HIGH_ALA_1 <Probcause>
        transmitterFailure (56) <Alarmtype>
        equipmentAlarm (5) <Polarity> (2)
        "
	::= { pm20020maAlmclientSfpAlmDdmEntry 3 }


pm20020maAlmTxPwrLowAlaPortn OBJECT-TYPE
	SYNTAX  EkiOnOff
	MAX-ACCESS read-only
	STATUS current
	DESCRIPTION
        "
        Client Trscv Tx Power Low :This
        OID indicates that the Trscv output
        power of port is lower than the
        threshold value written in the
         Trscv EEPROM <Help> Alarm indicating
        that the Trscv output power of
         port is lower than the threshold
        value written in the Trscv EEPROM
        <Condtype> TX_PWR_LOW_ALA_1 <Probcause>
        transmitterFailure (56) <Alarmtype>
        equipmentAlarm (5) <Polarity> (2)
        "
	::= { pm20020maAlmclientSfpAlmDdmEntry 2 }


--- *********************************************************
---     TABLE for the pm20020maAlmclientSfpWarnDdm articles
--- *********************************************************

pm20020maAlmclientSfpWarnDdmTable OBJECT-TYPE
	SYNTAX  SEQUENCE OF Pm20020maAlmclientSfpWarnDdmEntry
	MAX-ACCESS not-accessible
	STATUS current
	DESCRIPTION
        "
        List of pm20020maAlmclientSfpWarnDdm
        Article
        "
	::= { pm20020maAlmClientNurg 272 }


pm20020maAlmclientSfpWarnDdmEntry OBJECT-TYPE
	SYNTAX Pm20020maAlmclientSfpWarnDdmEntry
	MAX-ACCESS not-accessible
	STATUS current
	DESCRIPTION
        "
        Row definition for the pm20020maAlmclientSfpWarnDdm
        table
        "
	INDEX   { pm20020maAlmclientSfpWarnDdmIndex }
	::= { pm20020maAlmclientSfpWarnDdmTable 1 }


Pm20020maAlmclientSfpWarnDdmEntry ::=
	SEQUENCE {
	pm20020maAlmclientSfpWarnDdmIndex
		INTEGER,
	pm20020maAlmRxPwrHighWngPortn
		EkiOnOff,
	pm20020maAlmRxPwrLowWngPortn
		EkiOnOff,
	pm20020maAlmTempHighWngPortn
		EkiOnOff,
	pm20020maAlmTempLowWngPortn
		EkiOnOff,
	pm20020maAlmVccHighWngPortn
		EkiOnOff,
	pm20020maAlmVccLowWngPortn
		EkiOnOff,
	pm20020maAlmTxBiasHighWngPortn
		EkiOnOff,
	pm20020maAlmTxBiasLowWngPortn
		EkiOnOff,
	pm20020maAlmTxPwrHighWngPortn
		EkiOnOff,
	pm20020maAlmTxPwLowWngPortn
		EkiOnOff
	}


pm20020maAlmclientSfpWarnDdmIndex OBJECT-TYPE
	SYNTAX  INTEGER(0..128)
	MAX-ACCESS  read-only
	STATUS current
	DESCRIPTION
        "
        Index definition for the pm20020maAlmclientSfpWarnDdm
        table
        "
	::= { pm20020maAlmclientSfpWarnDdmEntry 1 }


pm20020maAlmRxPwrHighWngPortn OBJECT-TYPE
	SYNTAX  EkiOnOff
	MAX-ACCESS read-only
	STATUS current
	DESCRIPTION
        "
        Client Trscv Rx Power High Warning
        :This OID indicates that the Trscv
        input power is higher than the
         threshold value written in the
        Trscv EEPROM <Help> Warning indicating
        that the Trscv input power is higher
        than the threshold value written
        in the Trscv EEPROM <Condtype>
         RX_PWR_HIGH_WNG_1 <Probcause>
         receiveFailure (41) <Alarmtype>
        equipmentAlarm (5) <Polarity> (2)
        "
	::= { pm20020maAlmclientSfpWarnDdmEntry 17 }


pm20020maAlmRxPwrLowWngPortn OBJECT-TYPE
	SYNTAX  EkiOnOff
	MAX-ACCESS read-only
	STATUS current
	DESCRIPTION
        "
        Client Trscv Rx Power Low Warning
        :This OID indicates that the Trscv
        input power is lower than the threshold
        value written in the Trscv EEPROM
        <Help> Warning indicating that
         the Trscv input power is lower
        than the threshold value written
        in the Trscv EEPROM <Condtype>
         RX_PWR_LOW_WNG_1 <Probcause> receiveFailure
        (41) <Alarmtype> equipmentAlarm
        (5) <Polarity> (2)
        "
	::= { pm20020maAlmclientSfpWarnDdmEntry 16 }


pm20020maAlmTempHighWngPortn OBJECT-TYPE
	SYNTAX  EkiOnOff
	MAX-ACCESS read-only
	STATUS current
	DESCRIPTION
        "
        Client Trscv Temp High Warning
        :This OID indicates that the Trscv
        temperature is higher than the
         threshold value written in the
        Trscv EEPROM <Help> Warning indicating
        that the Trscv temperature is higher
        than the threshold value written
        in the Trscv EEPROM <Condtype>
         TEMP_HIGH_WNG_1 <Probcause> temperatureUnacceptable
        (51) <Alarmtype> equipmentAlarm
        (5) <Polarity> (2)
        "
	::= { pm20020maAlmclientSfpWarnDdmEntry 9 }


pm20020maAlmTempLowWngPortn OBJECT-TYPE
	SYNTAX  EkiOnOff
	MAX-ACCESS read-only
	STATUS current
	DESCRIPTION
        "
        Client Trscv Temp Low Warning
         :This OID indicates that the Trscv
        temperature is lower than the threshold
        value written in the Trscv EEPROM
        <Help> Warning indicating that
         the Trscv temperature is lower
        than the threshold value written
        in the Trscv EEPROM <Condtype>
         TEMP_LOW_WNG_1 <Probcause> temperatureUnacceptable
        (51) <Alarmtype> equipmentAlarm
        (5) <Polarity> (2)
        "
	::= { pm20020maAlmclientSfpWarnDdmEntry 8 }


pm20020maAlmVccHighWngPortn OBJECT-TYPE
	SYNTAX  EkiOnOff
	MAX-ACCESS read-only
	STATUS current
	DESCRIPTION
        "
        Client Trscv Power Supply High
        Warning :This OID indicates that
        the Trscv power supply is higher
        than the threshold value written
        in the Trscv EEPROM <Help> Warning
        indicating that the Trscv power
        supply is higher than the threshold
        value written in the Trscv EEPROM
        <Condtype> VCC_HIGH_WNG_1 <Probcause>
        powerProblem (36) <Alarmtype> equipmentAlarm
        (5) <Polarity> (2)
        "
	::= { pm20020maAlmclientSfpWarnDdmEntry 7 }


pm20020maAlmVccLowWngPortn OBJECT-TYPE
	SYNTAX  EkiOnOff
	MAX-ACCESS read-only
	STATUS current
	DESCRIPTION
        "
        Client Trscv Power Supply Low
         Warning :This OID indicates that
        the Trscv power supply is lower
        than the threshold value written
        in the Trscv EEPROM <Help> Warning
        indicating that the Trscv power
        supply is lower than the threshold
        value written in the Trscv EEPROM
        <Condtype> VCC_LOW_WNG_1 <Probcause>
        powerProblem (36) <Alarmtype> equipmentAlarm
        (5) <Polarity> (2)
        "
	::= { pm20020maAlmclientSfpWarnDdmEntry 6 }


pm20020maAlmTxBiasHighWngPortn OBJECT-TYPE
	SYNTAX  EkiOnOff
	MAX-ACCESS read-only
	STATUS current
	DESCRIPTION
        "
        Client Trscv Bias High Warning
        :This OID indicates that the Trscv
        laser bias current is higher than
        the threshold value written in
         the Trscv EEPROM <Help> Warning
        indicating that the Trscv laser
        bias current is higher than the
        threshold value written in the
         Trscv EEPROM <Condtype> TX_BIAS_HIGH_WNG_1
        <Probcause> transmitterFailure
         (56) <Alarmtype> equipmentAlarm
        (5) <Polarity> (2)
        "
	::= { pm20020maAlmclientSfpWarnDdmEntry 5 }


pm20020maAlmTxBiasLowWngPortn OBJECT-TYPE
	SYNTAX  EkiOnOff
	MAX-ACCESS read-only
	STATUS current
	DESCRIPTION
        "
        Client Trscv Bias Low Warning
         :This OID indicates that the Trscv
        laser bias current is lower than
        the threshold value written in
         the Trscv EEPROM <Help> Warning
        indicating that the Trscv laser
        bias current is lower than the
         threshold value written in the
        Trscv EEPROM <Condtype> TX_BIAS_LOW_WNG_1
        <Probcause> transmitterFailure
         (56) <Alarmtype> equipmentAlarm
        (5) <Polarity> (2)
        "
	::= { pm20020maAlmclientSfpWarnDdmEntry 4 }


pm20020maAlmTxPwrHighWngPortn OBJECT-TYPE
	SYNTAX  EkiOnOff
	MAX-ACCESS read-only
	STATUS current
	DESCRIPTION
        "
        Client Trscv Tx Power High Warning
        :This OID indicates that the Trscv
        output power is higher than the
        threshold value written in the
         Trscv EEPROM <Help> Warning indicating
        that the Trscv output power is
         higher than the threshold value
        written in the Trscv EEPROM <Condtype>
        TX_PWR_HIGH_WNG_1 <Probcause> transmitterFailure
        (56) <Alarmtype> equipmentAlarm
        (5) <Polarity> (2)
        "
	::= { pm20020maAlmclientSfpWarnDdmEntry 3 }


pm20020maAlmTxPwLowWngPortn OBJECT-TYPE
	SYNTAX  EkiOnOff
	MAX-ACCESS read-only
	STATUS current
	DESCRIPTION
        "
        Client Trscv Tx Power Low Warning
        :This OID indicates that the Trscv
        output power is lower than the
         threshold value written in the
        Trscv EEPROM <Help> Warning indicating
        that the Trscv output power is
         lower than the threshold value
        written in the Trscv EEPROM <Condtype>
        TX_PW_LOW_WNG_1 <Probcause> transmitterFailure
        (56) <Alarmtype> equipmentAlarm
        (5) <Polarity> (2)
        "
	::= { pm20020maAlmclientSfpWarnDdmEntry 2 }


--- *****************************************************
---     LEAF for the modFanFail article
--- *****************************************************
pm20020maAlmmodFanFail OBJECT IDENTIFIER ::= { pm20020maAlmOtherUrg 336 }




pm20020maAlmFanHighSpeed OBJECT-TYPE
	  SYNTAX EkiOnOff
	  MAX-ACCESS read-only
	  STATUS current
	  DESCRIPTION
        "
        Fan High Speed :This OID indicates
        the fan is blowing at high speed
        <Help> This alarm indicates the
        fan is blowing at high speed <Condtype>
        FAN_HIGH_SPEED <Probcause> other
        (1) <Alarmtype> other (1) <Polarity>
        (2)
        "
	  ::= { pm20020maAlmmodFanFail 2 }



pm20020maAlmFanFail OBJECT-TYPE
	  SYNTAX EkiOnOff
	  MAX-ACCESS read-only
	  STATUS current
	  DESCRIPTION
        "
        Fan Module Failure :This OID indicates
        that the FAN unit inside the module
        is in fail condition  <Help>  This
        alarm indicates that the FAN is
        in a fail condition. <Condtype>
        FAN_FAIL <Probcause> heatingVentCoolingSystemProblem
        (22) <Alarmtype> equipmentAlarm
        (5) <Polarity> (2)
        "
	  ::= { pm20020maAlmmodFanFail 1 }








--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pm20020maCtrlconfMgnt1 OBJECT IDENTIFIER ::= { pm20020maCtrlOther 1 }




pm20020maCtrlConf2Clear1 OBJECT-TYPE
	  SYNTAX EkiOnOff
	  MAX-ACCESS read-write
	  STATUS current
	  DESCRIPTION
        "
        Clear Configuration Tables :This
        OID clears the configuration tables
        from configuration2 in the flash.
         <Help>  This control restores
         the default configuration of the
        module
        "
	  ::= { pm20020maCtrlconfMgnt1 14 }



pm20020maCtrlConf2Flash1 OBJECT-TYPE
	  SYNTAX EkiOnOff
	  MAX-ACCESS read-write
	  STATUS current
	  DESCRIPTION
        "
        Write Configuration Tables :This
        OID saves the current configuration
        of the PM as configuration2 in
         the flash.  <Help>  This control
        saves the customer configuration
        on the module
        "
	  ::= { pm20020maCtrlconfMgnt1 10 }



pm20020maCtrlConf2Load1 OBJECT-TYPE
	  SYNTAX EkiOnOff
	  MAX-ACCESS read-write
	  STATUS current
	  DESCRIPTION
        "
        Load Configuration Tables Set
         Nb 2 :When set this OID enables
        loading from flash configuration2
        into the PM.
        "
	  ::= { pm20020maCtrlconfMgnt1 2 }



pm20020maCtrlConf1Load1 OBJECT-TYPE
	  SYNTAX EkiOnOff
	  MAX-ACCESS read-write
	  STATUS current
	  DESCRIPTION
        "
        Load Configuration Tables Set
         Nb 1 :When set this OID enables
        loading from flash configuration1
        into the PM.
        "
	  ::= { pm20020maCtrlconfMgnt1 1 }



--- *****************************************************
---     LEAF for the synth4 article
--- *****************************************************
pm20020maCtrlsynth4 OBJECT IDENTIFIER ::= { pm20020maCtrlOther 4 }




pm20020maCtrlCorrelatOff OBJECT-TYPE
	  SYNTAX EkiOnOff
	  MAX-ACCESS read-write
	  STATUS current
	  DESCRIPTION
        "
        Disable Alarm Correlation :This
        OID disables the alarm correlation
        in the PM.
        "
	  ::= { pm20020maCtrlsynth4 2 }



pm20020maCtrlCorrelatOn OBJECT-TYPE
	  SYNTAX EkiOnOff
	  MAX-ACCESS read-write
	  STATUS current
	  DESCRIPTION
        "
        Enable Alarm Correlation :This
        OID enables the alarm correlation
        in the PM.
        "
	  ::= { pm20020maCtrlsynth4 1 }



--- *****************************************************
---     LEAF for the swMgnt article
--- *****************************************************
pm20020maCtrlswMgnt OBJECT IDENTIFIER ::= { pm20020maCtrlOther 5 }




pm20020maCtrlLoadSwBank2 OBJECT-TYPE
	  SYNTAX EkiOnOff
	  MAX-ACCESS read-write
	  STATUS current
	  DESCRIPTION
        "
        Set Software Nb 2 As Active :This
        OID, when set, loads the SW from
        bank2 into the PM. It must be followed
        by a reset.  <Help>  This controls
        selects the second SW bank as the
        active bank for the next module
        reset
        "
	  ::= { pm20020maCtrlswMgnt 6 }



pm20020maCtrlLoadSwBank1 OBJECT-TYPE
	  SYNTAX EkiOnOff
	  MAX-ACCESS read-write
	  STATUS current
	  DESCRIPTION
        "
        Set Software Nb 1 As Active :This
        OID, when set, loads the SW from
        bank1 into the PM. It must be followed
        by a reset.  <Help>  This controls
        selects the first SW bank as the
        active bank for the next module
        reset
        "
	  ::= { pm20020maCtrlswMgnt 5 }



pm20020maCtrlWarmReset OBJECT-TYPE
	  SYNTAX EkiOnOff
	  MAX-ACCESS read-write
	  STATUS current
	  DESCRIPTION
        "
        PM Warm Reset :This OID, when
         set, causes a warm reset of the
        PM. This reset is not traffic affecting,
        and the configuration of PM remains
        unchanged.  <Help>  This control
        initiates a warm reset of the module.
        "
	  ::= { pm20020maCtrlswMgnt 3 }



pm20020maCtrlColdReset OBJECT-TYPE
	  SYNTAX EkiOnOff
	  MAX-ACCESS read-write
	  STATUS current
	  DESCRIPTION
        "
        PM Cold Reset :This OID, when
         set, causes a cold reset of the
        PM. This reset is traffic affecting,
        and the configuration of PM is
         reloaded on start-up.  <Help>
          This control initiates a cold
        reset of the module.
        "
	  ::= { pm20020maCtrlswMgnt 2 }



--- *****************************************************
---     LEAF for the gwMgnt article
--- *****************************************************
pm20020maCtrlgwMgnt OBJECT IDENTIFIER ::= { pm20020maCtrlOther 6 }




pm20020maCtrlLoadGwBank4 OBJECT-TYPE
	  SYNTAX EkiOnOff
	  MAX-ACCESS read-write
	  STATUS current
	  DESCRIPTION
        "
        Set Gateware Nb 4 As Active :This
        OID, when set, loads the GW from
        bank4 (Flash) into the PM. It is
        followed by an automatic gateware
        cold reset.
        "
	  ::= { pm20020maCtrlgwMgnt 8 }



pm20020maCtrlLoadGwBank3 OBJECT-TYPE
	  SYNTAX EkiOnOff
	  MAX-ACCESS read-write
	  STATUS current
	  DESCRIPTION
        "
        Set Gateware Nb 3 As Active :This
        OID, when set, loads the GW from
        bank3 (Flash) into the PM. It is
        followed by an automatic gateware
        cold reset.  <Help>  This controls
        initiates a cold reset of the module
        and select the third GW bank as
        the active bank
        "
	  ::= { pm20020maCtrlgwMgnt 7 }



pm20020maCtrlLoadGwBank2 OBJECT-TYPE
	  SYNTAX EkiOnOff
	  MAX-ACCESS read-write
	  STATUS current
	  DESCRIPTION
        "
        Set Gateware Nb 2 As Active :This
        OID, when set, loads the GW from
        bank2 (Flash) into the PM. It is
        followed by an automatic gateware
        cold reset.
        "
	  ::= { pm20020maCtrlgwMgnt 6 }



pm20020maCtrlLoadGwBank1 OBJECT-TYPE
	  SYNTAX EkiOnOff
	  MAX-ACCESS read-write
	  STATUS current
	  DESCRIPTION
        "
        Set Gateware Nb 1 As Active :This
        OID, when set, loads the GW from
        bank1 (Flash) into the PM. It is
        followed by an automatic gateware
        cold reset.  <Help>  This controls
        initiates a cold reset of the module
        and select the first GW bank as
        the active bank
        "
	  ::= { pm20020maCtrlgwMgnt 5 }



pm20020maCtrlCurrentGwReset OBJECT-TYPE
	  SYNTAX EkiOnOff
	  MAX-ACCESS read-write
	  STATUS current
	  DESCRIPTION
        "
        Active Gateware Reset :This OID,
        when set, resets the active gateware.
        It is traffic affecting.
        "
	  ::= { pm20020maCtrlgwMgnt 1 }



--- *********************************************************
---     TABLE for the pm20020maCtrlaccessLoop articles
--- *********************************************************

pm20020maCtrlaccessLoopTable OBJECT-TYPE
	SYNTAX  SEQUENCE OF Pm20020maCtrlaccessLoopEntry
	MAX-ACCESS not-accessible
	STATUS current
	DESCRIPTION
        "
        List of pm20020maCtrlaccessLoop
        Article
        "
	::= { pm20020maCtrlClient 16 }


pm20020maCtrlaccessLoopEntry OBJECT-TYPE
	SYNTAX Pm20020maCtrlaccessLoopEntry
	MAX-ACCESS not-accessible
	STATUS current
	DESCRIPTION
        "
        Row definition for the pm20020maCtrlaccessLoop
        table
        "
	INDEX   { pm20020maCtrlaccessLoopIndex }
	::= { pm20020maCtrlaccessLoopTable 1 }


Pm20020maCtrlaccessLoopEntry ::=
	SEQUENCE {
	pm20020maCtrlaccessLoopIndex
		INTEGER,
	pm20020maCtrlaccessLoopPortn
		EkiState
	}


pm20020maCtrlaccessLoopIndex OBJECT-TYPE
	SYNTAX  INTEGER(0..128)
	MAX-ACCESS  read-only
	STATUS current
	DESCRIPTION
        "
        Index definition for the pm20020maCtrlaccessLoop
        table
        "
	::= { pm20020maCtrlaccessLoopEntry 1 }


pm20020maCtrlaccessLoopPortn OBJECT-TYPE
	SYNTAX  EkiState
	MAX-ACCESS read-write
	STATUS current
	DESCRIPTION
        "
        Client Facility Loopback :This
        OID, when set at '1' puts the client
        port in loopback, looping the received
        10 Gb/s signal on the transmit
         10 Gb/s output.  <Help> This control
        enables the Out Loopback on the
        client port, looping the client
        input signal on the client output
        "
	::= { pm20020maCtrlaccessLoopEntry 2 }


--- *********************************************************
---     TABLE for the pm20020maCtrlclientLoopToLine articles
--- *********************************************************

pm20020maCtrlclientLoopToLineTable OBJECT-TYPE
	SYNTAX  SEQUENCE OF Pm20020maCtrlclientLoopToLineEntry
	MAX-ACCESS not-accessible
	STATUS current
	DESCRIPTION
        "
        List of pm20020maCtrlclientLoopToLine
        Article
        "
	::= { pm20020maCtrlClient 17 }


pm20020maCtrlclientLoopToLineEntry OBJECT-TYPE
	SYNTAX Pm20020maCtrlclientLoopToLineEntry
	MAX-ACCESS not-accessible
	STATUS current
	DESCRIPTION
        "
        Row definition for the pm20020maCtrlclientLoopToLine
        table
        "
	INDEX   { pm20020maCtrlclientLoopToLineIndex }
	::= { pm20020maCtrlclientLoopToLineTable 1 }


Pm20020maCtrlclientLoopToLineEntry ::=
	SEQUENCE {
	pm20020maCtrlclientLoopToLineIndex
		INTEGER,
	pm20020maCtrlclientLoopToLinePortn
		EkiState
	}


pm20020maCtrlclientLoopToLineIndex OBJECT-TYPE
	SYNTAX  INTEGER(0..128)
	MAX-ACCESS  read-only
	STATUS current
	DESCRIPTION
        "
        Index definition for the pm20020maCtrlclientLoopToLine
        table
        "
	::= { pm20020maCtrlclientLoopToLineEntry 1 }


pm20020maCtrlclientLoopToLinePortn OBJECT-TYPE
	SYNTAX  EkiState
	MAX-ACCESS read-write
	STATUS current
	DESCRIPTION
        "
        Client Terminal Loopback :This
        OID, when set, puts the client
         port in loop back, looping the
        10 Gb/s output signal on the 10
        Gb/s input.<Help> This control
         enables the In Loopback on the
        client port, looping the client
        output signal on the client input
        "
	::= { pm20020maCtrlclientLoopToLineEntry 2 }


--- *********************************************************
---     TABLE for the pm20020maCtrlcsfUpIns articles
--- *********************************************************

pm20020maCtrlcsfUpInsTable OBJECT-TYPE
	SYNTAX  SEQUENCE OF Pm20020maCtrlcsfUpInsEntry
	MAX-ACCESS not-accessible
	STATUS current
	DESCRIPTION
        "
        List of pm20020maCtrlcsfUpIns
         Article
        "
	::= { pm20020maCtrlClient 21 }


pm20020maCtrlcsfUpInsEntry OBJECT-TYPE
	SYNTAX Pm20020maCtrlcsfUpInsEntry
	MAX-ACCESS not-accessible
	STATUS current
	DESCRIPTION
        "
        Row definition for the pm20020maCtrlcsfUpIns
        table
        "
	INDEX   { pm20020maCtrlcsfUpInsIndex }
	::= { pm20020maCtrlcsfUpInsTable 1 }


Pm20020maCtrlcsfUpInsEntry ::=
	SEQUENCE {
	pm20020maCtrlcsfUpInsIndex
		INTEGER,
	pm20020maCtrlcsfUpInsPortn
		EkiState
	}


pm20020maCtrlcsfUpInsIndex OBJECT-TYPE
	SYNTAX  INTEGER(0..128)
	MAX-ACCESS  read-only
	STATUS current
	DESCRIPTION
        "
        Index definition for the pm20020maCtrlcsfUpIns
        table
        "
	::= { pm20020maCtrlcsfUpInsEntry 1 }


pm20020maCtrlcsfUpInsPortn OBJECT-TYPE
	SYNTAX  EkiState
	MAX-ACCESS read-write
	STATUS current
	DESCRIPTION
        "
        Client Signal Fail Insertion :This
        OID, when set, inserts  a client
        signal fail in the upstream client
        Port.  <Help>  This control inserts
        a Client Signal Fail for the client
        port
        "
	::= { pm20020maCtrlcsfUpInsEntry 2 }


--- *********************************************************
---     TABLE for the pm20020maCtrlcaisDwIns articles
--- *********************************************************

pm20020maCtrlcaisDwInsTable OBJECT-TYPE
	SYNTAX  SEQUENCE OF Pm20020maCtrlcaisDwInsEntry
	MAX-ACCESS not-accessible
	STATUS current
	DESCRIPTION
        "
        List of pm20020maCtrlcaisDwIns
        Article
        "
	::= { pm20020maCtrlClient 22 }


pm20020maCtrlcaisDwInsEntry OBJECT-TYPE
	SYNTAX Pm20020maCtrlcaisDwInsEntry
	MAX-ACCESS not-accessible
	STATUS current
	DESCRIPTION
        "
        Row definition for the pm20020maCtrlcaisDwIns
        table
        "
	INDEX   { pm20020maCtrlcaisDwInsIndex }
	::= { pm20020maCtrlcaisDwInsTable 1 }


Pm20020maCtrlcaisDwInsEntry ::=
	SEQUENCE {
	pm20020maCtrlcaisDwInsIndex
		INTEGER,
	pm20020maCtrlcaisDwInsPortn
		EkiState
	}


pm20020maCtrlcaisDwInsIndex OBJECT-TYPE
	SYNTAX  INTEGER(0..128)
	MAX-ACCESS  read-only
	STATUS current
	DESCRIPTION
        "
        Index definition for the pm20020maCtrlcaisDwIns
        table
        "
	::= { pm20020maCtrlcaisDwInsEntry 1 }


pm20020maCtrlcaisDwInsPortn OBJECT-TYPE
	SYNTAX  EkiState
	MAX-ACCESS read-write
	STATUS current
	DESCRIPTION
        "
        Client AIS Insertion :This OID,
        when set, inserts a client AIS
         on the downstream client Port.
         <Help>  This control inserts a
        Client AIS for the client port
        "
	::= { pm20020maCtrlcaisDwInsEntry 2 }


--- *********************************************************
---     TABLE for the pm20020maCtrlcommAccessLoop articles
--- *********************************************************

pm20020maCtrlcommAccessLoopTable OBJECT-TYPE
	SYNTAX  SEQUENCE OF Pm20020maCtrlcommAccessLoopEntry
	MAX-ACCESS not-accessible
	STATUS current
	DESCRIPTION
        "
        List of pm20020maCtrlcommAccessLoop
        Article
        "
	::= { pm20020maCtrlLine 64 }


pm20020maCtrlcommAccessLoopEntry OBJECT-TYPE
	SYNTAX Pm20020maCtrlcommAccessLoopEntry
	MAX-ACCESS not-accessible
	STATUS current
	DESCRIPTION
        "
        Row definition for the pm20020maCtrlcommAccessLoop
        table
        "
	INDEX   { pm20020maCtrlcommAccessLoopIndex }
	::= { pm20020maCtrlcommAccessLoopTable 1 }


Pm20020maCtrlcommAccessLoopEntry ::=
	SEQUENCE {
	pm20020maCtrlcommAccessLoopIndex
		INTEGER,
	pm20020maCtrlcommAccessLoopPortn
		EkiState
	}


pm20020maCtrlcommAccessLoopIndex OBJECT-TYPE
	SYNTAX  INTEGER(0..128)
	MAX-ACCESS  read-only
	STATUS current
	DESCRIPTION
        "
        Index definition for the pm20020maCtrlcommAccessLoop
        table
        "
	::= { pm20020maCtrlcommAccessLoopEntry 1 }


pm20020maCtrlcommAccessLoopPortn OBJECT-TYPE
	SYNTAX  EkiState
	MAX-ACCESS read-write
	STATUS current
	DESCRIPTION
        "
        Line Terminal Loopback :This OID,
        when set, puts the module in common
        access loop back, looping the 200
        Gb/s output signal on the 200 Gb/s
        input.<Help> This control enables
        the In Loopback on the line port,
        looping the 200 Gb/s output signal
        on the 200 Gb/s input
        "
	::= { pm20020maCtrlcommAccessLoopEntry 2 }


--- *********************************************************
---     TABLE for the pm20020maCtrllineLoop articles
--- *********************************************************

pm20020maCtrllineLoopTable OBJECT-TYPE
	SYNTAX  SEQUENCE OF Pm20020maCtrllineLoopEntry
	MAX-ACCESS not-accessible
	STATUS current
	DESCRIPTION
        "
        List of pm20020maCtrllineLoop
         Article
        "
	::= { pm20020maCtrlLine 66 }


pm20020maCtrllineLoopEntry OBJECT-TYPE
	SYNTAX Pm20020maCtrllineLoopEntry
	MAX-ACCESS not-accessible
	STATUS current
	DESCRIPTION
        "
        Row definition for the pm20020maCtrllineLoop
        table
        "
	INDEX   { pm20020maCtrllineLoopIndex }
	::= { pm20020maCtrllineLoopTable 1 }


Pm20020maCtrllineLoopEntry ::=
	SEQUENCE {
	pm20020maCtrllineLoopIndex
		INTEGER,
	pm20020maCtrllineLoopPortn
		EkiState
	}


pm20020maCtrllineLoopIndex OBJECT-TYPE
	SYNTAX  INTEGER(0..128)
	MAX-ACCESS  read-only
	STATUS current
	DESCRIPTION
        "
        Index definition for the pm20020maCtrllineLoop
        table
        "
	::= { pm20020maCtrllineLoopEntry 1 }


pm20020maCtrllineLoopPortn OBJECT-TYPE
	SYNTAX  EkiState
	MAX-ACCESS read-write
	STATUS current
	DESCRIPTION
        "
        Line Facility Loopback :This OID,
        when set at '1' puts the module
        in line loopback mode, looping
         the received 200 Gb/s signal on
        the transmit 200 Gb/s output. The
        Upstream part of the module is
         timed on the 200 Gb/s recovered
        clock in that case.<Help> This
         control enables the Out Loopback
        on the line port, looping the 200
        Gb/s input signal on the 200 Gb/s
        output
        "
	::= { pm20020maCtrllineLoopEntry 2 }


--- *********************************************************
---     TABLE for the pm20020maCtrlfecDisable articles
--- *********************************************************

pm20020maCtrlfecDisableTable OBJECT-TYPE
	SYNTAX  SEQUENCE OF Pm20020maCtrlfecDisableEntry
	MAX-ACCESS not-accessible
	STATUS current
	DESCRIPTION
        "
        List of pm20020maCtrlfecDisable
        Article
        "
	::= { pm20020maCtrlLine 69 }


pm20020maCtrlfecDisableEntry OBJECT-TYPE
	SYNTAX Pm20020maCtrlfecDisableEntry
	MAX-ACCESS not-accessible
	STATUS current
	DESCRIPTION
        "
        Row definition for the pm20020maCtrlfecDisable
        table
        "
	INDEX   { pm20020maCtrlfecDisableIndex }
	::= { pm20020maCtrlfecDisableTable 1 }


Pm20020maCtrlfecDisableEntry ::=
	SEQUENCE {
	pm20020maCtrlfecDisableIndex
		INTEGER,
	pm20020maCtrlfecDisablePortn
		EkiState
	}


pm20020maCtrlfecDisableIndex OBJECT-TYPE
	SYNTAX  INTEGER(0..128)
	MAX-ACCESS  read-only
	STATUS current
	DESCRIPTION
        "
        Index definition for the pm20020maCtrlfecDisable
        table
        "
	::= { pm20020maCtrlfecDisableEntry 1 }


pm20020maCtrlfecDisablePortn OBJECT-TYPE
	SYNTAX  EkiState
	MAX-ACCESS read-write
	STATUS current
	DESCRIPTION
        "
        Forward Error Correction Inhibition
        :This OID, when set, inhibits the
        Forward Error Correction feature
        on the line input  <Help>  This
        control enables/disables the Forward
        Error Correction on the line interface
        "
	::= { pm20020maCtrlfecDisableEntry 2 }


--- *****************************************************
---     LEAF for the ledTest article
--- *****************************************************
pm20020maCtrlledTest OBJECT IDENTIFIER ::= { pm20020maCtrlOther 192 }




pm20020maCtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { pm20020maCtrlledTest 3 }



pm20020maCtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { pm20020maCtrlledTest 2 }



pm20020maCtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { pm20020maCtrlledTest 1 }



--- *****************************************************
---     LEAF for the initSwitchMarvell article
--- *****************************************************
pm20020maCtrlinitSwitchMarvell OBJECT IDENTIFIER ::= { pm20020maCtrlOther 201 }




pm20020maCtrlInitSwitchMarvell OBJECT-TYPE
	  SYNTAX EkiOnOff
	  MAX-ACCESS read-write
	  STATUS current
	  DESCRIPTION
        "
        Switch Initialization :This OID
        operates an initialization of the
        switch managed through the module
         <Help>  This control activates
        an initialization of the switch
        managed through the module
        "
	  ::= { pm20020maCtrlinitSwitchMarvell 1 }



--- *********************************************************
---     TABLE for the pm20020maCtrlmsaLineLoop articles
--- *********************************************************

pm20020maCtrlmsaLineLoopTable OBJECT-TYPE
	SYNTAX  SEQUENCE OF Pm20020maCtrlmsaLineLoopEntry
	MAX-ACCESS not-accessible
	STATUS current
	DESCRIPTION
        "
        List of pm20020maCtrlmsaLineLoop
        Article
        "
	::= { pm20020maCtrlLine 209 }


pm20020maCtrlmsaLineLoopEntry OBJECT-TYPE
	SYNTAX Pm20020maCtrlmsaLineLoopEntry
	MAX-ACCESS not-accessible
	STATUS current
	DESCRIPTION
        "
        Row definition for the pm20020maCtrlmsaLineLoop
        table
        "
	INDEX   { pm20020maCtrlmsaLineLoopIndex }
	::= { pm20020maCtrlmsaLineLoopTable 1 }


Pm20020maCtrlmsaLineLoopEntry ::=
	SEQUENCE {
	pm20020maCtrlmsaLineLoopIndex
		INTEGER,
	pm20020maCtrlmsaLineLoopPortn
		EkiState
	}


pm20020maCtrlmsaLineLoopIndex OBJECT-TYPE
	SYNTAX  INTEGER(0..128)
	MAX-ACCESS  read-only
	STATUS current
	DESCRIPTION
        "
        Index definition for the pm20020maCtrlmsaLineLoop
        table
        "
	::= { pm20020maCtrlmsaLineLoopEntry 1 }


pm20020maCtrlmsaLineLoopPortn OBJECT-TYPE
	SYNTAX  EkiState
	MAX-ACCESS read-write
	STATUS current
	DESCRIPTION
        "
        MSA Line Loop :This OID operates
        a line loopback on the MSA Line
         <Help>  This control defines the
        line loop back of the line transceiver
        "
	::= { pm20020maCtrlmsaLineLoopEntry 2 }


--- *********************************************************
---     TABLE for the pm20020maCtrlmsaTxReset articles
--- *********************************************************

pm20020maCtrlmsaTxResetTable OBJECT-TYPE
	SYNTAX  SEQUENCE OF Pm20020maCtrlmsaTxResetEntry
	MAX-ACCESS not-accessible
	STATUS current
	DESCRIPTION
        "
        List of pm20020maCtrlmsaTxReset
        Article
        "
	::= { pm20020maCtrlLine 210 }


pm20020maCtrlmsaTxResetEntry OBJECT-TYPE
	SYNTAX Pm20020maCtrlmsaTxResetEntry
	MAX-ACCESS not-accessible
	STATUS current
	DESCRIPTION
        "
        Row definition for the pm20020maCtrlmsaTxReset
        table
        "
	INDEX   { pm20020maCtrlmsaTxResetIndex }
	::= { pm20020maCtrlmsaTxResetTable 1 }


Pm20020maCtrlmsaTxResetEntry ::=
	SEQUENCE {
	pm20020maCtrlmsaTxResetIndex
		INTEGER,
	pm20020maCtrlmsaTxResetPortn
		EkiState
	}


pm20020maCtrlmsaTxResetIndex OBJECT-TYPE
	SYNTAX  INTEGER(0..128)
	MAX-ACCESS  read-only
	STATUS current
	DESCRIPTION
        "
        Index definition for the pm20020maCtrlmsaTxReset
        table
        "
	::= { pm20020maCtrlmsaTxResetEntry 1 }


pm20020maCtrlmsaTxResetPortn OBJECT-TYPE
	SYNTAX  EkiState
	MAX-ACCESS read-write
	STATUS current
	DESCRIPTION
        "
        Line MSA TX Reset :This OID resets
        the TX portion of the MSA line
         module  <Help > This control
         initiates a reset of the transmitting
        side
        "
	::= { pm20020maCtrlmsaTxResetEntry 2 }


--- *********************************************************
---     TABLE for the pm20020maCtrlmsaRxReset articles
--- *********************************************************

pm20020maCtrlmsaRxResetTable OBJECT-TYPE
	SYNTAX  SEQUENCE OF Pm20020maCtrlmsaRxResetEntry
	MAX-ACCESS not-accessible
	STATUS current
	DESCRIPTION
        "
        List of pm20020maCtrlmsaRxReset
        Article
        "
	::= { pm20020maCtrlLine 211 }


pm20020maCtrlmsaRxResetEntry OBJECT-TYPE
	SYNTAX Pm20020maCtrlmsaRxResetEntry
	MAX-ACCESS not-accessible
	STATUS current
	DESCRIPTION
        "
        Row definition for the pm20020maCtrlmsaRxReset
        table
        "
	INDEX   { pm20020maCtrlmsaRxResetIndex }
	::= { pm20020maCtrlmsaRxResetTable 1 }


Pm20020maCtrlmsaRxResetEntry ::=
	SEQUENCE {
	pm20020maCtrlmsaRxResetIndex
		INTEGER,
	pm20020maCtrlmsaRxResetPortn
		EkiState
	}


pm20020maCtrlmsaRxResetIndex OBJECT-TYPE
	SYNTAX  INTEGER(0..128)
	MAX-ACCESS  read-only
	STATUS current
	DESCRIPTION
        "
        Index definition for the pm20020maCtrlmsaRxReset
        table
        "
	::= { pm20020maCtrlmsaRxResetEntry 1 }


pm20020maCtrlmsaRxResetPortn OBJECT-TYPE
	SYNTAX  EkiState
	MAX-ACCESS read-write
	STATUS current
	DESCRIPTION
        "
        Line MSA RX Reset :This OID resets
        the RX portion of the MSA line
         module  <Help > This control
         initiates a reset of the receiving
        side
        "
	::= { pm20020maCtrlmsaRxResetEntry 2 }


--- *********************************************************
---     TABLE for the pm20020maCtrlmsaShutdown articles
--- *********************************************************

pm20020maCtrlmsaShutdownTable OBJECT-TYPE
	SYNTAX  SEQUENCE OF Pm20020maCtrlmsaShutdownEntry
	MAX-ACCESS not-accessible
	STATUS current
	DESCRIPTION
        "
        List of pm20020maCtrlmsaShutdown
        Article
        "
	::= { pm20020maCtrlLine 212 }


pm20020maCtrlmsaShutdownEntry OBJECT-TYPE
	SYNTAX Pm20020maCtrlmsaShutdownEntry
	MAX-ACCESS not-accessible
	STATUS current
	DESCRIPTION
        "
        Row definition for the pm20020maCtrlmsaShutdown
        table
        "
	INDEX   { pm20020maCtrlmsaShutdownIndex }
	::= { pm20020maCtrlmsaShutdownTable 1 }


Pm20020maCtrlmsaShutdownEntry ::=
	SEQUENCE {
	pm20020maCtrlmsaShutdownIndex
		INTEGER,
	pm20020maCtrlmsaShutdownPortn
		EkiState
	}


pm20020maCtrlmsaShutdownIndex OBJECT-TYPE
	SYNTAX  INTEGER(0..128)
	MAX-ACCESS  read-only
	STATUS current
	DESCRIPTION
        "
        Index definition for the pm20020maCtrlmsaShutdown
        table
        "
	::= { pm20020maCtrlmsaShutdownEntry 1 }


pm20020maCtrlmsaShutdownPortn OBJECT-TYPE
	SYNTAX  EkiState
	MAX-ACCESS read-write
	STATUS current
	DESCRIPTION
        "
        Line MSA Shutdown :This OID enters
        a process to shutdown the MSA line
        module  <Help > This control  initiates
        a shutdown of the module
        "
	::= { pm20020maCtrlmsaShutdownEntry 2 }


--- *****************************************************
---     LEAF for the resetCount article
--- *****************************************************
pm20020maCtrlresetCount OBJECT IDENTIFIER ::= { pm20020maCtrlOther 259 }




pm20020maCtrlResetcount OBJECT-TYPE
	  SYNTAX EkiOnOff
	  MAX-ACCESS read-write
	  STATUS current
	  DESCRIPTION
        "
        Module Count Global Reset :This
        OID resets all the errors counters
        on the module  <Help > This control
         initiates a reset of the errors
        counters on the module
        "
	  ::= { pm20020maCtrlresetCount 1 }



--- *****************************************************
---     LEAF for the resetRmon article
--- *****************************************************
pm20020maCtrlresetRmon OBJECT IDENTIFIER ::= { pm20020maCtrlOther 260 }




pm20020maCtrlResetrmon OBJECT-TYPE
	  SYNTAX EkiOnOff
	  MAX-ACCESS read-write
	  STATUS current
	  DESCRIPTION
        "
        Module Rmon Global Reset :This
        OID resets all the Rmon counters
        on the module  <Help > This control
         initiates a reset of the Rmon
         counters on the module
        "
	  ::= { pm20020maCtrlresetRmon 1 }



--- *****************************************************
---     LEAF for the resetMeasurements article
--- *****************************************************
pm20020maCtrlresetMeasurements OBJECT IDENTIFIER ::= { pm20020maCtrlOther 261 }




pm20020maCtrlResetmeasurements OBJECT-TYPE
	  SYNTAX EkiOnOff
	  MAX-ACCESS read-write
	  STATUS current
	  DESCRIPTION
        "
        Management Meas Global Reset :This
        OID resets some measurements on
        the management  <Help > This control
         initiates a reset of some measurements
        on the management
        "
	  ::= { pm20020maCtrlresetMeasurements 1 }



--- *********************************************************
---     TABLE for the pm20020maCtrlclientResetAllCount articles
--- *********************************************************

pm20020maCtrlclientResetAllCountTable OBJECT-TYPE
	SYNTAX  SEQUENCE OF Pm20020maCtrlclientResetAllCountEntry
	MAX-ACCESS not-accessible
	STATUS current
	DESCRIPTION
        "
        List of pm20020maCtrlclientResetAllCount
        Article
        "
	::= { pm20020maCtrlClient 262 }


pm20020maCtrlclientResetAllCountEntry OBJECT-TYPE
	SYNTAX Pm20020maCtrlclientResetAllCountEntry
	MAX-ACCESS not-accessible
	STATUS current
	DESCRIPTION
        "
        Row definition for the pm20020maCtrlclientResetAllCount
        table
        "
	INDEX   { pm20020maCtrlclientResetAllCountIndex }
	::= { pm20020maCtrlclientResetAllCountTable 1 }


Pm20020maCtrlclientResetAllCountEntry ::=
	SEQUENCE {
	pm20020maCtrlclientResetAllCountIndex
		INTEGER,
	pm20020maCtrlclientResetAllCountsPortn
		EkiState
	}


pm20020maCtrlclientResetAllCountIndex OBJECT-TYPE
	SYNTAX  INTEGER(0..128)
	MAX-ACCESS  read-only
	STATUS current
	DESCRIPTION
        "
        Index definition for the pm20020maCtrlclientResetAllCount
        table
        "
	::= { pm20020maCtrlclientResetAllCountEntry 1 }


pm20020maCtrlclientResetAllCountsPortn OBJECT-TYPE
	SYNTAX  EkiState
	MAX-ACCESS read-write
	STATUS current
	DESCRIPTION
        "
        Client Counters Reset :This OID
        resets every counter on the client
        port  <Help>   This control operates
        a reset on the statistics current
        ,previous and history client port
        counters
        "
	::= { pm20020maCtrlclientResetAllCountEntry 2 }


--- *********************************************************
---     TABLE for the pm20020maCtrllineResetAllCount articles
--- *********************************************************

pm20020maCtrllineResetAllCountTable OBJECT-TYPE
	SYNTAX  SEQUENCE OF Pm20020maCtrllineResetAllCountEntry
	MAX-ACCESS not-accessible
	STATUS current
	DESCRIPTION
        "
        List of pm20020maCtrllineResetAllCount
        Article
        "
	::= { pm20020maCtrlLine 263 }


pm20020maCtrllineResetAllCountEntry OBJECT-TYPE
	SYNTAX Pm20020maCtrllineResetAllCountEntry
	MAX-ACCESS not-accessible
	STATUS current
	DESCRIPTION
        "
        Row definition for the pm20020maCtrllineResetAllCount
        table
        "
	INDEX   { pm20020maCtrllineResetAllCountIndex }
	::= { pm20020maCtrllineResetAllCountTable 1 }


Pm20020maCtrllineResetAllCountEntry ::=
	SEQUENCE {
	pm20020maCtrllineResetAllCountIndex
		INTEGER,
	pm20020maCtrllineResetAllCountsPortn
		EkiState
	}


pm20020maCtrllineResetAllCountIndex OBJECT-TYPE
	SYNTAX  INTEGER(0..128)
	MAX-ACCESS  read-only
	STATUS current
	DESCRIPTION
        "
        Index definition for the pm20020maCtrllineResetAllCount
        table
        "
	::= { pm20020maCtrllineResetAllCountEntry 1 }


pm20020maCtrllineResetAllCountsPortn OBJECT-TYPE
	SYNTAX  EkiState
	MAX-ACCESS read-write
	STATUS current
	DESCRIPTION
        "
        Line Counters Reset :This OID
         resets every counter on the line
        port  <Help>   This control operates
        a reset on the statistics current
        ,previous and history line port
        counters
        "
	::= { pm20020maCtrllineResetAllCountEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pm20020maCntclientInputErrorCounter articles
--- *********************************************************

pm20020maCntclientInputErrorCounterTable OBJECT-TYPE
	SYNTAX  SEQUENCE OF Pm20020maCntclientInputErrorCounterEntry
	MAX-ACCESS not-accessible
	STATUS current
	DESCRIPTION
        "
        List of pm20020maCntclientInputErrorCounter
        Article
        "
	::= { pm20020maCntClient 112 }


pm20020maCntclientInputErrorCounterEntry OBJECT-TYPE
	SYNTAX Pm20020maCntclientInputErrorCounterEntry
	MAX-ACCESS not-accessible
	STATUS current
	DESCRIPTION
        "
        Row definition for the pm20020maCntclientInputErrorCounter
        table
        "
	INDEX   { pm20020maCntclientInputErrorCounterIndex }
	::= { pm20020maCntclientInputErrorCounterTable 1 }


Pm20020maCntclientInputErrorCounterEntry ::=
	SEQUENCE {
	pm20020maCntclientInputErrorCounterIndex
		INTEGER,
	pm20020maCntclientInputErrorCounterValuePortn
		Counter32,
	pm20020maCntclientInputErrorCounterErrorPortn
		EkiOnOff,
	pm20020maCntclientInputErrorCounterOverloadPortn
		EkiOnOff
	}


pm20020maCntclientInputErrorCounterIndex OBJECT-TYPE
	SYNTAX  INTEGER(0..128)
	MAX-ACCESS  read-only
	STATUS current
	DESCRIPTION
        "
        Index definition for the pm20020maCntclientInputErrorCounter
        table
        "
	::= { pm20020maCntclientInputErrorCounterEntry 1 }


pm20020maCntclientInputErrorCounterValuePortn OBJECT-TYPE
	SYNTAX  Counter32
	MAX-ACCESS read-only
	STATUS current
	DESCRIPTION
        "
        Client Input Errors :This counter
        is increased each time a 10b/8b
        running disparity error is detected
        on the Client input stream  <Help>
         This counter gives the number
         of 10b/8b running disparity errors
        on the client port
        "
	::= { pm20020maCntclientInputErrorCounterEntry 2 }


pm20020maCntclientInputErrorCounterErrorPortn OBJECT-TYPE
	SYNTAX  EkiOnOff
	MAX-ACCESS read-only
	STATUS current
	DESCRIPTION
        "
        Client Counter Error :This OID
        when set indicates the client error
        counter value is invalid on Port
        "
	::= { pm20020maCntclientInputErrorCounterEntry 3 }


pm20020maCntclientInputErrorCounterOverloadPortn OBJECT-TYPE
	SYNTAX  EkiOnOff
	MAX-ACCESS read-only
	STATUS current
	DESCRIPTION
        "
        Client Counter Overload :This
         OID when set indicates a client
        input error counter overload on
        Port
        "
	::= { pm20020maCntclientInputErrorCounterEntry 4 }


--- *********************************************************
---     TABLE for the pm20020maCntclientCbipCounter articles
--- *********************************************************

pm20020maCntclientCbipCounterTable OBJECT-TYPE
	SYNTAX  SEQUENCE OF Pm20020maCntclientCbipCounterEntry
	MAX-ACCESS not-accessible
	STATUS current
	DESCRIPTION
        "
        List of pm20020maCntclientCbipCounter
        Article
        "
	::= { pm20020maCntClient 144 }


pm20020maCntclientCbipCounterEntry OBJECT-TYPE
	SYNTAX Pm20020maCntclientCbipCounterEntry
	MAX-ACCESS not-accessible
	STATUS current
	DESCRIPTION
        "
        Row definition for the pm20020maCntclientCbipCounter
        table
        "
	INDEX   { pm20020maCntclientCbipCounterIndex }
	::= { pm20020maCntclientCbipCounterTable 1 }


Pm20020maCntclientCbipCounterEntry ::=
	SEQUENCE {
	pm20020maCntclientCbipCounterIndex
		INTEGER,
	pm20020maCntclientCbipCounterValuePortn
		Counter32,
	pm20020maCntclientCbipCounterErrorPortn
		EkiOnOff,
	pm20020maCntclientCbipCounterOverloadPortn
		EkiOnOff
	}


pm20020maCntclientCbipCounterIndex OBJECT-TYPE
	SYNTAX  INTEGER(0..128)
	MAX-ACCESS  read-only
	STATUS current
	DESCRIPTION
        "
        Index definition for the pm20020maCntclientCbipCounter
        table
        "
	::= { pm20020maCntclientCbipCounterEntry 1 }


pm20020maCntclientCbipCounterValuePortn OBJECT-TYPE
	SYNTAX  Counter32
	MAX-ACCESS read-only
	STATUS current
	DESCRIPTION
        "
        Client Output Errors :This counter
        is incremented each time a CBIP
        parity error is detected on the
        Client output stream  <Help>  This
        counter gives the number of CBIP
        errors on the client port
        "
	::= { pm20020maCntclientCbipCounterEntry 2 }


pm20020maCntclientCbipCounterErrorPortn OBJECT-TYPE
	SYNTAX  EkiOnOff
	MAX-ACCESS read-only
	STATUS current
	DESCRIPTION
        "
        Client Counter Error :This OID
        when set indicates the CBIP error
        counter value is invalid on Port
        "
	::= { pm20020maCntclientCbipCounterEntry 3 }


pm20020maCntclientCbipCounterOverloadPortn OBJECT-TYPE
	SYNTAX  EkiOnOff
	MAX-ACCESS read-only
	STATUS current
	DESCRIPTION
        "
        Client CBIP Counter Overload :This
        OID when set indicates a CBIP error
        counter overload on Port
        "
	::= { pm20020maCntclientCbipCounterEntry 4 }


--- *********************************************************
---     TABLE for the pm20020maCntlocalLineSmBip8ErrorCounter articles
--- *********************************************************

pm20020maCntlocalLineSmBip8ErrorCounterTable OBJECT-TYPE
	SYNTAX  SEQUENCE OF Pm20020maCntlocalLineSmBip8ErrorCounterEntry
	MAX-ACCESS not-accessible
	STATUS current
	DESCRIPTION
        "
        List of pm20020maCntlocalLineSmBip8ErrorCounter
        Article
        "
	::= { pm20020maCntLine 192 }


pm20020maCntlocalLineSmBip8ErrorCounterEntry OBJECT-TYPE
	SYNTAX Pm20020maCntlocalLineSmBip8ErrorCounterEntry
	MAX-ACCESS not-accessible
	STATUS current
	DESCRIPTION
        "
        Row definition for the pm20020maCntlocalLineSmBip8ErrorCounter
        table
        "
	INDEX   { pm20020maCntlocalLineSmBip8ErrorCounterIndex }
	::= { pm20020maCntlocalLineSmBip8ErrorCounterTable 1 }


Pm20020maCntlocalLineSmBip8ErrorCounterEntry ::=
	SEQUENCE {
	pm20020maCntlocalLineSmBip8ErrorCounterIndex
		INTEGER,
	pm20020maCntlocalLineSmBip8ErrorCounterValuePortn
		Counter64,
	pm20020maCntlocalLineSmBip8ErrorCounterErrorPortn
		EkiOnOff,
	pm20020maCntlocalLineSmBip8ErrorCounterOverloadPortn
		EkiOnOff
	}


pm20020maCntlocalLineSmBip8ErrorCounterIndex OBJECT-TYPE
	SYNTAX  INTEGER(0..128)
	MAX-ACCESS  read-only
	STATUS current
	DESCRIPTION
        "
        Index definition for the pm20020maCntlocalLineSmBip8ErrorCounter
        table
        "
	::= { pm20020maCntlocalLineSmBip8ErrorCounterEntry 1 }


pm20020maCntlocalLineSmBip8ErrorCounterValuePortn OBJECT-TYPE
	SYNTAX  Counter64
	MAX-ACCESS read-only
	STATUS current
	DESCRIPTION
        "
        Uncorrected SD FEC Errors :This
        OID gives the current Bit Error
        Rate (residual SM-BIP8 error) after
        FEC   <Help> This counter gives
        the current Bit Error Rate (residual
        SM-BIP8 error) after FEC
        "
	::= { pm20020maCntlocalLineSmBip8ErrorCounterEntry 2 }


pm20020maCntlocalLineSmBip8ErrorCounterErrorPortn OBJECT-TYPE
	SYNTAX  EkiOnOff
	MAX-ACCESS read-only
	STATUS current
	DESCRIPTION
        "
        Line Counter Error :This OID when
        set indicates the B1 error counter
        value is invalid on Port
        "
	::= { pm20020maCntlocalLineSmBip8ErrorCounterEntry 3 }


pm20020maCntlocalLineSmBip8ErrorCounterOverloadPortn OBJECT-TYPE
	SYNTAX  EkiOnOff
	MAX-ACCESS read-only
	STATUS current
	DESCRIPTION
        "
        Line Counter Overload :This OID
        when set indicates a B1 error counter
        overload on Port
        "
	::= { pm20020maCntlocalLineSmBip8ErrorCounterEntry 4 }


--- *********************************************************
---     TABLE for the pm20020maCntlocalLineFecCorrectedErrorsCounter articles
--- *********************************************************

pm20020maCntlocalLineFecCorrectedErrorsCounterTable OBJECT-TYPE
	SYNTAX  SEQUENCE OF Pm20020maCntlocalLineFecCorrectedErrorsCounterEntry
	MAX-ACCESS not-accessible
	STATUS current
	DESCRIPTION
        "
        List of pm20020maCntlocalLineFecCorrectedErrorsCounter
        Article
        "
	::= { pm20020maCntLine 193 }


pm20020maCntlocalLineFecCorrectedErrorsCounterEntry OBJECT-TYPE
	SYNTAX Pm20020maCntlocalLineFecCorrectedErrorsCounterEntry
	MAX-ACCESS not-accessible
	STATUS current
	DESCRIPTION
        "
        Row definition for the pm20020maCntlocalLineFecCorrectedErrorsCounter
        table
        "
	INDEX   { pm20020maCntlocalLineFecCorrectedErrorsCounterIndex }
	::= { pm20020maCntlocalLineFecCorrectedErrorsCounterTable 1 }


Pm20020maCntlocalLineFecCorrectedErrorsCounterEntry ::=
	SEQUENCE {
	pm20020maCntlocalLineFecCorrectedErrorsCounterIndex
		INTEGER,
	pm20020maCntlocalLineFecCorrectedErrorsCounterValuePortn
		Counter64,
	pm20020maCntlocalLineFecCorrectedErrorsCounterErrorPortn
		EkiOnOff,
	pm20020maCntlocalLineFecCorrectedErrorsCounterOverloadPortn
		EkiOnOff
	}


pm20020maCntlocalLineFecCorrectedErrorsCounterIndex OBJECT-TYPE
	SYNTAX  INTEGER(0..128)
	MAX-ACCESS  read-only
	STATUS current
	DESCRIPTION
        "
        Index definition for the pm20020maCntlocalLineFecCorrectedErrorsCounter
        table
        "
	::= { pm20020maCntlocalLineFecCorrectedErrorsCounterEntry 1 }


pm20020maCntlocalLineFecCorrectedErrorsCounterValuePortn OBJECT-TYPE
	SYNTAX  Counter64
	MAX-ACCESS read-only
	STATUS current
	DESCRIPTION
        "
        Line Input HD FEC Corrected Errors
        :This OID gives the current Bit
        Error Rate before the Hard Decision
        FEC  <Help> This counter gives
         the current Bit Error Rate before
        the Hard Decision FEC
        "
	::= { pm20020maCntlocalLineFecCorrectedErrorsCounterEntry 2 }


pm20020maCntlocalLineFecCorrectedErrorsCounterErrorPortn OBJECT-TYPE
	SYNTAX  EkiOnOff
	MAX-ACCESS read-only
	STATUS current
	DESCRIPTION
        "
        FEC Counter Error :This bit when
        set indicates the FEC corrected
        errors counter value is invalid
        on Line
        "
	::= { pm20020maCntlocalLineFecCorrectedErrorsCounterEntry 3 }


pm20020maCntlocalLineFecCorrectedErrorsCounterOverloadPortn OBJECT-TYPE
	SYNTAX  EkiOnOff
	MAX-ACCESS read-only
	STATUS current
	DESCRIPTION
        "
        FEC Counter Overload :This bit
        when set indicates a FEC corrected
        errors counter overload on Line
        "
	::= { pm20020maCntlocalLineFecCorrectedErrorsCounterEntry 4 }


--- *********************************************************
---     TABLE for the pm20020maCntremoteLineSmBip8ErrorCounter articles
--- *********************************************************

pm20020maCntremoteLineSmBip8ErrorCounterTable OBJECT-TYPE
	SYNTAX  SEQUENCE OF Pm20020maCntremoteLineSmBip8ErrorCounterEntry
	MAX-ACCESS not-accessible
	STATUS current
	DESCRIPTION
        "
        List of pm20020maCntremoteLineSmBip8ErrorCounter
        Article
        "
	::= { pm20020maCntLine 194 }


pm20020maCntremoteLineSmBip8ErrorCounterEntry OBJECT-TYPE
	SYNTAX Pm20020maCntremoteLineSmBip8ErrorCounterEntry
	MAX-ACCESS not-accessible
	STATUS current
	DESCRIPTION
        "
        Row definition for the pm20020maCntremoteLineSmBip8ErrorCounter
        table
        "
	INDEX   { pm20020maCntremoteLineSmBip8ErrorCounterIndex }
	::= { pm20020maCntremoteLineSmBip8ErrorCounterTable 1 }


Pm20020maCntremoteLineSmBip8ErrorCounterEntry ::=
	SEQUENCE {
	pm20020maCntremoteLineSmBip8ErrorCounterIndex
		INTEGER,
	pm20020maCntremoteLineSmBip8ErrorCounterValuePortn
		Counter64,
	pm20020maCntremoteLineSmBip8ErrorCounterErrorPortn
		EkiOnOff,
	pm20020maCntremoteLineSmBip8ErrorCounterOverloadPortn
		EkiOnOff
	}


pm20020maCntremoteLineSmBip8ErrorCounterIndex OBJECT-TYPE
	SYNTAX  INTEGER(0..128)
	MAX-ACCESS  read-only
	STATUS current
	DESCRIPTION
        "
        Index definition for the pm20020maCntremoteLineSmBip8ErrorCounter
        table
        "
	::= { pm20020maCntremoteLineSmBip8ErrorCounterEntry 1 }


pm20020maCntremoteLineSmBip8ErrorCounterValuePortn OBJECT-TYPE
	SYNTAX  Counter64
	MAX-ACCESS read-only
	STATUS current
	DESCRIPTION
        "
        Remote SM BIP8 :This OID gives
        the current Bit Error Rate (residual
        SM-BIP8 error) after FEC on the
        remote side  <Help> This counter
        gives the current Bit Error Rate
        (residual SM-BIP8 error) after
         FEC on the remote side
        "
	::= { pm20020maCntremoteLineSmBip8ErrorCounterEntry 2 }


pm20020maCntremoteLineSmBip8ErrorCounterErrorPortn OBJECT-TYPE
	SYNTAX  EkiOnOff
	MAX-ACCESS read-only
	STATUS current
	DESCRIPTION
        "
        Remote Counter Error :
        "
	::= { pm20020maCntremoteLineSmBip8ErrorCounterEntry 3 }


pm20020maCntremoteLineSmBip8ErrorCounterOverloadPortn OBJECT-TYPE
	SYNTAX  EkiOnOff
	MAX-ACCESS read-only
	STATUS current
	DESCRIPTION
        "
        Remote Counter Overload :
        "
	::= { pm20020maCntremoteLineSmBip8ErrorCounterEntry 4 }


--- *********************************************************
---     TABLE for the pm20020maCntlineDfrmTimCnt articles
--- *********************************************************

pm20020maCntlineDfrmTimCntTable OBJECT-TYPE
	SYNTAX  SEQUENCE OF Pm20020maCntlineDfrmTimCntEntry
	MAX-ACCESS not-accessible
	STATUS current
	DESCRIPTION
        "
        List of pm20020maCntlineDfrmTimCnt
        Article
        "
	::= { pm20020maCntLine 195 }


pm20020maCntlineDfrmTimCntEntry OBJECT-TYPE
	SYNTAX Pm20020maCntlineDfrmTimCntEntry
	MAX-ACCESS not-accessible
	STATUS current
	DESCRIPTION
        "
        Row definition for the pm20020maCntlineDfrmTimCnt
        table
        "
	INDEX   { pm20020maCntlineDfrmTimCntIndex }
	::= { pm20020maCntlineDfrmTimCntTable 1 }


Pm20020maCntlineDfrmTimCntEntry ::=
	SEQUENCE {
	pm20020maCntlineDfrmTimCntIndex
		INTEGER,
	pm20020maCntlineDfrmTimCntValuePortn
		Counter64,
	pm20020maCntlineDfrmTimCntErrorPortn
		EkiOnOff,
	pm20020maCntlineDfrmTimCntOverloadPortn
		EkiOnOff
	}


pm20020maCntlineDfrmTimCntIndex OBJECT-TYPE
	SYNTAX  INTEGER(0..128)
	MAX-ACCESS  read-only
	STATUS current
	DESCRIPTION
        "
        Index definition for the pm20020maCntlineDfrmTimCnt
        table
        "
	::= { pm20020maCntlineDfrmTimCntEntry 1 }


pm20020maCntlineDfrmTimCntValuePortn OBJECT-TYPE
	SYNTAX  Counter64
	MAX-ACCESS read-only
	STATUS current
	DESCRIPTION
        "
        Line Timer Counter :
        "
	::= { pm20020maCntlineDfrmTimCntEntry 2 }


pm20020maCntlineDfrmTimCntErrorPortn OBJECT-TYPE
	SYNTAX  EkiOnOff
	MAX-ACCESS read-only
	STATUS current
	DESCRIPTION
        "
        Line Counter Error :This OID when
        set indicates the deframer timer
        counter value is invalid on Port
        "
	::= { pm20020maCntlineDfrmTimCntEntry 3 }


pm20020maCntlineDfrmTimCntOverloadPortn OBJECT-TYPE
	SYNTAX  EkiOnOff
	MAX-ACCESS read-only
	STATUS current
	DESCRIPTION
        "
        Line Counter Overload :This OID
        when set indicates a deframer timer
        counter overload on Port
        "
	::= { pm20020maCntlineDfrmTimCntEntry 4 }


--- *********************************************************
---     TABLE for the pm20020maCntlocalLineTrscvPreSdFecErrorCounter articles
--- *********************************************************

pm20020maCntlocalLineTrscvPreSdFecErrorCounterTable OBJECT-TYPE
	SYNTAX  SEQUENCE OF Pm20020maCntlocalLineTrscvPreSdFecErrorCounterEntry
	MAX-ACCESS not-accessible
	STATUS current
	DESCRIPTION
        "
        List of pm20020maCntlocalLineTrscvPreSdFecErrorCounter
        Article
        "
	::= { pm20020maCntLine 196 }


pm20020maCntlocalLineTrscvPreSdFecErrorCounterEntry OBJECT-TYPE
	SYNTAX Pm20020maCntlocalLineTrscvPreSdFecErrorCounterEntry
	MAX-ACCESS not-accessible
	STATUS current
	DESCRIPTION
        "
        Row definition for the pm20020maCntlocalLineTrscvPreSdFecErrorCounter
        table
        "
	INDEX   { pm20020maCntlocalLineTrscvPreSdFecErrorCounterIndex }
	::= { pm20020maCntlocalLineTrscvPreSdFecErrorCounterTable 1 }


Pm20020maCntlocalLineTrscvPreSdFecErrorCounterEntry ::=
	SEQUENCE {
	pm20020maCntlocalLineTrscvPreSdFecErrorCounterIndex
		INTEGER,
	pm20020maCntlocalLineTrscvPreSdFecErrorCounterValuePortn
		Counter64,
	pm20020maCntlocalLineTrscvPreSdFecErrorCounterErrorPortn
		EkiOnOff,
	pm20020maCntlocalLineTrscvPreSdFecErrorCounterOverloadPortn
		EkiOnOff
	}


pm20020maCntlocalLineTrscvPreSdFecErrorCounterIndex OBJECT-TYPE
	SYNTAX  INTEGER(0..128)
	MAX-ACCESS  read-only
	STATUS current
	DESCRIPTION
        "
        Index definition for the pm20020maCntlocalLineTrscvPreSdFecErrorCounter
        table
        "
	::= { pm20020maCntlocalLineTrscvPreSdFecErrorCounterEntry 1 }


pm20020maCntlocalLineTrscvPreSdFecErrorCounterValuePortn OBJECT-TYPE
	SYNTAX  Counter64
	MAX-ACCESS read-only
	STATUS current
	DESCRIPTION
        "
        Pre-SD FEC Errors :This OID gives
        the current Bit Error Rate before
        the Soft Decision FEC  <Help> This
        counter gives the current Bit Error
        Rate before the Soft Decision FEC
        "
	::= { pm20020maCntlocalLineTrscvPreSdFecErrorCounterEntry 2 }


pm20020maCntlocalLineTrscvPreSdFecErrorCounterErrorPortn OBJECT-TYPE
	SYNTAX  EkiOnOff
	MAX-ACCESS read-only
	STATUS current
	DESCRIPTION
        "
        Line Counter Error :This OID when
        set indicates the deframer timer
        counter value is invalid on Port
        "
	::= { pm20020maCntlocalLineTrscvPreSdFecErrorCounterEntry 3 }


pm20020maCntlocalLineTrscvPreSdFecErrorCounterOverloadPortn OBJECT-TYPE
	SYNTAX  EkiOnOff
	MAX-ACCESS read-only
	STATUS current
	DESCRIPTION
        "
        Line Counter Overload :This OID
        when set indicates a deframer timer
        counter overload on Port
        "
	::= { pm20020maCntlocalLineTrscvPreSdFecErrorCounterEntry 4 }


--- *********************************************************
---     TABLE for the pm20020maCntlocalLineTrscvUncorrectedSdFecErrorCounter articles
--- *********************************************************

pm20020maCntlocalLineTrscvUncorrectedSdFecErrorCounterTable OBJECT-TYPE
	SYNTAX  SEQUENCE OF Pm20020maCntlocalLineTrscvUncorrectedSdFecErrorCounterEntry
	MAX-ACCESS not-accessible
	STATUS current
	DESCRIPTION
        "
        List of pm20020maCntlocalLineTrscvUncorrectedSdFecErrorCounter
        Article
        "
	::= { pm20020maCntLine 197 }


pm20020maCntlocalLineTrscvUncorrectedSdFecErrorCounterEntry OBJECT-TYPE
	SYNTAX Pm20020maCntlocalLineTrscvUncorrectedSdFecErrorCounterEntry
	MAX-ACCESS not-accessible
	STATUS current
	DESCRIPTION
        "
        Row definition for the pm20020maCntlocalLineTrscvUncorrectedSdFecErrorCounter
        table
        "
	INDEX   { pm20020maCntlocalLineTrscvUncorrectedSdFecErrorCounterIndex }
	::= { pm20020maCntlocalLineTrscvUncorrectedSdFecErrorCounterTable 1 }


Pm20020maCntlocalLineTrscvUncorrectedSdFecErrorCounterEntry ::=
	SEQUENCE {
	pm20020maCntlocalLineTrscvUncorrectedSdFecErrorCounterIndex
		INTEGER,
	pm20020maCntlocalLineTrscvUncorrectedSdFecErrorCounterValuePortn
		Counter64,
	pm20020maCntlocalLineTrscvUncorrectedSdFecErrorCounterErrorPortn
		EkiOnOff,
	pm20020maCntlocalLineTrscvUncorrectedSdFecErrorCounterOverloadPortn
		EkiOnOff
	}


pm20020maCntlocalLineTrscvUncorrectedSdFecErrorCounterIndex OBJECT-TYPE
	SYNTAX  INTEGER(0..128)
	MAX-ACCESS  read-only
	STATUS current
	DESCRIPTION
        "
        Index definition for the pm20020maCntlocalLineTrscvUncorrectedSdFecErrorCounter
        table
        "
	::= { pm20020maCntlocalLineTrscvUncorrectedSdFecErrorCounterEntry 1 }


pm20020maCntlocalLineTrscvUncorrectedSdFecErrorCounterValuePortn OBJECT-TYPE
	SYNTAX  Counter64
	MAX-ACCESS read-only
	STATUS current
	DESCRIPTION
        "
        Uncorrected SD FEC Errors :This
        OID gives the current Bit Error
        Rate after the Soft Decision FEC
        (residual)  <Help> This counter
        gives the current Bit Error Rate
        after the Soft Decision FEC (residual)
        "
	::= { pm20020maCntlocalLineTrscvUncorrectedSdFecErrorCounterEntry 2 }


pm20020maCntlocalLineTrscvUncorrectedSdFecErrorCounterErrorPortn OBJECT-TYPE
	SYNTAX  EkiOnOff
	MAX-ACCESS read-only
	STATUS current
	DESCRIPTION
        "
        Line Counter Error :This OID when
        set indicates the deframer timer
        counter value is invalid on Port
        "
	::= { pm20020maCntlocalLineTrscvUncorrectedSdFecErrorCounterEntry 3 }


pm20020maCntlocalLineTrscvUncorrectedSdFecErrorCounterOverloadPortn OBJECT-TYPE
	SYNTAX  EkiOnOff
	MAX-ACCESS read-only
	STATUS current
	DESCRIPTION
        "
        Line Counter Overload :This OID
        when set indicates a deframer timer
        counter overload on Port
        "
	::= { pm20020maCntlocalLineTrscvUncorrectedSdFecErrorCounterEntry 4 }


--- *********************************************************
---     TABLE for the pm20020maCntlocalLineTrscvPreSdFecBitCounter articles
--- *********************************************************

pm20020maCntlocalLineTrscvPreSdFecBitCounterTable OBJECT-TYPE
	SYNTAX  SEQUENCE OF Pm20020maCntlocalLineTrscvPreSdFecBitCounterEntry
	MAX-ACCESS not-accessible
	STATUS current
	DESCRIPTION
        "
        List of pm20020maCntlocalLineTrscvPreSdFecBitCounter
        Article
        "
	::= { pm20020maCntLine 198 }


pm20020maCntlocalLineTrscvPreSdFecBitCounterEntry OBJECT-TYPE
	SYNTAX Pm20020maCntlocalLineTrscvPreSdFecBitCounterEntry
	MAX-ACCESS not-accessible
	STATUS current
	DESCRIPTION
        "
        Row definition for the pm20020maCntlocalLineTrscvPreSdFecBitCounter
        table
        "
	INDEX   { pm20020maCntlocalLineTrscvPreSdFecBitCounterIndex }
	::= { pm20020maCntlocalLineTrscvPreSdFecBitCounterTable 1 }


Pm20020maCntlocalLineTrscvPreSdFecBitCounterEntry ::=
	SEQUENCE {
	pm20020maCntlocalLineTrscvPreSdFecBitCounterIndex
		INTEGER,
	pm20020maCntlocalLineTrscvPreSdFecBitCounterValuePortn
		Counter64,
	pm20020maCntlocalLineTrscvPreSdFecBitCounterErrorPortn
		EkiOnOff,
	pm20020maCntlocalLineTrscvPreSdFecBitCounterOverloadPortn
		EkiOnOff
	}


pm20020maCntlocalLineTrscvPreSdFecBitCounterIndex OBJECT-TYPE
	SYNTAX  INTEGER(0..128)
	MAX-ACCESS  read-only
	STATUS current
	DESCRIPTION
        "
        Index definition for the pm20020maCntlocalLineTrscvPreSdFecBitCounter
        table
        "
	::= { pm20020maCntlocalLineTrscvPreSdFecBitCounterEntry 1 }


pm20020maCntlocalLineTrscvPreSdFecBitCounterValuePortn OBJECT-TYPE
	SYNTAX  Counter64
	MAX-ACCESS read-only
	STATUS current
	DESCRIPTION
        "
        Pre-SD FEC Bit Counter :This OID
        gives the current Bit count before
        the Soft Decision FEC  <Help> This
        counter gives the current Bit Count
        before the Soft Decision FEC
        "
	::= { pm20020maCntlocalLineTrscvPreSdFecBitCounterEntry 2 }


pm20020maCntlocalLineTrscvPreSdFecBitCounterErrorPortn OBJECT-TYPE
	SYNTAX  EkiOnOff
	MAX-ACCESS read-only
	STATUS current
	DESCRIPTION
        "
        Line Counter Error :This OID when
        set indicates the deframer timer
        counter value is invalid on Port
        "
	::= { pm20020maCntlocalLineTrscvPreSdFecBitCounterEntry 3 }


pm20020maCntlocalLineTrscvPreSdFecBitCounterOverloadPortn OBJECT-TYPE
	SYNTAX  EkiOnOff
	MAX-ACCESS read-only
	STATUS current
	DESCRIPTION
        "
        Line Counter Overload :This OID
        when set indicates a deframer timer
        counter overload on Port
        "
	::= { pm20020maCntlocalLineTrscvPreSdFecBitCounterEntry 4 }


--- *********************************************************
---     TABLE for the pm20020maCntlocalLineTrscvUncorrectedSdFecBitCounter articles
--- *********************************************************

pm20020maCntlocalLineTrscvUncorrectedSdFecBitCounterTable OBJECT-TYPE
	SYNTAX  SEQUENCE OF Pm20020maCntlocalLineTrscvUncorrectedSdFecBitCounterEntry
	MAX-ACCESS not-accessible
	STATUS current
	DESCRIPTION
        "
        List of pm20020maCntlocalLineTrscvUncorrectedSdFecBitCounter
        Article
        "
	::= { pm20020maCntLine 199 }


pm20020maCntlocalLineTrscvUncorrectedSdFecBitCounterEntry OBJECT-TYPE
	SYNTAX Pm20020maCntlocalLineTrscvUncorrectedSdFecBitCounterEntry
	MAX-ACCESS not-accessible
	STATUS current
	DESCRIPTION
        "
        Row definition for the pm20020maCntlocalLineTrscvUncorrectedSdFecBitCounter
        table
        "
	INDEX   { pm20020maCntlocalLineTrscvUncorrectedSdFecBitCounterIndex }
	::= { pm20020maCntlocalLineTrscvUncorrectedSdFecBitCounterTable 1 }


Pm20020maCntlocalLineTrscvUncorrectedSdFecBitCounterEntry ::=
	SEQUENCE {
	pm20020maCntlocalLineTrscvUncorrectedSdFecBitCounterIndex
		INTEGER,
	pm20020maCntlocalLineTrscvUncorrectedSdFecBitCounterValuePortn
		Counter64,
	pm20020maCntlocalLineTrscvUncorrectedSdFecBitCounterErrorPortn
		EkiOnOff,
	pm20020maCntlocalLineTrscvUncorrectedSdFecBitCounterOverloadPortn
		EkiOnOff
	}


pm20020maCntlocalLineTrscvUncorrectedSdFecBitCounterIndex OBJECT-TYPE
	SYNTAX  INTEGER(0..128)
	MAX-ACCESS  read-only
	STATUS current
	DESCRIPTION
        "
        Index definition for the pm20020maCntlocalLineTrscvUncorrectedSdFecBitCounter
        table
        "
	::= { pm20020maCntlocalLineTrscvUncorrectedSdFecBitCounterEntry 1 }


pm20020maCntlocalLineTrscvUncorrectedSdFecBitCounterValuePortn OBJECT-TYPE
	SYNTAX  Counter64
	MAX-ACCESS read-only
	STATUS current
	DESCRIPTION
        "
        Uncorrected SD FEC Bit Counter
        :This OID gives the current Bit
        count after the Soft Decision FEC
        (residual)  <Help> This counter
        gives the current Bit Count after
        the Soft Decision FEC (residual)
        "
	::= { pm20020maCntlocalLineTrscvUncorrectedSdFecBitCounterEntry 2 }


pm20020maCntlocalLineTrscvUncorrectedSdFecBitCounterErrorPortn OBJECT-TYPE
	SYNTAX  EkiOnOff
	MAX-ACCESS read-only
	STATUS current
	DESCRIPTION
        "
        Line Counter Error :This OID when
        set indicates the deframer timer
        counter value is invalid on Port
        "
	::= { pm20020maCntlocalLineTrscvUncorrectedSdFecBitCounterEntry 3 }


pm20020maCntlocalLineTrscvUncorrectedSdFecBitCounterOverloadPortn OBJECT-TYPE
	SYNTAX  EkiOnOff
	MAX-ACCESS read-only
	STATUS current
	DESCRIPTION
        "
        Line Counter Overload :This OID
        when set indicates a deframer timer
        counter overload on Port
        "
	::= { pm20020maCntlocalLineTrscvUncorrectedSdFecBitCounterEntry 4 }







--- *****************************************************
--- $$$$$$$$$$$$$$$$$$$$$$$$$$$$$$$$$$$$$$$$$$$$$$$$$$$$$
---     RMON - 64 bits COUNTERS
--- $$$$$$$$$$$$$$$$$$$$$$$$$$$$$$$$$$$$$$$$$$$$$$$$$$$$$
--- *****************************************************



--- *********************************************************
---     TABLE for the pm20020maMonupRmonBytesCounterClientInput articles
--- *********************************************************

pm20020maMonupRmonBytesCounterClientInputTable OBJECT-TYPE
	SYNTAX  SEQUENCE OF Pm20020maMonupRmonBytesCounterClientInputEntry
	MAX-ACCESS not-accessible
	STATUS current
	DESCRIPTION
        "
        List of pm20020maMonupRmonBytesCounterClientInput
        Article
        "
	::= { pm20020maMonClientRmonCounter 16 }


pm20020maMonupRmonBytesCounterClientInputEntry OBJECT-TYPE
	SYNTAX Pm20020maMonupRmonBytesCounterClientInputEntry
	MAX-ACCESS not-accessible
	STATUS current
	DESCRIPTION
        "
        Row definition for the pm20020maMonupRmonBytesCounterClientInput
        table
        "
	INDEX   { pm20020maMonupRmonBytesCounterClientInputIndex }
	::= { pm20020maMonupRmonBytesCounterClientInputTable 1 }


Pm20020maMonupRmonBytesCounterClientInputEntry ::=
	SEQUENCE {
	pm20020maMonupRmonBytesCounterClientInputIndex
		INTEGER,
	pm20020maMonupRmonBytesCounterClientInputValuePortn
		Counter64,
	pm20020maMonupRmonBytesCounterClientInputErrorPortn
		EkiOnOff,
	pm20020maMonupRmonBytesCounterClientInputOverloadPortn
		EkiOnOff
	}


pm20020maMonupRmonBytesCounterClientInputIndex OBJECT-TYPE
	SYNTAX  INTEGER(0..128)
	MAX-ACCESS  read-only
	STATUS current
	DESCRIPTION
        "
        Index definition for the pm20020maMonupRmonBytesCounterClientInput
        table
        "
	::= { pm20020maMonupRmonBytesCounterClientInputEntry 1 }


pm20020maMonupRmonBytesCounterClientInputValuePortn OBJECT-TYPE
	SYNTAX  Counter64
	MAX-ACCESS read-only
	STATUS current
	DESCRIPTION
        "
        Client Input Bytes :This counter
        is increased each time a data byte
        is received on the client port
          <Help>  This counter gives the
        number of bytes received on the
        client port
        "
	::= { pm20020maMonupRmonBytesCounterClientInputEntry 2 }


pm20020maMonupRmonBytesCounterClientInputErrorPortn OBJECT-TYPE
	SYNTAX  EkiOnOff
	MAX-ACCESS read-only
	STATUS current
	DESCRIPTION
        "
        Bytes Counter Error :This OID
         when set indicates the Bytes counter
        value is invalid on client port
        "
	::= { pm20020maMonupRmonBytesCounterClientInputEntry 3 }


pm20020maMonupRmonBytesCounterClientInputOverloadPortn OBJECT-TYPE
	SYNTAX  EkiOnOff
	MAX-ACCESS read-only
	STATUS current
	DESCRIPTION
        "
        Bytes Counter Overload :This OID
        when set indicates a Bytes counter
        overload on client port
        "
	::= { pm20020maMonupRmonBytesCounterClientInputEntry 4 }


--- *********************************************************
---     TABLE for the pm20020maMonupRmonCrcErrorsCounterClientInput articles
--- *********************************************************

pm20020maMonupRmonCrcErrorsCounterClientInputTable OBJECT-TYPE
	SYNTAX  SEQUENCE OF Pm20020maMonupRmonCrcErrorsCounterClientInputEntry
	MAX-ACCESS not-accessible
	STATUS current
	DESCRIPTION
        "
        List of pm20020maMonupRmonCrcErrorsCounterClientInput
        Article
        "
	::= { pm20020maMonClientRmonCounter 48 }


pm20020maMonupRmonCrcErrorsCounterClientInputEntry OBJECT-TYPE
	SYNTAX Pm20020maMonupRmonCrcErrorsCounterClientInputEntry
	MAX-ACCESS not-accessible
	STATUS current
	DESCRIPTION
        "
        Row definition for the pm20020maMonupRmonCrcErrorsCounterClientInput
        table
        "
	INDEX   { pm20020maMonupRmonCrcErrorsCounterClientInputIndex }
	::= { pm20020maMonupRmonCrcErrorsCounterClientInputTable 1 }


Pm20020maMonupRmonCrcErrorsCounterClientInputEntry ::=
	SEQUENCE {
	pm20020maMonupRmonCrcErrorsCounterClientInputIndex
		INTEGER,
	pm20020maMonupRmonCrcErrorsCounterClientInputValuePortn
		Counter64,
	pm20020maMonupRmonCrcErrorsCounterClientInputErrorPortn
		EkiOnOff,
	pm20020maMonupRmonCrcErrorsCounterClientInputOverloadPortn
		EkiOnOff
	}


pm20020maMonupRmonCrcErrorsCounterClientInputIndex OBJECT-TYPE
	SYNTAX  INTEGER(0..128)
	MAX-ACCESS  read-only
	STATUS current
	DESCRIPTION
        "
        Index definition for the pm20020maMonupRmonCrcErrorsCounterClientInput
        table
        "
	::= { pm20020maMonupRmonCrcErrorsCounterClientInputEntry 1 }


pm20020maMonupRmonCrcErrorsCounterClientInputValuePortn OBJECT-TYPE
	SYNTAX  Counter64
	MAX-ACCESS read-only
	STATUS current
	DESCRIPTION
        "
        Client Input CRC Errors :This
         counter is increased each time
        a CRC error is detected on the
         client port<Help>  This counter
        gives the number of CRC Errors
         received on the client port
        "
	::= { pm20020maMonupRmonCrcErrorsCounterClientInputEntry 2 }


pm20020maMonupRmonCrcErrorsCounterClientInputErrorPortn OBJECT-TYPE
	SYNTAX  EkiOnOff
	MAX-ACCESS read-only
	STATUS current
	DESCRIPTION
        "
        CRC Errors Counter Error :This
        OID when set indicates the CRC
         Errors counter value is invalid
        on client port
        "
	::= { pm20020maMonupRmonCrcErrorsCounterClientInputEntry 3 }


pm20020maMonupRmonCrcErrorsCounterClientInputOverloadPortn OBJECT-TYPE
	SYNTAX  EkiOnOff
	MAX-ACCESS read-only
	STATUS current
	DESCRIPTION
        "
        CRC Errors Counter Overload :This
        OID when set indicates a CRC Errors
        counter overload on client port
        "
	::= { pm20020maMonupRmonCrcErrorsCounterClientInputEntry 4 }


--- *********************************************************
---     TABLE for the pm20020maMonupRmonPacketsCounterClientInput articles
--- *********************************************************

pm20020maMonupRmonPacketsCounterClientInputTable OBJECT-TYPE
	SYNTAX  SEQUENCE OF Pm20020maMonupRmonPacketsCounterClientInputEntry
	MAX-ACCESS not-accessible
	STATUS current
	DESCRIPTION
        "
        List of pm20020maMonupRmonPacketsCounterClientInput
        Article
        "
	::= { pm20020maMonClientRmonCounter 80 }


pm20020maMonupRmonPacketsCounterClientInputEntry OBJECT-TYPE
	SYNTAX Pm20020maMonupRmonPacketsCounterClientInputEntry
	MAX-ACCESS not-accessible
	STATUS current
	DESCRIPTION
        "
        Row definition for the pm20020maMonupRmonPacketsCounterClientInput
        table
        "
	INDEX   { pm20020maMonupRmonPacketsCounterClientInputIndex }
	::= { pm20020maMonupRmonPacketsCounterClientInputTable 1 }


Pm20020maMonupRmonPacketsCounterClientInputEntry ::=
	SEQUENCE {
	pm20020maMonupRmonPacketsCounterClientInputIndex
		INTEGER,
	pm20020maMonupRmonPacketsCounterClientInputValuePortn
		Counter64,
	pm20020maMonupRmonPacketsCounterClientInputErrorPortn
		EkiOnOff,
	pm20020maMonupRmonPacketsCounterClientInputOverloadPortn
		EkiOnOff
	}


pm20020maMonupRmonPacketsCounterClientInputIndex OBJECT-TYPE
	SYNTAX  INTEGER(0..128)
	MAX-ACCESS  read-only
	STATUS current
	DESCRIPTION
        "
        Index definition for the pm20020maMonupRmonPacketsCounterClientInput
        table
        "
	::= { pm20020maMonupRmonPacketsCounterClientInputEntry 1 }


pm20020maMonupRmonPacketsCounterClientInputValuePortn OBJECT-TYPE
	SYNTAX  Counter64
	MAX-ACCESS read-only
	STATUS current
	DESCRIPTION
        "
        Client Input Packets :This counter
        is increased each time a packet
        is received on the client port
          <Help>  This counter gives the
        number of packets received on the
        client port
        "
	::= { pm20020maMonupRmonPacketsCounterClientInputEntry 2 }


pm20020maMonupRmonPacketsCounterClientInputErrorPortn OBJECT-TYPE
	SYNTAX  EkiOnOff
	MAX-ACCESS read-only
	STATUS current
	DESCRIPTION
        "
        Packets Counter Error :This OID
        when set indicates the Packets
         counter value is invalid on client
        port
        "
	::= { pm20020maMonupRmonPacketsCounterClientInputEntry 3 }


pm20020maMonupRmonPacketsCounterClientInputOverloadPortn OBJECT-TYPE
	SYNTAX  EkiOnOff
	MAX-ACCESS read-only
	STATUS current
	DESCRIPTION
        "
        Packets Counter Overload :This
        OID when set indicates a Packets
        counter overload on client port
        "
	::= { pm20020maMonupRmonPacketsCounterClientInputEntry 4 }


--- *********************************************************
---     TABLE for the pm20020maMonupRmonBroadcastCounterClientInput articles
--- *********************************************************

pm20020maMonupRmonBroadcastCounterClientInputTable OBJECT-TYPE
	SYNTAX  SEQUENCE OF Pm20020maMonupRmonBroadcastCounterClientInputEntry
	MAX-ACCESS not-accessible
	STATUS current
	DESCRIPTION
        "
        List of pm20020maMonupRmonBroadcastCounterClientInput
        Article
        "
	::= { pm20020maMonClientRmonCounter 112 }


pm20020maMonupRmonBroadcastCounterClientInputEntry OBJECT-TYPE
	SYNTAX Pm20020maMonupRmonBroadcastCounterClientInputEntry
	MAX-ACCESS not-accessible
	STATUS current
	DESCRIPTION
        "
        Row definition for the pm20020maMonupRmonBroadcastCounterClientInput
        table
        "
	INDEX   { pm20020maMonupRmonBroadcastCounterClientInputIndex }
	::= { pm20020maMonupRmonBroadcastCounterClientInputTable 1 }


Pm20020maMonupRmonBroadcastCounterClientInputEntry ::=
	SEQUENCE {
	pm20020maMonupRmonBroadcastCounterClientInputIndex
		INTEGER,
	pm20020maMonupRmonBroadcastCounterClientInputValuePortn
		Counter64,
	pm20020maMonupRmonBroadcastCounterClientInputErrorPortn
		EkiOnOff,
	pm20020maMonupRmonBroadcastCounterClientInputOverloadPortn
		EkiOnOff
	}


pm20020maMonupRmonBroadcastCounterClientInputIndex OBJECT-TYPE
	SYNTAX  INTEGER(0..128)
	MAX-ACCESS  read-only
	STATUS current
	DESCRIPTION
        "
        Index definition for the pm20020maMonupRmonBroadcastCounterClientInput
        table
        "
	::= { pm20020maMonupRmonBroadcastCounterClientInputEntry 1 }


pm20020maMonupRmonBroadcastCounterClientInputValuePortn OBJECT-TYPE
	SYNTAX  Counter64
	MAX-ACCESS read-only
	STATUS current
	DESCRIPTION
        "
        Client Input Broadcast Packets
        :This counter is increased each
        time a broadcast packet is received
        on the client port  <Help>  This
        counter gives the number of Broadcast
        packets received on the client
         port
        "
	::= { pm20020maMonupRmonBroadcastCounterClientInputEntry 2 }


pm20020maMonupRmonBroadcastCounterClientInputErrorPortn OBJECT-TYPE
	SYNTAX  EkiOnOff
	MAX-ACCESS read-only
	STATUS current
	DESCRIPTION
        "
        Broadcast Counter Error :This
         OID when set indicates the Broadcast
        counter value is invalid on client
        port
        "
	::= { pm20020maMonupRmonBroadcastCounterClientInputEntry 3 }


pm20020maMonupRmonBroadcastCounterClientInputOverloadPortn OBJECT-TYPE
	SYNTAX  EkiOnOff
	MAX-ACCESS read-only
	STATUS current
	DESCRIPTION
        "
        Broadcast Counter Overload :This
        OID when set indicates a Broadcast
        counter overload on client port
        "
	::= { pm20020maMonupRmonBroadcastCounterClientInputEntry 4 }


--- *********************************************************
---     TABLE for the pm20020maMonupRmonMulticastCounterClientInput articles
--- *********************************************************

pm20020maMonupRmonMulticastCounterClientInputTable OBJECT-TYPE
	SYNTAX  SEQUENCE OF Pm20020maMonupRmonMulticastCounterClientInputEntry
	MAX-ACCESS not-accessible
	STATUS current
	DESCRIPTION
        "
        List of pm20020maMonupRmonMulticastCounterClientInput
        Article
        "
	::= { pm20020maMonClientRmonCounter 144 }


pm20020maMonupRmonMulticastCounterClientInputEntry OBJECT-TYPE
	SYNTAX Pm20020maMonupRmonMulticastCounterClientInputEntry
	MAX-ACCESS not-accessible
	STATUS current
	DESCRIPTION
        "
        Row definition for the pm20020maMonupRmonMulticastCounterClientInput
        table
        "
	INDEX   { pm20020maMonupRmonMulticastCounterClientInputIndex }
	::= { pm20020maMonupRmonMulticastCounterClientInputTable 1 }


Pm20020maMonupRmonMulticastCounterClientInputEntry ::=
	SEQUENCE {
	pm20020maMonupRmonMulticastCounterClientInputIndex
		INTEGER,
	pm20020maMonupRmonMulticastCounterClientInputValuePortn
		Counter64,
	pm20020maMonupRmonMulticastCounterClientInputErrorPortn
		EkiOnOff,
	pm20020maMonupRmonMulticastCounterClientInputOverloadPortn
		EkiOnOff
	}


pm20020maMonupRmonMulticastCounterClientInputIndex OBJECT-TYPE
	SYNTAX  INTEGER(0..128)
	MAX-ACCESS  read-only
	STATUS current
	DESCRIPTION
        "
        Index definition for the pm20020maMonupRmonMulticastCounterClientInput
        table
        "
	::= { pm20020maMonupRmonMulticastCounterClientInputEntry 1 }


pm20020maMonupRmonMulticastCounterClientInputValuePortn OBJECT-TYPE
	SYNTAX  Counter64
	MAX-ACCESS read-only
	STATUS current
	DESCRIPTION
        "
        Client Input Multicast Packets
        :This counter is increased each
        time a Multicast packet is received
        on the client port  <Help>  This
        counter gives the number of Multicast
        packets received on the client
         port
        "
	::= { pm20020maMonupRmonMulticastCounterClientInputEntry 2 }


pm20020maMonupRmonMulticastCounterClientInputErrorPortn OBJECT-TYPE
	SYNTAX  EkiOnOff
	MAX-ACCESS read-only
	STATUS current
	DESCRIPTION
        "
        Multicast Counter Error :This
         OID when set indicates the Multicast
        counter value is invalid on client
        port
        "
	::= { pm20020maMonupRmonMulticastCounterClientInputEntry 3 }


pm20020maMonupRmonMulticastCounterClientInputOverloadPortn OBJECT-TYPE
	SYNTAX  EkiOnOff
	MAX-ACCESS read-only
	STATUS current
	DESCRIPTION
        "
        Multicast Counter Overload :This
        OID when set indicates a Multicast
        counter overload on client port
        "
	::= { pm20020maMonupRmonMulticastCounterClientInputEntry 4 }


--- *********************************************************
---     TABLE for the pm20020maMonupRmonPauseFrameCounterClientInput articles
--- *********************************************************

pm20020maMonupRmonPauseFrameCounterClientInputTable OBJECT-TYPE
	SYNTAX  SEQUENCE OF Pm20020maMonupRmonPauseFrameCounterClientInputEntry
	MAX-ACCESS not-accessible
	STATUS current
	DESCRIPTION
        "
        List of pm20020maMonupRmonPauseFrameCounterClientInput
        Article
        "
	::= { pm20020maMonClientRmonCounter 176 }


pm20020maMonupRmonPauseFrameCounterClientInputEntry OBJECT-TYPE
	SYNTAX Pm20020maMonupRmonPauseFrameCounterClientInputEntry
	MAX-ACCESS not-accessible
	STATUS current
	DESCRIPTION
        "
        Row definition for the pm20020maMonupRmonPauseFrameCounterClientInput
        table
        "
	INDEX   { pm20020maMonupRmonPauseFrameCounterClientInputIndex }
	::= { pm20020maMonupRmonPauseFrameCounterClientInputTable 1 }


Pm20020maMonupRmonPauseFrameCounterClientInputEntry ::=
	SEQUENCE {
	pm20020maMonupRmonPauseFrameCounterClientInputIndex
		INTEGER,
	pm20020maMonupRmonPauseFrameCounterClientInputValuePortn
		Counter64,
	pm20020maMonupRmonPauseFrameCounterClientInputErrorPortn
		EkiOnOff,
	pm20020maMonupRmonPauseFrameCounterClientInputOverloadPortn
		EkiOnOff
	}


pm20020maMonupRmonPauseFrameCounterClientInputIndex OBJECT-TYPE
	SYNTAX  INTEGER(0..128)
	MAX-ACCESS  read-only
	STATUS current
	DESCRIPTION
        "
        Index definition for the pm20020maMonupRmonPauseFrameCounterClientInput
        table
        "
	::= { pm20020maMonupRmonPauseFrameCounterClientInputEntry 1 }


pm20020maMonupRmonPauseFrameCounterClientInputValuePortn OBJECT-TYPE
	SYNTAX  Counter64
	MAX-ACCESS read-only
	STATUS current
	DESCRIPTION
        "
        Client Input Pause Frames :This
        counter is increased each time
         a Pause frame is received on the
        client port  <Help>  This counter
        gives the number of Pause frames
        received on the client port
        "
	::= { pm20020maMonupRmonPauseFrameCounterClientInputEntry 2 }


pm20020maMonupRmonPauseFrameCounterClientInputErrorPortn OBJECT-TYPE
	SYNTAX  EkiOnOff
	MAX-ACCESS read-only
	STATUS current
	DESCRIPTION
        "
        Pause Counter Error :This OID
         when set indicates the Pause counter
        value is invalid on client port
        "
	::= { pm20020maMonupRmonPauseFrameCounterClientInputEntry 3 }


pm20020maMonupRmonPauseFrameCounterClientInputOverloadPortn OBJECT-TYPE
	SYNTAX  EkiOnOff
	MAX-ACCESS read-only
	STATUS current
	DESCRIPTION
        "
        Pause Counter Overload :This OID
        when set indicates a Pause counter
        overload on client port
        "
	::= { pm20020maMonupRmonPauseFrameCounterClientInputEntry 4 }


--- *********************************************************
---     TABLE for the pm20020maMonupRmonUnicastCounterClientInput articles
--- *********************************************************

pm20020maMonupRmonUnicastCounterClientInputTable OBJECT-TYPE
	SYNTAX  SEQUENCE OF Pm20020maMonupRmonUnicastCounterClientInputEntry
	MAX-ACCESS not-accessible
	STATUS current
	DESCRIPTION
        "
        List of pm20020maMonupRmonUnicastCounterClientInput
        Article
        "
	::= { pm20020maMonClientRmonCounter 304 }


pm20020maMonupRmonUnicastCounterClientInputEntry OBJECT-TYPE
	SYNTAX Pm20020maMonupRmonUnicastCounterClientInputEntry
	MAX-ACCESS not-accessible
	STATUS current
	DESCRIPTION
        "
        Row definition for the pm20020maMonupRmonUnicastCounterClientInput
        table
        "
	INDEX   { pm20020maMonupRmonUnicastCounterClientInputIndex }
	::= { pm20020maMonupRmonUnicastCounterClientInputTable 1 }


Pm20020maMonupRmonUnicastCounterClientInputEntry ::=
	SEQUENCE {
	pm20020maMonupRmonUnicastCounterClientInputIndex
		INTEGER,
	pm20020maMonupRmonUnicastCounterClientInputValuePortn
		Counter64,
	pm20020maMonupRmonUnicastCounterClientInputErrorPortn
		EkiOnOff,
	pm20020maMonupRmonUnicastCounterClientInputOverloadPortn
		EkiOnOff
	}


pm20020maMonupRmonUnicastCounterClientInputIndex OBJECT-TYPE
	SYNTAX  INTEGER(0..128)
	MAX-ACCESS  read-only
	STATUS current
	DESCRIPTION
        "
        Index definition for the pm20020maMonupRmonUnicastCounterClientInput
        table
        "
	::= { pm20020maMonupRmonUnicastCounterClientInputEntry 1 }


pm20020maMonupRmonUnicastCounterClientInputValuePortn OBJECT-TYPE
	SYNTAX  Counter64
	MAX-ACCESS read-only
	STATUS current
	DESCRIPTION
        "
        Client Input Unicast Packets :This
        counter is increased each time
         a Unicast packet is received on
        the client port  <Help>  This counter
        gives the number of Unicast packets
        received on the client port
        "
	::= { pm20020maMonupRmonUnicastCounterClientInputEntry 2 }


pm20020maMonupRmonUnicastCounterClientInputErrorPortn OBJECT-TYPE
	SYNTAX  EkiOnOff
	MAX-ACCESS read-only
	STATUS current
	DESCRIPTION
        "
        Unicast Counter Error :This OID
        when set indicates the Unicast
         counter value is invalid on client
        port
        "
	::= { pm20020maMonupRmonUnicastCounterClientInputEntry 3 }


pm20020maMonupRmonUnicastCounterClientInputOverloadPortn OBJECT-TYPE
	SYNTAX  EkiOnOff
	MAX-ACCESS read-only
	STATUS current
	DESCRIPTION
        "
        Unicast Counter Overload :This
        OID when set indicates a Unicast
        counter overload on client port
        "
	::= { pm20020maMonupRmonUnicastCounterClientInputEntry 4 }


--- *********************************************************
---     TABLE for the pm20020maMonupRmonNonunicastCounterClientInput articles
--- *********************************************************

pm20020maMonupRmonNonunicastCounterClientInputTable OBJECT-TYPE
	SYNTAX  SEQUENCE OF Pm20020maMonupRmonNonunicastCounterClientInputEntry
	MAX-ACCESS not-accessible
	STATUS current
	DESCRIPTION
        "
        List of pm20020maMonupRmonNonunicastCounterClientInput
        Article
        "
	::= { pm20020maMonClientRmonCounter 336 }


pm20020maMonupRmonNonunicastCounterClientInputEntry OBJECT-TYPE
	SYNTAX Pm20020maMonupRmonNonunicastCounterClientInputEntry
	MAX-ACCESS not-accessible
	STATUS current
	DESCRIPTION
        "
        Row definition for the pm20020maMonupRmonNonunicastCounterClientInput
        table
        "
	INDEX   { pm20020maMonupRmonNonunicastCounterClientInputIndex }
	::= { pm20020maMonupRmonNonunicastCounterClientInputTable 1 }


Pm20020maMonupRmonNonunicastCounterClientInputEntry ::=
	SEQUENCE {
	pm20020maMonupRmonNonunicastCounterClientInputIndex
		INTEGER,
	pm20020maMonupRmonNonunicastCounterClientInputValuePortn
		Counter64,
	pm20020maMonupRmonNonunicastCounterClientInputErrorPortn
		EkiOnOff,
	pm20020maMonupRmonNonunicastCounterClientInputOverloadPortn
		EkiOnOff
	}


pm20020maMonupRmonNonunicastCounterClientInputIndex OBJECT-TYPE
	SYNTAX  INTEGER(0..128)
	MAX-ACCESS  read-only
	STATUS current
	DESCRIPTION
        "
        Index definition for the pm20020maMonupRmonNonunicastCounterClientInput
        table
        "
	::= { pm20020maMonupRmonNonunicastCounterClientInputEntry 1 }


pm20020maMonupRmonNonunicastCounterClientInputValuePortn OBJECT-TYPE
	SYNTAX  Counter64
	MAX-ACCESS read-only
	STATUS current
	DESCRIPTION
        "
        Client Input Non Unicast Packets
        :This counter is increased each
        time a Non-Unicast packet is received
        on the client port  <Help>  This
        counter gives the number of Non-Unicast
        packets received on the client
         port
        "
	::= { pm20020maMonupRmonNonunicastCounterClientInputEntry 2 }


pm20020maMonupRmonNonunicastCounterClientInputErrorPortn OBJECT-TYPE
	SYNTAX  EkiOnOff
	MAX-ACCESS read-only
	STATUS current
	DESCRIPTION
        "
        Non Unicast Counter Error :This
        OID when set indicates the Non-Unicast
        counter value is invalid on client
        port
        "
	::= { pm20020maMonupRmonNonunicastCounterClientInputEntry 3 }


pm20020maMonupRmonNonunicastCounterClientInputOverloadPortn OBJECT-TYPE
	SYNTAX  EkiOnOff
	MAX-ACCESS read-only
	STATUS current
	DESCRIPTION
        "
        Non Unicast Counter Overload :This
        OID when set indicates a Non-Unicast
        counter overload on client port
        "
	::= { pm20020maMonupRmonNonunicastCounterClientInputEntry 4 }


--- *********************************************************
---     TABLE for the pm20020maMondownRmonBytesCounterClientOutput articles
--- *********************************************************

pm20020maMondownRmonBytesCounterClientOutputTable OBJECT-TYPE
	SYNTAX  SEQUENCE OF Pm20020maMondownRmonBytesCounterClientOutputEntry
	MAX-ACCESS not-accessible
	STATUS current
	DESCRIPTION
        "
        List of pm20020maMondownRmonBytesCounterClientOutput
        Article
        "
	::= { pm20020maMonClientRmonCounter 400 }


pm20020maMondownRmonBytesCounterClientOutputEntry OBJECT-TYPE
	SYNTAX Pm20020maMondownRmonBytesCounterClientOutputEntry
	MAX-ACCESS not-accessible
	STATUS current
	DESCRIPTION
        "
        Row definition for the pm20020maMondownRmonBytesCounterClientOutput
        table
        "
	INDEX   { pm20020maMondownRmonBytesCounterClientOutputIndex }
	::= { pm20020maMondownRmonBytesCounterClientOutputTable 1 }


Pm20020maMondownRmonBytesCounterClientOutputEntry ::=
	SEQUENCE {
	pm20020maMondownRmonBytesCounterClientOutputIndex
		INTEGER,
	pm20020maMondownRmonBytesCounterClientOutputValuePortn
		Counter64,
	pm20020maMondownRmonBytesCounterClientOutputErrorPortn
		EkiOnOff,
	pm20020maMondownRmonBytesCounterClientOutputOverloadPortn
		EkiOnOff
	}


pm20020maMondownRmonBytesCounterClientOutputIndex OBJECT-TYPE
	SYNTAX  INTEGER(0..128)
	MAX-ACCESS  read-only
	STATUS current
	DESCRIPTION
        "
        Index definition for the pm20020maMondownRmonBytesCounterClientOutput
        table
        "
	::= { pm20020maMondownRmonBytesCounterClientOutputEntry 1 }


pm20020maMondownRmonBytesCounterClientOutputValuePortn OBJECT-TYPE
	SYNTAX  Counter64
	MAX-ACCESS read-only
	STATUS current
	DESCRIPTION
        "
        Client Output Bytes :This counter
        is increased each time a data byte
        is transmitted on the client port
        <Help> This counter gives the number
        of bytes transmitted on the client
        port
        "
	::= { pm20020maMondownRmonBytesCounterClientOutputEntry 2 }


pm20020maMondownRmonBytesCounterClientOutputErrorPortn OBJECT-TYPE
	SYNTAX  EkiOnOff
	MAX-ACCESS read-only
	STATUS current
	DESCRIPTION
        "
        Bytes Counter Error :This OID
         when set indicates the Bytes counter
        value is invalid on client port
        "
	::= { pm20020maMondownRmonBytesCounterClientOutputEntry 3 }


pm20020maMondownRmonBytesCounterClientOutputOverloadPortn OBJECT-TYPE
	SYNTAX  EkiOnOff
	MAX-ACCESS read-only
	STATUS current
	DESCRIPTION
        "
        Bytes Counter Overload :This OID
        when set indicates a Bytes counter
        overload on client port

        "
	::= { pm20020maMondownRmonBytesCounterClientOutputEntry 4 }


--- *********************************************************
---     TABLE for the pm20020maMondownRmonCrcErrorsCounterClientOutput articles
--- *********************************************************

pm20020maMondownRmonCrcErrorsCounterClientOutputTable OBJECT-TYPE
	SYNTAX  SEQUENCE OF Pm20020maMondownRmonCrcErrorsCounterClientOutputEntry
	MAX-ACCESS not-accessible
	STATUS current
	DESCRIPTION
        "
        List of pm20020maMondownRmonCrcErrorsCounterClientOutput
        Article
        "
	::= { pm20020maMonClientRmonCounter 432 }


pm20020maMondownRmonCrcErrorsCounterClientOutputEntry OBJECT-TYPE
	SYNTAX Pm20020maMondownRmonCrcErrorsCounterClientOutputEntry
	MAX-ACCESS not-accessible
	STATUS current
	DESCRIPTION
        "
        Row definition for the pm20020maMondownRmonCrcErrorsCounterClientOutput
        table
        "
	INDEX   { pm20020maMondownRmonCrcErrorsCounterClientOutputIndex }
	::= { pm20020maMondownRmonCrcErrorsCounterClientOutputTable 1 }


Pm20020maMondownRmonCrcErrorsCounterClientOutputEntry ::=
	SEQUENCE {
	pm20020maMondownRmonCrcErrorsCounterClientOutputIndex
		INTEGER,
	pm20020maMondownRmonCrcErrorsCounterClientOutputValuePortn
		Counter64,
	pm20020maMondownRmonCrcErrorsCounterClientOutputErrorPortn
		EkiOnOff,
	pm20020maMondownRmonCrcErrorsCounterClientOutputOverloadPortn
		EkiOnOff
	}


pm20020maMondownRmonCrcErrorsCounterClientOutputIndex OBJECT-TYPE
	SYNTAX  INTEGER(0..128)
	MAX-ACCESS  read-only
	STATUS current
	DESCRIPTION
        "
        Index definition for the pm20020maMondownRmonCrcErrorsCounterClientOutput
        table
        "
	::= { pm20020maMondownRmonCrcErrorsCounterClientOutputEntry 1 }


pm20020maMondownRmonCrcErrorsCounterClientOutputValuePortn OBJECT-TYPE
	SYNTAX  Counter64
	MAX-ACCESS read-only
	STATUS current
	DESCRIPTION
        "
        Client Output CRC Errors :This
        counter is increased each time
         a CRC error is detected on the
        transmit client port  <Help>  This
        counter gives the number of CRC
        Errors transmitted on the client
        port
        "
	::= { pm20020maMondownRmonCrcErrorsCounterClientOutputEntry 2 }


pm20020maMondownRmonCrcErrorsCounterClientOutputErrorPortn OBJECT-TYPE
	SYNTAX  EkiOnOff
	MAX-ACCESS read-only
	STATUS current
	DESCRIPTION
        "
        CRC Errors Counter Error :This
        OID when set indicates the CRC
         Errors counter value is invalid
        on client port
        "
	::= { pm20020maMondownRmonCrcErrorsCounterClientOutputEntry 3 }


pm20020maMondownRmonCrcErrorsCounterClientOutputOverloadPortn OBJECT-TYPE
	SYNTAX  EkiOnOff
	MAX-ACCESS read-only
	STATUS current
	DESCRIPTION
        "
        CRC Errors Counter Overload :This
        OID when set indicates a CRC Errors
        counter overload on client port
        "
	::= { pm20020maMondownRmonCrcErrorsCounterClientOutputEntry 4 }


--- *********************************************************
---     TABLE for the pm20020maMondownRmonPacketsCounterClientOutput articles
--- *********************************************************

pm20020maMondownRmonPacketsCounterClientOutputTable OBJECT-TYPE
	SYNTAX  SEQUENCE OF Pm20020maMondownRmonPacketsCounterClientOutputEntry
	MAX-ACCESS not-accessible
	STATUS current
	DESCRIPTION
        "
        List of pm20020maMondownRmonPacketsCounterClientOutput
        Article
        "
	::= { pm20020maMonClientRmonCounter 464 }


pm20020maMondownRmonPacketsCounterClientOutputEntry OBJECT-TYPE
	SYNTAX Pm20020maMondownRmonPacketsCounterClientOutputEntry
	MAX-ACCESS not-accessible
	STATUS current
	DESCRIPTION
        "
        Row definition for the pm20020maMondownRmonPacketsCounterClientOutput
        table
        "
	INDEX   { pm20020maMondownRmonPacketsCounterClientOutputIndex }
	::= { pm20020maMondownRmonPacketsCounterClientOutputTable 1 }


Pm20020maMondownRmonPacketsCounterClientOutputEntry ::=
	SEQUENCE {
	pm20020maMondownRmonPacketsCounterClientOutputIndex
		INTEGER,
	pm20020maMondownRmonPacketsCounterClientOutputValuePortn
		Counter64,
	pm20020maMondownRmonPacketsCounterClientOutputErrorPortn
		EkiOnOff,
	pm20020maMondownRmonPacketsCounterClientOutputOverloadPortn
		EkiOnOff
	}


pm20020maMondownRmonPacketsCounterClientOutputIndex OBJECT-TYPE
	SYNTAX  INTEGER(0..128)
	MAX-ACCESS  read-only
	STATUS current
	DESCRIPTION
        "
        Index definition for the pm20020maMondownRmonPacketsCounterClientOutput
        table
        "
	::= { pm20020maMondownRmonPacketsCounterClientOutputEntry 1 }


pm20020maMondownRmonPacketsCounterClientOutputValuePortn OBJECT-TYPE
	SYNTAX  Counter64
	MAX-ACCESS read-only
	STATUS current
	DESCRIPTION
        "
        Client Output Packets :This counter
        is increased each time a packet
        is transmitted on the client port
         <Help>  This counter gives the
        number of packets transmitted on
        the client port
        "
	::= { pm20020maMondownRmonPacketsCounterClientOutputEntry 2 }


pm20020maMondownRmonPacketsCounterClientOutputErrorPortn OBJECT-TYPE
	SYNTAX  EkiOnOff
	MAX-ACCESS read-only
	STATUS current
	DESCRIPTION
        "
        Packets Counter Error :This OID
        when set indicates the Packets
         counter value is invalid on client
        port
        "
	::= { pm20020maMondownRmonPacketsCounterClientOutputEntry 3 }


pm20020maMondownRmonPacketsCounterClientOutputOverloadPortn OBJECT-TYPE
	SYNTAX  EkiOnOff
	MAX-ACCESS read-only
	STATUS current
	DESCRIPTION
        "
        Packets Counter Overload :This
        OID when set indicates a Packets
        counter overload on client port
        "
	::= { pm20020maMondownRmonPacketsCounterClientOutputEntry 4 }


--- *********************************************************
---     TABLE for the pm20020maMondownRmonBroadcastCounterClientOutput articles
--- *********************************************************

pm20020maMondownRmonBroadcastCounterClientOutputTable OBJECT-TYPE
	SYNTAX  SEQUENCE OF Pm20020maMondownRmonBroadcastCounterClientOutputEntry
	MAX-ACCESS not-accessible
	STATUS current
	DESCRIPTION
        "
        List of pm20020maMondownRmonBroadcastCounterClientOutput
        Article
        "
	::= { pm20020maMonClientRmonCounter 496 }


pm20020maMondownRmonBroadcastCounterClientOutputEntry OBJECT-TYPE
	SYNTAX Pm20020maMondownRmonBroadcastCounterClientOutputEntry
	MAX-ACCESS not-accessible
	STATUS current
	DESCRIPTION
        "
        Row definition for the pm20020maMondownRmonBroadcastCounterClientOutput
        table
        "
	INDEX   { pm20020maMondownRmonBroadcastCounterClientOutputIndex }
	::= { pm20020maMondownRmonBroadcastCounterClientOutputTable 1 }


Pm20020maMondownRmonBroadcastCounterClientOutputEntry ::=
	SEQUENCE {
	pm20020maMondownRmonBroadcastCounterClientOutputIndex
		INTEGER,
	pm20020maMondownRmonBroadcastCounterClientOutputValuePortn
		Counter64,
	pm20020maMondownRmonBroadcastCounterClientOutputErrorPortn
		EkiOnOff,
	pm20020maMondownRmonBroadcastCounterClientOutputOverloadPortn
		EkiOnOff
	}


pm20020maMondownRmonBroadcastCounterClientOutputIndex OBJECT-TYPE
	SYNTAX  INTEGER(0..128)
	MAX-ACCESS  read-only
	STATUS current
	DESCRIPTION
        "
        Index definition for the pm20020maMondownRmonBroadcastCounterClientOutput
        table
        "
	::= { pm20020maMondownRmonBroadcastCounterClientOutputEntry 1 }


pm20020maMondownRmonBroadcastCounterClientOutputValuePortn OBJECT-TYPE
	SYNTAX  Counter64
	MAX-ACCESS read-only
	STATUS current
	DESCRIPTION
        "
        Client Output Broadcast Packets
        :This counter is increased each
        time a broadcast packet is transmitted
        on the client port  <Help>  This
        counter gives the number of Broadcast
        packets transmitted on the client
        port
        "
	::= { pm20020maMondownRmonBroadcastCounterClientOutputEntry 2 }


pm20020maMondownRmonBroadcastCounterClientOutputErrorPortn OBJECT-TYPE
	SYNTAX  EkiOnOff
	MAX-ACCESS read-only
	STATUS current
	DESCRIPTION
        "
        Broadcast Counter Error :This
         OID when set indicates the Broadcast
        counter value is invalid on client
        port
        "
	::= { pm20020maMondownRmonBroadcastCounterClientOutputEntry 3 }


pm20020maMondownRmonBroadcastCounterClientOutputOverloadPortn OBJECT-TYPE
	SYNTAX  EkiOnOff
	MAX-ACCESS read-only
	STATUS current
	DESCRIPTION
        "
        Broadcast Counter Overload :This
        OID when set indicates a Broadcast
        counter overload on client port
        "
	::= { pm20020maMondownRmonBroadcastCounterClientOutputEntry 4 }


--- *********************************************************
---     TABLE for the pm20020maMondownRmonMulticastCounterClientOutput articles
--- *********************************************************

pm20020maMondownRmonMulticastCounterClientOutputTable OBJECT-TYPE
	SYNTAX  SEQUENCE OF Pm20020maMondownRmonMulticastCounterClientOutputEntry
	MAX-ACCESS not-accessible
	STATUS current
	DESCRIPTION
        "
        List of pm20020maMondownRmonMulticastCounterClientOutput
        Article
        "
	::= { pm20020maMonClientRmonCounter 528 }


pm20020maMondownRmonMulticastCounterClientOutputEntry OBJECT-TYPE
	SYNTAX Pm20020maMondownRmonMulticastCounterClientOutputEntry
	MAX-ACCESS not-accessible
	STATUS current
	DESCRIPTION
        "
        Row definition for the pm20020maMondownRmonMulticastCounterClientOutput
        table
        "
	INDEX   { pm20020maMondownRmonMulticastCounterClientOutputIndex }
	::= { pm20020maMondownRmonMulticastCounterClientOutputTable 1 }


Pm20020maMondownRmonMulticastCounterClientOutputEntry ::=
	SEQUENCE {
	pm20020maMondownRmonMulticastCounterClientOutputIndex
		INTEGER,
	pm20020maMondownRmonMulticastCounterClientOutputValuePortn
		Counter64,
	pm20020maMondownRmonMulticastCounterClientOutputErrorPortn
		EkiOnOff,
	pm20020maMondownRmonMulticastCounterClientOutputOverloadPortn
		EkiOnOff
	}


pm20020maMondownRmonMulticastCounterClientOutputIndex OBJECT-TYPE
	SYNTAX  INTEGER(0..128)
	MAX-ACCESS  read-only
	STATUS current
	DESCRIPTION
        "
        Index definition for the pm20020maMondownRmonMulticastCounterClientOutput
        table
        "
	::= { pm20020maMondownRmonMulticastCounterClientOutputEntry 1 }


pm20020maMondownRmonMulticastCounterClientOutputValuePortn OBJECT-TYPE
	SYNTAX  Counter64
	MAX-ACCESS read-only
	STATUS current
	DESCRIPTION
        "
        Client Output Multicast Packets
        :This counter is increased each
        time a Multicast packet is transmitted
        on the client port  <Help>  This
        counter gives the number of Multicast
        packets transmitted on the client
        port
        "
	::= { pm20020maMondownRmonMulticastCounterClientOutputEntry 2 }


pm20020maMondownRmonMulticastCounterClientOutputErrorPortn OBJECT-TYPE
	SYNTAX  EkiOnOff
	MAX-ACCESS read-only
	STATUS current
	DESCRIPTION
        "
        Multicast Counter Error :This
         OID when set indicates the Multicast
        counter value is invalid on client
        port
        "
	::= { pm20020maMondownRmonMulticastCounterClientOutputEntry 3 }


pm20020maMondownRmonMulticastCounterClientOutputOverloadPortn OBJECT-TYPE
	SYNTAX  EkiOnOff
	MAX-ACCESS read-only
	STATUS current
	DESCRIPTION
        "
        Multicast Counter Overload :This
        OID when set indicates a Multicast
        counter overload on client port
        "
	::= { pm20020maMondownRmonMulticastCounterClientOutputEntry 4 }


--- *********************************************************
---     TABLE for the pm20020maMondownRmonPauseFrameCounterClientOutput articles
--- *********************************************************

pm20020maMondownRmonPauseFrameCounterClientOutputTable OBJECT-TYPE
	SYNTAX  SEQUENCE OF Pm20020maMondownRmonPauseFrameCounterClientOutputEntry
	MAX-ACCESS not-accessible
	STATUS current
	DESCRIPTION
        "
        List of pm20020maMondownRmonPauseFrameCounterClientOutput
        Article
        "
	::= { pm20020maMonClientRmonCounter 560 }


pm20020maMondownRmonPauseFrameCounterClientOutputEntry OBJECT-TYPE
	SYNTAX Pm20020maMondownRmonPauseFrameCounterClientOutputEntry
	MAX-ACCESS not-accessible
	STATUS current
	DESCRIPTION
        "
        Row definition for the pm20020maMondownRmonPauseFrameCounterClientOutput
        table
        "
	INDEX   { pm20020maMondownRmonPauseFrameCounterClientOutputIndex }
	::= { pm20020maMondownRmonPauseFrameCounterClientOutputTable 1 }


Pm20020maMondownRmonPauseFrameCounterClientOutputEntry ::=
	SEQUENCE {
	pm20020maMondownRmonPauseFrameCounterClientOutputIndex
		INTEGER,
	pm20020maMondownRmonPauseFrameCounterClientOutputValuePortn
		Counter64,
	pm20020maMondownRmonPauseFrameCounterClientOutputErrorPortn
		EkiOnOff,
	pm20020maMondownRmonPauseFrameCounterClientOutputOverloadPortn
		EkiOnOff
	}


pm20020maMondownRmonPauseFrameCounterClientOutputIndex OBJECT-TYPE
	SYNTAX  INTEGER(0..128)
	MAX-ACCESS  read-only
	STATUS current
	DESCRIPTION
        "
        Index definition for the pm20020maMondownRmonPauseFrameCounterClientOutput
        table
        "
	::= { pm20020maMondownRmonPauseFrameCounterClientOutputEntry 1 }


pm20020maMondownRmonPauseFrameCounterClientOutputValuePortn OBJECT-TYPE
	SYNTAX  Counter64
	MAX-ACCESS read-only
	STATUS current
	DESCRIPTION
        "
        Client Output Pause Frames :This
        counter is increased each time
         a Pause frame is transmitted on
        the client port  <Help>  This counter
        gives the number of Pause frames
        transmitted on the client port
        "
	::= { pm20020maMondownRmonPauseFrameCounterClientOutputEntry 2 }


pm20020maMondownRmonPauseFrameCounterClientOutputErrorPortn OBJECT-TYPE
	SYNTAX  EkiOnOff
	MAX-ACCESS read-only
	STATUS current
	DESCRIPTION
        "
        Pause Counter Error :This OID
         when set indicates the Pause counter
        value is invalid on client port
        "
	::= { pm20020maMondownRmonPauseFrameCounterClientOutputEntry 3 }


pm20020maMondownRmonPauseFrameCounterClientOutputOverloadPortn OBJECT-TYPE
	SYNTAX  EkiOnOff
	MAX-ACCESS read-only
	STATUS current
	DESCRIPTION
        "
        Pause Counter Overload :This OID
        when set indicates a Pause counter
        overload on client port
        "
	::= { pm20020maMondownRmonPauseFrameCounterClientOutputEntry 4 }


--- *********************************************************
---     TABLE for the pm20020maMondownRmonUnicastCounterClientOutput articles
--- *********************************************************

pm20020maMondownRmonUnicastCounterClientOutputTable OBJECT-TYPE
	SYNTAX  SEQUENCE OF Pm20020maMondownRmonUnicastCounterClientOutputEntry
	MAX-ACCESS not-accessible
	STATUS current
	DESCRIPTION
        "
        List of pm20020maMondownRmonUnicastCounterClientOutput
        Article
        "
	::= { pm20020maMonClientRmonCounter 688 }


pm20020maMondownRmonUnicastCounterClientOutputEntry OBJECT-TYPE
	SYNTAX Pm20020maMondownRmonUnicastCounterClientOutputEntry
	MAX-ACCESS not-accessible
	STATUS current
	DESCRIPTION
        "
        Row definition for the pm20020maMondownRmonUnicastCounterClientOutput
        table
        "
	INDEX   { pm20020maMondownRmonUnicastCounterClientOutputIndex }
	::= { pm20020maMondownRmonUnicastCounterClientOutputTable 1 }


Pm20020maMondownRmonUnicastCounterClientOutputEntry ::=
	SEQUENCE {
	pm20020maMondownRmonUnicastCounterClientOutputIndex
		INTEGER,
	pm20020maMondownRmonUnicastCounterClientOutputValuePortn
		Counter64,
	pm20020maMondownRmonUnicastCounterClientOutputErrorPortn
		EkiOnOff,
	pm20020maMondownRmonUnicastCounterClientOutputOverloadPortn
		EkiOnOff
	}


pm20020maMondownRmonUnicastCounterClientOutputIndex OBJECT-TYPE
	SYNTAX  INTEGER(0..128)
	MAX-ACCESS  read-only
	STATUS current
	DESCRIPTION
        "
        Index definition for the pm20020maMondownRmonUnicastCounterClientOutput
        table
        "
	::= { pm20020maMondownRmonUnicastCounterClientOutputEntry 1 }


pm20020maMondownRmonUnicastCounterClientOutputValuePortn OBJECT-TYPE
	SYNTAX  Counter64
	MAX-ACCESS read-only
	STATUS current
	DESCRIPTION
        "
        Client Output Unicast Packets
         :This counter is increased each
        time a Unicast packet is transmitted
        on the client port  <Help>  This
        counter gives the number of Unicast
        packets transmitted on the client
        port
        "
	::= { pm20020maMondownRmonUnicastCounterClientOutputEntry 2 }


pm20020maMondownRmonUnicastCounterClientOutputErrorPortn OBJECT-TYPE
	SYNTAX  EkiOnOff
	MAX-ACCESS read-only
	STATUS current
	DESCRIPTION
        "
        Unicast Counter Error :This OID
        when set indicates the Unicast
         counter value is invalid on client
        port
        "
	::= { pm20020maMondownRmonUnicastCounterClientOutputEntry 3 }


pm20020maMondownRmonUnicastCounterClientOutputOverloadPortn OBJECT-TYPE
	SYNTAX  EkiOnOff
	MAX-ACCESS read-only
	STATUS current
	DESCRIPTION
        "
        Unicast Counter Overload :This
        OID when set indicates a Unicast
        counter overload on client port
        "
	::= { pm20020maMondownRmonUnicastCounterClientOutputEntry 4 }


--- *********************************************************
---     TABLE for the pm20020maMondownRmonNonunicastCounterClientOutput articles
--- *********************************************************

pm20020maMondownRmonNonunicastCounterClientOutputTable OBJECT-TYPE
	SYNTAX  SEQUENCE OF Pm20020maMondownRmonNonunicastCounterClientOutputEntry
	MAX-ACCESS not-accessible
	STATUS current
	DESCRIPTION
        "
        List of pm20020maMondownRmonNonunicastCounterClientOutput
        Article
        "
	::= { pm20020maMonClientRmonCounter 720 }


pm20020maMondownRmonNonunicastCounterClientOutputEntry OBJECT-TYPE
	SYNTAX Pm20020maMondownRmonNonunicastCounterClientOutputEntry
	MAX-ACCESS not-accessible
	STATUS current
	DESCRIPTION
        "
        Row definition for the pm20020maMondownRmonNonunicastCounterClientOutput
        table
        "
	INDEX   { pm20020maMondownRmonNonunicastCounterClientOutputIndex }
	::= { pm20020maMondownRmonNonunicastCounterClientOutputTable 1 }


Pm20020maMondownRmonNonunicastCounterClientOutputEntry ::=
	SEQUENCE {
	pm20020maMondownRmonNonunicastCounterClientOutputIndex
		INTEGER,
	pm20020maMondownRmonNonunicastCounterClientOutputValuePortn
		Counter64,
	pm20020maMondownRmonNonunicastCounterClientOutputErrorPortn
		EkiOnOff,
	pm20020maMondownRmonNonunicastCounterClientOutputOverloadPortn
		EkiOnOff
	}


pm20020maMondownRmonNonunicastCounterClientOutputIndex OBJECT-TYPE
	SYNTAX  INTEGER(0..128)
	MAX-ACCESS  read-only
	STATUS current
	DESCRIPTION
        "
        Index definition for the pm20020maMondownRmonNonunicastCounterClientOutput
        table
        "
	::= { pm20020maMondownRmonNonunicastCounterClientOutputEntry 1 }


pm20020maMondownRmonNonunicastCounterClientOutputValuePortn OBJECT-TYPE
	SYNTAX  Counter64
	MAX-ACCESS read-only
	STATUS current
	DESCRIPTION
        "
        Client Output Non Unicast Packets
        :This counter is increased each
        time a Non-Unicast packet is transmitted
        on the client port  <Help>  This
        counter gives the number of Non-Unicast
        packets transmitted on the client
        port
        "
	::= { pm20020maMondownRmonNonunicastCounterClientOutputEntry 2 }


pm20020maMondownRmonNonunicastCounterClientOutputErrorPortn OBJECT-TYPE
	SYNTAX  EkiOnOff
	MAX-ACCESS read-only
	STATUS current
	DESCRIPTION
        "
        Non Unicast Counter Error :This
        OID when set indicates the Non-Unicast
        counter value is invalid on client
        port
        "
	::= { pm20020maMondownRmonNonunicastCounterClientOutputEntry 3 }


pm20020maMondownRmonNonunicastCounterClientOutputOverloadPortn OBJECT-TYPE
	SYNTAX  EkiOnOff
	MAX-ACCESS read-only
	STATUS current
	DESCRIPTION
        "
        Non Unicast Counter Overload :This
        OID when set indicates a Non-Unicast
        counter overload on client port
        "
	::= { pm20020maMondownRmonNonunicastCounterClientOutputEntry 4 }







--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pm20020maMesrsynth0 OBJECT-TYPE
	  SYNTAX EkiMeasureType
	  MAX-ACCESS read-only
	  STATUS deprecated
	  DESCRIPTION
        "
        Not Used :
        "
	  ::= { pm20020maMesrOther 0 }



pm20020maMesrsynth1 OBJECT-TYPE
	  SYNTAX EkiMeasureType
	  MAX-ACCESS read-only
	  STATUS deprecated
	  DESCRIPTION
        "
        Not Used :
        "
	  ::= { pm20020maMesrOther 1 }



--- *****************************************************
---     LEAF for the pmIntervalNumber article
--- *****************************************************

pm20020maMesrpmIntervalNumber OBJECT-TYPE
	  SYNTAX Unsigned32 (0..65535)
	  MAX-ACCESS read-only
	  STATUS current
	  DESCRIPTION
        "
        PM Interval Counter :
        "
	  ::= { pm20020maMesrOther 7 }



--- *****************************************************
---     LEAF for the clientCfpTemp article
--- *****************************************************

pm20020maMesrclientCfpTemp OBJECT-TYPE
	  SYNTAX Unsigned32 (0..65535)
	  MAX-ACCESS read-only
	  STATUS current
	  DESCRIPTION
        "
        Client Trscv Temperature :This
        OID gives the temperature value
        of the Client Transceiver, read
        from the DDM (Digital Diagnostic
        Monitoring) (Temperature = AV/256)
        (Unit = C) <Help> This Measure
         gives the temperature value of
        the Client Transceiver
        "
	  ::= { pm20020maMesrClient 8 }



--- *****************************************************
---     LEAF for the clientCfp3v3Voltage article
--- *****************************************************

pm20020maMesrclientCfp3v3Voltage OBJECT-TYPE
	  SYNTAX Unsigned32 (0..65535)
	  MAX-ACCESS read-only
	  STATUS current
	  DESCRIPTION
        "
        Client Trscv Voltage :This OID
        gives the 3V3 voltage value of
         the Client Transceiver, read from
        the DDM (Digital Diagnostic Monitoring)
         (Voltage = AV/1000) (Unit = V)
        <Help> This Measure gives the 3V3
        voltage value of the Client Transceiver
        "
	  ::= { pm20020maMesrClient 9 }



--- *****************************************************
---     LEAF for the clientSoaBiasCurrent article
--- *****************************************************

pm20020maMesrclientSoaBiasCurrent OBJECT-TYPE
	  SYNTAX Unsigned32 (0..65535)
	  MAX-ACCESS read-only
	  STATUS current
	  DESCRIPTION
        "
        Client Trscv SOA Bias :This OID
        gives the SOA bias value of the
        Client Transceiver, read from the
        DDM (Digital Diagnostic Monitoring)
         (Bias = AV/500) (Unit = mA) <Help>
        This Measure gives the SOA bias
        value of the Client Transceiver
        "
	  ::= { pm20020maMesrClient 10 }



--- *****************************************************
---     LEAF for the lineMsaTemp article
--- *****************************************************

pm20020maMesrlineMsaTemp OBJECT-TYPE
	  SYNTAX Unsigned32 (0..65535)
	  MAX-ACCESS read-only
	  STATUS current
	  DESCRIPTION
        "
        Line Trscv Temperature :This OID
        gives the temperature value of
         the Line Transceiver, read from
        the DDM (Digital Diagnostic Monitoring)
         (Temperature = AV/256) (Unit =
        C) <Help> This Measure gives the
        temperature value of the Line Transceiver.This
        temperature must remain below 95°C
        for proper operation
        "
	  ::= { pm20020maMesrLine 12 }



--- *****************************************************
---     LEAF for the lineMsa3v3Voltage article
--- *****************************************************

pm20020maMesrlineMsa3v3Voltage OBJECT-TYPE
	  SYNTAX Unsigned32 (0..65535)
	  MAX-ACCESS read-only
	  STATUS current
	  DESCRIPTION
        "
        Line Trscv Voltage :This OID gives
        the 3V3 voltage value of the Line
        Transceiver, read from the DDM
         (Digital Diagnostic Monitoring)
        (Voltage = AV/1000) (Unit = V)
         <Help> This Measure gives the
         3V3 voltage value of the Line
         Transceiver
        "
	  ::= { pm20020maMesrLine 13 }



--- *****************************************************
---     LEAF for the lineSoaBiasCurrent article
--- *****************************************************

pm20020maMesrlineSoaBiasCurrent OBJECT-TYPE
	  SYNTAX Unsigned32 (0..65535)
	  MAX-ACCESS read-only
	  STATUS current
	  DESCRIPTION
        "
        Line Trscv SOA Bias :This OID
         gives the SOA bias value of the
        Line Transceiver,read from the
         DDM (Digital Diagnostic Monitoring)
         (Bias = AV/500) (Unit = mA) <Help>
        This Measure gives the SOA bias
        value of the Line Transceiver
        "
	  ::= { pm20020maMesrLine 14 }



--- *********************************************************
---     TABLE for the pm20020maMesrclientNetTxTemp articles
--- *********************************************************

pm20020maMesrclientNetTxTempTable OBJECT-TYPE
	SYNTAX  SEQUENCE OF Pm20020maMesrclientNetTxTempEntry
	MAX-ACCESS not-accessible
	STATUS current
	DESCRIPTION
        "
        List of pm20020maMesrclientNetTxTemp
        Article
        "
	::= { pm20020maMesrClient 16 }


pm20020maMesrclientNetTxTempEntry OBJECT-TYPE
	SYNTAX Pm20020maMesrclientNetTxTempEntry
	MAX-ACCESS not-accessible
	STATUS current
	DESCRIPTION
        "
        Row definition for the pm20020maMesrclientNetTxTemp
        table
        "
	INDEX   { pm20020maMesrclientNetTxTempIndex }
	::= { pm20020maMesrclientNetTxTempTable 1 }


Pm20020maMesrclientNetTxTempEntry ::=
	SEQUENCE {
	pm20020maMesrclientNetTxTempIndex
		INTEGER,
	pm20020maMesrclientNetTxTempPortn
		INTEGER
	}


pm20020maMesrclientNetTxTempIndex OBJECT-TYPE
	SYNTAX  INTEGER(0..128)
	MAX-ACCESS  read-only
	STATUS current
	DESCRIPTION
        "
        Index definition for the pm20020maMesrclientNetTxTemp
        table
        "
	::= { pm20020maMesrclientNetTxTempEntry 1 }


pm20020maMesrclientNetTxTempPortn OBJECT-TYPE
	SYNTAX  INTEGER (0..65535)
	MAX-ACCESS read-only
	STATUS current
	DESCRIPTION
        "
        Client Trscv Temperature :This
        OID gives the Laser temperature
        value of the Client Transceiver,
        read from the DDM (Digital Diagnostic
        Monitoring) (Temperature = AV/256)
        (Unit = C) <Help> This Measure
         gives the Laser temperature value
        of the Client Transceiver
        "
	::= { pm20020maMesrclientNetTxTempEntry 2 }


--- *********************************************************
---     TABLE for the pm20020maMesrclientNetTxBias articles
--- *********************************************************

pm20020maMesrclientNetTxBiasTable OBJECT-TYPE
	SYNTAX  SEQUENCE OF Pm20020maMesrclientNetTxBiasEntry
	MAX-ACCESS not-accessible
	STATUS current
	DESCRIPTION
        "
        List of pm20020maMesrclientNetTxBias
        Article
        "
	::= { pm20020maMesrClient 48 }


pm20020maMesrclientNetTxBiasEntry OBJECT-TYPE
	SYNTAX Pm20020maMesrclientNetTxBiasEntry
	MAX-ACCESS not-accessible
	STATUS current
	DESCRIPTION
        "
        Row definition for the pm20020maMesrclientNetTxBias
        table
        "
	INDEX   { pm20020maMesrclientNetTxBiasIndex }
	::= { pm20020maMesrclientNetTxBiasTable 1 }


Pm20020maMesrclientNetTxBiasEntry ::=
	SEQUENCE {
	pm20020maMesrclientNetTxBiasIndex
		INTEGER,
	pm20020maMesrclientNetTxBiasPortn
		INTEGER
	}


pm20020maMesrclientNetTxBiasIndex OBJECT-TYPE
	SYNTAX  INTEGER(0..128)
	MAX-ACCESS  read-only
	STATUS current
	DESCRIPTION
        "
        Index definition for the pm20020maMesrclientNetTxBias
        table
        "
	::= { pm20020maMesrclientNetTxBiasEntry 1 }


pm20020maMesrclientNetTxBiasPortn OBJECT-TYPE
	SYNTAX  INTEGER (0..65535)
	MAX-ACCESS read-only
	STATUS current
	DESCRIPTION
        "
        Client Trscv Laser Bias :This
         OID gives the Laser bias value
        of the Client Transceiver, read
        from the DDM (Digital Diagnostic
        Monitoring) (Bias = AV/500) (Unit
        = mA) <Help> This Measure gives
        the Laser bias value of the Client
        Transceiver
        "
	::= { pm20020maMesrclientNetTxBiasEntry 2 }


--- *********************************************************
---     TABLE for the pm20020maMesrclientNetTxPwr articles
--- *********************************************************

pm20020maMesrclientNetTxPwrTable OBJECT-TYPE
	SYNTAX  SEQUENCE OF Pm20020maMesrclientNetTxPwrEntry
	MAX-ACCESS not-accessible
	STATUS current
	DESCRIPTION
        "
        List of pm20020maMesrclientNetTxPwr
        Article
        "
	::= { pm20020maMesrClient 80 }


pm20020maMesrclientNetTxPwrEntry OBJECT-TYPE
	SYNTAX Pm20020maMesrclientNetTxPwrEntry
	MAX-ACCESS not-accessible
	STATUS current
	DESCRIPTION
        "
        Row definition for the pm20020maMesrclientNetTxPwr
        table
        "
	INDEX   { pm20020maMesrclientNetTxPwrIndex }
	::= { pm20020maMesrclientNetTxPwrTable 1 }


Pm20020maMesrclientNetTxPwrEntry ::=
	SEQUENCE {
	pm20020maMesrclientNetTxPwrIndex
		INTEGER,
	pm20020maMesrclientNetTxPwrPortn
		INTEGER
	}


pm20020maMesrclientNetTxPwrIndex OBJECT-TYPE
	SYNTAX  INTEGER(0..128)
	MAX-ACCESS  read-only
	STATUS current
	DESCRIPTION
        "
        Index definition for the pm20020maMesrclientNetTxPwr
        table
        "
	::= { pm20020maMesrclientNetTxPwrEntry 1 }


pm20020maMesrclientNetTxPwrPortn OBJECT-TYPE
	SYNTAX  INTEGER (0..65535)
	MAX-ACCESS read-only
	STATUS current
	DESCRIPTION
        "
        Client Trscv Tx Power :This OID
        gives the transmit power value
         of the Client Transceiver, read
        from the DDM (Digital Diagnostic
        Monitoring) (Power = 10*log(AV)-40)
        (Unit = dBm) <Help> This Measure
        gives the transmit power value
         of the Client Transceiver
        "
	::= { pm20020maMesrclientNetTxPwrEntry 2 }


--- *********************************************************
---     TABLE for the pm20020maMesrclientNetRxPwr articles
--- *********************************************************

pm20020maMesrclientNetRxPwrTable OBJECT-TYPE
	SYNTAX  SEQUENCE OF Pm20020maMesrclientNetRxPwrEntry
	MAX-ACCESS not-accessible
	STATUS current
	DESCRIPTION
        "
        List of pm20020maMesrclientNetRxPwr
        Article
        "
	::= { pm20020maMesrClient 112 }


pm20020maMesrclientNetRxPwrEntry OBJECT-TYPE
	SYNTAX Pm20020maMesrclientNetRxPwrEntry
	MAX-ACCESS not-accessible
	STATUS current
	DESCRIPTION
        "
        Row definition for the pm20020maMesrclientNetRxPwr
        table
        "
	INDEX   { pm20020maMesrclientNetRxPwrIndex }
	::= { pm20020maMesrclientNetRxPwrTable 1 }


Pm20020maMesrclientNetRxPwrEntry ::=
	SEQUENCE {
	pm20020maMesrclientNetRxPwrIndex
		INTEGER,
	pm20020maMesrclientNetRxPwrPortn
		INTEGER
	}


pm20020maMesrclientNetRxPwrIndex OBJECT-TYPE
	SYNTAX  INTEGER(0..128)
	MAX-ACCESS  read-only
	STATUS current
	DESCRIPTION
        "
        Index definition for the pm20020maMesrclientNetRxPwr
        table
        "
	::= { pm20020maMesrclientNetRxPwrEntry 1 }


pm20020maMesrclientNetRxPwrPortn OBJECT-TYPE
	SYNTAX  INTEGER (0..65535)
	MAX-ACCESS read-only
	STATUS current
	DESCRIPTION
        "
        Client Trscv Rx Power :This OID
        gives the receive power value of
        the Client Transceiver, read in
        the DDM (Digital Diagnostic Monitoring)
        (Power = 10*log(AV)-40) (Unit =
        dBm) <Help> This Measure gives
         the receive power value of the
        Client Transceiver
        "
	::= { pm20020maMesrclientNetRxPwrEntry 2 }


--- *********************************************************
---     TABLE for the pm20020maMesrlineNetTxLaserOutputPwr articles
--- *********************************************************

pm20020maMesrlineNetTxLaserOutputPwrTable OBJECT-TYPE
	SYNTAX  SEQUENCE OF Pm20020maMesrlineNetTxLaserOutputPwrEntry
	MAX-ACCESS not-accessible
	STATUS current
	DESCRIPTION
        "
        List of pm20020maMesrlineNetTxLaserOutputPwr
        Article
        "
	::= { pm20020maMesrLine 144 }


pm20020maMesrlineNetTxLaserOutputPwrEntry OBJECT-TYPE
	SYNTAX Pm20020maMesrlineNetTxLaserOutputPwrEntry
	MAX-ACCESS not-accessible
	STATUS current
	DESCRIPTION
        "
        Row definition for the pm20020maMesrlineNetTxLaserOutputPwr
        table
        "
	INDEX   { pm20020maMesrlineNetTxLaserOutputPwrIndex }
	::= { pm20020maMesrlineNetTxLaserOutputPwrTable 1 }


Pm20020maMesrlineNetTxLaserOutputPwrEntry ::=
	SEQUENCE {
	pm20020maMesrlineNetTxLaserOutputPwrIndex
		INTEGER,
	pm20020maMesrlineNetTxLaserOutputPwrPortn
		INTEGER
	}


pm20020maMesrlineNetTxLaserOutputPwrIndex OBJECT-TYPE
	SYNTAX  INTEGER(0..128)
	MAX-ACCESS  read-only
	STATUS current
	DESCRIPTION
        "
        Index definition for the pm20020maMesrlineNetTxLaserOutputPwr
        table
        "
	::= { pm20020maMesrlineNetTxLaserOutputPwrEntry 1 }


pm20020maMesrlineNetTxLaserOutputPwrPortn OBJECT-TYPE
	SYNTAX  INTEGER (0..65535)
	MAX-ACCESS read-only
	STATUS current
	DESCRIPTION
        "
        Current Line Trscv Tx Power :This
        OID gives the Tx Laser transmit
        power value of the Line Transceiver,
        read in the DDM (Digital Diagnostic
        Monitoring) (Power = AV/100) (Unit
        = dBm) <Help> This Measure gives
        the Tx Laser transmit power value
        of the Line Transceiver
        "
	::= { pm20020maMesrlineNetTxLaserOutputPwrEntry 2 }


--- *********************************************************
---     TABLE for the pm20020maMesrlineNetTxLaserTemp articles
--- *********************************************************

pm20020maMesrlineNetTxLaserTempTable OBJECT-TYPE
	SYNTAX  SEQUENCE OF Pm20020maMesrlineNetTxLaserTempEntry
	MAX-ACCESS not-accessible
	STATUS current
	DESCRIPTION
        "
        List of pm20020maMesrlineNetTxLaserTemp
        Article
        "
	::= { pm20020maMesrLine 148 }


pm20020maMesrlineNetTxLaserTempEntry OBJECT-TYPE
	SYNTAX Pm20020maMesrlineNetTxLaserTempEntry
	MAX-ACCESS not-accessible
	STATUS current
	DESCRIPTION
        "
        Row definition for the pm20020maMesrlineNetTxLaserTemp
        table
        "
	INDEX   { pm20020maMesrlineNetTxLaserTempIndex }
	::= { pm20020maMesrlineNetTxLaserTempTable 1 }


Pm20020maMesrlineNetTxLaserTempEntry ::=
	SEQUENCE {
	pm20020maMesrlineNetTxLaserTempIndex
		INTEGER,
	pm20020maMesrlineNetTxLaserTempPortn
		INTEGER
	}


pm20020maMesrlineNetTxLaserTempIndex OBJECT-TYPE
	SYNTAX  INTEGER(0..128)
	MAX-ACCESS  read-only
	STATUS current
	DESCRIPTION
        "
        Index definition for the pm20020maMesrlineNetTxLaserTemp
        table
        "
	::= { pm20020maMesrlineNetTxLaserTempEntry 1 }


pm20020maMesrlineNetTxLaserTempPortn OBJECT-TYPE
	SYNTAX  INTEGER (0..65535)
	MAX-ACCESS read-only
	STATUS current
	DESCRIPTION
        "
        Current Line Trscv Tx Laser Temperature
        :This OID gives the Tx Laser Temperature
        value of the Line Transceiver,
         read from the DDM (Digital Diagnostic
        Monitoring) (Temperature = AV/256)
        (Unit = C) <Help> This Measure
         gives the Tx Laser Temperature
        value of the Line Transceiver
        "
	::= { pm20020maMesrlineNetTxLaserTempEntry 2 }


--- *********************************************************
---     TABLE for the pm20020maMesrlineNetTxBiasCurrent articles
--- *********************************************************

pm20020maMesrlineNetTxBiasCurrentTable OBJECT-TYPE
	SYNTAX  SEQUENCE OF Pm20020maMesrlineNetTxBiasCurrentEntry
	MAX-ACCESS not-accessible
	STATUS current
	DESCRIPTION
        "
        List of pm20020maMesrlineNetTxBiasCurrent
        Article
        "
	::= { pm20020maMesrLine 152 }


pm20020maMesrlineNetTxBiasCurrentEntry OBJECT-TYPE
	SYNTAX Pm20020maMesrlineNetTxBiasCurrentEntry
	MAX-ACCESS not-accessible
	STATUS current
	DESCRIPTION
        "
        Row definition for the pm20020maMesrlineNetTxBiasCurrent
        table
        "
	INDEX   { pm20020maMesrlineNetTxBiasCurrentIndex }
	::= { pm20020maMesrlineNetTxBiasCurrentTable 1 }


Pm20020maMesrlineNetTxBiasCurrentEntry ::=
	SEQUENCE {
	pm20020maMesrlineNetTxBiasCurrentIndex
		INTEGER,
	pm20020maMesrlineNetTxBiasCurrentPortn
		INTEGER
	}


pm20020maMesrlineNetTxBiasCurrentIndex OBJECT-TYPE
	SYNTAX  INTEGER(0..128)
	MAX-ACCESS  read-only
	STATUS current
	DESCRIPTION
        "
        Index definition for the pm20020maMesrlineNetTxBiasCurrent
        table
        "
	::= { pm20020maMesrlineNetTxBiasCurrentEntry 1 }


pm20020maMesrlineNetTxBiasCurrentPortn OBJECT-TYPE
	SYNTAX  INTEGER (0..65535)
	MAX-ACCESS read-only
	STATUS current
	DESCRIPTION
        "
        Current Line Trscv Tx Laser Bias
        :This OID gives the Tx Laser Bias
        value of the Line Transceiver,
         read from the DDM (Digital Diagnostic
        Monitoring) (Bias = AV/10) (Unit
        = mA) <Help> This Measure gives
        the Tx Laser Bias value of the
         Line Transceiver
        "
	::= { pm20020maMesrlineNetTxBiasCurrentEntry 2 }


--- *********************************************************
---     TABLE for the pm20020maMesrlineNetRxInputPwr articles
--- *********************************************************

pm20020maMesrlineNetRxInputPwrTable OBJECT-TYPE
	SYNTAX  SEQUENCE OF Pm20020maMesrlineNetRxInputPwrEntry
	MAX-ACCESS not-accessible
	STATUS current
	DESCRIPTION
        "
        List of pm20020maMesrlineNetRxInputPwr
        Article
        "
	::= { pm20020maMesrLine 156 }


pm20020maMesrlineNetRxInputPwrEntry OBJECT-TYPE
	SYNTAX Pm20020maMesrlineNetRxInputPwrEntry
	MAX-ACCESS not-accessible
	STATUS current
	DESCRIPTION
        "
        Row definition for the pm20020maMesrlineNetRxInputPwr
        table
        "
	INDEX   { pm20020maMesrlineNetRxInputPwrIndex }
	::= { pm20020maMesrlineNetRxInputPwrTable 1 }


Pm20020maMesrlineNetRxInputPwrEntry ::=
	SEQUENCE {
	pm20020maMesrlineNetRxInputPwrIndex
		INTEGER,
	pm20020maMesrlineNetRxInputPwrPortn
		INTEGER
	}


pm20020maMesrlineNetRxInputPwrIndex OBJECT-TYPE
	SYNTAX  INTEGER(0..128)
	MAX-ACCESS  read-only
	STATUS current
	DESCRIPTION
        "
        Index definition for the pm20020maMesrlineNetRxInputPwr
        table
        "
	::= { pm20020maMesrlineNetRxInputPwrEntry 1 }


pm20020maMesrlineNetRxInputPwrPortn OBJECT-TYPE
	SYNTAX  INTEGER (0..65535)
	MAX-ACCESS read-only
	STATUS current
	DESCRIPTION
        "
        Current Line Trscv Rx Power :This
        OID gives the Receive power value
        of the Line Transceiver, read in
        the DDM (Digital Diagnostic Monitoring)
        (Power = AV/100) (Unit = dBm) <Help>
        This Measure gives the Receive
         power value of the Line Transceiver
        "
	::= { pm20020maMesrlineNetRxInputPwrEntry 2 }


--- *********************************************************
---     TABLE for the pm20020maMesrlineResidualChromaticDisp articles
--- *********************************************************

pm20020maMesrlineResidualChromaticDispTable OBJECT-TYPE
	SYNTAX  SEQUENCE OF Pm20020maMesrlineResidualChromaticDispEntry
	MAX-ACCESS not-accessible
	STATUS current
	DESCRIPTION
        "
        List of pm20020maMesrlineResidualChromaticDisp
        Article
        "
	::= { pm20020maMesrLine 160 }


pm20020maMesrlineResidualChromaticDispEntry OBJECT-TYPE
	SYNTAX Pm20020maMesrlineResidualChromaticDispEntry
	MAX-ACCESS not-accessible
	STATUS current
	DESCRIPTION
        "
        Row definition for the pm20020maMesrlineResidualChromaticDisp
        table
        "
	INDEX   { pm20020maMesrlineResidualChromaticDispIndex }
	::= { pm20020maMesrlineResidualChromaticDispTable 1 }


Pm20020maMesrlineResidualChromaticDispEntry ::=
	SEQUENCE {
	pm20020maMesrlineResidualChromaticDispIndex
		INTEGER,
	pm20020maMesrlineResidualChromaticDispPortn
		INTEGER
	}


pm20020maMesrlineResidualChromaticDispIndex OBJECT-TYPE
	SYNTAX  INTEGER(0..128)
	MAX-ACCESS  read-only
	STATUS current
	DESCRIPTION
        "
        Index definition for the pm20020maMesrlineResidualChromaticDisp
        table
        "
	::= { pm20020maMesrlineResidualChromaticDispEntry 1 }


pm20020maMesrlineResidualChromaticDispPortn OBJECT-TYPE
	SYNTAX  INTEGER (0..65535)
	MAX-ACCESS read-only
	STATUS current
	DESCRIPTION
        "
        Current Residual Chromatic Dispersion
        :This OID gives the current Residual
        Chromatic Dispersion on the Line
        interface  (Unit = ps/nm)<Help>
        This measure gives the current
         Residual Chromatic Dispersion
         on the Line interface.
        "
	::= { pm20020maMesrlineResidualChromaticDispEntry 2 }


--- *********************************************************
---     TABLE for the pm20020maMesrlineDiffGroupDelay articles
--- *********************************************************

pm20020maMesrlineDiffGroupDelayTable OBJECT-TYPE
	SYNTAX  SEQUENCE OF Pm20020maMesrlineDiffGroupDelayEntry
	MAX-ACCESS not-accessible
	STATUS current
	DESCRIPTION
        "
        List of pm20020maMesrlineDiffGroupDelay
        Article
        "
	::= { pm20020maMesrLine 164 }


pm20020maMesrlineDiffGroupDelayEntry OBJECT-TYPE
	SYNTAX Pm20020maMesrlineDiffGroupDelayEntry
	MAX-ACCESS not-accessible
	STATUS current
	DESCRIPTION
        "
        Row definition for the pm20020maMesrlineDiffGroupDelay
        table
        "
	INDEX   { pm20020maMesrlineDiffGroupDelayIndex }
	::= { pm20020maMesrlineDiffGroupDelayTable 1 }


Pm20020maMesrlineDiffGroupDelayEntry ::=
	SEQUENCE {
	pm20020maMesrlineDiffGroupDelayIndex
		INTEGER,
	pm20020maMesrlineDiffGroupDelayPortn
		INTEGER
	}


pm20020maMesrlineDiffGroupDelayIndex OBJECT-TYPE
	SYNTAX  INTEGER(0..128)
	MAX-ACCESS  read-only
	STATUS current
	DESCRIPTION
        "
        Index definition for the pm20020maMesrlineDiffGroupDelay
        table
        "
	::= { pm20020maMesrlineDiffGroupDelayEntry 1 }


pm20020maMesrlineDiffGroupDelayPortn OBJECT-TYPE
	SYNTAX  INTEGER (0..65535)
	MAX-ACCESS read-only
	STATUS current
	DESCRIPTION
        "
        Current Differential Group Delay
        :This OID gives the current Differential
        Group Delay on the Line interface
          (Unit = ps)<Help> This measure
        gives the current Differential
         Group Delay on the Line interface.
        "
	::= { pm20020maMesrlineDiffGroupDelayEntry 2 }


--- *********************************************************
---     TABLE for the pm20020maMesrlineQFactor articles
--- *********************************************************

pm20020maMesrlineQFactorTable OBJECT-TYPE
	SYNTAX  SEQUENCE OF Pm20020maMesrlineQFactorEntry
	MAX-ACCESS not-accessible
	STATUS current
	DESCRIPTION
        "
        List of pm20020maMesrlineQFactor
        Article
        "
	::= { pm20020maMesrLine 168 }


pm20020maMesrlineQFactorEntry OBJECT-TYPE
	SYNTAX Pm20020maMesrlineQFactorEntry
	MAX-ACCESS not-accessible
	STATUS current
	DESCRIPTION
        "
        Row definition for the pm20020maMesrlineQFactor
        table
        "
	INDEX   { pm20020maMesrlineQFactorIndex }
	::= { pm20020maMesrlineQFactorTable 1 }


Pm20020maMesrlineQFactorEntry ::=
	SEQUENCE {
	pm20020maMesrlineQFactorIndex
		INTEGER,
	pm20020maMesrlineQFactorPortn
		INTEGER
	}


pm20020maMesrlineQFactorIndex OBJECT-TYPE
	SYNTAX  INTEGER(0..128)
	MAX-ACCESS  read-only
	STATUS current
	DESCRIPTION
        "
        Index definition for the pm20020maMesrlineQFactor
        table
        "
	::= { pm20020maMesrlineQFactorEntry 1 }


pm20020maMesrlineQFactorPortn OBJECT-TYPE
	SYNTAX  INTEGER (0..65535)
	MAX-ACCESS read-only
	STATUS current
	DESCRIPTION
        "
        Current Q Factor :This OID gives
        the current Q Factor on the Line
        interface   (Unit = dB) <Help>
         This measure gives the current
        Q Factor on the Line interface.
        "
	::= { pm20020maMesrlineQFactorEntry 2 }


--- *********************************************************
---     TABLE for the pm20020maMesrlineCarrierFreqOffset articles
--- *********************************************************

pm20020maMesrlineCarrierFreqOffsetTable OBJECT-TYPE
	SYNTAX  SEQUENCE OF Pm20020maMesrlineCarrierFreqOffsetEntry
	MAX-ACCESS not-accessible
	STATUS current
	DESCRIPTION
        "
        List of pm20020maMesrlineCarrierFreqOffset
        Article
        "
	::= { pm20020maMesrLine 172 }


pm20020maMesrlineCarrierFreqOffsetEntry OBJECT-TYPE
	SYNTAX Pm20020maMesrlineCarrierFreqOffsetEntry
	MAX-ACCESS not-accessible
	STATUS current
	DESCRIPTION
        "
        Row definition for the pm20020maMesrlineCarrierFreqOffset
        table
        "
	INDEX   { pm20020maMesrlineCarrierFreqOffsetIndex }
	::= { pm20020maMesrlineCarrierFreqOffsetTable 1 }


Pm20020maMesrlineCarrierFreqOffsetEntry ::=
	SEQUENCE {
	pm20020maMesrlineCarrierFreqOffsetIndex
		INTEGER,
	pm20020maMesrlineCarrierFreqOffsetPortn
		INTEGER
	}


pm20020maMesrlineCarrierFreqOffsetIndex OBJECT-TYPE
	SYNTAX  INTEGER(0..128)
	MAX-ACCESS  read-only
	STATUS current
	DESCRIPTION
        "
        Index definition for the pm20020maMesrlineCarrierFreqOffset
        table
        "
	::= { pm20020maMesrlineCarrierFreqOffsetEntry 1 }


pm20020maMesrlineCarrierFreqOffsetPortn OBJECT-TYPE
	SYNTAX  INTEGER (0..65535)
	MAX-ACCESS read-only
	STATUS current
	DESCRIPTION
        "
        Current Carrier Frequency Offset
        :This OID gives the current Carrier
        Frequency Offset on the Line interface
          (Unit = Mhz)<Help> This measure
        gives the current Carrier Frequency
        Offset on the Line interface.
        "
	::= { pm20020maMesrlineCarrierFreqOffsetEntry 2 }


--- *********************************************************
---     TABLE for the pm20020maMesrlineOsnr articles
--- *********************************************************

pm20020maMesrlineOsnrTable OBJECT-TYPE
	SYNTAX  SEQUENCE OF Pm20020maMesrlineOsnrEntry
	MAX-ACCESS not-accessible
	STATUS current
	DESCRIPTION
        "
        List of pm20020maMesrlineOsnr
         Article
        "
	::= { pm20020maMesrLine 176 }


pm20020maMesrlineOsnrEntry OBJECT-TYPE
	SYNTAX Pm20020maMesrlineOsnrEntry
	MAX-ACCESS not-accessible
	STATUS current
	DESCRIPTION
        "
        Row definition for the pm20020maMesrlineOsnr
        table
        "
	INDEX   { pm20020maMesrlineOsnrIndex }
	::= { pm20020maMesrlineOsnrTable 1 }


Pm20020maMesrlineOsnrEntry ::=
	SEQUENCE {
	pm20020maMesrlineOsnrIndex
		INTEGER,
	pm20020maMesrlineOsnrPortn
		INTEGER
	}


pm20020maMesrlineOsnrIndex OBJECT-TYPE
	SYNTAX  INTEGER(0..128)
	MAX-ACCESS  read-only
	STATUS current
	DESCRIPTION
        "
        Index definition for the pm20020maMesrlineOsnr
        table
        "
	::= { pm20020maMesrlineOsnrEntry 1 }


pm20020maMesrlineOsnrPortn OBJECT-TYPE
	SYNTAX  INTEGER (0..65535)
	MAX-ACCESS read-only
	STATUS current
	DESCRIPTION
        "
        Current OSNR :This OID gives the
        current OSNR on the Line interface
          (OSNR = AV/10) (Unit = dB)<Help>
        This measure gives the current
         OSNR on the Line interface.
        "
	::= { pm20020maMesrlineOsnrEntry 2 }


--- *****************************************************
---     LEAF for the lineNetTxLaserOutputPwrAverage article
--- *****************************************************

pm20020maMesrlineNetTxLaserOutputPwrAverage OBJECT-TYPE
	  SYNTAX Unsigned32 (0..65535)
	  MAX-ACCESS read-only
	  STATUS current
	  DESCRIPTION
        "
        Average Line Trscv Tx Power :This
        OID gives the average Tx Laser
         transmit power value among the
        network lanes of the Line Transceiver,
        read in the DDM (Digital Diagnostic
        Monitoring)  (Power = AV/100) (Unit
        = dBm) (Unit = dBm) <Help> This
        Measure gives the average Tx Laser
        transmit power value among the
         network lanes of the Line Transceiver
        "
	  ::= { pm20020maMesrOther 196 }



--- *****************************************************
---     LEAF for the lineNetTxLaserTempAverage article
--- *****************************************************

pm20020maMesrlineNetTxLaserTempAverage OBJECT-TYPE
	  SYNTAX Unsigned32 (0..65535)
	  MAX-ACCESS read-only
	  STATUS current
	  DESCRIPTION
        "
        Average Line Trscv Tx Laser Temperature
        :This OID gives the average Tx
         Laser Temperature value among
         the network lanes of the Line
         Transceiver, read from the DDM
        (Digital Diagnostic Monitoring)
        (Temperature = AV/256) (Unit =
         C) <Help> This Measure gives the
        average Tx Laser Temperature value
        among the network lanes of the
         Line Transceiver
        "
	  ::= { pm20020maMesrOther 197 }



--- *****************************************************
---     LEAF for the lineNetTxBiasCurrentAverage article
--- *****************************************************

pm20020maMesrlineNetTxBiasCurrentAverage OBJECT-TYPE
	  SYNTAX Unsigned32 (0..65535)
	  MAX-ACCESS read-only
	  STATUS current
	  DESCRIPTION
        "
        Average Line Trscv Tx Laser Bias
        :This OID gives the average Tx
         Laser Bias value among the network
        lanes of the Line Transceiver,
         read from the DDM (Digital Diagnostic
        Monitoring) (Bias = AV/10) (Unit
        = mA) <Help> This Measure gives
        the average Tx Laser Bias value
        among the network lanes of the
         Line Transceiver
        "
	  ::= { pm20020maMesrOther 198 }



--- *****************************************************
---     LEAF for the lineNetRxInputPwrAverage article
--- *****************************************************

pm20020maMesrlineNetRxInputPwrAverage OBJECT-TYPE
	  SYNTAX Unsigned32 (0..65535)
	  MAX-ACCESS read-only
	  STATUS current
	  DESCRIPTION
        "
        Average Line Trscv Rx Power :This
        OID gives the average Receive power
        value among the network lanes of
        the Line Transceiver, read in the
        DDM (Digital Diagnostic Monitoring)
        (Power = AV/100) (Unit = dBm) <Help>
        This Measure gives the average
         Receive power value among the
         network lanes of the Line Transceiver
        "
	  ::= { pm20020maMesrOther 199 }



--- *****************************************************
---     LEAF for the lineResidualChromaticDispAverage article
--- *****************************************************

pm20020maMesrlineResidualChromaticDispAverage OBJECT-TYPE
	  SYNTAX Unsigned32 (0..65535)
	  MAX-ACCESS read-only
	  STATUS current
	  DESCRIPTION
        "
        Average Residual Chromatic Dispersion
        :This OID gives the average Residual
        Chromatic Dispersion on the Line
        interface since the last measure
        reset <Help> This measure gives
        the average Residual Chromatic
         Dispersion on the Line interface
        since the last measure reset.
        "
	  ::= { pm20020maMesrOther 200 }



--- *****************************************************
---     LEAF for the lineDiffGroupDelayAverage article
--- *****************************************************

pm20020maMesrlineDiffGroupDelayAverage OBJECT-TYPE
	  SYNTAX Unsigned32 (0..65535)
	  MAX-ACCESS read-only
	  STATUS current
	  DESCRIPTION
        "
        Average Differential Group Delay
        :This OID gives the average Group
        Delay on the Line interface since
        the last measure reset <Help> This
        measure gives the average Differential
        Group Delay on the Line interface
        since the last measure reset.
        "
	  ::= { pm20020maMesrOther 201 }



--- *****************************************************
---     LEAF for the lineQFactorAverage article
--- *****************************************************

pm20020maMesrlineQFactorAverage OBJECT-TYPE
	  SYNTAX Unsigned32 (0..65535)
	  MAX-ACCESS read-only
	  STATUS current
	  DESCRIPTION
        "
        Average Q Factor :This OID gives
        the average Q Factor on the Line
        interface since the last measure
        reset <Help> This measure gives
        the average Q Factor on the Line
        interface since the last measure
        reset.
        "
	  ::= { pm20020maMesrOther 202 }



--- *****************************************************
---     LEAF for the lineCarrierFreqOffsetAverage article
--- *****************************************************

pm20020maMesrlineCarrierFreqOffsetAverage OBJECT-TYPE
	  SYNTAX Unsigned32 (0..65535)
	  MAX-ACCESS read-only
	  STATUS current
	  DESCRIPTION
        "
        Average Carrier Frequency Offset
        :This OID gives the average Carrier
        Frequency Offset on the Line interface
        since the last measure reset <Help>
        This measure gives the average
         Carrier Frequency Offset on the
        Line interface since the last measure
        reset
        "
	  ::= { pm20020maMesrOther 203 }



--- *****************************************************
---     LEAF for the lineOsnrAverage article
--- *****************************************************

pm20020maMesrlineOsnrAverage OBJECT-TYPE
	  SYNTAX Unsigned32 (0..65535)
	  MAX-ACCESS read-only
	  STATUS current
	  DESCRIPTION
        "
        Average OSNR :This OID gives the
        average OSNR on the Line interface
        since the last measure reset <Help>
        This measure gives the average
         OSNR on the Line interface since
        the last measure reset.
        "
	  ::= { pm20020maMesrOther 204 }



--- *****************************************************
---     LEAF for the clientNetTxTempMin article
--- *****************************************************

pm20020maMesrclientNetTxTempMin OBJECT-TYPE
	  SYNTAX Unsigned32 (0..65535)
	  MAX-ACCESS read-only
	  STATUS current
	  DESCRIPTION
        "
        Min Client Trscv Laser Temperature
        :This OID gives the minimum Laser
        temperature value among the network
        lanes of the Client Transceiver,
        read from the DDM (Digital Diagnostic
        Monitoring) (Temperature = AV/256)
        (Unit = C) <Help> This Measure
         gives the minimum Laser temperature
        value among the network lanes of
        the Client Transceiver
        "
	  ::= { pm20020maMesrOther 208 }



--- *****************************************************
---     LEAF for the clientNetTxBiasMin article
--- *****************************************************

pm20020maMesrclientNetTxBiasMin OBJECT-TYPE
	  SYNTAX Unsigned32 (0..65535)
	  MAX-ACCESS read-only
	  STATUS current
	  DESCRIPTION
        "
        Min Client Trscv Laser Bias :This
        OID gives the minimum Laser bias
        value among the network lanes of
        the Client Transceiver, read from
        the DDM (Digital Diagnostic Monitoring)
        (Bias = AV/500) (Unit = mA) <Help>
        This Measure gives the minimum
         Laser bias value among the network
        lanes of the Client Transceiver
        "
	  ::= { pm20020maMesrOther 209 }



--- *****************************************************
---     LEAF for the clientNetTxPwrMin article
--- *****************************************************

pm20020maMesrclientNetTxPwrMin OBJECT-TYPE
	  SYNTAX Unsigned32 (0..65535)
	  MAX-ACCESS read-only
	  STATUS current
	  DESCRIPTION
        "
        Min Client Trscv Tx Power :This
        OID gives the minimum transmit
         power value among the network
         lanes of the Client Transceiver,
        read from the DDM (Digital Diagnostic
        Monitoring) (Power = 10*log(AV)-40)
        (Unit = dBm) <Help> This Measure
        gives the minimum transmit power
        value among the network lanes of
        the Client Transceiver
        "
	  ::= { pm20020maMesrOther 210 }



--- *****************************************************
---     LEAF for the clientNetRxPwrMin article
--- *****************************************************

pm20020maMesrclientNetRxPwrMin OBJECT-TYPE
	  SYNTAX Unsigned32 (0..65535)
	  MAX-ACCESS read-only
	  STATUS current
	  DESCRIPTION
        "
        Min Client Trscv Rx Power :This
        OID gives the minimum receive power
        value among the network lanes of
        the Client Transceiver, read in
        the DDM (Digital Diagnostic Monitoring)
        (Power = 10*log(AV)-40) (Unit =
        dBm) <Help> This Measure gives
         the minimum receive power value
        among the network lanes of the
         Client Transceiver
        "
	  ::= { pm20020maMesrOther 211 }



--- *****************************************************
---     LEAF for the lineNetTxLaserOutputPwrMin article
--- *****************************************************

pm20020maMesrlineNetTxLaserOutputPwrMin OBJECT-TYPE
	  SYNTAX Unsigned32 (0..65535)
	  MAX-ACCESS read-only
	  STATUS current
	  DESCRIPTION
        "
        Min Line Trscv Tx Power :This
         OID gives the minimum Tx Laser
        transmit power value among the
         network lanes of the Line Transceiver,
        read in the DDM (Digital Diagnostic
        Monitoring)  (Power = AV/100) (Unit
        = dBm) (Unit = dBm) <Help> This
        Measure gives the minimum Tx Laser
        transmit power value among the
         network lanes of the Line Transceiver
        "
	  ::= { pm20020maMesrOther 212 }



--- *****************************************************
---     LEAF for the lineNetTxLaserTempMin article
--- *****************************************************

pm20020maMesrlineNetTxLaserTempMin OBJECT-TYPE
	  SYNTAX Unsigned32 (0..65535)
	  MAX-ACCESS read-only
	  STATUS current
	  DESCRIPTION
        "
        Min Line Trscv Tx Laser Temperature
        :This OID gives the minimum Tx
         Laser Temperature value among
         the network lanes of the Line
         Transceiver, read from the DDM
        (Digital Diagnostic Monitoring)
        (Temperature = AV/256) (Unit =
         C) <Help> This Measure gives the
        minimum Tx Laser Temperature value
        among the network lanes of the
         Line Transceiver
        "
	  ::= { pm20020maMesrOther 213 }



--- *****************************************************
---     LEAF for the lineNetTxBiasCurrentMin article
--- *****************************************************

pm20020maMesrlineNetTxBiasCurrentMin OBJECT-TYPE
	  SYNTAX Unsigned32 (0..65535)
	  MAX-ACCESS read-only
	  STATUS current
	  DESCRIPTION
        "
        Min Line Trscv Tx Laser Bias :This
        OID gives the minimum Tx Laser
         Bias value among the network lanes
        of the Line Transceiver, read from
        the DDM (Digital Diagnostic Monitoring)
        (Bias = AV/10) (Unit = mA) <Help>
        This Measure gives the minimum
         Tx Laser Bias value among the
         network lanes of the Line Transceiver
        "
	  ::= { pm20020maMesrOther 214 }



--- *****************************************************
---     LEAF for the lineNetRxInputPwrMin article
--- *****************************************************

pm20020maMesrlineNetRxInputPwrMin OBJECT-TYPE
	  SYNTAX Unsigned32 (0..65535)
	  MAX-ACCESS read-only
	  STATUS current
	  DESCRIPTION
        "
        Min Line Trscv Rx Power :This
         OID gives the minimum Receive
         power value among the network
         lanes of the Line Transceiver,
        read in the DDM (Digital Diagnostic
        Monitoring) (Power = AV/100) (Unit
        = dBm) <Help> This Measure gives
        the minimum Receive power value
        among the network lanes of the
         Line Transceiver
        "
	  ::= { pm20020maMesrOther 215 }



--- *****************************************************
---     LEAF for the lineResidualChromaticDispMin article
--- *****************************************************

pm20020maMesrlineResidualChromaticDispMin OBJECT-TYPE
	  SYNTAX Unsigned32 (0..65535)
	  MAX-ACCESS read-only
	  STATUS current
	  DESCRIPTION
        "
        Min Residual Chromatic Dispersion
        :This OID gives the minimum Residual
        Chromatic Dispersion on the Line
        interface since the last measure
        reset  (Unit = ps/nm)<Help> This
        measure gives the minimum Residual
        Chromatic Dispersion on the Line
        interface since the last measure
        reset.
        "
	  ::= { pm20020maMesrOther 216 }



--- *****************************************************
---     LEAF for the lineDiffGroupDelayMin article
--- *****************************************************

pm20020maMesrlineDiffGroupDelayMin OBJECT-TYPE
	  SYNTAX Unsigned32 (0..65535)
	  MAX-ACCESS read-only
	  STATUS current
	  DESCRIPTION
        "
        Min Differential Group Delay :This
        OID gives the minimum Differential
        Group Delay  on the Line interface
        since the last measure reset  (Unit
        = ps)<Help> This measure gives
         the minimum Differential Group
        Delay on the Line interface since
        the last measure reset.
        "
	  ::= { pm20020maMesrOther 217 }



--- *****************************************************
---     LEAF for the lineQFactorMin article
--- *****************************************************

pm20020maMesrlineQFactorMin OBJECT-TYPE
	  SYNTAX Unsigned32 (0..65535)
	  MAX-ACCESS read-only
	  STATUS current
	  DESCRIPTION
        "
        Min Q Factor :This OID gives the
        minimum Q Factor on the Line interface
        since the last measure reset  (Unit
        = dB)<Help> This measure gives
         the minimum Q Factor on the Line
        interface since the last measure
        reset.
        "
	  ::= { pm20020maMesrOther 218 }



--- *****************************************************
---     LEAF for the lineCarrierFreqOffsetMin article
--- *****************************************************

pm20020maMesrlineCarrierFreqOffsetMin OBJECT-TYPE
	  SYNTAX Unsigned32 (0..65535)
	  MAX-ACCESS read-only
	  STATUS current
	  DESCRIPTION
        "
        Min Carrier Frequency Offset :This
        OID gives the minimum Carrier Frequency
        Offset on the Line interface since
        the last measure reset  (Unit =
        Mhz)<Help> This measure gives the
        minimum Carrier Frequency Offset
        on the Line interface since the
        last measure reset
        "
	  ::= { pm20020maMesrOther 219 }



--- *****************************************************
---     LEAF for the lineOsnrMin article
--- *****************************************************

pm20020maMesrlineOsnrMin OBJECT-TYPE
	  SYNTAX Unsigned32 (0..65535)
	  MAX-ACCESS read-only
	  STATUS current
	  DESCRIPTION
        "
        Min OSNR :This OID gives the minimum
        OSNR on the Line interface since
        the last measure reset  (OSNR =
        AV/10) (Unit = dB)<Help> This measure
        gives the minimum OSNR on the Line
        interface since the last measure
        reset.
        "
	  ::= { pm20020maMesrOther 220 }



--- *****************************************************
---     LEAF for the clientNetTxTempMax article
--- *****************************************************

pm20020maMesrclientNetTxTempMax OBJECT-TYPE
	  SYNTAX Unsigned32 (0..65535)
	  MAX-ACCESS read-only
	  STATUS current
	  DESCRIPTION
        "
        Max Client Trscv Laser Temperature
        :This OID gives the maximum Laser
        temperature value among the network
        lanes of the Client Transceiver,
        read from the DDM (Digital Diagnostic
        Monitoring) (Temperature = AV/256)
        (Unit = C) <Help> This Measure
         gives the maximum Laser temperature
        value among the network lanes of
        the Client Transceiver
        "
	  ::= { pm20020maMesrOther 224 }



--- *****************************************************
---     LEAF for the clientNetTxBiasMax article
--- *****************************************************

pm20020maMesrclientNetTxBiasMax OBJECT-TYPE
	  SYNTAX Unsigned32 (0..65535)
	  MAX-ACCESS read-only
	  STATUS current
	  DESCRIPTION
        "
        Max Client Trscv Laser Bias :This
        OID gives the maximum Laser bias
        value among the network lanes of
        the Client Transceiver, read from
        the DDM (Digital Diagnostic Monitoring)
        (Bias = AV/500) (Unit = mA) <Help>
        This Measure gives the maximum
         Laser bias value among the network
        lanes of the Client Transceiver
        "
	  ::= { pm20020maMesrOther 225 }



--- *****************************************************
---     LEAF for the clientNetTxPwrMax article
--- *****************************************************

pm20020maMesrclientNetTxPwrMax OBJECT-TYPE
	  SYNTAX Unsigned32 (0..65535)
	  MAX-ACCESS read-only
	  STATUS current
	  DESCRIPTION
        "
        Max Client Trscv Tx Power :This
        OID gives the maximum transmit
         power value among the network
         lanes of the Client Transceiver,
        read from the DDM (Digital Diagnostic
        Monitoring) (Power = 10*log(AV)-40)
        (Unit = dBm) <Help> This Measure
        gives the maximum transmit power
        value among the network lanes of
        the Client Transceiver
        "
	  ::= { pm20020maMesrOther 226 }



--- *****************************************************
---     LEAF for the clientNetRxPwrMax article
--- *****************************************************

pm20020maMesrclientNetRxPwrMax OBJECT-TYPE
	  SYNTAX Unsigned32 (0..65535)
	  MAX-ACCESS read-only
	  STATUS current
	  DESCRIPTION
        "
        Max Client Trscv Rx Power :This
        OID gives the maximum receive power
        value among the network lanes of
        the Client Transceiver, read in
        the DDM (Digital Diagnostic Monitoring)
        (Power = 10*log(AV)-40) (Unit =
        dBm) <Help> This Measure gives
         the maximum receive power value
        among the network lanes of the
         Client Transceiver
        "
	  ::= { pm20020maMesrOther 227 }



--- *****************************************************
---     LEAF for the lineNetTxLaserOutputPwrMax article
--- *****************************************************

pm20020maMesrlineNetTxLaserOutputPwrMax OBJECT-TYPE
	  SYNTAX Unsigned32 (0..65535)
	  MAX-ACCESS read-only
	  STATUS current
	  DESCRIPTION
        "
        Max Line Trscv Tx Power :This
         OID gives the maximum Tx Laser
        transmit power value among the
         network lanes of the Line Transceiver,
        read in the DDM (Digital Diagnostic
        Monitoring) (Power = 10*log(AV)-40)
        (Unit = dBm) <Help> This Measure
        gives the maximum Tx Laser transmit
        power value among the network lanes
        of the Line Transceiver
        "
	  ::= { pm20020maMesrOther 228 }



--- *****************************************************
---     LEAF for the lineNetTxLaserTempMax article
--- *****************************************************

pm20020maMesrlineNetTxLaserTempMax OBJECT-TYPE
	  SYNTAX Unsigned32 (0..65535)
	  MAX-ACCESS read-only
	  STATUS current
	  DESCRIPTION
        "
        Max Line Trscv Tx Laser Temperature
        :This OID gives the maximum Tx
         Laser Temperature value among
         the network lanes of the Line
         Transceiver, read from the DDM
        (Digital Diagnostic Monitoring)
        (Temperature = AV/256) (Unit =
         C) <Help> This Measure gives the
        maximum Tx Laser Temperature value
        among the network lanes of the
         Line Transceiver
        "
	  ::= { pm20020maMesrOther 229 }



--- *****************************************************
---     LEAF for the lineNetTxBiasCurrentMax article
--- *****************************************************

pm20020maMesrlineNetTxBiasCurrentMax OBJECT-TYPE
	  SYNTAX Unsigned32 (0..65535)
	  MAX-ACCESS read-only
	  STATUS current
	  DESCRIPTION
        "
        Max Line Trscv Tx Laser Bias :This
        OID gives the maximum Tx Laser
         Bias value among the network lanes
        of the Line Transceiver, read from
        the DDM (Digital Diagnostic Monitoring)
        (Bias = AV/10) (Unit = mA) <Help>
        This Measure gives the maximum
         Tx Laser Bias value among the
         network lanes of the Line Transceiver
        "
	  ::= { pm20020maMesrOther 230 }



--- *****************************************************
---     LEAF for the lineNetRxInputPwrMax article
--- *****************************************************

pm20020maMesrlineNetRxInputPwrMax OBJECT-TYPE
	  SYNTAX Unsigned32 (0..65535)
	  MAX-ACCESS read-only
	  STATUS current
	  DESCRIPTION
        "
        Max Line Trscv Rx Power :This
         OID gives the maximum Receive
         power value among the network
         lanes of the Line Transceiver,
        read in the DDM (Digital Diagnostic
        Monitoring) (Power = 10*log(AV)-40)
        (Unit = dBm) <Help> This Measure
        gives the maximum Receive power
        value among the network lanes of
        the Line Transceiver
        "
	  ::= { pm20020maMesrOther 231 }



--- *****************************************************
---     LEAF for the lineResidualChromaticDispMax article
--- *****************************************************

pm20020maMesrlineResidualChromaticDispMax OBJECT-TYPE
	  SYNTAX Unsigned32 (0..65535)
	  MAX-ACCESS read-only
	  STATUS current
	  DESCRIPTION
        "
        Max Residual Chromatic Dispersion
        :This OID gives the maximum Residual
        Chromatic Dispersion on the Line
        interface since the last measure
        reset  (Unit = ps/nm)<Help> This
        measure gives the maximum Residual
        Chromatic Dispersion on the Line
        interface since the last measure
        reset.
        "
	  ::= { pm20020maMesrOther 232 }



--- *****************************************************
---     LEAF for the lineDiffGroupDelayMax article
--- *****************************************************

pm20020maMesrlineDiffGroupDelayMax OBJECT-TYPE
	  SYNTAX Unsigned32 (0..65535)
	  MAX-ACCESS read-only
	  STATUS current
	  DESCRIPTION
        "
        Max Differential Group Delay :This
        OID gives the maximum Differential
        Group Delay  on the Line interface
        since the last measure reset
         (Unit = ps)<Help> This measure
        gives the maximum Differential
         Group Delay on the Line interface
        since the last measure reset.
        "
	  ::= { pm20020maMesrOther 233 }



--- *****************************************************
---     LEAF for the lineQFactorMax article
--- *****************************************************

pm20020maMesrlineQFactorMax OBJECT-TYPE
	  SYNTAX Unsigned32 (0..65535)
	  MAX-ACCESS read-only
	  STATUS current
	  DESCRIPTION
        "
        Max Q Factor :This OID gives the
        maximum Q Factor on the Line interface
        since the last measure reset  (Unit
        = dB)<Help> This measure gives
         the maximum Q Factor on the Line
        interface since the last measure
        reset.
        "
	  ::= { pm20020maMesrOther 234 }



--- *****************************************************
---     LEAF for the lineCarrierFreqOffsetMax article
--- *****************************************************

pm20020maMesrlineCarrierFreqOffsetMax OBJECT-TYPE
	  SYNTAX Unsigned32 (0..65535)
	  MAX-ACCESS read-only
	  STATUS current
	  DESCRIPTION
        "
        Max Carrier Frequency Offset :This
        OID gives the maximum Carrier Frequency
        Offset on the Line interface since
        the last measure reset   (Unit
         = Mhz)<Help> This measure gives
        the maximum Carrier Frequency Offset
        on the Line interface since the
        last measure reset.
        "
	  ::= { pm20020maMesrOther 235 }



--- *****************************************************
---     LEAF for the lineOsnrMax article
--- *****************************************************

pm20020maMesrlineOsnrMax OBJECT-TYPE
	  SYNTAX Unsigned32 (0..65535)
	  MAX-ACCESS read-only
	  STATUS current
	  DESCRIPTION
        "
        Max OSNR :This OID gives the maximum
        OSNR on the Line interface since
        the last measure reset  (OSNR =
        AV/10) (Unit = dB) <Help> This
         measure gives the maximum OSNR
        on the Line interface since the
        last measure reset
        "
	  ::= { pm20020maMesrOther 236 }








--- *****************************************************
--- $$$$$$$$$$$$$$$$$$$$$$$$$$$$$$$$$$$$$$$$$$$$$$$$$$$$$
---     PERFORMANCE
--- $$$$$$$$$$$$$$$$$$$$$$$$$$$$$$$$$$$$$$$$$$$$$$$$$$$$$
--- *****************************************************



--- *****************************************************
---     Leaf of the telecomInputClientCurrent15Stat
--- *****************************************************
--- *********************************************************
---     TABLE for the pm20020maPerfTelecomInputClientCurrent15Stat articles
--- *********************************************************

pm20020maPerfTelecomInputClientCurrent15StatTable OBJECT-TYPE
	SYNTAX  SEQUENCE OF Pm20020maPerfTelecomInputClientCurrent15StatEntry
	MAX-ACCESS not-accessible
	STATUS current
	DESCRIPTION
        "
        List of pm20020maPerfTelecomInputClientCurrent15Stat
        Article
        "
	::= { pm20020maMonPerfClient 16 }


pm20020maPerfTelecomInputClientCurrent15StatEntry OBJECT-TYPE
	SYNTAX Pm20020maPerfTelecomInputClientCurrent15StatEntry
	MAX-ACCESS not-accessible
	STATUS current
	DESCRIPTION
        "
        Row definition for the pm20020maPerfTelecomInputClientCurrent15Stat
        table
        "
	INDEX   { pm20020maPerfTelecomInputClientCurrent15StatIndex }
	::= { pm20020maPerfTelecomInputClientCurrent15StatTable 1 }


Pm20020maPerfTelecomInputClientCurrent15StatEntry ::=
	SEQUENCE {
	pm20020maPerfTelecomInputClientCurrent15StatIndex
		INTEGER,
	pm20020maPerfTelecomInputClientCurrent15StatInvCvPortn
		EkiOnOff,
	pm20020maPerfTelecomInputClientCurrent15StatCvValuePortn
		Unsigned32,
	pm20020maPerfTelecomInputClientCurrent15StatInvEsPortn
		EkiOnOff,
	pm20020maPerfTelecomInputClientCurrent15StatEsValuePortn
		Unsigned32,
	pm20020maPerfTelecomInputClientCurrent15StatInvSesPortn
		EkiOnOff,
	pm20020maPerfTelecomInputClientCurrent15StatSesValuePortn
		Unsigned32,
	pm20020maPerfTelecomInputClientCurrent15StatInvSefsPortn
		EkiOnOff,
	pm20020maPerfTelecomInputClientCurrent15StatSefsValuePortn
		Unsigned32,
	pm20020maPerfTelecomInputClientCurrent15StatInvUasPortn
		EkiOnOff,
	pm20020maPerfTelecomInputClientCurrent15StatUasValuePortn
		Unsigned32
	}


pm20020maPerfTelecomInputClientCurrent15StatIndex OBJECT-TYPE
	SYNTAX  INTEGER(0..128)
	MAX-ACCESS  read-only
	STATUS current
	DESCRIPTION
        "
        Index definition for the pm20020maPerfTelecomInputClientCurrent15Stat
        table
        "
	::= { pm20020maPerfTelecomInputClientCurrent15StatEntry 1 }


pm20020maPerfTelecomInputClientCurrent15StatInvCvPortn OBJECT-TYPE
	SYNTAX  EkiOnOff
	MAX-ACCESS read-only
	STATUS current
	DESCRIPTION
        "
        Current 15-min EBC counter inv.
        :This OID indicates that the current
        15-min Coding Violation counter
        is invalid
        "
	::= { pm20020maPerfTelecomInputClientCurrent15StatEntry 2 }


pm20020maPerfTelecomInputClientCurrent15StatCvValuePortn OBJECT-TYPE
	SYNTAX  Unsigned32
	MAX-ACCESS read-only
	STATUS current
	DESCRIPTION
        "
        Current 15-min EBC counter :This
        OID gives the current 15-min Coding
        Violation counter value
        "
	::= { pm20020maPerfTelecomInputClientCurrent15StatEntry 3 }


pm20020maPerfTelecomInputClientCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pm20020maPerfTelecomInputClientCurrent15StatEntry 4 }


pm20020maPerfTelecomInputClientCurrent15StatEsValuePortn OBJECT-TYPE
	SYNTAX  Unsigned32
	MAX-ACCESS read-only
	STATUS current
	DESCRIPTION
        "
        Current 15-min ES counter :This
        OID gives the current 15-min Errored
        Second counter value
        "
	::= { pm20020maPerfTelecomInputClientCurrent15StatEntry 5 }


pm20020maPerfTelecomInputClientCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pm20020maPerfTelecomInputClientCurrent15StatEntry 6 }


pm20020maPerfTelecomInputClientCurrent15StatSesValuePortn OBJECT-TYPE
	SYNTAX  Unsigned32
	MAX-ACCESS read-only
	STATUS current
	DESCRIPTION
        "
        Current 15-min SES counter :This
        OID gives the current 15-min severely
        Errored Second counter value
        "
	::= { pm20020maPerfTelecomInputClientCurrent15StatEntry 7 }


pm20020maPerfTelecomInputClientCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pm20020maPerfTelecomInputClientCurrent15StatEntry 8 }


pm20020maPerfTelecomInputClientCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pm20020maPerfTelecomInputClientCurrent15StatEntry 9 }


pm20020maPerfTelecomInputClientCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pm20020maPerfTelecomInputClientCurrent15StatEntry 10 }


pm20020maPerfTelecomInputClientCurrent15StatUasValuePortn OBJECT-TYPE
	SYNTAX  Unsigned32
	MAX-ACCESS read-only
	STATUS current
	DESCRIPTION
        "
        Current 15-min UAS counter :This
        OID gives the current 15-min UnAvailable
        Second counter value
        "
	::= { pm20020maPerfTelecomInputClientCurrent15StatEntry 11 }


--- *****************************************************
---     Leaf of the telecomInputClientPast15Stat
--- *****************************************************
--- *********************************************************
---     TABLE for the pm20020maPerfTelecomInputClientPast15StatHistory articles
--- *********************************************************

pm20020maPerfTelecomInputClientPast15StatHistoryPort1Table OBJECT-TYPE
	SYNTAX  SEQUENCE OF Pm20020maPerfTelecomInputClientPast15StatHistoryPort1Entry
	MAX-ACCESS not-accessible
	STATUS current
	DESCRIPTION
        "
        List of pm20020maPerfTelecomInputClientPast15StatHistory
        Article
        "
	::= { pm20020maMonPerfClient 48 }


pm20020maPerfTelecomInputClientPast15StatHistoryPort1Entry OBJECT-TYPE
	SYNTAX Pm20020maPerfTelecomInputClientPast15StatHistoryPort1Entry
	MAX-ACCESS not-accessible
	STATUS current
	DESCRIPTION
        "
        Row definition for the pm20020maPerfTelecomInputClientPast15StatHistory
        table
        "
	INDEX   { pm20020maPerfTelecomInputClientPast15StatHistoryPort1Index }
	::= { pm20020maPerfTelecomInputClientPast15StatHistoryPort1Table 1 }


Pm20020maPerfTelecomInputClientPast15StatHistoryPort1Entry ::=
	SEQUENCE {
	pm20020maPerfTelecomInputClientPast15StatHistoryPort1Index
		INTEGER,
	pm20020maPerfTelecomInputClientPast15StatHistoryInvCvPort1
		EkiOnOff,
	pm20020maPerfTelecomInputClientPast15StatHistoryCvValuePort1
		Unsigned32,
	pm20020maPerfTelecomInputClientPast15StatHistoryInvEsPort1
		EkiOnOff,
	pm20020maPerfTelecomInputClientPast15StatHistoryEsValuePort1
		Unsigned32,
	pm20020maPerfTelecomInputClientPast15StatHistoryInvSesPort1
		EkiOnOff,
	pm20020maPerfTelecomInputClientPast15StatHistorySesValuePort1
		Unsigned32,
	pm20020maPerfTelecomInputClientPast15StatHistoryInvSefsPort1
		EkiOnOff,
	pm20020maPerfTelecomInputClientPast15StatHistorySefsValuePort1
		Unsigned32,
	pm20020maPerfTelecomInputClientPast15StatHistoryInvUasPort1
		EkiOnOff,
	pm20020maPerfTelecomInputClientPast15StatHistoryUasValuePort1
		Unsigned32
	}


pm20020maPerfTelecomInputClientPast15StatHistoryPort1Index OBJECT-TYPE
	SYNTAX  INTEGER(0..128)
	MAX-ACCESS  read-only
	STATUS current
	DESCRIPTION
        "
        Index definition for the pm20020maPerfTelecomInputClientPast15StatHistory
        table
        "
	::= { pm20020maPerfTelecomInputClientPast15StatHistoryPort1Entry 1 }


pm20020maPerfTelecomInputClientPast15StatHistoryInvCvPort1 OBJECT-TYPE
	SYNTAX  EkiOnOff
	MAX-ACCESS read-only
	STATUS current
	DESCRIPTION
        "
        Previous 15-min EBC counter inv.
        :This OID indicates that the previous
        15-min Coding Violation counter
        is invalid
        "
	::= { pm20020maPerfTelecomInputClientPast15StatHistoryPort1Entry 2 }


pm20020maPerfTelecomInputClientPast15StatHistoryCvValuePort1 OBJECT-TYPE
	SYNTAX  Unsigned32
	MAX-ACCESS read-only
	STATUS current
	DESCRIPTION
        "
        Previous 15-min EBC counter :This
        OID gives the previous 15-min Coding
        Violation counter value
        "
	::= { pm20020maPerfTelecomInputClientPast15StatHistoryPort1Entry 3 }


pm20020maPerfTelecomInputClientPast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pm20020maPerfTelecomInputClientPast15StatHistoryPort1Entry 4 }


pm20020maPerfTelecomInputClientPast15StatHistoryEsValuePort1 OBJECT-TYPE
	SYNTAX  Unsigned32
	MAX-ACCESS read-only
	STATUS current
	DESCRIPTION
        "
        Previous 15-min ES counter :This
        OID gives the previous 15-min Errored
        Second counter value
        "
	::= { pm20020maPerfTelecomInputClientPast15StatHistoryPort1Entry 5 }


pm20020maPerfTelecomInputClientPast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pm20020maPerfTelecomInputClientPast15StatHistoryPort1Entry 6 }


pm20020maPerfTelecomInputClientPast15StatHistorySesValuePort1 OBJECT-TYPE
	SYNTAX  Unsigned32
	MAX-ACCESS read-only
	STATUS current
	DESCRIPTION
        "
        Previous 15-min SES counter :This
        OID gives the previous 15-min severely
        Errored Second counter value
        "
	::= { pm20020maPerfTelecomInputClientPast15StatHistoryPort1Entry 7 }


pm20020maPerfTelecomInputClientPast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pm20020maPerfTelecomInputClientPast15StatHistoryPort1Entry 8 }


pm20020maPerfTelecomInputClientPast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pm20020maPerfTelecomInputClientPast15StatHistoryPort1Entry 9 }


pm20020maPerfTelecomInputClientPast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pm20020maPerfTelecomInputClientPast15StatHistoryPort1Entry 10 }


pm20020maPerfTelecomInputClientPast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pm20020maPerfTelecomInputClientPast15StatHistoryPort1Entry 11 }


--- *****************************************************
---     Leaf of the telecomInputClientCurrent24Stat
--- *****************************************************
--- *********************************************************
---     TABLE for the pm20020maPerfTelecomInputClientCurrent24Stat articles
--- *********************************************************

pm20020maPerfTelecomInputClientCurrent24StatTable OBJECT-TYPE
	SYNTAX  SEQUENCE OF Pm20020maPerfTelecomInputClientCurrent24StatEntry
	MAX-ACCESS not-accessible
	STATUS current
	DESCRIPTION
        "
        List of pm20020maPerfTelecomInputClientCurrent24Stat
        Article
        "
	::= { pm20020maMonPerfClient 80 }


pm20020maPerfTelecomInputClientCurrent24StatEntry OBJECT-TYPE
	SYNTAX Pm20020maPerfTelecomInputClientCurrent24StatEntry
	MAX-ACCESS not-accessible
	STATUS current
	DESCRIPTION
        "
        Row definition for the pm20020maPerfTelecomInputClientCurrent24Stat
        table
        "
	INDEX   { pm20020maPerfTelecomInputClientCurrent24StatIndex }
	::= { pm20020maPerfTelecomInputClientCurrent24StatTable 1 }


Pm20020maPerfTelecomInputClientCurrent24StatEntry ::=
	SEQUENCE {
	pm20020maPerfTelecomInputClientCurrent24StatIndex
		INTEGER,
	pm20020maPerfTelecomInputClientCurrent24StatInvCvPortn
		EkiOnOff,
	pm20020maPerfTelecomInputClientCurrent24StatCvValuePortn
		Unsigned32,
	pm20020maPerfTelecomInputClientCurrent24StatInvEsPortn
		EkiOnOff,
	pm20020maPerfTelecomInputClientCurrent24StatEsValuePortn
		Unsigned32,
	pm20020maPerfTelecomInputClientCurrent24StatInvSesPortn
		EkiOnOff,
	pm20020maPerfTelecomInputClientCurrent24StatSesValuePortn
		Unsigned32,
	pm20020maPerfTelecomInputClientCurrent24StatInvSefsPortn
		EkiOnOff,
	pm20020maPerfTelecomInputClientCurrent24StatSefsValuePortn
		Unsigned32,
	pm20020maPerfTelecomInputClientCurrent24StatInvUasPortn
		EkiOnOff,
	pm20020maPerfTelecomInputClientCurrent24StatUasValuePortn
		Unsigned32
	}


pm20020maPerfTelecomInputClientCurrent24StatIndex OBJECT-TYPE
	SYNTAX  INTEGER(0..128)
	MAX-ACCESS  read-only
	STATUS current
	DESCRIPTION
        "
        Index definition for the pm20020maPerfTelecomInputClientCurrent24Stat
        table
        "
	::= { pm20020maPerfTelecomInputClientCurrent24StatEntry 1 }


pm20020maPerfTelecomInputClientCurrent24StatInvCvPortn OBJECT-TYPE
	SYNTAX  EkiOnOff
	MAX-ACCESS read-only
	STATUS current
	DESCRIPTION
        "
        Current 24-hours EBC counter inv.
        :This OID indicates that the current
        24-hours Coding Violation counter
        is invalid
        "
	::= { pm20020maPerfTelecomInputClientCurrent24StatEntry 2 }


pm20020maPerfTelecomInputClientCurrent24StatCvValuePortn OBJECT-TYPE
	SYNTAX  Unsigned32
	MAX-ACCESS read-only
	STATUS current
	DESCRIPTION
        "
        Current 24-hours EBC counter :This
        OID gives the current 24-hours
         Coding Violation counter value
        "
	::= { pm20020maPerfTelecomInputClientCurrent24StatEntry 3 }


pm20020maPerfTelecomInputClientCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pm20020maPerfTelecomInputClientCurrent24StatEntry 4 }


pm20020maPerfTelecomInputClientCurrent24StatEsValuePortn OBJECT-TYPE
	SYNTAX  Unsigned32
	MAX-ACCESS read-only
	STATUS current
	DESCRIPTION
        "
        Current 24-hours ES counter :This
        OID gives the current 24-hours
         Errored Second counter value
        "
	::= { pm20020maPerfTelecomInputClientCurrent24StatEntry 5 }


pm20020maPerfTelecomInputClientCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pm20020maPerfTelecomInputClientCurrent24StatEntry 6 }


pm20020maPerfTelecomInputClientCurrent24StatSesValuePortn OBJECT-TYPE
	SYNTAX  Unsigned32
	MAX-ACCESS read-only
	STATUS current
	DESCRIPTION
        "
        Current 24-hours SES counter :This
        OID gives the current 24-hours
         severely Errored Second counter
        value
        "
	::= { pm20020maPerfTelecomInputClientCurrent24StatEntry 7 }


pm20020maPerfTelecomInputClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pm20020maPerfTelecomInputClientCurrent24StatEntry 8 }


pm20020maPerfTelecomInputClientCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pm20020maPerfTelecomInputClientCurrent24StatEntry 9 }


pm20020maPerfTelecomInputClientCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pm20020maPerfTelecomInputClientCurrent24StatEntry 10 }


pm20020maPerfTelecomInputClientCurrent24StatUasValuePortn OBJECT-TYPE
	SYNTAX  Unsigned32
	MAX-ACCESS read-only
	STATUS current
	DESCRIPTION
        "
        Current 24-hours UAS counter :This
        OID gives the current 24-hours
         UnAvailable Second counter value
        "
	::= { pm20020maPerfTelecomInputClientCurrent24StatEntry 11 }


--- *****************************************************
---     Leaf of the telecomInputClientPast24Stat
--- *****************************************************
--- *********************************************************
---     TABLE for the pm20020maPerfTelecomInputClientPast24StatHistory articles
--- *********************************************************

pm20020maPerfTelecomInputClientPast24StatHistoryPort1Table OBJECT-TYPE
	SYNTAX  SEQUENCE OF Pm20020maPerfTelecomInputClientPast24StatHistoryPort1Entry
	MAX-ACCESS not-accessible
	STATUS current
	DESCRIPTION
        "
        List of pm20020maPerfTelecomInputClientPast24StatHistory
        Article
        "
	::= { pm20020maMonPerfClient 112 }


pm20020maPerfTelecomInputClientPast24StatHistoryPort1Entry OBJECT-TYPE
	SYNTAX Pm20020maPerfTelecomInputClientPast24StatHistoryPort1Entry
	MAX-ACCESS not-accessible
	STATUS current
	DESCRIPTION
        "
        Row definition for the pm20020maPerfTelecomInputClientPast24StatHistory
        table
        "
	INDEX   { pm20020maPerfTelecomInputClientPast24StatHistoryPort1Index }
	::= { pm20020maPerfTelecomInputClientPast24StatHistoryPort1Table 1 }


Pm20020maPerfTelecomInputClientPast24StatHistoryPort1Entry ::=
	SEQUENCE {
	pm20020maPerfTelecomInputClientPast24StatHistoryPort1Index
		INTEGER,
	pm20020maPerfTelecomInputClientPast24StatHistoryInvCvPort1
		EkiOnOff,
	pm20020maPerfTelecomInputClientPast24StatHistoryCvValuePort1
		Unsigned32,
	pm20020maPerfTelecomInputClientPast24StatHistoryInvEsPort1
		EkiOnOff,
	pm20020maPerfTelecomInputClientPast24StatHistoryEsValuePort1
		Unsigned32,
	pm20020maPerfTelecomInputClientPast24StatHistoryInvSesPort1
		EkiOnOff,
	pm20020maPerfTelecomInputClientPast24StatHistorySesValuePort1
		Unsigned32,
	pm20020maPerfTelecomInputClientPast24StatHistoryInvSefsPort1
		EkiOnOff,
	pm20020maPerfTelecomInputClientPast24StatHistorySefsValuePort1
		Unsigned32,
	pm20020maPerfTelecomInputClientPast24StatHistoryInvUasPort1
		EkiOnOff,
	pm20020maPerfTelecomInputClientPast24StatHistoryUasValuePort1
		Unsigned32
	}


pm20020maPerfTelecomInputClientPast24StatHistoryPort1Index OBJECT-TYPE
	SYNTAX  INTEGER(0..128)
	MAX-ACCESS  read-only
	STATUS current
	DESCRIPTION
        "
        Index definition for the pm20020maPerfTelecomInputClientPast24StatHistory
        table
        "
	::= { pm20020maPerfTelecomInputClientPast24StatHistoryPort1Entry 1 }


pm20020maPerfTelecomInputClientPast24StatHistoryInvCvPort1 OBJECT-TYPE
	SYNTAX  EkiOnOff
	MAX-ACCESS read-only
	STATUS current
	DESCRIPTION
        "
        Previous 24-hours EBC counter
         inv. :This OID indicates that
         the previous 24-hours Coding Violation
        counter is invalid
        "
	::= { pm20020maPerfTelecomInputClientPast24StatHistoryPort1Entry 2 }


pm20020maPerfTelecomInputClientPast24StatHistoryCvValuePort1 OBJECT-TYPE
	SYNTAX  Unsigned32
	MAX-ACCESS read-only
	STATUS current
	DESCRIPTION
        "
        Previous 24-hours EBC counter
         :This OID gives the previous 24-hours
        Coding Violation counter value
        "
	::= { pm20020maPerfTelecomInputClientPast24StatHistoryPort1Entry 3 }


pm20020maPerfTelecomInputClientPast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pm20020maPerfTelecomInputClientPast24StatHistoryPort1Entry 4 }


pm20020maPerfTelecomInputClientPast24StatHistoryEsValuePort1 OBJECT-TYPE
	SYNTAX  Unsigned32
	MAX-ACCESS read-only
	STATUS current
	DESCRIPTION
        "
        Previous 24-hours ES counter :This
        OID gives the previous 24-hours
        Errored Second counter value
        "
	::= { pm20020maPerfTelecomInputClientPast24StatHistoryPort1Entry 5 }


pm20020maPerfTelecomInputClientPast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pm20020maPerfTelecomInputClientPast24StatHistoryPort1Entry 6 }


pm20020maPerfTelecomInputClientPast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pm20020maPerfTelecomInputClientPast24StatHistoryPort1Entry 7 }


pm20020maPerfTelecomInputClientPast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm20020maPerfTelecomInputClientPast24StatHistoryPort1Entry 8 }


pm20020maPerfTelecomInputClientPast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pm20020maPerfTelecomInputClientPast24StatHistoryPort1Entry 9 }


pm20020maPerfTelecomInputClientPast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pm20020maPerfTelecomInputClientPast24StatHistoryPort1Entry 10 }


pm20020maPerfTelecomInputClientPast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pm20020maPerfTelecomInputClientPast24StatHistoryPort1Entry 11 }


--- *****************************************************
---     Leaf of the telecomOutputClientCurrent15Stat
--- *****************************************************
--- *********************************************************
---     TABLE for the pm20020maPerfTelecomOutputClientCurrent15Stat articles
--- *********************************************************

pm20020maPerfTelecomOutputClientCurrent15StatTable OBJECT-TYPE
	SYNTAX  SEQUENCE OF Pm20020maPerfTelecomOutputClientCurrent15StatEntry
	MAX-ACCESS not-accessible
	STATUS current
	DESCRIPTION
        "
        List of pm20020maPerfTelecomOutputClientCurrent15Stat
        Article
        "
	::= { pm20020maMonPerfClient 144 }


pm20020maPerfTelecomOutputClientCurrent15StatEntry OBJECT-TYPE
	SYNTAX Pm20020maPerfTelecomOutputClientCurrent15StatEntry
	MAX-ACCESS not-accessible
	STATUS current
	DESCRIPTION
        "
        Row definition for the pm20020maPerfTelecomOutputClientCurrent15Stat
        table
        "
	INDEX   { pm20020maPerfTelecomOutputClientCurrent15StatIndex }
	::= { pm20020maPerfTelecomOutputClientCurrent15StatTable 1 }


Pm20020maPerfTelecomOutputClientCurrent15StatEntry ::=
	SEQUENCE {
	pm20020maPerfTelecomOutputClientCurrent15StatIndex
		INTEGER,
	pm20020maPerfTelecomOutputClientCurrent15StatInvCvPortn
		EkiOnOff,
	pm20020maPerfTelecomOutputClientCurrent15StatCvValuePortn
		Unsigned32,
	pm20020maPerfTelecomOutputClientCurrent15StatInvEsPortn
		EkiOnOff,
	pm20020maPerfTelecomOutputClientCurrent15StatEsValuePortn
		Unsigned32,
	pm20020maPerfTelecomOutputClientCurrent15StatInvSesPortn
		EkiOnOff,
	pm20020maPerfTelecomOutputClientCurrent15StatSesValuePortn
		Unsigned32,
	pm20020maPerfTelecomOutputClientCurrent15StatInvSefsPortn
		EkiOnOff,
	pm20020maPerfTelecomOutputClientCurrent15StatSefsValuePortn
		Unsigned32,
	pm20020maPerfTelecomOutputClientCurrent15StatInvUasPortn
		EkiOnOff,
	pm20020maPerfTelecomOutputClientCurrent15StatUasValuePortn
		Unsigned32
	}


pm20020maPerfTelecomOutputClientCurrent15StatIndex OBJECT-TYPE
	SYNTAX  INTEGER(0..128)
	MAX-ACCESS  read-only
	STATUS current
	DESCRIPTION
        "
        Index definition for the pm20020maPerfTelecomOutputClientCurrent15Stat
        table
        "
	::= { pm20020maPerfTelecomOutputClientCurrent15StatEntry 1 }


pm20020maPerfTelecomOutputClientCurrent15StatInvCvPortn OBJECT-TYPE
	SYNTAX  EkiOnOff
	MAX-ACCESS read-only
	STATUS current
	DESCRIPTION
        "
        Current 15-min EBC counter inv.
        :This OID indicates that the current
        15-min Coding Violation counter
        is invalid
        "
	::= { pm20020maPerfTelecomOutputClientCurrent15StatEntry 2 }


pm20020maPerfTelecomOutputClientCurrent15StatCvValuePortn OBJECT-TYPE
	SYNTAX  Unsigned32
	MAX-ACCESS read-only
	STATUS current
	DESCRIPTION
        "
        Current 15-min EBC counter :This
        OID gives the current 15-min Coding
        Violation counter value
        "
	::= { pm20020maPerfTelecomOutputClientCurrent15StatEntry 3 }


pm20020maPerfTelecomOutputClientCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pm20020maPerfTelecomOutputClientCurrent15StatEntry 4 }


pm20020maPerfTelecomOutputClientCurrent15StatEsValuePortn OBJECT-TYPE
	SYNTAX  Unsigned32
	MAX-ACCESS read-only
	STATUS current
	DESCRIPTION
        "
        Current 15-min ES counter :This
        OID gives the current 15-min Errored
        Second counter value
        "
	::= { pm20020maPerfTelecomOutputClientCurrent15StatEntry 5 }


pm20020maPerfTelecomOutputClientCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pm20020maPerfTelecomOutputClientCurrent15StatEntry 6 }


pm20020maPerfTelecomOutputClientCurrent15StatSesValuePortn OBJECT-TYPE
	SYNTAX  Unsigned32
	MAX-ACCESS read-only
	STATUS current
	DESCRIPTION
        "
        Current 15-min SES counter :This
        OID gives the current 15-min severely
        Errored Second counter value
        "
	::= { pm20020maPerfTelecomOutputClientCurrent15StatEntry 7 }


pm20020maPerfTelecomOutputClientCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pm20020maPerfTelecomOutputClientCurrent15StatEntry 8 }


pm20020maPerfTelecomOutputClientCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pm20020maPerfTelecomOutputClientCurrent15StatEntry 9 }


pm20020maPerfTelecomOutputClientCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pm20020maPerfTelecomOutputClientCurrent15StatEntry 10 }


pm20020maPerfTelecomOutputClientCurrent15StatUasValuePortn OBJECT-TYPE
	SYNTAX  Unsigned32
	MAX-ACCESS read-only
	STATUS current
	DESCRIPTION
        "
        Current 15-min UAS counter :This
        OID gives the current 15-min UnAvailable
        Second counter value
        "
	::= { pm20020maPerfTelecomOutputClientCurrent15StatEntry 11 }


--- *****************************************************
---     Leaf of the telecomOutputClientPast15Stat
--- *****************************************************
--- *********************************************************
---     TABLE for the pm20020maPerfTelecomOutputClientPast15StatHistory articles
--- *********************************************************

pm20020maPerfTelecomOutputClientPast15StatHistoryPort1Table OBJECT-TYPE
	SYNTAX  SEQUENCE OF Pm20020maPerfTelecomOutputClientPast15StatHistoryPort1Entry
	MAX-ACCESS not-accessible
	STATUS current
	DESCRIPTION
        "
        List of pm20020maPerfTelecomOutputClientPast15StatHistory
        Article
        "
	::= { pm20020maMonPerfClient 176 }


pm20020maPerfTelecomOutputClientPast15StatHistoryPort1Entry OBJECT-TYPE
	SYNTAX Pm20020maPerfTelecomOutputClientPast15StatHistoryPort1Entry
	MAX-ACCESS not-accessible
	STATUS current
	DESCRIPTION
        "
        Row definition for the pm20020maPerfTelecomOutputClientPast15StatHistory
        table
        "
	INDEX   { pm20020maPerfTelecomOutputClientPast15StatHistoryPort1Index }
	::= { pm20020maPerfTelecomOutputClientPast15StatHistoryPort1Table 1 }


Pm20020maPerfTelecomOutputClientPast15StatHistoryPort1Entry ::=
	SEQUENCE {
	pm20020maPerfTelecomOutputClientPast15StatHistoryPort1Index
		INTEGER,
	pm20020maPerfTelecomOutputClientPast15StatHistoryInvCvPort1
		EkiOnOff,
	pm20020maPerfTelecomOutputClientPast15StatHistoryCvValuePort1
		Unsigned32,
	pm20020maPerfTelecomOutputClientPast15StatHistoryInvEsPort1
		EkiOnOff,
	pm20020maPerfTelecomOutputClientPast15StatHistoryEsValuePort1
		Unsigned32,
	pm20020maPerfTelecomOutputClientPast15StatHistoryInvSesPort1
		EkiOnOff,
	pm20020maPerfTelecomOutputClientPast15StatHistorySesValuePort1
		Unsigned32,
	pm20020maPerfTelecomOutputClientPast15StatHistoryInvSefsPort1
		EkiOnOff,
	pm20020maPerfTelecomOutputClientPast15StatHistorySefsValuePort1
		Unsigned32,
	pm20020maPerfTelecomOutputClientPast15StatHistoryInvUasPort1
		EkiOnOff,
	pm20020maPerfTelecomOutputClientPast15StatHistoryUasValuePort1
		Unsigned32
	}


pm20020maPerfTelecomOutputClientPast15StatHistoryPort1Index OBJECT-TYPE
	SYNTAX  INTEGER(0..128)
	MAX-ACCESS  read-only
	STATUS current
	DESCRIPTION
        "
        Index definition for the pm20020maPerfTelecomOutputClientPast15StatHistory
        table
        "
	::= { pm20020maPerfTelecomOutputClientPast15StatHistoryPort1Entry 1 }


pm20020maPerfTelecomOutputClientPast15StatHistoryInvCvPort1 OBJECT-TYPE
	SYNTAX  EkiOnOff
	MAX-ACCESS read-only
	STATUS current
	DESCRIPTION
        "
        Previous 15-min EBC counter inv.
        :This OID indicates that the previous
        15-min Coding Violation counter
        is invalid
        "
	::= { pm20020maPerfTelecomOutputClientPast15StatHistoryPort1Entry 2 }


pm20020maPerfTelecomOutputClientPast15StatHistoryCvValuePort1 OBJECT-TYPE
	SYNTAX  Unsigned32
	MAX-ACCESS read-only
	STATUS current
	DESCRIPTION
        "
        Previous 15-min EBC counter :This
        OID gives the previous 15-min Coding
        Violation counter value
        "
	::= { pm20020maPerfTelecomOutputClientPast15StatHistoryPort1Entry 3 }


pm20020maPerfTelecomOutputClientPast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pm20020maPerfTelecomOutputClientPast15StatHistoryPort1Entry 4 }


pm20020maPerfTelecomOutputClientPast15StatHistoryEsValuePort1 OBJECT-TYPE
	SYNTAX  Unsigned32
	MAX-ACCESS read-only
	STATUS current
	DESCRIPTION
        "
        Previous 15-min ES counter :This
        OID gives the previous 15-min Errored
        Second counter value
        "
	::= { pm20020maPerfTelecomOutputClientPast15StatHistoryPort1Entry 5 }


pm20020maPerfTelecomOutputClientPast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pm20020maPerfTelecomOutputClientPast15StatHistoryPort1Entry 6 }


pm20020maPerfTelecomOutputClientPast15StatHistorySesValuePort1 OBJECT-TYPE
	SYNTAX  Unsigned32
	MAX-ACCESS read-only
	STATUS current
	DESCRIPTION
        "
        Previous 15-min SES counter :This
        OID gives the previous 15-min severely
        Errored Second counter value
        "
	::= { pm20020maPerfTelecomOutputClientPast15StatHistoryPort1Entry 7 }


pm20020maPerfTelecomOutputClientPast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pm20020maPerfTelecomOutputClientPast15StatHistoryPort1Entry 8 }


pm20020maPerfTelecomOutputClientPast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pm20020maPerfTelecomOutputClientPast15StatHistoryPort1Entry 9 }


pm20020maPerfTelecomOutputClientPast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pm20020maPerfTelecomOutputClientPast15StatHistoryPort1Entry 10 }


pm20020maPerfTelecomOutputClientPast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pm20020maPerfTelecomOutputClientPast15StatHistoryPort1Entry 11 }


--- *****************************************************
---     Leaf of the telecomOutputClientCurrent24Stat
--- *****************************************************
--- *********************************************************
---     TABLE for the pm20020maPerfTelecomOutputClientCurrent24Stat articles
--- *********************************************************

pm20020maPerfTelecomOutputClientCurrent24StatTable OBJECT-TYPE
	SYNTAX  SEQUENCE OF Pm20020maPerfTelecomOutputClientCurrent24StatEntry
	MAX-ACCESS not-accessible
	STATUS current
	DESCRIPTION
        "
        List of pm20020maPerfTelecomOutputClientCurrent24Stat
        Article
        "
	::= { pm20020maMonPerfClient 208 }


pm20020maPerfTelecomOutputClientCurrent24StatEntry OBJECT-TYPE
	SYNTAX Pm20020maPerfTelecomOutputClientCurrent24StatEntry
	MAX-ACCESS not-accessible
	STATUS current
	DESCRIPTION
        "
        Row definition for the pm20020maPerfTelecomOutputClientCurrent24Stat
        table
        "
	INDEX   { pm20020maPerfTelecomOutputClientCurrent24StatIndex }
	::= { pm20020maPerfTelecomOutputClientCurrent24StatTable 1 }


Pm20020maPerfTelecomOutputClientCurrent24StatEntry ::=
	SEQUENCE {
	pm20020maPerfTelecomOutputClientCurrent24StatIndex
		INTEGER,
	pm20020maPerfTelecomOutputClientCurrent24StatInvCvPortn
		EkiOnOff,
	pm20020maPerfTelecomOutputClientCurrent24StatCvValuePortn
		Unsigned32,
	pm20020maPerfTelecomOutputClientCurrent24StatInvEsPortn
		EkiOnOff,
	pm20020maPerfTelecomOutputClientCurrent24StatEsValuePortn
		Unsigned32,
	pm20020maPerfTelecomOutputClientCurrent24StatInvSesPortn
		EkiOnOff,
	pm20020maPerfTelecomOutputClientCurrent24StatSesValuePortn
		Unsigned32,
	pm20020maPerfTelecomOutputClientCurrent24StatInvSefsPortn
		EkiOnOff,
	pm20020maPerfTelecomOutputClientCurrent24StatSefsValuePortn
		Unsigned32,
	pm20020maPerfTelecomOutputClientCurrent24StatInvUasPortn
		EkiOnOff,
	pm20020maPerfTelecomOutputClientCurrent24StatUasValuePortn
		Unsigned32
	}


pm20020maPerfTelecomOutputClientCurrent24StatIndex OBJECT-TYPE
	SYNTAX  INTEGER(0..128)
	MAX-ACCESS  read-only
	STATUS current
	DESCRIPTION
        "
        Index definition for the pm20020maPerfTelecomOutputClientCurrent24Stat
        table
        "
	::= { pm20020maPerfTelecomOutputClientCurrent24StatEntry 1 }


pm20020maPerfTelecomOutputClientCurrent24StatInvCvPortn OBJECT-TYPE
	SYNTAX  EkiOnOff
	MAX-ACCESS read-only
	STATUS current
	DESCRIPTION
        "
        Current 24-hours EBC counter inv.
        :This OID indicates that the current
        24-hours Coding Violation counter
        is invalid
        "
	::= { pm20020maPerfTelecomOutputClientCurrent24StatEntry 2 }


pm20020maPerfTelecomOutputClientCurrent24StatCvValuePortn OBJECT-TYPE
	SYNTAX  Unsigned32
	MAX-ACCESS read-only
	STATUS current
	DESCRIPTION
        "
        Current 24-hours EBC counter :This
        OID gives the current 24-hours
         Coding Violation counter value
        "
	::= { pm20020maPerfTelecomOutputClientCurrent24StatEntry 3 }


pm20020maPerfTelecomOutputClientCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pm20020maPerfTelecomOutputClientCurrent24StatEntry 4 }


pm20020maPerfTelecomOutputClientCurrent24StatEsValuePortn OBJECT-TYPE
	SYNTAX  Unsigned32
	MAX-ACCESS read-only
	STATUS current
	DESCRIPTION
        "
        Current 24-hours ES counter :This
        OID gives the current 24-hours
         Errored Second counter value
        "
	::= { pm20020maPerfTelecomOutputClientCurrent24StatEntry 5 }


pm20020maPerfTelecomOutputClientCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pm20020maPerfTelecomOutputClientCurrent24StatEntry 6 }


pm20020maPerfTelecomOutputClientCurrent24StatSesValuePortn OBJECT-TYPE
	SYNTAX  Unsigned32
	MAX-ACCESS read-only
	STATUS current
	DESCRIPTION
        "
        Current 24-hours SES counter :This
        OID gives the current 24-hours
         severely Errored Second counter
        value
        "
	::= { pm20020maPerfTelecomOutputClientCurrent24StatEntry 7 }


pm20020maPerfTelecomOutputClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pm20020maPerfTelecomOutputClientCurrent24StatEntry 8 }


pm20020maPerfTelecomOutputClientCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pm20020maPerfTelecomOutputClientCurrent24StatEntry 9 }


pm20020maPerfTelecomOutputClientCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pm20020maPerfTelecomOutputClientCurrent24StatEntry 10 }


pm20020maPerfTelecomOutputClientCurrent24StatUasValuePortn OBJECT-TYPE
	SYNTAX  Unsigned32
	MAX-ACCESS read-only
	STATUS current
	DESCRIPTION
        "
        Current 24-hours UAS counter :This
        OID gives the current 24-hours
         UnAvailable Second counter value
        "
	::= { pm20020maPerfTelecomOutputClientCurrent24StatEntry 11 }


--- *****************************************************
---     Leaf of the telecomOutputClientPast24Stat
--- *****************************************************
--- *********************************************************
---     TABLE for the pm20020maPerfTelecomOutputClientPast24StatHistory articles
--- *********************************************************

pm20020maPerfTelecomOutputClientPast24StatHistoryPort1Table OBJECT-TYPE
	SYNTAX  SEQUENCE OF Pm20020maPerfTelecomOutputClientPast24StatHistoryPort1Entry
	MAX-ACCESS not-accessible
	STATUS current
	DESCRIPTION
        "
        List of pm20020maPerfTelecomOutputClientPast24StatHistory
        Article
        "
	::= { pm20020maMonPerfClient 240 }


pm20020maPerfTelecomOutputClientPast24StatHistoryPort1Entry OBJECT-TYPE
	SYNTAX Pm20020maPerfTelecomOutputClientPast24StatHistoryPort1Entry
	MAX-ACCESS not-accessible
	STATUS current
	DESCRIPTION
        "
        Row definition for the pm20020maPerfTelecomOutputClientPast24StatHistory
        table
        "
	INDEX   { pm20020maPerfTelecomOutputClientPast24StatHistoryPort1Index }
	::= { pm20020maPerfTelecomOutputClientPast24StatHistoryPort1Table 1 }


Pm20020maPerfTelecomOutputClientPast24StatHistoryPort1Entry ::=
	SEQUENCE {
	pm20020maPerfTelecomOutputClientPast24StatHistoryPort1Index
		INTEGER,
	pm20020maPerfTelecomOutputClientPast24StatHistoryInvCvPort1
		EkiOnOff,
	pm20020maPerfTelecomOutputClientPast24StatHistoryCvValuePort1
		Unsigned32,
	pm20020maPerfTelecomOutputClientPast24StatHistoryInvEsPort1
		EkiOnOff,
	pm20020maPerfTelecomOutputClientPast24StatHistoryEsValuePort1
		Unsigned32,
	pm20020maPerfTelecomOutputClientPast24StatHistoryInvSesPort1
		EkiOnOff,
	pm20020maPerfTelecomOutputClientPast24StatHistorySesValuePort1
		Unsigned32,
	pm20020maPerfTelecomOutputClientPast24StatHistoryInvSefsPort1
		EkiOnOff,
	pm20020maPerfTelecomOutputClientPast24StatHistorySefsValuePort1
		Unsigned32,
	pm20020maPerfTelecomOutputClientPast24StatHistoryInvUasPort1
		EkiOnOff,
	pm20020maPerfTelecomOutputClientPast24StatHistoryUasValuePort1
		Unsigned32
	}


pm20020maPerfTelecomOutputClientPast24StatHistoryPort1Index OBJECT-TYPE
	SYNTAX  INTEGER(0..128)
	MAX-ACCESS  read-only
	STATUS current
	DESCRIPTION
        "
        Index definition for the pm20020maPerfTelecomOutputClientPast24StatHistory
        table
        "
	::= { pm20020maPerfTelecomOutputClientPast24StatHistoryPort1Entry 1 }


pm20020maPerfTelecomOutputClientPast24StatHistoryInvCvPort1 OBJECT-TYPE
	SYNTAX  EkiOnOff
	MAX-ACCESS read-only
	STATUS current
	DESCRIPTION
        "
        Previous 24-hours EBC counter
         inv. :This OID indicates that
         the previous 24-hours Coding Violation
        counter is invalid
        "
	::= { pm20020maPerfTelecomOutputClientPast24StatHistoryPort1Entry 2 }


pm20020maPerfTelecomOutputClientPast24StatHistoryCvValuePort1 OBJECT-TYPE
	SYNTAX  Unsigned32
	MAX-ACCESS read-only
	STATUS current
	DESCRIPTION
        "
        Previous 24-hours EBC counter
         :This OID gives the previous 24-hours
        Coding Violation counter value
        "
	::= { pm20020maPerfTelecomOutputClientPast24StatHistoryPort1Entry 3 }


pm20020maPerfTelecomOutputClientPast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pm20020maPerfTelecomOutputClientPast24StatHistoryPort1Entry 4 }


pm20020maPerfTelecomOutputClientPast24StatHistoryEsValuePort1 OBJECT-TYPE
	SYNTAX  Unsigned32
	MAX-ACCESS read-only
	STATUS current
	DESCRIPTION
        "
        Previous 24-hours ES counter :This
        OID gives the previous 24-hours
        Errored Second counter value
        "
	::= { pm20020maPerfTelecomOutputClientPast24StatHistoryPort1Entry 5 }


pm20020maPerfTelecomOutputClientPast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pm20020maPerfTelecomOutputClientPast24StatHistoryPort1Entry 6 }


pm20020maPerfTelecomOutputClientPast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pm20020maPerfTelecomOutputClientPast24StatHistoryPort1Entry 7 }


pm20020maPerfTelecomOutputClientPast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm20020maPerfTelecomOutputClientPast24StatHistoryPort1Entry 8 }


pm20020maPerfTelecomOutputClientPast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pm20020maPerfTelecomOutputClientPast24StatHistoryPort1Entry 9 }


pm20020maPerfTelecomOutputClientPast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pm20020maPerfTelecomOutputClientPast24StatHistoryPort1Entry 10 }


pm20020maPerfTelecomOutputClientPast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pm20020maPerfTelecomOutputClientPast24StatHistoryPort1Entry 11 }


--- *****************************************************
---     Leaf of the telecomLinePostFecCurrent15Stat
--- *****************************************************
--- *********************************************************
---     TABLE for the pm20020maPerfTelecomLinePostFecCurrent15Stat articles
--- *********************************************************

pm20020maPerfTelecomLinePostFecCurrent15StatTable OBJECT-TYPE
	SYNTAX  SEQUENCE OF Pm20020maPerfTelecomLinePostFecCurrent15StatEntry
	MAX-ACCESS not-accessible
	STATUS current
	DESCRIPTION
        "
        List of pm20020maPerfTelecomLinePostFecCurrent15Stat
        Article
        "
	::= { pm20020maMonPerfLine 336 }


pm20020maPerfTelecomLinePostFecCurrent15StatEntry OBJECT-TYPE
	SYNTAX Pm20020maPerfTelecomLinePostFecCurrent15StatEntry
	MAX-ACCESS not-accessible
	STATUS current
	DESCRIPTION
        "
        Row definition for the pm20020maPerfTelecomLinePostFecCurrent15Stat
        table
        "
	INDEX   { pm20020maPerfTelecomLinePostFecCurrent15StatIndex }
	::= { pm20020maPerfTelecomLinePostFecCurrent15StatTable 1 }


Pm20020maPerfTelecomLinePostFecCurrent15StatEntry ::=
	SEQUENCE {
	pm20020maPerfTelecomLinePostFecCurrent15StatIndex
		INTEGER,
	pm20020maPerfTelecomLinePostFecCurrent15StatInvCvPortn
		EkiOnOff,
	pm20020maPerfTelecomLinePostFecCurrent15StatCvValuePortn
		Unsigned32,
	pm20020maPerfTelecomLinePostFecCurrent15StatInvEsPortn
		EkiOnOff,
	pm20020maPerfTelecomLinePostFecCurrent15StatEsValuePortn
		Unsigned32,
	pm20020maPerfTelecomLinePostFecCurrent15StatInvSesPortn
		EkiOnOff,
	pm20020maPerfTelecomLinePostFecCurrent15StatSesValuePortn
		Unsigned32,
	pm20020maPerfTelecomLinePostFecCurrent15StatInvSefsPortn
		EkiOnOff,
	pm20020maPerfTelecomLinePostFecCurrent15StatSefsValuePortn
		Unsigned32,
	pm20020maPerfTelecomLinePostFecCurrent15StatInvUasPortn
		EkiOnOff,
	pm20020maPerfTelecomLinePostFecCurrent15StatUasValuePortn
		Unsigned32
	}


pm20020maPerfTelecomLinePostFecCurrent15StatIndex OBJECT-TYPE
	SYNTAX  INTEGER(0..128)
	MAX-ACCESS  read-only
	STATUS current
	DESCRIPTION
        "
        Index definition for the pm20020maPerfTelecomLinePostFecCurrent15Stat
        table
        "
	::= { pm20020maPerfTelecomLinePostFecCurrent15StatEntry 1 }


pm20020maPerfTelecomLinePostFecCurrent15StatInvCvPortn OBJECT-TYPE
	SYNTAX  EkiOnOff
	MAX-ACCESS read-only
	STATUS current
	DESCRIPTION
        "
        Current 15-min EBC counter inv.
        :This OID indicates that the current
        15-min Coding Violation counter
        is invalid
        "
	::= { pm20020maPerfTelecomLinePostFecCurrent15StatEntry 2 }


pm20020maPerfTelecomLinePostFecCurrent15StatCvValuePortn OBJECT-TYPE
	SYNTAX  Unsigned32
	MAX-ACCESS read-only
	STATUS current
	DESCRIPTION
        "
        Current 15-min EBC counter :This
        OID gives the current 15-min Coding
        Violation counter value
        "
	::= { pm20020maPerfTelecomLinePostFecCurrent15StatEntry 3 }


pm20020maPerfTelecomLinePostFecCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pm20020maPerfTelecomLinePostFecCurrent15StatEntry 4 }


pm20020maPerfTelecomLinePostFecCurrent15StatEsValuePortn OBJECT-TYPE
	SYNTAX  Unsigned32
	MAX-ACCESS read-only
	STATUS current
	DESCRIPTION
        "
        Current 15-min ES counter :This
        OID gives the current 15-min Errored
        Second counter value
        "
	::= { pm20020maPerfTelecomLinePostFecCurrent15StatEntry 5 }


pm20020maPerfTelecomLinePostFecCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pm20020maPerfTelecomLinePostFecCurrent15StatEntry 6 }


pm20020maPerfTelecomLinePostFecCurrent15StatSesValuePortn OBJECT-TYPE
	SYNTAX  Unsigned32
	MAX-ACCESS read-only
	STATUS current
	DESCRIPTION
        "
        Current 15-min SES counter :This
        OID gives the current 15-min severely
        Errored Second counter value
        "
	::= { pm20020maPerfTelecomLinePostFecCurrent15StatEntry 7 }


pm20020maPerfTelecomLinePostFecCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pm20020maPerfTelecomLinePostFecCurrent15StatEntry 8 }


pm20020maPerfTelecomLinePostFecCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pm20020maPerfTelecomLinePostFecCurrent15StatEntry 9 }


pm20020maPerfTelecomLinePostFecCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pm20020maPerfTelecomLinePostFecCurrent15StatEntry 10 }


pm20020maPerfTelecomLinePostFecCurrent15StatUasValuePortn OBJECT-TYPE
	SYNTAX  Unsigned32
	MAX-ACCESS read-only
	STATUS current
	DESCRIPTION
        "
        Current 15-min UAS counter :This
        OID gives the current 15-min UnAvailable
        Second counter value
        "
	::= { pm20020maPerfTelecomLinePostFecCurrent15StatEntry 11 }


--- *****************************************************
---     Leaf of the telecomLinePostFecPast15Stat
--- *****************************************************
--- *********************************************************
---     TABLE for the pm20020maPerfTelecomLinePostFecPast15StatHistory articles
--- *********************************************************

pm20020maPerfTelecomLinePostFecPast15StatHistoryPort1Table OBJECT-TYPE
	SYNTAX  SEQUENCE OF Pm20020maPerfTelecomLinePostFecPast15StatHistoryPort1Entry
	MAX-ACCESS not-accessible
	STATUS current
	DESCRIPTION
        "
        List of pm20020maPerfTelecomLinePostFecPast15StatHistory
        Article
        "
	::= { pm20020maMonPerfLine 337 }


pm20020maPerfTelecomLinePostFecPast15StatHistoryPort1Entry OBJECT-TYPE
	SYNTAX Pm20020maPerfTelecomLinePostFecPast15StatHistoryPort1Entry
	MAX-ACCESS not-accessible
	STATUS current
	DESCRIPTION
        "
        Row definition for the pm20020maPerfTelecomLinePostFecPast15StatHistory
        table
        "
	INDEX   { pm20020maPerfTelecomLinePostFecPast15StatHistoryPort1Index }
	::= { pm20020maPerfTelecomLinePostFecPast15StatHistoryPort1Table 1 }


Pm20020maPerfTelecomLinePostFecPast15StatHistoryPort1Entry ::=
	SEQUENCE {
	pm20020maPerfTelecomLinePostFecPast15StatHistoryPort1Index
		INTEGER,
	pm20020maPerfTelecomLinePostFecPast15StatHistoryInvCvPort1
		EkiOnOff,
	pm20020maPerfTelecomLinePostFecPast15StatHistoryCvValuePort1
		Unsigned32,
	pm20020maPerfTelecomLinePostFecPast15StatHistoryInvEsPort1
		EkiOnOff,
	pm20020maPerfTelecomLinePostFecPast15StatHistoryEsValuePort1
		Unsigned32,
	pm20020maPerfTelecomLinePostFecPast15StatHistoryInvSesPort1
		EkiOnOff,
	pm20020maPerfTelecomLinePostFecPast15StatHistorySesValuePort1
		Unsigned32,
	pm20020maPerfTelecomLinePostFecPast15StatHistoryInvSefsPort1
		EkiOnOff,
	pm20020maPerfTelecomLinePostFecPast15StatHistorySefsValuePort1
		Unsigned32,
	pm20020maPerfTelecomLinePostFecPast15StatHistoryInvUasPort1
		EkiOnOff,
	pm20020maPerfTelecomLinePostFecPast15StatHistoryUasValuePort1
		Unsigned32
	}


pm20020maPerfTelecomLinePostFecPast15StatHistoryPort1Index OBJECT-TYPE
	SYNTAX  INTEGER(0..128)
	MAX-ACCESS  read-only
	STATUS current
	DESCRIPTION
        "
        Index definition for the pm20020maPerfTelecomLinePostFecPast15StatHistory
        table
        "
	::= { pm20020maPerfTelecomLinePostFecPast15StatHistoryPort1Entry 1 }


pm20020maPerfTelecomLinePostFecPast15StatHistoryInvCvPort1 OBJECT-TYPE
	SYNTAX  EkiOnOff
	MAX-ACCESS read-only
	STATUS current
	DESCRIPTION
        "
        Previous 15-min EBC counter inv.
        :This OID indicates that the previous
        15-min Coding Violation counter
        is invalid
        "
	::= { pm20020maPerfTelecomLinePostFecPast15StatHistoryPort1Entry 2 }


pm20020maPerfTelecomLinePostFecPast15StatHistoryCvValuePort1 OBJECT-TYPE
	SYNTAX  Unsigned32
	MAX-ACCESS read-only
	STATUS current
	DESCRIPTION
        "
        Previous 15-min EBC counter :This
        OID gives the previous 15-min Coding
        Violation counter value
        "
	::= { pm20020maPerfTelecomLinePostFecPast15StatHistoryPort1Entry 3 }


pm20020maPerfTelecomLinePostFecPast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pm20020maPerfTelecomLinePostFecPast15StatHistoryPort1Entry 4 }


pm20020maPerfTelecomLinePostFecPast15StatHistoryEsValuePort1 OBJECT-TYPE
	SYNTAX  Unsigned32
	MAX-ACCESS read-only
	STATUS current
	DESCRIPTION
        "
        Previous 15-min ES counter :This
        OID gives the previous 15-min Errored
        Second counter value
        "
	::= { pm20020maPerfTelecomLinePostFecPast15StatHistoryPort1Entry 5 }


pm20020maPerfTelecomLinePostFecPast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pm20020maPerfTelecomLinePostFecPast15StatHistoryPort1Entry 6 }


pm20020maPerfTelecomLinePostFecPast15StatHistorySesValuePort1 OBJECT-TYPE
	SYNTAX  Unsigned32
	MAX-ACCESS read-only
	STATUS current
	DESCRIPTION
        "
        Previous 15-min SES counter :This
        OID gives the previous 15-min severely
        Errored Second counter value
        "
	::= { pm20020maPerfTelecomLinePostFecPast15StatHistoryPort1Entry 7 }


pm20020maPerfTelecomLinePostFecPast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pm20020maPerfTelecomLinePostFecPast15StatHistoryPort1Entry 8 }


pm20020maPerfTelecomLinePostFecPast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pm20020maPerfTelecomLinePostFecPast15StatHistoryPort1Entry 9 }


pm20020maPerfTelecomLinePostFecPast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pm20020maPerfTelecomLinePostFecPast15StatHistoryPort1Entry 10 }


pm20020maPerfTelecomLinePostFecPast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pm20020maPerfTelecomLinePostFecPast15StatHistoryPort1Entry 11 }


--- *****************************************************
---     Leaf of the telecomLinePostFecCurrent24Stat
--- *****************************************************
--- *********************************************************
---     TABLE for the pm20020maPerfTelecomLinePostFecCurrent24Stat articles
--- *********************************************************

pm20020maPerfTelecomLinePostFecCurrent24StatTable OBJECT-TYPE
	SYNTAX  SEQUENCE OF Pm20020maPerfTelecomLinePostFecCurrent24StatEntry
	MAX-ACCESS not-accessible
	STATUS current
	DESCRIPTION
        "
        List of pm20020maPerfTelecomLinePostFecCurrent24Stat
        Article
        "
	::= { pm20020maMonPerfLine 338 }


pm20020maPerfTelecomLinePostFecCurrent24StatEntry OBJECT-TYPE
	SYNTAX Pm20020maPerfTelecomLinePostFecCurrent24StatEntry
	MAX-ACCESS not-accessible
	STATUS current
	DESCRIPTION
        "
        Row definition for the pm20020maPerfTelecomLinePostFecCurrent24Stat
        table
        "
	INDEX   { pm20020maPerfTelecomLinePostFecCurrent24StatIndex }
	::= { pm20020maPerfTelecomLinePostFecCurrent24StatTable 1 }


Pm20020maPerfTelecomLinePostFecCurrent24StatEntry ::=
	SEQUENCE {
	pm20020maPerfTelecomLinePostFecCurrent24StatIndex
		INTEGER,
	pm20020maPerfTelecomLinePostFecCurrent24StatInvCvPortn
		EkiOnOff,
	pm20020maPerfTelecomLinePostFecCurrent24StatCvValuePortn
		Unsigned32,
	pm20020maPerfTelecomLinePostFecCurrent24StatInvEsPortn
		EkiOnOff,
	pm20020maPerfTelecomLinePostFecCurrent24StatEsValuePortn
		Unsigned32,
	pm20020maPerfTelecomLinePostFecCurrent24StatInvSesPortn
		EkiOnOff,
	pm20020maPerfTelecomLinePostFecCurrent24StatSesValuePortn
		Unsigned32,
	pm20020maPerfTelecomLinePostFecCurrent24StatInvSefsPortn
		EkiOnOff,
	pm20020maPerfTelecomLinePostFecCurrent24StatSefsValuePortn
		Unsigned32,
	pm20020maPerfTelecomLinePostFecCurrent24StatInvUasPortn
		EkiOnOff,
	pm20020maPerfTelecomLinePostFecCurrent24StatUasValuePortn
		Unsigned32
	}


pm20020maPerfTelecomLinePostFecCurrent24StatIndex OBJECT-TYPE
	SYNTAX  INTEGER(0..128)
	MAX-ACCESS  read-only
	STATUS current
	DESCRIPTION
        "
        Index definition for the pm20020maPerfTelecomLinePostFecCurrent24Stat
        table
        "
	::= { pm20020maPerfTelecomLinePostFecCurrent24StatEntry 1 }


pm20020maPerfTelecomLinePostFecCurrent24StatInvCvPortn OBJECT-TYPE
	SYNTAX  EkiOnOff
	MAX-ACCESS read-only
	STATUS current
	DESCRIPTION
        "
        Current 24-hours EBC counter inv.
        :This OID indicates that the current
        24-hours Coding Violation counter
        is invalid
        "
	::= { pm20020maPerfTelecomLinePostFecCurrent24StatEntry 2 }


pm20020maPerfTelecomLinePostFecCurrent24StatCvValuePortn OBJECT-TYPE
	SYNTAX  Unsigned32
	MAX-ACCESS read-only
	STATUS current
	DESCRIPTION
        "
        Current 24-hours EBC counter :This
        OID gives the current 24-hours
         Coding Violation counter value
        "
	::= { pm20020maPerfTelecomLinePostFecCurrent24StatEntry 3 }


pm20020maPerfTelecomLinePostFecCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pm20020maPerfTelecomLinePostFecCurrent24StatEntry 4 }


pm20020maPerfTelecomLinePostFecCurrent24StatEsValuePortn OBJECT-TYPE
	SYNTAX  Unsigned32
	MAX-ACCESS read-only
	STATUS current
	DESCRIPTION
        "
        Current 24-hours ES counter :This
        OID gives the current 24-hours
         Errored Second counter value
        "
	::= { pm20020maPerfTelecomLinePostFecCurrent24StatEntry 5 }


pm20020maPerfTelecomLinePostFecCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pm20020maPerfTelecomLinePostFecCurrent24StatEntry 6 }


pm20020maPerfTelecomLinePostFecCurrent24StatSesValuePortn OBJECT-TYPE
	SYNTAX  Unsigned32
	MAX-ACCESS read-only
	STATUS current
	DESCRIPTION
        "
        Current 24-hours SES counter :This
        OID gives the current 24-hours
         severely Errored Second counter
        value
        "
	::= { pm20020maPerfTelecomLinePostFecCurrent24StatEntry 7 }


pm20020maPerfTelecomLinePostFecCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pm20020maPerfTelecomLinePostFecCurrent24StatEntry 8 }


pm20020maPerfTelecomLinePostFecCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pm20020maPerfTelecomLinePostFecCurrent24StatEntry 9 }


pm20020maPerfTelecomLinePostFecCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pm20020maPerfTelecomLinePostFecCurrent24StatEntry 10 }


pm20020maPerfTelecomLinePostFecCurrent24StatUasValuePortn OBJECT-TYPE
	SYNTAX  Unsigned32
	MAX-ACCESS read-only
	STATUS current
	DESCRIPTION
        "
        Current 24-hours UAS counter :This
        OID gives the current 24-hours
         UnAvailable Second counter value
        "
	::= { pm20020maPerfTelecomLinePostFecCurrent24StatEntry 11 }


--- *****************************************************
---     Leaf of the telecomLinePostFecPast24Stat
--- *****************************************************
--- *********************************************************
---     TABLE for the pm20020maPerfTelecomLinePostFecPast24StatHistory articles
--- *********************************************************

pm20020maPerfTelecomLinePostFecPast24StatHistoryPort1Table OBJECT-TYPE
	SYNTAX  SEQUENCE OF Pm20020maPerfTelecomLinePostFecPast24StatHistoryPort1Entry
	MAX-ACCESS not-accessible
	STATUS current
	DESCRIPTION
        "
        List of pm20020maPerfTelecomLinePostFecPast24StatHistory
        Article
        "
	::= { pm20020maMonPerfLine 339 }


pm20020maPerfTelecomLinePostFecPast24StatHistoryPort1Entry OBJECT-TYPE
	SYNTAX Pm20020maPerfTelecomLinePostFecPast24StatHistoryPort1Entry
	MAX-ACCESS not-accessible
	STATUS current
	DESCRIPTION
        "
        Row definition for the pm20020maPerfTelecomLinePostFecPast24StatHistory
        table
        "
	INDEX   { pm20020maPerfTelecomLinePostFecPast24StatHistoryPort1Index }
	::= { pm20020maPerfTelecomLinePostFecPast24StatHistoryPort1Table 1 }


Pm20020maPerfTelecomLinePostFecPast24StatHistoryPort1Entry ::=
	SEQUENCE {
	pm20020maPerfTelecomLinePostFecPast24StatHistoryPort1Index
		INTEGER,
	pm20020maPerfTelecomLinePostFecPast24StatHistoryInvCvPort1
		EkiOnOff,
	pm20020maPerfTelecomLinePostFecPast24StatHistoryCvValuePort1
		Unsigned32,
	pm20020maPerfTelecomLinePostFecPast24StatHistoryInvEsPort1
		EkiOnOff,
	pm20020maPerfTelecomLinePostFecPast24StatHistoryEsValuePort1
		Unsigned32,
	pm20020maPerfTelecomLinePostFecPast24StatHistoryInvSesPort1
		EkiOnOff,
	pm20020maPerfTelecomLinePostFecPast24StatHistorySesValuePort1
		Unsigned32,
	pm20020maPerfTelecomLinePostFecPast24StatHistoryInvSefsPort1
		EkiOnOff,
	pm20020maPerfTelecomLinePostFecPast24StatHistorySefsValuePort1
		Unsigned32,
	pm20020maPerfTelecomLinePostFecPast24StatHistoryInvUasPort1
		EkiOnOff,
	pm20020maPerfTelecomLinePostFecPast24StatHistoryUasValuePort1
		Unsigned32
	}


pm20020maPerfTelecomLinePostFecPast24StatHistoryPort1Index OBJECT-TYPE
	SYNTAX  INTEGER(0..128)
	MAX-ACCESS  read-only
	STATUS current
	DESCRIPTION
        "
        Index definition for the pm20020maPerfTelecomLinePostFecPast24StatHistory
        table
        "
	::= { pm20020maPerfTelecomLinePostFecPast24StatHistoryPort1Entry 1 }


pm20020maPerfTelecomLinePostFecPast24StatHistoryInvCvPort1 OBJECT-TYPE
	SYNTAX  EkiOnOff
	MAX-ACCESS read-only
	STATUS current
	DESCRIPTION
        "
        Previous 24-hours EBC counter
         inv. :This OID indicates that
         the previous 24-hours Coding Violation
        counter is invalid
        "
	::= { pm20020maPerfTelecomLinePostFecPast24StatHistoryPort1Entry 2 }


pm20020maPerfTelecomLinePostFecPast24StatHistoryCvValuePort1 OBJECT-TYPE
	SYNTAX  Unsigned32
	MAX-ACCESS read-only
	STATUS current
	DESCRIPTION
        "
        Previous 24-hours EBC counter
         :This OID gives the previous 24-hours
        Coding Violation counter value
        "
	::= { pm20020maPerfTelecomLinePostFecPast24StatHistoryPort1Entry 3 }


pm20020maPerfTelecomLinePostFecPast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pm20020maPerfTelecomLinePostFecPast24StatHistoryPort1Entry 4 }


pm20020maPerfTelecomLinePostFecPast24StatHistoryEsValuePort1 OBJECT-TYPE
	SYNTAX  Unsigned32
	MAX-ACCESS read-only
	STATUS current
	DESCRIPTION
        "
        Previous 24-hours ES counter :This
        OID gives the previous 24-hours
        Errored Second counter value
        "
	::= { pm20020maPerfTelecomLinePostFecPast24StatHistoryPort1Entry 5 }


pm20020maPerfTelecomLinePostFecPast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pm20020maPerfTelecomLinePostFecPast24StatHistoryPort1Entry 6 }


pm20020maPerfTelecomLinePostFecPast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pm20020maPerfTelecomLinePostFecPast24StatHistoryPort1Entry 7 }


pm20020maPerfTelecomLinePostFecPast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm20020maPerfTelecomLinePostFecPast24StatHistoryPort1Entry 8 }


pm20020maPerfTelecomLinePostFecPast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pm20020maPerfTelecomLinePostFecPast24StatHistoryPort1Entry 9 }


pm20020maPerfTelecomLinePostFecPast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pm20020maPerfTelecomLinePostFecPast24StatHistoryPort1Entry 10 }


pm20020maPerfTelecomLinePostFecPast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pm20020maPerfTelecomLinePostFecPast24StatHistoryPort1Entry 11 }


--- *****************************************************
---     Leaf of the telecomBerLinePreFecCurrent15Stat
--- *****************************************************
--- *********************************************************
---     TABLE for the pm20020maPerfTelecomBerLinePreFecCurrent15Stat articles
--- *********************************************************

pm20020maPerfTelecomBerLinePreFecCurrent15StatTable OBJECT-TYPE
	SYNTAX  SEQUENCE OF Pm20020maPerfTelecomBerLinePreFecCurrent15StatEntry
	MAX-ACCESS not-accessible
	STATUS current
	DESCRIPTION
        "
        List of pm20020maPerfTelecomBerLinePreFecCurrent15Stat
        Article
        "
	::= { pm20020maMonPerfLine 352 }


pm20020maPerfTelecomBerLinePreFecCurrent15StatEntry OBJECT-TYPE
	SYNTAX Pm20020maPerfTelecomBerLinePreFecCurrent15StatEntry
	MAX-ACCESS not-accessible
	STATUS current
	DESCRIPTION
        "
        Row definition for the pm20020maPerfTelecomBerLinePreFecCurrent15Stat
        table
        "
	INDEX   { pm20020maPerfTelecomBerLinePreFecCurrent15StatIndex }
	::= { pm20020maPerfTelecomBerLinePreFecCurrent15StatTable 1 }


Pm20020maPerfTelecomBerLinePreFecCurrent15StatEntry ::=
	SEQUENCE {
	pm20020maPerfTelecomBerLinePreFecCurrent15StatIndex
		INTEGER,
	pm20020maPerfTelecomBerLinePreFecCurrent15StatInvBerPortn
		EkiOnOff,
	pm20020maPerfTelecomBerLinePreFecCurrent15StatBerValuePortn
		Unsigned32,
	pm20020maPerfTelecomBerLinePreFecCurrent15StatInvMinBerPortn
		EkiOnOff,
	pm20020maPerfTelecomBerLinePreFecCurrent15StatMinBerValuePortn
		Unsigned32,
	pm20020maPerfTelecomBerLinePreFecCurrent15StatInvMaxBerPortn
		EkiOnOff,
	pm20020maPerfTelecomBerLinePreFecCurrent15StatMaxBerValuePortn
		Unsigned32
	}


pm20020maPerfTelecomBerLinePreFecCurrent15StatIndex OBJECT-TYPE
	SYNTAX  INTEGER(0..128)
	MAX-ACCESS  read-only
	STATUS current
	DESCRIPTION
        "
        Index definition for the pm20020maPerfTelecomBerLinePreFecCurrent15Stat
        table
        "
	::= { pm20020maPerfTelecomBerLinePreFecCurrent15StatEntry 1 }


pm20020maPerfTelecomBerLinePreFecCurrent15StatInvBerPortn OBJECT-TYPE
	SYNTAX  EkiOnOff
	MAX-ACCESS read-only
	STATUS current
	DESCRIPTION
        "
        Current 15-min BER counter inv.
        :This OID indicates that the current
        15-min Coding Violation counter
        is invalid
        "
	::= { pm20020maPerfTelecomBerLinePreFecCurrent15StatEntry 2 }


pm20020maPerfTelecomBerLinePreFecCurrent15StatBerValuePortn OBJECT-TYPE
	SYNTAX  Unsigned32
	MAX-ACCESS read-only
	STATUS current
	DESCRIPTION
        "
        Current 15-min BER counter :This
        OID gives the current 15-min Coding
        Violation counter value
        "
	::= { pm20020maPerfTelecomBerLinePreFecCurrent15StatEntry 3 }


pm20020maPerfTelecomBerLinePreFecCurrent15StatInvMinBerPortn OBJECT-TYPE
	SYNTAX  EkiOnOff
	MAX-ACCESS read-only
	STATUS current
	DESCRIPTION
        "
        Current 15-min MinBER counter
         inv. :This OID indicates that
         the current 15-min Errored Second
        counter is invalid
        "
	::= { pm20020maPerfTelecomBerLinePreFecCurrent15StatEntry 4 }


pm20020maPerfTelecomBerLinePreFecCurrent15StatMinBerValuePortn OBJECT-TYPE
	SYNTAX  Unsigned32
	MAX-ACCESS read-only
	STATUS current
	DESCRIPTION
        "
        Current 15-min MinBER counter
         :This OID gives the current 15-min
        Errored Second counter value
        "
	::= { pm20020maPerfTelecomBerLinePreFecCurrent15StatEntry 5 }


pm20020maPerfTelecomBerLinePreFecCurrent15StatInvMaxBerPortn OBJECT-TYPE
	SYNTAX  EkiOnOff
	MAX-ACCESS read-only
	STATUS current
	DESCRIPTION
        "
        Current 15-min MaxBER counter
         inv. :This OID indicates that
         the current 15-min severely Errored
        Second counter is invalid
        "
	::= { pm20020maPerfTelecomBerLinePreFecCurrent15StatEntry 6 }


pm20020maPerfTelecomBerLinePreFecCurrent15StatMaxBerValuePortn OBJECT-TYPE
	SYNTAX  Unsigned32
	MAX-ACCESS read-only
	STATUS current
	DESCRIPTION
        "
        Current 15-min MaxBER counter
         :This OID gives the current 15-min
        severely Errored Second counter
        value
        "
	::= { pm20020maPerfTelecomBerLinePreFecCurrent15StatEntry 7 }


--- *****************************************************
---     Leaf of the telecomBerLinePreFecPast15Stat
--- *****************************************************
--- *********************************************************
---     TABLE for the pm20020maPerfTelecomBerLinePreFecPast15StatHistory articles
--- *********************************************************

pm20020maPerfTelecomBerLinePreFecPast15StatHistoryPort1Table OBJECT-TYPE
	SYNTAX  SEQUENCE OF Pm20020maPerfTelecomBerLinePreFecPast15StatHistoryPort1Entry
	MAX-ACCESS not-accessible
	STATUS current
	DESCRIPTION
        "
        List of pm20020maPerfTelecomBerLinePreFecPast15StatHistory
        Article
        "
	::= { pm20020maMonPerfLine 353 }


pm20020maPerfTelecomBerLinePreFecPast15StatHistoryPort1Entry OBJECT-TYPE
	SYNTAX Pm20020maPerfTelecomBerLinePreFecPast15StatHistoryPort1Entry
	MAX-ACCESS not-accessible
	STATUS current
	DESCRIPTION
        "
        Row definition for the pm20020maPerfTelecomBerLinePreFecPast15StatHistory
        table
        "
	INDEX   { pm20020maPerfTelecomBerLinePreFecPast15StatHistoryPort1Index }
	::= { pm20020maPerfTelecomBerLinePreFecPast15StatHistoryPort1Table 1 }


Pm20020maPerfTelecomBerLinePreFecPast15StatHistoryPort1Entry ::=
	SEQUENCE {
	pm20020maPerfTelecomBerLinePreFecPast15StatHistoryPort1Index
		INTEGER,
	pm20020maPerfTelecomBerLinePreFecPast15StatHistoryInvBerPort1
		EkiOnOff,
	pm20020maPerfTelecomBerLinePreFecPast15StatHistoryBerValuePort1
		Unsigned32,
	pm20020maPerfTelecomBerLinePreFecPast15StatHistoryInvMinBerPort1
		EkiOnOff,
	pm20020maPerfTelecomBerLinePreFecPast15StatHistoryMinBerValuePort1
		Unsigned32,
	pm20020maPerfTelecomBerLinePreFecPast15StatHistoryInvMaxBerPort1
		EkiOnOff,
	pm20020maPerfTelecomBerLinePreFecPast15StatHistoryMaxBerValuePort1
		Unsigned32
	}


pm20020maPerfTelecomBerLinePreFecPast15StatHistoryPort1Index OBJECT-TYPE
	SYNTAX  INTEGER(0..128)
	MAX-ACCESS  read-only
	STATUS current
	DESCRIPTION
        "
        Index definition for the pm20020maPerfTelecomBerLinePreFecPast15StatHistory
        table
        "
	::= { pm20020maPerfTelecomBerLinePreFecPast15StatHistoryPort1Entry 1 }


pm20020maPerfTelecomBerLinePreFecPast15StatHistoryInvBerPort1 OBJECT-TYPE
	SYNTAX  EkiOnOff
	MAX-ACCESS read-only
	STATUS current
	DESCRIPTION
        "
        Previous 15-min BER counter inv.
        :This OID indicates that the previous
        15-min Coding Violation counter
        is invalid
        "
	::= { pm20020maPerfTelecomBerLinePreFecPast15StatHistoryPort1Entry 2 }


pm20020maPerfTelecomBerLinePreFecPast15StatHistoryBerValuePort1 OBJECT-TYPE
	SYNTAX  Unsigned32
	MAX-ACCESS read-only
	STATUS current
	DESCRIPTION
        "
        Previous 15-min BER counter :This
        OID gives the previous 15-min Coding
        Violation counter value
        "
	::= { pm20020maPerfTelecomBerLinePreFecPast15StatHistoryPort1Entry 3 }


pm20020maPerfTelecomBerLinePreFecPast15StatHistoryInvMinBerPort1 OBJECT-TYPE
	SYNTAX  EkiOnOff
	MAX-ACCESS read-only
	STATUS current
	DESCRIPTION
        "
        Previous 15-min MinBER counter
        inv. :This OID indicates that the
        previous 15-min Errored Second
         counter is invalid
        "
	::= { pm20020maPerfTelecomBerLinePreFecPast15StatHistoryPort1Entry 4 }


pm20020maPerfTelecomBerLinePreFecPast15StatHistoryMinBerValuePort1 OBJECT-TYPE
	SYNTAX  Unsigned32
	MAX-ACCESS read-only
	STATUS current
	DESCRIPTION
        "
        Previous 15-min MinBER counter
        :This OID gives the previous 15-min
        Errored Second counter value
        "
	::= { pm20020maPerfTelecomBerLinePreFecPast15StatHistoryPort1Entry 5 }


pm20020maPerfTelecomBerLinePreFecPast15StatHistoryInvMaxBerPort1 OBJECT-TYPE
	SYNTAX  EkiOnOff
	MAX-ACCESS read-only
	STATUS current
	DESCRIPTION
        "
        Previous 15-min MaxBER counter
        inv. :This OID indicates that the
        previous 15-min severely Errored
        Second counter is invalid
        "
	::= { pm20020maPerfTelecomBerLinePreFecPast15StatHistoryPort1Entry 6 }


pm20020maPerfTelecomBerLinePreFecPast15StatHistoryMaxBerValuePort1 OBJECT-TYPE
	SYNTAX  Unsigned32
	MAX-ACCESS read-only
	STATUS current
	DESCRIPTION
        "
        Previous 15-min MaxBER counter
        :This OID gives the previous 15-min
        severely Errored Second counter
        value
        "
	::= { pm20020maPerfTelecomBerLinePreFecPast15StatHistoryPort1Entry 7 }


--- *****************************************************
---     Leaf of the telecomBerLinePreFecCurrent24Stat
--- *****************************************************
--- *********************************************************
---     TABLE for the pm20020maPerfTelecomBerLinePreFecCurrent24Stat articles
--- *********************************************************

pm20020maPerfTelecomBerLinePreFecCurrent24StatTable OBJECT-TYPE
	SYNTAX  SEQUENCE OF Pm20020maPerfTelecomBerLinePreFecCurrent24StatEntry
	MAX-ACCESS not-accessible
	STATUS current
	DESCRIPTION
        "
        List of pm20020maPerfTelecomBerLinePreFecCurrent24Stat
        Article
        "
	::= { pm20020maMonPerfLine 354 }


pm20020maPerfTelecomBerLinePreFecCurrent24StatEntry OBJECT-TYPE
	SYNTAX Pm20020maPerfTelecomBerLinePreFecCurrent24StatEntry
	MAX-ACCESS not-accessible
	STATUS current
	DESCRIPTION
        "
        Row definition for the pm20020maPerfTelecomBerLinePreFecCurrent24Stat
        table
        "
	INDEX   { pm20020maPerfTelecomBerLinePreFecCurrent24StatIndex }
	::= { pm20020maPerfTelecomBerLinePreFecCurrent24StatTable 1 }


Pm20020maPerfTelecomBerLinePreFecCurrent24StatEntry ::=
	SEQUENCE {
	pm20020maPerfTelecomBerLinePreFecCurrent24StatIndex
		INTEGER,
	pm20020maPerfTelecomBerLinePreFecCurrent24StatInvBerPortn
		EkiOnOff,
	pm20020maPerfTelecomBerLinePreFecCurrent24StatBerValuePortn
		Unsigned32,
	pm20020maPerfTelecomBerLinePreFecCurrent24StatInvMinBerPortn
		EkiOnOff,
	pm20020maPerfTelecomBerLinePreFecCurrent24StatMinBerValuePortn
		Unsigned32,
	pm20020maPerfTelecomBerLinePreFecCurrent24StatInvMaxBerPortn
		EkiOnOff,
	pm20020maPerfTelecomBerLinePreFecCurrent24StatMaxBerValuePortn
		Unsigned32
	}


pm20020maPerfTelecomBerLinePreFecCurrent24StatIndex OBJECT-TYPE
	SYNTAX  INTEGER(0..128)
	MAX-ACCESS  read-only
	STATUS current
	DESCRIPTION
        "
        Index definition for the pm20020maPerfTelecomBerLinePreFecCurrent24Stat
        table
        "
	::= { pm20020maPerfTelecomBerLinePreFecCurrent24StatEntry 1 }


pm20020maPerfTelecomBerLinePreFecCurrent24StatInvBerPortn OBJECT-TYPE
	SYNTAX  EkiOnOff
	MAX-ACCESS read-only
	STATUS current
	DESCRIPTION
        "
        Current 24-hours BER counter inv.
        :This OID indicates that the current
        24-hours Coding Violation counter
        is invalid
        "
	::= { pm20020maPerfTelecomBerLinePreFecCurrent24StatEntry 2 }


pm20020maPerfTelecomBerLinePreFecCurrent24StatBerValuePortn OBJECT-TYPE
	SYNTAX  Unsigned32
	MAX-ACCESS read-only
	STATUS current
	DESCRIPTION
        "
        Current 24-hours BER counter :This
        OID gives the current 24-hours
         Coding Violation counter value
        "
	::= { pm20020maPerfTelecomBerLinePreFecCurrent24StatEntry 3 }


pm20020maPerfTelecomBerLinePreFecCurrent24StatInvMinBerPortn OBJECT-TYPE
	SYNTAX  EkiOnOff
	MAX-ACCESS read-only
	STATUS current
	DESCRIPTION
        "
        Current 24-hoursMinBER counter
        inv. :This OID indicates that the
        current 24-hours Errored Second
        counter is invalid
        "
	::= { pm20020maPerfTelecomBerLinePreFecCurrent24StatEntry 4 }


pm20020maPerfTelecomBerLinePreFecCurrent24StatMinBerValuePortn OBJECT-TYPE
	SYNTAX  Unsigned32
	MAX-ACCESS read-only
	STATUS current
	DESCRIPTION
        "
        Current 24-hours MinBER counter
        :This OID gives the current 24-hours
        Errored Second counter value
        "
	::= { pm20020maPerfTelecomBerLinePreFecCurrent24StatEntry 5 }


pm20020maPerfTelecomBerLinePreFecCurrent24StatInvMaxBerPortn OBJECT-TYPE
	SYNTAX  EkiOnOff
	MAX-ACCESS read-only
	STATUS current
	DESCRIPTION
        "
        Current 24-hours MaxBER counter
        inv. :This OID indicates that the
        current 24-hours severely Errored
        Second counter is invalid
        "
	::= { pm20020maPerfTelecomBerLinePreFecCurrent24StatEntry 6 }


pm20020maPerfTelecomBerLinePreFecCurrent24StatMaxBerValuePortn OBJECT-TYPE
	SYNTAX  Unsigned32
	MAX-ACCESS read-only
	STATUS current
	DESCRIPTION
        "
        Current 24-hours MaxBER counter
        :This OID gives the current 24-hours
        severely Errored Second counter
        value
        "
	::= { pm20020maPerfTelecomBerLinePreFecCurrent24StatEntry 7 }


--- *****************************************************
---     Leaf of the telecomBerLinePreFecPast24Stat
--- *****************************************************
--- *********************************************************
---     TABLE for the pm20020maPerfTelecomBerLinePreFecPast24StatHistory articles
--- *********************************************************

pm20020maPerfTelecomBerLinePreFecPast24StatHistoryPort1Table OBJECT-TYPE
	SYNTAX  SEQUENCE OF Pm20020maPerfTelecomBerLinePreFecPast24StatHistoryPort1Entry
	MAX-ACCESS not-accessible
	STATUS current
	DESCRIPTION
        "
        List of pm20020maPerfTelecomBerLinePreFecPast24StatHistory
        Article
        "
	::= { pm20020maMonPerfLine 355 }


pm20020maPerfTelecomBerLinePreFecPast24StatHistoryPort1Entry OBJECT-TYPE
	SYNTAX Pm20020maPerfTelecomBerLinePreFecPast24StatHistoryPort1Entry
	MAX-ACCESS not-accessible
	STATUS current
	DESCRIPTION
        "
        Row definition for the pm20020maPerfTelecomBerLinePreFecPast24StatHistory
        table
        "
	INDEX   { pm20020maPerfTelecomBerLinePreFecPast24StatHistoryPort1Index }
	::= { pm20020maPerfTelecomBerLinePreFecPast24StatHistoryPort1Table 1 }


Pm20020maPerfTelecomBerLinePreFecPast24StatHistoryPort1Entry ::=
	SEQUENCE {
	pm20020maPerfTelecomBerLinePreFecPast24StatHistoryPort1Index
		INTEGER,
	pm20020maPerfTelecomBerLinePreFecPast24StatHistoryInvBerPort1
		EkiOnOff,
	pm20020maPerfTelecomBerLinePreFecPast24StatHistoryBerValuePort1
		Unsigned32,
	pm20020maPerfTelecomBerLinePreFecPast24StatHistoryInvMinBerPort1
		EkiOnOff,
	pm20020maPerfTelecomBerLinePreFecPast24StatHistoryMinBerValuePort1
		Unsigned32,
	pm20020maPerfTelecomBerLinePreFecPast24StatHistoryInvMaxBerPort1
		EkiOnOff,
	pm20020maPerfTelecomBerLinePreFecPast24StatHistoryMaxBerValuePort1
		Unsigned32
	}


pm20020maPerfTelecomBerLinePreFecPast24StatHistoryPort1Index OBJECT-TYPE
	SYNTAX  INTEGER(0..128)
	MAX-ACCESS  read-only
	STATUS current
	DESCRIPTION
        "
        Index definition for the pm20020maPerfTelecomBerLinePreFecPast24StatHistory
        table
        "
	::= { pm20020maPerfTelecomBerLinePreFecPast24StatHistoryPort1Entry 1 }


pm20020maPerfTelecomBerLinePreFecPast24StatHistoryInvBerPort1 OBJECT-TYPE
	SYNTAX  EkiOnOff
	MAX-ACCESS read-only
	STATUS current
	DESCRIPTION
        "
        Previous 24-hours BER counter
         inv. :This OID indicates that
         the previous 24-hours Coding Violation
        counter is invalid
        "
	::= { pm20020maPerfTelecomBerLinePreFecPast24StatHistoryPort1Entry 2 }


pm20020maPerfTelecomBerLinePreFecPast24StatHistoryBerValuePort1 OBJECT-TYPE
	SYNTAX  Unsigned32
	MAX-ACCESS read-only
	STATUS current
	DESCRIPTION
        "
        Previous 24-hours BER counter
         :This OID gives the previous 24-hours
        Coding Violation counter value
        "
	::= { pm20020maPerfTelecomBerLinePreFecPast24StatHistoryPort1Entry 3 }


pm20020maPerfTelecomBerLinePreFecPast24StatHistoryInvMinBerPort1 OBJECT-TYPE
	SYNTAX  EkiOnOff
	MAX-ACCESS read-only
	STATUS current
	DESCRIPTION
        "
        Previous 24-hours MinBER counter
        inv. :This OID indicates that the
        previous 24-hours Errored Second
        counter is invalid
        "
	::= { pm20020maPerfTelecomBerLinePreFecPast24StatHistoryPort1Entry 4 }


pm20020maPerfTelecomBerLinePreFecPast24StatHistoryMinBerValuePort1 OBJECT-TYPE
	SYNTAX  Unsigned32
	MAX-ACCESS read-only
	STATUS current
	DESCRIPTION
        "
        Previous 24-hours MinBER counter
        :This OID gives the previous 24-hours
        Errored Second counter value
        "
	::= { pm20020maPerfTelecomBerLinePreFecPast24StatHistoryPort1Entry 5 }


pm20020maPerfTelecomBerLinePreFecPast24StatHistoryInvMaxBerPort1 OBJECT-TYPE
	SYNTAX  EkiOnOff
	MAX-ACCESS read-only
	STATUS current
	DESCRIPTION
        "
        Previous 24-hours MaxBER counter
        inv. :This OID indicates that the
        previous 24-hours severely Errored
        Second counter is invalid
        "
	::= { pm20020maPerfTelecomBerLinePreFecPast24StatHistoryPort1Entry 6 }


pm20020maPerfTelecomBerLinePreFecPast24StatHistoryMaxBerValuePort1 OBJECT-TYPE
	SYNTAX  Unsigned32
	MAX-ACCESS read-only
	STATUS current
	DESCRIPTION
        "
        Previous 24-hours MaxBER counter
        :This OID gives the previous 24-hours
        severely Errored Second counter
        value
        "
	::= { pm20020maPerfTelecomBerLinePreFecPast24StatHistoryPort1Entry 7 }


--- *****************************************************
---     Leaf of the datacomClientCurrent15Stat
--- *****************************************************
--- *********************************************************
---     TABLE for the pm20020maPerfDatacomClientCurrent15Stat articles
--- *********************************************************

pm20020maPerfDatacomClientCurrent15StatTable OBJECT-TYPE
	SYNTAX  SEQUENCE OF Pm20020maPerfDatacomClientCurrent15StatEntry
	MAX-ACCESS not-accessible
	STATUS current
	DESCRIPTION
        "
        List of pm20020maPerfDatacomClientCurrent15Stat
        Article
        "
	::= { pm20020maMonPerfClient 848 }


pm20020maPerfDatacomClientCurrent15StatEntry OBJECT-TYPE
	SYNTAX Pm20020maPerfDatacomClientCurrent15StatEntry
	MAX-ACCESS not-accessible
	STATUS current
	DESCRIPTION
        "
        Row definition for the pm20020maPerfDatacomClientCurrent15Stat
        table
        "
	INDEX   { pm20020maPerfDatacomClientCurrent15StatIndex }
	::= { pm20020maPerfDatacomClientCurrent15StatTable 1 }


Pm20020maPerfDatacomClientCurrent15StatEntry ::=
	SEQUENCE {
	pm20020maPerfDatacomClientCurrent15StatIndex
		INTEGER,
	pm20020maperfdatacomclientCurrent15StatOutPacketCountInvPortn
		EkiOnOff,
	pm20020maperfdatacomclientCurrent15StatOutPacketCountPortn
		Counter64,
	pm20020maperfdatacomclientCurrent15StatOutCrcCountInvPortn
		EkiOnOff,
	pm20020maperfdatacomclientCurrent15StatOutCrcCountPortn
		Counter64,
	pm20020maperfdatacomclientCurrent15StatInPacketCountInvPortn
		EkiOnOff,
	pm20020maperfdatacomclientCurrent15StatInPacketCountPortn
		Counter64,
	pm20020maperfdatacomclientCurrent15StatInCrcCountInvPortn
		EkiOnOff,
	pm20020maperfdatacomclientCurrent15StatInCrcCountPortn
		Counter64
	}


pm20020maPerfDatacomClientCurrent15StatIndex OBJECT-TYPE
	SYNTAX  INTEGER(0..128)
	MAX-ACCESS  read-only
	STATUS current
	DESCRIPTION
        "
        Index definition for the pm20020maPerfDatacomClientCurrent15Stat
        table
        "
	::= { pm20020maPerfDatacomClientCurrent15StatEntry 1 }


pm20020maperfdatacomclientCurrent15StatOutPacketCountInvPortn OBJECT-TYPE
	SYNTAX  EkiOnOff
	MAX-ACCESS read-only
	STATUS current
	DESCRIPTION
        "
        Client Current 15-min Output Packet
        counter inv. :This OID indicates
        that the current 15-min Output
         Packets counter is invalid
        "
	::= { pm20020maPerfDatacomClientCurrent15StatEntry 30 }


pm20020maperfdatacomclientCurrent15StatOutPacketCountPortn OBJECT-TYPE
	SYNTAX  Counter64
	MAX-ACCESS read-only
	STATUS current
	DESCRIPTION
        "
        Client Current 15-min Output Packet
        counter :This OID gives the current
        15-min Output Packets counter value
        "
	::= { pm20020maPerfDatacomClientCurrent15StatEntry 31 }


pm20020maperfdatacomclientCurrent15StatOutCrcCountInvPortn OBJECT-TYPE
	SYNTAX  EkiOnOff
	MAX-ACCESS read-only
	STATUS current
	DESCRIPTION
        "
        Client Current 15-min Output CRC
        counter inv. :This OID indicates
        that the current 15-min Output
         CRC counter is invalid
        "
	::= { pm20020maPerfDatacomClientCurrent15StatEntry 28 }


pm20020maperfdatacomclientCurrent15StatOutCrcCountPortn OBJECT-TYPE
	SYNTAX  Counter64
	MAX-ACCESS read-only
	STATUS current
	DESCRIPTION
        "
        Client Current 15-min Output CRC
        counter :This OID gives the current
        15-min Output CRC counter value
        "
	::= { pm20020maPerfDatacomClientCurrent15StatEntry 29 }


pm20020maperfdatacomclientCurrent15StatInPacketCountInvPortn OBJECT-TYPE
	SYNTAX  EkiOnOff
	MAX-ACCESS read-only
	STATUS current
	DESCRIPTION
        "
        Client Current 15-min Input Packet
        counter inv. :This OID indicates
        that the current 15-min Input Packet
        counter is invalid
        "
	::= { pm20020maPerfDatacomClientCurrent15StatEntry 6 }


pm20020maperfdatacomclientCurrent15StatInPacketCountPortn OBJECT-TYPE
	SYNTAX  Counter64
	MAX-ACCESS read-only
	STATUS current
	DESCRIPTION
        "
        Client Current 15-min Input Packet
        counter :This OID gives the current
        15-min Input Packet counter value
        "
	::= { pm20020maPerfDatacomClientCurrent15StatEntry 7 }


pm20020maperfdatacomclientCurrent15StatInCrcCountInvPortn OBJECT-TYPE
	SYNTAX  EkiOnOff
	MAX-ACCESS read-only
	STATUS current
	DESCRIPTION
        "
        Client Current 15-min Input CRC
        counter inv. :This OID indicates
        that the current 15-min Input CRC
        counter is invalid
        "
	::= { pm20020maPerfDatacomClientCurrent15StatEntry 4 }


pm20020maperfdatacomclientCurrent15StatInCrcCountPortn OBJECT-TYPE
	SYNTAX  Counter64
	MAX-ACCESS read-only
	STATUS current
	DESCRIPTION
        "
        Client Current 15-min Input CRC
        counter :This OID gives the current
        15-min Input CRC counter value
        "
	::= { pm20020maPerfDatacomClientCurrent15StatEntry 5 }


--- *****************************************************
---     Leaf of the datacomClientPast15Stat
--- *****************************************************
--- *********************************************************
---     TABLE for the pm20020maPerfDatacomClientPast15StatHistory articles
--- *********************************************************

pm20020maPerfDatacomClientPast15StatHistoryPort1Table OBJECT-TYPE
	SYNTAX  SEQUENCE OF Pm20020maPerfDatacomClientPast15StatHistoryPort1Entry
	MAX-ACCESS not-accessible
	STATUS current
	DESCRIPTION
        "
        List of pm20020maPerfDatacomClientPast15StatHistory
        Article
        "
	::= { pm20020maMonPerfClient 880 }


pm20020maPerfDatacomClientPast15StatHistoryPort1Entry OBJECT-TYPE
	SYNTAX Pm20020maPerfDatacomClientPast15StatHistoryPort1Entry
	MAX-ACCESS not-accessible
	STATUS current
	DESCRIPTION
        "
        Row definition for the pm20020maPerfDatacomClientPast15StatHistory
        table
        "
	INDEX   { pm20020maPerfDatacomClientPast15StatHistoryPort1Index }
	::= { pm20020maPerfDatacomClientPast15StatHistoryPort1Table 1 }


Pm20020maPerfDatacomClientPast15StatHistoryPort1Entry ::=
	SEQUENCE {
	pm20020maPerfDatacomClientPast15StatHistoryPort1Index
		INTEGER,
	pm20020maperfdatacomclientPast15StatOutPacketCountInvPort1
		EkiOnOff,
	pm20020maperfdatacomclientPast15StatOutPacketCountPort1
		Counter64,
	pm20020maperfdatacomclientPast15StatOutCrcCountInvPort1
		EkiOnOff,
	pm20020maperfdatacomclientPast15StatOutCrcCountPort1
		Counter64,
	pm20020maperfdatacomclientPast15StatInPacketCountInvPort1
		EkiOnOff,
	pm20020maperfdatacomclientPast15StatInPacketCountPort1
		Counter64,
	pm20020maperfdatacomclientPast15StatInCrcCountInvPort1
		EkiOnOff,
	pm20020maperfdatacomclientPast15StatInCrcCountPort1
		Counter64
	}


pm20020maPerfDatacomClientPast15StatHistoryPort1Index OBJECT-TYPE
	SYNTAX  INTEGER(0..128)
	MAX-ACCESS  read-only
	STATUS current
	DESCRIPTION
        "
        Index definition for the pm20020maPerfDatacomClientPast15StatHistory
        table
        "
	::= { pm20020maPerfDatacomClientPast15StatHistoryPort1Entry 1 }


pm20020maperfdatacomclientPast15StatOutPacketCountInvPort1 OBJECT-TYPE
	SYNTAX  EkiOnOff
	MAX-ACCESS read-only
	STATUS current
	DESCRIPTION
        "
        Client Past 15-min Output Packet
        counter inv. :This OID indicates
        that the past 15-min Output Packets
        counter is invalid
        "
	::= { pm20020maPerfDatacomClientPast15StatHistoryPort1Entry 30 }


pm20020maperfdatacomclientPast15StatOutPacketCountPort1 OBJECT-TYPE
	SYNTAX  Counter64
	MAX-ACCESS read-only
	STATUS current
	DESCRIPTION
        "
        Client Past 15-min Output Packet
        counter :This OID gives the past
        15-min Output Packets counter value
        "
	::= { pm20020maPerfDatacomClientPast15StatHistoryPort1Entry 31 }


pm20020maperfdatacomclientPast15StatOutCrcCountInvPort1 OBJECT-TYPE
	SYNTAX  EkiOnOff
	MAX-ACCESS read-only
	STATUS current
	DESCRIPTION
        "
        Client Past 15-min Output CRC
         counter inv. :This OID indicates
        that the past 15-min Output CRC
        counter is invalid
        "
	::= { pm20020maPerfDatacomClientPast15StatHistoryPort1Entry 28 }


pm20020maperfdatacomclientPast15StatOutCrcCountPort1 OBJECT-TYPE
	SYNTAX  Counter64
	MAX-ACCESS read-only
	STATUS current
	DESCRIPTION
        "
        Client Past 15-min Output CRC
         counter :This OID gives the past
        15-min Output CRC counter value
        "
	::= { pm20020maPerfDatacomClientPast15StatHistoryPort1Entry 29 }


pm20020maperfdatacomclientPast15StatInPacketCountInvPort1 OBJECT-TYPE
	SYNTAX  EkiOnOff
	MAX-ACCESS read-only
	STATUS current
	DESCRIPTION
        "
        Client Past 15-min Input Packet
        counter inv. :This OID indicates
        that the past 15-min Input Packet
        counter is invalid
        "
	::= { pm20020maPerfDatacomClientPast15StatHistoryPort1Entry 6 }


pm20020maperfdatacomclientPast15StatInPacketCountPort1 OBJECT-TYPE
	SYNTAX  Counter64
	MAX-ACCESS read-only
	STATUS current
	DESCRIPTION
        "
        Client Past 15-min Input Packet
        counter :This OID gives the past
        15-min Input Packet counter value
        "
	::= { pm20020maPerfDatacomClientPast15StatHistoryPort1Entry 7 }


pm20020maperfdatacomclientPast15StatInCrcCountInvPort1 OBJECT-TYPE
	SYNTAX  EkiOnOff
	MAX-ACCESS read-only
	STATUS current
	DESCRIPTION
        "
        Client Past 15-min Input CRC counter
        inv. :This OID indicates that the
        past 15-min Input CRC counter is
        invalid
        "
	::= { pm20020maPerfDatacomClientPast15StatHistoryPort1Entry 4 }


pm20020maperfdatacomclientPast15StatInCrcCountPort1 OBJECT-TYPE
	SYNTAX  Counter64
	MAX-ACCESS read-only
	STATUS current
	DESCRIPTION
        "
        Client Past 15-min Input CRC counter
        :This OID gives the past 15-min
        Input CRC counter value
        "
	::= { pm20020maPerfDatacomClientPast15StatHistoryPort1Entry 5 }


--- *****************************************************
---     Leaf of the datacomClientCurrent24Stat
--- *****************************************************
--- *********************************************************
---     TABLE for the pm20020maPerfDatacomClientCurrent24Stat articles
--- *********************************************************

pm20020maPerfDatacomClientCurrent24StatTable OBJECT-TYPE
	SYNTAX  SEQUENCE OF Pm20020maPerfDatacomClientCurrent24StatEntry
	MAX-ACCESS not-accessible
	STATUS current
	DESCRIPTION
        "
        List of pm20020maPerfDatacomClientCurrent24Stat
        Article
        "
	::= { pm20020maMonPerfClient 912 }


pm20020maPerfDatacomClientCurrent24StatEntry OBJECT-TYPE
	SYNTAX Pm20020maPerfDatacomClientCurrent24StatEntry
	MAX-ACCESS not-accessible
	STATUS current
	DESCRIPTION
        "
        Row definition for the pm20020maPerfDatacomClientCurrent24Stat
        table
        "
	INDEX   { pm20020maPerfDatacomClientCurrent24StatIndex }
	::= { pm20020maPerfDatacomClientCurrent24StatTable 1 }


Pm20020maPerfDatacomClientCurrent24StatEntry ::=
	SEQUENCE {
	pm20020maPerfDatacomClientCurrent24StatIndex
		INTEGER,
	pm20020maperfdatacomclientCurrent24StatOutPacketCountInvPortn
		EkiOnOff,
	pm20020maperfdatacomclientCurrent24StatOutPacketCountPortn
		Counter64,
	pm20020maperfdatacomclientCurrent24StatOutCrcCountInvPortn
		EkiOnOff,
	pm20020maperfdatacomclientCurrent24StatOutCrcCountPortn
		Counter64,
	pm20020maperfdatacomclientCurrent24StatInPacketCountInvPortn
		EkiOnOff,
	pm20020maperfdatacomclientCurrent24StatInPacketCountPortn
		Counter64,
	pm20020maperfdatacomclientCurrent24StatInCrcCountInvPortn
		EkiOnOff,
	pm20020maperfdatacomclientCurrent24StatInCrcCountPortn
		Counter64
	}


pm20020maPerfDatacomClientCurrent24StatIndex OBJECT-TYPE
	SYNTAX  INTEGER(0..128)
	MAX-ACCESS  read-only
	STATUS current
	DESCRIPTION
        "
        Index definition for the pm20020maPerfDatacomClientCurrent24Stat
        table
        "
	::= { pm20020maPerfDatacomClientCurrent24StatEntry 1 }


pm20020maperfdatacomclientCurrent24StatOutPacketCountInvPortn OBJECT-TYPE
	SYNTAX  EkiOnOff
	MAX-ACCESS read-only
	STATUS current
	DESCRIPTION
        "
        Client Current 24-hours Output
        Packet counter inv. :This OID indicates
        that the current 24-hours Output
        Packets counter is invalid
        "
	::= { pm20020maPerfDatacomClientCurrent24StatEntry 30 }


pm20020maperfdatacomclientCurrent24StatOutPacketCountPortn OBJECT-TYPE
	SYNTAX  Counter64
	MAX-ACCESS read-only
	STATUS current
	DESCRIPTION
        "
        Client Current 24-hours Output
        Packet counter :This OID gives
         the current 24-hours Output Packets
        counter value
        "
	::= { pm20020maPerfDatacomClientCurrent24StatEntry 31 }


pm20020maperfdatacomclientCurrent24StatOutCrcCountInvPortn OBJECT-TYPE
	SYNTAX  EkiOnOff
	MAX-ACCESS read-only
	STATUS current
	DESCRIPTION
        "
        Client Current 24-hours Output
        CRC counter inv. :This OID indicates
        that the current 24-hours Output
        CRC counter is invalid
        "
	::= { pm20020maPerfDatacomClientCurrent24StatEntry 28 }


pm20020maperfdatacomclientCurrent24StatOutCrcCountPortn OBJECT-TYPE
	SYNTAX  Counter64
	MAX-ACCESS read-only
	STATUS current
	DESCRIPTION
        "
        Client Current 24-hours Output
        CRC counter :This OID gives the
        current 24-hours Output CRC counter
        value
        "
	::= { pm20020maPerfDatacomClientCurrent24StatEntry 29 }


pm20020maperfdatacomclientCurrent24StatInPacketCountInvPortn OBJECT-TYPE
	SYNTAX  EkiOnOff
	MAX-ACCESS read-only
	STATUS current
	DESCRIPTION
        "
        Client Current 24-hours Input
         Packet counter inv. :This OID
         indicates that the current 24-hours
        Input Packet counter is invalid
        "
	::= { pm20020maPerfDatacomClientCurrent24StatEntry 6 }


pm20020maperfdatacomclientCurrent24StatInPacketCountPortn OBJECT-TYPE
	SYNTAX  Counter64
	MAX-ACCESS read-only
	STATUS current
	DESCRIPTION
        "
        Client Current 24-hours Input
         Packet counter :This OID gives
        the current 24-hours Input Packet
        counter value
        "
	::= { pm20020maPerfDatacomClientCurrent24StatEntry 7 }


pm20020maperfdatacomclientCurrent24StatInCrcCountInvPortn OBJECT-TYPE
	SYNTAX  EkiOnOff
	MAX-ACCESS read-only
	STATUS current
	DESCRIPTION
        "
        Client Current 24-hours Input
         CRC counter inv. :This OID indicates
        that the current 24-hours Input
        CRC counter is invalid
        "
	::= { pm20020maPerfDatacomClientCurrent24StatEntry 4 }


pm20020maperfdatacomclientCurrent24StatInCrcCountPortn OBJECT-TYPE
	SYNTAX  Counter64
	MAX-ACCESS read-only
	STATUS current
	DESCRIPTION
        "
        Client Current 24-hours Input
         CRC counter :This OID gives the
        current 24-hours Input CRC counter
        value
        "
	::= { pm20020maPerfDatacomClientCurrent24StatEntry 5 }


--- *****************************************************
---     Leaf of the datacomClientPast24Stat
--- *****************************************************
--- *********************************************************
---     TABLE for the pm20020maPerfDatacomClientPast24StatHistory articles
--- *********************************************************

pm20020maPerfDatacomClientPast24StatHistoryPort1Table OBJECT-TYPE
	SYNTAX  SEQUENCE OF Pm20020maPerfDatacomClientPast24StatHistoryPort1Entry
	MAX-ACCESS not-accessible
	STATUS current
	DESCRIPTION
        "
        List of pm20020maPerfDatacomClientPast24StatHistory
        Article
        "
	::= { pm20020maMonPerfClient 944 }


pm20020maPerfDatacomClientPast24StatHistoryPort1Entry OBJECT-TYPE
	SYNTAX Pm20020maPerfDatacomClientPast24StatHistoryPort1Entry
	MAX-ACCESS not-accessible
	STATUS current
	DESCRIPTION
        "
        Row definition for the pm20020maPerfDatacomClientPast24StatHistory
        table
        "
	INDEX   { pm20020maPerfDatacomClientPast24StatHistoryPort1Index }
	::= { pm20020maPerfDatacomClientPast24StatHistoryPort1Table 1 }


Pm20020maPerfDatacomClientPast24StatHistoryPort1Entry ::=
	SEQUENCE {
	pm20020maPerfDatacomClientPast24StatHistoryPort1Index
		INTEGER,
	pm20020maperfdatacomclientPast24StatOutPacketCountInvPort1
		EkiOnOff,
	pm20020maperfdatacomclientPast24StatOutPacketCountPort1
		Counter64,
	pm20020maperfdatacomclientPast24StatOutCrcCountInvPort1
		EkiOnOff,
	pm20020maperfdatacomclientPast24StatOutCrcCountPort1
		Counter64,
	pm20020maperfdatacomclientPast24StatInPacketCountInvPort1
		EkiOnOff,
	pm20020maperfdatacomclientPast24StatInPacketCountPort1
		Counter64,
	pm20020maperfdatacomclientPast24StatInCrcCountInvPort1
		EkiOnOff,
	pm20020maperfdatacomclientPast24StatInCrcCountPort1
		Counter64
	}


pm20020maPerfDatacomClientPast24StatHistoryPort1Index OBJECT-TYPE
	SYNTAX  INTEGER(0..128)
	MAX-ACCESS  read-only
	STATUS current
	DESCRIPTION
        "
        Index definition for the pm20020maPerfDatacomClientPast24StatHistory
        table
        "
	::= { pm20020maPerfDatacomClientPast24StatHistoryPort1Entry 1 }


pm20020maperfdatacomclientPast24StatOutPacketCountInvPort1 OBJECT-TYPE
	SYNTAX  EkiOnOff
	MAX-ACCESS read-only
	STATUS current
	DESCRIPTION
        "
        Client Past 24-hours Output Packet
        counter inv. :This OID indicates
        that the past 24-hours Output Packets
        counter is invalid
        "
	::= { pm20020maPerfDatacomClientPast24StatHistoryPort1Entry 30 }


pm20020maperfdatacomclientPast24StatOutPacketCountPort1 OBJECT-TYPE
	SYNTAX  Counter64
	MAX-ACCESS read-only
	STATUS current
	DESCRIPTION
        "
        Client Past 24-hours Output Packet
        counter :This OID gives the past
        24-hours Output Packets counter
        value
        "
	::= { pm20020maPerfDatacomClientPast24StatHistoryPort1Entry 31 }


pm20020maperfdatacomclientPast24StatOutCrcCountInvPort1 OBJECT-TYPE
	SYNTAX  EkiOnOff
	MAX-ACCESS read-only
	STATUS current
	DESCRIPTION
        "
        Client Past 24-hours Output CRC
        counter inv. :This OID indicates
        that the past 24-hours Output CRC
        counter is invalid
        "
	::= { pm20020maPerfDatacomClientPast24StatHistoryPort1Entry 28 }


pm20020maperfdatacomclientPast24StatOutCrcCountPort1 OBJECT-TYPE
	SYNTAX  Counter64
	MAX-ACCESS read-only
	STATUS current
	DESCRIPTION
        "
        Client Past 24-hours Output CRC
        counter :This OID gives the past
        24-hours Output CRC counter value
        "
	::= { pm20020maPerfDatacomClientPast24StatHistoryPort1Entry 29 }


pm20020maperfdatacomclientPast24StatInPacketCountInvPort1 OBJECT-TYPE
	SYNTAX  EkiOnOff
	MAX-ACCESS read-only
	STATUS current
	DESCRIPTION
        "
        Client Past 24-hours Input Packet
        counter inv. :This OID indicates
        that the past 24-hours Input Packet
        counter is invalid
        "
	::= { pm20020maPerfDatacomClientPast24StatHistoryPort1Entry 6 }


pm20020maperfdatacomclientPast24StatInPacketCountPort1 OBJECT-TYPE
	SYNTAX  Counter64
	MAX-ACCESS read-only
	STATUS current
	DESCRIPTION
        "
        Client Past 24-hours Input Packet
        counter :This OID gives the past
        24-hours Input Packet counter value
        "
	::= { pm20020maPerfDatacomClientPast24StatHistoryPort1Entry 7 }


pm20020maperfdatacomclientPast24StatInCrcCountInvPort1 OBJECT-TYPE
	SYNTAX  EkiOnOff
	MAX-ACCESS read-only
	STATUS current
	DESCRIPTION
        "
        Client Past 24-hours Input CRC
        counter inv. :This OID indicates
        that the past 24-hours Input CRC
        counter is invalid
        "
	::= { pm20020maPerfDatacomClientPast24StatHistoryPort1Entry 4 }


pm20020maperfdatacomclientPast24StatInCrcCountPort1 OBJECT-TYPE
	SYNTAX  Counter64
	MAX-ACCESS read-only
	STATUS current
	DESCRIPTION
        "
        Client Past 24-hours Input CRC
        counter :This OID gives the past
        24-hours Input CRC counter value
        "
	::= { pm20020maPerfDatacomClientPast24StatHistoryPort1Entry 5 }



pm20020maPerfEnable OBJECT-TYPE
	SYNTAX EkiOnOff
	MAX-ACCESS read-write
	STATUS current
	DESCRIPTION
        "
        Perf. Mon. Enable :This OID enables
        the Performance Monitoring application
        "
	::= { pm20020maMonPerfSync 257 }


pm20020maPerf15minSync OBJECT-TYPE
	SYNTAX EkiOnOff
	MAX-ACCESS read-write
	STATUS current
	DESCRIPTION
        "
        Perf. Mon. 15-min sync. :This
         OID must be used in external synchronisation
        mode only to send a 15-min synchronisation
        command
        "
	::= { pm20020maMonPerfSync 259 }


pm20020maPerf24hSync OBJECT-TYPE
	SYNTAX EkiOnOff
	MAX-ACCESS read-write
	STATUS current
	DESCRIPTION
        "
        Perf. Mon. 24-hours sync. :This
        OID must be used in external synchronisation
        mode only to send a 24-hours synchronisation
        command
        "
	::= { pm20020maMonPerfSync 260 }


pm20020maPerf15MinShort OBJECT-TYPE
	SYNTAX EkiOnOff
	MAX-ACCESS read-write
	STATUS current
	DESCRIPTION
        "
        15-min period is short :This OID
        indicates that the 15-min period
        lasts less than 890 seconds
        "
	::= { pm20020maMonPerfTimeStamp 1 }


pm20020maPerf15MinLong OBJECT-TYPE
	SYNTAX EkiOnOff
	MAX-ACCESS read-write
	STATUS current
	DESCRIPTION
        "
        15-min period is long :This OID
        indicates that the 15-min period
        lasts more than 910 seconds
        "
	::= { pm20020maMonPerfTimeStamp 2 }


pm20020maPerf24HoursShort OBJECT-TYPE
	SYNTAX Counter32
	MAX-ACCESS read-write
	STATUS current
	DESCRIPTION
        "
        24-hours period is short :This
        OID indicates that 24-hours period
        lasts less than 86390 seconds
        "
	::= { pm20020maMonPerfTimeStamp 5 }


pm20020maPerf24HoursLong OBJECT-TYPE
	SYNTAX Counter32
	MAX-ACCESS read-write
	STATUS current
	DESCRIPTION
        "
        24-hours period is long :This
         OID indicates that 24-hours period
        lasts more than 86410 seconds
        "
	::= { pm20020maMonPerfTimeStamp 6 }


pm20020maPerfCurrent15MinElapsedTime OBJECT-TYPE
	SYNTAX Counter32
	MAX-ACCESS read-write
	STATUS current
	DESCRIPTION
        "
        Current 15min period Elapsed Time
         :This OID gives the number of
         seconds elapsed in the current
        15-minutes period
        "
	::= { pm20020maMonPerfTimeStamp 7 }


pm20020maPerfCurrent24HoursElapsedTime OBJECT-TYPE
	SYNTAX Counter32
	MAX-ACCESS read-write
	STATUS current
	DESCRIPTION
        "
        Current 24hours period Elapsed
        Time :This OID gives the number
        of seconds elapsed in the current
        24-hours period
        "
	::= { pm20020maMonPerfTimeStamp 8 }






--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pm20020maDwlrestartProcess OBJECT IDENTIFIER ::= { pm20020maDwlOther 0 }




pm20020maDwlColdRestartProcessed OBJECT-TYPE
	  SYNTAX EkiOnOff
	  MAX-ACCESS read-only
	  STATUS current
	  DESCRIPTION
        "
        Cold Restart :This OID indicates
        that the module last restart was
        a Cold RESTART
        "
	  ::= { pm20020maDwlrestartProcess 2 }



pm20020maDwlWarmRestartProcessed OBJECT-TYPE
	  SYNTAX EkiOnOff
	  MAX-ACCESS read-only
	  STATUS current
	  DESCRIPTION
        "
        Warm Restart :This OID indicates
        that the module last restart was
        a Warm RESTART
        "
	  ::= { pm20020maDwlrestartProcess 1 }



--- *****************************************************
---     LEAF for the swBanksUsed article
--- *****************************************************
pm20020maDwlswBanksUsed OBJECT IDENTIFIER ::= { pm20020maDwlOther 1 }




pm20020maDwlSwBank2Notempty OBJECT-TYPE
	  SYNTAX EkiOnOff
	  MAX-ACCESS read-only
	  STATUS current
	  DESCRIPTION
        "
        SW bank 2 loaded :This OID indicates
        a software is loaded in SW bank
        2  <Help>  This status indicates
        if the SW bank 2 contains SW package
        "
	  ::= { pm20020maDwlswBanksUsed 6 }



pm20020maDwlSwBank1Notempty OBJECT-TYPE
	  SYNTAX EkiOnOff
	  MAX-ACCESS read-only
	  STATUS current
	  DESCRIPTION
        "
        SW bank 1 loaded :This OID indicates
        a software is loaded in SW bank
        1  <Help>  This status indicates
        if the SW bank 1 contains SW package
        "
	  ::= { pm20020maDwlswBanksUsed 5 }



pm20020maDwlSwBank2Used OBJECT-TYPE
	  SYNTAX EkiOnOff
	  MAX-ACCESS read-only
	  STATUS current
	  DESCRIPTION
        "
        SW bank 2 active :This OID indicates
        the module is working on SW bank
        2  <Help>  This status indicates
        if the SW bank 2 is active or standby
        "
	  ::= { pm20020maDwlswBanksUsed 2 }



pm20020maDwlSwBank1Used OBJECT-TYPE
	  SYNTAX EkiOnOff
	  MAX-ACCESS read-only
	  STATUS current
	  DESCRIPTION
        "
        SW bank 1 active :This OID indicates
        the module is working on SW bank
        1  <Help>  This status indicates
        if the SW bank 1 is active or standby
        "
	  ::= { pm20020maDwlswBanksUsed 1 }



--- *****************************************************
---     LEAF for the gwBanksUsed article
--- *****************************************************
pm20020maDwlgwBanksUsed OBJECT IDENTIFIER ::= { pm20020maDwlOther 2 }




pm20020maDwlGwBank4Notempty OBJECT-TYPE
	  SYNTAX EkiOnOff
	  MAX-ACCESS read-only
	  STATUS current
	  DESCRIPTION
        "
        GW bank 4 loaded :This OID indicates
        a gateware is loaded in GW bank
        4
        "
	  ::= { pm20020maDwlgwBanksUsed 8 }



pm20020maDwlGwBank3Notempty OBJECT-TYPE
	  SYNTAX EkiOnOff
	  MAX-ACCESS read-only
	  STATUS current
	  DESCRIPTION
        "
        GW bank 3 loaded :This OID indicates
        a gateware is loaded in GW bank
        3  <Help>  This status indicates
        if the GW bank 3 contains GW package
        "
	  ::= { pm20020maDwlgwBanksUsed 7 }



pm20020maDwlGwBank2Notempty OBJECT-TYPE
	  SYNTAX EkiOnOff
	  MAX-ACCESS read-only
	  STATUS current
	  DESCRIPTION
        "
        GW bank 2 loaded :This OID indicates
        a gateware is loaded in GW bank
        2
        "
	  ::= { pm20020maDwlgwBanksUsed 6 }



pm20020maDwlGwBank1Notempty OBJECT-TYPE
	  SYNTAX EkiOnOff
	  MAX-ACCESS read-only
	  STATUS current
	  DESCRIPTION
        "
        GW bank 1 loaded :This OID indicates
        a gateware is loaded in GW bank
        1  <Help>  This status indicates
        if the GW bank 1 contains GW package
        "
	  ::= { pm20020maDwlgwBanksUsed 5 }



pm20020maDwlGwBank4Used OBJECT-TYPE
	  SYNTAX EkiOnOff
	  MAX-ACCESS read-only
	  STATUS current
	  DESCRIPTION
        "
        GW bank 4 active :This OID indicates
        the module is working on GW bank
        4
        "
	  ::= { pm20020maDwlgwBanksUsed 4 }



pm20020maDwlGwBank3Used OBJECT-TYPE
	  SYNTAX EkiOnOff
	  MAX-ACCESS read-only
	  STATUS current
	  DESCRIPTION
        "
        GW bank 3 active :This OID indicates
        the module is working on GW bank
        3  <Help>  This status indicates
        if the GW bank 3 is active or standby
        "
	  ::= { pm20020maDwlgwBanksUsed 3 }



pm20020maDwlGwBank2Used OBJECT-TYPE
	  SYNTAX EkiOnOff
	  MAX-ACCESS read-only
	  STATUS current
	  DESCRIPTION
        "
        GW bank 2 active :This OID indicates
        the module is working on GW bank
        2
        "
	  ::= { pm20020maDwlgwBanksUsed 2 }



pm20020maDwlGwBank1Used OBJECT-TYPE
	  SYNTAX EkiOnOff
	  MAX-ACCESS read-only
	  STATUS current
	  DESCRIPTION
        "
        GW bank 1 active :This OID indicates
        the module is working on GW bank
        1  <Help>  This status indicates
        if the GW bank 1 is active or standby
        "
	  ::= { pm20020maDwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pm20020maCfgAccessCAisCsf OBJECT IDENTIFIER ::= { pm20020maConfig 1 }



--- *****************************************************
---     LEAF for the table 0012
--- *****************************************************

pm20020maCfgClientcaiscsfTable OBJECT-TYPE
	SYNTAX  SEQUENCE OF Pm20020maCfgClientcaiscsfEntry
	MAX-ACCESS not-accessible
	STATUS current
	DESCRIPTION
        "
        List of  Article
        "
	::= { pm20020maCfgAccessCAisCsf 1 }


pm20020maCfgClientcaiscsfEntry OBJECT-TYPE
	SYNTAX Pm20020maCfgClientcaiscsfEntry
	MAX-ACCESS not-accessible
	STATUS current
	DESCRIPTION
        "
        Row definition for the accessCAisCsf
        table
        "
	INDEX   { pm20020maCfgClientcaiscsfIndex }
	::= { pm20020maCfgClientcaiscsfTable 1 }


Pm20020maCfgClientcaiscsfEntry ::=
	SEQUENCE {
	pm20020maCfgClientcaiscsfIndex
		INTEGER,
	pm20020maCfgReservePortn
		Unsigned32
	}


pm20020maCfgClientcaiscsfIndex OBJECT-TYPE
	SYNTAX  INTEGER(0..128)
	MAX-ACCESS  read-only
	STATUS current
	DESCRIPTION
        "
        Index definition for the clientcaiscsf
        table
        "
	::= { pm20020maCfgClientcaiscsfEntry 1 }


pm20020maCfgReservePortn OBJECT-TYPE
	SYNTAX  Unsigned32 (0..65536)
	MAX-ACCESS read-write
	STATUS current
	DESCRIPTION
        "
        CAIS mode  on Client Port :This
        register enables/disables port
          laser shutdown on CAIS insertion
        condition
        "
	::= { pm20020maCfgClientcaiscsfEntry 3 }


--- *****************************************************
---     LEAF for the table Group startup
--- *****************************************************

pm20020maCfgStartup OBJECT IDENTIFIER ::= { pm20020maConfig 2 }



--- *****************************************************
---     LEAF for the table 2110
--- *****************************************************

pm20020maCfgClientStartupTable OBJECT-TYPE
	SYNTAX  SEQUENCE OF Pm20020maCfgClientStartupEntry
	MAX-ACCESS not-accessible
	STATUS current
	DESCRIPTION
        "
        List of  Article
        "
	::= { pm20020maCfgStartup 1 }


pm20020maCfgClientStartupEntry OBJECT-TYPE
	SYNTAX Pm20020maCfgClientStartupEntry
	MAX-ACCESS not-accessible
	STATUS current
	DESCRIPTION
        "
        Row definition for the startup
        table
        "
	INDEX   { pm20020maCfgClientStartupIndex }
	::= { pm20020maCfgClientStartupTable 1 }


Pm20020maCfgClientStartupEntry ::=
	SEQUENCE {
	pm20020maCfgClientStartupIndex
		INTEGER,
	pm20020maCfgSystConfPortPortn
		Unsigned32,
	pm20020maCfgNetConfPortPortn
		Unsigned32,
	pm20020maCfgOptionsPortPortn
		Unsigned32
	}


pm20020maCfgClientStartupIndex OBJECT-TYPE
	SYNTAX  INTEGER(0..128)
	MAX-ACCESS  read-only
	STATUS current
	DESCRIPTION
        "
        Index definition for the clientStartup
        table
        "
	::= { pm20020maCfgClientStartupEntry 1 }


pm20020maCfgSystConfPortPortn OBJECT-TYPE
	SYNTAX  Unsigned32 (0..65536)
	MAX-ACCESS read-write
	STATUS current
	DESCRIPTION
        "
        Default Settings on Client Port
        :This  register configures the
         default initialisation settings
        on the port.
        "
	::= { pm20020maCfgClientStartupEntry 3 }


pm20020maCfgNetConfPortPortn OBJECT-TYPE
	SYNTAX  Unsigned32 (0..65536)
	MAX-ACCESS read-write
	STATUS current
	DESCRIPTION
        "
        Default Settings on Client Port
        :This  register configures the
         default initialisation settings
        on the port.
        "
	::= { pm20020maCfgClientStartupEntry 4 }


pm20020maCfgOptionsPortPortn OBJECT-TYPE
	SYNTAX  Unsigned32 (0..65536)
	MAX-ACCESS read-write
	STATUS current
	DESCRIPTION
        "
        Default Options on Client Port
        :This register configures the default
        options on the port.
        "
	::= { pm20020maCfgClientStartupEntry 14 }


--- *****************************************************
---     LEAF for the table 2190
--- *****************************************************

pm20020maCfgLineStartupTable OBJECT-TYPE
	SYNTAX  SEQUENCE OF Pm20020maCfgLineStartupEntry
	MAX-ACCESS not-accessible
	STATUS current
	DESCRIPTION
        "
        List of  Article
        "
	::= { pm20020maCfgStartup 2 }


pm20020maCfgLineStartupEntry OBJECT-TYPE
	SYNTAX Pm20020maCfgLineStartupEntry
	MAX-ACCESS not-accessible
	STATUS current
	DESCRIPTION
        "
        Row definition for the startup
        table
        "
	INDEX   { pm20020maCfgLineStartupIndex }
	::= { pm20020maCfgLineStartupTable 1 }


Pm20020maCfgLineStartupEntry ::=
	SEQUENCE {
	pm20020maCfgLineStartupIndex
		INTEGER,
	pm20020maCfgSystConfLinePortn
		Unsigned32,
	pm20020maCfgOptionsLinePortn
		Unsigned32
	}


pm20020maCfgLineStartupIndex OBJECT-TYPE
	SYNTAX  INTEGER(0..128)
	MAX-ACCESS  read-only
	STATUS current
	DESCRIPTION
        "
        Index definition for the lineStartup
        table
        "
	::= { pm20020maCfgLineStartupEntry 1 }


pm20020maCfgSystConfLinePortn OBJECT-TYPE
	SYNTAX  Unsigned32 (0..65536)
	MAX-ACCESS read-write
	STATUS current
	DESCRIPTION
        "
        Default Settings on Line :This
        register configures the default
        initialisation settings on Line
        "
	::= { pm20020maCfgLineStartupEntry 3 }


pm20020maCfgOptionsLinePortn OBJECT-TYPE
	SYNTAX  Unsigned32 (0..65536)
	MAX-ACCESS read-write
	STATUS current
	DESCRIPTION
        "
        Default Options on Line :This
         register configures the default
        options on the line
        "
	::= { pm20020maCfgLineStartupEntry 14 }


--- *****************************************************
---     LEAF for the table 21AB
--- *****************************************************

pm20020maCfgXfpTable OBJECT-TYPE
	SYNTAX  SEQUENCE OF Pm20020maCfgXfpEntry
	MAX-ACCESS not-accessible
	STATUS current
	DESCRIPTION
        "
        List of  Article
        "
	::= { pm20020maCfgStartup 3 }


pm20020maCfgXfpEntry OBJECT-TYPE
	SYNTAX Pm20020maCfgXfpEntry
	MAX-ACCESS not-accessible
	STATUS current
	DESCRIPTION
        "
        Row definition for the startup
        table
        "
	INDEX   { pm20020maCfgXfpIndex }
	::= { pm20020maCfgXfpTable 1 }


Pm20020maCfgXfpEntry ::=
	SEQUENCE {
	pm20020maCfgXfpIndex
		INTEGER,
	pm20020maCfgSystConfMsaLinePortn
		Unsigned32
	}


pm20020maCfgXfpIndex OBJECT-TYPE
	SYNTAX  INTEGER(0..128)
	MAX-ACCESS  read-only
	STATUS current
	DESCRIPTION
        "
        Index definition for the xfp table
        "
	::= { pm20020maCfgXfpEntry 1 }


pm20020maCfgSystConfMsaLinePortn OBJECT-TYPE
	SYNTAX  Unsigned32 (0..65536)
	MAX-ACCESS read-write
	STATUS current
	DESCRIPTION
        "
        Default settings on MSA :This
         register configures the default
        initialisation settings on MSA
        "
	::= { pm20020maCfgXfpEntry 3 }


--- *****************************************************
---     LEAF for the table Group labels
--- *****************************************************

pm20020maCfgLabels OBJECT IDENTIFIER ::= { pm20020maConfig 3 }



--- *****************************************************
---     LEAF for the table 0003
--- *****************************************************

pm20020maCfgLabelclientTable OBJECT-TYPE
	SYNTAX  SEQUENCE OF Pm20020maCfgLabelclientEntry
	MAX-ACCESS not-accessible
	STATUS current
	DESCRIPTION
        "
        List of  Article
        "
	::= { pm20020maCfgLabels 1 }


pm20020maCfgLabelclientEntry OBJECT-TYPE
	SYNTAX Pm20020maCfgLabelclientEntry
	MAX-ACCESS not-accessible
	STATUS current
	DESCRIPTION
        "
        Row definition for the labels
         table
        "
	INDEX   { pm20020maCfgLabelclientIndex }
	::= { pm20020maCfgLabelclientTable 1 }


Pm20020maCfgLabelclientEntry ::=
	SEQUENCE {
	pm20020maCfgLabelclientIndex
		INTEGER,
	pm20020maCfgLabelclientPortn
		DisplayString
	}


pm20020maCfgLabelclientIndex OBJECT-TYPE
	SYNTAX  INTEGER(0..128)
	MAX-ACCESS  read-only
	STATUS current
	DESCRIPTION
        "
        Index definition for the labelclient
        table
        "
	::= { pm20020maCfgLabelclientEntry 1 }


pm20020maCfgLabelclientPortn OBJECT-TYPE
	SYNTAX  DisplayString( SIZE(1..16))
	MAX-ACCESS read-write
	STATUS current
	DESCRIPTION
        "
        Default settings on the label
         of the Ports :These registers
         configures the default initialisation
        settings of the labels of the ports.
        "
	::= { pm20020maCfgLabelclientEntry 3 }


--- *****************************************************
---     LEAF for the table 0004
--- *****************************************************

pm20020maCfgLabellineTable OBJECT-TYPE
	SYNTAX  SEQUENCE OF Pm20020maCfgLabellineEntry
	MAX-ACCESS not-accessible
	STATUS current
	DESCRIPTION
        "
        List of  Article
        "
	::= { pm20020maCfgLabels 2 }


pm20020maCfgLabellineEntry OBJECT-TYPE
	SYNTAX Pm20020maCfgLabellineEntry
	MAX-ACCESS not-accessible
	STATUS current
	DESCRIPTION
        "
        Row definition for the labels
         table
        "
	INDEX   { pm20020maCfgLabellineIndex }
	::= { pm20020maCfgLabellineTable 1 }


Pm20020maCfgLabellineEntry ::=
	SEQUENCE {
	pm20020maCfgLabellineIndex
		INTEGER,
	pm20020maCfgLabellinePortn
		DisplayString
	}


pm20020maCfgLabellineIndex OBJECT-TYPE
	SYNTAX  INTEGER(0..128)
	MAX-ACCESS  read-only
	STATUS current
	DESCRIPTION
        "
        Index definition for the labelline
        table
        "
	::= { pm20020maCfgLabellineEntry 1 }


pm20020maCfgLabellinePortn OBJECT-TYPE
	SYNTAX  DisplayString( SIZE(1..16))
	MAX-ACCESS read-write
	STATUS current
	DESCRIPTION
        "
        Default settings on the label
         of the lines :These registers
         configures the default initialisation
        settings of the labels of the lines.
        "
	::= { pm20020maCfgLabellineEntry 3 }


--- *****************************************************
---     LEAF for the table Group startuptlh
--- *****************************************************

pm20020maCfgStartuptlh OBJECT IDENTIFIER ::= { pm20020maConfig 4 }



--- *****************************************************
---     LEAF for the table 25AB
--- *****************************************************

pm20020maCfgOtxtlhTable OBJECT-TYPE
	SYNTAX  SEQUENCE OF Pm20020maCfgOtxtlhEntry
	MAX-ACCESS not-accessible
	STATUS current
	DESCRIPTION
        "
        List of  Article
        "
	::= { pm20020maCfgStartuptlh 1 }


pm20020maCfgOtxtlhEntry OBJECT-TYPE
	SYNTAX Pm20020maCfgOtxtlhEntry
	MAX-ACCESS not-accessible
	STATUS current
	DESCRIPTION
        "
        Row definition for the startuptlh
        table
        "
	INDEX   { pm20020maCfgOtxtlhIndex }
	::= { pm20020maCfgOtxtlhTable 1 }


Pm20020maCfgOtxtlhEntry ::=
	SEQUENCE {
	pm20020maCfgOtxtlhIndex
		INTEGER,
	pm20020maCfgLinePwrLaserPortn
		Unsigned32,
	pm20020maCfgLineFCurrentPortn
		Unsigned32,
	pm20020maCfgLineGridCurrentPortn
		Unsigned32,
	pm20020maCfgFPortn
		Unsigned32,
	pm20020maCfgRxLineFCurrentPortn
		Unsigned32
	}


pm20020maCfgOtxtlhIndex OBJECT-TYPE
	SYNTAX  INTEGER(0..128)
	MAX-ACCESS  read-only
	STATUS current
	DESCRIPTION
        "
        Index definition for the otxtlh
        table
        "
	::= { pm20020maCfgOtxtlhEntry 1 }


pm20020maCfgLinePwrLaserPortn OBJECT-TYPE
	SYNTAX  Unsigned32 (0..65536)
	MAX-ACCESS read-write
	STATUS current
	DESCRIPTION
        "
        Defaut Line output Power :This
        register configures the start-up
        output power of the Line tranceiver
         (Unit = dBm)
        "
	::= { pm20020maCfgOtxtlhEntry 6 }


pm20020maCfgLineFCurrentPortn OBJECT-TYPE
	SYNTAX  Unsigned32 (0..65536)
	MAX-ACCESS read-write
	STATUS current
	DESCRIPTION
        "
        Default Line transceiver Tx Channel
        :This register configures the start-up
        laser channel of the Line Tx transceiver
        "
	::= { pm20020maCfgOtxtlhEntry 7 }


pm20020maCfgLineGridCurrentPortn OBJECT-TYPE
	SYNTAX  Unsigned32 (0..65536)
	MAX-ACCESS read-write
	STATUS current
	DESCRIPTION
        "
        Default Line transceiver Grid
         :This register configures the
         start-up laser grid of the Line
        transceiver
        "
	::= { pm20020maCfgOtxtlhEntry 8 }


pm20020maCfgFPortn OBJECT-TYPE
	SYNTAX  Unsigned32 (0..65536)
	MAX-ACCESS read-write
	STATUS current
	DESCRIPTION
        "
        Default Line TRX lowest Freq :This
        register configures the start-up
        lowest frequency of the Line transceiver
        "
	::= { pm20020maCfgOtxtlhEntry 9 }


pm20020maCfgRxLineFCurrentPortn OBJECT-TYPE
	SYNTAX  Unsigned32 (0..65536)
	MAX-ACCESS read-write
	STATUS current
	DESCRIPTION
        "
        Default Line transceiver Rx Channel
        :This register configures the start-up
        laser channel of the Line Rx transceiver
        "
	::= { pm20020maCfgOtxtlhEntry 10 }


--- *****************************************************
---     LEAF for the table Group other
--- *****************************************************

pm20020maCfgOther OBJECT IDENTIFIER ::= { pm20020maConfig 5 }



--- *****************************************************
---     LEAF for the table 2300
--- *****************************************************

pm20020matablemoduleOther OBJECT IDENTIFIER ::= { pm20020maCfgOther 1 }



pm20020maCfgmode OBJECT-TYPE
	  SYNTAX Unsigned32 (0..65536)
	  MAX-ACCESS read-write
	  STATUS current
	  DESCRIPTION
        "
        Default settings on Module :This
        register selects the configuration
        mode of the module
        "
	  ::= { pm20020matablemoduleOther 2 }



pm20020maCfgfanLowSpeedThreshold OBJECT-TYPE
	  SYNTAX Unsigned32 (0..65536)
	  MAX-ACCESS read-write
	  STATUS current
	  DESCRIPTION
        "
        Default settings on Module :This
        register selects the speed threshold
        of the fan's
        "
	  ::= { pm20020matablemoduleOther 3 }



pm20020maCfgfanHighSpeedThreshold OBJECT-TYPE
	  SYNTAX Unsigned32 (0..65536)
	  MAX-ACCESS read-write
	  STATUS current
	  DESCRIPTION
        "
        Default settings on Module :This
        register selects the speed threshold
        of the fan's
        "
	  ::= { pm20020matablemoduleOther 4 }



--- *****************************************************
---     LEAF for the table Group startuptablefive
--- *****************************************************

pm20020maCfgStartuptablefive OBJECT IDENTIFIER ::= { pm20020maConfig 6 }



--- *****************************************************
---     LEAF for the table 0005
--- *****************************************************

pm20020maCfgOtxtlhcapabilitiesTable OBJECT-TYPE
	SYNTAX  SEQUENCE OF Pm20020maCfgOtxtlhcapabilitiesEntry
	MAX-ACCESS not-accessible
	STATUS current
	DESCRIPTION
        "
        List of  Article
        "
	::= { pm20020maCfgStartuptablefive 1 }


pm20020maCfgOtxtlhcapabilitiesEntry OBJECT-TYPE
	SYNTAX Pm20020maCfgOtxtlhcapabilitiesEntry
	MAX-ACCESS not-accessible
	STATUS current
	DESCRIPTION
        "
        Row definition for the startuptablefive
        table
        "
	INDEX   { pm20020maCfgOtxtlhcapabilitiesIndex }
	::= { pm20020maCfgOtxtlhcapabilitiesTable 1 }


Pm20020maCfgOtxtlhcapabilitiesEntry ::=
	SEQUENCE {
	pm20020maCfgOtxtlhcapabilitiesIndex
		INTEGER,
	pm20020maCfgComponentTypePortn
		Unsigned32,
	pm20020maCfgMiscellaneousPortn
		Unsigned32,
	pm20020maCfgFirstChannelPortn
		Unsigned32,
	pm20020maCfgLastChannelPortn
		Unsigned32,
	pm20020maCfgGridPortn
		Unsigned32
	}


pm20020maCfgOtxtlhcapabilitiesIndex OBJECT-TYPE
	SYNTAX  INTEGER(0..128)
	MAX-ACCESS  read-only
	STATUS current
	DESCRIPTION
        "
        Index definition for the otxtlhcapabilities
        table
        "
	::= { pm20020maCfgOtxtlhcapabilitiesEntry 1 }


pm20020maCfgComponentTypePortn OBJECT-TYPE
	SYNTAX  Unsigned32 (0..65536)
	MAX-ACCESS read-only
	STATUS current
	DESCRIPTION
        "
        Component parameters :This OID
        defines the component parameters
        "
	::= { pm20020maCfgOtxtlhcapabilitiesEntry 3 }


pm20020maCfgMiscellaneousPortn OBJECT-TYPE
	SYNTAX  Unsigned32 (0..65536)
	MAX-ACCESS read-only
	STATUS current
	DESCRIPTION
        "
        Miscellaneous default settings
        :This OID defines the miscellaneous
        parameters
        "
	::= { pm20020maCfgOtxtlhcapabilitiesEntry 4 }


pm20020maCfgFirstChannelPortn OBJECT-TYPE
	SYNTAX  Unsigned32 (0..65536)
	MAX-ACCESS read-only
	STATUS current
	DESCRIPTION
        "
        Number of the first channel of
        the component :This OID defines
        the first channel number of the
        PM
        "
	::= { pm20020maCfgOtxtlhcapabilitiesEntry 5 }


pm20020maCfgLastChannelPortn OBJECT-TYPE
	SYNTAX  Unsigned32 (0..65536)
	MAX-ACCESS read-only
	STATUS current
	DESCRIPTION
        "
        Number of the last channel of
         the component :This OID defines
        the last channel number of the
         PM
        "
	::= { pm20020maCfgOtxtlhcapabilitiesEntry 6 }


pm20020maCfgGridPortn OBJECT-TYPE
	SYNTAX  Unsigned32 (0..65536)
	MAX-ACCESS read-only
	STATUS current
	DESCRIPTION
        "
        Grid value of the component :This
        OID defines the grid of the PM
        "
	::= { pm20020maCfgOtxtlhcapabilitiesEntry 7 }



pm20020maCfgWriteConfiguration  OBJECT-TYPE
	SYNTAX EkiOnOff
	MAX-ACCESS read-write
	STATUS current
	DESCRIPTION
	"Write configuration to module:This OID
	 writes the complete configuration to the module"
	::= { pm20020maConfig 257 }






--- *****************************************************
---     TRAP OBJECTS
--- *****************************************************

pm20020matrapPortNumber OBJECT-TYPE
	SYNTAX INTEGER(1..64)
	MAX-ACCESS read-only
	STATUS current
	DESCRIPTION
	"Last port which generates a trap"
	::= { pm20020matraps 2 }

pm20020matrapLineNumber OBJECT-TYPE
	SYNTAX INTEGER(1..64)
	MAX-ACCESS read-only
	STATUS current
	DESCRIPTION
	"Last Line which generates a trap"
	::= { pm20020matraps 3 }

pm20020matrapBoardNumber OBJECT-TYPE
	SYNTAX INTEGER(1..64)
	MAX-ACCESS read-only
	STATUS current
	DESCRIPTION
	"Last module which generates a trap"
	::= { pm20020matraps 4 }







--- *****************************************************
---     LINE TRAPS
--- *****************************************************

pm20020maLineTrapNotUrgentGoesOn NOTIFICATION-TYPE
	OBJECTS {pm20020maAlmLineDdmWarningPortn, pm20020matrapLineNumber, pm20020matrapBoardNumber}
	STATUS current
	--&FILTNAME    "PM20020MA Line Not Urgent ON"
	--&ACTIONS     { log, minor }
	--&MATCH       { pm20020maAlmLineDdmWarningPortn "on", pm20020matrapLineNumber "$2", pm20020matrapBoardNumber "$3"}
	--&MESG        "DDM Warning appears on Line Port $2 of PM20020MA in Slot $3 ($A)"
	DESCRIPTION "Not urgent Line default is activated"
	::= { pm20020matraps 30 }

pm20020maLineTrapNotUrgentGoesOff NOTIFICATION-TYPE
	OBJECTS {pm20020maAlmLineDdmWarningPortn, pm20020matrapLineNumber, pm20020matrapBoardNumber}
	STATUS current
	--&FILTNAME    "PM20020MA Line Not Urgent OFF"
	--&ACTIONS     { log, normal }
	--&CLEARS      { "PM20020MA Line Not Urgent ON" }
	--&MATCH       { pm20020maAlmLineDdmWarningPortn "on", pm20020matrapLineNumber "$2", pm20020matrapBoardNumber "$3"}
	--&MESG        "DDM Warning disappears on Line Port $2 of PM20020MA in Slot $3 ($A)"
	DESCRIPTION "Not urgent Line default disappeared"
	::= { pm20020matraps 31 }

pm20020maLineTrapUrgentGoesOn NOTIFICATION-TYPE
	OBJECTS {pm20020maAlmLineDdmAlmPortn, pm20020matrapLineNumber, pm20020matrapBoardNumber}
	STATUS current
	--&FILTNAME    "PM20020MA Line Urgent ON"
	--&ACTIONS     { log, major }
	--&MATCH       { pm20020maAlmLineDdmAlmPortn "on", pm20020matrapLineNumber "$2", pm20020matrapBoardNumber "$3"}
	--&MESG        "DDM Alarm appears on Line Port $2 of PM20020MA in Slot $3 ($A)"
	DESCRIPTION "Urgent Line default is activated"
	::= { pm20020matraps 32 }

pm20020maLineTrapUrgentGoesOff NOTIFICATION-TYPE
	OBJECTS {pm20020maAlmLineDdmAlmPortn, pm20020matrapLineNumber, pm20020matrapBoardNumber}
	STATUS current
	--&FILTNAME    "PM20020MA Line Urgent OFF"
	--&ACTIONS     { log, normal }
	--&CLEARS      { "PM20020MA Line Urgent ON" }
	--&MATCH       { pm20020maAlmLineDdmAlmPortn "on", pm20020matrapLineNumber "$2", pm20020matrapBoardNumber "$3"}
	--&MESG        "DDM Alarm disappears on Line Port $2 of PM20020MA in Slot $3 ($A)"
	DESCRIPTION "Urgent Line default disappeared"
	::= { pm20020matraps 33 }

pm20020maLineTrapCritGoesOn NOTIFICATION-TYPE
	OBJECTS {pm20020maAlmLineFailPortn , pm20020maAlmLineHwFailPortn , pm20020matrapLineNumber, pm20020matrapBoardNumber}
	STATUS current
	--&FILTNAME    "PM20020MA Line Fail ON"
	--&ACTIONS     { log, critical }
	--&MATCH       { pm20020maAlmLineFailPortn "on", pm20020maAlmLineHwFailPortn "*", pm20020matrapLineNumber "$3", pm20020matrapBoardNumber "$4"}
	--&MESG        "Line Port $3 Down on PM20020MA in Slot $4 ($A)"

	--&FILTNAME    "PM20020MA Line HW Fail ON (Hidden)"
	--&ACTIONS     { info }
	--&MATCH       { pm20020maAlmLineFailPortn "*", pm20020maAlmLineHwFailPortn "on", pm20020matrapLineNumber "$3", pm20020matrapBoardNumber "$4"}
	--&MESG        "Line Port $3 Down on PM20020MA in Slot $4 ($A)"
	DESCRIPTION "Critical Line default is activated"
	::= { pm20020matraps 34 }

pm20020maLineTrapCritGoesOff NOTIFICATION-TYPE
	OBJECTS {pm20020maAlmLineFailPortn , pm20020maAlmLineHwFailPortn , pm20020matrapLineNumber, pm20020matrapBoardNumber}
	STATUS current
	--&FILTNAME    "PM20020MA Line Fail OFF"
	--&ACTIONS     { log,  normal }
	--&CLEARS      { "PM20020MA Line Fail ON" }
	--&MATCH       { pm20020maAlmLineFailPortn "on", pm20020maAlmLineHwFailPortn "*", pm20020matrapLineNumber "$3", pm20020matrapBoardNumber "$4"}
	--&MESG        "Line Port $3 Up on PM20020MA in Slot $4 ($A)"

	--&FILTNAME    "PM20020MA Line HW Fail OFF (Hidden)"
	--&ACTIONS     { info }
	--&MATCH       { pm20020maAlmLineFailPortn "*", pm20020maAlmLineHwFailPortn "on", pm20020matrapLineNumber "$3", pm20020matrapBoardNumber "$4"}
	--&MESG        "Line Port $3 Up on PM20020MA in Slot $4 ($A)"
	DESCRIPTION "Critical Line default disappeared"
	::= { pm20020matraps 35 }






--- *****************************************************
---     CLIENT TRAPS
--- *****************************************************

pm20020maClientTrapNotUrgentGoesOn NOTIFICATION-TYPE
	OBJECTS {pm20020maAlmSfpDdmWarningPortn, pm20020matrapPortNumber, pm20020matrapBoardNumber}
	STATUS current
		--&FILTNAME    "PM20020MA Client Not Urgent ON"
		--&ACTIONS     { log, minor }
		--&MATCH       { pm20020maAlmSfpDdmWarningPortn "on", pm20020matrapPortNumber "$2", pm20020matrapBoardNumber "$3"}
		--&MESG        "DDM Warning appears on Client Port $2 of PM20020MA in Slot $3 ($A)"
	DESCRIPTION "Not urgent client default is activated"
	::= { pm20020matraps 40 }

pm20020maClientTrapNotUrgentGoesOff NOTIFICATION-TYPE
	OBJECTS {pm20020maAlmSfpDdmWarningPortn, pm20020matrapPortNumber, pm20020matrapBoardNumber}
	STATUS current
		--&FILTNAME    "PM20020MA Client Not Urgent OFF"
		--&ACTIONS     { log, normal }
		--&CLEARS      { "PM20020MA Client Not Urgent ON" }
		--&MATCH       { pm20020maAlmSfpDdmWarningPortn "on", pm20020matrapPortNumber "$2", pm20020matrapBoardNumber "$3"}
		--&MESG        "DDM Warning appears on Client Port $2 of PM20020MA in Slot $3 ($A)"
	DESCRIPTION "Not urgent client default disappeared"
	::= { pm20020matraps 41 }

pm20020maClientTrapUrgentGoesOn NOTIFICATION-TYPE
	OBJECTS {pm20020maAlmSfpDdmAlmPortn, pm20020matrapPortNumber, pm20020matrapBoardNumber}
	STATUS current
		--&FILTNAME    "PM20020MA Client Urgent ON"
		--&ACTIONS     { log, major }
		--&MATCH       { pm20020maAlmSfpDdmAlmPortn "on", pm20020matrapPortNumber "$2", pm20020matrapBoardNumber "$3"}
		--&MESG        "DDM Alarm appears on Client Port $2 of PM20020MA in Slot $3 ($A)"
	DESCRIPTION "Urgent client default is activated"
	::= { pm20020matraps 42 }

pm20020maClientTrapUrgentGoesOff NOTIFICATION-TYPE
	OBJECTS {pm20020maAlmSfpDdmAlmPortn, pm20020matrapPortNumber, pm20020matrapBoardNumber}
	STATUS current
		--&FILTNAME    "PM20020MA Client Urgent OFF"
		--&ACTIONS     { log, normal }
		--&CLEARS      { "PM20020MA Client Urgent ON" }
		--&MATCH       { pm20020maAlmSfpDdmAlmPortn "on", pm20020matrapPortNumber "$2", pm20020matrapBoardNumber "$3"}
		--&MESG        "DDM Alarm disappears on Client Port $2 of PM20020MA in Slot $3 ($A)"
	DESCRIPTION "Urgent client default disappeared"
	::= { pm20020matraps 43 }

pm20020maClientTrapCritGoesOn NOTIFICATION-TYPE
	OBJECTS {pm20020maAlmFailAccPortn, pm20020maAlmHwFailAccPortn, pm20020matrapPortNumber, pm20020matrapBoardNumber}
	STATUS current
		--&FILTNAME    "PM20020MA Client Fail ON"
		--&ACTIONS     { log, critical }
		--&MATCH       { pm20020maAlmFailAccPortn "on", pm20020maAlmHwFailAccPortn "*", pm20020matrapPortNumber "$3", pm20020matrapBoardNumber "$4"}
		--&MESG        "Client Port $3 Down on PM20020MA in Slot $4 ($A)"

		--&FILTNAME    "PM20020MA Client HW Fail ON (Hidden)"
		--&ACTIONS     { info }
		--&MATCH       { pm20020maAlmFailAccPortn "*", pm20020maAlmHwFailAccPortn "on", pm20020matrapPortNumber "$3", pm20020matrapBoardNumber "$4"}
		--&MESG        "Client Port $3 Down on PM20020MA in Slot $4 ($A)"
	DESCRIPTION "Critical client default is activated"
	::= { pm20020matraps 44 }

pm20020maClientTrapCritGoesOff NOTIFICATION-TYPE
	OBJECTS {pm20020maAlmFailAccPortn, pm20020maAlmHwFailAccPortn, pm20020matrapPortNumber, pm20020matrapBoardNumber}
	STATUS current
		--&FILTNAME    "PM20020MA Client Fail OFF"
		--&ACTIONS     { log, normal }
		--&CLEARS      { "PM20020MA Client Fail ON" }
		--&MATCH       { pm20020maAlmFailAccPortn "on", pm20020maAlmHwFailAccPortn "*", pm20020matrapPortNumber "$3", pm20020matrapBoardNumber "$4"}
		--&MESG        "Client Port $3 Up on PM20020MA in Slot $4 ($A)"

		--&FILTNAME    "PM20020MA Client HW Fail OFF (Hidden)"
		--&ACTIONS     { info }
		--&MATCH       { pm20020maAlmFailAccPortn "*", pm20020maAlmHwFailAccPortn "on", pm20020matrapPortNumber "$3", pm20020matrapBoardNumber "$4"}
		--&MESG        "Client Port $3 Up on PM20020MA in Slot $4 ($A)"
	DESCRIPTION "Critical client default disappeared"
	::= { pm20020matraps 45 }






--- *****************************************************
---     HW TRAPS
--- *****************************************************

pm20020maPowerTrapUrgentGoesOn NOTIFICATION-TYPE
	OBJECTS {pm20020maAlmDefFuseB, pm20020maAlmDefFuseA , pm20020matrapBoardNumber}
	STATUS current
		--&FILTNAME    "PM20020MA Fuse A Fail ON"
		--&ACTIONS     { log, major }
		--&MATCH       { pm20020maAlmDefFuseB "*", pm20020maAlmDefFuseA "on", pm20020matrapBoardNumber "$3"}
		--&MESG        "Power Input A Fail on PM20020MA in Slot $3 ($A)"

		--&FILTNAME    "PM20020MA Fuse B Fail ON"
		--&ACTIONS     { log, major }
		--&MATCH       { pm20020maAlmDefFuseB "on", pm20020maAlmDefFuseA "*", pm20020matrapBoardNumber "$3"}
		--&MESG        "Power Input B Fail on PM20020MA in Slot $3 ($A)"
	DESCRIPTION "Urgent power supply default is activated"
	::= { pm20020matraps 50 }

pm20020maPowerTrapUrgentGoesOff NOTIFICATION-TYPE
	OBJECTS {pm20020maAlmDefFuseB, pm20020maAlmDefFuseA , pm20020matrapBoardNumber}
	STATUS current
		--&FILTNAME    "PM20020MA Fuse A&B Fail OFF"
		--&ACTIONS     { log, normal}
		--&CLEARS      { "PM20020MA Fuse A Fail ON", "PM20020MA Fuse B Fail ON" }
		--&MATCH       { pm20020maAlmDefFuseB "on", pm20020maAlmDefFuseA "on", pm20020matrapBoardNumber "$3"}
		--&MESG        "Power Inputs A and B Present on PM20020MA in Slot $3 ($A)"
	DESCRIPTION "Urgent power supply default disappeared"
	::= { pm20020matraps 51 }






END
