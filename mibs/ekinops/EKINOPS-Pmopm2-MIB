-- *****************************************************************
-- EKINOPS-Pmopm2.TXT:  MIB
--
--MIB Part Number:3MI00213AAAB
--MIB Version:02
--
-- Copyright (c) 2016 by Ekinops
-- All rights reserved.
--
-- *****************************************************************

EKINOPS-Pmopm2-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

modulePmopm2 MODULE-IDENTITY
        LAST-UPDATED "201605310000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.net"
        DESCRIPTION
          "MIB for managing Ekinops modules"
	REVISION "200412200000Z"
	DESCRIPTION
	  "Initial Version."


	REVISION "201605230000Z"
	DESCRIPTION
	  "New AlarmType – synthesisAlarm (12)"
	REVISION "201605310000Z"
	DESCRIPTION
	  "Labels cosmetic updates"
        ::= { ekinops 64 }



--- *****************************************************
---     LEAF LEVEL 2
--- *****************************************************


pmopm2alarms OBJECT IDENTIFIER ::= { modulePmopm2 2 }
pmopm2AlmOther OBJECT IDENTIFIER ::= { pmopm2alarms 1 }
pmopm2AlmOtherNurg OBJECT IDENTIFIER ::= { pmopm2AlmOther 1 }
pmopm2AlmOtherUrg OBJECT IDENTIFIER ::= { pmopm2AlmOther 2 }
pmopm2AlmOtherCrit OBJECT IDENTIFIER ::= { pmopm2AlmOther 3 }

pmopm2AlmClient OBJECT IDENTIFIER ::= { pmopm2alarms 2 }
pmopm2AlmClientNurg OBJECT IDENTIFIER ::= { pmopm2AlmClient 1 }
pmopm2AlmClientUrg OBJECT IDENTIFIER ::= { pmopm2AlmClient 2 }
pmopm2AlmClientCrit OBJECT IDENTIFIER ::= { pmopm2AlmClient 3 }

pmopm2AlmLine OBJECT IDENTIFIER ::= { pmopm2alarms 3 }
pmopm2AlmLineNurg OBJECT IDENTIFIER ::= { pmopm2AlmLine 1 }
pmopm2AlmLineUrg OBJECT IDENTIFIER ::= { pmopm2AlmLine 2 }
pmopm2AlmLineCrit OBJECT IDENTIFIER ::= { pmopm2AlmLine 3 }



pmopm2measures OBJECT IDENTIFIER ::= { modulePmopm2 3 }
pmopm2MesrOther OBJECT IDENTIFIER ::= { pmopm2measures 1 }
pmopm2MesrClient OBJECT IDENTIFIER ::= { pmopm2measures 2 }
pmopm2MesrLine OBJECT IDENTIFIER ::= { pmopm2measures 3 }




pmopm2controlsWrite OBJECT IDENTIFIER ::= { modulePmopm2 6 }
pmopm2CtrlOther OBJECT IDENTIFIER ::= { pmopm2controlsWrite 1 }
pmopm2CtrlClient OBJECT IDENTIFIER ::= { pmopm2controlsWrite 2 }
pmopm2CtrlLine OBJECT IDENTIFIER ::= { pmopm2controlsWrite 3 }

pmopm2ri OBJECT IDENTIFIER ::= { modulePmopm2 7 }
pmopm2riTable OBJECT IDENTIFIER ::= { pmopm2ri 1 }

pmopm2download OBJECT IDENTIFIER ::= { modulePmopm2 8 }
pmopm2DwlOther OBJECT IDENTIFIER ::= { pmopm2download 1 }
pmopm2DwlClient OBJECT IDENTIFIER ::= { pmopm2download 2 }
pmopm2DwlLine OBJECT IDENTIFIER ::= { pmopm2download 3 }


pmopm2Config OBJECT IDENTIFIER ::= { modulePmopm2 9 }

pmopm2traps OBJECT IDENTIFIER ::= { modulePmopm2 10 }




--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************


Pmopm2Grid ::= TEXTUAL-CONVENTION
    STATUS      current
    DESCRIPTION "Different grids on the modules"
    SYNTAX INTEGER {
		grid200(200),
		grid100(100),
		grid50(50)
           }

Pmopm2MultiRate ::= TEXTUAL-CONVENTION
    STATUS      current
    DESCRIPTION "different values for a client port"
    SYNTAX INTEGER

Pmopm2OtxChannel ::= TEXTUAL-CONVENTION
    STATUS      current
    DESCRIPTION "different values for a client port"
    SYNTAX INTEGER

Pmopm2AdjustValue ::= TEXTUAL-CONVENTION
    STATUS      current
    DESCRIPTION "different values for a client port"
    SYNTAX INTEGER

Pmopm2OtxMode ::= TEXTUAL-CONVENTION
    STATUS      current
    DESCRIPTION "different values for a client port"
    SYNTAX INTEGER

--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pmopm2RinvReloadInventory OBJECT-TYPE
  SYNTAX EkiOnOff
  MAX-ACCESS read-write
  STATUS current
  DESCRIPTION
        "Reload the inventory: This OID triggers an
         inventory reload."
  ::= { pmopm2ri 2 }

pmopm2RinvHwPlatform OBJECT-TYPE
  SYNTAX DisplayString
  MAX-ACCESS read-only
  STATUS current
  DESCRIPTION
        "HW platform description: This OID contains the
         description of the Hardware platform."
  ::= { pmopm2ri 3 }

pmopm2RinvModulePlatform OBJECT-TYPE
  SYNTAX DisplayString
  MAX-ACCESS read-only
  STATUS current
  DESCRIPTION
        "Module platform description: This OID contains the
         description of the Module."
  ::= { pmopm2ri 4 }

pmopm2RinvSwPlatform OBJECT-TYPE
  SYNTAX DisplayString
  MAX-ACCESS read-only
  STATUS current
  DESCRIPTION
        "SW platform description: This OID contains the
         description of the Software platform."
  ::= { pmopm2ri 5 }

pmopm2RinvGwPlatform OBJECT-TYPE
  SYNTAX DisplayString
  MAX-ACCESS read-only
  STATUS current
  DESCRIPTION
        "GW platform desciption: This OID contains the
         description of the Gateware platform."
  ::= { pmopm2ri 6 }


pmopm2RinvSfpTable OBJECT-TYPE
      SYNTAX  SEQUENCE OF Pmopm2RinvSfpEntry
      MAX-ACCESS  not-accessible
      STATUS  current
      DESCRIPTION
              "List of the SFPs on the selected module"
      ::= { pmopm2riTable 1 }

pmopm2RinvSfpEntry OBJECT-TYPE
        SYNTAX  Pmopm2RinvSfpEntry
        MAX-ACCESS  not-accessible
        STATUS  current
        DESCRIPTION
              "Row definition for the SFP table"
        INDEX   { pmopm2RinvSfpIndex }
        ::= { pmopm2RinvSfpTable 1 }



Pmopm2RinvSfpEntry::=
        SEQUENCE {
          pmopm2RinvSfpIndex
              Integer32,
          pmopm2Rinvsfp
              DisplayString
        }


    pmopm2RinvSfpIndex OBJECT-TYPE
        SYNTAX  Integer32(1..16)
        MAX-ACCESS  read-only
        STATUS  current
        DESCRIPTION
              "Index for SFP table"
        ::= { pmopm2RinvSfpEntry 1 }


    pmopm2Rinvsfp OBJECT-TYPE
        SYNTAX  DisplayString
        MAX-ACCESS  read-only
        STATUS  current
        DESCRIPTION
              "Inventory for the SFP: This OID contains the inventory for the SFP"
        ::= { pmopm2RinvSfpEntry 2 }




pmopm2RinvLineTable OBJECT-TYPE
      SYNTAX  SEQUENCE OF Pmopm2RinvLineEntry
      MAX-ACCESS  not-accessible
      STATUS  current
      DESCRIPTION
              "List of the XFPs on the selected module"
      ::= { pmopm2riTable 2 }

pmopm2RinvLineEntry OBJECT-TYPE
        SYNTAX  Pmopm2RinvLineEntry
        MAX-ACCESS  not-accessible
        STATUS  current
        DESCRIPTION
              "Row definition for the XFP table"
        INDEX   { pmopm2RinvLineIndex }
        ::= { pmopm2RinvLineTable 1 }



Pmopm2RinvLineEntry::=
        SEQUENCE {
          pmopm2RinvLineIndex
              Integer32,
          pmopm2RinvxfpLine
              DisplayString
        }


    pmopm2RinvLineIndex OBJECT-TYPE
        SYNTAX  Integer32(1..16)
        MAX-ACCESS  read-only
        STATUS  current
        DESCRIPTION
              "Index for XFP table"
        ::= { pmopm2RinvLineEntry 1 }


    pmopm2RinvxfpLine OBJECT-TYPE
        SYNTAX  DisplayString
        MAX-ACCESS  read-only
        STATUS  current
        DESCRIPTION
              "Inventory for the XFP: This OID contains the inventory for the XFP"
        ::= { pmopm2RinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pmopm2AlmsynthAlm0 OBJECT IDENTIFIER ::= { pmopm2AlmOtherCrit 0 }




pmopm2AlmDefFuseB OBJECT-TYPE
	  SYNTAX EkiOnOff
	  MAX-ACCESS read-only
	  STATUS current
	  DESCRIPTION
        "
        Fuse B Fail :This OID indicates
        that the fuse of the power input
        B is in fail condition  <Help>
          Status of the Fuse B <Condtype>
        DEF_FUSE_B <Probcause> powerProblem
        (36) <Alarmtype> equipmentAlarm
        (5) <Polarity> (2)
        "
	  ::= { pmopm2AlmsynthAlm0 16 }



pmopm2AlmDefFuseA OBJECT-TYPE
	  SYNTAX EkiOnOff
	  MAX-ACCESS read-only
	  STATUS current
	  DESCRIPTION
        "
        Fuse A Fail :This OID indicates
        that the fuse of the power input
        A is in fail condition  <Help>
          Status of the Fuse A <Condtype>
        DEF_FUSE_A <Probcause> powerProblem
        (36) <Alarmtype> equipmentAlarm
        (5) <Polarity> (2)
        "
	  ::= { pmopm2AlmsynthAlm0 15 }



pmopm2AlmModGlobFail OBJECT-TYPE
	  SYNTAX EkiOnOff
	  MAX-ACCESS read-only
	  STATUS current
	  DESCRIPTION
        "
        Module Failure :This OID is set
        on detection of a failure originating
        from the PM <Condtype> MOD_GLOB_FAIL
        <Probcause> equipmentMalfunction
        (16) <Alarmtype> synthesisAlarm
        (12)  <Polarity> (2)
        "
	  ::= { pmopm2AlmsynthAlm0 9 }



--- *****************************************************
---     LEAF for the synthAlm2 article
--- *****************************************************
pmopm2AlmsynthAlm2 OBJECT IDENTIFIER ::= { pmopm2AlmOtherNurg 2 }




pmopm2AlmCorrelatOff OBJECT-TYPE
	  SYNTAX EkiOnOff
	  MAX-ACCESS read-only
	  STATUS current
	  DESCRIPTION
        "
        Not Used : <Condtype> CORRELAT_OFF
        <Probcause> other (1) <Alarmtype>
        other (1) <Polarity> (2)
        "
	  ::= { pmopm2AlmsynthAlm2 4 }



pmopm2AlmConfTableLoad OBJECT-TYPE
	  SYNTAX EkiOnOff
	  MAX-ACCESS read-only
	  STATUS current
	  DESCRIPTION
        "
        PM Configuration Load : <Condtype>
        CONF_TABLE_LOAD <Probcause> other
        (1) <Alarmtype> other (1) <Polarity>
        (2)
        "
	  ::= { pmopm2AlmsynthAlm2 3 }



pmopm2AlmInvUpload OBJECT-TYPE
	  SYNTAX EkiOnOff
	  MAX-ACCESS read-only
	  STATUS current
	  DESCRIPTION
        "
        Inventory Upload : <Condtype>
         INV_UPLOAD <Probcause> other (1)
        <Alarmtype> other (1) <Polarity>
        (2)
        "
	  ::= { pmopm2AlmsynthAlm2 2 }



pmopm2AlmConfTableSave OBJECT-TYPE
	  SYNTAX EkiOnOff
	  MAX-ACCESS read-only
	  STATUS current
	  DESCRIPTION
        "
        PM Configuration Save : <Condtype>
        CONF_TABLE_SAVE <Probcause> other
        (1) <Alarmtype> other (1) <Polarity>
        (2)
        "
	  ::= { pmopm2AlmsynthAlm2 1 }



--- *********************************************************
---     TABLE for the pmopm2AlmsynthAlmPort articles
--- *********************************************************

pmopm2AlmsynthAlmPortTable OBJECT-TYPE
	SYNTAX  SEQUENCE OF Pmopm2AlmsynthAlmPortEntry
	MAX-ACCESS not-accessible
	STATUS current
	DESCRIPTION
        "
        List of pmopm2AlmsynthAlmPort
         Article
        "
	::= { pmopm2AlmClientCrit 8 }


pmopm2AlmsynthAlmPortEntry OBJECT-TYPE
	SYNTAX Pmopm2AlmsynthAlmPortEntry
	MAX-ACCESS not-accessible
	STATUS current
	DESCRIPTION
        "
        Row definition for the pmopm2AlmsynthAlmPort
        table
        "
	INDEX   { pmopm2AlmsynthAlmPortIndex }
	::= { pmopm2AlmsynthAlmPortTable 1 }


Pmopm2AlmsynthAlmPortEntry ::=
	SEQUENCE {
	pmopm2AlmsynthAlmPortIndex
		INTEGER,
	pmopm2AlmSpectrumAbsentPortn
		EkiOnOff
	}


pmopm2AlmsynthAlmPortIndex OBJECT-TYPE
	SYNTAX  INTEGER(0..128)
	MAX-ACCESS  read-only
	STATUS current
	DESCRIPTION
        "
        Index definition for the pmopm2AlmsynthAlmPort
        table
        "
	::= { pmopm2AlmsynthAlmPortEntry 1 }


pmopm2AlmSpectrumAbsentPortn OBJECT-TYPE
	SYNTAX  EkiOnOff
	MAX-ACCESS read-only
	STATUS current
	DESCRIPTION
        "
        Spectrum Absent :This OID indicates
        there is no spectrum detected on
        the Optical Power Monitoring input<Help>
        This alarm indicates there is no
        spectrum detected on the Optical
        Power Monitoring input <Condtype>
        SPECTRUM_ABSENT_1 <Probcause> inputOutputDeviceError
        (24) <Alarmtype> equipmentAlarm
        (5) <Polarity> (2)
        "
	::= { pmopm2AlmsynthAlmPortEntry 2 }


--- *********************************************************
---     TABLE for the pmopm2Almchannel1Port articles
--- *********************************************************

pmopm2Almchannel1PortTable OBJECT-TYPE
	SYNTAX  SEQUENCE OF Pmopm2Almchannel1PortEntry
	MAX-ACCESS not-accessible
	STATUS current
	DESCRIPTION
        "
        List of pmopm2Almchannel1Port
         Article
        "
	::= { pmopm2AlmClientCrit 16 }


pmopm2Almchannel1PortEntry OBJECT-TYPE
	SYNTAX Pmopm2Almchannel1PortEntry
	MAX-ACCESS not-accessible
	STATUS current
	DESCRIPTION
        "
        Row definition for the pmopm2Almchannel1Port
        table
        "
	INDEX   { pmopm2Almchannel1PortIndex }
	::= { pmopm2Almchannel1PortTable 1 }


Pmopm2Almchannel1PortEntry ::=
	SEQUENCE {
	pmopm2Almchannel1PortIndex
		INTEGER,
	pmopm2AlmChannel1OosPortn
		EkiOnOff,
	pmopm2AlmChannel1PowerHighPortn
		EkiOnOff,
	pmopm2AlmChannel1PowerLowPortn
		EkiOnOff,
	pmopm2AlmChannel1BalancedPortn
		EkiOnOff,
	pmopm2AlmChannel1MismatchPortn
		EkiOnOff,
	pmopm2AlmChannel1AbsentPortn
		EkiOnOff
	}


pmopm2Almchannel1PortIndex OBJECT-TYPE
	SYNTAX  INTEGER(0..128)
	MAX-ACCESS  read-only
	STATUS current
	DESCRIPTION
        "
        Index definition for the pmopm2Almchannel1Port
        table
        "
	::= { pmopm2Almchannel1PortEntry 1 }


pmopm2AlmChannel1OosPortn OBJECT-TYPE
	SYNTAX  EkiOnOff
	MAX-ACCESS read-only
	STATUS current
	DESCRIPTION
        "
        Channel Out Of Service :This OID
        indicates that the channel is out
        of service  <Help> This alarm indicates
        that the channel is in service
         <Condtype> CHANNEL1_OOS_1 <Probcause>
        informationalStatus(1000) <Alarmtype>
        other (1) <Polarity> (2)
        "
	::= { pmopm2Almchannel1PortEntry 7 }


pmopm2AlmChannel1PowerHighPortn OBJECT-TYPE
	SYNTAX  EkiOnOff
	MAX-ACCESS read-only
	STATUS current
	DESCRIPTION
        "
        Channel Power High :This OID indicates
        that the power of the channel is
        higher than the configured threshold<Help>
        This alarm indicates that the power
        of the channel is higher than the
        configured threshold <Condtype>
        CHANNEL1_POWER_HIGH_1 <Probcause>
        degradedSignal (13) <Alarmtype>
        equipmentAlarm <Polarity> (2)
        "
	::= { pmopm2Almchannel1PortEntry 6 }


pmopm2AlmChannel1PowerLowPortn OBJECT-TYPE
	SYNTAX  EkiOnOff
	MAX-ACCESS read-only
	STATUS current
	DESCRIPTION
        "
        Channel Power Low :This OID indicates
        that the power of the channel is
        lower than the configured threshold<Help>
        This alarm indicates that the power
        of the channel is lower than the
        configured threshold <Condtype>
        CHANNEL1_POWER_LOW_1 <Probcause>
        degradedSignal (13) <Alarmtype>
        equipmentAlarm <Polarity> (2)
        "
	::= { pmopm2Almchannel1PortEntry 5 }


pmopm2AlmChannel1BalancedPortn OBJECT-TYPE
	SYNTAX  EkiOnOff
	MAX-ACCESS read-only
	STATUS current
	DESCRIPTION
        "
        Channel Balanced :This OID indicates
        that an in service channel is balanced
        by the Ekinops auto turn up application<Help>
        This status indicates that an in
        service channel is balanced by
         the Ekinops auto turn up application
        <Condtype> CHANNEL1_BALANCED_1
         <Probcause> informationalStatus(1000)
        <Alarmtype> other (1) <Polarity>
        (2)
        "
	::= { pmopm2Almchannel1PortEntry 4 }


pmopm2AlmChannel1MismatchPortn OBJECT-TYPE
	SYNTAX  EkiOnOff
	MAX-ACCESS read-only
	STATUS current
	DESCRIPTION
        "
        Channel Mismatch :This OID indicates
        that an out of service channel
         is detected on the Optical Power
        Monitoring input<Help> This alarm
        indicates that an out of service
        channel is detected on the Optical
        Power Monitoring input <Condtype>
        CHANNEL1_MISMATCH_1 <Probcause>
        unexpectedInformation (75) <Alarmtype>
        equipmentAlarm <Polarity> (2)
        "
	::= { pmopm2Almchannel1PortEntry 3 }


pmopm2AlmChannel1AbsentPortn OBJECT-TYPE
	SYNTAX  EkiOnOff
	MAX-ACCESS read-only
	STATUS current
	DESCRIPTION
        "
        Channel Absent :This OID indicates
        that an in service channel is absent
        on the Optical Power Monitoring
        input<Help> This alarm indicates
        that an in service channel is absent
        on the Optical Power Monitoring
        input <Condtype> CHANNEL1_ABSENT_1
        <Probcause> informationMissing
         (65) <Alarmtype> equipmentAlarm
        (5) <Polarity> (2)
        "
	::= { pmopm2Almchannel1PortEntry 2 }


--- *********************************************************
---     TABLE for the pmopm2Almchannel2Port articles
--- *********************************************************

pmopm2Almchannel2PortTable OBJECT-TYPE
	SYNTAX  SEQUENCE OF Pmopm2Almchannel2PortEntry
	MAX-ACCESS not-accessible
	STATUS current
	DESCRIPTION
        "
        List of pmopm2Almchannel2Port
         Article
        "
	::= { pmopm2AlmClientCrit 18 }


pmopm2Almchannel2PortEntry OBJECT-TYPE
	SYNTAX Pmopm2Almchannel2PortEntry
	MAX-ACCESS not-accessible
	STATUS current
	DESCRIPTION
        "
        Row definition for the pmopm2Almchannel2Port
        table
        "
	INDEX   { pmopm2Almchannel2PortIndex }
	::= { pmopm2Almchannel2PortTable 1 }


Pmopm2Almchannel2PortEntry ::=
	SEQUENCE {
	pmopm2Almchannel2PortIndex
		INTEGER,
	pmopm2AlmChannel2OosPortn
		EkiOnOff,
	pmopm2AlmChannel2PowerHighPortn
		EkiOnOff,
	pmopm2AlmChannel2PowerLowPortn
		EkiOnOff,
	pmopm2AlmChannel2BalancedPortn
		EkiOnOff,
	pmopm2AlmChannel2MismatchPortn
		EkiOnOff,
	pmopm2AlmChannel2AbsentPortn
		EkiOnOff
	}


pmopm2Almchannel2PortIndex OBJECT-TYPE
	SYNTAX  INTEGER(0..128)
	MAX-ACCESS  read-only
	STATUS current
	DESCRIPTION
        "
        Index definition for the pmopm2Almchannel2Port
        table
        "
	::= { pmopm2Almchannel2PortEntry 1 }


pmopm2AlmChannel2OosPortn OBJECT-TYPE
	SYNTAX  EkiOnOff
	MAX-ACCESS read-only
	STATUS current
	DESCRIPTION
        "
        Channel Out Of Service 2 :This
        OID indicates that the channel
         is out of service  <Help> This
        alarm indicates that the channel
        is in service <Condtype> CHANNEL2_OOS_1
        <Probcause> informationalStatus(1000)
        <Alarmtype> other (1) <Polarity>
        (2)
        "
	::= { pmopm2Almchannel2PortEntry 7 }


pmopm2AlmChannel2PowerHighPortn OBJECT-TYPE
	SYNTAX  EkiOnOff
	MAX-ACCESS read-only
	STATUS current
	DESCRIPTION
        "
        Channel Power High 2 :This OID
        indicates that the power of the
        channel is higher than the configured
        threshold<Help> This alarm indicates
        that the power of the channel is
        higher than the configured threshold
        <Condtype> CHANNEL2_POWER_HIGH_1
        <Probcause> degradedSignal (13)
        <Alarmtype> equipmentAlarm <Polarity>
        (2)
        "
	::= { pmopm2Almchannel2PortEntry 6 }


pmopm2AlmChannel2PowerLowPortn OBJECT-TYPE
	SYNTAX  EkiOnOff
	MAX-ACCESS read-only
	STATUS current
	DESCRIPTION
        "
        Channel Power Low 2 :This OID
         indicates that the power of the
        channel is lower than the configured
        threshold<Help> This alarm indicates
        that the power of the channel is
        lower than the configured threshold
        <Condtype> CHANNEL2_POWER_LOW_1
        <Probcause> degradedSignal (13)
        <Alarmtype> equipmentAlarm <Polarity>
        (2)
        "
	::= { pmopm2Almchannel2PortEntry 5 }


pmopm2AlmChannel2BalancedPortn OBJECT-TYPE
	SYNTAX  EkiOnOff
	MAX-ACCESS read-only
	STATUS current
	DESCRIPTION
        "
        Channel Balanced 2 :This OID indicates
        that an in service channel is balanced
        by the Ekinops auto turn up application<Help>
        This status indicates that an in
        service channel is balanced by
         the Ekinops auto turn up application
        <Condtype> CHANNEL2_BALANCED_1
         <Probcause> informationalStatus(1000)
        <Alarmtype> other (1) <Polarity>
        (2)
        "
	::= { pmopm2Almchannel2PortEntry 4 }


pmopm2AlmChannel2MismatchPortn OBJECT-TYPE
	SYNTAX  EkiOnOff
	MAX-ACCESS read-only
	STATUS current
	DESCRIPTION
        "
        Channel Mismatch 2 :This OID indicates
        that an out of service channel
         is detected on the Optical Power
        Monitoring input<Help> This alarm
        indicates that an out of service
        channel is detected on the Optical
        Power Monitoring input <Condtype>
        CHANNEL2_MISMATCH_1 <Probcause>
        unexpectedInformation (75) <Alarmtype>
        equipmentAlarm <Polarity> (2)
        "
	::= { pmopm2Almchannel2PortEntry 3 }


pmopm2AlmChannel2AbsentPortn OBJECT-TYPE
	SYNTAX  EkiOnOff
	MAX-ACCESS read-only
	STATUS current
	DESCRIPTION
        "
        Channel Absent 2 :This OID indicates
        that an in service channel is absent
        on the Optical Power Monitoring
        input<Help> This alarm indicates
        that an in service channel is absent
        on the Optical Power Monitoring
        input <Condtype> CHANNEL2_ABSENT_1
        <Probcause> informationMissing
         (65) <Alarmtype> equipmentAlarm
        (5) <Polarity> (2)
        "
	::= { pmopm2Almchannel2PortEntry 2 }


--- *********************************************************
---     TABLE for the pmopm2Almchannel3Port articles
--- *********************************************************

pmopm2Almchannel3PortTable OBJECT-TYPE
	SYNTAX  SEQUENCE OF Pmopm2Almchannel3PortEntry
	MAX-ACCESS not-accessible
	STATUS current
	DESCRIPTION
        "
        List of pmopm2Almchannel3Port
         Article
        "
	::= { pmopm2AlmClientCrit 20 }


pmopm2Almchannel3PortEntry OBJECT-TYPE
	SYNTAX Pmopm2Almchannel3PortEntry
	MAX-ACCESS not-accessible
	STATUS current
	DESCRIPTION
        "
        Row definition for the pmopm2Almchannel3Port
        table
        "
	INDEX   { pmopm2Almchannel3PortIndex }
	::= { pmopm2Almchannel3PortTable 1 }


Pmopm2Almchannel3PortEntry ::=
	SEQUENCE {
	pmopm2Almchannel3PortIndex
		INTEGER,
	pmopm2AlmChannel3OosPortn
		EkiOnOff,
	pmopm2AlmChannel3PowerHighPortn
		EkiOnOff,
	pmopm2AlmChannel3PowerLowPortn
		EkiOnOff,
	pmopm2AlmChannel3BalancedPortn
		EkiOnOff,
	pmopm2AlmChannel3MismatchPortn
		EkiOnOff,
	pmopm2AlmChannel3AbsentPortn
		EkiOnOff
	}


pmopm2Almchannel3PortIndex OBJECT-TYPE
	SYNTAX  INTEGER(0..128)
	MAX-ACCESS  read-only
	STATUS current
	DESCRIPTION
        "
        Index definition for the pmopm2Almchannel3Port
        table
        "
	::= { pmopm2Almchannel3PortEntry 1 }


pmopm2AlmChannel3OosPortn OBJECT-TYPE
	SYNTAX  EkiOnOff
	MAX-ACCESS read-only
	STATUS current
	DESCRIPTION
        "
        Channel Out Of Service 3 :This
        OID indicates that the channel
         is out of service  <Help> This
        alarm indicates that the channel
        is in service <Condtype> CHANNEL3_OOS_1
        <Probcause> informationalStatus(1000)
        <Alarmtype> other (1) <Polarity>
        (2)
        "
	::= { pmopm2Almchannel3PortEntry 7 }


pmopm2AlmChannel3PowerHighPortn OBJECT-TYPE
	SYNTAX  EkiOnOff
	MAX-ACCESS read-only
	STATUS current
	DESCRIPTION
        "
        Channel Power High 3 :This OID
        indicates that the power of the
        channel is higher than the configured
        threshold<Help> This alarm indicates
        that the power of the channel is
        higher than the configured threshold
        <Condtype> CHANNEL3_POWER_HIGH_1
        <Probcause> degradedSignal (13)
        <Alarmtype> equipmentAlarm <Polarity>
        (2)
        "
	::= { pmopm2Almchannel3PortEntry 6 }


pmopm2AlmChannel3PowerLowPortn OBJECT-TYPE
	SYNTAX  EkiOnOff
	MAX-ACCESS read-only
	STATUS current
	DESCRIPTION
        "
        Channel Power Low 3 :This OID
         indicates that the power of the
        channel is lower than the configured
        threshold<Help> This alarm indicates
        that the power of the channel is
        lower than the configured threshold
        <Condtype> CHANNEL3_POWER_LOW_1
        <Probcause> degradedSignal (13)
        <Alarmtype> equipmentAlarm <Polarity>
        (2)
        "
	::= { pmopm2Almchannel3PortEntry 5 }


pmopm2AlmChannel3BalancedPortn OBJECT-TYPE
	SYNTAX  EkiOnOff
	MAX-ACCESS read-only
	STATUS current
	DESCRIPTION
        "
        Channel Balanced 3 :This OID indicates
        that an in service channel is balanced
        by the Ekinops auto turn up application<Help>
        This status indicates that an in
        service channel is balanced by
         the Ekinops auto turn up application
        <Condtype> CHANNEL3_BALANCED_1
         <Probcause> informationalStatus(1000)
        <Alarmtype> other (1) <Polarity>
        (2)
        "
	::= { pmopm2Almchannel3PortEntry 4 }


pmopm2AlmChannel3MismatchPortn OBJECT-TYPE
	SYNTAX  EkiOnOff
	MAX-ACCESS read-only
	STATUS current
	DESCRIPTION
        "
        Channel Mismatch 3 :This OID indicates
        that an out of service channel
         is detected on the Optical Power
        Monitoring input<Help> This alarm
        indicates that an out of service
        channel is detected on the Optical
        Power Monitoring input <Condtype>
        CHANNEL3_MISMATCH_1 <Probcause>
        unexpectedInformation (75) <Alarmtype>
        equipmentAlarm <Polarity> (2)
        "
	::= { pmopm2Almchannel3PortEntry 3 }


pmopm2AlmChannel3AbsentPortn OBJECT-TYPE
	SYNTAX  EkiOnOff
	MAX-ACCESS read-only
	STATUS current
	DESCRIPTION
        "
        Channel Absent 3 :This OID indicates
        that an in service channel is absent
        on the Optical Power Monitoring
        input<Help> This alarm indicates
        that an in service channel is absent
        on the Optical Power Monitoring
        input <Condtype> CHANNEL3_ABSENT_1
        <Probcause> informationMissing
         (65) <Alarmtype> equipmentAlarm
        (5) <Polarity> (2)
        "
	::= { pmopm2Almchannel3PortEntry 2 }


--- *********************************************************
---     TABLE for the pmopm2Almchannel4Port articles
--- *********************************************************

pmopm2Almchannel4PortTable OBJECT-TYPE
	SYNTAX  SEQUENCE OF Pmopm2Almchannel4PortEntry
	MAX-ACCESS not-accessible
	STATUS current
	DESCRIPTION
        "
        List of pmopm2Almchannel4Port
         Article
        "
	::= { pmopm2AlmClientCrit 22 }


pmopm2Almchannel4PortEntry OBJECT-TYPE
	SYNTAX Pmopm2Almchannel4PortEntry
	MAX-ACCESS not-accessible
	STATUS current
	DESCRIPTION
        "
        Row definition for the pmopm2Almchannel4Port
        table
        "
	INDEX   { pmopm2Almchannel4PortIndex }
	::= { pmopm2Almchannel4PortTable 1 }


Pmopm2Almchannel4PortEntry ::=
	SEQUENCE {
	pmopm2Almchannel4PortIndex
		INTEGER,
	pmopm2AlmChannel4OosPortn
		EkiOnOff,
	pmopm2AlmChannel4PowerHighPortn
		EkiOnOff,
	pmopm2AlmChannel4PowerLowPortn
		EkiOnOff,
	pmopm2AlmChannel4BalancedPortn
		EkiOnOff,
	pmopm2AlmChannel4MismatchPortn
		EkiOnOff,
	pmopm2AlmChannel4AbsentPortn
		EkiOnOff
	}


pmopm2Almchannel4PortIndex OBJECT-TYPE
	SYNTAX  INTEGER(0..128)
	MAX-ACCESS  read-only
	STATUS current
	DESCRIPTION
        "
        Index definition for the pmopm2Almchannel4Port
        table
        "
	::= { pmopm2Almchannel4PortEntry 1 }


pmopm2AlmChannel4OosPortn OBJECT-TYPE
	SYNTAX  EkiOnOff
	MAX-ACCESS read-only
	STATUS current
	DESCRIPTION
        "
        Channel Out Of Service 4 :This
        OID indicates that the channel
         is out of service  <Help> This
        alarm indicates that the channel
        is in service <Condtype> CHANNEL4_OOS_1
        <Probcause> informationalStatus(1000)
        <Alarmtype> other (1) <Polarity>
        (2)
        "
	::= { pmopm2Almchannel4PortEntry 7 }


pmopm2AlmChannel4PowerHighPortn OBJECT-TYPE
	SYNTAX  EkiOnOff
	MAX-ACCESS read-only
	STATUS current
	DESCRIPTION
        "
        Channel Power High 4 :This OID
        indicates that the power of the
        channel is higher than the configured
        threshold<Help> This alarm indicates
        that the power of the channel is
        higher than the configured threshold
        <Condtype> CHANNEL4_POWER_HIGH_1
        <Probcause> degradedSignal (13)
        <Alarmtype> equipmentAlarm <Polarity>
        (2)
        "
	::= { pmopm2Almchannel4PortEntry 6 }


pmopm2AlmChannel4PowerLowPortn OBJECT-TYPE
	SYNTAX  EkiOnOff
	MAX-ACCESS read-only
	STATUS current
	DESCRIPTION
        "
        Channel Power Low 4 :This OID
         indicates that the power of the
        channel is lower than the configured
        threshold<Help> This alarm indicates
        that the power of the channel is
        lower than the configured threshold
        <Condtype> CHANNEL4_POWER_LOW_1
        <Probcause> degradedSignal (13)
        <Alarmtype> equipmentAlarm <Polarity>
        (2)
        "
	::= { pmopm2Almchannel4PortEntry 5 }


pmopm2AlmChannel4BalancedPortn OBJECT-TYPE
	SYNTAX  EkiOnOff
	MAX-ACCESS read-only
	STATUS current
	DESCRIPTION
        "
        Channel Balanced 4 :This OID indicates
        that an in service channel is balanced
        by the Ekinops auto turn up application<Help>
        This status indicates that an in
        service channel is balanced by
         the Ekinops auto turn up application
        <Condtype> CHANNEL4_BALANCED_1
         <Probcause> informationalStatus(1000)
        <Alarmtype> other (1) <Polarity>
        (2)
        "
	::= { pmopm2Almchannel4PortEntry 4 }


pmopm2AlmChannel4MismatchPortn OBJECT-TYPE
	SYNTAX  EkiOnOff
	MAX-ACCESS read-only
	STATUS current
	DESCRIPTION
        "
        Channel Mismatch 4 :This OID indicates
        that an out of service channel
         is detected on the Optical Power
        Monitoring input<Help> This alarm
        indicates that an out of service
        channel is detected on the Optical
        Power Monitoring input <Condtype>
        CHANNEL4_MISMATCH_1 <Probcause>
        unexpectedInformation (75) <Alarmtype>
        equipmentAlarm <Polarity> (2)
        "
	::= { pmopm2Almchannel4PortEntry 3 }


pmopm2AlmChannel4AbsentPortn OBJECT-TYPE
	SYNTAX  EkiOnOff
	MAX-ACCESS read-only
	STATUS current
	DESCRIPTION
        "
        Channel Absent 4 :This OID indicates
        that an in service channel is absent
        on the Optical Power Monitoring
        input<Help> This alarm indicates
        that an in service channel is absent
        on the Optical Power Monitoring
        input <Condtype> CHANNEL4_ABSENT_1
        <Probcause> informationMissing
         (65) <Alarmtype> equipmentAlarm
        (5) <Polarity> (2)
        "
	::= { pmopm2Almchannel4PortEntry 2 }


--- *********************************************************
---     TABLE for the pmopm2Almchannel5Port articles
--- *********************************************************

pmopm2Almchannel5PortTable OBJECT-TYPE
	SYNTAX  SEQUENCE OF Pmopm2Almchannel5PortEntry
	MAX-ACCESS not-accessible
	STATUS current
	DESCRIPTION
        "
        List of pmopm2Almchannel5Port
         Article
        "
	::= { pmopm2AlmClientCrit 24 }


pmopm2Almchannel5PortEntry OBJECT-TYPE
	SYNTAX Pmopm2Almchannel5PortEntry
	MAX-ACCESS not-accessible
	STATUS current
	DESCRIPTION
        "
        Row definition for the pmopm2Almchannel5Port
        table
        "
	INDEX   { pmopm2Almchannel5PortIndex }
	::= { pmopm2Almchannel5PortTable 1 }


Pmopm2Almchannel5PortEntry ::=
	SEQUENCE {
	pmopm2Almchannel5PortIndex
		INTEGER,
	pmopm2AlmChannel5OosPortn
		EkiOnOff,
	pmopm2AlmChannel5PowerHighPortn
		EkiOnOff,
	pmopm2AlmChannel5PowerLowPortn
		EkiOnOff,
	pmopm2AlmChannel5BalancedPortn
		EkiOnOff,
	pmopm2AlmChannel5MismatchPortn
		EkiOnOff,
	pmopm2AlmChannel5AbsentPortn
		EkiOnOff
	}


pmopm2Almchannel5PortIndex OBJECT-TYPE
	SYNTAX  INTEGER(0..128)
	MAX-ACCESS  read-only
	STATUS current
	DESCRIPTION
        "
        Index definition for the pmopm2Almchannel5Port
        table
        "
	::= { pmopm2Almchannel5PortEntry 1 }


pmopm2AlmChannel5OosPortn OBJECT-TYPE
	SYNTAX  EkiOnOff
	MAX-ACCESS read-only
	STATUS current
	DESCRIPTION
        "
        Channel Out Of Service 5 :This
        OID indicates that the channel
         is out of service  <Help> This
        alarm indicates that the channel
        is in service <Condtype> CHANNEL5_OOS_1
        <Probcause> informationalStatus(1000)
        <Alarmtype> other (1) <Polarity>
        (2)
        "
	::= { pmopm2Almchannel5PortEntry 7 }


pmopm2AlmChannel5PowerHighPortn OBJECT-TYPE
	SYNTAX  EkiOnOff
	MAX-ACCESS read-only
	STATUS current
	DESCRIPTION
        "
        Channel Power High 5 :This OID
        indicates that the power of the
        channel is higher than the configured
        threshold<Help> This alarm indicates
        that the power of the channel is
        higher than the configured threshold
        <Condtype> CHANNEL5_POWER_HIGH_1
        <Probcause> degradedSignal (13)
        <Alarmtype> equipmentAlarm <Polarity>
        (2)
        "
	::= { pmopm2Almchannel5PortEntry 6 }


pmopm2AlmChannel5PowerLowPortn OBJECT-TYPE
	SYNTAX  EkiOnOff
	MAX-ACCESS read-only
	STATUS current
	DESCRIPTION
        "
        Channel Power Low 5 :This OID
         indicates that the power of the
        channel is lower than the configured
        threshold<Help> This alarm indicates
        that the power of the channel is
        lower than the configured threshold
        <Condtype> CHANNEL5_POWER_LOW_1
        <Probcause> degradedSignal (13)
        <Alarmtype> equipmentAlarm <Polarity>
        (2)
        "
	::= { pmopm2Almchannel5PortEntry 5 }


pmopm2AlmChannel5BalancedPortn OBJECT-TYPE
	SYNTAX  EkiOnOff
	MAX-ACCESS read-only
	STATUS current
	DESCRIPTION
        "
        Channel Balanced 5 :This OID indicates
        that an in service channel is balanced
        by the Ekinops auto turn up application<Help>
        This status indicates that an in
        service channel is balanced by
         the Ekinops auto turn up application
        <Condtype> CHANNEL5_BALANCED_1
         <Probcause> informationalStatus(1000)
        <Alarmtype> other (1) <Polarity>
        (2)
        "
	::= { pmopm2Almchannel5PortEntry 4 }


pmopm2AlmChannel5MismatchPortn OBJECT-TYPE
	SYNTAX  EkiOnOff
	MAX-ACCESS read-only
	STATUS current
	DESCRIPTION
        "
        Channel Mismatch 5 :This OID indicates
        that an out of service channel
         is detected on the Optical Power
        Monitoring input<Help> This alarm
        indicates that an out of service
        channel is detected on the Optical
        Power Monitoring input <Condtype>
        CHANNEL5_MISMATCH_1 <Probcause>
        unexpectedInformation (75) <Alarmtype>
        equipmentAlarm <Polarity> (2)
        "
	::= { pmopm2Almchannel5PortEntry 3 }


pmopm2AlmChannel5AbsentPortn OBJECT-TYPE
	SYNTAX  EkiOnOff
	MAX-ACCESS read-only
	STATUS current
	DESCRIPTION
        "
        Channel Absent 5 :This OID indicates
        that an in service channel is absent
        on the Optical Power Monitoring
        input<Help> This alarm indicates
        that an in service channel is absent
        on the Optical Power Monitoring
        input <Condtype> CHANNEL5_ABSENT_1
        <Probcause> informationMissing
         (65) <Alarmtype> equipmentAlarm
        (5) <Polarity> (2)
        "
	::= { pmopm2Almchannel5PortEntry 2 }


--- *********************************************************
---     TABLE for the pmopm2Almchannel6Port articles
--- *********************************************************

pmopm2Almchannel6PortTable OBJECT-TYPE
	SYNTAX  SEQUENCE OF Pmopm2Almchannel6PortEntry
	MAX-ACCESS not-accessible
	STATUS current
	DESCRIPTION
        "
        List of pmopm2Almchannel6Port
         Article
        "
	::= { pmopm2AlmClientCrit 26 }


pmopm2Almchannel6PortEntry OBJECT-TYPE
	SYNTAX Pmopm2Almchannel6PortEntry
	MAX-ACCESS not-accessible
	STATUS current
	DESCRIPTION
        "
        Row definition for the pmopm2Almchannel6Port
        table
        "
	INDEX   { pmopm2Almchannel6PortIndex }
	::= { pmopm2Almchannel6PortTable 1 }


Pmopm2Almchannel6PortEntry ::=
	SEQUENCE {
	pmopm2Almchannel6PortIndex
		INTEGER,
	pmopm2AlmChannel6OosPortn
		EkiOnOff,
	pmopm2AlmChannel6PowerHighPortn
		EkiOnOff,
	pmopm2AlmChannel6PowerLowPortn
		EkiOnOff,
	pmopm2AlmChannel6BalancedPortn
		EkiOnOff,
	pmopm2AlmChannel6MismatchPortn
		EkiOnOff,
	pmopm2AlmChannel6AbsentPortn
		EkiOnOff
	}


pmopm2Almchannel6PortIndex OBJECT-TYPE
	SYNTAX  INTEGER(0..128)
	MAX-ACCESS  read-only
	STATUS current
	DESCRIPTION
        "
        Index definition for the pmopm2Almchannel6Port
        table
        "
	::= { pmopm2Almchannel6PortEntry 1 }


pmopm2AlmChannel6OosPortn OBJECT-TYPE
	SYNTAX  EkiOnOff
	MAX-ACCESS read-only
	STATUS current
	DESCRIPTION
        "
        Channel Out Of Service 6 :This
        OID indicates that the channel
         is out of service  <Help> This
        alarm indicates that the channel
        is in service <Condtype> CHANNEL6_OOS_1
        <Probcause> informationalStatus(1000)
        <Alarmtype> other (1) <Polarity>
        (2)
        "
	::= { pmopm2Almchannel6PortEntry 7 }


pmopm2AlmChannel6PowerHighPortn OBJECT-TYPE
	SYNTAX  EkiOnOff
	MAX-ACCESS read-only
	STATUS current
	DESCRIPTION
        "
        Channel Power High 6 :This OID
        indicates that the power of the
        channel is higher than the configured
        threshold<Help> This alarm indicates
        that the power of the channel is
        higher than the configured threshold
        <Condtype> CHANNEL6_POWER_HIGH_1
        <Probcause> degradedSignal (13)
        <Alarmtype> equipmentAlarm <Polarity>
        (2)
        "
	::= { pmopm2Almchannel6PortEntry 6 }


pmopm2AlmChannel6PowerLowPortn OBJECT-TYPE
	SYNTAX  EkiOnOff
	MAX-ACCESS read-only
	STATUS current
	DESCRIPTION
        "
        Channel Power Low 6 :This OID
         indicates that the power of the
        channel is lower than the configured
        threshold<Help> This alarm indicates
        that the power of the channel is
        lower than the configured threshold
        <Condtype> CHANNEL6_POWER_LOW_1
        <Probcause> degradedSignal (13)
        <Alarmtype> equipmentAlarm <Polarity>
        (2)
        "
	::= { pmopm2Almchannel6PortEntry 5 }


pmopm2AlmChannel6BalancedPortn OBJECT-TYPE
	SYNTAX  EkiOnOff
	MAX-ACCESS read-only
	STATUS current
	DESCRIPTION
        "
        Channel Balanced 6 :This OID indicates
        that an in service channel is balanced
        by the Ekinops auto turn up application<Help>
        This status indicates that an in
        service channel is balanced by
         the Ekinops auto turn up application
        <Condtype> CHANNEL6_BALANCED_1
         <Probcause> informationalStatus(1000)
        <Alarmtype> other (1) <Polarity>
        (2)
        "
	::= { pmopm2Almchannel6PortEntry 4 }


pmopm2AlmChannel6MismatchPortn OBJECT-TYPE
	SYNTAX  EkiOnOff
	MAX-ACCESS read-only
	STATUS current
	DESCRIPTION
        "
        Channel Mismatch 6 :This OID indicates
        that an out of service channel
         is detected on the Optical Power
        Monitoring input<Help> This alarm
        indicates that an out of service
        channel is detected on the Optical
        Power Monitoring input <Condtype>
        CHANNEL6_MISMATCH_1 <Probcause>
        unexpectedInformation (75) <Alarmtype>
        equipmentAlarm <Polarity> (2)
        "
	::= { pmopm2Almchannel6PortEntry 3 }


pmopm2AlmChannel6AbsentPortn OBJECT-TYPE
	SYNTAX  EkiOnOff
	MAX-ACCESS read-only
	STATUS current
	DESCRIPTION
        "
        Channel Absent 6 :This OID indicates
        that an in service channel is absent
        on the Optical Power Monitoring
        input<Help> This alarm indicates
        that an in service channel is absent
        on the Optical Power Monitoring
        input <Condtype> CHANNEL6_ABSENT_1
        <Probcause> informationMissing
         (65) <Alarmtype> equipmentAlarm
        (5) <Polarity> (2)
        "
	::= { pmopm2Almchannel6PortEntry 2 }


--- *********************************************************
---     TABLE for the pmopm2Almchannel7Port articles
--- *********************************************************

pmopm2Almchannel7PortTable OBJECT-TYPE
	SYNTAX  SEQUENCE OF Pmopm2Almchannel7PortEntry
	MAX-ACCESS not-accessible
	STATUS current
	DESCRIPTION
        "
        List of pmopm2Almchannel7Port
         Article
        "
	::= { pmopm2AlmClientCrit 28 }


pmopm2Almchannel7PortEntry OBJECT-TYPE
	SYNTAX Pmopm2Almchannel7PortEntry
	MAX-ACCESS not-accessible
	STATUS current
	DESCRIPTION
        "
        Row definition for the pmopm2Almchannel7Port
        table
        "
	INDEX   { pmopm2Almchannel7PortIndex }
	::= { pmopm2Almchannel7PortTable 1 }


Pmopm2Almchannel7PortEntry ::=
	SEQUENCE {
	pmopm2Almchannel7PortIndex
		INTEGER,
	pmopm2AlmChannel7OosPortn
		EkiOnOff,
	pmopm2AlmChannel7PowerHighPortn
		EkiOnOff,
	pmopm2AlmChannel7PowerLowPortn
		EkiOnOff,
	pmopm2AlmChannel7BalancedPortn
		EkiOnOff,
	pmopm2AlmChannel7MismatchPortn
		EkiOnOff,
	pmopm2AlmChannel7AbsentPortn
		EkiOnOff
	}


pmopm2Almchannel7PortIndex OBJECT-TYPE
	SYNTAX  INTEGER(0..128)
	MAX-ACCESS  read-only
	STATUS current
	DESCRIPTION
        "
        Index definition for the pmopm2Almchannel7Port
        table
        "
	::= { pmopm2Almchannel7PortEntry 1 }


pmopm2AlmChannel7OosPortn OBJECT-TYPE
	SYNTAX  EkiOnOff
	MAX-ACCESS read-only
	STATUS current
	DESCRIPTION
        "
        Channel Out Of Service 7 :This
        OID indicates that the channel
         is out of service  <Help> This
        alarm indicates that the channel
        is in service <Condtype> CHANNEL7_OOS_1
        <Probcause> informationalStatus(1000)
        <Alarmtype> other (1) <Polarity>
        (2)
        "
	::= { pmopm2Almchannel7PortEntry 7 }


pmopm2AlmChannel7PowerHighPortn OBJECT-TYPE
	SYNTAX  EkiOnOff
	MAX-ACCESS read-only
	STATUS current
	DESCRIPTION
        "
        Channel Power High 7 :This OID
        indicates that the power of the
        channel is higher than the configured
        threshold<Help> This alarm indicates
        that the power of the channel is
        higher than the configured threshold
        <Condtype> CHANNEL7_POWER_HIGH_1
        <Probcause> degradedSignal (13)
        <Alarmtype> equipmentAlarm <Polarity>
        (2)
        "
	::= { pmopm2Almchannel7PortEntry 6 }


pmopm2AlmChannel7PowerLowPortn OBJECT-TYPE
	SYNTAX  EkiOnOff
	MAX-ACCESS read-only
	STATUS current
	DESCRIPTION
        "
        Channel Power Low 7 :This OID
         indicates that the power of the
        channel is lower than the configured
        threshold<Help> This alarm indicates
        that the power of the channel is
        lower than the configured threshold
        <Condtype> CHANNEL7_POWER_LOW_1
        <Probcause> degradedSignal (13)
        <Alarmtype> equipmentAlarm <Polarity>
        (2)
        "
	::= { pmopm2Almchannel7PortEntry 5 }


pmopm2AlmChannel7BalancedPortn OBJECT-TYPE
	SYNTAX  EkiOnOff
	MAX-ACCESS read-only
	STATUS current
	DESCRIPTION
        "
        Channel Balanced 7 :This OID indicates
        that an in service channel is balanced
        by the Ekinops auto turn up application<Help>
        This status indicates that an in
        service channel is balanced by
         the Ekinops auto turn up application
        <Condtype> CHANNEL7_BALANCED_1
         <Probcause> informationalStatus(1000)
        <Alarmtype> other (1) <Polarity>
        (2)
        "
	::= { pmopm2Almchannel7PortEntry 4 }


pmopm2AlmChannel7MismatchPortn OBJECT-TYPE
	SYNTAX  EkiOnOff
	MAX-ACCESS read-only
	STATUS current
	DESCRIPTION
        "
        Channel Mismatch 7 :This OID indicates
        that an out of service channel
         is detected on the Optical Power
        Monitoring input<Help> This alarm
        indicates that an out of service
        channel is detected on the Optical
        Power Monitoring input <Condtype>
        CHANNEL7_MISMATCH_1 <Probcause>
        unexpectedInformation (75) <Alarmtype>
        equipmentAlarm <Polarity> (2)
        "
	::= { pmopm2Almchannel7PortEntry 3 }


pmopm2AlmChannel7AbsentPortn OBJECT-TYPE
	SYNTAX  EkiOnOff
	MAX-ACCESS read-only
	STATUS current
	DESCRIPTION
        "
        Channel Absent 7 :This OID indicates
        that an in service channel is absent
        on the Optical Power Monitoring
        input<Help> This alarm indicates
        that an in service channel is absent
        on the Optical Power Monitoring
        input <Condtype> CHANNEL7_ABSENT_1
        <Probcause> informationMissing
         (65) <Alarmtype> equipmentAlarm
        (5) <Polarity> (2)
        "
	::= { pmopm2Almchannel7PortEntry 2 }


--- *********************************************************
---     TABLE for the pmopm2Almchannel8Port articles
--- *********************************************************

pmopm2Almchannel8PortTable OBJECT-TYPE
	SYNTAX  SEQUENCE OF Pmopm2Almchannel8PortEntry
	MAX-ACCESS not-accessible
	STATUS current
	DESCRIPTION
        "
        List of pmopm2Almchannel8Port
         Article
        "
	::= { pmopm2AlmClientCrit 30 }


pmopm2Almchannel8PortEntry OBJECT-TYPE
	SYNTAX Pmopm2Almchannel8PortEntry
	MAX-ACCESS not-accessible
	STATUS current
	DESCRIPTION
        "
        Row definition for the pmopm2Almchannel8Port
        table
        "
	INDEX   { pmopm2Almchannel8PortIndex }
	::= { pmopm2Almchannel8PortTable 1 }


Pmopm2Almchannel8PortEntry ::=
	SEQUENCE {
	pmopm2Almchannel8PortIndex
		INTEGER,
	pmopm2AlmChannel8OosPortn
		EkiOnOff,
	pmopm2AlmChannel8PowerHighPortn
		EkiOnOff,
	pmopm2AlmChannel8PowerLowPortn
		EkiOnOff,
	pmopm2AlmChannel8BalancedPortn
		EkiOnOff,
	pmopm2AlmChannel8MismatchPortn
		EkiOnOff,
	pmopm2AlmChannel8AbsentPortn
		EkiOnOff
	}


pmopm2Almchannel8PortIndex OBJECT-TYPE
	SYNTAX  INTEGER(0..128)
	MAX-ACCESS  read-only
	STATUS current
	DESCRIPTION
        "
        Index definition for the pmopm2Almchannel8Port
        table
        "
	::= { pmopm2Almchannel8PortEntry 1 }


pmopm2AlmChannel8OosPortn OBJECT-TYPE
	SYNTAX  EkiOnOff
	MAX-ACCESS read-only
	STATUS current
	DESCRIPTION
        "
        Channel Out Of Service 8 :This
        OID indicates that the channel
         is out of service  <Help> This
        alarm indicates that the channel
        is in service <Condtype> CHANNEL8_OOS_1
        <Probcause> informationalStatus(1000)
        <Alarmtype> other (1) <Polarity>
        (2)
        "
	::= { pmopm2Almchannel8PortEntry 7 }


pmopm2AlmChannel8PowerHighPortn OBJECT-TYPE
	SYNTAX  EkiOnOff
	MAX-ACCESS read-only
	STATUS current
	DESCRIPTION
        "
        Channel Power High 8 :This OID
        indicates that the power of the
        channel is higher than the configured
        threshold<Help> This alarm indicates
        that the power of the channel is
        higher than the configured threshold
        <Condtype> CHANNEL8_POWER_HIGH_1
        <Probcause> degradedSignal (13)
        <Alarmtype> equipmentAlarm <Polarity>
        (2)
        "
	::= { pmopm2Almchannel8PortEntry 6 }


pmopm2AlmChannel8PowerLowPortn OBJECT-TYPE
	SYNTAX  EkiOnOff
	MAX-ACCESS read-only
	STATUS current
	DESCRIPTION
        "
        Channel Power Low 8 :This OID
         indicates that the power of the
        channel is lower than the configured
        threshold<Help> This alarm indicates
        that the power of the channel is
        lower than the configured threshold
        <Condtype> CHANNEL8_POWER_LOW_1
        <Probcause> degradedSignal (13)
        <Alarmtype> equipmentAlarm <Polarity>
        (2)
        "
	::= { pmopm2Almchannel8PortEntry 5 }


pmopm2AlmChannel8BalancedPortn OBJECT-TYPE
	SYNTAX  EkiOnOff
	MAX-ACCESS read-only
	STATUS current
	DESCRIPTION
        "
        Channel Balanced 8 :This OID indicates
        that an in service channel is balanced
        by the Ekinops auto turn up application<Help>
        This status indicates that an in
        service channel is balanced by
         the Ekinops auto turn up application
        <Condtype> CHANNEL8_BALANCED_1
         <Probcause> informationalStatus(1000)
        <Alarmtype> other (1) <Polarity>
        (2)
        "
	::= { pmopm2Almchannel8PortEntry 4 }


pmopm2AlmChannel8MismatchPortn OBJECT-TYPE
	SYNTAX  EkiOnOff
	MAX-ACCESS read-only
	STATUS current
	DESCRIPTION
        "
        Channel Mismatch 8 :This OID indicates
        that an out of service channel
         is detected on the Optical Power
        Monitoring input<Help> This alarm
        indicates that an out of service
        channel is detected on the Optical
        Power Monitoring input <Condtype>
        CHANNEL8_MISMATCH_1 <Probcause>
        unexpectedInformation (75) <Alarmtype>
        equipmentAlarm <Polarity> (2)
        "
	::= { pmopm2Almchannel8PortEntry 3 }


pmopm2AlmChannel8AbsentPortn OBJECT-TYPE
	SYNTAX  EkiOnOff
	MAX-ACCESS read-only
	STATUS current
	DESCRIPTION
        "
        Channel Absent 8 :This OID indicates
        that an in service channel is absent
        on the Optical Power Monitoring
        input<Help> This alarm indicates
        that an in service channel is absent
        on the Optical Power Monitoring
        input <Condtype> CHANNEL8_ABSENT_1
        <Probcause> informationMissing
         (65) <Alarmtype> equipmentAlarm
        (5) <Polarity> (2)
        "
	::= { pmopm2Almchannel8PortEntry 2 }


--- *********************************************************
---     TABLE for the pmopm2Almchannel9Port articles
--- *********************************************************

pmopm2Almchannel9PortTable OBJECT-TYPE
	SYNTAX  SEQUENCE OF Pmopm2Almchannel9PortEntry
	MAX-ACCESS not-accessible
	STATUS current
	DESCRIPTION
        "
        List of pmopm2Almchannel9Port
         Article
        "
	::= { pmopm2AlmClientCrit 32 }


pmopm2Almchannel9PortEntry OBJECT-TYPE
	SYNTAX Pmopm2Almchannel9PortEntry
	MAX-ACCESS not-accessible
	STATUS current
	DESCRIPTION
        "
        Row definition for the pmopm2Almchannel9Port
        table
        "
	INDEX   { pmopm2Almchannel9PortIndex }
	::= { pmopm2Almchannel9PortTable 1 }


Pmopm2Almchannel9PortEntry ::=
	SEQUENCE {
	pmopm2Almchannel9PortIndex
		INTEGER,
	pmopm2AlmChannel9OosPortn
		EkiOnOff,
	pmopm2AlmChannel9PowerHighPortn
		EkiOnOff,
	pmopm2AlmChannel9PowerLowPortn
		EkiOnOff,
	pmopm2AlmChannel9BalancedPortn
		EkiOnOff,
	pmopm2AlmChannel9MismatchPortn
		EkiOnOff,
	pmopm2AlmChannel9AbsentPortn
		EkiOnOff
	}


pmopm2Almchannel9PortIndex OBJECT-TYPE
	SYNTAX  INTEGER(0..128)
	MAX-ACCESS  read-only
	STATUS current
	DESCRIPTION
        "
        Index definition for the pmopm2Almchannel9Port
        table
        "
	::= { pmopm2Almchannel9PortEntry 1 }


pmopm2AlmChannel9OosPortn OBJECT-TYPE
	SYNTAX  EkiOnOff
	MAX-ACCESS read-only
	STATUS current
	DESCRIPTION
        "
        Channel Out Of Service 9 :This
        OID indicates that the channel
         is out of service  <Help> This
        alarm indicates that the channel
        is in service <Condtype> CHANNEL9_OOS_1
        <Probcause> informationalStatus(1000)
        <Alarmtype> other (1) <Polarity>
        (2)
        "
	::= { pmopm2Almchannel9PortEntry 7 }


pmopm2AlmChannel9PowerHighPortn OBJECT-TYPE
	SYNTAX  EkiOnOff
	MAX-ACCESS read-only
	STATUS current
	DESCRIPTION
        "
        Channel Power High 9 :This OID
        indicates that the power of the
        channel is higher than the configured
        threshold<Help> This alarm indicates
        that the power of the channel is
        higher than the configured threshold
        <Condtype> CHANNEL9_POWER_HIGH_1
        <Probcause> degradedSignal (13)
        <Alarmtype> equipmentAlarm <Polarity>
        (2)
        "
	::= { pmopm2Almchannel9PortEntry 6 }


pmopm2AlmChannel9PowerLowPortn OBJECT-TYPE
	SYNTAX  EkiOnOff
	MAX-ACCESS read-only
	STATUS current
	DESCRIPTION
        "
        Channel Power Low 9 :This OID
         indicates that the power of the
        channel is lower than the configured
        threshold<Help> This alarm indicates
        that the power of the channel is
        lower than the configured threshold
        <Condtype> CHANNEL9_POWER_LOW_1
        <Probcause> degradedSignal (13)
        <Alarmtype> equipmentAlarm <Polarity>
        (2)
        "
	::= { pmopm2Almchannel9PortEntry 5 }


pmopm2AlmChannel9BalancedPortn OBJECT-TYPE
	SYNTAX  EkiOnOff
	MAX-ACCESS read-only
	STATUS current
	DESCRIPTION
        "
        Channel Balanced 9 :This OID indicates
        that an in service channel is balanced
        by the Ekinops auto turn up application<Help>
        This status indicates that an in
        service channel is balanced by
         the Ekinops auto turn up application
        <Condtype> CHANNEL9_BALANCED_1
         <Probcause> informationalStatus(1000)
        <Alarmtype> other (1) <Polarity>
        (2)
        "
	::= { pmopm2Almchannel9PortEntry 4 }


pmopm2AlmChannel9MismatchPortn OBJECT-TYPE
	SYNTAX  EkiOnOff
	MAX-ACCESS read-only
	STATUS current
	DESCRIPTION
        "
        Channel Mismatch 9 :This OID indicates
        that an out of service channel
         is detected on the Optical Power
        Monitoring input<Help> This alarm
        indicates that an out of service
        channel is detected on the Optical
        Power Monitoring input <Condtype>
        CHANNEL9_MISMATCH_1 <Probcause>
        unexpectedInformation (75) <Alarmtype>
        equipmentAlarm <Polarity> (2)
        "
	::= { pmopm2Almchannel9PortEntry 3 }


pmopm2AlmChannel9AbsentPortn OBJECT-TYPE
	SYNTAX  EkiOnOff
	MAX-ACCESS read-only
	STATUS current
	DESCRIPTION
        "
        Channel Absent 9 :This OID indicates
        that an in service channel is absent
        on the Optical Power Monitoring
        input<Help> This alarm indicates
        that an in service channel is absent
        on the Optical Power Monitoring
        input <Condtype> CHANNEL9_ABSENT_1
        <Probcause> informationMissing
         (65) <Alarmtype> equipmentAlarm
        (5) <Polarity> (2)
        "
	::= { pmopm2Almchannel9PortEntry 2 }


--- *********************************************************
---     TABLE for the pmopm2Almchannel10Port articles
--- *********************************************************

pmopm2Almchannel10PortTable OBJECT-TYPE
	SYNTAX  SEQUENCE OF Pmopm2Almchannel10PortEntry
	MAX-ACCESS not-accessible
	STATUS current
	DESCRIPTION
        "
        List of pmopm2Almchannel10Port
        Article
        "
	::= { pmopm2AlmClientCrit 34 }


pmopm2Almchannel10PortEntry OBJECT-TYPE
	SYNTAX Pmopm2Almchannel10PortEntry
	MAX-ACCESS not-accessible
	STATUS current
	DESCRIPTION
        "
        Row definition for the pmopm2Almchannel10Port
        table
        "
	INDEX   { pmopm2Almchannel10PortIndex }
	::= { pmopm2Almchannel10PortTable 1 }


Pmopm2Almchannel10PortEntry ::=
	SEQUENCE {
	pmopm2Almchannel10PortIndex
		INTEGER,
	pmopm2AlmChannel10OosPortn
		EkiOnOff,
	pmopm2AlmChannel10PowerHighPortn
		EkiOnOff,
	pmopm2AlmChannel10PowerLowPortn
		EkiOnOff,
	pmopm2AlmChannel10BalancedPortn
		EkiOnOff,
	pmopm2AlmChannel10MismatchPortn
		EkiOnOff,
	pmopm2AlmChannel10AbsentPortn
		EkiOnOff
	}


pmopm2Almchannel10PortIndex OBJECT-TYPE
	SYNTAX  INTEGER(0..128)
	MAX-ACCESS  read-only
	STATUS current
	DESCRIPTION
        "
        Index definition for the pmopm2Almchannel10Port
        table
        "
	::= { pmopm2Almchannel10PortEntry 1 }


pmopm2AlmChannel10OosPortn OBJECT-TYPE
	SYNTAX  EkiOnOff
	MAX-ACCESS read-only
	STATUS current
	DESCRIPTION
        "
        Channel Out Of Service 10 :This
        OID indicates that the channel
         is out of service  <Help> This
        alarm indicates that the channel
        is in service <Condtype> CHANNEL10_OOS_1
        <Probcause> informationalStatus(1000)
        <Alarmtype> other (1) <Polarity>
        (2)
        "
	::= { pmopm2Almchannel10PortEntry 7 }


pmopm2AlmChannel10PowerHighPortn OBJECT-TYPE
	SYNTAX  EkiOnOff
	MAX-ACCESS read-only
	STATUS current
	DESCRIPTION
        "
        Channel Power High 10 :This OID
        indicates that the power of the
        channel is higher than the configured
        threshold<Help> This alarm indicates
        that the power of the channel is
        higher than the configured threshold
        <Condtype> CHANNEL10_POWER_HIGH_1
        <Probcause> degradedSignal (13)
        <Alarmtype> equipmentAlarm <Polarity>
        (2)
        "
	::= { pmopm2Almchannel10PortEntry 6 }


pmopm2AlmChannel10PowerLowPortn OBJECT-TYPE
	SYNTAX  EkiOnOff
	MAX-ACCESS read-only
	STATUS current
	DESCRIPTION
        "
        Channel Power Low 10 :This OID
        indicates that the power of the
        channel is lower than the configured
        threshold<Help> This alarm indicates
        that the power of the channel is
        lower than the configured threshold
        <Condtype> CHANNEL10_POWER_LOW_1
        <Probcause> degradedSignal (13)
        <Alarmtype> equipmentAlarm <Polarity>
        (2)
        "
	::= { pmopm2Almchannel10PortEntry 5 }


pmopm2AlmChannel10BalancedPortn OBJECT-TYPE
	SYNTAX  EkiOnOff
	MAX-ACCESS read-only
	STATUS current
	DESCRIPTION
        "
        Channel Balanced 10 :This OID
         indicates that an in service channel
        is balanced by the Ekinops auto
        turn up application<Help> This
         status indicates that an in service
        channel is balanced by the Ekinops
        auto turn up application <Condtype>
        CHANNEL10_BALANCED_1 <Probcause>
        informationalStatus(1000) <Alarmtype>
        other (1) <Polarity> (2)
        "
	::= { pmopm2Almchannel10PortEntry 4 }


pmopm2AlmChannel10MismatchPortn OBJECT-TYPE
	SYNTAX  EkiOnOff
	MAX-ACCESS read-only
	STATUS current
	DESCRIPTION
        "
        Channel Mismatch 10 :This OID
         indicates that an out of service
        channel is detected on the Optical
        Power Monitoring input<Help> This
        alarm indicates that an out of
         service channel is detected on
        the Optical Power Monitoring input
        <Condtype> CHANNEL10_MISMATCH_1
        <Probcause> unexpectedInformation
        (75) <Alarmtype> equipmentAlarm
        <Polarity> (2)
        "
	::= { pmopm2Almchannel10PortEntry 3 }


pmopm2AlmChannel10AbsentPortn OBJECT-TYPE
	SYNTAX  EkiOnOff
	MAX-ACCESS read-only
	STATUS current
	DESCRIPTION
        "
        Channel Absent 10 :This OID indicates
        that an in service channel is absent
        on the Optical Power Monitoring
        input<Help> This alarm indicates
        that an in service channel is absent
        on the Optical Power Monitoring
        input <Condtype> CHANNEL10_ABSENT_1
        <Probcause> informationMissing
         (65) <Alarmtype> equipmentAlarm
        (5) <Polarity> (2)
        "
	::= { pmopm2Almchannel10PortEntry 2 }


--- *********************************************************
---     TABLE for the pmopm2Almchannel11Port articles
--- *********************************************************

pmopm2Almchannel11PortTable OBJECT-TYPE
	SYNTAX  SEQUENCE OF Pmopm2Almchannel11PortEntry
	MAX-ACCESS not-accessible
	STATUS current
	DESCRIPTION
        "
        List of pmopm2Almchannel11Port
        Article
        "
	::= { pmopm2AlmClientCrit 36 }


pmopm2Almchannel11PortEntry OBJECT-TYPE
	SYNTAX Pmopm2Almchannel11PortEntry
	MAX-ACCESS not-accessible
	STATUS current
	DESCRIPTION
        "
        Row definition for the pmopm2Almchannel11Port
        table
        "
	INDEX   { pmopm2Almchannel11PortIndex }
	::= { pmopm2Almchannel11PortTable 1 }


Pmopm2Almchannel11PortEntry ::=
	SEQUENCE {
	pmopm2Almchannel11PortIndex
		INTEGER,
	pmopm2AlmChannel11OosPortn
		EkiOnOff,
	pmopm2AlmChannel11PowerHighPortn
		EkiOnOff,
	pmopm2AlmChannel11PowerLowPortn
		EkiOnOff,
	pmopm2AlmChannel11BalancedPortn
		EkiOnOff,
	pmopm2AlmChannel11MismatchPortn
		EkiOnOff,
	pmopm2AlmChannel11AbsentPortn
		EkiOnOff
	}


pmopm2Almchannel11PortIndex OBJECT-TYPE
	SYNTAX  INTEGER(0..128)
	MAX-ACCESS  read-only
	STATUS current
	DESCRIPTION
        "
        Index definition for the pmopm2Almchannel11Port
        table
        "
	::= { pmopm2Almchannel11PortEntry 1 }


pmopm2AlmChannel11OosPortn OBJECT-TYPE
	SYNTAX  EkiOnOff
	MAX-ACCESS read-only
	STATUS current
	DESCRIPTION
        "
        Channel Out Of Service 11 :This
        OID indicates that the channel
         is out of service  <Help> This
        alarm indicates that the channel
        is in service <Condtype> CHANNEL11_OOS_1
        <Probcause> informationalStatus(1000)
        <Alarmtype> other (1) <Polarity>
        (2)
        "
	::= { pmopm2Almchannel11PortEntry 7 }


pmopm2AlmChannel11PowerHighPortn OBJECT-TYPE
	SYNTAX  EkiOnOff
	MAX-ACCESS read-only
	STATUS current
	DESCRIPTION
        "
        Channel Power High 11 :This OID
        indicates that the power of the
        channel is higher than the configured
        threshold<Help> This alarm indicates
        that the power of the channel is
        higher than the configured threshold
        <Condtype> CHANNEL11_POWER_HIGH_1
        <Probcause> degradedSignal (13)
        <Alarmtype> equipmentAlarm <Polarity>
        (2)
        "
	::= { pmopm2Almchannel11PortEntry 6 }


pmopm2AlmChannel11PowerLowPortn OBJECT-TYPE
	SYNTAX  EkiOnOff
	MAX-ACCESS read-only
	STATUS current
	DESCRIPTION
        "
        Channel Power Low 11 :This OID
        indicates that the power of the
        channel is lower than the configured
        threshold<Help> This alarm indicates
        that the power of the channel is
        lower than the configured threshold
        <Condtype> CHANNEL11_POWER_LOW_1
        <Probcause> degradedSignal (13)
        <Alarmtype> equipmentAlarm <Polarity>
        (2)
        "
	::= { pmopm2Almchannel11PortEntry 5 }


pmopm2AlmChannel11BalancedPortn OBJECT-TYPE
	SYNTAX  EkiOnOff
	MAX-ACCESS read-only
	STATUS current
	DESCRIPTION
        "
        Channel Balanced 11 :This OID
         indicates that an in service channel
        is balanced by the Ekinops auto
        turn up application<Help> This
         status indicates that an in service
        channel is balanced by the Ekinops
        auto turn up application <Condtype>
        CHANNEL11_BALANCED_1 <Probcause>
        informationalStatus(1000) <Alarmtype>
        other (1) <Polarity> (2)
        "
	::= { pmopm2Almchannel11PortEntry 4 }


pmopm2AlmChannel11MismatchPortn OBJECT-TYPE
	SYNTAX  EkiOnOff
	MAX-ACCESS read-only
	STATUS current
	DESCRIPTION
        "
        Channel Mismatch 11 :This OID
         indicates that an out of service
        channel is detected on the Optical
        Power Monitoring input<Help> This
        alarm indicates that an out of
         service channel is detected on
        the Optical Power Monitoring input
        <Condtype> CHANNEL11_MISMATCH_1
        <Probcause> unexpectedInformation
        (75) <Alarmtype> equipmentAlarm
        <Polarity> (2)
        "
	::= { pmopm2Almchannel11PortEntry 3 }


pmopm2AlmChannel11AbsentPortn OBJECT-TYPE
	SYNTAX  EkiOnOff
	MAX-ACCESS read-only
	STATUS current
	DESCRIPTION
        "
        Channel Absent 11 :This OID indicates
        that an in service channel is absent
        on the Optical Power Monitoring
        input<Help> This alarm indicates
        that an in service channel is absent
        on the Optical Power Monitoring
        input <Condtype> CHANNEL11_ABSENT_1
        <Probcause> informationMissing
         (65) <Alarmtype> equipmentAlarm
        (5) <Polarity> (2)
        "
	::= { pmopm2Almchannel11PortEntry 2 }


--- *********************************************************
---     TABLE for the pmopm2Almchannel12Port articles
--- *********************************************************

pmopm2Almchannel12PortTable OBJECT-TYPE
	SYNTAX  SEQUENCE OF Pmopm2Almchannel12PortEntry
	MAX-ACCESS not-accessible
	STATUS current
	DESCRIPTION
        "
        List of pmopm2Almchannel12Port
        Article
        "
	::= { pmopm2AlmClientCrit 38 }


pmopm2Almchannel12PortEntry OBJECT-TYPE
	SYNTAX Pmopm2Almchannel12PortEntry
	MAX-ACCESS not-accessible
	STATUS current
	DESCRIPTION
        "
        Row definition for the pmopm2Almchannel12Port
        table
        "
	INDEX   { pmopm2Almchannel12PortIndex }
	::= { pmopm2Almchannel12PortTable 1 }


Pmopm2Almchannel12PortEntry ::=
	SEQUENCE {
	pmopm2Almchannel12PortIndex
		INTEGER,
	pmopm2AlmChannel12OosPortn
		EkiOnOff,
	pmopm2AlmChannel12PowerHighPortn
		EkiOnOff,
	pmopm2AlmChannel12PowerLowPortn
		EkiOnOff,
	pmopm2AlmChannel12BalancedPortn
		EkiOnOff,
	pmopm2AlmChannel12MismatchPortn
		EkiOnOff,
	pmopm2AlmChannel12AbsentPortn
		EkiOnOff
	}


pmopm2Almchannel12PortIndex OBJECT-TYPE
	SYNTAX  INTEGER(0..128)
	MAX-ACCESS  read-only
	STATUS current
	DESCRIPTION
        "
        Index definition for the pmopm2Almchannel12Port
        table
        "
	::= { pmopm2Almchannel12PortEntry 1 }


pmopm2AlmChannel12OosPortn OBJECT-TYPE
	SYNTAX  EkiOnOff
	MAX-ACCESS read-only
	STATUS current
	DESCRIPTION
        "
        Channel Out Of Service 12 :This
        OID indicates that the channel
         is out of service  <Help> This
        alarm indicates that the channel
        is in service <Condtype> CHANNEL12_OOS_1
        <Probcause> informationalStatus(1000)
        <Alarmtype> other (1) <Polarity>
        (2)
        "
	::= { pmopm2Almchannel12PortEntry 7 }


pmopm2AlmChannel12PowerHighPortn OBJECT-TYPE
	SYNTAX  EkiOnOff
	MAX-ACCESS read-only
	STATUS current
	DESCRIPTION
        "
        Channel Power High 12 :This OID
        indicates that the power of the
        channel is higher than the configured
        threshold<Help> This alarm indicates
        that the power of the channel is
        higher than the configured threshold
        <Condtype> CHANNEL12_POWER_HIGH_1
        <Probcause> degradedSignal (13)
        <Alarmtype> equipmentAlarm <Polarity>
        (2)
        "
	::= { pmopm2Almchannel12PortEntry 6 }


pmopm2AlmChannel12PowerLowPortn OBJECT-TYPE
	SYNTAX  EkiOnOff
	MAX-ACCESS read-only
	STATUS current
	DESCRIPTION
        "
        Channel Power Low 12 :This OID
        indicates that the power of the
        channel is lower than the configured
        threshold<Help> This alarm indicates
        that the power of the channel is
        lower than the configured threshold
        <Condtype> CHANNEL12_POWER_LOW_1
        <Probcause> degradedSignal (13)
        <Alarmtype> equipmentAlarm <Polarity>
        (2)
        "
	::= { pmopm2Almchannel12PortEntry 5 }


pmopm2AlmChannel12BalancedPortn OBJECT-TYPE
	SYNTAX  EkiOnOff
	MAX-ACCESS read-only
	STATUS current
	DESCRIPTION
        "
        Channel Balanced 12 :This OID
         indicates that an in service channel
        is balanced by the Ekinops auto
        turn up application<Help> This
         status indicates that an in service
        channel is balanced by the Ekinops
        auto turn up application <Condtype>
        CHANNEL12_BALANCED_1 <Probcause>
        informationalStatus(1000) <Alarmtype>
        other (1) <Polarity> (2)
        "
	::= { pmopm2Almchannel12PortEntry 4 }


pmopm2AlmChannel12MismatchPortn OBJECT-TYPE
	SYNTAX  EkiOnOff
	MAX-ACCESS read-only
	STATUS current
	DESCRIPTION
        "
        Channel Mismatch 12 :This OID
         indicates that an out of service
        channel is detected on the Optical
        Power Monitoring input<Help> This
        alarm indicates that an out of
         service channel is detected on
        the Optical Power Monitoring input
        <Condtype> CHANNEL12_MISMATCH_1
        <Probcause> unexpectedInformation
        (75) <Alarmtype> equipmentAlarm
        <Polarity> (2)
        "
	::= { pmopm2Almchannel12PortEntry 3 }


pmopm2AlmChannel12AbsentPortn OBJECT-TYPE
	SYNTAX  EkiOnOff
	MAX-ACCESS read-only
	STATUS current
	DESCRIPTION
        "
        Channel Absent 12 :This OID indicates
        that an in service channel is absent
        on the Optical Power Monitoring
        input<Help> This alarm indicates
        that an in service channel is absent
        on the Optical Power Monitoring
        input <Condtype> CHANNEL12_ABSENT_1
        <Probcause> informationMissing
         (65) <Alarmtype> equipmentAlarm
        (5) <Polarity> (2)
        "
	::= { pmopm2Almchannel12PortEntry 2 }


--- *********************************************************
---     TABLE for the pmopm2Almchannel13Port articles
--- *********************************************************

pmopm2Almchannel13PortTable OBJECT-TYPE
	SYNTAX  SEQUENCE OF Pmopm2Almchannel13PortEntry
	MAX-ACCESS not-accessible
	STATUS current
	DESCRIPTION
        "
        List of pmopm2Almchannel13Port
        Article
        "
	::= { pmopm2AlmClientCrit 40 }


pmopm2Almchannel13PortEntry OBJECT-TYPE
	SYNTAX Pmopm2Almchannel13PortEntry
	MAX-ACCESS not-accessible
	STATUS current
	DESCRIPTION
        "
        Row definition for the pmopm2Almchannel13Port
        table
        "
	INDEX   { pmopm2Almchannel13PortIndex }
	::= { pmopm2Almchannel13PortTable 1 }


Pmopm2Almchannel13PortEntry ::=
	SEQUENCE {
	pmopm2Almchannel13PortIndex
		INTEGER,
	pmopm2AlmChannel13OosPortn
		EkiOnOff,
	pmopm2AlmChannel13PowerHighPortn
		EkiOnOff,
	pmopm2AlmChannel13PowerLowPortn
		EkiOnOff,
	pmopm2AlmChannel13BalancedPortn
		EkiOnOff,
	pmopm2AlmChannel13MismatchPortn
		EkiOnOff,
	pmopm2AlmChannel13AbsentPortn
		EkiOnOff
	}


pmopm2Almchannel13PortIndex OBJECT-TYPE
	SYNTAX  INTEGER(0..128)
	MAX-ACCESS  read-only
	STATUS current
	DESCRIPTION
        "
        Index definition for the pmopm2Almchannel13Port
        table
        "
	::= { pmopm2Almchannel13PortEntry 1 }


pmopm2AlmChannel13OosPortn OBJECT-TYPE
	SYNTAX  EkiOnOff
	MAX-ACCESS read-only
	STATUS current
	DESCRIPTION
        "
        Channel Out Of Service 13 :This
        OID indicates that the channel
         is out of service  <Help> This
        alarm indicates that the channel
        is in service <Condtype> CHANNEL13_OOS_1
        <Probcause> informationalStatus(1000)
        <Alarmtype> other (1) <Polarity>
        (2)
        "
	::= { pmopm2Almchannel13PortEntry 7 }


pmopm2AlmChannel13PowerHighPortn OBJECT-TYPE
	SYNTAX  EkiOnOff
	MAX-ACCESS read-only
	STATUS current
	DESCRIPTION
        "
        Channel Power High 13 :This OID
        indicates that the power of the
        channel is higher than the configured
        threshold<Help> This alarm indicates
        that the power of the channel is
        higher than the configured threshold
        <Condtype> CHANNEL13_POWER_HIGH_1
        <Probcause> degradedSignal (13)
        <Alarmtype> equipmentAlarm <Polarity>
        (2)
        "
	::= { pmopm2Almchannel13PortEntry 6 }


pmopm2AlmChannel13PowerLowPortn OBJECT-TYPE
	SYNTAX  EkiOnOff
	MAX-ACCESS read-only
	STATUS current
	DESCRIPTION
        "
        Channel Power Low 13 :This OID
        indicates that the power of the
        channel is lower than the configured
        threshold<Help> This alarm indicates
        that the power of the channel is
        lower than the configured threshold
        <Condtype> CHANNEL13_POWER_LOW_1
        <Probcause> degradedSignal (13)
        <Alarmtype> equipmentAlarm <Polarity>
        (2)
        "
	::= { pmopm2Almchannel13PortEntry 5 }


pmopm2AlmChannel13BalancedPortn OBJECT-TYPE
	SYNTAX  EkiOnOff
	MAX-ACCESS read-only
	STATUS current
	DESCRIPTION
        "
        Channel Balanced 13 :This OID
         indicates that an in service channel
        is balanced by the Ekinops auto
        turn up application<Help> This
         status indicates that an in service
        channel is balanced by the Ekinops
        auto turn up application <Condtype>
        CHANNEL13_BALANCED_1 <Probcause>
        informationalStatus(1000) <Alarmtype>
        other (1) <Polarity> (2)
        "
	::= { pmopm2Almchannel13PortEntry 4 }


pmopm2AlmChannel13MismatchPortn OBJECT-TYPE
	SYNTAX  EkiOnOff
	MAX-ACCESS read-only
	STATUS current
	DESCRIPTION
        "
        Channel Mismatch 13 :This OID
         indicates that an out of service
        channel is detected on the Optical
        Power Monitoring input<Help> This
        alarm indicates that an out of
         service channel is detected on
        the Optical Power Monitoring input
        <Condtype> CHANNEL13_MISMATCH_1
        <Probcause> unexpectedInformation
        (75) <Alarmtype> equipmentAlarm
        <Polarity> (2)
        "
	::= { pmopm2Almchannel13PortEntry 3 }


pmopm2AlmChannel13AbsentPortn OBJECT-TYPE
	SYNTAX  EkiOnOff
	MAX-ACCESS read-only
	STATUS current
	DESCRIPTION
        "
        Channel Absent 13 :This OID indicates
        that an in service channel is absent
        on the Optical Power Monitoring
        input<Help> This alarm indicates
        that an in service channel is absent
        on the Optical Power Monitoring
        input <Condtype> CHANNEL13_ABSENT_1
        <Probcause> informationMissing
         (65) <Alarmtype> equipmentAlarm
        (5) <Polarity> (2)
        "
	::= { pmopm2Almchannel13PortEntry 2 }


--- *********************************************************
---     TABLE for the pmopm2Almchannel14Port articles
--- *********************************************************

pmopm2Almchannel14PortTable OBJECT-TYPE
	SYNTAX  SEQUENCE OF Pmopm2Almchannel14PortEntry
	MAX-ACCESS not-accessible
	STATUS current
	DESCRIPTION
        "
        List of pmopm2Almchannel14Port
        Article
        "
	::= { pmopm2AlmClientCrit 42 }


pmopm2Almchannel14PortEntry OBJECT-TYPE
	SYNTAX Pmopm2Almchannel14PortEntry
	MAX-ACCESS not-accessible
	STATUS current
	DESCRIPTION
        "
        Row definition for the pmopm2Almchannel14Port
        table
        "
	INDEX   { pmopm2Almchannel14PortIndex }
	::= { pmopm2Almchannel14PortTable 1 }


Pmopm2Almchannel14PortEntry ::=
	SEQUENCE {
	pmopm2Almchannel14PortIndex
		INTEGER,
	pmopm2AlmChannel14OosPortn
		EkiOnOff,
	pmopm2AlmChannel14PowerHighPortn
		EkiOnOff,
	pmopm2AlmChannel14PowerLowPortn
		EkiOnOff,
	pmopm2AlmChannel14BalancedPortn
		EkiOnOff,
	pmopm2AlmChannel14MismatchPortn
		EkiOnOff,
	pmopm2AlmChannel14AbsentPortn
		EkiOnOff
	}


pmopm2Almchannel14PortIndex OBJECT-TYPE
	SYNTAX  INTEGER(0..128)
	MAX-ACCESS  read-only
	STATUS current
	DESCRIPTION
        "
        Index definition for the pmopm2Almchannel14Port
        table
        "
	::= { pmopm2Almchannel14PortEntry 1 }


pmopm2AlmChannel14OosPortn OBJECT-TYPE
	SYNTAX  EkiOnOff
	MAX-ACCESS read-only
	STATUS current
	DESCRIPTION
        "
        Channel Out Of Service 14 :This
        OID indicates that the channel
         is out of service  <Help> This
        alarm indicates that the channel
        is in service <Condtype> CHANNEL14_OOS_1
        <Probcause> informationalStatus(1000)
        <Alarmtype> other (1) <Polarity>
        (2)
        "
	::= { pmopm2Almchannel14PortEntry 7 }


pmopm2AlmChannel14PowerHighPortn OBJECT-TYPE
	SYNTAX  EkiOnOff
	MAX-ACCESS read-only
	STATUS current
	DESCRIPTION
        "
        Channel Power High 14 :This OID
        indicates that the power of the
        channel is higher than the configured
        threshold<Help> This alarm indicates
        that the power of the channel is
        higher than the configured threshold
        <Condtype> CHANNEL14_POWER_HIGH_1
        <Probcause> degradedSignal (13)
        <Alarmtype> equipmentAlarm <Polarity>
        (2)
        "
	::= { pmopm2Almchannel14PortEntry 6 }


pmopm2AlmChannel14PowerLowPortn OBJECT-TYPE
	SYNTAX  EkiOnOff
	MAX-ACCESS read-only
	STATUS current
	DESCRIPTION
        "
        Channel Power Low 14 :This OID
        indicates that the power of the
        channel is lower than the configured
        threshold<Help> This alarm indicates
        that the power of the channel is
        lower than the configured threshold
        <Condtype> CHANNEL14_POWER_LOW_1
        <Probcause> degradedSignal (13)
        <Alarmtype> equipmentAlarm <Polarity>
        (2)
        "
	::= { pmopm2Almchannel14PortEntry 5 }


pmopm2AlmChannel14BalancedPortn OBJECT-TYPE
	SYNTAX  EkiOnOff
	MAX-ACCESS read-only
	STATUS current
	DESCRIPTION
        "
        Channel Balanced 14 :This OID
         indicates that an in service channel
        is balanced by the Ekinops auto
        turn up application<Help> This
         status indicates that an in service
        channel is balanced by the Ekinops
        auto turn up application <Condtype>
        CHANNEL14_BALANCED_1 <Probcause>
        informationalStatus(1000) <Alarmtype>
        other (1) <Polarity> (2)
        "
	::= { pmopm2Almchannel14PortEntry 4 }


pmopm2AlmChannel14MismatchPortn OBJECT-TYPE
	SYNTAX  EkiOnOff
	MAX-ACCESS read-only
	STATUS current
	DESCRIPTION
        "
        Channel Mismatch 14 :This OID
         indicates that an out of service
        channel is detected on the Optical
        Power Monitoring input<Help> This
        alarm indicates that an out of
         service channel is detected on
        the Optical Power Monitoring input
        <Condtype> CHANNEL14_MISMATCH_1
        <Probcause> unexpectedInformation
        (75) <Alarmtype> equipmentAlarm
        <Polarity> (2)
        "
	::= { pmopm2Almchannel14PortEntry 3 }


pmopm2AlmChannel14AbsentPortn OBJECT-TYPE
	SYNTAX  EkiOnOff
	MAX-ACCESS read-only
	STATUS current
	DESCRIPTION
        "
        Channel Absent 14 :This OID indicates
        that an in service channel is absent
        on the Optical Power Monitoring
        input<Help> This alarm indicates
        that an in service channel is absent
        on the Optical Power Monitoring
        input <Condtype> CHANNEL14_ABSENT_1
        <Probcause> informationMissing
         (65) <Alarmtype> equipmentAlarm
        (5) <Polarity> (2)
        "
	::= { pmopm2Almchannel14PortEntry 2 }


--- *********************************************************
---     TABLE for the pmopm2Almchannel15Port articles
--- *********************************************************

pmopm2Almchannel15PortTable OBJECT-TYPE
	SYNTAX  SEQUENCE OF Pmopm2Almchannel15PortEntry
	MAX-ACCESS not-accessible
	STATUS current
	DESCRIPTION
        "
        List of pmopm2Almchannel15Port
        Article
        "
	::= { pmopm2AlmClientCrit 44 }


pmopm2Almchannel15PortEntry OBJECT-TYPE
	SYNTAX Pmopm2Almchannel15PortEntry
	MAX-ACCESS not-accessible
	STATUS current
	DESCRIPTION
        "
        Row definition for the pmopm2Almchannel15Port
        table
        "
	INDEX   { pmopm2Almchannel15PortIndex }
	::= { pmopm2Almchannel15PortTable 1 }


Pmopm2Almchannel15PortEntry ::=
	SEQUENCE {
	pmopm2Almchannel15PortIndex
		INTEGER,
	pmopm2AlmChannel15OosPortn
		EkiOnOff,
	pmopm2AlmChannel15PowerHighPortn
		EkiOnOff,
	pmopm2AlmChannel15PowerLowPortn
		EkiOnOff,
	pmopm2AlmChannel15BalancedPortn
		EkiOnOff,
	pmopm2AlmChannel15MismatchPortn
		EkiOnOff,
	pmopm2AlmChannel15AbsentPortn
		EkiOnOff
	}


pmopm2Almchannel15PortIndex OBJECT-TYPE
	SYNTAX  INTEGER(0..128)
	MAX-ACCESS  read-only
	STATUS current
	DESCRIPTION
        "
        Index definition for the pmopm2Almchannel15Port
        table
        "
	::= { pmopm2Almchannel15PortEntry 1 }


pmopm2AlmChannel15OosPortn OBJECT-TYPE
	SYNTAX  EkiOnOff
	MAX-ACCESS read-only
	STATUS current
	DESCRIPTION
        "
        Channel Out Of Service 15 :This
        OID indicates that the channel
         is out of service  <Help> This
        alarm indicates that the channel
        is in service <Condtype> CHANNEL15_OOS_1
        <Probcause> informationalStatus(1000)
        <Alarmtype> other (1) <Polarity>
        (2)
        "
	::= { pmopm2Almchannel15PortEntry 7 }


pmopm2AlmChannel15PowerHighPortn OBJECT-TYPE
	SYNTAX  EkiOnOff
	MAX-ACCESS read-only
	STATUS current
	DESCRIPTION
        "
        Channel Power High 15 :This OID
        indicates that the power of the
        channel is higher than the configured
        threshold<Help> This alarm indicates
        that the power of the channel is
        higher than the configured threshold
        <Condtype> CHANNEL15_POWER_HIGH_1
        <Probcause> degradedSignal (13)
        <Alarmtype> equipmentAlarm <Polarity>
        (2)
        "
	::= { pmopm2Almchannel15PortEntry 6 }


pmopm2AlmChannel15PowerLowPortn OBJECT-TYPE
	SYNTAX  EkiOnOff
	MAX-ACCESS read-only
	STATUS current
	DESCRIPTION
        "
        Channel Power Low 15 :This OID
        indicates that the power of the
        channel is lower than the configured
        threshold<Help> This alarm indicates
        that the power of the channel is
        lower than the configured threshold
        <Condtype> CHANNEL15_POWER_LOW_1
        <Probcause> degradedSignal (13)
        <Alarmtype> equipmentAlarm <Polarity>
        (2)
        "
	::= { pmopm2Almchannel15PortEntry 5 }


pmopm2AlmChannel15BalancedPortn OBJECT-TYPE
	SYNTAX  EkiOnOff
	MAX-ACCESS read-only
	STATUS current
	DESCRIPTION
        "
        Channel Balanced 15 :This OID
         indicates that an in service channel
        is balanced by the Ekinops auto
        turn up application<Help> This
         status indicates that an in service
        channel is balanced by the Ekinops
        auto turn up application <Condtype>
        CHANNEL15_BALANCED_1 <Probcause>
        informationalStatus(1000) <Alarmtype>
        other (1) <Polarity> (2)
        "
	::= { pmopm2Almchannel15PortEntry 4 }


pmopm2AlmChannel15MismatchPortn OBJECT-TYPE
	SYNTAX  EkiOnOff
	MAX-ACCESS read-only
	STATUS current
	DESCRIPTION
        "
        Channel Mismatch 15 :This OID
         indicates that an out of service
        channel is detected on the Optical
        Power Monitoring input<Help> This
        alarm indicates that an out of
         service channel is detected on
        the Optical Power Monitoring input
        <Condtype> CHANNEL15_MISMATCH_1
        <Probcause> unexpectedInformation
        (75) <Alarmtype> equipmentAlarm
        <Polarity> (2)
        "
	::= { pmopm2Almchannel15PortEntry 3 }


pmopm2AlmChannel15AbsentPortn OBJECT-TYPE
	SYNTAX  EkiOnOff
	MAX-ACCESS read-only
	STATUS current
	DESCRIPTION
        "
        Channel Absent 15 :This OID indicates
        that an in service channel is absent
        on the Optical Power Monitoring
        input<Help> This alarm indicates
        that an in service channel is absent
        on the Optical Power Monitoring
        input <Condtype> CHANNEL15_ABSENT_1
        <Probcause> informationMissing
         (65) <Alarmtype> equipmentAlarm
        (5) <Polarity> (2)
        "
	::= { pmopm2Almchannel15PortEntry 2 }


--- *********************************************************
---     TABLE for the pmopm2Almchannel16Port articles
--- *********************************************************

pmopm2Almchannel16PortTable OBJECT-TYPE
	SYNTAX  SEQUENCE OF Pmopm2Almchannel16PortEntry
	MAX-ACCESS not-accessible
	STATUS current
	DESCRIPTION
        "
        List of pmopm2Almchannel16Port
        Article
        "
	::= { pmopm2AlmClientCrit 46 }


pmopm2Almchannel16PortEntry OBJECT-TYPE
	SYNTAX Pmopm2Almchannel16PortEntry
	MAX-ACCESS not-accessible
	STATUS current
	DESCRIPTION
        "
        Row definition for the pmopm2Almchannel16Port
        table
        "
	INDEX   { pmopm2Almchannel16PortIndex }
	::= { pmopm2Almchannel16PortTable 1 }


Pmopm2Almchannel16PortEntry ::=
	SEQUENCE {
	pmopm2Almchannel16PortIndex
		INTEGER,
	pmopm2AlmChannel16OosPortn
		EkiOnOff,
	pmopm2AlmChannel16PowerHighPortn
		EkiOnOff,
	pmopm2AlmChannel16PowerLowPortn
		EkiOnOff,
	pmopm2AlmChannel16BalancedPortn
		EkiOnOff,
	pmopm2AlmChannel16MismatchPortn
		EkiOnOff,
	pmopm2AlmChannel16AbsentPortn
		EkiOnOff
	}


pmopm2Almchannel16PortIndex OBJECT-TYPE
	SYNTAX  INTEGER(0..128)
	MAX-ACCESS  read-only
	STATUS current
	DESCRIPTION
        "
        Index definition for the pmopm2Almchannel16Port
        table
        "
	::= { pmopm2Almchannel16PortEntry 1 }


pmopm2AlmChannel16OosPortn OBJECT-TYPE
	SYNTAX  EkiOnOff
	MAX-ACCESS read-only
	STATUS current
	DESCRIPTION
        "
        Channel Out Of Service 16 :This
        OID indicates that the channel
         is out of service  <Help> This
        alarm indicates that the channel
        is in service <Condtype> CHANNEL16_OOS_1
        <Probcause> informationalStatus(1000)
        <Alarmtype> other (1) <Polarity>
        (2)
        "
	::= { pmopm2Almchannel16PortEntry 7 }


pmopm2AlmChannel16PowerHighPortn OBJECT-TYPE
	SYNTAX  EkiOnOff
	MAX-ACCESS read-only
	STATUS current
	DESCRIPTION
        "
        Channel Power High 16 :This OID
        indicates that the power of the
        channel is higher than the configured
        threshold<Help> This alarm indicates
        that the power of the channel is
        higher than the configured threshold
        <Condtype> CHANNEL16_POWER_HIGH_1
        <Probcause> degradedSignal (13)
        <Alarmtype> equipmentAlarm <Polarity>
        (2)
        "
	::= { pmopm2Almchannel16PortEntry 6 }


pmopm2AlmChannel16PowerLowPortn OBJECT-TYPE
	SYNTAX  EkiOnOff
	MAX-ACCESS read-only
	STATUS current
	DESCRIPTION
        "
        Channel Power Low 16 :This OID
        indicates that the power of the
        channel is lower than the configured
        threshold<Help> This alarm indicates
        that the power of the channel is
        lower than the configured threshold
        <Condtype> CHANNEL16_POWER_LOW_1
        <Probcause> degradedSignal (13)
        <Alarmtype> equipmentAlarm <Polarity>
        (2)
        "
	::= { pmopm2Almchannel16PortEntry 5 }


pmopm2AlmChannel16BalancedPortn OBJECT-TYPE
	SYNTAX  EkiOnOff
	MAX-ACCESS read-only
	STATUS current
	DESCRIPTION
        "
        Channel Balanced 16 :This OID
         indicates that an in service channel
        is balanced by the Ekinops auto
        turn up application<Help> This
         status indicates that an in service
        channel is balanced by the Ekinops
        auto turn up application <Condtype>
        CHANNEL16_BALANCED_1 <Probcause>
        informationalStatus(1000) <Alarmtype>
        other (1) <Polarity> (2)
        "
	::= { pmopm2Almchannel16PortEntry 4 }


pmopm2AlmChannel16MismatchPortn OBJECT-TYPE
	SYNTAX  EkiOnOff
	MAX-ACCESS read-only
	STATUS current
	DESCRIPTION
        "
        Channel Mismatch 16 :This OID
         indicates that an out of service
        channel is detected on the Optical
        Power Monitoring input<Help> This
        alarm indicates that an out of
         service channel is detected on
        the Optical Power Monitoring input
        <Condtype> CHANNEL16_MISMATCH_1
        <Probcause> unexpectedInformation
        (75) <Alarmtype> equipmentAlarm
        <Polarity> (2)
        "
	::= { pmopm2Almchannel16PortEntry 3 }


pmopm2AlmChannel16AbsentPortn OBJECT-TYPE
	SYNTAX  EkiOnOff
	MAX-ACCESS read-only
	STATUS current
	DESCRIPTION
        "
        Channel Absent 16 :This OID indicates
        that an in service channel is absent
        on the Optical Power Monitoring
        input<Help> This alarm indicates
        that an in service channel is absent
        on the Optical Power Monitoring
        input <Condtype> CHANNEL16_ABSENT_1
        <Probcause> informationMissing
         (65) <Alarmtype> equipmentAlarm
        (5) <Polarity> (2)
        "
	::= { pmopm2Almchannel16PortEntry 2 }


--- *********************************************************
---     TABLE for the pmopm2Almchannel17Port articles
--- *********************************************************

pmopm2Almchannel17PortTable OBJECT-TYPE
	SYNTAX  SEQUENCE OF Pmopm2Almchannel17PortEntry
	MAX-ACCESS not-accessible
	STATUS current
	DESCRIPTION
        "
        List of pmopm2Almchannel17Port
        Article
        "
	::= { pmopm2AlmClientCrit 48 }


pmopm2Almchannel17PortEntry OBJECT-TYPE
	SYNTAX Pmopm2Almchannel17PortEntry
	MAX-ACCESS not-accessible
	STATUS current
	DESCRIPTION
        "
        Row definition for the pmopm2Almchannel17Port
        table
        "
	INDEX   { pmopm2Almchannel17PortIndex }
	::= { pmopm2Almchannel17PortTable 1 }


Pmopm2Almchannel17PortEntry ::=
	SEQUENCE {
	pmopm2Almchannel17PortIndex
		INTEGER,
	pmopm2AlmChannel17OosPortn
		EkiOnOff,
	pmopm2AlmChannel17PowerHighPortn
		EkiOnOff,
	pmopm2AlmChannel17PowerLowPortn
		EkiOnOff,
	pmopm2AlmChannel17BalancedPortn
		EkiOnOff,
	pmopm2AlmChannel17MismatchPortn
		EkiOnOff,
	pmopm2AlmChannel17AbsentPortn
		EkiOnOff
	}


pmopm2Almchannel17PortIndex OBJECT-TYPE
	SYNTAX  INTEGER(0..128)
	MAX-ACCESS  read-only
	STATUS current
	DESCRIPTION
        "
        Index definition for the pmopm2Almchannel17Port
        table
        "
	::= { pmopm2Almchannel17PortEntry 1 }


pmopm2AlmChannel17OosPortn OBJECT-TYPE
	SYNTAX  EkiOnOff
	MAX-ACCESS read-only
	STATUS current
	DESCRIPTION
        "
        Channel Out Of Service 17 :This
        OID indicates that the channel
         is out of service  <Help> This
        alarm indicates that the channel
        is in service <Condtype> CHANNEL17_OOS_1
        <Probcause> informationalStatus(1000)
        <Alarmtype> other (1) <Polarity>
        (2)
        "
	::= { pmopm2Almchannel17PortEntry 7 }


pmopm2AlmChannel17PowerHighPortn OBJECT-TYPE
	SYNTAX  EkiOnOff
	MAX-ACCESS read-only
	STATUS current
	DESCRIPTION
        "
        Channel Power High 17 :This OID
        indicates that the power of the
        channel is higher than the configured
        threshold<Help> This alarm indicates
        that the power of the channel is
        higher than the configured threshold
        <Condtype> CHANNEL17_POWER_HIGH_1
        <Probcause> degradedSignal (13)
        <Alarmtype> equipmentAlarm <Polarity>
        (2)
        "
	::= { pmopm2Almchannel17PortEntry 6 }


pmopm2AlmChannel17PowerLowPortn OBJECT-TYPE
	SYNTAX  EkiOnOff
	MAX-ACCESS read-only
	STATUS current
	DESCRIPTION
        "
        Channel Power Low 17 :This OID
        indicates that the power of the
        channel is lower than the configured
        threshold<Help> This alarm indicates
        that the power of the channel is
        lower than the configured threshold
        <Condtype> CHANNEL17_POWER_LOW_1
        <Probcause> degradedSignal (13)
        <Alarmtype> equipmentAlarm <Polarity>
        (2)
        "
	::= { pmopm2Almchannel17PortEntry 5 }


pmopm2AlmChannel17BalancedPortn OBJECT-TYPE
	SYNTAX  EkiOnOff
	MAX-ACCESS read-only
	STATUS current
	DESCRIPTION
        "
        Channel Balanced 17 :This OID
         indicates that an in service channel
        is balanced by the Ekinops auto
        turn up application<Help> This
         status indicates that an in service
        channel is balanced by the Ekinops
        auto turn up application <Condtype>
        CHANNEL17_BALANCED_1 <Probcause>
        informationalStatus(1000) <Alarmtype>
        other (1) <Polarity> (2)
        "
	::= { pmopm2Almchannel17PortEntry 4 }


pmopm2AlmChannel17MismatchPortn OBJECT-TYPE
	SYNTAX  EkiOnOff
	MAX-ACCESS read-only
	STATUS current
	DESCRIPTION
        "
        Channel Mismatch 17 :This OID
         indicates that an out of service
        channel is detected on the Optical
        Power Monitoring input<Help> This
        alarm indicates that an out of
         service channel is detected on
        the Optical Power Monitoring input
        <Condtype> CHANNEL17_MISMATCH_1
        <Probcause> unexpectedInformation
        (75) <Alarmtype> equipmentAlarm
        <Polarity> (2)
        "
	::= { pmopm2Almchannel17PortEntry 3 }


pmopm2AlmChannel17AbsentPortn OBJECT-TYPE
	SYNTAX  EkiOnOff
	MAX-ACCESS read-only
	STATUS current
	DESCRIPTION
        "
        Channel Absent 17 :This OID indicates
        that an in service channel is absent
        on the Optical Power Monitoring
        input<Help> This alarm indicates
        that an in service channel is absent
        on the Optical Power Monitoring
        input <Condtype> CHANNEL17_ABSENT_1
        <Probcause> informationMissing
         (65) <Alarmtype> equipmentAlarm
        (5) <Polarity> (2)
        "
	::= { pmopm2Almchannel17PortEntry 2 }


--- *********************************************************
---     TABLE for the pmopm2Almchannel18Port articles
--- *********************************************************

pmopm2Almchannel18PortTable OBJECT-TYPE
	SYNTAX  SEQUENCE OF Pmopm2Almchannel18PortEntry
	MAX-ACCESS not-accessible
	STATUS current
	DESCRIPTION
        "
        List of pmopm2Almchannel18Port
        Article
        "
	::= { pmopm2AlmClientCrit 50 }


pmopm2Almchannel18PortEntry OBJECT-TYPE
	SYNTAX Pmopm2Almchannel18PortEntry
	MAX-ACCESS not-accessible
	STATUS current
	DESCRIPTION
        "
        Row definition for the pmopm2Almchannel18Port
        table
        "
	INDEX   { pmopm2Almchannel18PortIndex }
	::= { pmopm2Almchannel18PortTable 1 }


Pmopm2Almchannel18PortEntry ::=
	SEQUENCE {
	pmopm2Almchannel18PortIndex
		INTEGER,
	pmopm2AlmChannel18OosPortn
		EkiOnOff,
	pmopm2AlmChannel18PowerHighPortn
		EkiOnOff,
	pmopm2AlmChannel18PowerLowPortn
		EkiOnOff,
	pmopm2AlmChannel18BalancedPortn
		EkiOnOff,
	pmopm2AlmChannel18MismatchPortn
		EkiOnOff,
	pmopm2AlmChannel18AbsentPortn
		EkiOnOff
	}


pmopm2Almchannel18PortIndex OBJECT-TYPE
	SYNTAX  INTEGER(0..128)
	MAX-ACCESS  read-only
	STATUS current
	DESCRIPTION
        "
        Index definition for the pmopm2Almchannel18Port
        table
        "
	::= { pmopm2Almchannel18PortEntry 1 }


pmopm2AlmChannel18OosPortn OBJECT-TYPE
	SYNTAX  EkiOnOff
	MAX-ACCESS read-only
	STATUS current
	DESCRIPTION
        "
        Channel Out Of Service 18 :This
        OID indicates that the channel
         is out of service  <Help> This
        alarm indicates that the channel
        is in service <Condtype> CHANNEL18_OOS_1
        <Probcause> informationalStatus(1000)
        <Alarmtype> other (1) <Polarity>
        (2)
        "
	::= { pmopm2Almchannel18PortEntry 7 }


pmopm2AlmChannel18PowerHighPortn OBJECT-TYPE
	SYNTAX  EkiOnOff
	MAX-ACCESS read-only
	STATUS current
	DESCRIPTION
        "
        Channel Power High 18 :This OID
        indicates that the power of the
        channel is higher than the configured
        threshold<Help> This alarm indicates
        that the power of the channel is
        higher than the configured threshold
        <Condtype> CHANNEL18_POWER_HIGH_1
        <Probcause> degradedSignal (13)
        <Alarmtype> equipmentAlarm <Polarity>
        (2)
        "
	::= { pmopm2Almchannel18PortEntry 6 }


pmopm2AlmChannel18PowerLowPortn OBJECT-TYPE
	SYNTAX  EkiOnOff
	MAX-ACCESS read-only
	STATUS current
	DESCRIPTION
        "
        Channel Power Low 18 :This OID
        indicates that the power of the
        channel is lower than the configured
        threshold<Help> This alarm indicates
        that the power of the channel is
        lower than the configured threshold
        <Condtype> CHANNEL18_POWER_LOW_1
        <Probcause> degradedSignal (13)
        <Alarmtype> equipmentAlarm <Polarity>
        (2)
        "
	::= { pmopm2Almchannel18PortEntry 5 }


pmopm2AlmChannel18BalancedPortn OBJECT-TYPE
	SYNTAX  EkiOnOff
	MAX-ACCESS read-only
	STATUS current
	DESCRIPTION
        "
        Channel Balanced 18 :This OID
         indicates that an in service channel
        is balanced by the Ekinops auto
        turn up application<Help> This
         status indicates that an in service
        channel is balanced by the Ekinops
        auto turn up application <Condtype>
        CHANNEL18_BALANCED_1 <Probcause>
        informationalStatus(1000) <Alarmtype>
        other (1) <Polarity> (2)
        "
	::= { pmopm2Almchannel18PortEntry 4 }


pmopm2AlmChannel18MismatchPortn OBJECT-TYPE
	SYNTAX  EkiOnOff
	MAX-ACCESS read-only
	STATUS current
	DESCRIPTION
        "
        Channel Mismatch 18 :This OID
         indicates that an out of service
        channel is detected on the Optical
        Power Monitoring input<Help> This
        alarm indicates that an out of
         service channel is detected on
        the Optical Power Monitoring input
        <Condtype> CHANNEL18_MISMATCH_1
        <Probcause> unexpectedInformation
        (75) <Alarmtype> equipmentAlarm
        <Polarity> (2)
        "
	::= { pmopm2Almchannel18PortEntry 3 }


pmopm2AlmChannel18AbsentPortn OBJECT-TYPE
	SYNTAX  EkiOnOff
	MAX-ACCESS read-only
	STATUS current
	DESCRIPTION
        "
        Channel Absent 18 :This OID indicates
        that an in service channel is absent
        on the Optical Power Monitoring
        input<Help> This alarm indicates
        that an in service channel is absent
        on the Optical Power Monitoring
        input <Condtype> CHANNEL18_ABSENT_1
        <Probcause> informationMissing
         (65) <Alarmtype> equipmentAlarm
        (5) <Polarity> (2)
        "
	::= { pmopm2Almchannel18PortEntry 2 }


--- *********************************************************
---     TABLE for the pmopm2Almchannel19Port articles
--- *********************************************************

pmopm2Almchannel19PortTable OBJECT-TYPE
	SYNTAX  SEQUENCE OF Pmopm2Almchannel19PortEntry
	MAX-ACCESS not-accessible
	STATUS current
	DESCRIPTION
        "
        List of pmopm2Almchannel19Port
        Article
        "
	::= { pmopm2AlmClientCrit 52 }


pmopm2Almchannel19PortEntry OBJECT-TYPE
	SYNTAX Pmopm2Almchannel19PortEntry
	MAX-ACCESS not-accessible
	STATUS current
	DESCRIPTION
        "
        Row definition for the pmopm2Almchannel19Port
        table
        "
	INDEX   { pmopm2Almchannel19PortIndex }
	::= { pmopm2Almchannel19PortTable 1 }


Pmopm2Almchannel19PortEntry ::=
	SEQUENCE {
	pmopm2Almchannel19PortIndex
		INTEGER,
	pmopm2AlmChannel19OosPortn
		EkiOnOff,
	pmopm2AlmChannel19PowerHighPortn
		EkiOnOff,
	pmopm2AlmChannel19PowerLowPortn
		EkiOnOff,
	pmopm2AlmChannel19BalancedPortn
		EkiOnOff,
	pmopm2AlmChannel19MismatchPortn
		EkiOnOff,
	pmopm2AlmChannel19AbsentPortn
		EkiOnOff
	}


pmopm2Almchannel19PortIndex OBJECT-TYPE
	SYNTAX  INTEGER(0..128)
	MAX-ACCESS  read-only
	STATUS current
	DESCRIPTION
        "
        Index definition for the pmopm2Almchannel19Port
        table
        "
	::= { pmopm2Almchannel19PortEntry 1 }


pmopm2AlmChannel19OosPortn OBJECT-TYPE
	SYNTAX  EkiOnOff
	MAX-ACCESS read-only
	STATUS current
	DESCRIPTION
        "
        Channel Out Of Service 19 :This
        OID indicates that the channel
         is out of service  <Help> This
        alarm indicates that the channel
        is in service <Condtype> CHANNEL19_OOS_1
        <Probcause> informationalStatus(1000)
        <Alarmtype> other (1) <Polarity>
        (2)
        "
	::= { pmopm2Almchannel19PortEntry 7 }


pmopm2AlmChannel19PowerHighPortn OBJECT-TYPE
	SYNTAX  EkiOnOff
	MAX-ACCESS read-only
	STATUS current
	DESCRIPTION
        "
        Channel Power High 19 :This OID
        indicates that the power of the
        channel is higher than the configured
        threshold<Help> This alarm indicates
        that the power of the channel is
        higher than the configured threshold
        <Condtype> CHANNEL19_POWER_HIGH_1
        <Probcause> degradedSignal (13)
        <Alarmtype> equipmentAlarm <Polarity>
        (2)
        "
	::= { pmopm2Almchannel19PortEntry 6 }


pmopm2AlmChannel19PowerLowPortn OBJECT-TYPE
	SYNTAX  EkiOnOff
	MAX-ACCESS read-only
	STATUS current
	DESCRIPTION
        "
        Channel Power Low 19 :This OID
        indicates that the power of the
        channel is lower than the configured
        threshold<Help> This alarm indicates
        that the power of the channel is
        lower than the configured threshold
        <Condtype> CHANNEL19_POWER_LOW_1
        <Probcause> degradedSignal (13)
        <Alarmtype> equipmentAlarm <Polarity>
        (2)
        "
	::= { pmopm2Almchannel19PortEntry 5 }


pmopm2AlmChannel19BalancedPortn OBJECT-TYPE
	SYNTAX  EkiOnOff
	MAX-ACCESS read-only
	STATUS current
	DESCRIPTION
        "
        Channel Balanced 19 :This OID
         indicates that an in service channel
        is balanced by the Ekinops auto
        turn up application<Help> This
         status indicates that an in service
        channel is balanced by the Ekinops
        auto turn up application <Condtype>
        CHANNEL19_BALANCED_1 <Probcause>
        informationalStatus(1000) <Alarmtype>
        other (1) <Polarity> (2)
        "
	::= { pmopm2Almchannel19PortEntry 4 }


pmopm2AlmChannel19MismatchPortn OBJECT-TYPE
	SYNTAX  EkiOnOff
	MAX-ACCESS read-only
	STATUS current
	DESCRIPTION
        "
        Channel Mismatch 19 :This OID
         indicates that an out of service
        channel is detected on the Optical
        Power Monitoring input<Help> This
        alarm indicates that an out of
         service channel is detected on
        the Optical Power Monitoring input
        <Condtype> CHANNEL19_MISMATCH_1
        <Probcause> unexpectedInformation
        (75) <Alarmtype> equipmentAlarm
        <Polarity> (2)
        "
	::= { pmopm2Almchannel19PortEntry 3 }


pmopm2AlmChannel19AbsentPortn OBJECT-TYPE
	SYNTAX  EkiOnOff
	MAX-ACCESS read-only
	STATUS current
	DESCRIPTION
        "
        Channel Absent 19 :This OID indicates
        that an in service channel is absent
        on the Optical Power Monitoring
        input<Help> This alarm indicates
        that an in service channel is absent
        on the Optical Power Monitoring
        input <Condtype> CHANNEL19_ABSENT_1
        <Probcause> informationMissing
         (65) <Alarmtype> equipmentAlarm
        (5) <Polarity> (2)
        "
	::= { pmopm2Almchannel19PortEntry 2 }


--- *********************************************************
---     TABLE for the pmopm2Almchannel20Port articles
--- *********************************************************

pmopm2Almchannel20PortTable OBJECT-TYPE
	SYNTAX  SEQUENCE OF Pmopm2Almchannel20PortEntry
	MAX-ACCESS not-accessible
	STATUS current
	DESCRIPTION
        "
        List of pmopm2Almchannel20Port
        Article
        "
	::= { pmopm2AlmClientCrit 54 }


pmopm2Almchannel20PortEntry OBJECT-TYPE
	SYNTAX Pmopm2Almchannel20PortEntry
	MAX-ACCESS not-accessible
	STATUS current
	DESCRIPTION
        "
        Row definition for the pmopm2Almchannel20Port
        table
        "
	INDEX   { pmopm2Almchannel20PortIndex }
	::= { pmopm2Almchannel20PortTable 1 }


Pmopm2Almchannel20PortEntry ::=
	SEQUENCE {
	pmopm2Almchannel20PortIndex
		INTEGER,
	pmopm2AlmChannel20OosPortn
		EkiOnOff,
	pmopm2AlmChannel20PowerHighPortn
		EkiOnOff,
	pmopm2AlmChannel20PowerLowPortn
		EkiOnOff,
	pmopm2AlmChannel20BalancedPortn
		EkiOnOff,
	pmopm2AlmChannel20MismatchPortn
		EkiOnOff,
	pmopm2AlmChannel20AbsentPortn
		EkiOnOff
	}


pmopm2Almchannel20PortIndex OBJECT-TYPE
	SYNTAX  INTEGER(0..128)
	MAX-ACCESS  read-only
	STATUS current
	DESCRIPTION
        "
        Index definition for the pmopm2Almchannel20Port
        table
        "
	::= { pmopm2Almchannel20PortEntry 1 }


pmopm2AlmChannel20OosPortn OBJECT-TYPE
	SYNTAX  EkiOnOff
	MAX-ACCESS read-only
	STATUS current
	DESCRIPTION
        "
        Channel Out Of Service 20 :This
        OID indicates that the channel
         is out of service  <Help> This
        alarm indicates that the channel
        is in service <Condtype> CHANNEL20_OOS_1
        <Probcause> informationalStatus(1000)
        <Alarmtype> other (1) <Polarity>
        (2)
        "
	::= { pmopm2Almchannel20PortEntry 7 }


pmopm2AlmChannel20PowerHighPortn OBJECT-TYPE
	SYNTAX  EkiOnOff
	MAX-ACCESS read-only
	STATUS current
	DESCRIPTION
        "
        Channel Power High 20 :This OID
        indicates that the power of the
        channel is higher than the configured
        threshold<Help> This alarm indicates
        that the power of the channel is
        higher than the configured threshold
        <Condtype> CHANNEL20_POWER_HIGH_1
        <Probcause> degradedSignal (13)
        <Alarmtype> equipmentAlarm <Polarity>
        (2)
        "
	::= { pmopm2Almchannel20PortEntry 6 }


pmopm2AlmChannel20PowerLowPortn OBJECT-TYPE
	SYNTAX  EkiOnOff
	MAX-ACCESS read-only
	STATUS current
	DESCRIPTION
        "
        Channel Power Low 20 :This OID
        indicates that the power of the
        channel is lower than the configured
        threshold<Help> This alarm indicates
        that the power of the channel is
        lower than the configured threshold
        <Condtype> CHANNEL20_POWER_LOW_1
        <Probcause> degradedSignal (13)
        <Alarmtype> equipmentAlarm <Polarity>
        (2)
        "
	::= { pmopm2Almchannel20PortEntry 5 }


pmopm2AlmChannel20BalancedPortn OBJECT-TYPE
	SYNTAX  EkiOnOff
	MAX-ACCESS read-only
	STATUS current
	DESCRIPTION
        "
        Channel Balanced 20 :This OID
         indicates that an in service channel
        is balanced by the Ekinops auto
        turn up application<Help> This
         status indicates that an in service
        channel is balanced by the Ekinops
        auto turn up application <Condtype>
        CHANNEL20_BALANCED_1 <Probcause>
        informationalStatus(1000) <Alarmtype>
        other (1) <Polarity> (2)
        "
	::= { pmopm2Almchannel20PortEntry 4 }


pmopm2AlmChannel20MismatchPortn OBJECT-TYPE
	SYNTAX  EkiOnOff
	MAX-ACCESS read-only
	STATUS current
	DESCRIPTION
        "
        Channel Mismatch 20 :This OID
         indicates that an out of service
        channel is detected on the Optical
        Power Monitoring input<Help> This
        alarm indicates that an out of
         service channel is detected on
        the Optical Power Monitoring input
        <Condtype> CHANNEL20_MISMATCH_1
        <Probcause> unexpectedInformation
        (75) <Alarmtype> equipmentAlarm
        <Polarity> (2)
        "
	::= { pmopm2Almchannel20PortEntry 3 }


pmopm2AlmChannel20AbsentPortn OBJECT-TYPE
	SYNTAX  EkiOnOff
	MAX-ACCESS read-only
	STATUS current
	DESCRIPTION
        "
        Channel Absent 20 :This OID indicates
        that an in service channel is absent
        on the Optical Power Monitoring
        input<Help> This alarm indicates
        that an in service channel is absent
        on the Optical Power Monitoring
        input <Condtype> CHANNEL20_ABSENT_1
        <Probcause> informationMissing
         (65) <Alarmtype> equipmentAlarm
        (5) <Polarity> (2)
        "
	::= { pmopm2Almchannel20PortEntry 2 }


--- *********************************************************
---     TABLE for the pmopm2Almchannel21Port articles
--- *********************************************************

pmopm2Almchannel21PortTable OBJECT-TYPE
	SYNTAX  SEQUENCE OF Pmopm2Almchannel21PortEntry
	MAX-ACCESS not-accessible
	STATUS current
	DESCRIPTION
        "
        List of pmopm2Almchannel21Port
        Article
        "
	::= { pmopm2AlmClientCrit 56 }


pmopm2Almchannel21PortEntry OBJECT-TYPE
	SYNTAX Pmopm2Almchannel21PortEntry
	MAX-ACCESS not-accessible
	STATUS current
	DESCRIPTION
        "
        Row definition for the pmopm2Almchannel21Port
        table
        "
	INDEX   { pmopm2Almchannel21PortIndex }
	::= { pmopm2Almchannel21PortTable 1 }


Pmopm2Almchannel21PortEntry ::=
	SEQUENCE {
	pmopm2Almchannel21PortIndex
		INTEGER,
	pmopm2AlmChannel21OosPortn
		EkiOnOff,
	pmopm2AlmChannel21PowerHighPortn
		EkiOnOff,
	pmopm2AlmChannel21PowerLowPortn
		EkiOnOff,
	pmopm2AlmChannel21BalancedPortn
		EkiOnOff,
	pmopm2AlmChannel21MismatchPortn
		EkiOnOff,
	pmopm2AlmChannel21AbsentPortn
		EkiOnOff
	}


pmopm2Almchannel21PortIndex OBJECT-TYPE
	SYNTAX  INTEGER(0..128)
	MAX-ACCESS  read-only
	STATUS current
	DESCRIPTION
        "
        Index definition for the pmopm2Almchannel21Port
        table
        "
	::= { pmopm2Almchannel21PortEntry 1 }


pmopm2AlmChannel21OosPortn OBJECT-TYPE
	SYNTAX  EkiOnOff
	MAX-ACCESS read-only
	STATUS current
	DESCRIPTION
        "
        Channel Out Of Service 21 :This
        OID indicates that the channel
         is out of service  <Help> This
        alarm indicates that the channel
        is in service <Condtype> CHANNEL21_OOS_1
        <Probcause> informationalStatus(1000)
        <Alarmtype> other (1) <Polarity>
        (2)
        "
	::= { pmopm2Almchannel21PortEntry 7 }


pmopm2AlmChannel21PowerHighPortn OBJECT-TYPE
	SYNTAX  EkiOnOff
	MAX-ACCESS read-only
	STATUS current
	DESCRIPTION
        "
        Channel Power High 21 :This OID
        indicates that the power of the
        channel is higher than the configured
        threshold<Help> This alarm indicates
        that the power of the channel is
        higher than the configured threshold
        <Condtype> CHANNEL21_POWER_HIGH_1
        <Probcause> degradedSignal (13)
        <Alarmtype> equipmentAlarm <Polarity>
        (2)
        "
	::= { pmopm2Almchannel21PortEntry 6 }


pmopm2AlmChannel21PowerLowPortn OBJECT-TYPE
	SYNTAX  EkiOnOff
	MAX-ACCESS read-only
	STATUS current
	DESCRIPTION
        "
        Channel Power Low 21 :This OID
        indicates that the power of the
        channel is lower than the configured
        threshold<Help> This alarm indicates
        that the power of the channel is
        lower than the configured threshold
        <Condtype> CHANNEL21_POWER_LOW_1
        <Probcause> degradedSignal (13)
        <Alarmtype> equipmentAlarm <Polarity>
        (2)
        "
	::= { pmopm2Almchannel21PortEntry 5 }


pmopm2AlmChannel21BalancedPortn OBJECT-TYPE
	SYNTAX  EkiOnOff
	MAX-ACCESS read-only
	STATUS current
	DESCRIPTION
        "
        Channel Balanced 21 :This OID
         indicates that an in service channel
        is balanced by the Ekinops auto
        turn up application<Help> This
         status indicates that an in service
        channel is balanced by the Ekinops
        auto turn up application <Condtype>
        CHANNEL21_BALANCED_1 <Probcause>
        informationalStatus(1000) <Alarmtype>
        other (1) <Polarity> (2)
        "
	::= { pmopm2Almchannel21PortEntry 4 }


pmopm2AlmChannel21MismatchPortn OBJECT-TYPE
	SYNTAX  EkiOnOff
	MAX-ACCESS read-only
	STATUS current
	DESCRIPTION
        "
        Channel Mismatch 21 :This OID
         indicates that an out of service
        channel is detected on the Optical
        Power Monitoring input<Help> This
        alarm indicates that an out of
         service channel is detected on
        the Optical Power Monitoring input
        <Condtype> CHANNEL21_MISMATCH_1
        <Probcause> unexpectedInformation
        (75) <Alarmtype> equipmentAlarm
        <Polarity> (2)
        "
	::= { pmopm2Almchannel21PortEntry 3 }


pmopm2AlmChannel21AbsentPortn OBJECT-TYPE
	SYNTAX  EkiOnOff
	MAX-ACCESS read-only
	STATUS current
	DESCRIPTION
        "
        Channel Absent 21 :This OID indicates
        that an in service channel is absent
        on the Optical Power Monitoring
        input<Help> This alarm indicates
        that an in service channel is absent
        on the Optical Power Monitoring
        input <Condtype> CHANNEL21_ABSENT_1
        <Probcause> informationMissing
         (65) <Alarmtype> equipmentAlarm
        (5) <Polarity> (2)
        "
	::= { pmopm2Almchannel21PortEntry 2 }


--- *********************************************************
---     TABLE for the pmopm2Almchannel22Port articles
--- *********************************************************

pmopm2Almchannel22PortTable OBJECT-TYPE
	SYNTAX  SEQUENCE OF Pmopm2Almchannel22PortEntry
	MAX-ACCESS not-accessible
	STATUS current
	DESCRIPTION
        "
        List of pmopm2Almchannel22Port
        Article
        "
	::= { pmopm2AlmClientCrit 58 }


pmopm2Almchannel22PortEntry OBJECT-TYPE
	SYNTAX Pmopm2Almchannel22PortEntry
	MAX-ACCESS not-accessible
	STATUS current
	DESCRIPTION
        "
        Row definition for the pmopm2Almchannel22Port
        table
        "
	INDEX   { pmopm2Almchannel22PortIndex }
	::= { pmopm2Almchannel22PortTable 1 }


Pmopm2Almchannel22PortEntry ::=
	SEQUENCE {
	pmopm2Almchannel22PortIndex
		INTEGER,
	pmopm2AlmChannel22OosPortn
		EkiOnOff,
	pmopm2AlmChannel22PowerHighPortn
		EkiOnOff,
	pmopm2AlmChannel22PowerLowPortn
		EkiOnOff,
	pmopm2AlmChannel22BalancedPortn
		EkiOnOff,
	pmopm2AlmChannel22MismatchPortn
		EkiOnOff,
	pmopm2AlmChannel22AbsentPortn
		EkiOnOff
	}


pmopm2Almchannel22PortIndex OBJECT-TYPE
	SYNTAX  INTEGER(0..128)
	MAX-ACCESS  read-only
	STATUS current
	DESCRIPTION
        "
        Index definition for the pmopm2Almchannel22Port
        table
        "
	::= { pmopm2Almchannel22PortEntry 1 }


pmopm2AlmChannel22OosPortn OBJECT-TYPE
	SYNTAX  EkiOnOff
	MAX-ACCESS read-only
	STATUS current
	DESCRIPTION
        "
        Channel Out Of Service 22 :This
        OID indicates that the channel
         is out of service  <Help> This
        alarm indicates that the channel
        is in service <Condtype> CHANNEL22_OOS_1
        <Probcause> informationalStatus(1000)
        <Alarmtype> other (1) <Polarity>
        (2)
        "
	::= { pmopm2Almchannel22PortEntry 7 }


pmopm2AlmChannel22PowerHighPortn OBJECT-TYPE
	SYNTAX  EkiOnOff
	MAX-ACCESS read-only
	STATUS current
	DESCRIPTION
        "
        Channel Power High 22 :This OID
        indicates that the power of the
        channel is higher than the configured
        threshold<Help> This alarm indicates
        that the power of the channel is
        higher than the configured threshold
        <Condtype> CHANNEL22_POWER_HIGH_1
        <Probcause> degradedSignal (13)
        <Alarmtype> equipmentAlarm <Polarity>
        (2)
        "
	::= { pmopm2Almchannel22PortEntry 6 }


pmopm2AlmChannel22PowerLowPortn OBJECT-TYPE
	SYNTAX  EkiOnOff
	MAX-ACCESS read-only
	STATUS current
	DESCRIPTION
        "
        Channel Power Low 22 :This OID
        indicates that the power of the
        channel is lower than the configured
        threshold<Help> This alarm indicates
        that the power of the channel is
        lower than the configured threshold
        <Condtype> CHANNEL22_POWER_LOW_1
        <Probcause> degradedSignal (13)
        <Alarmtype> equipmentAlarm <Polarity>
        (2)
        "
	::= { pmopm2Almchannel22PortEntry 5 }


pmopm2AlmChannel22BalancedPortn OBJECT-TYPE
	SYNTAX  EkiOnOff
	MAX-ACCESS read-only
	STATUS current
	DESCRIPTION
        "
        Channel Balanced 22 :This OID
         indicates that an in service channel
        is balanced by the Ekinops auto
        turn up application<Help> This
         status indicates that an in service
        channel is balanced by the Ekinops
        auto turn up application <Condtype>
        CHANNEL22_BALANCED_1 <Probcause>
        informationalStatus(1000) <Alarmtype>
        other (1) <Polarity> (2)
        "
	::= { pmopm2Almchannel22PortEntry 4 }


pmopm2AlmChannel22MismatchPortn OBJECT-TYPE
	SYNTAX  EkiOnOff
	MAX-ACCESS read-only
	STATUS current
	DESCRIPTION
        "
        Channel Mismatch 22 :This OID
         indicates that an out of service
        channel is detected on the Optical
        Power Monitoring input<Help> This
        alarm indicates that an out of
         service channel is detected on
        the Optical Power Monitoring input
        <Condtype> CHANNEL22_MISMATCH_1
        <Probcause> unexpectedInformation
        (75) <Alarmtype> equipmentAlarm
        <Polarity> (2)
        "
	::= { pmopm2Almchannel22PortEntry 3 }


pmopm2AlmChannel22AbsentPortn OBJECT-TYPE
	SYNTAX  EkiOnOff
	MAX-ACCESS read-only
	STATUS current
	DESCRIPTION
        "
        Channel Absent 22 :This OID indicates
        that an in service channel is absent
        on the Optical Power Monitoring
        input<Help> This alarm indicates
        that an in service channel is absent
        on the Optical Power Monitoring
        input <Condtype> CHANNEL22_ABSENT_1
        <Probcause> informationMissing
         (65) <Alarmtype> equipmentAlarm
        (5) <Polarity> (2)
        "
	::= { pmopm2Almchannel22PortEntry 2 }


--- *********************************************************
---     TABLE for the pmopm2Almchannel23Port articles
--- *********************************************************

pmopm2Almchannel23PortTable OBJECT-TYPE
	SYNTAX  SEQUENCE OF Pmopm2Almchannel23PortEntry
	MAX-ACCESS not-accessible
	STATUS current
	DESCRIPTION
        "
        List of pmopm2Almchannel23Port
        Article
        "
	::= { pmopm2AlmClientCrit 60 }


pmopm2Almchannel23PortEntry OBJECT-TYPE
	SYNTAX Pmopm2Almchannel23PortEntry
	MAX-ACCESS not-accessible
	STATUS current
	DESCRIPTION
        "
        Row definition for the pmopm2Almchannel23Port
        table
        "
	INDEX   { pmopm2Almchannel23PortIndex }
	::= { pmopm2Almchannel23PortTable 1 }


Pmopm2Almchannel23PortEntry ::=
	SEQUENCE {
	pmopm2Almchannel23PortIndex
		INTEGER,
	pmopm2AlmChannel23OosPortn
		EkiOnOff,
	pmopm2AlmChannel23PowerHighPortn
		EkiOnOff,
	pmopm2AlmChannel23PowerLowPortn
		EkiOnOff,
	pmopm2AlmChannel23BalancedPortn
		EkiOnOff,
	pmopm2AlmChannel23MismatchPortn
		EkiOnOff,
	pmopm2AlmChannel23AbsentPortn
		EkiOnOff
	}


pmopm2Almchannel23PortIndex OBJECT-TYPE
	SYNTAX  INTEGER(0..128)
	MAX-ACCESS  read-only
	STATUS current
	DESCRIPTION
        "
        Index definition for the pmopm2Almchannel23Port
        table
        "
	::= { pmopm2Almchannel23PortEntry 1 }


pmopm2AlmChannel23OosPortn OBJECT-TYPE
	SYNTAX  EkiOnOff
	MAX-ACCESS read-only
	STATUS current
	DESCRIPTION
        "
        Channel Out Of Service 23 :This
        OID indicates that the channel
         is out of service  <Help> This
        alarm indicates that the channel
        is in service <Condtype> CHANNEL23_OOS_1
        <Probcause> informationalStatus(1000)
        <Alarmtype> other (1) <Polarity>
        (2)
        "
	::= { pmopm2Almchannel23PortEntry 7 }


pmopm2AlmChannel23PowerHighPortn OBJECT-TYPE
	SYNTAX  EkiOnOff
	MAX-ACCESS read-only
	STATUS current
	DESCRIPTION
        "
        Channel Power High 23 :This OID
        indicates that the power of the
        channel is higher than the configured
        threshold<Help> This alarm indicates
        that the power of the channel is
        higher than the configured threshold
        <Condtype> CHANNEL23_POWER_HIGH_1
        <Probcause> degradedSignal (13)
        <Alarmtype> equipmentAlarm <Polarity>
        (2)
        "
	::= { pmopm2Almchannel23PortEntry 6 }


pmopm2AlmChannel23PowerLowPortn OBJECT-TYPE
	SYNTAX  EkiOnOff
	MAX-ACCESS read-only
	STATUS current
	DESCRIPTION
        "
        Channel Power Low 23 :This OID
        indicates that the power of the
        channel is lower than the configured
        threshold<Help> This alarm indicates
        that the power of the channel is
        lower than the configured threshold
        <Condtype> CHANNEL23_POWER_LOW_1
        <Probcause> degradedSignal (13)
        <Alarmtype> equipmentAlarm <Polarity>
        (2)
        "
	::= { pmopm2Almchannel23PortEntry 5 }


pmopm2AlmChannel23BalancedPortn OBJECT-TYPE
	SYNTAX  EkiOnOff
	MAX-ACCESS read-only
	STATUS current
	DESCRIPTION
        "
        Channel Balanced 23 :This OID
         indicates that an in service channel
        is balanced by the Ekinops auto
        turn up application<Help> This
         status indicates that an in service
        channel is balanced by the Ekinops
        auto turn up application <Condtype>
        CHANNEL23_BALANCED_1 <Probcause>
        informationalStatus(1000) <Alarmtype>
        other (1) <Polarity> (2)
        "
	::= { pmopm2Almchannel23PortEntry 4 }


pmopm2AlmChannel23MismatchPortn OBJECT-TYPE
	SYNTAX  EkiOnOff
	MAX-ACCESS read-only
	STATUS current
	DESCRIPTION
        "
        Channel Mismatch 23 :This OID
         indicates that an out of service
        channel is detected on the Optical
        Power Monitoring input<Help> This
        alarm indicates that an out of
         service channel is detected on
        the Optical Power Monitoring input
        <Condtype> CHANNEL23_MISMATCH_1
        <Probcause> unexpectedInformation
        (75) <Alarmtype> equipmentAlarm
        <Polarity> (2)
        "
	::= { pmopm2Almchannel23PortEntry 3 }


pmopm2AlmChannel23AbsentPortn OBJECT-TYPE
	SYNTAX  EkiOnOff
	MAX-ACCESS read-only
	STATUS current
	DESCRIPTION
        "
        Channel Absent 23 :This OID indicates
        that an in service channel is absent
        on the Optical Power Monitoring
        input<Help> This alarm indicates
        that an in service channel is absent
        on the Optical Power Monitoring
        input <Condtype> CHANNEL23_ABSENT_1
        <Probcause> informationMissing
         (65) <Alarmtype> equipmentAlarm
        (5) <Polarity> (2)
        "
	::= { pmopm2Almchannel23PortEntry 2 }


--- *********************************************************
---     TABLE for the pmopm2Almchannel24Port articles
--- *********************************************************

pmopm2Almchannel24PortTable OBJECT-TYPE
	SYNTAX  SEQUENCE OF Pmopm2Almchannel24PortEntry
	MAX-ACCESS not-accessible
	STATUS current
	DESCRIPTION
        "
        List of pmopm2Almchannel24Port
        Article
        "
	::= { pmopm2AlmClientCrit 62 }


pmopm2Almchannel24PortEntry OBJECT-TYPE
	SYNTAX Pmopm2Almchannel24PortEntry
	MAX-ACCESS not-accessible
	STATUS current
	DESCRIPTION
        "
        Row definition for the pmopm2Almchannel24Port
        table
        "
	INDEX   { pmopm2Almchannel24PortIndex }
	::= { pmopm2Almchannel24PortTable 1 }


Pmopm2Almchannel24PortEntry ::=
	SEQUENCE {
	pmopm2Almchannel24PortIndex
		INTEGER,
	pmopm2AlmChannel24OosPortn
		EkiOnOff,
	pmopm2AlmChannel24PowerHighPortn
		EkiOnOff,
	pmopm2AlmChannel24PowerLowPortn
		EkiOnOff,
	pmopm2AlmChannel24BalancedPortn
		EkiOnOff,
	pmopm2AlmChannel24MismatchPortn
		EkiOnOff,
	pmopm2AlmChannel24AbsentPortn
		EkiOnOff
	}


pmopm2Almchannel24PortIndex OBJECT-TYPE
	SYNTAX  INTEGER(0..128)
	MAX-ACCESS  read-only
	STATUS current
	DESCRIPTION
        "
        Index definition for the pmopm2Almchannel24Port
        table
        "
	::= { pmopm2Almchannel24PortEntry 1 }


pmopm2AlmChannel24OosPortn OBJECT-TYPE
	SYNTAX  EkiOnOff
	MAX-ACCESS read-only
	STATUS current
	DESCRIPTION
        "
        Channel Out Of Service 24 :This
        OID indicates that the channel
         is out of service  <Help> This
        alarm indicates that the channel
        is in service <Condtype> CHANNEL24_OOS_1
        <Probcause> informationalStatus(1000)
        <Alarmtype> other (1) <Polarity>
        (2)
        "
	::= { pmopm2Almchannel24PortEntry 7 }


pmopm2AlmChannel24PowerHighPortn OBJECT-TYPE
	SYNTAX  EkiOnOff
	MAX-ACCESS read-only
	STATUS current
	DESCRIPTION
        "
        Channel Power High 24 :This OID
        indicates that the power of the
        channel is higher than the configured
        threshold<Help> This alarm indicates
        that the power of the channel is
        higher than the configured threshold
        <Condtype> CHANNEL24_POWER_HIGH_1
        <Probcause> degradedSignal (13)
        <Alarmtype> equipmentAlarm <Polarity>
        (2)
        "
	::= { pmopm2Almchannel24PortEntry 6 }


pmopm2AlmChannel24PowerLowPortn OBJECT-TYPE
	SYNTAX  EkiOnOff
	MAX-ACCESS read-only
	STATUS current
	DESCRIPTION
        "
        Channel Power Low 24 :This OID
        indicates that the power of the
        channel is lower than the configured
        threshold<Help> This alarm indicates
        that the power of the channel is
        lower than the configured threshold
        <Condtype> CHANNEL24_POWER_LOW_1
        <Probcause> degradedSignal (13)
        <Alarmtype> equipmentAlarm <Polarity>
        (2)
        "
	::= { pmopm2Almchannel24PortEntry 5 }


pmopm2AlmChannel24BalancedPortn OBJECT-TYPE
	SYNTAX  EkiOnOff
	MAX-ACCESS read-only
	STATUS current
	DESCRIPTION
        "
        Channel Balanced 24 :This OID
         indicates that an in service channel
        is balanced by the Ekinops auto
        turn up application<Help> This
         status indicates that an in service
        channel is balanced by the Ekinops
        auto turn up application <Condtype>
        CHANNEL24_BALANCED_1 <Probcause>
        informationalStatus(1000) <Alarmtype>
        other (1) <Polarity> (2)
        "
	::= { pmopm2Almchannel24PortEntry 4 }


pmopm2AlmChannel24MismatchPortn OBJECT-TYPE
	SYNTAX  EkiOnOff
	MAX-ACCESS read-only
	STATUS current
	DESCRIPTION
        "
        Channel Mismatch 24 :This OID
         indicates that an out of service
        channel is detected on the Optical
        Power Monitoring input<Help> This
        alarm indicates that an out of
         service channel is detected on
        the Optical Power Monitoring input
        <Condtype> CHANNEL24_MISMATCH_1
        <Probcause> unexpectedInformation
        (75) <Alarmtype> equipmentAlarm
        <Polarity> (2)
        "
	::= { pmopm2Almchannel24PortEntry 3 }


pmopm2AlmChannel24AbsentPortn OBJECT-TYPE
	SYNTAX  EkiOnOff
	MAX-ACCESS read-only
	STATUS current
	DESCRIPTION
        "
        Channel Absent 24 :This OID indicates
        that an in service channel is absent
        on the Optical Power Monitoring
        input<Help> This alarm indicates
        that an in service channel is absent
        on the Optical Power Monitoring
        input <Condtype> CHANNEL24_ABSENT_1
        <Probcause> informationMissing
         (65) <Alarmtype> equipmentAlarm
        (5) <Polarity> (2)
        "
	::= { pmopm2Almchannel24PortEntry 2 }


--- *********************************************************
---     TABLE for the pmopm2Almchannel25Port articles
--- *********************************************************

pmopm2Almchannel25PortTable OBJECT-TYPE
	SYNTAX  SEQUENCE OF Pmopm2Almchannel25PortEntry
	MAX-ACCESS not-accessible
	STATUS current
	DESCRIPTION
        "
        List of pmopm2Almchannel25Port
        Article
        "
	::= { pmopm2AlmClientCrit 64 }


pmopm2Almchannel25PortEntry OBJECT-TYPE
	SYNTAX Pmopm2Almchannel25PortEntry
	MAX-ACCESS not-accessible
	STATUS current
	DESCRIPTION
        "
        Row definition for the pmopm2Almchannel25Port
        table
        "
	INDEX   { pmopm2Almchannel25PortIndex }
	::= { pmopm2Almchannel25PortTable 1 }


Pmopm2Almchannel25PortEntry ::=
	SEQUENCE {
	pmopm2Almchannel25PortIndex
		INTEGER,
	pmopm2AlmChannel25OosPortn
		EkiOnOff,
	pmopm2AlmChannel25PowerHighPortn
		EkiOnOff,
	pmopm2AlmChannel25PowerLowPortn
		EkiOnOff,
	pmopm2AlmChannel25BalancedPortn
		EkiOnOff,
	pmopm2AlmChannel25MismatchPortn
		EkiOnOff,
	pmopm2AlmChannel25AbsentPortn
		EkiOnOff
	}


pmopm2Almchannel25PortIndex OBJECT-TYPE
	SYNTAX  INTEGER(0..128)
	MAX-ACCESS  read-only
	STATUS current
	DESCRIPTION
        "
        Index definition for the pmopm2Almchannel25Port
        table
        "
	::= { pmopm2Almchannel25PortEntry 1 }


pmopm2AlmChannel25OosPortn OBJECT-TYPE
	SYNTAX  EkiOnOff
	MAX-ACCESS read-only
	STATUS current
	DESCRIPTION
        "
        Channel Out Of Service 25 :This
        OID indicates that the channel
         is out of service  <Help> This
        alarm indicates that the channel
        is in service <Condtype> CHANNEL25_OOS_1
        <Probcause> informationalStatus(1000)
        <Alarmtype> other (1) <Polarity>
        (2)
        "
	::= { pmopm2Almchannel25PortEntry 7 }


pmopm2AlmChannel25PowerHighPortn OBJECT-TYPE
	SYNTAX  EkiOnOff
	MAX-ACCESS read-only
	STATUS current
	DESCRIPTION
        "
        Channel Power High 25 :This OID
        indicates that the power of the
        channel is higher than the configured
        threshold<Help> This alarm indicates
        that the power of the channel is
        higher than the configured threshold
        <Condtype> CHANNEL25_POWER_HIGH_1
        <Probcause> degradedSignal (13)
        <Alarmtype> equipmentAlarm <Polarity>
        (2)
        "
	::= { pmopm2Almchannel25PortEntry 6 }


pmopm2AlmChannel25PowerLowPortn OBJECT-TYPE
	SYNTAX  EkiOnOff
	MAX-ACCESS read-only
	STATUS current
	DESCRIPTION
        "
        Channel Power Low 25 :This OID
        indicates that the power of the
        channel is lower than the configured
        threshold<Help> This alarm indicates
        that the power of the channel is
        lower than the configured threshold
        <Condtype> CHANNEL25_POWER_LOW_1
        <Probcause> degradedSignal (13)
        <Alarmtype> equipmentAlarm <Polarity>
        (2)
        "
	::= { pmopm2Almchannel25PortEntry 5 }


pmopm2AlmChannel25BalancedPortn OBJECT-TYPE
	SYNTAX  EkiOnOff
	MAX-ACCESS read-only
	STATUS current
	DESCRIPTION
        "
        Channel Balanced 25 :This OID
         indicates that an in service channel
        is balanced by the Ekinops auto
        turn up application<Help> This
         status indicates that an in service
        channel is balanced by the Ekinops
        auto turn up application <Condtype>
        CHANNEL25_BALANCED_1 <Probcause>
        informationalStatus(1000) <Alarmtype>
        other (1) <Polarity> (2)
        "
	::= { pmopm2Almchannel25PortEntry 4 }


pmopm2AlmChannel25MismatchPortn OBJECT-TYPE
	SYNTAX  EkiOnOff
	MAX-ACCESS read-only
	STATUS current
	DESCRIPTION
        "
        Channel Mismatch 25 :This OID
         indicates that an out of service
        channel is detected on the Optical
        Power Monitoring input<Help> This
        alarm indicates that an out of
         service channel is detected on
        the Optical Power Monitoring input
        <Condtype> CHANNEL25_MISMATCH_1
        <Probcause> unexpectedInformation
        (75) <Alarmtype> equipmentAlarm
        <Polarity> (2)
        "
	::= { pmopm2Almchannel25PortEntry 3 }


pmopm2AlmChannel25AbsentPortn OBJECT-TYPE
	SYNTAX  EkiOnOff
	MAX-ACCESS read-only
	STATUS current
	DESCRIPTION
        "
        Channel Absent 25 :This OID indicates
        that an in service channel is absent
        on the Optical Power Monitoring
        input<Help> This alarm indicates
        that an in service channel is absent
        on the Optical Power Monitoring
        input <Condtype> CHANNEL25_ABSENT_1
        <Probcause> informationMissing
         (65) <Alarmtype> equipmentAlarm
        (5) <Polarity> (2)
        "
	::= { pmopm2Almchannel25PortEntry 2 }


--- *********************************************************
---     TABLE for the pmopm2Almchannel26Port articles
--- *********************************************************

pmopm2Almchannel26PortTable OBJECT-TYPE
	SYNTAX  SEQUENCE OF Pmopm2Almchannel26PortEntry
	MAX-ACCESS not-accessible
	STATUS current
	DESCRIPTION
        "
        List of pmopm2Almchannel26Port
        Article
        "
	::= { pmopm2AlmClientCrit 66 }


pmopm2Almchannel26PortEntry OBJECT-TYPE
	SYNTAX Pmopm2Almchannel26PortEntry
	MAX-ACCESS not-accessible
	STATUS current
	DESCRIPTION
        "
        Row definition for the pmopm2Almchannel26Port
        table
        "
	INDEX   { pmopm2Almchannel26PortIndex }
	::= { pmopm2Almchannel26PortTable 1 }


Pmopm2Almchannel26PortEntry ::=
	SEQUENCE {
	pmopm2Almchannel26PortIndex
		INTEGER,
	pmopm2AlmChannel26OosPortn
		EkiOnOff,
	pmopm2AlmChannel26PowerHighPortn
		EkiOnOff,
	pmopm2AlmChannel26PowerLowPortn
		EkiOnOff,
	pmopm2AlmChannel26BalancedPortn
		EkiOnOff,
	pmopm2AlmChannel26MismatchPortn
		EkiOnOff,
	pmopm2AlmChannel26AbsentPortn
		EkiOnOff
	}


pmopm2Almchannel26PortIndex OBJECT-TYPE
	SYNTAX  INTEGER(0..128)
	MAX-ACCESS  read-only
	STATUS current
	DESCRIPTION
        "
        Index definition for the pmopm2Almchannel26Port
        table
        "
	::= { pmopm2Almchannel26PortEntry 1 }


pmopm2AlmChannel26OosPortn OBJECT-TYPE
	SYNTAX  EkiOnOff
	MAX-ACCESS read-only
	STATUS current
	DESCRIPTION
        "
        Channel Out Of Service 26 :This
        OID indicates that the channel
         is out of service  <Help> This
        alarm indicates that the channel
        is in service <Condtype> CHANNEL26_OOS_1
        <Probcause> informationalStatus(1000)
        <Alarmtype> other (1) <Polarity>
        (2)
        "
	::= { pmopm2Almchannel26PortEntry 7 }


pmopm2AlmChannel26PowerHighPortn OBJECT-TYPE
	SYNTAX  EkiOnOff
	MAX-ACCESS read-only
	STATUS current
	DESCRIPTION
        "
        Channel Power High 26 :This OID
        indicates that the power of the
        channel is higher than the configured
        threshold<Help> This alarm indicates
        that the power of the channel is
        higher than the configured threshold
        <Condtype> CHANNEL26_POWER_HIGH_1
        <Probcause> degradedSignal (13)
        <Alarmtype> equipmentAlarm <Polarity>
        (2)
        "
	::= { pmopm2Almchannel26PortEntry 6 }


pmopm2AlmChannel26PowerLowPortn OBJECT-TYPE
	SYNTAX  EkiOnOff
	MAX-ACCESS read-only
	STATUS current
	DESCRIPTION
        "
        Channel Power Low 26 :This OID
        indicates that the power of the
        channel is lower than the configured
        threshold<Help> This alarm indicates
        that the power of the channel is
        lower than the configured threshold
        <Condtype> CHANNEL26_POWER_LOW_1
        <Probcause> degradedSignal (13)
        <Alarmtype> equipmentAlarm <Polarity>
        (2)
        "
	::= { pmopm2Almchannel26PortEntry 5 }


pmopm2AlmChannel26BalancedPortn OBJECT-TYPE
	SYNTAX  EkiOnOff
	MAX-ACCESS read-only
	STATUS current
	DESCRIPTION
        "
        Channel Balanced 26 :This OID
         indicates that an in service channel
        is balanced by the Ekinops auto
        turn up application<Help> This
         status indicates that an in service
        channel is balanced by the Ekinops
        auto turn up application <Condtype>
        CHANNEL26_BALANCED_1 <Probcause>
        informationalStatus(1000) <Alarmtype>
        other (1) <Polarity> (2)
        "
	::= { pmopm2Almchannel26PortEntry 4 }


pmopm2AlmChannel26MismatchPortn OBJECT-TYPE
	SYNTAX  EkiOnOff
	MAX-ACCESS read-only
	STATUS current
	DESCRIPTION
        "
        Channel Mismatch 26 :This OID
         indicates that an out of service
        channel is detected on the Optical
        Power Monitoring input<Help> This
        alarm indicates that an out of
         service channel is detected on
        the Optical Power Monitoring input
        <Condtype> CHANNEL26_MISMATCH_1
        <Probcause> unexpectedInformation
        (75) <Alarmtype> equipmentAlarm
        <Polarity> (2)
        "
	::= { pmopm2Almchannel26PortEntry 3 }


pmopm2AlmChannel26AbsentPortn OBJECT-TYPE
	SYNTAX  EkiOnOff
	MAX-ACCESS read-only
	STATUS current
	DESCRIPTION
        "
        Channel Absent 26 :This OID indicates
        that an in service channel is absent
        on the Optical Power Monitoring
        input<Help> This alarm indicates
        that an in service channel is absent
        on the Optical Power Monitoring
        input <Condtype> CHANNEL26_ABSENT_1
        <Probcause> informationMissing
         (65) <Alarmtype> equipmentAlarm
        (5) <Polarity> (2)
        "
	::= { pmopm2Almchannel26PortEntry 2 }


--- *********************************************************
---     TABLE for the pmopm2Almchannel27Port articles
--- *********************************************************

pmopm2Almchannel27PortTable OBJECT-TYPE
	SYNTAX  SEQUENCE OF Pmopm2Almchannel27PortEntry
	MAX-ACCESS not-accessible
	STATUS current
	DESCRIPTION
        "
        List of pmopm2Almchannel27Port
        Article
        "
	::= { pmopm2AlmClientCrit 68 }


pmopm2Almchannel27PortEntry OBJECT-TYPE
	SYNTAX Pmopm2Almchannel27PortEntry
	MAX-ACCESS not-accessible
	STATUS current
	DESCRIPTION
        "
        Row definition for the pmopm2Almchannel27Port
        table
        "
	INDEX   { pmopm2Almchannel27PortIndex }
	::= { pmopm2Almchannel27PortTable 1 }


Pmopm2Almchannel27PortEntry ::=
	SEQUENCE {
	pmopm2Almchannel27PortIndex
		INTEGER,
	pmopm2AlmChannel27OosPortn
		EkiOnOff,
	pmopm2AlmChannel27PowerHighPortn
		EkiOnOff,
	pmopm2AlmChannel27PowerLowPortn
		EkiOnOff,
	pmopm2AlmChannel27BalancedPortn
		EkiOnOff,
	pmopm2AlmChannel27MismatchPortn
		EkiOnOff,
	pmopm2AlmChannel27AbsentPortn
		EkiOnOff
	}


pmopm2Almchannel27PortIndex OBJECT-TYPE
	SYNTAX  INTEGER(0..128)
	MAX-ACCESS  read-only
	STATUS current
	DESCRIPTION
        "
        Index definition for the pmopm2Almchannel27Port
        table
        "
	::= { pmopm2Almchannel27PortEntry 1 }


pmopm2AlmChannel27OosPortn OBJECT-TYPE
	SYNTAX  EkiOnOff
	MAX-ACCESS read-only
	STATUS current
	DESCRIPTION
        "
        Channel Out Of Service 27 :This
        OID indicates that the channel
         is out of service  <Help> This
        alarm indicates that the channel
        is in service <Condtype> CHANNEL27_OOS_1
        <Probcause> informationalStatus(1000)
        <Alarmtype> other (1) <Polarity>
        (2)
        "
	::= { pmopm2Almchannel27PortEntry 7 }


pmopm2AlmChannel27PowerHighPortn OBJECT-TYPE
	SYNTAX  EkiOnOff
	MAX-ACCESS read-only
	STATUS current
	DESCRIPTION
        "
        Channel Power High 27 :This OID
        indicates that the power of the
        channel is higher than the configured
        threshold<Help> This alarm indicates
        that the power of the channel is
        higher than the configured threshold
        <Condtype> CHANNEL27_POWER_HIGH_1
        <Probcause> degradedSignal (13)
        <Alarmtype> equipmentAlarm <Polarity>
        (2)
        "
	::= { pmopm2Almchannel27PortEntry 6 }


pmopm2AlmChannel27PowerLowPortn OBJECT-TYPE
	SYNTAX  EkiOnOff
	MAX-ACCESS read-only
	STATUS current
	DESCRIPTION
        "
        Channel Power Low 27 :This OID
        indicates that the power of the
        channel is lower than the configured
        threshold<Help> This alarm indicates
        that the power of the channel is
        lower than the configured threshold
        <Condtype> CHANNEL27_POWER_LOW_1
        <Probcause> degradedSignal (13)
        <Alarmtype> equipmentAlarm <Polarity>
        (2)
        "
	::= { pmopm2Almchannel27PortEntry 5 }


pmopm2AlmChannel27BalancedPortn OBJECT-TYPE
	SYNTAX  EkiOnOff
	MAX-ACCESS read-only
	STATUS current
	DESCRIPTION
        "
        Channel Balanced 27 :This OID
         indicates that an in service channel
        is balanced by the Ekinops auto
        turn up application<Help> This
         status indicates that an in service
        channel is balanced by the Ekinops
        auto turn up application <Condtype>
        CHANNEL27_BALANCED_1 <Probcause>
        informationalStatus(1000) <Alarmtype>
        other (1) <Polarity> (2)
        "
	::= { pmopm2Almchannel27PortEntry 4 }


pmopm2AlmChannel27MismatchPortn OBJECT-TYPE
	SYNTAX  EkiOnOff
	MAX-ACCESS read-only
	STATUS current
	DESCRIPTION
        "
        Channel Mismatch 27 :This OID
         indicates that an out of service
        channel is detected on the Optical
        Power Monitoring input<Help> This
        alarm indicates that an out of
         service channel is detected on
        the Optical Power Monitoring input
        <Condtype> CHANNEL27_MISMATCH_1
        <Probcause> unexpectedInformation
        (75) <Alarmtype> equipmentAlarm
        <Polarity> (2)
        "
	::= { pmopm2Almchannel27PortEntry 3 }


pmopm2AlmChannel27AbsentPortn OBJECT-TYPE
	SYNTAX  EkiOnOff
	MAX-ACCESS read-only
	STATUS current
	DESCRIPTION
        "
        Channel Absent 27 :This OID indicates
        that an in service channel is absent
        on the Optical Power Monitoring
        input<Help> This alarm indicates
        that an in service channel is absent
        on the Optical Power Monitoring
        input <Condtype> CHANNEL27_ABSENT_1
        <Probcause> informationMissing
         (65) <Alarmtype> equipmentAlarm
        (5) <Polarity> (2)
        "
	::= { pmopm2Almchannel27PortEntry 2 }


--- *********************************************************
---     TABLE for the pmopm2Almchannel28Port articles
--- *********************************************************

pmopm2Almchannel28PortTable OBJECT-TYPE
	SYNTAX  SEQUENCE OF Pmopm2Almchannel28PortEntry
	MAX-ACCESS not-accessible
	STATUS current
	DESCRIPTION
        "
        List of pmopm2Almchannel28Port
        Article
        "
	::= { pmopm2AlmClientCrit 70 }


pmopm2Almchannel28PortEntry OBJECT-TYPE
	SYNTAX Pmopm2Almchannel28PortEntry
	MAX-ACCESS not-accessible
	STATUS current
	DESCRIPTION
        "
        Row definition for the pmopm2Almchannel28Port
        table
        "
	INDEX   { pmopm2Almchannel28PortIndex }
	::= { pmopm2Almchannel28PortTable 1 }


Pmopm2Almchannel28PortEntry ::=
	SEQUENCE {
	pmopm2Almchannel28PortIndex
		INTEGER,
	pmopm2AlmChannel28OosPortn
		EkiOnOff,
	pmopm2AlmChannel28PowerHighPortn
		EkiOnOff,
	pmopm2AlmChannel28PowerLowPortn
		EkiOnOff,
	pmopm2AlmChannel28BalancedPortn
		EkiOnOff,
	pmopm2AlmChannel28MismatchPortn
		EkiOnOff,
	pmopm2AlmChannel28AbsentPortn
		EkiOnOff
	}


pmopm2Almchannel28PortIndex OBJECT-TYPE
	SYNTAX  INTEGER(0..128)
	MAX-ACCESS  read-only
	STATUS current
	DESCRIPTION
        "
        Index definition for the pmopm2Almchannel28Port
        table
        "
	::= { pmopm2Almchannel28PortEntry 1 }


pmopm2AlmChannel28OosPortn OBJECT-TYPE
	SYNTAX  EkiOnOff
	MAX-ACCESS read-only
	STATUS current
	DESCRIPTION
        "
        Channel Out Of Service 28 :This
        OID indicates that the channel
         is out of service  <Help> This
        alarm indicates that the channel
        is in service <Condtype> CHANNEL28_OOS_1
        <Probcause> informationalStatus(1000)
        <Alarmtype> other (1) <Polarity>
        (2)
        "
	::= { pmopm2Almchannel28PortEntry 7 }


pmopm2AlmChannel28PowerHighPortn OBJECT-TYPE
	SYNTAX  EkiOnOff
	MAX-ACCESS read-only
	STATUS current
	DESCRIPTION
        "
        Channel Power High 28 :This OID
        indicates that the power of the
        channel is higher than the configured
        threshold<Help> This alarm indicates
        that the power of the channel is
        higher than the configured threshold
        <Condtype> CHANNEL28_POWER_HIGH_1
        <Probcause> degradedSignal (13)
        <Alarmtype> equipmentAlarm <Polarity>
        (2)
        "
	::= { pmopm2Almchannel28PortEntry 6 }


pmopm2AlmChannel28PowerLowPortn OBJECT-TYPE
	SYNTAX  EkiOnOff
	MAX-ACCESS read-only
	STATUS current
	DESCRIPTION
        "
        Channel Power Low 28 :This OID
        indicates that the power of the
        channel is lower than the configured
        threshold<Help> This alarm indicates
        that the power of the channel is
        lower than the configured threshold
        <Condtype> CHANNEL28_POWER_LOW_1
        <Probcause> degradedSignal (13)
        <Alarmtype> equipmentAlarm <Polarity>
        (2)
        "
	::= { pmopm2Almchannel28PortEntry 5 }


pmopm2AlmChannel28BalancedPortn OBJECT-TYPE
	SYNTAX  EkiOnOff
	MAX-ACCESS read-only
	STATUS current
	DESCRIPTION
        "
        Channel Balanced 28 :This OID
         indicates that an in service channel
        is balanced by the Ekinops auto
        turn up application<Help> This
         status indicates that an in service
        channel is balanced by the Ekinops
        auto turn up application <Condtype>
        CHANNEL28_BALANCED_1 <Probcause>
        informationalStatus(1000) <Alarmtype>
        other (1) <Polarity> (2)
        "
	::= { pmopm2Almchannel28PortEntry 4 }


pmopm2AlmChannel28MismatchPortn OBJECT-TYPE
	SYNTAX  EkiOnOff
	MAX-ACCESS read-only
	STATUS current
	DESCRIPTION
        "
        Channel Mismatch 28 :This OID
         indicates that an out of service
        channel is detected on the Optical
        Power Monitoring input<Help> This
        alarm indicates that an out of
         service channel is detected on
        the Optical Power Monitoring input
        <Condtype> CHANNEL28_MISMATCH_1
        <Probcause> unexpectedInformation
        (75) <Alarmtype> equipmentAlarm
        <Polarity> (2)
        "
	::= { pmopm2Almchannel28PortEntry 3 }


pmopm2AlmChannel28AbsentPortn OBJECT-TYPE
	SYNTAX  EkiOnOff
	MAX-ACCESS read-only
	STATUS current
	DESCRIPTION
        "
        Channel Absent 28 :This OID indicates
        that an in service channel is absent
        on the Optical Power Monitoring
        input<Help> This alarm indicates
        that an in service channel is absent
        on the Optical Power Monitoring
        input <Condtype> CHANNEL28_ABSENT_1
        <Probcause> informationMissing
         (65) <Alarmtype> equipmentAlarm
        (5) <Polarity> (2)
        "
	::= { pmopm2Almchannel28PortEntry 2 }


--- *********************************************************
---     TABLE for the pmopm2Almchannel29Port articles
--- *********************************************************

pmopm2Almchannel29PortTable OBJECT-TYPE
	SYNTAX  SEQUENCE OF Pmopm2Almchannel29PortEntry
	MAX-ACCESS not-accessible
	STATUS current
	DESCRIPTION
        "
        List of pmopm2Almchannel29Port
        Article
        "
	::= { pmopm2AlmClientCrit 72 }


pmopm2Almchannel29PortEntry OBJECT-TYPE
	SYNTAX Pmopm2Almchannel29PortEntry
	MAX-ACCESS not-accessible
	STATUS current
	DESCRIPTION
        "
        Row definition for the pmopm2Almchannel29Port
        table
        "
	INDEX   { pmopm2Almchannel29PortIndex }
	::= { pmopm2Almchannel29PortTable 1 }


Pmopm2Almchannel29PortEntry ::=
	SEQUENCE {
	pmopm2Almchannel29PortIndex
		INTEGER,
	pmopm2AlmChannel29OosPortn
		EkiOnOff,
	pmopm2AlmChannel29PowerHighPortn
		EkiOnOff,
	pmopm2AlmChannel29PowerLowPortn
		EkiOnOff,
	pmopm2AlmChannel29BalancedPortn
		EkiOnOff,
	pmopm2AlmChannel29MismatchPortn
		EkiOnOff,
	pmopm2AlmChannel29AbsentPortn
		EkiOnOff
	}


pmopm2Almchannel29PortIndex OBJECT-TYPE
	SYNTAX  INTEGER(0..128)
	MAX-ACCESS  read-only
	STATUS current
	DESCRIPTION
        "
        Index definition for the pmopm2Almchannel29Port
        table
        "
	::= { pmopm2Almchannel29PortEntry 1 }


pmopm2AlmChannel29OosPortn OBJECT-TYPE
	SYNTAX  EkiOnOff
	MAX-ACCESS read-only
	STATUS current
	DESCRIPTION
        "
        Channel Out Of Service 29 :This
        OID indicates that the channel
         is out of service  <Help> This
        alarm indicates that the channel
        is in service <Condtype> CHANNEL29_OOS_1
        <Probcause> informationalStatus(1000)
        <Alarmtype> other (1) <Polarity>
        (2)
        "
	::= { pmopm2Almchannel29PortEntry 7 }


pmopm2AlmChannel29PowerHighPortn OBJECT-TYPE
	SYNTAX  EkiOnOff
	MAX-ACCESS read-only
	STATUS current
	DESCRIPTION
        "
        Channel Power High 29 :This OID
        indicates that the power of the
        channel is higher than the configured
        threshold<Help> This alarm indicates
        that the power of the channel is
        higher than the configured threshold
        <Condtype> CHANNEL29_POWER_HIGH_1
        <Probcause> degradedSignal (13)
        <Alarmtype> equipmentAlarm <Polarity>
        (2)
        "
	::= { pmopm2Almchannel29PortEntry 6 }


pmopm2AlmChannel29PowerLowPortn OBJECT-TYPE
	SYNTAX  EkiOnOff
	MAX-ACCESS read-only
	STATUS current
	DESCRIPTION
        "
        Channel Power Low 29 :This OID
        indicates that the power of the
        channel is lower than the configured
        threshold<Help> This alarm indicates
        that the power of the channel is
        lower than the configured threshold
        <Condtype> CHANNEL29_POWER_LOW_1
        <Probcause> degradedSignal (13)
        <Alarmtype> equipmentAlarm <Polarity>
        (2)
        "
	::= { pmopm2Almchannel29PortEntry 5 }


pmopm2AlmChannel29BalancedPortn OBJECT-TYPE
	SYNTAX  EkiOnOff
	MAX-ACCESS read-only
	STATUS current
	DESCRIPTION
        "
        Channel Balanced 29 :This OID
         indicates that an in service channel
        is balanced by the Ekinops auto
        turn up application<Help> This
         status indicates that an in service
        channel is balanced by the Ekinops
        auto turn up application <Condtype>
        CHANNEL29_BALANCED_1 <Probcause>
        informationalStatus(1000) <Alarmtype>
        other (1) <Polarity> (2)
        "
	::= { pmopm2Almchannel29PortEntry 4 }


pmopm2AlmChannel29MismatchPortn OBJECT-TYPE
	SYNTAX  EkiOnOff
	MAX-ACCESS read-only
	STATUS current
	DESCRIPTION
        "
        Channel Mismatch 29 :This OID
         indicates that an out of service
        channel is detected on the Optical
        Power Monitoring input<Help> This
        alarm indicates that an out of
         service channel is detected on
        the Optical Power Monitoring input
        <Condtype> CHANNEL29_MISMATCH_1
        <Probcause> unexpectedInformation
        (75) <Alarmtype> equipmentAlarm
        <Polarity> (2)
        "
	::= { pmopm2Almchannel29PortEntry 3 }


pmopm2AlmChannel29AbsentPortn OBJECT-TYPE
	SYNTAX  EkiOnOff
	MAX-ACCESS read-only
	STATUS current
	DESCRIPTION
        "
        Channel Absent 29 :This OID indicates
        that an in service channel is absent
        on the Optical Power Monitoring
        input<Help> This alarm indicates
        that an in service channel is absent
        on the Optical Power Monitoring
        input <Condtype> CHANNEL29_ABSENT_1
        <Probcause> informationMissing
         (65) <Alarmtype> equipmentAlarm
        (5) <Polarity> (2)
        "
	::= { pmopm2Almchannel29PortEntry 2 }


--- *********************************************************
---     TABLE for the pmopm2Almchannel30Port articles
--- *********************************************************

pmopm2Almchannel30PortTable OBJECT-TYPE
	SYNTAX  SEQUENCE OF Pmopm2Almchannel30PortEntry
	MAX-ACCESS not-accessible
	STATUS current
	DESCRIPTION
        "
        List of pmopm2Almchannel30Port
        Article
        "
	::= { pmopm2AlmClientCrit 74 }


pmopm2Almchannel30PortEntry OBJECT-TYPE
	SYNTAX Pmopm2Almchannel30PortEntry
	MAX-ACCESS not-accessible
	STATUS current
	DESCRIPTION
        "
        Row definition for the pmopm2Almchannel30Port
        table
        "
	INDEX   { pmopm2Almchannel30PortIndex }
	::= { pmopm2Almchannel30PortTable 1 }


Pmopm2Almchannel30PortEntry ::=
	SEQUENCE {
	pmopm2Almchannel30PortIndex
		INTEGER,
	pmopm2AlmChannel30OosPortn
		EkiOnOff,
	pmopm2AlmChannel30PowerHighPortn
		EkiOnOff,
	pmopm2AlmChannel30PowerLowPortn
		EkiOnOff,
	pmopm2AlmChannel30BalancedPortn
		EkiOnOff,
	pmopm2AlmChannel30MismatchPortn
		EkiOnOff,
	pmopm2AlmChannel30AbsentPortn
		EkiOnOff
	}


pmopm2Almchannel30PortIndex OBJECT-TYPE
	SYNTAX  INTEGER(0..128)
	MAX-ACCESS  read-only
	STATUS current
	DESCRIPTION
        "
        Index definition for the pmopm2Almchannel30Port
        table
        "
	::= { pmopm2Almchannel30PortEntry 1 }


pmopm2AlmChannel30OosPortn OBJECT-TYPE
	SYNTAX  EkiOnOff
	MAX-ACCESS read-only
	STATUS current
	DESCRIPTION
        "
        Channel Out Of Service 30 :This
        OID indicates that the channel
         is out of service  <Help> This
        alarm indicates that the channel
        is in service <Condtype> CHANNEL30_OOS_1
        <Probcause> informationalStatus(1000)
        <Alarmtype> other (1) <Polarity>
        (2)
        "
	::= { pmopm2Almchannel30PortEntry 7 }


pmopm2AlmChannel30PowerHighPortn OBJECT-TYPE
	SYNTAX  EkiOnOff
	MAX-ACCESS read-only
	STATUS current
	DESCRIPTION
        "
        Channel Power High 30 :This OID
        indicates that the power of the
        channel is higher than the configured
        threshold<Help> This alarm indicates
        that the power of the channel is
        higher than the configured threshold
        <Condtype> CHANNEL30_POWER_HIGH_1
        <Probcause> degradedSignal (13)
        <Alarmtype> equipmentAlarm <Polarity>
        (2)
        "
	::= { pmopm2Almchannel30PortEntry 6 }


pmopm2AlmChannel30PowerLowPortn OBJECT-TYPE
	SYNTAX  EkiOnOff
	MAX-ACCESS read-only
	STATUS current
	DESCRIPTION
        "
        Channel Power Low 30 :This OID
        indicates that the power of the
        channel is lower than the configured
        threshold<Help> This alarm indicates
        that the power of the channel is
        lower than the configured threshold
        <Condtype> CHANNEL30_POWER_LOW_1
        <Probcause> degradedSignal (13)
        <Alarmtype> equipmentAlarm <Polarity>
        (2)
        "
	::= { pmopm2Almchannel30PortEntry 5 }


pmopm2AlmChannel30BalancedPortn OBJECT-TYPE
	SYNTAX  EkiOnOff
	MAX-ACCESS read-only
	STATUS current
	DESCRIPTION
        "
        Channel Balanced 30 :This OID
         indicates that an in service channel
        is balanced by the Ekinops auto
        turn up application<Help> This
         status indicates that an in service
        channel is balanced by the Ekinops
        auto turn up application <Condtype>
        CHANNEL30_BALANCED_1 <Probcause>
        informationalStatus(1000) <Alarmtype>
        other (1) <Polarity> (2)
        "
	::= { pmopm2Almchannel30PortEntry 4 }


pmopm2AlmChannel30MismatchPortn OBJECT-TYPE
	SYNTAX  EkiOnOff
	MAX-ACCESS read-only
	STATUS current
	DESCRIPTION
        "
        Channel Mismatch 30 :This OID
         indicates that an out of service
        channel is detected on the Optical
        Power Monitoring input<Help> This
        alarm indicates that an out of
         service channel is detected on
        the Optical Power Monitoring input
        <Condtype> CHANNEL30_MISMATCH_1
        <Probcause> unexpectedInformation
        (75) <Alarmtype> equipmentAlarm
        <Polarity> (2)
        "
	::= { pmopm2Almchannel30PortEntry 3 }


pmopm2AlmChannel30AbsentPortn OBJECT-TYPE
	SYNTAX  EkiOnOff
	MAX-ACCESS read-only
	STATUS current
	DESCRIPTION
        "
        Channel Absent 30 :This OID indicates
        that an in service channel is absent
        on the Optical Power Monitoring
        input<Help> This alarm indicates
        that an in service channel is absent
        on the Optical Power Monitoring
        input <Condtype> CHANNEL30_ABSENT_1
        <Probcause> informationMissing
         (65) <Alarmtype> equipmentAlarm
        (5) <Polarity> (2)
        "
	::= { pmopm2Almchannel30PortEntry 2 }


--- *********************************************************
---     TABLE for the pmopm2Almchannel31Port articles
--- *********************************************************

pmopm2Almchannel31PortTable OBJECT-TYPE
	SYNTAX  SEQUENCE OF Pmopm2Almchannel31PortEntry
	MAX-ACCESS not-accessible
	STATUS current
	DESCRIPTION
        "
        List of pmopm2Almchannel31Port
        Article
        "
	::= { pmopm2AlmClientCrit 76 }


pmopm2Almchannel31PortEntry OBJECT-TYPE
	SYNTAX Pmopm2Almchannel31PortEntry
	MAX-ACCESS not-accessible
	STATUS current
	DESCRIPTION
        "
        Row definition for the pmopm2Almchannel31Port
        table
        "
	INDEX   { pmopm2Almchannel31PortIndex }
	::= { pmopm2Almchannel31PortTable 1 }


Pmopm2Almchannel31PortEntry ::=
	SEQUENCE {
	pmopm2Almchannel31PortIndex
		INTEGER,
	pmopm2AlmChannel31OosPortn
		EkiOnOff,
	pmopm2AlmChannel31PowerHighPortn
		EkiOnOff,
	pmopm2AlmChannel31PowerLowPortn
		EkiOnOff,
	pmopm2AlmChannel31BalancedPortn
		EkiOnOff,
	pmopm2AlmChannel31MismatchPortn
		EkiOnOff,
	pmopm2AlmChannel31AbsentPortn
		EkiOnOff
	}


pmopm2Almchannel31PortIndex OBJECT-TYPE
	SYNTAX  INTEGER(0..128)
	MAX-ACCESS  read-only
	STATUS current
	DESCRIPTION
        "
        Index definition for the pmopm2Almchannel31Port
        table
        "
	::= { pmopm2Almchannel31PortEntry 1 }


pmopm2AlmChannel31OosPortn OBJECT-TYPE
	SYNTAX  EkiOnOff
	MAX-ACCESS read-only
	STATUS current
	DESCRIPTION
        "
        Channel Out Of Service 31 :This
        OID indicates that the channel
         is out of service  <Help> This
        alarm indicates that the channel
        is in service <Condtype> CHANNEL31_OOS_1
        <Probcause> informationalStatus(1000)
        <Alarmtype> other (1) <Polarity>
        (2)
        "
	::= { pmopm2Almchannel31PortEntry 7 }


pmopm2AlmChannel31PowerHighPortn OBJECT-TYPE
	SYNTAX  EkiOnOff
	MAX-ACCESS read-only
	STATUS current
	DESCRIPTION
        "
        Channel Power High 31 :This OID
        indicates that the power of the
        channel is higher than the configured
        threshold<Help> This alarm indicates
        that the power of the channel is
        higher than the configured threshold
        <Condtype> CHANNEL31_POWER_HIGH_1
        <Probcause> degradedSignal (13)
        <Alarmtype> equipmentAlarm <Polarity>
        (2)
        "
	::= { pmopm2Almchannel31PortEntry 6 }


pmopm2AlmChannel31PowerLowPortn OBJECT-TYPE
	SYNTAX  EkiOnOff
	MAX-ACCESS read-only
	STATUS current
	DESCRIPTION
        "
        Channel Power Low 31 :This OID
        indicates that the power of the
        channel is lower than the configured
        threshold<Help> This alarm indicates
        that the power of the channel is
        lower than the configured threshold
        <Condtype> CHANNEL31_POWER_LOW_1
        <Probcause> degradedSignal (13)
        <Alarmtype> equipmentAlarm <Polarity>
        (2)
        "
	::= { pmopm2Almchannel31PortEntry 5 }


pmopm2AlmChannel31BalancedPortn OBJECT-TYPE
	SYNTAX  EkiOnOff
	MAX-ACCESS read-only
	STATUS current
	DESCRIPTION
        "
        Channel Balanced 31 :This OID
         indicates that an in service channel
        is balanced by the Ekinops auto
        turn up application<Help> This
         status indicates that an in service
        channel is balanced by the Ekinops
        auto turn up application <Condtype>
        CHANNEL31_BALANCED_1 <Probcause>
        informationalStatus(1000) <Alarmtype>
        other (1) <Polarity> (2)
        "
	::= { pmopm2Almchannel31PortEntry 4 }


pmopm2AlmChannel31MismatchPortn OBJECT-TYPE
	SYNTAX  EkiOnOff
	MAX-ACCESS read-only
	STATUS current
	DESCRIPTION
        "
        Channel Mismatch 31 :This OID
         indicates that an out of service
        channel is detected on the Optical
        Power Monitoring input<Help> This
        alarm indicates that an out of
         service channel is detected on
        the Optical Power Monitoring input
        <Condtype> CHANNEL31_MISMATCH_1
        <Probcause> unexpectedInformation
        (75) <Alarmtype> equipmentAlarm
        <Polarity> (2)
        "
	::= { pmopm2Almchannel31PortEntry 3 }


pmopm2AlmChannel31AbsentPortn OBJECT-TYPE
	SYNTAX  EkiOnOff
	MAX-ACCESS read-only
	STATUS current
	DESCRIPTION
        "
        Channel Absent 31 :This OID indicates
        that an in service channel is absent
        on the Optical Power Monitoring
        input<Help> This alarm indicates
        that an in service channel is absent
        on the Optical Power Monitoring
        input <Condtype> CHANNEL31_ABSENT_1
        <Probcause> informationMissing
         (65) <Alarmtype> equipmentAlarm
        (5) <Polarity> (2)
        "
	::= { pmopm2Almchannel31PortEntry 2 }


--- *********************************************************
---     TABLE for the pmopm2Almchannel32Port articles
--- *********************************************************

pmopm2Almchannel32PortTable OBJECT-TYPE
	SYNTAX  SEQUENCE OF Pmopm2Almchannel32PortEntry
	MAX-ACCESS not-accessible
	STATUS current
	DESCRIPTION
        "
        List of pmopm2Almchannel32Port
        Article
        "
	::= { pmopm2AlmClientCrit 78 }


pmopm2Almchannel32PortEntry OBJECT-TYPE
	SYNTAX Pmopm2Almchannel32PortEntry
	MAX-ACCESS not-accessible
	STATUS current
	DESCRIPTION
        "
        Row definition for the pmopm2Almchannel32Port
        table
        "
	INDEX   { pmopm2Almchannel32PortIndex }
	::= { pmopm2Almchannel32PortTable 1 }


Pmopm2Almchannel32PortEntry ::=
	SEQUENCE {
	pmopm2Almchannel32PortIndex
		INTEGER,
	pmopm2AlmChannel32OosPortn
		EkiOnOff,
	pmopm2AlmChannel32PowerHighPortn
		EkiOnOff,
	pmopm2AlmChannel32PowerLowPortn
		EkiOnOff,
	pmopm2AlmChannel32BalancedPortn
		EkiOnOff,
	pmopm2AlmChannel32MismatchPortn
		EkiOnOff,
	pmopm2AlmChannel32AbsentPortn
		EkiOnOff
	}


pmopm2Almchannel32PortIndex OBJECT-TYPE
	SYNTAX  INTEGER(0..128)
	MAX-ACCESS  read-only
	STATUS current
	DESCRIPTION
        "
        Index definition for the pmopm2Almchannel32Port
        table
        "
	::= { pmopm2Almchannel32PortEntry 1 }


pmopm2AlmChannel32OosPortn OBJECT-TYPE
	SYNTAX  EkiOnOff
	MAX-ACCESS read-only
	STATUS current
	DESCRIPTION
        "
        Channel Out Of Service 32 :This
        OID indicates that the channel
         is out of service  <Help> This
        alarm indicates that the channel
        is in service <Condtype> CHANNEL32_OOS_1
        <Probcause> informationalStatus(1000)
        <Alarmtype> other (1) <Polarity>
        (2)
        "
	::= { pmopm2Almchannel32PortEntry 7 }


pmopm2AlmChannel32PowerHighPortn OBJECT-TYPE
	SYNTAX  EkiOnOff
	MAX-ACCESS read-only
	STATUS current
	DESCRIPTION
        "
        Channel Power High 32 :This OID
        indicates that the power of the
        channel is higher than the configured
        threshold<Help> This alarm indicates
        that the power of the channel is
        higher than the configured threshold
        <Condtype> CHANNEL32_POWER_HIGH_1
        <Probcause> degradedSignal (13)
        <Alarmtype> equipmentAlarm <Polarity>
        (2)
        "
	::= { pmopm2Almchannel32PortEntry 6 }


pmopm2AlmChannel32PowerLowPortn OBJECT-TYPE
	SYNTAX  EkiOnOff
	MAX-ACCESS read-only
	STATUS current
	DESCRIPTION
        "
        Channel Power Low 32 :This OID
        indicates that the power of the
        channel is lower than the configured
        threshold<Help> This alarm indicates
        that the power of the channel is
        lower than the configured threshold
        <Condtype> CHANNEL32_POWER_LOW_1
        <Probcause> degradedSignal (13)
        <Alarmtype> equipmentAlarm <Polarity>
        (2)
        "
	::= { pmopm2Almchannel32PortEntry 5 }


pmopm2AlmChannel32BalancedPortn OBJECT-TYPE
	SYNTAX  EkiOnOff
	MAX-ACCESS read-only
	STATUS current
	DESCRIPTION
        "
        Channel Balanced 32 :This OID
         indicates that an in service channel
        is balanced by the Ekinops auto
        turn up application<Help> This
         status indicates that an in service
        channel is balanced by the Ekinops
        auto turn up application <Condtype>
        CHANNEL32_BALANCED_1 <Probcause>
        informationalStatus(1000) <Alarmtype>
        other (1) <Polarity> (2)
        "
	::= { pmopm2Almchannel32PortEntry 4 }


pmopm2AlmChannel32MismatchPortn OBJECT-TYPE
	SYNTAX  EkiOnOff
	MAX-ACCESS read-only
	STATUS current
	DESCRIPTION
        "
        Channel Mismatch 32 :This OID
         indicates that an out of service
        channel is detected on the Optical
        Power Monitoring input<Help> This
        alarm indicates that an out of
         service channel is detected on
        the Optical Power Monitoring input
        <Condtype> CHANNEL32_MISMATCH_1
        <Probcause> unexpectedInformation
        (75) <Alarmtype> equipmentAlarm
        <Polarity> (2)
        "
	::= { pmopm2Almchannel32PortEntry 3 }


pmopm2AlmChannel32AbsentPortn OBJECT-TYPE
	SYNTAX  EkiOnOff
	MAX-ACCESS read-only
	STATUS current
	DESCRIPTION
        "
        Channel Absent 32 :This OID indicates
        that an in service channel is absent
        on the Optical Power Monitoring
        input<Help> This alarm indicates
        that an in service channel is absent
        on the Optical Power Monitoring
        input <Condtype> CHANNEL32_ABSENT_1
        <Probcause> informationMissing
         (65) <Alarmtype> equipmentAlarm
        (5) <Polarity> (2)
        "
	::= { pmopm2Almchannel32PortEntry 2 }


--- *********************************************************
---     TABLE for the pmopm2Almchannel33Port articles
--- *********************************************************

pmopm2Almchannel33PortTable OBJECT-TYPE
	SYNTAX  SEQUENCE OF Pmopm2Almchannel33PortEntry
	MAX-ACCESS not-accessible
	STATUS current
	DESCRIPTION
        "
        List of pmopm2Almchannel33Port
        Article
        "
	::= { pmopm2AlmClientCrit 80 }


pmopm2Almchannel33PortEntry OBJECT-TYPE
	SYNTAX Pmopm2Almchannel33PortEntry
	MAX-ACCESS not-accessible
	STATUS current
	DESCRIPTION
        "
        Row definition for the pmopm2Almchannel33Port
        table
        "
	INDEX   { pmopm2Almchannel33PortIndex }
	::= { pmopm2Almchannel33PortTable 1 }


Pmopm2Almchannel33PortEntry ::=
	SEQUENCE {
	pmopm2Almchannel33PortIndex
		INTEGER,
	pmopm2AlmChannel33OosPortn
		EkiOnOff,
	pmopm2AlmChannel33PowerHighPortn
		EkiOnOff,
	pmopm2AlmChannel33PowerLowPortn
		EkiOnOff,
	pmopm2AlmChannel33BalancedPortn
		EkiOnOff,
	pmopm2AlmChannel33MismatchPortn
		EkiOnOff,
	pmopm2AlmChannel33AbsentPortn
		EkiOnOff
	}


pmopm2Almchannel33PortIndex OBJECT-TYPE
	SYNTAX  INTEGER(0..128)
	MAX-ACCESS  read-only
	STATUS current
	DESCRIPTION
        "
        Index definition for the pmopm2Almchannel33Port
        table
        "
	::= { pmopm2Almchannel33PortEntry 1 }


pmopm2AlmChannel33OosPortn OBJECT-TYPE
	SYNTAX  EkiOnOff
	MAX-ACCESS read-only
	STATUS current
	DESCRIPTION
        "
        Channel Out Of Service 33 :This
        OID indicates that the channel
         is out of service  <Help> This
        alarm indicates that the channel
        is in service <Condtype> CHANNEL33_OOS_1
        <Probcause> informationalStatus(1000)
        <Alarmtype> other (1) <Polarity>
        (2)
        "
	::= { pmopm2Almchannel33PortEntry 7 }


pmopm2AlmChannel33PowerHighPortn OBJECT-TYPE
	SYNTAX  EkiOnOff
	MAX-ACCESS read-only
	STATUS current
	DESCRIPTION
        "
        Channel Power High 33 :This OID
        indicates that the power of the
        channel is higher than the configured
        threshold<Help> This alarm indicates
        that the power of the channel is
        higher than the configured threshold
        <Condtype> CHANNEL33_POWER_HIGH_1
        <Probcause> degradedSignal (13)
        <Alarmtype> equipmentAlarm <Polarity>
        (2)
        "
	::= { pmopm2Almchannel33PortEntry 6 }


pmopm2AlmChannel33PowerLowPortn OBJECT-TYPE
	SYNTAX  EkiOnOff
	MAX-ACCESS read-only
	STATUS current
	DESCRIPTION
        "
        Channel Power Low 33 :This OID
        indicates that the power of the
        channel is lower than the configured
        threshold<Help> This alarm indicates
        that the power of the channel is
        lower than the configured threshold
        <Condtype> CHANNEL33_POWER_LOW_1
        <Probcause> degradedSignal (13)
        <Alarmtype> equipmentAlarm <Polarity>
        (2)
        "
	::= { pmopm2Almchannel33PortEntry 5 }


pmopm2AlmChannel33BalancedPortn OBJECT-TYPE
	SYNTAX  EkiOnOff
	MAX-ACCESS read-only
	STATUS current
	DESCRIPTION
        "
        Channel Balanced 33 :This OID
         indicates that an in service channel
        is balanced by the Ekinops auto
        turn up application<Help> This
         status indicates that an in service
        channel is balanced by the Ekinops
        auto turn up application <Condtype>
        CHANNEL33_BALANCED_1 <Probcause>
        informationalStatus(1000) <Alarmtype>
        other (1) <Polarity> (2)
        "
	::= { pmopm2Almchannel33PortEntry 4 }


pmopm2AlmChannel33MismatchPortn OBJECT-TYPE
	SYNTAX  EkiOnOff
	MAX-ACCESS read-only
	STATUS current
	DESCRIPTION
        "
        Channel Mismatch 33 :This OID
         indicates that an out of service
        channel is detected on the Optical
        Power Monitoring input<Help> This
        alarm indicates that an out of
         service channel is detected on
        the Optical Power Monitoring input
        <Condtype> CHANNEL33_MISMATCH_1
        <Probcause> unexpectedInformation
        (75) <Alarmtype> equipmentAlarm
        <Polarity> (2)
        "
	::= { pmopm2Almchannel33PortEntry 3 }


pmopm2AlmChannel33AbsentPortn OBJECT-TYPE
	SYNTAX  EkiOnOff
	MAX-ACCESS read-only
	STATUS current
	DESCRIPTION
        "
        Channel Absent 33 :This OID indicates
        that an in service channel is absent
        on the Optical Power Monitoring
        input<Help> This alarm indicates
        that an in service channel is absent
        on the Optical Power Monitoring
        input <Condtype> CHANNEL33_ABSENT_1
        <Probcause> informationMissing
         (65) <Alarmtype> equipmentAlarm
        (5) <Polarity> (2)
        "
	::= { pmopm2Almchannel33PortEntry 2 }


--- *********************************************************
---     TABLE for the pmopm2Almchannel34Port articles
--- *********************************************************

pmopm2Almchannel34PortTable OBJECT-TYPE
	SYNTAX  SEQUENCE OF Pmopm2Almchannel34PortEntry
	MAX-ACCESS not-accessible
	STATUS current
	DESCRIPTION
        "
        List of pmopm2Almchannel34Port
        Article
        "
	::= { pmopm2AlmClientCrit 82 }


pmopm2Almchannel34PortEntry OBJECT-TYPE
	SYNTAX Pmopm2Almchannel34PortEntry
	MAX-ACCESS not-accessible
	STATUS current
	DESCRIPTION
        "
        Row definition for the pmopm2Almchannel34Port
        table
        "
	INDEX   { pmopm2Almchannel34PortIndex }
	::= { pmopm2Almchannel34PortTable 1 }


Pmopm2Almchannel34PortEntry ::=
	SEQUENCE {
	pmopm2Almchannel34PortIndex
		INTEGER,
	pmopm2AlmChannel34OosPortn
		EkiOnOff,
	pmopm2AlmChannel34PowerHighPortn
		EkiOnOff,
	pmopm2AlmChannel34PowerLowPortn
		EkiOnOff,
	pmopm2AlmChannel34BalancedPortn
		EkiOnOff,
	pmopm2AlmChannel34MismatchPortn
		EkiOnOff,
	pmopm2AlmChannel34AbsentPortn
		EkiOnOff
	}


pmopm2Almchannel34PortIndex OBJECT-TYPE
	SYNTAX  INTEGER(0..128)
	MAX-ACCESS  read-only
	STATUS current
	DESCRIPTION
        "
        Index definition for the pmopm2Almchannel34Port
        table
        "
	::= { pmopm2Almchannel34PortEntry 1 }


pmopm2AlmChannel34OosPortn OBJECT-TYPE
	SYNTAX  EkiOnOff
	MAX-ACCESS read-only
	STATUS current
	DESCRIPTION
        "
        Channel Out Of Service 34 :This
        OID indicates that the channel
         is out of service  <Help> This
        alarm indicates that the channel
        is in service <Condtype> CHANNEL34_OOS_1
        <Probcause> informationalStatus(1000)
        <Alarmtype> other (1) <Polarity>
        (2)
        "
	::= { pmopm2Almchannel34PortEntry 7 }


pmopm2AlmChannel34PowerHighPortn OBJECT-TYPE
	SYNTAX  EkiOnOff
	MAX-ACCESS read-only
	STATUS current
	DESCRIPTION
        "
        Channel Power High 34 :This OID
        indicates that the power of the
        channel is higher than the configured
        threshold<Help> This alarm indicates
        that the power of the channel is
        higher than the configured threshold
        <Condtype> CHANNEL34_POWER_HIGH_1
        <Probcause> degradedSignal (13)
        <Alarmtype> equipmentAlarm <Polarity>
        (2)
        "
	::= { pmopm2Almchannel34PortEntry 6 }


pmopm2AlmChannel34PowerLowPortn OBJECT-TYPE
	SYNTAX  EkiOnOff
	MAX-ACCESS read-only
	STATUS current
	DESCRIPTION
        "
        Channel Power Low 34 :This OID
        indicates that the power of the
        channel is lower than the configured
        threshold<Help> This alarm indicates
        that the power of the channel is
        lower than the configured threshold
        <Condtype> CHANNEL34_POWER_LOW_1
        <Probcause> degradedSignal (13)
        <Alarmtype> equipmentAlarm <Polarity>
        (2)
        "
	::= { pmopm2Almchannel34PortEntry 5 }


pmopm2AlmChannel34BalancedPortn OBJECT-TYPE
	SYNTAX  EkiOnOff
	MAX-ACCESS read-only
	STATUS current
	DESCRIPTION
        "
        Channel Balanced 34 :This OID
         indicates that an in service channel
        is balanced by the Ekinops auto
        turn up application<Help> This
         status indicates that an in service
        channel is balanced by the Ekinops
        auto turn up application <Condtype>
        CHANNEL34_BALANCED_1 <Probcause>
        informationalStatus(1000) <Alarmtype>
        other (1) <Polarity> (2)
        "
	::= { pmopm2Almchannel34PortEntry 4 }


pmopm2AlmChannel34MismatchPortn OBJECT-TYPE
	SYNTAX  EkiOnOff
	MAX-ACCESS read-only
	STATUS current
	DESCRIPTION
        "
        Channel Mismatch 34 :This OID
         indicates that an out of service
        channel is detected on the Optical
        Power Monitoring input<Help> This
        alarm indicates that an out of
         service channel is detected on
        the Optical Power Monitoring input
        <Condtype> CHANNEL34_MISMATCH_1
        <Probcause> unexpectedInformation
        (75) <Alarmtype> equipmentAlarm
        <Polarity> (2)
        "
	::= { pmopm2Almchannel34PortEntry 3 }


pmopm2AlmChannel34AbsentPortn OBJECT-TYPE
	SYNTAX  EkiOnOff
	MAX-ACCESS read-only
	STATUS current
	DESCRIPTION
        "
        Channel Absent 34 :This OID indicates
        that an in service channel is absent
        on the Optical Power Monitoring
        input<Help> This alarm indicates
        that an in service channel is absent
        on the Optical Power Monitoring
        input <Condtype> CHANNEL34_ABSENT_1
        <Probcause> informationMissing
         (65) <Alarmtype> equipmentAlarm
        (5) <Polarity> (2)
        "
	::= { pmopm2Almchannel34PortEntry 2 }


--- *********************************************************
---     TABLE for the pmopm2Almchannel35Port articles
--- *********************************************************

pmopm2Almchannel35PortTable OBJECT-TYPE
	SYNTAX  SEQUENCE OF Pmopm2Almchannel35PortEntry
	MAX-ACCESS not-accessible
	STATUS current
	DESCRIPTION
        "
        List of pmopm2Almchannel35Port
        Article
        "
	::= { pmopm2AlmClientCrit 84 }


pmopm2Almchannel35PortEntry OBJECT-TYPE
	SYNTAX Pmopm2Almchannel35PortEntry
	MAX-ACCESS not-accessible
	STATUS current
	DESCRIPTION
        "
        Row definition for the pmopm2Almchannel35Port
        table
        "
	INDEX   { pmopm2Almchannel35PortIndex }
	::= { pmopm2Almchannel35PortTable 1 }


Pmopm2Almchannel35PortEntry ::=
	SEQUENCE {
	pmopm2Almchannel35PortIndex
		INTEGER,
	pmopm2AlmChannel35OosPortn
		EkiOnOff,
	pmopm2AlmChannel35PowerHighPortn
		EkiOnOff,
	pmopm2AlmChannel35PowerLowPortn
		EkiOnOff,
	pmopm2AlmChannel35BalancedPortn
		EkiOnOff,
	pmopm2AlmChannel35MismatchPortn
		EkiOnOff,
	pmopm2AlmChannel35AbsentPortn
		EkiOnOff
	}


pmopm2Almchannel35PortIndex OBJECT-TYPE
	SYNTAX  INTEGER(0..128)
	MAX-ACCESS  read-only
	STATUS current
	DESCRIPTION
        "
        Index definition for the pmopm2Almchannel35Port
        table
        "
	::= { pmopm2Almchannel35PortEntry 1 }


pmopm2AlmChannel35OosPortn OBJECT-TYPE
	SYNTAX  EkiOnOff
	MAX-ACCESS read-only
	STATUS current
	DESCRIPTION
        "
        Channel Out Of Service 35 :This
        OID indicates that the channel
         is out of service  <Help> This
        alarm indicates that the channel
        is in service <Condtype> CHANNEL35_OOS_1
        <Probcause> informationalStatus(1000)
        <Alarmtype> other (1) <Polarity>
        (2)
        "
	::= { pmopm2Almchannel35PortEntry 7 }


pmopm2AlmChannel35PowerHighPortn OBJECT-TYPE
	SYNTAX  EkiOnOff
	MAX-ACCESS read-only
	STATUS current
	DESCRIPTION
        "
        Channel Power High 35 :This OID
        indicates that the power of the
        channel is higher than the configured
        threshold<Help> This alarm indicates
        that the power of the channel is
        higher than the configured threshold
        <Condtype> CHANNEL35_POWER_HIGH_1
        <Probcause> degradedSignal (13)
        <Alarmtype> equipmentAlarm <Polarity>
        (2)
        "
	::= { pmopm2Almchannel35PortEntry 6 }


pmopm2AlmChannel35PowerLowPortn OBJECT-TYPE
	SYNTAX  EkiOnOff
	MAX-ACCESS read-only
	STATUS current
	DESCRIPTION
        "
        Channel Power Low 35 :This OID
        indicates that the power of the
        channel is lower than the configured
        threshold<Help> This alarm indicates
        that the power of the channel is
        lower than the configured threshold
        <Condtype> CHANNEL35_POWER_LOW_1
        <Probcause> degradedSignal (13)
        <Alarmtype> equipmentAlarm <Polarity>
        (2)
        "
	::= { pmopm2Almchannel35PortEntry 5 }


pmopm2AlmChannel35BalancedPortn OBJECT-TYPE
	SYNTAX  EkiOnOff
	MAX-ACCESS read-only
	STATUS current
	DESCRIPTION
        "
        Channel Balanced 35 :This OID
         indicates that an in service channel
        is balanced by the Ekinops auto
        turn up application<Help> This
         status indicates that an in service
        channel is balanced by the Ekinops
        auto turn up application <Condtype>
        CHANNEL35_BALANCED_1 <Probcause>
        informationalStatus(1000) <Alarmtype>
        other (1) <Polarity> (2)
        "
	::= { pmopm2Almchannel35PortEntry 4 }


pmopm2AlmChannel35MismatchPortn OBJECT-TYPE
	SYNTAX  EkiOnOff
	MAX-ACCESS read-only
	STATUS current
	DESCRIPTION
        "
        Channel Mismatch 35 :This OID
         indicates that an out of service
        channel is detected on the Optical
        Power Monitoring input<Help> This
        alarm indicates that an out of
         service channel is detected on
        the Optical Power Monitoring input
        <Condtype> CHANNEL35_MISMATCH_1
        <Probcause> unexpectedInformation
        (75) <Alarmtype> equipmentAlarm
        <Polarity> (2)
        "
	::= { pmopm2Almchannel35PortEntry 3 }


pmopm2AlmChannel35AbsentPortn OBJECT-TYPE
	SYNTAX  EkiOnOff
	MAX-ACCESS read-only
	STATUS current
	DESCRIPTION
        "
        Channel Absent 35 :This OID indicates
        that an in service channel is absent
        on the Optical Power Monitoring
        input<Help> This alarm indicates
        that an in service channel is absent
        on the Optical Power Monitoring
        input <Condtype> CHANNEL35_ABSENT_1
        <Probcause> informationMissing
         (65) <Alarmtype> equipmentAlarm
        (5) <Polarity> (2)
        "
	::= { pmopm2Almchannel35PortEntry 2 }


--- *********************************************************
---     TABLE for the pmopm2Almchannel36Port articles
--- *********************************************************

pmopm2Almchannel36PortTable OBJECT-TYPE
	SYNTAX  SEQUENCE OF Pmopm2Almchannel36PortEntry
	MAX-ACCESS not-accessible
	STATUS current
	DESCRIPTION
        "
        List of pmopm2Almchannel36Port
        Article
        "
	::= { pmopm2AlmClientCrit 86 }


pmopm2Almchannel36PortEntry OBJECT-TYPE
	SYNTAX Pmopm2Almchannel36PortEntry
	MAX-ACCESS not-accessible
	STATUS current
	DESCRIPTION
        "
        Row definition for the pmopm2Almchannel36Port
        table
        "
	INDEX   { pmopm2Almchannel36PortIndex }
	::= { pmopm2Almchannel36PortTable 1 }


Pmopm2Almchannel36PortEntry ::=
	SEQUENCE {
	pmopm2Almchannel36PortIndex
		INTEGER,
	pmopm2AlmChannel36OosPortn
		EkiOnOff,
	pmopm2AlmChannel36PowerHighPortn
		EkiOnOff,
	pmopm2AlmChannel36PowerLowPortn
		EkiOnOff,
	pmopm2AlmChannel36BalancedPortn
		EkiOnOff,
	pmopm2AlmChannel36MismatchPortn
		EkiOnOff,
	pmopm2AlmChannel36AbsentPortn
		EkiOnOff
	}


pmopm2Almchannel36PortIndex OBJECT-TYPE
	SYNTAX  INTEGER(0..128)
	MAX-ACCESS  read-only
	STATUS current
	DESCRIPTION
        "
        Index definition for the pmopm2Almchannel36Port
        table
        "
	::= { pmopm2Almchannel36PortEntry 1 }


pmopm2AlmChannel36OosPortn OBJECT-TYPE
	SYNTAX  EkiOnOff
	MAX-ACCESS read-only
	STATUS current
	DESCRIPTION
        "
        Channel Out Of Service 36 :This
        OID indicates that the channel
         is out of service  <Help> This
        alarm indicates that the channel
        is in service <Condtype> CHANNEL36_OOS_1
        <Probcause> informationalStatus(1000)
        <Alarmtype> other (1) <Polarity>
        (2)
        "
	::= { pmopm2Almchannel36PortEntry 7 }


pmopm2AlmChannel36PowerHighPortn OBJECT-TYPE
	SYNTAX  EkiOnOff
	MAX-ACCESS read-only
	STATUS current
	DESCRIPTION
        "
        Channel Power High 36 :This OID
        indicates that the power of the
        channel is higher than the configured
        threshold<Help> This alarm indicates
        that the power of the channel is
        higher than the configured threshold
        <Condtype> CHANNEL36_POWER_HIGH_1
        <Probcause> degradedSignal (13)
        <Alarmtype> equipmentAlarm <Polarity>
        (2)
        "
	::= { pmopm2Almchannel36PortEntry 6 }


pmopm2AlmChannel36PowerLowPortn OBJECT-TYPE
	SYNTAX  EkiOnOff
	MAX-ACCESS read-only
	STATUS current
	DESCRIPTION
        "
        Channel Power Low 36 :This OID
        indicates that the power of the
        channel is lower than the configured
        threshold<Help> This alarm indicates
        that the power of the channel is
        lower than the configured threshold
        <Condtype> CHANNEL36_POWER_LOW_1
        <Probcause> degradedSignal (13)
        <Alarmtype> equipmentAlarm <Polarity>
        (2)
        "
	::= { pmopm2Almchannel36PortEntry 5 }


pmopm2AlmChannel36BalancedPortn OBJECT-TYPE
	SYNTAX  EkiOnOff
	MAX-ACCESS read-only
	STATUS current
	DESCRIPTION
        "
        Channel Balanced 36 :This OID
         indicates that an in service channel
        is balanced by the Ekinops auto
        turn up application<Help> This
         status indicates that an in service
        channel is balanced by the Ekinops
        auto turn up application <Condtype>
        CHANNEL36_BALANCED_1 <Probcause>
        informationalStatus(1000) <Alarmtype>
        other (1) <Polarity> (2)
        "
	::= { pmopm2Almchannel36PortEntry 4 }


pmopm2AlmChannel36MismatchPortn OBJECT-TYPE
	SYNTAX  EkiOnOff
	MAX-ACCESS read-only
	STATUS current
	DESCRIPTION
        "
        Channel Mismatch 36 :This OID
         indicates that an out of service
        channel is detected on the Optical
        Power Monitoring input<Help> This
        alarm indicates that an out of
         service channel is detected on
        the Optical Power Monitoring input
        <Condtype> CHANNEL36_MISMATCH_1
        <Probcause> unexpectedInformation
        (75) <Alarmtype> equipmentAlarm
        <Polarity> (2)
        "
	::= { pmopm2Almchannel36PortEntry 3 }


pmopm2AlmChannel36AbsentPortn OBJECT-TYPE
	SYNTAX  EkiOnOff
	MAX-ACCESS read-only
	STATUS current
	DESCRIPTION
        "
        Channel Absent 36 :This OID indicates
        that an in service channel is absent
        on the Optical Power Monitoring
        input<Help> This alarm indicates
        that an in service channel is absent
        on the Optical Power Monitoring
        input <Condtype> CHANNEL36_ABSENT_1
        <Probcause> informationMissing
         (65) <Alarmtype> equipmentAlarm
        (5) <Polarity> (2)
        "
	::= { pmopm2Almchannel36PortEntry 2 }


--- *********************************************************
---     TABLE for the pmopm2Almchannel37Port articles
--- *********************************************************

pmopm2Almchannel37PortTable OBJECT-TYPE
	SYNTAX  SEQUENCE OF Pmopm2Almchannel37PortEntry
	MAX-ACCESS not-accessible
	STATUS current
	DESCRIPTION
        "
        List of pmopm2Almchannel37Port
        Article
        "
	::= { pmopm2AlmClientCrit 88 }


pmopm2Almchannel37PortEntry OBJECT-TYPE
	SYNTAX Pmopm2Almchannel37PortEntry
	MAX-ACCESS not-accessible
	STATUS current
	DESCRIPTION
        "
        Row definition for the pmopm2Almchannel37Port
        table
        "
	INDEX   { pmopm2Almchannel37PortIndex }
	::= { pmopm2Almchannel37PortTable 1 }


Pmopm2Almchannel37PortEntry ::=
	SEQUENCE {
	pmopm2Almchannel37PortIndex
		INTEGER,
	pmopm2AlmChannel37OosPortn
		EkiOnOff,
	pmopm2AlmChannel37PowerHighPortn
		EkiOnOff,
	pmopm2AlmChannel37PowerLowPortn
		EkiOnOff,
	pmopm2AlmChannel37BalancedPortn
		EkiOnOff,
	pmopm2AlmChannel37MismatchPortn
		EkiOnOff,
	pmopm2AlmChannel37AbsentPortn
		EkiOnOff
	}


pmopm2Almchannel37PortIndex OBJECT-TYPE
	SYNTAX  INTEGER(0..128)
	MAX-ACCESS  read-only
	STATUS current
	DESCRIPTION
        "
        Index definition for the pmopm2Almchannel37Port
        table
        "
	::= { pmopm2Almchannel37PortEntry 1 }


pmopm2AlmChannel37OosPortn OBJECT-TYPE
	SYNTAX  EkiOnOff
	MAX-ACCESS read-only
	STATUS current
	DESCRIPTION
        "
        Channel Out Of Service 37 :This
        OID indicates that the channel
         is out of service  <Help> This
        alarm indicates that the channel
        is in service <Condtype> CHANNEL37_OOS_1
        <Probcause> informationalStatus(1000)
        <Alarmtype> other (1) <Polarity>
        (2)
        "
	::= { pmopm2Almchannel37PortEntry 7 }


pmopm2AlmChannel37PowerHighPortn OBJECT-TYPE
	SYNTAX  EkiOnOff
	MAX-ACCESS read-only
	STATUS current
	DESCRIPTION
        "
        Channel Power High 37 :This OID
        indicates that the power of the
        channel is higher than the configured
        threshold<Help> This alarm indicates
        that the power of the channel is
        higher than the configured threshold
        <Condtype> CHANNEL37_POWER_HIGH_1
        <Probcause> degradedSignal (13)
        <Alarmtype> equipmentAlarm <Polarity>
        (2)
        "
	::= { pmopm2Almchannel37PortEntry 6 }


pmopm2AlmChannel37PowerLowPortn OBJECT-TYPE
	SYNTAX  EkiOnOff
	MAX-ACCESS read-only
	STATUS current
	DESCRIPTION
        "
        Channel Power Low 37 :This OID
        indicates that the power of the
        channel is lower than the configured
        threshold<Help> This alarm indicates
        that the power of the channel is
        lower than the configured threshold
        <Condtype> CHANNEL37_POWER_LOW_1
        <Probcause> degradedSignal (13)
        <Alarmtype> equipmentAlarm <Polarity>
        (2)
        "
	::= { pmopm2Almchannel37PortEntry 5 }


pmopm2AlmChannel37BalancedPortn OBJECT-TYPE
	SYNTAX  EkiOnOff
	MAX-ACCESS read-only
	STATUS current
	DESCRIPTION
        "
        Channel Balanced 37 :This OID
         indicates that an in service channel
        is balanced by the Ekinops auto
        turn up application<Help> This
         status indicates that an in service
        channel is balanced by the Ekinops
        auto turn up application <Condtype>
        CHANNEL37_BALANCED_1 <Probcause>
        informationalStatus(1000) <Alarmtype>
        other (1) <Polarity> (2)
        "
	::= { pmopm2Almchannel37PortEntry 4 }


pmopm2AlmChannel37MismatchPortn OBJECT-TYPE
	SYNTAX  EkiOnOff
	MAX-ACCESS read-only
	STATUS current
	DESCRIPTION
        "
        Channel Mismatch 37 :This OID
         indicates that an out of service
        channel is detected on the Optical
        Power Monitoring input<Help> This
        alarm indicates that an out of
         service channel is detected on
        the Optical Power Monitoring input
        <Condtype> CHANNEL37_MISMATCH_1
        <Probcause> unexpectedInformation
        (75) <Alarmtype> equipmentAlarm
        <Polarity> (2)
        "
	::= { pmopm2Almchannel37PortEntry 3 }


pmopm2AlmChannel37AbsentPortn OBJECT-TYPE
	SYNTAX  EkiOnOff
	MAX-ACCESS read-only
	STATUS current
	DESCRIPTION
        "
        Channel Absent 37 :This OID indicates
        that an in service channel is absent
        on the Optical Power Monitoring
        input<Help> This alarm indicates
        that an in service channel is absent
        on the Optical Power Monitoring
        input <Condtype> CHANNEL37_ABSENT_1
        <Probcause> informationMissing
         (65) <Alarmtype> equipmentAlarm
        (5) <Polarity> (2)
        "
	::= { pmopm2Almchannel37PortEntry 2 }


--- *********************************************************
---     TABLE for the pmopm2Almchannel38Port articles
--- *********************************************************

pmopm2Almchannel38PortTable OBJECT-TYPE
	SYNTAX  SEQUENCE OF Pmopm2Almchannel38PortEntry
	MAX-ACCESS not-accessible
	STATUS current
	DESCRIPTION
        "
        List of pmopm2Almchannel38Port
        Article
        "
	::= { pmopm2AlmClientCrit 90 }


pmopm2Almchannel38PortEntry OBJECT-TYPE
	SYNTAX Pmopm2Almchannel38PortEntry
	MAX-ACCESS not-accessible
	STATUS current
	DESCRIPTION
        "
        Row definition for the pmopm2Almchannel38Port
        table
        "
	INDEX   { pmopm2Almchannel38PortIndex }
	::= { pmopm2Almchannel38PortTable 1 }


Pmopm2Almchannel38PortEntry ::=
	SEQUENCE {
	pmopm2Almchannel38PortIndex
		INTEGER,
	pmopm2AlmChannel38OosPortn
		EkiOnOff,
	pmopm2AlmChannel38PowerHighPortn
		EkiOnOff,
	pmopm2AlmChannel38PowerLowPortn
		EkiOnOff,
	pmopm2AlmChannel38BalancedPortn
		EkiOnOff,
	pmopm2AlmChannel38MismatchPortn
		EkiOnOff,
	pmopm2AlmChannel38AbsentPortn
		EkiOnOff
	}


pmopm2Almchannel38PortIndex OBJECT-TYPE
	SYNTAX  INTEGER(0..128)
	MAX-ACCESS  read-only
	STATUS current
	DESCRIPTION
        "
        Index definition for the pmopm2Almchannel38Port
        table
        "
	::= { pmopm2Almchannel38PortEntry 1 }


pmopm2AlmChannel38OosPortn OBJECT-TYPE
	SYNTAX  EkiOnOff
	MAX-ACCESS read-only
	STATUS current
	DESCRIPTION
        "
        Channel Out Of Service 38 :This
        OID indicates that the channel
         is out of service  <Help> This
        alarm indicates that the channel
        is in service <Condtype> CHANNEL38_OOS_1
        <Probcause> informationalStatus(1000)
        <Alarmtype> other (1) <Polarity>
        (2)
        "
	::= { pmopm2Almchannel38PortEntry 7 }


pmopm2AlmChannel38PowerHighPortn OBJECT-TYPE
	SYNTAX  EkiOnOff
	MAX-ACCESS read-only
	STATUS current
	DESCRIPTION
        "
        Channel Power High 38 :This OID
        indicates that the power of the
        channel is higher than the configured
        threshold<Help> This alarm indicates
        that the power of the channel is
        higher than the configured threshold
        <Condtype> CHANNEL38_POWER_HIGH_1
        <Probcause> degradedSignal (13)
        <Alarmtype> equipmentAlarm <Polarity>
        (2)
        "
	::= { pmopm2Almchannel38PortEntry 6 }


pmopm2AlmChannel38PowerLowPortn OBJECT-TYPE
	SYNTAX  EkiOnOff
	MAX-ACCESS read-only
	STATUS current
	DESCRIPTION
        "
        Channel Power Low 38 :This OID
        indicates that the power of the
        channel is lower than the configured
        threshold<Help> This alarm indicates
        that the power of the channel is
        lower than the configured threshold
        <Condtype> CHANNEL38_POWER_LOW_1
        <Probcause> degradedSignal (13)
        <Alarmtype> equipmentAlarm <Polarity>
        (2)
        "
	::= { pmopm2Almchannel38PortEntry 5 }


pmopm2AlmChannel38BalancedPortn OBJECT-TYPE
	SYNTAX  EkiOnOff
	MAX-ACCESS read-only
	STATUS current
	DESCRIPTION
        "
        Channel Balanced 38 :This OID
         indicates that an in service channel
        is balanced by the Ekinops auto
        turn up application<Help> This
         status indicates that an in service
        channel is balanced by the Ekinops
        auto turn up application <Condtype>
        CHANNEL38_BALANCED_1 <Probcause>
        informationalStatus(1000) <Alarmtype>
        other (1) <Polarity> (2)
        "
	::= { pmopm2Almchannel38PortEntry 4 }


pmopm2AlmChannel38MismatchPortn OBJECT-TYPE
	SYNTAX  EkiOnOff
	MAX-ACCESS read-only
	STATUS current
	DESCRIPTION
        "
        Channel Mismatch 38 :This OID
         indicates that an out of service
        channel is detected on the Optical
        Power Monitoring input<Help> This
        alarm indicates that an out of
         service channel is detected on
        the Optical Power Monitoring input
        <Condtype> CHANNEL38_MISMATCH_1
        <Probcause> unexpectedInformation
        (75) <Alarmtype> equipmentAlarm
        <Polarity> (2)
        "
	::= { pmopm2Almchannel38PortEntry 3 }


pmopm2AlmChannel38AbsentPortn OBJECT-TYPE
	SYNTAX  EkiOnOff
	MAX-ACCESS read-only
	STATUS current
	DESCRIPTION
        "
        Channel Absent 38 :This OID indicates
        that an in service channel is absent
        on the Optical Power Monitoring
        input<Help> This alarm indicates
        that an in service channel is absent
        on the Optical Power Monitoring
        input <Condtype> CHANNEL38_ABSENT_1
        <Probcause> informationMissing
         (65) <Alarmtype> equipmentAlarm
        (5) <Polarity> (2)
        "
	::= { pmopm2Almchannel38PortEntry 2 }


--- *********************************************************
---     TABLE for the pmopm2Almchannel39Port articles
--- *********************************************************

pmopm2Almchannel39PortTable OBJECT-TYPE
	SYNTAX  SEQUENCE OF Pmopm2Almchannel39PortEntry
	MAX-ACCESS not-accessible
	STATUS current
	DESCRIPTION
        "
        List of pmopm2Almchannel39Port
        Article
        "
	::= { pmopm2AlmClientCrit 92 }


pmopm2Almchannel39PortEntry OBJECT-TYPE
	SYNTAX Pmopm2Almchannel39PortEntry
	MAX-ACCESS not-accessible
	STATUS current
	DESCRIPTION
        "
        Row definition for the pmopm2Almchannel39Port
        table
        "
	INDEX   { pmopm2Almchannel39PortIndex }
	::= { pmopm2Almchannel39PortTable 1 }


Pmopm2Almchannel39PortEntry ::=
	SEQUENCE {
	pmopm2Almchannel39PortIndex
		INTEGER,
	pmopm2AlmChannel39OosPortn
		EkiOnOff,
	pmopm2AlmChannel39PowerHighPortn
		EkiOnOff,
	pmopm2AlmChannel39PowerLowPortn
		EkiOnOff,
	pmopm2AlmChannel39BalancedPortn
		EkiOnOff,
	pmopm2AlmChannel39MismatchPortn
		EkiOnOff,
	pmopm2AlmChannel39AbsentPortn
		EkiOnOff
	}


pmopm2Almchannel39PortIndex OBJECT-TYPE
	SYNTAX  INTEGER(0..128)
	MAX-ACCESS  read-only
	STATUS current
	DESCRIPTION
        "
        Index definition for the pmopm2Almchannel39Port
        table
        "
	::= { pmopm2Almchannel39PortEntry 1 }


pmopm2AlmChannel39OosPortn OBJECT-TYPE
	SYNTAX  EkiOnOff
	MAX-ACCESS read-only
	STATUS current
	DESCRIPTION
        "
        Channel Out Of Service 39 :This
        OID indicates that the channel
         is out of service  <Help> This
        alarm indicates that the channel
        is in service <Condtype> CHANNEL39_OOS_1
        <Probcause> informationalStatus(1000)
        <Alarmtype> other (1) <Polarity>
        (2)
        "
	::= { pmopm2Almchannel39PortEntry 7 }


pmopm2AlmChannel39PowerHighPortn OBJECT-TYPE
	SYNTAX  EkiOnOff
	MAX-ACCESS read-only
	STATUS current
	DESCRIPTION
        "
        Channel Power High 39 :This OID
        indicates that the power of the
        channel is higher than the configured
        threshold<Help> This alarm indicates
        that the power of the channel is
        higher than the configured threshold
        <Condtype> CHANNEL39_POWER_HIGH_1
        <Probcause> degradedSignal (13)
        <Alarmtype> equipmentAlarm <Polarity>
        (2)
        "
	::= { pmopm2Almchannel39PortEntry 6 }


pmopm2AlmChannel39PowerLowPortn OBJECT-TYPE
	SYNTAX  EkiOnOff
	MAX-ACCESS read-only
	STATUS current
	DESCRIPTION
        "
        Channel Power Low 39 :This OID
        indicates that the power of the
        channel is lower than the configured
        threshold<Help> This alarm indicates
        that the power of the channel is
        lower than the configured threshold
        <Condtype> CHANNEL39_POWER_LOW_1
        <Probcause> degradedSignal (13)
        <Alarmtype> equipmentAlarm <Polarity>
        (2)
        "
	::= { pmopm2Almchannel39PortEntry 5 }


pmopm2AlmChannel39BalancedPortn OBJECT-TYPE
	SYNTAX  EkiOnOff
	MAX-ACCESS read-only
	STATUS current
	DESCRIPTION
        "
        Channel Balanced 39 :This OID
         indicates that an in service channel
        is balanced by the Ekinops auto
        turn up application<Help> This
         status indicates that an in service
        channel is balanced by the Ekinops
        auto turn up application <Condtype>
        CHANNEL39_BALANCED_1 <Probcause>
        informationalStatus(1000) <Alarmtype>
        other (1) <Polarity> (2)
        "
	::= { pmopm2Almchannel39PortEntry 4 }


pmopm2AlmChannel39MismatchPortn OBJECT-TYPE
	SYNTAX  EkiOnOff
	MAX-ACCESS read-only
	STATUS current
	DESCRIPTION
        "
        Channel Mismatch 39 :This OID
         indicates that an out of service
        channel is detected on the Optical
        Power Monitoring input<Help> This
        alarm indicates that an out of
         service channel is detected on
        the Optical Power Monitoring input
        <Condtype> CHANNEL39_MISMATCH_1
        <Probcause> unexpectedInformation
        (75) <Alarmtype> equipmentAlarm
        <Polarity> (2)
        "
	::= { pmopm2Almchannel39PortEntry 3 }


pmopm2AlmChannel39AbsentPortn OBJECT-TYPE
	SYNTAX  EkiOnOff
	MAX-ACCESS read-only
	STATUS current
	DESCRIPTION
        "
        Channel Absent 39 :This OID indicates
        that an in service channel is absent
        on the Optical Power Monitoring
        input<Help> This alarm indicates
        that an in service channel is absent
        on the Optical Power Monitoring
        input <Condtype> CHANNEL39_ABSENT_1
        <Probcause> informationMissing
         (65) <Alarmtype> equipmentAlarm
        (5) <Polarity> (2)
        "
	::= { pmopm2Almchannel39PortEntry 2 }


--- *********************************************************
---     TABLE for the pmopm2Almchannel40Port articles
--- *********************************************************

pmopm2Almchannel40PortTable OBJECT-TYPE
	SYNTAX  SEQUENCE OF Pmopm2Almchannel40PortEntry
	MAX-ACCESS not-accessible
	STATUS current
	DESCRIPTION
        "
        List of pmopm2Almchannel40Port
        Article
        "
	::= { pmopm2AlmClientCrit 94 }


pmopm2Almchannel40PortEntry OBJECT-TYPE
	SYNTAX Pmopm2Almchannel40PortEntry
	MAX-ACCESS not-accessible
	STATUS current
	DESCRIPTION
        "
        Row definition for the pmopm2Almchannel40Port
        table
        "
	INDEX   { pmopm2Almchannel40PortIndex }
	::= { pmopm2Almchannel40PortTable 1 }


Pmopm2Almchannel40PortEntry ::=
	SEQUENCE {
	pmopm2Almchannel40PortIndex
		INTEGER,
	pmopm2AlmChannel40OosPortn
		EkiOnOff,
	pmopm2AlmChannel40PowerHighPortn
		EkiOnOff,
	pmopm2AlmChannel40PowerLowPortn
		EkiOnOff,
	pmopm2AlmChannel40BalancedPortn
		EkiOnOff,
	pmopm2AlmChannel40MismatchPortn
		EkiOnOff,
	pmopm2AlmChannel40AbsentPortn
		EkiOnOff
	}


pmopm2Almchannel40PortIndex OBJECT-TYPE
	SYNTAX  INTEGER(0..128)
	MAX-ACCESS  read-only
	STATUS current
	DESCRIPTION
        "
        Index definition for the pmopm2Almchannel40Port
        table
        "
	::= { pmopm2Almchannel40PortEntry 1 }


pmopm2AlmChannel40OosPortn OBJECT-TYPE
	SYNTAX  EkiOnOff
	MAX-ACCESS read-only
	STATUS current
	DESCRIPTION
        "
        Channel Out Of Service 40 :This
        OID indicates that the channel
         is out of service  <Help> This
        alarm indicates that the channel
        is in service <Condtype> CHANNEL40_OOS_1
        <Probcause> informationalStatus(1000)
        <Alarmtype> other (1) <Polarity>
        (2)
        "
	::= { pmopm2Almchannel40PortEntry 7 }


pmopm2AlmChannel40PowerHighPortn OBJECT-TYPE
	SYNTAX  EkiOnOff
	MAX-ACCESS read-only
	STATUS current
	DESCRIPTION
        "
        Channel Power High 40 :This OID
        indicates that the power of the
        channel is higher than the configured
        threshold<Help> This alarm indicates
        that the power of the channel is
        higher than the configured threshold
        <Condtype> CHANNEL40_POWER_HIGH_1
        <Probcause> degradedSignal (13)
        <Alarmtype> equipmentAlarm <Polarity>
        (2)
        "
	::= { pmopm2Almchannel40PortEntry 6 }


pmopm2AlmChannel40PowerLowPortn OBJECT-TYPE
	SYNTAX  EkiOnOff
	MAX-ACCESS read-only
	STATUS current
	DESCRIPTION
        "
        Channel Power Low 40 :This OID
        indicates that the power of the
        channel is lower than the configured
        threshold<Help> This alarm indicates
        that the power of the channel is
        lower than the configured threshold
        <Condtype> CHANNEL40_POWER_LOW_1
        <Probcause> degradedSignal (13)
        <Alarmtype> equipmentAlarm <Polarity>
        (2)
        "
	::= { pmopm2Almchannel40PortEntry 5 }


pmopm2AlmChannel40BalancedPortn OBJECT-TYPE
	SYNTAX  EkiOnOff
	MAX-ACCESS read-only
	STATUS current
	DESCRIPTION
        "
        Channel Balanced 40 :This OID
         indicates that an in service channel
        is balanced by the Ekinops auto
        turn up application<Help> This
         status indicates that an in service
        channel is balanced by the Ekinops
        auto turn up application <Condtype>
        CHANNEL40_BALANCED_1 <Probcause>
        informationalStatus(1000) <Alarmtype>
        other (1) <Polarity> (2)
        "
	::= { pmopm2Almchannel40PortEntry 4 }


pmopm2AlmChannel40MismatchPortn OBJECT-TYPE
	SYNTAX  EkiOnOff
	MAX-ACCESS read-only
	STATUS current
	DESCRIPTION
        "
        Channel Mismatch 40 :This OID
         indicates that an out of service
        channel is detected on the Optical
        Power Monitoring input<Help> This
        alarm indicates that an out of
         service channel is detected on
        the Optical Power Monitoring input
        <Condtype> CHANNEL40_MISMATCH_1
        <Probcause> unexpectedInformation
        (75) <Alarmtype> equipmentAlarm
        <Polarity> (2)
        "
	::= { pmopm2Almchannel40PortEntry 3 }


pmopm2AlmChannel40AbsentPortn OBJECT-TYPE
	SYNTAX  EkiOnOff
	MAX-ACCESS read-only
	STATUS current
	DESCRIPTION
        "
        Channel Absent 40 :This OID indicates
        that an in service channel is absent
        on the Optical Power Monitoring
        input<Help> This alarm indicates
        that an in service channel is absent
        on the Optical Power Monitoring
        input <Condtype> CHANNEL40_ABSENT_1
        <Probcause> informationMissing
         (65) <Alarmtype> equipmentAlarm
        (5) <Polarity> (2)
        "
	::= { pmopm2Almchannel40PortEntry 2 }


--- *********************************************************
---     TABLE for the pmopm2Almchannel41Port articles
--- *********************************************************

pmopm2Almchannel41PortTable OBJECT-TYPE
	SYNTAX  SEQUENCE OF Pmopm2Almchannel41PortEntry
	MAX-ACCESS not-accessible
	STATUS current
	DESCRIPTION
        "
        List of pmopm2Almchannel41Port
        Article
        "
	::= { pmopm2AlmClientCrit 96 }


pmopm2Almchannel41PortEntry OBJECT-TYPE
	SYNTAX Pmopm2Almchannel41PortEntry
	MAX-ACCESS not-accessible
	STATUS current
	DESCRIPTION
        "
        Row definition for the pmopm2Almchannel41Port
        table
        "
	INDEX   { pmopm2Almchannel41PortIndex }
	::= { pmopm2Almchannel41PortTable 1 }


Pmopm2Almchannel41PortEntry ::=
	SEQUENCE {
	pmopm2Almchannel41PortIndex
		INTEGER,
	pmopm2AlmChannel41OosPortn
		EkiOnOff,
	pmopm2AlmChannel41PowerHighPortn
		EkiOnOff,
	pmopm2AlmChannel41PowerLowPortn
		EkiOnOff,
	pmopm2AlmChannel41BalancedPortn
		EkiOnOff,
	pmopm2AlmChannel41MismatchPortn
		EkiOnOff,
	pmopm2AlmChannel41AbsentPortn
		EkiOnOff
	}


pmopm2Almchannel41PortIndex OBJECT-TYPE
	SYNTAX  INTEGER(0..128)
	MAX-ACCESS  read-only
	STATUS current
	DESCRIPTION
        "
        Index definition for the pmopm2Almchannel41Port
        table
        "
	::= { pmopm2Almchannel41PortEntry 1 }


pmopm2AlmChannel41OosPortn OBJECT-TYPE
	SYNTAX  EkiOnOff
	MAX-ACCESS read-only
	STATUS current
	DESCRIPTION
        "
        Channel Out Of Service 41 :This
        OID indicates that the channel
         is out of service  <Help> This
        alarm indicates that the channel
        is in service <Condtype> CHANNEL41_OOS_1
        <Probcause> informationalStatus(1000)
        <Alarmtype> other (1) <Polarity>
        (2)
        "
	::= { pmopm2Almchannel41PortEntry 7 }


pmopm2AlmChannel41PowerHighPortn OBJECT-TYPE
	SYNTAX  EkiOnOff
	MAX-ACCESS read-only
	STATUS current
	DESCRIPTION
        "
        Channel Power High 41 :This OID
        indicates that the power of the
        channel is higher than the configured
        threshold<Help> This alarm indicates
        that the power of the channel is
        higher than the configured threshold
        <Condtype> CHANNEL41_POWER_HIGH_1
        <Probcause> degradedSignal (13)
        <Alarmtype> equipmentAlarm <Polarity>
        (2)
        "
	::= { pmopm2Almchannel41PortEntry 6 }


pmopm2AlmChannel41PowerLowPortn OBJECT-TYPE
	SYNTAX  EkiOnOff
	MAX-ACCESS read-only
	STATUS current
	DESCRIPTION
        "
        Channel Power Low 41 :This OID
        indicates that the power of the
        channel is lower than the configured
        threshold<Help> This alarm indicates
        that the power of the channel is
        lower than the configured threshold
        <Condtype> CHANNEL41_POWER_LOW_1
        <Probcause> degradedSignal (13)
        <Alarmtype> equipmentAlarm <Polarity>
        (2)
        "
	::= { pmopm2Almchannel41PortEntry 5 }


pmopm2AlmChannel41BalancedPortn OBJECT-TYPE
	SYNTAX  EkiOnOff
	MAX-ACCESS read-only
	STATUS current
	DESCRIPTION
        "
        Channel Balanced 41 :This OID
         indicates that an in service channel
        is balanced by the Ekinops auto
        turn up application<Help> This
         status indicates that an in service
        channel is balanced by the Ekinops
        auto turn up application <Condtype>
        CHANNEL41_BALANCED_1 <Probcause>
        informationalStatus(1000) <Alarmtype>
        other (1) <Polarity> (2)
        "
	::= { pmopm2Almchannel41PortEntry 4 }


pmopm2AlmChannel41MismatchPortn OBJECT-TYPE
	SYNTAX  EkiOnOff
	MAX-ACCESS read-only
	STATUS current
	DESCRIPTION
        "
        Channel Mismatch 41 :This OID
         indicates that an out of service
        channel is detected on the Optical
        Power Monitoring input<Help> This
        alarm indicates that an out of
         service channel is detected on
        the Optical Power Monitoring input
        <Condtype> CHANNEL41_MISMATCH_1
        <Probcause> unexpectedInformation
        (75) <Alarmtype> equipmentAlarm
        <Polarity> (2)
        "
	::= { pmopm2Almchannel41PortEntry 3 }


pmopm2AlmChannel41AbsentPortn OBJECT-TYPE
	SYNTAX  EkiOnOff
	MAX-ACCESS read-only
	STATUS current
	DESCRIPTION
        "
        Channel Absent 41 :This OID indicates
        that an in service channel is absent
        on the Optical Power Monitoring
        input<Help> This alarm indicates
        that an in service channel is absent
        on the Optical Power Monitoring
        input <Condtype> CHANNEL41_ABSENT_1
        <Probcause> informationMissing
         (65) <Alarmtype> equipmentAlarm
        (5) <Polarity> (2)
        "
	::= { pmopm2Almchannel41PortEntry 2 }


--- *********************************************************
---     TABLE for the pmopm2Almchannel42Port articles
--- *********************************************************

pmopm2Almchannel42PortTable OBJECT-TYPE
	SYNTAX  SEQUENCE OF Pmopm2Almchannel42PortEntry
	MAX-ACCESS not-accessible
	STATUS current
	DESCRIPTION
        "
        List of pmopm2Almchannel42Port
        Article
        "
	::= { pmopm2AlmClientCrit 98 }


pmopm2Almchannel42PortEntry OBJECT-TYPE
	SYNTAX Pmopm2Almchannel42PortEntry
	MAX-ACCESS not-accessible
	STATUS current
	DESCRIPTION
        "
        Row definition for the pmopm2Almchannel42Port
        table
        "
	INDEX   { pmopm2Almchannel42PortIndex }
	::= { pmopm2Almchannel42PortTable 1 }


Pmopm2Almchannel42PortEntry ::=
	SEQUENCE {
	pmopm2Almchannel42PortIndex
		INTEGER,
	pmopm2AlmChannel42OosPortn
		EkiOnOff,
	pmopm2AlmChannel42PowerHighPortn
		EkiOnOff,
	pmopm2AlmChannel42PowerLowPortn
		EkiOnOff,
	pmopm2AlmChannel42BalancedPortn
		EkiOnOff,
	pmopm2AlmChannel42MismatchPortn
		EkiOnOff,
	pmopm2AlmChannel42AbsentPortn
		EkiOnOff
	}


pmopm2Almchannel42PortIndex OBJECT-TYPE
	SYNTAX  INTEGER(0..128)
	MAX-ACCESS  read-only
	STATUS current
	DESCRIPTION
        "
        Index definition for the pmopm2Almchannel42Port
        table
        "
	::= { pmopm2Almchannel42PortEntry 1 }


pmopm2AlmChannel42OosPortn OBJECT-TYPE
	SYNTAX  EkiOnOff
	MAX-ACCESS read-only
	STATUS current
	DESCRIPTION
        "
        Channel Out Of Service 42 :This
        OID indicates that the channel
         is out of service  <Help> This
        alarm indicates that the channel
        is in service <Condtype> CHANNEL42_OOS_1
        <Probcause> informationalStatus(1000)
        <Alarmtype> other (1) <Polarity>
        (2)
        "
	::= { pmopm2Almchannel42PortEntry 7 }


pmopm2AlmChannel42PowerHighPortn OBJECT-TYPE
	SYNTAX  EkiOnOff
	MAX-ACCESS read-only
	STATUS current
	DESCRIPTION
        "
        Channel Power High 42 :This OID
        indicates that the power of the
        channel is higher than the configured
        threshold<Help> This alarm indicates
        that the power of the channel is
        higher than the configured threshold
        <Condtype> CHANNEL42_POWER_HIGH_1
        <Probcause> degradedSignal (13)
        <Alarmtype> equipmentAlarm <Polarity>
        (2)
        "
	::= { pmopm2Almchannel42PortEntry 6 }


pmopm2AlmChannel42PowerLowPortn OBJECT-TYPE
	SYNTAX  EkiOnOff
	MAX-ACCESS read-only
	STATUS current
	DESCRIPTION
        "
        Channel Power Low 42 :This OID
        indicates that the power of the
        channel is lower than the configured
        threshold<Help> This alarm indicates
        that the power of the channel is
        lower than the configured threshold
        <Condtype> CHANNEL42_POWER_LOW_1
        <Probcause> degradedSignal (13)
        <Alarmtype> equipmentAlarm <Polarity>
        (2)
        "
	::= { pmopm2Almchannel42PortEntry 5 }


pmopm2AlmChannel42BalancedPortn OBJECT-TYPE
	SYNTAX  EkiOnOff
	MAX-ACCESS read-only
	STATUS current
	DESCRIPTION
        "
        Channel Balanced 42 :This OID
         indicates that an in service channel
        is balanced by the Ekinops auto
        turn up application<Help> This
         status indicates that an in service
        channel is balanced by the Ekinops
        auto turn up application <Condtype>
        CHANNEL42_BALANCED_1 <Probcause>
        informationalStatus(1000) <Alarmtype>
        other (1) <Polarity> (2)
        "
	::= { pmopm2Almchannel42PortEntry 4 }


pmopm2AlmChannel42MismatchPortn OBJECT-TYPE
	SYNTAX  EkiOnOff
	MAX-ACCESS read-only
	STATUS current
	DESCRIPTION
        "
        Channel Mismatch 42 :This OID
         indicates that an out of service
        channel is detected on the Optical
        Power Monitoring input<Help> This
        alarm indicates that an out of
         service channel is detected on
        the Optical Power Monitoring input
        <Condtype> CHANNEL42_MISMATCH_1
        <Probcause> unexpectedInformation
        (75) <Alarmtype> equipmentAlarm
        <Polarity> (2)
        "
	::= { pmopm2Almchannel42PortEntry 3 }


pmopm2AlmChannel42AbsentPortn OBJECT-TYPE
	SYNTAX  EkiOnOff
	MAX-ACCESS read-only
	STATUS current
	DESCRIPTION
        "
        Channel Absent 42 :This OID indicates
        that an in service channel is absent
        on the Optical Power Monitoring
        input<Help> This alarm indicates
        that an in service channel is absent
        on the Optical Power Monitoring
        input <Condtype> CHANNEL42_ABSENT_1
        <Probcause> informationMissing
         (65) <Alarmtype> equipmentAlarm
        (5) <Polarity> (2)
        "
	::= { pmopm2Almchannel42PortEntry 2 }


--- *********************************************************
---     TABLE for the pmopm2Almchannel43Port articles
--- *********************************************************

pmopm2Almchannel43PortTable OBJECT-TYPE
	SYNTAX  SEQUENCE OF Pmopm2Almchannel43PortEntry
	MAX-ACCESS not-accessible
	STATUS current
	DESCRIPTION
        "
        List of pmopm2Almchannel43Port
        Article
        "
	::= { pmopm2AlmClientCrit 100 }


pmopm2Almchannel43PortEntry OBJECT-TYPE
	SYNTAX Pmopm2Almchannel43PortEntry
	MAX-ACCESS not-accessible
	STATUS current
	DESCRIPTION
        "
        Row definition for the pmopm2Almchannel43Port
        table
        "
	INDEX   { pmopm2Almchannel43PortIndex }
	::= { pmopm2Almchannel43PortTable 1 }


Pmopm2Almchannel43PortEntry ::=
	SEQUENCE {
	pmopm2Almchannel43PortIndex
		INTEGER,
	pmopm2AlmChannel43OosPortn
		EkiOnOff,
	pmopm2AlmChannel43PowerHighPortn
		EkiOnOff,
	pmopm2AlmChannel43PowerLowPortn
		EkiOnOff,
	pmopm2AlmChannel43BalancedPortn
		EkiOnOff,
	pmopm2AlmChannel43MismatchPortn
		EkiOnOff,
	pmopm2AlmChannel43AbsentPortn
		EkiOnOff
	}


pmopm2Almchannel43PortIndex OBJECT-TYPE
	SYNTAX  INTEGER(0..128)
	MAX-ACCESS  read-only
	STATUS current
	DESCRIPTION
        "
        Index definition for the pmopm2Almchannel43Port
        table
        "
	::= { pmopm2Almchannel43PortEntry 1 }


pmopm2AlmChannel43OosPortn OBJECT-TYPE
	SYNTAX  EkiOnOff
	MAX-ACCESS read-only
	STATUS current
	DESCRIPTION
        "
        Channel Out Of Service 43 :This
        OID indicates that the channel
         is out of service  <Help> This
        alarm indicates that the channel
        is in service <Condtype> CHANNEL43_OOS_1
        <Probcause> informationalStatus(1000)
        <Alarmtype> other (1) <Polarity>
        (2)
        "
	::= { pmopm2Almchannel43PortEntry 7 }


pmopm2AlmChannel43PowerHighPortn OBJECT-TYPE
	SYNTAX  EkiOnOff
	MAX-ACCESS read-only
	STATUS current
	DESCRIPTION
        "
        Channel Power High 43 :This OID
        indicates that the power of the
        channel is higher than the configured
        threshold<Help> This alarm indicates
        that the power of the channel is
        higher than the configured threshold
        <Condtype> CHANNEL43_POWER_HIGH_1
        <Probcause> degradedSignal (13)
        <Alarmtype> equipmentAlarm <Polarity>
        (2)
        "
	::= { pmopm2Almchannel43PortEntry 6 }


pmopm2AlmChannel43PowerLowPortn OBJECT-TYPE
	SYNTAX  EkiOnOff
	MAX-ACCESS read-only
	STATUS current
	DESCRIPTION
        "
        Channel Power Low 43 :This OID
        indicates that the power of the
        channel is lower than the configured
        threshold<Help> This alarm indicates
        that the power of the channel is
        lower than the configured threshold
        <Condtype> CHANNEL43_POWER_LOW_1
        <Probcause> degradedSignal (13)
        <Alarmtype> equipmentAlarm <Polarity>
        (2)
        "
	::= { pmopm2Almchannel43PortEntry 5 }


pmopm2AlmChannel43BalancedPortn OBJECT-TYPE
	SYNTAX  EkiOnOff
	MAX-ACCESS read-only
	STATUS current
	DESCRIPTION
        "
        Channel Balanced 43 :This OID
         indicates that an in service channel
        is balanced by the Ekinops auto
        turn up application<Help> This
         status indicates that an in service
        channel is balanced by the Ekinops
        auto turn up application <Condtype>
        CHANNEL43_BALANCED_1 <Probcause>
        informationalStatus(1000) <Alarmtype>
        other (1) <Polarity> (2)
        "
	::= { pmopm2Almchannel43PortEntry 4 }


pmopm2AlmChannel43MismatchPortn OBJECT-TYPE
	SYNTAX  EkiOnOff
	MAX-ACCESS read-only
	STATUS current
	DESCRIPTION
        "
        Channel Mismatch 43 :This OID
         indicates that an out of service
        channel is detected on the Optical
        Power Monitoring input<Help> This
        alarm indicates that an out of
         service channel is detected on
        the Optical Power Monitoring input
        <Condtype> CHANNEL43_MISMATCH_1
        <Probcause> unexpectedInformation
        (75) <Alarmtype> equipmentAlarm
        <Polarity> (2)
        "
	::= { pmopm2Almchannel43PortEntry 3 }


pmopm2AlmChannel43AbsentPortn OBJECT-TYPE
	SYNTAX  EkiOnOff
	MAX-ACCESS read-only
	STATUS current
	DESCRIPTION
        "
        Channel Absent 43 :This OID indicates
        that an in service channel is absent
        on the Optical Power Monitoring
        input<Help> This alarm indicates
        that an in service channel is absent
        on the Optical Power Monitoring
        input <Condtype> CHANNEL43_ABSENT_1
        <Probcause> informationMissing
         (65) <Alarmtype> equipmentAlarm
        (5) <Polarity> (2)
        "
	::= { pmopm2Almchannel43PortEntry 2 }


--- *********************************************************
---     TABLE for the pmopm2Almchannel44Port articles
--- *********************************************************

pmopm2Almchannel44PortTable OBJECT-TYPE
	SYNTAX  SEQUENCE OF Pmopm2Almchannel44PortEntry
	MAX-ACCESS not-accessible
	STATUS current
	DESCRIPTION
        "
        List of pmopm2Almchannel44Port
        Article
        "
	::= { pmopm2AlmClientCrit 102 }


pmopm2Almchannel44PortEntry OBJECT-TYPE
	SYNTAX Pmopm2Almchannel44PortEntry
	MAX-ACCESS not-accessible
	STATUS current
	DESCRIPTION
        "
        Row definition for the pmopm2Almchannel44Port
        table
        "
	INDEX   { pmopm2Almchannel44PortIndex }
	::= { pmopm2Almchannel44PortTable 1 }


Pmopm2Almchannel44PortEntry ::=
	SEQUENCE {
	pmopm2Almchannel44PortIndex
		INTEGER,
	pmopm2AlmChannel44OosPortn
		EkiOnOff,
	pmopm2AlmChannel44PowerHighPortn
		EkiOnOff,
	pmopm2AlmChannel44PowerLowPortn
		EkiOnOff,
	pmopm2AlmChannel44BalancedPortn
		EkiOnOff,
	pmopm2AlmChannel44MismatchPortn
		EkiOnOff,
	pmopm2AlmChannel44AbsentPortn
		EkiOnOff
	}


pmopm2Almchannel44PortIndex OBJECT-TYPE
	SYNTAX  INTEGER(0..128)
	MAX-ACCESS  read-only
	STATUS current
	DESCRIPTION
        "
        Index definition for the pmopm2Almchannel44Port
        table
        "
	::= { pmopm2Almchannel44PortEntry 1 }


pmopm2AlmChannel44OosPortn OBJECT-TYPE
	SYNTAX  EkiOnOff
	MAX-ACCESS read-only
	STATUS current
	DESCRIPTION
        "
        Channel Out Of Service 44 :This
        OID indicates that the channel
         is out of service  <Help> This
        alarm indicates that the channel
        is in service <Condtype> CHANNEL44_OOS_1
        <Probcause> informationalStatus(1000)
        <Alarmtype> other (1) <Polarity>
        (2)
        "
	::= { pmopm2Almchannel44PortEntry 7 }


pmopm2AlmChannel44PowerHighPortn OBJECT-TYPE
	SYNTAX  EkiOnOff
	MAX-ACCESS read-only
	STATUS current
	DESCRIPTION
        "
        Channel Power High 44 :This OID
        indicates that the power of the
        channel is higher than the configured
        threshold<Help> This alarm indicates
        that the power of the channel is
        higher than the configured threshold
        <Condtype> CHANNEL44_POWER_HIGH_1
        <Probcause> degradedSignal (13)
        <Alarmtype> equipmentAlarm <Polarity>
        (2)
        "
	::= { pmopm2Almchannel44PortEntry 6 }


pmopm2AlmChannel44PowerLowPortn OBJECT-TYPE
	SYNTAX  EkiOnOff
	MAX-ACCESS read-only
	STATUS current
	DESCRIPTION
        "
        Channel Power Low 44 :This OID
        indicates that the power of the
        channel is lower than the configured
        threshold<Help> This alarm indicates
        that the power of the channel is
        lower than the configured threshold
        <Condtype> CHANNEL44_POWER_LOW_1
        <Probcause> degradedSignal (13)
        <Alarmtype> equipmentAlarm <Polarity>
        (2)
        "
	::= { pmopm2Almchannel44PortEntry 5 }


pmopm2AlmChannel44BalancedPortn OBJECT-TYPE
	SYNTAX  EkiOnOff
	MAX-ACCESS read-only
	STATUS current
	DESCRIPTION
        "
        Channel Balanced 44 :This OID
         indicates that an in service channel
        is balanced by the Ekinops auto
        turn up application<Help> This
         status indicates that an in service
        channel is balanced by the Ekinops
        auto turn up application <Condtype>
        CHANNEL44_BALANCED_1 <Probcause>
        informationalStatus(1000) <Alarmtype>
        other (1) <Polarity> (2)
        "
	::= { pmopm2Almchannel44PortEntry 4 }


pmopm2AlmChannel44MismatchPortn OBJECT-TYPE
	SYNTAX  EkiOnOff
	MAX-ACCESS read-only
	STATUS current
	DESCRIPTION
        "
        Channel Mismatch 44 :This OID
         indicates that an out of service
        channel is detected on the Optical
        Power Monitoring input<Help> This
        alarm indicates that an out of
         service channel is detected on
        the Optical Power Monitoring input
        <Condtype> CHANNEL44_MISMATCH_1
        <Probcause> unexpectedInformation
        (75) <Alarmtype> equipmentAlarm
        <Polarity> (2)
        "
	::= { pmopm2Almchannel44PortEntry 3 }


pmopm2AlmChannel44AbsentPortn OBJECT-TYPE
	SYNTAX  EkiOnOff
	MAX-ACCESS read-only
	STATUS current
	DESCRIPTION
        "
        Channel Absent 44 :This OID indicates
        that an in service channel is absent
        on the Optical Power Monitoring
        input<Help> This alarm indicates
        that an in service channel is absent
        on the Optical Power Monitoring
        input <Condtype> CHANNEL44_ABSENT_1
        <Probcause> informationMissing
         (65) <Alarmtype> equipmentAlarm
        (5) <Polarity> (2)
        "
	::= { pmopm2Almchannel44PortEntry 2 }


--- *********************************************************
---     TABLE for the pmopm2Almchannel45Port articles
--- *********************************************************

pmopm2Almchannel45PortTable OBJECT-TYPE
	SYNTAX  SEQUENCE OF Pmopm2Almchannel45PortEntry
	MAX-ACCESS not-accessible
	STATUS current
	DESCRIPTION
        "
        List of pmopm2Almchannel45Port
        Article
        "
	::= { pmopm2AlmClientCrit 104 }


pmopm2Almchannel45PortEntry OBJECT-TYPE
	SYNTAX Pmopm2Almchannel45PortEntry
	MAX-ACCESS not-accessible
	STATUS current
	DESCRIPTION
        "
        Row definition for the pmopm2Almchannel45Port
        table
        "
	INDEX   { pmopm2Almchannel45PortIndex }
	::= { pmopm2Almchannel45PortTable 1 }


Pmopm2Almchannel45PortEntry ::=
	SEQUENCE {
	pmopm2Almchannel45PortIndex
		INTEGER,
	pmopm2AlmChannel45OosPortn
		EkiOnOff,
	pmopm2AlmChannel45PowerHighPortn
		EkiOnOff,
	pmopm2AlmChannel45PowerLowPortn
		EkiOnOff,
	pmopm2AlmChannel45BalancedPortn
		EkiOnOff,
	pmopm2AlmChannel45MismatchPortn
		EkiOnOff,
	pmopm2AlmChannel45AbsentPortn
		EkiOnOff
	}


pmopm2Almchannel45PortIndex OBJECT-TYPE
	SYNTAX  INTEGER(0..128)
	MAX-ACCESS  read-only
	STATUS current
	DESCRIPTION
        "
        Index definition for the pmopm2Almchannel45Port
        table
        "
	::= { pmopm2Almchannel45PortEntry 1 }


pmopm2AlmChannel45OosPortn OBJECT-TYPE
	SYNTAX  EkiOnOff
	MAX-ACCESS read-only
	STATUS current
	DESCRIPTION
        "
        Channel Out Of Service 45 :This
        OID indicates that the channel
         is out of service  <Help> This
        alarm indicates that the channel
        is in service <Condtype> CHANNEL45_OOS_1
        <Probcause> informationalStatus(1000)
        <Alarmtype> other (1) <Polarity>
        (2)
        "
	::= { pmopm2Almchannel45PortEntry 7 }


pmopm2AlmChannel45PowerHighPortn OBJECT-TYPE
	SYNTAX  EkiOnOff
	MAX-ACCESS read-only
	STATUS current
	DESCRIPTION
        "
        Channel Power High 45 :This OID
        indicates that the power of the
        channel is higher than the configured
        threshold<Help> This alarm indicates
        that the power of the channel is
        higher than the configured threshold
        <Condtype> CHANNEL45_POWER_HIGH_1
        <Probcause> degradedSignal (13)
        <Alarmtype> equipmentAlarm <Polarity>
        (2)
        "
	::= { pmopm2Almchannel45PortEntry 6 }


pmopm2AlmChannel45PowerLowPortn OBJECT-TYPE
	SYNTAX  EkiOnOff
	MAX-ACCESS read-only
	STATUS current
	DESCRIPTION
        "
        Channel Power Low 45 :This OID
        indicates that the power of the
        channel is lower than the configured
        threshold<Help> This alarm indicates
        that the power of the channel is
        lower than the configured threshold
        <Condtype> CHANNEL45_POWER_LOW_1
        <Probcause> degradedSignal (13)
        <Alarmtype> equipmentAlarm <Polarity>
        (2)
        "
	::= { pmopm2Almchannel45PortEntry 5 }


pmopm2AlmChannel45BalancedPortn OBJECT-TYPE
	SYNTAX  EkiOnOff
	MAX-ACCESS read-only
	STATUS current
	DESCRIPTION
        "
        Channel Balanced 45 :This OID
         indicates that an in service channel
        is balanced by the Ekinops auto
        turn up application<Help> This
         status indicates that an in service
        channel is balanced by the Ekinops
        auto turn up application <Condtype>
        CHANNEL45_BALANCED_1 <Probcause>
        informationalStatus(1000) <Alarmtype>
        other (1) <Polarity> (2)
        "
	::= { pmopm2Almchannel45PortEntry 4 }


pmopm2AlmChannel45MismatchPortn OBJECT-TYPE
	SYNTAX  EkiOnOff
	MAX-ACCESS read-only
	STATUS current
	DESCRIPTION
        "
        Channel Mismatch 45 :This OID
         indicates that an out of service
        channel is detected on the Optical
        Power Monitoring input<Help> This
        alarm indicates that an out of
         service channel is detected on
        the Optical Power Monitoring input
        <Condtype> CHANNEL45_MISMATCH_1
        <Probcause> unexpectedInformation
        (75) <Alarmtype> equipmentAlarm
        <Polarity> (2)
        "
	::= { pmopm2Almchannel45PortEntry 3 }


pmopm2AlmChannel45AbsentPortn OBJECT-TYPE
	SYNTAX  EkiOnOff
	MAX-ACCESS read-only
	STATUS current
	DESCRIPTION
        "
        Channel Absent 45 :This OID indicates
        that an in service channel is absent
        on the Optical Power Monitoring
        input<Help> This alarm indicates
        that an in service channel is absent
        on the Optical Power Monitoring
        input <Condtype> CHANNEL45_ABSENT_1
        <Probcause> informationMissing
         (65) <Alarmtype> equipmentAlarm
        (5) <Polarity> (2)
        "
	::= { pmopm2Almchannel45PortEntry 2 }


--- *********************************************************
---     TABLE for the pmopm2Almchannel46Port articles
--- *********************************************************

pmopm2Almchannel46PortTable OBJECT-TYPE
	SYNTAX  SEQUENCE OF Pmopm2Almchannel46PortEntry
	MAX-ACCESS not-accessible
	STATUS current
	DESCRIPTION
        "
        List of pmopm2Almchannel46Port
        Article
        "
	::= { pmopm2AlmClientCrit 106 }


pmopm2Almchannel46PortEntry OBJECT-TYPE
	SYNTAX Pmopm2Almchannel46PortEntry
	MAX-ACCESS not-accessible
	STATUS current
	DESCRIPTION
        "
        Row definition for the pmopm2Almchannel46Port
        table
        "
	INDEX   { pmopm2Almchannel46PortIndex }
	::= { pmopm2Almchannel46PortTable 1 }


Pmopm2Almchannel46PortEntry ::=
	SEQUENCE {
	pmopm2Almchannel46PortIndex
		INTEGER,
	pmopm2AlmChannel46OosPortn
		EkiOnOff,
	pmopm2AlmChannel46PowerHighPortn
		EkiOnOff,
	pmopm2AlmChannel46PowerLowPortn
		EkiOnOff,
	pmopm2AlmChannel46BalancedPortn
		EkiOnOff,
	pmopm2AlmChannel46MismatchPortn
		EkiOnOff,
	pmopm2AlmChannel46AbsentPortn
		EkiOnOff
	}


pmopm2Almchannel46PortIndex OBJECT-TYPE
	SYNTAX  INTEGER(0..128)
	MAX-ACCESS  read-only
	STATUS current
	DESCRIPTION
        "
        Index definition for the pmopm2Almchannel46Port
        table
        "
	::= { pmopm2Almchannel46PortEntry 1 }


pmopm2AlmChannel46OosPortn OBJECT-TYPE
	SYNTAX  EkiOnOff
	MAX-ACCESS read-only
	STATUS current
	DESCRIPTION
        "
        Channel Out Of Service 46 :This
        OID indicates that the channel
         is out of service  <Help> This
        alarm indicates that the channel
        is in service <Condtype> CHANNEL46_OOS_1
        <Probcause> informationalStatus(1000)
        <Alarmtype> other (1) <Polarity>
        (2)
        "
	::= { pmopm2Almchannel46PortEntry 7 }


pmopm2AlmChannel46PowerHighPortn OBJECT-TYPE
	SYNTAX  EkiOnOff
	MAX-ACCESS read-only
	STATUS current
	DESCRIPTION
        "
        Channel Power High 46 :This OID
        indicates that the power of the
        channel is higher than the configured
        threshold<Help> This alarm indicates
        that the power of the channel is
        higher than the configured threshold
        <Condtype> CHANNEL46_POWER_HIGH_1
        <Probcause> degradedSignal (13)
        <Alarmtype> equipmentAlarm <Polarity>
        (2)
        "
	::= { pmopm2Almchannel46PortEntry 6 }


pmopm2AlmChannel46PowerLowPortn OBJECT-TYPE
	SYNTAX  EkiOnOff
	MAX-ACCESS read-only
	STATUS current
	DESCRIPTION
        "
        Channel Power Low 46 :This OID
        indicates that the power of the
        channel is lower than the configured
        threshold<Help> This alarm indicates
        that the power of the channel is
        lower than the configured threshold
        <Condtype> CHANNEL46_POWER_LOW_1
        <Probcause> degradedSignal (13)
        <Alarmtype> equipmentAlarm <Polarity>
        (2)
        "
	::= { pmopm2Almchannel46PortEntry 5 }


pmopm2AlmChannel46BalancedPortn OBJECT-TYPE
	SYNTAX  EkiOnOff
	MAX-ACCESS read-only
	STATUS current
	DESCRIPTION
        "
        Channel Balanced 46 :This OID
         indicates that an in service channel
        is balanced by the Ekinops auto
        turn up application<Help> This
         status indicates that an in service
        channel is balanced by the Ekinops
        auto turn up application <Condtype>
        CHANNEL46_BALANCED_1 <Probcause>
        informationalStatus(1000) <Alarmtype>
        other (1) <Polarity> (2)
        "
	::= { pmopm2Almchannel46PortEntry 4 }


pmopm2AlmChannel46MismatchPortn OBJECT-TYPE
	SYNTAX  EkiOnOff
	MAX-ACCESS read-only
	STATUS current
	DESCRIPTION
        "
        Channel Mismatch 46 :This OID
         indicates that an out of service
        channel is detected on the Optical
        Power Monitoring input<Help> This
        alarm indicates that an out of
         service channel is detected on
        the Optical Power Monitoring input
        <Condtype> CHANNEL46_MISMATCH_1
        <Probcause> unexpectedInformation
        (75) <Alarmtype> equipmentAlarm
        <Polarity> (2)
        "
	::= { pmopm2Almchannel46PortEntry 3 }


pmopm2AlmChannel46AbsentPortn OBJECT-TYPE
	SYNTAX  EkiOnOff
	MAX-ACCESS read-only
	STATUS current
	DESCRIPTION
        "
        Channel Absent 46 :This OID indicates
        that an in service channel is absent
        on the Optical Power Monitoring
        input<Help> This alarm indicates
        that an in service channel is absent
        on the Optical Power Monitoring
        input <Condtype> CHANNEL46_ABSENT_1
        <Probcause> informationMissing
         (65) <Alarmtype> equipmentAlarm
        (5) <Polarity> (2)
        "
	::= { pmopm2Almchannel46PortEntry 2 }


--- *********************************************************
---     TABLE for the pmopm2Almchannel47Port articles
--- *********************************************************

pmopm2Almchannel47PortTable OBJECT-TYPE
	SYNTAX  SEQUENCE OF Pmopm2Almchannel47PortEntry
	MAX-ACCESS not-accessible
	STATUS current
	DESCRIPTION
        "
        List of pmopm2Almchannel47Port
        Article
        "
	::= { pmopm2AlmClientCrit 108 }


pmopm2Almchannel47PortEntry OBJECT-TYPE
	SYNTAX Pmopm2Almchannel47PortEntry
	MAX-ACCESS not-accessible
	STATUS current
	DESCRIPTION
        "
        Row definition for the pmopm2Almchannel47Port
        table
        "
	INDEX   { pmopm2Almchannel47PortIndex }
	::= { pmopm2Almchannel47PortTable 1 }


Pmopm2Almchannel47PortEntry ::=
	SEQUENCE {
	pmopm2Almchannel47PortIndex
		INTEGER,
	pmopm2AlmChannel47OosPortn
		EkiOnOff,
	pmopm2AlmChannel47PowerHighPortn
		EkiOnOff,
	pmopm2AlmChannel47PowerLowPortn
		EkiOnOff,
	pmopm2AlmChannel47BalancedPortn
		EkiOnOff,
	pmopm2AlmChannel47MismatchPortn
		EkiOnOff,
	pmopm2AlmChannel47AbsentPortn
		EkiOnOff
	}


pmopm2Almchannel47PortIndex OBJECT-TYPE
	SYNTAX  INTEGER(0..128)
	MAX-ACCESS  read-only
	STATUS current
	DESCRIPTION
        "
        Index definition for the pmopm2Almchannel47Port
        table
        "
	::= { pmopm2Almchannel47PortEntry 1 }


pmopm2AlmChannel47OosPortn OBJECT-TYPE
	SYNTAX  EkiOnOff
	MAX-ACCESS read-only
	STATUS current
	DESCRIPTION
        "
        Channel Out Of Service 47 :This
        OID indicates that the channel
         is out of service  <Help> This
        alarm indicates that the channel
        is in service <Condtype> CHANNEL47_OOS_1
        <Probcause> informationalStatus(1000)
        <Alarmtype> other (1) <Polarity>
        (2)
        "
	::= { pmopm2Almchannel47PortEntry 7 }


pmopm2AlmChannel47PowerHighPortn OBJECT-TYPE
	SYNTAX  EkiOnOff
	MAX-ACCESS read-only
	STATUS current
	DESCRIPTION
        "
        Channel Power High 47 :This OID
        indicates that the power of the
        channel is higher than the configured
        threshold<Help> This alarm indicates
        that the power of the channel is
        higher than the configured threshold
        <Condtype> CHANNEL47_POWER_HIGH_1
        <Probcause> degradedSignal (13)
        <Alarmtype> equipmentAlarm <Polarity>
        (2)
        "
	::= { pmopm2Almchannel47PortEntry 6 }


pmopm2AlmChannel47PowerLowPortn OBJECT-TYPE
	SYNTAX  EkiOnOff
	MAX-ACCESS read-only
	STATUS current
	DESCRIPTION
        "
        Channel Power Low 47 :This OID
        indicates that the power of the
        channel is lower than the configured
        threshold<Help> This alarm indicates
        that the power of the channel is
        lower than the configured threshold
        <Condtype> CHANNEL47_POWER_LOW_1
        <Probcause> degradedSignal (13)
        <Alarmtype> equipmentAlarm <Polarity>
        (2)
        "
	::= { pmopm2Almchannel47PortEntry 5 }


pmopm2AlmChannel47BalancedPortn OBJECT-TYPE
	SYNTAX  EkiOnOff
	MAX-ACCESS read-only
	STATUS current
	DESCRIPTION
        "
        Channel Balanced 47 :This OID
         indicates that an in service channel
        is balanced by the Ekinops auto
        turn up application<Help> This
         status indicates that an in service
        channel is balanced by the Ekinops
        auto turn up application <Condtype>
        CHANNEL47_BALANCED_1 <Probcause>
        informationalStatus(1000) <Alarmtype>
        other (1) <Polarity> (2)
        "
	::= { pmopm2Almchannel47PortEntry 4 }


pmopm2AlmChannel47MismatchPortn OBJECT-TYPE
	SYNTAX  EkiOnOff
	MAX-ACCESS read-only
	STATUS current
	DESCRIPTION
        "
        Channel Mismatch 47 :This OID
         indicates that an out of service
        channel is detected on the Optical
        Power Monitoring input<Help> This
        alarm indicates that an out of
         service channel is detected on
        the Optical Power Monitoring input
        <Condtype> CHANNEL47_MISMATCH_1
        <Probcause> unexpectedInformation
        (75) <Alarmtype> equipmentAlarm
        <Polarity> (2)
        "
	::= { pmopm2Almchannel47PortEntry 3 }


pmopm2AlmChannel47AbsentPortn OBJECT-TYPE
	SYNTAX  EkiOnOff
	MAX-ACCESS read-only
	STATUS current
	DESCRIPTION
        "
        Channel Absent 47 :This OID indicates
        that an in service channel is absent
        on the Optical Power Monitoring
        input<Help> This alarm indicates
        that an in service channel is absent
        on the Optical Power Monitoring
        input <Condtype> CHANNEL47_ABSENT_1
        <Probcause> informationMissing
         (65) <Alarmtype> equipmentAlarm
        (5) <Polarity> (2)
        "
	::= { pmopm2Almchannel47PortEntry 2 }


--- *********************************************************
---     TABLE for the pmopm2Almchannel48Port articles
--- *********************************************************

pmopm2Almchannel48PortTable OBJECT-TYPE
	SYNTAX  SEQUENCE OF Pmopm2Almchannel48PortEntry
	MAX-ACCESS not-accessible
	STATUS current
	DESCRIPTION
        "
        List of pmopm2Almchannel48Port
        Article
        "
	::= { pmopm2AlmClientCrit 110 }


pmopm2Almchannel48PortEntry OBJECT-TYPE
	SYNTAX Pmopm2Almchannel48PortEntry
	MAX-ACCESS not-accessible
	STATUS current
	DESCRIPTION
        "
        Row definition for the pmopm2Almchannel48Port
        table
        "
	INDEX   { pmopm2Almchannel48PortIndex }
	::= { pmopm2Almchannel48PortTable 1 }


Pmopm2Almchannel48PortEntry ::=
	SEQUENCE {
	pmopm2Almchannel48PortIndex
		INTEGER,
	pmopm2AlmChannel48OosPortn
		EkiOnOff,
	pmopm2AlmChannel48PowerHighPortn
		EkiOnOff,
	pmopm2AlmChannel48PowerLowPortn
		EkiOnOff,
	pmopm2AlmChannel48BalancedPortn
		EkiOnOff,
	pmopm2AlmChannel48MismatchPortn
		EkiOnOff,
	pmopm2AlmChannel48AbsentPortn
		EkiOnOff
	}


pmopm2Almchannel48PortIndex OBJECT-TYPE
	SYNTAX  INTEGER(0..128)
	MAX-ACCESS  read-only
	STATUS current
	DESCRIPTION
        "
        Index definition for the pmopm2Almchannel48Port
        table
        "
	::= { pmopm2Almchannel48PortEntry 1 }


pmopm2AlmChannel48OosPortn OBJECT-TYPE
	SYNTAX  EkiOnOff
	MAX-ACCESS read-only
	STATUS current
	DESCRIPTION
        "
        Channel Out Of Service 48 :This
        OID indicates that the channel
         is out of service  <Help> This
        alarm indicates that the channel
        is in service <Condtype> CHANNEL48_OOS_1
        <Probcause> informationalStatus(1000)
        <Alarmtype> other (1) <Polarity>
        (2)
        "
	::= { pmopm2Almchannel48PortEntry 7 }


pmopm2AlmChannel48PowerHighPortn OBJECT-TYPE
	SYNTAX  EkiOnOff
	MAX-ACCESS read-only
	STATUS current
	DESCRIPTION
        "
        Channel Power High 48 :This OID
        indicates that the power of the
        channel is higher than the configured
        threshold<Help> This alarm indicates
        that the power of the channel is
        higher than the configured threshold
        <Condtype> CHANNEL48_POWER_HIGH_1
        <Probcause> degradedSignal (13)
        <Alarmtype> equipmentAlarm <Polarity>
        (2)
        "
	::= { pmopm2Almchannel48PortEntry 6 }


pmopm2AlmChannel48PowerLowPortn OBJECT-TYPE
	SYNTAX  EkiOnOff
	MAX-ACCESS read-only
	STATUS current
	DESCRIPTION
        "
        Channel Power Low 48 :This OID
        indicates that the power of the
        channel is lower than the configured
        threshold<Help> This alarm indicates
        that the power of the channel is
        lower than the configured threshold
        <Condtype> CHANNEL48_POWER_LOW_1
        <Probcause> degradedSignal (13)
        <Alarmtype> equipmentAlarm <Polarity>
        (2)
        "
	::= { pmopm2Almchannel48PortEntry 5 }


pmopm2AlmChannel48BalancedPortn OBJECT-TYPE
	SYNTAX  EkiOnOff
	MAX-ACCESS read-only
	STATUS current
	DESCRIPTION
        "
        Channel Balanced 48 :This OID
         indicates that an in service channel
        is balanced by the Ekinops auto
        turn up application<Help> This
         status indicates that an in service
        channel is balanced by the Ekinops
        auto turn up application <Condtype>
        CHANNEL48_BALANCED_1 <Probcause>
        informationalStatus(1000) <Alarmtype>
        other (1) <Polarity> (2)
        "
	::= { pmopm2Almchannel48PortEntry 4 }


pmopm2AlmChannel48MismatchPortn OBJECT-TYPE
	SYNTAX  EkiOnOff
	MAX-ACCESS read-only
	STATUS current
	DESCRIPTION
        "
        Channel Mismatch 48 :This OID
         indicates that an out of service
        channel is detected on the Optical
        Power Monitoring input<Help> This
        alarm indicates that an out of
         service channel is detected on
        the Optical Power Monitoring input
        <Condtype> CHANNEL48_MISMATCH_1
        <Probcause> unexpectedInformation
        (75) <Alarmtype> equipmentAlarm
        <Polarity> (2)
        "
	::= { pmopm2Almchannel48PortEntry 3 }


pmopm2AlmChannel48AbsentPortn OBJECT-TYPE
	SYNTAX  EkiOnOff
	MAX-ACCESS read-only
	STATUS current
	DESCRIPTION
        "
        Channel Absent 48 :This OID indicates
        that an in service channel is absent
        on the Optical Power Monitoring
        input<Help> This alarm indicates
        that an in service channel is absent
        on the Optical Power Monitoring
        input <Condtype> CHANNEL48_ABSENT_1
        <Probcause> informationMissing
         (65) <Alarmtype> equipmentAlarm
        (5) <Polarity> (2)
        "
	::= { pmopm2Almchannel48PortEntry 2 }


--- *********************************************************
---     TABLE for the pmopm2Almchannel49Port articles
--- *********************************************************

pmopm2Almchannel49PortTable OBJECT-TYPE
	SYNTAX  SEQUENCE OF Pmopm2Almchannel49PortEntry
	MAX-ACCESS not-accessible
	STATUS current
	DESCRIPTION
        "
        List of pmopm2Almchannel49Port
        Article
        "
	::= { pmopm2AlmClientCrit 112 }


pmopm2Almchannel49PortEntry OBJECT-TYPE
	SYNTAX Pmopm2Almchannel49PortEntry
	MAX-ACCESS not-accessible
	STATUS current
	DESCRIPTION
        "
        Row definition for the pmopm2Almchannel49Port
        table
        "
	INDEX   { pmopm2Almchannel49PortIndex }
	::= { pmopm2Almchannel49PortTable 1 }


Pmopm2Almchannel49PortEntry ::=
	SEQUENCE {
	pmopm2Almchannel49PortIndex
		INTEGER,
	pmopm2AlmChannel49OosPortn
		EkiOnOff,
	pmopm2AlmChannel49PowerHighPortn
		EkiOnOff,
	pmopm2AlmChannel49PowerLowPortn
		EkiOnOff,
	pmopm2AlmChannel49BalancedPortn
		EkiOnOff,
	pmopm2AlmChannel49MismatchPortn
		EkiOnOff,
	pmopm2AlmChannel49AbsentPortn
		EkiOnOff
	}


pmopm2Almchannel49PortIndex OBJECT-TYPE
	SYNTAX  INTEGER(0..128)
	MAX-ACCESS  read-only
	STATUS current
	DESCRIPTION
        "
        Index definition for the pmopm2Almchannel49Port
        table
        "
	::= { pmopm2Almchannel49PortEntry 1 }


pmopm2AlmChannel49OosPortn OBJECT-TYPE
	SYNTAX  EkiOnOff
	MAX-ACCESS read-only
	STATUS current
	DESCRIPTION
        "
        Channel Out Of Service 49 :This
        OID indicates that the channel
         is out of service  <Help> This
        alarm indicates that the channel
        is in service <Condtype> CHANNEL49_OOS_1
        <Probcause> informationalStatus(1000)
        <Alarmtype> other (1) <Polarity>
        (2)
        "
	::= { pmopm2Almchannel49PortEntry 7 }


pmopm2AlmChannel49PowerHighPortn OBJECT-TYPE
	SYNTAX  EkiOnOff
	MAX-ACCESS read-only
	STATUS current
	DESCRIPTION
        "
        Channel Power High 49 :This OID
        indicates that the power of the
        channel is higher than the configured
        threshold<Help> This alarm indicates
        that the power of the channel is
        higher than the configured threshold
        <Condtype> CHANNEL49_POWER_HIGH_1
        <Probcause> degradedSignal (13)
        <Alarmtype> equipmentAlarm <Polarity>
        (2)
        "
	::= { pmopm2Almchannel49PortEntry 6 }


pmopm2AlmChannel49PowerLowPortn OBJECT-TYPE
	SYNTAX  EkiOnOff
	MAX-ACCESS read-only
	STATUS current
	DESCRIPTION
        "
        Channel Power Low 49 :This OID
        indicates that the power of the
        channel is lower than the configured
        threshold<Help> This alarm indicates
        that the power of the channel is
        lower than the configured threshold
        <Condtype> CHANNEL49_POWER_LOW_1
        <Probcause> degradedSignal (13)
        <Alarmtype> equipmentAlarm <Polarity>
        (2)
        "
	::= { pmopm2Almchannel49PortEntry 5 }


pmopm2AlmChannel49BalancedPortn OBJECT-TYPE
	SYNTAX  EkiOnOff
	MAX-ACCESS read-only
	STATUS current
	DESCRIPTION
        "
        Channel Balanced 49 :This OID
         indicates that an in service channel
        is balanced by the Ekinops auto
        turn up application<Help> This
         status indicates that an in service
        channel is balanced by the Ekinops
        auto turn up application <Condtype>
        CHANNEL49_BALANCED_1 <Probcause>
        informationalStatus(1000) <Alarmtype>
        other (1) <Polarity> (2)
        "
	::= { pmopm2Almchannel49PortEntry 4 }


pmopm2AlmChannel49MismatchPortn OBJECT-TYPE
	SYNTAX  EkiOnOff
	MAX-ACCESS read-only
	STATUS current
	DESCRIPTION
        "
        Channel Mismatch 49 :This OID
         indicates that an out of service
        channel is detected on the Optical
        Power Monitoring input<Help> This
        alarm indicates that an out of
         service channel is detected on
        the Optical Power Monitoring input
        <Condtype> CHANNEL49_MISMATCH_1
        <Probcause> unexpectedInformation
        (75) <Alarmtype> equipmentAlarm
        <Polarity> (2)
        "
	::= { pmopm2Almchannel49PortEntry 3 }


pmopm2AlmChannel49AbsentPortn OBJECT-TYPE
	SYNTAX  EkiOnOff
	MAX-ACCESS read-only
	STATUS current
	DESCRIPTION
        "
        Channel Absent 49 :This OID indicates
        that an in service channel is absent
        on the Optical Power Monitoring
        input<Help> This alarm indicates
        that an in service channel is absent
        on the Optical Power Monitoring
        input <Condtype> CHANNEL49_ABSENT_1
        <Probcause> informationMissing
         (65) <Alarmtype> equipmentAlarm
        (5) <Polarity> (2)
        "
	::= { pmopm2Almchannel49PortEntry 2 }


--- *********************************************************
---     TABLE for the pmopm2Almchannel50Port articles
--- *********************************************************

pmopm2Almchannel50PortTable OBJECT-TYPE
	SYNTAX  SEQUENCE OF Pmopm2Almchannel50PortEntry
	MAX-ACCESS not-accessible
	STATUS current
	DESCRIPTION
        "
        List of pmopm2Almchannel50Port
        Article
        "
	::= { pmopm2AlmClientCrit 114 }


pmopm2Almchannel50PortEntry OBJECT-TYPE
	SYNTAX Pmopm2Almchannel50PortEntry
	MAX-ACCESS not-accessible
	STATUS current
	DESCRIPTION
        "
        Row definition for the pmopm2Almchannel50Port
        table
        "
	INDEX   { pmopm2Almchannel50PortIndex }
	::= { pmopm2Almchannel50PortTable 1 }


Pmopm2Almchannel50PortEntry ::=
	SEQUENCE {
	pmopm2Almchannel50PortIndex
		INTEGER,
	pmopm2AlmChannel50OosPortn
		EkiOnOff,
	pmopm2AlmChannel50PowerHighPortn
		EkiOnOff,
	pmopm2AlmChannel50PowerLowPortn
		EkiOnOff,
	pmopm2AlmChannel50BalancedPortn
		EkiOnOff,
	pmopm2AlmChannel50MismatchPortn
		EkiOnOff,
	pmopm2AlmChannel50AbsentPortn
		EkiOnOff
	}


pmopm2Almchannel50PortIndex OBJECT-TYPE
	SYNTAX  INTEGER(0..128)
	MAX-ACCESS  read-only
	STATUS current
	DESCRIPTION
        "
        Index definition for the pmopm2Almchannel50Port
        table
        "
	::= { pmopm2Almchannel50PortEntry 1 }


pmopm2AlmChannel50OosPortn OBJECT-TYPE
	SYNTAX  EkiOnOff
	MAX-ACCESS read-only
	STATUS current
	DESCRIPTION
        "
        Channel Out Of Service 50 :This
        OID indicates that the channel
         is out of service  <Help> This
        alarm indicates that the channel
        is in service <Condtype> CHANNEL50_OOS_1
        <Probcause> informationalStatus(1000)
        <Alarmtype> other (1) <Polarity>
        (2)
        "
	::= { pmopm2Almchannel50PortEntry 7 }


pmopm2AlmChannel50PowerHighPortn OBJECT-TYPE
	SYNTAX  EkiOnOff
	MAX-ACCESS read-only
	STATUS current
	DESCRIPTION
        "
        Channel Power High 50 :This OID
        indicates that the power of the
        channel is higher than the configured
        threshold<Help> This alarm indicates
        that the power of the channel is
        higher than the configured threshold
        <Condtype> CHANNEL50_POWER_HIGH_1
        <Probcause> degradedSignal (13)
        <Alarmtype> equipmentAlarm <Polarity>
        (2)
        "
	::= { pmopm2Almchannel50PortEntry 6 }


pmopm2AlmChannel50PowerLowPortn OBJECT-TYPE
	SYNTAX  EkiOnOff
	MAX-ACCESS read-only
	STATUS current
	DESCRIPTION
        "
        Channel Power Low 50 :This OID
        indicates that the power of the
        channel is lower than the configured
        threshold<Help> This alarm indicates
        that the power of the channel is
        lower than the configured threshold
        <Condtype> CHANNEL50_POWER_LOW_1
        <Probcause> degradedSignal (13)
        <Alarmtype> equipmentAlarm <Polarity>
        (2)
        "
	::= { pmopm2Almchannel50PortEntry 5 }


pmopm2AlmChannel50BalancedPortn OBJECT-TYPE
	SYNTAX  EkiOnOff
	MAX-ACCESS read-only
	STATUS current
	DESCRIPTION
        "
        Channel Balanced 50 :This OID
         indicates that an in service channel
        is balanced by the Ekinops auto
        turn up application<Help> This
         status indicates that an in service
        channel is balanced by the Ekinops
        auto turn up application <Condtype>
        CHANNEL50_BALANCED_1 <Probcause>
        informationalStatus(1000) <Alarmtype>
        other (1) <Polarity> (2)
        "
	::= { pmopm2Almchannel50PortEntry 4 }


pmopm2AlmChannel50MismatchPortn OBJECT-TYPE
	SYNTAX  EkiOnOff
	MAX-ACCESS read-only
	STATUS current
	DESCRIPTION
        "
        Channel Mismatch 50 :This OID
         indicates that an out of service
        channel is detected on the Optical
        Power Monitoring input<Help> This
        alarm indicates that an out of
         service channel is detected on
        the Optical Power Monitoring input
        <Condtype> CHANNEL50_MISMATCH_1
        <Probcause> unexpectedInformation
        (75) <Alarmtype> equipmentAlarm
        <Polarity> (2)
        "
	::= { pmopm2Almchannel50PortEntry 3 }


pmopm2AlmChannel50AbsentPortn OBJECT-TYPE
	SYNTAX  EkiOnOff
	MAX-ACCESS read-only
	STATUS current
	DESCRIPTION
        "
        Channel Absent 50 :This OID indicates
        that an in service channel is absent
        on the Optical Power Monitoring
        input<Help> This alarm indicates
        that an in service channel is absent
        on the Optical Power Monitoring
        input <Condtype> CHANNEL50_ABSENT_1
        <Probcause> informationMissing
         (65) <Alarmtype> equipmentAlarm
        (5) <Polarity> (2)
        "
	::= { pmopm2Almchannel50PortEntry 2 }


--- *********************************************************
---     TABLE for the pmopm2Almchannel51Port articles
--- *********************************************************

pmopm2Almchannel51PortTable OBJECT-TYPE
	SYNTAX  SEQUENCE OF Pmopm2Almchannel51PortEntry
	MAX-ACCESS not-accessible
	STATUS current
	DESCRIPTION
        "
        List of pmopm2Almchannel51Port
        Article
        "
	::= { pmopm2AlmClientCrit 116 }


pmopm2Almchannel51PortEntry OBJECT-TYPE
	SYNTAX Pmopm2Almchannel51PortEntry
	MAX-ACCESS not-accessible
	STATUS current
	DESCRIPTION
        "
        Row definition for the pmopm2Almchannel51Port
        table
        "
	INDEX   { pmopm2Almchannel51PortIndex }
	::= { pmopm2Almchannel51PortTable 1 }


Pmopm2Almchannel51PortEntry ::=
	SEQUENCE {
	pmopm2Almchannel51PortIndex
		INTEGER,
	pmopm2AlmChannel51OosPortn
		EkiOnOff,
	pmopm2AlmChannel51PowerHighPortn
		EkiOnOff,
	pmopm2AlmChannel51PowerLowPortn
		EkiOnOff,
	pmopm2AlmChannel51BalancedPortn
		EkiOnOff,
	pmopm2AlmChannel51MismatchPortn
		EkiOnOff,
	pmopm2AlmChannel51AbsentPortn
		EkiOnOff
	}


pmopm2Almchannel51PortIndex OBJECT-TYPE
	SYNTAX  INTEGER(0..128)
	MAX-ACCESS  read-only
	STATUS current
	DESCRIPTION
        "
        Index definition for the pmopm2Almchannel51Port
        table
        "
	::= { pmopm2Almchannel51PortEntry 1 }


pmopm2AlmChannel51OosPortn OBJECT-TYPE
	SYNTAX  EkiOnOff
	MAX-ACCESS read-only
	STATUS current
	DESCRIPTION
        "
        Channel Out Of Service 51 :This
        OID indicates that the channel
         is out of service  <Help> This
        alarm indicates that the channel
        is in service <Condtype> CHANNEL51_OOS_1
        <Probcause> informationalStatus(1000)
        <Alarmtype> other (1) <Polarity>
        (2)
        "
	::= { pmopm2Almchannel51PortEntry 7 }


pmopm2AlmChannel51PowerHighPortn OBJECT-TYPE
	SYNTAX  EkiOnOff
	MAX-ACCESS read-only
	STATUS current
	DESCRIPTION
        "
        Channel Power High 51 :This OID
        indicates that the power of the
        channel is higher than the configured
        threshold<Help> This alarm indicates
        that the power of the channel is
        higher than the configured threshold
        <Condtype> CHANNEL51_POWER_HIGH_1
        <Probcause> degradedSignal (13)
        <Alarmtype> equipmentAlarm <Polarity>
        (2)
        "
	::= { pmopm2Almchannel51PortEntry 6 }


pmopm2AlmChannel51PowerLowPortn OBJECT-TYPE
	SYNTAX  EkiOnOff
	MAX-ACCESS read-only
	STATUS current
	DESCRIPTION
        "
        Channel Power Low 51 :This OID
        indicates that the power of the
        channel is lower than the configured
        threshold<Help> This alarm indicates
        that the power of the channel is
        lower than the configured threshold
        <Condtype> CHANNEL51_POWER_LOW_1
        <Probcause> degradedSignal (13)
        <Alarmtype> equipmentAlarm <Polarity>
        (2)
        "
	::= { pmopm2Almchannel51PortEntry 5 }


pmopm2AlmChannel51BalancedPortn OBJECT-TYPE
	SYNTAX  EkiOnOff
	MAX-ACCESS read-only
	STATUS current
	DESCRIPTION
        "
        Channel Balanced 51 :This OID
         indicates that an in service channel
        is balanced by the Ekinops auto
        turn up application<Help> This
         status indicates that an in service
        channel is balanced by the Ekinops
        auto turn up application <Condtype>
        CHANNEL51_BALANCED_1 <Probcause>
        informationalStatus(1000) <Alarmtype>
        other (1) <Polarity> (2)
        "
	::= { pmopm2Almchannel51PortEntry 4 }


pmopm2AlmChannel51MismatchPortn OBJECT-TYPE
	SYNTAX  EkiOnOff
	MAX-ACCESS read-only
	STATUS current
	DESCRIPTION
        "
        Channel Mismatch 51 :This OID
         indicates that an out of service
        channel is detected on the Optical
        Power Monitoring input<Help> This
        alarm indicates that an out of
         service channel is detected on
        the Optical Power Monitoring input
        <Condtype> CHANNEL51_MISMATCH_1
        <Probcause> unexpectedInformation
        (75) <Alarmtype> equipmentAlarm
        <Polarity> (2)
        "
	::= { pmopm2Almchannel51PortEntry 3 }


pmopm2AlmChannel51AbsentPortn OBJECT-TYPE
	SYNTAX  EkiOnOff
	MAX-ACCESS read-only
	STATUS current
	DESCRIPTION
        "
        Channel Absent 51 :This OID indicates
        that an in service channel is absent
        on the Optical Power Monitoring
        input<Help> This alarm indicates
        that an in service channel is absent
        on the Optical Power Monitoring
        input <Condtype> CHANNEL51_ABSENT_1
        <Probcause> informationMissing
         (65) <Alarmtype> equipmentAlarm
        (5) <Polarity> (2)
        "
	::= { pmopm2Almchannel51PortEntry 2 }


--- *********************************************************
---     TABLE for the pmopm2Almchannel52Port articles
--- *********************************************************

pmopm2Almchannel52PortTable OBJECT-TYPE
	SYNTAX  SEQUENCE OF Pmopm2Almchannel52PortEntry
	MAX-ACCESS not-accessible
	STATUS current
	DESCRIPTION
        "
        List of pmopm2Almchannel52Port
        Article
        "
	::= { pmopm2AlmClientCrit 118 }


pmopm2Almchannel52PortEntry OBJECT-TYPE
	SYNTAX Pmopm2Almchannel52PortEntry
	MAX-ACCESS not-accessible
	STATUS current
	DESCRIPTION
        "
        Row definition for the pmopm2Almchannel52Port
        table
        "
	INDEX   { pmopm2Almchannel52PortIndex }
	::= { pmopm2Almchannel52PortTable 1 }


Pmopm2Almchannel52PortEntry ::=
	SEQUENCE {
	pmopm2Almchannel52PortIndex
		INTEGER,
	pmopm2AlmChannel52OosPortn
		EkiOnOff,
	pmopm2AlmChannel52PowerHighPortn
		EkiOnOff,
	pmopm2AlmChannel52PowerLowPortn
		EkiOnOff,
	pmopm2AlmChannel52BalancedPortn
		EkiOnOff,
	pmopm2AlmChannel52MismatchPortn
		EkiOnOff,
	pmopm2AlmChannel52AbsentPortn
		EkiOnOff
	}


pmopm2Almchannel52PortIndex OBJECT-TYPE
	SYNTAX  INTEGER(0..128)
	MAX-ACCESS  read-only
	STATUS current
	DESCRIPTION
        "
        Index definition for the pmopm2Almchannel52Port
        table
        "
	::= { pmopm2Almchannel52PortEntry 1 }


pmopm2AlmChannel52OosPortn OBJECT-TYPE
	SYNTAX  EkiOnOff
	MAX-ACCESS read-only
	STATUS current
	DESCRIPTION
        "
        Channel Out Of Service 52 :This
        OID indicates that the channel
         is out of service  <Help> This
        alarm indicates that the channel
        is in service <Condtype> CHANNEL52_OOS_1
        <Probcause> informationalStatus(1000)
        <Alarmtype> other (1) <Polarity>
        (2)
        "
	::= { pmopm2Almchannel52PortEntry 7 }


pmopm2AlmChannel52PowerHighPortn OBJECT-TYPE
	SYNTAX  EkiOnOff
	MAX-ACCESS read-only
	STATUS current
	DESCRIPTION
        "
        Channel Power High 52 :This OID
        indicates that the power of the
        channel is higher than the configured
        threshold<Help> This alarm indicates
        that the power of the channel is
        higher than the configured threshold
        <Condtype> CHANNEL52_POWER_HIGH_1
        <Probcause> degradedSignal (13)
        <Alarmtype> equipmentAlarm <Polarity>
        (2)
        "
	::= { pmopm2Almchannel52PortEntry 6 }


pmopm2AlmChannel52PowerLowPortn OBJECT-TYPE
	SYNTAX  EkiOnOff
	MAX-ACCESS read-only
	STATUS current
	DESCRIPTION
        "
        Channel Power Low 52 :This OID
        indicates that the power of the
        channel is lower than the configured
        threshold<Help> This alarm indicates
        that the power of the channel is
        lower than the configured threshold
        <Condtype> CHANNEL52_POWER_LOW_1
        <Probcause> degradedSignal (13)
        <Alarmtype> equipmentAlarm <Polarity>
        (2)
        "
	::= { pmopm2Almchannel52PortEntry 5 }


pmopm2AlmChannel52BalancedPortn OBJECT-TYPE
	SYNTAX  EkiOnOff
	MAX-ACCESS read-only
	STATUS current
	DESCRIPTION
        "
        Channel Balanced 52 :This OID
         indicates that an in service channel
        is balanced by the Ekinops auto
        turn up application<Help> This
         status indicates that an in service
        channel is balanced by the Ekinops
        auto turn up application <Condtype>
        CHANNEL52_BALANCED_1 <Probcause>
        informationalStatus(1000) <Alarmtype>
        other (1) <Polarity> (2)
        "
	::= { pmopm2Almchannel52PortEntry 4 }


pmopm2AlmChannel52MismatchPortn OBJECT-TYPE
	SYNTAX  EkiOnOff
	MAX-ACCESS read-only
	STATUS current
	DESCRIPTION
        "
        Channel Mismatch 52 :This OID
         indicates that an out of service
        channel is detected on the Optical
        Power Monitoring input<Help> This
        alarm indicates that an out of
         service channel is detected on
        the Optical Power Monitoring input
        <Condtype> CHANNEL52_MISMATCH_1
        <Probcause> unexpectedInformation
        (75) <Alarmtype> equipmentAlarm
        <Polarity> (2)
        "
	::= { pmopm2Almchannel52PortEntry 3 }


pmopm2AlmChannel52AbsentPortn OBJECT-TYPE
	SYNTAX  EkiOnOff
	MAX-ACCESS read-only
	STATUS current
	DESCRIPTION
        "
        Channel Absent 52 :This OID indicates
        that an in service channel is absent
        on the Optical Power Monitoring
        input<Help> This alarm indicates
        that an in service channel is absent
        on the Optical Power Monitoring
        input <Condtype> CHANNEL52_ABSENT_1
        <Probcause> informationMissing
         (65) <Alarmtype> equipmentAlarm
        (5) <Polarity> (2)
        "
	::= { pmopm2Almchannel52PortEntry 2 }


--- *********************************************************
---     TABLE for the pmopm2Almchannel53Port articles
--- *********************************************************

pmopm2Almchannel53PortTable OBJECT-TYPE
	SYNTAX  SEQUENCE OF Pmopm2Almchannel53PortEntry
	MAX-ACCESS not-accessible
	STATUS current
	DESCRIPTION
        "
        List of pmopm2Almchannel53Port
        Article
        "
	::= { pmopm2AlmClientCrit 120 }


pmopm2Almchannel53PortEntry OBJECT-TYPE
	SYNTAX Pmopm2Almchannel53PortEntry
	MAX-ACCESS not-accessible
	STATUS current
	DESCRIPTION
        "
        Row definition for the pmopm2Almchannel53Port
        table
        "
	INDEX   { pmopm2Almchannel53PortIndex }
	::= { pmopm2Almchannel53PortTable 1 }


Pmopm2Almchannel53PortEntry ::=
	SEQUENCE {
	pmopm2Almchannel53PortIndex
		INTEGER,
	pmopm2AlmChannel53OosPortn
		EkiOnOff,
	pmopm2AlmChannel53PowerHighPortn
		EkiOnOff,
	pmopm2AlmChannel53PowerLowPortn
		EkiOnOff,
	pmopm2AlmChannel53BalancedPortn
		EkiOnOff,
	pmopm2AlmChannel53MismatchPortn
		EkiOnOff,
	pmopm2AlmChannel53AbsentPortn
		EkiOnOff
	}


pmopm2Almchannel53PortIndex OBJECT-TYPE
	SYNTAX  INTEGER(0..128)
	MAX-ACCESS  read-only
	STATUS current
	DESCRIPTION
        "
        Index definition for the pmopm2Almchannel53Port
        table
        "
	::= { pmopm2Almchannel53PortEntry 1 }


pmopm2AlmChannel53OosPortn OBJECT-TYPE
	SYNTAX  EkiOnOff
	MAX-ACCESS read-only
	STATUS current
	DESCRIPTION
        "
        Channel Out Of Service 53 :This
        OID indicates that the channel
         is out of service  <Help> This
        alarm indicates that the channel
        is in service <Condtype> CHANNEL53_OOS_1
        <Probcause> informationalStatus(1000)
        <Alarmtype> other (1) <Polarity>
        (2)
        "
	::= { pmopm2Almchannel53PortEntry 7 }


pmopm2AlmChannel53PowerHighPortn OBJECT-TYPE
	SYNTAX  EkiOnOff
	MAX-ACCESS read-only
	STATUS current
	DESCRIPTION
        "
        Channel Power High 53 :This OID
        indicates that the power of the
        channel is higher than the configured
        threshold<Help> This alarm indicates
        that the power of the channel is
        higher than the configured threshold
        <Condtype> CHANNEL53_POWER_HIGH_1
        <Probcause> degradedSignal (13)
        <Alarmtype> equipmentAlarm <Polarity>
        (2)
        "
	::= { pmopm2Almchannel53PortEntry 6 }


pmopm2AlmChannel53PowerLowPortn OBJECT-TYPE
	SYNTAX  EkiOnOff
	MAX-ACCESS read-only
	STATUS current
	DESCRIPTION
        "
        Channel Power Low 53 :This OID
        indicates that the power of the
        channel is lower than the configured
        threshold<Help> This alarm indicates
        that the power of the channel is
        lower than the configured threshold
        <Condtype> CHANNEL53_POWER_LOW_1
        <Probcause> degradedSignal (13)
        <Alarmtype> equipmentAlarm <Polarity>
        (2)
        "
	::= { pmopm2Almchannel53PortEntry 5 }


pmopm2AlmChannel53BalancedPortn OBJECT-TYPE
	SYNTAX  EkiOnOff
	MAX-ACCESS read-only
	STATUS current
	DESCRIPTION
        "
        Channel Balanced 53 :This OID
         indicates that an in service channel
        is balanced by the Ekinops auto
        turn up application<Help> This
         status indicates that an in service
        channel is balanced by the Ekinops
        auto turn up application <Condtype>
        CHANNEL53_BALANCED_1 <Probcause>
        informationalStatus(1000) <Alarmtype>
        other (1) <Polarity> (2)
        "
	::= { pmopm2Almchannel53PortEntry 4 }


pmopm2AlmChannel53MismatchPortn OBJECT-TYPE
	SYNTAX  EkiOnOff
	MAX-ACCESS read-only
	STATUS current
	DESCRIPTION
        "
        Channel Mismatch 53 :This OID
         indicates that an out of service
        channel is detected on the Optical
        Power Monitoring input<Help> This
        alarm indicates that an out of
         service channel is detected on
        the Optical Power Monitoring input
        <Condtype> CHANNEL53_MISMATCH_1
        <Probcause> unexpectedInformation
        (75) <Alarmtype> equipmentAlarm
        <Polarity> (2)
        "
	::= { pmopm2Almchannel53PortEntry 3 }


pmopm2AlmChannel53AbsentPortn OBJECT-TYPE
	SYNTAX  EkiOnOff
	MAX-ACCESS read-only
	STATUS current
	DESCRIPTION
        "
        Channel Absent 53 :This OID indicates
        that an in service channel is absent
        on the Optical Power Monitoring
        input<Help> This alarm indicates
        that an in service channel is absent
        on the Optical Power Monitoring
        input <Condtype> CHANNEL53_ABSENT_1
        <Probcause> informationMissing
         (65) <Alarmtype> equipmentAlarm
        (5) <Polarity> (2)
        "
	::= { pmopm2Almchannel53PortEntry 2 }


--- *********************************************************
---     TABLE for the pmopm2Almchannel54Port articles
--- *********************************************************

pmopm2Almchannel54PortTable OBJECT-TYPE
	SYNTAX  SEQUENCE OF Pmopm2Almchannel54PortEntry
	MAX-ACCESS not-accessible
	STATUS current
	DESCRIPTION
        "
        List of pmopm2Almchannel54Port
        Article
        "
	::= { pmopm2AlmClientCrit 122 }


pmopm2Almchannel54PortEntry OBJECT-TYPE
	SYNTAX Pmopm2Almchannel54PortEntry
	MAX-ACCESS not-accessible
	STATUS current
	DESCRIPTION
        "
        Row definition for the pmopm2Almchannel54Port
        table
        "
	INDEX   { pmopm2Almchannel54PortIndex }
	::= { pmopm2Almchannel54PortTable 1 }


Pmopm2Almchannel54PortEntry ::=
	SEQUENCE {
	pmopm2Almchannel54PortIndex
		INTEGER,
	pmopm2AlmChannel54OosPortn
		EkiOnOff,
	pmopm2AlmChannel54PowerHighPortn
		EkiOnOff,
	pmopm2AlmChannel54PowerLowPortn
		EkiOnOff,
	pmopm2AlmChannel54BalancedPortn
		EkiOnOff,
	pmopm2AlmChannel54MismatchPortn
		EkiOnOff,
	pmopm2AlmChannel54AbsentPortn
		EkiOnOff
	}


pmopm2Almchannel54PortIndex OBJECT-TYPE
	SYNTAX  INTEGER(0..128)
	MAX-ACCESS  read-only
	STATUS current
	DESCRIPTION
        "
        Index definition for the pmopm2Almchannel54Port
        table
        "
	::= { pmopm2Almchannel54PortEntry 1 }


pmopm2AlmChannel54OosPortn OBJECT-TYPE
	SYNTAX  EkiOnOff
	MAX-ACCESS read-only
	STATUS current
	DESCRIPTION
        "
        Channel Out Of Service 54 :This
        OID indicates that the channel
         is out of service  <Help> This
        alarm indicates that the channel
        is in service <Condtype> CHANNEL54_OOS_1
        <Probcause> informationalStatus(1000)
        <Alarmtype> other (1) <Polarity>
        (2)
        "
	::= { pmopm2Almchannel54PortEntry 7 }


pmopm2AlmChannel54PowerHighPortn OBJECT-TYPE
	SYNTAX  EkiOnOff
	MAX-ACCESS read-only
	STATUS current
	DESCRIPTION
        "
        Channel Power High 54 :This OID
        indicates that the power of the
        channel is higher than the configured
        threshold<Help> This alarm indicates
        that the power of the channel is
        higher than the configured threshold
        <Condtype> CHANNEL54_POWER_HIGH_1
        <Probcause> degradedSignal (13)
        <Alarmtype> equipmentAlarm <Polarity>
        (2)
        "
	::= { pmopm2Almchannel54PortEntry 6 }


pmopm2AlmChannel54PowerLowPortn OBJECT-TYPE
	SYNTAX  EkiOnOff
	MAX-ACCESS read-only
	STATUS current
	DESCRIPTION
        "
        Channel Power Low 54 :This OID
        indicates that the power of the
        channel is lower than the configured
        threshold<Help> This alarm indicates
        that the power of the channel is
        lower than the configured threshold
        <Condtype> CHANNEL54_POWER_LOW_1
        <Probcause> degradedSignal (13)
        <Alarmtype> equipmentAlarm <Polarity>
        (2)
        "
	::= { pmopm2Almchannel54PortEntry 5 }


pmopm2AlmChannel54BalancedPortn OBJECT-TYPE
	SYNTAX  EkiOnOff
	MAX-ACCESS read-only
	STATUS current
	DESCRIPTION
        "
        Channel Balanced 54 :This OID
         indicates that an in service channel
        is balanced by the Ekinops auto
        turn up application<Help> This
         status indicates that an in service
        channel is balanced by the Ekinops
        auto turn up application <Condtype>
        CHANNEL54_BALANCED_1 <Probcause>
        informationalStatus(1000) <Alarmtype>
        other (1) <Polarity> (2)
        "
	::= { pmopm2Almchannel54PortEntry 4 }


pmopm2AlmChannel54MismatchPortn OBJECT-TYPE
	SYNTAX  EkiOnOff
	MAX-ACCESS read-only
	STATUS current
	DESCRIPTION
        "
        Channel Mismatch 54 :This OID
         indicates that an out of service
        channel is detected on the Optical
        Power Monitoring input<Help> This
        alarm indicates that an out of
         service channel is detected on
        the Optical Power Monitoring input
        <Condtype> CHANNEL54_MISMATCH_1
        <Probcause> unexpectedInformation
        (75) <Alarmtype> equipmentAlarm
        <Polarity> (2)
        "
	::= { pmopm2Almchannel54PortEntry 3 }


pmopm2AlmChannel54AbsentPortn OBJECT-TYPE
	SYNTAX  EkiOnOff
	MAX-ACCESS read-only
	STATUS current
	DESCRIPTION
        "
        Channel Absent 54 :This OID indicates
        that an in service channel is absent
        on the Optical Power Monitoring
        input<Help> This alarm indicates
        that an in service channel is absent
        on the Optical Power Monitoring
        input <Condtype> CHANNEL54_ABSENT_1
        <Probcause> informationMissing
         (65) <Alarmtype> equipmentAlarm
        (5) <Polarity> (2)
        "
	::= { pmopm2Almchannel54PortEntry 2 }


--- *********************************************************
---     TABLE for the pmopm2Almchannel55Port articles
--- *********************************************************

pmopm2Almchannel55PortTable OBJECT-TYPE
	SYNTAX  SEQUENCE OF Pmopm2Almchannel55PortEntry
	MAX-ACCESS not-accessible
	STATUS current
	DESCRIPTION
        "
        List of pmopm2Almchannel55Port
        Article
        "
	::= { pmopm2AlmClientCrit 124 }


pmopm2Almchannel55PortEntry OBJECT-TYPE
	SYNTAX Pmopm2Almchannel55PortEntry
	MAX-ACCESS not-accessible
	STATUS current
	DESCRIPTION
        "
        Row definition for the pmopm2Almchannel55Port
        table
        "
	INDEX   { pmopm2Almchannel55PortIndex }
	::= { pmopm2Almchannel55PortTable 1 }


Pmopm2Almchannel55PortEntry ::=
	SEQUENCE {
	pmopm2Almchannel55PortIndex
		INTEGER,
	pmopm2AlmChannel55OosPortn
		EkiOnOff,
	pmopm2AlmChannel55PowerHighPortn
		EkiOnOff,
	pmopm2AlmChannel55PowerLowPortn
		EkiOnOff,
	pmopm2AlmChannel55BalancedPortn
		EkiOnOff,
	pmopm2AlmChannel55MismatchPortn
		EkiOnOff,
	pmopm2AlmChannel55AbsentPortn
		EkiOnOff
	}


pmopm2Almchannel55PortIndex OBJECT-TYPE
	SYNTAX  INTEGER(0..128)
	MAX-ACCESS  read-only
	STATUS current
	DESCRIPTION
        "
        Index definition for the pmopm2Almchannel55Port
        table
        "
	::= { pmopm2Almchannel55PortEntry 1 }


pmopm2AlmChannel55OosPortn OBJECT-TYPE
	SYNTAX  EkiOnOff
	MAX-ACCESS read-only
	STATUS current
	DESCRIPTION
        "
        Channel Out Of Service 55 :This
        OID indicates that the channel
         is out of service  <Help> This
        alarm indicates that the channel
        is in service <Condtype> CHANNEL55_OOS_1
        <Probcause> informationalStatus(1000)
        <Alarmtype> other (1) <Polarity>
        (2)
        "
	::= { pmopm2Almchannel55PortEntry 7 }


pmopm2AlmChannel55PowerHighPortn OBJECT-TYPE
	SYNTAX  EkiOnOff
	MAX-ACCESS read-only
	STATUS current
	DESCRIPTION
        "
        Channel Power High 55 :This OID
        indicates that the power of the
        channel is higher than the configured
        threshold<Help> This alarm indicates
        that the power of the channel is
        higher than the configured threshold
        <Condtype> CHANNEL55_POWER_HIGH_1
        <Probcause> degradedSignal (13)
        <Alarmtype> equipmentAlarm <Polarity>
        (2)
        "
	::= { pmopm2Almchannel55PortEntry 6 }


pmopm2AlmChannel55PowerLowPortn OBJECT-TYPE
	SYNTAX  EkiOnOff
	MAX-ACCESS read-only
	STATUS current
	DESCRIPTION
        "
        Channel Power Low 55 :This OID
        indicates that the power of the
        channel is lower than the configured
        threshold<Help> This alarm indicates
        that the power of the channel is
        lower than the configured threshold
        <Condtype> CHANNEL55_POWER_LOW_1
        <Probcause> degradedSignal (13)
        <Alarmtype> equipmentAlarm <Polarity>
        (2)
        "
	::= { pmopm2Almchannel55PortEntry 5 }


pmopm2AlmChannel55BalancedPortn OBJECT-TYPE
	SYNTAX  EkiOnOff
	MAX-ACCESS read-only
	STATUS current
	DESCRIPTION
        "
        Channel Balanced 55 :This OID
         indicates that an in service channel
        is balanced by the Ekinops auto
        turn up application<Help> This
         status indicates that an in service
        channel is balanced by the Ekinops
        auto turn up application <Condtype>
        CHANNEL55_BALANCED_1 <Probcause>
        informationalStatus(1000) <Alarmtype>
        other (1) <Polarity> (2)
        "
	::= { pmopm2Almchannel55PortEntry 4 }


pmopm2AlmChannel55MismatchPortn OBJECT-TYPE
	SYNTAX  EkiOnOff
	MAX-ACCESS read-only
	STATUS current
	DESCRIPTION
        "
        Channel Mismatch 55 :This OID
         indicates that an out of service
        channel is detected on the Optical
        Power Monitoring input<Help> This
        alarm indicates that an out of
         service channel is detected on
        the Optical Power Monitoring input
        <Condtype> CHANNEL55_MISMATCH_1
        <Probcause> unexpectedInformation
        (75) <Alarmtype> equipmentAlarm
        <Polarity> (2)
        "
	::= { pmopm2Almchannel55PortEntry 3 }


pmopm2AlmChannel55AbsentPortn OBJECT-TYPE
	SYNTAX  EkiOnOff
	MAX-ACCESS read-only
	STATUS current
	DESCRIPTION
        "
        Channel Absent 55 :This OID indicates
        that an in service channel is absent
        on the Optical Power Monitoring
        input<Help> This alarm indicates
        that an in service channel is absent
        on the Optical Power Monitoring
        input <Condtype> CHANNEL55_ABSENT_1
        <Probcause> informationMissing
         (65) <Alarmtype> equipmentAlarm
        (5) <Polarity> (2)
        "
	::= { pmopm2Almchannel55PortEntry 2 }


--- *********************************************************
---     TABLE for the pmopm2Almchannel56Port articles
--- *********************************************************

pmopm2Almchannel56PortTable OBJECT-TYPE
	SYNTAX  SEQUENCE OF Pmopm2Almchannel56PortEntry
	MAX-ACCESS not-accessible
	STATUS current
	DESCRIPTION
        "
        List of pmopm2Almchannel56Port
        Article
        "
	::= { pmopm2AlmClientCrit 126 }


pmopm2Almchannel56PortEntry OBJECT-TYPE
	SYNTAX Pmopm2Almchannel56PortEntry
	MAX-ACCESS not-accessible
	STATUS current
	DESCRIPTION
        "
        Row definition for the pmopm2Almchannel56Port
        table
        "
	INDEX   { pmopm2Almchannel56PortIndex }
	::= { pmopm2Almchannel56PortTable 1 }


Pmopm2Almchannel56PortEntry ::=
	SEQUENCE {
	pmopm2Almchannel56PortIndex
		INTEGER,
	pmopm2AlmChannel56OosPortn
		EkiOnOff,
	pmopm2AlmChannel56PowerHighPortn
		EkiOnOff,
	pmopm2AlmChannel56PowerLowPortn
		EkiOnOff,
	pmopm2AlmChannel56BalancedPortn
		EkiOnOff,
	pmopm2AlmChannel56MismatchPortn
		EkiOnOff,
	pmopm2AlmChannel56AbsentPortn
		EkiOnOff
	}


pmopm2Almchannel56PortIndex OBJECT-TYPE
	SYNTAX  INTEGER(0..128)
	MAX-ACCESS  read-only
	STATUS current
	DESCRIPTION
        "
        Index definition for the pmopm2Almchannel56Port
        table
        "
	::= { pmopm2Almchannel56PortEntry 1 }


pmopm2AlmChannel56OosPortn OBJECT-TYPE
	SYNTAX  EkiOnOff
	MAX-ACCESS read-only
	STATUS current
	DESCRIPTION
        "
        Channel Out Of Service 56 :This
        OID indicates that the channel
         is out of service  <Help> This
        alarm indicates that the channel
        is in service <Condtype> CHANNEL56_OOS_1
        <Probcause> informationalStatus(1000)
        <Alarmtype> other (1) <Polarity>
        (2)
        "
	::= { pmopm2Almchannel56PortEntry 7 }


pmopm2AlmChannel56PowerHighPortn OBJECT-TYPE
	SYNTAX  EkiOnOff
	MAX-ACCESS read-only
	STATUS current
	DESCRIPTION
        "
        Channel Power High 56 :This OID
        indicates that the power of the
        channel is higher than the configured
        threshold<Help> This alarm indicates
        that the power of the channel is
        higher than the configured threshold
        <Condtype> CHANNEL56_POWER_HIGH_1
        <Probcause> degradedSignal (13)
        <Alarmtype> equipmentAlarm <Polarity>
        (2)
        "
	::= { pmopm2Almchannel56PortEntry 6 }


pmopm2AlmChannel56PowerLowPortn OBJECT-TYPE
	SYNTAX  EkiOnOff
	MAX-ACCESS read-only
	STATUS current
	DESCRIPTION
        "
        Channel Power Low 56 :This OID
        indicates that the power of the
        channel is lower than the configured
        threshold<Help> This alarm indicates
        that the power of the channel is
        lower than the configured threshold
        <Condtype> CHANNEL56_POWER_LOW_1
        <Probcause> degradedSignal (13)
        <Alarmtype> equipmentAlarm <Polarity>
        (2)
        "
	::= { pmopm2Almchannel56PortEntry 5 }


pmopm2AlmChannel56BalancedPortn OBJECT-TYPE
	SYNTAX  EkiOnOff
	MAX-ACCESS read-only
	STATUS current
	DESCRIPTION
        "
        Channel Balanced 56 :This OID
         indicates that an in service channel
        is balanced by the Ekinops auto
        turn up application<Help> This
         status indicates that an in service
        channel is balanced by the Ekinops
        auto turn up application <Condtype>
        CHANNEL56_BALANCED_1 <Probcause>
        informationalStatus(1000) <Alarmtype>
        other (1) <Polarity> (2)
        "
	::= { pmopm2Almchannel56PortEntry 4 }


pmopm2AlmChannel56MismatchPortn OBJECT-TYPE
	SYNTAX  EkiOnOff
	MAX-ACCESS read-only
	STATUS current
	DESCRIPTION
        "
        Channel Mismatch 56 :This OID
         indicates that an out of service
        channel is detected on the Optical
        Power Monitoring input<Help> This
        alarm indicates that an out of
         service channel is detected on
        the Optical Power Monitoring input
        <Condtype> CHANNEL56_MISMATCH_1
        <Probcause> unexpectedInformation
        (75) <Alarmtype> equipmentAlarm
        <Polarity> (2)
        "
	::= { pmopm2Almchannel56PortEntry 3 }


pmopm2AlmChannel56AbsentPortn OBJECT-TYPE
	SYNTAX  EkiOnOff
	MAX-ACCESS read-only
	STATUS current
	DESCRIPTION
        "
        Channel Absent 56 :This OID indicates
        that an in service channel is absent
        on the Optical Power Monitoring
        input<Help> This alarm indicates
        that an in service channel is absent
        on the Optical Power Monitoring
        input <Condtype> CHANNEL56_ABSENT_1
        <Probcause> informationMissing
         (65) <Alarmtype> equipmentAlarm
        (5) <Polarity> (2)
        "
	::= { pmopm2Almchannel56PortEntry 2 }


--- *********************************************************
---     TABLE for the pmopm2Almchannel57Port articles
--- *********************************************************

pmopm2Almchannel57PortTable OBJECT-TYPE
	SYNTAX  SEQUENCE OF Pmopm2Almchannel57PortEntry
	MAX-ACCESS not-accessible
	STATUS current
	DESCRIPTION
        "
        List of pmopm2Almchannel57Port
        Article
        "
	::= { pmopm2AlmClientCrit 128 }


pmopm2Almchannel57PortEntry OBJECT-TYPE
	SYNTAX Pmopm2Almchannel57PortEntry
	MAX-ACCESS not-accessible
	STATUS current
	DESCRIPTION
        "
        Row definition for the pmopm2Almchannel57Port
        table
        "
	INDEX   { pmopm2Almchannel57PortIndex }
	::= { pmopm2Almchannel57PortTable 1 }


Pmopm2Almchannel57PortEntry ::=
	SEQUENCE {
	pmopm2Almchannel57PortIndex
		INTEGER,
	pmopm2AlmChannel57OosPortn
		EkiOnOff,
	pmopm2AlmChannel57PowerHighPortn
		EkiOnOff,
	pmopm2AlmChannel57PowerLowPortn
		EkiOnOff,
	pmopm2AlmChannel57BalancedPortn
		EkiOnOff,
	pmopm2AlmChannel57MismatchPortn
		EkiOnOff,
	pmopm2AlmChannel57AbsentPortn
		EkiOnOff
	}


pmopm2Almchannel57PortIndex OBJECT-TYPE
	SYNTAX  INTEGER(0..128)
	MAX-ACCESS  read-only
	STATUS current
	DESCRIPTION
        "
        Index definition for the pmopm2Almchannel57Port
        table
        "
	::= { pmopm2Almchannel57PortEntry 1 }


pmopm2AlmChannel57OosPortn OBJECT-TYPE
	SYNTAX  EkiOnOff
	MAX-ACCESS read-only
	STATUS current
	DESCRIPTION
        "
        Channel Out Of Service 57 :This
        OID indicates that the channel
         is out of service  <Help> This
        alarm indicates that the channel
        is in service <Condtype> CHANNEL57_OOS_1
        <Probcause> informationalStatus(1000)
        <Alarmtype> other (1) <Polarity>
        (2)
        "
	::= { pmopm2Almchannel57PortEntry 7 }


pmopm2AlmChannel57PowerHighPortn OBJECT-TYPE
	SYNTAX  EkiOnOff
	MAX-ACCESS read-only
	STATUS current
	DESCRIPTION
        "
        Channel Power High 57 :This OID
        indicates that the power of the
        channel is higher than the configured
        threshold<Help> This alarm indicates
        that the power of the channel is
        higher than the configured threshold
        <Condtype> CHANNEL57_POWER_HIGH_1
        <Probcause> degradedSignal (13)
        <Alarmtype> equipmentAlarm <Polarity>
        (2)
        "
	::= { pmopm2Almchannel57PortEntry 6 }


pmopm2AlmChannel57PowerLowPortn OBJECT-TYPE
	SYNTAX  EkiOnOff
	MAX-ACCESS read-only
	STATUS current
	DESCRIPTION
        "
        Channel Power Low 57 :This OID
        indicates that the power of the
        channel is lower than the configured
        threshold<Help> This alarm indicates
        that the power of the channel is
        lower than the configured threshold
        <Condtype> CHANNEL57_POWER_LOW_1
        <Probcause> degradedSignal (13)
        <Alarmtype> equipmentAlarm <Polarity>
        (2)
        "
	::= { pmopm2Almchannel57PortEntry 5 }


pmopm2AlmChannel57BalancedPortn OBJECT-TYPE
	SYNTAX  EkiOnOff
	MAX-ACCESS read-only
	STATUS current
	DESCRIPTION
        "
        Channel Balanced 57 :This OID
         indicates that an in service channel
        is balanced by the Ekinops auto
        turn up application<Help> This
         status indicates that an in service
        channel is balanced by the Ekinops
        auto turn up application <Condtype>
        CHANNEL57_BALANCED_1 <Probcause>
        informationalStatus(1000) <Alarmtype>
        other (1) <Polarity> (2)
        "
	::= { pmopm2Almchannel57PortEntry 4 }


pmopm2AlmChannel57MismatchPortn OBJECT-TYPE
	SYNTAX  EkiOnOff
	MAX-ACCESS read-only
	STATUS current
	DESCRIPTION
        "
        Channel Mismatch 57 :This OID
         indicates that an out of service
        channel is detected on the Optical
        Power Monitoring input<Help> This
        alarm indicates that an out of
         service channel is detected on
        the Optical Power Monitoring input
        <Condtype> CHANNEL57_MISMATCH_1
        <Probcause> unexpectedInformation
        (75) <Alarmtype> equipmentAlarm
        <Polarity> (2)
        "
	::= { pmopm2Almchannel57PortEntry 3 }


pmopm2AlmChannel57AbsentPortn OBJECT-TYPE
	SYNTAX  EkiOnOff
	MAX-ACCESS read-only
	STATUS current
	DESCRIPTION
        "
        Channel Absent 57 :This OID indicates
        that an in service channel is absent
        on the Optical Power Monitoring
        input<Help> This alarm indicates
        that an in service channel is absent
        on the Optical Power Monitoring
        input <Condtype> CHANNEL57_ABSENT_1
        <Probcause> informationMissing
         (65) <Alarmtype> equipmentAlarm
        (5) <Polarity> (2)
        "
	::= { pmopm2Almchannel57PortEntry 2 }


--- *********************************************************
---     TABLE for the pmopm2Almchannel58Port articles
--- *********************************************************

pmopm2Almchannel58PortTable OBJECT-TYPE
	SYNTAX  SEQUENCE OF Pmopm2Almchannel58PortEntry
	MAX-ACCESS not-accessible
	STATUS current
	DESCRIPTION
        "
        List of pmopm2Almchannel58Port
        Article
        "
	::= { pmopm2AlmClientCrit 130 }


pmopm2Almchannel58PortEntry OBJECT-TYPE
	SYNTAX Pmopm2Almchannel58PortEntry
	MAX-ACCESS not-accessible
	STATUS current
	DESCRIPTION
        "
        Row definition for the pmopm2Almchannel58Port
        table
        "
	INDEX   { pmopm2Almchannel58PortIndex }
	::= { pmopm2Almchannel58PortTable 1 }


Pmopm2Almchannel58PortEntry ::=
	SEQUENCE {
	pmopm2Almchannel58PortIndex
		INTEGER,
	pmopm2AlmChannel58OosPortn
		EkiOnOff,
	pmopm2AlmChannel58PowerHighPortn
		EkiOnOff,
	pmopm2AlmChannel58PowerLowPortn
		EkiOnOff,
	pmopm2AlmChannel58BalancedPortn
		EkiOnOff,
	pmopm2AlmChannel58MismatchPortn
		EkiOnOff,
	pmopm2AlmChannel58AbsentPortn
		EkiOnOff
	}


pmopm2Almchannel58PortIndex OBJECT-TYPE
	SYNTAX  INTEGER(0..128)
	MAX-ACCESS  read-only
	STATUS current
	DESCRIPTION
        "
        Index definition for the pmopm2Almchannel58Port
        table
        "
	::= { pmopm2Almchannel58PortEntry 1 }


pmopm2AlmChannel58OosPortn OBJECT-TYPE
	SYNTAX  EkiOnOff
	MAX-ACCESS read-only
	STATUS current
	DESCRIPTION
        "
        Channel Out Of Service 58 :This
        OID indicates that the channel
         is out of service  <Help> This
        alarm indicates that the channel
        is in service <Condtype> CHANNEL58_OOS_1
        <Probcause> informationalStatus(1000)
        <Alarmtype> other (1) <Polarity>
        (2)
        "
	::= { pmopm2Almchannel58PortEntry 7 }


pmopm2AlmChannel58PowerHighPortn OBJECT-TYPE
	SYNTAX  EkiOnOff
	MAX-ACCESS read-only
	STATUS current
	DESCRIPTION
        "
        Channel Power High 58 :This OID
        indicates that the power of the
        channel is higher than the configured
        threshold<Help> This alarm indicates
        that the power of the channel is
        higher than the configured threshold
        <Condtype> CHANNEL58_POWER_HIGH_1
        <Probcause> degradedSignal (13)
        <Alarmtype> equipmentAlarm <Polarity>
        (2)
        "
	::= { pmopm2Almchannel58PortEntry 6 }


pmopm2AlmChannel58PowerLowPortn OBJECT-TYPE
	SYNTAX  EkiOnOff
	MAX-ACCESS read-only
	STATUS current
	DESCRIPTION
        "
        Channel Power Low 58 :This OID
        indicates that the power of the
        channel is lower than the configured
        threshold<Help> This alarm indicates
        that the power of the channel is
        lower than the configured threshold
        <Condtype> CHANNEL58_POWER_LOW_1
        <Probcause> degradedSignal (13)
        <Alarmtype> equipmentAlarm <Polarity>
        (2)
        "
	::= { pmopm2Almchannel58PortEntry 5 }


pmopm2AlmChannel58BalancedPortn OBJECT-TYPE
	SYNTAX  EkiOnOff
	MAX-ACCESS read-only
	STATUS current
	DESCRIPTION
        "
        Channel Balanced 58 :This OID
         indicates that an in service channel
        is balanced by the Ekinops auto
        turn up application<Help> This
         status indicates that an in service
        channel is balanced by the Ekinops
        auto turn up application <Condtype>
        CHANNEL58_BALANCED_1 <Probcause>
        informationalStatus(1000) <Alarmtype>
        other (1) <Polarity> (2)
        "
	::= { pmopm2Almchannel58PortEntry 4 }


pmopm2AlmChannel58MismatchPortn OBJECT-TYPE
	SYNTAX  EkiOnOff
	MAX-ACCESS read-only
	STATUS current
	DESCRIPTION
        "
        Channel Mismatch 58 :This OID
         indicates that an out of service
        channel is detected on the Optical
        Power Monitoring input<Help> This
        alarm indicates that an out of
         service channel is detected on
        the Optical Power Monitoring input
        <Condtype> CHANNEL58_MISMATCH_1
        <Probcause> unexpectedInformation
        (75) <Alarmtype> equipmentAlarm
        <Polarity> (2)
        "
	::= { pmopm2Almchannel58PortEntry 3 }


pmopm2AlmChannel58AbsentPortn OBJECT-TYPE
	SYNTAX  EkiOnOff
	MAX-ACCESS read-only
	STATUS current
	DESCRIPTION
        "
        Channel Absent 58 :This OID indicates
        that an in service channel is absent
        on the Optical Power Monitoring
        input<Help> This alarm indicates
        that an in service channel is absent
        on the Optical Power Monitoring
        input <Condtype> CHANNEL58_ABSENT_1
        <Probcause> informationMissing
         (65) <Alarmtype> equipmentAlarm
        (5) <Polarity> (2)
        "
	::= { pmopm2Almchannel58PortEntry 2 }


--- *********************************************************
---     TABLE for the pmopm2Almchannel59Port articles
--- *********************************************************

pmopm2Almchannel59PortTable OBJECT-TYPE
	SYNTAX  SEQUENCE OF Pmopm2Almchannel59PortEntry
	MAX-ACCESS not-accessible
	STATUS current
	DESCRIPTION
        "
        List of pmopm2Almchannel59Port
        Article
        "
	::= { pmopm2AlmClientCrit 132 }


pmopm2Almchannel59PortEntry OBJECT-TYPE
	SYNTAX Pmopm2Almchannel59PortEntry
	MAX-ACCESS not-accessible
	STATUS current
	DESCRIPTION
        "
        Row definition for the pmopm2Almchannel59Port
        table
        "
	INDEX   { pmopm2Almchannel59PortIndex }
	::= { pmopm2Almchannel59PortTable 1 }


Pmopm2Almchannel59PortEntry ::=
	SEQUENCE {
	pmopm2Almchannel59PortIndex
		INTEGER,
	pmopm2AlmChannel59OosPortn
		EkiOnOff,
	pmopm2AlmChannel59PowerHighPortn
		EkiOnOff,
	pmopm2AlmChannel59PowerLowPortn
		EkiOnOff,
	pmopm2AlmChannel59BalancedPortn
		EkiOnOff,
	pmopm2AlmChannel59MismatchPortn
		EkiOnOff,
	pmopm2AlmChannel59AbsentPortn
		EkiOnOff
	}


pmopm2Almchannel59PortIndex OBJECT-TYPE
	SYNTAX  INTEGER(0..128)
	MAX-ACCESS  read-only
	STATUS current
	DESCRIPTION
        "
        Index definition for the pmopm2Almchannel59Port
        table
        "
	::= { pmopm2Almchannel59PortEntry 1 }


pmopm2AlmChannel59OosPortn OBJECT-TYPE
	SYNTAX  EkiOnOff
	MAX-ACCESS read-only
	STATUS current
	DESCRIPTION
        "
        Channel Out Of Service 59 :This
        OID indicates that the channel
         is out of service  <Help> This
        alarm indicates that the channel
        is in service <Condtype> CHANNEL59_OOS_1
        <Probcause> informationalStatus(1000)
        <Alarmtype> other (1) <Polarity>
        (2)
        "
	::= { pmopm2Almchannel59PortEntry 7 }


pmopm2AlmChannel59PowerHighPortn OBJECT-TYPE
	SYNTAX  EkiOnOff
	MAX-ACCESS read-only
	STATUS current
	DESCRIPTION
        "
        Channel Power High 59 :This OID
        indicates that the power of the
        channel is higher than the configured
        threshold<Help> This alarm indicates
        that the power of the channel is
        higher than the configured threshold
        <Condtype> CHANNEL59_POWER_HIGH_1
        <Probcause> degradedSignal (13)
        <Alarmtype> equipmentAlarm <Polarity>
        (2)
        "
	::= { pmopm2Almchannel59PortEntry 6 }


pmopm2AlmChannel59PowerLowPortn OBJECT-TYPE
	SYNTAX  EkiOnOff
	MAX-ACCESS read-only
	STATUS current
	DESCRIPTION
        "
        Channel Power Low 59 :This OID
        indicates that the power of the
        channel is lower than the configured
        threshold<Help> This alarm indicates
        that the power of the channel is
        lower than the configured threshold
        <Condtype> CHANNEL59_POWER_LOW_1
        <Probcause> degradedSignal (13)
        <Alarmtype> equipmentAlarm <Polarity>
        (2)
        "
	::= { pmopm2Almchannel59PortEntry 5 }


pmopm2AlmChannel59BalancedPortn OBJECT-TYPE
	SYNTAX  EkiOnOff
	MAX-ACCESS read-only
	STATUS current
	DESCRIPTION
        "
        Channel Balanced 59 :This OID
         indicates that an in service channel
        is balanced by the Ekinops auto
        turn up application<Help> This
         status indicates that an in service
        channel is balanced by the Ekinops
        auto turn up application <Condtype>
        CHANNEL59_BALANCED_1 <Probcause>
        informationalStatus(1000) <Alarmtype>
        other (1) <Polarity> (2)
        "
	::= { pmopm2Almchannel59PortEntry 4 }


pmopm2AlmChannel59MismatchPortn OBJECT-TYPE
	SYNTAX  EkiOnOff
	MAX-ACCESS read-only
	STATUS current
	DESCRIPTION
        "
        Channel Mismatch 59 :This OID
         indicates that an out of service
        channel is detected on the Optical
        Power Monitoring input<Help> This
        alarm indicates that an out of
         service channel is detected on
        the Optical Power Monitoring input
        <Condtype> CHANNEL59_MISMATCH_1
        <Probcause> unexpectedInformation
        (75) <Alarmtype> equipmentAlarm
        <Polarity> (2)
        "
	::= { pmopm2Almchannel59PortEntry 3 }


pmopm2AlmChannel59AbsentPortn OBJECT-TYPE
	SYNTAX  EkiOnOff
	MAX-ACCESS read-only
	STATUS current
	DESCRIPTION
        "
        Channel Absent 59 :This OID indicates
        that an in service channel is absent
        on the Optical Power Monitoring
        input<Help> This alarm indicates
        that an in service channel is absent
        on the Optical Power Monitoring
        input <Condtype> CHANNEL59_ABSENT_1
        <Probcause> informationMissing
         (65) <Alarmtype> equipmentAlarm
        (5) <Polarity> (2)
        "
	::= { pmopm2Almchannel59PortEntry 2 }


--- *********************************************************
---     TABLE for the pmopm2Almchannel60Port articles
--- *********************************************************

pmopm2Almchannel60PortTable OBJECT-TYPE
	SYNTAX  SEQUENCE OF Pmopm2Almchannel60PortEntry
	MAX-ACCESS not-accessible
	STATUS current
	DESCRIPTION
        "
        List of pmopm2Almchannel60Port
        Article
        "
	::= { pmopm2AlmClientCrit 134 }


pmopm2Almchannel60PortEntry OBJECT-TYPE
	SYNTAX Pmopm2Almchannel60PortEntry
	MAX-ACCESS not-accessible
	STATUS current
	DESCRIPTION
        "
        Row definition for the pmopm2Almchannel60Port
        table
        "
	INDEX   { pmopm2Almchannel60PortIndex }
	::= { pmopm2Almchannel60PortTable 1 }


Pmopm2Almchannel60PortEntry ::=
	SEQUENCE {
	pmopm2Almchannel60PortIndex
		INTEGER,
	pmopm2AlmChannel60OosPortn
		EkiOnOff,
	pmopm2AlmChannel60PowerHighPortn
		EkiOnOff,
	pmopm2AlmChannel60PowerLowPortn
		EkiOnOff,
	pmopm2AlmChannel60BalancedPortn
		EkiOnOff,
	pmopm2AlmChannel60MismatchPortn
		EkiOnOff,
	pmopm2AlmChannel60AbsentPortn
		EkiOnOff
	}


pmopm2Almchannel60PortIndex OBJECT-TYPE
	SYNTAX  INTEGER(0..128)
	MAX-ACCESS  read-only
	STATUS current
	DESCRIPTION
        "
        Index definition for the pmopm2Almchannel60Port
        table
        "
	::= { pmopm2Almchannel60PortEntry 1 }


pmopm2AlmChannel60OosPortn OBJECT-TYPE
	SYNTAX  EkiOnOff
	MAX-ACCESS read-only
	STATUS current
	DESCRIPTION
        "
        Channel Out Of Service 60 :This
        OID indicates that the channel
         is out of service  <Help> This
        alarm indicates that the channel
        is in service <Condtype> CHANNEL60_OOS_1
        <Probcause> informationalStatus(1000)
        <Alarmtype> other (1) <Polarity>
        (2)
        "
	::= { pmopm2Almchannel60PortEntry 7 }


pmopm2AlmChannel60PowerHighPortn OBJECT-TYPE
	SYNTAX  EkiOnOff
	MAX-ACCESS read-only
	STATUS current
	DESCRIPTION
        "
        Channel Power High 60 :This OID
        indicates that the power of the
        channel is higher than the configured
        threshold<Help> This alarm indicates
        that the power of the channel is
        higher than the configured threshold
        <Condtype> CHANNEL60_POWER_HIGH_1
        <Probcause> degradedSignal (13)
        <Alarmtype> equipmentAlarm <Polarity>
        (2)
        "
	::= { pmopm2Almchannel60PortEntry 6 }


pmopm2AlmChannel60PowerLowPortn OBJECT-TYPE
	SYNTAX  EkiOnOff
	MAX-ACCESS read-only
	STATUS current
	DESCRIPTION
        "
        Channel Power Low 60 :This OID
        indicates that the power of the
        channel is lower than the configured
        threshold<Help> This alarm indicates
        that the power of the channel is
        lower than the configured threshold
        <Condtype> CHANNEL60_POWER_LOW_1
        <Probcause> degradedSignal (13)
        <Alarmtype> equipmentAlarm <Polarity>
        (2)
        "
	::= { pmopm2Almchannel60PortEntry 5 }


pmopm2AlmChannel60BalancedPortn OBJECT-TYPE
	SYNTAX  EkiOnOff
	MAX-ACCESS read-only
	STATUS current
	DESCRIPTION
        "
        Channel Balanced 60 :This OID
         indicates that an in service channel
        is balanced by the Ekinops auto
        turn up application<Help> This
         status indicates that an in service
        channel is balanced by the Ekinops
        auto turn up application <Condtype>
        CHANNEL60_BALANCED_1 <Probcause>
        informationalStatus(1000) <Alarmtype>
        other (1) <Polarity> (2)
        "
	::= { pmopm2Almchannel60PortEntry 4 }


pmopm2AlmChannel60MismatchPortn OBJECT-TYPE
	SYNTAX  EkiOnOff
	MAX-ACCESS read-only
	STATUS current
	DESCRIPTION
        "
        Channel Mismatch 60 :This OID
         indicates that an out of service
        channel is detected on the Optical
        Power Monitoring input<Help> This
        alarm indicates that an out of
         service channel is detected on
        the Optical Power Monitoring input
        <Condtype> CHANNEL60_MISMATCH_1
        <Probcause> unexpectedInformation
        (75) <Alarmtype> equipmentAlarm
        <Polarity> (2)
        "
	::= { pmopm2Almchannel60PortEntry 3 }


pmopm2AlmChannel60AbsentPortn OBJECT-TYPE
	SYNTAX  EkiOnOff
	MAX-ACCESS read-only
	STATUS current
	DESCRIPTION
        "
        Channel Absent 60 :This OID indicates
        that an in service channel is absent
        on the Optical Power Monitoring
        input<Help> This alarm indicates
        that an in service channel is absent
        on the Optical Power Monitoring
        input <Condtype> CHANNEL60_ABSENT_1
        <Probcause> informationMissing
         (65) <Alarmtype> equipmentAlarm
        (5) <Polarity> (2)
        "
	::= { pmopm2Almchannel60PortEntry 2 }


--- *********************************************************
---     TABLE for the pmopm2Almchannel61Port articles
--- *********************************************************

pmopm2Almchannel61PortTable OBJECT-TYPE
	SYNTAX  SEQUENCE OF Pmopm2Almchannel61PortEntry
	MAX-ACCESS not-accessible
	STATUS current
	DESCRIPTION
        "
        List of pmopm2Almchannel61Port
        Article
        "
	::= { pmopm2AlmClientCrit 136 }


pmopm2Almchannel61PortEntry OBJECT-TYPE
	SYNTAX Pmopm2Almchannel61PortEntry
	MAX-ACCESS not-accessible
	STATUS current
	DESCRIPTION
        "
        Row definition for the pmopm2Almchannel61Port
        table
        "
	INDEX   { pmopm2Almchannel61PortIndex }
	::= { pmopm2Almchannel61PortTable 1 }


Pmopm2Almchannel61PortEntry ::=
	SEQUENCE {
	pmopm2Almchannel61PortIndex
		INTEGER,
	pmopm2AlmChannel61OosPortn
		EkiOnOff,
	pmopm2AlmChannel61PowerHighPortn
		EkiOnOff,
	pmopm2AlmChannel61PowerLowPortn
		EkiOnOff,
	pmopm2AlmChannel61BalancedPortn
		EkiOnOff,
	pmopm2AlmChannel61MismatchPortn
		EkiOnOff,
	pmopm2AlmChannel61AbsentPortn
		EkiOnOff
	}


pmopm2Almchannel61PortIndex OBJECT-TYPE
	SYNTAX  INTEGER(0..128)
	MAX-ACCESS  read-only
	STATUS current
	DESCRIPTION
        "
        Index definition for the pmopm2Almchannel61Port
        table
        "
	::= { pmopm2Almchannel61PortEntry 1 }


pmopm2AlmChannel61OosPortn OBJECT-TYPE
	SYNTAX  EkiOnOff
	MAX-ACCESS read-only
	STATUS current
	DESCRIPTION
        "
        Channel Out Of Service 61 :This
        OID indicates that the channel
         is out of service  <Help> This
        alarm indicates that the channel
        is in service <Condtype> CHANNEL61_OOS_1
        <Probcause> informationalStatus(1000)
        <Alarmtype> other (1) <Polarity>
        (2)
        "
	::= { pmopm2Almchannel61PortEntry 7 }


pmopm2AlmChannel61PowerHighPortn OBJECT-TYPE
	SYNTAX  EkiOnOff
	MAX-ACCESS read-only
	STATUS current
	DESCRIPTION
        "
        Channel Power High 61 :This OID
        indicates that the power of the
        channel is higher than the configured
        threshold<Help> This alarm indicates
        that the power of the channel is
        higher than the configured threshold
        <Condtype> CHANNEL61_POWER_HIGH_1
        <Probcause> degradedSignal (13)
        <Alarmtype> equipmentAlarm <Polarity>
        (2)
        "
	::= { pmopm2Almchannel61PortEntry 6 }


pmopm2AlmChannel61PowerLowPortn OBJECT-TYPE
	SYNTAX  EkiOnOff
	MAX-ACCESS read-only
	STATUS current
	DESCRIPTION
        "
        Channel Power Low 61 :This OID
        indicates that the power of the
        channel is lower than the configured
        threshold<Help> This alarm indicates
        that the power of the channel is
        lower than the configured threshold
        <Condtype> CHANNEL61_POWER_LOW_1
        <Probcause> degradedSignal (13)
        <Alarmtype> equipmentAlarm <Polarity>
        (2)
        "
	::= { pmopm2Almchannel61PortEntry 5 }


pmopm2AlmChannel61BalancedPortn OBJECT-TYPE
	SYNTAX  EkiOnOff
	MAX-ACCESS read-only
	STATUS current
	DESCRIPTION
        "
        Channel Balanced 61 :This OID
         indicates that an in service channel
        is balanced by the Ekinops auto
        turn up application<Help> This
         status indicates that an in service
        channel is balanced by the Ekinops
        auto turn up application <Condtype>
        CHANNEL61_BALANCED_1 <Probcause>
        informationalStatus(1000) <Alarmtype>
        other (1) <Polarity> (2)
        "
	::= { pmopm2Almchannel61PortEntry 4 }


pmopm2AlmChannel61MismatchPortn OBJECT-TYPE
	SYNTAX  EkiOnOff
	MAX-ACCESS read-only
	STATUS current
	DESCRIPTION
        "
        Channel Mismatch 61 :This OID
         indicates that an out of service
        channel is detected on the Optical
        Power Monitoring input<Help> This
        alarm indicates that an out of
         service channel is detected on
        the Optical Power Monitoring input
        <Condtype> CHANNEL61_MISMATCH_1
        <Probcause> unexpectedInformation
        (75) <Alarmtype> equipmentAlarm
        <Polarity> (2)
        "
	::= { pmopm2Almchannel61PortEntry 3 }


pmopm2AlmChannel61AbsentPortn OBJECT-TYPE
	SYNTAX  EkiOnOff
	MAX-ACCESS read-only
	STATUS current
	DESCRIPTION
        "
        Channel Absent 61 :This OID indicates
        that an in service channel is absent
        on the Optical Power Monitoring
        input<Help> This alarm indicates
        that an in service channel is absent
        on the Optical Power Monitoring
        input <Condtype> CHANNEL61_ABSENT_1
        <Probcause> informationMissing
         (65) <Alarmtype> equipmentAlarm
        (5) <Polarity> (2)
        "
	::= { pmopm2Almchannel61PortEntry 2 }


--- *********************************************************
---     TABLE for the pmopm2Almchannel62Port articles
--- *********************************************************

pmopm2Almchannel62PortTable OBJECT-TYPE
	SYNTAX  SEQUENCE OF Pmopm2Almchannel62PortEntry
	MAX-ACCESS not-accessible
	STATUS current
	DESCRIPTION
        "
        List of pmopm2Almchannel62Port
        Article
        "
	::= { pmopm2AlmClientCrit 138 }


pmopm2Almchannel62PortEntry OBJECT-TYPE
	SYNTAX Pmopm2Almchannel62PortEntry
	MAX-ACCESS not-accessible
	STATUS current
	DESCRIPTION
        "
        Row definition for the pmopm2Almchannel62Port
        table
        "
	INDEX   { pmopm2Almchannel62PortIndex }
	::= { pmopm2Almchannel62PortTable 1 }


Pmopm2Almchannel62PortEntry ::=
	SEQUENCE {
	pmopm2Almchannel62PortIndex
		INTEGER,
	pmopm2AlmChannel62OosPortn
		EkiOnOff,
	pmopm2AlmChannel62PowerHighPortn
		EkiOnOff,
	pmopm2AlmChannel62PowerLowPortn
		EkiOnOff,
	pmopm2AlmChannel62BalancedPortn
		EkiOnOff,
	pmopm2AlmChannel62MismatchPortn
		EkiOnOff,
	pmopm2AlmChannel62AbsentPortn
		EkiOnOff
	}


pmopm2Almchannel62PortIndex OBJECT-TYPE
	SYNTAX  INTEGER(0..128)
	MAX-ACCESS  read-only
	STATUS current
	DESCRIPTION
        "
        Index definition for the pmopm2Almchannel62Port
        table
        "
	::= { pmopm2Almchannel62PortEntry 1 }


pmopm2AlmChannel62OosPortn OBJECT-TYPE
	SYNTAX  EkiOnOff
	MAX-ACCESS read-only
	STATUS current
	DESCRIPTION
        "
        Channel Out Of Service 62 :This
        OID indicates that the channel
         is out of service  <Help> This
        alarm indicates that the channel
        is in service <Condtype> CHANNEL62_OOS_1
        <Probcause> informationalStatus(1000)
        <Alarmtype> other (1) <Polarity>
        (2)
        "
	::= { pmopm2Almchannel62PortEntry 7 }


pmopm2AlmChannel62PowerHighPortn OBJECT-TYPE
	SYNTAX  EkiOnOff
	MAX-ACCESS read-only
	STATUS current
	DESCRIPTION
        "
        Channel Power High 62 :This OID
        indicates that the power of the
        channel is higher than the configured
        threshold<Help> This alarm indicates
        that the power of the channel is
        higher than the configured threshold
        <Condtype> CHANNEL62_POWER_HIGH_1
        <Probcause> degradedSignal (13)
        <Alarmtype> equipmentAlarm <Polarity>
        (2)
        "
	::= { pmopm2Almchannel62PortEntry 6 }


pmopm2AlmChannel62PowerLowPortn OBJECT-TYPE
	SYNTAX  EkiOnOff
	MAX-ACCESS read-only
	STATUS current
	DESCRIPTION
        "
        Channel Power Low 62 :This OID
        indicates that the power of the
        channel is lower than the configured
        threshold<Help> This alarm indicates
        that the power of the channel is
        lower than the configured threshold
        <Condtype> CHANNEL62_POWER_LOW_1
        <Probcause> degradedSignal (13)
        <Alarmtype> equipmentAlarm <Polarity>
        (2)
        "
	::= { pmopm2Almchannel62PortEntry 5 }


pmopm2AlmChannel62BalancedPortn OBJECT-TYPE
	SYNTAX  EkiOnOff
	MAX-ACCESS read-only
	STATUS current
	DESCRIPTION
        "
        Channel Balanced 62 :This OID
         indicates that an in service channel
        is balanced by the Ekinops auto
        turn up application<Help> This
         status indicates that an in service
        channel is balanced by the Ekinops
        auto turn up application <Condtype>
        CHANNEL62_BALANCED_1 <Probcause>
        informationalStatus(1000) <Alarmtype>
        other (1) <Polarity> (2)
        "
	::= { pmopm2Almchannel62PortEntry 4 }


pmopm2AlmChannel62MismatchPortn OBJECT-TYPE
	SYNTAX  EkiOnOff
	MAX-ACCESS read-only
	STATUS current
	DESCRIPTION
        "
        Channel Mismatch 62 :This OID
         indicates that an out of service
        channel is detected on the Optical
        Power Monitoring input<Help> This
        alarm indicates that an out of
         service channel is detected on
        the Optical Power Monitoring input
        <Condtype> CHANNEL62_MISMATCH_1
        <Probcause> unexpectedInformation
        (75) <Alarmtype> equipmentAlarm
        <Polarity> (2)
        "
	::= { pmopm2Almchannel62PortEntry 3 }


pmopm2AlmChannel62AbsentPortn OBJECT-TYPE
	SYNTAX  EkiOnOff
	MAX-ACCESS read-only
	STATUS current
	DESCRIPTION
        "
        Channel Absent 62 :This OID indicates
        that an in service channel is absent
        on the Optical Power Monitoring
        input<Help> This alarm indicates
        that an in service channel is absent
        on the Optical Power Monitoring
        input <Condtype> CHANNEL62_ABSENT_1
        <Probcause> informationMissing
         (65) <Alarmtype> equipmentAlarm
        (5) <Polarity> (2)
        "
	::= { pmopm2Almchannel62PortEntry 2 }


--- *********************************************************
---     TABLE for the pmopm2Almchannel63Port articles
--- *********************************************************

pmopm2Almchannel63PortTable OBJECT-TYPE
	SYNTAX  SEQUENCE OF Pmopm2Almchannel63PortEntry
	MAX-ACCESS not-accessible
	STATUS current
	DESCRIPTION
        "
        List of pmopm2Almchannel63Port
        Article
        "
	::= { pmopm2AlmClientCrit 140 }


pmopm2Almchannel63PortEntry OBJECT-TYPE
	SYNTAX Pmopm2Almchannel63PortEntry
	MAX-ACCESS not-accessible
	STATUS current
	DESCRIPTION
        "
        Row definition for the pmopm2Almchannel63Port
        table
        "
	INDEX   { pmopm2Almchannel63PortIndex }
	::= { pmopm2Almchannel63PortTable 1 }


Pmopm2Almchannel63PortEntry ::=
	SEQUENCE {
	pmopm2Almchannel63PortIndex
		INTEGER,
	pmopm2AlmChannel63OosPortn
		EkiOnOff,
	pmopm2AlmChannel63PowerHighPortn
		EkiOnOff,
	pmopm2AlmChannel63PowerLowPortn
		EkiOnOff,
	pmopm2AlmChannel63BalancedPortn
		EkiOnOff,
	pmopm2AlmChannel63MismatchPortn
		EkiOnOff,
	pmopm2AlmChannel63AbsentPortn
		EkiOnOff
	}


pmopm2Almchannel63PortIndex OBJECT-TYPE
	SYNTAX  INTEGER(0..128)
	MAX-ACCESS  read-only
	STATUS current
	DESCRIPTION
        "
        Index definition for the pmopm2Almchannel63Port
        table
        "
	::= { pmopm2Almchannel63PortEntry 1 }


pmopm2AlmChannel63OosPortn OBJECT-TYPE
	SYNTAX  EkiOnOff
	MAX-ACCESS read-only
	STATUS current
	DESCRIPTION
        "
        Channel Out Of Service 63 :This
        OID indicates that the channel
         is out of service  <Help> This
        alarm indicates that the channel
        is in service <Condtype> CHANNEL63_OOS_1
        <Probcause> informationalStatus(1000)
        <Alarmtype> other (1) <Polarity>
        (2)
        "
	::= { pmopm2Almchannel63PortEntry 7 }


pmopm2AlmChannel63PowerHighPortn OBJECT-TYPE
	SYNTAX  EkiOnOff
	MAX-ACCESS read-only
	STATUS current
	DESCRIPTION
        "
        Channel Power High 63 :This OID
        indicates that the power of the
        channel is higher than the configured
        threshold<Help> This alarm indicates
        that the power of the channel is
        higher than the configured threshold
        <Condtype> CHANNEL63_POWER_HIGH_1
        <Probcause> degradedSignal (13)
        <Alarmtype> equipmentAlarm <Polarity>
        (2)
        "
	::= { pmopm2Almchannel63PortEntry 6 }


pmopm2AlmChannel63PowerLowPortn OBJECT-TYPE
	SYNTAX  EkiOnOff
	MAX-ACCESS read-only
	STATUS current
	DESCRIPTION
        "
        Channel Power Low 63 :This OID
        indicates that the power of the
        channel is lower than the configured
        threshold<Help> This alarm indicates
        that the power of the channel is
        lower than the configured threshold
        <Condtype> CHANNEL63_POWER_LOW_1
        <Probcause> degradedSignal (13)
        <Alarmtype> equipmentAlarm <Polarity>
        (2)
        "
	::= { pmopm2Almchannel63PortEntry 5 }


pmopm2AlmChannel63BalancedPortn OBJECT-TYPE
	SYNTAX  EkiOnOff
	MAX-ACCESS read-only
	STATUS current
	DESCRIPTION
        "
        Channel Balanced 63 :This OID
         indicates that an in service channel
        is balanced by the Ekinops auto
        turn up application<Help> This
         status indicates that an in service
        channel is balanced by the Ekinops
        auto turn up application <Condtype>
        CHANNEL63_BALANCED_1 <Probcause>
        informationalStatus(1000) <Alarmtype>
        other (1) <Polarity> (2)
        "
	::= { pmopm2Almchannel63PortEntry 4 }


pmopm2AlmChannel63MismatchPortn OBJECT-TYPE
	SYNTAX  EkiOnOff
	MAX-ACCESS read-only
	STATUS current
	DESCRIPTION
        "
        Channel Mismatch 63 :This OID
         indicates that an out of service
        channel is detected on the Optical
        Power Monitoring input<Help> This
        alarm indicates that an out of
         service channel is detected on
        the Optical Power Monitoring input
        <Condtype> CHANNEL63_MISMATCH_1
        <Probcause> unexpectedInformation
        (75) <Alarmtype> equipmentAlarm
        <Polarity> (2)
        "
	::= { pmopm2Almchannel63PortEntry 3 }


pmopm2AlmChannel63AbsentPortn OBJECT-TYPE
	SYNTAX  EkiOnOff
	MAX-ACCESS read-only
	STATUS current
	DESCRIPTION
        "
        Channel Absent 63 :This OID indicates
        that an in service channel is absent
        on the Optical Power Monitoring
        input<Help> This alarm indicates
        that an in service channel is absent
        on the Optical Power Monitoring
        input <Condtype> CHANNEL63_ABSENT_1
        <Probcause> informationMissing
         (65) <Alarmtype> equipmentAlarm
        (5) <Polarity> (2)
        "
	::= { pmopm2Almchannel63PortEntry 2 }


--- *********************************************************
---     TABLE for the pmopm2Almchannel64Port articles
--- *********************************************************

pmopm2Almchannel64PortTable OBJECT-TYPE
	SYNTAX  SEQUENCE OF Pmopm2Almchannel64PortEntry
	MAX-ACCESS not-accessible
	STATUS current
	DESCRIPTION
        "
        List of pmopm2Almchannel64Port
        Article
        "
	::= { pmopm2AlmClientCrit 142 }


pmopm2Almchannel64PortEntry OBJECT-TYPE
	SYNTAX Pmopm2Almchannel64PortEntry
	MAX-ACCESS not-accessible
	STATUS current
	DESCRIPTION
        "
        Row definition for the pmopm2Almchannel64Port
        table
        "
	INDEX   { pmopm2Almchannel64PortIndex }
	::= { pmopm2Almchannel64PortTable 1 }


Pmopm2Almchannel64PortEntry ::=
	SEQUENCE {
	pmopm2Almchannel64PortIndex
		INTEGER,
	pmopm2AlmChannel64OosPortn
		EkiOnOff,
	pmopm2AlmChannel64PowerHighPortn
		EkiOnOff,
	pmopm2AlmChannel64PowerLowPortn
		EkiOnOff,
	pmopm2AlmChannel64BalancedPortn
		EkiOnOff,
	pmopm2AlmChannel64MismatchPortn
		EkiOnOff,
	pmopm2AlmChannel64AbsentPortn
		EkiOnOff
	}


pmopm2Almchannel64PortIndex OBJECT-TYPE
	SYNTAX  INTEGER(0..128)
	MAX-ACCESS  read-only
	STATUS current
	DESCRIPTION
        "
        Index definition for the pmopm2Almchannel64Port
        table
        "
	::= { pmopm2Almchannel64PortEntry 1 }


pmopm2AlmChannel64OosPortn OBJECT-TYPE
	SYNTAX  EkiOnOff
	MAX-ACCESS read-only
	STATUS current
	DESCRIPTION
        "
        Channel Out Of Service 64 :This
        OID indicates that the channel
         is out of service  <Help> This
        alarm indicates that the channel
        is in service <Condtype> CHANNEL64_OOS_1
        <Probcause> informationalStatus(1000)
        <Alarmtype> other (1) <Polarity>
        (2)
        "
	::= { pmopm2Almchannel64PortEntry 7 }


pmopm2AlmChannel64PowerHighPortn OBJECT-TYPE
	SYNTAX  EkiOnOff
	MAX-ACCESS read-only
	STATUS current
	DESCRIPTION
        "
        Channel Power High 64 :This OID
        indicates that the power of the
        channel is higher than the configured
        threshold<Help> This alarm indicates
        that the power of the channel is
        higher than the configured threshold
        <Condtype> CHANNEL64_POWER_HIGH_1
        <Probcause> degradedSignal (13)
        <Alarmtype> equipmentAlarm <Polarity>
        (2)
        "
	::= { pmopm2Almchannel64PortEntry 6 }


pmopm2AlmChannel64PowerLowPortn OBJECT-TYPE
	SYNTAX  EkiOnOff
	MAX-ACCESS read-only
	STATUS current
	DESCRIPTION
        "
        Channel Power Low 64 :This OID
        indicates that the power of the
        channel is lower than the configured
        threshold<Help> This alarm indicates
        that the power of the channel is
        lower than the configured threshold
        <Condtype> CHANNEL64_POWER_LOW_1
        <Probcause> degradedSignal (13)
        <Alarmtype> equipmentAlarm <Polarity>
        (2)
        "
	::= { pmopm2Almchannel64PortEntry 5 }


pmopm2AlmChannel64BalancedPortn OBJECT-TYPE
	SYNTAX  EkiOnOff
	MAX-ACCESS read-only
	STATUS current
	DESCRIPTION
        "
        Channel Balanced 64 :This OID
         indicates that an in service channel
        is balanced by the Ekinops auto
        turn up application<Help> This
         status indicates that an in service
        channel is balanced by the Ekinops
        auto turn up application <Condtype>
        CHANNEL64_BALANCED_1 <Probcause>
        informationalStatus(1000) <Alarmtype>
        other (1) <Polarity> (2)
        "
	::= { pmopm2Almchannel64PortEntry 4 }


pmopm2AlmChannel64MismatchPortn OBJECT-TYPE
	SYNTAX  EkiOnOff
	MAX-ACCESS read-only
	STATUS current
	DESCRIPTION
        "
        Channel Mismatch 64 :This OID
         indicates that an out of service
        channel is detected on the Optical
        Power Monitoring input<Help> This
        alarm indicates that an out of
         service channel is detected on
        the Optical Power Monitoring input
        <Condtype> CHANNEL64_MISMATCH_1
        <Probcause> unexpectedInformation
        (75) <Alarmtype> equipmentAlarm
        <Polarity> (2)
        "
	::= { pmopm2Almchannel64PortEntry 3 }


pmopm2AlmChannel64AbsentPortn OBJECT-TYPE
	SYNTAX  EkiOnOff
	MAX-ACCESS read-only
	STATUS current
	DESCRIPTION
        "
        Channel Absent 64 :This OID indicates
        that an in service channel is absent
        on the Optical Power Monitoring
        input<Help> This alarm indicates
        that an in service channel is absent
        on the Optical Power Monitoring
        input <Condtype> CHANNEL64_ABSENT_1
        <Probcause> informationMissing
         (65) <Alarmtype> equipmentAlarm
        (5) <Polarity> (2)
        "
	::= { pmopm2Almchannel64PortEntry 2 }


--- *********************************************************
---     TABLE for the pmopm2Almchannel65Port articles
--- *********************************************************

pmopm2Almchannel65PortTable OBJECT-TYPE
	SYNTAX  SEQUENCE OF Pmopm2Almchannel65PortEntry
	MAX-ACCESS not-accessible
	STATUS current
	DESCRIPTION
        "
        List of pmopm2Almchannel65Port
        Article
        "
	::= { pmopm2AlmClientCrit 144 }


pmopm2Almchannel65PortEntry OBJECT-TYPE
	SYNTAX Pmopm2Almchannel65PortEntry
	MAX-ACCESS not-accessible
	STATUS current
	DESCRIPTION
        "
        Row definition for the pmopm2Almchannel65Port
        table
        "
	INDEX   { pmopm2Almchannel65PortIndex }
	::= { pmopm2Almchannel65PortTable 1 }


Pmopm2Almchannel65PortEntry ::=
	SEQUENCE {
	pmopm2Almchannel65PortIndex
		INTEGER,
	pmopm2AlmChannel65OosPortn
		EkiOnOff,
	pmopm2AlmChannel65PowerHighPortn
		EkiOnOff,
	pmopm2AlmChannel65PowerLowPortn
		EkiOnOff,
	pmopm2AlmChannel65BalancedPortn
		EkiOnOff,
	pmopm2AlmChannel65MismatchPortn
		EkiOnOff,
	pmopm2AlmChannel65AbsentPortn
		EkiOnOff
	}


pmopm2Almchannel65PortIndex OBJECT-TYPE
	SYNTAX  INTEGER(0..128)
	MAX-ACCESS  read-only
	STATUS current
	DESCRIPTION
        "
        Index definition for the pmopm2Almchannel65Port
        table
        "
	::= { pmopm2Almchannel65PortEntry 1 }


pmopm2AlmChannel65OosPortn OBJECT-TYPE
	SYNTAX  EkiOnOff
	MAX-ACCESS read-only
	STATUS current
	DESCRIPTION
        "
        Channel Out Of Service 65 :This
        OID indicates that the channel
         is out of service  <Help> This
        alarm indicates that the channel
        is in service <Condtype> CHANNEL65_OOS_1
        <Probcause> informationalStatus(1000)
        <Alarmtype> other (1) <Polarity>
        (2)
        "
	::= { pmopm2Almchannel65PortEntry 7 }


pmopm2AlmChannel65PowerHighPortn OBJECT-TYPE
	SYNTAX  EkiOnOff
	MAX-ACCESS read-only
	STATUS current
	DESCRIPTION
        "
        Channel Power High 65 :This OID
        indicates that the power of the
        channel is higher than the configured
        threshold<Help> This alarm indicates
        that the power of the channel is
        higher than the configured threshold
        <Condtype> CHANNEL65_POWER_HIGH_1
        <Probcause> degradedSignal (13)
        <Alarmtype> equipmentAlarm <Polarity>
        (2)
        "
	::= { pmopm2Almchannel65PortEntry 6 }


pmopm2AlmChannel65PowerLowPortn OBJECT-TYPE
	SYNTAX  EkiOnOff
	MAX-ACCESS read-only
	STATUS current
	DESCRIPTION
        "
        Channel Power Low 65 :This OID
        indicates that the power of the
        channel is lower than the configured
        threshold<Help> This alarm indicates
        that the power of the channel is
        lower than the configured threshold
        <Condtype> CHANNEL65_POWER_LOW_1
        <Probcause> degradedSignal (13)
        <Alarmtype> equipmentAlarm <Polarity>
        (2)
        "
	::= { pmopm2Almchannel65PortEntry 5 }


pmopm2AlmChannel65BalancedPortn OBJECT-TYPE
	SYNTAX  EkiOnOff
	MAX-ACCESS read-only
	STATUS current
	DESCRIPTION
        "
        Channel Balanced 65 :This OID
         indicates that an in service channel
        is balanced by the Ekinops auto
        turn up application<Help> This
         status indicates that an in service
        channel is balanced by the Ekinops
        auto turn up application <Condtype>
        CHANNEL65_BALANCED_1 <Probcause>
        informationalStatus(1000) <Alarmtype>
        other (1) <Polarity> (2)
        "
	::= { pmopm2Almchannel65PortEntry 4 }


pmopm2AlmChannel65MismatchPortn OBJECT-TYPE
	SYNTAX  EkiOnOff
	MAX-ACCESS read-only
	STATUS current
	DESCRIPTION
        "
        Channel Mismatch 65 :This OID
         indicates that an out of service
        channel is detected on the Optical
        Power Monitoring input<Help> This
        alarm indicates that an out of
         service channel is detected on
        the Optical Power Monitoring input
        <Condtype> CHANNEL65_MISMATCH_1
        <Probcause> unexpectedInformation
        (75) <Alarmtype> equipmentAlarm
        <Polarity> (2)
        "
	::= { pmopm2Almchannel65PortEntry 3 }


pmopm2AlmChannel65AbsentPortn OBJECT-TYPE
	SYNTAX  EkiOnOff
	MAX-ACCESS read-only
	STATUS current
	DESCRIPTION
        "
        Channel Absent 65 :This OID indicates
        that an in service channel is absent
        on the Optical Power Monitoring
        input<Help> This alarm indicates
        that an in service channel is absent
        on the Optical Power Monitoring
        input <Condtype> CHANNEL65_ABSENT_1
        <Probcause> informationMissing
         (65) <Alarmtype> equipmentAlarm
        (5) <Polarity> (2)
        "
	::= { pmopm2Almchannel65PortEntry 2 }


--- *********************************************************
---     TABLE for the pmopm2Almchannel66Port articles
--- *********************************************************

pmopm2Almchannel66PortTable OBJECT-TYPE
	SYNTAX  SEQUENCE OF Pmopm2Almchannel66PortEntry
	MAX-ACCESS not-accessible
	STATUS current
	DESCRIPTION
        "
        List of pmopm2Almchannel66Port
        Article
        "
	::= { pmopm2AlmClientCrit 146 }


pmopm2Almchannel66PortEntry OBJECT-TYPE
	SYNTAX Pmopm2Almchannel66PortEntry
	MAX-ACCESS not-accessible
	STATUS current
	DESCRIPTION
        "
        Row definition for the pmopm2Almchannel66Port
        table
        "
	INDEX   { pmopm2Almchannel66PortIndex }
	::= { pmopm2Almchannel66PortTable 1 }


Pmopm2Almchannel66PortEntry ::=
	SEQUENCE {
	pmopm2Almchannel66PortIndex
		INTEGER,
	pmopm2AlmChannel66OosPortn
		EkiOnOff,
	pmopm2AlmChannel66PowerHighPortn
		EkiOnOff,
	pmopm2AlmChannel66PowerLowPortn
		EkiOnOff,
	pmopm2AlmChannel66BalancedPortn
		EkiOnOff,
	pmopm2AlmChannel66MismatchPortn
		EkiOnOff,
	pmopm2AlmChannel66AbsentPortn
		EkiOnOff
	}


pmopm2Almchannel66PortIndex OBJECT-TYPE
	SYNTAX  INTEGER(0..128)
	MAX-ACCESS  read-only
	STATUS current
	DESCRIPTION
        "
        Index definition for the pmopm2Almchannel66Port
        table
        "
	::= { pmopm2Almchannel66PortEntry 1 }


pmopm2AlmChannel66OosPortn OBJECT-TYPE
	SYNTAX  EkiOnOff
	MAX-ACCESS read-only
	STATUS current
	DESCRIPTION
        "
        Channel Out Of Service 66 :This
        OID indicates that the channel
         is out of service  <Help> This
        alarm indicates that the channel
        is in service <Condtype> CHANNEL66_OOS_1
        <Probcause> informationalStatus(1000)
        <Alarmtype> other (1) <Polarity>
        (2)
        "
	::= { pmopm2Almchannel66PortEntry 7 }


pmopm2AlmChannel66PowerHighPortn OBJECT-TYPE
	SYNTAX  EkiOnOff
	MAX-ACCESS read-only
	STATUS current
	DESCRIPTION
        "
        Channel Power High 66 :This OID
        indicates that the power of the
        channel is higher than the configured
        threshold<Help> This alarm indicates
        that the power of the channel is
        higher than the configured threshold
        <Condtype> CHANNEL66_POWER_HIGH_1
        <Probcause> degradedSignal (13)
        <Alarmtype> equipmentAlarm <Polarity>
        (2)
        "
	::= { pmopm2Almchannel66PortEntry 6 }


pmopm2AlmChannel66PowerLowPortn OBJECT-TYPE
	SYNTAX  EkiOnOff
	MAX-ACCESS read-only
	STATUS current
	DESCRIPTION
        "
        Channel Power Low 66 :This OID
        indicates that the power of the
        channel is lower than the configured
        threshold<Help> This alarm indicates
        that the power of the channel is
        lower than the configured threshold
        <Condtype> CHANNEL66_POWER_LOW_1
        <Probcause> degradedSignal (13)
        <Alarmtype> equipmentAlarm <Polarity>
        (2)
        "
	::= { pmopm2Almchannel66PortEntry 5 }


pmopm2AlmChannel66BalancedPortn OBJECT-TYPE
	SYNTAX  EkiOnOff
	MAX-ACCESS read-only
	STATUS current
	DESCRIPTION
        "
        Channel Balanced 66 :This OID
         indicates that an in service channel
        is balanced by the Ekinops auto
        turn up application<Help> This
         status indicates that an in service
        channel is balanced by the Ekinops
        auto turn up application <Condtype>
        CHANNEL66_BALANCED_1 <Probcause>
        informationalStatus(1000) <Alarmtype>
        other (1) <Polarity> (2)
        "
	::= { pmopm2Almchannel66PortEntry 4 }


pmopm2AlmChannel66MismatchPortn OBJECT-TYPE
	SYNTAX  EkiOnOff
	MAX-ACCESS read-only
	STATUS current
	DESCRIPTION
        "
        Channel Mismatch 66 :This OID
         indicates that an out of service
        channel is detected on the Optical
        Power Monitoring input<Help> This
        alarm indicates that an out of
         service channel is detected on
        the Optical Power Monitoring input
        <Condtype> CHANNEL66_MISMATCH_1
        <Probcause> unexpectedInformation
        (75) <Alarmtype> equipmentAlarm
        <Polarity> (2)
        "
	::= { pmopm2Almchannel66PortEntry 3 }


pmopm2AlmChannel66AbsentPortn OBJECT-TYPE
	SYNTAX  EkiOnOff
	MAX-ACCESS read-only
	STATUS current
	DESCRIPTION
        "
        Channel Absent 66 :This OID indicates
        that an in service channel is absent
        on the Optical Power Monitoring
        input<Help> This alarm indicates
        that an in service channel is absent
        on the Optical Power Monitoring
        input <Condtype> CHANNEL66_ABSENT_1
        <Probcause> informationMissing
         (65) <Alarmtype> equipmentAlarm
        (5) <Polarity> (2)
        "
	::= { pmopm2Almchannel66PortEntry 2 }


--- *********************************************************
---     TABLE for the pmopm2Almchannel67Port articles
--- *********************************************************

pmopm2Almchannel67PortTable OBJECT-TYPE
	SYNTAX  SEQUENCE OF Pmopm2Almchannel67PortEntry
	MAX-ACCESS not-accessible
	STATUS current
	DESCRIPTION
        "
        List of pmopm2Almchannel67Port
        Article
        "
	::= { pmopm2AlmClientCrit 148 }


pmopm2Almchannel67PortEntry OBJECT-TYPE
	SYNTAX Pmopm2Almchannel67PortEntry
	MAX-ACCESS not-accessible
	STATUS current
	DESCRIPTION
        "
        Row definition for the pmopm2Almchannel67Port
        table
        "
	INDEX   { pmopm2Almchannel67PortIndex }
	::= { pmopm2Almchannel67PortTable 1 }


Pmopm2Almchannel67PortEntry ::=
	SEQUENCE {
	pmopm2Almchannel67PortIndex
		INTEGER,
	pmopm2AlmChannel67OosPortn
		EkiOnOff,
	pmopm2AlmChannel67PowerHighPortn
		EkiOnOff,
	pmopm2AlmChannel67PowerLowPortn
		EkiOnOff,
	pmopm2AlmChannel67BalancedPortn
		EkiOnOff,
	pmopm2AlmChannel67MismatchPortn
		EkiOnOff,
	pmopm2AlmChannel67AbsentPortn
		EkiOnOff
	}


pmopm2Almchannel67PortIndex OBJECT-TYPE
	SYNTAX  INTEGER(0..128)
	MAX-ACCESS  read-only
	STATUS current
	DESCRIPTION
        "
        Index definition for the pmopm2Almchannel67Port
        table
        "
	::= { pmopm2Almchannel67PortEntry 1 }


pmopm2AlmChannel67OosPortn OBJECT-TYPE
	SYNTAX  EkiOnOff
	MAX-ACCESS read-only
	STATUS current
	DESCRIPTION
        "
        Channel Out Of Service 67 :This
        OID indicates that the channel
         is out of service  <Help> This
        alarm indicates that the channel
        is in service <Condtype> CHANNEL67_OOS_1
        <Probcause> informationalStatus(1000)
        <Alarmtype> other (1) <Polarity>
        (2)
        "
	::= { pmopm2Almchannel67PortEntry 7 }


pmopm2AlmChannel67PowerHighPortn OBJECT-TYPE
	SYNTAX  EkiOnOff
	MAX-ACCESS read-only
	STATUS current
	DESCRIPTION
        "
        Channel Power High 67 :This OID
        indicates that the power of the
        channel is higher than the configured
        threshold<Help> This alarm indicates
        that the power of the channel is
        higher than the configured threshold
        <Condtype> CHANNEL67_POWER_HIGH_1
        <Probcause> degradedSignal (13)
        <Alarmtype> equipmentAlarm <Polarity>
        (2)
        "
	::= { pmopm2Almchannel67PortEntry 6 }


pmopm2AlmChannel67PowerLowPortn OBJECT-TYPE
	SYNTAX  EkiOnOff
	MAX-ACCESS read-only
	STATUS current
	DESCRIPTION
        "
        Channel Power Low 67 :This OID
        indicates that the power of the
        channel is lower than the configured
        threshold<Help> This alarm indicates
        that the power of the channel is
        lower than the configured threshold
        <Condtype> CHANNEL67_POWER_LOW_1
        <Probcause> degradedSignal (13)
        <Alarmtype> equipmentAlarm <Polarity>
        (2)
        "
	::= { pmopm2Almchannel67PortEntry 5 }


pmopm2AlmChannel67BalancedPortn OBJECT-TYPE
	SYNTAX  EkiOnOff
	MAX-ACCESS read-only
	STATUS current
	DESCRIPTION
        "
        Channel Balanced 67 :This OID
         indicates that an in service channel
        is balanced by the Ekinops auto
        turn up application<Help> This
         status indicates that an in service
        channel is balanced by the Ekinops
        auto turn up application <Condtype>
        CHANNEL67_BALANCED_1 <Probcause>
        informationalStatus(1000) <Alarmtype>
        other (1) <Polarity> (2)
        "
	::= { pmopm2Almchannel67PortEntry 4 }


pmopm2AlmChannel67MismatchPortn OBJECT-TYPE
	SYNTAX  EkiOnOff
	MAX-ACCESS read-only
	STATUS current
	DESCRIPTION
        "
        Channel Mismatch 67 :This OID
         indicates that an out of service
        channel is detected on the Optical
        Power Monitoring input<Help> This
        alarm indicates that an out of
         service channel is detected on
        the Optical Power Monitoring input
        <Condtype> CHANNEL67_MISMATCH_1
        <Probcause> unexpectedInformation
        (75) <Alarmtype> equipmentAlarm
        <Polarity> (2)
        "
	::= { pmopm2Almchannel67PortEntry 3 }


pmopm2AlmChannel67AbsentPortn OBJECT-TYPE
	SYNTAX  EkiOnOff
	MAX-ACCESS read-only
	STATUS current
	DESCRIPTION
        "
        Channel Absent 67 :This OID indicates
        that an in service channel is absent
        on the Optical Power Monitoring
        input<Help> This alarm indicates
        that an in service channel is absent
        on the Optical Power Monitoring
        input <Condtype> CHANNEL67_ABSENT_1
        <Probcause> informationMissing
         (65) <Alarmtype> equipmentAlarm
        (5) <Polarity> (2)
        "
	::= { pmopm2Almchannel67PortEntry 2 }


--- *********************************************************
---     TABLE for the pmopm2Almchannel68Port articles
--- *********************************************************

pmopm2Almchannel68PortTable OBJECT-TYPE
	SYNTAX  SEQUENCE OF Pmopm2Almchannel68PortEntry
	MAX-ACCESS not-accessible
	STATUS current
	DESCRIPTION
        "
        List of pmopm2Almchannel68Port
        Article
        "
	::= { pmopm2AlmClientCrit 150 }


pmopm2Almchannel68PortEntry OBJECT-TYPE
	SYNTAX Pmopm2Almchannel68PortEntry
	MAX-ACCESS not-accessible
	STATUS current
	DESCRIPTION
        "
        Row definition for the pmopm2Almchannel68Port
        table
        "
	INDEX   { pmopm2Almchannel68PortIndex }
	::= { pmopm2Almchannel68PortTable 1 }


Pmopm2Almchannel68PortEntry ::=
	SEQUENCE {
	pmopm2Almchannel68PortIndex
		INTEGER,
	pmopm2AlmChannel68OosPortn
		EkiOnOff,
	pmopm2AlmChannel68PowerHighPortn
		EkiOnOff,
	pmopm2AlmChannel68PowerLowPortn
		EkiOnOff,
	pmopm2AlmChannel68BalancedPortn
		EkiOnOff,
	pmopm2AlmChannel68MismatchPortn
		EkiOnOff,
	pmopm2AlmChannel68AbsentPortn
		EkiOnOff
	}


pmopm2Almchannel68PortIndex OBJECT-TYPE
	SYNTAX  INTEGER(0..128)
	MAX-ACCESS  read-only
	STATUS current
	DESCRIPTION
        "
        Index definition for the pmopm2Almchannel68Port
        table
        "
	::= { pmopm2Almchannel68PortEntry 1 }


pmopm2AlmChannel68OosPortn OBJECT-TYPE
	SYNTAX  EkiOnOff
	MAX-ACCESS read-only
	STATUS current
	DESCRIPTION
        "
        Channel Out Of Service 68 :This
        OID indicates that the channel
         is out of service  <Help> This
        alarm indicates that the channel
        is in service <Condtype> CHANNEL68_OOS_1
        <Probcause> informationalStatus(1000)
        <Alarmtype> other (1) <Polarity>
        (2)
        "
	::= { pmopm2Almchannel68PortEntry 7 }


pmopm2AlmChannel68PowerHighPortn OBJECT-TYPE
	SYNTAX  EkiOnOff
	MAX-ACCESS read-only
	STATUS current
	DESCRIPTION
        "
        Channel Power High 68 :This OID
        indicates that the power of the
        channel is higher than the configured
        threshold<Help> This alarm indicates
        that the power of the channel is
        higher than the configured threshold
        <Condtype> CHANNEL68_POWER_HIGH_1
        <Probcause> degradedSignal (13)
        <Alarmtype> equipmentAlarm <Polarity>
        (2)
        "
	::= { pmopm2Almchannel68PortEntry 6 }


pmopm2AlmChannel68PowerLowPortn OBJECT-TYPE
	SYNTAX  EkiOnOff
	MAX-ACCESS read-only
	STATUS current
	DESCRIPTION
        "
        Channel Power Low 68 :This OID
        indicates that the power of the
        channel is lower than the configured
        threshold<Help> This alarm indicates
        that the power of the channel is
        lower than the configured threshold
        <Condtype> CHANNEL68_POWER_LOW_1
        <Probcause> degradedSignal (13)
        <Alarmtype> equipmentAlarm <Polarity>
        (2)
        "
	::= { pmopm2Almchannel68PortEntry 5 }


pmopm2AlmChannel68BalancedPortn OBJECT-TYPE
	SYNTAX  EkiOnOff
	MAX-ACCESS read-only
	STATUS current
	DESCRIPTION
        "
        Channel Balanced 68 :This OID
         indicates that an in service channel
        is balanced by the Ekinops auto
        turn up application<Help> This
         status indicates that an in service
        channel is balanced by the Ekinops
        auto turn up application <Condtype>
        CHANNEL68_BALANCED_1 <Probcause>
        informationalStatus(1000) <Alarmtype>
        other (1) <Polarity> (2)
        "
	::= { pmopm2Almchannel68PortEntry 4 }


pmopm2AlmChannel68MismatchPortn OBJECT-TYPE
	SYNTAX  EkiOnOff
	MAX-ACCESS read-only
	STATUS current
	DESCRIPTION
        "
        Channel Mismatch 68 :This OID
         indicates that an out of service
        channel is detected on the Optical
        Power Monitoring input<Help> This
        alarm indicates that an out of
         service channel is detected on
        the Optical Power Monitoring input
        <Condtype> CHANNEL68_MISMATCH_1
        <Probcause> unexpectedInformation
        (75) <Alarmtype> equipmentAlarm
        <Polarity> (2)
        "
	::= { pmopm2Almchannel68PortEntry 3 }


pmopm2AlmChannel68AbsentPortn OBJECT-TYPE
	SYNTAX  EkiOnOff
	MAX-ACCESS read-only
	STATUS current
	DESCRIPTION
        "
        Channel Absent 68 :This OID indicates
        that an in service channel is absent
        on the Optical Power Monitoring
        input<Help> This alarm indicates
        that an in service channel is absent
        on the Optical Power Monitoring
        input <Condtype> CHANNEL68_ABSENT_1
        <Probcause> informationMissing
         (65) <Alarmtype> equipmentAlarm
        (5) <Polarity> (2)
        "
	::= { pmopm2Almchannel68PortEntry 2 }


--- *********************************************************
---     TABLE for the pmopm2Almchannel69Port articles
--- *********************************************************

pmopm2Almchannel69PortTable OBJECT-TYPE
	SYNTAX  SEQUENCE OF Pmopm2Almchannel69PortEntry
	MAX-ACCESS not-accessible
	STATUS current
	DESCRIPTION
        "
        List of pmopm2Almchannel69Port
        Article
        "
	::= { pmopm2AlmClientCrit 152 }


pmopm2Almchannel69PortEntry OBJECT-TYPE
	SYNTAX Pmopm2Almchannel69PortEntry
	MAX-ACCESS not-accessible
	STATUS current
	DESCRIPTION
        "
        Row definition for the pmopm2Almchannel69Port
        table
        "
	INDEX   { pmopm2Almchannel69PortIndex }
	::= { pmopm2Almchannel69PortTable 1 }


Pmopm2Almchannel69PortEntry ::=
	SEQUENCE {
	pmopm2Almchannel69PortIndex
		INTEGER,
	pmopm2AlmChannel69OosPortn
		EkiOnOff,
	pmopm2AlmChannel69PowerHighPortn
		EkiOnOff,
	pmopm2AlmChannel69PowerLowPortn
		EkiOnOff,
	pmopm2AlmChannel69BalancedPortn
		EkiOnOff,
	pmopm2AlmChannel69MismatchPortn
		EkiOnOff,
	pmopm2AlmChannel69AbsentPortn
		EkiOnOff
	}


pmopm2Almchannel69PortIndex OBJECT-TYPE
	SYNTAX  INTEGER(0..128)
	MAX-ACCESS  read-only
	STATUS current
	DESCRIPTION
        "
        Index definition for the pmopm2Almchannel69Port
        table
        "
	::= { pmopm2Almchannel69PortEntry 1 }


pmopm2AlmChannel69OosPortn OBJECT-TYPE
	SYNTAX  EkiOnOff
	MAX-ACCESS read-only
	STATUS current
	DESCRIPTION
        "
        Channel Out Of Service 69 :This
        OID indicates that the channel
         is out of service  <Help> This
        alarm indicates that the channel
        is in service <Condtype> CHANNEL69_OOS_1
        <Probcause> informationalStatus(1000)
        <Alarmtype> other (1) <Polarity>
        (2)
        "
	::= { pmopm2Almchannel69PortEntry 7 }


pmopm2AlmChannel69PowerHighPortn OBJECT-TYPE
	SYNTAX  EkiOnOff
	MAX-ACCESS read-only
	STATUS current
	DESCRIPTION
        "
        Channel Power High 69 :This OID
        indicates that the power of the
        channel is higher than the configured
        threshold<Help> This alarm indicates
        that the power of the channel is
        higher than the configured threshold
        <Condtype> CHANNEL69_POWER_HIGH_1
        <Probcause> degradedSignal (13)
        <Alarmtype> equipmentAlarm <Polarity>
        (2)
        "
	::= { pmopm2Almchannel69PortEntry 6 }


pmopm2AlmChannel69PowerLowPortn OBJECT-TYPE
	SYNTAX  EkiOnOff
	MAX-ACCESS read-only
	STATUS current
	DESCRIPTION
        "
        Channel Power Low 69 :This OID
        indicates that the power of the
        channel is lower than the configured
        threshold<Help> This alarm indicates
        that the power of the channel is
        lower than the configured threshold
        <Condtype> CHANNEL69_POWER_LOW_1
        <Probcause> degradedSignal (13)
        <Alarmtype> equipmentAlarm <Polarity>
        (2)
        "
	::= { pmopm2Almchannel69PortEntry 5 }


pmopm2AlmChannel69BalancedPortn OBJECT-TYPE
	SYNTAX  EkiOnOff
	MAX-ACCESS read-only
	STATUS current
	DESCRIPTION
        "
        Channel Balanced 69 :This OID
         indicates that an in service channel
        is balanced by the Ekinops auto
        turn up application<Help> This
         status indicates that an in service
        channel is balanced by the Ekinops
        auto turn up application <Condtype>
        CHANNEL69_BALANCED_1 <Probcause>
        informationalStatus(1000) <Alarmtype>
        other (1) <Polarity> (2)
        "
	::= { pmopm2Almchannel69PortEntry 4 }


pmopm2AlmChannel69MismatchPortn OBJECT-TYPE
	SYNTAX  EkiOnOff
	MAX-ACCESS read-only
	STATUS current
	DESCRIPTION
        "
        Channel Mismatch 69 :This OID
         indicates that an out of service
        channel is detected on the Optical
        Power Monitoring input<Help> This
        alarm indicates that an out of
         service channel is detected on
        the Optical Power Monitoring input
        <Condtype> CHANNEL69_MISMATCH_1
        <Probcause> unexpectedInformation
        (75) <Alarmtype> equipmentAlarm
        <Polarity> (2)
        "
	::= { pmopm2Almchannel69PortEntry 3 }


pmopm2AlmChannel69AbsentPortn OBJECT-TYPE
	SYNTAX  EkiOnOff
	MAX-ACCESS read-only
	STATUS current
	DESCRIPTION
        "
        Channel Absent 69 :This OID indicates
        that an in service channel is absent
        on the Optical Power Monitoring
        input<Help> This alarm indicates
        that an in service channel is absent
        on the Optical Power Monitoring
        input <Condtype> CHANNEL69_ABSENT_1
        <Probcause> informationMissing
         (65) <Alarmtype> equipmentAlarm
        (5) <Polarity> (2)
        "
	::= { pmopm2Almchannel69PortEntry 2 }


--- *********************************************************
---     TABLE for the pmopm2Almchannel70Port articles
--- *********************************************************

pmopm2Almchannel70PortTable OBJECT-TYPE
	SYNTAX  SEQUENCE OF Pmopm2Almchannel70PortEntry
	MAX-ACCESS not-accessible
	STATUS current
	DESCRIPTION
        "
        List of pmopm2Almchannel70Port
        Article
        "
	::= { pmopm2AlmClientCrit 154 }


pmopm2Almchannel70PortEntry OBJECT-TYPE
	SYNTAX Pmopm2Almchannel70PortEntry
	MAX-ACCESS not-accessible
	STATUS current
	DESCRIPTION
        "
        Row definition for the pmopm2Almchannel70Port
        table
        "
	INDEX   { pmopm2Almchannel70PortIndex }
	::= { pmopm2Almchannel70PortTable 1 }


Pmopm2Almchannel70PortEntry ::=
	SEQUENCE {
	pmopm2Almchannel70PortIndex
		INTEGER,
	pmopm2AlmChannel70OosPortn
		EkiOnOff,
	pmopm2AlmChannel70PowerHighPortn
		EkiOnOff,
	pmopm2AlmChannel70PowerLowPortn
		EkiOnOff,
	pmopm2AlmChannel70BalancedPortn
		EkiOnOff,
	pmopm2AlmChannel70MismatchPortn
		EkiOnOff,
	pmopm2AlmChannel70AbsentPortn
		EkiOnOff
	}


pmopm2Almchannel70PortIndex OBJECT-TYPE
	SYNTAX  INTEGER(0..128)
	MAX-ACCESS  read-only
	STATUS current
	DESCRIPTION
        "
        Index definition for the pmopm2Almchannel70Port
        table
        "
	::= { pmopm2Almchannel70PortEntry 1 }


pmopm2AlmChannel70OosPortn OBJECT-TYPE
	SYNTAX  EkiOnOff
	MAX-ACCESS read-only
	STATUS current
	DESCRIPTION
        "
        Channel Out Of Service 70 :This
        OID indicates that the channel
         is out of service  <Help> This
        alarm indicates that the channel
        is in service <Condtype> CHANNEL70_OOS_1
        <Probcause> informationalStatus(1000)
        <Alarmtype> other (1) <Polarity>
        (2)
        "
	::= { pmopm2Almchannel70PortEntry 7 }


pmopm2AlmChannel70PowerHighPortn OBJECT-TYPE
	SYNTAX  EkiOnOff
	MAX-ACCESS read-only
	STATUS current
	DESCRIPTION
        "
        Channel Power High 70 :This OID
        indicates that the power of the
        channel is higher than the configured
        threshold<Help> This alarm indicates
        that the power of the channel is
        higher than the configured threshold
        <Condtype> CHANNEL70_POWER_HIGH_1
        <Probcause> degradedSignal (13)
        <Alarmtype> equipmentAlarm <Polarity>
        (2)
        "
	::= { pmopm2Almchannel70PortEntry 6 }


pmopm2AlmChannel70PowerLowPortn OBJECT-TYPE
	SYNTAX  EkiOnOff
	MAX-ACCESS read-only
	STATUS current
	DESCRIPTION
        "
        Channel Power Low 70 :This OID
        indicates that the power of the
        channel is lower than the configured
        threshold<Help> This alarm indicates
        that the power of the channel is
        lower than the configured threshold
        <Condtype> CHANNEL70_POWER_LOW_1
        <Probcause> degradedSignal (13)
        <Alarmtype> equipmentAlarm <Polarity>
        (2)
        "
	::= { pmopm2Almchannel70PortEntry 5 }


pmopm2AlmChannel70BalancedPortn OBJECT-TYPE
	SYNTAX  EkiOnOff
	MAX-ACCESS read-only
	STATUS current
	DESCRIPTION
        "
        Channel Balanced 70 :This OID
         indicates that an in service channel
        is balanced by the Ekinops auto
        turn up application<Help> This
         status indicates that an in service
        channel is balanced by the Ekinops
        auto turn up application <Condtype>
        CHANNEL70_BALANCED_1 <Probcause>
        informationalStatus(1000) <Alarmtype>
        other (1) <Polarity> (2)
        "
	::= { pmopm2Almchannel70PortEntry 4 }


pmopm2AlmChannel70MismatchPortn OBJECT-TYPE
	SYNTAX  EkiOnOff
	MAX-ACCESS read-only
	STATUS current
	DESCRIPTION
        "
        Channel Mismatch 70 :This OID
         indicates that an out of service
        channel is detected on the Optical
        Power Monitoring input<Help> This
        alarm indicates that an out of
         service channel is detected on
        the Optical Power Monitoring input
        <Condtype> CHANNEL70_MISMATCH_1
        <Probcause> unexpectedInformation
        (75) <Alarmtype> equipmentAlarm
        <Polarity> (2)
        "
	::= { pmopm2Almchannel70PortEntry 3 }


pmopm2AlmChannel70AbsentPortn OBJECT-TYPE
	SYNTAX  EkiOnOff
	MAX-ACCESS read-only
	STATUS current
	DESCRIPTION
        "
        Channel Absent 70 :This OID indicates
        that an in service channel is absent
        on the Optical Power Monitoring
        input<Help> This alarm indicates
        that an in service channel is absent
        on the Optical Power Monitoring
        input <Condtype> CHANNEL70_ABSENT_1
        <Probcause> informationMissing
         (65) <Alarmtype> equipmentAlarm
        (5) <Polarity> (2)
        "
	::= { pmopm2Almchannel70PortEntry 2 }


--- *********************************************************
---     TABLE for the pmopm2Almchannel71Port articles
--- *********************************************************

pmopm2Almchannel71PortTable OBJECT-TYPE
	SYNTAX  SEQUENCE OF Pmopm2Almchannel71PortEntry
	MAX-ACCESS not-accessible
	STATUS current
	DESCRIPTION
        "
        List of pmopm2Almchannel71Port
        Article
        "
	::= { pmopm2AlmClientCrit 156 }


pmopm2Almchannel71PortEntry OBJECT-TYPE
	SYNTAX Pmopm2Almchannel71PortEntry
	MAX-ACCESS not-accessible
	STATUS current
	DESCRIPTION
        "
        Row definition for the pmopm2Almchannel71Port
        table
        "
	INDEX   { pmopm2Almchannel71PortIndex }
	::= { pmopm2Almchannel71PortTable 1 }


Pmopm2Almchannel71PortEntry ::=
	SEQUENCE {
	pmopm2Almchannel71PortIndex
		INTEGER,
	pmopm2AlmChannel71OosPortn
		EkiOnOff,
	pmopm2AlmChannel71PowerHighPortn
		EkiOnOff,
	pmopm2AlmChannel71PowerLowPortn
		EkiOnOff,
	pmopm2AlmChannel71BalancedPortn
		EkiOnOff,
	pmopm2AlmChannel71MismatchPortn
		EkiOnOff,
	pmopm2AlmChannel71AbsentPortn
		EkiOnOff
	}


pmopm2Almchannel71PortIndex OBJECT-TYPE
	SYNTAX  INTEGER(0..128)
	MAX-ACCESS  read-only
	STATUS current
	DESCRIPTION
        "
        Index definition for the pmopm2Almchannel71Port
        table
        "
	::= { pmopm2Almchannel71PortEntry 1 }


pmopm2AlmChannel71OosPortn OBJECT-TYPE
	SYNTAX  EkiOnOff
	MAX-ACCESS read-only
	STATUS current
	DESCRIPTION
        "
        Channel Out Of Service 71 :This
        OID indicates that the channel
         is out of service  <Help> This
        alarm indicates that the channel
        is in service <Condtype> CHANNEL71_OOS_1
        <Probcause> informationalStatus(1000)
        <Alarmtype> other (1) <Polarity>
        (2)
        "
	::= { pmopm2Almchannel71PortEntry 7 }


pmopm2AlmChannel71PowerHighPortn OBJECT-TYPE
	SYNTAX  EkiOnOff
	MAX-ACCESS read-only
	STATUS current
	DESCRIPTION
        "
        Channel Power High 71 :This OID
        indicates that the power of the
        channel is higher than the configured
        threshold<Help> This alarm indicates
        that the power of the channel is
        higher than the configured threshold
        <Condtype> CHANNEL71_POWER_HIGH_1
        <Probcause> degradedSignal (13)
        <Alarmtype> equipmentAlarm <Polarity>
        (2)
        "
	::= { pmopm2Almchannel71PortEntry 6 }


pmopm2AlmChannel71PowerLowPortn OBJECT-TYPE
	SYNTAX  EkiOnOff
	MAX-ACCESS read-only
	STATUS current
	DESCRIPTION
        "
        Channel Power Low 71 :This OID
        indicates that the power of the
        channel is lower than the configured
        threshold<Help> This alarm indicates
        that the power of the channel is
        lower than the configured threshold
        <Condtype> CHANNEL71_POWER_LOW_1
        <Probcause> degradedSignal (13)
        <Alarmtype> equipmentAlarm <Polarity>
        (2)
        "
	::= { pmopm2Almchannel71PortEntry 5 }


pmopm2AlmChannel71BalancedPortn OBJECT-TYPE
	SYNTAX  EkiOnOff
	MAX-ACCESS read-only
	STATUS current
	DESCRIPTION
        "
        Channel Balanced 71 :This OID
         indicates that an in service channel
        is balanced by the Ekinops auto
        turn up application<Help> This
         status indicates that an in service
        channel is balanced by the Ekinops
        auto turn up application <Condtype>
        CHANNEL71_BALANCED_1 <Probcause>
        informationalStatus(1000) <Alarmtype>
        other (1) <Polarity> (2)
        "
	::= { pmopm2Almchannel71PortEntry 4 }


pmopm2AlmChannel71MismatchPortn OBJECT-TYPE
	SYNTAX  EkiOnOff
	MAX-ACCESS read-only
	STATUS current
	DESCRIPTION
        "
        Channel Mismatch 71 :This OID
         indicates that an out of service
        channel is detected on the Optical
        Power Monitoring input<Help> This
        alarm indicates that an out of
         service channel is detected on
        the Optical Power Monitoring input
        <Condtype> CHANNEL71_MISMATCH_1
        <Probcause> unexpectedInformation
        (75) <Alarmtype> equipmentAlarm
        <Polarity> (2)
        "
	::= { pmopm2Almchannel71PortEntry 3 }


pmopm2AlmChannel71AbsentPortn OBJECT-TYPE
	SYNTAX  EkiOnOff
	MAX-ACCESS read-only
	STATUS current
	DESCRIPTION
        "
        Channel Absent 71 :This OID indicates
        that an in service channel is absent
        on the Optical Power Monitoring
        input<Help> This alarm indicates
        that an in service channel is absent
        on the Optical Power Monitoring
        input <Condtype> CHANNEL71_ABSENT_1
        <Probcause> informationMissing
         (65) <Alarmtype> equipmentAlarm
        (5) <Polarity> (2)
        "
	::= { pmopm2Almchannel71PortEntry 2 }


--- *********************************************************
---     TABLE for the pmopm2Almchannel72Port articles
--- *********************************************************

pmopm2Almchannel72PortTable OBJECT-TYPE
	SYNTAX  SEQUENCE OF Pmopm2Almchannel72PortEntry
	MAX-ACCESS not-accessible
	STATUS current
	DESCRIPTION
        "
        List of pmopm2Almchannel72Port
        Article
        "
	::= { pmopm2AlmClientCrit 158 }


pmopm2Almchannel72PortEntry OBJECT-TYPE
	SYNTAX Pmopm2Almchannel72PortEntry
	MAX-ACCESS not-accessible
	STATUS current
	DESCRIPTION
        "
        Row definition for the pmopm2Almchannel72Port
        table
        "
	INDEX   { pmopm2Almchannel72PortIndex }
	::= { pmopm2Almchannel72PortTable 1 }


Pmopm2Almchannel72PortEntry ::=
	SEQUENCE {
	pmopm2Almchannel72PortIndex
		INTEGER,
	pmopm2AlmChannel72OosPortn
		EkiOnOff,
	pmopm2AlmChannel72PowerHighPortn
		EkiOnOff,
	pmopm2AlmChannel72PowerLowPortn
		EkiOnOff,
	pmopm2AlmChannel72BalancedPortn
		EkiOnOff,
	pmopm2AlmChannel72MismatchPortn
		EkiOnOff,
	pmopm2AlmChannel72AbsentPortn
		EkiOnOff
	}


pmopm2Almchannel72PortIndex OBJECT-TYPE
	SYNTAX  INTEGER(0..128)
	MAX-ACCESS  read-only
	STATUS current
	DESCRIPTION
        "
        Index definition for the pmopm2Almchannel72Port
        table
        "
	::= { pmopm2Almchannel72PortEntry 1 }


pmopm2AlmChannel72OosPortn OBJECT-TYPE
	SYNTAX  EkiOnOff
	MAX-ACCESS read-only
	STATUS current
	DESCRIPTION
        "
        Channel Out Of Service 72 :This
        OID indicates that the channel
         is out of service  <Help> This
        alarm indicates that the channel
        is in service <Condtype> CHANNEL72_OOS_1
        <Probcause> informationalStatus(1000)
        <Alarmtype> other (1) <Polarity>
        (2)
        "
	::= { pmopm2Almchannel72PortEntry 7 }


pmopm2AlmChannel72PowerHighPortn OBJECT-TYPE
	SYNTAX  EkiOnOff
	MAX-ACCESS read-only
	STATUS current
	DESCRIPTION
        "
        Channel Power High 72 :This OID
        indicates that the power of the
        channel is higher than the configured
        threshold<Help> This alarm indicates
        that the power of the channel is
        higher than the configured threshold
        <Condtype> CHANNEL72_POWER_HIGH_1
        <Probcause> degradedSignal (13)
        <Alarmtype> equipmentAlarm <Polarity>
        (2)
        "
	::= { pmopm2Almchannel72PortEntry 6 }


pmopm2AlmChannel72PowerLowPortn OBJECT-TYPE
	SYNTAX  EkiOnOff
	MAX-ACCESS read-only
	STATUS current
	DESCRIPTION
        "
        Channel Power Low 72 :This OID
        indicates that the power of the
        channel is lower than the configured
        threshold<Help> This alarm indicates
        that the power of the channel is
        lower than the configured threshold
        <Condtype> CHANNEL72_POWER_LOW_1
        <Probcause> degradedSignal (13)
        <Alarmtype> equipmentAlarm <Polarity>
        (2)
        "
	::= { pmopm2Almchannel72PortEntry 5 }


pmopm2AlmChannel72BalancedPortn OBJECT-TYPE
	SYNTAX  EkiOnOff
	MAX-ACCESS read-only
	STATUS current
	DESCRIPTION
        "
        Channel Balanced 72 :This OID
         indicates that an in service channel
        is balanced by the Ekinops auto
        turn up application<Help> This
         status indicates that an in service
        channel is balanced by the Ekinops
        auto turn up application <Condtype>
        CHANNEL72_BALANCED_1 <Probcause>
        informationalStatus(1000) <Alarmtype>
        other (1) <Polarity> (2)
        "
	::= { pmopm2Almchannel72PortEntry 4 }


pmopm2AlmChannel72MismatchPortn OBJECT-TYPE
	SYNTAX  EkiOnOff
	MAX-ACCESS read-only
	STATUS current
	DESCRIPTION
        "
        Channel Mismatch 72 :This OID
         indicates that an out of service
        channel is detected on the Optical
        Power Monitoring input<Help> This
        alarm indicates that an out of
         service channel is detected on
        the Optical Power Monitoring input
        <Condtype> CHANNEL72_MISMATCH_1
        <Probcause> unexpectedInformation
        (75) <Alarmtype> equipmentAlarm
        <Polarity> (2)
        "
	::= { pmopm2Almchannel72PortEntry 3 }


pmopm2AlmChannel72AbsentPortn OBJECT-TYPE
	SYNTAX  EkiOnOff
	MAX-ACCESS read-only
	STATUS current
	DESCRIPTION
        "
        Channel Absent 72 :This OID indicates
        that an in service channel is absent
        on the Optical Power Monitoring
        input<Help> This alarm indicates
        that an in service channel is absent
        on the Optical Power Monitoring
        input <Condtype> CHANNEL72_ABSENT_1
        <Probcause> informationMissing
         (65) <Alarmtype> equipmentAlarm
        (5) <Polarity> (2)
        "
	::= { pmopm2Almchannel72PortEntry 2 }


--- *********************************************************
---     TABLE for the pmopm2Almchannel73Port articles
--- *********************************************************

pmopm2Almchannel73PortTable OBJECT-TYPE
	SYNTAX  SEQUENCE OF Pmopm2Almchannel73PortEntry
	MAX-ACCESS not-accessible
	STATUS current
	DESCRIPTION
        "
        List of pmopm2Almchannel73Port
        Article
        "
	::= { pmopm2AlmClientCrit 160 }


pmopm2Almchannel73PortEntry OBJECT-TYPE
	SYNTAX Pmopm2Almchannel73PortEntry
	MAX-ACCESS not-accessible
	STATUS current
	DESCRIPTION
        "
        Row definition for the pmopm2Almchannel73Port
        table
        "
	INDEX   { pmopm2Almchannel73PortIndex }
	::= { pmopm2Almchannel73PortTable 1 }


Pmopm2Almchannel73PortEntry ::=
	SEQUENCE {
	pmopm2Almchannel73PortIndex
		INTEGER,
	pmopm2AlmChannel73OosPortn
		EkiOnOff,
	pmopm2AlmChannel73PowerHighPortn
		EkiOnOff,
	pmopm2AlmChannel73PowerLowPortn
		EkiOnOff,
	pmopm2AlmChannel73BalancedPortn
		EkiOnOff,
	pmopm2AlmChannel73MismatchPortn
		EkiOnOff,
	pmopm2AlmChannel73AbsentPortn
		EkiOnOff
	}


pmopm2Almchannel73PortIndex OBJECT-TYPE
	SYNTAX  INTEGER(0..128)
	MAX-ACCESS  read-only
	STATUS current
	DESCRIPTION
        "
        Index definition for the pmopm2Almchannel73Port
        table
        "
	::= { pmopm2Almchannel73PortEntry 1 }


pmopm2AlmChannel73OosPortn OBJECT-TYPE
	SYNTAX  EkiOnOff
	MAX-ACCESS read-only
	STATUS current
	DESCRIPTION
        "
        Channel Out Of Service 73 :This
        OID indicates that the channel
         is out of service  <Help> This
        alarm indicates that the channel
        is in service <Condtype> CHANNEL73_OOS_1
        <Probcause> informationalStatus(1000)
        <Alarmtype> other (1) <Polarity>
        (2)
        "
	::= { pmopm2Almchannel73PortEntry 7 }


pmopm2AlmChannel73PowerHighPortn OBJECT-TYPE
	SYNTAX  EkiOnOff
	MAX-ACCESS read-only
	STATUS current
	DESCRIPTION
        "
        Channel Power High 73 :This OID
        indicates that the power of the
        channel is higher than the configured
        threshold<Help> This alarm indicates
        that the power of the channel is
        higher than the configured threshold
        <Condtype> CHANNEL73_POWER_HIGH_1
        <Probcause> degradedSignal (13)
        <Alarmtype> equipmentAlarm <Polarity>
        (2)
        "
	::= { pmopm2Almchannel73PortEntry 6 }


pmopm2AlmChannel73PowerLowPortn OBJECT-TYPE
	SYNTAX  EkiOnOff
	MAX-ACCESS read-only
	STATUS current
	DESCRIPTION
        "
        Channel Power Low 73 :This OID
        indicates that the power of the
        channel is lower than the configured
        threshold<Help> This alarm indicates
        that the power of the channel is
        lower than the configured threshold
        <Condtype> CHANNEL73_POWER_LOW_1
        <Probcause> degradedSignal (13)
        <Alarmtype> equipmentAlarm <Polarity>
        (2)
        "
	::= { pmopm2Almchannel73PortEntry 5 }


pmopm2AlmChannel73BalancedPortn OBJECT-TYPE
	SYNTAX  EkiOnOff
	MAX-ACCESS read-only
	STATUS current
	DESCRIPTION
        "
        Channel Balanced 73 :This OID
         indicates that an in service channel
        is balanced by the Ekinops auto
        turn up application<Help> This
         status indicates that an in service
        channel is balanced by the Ekinops
        auto turn up application <Condtype>
        CHANNEL73_BALANCED_1 <Probcause>
        informationalStatus(1000) <Alarmtype>
        other (1) <Polarity> (2)
        "
	::= { pmopm2Almchannel73PortEntry 4 }


pmopm2AlmChannel73MismatchPortn OBJECT-TYPE
	SYNTAX  EkiOnOff
	MAX-ACCESS read-only
	STATUS current
	DESCRIPTION
        "
        Channel Mismatch 73 :This OID
         indicates that an out of service
        channel is detected on the Optical
        Power Monitoring input<Help> This
        alarm indicates that an out of
         service channel is detected on
        the Optical Power Monitoring input
        <Condtype> CHANNEL73_MISMATCH_1
        <Probcause> unexpectedInformation
        (75) <Alarmtype> equipmentAlarm
        <Polarity> (2)
        "
	::= { pmopm2Almchannel73PortEntry 3 }


pmopm2AlmChannel73AbsentPortn OBJECT-TYPE
	SYNTAX  EkiOnOff
	MAX-ACCESS read-only
	STATUS current
	DESCRIPTION
        "
        Channel Absent 73 :This OID indicates
        that an in service channel is absent
        on the Optical Power Monitoring
        input<Help> This alarm indicates
        that an in service channel is absent
        on the Optical Power Monitoring
        input <Condtype> CHANNEL73_ABSENT_1
        <Probcause> informationMissing
         (65) <Alarmtype> equipmentAlarm
        (5) <Polarity> (2)
        "
	::= { pmopm2Almchannel73PortEntry 2 }


--- *********************************************************
---     TABLE for the pmopm2Almchannel74Port articles
--- *********************************************************

pmopm2Almchannel74PortTable OBJECT-TYPE
	SYNTAX  SEQUENCE OF Pmopm2Almchannel74PortEntry
	MAX-ACCESS not-accessible
	STATUS current
	DESCRIPTION
        "
        List of pmopm2Almchannel74Port
        Article
        "
	::= { pmopm2AlmClientCrit 162 }


pmopm2Almchannel74PortEntry OBJECT-TYPE
	SYNTAX Pmopm2Almchannel74PortEntry
	MAX-ACCESS not-accessible
	STATUS current
	DESCRIPTION
        "
        Row definition for the pmopm2Almchannel74Port
        table
        "
	INDEX   { pmopm2Almchannel74PortIndex }
	::= { pmopm2Almchannel74PortTable 1 }


Pmopm2Almchannel74PortEntry ::=
	SEQUENCE {
	pmopm2Almchannel74PortIndex
		INTEGER,
	pmopm2AlmChannel74OosPortn
		EkiOnOff,
	pmopm2AlmChannel74PowerHighPortn
		EkiOnOff,
	pmopm2AlmChannel74PowerLowPortn
		EkiOnOff,
	pmopm2AlmChannel74BalancedPortn
		EkiOnOff,
	pmopm2AlmChannel74MismatchPortn
		EkiOnOff,
	pmopm2AlmChannel74AbsentPortn
		EkiOnOff
	}


pmopm2Almchannel74PortIndex OBJECT-TYPE
	SYNTAX  INTEGER(0..128)
	MAX-ACCESS  read-only
	STATUS current
	DESCRIPTION
        "
        Index definition for the pmopm2Almchannel74Port
        table
        "
	::= { pmopm2Almchannel74PortEntry 1 }


pmopm2AlmChannel74OosPortn OBJECT-TYPE
	SYNTAX  EkiOnOff
	MAX-ACCESS read-only
	STATUS current
	DESCRIPTION
        "
        Channel Out Of Service 74 :This
        OID indicates that the channel
         is out of service  <Help> This
        alarm indicates that the channel
        is in service <Condtype> CHANNEL74_OOS_1
        <Probcause> informationalStatus(1000)
        <Alarmtype> other (1) <Polarity>
        (2)
        "
	::= { pmopm2Almchannel74PortEntry 7 }


pmopm2AlmChannel74PowerHighPortn OBJECT-TYPE
	SYNTAX  EkiOnOff
	MAX-ACCESS read-only
	STATUS current
	DESCRIPTION
        "
        Channel Power High 74 :This OID
        indicates that the power of the
        channel is higher than the configured
        threshold<Help> This alarm indicates
        that the power of the channel is
        higher than the configured threshold
        <Condtype> CHANNEL74_POWER_HIGH_1
        <Probcause> degradedSignal (13)
        <Alarmtype> equipmentAlarm <Polarity>
        (2)
        "
	::= { pmopm2Almchannel74PortEntry 6 }


pmopm2AlmChannel74PowerLowPortn OBJECT-TYPE
	SYNTAX  EkiOnOff
	MAX-ACCESS read-only
	STATUS current
	DESCRIPTION
        "
        Channel Power Low 74 :This OID
        indicates that the power of the
        channel is lower than the configured
        threshold<Help> This alarm indicates
        that the power of the channel is
        lower than the configured threshold
        <Condtype> CHANNEL74_POWER_LOW_1
        <Probcause> degradedSignal (13)
        <Alarmtype> equipmentAlarm <Polarity>
        (2)
        "
	::= { pmopm2Almchannel74PortEntry 5 }


pmopm2AlmChannel74BalancedPortn OBJECT-TYPE
	SYNTAX  EkiOnOff
	MAX-ACCESS read-only
	STATUS current
	DESCRIPTION
        "
        Channel Balanced 74 :This OID
         indicates that an in service channel
        is balanced by the Ekinops auto
        turn up application<Help> This
         status indicates that an in service
        channel is balanced by the Ekinops
        auto turn up application <Condtype>
        CHANNEL74_BALANCED_1 <Probcause>
        informationalStatus(1000) <Alarmtype>
        other (1) <Polarity> (2)
        "
	::= { pmopm2Almchannel74PortEntry 4 }


pmopm2AlmChannel74MismatchPortn OBJECT-TYPE
	SYNTAX  EkiOnOff
	MAX-ACCESS read-only
	STATUS current
	DESCRIPTION
        "
        Channel Mismatch 74 :This OID
         indicates that an out of service
        channel is detected on the Optical
        Power Monitoring input<Help> This
        alarm indicates that an out of
         service channel is detected on
        the Optical Power Monitoring input
        <Condtype> CHANNEL74_MISMATCH_1
        <Probcause> unexpectedInformation
        (75) <Alarmtype> equipmentAlarm
        <Polarity> (2)
        "
	::= { pmopm2Almchannel74PortEntry 3 }


pmopm2AlmChannel74AbsentPortn OBJECT-TYPE
	SYNTAX  EkiOnOff
	MAX-ACCESS read-only
	STATUS current
	DESCRIPTION
        "
        Channel Absent 74 :This OID indicates
        that an in service channel is absent
        on the Optical Power Monitoring
        input<Help> This alarm indicates
        that an in service channel is absent
        on the Optical Power Monitoring
        input <Condtype> CHANNEL74_ABSENT_1
        <Probcause> informationMissing
         (65) <Alarmtype> equipmentAlarm
        (5) <Polarity> (2)
        "
	::= { pmopm2Almchannel74PortEntry 2 }


--- *********************************************************
---     TABLE for the pmopm2Almchannel75Port articles
--- *********************************************************

pmopm2Almchannel75PortTable OBJECT-TYPE
	SYNTAX  SEQUENCE OF Pmopm2Almchannel75PortEntry
	MAX-ACCESS not-accessible
	STATUS current
	DESCRIPTION
        "
        List of pmopm2Almchannel75Port
        Article
        "
	::= { pmopm2AlmClientCrit 164 }


pmopm2Almchannel75PortEntry OBJECT-TYPE
	SYNTAX Pmopm2Almchannel75PortEntry
	MAX-ACCESS not-accessible
	STATUS current
	DESCRIPTION
        "
        Row definition for the pmopm2Almchannel75Port
        table
        "
	INDEX   { pmopm2Almchannel75PortIndex }
	::= { pmopm2Almchannel75PortTable 1 }


Pmopm2Almchannel75PortEntry ::=
	SEQUENCE {
	pmopm2Almchannel75PortIndex
		INTEGER,
	pmopm2AlmChannel75OosPortn
		EkiOnOff,
	pmopm2AlmChannel75PowerHighPortn
		EkiOnOff,
	pmopm2AlmChannel75PowerLowPortn
		EkiOnOff,
	pmopm2AlmChannel75BalancedPortn
		EkiOnOff,
	pmopm2AlmChannel75MismatchPortn
		EkiOnOff,
	pmopm2AlmChannel75AbsentPortn
		EkiOnOff
	}


pmopm2Almchannel75PortIndex OBJECT-TYPE
	SYNTAX  INTEGER(0..128)
	MAX-ACCESS  read-only
	STATUS current
	DESCRIPTION
        "
        Index definition for the pmopm2Almchannel75Port
        table
        "
	::= { pmopm2Almchannel75PortEntry 1 }


pmopm2AlmChannel75OosPortn OBJECT-TYPE
	SYNTAX  EkiOnOff
	MAX-ACCESS read-only
	STATUS current
	DESCRIPTION
        "
        Channel Out Of Service 75 :This
        OID indicates that the channel
         is out of service  <Help> This
        alarm indicates that the channel
        is in service <Condtype> CHANNEL75_OOS_1
        <Probcause> informationalStatus(1000)
        <Alarmtype> other (1) <Polarity>
        (2)
        "
	::= { pmopm2Almchannel75PortEntry 7 }


pmopm2AlmChannel75PowerHighPortn OBJECT-TYPE
	SYNTAX  EkiOnOff
	MAX-ACCESS read-only
	STATUS current
	DESCRIPTION
        "
        Channel Power High 75 :This OID
        indicates that the power of the
        channel is higher than the configured
        threshold<Help> This alarm indicates
        that the power of the channel is
        higher than the configured threshold
        <Condtype> CHANNEL75_POWER_HIGH_1
        <Probcause> degradedSignal (13)
        <Alarmtype> equipmentAlarm <Polarity>
        (2)
        "
	::= { pmopm2Almchannel75PortEntry 6 }


pmopm2AlmChannel75PowerLowPortn OBJECT-TYPE
	SYNTAX  EkiOnOff
	MAX-ACCESS read-only
	STATUS current
	DESCRIPTION
        "
        Channel Power Low 75 :This OID
        indicates that the power of the
        channel is lower than the configured
        threshold<Help> This alarm indicates
        that the power of the channel is
        lower than the configured threshold
        <Condtype> CHANNEL75_POWER_LOW_1
        <Probcause> degradedSignal (13)
        <Alarmtype> equipmentAlarm <Polarity>
        (2)
        "
	::= { pmopm2Almchannel75PortEntry 5 }


pmopm2AlmChannel75BalancedPortn OBJECT-TYPE
	SYNTAX  EkiOnOff
	MAX-ACCESS read-only
	STATUS current
	DESCRIPTION
        "
        Channel Balanced 75 :This OID
         indicates that an in service channel
        is balanced by the Ekinops auto
        turn up application<Help> This
         status indicates that an in service
        channel is balanced by the Ekinops
        auto turn up application <Condtype>
        CHANNEL75_BALANCED_1 <Probcause>
        informationalStatus(1000) <Alarmtype>
        other (1) <Polarity> (2)
        "
	::= { pmopm2Almchannel75PortEntry 4 }


pmopm2AlmChannel75MismatchPortn OBJECT-TYPE
	SYNTAX  EkiOnOff
	MAX-ACCESS read-only
	STATUS current
	DESCRIPTION
        "
        Channel Mismatch 75 :This OID
         indicates that an out of service
        channel is detected on the Optical
        Power Monitoring input<Help> This
        alarm indicates that an out of
         service channel is detected on
        the Optical Power Monitoring input
        <Condtype> CHANNEL75_MISMATCH_1
        <Probcause> unexpectedInformation
        (75) <Alarmtype> equipmentAlarm
        <Polarity> (2)
        "
	::= { pmopm2Almchannel75PortEntry 3 }


pmopm2AlmChannel75AbsentPortn OBJECT-TYPE
	SYNTAX  EkiOnOff
	MAX-ACCESS read-only
	STATUS current
	DESCRIPTION
        "
        Channel Absent 75 :This OID indicates
        that an in service channel is absent
        on the Optical Power Monitoring
        input<Help> This alarm indicates
        that an in service channel is absent
        on the Optical Power Monitoring
        input <Condtype> CHANNEL75_ABSENT_1
        <Probcause> informationMissing
         (65) <Alarmtype> equipmentAlarm
        (5) <Polarity> (2)
        "
	::= { pmopm2Almchannel75PortEntry 2 }


--- *********************************************************
---     TABLE for the pmopm2Almchannel76Port articles
--- *********************************************************

pmopm2Almchannel76PortTable OBJECT-TYPE
	SYNTAX  SEQUENCE OF Pmopm2Almchannel76PortEntry
	MAX-ACCESS not-accessible
	STATUS current
	DESCRIPTION
        "
        List of pmopm2Almchannel76Port
        Article
        "
	::= { pmopm2AlmClientCrit 166 }


pmopm2Almchannel76PortEntry OBJECT-TYPE
	SYNTAX Pmopm2Almchannel76PortEntry
	MAX-ACCESS not-accessible
	STATUS current
	DESCRIPTION
        "
        Row definition for the pmopm2Almchannel76Port
        table
        "
	INDEX   { pmopm2Almchannel76PortIndex }
	::= { pmopm2Almchannel76PortTable 1 }


Pmopm2Almchannel76PortEntry ::=
	SEQUENCE {
	pmopm2Almchannel76PortIndex
		INTEGER,
	pmopm2AlmChannel76OosPortn
		EkiOnOff,
	pmopm2AlmChannel76PowerHighPortn
		EkiOnOff,
	pmopm2AlmChannel76PowerLowPortn
		EkiOnOff,
	pmopm2AlmChannel76BalancedPortn
		EkiOnOff,
	pmopm2AlmChannel76MismatchPortn
		EkiOnOff,
	pmopm2AlmChannel76AbsentPortn
		EkiOnOff
	}


pmopm2Almchannel76PortIndex OBJECT-TYPE
	SYNTAX  INTEGER(0..128)
	MAX-ACCESS  read-only
	STATUS current
	DESCRIPTION
        "
        Index definition for the pmopm2Almchannel76Port
        table
        "
	::= { pmopm2Almchannel76PortEntry 1 }


pmopm2AlmChannel76OosPortn OBJECT-TYPE
	SYNTAX  EkiOnOff
	MAX-ACCESS read-only
	STATUS current
	DESCRIPTION
        "
        Channel Out Of Service 76 :This
        OID indicates that the channel
         is out of service  <Help> This
        alarm indicates that the channel
        is in service <Condtype> CHANNEL76_OOS_1
        <Probcause> informationalStatus(1000)
        <Alarmtype> other (1) <Polarity>
        (2)
        "
	::= { pmopm2Almchannel76PortEntry 7 }


pmopm2AlmChannel76PowerHighPortn OBJECT-TYPE
	SYNTAX  EkiOnOff
	MAX-ACCESS read-only
	STATUS current
	DESCRIPTION
        "
        Channel Power High 76 :This OID
        indicates that the power of the
        channel is higher than the configured
        threshold<Help> This alarm indicates
        that the power of the channel is
        higher than the configured threshold
        <Condtype> CHANNEL76_POWER_HIGH_1
        <Probcause> degradedSignal (13)
        <Alarmtype> equipmentAlarm <Polarity>
        (2)
        "
	::= { pmopm2Almchannel76PortEntry 6 }


pmopm2AlmChannel76PowerLowPortn OBJECT-TYPE
	SYNTAX  EkiOnOff
	MAX-ACCESS read-only
	STATUS current
	DESCRIPTION
        "
        Channel Power Low 76 :This OID
        indicates that the power of the
        channel is lower than the configured
        threshold<Help> This alarm indicates
        that the power of the channel is
        lower than the configured threshold
        <Condtype> CHANNEL76_POWER_LOW_1
        <Probcause> degradedSignal (13)
        <Alarmtype> equipmentAlarm <Polarity>
        (2)
        "
	::= { pmopm2Almchannel76PortEntry 5 }


pmopm2AlmChannel76BalancedPortn OBJECT-TYPE
	SYNTAX  EkiOnOff
	MAX-ACCESS read-only
	STATUS current
	DESCRIPTION
        "
        Channel Balanced 76 :This OID
         indicates that an in service channel
        is balanced by the Ekinops auto
        turn up application<Help> This
         status indicates that an in service
        channel is balanced by the Ekinops
        auto turn up application <Condtype>
        CHANNEL76_BALANCED_1 <Probcause>
        informationalStatus(1000) <Alarmtype>
        other (1) <Polarity> (2)
        "
	::= { pmopm2Almchannel76PortEntry 4 }


pmopm2AlmChannel76MismatchPortn OBJECT-TYPE
	SYNTAX  EkiOnOff
	MAX-ACCESS read-only
	STATUS current
	DESCRIPTION
        "
        Channel Mismatch 76 :This OID
         indicates that an out of service
        channel is detected on the Optical
        Power Monitoring input<Help> This
        alarm indicates that an out of
         service channel is detected on
        the Optical Power Monitoring input
        <Condtype> CHANNEL76_MISMATCH_1
        <Probcause> unexpectedInformation
        (75) <Alarmtype> equipmentAlarm
        <Polarity> (2)
        "
	::= { pmopm2Almchannel76PortEntry 3 }


pmopm2AlmChannel76AbsentPortn OBJECT-TYPE
	SYNTAX  EkiOnOff
	MAX-ACCESS read-only
	STATUS current
	DESCRIPTION
        "
        Channel Absent 76 :This OID indicates
        that an in service channel is absent
        on the Optical Power Monitoring
        input<Help> This alarm indicates
        that an in service channel is absent
        on the Optical Power Monitoring
        input <Condtype> CHANNEL76_ABSENT_1
        <Probcause> informationMissing
         (65) <Alarmtype> equipmentAlarm
        (5) <Polarity> (2)
        "
	::= { pmopm2Almchannel76PortEntry 2 }


--- *********************************************************
---     TABLE for the pmopm2Almchannel77Port articles
--- *********************************************************

pmopm2Almchannel77PortTable OBJECT-TYPE
	SYNTAX  SEQUENCE OF Pmopm2Almchannel77PortEntry
	MAX-ACCESS not-accessible
	STATUS current
	DESCRIPTION
        "
        List of pmopm2Almchannel77Port
        Article
        "
	::= { pmopm2AlmClientCrit 168 }


pmopm2Almchannel77PortEntry OBJECT-TYPE
	SYNTAX Pmopm2Almchannel77PortEntry
	MAX-ACCESS not-accessible
	STATUS current
	DESCRIPTION
        "
        Row definition for the pmopm2Almchannel77Port
        table
        "
	INDEX   { pmopm2Almchannel77PortIndex }
	::= { pmopm2Almchannel77PortTable 1 }


Pmopm2Almchannel77PortEntry ::=
	SEQUENCE {
	pmopm2Almchannel77PortIndex
		INTEGER,
	pmopm2AlmChannel77OosPortn
		EkiOnOff,
	pmopm2AlmChannel77PowerHighPortn
		EkiOnOff,
	pmopm2AlmChannel77PowerLowPortn
		EkiOnOff,
	pmopm2AlmChannel77BalancedPortn
		EkiOnOff,
	pmopm2AlmChannel77MismatchPortn
		EkiOnOff,
	pmopm2AlmChannel77AbsentPortn
		EkiOnOff
	}


pmopm2Almchannel77PortIndex OBJECT-TYPE
	SYNTAX  INTEGER(0..128)
	MAX-ACCESS  read-only
	STATUS current
	DESCRIPTION
        "
        Index definition for the pmopm2Almchannel77Port
        table
        "
	::= { pmopm2Almchannel77PortEntry 1 }


pmopm2AlmChannel77OosPortn OBJECT-TYPE
	SYNTAX  EkiOnOff
	MAX-ACCESS read-only
	STATUS current
	DESCRIPTION
        "
        Channel Out Of Service 77 :This
        OID indicates that the channel
         is out of service  <Help> This
        alarm indicates that the channel
        is in service <Condtype> CHANNEL77_OOS_1
        <Probcause> informationalStatus(1000)
        <Alarmtype> other (1) <Polarity>
        (2)
        "
	::= { pmopm2Almchannel77PortEntry 7 }


pmopm2AlmChannel77PowerHighPortn OBJECT-TYPE
	SYNTAX  EkiOnOff
	MAX-ACCESS read-only
	STATUS current
	DESCRIPTION
        "
        Channel Power High 77 :This OID
        indicates that the power of the
        channel is higher than the configured
        threshold<Help> This alarm indicates
        that the power of the channel is
        higher than the configured threshold
        <Condtype> CHANNEL77_POWER_HIGH_1
        <Probcause> degradedSignal (13)
        <Alarmtype> equipmentAlarm <Polarity>
        (2)
        "
	::= { pmopm2Almchannel77PortEntry 6 }


pmopm2AlmChannel77PowerLowPortn OBJECT-TYPE
	SYNTAX  EkiOnOff
	MAX-ACCESS read-only
	STATUS current
	DESCRIPTION
        "
        Channel Power Low 77 :This OID
        indicates that the power of the
        channel is lower than the configured
        threshold<Help> This alarm indicates
        that the power of the channel is
        lower than the configured threshold
        <Condtype> CHANNEL77_POWER_LOW_1
        <Probcause> degradedSignal (13)
        <Alarmtype> equipmentAlarm <Polarity>
        (2)
        "
	::= { pmopm2Almchannel77PortEntry 5 }


pmopm2AlmChannel77BalancedPortn OBJECT-TYPE
	SYNTAX  EkiOnOff
	MAX-ACCESS read-only
	STATUS current
	DESCRIPTION
        "
        Channel Balanced 77 :This OID
         indicates that an in service channel
        is balanced by the Ekinops auto
        turn up application<Help> This
         status indicates that an in service
        channel is balanced by the Ekinops
        auto turn up application <Condtype>
        CHANNEL77_BALANCED_1 <Probcause>
        informationalStatus(1000) <Alarmtype>
        other (1) <Polarity> (2)
        "
	::= { pmopm2Almchannel77PortEntry 4 }


pmopm2AlmChannel77MismatchPortn OBJECT-TYPE
	SYNTAX  EkiOnOff
	MAX-ACCESS read-only
	STATUS current
	DESCRIPTION
        "
        Channel Mismatch 77 :This OID
         indicates that an out of service
        channel is detected on the Optical
        Power Monitoring input<Help> This
        alarm indicates that an out of
         service channel is detected on
        the Optical Power Monitoring input
        <Condtype> CHANNEL77_MISMATCH_1
        <Probcause> unexpectedInformation
        (75) <Alarmtype> equipmentAlarm
        <Polarity> (2)
        "
	::= { pmopm2Almchannel77PortEntry 3 }


pmopm2AlmChannel77AbsentPortn OBJECT-TYPE
	SYNTAX  EkiOnOff
	MAX-ACCESS read-only
	STATUS current
	DESCRIPTION
        "
        Channel Absent 77 :This OID indicates
        that an in service channel is absent
        on the Optical Power Monitoring
        input<Help> This alarm indicates
        that an in service channel is absent
        on the Optical Power Monitoring
        input <Condtype> CHANNEL77_ABSENT_1
        <Probcause> informationMissing
         (65) <Alarmtype> equipmentAlarm
        (5) <Polarity> (2)
        "
	::= { pmopm2Almchannel77PortEntry 2 }


--- *********************************************************
---     TABLE for the pmopm2Almchannel78Port articles
--- *********************************************************

pmopm2Almchannel78PortTable OBJECT-TYPE
	SYNTAX  SEQUENCE OF Pmopm2Almchannel78PortEntry
	MAX-ACCESS not-accessible
	STATUS current
	DESCRIPTION
        "
        List of pmopm2Almchannel78Port
        Article
        "
	::= { pmopm2AlmClientCrit 170 }


pmopm2Almchannel78PortEntry OBJECT-TYPE
	SYNTAX Pmopm2Almchannel78PortEntry
	MAX-ACCESS not-accessible
	STATUS current
	DESCRIPTION
        "
        Row definition for the pmopm2Almchannel78Port
        table
        "
	INDEX   { pmopm2Almchannel78PortIndex }
	::= { pmopm2Almchannel78PortTable 1 }


Pmopm2Almchannel78PortEntry ::=
	SEQUENCE {
	pmopm2Almchannel78PortIndex
		INTEGER,
	pmopm2AlmChannel78OosPortn
		EkiOnOff,
	pmopm2AlmChannel78PowerHighPortn
		EkiOnOff,
	pmopm2AlmChannel78PowerLowPortn
		EkiOnOff,
	pmopm2AlmChannel78BalancedPortn
		EkiOnOff,
	pmopm2AlmChannel78MismatchPortn
		EkiOnOff,
	pmopm2AlmChannel78AbsentPortn
		EkiOnOff
	}


pmopm2Almchannel78PortIndex OBJECT-TYPE
	SYNTAX  INTEGER(0..128)
	MAX-ACCESS  read-only
	STATUS current
	DESCRIPTION
        "
        Index definition for the pmopm2Almchannel78Port
        table
        "
	::= { pmopm2Almchannel78PortEntry 1 }


pmopm2AlmChannel78OosPortn OBJECT-TYPE
	SYNTAX  EkiOnOff
	MAX-ACCESS read-only
	STATUS current
	DESCRIPTION
        "
        Channel Out Of Service 78 :This
        OID indicates that the channel
         is out of service  <Help> This
        alarm indicates that the channel
        is in service <Condtype> CHANNEL78_OOS_1
        <Probcause> informationalStatus(1000)
        <Alarmtype> other (1) <Polarity>
        (2)
        "
	::= { pmopm2Almchannel78PortEntry 7 }


pmopm2AlmChannel78PowerHighPortn OBJECT-TYPE
	SYNTAX  EkiOnOff
	MAX-ACCESS read-only
	STATUS current
	DESCRIPTION
        "
        Channel Power High 78 :This OID
        indicates that the power of the
        channel is higher than the configured
        threshold<Help> This alarm indicates
        that the power of the channel is
        higher than the configured threshold
        <Condtype> CHANNEL78_POWER_HIGH_1
        <Probcause> degradedSignal (13)
        <Alarmtype> equipmentAlarm <Polarity>
        (2)
        "
	::= { pmopm2Almchannel78PortEntry 6 }


pmopm2AlmChannel78PowerLowPortn OBJECT-TYPE
	SYNTAX  EkiOnOff
	MAX-ACCESS read-only
	STATUS current
	DESCRIPTION
        "
        Channel Power Low 78 :This OID
        indicates that the power of the
        channel is lower than the configured
        threshold<Help> This alarm indicates
        that the power of the channel is
        lower than the configured threshold
        <Condtype> CHANNEL78_POWER_LOW_1
        <Probcause> degradedSignal (13)
        <Alarmtype> equipmentAlarm <Polarity>
        (2)
        "
	::= { pmopm2Almchannel78PortEntry 5 }


pmopm2AlmChannel78BalancedPortn OBJECT-TYPE
	SYNTAX  EkiOnOff
	MAX-ACCESS read-only
	STATUS current
	DESCRIPTION
        "
        Channel Balanced 78 :This OID
         indicates that an in service channel
        is balanced by the Ekinops auto
        turn up application<Help> This
         status indicates that an in service
        channel is balanced by the Ekinops
        auto turn up application <Condtype>
        CHANNEL78_BALANCED_1 <Probcause>
        informationalStatus(1000) <Alarmtype>
        other (1) <Polarity> (2)
        "
	::= { pmopm2Almchannel78PortEntry 4 }


pmopm2AlmChannel78MismatchPortn OBJECT-TYPE
	SYNTAX  EkiOnOff
	MAX-ACCESS read-only
	STATUS current
	DESCRIPTION
        "
        Channel Mismatch 78 :This OID
         indicates that an out of service
        channel is detected on the Optical
        Power Monitoring input<Help> This
        alarm indicates that an out of
         service channel is detected on
        the Optical Power Monitoring input
        <Condtype> CHANNEL78_MISMATCH_1
        <Probcause> unexpectedInformation
        (75) <Alarmtype> equipmentAlarm
        <Polarity> (2)
        "
	::= { pmopm2Almchannel78PortEntry 3 }


pmopm2AlmChannel78AbsentPortn OBJECT-TYPE
	SYNTAX  EkiOnOff
	MAX-ACCESS read-only
	STATUS current
	DESCRIPTION
        "
        Channel Absent 78 :This OID indicates
        that an in service channel is absent
        on the Optical Power Monitoring
        input<Help> This alarm indicates
        that an in service channel is absent
        on the Optical Power Monitoring
        input <Condtype> CHANNEL78_ABSENT_1
        <Probcause> informationMissing
         (65) <Alarmtype> equipmentAlarm
        (5) <Polarity> (2)
        "
	::= { pmopm2Almchannel78PortEntry 2 }


--- *********************************************************
---     TABLE for the pmopm2Almchannel79Port articles
--- *********************************************************

pmopm2Almchannel79PortTable OBJECT-TYPE
	SYNTAX  SEQUENCE OF Pmopm2Almchannel79PortEntry
	MAX-ACCESS not-accessible
	STATUS current
	DESCRIPTION
        "
        List of pmopm2Almchannel79Port
        Article
        "
	::= { pmopm2AlmClientCrit 172 }


pmopm2Almchannel79PortEntry OBJECT-TYPE
	SYNTAX Pmopm2Almchannel79PortEntry
	MAX-ACCESS not-accessible
	STATUS current
	DESCRIPTION
        "
        Row definition for the pmopm2Almchannel79Port
        table
        "
	INDEX   { pmopm2Almchannel79PortIndex }
	::= { pmopm2Almchannel79PortTable 1 }


Pmopm2Almchannel79PortEntry ::=
	SEQUENCE {
	pmopm2Almchannel79PortIndex
		INTEGER,
	pmopm2AlmChannel79OosPortn
		EkiOnOff,
	pmopm2AlmChannel79PowerHighPortn
		EkiOnOff,
	pmopm2AlmChannel79PowerLowPortn
		EkiOnOff,
	pmopm2AlmChannel79BalancedPortn
		EkiOnOff,
	pmopm2AlmChannel79MismatchPortn
		EkiOnOff,
	pmopm2AlmChannel79AbsentPortn
		EkiOnOff
	}


pmopm2Almchannel79PortIndex OBJECT-TYPE
	SYNTAX  INTEGER(0..128)
	MAX-ACCESS  read-only
	STATUS current
	DESCRIPTION
        "
        Index definition for the pmopm2Almchannel79Port
        table
        "
	::= { pmopm2Almchannel79PortEntry 1 }


pmopm2AlmChannel79OosPortn OBJECT-TYPE
	SYNTAX  EkiOnOff
	MAX-ACCESS read-only
	STATUS current
	DESCRIPTION
        "
        Channel Out Of Service 79 :This
        OID indicates that the channel
         is out of service  <Help> This
        alarm indicates that the channel
        is in service <Condtype> CHANNEL79_OOS_1
        <Probcause> informationalStatus(1000)
        <Alarmtype> other (1) <Polarity>
        (2)
        "
	::= { pmopm2Almchannel79PortEntry 7 }


pmopm2AlmChannel79PowerHighPortn OBJECT-TYPE
	SYNTAX  EkiOnOff
	MAX-ACCESS read-only
	STATUS current
	DESCRIPTION
        "
        Channel Power High 79 :This OID
        indicates that the power of the
        channel is higher than the configured
        threshold<Help> This alarm indicates
        that the power of the channel is
        higher than the configured threshold
        <Condtype> CHANNEL79_POWER_HIGH_1
        <Probcause> degradedSignal (13)
        <Alarmtype> equipmentAlarm <Polarity>
        (2)
        "
	::= { pmopm2Almchannel79PortEntry 6 }


pmopm2AlmChannel79PowerLowPortn OBJECT-TYPE
	SYNTAX  EkiOnOff
	MAX-ACCESS read-only
	STATUS current
	DESCRIPTION
        "
        Channel Power Low 79 :This OID
        indicates that the power of the
        channel is lower than the configured
        threshold<Help> This alarm indicates
        that the power of the channel is
        lower than the configured threshold
        <Condtype> CHANNEL79_POWER_LOW_1
        <Probcause> degradedSignal (13)
        <Alarmtype> equipmentAlarm <Polarity>
        (2)
        "
	::= { pmopm2Almchannel79PortEntry 5 }


pmopm2AlmChannel79BalancedPortn OBJECT-TYPE
	SYNTAX  EkiOnOff
	MAX-ACCESS read-only
	STATUS current
	DESCRIPTION
        "
        Channel Balanced 79 :This OID
         indicates that an in service channel
        is balanced by the Ekinops auto
        turn up application<Help> This
         status indicates that an in service
        channel is balanced by the Ekinops
        auto turn up application <Condtype>
        CHANNEL79_BALANCED_1 <Probcause>
        informationalStatus(1000) <Alarmtype>
        other (1) <Polarity> (2)
        "
	::= { pmopm2Almchannel79PortEntry 4 }


pmopm2AlmChannel79MismatchPortn OBJECT-TYPE
	SYNTAX  EkiOnOff
	MAX-ACCESS read-only
	STATUS current
	DESCRIPTION
        "
        Channel Mismatch 79 :This OID
         indicates that an out of service
        channel is detected on the Optical
        Power Monitoring input<Help> This
        alarm indicates that an out of
         service channel is detected on
        the Optical Power Monitoring input
        <Condtype> CHANNEL79_MISMATCH_1
        <Probcause> unexpectedInformation
        (75) <Alarmtype> equipmentAlarm
        <Polarity> (2)
        "
	::= { pmopm2Almchannel79PortEntry 3 }


pmopm2AlmChannel79AbsentPortn OBJECT-TYPE
	SYNTAX  EkiOnOff
	MAX-ACCESS read-only
	STATUS current
	DESCRIPTION
        "
        Channel Absent 79 :This OID indicates
        that an in service channel is absent
        on the Optical Power Monitoring
        input<Help> This alarm indicates
        that an in service channel is absent
        on the Optical Power Monitoring
        input <Condtype> CHANNEL79_ABSENT_1
        <Probcause> informationMissing
         (65) <Alarmtype> equipmentAlarm
        (5) <Polarity> (2)
        "
	::= { pmopm2Almchannel79PortEntry 2 }


--- *********************************************************
---     TABLE for the pmopm2Almchannel80Port articles
--- *********************************************************

pmopm2Almchannel80PortTable OBJECT-TYPE
	SYNTAX  SEQUENCE OF Pmopm2Almchannel80PortEntry
	MAX-ACCESS not-accessible
	STATUS current
	DESCRIPTION
        "
        List of pmopm2Almchannel80Port
        Article
        "
	::= { pmopm2AlmClientCrit 174 }


pmopm2Almchannel80PortEntry OBJECT-TYPE
	SYNTAX Pmopm2Almchannel80PortEntry
	MAX-ACCESS not-accessible
	STATUS current
	DESCRIPTION
        "
        Row definition for the pmopm2Almchannel80Port
        table
        "
	INDEX   { pmopm2Almchannel80PortIndex }
	::= { pmopm2Almchannel80PortTable 1 }


Pmopm2Almchannel80PortEntry ::=
	SEQUENCE {
	pmopm2Almchannel80PortIndex
		INTEGER,
	pmopm2AlmChannel80OosPortn
		EkiOnOff,
	pmopm2AlmChannel80PowerHighPortn
		EkiOnOff,
	pmopm2AlmChannel80PowerLowPortn
		EkiOnOff,
	pmopm2AlmChannel80BalancedPortn
		EkiOnOff,
	pmopm2AlmChannel80MismatchPortn
		EkiOnOff,
	pmopm2AlmChannel80AbsentPortn
		EkiOnOff
	}


pmopm2Almchannel80PortIndex OBJECT-TYPE
	SYNTAX  INTEGER(0..128)
	MAX-ACCESS  read-only
	STATUS current
	DESCRIPTION
        "
        Index definition for the pmopm2Almchannel80Port
        table
        "
	::= { pmopm2Almchannel80PortEntry 1 }


pmopm2AlmChannel80OosPortn OBJECT-TYPE
	SYNTAX  EkiOnOff
	MAX-ACCESS read-only
	STATUS current
	DESCRIPTION
        "
        Channel Out Of Service 80 :This
        OID indicates that the channel
         is out of service  <Help> This
        alarm indicates that the channel
        is in service <Condtype> CHANNEL80_OOS_1
        <Probcause> informationalStatus(1000)
        <Alarmtype> other (1) <Polarity>
        (2)
        "
	::= { pmopm2Almchannel80PortEntry 7 }


pmopm2AlmChannel80PowerHighPortn OBJECT-TYPE
	SYNTAX  EkiOnOff
	MAX-ACCESS read-only
	STATUS current
	DESCRIPTION
        "
        Channel Power High 80 :This OID
        indicates that the power of the
        channel is higher than the configured
        threshold<Help> This alarm indicates
        that the power of the channel is
        higher than the configured threshold
        <Condtype> CHANNEL80_POWER_HIGH_1
        <Probcause> degradedSignal (13)
        <Alarmtype> equipmentAlarm <Polarity>
        (2)
        "
	::= { pmopm2Almchannel80PortEntry 6 }


pmopm2AlmChannel80PowerLowPortn OBJECT-TYPE
	SYNTAX  EkiOnOff
	MAX-ACCESS read-only
	STATUS current
	DESCRIPTION
        "
        Channel Power Low 80 :This OID
        indicates that the power of the
        channel is lower than the configured
        threshold<Help> This alarm indicates
        that the power of the channel is
        lower than the configured threshold
        <Condtype> CHANNEL80_POWER_LOW_1
        <Probcause> degradedSignal (13)
        <Alarmtype> equipmentAlarm <Polarity>
        (2)
        "
	::= { pmopm2Almchannel80PortEntry 5 }


pmopm2AlmChannel80BalancedPortn OBJECT-TYPE
	SYNTAX  EkiOnOff
	MAX-ACCESS read-only
	STATUS current
	DESCRIPTION
        "
        Channel Balanced 80 :This OID
         indicates that an in service channel
        is balanced by the Ekinops auto
        turn up application<Help> This
         status indicates that an in service
        channel is balanced by the Ekinops
        auto turn up application <Condtype>
        CHANNEL80_BALANCED_1 <Probcause>
        informationalStatus(1000) <Alarmtype>
        other (1) <Polarity> (2)
        "
	::= { pmopm2Almchannel80PortEntry 4 }


pmopm2AlmChannel80MismatchPortn OBJECT-TYPE
	SYNTAX  EkiOnOff
	MAX-ACCESS read-only
	STATUS current
	DESCRIPTION
        "
        Channel Mismatch 80 :This OID
         indicates that an out of service
        channel is detected on the Optical
        Power Monitoring input<Help> This
        alarm indicates that an out of
         service channel is detected on
        the Optical Power Monitoring input
        <Condtype> CHANNEL80_MISMATCH_1
        <Probcause> unexpectedInformation
        (75) <Alarmtype> equipmentAlarm
        <Polarity> (2)
        "
	::= { pmopm2Almchannel80PortEntry 3 }


pmopm2AlmChannel80AbsentPortn OBJECT-TYPE
	SYNTAX  EkiOnOff
	MAX-ACCESS read-only
	STATUS current
	DESCRIPTION
        "
        Channel Absent 80 :This OID indicates
        that an in service channel is absent
        on the Optical Power Monitoring
        input<Help> This alarm indicates
        that an in service channel is absent
        on the Optical Power Monitoring
        input <Condtype> CHANNEL80_ABSENT_1
        <Probcause> informationMissing
         (65) <Alarmtype> equipmentAlarm
        (5) <Polarity> (2)
        "
	::= { pmopm2Almchannel80PortEntry 2 }


--- *********************************************************
---     TABLE for the pmopm2Almchannel81Port articles
--- *********************************************************

pmopm2Almchannel81PortTable OBJECT-TYPE
	SYNTAX  SEQUENCE OF Pmopm2Almchannel81PortEntry
	MAX-ACCESS not-accessible
	STATUS current
	DESCRIPTION
        "
        List of pmopm2Almchannel81Port
        Article
        "
	::= { pmopm2AlmClientCrit 176 }


pmopm2Almchannel81PortEntry OBJECT-TYPE
	SYNTAX Pmopm2Almchannel81PortEntry
	MAX-ACCESS not-accessible
	STATUS current
	DESCRIPTION
        "
        Row definition for the pmopm2Almchannel81Port
        table
        "
	INDEX   { pmopm2Almchannel81PortIndex }
	::= { pmopm2Almchannel81PortTable 1 }


Pmopm2Almchannel81PortEntry ::=
	SEQUENCE {
	pmopm2Almchannel81PortIndex
		INTEGER,
	pmopm2AlmChannel81OosPortn
		EkiOnOff,
	pmopm2AlmChannel81PowerHighPortn
		EkiOnOff,
	pmopm2AlmChannel81PowerLowPortn
		EkiOnOff,
	pmopm2AlmChannel81BalancedPortn
		EkiOnOff,
	pmopm2AlmChannel81MismatchPortn
		EkiOnOff,
	pmopm2AlmChannel81AbsentPortn
		EkiOnOff
	}


pmopm2Almchannel81PortIndex OBJECT-TYPE
	SYNTAX  INTEGER(0..128)
	MAX-ACCESS  read-only
	STATUS current
	DESCRIPTION
        "
        Index definition for the pmopm2Almchannel81Port
        table
        "
	::= { pmopm2Almchannel81PortEntry 1 }


pmopm2AlmChannel81OosPortn OBJECT-TYPE
	SYNTAX  EkiOnOff
	MAX-ACCESS read-only
	STATUS current
	DESCRIPTION
        "
        Channel Out Of Service 81 :This
        OID indicates that the channel
         is out of service  <Help> This
        alarm indicates that the channel
        is in service <Condtype> CHANNEL81_OOS_1
        <Probcause> informationalStatus(1000)
        <Alarmtype> other (1) <Polarity>
        (2)
        "
	::= { pmopm2Almchannel81PortEntry 7 }


pmopm2AlmChannel81PowerHighPortn OBJECT-TYPE
	SYNTAX  EkiOnOff
	MAX-ACCESS read-only
	STATUS current
	DESCRIPTION
        "
        Channel Power High 81 :This OID
        indicates that the power of the
        channel is higher than the configured
        threshold<Help> This alarm indicates
        that the power of the channel is
        higher than the configured threshold
        <Condtype> CHANNEL81_POWER_HIGH_1
        <Probcause> degradedSignal (13)
        <Alarmtype> equipmentAlarm <Polarity>
        (2)
        "
	::= { pmopm2Almchannel81PortEntry 6 }


pmopm2AlmChannel81PowerLowPortn OBJECT-TYPE
	SYNTAX  EkiOnOff
	MAX-ACCESS read-only
	STATUS current
	DESCRIPTION
        "
        Channel Power Low 81 :This OID
        indicates that the power of the
        channel is lower than the configured
        threshold<Help> This alarm indicates
        that the power of the channel is
        lower than the configured threshold
        <Condtype> CHANNEL81_POWER_LOW_1
        <Probcause> degradedSignal (13)
        <Alarmtype> equipmentAlarm <Polarity>
        (2)
        "
	::= { pmopm2Almchannel81PortEntry 5 }


pmopm2AlmChannel81BalancedPortn OBJECT-TYPE
	SYNTAX  EkiOnOff
	MAX-ACCESS read-only
	STATUS current
	DESCRIPTION
        "
        Channel Balanced 81 :This OID
         indicates that an in service channel
        is balanced by the Ekinops auto
        turn up application<Help> This
         status indicates that an in service
        channel is balanced by the Ekinops
        auto turn up application <Condtype>
        CHANNEL81_BALANCED_1 <Probcause>
        informationalStatus(1000) <Alarmtype>
        other (1) <Polarity> (2)
        "
	::= { pmopm2Almchannel81PortEntry 4 }


pmopm2AlmChannel81MismatchPortn OBJECT-TYPE
	SYNTAX  EkiOnOff
	MAX-ACCESS read-only
	STATUS current
	DESCRIPTION
        "
        Channel Mismatch 81 :This OID
         indicates that an out of service
        channel is detected on the Optical
        Power Monitoring input<Help> This
        alarm indicates that an out of
         service channel is detected on
        the Optical Power Monitoring input
        <Condtype> CHANNEL81_MISMATCH_1
        <Probcause> unexpectedInformation
        (75) <Alarmtype> equipmentAlarm
        <Polarity> (2)
        "
	::= { pmopm2Almchannel81PortEntry 3 }


pmopm2AlmChannel81AbsentPortn OBJECT-TYPE
	SYNTAX  EkiOnOff
	MAX-ACCESS read-only
	STATUS current
	DESCRIPTION
        "
        Channel Absent 81 :This OID indicates
        that an in service channel is absent
        on the Optical Power Monitoring
        input<Help> This alarm indicates
        that an in service channel is absent
        on the Optical Power Monitoring
        input <Condtype> CHANNEL81_ABSENT_1
        <Probcause> informationMissing
         (65) <Alarmtype> equipmentAlarm
        (5) <Polarity> (2)
        "
	::= { pmopm2Almchannel81PortEntry 2 }


--- *********************************************************
---     TABLE for the pmopm2Almchannel82Port articles
--- *********************************************************

pmopm2Almchannel82PortTable OBJECT-TYPE
	SYNTAX  SEQUENCE OF Pmopm2Almchannel82PortEntry
	MAX-ACCESS not-accessible
	STATUS current
	DESCRIPTION
        "
        List of pmopm2Almchannel82Port
        Article
        "
	::= { pmopm2AlmClientCrit 178 }


pmopm2Almchannel82PortEntry OBJECT-TYPE
	SYNTAX Pmopm2Almchannel82PortEntry
	MAX-ACCESS not-accessible
	STATUS current
	DESCRIPTION
        "
        Row definition for the pmopm2Almchannel82Port
        table
        "
	INDEX   { pmopm2Almchannel82PortIndex }
	::= { pmopm2Almchannel82PortTable 1 }


Pmopm2Almchannel82PortEntry ::=
	SEQUENCE {
	pmopm2Almchannel82PortIndex
		INTEGER,
	pmopm2AlmChannel82OosPortn
		EkiOnOff,
	pmopm2AlmChannel82PowerHighPortn
		EkiOnOff,
	pmopm2AlmChannel82PowerLowPortn
		EkiOnOff,
	pmopm2AlmChannel82BalancedPortn
		EkiOnOff,
	pmopm2AlmChannel82MismatchPortn
		EkiOnOff,
	pmopm2AlmChannel82AbsentPortn
		EkiOnOff
	}


pmopm2Almchannel82PortIndex OBJECT-TYPE
	SYNTAX  INTEGER(0..128)
	MAX-ACCESS  read-only
	STATUS current
	DESCRIPTION
        "
        Index definition for the pmopm2Almchannel82Port
        table
        "
	::= { pmopm2Almchannel82PortEntry 1 }


pmopm2AlmChannel82OosPortn OBJECT-TYPE
	SYNTAX  EkiOnOff
	MAX-ACCESS read-only
	STATUS current
	DESCRIPTION
        "
        Channel Out Of Service 82 :This
        OID indicates that the channel
         is out of service  <Help> This
        alarm indicates that the channel
        is in service <Condtype> CHANNEL82_OOS_1
        <Probcause> informationalStatus(1000)
        <Alarmtype> other (1) <Polarity>
        (2)
        "
	::= { pmopm2Almchannel82PortEntry 7 }


pmopm2AlmChannel82PowerHighPortn OBJECT-TYPE
	SYNTAX  EkiOnOff
	MAX-ACCESS read-only
	STATUS current
	DESCRIPTION
        "
        Channel Power High 82 :This OID
        indicates that the power of the
        channel is higher than the configured
        threshold<Help> This alarm indicates
        that the power of the channel is
        higher than the configured threshold
        <Condtype> CHANNEL82_POWER_HIGH_1
        <Probcause> degradedSignal (13)
        <Alarmtype> equipmentAlarm <Polarity>
        (2)
        "
	::= { pmopm2Almchannel82PortEntry 6 }


pmopm2AlmChannel82PowerLowPortn OBJECT-TYPE
	SYNTAX  EkiOnOff
	MAX-ACCESS read-only
	STATUS current
	DESCRIPTION
        "
        Channel Power Low 82 :This OID
        indicates that the power of the
        channel is lower than the configured
        threshold<Help> This alarm indicates
        that the power of the channel is
        lower than the configured threshold
        <Condtype> CHANNEL82_POWER_LOW_1
        <Probcause> degradedSignal (13)
        <Alarmtype> equipmentAlarm <Polarity>
        (2)
        "
	::= { pmopm2Almchannel82PortEntry 5 }


pmopm2AlmChannel82BalancedPortn OBJECT-TYPE
	SYNTAX  EkiOnOff
	MAX-ACCESS read-only
	STATUS current
	DESCRIPTION
        "
        Channel Balanced 82 :This OID
         indicates that an in service channel
        is balanced by the Ekinops auto
        turn up application<Help> This
         status indicates that an in service
        channel is balanced by the Ekinops
        auto turn up application <Condtype>
        CHANNEL82_BALANCED_1 <Probcause>
        informationalStatus(1000) <Alarmtype>
        other (1) <Polarity> (2)
        "
	::= { pmopm2Almchannel82PortEntry 4 }


pmopm2AlmChannel82MismatchPortn OBJECT-TYPE
	SYNTAX  EkiOnOff
	MAX-ACCESS read-only
	STATUS current
	DESCRIPTION
        "
        Channel Mismatch 82 :This OID
         indicates that an out of service
        channel is detected on the Optical
        Power Monitoring input<Help> This
        alarm indicates that an out of
         service channel is detected on
        the Optical Power Monitoring input
        <Condtype> CHANNEL82_MISMATCH_1
        <Probcause> unexpectedInformation
        (75) <Alarmtype> equipmentAlarm
        <Polarity> (2)
        "
	::= { pmopm2Almchannel82PortEntry 3 }


pmopm2AlmChannel82AbsentPortn OBJECT-TYPE
	SYNTAX  EkiOnOff
	MAX-ACCESS read-only
	STATUS current
	DESCRIPTION
        "
        Channel Absent 82 :This OID indicates
        that an in service channel is absent
        on the Optical Power Monitoring
        input<Help> This alarm indicates
        that an in service channel is absent
        on the Optical Power Monitoring
        input <Condtype> CHANNEL82_ABSENT_1
        <Probcause> informationMissing
         (65) <Alarmtype> equipmentAlarm
        (5) <Polarity> (2)
        "
	::= { pmopm2Almchannel82PortEntry 2 }


--- *********************************************************
---     TABLE for the pmopm2Almchannel83Port articles
--- *********************************************************

pmopm2Almchannel83PortTable OBJECT-TYPE
	SYNTAX  SEQUENCE OF Pmopm2Almchannel83PortEntry
	MAX-ACCESS not-accessible
	STATUS current
	DESCRIPTION
        "
        List of pmopm2Almchannel83Port
        Article
        "
	::= { pmopm2AlmClientCrit 180 }


pmopm2Almchannel83PortEntry OBJECT-TYPE
	SYNTAX Pmopm2Almchannel83PortEntry
	MAX-ACCESS not-accessible
	STATUS current
	DESCRIPTION
        "
        Row definition for the pmopm2Almchannel83Port
        table
        "
	INDEX   { pmopm2Almchannel83PortIndex }
	::= { pmopm2Almchannel83PortTable 1 }


Pmopm2Almchannel83PortEntry ::=
	SEQUENCE {
	pmopm2Almchannel83PortIndex
		INTEGER,
	pmopm2AlmChannel83OosPortn
		EkiOnOff,
	pmopm2AlmChannel83PowerHighPortn
		EkiOnOff,
	pmopm2AlmChannel83PowerLowPortn
		EkiOnOff,
	pmopm2AlmChannel83BalancedPortn
		EkiOnOff,
	pmopm2AlmChannel83MismatchPortn
		EkiOnOff,
	pmopm2AlmChannel83AbsentPortn
		EkiOnOff
	}


pmopm2Almchannel83PortIndex OBJECT-TYPE
	SYNTAX  INTEGER(0..128)
	MAX-ACCESS  read-only
	STATUS current
	DESCRIPTION
        "
        Index definition for the pmopm2Almchannel83Port
        table
        "
	::= { pmopm2Almchannel83PortEntry 1 }


pmopm2AlmChannel83OosPortn OBJECT-TYPE
	SYNTAX  EkiOnOff
	MAX-ACCESS read-only
	STATUS current
	DESCRIPTION
        "
        Channel Out Of Service 83 :This
        OID indicates that the channel
         is out of service  <Help> This
        alarm indicates that the channel
        is in service <Condtype> CHANNEL83_OOS_1
        <Probcause> informationalStatus(1000)
        <Alarmtype> other (1) <Polarity>
        (2)
        "
	::= { pmopm2Almchannel83PortEntry 7 }


pmopm2AlmChannel83PowerHighPortn OBJECT-TYPE
	SYNTAX  EkiOnOff
	MAX-ACCESS read-only
	STATUS current
	DESCRIPTION
        "
        Channel Power High 83 :This OID
        indicates that the power of the
        channel is higher than the configured
        threshold<Help> This alarm indicates
        that the power of the channel is
        higher than the configured threshold
        <Condtype> CHANNEL83_POWER_HIGH_1
        <Probcause> degradedSignal (13)
        <Alarmtype> equipmentAlarm <Polarity>
        (2)
        "
	::= { pmopm2Almchannel83PortEntry 6 }


pmopm2AlmChannel83PowerLowPortn OBJECT-TYPE
	SYNTAX  EkiOnOff
	MAX-ACCESS read-only
	STATUS current
	DESCRIPTION
        "
        Channel Power Low 83 :This OID
        indicates that the power of the
        channel is lower than the configured
        threshold<Help> This alarm indicates
        that the power of the channel is
        lower than the configured threshold
        <Condtype> CHANNEL83_POWER_LOW_1
        <Probcause> degradedSignal (13)
        <Alarmtype> equipmentAlarm <Polarity>
        (2)
        "
	::= { pmopm2Almchannel83PortEntry 5 }


pmopm2AlmChannel83BalancedPortn OBJECT-TYPE
	SYNTAX  EkiOnOff
	MAX-ACCESS read-only
	STATUS current
	DESCRIPTION
        "
        Channel Balanced 83 :This OID
         indicates that an in service channel
        is balanced by the Ekinops auto
        turn up application<Help> This
         status indicates that an in service
        channel is balanced by the Ekinops
        auto turn up application <Condtype>
        CHANNEL83_BALANCED_1 <Probcause>
        informationalStatus(1000) <Alarmtype>
        other (1) <Polarity> (2)
        "
	::= { pmopm2Almchannel83PortEntry 4 }


pmopm2AlmChannel83MismatchPortn OBJECT-TYPE
	SYNTAX  EkiOnOff
	MAX-ACCESS read-only
	STATUS current
	DESCRIPTION
        "
        Channel Mismatch 83 :This OID
         indicates that an out of service
        channel is detected on the Optical
        Power Monitoring input<Help> This
        alarm indicates that an out of
         service channel is detected on
        the Optical Power Monitoring input
        <Condtype> CHANNEL83_MISMATCH_1
        <Probcause> unexpectedInformation
        (75) <Alarmtype> equipmentAlarm
        <Polarity> (2)
        "
	::= { pmopm2Almchannel83PortEntry 3 }


pmopm2AlmChannel83AbsentPortn OBJECT-TYPE
	SYNTAX  EkiOnOff
	MAX-ACCESS read-only
	STATUS current
	DESCRIPTION
        "
        Channel Absent 83 :This OID indicates
        that an in service channel is absent
        on the Optical Power Monitoring
        input<Help> This alarm indicates
        that an in service channel is absent
        on the Optical Power Monitoring
        input <Condtype> CHANNEL83_ABSENT_1
        <Probcause> informationMissing
         (65) <Alarmtype> equipmentAlarm
        (5) <Polarity> (2)
        "
	::= { pmopm2Almchannel83PortEntry 2 }


--- *********************************************************
---     TABLE for the pmopm2Almchannel84Port articles
--- *********************************************************

pmopm2Almchannel84PortTable OBJECT-TYPE
	SYNTAX  SEQUENCE OF Pmopm2Almchannel84PortEntry
	MAX-ACCESS not-accessible
	STATUS current
	DESCRIPTION
        "
        List of pmopm2Almchannel84Port
        Article
        "
	::= { pmopm2AlmClientCrit 182 }


pmopm2Almchannel84PortEntry OBJECT-TYPE
	SYNTAX Pmopm2Almchannel84PortEntry
	MAX-ACCESS not-accessible
	STATUS current
	DESCRIPTION
        "
        Row definition for the pmopm2Almchannel84Port
        table
        "
	INDEX   { pmopm2Almchannel84PortIndex }
	::= { pmopm2Almchannel84PortTable 1 }


Pmopm2Almchannel84PortEntry ::=
	SEQUENCE {
	pmopm2Almchannel84PortIndex
		INTEGER,
	pmopm2AlmChannel84OosPortn
		EkiOnOff,
	pmopm2AlmChannel84PowerHighPortn
		EkiOnOff,
	pmopm2AlmChannel84PowerLowPortn
		EkiOnOff,
	pmopm2AlmChannel84BalancedPortn
		EkiOnOff,
	pmopm2AlmChannel84MismatchPortn
		EkiOnOff,
	pmopm2AlmChannel84AbsentPortn
		EkiOnOff
	}


pmopm2Almchannel84PortIndex OBJECT-TYPE
	SYNTAX  INTEGER(0..128)
	MAX-ACCESS  read-only
	STATUS current
	DESCRIPTION
        "
        Index definition for the pmopm2Almchannel84Port
        table
        "
	::= { pmopm2Almchannel84PortEntry 1 }


pmopm2AlmChannel84OosPortn OBJECT-TYPE
	SYNTAX  EkiOnOff
	MAX-ACCESS read-only
	STATUS current
	DESCRIPTION
        "
        Channel Out Of Service 84 :This
        OID indicates that the channel
         is out of service  <Help> This
        alarm indicates that the channel
        is in service <Condtype> CHANNEL84_OOS_1
        <Probcause> informationalStatus(1000)
        <Alarmtype> other (1) <Polarity>
        (2)
        "
	::= { pmopm2Almchannel84PortEntry 7 }


pmopm2AlmChannel84PowerHighPortn OBJECT-TYPE
	SYNTAX  EkiOnOff
	MAX-ACCESS read-only
	STATUS current
	DESCRIPTION
        "
        Channel Power High 84 :This OID
        indicates that the power of the
        channel is higher than the configured
        threshold<Help> This alarm indicates
        that the power of the channel is
        higher than the configured threshold
        <Condtype> CHANNEL84_POWER_HIGH_1
        <Probcause> degradedSignal (13)
        <Alarmtype> equipmentAlarm <Polarity>
        (2)
        "
	::= { pmopm2Almchannel84PortEntry 6 }


pmopm2AlmChannel84PowerLowPortn OBJECT-TYPE
	SYNTAX  EkiOnOff
	MAX-ACCESS read-only
	STATUS current
	DESCRIPTION
        "
        Channel Power Low 84 :This OID
        indicates that the power of the
        channel is lower than the configured
        threshold<Help> This alarm indicates
        that the power of the channel is
        lower than the configured threshold
        <Condtype> CHANNEL84_POWER_LOW_1
        <Probcause> degradedSignal (13)
        <Alarmtype> equipmentAlarm <Polarity>
        (2)
        "
	::= { pmopm2Almchannel84PortEntry 5 }


pmopm2AlmChannel84BalancedPortn OBJECT-TYPE
	SYNTAX  EkiOnOff
	MAX-ACCESS read-only
	STATUS current
	DESCRIPTION
        "
        Channel Balanced 84 :This OID
         indicates that an in service channel
        is balanced by the Ekinops auto
        turn up application<Help> This
         status indicates that an in service
        channel is balanced by the Ekinops
        auto turn up application <Condtype>
        CHANNEL84_BALANCED_1 <Probcause>
        informationalStatus(1000) <Alarmtype>
        other (1) <Polarity> (2)
        "
	::= { pmopm2Almchannel84PortEntry 4 }


pmopm2AlmChannel84MismatchPortn OBJECT-TYPE
	SYNTAX  EkiOnOff
	MAX-ACCESS read-only
	STATUS current
	DESCRIPTION
        "
        Channel Mismatch 84 :This OID
         indicates that an out of service
        channel is detected on the Optical
        Power Monitoring input<Help> This
        alarm indicates that an out of
         service channel is detected on
        the Optical Power Monitoring input
        <Condtype> CHANNEL84_MISMATCH_1
        <Probcause> unexpectedInformation
        (75) <Alarmtype> equipmentAlarm
        <Polarity> (2)
        "
	::= { pmopm2Almchannel84PortEntry 3 }


pmopm2AlmChannel84AbsentPortn OBJECT-TYPE
	SYNTAX  EkiOnOff
	MAX-ACCESS read-only
	STATUS current
	DESCRIPTION
        "
        Channel Absent 84 :This OID indicates
        that an in service channel is absent
        on the Optical Power Monitoring
        input<Help> This alarm indicates
        that an in service channel is absent
        on the Optical Power Monitoring
        input <Condtype> CHANNEL84_ABSENT_1
        <Probcause> informationMissing
         (65) <Alarmtype> equipmentAlarm
        (5) <Polarity> (2)
        "
	::= { pmopm2Almchannel84PortEntry 2 }


--- *********************************************************
---     TABLE for the pmopm2Almchannel85Port articles
--- *********************************************************

pmopm2Almchannel85PortTable OBJECT-TYPE
	SYNTAX  SEQUENCE OF Pmopm2Almchannel85PortEntry
	MAX-ACCESS not-accessible
	STATUS current
	DESCRIPTION
        "
        List of pmopm2Almchannel85Port
        Article
        "
	::= { pmopm2AlmClientCrit 184 }


pmopm2Almchannel85PortEntry OBJECT-TYPE
	SYNTAX Pmopm2Almchannel85PortEntry
	MAX-ACCESS not-accessible
	STATUS current
	DESCRIPTION
        "
        Row definition for the pmopm2Almchannel85Port
        table
        "
	INDEX   { pmopm2Almchannel85PortIndex }
	::= { pmopm2Almchannel85PortTable 1 }


Pmopm2Almchannel85PortEntry ::=
	SEQUENCE {
	pmopm2Almchannel85PortIndex
		INTEGER,
	pmopm2AlmChannel85OosPortn
		EkiOnOff,
	pmopm2AlmChannel85PowerHighPortn
		EkiOnOff,
	pmopm2AlmChannel85PowerLowPortn
		EkiOnOff,
	pmopm2AlmChannel85BalancedPortn
		EkiOnOff,
	pmopm2AlmChannel85MismatchPortn
		EkiOnOff,
	pmopm2AlmChannel85AbsentPortn
		EkiOnOff
	}


pmopm2Almchannel85PortIndex OBJECT-TYPE
	SYNTAX  INTEGER(0..128)
	MAX-ACCESS  read-only
	STATUS current
	DESCRIPTION
        "
        Index definition for the pmopm2Almchannel85Port
        table
        "
	::= { pmopm2Almchannel85PortEntry 1 }


pmopm2AlmChannel85OosPortn OBJECT-TYPE
	SYNTAX  EkiOnOff
	MAX-ACCESS read-only
	STATUS current
	DESCRIPTION
        "
        Channel Out Of Service 85 :This
        OID indicates that the channel
         is out of service  <Help> This
        alarm indicates that the channel
        is in service <Condtype> CHANNEL85_OOS_1
        <Probcause> informationalStatus(1000)
        <Alarmtype> other (1) <Polarity>
        (2)
        "
	::= { pmopm2Almchannel85PortEntry 7 }


pmopm2AlmChannel85PowerHighPortn OBJECT-TYPE
	SYNTAX  EkiOnOff
	MAX-ACCESS read-only
	STATUS current
	DESCRIPTION
        "
        Channel Power High 85 :This OID
        indicates that the power of the
        channel is higher than the configured
        threshold<Help> This alarm indicates
        that the power of the channel is
        higher than the configured threshold
        <Condtype> CHANNEL85_POWER_HIGH_1
        <Probcause> degradedSignal (13)
        <Alarmtype> equipmentAlarm <Polarity>
        (2)
        "
	::= { pmopm2Almchannel85PortEntry 6 }


pmopm2AlmChannel85PowerLowPortn OBJECT-TYPE
	SYNTAX  EkiOnOff
	MAX-ACCESS read-only
	STATUS current
	DESCRIPTION
        "
        Channel Power Low 85 :This OID
        indicates that the power of the
        channel is lower than the configured
        threshold<Help> This alarm indicates
        that the power of the channel is
        lower than the configured threshold
        <Condtype> CHANNEL85_POWER_LOW_1
        <Probcause> degradedSignal (13)
        <Alarmtype> equipmentAlarm <Polarity>
        (2)
        "
	::= { pmopm2Almchannel85PortEntry 5 }


pmopm2AlmChannel85BalancedPortn OBJECT-TYPE
	SYNTAX  EkiOnOff
	MAX-ACCESS read-only
	STATUS current
	DESCRIPTION
        "
        Channel Balanced 85 :This OID
         indicates that an in service channel
        is balanced by the Ekinops auto
        turn up application<Help> This
         status indicates that an in service
        channel is balanced by the Ekinops
        auto turn up application <Condtype>
        CHANNEL85_BALANCED_1 <Probcause>
        informationalStatus(1000) <Alarmtype>
        other (1) <Polarity> (2)
        "
	::= { pmopm2Almchannel85PortEntry 4 }


pmopm2AlmChannel85MismatchPortn OBJECT-TYPE
	SYNTAX  EkiOnOff
	MAX-ACCESS read-only
	STATUS current
	DESCRIPTION
        "
        Channel Mismatch 85 :This OID
         indicates that an out of service
        channel is detected on the Optical
        Power Monitoring input<Help> This
        alarm indicates that an out of
         service channel is detected on
        the Optical Power Monitoring input
        <Condtype> CHANNEL85_MISMATCH_1
        <Probcause> unexpectedInformation
        (75) <Alarmtype> equipmentAlarm
        <Polarity> (2)
        "
	::= { pmopm2Almchannel85PortEntry 3 }


pmopm2AlmChannel85AbsentPortn OBJECT-TYPE
	SYNTAX  EkiOnOff
	MAX-ACCESS read-only
	STATUS current
	DESCRIPTION
        "
        Channel Absent 85 :This OID indicates
        that an in service channel is absent
        on the Optical Power Monitoring
        input<Help> This alarm indicates
        that an in service channel is absent
        on the Optical Power Monitoring
        input <Condtype> CHANNEL85_ABSENT_1
        <Probcause> informationMissing
         (65) <Alarmtype> equipmentAlarm
        (5) <Polarity> (2)
        "
	::= { pmopm2Almchannel85PortEntry 2 }


--- *********************************************************
---     TABLE for the pmopm2Almchannel86Port articles
--- *********************************************************

pmopm2Almchannel86PortTable OBJECT-TYPE
	SYNTAX  SEQUENCE OF Pmopm2Almchannel86PortEntry
	MAX-ACCESS not-accessible
	STATUS current
	DESCRIPTION
        "
        List of pmopm2Almchannel86Port
        Article
        "
	::= { pmopm2AlmClientCrit 186 }


pmopm2Almchannel86PortEntry OBJECT-TYPE
	SYNTAX Pmopm2Almchannel86PortEntry
	MAX-ACCESS not-accessible
	STATUS current
	DESCRIPTION
        "
        Row definition for the pmopm2Almchannel86Port
        table
        "
	INDEX   { pmopm2Almchannel86PortIndex }
	::= { pmopm2Almchannel86PortTable 1 }


Pmopm2Almchannel86PortEntry ::=
	SEQUENCE {
	pmopm2Almchannel86PortIndex
		INTEGER,
	pmopm2AlmChannel86OosPortn
		EkiOnOff,
	pmopm2AlmChannel86PowerHighPortn
		EkiOnOff,
	pmopm2AlmChannel86PowerLowPortn
		EkiOnOff,
	pmopm2AlmChannel86BalancedPortn
		EkiOnOff,
	pmopm2AlmChannel86MismatchPortn
		EkiOnOff,
	pmopm2AlmChannel86AbsentPortn
		EkiOnOff
	}


pmopm2Almchannel86PortIndex OBJECT-TYPE
	SYNTAX  INTEGER(0..128)
	MAX-ACCESS  read-only
	STATUS current
	DESCRIPTION
        "
        Index definition for the pmopm2Almchannel86Port
        table
        "
	::= { pmopm2Almchannel86PortEntry 1 }


pmopm2AlmChannel86OosPortn OBJECT-TYPE
	SYNTAX  EkiOnOff
	MAX-ACCESS read-only
	STATUS current
	DESCRIPTION
        "
        Channel Out Of Service 86 :This
        OID indicates that the channel
         is out of service  <Help> This
        alarm indicates that the channel
        is in service <Condtype> CHANNEL86_OOS_1
        <Probcause> informationalStatus(1000)
        <Alarmtype> other (1) <Polarity>
        (2)
        "
	::= { pmopm2Almchannel86PortEntry 7 }


pmopm2AlmChannel86PowerHighPortn OBJECT-TYPE
	SYNTAX  EkiOnOff
	MAX-ACCESS read-only
	STATUS current
	DESCRIPTION
        "
        Channel Power High 86 :This OID
        indicates that the power of the
        channel is higher than the configured
        threshold<Help> This alarm indicates
        that the power of the channel is
        higher than the configured threshold
        <Condtype> CHANNEL86_POWER_HIGH_1
        <Probcause> degradedSignal (13)
        <Alarmtype> equipmentAlarm <Polarity>
        (2)
        "
	::= { pmopm2Almchannel86PortEntry 6 }


pmopm2AlmChannel86PowerLowPortn OBJECT-TYPE
	SYNTAX  EkiOnOff
	MAX-ACCESS read-only
	STATUS current
	DESCRIPTION
        "
        Channel Power Low 86 :This OID
        indicates that the power of the
        channel is lower than the configured
        threshold<Help> This alarm indicates
        that the power of the channel is
        lower than the configured threshold
        <Condtype> CHANNEL86_POWER_LOW_1
        <Probcause> degradedSignal (13)
        <Alarmtype> equipmentAlarm <Polarity>
        (2)
        "
	::= { pmopm2Almchannel86PortEntry 5 }


pmopm2AlmChannel86BalancedPortn OBJECT-TYPE
	SYNTAX  EkiOnOff
	MAX-ACCESS read-only
	STATUS current
	DESCRIPTION
        "
        Channel Balanced 86 :This OID
         indicates that an in service channel
        is balanced by the Ekinops auto
        turn up application<Help> This
         status indicates that an in service
        channel is balanced by the Ekinops
        auto turn up application <Condtype>
        CHANNEL86_BALANCED_1 <Probcause>
        informationalStatus(1000) <Alarmtype>
        other (1) <Polarity> (2)
        "
	::= { pmopm2Almchannel86PortEntry 4 }


pmopm2AlmChannel86MismatchPortn OBJECT-TYPE
	SYNTAX  EkiOnOff
	MAX-ACCESS read-only
	STATUS current
	DESCRIPTION
        "
        Channel Mismatch 86 :This OID
         indicates that an out of service
        channel is detected on the Optical
        Power Monitoring input<Help> This
        alarm indicates that an out of
         service channel is detected on
        the Optical Power Monitoring input
        <Condtype> CHANNEL86_MISMATCH_1
        <Probcause> unexpectedInformation
        (75) <Alarmtype> equipmentAlarm
        <Polarity> (2)
        "
	::= { pmopm2Almchannel86PortEntry 3 }


pmopm2AlmChannel86AbsentPortn OBJECT-TYPE
	SYNTAX  EkiOnOff
	MAX-ACCESS read-only
	STATUS current
	DESCRIPTION
        "
        Channel Absent 86 :This OID indicates
        that an in service channel is absent
        on the Optical Power Monitoring
        input<Help> This alarm indicates
        that an in service channel is absent
        on the Optical Power Monitoring
        input <Condtype> CHANNEL86_ABSENT_1
        <Probcause> informationMissing
         (65) <Alarmtype> equipmentAlarm
        (5) <Polarity> (2)
        "
	::= { pmopm2Almchannel86PortEntry 2 }


--- *********************************************************
---     TABLE for the pmopm2Almchannel87Port articles
--- *********************************************************

pmopm2Almchannel87PortTable OBJECT-TYPE
	SYNTAX  SEQUENCE OF Pmopm2Almchannel87PortEntry
	MAX-ACCESS not-accessible
	STATUS current
	DESCRIPTION
        "
        List of pmopm2Almchannel87Port
        Article
        "
	::= { pmopm2AlmClientCrit 188 }


pmopm2Almchannel87PortEntry OBJECT-TYPE
	SYNTAX Pmopm2Almchannel87PortEntry
	MAX-ACCESS not-accessible
	STATUS current
	DESCRIPTION
        "
        Row definition for the pmopm2Almchannel87Port
        table
        "
	INDEX   { pmopm2Almchannel87PortIndex }
	::= { pmopm2Almchannel87PortTable 1 }


Pmopm2Almchannel87PortEntry ::=
	SEQUENCE {
	pmopm2Almchannel87PortIndex
		INTEGER,
	pmopm2AlmChannel87OosPortn
		EkiOnOff,
	pmopm2AlmChannel87PowerHighPortn
		EkiOnOff,
	pmopm2AlmChannel87PowerLowPortn
		EkiOnOff,
	pmopm2AlmChannel87BalancedPortn
		EkiOnOff,
	pmopm2AlmChannel87MismatchPortn
		EkiOnOff,
	pmopm2AlmChannel87AbsentPortn
		EkiOnOff
	}


pmopm2Almchannel87PortIndex OBJECT-TYPE
	SYNTAX  INTEGER(0..128)
	MAX-ACCESS  read-only
	STATUS current
	DESCRIPTION
        "
        Index definition for the pmopm2Almchannel87Port
        table
        "
	::= { pmopm2Almchannel87PortEntry 1 }


pmopm2AlmChannel87OosPortn OBJECT-TYPE
	SYNTAX  EkiOnOff
	MAX-ACCESS read-only
	STATUS current
	DESCRIPTION
        "
        Channel Out Of Service 87 :This
        OID indicates that the channel
         is out of service  <Help> This
        alarm indicates that the channel
        is in service <Condtype> CHANNEL87_OOS_1
        <Probcause> informationalStatus(1000)
        <Alarmtype> other (1) <Polarity>
        (2)
        "
	::= { pmopm2Almchannel87PortEntry 7 }


pmopm2AlmChannel87PowerHighPortn OBJECT-TYPE
	SYNTAX  EkiOnOff
	MAX-ACCESS read-only
	STATUS current
	DESCRIPTION
        "
        Channel Power High 87 :This OID
        indicates that the power of the
        channel is higher than the configured
        threshold<Help> This alarm indicates
        that the power of the channel is
        higher than the configured threshold
        <Condtype> CHANNEL87_POWER_HIGH_1
        <Probcause> degradedSignal (13)
        <Alarmtype> equipmentAlarm <Polarity>
        (2)
        "
	::= { pmopm2Almchannel87PortEntry 6 }


pmopm2AlmChannel87PowerLowPortn OBJECT-TYPE
	SYNTAX  EkiOnOff
	MAX-ACCESS read-only
	STATUS current
	DESCRIPTION
        "
        Channel Power Low 87 :This OID
        indicates that the power of the
        channel is lower than the configured
        threshold<Help> This alarm indicates
        that the power of the channel is
        lower than the configured threshold
        <Condtype> CHANNEL87_POWER_LOW_1
        <Probcause> degradedSignal (13)
        <Alarmtype> equipmentAlarm <Polarity>
        (2)
        "
	::= { pmopm2Almchannel87PortEntry 5 }


pmopm2AlmChannel87BalancedPortn OBJECT-TYPE
	SYNTAX  EkiOnOff
	MAX-ACCESS read-only
	STATUS current
	DESCRIPTION
        "
        Channel Balanced 87 :This OID
         indicates that an in service channel
        is balanced by the Ekinops auto
        turn up application<Help> This
         status indicates that an in service
        channel is balanced by the Ekinops
        auto turn up application <Condtype>
        CHANNEL87_BALANCED_1 <Probcause>
        informationalStatus(1000) <Alarmtype>
        other (1) <Polarity> (2)
        "
	::= { pmopm2Almchannel87PortEntry 4 }


pmopm2AlmChannel87MismatchPortn OBJECT-TYPE
	SYNTAX  EkiOnOff
	MAX-ACCESS read-only
	STATUS current
	DESCRIPTION
        "
        Channel Mismatch 87 :This OID
         indicates that an out of service
        channel is detected on the Optical
        Power Monitoring input<Help> This
        alarm indicates that an out of
         service channel is detected on
        the Optical Power Monitoring input
        <Condtype> CHANNEL87_MISMATCH_1
        <Probcause> unexpectedInformation
        (75) <Alarmtype> equipmentAlarm
        <Polarity> (2)
        "
	::= { pmopm2Almchannel87PortEntry 3 }


pmopm2AlmChannel87AbsentPortn OBJECT-TYPE
	SYNTAX  EkiOnOff
	MAX-ACCESS read-only
	STATUS current
	DESCRIPTION
        "
        Channel Absent 87 :This OID indicates
        that an in service channel is absent
        on the Optical Power Monitoring
        input<Help> This alarm indicates
        that an in service channel is absent
        on the Optical Power Monitoring
        input <Condtype> CHANNEL87_ABSENT_1
        <Probcause> informationMissing
         (65) <Alarmtype> equipmentAlarm
        (5) <Polarity> (2)
        "
	::= { pmopm2Almchannel87PortEntry 2 }


--- *********************************************************
---     TABLE for the pmopm2Almchannel88Port articles
--- *********************************************************

pmopm2Almchannel88PortTable OBJECT-TYPE
	SYNTAX  SEQUENCE OF Pmopm2Almchannel88PortEntry
	MAX-ACCESS not-accessible
	STATUS current
	DESCRIPTION
        "
        List of pmopm2Almchannel88Port
        Article
        "
	::= { pmopm2AlmClientCrit 190 }


pmopm2Almchannel88PortEntry OBJECT-TYPE
	SYNTAX Pmopm2Almchannel88PortEntry
	MAX-ACCESS not-accessible
	STATUS current
	DESCRIPTION
        "
        Row definition for the pmopm2Almchannel88Port
        table
        "
	INDEX   { pmopm2Almchannel88PortIndex }
	::= { pmopm2Almchannel88PortTable 1 }


Pmopm2Almchannel88PortEntry ::=
	SEQUENCE {
	pmopm2Almchannel88PortIndex
		INTEGER,
	pmopm2AlmChannel88OosPortn
		EkiOnOff,
	pmopm2AlmChannel88PowerHighPortn
		EkiOnOff,
	pmopm2AlmChannel88PowerLowPortn
		EkiOnOff,
	pmopm2AlmChannel88BalancedPortn
		EkiOnOff,
	pmopm2AlmChannel88MismatchPortn
		EkiOnOff,
	pmopm2AlmChannel88AbsentPortn
		EkiOnOff
	}


pmopm2Almchannel88PortIndex OBJECT-TYPE
	SYNTAX  INTEGER(0..128)
	MAX-ACCESS  read-only
	STATUS current
	DESCRIPTION
        "
        Index definition for the pmopm2Almchannel88Port
        table
        "
	::= { pmopm2Almchannel88PortEntry 1 }


pmopm2AlmChannel88OosPortn OBJECT-TYPE
	SYNTAX  EkiOnOff
	MAX-ACCESS read-only
	STATUS current
	DESCRIPTION
        "
        Channel Out Of Service 88 :This
        OID indicates that the channel
         is out of service  <Help> This
        alarm indicates that the channel
        is in service <Condtype> CHANNEL88_OOS_1
        <Probcause> informationalStatus(1000)
        <Alarmtype> other (1) <Polarity>
        (2)
        "
	::= { pmopm2Almchannel88PortEntry 7 }


pmopm2AlmChannel88PowerHighPortn OBJECT-TYPE
	SYNTAX  EkiOnOff
	MAX-ACCESS read-only
	STATUS current
	DESCRIPTION
        "
        Channel Power High 88 :This OID
        indicates that the power of the
        channel is higher than the configured
        threshold<Help> This alarm indicates
        that the power of the channel is
        higher than the configured threshold
        <Condtype> CHANNEL88_POWER_HIGH_1
        <Probcause> degradedSignal (13)
        <Alarmtype> equipmentAlarm <Polarity>
        (2)
        "
	::= { pmopm2Almchannel88PortEntry 6 }


pmopm2AlmChannel88PowerLowPortn OBJECT-TYPE
	SYNTAX  EkiOnOff
	MAX-ACCESS read-only
	STATUS current
	DESCRIPTION
        "
        Channel Power Low 88 :This OID
        indicates that the power of the
        channel is lower than the configured
        threshold<Help> This alarm indicates
        that the power of the channel is
        lower than the configured threshold
        <Condtype> CHANNEL88_POWER_LOW_1
        <Probcause> degradedSignal (13)
        <Alarmtype> equipmentAlarm <Polarity>
        (2)
        "
	::= { pmopm2Almchannel88PortEntry 5 }


pmopm2AlmChannel88BalancedPortn OBJECT-TYPE
	SYNTAX  EkiOnOff
	MAX-ACCESS read-only
	STATUS current
	DESCRIPTION
        "
        Channel Balanced 88 :This OID
         indicates that an in service channel
        is balanced by the Ekinops auto
        turn up application<Help> This
         status indicates that an in service
        channel is balanced by the Ekinops
        auto turn up application <Condtype>
        CHANNEL88_BALANCED_1 <Probcause>
        informationalStatus(1000) <Alarmtype>
        other (1) <Polarity> (2)
        "
	::= { pmopm2Almchannel88PortEntry 4 }


pmopm2AlmChannel88MismatchPortn OBJECT-TYPE
	SYNTAX  EkiOnOff
	MAX-ACCESS read-only
	STATUS current
	DESCRIPTION
        "
        Channel Mismatch 88 :This OID
         indicates that an out of service
        channel is detected on the Optical
        Power Monitoring input<Help> This
        alarm indicates that an out of
         service channel is detected on
        the Optical Power Monitoring input
        <Condtype> CHANNEL88_MISMATCH_1
        <Probcause> unexpectedInformation
        (75) <Alarmtype> equipmentAlarm
        <Polarity> (2)
        "
	::= { pmopm2Almchannel88PortEntry 3 }


pmopm2AlmChannel88AbsentPortn OBJECT-TYPE
	SYNTAX  EkiOnOff
	MAX-ACCESS read-only
	STATUS current
	DESCRIPTION
        "
        Channel Absent 88 :This OID indicates
        that an in service channel is absent
        on the Optical Power Monitoring
        input<Help> This alarm indicates
        that an in service channel is absent
        on the Optical Power Monitoring
        input <Condtype> CHANNEL88_ABSENT_1
        <Probcause> informationMissing
         (65) <Alarmtype> equipmentAlarm
        (5) <Polarity> (2)
        "
	::= { pmopm2Almchannel88PortEntry 2 }


--- *********************************************************
---     TABLE for the pmopm2Almchannel89Port articles
--- *********************************************************

pmopm2Almchannel89PortTable OBJECT-TYPE
	SYNTAX  SEQUENCE OF Pmopm2Almchannel89PortEntry
	MAX-ACCESS not-accessible
	STATUS current
	DESCRIPTION
        "
        List of pmopm2Almchannel89Port
        Article
        "
	::= { pmopm2AlmClientCrit 192 }


pmopm2Almchannel89PortEntry OBJECT-TYPE
	SYNTAX Pmopm2Almchannel89PortEntry
	MAX-ACCESS not-accessible
	STATUS current
	DESCRIPTION
        "
        Row definition for the pmopm2Almchannel89Port
        table
        "
	INDEX   { pmopm2Almchannel89PortIndex }
	::= { pmopm2Almchannel89PortTable 1 }


Pmopm2Almchannel89PortEntry ::=
	SEQUENCE {
	pmopm2Almchannel89PortIndex
		INTEGER,
	pmopm2AlmChannel89OosPortn
		EkiOnOff,
	pmopm2AlmChannel89PowerHighPortn
		EkiOnOff,
	pmopm2AlmChannel89PowerLowPortn
		EkiOnOff,
	pmopm2AlmChannel89BalancedPortn
		EkiOnOff,
	pmopm2AlmChannel89MismatchPortn
		EkiOnOff,
	pmopm2AlmChannel89AbsentPortn
		EkiOnOff
	}


pmopm2Almchannel89PortIndex OBJECT-TYPE
	SYNTAX  INTEGER(0..128)
	MAX-ACCESS  read-only
	STATUS current
	DESCRIPTION
        "
        Index definition for the pmopm2Almchannel89Port
        table
        "
	::= { pmopm2Almchannel89PortEntry 1 }


pmopm2AlmChannel89OosPortn OBJECT-TYPE
	SYNTAX  EkiOnOff
	MAX-ACCESS read-only
	STATUS current
	DESCRIPTION
        "
        Channel Out Of Service 89 :This
        OID indicates that the channel
         is out of service  <Help> This
        alarm indicates that the channel
        is in service <Condtype> CHANNEL89_OOS_1
        <Probcause> informationalStatus(1000)
        <Alarmtype> other (1) <Polarity>
        (2)
        "
	::= { pmopm2Almchannel89PortEntry 7 }


pmopm2AlmChannel89PowerHighPortn OBJECT-TYPE
	SYNTAX  EkiOnOff
	MAX-ACCESS read-only
	STATUS current
	DESCRIPTION
        "
        Channel Power High 89 :This OID
        indicates that the power of the
        channel is higher than the configured
        threshold<Help> This alarm indicates
        that the power of the channel is
        higher than the configured threshold
        <Condtype> CHANNEL89_POWER_HIGH_1
        <Probcause> degradedSignal (13)
        <Alarmtype> equipmentAlarm <Polarity>
        (2)
        "
	::= { pmopm2Almchannel89PortEntry 6 }


pmopm2AlmChannel89PowerLowPortn OBJECT-TYPE
	SYNTAX  EkiOnOff
	MAX-ACCESS read-only
	STATUS current
	DESCRIPTION
        "
        Channel Power Low 89 :This OID
        indicates that the power of the
        channel is lower than the configured
        threshold<Help> This alarm indicates
        that the power of the channel is
        lower than the configured threshold
        <Condtype> CHANNEL89_POWER_LOW_1
        <Probcause> degradedSignal (13)
        <Alarmtype> equipmentAlarm <Polarity>
        (2)
        "
	::= { pmopm2Almchannel89PortEntry 5 }


pmopm2AlmChannel89BalancedPortn OBJECT-TYPE
	SYNTAX  EkiOnOff
	MAX-ACCESS read-only
	STATUS current
	DESCRIPTION
        "
        Channel Balanced 89 :This OID
         indicates that an in service channel
        is balanced by the Ekinops auto
        turn up application<Help> This
         status indicates that an in service
        channel is balanced by the Ekinops
        auto turn up application <Condtype>
        CHANNEL89_BALANCED_1 <Probcause>
        informationalStatus(1000) <Alarmtype>
        other (1) <Polarity> (2)
        "
	::= { pmopm2Almchannel89PortEntry 4 }


pmopm2AlmChannel89MismatchPortn OBJECT-TYPE
	SYNTAX  EkiOnOff
	MAX-ACCESS read-only
	STATUS current
	DESCRIPTION
        "
        Channel Mismatch 89 :This OID
         indicates that an out of service
        channel is detected on the Optical
        Power Monitoring input<Help> This
        alarm indicates that an out of
         service channel is detected on
        the Optical Power Monitoring input
        <Condtype> CHANNEL89_MISMATCH_1
        <Probcause> unexpectedInformation
        (75) <Alarmtype> equipmentAlarm
        <Polarity> (2)
        "
	::= { pmopm2Almchannel89PortEntry 3 }


pmopm2AlmChannel89AbsentPortn OBJECT-TYPE
	SYNTAX  EkiOnOff
	MAX-ACCESS read-only
	STATUS current
	DESCRIPTION
        "
        Channel Absent 89 :This OID indicates
        that an in service channel is absent
        on the Optical Power Monitoring
        input<Help> This alarm indicates
        that an in service channel is absent
        on the Optical Power Monitoring
        input <Condtype> CHANNEL89_ABSENT_1
        <Probcause> informationMissing
         (65) <Alarmtype> equipmentAlarm
        (5) <Polarity> (2)
        "
	::= { pmopm2Almchannel89PortEntry 2 }


--- *********************************************************
---     TABLE for the pmopm2Almchannel90Port articles
--- *********************************************************

pmopm2Almchannel90PortTable OBJECT-TYPE
	SYNTAX  SEQUENCE OF Pmopm2Almchannel90PortEntry
	MAX-ACCESS not-accessible
	STATUS current
	DESCRIPTION
        "
        List of pmopm2Almchannel90Port
        Article
        "
	::= { pmopm2AlmClientCrit 194 }


pmopm2Almchannel90PortEntry OBJECT-TYPE
	SYNTAX Pmopm2Almchannel90PortEntry
	MAX-ACCESS not-accessible
	STATUS current
	DESCRIPTION
        "
        Row definition for the pmopm2Almchannel90Port
        table
        "
	INDEX   { pmopm2Almchannel90PortIndex }
	::= { pmopm2Almchannel90PortTable 1 }


Pmopm2Almchannel90PortEntry ::=
	SEQUENCE {
	pmopm2Almchannel90PortIndex
		INTEGER,
	pmopm2AlmChannel90OosPortn
		EkiOnOff,
	pmopm2AlmChannel90PowerHighPortn
		EkiOnOff,
	pmopm2AlmChannel90PowerLowPortn
		EkiOnOff,
	pmopm2AlmChannel90BalancedPortn
		EkiOnOff,
	pmopm2AlmChannel90MismatchPortn
		EkiOnOff,
	pmopm2AlmChannel90AbsentPortn
		EkiOnOff
	}


pmopm2Almchannel90PortIndex OBJECT-TYPE
	SYNTAX  INTEGER(0..128)
	MAX-ACCESS  read-only
	STATUS current
	DESCRIPTION
        "
        Index definition for the pmopm2Almchannel90Port
        table
        "
	::= { pmopm2Almchannel90PortEntry 1 }


pmopm2AlmChannel90OosPortn OBJECT-TYPE
	SYNTAX  EkiOnOff
	MAX-ACCESS read-only
	STATUS current
	DESCRIPTION
        "
        Channel Out Of Service 90 :This
        OID indicates that the channel
         is out of service  <Help> This
        alarm indicates that the channel
        is in service <Condtype> CHANNEL90_OOS_1
        <Probcause> informationalStatus(1000)
        <Alarmtype> other (1) <Polarity>
        (2)
        "
	::= { pmopm2Almchannel90PortEntry 7 }


pmopm2AlmChannel90PowerHighPortn OBJECT-TYPE
	SYNTAX  EkiOnOff
	MAX-ACCESS read-only
	STATUS current
	DESCRIPTION
        "
        Channel Power High 90 :This OID
        indicates that the power of the
        channel is higher than the configured
        threshold<Help> This alarm indicates
        that the power of the channel is
        higher than the configured threshold
        <Condtype> CHANNEL90_POWER_HIGH_1
        <Probcause> degradedSignal (13)
        <Alarmtype> equipmentAlarm <Polarity>
        (2)
        "
	::= { pmopm2Almchannel90PortEntry 6 }


pmopm2AlmChannel90PowerLowPortn OBJECT-TYPE
	SYNTAX  EkiOnOff
	MAX-ACCESS read-only
	STATUS current
	DESCRIPTION
        "
        Channel Power Low 90 :This OID
        indicates that the power of the
        channel is lower than the configured
        threshold<Help> This alarm indicates
        that the power of the channel is
        lower than the configured threshold
        <Condtype> CHANNEL90_POWER_LOW_1
        <Probcause> degradedSignal (13)
        <Alarmtype> equipmentAlarm <Polarity>
        (2)
        "
	::= { pmopm2Almchannel90PortEntry 5 }


pmopm2AlmChannel90BalancedPortn OBJECT-TYPE
	SYNTAX  EkiOnOff
	MAX-ACCESS read-only
	STATUS current
	DESCRIPTION
        "
        Channel Balanced 90 :This OID
         indicates that an in service channel
        is balanced by the Ekinops auto
        turn up application<Help> This
         status indicates that an in service
        channel is balanced by the Ekinops
        auto turn up application <Condtype>
        CHANNEL90_BALANCED_1 <Probcause>
        informationalStatus(1000) <Alarmtype>
        other (1) <Polarity> (2)
        "
	::= { pmopm2Almchannel90PortEntry 4 }


pmopm2AlmChannel90MismatchPortn OBJECT-TYPE
	SYNTAX  EkiOnOff
	MAX-ACCESS read-only
	STATUS current
	DESCRIPTION
        "
        Channel Mismatch 90 :This OID
         indicates that an out of service
        channel is detected on the Optical
        Power Monitoring input<Help> This
        alarm indicates that an out of
         service channel is detected on
        the Optical Power Monitoring input
        <Condtype> CHANNEL90_MISMATCH_1
        <Probcause> unexpectedInformation
        (75) <Alarmtype> equipmentAlarm
        <Polarity> (2)
        "
	::= { pmopm2Almchannel90PortEntry 3 }


pmopm2AlmChannel90AbsentPortn OBJECT-TYPE
	SYNTAX  EkiOnOff
	MAX-ACCESS read-only
	STATUS current
	DESCRIPTION
        "
        Channel Absent 90 :This OID indicates
        that an in service channel is absent
        on the Optical Power Monitoring
        input<Help> This alarm indicates
        that an in service channel is absent
        on the Optical Power Monitoring
        input <Condtype> CHANNEL90_ABSENT_1
        <Probcause> informationMissing
         (65) <Alarmtype> equipmentAlarm
        (5) <Polarity> (2)
        "
	::= { pmopm2Almchannel90PortEntry 2 }


--- *********************************************************
---     TABLE for the pmopm2Almchannel91Port articles
--- *********************************************************

pmopm2Almchannel91PortTable OBJECT-TYPE
	SYNTAX  SEQUENCE OF Pmopm2Almchannel91PortEntry
	MAX-ACCESS not-accessible
	STATUS current
	DESCRIPTION
        "
        List of pmopm2Almchannel91Port
        Article
        "
	::= { pmopm2AlmClientCrit 196 }


pmopm2Almchannel91PortEntry OBJECT-TYPE
	SYNTAX Pmopm2Almchannel91PortEntry
	MAX-ACCESS not-accessible
	STATUS current
	DESCRIPTION
        "
        Row definition for the pmopm2Almchannel91Port
        table
        "
	INDEX   { pmopm2Almchannel91PortIndex }
	::= { pmopm2Almchannel91PortTable 1 }


Pmopm2Almchannel91PortEntry ::=
	SEQUENCE {
	pmopm2Almchannel91PortIndex
		INTEGER,
	pmopm2AlmChannel91OosPortn
		EkiOnOff,
	pmopm2AlmChannel91PowerHighPortn
		EkiOnOff,
	pmopm2AlmChannel91PowerLowPortn
		EkiOnOff,
	pmopm2AlmChannel91BalancedPortn
		EkiOnOff,
	pmopm2AlmChannel91MismatchPortn
		EkiOnOff,
	pmopm2AlmChannel91AbsentPortn
		EkiOnOff
	}


pmopm2Almchannel91PortIndex OBJECT-TYPE
	SYNTAX  INTEGER(0..128)
	MAX-ACCESS  read-only
	STATUS current
	DESCRIPTION
        "
        Index definition for the pmopm2Almchannel91Port
        table
        "
	::= { pmopm2Almchannel91PortEntry 1 }


pmopm2AlmChannel91OosPortn OBJECT-TYPE
	SYNTAX  EkiOnOff
	MAX-ACCESS read-only
	STATUS current
	DESCRIPTION
        "
        Channel Out Of Service 91 :This
        OID indicates that the channel
         is out of service  <Help> This
        alarm indicates that the channel
        is in service <Condtype> CHANNEL91_OOS_1
        <Probcause> informationalStatus(1000)
        <Alarmtype> other (1) <Polarity>
        (2)
        "
	::= { pmopm2Almchannel91PortEntry 7 }


pmopm2AlmChannel91PowerHighPortn OBJECT-TYPE
	SYNTAX  EkiOnOff
	MAX-ACCESS read-only
	STATUS current
	DESCRIPTION
        "
        Channel Power High 91 :This OID
        indicates that the power of the
        channel is higher than the configured
        threshold<Help> This alarm indicates
        that the power of the channel is
        higher than the configured threshold
        <Condtype> CHANNEL91_POWER_HIGH_1
        <Probcause> degradedSignal (13)
        <Alarmtype> equipmentAlarm <Polarity>
        (2)
        "
	::= { pmopm2Almchannel91PortEntry 6 }


pmopm2AlmChannel91PowerLowPortn OBJECT-TYPE
	SYNTAX  EkiOnOff
	MAX-ACCESS read-only
	STATUS current
	DESCRIPTION
        "
        Channel Power Low 91 :This OID
        indicates that the power of the
        channel is lower than the configured
        threshold<Help> This alarm indicates
        that the power of the channel is
        lower than the configured threshold
        <Condtype> CHANNEL91_POWER_LOW_1
        <Probcause> degradedSignal (13)
        <Alarmtype> equipmentAlarm <Polarity>
        (2)
        "
	::= { pmopm2Almchannel91PortEntry 5 }


pmopm2AlmChannel91BalancedPortn OBJECT-TYPE
	SYNTAX  EkiOnOff
	MAX-ACCESS read-only
	STATUS current
	DESCRIPTION
        "
        Channel Balanced 91 :This OID
         indicates that an in service channel
        is balanced by the Ekinops auto
        turn up application<Help> This
         status indicates that an in service
        channel is balanced by the Ekinops
        auto turn up application <Condtype>
        CHANNEL91_BALANCED_1 <Probcause>
        informationalStatus(1000) <Alarmtype>
        other (1) <Polarity> (2)
        "
	::= { pmopm2Almchannel91PortEntry 4 }


pmopm2AlmChannel91MismatchPortn OBJECT-TYPE
	SYNTAX  EkiOnOff
	MAX-ACCESS read-only
	STATUS current
	DESCRIPTION
        "
        Channel Mismatch 91 :This OID
         indicates that an out of service
        channel is detected on the Optical
        Power Monitoring input<Help> This
        alarm indicates that an out of
         service channel is detected on
        the Optical Power Monitoring input
        <Condtype> CHANNEL91_MISMATCH_1
        <Probcause> unexpectedInformation
        (75) <Alarmtype> equipmentAlarm
        <Polarity> (2)
        "
	::= { pmopm2Almchannel91PortEntry 3 }


pmopm2AlmChannel91AbsentPortn OBJECT-TYPE
	SYNTAX  EkiOnOff
	MAX-ACCESS read-only
	STATUS current
	DESCRIPTION
        "
        Channel Absent 91 :This OID indicates
        that an in service channel is absent
        on the Optical Power Monitoring
        input<Help> This alarm indicates
        that an in service channel is absent
        on the Optical Power Monitoring
        input <Condtype> CHANNEL91_ABSENT_1
        <Probcause> informationMissing
         (65) <Alarmtype> equipmentAlarm
        (5) <Polarity> (2)
        "
	::= { pmopm2Almchannel91PortEntry 2 }


--- *********************************************************
---     TABLE for the pmopm2Almchannel92Port articles
--- *********************************************************

pmopm2Almchannel92PortTable OBJECT-TYPE
	SYNTAX  SEQUENCE OF Pmopm2Almchannel92PortEntry
	MAX-ACCESS not-accessible
	STATUS current
	DESCRIPTION
        "
        List of pmopm2Almchannel92Port
        Article
        "
	::= { pmopm2AlmClientCrit 198 }


pmopm2Almchannel92PortEntry OBJECT-TYPE
	SYNTAX Pmopm2Almchannel92PortEntry
	MAX-ACCESS not-accessible
	STATUS current
	DESCRIPTION
        "
        Row definition for the pmopm2Almchannel92Port
        table
        "
	INDEX   { pmopm2Almchannel92PortIndex }
	::= { pmopm2Almchannel92PortTable 1 }


Pmopm2Almchannel92PortEntry ::=
	SEQUENCE {
	pmopm2Almchannel92PortIndex
		INTEGER,
	pmopm2AlmChannel92OosPortn
		EkiOnOff,
	pmopm2AlmChannel92PowerHighPortn
		EkiOnOff,
	pmopm2AlmChannel92PowerLowPortn
		EkiOnOff,
	pmopm2AlmChannel92BalancedPortn
		EkiOnOff,
	pmopm2AlmChannel92MismatchPortn
		EkiOnOff,
	pmopm2AlmChannel92AbsentPortn
		EkiOnOff
	}


pmopm2Almchannel92PortIndex OBJECT-TYPE
	SYNTAX  INTEGER(0..128)
	MAX-ACCESS  read-only
	STATUS current
	DESCRIPTION
        "
        Index definition for the pmopm2Almchannel92Port
        table
        "
	::= { pmopm2Almchannel92PortEntry 1 }


pmopm2AlmChannel92OosPortn OBJECT-TYPE
	SYNTAX  EkiOnOff
	MAX-ACCESS read-only
	STATUS current
	DESCRIPTION
        "
        Channel Out Of Service 92 :This
        OID indicates that the channel
         is out of service  <Help> This
        alarm indicates that the channel
        is in service <Condtype> CHANNEL92_OOS_1
        <Probcause> informationalStatus(1000)
        <Alarmtype> other (1) <Polarity>
        (2)
        "
	::= { pmopm2Almchannel92PortEntry 7 }


pmopm2AlmChannel92PowerHighPortn OBJECT-TYPE
	SYNTAX  EkiOnOff
	MAX-ACCESS read-only
	STATUS current
	DESCRIPTION
        "
        Channel Power High 92 :This OID
        indicates that the power of the
        channel is higher than the configured
        threshold<Help> This alarm indicates
        that the power of the channel is
        higher than the configured threshold
        <Condtype> CHANNEL92_POWER_HIGH_1
        <Probcause> degradedSignal (13)
        <Alarmtype> equipmentAlarm <Polarity>
        (2)
        "
	::= { pmopm2Almchannel92PortEntry 6 }


pmopm2AlmChannel92PowerLowPortn OBJECT-TYPE
	SYNTAX  EkiOnOff
	MAX-ACCESS read-only
	STATUS current
	DESCRIPTION
        "
        Channel Power Low 92 :This OID
        indicates that the power of the
        channel is lower than the configured
        threshold<Help> This alarm indicates
        that the power of the channel is
        lower than the configured threshold
        <Condtype> CHANNEL92_POWER_LOW_1
        <Probcause> degradedSignal (13)
        <Alarmtype> equipmentAlarm <Polarity>
        (2)
        "
	::= { pmopm2Almchannel92PortEntry 5 }


pmopm2AlmChannel92BalancedPortn OBJECT-TYPE
	SYNTAX  EkiOnOff
	MAX-ACCESS read-only
	STATUS current
	DESCRIPTION
        "
        Channel Balanced 92 :This OID
         indicates that an in service channel
        is balanced by the Ekinops auto
        turn up application<Help> This
         status indicates that an in service
        channel is balanced by the Ekinops
        auto turn up application <Condtype>
        CHANNEL92_BALANCED_1 <Probcause>
        informationalStatus(1000) <Alarmtype>
        other (1) <Polarity> (2)
        "
	::= { pmopm2Almchannel92PortEntry 4 }


pmopm2AlmChannel92MismatchPortn OBJECT-TYPE
	SYNTAX  EkiOnOff
	MAX-ACCESS read-only
	STATUS current
	DESCRIPTION
        "
        Channel Mismatch 92 :This OID
         indicates that an out of service
        channel is detected on the Optical
        Power Monitoring input<Help> This
        alarm indicates that an out of
         service channel is detected on
        the Optical Power Monitoring input
        <Condtype> CHANNEL92_MISMATCH_1
        <Probcause> unexpectedInformation
        (75) <Alarmtype> equipmentAlarm
        <Polarity> (2)
        "
	::= { pmopm2Almchannel92PortEntry 3 }


pmopm2AlmChannel92AbsentPortn OBJECT-TYPE
	SYNTAX  EkiOnOff
	MAX-ACCESS read-only
	STATUS current
	DESCRIPTION
        "
        Channel Absent 92 :This OID indicates
        that an in service channel is absent
        on the Optical Power Monitoring
        input<Help> This alarm indicates
        that an in service channel is absent
        on the Optical Power Monitoring
        input <Condtype> CHANNEL92_ABSENT_1
        <Probcause> informationMissing
         (65) <Alarmtype> equipmentAlarm
        (5) <Polarity> (2)
        "
	::= { pmopm2Almchannel92PortEntry 2 }


--- *********************************************************
---     TABLE for the pmopm2Almchannel93Port articles
--- *********************************************************

pmopm2Almchannel93PortTable OBJECT-TYPE
	SYNTAX  SEQUENCE OF Pmopm2Almchannel93PortEntry
	MAX-ACCESS not-accessible
	STATUS current
	DESCRIPTION
        "
        List of pmopm2Almchannel93Port
        Article
        "
	::= { pmopm2AlmClientCrit 200 }


pmopm2Almchannel93PortEntry OBJECT-TYPE
	SYNTAX Pmopm2Almchannel93PortEntry
	MAX-ACCESS not-accessible
	STATUS current
	DESCRIPTION
        "
        Row definition for the pmopm2Almchannel93Port
        table
        "
	INDEX   { pmopm2Almchannel93PortIndex }
	::= { pmopm2Almchannel93PortTable 1 }


Pmopm2Almchannel93PortEntry ::=
	SEQUENCE {
	pmopm2Almchannel93PortIndex
		INTEGER,
	pmopm2AlmChannel93OosPortn
		EkiOnOff,
	pmopm2AlmChannel93PowerHighPortn
		EkiOnOff,
	pmopm2AlmChannel93PowerLowPortn
		EkiOnOff,
	pmopm2AlmChannel93BalancedPortn
		EkiOnOff,
	pmopm2AlmChannel93MismatchPortn
		EkiOnOff,
	pmopm2AlmChannel93AbsentPortn
		EkiOnOff
	}


pmopm2Almchannel93PortIndex OBJECT-TYPE
	SYNTAX  INTEGER(0..128)
	MAX-ACCESS  read-only
	STATUS current
	DESCRIPTION
        "
        Index definition for the pmopm2Almchannel93Port
        table
        "
	::= { pmopm2Almchannel93PortEntry 1 }


pmopm2AlmChannel93OosPortn OBJECT-TYPE
	SYNTAX  EkiOnOff
	MAX-ACCESS read-only
	STATUS current
	DESCRIPTION
        "
        Channel Out Of Service 93 :This
        OID indicates that the channel
         is out of service  <Help> This
        alarm indicates that the channel
        is in service <Condtype> CHANNEL93_OOS_1
        <Probcause> informationalStatus(1000)
        <Alarmtype> other (1) <Polarity>
        (2)
        "
	::= { pmopm2Almchannel93PortEntry 7 }


pmopm2AlmChannel93PowerHighPortn OBJECT-TYPE
	SYNTAX  EkiOnOff
	MAX-ACCESS read-only
	STATUS current
	DESCRIPTION
        "
        Channel Power High 93 :This OID
        indicates that the power of the
        channel is higher than the configured
        threshold<Help> This alarm indicates
        that the power of the channel is
        higher than the configured threshold
        <Condtype> CHANNEL93_POWER_HIGH_1
        <Probcause> degradedSignal (13)
        <Alarmtype> equipmentAlarm <Polarity>
        (2)
        "
	::= { pmopm2Almchannel93PortEntry 6 }


pmopm2AlmChannel93PowerLowPortn OBJECT-TYPE
	SYNTAX  EkiOnOff
	MAX-ACCESS read-only
	STATUS current
	DESCRIPTION
        "
        Channel Power Low 93 :This OID
        indicates that the power of the
        channel is lower than the configured
        threshold<Help> This alarm indicates
        that the power of the channel is
        lower than the configured threshold
        <Condtype> CHANNEL93_POWER_LOW_1
        <Probcause> degradedSignal (13)
        <Alarmtype> equipmentAlarm <Polarity>
        (2)
        "
	::= { pmopm2Almchannel93PortEntry 5 }


pmopm2AlmChannel93BalancedPortn OBJECT-TYPE
	SYNTAX  EkiOnOff
	MAX-ACCESS read-only
	STATUS current
	DESCRIPTION
        "
        Channel Balanced 93 :This OID
         indicates that an in service channel
        is balanced by the Ekinops auto
        turn up application<Help> This
         status indicates that an in service
        channel is balanced by the Ekinops
        auto turn up application <Condtype>
        CHANNEL93_BALANCED_1 <Probcause>
        informationalStatus(1000) <Alarmtype>
        other (1) <Polarity> (2)
        "
	::= { pmopm2Almchannel93PortEntry 4 }


pmopm2AlmChannel93MismatchPortn OBJECT-TYPE
	SYNTAX  EkiOnOff
	MAX-ACCESS read-only
	STATUS current
	DESCRIPTION
        "
        Channel Mismatch 93 :This OID
         indicates that an out of service
        channel is detected on the Optical
        Power Monitoring input<Help> This
        alarm indicates that an out of
         service channel is detected on
        the Optical Power Monitoring input
        <Condtype> CHANNEL93_MISMATCH_1
        <Probcause> unexpectedInformation
        (75) <Alarmtype> equipmentAlarm
        <Polarity> (2)
        "
	::= { pmopm2Almchannel93PortEntry 3 }


pmopm2AlmChannel93AbsentPortn OBJECT-TYPE
	SYNTAX  EkiOnOff
	MAX-ACCESS read-only
	STATUS current
	DESCRIPTION
        "
        Channel Absent 93 :This OID indicates
        that an in service channel is absent
        on the Optical Power Monitoring
        input<Help> This alarm indicates
        that an in service channel is absent
        on the Optical Power Monitoring
        input <Condtype> CHANNEL93_ABSENT_1
        <Probcause> informationMissing
         (65) <Alarmtype> equipmentAlarm
        (5) <Polarity> (2)
        "
	::= { pmopm2Almchannel93PortEntry 2 }


--- *********************************************************
---     TABLE for the pmopm2Almchannel94Port articles
--- *********************************************************

pmopm2Almchannel94PortTable OBJECT-TYPE
	SYNTAX  SEQUENCE OF Pmopm2Almchannel94PortEntry
	MAX-ACCESS not-accessible
	STATUS current
	DESCRIPTION
        "
        List of pmopm2Almchannel94Port
        Article
        "
	::= { pmopm2AlmClientCrit 202 }


pmopm2Almchannel94PortEntry OBJECT-TYPE
	SYNTAX Pmopm2Almchannel94PortEntry
	MAX-ACCESS not-accessible
	STATUS current
	DESCRIPTION
        "
        Row definition for the pmopm2Almchannel94Port
        table
        "
	INDEX   { pmopm2Almchannel94PortIndex }
	::= { pmopm2Almchannel94PortTable 1 }


Pmopm2Almchannel94PortEntry ::=
	SEQUENCE {
	pmopm2Almchannel94PortIndex
		INTEGER,
	pmopm2AlmChannel94OosPortn
		EkiOnOff,
	pmopm2AlmChannel94PowerHighPortn
		EkiOnOff,
	pmopm2AlmChannel94PowerLowPortn
		EkiOnOff,
	pmopm2AlmChannel94BalancedPortn
		EkiOnOff,
	pmopm2AlmChannel94MismatchPortn
		EkiOnOff,
	pmopm2AlmChannel94AbsentPortn
		EkiOnOff
	}


pmopm2Almchannel94PortIndex OBJECT-TYPE
	SYNTAX  INTEGER(0..128)
	MAX-ACCESS  read-only
	STATUS current
	DESCRIPTION
        "
        Index definition for the pmopm2Almchannel94Port
        table
        "
	::= { pmopm2Almchannel94PortEntry 1 }


pmopm2AlmChannel94OosPortn OBJECT-TYPE
	SYNTAX  EkiOnOff
	MAX-ACCESS read-only
	STATUS current
	DESCRIPTION
        "
        Channel Out Of Service 94 :This
        OID indicates that the channel
         is out of service  <Help> This
        alarm indicates that the channel
        is in service <Condtype> CHANNEL94_OOS_1
        <Probcause> informationalStatus(1000)
        <Alarmtype> other (1) <Polarity>
        (2)
        "
	::= { pmopm2Almchannel94PortEntry 7 }


pmopm2AlmChannel94PowerHighPortn OBJECT-TYPE
	SYNTAX  EkiOnOff
	MAX-ACCESS read-only
	STATUS current
	DESCRIPTION
        "
        Channel Power High 94 :This OID
        indicates that the power of the
        channel is higher than the configured
        threshold<Help> This alarm indicates
        that the power of the channel is
        higher than the configured threshold
        <Condtype> CHANNEL94_POWER_HIGH_1
        <Probcause> degradedSignal (13)
        <Alarmtype> equipmentAlarm <Polarity>
        (2)
        "
	::= { pmopm2Almchannel94PortEntry 6 }


pmopm2AlmChannel94PowerLowPortn OBJECT-TYPE
	SYNTAX  EkiOnOff
	MAX-ACCESS read-only
	STATUS current
	DESCRIPTION
        "
        Channel Power Low 94 :This OID
        indicates that the power of the
        channel is lower than the configured
        threshold<Help> This alarm indicates
        that the power of the channel is
        lower than the configured threshold
        <Condtype> CHANNEL94_POWER_LOW_1
        <Probcause> degradedSignal (13)
        <Alarmtype> equipmentAlarm <Polarity>
        (2)
        "
	::= { pmopm2Almchannel94PortEntry 5 }


pmopm2AlmChannel94BalancedPortn OBJECT-TYPE
	SYNTAX  EkiOnOff
	MAX-ACCESS read-only
	STATUS current
	DESCRIPTION
        "
        Channel Balanced 94 :This OID
         indicates that an in service channel
        is balanced by the Ekinops auto
        turn up application<Help> This
         status indicates that an in service
        channel is balanced by the Ekinops
        auto turn up application <Condtype>
        CHANNEL94_BALANCED_1 <Probcause>
        informationalStatus(1000) <Alarmtype>
        other (1) <Polarity> (2)
        "
	::= { pmopm2Almchannel94PortEntry 4 }


pmopm2AlmChannel94MismatchPortn OBJECT-TYPE
	SYNTAX  EkiOnOff
	MAX-ACCESS read-only
	STATUS current
	DESCRIPTION
        "
        Channel Mismatch 94 :This OID
         indicates that an out of service
        channel is detected on the Optical
        Power Monitoring input<Help> This
        alarm indicates that an out of
         service channel is detected on
        the Optical Power Monitoring input
        <Condtype> CHANNEL94_MISMATCH_1
        <Probcause> unexpectedInformation
        (75) <Alarmtype> equipmentAlarm
        <Polarity> (2)
        "
	::= { pmopm2Almchannel94PortEntry 3 }


pmopm2AlmChannel94AbsentPortn OBJECT-TYPE
	SYNTAX  EkiOnOff
	MAX-ACCESS read-only
	STATUS current
	DESCRIPTION
        "
        Channel Absent 94 :This OID indicates
        that an in service channel is absent
        on the Optical Power Monitoring
        input<Help> This alarm indicates
        that an in service channel is absent
        on the Optical Power Monitoring
        input <Condtype> CHANNEL94_ABSENT_1
        <Probcause> informationMissing
         (65) <Alarmtype> equipmentAlarm
        (5) <Polarity> (2)
        "
	::= { pmopm2Almchannel94PortEntry 2 }


--- *********************************************************
---     TABLE for the pmopm2Almchannel95Port articles
--- *********************************************************

pmopm2Almchannel95PortTable OBJECT-TYPE
	SYNTAX  SEQUENCE OF Pmopm2Almchannel95PortEntry
	MAX-ACCESS not-accessible
	STATUS current
	DESCRIPTION
        "
        List of pmopm2Almchannel95Port
        Article
        "
	::= { pmopm2AlmClientCrit 204 }


pmopm2Almchannel95PortEntry OBJECT-TYPE
	SYNTAX Pmopm2Almchannel95PortEntry
	MAX-ACCESS not-accessible
	STATUS current
	DESCRIPTION
        "
        Row definition for the pmopm2Almchannel95Port
        table
        "
	INDEX   { pmopm2Almchannel95PortIndex }
	::= { pmopm2Almchannel95PortTable 1 }


Pmopm2Almchannel95PortEntry ::=
	SEQUENCE {
	pmopm2Almchannel95PortIndex
		INTEGER,
	pmopm2AlmChannel95OosPortn
		EkiOnOff,
	pmopm2AlmChannel95PowerHighPortn
		EkiOnOff,
	pmopm2AlmChannel95PowerLowPortn
		EkiOnOff,
	pmopm2AlmChannel95BalancedPortn
		EkiOnOff,
	pmopm2AlmChannel95MismatchPortn
		EkiOnOff,
	pmopm2AlmChannel95AbsentPortn
		EkiOnOff
	}


pmopm2Almchannel95PortIndex OBJECT-TYPE
	SYNTAX  INTEGER(0..128)
	MAX-ACCESS  read-only
	STATUS current
	DESCRIPTION
        "
        Index definition for the pmopm2Almchannel95Port
        table
        "
	::= { pmopm2Almchannel95PortEntry 1 }


pmopm2AlmChannel95OosPortn OBJECT-TYPE
	SYNTAX  EkiOnOff
	MAX-ACCESS read-only
	STATUS current
	DESCRIPTION
        "
        Channel Out Of Service 95 :This
        OID indicates that the channel
         is out of service  <Help> This
        alarm indicates that the channel
        is in service <Condtype> CHANNEL95_OOS_1
        <Probcause> informationalStatus(1000)
        <Alarmtype> other (1) <Polarity>
        (2)
        "
	::= { pmopm2Almchannel95PortEntry 7 }


pmopm2AlmChannel95PowerHighPortn OBJECT-TYPE
	SYNTAX  EkiOnOff
	MAX-ACCESS read-only
	STATUS current
	DESCRIPTION
        "
        Channel Power High 95 :This OID
        indicates that the power of the
        channel is higher than the configured
        threshold<Help> This alarm indicates
        that the power of the channel is
        higher than the configured threshold
        <Condtype> CHANNEL95_POWER_HIGH_1
        <Probcause> degradedSignal (13)
        <Alarmtype> equipmentAlarm <Polarity>
        (2)
        "
	::= { pmopm2Almchannel95PortEntry 6 }


pmopm2AlmChannel95PowerLowPortn OBJECT-TYPE
	SYNTAX  EkiOnOff
	MAX-ACCESS read-only
	STATUS current
	DESCRIPTION
        "
        Channel Power Low 95 :This OID
        indicates that the power of the
        channel is lower than the configured
        threshold<Help> This alarm indicates
        that the power of the channel is
        lower than the configured threshold
        <Condtype> CHANNEL95_POWER_LOW_1
        <Probcause> degradedSignal (13)
        <Alarmtype> equipmentAlarm <Polarity>
        (2)
        "
	::= { pmopm2Almchannel95PortEntry 5 }


pmopm2AlmChannel95BalancedPortn OBJECT-TYPE
	SYNTAX  EkiOnOff
	MAX-ACCESS read-only
	STATUS current
	DESCRIPTION
        "
        Channel Balanced 95 :This OID
         indicates that an in service channel
        is balanced by the Ekinops auto
        turn up application<Help> This
         status indicates that an in service
        channel is balanced by the Ekinops
        auto turn up application <Condtype>
        CHANNEL95_BALANCED_1 <Probcause>
        informationalStatus(1000) <Alarmtype>
        other (1) <Polarity> (2)
        "
	::= { pmopm2Almchannel95PortEntry 4 }


pmopm2AlmChannel95MismatchPortn OBJECT-TYPE
	SYNTAX  EkiOnOff
	MAX-ACCESS read-only
	STATUS current
	DESCRIPTION
        "
        Channel Mismatch 95 :This OID
         indicates that an out of service
        channel is detected on the Optical
        Power Monitoring input<Help> This
        alarm indicates that an out of
         service channel is detected on
        the Optical Power Monitoring input
        <Condtype> CHANNEL95_MISMATCH_1
        <Probcause> unexpectedInformation
        (75) <Alarmtype> equipmentAlarm
        <Polarity> (2)
        "
	::= { pmopm2Almchannel95PortEntry 3 }


pmopm2AlmChannel95AbsentPortn OBJECT-TYPE
	SYNTAX  EkiOnOff
	MAX-ACCESS read-only
	STATUS current
	DESCRIPTION
        "
        Channel Absent 95 :This OID indicates
        that an in service channel is absent
        on the Optical Power Monitoring
        input<Help> This alarm indicates
        that an in service channel is absent
        on the Optical Power Monitoring
        input <Condtype> CHANNEL95_ABSENT_1
        <Probcause> informationMissing
         (65) <Alarmtype> equipmentAlarm
        (5) <Polarity> (2)
        "
	::= { pmopm2Almchannel95PortEntry 2 }


--- *********************************************************
---     TABLE for the pmopm2Almchannel96Port articles
--- *********************************************************

pmopm2Almchannel96PortTable OBJECT-TYPE
	SYNTAX  SEQUENCE OF Pmopm2Almchannel96PortEntry
	MAX-ACCESS not-accessible
	STATUS current
	DESCRIPTION
        "
        List of pmopm2Almchannel96Port
        Article
        "
	::= { pmopm2AlmClientCrit 206 }


pmopm2Almchannel96PortEntry OBJECT-TYPE
	SYNTAX Pmopm2Almchannel96PortEntry
	MAX-ACCESS not-accessible
	STATUS current
	DESCRIPTION
        "
        Row definition for the pmopm2Almchannel96Port
        table
        "
	INDEX   { pmopm2Almchannel96PortIndex }
	::= { pmopm2Almchannel96PortTable 1 }


Pmopm2Almchannel96PortEntry ::=
	SEQUENCE {
	pmopm2Almchannel96PortIndex
		INTEGER,
	pmopm2AlmChannel96OosPortn
		EkiOnOff,
	pmopm2AlmChannel96PowerHighPortn
		EkiOnOff,
	pmopm2AlmChannel96PowerLowPortn
		EkiOnOff,
	pmopm2AlmChannel96BalancedPortn
		EkiOnOff,
	pmopm2AlmChannel96MismatchPortn
		EkiOnOff,
	pmopm2AlmChannel96AbsentPortn
		EkiOnOff
	}


pmopm2Almchannel96PortIndex OBJECT-TYPE
	SYNTAX  INTEGER(0..128)
	MAX-ACCESS  read-only
	STATUS current
	DESCRIPTION
        "
        Index definition for the pmopm2Almchannel96Port
        table
        "
	::= { pmopm2Almchannel96PortEntry 1 }


pmopm2AlmChannel96OosPortn OBJECT-TYPE
	SYNTAX  EkiOnOff
	MAX-ACCESS read-only
	STATUS current
	DESCRIPTION
        "
        Channel Out Of Service 96 :This
        OID indicates that the channel
         is out of service  <Help> This
        alarm indicates that the channel
        is in service <Condtype> CHANNEL96_OOS_1
        <Probcause> informationalStatus(1000)
        <Alarmtype> other (1) <Polarity>
        (2)
        "
	::= { pmopm2Almchannel96PortEntry 7 }


pmopm2AlmChannel96PowerHighPortn OBJECT-TYPE
	SYNTAX  EkiOnOff
	MAX-ACCESS read-only
	STATUS current
	DESCRIPTION
        "
        Channel Power High 96 :This OID
        indicates that the power of the
        channel is higher than the configured
        threshold<Help> This alarm indicates
        that the power of the channel is
        higher than the configured threshold
        <Condtype> CHANNEL96_POWER_HIGH_1
        <Probcause> degradedSignal (13)
        <Alarmtype> equipmentAlarm <Polarity>
        (2)
        "
	::= { pmopm2Almchannel96PortEntry 6 }


pmopm2AlmChannel96PowerLowPortn OBJECT-TYPE
	SYNTAX  EkiOnOff
	MAX-ACCESS read-only
	STATUS current
	DESCRIPTION
        "
        Channel Power Low 96 :This OID
        indicates that the power of the
        channel is lower than the configured
        threshold<Help> This alarm indicates
        that the power of the channel is
        lower than the configured threshold
        <Condtype> CHANNEL96_POWER_LOW_1
        <Probcause> degradedSignal (13)
        <Alarmtype> equipmentAlarm <Polarity>
        (2)
        "
	::= { pmopm2Almchannel96PortEntry 5 }


pmopm2AlmChannel96BalancedPortn OBJECT-TYPE
	SYNTAX  EkiOnOff
	MAX-ACCESS read-only
	STATUS current
	DESCRIPTION
        "
        Channel Balanced 96 :This OID
         indicates that an in service channel
        is balanced by the Ekinops auto
        turn up application<Help> This
         status indicates that an in service
        channel is balanced by the Ekinops
        auto turn up application <Condtype>
        CHANNEL96_BALANCED_1 <Probcause>
        informationalStatus(1000) <Alarmtype>
        other (1) <Polarity> (2)
        "
	::= { pmopm2Almchannel96PortEntry 4 }


pmopm2AlmChannel96MismatchPortn OBJECT-TYPE
	SYNTAX  EkiOnOff
	MAX-ACCESS read-only
	STATUS current
	DESCRIPTION
        "
        Channel Mismatch 96 :This OID
         indicates that an out of service
        channel is detected on the Optical
        Power Monitoring input<Help> This
        alarm indicates that an out of
         service channel is detected on
        the Optical Power Monitoring input
        <Condtype> CHANNEL96_MISMATCH_1
        <Probcause> unexpectedInformation
        (75) <Alarmtype> equipmentAlarm
        <Polarity> (2)
        "
	::= { pmopm2Almchannel96PortEntry 3 }


pmopm2AlmChannel96AbsentPortn OBJECT-TYPE
	SYNTAX  EkiOnOff
	MAX-ACCESS read-only
	STATUS current
	DESCRIPTION
        "
        Channel Absent 96 :This OID indicates
        that an in service channel is absent
        on the Optical Power Monitoring
        input<Help> This alarm indicates
        that an in service channel is absent
        on the Optical Power Monitoring
        input <Condtype> CHANNEL96_ABSENT_1
        <Probcause> informationMissing
         (65) <Alarmtype> equipmentAlarm
        (5) <Polarity> (2)
        "
	::= { pmopm2Almchannel96PortEntry 2 }







--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pmopm2CtrlconfMgnt1 OBJECT IDENTIFIER ::= { pmopm2CtrlOther 1 }




pmopm2CtrlConf2Clear1 OBJECT-TYPE
	  SYNTAX EkiOnOff
	  MAX-ACCESS read-write
	  STATUS current
	  DESCRIPTION
        "
        Clear Configuration Tables :This
        OID clears the configuration tables
        from configuration2 in the flash.
         <Help>  This control restores
         the default configuration of the
        module
        "
	  ::= { pmopm2CtrlconfMgnt1 14 }



pmopm2CtrlConf2Flash1 OBJECT-TYPE
	  SYNTAX EkiOnOff
	  MAX-ACCESS read-write
	  STATUS current
	  DESCRIPTION
        "
        Write Configuration Tables :This
        OID saves the current configuration
        of the PM as configuration2 in
         the flash.  <Help>  This control
        saves the customer configuration
        on the module
        "
	  ::= { pmopm2CtrlconfMgnt1 10 }



pmopm2CtrlConf2Load1 OBJECT-TYPE
	  SYNTAX EkiOnOff
	  MAX-ACCESS read-write
	  STATUS current
	  DESCRIPTION
        "
        Load Configuration Tables Set
         Nb 2 :When set this OID enables
        loading from flash configuration2
        into the PM.
        "
	  ::= { pmopm2CtrlconfMgnt1 2 }



pmopm2CtrlConf1Load1 OBJECT-TYPE
	  SYNTAX EkiOnOff
	  MAX-ACCESS read-write
	  STATUS current
	  DESCRIPTION
        "
        Load Configuration Tables Set
         Nb 1 :When set this OID enables
        loading from flash configuration1
        into the PM.
        "
	  ::= { pmopm2CtrlconfMgnt1 1 }



--- *****************************************************
---     LEAF for the synth4 article
--- *****************************************************
pmopm2Ctrlsynth4 OBJECT IDENTIFIER ::= { pmopm2CtrlOther 4 }




pmopm2CtrlCorrelatOff OBJECT-TYPE
	  SYNTAX EkiOnOff
	  MAX-ACCESS read-write
	  STATUS current
	  DESCRIPTION
        "
        Disable Alarm Correlation :This
        OID disables the alarm correlation
        in the PM.
        "
	  ::= { pmopm2Ctrlsynth4 2 }



pmopm2CtrlCorrelatOn OBJECT-TYPE
	  SYNTAX EkiOnOff
	  MAX-ACCESS read-write
	  STATUS current
	  DESCRIPTION
        "
        Enable Alarm Correlation :This
        OID enables the alarm correlation
        in the PM.
        "
	  ::= { pmopm2Ctrlsynth4 1 }



--- *****************************************************
---     LEAF for the swMgnt article
--- *****************************************************
pmopm2CtrlswMgnt OBJECT IDENTIFIER ::= { pmopm2CtrlOther 5 }




pmopm2CtrlLoadSwBank2 OBJECT-TYPE
	  SYNTAX EkiOnOff
	  MAX-ACCESS read-write
	  STATUS current
	  DESCRIPTION
        "
        Set Software Nb 2 As Active :This
        OID, when set, loads the SW from
        bank2 into the PM. It must be followed
        by a reset.  <Help>  This controls
        selects the second SW bank as the
        active bank for the next module
        reset
        "
	  ::= { pmopm2CtrlswMgnt 6 }



pmopm2CtrlLoadSwBank1 OBJECT-TYPE
	  SYNTAX EkiOnOff
	  MAX-ACCESS read-write
	  STATUS current
	  DESCRIPTION
        "
        Set Software Nb 1 As Active :This
        OID, when set, loads the SW from
        bank1 into the PM. It must be followed
        by a reset.  <Help>  This controls
        selects the first SW bank as the
        active bank for the next module
        reset
        "
	  ::= { pmopm2CtrlswMgnt 5 }



pmopm2CtrlWarmReset OBJECT-TYPE
	  SYNTAX EkiOnOff
	  MAX-ACCESS read-write
	  STATUS current
	  DESCRIPTION
        "
        PM Warm Reset :This OID, when
         set, causes a warm reset of the
        PM. This reset is not traffic affecting,
        and the configuration of PM remains
        unchanged.  <Help>  This control
        initiates a warm reset of the module.
        "
	  ::= { pmopm2CtrlswMgnt 3 }



pmopm2CtrlColdReset OBJECT-TYPE
	  SYNTAX EkiOnOff
	  MAX-ACCESS read-write
	  STATUS current
	  DESCRIPTION
        "
        PM Cold Reset :This OID, when
         set, causes a cold reset of the
        PM. This reset is traffic affecting,
        and the configuration of PM is
         reloaded on start-up.  <Help>
          This control initiates a cold
        reset of the module.
        "
	  ::= { pmopm2CtrlswMgnt 2 }



--- *****************************************************
---     LEAF for the gwMgnt article
--- *****************************************************
pmopm2CtrlgwMgnt OBJECT IDENTIFIER ::= { pmopm2CtrlOther 6 }




pmopm2CtrlLoadGwBank4 OBJECT-TYPE
	  SYNTAX EkiOnOff
	  MAX-ACCESS read-write
	  STATUS current
	  DESCRIPTION
        "
        Set Gateware Nb 4 As Active :This
        OID, when set, loads the GW from
        bank4 (Flash) into the PM. It is
        followed by an automatic gateware
        cold reset.
        "
	  ::= { pmopm2CtrlgwMgnt 8 }



pmopm2CtrlLoadGwBank3 OBJECT-TYPE
	  SYNTAX EkiOnOff
	  MAX-ACCESS read-write
	  STATUS current
	  DESCRIPTION
        "
        Set Gateware Nb 3 As Active :This
        OID, when set, loads the GW from
        bank3 (Flash) into the PM. It is
        followed by an automatic gateware
        cold reset.  <Help>  This controls
        initiates a cold reset of the module
        and select the third GW bank as
        the active bank
        "
	  ::= { pmopm2CtrlgwMgnt 7 }



pmopm2CtrlLoadGwBank2 OBJECT-TYPE
	  SYNTAX EkiOnOff
	  MAX-ACCESS read-write
	  STATUS current
	  DESCRIPTION
        "
        Set Gateware Nb 2 As Active :This
        OID, when set, loads the GW from
        bank2 (Flash) into the PM. It is
        followed by an automatic gateware
        cold reset.
        "
	  ::= { pmopm2CtrlgwMgnt 6 }



pmopm2CtrlLoadGwBank1 OBJECT-TYPE
	  SYNTAX EkiOnOff
	  MAX-ACCESS read-write
	  STATUS current
	  DESCRIPTION
        "
        Set Gateware Nb 1 As Active :This
        OID, when set, loads the GW from
        bank1 (Flash) into the PM. It is
        followed by an automatic gateware
        cold reset.  <Help>  This controls
        initiates a cold reset of the module
        and select the first GW bank as
        the active bank
        "
	  ::= { pmopm2CtrlgwMgnt 5 }



pmopm2CtrlCurrentGwReset OBJECT-TYPE
	  SYNTAX EkiOnOff
	  MAX-ACCESS read-write
	  STATUS current
	  DESCRIPTION
        "
        Active Gateware Reset :This OID,
        when set, resets the active gateware.
        It is traffic affecting.
        "
	  ::= { pmopm2CtrlgwMgnt 1 }



--- *********************************************************
---     TABLE for the pmopm2Ctrlcalibration articles
--- *********************************************************

pmopm2CtrlcalibrationTable OBJECT-TYPE
	SYNTAX  SEQUENCE OF Pmopm2CtrlcalibrationEntry
	MAX-ACCESS not-accessible
	STATUS current
	DESCRIPTION
        "
        List of pmopm2Ctrlcalibration
         Article
        "
	::= { pmopm2CtrlClient 16 }


pmopm2CtrlcalibrationEntry OBJECT-TYPE
	SYNTAX Pmopm2CtrlcalibrationEntry
	MAX-ACCESS not-accessible
	STATUS current
	DESCRIPTION
        "
        Row definition for the pmopm2Ctrlcalibration
        table
        "
	INDEX   { pmopm2CtrlcalibrationIndex }
	::= { pmopm2CtrlcalibrationTable 1 }


Pmopm2CtrlcalibrationEntry ::=
	SEQUENCE {
	pmopm2CtrlcalibrationIndex
		INTEGER,
	pmopm2CtrlcalibrationPortn
		EkiState
	}


pmopm2CtrlcalibrationIndex OBJECT-TYPE
	SYNTAX  INTEGER(0..128)
	MAX-ACCESS  read-only
	STATUS current
	DESCRIPTION
        "
        Index definition for the pmopm2Ctrlcalibration
        table
        "
	::= { pmopm2CtrlcalibrationEntry 1 }


pmopm2CtrlcalibrationPortn OBJECT-TYPE
	SYNTAX  EkiState
	MAX-ACCESS read-write
	STATUS current
	DESCRIPTION
        "
        Port Calibration :This OID initiates
        the OPM input calibration to define
        automatically the OPM offset value.
         <Help>  This parameter initiates
        the OPM input calibration to define
        automatically the OPM offset value.
        "
	::= { pmopm2CtrlcalibrationEntry 2 }


--- *********************************************************
---     TABLE for the pmopm2CtrlspectrumAutodiscovery articles
--- *********************************************************

pmopm2CtrlspectrumAutodiscoveryTable OBJECT-TYPE
	SYNTAX  SEQUENCE OF Pmopm2CtrlspectrumAutodiscoveryEntry
	MAX-ACCESS not-accessible
	STATUS current
	DESCRIPTION
        "
        List of pmopm2CtrlspectrumAutodiscovery
        Article
        "
	::= { pmopm2CtrlClient 17 }


pmopm2CtrlspectrumAutodiscoveryEntry OBJECT-TYPE
	SYNTAX Pmopm2CtrlspectrumAutodiscoveryEntry
	MAX-ACCESS not-accessible
	STATUS current
	DESCRIPTION
        "
        Row definition for the pmopm2CtrlspectrumAutodiscovery
        table
        "
	INDEX   { pmopm2CtrlspectrumAutodiscoveryIndex }
	::= { pmopm2CtrlspectrumAutodiscoveryTable 1 }


Pmopm2CtrlspectrumAutodiscoveryEntry ::=
	SEQUENCE {
	pmopm2CtrlspectrumAutodiscoveryIndex
		INTEGER,
	pmopm2CtrlspectrumAutodiscoveryPortn
		EkiState
	}


pmopm2CtrlspectrumAutodiscoveryIndex OBJECT-TYPE
	SYNTAX  INTEGER(0..128)
	MAX-ACCESS  read-only
	STATUS current
	DESCRIPTION
        "
        Index definition for the pmopm2CtrlspectrumAutodiscovery
        table
        "
	::= { pmopm2CtrlspectrumAutodiscoveryEntry 1 }


pmopm2CtrlspectrumAutodiscoveryPortn OBJECT-TYPE
	SYNTAX  EkiState
	MAX-ACCESS read-write
	STATUS current
	DESCRIPTION
        "
        Spectrum Auto Discovery :This
         OID initiates the OPM scanning
        to define automatically the channels
        to monitor  <Help>  This parameter
        initiates the automatic configuration
        of the thresholds (for each channel)
        using the user-defined delta.
        "
	::= { pmopm2CtrlspectrumAutodiscoveryEntry 2 }


--- *********************************************************
---     TABLE for the pmopm2CtrlthresholdsAutoconfig articles
--- *********************************************************

pmopm2CtrlthresholdsAutoconfigTable OBJECT-TYPE
	SYNTAX  SEQUENCE OF Pmopm2CtrlthresholdsAutoconfigEntry
	MAX-ACCESS not-accessible
	STATUS current
	DESCRIPTION
        "
        List of pmopm2CtrlthresholdsAutoconfig
        Article
        "
	::= { pmopm2CtrlClient 18 }


pmopm2CtrlthresholdsAutoconfigEntry OBJECT-TYPE
	SYNTAX Pmopm2CtrlthresholdsAutoconfigEntry
	MAX-ACCESS not-accessible
	STATUS current
	DESCRIPTION
        "
        Row definition for the pmopm2CtrlthresholdsAutoconfig
        table
        "
	INDEX   { pmopm2CtrlthresholdsAutoconfigIndex }
	::= { pmopm2CtrlthresholdsAutoconfigTable 1 }


Pmopm2CtrlthresholdsAutoconfigEntry ::=
	SEQUENCE {
	pmopm2CtrlthresholdsAutoconfigIndex
		INTEGER,
	pmopm2CtrlthresholdsAutoconfigPortn
		EkiState
	}


pmopm2CtrlthresholdsAutoconfigIndex OBJECT-TYPE
	SYNTAX  INTEGER(0..128)
	MAX-ACCESS  read-only
	STATUS current
	DESCRIPTION
        "
        Index definition for the pmopm2CtrlthresholdsAutoconfig
        table
        "
	::= { pmopm2CtrlthresholdsAutoconfigEntry 1 }


pmopm2CtrlthresholdsAutoconfigPortn OBJECT-TYPE
	SYNTAX  EkiState
	MAX-ACCESS read-write
	STATUS current
	DESCRIPTION
        "
        Thresholds Auto Configuration
         :This OID initiates the automatic
        configuration of the thresholds
        (for each channel) using the user-defined
        delta.<Help> This parameter initiates
        the automatic configuration of
         the thresholds (for each channel)
        using the user-defined delta.
        "
	::= { pmopm2CtrlthresholdsAutoconfigEntry 2 }


--- *********************************************************
---     TABLE for the pmopm2CtrlpowerLossDelta articles
--- *********************************************************

pmopm2CtrlpowerLossDeltaTable OBJECT-TYPE
	SYNTAX  SEQUENCE OF Pmopm2CtrlpowerLossDeltaEntry
	MAX-ACCESS not-accessible
	STATUS current
	DESCRIPTION
        "
        List of pmopm2CtrlpowerLossDelta
        Article
        "
	::= { pmopm2CtrlClient 32 }


pmopm2CtrlpowerLossDeltaEntry OBJECT-TYPE
	SYNTAX Pmopm2CtrlpowerLossDeltaEntry
	MAX-ACCESS not-accessible
	STATUS current
	DESCRIPTION
        "
        Row definition for the pmopm2CtrlpowerLossDelta
        table
        "
	INDEX   { pmopm2CtrlpowerLossDeltaIndex }
	::= { pmopm2CtrlpowerLossDeltaTable 1 }


Pmopm2CtrlpowerLossDeltaEntry ::=
	SEQUENCE {
	pmopm2CtrlpowerLossDeltaIndex
		INTEGER,
	pmopm2CtrlpowerLossDeltaPortn
		INTEGER
	}


pmopm2CtrlpowerLossDeltaIndex OBJECT-TYPE
	SYNTAX  INTEGER(0..128)
	MAX-ACCESS  read-only
	STATUS current
	DESCRIPTION
        "
        Index definition for the pmopm2CtrlpowerLossDelta
        table
        "
	::= { pmopm2CtrlpowerLossDeltaEntry 1 }


pmopm2CtrlpowerLossDeltaPortn OBJECT-TYPE
	SYNTAX  INTEGER (0..65535)
	MAX-ACCESS read-write
	STATUS current
	DESCRIPTION
        "
        Power Loss Delta :This OID defines
        the delta to use to define the
         channel absence threshold  (AV=InvQ8(Delta))
        (Unit = dB)<Help> This parameter
        defines the delta to use to defined
        the channel absence threshold
        "
	::= { pmopm2CtrlpowerLossDeltaEntry 2 }


--- *********************************************************
---     TABLE for the pmopm2CtrlpowerHighDelta articles
--- *********************************************************

pmopm2CtrlpowerHighDeltaTable OBJECT-TYPE
	SYNTAX  SEQUENCE OF Pmopm2CtrlpowerHighDeltaEntry
	MAX-ACCESS not-accessible
	STATUS current
	DESCRIPTION
        "
        List of pmopm2CtrlpowerHighDelta
        Article
        "
	::= { pmopm2CtrlClient 40 }


pmopm2CtrlpowerHighDeltaEntry OBJECT-TYPE
	SYNTAX Pmopm2CtrlpowerHighDeltaEntry
	MAX-ACCESS not-accessible
	STATUS current
	DESCRIPTION
        "
        Row definition for the pmopm2CtrlpowerHighDelta
        table
        "
	INDEX   { pmopm2CtrlpowerHighDeltaIndex }
	::= { pmopm2CtrlpowerHighDeltaTable 1 }


Pmopm2CtrlpowerHighDeltaEntry ::=
	SEQUENCE {
	pmopm2CtrlpowerHighDeltaIndex
		INTEGER,
	pmopm2CtrlpowerHighDeltaPortn
		INTEGER
	}


pmopm2CtrlpowerHighDeltaIndex OBJECT-TYPE
	SYNTAX  INTEGER(0..128)
	MAX-ACCESS  read-only
	STATUS current
	DESCRIPTION
        "
        Index definition for the pmopm2CtrlpowerHighDelta
        table
        "
	::= { pmopm2CtrlpowerHighDeltaEntry 1 }


pmopm2CtrlpowerHighDeltaPortn OBJECT-TYPE
	SYNTAX  INTEGER (0..65535)
	MAX-ACCESS read-write
	STATUS current
	DESCRIPTION
        "
        Power High Delta :This OID defines
        the delta to use to define the
         channel absence threshold  (AV=InvQ8(Delta))
        (Unit = dB)<Help> This parameter
        defines the delta to use to defined
        the channel power high threshold
        "
	::= { pmopm2CtrlpowerHighDeltaEntry 2 }


--- *********************************************************
---     TABLE for the pmopm2CtrlpowerLowDelta articles
--- *********************************************************

pmopm2CtrlpowerLowDeltaTable OBJECT-TYPE
	SYNTAX  SEQUENCE OF Pmopm2CtrlpowerLowDeltaEntry
	MAX-ACCESS not-accessible
	STATUS current
	DESCRIPTION
        "
        List of pmopm2CtrlpowerLowDelta
        Article
        "
	::= { pmopm2CtrlClient 48 }


pmopm2CtrlpowerLowDeltaEntry OBJECT-TYPE
	SYNTAX Pmopm2CtrlpowerLowDeltaEntry
	MAX-ACCESS not-accessible
	STATUS current
	DESCRIPTION
        "
        Row definition for the pmopm2CtrlpowerLowDelta
        table
        "
	INDEX   { pmopm2CtrlpowerLowDeltaIndex }
	::= { pmopm2CtrlpowerLowDeltaTable 1 }


Pmopm2CtrlpowerLowDeltaEntry ::=
	SEQUENCE {
	pmopm2CtrlpowerLowDeltaIndex
		INTEGER,
	pmopm2CtrlpowerLowDeltaPortn
		INTEGER
	}


pmopm2CtrlpowerLowDeltaIndex OBJECT-TYPE
	SYNTAX  INTEGER(0..128)
	MAX-ACCESS  read-only
	STATUS current
	DESCRIPTION
        "
        Index definition for the pmopm2CtrlpowerLowDelta
        table
        "
	::= { pmopm2CtrlpowerLowDeltaEntry 1 }


pmopm2CtrlpowerLowDeltaPortn OBJECT-TYPE
	SYNTAX  INTEGER (0..65535)
	MAX-ACCESS read-write
	STATUS current
	DESCRIPTION
        "
        Power Low Delta :This OID defines
        the delta to use to define the
         channel absence threshold  (AV=InvQ8(Delta))
        (Unit = dB)<Help> This parameter
        defines the delta to use to defined
        the channel power low threshold
        "
	::= { pmopm2CtrlpowerLowDeltaEntry 2 }


--- *********************************************************
---     TABLE for the pmopm2CtrlinputPowerRef articles
--- *********************************************************

pmopm2CtrlinputPowerRefTable OBJECT-TYPE
	SYNTAX  SEQUENCE OF Pmopm2CtrlinputPowerRefEntry
	MAX-ACCESS not-accessible
	STATUS current
	DESCRIPTION
        "
        List of pmopm2CtrlinputPowerRef
        Article
        "
	::= { pmopm2CtrlClient 64 }


pmopm2CtrlinputPowerRefEntry OBJECT-TYPE
	SYNTAX Pmopm2CtrlinputPowerRefEntry
	MAX-ACCESS not-accessible
	STATUS current
	DESCRIPTION
        "
        Row definition for the pmopm2CtrlinputPowerRef
        table
        "
	INDEX   { pmopm2CtrlinputPowerRefIndex }
	::= { pmopm2CtrlinputPowerRefTable 1 }


Pmopm2CtrlinputPowerRefEntry ::=
	SEQUENCE {
	pmopm2CtrlinputPowerRefIndex
		INTEGER,
	pmopm2CtrlinputPowerRefPortn
		INTEGER
	}


pmopm2CtrlinputPowerRefIndex OBJECT-TYPE
	SYNTAX  INTEGER(0..128)
	MAX-ACCESS  read-only
	STATUS current
	DESCRIPTION
        "
        Index definition for the pmopm2CtrlinputPowerRef
        table
        "
	::= { pmopm2CtrlinputPowerRefEntry 1 }


pmopm2CtrlinputPowerRefPortn OBJECT-TYPE
	SYNTAX  INTEGER (0..65535)
	MAX-ACCESS read-write
	STATUS current
	DESCRIPTION
        "
        Input Power Reference :This OID
        defines the input power reference
        used to calibrate the OPM input
        power.   (AV=InvQ8(Power)) (Unit
        = dBm)<Help> This parameter defines
        the input power reference used
         to calibrate the OPM input power.
        "
	::= { pmopm2CtrlinputPowerRefEntry 2 }


--- *****************************************************
---     LEAF for the ledTest article
--- *****************************************************
pmopm2CtrlledTest OBJECT IDENTIFIER ::= { pmopm2CtrlOther 192 }




pmopm2CtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { pmopm2CtrlledTest 3 }



pmopm2CtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { pmopm2CtrlledTest 2 }



pmopm2CtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { pmopm2CtrlledTest 1 }








--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



--- *********************************************************
---     TABLE for the pmopm2Mesrchannel1 articles
--- *********************************************************

pmopm2Mesrchannel1Table OBJECT-TYPE
	SYNTAX  SEQUENCE OF Pmopm2Mesrchannel1Entry
	MAX-ACCESS not-accessible
	STATUS current
	DESCRIPTION
        "
        List of pmopm2Mesrchannel1 Article
        "
	::= { pmopm2MesrClient 16 }


pmopm2Mesrchannel1Entry OBJECT-TYPE
	SYNTAX Pmopm2Mesrchannel1Entry
	MAX-ACCESS not-accessible
	STATUS current
	DESCRIPTION
        "
        Row definition for the pmopm2Mesrchannel1
        table
        "
	INDEX   { pmopm2Mesrchannel1Index }
	::= { pmopm2Mesrchannel1Table 1 }


Pmopm2Mesrchannel1Entry ::=
	SEQUENCE {
	pmopm2Mesrchannel1Index
		INTEGER,
	pmopm2Mesrchannel1Portn
		INTEGER
	}


pmopm2Mesrchannel1Index OBJECT-TYPE
	SYNTAX  INTEGER(0..128)
	MAX-ACCESS  read-only
	STATUS current
	DESCRIPTION
        "
        Index definition for the pmopm2Mesrchannel1
        table
        "
	::= { pmopm2Mesrchannel1Entry 1 }


pmopm2Mesrchannel1Portn OBJECT-TYPE
	SYNTAX  INTEGER (0..65535)
	MAX-ACCESS read-only
	STATUS current
	DESCRIPTION
        "
        Channel Power :This OID indicates
        the channel power  (Power =Q8(Number
        format)) (Unit = dBm)<Help> This
        measure indicates the channel power
        "
	::= { pmopm2Mesrchannel1Entry 2 }


--- *********************************************************
---     TABLE for the pmopm2Mesrchannel2 articles
--- *********************************************************

pmopm2Mesrchannel2Table OBJECT-TYPE
	SYNTAX  SEQUENCE OF Pmopm2Mesrchannel2Entry
	MAX-ACCESS not-accessible
	STATUS current
	DESCRIPTION
        "
        List of pmopm2Mesrchannel2 Article
        "
	::= { pmopm2MesrClient 18 }


pmopm2Mesrchannel2Entry OBJECT-TYPE
	SYNTAX Pmopm2Mesrchannel2Entry
	MAX-ACCESS not-accessible
	STATUS current
	DESCRIPTION
        "
        Row definition for the pmopm2Mesrchannel2
        table
        "
	INDEX   { pmopm2Mesrchannel2Index }
	::= { pmopm2Mesrchannel2Table 1 }


Pmopm2Mesrchannel2Entry ::=
	SEQUENCE {
	pmopm2Mesrchannel2Index
		INTEGER,
	pmopm2Mesrchannel2Portn
		INTEGER
	}


pmopm2Mesrchannel2Index OBJECT-TYPE
	SYNTAX  INTEGER(0..128)
	MAX-ACCESS  read-only
	STATUS current
	DESCRIPTION
        "
        Index definition for the pmopm2Mesrchannel2
        table
        "
	::= { pmopm2Mesrchannel2Entry 1 }


pmopm2Mesrchannel2Portn OBJECT-TYPE
	SYNTAX  INTEGER (0..65535)
	MAX-ACCESS read-only
	STATUS current
	DESCRIPTION
        "
        Channel2 Power :This OID indicates
        the channel power  (Power =Q8(Number
        format)) (Unit = dBm)<Help> This
        measure indicates the channel power
        "
	::= { pmopm2Mesrchannel2Entry 2 }


--- *********************************************************
---     TABLE for the pmopm2Mesrchannel3 articles
--- *********************************************************

pmopm2Mesrchannel3Table OBJECT-TYPE
	SYNTAX  SEQUENCE OF Pmopm2Mesrchannel3Entry
	MAX-ACCESS not-accessible
	STATUS current
	DESCRIPTION
        "
        List of pmopm2Mesrchannel3 Article
        "
	::= { pmopm2MesrClient 20 }


pmopm2Mesrchannel3Entry OBJECT-TYPE
	SYNTAX Pmopm2Mesrchannel3Entry
	MAX-ACCESS not-accessible
	STATUS current
	DESCRIPTION
        "
        Row definition for the pmopm2Mesrchannel3
        table
        "
	INDEX   { pmopm2Mesrchannel3Index }
	::= { pmopm2Mesrchannel3Table 1 }


Pmopm2Mesrchannel3Entry ::=
	SEQUENCE {
	pmopm2Mesrchannel3Index
		INTEGER,
	pmopm2Mesrchannel3Portn
		INTEGER
	}


pmopm2Mesrchannel3Index OBJECT-TYPE
	SYNTAX  INTEGER(0..128)
	MAX-ACCESS  read-only
	STATUS current
	DESCRIPTION
        "
        Index definition for the pmopm2Mesrchannel3
        table
        "
	::= { pmopm2Mesrchannel3Entry 1 }


pmopm2Mesrchannel3Portn OBJECT-TYPE
	SYNTAX  INTEGER (0..65535)
	MAX-ACCESS read-only
	STATUS current
	DESCRIPTION
        "
        Channel3 Power :This OID indicates
        the channel power  (Power =Q8(Number
        format)) (Unit = dBm)<Help> This
        measure indicates the channel power
        "
	::= { pmopm2Mesrchannel3Entry 2 }


--- *********************************************************
---     TABLE for the pmopm2Mesrchannel4 articles
--- *********************************************************

pmopm2Mesrchannel4Table OBJECT-TYPE
	SYNTAX  SEQUENCE OF Pmopm2Mesrchannel4Entry
	MAX-ACCESS not-accessible
	STATUS current
	DESCRIPTION
        "
        List of pmopm2Mesrchannel4 Article
        "
	::= { pmopm2MesrClient 22 }


pmopm2Mesrchannel4Entry OBJECT-TYPE
	SYNTAX Pmopm2Mesrchannel4Entry
	MAX-ACCESS not-accessible
	STATUS current
	DESCRIPTION
        "
        Row definition for the pmopm2Mesrchannel4
        table
        "
	INDEX   { pmopm2Mesrchannel4Index }
	::= { pmopm2Mesrchannel4Table 1 }


Pmopm2Mesrchannel4Entry ::=
	SEQUENCE {
	pmopm2Mesrchannel4Index
		INTEGER,
	pmopm2Mesrchannel4Portn
		INTEGER
	}


pmopm2Mesrchannel4Index OBJECT-TYPE
	SYNTAX  INTEGER(0..128)
	MAX-ACCESS  read-only
	STATUS current
	DESCRIPTION
        "
        Index definition for the pmopm2Mesrchannel4
        table
        "
	::= { pmopm2Mesrchannel4Entry 1 }


pmopm2Mesrchannel4Portn OBJECT-TYPE
	SYNTAX  INTEGER (0..65535)
	MAX-ACCESS read-only
	STATUS current
	DESCRIPTION
        "
        Channel4 Power :This OID indicates
        the channel power  (Power =Q8(Number
        format)) (Unit = dBm)<Help> This
        measure indicates the channel power
        "
	::= { pmopm2Mesrchannel4Entry 2 }


--- *********************************************************
---     TABLE for the pmopm2Mesrchannel5 articles
--- *********************************************************

pmopm2Mesrchannel5Table OBJECT-TYPE
	SYNTAX  SEQUENCE OF Pmopm2Mesrchannel5Entry
	MAX-ACCESS not-accessible
	STATUS current
	DESCRIPTION
        "
        List of pmopm2Mesrchannel5 Article
        "
	::= { pmopm2MesrClient 24 }


pmopm2Mesrchannel5Entry OBJECT-TYPE
	SYNTAX Pmopm2Mesrchannel5Entry
	MAX-ACCESS not-accessible
	STATUS current
	DESCRIPTION
        "
        Row definition for the pmopm2Mesrchannel5
        table
        "
	INDEX   { pmopm2Mesrchannel5Index }
	::= { pmopm2Mesrchannel5Table 1 }


Pmopm2Mesrchannel5Entry ::=
	SEQUENCE {
	pmopm2Mesrchannel5Index
		INTEGER,
	pmopm2Mesrchannel5Portn
		INTEGER
	}


pmopm2Mesrchannel5Index OBJECT-TYPE
	SYNTAX  INTEGER(0..128)
	MAX-ACCESS  read-only
	STATUS current
	DESCRIPTION
        "
        Index definition for the pmopm2Mesrchannel5
        table
        "
	::= { pmopm2Mesrchannel5Entry 1 }


pmopm2Mesrchannel5Portn OBJECT-TYPE
	SYNTAX  INTEGER (0..65535)
	MAX-ACCESS read-only
	STATUS current
	DESCRIPTION
        "
        Channel5 Power :This OID indicates
        the channel power  (Power =Q8(Number
        format)) (Unit = dBm)<Help> This
        measure indicates the channel power
        "
	::= { pmopm2Mesrchannel5Entry 2 }


--- *********************************************************
---     TABLE for the pmopm2Mesrchannel6 articles
--- *********************************************************

pmopm2Mesrchannel6Table OBJECT-TYPE
	SYNTAX  SEQUENCE OF Pmopm2Mesrchannel6Entry
	MAX-ACCESS not-accessible
	STATUS current
	DESCRIPTION
        "
        List of pmopm2Mesrchannel6 Article
        "
	::= { pmopm2MesrClient 26 }


pmopm2Mesrchannel6Entry OBJECT-TYPE
	SYNTAX Pmopm2Mesrchannel6Entry
	MAX-ACCESS not-accessible
	STATUS current
	DESCRIPTION
        "
        Row definition for the pmopm2Mesrchannel6
        table
        "
	INDEX   { pmopm2Mesrchannel6Index }
	::= { pmopm2Mesrchannel6Table 1 }


Pmopm2Mesrchannel6Entry ::=
	SEQUENCE {
	pmopm2Mesrchannel6Index
		INTEGER,
	pmopm2Mesrchannel6Portn
		INTEGER
	}


pmopm2Mesrchannel6Index OBJECT-TYPE
	SYNTAX  INTEGER(0..128)
	MAX-ACCESS  read-only
	STATUS current
	DESCRIPTION
        "
        Index definition for the pmopm2Mesrchannel6
        table
        "
	::= { pmopm2Mesrchannel6Entry 1 }


pmopm2Mesrchannel6Portn OBJECT-TYPE
	SYNTAX  INTEGER (0..65535)
	MAX-ACCESS read-only
	STATUS current
	DESCRIPTION
        "
        Channel6 Power :This OID indicates
        the channel power  (Power =Q8(Number
        format)) (Unit = dBm)<Help> This
        measure indicates the channel power
        "
	::= { pmopm2Mesrchannel6Entry 2 }


--- *********************************************************
---     TABLE for the pmopm2Mesrchannel7 articles
--- *********************************************************

pmopm2Mesrchannel7Table OBJECT-TYPE
	SYNTAX  SEQUENCE OF Pmopm2Mesrchannel7Entry
	MAX-ACCESS not-accessible
	STATUS current
	DESCRIPTION
        "
        List of pmopm2Mesrchannel7 Article
        "
	::= { pmopm2MesrClient 28 }


pmopm2Mesrchannel7Entry OBJECT-TYPE
	SYNTAX Pmopm2Mesrchannel7Entry
	MAX-ACCESS not-accessible
	STATUS current
	DESCRIPTION
        "
        Row definition for the pmopm2Mesrchannel7
        table
        "
	INDEX   { pmopm2Mesrchannel7Index }
	::= { pmopm2Mesrchannel7Table 1 }


Pmopm2Mesrchannel7Entry ::=
	SEQUENCE {
	pmopm2Mesrchannel7Index
		INTEGER,
	pmopm2Mesrchannel7Portn
		INTEGER
	}


pmopm2Mesrchannel7Index OBJECT-TYPE
	SYNTAX  INTEGER(0..128)
	MAX-ACCESS  read-only
	STATUS current
	DESCRIPTION
        "
        Index definition for the pmopm2Mesrchannel7
        table
        "
	::= { pmopm2Mesrchannel7Entry 1 }


pmopm2Mesrchannel7Portn OBJECT-TYPE
	SYNTAX  INTEGER (0..65535)
	MAX-ACCESS read-only
	STATUS current
	DESCRIPTION
        "
        Channel7 Power :This OID indicates
        the channel power  (Power =Q8(Number
        format)) (Unit = dBm)<Help> This
        measure indicates the channel power
        "
	::= { pmopm2Mesrchannel7Entry 2 }


--- *********************************************************
---     TABLE for the pmopm2Mesrchannel8 articles
--- *********************************************************

pmopm2Mesrchannel8Table OBJECT-TYPE
	SYNTAX  SEQUENCE OF Pmopm2Mesrchannel8Entry
	MAX-ACCESS not-accessible
	STATUS current
	DESCRIPTION
        "
        List of pmopm2Mesrchannel8 Article
        "
	::= { pmopm2MesrClient 30 }


pmopm2Mesrchannel8Entry OBJECT-TYPE
	SYNTAX Pmopm2Mesrchannel8Entry
	MAX-ACCESS not-accessible
	STATUS current
	DESCRIPTION
        "
        Row definition for the pmopm2Mesrchannel8
        table
        "
	INDEX   { pmopm2Mesrchannel8Index }
	::= { pmopm2Mesrchannel8Table 1 }


Pmopm2Mesrchannel8Entry ::=
	SEQUENCE {
	pmopm2Mesrchannel8Index
		INTEGER,
	pmopm2Mesrchannel8Portn
		INTEGER
	}


pmopm2Mesrchannel8Index OBJECT-TYPE
	SYNTAX  INTEGER(0..128)
	MAX-ACCESS  read-only
	STATUS current
	DESCRIPTION
        "
        Index definition for the pmopm2Mesrchannel8
        table
        "
	::= { pmopm2Mesrchannel8Entry 1 }


pmopm2Mesrchannel8Portn OBJECT-TYPE
	SYNTAX  INTEGER (0..65535)
	MAX-ACCESS read-only
	STATUS current
	DESCRIPTION
        "
        Channel8 Power :This OID indicates
        the channel power  (Power =Q8(Number
        format)) (Unit = dBm)<Help> This
        measure indicates the channel power
        "
	::= { pmopm2Mesrchannel8Entry 2 }


--- *********************************************************
---     TABLE for the pmopm2Mesrchannel9 articles
--- *********************************************************

pmopm2Mesrchannel9Table OBJECT-TYPE
	SYNTAX  SEQUENCE OF Pmopm2Mesrchannel9Entry
	MAX-ACCESS not-accessible
	STATUS current
	DESCRIPTION
        "
        List of pmopm2Mesrchannel9 Article
        "
	::= { pmopm2MesrClient 32 }


pmopm2Mesrchannel9Entry OBJECT-TYPE
	SYNTAX Pmopm2Mesrchannel9Entry
	MAX-ACCESS not-accessible
	STATUS current
	DESCRIPTION
        "
        Row definition for the pmopm2Mesrchannel9
        table
        "
	INDEX   { pmopm2Mesrchannel9Index }
	::= { pmopm2Mesrchannel9Table 1 }


Pmopm2Mesrchannel9Entry ::=
	SEQUENCE {
	pmopm2Mesrchannel9Index
		INTEGER,
	pmopm2Mesrchannel9Portn
		INTEGER
	}


pmopm2Mesrchannel9Index OBJECT-TYPE
	SYNTAX  INTEGER(0..128)
	MAX-ACCESS  read-only
	STATUS current
	DESCRIPTION
        "
        Index definition for the pmopm2Mesrchannel9
        table
        "
	::= { pmopm2Mesrchannel9Entry 1 }


pmopm2Mesrchannel9Portn OBJECT-TYPE
	SYNTAX  INTEGER (0..65535)
	MAX-ACCESS read-only
	STATUS current
	DESCRIPTION
        "
        Channel9 Power :This OID indicates
        the channel power  (Power =Q8(Number
        format)) (Unit = dBm)<Help> This
        measure indicates the channel power
        "
	::= { pmopm2Mesrchannel9Entry 2 }


--- *********************************************************
---     TABLE for the pmopm2Mesrchannel10 articles
--- *********************************************************

pmopm2Mesrchannel10Table OBJECT-TYPE
	SYNTAX  SEQUENCE OF Pmopm2Mesrchannel10Entry
	MAX-ACCESS not-accessible
	STATUS current
	DESCRIPTION
        "
        List of pmopm2Mesrchannel10 Article
        "
	::= { pmopm2MesrClient 34 }


pmopm2Mesrchannel10Entry OBJECT-TYPE
	SYNTAX Pmopm2Mesrchannel10Entry
	MAX-ACCESS not-accessible
	STATUS current
	DESCRIPTION
        "
        Row definition for the pmopm2Mesrchannel10
        table
        "
	INDEX   { pmopm2Mesrchannel10Index }
	::= { pmopm2Mesrchannel10Table 1 }


Pmopm2Mesrchannel10Entry ::=
	SEQUENCE {
	pmopm2Mesrchannel10Index
		INTEGER,
	pmopm2Mesrchannel10Portn
		INTEGER
	}


pmopm2Mesrchannel10Index OBJECT-TYPE
	SYNTAX  INTEGER(0..128)
	MAX-ACCESS  read-only
	STATUS current
	DESCRIPTION
        "
        Index definition for the pmopm2Mesrchannel10
        table
        "
	::= { pmopm2Mesrchannel10Entry 1 }


pmopm2Mesrchannel10Portn OBJECT-TYPE
	SYNTAX  INTEGER (0..65535)
	MAX-ACCESS read-only
	STATUS current
	DESCRIPTION
        "
        Channel10 Power :This OID indicates
        the channel power  (Power =Q8(Number
        format)) (Unit = dBm)<Help> This
        measure indicates the channel power
        "
	::= { pmopm2Mesrchannel10Entry 2 }


--- *********************************************************
---     TABLE for the pmopm2Mesrchannel11 articles
--- *********************************************************

pmopm2Mesrchannel11Table OBJECT-TYPE
	SYNTAX  SEQUENCE OF Pmopm2Mesrchannel11Entry
	MAX-ACCESS not-accessible
	STATUS current
	DESCRIPTION
        "
        List of pmopm2Mesrchannel11 Article
        "
	::= { pmopm2MesrClient 36 }


pmopm2Mesrchannel11Entry OBJECT-TYPE
	SYNTAX Pmopm2Mesrchannel11Entry
	MAX-ACCESS not-accessible
	STATUS current
	DESCRIPTION
        "
        Row definition for the pmopm2Mesrchannel11
        table
        "
	INDEX   { pmopm2Mesrchannel11Index }
	::= { pmopm2Mesrchannel11Table 1 }


Pmopm2Mesrchannel11Entry ::=
	SEQUENCE {
	pmopm2Mesrchannel11Index
		INTEGER,
	pmopm2Mesrchannel11Portn
		INTEGER
	}


pmopm2Mesrchannel11Index OBJECT-TYPE
	SYNTAX  INTEGER(0..128)
	MAX-ACCESS  read-only
	STATUS current
	DESCRIPTION
        "
        Index definition for the pmopm2Mesrchannel11
        table
        "
	::= { pmopm2Mesrchannel11Entry 1 }


pmopm2Mesrchannel11Portn OBJECT-TYPE
	SYNTAX  INTEGER (0..65535)
	MAX-ACCESS read-only
	STATUS current
	DESCRIPTION
        "
        Channel11 Power :This OID indicates
        the channel power  (Power =Q8(Number
        format)) (Unit = dBm)<Help> This
        measure indicates the channel power
        "
	::= { pmopm2Mesrchannel11Entry 2 }


--- *********************************************************
---     TABLE for the pmopm2Mesrchannel12 articles
--- *********************************************************

pmopm2Mesrchannel12Table OBJECT-TYPE
	SYNTAX  SEQUENCE OF Pmopm2Mesrchannel12Entry
	MAX-ACCESS not-accessible
	STATUS current
	DESCRIPTION
        "
        List of pmopm2Mesrchannel12 Article
        "
	::= { pmopm2MesrClient 38 }


pmopm2Mesrchannel12Entry OBJECT-TYPE
	SYNTAX Pmopm2Mesrchannel12Entry
	MAX-ACCESS not-accessible
	STATUS current
	DESCRIPTION
        "
        Row definition for the pmopm2Mesrchannel12
        table
        "
	INDEX   { pmopm2Mesrchannel12Index }
	::= { pmopm2Mesrchannel12Table 1 }


Pmopm2Mesrchannel12Entry ::=
	SEQUENCE {
	pmopm2Mesrchannel12Index
		INTEGER,
	pmopm2Mesrchannel12Portn
		INTEGER
	}


pmopm2Mesrchannel12Index OBJECT-TYPE
	SYNTAX  INTEGER(0..128)
	MAX-ACCESS  read-only
	STATUS current
	DESCRIPTION
        "
        Index definition for the pmopm2Mesrchannel12
        table
        "
	::= { pmopm2Mesrchannel12Entry 1 }


pmopm2Mesrchannel12Portn OBJECT-TYPE
	SYNTAX  INTEGER (0..65535)
	MAX-ACCESS read-only
	STATUS current
	DESCRIPTION
        "
        Channel12 Power :This OID indicates
        the channel power  (Power =Q8(Number
        format)) (Unit = dBm)<Help> This
        measure indicates the channel power
        "
	::= { pmopm2Mesrchannel12Entry 2 }


--- *********************************************************
---     TABLE for the pmopm2Mesrchannel13 articles
--- *********************************************************

pmopm2Mesrchannel13Table OBJECT-TYPE
	SYNTAX  SEQUENCE OF Pmopm2Mesrchannel13Entry
	MAX-ACCESS not-accessible
	STATUS current
	DESCRIPTION
        "
        List of pmopm2Mesrchannel13 Article
        "
	::= { pmopm2MesrClient 40 }


pmopm2Mesrchannel13Entry OBJECT-TYPE
	SYNTAX Pmopm2Mesrchannel13Entry
	MAX-ACCESS not-accessible
	STATUS current
	DESCRIPTION
        "
        Row definition for the pmopm2Mesrchannel13
        table
        "
	INDEX   { pmopm2Mesrchannel13Index }
	::= { pmopm2Mesrchannel13Table 1 }


Pmopm2Mesrchannel13Entry ::=
	SEQUENCE {
	pmopm2Mesrchannel13Index
		INTEGER,
	pmopm2Mesrchannel13Portn
		INTEGER
	}


pmopm2Mesrchannel13Index OBJECT-TYPE
	SYNTAX  INTEGER(0..128)
	MAX-ACCESS  read-only
	STATUS current
	DESCRIPTION
        "
        Index definition for the pmopm2Mesrchannel13
        table
        "
	::= { pmopm2Mesrchannel13Entry 1 }


pmopm2Mesrchannel13Portn OBJECT-TYPE
	SYNTAX  INTEGER (0..65535)
	MAX-ACCESS read-only
	STATUS current
	DESCRIPTION
        "
        Channel13 Power :This OID indicates
        the channel power  (Power =Q8(Number
        format)) (Unit = dBm)<Help> This
        measure indicates the channel power
        "
	::= { pmopm2Mesrchannel13Entry 2 }


--- *********************************************************
---     TABLE for the pmopm2Mesrchannel14 articles
--- *********************************************************

pmopm2Mesrchannel14Table OBJECT-TYPE
	SYNTAX  SEQUENCE OF Pmopm2Mesrchannel14Entry
	MAX-ACCESS not-accessible
	STATUS current
	DESCRIPTION
        "
        List of pmopm2Mesrchannel14 Article
        "
	::= { pmopm2MesrClient 42 }


pmopm2Mesrchannel14Entry OBJECT-TYPE
	SYNTAX Pmopm2Mesrchannel14Entry
	MAX-ACCESS not-accessible
	STATUS current
	DESCRIPTION
        "
        Row definition for the pmopm2Mesrchannel14
        table
        "
	INDEX   { pmopm2Mesrchannel14Index }
	::= { pmopm2Mesrchannel14Table 1 }


Pmopm2Mesrchannel14Entry ::=
	SEQUENCE {
	pmopm2Mesrchannel14Index
		INTEGER,
	pmopm2Mesrchannel14Portn
		INTEGER
	}


pmopm2Mesrchannel14Index OBJECT-TYPE
	SYNTAX  INTEGER(0..128)
	MAX-ACCESS  read-only
	STATUS current
	DESCRIPTION
        "
        Index definition for the pmopm2Mesrchannel14
        table
        "
	::= { pmopm2Mesrchannel14Entry 1 }


pmopm2Mesrchannel14Portn OBJECT-TYPE
	SYNTAX  INTEGER (0..65535)
	MAX-ACCESS read-only
	STATUS current
	DESCRIPTION
        "
        Channel14 Power :This OID indicates
        the channel power  (Power =Q8(Number
        format)) (Unit = dBm)<Help> This
        measure indicates the channel power
        "
	::= { pmopm2Mesrchannel14Entry 2 }


--- *********************************************************
---     TABLE for the pmopm2Mesrchannel15 articles
--- *********************************************************

pmopm2Mesrchannel15Table OBJECT-TYPE
	SYNTAX  SEQUENCE OF Pmopm2Mesrchannel15Entry
	MAX-ACCESS not-accessible
	STATUS current
	DESCRIPTION
        "
        List of pmopm2Mesrchannel15 Article
        "
	::= { pmopm2MesrClient 44 }


pmopm2Mesrchannel15Entry OBJECT-TYPE
	SYNTAX Pmopm2Mesrchannel15Entry
	MAX-ACCESS not-accessible
	STATUS current
	DESCRIPTION
        "
        Row definition for the pmopm2Mesrchannel15
        table
        "
	INDEX   { pmopm2Mesrchannel15Index }
	::= { pmopm2Mesrchannel15Table 1 }


Pmopm2Mesrchannel15Entry ::=
	SEQUENCE {
	pmopm2Mesrchannel15Index
		INTEGER,
	pmopm2Mesrchannel15Portn
		INTEGER
	}


pmopm2Mesrchannel15Index OBJECT-TYPE
	SYNTAX  INTEGER(0..128)
	MAX-ACCESS  read-only
	STATUS current
	DESCRIPTION
        "
        Index definition for the pmopm2Mesrchannel15
        table
        "
	::= { pmopm2Mesrchannel15Entry 1 }


pmopm2Mesrchannel15Portn OBJECT-TYPE
	SYNTAX  INTEGER (0..65535)
	MAX-ACCESS read-only
	STATUS current
	DESCRIPTION
        "
        Channel15 Power :This OID indicates
        the channel power  (Power =Q8(Number
        format)) (Unit = dBm)<Help> This
        measure indicates the channel power
        "
	::= { pmopm2Mesrchannel15Entry 2 }


--- *********************************************************
---     TABLE for the pmopm2Mesrchannel16 articles
--- *********************************************************

pmopm2Mesrchannel16Table OBJECT-TYPE
	SYNTAX  SEQUENCE OF Pmopm2Mesrchannel16Entry
	MAX-ACCESS not-accessible
	STATUS current
	DESCRIPTION
        "
        List of pmopm2Mesrchannel16 Article
        "
	::= { pmopm2MesrClient 46 }


pmopm2Mesrchannel16Entry OBJECT-TYPE
	SYNTAX Pmopm2Mesrchannel16Entry
	MAX-ACCESS not-accessible
	STATUS current
	DESCRIPTION
        "
        Row definition for the pmopm2Mesrchannel16
        table
        "
	INDEX   { pmopm2Mesrchannel16Index }
	::= { pmopm2Mesrchannel16Table 1 }


Pmopm2Mesrchannel16Entry ::=
	SEQUENCE {
	pmopm2Mesrchannel16Index
		INTEGER,
	pmopm2Mesrchannel16Portn
		INTEGER
	}


pmopm2Mesrchannel16Index OBJECT-TYPE
	SYNTAX  INTEGER(0..128)
	MAX-ACCESS  read-only
	STATUS current
	DESCRIPTION
        "
        Index definition for the pmopm2Mesrchannel16
        table
        "
	::= { pmopm2Mesrchannel16Entry 1 }


pmopm2Mesrchannel16Portn OBJECT-TYPE
	SYNTAX  INTEGER (0..65535)
	MAX-ACCESS read-only
	STATUS current
	DESCRIPTION
        "
        Channel16 Power :This OID indicates
        the channel power  (Power =Q8(Number
        format)) (Unit = dBm)<Help> This
        measure indicates the channel power
        "
	::= { pmopm2Mesrchannel16Entry 2 }


--- *********************************************************
---     TABLE for the pmopm2Mesrchannel17 articles
--- *********************************************************

pmopm2Mesrchannel17Table OBJECT-TYPE
	SYNTAX  SEQUENCE OF Pmopm2Mesrchannel17Entry
	MAX-ACCESS not-accessible
	STATUS current
	DESCRIPTION
        "
        List of pmopm2Mesrchannel17 Article
        "
	::= { pmopm2MesrClient 48 }


pmopm2Mesrchannel17Entry OBJECT-TYPE
	SYNTAX Pmopm2Mesrchannel17Entry
	MAX-ACCESS not-accessible
	STATUS current
	DESCRIPTION
        "
        Row definition for the pmopm2Mesrchannel17
        table
        "
	INDEX   { pmopm2Mesrchannel17Index }
	::= { pmopm2Mesrchannel17Table 1 }


Pmopm2Mesrchannel17Entry ::=
	SEQUENCE {
	pmopm2Mesrchannel17Index
		INTEGER,
	pmopm2Mesrchannel17Portn
		INTEGER
	}


pmopm2Mesrchannel17Index OBJECT-TYPE
	SYNTAX  INTEGER(0..128)
	MAX-ACCESS  read-only
	STATUS current
	DESCRIPTION
        "
        Index definition for the pmopm2Mesrchannel17
        table
        "
	::= { pmopm2Mesrchannel17Entry 1 }


pmopm2Mesrchannel17Portn OBJECT-TYPE
	SYNTAX  INTEGER (0..65535)
	MAX-ACCESS read-only
	STATUS current
	DESCRIPTION
        "
        Channel17 Power :This OID indicates
        the channel power  (Power =Q8(Number
        format)) (Unit = dBm)<Help> This
        measure indicates the channel power
        "
	::= { pmopm2Mesrchannel17Entry 2 }


--- *********************************************************
---     TABLE for the pmopm2Mesrchannel18 articles
--- *********************************************************

pmopm2Mesrchannel18Table OBJECT-TYPE
	SYNTAX  SEQUENCE OF Pmopm2Mesrchannel18Entry
	MAX-ACCESS not-accessible
	STATUS current
	DESCRIPTION
        "
        List of pmopm2Mesrchannel18 Article
        "
	::= { pmopm2MesrClient 50 }


pmopm2Mesrchannel18Entry OBJECT-TYPE
	SYNTAX Pmopm2Mesrchannel18Entry
	MAX-ACCESS not-accessible
	STATUS current
	DESCRIPTION
        "
        Row definition for the pmopm2Mesrchannel18
        table
        "
	INDEX   { pmopm2Mesrchannel18Index }
	::= { pmopm2Mesrchannel18Table 1 }


Pmopm2Mesrchannel18Entry ::=
	SEQUENCE {
	pmopm2Mesrchannel18Index
		INTEGER,
	pmopm2Mesrchannel18Portn
		INTEGER
	}


pmopm2Mesrchannel18Index OBJECT-TYPE
	SYNTAX  INTEGER(0..128)
	MAX-ACCESS  read-only
	STATUS current
	DESCRIPTION
        "
        Index definition for the pmopm2Mesrchannel18
        table
        "
	::= { pmopm2Mesrchannel18Entry 1 }


pmopm2Mesrchannel18Portn OBJECT-TYPE
	SYNTAX  INTEGER (0..65535)
	MAX-ACCESS read-only
	STATUS current
	DESCRIPTION
        "
        Channel18 Power :This OID indicates
        the channel power  (Power =Q8(Number
        format)) (Unit = dBm)<Help> This
        measure indicates the channel power
        "
	::= { pmopm2Mesrchannel18Entry 2 }


--- *********************************************************
---     TABLE for the pmopm2Mesrchannel19 articles
--- *********************************************************

pmopm2Mesrchannel19Table OBJECT-TYPE
	SYNTAX  SEQUENCE OF Pmopm2Mesrchannel19Entry
	MAX-ACCESS not-accessible
	STATUS current
	DESCRIPTION
        "
        List of pmopm2Mesrchannel19 Article
        "
	::= { pmopm2MesrClient 52 }


pmopm2Mesrchannel19Entry OBJECT-TYPE
	SYNTAX Pmopm2Mesrchannel19Entry
	MAX-ACCESS not-accessible
	STATUS current
	DESCRIPTION
        "
        Row definition for the pmopm2Mesrchannel19
        table
        "
	INDEX   { pmopm2Mesrchannel19Index }
	::= { pmopm2Mesrchannel19Table 1 }


Pmopm2Mesrchannel19Entry ::=
	SEQUENCE {
	pmopm2Mesrchannel19Index
		INTEGER,
	pmopm2Mesrchannel19Portn
		INTEGER
	}


pmopm2Mesrchannel19Index OBJECT-TYPE
	SYNTAX  INTEGER(0..128)
	MAX-ACCESS  read-only
	STATUS current
	DESCRIPTION
        "
        Index definition for the pmopm2Mesrchannel19
        table
        "
	::= { pmopm2Mesrchannel19Entry 1 }


pmopm2Mesrchannel19Portn OBJECT-TYPE
	SYNTAX  INTEGER (0..65535)
	MAX-ACCESS read-only
	STATUS current
	DESCRIPTION
        "
        Channel19 Power :This OID indicates
        the channel power  (Power =Q8(Number
        format)) (Unit = dBm)<Help> This
        measure indicates the channel power
        "
	::= { pmopm2Mesrchannel19Entry 2 }


--- *********************************************************
---     TABLE for the pmopm2Mesrchannel20 articles
--- *********************************************************

pmopm2Mesrchannel20Table OBJECT-TYPE
	SYNTAX  SEQUENCE OF Pmopm2Mesrchannel20Entry
	MAX-ACCESS not-accessible
	STATUS current
	DESCRIPTION
        "
        List of pmopm2Mesrchannel20 Article
        "
	::= { pmopm2MesrClient 54 }


pmopm2Mesrchannel20Entry OBJECT-TYPE
	SYNTAX Pmopm2Mesrchannel20Entry
	MAX-ACCESS not-accessible
	STATUS current
	DESCRIPTION
        "
        Row definition for the pmopm2Mesrchannel20
        table
        "
	INDEX   { pmopm2Mesrchannel20Index }
	::= { pmopm2Mesrchannel20Table 1 }


Pmopm2Mesrchannel20Entry ::=
	SEQUENCE {
	pmopm2Mesrchannel20Index
		INTEGER,
	pmopm2Mesrchannel20Portn
		INTEGER
	}


pmopm2Mesrchannel20Index OBJECT-TYPE
	SYNTAX  INTEGER(0..128)
	MAX-ACCESS  read-only
	STATUS current
	DESCRIPTION
        "
        Index definition for the pmopm2Mesrchannel20
        table
        "
	::= { pmopm2Mesrchannel20Entry 1 }


pmopm2Mesrchannel20Portn OBJECT-TYPE
	SYNTAX  INTEGER (0..65535)
	MAX-ACCESS read-only
	STATUS current
	DESCRIPTION
        "
        Channel20 Power :This OID indicates
        the channel power  (Power =Q8(Number
        format)) (Unit = dBm)<Help> This
        measure indicates the channel power
        "
	::= { pmopm2Mesrchannel20Entry 2 }


--- *********************************************************
---     TABLE for the pmopm2Mesrchannel21 articles
--- *********************************************************

pmopm2Mesrchannel21Table OBJECT-TYPE
	SYNTAX  SEQUENCE OF Pmopm2Mesrchannel21Entry
	MAX-ACCESS not-accessible
	STATUS current
	DESCRIPTION
        "
        List of pmopm2Mesrchannel21 Article
        "
	::= { pmopm2MesrClient 56 }


pmopm2Mesrchannel21Entry OBJECT-TYPE
	SYNTAX Pmopm2Mesrchannel21Entry
	MAX-ACCESS not-accessible
	STATUS current
	DESCRIPTION
        "
        Row definition for the pmopm2Mesrchannel21
        table
        "
	INDEX   { pmopm2Mesrchannel21Index }
	::= { pmopm2Mesrchannel21Table 1 }


Pmopm2Mesrchannel21Entry ::=
	SEQUENCE {
	pmopm2Mesrchannel21Index
		INTEGER,
	pmopm2Mesrchannel21Portn
		INTEGER
	}


pmopm2Mesrchannel21Index OBJECT-TYPE
	SYNTAX  INTEGER(0..128)
	MAX-ACCESS  read-only
	STATUS current
	DESCRIPTION
        "
        Index definition for the pmopm2Mesrchannel21
        table
        "
	::= { pmopm2Mesrchannel21Entry 1 }


pmopm2Mesrchannel21Portn OBJECT-TYPE
	SYNTAX  INTEGER (0..65535)
	MAX-ACCESS read-only
	STATUS current
	DESCRIPTION
        "
        Channel21 Power :This OID indicates
        the channel power  (Power =Q8(Number
        format)) (Unit = dBm)<Help> This
        measure indicates the channel power
        "
	::= { pmopm2Mesrchannel21Entry 2 }


--- *********************************************************
---     TABLE for the pmopm2Mesrchannel22 articles
--- *********************************************************

pmopm2Mesrchannel22Table OBJECT-TYPE
	SYNTAX  SEQUENCE OF Pmopm2Mesrchannel22Entry
	MAX-ACCESS not-accessible
	STATUS current
	DESCRIPTION
        "
        List of pmopm2Mesrchannel22 Article
        "
	::= { pmopm2MesrClient 58 }


pmopm2Mesrchannel22Entry OBJECT-TYPE
	SYNTAX Pmopm2Mesrchannel22Entry
	MAX-ACCESS not-accessible
	STATUS current
	DESCRIPTION
        "
        Row definition for the pmopm2Mesrchannel22
        table
        "
	INDEX   { pmopm2Mesrchannel22Index }
	::= { pmopm2Mesrchannel22Table 1 }


Pmopm2Mesrchannel22Entry ::=
	SEQUENCE {
	pmopm2Mesrchannel22Index
		INTEGER,
	pmopm2Mesrchannel22Portn
		INTEGER
	}


pmopm2Mesrchannel22Index OBJECT-TYPE
	SYNTAX  INTEGER(0..128)
	MAX-ACCESS  read-only
	STATUS current
	DESCRIPTION
        "
        Index definition for the pmopm2Mesrchannel22
        table
        "
	::= { pmopm2Mesrchannel22Entry 1 }


pmopm2Mesrchannel22Portn OBJECT-TYPE
	SYNTAX  INTEGER (0..65535)
	MAX-ACCESS read-only
	STATUS current
	DESCRIPTION
        "
        Channel22 Power :This OID indicates
        the channel power  (Power =Q8(Number
        format)) (Unit = dBm)<Help> This
        measure indicates the channel power
        "
	::= { pmopm2Mesrchannel22Entry 2 }


--- *********************************************************
---     TABLE for the pmopm2Mesrchannel23 articles
--- *********************************************************

pmopm2Mesrchannel23Table OBJECT-TYPE
	SYNTAX  SEQUENCE OF Pmopm2Mesrchannel23Entry
	MAX-ACCESS not-accessible
	STATUS current
	DESCRIPTION
        "
        List of pmopm2Mesrchannel23 Article
        "
	::= { pmopm2MesrClient 60 }


pmopm2Mesrchannel23Entry OBJECT-TYPE
	SYNTAX Pmopm2Mesrchannel23Entry
	MAX-ACCESS not-accessible
	STATUS current
	DESCRIPTION
        "
        Row definition for the pmopm2Mesrchannel23
        table
        "
	INDEX   { pmopm2Mesrchannel23Index }
	::= { pmopm2Mesrchannel23Table 1 }


Pmopm2Mesrchannel23Entry ::=
	SEQUENCE {
	pmopm2Mesrchannel23Index
		INTEGER,
	pmopm2Mesrchannel23Portn
		INTEGER
	}


pmopm2Mesrchannel23Index OBJECT-TYPE
	SYNTAX  INTEGER(0..128)
	MAX-ACCESS  read-only
	STATUS current
	DESCRIPTION
        "
        Index definition for the pmopm2Mesrchannel23
        table
        "
	::= { pmopm2Mesrchannel23Entry 1 }


pmopm2Mesrchannel23Portn OBJECT-TYPE
	SYNTAX  INTEGER (0..65535)
	MAX-ACCESS read-only
	STATUS current
	DESCRIPTION
        "
        Channel23 Power :This OID indicates
        the channel power  (Power =Q8(Number
        format)) (Unit = dBm)<Help> This
        measure indicates the channel power
        "
	::= { pmopm2Mesrchannel23Entry 2 }


--- *********************************************************
---     TABLE for the pmopm2Mesrchannel24 articles
--- *********************************************************

pmopm2Mesrchannel24Table OBJECT-TYPE
	SYNTAX  SEQUENCE OF Pmopm2Mesrchannel24Entry
	MAX-ACCESS not-accessible
	STATUS current
	DESCRIPTION
        "
        List of pmopm2Mesrchannel24 Article
        "
	::= { pmopm2MesrClient 62 }


pmopm2Mesrchannel24Entry OBJECT-TYPE
	SYNTAX Pmopm2Mesrchannel24Entry
	MAX-ACCESS not-accessible
	STATUS current
	DESCRIPTION
        "
        Row definition for the pmopm2Mesrchannel24
        table
        "
	INDEX   { pmopm2Mesrchannel24Index }
	::= { pmopm2Mesrchannel24Table 1 }


Pmopm2Mesrchannel24Entry ::=
	SEQUENCE {
	pmopm2Mesrchannel24Index
		INTEGER,
	pmopm2Mesrchannel24Portn
		INTEGER
	}


pmopm2Mesrchannel24Index OBJECT-TYPE
	SYNTAX  INTEGER(0..128)
	MAX-ACCESS  read-only
	STATUS current
	DESCRIPTION
        "
        Index definition for the pmopm2Mesrchannel24
        table
        "
	::= { pmopm2Mesrchannel24Entry 1 }


pmopm2Mesrchannel24Portn OBJECT-TYPE
	SYNTAX  INTEGER (0..65535)
	MAX-ACCESS read-only
	STATUS current
	DESCRIPTION
        "
        Channel24 Power :This OID indicates
        the channel power  (Power =Q8(Number
        format)) (Unit = dBm)<Help> This
        measure indicates the channel power
        "
	::= { pmopm2Mesrchannel24Entry 2 }


--- *********************************************************
---     TABLE for the pmopm2Mesrchannel25 articles
--- *********************************************************

pmopm2Mesrchannel25Table OBJECT-TYPE
	SYNTAX  SEQUENCE OF Pmopm2Mesrchannel25Entry
	MAX-ACCESS not-accessible
	STATUS current
	DESCRIPTION
        "
        List of pmopm2Mesrchannel25 Article
        "
	::= { pmopm2MesrClient 64 }


pmopm2Mesrchannel25Entry OBJECT-TYPE
	SYNTAX Pmopm2Mesrchannel25Entry
	MAX-ACCESS not-accessible
	STATUS current
	DESCRIPTION
        "
        Row definition for the pmopm2Mesrchannel25
        table
        "
	INDEX   { pmopm2Mesrchannel25Index }
	::= { pmopm2Mesrchannel25Table 1 }


Pmopm2Mesrchannel25Entry ::=
	SEQUENCE {
	pmopm2Mesrchannel25Index
		INTEGER,
	pmopm2Mesrchannel25Portn
		INTEGER
	}


pmopm2Mesrchannel25Index OBJECT-TYPE
	SYNTAX  INTEGER(0..128)
	MAX-ACCESS  read-only
	STATUS current
	DESCRIPTION
        "
        Index definition for the pmopm2Mesrchannel25
        table
        "
	::= { pmopm2Mesrchannel25Entry 1 }


pmopm2Mesrchannel25Portn OBJECT-TYPE
	SYNTAX  INTEGER (0..65535)
	MAX-ACCESS read-only
	STATUS current
	DESCRIPTION
        "
        Channel25 Power :This OID indicates
        the channel power  (Power =Q8(Number
        format)) (Unit = dBm)<Help> This
        measure indicates the channel power
        "
	::= { pmopm2Mesrchannel25Entry 2 }


--- *********************************************************
---     TABLE for the pmopm2Mesrchannel26 articles
--- *********************************************************

pmopm2Mesrchannel26Table OBJECT-TYPE
	SYNTAX  SEQUENCE OF Pmopm2Mesrchannel26Entry
	MAX-ACCESS not-accessible
	STATUS current
	DESCRIPTION
        "
        List of pmopm2Mesrchannel26 Article
        "
	::= { pmopm2MesrClient 66 }


pmopm2Mesrchannel26Entry OBJECT-TYPE
	SYNTAX Pmopm2Mesrchannel26Entry
	MAX-ACCESS not-accessible
	STATUS current
	DESCRIPTION
        "
        Row definition for the pmopm2Mesrchannel26
        table
        "
	INDEX   { pmopm2Mesrchannel26Index }
	::= { pmopm2Mesrchannel26Table 1 }


Pmopm2Mesrchannel26Entry ::=
	SEQUENCE {
	pmopm2Mesrchannel26Index
		INTEGER,
	pmopm2Mesrchannel26Portn
		INTEGER
	}


pmopm2Mesrchannel26Index OBJECT-TYPE
	SYNTAX  INTEGER(0..128)
	MAX-ACCESS  read-only
	STATUS current
	DESCRIPTION
        "
        Index definition for the pmopm2Mesrchannel26
        table
        "
	::= { pmopm2Mesrchannel26Entry 1 }


pmopm2Mesrchannel26Portn OBJECT-TYPE
	SYNTAX  INTEGER (0..65535)
	MAX-ACCESS read-only
	STATUS current
	DESCRIPTION
        "
        Channel26 Power :This OID indicates
        the channel power  (Power =Q8(Number
        format)) (Unit = dBm)<Help> This
        measure indicates the channel power
        "
	::= { pmopm2Mesrchannel26Entry 2 }


--- *********************************************************
---     TABLE for the pmopm2Mesrchannel27 articles
--- *********************************************************

pmopm2Mesrchannel27Table OBJECT-TYPE
	SYNTAX  SEQUENCE OF Pmopm2Mesrchannel27Entry
	MAX-ACCESS not-accessible
	STATUS current
	DESCRIPTION
        "
        List of pmopm2Mesrchannel27 Article
        "
	::= { pmopm2MesrClient 68 }


pmopm2Mesrchannel27Entry OBJECT-TYPE
	SYNTAX Pmopm2Mesrchannel27Entry
	MAX-ACCESS not-accessible
	STATUS current
	DESCRIPTION
        "
        Row definition for the pmopm2Mesrchannel27
        table
        "
	INDEX   { pmopm2Mesrchannel27Index }
	::= { pmopm2Mesrchannel27Table 1 }


Pmopm2Mesrchannel27Entry ::=
	SEQUENCE {
	pmopm2Mesrchannel27Index
		INTEGER,
	pmopm2Mesrchannel27Portn
		INTEGER
	}


pmopm2Mesrchannel27Index OBJECT-TYPE
	SYNTAX  INTEGER(0..128)
	MAX-ACCESS  read-only
	STATUS current
	DESCRIPTION
        "
        Index definition for the pmopm2Mesrchannel27
        table
        "
	::= { pmopm2Mesrchannel27Entry 1 }


pmopm2Mesrchannel27Portn OBJECT-TYPE
	SYNTAX  INTEGER (0..65535)
	MAX-ACCESS read-only
	STATUS current
	DESCRIPTION
        "
        Channel27 Power :This OID indicates
        the channel power  (Power =Q8(Number
        format)) (Unit = dBm)<Help> This
        measure indicates the channel power
        "
	::= { pmopm2Mesrchannel27Entry 2 }


--- *********************************************************
---     TABLE for the pmopm2Mesrchannel28 articles
--- *********************************************************

pmopm2Mesrchannel28Table OBJECT-TYPE
	SYNTAX  SEQUENCE OF Pmopm2Mesrchannel28Entry
	MAX-ACCESS not-accessible
	STATUS current
	DESCRIPTION
        "
        List of pmopm2Mesrchannel28 Article
        "
	::= { pmopm2MesrClient 70 }


pmopm2Mesrchannel28Entry OBJECT-TYPE
	SYNTAX Pmopm2Mesrchannel28Entry
	MAX-ACCESS not-accessible
	STATUS current
	DESCRIPTION
        "
        Row definition for the pmopm2Mesrchannel28
        table
        "
	INDEX   { pmopm2Mesrchannel28Index }
	::= { pmopm2Mesrchannel28Table 1 }


Pmopm2Mesrchannel28Entry ::=
	SEQUENCE {
	pmopm2Mesrchannel28Index
		INTEGER,
	pmopm2Mesrchannel28Portn
		INTEGER
	}


pmopm2Mesrchannel28Index OBJECT-TYPE
	SYNTAX  INTEGER(0..128)
	MAX-ACCESS  read-only
	STATUS current
	DESCRIPTION
        "
        Index definition for the pmopm2Mesrchannel28
        table
        "
	::= { pmopm2Mesrchannel28Entry 1 }


pmopm2Mesrchannel28Portn OBJECT-TYPE
	SYNTAX  INTEGER (0..65535)
	MAX-ACCESS read-only
	STATUS current
	DESCRIPTION
        "
        Channel28 Power :This OID indicates
        the channel power  (Power =Q8(Number
        format)) (Unit = dBm)<Help> This
        measure indicates the channel power
        "
	::= { pmopm2Mesrchannel28Entry 2 }


--- *********************************************************
---     TABLE for the pmopm2Mesrchannel29 articles
--- *********************************************************

pmopm2Mesrchannel29Table OBJECT-TYPE
	SYNTAX  SEQUENCE OF Pmopm2Mesrchannel29Entry
	MAX-ACCESS not-accessible
	STATUS current
	DESCRIPTION
        "
        List of pmopm2Mesrchannel29 Article
        "
	::= { pmopm2MesrClient 72 }


pmopm2Mesrchannel29Entry OBJECT-TYPE
	SYNTAX Pmopm2Mesrchannel29Entry
	MAX-ACCESS not-accessible
	STATUS current
	DESCRIPTION
        "
        Row definition for the pmopm2Mesrchannel29
        table
        "
	INDEX   { pmopm2Mesrchannel29Index }
	::= { pmopm2Mesrchannel29Table 1 }


Pmopm2Mesrchannel29Entry ::=
	SEQUENCE {
	pmopm2Mesrchannel29Index
		INTEGER,
	pmopm2Mesrchannel29Portn
		INTEGER
	}


pmopm2Mesrchannel29Index OBJECT-TYPE
	SYNTAX  INTEGER(0..128)
	MAX-ACCESS  read-only
	STATUS current
	DESCRIPTION
        "
        Index definition for the pmopm2Mesrchannel29
        table
        "
	::= { pmopm2Mesrchannel29Entry 1 }


pmopm2Mesrchannel29Portn OBJECT-TYPE
	SYNTAX  INTEGER (0..65535)
	MAX-ACCESS read-only
	STATUS current
	DESCRIPTION
        "
        Channel29 Power :This OID indicates
        the channel power  (Power =Q8(Number
        format)) (Unit = dBm)<Help> This
        measure indicates the channel power
        "
	::= { pmopm2Mesrchannel29Entry 2 }


--- *********************************************************
---     TABLE for the pmopm2Mesrchannel30 articles
--- *********************************************************

pmopm2Mesrchannel30Table OBJECT-TYPE
	SYNTAX  SEQUENCE OF Pmopm2Mesrchannel30Entry
	MAX-ACCESS not-accessible
	STATUS current
	DESCRIPTION
        "
        List of pmopm2Mesrchannel30 Article
        "
	::= { pmopm2MesrClient 74 }


pmopm2Mesrchannel30Entry OBJECT-TYPE
	SYNTAX Pmopm2Mesrchannel30Entry
	MAX-ACCESS not-accessible
	STATUS current
	DESCRIPTION
        "
        Row definition for the pmopm2Mesrchannel30
        table
        "
	INDEX   { pmopm2Mesrchannel30Index }
	::= { pmopm2Mesrchannel30Table 1 }


Pmopm2Mesrchannel30Entry ::=
	SEQUENCE {
	pmopm2Mesrchannel30Index
		INTEGER,
	pmopm2Mesrchannel30Portn
		INTEGER
	}


pmopm2Mesrchannel30Index OBJECT-TYPE
	SYNTAX  INTEGER(0..128)
	MAX-ACCESS  read-only
	STATUS current
	DESCRIPTION
        "
        Index definition for the pmopm2Mesrchannel30
        table
        "
	::= { pmopm2Mesrchannel30Entry 1 }


pmopm2Mesrchannel30Portn OBJECT-TYPE
	SYNTAX  INTEGER (0..65535)
	MAX-ACCESS read-only
	STATUS current
	DESCRIPTION
        "
        Channel30 Power :This OID indicates
        the channel power  (Power =Q8(Number
        format)) (Unit = dBm)<Help> This
        measure indicates the channel power
        "
	::= { pmopm2Mesrchannel30Entry 2 }


--- *********************************************************
---     TABLE for the pmopm2Mesrchannel31 articles
--- *********************************************************

pmopm2Mesrchannel31Table OBJECT-TYPE
	SYNTAX  SEQUENCE OF Pmopm2Mesrchannel31Entry
	MAX-ACCESS not-accessible
	STATUS current
	DESCRIPTION
        "
        List of pmopm2Mesrchannel31 Article
        "
	::= { pmopm2MesrClient 76 }


pmopm2Mesrchannel31Entry OBJECT-TYPE
	SYNTAX Pmopm2Mesrchannel31Entry
	MAX-ACCESS not-accessible
	STATUS current
	DESCRIPTION
        "
        Row definition for the pmopm2Mesrchannel31
        table
        "
	INDEX   { pmopm2Mesrchannel31Index }
	::= { pmopm2Mesrchannel31Table 1 }


Pmopm2Mesrchannel31Entry ::=
	SEQUENCE {
	pmopm2Mesrchannel31Index
		INTEGER,
	pmopm2Mesrchannel31Portn
		INTEGER
	}


pmopm2Mesrchannel31Index OBJECT-TYPE
	SYNTAX  INTEGER(0..128)
	MAX-ACCESS  read-only
	STATUS current
	DESCRIPTION
        "
        Index definition for the pmopm2Mesrchannel31
        table
        "
	::= { pmopm2Mesrchannel31Entry 1 }


pmopm2Mesrchannel31Portn OBJECT-TYPE
	SYNTAX  INTEGER (0..65535)
	MAX-ACCESS read-only
	STATUS current
	DESCRIPTION
        "
        Channel31 Power :This OID indicates
        the channel power  (Power =Q8(Number
        format)) (Unit = dBm)<Help> This
        measure indicates the channel power
        "
	::= { pmopm2Mesrchannel31Entry 2 }


--- *********************************************************
---     TABLE for the pmopm2Mesrchannel32 articles
--- *********************************************************

pmopm2Mesrchannel32Table OBJECT-TYPE
	SYNTAX  SEQUENCE OF Pmopm2Mesrchannel32Entry
	MAX-ACCESS not-accessible
	STATUS current
	DESCRIPTION
        "
        List of pmopm2Mesrchannel32 Article
        "
	::= { pmopm2MesrClient 78 }


pmopm2Mesrchannel32Entry OBJECT-TYPE
	SYNTAX Pmopm2Mesrchannel32Entry
	MAX-ACCESS not-accessible
	STATUS current
	DESCRIPTION
        "
        Row definition for the pmopm2Mesrchannel32
        table
        "
	INDEX   { pmopm2Mesrchannel32Index }
	::= { pmopm2Mesrchannel32Table 1 }


Pmopm2Mesrchannel32Entry ::=
	SEQUENCE {
	pmopm2Mesrchannel32Index
		INTEGER,
	pmopm2Mesrchannel32Portn
		INTEGER
	}


pmopm2Mesrchannel32Index OBJECT-TYPE
	SYNTAX  INTEGER(0..128)
	MAX-ACCESS  read-only
	STATUS current
	DESCRIPTION
        "
        Index definition for the pmopm2Mesrchannel32
        table
        "
	::= { pmopm2Mesrchannel32Entry 1 }


pmopm2Mesrchannel32Portn OBJECT-TYPE
	SYNTAX  INTEGER (0..65535)
	MAX-ACCESS read-only
	STATUS current
	DESCRIPTION
        "
        Channel32 Power :This OID indicates
        the channel power  (Power =Q8(Number
        format)) (Unit = dBm)<Help> This
        measure indicates the channel power
        "
	::= { pmopm2Mesrchannel32Entry 2 }


--- *********************************************************
---     TABLE for the pmopm2Mesrchannel33 articles
--- *********************************************************

pmopm2Mesrchannel33Table OBJECT-TYPE
	SYNTAX  SEQUENCE OF Pmopm2Mesrchannel33Entry
	MAX-ACCESS not-accessible
	STATUS current
	DESCRIPTION
        "
        List of pmopm2Mesrchannel33 Article
        "
	::= { pmopm2MesrClient 80 }


pmopm2Mesrchannel33Entry OBJECT-TYPE
	SYNTAX Pmopm2Mesrchannel33Entry
	MAX-ACCESS not-accessible
	STATUS current
	DESCRIPTION
        "
        Row definition for the pmopm2Mesrchannel33
        table
        "
	INDEX   { pmopm2Mesrchannel33Index }
	::= { pmopm2Mesrchannel33Table 1 }


Pmopm2Mesrchannel33Entry ::=
	SEQUENCE {
	pmopm2Mesrchannel33Index
		INTEGER,
	pmopm2Mesrchannel33Portn
		INTEGER
	}


pmopm2Mesrchannel33Index OBJECT-TYPE
	SYNTAX  INTEGER(0..128)
	MAX-ACCESS  read-only
	STATUS current
	DESCRIPTION
        "
        Index definition for the pmopm2Mesrchannel33
        table
        "
	::= { pmopm2Mesrchannel33Entry 1 }


pmopm2Mesrchannel33Portn OBJECT-TYPE
	SYNTAX  INTEGER (0..65535)
	MAX-ACCESS read-only
	STATUS current
	DESCRIPTION
        "
        Channel33 Power :This OID indicates
        the channel power  (Power =Q8(Number
        format)) (Unit = dBm)<Help> This
        measure indicates the channel power
        "
	::= { pmopm2Mesrchannel33Entry 2 }


--- *********************************************************
---     TABLE for the pmopm2Mesrchannel34 articles
--- *********************************************************

pmopm2Mesrchannel34Table OBJECT-TYPE
	SYNTAX  SEQUENCE OF Pmopm2Mesrchannel34Entry
	MAX-ACCESS not-accessible
	STATUS current
	DESCRIPTION
        "
        List of pmopm2Mesrchannel34 Article
        "
	::= { pmopm2MesrClient 82 }


pmopm2Mesrchannel34Entry OBJECT-TYPE
	SYNTAX Pmopm2Mesrchannel34Entry
	MAX-ACCESS not-accessible
	STATUS current
	DESCRIPTION
        "
        Row definition for the pmopm2Mesrchannel34
        table
        "
	INDEX   { pmopm2Mesrchannel34Index }
	::= { pmopm2Mesrchannel34Table 1 }


Pmopm2Mesrchannel34Entry ::=
	SEQUENCE {
	pmopm2Mesrchannel34Index
		INTEGER,
	pmopm2Mesrchannel34Portn
		INTEGER
	}


pmopm2Mesrchannel34Index OBJECT-TYPE
	SYNTAX  INTEGER(0..128)
	MAX-ACCESS  read-only
	STATUS current
	DESCRIPTION
        "
        Index definition for the pmopm2Mesrchannel34
        table
        "
	::= { pmopm2Mesrchannel34Entry 1 }


pmopm2Mesrchannel34Portn OBJECT-TYPE
	SYNTAX  INTEGER (0..65535)
	MAX-ACCESS read-only
	STATUS current
	DESCRIPTION
        "
        Channel34 Power :This OID indicates
        the channel power  (Power =Q8(Number
        format)) (Unit = dBm)<Help> This
        measure indicates the channel power
        "
	::= { pmopm2Mesrchannel34Entry 2 }


--- *********************************************************
---     TABLE for the pmopm2Mesrchannel35 articles
--- *********************************************************

pmopm2Mesrchannel35Table OBJECT-TYPE
	SYNTAX  SEQUENCE OF Pmopm2Mesrchannel35Entry
	MAX-ACCESS not-accessible
	STATUS current
	DESCRIPTION
        "
        List of pmopm2Mesrchannel35 Article
        "
	::= { pmopm2MesrClient 84 }


pmopm2Mesrchannel35Entry OBJECT-TYPE
	SYNTAX Pmopm2Mesrchannel35Entry
	MAX-ACCESS not-accessible
	STATUS current
	DESCRIPTION
        "
        Row definition for the pmopm2Mesrchannel35
        table
        "
	INDEX   { pmopm2Mesrchannel35Index }
	::= { pmopm2Mesrchannel35Table 1 }


Pmopm2Mesrchannel35Entry ::=
	SEQUENCE {
	pmopm2Mesrchannel35Index
		INTEGER,
	pmopm2Mesrchannel35Portn
		INTEGER
	}


pmopm2Mesrchannel35Index OBJECT-TYPE
	SYNTAX  INTEGER(0..128)
	MAX-ACCESS  read-only
	STATUS current
	DESCRIPTION
        "
        Index definition for the pmopm2Mesrchannel35
        table
        "
	::= { pmopm2Mesrchannel35Entry 1 }


pmopm2Mesrchannel35Portn OBJECT-TYPE
	SYNTAX  INTEGER (0..65535)
	MAX-ACCESS read-only
	STATUS current
	DESCRIPTION
        "
        Channel35 Power :This OID indicates
        the channel power  (Power =Q8(Number
        format)) (Unit = dBm)<Help> This
        measure indicates the channel power
        "
	::= { pmopm2Mesrchannel35Entry 2 }


--- *********************************************************
---     TABLE for the pmopm2Mesrchannel36 articles
--- *********************************************************

pmopm2Mesrchannel36Table OBJECT-TYPE
	SYNTAX  SEQUENCE OF Pmopm2Mesrchannel36Entry
	MAX-ACCESS not-accessible
	STATUS current
	DESCRIPTION
        "
        List of pmopm2Mesrchannel36 Article
        "
	::= { pmopm2MesrClient 86 }


pmopm2Mesrchannel36Entry OBJECT-TYPE
	SYNTAX Pmopm2Mesrchannel36Entry
	MAX-ACCESS not-accessible
	STATUS current
	DESCRIPTION
        "
        Row definition for the pmopm2Mesrchannel36
        table
        "
	INDEX   { pmopm2Mesrchannel36Index }
	::= { pmopm2Mesrchannel36Table 1 }


Pmopm2Mesrchannel36Entry ::=
	SEQUENCE {
	pmopm2Mesrchannel36Index
		INTEGER,
	pmopm2Mesrchannel36Portn
		INTEGER
	}


pmopm2Mesrchannel36Index OBJECT-TYPE
	SYNTAX  INTEGER(0..128)
	MAX-ACCESS  read-only
	STATUS current
	DESCRIPTION
        "
        Index definition for the pmopm2Mesrchannel36
        table
        "
	::= { pmopm2Mesrchannel36Entry 1 }


pmopm2Mesrchannel36Portn OBJECT-TYPE
	SYNTAX  INTEGER (0..65535)
	MAX-ACCESS read-only
	STATUS current
	DESCRIPTION
        "
        Channel36 Power :This OID indicates
        the channel power  (Power =Q8(Number
        format)) (Unit = dBm)<Help> This
        measure indicates the channel power
        "
	::= { pmopm2Mesrchannel36Entry 2 }


--- *********************************************************
---     TABLE for the pmopm2Mesrchannel37 articles
--- *********************************************************

pmopm2Mesrchannel37Table OBJECT-TYPE
	SYNTAX  SEQUENCE OF Pmopm2Mesrchannel37Entry
	MAX-ACCESS not-accessible
	STATUS current
	DESCRIPTION
        "
        List of pmopm2Mesrchannel37 Article
        "
	::= { pmopm2MesrClient 88 }


pmopm2Mesrchannel37Entry OBJECT-TYPE
	SYNTAX Pmopm2Mesrchannel37Entry
	MAX-ACCESS not-accessible
	STATUS current
	DESCRIPTION
        "
        Row definition for the pmopm2Mesrchannel37
        table
        "
	INDEX   { pmopm2Mesrchannel37Index }
	::= { pmopm2Mesrchannel37Table 1 }


Pmopm2Mesrchannel37Entry ::=
	SEQUENCE {
	pmopm2Mesrchannel37Index
		INTEGER,
	pmopm2Mesrchannel37Portn
		INTEGER
	}


pmopm2Mesrchannel37Index OBJECT-TYPE
	SYNTAX  INTEGER(0..128)
	MAX-ACCESS  read-only
	STATUS current
	DESCRIPTION
        "
        Index definition for the pmopm2Mesrchannel37
        table
        "
	::= { pmopm2Mesrchannel37Entry 1 }


pmopm2Mesrchannel37Portn OBJECT-TYPE
	SYNTAX  INTEGER (0..65535)
	MAX-ACCESS read-only
	STATUS current
	DESCRIPTION
        "
        Channel37 Power :This OID indicates
        the channel power  (Power =Q8(Number
        format)) (Unit = dBm)<Help> This
        measure indicates the channel power
        "
	::= { pmopm2Mesrchannel37Entry 2 }


--- *********************************************************
---     TABLE for the pmopm2Mesrchannel38 articles
--- *********************************************************

pmopm2Mesrchannel38Table OBJECT-TYPE
	SYNTAX  SEQUENCE OF Pmopm2Mesrchannel38Entry
	MAX-ACCESS not-accessible
	STATUS current
	DESCRIPTION
        "
        List of pmopm2Mesrchannel38 Article
        "
	::= { pmopm2MesrClient 90 }


pmopm2Mesrchannel38Entry OBJECT-TYPE
	SYNTAX Pmopm2Mesrchannel38Entry
	MAX-ACCESS not-accessible
	STATUS current
	DESCRIPTION
        "
        Row definition for the pmopm2Mesrchannel38
        table
        "
	INDEX   { pmopm2Mesrchannel38Index }
	::= { pmopm2Mesrchannel38Table 1 }


Pmopm2Mesrchannel38Entry ::=
	SEQUENCE {
	pmopm2Mesrchannel38Index
		INTEGER,
	pmopm2Mesrchannel38Portn
		INTEGER
	}


pmopm2Mesrchannel38Index OBJECT-TYPE
	SYNTAX  INTEGER(0..128)
	MAX-ACCESS  read-only
	STATUS current
	DESCRIPTION
        "
        Index definition for the pmopm2Mesrchannel38
        table
        "
	::= { pmopm2Mesrchannel38Entry 1 }


pmopm2Mesrchannel38Portn OBJECT-TYPE
	SYNTAX  INTEGER (0..65535)
	MAX-ACCESS read-only
	STATUS current
	DESCRIPTION
        "
        Channel38 Power :This OID indicates
        the channel power  (Power =Q8(Number
        format)) (Unit = dBm)<Help> This
        measure indicates the channel power
        "
	::= { pmopm2Mesrchannel38Entry 2 }


--- *********************************************************
---     TABLE for the pmopm2Mesrchannel39 articles
--- *********************************************************

pmopm2Mesrchannel39Table OBJECT-TYPE
	SYNTAX  SEQUENCE OF Pmopm2Mesrchannel39Entry
	MAX-ACCESS not-accessible
	STATUS current
	DESCRIPTION
        "
        List of pmopm2Mesrchannel39 Article
        "
	::= { pmopm2MesrClient 92 }


pmopm2Mesrchannel39Entry OBJECT-TYPE
	SYNTAX Pmopm2Mesrchannel39Entry
	MAX-ACCESS not-accessible
	STATUS current
	DESCRIPTION
        "
        Row definition for the pmopm2Mesrchannel39
        table
        "
	INDEX   { pmopm2Mesrchannel39Index }
	::= { pmopm2Mesrchannel39Table 1 }


Pmopm2Mesrchannel39Entry ::=
	SEQUENCE {
	pmopm2Mesrchannel39Index
		INTEGER,
	pmopm2Mesrchannel39Portn
		INTEGER
	}


pmopm2Mesrchannel39Index OBJECT-TYPE
	SYNTAX  INTEGER(0..128)
	MAX-ACCESS  read-only
	STATUS current
	DESCRIPTION
        "
        Index definition for the pmopm2Mesrchannel39
        table
        "
	::= { pmopm2Mesrchannel39Entry 1 }


pmopm2Mesrchannel39Portn OBJECT-TYPE
	SYNTAX  INTEGER (0..65535)
	MAX-ACCESS read-only
	STATUS current
	DESCRIPTION
        "
        Channel39 Power :This OID indicates
        the channel power  (Power =Q8(Number
        format)) (Unit = dBm)<Help> This
        measure indicates the channel power
        "
	::= { pmopm2Mesrchannel39Entry 2 }


--- *********************************************************
---     TABLE for the pmopm2Mesrchannel40 articles
--- *********************************************************

pmopm2Mesrchannel40Table OBJECT-TYPE
	SYNTAX  SEQUENCE OF Pmopm2Mesrchannel40Entry
	MAX-ACCESS not-accessible
	STATUS current
	DESCRIPTION
        "
        List of pmopm2Mesrchannel40 Article
        "
	::= { pmopm2MesrClient 94 }


pmopm2Mesrchannel40Entry OBJECT-TYPE
	SYNTAX Pmopm2Mesrchannel40Entry
	MAX-ACCESS not-accessible
	STATUS current
	DESCRIPTION
        "
        Row definition for the pmopm2Mesrchannel40
        table
        "
	INDEX   { pmopm2Mesrchannel40Index }
	::= { pmopm2Mesrchannel40Table 1 }


Pmopm2Mesrchannel40Entry ::=
	SEQUENCE {
	pmopm2Mesrchannel40Index
		INTEGER,
	pmopm2Mesrchannel40Portn
		INTEGER
	}


pmopm2Mesrchannel40Index OBJECT-TYPE
	SYNTAX  INTEGER(0..128)
	MAX-ACCESS  read-only
	STATUS current
	DESCRIPTION
        "
        Index definition for the pmopm2Mesrchannel40
        table
        "
	::= { pmopm2Mesrchannel40Entry 1 }


pmopm2Mesrchannel40Portn OBJECT-TYPE
	SYNTAX  INTEGER (0..65535)
	MAX-ACCESS read-only
	STATUS current
	DESCRIPTION
        "
        Channel40 Power :This OID indicates
        the channel power  (Power =Q8(Number
        format)) (Unit = dBm)<Help> This
        measure indicates the channel power
        "
	::= { pmopm2Mesrchannel40Entry 2 }


--- *********************************************************
---     TABLE for the pmopm2Mesrchannel41 articles
--- *********************************************************

pmopm2Mesrchannel41Table OBJECT-TYPE
	SYNTAX  SEQUENCE OF Pmopm2Mesrchannel41Entry
	MAX-ACCESS not-accessible
	STATUS current
	DESCRIPTION
        "
        List of pmopm2Mesrchannel41 Article
        "
	::= { pmopm2MesrClient 96 }


pmopm2Mesrchannel41Entry OBJECT-TYPE
	SYNTAX Pmopm2Mesrchannel41Entry
	MAX-ACCESS not-accessible
	STATUS current
	DESCRIPTION
        "
        Row definition for the pmopm2Mesrchannel41
        table
        "
	INDEX   { pmopm2Mesrchannel41Index }
	::= { pmopm2Mesrchannel41Table 1 }


Pmopm2Mesrchannel41Entry ::=
	SEQUENCE {
	pmopm2Mesrchannel41Index
		INTEGER,
	pmopm2Mesrchannel41Portn
		INTEGER
	}


pmopm2Mesrchannel41Index OBJECT-TYPE
	SYNTAX  INTEGER(0..128)
	MAX-ACCESS  read-only
	STATUS current
	DESCRIPTION
        "
        Index definition for the pmopm2Mesrchannel41
        table
        "
	::= { pmopm2Mesrchannel41Entry 1 }


pmopm2Mesrchannel41Portn OBJECT-TYPE
	SYNTAX  INTEGER (0..65535)
	MAX-ACCESS read-only
	STATUS current
	DESCRIPTION
        "
        Channel41 Power :This OID indicates
        the channel power  (Power =Q8(Number
        format)) (Unit = dBm)<Help> This
        measure indicates the channel power
        "
	::= { pmopm2Mesrchannel41Entry 2 }


--- *********************************************************
---     TABLE for the pmopm2Mesrchannel42 articles
--- *********************************************************

pmopm2Mesrchannel42Table OBJECT-TYPE
	SYNTAX  SEQUENCE OF Pmopm2Mesrchannel42Entry
	MAX-ACCESS not-accessible
	STATUS current
	DESCRIPTION
        "
        List of pmopm2Mesrchannel42 Article
        "
	::= { pmopm2MesrClient 98 }


pmopm2Mesrchannel42Entry OBJECT-TYPE
	SYNTAX Pmopm2Mesrchannel42Entry
	MAX-ACCESS not-accessible
	STATUS current
	DESCRIPTION
        "
        Row definition for the pmopm2Mesrchannel42
        table
        "
	INDEX   { pmopm2Mesrchannel42Index }
	::= { pmopm2Mesrchannel42Table 1 }


Pmopm2Mesrchannel42Entry ::=
	SEQUENCE {
	pmopm2Mesrchannel42Index
		INTEGER,
	pmopm2Mesrchannel42Portn
		INTEGER
	}


pmopm2Mesrchannel42Index OBJECT-TYPE
	SYNTAX  INTEGER(0..128)
	MAX-ACCESS  read-only
	STATUS current
	DESCRIPTION
        "
        Index definition for the pmopm2Mesrchannel42
        table
        "
	::= { pmopm2Mesrchannel42Entry 1 }


pmopm2Mesrchannel42Portn OBJECT-TYPE
	SYNTAX  INTEGER (0..65535)
	MAX-ACCESS read-only
	STATUS current
	DESCRIPTION
        "
        Channel42 Power :This OID indicates
        the channel power  (Power =Q8(Number
        format)) (Unit = dBm)<Help> This
        measure indicates the channel power
        "
	::= { pmopm2Mesrchannel42Entry 2 }


--- *********************************************************
---     TABLE for the pmopm2Mesrchannel43 articles
--- *********************************************************

pmopm2Mesrchannel43Table OBJECT-TYPE
	SYNTAX  SEQUENCE OF Pmopm2Mesrchannel43Entry
	MAX-ACCESS not-accessible
	STATUS current
	DESCRIPTION
        "
        List of pmopm2Mesrchannel43 Article
        "
	::= { pmopm2MesrClient 100 }


pmopm2Mesrchannel43Entry OBJECT-TYPE
	SYNTAX Pmopm2Mesrchannel43Entry
	MAX-ACCESS not-accessible
	STATUS current
	DESCRIPTION
        "
        Row definition for the pmopm2Mesrchannel43
        table
        "
	INDEX   { pmopm2Mesrchannel43Index }
	::= { pmopm2Mesrchannel43Table 1 }


Pmopm2Mesrchannel43Entry ::=
	SEQUENCE {
	pmopm2Mesrchannel43Index
		INTEGER,
	pmopm2Mesrchannel43Portn
		INTEGER
	}


pmopm2Mesrchannel43Index OBJECT-TYPE
	SYNTAX  INTEGER(0..128)
	MAX-ACCESS  read-only
	STATUS current
	DESCRIPTION
        "
        Index definition for the pmopm2Mesrchannel43
        table
        "
	::= { pmopm2Mesrchannel43Entry 1 }


pmopm2Mesrchannel43Portn OBJECT-TYPE
	SYNTAX  INTEGER (0..65535)
	MAX-ACCESS read-only
	STATUS current
	DESCRIPTION
        "
        Channel43 Power :This OID indicates
        the channel power  (Power =Q8(Number
        format)) (Unit = dBm)<Help> This
        measure indicates the channel power
        "
	::= { pmopm2Mesrchannel43Entry 2 }


--- *********************************************************
---     TABLE for the pmopm2Mesrchannel44 articles
--- *********************************************************

pmopm2Mesrchannel44Table OBJECT-TYPE
	SYNTAX  SEQUENCE OF Pmopm2Mesrchannel44Entry
	MAX-ACCESS not-accessible
	STATUS current
	DESCRIPTION
        "
        List of pmopm2Mesrchannel44 Article
        "
	::= { pmopm2MesrClient 102 }


pmopm2Mesrchannel44Entry OBJECT-TYPE
	SYNTAX Pmopm2Mesrchannel44Entry
	MAX-ACCESS not-accessible
	STATUS current
	DESCRIPTION
        "
        Row definition for the pmopm2Mesrchannel44
        table
        "
	INDEX   { pmopm2Mesrchannel44Index }
	::= { pmopm2Mesrchannel44Table 1 }


Pmopm2Mesrchannel44Entry ::=
	SEQUENCE {
	pmopm2Mesrchannel44Index
		INTEGER,
	pmopm2Mesrchannel44Portn
		INTEGER
	}


pmopm2Mesrchannel44Index OBJECT-TYPE
	SYNTAX  INTEGER(0..128)
	MAX-ACCESS  read-only
	STATUS current
	DESCRIPTION
        "
        Index definition for the pmopm2Mesrchannel44
        table
        "
	::= { pmopm2Mesrchannel44Entry 1 }


pmopm2Mesrchannel44Portn OBJECT-TYPE
	SYNTAX  INTEGER (0..65535)
	MAX-ACCESS read-only
	STATUS current
	DESCRIPTION
        "
        Channel44 Power :This OID indicates
        the channel power  (Power =Q8(Number
        format)) (Unit = dBm)<Help> This
        measure indicates the channel power
        "
	::= { pmopm2Mesrchannel44Entry 2 }


--- *********************************************************
---     TABLE for the pmopm2Mesrchannel45 articles
--- *********************************************************

pmopm2Mesrchannel45Table OBJECT-TYPE
	SYNTAX  SEQUENCE OF Pmopm2Mesrchannel45Entry
	MAX-ACCESS not-accessible
	STATUS current
	DESCRIPTION
        "
        List of pmopm2Mesrchannel45 Article
        "
	::= { pmopm2MesrClient 104 }


pmopm2Mesrchannel45Entry OBJECT-TYPE
	SYNTAX Pmopm2Mesrchannel45Entry
	MAX-ACCESS not-accessible
	STATUS current
	DESCRIPTION
        "
        Row definition for the pmopm2Mesrchannel45
        table
        "
	INDEX   { pmopm2Mesrchannel45Index }
	::= { pmopm2Mesrchannel45Table 1 }


Pmopm2Mesrchannel45Entry ::=
	SEQUENCE {
	pmopm2Mesrchannel45Index
		INTEGER,
	pmopm2Mesrchannel45Portn
		INTEGER
	}


pmopm2Mesrchannel45Index OBJECT-TYPE
	SYNTAX  INTEGER(0..128)
	MAX-ACCESS  read-only
	STATUS current
	DESCRIPTION
        "
        Index definition for the pmopm2Mesrchannel45
        table
        "
	::= { pmopm2Mesrchannel45Entry 1 }


pmopm2Mesrchannel45Portn OBJECT-TYPE
	SYNTAX  INTEGER (0..65535)
	MAX-ACCESS read-only
	STATUS current
	DESCRIPTION
        "
        Channel45 Power :This OID indicates
        the channel power  (Power =Q8(Number
        format)) (Unit = dBm)<Help> This
        measure indicates the channel power
        "
	::= { pmopm2Mesrchannel45Entry 2 }


--- *********************************************************
---     TABLE for the pmopm2Mesrchannel46 articles
--- *********************************************************

pmopm2Mesrchannel46Table OBJECT-TYPE
	SYNTAX  SEQUENCE OF Pmopm2Mesrchannel46Entry
	MAX-ACCESS not-accessible
	STATUS current
	DESCRIPTION
        "
        List of pmopm2Mesrchannel46 Article
        "
	::= { pmopm2MesrClient 106 }


pmopm2Mesrchannel46Entry OBJECT-TYPE
	SYNTAX Pmopm2Mesrchannel46Entry
	MAX-ACCESS not-accessible
	STATUS current
	DESCRIPTION
        "
        Row definition for the pmopm2Mesrchannel46
        table
        "
	INDEX   { pmopm2Mesrchannel46Index }
	::= { pmopm2Mesrchannel46Table 1 }


Pmopm2Mesrchannel46Entry ::=
	SEQUENCE {
	pmopm2Mesrchannel46Index
		INTEGER,
	pmopm2Mesrchannel46Portn
		INTEGER
	}


pmopm2Mesrchannel46Index OBJECT-TYPE
	SYNTAX  INTEGER(0..128)
	MAX-ACCESS  read-only
	STATUS current
	DESCRIPTION
        "
        Index definition for the pmopm2Mesrchannel46
        table
        "
	::= { pmopm2Mesrchannel46Entry 1 }


pmopm2Mesrchannel46Portn OBJECT-TYPE
	SYNTAX  INTEGER (0..65535)
	MAX-ACCESS read-only
	STATUS current
	DESCRIPTION
        "
        Channel46 Power :This OID indicates
        the channel power  (Power =Q8(Number
        format)) (Unit = dBm)<Help> This
        measure indicates the channel power
        "
	::= { pmopm2Mesrchannel46Entry 2 }


--- *********************************************************
---     TABLE for the pmopm2Mesrchannel47 articles
--- *********************************************************

pmopm2Mesrchannel47Table OBJECT-TYPE
	SYNTAX  SEQUENCE OF Pmopm2Mesrchannel47Entry
	MAX-ACCESS not-accessible
	STATUS current
	DESCRIPTION
        "
        List of pmopm2Mesrchannel47 Article
        "
	::= { pmopm2MesrClient 108 }


pmopm2Mesrchannel47Entry OBJECT-TYPE
	SYNTAX Pmopm2Mesrchannel47Entry
	MAX-ACCESS not-accessible
	STATUS current
	DESCRIPTION
        "
        Row definition for the pmopm2Mesrchannel47
        table
        "
	INDEX   { pmopm2Mesrchannel47Index }
	::= { pmopm2Mesrchannel47Table 1 }


Pmopm2Mesrchannel47Entry ::=
	SEQUENCE {
	pmopm2Mesrchannel47Index
		INTEGER,
	pmopm2Mesrchannel47Portn
		INTEGER
	}


pmopm2Mesrchannel47Index OBJECT-TYPE
	SYNTAX  INTEGER(0..128)
	MAX-ACCESS  read-only
	STATUS current
	DESCRIPTION
        "
        Index definition for the pmopm2Mesrchannel47
        table
        "
	::= { pmopm2Mesrchannel47Entry 1 }


pmopm2Mesrchannel47Portn OBJECT-TYPE
	SYNTAX  INTEGER (0..65535)
	MAX-ACCESS read-only
	STATUS current
	DESCRIPTION
        "
        Channel47 Power :This OID indicates
        the channel power  (Power =Q8(Number
        format)) (Unit = dBm)<Help> This
        measure indicates the channel power
        "
	::= { pmopm2Mesrchannel47Entry 2 }


--- *********************************************************
---     TABLE for the pmopm2Mesrchannel48 articles
--- *********************************************************

pmopm2Mesrchannel48Table OBJECT-TYPE
	SYNTAX  SEQUENCE OF Pmopm2Mesrchannel48Entry
	MAX-ACCESS not-accessible
	STATUS current
	DESCRIPTION
        "
        List of pmopm2Mesrchannel48 Article
        "
	::= { pmopm2MesrClient 110 }


pmopm2Mesrchannel48Entry OBJECT-TYPE
	SYNTAX Pmopm2Mesrchannel48Entry
	MAX-ACCESS not-accessible
	STATUS current
	DESCRIPTION
        "
        Row definition for the pmopm2Mesrchannel48
        table
        "
	INDEX   { pmopm2Mesrchannel48Index }
	::= { pmopm2Mesrchannel48Table 1 }


Pmopm2Mesrchannel48Entry ::=
	SEQUENCE {
	pmopm2Mesrchannel48Index
		INTEGER,
	pmopm2Mesrchannel48Portn
		INTEGER
	}


pmopm2Mesrchannel48Index OBJECT-TYPE
	SYNTAX  INTEGER(0..128)
	MAX-ACCESS  read-only
	STATUS current
	DESCRIPTION
        "
        Index definition for the pmopm2Mesrchannel48
        table
        "
	::= { pmopm2Mesrchannel48Entry 1 }


pmopm2Mesrchannel48Portn OBJECT-TYPE
	SYNTAX  INTEGER (0..65535)
	MAX-ACCESS read-only
	STATUS current
	DESCRIPTION
        "
        Channel48 Power :This OID indicates
        the channel power  (Power =Q8(Number
        format)) (Unit = dBm)<Help> This
        measure indicates the channel power
        "
	::= { pmopm2Mesrchannel48Entry 2 }


--- *********************************************************
---     TABLE for the pmopm2Mesrchannel49 articles
--- *********************************************************

pmopm2Mesrchannel49Table OBJECT-TYPE
	SYNTAX  SEQUENCE OF Pmopm2Mesrchannel49Entry
	MAX-ACCESS not-accessible
	STATUS current
	DESCRIPTION
        "
        List of pmopm2Mesrchannel49 Article
        "
	::= { pmopm2MesrClient 112 }


pmopm2Mesrchannel49Entry OBJECT-TYPE
	SYNTAX Pmopm2Mesrchannel49Entry
	MAX-ACCESS not-accessible
	STATUS current
	DESCRIPTION
        "
        Row definition for the pmopm2Mesrchannel49
        table
        "
	INDEX   { pmopm2Mesrchannel49Index }
	::= { pmopm2Mesrchannel49Table 1 }


Pmopm2Mesrchannel49Entry ::=
	SEQUENCE {
	pmopm2Mesrchannel49Index
		INTEGER,
	pmopm2Mesrchannel49Portn
		INTEGER
	}


pmopm2Mesrchannel49Index OBJECT-TYPE
	SYNTAX  INTEGER(0..128)
	MAX-ACCESS  read-only
	STATUS current
	DESCRIPTION
        "
        Index definition for the pmopm2Mesrchannel49
        table
        "
	::= { pmopm2Mesrchannel49Entry 1 }


pmopm2Mesrchannel49Portn OBJECT-TYPE
	SYNTAX  INTEGER (0..65535)
	MAX-ACCESS read-only
	STATUS current
	DESCRIPTION
        "
        Channel49 Power :This OID indicates
        the channel power  (Power =Q8(Number
        format)) (Unit = dBm)<Help> This
        measure indicates the channel power
        "
	::= { pmopm2Mesrchannel49Entry 2 }


--- *********************************************************
---     TABLE for the pmopm2Mesrchannel50 articles
--- *********************************************************

pmopm2Mesrchannel50Table OBJECT-TYPE
	SYNTAX  SEQUENCE OF Pmopm2Mesrchannel50Entry
	MAX-ACCESS not-accessible
	STATUS current
	DESCRIPTION
        "
        List of pmopm2Mesrchannel50 Article
        "
	::= { pmopm2MesrClient 114 }


pmopm2Mesrchannel50Entry OBJECT-TYPE
	SYNTAX Pmopm2Mesrchannel50Entry
	MAX-ACCESS not-accessible
	STATUS current
	DESCRIPTION
        "
        Row definition for the pmopm2Mesrchannel50
        table
        "
	INDEX   { pmopm2Mesrchannel50Index }
	::= { pmopm2Mesrchannel50Table 1 }


Pmopm2Mesrchannel50Entry ::=
	SEQUENCE {
	pmopm2Mesrchannel50Index
		INTEGER,
	pmopm2Mesrchannel50Portn
		INTEGER
	}


pmopm2Mesrchannel50Index OBJECT-TYPE
	SYNTAX  INTEGER(0..128)
	MAX-ACCESS  read-only
	STATUS current
	DESCRIPTION
        "
        Index definition for the pmopm2Mesrchannel50
        table
        "
	::= { pmopm2Mesrchannel50Entry 1 }


pmopm2Mesrchannel50Portn OBJECT-TYPE
	SYNTAX  INTEGER (0..65535)
	MAX-ACCESS read-only
	STATUS current
	DESCRIPTION
        "
        Channel50 Power :This OID indicates
        the channel power  (Power =Q8(Number
        format)) (Unit = dBm)<Help> This
        measure indicates the channel power
        "
	::= { pmopm2Mesrchannel50Entry 2 }


--- *********************************************************
---     TABLE for the pmopm2Mesrchannel51 articles
--- *********************************************************

pmopm2Mesrchannel51Table OBJECT-TYPE
	SYNTAX  SEQUENCE OF Pmopm2Mesrchannel51Entry
	MAX-ACCESS not-accessible
	STATUS current
	DESCRIPTION
        "
        List of pmopm2Mesrchannel51 Article
        "
	::= { pmopm2MesrClient 116 }


pmopm2Mesrchannel51Entry OBJECT-TYPE
	SYNTAX Pmopm2Mesrchannel51Entry
	MAX-ACCESS not-accessible
	STATUS current
	DESCRIPTION
        "
        Row definition for the pmopm2Mesrchannel51
        table
        "
	INDEX   { pmopm2Mesrchannel51Index }
	::= { pmopm2Mesrchannel51Table 1 }


Pmopm2Mesrchannel51Entry ::=
	SEQUENCE {
	pmopm2Mesrchannel51Index
		INTEGER,
	pmopm2Mesrchannel51Portn
		INTEGER
	}


pmopm2Mesrchannel51Index OBJECT-TYPE
	SYNTAX  INTEGER(0..128)
	MAX-ACCESS  read-only
	STATUS current
	DESCRIPTION
        "
        Index definition for the pmopm2Mesrchannel51
        table
        "
	::= { pmopm2Mesrchannel51Entry 1 }


pmopm2Mesrchannel51Portn OBJECT-TYPE
	SYNTAX  INTEGER (0..65535)
	MAX-ACCESS read-only
	STATUS current
	DESCRIPTION
        "
        Channel51 Power :This OID indicates
        the channel power  (Power =Q8(Number
        format)) (Unit = dBm)<Help> This
        measure indicates the channel power
        "
	::= { pmopm2Mesrchannel51Entry 2 }


--- *********************************************************
---     TABLE for the pmopm2Mesrchannel52 articles
--- *********************************************************

pmopm2Mesrchannel52Table OBJECT-TYPE
	SYNTAX  SEQUENCE OF Pmopm2Mesrchannel52Entry
	MAX-ACCESS not-accessible
	STATUS current
	DESCRIPTION
        "
        List of pmopm2Mesrchannel52 Article
        "
	::= { pmopm2MesrClient 118 }


pmopm2Mesrchannel52Entry OBJECT-TYPE
	SYNTAX Pmopm2Mesrchannel52Entry
	MAX-ACCESS not-accessible
	STATUS current
	DESCRIPTION
        "
        Row definition for the pmopm2Mesrchannel52
        table
        "
	INDEX   { pmopm2Mesrchannel52Index }
	::= { pmopm2Mesrchannel52Table 1 }


Pmopm2Mesrchannel52Entry ::=
	SEQUENCE {
	pmopm2Mesrchannel52Index
		INTEGER,
	pmopm2Mesrchannel52Portn
		INTEGER
	}


pmopm2Mesrchannel52Index OBJECT-TYPE
	SYNTAX  INTEGER(0..128)
	MAX-ACCESS  read-only
	STATUS current
	DESCRIPTION
        "
        Index definition for the pmopm2Mesrchannel52
        table
        "
	::= { pmopm2Mesrchannel52Entry 1 }


pmopm2Mesrchannel52Portn OBJECT-TYPE
	SYNTAX  INTEGER (0..65535)
	MAX-ACCESS read-only
	STATUS current
	DESCRIPTION
        "
        Channel52 Power :This OID indicates
        the channel power  (Power =Q8(Number
        format)) (Unit = dBm)<Help> This
        measure indicates the channel power
        "
	::= { pmopm2Mesrchannel52Entry 2 }


--- *********************************************************
---     TABLE for the pmopm2Mesrchannel53 articles
--- *********************************************************

pmopm2Mesrchannel53Table OBJECT-TYPE
	SYNTAX  SEQUENCE OF Pmopm2Mesrchannel53Entry
	MAX-ACCESS not-accessible
	STATUS current
	DESCRIPTION
        "
        List of pmopm2Mesrchannel53 Article
        "
	::= { pmopm2MesrClient 120 }


pmopm2Mesrchannel53Entry OBJECT-TYPE
	SYNTAX Pmopm2Mesrchannel53Entry
	MAX-ACCESS not-accessible
	STATUS current
	DESCRIPTION
        "
        Row definition for the pmopm2Mesrchannel53
        table
        "
	INDEX   { pmopm2Mesrchannel53Index }
	::= { pmopm2Mesrchannel53Table 1 }


Pmopm2Mesrchannel53Entry ::=
	SEQUENCE {
	pmopm2Mesrchannel53Index
		INTEGER,
	pmopm2Mesrchannel53Portn
		INTEGER
	}


pmopm2Mesrchannel53Index OBJECT-TYPE
	SYNTAX  INTEGER(0..128)
	MAX-ACCESS  read-only
	STATUS current
	DESCRIPTION
        "
        Index definition for the pmopm2Mesrchannel53
        table
        "
	::= { pmopm2Mesrchannel53Entry 1 }


pmopm2Mesrchannel53Portn OBJECT-TYPE
	SYNTAX  INTEGER (0..65535)
	MAX-ACCESS read-only
	STATUS current
	DESCRIPTION
        "
        Channel53 Power :This OID indicates
        the channel power  (Power =Q8(Number
        format)) (Unit = dBm)<Help> This
        measure indicates the channel power
        "
	::= { pmopm2Mesrchannel53Entry 2 }


--- *********************************************************
---     TABLE for the pmopm2Mesrchannel54 articles
--- *********************************************************

pmopm2Mesrchannel54Table OBJECT-TYPE
	SYNTAX  SEQUENCE OF Pmopm2Mesrchannel54Entry
	MAX-ACCESS not-accessible
	STATUS current
	DESCRIPTION
        "
        List of pmopm2Mesrchannel54 Article
        "
	::= { pmopm2MesrClient 122 }


pmopm2Mesrchannel54Entry OBJECT-TYPE
	SYNTAX Pmopm2Mesrchannel54Entry
	MAX-ACCESS not-accessible
	STATUS current
	DESCRIPTION
        "
        Row definition for the pmopm2Mesrchannel54
        table
        "
	INDEX   { pmopm2Mesrchannel54Index }
	::= { pmopm2Mesrchannel54Table 1 }


Pmopm2Mesrchannel54Entry ::=
	SEQUENCE {
	pmopm2Mesrchannel54Index
		INTEGER,
	pmopm2Mesrchannel54Portn
		INTEGER
	}


pmopm2Mesrchannel54Index OBJECT-TYPE
	SYNTAX  INTEGER(0..128)
	MAX-ACCESS  read-only
	STATUS current
	DESCRIPTION
        "
        Index definition for the pmopm2Mesrchannel54
        table
        "
	::= { pmopm2Mesrchannel54Entry 1 }


pmopm2Mesrchannel54Portn OBJECT-TYPE
	SYNTAX  INTEGER (0..65535)
	MAX-ACCESS read-only
	STATUS current
	DESCRIPTION
        "
        Channel54 Power :This OID indicates
        the channel power  (Power =Q8(Number
        format)) (Unit = dBm)<Help> This
        measure indicates the channel power
        "
	::= { pmopm2Mesrchannel54Entry 2 }


--- *********************************************************
---     TABLE for the pmopm2Mesrchannel55 articles
--- *********************************************************

pmopm2Mesrchannel55Table OBJECT-TYPE
	SYNTAX  SEQUENCE OF Pmopm2Mesrchannel55Entry
	MAX-ACCESS not-accessible
	STATUS current
	DESCRIPTION
        "
        List of pmopm2Mesrchannel55 Article
        "
	::= { pmopm2MesrClient 124 }


pmopm2Mesrchannel55Entry OBJECT-TYPE
	SYNTAX Pmopm2Mesrchannel55Entry
	MAX-ACCESS not-accessible
	STATUS current
	DESCRIPTION
        "
        Row definition for the pmopm2Mesrchannel55
        table
        "
	INDEX   { pmopm2Mesrchannel55Index }
	::= { pmopm2Mesrchannel55Table 1 }


Pmopm2Mesrchannel55Entry ::=
	SEQUENCE {
	pmopm2Mesrchannel55Index
		INTEGER,
	pmopm2Mesrchannel55Portn
		INTEGER
	}


pmopm2Mesrchannel55Index OBJECT-TYPE
	SYNTAX  INTEGER(0..128)
	MAX-ACCESS  read-only
	STATUS current
	DESCRIPTION
        "
        Index definition for the pmopm2Mesrchannel55
        table
        "
	::= { pmopm2Mesrchannel55Entry 1 }


pmopm2Mesrchannel55Portn OBJECT-TYPE
	SYNTAX  INTEGER (0..65535)
	MAX-ACCESS read-only
	STATUS current
	DESCRIPTION
        "
        Channel55 Power :This OID indicates
        the channel power  (Power =Q8(Number
        format)) (Unit = dBm)<Help> This
        measure indicates the channel power
        "
	::= { pmopm2Mesrchannel55Entry 2 }


--- *********************************************************
---     TABLE for the pmopm2Mesrchannel56 articles
--- *********************************************************

pmopm2Mesrchannel56Table OBJECT-TYPE
	SYNTAX  SEQUENCE OF Pmopm2Mesrchannel56Entry
	MAX-ACCESS not-accessible
	STATUS current
	DESCRIPTION
        "
        List of pmopm2Mesrchannel56 Article
        "
	::= { pmopm2MesrClient 126 }


pmopm2Mesrchannel56Entry OBJECT-TYPE
	SYNTAX Pmopm2Mesrchannel56Entry
	MAX-ACCESS not-accessible
	STATUS current
	DESCRIPTION
        "
        Row definition for the pmopm2Mesrchannel56
        table
        "
	INDEX   { pmopm2Mesrchannel56Index }
	::= { pmopm2Mesrchannel56Table 1 }


Pmopm2Mesrchannel56Entry ::=
	SEQUENCE {
	pmopm2Mesrchannel56Index
		INTEGER,
	pmopm2Mesrchannel56Portn
		INTEGER
	}


pmopm2Mesrchannel56Index OBJECT-TYPE
	SYNTAX  INTEGER(0..128)
	MAX-ACCESS  read-only
	STATUS current
	DESCRIPTION
        "
        Index definition for the pmopm2Mesrchannel56
        table
        "
	::= { pmopm2Mesrchannel56Entry 1 }


pmopm2Mesrchannel56Portn OBJECT-TYPE
	SYNTAX  INTEGER (0..65535)
	MAX-ACCESS read-only
	STATUS current
	DESCRIPTION
        "
        Channel56 Power :This OID indicates
        the channel power  (Power =Q8(Number
        format)) (Unit = dBm)<Help> This
        measure indicates the channel power
        "
	::= { pmopm2Mesrchannel56Entry 2 }


--- *********************************************************
---     TABLE for the pmopm2Mesrchannel57 articles
--- *********************************************************

pmopm2Mesrchannel57Table OBJECT-TYPE
	SYNTAX  SEQUENCE OF Pmopm2Mesrchannel57Entry
	MAX-ACCESS not-accessible
	STATUS current
	DESCRIPTION
        "
        List of pmopm2Mesrchannel57 Article
        "
	::= { pmopm2MesrClient 128 }


pmopm2Mesrchannel57Entry OBJECT-TYPE
	SYNTAX Pmopm2Mesrchannel57Entry
	MAX-ACCESS not-accessible
	STATUS current
	DESCRIPTION
        "
        Row definition for the pmopm2Mesrchannel57
        table
        "
	INDEX   { pmopm2Mesrchannel57Index }
	::= { pmopm2Mesrchannel57Table 1 }


Pmopm2Mesrchannel57Entry ::=
	SEQUENCE {
	pmopm2Mesrchannel57Index
		INTEGER,
	pmopm2Mesrchannel57Portn
		INTEGER
	}


pmopm2Mesrchannel57Index OBJECT-TYPE
	SYNTAX  INTEGER(0..128)
	MAX-ACCESS  read-only
	STATUS current
	DESCRIPTION
        "
        Index definition for the pmopm2Mesrchannel57
        table
        "
	::= { pmopm2Mesrchannel57Entry 1 }


pmopm2Mesrchannel57Portn OBJECT-TYPE
	SYNTAX  INTEGER (0..65535)
	MAX-ACCESS read-only
	STATUS current
	DESCRIPTION
        "
        Channel57 Power :This OID indicates
        the channel power  (Power =Q8(Number
        format)) (Unit = dBm)<Help> This
        measure indicates the channel power
        "
	::= { pmopm2Mesrchannel57Entry 2 }


--- *********************************************************
---     TABLE for the pmopm2Mesrchannel58 articles
--- *********************************************************

pmopm2Mesrchannel58Table OBJECT-TYPE
	SYNTAX  SEQUENCE OF Pmopm2Mesrchannel58Entry
	MAX-ACCESS not-accessible
	STATUS current
	DESCRIPTION
        "
        List of pmopm2Mesrchannel58 Article
        "
	::= { pmopm2MesrClient 130 }


pmopm2Mesrchannel58Entry OBJECT-TYPE
	SYNTAX Pmopm2Mesrchannel58Entry
	MAX-ACCESS not-accessible
	STATUS current
	DESCRIPTION
        "
        Row definition for the pmopm2Mesrchannel58
        table
        "
	INDEX   { pmopm2Mesrchannel58Index }
	::= { pmopm2Mesrchannel58Table 1 }


Pmopm2Mesrchannel58Entry ::=
	SEQUENCE {
	pmopm2Mesrchannel58Index
		INTEGER,
	pmopm2Mesrchannel58Portn
		INTEGER
	}


pmopm2Mesrchannel58Index OBJECT-TYPE
	SYNTAX  INTEGER(0..128)
	MAX-ACCESS  read-only
	STATUS current
	DESCRIPTION
        "
        Index definition for the pmopm2Mesrchannel58
        table
        "
	::= { pmopm2Mesrchannel58Entry 1 }


pmopm2Mesrchannel58Portn OBJECT-TYPE
	SYNTAX  INTEGER (0..65535)
	MAX-ACCESS read-only
	STATUS current
	DESCRIPTION
        "
        Channel58 Power :This OID indicates
        the channel power  (Power =Q8(Number
        format)) (Unit = dBm)<Help> This
        measure indicates the channel power
        "
	::= { pmopm2Mesrchannel58Entry 2 }


--- *********************************************************
---     TABLE for the pmopm2Mesrchannel59 articles
--- *********************************************************

pmopm2Mesrchannel59Table OBJECT-TYPE
	SYNTAX  SEQUENCE OF Pmopm2Mesrchannel59Entry
	MAX-ACCESS not-accessible
	STATUS current
	DESCRIPTION
        "
        List of pmopm2Mesrchannel59 Article
        "
	::= { pmopm2MesrClient 132 }


pmopm2Mesrchannel59Entry OBJECT-TYPE
	SYNTAX Pmopm2Mesrchannel59Entry
	MAX-ACCESS not-accessible
	STATUS current
	DESCRIPTION
        "
        Row definition for the pmopm2Mesrchannel59
        table
        "
	INDEX   { pmopm2Mesrchannel59Index }
	::= { pmopm2Mesrchannel59Table 1 }


Pmopm2Mesrchannel59Entry ::=
	SEQUENCE {
	pmopm2Mesrchannel59Index
		INTEGER,
	pmopm2Mesrchannel59Portn
		INTEGER
	}


pmopm2Mesrchannel59Index OBJECT-TYPE
	SYNTAX  INTEGER(0..128)
	MAX-ACCESS  read-only
	STATUS current
	DESCRIPTION
        "
        Index definition for the pmopm2Mesrchannel59
        table
        "
	::= { pmopm2Mesrchannel59Entry 1 }


pmopm2Mesrchannel59Portn OBJECT-TYPE
	SYNTAX  INTEGER (0..65535)
	MAX-ACCESS read-only
	STATUS current
	DESCRIPTION
        "
        Channel59 Power :This OID indicates
        the channel power  (Power =Q8(Number
        format)) (Unit = dBm)<Help> This
        measure indicates the channel power
        "
	::= { pmopm2Mesrchannel59Entry 2 }


--- *********************************************************
---     TABLE for the pmopm2Mesrchannel60 articles
--- *********************************************************

pmopm2Mesrchannel60Table OBJECT-TYPE
	SYNTAX  SEQUENCE OF Pmopm2Mesrchannel60Entry
	MAX-ACCESS not-accessible
	STATUS current
	DESCRIPTION
        "
        List of pmopm2Mesrchannel60 Article
        "
	::= { pmopm2MesrClient 134 }


pmopm2Mesrchannel60Entry OBJECT-TYPE
	SYNTAX Pmopm2Mesrchannel60Entry
	MAX-ACCESS not-accessible
	STATUS current
	DESCRIPTION
        "
        Row definition for the pmopm2Mesrchannel60
        table
        "
	INDEX   { pmopm2Mesrchannel60Index }
	::= { pmopm2Mesrchannel60Table 1 }


Pmopm2Mesrchannel60Entry ::=
	SEQUENCE {
	pmopm2Mesrchannel60Index
		INTEGER,
	pmopm2Mesrchannel60Portn
		INTEGER
	}


pmopm2Mesrchannel60Index OBJECT-TYPE
	SYNTAX  INTEGER(0..128)
	MAX-ACCESS  read-only
	STATUS current
	DESCRIPTION
        "
        Index definition for the pmopm2Mesrchannel60
        table
        "
	::= { pmopm2Mesrchannel60Entry 1 }


pmopm2Mesrchannel60Portn OBJECT-TYPE
	SYNTAX  INTEGER (0..65535)
	MAX-ACCESS read-only
	STATUS current
	DESCRIPTION
        "
        Channel60 Power :This OID indicates
        the channel power  (Power =Q8(Number
        format)) (Unit = dBm)<Help> This
        measure indicates the channel power
        "
	::= { pmopm2Mesrchannel60Entry 2 }


--- *********************************************************
---     TABLE for the pmopm2Mesrchannel61 articles
--- *********************************************************

pmopm2Mesrchannel61Table OBJECT-TYPE
	SYNTAX  SEQUENCE OF Pmopm2Mesrchannel61Entry
	MAX-ACCESS not-accessible
	STATUS current
	DESCRIPTION
        "
        List of pmopm2Mesrchannel61 Article
        "
	::= { pmopm2MesrClient 136 }


pmopm2Mesrchannel61Entry OBJECT-TYPE
	SYNTAX Pmopm2Mesrchannel61Entry
	MAX-ACCESS not-accessible
	STATUS current
	DESCRIPTION
        "
        Row definition for the pmopm2Mesrchannel61
        table
        "
	INDEX   { pmopm2Mesrchannel61Index }
	::= { pmopm2Mesrchannel61Table 1 }


Pmopm2Mesrchannel61Entry ::=
	SEQUENCE {
	pmopm2Mesrchannel61Index
		INTEGER,
	pmopm2Mesrchannel61Portn
		INTEGER
	}


pmopm2Mesrchannel61Index OBJECT-TYPE
	SYNTAX  INTEGER(0..128)
	MAX-ACCESS  read-only
	STATUS current
	DESCRIPTION
        "
        Index definition for the pmopm2Mesrchannel61
        table
        "
	::= { pmopm2Mesrchannel61Entry 1 }


pmopm2Mesrchannel61Portn OBJECT-TYPE
	SYNTAX  INTEGER (0..65535)
	MAX-ACCESS read-only
	STATUS current
	DESCRIPTION
        "
        Channel61 Power :This OID indicates
        the channel power  (Power =Q8(Number
        format)) (Unit = dBm)<Help> This
        measure indicates the channel power
        "
	::= { pmopm2Mesrchannel61Entry 2 }


--- *********************************************************
---     TABLE for the pmopm2Mesrchannel62 articles
--- *********************************************************

pmopm2Mesrchannel62Table OBJECT-TYPE
	SYNTAX  SEQUENCE OF Pmopm2Mesrchannel62Entry
	MAX-ACCESS not-accessible
	STATUS current
	DESCRIPTION
        "
        List of pmopm2Mesrchannel62 Article
        "
	::= { pmopm2MesrClient 138 }


pmopm2Mesrchannel62Entry OBJECT-TYPE
	SYNTAX Pmopm2Mesrchannel62Entry
	MAX-ACCESS not-accessible
	STATUS current
	DESCRIPTION
        "
        Row definition for the pmopm2Mesrchannel62
        table
        "
	INDEX   { pmopm2Mesrchannel62Index }
	::= { pmopm2Mesrchannel62Table 1 }


Pmopm2Mesrchannel62Entry ::=
	SEQUENCE {
	pmopm2Mesrchannel62Index
		INTEGER,
	pmopm2Mesrchannel62Portn
		INTEGER
	}


pmopm2Mesrchannel62Index OBJECT-TYPE
	SYNTAX  INTEGER(0..128)
	MAX-ACCESS  read-only
	STATUS current
	DESCRIPTION
        "
        Index definition for the pmopm2Mesrchannel62
        table
        "
	::= { pmopm2Mesrchannel62Entry 1 }


pmopm2Mesrchannel62Portn OBJECT-TYPE
	SYNTAX  INTEGER (0..65535)
	MAX-ACCESS read-only
	STATUS current
	DESCRIPTION
        "
        Channel62 Power :This OID indicates
        the channel power  (Power =Q8(Number
        format)) (Unit = dBm)<Help> This
        measure indicates the channel power
        "
	::= { pmopm2Mesrchannel62Entry 2 }


--- *********************************************************
---     TABLE for the pmopm2Mesrchannel63 articles
--- *********************************************************

pmopm2Mesrchannel63Table OBJECT-TYPE
	SYNTAX  SEQUENCE OF Pmopm2Mesrchannel63Entry
	MAX-ACCESS not-accessible
	STATUS current
	DESCRIPTION
        "
        List of pmopm2Mesrchannel63 Article
        "
	::= { pmopm2MesrClient 140 }


pmopm2Mesrchannel63Entry OBJECT-TYPE
	SYNTAX Pmopm2Mesrchannel63Entry
	MAX-ACCESS not-accessible
	STATUS current
	DESCRIPTION
        "
        Row definition for the pmopm2Mesrchannel63
        table
        "
	INDEX   { pmopm2Mesrchannel63Index }
	::= { pmopm2Mesrchannel63Table 1 }


Pmopm2Mesrchannel63Entry ::=
	SEQUENCE {
	pmopm2Mesrchannel63Index
		INTEGER,
	pmopm2Mesrchannel63Portn
		INTEGER
	}


pmopm2Mesrchannel63Index OBJECT-TYPE
	SYNTAX  INTEGER(0..128)
	MAX-ACCESS  read-only
	STATUS current
	DESCRIPTION
        "
        Index definition for the pmopm2Mesrchannel63
        table
        "
	::= { pmopm2Mesrchannel63Entry 1 }


pmopm2Mesrchannel63Portn OBJECT-TYPE
	SYNTAX  INTEGER (0..65535)
	MAX-ACCESS read-only
	STATUS current
	DESCRIPTION
        "
        Channel63 Power :This OID indicates
        the channel power  (Power =Q8(Number
        format)) (Unit = dBm)<Help> This
        measure indicates the channel power
        "
	::= { pmopm2Mesrchannel63Entry 2 }


--- *********************************************************
---     TABLE for the pmopm2Mesrchannel64 articles
--- *********************************************************

pmopm2Mesrchannel64Table OBJECT-TYPE
	SYNTAX  SEQUENCE OF Pmopm2Mesrchannel64Entry
	MAX-ACCESS not-accessible
	STATUS current
	DESCRIPTION
        "
        List of pmopm2Mesrchannel64 Article
        "
	::= { pmopm2MesrClient 142 }


pmopm2Mesrchannel64Entry OBJECT-TYPE
	SYNTAX Pmopm2Mesrchannel64Entry
	MAX-ACCESS not-accessible
	STATUS current
	DESCRIPTION
        "
        Row definition for the pmopm2Mesrchannel64
        table
        "
	INDEX   { pmopm2Mesrchannel64Index }
	::= { pmopm2Mesrchannel64Table 1 }


Pmopm2Mesrchannel64Entry ::=
	SEQUENCE {
	pmopm2Mesrchannel64Index
		INTEGER,
	pmopm2Mesrchannel64Portn
		INTEGER
	}


pmopm2Mesrchannel64Index OBJECT-TYPE
	SYNTAX  INTEGER(0..128)
	MAX-ACCESS  read-only
	STATUS current
	DESCRIPTION
        "
        Index definition for the pmopm2Mesrchannel64
        table
        "
	::= { pmopm2Mesrchannel64Entry 1 }


pmopm2Mesrchannel64Portn OBJECT-TYPE
	SYNTAX  INTEGER (0..65535)
	MAX-ACCESS read-only
	STATUS current
	DESCRIPTION
        "
        Channel64 Power :This OID indicates
        the channel power  (Power =Q8(Number
        format)) (Unit = dBm)<Help> This
        measure indicates the channel power
        "
	::= { pmopm2Mesrchannel64Entry 2 }


--- *********************************************************
---     TABLE for the pmopm2Mesrchannel65 articles
--- *********************************************************

pmopm2Mesrchannel65Table OBJECT-TYPE
	SYNTAX  SEQUENCE OF Pmopm2Mesrchannel65Entry
	MAX-ACCESS not-accessible
	STATUS current
	DESCRIPTION
        "
        List of pmopm2Mesrchannel65 Article
        "
	::= { pmopm2MesrClient 144 }


pmopm2Mesrchannel65Entry OBJECT-TYPE
	SYNTAX Pmopm2Mesrchannel65Entry
	MAX-ACCESS not-accessible
	STATUS current
	DESCRIPTION
        "
        Row definition for the pmopm2Mesrchannel65
        table
        "
	INDEX   { pmopm2Mesrchannel65Index }
	::= { pmopm2Mesrchannel65Table 1 }


Pmopm2Mesrchannel65Entry ::=
	SEQUENCE {
	pmopm2Mesrchannel65Index
		INTEGER,
	pmopm2Mesrchannel65Portn
		INTEGER
	}


pmopm2Mesrchannel65Index OBJECT-TYPE
	SYNTAX  INTEGER(0..128)
	MAX-ACCESS  read-only
	STATUS current
	DESCRIPTION
        "
        Index definition for the pmopm2Mesrchannel65
        table
        "
	::= { pmopm2Mesrchannel65Entry 1 }


pmopm2Mesrchannel65Portn OBJECT-TYPE
	SYNTAX  INTEGER (0..65535)
	MAX-ACCESS read-only
	STATUS current
	DESCRIPTION
        "
        Channel65 Power :This OID indicates
        the channel power  (Power =Q8(Number
        format)) (Unit = dBm)<Help> This
        measure indicates the channel power
        "
	::= { pmopm2Mesrchannel65Entry 2 }


--- *********************************************************
---     TABLE for the pmopm2Mesrchannel66 articles
--- *********************************************************

pmopm2Mesrchannel66Table OBJECT-TYPE
	SYNTAX  SEQUENCE OF Pmopm2Mesrchannel66Entry
	MAX-ACCESS not-accessible
	STATUS current
	DESCRIPTION
        "
        List of pmopm2Mesrchannel66 Article
        "
	::= { pmopm2MesrClient 146 }


pmopm2Mesrchannel66Entry OBJECT-TYPE
	SYNTAX Pmopm2Mesrchannel66Entry
	MAX-ACCESS not-accessible
	STATUS current
	DESCRIPTION
        "
        Row definition for the pmopm2Mesrchannel66
        table
        "
	INDEX   { pmopm2Mesrchannel66Index }
	::= { pmopm2Mesrchannel66Table 1 }


Pmopm2Mesrchannel66Entry ::=
	SEQUENCE {
	pmopm2Mesrchannel66Index
		INTEGER,
	pmopm2Mesrchannel66Portn
		INTEGER
	}


pmopm2Mesrchannel66Index OBJECT-TYPE
	SYNTAX  INTEGER(0..128)
	MAX-ACCESS  read-only
	STATUS current
	DESCRIPTION
        "
        Index definition for the pmopm2Mesrchannel66
        table
        "
	::= { pmopm2Mesrchannel66Entry 1 }


pmopm2Mesrchannel66Portn OBJECT-TYPE
	SYNTAX  INTEGER (0..65535)
	MAX-ACCESS read-only
	STATUS current
	DESCRIPTION
        "
        Channel66 Power :This OID indicates
        the channel power  (Power =Q8(Number
        format)) (Unit = dBm)<Help> This
        measure indicates the channel power
        "
	::= { pmopm2Mesrchannel66Entry 2 }


--- *********************************************************
---     TABLE for the pmopm2Mesrchannel67 articles
--- *********************************************************

pmopm2Mesrchannel67Table OBJECT-TYPE
	SYNTAX  SEQUENCE OF Pmopm2Mesrchannel67Entry
	MAX-ACCESS not-accessible
	STATUS current
	DESCRIPTION
        "
        List of pmopm2Mesrchannel67 Article
        "
	::= { pmopm2MesrClient 148 }


pmopm2Mesrchannel67Entry OBJECT-TYPE
	SYNTAX Pmopm2Mesrchannel67Entry
	MAX-ACCESS not-accessible
	STATUS current
	DESCRIPTION
        "
        Row definition for the pmopm2Mesrchannel67
        table
        "
	INDEX   { pmopm2Mesrchannel67Index }
	::= { pmopm2Mesrchannel67Table 1 }


Pmopm2Mesrchannel67Entry ::=
	SEQUENCE {
	pmopm2Mesrchannel67Index
		INTEGER,
	pmopm2Mesrchannel67Portn
		INTEGER
	}


pmopm2Mesrchannel67Index OBJECT-TYPE
	SYNTAX  INTEGER(0..128)
	MAX-ACCESS  read-only
	STATUS current
	DESCRIPTION
        "
        Index definition for the pmopm2Mesrchannel67
        table
        "
	::= { pmopm2Mesrchannel67Entry 1 }


pmopm2Mesrchannel67Portn OBJECT-TYPE
	SYNTAX  INTEGER (0..65535)
	MAX-ACCESS read-only
	STATUS current
	DESCRIPTION
        "
        Channel67 Power :This OID indicates
        the channel power  (Power =Q8(Number
        format)) (Unit = dBm)<Help> This
        measure indicates the channel power
        "
	::= { pmopm2Mesrchannel67Entry 2 }


--- *********************************************************
---     TABLE for the pmopm2Mesrchannel68 articles
--- *********************************************************

pmopm2Mesrchannel68Table OBJECT-TYPE
	SYNTAX  SEQUENCE OF Pmopm2Mesrchannel68Entry
	MAX-ACCESS not-accessible
	STATUS current
	DESCRIPTION
        "
        List of pmopm2Mesrchannel68 Article
        "
	::= { pmopm2MesrClient 150 }


pmopm2Mesrchannel68Entry OBJECT-TYPE
	SYNTAX Pmopm2Mesrchannel68Entry
	MAX-ACCESS not-accessible
	STATUS current
	DESCRIPTION
        "
        Row definition for the pmopm2Mesrchannel68
        table
        "
	INDEX   { pmopm2Mesrchannel68Index }
	::= { pmopm2Mesrchannel68Table 1 }


Pmopm2Mesrchannel68Entry ::=
	SEQUENCE {
	pmopm2Mesrchannel68Index
		INTEGER,
	pmopm2Mesrchannel68Portn
		INTEGER
	}


pmopm2Mesrchannel68Index OBJECT-TYPE
	SYNTAX  INTEGER(0..128)
	MAX-ACCESS  read-only
	STATUS current
	DESCRIPTION
        "
        Index definition for the pmopm2Mesrchannel68
        table
        "
	::= { pmopm2Mesrchannel68Entry 1 }


pmopm2Mesrchannel68Portn OBJECT-TYPE
	SYNTAX  INTEGER (0..65535)
	MAX-ACCESS read-only
	STATUS current
	DESCRIPTION
        "
        Channel68 Power :This OID indicates
        the channel power  (Power =Q8(Number
        format)) (Unit = dBm)<Help> This
        measure indicates the channel power
        "
	::= { pmopm2Mesrchannel68Entry 2 }


--- *********************************************************
---     TABLE for the pmopm2Mesrchannel69 articles
--- *********************************************************

pmopm2Mesrchannel69Table OBJECT-TYPE
	SYNTAX  SEQUENCE OF Pmopm2Mesrchannel69Entry
	MAX-ACCESS not-accessible
	STATUS current
	DESCRIPTION
        "
        List of pmopm2Mesrchannel69 Article
        "
	::= { pmopm2MesrClient 152 }


pmopm2Mesrchannel69Entry OBJECT-TYPE
	SYNTAX Pmopm2Mesrchannel69Entry
	MAX-ACCESS not-accessible
	STATUS current
	DESCRIPTION
        "
        Row definition for the pmopm2Mesrchannel69
        table
        "
	INDEX   { pmopm2Mesrchannel69Index }
	::= { pmopm2Mesrchannel69Table 1 }


Pmopm2Mesrchannel69Entry ::=
	SEQUENCE {
	pmopm2Mesrchannel69Index
		INTEGER,
	pmopm2Mesrchannel69Portn
		INTEGER
	}


pmopm2Mesrchannel69Index OBJECT-TYPE
	SYNTAX  INTEGER(0..128)
	MAX-ACCESS  read-only
	STATUS current
	DESCRIPTION
        "
        Index definition for the pmopm2Mesrchannel69
        table
        "
	::= { pmopm2Mesrchannel69Entry 1 }


pmopm2Mesrchannel69Portn OBJECT-TYPE
	SYNTAX  INTEGER (0..65535)
	MAX-ACCESS read-only
	STATUS current
	DESCRIPTION
        "
        Channel69 Power :This OID indicates
        the channel power  (Power =Q8(Number
        format)) (Unit = dBm)<Help> This
        measure indicates the channel power
        "
	::= { pmopm2Mesrchannel69Entry 2 }


--- *********************************************************
---     TABLE for the pmopm2Mesrchannel70 articles
--- *********************************************************

pmopm2Mesrchannel70Table OBJECT-TYPE
	SYNTAX  SEQUENCE OF Pmopm2Mesrchannel70Entry
	MAX-ACCESS not-accessible
	STATUS current
	DESCRIPTION
        "
        List of pmopm2Mesrchannel70 Article
        "
	::= { pmopm2MesrClient 154 }


pmopm2Mesrchannel70Entry OBJECT-TYPE
	SYNTAX Pmopm2Mesrchannel70Entry
	MAX-ACCESS not-accessible
	STATUS current
	DESCRIPTION
        "
        Row definition for the pmopm2Mesrchannel70
        table
        "
	INDEX   { pmopm2Mesrchannel70Index }
	::= { pmopm2Mesrchannel70Table 1 }


Pmopm2Mesrchannel70Entry ::=
	SEQUENCE {
	pmopm2Mesrchannel70Index
		INTEGER,
	pmopm2Mesrchannel70Portn
		INTEGER
	}


pmopm2Mesrchannel70Index OBJECT-TYPE
	SYNTAX  INTEGER(0..128)
	MAX-ACCESS  read-only
	STATUS current
	DESCRIPTION
        "
        Index definition for the pmopm2Mesrchannel70
        table
        "
	::= { pmopm2Mesrchannel70Entry 1 }


pmopm2Mesrchannel70Portn OBJECT-TYPE
	SYNTAX  INTEGER (0..65535)
	MAX-ACCESS read-only
	STATUS current
	DESCRIPTION
        "
        Channel70 Power :This OID indicates
        the channel power  (Power =Q8(Number
        format)) (Unit = dBm)<Help> This
        measure indicates the channel power
        "
	::= { pmopm2Mesrchannel70Entry 2 }


--- *********************************************************
---     TABLE for the pmopm2Mesrchannel71 articles
--- *********************************************************

pmopm2Mesrchannel71Table OBJECT-TYPE
	SYNTAX  SEQUENCE OF Pmopm2Mesrchannel71Entry
	MAX-ACCESS not-accessible
	STATUS current
	DESCRIPTION
        "
        List of pmopm2Mesrchannel71 Article
        "
	::= { pmopm2MesrClient 156 }


pmopm2Mesrchannel71Entry OBJECT-TYPE
	SYNTAX Pmopm2Mesrchannel71Entry
	MAX-ACCESS not-accessible
	STATUS current
	DESCRIPTION
        "
        Row definition for the pmopm2Mesrchannel71
        table
        "
	INDEX   { pmopm2Mesrchannel71Index }
	::= { pmopm2Mesrchannel71Table 1 }


Pmopm2Mesrchannel71Entry ::=
	SEQUENCE {
	pmopm2Mesrchannel71Index
		INTEGER,
	pmopm2Mesrchannel71Portn
		INTEGER
	}


pmopm2Mesrchannel71Index OBJECT-TYPE
	SYNTAX  INTEGER(0..128)
	MAX-ACCESS  read-only
	STATUS current
	DESCRIPTION
        "
        Index definition for the pmopm2Mesrchannel71
        table
        "
	::= { pmopm2Mesrchannel71Entry 1 }


pmopm2Mesrchannel71Portn OBJECT-TYPE
	SYNTAX  INTEGER (0..65535)
	MAX-ACCESS read-only
	STATUS current
	DESCRIPTION
        "
        Channel71 Power :This OID indicates
        the channel power  (Power =Q8(Number
        format)) (Unit = dBm)<Help> This
        measure indicates the channel power
        "
	::= { pmopm2Mesrchannel71Entry 2 }


--- *********************************************************
---     TABLE for the pmopm2Mesrchannel72 articles
--- *********************************************************

pmopm2Mesrchannel72Table OBJECT-TYPE
	SYNTAX  SEQUENCE OF Pmopm2Mesrchannel72Entry
	MAX-ACCESS not-accessible
	STATUS current
	DESCRIPTION
        "
        List of pmopm2Mesrchannel72 Article
        "
	::= { pmopm2MesrClient 158 }


pmopm2Mesrchannel72Entry OBJECT-TYPE
	SYNTAX Pmopm2Mesrchannel72Entry
	MAX-ACCESS not-accessible
	STATUS current
	DESCRIPTION
        "
        Row definition for the pmopm2Mesrchannel72
        table
        "
	INDEX   { pmopm2Mesrchannel72Index }
	::= { pmopm2Mesrchannel72Table 1 }


Pmopm2Mesrchannel72Entry ::=
	SEQUENCE {
	pmopm2Mesrchannel72Index
		INTEGER,
	pmopm2Mesrchannel72Portn
		INTEGER
	}


pmopm2Mesrchannel72Index OBJECT-TYPE
	SYNTAX  INTEGER(0..128)
	MAX-ACCESS  read-only
	STATUS current
	DESCRIPTION
        "
        Index definition for the pmopm2Mesrchannel72
        table
        "
	::= { pmopm2Mesrchannel72Entry 1 }


pmopm2Mesrchannel72Portn OBJECT-TYPE
	SYNTAX  INTEGER (0..65535)
	MAX-ACCESS read-only
	STATUS current
	DESCRIPTION
        "
        Channel72 Power :This OID indicates
        the channel power  (Power =Q8(Number
        format)) (Unit = dBm)<Help> This
        measure indicates the channel power
        "
	::= { pmopm2Mesrchannel72Entry 2 }


--- *********************************************************
---     TABLE for the pmopm2Mesrchannel73 articles
--- *********************************************************

pmopm2Mesrchannel73Table OBJECT-TYPE
	SYNTAX  SEQUENCE OF Pmopm2Mesrchannel73Entry
	MAX-ACCESS not-accessible
	STATUS current
	DESCRIPTION
        "
        List of pmopm2Mesrchannel73 Article
        "
	::= { pmopm2MesrClient 160 }


pmopm2Mesrchannel73Entry OBJECT-TYPE
	SYNTAX Pmopm2Mesrchannel73Entry
	MAX-ACCESS not-accessible
	STATUS current
	DESCRIPTION
        "
        Row definition for the pmopm2Mesrchannel73
        table
        "
	INDEX   { pmopm2Mesrchannel73Index }
	::= { pmopm2Mesrchannel73Table 1 }


Pmopm2Mesrchannel73Entry ::=
	SEQUENCE {
	pmopm2Mesrchannel73Index
		INTEGER,
	pmopm2Mesrchannel73Portn
		INTEGER
	}


pmopm2Mesrchannel73Index OBJECT-TYPE
	SYNTAX  INTEGER(0..128)
	MAX-ACCESS  read-only
	STATUS current
	DESCRIPTION
        "
        Index definition for the pmopm2Mesrchannel73
        table
        "
	::= { pmopm2Mesrchannel73Entry 1 }


pmopm2Mesrchannel73Portn OBJECT-TYPE
	SYNTAX  INTEGER (0..65535)
	MAX-ACCESS read-only
	STATUS current
	DESCRIPTION
        "
        Channel73 Power :This OID indicates
        the channel power  (Power =Q8(Number
        format)) (Unit = dBm)<Help> This
        measure indicates the channel power
        "
	::= { pmopm2Mesrchannel73Entry 2 }


--- *********************************************************
---     TABLE for the pmopm2Mesrchannel74 articles
--- *********************************************************

pmopm2Mesrchannel74Table OBJECT-TYPE
	SYNTAX  SEQUENCE OF Pmopm2Mesrchannel74Entry
	MAX-ACCESS not-accessible
	STATUS current
	DESCRIPTION
        "
        List of pmopm2Mesrchannel74 Article
        "
	::= { pmopm2MesrClient 162 }


pmopm2Mesrchannel74Entry OBJECT-TYPE
	SYNTAX Pmopm2Mesrchannel74Entry
	MAX-ACCESS not-accessible
	STATUS current
	DESCRIPTION
        "
        Row definition for the pmopm2Mesrchannel74
        table
        "
	INDEX   { pmopm2Mesrchannel74Index }
	::= { pmopm2Mesrchannel74Table 1 }


Pmopm2Mesrchannel74Entry ::=
	SEQUENCE {
	pmopm2Mesrchannel74Index
		INTEGER,
	pmopm2Mesrchannel74Portn
		INTEGER
	}


pmopm2Mesrchannel74Index OBJECT-TYPE
	SYNTAX  INTEGER(0..128)
	MAX-ACCESS  read-only
	STATUS current
	DESCRIPTION
        "
        Index definition for the pmopm2Mesrchannel74
        table
        "
	::= { pmopm2Mesrchannel74Entry 1 }


pmopm2Mesrchannel74Portn OBJECT-TYPE
	SYNTAX  INTEGER (0..65535)
	MAX-ACCESS read-only
	STATUS current
	DESCRIPTION
        "
        Channel74 Power :This OID indicates
        the channel power  (Power =Q8(Number
        format)) (Unit = dBm)<Help> This
        measure indicates the channel power
        "
	::= { pmopm2Mesrchannel74Entry 2 }


--- *********************************************************
---     TABLE for the pmopm2Mesrchannel75 articles
--- *********************************************************

pmopm2Mesrchannel75Table OBJECT-TYPE
	SYNTAX  SEQUENCE OF Pmopm2Mesrchannel75Entry
	MAX-ACCESS not-accessible
	STATUS current
	DESCRIPTION
        "
        List of pmopm2Mesrchannel75 Article
        "
	::= { pmopm2MesrClient 164 }


pmopm2Mesrchannel75Entry OBJECT-TYPE
	SYNTAX Pmopm2Mesrchannel75Entry
	MAX-ACCESS not-accessible
	STATUS current
	DESCRIPTION
        "
        Row definition for the pmopm2Mesrchannel75
        table
        "
	INDEX   { pmopm2Mesrchannel75Index }
	::= { pmopm2Mesrchannel75Table 1 }


Pmopm2Mesrchannel75Entry ::=
	SEQUENCE {
	pmopm2Mesrchannel75Index
		INTEGER,
	pmopm2Mesrchannel75Portn
		INTEGER
	}


pmopm2Mesrchannel75Index OBJECT-TYPE
	SYNTAX  INTEGER(0..128)
	MAX-ACCESS  read-only
	STATUS current
	DESCRIPTION
        "
        Index definition for the pmopm2Mesrchannel75
        table
        "
	::= { pmopm2Mesrchannel75Entry 1 }


pmopm2Mesrchannel75Portn OBJECT-TYPE
	SYNTAX  INTEGER (0..65535)
	MAX-ACCESS read-only
	STATUS current
	DESCRIPTION
        "
        Channel75 Power :This OID indicates
        the channel power  (Power =Q8(Number
        format)) (Unit = dBm)<Help> This
        measure indicates the channel power
        "
	::= { pmopm2Mesrchannel75Entry 2 }


--- *********************************************************
---     TABLE for the pmopm2Mesrchannel76 articles
--- *********************************************************

pmopm2Mesrchannel76Table OBJECT-TYPE
	SYNTAX  SEQUENCE OF Pmopm2Mesrchannel76Entry
	MAX-ACCESS not-accessible
	STATUS current
	DESCRIPTION
        "
        List of pmopm2Mesrchannel76 Article
        "
	::= { pmopm2MesrClient 166 }


pmopm2Mesrchannel76Entry OBJECT-TYPE
	SYNTAX Pmopm2Mesrchannel76Entry
	MAX-ACCESS not-accessible
	STATUS current
	DESCRIPTION
        "
        Row definition for the pmopm2Mesrchannel76
        table
        "
	INDEX   { pmopm2Mesrchannel76Index }
	::= { pmopm2Mesrchannel76Table 1 }


Pmopm2Mesrchannel76Entry ::=
	SEQUENCE {
	pmopm2Mesrchannel76Index
		INTEGER,
	pmopm2Mesrchannel76Portn
		INTEGER
	}


pmopm2Mesrchannel76Index OBJECT-TYPE
	SYNTAX  INTEGER(0..128)
	MAX-ACCESS  read-only
	STATUS current
	DESCRIPTION
        "
        Index definition for the pmopm2Mesrchannel76
        table
        "
	::= { pmopm2Mesrchannel76Entry 1 }


pmopm2Mesrchannel76Portn OBJECT-TYPE
	SYNTAX  INTEGER (0..65535)
	MAX-ACCESS read-only
	STATUS current
	DESCRIPTION
        "
        Channel76 Power :This OID indicates
        the channel power  (Power =Q8(Number
        format)) (Unit = dBm)<Help> This
        measure indicates the channel power
        "
	::= { pmopm2Mesrchannel76Entry 2 }


--- *********************************************************
---     TABLE for the pmopm2Mesrchannel77 articles
--- *********************************************************

pmopm2Mesrchannel77Table OBJECT-TYPE
	SYNTAX  SEQUENCE OF Pmopm2Mesrchannel77Entry
	MAX-ACCESS not-accessible
	STATUS current
	DESCRIPTION
        "
        List of pmopm2Mesrchannel77 Article
        "
	::= { pmopm2MesrClient 168 }


pmopm2Mesrchannel77Entry OBJECT-TYPE
	SYNTAX Pmopm2Mesrchannel77Entry
	MAX-ACCESS not-accessible
	STATUS current
	DESCRIPTION
        "
        Row definition for the pmopm2Mesrchannel77
        table
        "
	INDEX   { pmopm2Mesrchannel77Index }
	::= { pmopm2Mesrchannel77Table 1 }


Pmopm2Mesrchannel77Entry ::=
	SEQUENCE {
	pmopm2Mesrchannel77Index
		INTEGER,
	pmopm2Mesrchannel77Portn
		INTEGER
	}


pmopm2Mesrchannel77Index OBJECT-TYPE
	SYNTAX  INTEGER(0..128)
	MAX-ACCESS  read-only
	STATUS current
	DESCRIPTION
        "
        Index definition for the pmopm2Mesrchannel77
        table
        "
	::= { pmopm2Mesrchannel77Entry 1 }


pmopm2Mesrchannel77Portn OBJECT-TYPE
	SYNTAX  INTEGER (0..65535)
	MAX-ACCESS read-only
	STATUS current
	DESCRIPTION
        "
        Channel77 Power :This OID indicates
        the channel power  (Power =Q8(Number
        format)) (Unit = dBm)<Help> This
        measure indicates the channel power
        "
	::= { pmopm2Mesrchannel77Entry 2 }


--- *********************************************************
---     TABLE for the pmopm2Mesrchannel78 articles
--- *********************************************************

pmopm2Mesrchannel78Table OBJECT-TYPE
	SYNTAX  SEQUENCE OF Pmopm2Mesrchannel78Entry
	MAX-ACCESS not-accessible
	STATUS current
	DESCRIPTION
        "
        List of pmopm2Mesrchannel78 Article
        "
	::= { pmopm2MesrClient 170 }


pmopm2Mesrchannel78Entry OBJECT-TYPE
	SYNTAX Pmopm2Mesrchannel78Entry
	MAX-ACCESS not-accessible
	STATUS current
	DESCRIPTION
        "
        Row definition for the pmopm2Mesrchannel78
        table
        "
	INDEX   { pmopm2Mesrchannel78Index }
	::= { pmopm2Mesrchannel78Table 1 }


Pmopm2Mesrchannel78Entry ::=
	SEQUENCE {
	pmopm2Mesrchannel78Index
		INTEGER,
	pmopm2Mesrchannel78Portn
		INTEGER
	}


pmopm2Mesrchannel78Index OBJECT-TYPE
	SYNTAX  INTEGER(0..128)
	MAX-ACCESS  read-only
	STATUS current
	DESCRIPTION
        "
        Index definition for the pmopm2Mesrchannel78
        table
        "
	::= { pmopm2Mesrchannel78Entry 1 }


pmopm2Mesrchannel78Portn OBJECT-TYPE
	SYNTAX  INTEGER (0..65535)
	MAX-ACCESS read-only
	STATUS current
	DESCRIPTION
        "
        Channel78 Power :This OID indicates
        the channel power  (Power =Q8(Number
        format)) (Unit = dBm)<Help> This
        measure indicates the channel power
        "
	::= { pmopm2Mesrchannel78Entry 2 }


--- *********************************************************
---     TABLE for the pmopm2Mesrchannel79 articles
--- *********************************************************

pmopm2Mesrchannel79Table OBJECT-TYPE
	SYNTAX  SEQUENCE OF Pmopm2Mesrchannel79Entry
	MAX-ACCESS not-accessible
	STATUS current
	DESCRIPTION
        "
        List of pmopm2Mesrchannel79 Article
        "
	::= { pmopm2MesrClient 172 }


pmopm2Mesrchannel79Entry OBJECT-TYPE
	SYNTAX Pmopm2Mesrchannel79Entry
	MAX-ACCESS not-accessible
	STATUS current
	DESCRIPTION
        "
        Row definition for the pmopm2Mesrchannel79
        table
        "
	INDEX   { pmopm2Mesrchannel79Index }
	::= { pmopm2Mesrchannel79Table 1 }


Pmopm2Mesrchannel79Entry ::=
	SEQUENCE {
	pmopm2Mesrchannel79Index
		INTEGER,
	pmopm2Mesrchannel79Portn
		INTEGER
	}


pmopm2Mesrchannel79Index OBJECT-TYPE
	SYNTAX  INTEGER(0..128)
	MAX-ACCESS  read-only
	STATUS current
	DESCRIPTION
        "
        Index definition for the pmopm2Mesrchannel79
        table
        "
	::= { pmopm2Mesrchannel79Entry 1 }


pmopm2Mesrchannel79Portn OBJECT-TYPE
	SYNTAX  INTEGER (0..65535)
	MAX-ACCESS read-only
	STATUS current
	DESCRIPTION
        "
        Channel79 Power :This OID indicates
        the channel power  (Power =Q8(Number
        format)) (Unit = dBm)<Help> This
        measure indicates the channel power
        "
	::= { pmopm2Mesrchannel79Entry 2 }


--- *********************************************************
---     TABLE for the pmopm2Mesrchannel80 articles
--- *********************************************************

pmopm2Mesrchannel80Table OBJECT-TYPE
	SYNTAX  SEQUENCE OF Pmopm2Mesrchannel80Entry
	MAX-ACCESS not-accessible
	STATUS current
	DESCRIPTION
        "
        List of pmopm2Mesrchannel80 Article
        "
	::= { pmopm2MesrClient 174 }


pmopm2Mesrchannel80Entry OBJECT-TYPE
	SYNTAX Pmopm2Mesrchannel80Entry
	MAX-ACCESS not-accessible
	STATUS current
	DESCRIPTION
        "
        Row definition for the pmopm2Mesrchannel80
        table
        "
	INDEX   { pmopm2Mesrchannel80Index }
	::= { pmopm2Mesrchannel80Table 1 }


Pmopm2Mesrchannel80Entry ::=
	SEQUENCE {
	pmopm2Mesrchannel80Index
		INTEGER,
	pmopm2Mesrchannel80Portn
		INTEGER
	}


pmopm2Mesrchannel80Index OBJECT-TYPE
	SYNTAX  INTEGER(0..128)
	MAX-ACCESS  read-only
	STATUS current
	DESCRIPTION
        "
        Index definition for the pmopm2Mesrchannel80
        table
        "
	::= { pmopm2Mesrchannel80Entry 1 }


pmopm2Mesrchannel80Portn OBJECT-TYPE
	SYNTAX  INTEGER (0..65535)
	MAX-ACCESS read-only
	STATUS current
	DESCRIPTION
        "
        Channel80 Power :This OID indicates
        the channel power  (Power =Q8(Number
        format)) (Unit = dBm)<Help> This
        measure indicates the channel power
        "
	::= { pmopm2Mesrchannel80Entry 2 }


--- *********************************************************
---     TABLE for the pmopm2Mesrchannel81 articles
--- *********************************************************

pmopm2Mesrchannel81Table OBJECT-TYPE
	SYNTAX  SEQUENCE OF Pmopm2Mesrchannel81Entry
	MAX-ACCESS not-accessible
	STATUS current
	DESCRIPTION
        "
        List of pmopm2Mesrchannel81 Article
        "
	::= { pmopm2MesrClient 176 }


pmopm2Mesrchannel81Entry OBJECT-TYPE
	SYNTAX Pmopm2Mesrchannel81Entry
	MAX-ACCESS not-accessible
	STATUS current
	DESCRIPTION
        "
        Row definition for the pmopm2Mesrchannel81
        table
        "
	INDEX   { pmopm2Mesrchannel81Index }
	::= { pmopm2Mesrchannel81Table 1 }


Pmopm2Mesrchannel81Entry ::=
	SEQUENCE {
	pmopm2Mesrchannel81Index
		INTEGER,
	pmopm2Mesrchannel81Portn
		INTEGER
	}


pmopm2Mesrchannel81Index OBJECT-TYPE
	SYNTAX  INTEGER(0..128)
	MAX-ACCESS  read-only
	STATUS current
	DESCRIPTION
        "
        Index definition for the pmopm2Mesrchannel81
        table
        "
	::= { pmopm2Mesrchannel81Entry 1 }


pmopm2Mesrchannel81Portn OBJECT-TYPE
	SYNTAX  INTEGER (0..65535)
	MAX-ACCESS read-only
	STATUS current
	DESCRIPTION
        "
        Channel81 Power :This OID indicates
        the channel power  (Power =Q8(Number
        format)) (Unit = dBm)<Help> This
        measure indicates the channel power
        "
	::= { pmopm2Mesrchannel81Entry 2 }


--- *********************************************************
---     TABLE for the pmopm2Mesrchannel82 articles
--- *********************************************************

pmopm2Mesrchannel82Table OBJECT-TYPE
	SYNTAX  SEQUENCE OF Pmopm2Mesrchannel82Entry
	MAX-ACCESS not-accessible
	STATUS current
	DESCRIPTION
        "
        List of pmopm2Mesrchannel82 Article
        "
	::= { pmopm2MesrClient 178 }


pmopm2Mesrchannel82Entry OBJECT-TYPE
	SYNTAX Pmopm2Mesrchannel82Entry
	MAX-ACCESS not-accessible
	STATUS current
	DESCRIPTION
        "
        Row definition for the pmopm2Mesrchannel82
        table
        "
	INDEX   { pmopm2Mesrchannel82Index }
	::= { pmopm2Mesrchannel82Table 1 }


Pmopm2Mesrchannel82Entry ::=
	SEQUENCE {
	pmopm2Mesrchannel82Index
		INTEGER,
	pmopm2Mesrchannel82Portn
		INTEGER
	}


pmopm2Mesrchannel82Index OBJECT-TYPE
	SYNTAX  INTEGER(0..128)
	MAX-ACCESS  read-only
	STATUS current
	DESCRIPTION
        "
        Index definition for the pmopm2Mesrchannel82
        table
        "
	::= { pmopm2Mesrchannel82Entry 1 }


pmopm2Mesrchannel82Portn OBJECT-TYPE
	SYNTAX  INTEGER (0..65535)
	MAX-ACCESS read-only
	STATUS current
	DESCRIPTION
        "
        Channel82 Power :This OID indicates
        the channel power  (Power =Q8(Number
        format)) (Unit = dBm)<Help> This
        measure indicates the channel power
        "
	::= { pmopm2Mesrchannel82Entry 2 }


--- *********************************************************
---     TABLE for the pmopm2Mesrchannel83 articles
--- *********************************************************

pmopm2Mesrchannel83Table OBJECT-TYPE
	SYNTAX  SEQUENCE OF Pmopm2Mesrchannel83Entry
	MAX-ACCESS not-accessible
	STATUS current
	DESCRIPTION
        "
        List of pmopm2Mesrchannel83 Article
        "
	::= { pmopm2MesrClient 180 }


pmopm2Mesrchannel83Entry OBJECT-TYPE
	SYNTAX Pmopm2Mesrchannel83Entry
	MAX-ACCESS not-accessible
	STATUS current
	DESCRIPTION
        "
        Row definition for the pmopm2Mesrchannel83
        table
        "
	INDEX   { pmopm2Mesrchannel83Index }
	::= { pmopm2Mesrchannel83Table 1 }


Pmopm2Mesrchannel83Entry ::=
	SEQUENCE {
	pmopm2Mesrchannel83Index
		INTEGER,
	pmopm2Mesrchannel83Portn
		INTEGER
	}


pmopm2Mesrchannel83Index OBJECT-TYPE
	SYNTAX  INTEGER(0..128)
	MAX-ACCESS  read-only
	STATUS current
	DESCRIPTION
        "
        Index definition for the pmopm2Mesrchannel83
        table
        "
	::= { pmopm2Mesrchannel83Entry 1 }


pmopm2Mesrchannel83Portn OBJECT-TYPE
	SYNTAX  INTEGER (0..65535)
	MAX-ACCESS read-only
	STATUS current
	DESCRIPTION
        "
        Channel83 Power :This OID indicates
        the channel power  (Power =Q8(Number
        format)) (Unit = dBm)<Help> This
        measure indicates the channel power
        "
	::= { pmopm2Mesrchannel83Entry 2 }


--- *********************************************************
---     TABLE for the pmopm2Mesrchannel84 articles
--- *********************************************************

pmopm2Mesrchannel84Table OBJECT-TYPE
	SYNTAX  SEQUENCE OF Pmopm2Mesrchannel84Entry
	MAX-ACCESS not-accessible
	STATUS current
	DESCRIPTION
        "
        List of pmopm2Mesrchannel84 Article
        "
	::= { pmopm2MesrClient 182 }


pmopm2Mesrchannel84Entry OBJECT-TYPE
	SYNTAX Pmopm2Mesrchannel84Entry
	MAX-ACCESS not-accessible
	STATUS current
	DESCRIPTION
        "
        Row definition for the pmopm2Mesrchannel84
        table
        "
	INDEX   { pmopm2Mesrchannel84Index }
	::= { pmopm2Mesrchannel84Table 1 }


Pmopm2Mesrchannel84Entry ::=
	SEQUENCE {
	pmopm2Mesrchannel84Index
		INTEGER,
	pmopm2Mesrchannel84Portn
		INTEGER
	}


pmopm2Mesrchannel84Index OBJECT-TYPE
	SYNTAX  INTEGER(0..128)
	MAX-ACCESS  read-only
	STATUS current
	DESCRIPTION
        "
        Index definition for the pmopm2Mesrchannel84
        table
        "
	::= { pmopm2Mesrchannel84Entry 1 }


pmopm2Mesrchannel84Portn OBJECT-TYPE
	SYNTAX  INTEGER (0..65535)
	MAX-ACCESS read-only
	STATUS current
	DESCRIPTION
        "
        Channel84 Power :This OID indicates
        the channel power  (Power =Q8(Number
        format)) (Unit = dBm)<Help> This
        measure indicates the channel power
        "
	::= { pmopm2Mesrchannel84Entry 2 }


--- *********************************************************
---     TABLE for the pmopm2Mesrchannel85 articles
--- *********************************************************

pmopm2Mesrchannel85Table OBJECT-TYPE
	SYNTAX  SEQUENCE OF Pmopm2Mesrchannel85Entry
	MAX-ACCESS not-accessible
	STATUS current
	DESCRIPTION
        "
        List of pmopm2Mesrchannel85 Article
        "
	::= { pmopm2MesrClient 184 }


pmopm2Mesrchannel85Entry OBJECT-TYPE
	SYNTAX Pmopm2Mesrchannel85Entry
	MAX-ACCESS not-accessible
	STATUS current
	DESCRIPTION
        "
        Row definition for the pmopm2Mesrchannel85
        table
        "
	INDEX   { pmopm2Mesrchannel85Index }
	::= { pmopm2Mesrchannel85Table 1 }


Pmopm2Mesrchannel85Entry ::=
	SEQUENCE {
	pmopm2Mesrchannel85Index
		INTEGER,
	pmopm2Mesrchannel85Portn
		INTEGER
	}


pmopm2Mesrchannel85Index OBJECT-TYPE
	SYNTAX  INTEGER(0..128)
	MAX-ACCESS  read-only
	STATUS current
	DESCRIPTION
        "
        Index definition for the pmopm2Mesrchannel85
        table
        "
	::= { pmopm2Mesrchannel85Entry 1 }


pmopm2Mesrchannel85Portn OBJECT-TYPE
	SYNTAX  INTEGER (0..65535)
	MAX-ACCESS read-only
	STATUS current
	DESCRIPTION
        "
        Channel85 Power :This OID indicates
        the channel power  (Power =Q8(Number
        format)) (Unit = dBm)<Help> This
        measure indicates the channel power
        "
	::= { pmopm2Mesrchannel85Entry 2 }


--- *********************************************************
---     TABLE for the pmopm2Mesrchannel86 articles
--- *********************************************************

pmopm2Mesrchannel86Table OBJECT-TYPE
	SYNTAX  SEQUENCE OF Pmopm2Mesrchannel86Entry
	MAX-ACCESS not-accessible
	STATUS current
	DESCRIPTION
        "
        List of pmopm2Mesrchannel86 Article
        "
	::= { pmopm2MesrClient 186 }


pmopm2Mesrchannel86Entry OBJECT-TYPE
	SYNTAX Pmopm2Mesrchannel86Entry
	MAX-ACCESS not-accessible
	STATUS current
	DESCRIPTION
        "
        Row definition for the pmopm2Mesrchannel86
        table
        "
	INDEX   { pmopm2Mesrchannel86Index }
	::= { pmopm2Mesrchannel86Table 1 }


Pmopm2Mesrchannel86Entry ::=
	SEQUENCE {
	pmopm2Mesrchannel86Index
		INTEGER,
	pmopm2Mesrchannel86Portn
		INTEGER
	}


pmopm2Mesrchannel86Index OBJECT-TYPE
	SYNTAX  INTEGER(0..128)
	MAX-ACCESS  read-only
	STATUS current
	DESCRIPTION
        "
        Index definition for the pmopm2Mesrchannel86
        table
        "
	::= { pmopm2Mesrchannel86Entry 1 }


pmopm2Mesrchannel86Portn OBJECT-TYPE
	SYNTAX  INTEGER (0..65535)
	MAX-ACCESS read-only
	STATUS current
	DESCRIPTION
        "
        Channel86 Power :This OID indicates
        the channel power  (Power =Q8(Number
        format)) (Unit = dBm)<Help> This
        measure indicates the channel power
        "
	::= { pmopm2Mesrchannel86Entry 2 }


--- *********************************************************
---     TABLE for the pmopm2Mesrchannel87 articles
--- *********************************************************

pmopm2Mesrchannel87Table OBJECT-TYPE
	SYNTAX  SEQUENCE OF Pmopm2Mesrchannel87Entry
	MAX-ACCESS not-accessible
	STATUS current
	DESCRIPTION
        "
        List of pmopm2Mesrchannel87 Article
        "
	::= { pmopm2MesrClient 188 }


pmopm2Mesrchannel87Entry OBJECT-TYPE
	SYNTAX Pmopm2Mesrchannel87Entry
	MAX-ACCESS not-accessible
	STATUS current
	DESCRIPTION
        "
        Row definition for the pmopm2Mesrchannel87
        table
        "
	INDEX   { pmopm2Mesrchannel87Index }
	::= { pmopm2Mesrchannel87Table 1 }


Pmopm2Mesrchannel87Entry ::=
	SEQUENCE {
	pmopm2Mesrchannel87Index
		INTEGER,
	pmopm2Mesrchannel87Portn
		INTEGER
	}


pmopm2Mesrchannel87Index OBJECT-TYPE
	SYNTAX  INTEGER(0..128)
	MAX-ACCESS  read-only
	STATUS current
	DESCRIPTION
        "
        Index definition for the pmopm2Mesrchannel87
        table
        "
	::= { pmopm2Mesrchannel87Entry 1 }


pmopm2Mesrchannel87Portn OBJECT-TYPE
	SYNTAX  INTEGER (0..65535)
	MAX-ACCESS read-only
	STATUS current
	DESCRIPTION
        "
        Channel87 Power :This OID indicates
        the channel power  (Power =Q8(Number
        format)) (Unit = dBm)<Help> This
        measure indicates the channel power
        "
	::= { pmopm2Mesrchannel87Entry 2 }


--- *********************************************************
---     TABLE for the pmopm2Mesrchannel88 articles
--- *********************************************************

pmopm2Mesrchannel88Table OBJECT-TYPE
	SYNTAX  SEQUENCE OF Pmopm2Mesrchannel88Entry
	MAX-ACCESS not-accessible
	STATUS current
	DESCRIPTION
        "
        List of pmopm2Mesrchannel88 Article
        "
	::= { pmopm2MesrClient 190 }


pmopm2Mesrchannel88Entry OBJECT-TYPE
	SYNTAX Pmopm2Mesrchannel88Entry
	MAX-ACCESS not-accessible
	STATUS current
	DESCRIPTION
        "
        Row definition for the pmopm2Mesrchannel88
        table
        "
	INDEX   { pmopm2Mesrchannel88Index }
	::= { pmopm2Mesrchannel88Table 1 }


Pmopm2Mesrchannel88Entry ::=
	SEQUENCE {
	pmopm2Mesrchannel88Index
		INTEGER,
	pmopm2Mesrchannel88Portn
		INTEGER
	}


pmopm2Mesrchannel88Index OBJECT-TYPE
	SYNTAX  INTEGER(0..128)
	MAX-ACCESS  read-only
	STATUS current
	DESCRIPTION
        "
        Index definition for the pmopm2Mesrchannel88
        table
        "
	::= { pmopm2Mesrchannel88Entry 1 }


pmopm2Mesrchannel88Portn OBJECT-TYPE
	SYNTAX  INTEGER (0..65535)
	MAX-ACCESS read-only
	STATUS current
	DESCRIPTION
        "
        Channel88 Power :This OID indicates
        the channel power  (Power =Q8(Number
        format)) (Unit = dBm)<Help> This
        measure indicates the channel power
        "
	::= { pmopm2Mesrchannel88Entry 2 }


--- *********************************************************
---     TABLE for the pmopm2Mesrchannel89 articles
--- *********************************************************

pmopm2Mesrchannel89Table OBJECT-TYPE
	SYNTAX  SEQUENCE OF Pmopm2Mesrchannel89Entry
	MAX-ACCESS not-accessible
	STATUS current
	DESCRIPTION
        "
        List of pmopm2Mesrchannel89 Article
        "
	::= { pmopm2MesrClient 192 }


pmopm2Mesrchannel89Entry OBJECT-TYPE
	SYNTAX Pmopm2Mesrchannel89Entry
	MAX-ACCESS not-accessible
	STATUS current
	DESCRIPTION
        "
        Row definition for the pmopm2Mesrchannel89
        table
        "
	INDEX   { pmopm2Mesrchannel89Index }
	::= { pmopm2Mesrchannel89Table 1 }


Pmopm2Mesrchannel89Entry ::=
	SEQUENCE {
	pmopm2Mesrchannel89Index
		INTEGER,
	pmopm2Mesrchannel89Portn
		INTEGER
	}


pmopm2Mesrchannel89Index OBJECT-TYPE
	SYNTAX  INTEGER(0..128)
	MAX-ACCESS  read-only
	STATUS current
	DESCRIPTION
        "
        Index definition for the pmopm2Mesrchannel89
        table
        "
	::= { pmopm2Mesrchannel89Entry 1 }


pmopm2Mesrchannel89Portn OBJECT-TYPE
	SYNTAX  INTEGER (0..65535)
	MAX-ACCESS read-only
	STATUS current
	DESCRIPTION
        "
        Channel89 Power :This OID indicates
        the channel power  (Power =Q8(Number
        format)) (Unit = dBm)<Help> This
        measure indicates the channel power
        "
	::= { pmopm2Mesrchannel89Entry 2 }


--- *********************************************************
---     TABLE for the pmopm2Mesrchannel90 articles
--- *********************************************************

pmopm2Mesrchannel90Table OBJECT-TYPE
	SYNTAX  SEQUENCE OF Pmopm2Mesrchannel90Entry
	MAX-ACCESS not-accessible
	STATUS current
	DESCRIPTION
        "
        List of pmopm2Mesrchannel90 Article
        "
	::= { pmopm2MesrClient 194 }


pmopm2Mesrchannel90Entry OBJECT-TYPE
	SYNTAX Pmopm2Mesrchannel90Entry
	MAX-ACCESS not-accessible
	STATUS current
	DESCRIPTION
        "
        Row definition for the pmopm2Mesrchannel90
        table
        "
	INDEX   { pmopm2Mesrchannel90Index }
	::= { pmopm2Mesrchannel90Table 1 }


Pmopm2Mesrchannel90Entry ::=
	SEQUENCE {
	pmopm2Mesrchannel90Index
		INTEGER,
	pmopm2Mesrchannel90Portn
		INTEGER
	}


pmopm2Mesrchannel90Index OBJECT-TYPE
	SYNTAX  INTEGER(0..128)
	MAX-ACCESS  read-only
	STATUS current
	DESCRIPTION
        "
        Index definition for the pmopm2Mesrchannel90
        table
        "
	::= { pmopm2Mesrchannel90Entry 1 }


pmopm2Mesrchannel90Portn OBJECT-TYPE
	SYNTAX  INTEGER (0..65535)
	MAX-ACCESS read-only
	STATUS current
	DESCRIPTION
        "
        Channel90 Power :This OID indicates
        the channel power  (Power =Q8(Number
        format)) (Unit = dBm)<Help> This
        measure indicates the channel power
        "
	::= { pmopm2Mesrchannel90Entry 2 }


--- *********************************************************
---     TABLE for the pmopm2Mesrchannel91 articles
--- *********************************************************

pmopm2Mesrchannel91Table OBJECT-TYPE
	SYNTAX  SEQUENCE OF Pmopm2Mesrchannel91Entry
	MAX-ACCESS not-accessible
	STATUS current
	DESCRIPTION
        "
        List of pmopm2Mesrchannel91 Article
        "
	::= { pmopm2MesrClient 196 }


pmopm2Mesrchannel91Entry OBJECT-TYPE
	SYNTAX Pmopm2Mesrchannel91Entry
	MAX-ACCESS not-accessible
	STATUS current
	DESCRIPTION
        "
        Row definition for the pmopm2Mesrchannel91
        table
        "
	INDEX   { pmopm2Mesrchannel91Index }
	::= { pmopm2Mesrchannel91Table 1 }


Pmopm2Mesrchannel91Entry ::=
	SEQUENCE {
	pmopm2Mesrchannel91Index
		INTEGER,
	pmopm2Mesrchannel91Portn
		INTEGER
	}


pmopm2Mesrchannel91Index OBJECT-TYPE
	SYNTAX  INTEGER(0..128)
	MAX-ACCESS  read-only
	STATUS current
	DESCRIPTION
        "
        Index definition for the pmopm2Mesrchannel91
        table
        "
	::= { pmopm2Mesrchannel91Entry 1 }


pmopm2Mesrchannel91Portn OBJECT-TYPE
	SYNTAX  INTEGER (0..65535)
	MAX-ACCESS read-only
	STATUS current
	DESCRIPTION
        "
        Channel91 Power :This OID indicates
        the channel power  (Power =Q8(Number
        format)) (Unit = dBm)<Help> This
        measure indicates the channel power
        "
	::= { pmopm2Mesrchannel91Entry 2 }


--- *********************************************************
---     TABLE for the pmopm2Mesrchannel92 articles
--- *********************************************************

pmopm2Mesrchannel92Table OBJECT-TYPE
	SYNTAX  SEQUENCE OF Pmopm2Mesrchannel92Entry
	MAX-ACCESS not-accessible
	STATUS current
	DESCRIPTION
        "
        List of pmopm2Mesrchannel92 Article
        "
	::= { pmopm2MesrClient 198 }


pmopm2Mesrchannel92Entry OBJECT-TYPE
	SYNTAX Pmopm2Mesrchannel92Entry
	MAX-ACCESS not-accessible
	STATUS current
	DESCRIPTION
        "
        Row definition for the pmopm2Mesrchannel92
        table
        "
	INDEX   { pmopm2Mesrchannel92Index }
	::= { pmopm2Mesrchannel92Table 1 }


Pmopm2Mesrchannel92Entry ::=
	SEQUENCE {
	pmopm2Mesrchannel92Index
		INTEGER,
	pmopm2Mesrchannel92Portn
		INTEGER
	}


pmopm2Mesrchannel92Index OBJECT-TYPE
	SYNTAX  INTEGER(0..128)
	MAX-ACCESS  read-only
	STATUS current
	DESCRIPTION
        "
        Index definition for the pmopm2Mesrchannel92
        table
        "
	::= { pmopm2Mesrchannel92Entry 1 }


pmopm2Mesrchannel92Portn OBJECT-TYPE
	SYNTAX  INTEGER (0..65535)
	MAX-ACCESS read-only
	STATUS current
	DESCRIPTION
        "
        Channel92 Power :This OID indicates
        the channel power  (Power =Q8(Number
        format)) (Unit = dBm)<Help> This
        measure indicates the channel power
        "
	::= { pmopm2Mesrchannel92Entry 2 }


--- *********************************************************
---     TABLE for the pmopm2Mesrchannel93 articles
--- *********************************************************

pmopm2Mesrchannel93Table OBJECT-TYPE
	SYNTAX  SEQUENCE OF Pmopm2Mesrchannel93Entry
	MAX-ACCESS not-accessible
	STATUS current
	DESCRIPTION
        "
        List of pmopm2Mesrchannel93 Article
        "
	::= { pmopm2MesrClient 200 }


pmopm2Mesrchannel93Entry OBJECT-TYPE
	SYNTAX Pmopm2Mesrchannel93Entry
	MAX-ACCESS not-accessible
	STATUS current
	DESCRIPTION
        "
        Row definition for the pmopm2Mesrchannel93
        table
        "
	INDEX   { pmopm2Mesrchannel93Index }
	::= { pmopm2Mesrchannel93Table 1 }


Pmopm2Mesrchannel93Entry ::=
	SEQUENCE {
	pmopm2Mesrchannel93Index
		INTEGER,
	pmopm2Mesrchannel93Portn
		INTEGER
	}


pmopm2Mesrchannel93Index OBJECT-TYPE
	SYNTAX  INTEGER(0..128)
	MAX-ACCESS  read-only
	STATUS current
	DESCRIPTION
        "
        Index definition for the pmopm2Mesrchannel93
        table
        "
	::= { pmopm2Mesrchannel93Entry 1 }


pmopm2Mesrchannel93Portn OBJECT-TYPE
	SYNTAX  INTEGER (0..65535)
	MAX-ACCESS read-only
	STATUS current
	DESCRIPTION
        "
        Channel93 Power :This OID indicates
        the channel power  (Power =Q8(Number
        format)) (Unit = dBm)<Help> This
        measure indicates the channel power
        "
	::= { pmopm2Mesrchannel93Entry 2 }


--- *********************************************************
---     TABLE for the pmopm2Mesrchannel94 articles
--- *********************************************************

pmopm2Mesrchannel94Table OBJECT-TYPE
	SYNTAX  SEQUENCE OF Pmopm2Mesrchannel94Entry
	MAX-ACCESS not-accessible
	STATUS current
	DESCRIPTION
        "
        List of pmopm2Mesrchannel94 Article
        "
	::= { pmopm2MesrClient 202 }


pmopm2Mesrchannel94Entry OBJECT-TYPE
	SYNTAX Pmopm2Mesrchannel94Entry
	MAX-ACCESS not-accessible
	STATUS current
	DESCRIPTION
        "
        Row definition for the pmopm2Mesrchannel94
        table
        "
	INDEX   { pmopm2Mesrchannel94Index }
	::= { pmopm2Mesrchannel94Table 1 }


Pmopm2Mesrchannel94Entry ::=
	SEQUENCE {
	pmopm2Mesrchannel94Index
		INTEGER,
	pmopm2Mesrchannel94Portn
		INTEGER
	}


pmopm2Mesrchannel94Index OBJECT-TYPE
	SYNTAX  INTEGER(0..128)
	MAX-ACCESS  read-only
	STATUS current
	DESCRIPTION
        "
        Index definition for the pmopm2Mesrchannel94
        table
        "
	::= { pmopm2Mesrchannel94Entry 1 }


pmopm2Mesrchannel94Portn OBJECT-TYPE
	SYNTAX  INTEGER (0..65535)
	MAX-ACCESS read-only
	STATUS current
	DESCRIPTION
        "
        Channel94 Power :This OID indicates
        the channel power  (Power =Q8(Number
        format)) (Unit = dBm)<Help> This
        measure indicates the channel power
        "
	::= { pmopm2Mesrchannel94Entry 2 }


--- *********************************************************
---     TABLE for the pmopm2Mesrchannel95 articles
--- *********************************************************

pmopm2Mesrchannel95Table OBJECT-TYPE
	SYNTAX  SEQUENCE OF Pmopm2Mesrchannel95Entry
	MAX-ACCESS not-accessible
	STATUS current
	DESCRIPTION
        "
        List of pmopm2Mesrchannel95 Article
        "
	::= { pmopm2MesrClient 204 }


pmopm2Mesrchannel95Entry OBJECT-TYPE
	SYNTAX Pmopm2Mesrchannel95Entry
	MAX-ACCESS not-accessible
	STATUS current
	DESCRIPTION
        "
        Row definition for the pmopm2Mesrchannel95
        table
        "
	INDEX   { pmopm2Mesrchannel95Index }
	::= { pmopm2Mesrchannel95Table 1 }


Pmopm2Mesrchannel95Entry ::=
	SEQUENCE {
	pmopm2Mesrchannel95Index
		INTEGER,
	pmopm2Mesrchannel95Portn
		INTEGER
	}


pmopm2Mesrchannel95Index OBJECT-TYPE
	SYNTAX  INTEGER(0..128)
	MAX-ACCESS  read-only
	STATUS current
	DESCRIPTION
        "
        Index definition for the pmopm2Mesrchannel95
        table
        "
	::= { pmopm2Mesrchannel95Entry 1 }


pmopm2Mesrchannel95Portn OBJECT-TYPE
	SYNTAX  INTEGER (0..65535)
	MAX-ACCESS read-only
	STATUS current
	DESCRIPTION
        "
        Channel95 Power :This OID indicates
        the channel power  (Power =Q8(Number
        format)) (Unit = dBm)<Help> This
        measure indicates the channel power
        "
	::= { pmopm2Mesrchannel95Entry 2 }


--- *********************************************************
---     TABLE for the pmopm2Mesrchannel96 articles
--- *********************************************************

pmopm2Mesrchannel96Table OBJECT-TYPE
	SYNTAX  SEQUENCE OF Pmopm2Mesrchannel96Entry
	MAX-ACCESS not-accessible
	STATUS current
	DESCRIPTION
        "
        List of pmopm2Mesrchannel96 Article
        "
	::= { pmopm2MesrClient 206 }


pmopm2Mesrchannel96Entry OBJECT-TYPE
	SYNTAX Pmopm2Mesrchannel96Entry
	MAX-ACCESS not-accessible
	STATUS current
	DESCRIPTION
        "
        Row definition for the pmopm2Mesrchannel96
        table
        "
	INDEX   { pmopm2Mesrchannel96Index }
	::= { pmopm2Mesrchannel96Table 1 }


Pmopm2Mesrchannel96Entry ::=
	SEQUENCE {
	pmopm2Mesrchannel96Index
		INTEGER,
	pmopm2Mesrchannel96Portn
		INTEGER
	}


pmopm2Mesrchannel96Index OBJECT-TYPE
	SYNTAX  INTEGER(0..128)
	MAX-ACCESS  read-only
	STATUS current
	DESCRIPTION
        "
        Index definition for the pmopm2Mesrchannel96
        table
        "
	::= { pmopm2Mesrchannel96Entry 1 }


pmopm2Mesrchannel96Portn OBJECT-TYPE
	SYNTAX  INTEGER (0..65535)
	MAX-ACCESS read-only
	STATUS current
	DESCRIPTION
        "
        Channel96 Power :This OID indicates
        the channel power  (Power =Q8(Number
        format)) (Unit = dBm)<Help> This
        measure indicates the channel power
        "
	::= { pmopm2Mesrchannel96Entry 2 }


--- *********************************************************
---     TABLE for the pmopm2MesrportInputPwr articles
--- *********************************************************

pmopm2MesrportInputPwrTable OBJECT-TYPE
	SYNTAX  SEQUENCE OF Pmopm2MesrportInputPwrEntry
	MAX-ACCESS not-accessible
	STATUS current
	DESCRIPTION
        "
        List of pmopm2MesrportInputPwr
        Article
        "
	::= { pmopm2MesrClient 208 }


pmopm2MesrportInputPwrEntry OBJECT-TYPE
	SYNTAX Pmopm2MesrportInputPwrEntry
	MAX-ACCESS not-accessible
	STATUS current
	DESCRIPTION
        "
        Row definition for the pmopm2MesrportInputPwr
        table
        "
	INDEX   { pmopm2MesrportInputPwrIndex }
	::= { pmopm2MesrportInputPwrTable 1 }


Pmopm2MesrportInputPwrEntry ::=
	SEQUENCE {
	pmopm2MesrportInputPwrIndex
		INTEGER,
	pmopm2MesrportInputPwrPortn
		INTEGER
	}


pmopm2MesrportInputPwrIndex OBJECT-TYPE
	SYNTAX  INTEGER(0..128)
	MAX-ACCESS  read-only
	STATUS current
	DESCRIPTION
        "
        Index definition for the pmopm2MesrportInputPwr
        table
        "
	::= { pmopm2MesrportInputPwrEntry 1 }


pmopm2MesrportInputPwrPortn OBJECT-TYPE
	SYNTAX  INTEGER (0..65535)
	MAX-ACCESS read-only
	STATUS current
	DESCRIPTION
        "
        OPM Port Input Power :This OID
        indicates the total input power
        on the OPM port (Power =Q8(Number
        format)) (Unit = dBm)<Help> This
        measure indicates the total input
        power on the OPM port
        "
	::= { pmopm2MesrportInputPwrEntry 2 }


--- *********************************************************
---     TABLE for the pmopm2MesrchannelMaxPwr articles
--- *********************************************************

pmopm2MesrchannelMaxPwrTable OBJECT-TYPE
	SYNTAX  SEQUENCE OF Pmopm2MesrchannelMaxPwrEntry
	MAX-ACCESS not-accessible
	STATUS current
	DESCRIPTION
        "
        List of pmopm2MesrchannelMaxPwr
        Article
        "
	::= { pmopm2MesrClient 210 }


pmopm2MesrchannelMaxPwrEntry OBJECT-TYPE
	SYNTAX Pmopm2MesrchannelMaxPwrEntry
	MAX-ACCESS not-accessible
	STATUS current
	DESCRIPTION
        "
        Row definition for the pmopm2MesrchannelMaxPwr
        table
        "
	INDEX   { pmopm2MesrchannelMaxPwrIndex }
	::= { pmopm2MesrchannelMaxPwrTable 1 }


Pmopm2MesrchannelMaxPwrEntry ::=
	SEQUENCE {
	pmopm2MesrchannelMaxPwrIndex
		INTEGER,
	pmopm2MesrchannelMaxPwrPortn
		INTEGER
	}


pmopm2MesrchannelMaxPwrIndex OBJECT-TYPE
	SYNTAX  INTEGER(0..128)
	MAX-ACCESS  read-only
	STATUS current
	DESCRIPTION
        "
        Index definition for the pmopm2MesrchannelMaxPwr
        table
        "
	::= { pmopm2MesrchannelMaxPwrEntry 1 }


pmopm2MesrchannelMaxPwrPortn OBJECT-TYPE
	SYNTAX  INTEGER (0..65535)
	MAX-ACCESS read-only
	STATUS current
	DESCRIPTION
        "
        Channel Maximum Power :This OID
        indicates the maximum channel power
        on the OPM input port (Power =Q8(Number
        format)) (Unit = dBm)<Help> This
        measure indicates the maximum channel
        power on the OPM input port
        "
	::= { pmopm2MesrchannelMaxPwrEntry 2 }


--- *********************************************************
---     TABLE for the pmopm2MesrchannelMinPwr articles
--- *********************************************************

pmopm2MesrchannelMinPwrTable OBJECT-TYPE
	SYNTAX  SEQUENCE OF Pmopm2MesrchannelMinPwrEntry
	MAX-ACCESS not-accessible
	STATUS current
	DESCRIPTION
        "
        List of pmopm2MesrchannelMinPwr
        Article
        "
	::= { pmopm2MesrClient 212 }


pmopm2MesrchannelMinPwrEntry OBJECT-TYPE
	SYNTAX Pmopm2MesrchannelMinPwrEntry
	MAX-ACCESS not-accessible
	STATUS current
	DESCRIPTION
        "
        Row definition for the pmopm2MesrchannelMinPwr
        table
        "
	INDEX   { pmopm2MesrchannelMinPwrIndex }
	::= { pmopm2MesrchannelMinPwrTable 1 }


Pmopm2MesrchannelMinPwrEntry ::=
	SEQUENCE {
	pmopm2MesrchannelMinPwrIndex
		INTEGER,
	pmopm2MesrchannelMinPwrPortn
		INTEGER
	}


pmopm2MesrchannelMinPwrIndex OBJECT-TYPE
	SYNTAX  INTEGER(0..128)
	MAX-ACCESS  read-only
	STATUS current
	DESCRIPTION
        "
        Index definition for the pmopm2MesrchannelMinPwr
        table
        "
	::= { pmopm2MesrchannelMinPwrEntry 1 }


pmopm2MesrchannelMinPwrPortn OBJECT-TYPE
	SYNTAX  INTEGER (0..65535)
	MAX-ACCESS read-only
	STATUS current
	DESCRIPTION
        "
        Channel Minimum Power :This OID
        indicates the minimum channel power
        on the OPM input port (Power =Q8(Number
        format)) (Unit = dBm)<Help> This
        measure indicates the minimum channel
        power on the OPM input port
        "
	::= { pmopm2MesrchannelMinPwrEntry 2 }


--- *****************************************************
---     LEAF for the opmTemp article
--- *****************************************************

pmopm2MesropmTemp OBJECT-TYPE
	  SYNTAX Unsigned32 (0..65535)
	  MAX-ACCESS read-only
	  STATUS current
	  DESCRIPTION
        "
        PM OPM Temperature :This OID indicates
        the temperature of the PM OPM
         (Temperature = AV/256) (Unit =
        C)<Help> This measure indicates
        the temperature of the PM OPM
        "
	  ::= { pmopm2MesrOther 248 }








--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pmopm2DwlrestartProcess OBJECT IDENTIFIER ::= { pmopm2DwlOther 0 }




pmopm2DwlColdRestartProcessed OBJECT-TYPE
	  SYNTAX EkiOnOff
	  MAX-ACCESS read-only
	  STATUS current
	  DESCRIPTION
        "
        Cold Restart :This OID indicates
        that the module last restart was
        a Cold RESTART
        "
	  ::= { pmopm2DwlrestartProcess 2 }



pmopm2DwlWarmRestartProcessed OBJECT-TYPE
	  SYNTAX EkiOnOff
	  MAX-ACCESS read-only
	  STATUS current
	  DESCRIPTION
        "
        Warm Restart :This OID indicates
        that the module last restart was
        a Warm RESTART
        "
	  ::= { pmopm2DwlrestartProcess 1 }



--- *****************************************************
---     LEAF for the swBanksUsed article
--- *****************************************************
pmopm2DwlswBanksUsed OBJECT IDENTIFIER ::= { pmopm2DwlOther 1 }




pmopm2DwlSwBank2Notempty OBJECT-TYPE
	  SYNTAX EkiOnOff
	  MAX-ACCESS read-only
	  STATUS current
	  DESCRIPTION
        "
        SW bank 2 loaded :This OID indicates
        a software is loaded in SW bank
        2  <Help>  This status indicates
        if the SW bank 2 contains SW package
        "
	  ::= { pmopm2DwlswBanksUsed 6 }



pmopm2DwlSwBank1Notempty OBJECT-TYPE
	  SYNTAX EkiOnOff
	  MAX-ACCESS read-only
	  STATUS current
	  DESCRIPTION
        "
        SW bank 1 loaded :This OID indicates
        a software is loaded in SW bank
        1  <Help>  This status indicates
        if the SW bank 1 contains SW package
        "
	  ::= { pmopm2DwlswBanksUsed 5 }



pmopm2DwlSwBank2Used OBJECT-TYPE
	  SYNTAX EkiOnOff
	  MAX-ACCESS read-only
	  STATUS current
	  DESCRIPTION
        "
        SW bank 2 active :This OID indicates
        the module is working on SW bank
        2  <Help>  This status indicates
        if the SW bank 2 is active or standby
        "
	  ::= { pmopm2DwlswBanksUsed 2 }



pmopm2DwlSwBank1Used OBJECT-TYPE
	  SYNTAX EkiOnOff
	  MAX-ACCESS read-only
	  STATUS current
	  DESCRIPTION
        "
        SW bank 1 active :This OID indicates
        the module is working on SW bank
        1  <Help>  This status indicates
        if the SW bank 1 is active or standby
        "
	  ::= { pmopm2DwlswBanksUsed 1 }



--- *****************************************************
---     LEAF for the gwBanksUsed article
--- *****************************************************
pmopm2DwlgwBanksUsed OBJECT IDENTIFIER ::= { pmopm2DwlOther 2 }




pmopm2DwlGwBank4Notempty OBJECT-TYPE
	  SYNTAX EkiOnOff
	  MAX-ACCESS read-only
	  STATUS current
	  DESCRIPTION
        "
        GW bank 4 loaded :This OID indicates
        a gateware is loaded in GW bank
        4
        "
	  ::= { pmopm2DwlgwBanksUsed 8 }



pmopm2DwlGwBank3Notempty OBJECT-TYPE
	  SYNTAX EkiOnOff
	  MAX-ACCESS read-only
	  STATUS current
	  DESCRIPTION
        "
        GW bank 3 loaded :This OID indicates
        a gateware is loaded in GW bank
        3  <Help>  This status indicates
        if the GW bank 3 contains GW package
        "
	  ::= { pmopm2DwlgwBanksUsed 7 }



pmopm2DwlGwBank2Notempty OBJECT-TYPE
	  SYNTAX EkiOnOff
	  MAX-ACCESS read-only
	  STATUS current
	  DESCRIPTION
        "
        GW bank 2 loaded :This OID indicates
        a gateware is loaded in GW bank
        2
        "
	  ::= { pmopm2DwlgwBanksUsed 6 }



pmopm2DwlGwBank1Notempty OBJECT-TYPE
	  SYNTAX EkiOnOff
	  MAX-ACCESS read-only
	  STATUS current
	  DESCRIPTION
        "
        GW bank 1 loaded :This OID indicates
        a gateware is loaded in GW bank
        1  <Help>  This status indicates
        if the GW bank 1 contains GW package
        "
	  ::= { pmopm2DwlgwBanksUsed 5 }



pmopm2DwlGwBank4Used OBJECT-TYPE
	  SYNTAX EkiOnOff
	  MAX-ACCESS read-only
	  STATUS current
	  DESCRIPTION
        "
        GW bank 4 active :This OID indicates
        the module is working on GW bank
        4
        "
	  ::= { pmopm2DwlgwBanksUsed 4 }



pmopm2DwlGwBank3Used OBJECT-TYPE
	  SYNTAX EkiOnOff
	  MAX-ACCESS read-only
	  STATUS current
	  DESCRIPTION
        "
        GW bank 3 active :This OID indicates
        the module is working on GW bank
        3  <Help>  This status indicates
        if the GW bank 3 is active or standby
        "
	  ::= { pmopm2DwlgwBanksUsed 3 }



pmopm2DwlGwBank2Used OBJECT-TYPE
	  SYNTAX EkiOnOff
	  MAX-ACCESS read-only
	  STATUS current
	  DESCRIPTION
        "
        GW bank 2 active :This OID indicates
        the module is working on GW bank
        2
        "
	  ::= { pmopm2DwlgwBanksUsed 2 }



pmopm2DwlGwBank1Used OBJECT-TYPE
	  SYNTAX EkiOnOff
	  MAX-ACCESS read-only
	  STATUS current
	  DESCRIPTION
        "
        GW bank 1 active :This OID indicates
        the module is working on GW bank
        1  <Help>  This status indicates
        if the GW bank 1 is active or standby
        "
	  ::= { pmopm2DwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group lsd
--- *****************************************************

pmopm2CfgLsd OBJECT IDENTIFIER ::= { pmopm2Config 1 }



--- *****************************************************
---     LEAF for the table 0012
--- *****************************************************

pmopm2tableclientcaiscsf OBJECT IDENTIFIER ::= { pmopm2CfgLsd 1 }



--- *****************************************************
---     LEAF for the table Group startup
--- *****************************************************

pmopm2CfgStartup OBJECT IDENTIFIER ::= { pmopm2Config 2 }



--- *****************************************************
---     LEAF for the table 0005
--- *****************************************************

pmopm2tableother OBJECT IDENTIFIER ::= { pmopm2CfgStartup 1 }



pmopm2CfgcomponentType OBJECT-TYPE
	  SYNTAX Unsigned32 (0..65536)
	  MAX-ACCESS read-only
	  STATUS current
	  DESCRIPTION
        "
        Component parameters :This OID
        defines the component parameters
        "
	  ::= { pmopm2tableother 2 }



pmopm2Cfgmiscellaneous OBJECT-TYPE
	  SYNTAX Unsigned32 (0..65536)
	  MAX-ACCESS read-only
	  STATUS current
	  DESCRIPTION
        "
        Miscellaneous default settings
        :This OID defines the miscellaneous
        parameters
        "
	  ::= { pmopm2tableother 3 }



pmopm2CfgfirstChannel OBJECT-TYPE
	  SYNTAX Unsigned32 (0..65536)
	  MAX-ACCESS read-only
	  STATUS current
	  DESCRIPTION
        "
        Number of the first channel of
        the component :This OID defines
        the first channel number of the
        PMOPM
        "
	  ::= { pmopm2tableother 4 }



pmopm2CfglastChannel OBJECT-TYPE
	  SYNTAX Unsigned32 (0..65536)
	  MAX-ACCESS read-only
	  STATUS current
	  DESCRIPTION
        "
        Number of the last channel of
         the component :This OID defines
        the last channel number of the
         PMOPM
        "
	  ::= { pmopm2tableother 5 }



pmopm2Cfggrid OBJECT-TYPE
	  SYNTAX Unsigned32 (0..65536)
	  MAX-ACCESS read-only
	  STATUS current
	  DESCRIPTION
        "
        Grid value of the component :This
        OID defines the grid of the PMOPM
        "
	  ::= { pmopm2tableother 6 }



--- *****************************************************
---     LEAF for the table 2110
--- *****************************************************

pmopm2CfgClientStartupOosTable OBJECT-TYPE
	SYNTAX  SEQUENCE OF Pmopm2CfgClientStartupOosEntry
	MAX-ACCESS not-accessible
	STATUS current
	DESCRIPTION
        "
        List of  Article
        "
	::= { pmopm2CfgStartup 2 }


pmopm2CfgClientStartupOosEntry OBJECT-TYPE
	SYNTAX Pmopm2CfgClientStartupOosEntry
	MAX-ACCESS not-accessible
	STATUS current
	DESCRIPTION
        "
        Row definition for the startup
        table
        "
	INDEX   { pmopm2CfgClientStartupOosIndex }
	::= { pmopm2CfgClientStartupOosTable 1 }


Pmopm2CfgClientStartupOosEntry ::=
	SEQUENCE {
	pmopm2CfgClientStartupOosIndex
		INTEGER,
	pmopm2CfgSpectrumOosPortn
		Unsigned32,
	pmopm2CfgSpectrumOffsetPortn
		Unsigned32,
	pmopm2CfgCh1Ch16OosPortn
		Unsigned32,
	pmopm2CfgCh17Ch32OosPortn
		Unsigned32,
	pmopm2CfgCh33Ch48OosPortn
		Unsigned32,
	pmopm2CfgCh49Ch64OosPortn
		Unsigned32,
	pmopm2CfgCh65Ch80OosPortn
		Unsigned32,
	pmopm2CfgCh81Ch96OosPortn
		Unsigned32
	}


pmopm2CfgClientStartupOosIndex OBJECT-TYPE
	SYNTAX  INTEGER(0..128)
	MAX-ACCESS  read-only
	STATUS current
	DESCRIPTION
        "
        Index definition for the clientStartupOos
        table
        "
	::= { pmopm2CfgClientStartupOosEntry 1 }


pmopm2CfgSpectrumOosPortn OBJECT-TYPE
	SYNTAX  Unsigned32 (0..65536)
	MAX-ACCESS read-write
	STATUS current
	DESCRIPTION
        "
        Default Settings on Spectrum OOS
        :This OID sets the OPM input port
        out of service
        "
	::= { pmopm2CfgClientStartupOosEntry 3 }


pmopm2CfgSpectrumOffsetPortn OBJECT-TYPE
	SYNTAX  Unsigned32 (0..65536)
	MAX-ACCESS read-write
	STATUS current
	DESCRIPTION
        "
        Default Settings on Spectrum Offset
        :This OID defines a negative offset
        for the OPM input port
        "
	::= { pmopm2CfgClientStartupOosEntry 4 }


pmopm2CfgCh1Ch16OosPortn OBJECT-TYPE
	SYNTAX  Unsigned32 (0..65536)
	MAX-ACCESS read-write
	STATUS current
	DESCRIPTION
        "
        Default Settings on Channel OOS
        :This OID sets the channel out
         of service
        "
	::= { pmopm2CfgClientStartupOosEntry 5 }


pmopm2CfgCh17Ch32OosPortn OBJECT-TYPE
	SYNTAX  Unsigned32 (0..65536)
	MAX-ACCESS read-write
	STATUS current
	DESCRIPTION
        "
        Default Settings on Channel OOS
        :This OID sets the channel out
         of service
        "
	::= { pmopm2CfgClientStartupOosEntry 6 }


pmopm2CfgCh33Ch48OosPortn OBJECT-TYPE
	SYNTAX  Unsigned32 (0..65536)
	MAX-ACCESS read-write
	STATUS current
	DESCRIPTION
        "
        Default Settings on Channel OOS
        :This OID sets the channel out
         of service
        "
	::= { pmopm2CfgClientStartupOosEntry 7 }


pmopm2CfgCh49Ch64OosPortn OBJECT-TYPE
	SYNTAX  Unsigned32 (0..65536)
	MAX-ACCESS read-write
	STATUS current
	DESCRIPTION
        "
        Default Settings on Channel OOS
        :This OID sets the channel out
         of service
        "
	::= { pmopm2CfgClientStartupOosEntry 8 }


pmopm2CfgCh65Ch80OosPortn OBJECT-TYPE
	SYNTAX  Unsigned32 (0..65536)
	MAX-ACCESS read-write
	STATUS current
	DESCRIPTION
        "
        Default Settings on Channel OOS
        :This OID sets the channel out
         of service
        "
	::= { pmopm2CfgClientStartupOosEntry 9 }


pmopm2CfgCh81Ch96OosPortn OBJECT-TYPE
	SYNTAX  Unsigned32 (0..65536)
	MAX-ACCESS read-write
	STATUS current
	DESCRIPTION
        "
        Default Settings on Channel OOS
        :This OID sets the channel out
         of service
        "
	::= { pmopm2CfgClientStartupOosEntry 10 }


--- *****************************************************
---     LEAF for the table 2111
--- *****************************************************

pmopm2CfgClientStartupBalanceTable OBJECT-TYPE
	SYNTAX  SEQUENCE OF Pmopm2CfgClientStartupBalanceEntry
	MAX-ACCESS not-accessible
	STATUS current
	DESCRIPTION
        "
        List of  Article
        "
	::= { pmopm2CfgStartup 3 }


pmopm2CfgClientStartupBalanceEntry OBJECT-TYPE
	SYNTAX Pmopm2CfgClientStartupBalanceEntry
	MAX-ACCESS not-accessible
	STATUS current
	DESCRIPTION
        "
        Row definition for the startup
        table
        "
	INDEX   { pmopm2CfgClientStartupBalanceIndex }
	::= { pmopm2CfgClientStartupBalanceTable 1 }


Pmopm2CfgClientStartupBalanceEntry ::=
	SEQUENCE {
	pmopm2CfgClientStartupBalanceIndex
		INTEGER,
	pmopm2CfgCh1Ch16BalancePortn
		Unsigned32,
	pmopm2CfgCh17Ch32BalancePortn
		Unsigned32,
	pmopm2CfgCh33Ch48BalancePortn
		Unsigned32,
	pmopm2CfgCh49Ch64BalancePortn
		Unsigned32,
	pmopm2CfgCh65Ch80BalancePortn
		Unsigned32,
	pmopm2CfgCh81Ch96BalancePortn
		Unsigned32
	}


pmopm2CfgClientStartupBalanceIndex OBJECT-TYPE
	SYNTAX  INTEGER(0..128)
	MAX-ACCESS  read-only
	STATUS current
	DESCRIPTION
        "
        Index definition for the clientStartupBalance
        table
        "
	::= { pmopm2CfgClientStartupBalanceEntry 1 }


pmopm2CfgCh1Ch16BalancePortn OBJECT-TYPE
	SYNTAX  Unsigned32 (0..65536)
	MAX-ACCESS read-write
	STATUS current
	DESCRIPTION
        "
        Default Settings on Balance :This
        OID is used by the Ekinops auto
        turn up application to tag the
         channel as balanced
        "
	::= { pmopm2CfgClientStartupBalanceEntry 3 }


pmopm2CfgCh17Ch32BalancePortn OBJECT-TYPE
	SYNTAX  Unsigned32 (0..65536)
	MAX-ACCESS read-write
	STATUS current
	DESCRIPTION
        "
        Default Settings on Balance :This
        OID is used by the Ekinops auto
        turn up application to tag the
         channel as balanced
        "
	::= { pmopm2CfgClientStartupBalanceEntry 4 }


pmopm2CfgCh33Ch48BalancePortn OBJECT-TYPE
	SYNTAX  Unsigned32 (0..65536)
	MAX-ACCESS read-write
	STATUS current
	DESCRIPTION
        "
        Default Settings on Balance :This
        OID is used by the Ekinops auto
        turn up application to tag the
         channel as balanced
        "
	::= { pmopm2CfgClientStartupBalanceEntry 5 }


pmopm2CfgCh49Ch64BalancePortn OBJECT-TYPE
	SYNTAX  Unsigned32 (0..65536)
	MAX-ACCESS read-write
	STATUS current
	DESCRIPTION
        "
        Default Settings on Balance :This
        OID is used by the Ekinops auto
        turn up application to tag the
         channel as balanced
        "
	::= { pmopm2CfgClientStartupBalanceEntry 6 }


pmopm2CfgCh65Ch80BalancePortn OBJECT-TYPE
	SYNTAX  Unsigned32 (0..65536)
	MAX-ACCESS read-write
	STATUS current
	DESCRIPTION
        "
        Default Settings on Balance :This
        OID is used by the Ekinops auto
        turn up application to tag the
         channel as balanced
        "
	::= { pmopm2CfgClientStartupBalanceEntry 7 }


pmopm2CfgCh81Ch96BalancePortn OBJECT-TYPE
	SYNTAX  Unsigned32 (0..65536)
	MAX-ACCESS read-write
	STATUS current
	DESCRIPTION
        "
        Default Settings on Balance :This
        OID is used by the Ekinops auto
        turn up application to tag the
         channel as balanced
        "
	::= { pmopm2CfgClientStartupBalanceEntry 8 }


--- *****************************************************
---     LEAF for the table 2112
--- *****************************************************

pmopm2CfgClientStartupAbsthreshTable OBJECT-TYPE
	SYNTAX  SEQUENCE OF Pmopm2CfgClientStartupAbsthreshEntry
	MAX-ACCESS not-accessible
	STATUS current
	DESCRIPTION
        "
        List of  Article
        "
	::= { pmopm2CfgStartup 4 }


pmopm2CfgClientStartupAbsthreshEntry OBJECT-TYPE
	SYNTAX Pmopm2CfgClientStartupAbsthreshEntry
	MAX-ACCESS not-accessible
	STATUS current
	DESCRIPTION
        "
        Row definition for the startup
        table
        "
	INDEX   { pmopm2CfgClientStartupAbsthreshIndex }
	::= { pmopm2CfgClientStartupAbsthreshTable 1 }


Pmopm2CfgClientStartupAbsthreshEntry ::=
	SEQUENCE {
	pmopm2CfgClientStartupAbsthreshIndex
		INTEGER,
	pmopm2CfgChannel1AbsthreshPortn
		Unsigned32,
	pmopm2CfgChannel2AbsthreshPortn
		Unsigned32,
	pmopm2CfgChannel3AbsthreshPortn
		Unsigned32,
	pmopm2CfgChannel4AbsthreshPortn
		Unsigned32,
	pmopm2CfgChannel5AbsthreshPortn
		Unsigned32,
	pmopm2CfgChannel6AbsthreshPortn
		Unsigned32,
	pmopm2CfgChannel7AbsthreshPortn
		Unsigned32,
	pmopm2CfgChannel8AbsthreshPortn
		Unsigned32,
	pmopm2CfgChannel9AbsthreshPortn
		Unsigned32,
	pmopm2CfgChannel10AbsthreshPortn
		Unsigned32,
	pmopm2CfgChannel11AbsthreshPortn
		Unsigned32,
	pmopm2CfgChannel12AbsthreshPortn
		Unsigned32,
	pmopm2CfgChannel13AbsthreshPortn
		Unsigned32,
	pmopm2CfgChannel14AbsthreshPortn
		Unsigned32,
	pmopm2CfgChannel15AbsthreshPortn
		Unsigned32,
	pmopm2CfgChannel16AbsthreshPortn
		Unsigned32,
	pmopm2CfgChannel17AbsthreshPortn
		Unsigned32,
	pmopm2CfgChannel18AbsthreshPortn
		Unsigned32,
	pmopm2CfgChannel19AbsthreshPortn
		Unsigned32,
	pmopm2CfgChannel20AbsthreshPortn
		Unsigned32,
	pmopm2CfgChannel21AbsthreshPortn
		Unsigned32,
	pmopm2CfgChannel22AbsthreshPortn
		Unsigned32,
	pmopm2CfgChannel23AbsthreshPortn
		Unsigned32,
	pmopm2CfgChannel24AbsthreshPortn
		Unsigned32,
	pmopm2CfgChannel25AbsthreshPortn
		Unsigned32,
	pmopm2CfgChannel26AbsthreshPortn
		Unsigned32,
	pmopm2CfgChannel27AbsthreshPortn
		Unsigned32,
	pmopm2CfgChannel28AbsthreshPortn
		Unsigned32,
	pmopm2CfgChannel29AbsthreshPortn
		Unsigned32,
	pmopm2CfgChannel30AbsthreshPortn
		Unsigned32,
	pmopm2CfgChannel31AbsthreshPortn
		Unsigned32,
	pmopm2CfgChannel32AbsthreshPortn
		Unsigned32,
	pmopm2CfgChannel33AbsthreshPortn
		Unsigned32,
	pmopm2CfgChannel34AbsthreshPortn
		Unsigned32,
	pmopm2CfgChannel35AbsthreshPortn
		Unsigned32,
	pmopm2CfgChannel36AbsthreshPortn
		Unsigned32,
	pmopm2CfgChannel37AbsthreshPortn
		Unsigned32,
	pmopm2CfgChannel38AbsthreshPortn
		Unsigned32,
	pmopm2CfgChannel39AbsthreshPortn
		Unsigned32,
	pmopm2CfgChannel40AbsthreshPortn
		Unsigned32,
	pmopm2CfgChannel41AbsthreshPortn
		Unsigned32,
	pmopm2CfgChannel42AbsthreshPortn
		Unsigned32,
	pmopm2CfgChannel43AbsthreshPortn
		Unsigned32,
	pmopm2CfgChannel44AbsthreshPortn
		Unsigned32,
	pmopm2CfgChannel45AbsthreshPortn
		Unsigned32,
	pmopm2CfgChannel46AbsthreshPortn
		Unsigned32,
	pmopm2CfgChannel47AbsthreshPortn
		Unsigned32,
	pmopm2CfgChannel48AbsthreshPortn
		Unsigned32,
	pmopm2CfgChannel49AbsthreshPortn
		Unsigned32,
	pmopm2CfgChannel50AbsthreshPortn
		Unsigned32,
	pmopm2CfgChannel51AbsthreshPortn
		Unsigned32,
	pmopm2CfgChannel52AbsthreshPortn
		Unsigned32,
	pmopm2CfgChannel53AbsthreshPortn
		Unsigned32,
	pmopm2CfgChannel54AbsthreshPortn
		Unsigned32,
	pmopm2CfgChannel55AbsthreshPortn
		Unsigned32,
	pmopm2CfgChannel56AbsthreshPortn
		Unsigned32,
	pmopm2CfgChannel57AbsthreshPortn
		Unsigned32,
	pmopm2CfgChannel58AbsthreshPortn
		Unsigned32,
	pmopm2CfgChannel59AbsthreshPortn
		Unsigned32,
	pmopm2CfgChannel60AbsthreshPortn
		Unsigned32,
	pmopm2CfgChannel61AbsthreshPortn
		Unsigned32,
	pmopm2CfgChannel62AbsthreshPortn
		Unsigned32,
	pmopm2CfgChannel63AbsthreshPortn
		Unsigned32,
	pmopm2CfgChannel64AbsthreshPortn
		Unsigned32,
	pmopm2CfgChannel65AbsthreshPortn
		Unsigned32,
	pmopm2CfgChannel66AbsthreshPortn
		Unsigned32,
	pmopm2CfgChannel67AbsthreshPortn
		Unsigned32,
	pmopm2CfgChannel68AbsthreshPortn
		Unsigned32,
	pmopm2CfgChannel69AbsthreshPortn
		Unsigned32,
	pmopm2CfgChannel70AbsthreshPortn
		Unsigned32,
	pmopm2CfgChannel71AbsthreshPortn
		Unsigned32,
	pmopm2CfgChannel72AbsthreshPortn
		Unsigned32,
	pmopm2CfgChannel73AbsthreshPortn
		Unsigned32,
	pmopm2CfgChannel74AbsthreshPortn
		Unsigned32,
	pmopm2CfgChannel75AbsthreshPortn
		Unsigned32,
	pmopm2CfgChannel76AbsthreshPortn
		Unsigned32,
	pmopm2CfgChannel77AbsthreshPortn
		Unsigned32,
	pmopm2CfgChannel78AbsthreshPortn
		Unsigned32,
	pmopm2CfgChannel79AbsthreshPortn
		Unsigned32,
	pmopm2CfgChannel80AbsthreshPortn
		Unsigned32,
	pmopm2CfgChannel81AbsthreshPortn
		Unsigned32,
	pmopm2CfgChannel82AbsthreshPortn
		Unsigned32,
	pmopm2CfgChannel83AbsthreshPortn
		Unsigned32,
	pmopm2CfgChannel84AbsthreshPortn
		Unsigned32,
	pmopm2CfgChannel85AbsthreshPortn
		Unsigned32,
	pmopm2CfgChannel86AbsthreshPortn
		Unsigned32,
	pmopm2CfgChannel87AbsthreshPortn
		Unsigned32,
	pmopm2CfgChannel88AbsthreshPortn
		Unsigned32,
	pmopm2CfgChannel89AbsthreshPortn
		Unsigned32,
	pmopm2CfgChannel90AbsthreshPortn
		Unsigned32,
	pmopm2CfgChannel91AbsthreshPortn
		Unsigned32,
	pmopm2CfgChannel92AbsthreshPortn
		Unsigned32,
	pmopm2CfgChannel93AbsthreshPortn
		Unsigned32,
	pmopm2CfgChannel94AbsthreshPortn
		Unsigned32,
	pmopm2CfgChannel95AbsthreshPortn
		Unsigned32,
	pmopm2CfgChannel96AbsthreshPortn
		Unsigned32
	}


pmopm2CfgClientStartupAbsthreshIndex OBJECT-TYPE
	SYNTAX  INTEGER(0..128)
	MAX-ACCESS  read-only
	STATUS current
	DESCRIPTION
        "
        Index definition for the clientStartupAbsthresh
        table
        "
	::= { pmopm2CfgClientStartupAbsthreshEntry 1 }


pmopm2CfgChannel1AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 3 }


pmopm2CfgChannel2AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 4 }


pmopm2CfgChannel3AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 5 }


pmopm2CfgChannel4AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 6 }


pmopm2CfgChannel5AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 7 }


pmopm2CfgChannel6AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 8 }


pmopm2CfgChannel7AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 9 }


pmopm2CfgChannel8AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 10 }


pmopm2CfgChannel9AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 11 }


pmopm2CfgChannel10AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 12 }


pmopm2CfgChannel11AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 13 }


pmopm2CfgChannel12AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 14 }


pmopm2CfgChannel13AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 15 }


pmopm2CfgChannel14AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 16 }


pmopm2CfgChannel15AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 17 }


pmopm2CfgChannel16AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 18 }


pmopm2CfgChannel17AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 19 }


pmopm2CfgChannel18AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 20 }


pmopm2CfgChannel19AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 21 }


pmopm2CfgChannel20AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 22 }


pmopm2CfgChannel21AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 23 }


pmopm2CfgChannel22AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 24 }


pmopm2CfgChannel23AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 25 }


pmopm2CfgChannel24AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 26 }


pmopm2CfgChannel25AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 27 }


pmopm2CfgChannel26AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 28 }


pmopm2CfgChannel27AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 29 }


pmopm2CfgChannel28AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 30 }


pmopm2CfgChannel29AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 31 }


pmopm2CfgChannel30AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 32 }


pmopm2CfgChannel31AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 33 }


pmopm2CfgChannel32AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 34 }


pmopm2CfgChannel33AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 35 }


pmopm2CfgChannel34AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 36 }


pmopm2CfgChannel35AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 37 }


pmopm2CfgChannel36AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 38 }


pmopm2CfgChannel37AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 39 }


pmopm2CfgChannel38AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 40 }


pmopm2CfgChannel39AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 41 }


pmopm2CfgChannel40AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 42 }


pmopm2CfgChannel41AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 43 }


pmopm2CfgChannel42AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 44 }


pmopm2CfgChannel43AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 45 }


pmopm2CfgChannel44AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 46 }


pmopm2CfgChannel45AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 47 }


pmopm2CfgChannel46AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 48 }


pmopm2CfgChannel47AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 49 }


pmopm2CfgChannel48AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 50 }


pmopm2CfgChannel49AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 51 }


pmopm2CfgChannel50AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 52 }


pmopm2CfgChannel51AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 53 }


pmopm2CfgChannel52AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 54 }


pmopm2CfgChannel53AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 55 }


pmopm2CfgChannel54AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 56 }


pmopm2CfgChannel55AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 57 }


pmopm2CfgChannel56AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 58 }


pmopm2CfgChannel57AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 59 }


pmopm2CfgChannel58AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 60 }


pmopm2CfgChannel59AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 61 }


pmopm2CfgChannel60AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 62 }


pmopm2CfgChannel61AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 63 }


pmopm2CfgChannel62AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 64 }


pmopm2CfgChannel63AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 65 }


pmopm2CfgChannel64AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 66 }


pmopm2CfgChannel65AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 67 }


pmopm2CfgChannel66AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 68 }


pmopm2CfgChannel67AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 69 }


pmopm2CfgChannel68AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 70 }


pmopm2CfgChannel69AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 71 }


pmopm2CfgChannel70AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 72 }


pmopm2CfgChannel71AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 73 }


pmopm2CfgChannel72AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 74 }


pmopm2CfgChannel73AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 75 }


pmopm2CfgChannel74AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 76 }


pmopm2CfgChannel75AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 77 }


pmopm2CfgChannel76AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 78 }


pmopm2CfgChannel77AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 79 }


pmopm2CfgChannel78AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 80 }


pmopm2CfgChannel79AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 81 }


pmopm2CfgChannel80AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 82 }


pmopm2CfgChannel81AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 83 }


pmopm2CfgChannel82AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 84 }


pmopm2CfgChannel83AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 85 }


pmopm2CfgChannel84AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 86 }


pmopm2CfgChannel85AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 87 }


pmopm2CfgChannel86AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 88 }


pmopm2CfgChannel87AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 89 }


pmopm2CfgChannel88AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 90 }


pmopm2CfgChannel89AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 91 }


pmopm2CfgChannel90AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 92 }


pmopm2CfgChannel91AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 93 }


pmopm2CfgChannel92AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 94 }


pmopm2CfgChannel93AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 95 }


pmopm2CfgChannel94AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 96 }


pmopm2CfgChannel95AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 97 }


pmopm2CfgChannel96AbsthreshPortn OBJECT-TYPE
	SYNTAX  Unsigned32 (0..65536)
	MAX-ACCESS read-write
	STATUS current
	DESCRIPTION
        "
        Default Settings on Absence Threshold
        :This OID defines the threshold
        to consider a channel as absent
        "
	::= { pmopm2CfgClientStartupAbsthreshEntry 98 }


--- *****************************************************
---     LEAF for the table 2113
--- *****************************************************

pmopm2CfgClientStartupPwrHighTable OBJECT-TYPE
	SYNTAX  SEQUENCE OF Pmopm2CfgClientStartupPwrHighEntry
	MAX-ACCESS not-accessible
	STATUS current
	DESCRIPTION
        "
        List of  Article
        "
	::= { pmopm2CfgStartup 5 }


pmopm2CfgClientStartupPwrHighEntry OBJECT-TYPE
	SYNTAX Pmopm2CfgClientStartupPwrHighEntry
	MAX-ACCESS not-accessible
	STATUS current
	DESCRIPTION
        "
        Row definition for the startup
        table
        "
	INDEX   { pmopm2CfgClientStartupPwrHighIndex }
	::= { pmopm2CfgClientStartupPwrHighTable 1 }


Pmopm2CfgClientStartupPwrHighEntry ::=
	SEQUENCE {
	pmopm2CfgClientStartupPwrHighIndex
		INTEGER,
	pmopm2CfgChannel1PwrhighPortn
		Unsigned32,
	pmopm2CfgChannel2PwrhighPortn
		Unsigned32,
	pmopm2CfgChannel3PwrhighPortn
		Unsigned32,
	pmopm2CfgChannel4PwrhighPortn
		Unsigned32,
	pmopm2CfgChannel5PwrhighPortn
		Unsigned32,
	pmopm2CfgChannel6PwrhighPortn
		Unsigned32,
	pmopm2CfgChannel7PwrhighPortn
		Unsigned32,
	pmopm2CfgChannel8PwrhighPortn
		Unsigned32,
	pmopm2CfgChannel9PwrhighPortn
		Unsigned32,
	pmopm2CfgChannel10PwrhighPortn
		Unsigned32,
	pmopm2CfgChannel11PwrhighPortn
		Unsigned32,
	pmopm2CfgChannel12PwrhighPortn
		Unsigned32,
	pmopm2CfgChannel13PwrhighPortn
		Unsigned32,
	pmopm2CfgChannel14PwrhighPortn
		Unsigned32,
	pmopm2CfgChannel15PwrhighPortn
		Unsigned32,
	pmopm2CfgChannel16PwrhighPortn
		Unsigned32,
	pmopm2CfgChannel17PwrhighPortn
		Unsigned32,
	pmopm2CfgChannel18PwrhighPortn
		Unsigned32,
	pmopm2CfgChannel19PwrhighPortn
		Unsigned32,
	pmopm2CfgChannel20PwrhighPortn
		Unsigned32,
	pmopm2CfgChannel21PwrhighPortn
		Unsigned32,
	pmopm2CfgChannel22PwrhighPortn
		Unsigned32,
	pmopm2CfgChannel23PwrhighPortn
		Unsigned32,
	pmopm2CfgChannel24PwrhighPortn
		Unsigned32,
	pmopm2CfgChannel25PwrhighPortn
		Unsigned32,
	pmopm2CfgChannel26PwrhighPortn
		Unsigned32,
	pmopm2CfgChannel27PwrhighPortn
		Unsigned32,
	pmopm2CfgChannel28PwrhighPortn
		Unsigned32,
	pmopm2CfgChannel29PwrhighPortn
		Unsigned32,
	pmopm2CfgChannel30PwrhighPortn
		Unsigned32,
	pmopm2CfgChannel31PwrhighPortn
		Unsigned32,
	pmopm2CfgChannel32PwrhighPortn
		Unsigned32,
	pmopm2CfgChannel33PwrhighPortn
		Unsigned32,
	pmopm2CfgChannel34PwrhighPortn
		Unsigned32,
	pmopm2CfgChannel35PwrhighPortn
		Unsigned32,
	pmopm2CfgChannel36PwrhighPortn
		Unsigned32,
	pmopm2CfgChannel37PwrhighPortn
		Unsigned32,
	pmopm2CfgChannel38PwrhighPortn
		Unsigned32,
	pmopm2CfgChannel39PwrhighPortn
		Unsigned32,
	pmopm2CfgChannel40PwrhighPortn
		Unsigned32,
	pmopm2CfgChannel41PwrhighPortn
		Unsigned32,
	pmopm2CfgChannel42PwrhighPortn
		Unsigned32,
	pmopm2CfgChannel43PwrhighPortn
		Unsigned32,
	pmopm2CfgChannel44PwrhighPortn
		Unsigned32,
	pmopm2CfgChannel45PwrhighPortn
		Unsigned32,
	pmopm2CfgChannel46PwrhighPortn
		Unsigned32,
	pmopm2CfgChannel47PwrhighPortn
		Unsigned32,
	pmopm2CfgChannel48PwrhighPortn
		Unsigned32,
	pmopm2CfgChannel49PwrhighPortn
		Unsigned32,
	pmopm2CfgChannel50PwrhighPortn
		Unsigned32,
	pmopm2CfgChannel51PwrhighPortn
		Unsigned32,
	pmopm2CfgChannel52PwrhighPortn
		Unsigned32,
	pmopm2CfgChannel53PwrhighPortn
		Unsigned32,
	pmopm2CfgChannel54PwrhighPortn
		Unsigned32,
	pmopm2CfgChannel55PwrhighPortn
		Unsigned32,
	pmopm2CfgChannel56PwrhighPortn
		Unsigned32,
	pmopm2CfgChannel57PwrhighPortn
		Unsigned32,
	pmopm2CfgChannel58PwrhighPortn
		Unsigned32,
	pmopm2CfgChannel59PwrhighPortn
		Unsigned32,
	pmopm2CfgChannel60PwrhighPortn
		Unsigned32,
	pmopm2CfgChannel61PwrhighPortn
		Unsigned32,
	pmopm2CfgChannel62PwrhighPortn
		Unsigned32,
	pmopm2CfgChannel63PwrhighPortn
		Unsigned32,
	pmopm2CfgChannel64PwrhighPortn
		Unsigned32,
	pmopm2CfgChannel65PwrhighPortn
		Unsigned32,
	pmopm2CfgChannel66PwrhighPortn
		Unsigned32,
	pmopm2CfgChannel67PwrhighPortn
		Unsigned32,
	pmopm2CfgChannel68PwrhighPortn
		Unsigned32,
	pmopm2CfgChannel69PwrhighPortn
		Unsigned32,
	pmopm2CfgChannel70PwrhighPortn
		Unsigned32,
	pmopm2CfgChannel71PwrhighPortn
		Unsigned32,
	pmopm2CfgChannel72PwrhighPortn
		Unsigned32,
	pmopm2CfgChannel73PwrhighPortn
		Unsigned32,
	pmopm2CfgChannel74PwrhighPortn
		Unsigned32,
	pmopm2CfgChannel75PwrhighPortn
		Unsigned32,
	pmopm2CfgChannel76PwrhighPortn
		Unsigned32,
	pmopm2CfgChannel77PwrhighPortn
		Unsigned32,
	pmopm2CfgChannel78PwrhighPortn
		Unsigned32,
	pmopm2CfgChannel79PwrhighPortn
		Unsigned32,
	pmopm2CfgChannel80PwrhighPortn
		Unsigned32,
	pmopm2CfgChannel81PwrhighPortn
		Unsigned32,
	pmopm2CfgChannel82PwrhighPortn
		Unsigned32,
	pmopm2CfgChannel83PwrhighPortn
		Unsigned32,
	pmopm2CfgChannel84PwrhighPortn
		Unsigned32,
	pmopm2CfgChannel85PwrhighPortn
		Unsigned32,
	pmopm2CfgChannel86PwrhighPortn
		Unsigned32,
	pmopm2CfgChannel87PwrhighPortn
		Unsigned32,
	pmopm2CfgChannel88PwrhighPortn
		Unsigned32,
	pmopm2CfgChannel89PwrhighPortn
		Unsigned32,
	pmopm2CfgChannel90PwrhighPortn
		Unsigned32,
	pmopm2CfgChannel91PwrhighPortn
		Unsigned32,
	pmopm2CfgChannel92PwrhighPortn
		Unsigned32,
	pmopm2CfgChannel93PwrhighPortn
		Unsigned32,
	pmopm2CfgChannel94PwrhighPortn
		Unsigned32,
	pmopm2CfgChannel95PwrhighPortn
		Unsigned32,
	pmopm2CfgChannel96PwrhighPortn
		Unsigned32
	}


pmopm2CfgClientStartupPwrHighIndex OBJECT-TYPE
	SYNTAX  INTEGER(0..128)
	MAX-ACCESS  read-only
	STATUS current
	DESCRIPTION
        "
        Index definition for the clientStartupPwrHigh
        table
        "
	::= { pmopm2CfgClientStartupPwrHighEntry 1 }


pmopm2CfgChannel1PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 3 }


pmopm2CfgChannel2PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 4 }


pmopm2CfgChannel3PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 5 }


pmopm2CfgChannel4PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 6 }


pmopm2CfgChannel5PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 7 }


pmopm2CfgChannel6PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 8 }


pmopm2CfgChannel7PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 9 }


pmopm2CfgChannel8PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 10 }


pmopm2CfgChannel9PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 11 }


pmopm2CfgChannel10PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 12 }


pmopm2CfgChannel11PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 13 }


pmopm2CfgChannel12PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 14 }


pmopm2CfgChannel13PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 15 }


pmopm2CfgChannel14PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 16 }


pmopm2CfgChannel15PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 17 }


pmopm2CfgChannel16PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 18 }


pmopm2CfgChannel17PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 19 }


pmopm2CfgChannel18PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 20 }


pmopm2CfgChannel19PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 21 }


pmopm2CfgChannel20PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 22 }


pmopm2CfgChannel21PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 23 }


pmopm2CfgChannel22PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 24 }


pmopm2CfgChannel23PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 25 }


pmopm2CfgChannel24PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 26 }


pmopm2CfgChannel25PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 27 }


pmopm2CfgChannel26PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 28 }


pmopm2CfgChannel27PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 29 }


pmopm2CfgChannel28PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 30 }


pmopm2CfgChannel29PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 31 }


pmopm2CfgChannel30PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 32 }


pmopm2CfgChannel31PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 33 }


pmopm2CfgChannel32PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 34 }


pmopm2CfgChannel33PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 35 }


pmopm2CfgChannel34PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 36 }


pmopm2CfgChannel35PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 37 }


pmopm2CfgChannel36PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 38 }


pmopm2CfgChannel37PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 39 }


pmopm2CfgChannel38PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 40 }


pmopm2CfgChannel39PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 41 }


pmopm2CfgChannel40PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 42 }


pmopm2CfgChannel41PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 43 }


pmopm2CfgChannel42PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 44 }


pmopm2CfgChannel43PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 45 }


pmopm2CfgChannel44PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 46 }


pmopm2CfgChannel45PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 47 }


pmopm2CfgChannel46PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 48 }


pmopm2CfgChannel47PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 49 }


pmopm2CfgChannel48PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 50 }


pmopm2CfgChannel49PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 51 }


pmopm2CfgChannel50PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 52 }


pmopm2CfgChannel51PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 53 }


pmopm2CfgChannel52PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 54 }


pmopm2CfgChannel53PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 55 }


pmopm2CfgChannel54PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 56 }


pmopm2CfgChannel55PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 57 }


pmopm2CfgChannel56PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 58 }


pmopm2CfgChannel57PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 59 }


pmopm2CfgChannel58PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 60 }


pmopm2CfgChannel59PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 61 }


pmopm2CfgChannel60PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 62 }


pmopm2CfgChannel61PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 63 }


pmopm2CfgChannel62PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 64 }


pmopm2CfgChannel63PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 65 }


pmopm2CfgChannel64PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 66 }


pmopm2CfgChannel65PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 67 }


pmopm2CfgChannel66PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 68 }


pmopm2CfgChannel67PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 69 }


pmopm2CfgChannel68PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 70 }


pmopm2CfgChannel69PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 71 }


pmopm2CfgChannel70PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 72 }


pmopm2CfgChannel71PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 73 }


pmopm2CfgChannel72PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 74 }


pmopm2CfgChannel73PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 75 }


pmopm2CfgChannel74PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 76 }


pmopm2CfgChannel75PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 77 }


pmopm2CfgChannel76PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 78 }


pmopm2CfgChannel77PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 79 }


pmopm2CfgChannel78PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 80 }


pmopm2CfgChannel79PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 81 }


pmopm2CfgChannel80PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 82 }


pmopm2CfgChannel81PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 83 }


pmopm2CfgChannel82PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 84 }


pmopm2CfgChannel83PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 85 }


pmopm2CfgChannel84PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 86 }


pmopm2CfgChannel85PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 87 }


pmopm2CfgChannel86PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 88 }


pmopm2CfgChannel87PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 89 }


pmopm2CfgChannel88PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 90 }


pmopm2CfgChannel89PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 91 }


pmopm2CfgChannel90PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 92 }


pmopm2CfgChannel91PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 93 }


pmopm2CfgChannel92PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 94 }


pmopm2CfgChannel93PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 95 }


pmopm2CfgChannel94PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 96 }


pmopm2CfgChannel95PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 97 }


pmopm2CfgChannel96PwrhighPortn OBJECT-TYPE
	SYNTAX  Unsigned32 (0..65536)
	MAX-ACCESS read-write
	STATUS current
	DESCRIPTION
        "
        Default Settings on Max Power
         :This OID defines the threshold
        to rise a channel power high
        "
	::= { pmopm2CfgClientStartupPwrHighEntry 98 }


--- *****************************************************
---     LEAF for the table 2114
--- *****************************************************

pmopm2CfgClientStartupPwrLowTable OBJECT-TYPE
	SYNTAX  SEQUENCE OF Pmopm2CfgClientStartupPwrLowEntry
	MAX-ACCESS not-accessible
	STATUS current
	DESCRIPTION
        "
        List of  Article
        "
	::= { pmopm2CfgStartup 6 }


pmopm2CfgClientStartupPwrLowEntry OBJECT-TYPE
	SYNTAX Pmopm2CfgClientStartupPwrLowEntry
	MAX-ACCESS not-accessible
	STATUS current
	DESCRIPTION
        "
        Row definition for the startup
        table
        "
	INDEX   { pmopm2CfgClientStartupPwrLowIndex }
	::= { pmopm2CfgClientStartupPwrLowTable 1 }


Pmopm2CfgClientStartupPwrLowEntry ::=
	SEQUENCE {
	pmopm2CfgClientStartupPwrLowIndex
		INTEGER,
	pmopm2CfgChannel1PwrlowPortn
		Unsigned32,
	pmopm2CfgChannel2PwrlowPortn
		Unsigned32,
	pmopm2CfgChannel3PwrlowPortn
		Unsigned32,
	pmopm2CfgChannel4PwrlowPortn
		Unsigned32,
	pmopm2CfgChannel5PwrlowPortn
		Unsigned32,
	pmopm2CfgChannel6PwrlowPortn
		Unsigned32,
	pmopm2CfgChannel7PwrlowPortn
		Unsigned32,
	pmopm2CfgChannel8PwrlowPortn
		Unsigned32,
	pmopm2CfgChannel9PwrlowPortn
		Unsigned32,
	pmopm2CfgChannel10PwrlowPortn
		Unsigned32,
	pmopm2CfgChannel11PwrlowPortn
		Unsigned32,
	pmopm2CfgChannel12PwrlowPortn
		Unsigned32,
	pmopm2CfgChannel13PwrlowPortn
		Unsigned32,
	pmopm2CfgChannel14PwrlowPortn
		Unsigned32,
	pmopm2CfgChannel15PwrlowPortn
		Unsigned32,
	pmopm2CfgChannel16PwrlowPortn
		Unsigned32,
	pmopm2CfgChannel17PwrlowPortn
		Unsigned32,
	pmopm2CfgChannel18PwrlowPortn
		Unsigned32,
	pmopm2CfgChannel19PwrlowPortn
		Unsigned32,
	pmopm2CfgChannel20PwrlowPortn
		Unsigned32,
	pmopm2CfgChannel21PwrlowPortn
		Unsigned32,
	pmopm2CfgChannel22PwrlowPortn
		Unsigned32,
	pmopm2CfgChannel23PwrlowPortn
		Unsigned32,
	pmopm2CfgChannel24PwrlowPortn
		Unsigned32,
	pmopm2CfgChannel25PwrlowPortn
		Unsigned32,
	pmopm2CfgChannel26PwrlowPortn
		Unsigned32,
	pmopm2CfgChannel27PwrlowPortn
		Unsigned32,
	pmopm2CfgChannel28PwrlowPortn
		Unsigned32,
	pmopm2CfgChannel29PwrlowPortn
		Unsigned32,
	pmopm2CfgChannel30PwrlowPortn
		Unsigned32,
	pmopm2CfgChannel31PwrlowPortn
		Unsigned32,
	pmopm2CfgChannel32PwrlowPortn
		Unsigned32,
	pmopm2CfgChannel33PwrlowPortn
		Unsigned32,
	pmopm2CfgChannel34PwrlowPortn
		Unsigned32,
	pmopm2CfgChannel35PwrlowPortn
		Unsigned32,
	pmopm2CfgChannel36PwrlowPortn
		Unsigned32,
	pmopm2CfgChannel37PwrlowPortn
		Unsigned32,
	pmopm2CfgChannel38PwrlowPortn
		Unsigned32,
	pmopm2CfgChannel39PwrlowPortn
		Unsigned32,
	pmopm2CfgChannel40PwrlowPortn
		Unsigned32,
	pmopm2CfgChannel41PwrlowPortn
		Unsigned32,
	pmopm2CfgChannel42PwrlowPortn
		Unsigned32,
	pmopm2CfgChannel43PwrlowPortn
		Unsigned32,
	pmopm2CfgChannel44PwrlowPortn
		Unsigned32,
	pmopm2CfgChannel45PwrlowPortn
		Unsigned32,
	pmopm2CfgChannel46PwrlowPortn
		Unsigned32,
	pmopm2CfgChannel47PwrlowPortn
		Unsigned32,
	pmopm2CfgChannel48PwrlowPortn
		Unsigned32,
	pmopm2CfgChannel49PwrlowPortn
		Unsigned32,
	pmopm2CfgChannel50PwrlowPortn
		Unsigned32,
	pmopm2CfgChannel51PwrlowPortn
		Unsigned32,
	pmopm2CfgChannel52PwrlowPortn
		Unsigned32,
	pmopm2CfgChannel53PwrlowPortn
		Unsigned32,
	pmopm2CfgChannel54PwrlowPortn
		Unsigned32,
	pmopm2CfgChannel55PwrlowPortn
		Unsigned32,
	pmopm2CfgChannel56PwrlowPortn
		Unsigned32,
	pmopm2CfgChannel57PwrlowPortn
		Unsigned32,
	pmopm2CfgChannel58PwrlowPortn
		Unsigned32,
	pmopm2CfgChannel59PwrlowPortn
		Unsigned32,
	pmopm2CfgChannel60PwrlowPortn
		Unsigned32,
	pmopm2CfgChannel61PwrlowPortn
		Unsigned32,
	pmopm2CfgChannel62PwrlowPortn
		Unsigned32,
	pmopm2CfgChannel63PwrlowPortn
		Unsigned32,
	pmopm2CfgChannel64PwrlowPortn
		Unsigned32,
	pmopm2CfgChannel65PwrlowPortn
		Unsigned32,
	pmopm2CfgChannel66PwrlowPortn
		Unsigned32,
	pmopm2CfgChannel67PwrlowPortn
		Unsigned32,
	pmopm2CfgChannel68PwrlowPortn
		Unsigned32,
	pmopm2CfgChannel69PwrlowPortn
		Unsigned32,
	pmopm2CfgChannel70PwrlowPortn
		Unsigned32,
	pmopm2CfgChannel71PwrlowPortn
		Unsigned32,
	pmopm2CfgChannel72PwrlowPortn
		Unsigned32,
	pmopm2CfgChannel73PwrlowPortn
		Unsigned32,
	pmopm2CfgChannel74PwrlowPortn
		Unsigned32,
	pmopm2CfgChannel75PwrlowPortn
		Unsigned32,
	pmopm2CfgChannel76PwrlowPortn
		Unsigned32,
	pmopm2CfgChannel77PwrlowPortn
		Unsigned32,
	pmopm2CfgChannel78PwrlowPortn
		Unsigned32,
	pmopm2CfgChannel79PwrlowPortn
		Unsigned32,
	pmopm2CfgChannel80PwrlowPortn
		Unsigned32,
	pmopm2CfgChannel81PwrlowPortn
		Unsigned32,
	pmopm2CfgChannel82PwrlowPortn
		Unsigned32,
	pmopm2CfgChannel83PwrlowPortn
		Unsigned32,
	pmopm2CfgChannel84PwrlowPortn
		Unsigned32,
	pmopm2CfgChannel85PwrlowPortn
		Unsigned32,
	pmopm2CfgChannel86PwrlowPortn
		Unsigned32,
	pmopm2CfgChannel87PwrlowPortn
		Unsigned32,
	pmopm2CfgChannel88PwrlowPortn
		Unsigned32,
	pmopm2CfgChannel89PwrlowPortn
		Unsigned32,
	pmopm2CfgChannel90PwrlowPortn
		Unsigned32,
	pmopm2CfgChannel91PwrlowPortn
		Unsigned32,
	pmopm2CfgChannel92PwrlowPortn
		Unsigned32,
	pmopm2CfgChannel93PwrlowPortn
		Unsigned32,
	pmopm2CfgChannel94PwrlowPortn
		Unsigned32,
	pmopm2CfgChannel95PwrlowPortn
		Unsigned32,
	pmopm2CfgChannel96PwrlowPortn
		Unsigned32
	}


pmopm2CfgClientStartupPwrLowIndex OBJECT-TYPE
	SYNTAX  INTEGER(0..128)
	MAX-ACCESS  read-only
	STATUS current
	DESCRIPTION
        "
        Index definition for the clientStartupPwrLow
        table
        "
	::= { pmopm2CfgClientStartupPwrLowEntry 1 }


pmopm2CfgChannel1PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 3 }


pmopm2CfgChannel2PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 4 }


pmopm2CfgChannel3PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 5 }


pmopm2CfgChannel4PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 6 }


pmopm2CfgChannel5PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 7 }


pmopm2CfgChannel6PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 8 }


pmopm2CfgChannel7PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 9 }


pmopm2CfgChannel8PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 10 }


pmopm2CfgChannel9PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 11 }


pmopm2CfgChannel10PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 12 }


pmopm2CfgChannel11PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 13 }


pmopm2CfgChannel12PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 14 }


pmopm2CfgChannel13PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 15 }


pmopm2CfgChannel14PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 16 }


pmopm2CfgChannel15PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 17 }


pmopm2CfgChannel16PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 18 }


pmopm2CfgChannel17PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 19 }


pmopm2CfgChannel18PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 20 }


pmopm2CfgChannel19PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 21 }


pmopm2CfgChannel20PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 22 }


pmopm2CfgChannel21PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 23 }


pmopm2CfgChannel22PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 24 }


pmopm2CfgChannel23PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 25 }


pmopm2CfgChannel24PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 26 }


pmopm2CfgChannel25PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 27 }


pmopm2CfgChannel26PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 28 }


pmopm2CfgChannel27PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 29 }


pmopm2CfgChannel28PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 30 }


pmopm2CfgChannel29PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 31 }


pmopm2CfgChannel30PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 32 }


pmopm2CfgChannel31PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 33 }


pmopm2CfgChannel32PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 34 }


pmopm2CfgChannel33PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 35 }


pmopm2CfgChannel34PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 36 }


pmopm2CfgChannel35PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 37 }


pmopm2CfgChannel36PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 38 }


pmopm2CfgChannel37PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 39 }


pmopm2CfgChannel38PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 40 }


pmopm2CfgChannel39PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 41 }


pmopm2CfgChannel40PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 42 }


pmopm2CfgChannel41PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 43 }


pmopm2CfgChannel42PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 44 }


pmopm2CfgChannel43PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 45 }


pmopm2CfgChannel44PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 46 }


pmopm2CfgChannel45PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 47 }


pmopm2CfgChannel46PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 48 }


pmopm2CfgChannel47PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 49 }


pmopm2CfgChannel48PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 50 }


pmopm2CfgChannel49PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 51 }


pmopm2CfgChannel50PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 52 }


pmopm2CfgChannel51PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 53 }


pmopm2CfgChannel52PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 54 }


pmopm2CfgChannel53PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 55 }


pmopm2CfgChannel54PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 56 }


pmopm2CfgChannel55PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 57 }


pmopm2CfgChannel56PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 58 }


pmopm2CfgChannel57PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 59 }


pmopm2CfgChannel58PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 60 }


pmopm2CfgChannel59PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 61 }


pmopm2CfgChannel60PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 62 }


pmopm2CfgChannel61PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 63 }


pmopm2CfgChannel62PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 64 }


pmopm2CfgChannel63PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 65 }


pmopm2CfgChannel64PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 66 }


pmopm2CfgChannel65PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 67 }


pmopm2CfgChannel66PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 68 }


pmopm2CfgChannel67PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 69 }


pmopm2CfgChannel68PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 70 }


pmopm2CfgChannel69PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 71 }


pmopm2CfgChannel70PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 72 }


pmopm2CfgChannel71PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 73 }


pmopm2CfgChannel72PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 74 }


pmopm2CfgChannel73PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 75 }


pmopm2CfgChannel74PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 76 }


pmopm2CfgChannel75PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 77 }


pmopm2CfgChannel76PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 78 }


pmopm2CfgChannel77PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 79 }


pmopm2CfgChannel78PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 80 }


pmopm2CfgChannel79PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 81 }


pmopm2CfgChannel80PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 82 }


pmopm2CfgChannel81PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 83 }


pmopm2CfgChannel82PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 84 }


pmopm2CfgChannel83PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 85 }


pmopm2CfgChannel84PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 86 }


pmopm2CfgChannel85PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 87 }


pmopm2CfgChannel86PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 88 }


pmopm2CfgChannel87PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 89 }


pmopm2CfgChannel88PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 90 }


pmopm2CfgChannel89PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 91 }


pmopm2CfgChannel90PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 92 }


pmopm2CfgChannel91PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 93 }


pmopm2CfgChannel92PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 94 }


pmopm2CfgChannel93PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 95 }


pmopm2CfgChannel94PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 96 }


pmopm2CfgChannel95PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 97 }


pmopm2CfgChannel96PwrlowPortn OBJECT-TYPE
	SYNTAX  Unsigned32 (0..65536)
	MAX-ACCESS read-write
	STATUS current
	DESCRIPTION
        "
        Default Settings on Min Power
         :This OID defines the threshold
        to rise a channel power low
        "
	::= { pmopm2CfgClientStartupPwrLowEntry 98 }


--- *****************************************************
---     LEAF for the table NO_VALUE
--- *****************************************************

pmopm2CfgLabelclientTable OBJECT-TYPE
	SYNTAX  SEQUENCE OF Pmopm2CfgLabelclientEntry
	MAX-ACCESS not-accessible
	STATUS current
	DESCRIPTION
        "
        List of  Article
        "
	::= { pmopm2CfgStartup 7 }


pmopm2CfgLabelclientEntry OBJECT-TYPE
	SYNTAX Pmopm2CfgLabelclientEntry
	MAX-ACCESS not-accessible
	STATUS current
	DESCRIPTION
        "
        Row definition for the startup
        table
        "
	INDEX   { pmopm2CfgLabelclientIndex }
	::= { pmopm2CfgLabelclientTable 1 }


Pmopm2CfgLabelclientEntry ::=
	SEQUENCE {
	pmopm2CfgLabelclientIndex
		INTEGER,
	pmopm2CfgLabelclientPortn
		DisplayString
	}


pmopm2CfgLabelclientIndex OBJECT-TYPE
	SYNTAX  INTEGER(0..128)
	MAX-ACCESS  read-only
	STATUS current
	DESCRIPTION
        "
        Index definition for the labelclient
        table
        "
	::= { pmopm2CfgLabelclientEntry 1 }


pmopm2CfgLabelclientPortn OBJECT-TYPE
	SYNTAX  DisplayString( SIZE(1..16))
	MAX-ACCESS read-write
	STATUS current
	DESCRIPTION
        "
        Default settings on the label
         of the Ports :
        "
	::= { pmopm2CfgLabelclientEntry 3 }


--- *****************************************************
---     LEAF for the table NO_VALUE
--- *****************************************************

pmopm2CfgLabellineTable OBJECT-TYPE
	SYNTAX  SEQUENCE OF Pmopm2CfgLabellineEntry
	MAX-ACCESS not-accessible
	STATUS current
	DESCRIPTION
        "
        List of  Article
        "
	::= { pmopm2CfgStartup 8 }


pmopm2CfgLabellineEntry OBJECT-TYPE
	SYNTAX Pmopm2CfgLabellineEntry
	MAX-ACCESS not-accessible
	STATUS current
	DESCRIPTION
        "
        Row definition for the startup
        table
        "
	INDEX   { pmopm2CfgLabellineIndex }
	::= { pmopm2CfgLabellineTable 1 }


Pmopm2CfgLabellineEntry ::=
	SEQUENCE {
	pmopm2CfgLabellineIndex
		INTEGER,
	pmopm2CfgLabellinePortn
		DisplayString
	}


pmopm2CfgLabellineIndex OBJECT-TYPE
	SYNTAX  INTEGER(0..128)
	MAX-ACCESS  read-only
	STATUS current
	DESCRIPTION
        "
        Index definition for the labelline
        table
        "
	::= { pmopm2CfgLabellineEntry 1 }


pmopm2CfgLabellinePortn OBJECT-TYPE
	SYNTAX  DisplayString( SIZE(1..16))
	MAX-ACCESS read-write
	STATUS current
	DESCRIPTION
        "
        Default settings on the label
         of the lines :
        "
	::= { pmopm2CfgLabellineEntry 3 }



pmopm2CfgWriteConfiguration  OBJECT-TYPE
	SYNTAX EkiOnOff
	MAX-ACCESS read-write
	STATUS current
	DESCRIPTION
	"Write configuration to module:This OID
	 writes the complete configuration to the module"
	::= { pmopm2Config 257 }






--- *****************************************************
---     TRAP OBJECTS
--- *****************************************************

pmopm2trapPortNumber OBJECT-TYPE
	SYNTAX INTEGER(1..64)
	MAX-ACCESS read-only
	STATUS current
	DESCRIPTION
	"Last port which generates a trap"
	::= { pmopm2traps 2 }

pmopm2trapLineNumber OBJECT-TYPE
	SYNTAX INTEGER(1..64)
	MAX-ACCESS read-only
	STATUS current
	DESCRIPTION
	"Last Line which generates a trap"
	::= { pmopm2traps 3 }

pmopm2trapBoardNumber OBJECT-TYPE
	SYNTAX INTEGER(1..64)
	MAX-ACCESS read-only
	STATUS current
	DESCRIPTION
	"Last module which generates a trap"
	::= { pmopm2traps 4 }







--- *****************************************************
---     CLIENT TRAPS
--- *****************************************************






--- *****************************************************
---     HW TRAPS
--- *****************************************************

pmopm2PowerTrapUrgentGoesOn NOTIFICATION-TYPE
	OBJECTS {pmopm2AlmDefFuseB, pmopm2AlmDefFuseA , pmopm2trapBoardNumber}
	STATUS current
	--&FILTNAME    "PMOPM Fuse A Fail ON"
	--&ACTIONS     { log, major }
	--&MATCH       { pmopm2AlmDefFuseB "*", pmopm2AlmDefFuseA "on", pmopm2trapBoardNumber "$3"}
	--&MESG        "Power Input A Fail on PMOPM in Slot $3 ($A)"

	--&FILTNAME    "PMOPM Fuse B Fail ON"
	--&ACTIONS     { log, major }
	--&MATCH       { pmopm2AlmDefFuseB "on", pmopm2AlmDefFuseA "*", pmopm2trapBoardNumber "$3"}
	--&MESG        "Power Input B Fail on PMOPM in Slot $3 ($A)"
	DESCRIPTION "Urgent power supply default is activated"
	::= { pmopm2traps 50 }

pmopm2PowerTrapUrgentGoesOff NOTIFICATION-TYPE
	OBJECTS {pmopm2AlmDefFuseB, pmopm2AlmDefFuseA , pmopm2trapBoardNumber}
	STATUS current
	--&FILTNAME    "PMOPM Fuse A&B Fail OFF"
	--&ACTIONS     { log, normal}
	--&CLEARS      { "PMOPM Fuse A Fail ON", "PMOPM Fuse B Fail ON" }
	--&MATCH       { pmopm2AlmDefFuseB "on", pmopm2AlmDefFuseA "on", pmopm2trapBoardNumber "$3"}
	--&MESG        "Power Inputs A and B Present on PMOPM in Slot $3 ($A)"

	DESCRIPTION "Urgent power supply default disappeared"
	::= { pmopm2traps 51 }






END
