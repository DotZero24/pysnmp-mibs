-- *****************************************************************
-- EKINOPS-Pm1004dcp.TXT:  MIB
--
--MIB Part Number:3MI00018AFAE
--MIB Version:03
--
-- Copyright (c) 2016 by Ekinops
-- All rights reserved.
--
-- *****************************************************************

EKINOPS-Pm1004dcp-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

modulePm1004dcp MODULE-IDENTITY
        LAST-UPDATED "201606020000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.net"
        DESCRIPTION
          "MIB for managing Ekinops modules with PM1004DC software"
	REVISION "200911100000Z"
	DESCRIPTION
	  "Initial Version."

	REVISION "200902170000Z"
	DESCRIPTION
	  "Creation"
	REVISION "200902170000Z"
	DESCRIPTION
	  "Inital version"
	REVISION "200904070000Z"
	DESCRIPTION
	  "DCC Storm info suppress"
	REVISION "200909300000Z"
	DESCRIPTION
	  "Add CondType parameters"
	REVISION "201002150000Z"
	DESCRIPTION
	  "Probcause,AlarmType - NMS"
	REVISION "201107250000Z"
	DESCRIPTION
	  "Event fixed"
	REVISION "201207030000Z"
	DESCRIPTION
	  "Minor cosmetic updates"
	REVISION "201304030000Z"
	DESCRIPTION
	  "S1,K1,K2 suppress"
	REVISION "201403270000Z"
	DESCRIPTION
	  "Probcause,AlarmType - NMS completion"
	REVISION "201412220000Z"
	DESCRIPTION
	  "Labels cosmetic updates"
	REVISION "201605190000Z"
	DESCRIPTION
	  "New AlarmType – synthesisAlarm (12)"
	REVISION "201606020000Z"
	DESCRIPTION
	  "Capabilities objects of Table 5"
        ::= { ekinops 37 }



--- *****************************************************
---     LEAF LEVEL 2
--- *****************************************************


pm1004dcpalarms OBJECT IDENTIFIER ::= { modulePm1004dcp 2 }
pm1004dcpAlmOther OBJECT IDENTIFIER ::= { pm1004dcpalarms 1 }
pm1004dcpAlmOtherNurg OBJECT IDENTIFIER ::= { pm1004dcpAlmOther 1 }
pm1004dcpAlmOtherUrg OBJECT IDENTIFIER ::= { pm1004dcpAlmOther 2 }
pm1004dcpAlmOtherCrit OBJECT IDENTIFIER ::= { pm1004dcpAlmOther 3 }

pm1004dcpAlmClient OBJECT IDENTIFIER ::= { pm1004dcpalarms 2 }
pm1004dcpAlmClientNurg OBJECT IDENTIFIER ::= { pm1004dcpAlmClient 1 }
pm1004dcpAlmClientUrg OBJECT IDENTIFIER ::= { pm1004dcpAlmClient 2 }
pm1004dcpAlmClientCrit OBJECT IDENTIFIER ::= { pm1004dcpAlmClient 3 }

pm1004dcpAlmLine OBJECT IDENTIFIER ::= { pm1004dcpalarms 3 }
pm1004dcpAlmLineNurg OBJECT IDENTIFIER ::= { pm1004dcpAlmLine 1 }
pm1004dcpAlmLineUrg OBJECT IDENTIFIER ::= { pm1004dcpAlmLine 2 }
pm1004dcpAlmLineCrit OBJECT IDENTIFIER ::= { pm1004dcpAlmLine 3 }





pm1004dcpmeasures OBJECT IDENTIFIER ::= { modulePm1004dcp 3 }
pm1004dcpMesrOther OBJECT IDENTIFIER ::= { pm1004dcpmeasures 1 }
pm1004dcpMesrClient OBJECT IDENTIFIER ::= { pm1004dcpmeasures 2 }
pm1004dcpMesrLine OBJECT IDENTIFIER ::= { pm1004dcpmeasures 3 }




pm1004dcpcounters OBJECT IDENTIFIER ::= { modulePm1004dcp 4 }
pm1004dcpCntOther OBJECT IDENTIFIER ::= { pm1004dcpcounters 1 }
pm1004dcpCntClient OBJECT IDENTIFIER ::= { pm1004dcpcounters 2 }
pm1004dcpCntLine OBJECT IDENTIFIER ::= { pm1004dcpcounters 3 }


pm1004dcpcontrolsWrite OBJECT IDENTIFIER ::= { modulePm1004dcp 6 }
pm1004dcpCtrlOther OBJECT IDENTIFIER ::= { pm1004dcpcontrolsWrite 1 }
pm1004dcpCtrlClient OBJECT IDENTIFIER ::= { pm1004dcpcontrolsWrite 2 }
pm1004dcpCtrlLine OBJECT IDENTIFIER ::= { pm1004dcpcontrolsWrite 3 }

pm1004dcpri OBJECT IDENTIFIER ::= { modulePm1004dcp 7 }
pm1004dcpriTable OBJECT IDENTIFIER ::= { pm1004dcpri 1 }

pm1004dcpdownload OBJECT IDENTIFIER ::= { modulePm1004dcp 8 }
pm1004dcpDwlOther OBJECT IDENTIFIER ::= { pm1004dcpdownload 1 }
pm1004dcpDwlClient OBJECT IDENTIFIER ::= { pm1004dcpdownload 2 }
pm1004dcpDwlLine OBJECT IDENTIFIER ::= { pm1004dcpdownload 3 }


pm1004dcpConfig OBJECT IDENTIFIER ::= { modulePm1004dcp 9 }

pm1004dcptraps OBJECT IDENTIFIER ::= { modulePm1004dcp 10 }

pm1004dcpMonitoring OBJECT IDENTIFIER ::= { modulePm1004dcp 11}

pm1004dcpMonOther OBJECT IDENTIFIER ::= { pm1004dcpMonitoring 1 }
pm1004dcpMonSync OBJECT IDENTIFIER ::= { pm1004dcpMonOther 1 }
pm1004dcpMonTimeStamp OBJECT IDENTIFIER ::= { pm1004dcpMonOther 2 }

pm1004dcpMonClient OBJECT IDENTIFIER ::= { pm1004dcpMonitoring 2 }
pm1004dcpMonClientPerformance OBJECT IDENTIFIER ::= { pm1004dcpMonClient 1 }
pm1004dcpMonClientTraceIdentifier OBJECT IDENTIFIER ::= { pm1004dcpMonClient 2 }

pm1004dcpMonLine OBJECT IDENTIFIER ::= { pm1004dcpMonitoring 3 }
pm1004dcpMonLinePerformance OBJECT IDENTIFIER ::= { pm1004dcpMonLine 1 }
pm1004dcpMonLineTraceIdentifier OBJECT IDENTIFIER ::= { pm1004dcpMonLine 2 }


--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Pm1004dcpModeTimeSlot ::= TEXTUAL-CONVENTION
    STATUS      current
    DESCRIPTION "different mode for time slot"
    SYNTAX INTEGER {
		dualPassThrough(1),
		addDropTsA(2),
		addDropTsB(4),
		splitSelectTsA(8),
		splitSelectTsB(16),
		splitSelectTsATsB(32)
           }

Pm1004dcpModeAddDropA ::= TEXTUAL-CONVENTION
    STATUS      current
    DESCRIPTION "different mode for client A"
    SYNTAX INTEGER {
		passThroughA(1),
		addDropTsA(2),
		splitSelectTsA(4)
           }

Pm1004dcpModeAddDrop ::= TEXTUAL-CONVENTION
    STATUS      current
    DESCRIPTION "different mode for client B"
    SYNTAX INTEGER {
		dualPassThrough(1),
		addDropTsA(2),
		addDropTsB(4),
		splitSelectTsA(8),
		splitSelectTsB(16),
		splitSelectTsATsB(32)
           }


Pm1004dcpProtectionTimeSlot ::= TEXTUAL-CONVENTION
    STATUS      current
    DESCRIPTION "protection for control"
    SYNTAX INTEGER {
		auto(0),
		manualX1Line1(257),
		manualX2Line2(513)
           }

Pm1004dcpProtectionStartUp ::= TEXTUAL-CONVENTION
    STATUS      current
    DESCRIPTION "protection for startup"
    SYNTAX INTEGER {
		auto(2),
		manualX2Line2(0),
		manualX1Line1(1)
           }


Pm1004dcpDccMode ::= TEXTUAL-CONVENTION
    STATUS      current
    DESCRIPTION "Mode for DCC"
    SYNTAX INTEGER {
		dccNo(0),
		dcctermLine1(1),
		dcctermLine2(2),
		dcctermLines12(3),
		dccmaster(4),
		dccslaveLine12(7)
           }


Pm1004dcpOtxMode ::= TEXTUAL-CONVENTION
    STATUS      current
    DESCRIPTION "Different modes on OTX-TLH on line ports"
    SYNTAX INTEGER {
		otx80mode(1),
		otx60mode(2),
		otxadjustmode(4)
           }

Pm1004dcpOtxGrid ::= TEXTUAL-CONVENTION
    STATUS      current
    DESCRIPTION "Different grids on OTX-TLH on line ports"
    SYNTAX INTEGER {
		otxgrid200(200),
		otxgrid100(100),
		otxgrid50(50)
           }

Pm1004dcpAdjustValue ::= TEXTUAL-CONVENTION
    STATUS      current
    DESCRIPTION "Different values in Adjust mode on OTX-TLH on line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pm1004dcpOtxChannel ::= TEXTUAL-CONVENTION
    STATUS      current
    DESCRIPTION "Channel selection on OTX-TLH on line ports"
    SYNTAX INTEGER


--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm1004dcpRinvReloadInventory OBJECT-TYPE
  SYNTAX EkiOnOff
  MAX-ACCESS read-write
  STATUS current
  DESCRIPTION
        "Reload the inventory: This OID triggers an
         inventory reload."
  ::= { pm1004dcpri 2 }

pm1004dcpRinvHwPlatform OBJECT-TYPE
  SYNTAX DisplayString
  MAX-ACCESS read-only
  STATUS current
  DESCRIPTION
        "HW platform description: This OID contains the
         description of the Hardware platform."
  ::= { pm1004dcpri 3 }

pm1004dcpRinvModulePlatform OBJECT-TYPE
  SYNTAX DisplayString
  MAX-ACCESS read-only
  STATUS current
  DESCRIPTION
        "Module platform description: This OID contains the
         description of the Module."
  ::= { pm1004dcpri 4 }

pm1004dcpRinvSwPlatform OBJECT-TYPE
  SYNTAX DisplayString
  MAX-ACCESS read-only
  STATUS current
  DESCRIPTION
        "SW platform description: This OID contains the
         description of the Software platform."
  ::= { pm1004dcpri 5 }

pm1004dcpRinvGwPlatform OBJECT-TYPE
  SYNTAX DisplayString
  MAX-ACCESS read-only
  STATUS current
  DESCRIPTION
        "GW platform desciption: This OID contains the
         description of the Gateware platform."
  ::= { pm1004dcpri 6 }


pm1004dcpRinvSfpTable OBJECT-TYPE
      SYNTAX  SEQUENCE OF Pm1004dcpRinvSfpEntry
      MAX-ACCESS  not-accessible
      STATUS  current
      DESCRIPTION
              "List of the SFPs on the selected module"
      ::= { pm1004dcpriTable 1 }

pm1004dcpRinvSfpEntry OBJECT-TYPE
        SYNTAX  Pm1004dcpRinvSfpEntry
        MAX-ACCESS  not-accessible
        STATUS  current
        DESCRIPTION
              "Row definition for the SFP table"
        INDEX   { pm1004dcpRinvSfpIndex }
        ::= { pm1004dcpRinvSfpTable 1 }



Pm1004dcpRinvSfpEntry::=
        SEQUENCE {
          pm1004dcpRinvSfpIndex
              Integer32,
          pm1004dcpRinvsfp
              DisplayString
        }


    pm1004dcpRinvSfpIndex OBJECT-TYPE
        SYNTAX  Integer32(1..16)
        MAX-ACCESS  read-only
        STATUS  current
        DESCRIPTION
              "Index for SFP table"
        ::= { pm1004dcpRinvSfpEntry 1 }


    pm1004dcpRinvsfp OBJECT-TYPE
        SYNTAX  DisplayString
        MAX-ACCESS  read-only
        STATUS  current
        DESCRIPTION
              "Inventory for the SFP: This OID contains the inventory for the SFP"
        ::= { pm1004dcpRinvSfpEntry 2 }




pm1004dcpRinvLineTable OBJECT-TYPE
      SYNTAX  SEQUENCE OF Pm1004dcpRinvLineEntry
      MAX-ACCESS  not-accessible
      STATUS  current
      DESCRIPTION
              "List of the XFPs on the selected module"
      ::= { pm1004dcpriTable 2 }

pm1004dcpRinvLineEntry OBJECT-TYPE
        SYNTAX  Pm1004dcpRinvLineEntry
        MAX-ACCESS  not-accessible
        STATUS  current
        DESCRIPTION
              "Row definition for the XFP table"
        INDEX   { pm1004dcpRinvLineIndex }
        ::= { pm1004dcpRinvLineTable 1 }



Pm1004dcpRinvLineEntry::=
        SEQUENCE {
          pm1004dcpRinvLineIndex
              Integer32,
          pm1004dcpRinvxfpLine
              DisplayString
        }


    pm1004dcpRinvLineIndex OBJECT-TYPE
        SYNTAX  Integer32(1..16)
        MAX-ACCESS  read-only
        STATUS  current
        DESCRIPTION
              "Index for XFP table"
        ::= { pm1004dcpRinvLineEntry 1 }


    pm1004dcpRinvxfpLine OBJECT-TYPE
        SYNTAX  DisplayString
        MAX-ACCESS  read-only
        STATUS  current
        DESCRIPTION
              "Inventory for the XFP: This OID contains the inventory for the XFP"
        ::= { pm1004dcpRinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm1004dcpAlmsynthAlm0 OBJECT IDENTIFIER ::= { pm1004dcpAlmOtherCrit 0 }




pm1004dcpAlmDefFuseB OBJECT-TYPE
	  SYNTAX EkiOnOff
	  MAX-ACCESS read-only
	  STATUS current
	  DESCRIPTION
        "
        Fuse B Fail :This OID indicates
        that the fuse of the power input
        B is in fail condition  <Help>
          Status of the Fuse B <Condtype>
        DEF_FUSE_B <Probcause> powerProblem
        (36) <Alarmtype> equipmentAlarm
        (5) <Polarity> (2)
        "
	  ::= { pm1004dcpAlmsynthAlm0 16 }



pm1004dcpAlmDefFuseA OBJECT-TYPE
	  SYNTAX EkiOnOff
	  MAX-ACCESS read-only
	  STATUS current
	  DESCRIPTION
        "
        Fuse A Fail :This OID indicates
        that the fuse of the power input
        A is in fail condition  <Help>
          Status of the Fuse A <Condtype>
        DEF_FUSE_A <Probcause> powerProblem
        (36) <Alarmtype> equipmentAlarm
        (5) <Polarity> (2)
        "
	  ::= { pm1004dcpAlmsynthAlm0 15 }



pm1004dcpAlmModGlobFail OBJECT-TYPE
	  SYNTAX EkiOnOff
	  MAX-ACCESS read-only
	  STATUS current
	  DESCRIPTION
        "
        Module Failure :This OID is set
        on detection of a failure originating
        from the PM <Condtype> MOD_GLOB_FAIL
        <Probcause> equipmentMalfunction
        (16) <Alarmtype> synthesisAlarm
        (12)  <Polarity> (2)
        "
	  ::= { pm1004dcpAlmsynthAlm0 9 }



--- *****************************************************
---     LEAF for the synthAlm2 article
--- *****************************************************
pm1004dcpAlmsynthAlm2 OBJECT IDENTIFIER ::= { pm1004dcpAlmOtherNurg 2 }




pm1004dcpAlmMaintenanceOn OBJECT-TYPE
	  SYNTAX EkiOnOff
	  MAX-ACCESS read-only
	  STATUS current
	  DESCRIPTION
        "
        Maintenance Mode :This OID indicates
        that the PM is in maintenance mode.
         <Help>  This alarm indicates that
        the maintenance mode is enabled
        on the PM <Condtype> MAINTENANCE_ON
        <Probcause> other (1) <Alarmtype>
        other (1) <Polarity> (2)
        "
	  ::= { pm1004dcpAlmsynthAlm2 5 }



pm1004dcpAlmCorrelatOff OBJECT-TYPE
	  SYNTAX EkiOnOff
	  MAX-ACCESS read-only
	  STATUS current
	  DESCRIPTION
        "
        Not Used :This OID, when set,
         indicates that alarm correlation
        is not being performed. <Condtype>
        CORRELAT_OFF <Probcause> other
         (1) <Alarmtype> other (1) <Polarity>
        (2)
        "
	  ::= { pm1004dcpAlmsynthAlm2 4 }



pm1004dcpAlmConfTableLoad OBJECT-TYPE
	  SYNTAX EkiOnOff
	  MAX-ACCESS read-only
	  STATUS current
	  DESCRIPTION
        "
        PM Configuration Load :This OID
         is at 1 during the loading of
         configuration tables in the modules
        RAM. <Condtype> CONF_TABLE_LOAD
        <Probcause> other (1) <Alarmtype>
        other (1) <Polarity> (2)
        "
	  ::= { pm1004dcpAlmsynthAlm2 3 }



pm1004dcpAlmInvUpload OBJECT-TYPE
	  SYNTAX EkiOnOff
	  MAX-ACCESS read-only
	  STATUS current
	  DESCRIPTION
        "
        Inventory Upload :This OID is
         at 1 during the uploading of PM
        inventory information. <Condtype>
        INV_UPLOAD <Probcause> other (1)
        <Alarmtype> other (1) <Polarity>
        (2)
        "
	  ::= { pm1004dcpAlmsynthAlm2 2 }



pm1004dcpAlmConfTableSave OBJECT-TYPE
	  SYNTAX EkiOnOff
	  MAX-ACCESS read-only
	  STATUS current
	  DESCRIPTION
        "
        PM Configuration Save :This OID
        is at 1 during the saving of a
         new configuration table in the
        module Flash memory. <Condtype>
        CONF_TABLE_SAVE <Probcause> other
        (1) <Alarmtype> other (1) <Polarity>
        (2)
        "
	  ::= { pm1004dcpAlmsynthAlm2 1 }



--- *********************************************************
---     TABLE for the pm1004dcpAlmsynthAlmLine articles
--- *********************************************************

pm1004dcpAlmsynthAlmLineTable OBJECT-TYPE
	SYNTAX  SEQUENCE OF Pm1004dcpAlmsynthAlmLineEntry
	MAX-ACCESS not-accessible
	STATUS current
	DESCRIPTION
        "
        List of pm1004dcpAlmsynthAlmLine
        Article
        "
	::= { pm1004dcpAlmLineCrit 7 }


pm1004dcpAlmsynthAlmLineEntry OBJECT-TYPE
	SYNTAX Pm1004dcpAlmsynthAlmLineEntry
	MAX-ACCESS not-accessible
	STATUS current
	DESCRIPTION
        "
        Row definition for the pm1004dcpAlmsynthAlmLine
        table
        "
	INDEX   { pm1004dcpAlmsynthAlmLineIndex }
	::= { pm1004dcpAlmsynthAlmLineTable 1 }


Pm1004dcpAlmsynthAlmLineEntry ::=
	SEQUENCE {
	pm1004dcpAlmsynthAlmLineIndex
		INTEGER,
	pm1004dcpAlmLineFailPortn
		EkiOnOff,
	pm1004dcpAlmLineDdmAlmPortn
		EkiOnOff,
	pm1004dcpAlmLineDdmWarningPortn
		EkiOnOff,
	pm1004dcpAlmUpRdiInsPortn
		EkiOnOff,
	pm1004dcpAlmLineLocalOosPortn
		EkiOnOff,
	pm1004dcpAlmXfpTxOffPortn
		EkiOnOff,
	pm1004dcpAlmLineHwFailPortn
		EkiOnOff,
	pm1004dcpAlmXfpInitNotComplPortn
		EkiOnOff,
	pm1004dcpAlmXfpAbsentPortn
		EkiOnOff
	}


pm1004dcpAlmsynthAlmLineIndex OBJECT-TYPE
	SYNTAX  INTEGER(0..128)
	MAX-ACCESS  read-only
	STATUS current
	DESCRIPTION
        "
        Index definition for the pm1004dcpAlmsynthAlmLine
        table
        "
	::= { pm1004dcpAlmsynthAlmLineEntry 1 }


pm1004dcpAlmLineFailPortn OBJECT-TYPE
	SYNTAX  EkiOnOff
	MAX-ACCESS read-only
	STATUS current
	DESCRIPTION
        "
        Line Port Failure :This OID indicates
        a failure on the line port <Condtype>
        LINE_FAIL <Probcause> equipmentMalfunction
        (16) <Alarmtype> synthesisAlarm
        (12)  <Polarity> (2)
        "
	::= { pm1004dcpAlmsynthAlmLineEntry 13 }


pm1004dcpAlmLineDdmAlmPortn OBJECT-TYPE
	SYNTAX  EkiOnOff
	MAX-ACCESS read-only
	STATUS current
	DESCRIPTION
        "
        Alarm On Line Optical Module DDM
        :This OID indicates an alarm is
        present coming out of Line optical
        interface DDM  <Help>  This alarm
        indicates if a DDM Warning has
         been detected on the line transceiver
        <Condtype> LINE_DDM_ALM <Probcause>
        equipmentMalfunction (16) <Alarmtype>
        synthesisAlarm (12)  <Polarity>
        (2)
        "
	::= { pm1004dcpAlmsynthAlmLineEntry 11 }


pm1004dcpAlmLineDdmWarningPortn OBJECT-TYPE
	SYNTAX  EkiOnOff
	MAX-ACCESS read-only
	STATUS current
	DESCRIPTION
        "
        Warning On Line Optical Module
        DDM :This OID indicates a warning
        is present coming out of Line optical
        interface DDM  <Help>  This status
        indicates if a MS-RDI/L-RDI is
         currently inserted on the line
        interface. <Condtype> LINE_DDM_WARNING
        <Probcause> equipmentMalfunction
        (16) <Alarmtype> synthesisAlarm
        (12)  <Polarity> (2)
        "
	::= { pm1004dcpAlmsynthAlmLineEntry 10 }


pm1004dcpAlmUpRdiInsPortn OBJECT-TYPE
	SYNTAX  EkiOnOff
	MAX-ACCESS read-only
	STATUS current
	DESCRIPTION
        "
        SM-BDI Inserted On Line :This
         OID indicates an upstream SM-BDI
        has been inserted in the outgoing
        G709 signal.   <Help>  This status
        indicates if a SM-BDI is currently
        inserted on the line interface.
        <Condtype> UP_RDI_INS <Probcause>
        informationalStatus(1000) <Alarmtype>
        other (1) <Polarity> (2)
        "
	::= { pm1004dcpAlmsynthAlmLineEntry 9 }


pm1004dcpAlmLineLocalOosPortn OBJECT-TYPE
	SYNTAX  EkiOnOff
	MAX-ACCESS read-only
	STATUS current
	DESCRIPTION
        "
        Line Port In Service :This OID
        indicates that the Line port is
        In Service (1) of Out or Service
        (2)  <Help>  This status indicates
        if the line port is in service
         <Condtype> LINE_LOCAL_OOS <Probcause>
        informationalStatus(1000) <Alarmtype>
        other (1) <Polarity> (2)
        "
	::= { pm1004dcpAlmsynthAlmLineEntry 7 }


pm1004dcpAlmXfpTxOffPortn OBJECT-TYPE
	SYNTAX  EkiOnOff
	MAX-ACCESS read-only
	STATUS current
	DESCRIPTION
        "
        Line Optical Module Laser Shutdown
        :This OID indicates the line optical
        output power is on  <Help>  This
        status indicates if the line transceiver
        laser is ON or OFF <Condtype> XFP_TX_OFF
        <Probcause> other (1) <Alarmtype>
        equipmentAlarm (5) <Polarity> (2)
        "
	::= { pm1004dcpAlmsynthAlmLineEntry 6 }


pm1004dcpAlmLineHwFailPortn OBJECT-TYPE
	SYNTAX  EkiOnOff
	MAX-ACCESS read-only
	STATUS current
	DESCRIPTION
        "
        Line Port HW Failure :This OID
        indicates a failure on line port,
        most probably caused by a HW issue
        <Condtype> LINE_HW_FAIL <Probcause>
        equipmentMalfunction (16) <Alarmtype>
        synthesisAlarm (12)  <Polarity>
        (2)
        "
	::= { pm1004dcpAlmsynthAlmLineEntry 5 }


pm1004dcpAlmXfpInitNotComplPortn OBJECT-TYPE
	SYNTAX  EkiOnOff
	MAX-ACCESS read-only
	STATUS current
	DESCRIPTION
        "
        Line Optical Module Ready :This
        OID indicates that the optical
         interface (XFP or OTX) is not
         operational.  <Help>  This status
        indicates if the line transceiver
        has been correctly initialized
         <Condtype> XFP_INIT_NOT_COMPL
         <Probcause> equipmentMalfunction
        (16) <Alarmtype> equipmentAlarm
        (5) <Polarity> (2) <Event> ObjectCDINV
        "
	::= { pm1004dcpAlmsynthAlmLineEntry 3 }


pm1004dcpAlmXfpAbsentPortn OBJECT-TYPE
	SYNTAX  EkiOnOff
	MAX-ACCESS read-only
	STATUS current
	DESCRIPTION
        "
        Line Optical Module Absent :This
        OID indicates that the line optical
        interface (XFP or OTX) is not plugged
        in.  <Help>  This alarm indicates
        if the line transceiver is present.
        <Condtype> XFP_ABSENT <Probcause>
        inputOutputDeviceError (24) <Alarmtype>
        equipmentAlarm (5) <Polarity> (2)
        <Event> ObjectCDINV
        "
	::= { pm1004dcpAlmsynthAlmLineEntry 2 }


--- *********************************************************
---     TABLE for the pm1004dcpAlmsynthAlmPort articles
--- *********************************************************

pm1004dcpAlmsynthAlmPortTable OBJECT-TYPE
	SYNTAX  SEQUENCE OF Pm1004dcpAlmsynthAlmPortEntry
	MAX-ACCESS not-accessible
	STATUS current
	DESCRIPTION
        "
        List of pm1004dcpAlmsynthAlmPort
        Article
        "
	::= { pm1004dcpAlmClientCrit 8 }


pm1004dcpAlmsynthAlmPortEntry OBJECT-TYPE
	SYNTAX Pm1004dcpAlmsynthAlmPortEntry
	MAX-ACCESS not-accessible
	STATUS current
	DESCRIPTION
        "
        Row definition for the pm1004dcpAlmsynthAlmPort
        table
        "
	INDEX   { pm1004dcpAlmsynthAlmPortIndex }
	::= { pm1004dcpAlmsynthAlmPortTable 1 }


Pm1004dcpAlmsynthAlmPortEntry ::=
	SEQUENCE {
	pm1004dcpAlmsynthAlmPortIndex
		INTEGER,
	pm1004dcpAlmUpCsfPortn
		EkiOnOff,
	pm1004dcpAlmClientActivePortn
		EkiOnOff,
	pm1004dcpAlmFailAccPortn
		EkiOnOff,
	pm1004dcpAlmSfpDdmAlmPortn
		EkiOnOff,
	pm1004dcpAlmSfpDdmWarningPortn
		EkiOnOff,
	pm1004dcpAlmDwCaisPortn
		EkiOnOff,
	pm1004dcpAlmClientRemoteOosPortn
		EkiOnOff,
	pm1004dcpAlmClientLocalOosPortn
		EkiOnOff,
	pm1004dcpAlmDwLsdPortn
		EkiOnOff,
	pm1004dcpAlmHwFailAccPortn
		EkiOnOff,
	pm1004dcpAlmDdmAbsentPortn
		EkiOnOff,
	pm1004dcpAlmSfpAbsentPortn
		EkiOnOff
	}


pm1004dcpAlmsynthAlmPortIndex OBJECT-TYPE
	SYNTAX  INTEGER(0..128)
	MAX-ACCESS  read-only
	STATUS current
	DESCRIPTION
        "
        Index definition for the pm1004dcpAlmsynthAlmPort
        table
        "
	::= { pm1004dcpAlmsynthAlmPortEntry 1 }


pm1004dcpAlmUpCsfPortn OBJECT-TYPE
	SYNTAX  EkiOnOff
	MAX-ACCESS read-only
	STATUS current
	DESCRIPTION
        "
        Client Signal Fail Inserted :This
        OID indicates a CSF has been inserted
        in the upstream client port.  <Help>
         This status indicates if a Client
        Signal Fail is currently inserted
        on the line signal for this client
        port <Condtype> UP_CSF_1 <Probcause>
        other (1) <Alarmtype> other (1)
        <Polarity> (2)
        "
	::= { pm1004dcpAlmsynthAlmPortEntry 17 }


pm1004dcpAlmClientActivePortn OBJECT-TYPE
	SYNTAX  EkiOnOff
	MAX-ACCESS read-only
	STATUS current
	DESCRIPTION
        "
        Client Sink (Line1 Or Line2) :This
        bit indicates the Client #n is
         active on receive side  <Help>
         This status indicates whether
         the Client is extracted from Line
        1 or Line 2. <Condtype> CLIENT_ACTIVE
        <Probcause> other (1) <Alarmtype>
        other (1) <Polarity> (2)
        "
	::= { pm1004dcpAlmsynthAlmPortEntry 16 }


pm1004dcpAlmFailAccPortn OBJECT-TYPE
	SYNTAX  EkiOnOff
	MAX-ACCESS read-only
	STATUS current
	DESCRIPTION
        "
        Client Access Fail :This OID indicates
        a failure on the Client port <Condtype>
        FAIL_ACC_1 <Probcause> equipmentMalfunction
        (16) <Alarmtype> synthesisAlarm
        (12)  <Polarity> (2)
        "
	::= { pm1004dcpAlmsynthAlmPortEntry 13 }


pm1004dcpAlmSfpDdmAlmPortn OBJECT-TYPE
	SYNTAX  EkiOnOff
	MAX-ACCESS read-only
	STATUS current
	DESCRIPTION
        "
        Alarm On Client SFP DDM :This
         OID indicates an alarm is being
        received from the Client SFP DDM
         <Help>  This alarm indicates if
        a DDM Alarm has been detected on
        the client transceiver <Condtype>
        SFP_DDM_ALM_1 <Probcause> equipmentMalfunction
        (16) <Alarmtype> synthesisAlarm
        (12)  <Polarity> (2)
        "
	::= { pm1004dcpAlmsynthAlmPortEntry 11 }


pm1004dcpAlmSfpDdmWarningPortn OBJECT-TYPE
	SYNTAX  EkiOnOff
	MAX-ACCESS read-only
	STATUS current
	DESCRIPTION
        "
        Warning On Client SFP DDM :This
        OID indicates a warning is being
        received from the Client SFP DDM
         <Help>  This alarm indicates if
        a DDM Warning has been detected
        on the client transceiver <Condtype>
        SFP_DDM_WARNING_1 <Probcause> equipmentMalfunction
        (16) <Alarmtype> synthesisAlarm
        (12)  <Polarity> (2)
        "
	::= { pm1004dcpAlmsynthAlmPortEntry 10 }


pm1004dcpAlmDwCaisPortn OBJECT-TYPE
	SYNTAX  EkiOnOff
	MAX-ACCESS read-only
	STATUS current
	DESCRIPTION
        "
        Client AIS Inserted :This OID
         indicates a CAIS has been inserted
        on the output client port.  <Help>
         This status indicates if a Client
        Alarm Indication Signal is currently
        inserted on the client interface
        <Condtype> DW_CAIS_1 <Probcause>
        informationalStatus(1000) <Alarmtype>
        other (1) <Polarity> (2)
        "
	::= { pm1004dcpAlmsynthAlmPortEntry 9 }


pm1004dcpAlmClientRemoteOosPortn OBJECT-TYPE
	SYNTAX  EkiOnOff
	MAX-ACCESS read-only
	STATUS current
	DESCRIPTION
        "
        Remote Client Port In Service
         :This OID indicates that the remote
        Client port is In Service (1) or
        Out of Service (2)  <Help>  This
        status indicates if the remote
         client port is in service <Condtype>
        CLIENT_REMOTE_OOS <Probcause> informationalStatus(1000)
        <Alarmtype> other (1) <Polarity>
        (2)
        "
	::= { pm1004dcpAlmsynthAlmPortEntry 8 }


pm1004dcpAlmClientLocalOosPortn OBJECT-TYPE
	SYNTAX  EkiOnOff
	MAX-ACCESS read-only
	STATUS current
	DESCRIPTION
        "
        Local Client Port In Service :This
        OID indicates that the local Client
        port is In Service (1) or Out of
        Service (2)  <Help>  This status
        indicates if the local client port
        is in service <Condtype> CLIENT_LOCAL_OOS
        <Probcause> informationalStatus(1000)
        <Alarmtype> other (1) <Polarity>
        (2)
        "
	::= { pm1004dcpAlmsynthAlmPortEntry 7 }


pm1004dcpAlmDwLsdPortn OBJECT-TYPE
	SYNTAX  EkiOnOff
	MAX-ACCESS read-only
	STATUS current
	DESCRIPTION
        "
        Client SFP Laser Shutdown :This
        OID indicates the Client SFP transmitter
        output is ON.   <Help>  This status
        indicates if the client transceiver
        laser is ON or OFF <Condtype> DW_LSD_1
        <Probcause> other (1) <Alarmtype>
        equipmentAlarm (5) <Polarity> (2)
        "
	::= { pm1004dcpAlmsynthAlmPortEntry 6 }


pm1004dcpAlmHwFailAccPortn OBJECT-TYPE
	SYNTAX  EkiOnOff
	MAX-ACCESS read-only
	STATUS current
	DESCRIPTION
        "
        Client HW Fail :This OID indicates
        a failure on client port, most
         probably caused by a HW issue.
        <Condtype> HW_FAIL_ACC_1 <Probcause>
        equipmentMalfunction (16) <Alarmtype>
        synthesisAlarm (12)  <Polarity>
        (2)
        "
	::= { pm1004dcpAlmsynthAlmPortEntry 5 }


pm1004dcpAlmDdmAbsentPortn OBJECT-TYPE
	SYNTAX  EkiOnOff
	MAX-ACCESS read-only
	STATUS current
	DESCRIPTION
        "
        DDM Supported On Client SFP :This
        OID indicates that the Client SFP
        module supports the Digital Diagnostic
        Monitoring function  <Help>  This
        status indicates if the client
         transceiver includes the DDM feature
        <Condtype> DDM_ABSENT_1 <Probcause>
        informationalStatus(1000) <Alarmtype>
        other (1) <Polarity> (2)
        "
	::= { pm1004dcpAlmsynthAlmPortEntry 3 }


pm1004dcpAlmSfpAbsentPortn OBJECT-TYPE
	SYNTAX  EkiOnOff
	MAX-ACCESS read-only
	STATUS current
	DESCRIPTION
        "
        Client SFP Absent :This OID indicates
        that the SFP module is not present
        in the client port.  <Help>  This
        alarm indicates if the client transceiver
        is present. <Condtype> SFP_ABSENT_1
        <Probcause> inputOutputDeviceError
        (24) <Alarmtype> equipmentAlarm
        (5) <Polarity> (2) <Event> ObjectCDINV
        "
	::= { pm1004dcpAlmsynthAlmPortEntry 2 }


--- *********************************************************
---     TABLE for the pm1004dcpAlmaccessioAlm articles
--- *********************************************************

pm1004dcpAlmaccessioAlmTable OBJECT-TYPE
	SYNTAX  SEQUENCE OF Pm1004dcpAlmaccessioAlmEntry
	MAX-ACCESS not-accessible
	STATUS current
	DESCRIPTION
        "
        List of pm1004dcpAlmaccessioAlm
        Article
        "
	::= { pm1004dcpAlmClientCrit 16 }


pm1004dcpAlmaccessioAlmEntry OBJECT-TYPE
	SYNTAX Pm1004dcpAlmaccessioAlmEntry
	MAX-ACCESS not-accessible
	STATUS current
	DESCRIPTION
        "
        Row definition for the pm1004dcpAlmaccessioAlm
        table
        "
	INDEX   { pm1004dcpAlmaccessioAlmIndex }
	::= { pm1004dcpAlmaccessioAlmTable 1 }


Pm1004dcpAlmaccessioAlmEntry ::=
	SEQUENCE {
	pm1004dcpAlmaccessioAlmIndex
		INTEGER,
	pm1004dcpAlmUpLosPortn
		EkiOnOff,
	pm1004dcpAlmDwLasFailPortn
		EkiOnOff
	}


pm1004dcpAlmaccessioAlmIndex OBJECT-TYPE
	SYNTAX  INTEGER(0..128)
	MAX-ACCESS  read-only
	STATUS current
	DESCRIPTION
        "
        Index definition for the pm1004dcpAlmaccessioAlm
        table
        "
	::= { pm1004dcpAlmaccessioAlmEntry 1 }


pm1004dcpAlmUpLosPortn OBJECT-TYPE
	SYNTAX  EkiOnOff
	MAX-ACCESS read-only
	STATUS current
	DESCRIPTION
        "
        Client Input Loss Of Signal :This
        OID indicates that no signal is
        present on the SFP of the client
        port  <Help>  This alarm indicates
        if an optical signal is detected
        on the client transceiver input
        <Condtype> UP_LOS_1 <Probcause>
        receiveFailure (41) <Alarmtype>
        physicalViolation (9) <Polarity>
        (2)
        "
	::= { pm1004dcpAlmaccessioAlmEntry 5 }


pm1004dcpAlmDwLasFailPortn OBJECT-TYPE
	SYNTAX  EkiOnOff
	MAX-ACCESS read-only
	STATUS current
	DESCRIPTION
        "
        Client SFP Tx Failed :This OID
        indicates that the transmitter
         fails for the SFP plugged into
        the client port (this alarm reports
        the transmitter failure alarm generated
        by the SFPs)  <Help>  This alarm
        indicates if the laser of the client
        transceiver is in fail condition
        <Condtype> DW_LAS_FAIL_1 <Probcause>
        transmitterFailure (56) <Alarmtype>
        equipmentAlarm (5) <Polarity> (2)
        "
	::= { pm1004dcpAlmaccessioAlmEntry 2 }


--- *********************************************************
---     TABLE for the pm1004dcpAlmsfpAlmDdm articles
--- *********************************************************

pm1004dcpAlmsfpAlmDdmTable OBJECT-TYPE
	SYNTAX  SEQUENCE OF Pm1004dcpAlmsfpAlmDdmEntry
	MAX-ACCESS not-accessible
	STATUS current
	DESCRIPTION
        "
        List of pm1004dcpAlmsfpAlmDdm
         Article
        "
	::= { pm1004dcpAlmClientUrg 32 }


pm1004dcpAlmsfpAlmDdmEntry OBJECT-TYPE
	SYNTAX Pm1004dcpAlmsfpAlmDdmEntry
	MAX-ACCESS not-accessible
	STATUS current
	DESCRIPTION
        "
        Row definition for the pm1004dcpAlmsfpAlmDdm
        table
        "
	INDEX   { pm1004dcpAlmsfpAlmDdmIndex }
	::= { pm1004dcpAlmsfpAlmDdmTable 1 }


Pm1004dcpAlmsfpAlmDdmEntry ::=
	SEQUENCE {
	pm1004dcpAlmsfpAlmDdmIndex
		INTEGER,
	pm1004dcpAlmRxPwrHighAlaPortn
		EkiOnOff,
	pm1004dcpAlmRxPwrLowAlaPortn
		EkiOnOff,
	pm1004dcpAlmTempHighAlaPortn
		EkiOnOff,
	pm1004dcpAlmTempLowAlaPortn
		EkiOnOff,
	pm1004dcpAlmVccHighAlaPortn
		EkiOnOff,
	pm1004dcpAlmVccLowAlaPortn
		EkiOnOff,
	pm1004dcpAlmTxBiasHighAlaPortn
		EkiOnOff,
	pm1004dcpAlmTxBiasLowAlaPortn
		EkiOnOff,
	pm1004dcpAlmTxPwrHighAlaPortn
		EkiOnOff,
	pm1004dcpAlmTxPwrLowAlaPortn
		EkiOnOff
	}


pm1004dcpAlmsfpAlmDdmIndex OBJECT-TYPE
	SYNTAX  INTEGER(0..128)
	MAX-ACCESS  read-only
	STATUS current
	DESCRIPTION
        "
        Index definition for the pm1004dcpAlmsfpAlmDdm
        table
        "
	::= { pm1004dcpAlmsfpAlmDdmEntry 1 }


pm1004dcpAlmRxPwrHighAlaPortn OBJECT-TYPE
	SYNTAX  EkiOnOff
	MAX-ACCESS read-only
	STATUS current
	DESCRIPTION
        "
        Client SFP Rx Power High :Alarm
        indicating that the SFP input power
        of port is higher than the threshold
        value written in the SFP EEPROM
        <Condtype> RX_PWR_HIGH_ALA_1 <Probcause>
        receiveFailure (41) <Alarmtype>
        equipmentAlarm (5) <Polarity> (2)
        "
	::= { pm1004dcpAlmsfpAlmDdmEntry 17 }


pm1004dcpAlmRxPwrLowAlaPortn OBJECT-TYPE
	SYNTAX  EkiOnOff
	MAX-ACCESS read-only
	STATUS current
	DESCRIPTION
        "
        Client SFP Rx Power Low :Alarm
        indicating that the SFP input power
        of port is lower than the threshold
        value written in the SFP EEPROM
        <Condtype> RX_PWR_LOW_ALA_1 <Probcause>
        receiveFailure (41) <Alarmtype>
        equipmentAlarm (5) <Polarity> (2)
        "
	::= { pm1004dcpAlmsfpAlmDdmEntry 16 }


pm1004dcpAlmTempHighAlaPortn OBJECT-TYPE
	SYNTAX  EkiOnOff
	MAX-ACCESS read-only
	STATUS current
	DESCRIPTION
        "
        Client SFP Temp High :Alarm indicating
        that the SFP temperature of port
        is higher than the threshold value
        written in the SFP EEPROM <Condtype>
        TEMP_HIGH_ALA_1 <Probcause> temperatureUnacceptable
        (51) <Alarmtype> equipmentAlarm
        (5) <Polarity> (2)
        "
	::= { pm1004dcpAlmsfpAlmDdmEntry 9 }


pm1004dcpAlmTempLowAlaPortn OBJECT-TYPE
	SYNTAX  EkiOnOff
	MAX-ACCESS read-only
	STATUS current
	DESCRIPTION
        "
        Client SFP Temp Low :Alarm indicating
        that the SFP temperature of port
        is lower than the threshold value
        written in the SFP EEPROM <Condtype>
        TEMP_LOW_ALA_1 <Probcause> temperatureUnacceptable
        (51) <Alarmtype> equipmentAlarm
        (5) <Polarity> (2)
        "
	::= { pm1004dcpAlmsfpAlmDdmEntry 8 }


pm1004dcpAlmVccHighAlaPortn OBJECT-TYPE
	SYNTAX  EkiOnOff
	MAX-ACCESS read-only
	STATUS current
	DESCRIPTION
        "
        Client SFP Power Supply High :Alarm
        indicating that the SFP power supply
        of port is higher than the threshold
        value written in the SFP EEPROM
         <Condtype> VCC_HIGH_ALA_1 <Probcause>
        powerProblem (36) <Alarmtype> equipmentAlarm
        (5) <Polarity> (2)
        "
	::= { pm1004dcpAlmsfpAlmDdmEntry 7 }


pm1004dcpAlmVccLowAlaPortn OBJECT-TYPE
	SYNTAX  EkiOnOff
	MAX-ACCESS read-only
	STATUS current
	DESCRIPTION
        "
        Client SFP Power Supply Low :Alarm
        indicating that the SFP power supply
        of port is lower than the threshold
        value written in the SFP EEPROM
         <Condtype> VCC_LOW_ALA_1 <Probcause>
        powerProblem (36) <Alarmtype> equipmentAlarm
        (5) <Polarity> (2)
        "
	::= { pm1004dcpAlmsfpAlmDdmEntry 6 }


pm1004dcpAlmTxBiasHighAlaPortn OBJECT-TYPE
	SYNTAX  EkiOnOff
	MAX-ACCESS read-only
	STATUS current
	DESCRIPTION
        "
        Client SFP Bias High :Alarm indicating
        that the SFP laser bias current
        of port is higher than the threshold
        value written in the SFP EEPROM
        <Condtype> TX_BIAS_HIGH_ALA_1 <Probcause>
        transmitterFailure (56) <Alarmtype>
        equipmentAlarm (5) <Polarity> (2)
        "
	::= { pm1004dcpAlmsfpAlmDdmEntry 5 }


pm1004dcpAlmTxBiasLowAlaPortn OBJECT-TYPE
	SYNTAX  EkiOnOff
	MAX-ACCESS read-only
	STATUS current
	DESCRIPTION
        "
        Client SFP Bias Low :Alarm indicating
        that the SFP laser bias current
        of port is lower than the threshold
        value written in the SFP EEPROM
        <Condtype> TX_BIAS_LOW_ALA_1 <Probcause>
        transmitterFailure (56) <Alarmtype>
        equipmentAlarm (5) <Polarity> (2)
        "
	::= { pm1004dcpAlmsfpAlmDdmEntry 4 }


pm1004dcpAlmTxPwrHighAlaPortn OBJECT-TYPE
	SYNTAX  EkiOnOff
	MAX-ACCESS read-only
	STATUS current
	DESCRIPTION
        "
        Client SFP Tx Power High :Alarm
        indicating that the SFP output
         power of port is higher than the
        threshold value written in the
         SFP EEPROM <Condtype> TX_PWR_HIGH_ALA_1
        <Probcause> transmitterFailure
         (56) <Alarmtype> equipmentAlarm
        (5) <Polarity> (2)
        "
	::= { pm1004dcpAlmsfpAlmDdmEntry 3 }


pm1004dcpAlmTxPwrLowAlaPortn OBJECT-TYPE
	SYNTAX  EkiOnOff
	MAX-ACCESS read-only
	STATUS current
	DESCRIPTION
        "
        Client SFP Tx Power Low :Alarm
        indicating that the SFP output
         power of port is lower than the
        threshold value written in the
         SFP EEPROM <Condtype> TX_PWR_LOW_ALA_1
        <Probcause> transmitterFailure
         (56) <Alarmtype> equipmentAlarm
        (5) <Polarity> (2)
        "
	::= { pm1004dcpAlmsfpAlmDdmEntry 2 }


--- *********************************************************
---     TABLE for the pm1004dcpAlmsfpWarnDdm articles
--- *********************************************************

pm1004dcpAlmsfpWarnDdmTable OBJECT-TYPE
	SYNTAX  SEQUENCE OF Pm1004dcpAlmsfpWarnDdmEntry
	MAX-ACCESS not-accessible
	STATUS current
	DESCRIPTION
        "
        List of pm1004dcpAlmsfpWarnDdm
        Article
        "
	::= { pm1004dcpAlmClientNurg 48 }


pm1004dcpAlmsfpWarnDdmEntry OBJECT-TYPE
	SYNTAX Pm1004dcpAlmsfpWarnDdmEntry
	MAX-ACCESS not-accessible
	STATUS current
	DESCRIPTION
        "
        Row definition for the pm1004dcpAlmsfpWarnDdm
        table
        "
	INDEX   { pm1004dcpAlmsfpWarnDdmIndex }
	::= { pm1004dcpAlmsfpWarnDdmTable 1 }


Pm1004dcpAlmsfpWarnDdmEntry ::=
	SEQUENCE {
	pm1004dcpAlmsfpWarnDdmIndex
		INTEGER,
	pm1004dcpAlmRxPwrHighWngPortn
		EkiOnOff,
	pm1004dcpAlmRxPwrLowWngPortn
		EkiOnOff,
	pm1004dcpAlmTempHighWngPortn
		EkiOnOff,
	pm1004dcpAlmTempLowWngPortn
		EkiOnOff,
	pm1004dcpAlmVccHighWngPortn
		EkiOnOff,
	pm1004dcpAlmVccLowWngPortn
		EkiOnOff,
	pm1004dcpAlmTxBiasHighWngPortn
		EkiOnOff,
	pm1004dcpAlmTxBiasLowWngPortn
		EkiOnOff,
	pm1004dcpAlmTxPwrHighWngPortn
		EkiOnOff,
	pm1004dcpAlmTxPwLowWngPortn
		EkiOnOff
	}


pm1004dcpAlmsfpWarnDdmIndex OBJECT-TYPE
	SYNTAX  INTEGER(0..128)
	MAX-ACCESS  read-only
	STATUS current
	DESCRIPTION
        "
        Index definition for the pm1004dcpAlmsfpWarnDdm
        table
        "
	::= { pm1004dcpAlmsfpWarnDdmEntry 1 }


pm1004dcpAlmRxPwrHighWngPortn OBJECT-TYPE
	SYNTAX  EkiOnOff
	MAX-ACCESS read-only
	STATUS current
	DESCRIPTION
        "
        Client SFP Rx Power High Warning
        :Warning indicating that the SFP
        input power of port is higher than
        the threshold value written in
         the SFP EEPROM <Condtype> RX_PWR_HIGH_WNG_1
        <Probcause> receiveFailure (41)
        <Alarmtype> equipmentAlarm (5)
         <Polarity> (2)
        "
	::= { pm1004dcpAlmsfpWarnDdmEntry 17 }


pm1004dcpAlmRxPwrLowWngPortn OBJECT-TYPE
	SYNTAX  EkiOnOff
	MAX-ACCESS read-only
	STATUS current
	DESCRIPTION
        "
        Client SFP Rx Power Low Warning
        :Warning indicating that the SFP
        input power of port is lower than
        the threshold value written in
         the SFP EEPROM <Condtype> RX_PWR_LOW_WNG_1
        <Probcause> receiveFailure (41)
        <Alarmtype> equipmentAlarm (5)
         <Polarity> (2)
        "
	::= { pm1004dcpAlmsfpWarnDdmEntry 16 }


pm1004dcpAlmTempHighWngPortn OBJECT-TYPE
	SYNTAX  EkiOnOff
	MAX-ACCESS read-only
	STATUS current
	DESCRIPTION
        "
        Client SFP Temp High Warning :Warning
        indicating that the SFP temperature
        of port is higher than the threshold
        value written in the SFP EEPROM
        <Condtype> TEMP_HIGH_WNG_1 <Probcause>
        temperatureUnacceptable (51) <Alarmtype>
        equipmentAlarm (5) <Polarity> (2)
        "
	::= { pm1004dcpAlmsfpWarnDdmEntry 9 }


pm1004dcpAlmTempLowWngPortn OBJECT-TYPE
	SYNTAX  EkiOnOff
	MAX-ACCESS read-only
	STATUS current
	DESCRIPTION
        "
        Client SFP Temp Low Warning :Warning
        indicating that the SFP temperature
        of port is lower than the threshold
        value written in the SFP EEPROM
        <Condtype> TEMP_LOW_WNG_1 <Probcause>
        temperatureUnacceptable (51) <Alarmtype>
        equipmentAlarm (5) <Polarity> (2)
        "
	::= { pm1004dcpAlmsfpWarnDdmEntry 8 }


pm1004dcpAlmVccHighWngPortn OBJECT-TYPE
	SYNTAX  EkiOnOff
	MAX-ACCESS read-only
	STATUS current
	DESCRIPTION
        "
        Client SFP Power Supply High Warning
        :Warning indicating that the SFP
        power supply of port is higher
         than the threshold value written
        in the SFP EEPROM  <Condtype> VCC_HIGH_WNG_1
        <Probcause> powerProblem (36) <Alarmtype>
        equipmentAlarm (5) <Polarity> (2)
        "
	::= { pm1004dcpAlmsfpWarnDdmEntry 7 }


pm1004dcpAlmVccLowWngPortn OBJECT-TYPE
	SYNTAX  EkiOnOff
	MAX-ACCESS read-only
	STATUS current
	DESCRIPTION
        "
        Client SFP Power Supply Low Warning
        :Warning indicating that the SFP
        power supply of port is lower than
        the threshold value written in
         the SFP EEPROM  <Condtype> VCC_LOW_WNG_1
        <Probcause> powerProblem (36) <Alarmtype>
        equipmentAlarm (5) <Polarity> (2)
        "
	::= { pm1004dcpAlmsfpWarnDdmEntry 6 }


pm1004dcpAlmTxBiasHighWngPortn OBJECT-TYPE
	SYNTAX  EkiOnOff
	MAX-ACCESS read-only
	STATUS current
	DESCRIPTION
        "
        Client SFP Bias High Warning :Warning
        indicating that the SFP laser bias
        current of port is higher than
         the threshold value written in
        the SFP EEPROM <Condtype> TX_BIAS_HIGH_WNG_1
        <Probcause> transmitterFailure
         (56) <Alarmtype> equipmentAlarm
        (5) <Polarity> (2)
        "
	::= { pm1004dcpAlmsfpWarnDdmEntry 5 }


pm1004dcpAlmTxBiasLowWngPortn OBJECT-TYPE
	SYNTAX  EkiOnOff
	MAX-ACCESS read-only
	STATUS current
	DESCRIPTION
        "
        Client SFP Bias Low Warning :Warning
        indicating that the SFP laser bias
        current of port is lower than the
        threshold value written in the
         SFP EEPROM <Condtype> TX_BIAS_LOW_WNG_1
        <Probcause> transmitterFailure
         (56) <Alarmtype> equipmentAlarm
        (5) <Polarity> (2)
        "
	::= { pm1004dcpAlmsfpWarnDdmEntry 4 }


pm1004dcpAlmTxPwrHighWngPortn OBJECT-TYPE
	SYNTAX  EkiOnOff
	MAX-ACCESS read-only
	STATUS current
	DESCRIPTION
        "
        Client SFP Tx Power High Warning
        :Warning indicating that the SFP
        output power of port is higher
         than the threshold value written
        in the SFP EEPROM <Condtype> TX_PWR_HIGH_WNG_1
        <Probcause> transmitterFailure
         (56) <Alarmtype> equipmentAlarm
        (5) <Polarity> (2)
        "
	::= { pm1004dcpAlmsfpWarnDdmEntry 3 }


pm1004dcpAlmTxPwLowWngPortn OBJECT-TYPE
	SYNTAX  EkiOnOff
	MAX-ACCESS read-only
	STATUS current
	DESCRIPTION
        "
        Client SFP Tx Power Low Warning
        :Warning indicating that the SFP
        output power of port is lower than
        the threshold value written in
         the SFP EEPROM <Condtype> TX_PW_LOW_WNG_1
        <Probcause> transmitterFailure
         (56) <Alarmtype> equipmentAlarm
        (5) <Polarity> (2)
        "
	::= { pm1004dcpAlmsfpWarnDdmEntry 2 }


--- *********************************************************
---     TABLE for the pm1004dcpAlmmapperDeAlm articles
--- *********************************************************

pm1004dcpAlmmapperDeAlmTable OBJECT-TYPE
	SYNTAX  SEQUENCE OF Pm1004dcpAlmmapperDeAlmEntry
	MAX-ACCESS not-accessible
	STATUS current
	DESCRIPTION
        "
        List of pm1004dcpAlmmapperDeAlm
        Article
        "
	::= { pm1004dcpAlmClientCrit 72 }


pm1004dcpAlmmapperDeAlmEntry OBJECT-TYPE
	SYNTAX Pm1004dcpAlmmapperDeAlmEntry
	MAX-ACCESS not-accessible
	STATUS current
	DESCRIPTION
        "
        Row definition for the pm1004dcpAlmmapperDeAlm
        table
        "
	INDEX   { pm1004dcpAlmmapperDeAlmIndex }
	::= { pm1004dcpAlmmapperDeAlmTable 1 }


Pm1004dcpAlmmapperDeAlmEntry ::=
	SEQUENCE {
	pm1004dcpAlmmapperDeAlmIndex
		INTEGER,
	pm1004dcpAlmDwBufferOvlPortn
		EkiOnOff,
	pm1004dcpAlmDwCsfDetPortn
		EkiOnOff,
	pm1004dcpAlmUpBufferOvlPortn
		EkiOnOff,
	pm1004dcpAlmUpAccOosPortn
		EkiOnOff
	}


pm1004dcpAlmmapperDeAlmIndex OBJECT-TYPE
	SYNTAX  INTEGER(0..128)
	MAX-ACCESS  read-only
	STATUS current
	DESCRIPTION
        "
        Index definition for the pm1004dcpAlmmapperDeAlm
        table
        "
	::= { pm1004dcpAlmmapperDeAlmEntry 1 }


pm1004dcpAlmDwBufferOvlPortn OBJECT-TYPE
	SYNTAX  EkiOnOff
	MAX-ACCESS read-only
	STATUS current
	DESCRIPTION
        "
        Client Downstream Buffer Overload
        :This OID indicates that the de-mapper
        buffer for client port is in overload.
         <Help>  This alarm indicates if
        there is a downstream FIFO overload
        for this client port <Condtype>
        DW_BUFFER_OVL_1 <Probcause> equipmentMalfunction
        (16) <Alarmtype> equipmentAlarm
        (5) <Polarity> (2)
        "
	::= { pm1004dcpAlmmapperDeAlmEntry 15 }


pm1004dcpAlmDwCsfDetPortn OBJECT-TYPE
	SYNTAX  EkiOnOff
	MAX-ACCESS read-only
	STATUS current
	DESCRIPTION
        "
        Client Signal Fail Detected :This
        OID indicates that a CSF has been
        detected on client port in the
         downstream direction   <Help>
          This alarm indicates if a Client
        Signal Fail has been detected in
        the incoming line frame for this
        client port <Condtype> DW_CSF_DET_1
        <Probcause> receiveFailure (41)
        <Alarmtype> equipmentAlarm (5)
         <Polarity> (2)
        "
	::= { pm1004dcpAlmmapperDeAlmEntry 12 }


pm1004dcpAlmUpBufferOvlPortn OBJECT-TYPE
	SYNTAX  EkiOnOff
	MAX-ACCESS read-only
	STATUS current
	DESCRIPTION
        "
        Client Upstream Buffer Overload
        :This OID indicates that the rate
        adaptation buffer for client port
        is in overload.  <Help>  This alarm
        indicates if there is a upstream
        FIFO overload for this client port
        <Condtype> UP_BUFFER_OVL_1 <Probcause>
        receiveFailure (41) <Alarmtype>
        integrityViolation (7) <Polarity>
        (2)
        "
	::= { pm1004dcpAlmmapperDeAlmEntry 11 }


pm1004dcpAlmUpAccOosPortn OBJECT-TYPE
	SYNTAX  EkiOnOff
	MAX-ACCESS read-only
	STATUS current
	DESCRIPTION
        "
        Client Loss Of Frame :This OID
        indicates the upstream client input
        port is in Loss of Frame condition
         <Help>  This alarm indicates if
        there is a Loss of Frame is detected
        on the client input signal <Condtype>
        UP_ACC_OOS_1 <Probcause> receiveFailure
        (41) <Alarmtype> integrityViolation
        (7) <Polarity> (2)
        "
	::= { pm1004dcpAlmmapperDeAlmEntry 2 }


--- *********************************************************
---     TABLE for the pm1004dcpAlmk1K2Client articles
--- *********************************************************

pm1004dcpAlmk1K2ClientTable OBJECT-TYPE
	SYNTAX  SEQUENCE OF Pm1004dcpAlmk1K2ClientEntry
	MAX-ACCESS not-accessible
	STATUS current
	DESCRIPTION
        "
        List of pm1004dcpAlmk1K2Client
        Article
        "
	::= { pm1004dcpAlmClientNurg 96 }


pm1004dcpAlmk1K2ClientEntry OBJECT-TYPE
	SYNTAX Pm1004dcpAlmk1K2ClientEntry
	MAX-ACCESS not-accessible
	STATUS current
	DESCRIPTION
        "
        Row definition for the pm1004dcpAlmk1K2Client
        table
        "
	INDEX   { pm1004dcpAlmk1K2ClientIndex }
	::= { pm1004dcpAlmk1K2ClientTable 1 }


Pm1004dcpAlmk1K2ClientEntry ::=
	SEQUENCE {
	pm1004dcpAlmk1K2ClientIndex
		INTEGER,
	pm1004dcpAlmk1K2ClientPortn
		INTEGER
	}


pm1004dcpAlmk1K2ClientIndex OBJECT-TYPE
	SYNTAX  INTEGER(0..128)
	MAX-ACCESS  read-only
	STATUS current
	DESCRIPTION
        "
        Index definition for the pm1004dcpAlmk1K2Client
        table
        "
	::= { pm1004dcpAlmk1K2ClientEntry 1 }


pm1004dcpAlmk1K2ClientPortn OBJECT-TYPE
	SYNTAX  INTEGER (0..65535)
	MAX-ACCESS read-only
	STATUS current
	DESCRIPTION
        "
        Client K1-K2 Extracted Value :This
        OID gives the value of K1 (LSB)
        and K2 (MSB) extracted from the
        overhead of the received OC-48c/STM-16c
        signal <Condtype> CLIENT_1_K1_8
        <Probcause> other (1) <Alarmtype>
        other (1) <Polarity> (2)
        "
	::= { pm1004dcpAlmk1K2ClientEntry 2 }


--- *********************************************************
---     TABLE for the pm1004dcpAlmaccessioSdhAlarm articles
--- *********************************************************

pm1004dcpAlmaccessioSdhAlarmTable OBJECT-TYPE
	SYNTAX  SEQUENCE OF Pm1004dcpAlmaccessioSdhAlarmEntry
	MAX-ACCESS not-accessible
	STATUS current
	DESCRIPTION
        "
        List of pm1004dcpAlmaccessioSdhAlarm
        Article
        "
	::= { pm1004dcpAlmClientCrit 104 }


pm1004dcpAlmaccessioSdhAlarmEntry OBJECT-TYPE
	SYNTAX Pm1004dcpAlmaccessioSdhAlarmEntry
	MAX-ACCESS not-accessible
	STATUS current
	DESCRIPTION
        "
        Row definition for the pm1004dcpAlmaccessioSdhAlarm
        table
        "
	INDEX   { pm1004dcpAlmaccessioSdhAlarmIndex }
	::= { pm1004dcpAlmaccessioSdhAlarmTable 1 }


Pm1004dcpAlmaccessioSdhAlarmEntry ::=
	SEQUENCE {
	pm1004dcpAlmaccessioSdhAlarmIndex
		INTEGER,
	pm1004dcpAlmClientOofPortn
		EkiOnOff,
	pm1004dcpAlmClientRdiDetPortn
		EkiOnOff,
	pm1004dcpAlmClientAisDetPortn
		EkiOnOff,
	pm1004dcpAlmTxLossOfLockPortn
		EkiOnOff,
	pm1004dcpAlmRxLossOfLockPortn
		EkiOnOff,
	pm1004dcpAlmFifoErrPortn
		EkiOnOff
	}


pm1004dcpAlmaccessioSdhAlarmIndex OBJECT-TYPE
	SYNTAX  INTEGER(0..128)
	MAX-ACCESS  read-only
	STATUS current
	DESCRIPTION
        "
        Index definition for the pm1004dcpAlmaccessioSdhAlarm
        table
        "
	::= { pm1004dcpAlmaccessioSdhAlarmEntry 1 }


pm1004dcpAlmClientOofPortn OBJECT-TYPE
	SYNTAX  EkiOnOff
	MAX-ACCESS read-only
	STATUS current
	DESCRIPTION
        "
        Client Out Of Frame :This OID
         indicates that an Out Of Frame
        condition has been detected on
         the OC-48/STM-16 client input
         stream   <Help>  This alarm indicates
        if there is a Out of Frame is detected
        on the client input signal <Condtype>
        CLIENT_OOF_1 <Probcause> receiveFailure
        (41) <Alarmtype> integrityViolation
        (7) <Polarity> (2)
        "
	::= { pm1004dcpAlmaccessioSdhAlarmEntry 8 }


pm1004dcpAlmClientRdiDetPortn OBJECT-TYPE
	SYNTAX  EkiOnOff
	MAX-ACCESS read-only
	STATUS current
	DESCRIPTION
        "
        Client MS-RDI :This OID indicates
        that a MS-RDI has been detected
        on the client input stream  <Help>
         This alarm indicates if there
         is a MS-RDI/L-RDI is detected
         on the client input signal <Condtype>
        CLIENT_RDI_DET_1 <Probcause> remoteNodeTransmissionError
        (43) <Alarmtype> other (1) <Polarity>
        (2)
        "
	::= { pm1004dcpAlmaccessioSdhAlarmEntry 7 }


pm1004dcpAlmClientAisDetPortn OBJECT-TYPE
	SYNTAX  EkiOnOff
	MAX-ACCESS read-only
	STATUS current
	DESCRIPTION
        "
        Client MS-AIS :This OID indicates
        that a MS-AIS has been detected
        on the client input stream  <Help>
         This alarm indicates if there
         is a MS-AIS/L-AIS is detected
         on the client input signal <Condtype>
        CLIENT_AIS_DET_1 <Probcause> receiveFailure
        (41) <Alarmtype> operationalViolation
        (8) <Polarity> (2)
        "
	::= { pm1004dcpAlmaccessioSdhAlarmEntry 6 }


pm1004dcpAlmTxLossOfLockPortn OBJECT-TYPE
	SYNTAX  EkiOnOff
	MAX-ACCESS read-only
	STATUS current
	DESCRIPTION
        "
        Client Tx Clock Lock Error :This
        OID indicates that the transmit
        clock of the client transceiver
        is not locke <Condtype> TX_LOSS_OF_LOCK_1
        <Probcause> transmitterFailure
         (56) <Alarmtype> equipmentAlarm
        (5) <Polarity> (2)
        "
	::= { pm1004dcpAlmaccessioSdhAlarmEntry 5 }


pm1004dcpAlmRxLossOfLockPortn OBJECT-TYPE
	SYNTAX  EkiOnOff
	MAX-ACCESS read-only
	STATUS current
	DESCRIPTION
        "
        Client Rx Clock Lock Error :This
        OID indicates the recovered receive
        clock of the client transceiver
        is not locked <Condtype> RX_LOSS_OF_LOCK_1
        <Probcause> receiveFailure (41)
        <Alarmtype> equipmentAlarm (5)
         <Polarity> (2)
        "
	::= { pm1004dcpAlmaccessioSdhAlarmEntry 4 }


pm1004dcpAlmFifoErrPortn OBJECT-TYPE
	SYNTAX  EkiOnOff
	MAX-ACCESS read-only
	STATUS current
	DESCRIPTION
        "
        Client Transceiver Fifo Error
         :This OID indicates that an error
        has been detected in the FIFO of
        the client transceiver <Condtype>
        FIFO_ERR_1 <Probcause> transmitterFailure
        (56) <Alarmtype> equipmentAlarm
        (5) <Polarity> (2)
        "
	::= { pm1004dcpAlmaccessioSdhAlarmEntry 3 }


--- *********************************************************
---     TABLE for the pm1004dcpAlmj0Alarm articles
--- *********************************************************

pm1004dcpAlmj0AlarmTable OBJECT-TYPE
	SYNTAX  SEQUENCE OF Pm1004dcpAlmj0AlarmEntry
	MAX-ACCESS not-accessible
	STATUS current
	DESCRIPTION
        "
        List of pm1004dcpAlmj0Alarm Article
        "
	::= { pm1004dcpMonClientTraceIdentifier 2112 }


pm1004dcpAlmj0AlarmEntry OBJECT-TYPE
	SYNTAX Pm1004dcpAlmj0AlarmEntry
	MAX-ACCESS not-accessible
	STATUS current
	DESCRIPTION
        "
        Row definition for the pm1004dcpAlmj0Alarm
        table
        "
	INDEX   { pm1004dcpAlmj0AlarmIndex }
	::= { pm1004dcpAlmj0AlarmTable 1 }


Pm1004dcpAlmj0AlarmEntry ::=
	SEQUENCE {
	pm1004dcpAlmj0AlarmIndex
		INTEGER,
	pm1004dcpAlmCrc7ErrorPortn
		EkiOnOff,
	pm1004dcpAlmJ0TiiAlarmPortn
		EkiOnOff,
	pm1004dcpAlmJ0TimAlarmPortn
		EkiOnOff
	}


pm1004dcpAlmj0AlarmIndex OBJECT-TYPE
	SYNTAX  INTEGER(0..128)
	MAX-ACCESS  read-only
	STATUS current
	DESCRIPTION
        "
        Index definition for the pm1004dcpAlmj0Alarm
        table
        "
	::= { pm1004dcpAlmj0AlarmEntry 1 }


pm1004dcpAlmCrc7ErrorPortn OBJECT-TYPE
	SYNTAX  EkiOnOff
	MAX-ACCESS read-only
	STATUS current
	DESCRIPTION
        "
        CRC Error On Trace Identifier
         :This OID indicates that a CRC
        error has been detected in the
         stable Trace Identifier on the
        client input stream <Condtype>
         CRC7_ERROR_1 <Probcause> other
        (1) <Alarmtype> other (1) <Polarity>
        (2)
        "
	::= { pm1004dcpAlmj0AlarmEntry 4 }


pm1004dcpAlmJ0TiiAlarmPortn OBJECT-TYPE
	SYNTAX  EkiOnOff
	MAX-ACCESS read-only
	STATUS current
	DESCRIPTION
        "
        Trace Identifier Unstable :This
        OID indicates the Trace Identifier
        is unstable on the client input
        stream <Condtype> J0_TII_ALARM_1
        <Probcause> other (1) <Alarmtype>
        other (1) <Polarity> (2)
        "
	::= { pm1004dcpAlmj0AlarmEntry 3 }


pm1004dcpAlmJ0TimAlarmPortn OBJECT-TYPE
	SYNTAX  EkiOnOff
	MAX-ACCESS read-only
	STATUS current
	DESCRIPTION
        "
        Trace Identifier Mismatch :This
        OID indicates a Trace Identifier
        Mismatch has been detected on the
        client input stream <Condtype>
         J0_TIM_ALARM_1 <Probcause> other
        (1) <Alarmtype> other (1) <Polarity>
        (2)
        "
	::= { pm1004dcpAlmj0AlarmEntry 2 }


--- *********************************************************
---     TABLE for the pm1004dcpAlmdfrmAlm articles
--- *********************************************************

pm1004dcpAlmdfrmAlmTable OBJECT-TYPE
	SYNTAX  SEQUENCE OF Pm1004dcpAlmdfrmAlmEntry
	MAX-ACCESS not-accessible
	STATUS current
	DESCRIPTION
        "
        List of pm1004dcpAlmdfrmAlm Article
        "
	::= { pm1004dcpAlmLineCrit 128 }


pm1004dcpAlmdfrmAlmEntry OBJECT-TYPE
	SYNTAX Pm1004dcpAlmdfrmAlmEntry
	MAX-ACCESS not-accessible
	STATUS current
	DESCRIPTION
        "
        Row definition for the pm1004dcpAlmdfrmAlm
        table
        "
	INDEX   { pm1004dcpAlmdfrmAlmIndex }
	::= { pm1004dcpAlmdfrmAlmTable 1 }


Pm1004dcpAlmdfrmAlmEntry ::=
	SEQUENCE {
	pm1004dcpAlmdfrmAlmIndex
		INTEGER,
	pm1004dcpAlmDwLofPortn
		EkiOnOff,
	pm1004dcpAlmDwOofPortn
		EkiOnOff,
	pm1004dcpAlmDwRdiDetPortn
		EkiOnOff,
	pm1004dcpAlmDwAisDetPortn
		EkiOnOff
	}


pm1004dcpAlmdfrmAlmIndex OBJECT-TYPE
	SYNTAX  INTEGER(0..128)
	MAX-ACCESS  read-only
	STATUS current
	DESCRIPTION
        "
        Index definition for the pm1004dcpAlmdfrmAlm
        table
        "
	::= { pm1004dcpAlmdfrmAlmEntry 1 }


pm1004dcpAlmDwLofPortn OBJECT-TYPE
	SYNTAX  EkiOnOff
	MAX-ACCESS read-only
	STATUS current
	DESCRIPTION
        "
        Line Loss Of Frame :This OID indicates
        that a Loss Of Frame has been detected
        on G709 input signal  <Help>  This
        alarm indicates if there is a G,709
        Loss of Frame is detected on the
        line input signal <Condtype> DW_LOF_1
        <Probcause> receiveFailure (41)
        <Alarmtype> integrityViolation
         (7) <Polarity> (2)
        "
	::= { pm1004dcpAlmdfrmAlmEntry 5 }


pm1004dcpAlmDwOofPortn OBJECT-TYPE
	SYNTAX  EkiOnOff
	MAX-ACCESS read-only
	STATUS current
	DESCRIPTION
        "
        Line Out Of Frame :This OID indicates
        that an Out Of Frame has been detected
        on G709 input signal  <Help>  This
        alarm indicates if there is a G,709
        Out of Frame is detected on the
        line input signal <Condtype> DW_OOF_1
        <Probcause> receiveFailure (41)
        <Alarmtype> integrityViolation
         (7) <Polarity> (2)
        "
	::= { pm1004dcpAlmdfrmAlmEntry 4 }


pm1004dcpAlmDwRdiDetPortn OBJECT-TYPE
	SYNTAX  EkiOnOff
	MAX-ACCESS read-only
	STATUS current
	DESCRIPTION
        "
        OTU2 SM-BDI Detected On Line Input
        :This OID indicates that an SM-BDI
        has been detected on G709 input
        signal  <Help>  This alarm indicates
        if there is a SM-BDI is detected
        on the line input signal <Condtype>
        DW_RDI_DET_1 <Probcause> remoteNodeTransmissionError
        (43) <Alarmtype> other (1) <Polarity>
        (2)
        "
	::= { pm1004dcpAlmdfrmAlmEntry 3 }


pm1004dcpAlmDwAisDetPortn OBJECT-TYPE
	SYNTAX  EkiOnOff
	MAX-ACCESS read-only
	STATUS current
	DESCRIPTION
        "
        ODU2 AIS Detected On Line Input
        :This OID indicates that an ODU2-AIS
        has been detected on G709 input
        signal  <Help>  This alarm indicates
        if there is a ODU2 AIS is detected
        on the line input signal <Condtype>
        DW_AIS_DET_1 <Probcause> receiveFailure
        (41) <Alarmtype> operationalViolation
        (8) <Polarity> (2)
        "
	::= { pm1004dcpAlmdfrmAlmEntry 2 }


--- *********************************************************
---     TABLE for the pm1004dcpAlmdfrmBer articles
--- *********************************************************

pm1004dcpAlmdfrmBerTable OBJECT-TYPE
	SYNTAX  SEQUENCE OF Pm1004dcpAlmdfrmBerEntry
	MAX-ACCESS not-accessible
	STATUS current
	DESCRIPTION
        "
        List of pm1004dcpAlmdfrmBer Article
        "
	::= { pm1004dcpAlmLineUrg 129 }


pm1004dcpAlmdfrmBerEntry OBJECT-TYPE
	SYNTAX Pm1004dcpAlmdfrmBerEntry
	MAX-ACCESS not-accessible
	STATUS current
	DESCRIPTION
        "
        Row definition for the pm1004dcpAlmdfrmBer
        table
        "
	INDEX   { pm1004dcpAlmdfrmBerIndex }
	::= { pm1004dcpAlmdfrmBerTable 1 }


Pm1004dcpAlmdfrmBerEntry ::=
	SEQUENCE {
	pm1004dcpAlmdfrmBerIndex
		INTEGER,
	pm1004dcpAlmLineDegradePortn
		EkiOnOff,
	pm1004dcpAlmLineSignalFailPortn
		EkiOnOff,
	pm1004dcpAlmLineSignalDegradePortn
		EkiOnOff
	}


pm1004dcpAlmdfrmBerIndex OBJECT-TYPE
	SYNTAX  INTEGER(0..128)
	MAX-ACCESS  read-only
	STATUS current
	DESCRIPTION
        "
        Index definition for the pm1004dcpAlmdfrmBer
        table
        "
	::= { pm1004dcpAlmdfrmBerEntry 1 }


pm1004dcpAlmLineDegradePortn OBJECT-TYPE
	SYNTAX  EkiOnOff
	MAX-ACCESS read-only
	STATUS current
	DESCRIPTION
        "
        Fixed Line Signal Degrade :This
        OID indicates that the line input
        signal is DEGRADE. The assetion
        hysteresis is fixed to 10-8 (assertion)
        and 10-9 (de-assertion) <Condtype>
        LINE_DEGRADE_1 <Probcause> degradedSignal
        (13) <Alarmtype> qualityOfServiceAlarm
        (3) <Polarity> (2)
        "
	::= { pm1004dcpAlmdfrmBerEntry 6 }


pm1004dcpAlmLineSignalFailPortn OBJECT-TYPE
	SYNTAX  EkiOnOff
	MAX-ACCESS read-only
	STATUS current
	DESCRIPTION
        "
        Custom Line Signal Fail :This
         OID indicates that the line input
        signal is FAIL. The assertion hysteresis
        can be customized by the host <Condtype>
        LINE_SIGNAL_FAIL_1 <Probcause>
         receiveFailure (41) <Alarmtype>
        integrityViolation (7) <Polarity>
        (2)
        "
	::= { pm1004dcpAlmdfrmBerEntry 3 }


pm1004dcpAlmLineSignalDegradePortn OBJECT-TYPE
	SYNTAX  EkiOnOff
	MAX-ACCESS read-only
	STATUS current
	DESCRIPTION
        "
        Custom Line Signal Degrade :This
        OID indicates that the line input
        signal is DEGRADE. The assertion
        hysteresis can customized by the
        host <Condtype> LINE_SIGNAL_DEGRADE_1
        <Probcause> degradedSignal (13)
        <Alarmtype> qualityOfServiceAlarm
        (3) <Polarity> (2)
        "
	::= { pm1004dcpAlmdfrmBerEntry 2 }


--- *********************************************************
---     TABLE for the pm1004dcpAlmlineSyncAlarms articles
--- *********************************************************

pm1004dcpAlmlineSyncAlarmsTable OBJECT-TYPE
	SYNTAX  SEQUENCE OF Pm1004dcpAlmlineSyncAlarmsEntry
	MAX-ACCESS not-accessible
	STATUS current
	DESCRIPTION
        "
        List of pm1004dcpAlmlineSyncAlarms
        Article
        "
	::= { pm1004dcpAlmLineCrit 133 }


pm1004dcpAlmlineSyncAlarmsEntry OBJECT-TYPE
	SYNTAX Pm1004dcpAlmlineSyncAlarmsEntry
	MAX-ACCESS not-accessible
	STATUS current
	DESCRIPTION
        "
        Row definition for the pm1004dcpAlmlineSyncAlarms
        table
        "
	INDEX   { pm1004dcpAlmlineSyncAlarmsIndex }
	::= { pm1004dcpAlmlineSyncAlarmsTable 1 }


Pm1004dcpAlmlineSyncAlarmsEntry ::=
	SEQUENCE {
	pm1004dcpAlmlineSyncAlarmsIndex
		INTEGER,
	pm1004dcpAlmDwLosPortn
		EkiOnOff,
	pm1004dcpAlmUpLockerrPortn
		EkiOnOff,
	pm1004dcpAlmDwLockerrPortn
		EkiOnOff
	}


pm1004dcpAlmlineSyncAlarmsIndex OBJECT-TYPE
	SYNTAX  INTEGER(0..128)
	MAX-ACCESS  read-only
	STATUS current
	DESCRIPTION
        "
        Index definition for the pm1004dcpAlmlineSyncAlarms
        table
        "
	::= { pm1004dcpAlmlineSyncAlarmsEntry 1 }


pm1004dcpAlmDwLosPortn OBJECT-TYPE
	SYNTAX  EkiOnOff
	MAX-ACCESS read-only
	STATUS current
	DESCRIPTION
        "
        Line Input Loss Of Signal :This
        OID indicates a loss of signal
         on the 10 Gb/s input.  <Help>
          This alarm indicates if an optical
        signal is detected on the line
         transceiver input <Condtype> DW_LOS
        <Probcause> receiveFailure (41)
        <Alarmtype> physicalViolation (9)
        <Polarity> (2)
        "
	::= { pm1004dcpAlmlineSyncAlarmsEntry 17 }


pm1004dcpAlmUpLockerrPortn OBJECT-TYPE
	SYNTAX  EkiOnOff
	MAX-ACCESS read-only
	STATUS current
	DESCRIPTION
        "
        Upstream Clock Lock Error :This
        OID indicates that the serializer
        output 10 Gb/s clock multiplier
        unit is not locked. <Condtype>
         UP_LOCKERR <Probcause> receiveFailure
        (41) <Alarmtype> equipmentAlarm
        (5) <Polarity> (2)
        "
	::= { pm1004dcpAlmlineSyncAlarmsEntry 14 }


pm1004dcpAlmDwLockerrPortn OBJECT-TYPE
	SYNTAX  EkiOnOff
	MAX-ACCESS read-only
	STATUS current
	DESCRIPTION
        "
        Downstream Clock Lock Error :This
        OID indicates that the deserializer
        input 10 Gb/s clock recovery is
        not locked. <Condtype> DW_LOCKERR
        <Probcause> receiveFailure (41)
        <Alarmtype> equipmentAlarm (5)
         <Polarity> (2)
        "
	::= { pm1004dcpAlmlineSyncAlarmsEntry 13 }


--- *****************************************************
---     LEAF for the modInitFailLevel2 article
--- *****************************************************
pm1004dcpAlmmodInitFailLevel2 OBJECT IDENTIFIER ::= { pm1004dcpAlmOtherUrg 194 }




pm1004dcpAlmSwInitFail OBJECT-TYPE
	  SYNTAX EkiOnOff
	  MAX-ACCESS read-only
	  STATUS current
	  DESCRIPTION
        "
        SW Init Fail :This OID indicates
        that the SW intialization has caused
        unknown intial conditions  <Help>
         This alarm indicates if the SW
        module is correctly initialized
        <Condtype> SW_INIT_FAIL <Probcause>
        softwareError (47) <Alarmtype>
         processingErrorAlarm (4) <Polarity>
        (2)
        "
	  ::= { pm1004dcpAlmmodInitFailLevel2 5 }



pm1004dcpAlmResetHwInitFail OBJECT-TYPE
	  SYNTAX EkiOnOff
	  MAX-ACCESS read-only
	  STATUS current
	  DESCRIPTION
        "
        Reset HW Init Fail :This OID indicates
        that the HW intialization has caused
        unknown intial conditions  <Help>
         This alarm indicates if the HW
        has been correctly initialized
         <Condtype> RESET_HW_INIT_FAIL
         <Probcause> softwareError (47)
        <Alarmtype> processingErrorAlarm
        (4) <Polarity> (2)
        "
	  ::= { pm1004dcpAlmmodInitFailLevel2 4 }



pm1004dcpAlmBootUndone OBJECT-TYPE
	  SYNTAX EkiOnOff
	  MAX-ACCESS read-only
	  STATUS current
	  DESCRIPTION
        "
        Boot Undone :This OID indicates
        that the boot has not been correctly
        achieved  <Help>  This alarm indicates
        if the module has correctly boot
        <Condtype> BOOT_UNDONE <Probcause>
        softwareError (47) <Alarmtype>
         processingErrorAlarm (4) <Polarity>
        (2)
        "
	  ::= { pm1004dcpAlmmodInitFailLevel2 3 }



pm1004dcpAlmNextColdBootForced OBJECT-TYPE
	  SYNTAX EkiOnOff
	  MAX-ACCESS read-only
	  STATUS current
	  DESCRIPTION
        "
        Next Cold Boot Forced :This OID
        indicates that the next Reset will
        be forced Cold  <Help>  This alarm
        indicates that the next reset of
        the module will be forced to cold
        reset <Condtype> NEXT_COLD_BOOT_FORCED
        <Probcause> informationalStatus(1000)
        <Alarmtype> other (1) <Polarity>
        (2)
        "
	  ::= { pm1004dcpAlmmodInitFailLevel2 2 }



pm1004dcpAlmLedFail OBJECT-TYPE
	  SYNTAX EkiOnOff
	  MAX-ACCESS read-only
	  STATUS current
	  DESCRIPTION
        "
        Led Fail :This OID indicates that
        Led register has not been correctly
        initalized  <Help>  This alarm
         indicates if the module LEDs are
        correctly initialized <Condtype>
        LED_FAIL <Probcause> softwareError
        (47) <Alarmtype> processingErrorAlarm
        (4) <Polarity> (2)
        "
	  ::= { pm1004dcpAlmmodInitFailLevel2 1 }



--- *****************************************************
---     LEAF for the modInitFailLevel3 article
--- *****************************************************
pm1004dcpAlmmodInitFailLevel3 OBJECT IDENTIFIER ::= { pm1004dcpAlmOtherUrg 195 }




pm1004dcpAlmClient4InitFail OBJECT-TYPE
	  SYNTAX EkiOnOff
	  MAX-ACCESS read-only
	  STATUS current
	  DESCRIPTION
        "
        Client4 Init Fail :This OID indicates
        that Client 4 registers subset
         has not been correctly initialized
         <Help>  This alarm indicates if
        the client port 4 is correctly
         initialized <Condtype> CLIENT4_INIT_FAIL
        <Probcause> softwareError (47)
         <Alarmtype> processingErrorAlarm
        (4) <Polarity> (2)
        "
	  ::= { pm1004dcpAlmmodInitFailLevel3 12 }



pm1004dcpAlmClient3InitFail OBJECT-TYPE
	  SYNTAX EkiOnOff
	  MAX-ACCESS read-only
	  STATUS current
	  DESCRIPTION
        "
        Client3 Init Fail :This OID indicates
        that Client 3 registers subset
         has not been correctly initialized
         <Help>  This alarm indicates if
        the client port 3 is correctly
         initialized <Condtype> CLIENT3_INIT_FAIL
        <Probcause> softwareError (47)
         <Alarmtype> processingErrorAlarm
        (4) <Polarity> (2)
        "
	  ::= { pm1004dcpAlmmodInitFailLevel3 11 }



pm1004dcpAlmClient2InitFail OBJECT-TYPE
	  SYNTAX EkiOnOff
	  MAX-ACCESS read-only
	  STATUS current
	  DESCRIPTION
        "
        Client2 Init Fail :This OID indicates
        that Client 2 registers subset
         has not been correctly initialized
         <Help>  This alarm indicates if
        the client port 2 is correctly
         initialized <Condtype> CLIENT2_INIT_FAIL
        <Probcause> softwareError (47)
         <Alarmtype> processingErrorAlarm
        (4) <Polarity> (2)
        "
	  ::= { pm1004dcpAlmmodInitFailLevel3 10 }



pm1004dcpAlmClient1InitFail OBJECT-TYPE
	  SYNTAX EkiOnOff
	  MAX-ACCESS read-only
	  STATUS current
	  DESCRIPTION
        "
        Client1 Init Fail :This OID indicates
        that Client 1 registers subset
         has not been correctly initialized
         <Help>  This alarm indicates if
        the client port 1 is correctly
         initialized <Condtype> CLIENT1_INIT_FAIL
        <Probcause> softwareError (47)
         <Alarmtype> processingErrorAlarm
        (4) <Polarity> (2)
        "
	  ::= { pm1004dcpAlmmodInitFailLevel3 9 }



pm1004dcpAlmLine2InitFail OBJECT-TYPE
	  SYNTAX EkiOnOff
	  MAX-ACCESS read-only
	  STATUS current
	  DESCRIPTION
        "
        Line2 Init Fail :This OID indicates
        that the Line register subset has
        not been correctly initialized
          <Help>  This alarm indicates
         if the line port 2 is correctly
        initialized <Condtype> LINE2_INIT_FAIL
        <Probcause> softwareError (47)
         <Alarmtype> processingErrorAlarm
        (4) <Polarity> (2)
        "
	  ::= { pm1004dcpAlmmodInitFailLevel3 8 }



pm1004dcpAlmLine1InitFail OBJECT-TYPE
	  SYNTAX EkiOnOff
	  MAX-ACCESS read-only
	  STATUS current
	  DESCRIPTION
        "
        Line1 Init Fail :This OID indicates
        that the Line registersvsubset
         has not been correctly initialized
         <Help>  This alarm indicates if
        the line port 1 is correctly initialized
        <Condtype> LINE1_INIT_FAIL <Probcause>
        softwareError (47) <Alarmtype>
         processingErrorAlarm (4) <Polarity>
        (2)
        "
	  ::= { pm1004dcpAlmmodInitFailLevel3 7 }



pm1004dcpAlmXfp2InitFail OBJECT-TYPE
	  SYNTAX EkiOnOff
	  MAX-ACCESS read-only
	  STATUS current
	  DESCRIPTION
        "
        XFP2 Init Fail :This OID indicates
        that the XFP has not been correctly
        initialized  <Help>  This alarm
        indicates if the line transceiver
        2 is correctly initialized <Condtype>
        XFP2_INIT_FAIL <Probcause> softwareError
        (47) <Alarmtype> processingErrorAlarm
        (4) <Polarity> (2)
        "
	  ::= { pm1004dcpAlmmodInitFailLevel3 6 }



pm1004dcpAlmXfp1InitFail OBJECT-TYPE
	  SYNTAX EkiOnOff
	  MAX-ACCESS read-only
	  STATUS current
	  DESCRIPTION
        "
        XFP1 Init Fail :This OID indicates
        that the XFP has not been correctly
        initialized  <Help>  This alarm
        indicates if the line transceiver
        1 is correctly initialized <Condtype>
        XFP1_INIT_FAIL <Probcause> softwareError
        (47) <Alarmtype> processingErrorAlarm
        (4) <Polarity> (2)
        "
	  ::= { pm1004dcpAlmmodInitFailLevel3 5 }



pm1004dcpAlmInitModuleFail OBJECT-TYPE
	  SYNTAX EkiOnOff
	  MAX-ACCESS read-only
	  STATUS current
	  DESCRIPTION
        "
        Init Module Fail :This OID indicates
        that the Module has not been correctly
        initialized  <Help>  This alarm
        indicates if the SW module is correctly
        initialized <Condtype> INIT_MODULE_FAIL
        <Probcause> softwareError (47)
         <Alarmtype> processingErrorAlarm
        (4) <Polarity> (2)
        "
	  ::= { pm1004dcpAlmmodInitFailLevel3 3 }



pm1004dcpAlmObmTypeReadFail OBJECT-TYPE
	  SYNTAX EkiOnOff
	  MAX-ACCESS read-only
	  STATUS current
	  DESCRIPTION
        "
        OBM Type Read Fail :This OID indicates
        that OBM type has not been recognized
         <Help>  This alarm indicates if
        the OBM board has been correctly
        identified <Condtype> OBM_TYPE_READ_FAIL
        <Probcause> softwareError (47)
         <Alarmtype> processingErrorAlarm
        (4) <Polarity> (2)
        "
	  ::= { pm1004dcpAlmmodInitFailLevel3 2 }



pm1004dcpAlmGwIdentFail OBJECT-TYPE
	  SYNTAX EkiOnOff
	  MAX-ACCESS read-only
	  STATUS current
	  DESCRIPTION
        "
        GW Ident Fail :This OID indicates
        that GW identification has not
         been read  <Help>  This alarm
         indicates if the GW has been correctly
        identified <Condtype> GW_IDENT_FAIL
        <Probcause> softwareError (47)
         <Alarmtype> processingErrorAlarm
        (4) <Polarity> (2)
        "
	  ::= { pm1004dcpAlmmodInitFailLevel3 1 }



--- *****************************************************
---     LEAF for the adddropTsClientRxProt article
--- *****************************************************
pm1004dcpAlmadddropTsClientRxProt OBJECT IDENTIFIER ::= { pm1004dcpAlmOtherUrg 198 }




pm1004dcpAlmAdddropClient4East OBJECT-TYPE
	  SYNTAX EkiOnOff
	  MAX-ACCESS read-only
	  STATUS current
	  DESCRIPTION
        "
        Client 4 East Rx Side Active :This
        OID indicates the Client #4 is
         active on East receiving side
         <Condtype> ADDDROP_CLIENT4_EAST
        <Probcause> other (1) <Alarmtype>
        other (1) <Polarity> (2)
        "
	  ::= { pm1004dcpAlmadddropTsClientRxProt 12 }



pm1004dcpAlmAdddropClient3East OBJECT-TYPE
	  SYNTAX EkiOnOff
	  MAX-ACCESS read-only
	  STATUS current
	  DESCRIPTION
        "
        Client 3 East Rx Side Active :This
        OID indicates the Client #3 is
         active on East receiving side
         <Condtype> ADDDROP_CLIENT3_EAST
        <Probcause> other (1) <Alarmtype>
        other (1) <Polarity> (2)
        "
	  ::= { pm1004dcpAlmadddropTsClientRxProt 11 }



pm1004dcpAlmAdddropClient2East OBJECT-TYPE
	  SYNTAX EkiOnOff
	  MAX-ACCESS read-only
	  STATUS current
	  DESCRIPTION
        "
        Client 2 East Rx Side Active :This
        OID indicates the Client #2 is
         active on East receiving side
         <Condtype> ADDDROP_CLIENT2_EAST
        <Probcause> other (1) <Alarmtype>
        other (1) <Polarity> (2)
        "
	  ::= { pm1004dcpAlmadddropTsClientRxProt 10 }



pm1004dcpAlmAdddropClient1East OBJECT-TYPE
	  SYNTAX EkiOnOff
	  MAX-ACCESS read-only
	  STATUS current
	  DESCRIPTION
        "
        Client 1 East Rx Side Active :This
        OID indicates the Client #1 is
         active on East receiving side
         <Condtype> ADDDROP_CLIENT1_EAST
        <Probcause> other (1) <Alarmtype>
        other (1) <Polarity> (2)
        "
	  ::= { pm1004dcpAlmadddropTsClientRxProt 9 }



pm1004dcpAlmAdddropClient4West OBJECT-TYPE
	  SYNTAX EkiOnOff
	  MAX-ACCESS read-only
	  STATUS current
	  DESCRIPTION
        "
        Client 4 West Rx Side Active :This
        OID indicates the Client #4 is
         active on West receiving side
         <Condtype> ADDDROP_CLIENT4_WEST
        <Probcause> other (1) <Alarmtype>
        other (1) <Polarity> (2)
        "
	  ::= { pm1004dcpAlmadddropTsClientRxProt 4 }



pm1004dcpAlmAdddropClient3West OBJECT-TYPE
	  SYNTAX EkiOnOff
	  MAX-ACCESS read-only
	  STATUS current
	  DESCRIPTION
        "
        Client 3 West Rx Side Active :This
        OID indicates the Client #3 is
         active on West receiving side
         <Condtype> ADDDROP_CLIENT3_WEST
        <Probcause> other (1) <Alarmtype>
        other (1) <Polarity> (2)
        "
	  ::= { pm1004dcpAlmadddropTsClientRxProt 3 }



pm1004dcpAlmAdddropClient2West OBJECT-TYPE
	  SYNTAX EkiOnOff
	  MAX-ACCESS read-only
	  STATUS current
	  DESCRIPTION
        "
        Client 2 West Rx Side Active :This
        OID indicates the Client #2 is
         active on West receiving side
         <Condtype> ADDDROP_CLIENT2_WEST
        <Probcause> other (1) <Alarmtype>
        other (1) <Polarity> (2)
        "
	  ::= { pm1004dcpAlmadddropTsClientRxProt 2 }



pm1004dcpAlmAdddropClient1West OBJECT-TYPE
	  SYNTAX EkiOnOff
	  MAX-ACCESS read-only
	  STATUS current
	  DESCRIPTION
        "
        Client 1 West Rx Side Active :This
        OID indicates the Client #1 is
         active on West receiving side
         <Condtype> ADDDROP_CLIENT1_WEST
        <Probcause> other (1) <Alarmtype>
        other (1) <Polarity> (2)
        "
	  ::= { pm1004dcpAlmadddropTsClientRxProt 1 }



--- *********************************************************
---     TABLE for the pm1004dcpAlmlineXfp1Alarm articles
--- *********************************************************

pm1004dcpAlmlineXfp1AlarmTable OBJECT-TYPE
	SYNTAX  SEQUENCE OF Pm1004dcpAlmlineXfp1AlarmEntry
	MAX-ACCESS not-accessible
	STATUS current
	DESCRIPTION
        "
        List of pm1004dcpAlmlineXfp1Alarm
        Article
        "
	::= { pm1004dcpAlmLineUrg 208 }


pm1004dcpAlmlineXfp1AlarmEntry OBJECT-TYPE
	SYNTAX Pm1004dcpAlmlineXfp1AlarmEntry
	MAX-ACCESS not-accessible
	STATUS current
	DESCRIPTION
        "
        Row definition for the pm1004dcpAlmlineXfp1Alarm
        table
        "
	INDEX   { pm1004dcpAlmlineXfp1AlarmIndex }
	::= { pm1004dcpAlmlineXfp1AlarmTable 1 }


Pm1004dcpAlmlineXfp1AlarmEntry ::=
	SEQUENCE {
	pm1004dcpAlmlineXfp1AlarmIndex
		INTEGER,
	pm1004dcpAlmRxPowerHighAlarmPortn
		EkiOnOff,
	pm1004dcpAlmRxPowerLowAlarmPortn
		EkiOnOff,
	pm1004dcpAlmTempHighAlarmPortn
		EkiOnOff,
	pm1004dcpAlmTempLowAlarmPortn
		EkiOnOff,
	pm1004dcpAlmTxBiasHighAlarmPortn
		EkiOnOff,
	pm1004dcpAlmTxBiasLowAlarmPortn
		EkiOnOff,
	pm1004dcpAlmTxPowerHighAlarmPortn
		EkiOnOff,
	pm1004dcpAlmTxPowerLowAlarmPortn
		EkiOnOff
	}


pm1004dcpAlmlineXfp1AlarmIndex OBJECT-TYPE
	SYNTAX  INTEGER(0..128)
	MAX-ACCESS  read-only
	STATUS current
	DESCRIPTION
        "
        Index definition for the pm1004dcpAlmlineXfp1Alarm
        table
        "
	::= { pm1004dcpAlmlineXfp1AlarmEntry 1 }


pm1004dcpAlmRxPowerHighAlarmPortn OBJECT-TYPE
	SYNTAX  EkiOnOff
	MAX-ACCESS read-only
	STATUS current
	DESCRIPTION
        "
        Line Optical Rx Power High :Alarm
        indicating that the XFP received
        optical power is higher than the
        threshold value written in the
         XFP EEPROM <Condtype> RX_POWER_HIGH_ALARM_1
        <Probcause> receiveFailure (41)
        <Alarmtype> equipmentAlarm (5)
         <Polarity> (2)
        "
	::= { pm1004dcpAlmlineXfp1AlarmEntry 17 }


pm1004dcpAlmRxPowerLowAlarmPortn OBJECT-TYPE
	SYNTAX  EkiOnOff
	MAX-ACCESS read-only
	STATUS current
	DESCRIPTION
        "
        Line Optical Rx Power Low :Alarm
        indicating that the XFP received
        optical power is lower than the
        threshold value written in the
         XFP EEPROM  <Condtype> RX_POWER_LOW_ALARM_1
        <Probcause> receiveFailure (41)
        <Alarmtype> equipmentAlarm (5)
         <Polarity> (2)
        "
	::= { pm1004dcpAlmlineXfp1AlarmEntry 16 }


pm1004dcpAlmTempHighAlarmPortn OBJECT-TYPE
	SYNTAX  EkiOnOff
	MAX-ACCESS read-only
	STATUS current
	DESCRIPTION
        "
        Line Transceiver Temp High :Alarm
        indicating that the XFP/OTX temperature
        is higher than the threshold value
        written in the XFP EEPROM <Condtype>
        TEMP_HIGH_ALARM_1 <Probcause> temperatureUnacceptable
        (51) <Alarmtype> equipmentAlarm
        (5) <Polarity> (2)
        "
	::= { pm1004dcpAlmlineXfp1AlarmEntry 9 }


pm1004dcpAlmTempLowAlarmPortn OBJECT-TYPE
	SYNTAX  EkiOnOff
	MAX-ACCESS read-only
	STATUS current
	DESCRIPTION
        "
        Line Transceiver Temp Low :Alarm
        indicating that the XFP/OTX temperature
        is lower than the threshold value
        written in the XFP/OTX EEPROM <Condtype>
        TEMP_LOW_ALARM_1 <Probcause> temperatureUnacceptable
        (51) <Alarmtype> equipmentAlarm
        (5) <Polarity> (2)
        "
	::= { pm1004dcpAlmlineXfp1AlarmEntry 8 }


pm1004dcpAlmTxBiasHighAlarmPortn OBJECT-TYPE
	SYNTAX  EkiOnOff
	MAX-ACCESS read-only
	STATUS current
	DESCRIPTION
        "
        Line Transceiver Bias High :Alarm
        indicating that the XFP/OTX transmitter
        laser bias current is higher than
        the threshold value written in
         the XFP EEPROM <Condtype> TX_BIAS_HIGH_ALARM_1
        <Probcause> transmitterFailure
         (56) <Alarmtype> equipmentAlarm
        (5) <Polarity> (2)
        "
	::= { pm1004dcpAlmlineXfp1AlarmEntry 5 }


pm1004dcpAlmTxBiasLowAlarmPortn OBJECT-TYPE
	SYNTAX  EkiOnOff
	MAX-ACCESS read-only
	STATUS current
	DESCRIPTION
        "
        Line Transceiver Bias Low :Alarm
        indicating that the XFP/OTX transmitter
        laser bias current is lower than
        the threshold value written in
         the XFP/OTX EEPROM <Condtype>
         TX_BIAS_LOW_ALARM_1 <Probcause>
        transmitterFailure (56) <Alarmtype>
        equipmentAlarm (5) <Polarity> (2)
        "
	::= { pm1004dcpAlmlineXfp1AlarmEntry 4 }


pm1004dcpAlmTxPowerHighAlarmPortn OBJECT-TYPE
	SYNTAX  EkiOnOff
	MAX-ACCESS read-only
	STATUS current
	DESCRIPTION
        "
        Line Optical Tx Power High :Alarm
        indicating that the XFP/OTX transmitter
        transmitter output power is higher
        than the threshold value written
        in the XFP EEPROM <Condtype> TX_POWER_HIGH_ALARM_1
        <Probcause> transmitterFailure
         (56) <Alarmtype> equipmentAlarm
        (5) <Polarity> (2)
        "
	::= { pm1004dcpAlmlineXfp1AlarmEntry 3 }


pm1004dcpAlmTxPowerLowAlarmPortn OBJECT-TYPE
	SYNTAX  EkiOnOff
	MAX-ACCESS read-only
	STATUS current
	DESCRIPTION
        "
        Line Optical Tx Power Low :Alarm
        indicating that the XFP/OTX transmitter
        transmitter output power is lower
        than the threshold value written
        in the XFP/OTX EEPROM <Condtype>
        TX_POWER_LOW_ALARM_1 <Probcause>
        transmitterFailure (56) <Alarmtype>
        equipmentAlarm (5) <Polarity> (2)
        "
	::= { pm1004dcpAlmlineXfp1AlarmEntry 2 }


--- *********************************************************
---     TABLE for the pm1004dcpAlmlineXfp1Warnings articles
--- *********************************************************

pm1004dcpAlmlineXfp1WarningsTable OBJECT-TYPE
	SYNTAX  SEQUENCE OF Pm1004dcpAlmlineXfp1WarningsEntry
	MAX-ACCESS not-accessible
	STATUS current
	DESCRIPTION
        "
        List of pm1004dcpAlmlineXfp1Warnings
        Article
        "
	::= { pm1004dcpAlmLineNurg 209 }


pm1004dcpAlmlineXfp1WarningsEntry OBJECT-TYPE
	SYNTAX Pm1004dcpAlmlineXfp1WarningsEntry
	MAX-ACCESS not-accessible
	STATUS current
	DESCRIPTION
        "
        Row definition for the pm1004dcpAlmlineXfp1Warnings
        table
        "
	INDEX   { pm1004dcpAlmlineXfp1WarningsIndex }
	::= { pm1004dcpAlmlineXfp1WarningsTable 1 }


Pm1004dcpAlmlineXfp1WarningsEntry ::=
	SEQUENCE {
	pm1004dcpAlmlineXfp1WarningsIndex
		INTEGER,
	pm1004dcpAlmRxPowerHighWarningPortn
		EkiOnOff,
	pm1004dcpAlmRxPowerLowWarningPortn
		EkiOnOff,
	pm1004dcpAlmTempHighWarningPortn
		EkiOnOff,
	pm1004dcpAlmTempLowWarningPortn
		EkiOnOff,
	pm1004dcpAlmTxBiasHighWarningPortn
		EkiOnOff,
	pm1004dcpAlmTxBiasLowWarningPortn
		EkiOnOff,
	pm1004dcpAlmTxPowerHighWarningPortn
		EkiOnOff,
	pm1004dcpAlmTxPowerLowWarningPortn
		EkiOnOff
	}


pm1004dcpAlmlineXfp1WarningsIndex OBJECT-TYPE
	SYNTAX  INTEGER(0..128)
	MAX-ACCESS  read-only
	STATUS current
	DESCRIPTION
        "
        Index definition for the pm1004dcpAlmlineXfp1Warnings
        table
        "
	::= { pm1004dcpAlmlineXfp1WarningsEntry 1 }


pm1004dcpAlmRxPowerHighWarningPortn OBJECT-TYPE
	SYNTAX  EkiOnOff
	MAX-ACCESS read-only
	STATUS current
	DESCRIPTION
        "
        Line Optical Rx Power High Warning
        :Warning indicating that the XFP
        received optical power is higher
        than the threshold value written
        in the XFP EEPROM <Condtype> RX_POWER_HIGH_WARNING_1
        <Probcause> receiveFailure (41)
        <Alarmtype> equipmentAlarm (5)
         <Polarity> (2)
        "
	::= { pm1004dcpAlmlineXfp1WarningsEntry 17 }


pm1004dcpAlmRxPowerLowWarningPortn OBJECT-TYPE
	SYNTAX  EkiOnOff
	MAX-ACCESS read-only
	STATUS current
	DESCRIPTION
        "
        Line Optical Rx Power Low Warning
        :Warning indicating that the XFP
        received optical power is lower
        than the threshold value written
        in the XFP EEPROM  <Condtype> RX_POWER_LOW_WARNING_1
        <Probcause> receiveFailure (41)
        <Alarmtype> equipmentAlarm (5)
         <Polarity> (2)
        "
	::= { pm1004dcpAlmlineXfp1WarningsEntry 16 }


pm1004dcpAlmTempHighWarningPortn OBJECT-TYPE
	SYNTAX  EkiOnOff
	MAX-ACCESS read-only
	STATUS current
	DESCRIPTION
        "
        Line Transceiver Temp High Warning
        :Warning indicating that the XFP/OTX
        temperature is higher than the
         threshold value written in the
        XFP EEPROM <Condtype> TEMP_HIGH_WARNING_1
        <Probcause> temperatureUnacceptable
        (51) <Alarmtype> equipmentAlarm
        (5) <Polarity> (2)
        "
	::= { pm1004dcpAlmlineXfp1WarningsEntry 9 }


pm1004dcpAlmTempLowWarningPortn OBJECT-TYPE
	SYNTAX  EkiOnOff
	MAX-ACCESS read-only
	STATUS current
	DESCRIPTION
        "
        Line Transceiver Temp Low Warning
        :Warning indicating that the XFP/OTX
        temperature is lower than the threshold
        value written in the XFP/OTX EEPROM
        <Condtype> TEMP_LOW_WARNING_1 <Probcause>
        temperatureUnacceptable (51) <Alarmtype>
        equipmentAlarm (5) <Polarity> (2)
        "
	::= { pm1004dcpAlmlineXfp1WarningsEntry 8 }


pm1004dcpAlmTxBiasHighWarningPortn OBJECT-TYPE
	SYNTAX  EkiOnOff
	MAX-ACCESS read-only
	STATUS current
	DESCRIPTION
        "
        Line Transceiver Bias High Warning
        :Warning indicating that the XFP/OTX
        transmitter laser bias current
         is higher than the threshold value
        written in the XFP EEPROM <Condtype>
        TX_BIAS_HIGH_WARNING_1 <Probcause>
        transmitterFailure (56) <Alarmtype>
        equipmentAlarm (5) <Polarity> (2)
        "
	::= { pm1004dcpAlmlineXfp1WarningsEntry 5 }


pm1004dcpAlmTxBiasLowWarningPortn OBJECT-TYPE
	SYNTAX  EkiOnOff
	MAX-ACCESS read-only
	STATUS current
	DESCRIPTION
        "
        Line Transceiver Bias Low Warning
        :Warning indicating that the XFP/OTX
        transmitter laser bias current
         is lower than the threshold value
        written in the XFP/OTX EEPROM <Condtype>
        TX_BIAS_LOW_WARNING_1 <Probcause>
        transmitterFailure (56) <Alarmtype>
        equipmentAlarm (5) <Polarity> (2)
        "
	::= { pm1004dcpAlmlineXfp1WarningsEntry 4 }


pm1004dcpAlmTxPowerHighWarningPortn OBJECT-TYPE
	SYNTAX  EkiOnOff
	MAX-ACCESS read-only
	STATUS current
	DESCRIPTION
        "
        Line Optical Tx Power High Warning
        :Warning indicating that the XFP/OTX
        transmitter transmitter output
         power is higher than the threshold
        value written in the XFP EEPROM
        <Condtype> TX_POWER_HIGH_WARNING_1
        <Probcause> transmitterFailure
         (56) <Alarmtype> equipmentAlarm
        (5) <Polarity> (2)
        "
	::= { pm1004dcpAlmlineXfp1WarningsEntry 3 }


pm1004dcpAlmTxPowerLowWarningPortn OBJECT-TYPE
	SYNTAX  EkiOnOff
	MAX-ACCESS read-only
	STATUS current
	DESCRIPTION
        "
        Line Optical Tx Power Low Warning
        :Warning indicating that the XFP/OTX
        transmitter transmitter output
         power is lower than the threshold
        value written in the XFP/OTX EEPROM
        <Condtype> TX_POWER_LOW_WARNING_1
        <Probcause> transmitterFailure
         (56) <Alarmtype> equipmentAlarm
        (5) <Polarity> (2)
        "
	::= { pm1004dcpAlmlineXfp1WarningsEntry 2 }


--- *********************************************************
---     TABLE for the pm1004dcpAlmlineXfp1Alarms articles
--- *********************************************************

pm1004dcpAlmlineXfp1AlarmsTable OBJECT-TYPE
	SYNTAX  SEQUENCE OF Pm1004dcpAlmlineXfp1AlarmsEntry
	MAX-ACCESS not-accessible
	STATUS current
	DESCRIPTION
        "
        List of pm1004dcpAlmlineXfp1Alarms
        Article
        "
	::= { pm1004dcpAlmLineCrit 211 }


pm1004dcpAlmlineXfp1AlarmsEntry OBJECT-TYPE
	SYNTAX Pm1004dcpAlmlineXfp1AlarmsEntry
	MAX-ACCESS not-accessible
	STATUS current
	DESCRIPTION
        "
        Row definition for the pm1004dcpAlmlineXfp1Alarms
        table
        "
	INDEX   { pm1004dcpAlmlineXfp1AlarmsIndex }
	::= { pm1004dcpAlmlineXfp1AlarmsTable 1 }


Pm1004dcpAlmlineXfp1AlarmsEntry ::=
	SEQUENCE {
	pm1004dcpAlmlineXfp1AlarmsIndex
		INTEGER,
	pm1004dcpAlmApdSupplyFaultPortn
		EkiOnOff,
	pm1004dcpAlmTecFaultPortn
		EkiOnOff,
	pm1004dcpAlmWavelengthUnlockedPortn
		EkiOnOff,
	pm1004dcpAlmTxNrPortn
		EkiOnOff,
	pm1004dcpAlmTxFaultPortn
		EkiOnOff,
	pm1004dcpAlmTxCdrNotLockedPortn
		EkiOnOff,
	pm1004dcpAlmRxNrPortn
		EkiOnOff,
	pm1004dcpAlmRxCdrNotLockedPortn
		EkiOnOff,
	pm1004dcpAlmModNrPortn
		EkiOnOff
	}


pm1004dcpAlmlineXfp1AlarmsIndex OBJECT-TYPE
	SYNTAX  INTEGER(0..128)
	MAX-ACCESS  read-only
	STATUS current
	DESCRIPTION
        "
        Index definition for the pm1004dcpAlmlineXfp1Alarms
        table
        "
	::= { pm1004dcpAlmlineXfp1AlarmsEntry 1 }


pm1004dcpAlmApdSupplyFaultPortn OBJECT-TYPE
	SYNTAX  EkiOnOff
	MAX-ACCESS read-only
	STATUS current
	DESCRIPTION
        "
        Line Rx Photodiode Power Failed
        :This OID indicates a failure on
        the APD power supply  <Help>  This
        alarm indicates if the APD power
        supply is in fail condition <Condtype>
        APD_SUPPLY_FAULT_1 <Probcause>
         receiverFailure (42) <Alarmtype>
        equipmentAlarm (5) <Polarity> (2)
        "
	::= { pm1004dcpAlmlineXfp1AlarmsEntry 17 }


pm1004dcpAlmTecFaultPortn OBJECT-TYPE
	SYNTAX  EkiOnOff
	MAX-ACCESS read-only
	STATUS current
	DESCRIPTION
        "
        Line Optical Tx Temp Regul Failed
        :This OID indicates a failure on
        the TEC module  <Help>  This alarm
        indicates if the TEC of the line
        transceiver is in fail condition
        <Condtype> TEC_FAULT_1 <Probcause>
        transmitterFailure (56) <Alarmtype>
        equipmentAlarm (5) <Polarity> (2)
        "
	::= { pm1004dcpAlmlineXfp1AlarmsEntry 16 }


pm1004dcpAlmWavelengthUnlockedPortn OBJECT-TYPE
	SYNTAX  EkiOnOff
	MAX-ACCESS read-only
	STATUS current
	DESCRIPTION
        "
        Line Optical Tx Wavelength Unlocked
        :This OID indicates that the wavelength
        error is exceeding the manufacturer
        tolerance  <Help>  This alarm indicates
        if the wavelenght of the line transceiver
        is locked <Condtype> WAVELENGTH_UNLOCKED_1
        <Probcause> transmitterFailure
         (56) <Alarmtype> equipmentAlarm
        (5) <Polarity> (2)
        "
	::= { pm1004dcpAlmlineXfp1AlarmsEntry 15 }


pm1004dcpAlmTxNrPortn OBJECT-TYPE
	SYNTAX  EkiOnOff
	MAX-ACCESS read-only
	STATUS current
	DESCRIPTION
        "
        Line Optical Tx Not Ready :This
        OID indicates a condition has arisen
        leading to invalid data on the
         transmitting side  <Help>  This
        alarm indicates if the Tx part
         of the line transceiver is ready
        <Condtype> TX_NR_1 <Probcause>
         transmitterFailure (56) <Alarmtype>
        equipmentAlarm (5) <Polarity> (2)
        "
	::= { pm1004dcpAlmlineXfp1AlarmsEntry 9 }


pm1004dcpAlmTxFaultPortn OBJECT-TYPE
	SYNTAX  EkiOnOff
	MAX-ACCESS read-only
	STATUS current
	DESCRIPTION
        "
        Line Optical Tx Failure :This
         OID indicates a fault condition
        on the laser detected by the safety
        syste  <Help>  This alarm indicates
        if the laser of the line transceiver
        is in fail condition <Condtype>
        TX_FAULT_1 <Probcause> transmitterFailure
        (56) <Alarmtype> equipmentAlarm
        (5) <Polarity> (2)
        "
	::= { pm1004dcpAlmlineXfp1AlarmsEntry 8 }


pm1004dcpAlmTxCdrNotLockedPortn OBJECT-TYPE
	SYNTAX  EkiOnOff
	MAX-ACCESS read-only
	STATUS current
	DESCRIPTION
        "
        Line Optical Tx CDR Unlocked :This
        OID indicates a loss of lock on
        the transmitting side CDR has been
        detected.  <Help>  This alarm indicates
        if the Tx CDR is locked in the
         line transceiver <Condtype> TX_CDR_NOT_LOCKED1_1
        <Probcause> transmitterFailure
         (56) <Alarmtype> equipmentAlarm
        (5) <Polarity> (2)
        "
	::= { pm1004dcpAlmlineXfp1AlarmsEntry 7 }


pm1004dcpAlmRxNrPortn OBJECT-TYPE
	SYNTAX  EkiOnOff
	MAX-ACCESS read-only
	STATUS current
	DESCRIPTION
        "
        Line Optical Rx Not Ready :This
        OID indicates that a condition
         has arisen leading to invalid
         data on the receiving side.  <Help>
         This alarm indicates if the Rx
        part of the line transceiver is
        ready <Condtype> RX_NR_1 <Probcause>
        receiveFailure (41) <Alarmtype>
        equipmentAlarm (5) <Polarity> (2)
        "
	::= { pm1004dcpAlmlineXfp1AlarmsEntry 6 }


pm1004dcpAlmRxCdrNotLockedPortn OBJECT-TYPE
	SYNTAX  EkiOnOff
	MAX-ACCESS read-only
	STATUS current
	DESCRIPTION
        "
        Line Optical Rx CDR Unlocked :This
        OID indicates that a loss of lock
        on the receiving side CDR has been
        detected  <Help>  This alarm indicates
        if the Rx CDR is locked in the
         line transceiver <Condtype> RX_CDR_NOT_LOCKED1_1
        <Probcause> receiveFailure (41)
        <Alarmtype> equipmentAlarm (5)
         <Polarity> (2)
        "
	::= { pm1004dcpAlmlineXfp1AlarmsEntry 4 }


pm1004dcpAlmModNrPortn OBJECT-TYPE
	SYNTAX  EkiOnOff
	MAX-ACCESS read-only
	STATUS current
	DESCRIPTION
        "
        Line Optical Module Not Ready
         :This OID indicates that the module
        is unable to determine correct
         data.  <Help>  This alarm indicates
        if the line transceiver is ready
        <Condtype> MOD_NR_1 <Probcause>
        receiveFailure (41) <Alarmtype>
        equipmentAlarm (5) <Polarity> (2)
        "
	::= { pm1004dcpAlmlineXfp1AlarmsEntry 3 }


--- *********************************************************
---     TABLE for the pm1004dcpAlmlineXfp1SupplyAlarm articles
--- *********************************************************

pm1004dcpAlmlineXfp1SupplyAlarmTable OBJECT-TYPE
	SYNTAX  SEQUENCE OF Pm1004dcpAlmlineXfp1SupplyAlarmEntry
	MAX-ACCESS not-accessible
	STATUS current
	DESCRIPTION
        "
        List of pm1004dcpAlmlineXfp1SupplyAlarm
        Article
        "
	::= { pm1004dcpAlmLineUrg 212 }


pm1004dcpAlmlineXfp1SupplyAlarmEntry OBJECT-TYPE
	SYNTAX Pm1004dcpAlmlineXfp1SupplyAlarmEntry
	MAX-ACCESS not-accessible
	STATUS current
	DESCRIPTION
        "
        Row definition for the pm1004dcpAlmlineXfp1SupplyAlarm
        table
        "
	INDEX   { pm1004dcpAlmlineXfp1SupplyAlarmIndex }
	::= { pm1004dcpAlmlineXfp1SupplyAlarmTable 1 }


Pm1004dcpAlmlineXfp1SupplyAlarmEntry ::=
	SEQUENCE {
	pm1004dcpAlmlineXfp1SupplyAlarmIndex
		INTEGER,
	pm1004dcpAlmVcc5HighWarningPortn
		EkiOnOff,
	pm1004dcpAlmVcc5LowWarningPortn
		EkiOnOff,
	pm1004dcpAlmVcc3HighWarningPortn
		EkiOnOff,
	pm1004dcpAlmVcc3LowWarningPortn
		EkiOnOff,
	pm1004dcpAlmVcc2HighWarningPortn
		EkiOnOff,
	pm1004dcpAlmVcc2LowWarningPortn
		EkiOnOff,
	pm1004dcpAlmVee5HighWarningPortn
		EkiOnOff,
	pm1004dcpAlmVee5LowWarningPortn
		EkiOnOff,
	pm1004dcpAlmVcc5HighAlarmPortn
		EkiOnOff,
	pm1004dcpAlmVcc5LowAlarmPortn
		EkiOnOff,
	pm1004dcpAlmVcc3HighAlarmPortn
		EkiOnOff,
	pm1004dcpAlmVcc3LowAlarmPortn
		EkiOnOff,
	pm1004dcpAlmVcc2HighAlarmPortn
		EkiOnOff,
	pm1004dcpAlmVcc2LowAlarmPortn
		EkiOnOff,
	pm1004dcpAlmVee5HighAlarmPortn
		EkiOnOff,
	pm1004dcpAlmVee5LowAlarmPortn
		EkiOnOff
	}


pm1004dcpAlmlineXfp1SupplyAlarmIndex OBJECT-TYPE
	SYNTAX  INTEGER(0..128)
	MAX-ACCESS  read-only
	STATUS current
	DESCRIPTION
        "
        Index definition for the pm1004dcpAlmlineXfp1SupplyAlarm
        table
        "
	::= { pm1004dcpAlmlineXfp1SupplyAlarmEntry 1 }


pm1004dcpAlmVcc5HighWarningPortn OBJECT-TYPE
	SYNTAX  EkiOnOff
	MAX-ACCESS read-only
	STATUS current
	DESCRIPTION
        "
        VCC5 Power Supply High Warning
        :Warning indicating the XFP/OTX
        VCC5 power supply is higher than
        the threshold written in the EEPROM
        <Condtype> VCC5_HIGH_WARNING_1
         <Probcause> powerProblem (36)
         <Alarmtype> equipmentAlarm (5)
        <Polarity> (2)
        "
	::= { pm1004dcpAlmlineXfp1SupplyAlarmEntry 17 }


pm1004dcpAlmVcc5LowWarningPortn OBJECT-TYPE
	SYNTAX  EkiOnOff
	MAX-ACCESS read-only
	STATUS current
	DESCRIPTION
        "
        VCC5 Power Supply Low Warning
         :Warning indicating the XFP/OTX
        VCC5 power supply is lower than
        the threshold written in the EEPROM
        <Condtype> VCC5_LOW_WARNING_1 <Probcause>
        powerProblem (36) <Alarmtype> equipmentAlarm
        (5) <Polarity> (2)
        "
	::= { pm1004dcpAlmlineXfp1SupplyAlarmEntry 16 }


pm1004dcpAlmVcc3HighWarningPortn OBJECT-TYPE
	SYNTAX  EkiOnOff
	MAX-ACCESS read-only
	STATUS current
	DESCRIPTION
        "
        VCC3 Power Supply High Warning
        :Warning indicating the XFP/OTX
        VCC3 power supply is higher than
        the threshold written in the EEPROM
        <Condtype> VCC3_HIGH_WARNING_1
         <Probcause> powerProblem (36)
         <Alarmtype> equipmentAlarm (5)
        <Polarity> (2)
        "
	::= { pm1004dcpAlmlineXfp1SupplyAlarmEntry 15 }


pm1004dcpAlmVcc3LowWarningPortn OBJECT-TYPE
	SYNTAX  EkiOnOff
	MAX-ACCESS read-only
	STATUS current
	DESCRIPTION
        "
        VCC3 Power Supply Low Warning
         :Warning indicating the XFP/OTX
        VCC3 power supply is lower than
        the threshold written in the EEPROM
        <Condtype> VCC3_LOW_WARNING_1 <Probcause>
        powerProblem (36) <Alarmtype> equipmentAlarm
        (5) <Polarity> (2)
        "
	::= { pm1004dcpAlmlineXfp1SupplyAlarmEntry 14 }


pm1004dcpAlmVcc2HighWarningPortn OBJECT-TYPE
	SYNTAX  EkiOnOff
	MAX-ACCESS read-only
	STATUS current
	DESCRIPTION
        "
        VCC2 Power Supply High Warning
        :Warning indicating the XFP/OTX
        VCC2 power supply is higher than
        the threshold written in the EEPROM
        <Condtype> VCC2_HIGH_WARNING_1
         <Probcause> powerProblem (36)
         <Alarmtype> equipmentAlarm (5)
        <Polarity> (2)
        "
	::= { pm1004dcpAlmlineXfp1SupplyAlarmEntry 13 }


pm1004dcpAlmVcc2LowWarningPortn OBJECT-TYPE
	SYNTAX  EkiOnOff
	MAX-ACCESS read-only
	STATUS current
	DESCRIPTION
        "
        VCC2 Power Supply Low Warning
         :Warning indicating the XFP/OTX
        VCC2 power supply is lower than
        the threshold written in the EEPROM
        <Condtype> VCC2_LOW_WARNING_1 <Probcause>
        powerProblem (36) <Alarmtype> equipmentAlarm
        (5) <Polarity> (2)
        "
	::= { pm1004dcpAlmlineXfp1SupplyAlarmEntry 12 }


pm1004dcpAlmVee5HighWarningPortn OBJECT-TYPE
	SYNTAX  EkiOnOff
	MAX-ACCESS read-only
	STATUS current
	DESCRIPTION
        "
        VEE5 Power Supply High Warning
        :Warning indicating the XFP/OTX
        VEE5 power supply is higher than
        the threshold written in the EEPROM
        <Condtype> VEE5_HIGH_WARNING_1
         <Probcause> powerProblem (36)
         <Alarmtype> equipmentAlarm (5)
        <Polarity> (2)
        "
	::= { pm1004dcpAlmlineXfp1SupplyAlarmEntry 11 }


pm1004dcpAlmVee5LowWarningPortn OBJECT-TYPE
	SYNTAX  EkiOnOff
	MAX-ACCESS read-only
	STATUS current
	DESCRIPTION
        "
        VEE5 Power Supply Low Warning
         :Warning indicating the XFP/OTX
        VEE5 power supply is lower than
        the threshold written in the EEPROM
        <Condtype> VEE5_LOW_WARNING_1 <Probcause>
        powerProblem (36) <Alarmtype> equipmentAlarm
        (5) <Polarity> (2)
        "
	::= { pm1004dcpAlmlineXfp1SupplyAlarmEntry 10 }


pm1004dcpAlmVcc5HighAlarmPortn OBJECT-TYPE
	SYNTAX  EkiOnOff
	MAX-ACCESS read-only
	STATUS current
	DESCRIPTION
        "
        VCC5 Power Supply High :Alarm
         indicating the XFP/OTX VCC5 power
        supply is higher than the threshold
        written in the EEPROM <Condtype>
        VCC5_HIGH_ALARM_1 <Probcause> powerProblem
        (36) <Alarmtype> equipmentAlarm
        (5) <Polarity> (2)
        "
	::= { pm1004dcpAlmlineXfp1SupplyAlarmEntry 9 }


pm1004dcpAlmVcc5LowAlarmPortn OBJECT-TYPE
	SYNTAX  EkiOnOff
	MAX-ACCESS read-only
	STATUS current
	DESCRIPTION
        "
        VCC5 Power Supply Low :Alarm indicating
        the XFP/OTX VCC5 power supply is
        lower than the threshold written
        in the EEPROM <Condtype> VCC5_LOW_ALARM_1
        <Probcause> powerProblem (36) <Alarmtype>
        equipmentAlarm (5) <Polarity> (2)
        "
	::= { pm1004dcpAlmlineXfp1SupplyAlarmEntry 8 }


pm1004dcpAlmVcc3HighAlarmPortn OBJECT-TYPE
	SYNTAX  EkiOnOff
	MAX-ACCESS read-only
	STATUS current
	DESCRIPTION
        "
        VCC3 Power Supply High :Alarm
         indicating the XFP/OTX VCC3 power
        supply is higher than the threshold
        written in the EEPROM <Condtype>
        VCC3_HIGH_ALARM_1 <Probcause> powerProblem
        (36) <Alarmtype> equipmentAlarm
        (5) <Polarity> (2)
        "
	::= { pm1004dcpAlmlineXfp1SupplyAlarmEntry 7 }


pm1004dcpAlmVcc3LowAlarmPortn OBJECT-TYPE
	SYNTAX  EkiOnOff
	MAX-ACCESS read-only
	STATUS current
	DESCRIPTION
        "
        VCC3 Power Supply Low :Alarm indicating
        the XFP/OTX VCC3 power supply is
        lower than the threshold written
        in the EEPROM <Condtype> VCC3_LOW_ALARM_1
        <Probcause> powerProblem (36) <Alarmtype>
        equipmentAlarm (5) <Polarity> (2)
        "
	::= { pm1004dcpAlmlineXfp1SupplyAlarmEntry 6 }


pm1004dcpAlmVcc2HighAlarmPortn OBJECT-TYPE
	SYNTAX  EkiOnOff
	MAX-ACCESS read-only
	STATUS current
	DESCRIPTION
        "
        VCC2 Power Supply High :Alarm
         indicating the XFP/OTX VCC2 power
        supply is higher than the threshold
        written in the EEPROM <Condtype>
        VCC2_HIGH_ALARM_1 <Probcause> powerProblem
        (36) <Alarmtype> equipmentAlarm
        (5) <Polarity> (2)
        "
	::= { pm1004dcpAlmlineXfp1SupplyAlarmEntry 5 }


pm1004dcpAlmVcc2LowAlarmPortn OBJECT-TYPE
	SYNTAX  EkiOnOff
	MAX-ACCESS read-only
	STATUS current
	DESCRIPTION
        "
        VCC2 Power Supply Low :Alarm indicating
        the XFP/OTX VCC2 power supply is
        lower than the threshold written
        in the EEPROM <Condtype> VCC2_LOW_ALARM_1
        <Probcause> powerProblem (36) <Alarmtype>
        equipmentAlarm (5) <Polarity> (2)
        "
	::= { pm1004dcpAlmlineXfp1SupplyAlarmEntry 4 }


pm1004dcpAlmVee5HighAlarmPortn OBJECT-TYPE
	SYNTAX  EkiOnOff
	MAX-ACCESS read-only
	STATUS current
	DESCRIPTION
        "
        VEE5 Power Supply High :Alarm
         indicating the XFP/OTX VEE5 power
        supply is higher than the threshold
        written in the EEPROM <Condtype>
        VEE5_HIGH_ALARM_1 <Probcause> powerProblem
        (36) <Alarmtype> equipmentAlarm
        (5) <Polarity> (2)
        "
	::= { pm1004dcpAlmlineXfp1SupplyAlarmEntry 3 }


pm1004dcpAlmVee5LowAlarmPortn OBJECT-TYPE
	SYNTAX  EkiOnOff
	MAX-ACCESS read-only
	STATUS current
	DESCRIPTION
        "
        VEE5 Power Supply Low :Alarm indicating
        the XFP/OTX VEE5 power supply is
        lower than the threshold written
        in the EEPROM <Condtype> VEE5_LOW_ALARM_1
        <Probcause> powerProblem (36) <Alarmtype>
        equipmentAlarm (5) <Polarity> (2)
        "
	::= { pm1004dcpAlmlineXfp1SupplyAlarmEntry 2 }


--- *********************************************************
---     TABLE for the pm1004dcpAlmlineOtx1TlhAlarms articles
--- *********************************************************

pm1004dcpAlmlineOtx1TlhAlarmsTable OBJECT-TYPE
	SYNTAX  SEQUENCE OF Pm1004dcpAlmlineOtx1TlhAlarmsEntry
	MAX-ACCESS not-accessible
	STATUS current
	DESCRIPTION
        "
        List of pm1004dcpAlmlineOtx1TlhAlarms
        Article
        "
	::= { pm1004dcpAlmLineUrg 224 }


pm1004dcpAlmlineOtx1TlhAlarmsEntry OBJECT-TYPE
	SYNTAX Pm1004dcpAlmlineOtx1TlhAlarmsEntry
	MAX-ACCESS not-accessible
	STATUS current
	DESCRIPTION
        "
        Row definition for the pm1004dcpAlmlineOtx1TlhAlarms
        table
        "
	INDEX   { pm1004dcpAlmlineOtx1TlhAlarmsIndex }
	::= { pm1004dcpAlmlineOtx1TlhAlarmsTable 1 }


Pm1004dcpAlmlineOtx1TlhAlarmsEntry ::=
	SEQUENCE {
	pm1004dcpAlmlineOtx1TlhAlarmsIndex
		INTEGER,
	pm1004dcpAlmLineLaserTempHighAlaPortn
		EkiOnOff,
	pm1004dcpAlmLineFreqDevHighAlaPortn
		EkiOnOff,
	pm1004dcpAlmLineAgingHighAlaPortn
		EkiOnOff,
	pm1004dcpAlmLineModulatorAgingHighAlaPortn
		EkiOnOff
	}


pm1004dcpAlmlineOtx1TlhAlarmsIndex OBJECT-TYPE
	SYNTAX  INTEGER(0..128)
	MAX-ACCESS  read-only
	STATUS current
	DESCRIPTION
        "
        Index definition for the pm1004dcpAlmlineOtx1TlhAlarms
        table
        "
	::= { pm1004dcpAlmlineOtx1TlhAlarmsEntry 1 }


pm1004dcpAlmLineLaserTempHighAlaPortn OBJECT-TYPE
	SYNTAX  EkiOnOff
	MAX-ACCESS read-only
	STATUS current
	DESCRIPTION
        "
        Line Laser Temp. High Alarm :Alarm
        indicating the Line OTX TLH laser
        temperature is higher than the
         threshold written in the EEPROM
        <Condtype> LINE_LASER_TEMP_HIGH_ALA_1
        <Probcause> temperatureUnacceptable
        (51) <Alarmtype> equipmentAlarm
        (5) <Polarity> (2)
        "
	::= { pm1004dcpAlmlineOtx1TlhAlarmsEntry 15 }


pm1004dcpAlmLineFreqDevHighAlaPortn OBJECT-TYPE
	SYNTAX  EkiOnOff
	MAX-ACCESS read-only
	STATUS current
	DESCRIPTION
        "
        Line Freq. Deviation High Alarm
        :Alarm indicating the Line OTX
         TLH frequency deviation is higher
        than the threshold written in the
        EEPROM <Condtype> LINE_FREQ_DEV_HIGH_ALA_1
        <Probcause> transmitterFailure
         (56) <Alarmtype> equipmentAlarm
        (5) <Polarity> (2)
        "
	::= { pm1004dcpAlmlineOtx1TlhAlarmsEntry 13 }


pm1004dcpAlmLineAgingHighAlaPortn OBJECT-TYPE
	SYNTAX  EkiOnOff
	MAX-ACCESS read-only
	STATUS current
	DESCRIPTION
        "
        Line OTX TLH Aging High Alarm
         :Alarm indicating the Line OTX
        TLH aging is higher than the threshold
        written in the EEPROM <Condtype>
        LINE_AGING_HIGH_ALA_1 <Probcause>
        transmitterFailure (56) <Alarmtype>
        equipmentAlarm (5) <Polarity> (2)
        "
	::= { pm1004dcpAlmlineOtx1TlhAlarmsEntry 7 }


pm1004dcpAlmLineModulatorAgingHighAlaPortn OBJECT-TYPE
	SYNTAX  EkiOnOff
	MAX-ACCESS read-only
	STATUS current
	DESCRIPTION
        "
        Line Modulator Aging High Alarm
        :Alarm indicating the Line OTX
         TLH modulator aging is higher
         than the threshold written in
         the EEPROM <Condtype> LINE_MODULATOR_AGING_HIGH_ALA_1
        <Probcause> transmitterFailure
         (56) <Alarmtype> equipmentAlarm
        (5) <Polarity> (2)
        "
	::= { pm1004dcpAlmlineOtx1TlhAlarmsEntry 6 }


--- *********************************************************
---     TABLE for the pm1004dcpAlmlineOtx1TlhWarnings articles
--- *********************************************************

pm1004dcpAlmlineOtx1TlhWarningsTable OBJECT-TYPE
	SYNTAX  SEQUENCE OF Pm1004dcpAlmlineOtx1TlhWarningsEntry
	MAX-ACCESS not-accessible
	STATUS current
	DESCRIPTION
        "
        List of pm1004dcpAlmlineOtx1TlhWarnings
        Article
        "
	::= { pm1004dcpAlmLineNurg 225 }


pm1004dcpAlmlineOtx1TlhWarningsEntry OBJECT-TYPE
	SYNTAX Pm1004dcpAlmlineOtx1TlhWarningsEntry
	MAX-ACCESS not-accessible
	STATUS current
	DESCRIPTION
        "
        Row definition for the pm1004dcpAlmlineOtx1TlhWarnings
        table
        "
	INDEX   { pm1004dcpAlmlineOtx1TlhWarningsIndex }
	::= { pm1004dcpAlmlineOtx1TlhWarningsTable 1 }


Pm1004dcpAlmlineOtx1TlhWarningsEntry ::=
	SEQUENCE {
	pm1004dcpAlmlineOtx1TlhWarningsIndex
		INTEGER,
	pm1004dcpAlmLineLaserTempHighWarningPortn
		EkiOnOff,
	pm1004dcpAlmLineFreqDevHighWarningPortn
		EkiOnOff,
	pm1004dcpAlmLineAgingHighWarningPortn
		EkiOnOff,
	pm1004dcpAlmLineModulatorAgingHighWarningPortn
		EkiOnOff
	}


pm1004dcpAlmlineOtx1TlhWarningsIndex OBJECT-TYPE
	SYNTAX  INTEGER(0..128)
	MAX-ACCESS  read-only
	STATUS current
	DESCRIPTION
        "
        Index definition for the pm1004dcpAlmlineOtx1TlhWarnings
        table
        "
	::= { pm1004dcpAlmlineOtx1TlhWarningsEntry 1 }


pm1004dcpAlmLineLaserTempHighWarningPortn OBJECT-TYPE
	SYNTAX  EkiOnOff
	MAX-ACCESS read-only
	STATUS current
	DESCRIPTION
        "
        Line Laser Temp. High Warning
         :Warning indicating the Line OTX
        TLH laser temperature is higher
        than the threshold written in the
        EEPROM <Condtype> LINE_LASER_TEMP_HIGH_WARNING_1
        <Probcause> temperatureUnacceptable
        (51) <Alarmtype> equipmentAlarm
        (5) <Polarity> (2)
        "
	::= { pm1004dcpAlmlineOtx1TlhWarningsEntry 15 }


pm1004dcpAlmLineFreqDevHighWarningPortn OBJECT-TYPE
	SYNTAX  EkiOnOff
	MAX-ACCESS read-only
	STATUS current
	DESCRIPTION
        "
        Line Freq. Deviation High Warning
        :Warning indicating the Line OTX
        TLH frequency deviation is higher
        than the threshold written in the
        EEPROM <Condtype> LINE_FREQ_DEV_HIGH_WARNING_1
        <Probcause> transmitterFailure
         (56) <Alarmtype> equipmentAlarm
        (5) <Polarity> (2)
        "
	::= { pm1004dcpAlmlineOtx1TlhWarningsEntry 13 }


pm1004dcpAlmLineAgingHighWarningPortn OBJECT-TYPE
	SYNTAX  EkiOnOff
	MAX-ACCESS read-only
	STATUS current
	DESCRIPTION
        "
        Line OTX TLH Aging High Warning
        :Warning indicating the Line OTX
        TLH aging is higher than the threshold
        written in the EEPROM <Condtype>
        LINE_AGING_HIGH_WARNING_1 <Probcause>
        transmitterFailure (56) <Alarmtype>
        equipmentAlarm (5) <Polarity> (2)
        "
	::= { pm1004dcpAlmlineOtx1TlhWarningsEntry 7 }


pm1004dcpAlmLineModulatorAgingHighWarningPortn OBJECT-TYPE
	SYNTAX  EkiOnOff
	MAX-ACCESS read-only
	STATUS current
	DESCRIPTION
        "
        Line Modulator Aging High Warning
        :Warning indicating the Line OTX
        TLH modulator aging is higher than
        the threshold written in the EEPROM
        <Condtype> LINE_MODULATOR_AGING_HIGH_WARNING_1
        <Probcause> transmitterFailure
         (56) <Alarmtype> equipmentAlarm
        (5) <Polarity> (2)
        "
	::= { pm1004dcpAlmlineOtx1TlhWarningsEntry 6 }







--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pm1004dcpCtrlconfMgnt1 OBJECT IDENTIFIER ::= { pm1004dcpCtrlOther 1 }




pm1004dcpCtrlConf2Clear1 OBJECT-TYPE
	  SYNTAX EkiOnOff
	  MAX-ACCESS read-write
	  STATUS current
	  DESCRIPTION
        "
        Clear Configuration Tables :This
        OID clears the configuration tables
        from configuration2 in the flash.
         <Help>  This control restores
         the default configuration of the
        module
        "
	  ::= { pm1004dcpCtrlconfMgnt1 14 }



pm1004dcpCtrlConf2Flash1 OBJECT-TYPE
	  SYNTAX EkiOnOff
	  MAX-ACCESS read-write
	  STATUS current
	  DESCRIPTION
        "
        Write Configuration Tables :This
        OID saves the current configuration
        of the PM as configuration2 in
         the flash.  <Help>  This control
        saves the customer configuration
        on the module
        "
	  ::= { pm1004dcpCtrlconfMgnt1 10 }



pm1004dcpCtrlConf2Load1 OBJECT-TYPE
	  SYNTAX EkiOnOff
	  MAX-ACCESS read-write
	  STATUS current
	  DESCRIPTION
        "
        Load Configuration Tables Set
         Nb 2 :When set this OID enables
        loading from flash configuration2
        into the PM.
        "
	  ::= { pm1004dcpCtrlconfMgnt1 2 }



pm1004dcpCtrlConf1Load1 OBJECT-TYPE
	  SYNTAX EkiOnOff
	  MAX-ACCESS read-write
	  STATUS current
	  DESCRIPTION
        "
        Load Configuration Tables Set
         Nb 1 :When set this OID enables
        loading from flash configuration1
        into the PM.
        "
	  ::= { pm1004dcpCtrlconfMgnt1 1 }



--- *****************************************************
---     LEAF for the synth4 article
--- *****************************************************
pm1004dcpCtrlsynth4 OBJECT IDENTIFIER ::= { pm1004dcpCtrlOther 4 }




pm1004dcpCtrlCorrelatOff OBJECT-TYPE
	  SYNTAX EkiOnOff
	  MAX-ACCESS read-write
	  STATUS current
	  DESCRIPTION
        "
        Disable Alarm Correlation :This
        OID disables the alarm correlation
        in the PM.
        "
	  ::= { pm1004dcpCtrlsynth4 2 }



pm1004dcpCtrlCorrelatOn OBJECT-TYPE
	  SYNTAX EkiOnOff
	  MAX-ACCESS read-write
	  STATUS current
	  DESCRIPTION
        "
        Enable Alarm Correlation :This
        OID enables the alarm correlation
        in the PM.
        "
	  ::= { pm1004dcpCtrlsynth4 1 }



--- *****************************************************
---     LEAF for the swMgnt article
--- *****************************************************
pm1004dcpCtrlswMgnt OBJECT IDENTIFIER ::= { pm1004dcpCtrlOther 5 }




pm1004dcpCtrlLoadSwBank2 OBJECT-TYPE
	  SYNTAX EkiOnOff
	  MAX-ACCESS read-write
	  STATUS current
	  DESCRIPTION
        "
        Set Software Nb 2 As Active :This
        OID, when set, loads the SW from
        bank2 into the PM. It must be followed
        by a reset.  <Help>  This controls
        selects the second SW bank as the
        active bank for the next module
        reset
        "
	  ::= { pm1004dcpCtrlswMgnt 6 }



pm1004dcpCtrlLoadSwBank1 OBJECT-TYPE
	  SYNTAX EkiOnOff
	  MAX-ACCESS read-write
	  STATUS current
	  DESCRIPTION
        "
        Set Software Nb 1 As Active :This
        OID, when set, loads the SW from
        bank1 into the PM. It must be followed
        by a reset.  <Help>  This controls
        selects the first SW bank as the
        active bank for the next module
        reset
        "
	  ::= { pm1004dcpCtrlswMgnt 5 }



pm1004dcpCtrlWarmReset OBJECT-TYPE
	  SYNTAX EkiOnOff
	  MAX-ACCESS read-write
	  STATUS current
	  DESCRIPTION
        "
        PM Warm Reset :This OID, when
         set, causes a warm reset of the
        PM. This reset is not traffic affecting,
        and the configuration of PM remains
        unchanged.  <Help>  This control
        initiates a warm reset of the module.
        "
	  ::= { pm1004dcpCtrlswMgnt 3 }



pm1004dcpCtrlColdReset OBJECT-TYPE
	  SYNTAX EkiOnOff
	  MAX-ACCESS read-write
	  STATUS current
	  DESCRIPTION
        "
        PM Cold Reset :This OID, when
         set, causes a cold reset of the
        PM. This reset is traffic affecting,
        and the configuration of PM is
         reloaded on start-up.  <Help>
          This control initiates a cold
        reset of the module.
        "
	  ::= { pm1004dcpCtrlswMgnt 2 }



--- *****************************************************
---     LEAF for the gwMgnt article
--- *****************************************************
pm1004dcpCtrlgwMgnt OBJECT IDENTIFIER ::= { pm1004dcpCtrlOther 6 }




pm1004dcpCtrlLoadGwBank4 OBJECT-TYPE
	  SYNTAX EkiOnOff
	  MAX-ACCESS read-write
	  STATUS current
	  DESCRIPTION
        "
        Set Gateware Nb 4 As Active :This
        OID, when set, loads the GW from
        bank4 (Flash) into the PM. It is
        followed by an automatic gateware
        cold reset.
        "
	  ::= { pm1004dcpCtrlgwMgnt 8 }



pm1004dcpCtrlLoadGwBank3 OBJECT-TYPE
	  SYNTAX EkiOnOff
	  MAX-ACCESS read-write
	  STATUS current
	  DESCRIPTION
        "
        Set Gateware Nb 3 As Active :This
        OID, when set, loads the GW from
        bank3 (Flash) into the PM. It is
        followed by an automatic gateware
        cold reset.  <Help>  This controls
        initiates a cold reset of the module
        and select the third GW bank as
        the active bank
        "
	  ::= { pm1004dcpCtrlgwMgnt 7 }



pm1004dcpCtrlLoadGwBank2 OBJECT-TYPE
	  SYNTAX EkiOnOff
	  MAX-ACCESS read-write
	  STATUS current
	  DESCRIPTION
        "
        Set Gateware Nb 2 As Active :This
        OID, when set, loads the GW from
        bank2 (Flash) into the PM. It is
        followed by an automatic gateware
        cold reset.
        "
	  ::= { pm1004dcpCtrlgwMgnt 6 }



pm1004dcpCtrlLoadGwBank1 OBJECT-TYPE
	  SYNTAX EkiOnOff
	  MAX-ACCESS read-write
	  STATUS current
	  DESCRIPTION
        "
        Set Gateware Nb 1 As Active :This
        OID, when set, loads the GW from
        bank1 (Flash) into the PM. It is
        followed by an automatic gateware
        cold reset.  <Help>  This controls
        initiates a cold reset of the module
        and select the first GW bank as
        the active bank
        "
	  ::= { pm1004dcpCtrlgwMgnt 5 }



pm1004dcpCtrlCurrentGwReset OBJECT-TYPE
	  SYNTAX EkiOnOff
	  MAX-ACCESS read-write
	  STATUS current
	  DESCRIPTION
        "
        Active Gateware Reset :This OID,
        when set, resets the active gateware.
        It is traffic affecting.
        "
	  ::= { pm1004dcpCtrlgwMgnt 1 }



--- *********************************************************
---     TABLE for the pm1004dcpCtrlaccessLoop articles
--- *********************************************************

pm1004dcpCtrlaccessLoopTable OBJECT-TYPE
	SYNTAX  SEQUENCE OF Pm1004dcpCtrlaccessLoopEntry
	MAX-ACCESS not-accessible
	STATUS current
	DESCRIPTION
        "
        List of pm1004dcpCtrlaccessLoop
        Article
        "
	::= { pm1004dcpCtrlClient 16 }


pm1004dcpCtrlaccessLoopEntry OBJECT-TYPE
	SYNTAX Pm1004dcpCtrlaccessLoopEntry
	MAX-ACCESS not-accessible
	STATUS current
	DESCRIPTION
        "
        Row definition for the pm1004dcpCtrlaccessLoop
        table
        "
	INDEX   { pm1004dcpCtrlaccessLoopIndex }
	::= { pm1004dcpCtrlaccessLoopTable 1 }


Pm1004dcpCtrlaccessLoopEntry ::=
	SEQUENCE {
	pm1004dcpCtrlaccessLoopIndex
		INTEGER,
	pm1004dcpCtrlaccessLoopPortn
		EkiState
	}


pm1004dcpCtrlaccessLoopIndex OBJECT-TYPE
	SYNTAX  INTEGER(0..128)
	MAX-ACCESS  read-only
	STATUS current
	DESCRIPTION
        "
        Index definition for the pm1004dcpCtrlaccessLoop
        table
        "
	::= { pm1004dcpCtrlaccessLoopEntry 1 }


pm1004dcpCtrlaccessLoopPortn OBJECT-TYPE
	SYNTAX  EkiState
	MAX-ACCESS read-write
	STATUS current
	DESCRIPTION
        "
        Client Facility Loopback :This
        OID operates a Client Facility
         Loopback, looping client input
        signal on the client output port.
        The loop is located on the client
        transceiver  <Help> This maintenance
        parameter operates a Client Facility
        Loopback, looping client input
         signal on the client output port.
        The loop is located on the client
        transceiver
        "
	::= { pm1004dcpCtrlaccessLoopEntry 2 }


--- *********************************************************
---     TABLE for the pm1004dcpCtrlportOosMode articles
--- *********************************************************

pm1004dcpCtrlportOosModeTable OBJECT-TYPE
	SYNTAX  SEQUENCE OF Pm1004dcpCtrlportOosModeEntry
	MAX-ACCESS not-accessible
	STATUS current
	DESCRIPTION
        "
        List of pm1004dcpCtrlportOosMode
        Article
        "
	::= { pm1004dcpCtrlClient 18 }


pm1004dcpCtrlportOosModeEntry OBJECT-TYPE
	SYNTAX Pm1004dcpCtrlportOosModeEntry
	MAX-ACCESS not-accessible
	STATUS current
	DESCRIPTION
        "
        Row definition for the pm1004dcpCtrlportOosMode
        table
        "
	INDEX   { pm1004dcpCtrlportOosModeIndex }
	::= { pm1004dcpCtrlportOosModeTable 1 }


Pm1004dcpCtrlportOosModeEntry ::=
	SEQUENCE {
	pm1004dcpCtrlportOosModeIndex
		INTEGER,
	pm1004dcpCtrlportOosModePortn
		EkiState
	}


pm1004dcpCtrlportOosModeIndex OBJECT-TYPE
	SYNTAX  INTEGER(0..128)
	MAX-ACCESS  read-only
	STATUS current
	DESCRIPTION
        "
        Index definition for the pm1004dcpCtrlportOosMode
        table
        "
	::= { pm1004dcpCtrlportOosModeEntry 1 }


pm1004dcpCtrlportOosModePortn OBJECT-TYPE
	SYNTAX  EkiState
	MAX-ACCESS read-write
	STATUS current
	DESCRIPTION
        "
        Client Port Out Of Service :This
        OID sets the client port Out Of
        Service  <Help>  This controls
         defines the service state of the
        client port
        "
	::= { pm1004dcpCtrlportOosModeEntry 2 }


--- *********************************************************
---     TABLE for the pm1004dcpCtrlsfpOnCtrl articles
--- *********************************************************

pm1004dcpCtrlsfpOnCtrlTable OBJECT-TYPE
	SYNTAX  SEQUENCE OF Pm1004dcpCtrlsfpOnCtrlEntry
	MAX-ACCESS not-accessible
	STATUS current
	DESCRIPTION
        "
        List of pm1004dcpCtrlsfpOnCtrl
        Article
        "
	::= { pm1004dcpCtrlClient 19 }


pm1004dcpCtrlsfpOnCtrlEntry OBJECT-TYPE
	SYNTAX Pm1004dcpCtrlsfpOnCtrlEntry
	MAX-ACCESS not-accessible
	STATUS current
	DESCRIPTION
        "
        Row definition for the pm1004dcpCtrlsfpOnCtrl
        table
        "
	INDEX   { pm1004dcpCtrlsfpOnCtrlIndex }
	::= { pm1004dcpCtrlsfpOnCtrlTable 1 }


Pm1004dcpCtrlsfpOnCtrlEntry ::=
	SEQUENCE {
	pm1004dcpCtrlsfpOnCtrlIndex
		INTEGER,
	pm1004dcpCtrlsfpOnCtrlPortn
		EkiState
	}


pm1004dcpCtrlsfpOnCtrlIndex OBJECT-TYPE
	SYNTAX  INTEGER(0..128)
	MAX-ACCESS  read-only
	STATUS current
	DESCRIPTION
        "
        Index definition for the pm1004dcpCtrlsfpOnCtrl
        table
        "
	::= { pm1004dcpCtrlsfpOnCtrlEntry 1 }


pm1004dcpCtrlsfpOnCtrlPortn OBJECT-TYPE
	SYNTAX  EkiState
	MAX-ACCESS read-write
	STATUS current
	DESCRIPTION
        "
        Client SFP Optical Laser ON :This
        OID switches on the SFP.
        "
	::= { pm1004dcpCtrlsfpOnCtrlEntry 2 }


--- *********************************************************
---     TABLE for the pm1004dcpCtrlsfpOffCtrl articles
--- *********************************************************

pm1004dcpCtrlsfpOffCtrlTable OBJECT-TYPE
	SYNTAX  SEQUENCE OF Pm1004dcpCtrlsfpOffCtrlEntry
	MAX-ACCESS not-accessible
	STATUS current
	DESCRIPTION
        "
        List of pm1004dcpCtrlsfpOffCtrl
        Article
        "
	::= { pm1004dcpCtrlClient 20 }


pm1004dcpCtrlsfpOffCtrlEntry OBJECT-TYPE
	SYNTAX Pm1004dcpCtrlsfpOffCtrlEntry
	MAX-ACCESS not-accessible
	STATUS current
	DESCRIPTION
        "
        Row definition for the pm1004dcpCtrlsfpOffCtrl
        table
        "
	INDEX   { pm1004dcpCtrlsfpOffCtrlIndex }
	::= { pm1004dcpCtrlsfpOffCtrlTable 1 }


Pm1004dcpCtrlsfpOffCtrlEntry ::=
	SEQUENCE {
	pm1004dcpCtrlsfpOffCtrlIndex
		INTEGER,
	pm1004dcpCtrlsfpOffCtrlPortn
		EkiState
	}


pm1004dcpCtrlsfpOffCtrlIndex OBJECT-TYPE
	SYNTAX  INTEGER(0..128)
	MAX-ACCESS  read-only
	STATUS current
	DESCRIPTION
        "
        Index definition for the pm1004dcpCtrlsfpOffCtrl
        table
        "
	::= { pm1004dcpCtrlsfpOffCtrlEntry 1 }


pm1004dcpCtrlsfpOffCtrlPortn OBJECT-TYPE
	SYNTAX  EkiState
	MAX-ACCESS read-write
	STATUS current
	DESCRIPTION
        "
        Client SFP Laser Shutdown :This
        OID switches off the SFP.  <Help>
         This control defines the laser
        state of the client transceiver
        "
	::= { pm1004dcpCtrlsfpOffCtrlEntry 2 }


--- *********************************************************
---     TABLE for the pm1004dcpCtrlcsfUpIns articles
--- *********************************************************

pm1004dcpCtrlcsfUpInsTable OBJECT-TYPE
	SYNTAX  SEQUENCE OF Pm1004dcpCtrlcsfUpInsEntry
	MAX-ACCESS not-accessible
	STATUS current
	DESCRIPTION
        "
        List of pm1004dcpCtrlcsfUpIns
         Article
        "
	::= { pm1004dcpCtrlClient 21 }


pm1004dcpCtrlcsfUpInsEntry OBJECT-TYPE
	SYNTAX Pm1004dcpCtrlcsfUpInsEntry
	MAX-ACCESS not-accessible
	STATUS current
	DESCRIPTION
        "
        Row definition for the pm1004dcpCtrlcsfUpIns
        table
        "
	INDEX   { pm1004dcpCtrlcsfUpInsIndex }
	::= { pm1004dcpCtrlcsfUpInsTable 1 }


Pm1004dcpCtrlcsfUpInsEntry ::=
	SEQUENCE {
	pm1004dcpCtrlcsfUpInsIndex
		INTEGER,
	pm1004dcpCtrlcsfUpInsPortn
		EkiState
	}


pm1004dcpCtrlcsfUpInsIndex OBJECT-TYPE
	SYNTAX  INTEGER(0..128)
	MAX-ACCESS  read-only
	STATUS current
	DESCRIPTION
        "
        Index definition for the pm1004dcpCtrlcsfUpIns
        table
        "
	::= { pm1004dcpCtrlcsfUpInsEntry 1 }


pm1004dcpCtrlcsfUpInsPortn OBJECT-TYPE
	SYNTAX  EkiState
	MAX-ACCESS read-write
	STATUS current
	DESCRIPTION
        "
        Client Signal Fail Insertion :This
        OID, when set, inserts  a client
        signal fail in the upstream client
        Port.  <Help>  This control inserts
        a Client Signal Fail for the client
        port
        "
	::= { pm1004dcpCtrlcsfUpInsEntry 2 }


--- *********************************************************
---     TABLE for the pm1004dcpCtrlcaisDwIns articles
--- *********************************************************

pm1004dcpCtrlcaisDwInsTable OBJECT-TYPE
	SYNTAX  SEQUENCE OF Pm1004dcpCtrlcaisDwInsEntry
	MAX-ACCESS not-accessible
	STATUS current
	DESCRIPTION
        "
        List of pm1004dcpCtrlcaisDwIns
        Article
        "
	::= { pm1004dcpCtrlClient 22 }


pm1004dcpCtrlcaisDwInsEntry OBJECT-TYPE
	SYNTAX Pm1004dcpCtrlcaisDwInsEntry
	MAX-ACCESS not-accessible
	STATUS current
	DESCRIPTION
        "
        Row definition for the pm1004dcpCtrlcaisDwIns
        table
        "
	INDEX   { pm1004dcpCtrlcaisDwInsIndex }
	::= { pm1004dcpCtrlcaisDwInsTable 1 }


Pm1004dcpCtrlcaisDwInsEntry ::=
	SEQUENCE {
	pm1004dcpCtrlcaisDwInsIndex
		INTEGER,
	pm1004dcpCtrlcaisDwInsPortn
		EkiState
	}


pm1004dcpCtrlcaisDwInsIndex OBJECT-TYPE
	SYNTAX  INTEGER(0..128)
	MAX-ACCESS  read-only
	STATUS current
	DESCRIPTION
        "
        Index definition for the pm1004dcpCtrlcaisDwIns
        table
        "
	::= { pm1004dcpCtrlcaisDwInsEntry 1 }


pm1004dcpCtrlcaisDwInsPortn OBJECT-TYPE
	SYNTAX  EkiState
	MAX-ACCESS read-write
	STATUS current
	DESCRIPTION
        "
        Client AIS Insertion :This OID,
        when set, inserts a client AIS
         on the downstream client Port.
         <Help>  This control inserts a
        Client AIS for the client port
        "
	::= { pm1004dcpCtrlcaisDwInsEntry 2 }


--- *********************************************************
---     TABLE for the pm1004dcpCtrlclientAccessTermLoop articles
--- *********************************************************

pm1004dcpCtrlclientAccessTermLoopTable OBJECT-TYPE
	SYNTAX  SEQUENCE OF Pm1004dcpCtrlclientAccessTermLoopEntry
	MAX-ACCESS not-accessible
	STATUS current
	DESCRIPTION
        "
        List of pm1004dcpCtrlclientAccessTermLoop
        Article
        "
	::= { pm1004dcpCtrlClient 26 }


pm1004dcpCtrlclientAccessTermLoopEntry OBJECT-TYPE
	SYNTAX Pm1004dcpCtrlclientAccessTermLoopEntry
	MAX-ACCESS not-accessible
	STATUS current
	DESCRIPTION
        "
        Row definition for the pm1004dcpCtrlclientAccessTermLoop
        table
        "
	INDEX   { pm1004dcpCtrlclientAccessTermLoopIndex }
	::= { pm1004dcpCtrlclientAccessTermLoopTable 1 }


Pm1004dcpCtrlclientAccessTermLoopEntry ::=
	SEQUENCE {
	pm1004dcpCtrlclientAccessTermLoopIndex
		INTEGER,
	pm1004dcpCtrlclientAccessTermLoopPortn
		EkiState
	}


pm1004dcpCtrlclientAccessTermLoopIndex OBJECT-TYPE
	SYNTAX  INTEGER(0..128)
	MAX-ACCESS  read-only
	STATUS current
	DESCRIPTION
        "
        Index definition for the pm1004dcpCtrlclientAccessTermLoop
        table
        "
	::= { pm1004dcpCtrlclientAccessTermLoopEntry 1 }


pm1004dcpCtrlclientAccessTermLoopPortn OBJECT-TYPE
	SYNTAX  EkiState
	MAX-ACCESS read-write
	STATUS current
	DESCRIPTION
        "
        Client Terminal Loopback :This
        OID operates a Client Terminal
         Loopback, looping client input
        signal on the client output port.
        The loop is located on the line
        transceiver  <Help> This maintenance
        parameter operates a Client Terminal
        Loopback, looping client input
         signal on the client output port.
        The loop is located on the line
        transceiver
        "
	::= { pm1004dcpCtrlclientAccessTermLoopEntry 2 }


--- *********************************************************
---     TABLE for the pm1004dcpCtrlresetCount15Port articles
--- *********************************************************

pm1004dcpCtrlresetCount15PortTable OBJECT-TYPE
	SYNTAX  SEQUENCE OF Pm1004dcpCtrlresetCount15PortEntry
	MAX-ACCESS not-accessible
	STATUS current
	DESCRIPTION
        "
        List of pm1004dcpCtrlresetCount15Port
        Article
        "
	::= { pm1004dcpCtrlClient 35 }


pm1004dcpCtrlresetCount15PortEntry OBJECT-TYPE
	SYNTAX Pm1004dcpCtrlresetCount15PortEntry
	MAX-ACCESS not-accessible
	STATUS current
	DESCRIPTION
        "
        Row definition for the pm1004dcpCtrlresetCount15Port
        table
        "
	INDEX   { pm1004dcpCtrlresetCount15PortIndex }
	::= { pm1004dcpCtrlresetCount15PortTable 1 }


Pm1004dcpCtrlresetCount15PortEntry ::=
	SEQUENCE {
	pm1004dcpCtrlresetCount15PortIndex
		INTEGER,
	pm1004dcpCtrlclientResetAllPerfCount15Portn
		EkiState
	}


pm1004dcpCtrlresetCount15PortIndex OBJECT-TYPE
	SYNTAX  INTEGER(0..128)
	MAX-ACCESS  read-only
	STATUS current
	DESCRIPTION
        "
        Index definition for the pm1004dcpCtrlresetCount15Port
        table
        "
	::= { pm1004dcpCtrlresetCount15PortEntry 1 }


pm1004dcpCtrlclientResetAllPerfCount15Portn OBJECT-TYPE
	SYNTAX  EkiState
	MAX-ACCESS read-write
	STATUS current
	DESCRIPTION
        "
        Client 15-min Counters Reset :This
        OID resets all the current 15-min
        Counters on the client port
        "
	::= { pm1004dcpCtrlresetCount15PortEntry 2 }


--- *********************************************************
---     TABLE for the pm1004dcpCtrlresetCount24Port articles
--- *********************************************************

pm1004dcpCtrlresetCount24PortTable OBJECT-TYPE
	SYNTAX  SEQUENCE OF Pm1004dcpCtrlresetCount24PortEntry
	MAX-ACCESS not-accessible
	STATUS current
	DESCRIPTION
        "
        List of pm1004dcpCtrlresetCount24Port
        Article
        "
	::= { pm1004dcpCtrlClient 36 }


pm1004dcpCtrlresetCount24PortEntry OBJECT-TYPE
	SYNTAX Pm1004dcpCtrlresetCount24PortEntry
	MAX-ACCESS not-accessible
	STATUS current
	DESCRIPTION
        "
        Row definition for the pm1004dcpCtrlresetCount24Port
        table
        "
	INDEX   { pm1004dcpCtrlresetCount24PortIndex }
	::= { pm1004dcpCtrlresetCount24PortTable 1 }


Pm1004dcpCtrlresetCount24PortEntry ::=
	SEQUENCE {
	pm1004dcpCtrlresetCount24PortIndex
		INTEGER,
	pm1004dcpCtrlclientResetAllPerfCount24Portn
		EkiState
	}


pm1004dcpCtrlresetCount24PortIndex OBJECT-TYPE
	SYNTAX  INTEGER(0..128)
	MAX-ACCESS  read-only
	STATUS current
	DESCRIPTION
        "
        Index definition for the pm1004dcpCtrlresetCount24Port
        table
        "
	::= { pm1004dcpCtrlresetCount24PortEntry 1 }


pm1004dcpCtrlclientResetAllPerfCount24Portn OBJECT-TYPE
	SYNTAX  EkiState
	MAX-ACCESS read-write
	STATUS current
	DESCRIPTION
        "
        Client 24-hours Counters Reset
        :This OID resets all the current
        24-hours Counters on the client
        port
        "
	::= { pm1004dcpCtrlresetCount24PortEntry 2 }


--- *****************************************************
---     LEAF for the commAccessLoop article
--- *****************************************************
pm1004dcpCtrlcommAccessLoop OBJECT IDENTIFIER ::= { pm1004dcpCtrlLine 64 }




pm1004dcpCtrlCommAccessloop OBJECT-TYPE
	  SYNTAX EkiOnOff
	  MAX-ACCESS read-write
	  STATUS deprecated
	  DESCRIPTION
        "
        PM Full Access Loop Mode :This
        OID, when set, puts the module
         in common access loop back, looping
        the 10 Gb/s output signal on the
        10 Gb/s input.
        "
	  ::= { pm1004dcpCtrlcommAccessLoop 1 }



--- *****************************************************
---     LEAF for the lineLoop article
--- *****************************************************
pm1004dcpCtrllineLoop OBJECT IDENTIFIER ::= { pm1004dcpCtrlLine 66 }




pm1004dcpCtrlLineLoop OBJECT-TYPE
	  SYNTAX EkiOnOff
	  MAX-ACCESS read-write
	  STATUS deprecated
	  DESCRIPTION
        "
        PM Line Loop Mode :This OID, when
        set at '1' puts the module in line
        loopback mode, looping the received
        10 Gb/s signal on the transmit
         10 Gb/s output. The Upstream part
        of the module is timed on the 10
        Gb/s recovered clock in that case.
        "
	  ::= { pm1004dcpCtrllineLoop 1 }



--- *****************************************************
---     LEAF for the msAis article
--- *****************************************************
pm1004dcpCtrlmsAis OBJECT IDENTIFIER ::= { pm1004dcpCtrlLine 67 }




pm1004dcpCtrlMsAis OBJECT-TYPE
	  SYNTAX EkiOnOff
	  MAX-ACCESS read-write
	  STATUS current
	  DESCRIPTION
        "
        Insert MS-AIS/L-AIS On Line Output
        :This OID, when set, inserts an
        MS-AIS/L-AIS in the outgoing STM-64/OC-192
        signal.
        "
	  ::= { pm1004dcpCtrlmsAis 1 }



--- *********************************************************
---     TABLE for the pm1004dcpCtrlfecDisable articles
--- *********************************************************

pm1004dcpCtrlfecDisableTable OBJECT-TYPE
	SYNTAX  SEQUENCE OF Pm1004dcpCtrlfecDisableEntry
	MAX-ACCESS not-accessible
	STATUS current
	DESCRIPTION
        "
        List of pm1004dcpCtrlfecDisable
        Article
        "
	::= { pm1004dcpCtrlLine 69 }


pm1004dcpCtrlfecDisableEntry OBJECT-TYPE
	SYNTAX Pm1004dcpCtrlfecDisableEntry
	MAX-ACCESS not-accessible
	STATUS current
	DESCRIPTION
        "
        Row definition for the pm1004dcpCtrlfecDisable
        table
        "
	INDEX   { pm1004dcpCtrlfecDisableIndex }
	::= { pm1004dcpCtrlfecDisableTable 1 }


Pm1004dcpCtrlfecDisableEntry ::=
	SEQUENCE {
	pm1004dcpCtrlfecDisableIndex
		INTEGER,
	pm1004dcpCtrlfecDisablePortn
		EkiState
	}


pm1004dcpCtrlfecDisableIndex OBJECT-TYPE
	SYNTAX  INTEGER(0..128)
	MAX-ACCESS  read-only
	STATUS current
	DESCRIPTION
        "
        Index definition for the pm1004dcpCtrlfecDisable
        table
        "
	::= { pm1004dcpCtrlfecDisableEntry 1 }


pm1004dcpCtrlfecDisablePortn OBJECT-TYPE
	SYNTAX  EkiState
	MAX-ACCESS read-write
	STATUS current
	DESCRIPTION
        "
        Forward Error Correction Inhibition
        :This OID, when set, inhibits the
        Forward Error Correction feature
        on the line input  <Help>  This
        control enables/disables the Forward
        Error Correction on the line interface
        "
	::= { pm1004dcpCtrlfecDisableEntry 2 }


--- *********************************************************
---     TABLE for the pm1004dcpCtrllineOosMode articles
--- *********************************************************

pm1004dcpCtrllineOosModeTable OBJECT-TYPE
	SYNTAX  SEQUENCE OF Pm1004dcpCtrllineOosModeEntry
	MAX-ACCESS not-accessible
	STATUS current
	DESCRIPTION
        "
        List of pm1004dcpCtrllineOosMode
        Article
        "
	::= { pm1004dcpCtrlLine 74 }


pm1004dcpCtrllineOosModeEntry OBJECT-TYPE
	SYNTAX Pm1004dcpCtrllineOosModeEntry
	MAX-ACCESS not-accessible
	STATUS current
	DESCRIPTION
        "
        Row definition for the pm1004dcpCtrllineOosMode
        table
        "
	INDEX   { pm1004dcpCtrllineOosModeIndex }
	::= { pm1004dcpCtrllineOosModeTable 1 }


Pm1004dcpCtrllineOosModeEntry ::=
	SEQUENCE {
	pm1004dcpCtrllineOosModeIndex
		INTEGER,
	pm1004dcpCtrllineOosModePortn
		EkiState
	}


pm1004dcpCtrllineOosModeIndex OBJECT-TYPE
	SYNTAX  INTEGER(0..128)
	MAX-ACCESS  read-only
	STATUS current
	DESCRIPTION
        "
        Index definition for the pm1004dcpCtrllineOosMode
        table
        "
	::= { pm1004dcpCtrllineOosModeEntry 1 }


pm1004dcpCtrllineOosModePortn OBJECT-TYPE
	SYNTAX  EkiState
	MAX-ACCESS read-write
	STATUS current
	DESCRIPTION
        "
        Line Port Out Of Service :This
        OID sets the line port Out Of Service
         <Help>  This control defines the
        service state of the line port
        "
	::= { pm1004dcpCtrllineOosModeEntry 2 }


--- *********************************************************
---     TABLE for the pm1004dcpCtrllineResetCount15Line articles
--- *********************************************************

pm1004dcpCtrllineResetCount15LineTable OBJECT-TYPE
	SYNTAX  SEQUENCE OF Pm1004dcpCtrllineResetCount15LineEntry
	MAX-ACCESS not-accessible
	STATUS current
	DESCRIPTION
        "
        List of pm1004dcpCtrllineResetCount15Line
        Article
        "
	::= { pm1004dcpCtrlLine 86 }


pm1004dcpCtrllineResetCount15LineEntry OBJECT-TYPE
	SYNTAX Pm1004dcpCtrllineResetCount15LineEntry
	MAX-ACCESS not-accessible
	STATUS current
	DESCRIPTION
        "
        Row definition for the pm1004dcpCtrllineResetCount15Line
        table
        "
	INDEX   { pm1004dcpCtrllineResetCount15LineIndex }
	::= { pm1004dcpCtrllineResetCount15LineTable 1 }


Pm1004dcpCtrllineResetCount15LineEntry ::=
	SEQUENCE {
	pm1004dcpCtrllineResetCount15LineIndex
		INTEGER,
	pm1004dcpCtrlresetAllPerfCount15Portn
		EkiState
	}


pm1004dcpCtrllineResetCount15LineIndex OBJECT-TYPE
	SYNTAX  INTEGER(0..128)
	MAX-ACCESS  read-only
	STATUS current
	DESCRIPTION
        "
        Index definition for the pm1004dcpCtrllineResetCount15Line
        table
        "
	::= { pm1004dcpCtrllineResetCount15LineEntry 1 }


pm1004dcpCtrlresetAllPerfCount15Portn OBJECT-TYPE
	SYNTAX  EkiState
	MAX-ACCESS read-write
	STATUS current
	DESCRIPTION
        "
        Line 15-min Counters Reset :This
        OID resets all the current 15-min
        Counters on the client port
        "
	::= { pm1004dcpCtrllineResetCount15LineEntry 2 }


--- *********************************************************
---     TABLE for the pm1004dcpCtrllineResetCount24Line articles
--- *********************************************************

pm1004dcpCtrllineResetCount24LineTable OBJECT-TYPE
	SYNTAX  SEQUENCE OF Pm1004dcpCtrllineResetCount24LineEntry
	MAX-ACCESS not-accessible
	STATUS current
	DESCRIPTION
        "
        List of pm1004dcpCtrllineResetCount24Line
        Article
        "
	::= { pm1004dcpCtrlLine 87 }


pm1004dcpCtrllineResetCount24LineEntry OBJECT-TYPE
	SYNTAX Pm1004dcpCtrllineResetCount24LineEntry
	MAX-ACCESS not-accessible
	STATUS current
	DESCRIPTION
        "
        Row definition for the pm1004dcpCtrllineResetCount24Line
        table
        "
	INDEX   { pm1004dcpCtrllineResetCount24LineIndex }
	::= { pm1004dcpCtrllineResetCount24LineTable 1 }


Pm1004dcpCtrllineResetCount24LineEntry ::=
	SEQUENCE {
	pm1004dcpCtrllineResetCount24LineIndex
		INTEGER,
	pm1004dcpCtrlresetAllPerfCount24Portn
		EkiState
	}


pm1004dcpCtrllineResetCount24LineIndex OBJECT-TYPE
	SYNTAX  INTEGER(0..128)
	MAX-ACCESS  read-only
	STATUS current
	DESCRIPTION
        "
        Index definition for the pm1004dcpCtrllineResetCount24Line
        table
        "
	::= { pm1004dcpCtrllineResetCount24LineEntry 1 }


pm1004dcpCtrlresetAllPerfCount24Portn OBJECT-TYPE
	SYNTAX  EkiState
	MAX-ACCESS read-write
	STATUS current
	DESCRIPTION
        "
        Line 24-hours Counters Reset :This
        OID resets all the current 24-hours
        Counters on the client port
        "
	::= { pm1004dcpCtrllineResetCount24LineEntry 2 }


--- *********************************************************
---     TABLE for the pm1004dcpCtrladddropTsClientARxProtect articles
--- *********************************************************

pm1004dcpCtrladddropTsClientARxProtectTable OBJECT-TYPE
	SYNTAX  SEQUENCE OF Pm1004dcpCtrladddropTsClientARxProtectEntry
	MAX-ACCESS not-accessible
	STATUS current
	DESCRIPTION
        "
        List of pm1004dcpCtrladddropTsClientARxProtect
        Article
        "
	::= { pm1004dcpCtrlClient 128 }


pm1004dcpCtrladddropTsClientARxProtectEntry OBJECT-TYPE
	SYNTAX Pm1004dcpCtrladddropTsClientARxProtectEntry
	MAX-ACCESS not-accessible
	STATUS current
	DESCRIPTION
        "
        Row definition for the pm1004dcpCtrladddropTsClientARxProtect
        table
        "
	INDEX   { pm1004dcpCtrladddropTsClientARxProtectIndex }
	::= { pm1004dcpCtrladddropTsClientARxProtectTable 1 }


Pm1004dcpCtrladddropTsClientARxProtectEntry ::=
	SEQUENCE {
	pm1004dcpCtrladddropTsClientARxProtectIndex
		INTEGER,
	pm1004dcpCtrladddropTsClientARxProtectPortn
		Pm1004dcpProtectionTimeSlot
	}


pm1004dcpCtrladddropTsClientARxProtectIndex OBJECT-TYPE
	SYNTAX  INTEGER(0..128)
	MAX-ACCESS  read-only
	STATUS current
	DESCRIPTION
        "
        Index definition for the pm1004dcpCtrladddropTsClientARxProtect
        table
        "
	::= { pm1004dcpCtrladddropTsClientARxProtectEntry 1 }


pm1004dcpCtrladddropTsClientARxProtectPortn OBJECT-TYPE
	SYNTAX  Pm1004dcpProtectionTimeSlot
	MAX-ACCESS read-write
	STATUS current
	DESCRIPTION
        "
        Client A Switch Mode :This bit
        selects the manual (1) or automatic
        (0) switch method  <Help>  This
        control defines the protection
         switch mode on the client interface
        "
	::= { pm1004dcpCtrladddropTsClientARxProtectEntry 2 }


--- *********************************************************
---     TABLE for the pm1004dcpCtrladddropTsPairMode articles
--- *********************************************************

pm1004dcpCtrladddropTsPairModeTable OBJECT-TYPE
	SYNTAX  SEQUENCE OF Pm1004dcpCtrladddropTsPairModeEntry
	MAX-ACCESS not-accessible
	STATUS current
	DESCRIPTION
        "
        List of pm1004dcpCtrladddropTsPairMode
        Article
        "
	::= { pm1004dcpCtrlClient 136 }


pm1004dcpCtrladddropTsPairModeEntry OBJECT-TYPE
	SYNTAX Pm1004dcpCtrladddropTsPairModeEntry
	MAX-ACCESS not-accessible
	STATUS current
	DESCRIPTION
        "
        Row definition for the pm1004dcpCtrladddropTsPairMode
        table
        "
	INDEX   { pm1004dcpCtrladddropTsPairModeIndex }
	::= { pm1004dcpCtrladddropTsPairModeTable 1 }


Pm1004dcpCtrladddropTsPairModeEntry ::=
	SEQUENCE {
	pm1004dcpCtrladddropTsPairModeIndex
		INTEGER,
	pm1004dcpCtrladddropTsPairModePortn
		Pm1004dcpModeTimeSlot
	}


pm1004dcpCtrladddropTsPairModeIndex OBJECT-TYPE
	SYNTAX  INTEGER(0..128)
	MAX-ACCESS  read-only
	STATUS current
	DESCRIPTION
        "
        Index definition for the pm1004dcpCtrladddropTsPairMode
        table
        "
	::= { pm1004dcpCtrladddropTsPairModeEntry 1 }


pm1004dcpCtrladddropTsPairModePortn OBJECT-TYPE
	SYNTAX  Pm1004dcpModeTimeSlot
	MAX-ACCESS read-write
	STATUS current
	DESCRIPTION
        "
        TS Group Mode :This OID selects
        the mode on the group of clients
         <Help>   This control defines
         the mode (Add/Drop or Split&Select)
        of two consecutive Client (1/2
         , 3/4 , 5/6 , 7/8)
        "
	::= { pm1004dcpCtrladddropTsPairModeEntry 2 }


--- *****************************************************
---     LEAF for the ledTest article
--- *****************************************************
pm1004dcpCtrlledTest OBJECT IDENTIFIER ::= { pm1004dcpCtrlOther 192 }




pm1004dcpCtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { pm1004dcpCtrlledTest 3 }



pm1004dcpCtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { pm1004dcpCtrlledTest 2 }



pm1004dcpCtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { pm1004dcpCtrlledTest 1 }



--- *****************************************************
---     LEAF for the moduleOosMode article
--- *****************************************************
pm1004dcpCtrlmoduleOosMode OBJECT IDENTIFIER ::= { pm1004dcpCtrlOther 193 }




pm1004dcpCtrlModuleOosMode OBJECT-TYPE
	  SYNTAX EkiOnOff
	  MAX-ACCESS read-write
	  STATUS current
	  DESCRIPTION
        "
        PM Out Of Service :This OID sets
        the PM Out Of Service  <Help>
         This control defines the service
        state of the complete module
        "
	  ::= { pm1004dcpCtrlmoduleOosMode 1 }



--- *****************************************************
---     LEAF for the moduleDccMgnt article
--- *****************************************************

pm1004dcpCtrlmoduleDccMgnt OBJECT-TYPE
	  SYNTAX Pm1004dcpDccMode
	  MAX-ACCESS read-write
	  STATUS current
	  DESCRIPTION
        "
        DCC Mode :This OID defines the
        DCC mode of the PM (No DCC, Master,
        Slave Line 1&2, Terminal Line 1,
        Terminal Line 2, Terminal Line
         1&2)   <Help>  This control defines
        the DCC mode of the PM (No DCC,
        Master, Slave Line 1&2, Terminal
        Line 1, Terminal Line 2 or Terminal
        Line 1&2)

        "
	  ::= { pm1004dcpCtrlOther 196 }



--- *****************************************************
---     LEAF for the maintenanceMode article
--- *****************************************************
pm1004dcpCtrlmaintenanceMode OBJECT IDENTIFIER ::= { pm1004dcpCtrlOther 197 }




pm1004dcpCtrlMaintenanceMode OBJECT-TYPE
	  SYNTAX EkiOnOff
	  MAX-ACCESS read-write
	  STATUS current
	  DESCRIPTION
        "
        Module Maintenance Mode :This
         OID enables the maintenance mode
        on the PM.  <Help>  This control
        enables the maintenance mode on
        the PM.
        "
	  ::= { pm1004dcpCtrlmaintenanceMode 1 }



--- *********************************************************
---     TABLE for the pm1004dcpCtrlxfpOnoff articles
--- *********************************************************

pm1004dcpCtrlxfpOnoffTable OBJECT-TYPE
	SYNTAX  SEQUENCE OF Pm1004dcpCtrlxfpOnoffEntry
	MAX-ACCESS not-accessible
	STATUS current
	DESCRIPTION
        "
        List of pm1004dcpCtrlxfpOnoff
         Article
        "
	::= { pm1004dcpCtrlLine 208 }


pm1004dcpCtrlxfpOnoffEntry OBJECT-TYPE
	SYNTAX Pm1004dcpCtrlxfpOnoffEntry
	MAX-ACCESS not-accessible
	STATUS current
	DESCRIPTION
        "
        Row definition for the pm1004dcpCtrlxfpOnoff
        table
        "
	INDEX   { pm1004dcpCtrlxfpOnoffIndex }
	::= { pm1004dcpCtrlxfpOnoffTable 1 }


Pm1004dcpCtrlxfpOnoffEntry ::=
	SEQUENCE {
	pm1004dcpCtrlxfpOnoffIndex
		INTEGER,
	pm1004dcpCtrlxfpOnoffPortn
		EkiState
	}


pm1004dcpCtrlxfpOnoffIndex OBJECT-TYPE
	SYNTAX  INTEGER(0..128)
	MAX-ACCESS  read-only
	STATUS current
	DESCRIPTION
        "
        Index definition for the pm1004dcpCtrlxfpOnoff
        table
        "
	::= { pm1004dcpCtrlxfpOnoffEntry 1 }


pm1004dcpCtrlxfpOnoffPortn OBJECT-TYPE
	SYNTAX  EkiState
	MAX-ACCESS read-write
	STATUS current
	DESCRIPTION
        "
        Line Optical Laser Shutdown :This
        OID switches off the XFP or the
        OTX  <Help>  This control defines
        the laser state of the line transceiver
        "
	::= { pm1004dcpCtrlxfpOnoffEntry 2 }


--- *********************************************************
---     TABLE for the pm1004dcpCtrlxfpLineLoop articles
--- *********************************************************

pm1004dcpCtrlxfpLineLoopTable OBJECT-TYPE
	SYNTAX  SEQUENCE OF Pm1004dcpCtrlxfpLineLoopEntry
	MAX-ACCESS not-accessible
	STATUS current
	DESCRIPTION
        "
        List of pm1004dcpCtrlxfpLineLoop
        Article
        "
	::= { pm1004dcpCtrlLine 209 }


pm1004dcpCtrlxfpLineLoopEntry OBJECT-TYPE
	SYNTAX Pm1004dcpCtrlxfpLineLoopEntry
	MAX-ACCESS not-accessible
	STATUS current
	DESCRIPTION
        "
        Row definition for the pm1004dcpCtrlxfpLineLoop
        table
        "
	INDEX   { pm1004dcpCtrlxfpLineLoopIndex }
	::= { pm1004dcpCtrlxfpLineLoopTable 1 }


Pm1004dcpCtrlxfpLineLoopEntry ::=
	SEQUENCE {
	pm1004dcpCtrlxfpLineLoopIndex
		INTEGER,
	pm1004dcpCtrlxfpLineLoopPortn
		EkiState
	}


pm1004dcpCtrlxfpLineLoopIndex OBJECT-TYPE
	SYNTAX  INTEGER(0..128)
	MAX-ACCESS  read-only
	STATUS current
	DESCRIPTION
        "
        Index definition for the pm1004dcpCtrlxfpLineLoop
        table
        "
	::= { pm1004dcpCtrlxfpLineLoopEntry 1 }


pm1004dcpCtrlxfpLineLoopPortn OBJECT-TYPE
	SYNTAX  EkiState
	MAX-ACCESS read-write
	STATUS current
	DESCRIPTION
        "
        Line Facility Loopback :This OID
        operates a Line Facility Loopback,
        looping line input signal on the
        line output port. The loop is located
        on the line transceiver. If the
        Line signal carries DCC, the management
        network is impacted  <Help> This
        maintenance parameter operates
         a Line Facility Loopback, looping
        line input signal on the line output
        port. The loop is located on the
        line transceiver. If the Line signal
        carries DCC, the management network
        is impacted
        "
	::= { pm1004dcpCtrlxfpLineLoopEntry 2 }


--- *********************************************************
---     TABLE for the pm1004dcpCtrlxfpXfiLoop articles
--- *********************************************************

pm1004dcpCtrlxfpXfiLoopTable OBJECT-TYPE
	SYNTAX  SEQUENCE OF Pm1004dcpCtrlxfpXfiLoopEntry
	MAX-ACCESS not-accessible
	STATUS current
	DESCRIPTION
        "
        List of pm1004dcpCtrlxfpXfiLoop
        Article
        "
	::= { pm1004dcpCtrlLine 210 }


pm1004dcpCtrlxfpXfiLoopEntry OBJECT-TYPE
	SYNTAX Pm1004dcpCtrlxfpXfiLoopEntry
	MAX-ACCESS not-accessible
	STATUS current
	DESCRIPTION
        "
        Row definition for the pm1004dcpCtrlxfpXfiLoop
        table
        "
	INDEX   { pm1004dcpCtrlxfpXfiLoopIndex }
	::= { pm1004dcpCtrlxfpXfiLoopTable 1 }


Pm1004dcpCtrlxfpXfiLoopEntry ::=
	SEQUENCE {
	pm1004dcpCtrlxfpXfiLoopIndex
		INTEGER,
	pm1004dcpCtrlxfpXfiLoopPortn
		EkiState
	}


pm1004dcpCtrlxfpXfiLoopIndex OBJECT-TYPE
	SYNTAX  INTEGER(0..128)
	MAX-ACCESS  read-only
	STATUS current
	DESCRIPTION
        "
        Index definition for the pm1004dcpCtrlxfpXfiLoop
        table
        "
	::= { pm1004dcpCtrlxfpXfiLoopEntry 1 }


pm1004dcpCtrlxfpXfiLoopPortn OBJECT-TYPE
	SYNTAX  EkiState
	MAX-ACCESS read-write
	STATUS current
	DESCRIPTION
        "
        Line Terminal Loopback :This OID
        operates a Line Terminal Loopback,
        looping line input signal on the
        line output port. The loop is located
        on all client transceivers  <Help>
        This maintenance parameter operates
        a Line Terminal Loopback, looping
        line input signal on the line output
        port. The loop is located on all
        client transceivers.
        "
	::= { pm1004dcpCtrlxfpXfiLoopEntry 2 }


--- *********************************************************
---     TABLE for the pm1004dcpCtrllineTunableChannel articles
--- *********************************************************

pm1004dcpCtrllineTunableChannelTable OBJECT-TYPE
	SYNTAX  SEQUENCE OF Pm1004dcpCtrllineTunableChannelEntry
	MAX-ACCESS not-accessible
	STATUS current
	DESCRIPTION
        "
        List of pm1004dcpCtrllineTunableChannel
        Article
        "
	::= { pm1004dcpCtrlLine 212 }


pm1004dcpCtrllineTunableChannelEntry OBJECT-TYPE
	SYNTAX Pm1004dcpCtrllineTunableChannelEntry
	MAX-ACCESS not-accessible
	STATUS current
	DESCRIPTION
        "
        Row definition for the pm1004dcpCtrllineTunableChannel
        table
        "
	INDEX   { pm1004dcpCtrllineTunableChannelIndex }
	::= { pm1004dcpCtrllineTunableChannelTable 1 }


Pm1004dcpCtrllineTunableChannelEntry ::=
	SEQUENCE {
	pm1004dcpCtrllineTunableChannelIndex
		INTEGER,
	pm1004dcpCtrllineTunableChannelPortn
		Pm1004dcpOtxChannel
	}


pm1004dcpCtrllineTunableChannelIndex OBJECT-TYPE
	SYNTAX  INTEGER(0..128)
	MAX-ACCESS  read-only
	STATUS current
	DESCRIPTION
        "
        Index definition for the pm1004dcpCtrllineTunableChannel
        table
        "
	::= { pm1004dcpCtrllineTunableChannelEntry 1 }


pm1004dcpCtrllineTunableChannelPortn OBJECT-TYPE
	SYNTAX  Pm1004dcpOtxChannel
	MAX-ACCESS read-write
	STATUS current
	DESCRIPTION
        "
        ITU Channel :This OID selects
         the ITU channel of the Line OTX
        TLH Laser  <Help>   This control
        defines the ITU channel of the
         Line OTX TLH Laser
        "
	::= { pm1004dcpCtrllineTunableChannelEntry 2 }


--- *********************************************************
---     TABLE for the pm1004dcpCtrllinePhotodiodeMode articles
--- *********************************************************

pm1004dcpCtrllinePhotodiodeModeTable OBJECT-TYPE
	SYNTAX  SEQUENCE OF Pm1004dcpCtrllinePhotodiodeModeEntry
	MAX-ACCESS not-accessible
	STATUS current
	DESCRIPTION
        "
        List of pm1004dcpCtrllinePhotodiodeMode
        Article
        "
	::= { pm1004dcpCtrlLine 213 }


pm1004dcpCtrllinePhotodiodeModeEntry OBJECT-TYPE
	SYNTAX Pm1004dcpCtrllinePhotodiodeModeEntry
	MAX-ACCESS not-accessible
	STATUS current
	DESCRIPTION
        "
        Row definition for the pm1004dcpCtrllinePhotodiodeMode
        table
        "
	INDEX   { pm1004dcpCtrllinePhotodiodeModeIndex }
	::= { pm1004dcpCtrllinePhotodiodeModeTable 1 }


Pm1004dcpCtrllinePhotodiodeModeEntry ::=
	SEQUENCE {
	pm1004dcpCtrllinePhotodiodeModeIndex
		INTEGER,
	pm1004dcpCtrllinePhotodiodeModePortn
		Pm1004dcpOtxMode
	}


pm1004dcpCtrllinePhotodiodeModeIndex OBJECT-TYPE
	SYNTAX  INTEGER(0..128)
	MAX-ACCESS  read-only
	STATUS current
	DESCRIPTION
        "
        Index definition for the pm1004dcpCtrllinePhotodiodeMode
        table
        "
	::= { pm1004dcpCtrllinePhotodiodeModeEntry 1 }


pm1004dcpCtrllinePhotodiodeModePortn OBJECT-TYPE
	SYNTAX  Pm1004dcpOtxMode
	MAX-ACCESS read-write
	STATUS current
	DESCRIPTION
        "
        OTX TLH Rx Sens. Mode :This OID
        defines the Rx sensiblity mode
         of the Line OTX TLH  <Help>
         This control defines the receiver
        sensibility mode of the Line OTX
        TLH Laser (OTX60, OTX80 or Custom)
        "
	::= { pm1004dcpCtrllinePhotodiodeModeEntry 2 }


--- *********************************************************
---     TABLE for the pm1004dcpCtrllinePhotodiodeValue articles
--- *********************************************************

pm1004dcpCtrllinePhotodiodeValueTable OBJECT-TYPE
	SYNTAX  SEQUENCE OF Pm1004dcpCtrllinePhotodiodeValueEntry
	MAX-ACCESS not-accessible
	STATUS current
	DESCRIPTION
        "
        List of pm1004dcpCtrllinePhotodiodeValue
        Article
        "
	::= { pm1004dcpCtrlLine 214 }


pm1004dcpCtrllinePhotodiodeValueEntry OBJECT-TYPE
	SYNTAX Pm1004dcpCtrllinePhotodiodeValueEntry
	MAX-ACCESS not-accessible
	STATUS current
	DESCRIPTION
        "
        Row definition for the pm1004dcpCtrllinePhotodiodeValue
        table
        "
	INDEX   { pm1004dcpCtrllinePhotodiodeValueIndex }
	::= { pm1004dcpCtrllinePhotodiodeValueTable 1 }


Pm1004dcpCtrllinePhotodiodeValueEntry ::=
	SEQUENCE {
	pm1004dcpCtrllinePhotodiodeValueIndex
		INTEGER,
	pm1004dcpCtrllinePhotodiodeValuePortn
		Pm1004dcpAdjustValue
	}


pm1004dcpCtrllinePhotodiodeValueIndex OBJECT-TYPE
	SYNTAX  INTEGER(0..128)
	MAX-ACCESS  read-only
	STATUS current
	DESCRIPTION
        "
        Index definition for the pm1004dcpCtrllinePhotodiodeValue
        table
        "
	::= { pm1004dcpCtrllinePhotodiodeValueEntry 1 }


pm1004dcpCtrllinePhotodiodeValuePortn OBJECT-TYPE
	SYNTAX  Pm1004dcpAdjustValue
	MAX-ACCESS read-write
	STATUS current
	DESCRIPTION
        "
        OTX TLH Rx Sensibility :This OID
        sets the Rx sensibility of the
         Line OTX TLH (custom mode only)
         <Help>   This control defines
         the receiver sensibility value
        (only in Custom mode) of the Line
        OTX TLH Laser
        "
	::= { pm1004dcpCtrllinePhotodiodeValueEntry 2 }


--- *********************************************************
---     TABLE for the pm1004dcpCtrllinePowerLaser articles
--- *********************************************************

pm1004dcpCtrllinePowerLaserTable OBJECT-TYPE
	SYNTAX  SEQUENCE OF Pm1004dcpCtrllinePowerLaserEntry
	MAX-ACCESS not-accessible
	STATUS current
	DESCRIPTION
        "
        List of pm1004dcpCtrllinePowerLaser
        Article
        "
	::= { pm1004dcpCtrlLine 215 }


pm1004dcpCtrllinePowerLaserEntry OBJECT-TYPE
	SYNTAX Pm1004dcpCtrllinePowerLaserEntry
	MAX-ACCESS not-accessible
	STATUS current
	DESCRIPTION
        "
        Row definition for the pm1004dcpCtrllinePowerLaser
        table
        "
	INDEX   { pm1004dcpCtrllinePowerLaserIndex }
	::= { pm1004dcpCtrllinePowerLaserTable 1 }


Pm1004dcpCtrllinePowerLaserEntry ::=
	SEQUENCE {
	pm1004dcpCtrllinePowerLaserIndex
		INTEGER,
	pm1004dcpCtrllinePowerLaserPortn
		INTEGER
	}


pm1004dcpCtrllinePowerLaserIndex OBJECT-TYPE
	SYNTAX  INTEGER(0..128)
	MAX-ACCESS  read-only
	STATUS current
	DESCRIPTION
        "
        Index definition for the pm1004dcpCtrllinePowerLaser
        table
        "
	::= { pm1004dcpCtrllinePowerLaserEntry 1 }


pm1004dcpCtrllinePowerLaserPortn OBJECT-TYPE
	SYNTAX  INTEGER (0..255)
	MAX-ACCESS read-write
	STATUS current
	DESCRIPTION
        "
        Line Laser Output Power [3-5]
         :This OID sets the output power
        value on the laser of the Line
         OTX TLH  (Unit = dBm)  <Help>
           This control defines the start-up
        output power of the Line OTX TLH
        "
	::= { pm1004dcpCtrllinePowerLaserEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pm1004dcpCntupRaRemCnt articles
--- *********************************************************

pm1004dcpCntupRaRemCntTable OBJECT-TYPE
	SYNTAX  SEQUENCE OF Pm1004dcpCntupRaRemCntEntry
	MAX-ACCESS not-accessible
	STATUS current
	DESCRIPTION
        "
        List of pm1004dcpCntupRaRemCnt
        Article
        "
	::= { pm1004dcpCntClient 16 }


pm1004dcpCntupRaRemCntEntry OBJECT-TYPE
	SYNTAX Pm1004dcpCntupRaRemCntEntry
	MAX-ACCESS not-accessible
	STATUS current
	DESCRIPTION
        "
        Row definition for the pm1004dcpCntupRaRemCnt
        table
        "
	INDEX   { pm1004dcpCntupRaRemCntIndex }
	::= { pm1004dcpCntupRaRemCntTable 1 }


Pm1004dcpCntupRaRemCntEntry ::=
	SEQUENCE {
	pm1004dcpCntupRaRemCntIndex
		INTEGER,
	pm1004dcpCntupRaRemCntValuePortn
		Counter32,
	pm1004dcpCntupRaRemCntErrorPortn
		EkiOnOff,
	pm1004dcpCntupRaRemCntOverloadPortn
		EkiOnOff
	}


pm1004dcpCntupRaRemCntIndex OBJECT-TYPE
	SYNTAX  INTEGER(0..128)
	MAX-ACCESS  read-only
	STATUS current
	DESCRIPTION
        "
        Index definition for the pm1004dcpCntupRaRemCnt
        table
        "
	::= { pm1004dcpCntupRaRemCntEntry 1 }


pm1004dcpCntupRaRemCntValuePortn OBJECT-TYPE
	SYNTAX  Counter32
	MAX-ACCESS read-only
	STATUS current
	DESCRIPTION
        "
        Client Rate Adapt. Words Removal
        :This counter is incremented each
        time a rate adaptation 10B word
        is removed from the Client input
        stream
        "
	::= { pm1004dcpCntupRaRemCntEntry 2 }


pm1004dcpCntupRaRemCntErrorPortn OBJECT-TYPE
	SYNTAX  EkiOnOff
	MAX-ACCESS read-only
	STATUS current
	DESCRIPTION
        "
        Client Counter Error :This OID
        when set indicates the rate adaptation
        removal counter value is invalid
        on Port
        "
	::= { pm1004dcpCntupRaRemCntEntry 3 }


pm1004dcpCntupRaRemCntOverloadPortn OBJECT-TYPE
	SYNTAX  EkiOnOff
	MAX-ACCESS read-only
	STATUS current
	DESCRIPTION
        "
        Client Counter Overload :This
         OID when set indicates a rate
         adaptation removal counter overload
        on Port
        "
	::= { pm1004dcpCntupRaRemCntEntry 4 }


--- *********************************************************
---     TABLE for the pm1004dcpCntupRaInsCnt articles
--- *********************************************************

pm1004dcpCntupRaInsCntTable OBJECT-TYPE
	SYNTAX  SEQUENCE OF Pm1004dcpCntupRaInsCntEntry
	MAX-ACCESS not-accessible
	STATUS current
	DESCRIPTION
        "
        List of pm1004dcpCntupRaInsCnt
        Article
        "
	::= { pm1004dcpCntClient 24 }


pm1004dcpCntupRaInsCntEntry OBJECT-TYPE
	SYNTAX Pm1004dcpCntupRaInsCntEntry
	MAX-ACCESS not-accessible
	STATUS current
	DESCRIPTION
        "
        Row definition for the pm1004dcpCntupRaInsCnt
        table
        "
	INDEX   { pm1004dcpCntupRaInsCntIndex }
	::= { pm1004dcpCntupRaInsCntTable 1 }


Pm1004dcpCntupRaInsCntEntry ::=
	SEQUENCE {
	pm1004dcpCntupRaInsCntIndex
		INTEGER,
	pm1004dcpCntupRaInsCntValuePortn
		Counter32,
	pm1004dcpCntupRaInsCntErrorPortn
		EkiOnOff,
	pm1004dcpCntupRaInsCntOverloadPortn
		EkiOnOff
	}


pm1004dcpCntupRaInsCntIndex OBJECT-TYPE
	SYNTAX  INTEGER(0..128)
	MAX-ACCESS  read-only
	STATUS current
	DESCRIPTION
        "
        Index definition for the pm1004dcpCntupRaInsCnt
        table
        "
	::= { pm1004dcpCntupRaInsCntEntry 1 }


pm1004dcpCntupRaInsCntValuePortn OBJECT-TYPE
	SYNTAX  Counter32
	MAX-ACCESS read-only
	STATUS current
	DESCRIPTION
        "
        Client Rate Adapt. Words Insertion
        :This counter is incremented each
        time a rate adaptation 10B word
        is inserted in the Client input
        stream
        "
	::= { pm1004dcpCntupRaInsCntEntry 2 }


pm1004dcpCntupRaInsCntErrorPortn OBJECT-TYPE
	SYNTAX  EkiOnOff
	MAX-ACCESS read-only
	STATUS current
	DESCRIPTION
        "
        Client Counter Error :This OID
        when set indicates the rate adaptation
        insertion counter value is invalid
        on Port
        "
	::= { pm1004dcpCntupRaInsCntEntry 3 }


pm1004dcpCntupRaInsCntOverloadPortn OBJECT-TYPE
	SYNTAX  EkiOnOff
	MAX-ACCESS read-only
	STATUS current
	DESCRIPTION
        "
        Client Counter Overload :This
         OID when set indicates a rate
         adaptation insertion counter overload
        on Port
        "
	::= { pm1004dcpCntupRaInsCntEntry 4 }


--- *********************************************************
---     TABLE for the pm1004dcpCntupRdErrCnt articles
--- *********************************************************

pm1004dcpCntupRdErrCntTable OBJECT-TYPE
	SYNTAX  SEQUENCE OF Pm1004dcpCntupRdErrCntEntry
	MAX-ACCESS not-accessible
	STATUS current
	DESCRIPTION
        "
        List of pm1004dcpCntupRdErrCnt
        Article
        "
	::= { pm1004dcpCntClient 32 }


pm1004dcpCntupRdErrCntEntry OBJECT-TYPE
	SYNTAX Pm1004dcpCntupRdErrCntEntry
	MAX-ACCESS not-accessible
	STATUS current
	DESCRIPTION
        "
        Row definition for the pm1004dcpCntupRdErrCnt
        table
        "
	INDEX   { pm1004dcpCntupRdErrCntIndex }
	::= { pm1004dcpCntupRdErrCntTable 1 }


Pm1004dcpCntupRdErrCntEntry ::=
	SEQUENCE {
	pm1004dcpCntupRdErrCntIndex
		INTEGER,
	pm1004dcpCntupRdErrCntValuePortn
		Counter32,
	pm1004dcpCntupRdErrCntErrorPortn
		EkiOnOff,
	pm1004dcpCntupRdErrCntOverloadPortn
		EkiOnOff
	}


pm1004dcpCntupRdErrCntIndex OBJECT-TYPE
	SYNTAX  INTEGER(0..128)
	MAX-ACCESS  read-only
	STATUS current
	DESCRIPTION
        "
        Index definition for the pm1004dcpCntupRdErrCnt
        table
        "
	::= { pm1004dcpCntupRdErrCntEntry 1 }


pm1004dcpCntupRdErrCntValuePortn OBJECT-TYPE
	SYNTAX  Counter32
	MAX-ACCESS read-only
	STATUS current
	DESCRIPTION
        "
        Client Input Errors :This counter
        is increased each time a 10b/8b
        running disparity error is detected
        on the Client input stream  <Help>
         This counter gives the number
         of B1 errors on the client input
        port
        "
	::= { pm1004dcpCntupRdErrCntEntry 2 }


pm1004dcpCntupRdErrCntErrorPortn OBJECT-TYPE
	SYNTAX  EkiOnOff
	MAX-ACCESS read-only
	STATUS current
	DESCRIPTION
        "
        Client Counter Error :This OID
        when set indicates the client error
        counter value is invalid on Port
        "
	::= { pm1004dcpCntupRdErrCntEntry 3 }


pm1004dcpCntupRdErrCntOverloadPortn OBJECT-TYPE
	SYNTAX  EkiOnOff
	MAX-ACCESS read-only
	STATUS current
	DESCRIPTION
        "
        Client Counter Overload :This
         OID when set indicates a client
        input error counter overload on
        Port
        "
	::= { pm1004dcpCntupRdErrCntEntry 4 }


--- *********************************************************
---     TABLE for the pm1004dcpCntupTimCnt articles
--- *********************************************************

pm1004dcpCntupTimCntTable OBJECT-TYPE
	SYNTAX  SEQUENCE OF Pm1004dcpCntupTimCntEntry
	MAX-ACCESS not-accessible
	STATUS current
	DESCRIPTION
        "
        List of pm1004dcpCntupTimCnt Article
        "
	::= { pm1004dcpCntClient 40 }


pm1004dcpCntupTimCntEntry OBJECT-TYPE
	SYNTAX Pm1004dcpCntupTimCntEntry
	MAX-ACCESS not-accessible
	STATUS current
	DESCRIPTION
        "
        Row definition for the pm1004dcpCntupTimCnt
        table
        "
	INDEX   { pm1004dcpCntupTimCntIndex }
	::= { pm1004dcpCntupTimCntTable 1 }


Pm1004dcpCntupTimCntEntry ::=
	SEQUENCE {
	pm1004dcpCntupTimCntIndex
		INTEGER,
	pm1004dcpCntupTimCntValuePortn
		Counter32,
	pm1004dcpCntupTimCntErrorPortn
		EkiOnOff,
	pm1004dcpCntupTimCntOverloadPortn
		EkiOnOff
	}


pm1004dcpCntupTimCntIndex OBJECT-TYPE
	SYNTAX  INTEGER(0..128)
	MAX-ACCESS  read-only
	STATUS current
	DESCRIPTION
        "
        Index definition for the pm1004dcpCntupTimCnt
        table
        "
	::= { pm1004dcpCntupTimCntEntry 1 }


pm1004dcpCntupTimCntValuePortn OBJECT-TYPE
	SYNTAX  Counter32
	MAX-ACCESS read-only
	STATUS current
	DESCRIPTION
        "
        Client Upstream Timer Counter
         :This is the timing counter dedicated
        to the upstream access counters.
        It is incremented every 125 us.
        "
	::= { pm1004dcpCntupTimCntEntry 2 }


pm1004dcpCntupTimCntErrorPortn OBJECT-TYPE
	SYNTAX  EkiOnOff
	MAX-ACCESS read-only
	STATUS current
	DESCRIPTION
        "
        Client Counter Error :This OID
        when set indicates the upstream
        timing counter value is invalid
        on Port
        "
	::= { pm1004dcpCntupTimCntEntry 3 }


pm1004dcpCntupTimCntOverloadPortn OBJECT-TYPE
	SYNTAX  EkiOnOff
	MAX-ACCESS read-only
	STATUS current
	DESCRIPTION
        "
        Client Counter Overload :This
         OID when set indicates a upstream
        timing counter overload on Port
        "
	::= { pm1004dcpCntupTimCntEntry 4 }


--- *********************************************************
---     TABLE for the pm1004dcpCntupCvErrCnt articles
--- *********************************************************

pm1004dcpCntupCvErrCntTable OBJECT-TYPE
	SYNTAX  SEQUENCE OF Pm1004dcpCntupCvErrCntEntry
	MAX-ACCESS not-accessible
	STATUS current
	DESCRIPTION
        "
        List of pm1004dcpCntupCvErrCnt
        Article
        "
	::= { pm1004dcpCntClient 48 }


pm1004dcpCntupCvErrCntEntry OBJECT-TYPE
	SYNTAX Pm1004dcpCntupCvErrCntEntry
	MAX-ACCESS not-accessible
	STATUS current
	DESCRIPTION
        "
        Row definition for the pm1004dcpCntupCvErrCnt
        table
        "
	INDEX   { pm1004dcpCntupCvErrCntIndex }
	::= { pm1004dcpCntupCvErrCntTable 1 }


Pm1004dcpCntupCvErrCntEntry ::=
	SEQUENCE {
	pm1004dcpCntupCvErrCntIndex
		INTEGER,
	pm1004dcpCntupCvErrCntValuePortn
		Counter32,
	pm1004dcpCntupCvErrCntErrorPortn
		EkiOnOff,
	pm1004dcpCntupCvErrCntOverloadPortn
		EkiOnOff
	}


pm1004dcpCntupCvErrCntIndex OBJECT-TYPE
	SYNTAX  INTEGER(0..128)
	MAX-ACCESS  read-only
	STATUS current
	DESCRIPTION
        "
        Index definition for the pm1004dcpCntupCvErrCnt
        table
        "
	::= { pm1004dcpCntupCvErrCntEntry 1 }


pm1004dcpCntupCvErrCntValuePortn OBJECT-TYPE
	SYNTAX  Counter32
	MAX-ACCESS read-only
	STATUS current
	DESCRIPTION
        "
        Client Coding Violation Counter
        :This counter is increased each
        time a 10b/8b coding violation
         is detected on the Client input
        stream
        "
	::= { pm1004dcpCntupCvErrCntEntry 2 }


pm1004dcpCntupCvErrCntErrorPortn OBJECT-TYPE
	SYNTAX  EkiOnOff
	MAX-ACCESS read-only
	STATUS current
	DESCRIPTION
        "
        Client Counter Error :This OID
        when set indicates the coding violation
        counter value is invalid on Port
        "
	::= { pm1004dcpCntupCvErrCntEntry 3 }


pm1004dcpCntupCvErrCntOverloadPortn OBJECT-TYPE
	SYNTAX  EkiOnOff
	MAX-ACCESS read-only
	STATUS current
	DESCRIPTION
        "
        Client Counter Overload :This
         OID when set indicates a coding
        violation counter overload on Port
        "
	::= { pm1004dcpCntupCvErrCntEntry 4 }


--- *********************************************************
---     TABLE for the pm1004dcpCntdwCbipCnt articles
--- *********************************************************

pm1004dcpCntdwCbipCntTable OBJECT-TYPE
	SYNTAX  SEQUENCE OF Pm1004dcpCntdwCbipCntEntry
	MAX-ACCESS not-accessible
	STATUS current
	DESCRIPTION
        "
        List of pm1004dcpCntdwCbipCnt
         Article
        "
	::= { pm1004dcpCntClient 64 }


pm1004dcpCntdwCbipCntEntry OBJECT-TYPE
	SYNTAX Pm1004dcpCntdwCbipCntEntry
	MAX-ACCESS not-accessible
	STATUS current
	DESCRIPTION
        "
        Row definition for the pm1004dcpCntdwCbipCnt
        table
        "
	INDEX   { pm1004dcpCntdwCbipCntIndex }
	::= { pm1004dcpCntdwCbipCntTable 1 }


Pm1004dcpCntdwCbipCntEntry ::=
	SEQUENCE {
	pm1004dcpCntdwCbipCntIndex
		INTEGER,
	pm1004dcpCntdwCbipCntValuePortn
		Counter32,
	pm1004dcpCntdwCbipCntErrorPortn
		EkiOnOff,
	pm1004dcpCntdwCbipCntOverloadPortn
		EkiOnOff
	}


pm1004dcpCntdwCbipCntIndex OBJECT-TYPE
	SYNTAX  INTEGER(0..128)
	MAX-ACCESS  read-only
	STATUS current
	DESCRIPTION
        "
        Index definition for the pm1004dcpCntdwCbipCnt
        table
        "
	::= { pm1004dcpCntdwCbipCntEntry 1 }


pm1004dcpCntdwCbipCntValuePortn OBJECT-TYPE
	SYNTAX  Counter32
	MAX-ACCESS read-only
	STATUS current
	DESCRIPTION
        "
        Client Output Errors :This counter
        is incremented each time a CBIP
        parity error is detected on the
        Client output stream  <Help>  This
        counter gives the number of B1
         errors on the client output port
        "
	::= { pm1004dcpCntdwCbipCntEntry 2 }


pm1004dcpCntdwCbipCntErrorPortn OBJECT-TYPE
	SYNTAX  EkiOnOff
	MAX-ACCESS read-only
	STATUS current
	DESCRIPTION
        "
        Client Counter Error :This OID
        when set indicates the CBIP error
        counter value is invalid on Port
        "
	::= { pm1004dcpCntdwCbipCntEntry 3 }


pm1004dcpCntdwCbipCntOverloadPortn OBJECT-TYPE
	SYNTAX  EkiOnOff
	MAX-ACCESS read-only
	STATUS current
	DESCRIPTION
        "
        Client CBIP Counter Overload :This
        OID when set indicates a CBIP error
        counter overload on Port
        "
	::= { pm1004dcpCntdwCbipCntEntry 4 }


--- *********************************************************
---     TABLE for the pm1004dcpCntdwTimCnt articles
--- *********************************************************

pm1004dcpCntdwTimCntTable OBJECT-TYPE
	SYNTAX  SEQUENCE OF Pm1004dcpCntdwTimCntEntry
	MAX-ACCESS not-accessible
	STATUS current
	DESCRIPTION
        "
        List of pm1004dcpCntdwTimCnt Article
        "
	::= { pm1004dcpCntClient 72 }


pm1004dcpCntdwTimCntEntry OBJECT-TYPE
	SYNTAX Pm1004dcpCntdwTimCntEntry
	MAX-ACCESS not-accessible
	STATUS current
	DESCRIPTION
        "
        Row definition for the pm1004dcpCntdwTimCnt
        table
        "
	INDEX   { pm1004dcpCntdwTimCntIndex }
	::= { pm1004dcpCntdwTimCntTable 1 }


Pm1004dcpCntdwTimCntEntry ::=
	SEQUENCE {
	pm1004dcpCntdwTimCntIndex
		INTEGER,
	pm1004dcpCntdwTimCntValuePortn
		Counter32,
	pm1004dcpCntdwTimCntErrorPortn
		EkiOnOff,
	pm1004dcpCntdwTimCntOverloadPortn
		EkiOnOff
	}


pm1004dcpCntdwTimCntIndex OBJECT-TYPE
	SYNTAX  INTEGER(0..128)
	MAX-ACCESS  read-only
	STATUS current
	DESCRIPTION
        "
        Index definition for the pm1004dcpCntdwTimCnt
        table
        "
	::= { pm1004dcpCntdwTimCntEntry 1 }


pm1004dcpCntdwTimCntValuePortn OBJECT-TYPE
	SYNTAX  Counter32
	MAX-ACCESS read-only
	STATUS current
	DESCRIPTION
        "
        Client Downstream Timer Counter
        :This is the timing counter dedicated
        to the downstream access counters.
        It is incremented every 125 us.
        "
	::= { pm1004dcpCntdwTimCntEntry 2 }


pm1004dcpCntdwTimCntErrorPortn OBJECT-TYPE
	SYNTAX  EkiOnOff
	MAX-ACCESS read-only
	STATUS current
	DESCRIPTION
        "
        Client Counter Error :This OID
        when set indicates the downstream
        timer counter value is invalid
         on Port
        "
	::= { pm1004dcpCntdwTimCntEntry 3 }


pm1004dcpCntdwTimCntOverloadPortn OBJECT-TYPE
	SYNTAX  EkiOnOff
	MAX-ACCESS read-only
	STATUS current
	DESCRIPTION
        "
        Client Counter Overload :This
         OID when set indicates a downstream
        timer counter overload on Port
        "
	::= { pm1004dcpCntdwTimCntEntry 4 }


--- *********************************************************
---     TABLE for the pm1004dcpCntdfrmB1ErrCnt articles
--- *********************************************************

pm1004dcpCntdfrmB1ErrCntTable OBJECT-TYPE
	SYNTAX  SEQUENCE OF Pm1004dcpCntdfrmB1ErrCntEntry
	MAX-ACCESS not-accessible
	STATUS current
	DESCRIPTION
        "
        List of pm1004dcpCntdfrmB1ErrCnt
        Article
        "
	::= { pm1004dcpCntLine 152 }


pm1004dcpCntdfrmB1ErrCntEntry OBJECT-TYPE
	SYNTAX Pm1004dcpCntdfrmB1ErrCntEntry
	MAX-ACCESS not-accessible
	STATUS current
	DESCRIPTION
        "
        Row definition for the pm1004dcpCntdfrmB1ErrCnt
        table
        "
	INDEX   { pm1004dcpCntdfrmB1ErrCntIndex }
	::= { pm1004dcpCntdfrmB1ErrCntTable 1 }


Pm1004dcpCntdfrmB1ErrCntEntry ::=
	SEQUENCE {
	pm1004dcpCntdfrmB1ErrCntIndex
		INTEGER,
	pm1004dcpCntdfrmB1ErrCntValuePortn
		Counter32,
	pm1004dcpCntdfrmB1ErrCntErrorPortn
		EkiOnOff,
	pm1004dcpCntdfrmB1ErrCntOverloadPortn
		EkiOnOff
	}


pm1004dcpCntdfrmB1ErrCntIndex OBJECT-TYPE
	SYNTAX  INTEGER(0..128)
	MAX-ACCESS  read-only
	STATUS current
	DESCRIPTION
        "
        Index definition for the pm1004dcpCntdfrmB1ErrCnt
        table
        "
	::= { pm1004dcpCntdfrmB1ErrCntEntry 1 }


pm1004dcpCntdfrmB1ErrCntValuePortn OBJECT-TYPE
	SYNTAX  Counter32
	MAX-ACCESS read-only
	STATUS current
	DESCRIPTION
        "
        Line Input SM-BIP8 Errors :This
        counter is incremented each time
        a SM BIP error is detected on the
        Deframer input stream.  <Help>
          This counter gives the number
        of SM-BIP8 errors on the line port
        "
	::= { pm1004dcpCntdfrmB1ErrCntEntry 2 }


pm1004dcpCntdfrmB1ErrCntErrorPortn OBJECT-TYPE
	SYNTAX  EkiOnOff
	MAX-ACCESS read-only
	STATUS current
	DESCRIPTION
        "
        Line Counter Error :This OID when
        set indicates the SM BIP error
         counter value is invalid on Port
        "
	::= { pm1004dcpCntdfrmB1ErrCntEntry 3 }


pm1004dcpCntdfrmB1ErrCntOverloadPortn OBJECT-TYPE
	SYNTAX  EkiOnOff
	MAX-ACCESS read-only
	STATUS current
	DESCRIPTION
        "
        Line Counter Overload :This OID
        when set indicates a SM BIP error
        counter overload on Port
        "
	::= { pm1004dcpCntdfrmB1ErrCntEntry 4 }


--- *********************************************************
---     TABLE for the pm1004dcpCntdfrmTimCnt articles
--- *********************************************************

pm1004dcpCntdfrmTimCntTable OBJECT-TYPE
	SYNTAX  SEQUENCE OF Pm1004dcpCntdfrmTimCntEntry
	MAX-ACCESS not-accessible
	STATUS current
	DESCRIPTION
        "
        List of pm1004dcpCntdfrmTimCnt
        Article
        "
	::= { pm1004dcpCntLine 153 }


pm1004dcpCntdfrmTimCntEntry OBJECT-TYPE
	SYNTAX Pm1004dcpCntdfrmTimCntEntry
	MAX-ACCESS not-accessible
	STATUS current
	DESCRIPTION
        "
        Row definition for the pm1004dcpCntdfrmTimCnt
        table
        "
	INDEX   { pm1004dcpCntdfrmTimCntIndex }
	::= { pm1004dcpCntdfrmTimCntTable 1 }


Pm1004dcpCntdfrmTimCntEntry ::=
	SEQUENCE {
	pm1004dcpCntdfrmTimCntIndex
		INTEGER,
	pm1004dcpCntdfrmTimCntValuePortn
		Counter32,
	pm1004dcpCntdfrmTimCntErrorPortn
		EkiOnOff,
	pm1004dcpCntdfrmTimCntOverloadPortn
		EkiOnOff
	}


pm1004dcpCntdfrmTimCntIndex OBJECT-TYPE
	SYNTAX  INTEGER(0..128)
	MAX-ACCESS  read-only
	STATUS current
	DESCRIPTION
        "
        Index definition for the pm1004dcpCntdfrmTimCnt
        table
        "
	::= { pm1004dcpCntdfrmTimCntEntry 1 }


pm1004dcpCntdfrmTimCntValuePortn OBJECT-TYPE
	SYNTAX  Counter32
	MAX-ACCESS read-only
	STATUS current
	DESCRIPTION
        "
        Line Timer Counter :This is the
        timing counter dedicated to the
        downstream deframer counters. It
        is incremented every 125 us.
        "
	::= { pm1004dcpCntdfrmTimCntEntry 2 }


pm1004dcpCntdfrmTimCntErrorPortn OBJECT-TYPE
	SYNTAX  EkiOnOff
	MAX-ACCESS read-only
	STATUS current
	DESCRIPTION
        "
        Line Counter Error :This OID when
        set indicates the deframer timer
        counter value is invalid on Port
        "
	::= { pm1004dcpCntdfrmTimCntEntry 3 }


pm1004dcpCntdfrmTimCntOverloadPortn OBJECT-TYPE
	SYNTAX  EkiOnOff
	MAX-ACCESS read-only
	STATUS current
	DESCRIPTION
        "
        Line Counter Overload :This OID
        when set indicates a deframer timer
        counter overload on Port
        "
	::= { pm1004dcpCntdfrmTimCntEntry 4 }


--- *********************************************************
---     TABLE for the pm1004dcpCntdfrmPrimLineErrCnt articles
--- *********************************************************

pm1004dcpCntdfrmPrimLineErrCntTable OBJECT-TYPE
	SYNTAX  SEQUENCE OF Pm1004dcpCntdfrmPrimLineErrCntEntry
	MAX-ACCESS not-accessible
	STATUS current
	DESCRIPTION
        "
        List of pm1004dcpCntdfrmPrimLineErrCnt
        Article
        "
	::= { pm1004dcpCntLine 154 }


pm1004dcpCntdfrmPrimLineErrCntEntry OBJECT-TYPE
	SYNTAX Pm1004dcpCntdfrmPrimLineErrCntEntry
	MAX-ACCESS not-accessible
	STATUS current
	DESCRIPTION
        "
        Row definition for the pm1004dcpCntdfrmPrimLineErrCnt
        table
        "
	INDEX   { pm1004dcpCntdfrmPrimLineErrCntIndex }
	::= { pm1004dcpCntdfrmPrimLineErrCntTable 1 }


Pm1004dcpCntdfrmPrimLineErrCntEntry ::=
	SEQUENCE {
	pm1004dcpCntdfrmPrimLineErrCntIndex
		INTEGER,
	pm1004dcpCntdfrmPrimLineErrCntValuePortn
		Counter32,
	pm1004dcpCntdfrmPrimLineErrCntErrorPortn
		EkiOnOff,
	pm1004dcpCntdfrmPrimLineErrCntOverloadPortn
		EkiOnOff
	}


pm1004dcpCntdfrmPrimLineErrCntIndex OBJECT-TYPE
	SYNTAX  INTEGER(0..128)
	MAX-ACCESS  read-only
	STATUS current
	DESCRIPTION
        "
        Index definition for the pm1004dcpCntdfrmPrimLineErrCnt
        table
        "
	::= { pm1004dcpCntdfrmPrimLineErrCntEntry 1 }


pm1004dcpCntdfrmPrimLineErrCntValuePortn OBJECT-TYPE
	SYNTAX  Counter32
	MAX-ACCESS read-only
	STATUS current
	DESCRIPTION
        "
        Line Input FEC Corrected Errors
        :This counter is incremented each
        time the FEC is correcting an error
        on the line input stream.  <Help>
         This counter gives the number
         of errors corrected by the FEC
        on the line port
        "
	::= { pm1004dcpCntdfrmPrimLineErrCntEntry 2 }


pm1004dcpCntdfrmPrimLineErrCntErrorPortn OBJECT-TYPE
	SYNTAX  EkiOnOff
	MAX-ACCESS read-only
	STATUS current
	DESCRIPTION
        "
        FEC Counter Error :This bit when
        set indicates the FEC corrected
        errors counter value is invalid
        on Line
        "
	::= { pm1004dcpCntdfrmPrimLineErrCntEntry 3 }


pm1004dcpCntdfrmPrimLineErrCntOverloadPortn OBJECT-TYPE
	SYNTAX  EkiOnOff
	MAX-ACCESS read-only
	STATUS current
	DESCRIPTION
        "
        FEC Counter Overload :This bit
        when set indicates a FEC corrected
        errors counter overload on Line
        "
	::= { pm1004dcpCntdfrmPrimLineErrCntEntry 4 }


pm1004dcpCntCountersReset  OBJECT-TYPE
	SYNTAX EkiOnOff
	MAX-ACCESS read-write
	STATUS current
	DESCRIPTION
	"Counters Reset:This OID resets and restarts all the counters"
	::= { pm1004dcpcounters  259 }

pm1004dcpCntCountersStop  OBJECT-TYPE
	SYNTAX EkiOnOff
	MAX-ACCESS read-write
	STATUS current
	DESCRIPTION
	"Counters stop:This OID stops all the counters"
	::= { pm1004dcpcounters 260 }






--- *****************************************************
--- $$$$$$$$$$$$$$$$$$$$$$$$$$$$$$$$$$$$$$$$$$$$$$$$$$$$$
---     J0
--- $$$$$$$$$$$$$$$$$$$$$$$$$$$$$$$$$$$$$$$$$$$$$$$$$$$$$
--- *****************************************************








--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pm1004dcpMesrsynth0 OBJECT-TYPE
	  SYNTAX EkiMeasureType
	  MAX-ACCESS read-only
	  STATUS deprecated
	  DESCRIPTION
        "
        Not Used :This OID gives the unit
        used on AUX1 measurement of XFP#1
         (Unit = )
        "
	  ::= { pm1004dcpMesrOther 0 }



pm1004dcpMesrsynth1 OBJECT-TYPE
	  SYNTAX EkiMeasureType
	  MAX-ACCESS read-only
	  STATUS deprecated
	  DESCRIPTION
        "
        Not Used :This OID gives the unit
        used on AUX2 measurement of XFP#1
         (Unit = )
        "
	  ::= { pm1004dcpMesrOther 1 }



--- *********************************************************
---     TABLE for the pm1004dcpMesrtempMeas articles
--- *********************************************************

pm1004dcpMesrtempMeasTable OBJECT-TYPE
	SYNTAX  SEQUENCE OF Pm1004dcpMesrtempMeasEntry
	MAX-ACCESS not-accessible
	STATUS current
	DESCRIPTION
        "
        List of pm1004dcpMesrtempMeas
         Article
        "
	::= { pm1004dcpMesrClient 16 }


pm1004dcpMesrtempMeasEntry OBJECT-TYPE
	SYNTAX Pm1004dcpMesrtempMeasEntry
	MAX-ACCESS not-accessible
	STATUS current
	DESCRIPTION
        "
        Row definition for the pm1004dcpMesrtempMeas
        table
        "
	INDEX   { pm1004dcpMesrtempMeasIndex }
	::= { pm1004dcpMesrtempMeasTable 1 }


Pm1004dcpMesrtempMeasEntry ::=
	SEQUENCE {
	pm1004dcpMesrtempMeasIndex
		INTEGER,
	pm1004dcpMesrtempMeasPortn
		INTEGER
	}


pm1004dcpMesrtempMeasIndex OBJECT-TYPE
	SYNTAX  INTEGER(0..128)
	MAX-ACCESS  read-only
	STATUS current
	DESCRIPTION
        "
        Index definition for the pm1004dcpMesrtempMeas
        table
        "
	::= { pm1004dcpMesrtempMeasEntry 1 }


pm1004dcpMesrtempMeasPortn OBJECT-TYPE
	SYNTAX  INTEGER (0..65535)
	MAX-ACCESS read-only
	STATUS current
	DESCRIPTION
        "
        Client SFP Temperature :This OID
        gives the temperature value of
         the SFP plugged in port, read
         from the DDM (Digital Diagnostic
        Monitoring) (Temperature = AV/256)
          (Unit = C)  <Help>  This measure
        gives the temperature of the client
        transceiver
        "
	::= { pm1004dcpMesrtempMeasEntry 2 }


--- *********************************************************
---     TABLE for the pm1004dcpMesrvoltMeas articles
--- *********************************************************

pm1004dcpMesrvoltMeasTable OBJECT-TYPE
	SYNTAX  SEQUENCE OF Pm1004dcpMesrvoltMeasEntry
	MAX-ACCESS not-accessible
	STATUS current
	DESCRIPTION
        "
        List of pm1004dcpMesrvoltMeas
         Article
        "
	::= { pm1004dcpMesrClient 24 }


pm1004dcpMesrvoltMeasEntry OBJECT-TYPE
	SYNTAX Pm1004dcpMesrvoltMeasEntry
	MAX-ACCESS not-accessible
	STATUS current
	DESCRIPTION
        "
        Row definition for the pm1004dcpMesrvoltMeas
        table
        "
	INDEX   { pm1004dcpMesrvoltMeasIndex }
	::= { pm1004dcpMesrvoltMeasTable 1 }


Pm1004dcpMesrvoltMeasEntry ::=
	SEQUENCE {
	pm1004dcpMesrvoltMeasIndex
		INTEGER,
	pm1004dcpMesrvoltMeasPortn
		INTEGER
	}


pm1004dcpMesrvoltMeasIndex OBJECT-TYPE
	SYNTAX  INTEGER(0..128)
	MAX-ACCESS  read-only
	STATUS current
	DESCRIPTION
        "
        Index definition for the pm1004dcpMesrvoltMeas
        table
        "
	::= { pm1004dcpMesrvoltMeasEntry 1 }


pm1004dcpMesrvoltMeasPortn OBJECT-TYPE
	SYNTAX  INTEGER (0..65535)
	MAX-ACCESS read-only
	STATUS current
	DESCRIPTION
        "
        Client SFP Power Supply :This
         OID gives the 3V3 voltage value
        of the SFP plugged into port, read
        from the DDM (Digital Diagnostic
        Monitoring) (Voltage = AV/10000)
        (Unit = V)  <Help>  This measure
        gives the 3V3 voltage of the client
        transceiver
        "
	::= { pm1004dcpMesrvoltMeasEntry 2 }


--- *********************************************************
---     TABLE for the pm1004dcpMesrbiasMeas articles
--- *********************************************************

pm1004dcpMesrbiasMeasTable OBJECT-TYPE
	SYNTAX  SEQUENCE OF Pm1004dcpMesrbiasMeasEntry
	MAX-ACCESS not-accessible
	STATUS current
	DESCRIPTION
        "
        List of pm1004dcpMesrbiasMeas
         Article
        "
	::= { pm1004dcpMesrClient 32 }


pm1004dcpMesrbiasMeasEntry OBJECT-TYPE
	SYNTAX Pm1004dcpMesrbiasMeasEntry
	MAX-ACCESS not-accessible
	STATUS current
	DESCRIPTION
        "
        Row definition for the pm1004dcpMesrbiasMeas
        table
        "
	INDEX   { pm1004dcpMesrbiasMeasIndex }
	::= { pm1004dcpMesrbiasMeasTable 1 }


Pm1004dcpMesrbiasMeasEntry ::=
	SEQUENCE {
	pm1004dcpMesrbiasMeasIndex
		INTEGER,
	pm1004dcpMesrbiasMeasPortn
		INTEGER
	}


pm1004dcpMesrbiasMeasIndex OBJECT-TYPE
	SYNTAX  INTEGER(0..128)
	MAX-ACCESS  read-only
	STATUS current
	DESCRIPTION
        "
        Index definition for the pm1004dcpMesrbiasMeas
        table
        "
	::= { pm1004dcpMesrbiasMeasEntry 1 }


pm1004dcpMesrbiasMeasPortn OBJECT-TYPE
	SYNTAX  INTEGER (0..65535)
	MAX-ACCESS read-only
	STATUS current
	DESCRIPTION
        "
        Client SFP Laser Bias :This OID
        gives the bias value of the SFP
        plugged into port, read from the
        DDM (Digital Diagnostic Monitoring)
         (Bias = AV/500)  (Unit = mA)
         <Help>  This measure gives the
        bias of the client transceiver
        "
	::= { pm1004dcpMesrbiasMeasEntry 2 }


--- *********************************************************
---     TABLE for the pm1004dcpMesrtxpwrMeas articles
--- *********************************************************

pm1004dcpMesrtxpwrMeasTable OBJECT-TYPE
	SYNTAX  SEQUENCE OF Pm1004dcpMesrtxpwrMeasEntry
	MAX-ACCESS not-accessible
	STATUS current
	DESCRIPTION
        "
        List of pm1004dcpMesrtxpwrMeas
        Article
        "
	::= { pm1004dcpMesrClient 40 }


pm1004dcpMesrtxpwrMeasEntry OBJECT-TYPE
	SYNTAX Pm1004dcpMesrtxpwrMeasEntry
	MAX-ACCESS not-accessible
	STATUS current
	DESCRIPTION
        "
        Row definition for the pm1004dcpMesrtxpwrMeas
        table
        "
	INDEX   { pm1004dcpMesrtxpwrMeasIndex }
	::= { pm1004dcpMesrtxpwrMeasTable 1 }


Pm1004dcpMesrtxpwrMeasEntry ::=
	SEQUENCE {
	pm1004dcpMesrtxpwrMeasIndex
		INTEGER,
	pm1004dcpMesrtxpwrMeasPortn
		INTEGER
	}


pm1004dcpMesrtxpwrMeasIndex OBJECT-TYPE
	SYNTAX  INTEGER(0..128)
	MAX-ACCESS  read-only
	STATUS current
	DESCRIPTION
        "
        Index definition for the pm1004dcpMesrtxpwrMeas
        table
        "
	::= { pm1004dcpMesrtxpwrMeasEntry 1 }


pm1004dcpMesrtxpwrMeasPortn OBJECT-TYPE
	SYNTAX  INTEGER (0..65535)
	MAX-ACCESS read-only
	STATUS current
	DESCRIPTION
        "
        Client SFP Tx Power :This OID
         gives the transmit power value
        of the SFP plugged into port, read
        from the DDM (Digital Diagnostic
        Monitoring) (Power = 10*log(AV)-40)
         (Unit = dBm)  <Help>  This measure
        gives the Tx optical power of the
        client transceiver
        "
	::= { pm1004dcpMesrtxpwrMeasEntry 2 }


--- *********************************************************
---     TABLE for the pm1004dcpMesrrxpwrMeas articles
--- *********************************************************

pm1004dcpMesrrxpwrMeasTable OBJECT-TYPE
	SYNTAX  SEQUENCE OF Pm1004dcpMesrrxpwrMeasEntry
	MAX-ACCESS not-accessible
	STATUS current
	DESCRIPTION
        "
        List of pm1004dcpMesrrxpwrMeas
        Article
        "
	::= { pm1004dcpMesrClient 48 }


pm1004dcpMesrrxpwrMeasEntry OBJECT-TYPE
	SYNTAX Pm1004dcpMesrrxpwrMeasEntry
	MAX-ACCESS not-accessible
	STATUS current
	DESCRIPTION
        "
        Row definition for the pm1004dcpMesrrxpwrMeas
        table
        "
	INDEX   { pm1004dcpMesrrxpwrMeasIndex }
	::= { pm1004dcpMesrrxpwrMeasTable 1 }


Pm1004dcpMesrrxpwrMeasEntry ::=
	SEQUENCE {
	pm1004dcpMesrrxpwrMeasIndex
		INTEGER,
	pm1004dcpMesrrxpwrMeasPortn
		INTEGER
	}


pm1004dcpMesrrxpwrMeasIndex OBJECT-TYPE
	SYNTAX  INTEGER(0..128)
	MAX-ACCESS  read-only
	STATUS current
	DESCRIPTION
        "
        Index definition for the pm1004dcpMesrrxpwrMeas
        table
        "
	::= { pm1004dcpMesrrxpwrMeasEntry 1 }


pm1004dcpMesrrxpwrMeasPortn OBJECT-TYPE
	SYNTAX  INTEGER (0..65535)
	MAX-ACCESS read-only
	STATUS current
	DESCRIPTION
        "
        Client SFP Rx Power :This OID
         gives the receive power value
         of the SFP plugged into port,
         read in the DDM (Digital Diagnostic
        Monitoring) (Power = 10*log(AV)-40)
         (Unit = dBm)  <Help>  This measure
        gives the Rx optical power of the
        client transceiver
        "
	::= { pm1004dcpMesrrxpwrMeasEntry 2 }


--- *********************************************************
---     TABLE for the pm1004dcpMesrxfp1LxModTempMeas articles
--- *********************************************************

pm1004dcpMesrxfp1LxModTempMeasTable OBJECT-TYPE
	SYNTAX  SEQUENCE OF Pm1004dcpMesrxfp1LxModTempMeasEntry
	MAX-ACCESS not-accessible
	STATUS current
	DESCRIPTION
        "
        List of pm1004dcpMesrxfp1LxModTempMeas
        Article
        "
	::= { pm1004dcpMesrLine 208 }


pm1004dcpMesrxfp1LxModTempMeasEntry OBJECT-TYPE
	SYNTAX Pm1004dcpMesrxfp1LxModTempMeasEntry
	MAX-ACCESS not-accessible
	STATUS current
	DESCRIPTION
        "
        Row definition for the pm1004dcpMesrxfp1LxModTempMeas
        table
        "
	INDEX   { pm1004dcpMesrxfp1LxModTempMeasIndex }
	::= { pm1004dcpMesrxfp1LxModTempMeasTable 1 }


Pm1004dcpMesrxfp1LxModTempMeasEntry ::=
	SEQUENCE {
	pm1004dcpMesrxfp1LxModTempMeasIndex
		INTEGER,
	pm1004dcpMesrxfp1LxModTempMeasPortn
		INTEGER
	}


pm1004dcpMesrxfp1LxModTempMeasIndex OBJECT-TYPE
	SYNTAX  INTEGER(0..128)
	MAX-ACCESS  read-only
	STATUS current
	DESCRIPTION
        "
        Index definition for the pm1004dcpMesrxfp1LxModTempMeas
        table
        "
	::= { pm1004dcpMesrxfp1LxModTempMeasEntry 1 }


pm1004dcpMesrxfp1LxModTempMeasPortn OBJECT-TYPE
	SYNTAX  INTEGER (0..65535)
	MAX-ACCESS read-only
	STATUS current
	DESCRIPTION
        "
        Line Optical Module Temperature
        :This OID gives the temperature
        of the XFP or OTX plugged in line#n,
        read from the DDM (Digital Diagnostic
        Monitoring) (Temperature = AV/256)
        (Unit = C)  <Help>  This measure
        gives the temperature of the line
        transceiver
        "
	::= { pm1004dcpMesrxfp1LxModTempMeasEntry 2 }


--- *********************************************************
---     TABLE for the pm1004dcpMesrxfp1Reserved articles
--- *********************************************************

pm1004dcpMesrxfp1ReservedTable OBJECT-TYPE
	SYNTAX  SEQUENCE OF Pm1004dcpMesrxfp1ReservedEntry
	MAX-ACCESS not-accessible
	STATUS deprecated
	DESCRIPTION
        "
        List of pm1004dcpMesrxfp1Reserved
        Article
        "
	::= { pm1004dcpMesrLine 209 }


pm1004dcpMesrxfp1ReservedEntry OBJECT-TYPE
	SYNTAX Pm1004dcpMesrxfp1ReservedEntry
	MAX-ACCESS not-accessible
	STATUS deprecated
	DESCRIPTION
        "
        Row definition for the pm1004dcpMesrxfp1Reserved
        table
        "
	INDEX   { pm1004dcpMesrxfp1ReservedIndex }
	::= { pm1004dcpMesrxfp1ReservedTable 1 }


Pm1004dcpMesrxfp1ReservedEntry ::=
	SEQUENCE {
	pm1004dcpMesrxfp1ReservedIndex
		INTEGER,
	pm1004dcpMesrxfp1ReservedPortn
		INTEGER
	}


pm1004dcpMesrxfp1ReservedIndex OBJECT-TYPE
	SYNTAX  INTEGER(0..128)
	MAX-ACCESS  read-only
	STATUS deprecated
	DESCRIPTION
        "
        Index definition for the pm1004dcpMesrxfp1Reserved
        table
        "
	::= { pm1004dcpMesrxfp1ReservedEntry 1 }


pm1004dcpMesrxfp1ReservedPortn OBJECT-TYPE
	SYNTAX  INTEGER (0..65535)
	MAX-ACCESS read-only
	STATUS deprecated
	DESCRIPTION
        "
        Not Used :Reserved
        "
	::= { pm1004dcpMesrxfp1ReservedEntry 2 }


--- *********************************************************
---     TABLE for the pm1004dcpMesrxfp1LoBiasCurrentMeas articles
--- *********************************************************

pm1004dcpMesrxfp1LoBiasCurrentMeasTable OBJECT-TYPE
	SYNTAX  SEQUENCE OF Pm1004dcpMesrxfp1LoBiasCurrentMeasEntry
	MAX-ACCESS not-accessible
	STATUS current
	DESCRIPTION
        "
        List of pm1004dcpMesrxfp1LoBiasCurrentMeas
        Article
        "
	::= { pm1004dcpMesrLine 210 }


pm1004dcpMesrxfp1LoBiasCurrentMeasEntry OBJECT-TYPE
	SYNTAX Pm1004dcpMesrxfp1LoBiasCurrentMeasEntry
	MAX-ACCESS not-accessible
	STATUS current
	DESCRIPTION
        "
        Row definition for the pm1004dcpMesrxfp1LoBiasCurrentMeas
        table
        "
	INDEX   { pm1004dcpMesrxfp1LoBiasCurrentMeasIndex }
	::= { pm1004dcpMesrxfp1LoBiasCurrentMeasTable 1 }


Pm1004dcpMesrxfp1LoBiasCurrentMeasEntry ::=
	SEQUENCE {
	pm1004dcpMesrxfp1LoBiasCurrentMeasIndex
		INTEGER,
	pm1004dcpMesrxfp1LoBiasCurrentMeasPortn
		INTEGER
	}


pm1004dcpMesrxfp1LoBiasCurrentMeasIndex OBJECT-TYPE
	SYNTAX  INTEGER(0..128)
	MAX-ACCESS  read-only
	STATUS current
	DESCRIPTION
        "
        Index definition for the pm1004dcpMesrxfp1LoBiasCurrentMeas
        table
        "
	::= { pm1004dcpMesrxfp1LoBiasCurrentMeasEntry 1 }


pm1004dcpMesrxfp1LoBiasCurrentMeasPortn OBJECT-TYPE
	SYNTAX  INTEGER (0..65535)
	MAX-ACCESS read-only
	STATUS current
	DESCRIPTION
        "
        Line Optical Module Laser Bias
        :This OID gives the bias value
         of the XFP or OTX plugged in line
        #n, read from the DDM (Digital
         Diagnostic Monitoring) (Bias =
        AV/500)  (Unit = mA)  <Help>  This
        measure gives the bias of the line
        transceiver
        "
	::= { pm1004dcpMesrxfp1LoBiasCurrentMeasEntry 2 }


--- *********************************************************
---     TABLE for the pm1004dcpMesrxfp1LoTxPowerMeas articles
--- *********************************************************

pm1004dcpMesrxfp1LoTxPowerMeasTable OBJECT-TYPE
	SYNTAX  SEQUENCE OF Pm1004dcpMesrxfp1LoTxPowerMeasEntry
	MAX-ACCESS not-accessible
	STATUS current
	DESCRIPTION
        "
        List of pm1004dcpMesrxfp1LoTxPowerMeas
        Article
        "
	::= { pm1004dcpMesrLine 211 }


pm1004dcpMesrxfp1LoTxPowerMeasEntry OBJECT-TYPE
	SYNTAX Pm1004dcpMesrxfp1LoTxPowerMeasEntry
	MAX-ACCESS not-accessible
	STATUS current
	DESCRIPTION
        "
        Row definition for the pm1004dcpMesrxfp1LoTxPowerMeas
        table
        "
	INDEX   { pm1004dcpMesrxfp1LoTxPowerMeasIndex }
	::= { pm1004dcpMesrxfp1LoTxPowerMeasTable 1 }


Pm1004dcpMesrxfp1LoTxPowerMeasEntry ::=
	SEQUENCE {
	pm1004dcpMesrxfp1LoTxPowerMeasIndex
		INTEGER,
	pm1004dcpMesrxfp1LoTxPowerMeasPortn
		INTEGER
	}


pm1004dcpMesrxfp1LoTxPowerMeasIndex OBJECT-TYPE
	SYNTAX  INTEGER(0..128)
	MAX-ACCESS  read-only
	STATUS current
	DESCRIPTION
        "
        Index definition for the pm1004dcpMesrxfp1LoTxPowerMeas
        table
        "
	::= { pm1004dcpMesrxfp1LoTxPowerMeasEntry 1 }


pm1004dcpMesrxfp1LoTxPowerMeasPortn OBJECT-TYPE
	SYNTAX  INTEGER (0..65535)
	MAX-ACCESS read-only
	STATUS current
	DESCRIPTION
        "
        Line Optical Module Tx Power :This
        OID gives the transmit power value
        of the XFP or OTX plugged in line
        #n, read from the DDM (Digital
           Diagnostic Monitoring)  (Power
        = 10*log(AV)-40) (Unit = dBm)
         <Help>  This measure gives the
        Tx optical power of the line transceiver
        "
	::= { pm1004dcpMesrxfp1LoTxPowerMeasEntry 2 }


--- *********************************************************
---     TABLE for the pm1004dcpMesrxfp1LiRxPowerMeas articles
--- *********************************************************

pm1004dcpMesrxfp1LiRxPowerMeasTable OBJECT-TYPE
	SYNTAX  SEQUENCE OF Pm1004dcpMesrxfp1LiRxPowerMeasEntry
	MAX-ACCESS not-accessible
	STATUS current
	DESCRIPTION
        "
        List of pm1004dcpMesrxfp1LiRxPowerMeas
        Article
        "
	::= { pm1004dcpMesrLine 212 }


pm1004dcpMesrxfp1LiRxPowerMeasEntry OBJECT-TYPE
	SYNTAX Pm1004dcpMesrxfp1LiRxPowerMeasEntry
	MAX-ACCESS not-accessible
	STATUS current
	DESCRIPTION
        "
        Row definition for the pm1004dcpMesrxfp1LiRxPowerMeas
        table
        "
	INDEX   { pm1004dcpMesrxfp1LiRxPowerMeasIndex }
	::= { pm1004dcpMesrxfp1LiRxPowerMeasTable 1 }


Pm1004dcpMesrxfp1LiRxPowerMeasEntry ::=
	SEQUENCE {
	pm1004dcpMesrxfp1LiRxPowerMeasIndex
		INTEGER,
	pm1004dcpMesrxfp1LiRxPowerMeasPortn
		INTEGER
	}


pm1004dcpMesrxfp1LiRxPowerMeasIndex OBJECT-TYPE
	SYNTAX  INTEGER(0..128)
	MAX-ACCESS  read-only
	STATUS current
	DESCRIPTION
        "
        Index definition for the pm1004dcpMesrxfp1LiRxPowerMeas
        table
        "
	::= { pm1004dcpMesrxfp1LiRxPowerMeasEntry 1 }


pm1004dcpMesrxfp1LiRxPowerMeasPortn OBJECT-TYPE
	SYNTAX  INTEGER (0..65535)
	MAX-ACCESS read-only
	STATUS current
	DESCRIPTION
        "
        Line Optical Module Rx Power :This
        OID gives the receive power value
        of the XFP or OTX plugged in line
        #n, read from the DDM (Digital
         Diagnostic Monitoring)  (Power
        = 10*log(AV)-40) (Unit = dBm)
         <Help>  This measure gives the
        Rx optical power of the line transceiver
        "
	::= { pm1004dcpMesrxfp1LiRxPowerMeasEntry 2 }


--- *********************************************************
---     TABLE for the pm1004dcpMesrxfp1LxAux1Meas articles
--- *********************************************************

pm1004dcpMesrxfp1LxAux1MeasTable OBJECT-TYPE
	SYNTAX  SEQUENCE OF Pm1004dcpMesrxfp1LxAux1MeasEntry
	MAX-ACCESS not-accessible
	STATUS deprecated
	DESCRIPTION
        "
        List of pm1004dcpMesrxfp1LxAux1Meas
        Article
        "
	::= { pm1004dcpMesrLine 213 }


pm1004dcpMesrxfp1LxAux1MeasEntry OBJECT-TYPE
	SYNTAX Pm1004dcpMesrxfp1LxAux1MeasEntry
	MAX-ACCESS not-accessible
	STATUS deprecated
	DESCRIPTION
        "
        Row definition for the pm1004dcpMesrxfp1LxAux1Meas
        table
        "
	INDEX   { pm1004dcpMesrxfp1LxAux1MeasIndex }
	::= { pm1004dcpMesrxfp1LxAux1MeasTable 1 }


Pm1004dcpMesrxfp1LxAux1MeasEntry ::=
	SEQUENCE {
	pm1004dcpMesrxfp1LxAux1MeasIndex
		INTEGER,
	pm1004dcpMesrxfp1LxAux1MeasPortn
		INTEGER
	}


pm1004dcpMesrxfp1LxAux1MeasIndex OBJECT-TYPE
	SYNTAX  INTEGER(0..128)
	MAX-ACCESS  read-only
	STATUS deprecated
	DESCRIPTION
        "
        Index definition for the pm1004dcpMesrxfp1LxAux1Meas
        table
        "
	::= { pm1004dcpMesrxfp1LxAux1MeasEntry 1 }


pm1004dcpMesrxfp1LxAux1MeasPortn OBJECT-TYPE
	SYNTAX  INTEGER (0..65535)
	MAX-ACCESS read-only
	STATUS deprecated
	DESCRIPTION
        "
        Not Used :This OID gives the receive
        power value read in the DDM (Digital
        Diagnostic Monitoring) of the XFP
        or OTX plugged in line #n (Unit
        = ?)
        "
	::= { pm1004dcpMesrxfp1LxAux1MeasEntry 2 }


--- *********************************************************
---     TABLE for the pm1004dcpMesrxfp1LxAux2Meas articles
--- *********************************************************

pm1004dcpMesrxfp1LxAux2MeasTable OBJECT-TYPE
	SYNTAX  SEQUENCE OF Pm1004dcpMesrxfp1LxAux2MeasEntry
	MAX-ACCESS not-accessible
	STATUS deprecated
	DESCRIPTION
        "
        List of pm1004dcpMesrxfp1LxAux2Meas
        Article
        "
	::= { pm1004dcpMesrLine 214 }


pm1004dcpMesrxfp1LxAux2MeasEntry OBJECT-TYPE
	SYNTAX Pm1004dcpMesrxfp1LxAux2MeasEntry
	MAX-ACCESS not-accessible
	STATUS deprecated
	DESCRIPTION
        "
        Row definition for the pm1004dcpMesrxfp1LxAux2Meas
        table
        "
	INDEX   { pm1004dcpMesrxfp1LxAux2MeasIndex }
	::= { pm1004dcpMesrxfp1LxAux2MeasTable 1 }


Pm1004dcpMesrxfp1LxAux2MeasEntry ::=
	SEQUENCE {
	pm1004dcpMesrxfp1LxAux2MeasIndex
		INTEGER,
	pm1004dcpMesrxfp1LxAux2MeasPortn
		INTEGER
	}


pm1004dcpMesrxfp1LxAux2MeasIndex OBJECT-TYPE
	SYNTAX  INTEGER(0..128)
	MAX-ACCESS  read-only
	STATUS deprecated
	DESCRIPTION
        "
        Index definition for the pm1004dcpMesrxfp1LxAux2Meas
        table
        "
	::= { pm1004dcpMesrxfp1LxAux2MeasEntry 1 }


pm1004dcpMesrxfp1LxAux2MeasPortn OBJECT-TYPE
	SYNTAX  INTEGER (0..65535)
	MAX-ACCESS read-only
	STATUS deprecated
	DESCRIPTION
        "
        Not Used :This OID gives the receive
        power value read in the DDM (Digital
        Diagnostic Monitoring) of the XFP
        or OTX plugged in line #n (Unit
        = ?)
        "
	::= { pm1004dcpMesrxfp1LxAux2MeasEntry 2 }


--- *********************************************************
---     TABLE for the pm1004dcpMesrotx1Aging articles
--- *********************************************************

pm1004dcpMesrotx1AgingTable OBJECT-TYPE
	SYNTAX  SEQUENCE OF Pm1004dcpMesrotx1AgingEntry
	MAX-ACCESS not-accessible
	STATUS current
	DESCRIPTION
        "
        List of pm1004dcpMesrotx1Aging
        Article
        "
	::= { pm1004dcpMesrLine 224 }


pm1004dcpMesrotx1AgingEntry OBJECT-TYPE
	SYNTAX Pm1004dcpMesrotx1AgingEntry
	MAX-ACCESS not-accessible
	STATUS current
	DESCRIPTION
        "
        Row definition for the pm1004dcpMesrotx1Aging
        table
        "
	INDEX   { pm1004dcpMesrotx1AgingIndex }
	::= { pm1004dcpMesrotx1AgingTable 1 }


Pm1004dcpMesrotx1AgingEntry ::=
	SEQUENCE {
	pm1004dcpMesrotx1AgingIndex
		INTEGER,
	pm1004dcpMesrotx1AgingPortn
		INTEGER
	}


pm1004dcpMesrotx1AgingIndex OBJECT-TYPE
	SYNTAX  INTEGER(0..128)
	MAX-ACCESS  read-only
	STATUS current
	DESCRIPTION
        "
        Index definition for the pm1004dcpMesrotx1Aging
        table
        "
	::= { pm1004dcpMesrotx1AgingEntry 1 }


pm1004dcpMesrotx1AgingPortn OBJECT-TYPE
	SYNTAX  INTEGER (0..65535)
	MAX-ACCESS read-only
	STATUS current
	DESCRIPTION
        "
        Line OTX TLH Aging :This OID gives
        the aging of the Line OTX TLH,
         read from the DDM (Digital Diagnostic
        Monitoring)  (Aging = AV) (Unit
        = %)  <Help>  This measure gives
        the aging of the Line OTX TLH
        "
	::= { pm1004dcpMesrotx1AgingEntry 2 }


--- *********************************************************
---     TABLE for the pm1004dcpMesrotx1LaserTemperature articles
--- *********************************************************

pm1004dcpMesrotx1LaserTemperatureTable OBJECT-TYPE
	SYNTAX  SEQUENCE OF Pm1004dcpMesrotx1LaserTemperatureEntry
	MAX-ACCESS not-accessible
	STATUS deprecated
	DESCRIPTION
        "
        List of pm1004dcpMesrotx1LaserTemperature
        Article
        "
	::= { pm1004dcpMesrLine 225 }


pm1004dcpMesrotx1LaserTemperatureEntry OBJECT-TYPE
	SYNTAX Pm1004dcpMesrotx1LaserTemperatureEntry
	MAX-ACCESS not-accessible
	STATUS deprecated
	DESCRIPTION
        "
        Row definition for the pm1004dcpMesrotx1LaserTemperature
        table
        "
	INDEX   { pm1004dcpMesrotx1LaserTemperatureIndex }
	::= { pm1004dcpMesrotx1LaserTemperatureTable 1 }


Pm1004dcpMesrotx1LaserTemperatureEntry ::=
	SEQUENCE {
	pm1004dcpMesrotx1LaserTemperatureIndex
		INTEGER,
	pm1004dcpMesrotx1LaserTemperaturePortn
		INTEGER
	}


pm1004dcpMesrotx1LaserTemperatureIndex OBJECT-TYPE
	SYNTAX  INTEGER(0..128)
	MAX-ACCESS  read-only
	STATUS deprecated
	DESCRIPTION
        "
        Index definition for the pm1004dcpMesrotx1LaserTemperature
        table
        "
	::= { pm1004dcpMesrotx1LaserTemperatureEntry 1 }


pm1004dcpMesrotx1LaserTemperaturePortn OBJECT-TYPE
	SYNTAX  INTEGER (0..65535)
	MAX-ACCESS read-only
	STATUS deprecated
	DESCRIPTION
        "
        Line OTX TLH Laser Temperature
        :This OID gives the laser temperature
        of the Line OTX TLH, read from
         the DDM (Digital Diagnostic Monitoring)
         (Temperature = AV/256) (Unit =
        C)  <Help>  This measure gives
         the laser temperature of the Line
        OTX TLH
        "
	::= { pm1004dcpMesrotx1LaserTemperatureEntry 2 }


--- *********************************************************
---     TABLE for the pm1004dcpMesrotx1FreqDeviation articles
--- *********************************************************

pm1004dcpMesrotx1FreqDeviationTable OBJECT-TYPE
	SYNTAX  SEQUENCE OF Pm1004dcpMesrotx1FreqDeviationEntry
	MAX-ACCESS not-accessible
	STATUS current
	DESCRIPTION
        "
        List of pm1004dcpMesrotx1FreqDeviation
        Article
        "
	::= { pm1004dcpMesrLine 226 }


pm1004dcpMesrotx1FreqDeviationEntry OBJECT-TYPE
	SYNTAX Pm1004dcpMesrotx1FreqDeviationEntry
	MAX-ACCESS not-accessible
	STATUS current
	DESCRIPTION
        "
        Row definition for the pm1004dcpMesrotx1FreqDeviation
        table
        "
	INDEX   { pm1004dcpMesrotx1FreqDeviationIndex }
	::= { pm1004dcpMesrotx1FreqDeviationTable 1 }


Pm1004dcpMesrotx1FreqDeviationEntry ::=
	SEQUENCE {
	pm1004dcpMesrotx1FreqDeviationIndex
		INTEGER,
	pm1004dcpMesrotx1FreqDeviationPortn
		INTEGER
	}


pm1004dcpMesrotx1FreqDeviationIndex OBJECT-TYPE
	SYNTAX  INTEGER(0..128)
	MAX-ACCESS  read-only
	STATUS current
	DESCRIPTION
        "
        Index definition for the pm1004dcpMesrotx1FreqDeviation
        table
        "
	::= { pm1004dcpMesrotx1FreqDeviationEntry 1 }


pm1004dcpMesrotx1FreqDeviationPortn OBJECT-TYPE
	SYNTAX  INTEGER (0..65535)
	MAX-ACCESS read-only
	STATUS current
	DESCRIPTION
        "
        Line OTX TLH Frequency Deviation
        :This OID gives the frequency deviation
        of the Line OTX TLH, read from
         the DDM (Digital Diagnostic Monitoring)
         (Deviation = (AV-32768)*100)
         (Unit = MHz)  <Help>  This measure
        gives the frequency deviation of
        the Line OTX TLH
        "
	::= { pm1004dcpMesrotx1FreqDeviationEntry 2 }


--- *********************************************************
---     TABLE for the pm1004dcpMesrotx1LaserWvlength articles
--- *********************************************************

pm1004dcpMesrotx1LaserWvlengthTable OBJECT-TYPE
	SYNTAX  SEQUENCE OF Pm1004dcpMesrotx1LaserWvlengthEntry
	MAX-ACCESS not-accessible
	STATUS current
	DESCRIPTION
        "
        List of pm1004dcpMesrotx1LaserWvlength
        Article
        "
	::= { pm1004dcpMesrLine 227 }


pm1004dcpMesrotx1LaserWvlengthEntry OBJECT-TYPE
	SYNTAX Pm1004dcpMesrotx1LaserWvlengthEntry
	MAX-ACCESS not-accessible
	STATUS current
	DESCRIPTION
        "
        Row definition for the pm1004dcpMesrotx1LaserWvlength
        table
        "
	INDEX   { pm1004dcpMesrotx1LaserWvlengthIndex }
	::= { pm1004dcpMesrotx1LaserWvlengthTable 1 }


Pm1004dcpMesrotx1LaserWvlengthEntry ::=
	SEQUENCE {
	pm1004dcpMesrotx1LaserWvlengthIndex
		INTEGER,
	pm1004dcpMesrotx1LaserWvlengthPortn
		INTEGER
	}


pm1004dcpMesrotx1LaserWvlengthIndex OBJECT-TYPE
	SYNTAX  INTEGER(0..128)
	MAX-ACCESS  read-only
	STATUS current
	DESCRIPTION
        "
        Index definition for the pm1004dcpMesrotx1LaserWvlength
        table
        "
	::= { pm1004dcpMesrotx1LaserWvlengthEntry 1 }


pm1004dcpMesrotx1LaserWvlengthPortn OBJECT-TYPE
	SYNTAX  INTEGER (0..65535)
	MAX-ACCESS read-only
	STATUS current
	DESCRIPTION
        "
        Line Optical Module Wavelength
        :This OID gives the laser wavelength
        of the Line OTX TLH, read from
         the DDM (Digital Diagnostic Monitoring)
        (Wavelength=299792458/((193,100+(AV-32768
        )*12,5)*10 3)) (Unit = nm)  <Help>
         This measure gives the laser wavelength
        of the Line OTX TLH
        "
	::= { pm1004dcpMesrotx1LaserWvlengthEntry 2 }







--- *****************************************************
--- $$$$$$$$$$$$$$$$$$$$$$$$$$$$$$$$$$$$$$$$$$$$$$$$$$$$$
---     PERFORMANCE
--- $$$$$$$$$$$$$$$$$$$$$$$$$$$$$$$$$$$$$$$$$$$$$$$$$$$$$
--- *****************************************************



--- *********************************************************
---     TABLE for the pm1004dcpPerfUpCurrent15Cnt articles
--- *********************************************************

pm1004dcpPerfUpCurrent15CntTable OBJECT-TYPE
	SYNTAX  SEQUENCE OF Pm1004dcpPerfUpCurrent15CntEntry
	MAX-ACCESS not-accessible
	STATUS current
	DESCRIPTION
        "
        List of pm1004dcpPerfUpCurrent15Cnt
        Article
        "
	::= { pm1004dcpMonClientPerformance 16 }


pm1004dcpPerfUpCurrent15CntEntry OBJECT-TYPE
	SYNTAX Pm1004dcpPerfUpCurrent15CntEntry
	MAX-ACCESS not-accessible
	STATUS current
	DESCRIPTION
        "
        Row definition for the pm1004dcpPerfUpCurrent15Cnt
        table
        "
	INDEX   { pm1004dcpPerfUpCurrent15CntIndex }
	::= { pm1004dcpPerfUpCurrent15CntTable 1 }


Pm1004dcpPerfUpCurrent15CntEntry ::=
	SEQUENCE {
	pm1004dcpPerfUpCurrent15CntIndex
		INTEGER,
	pm1004dcpPerfUpCurrent15CntInvCvPortn
		EkiOnOff,
	pm1004dcpPerfUpCurrent15CntCvValuePortn
		Unsigned32,
	pm1004dcpPerfUpCurrent15CntInvEsPortn
		EkiOnOff,
	pm1004dcpPerfUpCurrent15CntEsValuePortn
		Unsigned32,
	pm1004dcpPerfUpCurrent15CntInvSesPortn
		EkiOnOff,
	pm1004dcpPerfUpCurrent15CntSesValuePortn
		Unsigned32,
	pm1004dcpPerfUpCurrent15CntInvSefsPortn
		EkiOnOff,
	pm1004dcpPerfUpCurrent15CntSefsValuePortn
		Unsigned32,
	pm1004dcpPerfUpCurrent15CntInvUasPortn
		EkiOnOff,
	pm1004dcpPerfUpCurrent15CntUasValuePortn
		Unsigned32
	}


pm1004dcpPerfUpCurrent15CntIndex OBJECT-TYPE
	SYNTAX  INTEGER(0..128)
	MAX-ACCESS  read-only
	STATUS current
	DESCRIPTION
        "
        Index definition for the pm1004dcpPerfUpCurrent15Cnt
        table
        "
	::= { pm1004dcpPerfUpCurrent15CntEntry 1 }


pm1004dcpPerfUpCurrent15CntInvCvPortn OBJECT-TYPE
	SYNTAX  EkiOnOff
	MAX-ACCESS read-only
	STATUS current
	DESCRIPTION
        "
        Current 15-min CV counter inv.
        :This OID indicates that the current
        15-min Coding Violation counter
        is invalid
        "
	::= { pm1004dcpPerfUpCurrent15CntEntry 2 }


pm1004dcpPerfUpCurrent15CntCvValuePortn OBJECT-TYPE
	SYNTAX  Unsigned32
	MAX-ACCESS read-only
	STATUS current
	DESCRIPTION
        "
        Current 15-min CV counter :This
        OID gives the current 15-min Coding
        Violation counter value
        "
	::= { pm1004dcpPerfUpCurrent15CntEntry 3 }


pm1004dcpPerfUpCurrent15CntInvEsPortn OBJECT-TYPE
	SYNTAX  EkiOnOff
	MAX-ACCESS read-only
	STATUS current
	DESCRIPTION
        "
        Current 15-min ES counter inv.
        :This OID indicates that the current
        15-min Errored Second counter is
        invalid
        "
	::= { pm1004dcpPerfUpCurrent15CntEntry 4 }


pm1004dcpPerfUpCurrent15CntEsValuePortn OBJECT-TYPE
	SYNTAX  Unsigned32
	MAX-ACCESS read-only
	STATUS current
	DESCRIPTION
        "
        Current 15-min ES counter :This
        OID gives the current 15-min Errored
        Second counter value
        "
	::= { pm1004dcpPerfUpCurrent15CntEntry 5 }


pm1004dcpPerfUpCurrent15CntInvSesPortn OBJECT-TYPE
	SYNTAX  EkiOnOff
	MAX-ACCESS read-only
	STATUS current
	DESCRIPTION
        "
        Current 15-min SES counter inv.
        :This OID indicates that the current
        15-min severely Errored Second
         counter is invalid
        "
	::= { pm1004dcpPerfUpCurrent15CntEntry 6 }


pm1004dcpPerfUpCurrent15CntSesValuePortn OBJECT-TYPE
	SYNTAX  Unsigned32
	MAX-ACCESS read-only
	STATUS current
	DESCRIPTION
        "
        Current 15-min SES counter :This
        OID gives the current 15-min severely
        Errored Second counter value
        "
	::= { pm1004dcpPerfUpCurrent15CntEntry 7 }


pm1004dcpPerfUpCurrent15CntInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pm1004dcpPerfUpCurrent15CntEntry 8 }


pm1004dcpPerfUpCurrent15CntSefsValuePortn OBJECT-TYPE
	SYNTAX  Unsigned32
	MAX-ACCESS read-only
	STATUS current
	DESCRIPTION
        "
        Current 15-min SEFS counter :This
        OID gives the current 15-min severely
        Errored Framing Second counter
         value
        "
	::= { pm1004dcpPerfUpCurrent15CntEntry 9 }


pm1004dcpPerfUpCurrent15CntInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pm1004dcpPerfUpCurrent15CntEntry 10 }


pm1004dcpPerfUpCurrent15CntUasValuePortn OBJECT-TYPE
	SYNTAX  Unsigned32
	MAX-ACCESS read-only
	STATUS current
	DESCRIPTION
        "
        Current 15-min UAS counter :This
        OID gives the current 15-min UnAvailable
        Second counter value
        "
	::= { pm1004dcpPerfUpCurrent15CntEntry 11 }


--- *********************************************************
---     TABLE for the pm1004dcpPerfUpPast15Cnt articles
--- *********************************************************

pm1004dcpPerfUpPast15CntTable OBJECT-TYPE
	SYNTAX  SEQUENCE OF Pm1004dcpPerfUpPast15CntEntry
	MAX-ACCESS not-accessible
	STATUS current
	DESCRIPTION
        "
        List of pm1004dcpPerfUpPast15Cnt
        Article
        "
	::= { pm1004dcpMonClientPerformance 24 }


pm1004dcpPerfUpPast15CntEntry OBJECT-TYPE
	SYNTAX Pm1004dcpPerfUpPast15CntEntry
	MAX-ACCESS not-accessible
	STATUS current
	DESCRIPTION
        "
        Row definition for the pm1004dcpPerfUpPast15Cnt
        table
        "
	INDEX   { pm1004dcpPerfUpPast15CntIndex }
	::= { pm1004dcpPerfUpPast15CntTable 1 }


Pm1004dcpPerfUpPast15CntEntry ::=
	SEQUENCE {
	pm1004dcpPerfUpPast15CntIndex
		INTEGER,
	pm1004dcpPerfUpPast15CntInvCvPortn
		EkiOnOff,
	pm1004dcpPerfUpPast15CntCvValuePortn
		Unsigned32,
	pm1004dcpPerfUpPast15CntInvEsPortn
		EkiOnOff,
	pm1004dcpPerfUpPast15CntEsValuePortn
		Unsigned32,
	pm1004dcpPerfUpPast15CntInvSesPortn
		EkiOnOff,
	pm1004dcpPerfUpPast15CntSesValuePortn
		Unsigned32,
	pm1004dcpPerfUpPast15CntInvSefsPortn
		EkiOnOff,
	pm1004dcpPerfUpPast15CntSefsValuePortn
		Unsigned32,
	pm1004dcpPerfUpPast15CntInvUasPortn
		EkiOnOff,
	pm1004dcpPerfUpPast15CntUasValuePortn
		Unsigned32
	}


pm1004dcpPerfUpPast15CntIndex OBJECT-TYPE
	SYNTAX  INTEGER(0..128)
	MAX-ACCESS  read-only
	STATUS current
	DESCRIPTION
        "
        Index definition for the pm1004dcpPerfUpPast15Cnt
        table
        "
	::= { pm1004dcpPerfUpPast15CntEntry 1 }


pm1004dcpPerfUpPast15CntInvCvPortn OBJECT-TYPE
	SYNTAX  EkiOnOff
	MAX-ACCESS read-only
	STATUS current
	DESCRIPTION
        "
        Previous 15-min CV counter inv.
        :This OID indicates that the previous
        15-min Coding Violation counter
        is invalid
        "
	::= { pm1004dcpPerfUpPast15CntEntry 2 }


pm1004dcpPerfUpPast15CntCvValuePortn OBJECT-TYPE
	SYNTAX  Unsigned32
	MAX-ACCESS read-only
	STATUS current
	DESCRIPTION
        "
        Previous 15-min CV counter :This
        OID gives the previous 15-min Coding
        Violation counter value
        "
	::= { pm1004dcpPerfUpPast15CntEntry 3 }


pm1004dcpPerfUpPast15CntInvEsPortn OBJECT-TYPE
	SYNTAX  EkiOnOff
	MAX-ACCESS read-only
	STATUS current
	DESCRIPTION
        "
        Previous 15-min ES counter inv.
        :This OID indicates that the previous
        15-min Errored Second counter is
        invalid
        "
	::= { pm1004dcpPerfUpPast15CntEntry 4 }


pm1004dcpPerfUpPast15CntEsValuePortn OBJECT-TYPE
	SYNTAX  Unsigned32
	MAX-ACCESS read-only
	STATUS current
	DESCRIPTION
        "
        Previous 15-min ES counter :This
        OID gives the previous 15-min Errored
        Second counter value
        "
	::= { pm1004dcpPerfUpPast15CntEntry 5 }


pm1004dcpPerfUpPast15CntInvSesPortn OBJECT-TYPE
	SYNTAX  EkiOnOff
	MAX-ACCESS read-only
	STATUS current
	DESCRIPTION
        "
        Previous 15-min SES counter inv.
        :This OID indicates that the previous
        15-min severely Errored Second
         counter is invalid
        "
	::= { pm1004dcpPerfUpPast15CntEntry 6 }


pm1004dcpPerfUpPast15CntSesValuePortn OBJECT-TYPE
	SYNTAX  Unsigned32
	MAX-ACCESS read-only
	STATUS current
	DESCRIPTION
        "
        Previous 15-min SES counter :This
        OID gives the previous 15-min severely
        Errored Second counter value
        "
	::= { pm1004dcpPerfUpPast15CntEntry 7 }


pm1004dcpPerfUpPast15CntInvSefsPortn OBJECT-TYPE
	SYNTAX  EkiOnOff
	MAX-ACCESS read-only
	STATUS current
	DESCRIPTION
        "
        Previous 15-min SEFS counter inv.
        :This OID indicates that the previous
        15-min severely Errored Framing
        Second counter is invalid
        "
	::= { pm1004dcpPerfUpPast15CntEntry 8 }


pm1004dcpPerfUpPast15CntSefsValuePortn OBJECT-TYPE
	SYNTAX  Unsigned32
	MAX-ACCESS read-only
	STATUS current
	DESCRIPTION
        "
        Previous 15-min SEFS counter :This
        OID gives the previous 15-min severely
        Errored Framing Second counter
         value
        "
	::= { pm1004dcpPerfUpPast15CntEntry 9 }


pm1004dcpPerfUpPast15CntInvUasPortn OBJECT-TYPE
	SYNTAX  EkiOnOff
	MAX-ACCESS read-only
	STATUS current
	DESCRIPTION
        "
        Previous 15-min UAS counter inv.
        :This OID indicates that the previous
        15-min UnAvailable Second counter
        is invalid
        "
	::= { pm1004dcpPerfUpPast15CntEntry 10 }


pm1004dcpPerfUpPast15CntUasValuePortn OBJECT-TYPE
	SYNTAX  Unsigned32
	MAX-ACCESS read-only
	STATUS current
	DESCRIPTION
        "
        Previous 15-min UAS counter :This
        OID gives the previous 15-min UnAvailable
        Second counter value
        "
	::= { pm1004dcpPerfUpPast15CntEntry 11 }


--- *********************************************************
---     TABLE for the pm1004dcpPerfUpCurrent24Cnt articles
--- *********************************************************

pm1004dcpPerfUpCurrent24CntTable OBJECT-TYPE
	SYNTAX  SEQUENCE OF Pm1004dcpPerfUpCurrent24CntEntry
	MAX-ACCESS not-accessible
	STATUS current
	DESCRIPTION
        "
        List of pm1004dcpPerfUpCurrent24Cnt
        Article
        "
	::= { pm1004dcpMonClientPerformance 32 }


pm1004dcpPerfUpCurrent24CntEntry OBJECT-TYPE
	SYNTAX Pm1004dcpPerfUpCurrent24CntEntry
	MAX-ACCESS not-accessible
	STATUS current
	DESCRIPTION
        "
        Row definition for the pm1004dcpPerfUpCurrent24Cnt
        table
        "
	INDEX   { pm1004dcpPerfUpCurrent24CntIndex }
	::= { pm1004dcpPerfUpCurrent24CntTable 1 }


Pm1004dcpPerfUpCurrent24CntEntry ::=
	SEQUENCE {
	pm1004dcpPerfUpCurrent24CntIndex
		INTEGER,
	pm1004dcpPerfUpCurrent24CntInvCvPortn
		EkiOnOff,
	pm1004dcpPerfUpCurrent24CntCvValuePortn
		Unsigned32,
	pm1004dcpPerfUpCurrent24CntInvEsPortn
		EkiOnOff,
	pm1004dcpPerfUpCurrent24CntEsValuePortn
		Unsigned32,
	pm1004dcpPerfUpCurrent24CntInvSesPortn
		EkiOnOff,
	pm1004dcpPerfUpCurrent24CntSesValuePortn
		Unsigned32,
	pm1004dcpPerfUpCurrent24CntInvSefsPortn
		EkiOnOff,
	pm1004dcpPerfUpCurrent24CntSefsValuePortn
		Unsigned32,
	pm1004dcpPerfUpCurrent24CntInvUasPortn
		EkiOnOff,
	pm1004dcpPerfUpCurrent24CntUasValuePortn
		Unsigned32
	}


pm1004dcpPerfUpCurrent24CntIndex OBJECT-TYPE
	SYNTAX  INTEGER(0..128)
	MAX-ACCESS  read-only
	STATUS current
	DESCRIPTION
        "
        Index definition for the pm1004dcpPerfUpCurrent24Cnt
        table
        "
	::= { pm1004dcpPerfUpCurrent24CntEntry 1 }


pm1004dcpPerfUpCurrent24CntInvCvPortn OBJECT-TYPE
	SYNTAX  EkiOnOff
	MAX-ACCESS read-only
	STATUS current
	DESCRIPTION
        "
        Current 24-hours CV counter inv.
        :This OID indicates that the current
        24-hours Coding Violation counter
        is invalid
        "
	::= { pm1004dcpPerfUpCurrent24CntEntry 2 }


pm1004dcpPerfUpCurrent24CntCvValuePortn OBJECT-TYPE
	SYNTAX  Unsigned32
	MAX-ACCESS read-only
	STATUS current
	DESCRIPTION
        "
        Current 24-hours CV counter :This
        OID gives the current 24-hours
         Coding Violation counter value
        "
	::= { pm1004dcpPerfUpCurrent24CntEntry 3 }


pm1004dcpPerfUpCurrent24CntInvEsPortn OBJECT-TYPE
	SYNTAX  EkiOnOff
	MAX-ACCESS read-only
	STATUS current
	DESCRIPTION
        "
        Current 24-hours ES counter inv.
        :This OID indicates that the current
        24-hours Errored Second counter
        is invalid
        "
	::= { pm1004dcpPerfUpCurrent24CntEntry 4 }


pm1004dcpPerfUpCurrent24CntEsValuePortn OBJECT-TYPE
	SYNTAX  Unsigned32
	MAX-ACCESS read-only
	STATUS current
	DESCRIPTION
        "
        Current 24-hours ES counter :This
        OID gives the current 24-hours
         Errored Second counter value
        "
	::= { pm1004dcpPerfUpCurrent24CntEntry 5 }


pm1004dcpPerfUpCurrent24CntInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pm1004dcpPerfUpCurrent24CntEntry 6 }


pm1004dcpPerfUpCurrent24CntSesValuePortn OBJECT-TYPE
	SYNTAX  Unsigned32
	MAX-ACCESS read-only
	STATUS current
	DESCRIPTION
        "
        Current 24-hours SES counter :This
        OID gives the current 24-hours
         severely Errored Second counter
        value
        "
	::= { pm1004dcpPerfUpCurrent24CntEntry 7 }


pm1004dcpPerfUpCurrent24CntInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pm1004dcpPerfUpCurrent24CntEntry 8 }


pm1004dcpPerfUpCurrent24CntSefsValuePortn OBJECT-TYPE
	SYNTAX  Unsigned32
	MAX-ACCESS read-only
	STATUS current
	DESCRIPTION
        "
        Current 24-hours SEFS counter
         :This OID gives the current 24-hours
        severely Errored Framing Second
        counter value
        "
	::= { pm1004dcpPerfUpCurrent24CntEntry 9 }


pm1004dcpPerfUpCurrent24CntInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pm1004dcpPerfUpCurrent24CntEntry 10 }


pm1004dcpPerfUpCurrent24CntUasValuePortn OBJECT-TYPE
	SYNTAX  Unsigned32
	MAX-ACCESS read-only
	STATUS current
	DESCRIPTION
        "
        Current 24-hours UAS counter :This
        OID gives the current 24-hours
         UnAvailable Second counter value
        "
	::= { pm1004dcpPerfUpCurrent24CntEntry 11 }


--- *********************************************************
---     TABLE for the pm1004dcpPerfUpPast24Cnt articles
--- *********************************************************

pm1004dcpPerfUpPast24CntTable OBJECT-TYPE
	SYNTAX  SEQUENCE OF Pm1004dcpPerfUpPast24CntEntry
	MAX-ACCESS not-accessible
	STATUS current
	DESCRIPTION
        "
        List of pm1004dcpPerfUpPast24Cnt
        Article
        "
	::= { pm1004dcpMonClientPerformance 40 }


pm1004dcpPerfUpPast24CntEntry OBJECT-TYPE
	SYNTAX Pm1004dcpPerfUpPast24CntEntry
	MAX-ACCESS not-accessible
	STATUS current
	DESCRIPTION
        "
        Row definition for the pm1004dcpPerfUpPast24Cnt
        table
        "
	INDEX   { pm1004dcpPerfUpPast24CntIndex }
	::= { pm1004dcpPerfUpPast24CntTable 1 }


Pm1004dcpPerfUpPast24CntEntry ::=
	SEQUENCE {
	pm1004dcpPerfUpPast24CntIndex
		INTEGER,
	pm1004dcpPerfUpPast24CntInvCvPortn
		EkiOnOff,
	pm1004dcpPerfUpPast24CntCvValuePortn
		Unsigned32,
	pm1004dcpPerfUpPast24CntInvEsPortn
		EkiOnOff,
	pm1004dcpPerfUpPast24CntEsValuePortn
		Unsigned32,
	pm1004dcpPerfUpPast24CntInvSesPortn
		EkiOnOff,
	pm1004dcpPerfUpPast24CntSesValuePortn
		Unsigned32,
	pm1004dcpPerfUpPast24CntInvSefsPortn
		EkiOnOff,
	pm1004dcpPerfUpPast24CntSefsValuePortn
		Unsigned32,
	pm1004dcpPerfUpPast24CntInvUasPortn
		EkiOnOff,
	pm1004dcpPerfUpPast24CntUasValuePortn
		Unsigned32
	}


pm1004dcpPerfUpPast24CntIndex OBJECT-TYPE
	SYNTAX  INTEGER(0..128)
	MAX-ACCESS  read-only
	STATUS current
	DESCRIPTION
        "
        Index definition for the pm1004dcpPerfUpPast24Cnt
        table
        "
	::= { pm1004dcpPerfUpPast24CntEntry 1 }


pm1004dcpPerfUpPast24CntInvCvPortn OBJECT-TYPE
	SYNTAX  EkiOnOff
	MAX-ACCESS read-only
	STATUS current
	DESCRIPTION
        "
        Previous 24-hours CV counter inv.
        :This OID indicates that the previous
        24-hours Coding Violation counter
        is invalid
        "
	::= { pm1004dcpPerfUpPast24CntEntry 2 }


pm1004dcpPerfUpPast24CntCvValuePortn OBJECT-TYPE
	SYNTAX  Unsigned32
	MAX-ACCESS read-only
	STATUS current
	DESCRIPTION
        "
        Previous 24-hours CV counter :This
        OID gives the previous 24-hours
        Coding Violation counter value
        "
	::= { pm1004dcpPerfUpPast24CntEntry 3 }


pm1004dcpPerfUpPast24CntInvEsPortn OBJECT-TYPE
	SYNTAX  EkiOnOff
	MAX-ACCESS read-only
	STATUS current
	DESCRIPTION
        "
        Previous 24-hours ES counter inv.
        :This OID indicates that the previous
        24-hours Errored Second counter
        is invalid
        "
	::= { pm1004dcpPerfUpPast24CntEntry 4 }


pm1004dcpPerfUpPast24CntEsValuePortn OBJECT-TYPE
	SYNTAX  Unsigned32
	MAX-ACCESS read-only
	STATUS current
	DESCRIPTION
        "
        Previous 24-hours ES counter :This
        OID gives the previous 24-hours
        Errored Second counter value
        "
	::= { pm1004dcpPerfUpPast24CntEntry 5 }


pm1004dcpPerfUpPast24CntInvSesPortn OBJECT-TYPE
	SYNTAX  EkiOnOff
	MAX-ACCESS read-only
	STATUS current
	DESCRIPTION
        "
        Previous 24-hours SES counter
         inv. :This OID indicates that
         the previous 24-hours severely
        Errored Second counter is invalid
        "
	::= { pm1004dcpPerfUpPast24CntEntry 6 }


pm1004dcpPerfUpPast24CntSesValuePortn OBJECT-TYPE
	SYNTAX  Unsigned32
	MAX-ACCESS read-only
	STATUS current
	DESCRIPTION
        "
        Previous 24-hours SES counter
         :This OID gives the previous 24-hours
        severely Errored Second counter
        value
        "
	::= { pm1004dcpPerfUpPast24CntEntry 7 }


pm1004dcpPerfUpPast24CntInvSefsPortn OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm1004dcpPerfUpPast24CntEntry 8 }


pm1004dcpPerfUpPast24CntSefsValuePortn OBJECT-TYPE
	SYNTAX  Unsigned32
	MAX-ACCESS read-only
	STATUS current
	DESCRIPTION
        "
        Previous 24-hours SEFS counter
        :This OID gives the previous 24-hours
        severely Errored Framing Second
        counter value
        "
	::= { pm1004dcpPerfUpPast24CntEntry 9 }


pm1004dcpPerfUpPast24CntInvUasPortn OBJECT-TYPE
	SYNTAX  EkiOnOff
	MAX-ACCESS read-only
	STATUS current
	DESCRIPTION
        "
        Previous 24-hours UAS counter
         inv. :This OID indicates that
         the previous 24-hours UnAvailable
        Second counter is invalid
        "
	::= { pm1004dcpPerfUpPast24CntEntry 10 }


pm1004dcpPerfUpPast24CntUasValuePortn OBJECT-TYPE
	SYNTAX  Unsigned32
	MAX-ACCESS read-only
	STATUS current
	DESCRIPTION
        "
        Previous 24-hours UAS counter
         :This OID gives the previous 24-hours
        UnAvailable Second counter value
        "
	::= { pm1004dcpPerfUpPast24CntEntry 11 }


--- *********************************************************
---     TABLE for the pm1004dcpPerfLineCurrent15Cnt articles
--- *********************************************************

pm1004dcpPerfLineCurrent15CntTable OBJECT-TYPE
	SYNTAX  SEQUENCE OF Pm1004dcpPerfLineCurrent15CntEntry
	MAX-ACCESS not-accessible
	STATUS current
	DESCRIPTION
        "
        List of pm1004dcpPerfLineCurrent15Cnt
        Article
        "
	::= { pm1004dcpMonLinePerformance 128 }


pm1004dcpPerfLineCurrent15CntEntry OBJECT-TYPE
	SYNTAX Pm1004dcpPerfLineCurrent15CntEntry
	MAX-ACCESS not-accessible
	STATUS current
	DESCRIPTION
        "
        Row definition for the pm1004dcpPerfLineCurrent15Cnt
        table
        "
	INDEX   { pm1004dcpPerfLineCurrent15CntIndex }
	::= { pm1004dcpPerfLineCurrent15CntTable 1 }


Pm1004dcpPerfLineCurrent15CntEntry ::=
	SEQUENCE {
	pm1004dcpPerfLineCurrent15CntIndex
		INTEGER,
	pm1004dcpPerfLineCurrent15CntInvCvPortn
		EkiOnOff,
	pm1004dcpPerfLineCurrent15CntCvValuePortn
		Unsigned32,
	pm1004dcpPerfLineCurrent15CntInvEsPortn
		EkiOnOff,
	pm1004dcpPerfLineCurrent15CntEsValuePortn
		Unsigned32,
	pm1004dcpPerfLineCurrent15CntInvSesPortn
		EkiOnOff,
	pm1004dcpPerfLineCurrent15CntSesValuePortn
		Unsigned32,
	pm1004dcpPerfLineCurrent15CntInvSefsPortn
		EkiOnOff,
	pm1004dcpPerfLineCurrent15CntSefsValuePortn
		Unsigned32,
	pm1004dcpPerfLineCurrent15CntInvUasPortn
		EkiOnOff,
	pm1004dcpPerfLineCurrent15CntUasValuePortn
		Unsigned32
	}


pm1004dcpPerfLineCurrent15CntIndex OBJECT-TYPE
	SYNTAX  INTEGER(0..128)
	MAX-ACCESS  read-only
	STATUS current
	DESCRIPTION
        "
        Index definition for the pm1004dcpPerfLineCurrent15Cnt
        table
        "
	::= { pm1004dcpPerfLineCurrent15CntEntry 1 }


pm1004dcpPerfLineCurrent15CntInvCvPortn OBJECT-TYPE
	SYNTAX  EkiOnOff
	MAX-ACCESS read-only
	STATUS current
	DESCRIPTION
        "
        Current 15-min CV counter inv.
        :This OID indicates that the current
        15-min Coding Violation counter
        is invalid
        "
	::= { pm1004dcpPerfLineCurrent15CntEntry 2 }


pm1004dcpPerfLineCurrent15CntCvValuePortn OBJECT-TYPE
	SYNTAX  Unsigned32
	MAX-ACCESS read-only
	STATUS current
	DESCRIPTION
        "
        Current 15-min CV counter :This
        OID gives the current 15-min Coding
        Violation counter value
        "
	::= { pm1004dcpPerfLineCurrent15CntEntry 3 }


pm1004dcpPerfLineCurrent15CntInvEsPortn OBJECT-TYPE
	SYNTAX  EkiOnOff
	MAX-ACCESS read-only
	STATUS current
	DESCRIPTION
        "
        Current 15-min ES counter inv.
        :This OID indicates that the current
        15-min Errored Second counter is
        invalid
        "
	::= { pm1004dcpPerfLineCurrent15CntEntry 4 }


pm1004dcpPerfLineCurrent15CntEsValuePortn OBJECT-TYPE
	SYNTAX  Unsigned32
	MAX-ACCESS read-only
	STATUS current
	DESCRIPTION
        "
        Current 15-min ES counter :This
        OID gives the current 15-min Errored
        Second counter value
        "
	::= { pm1004dcpPerfLineCurrent15CntEntry 5 }


pm1004dcpPerfLineCurrent15CntInvSesPortn OBJECT-TYPE
	SYNTAX  EkiOnOff
	MAX-ACCESS read-only
	STATUS current
	DESCRIPTION
        "
        Current 15-min SES counter inv.
        :This OID indicates that the current
        15-min severely Errored Second
         counter is invalid
        "
	::= { pm1004dcpPerfLineCurrent15CntEntry 6 }


pm1004dcpPerfLineCurrent15CntSesValuePortn OBJECT-TYPE
	SYNTAX  Unsigned32
	MAX-ACCESS read-only
	STATUS current
	DESCRIPTION
        "
        Current 15-min SES counter :This
        OID gives the current 15-min severely
        Errored Second counter value
        "
	::= { pm1004dcpPerfLineCurrent15CntEntry 7 }


pm1004dcpPerfLineCurrent15CntInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pm1004dcpPerfLineCurrent15CntEntry 8 }


pm1004dcpPerfLineCurrent15CntSefsValuePortn OBJECT-TYPE
	SYNTAX  Unsigned32
	MAX-ACCESS read-only
	STATUS current
	DESCRIPTION
        "
        Current 15-min SEFS counter :This
        OID gives the current 15-min severely
        Errored Framing Second counter
         value
        "
	::= { pm1004dcpPerfLineCurrent15CntEntry 9 }


pm1004dcpPerfLineCurrent15CntInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pm1004dcpPerfLineCurrent15CntEntry 10 }


pm1004dcpPerfLineCurrent15CntUasValuePortn OBJECT-TYPE
	SYNTAX  Unsigned32
	MAX-ACCESS read-only
	STATUS current
	DESCRIPTION
        "
        Current 15-min UAS counter :This
        OID gives the current 15-min UnAvailable
        Second counter value
        "
	::= { pm1004dcpPerfLineCurrent15CntEntry 11 }


--- *********************************************************
---     TABLE for the pm1004dcpPerfLinePast15Cnt articles
--- *********************************************************

pm1004dcpPerfLinePast15CntTable OBJECT-TYPE
	SYNTAX  SEQUENCE OF Pm1004dcpPerfLinePast15CntEntry
	MAX-ACCESS not-accessible
	STATUS current
	DESCRIPTION
        "
        List of pm1004dcpPerfLinePast15Cnt
        Article
        "
	::= { pm1004dcpMonLinePerformance 129 }


pm1004dcpPerfLinePast15CntEntry OBJECT-TYPE
	SYNTAX Pm1004dcpPerfLinePast15CntEntry
	MAX-ACCESS not-accessible
	STATUS current
	DESCRIPTION
        "
        Row definition for the pm1004dcpPerfLinePast15Cnt
        table
        "
	INDEX   { pm1004dcpPerfLinePast15CntIndex }
	::= { pm1004dcpPerfLinePast15CntTable 1 }


Pm1004dcpPerfLinePast15CntEntry ::=
	SEQUENCE {
	pm1004dcpPerfLinePast15CntIndex
		INTEGER,
	pm1004dcpPerfLinePast15CntInvCvPortn
		EkiOnOff,
	pm1004dcpPerfLinePast15CntCvValuePortn
		Unsigned32,
	pm1004dcpPerfLinePast15CntInvEsPortn
		EkiOnOff,
	pm1004dcpPerfLinePast15CntEsValuePortn
		Unsigned32,
	pm1004dcpPerfLinePast15CntInvSesPortn
		EkiOnOff,
	pm1004dcpPerfLinePast15CntSesValuePortn
		Unsigned32,
	pm1004dcpPerfLinePast15CntInvSefsPortn
		EkiOnOff,
	pm1004dcpPerfLinePast15CntSefsValuePortn
		Unsigned32,
	pm1004dcpPerfLinePast15CntInvUasPortn
		EkiOnOff,
	pm1004dcpPerfLinePast15CntUasValuePortn
		Unsigned32
	}


pm1004dcpPerfLinePast15CntIndex OBJECT-TYPE
	SYNTAX  INTEGER(0..128)
	MAX-ACCESS  read-only
	STATUS current
	DESCRIPTION
        "
        Index definition for the pm1004dcpPerfLinePast15Cnt
        table
        "
	::= { pm1004dcpPerfLinePast15CntEntry 1 }


pm1004dcpPerfLinePast15CntInvCvPortn OBJECT-TYPE
	SYNTAX  EkiOnOff
	MAX-ACCESS read-only
	STATUS current
	DESCRIPTION
        "
        Previous 15-min CV counter inv.
        :This OID indicates that the previous
        15-min Coding Violation counter
        is invalid
        "
	::= { pm1004dcpPerfLinePast15CntEntry 2 }


pm1004dcpPerfLinePast15CntCvValuePortn OBJECT-TYPE
	SYNTAX  Unsigned32
	MAX-ACCESS read-only
	STATUS current
	DESCRIPTION
        "
        Previous 15-min CV counter :This
        OID gives the previous 15-min Coding
        Violation counter value
        "
	::= { pm1004dcpPerfLinePast15CntEntry 3 }


pm1004dcpPerfLinePast15CntInvEsPortn OBJECT-TYPE
	SYNTAX  EkiOnOff
	MAX-ACCESS read-only
	STATUS current
	DESCRIPTION
        "
        Previous 15-min ES counter inv.
        :This OID indicates that the previous
        15-min Errored Second counter is
        invalid
        "
	::= { pm1004dcpPerfLinePast15CntEntry 4 }


pm1004dcpPerfLinePast15CntEsValuePortn OBJECT-TYPE
	SYNTAX  Unsigned32
	MAX-ACCESS read-only
	STATUS current
	DESCRIPTION
        "
        Previous 15-min ES counter :This
        OID gives the previous 15-min Errored
        Second counter value
        "
	::= { pm1004dcpPerfLinePast15CntEntry 5 }


pm1004dcpPerfLinePast15CntInvSesPortn OBJECT-TYPE
	SYNTAX  EkiOnOff
	MAX-ACCESS read-only
	STATUS current
	DESCRIPTION
        "
        Previous 15-min SES counter inv.
        :This OID indicates that the previous
        15-min severely Errored Second
         counter is invalid
        "
	::= { pm1004dcpPerfLinePast15CntEntry 6 }


pm1004dcpPerfLinePast15CntSesValuePortn OBJECT-TYPE
	SYNTAX  Unsigned32
	MAX-ACCESS read-only
	STATUS current
	DESCRIPTION
        "
        Previous 15-min SES counter :This
        OID gives the previous 15-min severely
        Errored Second counter value
        "
	::= { pm1004dcpPerfLinePast15CntEntry 7 }


pm1004dcpPerfLinePast15CntInvSefsPortn OBJECT-TYPE
	SYNTAX  EkiOnOff
	MAX-ACCESS read-only
	STATUS current
	DESCRIPTION
        "
        Previous 15-min SEFS counter inv.
        :This OID indicates that the previous
        15-min severely Errored Framing
        Second counter is invalid
        "
	::= { pm1004dcpPerfLinePast15CntEntry 8 }


pm1004dcpPerfLinePast15CntSefsValuePortn OBJECT-TYPE
	SYNTAX  Unsigned32
	MAX-ACCESS read-only
	STATUS current
	DESCRIPTION
        "
        Previous 15-min SEFS counter :This
        OID gives the previous 15-min severely
        Errored Framing Second counter
         value
        "
	::= { pm1004dcpPerfLinePast15CntEntry 9 }


pm1004dcpPerfLinePast15CntInvUasPortn OBJECT-TYPE
	SYNTAX  EkiOnOff
	MAX-ACCESS read-only
	STATUS current
	DESCRIPTION
        "
        Previous 15-min UAS counter inv.
        :This OID indicates that the previous
        15-min UnAvailable Second counter
        is invalid
        "
	::= { pm1004dcpPerfLinePast15CntEntry 10 }


pm1004dcpPerfLinePast15CntUasValuePortn OBJECT-TYPE
	SYNTAX  Unsigned32
	MAX-ACCESS read-only
	STATUS current
	DESCRIPTION
        "
        Previous 15-min UAS counter :This
        OID gives the previous 15-min UnAvailable
        Second counter value
        "
	::= { pm1004dcpPerfLinePast15CntEntry 11 }


--- *********************************************************
---     TABLE for the pm1004dcpPerfLineCurrent24Cnt articles
--- *********************************************************

pm1004dcpPerfLineCurrent24CntTable OBJECT-TYPE
	SYNTAX  SEQUENCE OF Pm1004dcpPerfLineCurrent24CntEntry
	MAX-ACCESS not-accessible
	STATUS current
	DESCRIPTION
        "
        List of pm1004dcpPerfLineCurrent24Cnt
        Article
        "
	::= { pm1004dcpMonLinePerformance 130 }


pm1004dcpPerfLineCurrent24CntEntry OBJECT-TYPE
	SYNTAX Pm1004dcpPerfLineCurrent24CntEntry
	MAX-ACCESS not-accessible
	STATUS current
	DESCRIPTION
        "
        Row definition for the pm1004dcpPerfLineCurrent24Cnt
        table
        "
	INDEX   { pm1004dcpPerfLineCurrent24CntIndex }
	::= { pm1004dcpPerfLineCurrent24CntTable 1 }


Pm1004dcpPerfLineCurrent24CntEntry ::=
	SEQUENCE {
	pm1004dcpPerfLineCurrent24CntIndex
		INTEGER,
	pm1004dcpPerfLineCurrent24CntInvCvPortn
		EkiOnOff,
	pm1004dcpPerfLineCurrent24CntCvValuePortn
		Unsigned32,
	pm1004dcpPerfLineCurrent24CntInvEsPortn
		EkiOnOff,
	pm1004dcpPerfLineCurrent24CntEsValuePortn
		Unsigned32,
	pm1004dcpPerfLineCurrent24CntInvSesPortn
		EkiOnOff,
	pm1004dcpPerfLineCurrent24CntSesValuePortn
		Unsigned32,
	pm1004dcpPerfLineCurrent24CntInvSefsPortn
		EkiOnOff,
	pm1004dcpPerfLineCurrent24CntSefsValuePortn
		Unsigned32,
	pm1004dcpPerfLineCurrent24CntInvUasPortn
		EkiOnOff,
	pm1004dcpPerfLineCurrent24CntUasValuePortn
		Unsigned32
	}


pm1004dcpPerfLineCurrent24CntIndex OBJECT-TYPE
	SYNTAX  INTEGER(0..128)
	MAX-ACCESS  read-only
	STATUS current
	DESCRIPTION
        "
        Index definition for the pm1004dcpPerfLineCurrent24Cnt
        table
        "
	::= { pm1004dcpPerfLineCurrent24CntEntry 1 }


pm1004dcpPerfLineCurrent24CntInvCvPortn OBJECT-TYPE
	SYNTAX  EkiOnOff
	MAX-ACCESS read-only
	STATUS current
	DESCRIPTION
        "
        Current 24-hours CV counter inv.
        :This OID indicates that the current
        24-hours Coding Violation counter
        is invalid
        "
	::= { pm1004dcpPerfLineCurrent24CntEntry 2 }


pm1004dcpPerfLineCurrent24CntCvValuePortn OBJECT-TYPE
	SYNTAX  Unsigned32
	MAX-ACCESS read-only
	STATUS current
	DESCRIPTION
        "
        Current 24-hours CV counter :This
        OID gives the current 24-hours
         Coding Violation counter value
        "
	::= { pm1004dcpPerfLineCurrent24CntEntry 3 }


pm1004dcpPerfLineCurrent24CntInvEsPortn OBJECT-TYPE
	SYNTAX  EkiOnOff
	MAX-ACCESS read-only
	STATUS current
	DESCRIPTION
        "
        Current 24-hours ES counter inv.
        :This OID indicates that the current
        24-hours Errored Second counter
        is invalid
        "
	::= { pm1004dcpPerfLineCurrent24CntEntry 4 }


pm1004dcpPerfLineCurrent24CntEsValuePortn OBJECT-TYPE
	SYNTAX  Unsigned32
	MAX-ACCESS read-only
	STATUS current
	DESCRIPTION
        "
        Current 24-hours ES counter :This
        OID gives the current 24-hours
         Errored Second counter value
        "
	::= { pm1004dcpPerfLineCurrent24CntEntry 5 }


pm1004dcpPerfLineCurrent24CntInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pm1004dcpPerfLineCurrent24CntEntry 6 }


pm1004dcpPerfLineCurrent24CntSesValuePortn OBJECT-TYPE
	SYNTAX  Unsigned32
	MAX-ACCESS read-only
	STATUS current
	DESCRIPTION
        "
        Current 24-hours SES counter :This
        OID gives the current 24-hours
         severely Errored Second counter
        value
        "
	::= { pm1004dcpPerfLineCurrent24CntEntry 7 }


pm1004dcpPerfLineCurrent24CntInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pm1004dcpPerfLineCurrent24CntEntry 8 }


pm1004dcpPerfLineCurrent24CntSefsValuePortn OBJECT-TYPE
	SYNTAX  Unsigned32
	MAX-ACCESS read-only
	STATUS current
	DESCRIPTION
        "
        Current 24-hours SEFS counter
         :This OID gives the current 24-hours
        severely Errored Framing Second
        counter value
        "
	::= { pm1004dcpPerfLineCurrent24CntEntry 9 }


pm1004dcpPerfLineCurrent24CntInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pm1004dcpPerfLineCurrent24CntEntry 10 }


pm1004dcpPerfLineCurrent24CntUasValuePortn OBJECT-TYPE
	SYNTAX  Unsigned32
	MAX-ACCESS read-only
	STATUS current
	DESCRIPTION
        "
        Current 24-hours UAS counter :This
        OID gives the current 24-hours
         UnAvailable Second counter value
        "
	::= { pm1004dcpPerfLineCurrent24CntEntry 11 }


--- *********************************************************
---     TABLE for the pm1004dcpPerfLinePast24Cnt articles
--- *********************************************************

pm1004dcpPerfLinePast24CntTable OBJECT-TYPE
	SYNTAX  SEQUENCE OF Pm1004dcpPerfLinePast24CntEntry
	MAX-ACCESS not-accessible
	STATUS current
	DESCRIPTION
        "
        List of pm1004dcpPerfLinePast24Cnt
        Article
        "
	::= { pm1004dcpMonLinePerformance 131 }


pm1004dcpPerfLinePast24CntEntry OBJECT-TYPE
	SYNTAX Pm1004dcpPerfLinePast24CntEntry
	MAX-ACCESS not-accessible
	STATUS current
	DESCRIPTION
        "
        Row definition for the pm1004dcpPerfLinePast24Cnt
        table
        "
	INDEX   { pm1004dcpPerfLinePast24CntIndex }
	::= { pm1004dcpPerfLinePast24CntTable 1 }


Pm1004dcpPerfLinePast24CntEntry ::=
	SEQUENCE {
	pm1004dcpPerfLinePast24CntIndex
		INTEGER,
	pm1004dcpPerfLinePast24CntInvCvPortn
		EkiOnOff,
	pm1004dcpPerfLinePast24CntCvValuePortn
		Unsigned32,
	pm1004dcpPerfLinePast24CntInvEsPortn
		EkiOnOff,
	pm1004dcpPerfLinePast24CntEsValuePortn
		Unsigned32,
	pm1004dcpPerfLinePast24CntInvSesPortn
		EkiOnOff,
	pm1004dcpPerfLinePast24CntSesValuePortn
		Unsigned32,
	pm1004dcpPerfLinePast24CntInvSefsPortn
		EkiOnOff,
	pm1004dcpPerfLinePast24CntSefsValuePortn
		Unsigned32,
	pm1004dcpPerfLinePast24CntInvUasPortn
		EkiOnOff,
	pm1004dcpPerfLinePast24CntUasValuePortn
		Unsigned32
	}


pm1004dcpPerfLinePast24CntIndex OBJECT-TYPE
	SYNTAX  INTEGER(0..128)
	MAX-ACCESS  read-only
	STATUS current
	DESCRIPTION
        "
        Index definition for the pm1004dcpPerfLinePast24Cnt
        table
        "
	::= { pm1004dcpPerfLinePast24CntEntry 1 }


pm1004dcpPerfLinePast24CntInvCvPortn OBJECT-TYPE
	SYNTAX  EkiOnOff
	MAX-ACCESS read-only
	STATUS current
	DESCRIPTION
        "
        Previous 24-hours CV counter inv.
        :This OID indicates that the previous
        24-hours Coding Violation counter
        is invalid
        "
	::= { pm1004dcpPerfLinePast24CntEntry 2 }


pm1004dcpPerfLinePast24CntCvValuePortn OBJECT-TYPE
	SYNTAX  Unsigned32
	MAX-ACCESS read-only
	STATUS current
	DESCRIPTION
        "
        Previous 24-hours CV counter :This
        OID gives the previous 24-hours
        Coding Violation counter value
        "
	::= { pm1004dcpPerfLinePast24CntEntry 3 }


pm1004dcpPerfLinePast24CntInvEsPortn OBJECT-TYPE
	SYNTAX  EkiOnOff
	MAX-ACCESS read-only
	STATUS current
	DESCRIPTION
        "
        Previous 24-hours ES counter inv.
        :This OID indicates that the previous
        24-hours Errored Second counter
        is invalid
        "
	::= { pm1004dcpPerfLinePast24CntEntry 4 }


pm1004dcpPerfLinePast24CntEsValuePortn OBJECT-TYPE
	SYNTAX  Unsigned32
	MAX-ACCESS read-only
	STATUS current
	DESCRIPTION
        "
        Previous 24-hours ES counter :This
        OID gives the previous 24-hours
        Errored Second counter value
        "
	::= { pm1004dcpPerfLinePast24CntEntry 5 }


pm1004dcpPerfLinePast24CntInvSesPortn OBJECT-TYPE
	SYNTAX  EkiOnOff
	MAX-ACCESS read-only
	STATUS current
	DESCRIPTION
        "
        Previous 24-hours SES counter
         inv. :This OID indicates that
         the previous 24-hours severely
        Errored Second counter is invalid
        "
	::= { pm1004dcpPerfLinePast24CntEntry 6 }


pm1004dcpPerfLinePast24CntSesValuePortn OBJECT-TYPE
	SYNTAX  Unsigned32
	MAX-ACCESS read-only
	STATUS current
	DESCRIPTION
        "
        Previous 24-hours SES counter
         :This OID gives the previous 24-hours
        severely Errored Second counter
        value
        "
	::= { pm1004dcpPerfLinePast24CntEntry 7 }


pm1004dcpPerfLinePast24CntInvSefsPortn OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm1004dcpPerfLinePast24CntEntry 8 }


pm1004dcpPerfLinePast24CntSefsValuePortn OBJECT-TYPE
	SYNTAX  Unsigned32
	MAX-ACCESS read-only
	STATUS current
	DESCRIPTION
        "
        Previous 24-hours SEFS counter
        :This OID gives the previous 24-hours
        severely Errored Framing Second
        counter value
        "
	::= { pm1004dcpPerfLinePast24CntEntry 9 }


pm1004dcpPerfLinePast24CntInvUasPortn OBJECT-TYPE
	SYNTAX  EkiOnOff
	MAX-ACCESS read-only
	STATUS current
	DESCRIPTION
        "
        Previous 24-hours UAS counter
         inv. :This OID indicates that
         the previous 24-hours UnAvailable
        Second counter is invalid
        "
	::= { pm1004dcpPerfLinePast24CntEntry 10 }


pm1004dcpPerfLinePast24CntUasValuePortn OBJECT-TYPE
	SYNTAX  Unsigned32
	MAX-ACCESS read-only
	STATUS current
	DESCRIPTION
        "
        Previous 24-hours UAS counter
         :This OID gives the previous 24-hours
        UnAvailable Second counter value
        "
	::= { pm1004dcpPerfLinePast24CntEntry 11 }



pm1004dcpPerfEnable OBJECT-TYPE
	SYNTAX EkiOnOff
	MAX-ACCESS read-write
	STATUS current
	DESCRIPTION
        "
        Perf. Mon. Enable :This OID enables
        the Performance Monitoring application
        "
	::= { pm1004dcpMonSync 257 }


pm1004dcpPerfSyncSource OBJECT-TYPE
	SYNTAX EkiSynchroMode
	MAX-ACCESS read-write
	STATUS current
	DESCRIPTION
        "
        Perf. Mon. Sync. Source :This
         OID selects the Synchronisation
        source for the Performance Monitoring
        application (internal of external)
        "
	::= { pm1004dcpMonSync 258 }


pm1004dcpPerf15minSync OBJECT-TYPE
	SYNTAX EkiOnOff
	MAX-ACCESS read-write
	STATUS current
	DESCRIPTION
        "
        Perf. Mon. 15-min sync. :This
         OID must be used in external synchronisation
        mode only to send a 15-min synchronisation
        command
        "
	::= { pm1004dcpMonSync 259 }


pm1004dcpPerf24hSync OBJECT-TYPE
	SYNTAX EkiOnOff
	MAX-ACCESS read-write
	STATUS current
	DESCRIPTION
        "
        Perf. Mon. 24-hours sync. :This
        OID must be used in external synchronisation
        mode only to send a 24-hours synchronisation
        command
        "
	::= { pm1004dcpMonSync 260 }


pm1004dcpPerfCurrent15MinElapsedTime OBJECT-TYPE
	SYNTAX Counter32
	MAX-ACCESS read-write
	STATUS current
	DESCRIPTION
        "
        Current 15min period Elapsed Time
         :This OID gives the number of
         seconds elapsed in the current
        15-minutes period
        "
	::= { pm1004dcpMonTimeStamp 5 }


pm1004dcpPerfCurrent24HoursElapsedTime OBJECT-TYPE
	SYNTAX Counter32
	MAX-ACCESS read-write
	STATUS current
	DESCRIPTION
        "
        Current 24hours period Elapsed
        Time :This OID gives the number
        of seconds elapsed in the current
        24-hours period
        "
	::= { pm1004dcpMonTimeStamp 6 }


pm1004dcpPerfPast15MinElapsedTime OBJECT-TYPE
	SYNTAX Counter32
	MAX-ACCESS read-write
	STATUS current
	DESCRIPTION
        "
        Past 15min period Elapsed Time
         :This OID gives the number of
         seconds elapsed in the past 15-minutes
        period
        "
	::= { pm1004dcpMonTimeStamp 7 }


pm1004dcpPerfPast24HoursElapsedTime OBJECT-TYPE
	SYNTAX Counter32
	MAX-ACCESS read-write
	STATUS current
	DESCRIPTION
        "
        Past 24hours period Elapsed Time
        :This OID gives the number of seconds
        elapsed in the past 24-hours period
        "
	::= { pm1004dcpMonTimeStamp 8 }






--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pm1004dcpDwlrestartProcess OBJECT IDENTIFIER ::= { pm1004dcpDwlOther 0 }




pm1004dcpDwlColdRestartProcessed OBJECT-TYPE
	  SYNTAX EkiOnOff
	  MAX-ACCESS read-only
	  STATUS current
	  DESCRIPTION
        "
        Cold Restart :This OID indicates
        that the module last restart was
        a Cold RESTART
        "
	  ::= { pm1004dcpDwlrestartProcess 2 }



pm1004dcpDwlWarmRestartProcessed OBJECT-TYPE
	  SYNTAX EkiOnOff
	  MAX-ACCESS read-only
	  STATUS current
	  DESCRIPTION
        "
        Warm Restart :This OID indicates
        that the module last restart was
        a Warm RESTART
        "
	  ::= { pm1004dcpDwlrestartProcess 1 }



--- *****************************************************
---     LEAF for the swBanksUsed article
--- *****************************************************
pm1004dcpDwlswBanksUsed OBJECT IDENTIFIER ::= { pm1004dcpDwlOther 1 }




pm1004dcpDwlSwBank2Notempty OBJECT-TYPE
	  SYNTAX EkiOnOff
	  MAX-ACCESS read-only
	  STATUS current
	  DESCRIPTION
        "
        SW bank 2 loaded  :This OID indicates
        a software is loaded in SW bank
        2  <Help>  This status indicates
        if the SW bank 2 contains SW package
        "
	  ::= { pm1004dcpDwlswBanksUsed 6 }



pm1004dcpDwlSwBank1Notempty OBJECT-TYPE
	  SYNTAX EkiOnOff
	  MAX-ACCESS read-only
	  STATUS current
	  DESCRIPTION
        "
        SW bank 1 loaded  :This OID indicates
        a software is loaded in SW bank
        1  <Help>  This status indicates
        if the SW bank 1 contains SW package
        "
	  ::= { pm1004dcpDwlswBanksUsed 5 }



pm1004dcpDwlSwBank2Used OBJECT-TYPE
	  SYNTAX EkiOnOff
	  MAX-ACCESS read-only
	  STATUS current
	  DESCRIPTION
        "
        SW bank 2 active  :This OID indicates
        the module is working on SW bank
        2  <Help>  This status indicates
        if the SW bank 2 is active or standby
        "
	  ::= { pm1004dcpDwlswBanksUsed 2 }



pm1004dcpDwlSwBank1Used OBJECT-TYPE
	  SYNTAX EkiOnOff
	  MAX-ACCESS read-only
	  STATUS current
	  DESCRIPTION
        "
        SW bank 1 active  :This OID indicates
        the module is working on SW bank
        1  <Help>  This status indicates
        if the SW bank 1 is active or standby
        "
	  ::= { pm1004dcpDwlswBanksUsed 1 }



--- *****************************************************
---     LEAF for the gwBanksUsed article
--- *****************************************************
pm1004dcpDwlgwBanksUsed OBJECT IDENTIFIER ::= { pm1004dcpDwlOther 2 }




pm1004dcpDwlGwBank4Notempty OBJECT-TYPE
	  SYNTAX EkiOnOff
	  MAX-ACCESS read-only
	  STATUS current
	  DESCRIPTION
        "
        GW bank 4 loaded  :This OID indicates
        a gateware is loaded in GW bank
        4
        "
	  ::= { pm1004dcpDwlgwBanksUsed 8 }



pm1004dcpDwlGwBank3Notempty OBJECT-TYPE
	  SYNTAX EkiOnOff
	  MAX-ACCESS read-only
	  STATUS current
	  DESCRIPTION
        "
        GW bank 3 loaded  :This OID indicates
        a gateware is loaded in GW bank
        3  <Help>  This status indicates
        if the GW bank 3 contains GW package
        "
	  ::= { pm1004dcpDwlgwBanksUsed 7 }



pm1004dcpDwlGwBank2Notempty OBJECT-TYPE
	  SYNTAX EkiOnOff
	  MAX-ACCESS read-only
	  STATUS current
	  DESCRIPTION
        "
        GW bank 2 loaded  :This OID indicates
        a gateware is loaded in GW bank
        2
        "
	  ::= { pm1004dcpDwlgwBanksUsed 6 }



pm1004dcpDwlGwBank1Notempty OBJECT-TYPE
	  SYNTAX EkiOnOff
	  MAX-ACCESS read-only
	  STATUS current
	  DESCRIPTION
        "
        GW bank 1 loaded  :This OID indicates
        a gateware is loaded in GW bank
        1  <Help>  This status indicates
        if the GW bank 1 contains GW package
        "
	  ::= { pm1004dcpDwlgwBanksUsed 5 }



pm1004dcpDwlGwBank4Used OBJECT-TYPE
	  SYNTAX EkiOnOff
	  MAX-ACCESS read-only
	  STATUS current
	  DESCRIPTION
        "
        GW bank 4 active  :This OID indicates
        the module is working on GW bank
        4
        "
	  ::= { pm1004dcpDwlgwBanksUsed 4 }



pm1004dcpDwlGwBank3Used OBJECT-TYPE
	  SYNTAX EkiOnOff
	  MAX-ACCESS read-only
	  STATUS current
	  DESCRIPTION
        "
        GW bank 3 active  :This OID indicates
        the module is working on GW bank
        3  <Help>  This status indicates
        if the GW bank 3 is active or standby
        "
	  ::= { pm1004dcpDwlgwBanksUsed 3 }



pm1004dcpDwlGwBank2Used OBJECT-TYPE
	  SYNTAX EkiOnOff
	  MAX-ACCESS read-only
	  STATUS current
	  DESCRIPTION
        "
        GW bank 2 active  :This OID indicates
        the module is working on GW bank
        2
        "
	  ::= { pm1004dcpDwlgwBanksUsed 2 }



pm1004dcpDwlGwBank1Used OBJECT-TYPE
	  SYNTAX EkiOnOff
	  MAX-ACCESS read-only
	  STATUS current
	  DESCRIPTION
        "
        GW bank 1 active  :This OID indicates
        the module is working on GW bank
        1  <Help>  This status indicates
        if the GW bank 1 is active or standby
        "
	  ::= { pm1004dcpDwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pm1004dcpCfgAccessCAisCsf OBJECT IDENTIFIER ::= { pm1004dcpConfig 1 }



--- *****************************************************
---     LEAF for the table 0012
--- *****************************************************

pm1004dcpCfgClientcaiscsfTable OBJECT-TYPE
	SYNTAX  SEQUENCE OF Pm1004dcpCfgClientcaiscsfEntry
	MAX-ACCESS not-accessible
	STATUS current
	DESCRIPTION
        "
        List of  Article
        "
	::= { pm1004dcpCfgAccessCAisCsf 1 }


pm1004dcpCfgClientcaiscsfEntry OBJECT-TYPE
	SYNTAX Pm1004dcpCfgClientcaiscsfEntry
	MAX-ACCESS not-accessible
	STATUS current
	DESCRIPTION
        "
        Row definition for the accessCAisCsf
        table
        "
	INDEX   { pm1004dcpCfgClientcaiscsfIndex }
	::= { pm1004dcpCfgClientcaiscsfTable 1 }


Pm1004dcpCfgClientcaiscsfEntry ::=
	SEQUENCE {
	pm1004dcpCfgClientcaiscsfIndex
		INTEGER,
	pm1004dcpCfgCAisModePortn
		Unsigned32,
	pm1004dcpCfgUpAccessioAlmPortn
		Unsigned32,
	pm1004dcpCfgUpMapperDeAlmPortn
		Unsigned32,
	pm1004dcpCfgUpAccessioSdhAlmPortn
		Unsigned32,
	pm1004dcpCfgDownAccessioAlmPortn
		Unsigned32,
	pm1004dcpCfgDownMapperDeAlmPortn
		Unsigned32,
	pm1004dcpCfgDownDfrmAlmPortn
		Unsigned32,
	pm1004dcpCfgDownLineSyncAlarmsPortn
		Unsigned32,
	pm1004dcpCfgDownAccessioSdhAlmPortn
		Unsigned32
	}


pm1004dcpCfgClientcaiscsfIndex OBJECT-TYPE
	SYNTAX  INTEGER(0..128)
	MAX-ACCESS  read-only
	STATUS current
	DESCRIPTION
        "
        Index definition for the clientcaiscsf
        table
        "
	::= { pm1004dcpCfgClientcaiscsfEntry 1 }


pm1004dcpCfgCAisModePortn OBJECT-TYPE
	SYNTAX  Unsigned32 (0..65536)
	MAX-ACCESS read-write
	STATUS current
	DESCRIPTION
        "
        CAIS mode  on Client Port :This
        register enables/disables port
          laser shutdown on CAIS insertion
        condition
        "
	::= { pm1004dcpCfgClientcaiscsfEntry 3 }


pm1004dcpCfgUpAccessioAlmPortn OBJECT-TYPE
	SYNTAX  Unsigned32 (0..65536)
	MAX-ACCESS read-write
	STATUS current
	DESCRIPTION
        "
        CSF contributors on Client Port
        :This register configures the contributors
        to upstream CSF insertion on the
        port.
        "
	::= { pm1004dcpCfgClientcaiscsfEntry 9 }


pm1004dcpCfgUpMapperDeAlmPortn OBJECT-TYPE
	SYNTAX  Unsigned32 (0..65536)
	MAX-ACCESS read-write
	STATUS current
	DESCRIPTION
        "
        CSF contributors on Client Port
        :This register configures the contributors
        to upstream CSF insertion on the
        port.
        "
	::= { pm1004dcpCfgClientcaiscsfEntry 10 }


pm1004dcpCfgUpAccessioSdhAlmPortn OBJECT-TYPE
	SYNTAX  Unsigned32 (0..65536)
	MAX-ACCESS read-write
	STATUS current
	DESCRIPTION
        "
        CSF contributors on Client Port
        :This register selects the contributors
        of SDH register to upstream CAIS/CSF
        on Port
        "
	::= { pm1004dcpCfgClientcaiscsfEntry 11 }


pm1004dcpCfgDownAccessioAlmPortn OBJECT-TYPE
	SYNTAX  Unsigned32 (0..65536)
	MAX-ACCESS read-write
	STATUS current
	DESCRIPTION
        "
        CAIS contributors on Client Port
        :This register configures the contributors
        to downstream CAIS insertion on
         port.
        "
	::= { pm1004dcpCfgClientcaiscsfEntry 17 }


pm1004dcpCfgDownMapperDeAlmPortn OBJECT-TYPE
	SYNTAX  Unsigned32 (0..65536)
	MAX-ACCESS read-write
	STATUS current
	DESCRIPTION
        "
        CAIS contributors on Client Port
        :This register configures the contributors
        to downstream CAIS insertion on
         port.
        "
	::= { pm1004dcpCfgClientcaiscsfEntry 18 }


pm1004dcpCfgDownDfrmAlmPortn OBJECT-TYPE
	SYNTAX  Unsigned32 (0..65536)
	MAX-ACCESS read-write
	STATUS current
	DESCRIPTION
        "
        CAIS contributors on Client Port
        :This register configures the contributors
        to downstream CAIS insertion on
         port.
        "
	::= { pm1004dcpCfgClientcaiscsfEntry 19 }


pm1004dcpCfgDownLineSyncAlarmsPortn OBJECT-TYPE
	SYNTAX  Unsigned32 (0..65536)
	MAX-ACCESS read-write
	STATUS deprecated
	DESCRIPTION
        "
        CAIS contributors on Client Port
        :This register configures the contributors
        to downstream CAIS insertion on
         port.
        "
	::= { pm1004dcpCfgClientcaiscsfEntry 20 }


pm1004dcpCfgDownAccessioSdhAlmPortn OBJECT-TYPE
	SYNTAX  Unsigned32 (0..65536)
	MAX-ACCESS read-write
	STATUS current
	DESCRIPTION
        "
        CAIS contributors on Client Port
        :This register selects the contributors
        of SDH register to downstream CAIS/CSF
        on Port
        "
	::= { pm1004dcpCfgClientcaiscsfEntry 21 }


--- *****************************************************
---     LEAF for the table Group startup
--- *****************************************************

pm1004dcpCfgStartup OBJECT IDENTIFIER ::= { pm1004dcpConfig 2 }



--- *****************************************************
---     LEAF for the table 2111
--- *****************************************************

pm1004dcpCfgClientStartupTable OBJECT-TYPE
	SYNTAX  SEQUENCE OF Pm1004dcpCfgClientStartupEntry
	MAX-ACCESS not-accessible
	STATUS current
	DESCRIPTION
        "
        List of  Article
        "
	::= { pm1004dcpCfgStartup 1 }


pm1004dcpCfgClientStartupEntry OBJECT-TYPE
	SYNTAX Pm1004dcpCfgClientStartupEntry
	MAX-ACCESS not-accessible
	STATUS current
	DESCRIPTION
        "
        Row definition for the startup
        table
        "
	INDEX   { pm1004dcpCfgClientStartupIndex }
	::= { pm1004dcpCfgClientStartupTable 1 }


Pm1004dcpCfgClientStartupEntry ::=
	SEQUENCE {
	pm1004dcpCfgClientStartupIndex
		INTEGER,
	pm1004dcpCfgSystConfPortPortn
		Unsigned32,
	pm1004dcpCfgNetConfPortPortn
		Unsigned32,
	pm1004dcpCfgAdddropConfPortPortn
		Unsigned32
	}


pm1004dcpCfgClientStartupIndex OBJECT-TYPE
	SYNTAX  INTEGER(0..128)
	MAX-ACCESS  read-only
	STATUS current
	DESCRIPTION
        "
        Index definition for the clientStartup
        table
        "
	::= { pm1004dcpCfgClientStartupEntry 1 }


pm1004dcpCfgSystConfPortPortn OBJECT-TYPE
	SYNTAX  Unsigned32 (0..65536)
	MAX-ACCESS read-write
	STATUS current
	DESCRIPTION
        "
        Default Settings on Client Port
        :This  register configures the
         default initialisation settings
        on the port.
        "
	::= { pm1004dcpCfgClientStartupEntry 3 }


pm1004dcpCfgNetConfPortPortn OBJECT-TYPE
	SYNTAX  Unsigned32 (0..65536)
	MAX-ACCESS read-write
	STATUS current
	DESCRIPTION
        "
        Default Protocol on Client Port
        :This register configures the default
        initialisation protocol on the
         port.
        "
	::= { pm1004dcpCfgClientStartupEntry 4 }


pm1004dcpCfgAdddropConfPortPortn OBJECT-TYPE
	SYNTAX  Unsigned32 (0..65536)
	MAX-ACCESS read-write
	STATUS deprecated
	DESCRIPTION
        "
        Default Add&Drop mode on Client
        Port :This register configures
         the default Add&Drop mode on the
        port.
        "
	::= { pm1004dcpCfgClientStartupEntry 5 }


--- *****************************************************
---     LEAF for the table 2191
--- *****************************************************

pm1004dcptablelineStartup OBJECT IDENTIFIER ::= { pm1004dcpCfgStartup 2 }



pm1004dcpCfgsystConfLine1 OBJECT-TYPE
	  SYNTAX Unsigned32 (0..65536)
	  MAX-ACCESS read-write
	  STATUS current
	  DESCRIPTION
        "
        Default Settings on Line 1 :This
        register configures the default
        initialisation settings on Line
        port 1.
        "
	  ::= { pm1004dcptablelineStartup 2 }



pm1004dcpCfglineOptions1 OBJECT-TYPE
	  SYNTAX Unsigned32 (0..65536)
	  MAX-ACCESS read-write
	  STATUS current
	  DESCRIPTION
        "
        Default Options on Active Line
        Port :This register configures
         the default options on the active
        line port
        "
	  ::= { pm1004dcptablelineStartup 5 }



pm1004dcpCfgsystConfLine2 OBJECT-TYPE
	  SYNTAX Unsigned32 (0..65536)
	  MAX-ACCESS read-write
	  STATUS current
	  DESCRIPTION
        "
        Default Settings on Line 2 :This
        register configures the default
        initialisation settings on Line
        port 2.
        "
	  ::= { pm1004dcptablelineStartup 6 }



pm1004dcpCfglineSelection OBJECT-TYPE
	  SYNTAX Unsigned32 (0..65536)
	  MAX-ACCESS read-write
	  STATUS current
	  DESCRIPTION
        "
        Default Settings of active line
        :This  register configures the
         start up active line.
        "
	  ::= { pm1004dcptablelineStartup 7 }



pm1004dcpCfglineOptions2 OBJECT-TYPE
	  SYNTAX Unsigned32 (0..65536)
	  MAX-ACCESS read-write
	  STATUS deprecated
	  DESCRIPTION
        "
        Default Options on Active Line
        Port :This register configures
         the default options on the active
        line port
        "
	  ::= { pm1004dcptablelineStartup 9 }



--- *****************************************************
---     LEAF for the table 21AB
--- *****************************************************

pm1004dcpCfgXfpTable OBJECT-TYPE
	SYNTAX  SEQUENCE OF Pm1004dcpCfgXfpEntry
	MAX-ACCESS not-accessible
	STATUS current
	DESCRIPTION
        "
        List of  Article
        "
	::= { pm1004dcpCfgStartup 3 }


pm1004dcpCfgXfpEntry OBJECT-TYPE
	SYNTAX Pm1004dcpCfgXfpEntry
	MAX-ACCESS not-accessible
	STATUS current
	DESCRIPTION
        "
        Row definition for the startup
        table
        "
	INDEX   { pm1004dcpCfgXfpIndex }
	::= { pm1004dcpCfgXfpTable 1 }


Pm1004dcpCfgXfpEntry ::=
	SEQUENCE {
	pm1004dcpCfgXfpIndex
		INTEGER,
	pm1004dcpCfgSystConfXfpPortn
		Unsigned32,
	pm1004dcpCfgDataRateConfXfpPortn
		Unsigned32
	}


pm1004dcpCfgXfpIndex OBJECT-TYPE
	SYNTAX  INTEGER(0..128)
	MAX-ACCESS  read-only
	STATUS current
	DESCRIPTION
        "
        Index definition for the xfp table
        "
	::= { pm1004dcpCfgXfpEntry 1 }


pm1004dcpCfgSystConfXfpPortn OBJECT-TYPE
	SYNTAX  Unsigned32 (0..65536)
	MAX-ACCESS read-write
	STATUS current
	DESCRIPTION
        "
        Default settings on XFP Port :This
        register configures the default
        initialisation settings on XFP
         port.
        "
	::= { pm1004dcpCfgXfpEntry 3 }


pm1004dcpCfgDataRateConfXfpPortn OBJECT-TYPE
	SYNTAX  Unsigned32 (0..65536)
	MAX-ACCESS read-write
	STATUS deprecated
	DESCRIPTION
        "
        :Reserved
        "
	::= { pm1004dcpCfgXfpEntry 4 }


--- *****************************************************
---     LEAF for the table Group modPerfConfig
--- *****************************************************

pm1004dcpCfgModPerfConfig OBJECT IDENTIFIER ::= { pm1004dcpConfig 3 }



--- *****************************************************
---     LEAF for the table 5002
--- *****************************************************

pm1004dcptablemodPerfConfig OBJECT IDENTIFIER ::= { pm1004dcpCfgModPerfConfig 1 }



pm1004dcpCfgperfMode OBJECT-TYPE
	  SYNTAX Unsigned32 (0..65536)
	  MAX-ACCESS read-write
	  STATUS current
	  DESCRIPTION
        "
        SONET or SDH monitoring mode :This
        OID defines the line monitoring
        mode (SONET or SDH mode)
        "
	  ::= { pm1004dcptablemodPerfConfig 2 }



--- *****************************************************
---     LEAF for the table Group j0Client
--- *****************************************************

pm1004dcpCfgJ0Client OBJECT IDENTIFIER ::= { pm1004dcpConfig 4 }



--- *****************************************************
---     LEAF for the table 0013
--- *****************************************************

pm1004dcpCfgEmptyTable OBJECT-TYPE
	SYNTAX  SEQUENCE OF Pm1004dcpCfgEmptyEntry
	MAX-ACCESS not-accessible
	STATUS current
	DESCRIPTION
        "
        List of  Article
        "
	::= { pm1004dcpCfgJ0Client 1 }


pm1004dcpCfgEmptyEntry OBJECT-TYPE
	SYNTAX Pm1004dcpCfgEmptyEntry
	MAX-ACCESS not-accessible
	STATUS current
	DESCRIPTION
        "
        Row definition for the j0Client
        table
        "
	INDEX   { pm1004dcpCfgEmptyIndex }
	::= { pm1004dcpCfgEmptyTable 1 }


Pm1004dcpCfgEmptyEntry ::=
	SEQUENCE {
	pm1004dcpCfgEmptyIndex
		INTEGER,
	pm1004dcpCfgClientExpectJ0SetupPortn
		Unsigned32
	}


pm1004dcpCfgEmptyIndex OBJECT-TYPE
	SYNTAX  INTEGER(0..128)
	MAX-ACCESS  read-only
	STATUS current
	DESCRIPTION
        "
        Index definition for the empty
        table
        "
	::= { pm1004dcpCfgEmptyEntry 1 }


pm1004dcpCfgClientExpectJ0SetupPortn OBJECT-TYPE
	SYNTAX  Unsigned32 (0..65536)
	MAX-ACCESS read-write
	STATUS current
	DESCRIPTION
        "
        Expected Trace Identifier mode
        :This register configures the Expected
        Trace Identifier Mode (single byte,
        16 bytes with CRC7, 64 bytes with
        CRC7 or 64 bytes with CR/LF terminaison)
        "
	::= { pm1004dcpCfgEmptyEntry 3 }


--- *****************************************************
---     LEAF for the table Group labels
--- *****************************************************

pm1004dcpCfgLabels OBJECT IDENTIFIER ::= { pm1004dcpConfig 5 }



--- *****************************************************
---     LEAF for the table NO_VALUE
--- *****************************************************

pm1004dcpCfgLabelclientTable OBJECT-TYPE
	SYNTAX  SEQUENCE OF Pm1004dcpCfgLabelclientEntry
	MAX-ACCESS not-accessible
	STATUS current
	DESCRIPTION
        "
        List of  Article
        "
	::= { pm1004dcpCfgLabels 1 }


pm1004dcpCfgLabelclientEntry OBJECT-TYPE
	SYNTAX Pm1004dcpCfgLabelclientEntry
	MAX-ACCESS not-accessible
	STATUS current
	DESCRIPTION
        "
        Row definition for the labels
         table
        "
	INDEX   { pm1004dcpCfgLabelclientIndex }
	::= { pm1004dcpCfgLabelclientTable 1 }


Pm1004dcpCfgLabelclientEntry ::=
	SEQUENCE {
	pm1004dcpCfgLabelclientIndex
		INTEGER,
	pm1004dcpCfgLabelclientPortn
		DisplayString
	}


pm1004dcpCfgLabelclientIndex OBJECT-TYPE
	SYNTAX  INTEGER(0..128)
	MAX-ACCESS  read-only
	STATUS current
	DESCRIPTION
        "
        Index definition for the labelclient
        table
        "
	::= { pm1004dcpCfgLabelclientEntry 1 }


pm1004dcpCfgLabelclientPortn OBJECT-TYPE
	SYNTAX  DisplayString( SIZE(1..16))
	MAX-ACCESS read-write
	STATUS current
	DESCRIPTION
        "
        Default settings on the label
         of the Ports :These registers
         configures the default initialisation
        settings of the labels of the ports.
        "
	::= { pm1004dcpCfgLabelclientEntry 3 }


--- *****************************************************
---     LEAF for the table NO_VALUE
--- *****************************************************

pm1004dcpCfgLabellineTable OBJECT-TYPE
	SYNTAX  SEQUENCE OF Pm1004dcpCfgLabellineEntry
	MAX-ACCESS not-accessible
	STATUS current
	DESCRIPTION
        "
        List of  Article
        "
	::= { pm1004dcpCfgLabels 2 }


pm1004dcpCfgLabellineEntry OBJECT-TYPE
	SYNTAX Pm1004dcpCfgLabellineEntry
	MAX-ACCESS not-accessible
	STATUS current
	DESCRIPTION
        "
        Row definition for the labels
         table
        "
	INDEX   { pm1004dcpCfgLabellineIndex }
	::= { pm1004dcpCfgLabellineTable 1 }


Pm1004dcpCfgLabellineEntry ::=
	SEQUENCE {
	pm1004dcpCfgLabellineIndex
		INTEGER,
	pm1004dcpCfgLabellinePortn
		DisplayString
	}


pm1004dcpCfgLabellineIndex OBJECT-TYPE
	SYNTAX  INTEGER(0..128)
	MAX-ACCESS  read-only
	STATUS current
	DESCRIPTION
        "
        Index definition for the labelline
        table
        "
	::= { pm1004dcpCfgLabellineEntry 1 }


pm1004dcpCfgLabellinePortn OBJECT-TYPE
	SYNTAX  DisplayString( SIZE(1..16))
	MAX-ACCESS read-write
	STATUS current
	DESCRIPTION
        "
        Default settings on the label
         of the lines :These registers
         configures the default initialisation
        settings of the labels of the lines.
        "
	::= { pm1004dcpCfgLabellineEntry 3 }


--- *****************************************************
---     LEAF for the table Group startuptlh
--- *****************************************************

pm1004dcpCfgStartuptlh OBJECT IDENTIFIER ::= { pm1004dcpConfig 6 }



--- *****************************************************
---     LEAF for the table 25A8
--- *****************************************************

pm1004dcpCfgOtxtlhTable OBJECT-TYPE
	SYNTAX  SEQUENCE OF Pm1004dcpCfgOtxtlhEntry
	MAX-ACCESS not-accessible
	STATUS current
	DESCRIPTION
        "
        List of  Article
        "
	::= { pm1004dcpCfgStartuptlh 1 }


pm1004dcpCfgOtxtlhEntry OBJECT-TYPE
	SYNTAX Pm1004dcpCfgOtxtlhEntry
	MAX-ACCESS not-accessible
	STATUS current
	DESCRIPTION
        "
        Row definition for the startuptlh
        table
        "
	INDEX   { pm1004dcpCfgOtxtlhIndex }
	::= { pm1004dcpCfgOtxtlhTable 1 }


Pm1004dcpCfgOtxtlhEntry ::=
	SEQUENCE {
	pm1004dcpCfgOtxtlhIndex
		INTEGER,
	pm1004dcpCfgNuPortn
		Unsigned32,
	pm1004dcpCfgLineDitherRatePortn
		Unsigned32,
	pm1004dcpCfgLineDitherFhzPortn
		Unsigned32,
	pm1004dcpCfgLinePwrLaserPortn
		Unsigned32,
	pm1004dcpCfgLineFCurrentPortn
		Unsigned32,
	pm1004dcpCfgLineGridCurrentPortn
		Unsigned32,
	pm1004dcpCfgFPortn
		Unsigned32,
	pm1004dcpCfgReservedPortn
		Unsigned32,
	pm1004dcpCfgLinePhotodiodeModePortn
		Unsigned32,
	pm1004dcpCfgLinePhotodiodeValuePortn
		Unsigned32
	}


pm1004dcpCfgOtxtlhIndex OBJECT-TYPE
	SYNTAX  INTEGER(0..128)
	MAX-ACCESS  read-only
	STATUS current
	DESCRIPTION
        "
        Index definition for the otxtlh
        table
        "
	::= { pm1004dcpCfgOtxtlhEntry 1 }


pm1004dcpCfgNuPortn OBJECT-TYPE
	SYNTAX  Unsigned32 (0..65536)
	MAX-ACCESS read-write
	STATUS deprecated
	DESCRIPTION
        "
        :
        "
	::= { pm1004dcpCfgOtxtlhEntry 3 }


pm1004dcpCfgLineDitherRatePortn OBJECT-TYPE
	SYNTAX  Unsigned32 (0..65536)
	MAX-ACCESS read-write
	STATUS current
	DESCRIPTION
        "
        Default Line OTX TLH FM amplitude
        :This register configures the start-up
        width of the frequency modulation
        of the Line OTX TLH
        "
	::= { pm1004dcpCfgOtxtlhEntry 4 }


pm1004dcpCfgLineDitherFhzPortn OBJECT-TYPE
	SYNTAX  Unsigned32 (0..65536)
	MAX-ACCESS read-write
	STATUS current
	DESCRIPTION
        "
        Default Line OTX TLH FM frequency
        :This register configures the start-up
        frequency of the frequency modulation
        of the Line OTX TLH
        "
	::= { pm1004dcpCfgOtxtlhEntry 5 }


pm1004dcpCfgLinePwrLaserPortn OBJECT-TYPE
	SYNTAX  Unsigned32 (0..65536)
	MAX-ACCESS read-write
	STATUS current
	DESCRIPTION
        "
        Defaut Line OTX TLH output Power
        :This register configures the start-up
        output power of the Line OTX TLH
         (Unit = dBm)
        "
	::= { pm1004dcpCfgOtxtlhEntry 6 }


pm1004dcpCfgLineFCurrentPortn OBJECT-TYPE
	SYNTAX  Unsigned32 (0..65536)
	MAX-ACCESS read-write
	STATUS current
	DESCRIPTION
        "
        Default Line OTX TLH Channel :This
        register configures the start-up
        laser channel of the Line OTX TLH
        "
	::= { pm1004dcpCfgOtxtlhEntry 7 }


pm1004dcpCfgLineGridCurrentPortn OBJECT-TYPE
	SYNTAX  Unsigned32 (0..65536)
	MAX-ACCESS read-write
	STATUS current
	DESCRIPTION
        "
        Default Line OTX TLH Grid :This
        register configures the start-up
        laser grid of the Line OTX TLH
        "
	::= { pm1004dcpCfgOtxtlhEntry 8 }


pm1004dcpCfgFPortn OBJECT-TYPE
	SYNTAX  Unsigned32 (0..65536)
	MAX-ACCESS read-write
	STATUS current
	DESCRIPTION
        "
        Default Line OTX TLH lowest Freq
        :This register configures the start-up
        lowest frequency supported on the
        Line OTX TLH
        "
	::= { pm1004dcpCfgOtxtlhEntry 9 }


pm1004dcpCfgReservedPortn OBJECT-TYPE
	SYNTAX  Unsigned32 (0..65536)
	MAX-ACCESS read-write
	STATUS deprecated
	DESCRIPTION
        "
        :
        "
	::= { pm1004dcpCfgOtxtlhEntry 10 }


pm1004dcpCfgLinePhotodiodeModePortn OBJECT-TYPE
	SYNTAX  Unsigned32 (0..65536)
	MAX-ACCESS read-write
	STATUS current
	DESCRIPTION
        "
        Default Line OTX TLH APD mode
         :This register configures the
         start-up APD mode of the Line
         OTX TLH
        "
	::= { pm1004dcpCfgOtxtlhEntry 11 }


pm1004dcpCfgLinePhotodiodeValuePortn OBJECT-TYPE
	SYNTAX  Unsigned32 (0..65536)
	MAX-ACCESS read-write
	STATUS current
	DESCRIPTION
        "
        Default Line OTX TLH APD atten.
        :This register configures the start-up
        APD attenuation on the Line OTX
        TLH
        "
	::= { pm1004dcpCfgOtxtlhEntry 12 }


--- *****************************************************
---     LEAF for the table Group other
--- *****************************************************

pm1004dcpCfgOther OBJECT IDENTIFIER ::= { pm1004dcpConfig 7 }



--- *****************************************************
---     LEAF for the table 2300
--- *****************************************************

pm1004dcptablemoduleOther OBJECT IDENTIFIER ::= { pm1004dcpCfgOther 1 }



pm1004dcpCfgmode OBJECT-TYPE
	  SYNTAX Unsigned32 (0..65536)
	  MAX-ACCESS read-write
	  STATUS current
	  DESCRIPTION
        "
        Default settings on Module :This
        register selects the DCC  configuration
        of the PM
        "
	  ::= { pm1004dcptablemoduleOther 2 }



pm1004dcpCfgadddropTsPairMode1 OBJECT-TYPE
	  SYNTAX Unsigned32 (0..65536)
	  MAX-ACCESS read-write
	  STATUS current
	  DESCRIPTION
        "
        Default settings on TS Group Mode
        :This register selects selects
         the mode on the group of clients
        "
	  ::= { pm1004dcptablemoduleOther 3 }



pm1004dcpCfgadddropTsPairMode2 OBJECT-TYPE
	  SYNTAX Unsigned32 (0..65536)
	  MAX-ACCESS read-write
	  STATUS current
	  DESCRIPTION
        "
        Default settings on TS Group Mode
        :This register selects selects
         the mode on the group of clients
        "
	  ::= { pm1004dcptablemoduleOther 4 }



pm1004dcpCfgadddropTsPairMode3 OBJECT-TYPE
	  SYNTAX Unsigned32 (0..65536)
	  MAX-ACCESS read-write
	  STATUS current
	  DESCRIPTION
        "
        Default settings on TS Group Mode
        :This register selects selects
         the mode on the group of clients
        "
	  ::= { pm1004dcptablemoduleOther 5 }



pm1004dcpCfgadddropTsPairMode4 OBJECT-TYPE
	  SYNTAX Unsigned32 (0..65536)
	  MAX-ACCESS read-write
	  STATUS current
	  DESCRIPTION
        "
        Default settings on TS Group Mode
        :This register selects selects
         the mode on the group of clients
        "
	  ::= { pm1004dcptablemoduleOther 6 }



--- *****************************************************
---     LEAF for the table Group startuptablefive
--- *****************************************************

pm1004dcpCfgStartuptablefive OBJECT IDENTIFIER ::= { pm1004dcpConfig 8 }



--- *****************************************************
---     LEAF for the table 0005
--- *****************************************************

pm1004dcpCfgOtxtlhcapabilitiesTable OBJECT-TYPE
	SYNTAX  SEQUENCE OF Pm1004dcpCfgOtxtlhcapabilitiesEntry
	MAX-ACCESS not-accessible
	STATUS current
	DESCRIPTION
        "
        List of  Article
        "
	::= { pm1004dcpCfgStartuptablefive 1 }


pm1004dcpCfgOtxtlhcapabilitiesEntry OBJECT-TYPE
	SYNTAX Pm1004dcpCfgOtxtlhcapabilitiesEntry
	MAX-ACCESS not-accessible
	STATUS current
	DESCRIPTION
        "
        Row definition for the startuptablefive
        table
        "
	INDEX   { pm1004dcpCfgOtxtlhcapabilitiesIndex }
	::= { pm1004dcpCfgOtxtlhcapabilitiesTable 1 }


Pm1004dcpCfgOtxtlhcapabilitiesEntry ::=
	SEQUENCE {
	pm1004dcpCfgOtxtlhcapabilitiesIndex
		INTEGER,
	pm1004dcpCfgComponentTypePortn
		Unsigned32,
	pm1004dcpCfgMiscellaneousPortn
		Unsigned32,
	pm1004dcpCfgFirstChannelPortn
		Unsigned32,
	pm1004dcpCfgLastChannelPortn
		Unsigned32,
	pm1004dcpCfgGridPortn
		Unsigned32
	}


pm1004dcpCfgOtxtlhcapabilitiesIndex OBJECT-TYPE
	SYNTAX  INTEGER(0..128)
	MAX-ACCESS  read-only
	STATUS current
	DESCRIPTION
        "
        Index definition for the otxtlhcapabilities
        table
        "
	::= { pm1004dcpCfgOtxtlhcapabilitiesEntry 1 }


pm1004dcpCfgComponentTypePortn OBJECT-TYPE
	SYNTAX  Unsigned32 (0..65536)
	MAX-ACCESS read-write
	STATUS current
	DESCRIPTION
        "
        Component parameters :This OID
        defines the component parameters
        "
	::= { pm1004dcpCfgOtxtlhcapabilitiesEntry 3 }


pm1004dcpCfgMiscellaneousPortn OBJECT-TYPE
	SYNTAX  Unsigned32 (0..65536)
	MAX-ACCESS read-write
	STATUS current
	DESCRIPTION
        "
        Miscellaneous default settings
        :This OID defines the miscellaneous
        parameters
        "
	::= { pm1004dcpCfgOtxtlhcapabilitiesEntry 4 }


pm1004dcpCfgFirstChannelPortn OBJECT-TYPE
	SYNTAX  Unsigned32 (0..65536)
	MAX-ACCESS read-write
	STATUS current
	DESCRIPTION
        "
        Number of the first channel of
        the component :This OID defines
        the first channel number of the
        PM
        "
	::= { pm1004dcpCfgOtxtlhcapabilitiesEntry 5 }


pm1004dcpCfgLastChannelPortn OBJECT-TYPE
	SYNTAX  Unsigned32 (0..65536)
	MAX-ACCESS read-write
	STATUS current
	DESCRIPTION
        "
        Number of the last channel of
         the component :This OID defines
        the last channel number of the
         PM
        "
	::= { pm1004dcpCfgOtxtlhcapabilitiesEntry 6 }


pm1004dcpCfgGridPortn OBJECT-TYPE
	SYNTAX  Unsigned32 (0..65536)
	MAX-ACCESS read-write
	STATUS current
	DESCRIPTION
        "
        Grid value of the component :This
        OID defines the grid of the PM
        "
	::= { pm1004dcpCfgOtxtlhcapabilitiesEntry 7 }



pm1004dcpCfgWriteConfiguration  OBJECT-TYPE
	SYNTAX EkiOnOff
	MAX-ACCESS read-write
	STATUS current
	DESCRIPTION
	"Write configuration to module:This OID
	 writes the complete configuration to the module"
	::= { pm1004dcpConfig 257 }






--- *****************************************************
---     TRAP OBJECTS
--- *****************************************************

pm1004dcptrapPortNumber OBJECT-TYPE
	SYNTAX INTEGER(1..64)
	MAX-ACCESS read-only
	STATUS current
	DESCRIPTION
	"Last port which generates a trap"
	::= { pm1004dcptraps 2 }

pm1004dcptrapLineNumber OBJECT-TYPE
	SYNTAX INTEGER(1..64)
	MAX-ACCESS read-only
	STATUS current
	DESCRIPTION
	"Last Line which generates a trap"
	::= { pm1004dcptraps 3 }

pm1004dcptrapBoardNumber OBJECT-TYPE
	SYNTAX INTEGER(1..64)
	MAX-ACCESS read-only
	STATUS current
	DESCRIPTION
	"Last module which generates a trap"
	::= { pm1004dcptraps 4 }







--- *****************************************************
---     LINE TRAPS
--- *****************************************************

pm1004dcpLineTrapNotUrgentGoesOn NOTIFICATION-TYPE
	OBJECTS {pm1004dcpAlmLineDdmWarningPortn, pm1004dcptrapLineNumber, pm1004dcptrapBoardNumber}
	STATUS current
	DESCRIPTION "Not urgent Line default is activated"
	::= { pm1004dcptraps 30 }

pm1004dcpLineTrapNotUrgentGoesOff NOTIFICATION-TYPE
	OBJECTS {pm1004dcpAlmLineDdmWarningPortn, pm1004dcptrapLineNumber, pm1004dcptrapBoardNumber}
	STATUS current
	DESCRIPTION "Not urgent Line default disappeared"
	::= { pm1004dcptraps 31 }

pm1004dcpLineTrapUrgentGoesOn NOTIFICATION-TYPE
	OBJECTS {pm1004dcpAlmLineDdmAlmPortn, pm1004dcptrapLineNumber, pm1004dcptrapBoardNumber}
	STATUS current
	DESCRIPTION "Urgent Line default is activated"
	::= { pm1004dcptraps 32 }

pm1004dcpLineTrapUrgentGoesOff NOTIFICATION-TYPE
	OBJECTS {pm1004dcpAlmLineDdmAlmPortn, pm1004dcptrapLineNumber, pm1004dcptrapBoardNumber}
	STATUS current
	DESCRIPTION "Urgent Line default disappeared"
	::= { pm1004dcptraps 33 }

pm1004dcpLineTrapCritGoesOn NOTIFICATION-TYPE
	OBJECTS {pm1004dcpAlmLineFailPortn , pm1004dcpAlmLineHwFailPortn , pm1004dcptrapLineNumber, pm1004dcptrapBoardNumber}
	STATUS current
	DESCRIPTION "Critical Line default is activated"
	::= { pm1004dcptraps 34 }

pm1004dcpLineTrapCritGoesOff NOTIFICATION-TYPE
	OBJECTS {pm1004dcpAlmLineFailPortn , pm1004dcpAlmLineHwFailPortn , pm1004dcptrapLineNumber, pm1004dcptrapBoardNumber}
	STATUS current
	DESCRIPTION "Critical Line default disappeared"
	::= { pm1004dcptraps 35 }






--- *****************************************************
---     CLIENT TRAPS
--- *****************************************************

pm1004dcpClientTrapNotUrgentGoesOn NOTIFICATION-TYPE
	OBJECTS {pm1004dcpAlmSfpDdmWarningPortn, pm1004dcptrapPortNumber, pm1004dcptrapBoardNumber}
	STATUS current
	DESCRIPTION "Not urgent client default is activated"
	::= { pm1004dcptraps 40 }

pm1004dcpClientTrapNotUrgentGoesOff NOTIFICATION-TYPE
	OBJECTS {pm1004dcpAlmSfpDdmWarningPortn, pm1004dcptrapPortNumber, pm1004dcptrapBoardNumber}
	STATUS current
	DESCRIPTION "Not urgent client default disappeared"
	::= { pm1004dcptraps 41 }

pm1004dcpClientTrapUrgentGoesOn NOTIFICATION-TYPE
	OBJECTS {pm1004dcpAlmSfpDdmAlmPortn, pm1004dcptrapPortNumber, pm1004dcptrapBoardNumber}
	STATUS current
	DESCRIPTION "Urgent client default is activated"
	::= { pm1004dcptraps 42 }

pm1004dcpClientTrapUrgentGoesOff NOTIFICATION-TYPE
	OBJECTS {pm1004dcpAlmSfpDdmAlmPortn, pm1004dcptrapPortNumber, pm1004dcptrapBoardNumber}
	STATUS current
	DESCRIPTION "Urgent client default disappeared"
	::= { pm1004dcptraps 43 }

pm1004dcpClientTrapCritGoesOn NOTIFICATION-TYPE
	OBJECTS {pm1004dcpAlmFailAccPortn, pm1004dcpAlmHwFailAccPortn, pm1004dcptrapPortNumber, pm1004dcptrapBoardNumber}
	STATUS current
	DESCRIPTION "Critical client default is activated"
	::= { pm1004dcptraps 44 }

pm1004dcpClientTrapCritGoesOff NOTIFICATION-TYPE
	OBJECTS {pm1004dcpAlmFailAccPortn, pm1004dcpAlmHwFailAccPortn, pm1004dcptrapPortNumber, pm1004dcptrapBoardNumber}
	STATUS current
	DESCRIPTION "Critical client default disappeared"
	::= { pm1004dcptraps 45 }






--- *****************************************************
---     HW TRAPS
--- *****************************************************

pm1004dcpPowerTrapUrgentGoesOn NOTIFICATION-TYPE
	OBJECTS {pm1004dcpAlmDefFuseB, pm1004dcpAlmDefFuseA , pm1004dcptrapBoardNumber}
	STATUS current
	DESCRIPTION "Urgent power supply default is activated"
	::= { pm1004dcptraps 50 }

pm1004dcpPowerTrapUrgentGoesOff NOTIFICATION-TYPE
	OBJECTS {pm1004dcpAlmDefFuseB, pm1004dcpAlmDefFuseA , pm1004dcptrapBoardNumber}
	STATUS current
	DESCRIPTION "Urgent power supply default disappeared"
	::= { pm1004dcptraps 51 }






END
