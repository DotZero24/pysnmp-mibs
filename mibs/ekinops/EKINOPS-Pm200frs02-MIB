-- *****************************************************************
-- EKINOPS-Pm200frs02.TXT:  MIB
--
--MIB Part Number:3MI00050AAAB
--MIB Version:01
--
-- Copyright (c) 2017 by Ekinops
-- All rights reserved.
--
-- *****************************************************************

EKINOPS-Pm200frs02-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

modulePm200frs02 MODULE-IDENTITY
        LAST-UPDATED "201709150000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.fr"
        DESCRIPTION
          "Creation."

	REVISION "201707250000Z"
	DESCRIPTION
	  "Creation for PM200FRS02"
	REVISION "201709150000Z"
	DESCRIPTION
	  "Adding Alarm Objects"
        ::= { ekinops 90 }



--- *****************************************************
---     LEAF LEVEL 2
--- *****************************************************


pm200frs02alarms OBJECT IDENTIFIER ::= { modulePm200frs02 2 }
pm200frs02AlmOther OBJECT IDENTIFIER ::= { pm200frs02alarms 1 }
pm200frs02AlmOtherNurg OBJECT IDENTIFIER ::= { pm200frs02AlmOther 1 }
pm200frs02AlmOtherUrg OBJECT IDENTIFIER ::= { pm200frs02AlmOther 2 }
pm200frs02AlmOtherCrit OBJECT IDENTIFIER ::= { pm200frs02AlmOther 3 }

pm200frs02AlmClient OBJECT IDENTIFIER ::= { pm200frs02alarms 2 }
pm200frs02AlmClientNurg OBJECT IDENTIFIER ::= { pm200frs02AlmClient 1 }
pm200frs02AlmClientUrg OBJECT IDENTIFIER ::= { pm200frs02AlmClient 2 }
pm200frs02AlmClientCrit OBJECT IDENTIFIER ::= { pm200frs02AlmClient 3 }

pm200frs02AlmLine OBJECT IDENTIFIER ::= { pm200frs02alarms 3 }
pm200frs02AlmLineNurg OBJECT IDENTIFIER ::= { pm200frs02AlmLine 1 }
pm200frs02AlmLineUrg OBJECT IDENTIFIER ::= { pm200frs02AlmLine 2 }
pm200frs02AlmLineCrit OBJECT IDENTIFIER ::= { pm200frs02AlmLine 3 }





pm200frs02measures OBJECT IDENTIFIER ::= { modulePm200frs02 3 }
pm200frs02MesrOther OBJECT IDENTIFIER ::= { pm200frs02measures 1 }
pm200frs02MesrClient OBJECT IDENTIFIER ::= { pm200frs02measures 2 }
pm200frs02MesrLine OBJECT IDENTIFIER ::= { pm200frs02measures 3 }




pm200frs02counters OBJECT IDENTIFIER ::= { modulePm200frs02 4 }
pm200frs02CntOther OBJECT IDENTIFIER ::= { pm200frs02counters 1 }
pm200frs02CntClient OBJECT IDENTIFIER ::= { pm200frs02counters 2 }
pm200frs02CntLine OBJECT IDENTIFIER ::= { pm200frs02counters 3 }


pm200frs02controlsWrite OBJECT IDENTIFIER ::= { modulePm200frs02 6 }
pm200frs02CtrlOther OBJECT IDENTIFIER ::= { pm200frs02controlsWrite 1 }
pm200frs02CtrlClient OBJECT IDENTIFIER ::= { pm200frs02controlsWrite 2 }
pm200frs02CtrlLine OBJECT IDENTIFIER ::= { pm200frs02controlsWrite 3 }

pm200frs02ri OBJECT IDENTIFIER ::= { modulePm200frs02 7 }
pm200frs02riTable OBJECT IDENTIFIER ::= { pm200frs02ri 1 }

pm200frs02download OBJECT IDENTIFIER ::= { modulePm200frs02 8 }
pm200frs02DwlOther OBJECT IDENTIFIER ::= { pm200frs02download 1 }
pm200frs02DwlClient OBJECT IDENTIFIER ::= { pm200frs02download 2 }
pm200frs02DwlLine OBJECT IDENTIFIER ::= { pm200frs02download 3 }


pm200frs02Config OBJECT IDENTIFIER ::= { modulePm200frs02 9 }

pm200frs02traps OBJECT IDENTIFIER ::= { modulePm200frs02 10 }



pm200frs02Monitoring OBJECT IDENTIFIER ::= { modulePm200frs02 11}

pm200frs02MonOther OBJECT IDENTIFIER ::= { pm200frs02Monitoring 1 }
pm200frs02MonRmon OBJECT IDENTIFIER ::= { pm200frs02MonOther 3 }

pm200frs02MonClient OBJECT IDENTIFIER ::= { pm200frs02Monitoring 2 }
pm200frs02MonClientRmonCounter OBJECT IDENTIFIER ::= { pm200frs02MonClient 4 }


pm200frs02MonPerfOther OBJECT IDENTIFIER ::= { pm200frs02Monitoring 5 }
pm200frs02MonPerfSync OBJECT IDENTIFIER ::= { pm200frs02MonPerfOther 1 }
pm200frs02MonPerfTimeStamp OBJECT IDENTIFIER ::= { pm200frs02MonPerfOther 2 }


pm200frs02MonPerfClient OBJECT IDENTIFIER ::= { pm200frs02Monitoring 6 }

pm200frs02MonPerfLine OBJECT IDENTIFIER ::= { pm200frs02Monitoring 7 }



--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Pm200frs02MultiRate ::= TEXTUAL-CONVENTION
    STATUS      current
    DESCRIPTION "different rate for a client port"
    SYNTAX INTEGER {
		rate100Mhz(0),
		rate250Mhz(1),
		rate500Mhz(2),
		rate1Ghz(3)
           }

Pm200frs02OtxMode ::= TEXTUAL-CONVENTION
    STATUS      current
    DESCRIPTION "Different modes on OTX-TLH on client and line ports"
    SYNTAX INTEGER {
		otx80mode(1),
		otx60mode(2),
		otxadjustmode(4)
           }

Pm200frs02OtxGrid ::= TEXTUAL-CONVENTION
    STATUS      current
    DESCRIPTION "Different grids on OTX-TLH on client and line ports"
    SYNTAX INTEGER {
		otxgrid200(200),
		otxgrid100(100),
		otxgrid50(50)
           }

Pm200frs02AdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pm200frs02ClientProtocol ::= TEXTUAL-CONVENTION
    STATUS      current
    DESCRIPTION "Different values on the protocol on the client ports"
    SYNTAX INTEGER {
		protocolclientvalue0(0),
		protocolclientvalue1(1),
		protocolclientvalue2(2),
		protocolclientvalue3(3),
		protocolclientvalue4(4),
		protocolclientvalue5(5),
		protocolclientvalue6(6),
		protocolclientvalue7(7),
		protocolclientvalue8(8)
           }

Pm200frs02ModuleMode ::= TEXTUAL-CONVENTION
    STATUS      current
    DESCRIPTION "Different values on the module mode"
    SYNTAX INTEGER {
		modulemodevalue0(0),
		modulemodevalue1(1),
		modulemodevalue2(2),
		modulemodevalue3(3),
		modulemodevalue4(4),
		modulemodevalue5(5)
           }

Pm200frs02OtxChannel ::= TEXTUAL-CONVENTION
    STATUS      current
    DESCRIPTION "Channel selection on transceiver Tx line ports"
    SYNTAX INTEGER

Pm200frs02OrxChannel ::= TEXTUAL-CONVENTION
    STATUS      current
    DESCRIPTION "Channel selection on transceiver Rx line ports"
    SYNTAX INTEGER

Pm200frs02DccMode ::= TEXTUAL-CONVENTION
    STATUS      current
    DESCRIPTION "Mode for DCC"
    SYNTAX INTEGER {
		dccNo(0),
		dccLine1(1),
		dccLine2(2)
           }

--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm200frs02RinvReloadInventory OBJECT-TYPE
  SYNTAX EkiOnOff
  MAX-ACCESS read-write
  STATUS current
  DESCRIPTION
        "Reload the inventory: This OID triggers an
         inventory reload."
  ::= { pm200frs02ri 2 }

pm200frs02RinvHwPlatform OBJECT-TYPE
  SYNTAX DisplayString
  MAX-ACCESS read-only
  STATUS current
  DESCRIPTION
        "HW platform description: This OID contains the
         description of the Hardware platform."
  ::= { pm200frs02ri 3 }

pm200frs02RinvModulePlatform OBJECT-TYPE
  SYNTAX DisplayString
  MAX-ACCESS read-only
  STATUS current
  DESCRIPTION
        "Module platform description: This OID contains the
         description of the Module."
  ::= { pm200frs02ri 4 }

pm200frs02RinvSwPlatform OBJECT-TYPE
  SYNTAX DisplayString
  MAX-ACCESS read-only
  STATUS current
  DESCRIPTION
        "SW platform description: This OID contains the
         description of the Software platform."
  ::= { pm200frs02ri 5 }

pm200frs02RinvGwPlatform OBJECT-TYPE
  SYNTAX DisplayString
  MAX-ACCESS read-only
  STATUS current
  DESCRIPTION
        "GW platform description: This OID contains the
         description of the Gateware platform."
  ::= { pm200frs02ri 6 }


pm200frs02RinvSfpTable OBJECT-TYPE
      SYNTAX  SEQUENCE OF Pm200frs02RinvSfpEntry
      MAX-ACCESS  not-accessible
      STATUS  current
      DESCRIPTION
              "List of the SFPs on the selected module"
      ::= { pm200frs02riTable 1 }

pm200frs02RinvSfpEntry OBJECT-TYPE
        SYNTAX  Pm200frs02RinvSfpEntry
        MAX-ACCESS  not-accessible
        STATUS  current
        DESCRIPTION
              "Row definition for the SFP table"
        INDEX   { pm200frs02RinvSfpIndex }
        ::= { pm200frs02RinvSfpTable 1 }



Pm200frs02RinvSfpEntry::=
        SEQUENCE {
          pm200frs02RinvSfpIndex
              Integer32,
          pm200frs02Rinvsfp
              DisplayString
        }


    pm200frs02RinvSfpIndex OBJECT-TYPE
        SYNTAX  Integer32(1..16)
        MAX-ACCESS  read-only
        STATUS  current
        DESCRIPTION
              "Index for SFP table"
        ::= { pm200frs02RinvSfpEntry 1 }


    pm200frs02Rinvsfp OBJECT-TYPE
        SYNTAX  DisplayString
        MAX-ACCESS  read-only
        STATUS  current
        DESCRIPTION
              "Inventory for the SFP: This OID contains the inventory for the SFP"
        ::= { pm200frs02RinvSfpEntry 2 }




pm200frs02RinvLineTable OBJECT-TYPE
      SYNTAX  SEQUENCE OF Pm200frs02RinvLineEntry
      MAX-ACCESS  not-accessible
      STATUS  current
      DESCRIPTION
              "List of the XFPs on the selected module"
      ::= { pm200frs02riTable 2 }

pm200frs02RinvLineEntry OBJECT-TYPE
        SYNTAX  Pm200frs02RinvLineEntry
        MAX-ACCESS  not-accessible
        STATUS  current
        DESCRIPTION
              "Row definition for the XFP table"
        INDEX   { pm200frs02RinvLineIndex }
        ::= { pm200frs02RinvLineTable 1 }



Pm200frs02RinvLineEntry::=
        SEQUENCE {
          pm200frs02RinvLineIndex
              Integer32,
          pm200frs02RinvxfpLine
              DisplayString
        }


    pm200frs02RinvLineIndex OBJECT-TYPE
        SYNTAX  Integer32(1..16)
        MAX-ACCESS  read-only
        STATUS  current
        DESCRIPTION
              "Index for XFP table"
        ::= { pm200frs02RinvLineEntry 1 }


    pm200frs02RinvxfpLine OBJECT-TYPE
        SYNTAX  DisplayString
        MAX-ACCESS  read-only
        STATUS  current
        DESCRIPTION
              "Inventory for the XFP: This OID contains the inventory for the XFP"
        ::= { pm200frs02RinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm200frs02AlmsynthAlm0 OBJECT IDENTIFIER ::= { pm200frs02AlmOtherCrit 0 }




pm200frs02AlmDefFuseB OBJECT-TYPE
	  SYNTAX EkiOnOff
	  MAX-ACCESS read-only
	  STATUS current
	  DESCRIPTION
        "
        Fuse B Fail :This OID indicates
        that the fuse of the power input
        B is in fail condition <Help> Status
        of the Fuse B <Condtype> DEF_FUSE_B
        <Probcause> powerProblem (36) <Alarmtype>
        equipmentAlarm (5) <Polarity> (2)
        "
	  ::= { pm200frs02AlmsynthAlm0 16 }



pm200frs02AlmDefFuseA OBJECT-TYPE
	  SYNTAX EkiOnOff
	  MAX-ACCESS read-only
	  STATUS current
	  DESCRIPTION
        "
        Fuse A Fail :This OID indicates
        that the fuse of the power input
        A is in fail condition <Help> Status
        of the Fuse A <Condtype> DEF_FUSE_A
        <Probcause> powerProblem (36) <Alarmtype>
        equipmentAlarm (5) <Polarity> (2)
        "
	  ::= { pm200frs02AlmsynthAlm0 15 }



pm200frs02AlmModGlobFail OBJECT-TYPE
	  SYNTAX EkiOnOff
	  MAX-ACCESS read-only
	  STATUS current
	  DESCRIPTION
        "
        Module Failure :This OID is set
        on detection of a failure originating
        from the RM <Help> This alarm is
        set on detection of a failure originating
        from the equipment <Condtype> MOD_GLOB_FAIL
        <Probcause> other (1) <Alarmtype>
        synthesisAlarm (12)  <Polarity>
        (2)
        "
	  ::= { pm200frs02AlmsynthAlm0 9 }



pm200frs02AlmFailFan OBJECT-TYPE
	  SYNTAX EkiOnOff
	  MAX-ACCESS read-only
	  STATUS current
	  DESCRIPTION
        "
        Fan Fail :This OID is at 1 when
        any fail occurs on the fan tray
        <Help> This alarm indicates that
        the Fan tray module is in a failure
        condition <Condtype> FAIL_FAN <Probcause>
        equipmentMalfunction (16) <Alarmtype>
        equipmentAlarm (5) <Polarity> (2)
        "
	  ::= { pm200frs02AlmsynthAlm0 2 }



--- *****************************************************
---     LEAF for the synthAlm2 article
--- *****************************************************
pm200frs02AlmsynthAlm2 OBJECT IDENTIFIER ::= { pm200frs02AlmOtherNurg 2 }




pm200frs02AlmMaintenanceOn OBJECT-TYPE
	  SYNTAX EkiOnOff
	  MAX-ACCESS read-only
	  STATUS current
	  DESCRIPTION
        "
        Maintenance Mode :This OID indicates
        that the RM is in maintenance mode.
        <Help> This alarm indicates that
        the maintenance mode is enabled
        on the PM <Condtype> MAINTENANCE_ON
        <Probcause> informationalStatus(1000)
        <Alarmtype> other (1) <Polarity>
        (2)
        "
	  ::= { pm200frs02AlmsynthAlm2 5 }



pm200frs02AlmCorrelatOff OBJECT-TYPE
	  SYNTAX EkiOnOff
	  MAX-ACCESS read-only
	  STATUS current
	  DESCRIPTION
        "
        Not Used :This OID, when set,
         indicates that alarm correlation
        is not being performed. <Condtype>
        CORRELAT_OFF <Probcause> informationalStatus(1000)
        <Alarmtype> other (1) <Polarity>
        (2)
        "
	  ::= { pm200frs02AlmsynthAlm2 4 }



pm200frs02AlmConfTableLoad OBJECT-TYPE
	  SYNTAX EkiOnOff
	  MAX-ACCESS read-only
	  STATUS current
	  DESCRIPTION
        "
        PM Configuration Load :This OID
         is at 1 during the loading of
         configuration tables in the modules
        RAM. <Condtype> CONF_TABLE_LOAD
        <Probcause> informationalStatus(1000)
        <Alarmtype> other (1) <Polarity>
        (2)
        "
	  ::= { pm200frs02AlmsynthAlm2 3 }



pm200frs02AlmInvUpload OBJECT-TYPE
	  SYNTAX EkiOnOff
	  MAX-ACCESS read-only
	  STATUS current
	  DESCRIPTION
        "
        Inventory Upload :This OID is
         at 1 during the uploading of PM
        inventory information. <Condtype>
        INV_UPLOAD <Probcause> informationalStatus(1000)
        <Alarmtype> other (1) <Polarity>
        (2)
        "
	  ::= { pm200frs02AlmsynthAlm2 2 }



pm200frs02AlmConfTableSave OBJECT-TYPE
	  SYNTAX EkiOnOff
	  MAX-ACCESS read-only
	  STATUS current
	  DESCRIPTION
        "
        PM Configuration Save :This OID
        is at 1 during the saving of a
         new configuration table in the
        module Flash memory. <Condtype>
        CONF_TABLE_SAVE <Probcause> informationalStatus(1000)
        <Alarmtype> other (1) <Polarity>
        (2)
        "
	  ::= { pm200frs02AlmsynthAlm2 1 }



--- *********************************************************
---     TABLE for the pm200frs02AlmsynthAlmPort articles
--- *********************************************************

pm200frs02AlmsynthAlmPortTable OBJECT-TYPE
	SYNTAX  SEQUENCE OF Pm200frs02AlmsynthAlmPortEntry
	MAX-ACCESS not-accessible
	STATUS current
	DESCRIPTION
        "
        List of pm200frs02AlmsynthAlmPort
        Article
        "
	::= { pm200frs02AlmClientCrit 8 }


pm200frs02AlmsynthAlmPortEntry OBJECT-TYPE
	SYNTAX Pm200frs02AlmsynthAlmPortEntry
	MAX-ACCESS not-accessible
	STATUS current
	DESCRIPTION
        "
        Row definition for the pm200frs02AlmsynthAlmPort
        table
        "
	INDEX   { pm200frs02AlmsynthAlmPortIndex }
	::= { pm200frs02AlmsynthAlmPortTable 1 }


Pm200frs02AlmsynthAlmPortEntry ::=
	SEQUENCE {
	pm200frs02AlmsynthAlmPortIndex
		INTEGER,
	pm200frs02AlmUpCsfPortn
		EkiOnOff,
	pm200frs02AlmFailAccPortn
		EkiOnOff,
	pm200frs02AlmSfpDdmAlmPortn
		EkiOnOff,
	pm200frs02AlmSfpDdmWarningPortn
		EkiOnOff,
	pm200frs02AlmDwCaisPortn
		EkiOnOff,
	pm200frs02AlmClientRemoteOosPortn
		EkiOnOff,
	pm200frs02AlmClientLocalOosPortn
		EkiOnOff,
	pm200frs02AlmDwLsdPortn
		EkiOnOff,
	pm200frs02AlmHwFailAccPortn
		EkiOnOff,
	pm200frs02AlmDdmAbsentPortn
		EkiOnOff,
	pm200frs02AlmSfpAbsentPortn
		EkiOnOff
	}


pm200frs02AlmsynthAlmPortIndex OBJECT-TYPE
	SYNTAX  INTEGER(0..128)
	MAX-ACCESS  read-only
	STATUS current
	DESCRIPTION
        "
        Index definition for the pm200frs02AlmsynthAlmPort
        table
        "
	::= { pm200frs02AlmsynthAlmPortEntry 1 }


pm200frs02AlmUpCsfPortn OBJECT-TYPE
	SYNTAX  EkiOnOff
	MAX-ACCESS read-only
	STATUS current
	DESCRIPTION
        "
        Client Signal Fail Inserted :This
        OID indicates a CSF has been inserted
        in the upstream client port. <Help>
        This status indicates if a Client
        Signal Fail is currently inserted
        on the line signal for this client
        port <Condtype> UP_CSF_1 <Probcause>
        informationalStatus(1000) <Alarmtype>
        other (1) <Polarity> (2)
        "
	::= { pm200frs02AlmsynthAlmPortEntry 17 }


pm200frs02AlmFailAccPortn OBJECT-TYPE
	SYNTAX  EkiOnOff
	MAX-ACCESS read-only
	STATUS current
	DESCRIPTION
        "
        Client Access Fail :This OID indicates
        a failure on the Client port <Help>
        This alarm indicates a failure
         on the Client port <Condtype>
         FAIL_ACC_1 <Probcause> equipmentMalfunction
        (16) <Alarmtype> synthesisAlarm
        (12)  <Polarity> (2)
        "
	::= { pm200frs02AlmsynthAlmPortEntry 13 }


pm200frs02AlmSfpDdmAlmPortn OBJECT-TYPE
	SYNTAX  EkiOnOff
	MAX-ACCESS read-only
	STATUS current
	DESCRIPTION
        "
        Alarm On Client Trscv DDM :This
        OID indicates an alarm is being
        received from the Client Transceiver
        DDM <Help> This alarm indicates
        if a DDM Alarm has been detected
        on the client transceiver <Condtype>
        SFP_DDM_ALM_1 <Probcause> inputOutputDeviceError
        (24) <Alarmtype> synthesisAlarm
        (12)  <Polarity> (2)
        "
	::= { pm200frs02AlmsynthAlmPortEntry 11 }


pm200frs02AlmSfpDdmWarningPortn OBJECT-TYPE
	SYNTAX  EkiOnOff
	MAX-ACCESS read-only
	STATUS current
	DESCRIPTION
        "
        Warning On Client Trscv DDM :This
        OID indicates a warning is being
        received from the Client Transceiver
        DDM <Help> This alarm indicates
        if a DDM Warning has been detected
        on the client transceiver <Condtype>
        SFP_DDM_WARNING_1 <Probcause> inputOutputDeviceError
        (24) <Alarmtype> synthesisAlarm
        (12)  <Polarity> (2)
        "
	::= { pm200frs02AlmsynthAlmPortEntry 10 }


pm200frs02AlmDwCaisPortn OBJECT-TYPE
	SYNTAX  EkiOnOff
	MAX-ACCESS read-only
	STATUS current
	DESCRIPTION
        "
        Client AIS Inserted :This OID
         indicates a CAIS has been inserted
        on the output client port. <Help>
        This status indicates if a Client
        Alarm Indication Signal is currently
        inserted on the client interface
        <Condtype> DW_CAIS_1 <Probcause>
        informationalStatus(1000) <Alarmtype>
        other (1) <Polarity> (2)
        "
	::= { pm200frs02AlmsynthAlmPortEntry 9 }


pm200frs02AlmClientRemoteOosPortn OBJECT-TYPE
	SYNTAX  EkiOnOff
	MAX-ACCESS read-only
	STATUS current
	DESCRIPTION
        "
        Remote Client Port In Service
         :This OID indicates that the remote
        Client port is In Service (1) or
        Out of Service (2) <Help> This
         status indicates if the remote
        client port is in service <Condtype>
        CLIENT_REMOTE_OOS <Probcause> informationalStatus(1000)
        <Alarmtype> other (1) <Polarity>
        (2)
        "
	::= { pm200frs02AlmsynthAlmPortEntry 8 }


pm200frs02AlmClientLocalOosPortn OBJECT-TYPE
	SYNTAX  EkiOnOff
	MAX-ACCESS read-only
	STATUS current
	DESCRIPTION
        "
        Local Client Port In Service :This
        OID indicates that the local Client
        port is In Service (1) or Out of
        Service (2) <Help> This status
         indicates if the local client
         port is in service <Condtype>
         CLIENT_LOCAL_OOS <Probcause> informationalStatus(1000)
        <Alarmtype> other (1) <Polarity>
        (2)
        "
	::= { pm200frs02AlmsynthAlmPortEntry 7 }


pm200frs02AlmDwLsdPortn OBJECT-TYPE
	SYNTAX  EkiOnOff
	MAX-ACCESS read-only
	STATUS current
	DESCRIPTION
        "
        Client Trscv Laser Shutdown :This
        OID indicates the Client transceiver
        laser is shutdown <Help> This status
        indicates if the client transceiver
        laser is shutdown <Condtype> DW_LSD_1
        <Probcause> other (1) <Alarmtype>
        equipmentAlarm (5) <Polarity> (2)
        "
	::= { pm200frs02AlmsynthAlmPortEntry 6 }


pm200frs02AlmHwFailAccPortn OBJECT-TYPE
	SYNTAX  EkiOnOff
	MAX-ACCESS read-only
	STATUS current
	DESCRIPTION
        "
        Client HW Fail :This OID indicates
        a failure on client port, most
         probably caused by a HW issue.
        <Help> This alarm indicates a failure
        on client port, most probably caused
        by a HW issue. <Condtype> HW_FAIL_ACC_1
        <Probcause> equipmentMalfunction
        (16) <Alarmtype> synthesisAlarm
        (12)  <Polarity> (2)
        "
	::= { pm200frs02AlmsynthAlmPortEntry 5 }


pm200frs02AlmDdmAbsentPortn OBJECT-TYPE
	SYNTAX  EkiOnOff
	MAX-ACCESS read-only
	STATUS current
	DESCRIPTION
        "
        DDM Supported On Client Trscv
         :This OID indicates that the Client
        transceiver supports the Digital
        Diagnostic Monitoring function
         <Help> This status indicates if
        the client transceiver includes
        the DDM feature <Condtype> DDM_ABSENT_1
        <Probcause> informationalStatus(1000)
        <Alarmtype> other (1) <Polarity>
        (2)
        "
	::= { pm200frs02AlmsynthAlmPortEntry 3 }


pm200frs02AlmSfpAbsentPortn OBJECT-TYPE
	SYNTAX  EkiOnOff
	MAX-ACCESS read-only
	STATUS current
	DESCRIPTION
        "
        Client Optical Module Absent :This
        OID indicates that the Transceiver
        is not present in the client port.
        <Help> This alarm indicates if
         the client transceiver is not
         plugged <Condtype> SFP_ABSENT_1
        <Probcause> inputOutputDeviceError
        (24) <Alarmtype> equipmentAlarm
        (5) <Polarity> (2) <Event> ObjectCDSingleClientInv
        "
	::= { pm200frs02AlmsynthAlmPortEntry 2 }


--- *********************************************************
---     TABLE for the pm200frs02AlmsynthAlmLine articles
--- *********************************************************

pm200frs02AlmsynthAlmLineTable OBJECT-TYPE
	SYNTAX  SEQUENCE OF Pm200frs02AlmsynthAlmLineEntry
	MAX-ACCESS not-accessible
	STATUS current
	DESCRIPTION
        "
        List of pm200frs02AlmsynthAlmLine
        Article
        "
	::= { pm200frs02AlmLineCrit 40 }


pm200frs02AlmsynthAlmLineEntry OBJECT-TYPE
	SYNTAX Pm200frs02AlmsynthAlmLineEntry
	MAX-ACCESS not-accessible
	STATUS current
	DESCRIPTION
        "
        Row definition for the pm200frs02AlmsynthAlmLine
        table
        "
	INDEX   { pm200frs02AlmsynthAlmLineIndex }
	::= { pm200frs02AlmsynthAlmLineTable 1 }


Pm200frs02AlmsynthAlmLineEntry ::=
	SEQUENCE {
	pm200frs02AlmsynthAlmLineIndex
		INTEGER,
	pm200frs02AlmLineActivePortn
		EkiOnOff,
	pm200frs02AlmLineFailPortn
		EkiOnOff,
	pm200frs02AlmLineDdmAlmPortn
		EkiOnOff,
	pm200frs02AlmLineDdmWarningPortn
		EkiOnOff,
	pm200frs02AlmUpRdiInsPortn
		EkiOnOff,
	pm200frs02AlmLineLocalOosPortn
		EkiOnOff,
	pm200frs02AlmXfpTxOffPortn
		EkiOnOff,
	pm200frs02AlmLineHwFailPortn
		EkiOnOff,
	pm200frs02AlmXfpInitNotComplPortn
		EkiOnOff,
	pm200frs02AlmXfpAbsentPortn
		EkiOnOff
	}


pm200frs02AlmsynthAlmLineIndex OBJECT-TYPE
	SYNTAX  INTEGER(0..128)
	MAX-ACCESS  read-only
	STATUS current
	DESCRIPTION
        "
        Index definition for the pm200frs02AlmsynthAlmLine
        table
        "
	::= { pm200frs02AlmsynthAlmLineEntry 1 }


pm200frs02AlmLineActivePortn OBJECT-TYPE
	SYNTAX  EkiOnOff
	MAX-ACCESS read-only
	STATUS current
	DESCRIPTION
        "
        Line Active :This OID indicates
        whether the line is active or standby.
        <Help> This status indicates whether
        the line is active or standby.
         <Condtype> LINE_ACTIVE <Probcause>
        informationalStatus(1000) <Alarmtype>
        other (1) <Polarity> (2)
        "
	::= { pm200frs02AlmsynthAlmLineEntry 17 }


pm200frs02AlmLineFailPortn OBJECT-TYPE
	SYNTAX  EkiOnOff
	MAX-ACCESS read-only
	STATUS current
	DESCRIPTION
        "
        Line Port Failure :This OID indicates
        a failure on the line port <Help>
        This alarm indicates a failure
         on the line port <Condtype> LINE_FAIL
        <Probcause> equipmentMalfunction
        (16) <Alarmtype> synthesisAlarm
        (12)  <Polarity> (2)
        "
	::= { pm200frs02AlmsynthAlmLineEntry 13 }


pm200frs02AlmLineDdmAlmPortn OBJECT-TYPE
	SYNTAX  EkiOnOff
	MAX-ACCESS read-only
	STATUS current
	DESCRIPTION
        "
        Alarm On Line Optical Module DDM
        :This OID indicates an alarm is
        present coming out of Line transceiver
        DDM <Help> This alarm indicates
        if a DDM Alarm has been detected
        on the line transceiver <Condtype>
        LINE_DDM_ALM <Probcause> inputOutputDeviceError
        (24) <Alarmtype> synthesisAlarm
        (12)  <Polarity> (2)
        "
	::= { pm200frs02AlmsynthAlmLineEntry 11 }


pm200frs02AlmLineDdmWarningPortn OBJECT-TYPE
	SYNTAX  EkiOnOff
	MAX-ACCESS read-only
	STATUS current
	DESCRIPTION
        "
        Warning On Line Optical Module
        DDM :This OID indicates a warning
        is present coming out of Line transceiver
        DDM <Help> This alarm indicates
        if a DDM Warning has been detected
        on the line transceiver <Condtype>
        LINE_DDM_WARNING <Probcause> inputOutputDeviceError
        (24) <Alarmtype> synthesisAlarm
        (12)  <Polarity> (2)
        "
	::= { pm200frs02AlmsynthAlmLineEntry 10 }


pm200frs02AlmUpRdiInsPortn OBJECT-TYPE
	SYNTAX  EkiOnOff
	MAX-ACCESS read-only
	STATUS current
	DESCRIPTION
        "
        MS-RDI/L-RDI Inserted On Line
         :This OID indicates an upstream
        MS-RDI/L-RDI has been inserted
         in the outgoing 10 Gb/s SDH/SONET
        signal. <Help> This status indicates
        if a MS-RDI/L-RDI is currently
         inserted on the line interface.
        <Condtype> UP_RDI_INS <Probcause>
        informationalStatus(1000) <Alarmtype>
        other (1) <Polarity> (2)
        "
	::= { pm200frs02AlmsynthAlmLineEntry 9 }


pm200frs02AlmLineLocalOosPortn OBJECT-TYPE
	SYNTAX  EkiOnOff
	MAX-ACCESS read-only
	STATUS current
	DESCRIPTION
        "
        Line Port In Service :This OID
        indicates that the Line port is
        In Service (1) of Out or Service
        (2) <Help> This status indicates
        if the line port is in service
         <Condtype> LINE_LOCAL_OOS <Probcause>
        informationalStatus(1000) <Alarmtype>
        other (1) <Polarity> (2)
        "
	::= { pm200frs02AlmsynthAlmLineEntry 7 }


pm200frs02AlmXfpTxOffPortn OBJECT-TYPE
	SYNTAX  EkiOnOff
	MAX-ACCESS read-only
	STATUS current
	DESCRIPTION
        "
        Line Trscv Laser Shutdown :This
        OID indicates the Line transceiver
        laser is shutdown <Help> This status
        indicates if the Line transceiver
        laser is shutdown <Condtype> XFP_TX_OFF
        <Probcause> other (1) <Alarmtype>
        equipmentAlarm (5) <Polarity> (2)
        "
	::= { pm200frs02AlmsynthAlmLineEntry 6 }


pm200frs02AlmLineHwFailPortn OBJECT-TYPE
	SYNTAX  EkiOnOff
	MAX-ACCESS read-only
	STATUS current
	DESCRIPTION
        "
        Line Port HW Failure :This OID
        indicates a failure on line port,
        most probably caused by a HW issue
        <Help> This alarm indicates a failure
        on line port, most probably caused
        by a HW issue <Condtype> LINE_HW_FAIL
        <Probcause> equipmentMalfunction
        (16) <Alarmtype> synthesisAlarm
        (12)  <Polarity> (2)
        "
	::= { pm200frs02AlmsynthAlmLineEntry 5 }


pm200frs02AlmXfpInitNotComplPortn OBJECT-TYPE
	SYNTAX  EkiOnOff
	MAX-ACCESS read-only
	STATUS current
	DESCRIPTION
        "
        Line Optical Module Ready :This
        OID indicates that the optical
         interface is not operational.
         <Help> This status indicates if
        the line transceiver has been correctly
        initialized <Condtype> XFP_INIT_NOT_COMPL
        <Probcause> equipmentMalfunction
        (16) <Alarmtype> equipmentAlarm
        (5) <Polarity> (2)
        "
	::= { pm200frs02AlmsynthAlmLineEntry 3 }


pm200frs02AlmXfpAbsentPortn OBJECT-TYPE
	SYNTAX  EkiOnOff
	MAX-ACCESS read-only
	STATUS current
	DESCRIPTION
        "
        Line Optical Module Absent :This
        OID indicates that the line optical
        interface is not present. <Help>
        This alarm indicates if the line
        transceiver is not plugged <Condtype>
        XFP_ABSENT <Probcause> inputOutputDeviceError
        (24) <Alarmtype> equipmentAlarm
        (5) <Polarity> (2)
        "
	::= { pm200frs02AlmsynthAlmLineEntry 2 }


--- *****************************************************
---     LEAF for the msaModuleState article
--- *****************************************************
pm200frs02AlmmsaModuleState OBJECT IDENTIFIER ::= { pm200frs02AlmOtherCrit 78 }




pm200frs02AlmMsaHighPowerDown OBJECT-TYPE
	  SYNTAX EkiOnOff
	  MAX-ACCESS read-only
	  STATUS current
	  DESCRIPTION
        "
        Line Trscv High Power Down :This
        OID indicates the Line Trscv is
        entering Low Power state <Help>
        Status indicating the Line Trscv
        is entering Low Power state <Condtype>
        MSA_HIGH_POWER_DOWN <Probcause>
        informationalStatus(1000) <Alarmtype>
        other (1) <Polarity> (2)
        "
	  ::= { pm200frs02AlmmsaModuleState 9 }



pm200frs02AlmMsaTxTurnOff OBJECT-TYPE
	  SYNTAX EkiOnOff
	  MAX-ACCESS read-only
	  STATUS current
	  DESCRIPTION
        "
        Line Trscv Laser Turn Off :This
        OID indicates the Line Trscv is
        turning off its laser <Help> Status
        indicating the Line Trscv is turning
        off its laser <Condtype> MSA_TX_TURN_OFF
        <Probcause> informationalStatus(1000)
        <Alarmtype> other (1) <Polarity>
        (2)
        "
	  ::= { pm200frs02AlmmsaModuleState 8 }



pm200frs02AlmMsaFault OBJECT-TYPE
	  SYNTAX EkiOnOff
	  MAX-ACCESS read-only
	  STATUS current
	  DESCRIPTION
        "
        Line Trscv Fault :This OID indicates
        the Line Trscv is in Fault state
        <Help> Status indicating the Line
        Trscv is in Fault state <Condtype>
        MSA_FAULT <Probcause> informationalStatus(1000)
        <Alarmtype> other (1) <Polarity>
        (2)
        "
	  ::= { pm200frs02AlmmsaModuleState 7 }



pm200frs02AlmMsaReady OBJECT-TYPE
	  SYNTAX EkiOnOff
	  MAX-ACCESS read-only
	  STATUS current
	  DESCRIPTION
        "
        Line Trscv Ready :This OID indicates
        the Line Trscv is ready to operate
        <Help> Status indicating the Line
        Trscv is ready to operate <Condtype>
        MSA_READY <Probcause> informationalStatus(1000)
        <Alarmtype> other (1) <Polarity>
        (2)
        "
	  ::= { pm200frs02AlmmsaModuleState 6 }



pm200frs02AlmMsaTxTurnOn OBJECT-TYPE
	  SYNTAX EkiOnOff
	  MAX-ACCESS read-only
	  STATUS current
	  DESCRIPTION
        "
        Line Trscv Laser Turn On :This
        OID indicates the Line Trscv is
        turning on its laser <Help> Status
        indicating the Line Trscv is turning
        on its laser <Condtype> MSA_TX_TURN_ON
        <Probcause> informationalStatus(1000)
        <Alarmtype> other (1) <Polarity>
        (2)
        "
	  ::= { pm200frs02AlmmsaModuleState 5 }



pm200frs02AlmMsaTxOff OBJECT-TYPE
	  SYNTAX EkiOnOff
	  MAX-ACCESS read-only
	  STATUS current
	  DESCRIPTION
        "
        Line Trscv Laser Shutdown :This
        OID indicates the Line Trscv Laser
        is OFF <Help> Status indicating
        the Line Trscv Laser is OFF <Condtype>
        MSA_TX_OFF <Probcause> informationalStatus(1000)
        <Alarmtype> other (1) <Polarity>
        (2)
        "
	  ::= { pm200frs02AlmmsaModuleState 4 }



pm200frs02AlmMsaHighPowerUp OBJECT-TYPE
	  SYNTAX EkiOnOff
	  MAX-ACCESS read-only
	  STATUS current
	  DESCRIPTION
        "
        Line Trscv High Power Up :This
        OID indicates the Line Trscv is
        leaving Low Power state <Help>
         Status indicating the Line Trscv
        is leaving Low Power state <Condtype>
        MSA_HIGH_POWER_UP <Probcause> informationalStatus(1000)
        <Alarmtype> other (1) <Polarity>
        (2)
        "
	  ::= { pm200frs02AlmmsaModuleState 3 }



pm200frs02AlmMsaLowPower OBJECT-TYPE
	  SYNTAX EkiOnOff
	  MAX-ACCESS read-only
	  STATUS current
	  DESCRIPTION
        "
        Line Trscv Low Power :This OID
        indicates the Line Trscv is in
         low power state <Help> Status
         indicating the Line Trscv is in
        low power state <Condtype> MSA_LOW_POWER
        <Probcause> informationalStatus(1000)
        <Alarmtype> other (1) <Polarity>
        (2)
        "
	  ::= { pm200frs02AlmmsaModuleState 2 }



pm200frs02AlmMsaInitialize OBJECT-TYPE
	  SYNTAX EkiOnOff
	  MAX-ACCESS read-only
	  STATUS current
	  DESCRIPTION
        "
        Line Trscv Initialize :This OID
        indicates the Line Trscv initialization
        is in progress <Help> Status indicating
        the Line Trscv initialization is
        in progress <Condtype> MSA_INITIALIZE
        <Probcause> informationalStatus(1000)
        <Alarmtype> other (1) <Polarity>
        (2)
        "
	  ::= { pm200frs02AlmmsaModuleState 1 }



--- *********************************************************
---     TABLE for the pm200frs02AlmclientHostLaneFault articles
--- *********************************************************

pm200frs02AlmclientHostLaneFaultTable OBJECT-TYPE
	SYNTAX  SEQUENCE OF Pm200frs02AlmclientHostLaneFaultEntry
	MAX-ACCESS not-accessible
	STATUS current
	DESCRIPTION
        "
        List of pm200frs02AlmclientHostLaneFault
        Article
        "
	::= { pm200frs02AlmClientUrg 152 }


pm200frs02AlmclientHostLaneFaultEntry OBJECT-TYPE
	SYNTAX Pm200frs02AlmclientHostLaneFaultEntry
	MAX-ACCESS not-accessible
	STATUS current
	DESCRIPTION
        "
        Row definition for the pm200frs02AlmclientHostLaneFault
        table
        "
	INDEX   { pm200frs02AlmclientHostLaneFaultIndex }
	::= { pm200frs02AlmclientHostLaneFaultTable 1 }


Pm200frs02AlmclientHostLaneFaultEntry ::=
	SEQUENCE {
	pm200frs02AlmclientHostLaneFaultIndex
		INTEGER,
	pm200frs02AlmClientLaneTxFifoErrorPortn
		EkiOnOff,
	pm200frs02AlmClientTxHostLolPortn
		EkiOnOff,
	pm200frs02AlmClientCsfDetectedPortn
		EkiOnOff,
	pm200frs02AlmClientLanesNotAlignedPortn
		EkiOnOff,
	pm200frs02AlmClientLanes6466UnlockPortn
		EkiOnOff,
	pm200frs02AlmClientLanesMarkerUnlockPortn
		EkiOnOff,
	pm200frs02AlmClientInputLossOfSigPortn
		EkiOnOff,
	pm200frs02AlmClientLossOfSyncPortn
		EkiOnOff
	}


pm200frs02AlmclientHostLaneFaultIndex OBJECT-TYPE
	SYNTAX  INTEGER(0..128)
	MAX-ACCESS  read-only
	STATUS current
	DESCRIPTION
        "
        Index definition for the pm200frs02AlmclientHostLaneFault
        table
        "
	::= { pm200frs02AlmclientHostLaneFaultEntry 1 }


pm200frs02AlmClientLaneTxFifoErrorPortn OBJECT-TYPE
	SYNTAX  EkiOnOff
	MAX-ACCESS read-only
	STATUS current
	DESCRIPTION
        "
        Client Host Lane Tx FIFO Error
        :This OID indicates a Tx FIFO Error
        on the Client Trscv Host Lane <Help>
        Alarm indicating a Tx FIFO Error
        on the Client Trscv Host Lane <Condtype>
        CLIENT_LANE_TX_FIFO_ERROR <Probcause>
        receiverFailure (42) <Alarmtype>
        equipmentAlarm (5) <Polarity> (2)
        "
	::= { pm200frs02AlmclientHostLaneFaultEntry 11 }


pm200frs02AlmClientTxHostLolPortn OBJECT-TYPE
	SYNTAX  EkiOnOff
	MAX-ACCESS read-only
	STATUS current
	DESCRIPTION
        "
        Client Host Lane Tx Loss Of Lock
        :This OID indicates a Tx Loss of
        Lock on the Client Trscv Host Lane
        <Help> Alarm indicating a Tx Loss
        of Lock on the Client Trscv Host
        Lane <Condtype> CLIENT_TX_HOST_LOL
        <Probcause> receiverFailure (42)
        <Alarmtype> equipmentAlarm (5)
         <Polarity> (2)
        "
	::= { pm200frs02AlmclientHostLaneFaultEntry 10 }


pm200frs02AlmClientCsfDetectedPortn OBJECT-TYPE
	SYNTAX  EkiOnOff
	MAX-ACCESS read-only
	STATUS current
	DESCRIPTION
        "
        Client Signal Fail Detected :This
        OID indicates that a CSF has been
        detected on client port in the
         downstream direction   <Help>
          This alarm indicates if a Client
        Signal Fail has been detected in
        the incoming line frame for this
        client port <Condtype> CLIENT_CSF_DETECTED
        <Probcause> receiveFailure (41)
        <Alarmtype> other(1) <Polarity>
        (2)
        "
	::= { pm200frs02AlmclientHostLaneFaultEntry 7 }


pm200frs02AlmClientLanesNotAlignedPortn OBJECT-TYPE
	SYNTAX  EkiOnOff
	MAX-ACCESS read-only
	STATUS current
	DESCRIPTION
        "
        Client Lanes Not Aligned :This
        OID indicates the Client lanes
         are not aligned <Help> Alarm indicating
        the Client lanes are not aligned
        <Condtype> CLIENT_LANES_NOT_ALIGNED
        <Probcause> receiveFailure (41)
        <Alarmtype> integrityViolation
         (7) <Polarity> (2)
        "
	::= { pm200frs02AlmclientHostLaneFaultEntry 6 }


pm200frs02AlmClientLanes6466UnlockPortn OBJECT-TYPE
	SYNTAX  EkiOnOff
	MAX-ACCESS read-only
	STATUS current
	DESCRIPTION
        "
        Client Lanes 64/66b Unlock :This
        OID indicates the Client 64/66b
        decoder is not lock <Help> Alarm
        indicating the Client 64/66b decoder
        is not lock <Condtype> CLIENT_LANES_64_66_UNLOCK
        <Probcause> receiveFailure (41)
        <Alarmtype> integrityViolation
         (7) <Polarity> (2)
        "
	::= { pm200frs02AlmclientHostLaneFaultEntry 5 }


pm200frs02AlmClientLanesMarkerUnlockPortn OBJECT-TYPE
	SYNTAX  EkiOnOff
	MAX-ACCESS read-only
	STATUS current
	DESCRIPTION
        "
        Client Lanes Marker Unlock :This
        OID indicates the Client lanes
         marker alignment is not lock <Help>
        Alarm indicating the Client lanes
        marker alignment is not lock <Condtype>
        CLIENT_LANES_MARKER_UNLOCK <Probcause>
        receiveFailure (41) <Alarmtype>
        integrityViolation (7) <Polarity>
        (2)
        "
	::= { pm200frs02AlmclientHostLaneFaultEntry 4 }


pm200frs02AlmClientInputLossOfSigPortn OBJECT-TYPE
	SYNTAX  EkiOnOff
	MAX-ACCESS read-only
	STATUS current
	DESCRIPTION
        "
        Client Input Loss Of Signal :This
        OID indicates a Loss of Signal
         is detected on the Client Trscv
        <Help> Alarm indicating a Loss
         of Signal is detected on the Client
        Trscv <Condtype> CLIENT_INPUT_LOSS_OF_SIG
        <Probcause> receiveFailure (41)
        <Alarmtype> physicalViolation (9)
        <Polarity> (2)
        "
	::= { pm200frs02AlmclientHostLaneFaultEntry 3 }


pm200frs02AlmClientLossOfSyncPortn OBJECT-TYPE
	SYNTAX  EkiOnOff
	MAX-ACCESS read-only
	STATUS current
	DESCRIPTION
        "
        Client Frame Alignment Loss :This
        OID indicates the module is not
        aligned with the incoming Client
        signal <Help> Alarm indicating
         the module is not aligned with
        the incoming client signal <Condtype>
        CLIENT_LOSS_OF_SYNC <Probcause>
        receiveFailure (41) <Alarmtype>
        integrityViolation (7) <Polarity>
        (2)
        "
	::= { pm200frs02AlmclientHostLaneFaultEntry 2 }


--- *********************************************************
---     TABLE for the pm200frs02AlmlineNetworkLaneAlarmWarning1 articles
--- *********************************************************

pm200frs02AlmlineNetworkLaneAlarmWarning1Table OBJECT-TYPE
	SYNTAX  SEQUENCE OF Pm200frs02AlmlineNetworkLaneAlarmWarning1Entry
	MAX-ACCESS not-accessible
	STATUS current
	DESCRIPTION
        "
        List of pm200frs02AlmlineNetworkLaneAlarmWarning1
        Article
        "
	::= { pm200frs02AlmLineNurg 184 }


pm200frs02AlmlineNetworkLaneAlarmWarning1Entry OBJECT-TYPE
	SYNTAX Pm200frs02AlmlineNetworkLaneAlarmWarning1Entry
	MAX-ACCESS not-accessible
	STATUS current
	DESCRIPTION
        "
        Row definition for the pm200frs02AlmlineNetworkLaneAlarmWarning1
        table
        "
	INDEX   { pm200frs02AlmlineNetworkLaneAlarmWarning1Index }
	::= { pm200frs02AlmlineNetworkLaneAlarmWarning1Table 1 }


Pm200frs02AlmlineNetworkLaneAlarmWarning1Entry ::=
	SEQUENCE {
	pm200frs02AlmlineNetworkLaneAlarmWarning1Index
		INTEGER,
	pm200frs02AlmLineBiasHighAlarmPortn
		EkiOnOff,
	pm200frs02AlmLineBiasHighWarningPortn
		EkiOnOff,
	pm200frs02AlmLineBiasLowWarningPortn
		EkiOnOff,
	pm200frs02AlmLineBiasLowAlarmPortn
		EkiOnOff,
	pm200frs02AlmLineTxPowerHighAlarmPortn
		EkiOnOff,
	pm200frs02AlmLineTxPowerHighWarningPortn
		EkiOnOff,
	pm200frs02AlmLineTxPowerLowWarningPortn
		EkiOnOff,
	pm200frs02AlmLineTxPowerLowAlarmPortn
		EkiOnOff,
	pm200frs02AlmLineLaserTempHighAlarmPortn
		EkiOnOff,
	pm200frs02AlmLineLaserTempHighWarningPortn
		EkiOnOff,
	pm200frs02AlmLineLaserTempLowWarningPortn
		EkiOnOff,
	pm200frs02AlmLineLaserTempLowAlarmPortn
		EkiOnOff,
	pm200frs02AlmLineRxPowerHighAlarmPortn
		EkiOnOff,
	pm200frs02AlmLineRxPowerHighWarningPortn
		EkiOnOff,
	pm200frs02AlmLineRxPowerLowWarningPortn
		EkiOnOff,
	pm200frs02AlmLineRxPowerLowAlarmPortn
		EkiOnOff
	}


pm200frs02AlmlineNetworkLaneAlarmWarning1Index OBJECT-TYPE
	SYNTAX  INTEGER(0..128)
	MAX-ACCESS  read-only
	STATUS current
	DESCRIPTION
        "
        Index definition for the pm200frs02AlmlineNetworkLaneAlarmWarning1
        table
        "
	::= { pm200frs02AlmlineNetworkLaneAlarmWarning1Entry 1 }


pm200frs02AlmLineBiasHighAlarmPortn OBJECT-TYPE
	SYNTAX  EkiOnOff
	MAX-ACCESS read-only
	STATUS current
	DESCRIPTION
        "
        Line Trscv Tx Bias High Alarm
         :This OID indicates that the Trscv
        laser bias current is higher than
        the threshold value written in
         the Trscv EEPROM <Help> Alarm
         indicating that the Trscv laser
        bias current is higher than the
        threshold value written in the
         Trscv EEPROM <Condtype> LINE_BIAS_HIGH_ALARM
        <Probcause> transmitterFailure
         (56) <Alarmtype> equipmentAlarm
        (5) <Polarity> (2)
        "
	::= { pm200frs02AlmlineNetworkLaneAlarmWarning1Entry 17 }


pm200frs02AlmLineBiasHighWarningPortn OBJECT-TYPE
	SYNTAX  EkiOnOff
	MAX-ACCESS read-only
	STATUS current
	DESCRIPTION
        "
        Line Trscv Tx Bias High Warning
        :This OID indicates that the Trscv
        laser bias current is higher than
        the threshold value written in
         the Trscv EEPROM <Help> Warning
        indicating that the Trscv laser
        bias current is higher than the
        threshold value written in the
         Trscv EEPROM <Condtype> LINE_BIAS_HIGH_WARNING
        <Probcause> transmitterFailure
         (56) <Alarmtype> equipmentAlarm
        (5) <Polarity> (2)
        "
	::= { pm200frs02AlmlineNetworkLaneAlarmWarning1Entry 16 }


pm200frs02AlmLineBiasLowWarningPortn OBJECT-TYPE
	SYNTAX  EkiOnOff
	MAX-ACCESS read-only
	STATUS current
	DESCRIPTION
        "
        Line Trscv Tx Bias Low Warning
        :This OID indicates that the Trscv
        laser bias current is lower than
        the threshold value written in
         the Trscv EEPROM <Help> Warning
        indicating that the Trscv laser
        bias current is lower than the
         threshold value written in the
        Trscv EEPROM <Condtype> LINE_BIAS_LOW_WARNING
        <Probcause> transmitterFailure
         (56) <Alarmtype> equipmentAlarm
        (5) <Polarity> (2)
        "
	::= { pm200frs02AlmlineNetworkLaneAlarmWarning1Entry 15 }


pm200frs02AlmLineBiasLowAlarmPortn OBJECT-TYPE
	SYNTAX  EkiOnOff
	MAX-ACCESS read-only
	STATUS current
	DESCRIPTION
        "
        Line Trscv Tx Bias Low Alarm :This
        OID indicates that the Trscv laser
        bias current is lower than the
         threshold value written in the
        Trscv EEPROM <Help> Alarm indicating
        that the Trscv laser bias current
        is lower than the threshold value
        written in the Trscv EEPROM <Condtype>
        LINE_BIAS_LOW_ALARM <Probcause>
        transmitterFailure (56) <Alarmtype>
        equipmentAlarm (5) <Polarity> (2)
        "
	::= { pm200frs02AlmlineNetworkLaneAlarmWarning1Entry 14 }


pm200frs02AlmLineTxPowerHighAlarmPortn OBJECT-TYPE
	SYNTAX  EkiOnOff
	MAX-ACCESS read-only
	STATUS current
	DESCRIPTION
        "
        Line Trscv Tx Power High Alarm
        :This OID indicates that the Trscv
        output power is higher than the
        threshold value written in the
         Trscv EEPROM <Help> Alarm indicating
        that the Trscv output power is
         higher than the threshold value
        written in the Trscv EEPROM <Condtype>
        LINE_TX_POWER_HIGH_ALARM <Probcause>
        transmitterFailure (56) <Alarmtype>
        equipmentAlarm (5) <Polarity> (2)
        "
	::= { pm200frs02AlmlineNetworkLaneAlarmWarning1Entry 13 }


pm200frs02AlmLineTxPowerHighWarningPortn OBJECT-TYPE
	SYNTAX  EkiOnOff
	MAX-ACCESS read-only
	STATUS current
	DESCRIPTION
        "
        Line Trscv Tx Power High Warning
        :This OID indicates that the Trscv
        output power is higher than the
        threshold value written in the
         Trscv EEPROM <Help> Warning indicating
        that the Trscv output power is
         higher than the threshold value
        written in the Trscv EEPROM <Condtype>
        LINE_TX_POWER_HIGH_WARNING <Probcause>
        transmitterFailure (56) <Alarmtype>
        equipmentAlarm (5) <Polarity> (2)
        "
	::= { pm200frs02AlmlineNetworkLaneAlarmWarning1Entry 12 }


pm200frs02AlmLineTxPowerLowWarningPortn OBJECT-TYPE
	SYNTAX  EkiOnOff
	MAX-ACCESS read-only
	STATUS current
	DESCRIPTION
        "
        Line Trscv Tx Power Low Warning
        :This OID indicates that the Trscv
        output power is lower than the
         threshold value written in the
        Trscv EEPROM <Help> Warning indicating
        that the Trscv output power is
         lower than the threshold value
        written in the Trscv EEPROM <Condtype>
        LINE_TX_POWER_LOW_WARNING <Probcause>
        transmitterFailure (56) <Alarmtype>
        equipmentAlarm (5) <Polarity> (2)
        "
	::= { pm200frs02AlmlineNetworkLaneAlarmWarning1Entry 11 }


pm200frs02AlmLineTxPowerLowAlarmPortn OBJECT-TYPE
	SYNTAX  EkiOnOff
	MAX-ACCESS read-only
	STATUS current
	DESCRIPTION
        "
        Line Trscv Tx Power Low Alarm
         :This OID indicates that the Trscv
        output power is lower than the
         threshold value written in the
        Trscv EEPROM <Help> Alarm indicating
        that the Trscv output power is
         lower than the threshold value
        written in the Trscv EEPROM <Condtype>
        LINE_TX_POWER_LOW_ALARM <Probcause>
        transmitterFailure (56) <Alarmtype>
        equipmentAlarm (5) <Polarity> (2)
        "
	::= { pm200frs02AlmlineNetworkLaneAlarmWarning1Entry 10 }


pm200frs02AlmLineLaserTempHighAlarmPortn OBJECT-TYPE
	SYNTAX  EkiOnOff
	MAX-ACCESS read-only
	STATUS current
	DESCRIPTION
        "
        Line Trscv Tx Laser Temp High
         Alarm :This OID indicates that
        the Trscv Tx Laser Temperature
         is higher than the threshold value
        written in the Trscv EEPROM <Help>
        Alarm indicating that the Trscv
        Tx Laser Temperature is higher
         than the threshold value written
        in the Trscv EEPROM <Condtype>
         LINE_LASER_TEMP_HIGH_ALARM <Probcause>
        temperatureUnacceptable (51) <Alarmtype>
        equipmentAlarm (5) <Polarity> (2)
        "
	::= { pm200frs02AlmlineNetworkLaneAlarmWarning1Entry 9 }


pm200frs02AlmLineLaserTempHighWarningPortn OBJECT-TYPE
	SYNTAX  EkiOnOff
	MAX-ACCESS read-only
	STATUS current
	DESCRIPTION
        "
        Line Trscv Tx Laser Temp High
         Warning :This OID indicates that
        the Trscv Tx Laser Temperature
         is higher than the threshold value
        written in the Trscv EEPROM <Help>
        Warning indicating that the Trscv
        Tx Laser Temperature is higher
         than the threshold value written
        in the Trscv EEPROM <Condtype>
         LINE_LASER_TEMP_HIGH_WARNING <Probcause>
        temperatureUnacceptable (51) <Alarmtype>
        equipmentAlarm (5) <Polarity> (2)
        "
	::= { pm200frs02AlmlineNetworkLaneAlarmWarning1Entry 8 }


pm200frs02AlmLineLaserTempLowWarningPortn OBJECT-TYPE
	SYNTAX  EkiOnOff
	MAX-ACCESS read-only
	STATUS current
	DESCRIPTION
        "
        Line Trscv Tx Laser Temp Low Warning
        :This OID indicates that the Trscv
        Tx Laser Temperature is lower than
        the threshold value written in
         the Trscv EEPROM <Help> Warning
        indicating that the Trscv Tx Laser
        Temperature is lower than the threshold
        value written in the Trscv EEPROM
        <Condtype> LINE_LASER_TEMP_LOW_WARNING
        <Probcause> temperatureUnacceptable
        (51) <Alarmtype> equipmentAlarm
        (5) <Polarity> (2)
        "
	::= { pm200frs02AlmlineNetworkLaneAlarmWarning1Entry 7 }


pm200frs02AlmLineLaserTempLowAlarmPortn OBJECT-TYPE
	SYNTAX  EkiOnOff
	MAX-ACCESS read-only
	STATUS current
	DESCRIPTION
        "
        Line Trscv Tx Laser Temp Low Alarm
        :This OID indicates that the Trscv
        Tx Laser Temperature is lower than
        the threshold value written in
         the Trscv EEPROM <Help> Alarm
         indicating that the Trscv Tx Laser
        Temperature is lower than the threshold
        value written in the Trscv EEPROM
        <Condtype> LINE_LASER_TEMP_LOW_ALARM
        <Probcause> temperatureUnacceptable
        (51) <Alarmtype> equipmentAlarm
        (5) <Polarity> (2)
        "
	::= { pm200frs02AlmlineNetworkLaneAlarmWarning1Entry 6 }


pm200frs02AlmLineRxPowerHighAlarmPortn OBJECT-TYPE
	SYNTAX  EkiOnOff
	MAX-ACCESS read-only
	STATUS current
	DESCRIPTION
        "
        Line Trscv Rx Power High Alarm
        :This OID indicates that the Trscv
        input power is higher than the
         threshold value written in the
        Trscv EEPROM <Help> Alarm indicating
        that the Trscv input power is higher
        than the threshold value written
        in the Trscv EEPROM <Condtype>
         LINE_RX_POWER_HIGH_ALARM <Probcause>
        receiveFailure (41) <Alarmtype>
        equipmentAlarm (5) <Polarity> (2)
        "
	::= { pm200frs02AlmlineNetworkLaneAlarmWarning1Entry 5 }


pm200frs02AlmLineRxPowerHighWarningPortn OBJECT-TYPE
	SYNTAX  EkiOnOff
	MAX-ACCESS read-only
	STATUS current
	DESCRIPTION
        "
        Line Trscv Rx Power High Warning
        :This OID indicates that the Trscv
        input power is higher than the
         threshold value written in the
        Trscv EEPROM <Help> Warning indicating
        that the Trscv input power is higher
        than the threshold value written
        in the Trscv EEPROM <Condtype>
         LINE_RX_POWER_HIGH_WARNING <Probcause>
        receiveFailure (41) <Alarmtype>
        equipmentAlarm (5) <Polarity> (2)
        "
	::= { pm200frs02AlmlineNetworkLaneAlarmWarning1Entry 4 }


pm200frs02AlmLineRxPowerLowWarningPortn OBJECT-TYPE
	SYNTAX  EkiOnOff
	MAX-ACCESS read-only
	STATUS current
	DESCRIPTION
        "
        Line Trscv Rx Power Low Warning
        :This OID indicates that the Trscv
        input power is lower than the threshold
        value written in the Trscv EEPROM
        <Help> Warning indicating that
         the Trscv input power is lower
        than the threshold value written
        in the Trscv EEPROM <Condtype>
         LINE_RX_POWER_LOW_WARNING <Probcause>
        receiveFailure (41) <Alarmtype>
        equipmentAlarm (5) <Polarity> (2)
        "
	::= { pm200frs02AlmlineNetworkLaneAlarmWarning1Entry 3 }


pm200frs02AlmLineRxPowerLowAlarmPortn OBJECT-TYPE
	SYNTAX  EkiOnOff
	MAX-ACCESS read-only
	STATUS current
	DESCRIPTION
        "
        Line Trscv Rx Power Low Alarm
         :This OID indicates that the Trscv
        input power is lower than the threshold
        value written in the Trscv EEPROM
        <Help> Alarm indicating that the
        Trscv input power is lower than
        the threshold value written in
         the Trscv EEPROM <Condtype> LINE_RX_POWER_LOW_ALARM
        <Probcause> receiveFailure (41)
        <Alarmtype> equipmentAlarm (5)
         <Polarity> (2)
        "
	::= { pm200frs02AlmlineNetworkLaneAlarmWarning1Entry 2 }


--- *********************************************************
---     TABLE for the pm200frs02AlmlineNetworkLaneAlarmWarning2 articles
--- *********************************************************

pm200frs02AlmlineNetworkLaneAlarmWarning2Table OBJECT-TYPE
	SYNTAX  SEQUENCE OF Pm200frs02AlmlineNetworkLaneAlarmWarning2Entry
	MAX-ACCESS not-accessible
	STATUS current
	DESCRIPTION
        "
        List of pm200frs02AlmlineNetworkLaneAlarmWarning2
        Article
        "
	::= { pm200frs02AlmLineNurg 188 }


pm200frs02AlmlineNetworkLaneAlarmWarning2Entry OBJECT-TYPE
	SYNTAX Pm200frs02AlmlineNetworkLaneAlarmWarning2Entry
	MAX-ACCESS not-accessible
	STATUS current
	DESCRIPTION
        "
        Row definition for the pm200frs02AlmlineNetworkLaneAlarmWarning2
        table
        "
	INDEX   { pm200frs02AlmlineNetworkLaneAlarmWarning2Index }
	::= { pm200frs02AlmlineNetworkLaneAlarmWarning2Table 1 }


Pm200frs02AlmlineNetworkLaneAlarmWarning2Entry ::=
	SEQUENCE {
	pm200frs02AlmlineNetworkLaneAlarmWarning2Index
		INTEGER,
	pm200frs02AlmRxLaserBiasHighAlarmPortn
		EkiOnOff,
	pm200frs02AlmRxLaserBiasHighWarningPortn
		EkiOnOff,
	pm200frs02AlmRxLaserBiasLowWarningPortn
		EkiOnOff,
	pm200frs02AlmRxLaserBiasLowAlarmPortn
		EkiOnOff,
	pm200frs02AlmRxLaserOutputHighAlarmPortn
		EkiOnOff,
	pm200frs02AlmRxLaserOutputHighWarningPortn
		EkiOnOff,
	pm200frs02AlmRxLaserOutputLowWarningPortn
		EkiOnOff,
	pm200frs02AlmRxLaserOutputLowAlarmPortn
		EkiOnOff,
	pm200frs02AlmRxLaserTempHighAlarmPortn
		EkiOnOff,
	pm200frs02AlmRxLaserTempHighWarningPortn
		EkiOnOff,
	pm200frs02AlmRxLaserTempLowWarningPortn
		EkiOnOff,
	pm200frs02AlmRxLaserTempLowAlarmPortn
		EkiOnOff,
	pm200frs02AlmTxModulatorBiasHighAlarmPortn
		EkiOnOff,
	pm200frs02AlmTxModulatorBiasHighWarningPortn
		EkiOnOff,
	pm200frs02AlmTxModulatorBiasLowWarningPortn
		EkiOnOff,
	pm200frs02AlmTxModulatorBiasLowAlarmPortn
		EkiOnOff
	}


pm200frs02AlmlineNetworkLaneAlarmWarning2Index OBJECT-TYPE
	SYNTAX  INTEGER(0..128)
	MAX-ACCESS  read-only
	STATUS current
	DESCRIPTION
        "
        Index definition for the pm200frs02AlmlineNetworkLaneAlarmWarning2
        table
        "
	::= { pm200frs02AlmlineNetworkLaneAlarmWarning2Entry 1 }


pm200frs02AlmRxLaserBiasHighAlarmPortn OBJECT-TYPE
	SYNTAX  EkiOnOff
	MAX-ACCESS read-only
	STATUS current
	DESCRIPTION
        "
        Line Trscv Rx Bias High Alarm
         :This OID indicates that the Trscv
        Rx laser bias current is higher
        than the threshold value written
        in the Trscv EEPROM <Help> Alarm
        indicating that the Trscv Rx laser
        bias current is higher than the
        threshold value written in the
         Trscv EEPROM <Condtype> RX_LASER_BIAS_HIGH_ALARM
        <Probcause> receiveFailure (41)
        <Alarmtype> equipmentAlarm (5)
         <Polarity> (2)
        "
	::= { pm200frs02AlmlineNetworkLaneAlarmWarning2Entry 17 }


pm200frs02AlmRxLaserBiasHighWarningPortn OBJECT-TYPE
	SYNTAX  EkiOnOff
	MAX-ACCESS read-only
	STATUS current
	DESCRIPTION
        "
        Line Trscv Rx Bias High Warning
        :This OID indicates that the Trscv
        Rx laser bias current is higher
        than the threshold value written
        in the Trscv EEPROM <Help> Warning
        indicating that the Trscv Rx laser
        bias current is higher than the
        threshold value written in the
         Trscv EEPROM <Condtype> RX_LASER_BIAS_HIGH_WARNING
        <Probcause> receiveFailure (41)
        <Alarmtype> equipmentAlarm (5)
         <Polarity> (2)
        "
	::= { pm200frs02AlmlineNetworkLaneAlarmWarning2Entry 16 }


pm200frs02AlmRxLaserBiasLowWarningPortn OBJECT-TYPE
	SYNTAX  EkiOnOff
	MAX-ACCESS read-only
	STATUS current
	DESCRIPTION
        "
        Line Trscv Rx Bias Low Warning
        :This OID indicates that the Trscv
        Rx laser bias current is lower
         than the threshold value written
        in the Trscv EEPROM <Help> Warning
        indicating that the Trscv Rx laser
        bias current is lower than the
         threshold value written in the
        Trscv EEPROM <Condtype> RX_LASER_BIAS_LOW_WARNING
        <Probcause> receiveFailure (41)
        <Alarmtype> equipmentAlarm (5)
         <Polarity> (2)
        "
	::= { pm200frs02AlmlineNetworkLaneAlarmWarning2Entry 15 }


pm200frs02AlmRxLaserBiasLowAlarmPortn OBJECT-TYPE
	SYNTAX  EkiOnOff
	MAX-ACCESS read-only
	STATUS current
	DESCRIPTION
        "
        Line Trscv Rx Bias Low Alarm :This
        OID indicates that the Trscv Rx
        laser bias current is lower than
        the threshold value written in
         the Trscv EEPROM <Help> Alarm
         indicating that the Trscv Rx laser
        bias current is lower than the
         threshold value written in the
        Trscv EEPROM <Condtype> RX_LASER_BIAS_LOW_ALARM
        <Probcause> receiveFailure (41)
        <Alarmtype> equipmentAlarm (5)
         <Polarity> (2)
        "
	::= { pm200frs02AlmlineNetworkLaneAlarmWarning2Entry 14 }


pm200frs02AlmRxLaserOutputHighAlarmPortn OBJECT-TYPE
	SYNTAX  EkiOnOff
	MAX-ACCESS read-only
	STATUS current
	DESCRIPTION
        "
        Line Trscv Rx Output Power High
        Alarm :This OID indicates that
         the Trscv Rx output power is higher
        than the threshold value written
        in the Trscv EEPROM <Help> Alarm
        indicating that the Trscv Rx output
        power is higher than the threshold
        value written in the Trscv EEPROM
        <Condtype> RX_LASER_OUTPUT_HIGH_ALARM
        <Probcause> receiveFailure (41)
        <Alarmtype> equipmentAlarm (5)
         <Polarity> (2)
        "
	::= { pm200frs02AlmlineNetworkLaneAlarmWarning2Entry 13 }


pm200frs02AlmRxLaserOutputHighWarningPortn OBJECT-TYPE
	SYNTAX  EkiOnOff
	MAX-ACCESS read-only
	STATUS current
	DESCRIPTION
        "
        Line Trscv Rx Output Power High
        Warning :This OID indicates that
        the Trscv Rx output power is higher
        than the threshold value written
        in the Trscv EEPROM <Help> Warning
        indicating that the Trscv Rx output
        power is higher than the threshold
        value written in the Trscv EEPROM
        <Condtype> RX_LASER_OUTPUT_HIGH_WARNING
        <Probcause> receiveFailure (41)
        <Alarmtype> equipmentAlarm (5)
         <Polarity> (2)
        "
	::= { pm200frs02AlmlineNetworkLaneAlarmWarning2Entry 12 }


pm200frs02AlmRxLaserOutputLowWarningPortn OBJECT-TYPE
	SYNTAX  EkiOnOff
	MAX-ACCESS read-only
	STATUS current
	DESCRIPTION
        "
        Line Trscv Rx Output Power Low
        Warning :This OID indicates that
        the Trscv Rx output power is lower
        than the threshold value written
        in the Trscv EEPROM <Help> Warning
        indicating that the Trscv Rx output
        power is lower than the threshold
        value written in the Trscv EEPROM
        <Condtype> RX_LASER_OUTPUT_LOW_WARNING
        <Probcause> receiveFailure (41)
        <Alarmtype> equipmentAlarm (5)
         <Polarity> (2)
        "
	::= { pm200frs02AlmlineNetworkLaneAlarmWarning2Entry 11 }


pm200frs02AlmRxLaserOutputLowAlarmPortn OBJECT-TYPE
	SYNTAX  EkiOnOff
	MAX-ACCESS read-only
	STATUS current
	DESCRIPTION
        "
        Line Trscv Rx Output Power Low
        Alarm :This OID indicates that
         the Trscv Rx output power is lower
        than the threshold value written
        in the Trscv EEPROM <Help> Alarm
        indicating that the Trscv Rx output
        power is lower than the threshold
        value written in the Trscv EEPROM
        <Condtype> RX_LASER_OUTPUT_LOW_ALARM
        <Probcause> receiveFailure (41)
        <Alarmtype> equipmentAlarm (5)
         <Polarity> (2)
        "
	::= { pm200frs02AlmlineNetworkLaneAlarmWarning2Entry 10 }


pm200frs02AlmRxLaserTempHighAlarmPortn OBJECT-TYPE
	SYNTAX  EkiOnOff
	MAX-ACCESS read-only
	STATUS current
	DESCRIPTION
        "
        Line Trscv Rx Laser Temp High
         Alarm :This OID indicates that
        the Trscv Rx Laser Temperature
         is higher than the threshold value
        written in the Trscv EEPROM <Help>
        Alarm indicating that the Trscv
        Rx Laser Temperature is higher
         than the threshold value written
        in the Trscv EEPROM <Condtype>
         RX_LASER_TEMP_HIGH_ALARM <Probcause>
        temperatureUnacceptable (51) <Alarmtype>
        equipmentAlarm (5) <Polarity> (2)
        "
	::= { pm200frs02AlmlineNetworkLaneAlarmWarning2Entry 9 }


pm200frs02AlmRxLaserTempHighWarningPortn OBJECT-TYPE
	SYNTAX  EkiOnOff
	MAX-ACCESS read-only
	STATUS current
	DESCRIPTION
        "
        Line Trscv Rx Laser Temp High
         Warning :This OID indicates that
        the Trscv Rx Laser Temperature
         is higher than the threshold value
        written in the Trscv EEPROM <Help>
        Warning indicating that the Trscv
        Rx Laser Temperature is higher
         than the threshold value written
        in the Trscv EEPROM <Condtype>
         RX_LASER_TEMP_HIGH_WARNING <Probcause>
        temperatureUnacceptable (51) <Alarmtype>
        equipmentAlarm (5) <Polarity> (2)
        "
	::= { pm200frs02AlmlineNetworkLaneAlarmWarning2Entry 8 }


pm200frs02AlmRxLaserTempLowWarningPortn OBJECT-TYPE
	SYNTAX  EkiOnOff
	MAX-ACCESS read-only
	STATUS current
	DESCRIPTION
        "
        Line Trscv Rx Laser Temp Low Warning
        :This OID indicates that the Trscv
        Rx Laser Temperature is lower than
        the threshold value written in
         the Trscv EEPROM <Help> Warning
        indicating that the Trscv Rx Laser
        Temperature is lower than the threshold
        value written in the Trscv EEPROM
        <Condtype> RX_LASER_TEMP_LOW_WARNING
        <Probcause> temperatureUnacceptable
        (51) <Alarmtype> equipmentAlarm
        (5) <Polarity> (2)
        "
	::= { pm200frs02AlmlineNetworkLaneAlarmWarning2Entry 7 }


pm200frs02AlmRxLaserTempLowAlarmPortn OBJECT-TYPE
	SYNTAX  EkiOnOff
	MAX-ACCESS read-only
	STATUS current
	DESCRIPTION
        "
        Line Trscv Rx Laser Temp Low Alarm
        :This OID indicates that the Trscv
        Rx Laser Temperature is lower than
        the threshold value written in
         the Trscv EEPROM <Help> Alarm
         indicating that the Trscv Rx Laser
        Temperature is lower than the threshold
        value written in the Trscv EEPROM
        <Condtype> RX_LASER_TEMP_LOW_ALARM
        <Probcause> temperatureUnacceptable
        (51) <Alarmtype> equipmentAlarm
        (5) <Polarity> (2)
        "
	::= { pm200frs02AlmlineNetworkLaneAlarmWarning2Entry 6 }


pm200frs02AlmTxModulatorBiasHighAlarmPortn OBJECT-TYPE
	SYNTAX  EkiOnOff
	MAX-ACCESS read-only
	STATUS current
	DESCRIPTION
        "
        Line Trscv Tx Modulator Bias High
        Alarm :This OID indicates that
         the Trscv Tx modulator bias current
        is higher than the threshold value
        written in the Trscv EEPROM <Help>
        Alarm indicating that the Trscv
        Tx modulator bias current is higher
        than the threshold value written
        in the Trscv EEPROM <Condtype>
         TX_MODULATOR_BIAS_HIGH_ALARM <Probcause>
        transmitterFailure (56) <Alarmtype>
        equipmentAlarm (5) <Polarity> (2)
        "
	::= { pm200frs02AlmlineNetworkLaneAlarmWarning2Entry 5 }


pm200frs02AlmTxModulatorBiasHighWarningPortn OBJECT-TYPE
	SYNTAX  EkiOnOff
	MAX-ACCESS read-only
	STATUS current
	DESCRIPTION
        "
        Line Trscv Tx Modulator Bias High
        Warning :This OID indicates that
        the Trscv Tx modulator bias current
        is higher than the threshold value
        written in the Trscv EEPROM <Help>
        Warning indicating that the Trscv
        Tx modulator bias current is higher
        than the threshold value written
        in the Trscv EEPROM <Condtype>
         TX_MODULATOR_BIAS_HIGH_WARNING
        <Probcause> transmitterFailure
         (56) <Alarmtype> equipmentAlarm
        (5) <Polarity> (2)
        "
	::= { pm200frs02AlmlineNetworkLaneAlarmWarning2Entry 4 }


pm200frs02AlmTxModulatorBiasLowWarningPortn OBJECT-TYPE
	SYNTAX  EkiOnOff
	MAX-ACCESS read-only
	STATUS current
	DESCRIPTION
        "
        Line Trscv Tx Modulator Bias Low
        Warning :This OID indicates that
        the Trscv Tx modulator bias current
        is lower than the threshold value
        written in the Trscv EEPROM <Help>
        Warning indicating that the Trscv
        Tx modulator bias current is lower
        than the threshold value written
        in the Trscv EEPROM <Condtype>
         TX_MODULATOR_BIAS_LOW_WARNING
         <Probcause> transmitterFailure
        (56) <Alarmtype> equipmentAlarm
        (5) <Polarity> (2)
        "
	::= { pm200frs02AlmlineNetworkLaneAlarmWarning2Entry 3 }


pm200frs02AlmTxModulatorBiasLowAlarmPortn OBJECT-TYPE
	SYNTAX  EkiOnOff
	MAX-ACCESS read-only
	STATUS current
	DESCRIPTION
        "
        Line Trscv Tx Modulator Bias Low
        Alarm :This OID indicates that
         the Trscv Tx modulator bias current
        is lower than the threshold value
        written in the Trscv EEPROM <Help>
        Alarm indicating that the Trscv
        Tx modulator bias current is lower
        than the threshold value written
        in the Trscv EEPROM <Condtype>
         TX_MODULATOR_BIAS_LOW_ALARM <Probcause>
        transmitterFailure (56) <Alarmtype>
        equipmentAlarm (5) <Polarity> (2)
        "
	::= { pm200frs02AlmlineNetworkLaneAlarmWarning2Entry 2 }


--- *********************************************************
---     TABLE for the pm200frs02AlmlineHostLaneFault articles
--- *********************************************************

pm200frs02AlmlineHostLaneFaultTable OBJECT-TYPE
	SYNTAX  SEQUENCE OF Pm200frs02AlmlineHostLaneFaultEntry
	MAX-ACCESS not-accessible
	STATUS current
	DESCRIPTION
        "
        List of pm200frs02AlmlineHostLaneFault
        Article
        "
	::= { pm200frs02AlmLineUrg 196 }


pm200frs02AlmlineHostLaneFaultEntry OBJECT-TYPE
	SYNTAX Pm200frs02AlmlineHostLaneFaultEntry
	MAX-ACCESS not-accessible
	STATUS current
	DESCRIPTION
        "
        Row definition for the pm200frs02AlmlineHostLaneFault
        table
        "
	INDEX   { pm200frs02AlmlineHostLaneFaultIndex }
	::= { pm200frs02AlmlineHostLaneFaultTable 1 }


Pm200frs02AlmlineHostLaneFaultEntry ::=
	SEQUENCE {
	pm200frs02AlmlineHostLaneFaultIndex
		INTEGER,
	pm200frs02AlmLineLaneTxFifoErrorPortn
		EkiOnOff,
	pm200frs02AlmLineTxHostLolPortn
		EkiOnOff,
	pm200frs02AlmLineSmIaeDetectedPortn
		EkiOnOff,
	pm200frs02AlmLineSmIaeInsertedPortn
		EkiOnOff,
	pm200frs02AlmLineSmBdiDetectedPortn
		EkiOnOff,
	pm200frs02AlmLineSmBdiInsertedPortn
		EkiOnOff,
	pm200frs02AlmLineLossOfFramePortn
		EkiOnOff,
	pm200frs02AlmLineInputLossOfSignalPortn
		EkiOnOff
	}


pm200frs02AlmlineHostLaneFaultIndex OBJECT-TYPE
	SYNTAX  INTEGER(0..128)
	MAX-ACCESS  read-only
	STATUS current
	DESCRIPTION
        "
        Index definition for the pm200frs02AlmlineHostLaneFault
        table
        "
	::= { pm200frs02AlmlineHostLaneFaultEntry 1 }


pm200frs02AlmLineLaneTxFifoErrorPortn OBJECT-TYPE
	SYNTAX  EkiOnOff
	MAX-ACCESS read-only
	STATUS current
	DESCRIPTION
        "
        Line Host Lane Tx FIFO Error :This
        OID indicates a Tx FIFO Error on
        the Line Trscv Host Lane <Help>
        Alarm indicating a Tx FIFO Error
        on the Line Trscv Host Lane <Condtype>
        LINE_LANE_TX_FIFO_ERROR <Probcause>
        receiverFailure (42) <Alarmtype>
        equipmentAlarm (5) <Polarity> (2)
        "
	::= { pm200frs02AlmlineHostLaneFaultEntry 11 }


pm200frs02AlmLineTxHostLolPortn OBJECT-TYPE
	SYNTAX  EkiOnOff
	MAX-ACCESS read-only
	STATUS current
	DESCRIPTION
        "
        Line Host Lane Tx Loss Of Lock
        :This OID indicates a Tx Loss of
        Lock on the Line Trscv Host Lane
        <Help> Alarm indicating a Tx Loss
        of Lock on the Line Trscv Host
         Lane <Condtype> LINE_TX_HOST_LOL
        <Probcause> receiverFailure (42)
        <Alarmtype> equipmentAlarm (5)
         <Polarity> (2)
        "
	::= { pm200frs02AlmlineHostLaneFaultEntry 10 }


pm200frs02AlmLineSmIaeDetectedPortn OBJECT-TYPE
	SYNTAX  EkiOnOff
	MAX-ACCESS read-only
	STATUS current
	DESCRIPTION
        "
        Line SM IAE Detected :This OID
        indicates a SM Incoming Alignment
        Error is detected on the incoming
        Line signal <Help> Alarm indicating
        a SM Incoming Alignment Error is
        detected on the incoming Line signal
        <Condtype> LINE_SM_IAE_DETECTED
        <Probcause> receiveFailure (41)
        <Alarmtype> integrityViolation
         (7) <Polarity> (2)
        "
	::= { pm200frs02AlmlineHostLaneFaultEntry 7 }


pm200frs02AlmLineSmIaeInsertedPortn OBJECT-TYPE
	SYNTAX  EkiOnOff
	MAX-ACCESS read-only
	STATUS current
	DESCRIPTION
        "
        Line SM IAE Inserted :This OID
        indicates a SM Incoming Alignment
        Error is inserted on the outgoing
        Line signal <Help> Status indicating
        a SM Incoming Alignment Error is
        inserted on the outgoing Line signal
        <Condtype> LINE_SM_IAE_INSERTED
        <Probcause> informationalStatus(1000)
        <Alarmtype> other (1) <Polarity>
        (2)
        "
	::= { pm200frs02AlmlineHostLaneFaultEntry 6 }


pm200frs02AlmLineSmBdiDetectedPortn OBJECT-TYPE
	SYNTAX  EkiOnOff
	MAX-ACCESS read-only
	STATUS current
	DESCRIPTION
        "
        Line SM BDI Detected :This OID
        indicates a SM Backward Defect
         Indication is detected on the
         incoming Line signal <Help> Alarm
        indicating a SM Backward Defect
        Indication is detected on the incoming
        Line signal <Condtype> LINE_SM_BDI_DETECTED
        <Probcause> receiveFailure (41)
        <Alarmtype> integrityViolation
         (7) <Polarity> (2)
        "
	::= { pm200frs02AlmlineHostLaneFaultEntry 5 }


pm200frs02AlmLineSmBdiInsertedPortn OBJECT-TYPE
	SYNTAX  EkiOnOff
	MAX-ACCESS read-only
	STATUS current
	DESCRIPTION
        "
        Line SM BDI Inserted :This OID
        indicates a SM Backward Defect
         Indication is inserted on the
         outgoing Line signal <Help> Status
        indicating a SM Backward Defect
        Indication is inserted on the outgoing
        Line signal <Condtype> LINE_SM_BDI_INSERTED
        <Probcause> informationalStatus(1000)
        <Alarmtype> other (1) <Polarity>
        (2)
        "
	::= { pm200frs02AlmlineHostLaneFaultEntry 4 }


pm200frs02AlmLineLossOfFramePortn OBJECT-TYPE
	SYNTAX  EkiOnOff
	MAX-ACCESS read-only
	STATUS current
	DESCRIPTION
        "
        Line Loss Of Frame :This OID indicates
        the module is not aligned with
         the incoming Line signal <Help>
        Alarm indicating the module is
         not aligned with the incoming
         Line signal <Condtype> LINE_LOSS_OF_FRAME
        <Probcause> receiveFailure (41)
        <Alarmtype> integrityViolation
         (7) <Polarity> (2)
        "
	::= { pm200frs02AlmlineHostLaneFaultEntry 3 }


pm200frs02AlmLineInputLossOfSignalPortn OBJECT-TYPE
	SYNTAX  EkiOnOff
	MAX-ACCESS read-only
	STATUS current
	DESCRIPTION
        "
        Line Input Loss Of Signal :This
        OID indicates a Loss of Signal
         is detected on the Line Trscv
         <Help> Alarm indicating a Loss
        of Signal is detected on the Line
        Trscv <Condtype> LINE_INPUT_LOSS_OF_SIGNAL
        <Probcause> receiveFailure (41)
        <Alarmtype> physicalViolation (9)
        <Polarity> (2)
        "
	::= { pm200frs02AlmlineHostLaneFaultEntry 2 }


--- *****************************************************
---     LEAF for the clientQsfpAlarmDdm article
--- *****************************************************
pm200frs02AlmclientQsfpAlarmDdm OBJECT IDENTIFIER ::= { pm200frs02AlmOtherUrg 337 }




pm200frs02AlmTrscv2TempHighAla1 OBJECT-TYPE
	  SYNTAX EkiOnOff
	  MAX-ACCESS read-only
	  STATUS current
	  DESCRIPTION
        "
        Q2 Trscv Temp High Alarm :This
        OID indicates that the Trscv temperature
        of port is higher than the threshold
        value written in the Trscv EEPROM
        <Help> Alarm indicating that the
        Trscv temperature of port is higher
        than the threshold value written
        in the Trscv EEPROM <Condtype>
         TRSCV2_TEMP_HIGH_ALA_1 <Probcause>
        temperatureUnacceptable (51) <Alarmtype>
        "
	  ::= { pm200frs02AlmclientQsfpAlarmDdm 8 }



pm200frs02AlmTrscv2TempLowAla1 OBJECT-TYPE
	  SYNTAX EkiOnOff
	  MAX-ACCESS read-only
	  STATUS current
	  DESCRIPTION
        "
        Q2 Trscv Temp Low Alarm :This
         OID indicates that the Trscv temperature
        of port is lower than the threshold
        value written in the Trscv EEPROM
        <Help> Alarm indicating that the
        Trscv temperature of port is lower
        than the threshold value written
        in the Trscv EEPROM <Condtype>
         TRSCV2_TEMP_LOW_ALA_1 <Probcause>
        temperatureUnacceptable (51) <Alarmtype>
        "
	  ::= { pm200frs02AlmclientQsfpAlarmDdm 7 }



pm200frs02AlmTrscv2VccHighAla1 OBJECT-TYPE
	  SYNTAX EkiOnOff
	  MAX-ACCESS read-only
	  STATUS current
	  DESCRIPTION
        "
        Q2 Trscv Power Supply High Alarm
        :This OID indicates that the Trscv
        power supply of port is higher
         than the threshold value written
        in the Trscv EEPROM <Help> Alarm
        indicating that the Trscv power
        supply of port is higher than the
        threshold value written in the
         Trscv EEPROM <Condtype> TRSCV2_VCC_HIGH_ALA_1
        <Probcause> powerProblem (36) <Alarmtype>
        "
	  ::= { pm200frs02AlmclientQsfpAlarmDdm 6 }



pm200frs02AlmTrscv2VccLowAla1 OBJECT-TYPE
	  SYNTAX EkiOnOff
	  MAX-ACCESS read-only
	  STATUS current
	  DESCRIPTION
        "
        Q2 Trscv Power Supply Low Alarm
        :This OID indicates that the Trscv
        power supply of port is lower than
        the threshold value written in
         the Trscv EEPROM <Help> Alarm
         indicating that the Trscv power
        supply of port is lower than the
        threshold value written in the
         Trscv EEPROM <Condtype> TRSCV2_VCC_LOW_ALA_1
        <Probcause> powerProblem (36) <Alarmtype>
        "
	  ::= { pm200frs02AlmclientQsfpAlarmDdm 5 }



pm200frs02AlmTrscv1TempHighAla OBJECT-TYPE
	  SYNTAX EkiOnOff
	  MAX-ACCESS read-only
	  STATUS current
	  DESCRIPTION
        "
        Q1 Trscv Temp High Alarm :This
        OID indicates that the Trscv temperature
        of port is higher than the threshold
        value written in the Trscv EEPROM
        <Help> Alarm indicating that the
        Trscv temperature of port is higher
        than the threshold value written
        in the Trscv EEPROM <Condtype>
         TRSCV1_TEMP_HIGH_ALA <Probcause>
        temperatureUnacceptable (51) <Alarmtype>
        "
	  ::= { pm200frs02AlmclientQsfpAlarmDdm 4 }



pm200frs02AlmTrscv1TempLowAla1 OBJECT-TYPE
	  SYNTAX EkiOnOff
	  MAX-ACCESS read-only
	  STATUS current
	  DESCRIPTION
        "
        Q1 Trscv Temp Low Alarm :This
         OID indicates that the Trscv temperature
        of port is lower than the threshold
        value written in the Trscv EEPROM
        <Help> Alarm indicating that the
        Trscv temperature of port is lower
        than the threshold value written
        in the Trscv EEPROM <Condtype>
         TRSCV1_TEMP_LOW_ALA_1 <Probcause>
        temperatureUnacceptable (51) <Alarmtype>
        "
	  ::= { pm200frs02AlmclientQsfpAlarmDdm 3 }



pm200frs02AlmTrscv1VccHighAla1 OBJECT-TYPE
	  SYNTAX EkiOnOff
	  MAX-ACCESS read-only
	  STATUS current
	  DESCRIPTION
        "
        Q1 Trscv Power Supply High Alarm
        :This OID indicates that the Trscv
        power supply of port is higher
         than the threshold value written
        in the Trscv EEPROM <Help> Alarm
        indicating that the Trscv power
        supply of port is higher than the
        threshold value written in the
         Trscv EEPROM <Condtype> TRSCV1_VCC_HIGH_ALA_1
        <Probcause> powerProblem (36) <Alarmtype>
        "
	  ::= { pm200frs02AlmclientQsfpAlarmDdm 2 }



pm200frs02AlmTrscv1VccLowAla1 OBJECT-TYPE
	  SYNTAX EkiOnOff
	  MAX-ACCESS read-only
	  STATUS current
	  DESCRIPTION
        "
        Q1 Trscv Power Supply Low Alarm
        :This OID indicates that the Trscv
        power supply of port is lower than
        the threshold value written in
         the Trscv EEPROM <Help> Alarm
         indicating that the Trscv power
        supply of port is lower than the
        threshold value written in the
         Trscv EEPROM <Condtype> TRSCV1_VCC_LOW_ALA_1
        <Probcause> powerProblem (36) <Alarmtype>
        "
	  ::= { pm200frs02AlmclientQsfpAlarmDdm 1 }



--- *****************************************************
---     LEAF for the clientQsfpWarnDdm article
--- *****************************************************
pm200frs02AlmclientQsfpWarnDdm OBJECT IDENTIFIER ::= { pm200frs02AlmOtherNurg 338 }




pm200frs02AlmTrscv2TempHighWng1 OBJECT-TYPE
	  SYNTAX EkiOnOff
	  MAX-ACCESS read-only
	  STATUS current
	  DESCRIPTION
        "
        Q2 Trscv Temp High Warning :This
        OID indicates that the Trscv temperature
        is higher than the threshold value
        written in the Trscv EEPROM <Help>
        Warning indicating that the Trscv
        temperature is higher than the
         threshold value written in the
        Trscv EEPROM <Condtype> TRSCV2_TEMP_HIGH_WNG_1
        <Probcause> temperatureUnacceptable
        (51) <Alarmtype>
        "
	  ::= { pm200frs02AlmclientQsfpWarnDdm 8 }



pm200frs02AlmTrscv2TempLowWng1 OBJECT-TYPE
	  SYNTAX EkiOnOff
	  MAX-ACCESS read-only
	  STATUS current
	  DESCRIPTION
        "
        Q2 Trscv Temp Low Warning :This
        OID indicates that the Trscv temperature
        is lower than the threshold value
        written in the Trscv EEPROM <Help>
        Warning indicating that the Trscv
        temperature is lower than the threshold
        value written in the Trscv EEPROM
        <Condtype> TRSCV2_TEMP_LOW_WNG_1
        <Probcause> temperatureUnacceptable
        (51) <Alarmtype>
        "
	  ::= { pm200frs02AlmclientQsfpWarnDdm 7 }



pm200frs02AlmTrscv2VccHighWng1 OBJECT-TYPE
	  SYNTAX EkiOnOff
	  MAX-ACCESS read-only
	  STATUS current
	  DESCRIPTION
        "
        Q2 Trscv Power Supply High Warning
        :This OID indicates that the Trscv
        power supply is higher than the
        threshold value written in the
         Trscv EEPROM <Help> Warning indicating
        that the Trscv power supply is
         higher than the threshold value
        written in the Trscv EEPROM <Condtype>
        TRSCV2_VCC_HIGH_WNG_1 <Probcause>
        powerProblem (36) <Alarmtype>
        "
	  ::= { pm200frs02AlmclientQsfpWarnDdm 6 }



pm200frs02AlmTrscv2VccLowWng1 OBJECT-TYPE
	  SYNTAX EkiOnOff
	  MAX-ACCESS read-only
	  STATUS current
	  DESCRIPTION
        "
        Q2 Trscv Power Supply Low Warning
        :This OID indicates that the Trscv
        power supply is lower than the
         threshold value written in the
        Trscv EEPROM <Help> Warning indicating
        that the Trscv power supply is
         lower than the threshold value
        written in the Trscv EEPROM <Condtype>
        TRSCV2_VCC_LOW_WNG_1 <Probcause>
        powerProblem (36) <Alarmtype>
        "
	  ::= { pm200frs02AlmclientQsfpWarnDdm 5 }



pm200frs02AlmTrscv1TempHighWng1 OBJECT-TYPE
	  SYNTAX EkiOnOff
	  MAX-ACCESS read-only
	  STATUS current
	  DESCRIPTION
        "
        Q1 Trscv Temp High Warning :This
        OID indicates that the Trscv temperature
        is higher than the threshold value
        written in the Trscv EEPROM <Help>
        Warning indicating that the Trscv
        temperature is higher than the
         threshold value written in the
        Trscv EEPROM <Condtype> TRSCV1_TEMP_HIGH_WNG_1
        <Probcause> temperatureUnacceptable
        (51) <Alarmtype>
        "
	  ::= { pm200frs02AlmclientQsfpWarnDdm 4 }



pm200frs02AlmTrscv1TempLowWng1 OBJECT-TYPE
	  SYNTAX EkiOnOff
	  MAX-ACCESS read-only
	  STATUS current
	  DESCRIPTION
        "
        Q1 Trscv Temp Low Warning :This
        OID indicates that the Trscv temperature
        is lower than the threshold value
        written in the Trscv EEPROM <Help>
        Warning indicating that the Trscv
        temperature is lower than the threshold
        value written in the Trscv EEPROM
        <Condtype> TRSCV1_TEMP_LOW_WNG_1
        <Probcause> temperatureUnacceptable
        (51) <Alarmtype>
        "
	  ::= { pm200frs02AlmclientQsfpWarnDdm 3 }



pm200frs02AlmTrscv1VccHighWng1 OBJECT-TYPE
	  SYNTAX EkiOnOff
	  MAX-ACCESS read-only
	  STATUS current
	  DESCRIPTION
        "
        Q1 Trscv Power Supply High Warning
        :This OID indicates that the Trscv
        power supply is higher than the
        threshold value written in the
         Trscv EEPROM <Help> Warning indicating
        that the Trscv power supply is
         higher than the threshold value
        written in the Trscv EEPROM <Condtype>
        TRSCV1_VCC_HIGH_WNG_1 <Probcause>
        powerProblem (36) <Alarmtype>
        "
	  ::= { pm200frs02AlmclientQsfpWarnDdm 2 }



pm200frs02AlmTrscv1VccLowWng1 OBJECT-TYPE
	  SYNTAX EkiOnOff
	  MAX-ACCESS read-only
	  STATUS current
	  DESCRIPTION
        "
        Q1 Trscv Power Supply Low Warning
        :This OID indicates that the Trscv
        power supply is lower than the
         threshold value written in the
        Trscv EEPROM <Help> Warning indicating
        that the Trscv power supply is
         lower than the threshold value
        written in the Trscv EEPROM <Condtype>
        TRSCV1_VCC_LOW_WNG_1 <Probcause>
        powerProblem (36) <Alarmtype>
        "
	  ::= { pm200frs02AlmclientQsfpWarnDdm 1 }








--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pm200frs02CtrlconfMgnt1 OBJECT IDENTIFIER ::= { pm200frs02CtrlOther 1 }




pm200frs02CtrlConf2Clear1 OBJECT-TYPE
	  SYNTAX EkiOnOff
	  MAX-ACCESS read-write
	  STATUS current
	  DESCRIPTION
        "
        Clear Configuration Tables :This
        OID clears the configuration tables
        from configuration2 in the flash.
         <Help>  This control restores
         the default configuration of the
        module
        "
	  ::= { pm200frs02CtrlconfMgnt1 14 }



pm200frs02CtrlConf2Flash1 OBJECT-TYPE
	  SYNTAX EkiOnOff
	  MAX-ACCESS read-write
	  STATUS current
	  DESCRIPTION
        "
        Write Configuration Tables :This
        OID saves the current configuration
        of the PM as configuration2 in
         the flash.  <Help>  This control
        saves the customer configuration
        on the module
        "
	  ::= { pm200frs02CtrlconfMgnt1 10 }



pm200frs02CtrlConf2Load1 OBJECT-TYPE
	  SYNTAX EkiOnOff
	  MAX-ACCESS read-write
	  STATUS current
	  DESCRIPTION
        "
        Load Configuration Tables Set
         Nb 2 :When set this OID enables
        loading from flash configuration2
        into the PM.
        "
	  ::= { pm200frs02CtrlconfMgnt1 2 }



pm200frs02CtrlConf1Load1 OBJECT-TYPE
	  SYNTAX EkiOnOff
	  MAX-ACCESS read-write
	  STATUS current
	  DESCRIPTION
        "
        Load Configuration Tables Set
         Nb 1 :When set this OID enables
        loading from flash configuration1
        into the PM.
        "
	  ::= { pm200frs02CtrlconfMgnt1 1 }



--- *****************************************************
---     LEAF for the synth4 article
--- *****************************************************
pm200frs02Ctrlsynth4 OBJECT IDENTIFIER ::= { pm200frs02CtrlOther 4 }




pm200frs02CtrlCorrelatOff OBJECT-TYPE
	  SYNTAX EkiOnOff
	  MAX-ACCESS read-write
	  STATUS current
	  DESCRIPTION
        "
        Disable Alarm Correlation :This
        OID disables the alarm correlation
        in the PM.
        "
	  ::= { pm200frs02Ctrlsynth4 2 }



pm200frs02CtrlCorrelatOn OBJECT-TYPE
	  SYNTAX EkiOnOff
	  MAX-ACCESS read-write
	  STATUS current
	  DESCRIPTION
        "
        Enable Alarm Correlation :This
        OID enables the alarm correlation
        in the PM.
        "
	  ::= { pm200frs02Ctrlsynth4 1 }



--- *****************************************************
---     LEAF for the swMgnt article
--- *****************************************************
pm200frs02CtrlswMgnt OBJECT IDENTIFIER ::= { pm200frs02CtrlOther 5 }




pm200frs02CtrlLoadSwBank2 OBJECT-TYPE
	  SYNTAX EkiOnOff
	  MAX-ACCESS read-write
	  STATUS current
	  DESCRIPTION
        "
        Set Software Nb 2 As Active :This
        OID, when set, loads the SW from
        bank2 into the PM. It must be followed
        by a reset.  <Help>  This controls
        selects the second SW bank as the
        active bank for the next module
        reset
        "
	  ::= { pm200frs02CtrlswMgnt 6 }



pm200frs02CtrlLoadSwBank1 OBJECT-TYPE
	  SYNTAX EkiOnOff
	  MAX-ACCESS read-write
	  STATUS current
	  DESCRIPTION
        "
        Set Software Nb 1 As Active :This
        OID, when set, loads the SW from
        bank1 into the PM. It must be followed
        by a reset.  <Help>  This controls
        selects the first SW bank as the
        active bank for the next module
        reset
        "
	  ::= { pm200frs02CtrlswMgnt 5 }



pm200frs02CtrlWarmReset OBJECT-TYPE
	  SYNTAX EkiOnOff
	  MAX-ACCESS read-write
	  STATUS current
	  DESCRIPTION
        "
        PM Warm Reset :This OID, when
         set, causes a warm reset of the
        PM. This reset is not traffic affecting,
        and the configuration of PM remains
        unchanged.  <Help>  This control
        initiates a warm reset of the module.
        "
	  ::= { pm200frs02CtrlswMgnt 3 }



pm200frs02CtrlColdReset OBJECT-TYPE
	  SYNTAX EkiOnOff
	  MAX-ACCESS read-write
	  STATUS current
	  DESCRIPTION
        "
        PM Cold Reset :This OID, when
         set, causes a cold reset of the
        PM. This reset is traffic affecting,
        and the configuration of PM is
         reloaded on start-up.  <Help>
          This control initiates a cold
        reset of the module.
        "
	  ::= { pm200frs02CtrlswMgnt 2 }



--- *****************************************************
---     LEAF for the gwMgnt article
--- *****************************************************
pm200frs02CtrlgwMgnt OBJECT IDENTIFIER ::= { pm200frs02CtrlOther 6 }




pm200frs02CtrlLoadGwBank4 OBJECT-TYPE
	  SYNTAX EkiOnOff
	  MAX-ACCESS read-write
	  STATUS current
	  DESCRIPTION
        "
        Set Gateware Nb 4 As Active :This
        OID, when set, loads the GW from
        bank4 (Flash) into the PM. It is
        followed by an automatic gateware
        cold reset.
        "
	  ::= { pm200frs02CtrlgwMgnt 8 }



pm200frs02CtrlLoadGwBank3 OBJECT-TYPE
	  SYNTAX EkiOnOff
	  MAX-ACCESS read-write
	  STATUS current
	  DESCRIPTION
        "
        Set Gateware Nb 3 As Active :This
        OID, when set, loads the GW from
        bank3 (Flash) into the PM. It is
        followed by an automatic gateware
        cold reset.  <Help>  This controls
        initiates a cold reset of the module
        and select the third GW bank as
        the active bank
        "
	  ::= { pm200frs02CtrlgwMgnt 7 }



pm200frs02CtrlLoadGwBank2 OBJECT-TYPE
	  SYNTAX EkiOnOff
	  MAX-ACCESS read-write
	  STATUS current
	  DESCRIPTION
        "
        Set Gateware Nb 2 As Active :This
        OID, when set, loads the GW from
        bank2 (Flash) into the PM. It is
        followed by an automatic gateware
        cold reset.
        "
	  ::= { pm200frs02CtrlgwMgnt 6 }



pm200frs02CtrlLoadGwBank1 OBJECT-TYPE
	  SYNTAX EkiOnOff
	  MAX-ACCESS read-write
	  STATUS current
	  DESCRIPTION
        "
        Set Gateware Nb 1 As Active :This
        OID, when set, loads the GW from
        bank1 (Flash) into the PM. It is
        followed by an automatic gateware
        cold reset.  <Help>  This controls
        initiates a cold reset of the module
        and select the first GW bank as
        the active bank
        "
	  ::= { pm200frs02CtrlgwMgnt 5 }



pm200frs02CtrlCurrentGwReset OBJECT-TYPE
	  SYNTAX EkiOnOff
	  MAX-ACCESS read-write
	  STATUS current
	  DESCRIPTION
        "
        Active Gateware Reset :This OID,
        when set, resets the active gateware.
        It is traffic affecting.
        "
	  ::= { pm200frs02CtrlgwMgnt 1 }



--- *********************************************************
---     TABLE for the pm200frs02CtrlaccessLoop articles
--- *********************************************************

pm200frs02CtrlaccessLoopTable OBJECT-TYPE
	SYNTAX  SEQUENCE OF Pm200frs02CtrlaccessLoopEntry
	MAX-ACCESS not-accessible
	STATUS current
	DESCRIPTION
        "
        List of pm200frs02CtrlaccessLoop
        Article
        "
	::= { pm200frs02CtrlClient 16 }


pm200frs02CtrlaccessLoopEntry OBJECT-TYPE
	SYNTAX Pm200frs02CtrlaccessLoopEntry
	MAX-ACCESS not-accessible
	STATUS current
	DESCRIPTION
        "
        Row definition for the pm200frs02CtrlaccessLoop
        table
        "
	INDEX   { pm200frs02CtrlaccessLoopIndex }
	::= { pm200frs02CtrlaccessLoopTable 1 }


Pm200frs02CtrlaccessLoopEntry ::=
	SEQUENCE {
	pm200frs02CtrlaccessLoopIndex
		INTEGER,
	pm200frs02CtrlaccessLoopPortn
		EkiState
	}


pm200frs02CtrlaccessLoopIndex OBJECT-TYPE
	SYNTAX  INTEGER(0..128)
	MAX-ACCESS  read-only
	STATUS current
	DESCRIPTION
        "
        Index definition for the pm200frs02CtrlaccessLoop
        table
        "
	::= { pm200frs02CtrlaccessLoopEntry 1 }


pm200frs02CtrlaccessLoopPortn OBJECT-TYPE
	SYNTAX  EkiState
	MAX-ACCESS read-write
	STATUS current
	DESCRIPTION
        "
        Client Facility Loopback :This
        OID, when set at '1' puts the client
        port in loopback, looping the received
        10 Gb/s signal on the transmit
         10 Gb/s output.  <Help> This control
        enables the Out Loopback on the
        client port, looping the client
        input signal on the client output
        "
	::= { pm200frs02CtrlaccessLoopEntry 2 }


--- *********************************************************
---     TABLE for the pm200frs02CtrlclientLoopToLine articles
--- *********************************************************

pm200frs02CtrlclientLoopToLineTable OBJECT-TYPE
	SYNTAX  SEQUENCE OF Pm200frs02CtrlclientLoopToLineEntry
	MAX-ACCESS not-accessible
	STATUS current
	DESCRIPTION
        "
        List of pm200frs02CtrlclientLoopToLine
        Article
        "
	::= { pm200frs02CtrlClient 17 }


pm200frs02CtrlclientLoopToLineEntry OBJECT-TYPE
	SYNTAX Pm200frs02CtrlclientLoopToLineEntry
	MAX-ACCESS not-accessible
	STATUS current
	DESCRIPTION
        "
        Row definition for the pm200frs02CtrlclientLoopToLine
        table
        "
	INDEX   { pm200frs02CtrlclientLoopToLineIndex }
	::= { pm200frs02CtrlclientLoopToLineTable 1 }


Pm200frs02CtrlclientLoopToLineEntry ::=
	SEQUENCE {
	pm200frs02CtrlclientLoopToLineIndex
		INTEGER,
	pm200frs02CtrlclientLoopToLinePortn
		EkiState
	}


pm200frs02CtrlclientLoopToLineIndex OBJECT-TYPE
	SYNTAX  INTEGER(0..128)
	MAX-ACCESS  read-only
	STATUS current
	DESCRIPTION
        "
        Index definition for the pm200frs02CtrlclientLoopToLine
        table
        "
	::= { pm200frs02CtrlclientLoopToLineEntry 1 }


pm200frs02CtrlclientLoopToLinePortn OBJECT-TYPE
	SYNTAX  EkiState
	MAX-ACCESS read-write
	STATUS current
	DESCRIPTION
        "
        Client Terminal Loopback :This
        OID, when set, puts the client
         port in loop back, looping the
        10 Gb/s output signal on the 10
        Gb/s input.<Help> This control
         enables the In Loopback on the
        client port, looping the client
        output signal on the client input
        "
	::= { pm200frs02CtrlclientLoopToLineEntry 2 }


--- *********************************************************
---     TABLE for the pm200frs02CtrlcsfUpIns articles
--- *********************************************************

pm200frs02CtrlcsfUpInsTable OBJECT-TYPE
	SYNTAX  SEQUENCE OF Pm200frs02CtrlcsfUpInsEntry
	MAX-ACCESS not-accessible
	STATUS current
	DESCRIPTION
        "
        List of pm200frs02CtrlcsfUpIns
        Article
        "
	::= { pm200frs02CtrlClient 21 }


pm200frs02CtrlcsfUpInsEntry OBJECT-TYPE
	SYNTAX Pm200frs02CtrlcsfUpInsEntry
	MAX-ACCESS not-accessible
	STATUS current
	DESCRIPTION
        "
        Row definition for the pm200frs02CtrlcsfUpIns
        table
        "
	INDEX   { pm200frs02CtrlcsfUpInsIndex }
	::= { pm200frs02CtrlcsfUpInsTable 1 }


Pm200frs02CtrlcsfUpInsEntry ::=
	SEQUENCE {
	pm200frs02CtrlcsfUpInsIndex
		INTEGER,
	pm200frs02CtrlcsfUpInsPortn
		EkiState
	}


pm200frs02CtrlcsfUpInsIndex OBJECT-TYPE
	SYNTAX  INTEGER(0..128)
	MAX-ACCESS  read-only
	STATUS current
	DESCRIPTION
        "
        Index definition for the pm200frs02CtrlcsfUpIns
        table
        "
	::= { pm200frs02CtrlcsfUpInsEntry 1 }


pm200frs02CtrlcsfUpInsPortn OBJECT-TYPE
	SYNTAX  EkiState
	MAX-ACCESS read-write
	STATUS current
	DESCRIPTION
        "
        Client Signal Fail Insertion :This
        OID, when set, inserts  a client
        signal fail in the upstream client
        Port.  <Help>  This control inserts
        a Client Signal Fail for the client
        port
        "
	::= { pm200frs02CtrlcsfUpInsEntry 2 }


--- *********************************************************
---     TABLE for the pm200frs02CtrlcaisDwIns articles
--- *********************************************************

pm200frs02CtrlcaisDwInsTable OBJECT-TYPE
	SYNTAX  SEQUENCE OF Pm200frs02CtrlcaisDwInsEntry
	MAX-ACCESS not-accessible
	STATUS current
	DESCRIPTION
        "
        List of pm200frs02CtrlcaisDwIns
        Article
        "
	::= { pm200frs02CtrlClient 22 }


pm200frs02CtrlcaisDwInsEntry OBJECT-TYPE
	SYNTAX Pm200frs02CtrlcaisDwInsEntry
	MAX-ACCESS not-accessible
	STATUS current
	DESCRIPTION
        "
        Row definition for the pm200frs02CtrlcaisDwIns
        table
        "
	INDEX   { pm200frs02CtrlcaisDwInsIndex }
	::= { pm200frs02CtrlcaisDwInsTable 1 }


Pm200frs02CtrlcaisDwInsEntry ::=
	SEQUENCE {
	pm200frs02CtrlcaisDwInsIndex
		INTEGER,
	pm200frs02CtrlcaisDwInsPortn
		EkiState
	}


pm200frs02CtrlcaisDwInsIndex OBJECT-TYPE
	SYNTAX  INTEGER(0..128)
	MAX-ACCESS  read-only
	STATUS current
	DESCRIPTION
        "
        Index definition for the pm200frs02CtrlcaisDwIns
        table
        "
	::= { pm200frs02CtrlcaisDwInsEntry 1 }


pm200frs02CtrlcaisDwInsPortn OBJECT-TYPE
	SYNTAX  EkiState
	MAX-ACCESS read-write
	STATUS current
	DESCRIPTION
        "
        Client AIS Insertion :This OID,
        when set, inserts a client AIS
         on the downstream client Port.
         <Help>  This control inserts a
        Client AIS for the client port
        "
	::= { pm200frs02CtrlcaisDwInsEntry 2 }


--- *********************************************************
---     TABLE for the pm200frs02CtrlcommAccessLoop articles
--- *********************************************************

pm200frs02CtrlcommAccessLoopTable OBJECT-TYPE
	SYNTAX  SEQUENCE OF Pm200frs02CtrlcommAccessLoopEntry
	MAX-ACCESS not-accessible
	STATUS current
	DESCRIPTION
        "
        List of pm200frs02CtrlcommAccessLoop
        Article
        "
	::= { pm200frs02CtrlLine 64 }


pm200frs02CtrlcommAccessLoopEntry OBJECT-TYPE
	SYNTAX Pm200frs02CtrlcommAccessLoopEntry
	MAX-ACCESS not-accessible
	STATUS current
	DESCRIPTION
        "
        Row definition for the pm200frs02CtrlcommAccessLoop
        table
        "
	INDEX   { pm200frs02CtrlcommAccessLoopIndex }
	::= { pm200frs02CtrlcommAccessLoopTable 1 }


Pm200frs02CtrlcommAccessLoopEntry ::=
	SEQUENCE {
	pm200frs02CtrlcommAccessLoopIndex
		INTEGER,
	pm200frs02CtrlcommAccessLoopPortn
		EkiState
	}


pm200frs02CtrlcommAccessLoopIndex OBJECT-TYPE
	SYNTAX  INTEGER(0..128)
	MAX-ACCESS  read-only
	STATUS current
	DESCRIPTION
        "
        Index definition for the pm200frs02CtrlcommAccessLoop
        table
        "
	::= { pm200frs02CtrlcommAccessLoopEntry 1 }


pm200frs02CtrlcommAccessLoopPortn OBJECT-TYPE
	SYNTAX  EkiState
	MAX-ACCESS read-write
	STATUS current
	DESCRIPTION
        "
        Line Terminal Loopback :This OID,
        when set, puts the module in common
        access loop back, looping the 200
        Gb/s output signal on the 200 Gb/s
        input.<Help> This control enables
        the In Loopback on the line port,
        looping the 200 Gb/s output signal
        on the 200 Gb/s input
        "
	::= { pm200frs02CtrlcommAccessLoopEntry 2 }


--- *********************************************************
---     TABLE for the pm200frs02CtrllineLoop articles
--- *********************************************************

pm200frs02CtrllineLoopTable OBJECT-TYPE
	SYNTAX  SEQUENCE OF Pm200frs02CtrllineLoopEntry
	MAX-ACCESS not-accessible
	STATUS current
	DESCRIPTION
        "
        List of pm200frs02CtrllineLoop
        Article
        "
	::= { pm200frs02CtrlLine 66 }


pm200frs02CtrllineLoopEntry OBJECT-TYPE
	SYNTAX Pm200frs02CtrllineLoopEntry
	MAX-ACCESS not-accessible
	STATUS current
	DESCRIPTION
        "
        Row definition for the pm200frs02CtrllineLoop
        table
        "
	INDEX   { pm200frs02CtrllineLoopIndex }
	::= { pm200frs02CtrllineLoopTable 1 }


Pm200frs02CtrllineLoopEntry ::=
	SEQUENCE {
	pm200frs02CtrllineLoopIndex
		INTEGER,
	pm200frs02CtrllineLoopPortn
		EkiState
	}


pm200frs02CtrllineLoopIndex OBJECT-TYPE
	SYNTAX  INTEGER(0..128)
	MAX-ACCESS  read-only
	STATUS current
	DESCRIPTION
        "
        Index definition for the pm200frs02CtrllineLoop
        table
        "
	::= { pm200frs02CtrllineLoopEntry 1 }


pm200frs02CtrllineLoopPortn OBJECT-TYPE
	SYNTAX  EkiState
	MAX-ACCESS read-write
	STATUS current
	DESCRIPTION
        "
        Line Facility Loopback :This OID,
        when set at '1' puts the module
        in line loopback mode, looping
         the received 200 Gb/s signal on
        the transmit 200 Gb/s output. The
        Upstream part of the module is
         timed on the 200 Gb/s recovered
        clock in that case.<Help> This
         control enables the Out Loopback
        on the line port, looping the 200
        Gb/s input signal on the 200 Gb/s
        output
        "
	::= { pm200frs02CtrllineLoopEntry 2 }


--- *********************************************************
---     TABLE for the pm200frs02CtrlfecDisable articles
--- *********************************************************

pm200frs02CtrlfecDisableTable OBJECT-TYPE
	SYNTAX  SEQUENCE OF Pm200frs02CtrlfecDisableEntry
	MAX-ACCESS not-accessible
	STATUS current
	DESCRIPTION
        "
        List of pm200frs02CtrlfecDisable
        Article
        "
	::= { pm200frs02CtrlLine 69 }


pm200frs02CtrlfecDisableEntry OBJECT-TYPE
	SYNTAX Pm200frs02CtrlfecDisableEntry
	MAX-ACCESS not-accessible
	STATUS current
	DESCRIPTION
        "
        Row definition for the pm200frs02CtrlfecDisable
        table
        "
	INDEX   { pm200frs02CtrlfecDisableIndex }
	::= { pm200frs02CtrlfecDisableTable 1 }


Pm200frs02CtrlfecDisableEntry ::=
	SEQUENCE {
	pm200frs02CtrlfecDisableIndex
		INTEGER,
	pm200frs02CtrlfecDisablePortn
		EkiState
	}


pm200frs02CtrlfecDisableIndex OBJECT-TYPE
	SYNTAX  INTEGER(0..128)
	MAX-ACCESS  read-only
	STATUS current
	DESCRIPTION
        "
        Index definition for the pm200frs02CtrlfecDisable
        table
        "
	::= { pm200frs02CtrlfecDisableEntry 1 }


pm200frs02CtrlfecDisablePortn OBJECT-TYPE
	SYNTAX  EkiState
	MAX-ACCESS read-write
	STATUS current
	DESCRIPTION
        "
        Forward Error Correction Inhibition
        :This OID, when set, inhibits the
        Forward Error Correction feature
        on the line input  <Help>  This
        control enables/disables the Forward
        Error Correction on the line interface
        "
	::= { pm200frs02CtrlfecDisableEntry 2 }


--- *****************************************************
---     LEAF for the ledTest article
--- *****************************************************
pm200frs02CtrlledTest OBJECT IDENTIFIER ::= { pm200frs02CtrlOther 192 }




pm200frs02CtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { pm200frs02CtrlledTest 3 }



pm200frs02CtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { pm200frs02CtrlledTest 2 }



pm200frs02CtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { pm200frs02CtrlledTest 1 }



--- *****************************************************
---     LEAF for the initSwitchMarvell article
--- *****************************************************
pm200frs02CtrlinitSwitchMarvell OBJECT IDENTIFIER ::= { pm200frs02CtrlOther 201 }




pm200frs02CtrlInitSwitchMarvell OBJECT-TYPE
	  SYNTAX EkiOnOff
	  MAX-ACCESS read-write
	  STATUS current
	  DESCRIPTION
        "
        Switch Initialization :This OID
        operates an initialization of the
        switch managed through the module
         <Help>  This control activates
        an initialization of the switch
        managed through the module
        "
	  ::= { pm200frs02CtrlinitSwitchMarvell 1 }



--- *********************************************************
---     TABLE for the pm200frs02CtrlmsaLineLoop articles
--- *********************************************************

pm200frs02CtrlmsaLineLoopTable OBJECT-TYPE
	SYNTAX  SEQUENCE OF Pm200frs02CtrlmsaLineLoopEntry
	MAX-ACCESS not-accessible
	STATUS current
	DESCRIPTION
        "
        List of pm200frs02CtrlmsaLineLoop
        Article
        "
	::= { pm200frs02CtrlLine 209 }


pm200frs02CtrlmsaLineLoopEntry OBJECT-TYPE
	SYNTAX Pm200frs02CtrlmsaLineLoopEntry
	MAX-ACCESS not-accessible
	STATUS current
	DESCRIPTION
        "
        Row definition for the pm200frs02CtrlmsaLineLoop
        table
        "
	INDEX   { pm200frs02CtrlmsaLineLoopIndex }
	::= { pm200frs02CtrlmsaLineLoopTable 1 }


Pm200frs02CtrlmsaLineLoopEntry ::=
	SEQUENCE {
	pm200frs02CtrlmsaLineLoopIndex
		INTEGER,
	pm200frs02CtrlmsaLineLoopPortn
		EkiState
	}


pm200frs02CtrlmsaLineLoopIndex OBJECT-TYPE
	SYNTAX  INTEGER(0..128)
	MAX-ACCESS  read-only
	STATUS current
	DESCRIPTION
        "
        Index definition for the pm200frs02CtrlmsaLineLoop
        table
        "
	::= { pm200frs02CtrlmsaLineLoopEntry 1 }


pm200frs02CtrlmsaLineLoopPortn OBJECT-TYPE
	SYNTAX  EkiState
	MAX-ACCESS read-write
	STATUS current
	DESCRIPTION
        "
        MSA Line Loop :This OID operates
        a line loopback on the MSA Line
         <Help>  This control defines the
        line loop back of the line transceiver
        "
	::= { pm200frs02CtrlmsaLineLoopEntry 2 }


--- *********************************************************
---     TABLE for the pm200frs02CtrlmsaTxReset articles
--- *********************************************************

pm200frs02CtrlmsaTxResetTable OBJECT-TYPE
	SYNTAX  SEQUENCE OF Pm200frs02CtrlmsaTxResetEntry
	MAX-ACCESS not-accessible
	STATUS current
	DESCRIPTION
        "
        List of pm200frs02CtrlmsaTxReset
        Article
        "
	::= { pm200frs02CtrlLine 210 }


pm200frs02CtrlmsaTxResetEntry OBJECT-TYPE
	SYNTAX Pm200frs02CtrlmsaTxResetEntry
	MAX-ACCESS not-accessible
	STATUS current
	DESCRIPTION
        "
        Row definition for the pm200frs02CtrlmsaTxReset
        table
        "
	INDEX   { pm200frs02CtrlmsaTxResetIndex }
	::= { pm200frs02CtrlmsaTxResetTable 1 }


Pm200frs02CtrlmsaTxResetEntry ::=
	SEQUENCE {
	pm200frs02CtrlmsaTxResetIndex
		INTEGER,
	pm200frs02CtrlmsaTxResetPortn
		EkiState
	}


pm200frs02CtrlmsaTxResetIndex OBJECT-TYPE
	SYNTAX  INTEGER(0..128)
	MAX-ACCESS  read-only
	STATUS current
	DESCRIPTION
        "
        Index definition for the pm200frs02CtrlmsaTxReset
        table
        "
	::= { pm200frs02CtrlmsaTxResetEntry 1 }


pm200frs02CtrlmsaTxResetPortn OBJECT-TYPE
	SYNTAX  EkiState
	MAX-ACCESS read-write
	STATUS current
	DESCRIPTION
        "
        Line MSA TX Reset :This OID resets
        the TX portion of the MSA line
         module  <Help > This control
         initiates a reset of the transmitting
        side
        "
	::= { pm200frs02CtrlmsaTxResetEntry 2 }


--- *********************************************************
---     TABLE for the pm200frs02CtrlmsaRxReset articles
--- *********************************************************

pm200frs02CtrlmsaRxResetTable OBJECT-TYPE
	SYNTAX  SEQUENCE OF Pm200frs02CtrlmsaRxResetEntry
	MAX-ACCESS not-accessible
	STATUS current
	DESCRIPTION
        "
        List of pm200frs02CtrlmsaRxReset
        Article
        "
	::= { pm200frs02CtrlLine 211 }


pm200frs02CtrlmsaRxResetEntry OBJECT-TYPE
	SYNTAX Pm200frs02CtrlmsaRxResetEntry
	MAX-ACCESS not-accessible
	STATUS current
	DESCRIPTION
        "
        Row definition for the pm200frs02CtrlmsaRxReset
        table
        "
	INDEX   { pm200frs02CtrlmsaRxResetIndex }
	::= { pm200frs02CtrlmsaRxResetTable 1 }


Pm200frs02CtrlmsaRxResetEntry ::=
	SEQUENCE {
	pm200frs02CtrlmsaRxResetIndex
		INTEGER,
	pm200frs02CtrlmsaRxResetPortn
		EkiState
	}


pm200frs02CtrlmsaRxResetIndex OBJECT-TYPE
	SYNTAX  INTEGER(0..128)
	MAX-ACCESS  read-only
	STATUS current
	DESCRIPTION
        "
        Index definition for the pm200frs02CtrlmsaRxReset
        table
        "
	::= { pm200frs02CtrlmsaRxResetEntry 1 }


pm200frs02CtrlmsaRxResetPortn OBJECT-TYPE
	SYNTAX  EkiState
	MAX-ACCESS read-write
	STATUS current
	DESCRIPTION
        "
        Line MSA RX Reset :This OID resets
        the RX portion of the MSA line
         module  <Help > This control
         initiates a reset of the receiving
        side
        "
	::= { pm200frs02CtrlmsaRxResetEntry 2 }


--- *********************************************************
---     TABLE for the pm200frs02CtrlmsaShutdown articles
--- *********************************************************

pm200frs02CtrlmsaShutdownTable OBJECT-TYPE
	SYNTAX  SEQUENCE OF Pm200frs02CtrlmsaShutdownEntry
	MAX-ACCESS not-accessible
	STATUS current
	DESCRIPTION
        "
        List of pm200frs02CtrlmsaShutdown
        Article
        "
	::= { pm200frs02CtrlLine 212 }


pm200frs02CtrlmsaShutdownEntry OBJECT-TYPE
	SYNTAX Pm200frs02CtrlmsaShutdownEntry
	MAX-ACCESS not-accessible
	STATUS current
	DESCRIPTION
        "
        Row definition for the pm200frs02CtrlmsaShutdown
        table
        "
	INDEX   { pm200frs02CtrlmsaShutdownIndex }
	::= { pm200frs02CtrlmsaShutdownTable 1 }


Pm200frs02CtrlmsaShutdownEntry ::=
	SEQUENCE {
	pm200frs02CtrlmsaShutdownIndex
		INTEGER,
	pm200frs02CtrlmsaShutdownPortn
		EkiState
	}


pm200frs02CtrlmsaShutdownIndex OBJECT-TYPE
	SYNTAX  INTEGER(0..128)
	MAX-ACCESS  read-only
	STATUS current
	DESCRIPTION
        "
        Index definition for the pm200frs02CtrlmsaShutdown
        table
        "
	::= { pm200frs02CtrlmsaShutdownEntry 1 }


pm200frs02CtrlmsaShutdownPortn OBJECT-TYPE
	SYNTAX  EkiState
	MAX-ACCESS read-write
	STATUS current
	DESCRIPTION
        "
        Line MSA Shutdown :This OID enters
        a process to shutdown the MSA line
        module  <Help > This control  initiates
        a shutdown of the module
        "
	::= { pm200frs02CtrlmsaShutdownEntry 2 }


--- *****************************************************
---     LEAF for the resetCount article
--- *****************************************************
pm200frs02CtrlresetCount OBJECT IDENTIFIER ::= { pm200frs02CtrlOther 259 }




pm200frs02CtrlResetcount OBJECT-TYPE
	  SYNTAX EkiOnOff
	  MAX-ACCESS read-write
	  STATUS current
	  DESCRIPTION
        "
        Module Count Global Reset :This
        OID resets all the errors counters
        on the module  <Help > This control
         initiates a reset of the errors
        counters on the module
        "
	  ::= { pm200frs02CtrlresetCount 1 }



--- *****************************************************
---     LEAF for the resetRmon article
--- *****************************************************
pm200frs02CtrlresetRmon OBJECT IDENTIFIER ::= { pm200frs02CtrlOther 260 }




pm200frs02CtrlResetrmon OBJECT-TYPE
	  SYNTAX EkiOnOff
	  MAX-ACCESS read-write
	  STATUS current
	  DESCRIPTION
        "
        Module Rmon Global Reset :This
        OID resets all the Rmon counters
        on the module  <Help > This control
         initiates a reset of the Rmon
         counters on the module
        "
	  ::= { pm200frs02CtrlresetRmon 1 }



--- *****************************************************
---     LEAF for the resetMeasurements article
--- *****************************************************
pm200frs02CtrlresetMeasurements OBJECT IDENTIFIER ::= { pm200frs02CtrlOther 261 }




pm200frs02CtrlResetmeasurements OBJECT-TYPE
	  SYNTAX EkiOnOff
	  MAX-ACCESS read-write
	  STATUS current
	  DESCRIPTION
        "
        Management Meas Global Reset :This
        OID resets some measurements on
        the management  <Help > This control
         initiates a reset of some measurements
        on the management
        "
	  ::= { pm200frs02CtrlresetMeasurements 1 }



--- *********************************************************
---     TABLE for the pm200frs02CtrlclientResetAllCount articles
--- *********************************************************

pm200frs02CtrlclientResetAllCountTable OBJECT-TYPE
	SYNTAX  SEQUENCE OF Pm200frs02CtrlclientResetAllCountEntry
	MAX-ACCESS not-accessible
	STATUS current
	DESCRIPTION
        "
        List of pm200frs02CtrlclientResetAllCount
        Article
        "
	::= { pm200frs02CtrlClient 262 }


pm200frs02CtrlclientResetAllCountEntry OBJECT-TYPE
	SYNTAX Pm200frs02CtrlclientResetAllCountEntry
	MAX-ACCESS not-accessible
	STATUS current
	DESCRIPTION
        "
        Row definition for the pm200frs02CtrlclientResetAllCount
        table
        "
	INDEX   { pm200frs02CtrlclientResetAllCountIndex }
	::= { pm200frs02CtrlclientResetAllCountTable 1 }


Pm200frs02CtrlclientResetAllCountEntry ::=
	SEQUENCE {
	pm200frs02CtrlclientResetAllCountIndex
		INTEGER,
	pm200frs02CtrlclientResetAllCountsPortn
		EkiState
	}


pm200frs02CtrlclientResetAllCountIndex OBJECT-TYPE
	SYNTAX  INTEGER(0..128)
	MAX-ACCESS  read-only
	STATUS current
	DESCRIPTION
        "
        Index definition for the pm200frs02CtrlclientResetAllCount
        table
        "
	::= { pm200frs02CtrlclientResetAllCountEntry 1 }


pm200frs02CtrlclientResetAllCountsPortn OBJECT-TYPE
	SYNTAX  EkiState
	MAX-ACCESS read-write
	STATUS current
	DESCRIPTION
        "
        Client Counters Reset :This OID
        resets every counter on the client
        port  <Help>   This control operates
        a reset on the statistics current
        ,previous and history client port
        counters
        "
	::= { pm200frs02CtrlclientResetAllCountEntry 2 }


--- *********************************************************
---     TABLE for the pm200frs02CtrllineResetAllCount articles
--- *********************************************************

pm200frs02CtrllineResetAllCountTable OBJECT-TYPE
	SYNTAX  SEQUENCE OF Pm200frs02CtrllineResetAllCountEntry
	MAX-ACCESS not-accessible
	STATUS current
	DESCRIPTION
        "
        List of pm200frs02CtrllineResetAllCount
        Article
        "
	::= { pm200frs02CtrlLine 263 }


pm200frs02CtrllineResetAllCountEntry OBJECT-TYPE
	SYNTAX Pm200frs02CtrllineResetAllCountEntry
	MAX-ACCESS not-accessible
	STATUS current
	DESCRIPTION
        "
        Row definition for the pm200frs02CtrllineResetAllCount
        table
        "
	INDEX   { pm200frs02CtrllineResetAllCountIndex }
	::= { pm200frs02CtrllineResetAllCountTable 1 }


Pm200frs02CtrllineResetAllCountEntry ::=
	SEQUENCE {
	pm200frs02CtrllineResetAllCountIndex
		INTEGER,
	pm200frs02CtrllineResetAllCountsPortn
		EkiState
	}


pm200frs02CtrllineResetAllCountIndex OBJECT-TYPE
	SYNTAX  INTEGER(0..128)
	MAX-ACCESS  read-only
	STATUS current
	DESCRIPTION
        "
        Index definition for the pm200frs02CtrllineResetAllCount
        table
        "
	::= { pm200frs02CtrllineResetAllCountEntry 1 }


pm200frs02CtrllineResetAllCountsPortn OBJECT-TYPE
	SYNTAX  EkiState
	MAX-ACCESS read-write
	STATUS current
	DESCRIPTION
        "
        Line Counters Reset :This OID
         resets every counter on the line
        port  <Help>   This control operates
        a reset on the statistics current
        ,previous and history line port
        counters
        "
	::= { pm200frs02CtrllineResetAllCountEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pm200frs02CntclientInputErrorCounter articles
--- *********************************************************

pm200frs02CntclientInputErrorCounterTable OBJECT-TYPE
	SYNTAX  SEQUENCE OF Pm200frs02CntclientInputErrorCounterEntry
	MAX-ACCESS not-accessible
	STATUS current
	DESCRIPTION
        "
        List of pm200frs02CntclientInputErrorCounter
        Article
        "
	::= { pm200frs02CntClient 112 }


pm200frs02CntclientInputErrorCounterEntry OBJECT-TYPE
	SYNTAX Pm200frs02CntclientInputErrorCounterEntry
	MAX-ACCESS not-accessible
	STATUS current
	DESCRIPTION
        "
        Row definition for the pm200frs02CntclientInputErrorCounter
        table
        "
	INDEX   { pm200frs02CntclientInputErrorCounterIndex }
	::= { pm200frs02CntclientInputErrorCounterTable 1 }


Pm200frs02CntclientInputErrorCounterEntry ::=
	SEQUENCE {
	pm200frs02CntclientInputErrorCounterIndex
		INTEGER,
	pm200frs02CntclientInputErrorCounterValuePortn
		Counter32,
	pm200frs02CntclientInputErrorCounterErrorPortn
		EkiOnOff,
	pm200frs02CntclientInputErrorCounterOverloadPortn
		EkiOnOff
	}


pm200frs02CntclientInputErrorCounterIndex OBJECT-TYPE
	SYNTAX  INTEGER(0..128)
	MAX-ACCESS  read-only
	STATUS current
	DESCRIPTION
        "
        Index definition for the pm200frs02CntclientInputErrorCounter
        table
        "
	::= { pm200frs02CntclientInputErrorCounterEntry 1 }


pm200frs02CntclientInputErrorCounterValuePortn OBJECT-TYPE
	SYNTAX  Counter32
	MAX-ACCESS read-only
	STATUS current
	DESCRIPTION
        "
        Client Input Errors :This counter
        gives the number of SM-BIP8 on
         the client port (OTU4 only)  <Help>
         This counter gives the number
         of SM-BIP8 on the client port
         (OTU4 only)
        "
	::= { pm200frs02CntclientInputErrorCounterEntry 2 }


pm200frs02CntclientInputErrorCounterErrorPortn OBJECT-TYPE
	SYNTAX  EkiOnOff
	MAX-ACCESS read-only
	STATUS current
	DESCRIPTION
        "
        Client Counter Error :This OID
        when set indicates the BIP8 error
        counter value is invalid on Port
        "
	::= { pm200frs02CntclientInputErrorCounterEntry 3 }


pm200frs02CntclientInputErrorCounterOverloadPortn OBJECT-TYPE
	SYNTAX  EkiOnOff
	MAX-ACCESS read-only
	STATUS current
	DESCRIPTION
        "
        Client Counter Overload :This
         OID when set indicates a BIP8
         error counter overload on Port
        "
	::= { pm200frs02CntclientInputErrorCounterEntry 4 }


--- *********************************************************
---     TABLE for the pm200frs02CntclientCbipCounter articles
--- *********************************************************

pm200frs02CntclientCbipCounterTable OBJECT-TYPE
	SYNTAX  SEQUENCE OF Pm200frs02CntclientCbipCounterEntry
	MAX-ACCESS not-accessible
	STATUS current
	DESCRIPTION
        "
        List of pm200frs02CntclientCbipCounter
        Article
        "
	::= { pm200frs02CntClient 144 }


pm200frs02CntclientCbipCounterEntry OBJECT-TYPE
	SYNTAX Pm200frs02CntclientCbipCounterEntry
	MAX-ACCESS not-accessible
	STATUS current
	DESCRIPTION
        "
        Row definition for the pm200frs02CntclientCbipCounter
        table
        "
	INDEX   { pm200frs02CntclientCbipCounterIndex }
	::= { pm200frs02CntclientCbipCounterTable 1 }


Pm200frs02CntclientCbipCounterEntry ::=
	SEQUENCE {
	pm200frs02CntclientCbipCounterIndex
		INTEGER,
	pm200frs02CntclientCbipCounterValuePortn
		Counter32,
	pm200frs02CntclientCbipCounterErrorPortn
		EkiOnOff,
	pm200frs02CntclientCbipCounterOverloadPortn
		EkiOnOff
	}


pm200frs02CntclientCbipCounterIndex OBJECT-TYPE
	SYNTAX  INTEGER(0..128)
	MAX-ACCESS  read-only
	STATUS current
	DESCRIPTION
        "
        Index definition for the pm200frs02CntclientCbipCounter
        table
        "
	::= { pm200frs02CntclientCbipCounterEntry 1 }


pm200frs02CntclientCbipCounterValuePortn OBJECT-TYPE
	SYNTAX  Counter32
	MAX-ACCESS read-only
	STATUS current
	DESCRIPTION
        "
        Client Output Errors :This counter
        gives the number of SM-BIP8 on
         the client port (OTU4 only)  <Help>
         This counter gives the number
         of SM-BIP8 on the client port
         (OTU4 only)
        "
	::= { pm200frs02CntclientCbipCounterEntry 2 }


pm200frs02CntclientCbipCounterErrorPortn OBJECT-TYPE
	SYNTAX  EkiOnOff
	MAX-ACCESS read-only
	STATUS current
	DESCRIPTION
        "
        Client Counter Error :This OID
        when set indicates the BIP8 error
        counter value is invalid on Port
        "
	::= { pm200frs02CntclientCbipCounterEntry 3 }


pm200frs02CntclientCbipCounterOverloadPortn OBJECT-TYPE
	SYNTAX  EkiOnOff
	MAX-ACCESS read-only
	STATUS current
	DESCRIPTION
        "
        Client CBIP Counter Overload :This
        OID when set indicates a BIP8 error
        counter overload on Port
        "
	::= { pm200frs02CntclientCbipCounterEntry 4 }


--- *********************************************************
---     TABLE for the pm200frs02CntlocalLineSmBip8ErrorCounter articles
--- *********************************************************

pm200frs02CntlocalLineSmBip8ErrorCounterTable OBJECT-TYPE
	SYNTAX  SEQUENCE OF Pm200frs02CntlocalLineSmBip8ErrorCounterEntry
	MAX-ACCESS not-accessible
	STATUS current
	DESCRIPTION
        "
        List of pm200frs02CntlocalLineSmBip8ErrorCounter
        Article
        "
	::= { pm200frs02CntLine 192 }


pm200frs02CntlocalLineSmBip8ErrorCounterEntry OBJECT-TYPE
	SYNTAX Pm200frs02CntlocalLineSmBip8ErrorCounterEntry
	MAX-ACCESS not-accessible
	STATUS current
	DESCRIPTION
        "
        Row definition for the pm200frs02CntlocalLineSmBip8ErrorCounter
        table
        "
	INDEX   { pm200frs02CntlocalLineSmBip8ErrorCounterIndex }
	::= { pm200frs02CntlocalLineSmBip8ErrorCounterTable 1 }


Pm200frs02CntlocalLineSmBip8ErrorCounterEntry ::=
	SEQUENCE {
	pm200frs02CntlocalLineSmBip8ErrorCounterIndex
		INTEGER,
	pm200frs02CntlocalLineSmBip8ErrorCounterValuePortn
		Counter64,
	pm200frs02CntlocalLineSmBip8ErrorCounterErrorPortn
		EkiOnOff,
	pm200frs02CntlocalLineSmBip8ErrorCounterOverloadPortn
		EkiOnOff
	}


pm200frs02CntlocalLineSmBip8ErrorCounterIndex OBJECT-TYPE
	SYNTAX  INTEGER(0..128)
	MAX-ACCESS  read-only
	STATUS current
	DESCRIPTION
        "
        Index definition for the pm200frs02CntlocalLineSmBip8ErrorCounter
        table
        "
	::= { pm200frs02CntlocalLineSmBip8ErrorCounterEntry 1 }


pm200frs02CntlocalLineSmBip8ErrorCounterValuePortn OBJECT-TYPE
	SYNTAX  Counter64
	MAX-ACCESS read-only
	STATUS current
	DESCRIPTION
        "
        Uncorrected FEC Errors :This OID
        gives the current Bit Error Rate
        (residual SM-BIP8 error) after
         FEC   <Help> This counter gives
        the current Bit Error Rate (residual
        SM-BIP8 error) after FEC
        "
	::= { pm200frs02CntlocalLineSmBip8ErrorCounterEntry 2 }


pm200frs02CntlocalLineSmBip8ErrorCounterErrorPortn OBJECT-TYPE
	SYNTAX  EkiOnOff
	MAX-ACCESS read-only
	STATUS current
	DESCRIPTION
        "
        Line Counter Error :This OID when
        set indicates the B1 error counter
        value is invalid on Port
        "
	::= { pm200frs02CntlocalLineSmBip8ErrorCounterEntry 3 }


pm200frs02CntlocalLineSmBip8ErrorCounterOverloadPortn OBJECT-TYPE
	SYNTAX  EkiOnOff
	MAX-ACCESS read-only
	STATUS current
	DESCRIPTION
        "
        Line Counter Overload :This OID
        when set indicates a B1 error counter
        overload on Port
        "
	::= { pm200frs02CntlocalLineSmBip8ErrorCounterEntry 4 }


--- *********************************************************
---     TABLE for the pm200frs02CntlocalLineFecCorrectedErrorsCounter articles
--- *********************************************************

pm200frs02CntlocalLineFecCorrectedErrorsCounterTable OBJECT-TYPE
	SYNTAX  SEQUENCE OF Pm200frs02CntlocalLineFecCorrectedErrorsCounterEntry
	MAX-ACCESS not-accessible
	STATUS current
	DESCRIPTION
        "
        List of pm200frs02CntlocalLineFecCorrectedErrorsCounter
        Article
        "
	::= { pm200frs02CntLine 193 }


pm200frs02CntlocalLineFecCorrectedErrorsCounterEntry OBJECT-TYPE
	SYNTAX Pm200frs02CntlocalLineFecCorrectedErrorsCounterEntry
	MAX-ACCESS not-accessible
	STATUS current
	DESCRIPTION
        "
        Row definition for the pm200frs02CntlocalLineFecCorrectedErrorsCounter
        table
        "
	INDEX   { pm200frs02CntlocalLineFecCorrectedErrorsCounterIndex }
	::= { pm200frs02CntlocalLineFecCorrectedErrorsCounterTable 1 }


Pm200frs02CntlocalLineFecCorrectedErrorsCounterEntry ::=
	SEQUENCE {
	pm200frs02CntlocalLineFecCorrectedErrorsCounterIndex
		INTEGER,
	pm200frs02CntlocalLineFecCorrectedErrorsCounterValuePortn
		Counter64,
	pm200frs02CntlocalLineFecCorrectedErrorsCounterErrorPortn
		EkiOnOff,
	pm200frs02CntlocalLineFecCorrectedErrorsCounterOverloadPortn
		EkiOnOff
	}


pm200frs02CntlocalLineFecCorrectedErrorsCounterIndex OBJECT-TYPE
	SYNTAX  INTEGER(0..128)
	MAX-ACCESS  read-only
	STATUS current
	DESCRIPTION
        "
        Index definition for the pm200frs02CntlocalLineFecCorrectedErrorsCounter
        table
        "
	::= { pm200frs02CntlocalLineFecCorrectedErrorsCounterEntry 1 }


pm200frs02CntlocalLineFecCorrectedErrorsCounterValuePortn OBJECT-TYPE
	SYNTAX  Counter64
	MAX-ACCESS read-only
	STATUS current
	DESCRIPTION
        "
        Line Input HD FEC Corrected Errors
        :This OID gives the current Bit
        Error Rate before the Hard Decision
        FEC  <Help> This counter gives
         the current Bit Error Rate before
        the Hard Decision FEC
        "
	::= { pm200frs02CntlocalLineFecCorrectedErrorsCounterEntry 2 }


pm200frs02CntlocalLineFecCorrectedErrorsCounterErrorPortn OBJECT-TYPE
	SYNTAX  EkiOnOff
	MAX-ACCESS read-only
	STATUS current
	DESCRIPTION
        "
        FEC Counter Error :This bit when
        set indicates the FEC corrected
        errors counter value is invalid
        on Line
        "
	::= { pm200frs02CntlocalLineFecCorrectedErrorsCounterEntry 3 }


pm200frs02CntlocalLineFecCorrectedErrorsCounterOverloadPortn OBJECT-TYPE
	SYNTAX  EkiOnOff
	MAX-ACCESS read-only
	STATUS current
	DESCRIPTION
        "
        FEC Counter Overload :This bit
        when set indicates a FEC corrected
        errors counter overload on Line
        "
	::= { pm200frs02CntlocalLineFecCorrectedErrorsCounterEntry 4 }


--- *********************************************************
---     TABLE for the pm200frs02CntremoteLineSmBip8ErrorCounter articles
--- *********************************************************

pm200frs02CntremoteLineSmBip8ErrorCounterTable OBJECT-TYPE
	SYNTAX  SEQUENCE OF Pm200frs02CntremoteLineSmBip8ErrorCounterEntry
	MAX-ACCESS not-accessible
	STATUS current
	DESCRIPTION
        "
        List of pm200frs02CntremoteLineSmBip8ErrorCounter
        Article
        "
	::= { pm200frs02CntLine 194 }


pm200frs02CntremoteLineSmBip8ErrorCounterEntry OBJECT-TYPE
	SYNTAX Pm200frs02CntremoteLineSmBip8ErrorCounterEntry
	MAX-ACCESS not-accessible
	STATUS current
	DESCRIPTION
        "
        Row definition for the pm200frs02CntremoteLineSmBip8ErrorCounter
        table
        "
	INDEX   { pm200frs02CntremoteLineSmBip8ErrorCounterIndex }
	::= { pm200frs02CntremoteLineSmBip8ErrorCounterTable 1 }


Pm200frs02CntremoteLineSmBip8ErrorCounterEntry ::=
	SEQUENCE {
	pm200frs02CntremoteLineSmBip8ErrorCounterIndex
		INTEGER,
	pm200frs02CntremoteLineSmBip8ErrorCounterValuePortn
		Counter64,
	pm200frs02CntremoteLineSmBip8ErrorCounterErrorPortn
		EkiOnOff,
	pm200frs02CntremoteLineSmBip8ErrorCounterOverloadPortn
		EkiOnOff
	}


pm200frs02CntremoteLineSmBip8ErrorCounterIndex OBJECT-TYPE
	SYNTAX  INTEGER(0..128)
	MAX-ACCESS  read-only
	STATUS current
	DESCRIPTION
        "
        Index definition for the pm200frs02CntremoteLineSmBip8ErrorCounter
        table
        "
	::= { pm200frs02CntremoteLineSmBip8ErrorCounterEntry 1 }


pm200frs02CntremoteLineSmBip8ErrorCounterValuePortn OBJECT-TYPE
	SYNTAX  Counter64
	MAX-ACCESS read-only
	STATUS current
	DESCRIPTION
        "
        Remote SM BIP8 :This OID gives
        the current Bit Error Rate (residual
        SM-BIP8 error) after FEC on the
        remote side  <Help> This counter
        gives the current Bit Error Rate
        (residual SM-BIP8 error) after
         FEC on the remote side
        "
	::= { pm200frs02CntremoteLineSmBip8ErrorCounterEntry 2 }


pm200frs02CntremoteLineSmBip8ErrorCounterErrorPortn OBJECT-TYPE
	SYNTAX  EkiOnOff
	MAX-ACCESS read-only
	STATUS current
	DESCRIPTION
        "
        Remote Counter Error :
        "
	::= { pm200frs02CntremoteLineSmBip8ErrorCounterEntry 3 }


pm200frs02CntremoteLineSmBip8ErrorCounterOverloadPortn OBJECT-TYPE
	SYNTAX  EkiOnOff
	MAX-ACCESS read-only
	STATUS current
	DESCRIPTION
        "
        Remote Counter Overload :
        "
	::= { pm200frs02CntremoteLineSmBip8ErrorCounterEntry 4 }


--- *********************************************************
---     TABLE for the pm200frs02CntlineDfrmTimCnt articles
--- *********************************************************

pm200frs02CntlineDfrmTimCntTable OBJECT-TYPE
	SYNTAX  SEQUENCE OF Pm200frs02CntlineDfrmTimCntEntry
	MAX-ACCESS not-accessible
	STATUS current
	DESCRIPTION
        "
        List of pm200frs02CntlineDfrmTimCnt
        Article
        "
	::= { pm200frs02CntLine 195 }


pm200frs02CntlineDfrmTimCntEntry OBJECT-TYPE
	SYNTAX Pm200frs02CntlineDfrmTimCntEntry
	MAX-ACCESS not-accessible
	STATUS current
	DESCRIPTION
        "
        Row definition for the pm200frs02CntlineDfrmTimCnt
        table
        "
	INDEX   { pm200frs02CntlineDfrmTimCntIndex }
	::= { pm200frs02CntlineDfrmTimCntTable 1 }


Pm200frs02CntlineDfrmTimCntEntry ::=
	SEQUENCE {
	pm200frs02CntlineDfrmTimCntIndex
		INTEGER,
	pm200frs02CntlineDfrmTimCntValuePortn
		Counter64,
	pm200frs02CntlineDfrmTimCntErrorPortn
		EkiOnOff,
	pm200frs02CntlineDfrmTimCntOverloadPortn
		EkiOnOff
	}


pm200frs02CntlineDfrmTimCntIndex OBJECT-TYPE
	SYNTAX  INTEGER(0..128)
	MAX-ACCESS  read-only
	STATUS current
	DESCRIPTION
        "
        Index definition for the pm200frs02CntlineDfrmTimCnt
        table
        "
	::= { pm200frs02CntlineDfrmTimCntEntry 1 }


pm200frs02CntlineDfrmTimCntValuePortn OBJECT-TYPE
	SYNTAX  Counter64
	MAX-ACCESS read-only
	STATUS current
	DESCRIPTION
        "
        Line Timer Counter :
        "
	::= { pm200frs02CntlineDfrmTimCntEntry 2 }


pm200frs02CntlineDfrmTimCntErrorPortn OBJECT-TYPE
	SYNTAX  EkiOnOff
	MAX-ACCESS read-only
	STATUS current
	DESCRIPTION
        "
        Line Counter Error :This OID when
        set indicates the deframer timer
        counter value is invalid on Port
        "
	::= { pm200frs02CntlineDfrmTimCntEntry 3 }


pm200frs02CntlineDfrmTimCntOverloadPortn OBJECT-TYPE
	SYNTAX  EkiOnOff
	MAX-ACCESS read-only
	STATUS current
	DESCRIPTION
        "
        Line Counter Overload :This OID
        when set indicates a deframer timer
        counter overload on Port
        "
	::= { pm200frs02CntlineDfrmTimCntEntry 4 }


--- *********************************************************
---     TABLE for the pm200frs02CntlocalLineTrscvPreSdFecErrorCounter articles
--- *********************************************************

pm200frs02CntlocalLineTrscvPreSdFecErrorCounterTable OBJECT-TYPE
	SYNTAX  SEQUENCE OF Pm200frs02CntlocalLineTrscvPreSdFecErrorCounterEntry
	MAX-ACCESS not-accessible
	STATUS current
	DESCRIPTION
        "
        List of pm200frs02CntlocalLineTrscvPreSdFecErrorCounter
        Article
        "
	::= { pm200frs02CntLine 196 }


pm200frs02CntlocalLineTrscvPreSdFecErrorCounterEntry OBJECT-TYPE
	SYNTAX Pm200frs02CntlocalLineTrscvPreSdFecErrorCounterEntry
	MAX-ACCESS not-accessible
	STATUS current
	DESCRIPTION
        "
        Row definition for the pm200frs02CntlocalLineTrscvPreSdFecErrorCounter
        table
        "
	INDEX   { pm200frs02CntlocalLineTrscvPreSdFecErrorCounterIndex }
	::= { pm200frs02CntlocalLineTrscvPreSdFecErrorCounterTable 1 }


Pm200frs02CntlocalLineTrscvPreSdFecErrorCounterEntry ::=
	SEQUENCE {
	pm200frs02CntlocalLineTrscvPreSdFecErrorCounterIndex
		INTEGER,
	pm200frs02CntlocalLineTrscvPreSdFecErrorCounterValuePortn
		Counter64,
	pm200frs02CntlocalLineTrscvPreSdFecErrorCounterErrorPortn
		EkiOnOff,
	pm200frs02CntlocalLineTrscvPreSdFecErrorCounterOverloadPortn
		EkiOnOff
	}


pm200frs02CntlocalLineTrscvPreSdFecErrorCounterIndex OBJECT-TYPE
	SYNTAX  INTEGER(0..128)
	MAX-ACCESS  read-only
	STATUS current
	DESCRIPTION
        "
        Index definition for the pm200frs02CntlocalLineTrscvPreSdFecErrorCounter
        table
        "
	::= { pm200frs02CntlocalLineTrscvPreSdFecErrorCounterEntry 1 }


pm200frs02CntlocalLineTrscvPreSdFecErrorCounterValuePortn OBJECT-TYPE
	SYNTAX  Counter64
	MAX-ACCESS read-only
	STATUS current
	DESCRIPTION
        "
        Pre FEC Errors :This OID gives
        the current Bit Error Rate before
        the FEC  <Help> This counter gives
        the current Bit Error Rate before
        the FEC
        "
	::= { pm200frs02CntlocalLineTrscvPreSdFecErrorCounterEntry 2 }


pm200frs02CntlocalLineTrscvPreSdFecErrorCounterErrorPortn OBJECT-TYPE
	SYNTAX  EkiOnOff
	MAX-ACCESS read-only
	STATUS current
	DESCRIPTION
        "
        Line Counter Error :This OID when
        set indicates the deframer timer
        counter value is invalid on Port
        "
	::= { pm200frs02CntlocalLineTrscvPreSdFecErrorCounterEntry 3 }


pm200frs02CntlocalLineTrscvPreSdFecErrorCounterOverloadPortn OBJECT-TYPE
	SYNTAX  EkiOnOff
	MAX-ACCESS read-only
	STATUS current
	DESCRIPTION
        "
        Line Counter Overload :This OID
        when set indicates a deframer timer
        counter overload on Port
        "
	::= { pm200frs02CntlocalLineTrscvPreSdFecErrorCounterEntry 4 }


--- *********************************************************
---     TABLE for the pm200frs02CntlocalLineTrscvUncorrectedSdFecErrorCounter articles
--- *********************************************************

pm200frs02CntlocalLineTrscvUncorrectedSdFecErrorCounterTable OBJECT-TYPE
	SYNTAX  SEQUENCE OF Pm200frs02CntlocalLineTrscvUncorrectedSdFecErrorCounterEntry
	MAX-ACCESS not-accessible
	STATUS current
	DESCRIPTION
        "
        List of pm200frs02CntlocalLineTrscvUncorrectedSdFecErrorCounter
        Article
        "
	::= { pm200frs02CntLine 197 }


pm200frs02CntlocalLineTrscvUncorrectedSdFecErrorCounterEntry OBJECT-TYPE
	SYNTAX Pm200frs02CntlocalLineTrscvUncorrectedSdFecErrorCounterEntry
	MAX-ACCESS not-accessible
	STATUS current
	DESCRIPTION
        "
        Row definition for the pm200frs02CntlocalLineTrscvUncorrectedSdFecErrorCounter
        table
        "
	INDEX   { pm200frs02CntlocalLineTrscvUncorrectedSdFecErrorCounterIndex }
	::= { pm200frs02CntlocalLineTrscvUncorrectedSdFecErrorCounterTable 1 }


Pm200frs02CntlocalLineTrscvUncorrectedSdFecErrorCounterEntry ::=
	SEQUENCE {
	pm200frs02CntlocalLineTrscvUncorrectedSdFecErrorCounterIndex
		INTEGER,
	pm200frs02CntlocalLineTrscvUncorrectedSdFecErrorCounterValuePortn
		Counter64,
	pm200frs02CntlocalLineTrscvUncorrectedSdFecErrorCounterErrorPortn
		EkiOnOff,
	pm200frs02CntlocalLineTrscvUncorrectedSdFecErrorCounterOverloadPortn
		EkiOnOff
	}


pm200frs02CntlocalLineTrscvUncorrectedSdFecErrorCounterIndex OBJECT-TYPE
	SYNTAX  INTEGER(0..128)
	MAX-ACCESS  read-only
	STATUS current
	DESCRIPTION
        "
        Index definition for the pm200frs02CntlocalLineTrscvUncorrectedSdFecErrorCounter
        table
        "
	::= { pm200frs02CntlocalLineTrscvUncorrectedSdFecErrorCounterEntry 1 }


pm200frs02CntlocalLineTrscvUncorrectedSdFecErrorCounterValuePortn OBJECT-TYPE
	SYNTAX  Counter64
	MAX-ACCESS read-only
	STATUS current
	DESCRIPTION
        "
        Uncorrected FEC Errors :This OID
        gives the current Bit Error Rate
        after the Soft Decision FEC (residual)
         <Help> This counter gives the
         current Bit Error Rate after the
        Soft Decision FEC (residual)
        "
	::= { pm200frs02CntlocalLineTrscvUncorrectedSdFecErrorCounterEntry 2 }


pm200frs02CntlocalLineTrscvUncorrectedSdFecErrorCounterErrorPortn OBJECT-TYPE
	SYNTAX  EkiOnOff
	MAX-ACCESS read-only
	STATUS current
	DESCRIPTION
        "
        Line Counter Error :This OID when
        set indicates the deframer timer
        counter value is invalid on Port
        "
	::= { pm200frs02CntlocalLineTrscvUncorrectedSdFecErrorCounterEntry 3 }


pm200frs02CntlocalLineTrscvUncorrectedSdFecErrorCounterOverloadPortn OBJECT-TYPE
	SYNTAX  EkiOnOff
	MAX-ACCESS read-only
	STATUS current
	DESCRIPTION
        "
        Line Counter Overload :This OID
        when set indicates a deframer timer
        counter overload on Port
        "
	::= { pm200frs02CntlocalLineTrscvUncorrectedSdFecErrorCounterEntry 4 }


--- *********************************************************
---     TABLE for the pm200frs02CntlocalLineTrscvPreSdFecBitCounter articles
--- *********************************************************

pm200frs02CntlocalLineTrscvPreSdFecBitCounterTable OBJECT-TYPE
	SYNTAX  SEQUENCE OF Pm200frs02CntlocalLineTrscvPreSdFecBitCounterEntry
	MAX-ACCESS not-accessible
	STATUS current
	DESCRIPTION
        "
        List of pm200frs02CntlocalLineTrscvPreSdFecBitCounter
        Article
        "
	::= { pm200frs02CntLine 198 }


pm200frs02CntlocalLineTrscvPreSdFecBitCounterEntry OBJECT-TYPE
	SYNTAX Pm200frs02CntlocalLineTrscvPreSdFecBitCounterEntry
	MAX-ACCESS not-accessible
	STATUS current
	DESCRIPTION
        "
        Row definition for the pm200frs02CntlocalLineTrscvPreSdFecBitCounter
        table
        "
	INDEX   { pm200frs02CntlocalLineTrscvPreSdFecBitCounterIndex }
	::= { pm200frs02CntlocalLineTrscvPreSdFecBitCounterTable 1 }


Pm200frs02CntlocalLineTrscvPreSdFecBitCounterEntry ::=
	SEQUENCE {
	pm200frs02CntlocalLineTrscvPreSdFecBitCounterIndex
		INTEGER,
	pm200frs02CntlocalLineTrscvPreSdFecBitCounterValuePortn
		Counter64,
	pm200frs02CntlocalLineTrscvPreSdFecBitCounterErrorPortn
		EkiOnOff,
	pm200frs02CntlocalLineTrscvPreSdFecBitCounterOverloadPortn
		EkiOnOff
	}


pm200frs02CntlocalLineTrscvPreSdFecBitCounterIndex OBJECT-TYPE
	SYNTAX  INTEGER(0..128)
	MAX-ACCESS  read-only
	STATUS current
	DESCRIPTION
        "
        Index definition for the pm200frs02CntlocalLineTrscvPreSdFecBitCounter
        table
        "
	::= { pm200frs02CntlocalLineTrscvPreSdFecBitCounterEntry 1 }


pm200frs02CntlocalLineTrscvPreSdFecBitCounterValuePortn OBJECT-TYPE
	SYNTAX  Counter64
	MAX-ACCESS read-only
	STATUS current
	DESCRIPTION
        "
        Pre-SD FEC Bit Counter :This OID
        gives the current Bit count before
        the Soft Decision FEC  <Help> This
        counter gives the current Bit Count
        before the Soft Decision FEC
        "
	::= { pm200frs02CntlocalLineTrscvPreSdFecBitCounterEntry 2 }


pm200frs02CntlocalLineTrscvPreSdFecBitCounterErrorPortn OBJECT-TYPE
	SYNTAX  EkiOnOff
	MAX-ACCESS read-only
	STATUS current
	DESCRIPTION
        "
        Line Counter Error :This OID when
        set indicates the deframer timer
        counter value is invalid on Port
        "
	::= { pm200frs02CntlocalLineTrscvPreSdFecBitCounterEntry 3 }


pm200frs02CntlocalLineTrscvPreSdFecBitCounterOverloadPortn OBJECT-TYPE
	SYNTAX  EkiOnOff
	MAX-ACCESS read-only
	STATUS current
	DESCRIPTION
        "
        Line Counter Overload :This OID
        when set indicates a deframer timer
        counter overload on Port
        "
	::= { pm200frs02CntlocalLineTrscvPreSdFecBitCounterEntry 4 }


--- *********************************************************
---     TABLE for the pm200frs02CntlocalLineTrscvUncorrectedSdFecBitCounter articles
--- *********************************************************

pm200frs02CntlocalLineTrscvUncorrectedSdFecBitCounterTable OBJECT-TYPE
	SYNTAX  SEQUENCE OF Pm200frs02CntlocalLineTrscvUncorrectedSdFecBitCounterEntry
	MAX-ACCESS not-accessible
	STATUS current
	DESCRIPTION
        "
        List of pm200frs02CntlocalLineTrscvUncorrectedSdFecBitCounter
        Article
        "
	::= { pm200frs02CntLine 199 }


pm200frs02CntlocalLineTrscvUncorrectedSdFecBitCounterEntry OBJECT-TYPE
	SYNTAX Pm200frs02CntlocalLineTrscvUncorrectedSdFecBitCounterEntry
	MAX-ACCESS not-accessible
	STATUS current
	DESCRIPTION
        "
        Row definition for the pm200frs02CntlocalLineTrscvUncorrectedSdFecBitCounter
        table
        "
	INDEX   { pm200frs02CntlocalLineTrscvUncorrectedSdFecBitCounterIndex }
	::= { pm200frs02CntlocalLineTrscvUncorrectedSdFecBitCounterTable 1 }


Pm200frs02CntlocalLineTrscvUncorrectedSdFecBitCounterEntry ::=
	SEQUENCE {
	pm200frs02CntlocalLineTrscvUncorrectedSdFecBitCounterIndex
		INTEGER,
	pm200frs02CntlocalLineTrscvUncorrectedSdFecBitCounterValuePortn
		Counter64,
	pm200frs02CntlocalLineTrscvUncorrectedSdFecBitCounterErrorPortn
		EkiOnOff,
	pm200frs02CntlocalLineTrscvUncorrectedSdFecBitCounterOverloadPortn
		EkiOnOff
	}


pm200frs02CntlocalLineTrscvUncorrectedSdFecBitCounterIndex OBJECT-TYPE
	SYNTAX  INTEGER(0..128)
	MAX-ACCESS  read-only
	STATUS current
	DESCRIPTION
        "
        Index definition for the pm200frs02CntlocalLineTrscvUncorrectedSdFecBitCounter
        table
        "
	::= { pm200frs02CntlocalLineTrscvUncorrectedSdFecBitCounterEntry 1 }


pm200frs02CntlocalLineTrscvUncorrectedSdFecBitCounterValuePortn OBJECT-TYPE
	SYNTAX  Counter64
	MAX-ACCESS read-only
	STATUS current
	DESCRIPTION
        "
        Uncorrected SD FEC Bit Counter
        :This OID gives the current Bit
        count after the Soft Decision FEC
        (residual)  <Help> This counter
        gives the current Bit Count after
        the Soft Decision FEC (residual)
        "
	::= { pm200frs02CntlocalLineTrscvUncorrectedSdFecBitCounterEntry 2 }


pm200frs02CntlocalLineTrscvUncorrectedSdFecBitCounterErrorPortn OBJECT-TYPE
	SYNTAX  EkiOnOff
	MAX-ACCESS read-only
	STATUS current
	DESCRIPTION
        "
        Line Counter Error :This OID when
        set indicates the deframer timer
        counter value is invalid on Port
        "
	::= { pm200frs02CntlocalLineTrscvUncorrectedSdFecBitCounterEntry 3 }


pm200frs02CntlocalLineTrscvUncorrectedSdFecBitCounterOverloadPortn OBJECT-TYPE
	SYNTAX  EkiOnOff
	MAX-ACCESS read-only
	STATUS current
	DESCRIPTION
        "
        Line Counter Overload :This OID
        when set indicates a deframer timer
        counter overload on Port
        "
	::= { pm200frs02CntlocalLineTrscvUncorrectedSdFecBitCounterEntry 4 }







--- *****************************************************
--- $$$$$$$$$$$$$$$$$$$$$$$$$$$$$$$$$$$$$$$$$$$$$$$$$$$$$
---     RMON - 64 bits COUNTERS
--- $$$$$$$$$$$$$$$$$$$$$$$$$$$$$$$$$$$$$$$$$$$$$$$$$$$$$
--- *****************************************************



--- *********************************************************
---     TABLE for the pm200frs02MonupRmonBytesCounterClientInput articles
--- *********************************************************

pm200frs02MonupRmonBytesCounterClientInputTable OBJECT-TYPE
	SYNTAX  SEQUENCE OF Pm200frs02MonupRmonBytesCounterClientInputEntry
	MAX-ACCESS not-accessible
	STATUS current
	DESCRIPTION
        "
        List of pm200frs02MonupRmonBytesCounterClientInput
        Article
        "
	::= { pm200frs02MonClientRmonCounter 16 }


pm200frs02MonupRmonBytesCounterClientInputEntry OBJECT-TYPE
	SYNTAX Pm200frs02MonupRmonBytesCounterClientInputEntry
	MAX-ACCESS not-accessible
	STATUS current
	DESCRIPTION
        "
        Row definition for the pm200frs02MonupRmonBytesCounterClientInput
        table
        "
	INDEX   { pm200frs02MonupRmonBytesCounterClientInputIndex }
	::= { pm200frs02MonupRmonBytesCounterClientInputTable 1 }


Pm200frs02MonupRmonBytesCounterClientInputEntry ::=
	SEQUENCE {
	pm200frs02MonupRmonBytesCounterClientInputIndex
		INTEGER,
	pm200frs02MonupRmonBytesCounterClientInputValuePortn
		Counter64,
	pm200frs02MonupRmonBytesCounterClientInputErrorPortn
		EkiOnOff,
	pm200frs02MonupRmonBytesCounterClientInputOverloadPortn
		EkiOnOff
	}


pm200frs02MonupRmonBytesCounterClientInputIndex OBJECT-TYPE
	SYNTAX  INTEGER(0..128)
	MAX-ACCESS  read-only
	STATUS current
	DESCRIPTION
        "
        Index definition for the pm200frs02MonupRmonBytesCounterClientInput
        table
        "
	::= { pm200frs02MonupRmonBytesCounterClientInputEntry 1 }


pm200frs02MonupRmonBytesCounterClientInputValuePortn OBJECT-TYPE
	SYNTAX  Counter64
	MAX-ACCESS read-only
	STATUS current
	DESCRIPTION
        "
        Client Input Bytes :This counter
        is increased each time a data byte
        is received on the client port
          <Help>  This counter gives the
        number of bytes received on the
        client port
        "
	::= { pm200frs02MonupRmonBytesCounterClientInputEntry 2 }


pm200frs02MonupRmonBytesCounterClientInputErrorPortn OBJECT-TYPE
	SYNTAX  EkiOnOff
	MAX-ACCESS read-only
	STATUS current
	DESCRIPTION
        "
        Bytes Counter Error :This OID
         when set indicates the Bytes counter
        value is invalid on client port
        "
	::= { pm200frs02MonupRmonBytesCounterClientInputEntry 3 }


pm200frs02MonupRmonBytesCounterClientInputOverloadPortn OBJECT-TYPE
	SYNTAX  EkiOnOff
	MAX-ACCESS read-only
	STATUS current
	DESCRIPTION
        "
        Bytes Counter Overload :This OID
        when set indicates a Bytes counter
        overload on client port
        "
	::= { pm200frs02MonupRmonBytesCounterClientInputEntry 4 }


--- *********************************************************
---     TABLE for the pm200frs02MonupRmonCrcErrorsCounterClientInput articles
--- *********************************************************

pm200frs02MonupRmonCrcErrorsCounterClientInputTable OBJECT-TYPE
	SYNTAX  SEQUENCE OF Pm200frs02MonupRmonCrcErrorsCounterClientInputEntry
	MAX-ACCESS not-accessible
	STATUS current
	DESCRIPTION
        "
        List of pm200frs02MonupRmonCrcErrorsCounterClientInput
        Article
        "
	::= { pm200frs02MonClientRmonCounter 48 }


pm200frs02MonupRmonCrcErrorsCounterClientInputEntry OBJECT-TYPE
	SYNTAX Pm200frs02MonupRmonCrcErrorsCounterClientInputEntry
	MAX-ACCESS not-accessible
	STATUS current
	DESCRIPTION
        "
        Row definition for the pm200frs02MonupRmonCrcErrorsCounterClientInput
        table
        "
	INDEX   { pm200frs02MonupRmonCrcErrorsCounterClientInputIndex }
	::= { pm200frs02MonupRmonCrcErrorsCounterClientInputTable 1 }


Pm200frs02MonupRmonCrcErrorsCounterClientInputEntry ::=
	SEQUENCE {
	pm200frs02MonupRmonCrcErrorsCounterClientInputIndex
		INTEGER,
	pm200frs02MonupRmonCrcErrorsCounterClientInputValuePortn
		Counter64,
	pm200frs02MonupRmonCrcErrorsCounterClientInputErrorPortn
		EkiOnOff,
	pm200frs02MonupRmonCrcErrorsCounterClientInputOverloadPortn
		EkiOnOff
	}


pm200frs02MonupRmonCrcErrorsCounterClientInputIndex OBJECT-TYPE
	SYNTAX  INTEGER(0..128)
	MAX-ACCESS  read-only
	STATUS current
	DESCRIPTION
        "
        Index definition for the pm200frs02MonupRmonCrcErrorsCounterClientInput
        table
        "
	::= { pm200frs02MonupRmonCrcErrorsCounterClientInputEntry 1 }


pm200frs02MonupRmonCrcErrorsCounterClientInputValuePortn OBJECT-TYPE
	SYNTAX  Counter64
	MAX-ACCESS read-only
	STATUS current
	DESCRIPTION
        "
        Client Input CRC Errors :This
         counter is increased each time
        a CRC error is detected on the
         client port<Help>  This counter
        gives the number of CRC Errors
         received on the client port
        "
	::= { pm200frs02MonupRmonCrcErrorsCounterClientInputEntry 2 }


pm200frs02MonupRmonCrcErrorsCounterClientInputErrorPortn OBJECT-TYPE
	SYNTAX  EkiOnOff
	MAX-ACCESS read-only
	STATUS current
	DESCRIPTION
        "
        CRC Errors Counter Error :This
        OID when set indicates the CRC
         Errors counter value is invalid
        on client port
        "
	::= { pm200frs02MonupRmonCrcErrorsCounterClientInputEntry 3 }


pm200frs02MonupRmonCrcErrorsCounterClientInputOverloadPortn OBJECT-TYPE
	SYNTAX  EkiOnOff
	MAX-ACCESS read-only
	STATUS current
	DESCRIPTION
        "
        CRC Errors Counter Overload :This
        OID when set indicates a CRC Errors
        counter overload on client port
        "
	::= { pm200frs02MonupRmonCrcErrorsCounterClientInputEntry 4 }


--- *********************************************************
---     TABLE for the pm200frs02MonupRmonPacketsCounterClientInput articles
--- *********************************************************

pm200frs02MonupRmonPacketsCounterClientInputTable OBJECT-TYPE
	SYNTAX  SEQUENCE OF Pm200frs02MonupRmonPacketsCounterClientInputEntry
	MAX-ACCESS not-accessible
	STATUS current
	DESCRIPTION
        "
        List of pm200frs02MonupRmonPacketsCounterClientInput
        Article
        "
	::= { pm200frs02MonClientRmonCounter 80 }


pm200frs02MonupRmonPacketsCounterClientInputEntry OBJECT-TYPE
	SYNTAX Pm200frs02MonupRmonPacketsCounterClientInputEntry
	MAX-ACCESS not-accessible
	STATUS current
	DESCRIPTION
        "
        Row definition for the pm200frs02MonupRmonPacketsCounterClientInput
        table
        "
	INDEX   { pm200frs02MonupRmonPacketsCounterClientInputIndex }
	::= { pm200frs02MonupRmonPacketsCounterClientInputTable 1 }


Pm200frs02MonupRmonPacketsCounterClientInputEntry ::=
	SEQUENCE {
	pm200frs02MonupRmonPacketsCounterClientInputIndex
		INTEGER,
	pm200frs02MonupRmonPacketsCounterClientInputValuePortn
		Counter64,
	pm200frs02MonupRmonPacketsCounterClientInputErrorPortn
		EkiOnOff,
	pm200frs02MonupRmonPacketsCounterClientInputOverloadPortn
		EkiOnOff
	}


pm200frs02MonupRmonPacketsCounterClientInputIndex OBJECT-TYPE
	SYNTAX  INTEGER(0..128)
	MAX-ACCESS  read-only
	STATUS current
	DESCRIPTION
        "
        Index definition for the pm200frs02MonupRmonPacketsCounterClientInput
        table
        "
	::= { pm200frs02MonupRmonPacketsCounterClientInputEntry 1 }


pm200frs02MonupRmonPacketsCounterClientInputValuePortn OBJECT-TYPE
	SYNTAX  Counter64
	MAX-ACCESS read-only
	STATUS current
	DESCRIPTION
        "
        Client Input Packets :This counter
        is increased each time a packet
        is received on the client port
          <Help>  This counter gives the
        number of packets received on the
        client port
        "
	::= { pm200frs02MonupRmonPacketsCounterClientInputEntry 2 }


pm200frs02MonupRmonPacketsCounterClientInputErrorPortn OBJECT-TYPE
	SYNTAX  EkiOnOff
	MAX-ACCESS read-only
	STATUS current
	DESCRIPTION
        "
        Packets Counter Error :This OID
        when set indicates the Packets
         counter value is invalid on client
        port
        "
	::= { pm200frs02MonupRmonPacketsCounterClientInputEntry 3 }


pm200frs02MonupRmonPacketsCounterClientInputOverloadPortn OBJECT-TYPE
	SYNTAX  EkiOnOff
	MAX-ACCESS read-only
	STATUS current
	DESCRIPTION
        "
        Packets Counter Overload :This
        OID when set indicates a Packets
        counter overload on client port
        "
	::= { pm200frs02MonupRmonPacketsCounterClientInputEntry 4 }


--- *********************************************************
---     TABLE for the pm200frs02MonupRmonBroadcastCounterClientInput articles
--- *********************************************************

pm200frs02MonupRmonBroadcastCounterClientInputTable OBJECT-TYPE
	SYNTAX  SEQUENCE OF Pm200frs02MonupRmonBroadcastCounterClientInputEntry
	MAX-ACCESS not-accessible
	STATUS current
	DESCRIPTION
        "
        List of pm200frs02MonupRmonBroadcastCounterClientInput
        Article
        "
	::= { pm200frs02MonClientRmonCounter 112 }


pm200frs02MonupRmonBroadcastCounterClientInputEntry OBJECT-TYPE
	SYNTAX Pm200frs02MonupRmonBroadcastCounterClientInputEntry
	MAX-ACCESS not-accessible
	STATUS current
	DESCRIPTION
        "
        Row definition for the pm200frs02MonupRmonBroadcastCounterClientInput
        table
        "
	INDEX   { pm200frs02MonupRmonBroadcastCounterClientInputIndex }
	::= { pm200frs02MonupRmonBroadcastCounterClientInputTable 1 }


Pm200frs02MonupRmonBroadcastCounterClientInputEntry ::=
	SEQUENCE {
	pm200frs02MonupRmonBroadcastCounterClientInputIndex
		INTEGER,
	pm200frs02MonupRmonBroadcastCounterClientInputValuePortn
		Counter64,
	pm200frs02MonupRmonBroadcastCounterClientInputErrorPortn
		EkiOnOff,
	pm200frs02MonupRmonBroadcastCounterClientInputOverloadPortn
		EkiOnOff
	}


pm200frs02MonupRmonBroadcastCounterClientInputIndex OBJECT-TYPE
	SYNTAX  INTEGER(0..128)
	MAX-ACCESS  read-only
	STATUS current
	DESCRIPTION
        "
        Index definition for the pm200frs02MonupRmonBroadcastCounterClientInput
        table
        "
	::= { pm200frs02MonupRmonBroadcastCounterClientInputEntry 1 }


pm200frs02MonupRmonBroadcastCounterClientInputValuePortn OBJECT-TYPE
	SYNTAX  Counter64
	MAX-ACCESS read-only
	STATUS current
	DESCRIPTION
        "
        Client Input Broadcast Packets
        :This counter is increased each
        time a broadcast packet is received
        on the client port  <Help>  This
        counter gives the number of Broadcast
        packets received on the client
         port
        "
	::= { pm200frs02MonupRmonBroadcastCounterClientInputEntry 2 }


pm200frs02MonupRmonBroadcastCounterClientInputErrorPortn OBJECT-TYPE
	SYNTAX  EkiOnOff
	MAX-ACCESS read-only
	STATUS current
	DESCRIPTION
        "
        Broadcast Counter Error :This
         OID when set indicates the Broadcast
        counter value is invalid on client
        port
        "
	::= { pm200frs02MonupRmonBroadcastCounterClientInputEntry 3 }


pm200frs02MonupRmonBroadcastCounterClientInputOverloadPortn OBJECT-TYPE
	SYNTAX  EkiOnOff
	MAX-ACCESS read-only
	STATUS current
	DESCRIPTION
        "
        Broadcast Counter Overload :This
        OID when set indicates a Broadcast
        counter overload on client port
        "
	::= { pm200frs02MonupRmonBroadcastCounterClientInputEntry 4 }


--- *********************************************************
---     TABLE for the pm200frs02MonupRmonMulticastCounterClientInput articles
--- *********************************************************

pm200frs02MonupRmonMulticastCounterClientInputTable OBJECT-TYPE
	SYNTAX  SEQUENCE OF Pm200frs02MonupRmonMulticastCounterClientInputEntry
	MAX-ACCESS not-accessible
	STATUS current
	DESCRIPTION
        "
        List of pm200frs02MonupRmonMulticastCounterClientInput
        Article
        "
	::= { pm200frs02MonClientRmonCounter 144 }


pm200frs02MonupRmonMulticastCounterClientInputEntry OBJECT-TYPE
	SYNTAX Pm200frs02MonupRmonMulticastCounterClientInputEntry
	MAX-ACCESS not-accessible
	STATUS current
	DESCRIPTION
        "
        Row definition for the pm200frs02MonupRmonMulticastCounterClientInput
        table
        "
	INDEX   { pm200frs02MonupRmonMulticastCounterClientInputIndex }
	::= { pm200frs02MonupRmonMulticastCounterClientInputTable 1 }


Pm200frs02MonupRmonMulticastCounterClientInputEntry ::=
	SEQUENCE {
	pm200frs02MonupRmonMulticastCounterClientInputIndex
		INTEGER,
	pm200frs02MonupRmonMulticastCounterClientInputValuePortn
		Counter64,
	pm200frs02MonupRmonMulticastCounterClientInputErrorPortn
		EkiOnOff,
	pm200frs02MonupRmonMulticastCounterClientInputOverloadPortn
		EkiOnOff
	}


pm200frs02MonupRmonMulticastCounterClientInputIndex OBJECT-TYPE
	SYNTAX  INTEGER(0..128)
	MAX-ACCESS  read-only
	STATUS current
	DESCRIPTION
        "
        Index definition for the pm200frs02MonupRmonMulticastCounterClientInput
        table
        "
	::= { pm200frs02MonupRmonMulticastCounterClientInputEntry 1 }


pm200frs02MonupRmonMulticastCounterClientInputValuePortn OBJECT-TYPE
	SYNTAX  Counter64
	MAX-ACCESS read-only
	STATUS current
	DESCRIPTION
        "
        Client Input Multicast Packets
        :This counter is increased each
        time a Multicast packet is received
        on the client port  <Help>  This
        counter gives the number of Multicast
        packets received on the client
         port
        "
	::= { pm200frs02MonupRmonMulticastCounterClientInputEntry 2 }


pm200frs02MonupRmonMulticastCounterClientInputErrorPortn OBJECT-TYPE
	SYNTAX  EkiOnOff
	MAX-ACCESS read-only
	STATUS current
	DESCRIPTION
        "
        Multicast Counter Error :This
         OID when set indicates the Multicast
        counter value is invalid on client
        port
        "
	::= { pm200frs02MonupRmonMulticastCounterClientInputEntry 3 }


pm200frs02MonupRmonMulticastCounterClientInputOverloadPortn OBJECT-TYPE
	SYNTAX  EkiOnOff
	MAX-ACCESS read-only
	STATUS current
	DESCRIPTION
        "
        Multicast Counter Overload :This
        OID when set indicates a Multicast
        counter overload on client port
        "
	::= { pm200frs02MonupRmonMulticastCounterClientInputEntry 4 }


--- *********************************************************
---     TABLE for the pm200frs02MonupRmonPauseFrameCounterClientInput articles
--- *********************************************************

pm200frs02MonupRmonPauseFrameCounterClientInputTable OBJECT-TYPE
	SYNTAX  SEQUENCE OF Pm200frs02MonupRmonPauseFrameCounterClientInputEntry
	MAX-ACCESS not-accessible
	STATUS current
	DESCRIPTION
        "
        List of pm200frs02MonupRmonPauseFrameCounterClientInput
        Article
        "
	::= { pm200frs02MonClientRmonCounter 176 }


pm200frs02MonupRmonPauseFrameCounterClientInputEntry OBJECT-TYPE
	SYNTAX Pm200frs02MonupRmonPauseFrameCounterClientInputEntry
	MAX-ACCESS not-accessible
	STATUS current
	DESCRIPTION
        "
        Row definition for the pm200frs02MonupRmonPauseFrameCounterClientInput
        table
        "
	INDEX   { pm200frs02MonupRmonPauseFrameCounterClientInputIndex }
	::= { pm200frs02MonupRmonPauseFrameCounterClientInputTable 1 }


Pm200frs02MonupRmonPauseFrameCounterClientInputEntry ::=
	SEQUENCE {
	pm200frs02MonupRmonPauseFrameCounterClientInputIndex
		INTEGER,
	pm200frs02MonupRmonPauseFrameCounterClientInputValuePortn
		Counter64,
	pm200frs02MonupRmonPauseFrameCounterClientInputErrorPortn
		EkiOnOff,
	pm200frs02MonupRmonPauseFrameCounterClientInputOverloadPortn
		EkiOnOff
	}


pm200frs02MonupRmonPauseFrameCounterClientInputIndex OBJECT-TYPE
	SYNTAX  INTEGER(0..128)
	MAX-ACCESS  read-only
	STATUS current
	DESCRIPTION
        "
        Index definition for the pm200frs02MonupRmonPauseFrameCounterClientInput
        table
        "
	::= { pm200frs02MonupRmonPauseFrameCounterClientInputEntry 1 }


pm200frs02MonupRmonPauseFrameCounterClientInputValuePortn OBJECT-TYPE
	SYNTAX  Counter64
	MAX-ACCESS read-only
	STATUS current
	DESCRIPTION
        "
        Client Input Pause Frames :This
        counter is increased each time
         a Pause frame is received on the
        client port  <Help>  This counter
        gives the number of Pause frames
        received on the client port
        "
	::= { pm200frs02MonupRmonPauseFrameCounterClientInputEntry 2 }


pm200frs02MonupRmonPauseFrameCounterClientInputErrorPortn OBJECT-TYPE
	SYNTAX  EkiOnOff
	MAX-ACCESS read-only
	STATUS current
	DESCRIPTION
        "
        Pause Counter Error :This OID
         when set indicates the Pause counter
        value is invalid on client port
        "
	::= { pm200frs02MonupRmonPauseFrameCounterClientInputEntry 3 }


pm200frs02MonupRmonPauseFrameCounterClientInputOverloadPortn OBJECT-TYPE
	SYNTAX  EkiOnOff
	MAX-ACCESS read-only
	STATUS current
	DESCRIPTION
        "
        Pause Counter Overload :This OID
        when set indicates a Pause counter
        overload on client port
        "
	::= { pm200frs02MonupRmonPauseFrameCounterClientInputEntry 4 }


--- *********************************************************
---     TABLE for the pm200frs02MonupRmonUnicastCounterClientInput articles
--- *********************************************************

pm200frs02MonupRmonUnicastCounterClientInputTable OBJECT-TYPE
	SYNTAX  SEQUENCE OF Pm200frs02MonupRmonUnicastCounterClientInputEntry
	MAX-ACCESS not-accessible
	STATUS current
	DESCRIPTION
        "
        List of pm200frs02MonupRmonUnicastCounterClientInput
        Article
        "
	::= { pm200frs02MonClientRmonCounter 304 }


pm200frs02MonupRmonUnicastCounterClientInputEntry OBJECT-TYPE
	SYNTAX Pm200frs02MonupRmonUnicastCounterClientInputEntry
	MAX-ACCESS not-accessible
	STATUS current
	DESCRIPTION
        "
        Row definition for the pm200frs02MonupRmonUnicastCounterClientInput
        table
        "
	INDEX   { pm200frs02MonupRmonUnicastCounterClientInputIndex }
	::= { pm200frs02MonupRmonUnicastCounterClientInputTable 1 }


Pm200frs02MonupRmonUnicastCounterClientInputEntry ::=
	SEQUENCE {
	pm200frs02MonupRmonUnicastCounterClientInputIndex
		INTEGER,
	pm200frs02MonupRmonUnicastCounterClientInputValuePortn
		Counter64,
	pm200frs02MonupRmonUnicastCounterClientInputErrorPortn
		EkiOnOff,
	pm200frs02MonupRmonUnicastCounterClientInputOverloadPortn
		EkiOnOff
	}


pm200frs02MonupRmonUnicastCounterClientInputIndex OBJECT-TYPE
	SYNTAX  INTEGER(0..128)
	MAX-ACCESS  read-only
	STATUS current
	DESCRIPTION
        "
        Index definition for the pm200frs02MonupRmonUnicastCounterClientInput
        table
        "
	::= { pm200frs02MonupRmonUnicastCounterClientInputEntry 1 }


pm200frs02MonupRmonUnicastCounterClientInputValuePortn OBJECT-TYPE
	SYNTAX  Counter64
	MAX-ACCESS read-only
	STATUS current
	DESCRIPTION
        "
        Client Input Unicast Packets :This
        counter is increased each time
         a Unicast packet is received on
        the client port  <Help>  This counter
        gives the number of Unicast packets
        received on the client port
        "
	::= { pm200frs02MonupRmonUnicastCounterClientInputEntry 2 }


pm200frs02MonupRmonUnicastCounterClientInputErrorPortn OBJECT-TYPE
	SYNTAX  EkiOnOff
	MAX-ACCESS read-only
	STATUS current
	DESCRIPTION
        "
        Unicast Counter Error :This OID
        when set indicates the Unicast
         counter value is invalid on client
        port
        "
	::= { pm200frs02MonupRmonUnicastCounterClientInputEntry 3 }


pm200frs02MonupRmonUnicastCounterClientInputOverloadPortn OBJECT-TYPE
	SYNTAX  EkiOnOff
	MAX-ACCESS read-only
	STATUS current
	DESCRIPTION
        "
        Unicast Counter Overload :This
        OID when set indicates a Unicast
        counter overload on client port
        "
	::= { pm200frs02MonupRmonUnicastCounterClientInputEntry 4 }


--- *********************************************************
---     TABLE for the pm200frs02MonupRmonNonunicastCounterClientInput articles
--- *********************************************************

pm200frs02MonupRmonNonunicastCounterClientInputTable OBJECT-TYPE
	SYNTAX  SEQUENCE OF Pm200frs02MonupRmonNonunicastCounterClientInputEntry
	MAX-ACCESS not-accessible
	STATUS current
	DESCRIPTION
        "
        List of pm200frs02MonupRmonNonunicastCounterClientInput
        Article
        "
	::= { pm200frs02MonClientRmonCounter 336 }


pm200frs02MonupRmonNonunicastCounterClientInputEntry OBJECT-TYPE
	SYNTAX Pm200frs02MonupRmonNonunicastCounterClientInputEntry
	MAX-ACCESS not-accessible
	STATUS current
	DESCRIPTION
        "
        Row definition for the pm200frs02MonupRmonNonunicastCounterClientInput
        table
        "
	INDEX   { pm200frs02MonupRmonNonunicastCounterClientInputIndex }
	::= { pm200frs02MonupRmonNonunicastCounterClientInputTable 1 }


Pm200frs02MonupRmonNonunicastCounterClientInputEntry ::=
	SEQUENCE {
	pm200frs02MonupRmonNonunicastCounterClientInputIndex
		INTEGER,
	pm200frs02MonupRmonNonunicastCounterClientInputValuePortn
		Counter64,
	pm200frs02MonupRmonNonunicastCounterClientInputErrorPortn
		EkiOnOff,
	pm200frs02MonupRmonNonunicastCounterClientInputOverloadPortn
		EkiOnOff
	}


pm200frs02MonupRmonNonunicastCounterClientInputIndex OBJECT-TYPE
	SYNTAX  INTEGER(0..128)
	MAX-ACCESS  read-only
	STATUS current
	DESCRIPTION
        "
        Index definition for the pm200frs02MonupRmonNonunicastCounterClientInput
        table
        "
	::= { pm200frs02MonupRmonNonunicastCounterClientInputEntry 1 }


pm200frs02MonupRmonNonunicastCounterClientInputValuePortn OBJECT-TYPE
	SYNTAX  Counter64
	MAX-ACCESS read-only
	STATUS current
	DESCRIPTION
        "
        Client Input Non Unicast Packets
        :This counter is increased each
        time a Non-Unicast packet is received
        on the client port  <Help>  This
        counter gives the number of Non-Unicast
        packets received on the client
         port
        "
	::= { pm200frs02MonupRmonNonunicastCounterClientInputEntry 2 }


pm200frs02MonupRmonNonunicastCounterClientInputErrorPortn OBJECT-TYPE
	SYNTAX  EkiOnOff
	MAX-ACCESS read-only
	STATUS current
	DESCRIPTION
        "
        Non Unicast Counter Error :This
        OID when set indicates the Non-Unicast
        counter value is invalid on client
        port
        "
	::= { pm200frs02MonupRmonNonunicastCounterClientInputEntry 3 }


pm200frs02MonupRmonNonunicastCounterClientInputOverloadPortn OBJECT-TYPE
	SYNTAX  EkiOnOff
	MAX-ACCESS read-only
	STATUS current
	DESCRIPTION
        "
        Non Unicast Counter Overload :This
        OID when set indicates a Non-Unicast
        counter overload on client port
        "
	::= { pm200frs02MonupRmonNonunicastCounterClientInputEntry 4 }


--- *********************************************************
---     TABLE for the pm200frs02MondownRmonBytesCounterClientOutput articles
--- *********************************************************

pm200frs02MondownRmonBytesCounterClientOutputTable OBJECT-TYPE
	SYNTAX  SEQUENCE OF Pm200frs02MondownRmonBytesCounterClientOutputEntry
	MAX-ACCESS not-accessible
	STATUS current
	DESCRIPTION
        "
        List of pm200frs02MondownRmonBytesCounterClientOutput
        Article
        "
	::= { pm200frs02MonClientRmonCounter 400 }


pm200frs02MondownRmonBytesCounterClientOutputEntry OBJECT-TYPE
	SYNTAX Pm200frs02MondownRmonBytesCounterClientOutputEntry
	MAX-ACCESS not-accessible
	STATUS current
	DESCRIPTION
        "
        Row definition for the pm200frs02MondownRmonBytesCounterClientOutput
        table
        "
	INDEX   { pm200frs02MondownRmonBytesCounterClientOutputIndex }
	::= { pm200frs02MondownRmonBytesCounterClientOutputTable 1 }


Pm200frs02MondownRmonBytesCounterClientOutputEntry ::=
	SEQUENCE {
	pm200frs02MondownRmonBytesCounterClientOutputIndex
		INTEGER,
	pm200frs02MondownRmonBytesCounterClientOutputValuePortn
		Counter64,
	pm200frs02MondownRmonBytesCounterClientOutputErrorPortn
		EkiOnOff,
	pm200frs02MondownRmonBytesCounterClientOutputOverloadPortn
		EkiOnOff
	}


pm200frs02MondownRmonBytesCounterClientOutputIndex OBJECT-TYPE
	SYNTAX  INTEGER(0..128)
	MAX-ACCESS  read-only
	STATUS current
	DESCRIPTION
        "
        Index definition for the pm200frs02MondownRmonBytesCounterClientOutput
        table
        "
	::= { pm200frs02MondownRmonBytesCounterClientOutputEntry 1 }


pm200frs02MondownRmonBytesCounterClientOutputValuePortn OBJECT-TYPE
	SYNTAX  Counter64
	MAX-ACCESS read-only
	STATUS current
	DESCRIPTION
        "
        Client Output Bytes :This counter
        is increased each time a data byte
        is transmitted on the client port
        <Help> This counter gives the number
        of bytes transmitted on the client
        port
        "
	::= { pm200frs02MondownRmonBytesCounterClientOutputEntry 2 }


pm200frs02MondownRmonBytesCounterClientOutputErrorPortn OBJECT-TYPE
	SYNTAX  EkiOnOff
	MAX-ACCESS read-only
	STATUS current
	DESCRIPTION
        "
        Bytes Counter Error :This OID
         when set indicates the Bytes counter
        value is invalid on client port
        "
	::= { pm200frs02MondownRmonBytesCounterClientOutputEntry 3 }


pm200frs02MondownRmonBytesCounterClientOutputOverloadPortn OBJECT-TYPE
	SYNTAX  EkiOnOff
	MAX-ACCESS read-only
	STATUS current
	DESCRIPTION
        "
        Bytes Counter Overload :This OID
        when set indicates a Bytes counter
        overload on client port

        "
	::= { pm200frs02MondownRmonBytesCounterClientOutputEntry 4 }


--- *********************************************************
---     TABLE for the pm200frs02MondownRmonCrcErrorsCounterClientOutput articles
--- *********************************************************

pm200frs02MondownRmonCrcErrorsCounterClientOutputTable OBJECT-TYPE
	SYNTAX  SEQUENCE OF Pm200frs02MondownRmonCrcErrorsCounterClientOutputEntry
	MAX-ACCESS not-accessible
	STATUS current
	DESCRIPTION
        "
        List of pm200frs02MondownRmonCrcErrorsCounterClientOutput
        Article
        "
	::= { pm200frs02MonClientRmonCounter 432 }


pm200frs02MondownRmonCrcErrorsCounterClientOutputEntry OBJECT-TYPE
	SYNTAX Pm200frs02MondownRmonCrcErrorsCounterClientOutputEntry
	MAX-ACCESS not-accessible
	STATUS current
	DESCRIPTION
        "
        Row definition for the pm200frs02MondownRmonCrcErrorsCounterClientOutput
        table
        "
	INDEX   { pm200frs02MondownRmonCrcErrorsCounterClientOutputIndex }
	::= { pm200frs02MondownRmonCrcErrorsCounterClientOutputTable 1 }


Pm200frs02MondownRmonCrcErrorsCounterClientOutputEntry ::=
	SEQUENCE {
	pm200frs02MondownRmonCrcErrorsCounterClientOutputIndex
		INTEGER,
	pm200frs02MondownRmonCrcErrorsCounterClientOutputValuePortn
		Counter64,
	pm200frs02MondownRmonCrcErrorsCounterClientOutputErrorPortn
		EkiOnOff,
	pm200frs02MondownRmonCrcErrorsCounterClientOutputOverloadPortn
		EkiOnOff
	}


pm200frs02MondownRmonCrcErrorsCounterClientOutputIndex OBJECT-TYPE
	SYNTAX  INTEGER(0..128)
	MAX-ACCESS  read-only
	STATUS current
	DESCRIPTION
        "
        Index definition for the pm200frs02MondownRmonCrcErrorsCounterClientOutput
        table
        "
	::= { pm200frs02MondownRmonCrcErrorsCounterClientOutputEntry 1 }


pm200frs02MondownRmonCrcErrorsCounterClientOutputValuePortn OBJECT-TYPE
	SYNTAX  Counter64
	MAX-ACCESS read-only
	STATUS current
	DESCRIPTION
        "
        Client Output CRC Errors :This
        counter is increased each time
         a CRC error is detected on the
        transmit client port  <Help>  This
        counter gives the number of CRC
        Errors transmitted on the client
        port
        "
	::= { pm200frs02MondownRmonCrcErrorsCounterClientOutputEntry 2 }


pm200frs02MondownRmonCrcErrorsCounterClientOutputErrorPortn OBJECT-TYPE
	SYNTAX  EkiOnOff
	MAX-ACCESS read-only
	STATUS current
	DESCRIPTION
        "
        CRC Errors Counter Error :This
        OID when set indicates the CRC
         Errors counter value is invalid
        on client port
        "
	::= { pm200frs02MondownRmonCrcErrorsCounterClientOutputEntry 3 }


pm200frs02MondownRmonCrcErrorsCounterClientOutputOverloadPortn OBJECT-TYPE
	SYNTAX  EkiOnOff
	MAX-ACCESS read-only
	STATUS current
	DESCRIPTION
        "
        CRC Errors Counter Overload :This
        OID when set indicates a CRC Errors
        counter overload on client port
        "
	::= { pm200frs02MondownRmonCrcErrorsCounterClientOutputEntry 4 }


--- *********************************************************
---     TABLE for the pm200frs02MondownRmonPacketsCounterClientOutput articles
--- *********************************************************

pm200frs02MondownRmonPacketsCounterClientOutputTable OBJECT-TYPE
	SYNTAX  SEQUENCE OF Pm200frs02MondownRmonPacketsCounterClientOutputEntry
	MAX-ACCESS not-accessible
	STATUS current
	DESCRIPTION
        "
        List of pm200frs02MondownRmonPacketsCounterClientOutput
        Article
        "
	::= { pm200frs02MonClientRmonCounter 464 }


pm200frs02MondownRmonPacketsCounterClientOutputEntry OBJECT-TYPE
	SYNTAX Pm200frs02MondownRmonPacketsCounterClientOutputEntry
	MAX-ACCESS not-accessible
	STATUS current
	DESCRIPTION
        "
        Row definition for the pm200frs02MondownRmonPacketsCounterClientOutput
        table
        "
	INDEX   { pm200frs02MondownRmonPacketsCounterClientOutputIndex }
	::= { pm200frs02MondownRmonPacketsCounterClientOutputTable 1 }


Pm200frs02MondownRmonPacketsCounterClientOutputEntry ::=
	SEQUENCE {
	pm200frs02MondownRmonPacketsCounterClientOutputIndex
		INTEGER,
	pm200frs02MondownRmonPacketsCounterClientOutputValuePortn
		Counter64,
	pm200frs02MondownRmonPacketsCounterClientOutputErrorPortn
		EkiOnOff,
	pm200frs02MondownRmonPacketsCounterClientOutputOverloadPortn
		EkiOnOff
	}


pm200frs02MondownRmonPacketsCounterClientOutputIndex OBJECT-TYPE
	SYNTAX  INTEGER(0..128)
	MAX-ACCESS  read-only
	STATUS current
	DESCRIPTION
        "
        Index definition for the pm200frs02MondownRmonPacketsCounterClientOutput
        table
        "
	::= { pm200frs02MondownRmonPacketsCounterClientOutputEntry 1 }


pm200frs02MondownRmonPacketsCounterClientOutputValuePortn OBJECT-TYPE
	SYNTAX  Counter64
	MAX-ACCESS read-only
	STATUS current
	DESCRIPTION
        "
        Client Output Packets :This counter
        is increased each time a packet
        is transmitted on the client port
         <Help>  This counter gives the
        number of packets transmitted on
        the client port
        "
	::= { pm200frs02MondownRmonPacketsCounterClientOutputEntry 2 }


pm200frs02MondownRmonPacketsCounterClientOutputErrorPortn OBJECT-TYPE
	SYNTAX  EkiOnOff
	MAX-ACCESS read-only
	STATUS current
	DESCRIPTION
        "
        Packets Counter Error :This OID
        when set indicates the Packets
         counter value is invalid on client
        port
        "
	::= { pm200frs02MondownRmonPacketsCounterClientOutputEntry 3 }


pm200frs02MondownRmonPacketsCounterClientOutputOverloadPortn OBJECT-TYPE
	SYNTAX  EkiOnOff
	MAX-ACCESS read-only
	STATUS current
	DESCRIPTION
        "
        Packets Counter Overload :This
        OID when set indicates a Packets
        counter overload on client port
        "
	::= { pm200frs02MondownRmonPacketsCounterClientOutputEntry 4 }


--- *********************************************************
---     TABLE for the pm200frs02MondownRmonBroadcastCounterClientOutput articles
--- *********************************************************

pm200frs02MondownRmonBroadcastCounterClientOutputTable OBJECT-TYPE
	SYNTAX  SEQUENCE OF Pm200frs02MondownRmonBroadcastCounterClientOutputEntry
	MAX-ACCESS not-accessible
	STATUS current
	DESCRIPTION
        "
        List of pm200frs02MondownRmonBroadcastCounterClientOutput
        Article
        "
	::= { pm200frs02MonClientRmonCounter 496 }


pm200frs02MondownRmonBroadcastCounterClientOutputEntry OBJECT-TYPE
	SYNTAX Pm200frs02MondownRmonBroadcastCounterClientOutputEntry
	MAX-ACCESS not-accessible
	STATUS current
	DESCRIPTION
        "
        Row definition for the pm200frs02MondownRmonBroadcastCounterClientOutput
        table
        "
	INDEX   { pm200frs02MondownRmonBroadcastCounterClientOutputIndex }
	::= { pm200frs02MondownRmonBroadcastCounterClientOutputTable 1 }


Pm200frs02MondownRmonBroadcastCounterClientOutputEntry ::=
	SEQUENCE {
	pm200frs02MondownRmonBroadcastCounterClientOutputIndex
		INTEGER,
	pm200frs02MondownRmonBroadcastCounterClientOutputValuePortn
		Counter64,
	pm200frs02MondownRmonBroadcastCounterClientOutputErrorPortn
		EkiOnOff,
	pm200frs02MondownRmonBroadcastCounterClientOutputOverloadPortn
		EkiOnOff
	}


pm200frs02MondownRmonBroadcastCounterClientOutputIndex OBJECT-TYPE
	SYNTAX  INTEGER(0..128)
	MAX-ACCESS  read-only
	STATUS current
	DESCRIPTION
        "
        Index definition for the pm200frs02MondownRmonBroadcastCounterClientOutput
        table
        "
	::= { pm200frs02MondownRmonBroadcastCounterClientOutputEntry 1 }


pm200frs02MondownRmonBroadcastCounterClientOutputValuePortn OBJECT-TYPE
	SYNTAX  Counter64
	MAX-ACCESS read-only
	STATUS current
	DESCRIPTION
        "
        Client Output Broadcast Packets
        :This counter is increased each
        time a broadcast packet is transmitted
        on the client port  <Help>  This
        counter gives the number of Broadcast
        packets transmitted on the client
        port
        "
	::= { pm200frs02MondownRmonBroadcastCounterClientOutputEntry 2 }


pm200frs02MondownRmonBroadcastCounterClientOutputErrorPortn OBJECT-TYPE
	SYNTAX  EkiOnOff
	MAX-ACCESS read-only
	STATUS current
	DESCRIPTION
        "
        Broadcast Counter Error :This
         OID when set indicates the Broadcast
        counter value is invalid on client
        port
        "
	::= { pm200frs02MondownRmonBroadcastCounterClientOutputEntry 3 }


pm200frs02MondownRmonBroadcastCounterClientOutputOverloadPortn OBJECT-TYPE
	SYNTAX  EkiOnOff
	MAX-ACCESS read-only
	STATUS current
	DESCRIPTION
        "
        Broadcast Counter Overload :This
        OID when set indicates a Broadcast
        counter overload on client port
        "
	::= { pm200frs02MondownRmonBroadcastCounterClientOutputEntry 4 }


--- *********************************************************
---     TABLE for the pm200frs02MondownRmonMulticastCounterClientOutput articles
--- *********************************************************

pm200frs02MondownRmonMulticastCounterClientOutputTable OBJECT-TYPE
	SYNTAX  SEQUENCE OF Pm200frs02MondownRmonMulticastCounterClientOutputEntry
	MAX-ACCESS not-accessible
	STATUS current
	DESCRIPTION
        "
        List of pm200frs02MondownRmonMulticastCounterClientOutput
        Article
        "
	::= { pm200frs02MonClientRmonCounter 528 }


pm200frs02MondownRmonMulticastCounterClientOutputEntry OBJECT-TYPE
	SYNTAX Pm200frs02MondownRmonMulticastCounterClientOutputEntry
	MAX-ACCESS not-accessible
	STATUS current
	DESCRIPTION
        "
        Row definition for the pm200frs02MondownRmonMulticastCounterClientOutput
        table
        "
	INDEX   { pm200frs02MondownRmonMulticastCounterClientOutputIndex }
	::= { pm200frs02MondownRmonMulticastCounterClientOutputTable 1 }


Pm200frs02MondownRmonMulticastCounterClientOutputEntry ::=
	SEQUENCE {
	pm200frs02MondownRmonMulticastCounterClientOutputIndex
		INTEGER,
	pm200frs02MondownRmonMulticastCounterClientOutputValuePortn
		Counter64,
	pm200frs02MondownRmonMulticastCounterClientOutputErrorPortn
		EkiOnOff,
	pm200frs02MondownRmonMulticastCounterClientOutputOverloadPortn
		EkiOnOff
	}


pm200frs02MondownRmonMulticastCounterClientOutputIndex OBJECT-TYPE
	SYNTAX  INTEGER(0..128)
	MAX-ACCESS  read-only
	STATUS current
	DESCRIPTION
        "
        Index definition for the pm200frs02MondownRmonMulticastCounterClientOutput
        table
        "
	::= { pm200frs02MondownRmonMulticastCounterClientOutputEntry 1 }


pm200frs02MondownRmonMulticastCounterClientOutputValuePortn OBJECT-TYPE
	SYNTAX  Counter64
	MAX-ACCESS read-only
	STATUS current
	DESCRIPTION
        "
        Client Output Multicast Packets
        :This counter is increased each
        time a Multicast packet is transmitted
        on the client port  <Help>  This
        counter gives the number of Multicast
        packets transmitted on the client
        port
        "
	::= { pm200frs02MondownRmonMulticastCounterClientOutputEntry 2 }


pm200frs02MondownRmonMulticastCounterClientOutputErrorPortn OBJECT-TYPE
	SYNTAX  EkiOnOff
	MAX-ACCESS read-only
	STATUS current
	DESCRIPTION
        "
        Multicast Counter Error :This
         OID when set indicates the Multicast
        counter value is invalid on client
        port
        "
	::= { pm200frs02MondownRmonMulticastCounterClientOutputEntry 3 }


pm200frs02MondownRmonMulticastCounterClientOutputOverloadPortn OBJECT-TYPE
	SYNTAX  EkiOnOff
	MAX-ACCESS read-only
	STATUS current
	DESCRIPTION
        "
        Multicast Counter Overload :This
        OID when set indicates a Multicast
        counter overload on client port
        "
	::= { pm200frs02MondownRmonMulticastCounterClientOutputEntry 4 }


--- *********************************************************
---     TABLE for the pm200frs02MondownRmonPauseFrameCounterClientOutput articles
--- *********************************************************

pm200frs02MondownRmonPauseFrameCounterClientOutputTable OBJECT-TYPE
	SYNTAX  SEQUENCE OF Pm200frs02MondownRmonPauseFrameCounterClientOutputEntry
	MAX-ACCESS not-accessible
	STATUS current
	DESCRIPTION
        "
        List of pm200frs02MondownRmonPauseFrameCounterClientOutput
        Article
        "
	::= { pm200frs02MonClientRmonCounter 560 }


pm200frs02MondownRmonPauseFrameCounterClientOutputEntry OBJECT-TYPE
	SYNTAX Pm200frs02MondownRmonPauseFrameCounterClientOutputEntry
	MAX-ACCESS not-accessible
	STATUS current
	DESCRIPTION
        "
        Row definition for the pm200frs02MondownRmonPauseFrameCounterClientOutput
        table
        "
	INDEX   { pm200frs02MondownRmonPauseFrameCounterClientOutputIndex }
	::= { pm200frs02MondownRmonPauseFrameCounterClientOutputTable 1 }


Pm200frs02MondownRmonPauseFrameCounterClientOutputEntry ::=
	SEQUENCE {
	pm200frs02MondownRmonPauseFrameCounterClientOutputIndex
		INTEGER,
	pm200frs02MondownRmonPauseFrameCounterClientOutputValuePortn
		Counter64,
	pm200frs02MondownRmonPauseFrameCounterClientOutputErrorPortn
		EkiOnOff,
	pm200frs02MondownRmonPauseFrameCounterClientOutputOverloadPortn
		EkiOnOff
	}


pm200frs02MondownRmonPauseFrameCounterClientOutputIndex OBJECT-TYPE
	SYNTAX  INTEGER(0..128)
	MAX-ACCESS  read-only
	STATUS current
	DESCRIPTION
        "
        Index definition for the pm200frs02MondownRmonPauseFrameCounterClientOutput
        table
        "
	::= { pm200frs02MondownRmonPauseFrameCounterClientOutputEntry 1 }


pm200frs02MondownRmonPauseFrameCounterClientOutputValuePortn OBJECT-TYPE
	SYNTAX  Counter64
	MAX-ACCESS read-only
	STATUS current
	DESCRIPTION
        "
        Client Output Pause Frames :This
        counter is increased each time
         a Pause frame is transmitted on
        the client port  <Help>  This counter
        gives the number of Pause frames
        transmitted on the client port
        "
	::= { pm200frs02MondownRmonPauseFrameCounterClientOutputEntry 2 }


pm200frs02MondownRmonPauseFrameCounterClientOutputErrorPortn OBJECT-TYPE
	SYNTAX  EkiOnOff
	MAX-ACCESS read-only
	STATUS current
	DESCRIPTION
        "
        Pause Counter Error :This OID
         when set indicates the Pause counter
        value is invalid on client port
        "
	::= { pm200frs02MondownRmonPauseFrameCounterClientOutputEntry 3 }


pm200frs02MondownRmonPauseFrameCounterClientOutputOverloadPortn OBJECT-TYPE
	SYNTAX  EkiOnOff
	MAX-ACCESS read-only
	STATUS current
	DESCRIPTION
        "
        Pause Counter Overload :This OID
        when set indicates a Pause counter
        overload on client port
        "
	::= { pm200frs02MondownRmonPauseFrameCounterClientOutputEntry 4 }


--- *********************************************************
---     TABLE for the pm200frs02MondownRmonUnicastCounterClientOutput articles
--- *********************************************************

pm200frs02MondownRmonUnicastCounterClientOutputTable OBJECT-TYPE
	SYNTAX  SEQUENCE OF Pm200frs02MondownRmonUnicastCounterClientOutputEntry
	MAX-ACCESS not-accessible
	STATUS current
	DESCRIPTION
        "
        List of pm200frs02MondownRmonUnicastCounterClientOutput
        Article
        "
	::= { pm200frs02MonClientRmonCounter 688 }


pm200frs02MondownRmonUnicastCounterClientOutputEntry OBJECT-TYPE
	SYNTAX Pm200frs02MondownRmonUnicastCounterClientOutputEntry
	MAX-ACCESS not-accessible
	STATUS current
	DESCRIPTION
        "
        Row definition for the pm200frs02MondownRmonUnicastCounterClientOutput
        table
        "
	INDEX   { pm200frs02MondownRmonUnicastCounterClientOutputIndex }
	::= { pm200frs02MondownRmonUnicastCounterClientOutputTable 1 }


Pm200frs02MondownRmonUnicastCounterClientOutputEntry ::=
	SEQUENCE {
	pm200frs02MondownRmonUnicastCounterClientOutputIndex
		INTEGER,
	pm200frs02MondownRmonUnicastCounterClientOutputValuePortn
		Counter64,
	pm200frs02MondownRmonUnicastCounterClientOutputErrorPortn
		EkiOnOff,
	pm200frs02MondownRmonUnicastCounterClientOutputOverloadPortn
		EkiOnOff
	}


pm200frs02MondownRmonUnicastCounterClientOutputIndex OBJECT-TYPE
	SYNTAX  INTEGER(0..128)
	MAX-ACCESS  read-only
	STATUS current
	DESCRIPTION
        "
        Index definition for the pm200frs02MondownRmonUnicastCounterClientOutput
        table
        "
	::= { pm200frs02MondownRmonUnicastCounterClientOutputEntry 1 }


pm200frs02MondownRmonUnicastCounterClientOutputValuePortn OBJECT-TYPE
	SYNTAX  Counter64
	MAX-ACCESS read-only
	STATUS current
	DESCRIPTION
        "
        Client Output Unicast Packets
         :This counter is increased each
        time a Unicast packet is transmitted
        on the client port  <Help>  This
        counter gives the number of Unicast
        packets transmitted on the client
        port
        "
	::= { pm200frs02MondownRmonUnicastCounterClientOutputEntry 2 }


pm200frs02MondownRmonUnicastCounterClientOutputErrorPortn OBJECT-TYPE
	SYNTAX  EkiOnOff
	MAX-ACCESS read-only
	STATUS current
	DESCRIPTION
        "
        Unicast Counter Error :This OID
        when set indicates the Unicast
         counter value is invalid on client
        port
        "
	::= { pm200frs02MondownRmonUnicastCounterClientOutputEntry 3 }


pm200frs02MondownRmonUnicastCounterClientOutputOverloadPortn OBJECT-TYPE
	SYNTAX  EkiOnOff
	MAX-ACCESS read-only
	STATUS current
	DESCRIPTION
        "
        Unicast Counter Overload :This
        OID when set indicates a Unicast
        counter overload on client port
        "
	::= { pm200frs02MondownRmonUnicastCounterClientOutputEntry 4 }


--- *********************************************************
---     TABLE for the pm200frs02MondownRmonNonunicastCounterClientOutput articles
--- *********************************************************

pm200frs02MondownRmonNonunicastCounterClientOutputTable OBJECT-TYPE
	SYNTAX  SEQUENCE OF Pm200frs02MondownRmonNonunicastCounterClientOutputEntry
	MAX-ACCESS not-accessible
	STATUS current
	DESCRIPTION
        "
        List of pm200frs02MondownRmonNonunicastCounterClientOutput
        Article
        "
	::= { pm200frs02MonClientRmonCounter 720 }


pm200frs02MondownRmonNonunicastCounterClientOutputEntry OBJECT-TYPE
	SYNTAX Pm200frs02MondownRmonNonunicastCounterClientOutputEntry
	MAX-ACCESS not-accessible
	STATUS current
	DESCRIPTION
        "
        Row definition for the pm200frs02MondownRmonNonunicastCounterClientOutput
        table
        "
	INDEX   { pm200frs02MondownRmonNonunicastCounterClientOutputIndex }
	::= { pm200frs02MondownRmonNonunicastCounterClientOutputTable 1 }


Pm200frs02MondownRmonNonunicastCounterClientOutputEntry ::=
	SEQUENCE {
	pm200frs02MondownRmonNonunicastCounterClientOutputIndex
		INTEGER,
	pm200frs02MondownRmonNonunicastCounterClientOutputValuePortn
		Counter64,
	pm200frs02MondownRmonNonunicastCounterClientOutputErrorPortn
		EkiOnOff,
	pm200frs02MondownRmonNonunicastCounterClientOutputOverloadPortn
		EkiOnOff
	}


pm200frs02MondownRmonNonunicastCounterClientOutputIndex OBJECT-TYPE
	SYNTAX  INTEGER(0..128)
	MAX-ACCESS  read-only
	STATUS current
	DESCRIPTION
        "
        Index definition for the pm200frs02MondownRmonNonunicastCounterClientOutput
        table
        "
	::= { pm200frs02MondownRmonNonunicastCounterClientOutputEntry 1 }


pm200frs02MondownRmonNonunicastCounterClientOutputValuePortn OBJECT-TYPE
	SYNTAX  Counter64
	MAX-ACCESS read-only
	STATUS current
	DESCRIPTION
        "
        Client Output Non Unicast Packets
        :This counter is increased each
        time a Non-Unicast packet is transmitted
        on the client port  <Help>  This
        counter gives the number of Non-Unicast
        packets transmitted on the client
        port
        "
	::= { pm200frs02MondownRmonNonunicastCounterClientOutputEntry 2 }


pm200frs02MondownRmonNonunicastCounterClientOutputErrorPortn OBJECT-TYPE
	SYNTAX  EkiOnOff
	MAX-ACCESS read-only
	STATUS current
	DESCRIPTION
        "
        Non Unicast Counter Error :This
        OID when set indicates the Non-Unicast
        counter value is invalid on client
        port
        "
	::= { pm200frs02MondownRmonNonunicastCounterClientOutputEntry 3 }


pm200frs02MondownRmonNonunicastCounterClientOutputOverloadPortn OBJECT-TYPE
	SYNTAX  EkiOnOff
	MAX-ACCESS read-only
	STATUS current
	DESCRIPTION
        "
        Non Unicast Counter Overload :This
        OID when set indicates a Non-Unicast
        counter overload on client port
        "
	::= { pm200frs02MondownRmonNonunicastCounterClientOutputEntry 4 }







--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pm200frs02Mesrsynth0 OBJECT-TYPE
	  SYNTAX EkiMeasureType
	  MAX-ACCESS read-only
	  STATUS deprecated
	  DESCRIPTION
        "
        Not Used :
        "
	  ::= { pm200frs02MesrOther 0 }



pm200frs02Mesrsynth1 OBJECT-TYPE
	  SYNTAX EkiMeasureType
	  MAX-ACCESS read-only
	  STATUS deprecated
	  DESCRIPTION
        "
        Not Used :
        "
	  ::= { pm200frs02MesrOther 1 }



--- *****************************************************
---     LEAF for the pmIntervalNumber article
--- *****************************************************

pm200frs02MesrpmIntervalNumber OBJECT-TYPE
	  SYNTAX Unsigned32 (0..65535)
	  MAX-ACCESS read-only
	  STATUS current
	  DESCRIPTION
        "
        PM Interval Counter :
        "
	  ::= { pm200frs02MesrOther 7 }



--- *****************************************************
---     LEAF for the clientCfpTemp article
--- *****************************************************

pm200frs02MesrclientCfpTemp OBJECT-TYPE
	  SYNTAX Unsigned32 (0..65535)
	  MAX-ACCESS read-only
	  STATUS current
	  DESCRIPTION
        "
        Client Trscv Temperature :This
        OID gives the temperature value
        of the Client Transceiver, read
        from the DDM (Digital Diagnostic
        Monitoring) (Temperature = AV_S16/256)
        (Unit = C) <Help> This Measure
         gives the temperature value of
        the Client Transceiver
        "
	  ::= { pm200frs02MesrClient 8 }



--- *****************************************************
---     LEAF for the clientCfp3v3Voltage article
--- *****************************************************

pm200frs02MesrclientCfp3v3Voltage OBJECT-TYPE
	  SYNTAX Unsigned32 (0..65535)
	  MAX-ACCESS read-only
	  STATUS current
	  DESCRIPTION
        "
        Client Trscv Voltage :This OID
        gives the 3V3 voltage value of
         the Client Transceiver, read from
        the DDM (Digital Diagnostic Monitoring)
         (Voltage = AV_U16/10000) (Unit
        = V) <Help> This Measure gives
         the 3V3 voltage value of the Client
        Transceiver
        "
	  ::= { pm200frs02MesrClient 9 }



--- *****************************************************
---     LEAF for the clientSoaBiasCurrent article
--- *****************************************************

pm200frs02MesrclientSoaBiasCurrent OBJECT-TYPE
	  SYNTAX Unsigned32 (0..65535)
	  MAX-ACCESS read-only
	  STATUS current
	  DESCRIPTION
        "
        Client Trscv SOA Bias :This OID
        gives the SOA bias value of the
        Client Transceiver, read from the
        DDM (Digital Diagnostic Monitoring)
         (Bias = AV_U16/500) (Unit = mA)
        <Help> This Measure gives the SOA
        bias value of the Client Transceiver
        "
	  ::= { pm200frs02MesrClient 10 }



--- *****************************************************
---     LEAF for the lineMsaTemp article
--- *****************************************************

pm200frs02MesrlineMsaTemp OBJECT-TYPE
	  SYNTAX Unsigned32 (0..65535)
	  MAX-ACCESS read-only
	  STATUS current
	  DESCRIPTION
        "
        Line Trscv Temperature :This OID
        gives the temperature value of
         the Line Transceiver, read from
        the DDM (Digital Diagnostic Monitoring)
         (Temperature = AV_S16/256) (Unit
        = C) <Help> This Measure gives
         the temperature value of the Line
        Transceiver.This temperature must
        remain below 95 C for proper operation
        "
	  ::= { pm200frs02MesrLine 12 }



--- *****************************************************
---     LEAF for the lineMsa3v3Voltage article
--- *****************************************************

pm200frs02MesrlineMsa3v3Voltage OBJECT-TYPE
	  SYNTAX Unsigned32 (0..65535)
	  MAX-ACCESS read-only
	  STATUS current
	  DESCRIPTION
        "
        Line Trscv Voltage :This OID gives
        the 3V3 voltage value of the Line
        Transceiver, read from the DDM
         (Digital Diagnostic Monitoring)
        (Voltage = AV_U16/10000) (Unit
         = V) <Help> This Measure gives
        the 3V3 voltage value of the Line
        Transceiver
        "
	  ::= { pm200frs02MesrLine 13 }



--- *****************************************************
---     LEAF for the lineSoaBiasCurrent article
--- *****************************************************

pm200frs02MesrlineSoaBiasCurrent OBJECT-TYPE
	  SYNTAX Unsigned32 (0..65535)
	  MAX-ACCESS read-only
	  STATUS current
	  DESCRIPTION
        "
        Line Trscv SOA Bias :This OID
         gives the SOA bias value of the
        Line Transceiver,read from the
         DDM (Digital Diagnostic Monitoring)
         (Bias = AV_U16/500) (Unit = mA)
        <Help> This Measure gives the SOA
        bias value of the Line Transceiver
        "
	  ::= { pm200frs02MesrLine 14 }



--- *********************************************************
---     TABLE for the pm200frs02MesrclientTxPwrMin articles
--- *********************************************************

pm200frs02MesrclientTxPwrMinTable OBJECT-TYPE
	SYNTAX  SEQUENCE OF Pm200frs02MesrclientTxPwrMinEntry
	MAX-ACCESS not-accessible
	STATUS current
	DESCRIPTION
        "
        List of pm200frs02MesrclientTxPwrMin
        Article
        "
	::= { pm200frs02MesrClient 16 }


pm200frs02MesrclientTxPwrMinEntry OBJECT-TYPE
	SYNTAX Pm200frs02MesrclientTxPwrMinEntry
	MAX-ACCESS not-accessible
	STATUS current
	DESCRIPTION
        "
        Row definition for the pm200frs02MesrclientTxPwrMin
        table
        "
	INDEX   { pm200frs02MesrclientTxPwrMinIndex }
	::= { pm200frs02MesrclientTxPwrMinTable 1 }


Pm200frs02MesrclientTxPwrMinEntry ::=
	SEQUENCE {
	pm200frs02MesrclientTxPwrMinIndex
		INTEGER,
	pm200frs02MesrclientTxPwrMinPortn
		INTEGER
	}


pm200frs02MesrclientTxPwrMinIndex OBJECT-TYPE
	SYNTAX  INTEGER(0..128)
	MAX-ACCESS  read-only
	STATUS current
	DESCRIPTION
        "
        Index definition for the pm200frs02MesrclientTxPwrMin
        table
        "
	::= { pm200frs02MesrclientTxPwrMinEntry 1 }


pm200frs02MesrclientTxPwrMinPortn OBJECT-TYPE
	SYNTAX  INTEGER (0..65535)
	MAX-ACCESS read-only
	STATUS current
	DESCRIPTION
        "
        Min Client Trscv Tx Power Per
         Lane :This OID gives the minimum
        transmit power value among the
         network lanes of the Client Transceiver,
        read from the DDM (Digital Diagnostic
        Monitoring) (Power = 10*log(AV_U16)-40)
        (Unit = dBm) <Help> This Measure
        gives the minimum transmit power
        value among the network lanes of
        the Client Transceiver
        "
	::= { pm200frs02MesrclientTxPwrMinEntry 2 }


--- *********************************************************
---     TABLE for the pm200frs02MesrclientRxPwrMin articles
--- *********************************************************

pm200frs02MesrclientRxPwrMinTable OBJECT-TYPE
	SYNTAX  SEQUENCE OF Pm200frs02MesrclientRxPwrMinEntry
	MAX-ACCESS not-accessible
	STATUS current
	DESCRIPTION
        "
        List of pm200frs02MesrclientRxPwrMin
        Article
        "
	::= { pm200frs02MesrClient 48 }


pm200frs02MesrclientRxPwrMinEntry OBJECT-TYPE
	SYNTAX Pm200frs02MesrclientRxPwrMinEntry
	MAX-ACCESS not-accessible
	STATUS current
	DESCRIPTION
        "
        Row definition for the pm200frs02MesrclientRxPwrMin
        table
        "
	INDEX   { pm200frs02MesrclientRxPwrMinIndex }
	::= { pm200frs02MesrclientRxPwrMinTable 1 }


Pm200frs02MesrclientRxPwrMinEntry ::=
	SEQUENCE {
	pm200frs02MesrclientRxPwrMinIndex
		INTEGER,
	pm200frs02MesrclientRxPwrMinPortn
		INTEGER
	}


pm200frs02MesrclientRxPwrMinIndex OBJECT-TYPE
	SYNTAX  INTEGER(0..128)
	MAX-ACCESS  read-only
	STATUS current
	DESCRIPTION
        "
        Index definition for the pm200frs02MesrclientRxPwrMin
        table
        "
	::= { pm200frs02MesrclientRxPwrMinEntry 1 }


pm200frs02MesrclientRxPwrMinPortn OBJECT-TYPE
	SYNTAX  INTEGER (0..65535)
	MAX-ACCESS read-only
	STATUS current
	DESCRIPTION
        "
        Min Client Trscv Rx Power Per
         Lane :This OID gives the minimum
        receive power value among the network
        lanes of the Client Transceiver,
        read from the DDM (Digital Diagnostic
        Monitoring) (Power = 10*log(AV_U16)-40)
        (Unit = dBm) <Help> This Measure
        gives the minimum receive power
        value among the network lanes of
        the Client Transceiver
        "
	::= { pm200frs02MesrclientRxPwrMinEntry 2 }


--- *********************************************************
---     TABLE for the pm200frs02MesrclientTxPwrMax articles
--- *********************************************************

pm200frs02MesrclientTxPwrMaxTable OBJECT-TYPE
	SYNTAX  SEQUENCE OF Pm200frs02MesrclientTxPwrMaxEntry
	MAX-ACCESS not-accessible
	STATUS current
	DESCRIPTION
        "
        List of pm200frs02MesrclientTxPwrMax
        Article
        "
	::= { pm200frs02MesrClient 80 }


pm200frs02MesrclientTxPwrMaxEntry OBJECT-TYPE
	SYNTAX Pm200frs02MesrclientTxPwrMaxEntry
	MAX-ACCESS not-accessible
	STATUS current
	DESCRIPTION
        "
        Row definition for the pm200frs02MesrclientTxPwrMax
        table
        "
	INDEX   { pm200frs02MesrclientTxPwrMaxIndex }
	::= { pm200frs02MesrclientTxPwrMaxTable 1 }


Pm200frs02MesrclientTxPwrMaxEntry ::=
	SEQUENCE {
	pm200frs02MesrclientTxPwrMaxIndex
		INTEGER,
	pm200frs02MesrclientTxPwrMaxPortn
		INTEGER
	}


pm200frs02MesrclientTxPwrMaxIndex OBJECT-TYPE
	SYNTAX  INTEGER(0..128)
	MAX-ACCESS  read-only
	STATUS current
	DESCRIPTION
        "
        Index definition for the pm200frs02MesrclientTxPwrMax
        table
        "
	::= { pm200frs02MesrclientTxPwrMaxEntry 1 }


pm200frs02MesrclientTxPwrMaxPortn OBJECT-TYPE
	SYNTAX  INTEGER (0..65535)
	MAX-ACCESS read-only
	STATUS current
	DESCRIPTION
        "
        Max Client Trscv Tx Power Per
         Lane :This OID gives the maximum
        transmit power value among the
         network lanes of the Client Transceiver,
        read from the DDM (Digital Diagnostic
        Monitoring)  (Power = 10*log(AV_U16)-40)
        (Unit = dBm) <Help> This Measure
        gives the maximum transmit power
        value among the network lanes of
        the Client Transceiver
        "
	::= { pm200frs02MesrclientTxPwrMaxEntry 2 }


--- *********************************************************
---     TABLE for the pm200frs02MesrclientRxPwrMax articles
--- *********************************************************

pm200frs02MesrclientRxPwrMaxTable OBJECT-TYPE
	SYNTAX  SEQUENCE OF Pm200frs02MesrclientRxPwrMaxEntry
	MAX-ACCESS not-accessible
	STATUS current
	DESCRIPTION
        "
        List of pm200frs02MesrclientRxPwrMax
        Article
        "
	::= { pm200frs02MesrClient 112 }


pm200frs02MesrclientRxPwrMaxEntry OBJECT-TYPE
	SYNTAX Pm200frs02MesrclientRxPwrMaxEntry
	MAX-ACCESS not-accessible
	STATUS current
	DESCRIPTION
        "
        Row definition for the pm200frs02MesrclientRxPwrMax
        table
        "
	INDEX   { pm200frs02MesrclientRxPwrMaxIndex }
	::= { pm200frs02MesrclientRxPwrMaxTable 1 }


Pm200frs02MesrclientRxPwrMaxEntry ::=
	SEQUENCE {
	pm200frs02MesrclientRxPwrMaxIndex
		INTEGER,
	pm200frs02MesrclientRxPwrMaxPortn
		INTEGER
	}


pm200frs02MesrclientRxPwrMaxIndex OBJECT-TYPE
	SYNTAX  INTEGER(0..128)
	MAX-ACCESS  read-only
	STATUS current
	DESCRIPTION
        "
        Index definition for the pm200frs02MesrclientRxPwrMax
        table
        "
	::= { pm200frs02MesrclientRxPwrMaxEntry 1 }


pm200frs02MesrclientRxPwrMaxPortn OBJECT-TYPE
	SYNTAX  INTEGER (0..65535)
	MAX-ACCESS read-only
	STATUS current
	DESCRIPTION
        "
        Max Client Trscv Rx Power Per
         Lane :This OID gives the maximum
        receive power value among the network
        lanes of the Client Transceiver,
        read in the DDM (Digital Diagnostic
        Monitoring) (Power = 10*log(AV_U16)-40)
        (Unit = dBm) <Help> This Measure
        gives the maximum receive power
        value among the network lanes of
        the Client Transceiver
        "
	::= { pm200frs02MesrclientRxPwrMaxEntry 2 }


--- *********************************************************
---     TABLE for the pm200frs02MesrlineNetTxLaserOutputPwr articles
--- *********************************************************

pm200frs02MesrlineNetTxLaserOutputPwrTable OBJECT-TYPE
	SYNTAX  SEQUENCE OF Pm200frs02MesrlineNetTxLaserOutputPwrEntry
	MAX-ACCESS not-accessible
	STATUS current
	DESCRIPTION
        "
        List of pm200frs02MesrlineNetTxLaserOutputPwr
        Article
        "
	::= { pm200frs02MesrLine 144 }


pm200frs02MesrlineNetTxLaserOutputPwrEntry OBJECT-TYPE
	SYNTAX Pm200frs02MesrlineNetTxLaserOutputPwrEntry
	MAX-ACCESS not-accessible
	STATUS current
	DESCRIPTION
        "
        Row definition for the pm200frs02MesrlineNetTxLaserOutputPwr
        table
        "
	INDEX   { pm200frs02MesrlineNetTxLaserOutputPwrIndex }
	::= { pm200frs02MesrlineNetTxLaserOutputPwrTable 1 }


Pm200frs02MesrlineNetTxLaserOutputPwrEntry ::=
	SEQUENCE {
	pm200frs02MesrlineNetTxLaserOutputPwrIndex
		INTEGER,
	pm200frs02MesrlineNetTxLaserOutputPwrPortn
		INTEGER
	}


pm200frs02MesrlineNetTxLaserOutputPwrIndex OBJECT-TYPE
	SYNTAX  INTEGER(0..128)
	MAX-ACCESS  read-only
	STATUS current
	DESCRIPTION
        "
        Index definition for the pm200frs02MesrlineNetTxLaserOutputPwr
        table
        "
	::= { pm200frs02MesrlineNetTxLaserOutputPwrEntry 1 }


pm200frs02MesrlineNetTxLaserOutputPwrPortn OBJECT-TYPE
	SYNTAX  INTEGER (0..65535)
	MAX-ACCESS read-only
	STATUS current
	DESCRIPTION
        "
        Current Line Trscv Tx Power :This
        OID gives the Tx Laser transmit
        power value of the Line Transceiver,
        read in the DDM (Digital Diagnostic
        Monitoring) (Power = AV_S16/100)
        (Unit = dBm) <Help> This Measure
        gives the Tx Laser transmit power
        value of the Line Transceiver
        "
	::= { pm200frs02MesrlineNetTxLaserOutputPwrEntry 2 }


--- *********************************************************
---     TABLE for the pm200frs02MesrlineNetTxLaserTemp articles
--- *********************************************************

pm200frs02MesrlineNetTxLaserTempTable OBJECT-TYPE
	SYNTAX  SEQUENCE OF Pm200frs02MesrlineNetTxLaserTempEntry
	MAX-ACCESS not-accessible
	STATUS current
	DESCRIPTION
        "
        List of pm200frs02MesrlineNetTxLaserTemp
        Article
        "
	::= { pm200frs02MesrLine 148 }


pm200frs02MesrlineNetTxLaserTempEntry OBJECT-TYPE
	SYNTAX Pm200frs02MesrlineNetTxLaserTempEntry
	MAX-ACCESS not-accessible
	STATUS current
	DESCRIPTION
        "
        Row definition for the pm200frs02MesrlineNetTxLaserTemp
        table
        "
	INDEX   { pm200frs02MesrlineNetTxLaserTempIndex }
	::= { pm200frs02MesrlineNetTxLaserTempTable 1 }


Pm200frs02MesrlineNetTxLaserTempEntry ::=
	SEQUENCE {
	pm200frs02MesrlineNetTxLaserTempIndex
		INTEGER,
	pm200frs02MesrlineNetTxLaserTempPortn
		INTEGER
	}


pm200frs02MesrlineNetTxLaserTempIndex OBJECT-TYPE
	SYNTAX  INTEGER(0..128)
	MAX-ACCESS  read-only
	STATUS current
	DESCRIPTION
        "
        Index definition for the pm200frs02MesrlineNetTxLaserTemp
        table
        "
	::= { pm200frs02MesrlineNetTxLaserTempEntry 1 }


pm200frs02MesrlineNetTxLaserTempPortn OBJECT-TYPE
	SYNTAX  INTEGER (0..65535)
	MAX-ACCESS read-only
	STATUS current
	DESCRIPTION
        "
        Current Line Trscv Tx Laser Temperature
        :This OID gives the Tx Laser Temperature
        value of the Line Transceiver,
         read from the DDM (Digital Diagnostic
        Monitoring) (Temperature = AV_S16/256)
        (Unit = C) <Help> This Measure
         gives the Tx Laser Temperature
        value of the Line Transceiver
        "
	::= { pm200frs02MesrlineNetTxLaserTempEntry 2 }


--- *********************************************************
---     TABLE for the pm200frs02MesrlineNetTxBiasCurrent articles
--- *********************************************************

pm200frs02MesrlineNetTxBiasCurrentTable OBJECT-TYPE
	SYNTAX  SEQUENCE OF Pm200frs02MesrlineNetTxBiasCurrentEntry
	MAX-ACCESS not-accessible
	STATUS current
	DESCRIPTION
        "
        List of pm200frs02MesrlineNetTxBiasCurrent
        Article
        "
	::= { pm200frs02MesrLine 152 }


pm200frs02MesrlineNetTxBiasCurrentEntry OBJECT-TYPE
	SYNTAX Pm200frs02MesrlineNetTxBiasCurrentEntry
	MAX-ACCESS not-accessible
	STATUS current
	DESCRIPTION
        "
        Row definition for the pm200frs02MesrlineNetTxBiasCurrent
        table
        "
	INDEX   { pm200frs02MesrlineNetTxBiasCurrentIndex }
	::= { pm200frs02MesrlineNetTxBiasCurrentTable 1 }


Pm200frs02MesrlineNetTxBiasCurrentEntry ::=
	SEQUENCE {
	pm200frs02MesrlineNetTxBiasCurrentIndex
		INTEGER,
	pm200frs02MesrlineNetTxBiasCurrentPortn
		INTEGER
	}


pm200frs02MesrlineNetTxBiasCurrentIndex OBJECT-TYPE
	SYNTAX  INTEGER(0..128)
	MAX-ACCESS  read-only
	STATUS current
	DESCRIPTION
        "
        Index definition for the pm200frs02MesrlineNetTxBiasCurrent
        table
        "
	::= { pm200frs02MesrlineNetTxBiasCurrentEntry 1 }


pm200frs02MesrlineNetTxBiasCurrentPortn OBJECT-TYPE
	SYNTAX  INTEGER (0..65535)
	MAX-ACCESS read-only
	STATUS current
	DESCRIPTION
        "
        Current Line Trscv Tx Laser Bias
        :This OID gives the Tx Laser Bias
        value of the Line Transceiver,
         read from the DDM (Digital Diagnostic
        Monitoring) (Bias = AV_S16/10)
         (Unit = mA) <Help> This Measure
        gives the Tx Laser Bias value of
        the Line Transceiver
        "
	::= { pm200frs02MesrlineNetTxBiasCurrentEntry 2 }


--- *********************************************************
---     TABLE for the pm200frs02MesrlineNetRxInputPwr articles
--- *********************************************************

pm200frs02MesrlineNetRxInputPwrTable OBJECT-TYPE
	SYNTAX  SEQUENCE OF Pm200frs02MesrlineNetRxInputPwrEntry
	MAX-ACCESS not-accessible
	STATUS current
	DESCRIPTION
        "
        List of pm200frs02MesrlineNetRxInputPwr
        Article
        "
	::= { pm200frs02MesrLine 156 }


pm200frs02MesrlineNetRxInputPwrEntry OBJECT-TYPE
	SYNTAX Pm200frs02MesrlineNetRxInputPwrEntry
	MAX-ACCESS not-accessible
	STATUS current
	DESCRIPTION
        "
        Row definition for the pm200frs02MesrlineNetRxInputPwr
        table
        "
	INDEX   { pm200frs02MesrlineNetRxInputPwrIndex }
	::= { pm200frs02MesrlineNetRxInputPwrTable 1 }


Pm200frs02MesrlineNetRxInputPwrEntry ::=
	SEQUENCE {
	pm200frs02MesrlineNetRxInputPwrIndex
		INTEGER,
	pm200frs02MesrlineNetRxInputPwrPortn
		INTEGER
	}


pm200frs02MesrlineNetRxInputPwrIndex OBJECT-TYPE
	SYNTAX  INTEGER(0..128)
	MAX-ACCESS  read-only
	STATUS current
	DESCRIPTION
        "
        Index definition for the pm200frs02MesrlineNetRxInputPwr
        table
        "
	::= { pm200frs02MesrlineNetRxInputPwrEntry 1 }


pm200frs02MesrlineNetRxInputPwrPortn OBJECT-TYPE
	SYNTAX  INTEGER (0..65535)
	MAX-ACCESS read-only
	STATUS current
	DESCRIPTION
        "
        Current Line Trscv Rx Power :This
        OID gives the Receive power value
        of the Line Transceiver, read in
        the DDM (Digital Diagnostic Monitoring)
        (Power = AV_S16/100) (Unit = dBm)
        <Help> This Measure gives the Receive
        power value of the Line Transceiver
        "
	::= { pm200frs02MesrlineNetRxInputPwrEntry 2 }


--- *********************************************************
---     TABLE for the pm200frs02MesrlineResidualChromaticDisp articles
--- *********************************************************

pm200frs02MesrlineResidualChromaticDispTable OBJECT-TYPE
	SYNTAX  SEQUENCE OF Pm200frs02MesrlineResidualChromaticDispEntry
	MAX-ACCESS not-accessible
	STATUS current
	DESCRIPTION
        "
        List of pm200frs02MesrlineResidualChromaticDisp
        Article
        "
	::= { pm200frs02MesrLine 160 }


pm200frs02MesrlineResidualChromaticDispEntry OBJECT-TYPE
	SYNTAX Pm200frs02MesrlineResidualChromaticDispEntry
	MAX-ACCESS not-accessible
	STATUS current
	DESCRIPTION
        "
        Row definition for the pm200frs02MesrlineResidualChromaticDisp
        table
        "
	INDEX   { pm200frs02MesrlineResidualChromaticDispIndex }
	::= { pm200frs02MesrlineResidualChromaticDispTable 1 }


Pm200frs02MesrlineResidualChromaticDispEntry ::=
	SEQUENCE {
	pm200frs02MesrlineResidualChromaticDispIndex
		INTEGER,
	pm200frs02MesrlineResidualChromaticDispPortn
		INTEGER
	}


pm200frs02MesrlineResidualChromaticDispIndex OBJECT-TYPE
	SYNTAX  INTEGER(0..128)
	MAX-ACCESS  read-only
	STATUS current
	DESCRIPTION
        "
        Index definition for the pm200frs02MesrlineResidualChromaticDisp
        table
        "
	::= { pm200frs02MesrlineResidualChromaticDispEntry 1 }


pm200frs02MesrlineResidualChromaticDispPortn OBJECT-TYPE
	SYNTAX  INTEGER (0..65535)
	MAX-ACCESS read-only
	STATUS current
	DESCRIPTION
        "
        Current Residual Chromatic Dispersion
        :This OID gives the current Residual
        Chromatic Dispersion on the Line
        interface (Dispersion = AV_S16*(-2))
          (Unit = ps/nm)<Help> This measure
        gives the current Residual Chromatic
        Dispersion on the Line interface.
        "
	::= { pm200frs02MesrlineResidualChromaticDispEntry 2 }


--- *********************************************************
---     TABLE for the pm200frs02MesrlineDiffGroupDelay articles
--- *********************************************************

pm200frs02MesrlineDiffGroupDelayTable OBJECT-TYPE
	SYNTAX  SEQUENCE OF Pm200frs02MesrlineDiffGroupDelayEntry
	MAX-ACCESS not-accessible
	STATUS current
	DESCRIPTION
        "
        List of pm200frs02MesrlineDiffGroupDelay
        Article
        "
	::= { pm200frs02MesrLine 164 }


pm200frs02MesrlineDiffGroupDelayEntry OBJECT-TYPE
	SYNTAX Pm200frs02MesrlineDiffGroupDelayEntry
	MAX-ACCESS not-accessible
	STATUS current
	DESCRIPTION
        "
        Row definition for the pm200frs02MesrlineDiffGroupDelay
        table
        "
	INDEX   { pm200frs02MesrlineDiffGroupDelayIndex }
	::= { pm200frs02MesrlineDiffGroupDelayTable 1 }


Pm200frs02MesrlineDiffGroupDelayEntry ::=
	SEQUENCE {
	pm200frs02MesrlineDiffGroupDelayIndex
		INTEGER,
	pm200frs02MesrlineDiffGroupDelayPortn
		INTEGER
	}


pm200frs02MesrlineDiffGroupDelayIndex OBJECT-TYPE
	SYNTAX  INTEGER(0..128)
	MAX-ACCESS  read-only
	STATUS current
	DESCRIPTION
        "
        Index definition for the pm200frs02MesrlineDiffGroupDelay
        table
        "
	::= { pm200frs02MesrlineDiffGroupDelayEntry 1 }


pm200frs02MesrlineDiffGroupDelayPortn OBJECT-TYPE
	SYNTAX  INTEGER (0..65535)
	MAX-ACCESS read-only
	STATUS current
	DESCRIPTION
        "
        Current Differential Group Delay
        :This OID gives the current Differential
        Group Delay on the Line interface
         (Delay = AV_S16)    (Unit = ps)<Help>
        This measure gives the current
         Differential Group Delay on the
        Line interface.
        "
	::= { pm200frs02MesrlineDiffGroupDelayEntry 2 }


--- *********************************************************
---     TABLE for the pm200frs02MesrlineQFactor articles
--- *********************************************************

pm200frs02MesrlineQFactorTable OBJECT-TYPE
	SYNTAX  SEQUENCE OF Pm200frs02MesrlineQFactorEntry
	MAX-ACCESS not-accessible
	STATUS current
	DESCRIPTION
        "
        List of pm200frs02MesrlineQFactor
        Article
        "
	::= { pm200frs02MesrLine 168 }


pm200frs02MesrlineQFactorEntry OBJECT-TYPE
	SYNTAX Pm200frs02MesrlineQFactorEntry
	MAX-ACCESS not-accessible
	STATUS current
	DESCRIPTION
        "
        Row definition for the pm200frs02MesrlineQFactor
        table
        "
	INDEX   { pm200frs02MesrlineQFactorIndex }
	::= { pm200frs02MesrlineQFactorTable 1 }


Pm200frs02MesrlineQFactorEntry ::=
	SEQUENCE {
	pm200frs02MesrlineQFactorIndex
		INTEGER,
	pm200frs02MesrlineQFactorPortn
		INTEGER
	}


pm200frs02MesrlineQFactorIndex OBJECT-TYPE
	SYNTAX  INTEGER(0..128)
	MAX-ACCESS  read-only
	STATUS current
	DESCRIPTION
        "
        Index definition for the pm200frs02MesrlineQFactor
        table
        "
	::= { pm200frs02MesrlineQFactorEntry 1 }


pm200frs02MesrlineQFactorPortn OBJECT-TYPE
	SYNTAX  INTEGER (0..65535)
	MAX-ACCESS read-only
	STATUS current
	DESCRIPTION
        "
        Current Q Factor :This OID gives
        the current Q Factor on the Line
        interface  (Q Factor = AV_U16)
           (Unit = dB) <Help> This measure
        gives the current Q Factor on the
        Line interface.
        "
	::= { pm200frs02MesrlineQFactorEntry 2 }


--- *********************************************************
---     TABLE for the pm200frs02MesrlineCarrierFreqOffset articles
--- *********************************************************

pm200frs02MesrlineCarrierFreqOffsetTable OBJECT-TYPE
	SYNTAX  SEQUENCE OF Pm200frs02MesrlineCarrierFreqOffsetEntry
	MAX-ACCESS not-accessible
	STATUS current
	DESCRIPTION
        "
        List of pm200frs02MesrlineCarrierFreqOffset
        Article
        "
	::= { pm200frs02MesrLine 172 }


pm200frs02MesrlineCarrierFreqOffsetEntry OBJECT-TYPE
	SYNTAX Pm200frs02MesrlineCarrierFreqOffsetEntry
	MAX-ACCESS not-accessible
	STATUS current
	DESCRIPTION
        "
        Row definition for the pm200frs02MesrlineCarrierFreqOffset
        table
        "
	INDEX   { pm200frs02MesrlineCarrierFreqOffsetIndex }
	::= { pm200frs02MesrlineCarrierFreqOffsetTable 1 }


Pm200frs02MesrlineCarrierFreqOffsetEntry ::=
	SEQUENCE {
	pm200frs02MesrlineCarrierFreqOffsetIndex
		INTEGER,
	pm200frs02MesrlineCarrierFreqOffsetPortn
		INTEGER
	}


pm200frs02MesrlineCarrierFreqOffsetIndex OBJECT-TYPE
	SYNTAX  INTEGER(0..128)
	MAX-ACCESS  read-only
	STATUS current
	DESCRIPTION
        "
        Index definition for the pm200frs02MesrlineCarrierFreqOffset
        table
        "
	::= { pm200frs02MesrlineCarrierFreqOffsetEntry 1 }


pm200frs02MesrlineCarrierFreqOffsetPortn OBJECT-TYPE
	SYNTAX  INTEGER (0..65535)
	MAX-ACCESS read-only
	STATUS current
	DESCRIPTION
        "
        Current Carrier Frequency Offset
        :This OID gives the current Carrier
        Frequency Offset on the Line interface
         (Offset = AV_S16)   (Unit = MHz)<Help>
        This measure gives the current
         Carrier Frequency Offset on the
        Line interface.
        "
	::= { pm200frs02MesrlineCarrierFreqOffsetEntry 2 }


--- *********************************************************
---     TABLE for the pm200frs02MesrlineOsnr articles
--- *********************************************************

pm200frs02MesrlineOsnrTable OBJECT-TYPE
	SYNTAX  SEQUENCE OF Pm200frs02MesrlineOsnrEntry
	MAX-ACCESS not-accessible
	STATUS current
	DESCRIPTION
        "
        List of pm200frs02MesrlineOsnr
        Article
        "
	::= { pm200frs02MesrLine 176 }


pm200frs02MesrlineOsnrEntry OBJECT-TYPE
	SYNTAX Pm200frs02MesrlineOsnrEntry
	MAX-ACCESS not-accessible
	STATUS current
	DESCRIPTION
        "
        Row definition for the pm200frs02MesrlineOsnr
        table
        "
	INDEX   { pm200frs02MesrlineOsnrIndex }
	::= { pm200frs02MesrlineOsnrTable 1 }


Pm200frs02MesrlineOsnrEntry ::=
	SEQUENCE {
	pm200frs02MesrlineOsnrIndex
		INTEGER,
	pm200frs02MesrlineOsnrPortn
		INTEGER
	}


pm200frs02MesrlineOsnrIndex OBJECT-TYPE
	SYNTAX  INTEGER(0..128)
	MAX-ACCESS  read-only
	STATUS current
	DESCRIPTION
        "
        Index definition for the pm200frs02MesrlineOsnr
        table
        "
	::= { pm200frs02MesrlineOsnrEntry 1 }


pm200frs02MesrlineOsnrPortn OBJECT-TYPE
	SYNTAX  INTEGER (0..65535)
	MAX-ACCESS read-only
	STATUS current
	DESCRIPTION
        "
        Current OSNR :This OID gives the
        current OSNR on the Line interface
          (OSNR = AV_S16/10) (Unit = dB)<Help>
        This measure gives the current
         OSNR on the Line interface.
        "
	::= { pm200frs02MesrlineOsnrEntry 2 }


--- *****************************************************
---     LEAF for the lineNetTxLaserOutputPwrAverage article
--- *****************************************************

pm200frs02MesrlineNetTxLaserOutputPwrAverage OBJECT-TYPE
	  SYNTAX Unsigned32 (0..65535)
	  MAX-ACCESS read-only
	  STATUS current
	  DESCRIPTION
        "
        Average Line Trscv Tx Power :This
        OID gives the average Tx Laser
         transmit power value among the
        network lanes of the Line Transceiver,
        read in the DDM (Digital Diagnostic
        Monitoring)  (Power = AV_S16/100)
        (Unit = dBm) <Help> This Measure
        gives the average Tx Laser transmit
        power value among the network lanes
        of the Line Transceiver
        "
	  ::= { pm200frs02MesrOther 196 }



--- *****************************************************
---     LEAF for the lineNetTxLaserTempAverage article
--- *****************************************************

pm200frs02MesrlineNetTxLaserTempAverage OBJECT-TYPE
	  SYNTAX Unsigned32 (0..65535)
	  MAX-ACCESS read-only
	  STATUS current
	  DESCRIPTION
        "
        Average Line Trscv Tx Laser Temperature
        :This OID gives the average Tx
         Laser Temperature value among
         the network lanes of the Line
         Transceiver, read from the DDM
        (Digital Diagnostic Monitoring)
        (Temperature = AV_S16/256) (Unit
        = C) <Help> This Measure gives
         the average Tx Laser Temperature
        value among the network lanes of
        the Line Transceiver
        "
	  ::= { pm200frs02MesrOther 197 }



--- *****************************************************
---     LEAF for the lineNetTxBiasCurrentAverage article
--- *****************************************************

pm200frs02MesrlineNetTxBiasCurrentAverage OBJECT-TYPE
	  SYNTAX Unsigned32 (0..65535)
	  MAX-ACCESS read-only
	  STATUS current
	  DESCRIPTION
        "
        Average Line Trscv Tx Laser Bias
        :This OID gives the average Tx
         Laser Bias value among the network
        lanes of the Line Transceiver,
         read from the DDM (Digital Diagnostic
        Monitoring) (Bias = AV_S16/10)
         (Unit = mA) <Help> This Measure
        gives the average Tx Laser Bias
        value among the network lanes of
        the Line Transceiver
        "
	  ::= { pm200frs02MesrOther 198 }



--- *****************************************************
---     LEAF for the lineNetRxInputPwrAverage article
--- *****************************************************

pm200frs02MesrlineNetRxInputPwrAverage OBJECT-TYPE
	  SYNTAX Unsigned32 (0..65535)
	  MAX-ACCESS read-only
	  STATUS current
	  DESCRIPTION
        "
        Average Line Trscv Rx Power :This
        OID gives the average Receive power
        value among the network lanes of
        the Line Transceiver, read in the
        DDM (Digital Diagnostic Monitoring)
        (Power = AV_S16/100) (Unit = dBm)
        <Help> This Measure gives the average
        Receive power value among the network
        lanes of the Line Transceiver
        "
	  ::= { pm200frs02MesrOther 199 }



--- *****************************************************
---     LEAF for the lineResidualChromaticDispAverage article
--- *****************************************************

pm200frs02MesrlineResidualChromaticDispAverage OBJECT-TYPE
	  SYNTAX Unsigned32 (0..65535)
	  MAX-ACCESS read-only
	  STATUS current
	  DESCRIPTION
        "
        Average Residual Chromatic Dispersion
        :This OID gives the average Residual
        Chromatic Dispersion on the Line
        interface since the last measure
        reset  (Dispersion = AV_S16*(-2))
         (Unit = ps/nm)<Help> This measure
        gives the average Residual Chromatic
        Dispersion on the Line interface
        since the last measure reset.
        "
	  ::= { pm200frs02MesrOther 200 }



--- *****************************************************
---     LEAF for the lineDiffGroupDelayAverage article
--- *****************************************************

pm200frs02MesrlineDiffGroupDelayAverage OBJECT-TYPE
	  SYNTAX Unsigned32 (0..65535)
	  MAX-ACCESS read-only
	  STATUS current
	  DESCRIPTION
        "
        Average Differential Group Delay
        :This OID gives the average Group
        Delay on the Line interface since
        the last measure reset (Delay =
        AV_S16)  (Unit = ps)<Help> This
        measure gives the average Differential
        Group Delay on the Line interface
        since the last measure reset.
        "
	  ::= { pm200frs02MesrOther 201 }



--- *****************************************************
---     LEAF for the lineQFactorAverage article
--- *****************************************************

pm200frs02MesrlineQFactorAverage OBJECT-TYPE
	  SYNTAX Unsigned32 (0..65535)
	  MAX-ACCESS read-only
	  STATUS current
	  DESCRIPTION
        "
        Average Q Factor :This OID gives
        the average Q Factor on the Line
        interface since the last measure
        reset (Q Factor = AV_U16)   (Unit
        = dB) <Help> This measure gives
        the average Q Factor on the Line
        interface since the last measure
        reset.
        "
	  ::= { pm200frs02MesrOther 202 }



--- *****************************************************
---     LEAF for the lineCarrierFreqOffsetAverage article
--- *****************************************************

pm200frs02MesrlineCarrierFreqOffsetAverage OBJECT-TYPE
	  SYNTAX Unsigned32 (0..65535)
	  MAX-ACCESS read-only
	  STATUS current
	  DESCRIPTION
        "
        Average Carrier Frequency Offset
        :This OID gives the average Carrier
        Frequency Offset on the Line interface
        since the last measure reset (Offset
        = AV_S16)  (Unit = MHz)<Help> This
        measure gives the average Carrier
        Frequency Offset on the Line interface
        since the last measure reset
        "
	  ::= { pm200frs02MesrOther 203 }



--- *****************************************************
---     LEAF for the lineOsnrAverage article
--- *****************************************************

pm200frs02MesrlineOsnrAverage OBJECT-TYPE
	  SYNTAX Unsigned32 (0..65535)
	  MAX-ACCESS read-only
	  STATUS current
	  DESCRIPTION
        "
        Average OSNR :This OID gives the
        average OSNR on the Line interface
        since the last measure reset (OSNR
        = AV_S16/10) (Unit = dB)<Help>
         This measure gives the average
        OSNR on the Line interface since
        the last measure reset.
        "
	  ::= { pm200frs02MesrOther 204 }



--- *****************************************************
---     LEAF for the lineNetTxLaserOutputPwrMin article
--- *****************************************************

pm200frs02MesrlineNetTxLaserOutputPwrMin OBJECT-TYPE
	  SYNTAX Unsigned32 (0..65535)
	  MAX-ACCESS read-only
	  STATUS current
	  DESCRIPTION
        "
        Min Line Trscv Tx Power :This
         OID gives the minimum Tx Laser
        transmit power value among the
         network lanes of the Line Transceiver,
        read in the DDM (Digital Diagnostic
        Monitoring)  (Power = AV_S16/100)
        (Unit = dBm) <Help> This Measure
        gives the minimum Tx Laser transmit
        power value among the network lanes
        of the Line Transceiver
        "
	  ::= { pm200frs02MesrOther 212 }



--- *****************************************************
---     LEAF for the lineNetTxLaserTempMin article
--- *****************************************************

pm200frs02MesrlineNetTxLaserTempMin OBJECT-TYPE
	  SYNTAX Unsigned32 (0..65535)
	  MAX-ACCESS read-only
	  STATUS current
	  DESCRIPTION
        "
        Min Line Trscv Tx Laser Temperature
        :This OID gives the minimum Tx
         Laser Temperature value among
         the network lanes of the Line
         Transceiver, read from the DDM
        (Digital Diagnostic Monitoring)
        (Temperature = AV_S16/256) (Unit
        = C) <Help> This Measure gives
         the minimum Tx Laser Temperature
        value among the network lanes of
        the Line Transceiver
        "
	  ::= { pm200frs02MesrOther 213 }



--- *****************************************************
---     LEAF for the lineNetTxBiasCurrentMin article
--- *****************************************************

pm200frs02MesrlineNetTxBiasCurrentMin OBJECT-TYPE
	  SYNTAX Unsigned32 (0..65535)
	  MAX-ACCESS read-only
	  STATUS current
	  DESCRIPTION
        "
        Min Line Trscv Tx Laser Bias :This
        OID gives the minimum Tx Laser
         Bias value among the network lanes
        of the Line Transceiver, read from
        the DDM (Digital Diagnostic Monitoring)
        (Bias = AV_S16/10) (Unit = mA)
         <Help> This Measure gives the
         minimum Tx Laser Bias value among
        the network lanes of the Line Transceiver
        "
	  ::= { pm200frs02MesrOther 214 }



--- *****************************************************
---     LEAF for the lineNetRxInputPwrMin article
--- *****************************************************

pm200frs02MesrlineNetRxInputPwrMin OBJECT-TYPE
	  SYNTAX Unsigned32 (0..65535)
	  MAX-ACCESS read-only
	  STATUS current
	  DESCRIPTION
        "
        Min Line Trscv Rx Power :This
         OID gives the minimum Receive
         power value among the network
         lanes of the Line Transceiver,
        read in the DDM (Digital Diagnostic
        Monitoring) (Power = AV_S16/100)
        (Unit = dBm) <Help> This Measure
        gives the minimum Receive power
        value among the network lanes of
        the Line Transceiver
        "
	  ::= { pm200frs02MesrOther 215 }



--- *****************************************************
---     LEAF for the lineResidualChromaticDispMin article
--- *****************************************************

pm200frs02MesrlineResidualChromaticDispMin OBJECT-TYPE
	  SYNTAX Unsigned32 (0..65535)
	  MAX-ACCESS read-only
	  STATUS current
	  DESCRIPTION
        "
        Min Residual Chromatic Dispersion
        :This OID gives the minimum Residual
        Chromatic Dispersion on the Line
        interface since the last measure
        reset (Dispersion = AV_S16*(-2))
          (Unit = ps/nm)<Help> This measure
        gives the minimum Residual Chromatic
        Dispersion on the Line interface
        since the last measure reset.
        "
	  ::= { pm200frs02MesrOther 216 }



--- *****************************************************
---     LEAF for the lineDiffGroupDelayMin article
--- *****************************************************

pm200frs02MesrlineDiffGroupDelayMin OBJECT-TYPE
	  SYNTAX Unsigned32 (0..65535)
	  MAX-ACCESS read-only
	  STATUS current
	  DESCRIPTION
        "
        Min Differential Group Delay :This
        OID gives the minimum Differential
        Group Delay  on the Line interface
        since the last measure reset (Delay
        = AV_S16)  (Unit = ps)<Help> This
        measure gives the minimum Differential
        Group Delay on the Line interface
        since the last measure reset.
        "
	  ::= { pm200frs02MesrOther 217 }



--- *****************************************************
---     LEAF for the lineQFactorMin article
--- *****************************************************

pm200frs02MesrlineQFactorMin OBJECT-TYPE
	  SYNTAX Unsigned32 (0..65535)
	  MAX-ACCESS read-only
	  STATUS current
	  DESCRIPTION
        "
        Min Q Factor :This OID gives the
        minimum Q Factor on the Line interface
        since the last measure reset (Q
        Factor = AV_U16)  (Unit = dB)<Help>
        This measure gives the minimum
         Q Factor on the Line interface
        since the last measure reset.
        "
	  ::= { pm200frs02MesrOther 218 }



--- *****************************************************
---     LEAF for the lineCarrierFreqOffsetMin article
--- *****************************************************

pm200frs02MesrlineCarrierFreqOffsetMin OBJECT-TYPE
	  SYNTAX Unsigned32 (0..65535)
	  MAX-ACCESS read-only
	  STATUS current
	  DESCRIPTION
        "
        Min Carrier Frequency Offset :This
        OID gives the minimum Carrier Frequency
        Offset on the Line interface since
        the last measure reset  (Offset
        = AV_S16)   (Unit = MHz)<Help>
         This measure gives the minimum
        Carrier Frequency Offset on the
        Line interface since the last measure
        reset
        "
	  ::= { pm200frs02MesrOther 219 }



--- *****************************************************
---     LEAF for the lineOsnrMin article
--- *****************************************************

pm200frs02MesrlineOsnrMin OBJECT-TYPE
	  SYNTAX Unsigned32 (0..65535)
	  MAX-ACCESS read-only
	  STATUS current
	  DESCRIPTION
        "
        Min OSNR :This OID gives the minimum
        OSNR on the Line interface since
        the last measure reset  (OSNR =
        AV_S16/10) (Unit = dB)<Help> This
        measure gives the minimum OSNR
         on the Line interface since the
        last measure reset.
        "
	  ::= { pm200frs02MesrOther 220 }



--- *****************************************************
---     LEAF for the lineNetTxLaserOutputPwrMax article
--- *****************************************************

pm200frs02MesrlineNetTxLaserOutputPwrMax OBJECT-TYPE
	  SYNTAX Unsigned32 (0..65535)
	  MAX-ACCESS read-only
	  STATUS current
	  DESCRIPTION
        "
        Max Line Trscv Tx Power :This
         OID gives the maximum Tx Laser
        transmit power value among the
         network lanes of the Line Transceiver,
        read in the DDM (Digital Diagnostic
        Monitoring) (Power = AV_S16/100)
        (Unit = dBm) <Help> This Measure
        gives the maximum Tx Laser transmit
        power value among the network lanes
        of the Line Transceiver
        "
	  ::= { pm200frs02MesrOther 228 }



--- *****************************************************
---     LEAF for the lineNetTxLaserTempMax article
--- *****************************************************

pm200frs02MesrlineNetTxLaserTempMax OBJECT-TYPE
	  SYNTAX Unsigned32 (0..65535)
	  MAX-ACCESS read-only
	  STATUS current
	  DESCRIPTION
        "
        Max Line Trscv Tx Laser Temperature
        :This OID gives the maximum Tx
         Laser Temperature value among
         the network lanes of the Line
         Transceiver, read from the DDM
        (Digital Diagnostic Monitoring)
        (Temperature = AV_S16/256) (Unit
        = C) <Help> This Measure gives
         the maximum Tx Laser Temperature
        value among the network lanes of
        the Line Transceiver
        "
	  ::= { pm200frs02MesrOther 229 }



--- *****************************************************
---     LEAF for the lineNetTxBiasCurrentMax article
--- *****************************************************

pm200frs02MesrlineNetTxBiasCurrentMax OBJECT-TYPE
	  SYNTAX Unsigned32 (0..65535)
	  MAX-ACCESS read-only
	  STATUS current
	  DESCRIPTION
        "
        Max Line Trscv Tx Laser Bias :This
        OID gives the maximum Tx Laser
         Bias value among the network lanes
        of the Line Transceiver, read from
        the DDM (Digital Diagnostic Monitoring)
        (Bias = AV_S16/10) (Unit = mA)
         <Help> This Measure gives the
         maximum Tx Laser Bias value among
        the network lanes of the Line Transceiver
        "
	  ::= { pm200frs02MesrOther 230 }



--- *****************************************************
---     LEAF for the lineNetRxInputPwrMax article
--- *****************************************************

pm200frs02MesrlineNetRxInputPwrMax OBJECT-TYPE
	  SYNTAX Unsigned32 (0..65535)
	  MAX-ACCESS read-only
	  STATUS current
	  DESCRIPTION
        "
        Max Line Trscv Rx Power :This
         OID gives the maximum Receive
         power value among the network
         lanes of the Line Transceiver,
        read in the DDM (Digital Diagnostic
        Monitoring) (Power = AV_S16/100)
        (Unit = dBm) <Help> This Measure
        gives the maximum Receive power
        value among the network lanes of
        the Line Transceiver
        "
	  ::= { pm200frs02MesrOther 231 }



--- *****************************************************
---     LEAF for the lineResidualChromaticDispMax article
--- *****************************************************

pm200frs02MesrlineResidualChromaticDispMax OBJECT-TYPE
	  SYNTAX Unsigned32 (0..65535)
	  MAX-ACCESS read-only
	  STATUS current
	  DESCRIPTION
        "
        Max Residual Chromatic Dispersion
        :This OID gives the maximum Residual
        Chromatic Dispersion on the Line
        interface since the last measure
        reset (Dispersion = AV_S16*(-2))
          (Unit = ps/nm)<Help> This measure
        gives the maximum Residual Chromatic
        Dispersion on the Line interface
        since the last measure reset.
        "
	  ::= { pm200frs02MesrOther 232 }



--- *****************************************************
---     LEAF for the lineDiffGroupDelayMax article
--- *****************************************************

pm200frs02MesrlineDiffGroupDelayMax OBJECT-TYPE
	  SYNTAX Unsigned32 (0..65535)
	  MAX-ACCESS read-only
	  STATUS current
	  DESCRIPTION
        "
        Max Differential Group Delay :This
        OID gives the maximum Differential
        Group Delay  on the Line interface
        since the last measure reset  (Delay
        = AV_S16)   (Unit = ps)<Help> This
        measure gives the maximum Differential
        Group Delay on the Line interface
        since the last measure reset.
        "
	  ::= { pm200frs02MesrOther 233 }



--- *****************************************************
---     LEAF for the lineQFactorMax article
--- *****************************************************

pm200frs02MesrlineQFactorMax OBJECT-TYPE
	  SYNTAX Unsigned32 (0..65535)
	  MAX-ACCESS read-only
	  STATUS current
	  DESCRIPTION
        "
        Max Q Factor :This OID gives the
        maximum Q Factor on the Line interface
        since the last measure reset (Q
        Factor = AV_U16)    (Unit = dB)<Help>
        This measure gives the maximum
         Q Factor on the Line interface
        since the last measure reset.
        "
	  ::= { pm200frs02MesrOther 234 }



--- *****************************************************
---     LEAF for the lineCarrierFreqOffsetMax article
--- *****************************************************

pm200frs02MesrlineCarrierFreqOffsetMax OBJECT-TYPE
	  SYNTAX Unsigned32 (0..65535)
	  MAX-ACCESS read-only
	  STATUS current
	  DESCRIPTION
        "
        Max Carrier Frequency Offset :This
        OID gives the maximum Carrier Frequency
        Offset on the Line interface since
        the last measure reset  (Offset
        = AV_S16)   (Unit = MHz)<Help>
         This measure gives the maximum
        Carrier Frequency Offset on the
        Line interface since the last measure
        reset.
        "
	  ::= { pm200frs02MesrOther 235 }



--- *****************************************************
---     LEAF for the lineOsnrMax article
--- *****************************************************

pm200frs02MesrlineOsnrMax OBJECT-TYPE
	  SYNTAX Unsigned32 (0..65535)
	  MAX-ACCESS read-only
	  STATUS current
	  DESCRIPTION
        "
        Max OSNR :This OID gives the maximum
        OSNR on the Line interface since
        the last measure reset   (OSNR
         = AV_S16/10) (Unit = dB)<Help>
        This measure gives the maximum
         OSNR on the Line interface since
        the last measure reset
        "
	  ::= { pm200frs02MesrOther 236 }



--- *****************************************************
---     LEAF for the regVoltage article
--- *****************************************************

pm200frs02MesrregVoltage OBJECT-TYPE
	  SYNTAX Unsigned32 (0..65535)
	  MAX-ACCESS read-only
	  STATUS current
	  DESCRIPTION
        "
        Regulator Voltage :This OID gives
        the voltage value of the Regulator
        (Voltage = AV_U16) (Unit = mV)
         <Help> This Measure gives the
         Regulator Voltage
        "
	  ::= { pm200frs02MesrOther 249 }



--- *****************************************************
---     LEAF for the regCurrent article
--- *****************************************************

pm200frs02MesrregCurrent OBJECT-TYPE
	  SYNTAX Unsigned32 (0..65535)
	  MAX-ACCESS read-only
	  STATUS current
	  DESCRIPTION
        "
        Regulator Current :This OID gives
        the current value of the Regulator
        (Current = AV_U16/1000) (Unit =
        A) <Help> This Measure gives the
        Regulator Current
        "
	  ::= { pm200frs02MesrOther 250 }



--- *****************************************************
---     LEAF for the regTemp article
--- *****************************************************

pm200frs02MesrregTemp OBJECT-TYPE
	  SYNTAX Unsigned32 (0..65535)
	  MAX-ACCESS read-only
	  STATUS current
	  DESCRIPTION
        "
        Regulator Temperature :This OID
        gives the temperature value of
         the Regulator (Temperature = AV_S16)
        (Unit = C) <Help> This Measure
         gives the Regulator Temperature
        "
	  ::= { pm200frs02MesrOther 251 }



--- *****************************************************
---     LEAF for the trscv1Temp article
--- *****************************************************

pm200frs02Mesrtrscv1Temp OBJECT-TYPE
	  SYNTAX Unsigned32 (0..65535)
	  MAX-ACCESS read-only
	  STATUS current
	  DESCRIPTION
        "
        Q1 Trscv Temperature :This OID
        gives the temperature value of
         the Transceiver, read from the
        DDM (Digital Diagnostic Monitoring)
        (Temperature = AV_S16/256) (Unit
        = C) <Help> This Measure gives
         the temperature value of the Transceiver
        "
	  ::= { pm200frs02MesrOther 252 }



--- *****************************************************
---     LEAF for the trscv2Temp article
--- *****************************************************

pm200frs02Mesrtrscv2Temp OBJECT-TYPE
	  SYNTAX Unsigned32 (0..65535)
	  MAX-ACCESS read-only
	  STATUS current
	  DESCRIPTION
        "
        Q2 Trscv Temperature :This OID
        gives the temperature value of
         the Transceiver, read from the
        DDM (Digital Diagnostic Monitoring)
        (Temperature = AV_S16/256) (Unit
        = C) <Help> This Measure gives
         the temperature value of the Transceiver
        "
	  ::= { pm200frs02MesrOther 253 }



--- *****************************************************
---     LEAF for the trscv1PowerSupply article
--- *****************************************************

pm200frs02Mesrtrscv1PowerSupply OBJECT-TYPE
	  SYNTAX Unsigned32 (0..65535)
	  MAX-ACCESS read-only
	  STATUS current
	  DESCRIPTION
        "
        Q1 Trscv Voltage :This OID gives
        the voltage value of the QSFP plugged
        into the port, read from the DDM
        (Digital Diagnostic Monitoring)
        (Voltage = AV_U16/10000) (Unit
         = V)  <Help>  This measure gives
        the power supply voltage of the
        client transceiver
        "
	  ::= { pm200frs02MesrOther 254 }



--- *****************************************************
---     LEAF for the trscv2PowerSupply article
--- *****************************************************

pm200frs02Mesrtrscv2PowerSupply OBJECT-TYPE
	  SYNTAX Unsigned32 (0..65535)
	  MAX-ACCESS read-only
	  STATUS current
	  DESCRIPTION
        "
        Q2 Trscv Voltage :This OID gives
        the voltage value of the QSFP plugged
        into the port, read from the DDM
        (Digital Diagnostic Monitoring)
        (Voltage = AV_U16/10000) (Unit
         = V)  <Help>  This measure gives
        the power supply voltage of the
        client transceiver
        "
	  ::= { pm200frs02MesrOther 255 }



--- *********************************************************
---     TABLE for the pm200frs02MesrclientTxCompositePwr articles
--- *********************************************************

pm200frs02MesrclientTxCompositePwrTable OBJECT-TYPE
	SYNTAX  SEQUENCE OF Pm200frs02MesrclientTxCompositePwrEntry
	MAX-ACCESS not-accessible
	STATUS current
	DESCRIPTION
        "
        List of pm200frs02MesrclientTxCompositePwr
        Article
        "
	::= { pm200frs02MesrClient 256 }


pm200frs02MesrclientTxCompositePwrEntry OBJECT-TYPE
	SYNTAX Pm200frs02MesrclientTxCompositePwrEntry
	MAX-ACCESS not-accessible
	STATUS current
	DESCRIPTION
        "
        Row definition for the pm200frs02MesrclientTxCompositePwr
        table
        "
	INDEX   { pm200frs02MesrclientTxCompositePwrIndex }
	::= { pm200frs02MesrclientTxCompositePwrTable 1 }


Pm200frs02MesrclientTxCompositePwrEntry ::=
	SEQUENCE {
	pm200frs02MesrclientTxCompositePwrIndex
		INTEGER,
	pm200frs02MesrclientTxCompositePwrPortn
		INTEGER
	}


pm200frs02MesrclientTxCompositePwrIndex OBJECT-TYPE
	SYNTAX  INTEGER(0..128)
	MAX-ACCESS  read-only
	STATUS current
	DESCRIPTION
        "
        Index definition for the pm200frs02MesrclientTxCompositePwr
        table
        "
	::= { pm200frs02MesrclientTxCompositePwrEntry 1 }


pm200frs02MesrclientTxCompositePwrPortn OBJECT-TYPE
	SYNTAX  INTEGER (0..65535)
	MAX-ACCESS read-only
	STATUS current
	DESCRIPTION
        "
        Client Composite Tx Power (LR4/SR4)
        :This OID gives the composite transmit
        power (sum of the network lanes
        transmit power) of the Client Transceiver,
        read from the DDM (Digital Diagnostic
        Monitoring) (Power = 10*log(AV_U16)-40)
          (Unit = dBm) <Help> This Measure
        gives the composite transmit power
        (sum of the network lanes transmit
        power) of the Client Transceiver
         (LR4/SR4 only)
        "
	::= { pm200frs02MesrclientTxCompositePwrEntry 2 }


--- *********************************************************
---     TABLE for the pm200frs02MesrclientRxCompositePwr articles
--- *********************************************************

pm200frs02MesrclientRxCompositePwrTable OBJECT-TYPE
	SYNTAX  SEQUENCE OF Pm200frs02MesrclientRxCompositePwrEntry
	MAX-ACCESS not-accessible
	STATUS current
	DESCRIPTION
        "
        List of pm200frs02MesrclientRxCompositePwr
        Article
        "
	::= { pm200frs02MesrClient 288 }


pm200frs02MesrclientRxCompositePwrEntry OBJECT-TYPE
	SYNTAX Pm200frs02MesrclientRxCompositePwrEntry
	MAX-ACCESS not-accessible
	STATUS current
	DESCRIPTION
        "
        Row definition for the pm200frs02MesrclientRxCompositePwr
        table
        "
	INDEX   { pm200frs02MesrclientRxCompositePwrIndex }
	::= { pm200frs02MesrclientRxCompositePwrTable 1 }


Pm200frs02MesrclientRxCompositePwrEntry ::=
	SEQUENCE {
	pm200frs02MesrclientRxCompositePwrIndex
		INTEGER,
	pm200frs02MesrclientRxCompositePwrPortn
		INTEGER
	}


pm200frs02MesrclientRxCompositePwrIndex OBJECT-TYPE
	SYNTAX  INTEGER(0..128)
	MAX-ACCESS  read-only
	STATUS current
	DESCRIPTION
        "
        Index definition for the pm200frs02MesrclientRxCompositePwr
        table
        "
	::= { pm200frs02MesrclientRxCompositePwrEntry 1 }


pm200frs02MesrclientRxCompositePwrPortn OBJECT-TYPE
	SYNTAX  INTEGER (0..65535)
	MAX-ACCESS read-only
	STATUS current
	DESCRIPTION
        "
        Client Composite Rx Power (LR4/SR4)
        :This OID gives the composite receive
        power (sum of the network lanes
        receive power) of the Client Transceiver,
        read from the DDM (Digital Diagnostic
        Monitoring) (Power = 10*log(AV_U16)-40)
         (Unit = dBm) <Help> This Measure
        gives the composite receive power
        (sum of the network lanes receive
        power) of the Client Transceiver
        (LR4/SR4 only)
        "
	::= { pm200frs02MesrclientRxCompositePwrEntry 2 }







--- *****************************************************
--- $$$$$$$$$$$$$$$$$$$$$$$$$$$$$$$$$$$$$$$$$$$$$$$$$$$$$
---     PERFORMANCE
--- $$$$$$$$$$$$$$$$$$$$$$$$$$$$$$$$$$$$$$$$$$$$$$$$$$$$$
--- *****************************************************



--- *****************************************************
---     Leaf of the telecomInputClientCurrent15Stat
--- *****************************************************
--- *********************************************************
---     TABLE for the pm200frs02PerfTelecomInputClientCurrent15Stat articles
--- *********************************************************

pm200frs02PerfTelecomInputClientCurrent15StatTable OBJECT-TYPE
	SYNTAX  SEQUENCE OF Pm200frs02PerfTelecomInputClientCurrent15StatEntry
	MAX-ACCESS not-accessible
	STATUS current
	DESCRIPTION
        "
        List of pm200frs02PerfTelecomInputClientCurrent15Stat
        Article
        "
	::= { pm200frs02MonPerfClient 16 }


pm200frs02PerfTelecomInputClientCurrent15StatEntry OBJECT-TYPE
	SYNTAX Pm200frs02PerfTelecomInputClientCurrent15StatEntry
	MAX-ACCESS not-accessible
	STATUS current
	DESCRIPTION
        "
        Row definition for the pm200frs02PerfTelecomInputClientCurrent15Stat
        table
        "
	INDEX   { pm200frs02PerfTelecomInputClientCurrent15StatIndex }
	::= { pm200frs02PerfTelecomInputClientCurrent15StatTable 1 }


Pm200frs02PerfTelecomInputClientCurrent15StatEntry ::=
	SEQUENCE {
	pm200frs02PerfTelecomInputClientCurrent15StatIndex
		INTEGER,
	pm200frs02PerfTelecomInputClientCurrent15StatInvCvPortn
		EkiOnOff,
	pm200frs02PerfTelecomInputClientCurrent15StatCvValuePortn
		Unsigned32,
	pm200frs02PerfTelecomInputClientCurrent15StatInvEsPortn
		EkiOnOff,
	pm200frs02PerfTelecomInputClientCurrent15StatEsValuePortn
		Unsigned32,
	pm200frs02PerfTelecomInputClientCurrent15StatInvSesPortn
		EkiOnOff,
	pm200frs02PerfTelecomInputClientCurrent15StatSesValuePortn
		Unsigned32,
	pm200frs02PerfTelecomInputClientCurrent15StatInvSefsPortn
		EkiOnOff,
	pm200frs02PerfTelecomInputClientCurrent15StatSefsValuePortn
		Unsigned32,
	pm200frs02PerfTelecomInputClientCurrent15StatInvUasPortn
		EkiOnOff,
	pm200frs02PerfTelecomInputClientCurrent15StatUasValuePortn
		Unsigned32
	}


pm200frs02PerfTelecomInputClientCurrent15StatIndex OBJECT-TYPE
	SYNTAX  INTEGER(0..128)
	MAX-ACCESS  read-only
	STATUS current
	DESCRIPTION
        "
        Index definition for the pm200frs02PerfTelecomInputClientCurrent15Stat
        table
        "
	::= { pm200frs02PerfTelecomInputClientCurrent15StatEntry 1 }


pm200frs02PerfTelecomInputClientCurrent15StatInvCvPortn OBJECT-TYPE
	SYNTAX  EkiOnOff
	MAX-ACCESS read-only
	STATUS current
	DESCRIPTION
        "
        Current 15-min EBC counter inv.
        :This OID indicates that the current
        15-min Coding Violation counter
        is invalid
        "
	::= { pm200frs02PerfTelecomInputClientCurrent15StatEntry 2 }


pm200frs02PerfTelecomInputClientCurrent15StatCvValuePortn OBJECT-TYPE
	SYNTAX  Unsigned32
	MAX-ACCESS read-only
	STATUS current
	DESCRIPTION
        "
        Current 15-min EBC counter :This
        OID gives the current 15-min Coding
        Violation counter value
        "
	::= { pm200frs02PerfTelecomInputClientCurrent15StatEntry 3 }


pm200frs02PerfTelecomInputClientCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pm200frs02PerfTelecomInputClientCurrent15StatEntry 4 }


pm200frs02PerfTelecomInputClientCurrent15StatEsValuePortn OBJECT-TYPE
	SYNTAX  Unsigned32
	MAX-ACCESS read-only
	STATUS current
	DESCRIPTION
        "
        Current 15-min ES counter :This
        OID gives the current 15-min Errored
        Second counter value
        "
	::= { pm200frs02PerfTelecomInputClientCurrent15StatEntry 5 }


pm200frs02PerfTelecomInputClientCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pm200frs02PerfTelecomInputClientCurrent15StatEntry 6 }


pm200frs02PerfTelecomInputClientCurrent15StatSesValuePortn OBJECT-TYPE
	SYNTAX  Unsigned32
	MAX-ACCESS read-only
	STATUS current
	DESCRIPTION
        "
        Current 15-min SES counter :This
        OID gives the current 15-min severely
        Errored Second counter value
        "
	::= { pm200frs02PerfTelecomInputClientCurrent15StatEntry 7 }


pm200frs02PerfTelecomInputClientCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pm200frs02PerfTelecomInputClientCurrent15StatEntry 8 }


pm200frs02PerfTelecomInputClientCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pm200frs02PerfTelecomInputClientCurrent15StatEntry 9 }


pm200frs02PerfTelecomInputClientCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pm200frs02PerfTelecomInputClientCurrent15StatEntry 10 }


pm200frs02PerfTelecomInputClientCurrent15StatUasValuePortn OBJECT-TYPE
	SYNTAX  Unsigned32
	MAX-ACCESS read-only
	STATUS current
	DESCRIPTION
        "
        Current 15-min UAS counter :This
        OID gives the current 15-min UnAvailable
        Second counter value
        "
	::= { pm200frs02PerfTelecomInputClientCurrent15StatEntry 11 }


--- *****************************************************
---     Leaf of the telecomInputClientPast15Stat
--- *****************************************************
--- *********************************************************
---     TABLE for the pm200frs02PerfTelecomInputClientPast15StatHistory articles
--- *********************************************************

pm200frs02PerfTelecomInputClientPast15StatHistoryPort1Table OBJECT-TYPE
	SYNTAX  SEQUENCE OF Pm200frs02PerfTelecomInputClientPast15StatHistoryPort1Entry
	MAX-ACCESS not-accessible
	STATUS current
	DESCRIPTION
        "
        List of pm200frs02PerfTelecomInputClientPast15StatHistory
        Article
        "
	::= { pm200frs02MonPerfClient 48 }


pm200frs02PerfTelecomInputClientPast15StatHistoryPort1Entry OBJECT-TYPE
	SYNTAX Pm200frs02PerfTelecomInputClientPast15StatHistoryPort1Entry
	MAX-ACCESS not-accessible
	STATUS current
	DESCRIPTION
        "
        Row definition for the pm200frs02PerfTelecomInputClientPast15StatHistory
        table
        "
	INDEX   { pm200frs02PerfTelecomInputClientPast15StatHistoryPort1Index }
	::= { pm200frs02PerfTelecomInputClientPast15StatHistoryPort1Table 1 }


Pm200frs02PerfTelecomInputClientPast15StatHistoryPort1Entry ::=
	SEQUENCE {
	pm200frs02PerfTelecomInputClientPast15StatHistoryPort1Index
		INTEGER,
	pm200frs02PerfTelecomInputClientPast15StatHistoryInvCvPort1
		EkiOnOff,
	pm200frs02PerfTelecomInputClientPast15StatHistoryCvValuePort1
		Unsigned32,
	pm200frs02PerfTelecomInputClientPast15StatHistoryInvEsPort1
		EkiOnOff,
	pm200frs02PerfTelecomInputClientPast15StatHistoryEsValuePort1
		Unsigned32,
	pm200frs02PerfTelecomInputClientPast15StatHistoryInvSesPort1
		EkiOnOff,
	pm200frs02PerfTelecomInputClientPast15StatHistorySesValuePort1
		Unsigned32,
	pm200frs02PerfTelecomInputClientPast15StatHistoryInvSefsPort1
		EkiOnOff,
	pm200frs02PerfTelecomInputClientPast15StatHistorySefsValuePort1
		Unsigned32,
	pm200frs02PerfTelecomInputClientPast15StatHistoryInvUasPort1
		EkiOnOff,
	pm200frs02PerfTelecomInputClientPast15StatHistoryUasValuePort1
		Unsigned32
	}


pm200frs02PerfTelecomInputClientPast15StatHistoryPort1Index OBJECT-TYPE
	SYNTAX  INTEGER(0..128)
	MAX-ACCESS  read-only
	STATUS current
	DESCRIPTION
        "
        Index definition for the pm200frs02PerfTelecomInputClientPast15StatHistory
        table
        "
	::= { pm200frs02PerfTelecomInputClientPast15StatHistoryPort1Entry 1 }


pm200frs02PerfTelecomInputClientPast15StatHistoryInvCvPort1 OBJECT-TYPE
	SYNTAX  EkiOnOff
	MAX-ACCESS read-only
	STATUS current
	DESCRIPTION
        "
        Previous 15-min EBC counter inv.
        :This OID indicates that the previous
        15-min Coding Violation counter
        is invalid
        "
	::= { pm200frs02PerfTelecomInputClientPast15StatHistoryPort1Entry 2 }


pm200frs02PerfTelecomInputClientPast15StatHistoryCvValuePort1 OBJECT-TYPE
	SYNTAX  Unsigned32
	MAX-ACCESS read-only
	STATUS current
	DESCRIPTION
        "
        Previous 15-min EBC counter :This
        OID gives the previous 15-min Coding
        Violation counter value
        "
	::= { pm200frs02PerfTelecomInputClientPast15StatHistoryPort1Entry 3 }


pm200frs02PerfTelecomInputClientPast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pm200frs02PerfTelecomInputClientPast15StatHistoryPort1Entry 4 }


pm200frs02PerfTelecomInputClientPast15StatHistoryEsValuePort1 OBJECT-TYPE
	SYNTAX  Unsigned32
	MAX-ACCESS read-only
	STATUS current
	DESCRIPTION
        "
        Previous 15-min ES counter :This
        OID gives the previous 15-min Errored
        Second counter value
        "
	::= { pm200frs02PerfTelecomInputClientPast15StatHistoryPort1Entry 5 }


pm200frs02PerfTelecomInputClientPast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pm200frs02PerfTelecomInputClientPast15StatHistoryPort1Entry 6 }


pm200frs02PerfTelecomInputClientPast15StatHistorySesValuePort1 OBJECT-TYPE
	SYNTAX  Unsigned32
	MAX-ACCESS read-only
	STATUS current
	DESCRIPTION
        "
        Previous 15-min SES counter :This
        OID gives the previous 15-min severely
        Errored Second counter value
        "
	::= { pm200frs02PerfTelecomInputClientPast15StatHistoryPort1Entry 7 }


pm200frs02PerfTelecomInputClientPast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pm200frs02PerfTelecomInputClientPast15StatHistoryPort1Entry 8 }


pm200frs02PerfTelecomInputClientPast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pm200frs02PerfTelecomInputClientPast15StatHistoryPort1Entry 9 }


pm200frs02PerfTelecomInputClientPast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pm200frs02PerfTelecomInputClientPast15StatHistoryPort1Entry 10 }


pm200frs02PerfTelecomInputClientPast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pm200frs02PerfTelecomInputClientPast15StatHistoryPort1Entry 11 }


--- *****************************************************
---     Leaf of the telecomInputClientCurrent24Stat
--- *****************************************************
--- *********************************************************
---     TABLE for the pm200frs02PerfTelecomInputClientCurrent24Stat articles
--- *********************************************************

pm200frs02PerfTelecomInputClientCurrent24StatTable OBJECT-TYPE
	SYNTAX  SEQUENCE OF Pm200frs02PerfTelecomInputClientCurrent24StatEntry
	MAX-ACCESS not-accessible
	STATUS current
	DESCRIPTION
        "
        List of pm200frs02PerfTelecomInputClientCurrent24Stat
        Article
        "
	::= { pm200frs02MonPerfClient 80 }


pm200frs02PerfTelecomInputClientCurrent24StatEntry OBJECT-TYPE
	SYNTAX Pm200frs02PerfTelecomInputClientCurrent24StatEntry
	MAX-ACCESS not-accessible
	STATUS current
	DESCRIPTION
        "
        Row definition for the pm200frs02PerfTelecomInputClientCurrent24Stat
        table
        "
	INDEX   { pm200frs02PerfTelecomInputClientCurrent24StatIndex }
	::= { pm200frs02PerfTelecomInputClientCurrent24StatTable 1 }


Pm200frs02PerfTelecomInputClientCurrent24StatEntry ::=
	SEQUENCE {
	pm200frs02PerfTelecomInputClientCurrent24StatIndex
		INTEGER,
	pm200frs02PerfTelecomInputClientCurrent24StatInvCvPortn
		EkiOnOff,
	pm200frs02PerfTelecomInputClientCurrent24StatCvValuePortn
		Unsigned32,
	pm200frs02PerfTelecomInputClientCurrent24StatInvEsPortn
		EkiOnOff,
	pm200frs02PerfTelecomInputClientCurrent24StatEsValuePortn
		Unsigned32,
	pm200frs02PerfTelecomInputClientCurrent24StatInvSesPortn
		EkiOnOff,
	pm200frs02PerfTelecomInputClientCurrent24StatSesValuePortn
		Unsigned32,
	pm200frs02PerfTelecomInputClientCurrent24StatInvSefsPortn
		EkiOnOff,
	pm200frs02PerfTelecomInputClientCurrent24StatSefsValuePortn
		Unsigned32,
	pm200frs02PerfTelecomInputClientCurrent24StatInvUasPortn
		EkiOnOff,
	pm200frs02PerfTelecomInputClientCurrent24StatUasValuePortn
		Unsigned32
	}


pm200frs02PerfTelecomInputClientCurrent24StatIndex OBJECT-TYPE
	SYNTAX  INTEGER(0..128)
	MAX-ACCESS  read-only
	STATUS current
	DESCRIPTION
        "
        Index definition for the pm200frs02PerfTelecomInputClientCurrent24Stat
        table
        "
	::= { pm200frs02PerfTelecomInputClientCurrent24StatEntry 1 }


pm200frs02PerfTelecomInputClientCurrent24StatInvCvPortn OBJECT-TYPE
	SYNTAX  EkiOnOff
	MAX-ACCESS read-only
	STATUS current
	DESCRIPTION
        "
        Current 24-hours EBC counter inv.
        :This OID indicates that the current
        24-hours Coding Violation counter
        is invalid
        "
	::= { pm200frs02PerfTelecomInputClientCurrent24StatEntry 2 }


pm200frs02PerfTelecomInputClientCurrent24StatCvValuePortn OBJECT-TYPE
	SYNTAX  Unsigned32
	MAX-ACCESS read-only
	STATUS current
	DESCRIPTION
        "
        Current 24-hours EBC counter :This
        OID gives the current 24-hours
         Coding Violation counter value
        "
	::= { pm200frs02PerfTelecomInputClientCurrent24StatEntry 3 }


pm200frs02PerfTelecomInputClientCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pm200frs02PerfTelecomInputClientCurrent24StatEntry 4 }


pm200frs02PerfTelecomInputClientCurrent24StatEsValuePortn OBJECT-TYPE
	SYNTAX  Unsigned32
	MAX-ACCESS read-only
	STATUS current
	DESCRIPTION
        "
        Current 24-hours ES counter :This
        OID gives the current 24-hours
         Errored Second counter value
        "
	::= { pm200frs02PerfTelecomInputClientCurrent24StatEntry 5 }


pm200frs02PerfTelecomInputClientCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pm200frs02PerfTelecomInputClientCurrent24StatEntry 6 }


pm200frs02PerfTelecomInputClientCurrent24StatSesValuePortn OBJECT-TYPE
	SYNTAX  Unsigned32
	MAX-ACCESS read-only
	STATUS current
	DESCRIPTION
        "
        Current 24-hours SES counter :This
        OID gives the current 24-hours
         severely Errored Second counter
        value
        "
	::= { pm200frs02PerfTelecomInputClientCurrent24StatEntry 7 }


pm200frs02PerfTelecomInputClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pm200frs02PerfTelecomInputClientCurrent24StatEntry 8 }


pm200frs02PerfTelecomInputClientCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pm200frs02PerfTelecomInputClientCurrent24StatEntry 9 }


pm200frs02PerfTelecomInputClientCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pm200frs02PerfTelecomInputClientCurrent24StatEntry 10 }


pm200frs02PerfTelecomInputClientCurrent24StatUasValuePortn OBJECT-TYPE
	SYNTAX  Unsigned32
	MAX-ACCESS read-only
	STATUS current
	DESCRIPTION
        "
        Current 24-hours UAS counter :This
        OID gives the current 24-hours
         UnAvailable Second counter value
        "
	::= { pm200frs02PerfTelecomInputClientCurrent24StatEntry 11 }


--- *****************************************************
---     Leaf of the telecomInputClientPast24Stat
--- *****************************************************
--- *********************************************************
---     TABLE for the pm200frs02PerfTelecomInputClientPast24StatHistory articles
--- *********************************************************

pm200frs02PerfTelecomInputClientPast24StatHistoryPort1Table OBJECT-TYPE
	SYNTAX  SEQUENCE OF Pm200frs02PerfTelecomInputClientPast24StatHistoryPort1Entry
	MAX-ACCESS not-accessible
	STATUS current
	DESCRIPTION
        "
        List of pm200frs02PerfTelecomInputClientPast24StatHistory
        Article
        "
	::= { pm200frs02MonPerfClient 112 }


pm200frs02PerfTelecomInputClientPast24StatHistoryPort1Entry OBJECT-TYPE
	SYNTAX Pm200frs02PerfTelecomInputClientPast24StatHistoryPort1Entry
	MAX-ACCESS not-accessible
	STATUS current
	DESCRIPTION
        "
        Row definition for the pm200frs02PerfTelecomInputClientPast24StatHistory
        table
        "
	INDEX   { pm200frs02PerfTelecomInputClientPast24StatHistoryPort1Index }
	::= { pm200frs02PerfTelecomInputClientPast24StatHistoryPort1Table 1 }


Pm200frs02PerfTelecomInputClientPast24StatHistoryPort1Entry ::=
	SEQUENCE {
	pm200frs02PerfTelecomInputClientPast24StatHistoryPort1Index
		INTEGER,
	pm200frs02PerfTelecomInputClientPast24StatHistoryInvCvPort1
		EkiOnOff,
	pm200frs02PerfTelecomInputClientPast24StatHistoryCvValuePort1
		Unsigned32,
	pm200frs02PerfTelecomInputClientPast24StatHistoryInvEsPort1
		EkiOnOff,
	pm200frs02PerfTelecomInputClientPast24StatHistoryEsValuePort1
		Unsigned32,
	pm200frs02PerfTelecomInputClientPast24StatHistoryInvSesPort1
		EkiOnOff,
	pm200frs02PerfTelecomInputClientPast24StatHistorySesValuePort1
		Unsigned32,
	pm200frs02PerfTelecomInputClientPast24StatHistoryInvSefsPort1
		EkiOnOff,
	pm200frs02PerfTelecomInputClientPast24StatHistorySefsValuePort1
		Unsigned32,
	pm200frs02PerfTelecomInputClientPast24StatHistoryInvUasPort1
		EkiOnOff,
	pm200frs02PerfTelecomInputClientPast24StatHistoryUasValuePort1
		Unsigned32
	}


pm200frs02PerfTelecomInputClientPast24StatHistoryPort1Index OBJECT-TYPE
	SYNTAX  INTEGER(0..128)
	MAX-ACCESS  read-only
	STATUS current
	DESCRIPTION
        "
        Index definition for the pm200frs02PerfTelecomInputClientPast24StatHistory
        table
        "
	::= { pm200frs02PerfTelecomInputClientPast24StatHistoryPort1Entry 1 }


pm200frs02PerfTelecomInputClientPast24StatHistoryInvCvPort1 OBJECT-TYPE
	SYNTAX  EkiOnOff
	MAX-ACCESS read-only
	STATUS current
	DESCRIPTION
        "
        Previous 24-hours EBC counter
         inv. :This OID indicates that
         the previous 24-hours Coding Violation
        counter is invalid
        "
	::= { pm200frs02PerfTelecomInputClientPast24StatHistoryPort1Entry 2 }


pm200frs02PerfTelecomInputClientPast24StatHistoryCvValuePort1 OBJECT-TYPE
	SYNTAX  Unsigned32
	MAX-ACCESS read-only
	STATUS current
	DESCRIPTION
        "
        Previous 24-hours EBC counter
         :This OID gives the previous 24-hours
        Coding Violation counter value
        "
	::= { pm200frs02PerfTelecomInputClientPast24StatHistoryPort1Entry 3 }


pm200frs02PerfTelecomInputClientPast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pm200frs02PerfTelecomInputClientPast24StatHistoryPort1Entry 4 }


pm200frs02PerfTelecomInputClientPast24StatHistoryEsValuePort1 OBJECT-TYPE
	SYNTAX  Unsigned32
	MAX-ACCESS read-only
	STATUS current
	DESCRIPTION
        "
        Previous 24-hours ES counter :This
        OID gives the previous 24-hours
        Errored Second counter value
        "
	::= { pm200frs02PerfTelecomInputClientPast24StatHistoryPort1Entry 5 }


pm200frs02PerfTelecomInputClientPast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pm200frs02PerfTelecomInputClientPast24StatHistoryPort1Entry 6 }


pm200frs02PerfTelecomInputClientPast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pm200frs02PerfTelecomInputClientPast24StatHistoryPort1Entry 7 }


pm200frs02PerfTelecomInputClientPast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm200frs02PerfTelecomInputClientPast24StatHistoryPort1Entry 8 }


pm200frs02PerfTelecomInputClientPast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pm200frs02PerfTelecomInputClientPast24StatHistoryPort1Entry 9 }


pm200frs02PerfTelecomInputClientPast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pm200frs02PerfTelecomInputClientPast24StatHistoryPort1Entry 10 }


pm200frs02PerfTelecomInputClientPast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pm200frs02PerfTelecomInputClientPast24StatHistoryPort1Entry 11 }


--- *****************************************************
---     Leaf of the telecomOutputClientCurrent15Stat
--- *****************************************************
--- *********************************************************
---     TABLE for the pm200frs02PerfTelecomOutputClientCurrent15Stat articles
--- *********************************************************

pm200frs02PerfTelecomOutputClientCurrent15StatTable OBJECT-TYPE
	SYNTAX  SEQUENCE OF Pm200frs02PerfTelecomOutputClientCurrent15StatEntry
	MAX-ACCESS not-accessible
	STATUS current
	DESCRIPTION
        "
        List of pm200frs02PerfTelecomOutputClientCurrent15Stat
        Article
        "
	::= { pm200frs02MonPerfClient 144 }


pm200frs02PerfTelecomOutputClientCurrent15StatEntry OBJECT-TYPE
	SYNTAX Pm200frs02PerfTelecomOutputClientCurrent15StatEntry
	MAX-ACCESS not-accessible
	STATUS current
	DESCRIPTION
        "
        Row definition for the pm200frs02PerfTelecomOutputClientCurrent15Stat
        table
        "
	INDEX   { pm200frs02PerfTelecomOutputClientCurrent15StatIndex }
	::= { pm200frs02PerfTelecomOutputClientCurrent15StatTable 1 }


Pm200frs02PerfTelecomOutputClientCurrent15StatEntry ::=
	SEQUENCE {
	pm200frs02PerfTelecomOutputClientCurrent15StatIndex
		INTEGER,
	pm200frs02PerfTelecomOutputClientCurrent15StatInvCvPortn
		EkiOnOff,
	pm200frs02PerfTelecomOutputClientCurrent15StatCvValuePortn
		Unsigned32,
	pm200frs02PerfTelecomOutputClientCurrent15StatInvEsPortn
		EkiOnOff,
	pm200frs02PerfTelecomOutputClientCurrent15StatEsValuePortn
		Unsigned32,
	pm200frs02PerfTelecomOutputClientCurrent15StatInvSesPortn
		EkiOnOff,
	pm200frs02PerfTelecomOutputClientCurrent15StatSesValuePortn
		Unsigned32,
	pm200frs02PerfTelecomOutputClientCurrent15StatInvSefsPortn
		EkiOnOff,
	pm200frs02PerfTelecomOutputClientCurrent15StatSefsValuePortn
		Unsigned32,
	pm200frs02PerfTelecomOutputClientCurrent15StatInvUasPortn
		EkiOnOff,
	pm200frs02PerfTelecomOutputClientCurrent15StatUasValuePortn
		Unsigned32
	}


pm200frs02PerfTelecomOutputClientCurrent15StatIndex OBJECT-TYPE
	SYNTAX  INTEGER(0..128)
	MAX-ACCESS  read-only
	STATUS current
	DESCRIPTION
        "
        Index definition for the pm200frs02PerfTelecomOutputClientCurrent15Stat
        table
        "
	::= { pm200frs02PerfTelecomOutputClientCurrent15StatEntry 1 }


pm200frs02PerfTelecomOutputClientCurrent15StatInvCvPortn OBJECT-TYPE
	SYNTAX  EkiOnOff
	MAX-ACCESS read-only
	STATUS current
	DESCRIPTION
        "
        Current 15-min EBC counter inv.
        :This OID indicates that the current
        15-min Coding Violation counter
        is invalid
        "
	::= { pm200frs02PerfTelecomOutputClientCurrent15StatEntry 2 }


pm200frs02PerfTelecomOutputClientCurrent15StatCvValuePortn OBJECT-TYPE
	SYNTAX  Unsigned32
	MAX-ACCESS read-only
	STATUS current
	DESCRIPTION
        "
        Current 15-min EBC counter :This
        OID gives the current 15-min Coding
        Violation counter value
        "
	::= { pm200frs02PerfTelecomOutputClientCurrent15StatEntry 3 }


pm200frs02PerfTelecomOutputClientCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pm200frs02PerfTelecomOutputClientCurrent15StatEntry 4 }


pm200frs02PerfTelecomOutputClientCurrent15StatEsValuePortn OBJECT-TYPE
	SYNTAX  Unsigned32
	MAX-ACCESS read-only
	STATUS current
	DESCRIPTION
        "
        Current 15-min ES counter :This
        OID gives the current 15-min Errored
        Second counter value
        "
	::= { pm200frs02PerfTelecomOutputClientCurrent15StatEntry 5 }


pm200frs02PerfTelecomOutputClientCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pm200frs02PerfTelecomOutputClientCurrent15StatEntry 6 }


pm200frs02PerfTelecomOutputClientCurrent15StatSesValuePortn OBJECT-TYPE
	SYNTAX  Unsigned32
	MAX-ACCESS read-only
	STATUS current
	DESCRIPTION
        "
        Current 15-min SES counter :This
        OID gives the current 15-min severely
        Errored Second counter value
        "
	::= { pm200frs02PerfTelecomOutputClientCurrent15StatEntry 7 }


pm200frs02PerfTelecomOutputClientCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pm200frs02PerfTelecomOutputClientCurrent15StatEntry 8 }


pm200frs02PerfTelecomOutputClientCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pm200frs02PerfTelecomOutputClientCurrent15StatEntry 9 }


pm200frs02PerfTelecomOutputClientCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pm200frs02PerfTelecomOutputClientCurrent15StatEntry 10 }


pm200frs02PerfTelecomOutputClientCurrent15StatUasValuePortn OBJECT-TYPE
	SYNTAX  Unsigned32
	MAX-ACCESS read-only
	STATUS current
	DESCRIPTION
        "
        Current 15-min UAS counter :This
        OID gives the current 15-min UnAvailable
        Second counter value
        "
	::= { pm200frs02PerfTelecomOutputClientCurrent15StatEntry 11 }


--- *****************************************************
---     Leaf of the telecomOutputClientPast15Stat
--- *****************************************************
--- *********************************************************
---     TABLE for the pm200frs02PerfTelecomOutputClientPast15StatHistory articles
--- *********************************************************

pm200frs02PerfTelecomOutputClientPast15StatHistoryPort1Table OBJECT-TYPE
	SYNTAX  SEQUENCE OF Pm200frs02PerfTelecomOutputClientPast15StatHistoryPort1Entry
	MAX-ACCESS not-accessible
	STATUS current
	DESCRIPTION
        "
        List of pm200frs02PerfTelecomOutputClientPast15StatHistory
        Article
        "
	::= { pm200frs02MonPerfClient 176 }


pm200frs02PerfTelecomOutputClientPast15StatHistoryPort1Entry OBJECT-TYPE
	SYNTAX Pm200frs02PerfTelecomOutputClientPast15StatHistoryPort1Entry
	MAX-ACCESS not-accessible
	STATUS current
	DESCRIPTION
        "
        Row definition for the pm200frs02PerfTelecomOutputClientPast15StatHistory
        table
        "
	INDEX   { pm200frs02PerfTelecomOutputClientPast15StatHistoryPort1Index }
	::= { pm200frs02PerfTelecomOutputClientPast15StatHistoryPort1Table 1 }


Pm200frs02PerfTelecomOutputClientPast15StatHistoryPort1Entry ::=
	SEQUENCE {
	pm200frs02PerfTelecomOutputClientPast15StatHistoryPort1Index
		INTEGER,
	pm200frs02PerfTelecomOutputClientPast15StatHistoryInvCvPort1
		EkiOnOff,
	pm200frs02PerfTelecomOutputClientPast15StatHistoryCvValuePort1
		Unsigned32,
	pm200frs02PerfTelecomOutputClientPast15StatHistoryInvEsPort1
		EkiOnOff,
	pm200frs02PerfTelecomOutputClientPast15StatHistoryEsValuePort1
		Unsigned32,
	pm200frs02PerfTelecomOutputClientPast15StatHistoryInvSesPort1
		EkiOnOff,
	pm200frs02PerfTelecomOutputClientPast15StatHistorySesValuePort1
		Unsigned32,
	pm200frs02PerfTelecomOutputClientPast15StatHistoryInvSefsPort1
		EkiOnOff,
	pm200frs02PerfTelecomOutputClientPast15StatHistorySefsValuePort1
		Unsigned32,
	pm200frs02PerfTelecomOutputClientPast15StatHistoryInvUasPort1
		EkiOnOff,
	pm200frs02PerfTelecomOutputClientPast15StatHistoryUasValuePort1
		Unsigned32
	}


pm200frs02PerfTelecomOutputClientPast15StatHistoryPort1Index OBJECT-TYPE
	SYNTAX  INTEGER(0..128)
	MAX-ACCESS  read-only
	STATUS current
	DESCRIPTION
        "
        Index definition for the pm200frs02PerfTelecomOutputClientPast15StatHistory
        table
        "
	::= { pm200frs02PerfTelecomOutputClientPast15StatHistoryPort1Entry 1 }


pm200frs02PerfTelecomOutputClientPast15StatHistoryInvCvPort1 OBJECT-TYPE
	SYNTAX  EkiOnOff
	MAX-ACCESS read-only
	STATUS current
	DESCRIPTION
        "
        Previous 15-min EBC counter inv.
        :This OID indicates that the previous
        15-min Coding Violation counter
        is invalid
        "
	::= { pm200frs02PerfTelecomOutputClientPast15StatHistoryPort1Entry 2 }


pm200frs02PerfTelecomOutputClientPast15StatHistoryCvValuePort1 OBJECT-TYPE
	SYNTAX  Unsigned32
	MAX-ACCESS read-only
	STATUS current
	DESCRIPTION
        "
        Previous 15-min EBC counter :This
        OID gives the previous 15-min Coding
        Violation counter value
        "
	::= { pm200frs02PerfTelecomOutputClientPast15StatHistoryPort1Entry 3 }


pm200frs02PerfTelecomOutputClientPast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pm200frs02PerfTelecomOutputClientPast15StatHistoryPort1Entry 4 }


pm200frs02PerfTelecomOutputClientPast15StatHistoryEsValuePort1 OBJECT-TYPE
	SYNTAX  Unsigned32
	MAX-ACCESS read-only
	STATUS current
	DESCRIPTION
        "
        Previous 15-min ES counter :This
        OID gives the previous 15-min Errored
        Second counter value
        "
	::= { pm200frs02PerfTelecomOutputClientPast15StatHistoryPort1Entry 5 }


pm200frs02PerfTelecomOutputClientPast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pm200frs02PerfTelecomOutputClientPast15StatHistoryPort1Entry 6 }


pm200frs02PerfTelecomOutputClientPast15StatHistorySesValuePort1 OBJECT-TYPE
	SYNTAX  Unsigned32
	MAX-ACCESS read-only
	STATUS current
	DESCRIPTION
        "
        Previous 15-min SES counter :This
        OID gives the previous 15-min severely
        Errored Second counter value
        "
	::= { pm200frs02PerfTelecomOutputClientPast15StatHistoryPort1Entry 7 }


pm200frs02PerfTelecomOutputClientPast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pm200frs02PerfTelecomOutputClientPast15StatHistoryPort1Entry 8 }


pm200frs02PerfTelecomOutputClientPast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pm200frs02PerfTelecomOutputClientPast15StatHistoryPort1Entry 9 }


pm200frs02PerfTelecomOutputClientPast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pm200frs02PerfTelecomOutputClientPast15StatHistoryPort1Entry 10 }


pm200frs02PerfTelecomOutputClientPast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pm200frs02PerfTelecomOutputClientPast15StatHistoryPort1Entry 11 }


--- *****************************************************
---     Leaf of the telecomOutputClientCurrent24Stat
--- *****************************************************
--- *********************************************************
---     TABLE for the pm200frs02PerfTelecomOutputClientCurrent24Stat articles
--- *********************************************************

pm200frs02PerfTelecomOutputClientCurrent24StatTable OBJECT-TYPE
	SYNTAX  SEQUENCE OF Pm200frs02PerfTelecomOutputClientCurrent24StatEntry
	MAX-ACCESS not-accessible
	STATUS current
	DESCRIPTION
        "
        List of pm200frs02PerfTelecomOutputClientCurrent24Stat
        Article
        "
	::= { pm200frs02MonPerfClient 208 }


pm200frs02PerfTelecomOutputClientCurrent24StatEntry OBJECT-TYPE
	SYNTAX Pm200frs02PerfTelecomOutputClientCurrent24StatEntry
	MAX-ACCESS not-accessible
	STATUS current
	DESCRIPTION
        "
        Row definition for the pm200frs02PerfTelecomOutputClientCurrent24Stat
        table
        "
	INDEX   { pm200frs02PerfTelecomOutputClientCurrent24StatIndex }
	::= { pm200frs02PerfTelecomOutputClientCurrent24StatTable 1 }


Pm200frs02PerfTelecomOutputClientCurrent24StatEntry ::=
	SEQUENCE {
	pm200frs02PerfTelecomOutputClientCurrent24StatIndex
		INTEGER,
	pm200frs02PerfTelecomOutputClientCurrent24StatInvCvPortn
		EkiOnOff,
	pm200frs02PerfTelecomOutputClientCurrent24StatCvValuePortn
		Unsigned32,
	pm200frs02PerfTelecomOutputClientCurrent24StatInvEsPortn
		EkiOnOff,
	pm200frs02PerfTelecomOutputClientCurrent24StatEsValuePortn
		Unsigned32,
	pm200frs02PerfTelecomOutputClientCurrent24StatInvSesPortn
		EkiOnOff,
	pm200frs02PerfTelecomOutputClientCurrent24StatSesValuePortn
		Unsigned32,
	pm200frs02PerfTelecomOutputClientCurrent24StatInvSefsPortn
		EkiOnOff,
	pm200frs02PerfTelecomOutputClientCurrent24StatSefsValuePortn
		Unsigned32,
	pm200frs02PerfTelecomOutputClientCurrent24StatInvUasPortn
		EkiOnOff,
	pm200frs02PerfTelecomOutputClientCurrent24StatUasValuePortn
		Unsigned32
	}


pm200frs02PerfTelecomOutputClientCurrent24StatIndex OBJECT-TYPE
	SYNTAX  INTEGER(0..128)
	MAX-ACCESS  read-only
	STATUS current
	DESCRIPTION
        "
        Index definition for the pm200frs02PerfTelecomOutputClientCurrent24Stat
        table
        "
	::= { pm200frs02PerfTelecomOutputClientCurrent24StatEntry 1 }


pm200frs02PerfTelecomOutputClientCurrent24StatInvCvPortn OBJECT-TYPE
	SYNTAX  EkiOnOff
	MAX-ACCESS read-only
	STATUS current
	DESCRIPTION
        "
        Current 24-hours EBC counter inv.
        :This OID indicates that the current
        24-hours Coding Violation counter
        is invalid
        "
	::= { pm200frs02PerfTelecomOutputClientCurrent24StatEntry 2 }


pm200frs02PerfTelecomOutputClientCurrent24StatCvValuePortn OBJECT-TYPE
	SYNTAX  Unsigned32
	MAX-ACCESS read-only
	STATUS current
	DESCRIPTION
        "
        Current 24-hours EBC counter :This
        OID gives the current 24-hours
         Coding Violation counter value
        "
	::= { pm200frs02PerfTelecomOutputClientCurrent24StatEntry 3 }


pm200frs02PerfTelecomOutputClientCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pm200frs02PerfTelecomOutputClientCurrent24StatEntry 4 }


pm200frs02PerfTelecomOutputClientCurrent24StatEsValuePortn OBJECT-TYPE
	SYNTAX  Unsigned32
	MAX-ACCESS read-only
	STATUS current
	DESCRIPTION
        "
        Current 24-hours ES counter :This
        OID gives the current 24-hours
         Errored Second counter value
        "
	::= { pm200frs02PerfTelecomOutputClientCurrent24StatEntry 5 }


pm200frs02PerfTelecomOutputClientCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pm200frs02PerfTelecomOutputClientCurrent24StatEntry 6 }


pm200frs02PerfTelecomOutputClientCurrent24StatSesValuePortn OBJECT-TYPE
	SYNTAX  Unsigned32
	MAX-ACCESS read-only
	STATUS current
	DESCRIPTION
        "
        Current 24-hours SES counter :This
        OID gives the current 24-hours
         severely Errored Second counter
        value
        "
	::= { pm200frs02PerfTelecomOutputClientCurrent24StatEntry 7 }


pm200frs02PerfTelecomOutputClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pm200frs02PerfTelecomOutputClientCurrent24StatEntry 8 }


pm200frs02PerfTelecomOutputClientCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pm200frs02PerfTelecomOutputClientCurrent24StatEntry 9 }


pm200frs02PerfTelecomOutputClientCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pm200frs02PerfTelecomOutputClientCurrent24StatEntry 10 }


pm200frs02PerfTelecomOutputClientCurrent24StatUasValuePortn OBJECT-TYPE
	SYNTAX  Unsigned32
	MAX-ACCESS read-only
	STATUS current
	DESCRIPTION
        "
        Current 24-hours UAS counter :This
        OID gives the current 24-hours
         UnAvailable Second counter value
        "
	::= { pm200frs02PerfTelecomOutputClientCurrent24StatEntry 11 }


--- *****************************************************
---     Leaf of the telecomOutputClientPast24Stat
--- *****************************************************
--- *********************************************************
---     TABLE for the pm200frs02PerfTelecomOutputClientPast24StatHistory articles
--- *********************************************************

pm200frs02PerfTelecomOutputClientPast24StatHistoryPort1Table OBJECT-TYPE
	SYNTAX  SEQUENCE OF Pm200frs02PerfTelecomOutputClientPast24StatHistoryPort1Entry
	MAX-ACCESS not-accessible
	STATUS current
	DESCRIPTION
        "
        List of pm200frs02PerfTelecomOutputClientPast24StatHistory
        Article
        "
	::= { pm200frs02MonPerfClient 240 }


pm200frs02PerfTelecomOutputClientPast24StatHistoryPort1Entry OBJECT-TYPE
	SYNTAX Pm200frs02PerfTelecomOutputClientPast24StatHistoryPort1Entry
	MAX-ACCESS not-accessible
	STATUS current
	DESCRIPTION
        "
        Row definition for the pm200frs02PerfTelecomOutputClientPast24StatHistory
        table
        "
	INDEX   { pm200frs02PerfTelecomOutputClientPast24StatHistoryPort1Index }
	::= { pm200frs02PerfTelecomOutputClientPast24StatHistoryPort1Table 1 }


Pm200frs02PerfTelecomOutputClientPast24StatHistoryPort1Entry ::=
	SEQUENCE {
	pm200frs02PerfTelecomOutputClientPast24StatHistoryPort1Index
		INTEGER,
	pm200frs02PerfTelecomOutputClientPast24StatHistoryInvCvPort1
		EkiOnOff,
	pm200frs02PerfTelecomOutputClientPast24StatHistoryCvValuePort1
		Unsigned32,
	pm200frs02PerfTelecomOutputClientPast24StatHistoryInvEsPort1
		EkiOnOff,
	pm200frs02PerfTelecomOutputClientPast24StatHistoryEsValuePort1
		Unsigned32,
	pm200frs02PerfTelecomOutputClientPast24StatHistoryInvSesPort1
		EkiOnOff,
	pm200frs02PerfTelecomOutputClientPast24StatHistorySesValuePort1
		Unsigned32,
	pm200frs02PerfTelecomOutputClientPast24StatHistoryInvSefsPort1
		EkiOnOff,
	pm200frs02PerfTelecomOutputClientPast24StatHistorySefsValuePort1
		Unsigned32,
	pm200frs02PerfTelecomOutputClientPast24StatHistoryInvUasPort1
		EkiOnOff,
	pm200frs02PerfTelecomOutputClientPast24StatHistoryUasValuePort1
		Unsigned32
	}


pm200frs02PerfTelecomOutputClientPast24StatHistoryPort1Index OBJECT-TYPE
	SYNTAX  INTEGER(0..128)
	MAX-ACCESS  read-only
	STATUS current
	DESCRIPTION
        "
        Index definition for the pm200frs02PerfTelecomOutputClientPast24StatHistory
        table
        "
	::= { pm200frs02PerfTelecomOutputClientPast24StatHistoryPort1Entry 1 }


pm200frs02PerfTelecomOutputClientPast24StatHistoryInvCvPort1 OBJECT-TYPE
	SYNTAX  EkiOnOff
	MAX-ACCESS read-only
	STATUS current
	DESCRIPTION
        "
        Previous 24-hours EBC counter
         inv. :This OID indicates that
         the previous 24-hours Coding Violation
        counter is invalid
        "
	::= { pm200frs02PerfTelecomOutputClientPast24StatHistoryPort1Entry 2 }


pm200frs02PerfTelecomOutputClientPast24StatHistoryCvValuePort1 OBJECT-TYPE
	SYNTAX  Unsigned32
	MAX-ACCESS read-only
	STATUS current
	DESCRIPTION
        "
        Previous 24-hours EBC counter
         :This OID gives the previous 24-hours
        Coding Violation counter value
        "
	::= { pm200frs02PerfTelecomOutputClientPast24StatHistoryPort1Entry 3 }


pm200frs02PerfTelecomOutputClientPast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pm200frs02PerfTelecomOutputClientPast24StatHistoryPort1Entry 4 }


pm200frs02PerfTelecomOutputClientPast24StatHistoryEsValuePort1 OBJECT-TYPE
	SYNTAX  Unsigned32
	MAX-ACCESS read-only
	STATUS current
	DESCRIPTION
        "
        Previous 24-hours ES counter :This
        OID gives the previous 24-hours
        Errored Second counter value
        "
	::= { pm200frs02PerfTelecomOutputClientPast24StatHistoryPort1Entry 5 }


pm200frs02PerfTelecomOutputClientPast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pm200frs02PerfTelecomOutputClientPast24StatHistoryPort1Entry 6 }


pm200frs02PerfTelecomOutputClientPast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pm200frs02PerfTelecomOutputClientPast24StatHistoryPort1Entry 7 }


pm200frs02PerfTelecomOutputClientPast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm200frs02PerfTelecomOutputClientPast24StatHistoryPort1Entry 8 }


pm200frs02PerfTelecomOutputClientPast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pm200frs02PerfTelecomOutputClientPast24StatHistoryPort1Entry 9 }


pm200frs02PerfTelecomOutputClientPast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pm200frs02PerfTelecomOutputClientPast24StatHistoryPort1Entry 10 }


pm200frs02PerfTelecomOutputClientPast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pm200frs02PerfTelecomOutputClientPast24StatHistoryPort1Entry 11 }


--- *****************************************************
---     Leaf of the telecomLinePostFecCurrent15Stat
--- *****************************************************
--- *********************************************************
---     TABLE for the pm200frs02PerfTelecomLinePostFecCurrent15Stat articles
--- *********************************************************

pm200frs02PerfTelecomLinePostFecCurrent15StatTable OBJECT-TYPE
	SYNTAX  SEQUENCE OF Pm200frs02PerfTelecomLinePostFecCurrent15StatEntry
	MAX-ACCESS not-accessible
	STATUS current
	DESCRIPTION
        "
        List of pm200frs02PerfTelecomLinePostFecCurrent15Stat
        Article
        "
	::= { pm200frs02MonPerfLine 336 }


pm200frs02PerfTelecomLinePostFecCurrent15StatEntry OBJECT-TYPE
	SYNTAX Pm200frs02PerfTelecomLinePostFecCurrent15StatEntry
	MAX-ACCESS not-accessible
	STATUS current
	DESCRIPTION
        "
        Row definition for the pm200frs02PerfTelecomLinePostFecCurrent15Stat
        table
        "
	INDEX   { pm200frs02PerfTelecomLinePostFecCurrent15StatIndex }
	::= { pm200frs02PerfTelecomLinePostFecCurrent15StatTable 1 }


Pm200frs02PerfTelecomLinePostFecCurrent15StatEntry ::=
	SEQUENCE {
	pm200frs02PerfTelecomLinePostFecCurrent15StatIndex
		INTEGER,
	pm200frs02PerfTelecomLinePostFecCurrent15StatInvCvPortn
		EkiOnOff,
	pm200frs02PerfTelecomLinePostFecCurrent15StatCvValuePortn
		Unsigned32,
	pm200frs02PerfTelecomLinePostFecCurrent15StatInvEsPortn
		EkiOnOff,
	pm200frs02PerfTelecomLinePostFecCurrent15StatEsValuePortn
		Unsigned32,
	pm200frs02PerfTelecomLinePostFecCurrent15StatInvSesPortn
		EkiOnOff,
	pm200frs02PerfTelecomLinePostFecCurrent15StatSesValuePortn
		Unsigned32,
	pm200frs02PerfTelecomLinePostFecCurrent15StatInvSefsPortn
		EkiOnOff,
	pm200frs02PerfTelecomLinePostFecCurrent15StatSefsValuePortn
		Unsigned32,
	pm200frs02PerfTelecomLinePostFecCurrent15StatInvUasPortn
		EkiOnOff,
	pm200frs02PerfTelecomLinePostFecCurrent15StatUasValuePortn
		Unsigned32
	}


pm200frs02PerfTelecomLinePostFecCurrent15StatIndex OBJECT-TYPE
	SYNTAX  INTEGER(0..128)
	MAX-ACCESS  read-only
	STATUS current
	DESCRIPTION
        "
        Index definition for the pm200frs02PerfTelecomLinePostFecCurrent15Stat
        table
        "
	::= { pm200frs02PerfTelecomLinePostFecCurrent15StatEntry 1 }


pm200frs02PerfTelecomLinePostFecCurrent15StatInvCvPortn OBJECT-TYPE
	SYNTAX  EkiOnOff
	MAX-ACCESS read-only
	STATUS current
	DESCRIPTION
        "
        Current 15-min EBC counter inv.
        :This OID indicates that the current
        15-min Coding Violation counter
        is invalid
        "
	::= { pm200frs02PerfTelecomLinePostFecCurrent15StatEntry 2 }


pm200frs02PerfTelecomLinePostFecCurrent15StatCvValuePortn OBJECT-TYPE
	SYNTAX  Unsigned32
	MAX-ACCESS read-only
	STATUS current
	DESCRIPTION
        "
        Current 15-min EBC counter :This
        OID gives the current 15-min Coding
        Violation counter value
        "
	::= { pm200frs02PerfTelecomLinePostFecCurrent15StatEntry 3 }


pm200frs02PerfTelecomLinePostFecCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pm200frs02PerfTelecomLinePostFecCurrent15StatEntry 4 }


pm200frs02PerfTelecomLinePostFecCurrent15StatEsValuePortn OBJECT-TYPE
	SYNTAX  Unsigned32
	MAX-ACCESS read-only
	STATUS current
	DESCRIPTION
        "
        Current 15-min ES counter :This
        OID gives the current 15-min Errored
        Second counter value
        "
	::= { pm200frs02PerfTelecomLinePostFecCurrent15StatEntry 5 }


pm200frs02PerfTelecomLinePostFecCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pm200frs02PerfTelecomLinePostFecCurrent15StatEntry 6 }


pm200frs02PerfTelecomLinePostFecCurrent15StatSesValuePortn OBJECT-TYPE
	SYNTAX  Unsigned32
	MAX-ACCESS read-only
	STATUS current
	DESCRIPTION
        "
        Current 15-min SES counter :This
        OID gives the current 15-min severely
        Errored Second counter value
        "
	::= { pm200frs02PerfTelecomLinePostFecCurrent15StatEntry 7 }


pm200frs02PerfTelecomLinePostFecCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pm200frs02PerfTelecomLinePostFecCurrent15StatEntry 8 }


pm200frs02PerfTelecomLinePostFecCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pm200frs02PerfTelecomLinePostFecCurrent15StatEntry 9 }


pm200frs02PerfTelecomLinePostFecCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pm200frs02PerfTelecomLinePostFecCurrent15StatEntry 10 }


pm200frs02PerfTelecomLinePostFecCurrent15StatUasValuePortn OBJECT-TYPE
	SYNTAX  Unsigned32
	MAX-ACCESS read-only
	STATUS current
	DESCRIPTION
        "
        Current 15-min UAS counter :This
        OID gives the current 15-min UnAvailable
        Second counter value
        "
	::= { pm200frs02PerfTelecomLinePostFecCurrent15StatEntry 11 }


--- *****************************************************
---     Leaf of the telecomLinePostFecPast15Stat
--- *****************************************************
--- *********************************************************
---     TABLE for the pm200frs02PerfTelecomLinePostFecPast15StatHistory articles
--- *********************************************************

pm200frs02PerfTelecomLinePostFecPast15StatHistoryPort1Table OBJECT-TYPE
	SYNTAX  SEQUENCE OF Pm200frs02PerfTelecomLinePostFecPast15StatHistoryPort1Entry
	MAX-ACCESS not-accessible
	STATUS current
	DESCRIPTION
        "
        List of pm200frs02PerfTelecomLinePostFecPast15StatHistory
        Article
        "
	::= { pm200frs02MonPerfLine 337 }


pm200frs02PerfTelecomLinePostFecPast15StatHistoryPort1Entry OBJECT-TYPE
	SYNTAX Pm200frs02PerfTelecomLinePostFecPast15StatHistoryPort1Entry
	MAX-ACCESS not-accessible
	STATUS current
	DESCRIPTION
        "
        Row definition for the pm200frs02PerfTelecomLinePostFecPast15StatHistory
        table
        "
	INDEX   { pm200frs02PerfTelecomLinePostFecPast15StatHistoryPort1Index }
	::= { pm200frs02PerfTelecomLinePostFecPast15StatHistoryPort1Table 1 }


Pm200frs02PerfTelecomLinePostFecPast15StatHistoryPort1Entry ::=
	SEQUENCE {
	pm200frs02PerfTelecomLinePostFecPast15StatHistoryPort1Index
		INTEGER,
	pm200frs02PerfTelecomLinePostFecPast15StatHistoryInvCvPort1
		EkiOnOff,
	pm200frs02PerfTelecomLinePostFecPast15StatHistoryCvValuePort1
		Unsigned32,
	pm200frs02PerfTelecomLinePostFecPast15StatHistoryInvEsPort1
		EkiOnOff,
	pm200frs02PerfTelecomLinePostFecPast15StatHistoryEsValuePort1
		Unsigned32,
	pm200frs02PerfTelecomLinePostFecPast15StatHistoryInvSesPort1
		EkiOnOff,
	pm200frs02PerfTelecomLinePostFecPast15StatHistorySesValuePort1
		Unsigned32,
	pm200frs02PerfTelecomLinePostFecPast15StatHistoryInvSefsPort1
		EkiOnOff,
	pm200frs02PerfTelecomLinePostFecPast15StatHistorySefsValuePort1
		Unsigned32,
	pm200frs02PerfTelecomLinePostFecPast15StatHistoryInvUasPort1
		EkiOnOff,
	pm200frs02PerfTelecomLinePostFecPast15StatHistoryUasValuePort1
		Unsigned32
	}


pm200frs02PerfTelecomLinePostFecPast15StatHistoryPort1Index OBJECT-TYPE
	SYNTAX  INTEGER(0..128)
	MAX-ACCESS  read-only
	STATUS current
	DESCRIPTION
        "
        Index definition for the pm200frs02PerfTelecomLinePostFecPast15StatHistory
        table
        "
	::= { pm200frs02PerfTelecomLinePostFecPast15StatHistoryPort1Entry 1 }


pm200frs02PerfTelecomLinePostFecPast15StatHistoryInvCvPort1 OBJECT-TYPE
	SYNTAX  EkiOnOff
	MAX-ACCESS read-only
	STATUS current
	DESCRIPTION
        "
        Previous 15-min EBC counter inv.
        :This OID indicates that the previous
        15-min Coding Violation counter
        is invalid
        "
	::= { pm200frs02PerfTelecomLinePostFecPast15StatHistoryPort1Entry 2 }


pm200frs02PerfTelecomLinePostFecPast15StatHistoryCvValuePort1 OBJECT-TYPE
	SYNTAX  Unsigned32
	MAX-ACCESS read-only
	STATUS current
	DESCRIPTION
        "
        Previous 15-min EBC counter :This
        OID gives the previous 15-min Coding
        Violation counter value
        "
	::= { pm200frs02PerfTelecomLinePostFecPast15StatHistoryPort1Entry 3 }


pm200frs02PerfTelecomLinePostFecPast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pm200frs02PerfTelecomLinePostFecPast15StatHistoryPort1Entry 4 }


pm200frs02PerfTelecomLinePostFecPast15StatHistoryEsValuePort1 OBJECT-TYPE
	SYNTAX  Unsigned32
	MAX-ACCESS read-only
	STATUS current
	DESCRIPTION
        "
        Previous 15-min ES counter :This
        OID gives the previous 15-min Errored
        Second counter value
        "
	::= { pm200frs02PerfTelecomLinePostFecPast15StatHistoryPort1Entry 5 }


pm200frs02PerfTelecomLinePostFecPast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pm200frs02PerfTelecomLinePostFecPast15StatHistoryPort1Entry 6 }


pm200frs02PerfTelecomLinePostFecPast15StatHistorySesValuePort1 OBJECT-TYPE
	SYNTAX  Unsigned32
	MAX-ACCESS read-only
	STATUS current
	DESCRIPTION
        "
        Previous 15-min SES counter :This
        OID gives the previous 15-min severely
        Errored Second counter value
        "
	::= { pm200frs02PerfTelecomLinePostFecPast15StatHistoryPort1Entry 7 }


pm200frs02PerfTelecomLinePostFecPast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pm200frs02PerfTelecomLinePostFecPast15StatHistoryPort1Entry 8 }


pm200frs02PerfTelecomLinePostFecPast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pm200frs02PerfTelecomLinePostFecPast15StatHistoryPort1Entry 9 }


pm200frs02PerfTelecomLinePostFecPast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pm200frs02PerfTelecomLinePostFecPast15StatHistoryPort1Entry 10 }


pm200frs02PerfTelecomLinePostFecPast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pm200frs02PerfTelecomLinePostFecPast15StatHistoryPort1Entry 11 }


--- *****************************************************
---     Leaf of the telecomLinePostFecCurrent24Stat
--- *****************************************************
--- *********************************************************
---     TABLE for the pm200frs02PerfTelecomLinePostFecCurrent24Stat articles
--- *********************************************************

pm200frs02PerfTelecomLinePostFecCurrent24StatTable OBJECT-TYPE
	SYNTAX  SEQUENCE OF Pm200frs02PerfTelecomLinePostFecCurrent24StatEntry
	MAX-ACCESS not-accessible
	STATUS current
	DESCRIPTION
        "
        List of pm200frs02PerfTelecomLinePostFecCurrent24Stat
        Article
        "
	::= { pm200frs02MonPerfLine 338 }


pm200frs02PerfTelecomLinePostFecCurrent24StatEntry OBJECT-TYPE
	SYNTAX Pm200frs02PerfTelecomLinePostFecCurrent24StatEntry
	MAX-ACCESS not-accessible
	STATUS current
	DESCRIPTION
        "
        Row definition for the pm200frs02PerfTelecomLinePostFecCurrent24Stat
        table
        "
	INDEX   { pm200frs02PerfTelecomLinePostFecCurrent24StatIndex }
	::= { pm200frs02PerfTelecomLinePostFecCurrent24StatTable 1 }


Pm200frs02PerfTelecomLinePostFecCurrent24StatEntry ::=
	SEQUENCE {
	pm200frs02PerfTelecomLinePostFecCurrent24StatIndex
		INTEGER,
	pm200frs02PerfTelecomLinePostFecCurrent24StatInvCvPortn
		EkiOnOff,
	pm200frs02PerfTelecomLinePostFecCurrent24StatCvValuePortn
		Unsigned32,
	pm200frs02PerfTelecomLinePostFecCurrent24StatInvEsPortn
		EkiOnOff,
	pm200frs02PerfTelecomLinePostFecCurrent24StatEsValuePortn
		Unsigned32,
	pm200frs02PerfTelecomLinePostFecCurrent24StatInvSesPortn
		EkiOnOff,
	pm200frs02PerfTelecomLinePostFecCurrent24StatSesValuePortn
		Unsigned32,
	pm200frs02PerfTelecomLinePostFecCurrent24StatInvSefsPortn
		EkiOnOff,
	pm200frs02PerfTelecomLinePostFecCurrent24StatSefsValuePortn
		Unsigned32,
	pm200frs02PerfTelecomLinePostFecCurrent24StatInvUasPortn
		EkiOnOff,
	pm200frs02PerfTelecomLinePostFecCurrent24StatUasValuePortn
		Unsigned32
	}


pm200frs02PerfTelecomLinePostFecCurrent24StatIndex OBJECT-TYPE
	SYNTAX  INTEGER(0..128)
	MAX-ACCESS  read-only
	STATUS current
	DESCRIPTION
        "
        Index definition for the pm200frs02PerfTelecomLinePostFecCurrent24Stat
        table
        "
	::= { pm200frs02PerfTelecomLinePostFecCurrent24StatEntry 1 }


pm200frs02PerfTelecomLinePostFecCurrent24StatInvCvPortn OBJECT-TYPE
	SYNTAX  EkiOnOff
	MAX-ACCESS read-only
	STATUS current
	DESCRIPTION
        "
        Current 24-hours EBC counter inv.
        :This OID indicates that the current
        24-hours Coding Violation counter
        is invalid
        "
	::= { pm200frs02PerfTelecomLinePostFecCurrent24StatEntry 2 }


pm200frs02PerfTelecomLinePostFecCurrent24StatCvValuePortn OBJECT-TYPE
	SYNTAX  Unsigned32
	MAX-ACCESS read-only
	STATUS current
	DESCRIPTION
        "
        Current 24-hours EBC counter :This
        OID gives the current 24-hours
         Coding Violation counter value
        "
	::= { pm200frs02PerfTelecomLinePostFecCurrent24StatEntry 3 }


pm200frs02PerfTelecomLinePostFecCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pm200frs02PerfTelecomLinePostFecCurrent24StatEntry 4 }


pm200frs02PerfTelecomLinePostFecCurrent24StatEsValuePortn OBJECT-TYPE
	SYNTAX  Unsigned32
	MAX-ACCESS read-only
	STATUS current
	DESCRIPTION
        "
        Current 24-hours ES counter :This
        OID gives the current 24-hours
         Errored Second counter value
        "
	::= { pm200frs02PerfTelecomLinePostFecCurrent24StatEntry 5 }


pm200frs02PerfTelecomLinePostFecCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pm200frs02PerfTelecomLinePostFecCurrent24StatEntry 6 }


pm200frs02PerfTelecomLinePostFecCurrent24StatSesValuePortn OBJECT-TYPE
	SYNTAX  Unsigned32
	MAX-ACCESS read-only
	STATUS current
	DESCRIPTION
        "
        Current 24-hours SES counter :This
        OID gives the current 24-hours
         severely Errored Second counter
        value
        "
	::= { pm200frs02PerfTelecomLinePostFecCurrent24StatEntry 7 }


pm200frs02PerfTelecomLinePostFecCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pm200frs02PerfTelecomLinePostFecCurrent24StatEntry 8 }


pm200frs02PerfTelecomLinePostFecCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pm200frs02PerfTelecomLinePostFecCurrent24StatEntry 9 }


pm200frs02PerfTelecomLinePostFecCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pm200frs02PerfTelecomLinePostFecCurrent24StatEntry 10 }


pm200frs02PerfTelecomLinePostFecCurrent24StatUasValuePortn OBJECT-TYPE
	SYNTAX  Unsigned32
	MAX-ACCESS read-only
	STATUS current
	DESCRIPTION
        "
        Current 24-hours UAS counter :This
        OID gives the current 24-hours
         UnAvailable Second counter value
        "
	::= { pm200frs02PerfTelecomLinePostFecCurrent24StatEntry 11 }


--- *****************************************************
---     Leaf of the telecomLinePostFecPast24Stat
--- *****************************************************
--- *********************************************************
---     TABLE for the pm200frs02PerfTelecomLinePostFecPast24StatHistory articles
--- *********************************************************

pm200frs02PerfTelecomLinePostFecPast24StatHistoryPort1Table OBJECT-TYPE
	SYNTAX  SEQUENCE OF Pm200frs02PerfTelecomLinePostFecPast24StatHistoryPort1Entry
	MAX-ACCESS not-accessible
	STATUS current
	DESCRIPTION
        "
        List of pm200frs02PerfTelecomLinePostFecPast24StatHistory
        Article
        "
	::= { pm200frs02MonPerfLine 339 }


pm200frs02PerfTelecomLinePostFecPast24StatHistoryPort1Entry OBJECT-TYPE
	SYNTAX Pm200frs02PerfTelecomLinePostFecPast24StatHistoryPort1Entry
	MAX-ACCESS not-accessible
	STATUS current
	DESCRIPTION
        "
        Row definition for the pm200frs02PerfTelecomLinePostFecPast24StatHistory
        table
        "
	INDEX   { pm200frs02PerfTelecomLinePostFecPast24StatHistoryPort1Index }
	::= { pm200frs02PerfTelecomLinePostFecPast24StatHistoryPort1Table 1 }


Pm200frs02PerfTelecomLinePostFecPast24StatHistoryPort1Entry ::=
	SEQUENCE {
	pm200frs02PerfTelecomLinePostFecPast24StatHistoryPort1Index
		INTEGER,
	pm200frs02PerfTelecomLinePostFecPast24StatHistoryInvCvPort1
		EkiOnOff,
	pm200frs02PerfTelecomLinePostFecPast24StatHistoryCvValuePort1
		Unsigned32,
	pm200frs02PerfTelecomLinePostFecPast24StatHistoryInvEsPort1
		EkiOnOff,
	pm200frs02PerfTelecomLinePostFecPast24StatHistoryEsValuePort1
		Unsigned32,
	pm200frs02PerfTelecomLinePostFecPast24StatHistoryInvSesPort1
		EkiOnOff,
	pm200frs02PerfTelecomLinePostFecPast24StatHistorySesValuePort1
		Unsigned32,
	pm200frs02PerfTelecomLinePostFecPast24StatHistoryInvSefsPort1
		EkiOnOff,
	pm200frs02PerfTelecomLinePostFecPast24StatHistorySefsValuePort1
		Unsigned32,
	pm200frs02PerfTelecomLinePostFecPast24StatHistoryInvUasPort1
		EkiOnOff,
	pm200frs02PerfTelecomLinePostFecPast24StatHistoryUasValuePort1
		Unsigned32
	}


pm200frs02PerfTelecomLinePostFecPast24StatHistoryPort1Index OBJECT-TYPE
	SYNTAX  INTEGER(0..128)
	MAX-ACCESS  read-only
	STATUS current
	DESCRIPTION
        "
        Index definition for the pm200frs02PerfTelecomLinePostFecPast24StatHistory
        table
        "
	::= { pm200frs02PerfTelecomLinePostFecPast24StatHistoryPort1Entry 1 }


pm200frs02PerfTelecomLinePostFecPast24StatHistoryInvCvPort1 OBJECT-TYPE
	SYNTAX  EkiOnOff
	MAX-ACCESS read-only
	STATUS current
	DESCRIPTION
        "
        Previous 24-hours EBC counter
         inv. :This OID indicates that
         the previous 24-hours Coding Violation
        counter is invalid
        "
	::= { pm200frs02PerfTelecomLinePostFecPast24StatHistoryPort1Entry 2 }


pm200frs02PerfTelecomLinePostFecPast24StatHistoryCvValuePort1 OBJECT-TYPE
	SYNTAX  Unsigned32
	MAX-ACCESS read-only
	STATUS current
	DESCRIPTION
        "
        Previous 24-hours EBC counter
         :This OID gives the previous 24-hours
        Coding Violation counter value
        "
	::= { pm200frs02PerfTelecomLinePostFecPast24StatHistoryPort1Entry 3 }


pm200frs02PerfTelecomLinePostFecPast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pm200frs02PerfTelecomLinePostFecPast24StatHistoryPort1Entry 4 }


pm200frs02PerfTelecomLinePostFecPast24StatHistoryEsValuePort1 OBJECT-TYPE
	SYNTAX  Unsigned32
	MAX-ACCESS read-only
	STATUS current
	DESCRIPTION
        "
        Previous 24-hours ES counter :This
        OID gives the previous 24-hours
        Errored Second counter value
        "
	::= { pm200frs02PerfTelecomLinePostFecPast24StatHistoryPort1Entry 5 }


pm200frs02PerfTelecomLinePostFecPast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pm200frs02PerfTelecomLinePostFecPast24StatHistoryPort1Entry 6 }


pm200frs02PerfTelecomLinePostFecPast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pm200frs02PerfTelecomLinePostFecPast24StatHistoryPort1Entry 7 }


pm200frs02PerfTelecomLinePostFecPast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm200frs02PerfTelecomLinePostFecPast24StatHistoryPort1Entry 8 }


pm200frs02PerfTelecomLinePostFecPast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pm200frs02PerfTelecomLinePostFecPast24StatHistoryPort1Entry 9 }


pm200frs02PerfTelecomLinePostFecPast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pm200frs02PerfTelecomLinePostFecPast24StatHistoryPort1Entry 10 }


pm200frs02PerfTelecomLinePostFecPast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pm200frs02PerfTelecomLinePostFecPast24StatHistoryPort1Entry 11 }


--- *****************************************************
---     Leaf of the telecomBerLinePreFecCurrent15Stat
--- *****************************************************
--- *********************************************************
---     TABLE for the pm200frs02PerfTelecomBerLinePreFecCurrent15Stat articles
--- *********************************************************

pm200frs02PerfTelecomBerLinePreFecCurrent15StatTable OBJECT-TYPE
	SYNTAX  SEQUENCE OF Pm200frs02PerfTelecomBerLinePreFecCurrent15StatEntry
	MAX-ACCESS not-accessible
	STATUS current
	DESCRIPTION
        "
        List of pm200frs02PerfTelecomBerLinePreFecCurrent15Stat
        Article
        "
	::= { pm200frs02MonPerfLine 352 }


pm200frs02PerfTelecomBerLinePreFecCurrent15StatEntry OBJECT-TYPE
	SYNTAX Pm200frs02PerfTelecomBerLinePreFecCurrent15StatEntry
	MAX-ACCESS not-accessible
	STATUS current
	DESCRIPTION
        "
        Row definition for the pm200frs02PerfTelecomBerLinePreFecCurrent15Stat
        table
        "
	INDEX   { pm200frs02PerfTelecomBerLinePreFecCurrent15StatIndex }
	::= { pm200frs02PerfTelecomBerLinePreFecCurrent15StatTable 1 }


Pm200frs02PerfTelecomBerLinePreFecCurrent15StatEntry ::=
	SEQUENCE {
	pm200frs02PerfTelecomBerLinePreFecCurrent15StatIndex
		INTEGER,
	pm200frs02PerfTelecomBerLinePreFecCurrent15StatInvBerPortn
		EkiOnOff,
	pm200frs02PerfTelecomBerLinePreFecCurrent15StatBerValuePortn
		Unsigned32,
	pm200frs02PerfTelecomBerLinePreFecCurrent15StatInvMinBerPortn
		EkiOnOff,
	pm200frs02PerfTelecomBerLinePreFecCurrent15StatMinBerValuePortn
		Unsigned32,
	pm200frs02PerfTelecomBerLinePreFecCurrent15StatInvMaxBerPortn
		EkiOnOff,
	pm200frs02PerfTelecomBerLinePreFecCurrent15StatMaxBerValuePortn
		Unsigned32
	}


pm200frs02PerfTelecomBerLinePreFecCurrent15StatIndex OBJECT-TYPE
	SYNTAX  INTEGER(0..128)
	MAX-ACCESS  read-only
	STATUS current
	DESCRIPTION
        "
        Index definition for the pm200frs02PerfTelecomBerLinePreFecCurrent15Stat
        table
        "
	::= { pm200frs02PerfTelecomBerLinePreFecCurrent15StatEntry 1 }


pm200frs02PerfTelecomBerLinePreFecCurrent15StatInvBerPortn OBJECT-TYPE
	SYNTAX  EkiOnOff
	MAX-ACCESS read-only
	STATUS current
	DESCRIPTION
        "
        Current 15-min BER counter inv.
        :This OID indicates that the current
        15-min Coding Violation counter
        is invalid
        "
	::= { pm200frs02PerfTelecomBerLinePreFecCurrent15StatEntry 2 }


pm200frs02PerfTelecomBerLinePreFecCurrent15StatBerValuePortn OBJECT-TYPE
	SYNTAX  Unsigned32
	MAX-ACCESS read-only
	STATUS current
	DESCRIPTION
        "
        Current 15-min BER counter :This
        OID gives the current 15-min Coding
        Violation counter value
        "
	::= { pm200frs02PerfTelecomBerLinePreFecCurrent15StatEntry 3 }


pm200frs02PerfTelecomBerLinePreFecCurrent15StatInvMinBerPortn OBJECT-TYPE
	SYNTAX  EkiOnOff
	MAX-ACCESS read-only
	STATUS current
	DESCRIPTION
        "
        Current 15-min MinBER counter
         inv. :This OID indicates that
         the current 15-min Errored Second
        counter is invalid
        "
	::= { pm200frs02PerfTelecomBerLinePreFecCurrent15StatEntry 4 }


pm200frs02PerfTelecomBerLinePreFecCurrent15StatMinBerValuePortn OBJECT-TYPE
	SYNTAX  Unsigned32
	MAX-ACCESS read-only
	STATUS current
	DESCRIPTION
        "
        Current 15-min MinBER counter
         :This OID gives the current 15-min
        Errored Second counter value
        "
	::= { pm200frs02PerfTelecomBerLinePreFecCurrent15StatEntry 5 }


pm200frs02PerfTelecomBerLinePreFecCurrent15StatInvMaxBerPortn OBJECT-TYPE
	SYNTAX  EkiOnOff
	MAX-ACCESS read-only
	STATUS current
	DESCRIPTION
        "
        Current 15-min MaxBER counter
         inv. :This OID indicates that
         the current 15-min severely Errored
        Second counter is invalid
        "
	::= { pm200frs02PerfTelecomBerLinePreFecCurrent15StatEntry 6 }


pm200frs02PerfTelecomBerLinePreFecCurrent15StatMaxBerValuePortn OBJECT-TYPE
	SYNTAX  Unsigned32
	MAX-ACCESS read-only
	STATUS current
	DESCRIPTION
        "
        Current 15-min MaxBER counter
         :This OID gives the current 15-min
        severely Errored Second counter
        value
        "
	::= { pm200frs02PerfTelecomBerLinePreFecCurrent15StatEntry 7 }


--- *****************************************************
---     Leaf of the telecomBerLinePreFecPast15Stat
--- *****************************************************
--- *********************************************************
---     TABLE for the pm200frs02PerfTelecomBerLinePreFecPast15StatHistory articles
--- *********************************************************

pm200frs02PerfTelecomBerLinePreFecPast15StatHistoryPort1Table OBJECT-TYPE
	SYNTAX  SEQUENCE OF Pm200frs02PerfTelecomBerLinePreFecPast15StatHistoryPort1Entry
	MAX-ACCESS not-accessible
	STATUS current
	DESCRIPTION
        "
        List of pm200frs02PerfTelecomBerLinePreFecPast15StatHistory
        Article
        "
	::= { pm200frs02MonPerfLine 353 }


pm200frs02PerfTelecomBerLinePreFecPast15StatHistoryPort1Entry OBJECT-TYPE
	SYNTAX Pm200frs02PerfTelecomBerLinePreFecPast15StatHistoryPort1Entry
	MAX-ACCESS not-accessible
	STATUS current
	DESCRIPTION
        "
        Row definition for the pm200frs02PerfTelecomBerLinePreFecPast15StatHistory
        table
        "
	INDEX   { pm200frs02PerfTelecomBerLinePreFecPast15StatHistoryPort1Index }
	::= { pm200frs02PerfTelecomBerLinePreFecPast15StatHistoryPort1Table 1 }


Pm200frs02PerfTelecomBerLinePreFecPast15StatHistoryPort1Entry ::=
	SEQUENCE {
	pm200frs02PerfTelecomBerLinePreFecPast15StatHistoryPort1Index
		INTEGER,
	pm200frs02PerfTelecomBerLinePreFecPast15StatHistoryInvBerPort1
		EkiOnOff,
	pm200frs02PerfTelecomBerLinePreFecPast15StatHistoryBerValuePort1
		Unsigned32,
	pm200frs02PerfTelecomBerLinePreFecPast15StatHistoryInvMinBerPort1
		EkiOnOff,
	pm200frs02PerfTelecomBerLinePreFecPast15StatHistoryMinBerValuePort1
		Unsigned32,
	pm200frs02PerfTelecomBerLinePreFecPast15StatHistoryInvMaxBerPort1
		EkiOnOff,
	pm200frs02PerfTelecomBerLinePreFecPast15StatHistoryMaxBerValuePort1
		Unsigned32
	}


pm200frs02PerfTelecomBerLinePreFecPast15StatHistoryPort1Index OBJECT-TYPE
	SYNTAX  INTEGER(0..128)
	MAX-ACCESS  read-only
	STATUS current
	DESCRIPTION
        "
        Index definition for the pm200frs02PerfTelecomBerLinePreFecPast15StatHistory
        table
        "
	::= { pm200frs02PerfTelecomBerLinePreFecPast15StatHistoryPort1Entry 1 }


pm200frs02PerfTelecomBerLinePreFecPast15StatHistoryInvBerPort1 OBJECT-TYPE
	SYNTAX  EkiOnOff
	MAX-ACCESS read-only
	STATUS current
	DESCRIPTION
        "
        Previous 15-min BER counter inv.
        :This OID indicates that the previous
        15-min Coding Violation counter
        is invalid
        "
	::= { pm200frs02PerfTelecomBerLinePreFecPast15StatHistoryPort1Entry 2 }


pm200frs02PerfTelecomBerLinePreFecPast15StatHistoryBerValuePort1 OBJECT-TYPE
	SYNTAX  Unsigned32
	MAX-ACCESS read-only
	STATUS current
	DESCRIPTION
        "
        Previous 15-min BER counter :This
        OID gives the previous 15-min Coding
        Violation counter value
        "
	::= { pm200frs02PerfTelecomBerLinePreFecPast15StatHistoryPort1Entry 3 }


pm200frs02PerfTelecomBerLinePreFecPast15StatHistoryInvMinBerPort1 OBJECT-TYPE
	SYNTAX  EkiOnOff
	MAX-ACCESS read-only
	STATUS current
	DESCRIPTION
        "
        Previous 15-min MinBER counter
        inv. :This OID indicates that the
        previous 15-min Errored Second
         counter is invalid
        "
	::= { pm200frs02PerfTelecomBerLinePreFecPast15StatHistoryPort1Entry 4 }


pm200frs02PerfTelecomBerLinePreFecPast15StatHistoryMinBerValuePort1 OBJECT-TYPE
	SYNTAX  Unsigned32
	MAX-ACCESS read-only
	STATUS current
	DESCRIPTION
        "
        Previous 15-min MinBER counter
        :This OID gives the previous 15-min
        Errored Second counter value
        "
	::= { pm200frs02PerfTelecomBerLinePreFecPast15StatHistoryPort1Entry 5 }


pm200frs02PerfTelecomBerLinePreFecPast15StatHistoryInvMaxBerPort1 OBJECT-TYPE
	SYNTAX  EkiOnOff
	MAX-ACCESS read-only
	STATUS current
	DESCRIPTION
        "
        Previous 15-min MaxBER counter
        inv. :This OID indicates that the
        previous 15-min severely Errored
        Second counter is invalid
        "
	::= { pm200frs02PerfTelecomBerLinePreFecPast15StatHistoryPort1Entry 6 }


pm200frs02PerfTelecomBerLinePreFecPast15StatHistoryMaxBerValuePort1 OBJECT-TYPE
	SYNTAX  Unsigned32
	MAX-ACCESS read-only
	STATUS current
	DESCRIPTION
        "
        Previous 15-min MaxBER counter
        :This OID gives the previous 15-min
        severely Errored Second counter
        value
        "
	::= { pm200frs02PerfTelecomBerLinePreFecPast15StatHistoryPort1Entry 7 }


--- *****************************************************
---     Leaf of the telecomBerLinePreFecCurrent24Stat
--- *****************************************************
--- *********************************************************
---     TABLE for the pm200frs02PerfTelecomBerLinePreFecCurrent24Stat articles
--- *********************************************************

pm200frs02PerfTelecomBerLinePreFecCurrent24StatTable OBJECT-TYPE
	SYNTAX  SEQUENCE OF Pm200frs02PerfTelecomBerLinePreFecCurrent24StatEntry
	MAX-ACCESS not-accessible
	STATUS current
	DESCRIPTION
        "
        List of pm200frs02PerfTelecomBerLinePreFecCurrent24Stat
        Article
        "
	::= { pm200frs02MonPerfLine 354 }


pm200frs02PerfTelecomBerLinePreFecCurrent24StatEntry OBJECT-TYPE
	SYNTAX Pm200frs02PerfTelecomBerLinePreFecCurrent24StatEntry
	MAX-ACCESS not-accessible
	STATUS current
	DESCRIPTION
        "
        Row definition for the pm200frs02PerfTelecomBerLinePreFecCurrent24Stat
        table
        "
	INDEX   { pm200frs02PerfTelecomBerLinePreFecCurrent24StatIndex }
	::= { pm200frs02PerfTelecomBerLinePreFecCurrent24StatTable 1 }


Pm200frs02PerfTelecomBerLinePreFecCurrent24StatEntry ::=
	SEQUENCE {
	pm200frs02PerfTelecomBerLinePreFecCurrent24StatIndex
		INTEGER,
	pm200frs02PerfTelecomBerLinePreFecCurrent24StatInvBerPortn
		EkiOnOff,
	pm200frs02PerfTelecomBerLinePreFecCurrent24StatBerValuePortn
		Unsigned32,
	pm200frs02PerfTelecomBerLinePreFecCurrent24StatInvMinBerPortn
		EkiOnOff,
	pm200frs02PerfTelecomBerLinePreFecCurrent24StatMinBerValuePortn
		Unsigned32,
	pm200frs02PerfTelecomBerLinePreFecCurrent24StatInvMaxBerPortn
		EkiOnOff,
	pm200frs02PerfTelecomBerLinePreFecCurrent24StatMaxBerValuePortn
		Unsigned32
	}


pm200frs02PerfTelecomBerLinePreFecCurrent24StatIndex OBJECT-TYPE
	SYNTAX  INTEGER(0..128)
	MAX-ACCESS  read-only
	STATUS current
	DESCRIPTION
        "
        Index definition for the pm200frs02PerfTelecomBerLinePreFecCurrent24Stat
        table
        "
	::= { pm200frs02PerfTelecomBerLinePreFecCurrent24StatEntry 1 }


pm200frs02PerfTelecomBerLinePreFecCurrent24StatInvBerPortn OBJECT-TYPE
	SYNTAX  EkiOnOff
	MAX-ACCESS read-only
	STATUS current
	DESCRIPTION
        "
        Current 24-hours BER counter inv.
        :This OID indicates that the current
        24-hours Coding Violation counter
        is invalid
        "
	::= { pm200frs02PerfTelecomBerLinePreFecCurrent24StatEntry 2 }


pm200frs02PerfTelecomBerLinePreFecCurrent24StatBerValuePortn OBJECT-TYPE
	SYNTAX  Unsigned32
	MAX-ACCESS read-only
	STATUS current
	DESCRIPTION
        "
        Current 24-hours BER counter :This
        OID gives the current 24-hours
         Coding Violation counter value
        "
	::= { pm200frs02PerfTelecomBerLinePreFecCurrent24StatEntry 3 }


pm200frs02PerfTelecomBerLinePreFecCurrent24StatInvMinBerPortn OBJECT-TYPE
	SYNTAX  EkiOnOff
	MAX-ACCESS read-only
	STATUS current
	DESCRIPTION
        "
        Current 24-hoursMinBER counter
        inv. :This OID indicates that the
        current 24-hours Errored Second
        counter is invalid
        "
	::= { pm200frs02PerfTelecomBerLinePreFecCurrent24StatEntry 4 }


pm200frs02PerfTelecomBerLinePreFecCurrent24StatMinBerValuePortn OBJECT-TYPE
	SYNTAX  Unsigned32
	MAX-ACCESS read-only
	STATUS current
	DESCRIPTION
        "
        Current 24-hours MinBER counter
        :This OID gives the current 24-hours
        Errored Second counter value
        "
	::= { pm200frs02PerfTelecomBerLinePreFecCurrent24StatEntry 5 }


pm200frs02PerfTelecomBerLinePreFecCurrent24StatInvMaxBerPortn OBJECT-TYPE
	SYNTAX  EkiOnOff
	MAX-ACCESS read-only
	STATUS current
	DESCRIPTION
        "
        Current 24-hours MaxBER counter
        inv. :This OID indicates that the
        current 24-hours severely Errored
        Second counter is invalid
        "
	::= { pm200frs02PerfTelecomBerLinePreFecCurrent24StatEntry 6 }


pm200frs02PerfTelecomBerLinePreFecCurrent24StatMaxBerValuePortn OBJECT-TYPE
	SYNTAX  Unsigned32
	MAX-ACCESS read-only
	STATUS current
	DESCRIPTION
        "
        Current 24-hours MaxBER counter
        :This OID gives the current 24-hours
        severely Errored Second counter
        value
        "
	::= { pm200frs02PerfTelecomBerLinePreFecCurrent24StatEntry 7 }


--- *****************************************************
---     Leaf of the telecomBerLinePreFecPast24Stat
--- *****************************************************
--- *********************************************************
---     TABLE for the pm200frs02PerfTelecomBerLinePreFecPast24StatHistory articles
--- *********************************************************

pm200frs02PerfTelecomBerLinePreFecPast24StatHistoryPort1Table OBJECT-TYPE
	SYNTAX  SEQUENCE OF Pm200frs02PerfTelecomBerLinePreFecPast24StatHistoryPort1Entry
	MAX-ACCESS not-accessible
	STATUS current
	DESCRIPTION
        "
        List of pm200frs02PerfTelecomBerLinePreFecPast24StatHistory
        Article
        "
	::= { pm200frs02MonPerfLine 355 }


pm200frs02PerfTelecomBerLinePreFecPast24StatHistoryPort1Entry OBJECT-TYPE
	SYNTAX Pm200frs02PerfTelecomBerLinePreFecPast24StatHistoryPort1Entry
	MAX-ACCESS not-accessible
	STATUS current
	DESCRIPTION
        "
        Row definition for the pm200frs02PerfTelecomBerLinePreFecPast24StatHistory
        table
        "
	INDEX   { pm200frs02PerfTelecomBerLinePreFecPast24StatHistoryPort1Index }
	::= { pm200frs02PerfTelecomBerLinePreFecPast24StatHistoryPort1Table 1 }


Pm200frs02PerfTelecomBerLinePreFecPast24StatHistoryPort1Entry ::=
	SEQUENCE {
	pm200frs02PerfTelecomBerLinePreFecPast24StatHistoryPort1Index
		INTEGER,
	pm200frs02PerfTelecomBerLinePreFecPast24StatHistoryInvBerPort1
		EkiOnOff,
	pm200frs02PerfTelecomBerLinePreFecPast24StatHistoryBerValuePort1
		Unsigned32,
	pm200frs02PerfTelecomBerLinePreFecPast24StatHistoryInvMinBerPort1
		EkiOnOff,
	pm200frs02PerfTelecomBerLinePreFecPast24StatHistoryMinBerValuePort1
		Unsigned32,
	pm200frs02PerfTelecomBerLinePreFecPast24StatHistoryInvMaxBerPort1
		EkiOnOff,
	pm200frs02PerfTelecomBerLinePreFecPast24StatHistoryMaxBerValuePort1
		Unsigned32
	}


pm200frs02PerfTelecomBerLinePreFecPast24StatHistoryPort1Index OBJECT-TYPE
	SYNTAX  INTEGER(0..128)
	MAX-ACCESS  read-only
	STATUS current
	DESCRIPTION
        "
        Index definition for the pm200frs02PerfTelecomBerLinePreFecPast24StatHistory
        table
        "
	::= { pm200frs02PerfTelecomBerLinePreFecPast24StatHistoryPort1Entry 1 }


pm200frs02PerfTelecomBerLinePreFecPast24StatHistoryInvBerPort1 OBJECT-TYPE
	SYNTAX  EkiOnOff
	MAX-ACCESS read-only
	STATUS current
	DESCRIPTION
        "
        Previous 24-hours BER counter
         inv. :This OID indicates that
         the previous 24-hours Coding Violation
        counter is invalid
        "
	::= { pm200frs02PerfTelecomBerLinePreFecPast24StatHistoryPort1Entry 2 }


pm200frs02PerfTelecomBerLinePreFecPast24StatHistoryBerValuePort1 OBJECT-TYPE
	SYNTAX  Unsigned32
	MAX-ACCESS read-only
	STATUS current
	DESCRIPTION
        "
        Previous 24-hours BER counter
         :This OID gives the previous 24-hours
        Coding Violation counter value
        "
	::= { pm200frs02PerfTelecomBerLinePreFecPast24StatHistoryPort1Entry 3 }


pm200frs02PerfTelecomBerLinePreFecPast24StatHistoryInvMinBerPort1 OBJECT-TYPE
	SYNTAX  EkiOnOff
	MAX-ACCESS read-only
	STATUS current
	DESCRIPTION
        "
        Previous 24-hours MinBER counter
        inv. :This OID indicates that the
        previous 24-hours Errored Second
        counter is invalid
        "
	::= { pm200frs02PerfTelecomBerLinePreFecPast24StatHistoryPort1Entry 4 }


pm200frs02PerfTelecomBerLinePreFecPast24StatHistoryMinBerValuePort1 OBJECT-TYPE
	SYNTAX  Unsigned32
	MAX-ACCESS read-only
	STATUS current
	DESCRIPTION
        "
        Previous 24-hours MinBER counter
        :This OID gives the previous 24-hours
        Errored Second counter value
        "
	::= { pm200frs02PerfTelecomBerLinePreFecPast24StatHistoryPort1Entry 5 }


pm200frs02PerfTelecomBerLinePreFecPast24StatHistoryInvMaxBerPort1 OBJECT-TYPE
	SYNTAX  EkiOnOff
	MAX-ACCESS read-only
	STATUS current
	DESCRIPTION
        "
        Previous 24-hours MaxBER counter
        inv. :This OID indicates that the
        previous 24-hours severely Errored
        Second counter is invalid
        "
	::= { pm200frs02PerfTelecomBerLinePreFecPast24StatHistoryPort1Entry 6 }


pm200frs02PerfTelecomBerLinePreFecPast24StatHistoryMaxBerValuePort1 OBJECT-TYPE
	SYNTAX  Unsigned32
	MAX-ACCESS read-only
	STATUS current
	DESCRIPTION
        "
        Previous 24-hours MaxBER counter
        :This OID gives the previous 24-hours
        severely Errored Second counter
        value
        "
	::= { pm200frs02PerfTelecomBerLinePreFecPast24StatHistoryPort1Entry 7 }


--- *****************************************************
---     Leaf of the datacomClientCurrent15Stat
--- *****************************************************
--- *********************************************************
---     TABLE for the pm200frs02PerfDatacomClientCurrent15Stat articles
--- *********************************************************

pm200frs02PerfDatacomClientCurrent15StatTable OBJECT-TYPE
	SYNTAX  SEQUENCE OF Pm200frs02PerfDatacomClientCurrent15StatEntry
	MAX-ACCESS not-accessible
	STATUS current
	DESCRIPTION
        "
        List of pm200frs02PerfDatacomClientCurrent15Stat
        Article
        "
	::= { pm200frs02MonPerfClient 848 }


pm200frs02PerfDatacomClientCurrent15StatEntry OBJECT-TYPE
	SYNTAX Pm200frs02PerfDatacomClientCurrent15StatEntry
	MAX-ACCESS not-accessible
	STATUS current
	DESCRIPTION
        "
        Row definition for the pm200frs02PerfDatacomClientCurrent15Stat
        table
        "
	INDEX   { pm200frs02PerfDatacomClientCurrent15StatIndex }
	::= { pm200frs02PerfDatacomClientCurrent15StatTable 1 }


Pm200frs02PerfDatacomClientCurrent15StatEntry ::=
	SEQUENCE {
	pm200frs02PerfDatacomClientCurrent15StatIndex
		INTEGER,
	pm200frs02perfdatacomclientCurrent15StatOutPacketCountInvPortn
		EkiOnOff,
	pm200frs02perfdatacomclientCurrent15StatOutPacketCountPortn
		Counter64,
	pm200frs02perfdatacomclientCurrent15StatOutCrcCountInvPortn
		EkiOnOff,
	pm200frs02perfdatacomclientCurrent15StatOutCrcCountPortn
		Counter64,
	pm200frs02perfdatacomclientCurrent15StatInPacketCountInvPortn
		EkiOnOff,
	pm200frs02perfdatacomclientCurrent15StatInPacketCountPortn
		Counter64,
	pm200frs02perfdatacomclientCurrent15StatInCrcCountInvPortn
		EkiOnOff,
	pm200frs02perfdatacomclientCurrent15StatInCrcCountPortn
		Counter64
	}


pm200frs02PerfDatacomClientCurrent15StatIndex OBJECT-TYPE
	SYNTAX  INTEGER(0..128)
	MAX-ACCESS  read-only
	STATUS current
	DESCRIPTION
        "
        Index definition for the pm200frs02PerfDatacomClientCurrent15Stat
        table
        "
	::= { pm200frs02PerfDatacomClientCurrent15StatEntry 1 }


pm200frs02perfdatacomclientCurrent15StatOutPacketCountInvPortn OBJECT-TYPE
	SYNTAX  EkiOnOff
	MAX-ACCESS read-only
	STATUS current
	DESCRIPTION
        "
        Client Current 15-min Output Packet
        counter inv. :This OID indicates
        that the current 15-min Output
         Packets counter is invalid
        "
	::= { pm200frs02PerfDatacomClientCurrent15StatEntry 30 }


pm200frs02perfdatacomclientCurrent15StatOutPacketCountPortn OBJECT-TYPE
	SYNTAX  Counter64
	MAX-ACCESS read-only
	STATUS current
	DESCRIPTION
        "
        Client Current 15-min Output Packet
        counter :This OID gives the current
        15-min Output Packets counter value
        "
	::= { pm200frs02PerfDatacomClientCurrent15StatEntry 31 }


pm200frs02perfdatacomclientCurrent15StatOutCrcCountInvPortn OBJECT-TYPE
	SYNTAX  EkiOnOff
	MAX-ACCESS read-only
	STATUS current
	DESCRIPTION
        "
        Client Current 15-min Output CRC
        counter inv. :This OID indicates
        that the current 15-min Output
         CRC counter is invalid
        "
	::= { pm200frs02PerfDatacomClientCurrent15StatEntry 28 }


pm200frs02perfdatacomclientCurrent15StatOutCrcCountPortn OBJECT-TYPE
	SYNTAX  Counter64
	MAX-ACCESS read-only
	STATUS current
	DESCRIPTION
        "
        Client Current 15-min Output CRC
        counter :This OID gives the current
        15-min Output CRC counter value
        "
	::= { pm200frs02PerfDatacomClientCurrent15StatEntry 29 }


pm200frs02perfdatacomclientCurrent15StatInPacketCountInvPortn OBJECT-TYPE
	SYNTAX  EkiOnOff
	MAX-ACCESS read-only
	STATUS current
	DESCRIPTION
        "
        Client Current 15-min Input Packet
        counter inv. :This OID indicates
        that the current 15-min Input Packet
        counter is invalid
        "
	::= { pm200frs02PerfDatacomClientCurrent15StatEntry 6 }


pm200frs02perfdatacomclientCurrent15StatInPacketCountPortn OBJECT-TYPE
	SYNTAX  Counter64
	MAX-ACCESS read-only
	STATUS current
	DESCRIPTION
        "
        Client Current 15-min Input Packet
        counter :This OID gives the current
        15-min Input Packet counter value
        "
	::= { pm200frs02PerfDatacomClientCurrent15StatEntry 7 }


pm200frs02perfdatacomclientCurrent15StatInCrcCountInvPortn OBJECT-TYPE
	SYNTAX  EkiOnOff
	MAX-ACCESS read-only
	STATUS current
	DESCRIPTION
        "
        Client Current 15-min Input CRC
        counter inv. :This OID indicates
        that the current 15-min Input CRC
        counter is invalid
        "
	::= { pm200frs02PerfDatacomClientCurrent15StatEntry 4 }


pm200frs02perfdatacomclientCurrent15StatInCrcCountPortn OBJECT-TYPE
	SYNTAX  Counter64
	MAX-ACCESS read-only
	STATUS current
	DESCRIPTION
        "
        Client Current 15-min Input CRC
        counter :This OID gives the current
        15-min Input CRC counter value
        "
	::= { pm200frs02PerfDatacomClientCurrent15StatEntry 5 }


--- *****************************************************
---     Leaf of the datacomClientPast15Stat
--- *****************************************************
--- *********************************************************
---     TABLE for the pm200frs02PerfDatacomClientPast15StatHistory articles
--- *********************************************************

pm200frs02PerfDatacomClientPast15StatHistoryPort1Table OBJECT-TYPE
	SYNTAX  SEQUENCE OF Pm200frs02PerfDatacomClientPast15StatHistoryPort1Entry
	MAX-ACCESS not-accessible
	STATUS current
	DESCRIPTION
        "
        List of pm200frs02PerfDatacomClientPast15StatHistory
        Article
        "
	::= { pm200frs02MonPerfClient 880 }


pm200frs02PerfDatacomClientPast15StatHistoryPort1Entry OBJECT-TYPE
	SYNTAX Pm200frs02PerfDatacomClientPast15StatHistoryPort1Entry
	MAX-ACCESS not-accessible
	STATUS current
	DESCRIPTION
        "
        Row definition for the pm200frs02PerfDatacomClientPast15StatHistory
        table
        "
	INDEX   { pm200frs02PerfDatacomClientPast15StatHistoryPort1Index }
	::= { pm200frs02PerfDatacomClientPast15StatHistoryPort1Table 1 }


Pm200frs02PerfDatacomClientPast15StatHistoryPort1Entry ::=
	SEQUENCE {
	pm200frs02PerfDatacomClientPast15StatHistoryPort1Index
		INTEGER,
	pm200frs02perfdatacomclientPast15StatOutPacketCountInvPort1
		EkiOnOff,
	pm200frs02perfdatacomclientPast15StatOutPacketCountPort1
		Counter64,
	pm200frs02perfdatacomclientPast15StatOutCrcCountInvPort1
		EkiOnOff,
	pm200frs02perfdatacomclientPast15StatOutCrcCountPort1
		Counter64,
	pm200frs02perfdatacomclientPast15StatInPacketCountInvPort1
		EkiOnOff,
	pm200frs02perfdatacomclientPast15StatInPacketCountPort1
		Counter64,
	pm200frs02perfdatacomclientPast15StatInCrcCountInvPort1
		EkiOnOff,
	pm200frs02perfdatacomclientPast15StatInCrcCountPort1
		Counter64
	}


pm200frs02PerfDatacomClientPast15StatHistoryPort1Index OBJECT-TYPE
	SYNTAX  INTEGER(0..128)
	MAX-ACCESS  read-only
	STATUS current
	DESCRIPTION
        "
        Index definition for the pm200frs02PerfDatacomClientPast15StatHistory
        table
        "
	::= { pm200frs02PerfDatacomClientPast15StatHistoryPort1Entry 1 }


pm200frs02perfdatacomclientPast15StatOutPacketCountInvPort1 OBJECT-TYPE
	SYNTAX  EkiOnOff
	MAX-ACCESS read-only
	STATUS current
	DESCRIPTION
        "
        Client Past 15-min Output Packet
        counter inv. :This OID indicates
        that the past 15-min Output Packets
        counter is invalid
        "
	::= { pm200frs02PerfDatacomClientPast15StatHistoryPort1Entry 30 }


pm200frs02perfdatacomclientPast15StatOutPacketCountPort1 OBJECT-TYPE
	SYNTAX  Counter64
	MAX-ACCESS read-only
	STATUS current
	DESCRIPTION
        "
        Client Past 15-min Output Packet
        counter :This OID gives the past
        15-min Output Packets counter value
        "
	::= { pm200frs02PerfDatacomClientPast15StatHistoryPort1Entry 31 }


pm200frs02perfdatacomclientPast15StatOutCrcCountInvPort1 OBJECT-TYPE
	SYNTAX  EkiOnOff
	MAX-ACCESS read-only
	STATUS current
	DESCRIPTION
        "
        Client Past 15-min Output CRC
         counter inv. :This OID indicates
        that the past 15-min Output CRC
        counter is invalid
        "
	::= { pm200frs02PerfDatacomClientPast15StatHistoryPort1Entry 28 }


pm200frs02perfdatacomclientPast15StatOutCrcCountPort1 OBJECT-TYPE
	SYNTAX  Counter64
	MAX-ACCESS read-only
	STATUS current
	DESCRIPTION
        "
        Client Past 15-min Output CRC
         counter :This OID gives the past
        15-min Output CRC counter value
        "
	::= { pm200frs02PerfDatacomClientPast15StatHistoryPort1Entry 29 }


pm200frs02perfdatacomclientPast15StatInPacketCountInvPort1 OBJECT-TYPE
	SYNTAX  EkiOnOff
	MAX-ACCESS read-only
	STATUS current
	DESCRIPTION
        "
        Client Past 15-min Input Packet
        counter inv. :This OID indicates
        that the past 15-min Input Packet
        counter is invalid
        "
	::= { pm200frs02PerfDatacomClientPast15StatHistoryPort1Entry 6 }


pm200frs02perfdatacomclientPast15StatInPacketCountPort1 OBJECT-TYPE
	SYNTAX  Counter64
	MAX-ACCESS read-only
	STATUS current
	DESCRIPTION
        "
        Client Past 15-min Input Packet
        counter :This OID gives the past
        15-min Input Packet counter value
        "
	::= { pm200frs02PerfDatacomClientPast15StatHistoryPort1Entry 7 }


pm200frs02perfdatacomclientPast15StatInCrcCountInvPort1 OBJECT-TYPE
	SYNTAX  EkiOnOff
	MAX-ACCESS read-only
	STATUS current
	DESCRIPTION
        "
        Client Past 15-min Input CRC counter
        inv. :This OID indicates that the
        past 15-min Input CRC counter is
        invalid
        "
	::= { pm200frs02PerfDatacomClientPast15StatHistoryPort1Entry 4 }


pm200frs02perfdatacomclientPast15StatInCrcCountPort1 OBJECT-TYPE
	SYNTAX  Counter64
	MAX-ACCESS read-only
	STATUS current
	DESCRIPTION
        "
        Client Past 15-min Input CRC counter
        :This OID gives the past 15-min
        Input CRC counter value
        "
	::= { pm200frs02PerfDatacomClientPast15StatHistoryPort1Entry 5 }


--- *****************************************************
---     Leaf of the datacomClientCurrent24Stat
--- *****************************************************
--- *********************************************************
---     TABLE for the pm200frs02PerfDatacomClientCurrent24Stat articles
--- *********************************************************

pm200frs02PerfDatacomClientCurrent24StatTable OBJECT-TYPE
	SYNTAX  SEQUENCE OF Pm200frs02PerfDatacomClientCurrent24StatEntry
	MAX-ACCESS not-accessible
	STATUS current
	DESCRIPTION
        "
        List of pm200frs02PerfDatacomClientCurrent24Stat
        Article
        "
	::= { pm200frs02MonPerfClient 912 }


pm200frs02PerfDatacomClientCurrent24StatEntry OBJECT-TYPE
	SYNTAX Pm200frs02PerfDatacomClientCurrent24StatEntry
	MAX-ACCESS not-accessible
	STATUS current
	DESCRIPTION
        "
        Row definition for the pm200frs02PerfDatacomClientCurrent24Stat
        table
        "
	INDEX   { pm200frs02PerfDatacomClientCurrent24StatIndex }
	::= { pm200frs02PerfDatacomClientCurrent24StatTable 1 }


Pm200frs02PerfDatacomClientCurrent24StatEntry ::=
	SEQUENCE {
	pm200frs02PerfDatacomClientCurrent24StatIndex
		INTEGER,
	pm200frs02perfdatacomclientCurrent24StatOutPacketCountInvPortn
		EkiOnOff,
	pm200frs02perfdatacomclientCurrent24StatOutPacketCountPortn
		Counter64,
	pm200frs02perfdatacomclientCurrent24StatOutCrcCountInvPortn
		EkiOnOff,
	pm200frs02perfdatacomclientCurrent24StatOutCrcCountPortn
		Counter64,
	pm200frs02perfdatacomclientCurrent24StatInPacketCountInvPortn
		EkiOnOff,
	pm200frs02perfdatacomclientCurrent24StatInPacketCountPortn
		Counter64,
	pm200frs02perfdatacomclientCurrent24StatInCrcCountInvPortn
		EkiOnOff,
	pm200frs02perfdatacomclientCurrent24StatInCrcCountPortn
		Counter64
	}


pm200frs02PerfDatacomClientCurrent24StatIndex OBJECT-TYPE
	SYNTAX  INTEGER(0..128)
	MAX-ACCESS  read-only
	STATUS current
	DESCRIPTION
        "
        Index definition for the pm200frs02PerfDatacomClientCurrent24Stat
        table
        "
	::= { pm200frs02PerfDatacomClientCurrent24StatEntry 1 }


pm200frs02perfdatacomclientCurrent24StatOutPacketCountInvPortn OBJECT-TYPE
	SYNTAX  EkiOnOff
	MAX-ACCESS read-only
	STATUS current
	DESCRIPTION
        "
        Client Current 24-hours Output
        Packet counter inv. :This OID indicates
        that the current 24-hours Output
        Packets counter is invalid
        "
	::= { pm200frs02PerfDatacomClientCurrent24StatEntry 30 }


pm200frs02perfdatacomclientCurrent24StatOutPacketCountPortn OBJECT-TYPE
	SYNTAX  Counter64
	MAX-ACCESS read-only
	STATUS current
	DESCRIPTION
        "
        Client Current 24-hours Output
        Packet counter :This OID gives
         the current 24-hours Output Packets
        counter value
        "
	::= { pm200frs02PerfDatacomClientCurrent24StatEntry 31 }


pm200frs02perfdatacomclientCurrent24StatOutCrcCountInvPortn OBJECT-TYPE
	SYNTAX  EkiOnOff
	MAX-ACCESS read-only
	STATUS current
	DESCRIPTION
        "
        Client Current 24-hours Output
        CRC counter inv. :This OID indicates
        that the current 24-hours Output
        CRC counter is invalid
        "
	::= { pm200frs02PerfDatacomClientCurrent24StatEntry 28 }


pm200frs02perfdatacomclientCurrent24StatOutCrcCountPortn OBJECT-TYPE
	SYNTAX  Counter64
	MAX-ACCESS read-only
	STATUS current
	DESCRIPTION
        "
        Client Current 24-hours Output
        CRC counter :This OID gives the
        current 24-hours Output CRC counter
        value
        "
	::= { pm200frs02PerfDatacomClientCurrent24StatEntry 29 }


pm200frs02perfdatacomclientCurrent24StatInPacketCountInvPortn OBJECT-TYPE
	SYNTAX  EkiOnOff
	MAX-ACCESS read-only
	STATUS current
	DESCRIPTION
        "
        Client Current 24-hours Input
         Packet counter inv. :This OID
         indicates that the current 24-hours
        Input Packet counter is invalid
        "
	::= { pm200frs02PerfDatacomClientCurrent24StatEntry 6 }


pm200frs02perfdatacomclientCurrent24StatInPacketCountPortn OBJECT-TYPE
	SYNTAX  Counter64
	MAX-ACCESS read-only
	STATUS current
	DESCRIPTION
        "
        Client Current 24-hours Input
         Packet counter :This OID gives
        the current 24-hours Input Packet
        counter value
        "
	::= { pm200frs02PerfDatacomClientCurrent24StatEntry 7 }


pm200frs02perfdatacomclientCurrent24StatInCrcCountInvPortn OBJECT-TYPE
	SYNTAX  EkiOnOff
	MAX-ACCESS read-only
	STATUS current
	DESCRIPTION
        "
        Client Current 24-hours Input
         CRC counter inv. :This OID indicates
        that the current 24-hours Input
        CRC counter is invalid
        "
	::= { pm200frs02PerfDatacomClientCurrent24StatEntry 4 }


pm200frs02perfdatacomclientCurrent24StatInCrcCountPortn OBJECT-TYPE
	SYNTAX  Counter64
	MAX-ACCESS read-only
	STATUS current
	DESCRIPTION
        "
        Client Current 24-hours Input
         CRC counter :This OID gives the
        current 24-hours Input CRC counter
        value
        "
	::= { pm200frs02PerfDatacomClientCurrent24StatEntry 5 }


--- *****************************************************
---     Leaf of the datacomClientPast24Stat
--- *****************************************************
--- *********************************************************
---     TABLE for the pm200frs02PerfDatacomClientPast24StatHistory articles
--- *********************************************************

pm200frs02PerfDatacomClientPast24StatHistoryPort1Table OBJECT-TYPE
	SYNTAX  SEQUENCE OF Pm200frs02PerfDatacomClientPast24StatHistoryPort1Entry
	MAX-ACCESS not-accessible
	STATUS current
	DESCRIPTION
        "
        List of pm200frs02PerfDatacomClientPast24StatHistory
        Article
        "
	::= { pm200frs02MonPerfClient 944 }


pm200frs02PerfDatacomClientPast24StatHistoryPort1Entry OBJECT-TYPE
	SYNTAX Pm200frs02PerfDatacomClientPast24StatHistoryPort1Entry
	MAX-ACCESS not-accessible
	STATUS current
	DESCRIPTION
        "
        Row definition for the pm200frs02PerfDatacomClientPast24StatHistory
        table
        "
	INDEX   { pm200frs02PerfDatacomClientPast24StatHistoryPort1Index }
	::= { pm200frs02PerfDatacomClientPast24StatHistoryPort1Table 1 }


Pm200frs02PerfDatacomClientPast24StatHistoryPort1Entry ::=
	SEQUENCE {
	pm200frs02PerfDatacomClientPast24StatHistoryPort1Index
		INTEGER,
	pm200frs02perfdatacomclientPast24StatOutPacketCountInvPort1
		EkiOnOff,
	pm200frs02perfdatacomclientPast24StatOutPacketCountPort1
		Counter64,
	pm200frs02perfdatacomclientPast24StatOutCrcCountInvPort1
		EkiOnOff,
	pm200frs02perfdatacomclientPast24StatOutCrcCountPort1
		Counter64,
	pm200frs02perfdatacomclientPast24StatInPacketCountInvPort1
		EkiOnOff,
	pm200frs02perfdatacomclientPast24StatInPacketCountPort1
		Counter64,
	pm200frs02perfdatacomclientPast24StatInCrcCountInvPort1
		EkiOnOff,
	pm200frs02perfdatacomclientPast24StatInCrcCountPort1
		Counter64
	}


pm200frs02PerfDatacomClientPast24StatHistoryPort1Index OBJECT-TYPE
	SYNTAX  INTEGER(0..128)
	MAX-ACCESS  read-only
	STATUS current
	DESCRIPTION
        "
        Index definition for the pm200frs02PerfDatacomClientPast24StatHistory
        table
        "
	::= { pm200frs02PerfDatacomClientPast24StatHistoryPort1Entry 1 }


pm200frs02perfdatacomclientPast24StatOutPacketCountInvPort1 OBJECT-TYPE
	SYNTAX  EkiOnOff
	MAX-ACCESS read-only
	STATUS current
	DESCRIPTION
        "
        Client Past 24-hours Output Packet
        counter inv. :This OID indicates
        that the past 24-hours Output Packets
        counter is invalid
        "
	::= { pm200frs02PerfDatacomClientPast24StatHistoryPort1Entry 30 }


pm200frs02perfdatacomclientPast24StatOutPacketCountPort1 OBJECT-TYPE
	SYNTAX  Counter64
	MAX-ACCESS read-only
	STATUS current
	DESCRIPTION
        "
        Client Past 24-hours Output Packet
        counter :This OID gives the past
        24-hours Output Packets counter
        value
        "
	::= { pm200frs02PerfDatacomClientPast24StatHistoryPort1Entry 31 }


pm200frs02perfdatacomclientPast24StatOutCrcCountInvPort1 OBJECT-TYPE
	SYNTAX  EkiOnOff
	MAX-ACCESS read-only
	STATUS current
	DESCRIPTION
        "
        Client Past 24-hours Output CRC
        counter inv. :This OID indicates
        that the past 24-hours Output CRC
        counter is invalid
        "
	::= { pm200frs02PerfDatacomClientPast24StatHistoryPort1Entry 28 }


pm200frs02perfdatacomclientPast24StatOutCrcCountPort1 OBJECT-TYPE
	SYNTAX  Counter64
	MAX-ACCESS read-only
	STATUS current
	DESCRIPTION
        "
        Client Past 24-hours Output CRC
        counter :This OID gives the past
        24-hours Output CRC counter value
        "
	::= { pm200frs02PerfDatacomClientPast24StatHistoryPort1Entry 29 }


pm200frs02perfdatacomclientPast24StatInPacketCountInvPort1 OBJECT-TYPE
	SYNTAX  EkiOnOff
	MAX-ACCESS read-only
	STATUS current
	DESCRIPTION
        "
        Client Past 24-hours Input Packet
        counter inv. :This OID indicates
        that the past 24-hours Input Packet
        counter is invalid
        "
	::= { pm200frs02PerfDatacomClientPast24StatHistoryPort1Entry 6 }


pm200frs02perfdatacomclientPast24StatInPacketCountPort1 OBJECT-TYPE
	SYNTAX  Counter64
	MAX-ACCESS read-only
	STATUS current
	DESCRIPTION
        "
        Client Past 24-hours Input Packet
        counter :This OID gives the past
        24-hours Input Packet counter value
        "
	::= { pm200frs02PerfDatacomClientPast24StatHistoryPort1Entry 7 }


pm200frs02perfdatacomclientPast24StatInCrcCountInvPort1 OBJECT-TYPE
	SYNTAX  EkiOnOff
	MAX-ACCESS read-only
	STATUS current
	DESCRIPTION
        "
        Client Past 24-hours Input CRC
        counter inv. :This OID indicates
        that the past 24-hours Input CRC
        counter is invalid
        "
	::= { pm200frs02PerfDatacomClientPast24StatHistoryPort1Entry 4 }


pm200frs02perfdatacomclientPast24StatInCrcCountPort1 OBJECT-TYPE
	SYNTAX  Counter64
	MAX-ACCESS read-only
	STATUS current
	DESCRIPTION
        "
        Client Past 24-hours Input CRC
        counter :This OID gives the past
        24-hours Input CRC counter value
        "
	::= { pm200frs02PerfDatacomClientPast24StatHistoryPort1Entry 5 }



pm200frs02PerfEnable OBJECT-TYPE
	SYNTAX EkiOnOff
	MAX-ACCESS read-write
	STATUS current
	DESCRIPTION
        "
        Perf. Mon. Enable :This OID enables
        the Performance Monitoring application
        "
	::= { pm200frs02MonPerfSync 257 }


pm200frs02Perf15minSync OBJECT-TYPE
	SYNTAX EkiOnOff
	MAX-ACCESS read-write
	STATUS current
	DESCRIPTION
        "
        Perf. Mon. 15-min sync. :This
         OID must be used in external synchronisation
        mode only to send a 15-min synchronisation
        command
        "
	::= { pm200frs02MonPerfSync 259 }


pm200frs02Perf24hSync OBJECT-TYPE
	SYNTAX EkiOnOff
	MAX-ACCESS read-write
	STATUS current
	DESCRIPTION
        "
        Perf. Mon. 24-hours sync. :This
        OID must be used in external synchronisation
        mode only to send a 24-hours synchronisation
        command
        "
	::= { pm200frs02MonPerfSync 260 }


pm200frs02Perf15MinShort OBJECT-TYPE
	SYNTAX EkiOnOff
	MAX-ACCESS read-write
	STATUS current
	DESCRIPTION
        "
        15-min period is short :This OID
        indicates that the 15-min period
        lasts less than 890 seconds
        "
	::= { pm200frs02MonPerfTimeStamp 1 }


pm200frs02Perf15MinLong OBJECT-TYPE
	SYNTAX EkiOnOff
	MAX-ACCESS read-write
	STATUS current
	DESCRIPTION
        "
        15-min period is long :This OID
        indicates that the 15-min period
        lasts more than 910 seconds
        "
	::= { pm200frs02MonPerfTimeStamp 2 }


pm200frs02Perf24HoursShort OBJECT-TYPE
	SYNTAX Counter32
	MAX-ACCESS read-write
	STATUS current
	DESCRIPTION
        "
        24-hours period is short :This
        OID indicates that 24-hours period
        lasts less than 86390 seconds
        "
	::= { pm200frs02MonPerfTimeStamp 5 }


pm200frs02Perf24HoursLong OBJECT-TYPE
	SYNTAX Counter32
	MAX-ACCESS read-write
	STATUS current
	DESCRIPTION
        "
        24-hours period is long :This
         OID indicates that 24-hours period
        lasts more than 86410 seconds
        "
	::= { pm200frs02MonPerfTimeStamp 6 }


pm200frs02PerfCurrent15MinElapsedTime OBJECT-TYPE
	SYNTAX Counter32
	MAX-ACCESS read-write
	STATUS current
	DESCRIPTION
        "
        Current 15min period Elapsed Time
         :This OID gives the number of
         seconds elapsed in the current
        15-minutes period
        "
	::= { pm200frs02MonPerfTimeStamp 7 }


pm200frs02PerfCurrent24HoursElapsedTime OBJECT-TYPE
	SYNTAX Counter32
	MAX-ACCESS read-write
	STATUS current
	DESCRIPTION
        "
        Current 24hours period Elapsed
        Time :This OID gives the number
        of seconds elapsed in the current
        24-hours period
        "
	::= { pm200frs02MonPerfTimeStamp 8 }






--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pm200frs02DwlrestartProcess OBJECT IDENTIFIER ::= { pm200frs02DwlOther 0 }




pm200frs02DwlColdRestartProcessed OBJECT-TYPE
	  SYNTAX EkiOnOff
	  MAX-ACCESS read-only
	  STATUS current
	  DESCRIPTION
        "
        Cold Restart :This OID indicates
        that the module last restart was
        a Cold RESTART
        "
	  ::= { pm200frs02DwlrestartProcess 2 }



pm200frs02DwlWarmRestartProcessed OBJECT-TYPE
	  SYNTAX EkiOnOff
	  MAX-ACCESS read-only
	  STATUS current
	  DESCRIPTION
        "
        Warm Restart :This OID indicates
        that the module last restart was
        a Warm RESTART
        "
	  ::= { pm200frs02DwlrestartProcess 1 }



--- *****************************************************
---     LEAF for the swBanksUsed article
--- *****************************************************
pm200frs02DwlswBanksUsed OBJECT IDENTIFIER ::= { pm200frs02DwlOther 1 }




pm200frs02DwlSwBank2Notempty OBJECT-TYPE
	  SYNTAX EkiOnOff
	  MAX-ACCESS read-only
	  STATUS current
	  DESCRIPTION
        "
        SW bank 2 loaded :This OID indicates
        a software is loaded in SW bank
        2  <Help>  This status indicates
        if the SW bank 2 contains SW package
        "
	  ::= { pm200frs02DwlswBanksUsed 6 }



pm200frs02DwlSwBank1Notempty OBJECT-TYPE
	  SYNTAX EkiOnOff
	  MAX-ACCESS read-only
	  STATUS current
	  DESCRIPTION
        "
        SW bank 1 loaded :This OID indicates
        a software is loaded in SW bank
        1  <Help>  This status indicates
        if the SW bank 1 contains SW package
        "
	  ::= { pm200frs02DwlswBanksUsed 5 }



pm200frs02DwlSwBank2Used OBJECT-TYPE
	  SYNTAX EkiOnOff
	  MAX-ACCESS read-only
	  STATUS current
	  DESCRIPTION
        "
        SW bank 2 active :This OID indicates
        the module is working on SW bank
        2  <Help>  This status indicates
        if the SW bank 2 is active or standby
        "
	  ::= { pm200frs02DwlswBanksUsed 2 }



pm200frs02DwlSwBank1Used OBJECT-TYPE
	  SYNTAX EkiOnOff
	  MAX-ACCESS read-only
	  STATUS current
	  DESCRIPTION
        "
        SW bank 1 active :This OID indicates
        the module is working on SW bank
        1  <Help>  This status indicates
        if the SW bank 1 is active or standby
        "
	  ::= { pm200frs02DwlswBanksUsed 1 }



--- *****************************************************
---     LEAF for the gwBanksUsed article
--- *****************************************************
pm200frs02DwlgwBanksUsed OBJECT IDENTIFIER ::= { pm200frs02DwlOther 2 }




pm200frs02DwlGwBank4Notempty OBJECT-TYPE
	  SYNTAX EkiOnOff
	  MAX-ACCESS read-only
	  STATUS current
	  DESCRIPTION
        "
        GW bank 4 loaded :This OID indicates
        a gateware is loaded in GW bank
        4
        "
	  ::= { pm200frs02DwlgwBanksUsed 8 }



pm200frs02DwlGwBank3Notempty OBJECT-TYPE
	  SYNTAX EkiOnOff
	  MAX-ACCESS read-only
	  STATUS current
	  DESCRIPTION
        "
        GW bank 3 loaded :This OID indicates
        a gateware is loaded in GW bank
        3  <Help>  This status indicates
        if the GW bank 3 contains GW package
        "
	  ::= { pm200frs02DwlgwBanksUsed 7 }



pm200frs02DwlGwBank2Notempty OBJECT-TYPE
	  SYNTAX EkiOnOff
	  MAX-ACCESS read-only
	  STATUS current
	  DESCRIPTION
        "
        GW bank 2 loaded :This OID indicates
        a gateware is loaded in GW bank
        2
        "
	  ::= { pm200frs02DwlgwBanksUsed 6 }



pm200frs02DwlGwBank1Notempty OBJECT-TYPE
	  SYNTAX EkiOnOff
	  MAX-ACCESS read-only
	  STATUS current
	  DESCRIPTION
        "
        GW bank 1 loaded :This OID indicates
        a gateware is loaded in GW bank
        1  <Help>  This status indicates
        if the GW bank 1 contains GW package
        "
	  ::= { pm200frs02DwlgwBanksUsed 5 }



pm200frs02DwlGwBank4Used OBJECT-TYPE
	  SYNTAX EkiOnOff
	  MAX-ACCESS read-only
	  STATUS current
	  DESCRIPTION
        "
        GW bank 4 active :This OID indicates
        the module is working on GW bank
        4
        "
	  ::= { pm200frs02DwlgwBanksUsed 4 }



pm200frs02DwlGwBank3Used OBJECT-TYPE
	  SYNTAX EkiOnOff
	  MAX-ACCESS read-only
	  STATUS current
	  DESCRIPTION
        "
        GW bank 3 active :This OID indicates
        the module is working on GW bank
        3  <Help>  This status indicates
        if the GW bank 3 is active or standby
        "
	  ::= { pm200frs02DwlgwBanksUsed 3 }



pm200frs02DwlGwBank2Used OBJECT-TYPE
	  SYNTAX EkiOnOff
	  MAX-ACCESS read-only
	  STATUS current
	  DESCRIPTION
        "
        GW bank 2 active :This OID indicates
        the module is working on GW bank
        2
        "
	  ::= { pm200frs02DwlgwBanksUsed 2 }



pm200frs02DwlGwBank1Used OBJECT-TYPE
	  SYNTAX EkiOnOff
	  MAX-ACCESS read-only
	  STATUS current
	  DESCRIPTION
        "
        GW bank 1 active :This OID indicates
        the module is working on GW bank
        1  <Help>  This status indicates
        if the GW bank 1 is active or standby
        "
	  ::= { pm200frs02DwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pm200frs02CfgAccessCAisCsf OBJECT IDENTIFIER ::= { pm200frs02Config 1 }



--- *****************************************************
---     LEAF for the table 0012
--- *****************************************************

pm200frs02CfgClientcaiscsfTable OBJECT-TYPE
	SYNTAX  SEQUENCE OF Pm200frs02CfgClientcaiscsfEntry
	MAX-ACCESS not-accessible
	STATUS current
	DESCRIPTION
        "
        List of  Article
        "
	::= { pm200frs02CfgAccessCAisCsf 1 }


pm200frs02CfgClientcaiscsfEntry OBJECT-TYPE
	SYNTAX Pm200frs02CfgClientcaiscsfEntry
	MAX-ACCESS not-accessible
	STATUS current
	DESCRIPTION
        "
        Row definition for the accessCAisCsf
        table
        "
	INDEX   { pm200frs02CfgClientcaiscsfIndex }
	::= { pm200frs02CfgClientcaiscsfTable 1 }


Pm200frs02CfgClientcaiscsfEntry ::=
	SEQUENCE {
	pm200frs02CfgClientcaiscsfIndex
		INTEGER,
	pm200frs02CfgReservePortn
		Unsigned32
	}


pm200frs02CfgClientcaiscsfIndex OBJECT-TYPE
	SYNTAX  INTEGER(0..128)
	MAX-ACCESS  read-only
	STATUS current
	DESCRIPTION
        "
        Index definition for the clientcaiscsf
        table
        "
	::= { pm200frs02CfgClientcaiscsfEntry 1 }


pm200frs02CfgReservePortn OBJECT-TYPE
	SYNTAX  Unsigned32 (0..65536)
	MAX-ACCESS read-write
	STATUS current
	DESCRIPTION
        "
        CAIS mode  on Client Port :This
        register enables/disables port
          laser shutdown on CAIS insertion
        condition
        "
	::= { pm200frs02CfgClientcaiscsfEntry 3 }


--- *****************************************************
---     LEAF for the table Group startup
--- *****************************************************

pm200frs02CfgStartup OBJECT IDENTIFIER ::= { pm200frs02Config 2 }



--- *****************************************************
---     LEAF for the table 2110
--- *****************************************************

pm200frs02CfgClientStartupTable OBJECT-TYPE
	SYNTAX  SEQUENCE OF Pm200frs02CfgClientStartupEntry
	MAX-ACCESS not-accessible
	STATUS current
	DESCRIPTION
        "
        List of  Article
        "
	::= { pm200frs02CfgStartup 1 }


pm200frs02CfgClientStartupEntry OBJECT-TYPE
	SYNTAX Pm200frs02CfgClientStartupEntry
	MAX-ACCESS not-accessible
	STATUS current
	DESCRIPTION
        "
        Row definition for the startup
        table
        "
	INDEX   { pm200frs02CfgClientStartupIndex }
	::= { pm200frs02CfgClientStartupTable 1 }


Pm200frs02CfgClientStartupEntry ::=
	SEQUENCE {
	pm200frs02CfgClientStartupIndex
		INTEGER,
	pm200frs02CfgSystConfPortPortn
		Unsigned32,
	pm200frs02CfgNetConfPortPortn
		Unsigned32,
	pm200frs02CfgOptionsPortPortn
		Unsigned32
	}


pm200frs02CfgClientStartupIndex OBJECT-TYPE
	SYNTAX  INTEGER(0..128)
	MAX-ACCESS  read-only
	STATUS current
	DESCRIPTION
        "
        Index definition for the clientStartup
        table
        "
	::= { pm200frs02CfgClientStartupEntry 1 }


pm200frs02CfgSystConfPortPortn OBJECT-TYPE
	SYNTAX  Unsigned32 (0..65536)
	MAX-ACCESS read-write
	STATUS current
	DESCRIPTION
        "
        Default Settings on Client Port
        :This  register configures the
         default initialisation settings
        on the port.
        "
	::= { pm200frs02CfgClientStartupEntry 3 }


pm200frs02CfgNetConfPortPortn OBJECT-TYPE
	SYNTAX  Unsigned32 (0..65536)
	MAX-ACCESS read-write
	STATUS current
	DESCRIPTION
        "
        Default Settings on Client Port
        :This  register configures the
         default initialisation settings
        on the port.
        "
	::= { pm200frs02CfgClientStartupEntry 4 }


pm200frs02CfgOptionsPortPortn OBJECT-TYPE
	SYNTAX  Unsigned32 (0..65536)
	MAX-ACCESS read-write
	STATUS current
	DESCRIPTION
        "
        Default Options on Client Port
        :This register configures the default
        options on the port.
        "
	::= { pm200frs02CfgClientStartupEntry 14 }


--- *****************************************************
---     LEAF for the table 2190
--- *****************************************************

pm200frs02CfgLineStartupTable OBJECT-TYPE
	SYNTAX  SEQUENCE OF Pm200frs02CfgLineStartupEntry
	MAX-ACCESS not-accessible
	STATUS current
	DESCRIPTION
        "
        List of  Article
        "
	::= { pm200frs02CfgStartup 2 }


pm200frs02CfgLineStartupEntry OBJECT-TYPE
	SYNTAX Pm200frs02CfgLineStartupEntry
	MAX-ACCESS not-accessible
	STATUS current
	DESCRIPTION
        "
        Row definition for the startup
        table
        "
	INDEX   { pm200frs02CfgLineStartupIndex }
	::= { pm200frs02CfgLineStartupTable 1 }


Pm200frs02CfgLineStartupEntry ::=
	SEQUENCE {
	pm200frs02CfgLineStartupIndex
		INTEGER,
	pm200frs02CfgSystConfLinePortn
		Unsigned32,
	pm200frs02CfgOptionsLinePortn
		Unsigned32
	}


pm200frs02CfgLineStartupIndex OBJECT-TYPE
	SYNTAX  INTEGER(0..128)
	MAX-ACCESS  read-only
	STATUS current
	DESCRIPTION
        "
        Index definition for the lineStartup
        table
        "
	::= { pm200frs02CfgLineStartupEntry 1 }


pm200frs02CfgSystConfLinePortn OBJECT-TYPE
	SYNTAX  Unsigned32 (0..65536)
	MAX-ACCESS read-write
	STATUS current
	DESCRIPTION
        "
        Default Settings on Line :This
        register configures the default
        initialisation settings on Line
        "
	::= { pm200frs02CfgLineStartupEntry 3 }


pm200frs02CfgOptionsLinePortn OBJECT-TYPE
	SYNTAX  Unsigned32 (0..65536)
	MAX-ACCESS read-write
	STATUS current
	DESCRIPTION
        "
        Default Options on Line :This
         register configures the default
        options on the line
        "
	::= { pm200frs02CfgLineStartupEntry 14 }


--- *****************************************************
---     LEAF for the table 21AB
--- *****************************************************

pm200frs02CfgXfpTable OBJECT-TYPE
	SYNTAX  SEQUENCE OF Pm200frs02CfgXfpEntry
	MAX-ACCESS not-accessible
	STATUS current
	DESCRIPTION
        "
        List of  Article
        "
	::= { pm200frs02CfgStartup 3 }


pm200frs02CfgXfpEntry OBJECT-TYPE
	SYNTAX Pm200frs02CfgXfpEntry
	MAX-ACCESS not-accessible
	STATUS current
	DESCRIPTION
        "
        Row definition for the startup
        table
        "
	INDEX   { pm200frs02CfgXfpIndex }
	::= { pm200frs02CfgXfpTable 1 }


Pm200frs02CfgXfpEntry ::=
	SEQUENCE {
	pm200frs02CfgXfpIndex
		INTEGER,
	pm200frs02CfgSystConfMsaLinePortn
		Unsigned32
	}


pm200frs02CfgXfpIndex OBJECT-TYPE
	SYNTAX  INTEGER(0..128)
	MAX-ACCESS  read-only
	STATUS current
	DESCRIPTION
        "
        Index definition for the xfp table
        "
	::= { pm200frs02CfgXfpEntry 1 }


pm200frs02CfgSystConfMsaLinePortn OBJECT-TYPE
	SYNTAX  Unsigned32 (0..65536)
	MAX-ACCESS read-write
	STATUS current
	DESCRIPTION
        "
        Default settings on MSA :This
         register configures the default
        initialisation settings on MSA
        "
	::= { pm200frs02CfgXfpEntry 3 }


--- *****************************************************
---     LEAF for the table Group labels
--- *****************************************************

pm200frs02CfgLabels OBJECT IDENTIFIER ::= { pm200frs02Config 3 }



--- *****************************************************
---     LEAF for the table 0003
--- *****************************************************

pm200frs02CfgLabelclientTable OBJECT-TYPE
	SYNTAX  SEQUENCE OF Pm200frs02CfgLabelclientEntry
	MAX-ACCESS not-accessible
	STATUS current
	DESCRIPTION
        "
        List of  Article
        "
	::= { pm200frs02CfgLabels 1 }


pm200frs02CfgLabelclientEntry OBJECT-TYPE
	SYNTAX Pm200frs02CfgLabelclientEntry
	MAX-ACCESS not-accessible
	STATUS current
	DESCRIPTION
        "
        Row definition for the labels
         table
        "
	INDEX   { pm200frs02CfgLabelclientIndex }
	::= { pm200frs02CfgLabelclientTable 1 }


Pm200frs02CfgLabelclientEntry ::=
	SEQUENCE {
	pm200frs02CfgLabelclientIndex
		INTEGER,
	pm200frs02CfgLabelclientPortn
		DisplayString
	}


pm200frs02CfgLabelclientIndex OBJECT-TYPE
	SYNTAX  INTEGER(0..128)
	MAX-ACCESS  read-only
	STATUS current
	DESCRIPTION
        "
        Index definition for the labelclient
        table
        "
	::= { pm200frs02CfgLabelclientEntry 1 }


pm200frs02CfgLabelclientPortn OBJECT-TYPE
	SYNTAX  DisplayString( SIZE(1..16))
	MAX-ACCESS read-write
	STATUS current
	DESCRIPTION
        "
        Default settings on the label
         of the Ports :These registers
         configures the default initialisation
        settings of the labels of the ports.
        "
	::= { pm200frs02CfgLabelclientEntry 3 }


--- *****************************************************
---     LEAF for the table 0004
--- *****************************************************

pm200frs02CfgLabellineTable OBJECT-TYPE
	SYNTAX  SEQUENCE OF Pm200frs02CfgLabellineEntry
	MAX-ACCESS not-accessible
	STATUS current
	DESCRIPTION
        "
        List of  Article
        "
	::= { pm200frs02CfgLabels 2 }


pm200frs02CfgLabellineEntry OBJECT-TYPE
	SYNTAX Pm200frs02CfgLabellineEntry
	MAX-ACCESS not-accessible
	STATUS current
	DESCRIPTION
        "
        Row definition for the labels
         table
        "
	INDEX   { pm200frs02CfgLabellineIndex }
	::= { pm200frs02CfgLabellineTable 1 }


Pm200frs02CfgLabellineEntry ::=
	SEQUENCE {
	pm200frs02CfgLabellineIndex
		INTEGER,
	pm200frs02CfgLabellinePortn
		DisplayString
	}


pm200frs02CfgLabellineIndex OBJECT-TYPE
	SYNTAX  INTEGER(0..128)
	MAX-ACCESS  read-only
	STATUS current
	DESCRIPTION
        "
        Index definition for the labelline
        table
        "
	::= { pm200frs02CfgLabellineEntry 1 }


pm200frs02CfgLabellinePortn OBJECT-TYPE
	SYNTAX  DisplayString( SIZE(1..16))
	MAX-ACCESS read-write
	STATUS current
	DESCRIPTION
        "
        Default settings on the label
         of the lines :These registers
         configures the default initialisation
        settings of the labels of the lines.
        "
	::= { pm200frs02CfgLabellineEntry 3 }


--- *****************************************************
---     LEAF for the table Group startuptlh
--- *****************************************************

pm200frs02CfgStartuptlh OBJECT IDENTIFIER ::= { pm200frs02Config 4 }



--- *****************************************************
---     LEAF for the table 25AB
--- *****************************************************

pm200frs02CfgOtxtlhTable OBJECT-TYPE
	SYNTAX  SEQUENCE OF Pm200frs02CfgOtxtlhEntry
	MAX-ACCESS not-accessible
	STATUS current
	DESCRIPTION
        "
        List of  Article
        "
	::= { pm200frs02CfgStartuptlh 1 }


pm200frs02CfgOtxtlhEntry OBJECT-TYPE
	SYNTAX Pm200frs02CfgOtxtlhEntry
	MAX-ACCESS not-accessible
	STATUS current
	DESCRIPTION
        "
        Row definition for the startuptlh
        table
        "
	INDEX   { pm200frs02CfgOtxtlhIndex }
	::= { pm200frs02CfgOtxtlhTable 1 }


Pm200frs02CfgOtxtlhEntry ::=
	SEQUENCE {
	pm200frs02CfgOtxtlhIndex
		INTEGER,
	pm200frs02CfgLinePwrLaserPortn
		Unsigned32,
	pm200frs02CfgLineFCurrentPortn
		Unsigned32,
	pm200frs02CfgLineGridCurrentPortn
		Unsigned32,
	pm200frs02CfgFPortn
		Unsigned32,
	pm200frs02CfgRxLineFCurrentPortn
		Unsigned32
	}


pm200frs02CfgOtxtlhIndex OBJECT-TYPE
	SYNTAX  INTEGER(0..128)
	MAX-ACCESS  read-only
	STATUS current
	DESCRIPTION
        "
        Index definition for the otxtlh
        table
        "
	::= { pm200frs02CfgOtxtlhEntry 1 }


pm200frs02CfgLinePwrLaserPortn OBJECT-TYPE
	SYNTAX  Unsigned32 (0..65536)
	MAX-ACCESS read-write
	STATUS current
	DESCRIPTION
        "
        Defaut Line output Power :This
        register configures the start-up
        output power of the Line tranceiver
         (Unit = dBm)
        "
	::= { pm200frs02CfgOtxtlhEntry 6 }


pm200frs02CfgLineFCurrentPortn OBJECT-TYPE
	SYNTAX  Unsigned32 (0..65536)
	MAX-ACCESS read-write
	STATUS current
	DESCRIPTION
        "
        Default Line transceiver Tx Channel
        :This register configures the start-up
        laser channel of the Line Tx transceiver
        "
	::= { pm200frs02CfgOtxtlhEntry 7 }


pm200frs02CfgLineGridCurrentPortn OBJECT-TYPE
	SYNTAX  Unsigned32 (0..65536)
	MAX-ACCESS read-write
	STATUS current
	DESCRIPTION
        "
        Default Line transceiver Grid
         :This register configures the
         start-up laser grid of the Line
        transceiver
        "
	::= { pm200frs02CfgOtxtlhEntry 8 }


pm200frs02CfgFPortn OBJECT-TYPE
	SYNTAX  Unsigned32 (0..65536)
	MAX-ACCESS read-write
	STATUS current
	DESCRIPTION
        "
        Default Line TRX lowest Freq :This
        register configures the start-up
        lowest frequency of the Line transceiver
        "
	::= { pm200frs02CfgOtxtlhEntry 9 }


pm200frs02CfgRxLineFCurrentPortn OBJECT-TYPE
	SYNTAX  Unsigned32 (0..65536)
	MAX-ACCESS read-write
	STATUS current
	DESCRIPTION
        "
        Default Line transceiver Rx Channel
        :This register configures the start-up
        laser channel of the Line Rx transceiver
        "
	::= { pm200frs02CfgOtxtlhEntry 10 }


--- *****************************************************
---     LEAF for the table Group other
--- *****************************************************

pm200frs02CfgOther OBJECT IDENTIFIER ::= { pm200frs02Config 5 }



--- *****************************************************
---     LEAF for the table 2300
--- *****************************************************

pm200frs02tablemoduleOther OBJECT IDENTIFIER ::= { pm200frs02CfgOther 1 }



pm200frs02Cfgmode OBJECT-TYPE
	  SYNTAX Unsigned32 (0..65536)
	  MAX-ACCESS read-write
	  STATUS current
	  DESCRIPTION
        "
        Default settings on Module :This
        register selects the configuration
        mode of the module
        "
	  ::= { pm200frs02tablemoduleOther 2 }



pm200frs02CfgfanLowSpeedThreshold OBJECT-TYPE
	  SYNTAX Unsigned32 (0..65536)
	  MAX-ACCESS read-write
	  STATUS current
	  DESCRIPTION
        "
        Default settings on Module :This
        register selects the speed threshold
        of the fan's
        "
	  ::= { pm200frs02tablemoduleOther 3 }



pm200frs02CfgfanHighSpeedThreshold OBJECT-TYPE
	  SYNTAX Unsigned32 (0..65536)
	  MAX-ACCESS read-write
	  STATUS current
	  DESCRIPTION
        "
        Default settings on Module :This
        register selects the speed threshold
        of the fan's
        "
	  ::= { pm200frs02tablemoduleOther 4 }



pm200frs02CfgmoduleMode OBJECT-TYPE
	  SYNTAX Unsigned32 (0..65536)
	  MAX-ACCESS read-write
	  STATUS current
	  DESCRIPTION
        "
        Default settings on Module :This
        register selects the configuration
        mode of the module
        "
	  ::= { pm200frs02tablemoduleOther 5 }



--- *****************************************************
---     LEAF for the table Group startuptablefive
--- *****************************************************

pm200frs02CfgStartuptablefive OBJECT IDENTIFIER ::= { pm200frs02Config 6 }



--- *****************************************************
---     LEAF for the table 0005
--- *****************************************************

pm200frs02CfgOtxtlhcapabilitiesTable OBJECT-TYPE
	SYNTAX  SEQUENCE OF Pm200frs02CfgOtxtlhcapabilitiesEntry
	MAX-ACCESS not-accessible
	STATUS current
	DESCRIPTION
        "
        List of  Article
        "
	::= { pm200frs02CfgStartuptablefive 1 }


pm200frs02CfgOtxtlhcapabilitiesEntry OBJECT-TYPE
	SYNTAX Pm200frs02CfgOtxtlhcapabilitiesEntry
	MAX-ACCESS not-accessible
	STATUS current
	DESCRIPTION
        "
        Row definition for the startuptablefive
        table
        "
	INDEX   { pm200frs02CfgOtxtlhcapabilitiesIndex }
	::= { pm200frs02CfgOtxtlhcapabilitiesTable 1 }


Pm200frs02CfgOtxtlhcapabilitiesEntry ::=
	SEQUENCE {
	pm200frs02CfgOtxtlhcapabilitiesIndex
		INTEGER,
	pm200frs02CfgComponentTypePortn
		Unsigned32,
	pm200frs02CfgMiscellaneousPortn
		Unsigned32,
	pm200frs02CfgFirstChannelPortn
		Unsigned32,
	pm200frs02CfgLastChannelPortn
		Unsigned32,
	pm200frs02CfgGridPortn
		Unsigned32
	}


pm200frs02CfgOtxtlhcapabilitiesIndex OBJECT-TYPE
	SYNTAX  INTEGER(0..128)
	MAX-ACCESS  read-only
	STATUS current
	DESCRIPTION
        "
        Index definition for the otxtlhcapabilities
        table
        "
	::= { pm200frs02CfgOtxtlhcapabilitiesEntry 1 }


pm200frs02CfgComponentTypePortn OBJECT-TYPE
	SYNTAX  Unsigned32 (0..65536)
	MAX-ACCESS read-only
	STATUS current
	DESCRIPTION
        "
        Component parameters :This OID
        defines the component parameters
        "
	::= { pm200frs02CfgOtxtlhcapabilitiesEntry 3 }


pm200frs02CfgMiscellaneousPortn OBJECT-TYPE
	SYNTAX  Unsigned32 (0..65536)
	MAX-ACCESS read-only
	STATUS current
	DESCRIPTION
        "
        Miscellaneous default settings
        :This OID defines the miscellaneous
        parameters
        "
	::= { pm200frs02CfgOtxtlhcapabilitiesEntry 4 }


pm200frs02CfgFirstChannelPortn OBJECT-TYPE
	SYNTAX  Unsigned32 (0..65536)
	MAX-ACCESS read-only
	STATUS current
	DESCRIPTION
        "
        Number of the first channel of
        the component :This OID defines
        the first channel number of the
        PM
        "
	::= { pm200frs02CfgOtxtlhcapabilitiesEntry 5 }


pm200frs02CfgLastChannelPortn OBJECT-TYPE
	SYNTAX  Unsigned32 (0..65536)
	MAX-ACCESS read-only
	STATUS current
	DESCRIPTION
        "
        Number of the last channel of
         the component :This OID defines
        the last channel number of the
         PM
        "
	::= { pm200frs02CfgOtxtlhcapabilitiesEntry 6 }


pm200frs02CfgGridPortn OBJECT-TYPE
	SYNTAX  Unsigned32 (0..65536)
	MAX-ACCESS read-only
	STATUS current
	DESCRIPTION
        "
        Grid value of the component :This
        OID defines the grid of the PM
        "
	::= { pm200frs02CfgOtxtlhcapabilitiesEntry 7 }



pm200frs02CfgWriteConfiguration  OBJECT-TYPE
	SYNTAX EkiOnOff
	MAX-ACCESS read-write
	STATUS current
	DESCRIPTION
	"Write configuration to module:This OID
	 writes the complete configuration to the module"
	::= { pm200frs02Config 257 }






--- *****************************************************
---     TRAP OBJECTS
--- *****************************************************

pm200frs02trapPortNumber OBJECT-TYPE
	SYNTAX INTEGER(1..64)
	MAX-ACCESS read-only
	STATUS current
	DESCRIPTION
	"Last port which generates a trap"
	::= { pm200frs02traps 2 }

pm200frs02trapLineNumber OBJECT-TYPE
	SYNTAX INTEGER(1..64)
	MAX-ACCESS read-only
	STATUS current
	DESCRIPTION
	"Last Line which generates a trap"
	::= { pm200frs02traps 3 }

pm200frs02trapBoardNumber OBJECT-TYPE
	SYNTAX INTEGER(1..64)
	MAX-ACCESS read-only
	STATUS current
	DESCRIPTION
	"Last module which generates a trap"
	::= { pm200frs02traps 4 }







--- *****************************************************
---     LINE TRAPS
--- *****************************************************

pm200frs02LineTrapNotUrgentGoesOn NOTIFICATION-TYPE
	OBJECTS {pm200frs02AlmLineDdmWarningPortn, pm200frs02trapLineNumber, pm200frs02trapBoardNumber}
	STATUS current
	DESCRIPTION "Not urgent Line default is activated"
	::= { pm200frs02traps 30 }

pm200frs02LineTrapNotUrgentGoesOff NOTIFICATION-TYPE
	OBJECTS {pm200frs02AlmLineDdmWarningPortn, pm200frs02trapLineNumber, pm200frs02trapBoardNumber}
	STATUS current
	DESCRIPTION "Not urgent Line default disappeared"
	::= { pm200frs02traps 31 }

pm200frs02LineTrapUrgentGoesOn NOTIFICATION-TYPE
	OBJECTS {pm200frs02AlmLineDdmAlmPortn, pm200frs02trapLineNumber, pm200frs02trapBoardNumber}
	STATUS current
	DESCRIPTION "Urgent Line default is activated"
	::= { pm200frs02traps 32 }

pm200frs02LineTrapUrgentGoesOff NOTIFICATION-TYPE
	OBJECTS {pm200frs02AlmLineDdmAlmPortn, pm200frs02trapLineNumber, pm200frs02trapBoardNumber}
	STATUS current
	DESCRIPTION "Urgent Line default disappeared"
	::= { pm200frs02traps 33 }

pm200frs02LineTrapCritGoesOn NOTIFICATION-TYPE
	OBJECTS {pm200frs02AlmLineFailPortn , pm200frs02AlmLineHwFailPortn , pm200frs02trapLineNumber, pm200frs02trapBoardNumber}
	STATUS current
	DESCRIPTION "Critical Line default is activated"
	::= { pm200frs02traps 34 }

pm200frs02LineTrapCritGoesOff NOTIFICATION-TYPE
	OBJECTS {pm200frs02AlmLineFailPortn , pm200frs02AlmLineHwFailPortn , pm200frs02trapLineNumber, pm200frs02trapBoardNumber}
	STATUS current
	DESCRIPTION "Critical Line default disappeared"
	::= { pm200frs02traps 35 }






--- *****************************************************
---     CLIENT TRAPS
--- *****************************************************

pm200frs02ClientTrapNotUrgentGoesOn NOTIFICATION-TYPE
	OBJECTS {pm200frs02AlmSfpDdmWarningPortn, pm200frs02trapPortNumber, pm200frs02trapBoardNumber}
	STATUS current
	DESCRIPTION "Not urgent client default is activated"
	::= { pm200frs02traps 40 }

pm200frs02ClientTrapNotUrgentGoesOff NOTIFICATION-TYPE
	OBJECTS {pm200frs02AlmSfpDdmWarningPortn, pm200frs02trapPortNumber, pm200frs02trapBoardNumber}
	STATUS current
	DESCRIPTION "Not urgent client default disappeared"
	::= { pm200frs02traps 41 }

pm200frs02ClientTrapUrgentGoesOn NOTIFICATION-TYPE
	OBJECTS {pm200frs02AlmSfpDdmAlmPortn, pm200frs02trapPortNumber, pm200frs02trapBoardNumber}
	STATUS current
	DESCRIPTION "Urgent client default is activated"
	::= { pm200frs02traps 42 }

pm200frs02ClientTrapUrgentGoesOff NOTIFICATION-TYPE
	OBJECTS {pm200frs02AlmSfpDdmAlmPortn, pm200frs02trapPortNumber, pm200frs02trapBoardNumber}
	STATUS current
	DESCRIPTION "Urgent client default disappeared"
	::= { pm200frs02traps 43 }

pm200frs02ClientTrapCritGoesOn NOTIFICATION-TYPE
	OBJECTS {pm200frs02AlmFailAccPortn, pm200frs02AlmHwFailAccPortn, pm200frs02trapPortNumber, pm200frs02trapBoardNumber}
	STATUS current
	DESCRIPTION "Critical client default is activated"
	::= { pm200frs02traps 44 }

pm200frs02ClientTrapCritGoesOff NOTIFICATION-TYPE
	OBJECTS {pm200frs02AlmFailAccPortn, pm200frs02AlmHwFailAccPortn, pm200frs02trapPortNumber, pm200frs02trapBoardNumber}
	STATUS current
	DESCRIPTION "Critical client default disappeared"
	::= { pm200frs02traps 45 }






--- *****************************************************
---     HW TRAPS
--- *****************************************************

pm200frs02PowerTrapUrgentGoesOn NOTIFICATION-TYPE
	OBJECTS {pm200frs02AlmDefFuseB, pm200frs02AlmDefFuseA , pm200frs02trapBoardNumber}
	STATUS current
	DESCRIPTION "Urgent power supply default is activated"
	::= { pm200frs02traps 50 }

pm200frs02PowerTrapUrgentGoesOff NOTIFICATION-TYPE
	OBJECTS {pm200frs02AlmDefFuseB, pm200frs02AlmDefFuseA , pm200frs02trapBoardNumber}
	STATUS current
	DESCRIPTION "Urgent power supply default disappeared"
	::= { pm200frs02traps 51 }






END
