-- *****************************************************************
-- EKINOPS-PmDGE.TXT:  MIB
--
--MIB Part Number:3MI00210AAAE
--MIB Version:01
--
-- Copyright (c) 2016 by Ekinops
-- All rights reserved.
--
-- *****************************************************************

EKINOPS-PmDGE-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

modulepmdge MODULE-IDENTITY
        LAST-UPDATED "201605230000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.net"
        DESCRIPTION
          "MIB for the Ekinops Pmdge hardware."
	REVISION "201210160000Z"
	DESCRIPTION
	  "Initial Version."

	REVISION "201303280000Z"
	DESCRIPTION
	  "Express Input Att in Config"
	REVISION "201403260000Z"
	DESCRIPTION
	  "Probcause,AlarmType - NMS completion"
	REVISION "201411250000Z"
	DESCRIPTION
	  "Labels cosmetic updates"
	REVISION "201605230000Z"
	DESCRIPTION
	  "New AlarmType – synthesisAlarm (12)"
        ::= { ekinops 56 }



--- *****************************************************
---     LEAF LEVEL 2
--- *****************************************************


pmdgealarms OBJECT IDENTIFIER ::= { modulepmdge 2 }
pmdgeAlmOther OBJECT IDENTIFIER ::= { pmdgealarms 1 }
pmdgeAlmOtherNurg OBJECT IDENTIFIER ::= { pmdgeAlmOther 1 }
pmdgeAlmOtherUrg OBJECT IDENTIFIER ::= { pmdgeAlmOther 2 }
pmdgeAlmOtherCrit OBJECT IDENTIFIER ::= { pmdgeAlmOther 3 }


pmdgemeasures OBJECT IDENTIFIER ::= { modulepmdge 3 }
pmdgeMesrOther OBJECT IDENTIFIER ::= { pmdgemeasures 1 }


pmdgecontrolsWrite OBJECT IDENTIFIER ::= { modulepmdge 6 }
pmdgeCtrlOther OBJECT IDENTIFIER ::= { pmdgecontrolsWrite 1 }
pmdgeCtrlEqualizer OBJECT IDENTIFIER ::= { pmdgecontrolsWrite 2 }
pmdgeCtrlLine OBJECT IDENTIFIER ::= { pmdgecontrolsWrite 3 }

pmdgeri OBJECT IDENTIFIER ::= { modulepmdge 7 }
pmdgeriTable OBJECT IDENTIFIER ::= { pmdgeri 1 }

pmdgeConfig OBJECT IDENTIFIER ::= { modulepmdge 9 }

pmdgetraps OBJECT IDENTIFIER ::= { modulepmdge 10 }


--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************


PmdgeGrid ::= TEXTUAL-CONVENTION
    STATUS      current
    DESCRIPTION "Different grids on line ports"
    SYNTAX INTEGER {
		dgegrid200(200),
		dgegrid100(100),
		dgegrid50(50)
           }

PmdgePlanNumber ::= TEXTUAL-CONVENTION
    STATUS      current
    DESCRIPTION "Different values for plans"
    SYNTAX INTEGER {
		workingPlan(0),
		savedPlan1(1),
		savedPlan2(2),
		usedPlan(7)
           }

PmdgeChannel ::= TEXTUAL-CONVENTION
    STATUS      current
    DESCRIPTION "Channel selection on line ports"
    SYNTAX INTEGER {

           }

--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pmdgeRinvReloadInventory OBJECT-TYPE
  SYNTAX EkiOnOff
  MAX-ACCESS read-write
  STATUS current
  DESCRIPTION
        "Reload the inventory: This OID triggers an
         inventory reload."
  ::= { pmdgeri 2 }


pmdgeRinvHwPlatform OBJECT-TYPE
  SYNTAX DisplayString
  MAX-ACCESS read-only
  STATUS current
  DESCRIPTION
        "Module platform description: This OID contains the
         description of the Module."
  ::= { pmdgeri 4 }

pmdgeRinvSwPlatform OBJECT-TYPE
  SYNTAX DisplayString
  MAX-ACCESS read-only
  STATUS current
  DESCRIPTION
        "SW platform description: This OID contains the
         description of the Software platform."
  ::= { pmdgeri 5 }




pmdgeRinvPortTable OBJECT-TYPE
      SYNTAX  SEQUENCE OF PmdgeRinvPortEntry
      MAX-ACCESS  not-accessible
      STATUS  current
      DESCRIPTION
              "List of the Ports on the selected module"
      ::= { pmdgeriTable 1 }

pmdgeRinvPortEntry OBJECT-TYPE
        SYNTAX  PmdgeRinvPortEntry
        MAX-ACCESS  not-accessible
        STATUS  current
        DESCRIPTION
              "Row definition for the Port table"
        INDEX   { pmdgeRinvPortIndex }
        ::= { pmdgeRinvPortTable 1 }



PmdgeRinvPortEntry::=
        SEQUENCE {
          pmdgeRinvPortIndex
              Integer32,
          pmdgeRinvPort
              DisplayString
        }


    pmdgeRinvPortIndex OBJECT-TYPE
        SYNTAX  Integer32(1..16)
        MAX-ACCESS  read-only
        STATUS  current
        DESCRIPTION
              "Index for Port table"
        ::= { pmdgeRinvPortEntry 1 }


    pmdgeRinvPort OBJECT-TYPE
        SYNTAX  DisplayString
        MAX-ACCESS  read-only
        STATUS  current
        DESCRIPTION
              "Inventory for the Port: This OID contains the inventory for the Port"
        ::= { pmdgeRinvPortEntry 2 }




pmdgeRinvLineTable OBJECT-TYPE
      SYNTAX  SEQUENCE OF PmdgeRinvLineEntry
      MAX-ACCESS  not-accessible
      STATUS  current
      DESCRIPTION
              "List of the Lines on the selected module"
      ::= { pmdgeriTable 2 }

pmdgeRinvLineEntry OBJECT-TYPE
        SYNTAX  PmdgeRinvLineEntry
        MAX-ACCESS  not-accessible
        STATUS  current
        DESCRIPTION
              "Row definition for the Line table"
        INDEX   { pmdgeRinvLineIndex }
        ::= { pmdgeRinvLineTable 1 }



PmdgeRinvLineEntry::=
        SEQUENCE {
          pmdgeRinvLineIndex
              Integer32,
          pmdgeRinvxfpLine
              DisplayString
        }


    pmdgeRinvLineIndex OBJECT-TYPE
        SYNTAX  Integer32(1..16)
        MAX-ACCESS  read-only
        STATUS  current
        DESCRIPTION
              "Index for Line table"
        ::= { pmdgeRinvLineEntry 1 }


    pmdgeRinvxfpLine OBJECT-TYPE
        SYNTAX  DisplayString
        MAX-ACCESS  read-only
        STATUS  current
        DESCRIPTION
              "Inventory for the Line: This OID contains the inventory for the Line"
        ::= { pmdgeRinvLineEntry 2 }






--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pmdgeAlmsynthAlm0 OBJECT IDENTIFIER ::= { pmdgeAlmOtherCrit 0 }




pmdgeAlmDefFuseB OBJECT-TYPE
	  SYNTAX EkiOnOff
	  MAX-ACCESS read-only
	  STATUS current
	  DESCRIPTION
        "
        Fuse B Fail :This OID indicates
        that the fuse of the power input
        B is in fail condition  <Help>
          Status of the Fuse B <Condtype>
        DEF_FUSE_B <Probcause> powerProblem
        (36) <Alarmtype> equipmentAlarm
        (5) <Polarity> (2)
        "
	  ::= { pmdgeAlmsynthAlm0 16 }



pmdgeAlmDefFuseA OBJECT-TYPE
	  SYNTAX EkiOnOff
	  MAX-ACCESS read-only
	  STATUS current
	  DESCRIPTION
        "
        Fuse A Fail :This OID indicates
        that the fuse of the power input
        A is in fail condition  <Help>
          Status of the Fuse A <Condtype>
        DEF_FUSE_A <Probcause> powerProblem
        (36) <Alarmtype> equipmentAlarm
        (5) <Polarity> (2)
        "
	  ::= { pmdgeAlmsynthAlm0 15 }



pmdgeAlmModuleGlobFailure OBJECT-TYPE
	  SYNTAX EkiOnOff
	  MAX-ACCESS read-only
	  STATUS current
	  DESCRIPTION
        "
        Module Failure :This OID is set
        on detection of a failure originating
        from the PM <Condtype> MODULE_GLOB_FAILURE
        <Probcause> equipmentMalfunction
        (16) <Alarmtype> synthesisAlarm
        (12)  <Polarity> (2)
        "
	  ::= { pmdgeAlmsynthAlm0 9 }



pmdgeAlmInServiceNotReady OBJECT-TYPE
	  SYNTAX EkiOnOff
	  MAX-ACCESS read-only
	  STATUS current
	  DESCRIPTION
        "
        Building Waveplan :This OID is
        a status indicating that the switch
        is currently setting a new waveplan
        (used plan)  <Help>  This status
        indicates that the module is building
        a new waveplan (used plan) <Condtype>
        IN_SERVICE_NOT_READY <Probcause>
        informationalStatus(1000) <Alarmtype>
        other (1) <Polarity> (2)
        "
	  ::= { pmdgeAlmsynthAlm0 1 }



--- *****************************************************
---     LEAF for the synthAlm7 article
--- *****************************************************
pmdgeAlmsynthAlm7 OBJECT IDENTIFIER ::= { pmdgeAlmOtherCrit 7 }




pmdgeAlmSwitchAlm OBJECT-TYPE
	  SYNTAX EkiOnOff
	  MAX-ACCESS read-only
	  STATUS current
	  DESCRIPTION
        "
        Alarm On Equalizer :This OID indicates
        an alarm is present coming out
         of the switch  <Help>  This alarm
        indicates if an Alarm has been
         detected on the switch <Condtype>
        SWITCH_ALM <Probcause> equipmentMalfunction
        (16) <Alarmtype> equipmentAlarm
        (5) <Polarity> (2)
        "
	  ::= { pmdgeAlmsynthAlm7 10 }



pmdgeAlmSwitchDegrade OBJECT-TYPE
	  SYNTAX EkiOnOff
	  MAX-ACCESS read-only
	  STATUS current
	  DESCRIPTION
        "
        Warning On Equalizer :This OID
        indicates a  warning is present
        coming out of the switch  <Help>
         This alarm indicates if a warning
        has been detected on the switch
        <Condtype> SWITCH_DEGRADE <Probcause>
        equipmentMalfunction (16) <Alarmtype>
        equipmentAlarm (5) <Polarity> (2)
        "
	  ::= { pmdgeAlmsynthAlm7 9 }



pmdgeAlmInitNotCompl OBJECT-TYPE
	  SYNTAX EkiOnOff
	  MAX-ACCESS read-only
	  STATUS current
	  DESCRIPTION
        "
        Equalizer Not Ready :This OID
         indicates the switch is not operational.

         <Help>  This status indicates
         if the switch has been correctly
        initialized <Condtype> INIT_NOT_COMPL
        <Probcause> other (1) <Alarmtype>
        other (1) <Polarity> (2)
        "
	  ::= { pmdgeAlmsynthAlm7 2 }



--- *****************************************************
---     LEAF for the switchAlarms article
--- *****************************************************
pmdgeAlmswitchAlarms OBJECT IDENTIFIER ::= { pmdgeAlmOtherUrg 16 }




pmdgeAlmSwitchTempHighAla OBJECT-TYPE
	  SYNTAX EkiOnOff
	  MAX-ACCESS read-only
	  STATUS current
	  DESCRIPTION
        "
        Equalizer Temperature High Alarm
        :Alarm indicating that the temperature
        of the Switch in the module is
         higher than the alarm threshold
        value  <Help>  This Alarm indicates
        if the temperature of the Switch
        in the module is higher than the
        alarm threshold value. <Condtype>
        SWITCH_TEMP_HIGH_ALA <Probcause>
        temperatureUnacceptable (51) <Alarmtype>
        equipmentAlarm (5) <Polarity> (2)
        "
	  ::= { pmdgeAlmswitchAlarms 2 }



--- *****************************************************
---     LEAF for the switchDegrade article
--- *****************************************************
pmdgeAlmswitchDegrade OBJECT IDENTIFIER ::= { pmdgeAlmOtherNurg 17 }




pmdgeAlmSwitchTempHighDeg OBJECT-TYPE
	  SYNTAX EkiOnOff
	  MAX-ACCESS read-only
	  STATUS current
	  DESCRIPTION
        "
        Equalizer Temperature High Warning
        :Warning indicating that the temperature
        of the Switch in the module is
         higher than the warning threshold
        value.  <Help>  This Warning indicates
        if the temperature of the Switch
        in the module is higher than the
        warning threshold value. <Condtype>
        SWITCH_TEMP_HIGH_DEG <Probcause>
        temperatureUnacceptable (51) <Alarmtype>
        equipmentAlarm (5) <Polarity> (2)
        "
	  ::= { pmdgeAlmswitchDegrade 2 }



--- *****************************************************
---     LEAF for the moduleStatus article
--- *****************************************************
pmdgeAlmmoduleStatus OBJECT IDENTIFIER ::= { pmdgeAlmOtherUrg 66 }




pmdgeAlmSwitchNotReady OBJECT-TYPE
	  SYNTAX EkiOnOff
	  MAX-ACCESS read-only
	  STATUS current
	  DESCRIPTION
        "
        Equalizer Not Ready :This OID
         indicates the switch is not operational.

         <Help>   This status indicates
        if the Switch of the module has
        been correctly initialized <Condtype>
        SWITCH_NOT_READY <Probcause> equipmentMalfunction
        (16) <Alarmtype> equipmentAlarm
        (5) <Polarity> (2)
        "
	  ::= { pmdgeAlmmoduleStatus 5 }



pmdgeAlmHotReset OBJECT-TYPE
	  SYNTAX EkiOnOff
	  MAX-ACCESS read-only
	  STATUS current
	  DESCRIPTION
        "
        Previous Hot Reset :  <Help>
         This status indicates that the
        previous reset was a Hot Reset.
        <Condtype> HOT_RESET <Probcause>
        other (1) <Alarmtype> other (1)
        <Polarity> (2)
        "
	  ::= { pmdgeAlmmoduleStatus 3 }



pmdgeAlmWarmReset OBJECT-TYPE
	  SYNTAX EkiOnOff
	  MAX-ACCESS read-only
	  STATUS current
	  DESCRIPTION
        "
        Previous Warm Reset :  <Help>
          This status indicates that the
        previous reset was a Warm Reset.
        <Condtype> WARM_RESET <Probcause>
        other (1) <Alarmtype> other (1)
        <Polarity> (2)
        "
	  ::= { pmdgeAlmmoduleStatus 2 }



pmdgeAlmColdReset OBJECT-TYPE
	  SYNTAX EkiOnOff
	  MAX-ACCESS read-only
	  STATUS current
	  DESCRIPTION
        "
        Previous Cold Reset :  <Help>
          This status indicates that the
        previous reset was a Cold Reset.
        <Condtype> COLD_RESET <Probcause>
        other (1) <Alarmtype> other (1)
        <Polarity> (2)
        "
	  ::= { pmdgeAlmmoduleStatus 1 }



--- *****************************************************
---     LEAF for the moduleAlarms article
--- *****************************************************
pmdgeAlmmoduleAlarms OBJECT IDENTIFIER ::= { pmdgeAlmOtherUrg 67 }




pmdgeAlmCaseTempHighAla OBJECT-TYPE
	  SYNTAX EkiOnOff
	  MAX-ACCESS read-only
	  STATUS current
	  DESCRIPTION
        "
        Case Temperature High Alarm :Alarm
        indicating that the temperature
        of the case is higher than the
         alarm threshold value  <Help>
          This Alarm indicates if the temperature
        of the case is higher than the
         alarm threshold value. <Condtype>
        CASE_TEMP_HIGH_ALA <Probcause>
         temperatureUnacceptable (51) <Alarmtype>
        equipmentAlarm (5) <Polarity> (2)
        "
	  ::= { pmdgeAlmmoduleAlarms 4 }



pmdgeAlmModuleTempHighAla OBJECT-TYPE
	  SYNTAX EkiOnOff
	  MAX-ACCESS read-only
	  STATUS current
	  DESCRIPTION
        "
        Module Temperature High Alarm
         :Alarm indicating that the temperature
        of the module is higher than the
        alarm threshold value  <Help>
         This Alarm indicates if the temperature
        of the module is higher than the
        alarm threshold value. <Condtype>
        MODULE_TEMP_HIGH_ALA <Probcause>
        temperatureUnacceptable (51) <Alarmtype>
        equipmentAlarm (5) <Polarity> (2)
        "
	  ::= { pmdgeAlmmoduleAlarms 2 }



--- *****************************************************
---     LEAF for the moduleDegrad article
--- *****************************************************
pmdgeAlmmoduleDegrad OBJECT IDENTIFIER ::= { pmdgeAlmOtherUrg 68 }




pmdgeAlmCaseTempHighDeg OBJECT-TYPE
	  SYNTAX EkiOnOff
	  MAX-ACCESS read-only
	  STATUS current
	  DESCRIPTION
        "
        Case Temperature High Warning
         :Alarm indicating that the temperature
        of the case is higher than the
         warning threshold value  <Help>
         This Warning indicates if the
         temperature of the case is higher
        than the warning threshold value.
        <Condtype> CASE_TEMP_HIGH_DEG <Probcause>
        temperatureUnacceptable (51) <Alarmtype>
        equipmentAlarm (5) <Polarity> (2)
        "
	  ::= { pmdgeAlmmoduleDegrad 4 }



pmdgeAlmModuleTempHighDeg OBJECT-TYPE
	  SYNTAX EkiOnOff
	  MAX-ACCESS read-only
	  STATUS current
	  DESCRIPTION
        "
        Module Temperature High Warning
        :Alarm indicating that the temperature
        of the module is higher than the
        warning threshold value  <Help>
         This Warning indicates if the
         temperature of the module is higher
        than the warning threshold value.
        <Condtype> MODULE_TEMP_HIGH_DEG
        <Probcause> temperatureUnacceptable
        (51) <Alarmtype> equipmentAlarm
        (5) <Polarity> (2)
        "
	  ::= { pmdgeAlmmoduleDegrad 2 }








--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the synth0 article
--- *****************************************************
pmdgeCtrlsynth0 OBJECT IDENTIFIER ::= { pmdgeCtrlOther 0 }




pmdgeCtrlConfClear OBJECT-TYPE
	  SYNTAX EkiOnOff
	  MAX-ACCESS read-write
	  STATUS current
	  DESCRIPTION
        "
        Clear Configuration Tables :This
        bit clears the configuration tables
        from configuration in the flash.
         <Help>  This control restores
         the default configuration of the
        module
        "
	  ::= { pmdgeCtrlsynth0 13 }



pmdgeCtrlConfFlash OBJECT-TYPE
	  SYNTAX EkiOnOff
	  MAX-ACCESS read-write
	  STATUS current
	  DESCRIPTION
        "
        Write Configuration Tables :This
        bit saves the current configuration
        of the module as configuration
         in the flash.  <Help>  This control
        saves the customer configuration
        on the module
        "
	  ::= { pmdgeCtrlsynth0 9 }



pmdgeCtrlConfLoad OBJECT-TYPE
	  SYNTAX EkiOnOff
	  MAX-ACCESS read-write
	  STATUS current
	  DESCRIPTION
        "
        Load Configuration Tables :When
        set this enables loading from flash
        configuration1 into the module.
        "
	  ::= { pmdgeCtrlsynth0 1 }



--- *****************************************************
---     LEAF for the synth4 article
--- *****************************************************
pmdgeCtrlsynth4 OBJECT IDENTIFIER ::= { pmdgeCtrlOther 4 }




pmdgeCtrlCorrelatOff OBJECT-TYPE
	  SYNTAX EkiOnOff
	  MAX-ACCESS read-write
	  STATUS current
	  DESCRIPTION
        "
        Disable Alarm Correlation :This
        OID disables the alarm correlation
        in the PM
        "
	  ::= { pmdgeCtrlsynth4 2 }



pmdgeCtrlCorrelatOn OBJECT-TYPE
	  SYNTAX EkiOnOff
	  MAX-ACCESS read-write
	  STATUS current
	  DESCRIPTION
        "
        Enable Alarm Correlation :This
        OID enables the alarm correlation
        in the PM
        "
	  ::= { pmdgeCtrlsynth4 1 }



--- *****************************************************
---     LEAF for the swMgnt article
--- *****************************************************
pmdgeCtrlswMgnt OBJECT IDENTIFIER ::= { pmdgeCtrlOther 5 }




pmdgeCtrlWarmReset OBJECT-TYPE
	  SYNTAX EkiOnOff
	  MAX-ACCESS read-write
	  STATUS current
	  DESCRIPTION
        "
        Software Warm Reset :This OID,
        when set, causes a warm reset of
        the Software. This reset is not
        traffic affecting, and the configuration
        of the Sofwtare remains unchanged.
         <Help>  This control initiates
        a warm reset of the module.
        "
	  ::= { pmdgeCtrlswMgnt 3 }



pmdgeCtrlColdReset OBJECT-TYPE
	  SYNTAX EkiOnOff
	  MAX-ACCESS read-write
	  STATUS current
	  DESCRIPTION
        "
        Software Cold Reset :This OID,
        when set, causes a cold reset of
        the Software. This reset is traffic
        affecting, and the configuration
        of Software is reloaded on start-up.
         <Help>  This control initiates
        a cold reset of the module.
        "
	  ::= { pmdgeCtrlswMgnt 2 }



--- *****************************************************
---     LEAF for the switchCtrl article
--- *****************************************************
pmdgeCtrlswitchCtrl OBJECT IDENTIFIER ::= { pmdgeCtrlOther 16 }




pmdgeCtrlAllChannelsHighLoss OBJECT-TYPE
	  SYNTAX EkiOnOff
	  MAX-ACCESS read-write
	  STATUS current
	  DESCRIPTION
        "
        Equalizer Shutdown :This OID ,
        when set, puts all the waves on
        a high attenuation mode.   <Help>
         This control sets the waves on
        a high attenuation mode
        "
	  ::= { pmdgeCtrlswitchCtrl 1 }



--- *****************************************************
---     LEAF for the craftSynch article
--- *****************************************************

pmdgeCtrlcraftSynch OBJECT-TYPE
	  SYNTAX Unsigned32 (0..65535)
	  MAX-ACCESS read-write
	  STATUS current
	  DESCRIPTION
        "
        Craft Synchro :This OID is used
        for internal purpose only
        "
	  ::= { pmdgeCtrlOther 17 }



--- *********************************************************
---     TABLE for the pmdgeCtrlequTxCommonAttDeg articles
--- *********************************************************

pmdgeCtrlequTxCommonAttDegTable OBJECT-TYPE
	SYNTAX  SEQUENCE OF PmdgeCtrlequTxCommonAttDegEntry
	MAX-ACCESS not-accessible
	STATUS current
	DESCRIPTION
        "
        List of pmdgeCtrlequTxCommonAttDeg
        Article
        "
	::= { pmdgeCtrlEqualizer 19 }


pmdgeCtrlequTxCommonAttDegEntry OBJECT-TYPE
	SYNTAX PmdgeCtrlequTxCommonAttDegEntry
	MAX-ACCESS not-accessible
	STATUS current
	DESCRIPTION
        "
        Row definition for the pmdgeCtrlequTxCommonAttDeg
        table
        "
	INDEX   { pmdgeCtrlequTxCommonAttDegIndex }
	::= { pmdgeCtrlequTxCommonAttDegTable 1 }


PmdgeCtrlequTxCommonAttDegEntry ::=
	SEQUENCE {
	pmdgeCtrlequTxCommonAttDegIndex
		INTEGER,
	pmdgeCtrlequTxCommonAttDegPortn
		INTEGER
	}


pmdgeCtrlequTxCommonAttDegIndex OBJECT-TYPE
	SYNTAX  INTEGER(0..128)
	MAX-ACCESS  read-only
	STATUS current
	DESCRIPTION
        "
        Index definition for the pmdgeCtrlequTxCommonAttDeg
        table
        "
	::= { pmdgeCtrlequTxCommonAttDegEntry 1 }


pmdgeCtrlequTxCommonAttDegPortn OBJECT-TYPE
	SYNTAX  INTEGER (0..65535)
	MAX-ACCESS read-write
	STATUS current
	DESCRIPTION
        "
        Equalizer Output Attenuation :This
        OID defines the line output attenuation.
          <Help>  This OID defines the
         line output attenuation
        "
	::= { pmdgeCtrlequTxCommonAttDegEntry 2 }


--- *****************************************************
---     LEAF for the applyPlanUpdate article
--- *****************************************************
pmdgeCtrlapplyPlanUpdate OBJECT IDENTIFIER ::= { pmdgeCtrlEqualizer 44 }




pmdgeCtrlApply OBJECT-TYPE
	  SYNTAX EkiOnOff
	  MAX-ACCESS read-write
	  STATUS current
	  DESCRIPTION
        "
        Apply Update :This OID confirms
        the parameters selected for the
        waveplan modification
        "
	  ::= { pmdgeCtrlapplyPlanUpdate 1 }



--- *****************************************************
---     LEAF for the ledTest article
--- *****************************************************
pmdgeCtrlledTest OBJECT IDENTIFIER ::= { pmdgeCtrlOther 64 }




pmdgeCtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { pmdgeCtrlledTest 3 }



pmdgeCtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { pmdgeCtrlledTest 2 }



pmdgeCtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { pmdgeCtrlledTest 1 }



--- *********************************************************
---     TABLE for the pmdgeCtrlwavePlanAssignmentsRefresh articles
--- *********************************************************

pmdgeCtrlwavePlanAssignmentsRefreshTable OBJECT-TYPE
	SYNTAX  SEQUENCE OF PmdgeCtrlwavePlanAssignmentsRefreshEntry
	MAX-ACCESS not-accessible
	STATUS current
	DESCRIPTION
        "
        List of pmdgeCtrlwavePlanAssignmentsRefresh
        Article
        "
	::= { pmdgeCtrlOther 65 }


pmdgeCtrlwavePlanAssignmentsRefreshEntry OBJECT-TYPE
	SYNTAX PmdgeCtrlwavePlanAssignmentsRefreshEntry
	MAX-ACCESS not-accessible
	STATUS current
	DESCRIPTION
        "
        Row definition for the pmdgeCtrlwavePlanAssignmentsRefresh
        table
        "
	INDEX   { pmdgeCtrlwavePlanAssignmentsRefreshIndex }
	::= { pmdgeCtrlwavePlanAssignmentsRefreshTable 1 }


PmdgeCtrlwavePlanAssignmentsRefreshEntry ::=
	SEQUENCE {
	pmdgeCtrlwavePlanAssignmentsRefreshIndex
		INTEGER,
	pmdgeCtrlWaveStatusRefreshPortn
		EkiOnOff,
	pmdgeCtrlWaveNarrowingRefreshPortn
		INTEGER,
	pmdgeCtrlWaveCenterFrequencyRefreshPortn
		INTEGER,
	pmdgeCtrlWaveOOSRefreshPortn
		EkiOnOff,
	pmdgeCtrlWaveAttenuationRefreshPortn
		INTEGER,
	pmdgeCtrlWaveItuRefreshPortn
		DisplayString,
	pmdgeCtrlWaveDegreeRefreshPortn
		INTEGER,
	pmdgeCtrlUsageRefreshPortn
		EkiOnOff
	}


pmdgeCtrlwavePlanAssignmentsRefreshIndex OBJECT-TYPE
	SYNTAX  INTEGER(0..128)
	MAX-ACCESS  read-only
	STATUS current
	DESCRIPTION
        "
        Index definition for the pmdgeCtrlwavePlanAssignmentsRefresh
        table
        "
	::= { pmdgeCtrlwavePlanAssignmentsRefreshEntry 1 }


pmdgeCtrlWaveStatusRefreshPortn OBJECT-TYPE
	SYNTAX  EkiOnOff
	MAX-ACCESS read-only
	STATUS current
	DESCRIPTION
        "
        WaveStatus :This OID sets  the
        waves status to ON or OFF inside
        the waveplan.
        "
	::= { pmdgeCtrlwavePlanAssignmentsRefreshEntry 2 }


pmdgeCtrlWaveNarrowingRefreshPortn OBJECT-TYPE
	SYNTAX  INTEGER
	MAX-ACCESS read-only
	STATUS current
	DESCRIPTION
        "
        WaveNarrowing :This OID sets
         the wave narrowing value  inside
        the waveplan (Not Used)
        "
	::= { pmdgeCtrlwavePlanAssignmentsRefreshEntry 3 }


pmdgeCtrlWaveCenterFrequencyRefreshPortn OBJECT-TYPE
	SYNTAX  INTEGER
	MAX-ACCESS read-only
	STATUS current
	DESCRIPTION
        "
        WaveCenterFrequency :This OID
         sets  the wave center frequency
        value  inside the waveplan (Not
        Used)
        "
	::= { pmdgeCtrlwavePlanAssignmentsRefreshEntry 4 }


pmdgeCtrlWaveOOSRefreshPortn OBJECT-TYPE
	SYNTAX  EkiOnOff
	MAX-ACCESS read-only
	STATUS current
	DESCRIPTION
        "
        WaveOOS :This OID sets  the wave
        Out Of Service value  inside the
        waveplan (Not Used)
        "
	::= { pmdgeCtrlwavePlanAssignmentsRefreshEntry 5 }


pmdgeCtrlWaveAttenuationRefreshPortn OBJECT-TYPE
	SYNTAX  INTEGER
	MAX-ACCESS read-only
	STATUS current
	DESCRIPTION
        "
        WaveAttenuation :This OID sets
         the wave attenuation value inside
        the waveplan.
        "
	::= { pmdgeCtrlwavePlanAssignmentsRefreshEntry 6 }


pmdgeCtrlWaveItuRefreshPortn OBJECT-TYPE
	SYNTAX  DisplayString
	MAX-ACCESS read-only
	STATUS current
	DESCRIPTION
        "
        WaveItu :This OID sets  the wave
        channel number inside the waveplan
        (Not Used)
        "
	::= { pmdgeCtrlwavePlanAssignmentsRefreshEntry 7 }


pmdgeCtrlWaveDegreeRefreshPortn OBJECT-TYPE
	SYNTAX  INTEGER
	MAX-ACCESS read-only
	STATUS current
	DESCRIPTION
        "
        WaveDegree :This OID sets  the
        degree assigned to the wave inside
        the waveplan (Not Used)
        "
	::= { pmdgeCtrlwavePlanAssignmentsRefreshEntry 8 }


pmdgeCtrlUsageRefreshPortn OBJECT-TYPE
	SYNTAX  EkiOnOff
	MAX-ACCESS read-only
	STATUS current
	DESCRIPTION
        "
        Wave Assignment :This OID gives
        the assignment of a wave for a
         given waveplan along with the
         full possible  waveplan.
        "
	::= { pmdgeCtrlwavePlanAssignmentsRefreshEntry 16 }


--- *********************************************************
---     TABLE for the pmdgeCtrlwavePlanAssignmentsWork articles
--- *********************************************************

pmdgeCtrlwavePlanAssignmentsWorkTable OBJECT-TYPE
	SYNTAX  SEQUENCE OF PmdgeCtrlwavePlanAssignmentsWorkEntry
	MAX-ACCESS not-accessible
	STATUS current
	DESCRIPTION
        "
        List of pmdgeCtrlwavePlanAssignmentsWork
        Article
        "
	::= { pmdgeCtrlOther 66 }


pmdgeCtrlwavePlanAssignmentsWorkEntry OBJECT-TYPE
	SYNTAX PmdgeCtrlwavePlanAssignmentsWorkEntry
	MAX-ACCESS not-accessible
	STATUS current
	DESCRIPTION
        "
        Row definition for the pmdgeCtrlwavePlanAssignmentsWork
        table
        "
	INDEX   { pmdgeCtrlwavePlanAssignmentsWorkIndex }
	::= { pmdgeCtrlwavePlanAssignmentsWorkTable 1 }


PmdgeCtrlwavePlanAssignmentsWorkEntry ::=
	SEQUENCE {
	pmdgeCtrlwavePlanAssignmentsWorkIndex
		INTEGER,
	pmdgeCtrlWaveStatusWorkPortn
		EkiOnOff,
	pmdgeCtrlWaveNarrowingWorkPortn
		INTEGER,
	pmdgeCtrlWaveCenterFrequencyWorkPortn
		INTEGER,
	pmdgeCtrlWaveOOSWorkPortn
		EkiOnOff,
	pmdgeCtrlWaveAttenuationWorkPortn
		INTEGER,
	pmdgeCtrlWaveItuWorkPortn
		DisplayString,
	pmdgeCtrlWaveDegreeWorkPortn
		INTEGER,
	pmdgeCtrlUsageWorkPortn
		EkiOnOff
	}


pmdgeCtrlwavePlanAssignmentsWorkIndex OBJECT-TYPE
	SYNTAX  INTEGER(0..128)
	MAX-ACCESS  read-only
	STATUS current
	DESCRIPTION
        "
        Index definition for the pmdgeCtrlwavePlanAssignmentsWork
        table
        "
	::= { pmdgeCtrlwavePlanAssignmentsWorkEntry 1 }


pmdgeCtrlWaveStatusWorkPortn OBJECT-TYPE
	SYNTAX  EkiOnOff
	MAX-ACCESS read-write
	STATUS current
	DESCRIPTION
        "
        WaveStatus :This OID sets  the
        waves status to ON or OFF inside
        the waveplan.
        "
	::= { pmdgeCtrlwavePlanAssignmentsWorkEntry 2 }


pmdgeCtrlWaveNarrowingWorkPortn OBJECT-TYPE
	SYNTAX  INTEGER
	MAX-ACCESS read-write
	STATUS current
	DESCRIPTION
        "
        WaveNarrowing :This OID sets
         the wave narrowing value  inside
        the waveplan (Not Used)
        "
	::= { pmdgeCtrlwavePlanAssignmentsWorkEntry 3 }


pmdgeCtrlWaveCenterFrequencyWorkPortn OBJECT-TYPE
	SYNTAX  INTEGER
	MAX-ACCESS read-write
	STATUS current
	DESCRIPTION
        "
        WaveCenterFrequency :This OID
         sets  the wave center frequency
        value  inside the waveplan (Not
        Used)
        "
	::= { pmdgeCtrlwavePlanAssignmentsWorkEntry 4 }


pmdgeCtrlWaveOOSWorkPortn OBJECT-TYPE
	SYNTAX  EkiOnOff
	MAX-ACCESS read-write
	STATUS current
	DESCRIPTION
        "
        WaveOOS :This OID sets  the wave
        Out Of Service value  inside the
        waveplan (Not Used)
        "
	::= { pmdgeCtrlwavePlanAssignmentsWorkEntry 5 }


pmdgeCtrlWaveAttenuationWorkPortn OBJECT-TYPE
	SYNTAX  INTEGER
	MAX-ACCESS read-write
	STATUS current
	DESCRIPTION
        "
        WaveAttenuation :This OID sets
         the wave attenuation value inside
        the waveplan.
        "
	::= { pmdgeCtrlwavePlanAssignmentsWorkEntry 6 }


pmdgeCtrlWaveItuWorkPortn OBJECT-TYPE
	SYNTAX  DisplayString
	MAX-ACCESS read-only
	STATUS current
	DESCRIPTION
        "
        WaveItu :This OID sets  the wave
        channel number inside the waveplan
        (Not Used)
        "
	::= { pmdgeCtrlwavePlanAssignmentsWorkEntry 7 }


pmdgeCtrlWaveDegreeWorkPortn OBJECT-TYPE
	SYNTAX  INTEGER
	MAX-ACCESS read-write
	STATUS current
	DESCRIPTION
        "
        WaveDegree :This OID sets  the
        degree assigned to the wave inside
        the waveplan (Not Used)
        "
	::= { pmdgeCtrlwavePlanAssignmentsWorkEntry 8 }


pmdgeCtrlUsageWorkPortn OBJECT-TYPE
	SYNTAX  EkiOnOff
	MAX-ACCESS read-only
	STATUS current
	DESCRIPTION
        "
        Wave Assignment :This OID gives
        the assignment of a wave for a
         given waveplan along with the
         full possible  waveplan.
        "
	::= { pmdgeCtrlwavePlanAssignmentsWorkEntry 16 }


--- *****************************************************
---     LEAF for the buildFromMgntPlan article
--- *****************************************************

pmdgeCtrlbuildFromMgntPlan OBJECT-TYPE
	  SYNTAX DisplayString
	  MAX-ACCESS read-write
	  STATUS current
	  DESCRIPTION
        "
        Build From MGNT :This OID builds
        a waveplan from the waveplans stored
        in the MGNT board.  <Help>  This
        control builds a waveplan from
         the waveplans stored in the MGNT
        board.
        "
	  ::= { pmdgeCtrlOther 67 }



--- *****************************************************
---     LEAF for the loadToWorkplan article
--- *****************************************************

pmdgeCtrlloadToWorkplan OBJECT-TYPE
	  SYNTAX PmdgePlanNumber
	  MAX-ACCESS read-write
	  STATUS current
	  DESCRIPTION
        "
        Display Waveplan :This OID displays
        in the user interface one of the
        following waveplan : In service
        Waveplan, Saved Waveplan 1, Saved
        Waveplan 2, Build from MGNT Waveplan.
         <Help>  This control displays
         in the user interface one of the
        following waveplan : In service
        Waveplan, Saved Waveplan 1, Saved
        Waveplan 2, Build from MGNT Waveplan.
        "
	  ::= { pmdgeCtrlOther 68 }



--- *****************************************************
---     LEAF for the saveWorkPlanTo article
--- *****************************************************

pmdgeCtrlsaveWorkPlanTo OBJECT-TYPE
	  SYNTAX PmdgePlanNumber
	  MAX-ACCESS read-write
	  STATUS current
	  DESCRIPTION
        "
        Save Waveplan : This OID saves
        (in the Saved Waveplan 1 or Saved
        Waveplan 2) the waveplan built
         with the user interface.  <Help>
         This control saves (in the Saved
        Waveplan 1 or Saved Waveplan 2)
        the waveplan displayed with the
        user interface.
        "
	  ::= { pmdgeCtrlOther 69 }



--- *****************************************************
---     LEAF for the loadPlanToUse article
--- *****************************************************

pmdgeCtrlloadPlanToUse OBJECT-TYPE
	  SYNTAX PmdgePlanNumber
	  MAX-ACCESS read-write
	  STATUS current
	  DESCRIPTION
        "
        Set Waveplan In Service : This
        OID sets on the following waveplan
        In Service (Saved Waveplan 1, Saved
        Waveplan 2 or Displayed Waveplan).
         <Help>  This control sets on the
        following waveplan In Service (Saved
        Waveplan 1, Saved Waveplan 2 or
        Displayed Waveplan).
        "
	  ::= { pmdgeCtrlOther 70 }



--- *****************************************************
---     LEAF for the refreshWithPlan article
--- *****************************************************

pmdgeCtrlrefreshWithPlan OBJECT-TYPE
	  SYNTAX PmdgePlanNumber
	  MAX-ACCESS read-write
	  STATUS current
	  DESCRIPTION
        "
        Refresh User Interface :This OID
        refreshes the user interface with
        the information coming from the
        In service Waveplan, the Saved
         Waveplan 1 or the Saved Waveplan
        2.  <Help>  This control refreshes
        the user interface with the information
        coming from the In service Waveplan,
        the Saved Waveplan 1 or the Saved
        Waveplan 2.
        "
	  ::= { pmdgeCtrlOther 71 }



--- *****************************************************
---     LEAF for the savePlanToFile article
--- *****************************************************

pmdgeCtrlsavePlanToFile OBJECT-TYPE
	  SYNTAX PmdgePlanNumber
	  MAX-ACCESS read-write
	  STATUS current
	  DESCRIPTION
        "
        Export To File On MGNT :This OID
        exports the Displayed Waveplan
         to a file on the MGNT board.
         <Help>  This control the Displayed
        waveplan to a file on the MGNT
         board.
        "
	  ::= { pmdgeCtrlOther 72 }



--- *****************************************************
---     LEAF for the loadPlanFromFile article
--- *****************************************************

pmdgeCtrlloadPlanFromFile OBJECT-TYPE
	  SYNTAX PmdgePlanNumber
	  MAX-ACCESS read-write
	  STATUS current
	  DESCRIPTION
        "
        Import From File On MGNT :This
        OID imports a waveplan from a file
        on the MGNT board to the Displayed
        Waveplan.  <Help>  This control
        imports a waveplan from a file
         on the MGNT board to the Displayed
        Waveplan.
        "
	  ::= { pmdgeCtrlOther 73 }








--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



--- *****************************************************
---     LEAF for the switchTemp article
--- *****************************************************

pmdgeMesrswitchTemp OBJECT-TYPE
	  SYNTAX Unsigned32 (0..65535)
	  MAX-ACCESS read-only
	  STATUS current
	  DESCRIPTION
        "
        Equalizer Temperature :This OID
        gives the temperature value of
         the switch in the module (Temperature
        = AV/256) (Unit = C)   <Help>
          This measure gives the temperature
        value of the switch in the module
        "
	  ::= { pmdgeMesrOther 16 }



--- *****************************************************
---     LEAF for the moduleTemp article
--- *****************************************************

pmdgeMesrmoduleTemp OBJECT-TYPE
	  SYNTAX Unsigned32 (0..65535)
	  MAX-ACCESS read-only
	  STATUS current
	  DESCRIPTION
        "
        Module Temperature :This OID gives
        the temperature value of the module
        (Temperature = AV/256) (Unit =
         C)  <Help>   This measure gives
        the temperature value of the module
        "
	  ::= { pmdgeMesrOther 64 }



--- *****************************************************
---     LEAF for the caseTemp article
--- *****************************************************

pmdgeMesrcaseTemp OBJECT-TYPE
	  SYNTAX Unsigned32 (0..65535)
	  MAX-ACCESS read-only
	  STATUS current
	  DESCRIPTION
        "
        Case Temperature :This OID gives
        the temperature value of the case
        of the module  (Temperature = AV/256)
        (Unit = C)  <Help>   This measure
        gives the temperature value of
         the case of the module
        "
	  ::= { pmdgeMesrOther 65 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group lsd
--- *****************************************************

pmdgeCfgLsd OBJECT IDENTIFIER ::= { pmdgeConfig 1 }



--- *****************************************************
---     LEAF for the table 0012
--- *****************************************************

pmdgetableclientLsd OBJECT IDENTIFIER ::= { pmdgeCfgLsd 1 }



--- *****************************************************
---     LEAF for the table Group startup
--- *****************************************************

pmdgeCfgStartup OBJECT IDENTIFIER ::= { pmdgeConfig 2 }



--- *****************************************************
---     LEAF for the table 2111
--- *****************************************************

pmdgeCfgClientStartupTable OBJECT-TYPE
	SYNTAX  SEQUENCE OF PmdgeCfgClientStartupEntry
	MAX-ACCESS not-accessible
	STATUS current
	DESCRIPTION
        "
        List of  Article
        "
	::= { pmdgeCfgStartup 1 }


pmdgeCfgClientStartupEntry OBJECT-TYPE
	SYNTAX PmdgeCfgClientStartupEntry
	MAX-ACCESS not-accessible
	STATUS current
	DESCRIPTION
        "
        Row definition for the startup
        table
        "
	INDEX   { pmdgeCfgClientStartupIndex }
	::= { pmdgeCfgClientStartupTable 1 }


PmdgeCfgClientStartupEntry ::=
	SEQUENCE {
	pmdgeCfgClientStartupIndex
		INTEGER,
	pmdgeCfgLineaRxCommonAttDegPortn
		Unsigned32
	}


pmdgeCfgClientStartupIndex OBJECT-TYPE
	SYNTAX  INTEGER(0..128)
	MAX-ACCESS  read-only
	STATUS current
	DESCRIPTION
        "
        Index definition for the clientStartup
        table
        "
	::= { pmdgeCfgClientStartupEntry 1 }


pmdgeCfgLineaRxCommonAttDegPortn OBJECT-TYPE
	SYNTAX  Unsigned32 (0..65536)
	MAX-ACCESS read-write
	STATUS current
	DESCRIPTION
        "
        Defaut setting on attenuation
         on Rx Express :This register selects
        the Rx attenuator value of the
         Express line on setup
        "
	::= { pmdgeCfgClientStartupEntry 3 }


--- *****************************************************
---     LEAF for the table 2191
--- *****************************************************

pmdgetablelineStartup OBJECT IDENTIFIER ::= { pmdgeCfgStartup 2 }



--- *****************************************************
---     LEAF for the table 2511
--- *****************************************************

pmdgetableclientsDge OBJECT IDENTIFIER ::= { pmdgeCfgStartup 3 }



--- *****************************************************
---     LEAF for the table 2591
--- *****************************************************

pmdgetablelinesDge OBJECT IDENTIFIER ::= { pmdgeCfgStartup 4 }



pmdgeCfgequGridCurrent OBJECT-TYPE
	  SYNTAX Unsigned32 (0..65536)
	  MAX-ACCESS read-write
	  STATUS current
	  DESCRIPTION
        "
        Default setting of the grid  :This
        register selects the configuration
        of the grid used on setup
        "
	  ::= { pmdgetablelinesDge 2 }



--- *****************************************************
---     LEAF for the table 0005
--- *****************************************************

pmdgetableother OBJECT IDENTIFIER ::= { pmdgeCfgStartup 5 }



pmdgeCfgcomponentType OBJECT-TYPE
	  SYNTAX Unsigned32 (0..65536)
	  MAX-ACCESS read-only
	  STATUS current
	  DESCRIPTION
        "
        Component parameters :This OID
        defines the component parameters
        "
	  ::= { pmdgetableother 2 }



pmdgeCfgmiscellaneous OBJECT-TYPE
	  SYNTAX Unsigned32 (0..65536)
	  MAX-ACCESS read-only
	  STATUS current
	  DESCRIPTION
        "
        Miscellaneous default settings
        :This OID defines the miscellaneous
        parameters
        "
	  ::= { pmdgetableother 3 }



pmdgeCfgfirstChannel OBJECT-TYPE
	  SYNTAX Unsigned32 (0..65536)
	  MAX-ACCESS read-only
	  STATUS current
	  DESCRIPTION
        "
        Number of the first channel of
        the component :This OID defines
        the first channel number of the
        PM
        "
	  ::= { pmdgetableother 4 }



pmdgeCfglastChannel OBJECT-TYPE
	  SYNTAX Unsigned32 (0..65536)
	  MAX-ACCESS read-only
	  STATUS current
	  DESCRIPTION
        "
        Number of the last channel of
         the component :This OID defines
        the last channel number of the
         PM
        "
	  ::= { pmdgetableother 5 }



pmdgeCfggrid OBJECT-TYPE
	  SYNTAX Unsigned32 (0..65536)
	  MAX-ACCESS read-only
	  STATUS current
	  DESCRIPTION
        "
        Grid value of the component :This
        OID defines the grid of the PM
        "
	  ::= { pmdgetableother 6 }



--- *****************************************************
---     LEAF for the table Group labels
--- *****************************************************

pmdgeCfgLabels OBJECT IDENTIFIER ::= { pmdgeConfig 3 }



--- *****************************************************
---     LEAF for the table NO_VALUE
--- *****************************************************

pmdgeCfgLabelclientTable OBJECT-TYPE
	SYNTAX  SEQUENCE OF PmdgeCfgLabelclientEntry
	MAX-ACCESS not-accessible
	STATUS current
	DESCRIPTION
        "
        List of  Article
        "
	::= { pmdgeCfgLabels 1 }


pmdgeCfgLabelclientEntry OBJECT-TYPE
	SYNTAX PmdgeCfgLabelclientEntry
	MAX-ACCESS not-accessible
	STATUS current
	DESCRIPTION
        "
        Row definition for the labels
         table
        "
	INDEX   { pmdgeCfgLabelclientIndex }
	::= { pmdgeCfgLabelclientTable 1 }


PmdgeCfgLabelclientEntry ::=
	SEQUENCE {
	pmdgeCfgLabelclientIndex
		INTEGER,
	pmdgeCfgLabelclientPortn
		DisplayString
	}


pmdgeCfgLabelclientIndex OBJECT-TYPE
	SYNTAX  INTEGER(0..128)
	MAX-ACCESS  read-only
	STATUS current
	DESCRIPTION
        "
        Index definition for the labelclient
        table
        "
	::= { pmdgeCfgLabelclientEntry 1 }


pmdgeCfgLabelclientPortn OBJECT-TYPE
	SYNTAX  DisplayString( SIZE(1..16))
	MAX-ACCESS read-write
	STATUS current
	DESCRIPTION
        "
        Default settings on the label
         of the Ports :These registers
         configures the default initialisation
        settings of the labels of the ports.
        "
	::= { pmdgeCfgLabelclientEntry 3 }


--- *****************************************************
---     LEAF for the table NO_VALUE
--- *****************************************************

pmdgeCfgLabellineTable OBJECT-TYPE
	SYNTAX  SEQUENCE OF PmdgeCfgLabellineEntry
	MAX-ACCESS not-accessible
	STATUS current
	DESCRIPTION
        "
        List of  Article
        "
	::= { pmdgeCfgLabels 2 }


pmdgeCfgLabellineEntry OBJECT-TYPE
	SYNTAX PmdgeCfgLabellineEntry
	MAX-ACCESS not-accessible
	STATUS current
	DESCRIPTION
        "
        Row definition for the labels
         table
        "
	INDEX   { pmdgeCfgLabellineIndex }
	::= { pmdgeCfgLabellineTable 1 }


PmdgeCfgLabellineEntry ::=
	SEQUENCE {
	pmdgeCfgLabellineIndex
		INTEGER,
	pmdgeCfgLabellinePortn
		DisplayString
	}


pmdgeCfgLabellineIndex OBJECT-TYPE
	SYNTAX  INTEGER(0..128)
	MAX-ACCESS  read-only
	STATUS current
	DESCRIPTION
        "
        Index definition for the labelline
        table
        "
	::= { pmdgeCfgLabellineEntry 1 }


pmdgeCfgLabellinePortn OBJECT-TYPE
	SYNTAX  DisplayString( SIZE(1..16))
	MAX-ACCESS read-write
	STATUS current
	DESCRIPTION
        "
        Default settings on the label
         of the lines :These registers
         configures the default initialisation
        settings of the labels of the lines.
        "
	::= { pmdgeCfgLabellineEntry 3 }



pmdgeCfgWriteConfiguration  OBJECT-TYPE
	SYNTAX EkiOnOff
	MAX-ACCESS read-write
	STATUS current
	DESCRIPTION
	"Write configuration to module:This OID
	 writes the complete configuration to the module"
	::= { pmdgeConfig 257 }






--- *****************************************************
---     TRAP OBJECTS
--- *****************************************************

pmdgetrapBoardNumber OBJECT-TYPE
	SYNTAX INTEGER(1..64)
	MAX-ACCESS read-only
	STATUS current
	DESCRIPTION
	"Last module which generates a trap"
	::= { pmdgetraps 4 }







--- *****************************************************
---     HW TRAPS
--- *****************************************************

pmdgePowerTrapUrgentGoesOn NOTIFICATION-TYPE
	OBJECTS {pmdgeAlmDefFuseB, pmdgeAlmDefFuseA , pmdgetrapBoardNumber}
	STATUS current
	DESCRIPTION "Urgent power supply default is activated"
	::= { pmdgetraps 50 }
pmdgePowerTrapUrgentGoesOff NOTIFICATION-TYPE
	OBJECTS {pmdgeAlmDefFuseB, pmdgeAlmDefFuseA , pmdgetrapBoardNumber}
	STATUS current
	DESCRIPTION "Urgent power supply default disappeared"
	::= { pmdgetraps 51 }






END
