-- *****************************************************************
-- EKINOPS-pmc1002.TXT:  MIB
--
--MIB Part Number:3MI00025ACAE
--MIB Version:03
--
-- Copyright (c) 2016 by Ekinops
-- All rights reserved.
--
-- *****************************************************************

EKINOPS-PMC1002-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

modulepmc1002 MODULE-IDENTITY
        LAST-UPDATED "201606020000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.net"
        DESCRIPTION
          "MIB for managing Ekinops modules with PM1002 software"
	REVISION "201101040000Z"
	DESCRIPTION
	  "Initial Version."

	REVISION "201102020000Z"
	DESCRIPTION
	  "Formulas and Event on XFP init"
	REVISION "201207030000Z"
	DESCRIPTION
	  "Minor cosmetic updates"
	REVISION "201304030000Z"
	DESCRIPTION
	  "S1,K1,K2 suppress"
	REVISION "201403260000Z"
	DESCRIPTION
	  "Probcause,AlarmType - NMS completion"
	REVISION "201501200000Z"
	DESCRIPTION
	  "Labels cosmetic updates"
	REVISION "201605200000Z"
	DESCRIPTION
	  "New AlarmType – synthesisAlarm (12)"
	REVISION "201606020000Z"
	DESCRIPTION
	  "Capabilities objects of Table 5"
        ::= { ekinops 50 }



--- *****************************************************
---     LEAF LEVEL 2
--- *****************************************************


pmc1002alarms OBJECT IDENTIFIER ::= { modulepmc1002 2 }
pmc1002AlmOther OBJECT IDENTIFIER ::= { pmc1002alarms 1 }
pmc1002AlmOtherNurg OBJECT IDENTIFIER ::= { pmc1002AlmOther 1 }
pmc1002AlmOtherUrg OBJECT IDENTIFIER ::= { pmc1002AlmOther 2 }
pmc1002AlmOtherCrit OBJECT IDENTIFIER ::= { pmc1002AlmOther 3 }

pmc1002AlmClient OBJECT IDENTIFIER ::= { pmc1002alarms 2 }
pmc1002AlmClientNurg OBJECT IDENTIFIER ::= { pmc1002AlmClient 1 }
pmc1002AlmClientUrg OBJECT IDENTIFIER ::= { pmc1002AlmClient 2 }
pmc1002AlmClientCrit OBJECT IDENTIFIER ::= { pmc1002AlmClient 3 }

pmc1002AlmLine OBJECT IDENTIFIER ::= { pmc1002alarms 3 }
pmc1002AlmLineNurg OBJECT IDENTIFIER ::= { pmc1002AlmLine 1 }
pmc1002AlmLineUrg OBJECT IDENTIFIER ::= { pmc1002AlmLine 2 }
pmc1002AlmLineCrit OBJECT IDENTIFIER ::= { pmc1002AlmLine 3 }





pmc1002measures OBJECT IDENTIFIER ::= { modulepmc1002 3 }
pmc1002MesrOther OBJECT IDENTIFIER ::= { pmc1002measures 1 }
pmc1002MesrClient OBJECT IDENTIFIER ::= { pmc1002measures 2 }
pmc1002MesrLine OBJECT IDENTIFIER ::= { pmc1002measures 3 }




pmc1002counters OBJECT IDENTIFIER ::= { modulepmc1002 4 }
pmc1002CntOther OBJECT IDENTIFIER ::= { pmc1002counters 1 }
pmc1002CntClient OBJECT IDENTIFIER ::= { pmc1002counters 2 }
pmc1002CntLine OBJECT IDENTIFIER ::= { pmc1002counters 3 }


pmc1002controlsWrite OBJECT IDENTIFIER ::= { modulepmc1002 6 }
pmc1002CtrlOther OBJECT IDENTIFIER ::= { pmc1002controlsWrite 1 }
pmc1002CtrlClient OBJECT IDENTIFIER ::= { pmc1002controlsWrite 2 }
pmc1002CtrlLine OBJECT IDENTIFIER ::= { pmc1002controlsWrite 3 }

pmc1002ri OBJECT IDENTIFIER ::= { modulepmc1002 7 }
pmc1002riTable OBJECT IDENTIFIER ::= { pmc1002ri 1 }

pmc1002download OBJECT IDENTIFIER ::= { modulepmc1002 8 }
pmc1002DwlOther OBJECT IDENTIFIER ::= { pmc1002download 1 }
pmc1002DwlClient OBJECT IDENTIFIER ::= { pmc1002download 2 }
pmc1002DwlLine OBJECT IDENTIFIER ::= { pmc1002download 3 }

pmc1002Config OBJECT IDENTIFIER ::= { modulepmc1002 10 }

pmc1002traps OBJECT IDENTIFIER ::= { modulepmc1002 11 }

pmc1002Monitoring OBJECT IDENTIFIER ::= { modulepmc1002 12}

pmc1002MonOther OBJECT IDENTIFIER ::= { pmc1002Monitoring 1 }
pmc1002MonSync OBJECT IDENTIFIER ::= { pmc1002MonOther 1 }
pmc1002MonTimeStamp OBJECT IDENTIFIER ::= { pmc1002MonOther 2 }

pmc1002MonClient OBJECT IDENTIFIER ::= { pmc1002Monitoring 2 }

pmc1002MonLine OBJECT IDENTIFIER ::= { pmc1002Monitoring 3 }

pmc1002Rmon OBJECT IDENTIFIER ::= { pmc1002Monitoring 4 }

pmc1002RmonClient OBJECT IDENTIFIER ::= { pmc1002Rmon 1 }
pmc1002RmonLine OBJECT IDENTIFIER ::= { pmc1002Rmon 2 }
pmc1002RmonOther OBJECT IDENTIFIER ::= { pmc1002Rmon 3 }

--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Pmc1002OtxMode ::= TEXTUAL-CONVENTION
    STATUS      current
    DESCRIPTION "Different modes on OTX-TLH on client and line ports"
    SYNTAX INTEGER {
		otx80mode(1),
		otx60mode(2),
		otxadjustmode(4)
           }

Pmc1002OtxGrid ::= TEXTUAL-CONVENTION
    STATUS      current
    DESCRIPTION "Different grids on OTX-TLH on client and line ports"
    SYNTAX INTEGER {
		otxgrid200(200),
		otxgrid100(100),
		otxgrid50(50)
           }

Pmc1002AdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pmc1002OtxChannel ::= TEXTUAL-CONVENTION
    STATUS      current
    DESCRIPTION "Channel selection on OTX-TLH on client and line ports"
    SYNTAX INTEGER

Pmc1002DccMode ::= TEXTUAL-CONVENTION
    STATUS      current
    DESCRIPTION "Mode for DCC"
    SYNTAX INTEGER {
		dccNo(0),
		dcctermLine1(1),
		dcctermLine2(2),
		dcctermLines12(3),
		dccmaster(4),
		dccslaveLine12(7)
           }

Pmc1002Mode ::= TEXTUAL-CONVENTION
    STATUS      current
    DESCRIPTION "Different modes for the module"
    SYNTAX INTEGER {
		modedual(0),
		modeprotect(1),
		moderegen(2)
           }

--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pmc1002RinvReloadInventory OBJECT-TYPE
  SYNTAX EkiOnOff
  MAX-ACCESS read-write
  STATUS current
  DESCRIPTION
        "Reload the inventory: This OID triggers an
         inventory reload."
  ::= { pmc1002ri 2 }

pmc1002RinvHwPlatform OBJECT-TYPE
  SYNTAX DisplayString
  MAX-ACCESS read-only
  STATUS current
  DESCRIPTION
        "HW platform description: This OID contains the
         description of the Hardware platform."
  ::= { pmc1002ri 3 }

pmc1002RinvModulePlatform OBJECT-TYPE
  SYNTAX DisplayString
  MAX-ACCESS read-only
  STATUS current
  DESCRIPTION
        "Module platform description: This OID contains the
         description of the Module."
  ::= { pmc1002ri 4 }

pmc1002RinvSwPlatform OBJECT-TYPE
  SYNTAX DisplayString
  MAX-ACCESS read-only
  STATUS current
  DESCRIPTION
        "SW platform description: This OID contains the
         description of the Software platform."
  ::= { pmc1002ri 5 }

pmc1002RinvGwPlatform OBJECT-TYPE
  SYNTAX DisplayString
  MAX-ACCESS read-only
  STATUS current
  DESCRIPTION
        "GW platform desciption: This OID contains the
         description of the Gateware platform."
  ::= { pmc1002ri 6 }



pmc1002RinvClientTable OBJECT-TYPE
      SYNTAX  SEQUENCE OF Pmc1002RinvClientEntry
      MAX-ACCESS  not-accessible
      STATUS  current
      DESCRIPTION
              "List of the Clients on the selected module"
      ::= { pmc1002riTable 1 }

pmc1002RinvClientEntry OBJECT-TYPE
        SYNTAX  Pmc1002RinvClientEntry
        MAX-ACCESS  not-accessible
        STATUS  current
        DESCRIPTION
              "Row definition for the Client table"
        INDEX   { pmc1002RinvClientIndex }
        ::= { pmc1002RinvClientTable 1 }



Pmc1002RinvClientEntry::=
        SEQUENCE {
          pmc1002RinvClientIndex
              Integer32,
          pmc1002RinvClient
              DisplayString
        }


    pmc1002RinvClientIndex OBJECT-TYPE
        SYNTAX  Integer32(1..16)
        MAX-ACCESS  read-only
        STATUS  current
        DESCRIPTION
              "Index for Client table"
        ::= { pmc1002RinvClientEntry 1 }


    pmc1002RinvClient OBJECT-TYPE
        SYNTAX  DisplayString
        MAX-ACCESS  read-only
        STATUS  current
        DESCRIPTION
              "Inventory for the Client: This OID contains the inventory for the Client Port"
        ::= { pmc1002RinvClientEntry 2 }




pmc1002RinvLineTable OBJECT-TYPE
      SYNTAX  SEQUENCE OF Pmc1002RinvLineEntry
      MAX-ACCESS  not-accessible
      STATUS  current
      DESCRIPTION
              "List of the Lines on the selected module"
      ::= { pmc1002riTable 2 }

pmc1002RinvLineEntry OBJECT-TYPE
        SYNTAX  Pmc1002RinvLineEntry
        MAX-ACCESS  not-accessible
        STATUS  current
        DESCRIPTION
              "Row definition for the Line table"
        INDEX   { pmc1002RinvLineIndex }
        ::= { pmc1002RinvLineTable 1 }



Pmc1002RinvLineEntry::=
        SEQUENCE {
          pmc1002RinvLineIndex
              Integer32,
          pmc1002RinvxfpLine
              DisplayString
        }


    pmc1002RinvLineIndex OBJECT-TYPE
        SYNTAX  Integer32(1..16)
        MAX-ACCESS  read-only
        STATUS  current
        DESCRIPTION
              "Index for XFP table"
        ::= { pmc1002RinvLineEntry 1 }


    pmc1002RinvxfpLine OBJECT-TYPE
        SYNTAX  DisplayString
        MAX-ACCESS  read-only
        STATUS  current
        DESCRIPTION
              "Inventory for the Line: This OID contains the inventory for the Line"
        ::= { pmc1002RinvLineEntry 2 }






--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pmc1002AlmsynthAlm0 OBJECT IDENTIFIER ::= { pmc1002AlmOtherCrit 0 }




pmc1002AlmDefFuseB OBJECT-TYPE
	  SYNTAX EkiOnOff
	  MAX-ACCESS read-only
	  STATUS current
	  DESCRIPTION
        "
        Fuse B Fail :This OID indicates
        that the fuse of the power input
        B is in fail condition  <Help>
          Status of the Fuse B <Condtype>
        DEF_FUSE_B <Probcause> powerProblem
        (36) <Alarmtype> equipmentAlarm
        (5) <Polarity> (2)
        "
	  ::= { pmc1002AlmsynthAlm0 16 }



pmc1002AlmDefFuseA OBJECT-TYPE
	  SYNTAX EkiOnOff
	  MAX-ACCESS read-only
	  STATUS current
	  DESCRIPTION
        "
        Fuse A Fail :This OID indicates
        that the fuse of the power input
        A is in fail condition  <Help>
          Status of the Fuse A <Condtype>
        DEF_FUSE_A <Probcause> powerProblem
        (36) <Alarmtype> equipmentAlarm
        (5) <Polarity> (2)
        "
	  ::= { pmc1002AlmsynthAlm0 15 }



pmc1002AlmModGlobFail OBJECT-TYPE
	  SYNTAX EkiOnOff
	  MAX-ACCESS read-only
	  STATUS current
	  DESCRIPTION
        "
        Module Failure :This OID is set
        on detection of a failure originating
        from the PM <Condtype> MOD_GLOB_FAIL
        <Probcause> equipmentMalfunction
        (16) <Alarmtype> synthesisAlarm
        (12)  <Polarity> (2)
        "
	  ::= { pmc1002AlmsynthAlm0 9 }



--- *****************************************************
---     LEAF for the synthAlm2 article
--- *****************************************************
pmc1002AlmsynthAlm2 OBJECT IDENTIFIER ::= { pmc1002AlmOtherNurg 2 }




pmc1002AlmMaintenanceOn OBJECT-TYPE
	  SYNTAX EkiOnOff
	  MAX-ACCESS read-only
	  STATUS current
	  DESCRIPTION
        "
        Maintenance Mode :This OID indicates
        that the PM is in maintenance mode.
         <Help>  This alarm indicates that
        the maintenance mode is enabled
        on the PM <Condtype> MAINTENANCE_ON
        <Probcause> other (1) <Alarmtype>
        other (1) <Polarity> (2)
        "
	  ::= { pmc1002AlmsynthAlm2 5 }



pmc1002AlmCorrelatOff OBJECT-TYPE
	  SYNTAX EkiOnOff
	  MAX-ACCESS read-only
	  STATUS current
	  DESCRIPTION
        "
        Not Used :This OID, when set,
         indicates that alarm correlation
        is not being performed. <Condtype>
        CORRELAT_OFF <Probcause> other
         (1) <Alarmtype> other (1) <Polarity>
        (2)
        "
	  ::= { pmc1002AlmsynthAlm2 4 }



pmc1002AlmConfTableLoad OBJECT-TYPE
	  SYNTAX EkiOnOff
	  MAX-ACCESS read-only
	  STATUS current
	  DESCRIPTION
        "
        PM Configuration Load :This OID
         is at 1 during the loading of
         configuration tables in the modules
        RAM. <Condtype> CONF_TABLE_LOAD
        <Probcause> other (1) <Alarmtype>
        other (1) <Polarity> (2)
        "
	  ::= { pmc1002AlmsynthAlm2 3 }



pmc1002AlmInvUpload OBJECT-TYPE
	  SYNTAX EkiOnOff
	  MAX-ACCESS read-only
	  STATUS current
	  DESCRIPTION
        "
        Inventory Upload :This OID is
         at 1 during the uploading of PM
        inventory information. <Condtype>
        INV_UPLOAD <Probcause> other (1)
        <Alarmtype> other (1) <Polarity>
        (2)
        "
	  ::= { pmc1002AlmsynthAlm2 2 }



pmc1002AlmConfTableSave OBJECT-TYPE
	  SYNTAX EkiOnOff
	  MAX-ACCESS read-only
	  STATUS current
	  DESCRIPTION
        "
        PM Configuration Save :This OID
        is at 1 during the saving of a
         new configuration table in the
        module Flash memory. <Condtype>
        CONF_TABLE_SAVE <Probcause> other
        (1) <Alarmtype> other (1) <Polarity>
        (2)
        "
	  ::= { pmc1002AlmsynthAlm2 1 }



--- *********************************************************
---     TABLE for the pmc1002AlmsynthAlmLine articles
--- *********************************************************

pmc1002AlmsynthAlmLineTable OBJECT-TYPE
	SYNTAX  SEQUENCE OF Pmc1002AlmsynthAlmLineEntry
	MAX-ACCESS not-accessible
	STATUS current
	DESCRIPTION
        "
        List of pmc1002AlmsynthAlmLine
        Article
        "
	::= { pmc1002AlmLineCrit 7 }


pmc1002AlmsynthAlmLineEntry OBJECT-TYPE
	SYNTAX Pmc1002AlmsynthAlmLineEntry
	MAX-ACCESS not-accessible
	STATUS current
	DESCRIPTION
        "
        Row definition for the pmc1002AlmsynthAlmLine
        table
        "
	INDEX   { pmc1002AlmsynthAlmLineIndex }
	::= { pmc1002AlmsynthAlmLineTable 1 }


Pmc1002AlmsynthAlmLineEntry ::=
	SEQUENCE {
	pmc1002AlmsynthAlmLineIndex
		INTEGER,
	pmc1002AlmLineActivePortn
		EkiOnOff,
	pmc1002AlmLineFailPortn
		EkiOnOff,
	pmc1002AlmLineDdmAlmPortn
		EkiOnOff,
	pmc1002AlmLineDdmWarningPortn
		EkiOnOff,
	pmc1002AlmLineUpRdiInsPortn
		EkiOnOff,
	pmc1002AlmLineLocalOosPortn
		EkiOnOff,
	pmc1002AlmLineXfpTxOffPortn
		EkiOnOff,
	pmc1002AlmLineHwFailPortn
		EkiOnOff,
	pmc1002AlmLineXfpInitNotComplPortn
		EkiOnOff,
	pmc1002AlmLineXfpAbsentPortn
		EkiOnOff
	}


pmc1002AlmsynthAlmLineIndex OBJECT-TYPE
	SYNTAX  INTEGER(0..128)
	MAX-ACCESS  read-only
	STATUS current
	DESCRIPTION
        "
        Index definition for the pmc1002AlmsynthAlmLine
        table
        "
	::= { pmc1002AlmsynthAlmLineEntry 1 }


pmc1002AlmLineActivePortn OBJECT-TYPE
	SYNTAX  EkiOnOff
	MAX-ACCESS read-only
	STATUS current
	DESCRIPTION
        "
        Line Active :This bit indicates
        the line #n is active on receive
        side <Condtype> LINE_ACTIVE <Probcause>
        informationalStatus(1000) <Alarmtype>
        other (1) <Polarity> (2)
        "
	::= { pmc1002AlmsynthAlmLineEntry 17 }


pmc1002AlmLineFailPortn OBJECT-TYPE
	SYNTAX  EkiOnOff
	MAX-ACCESS read-only
	STATUS current
	DESCRIPTION
        "
        Line Port Failure :This OID indicates
        a failure on the line port <Condtype>
        LINE_FAIL <Probcause> equipmentMalfunction
        (16) <Alarmtype> synthesisAlarm
        (12)  <Polarity> (2)
        "
	::= { pmc1002AlmsynthAlmLineEntry 13 }


pmc1002AlmLineDdmAlmPortn OBJECT-TYPE
	SYNTAX  EkiOnOff
	MAX-ACCESS read-only
	STATUS current
	DESCRIPTION
        "
        Alarm On Line Optical Module DDM
        :This OID indicates an alarm is
        present coming out of Line optical
        interface DDM  <Help>  This alarm
        indicates if a DDM Alarm has been
        detected on the line transceiver
        <Condtype> LINE_DDM_ALM <Probcause>
        equipmentMalfunction (16) <Alarmtype>
        synthesisAlarm (12)  <Polarity>
        (2)
        "
	::= { pmc1002AlmsynthAlmLineEntry 11 }


pmc1002AlmLineDdmWarningPortn OBJECT-TYPE
	SYNTAX  EkiOnOff
	MAX-ACCESS read-only
	STATUS current
	DESCRIPTION
        "
        Warning On Line Optical Module
        DDM :This OID indicates a warning
        is present coming out of Line optical
        interface DDM  <Help>  This alarm
        indicates if a DDM Warning has
         been detected on the line transceiver
        <Condtype> LINE_DDM_WARNING <Probcause>
        equipmentMalfunction (16) <Alarmtype>
        synthesisAlarm (12)  <Polarity>
        (2)
        "
	::= { pmc1002AlmsynthAlmLineEntry 10 }


pmc1002AlmLineUpRdiInsPortn OBJECT-TYPE
	SYNTAX  EkiOnOff
	MAX-ACCESS read-only
	STATUS current
	DESCRIPTION
        "
        MS-RDI/L-RDI Inserted On Line
         :This OID indicates an upstream
        RDI has been inserted in the outgoing
        10 Gb/s signal.   <Help>  This
         status indicates if a MS-RDI/L-RDI
        is currently inserted on the line
        interface. <Condtype> LINE_UP_RDI_INS
        <Probcause> informationalStatus(1000)
        <Alarmtype> other (1) <Polarity>
        (2)
        "
	::= { pmc1002AlmsynthAlmLineEntry 9 }


pmc1002AlmLineLocalOosPortn OBJECT-TYPE
	SYNTAX  EkiOnOff
	MAX-ACCESS read-only
	STATUS current
	DESCRIPTION
        "
        Line Port In Service :This OID
        indicates that the Line port is
        In Service (1) of Out or Service
        (2)  <Help>  This status indicates
        if the line port is in service
         <Condtype> LINE_LOCAL_OOS <Probcause>
        informationalStatus(1000) <Alarmtype>
        other (1) <Polarity> (2)
        "
	::= { pmc1002AlmsynthAlmLineEntry 7 }


pmc1002AlmLineXfpTxOffPortn OBJECT-TYPE
	SYNTAX  EkiOnOff
	MAX-ACCESS read-only
	STATUS current
	DESCRIPTION
        "
        Line Optical Laser Shutdown :This
        OID indicates the line optical
         output power is on  <Help>  This
        status indicates if the line transceiver
        laser is ON or OFF <Condtype> LINE_XFP_TX_OFF
        <Probcause> other (1) <Alarmtype>
        equipmentAlarm (5) <Polarity> (2)
        "
	::= { pmc1002AlmsynthAlmLineEntry 6 }


pmc1002AlmLineHwFailPortn OBJECT-TYPE
	SYNTAX  EkiOnOff
	MAX-ACCESS read-only
	STATUS current
	DESCRIPTION
        "
        Line Port HW Failure :This OID
        indicates a failure on line port,
        most probably caused by a HW issue
        <Condtype> LINE_HW_FAIL <Probcause>
        equipmentMalfunction (16) <Alarmtype>
        synthesisAlarm (12)  <Polarity>
        (2)
        "
	::= { pmc1002AlmsynthAlmLineEntry 5 }


pmc1002AlmLineXfpInitNotComplPortn OBJECT-TYPE
	SYNTAX  EkiOnOff
	MAX-ACCESS read-only
	STATUS current
	DESCRIPTION
        "
        Line Optical Module Ready :This
        OID indicates that the line optical
        interface (XFP or OTX) is not operational.
         <Help>  This status indicates
         if the line transceiver has been
        correctly initialized <Condtype>
        LINE_XFP_INIT_NOT_COMPL <Probcause>
        equipmentMalfunction (16) <Alarmtype>
        equipmentAlarm (5) <Polarity> (2)
        <Event> ObjectCDINV
        "
	::= { pmc1002AlmsynthAlmLineEntry 3 }


pmc1002AlmLineXfpAbsentPortn OBJECT-TYPE
	SYNTAX  EkiOnOff
	MAX-ACCESS read-only
	STATUS current
	DESCRIPTION
        "
        Line Optical Module Absent :This
        OID indicates that the line optical
        interface (XFP or OTX) is not plugged
        in.  <Help>  This alarm indicates
        if the line transceiver is present.
        <Condtype> LINE_XFP_ABSENT <Probcause>
        inputOutputDeviceError (24) <Alarmtype>
        equipmentAlarm (5) <Polarity> (2)
        <Event> ObjectCDINV
        "
	::= { pmc1002AlmsynthAlmLineEntry 2 }


--- *********************************************************
---     TABLE for the pmc1002AlmsynthAlmPort articles
--- *********************************************************

pmc1002AlmsynthAlmPortTable OBJECT-TYPE
	SYNTAX  SEQUENCE OF Pmc1002AlmsynthAlmPortEntry
	MAX-ACCESS not-accessible
	STATUS current
	DESCRIPTION
        "
        List of pmc1002AlmsynthAlmPort
        Article
        "
	::= { pmc1002AlmClientCrit 8 }


pmc1002AlmsynthAlmPortEntry OBJECT-TYPE
	SYNTAX Pmc1002AlmsynthAlmPortEntry
	MAX-ACCESS not-accessible
	STATUS current
	DESCRIPTION
        "
        Row definition for the pmc1002AlmsynthAlmPort
        table
        "
	INDEX   { pmc1002AlmsynthAlmPortIndex }
	::= { pmc1002AlmsynthAlmPortTable 1 }


Pmc1002AlmsynthAlmPortEntry ::=
	SEQUENCE {
	pmc1002AlmsynthAlmPortIndex
		INTEGER,
	pmc1002AlmClientUpCsfPortn
		EkiOnOff,
	pmc1002AlmClientFailPortn
		EkiOnOff,
	pmc1002AlmClientSfpDdmAlmPortn
		EkiOnOff,
	pmc1002AlmClientSfpDdmWarningPortn
		EkiOnOff,
	pmc1002AlmClientDwCaisPortn
		EkiOnOff,
	pmc1002AlmClientLocalOosPortn
		EkiOnOff,
	pmc1002AlmClientDwLsdPortn
		EkiOnOff,
	pmc1002AlmClientHwFailPortn
		EkiOnOff,
	pmc1002AlmClientDdmAbsentPortn
		EkiOnOff,
	pmc1002AlmClientSfpAbsentPortn
		EkiOnOff
	}


pmc1002AlmsynthAlmPortIndex OBJECT-TYPE
	SYNTAX  INTEGER(0..128)
	MAX-ACCESS  read-only
	STATUS current
	DESCRIPTION
        "
        Index definition for the pmc1002AlmsynthAlmPort
        table
        "
	::= { pmc1002AlmsynthAlmPortEntry 1 }


pmc1002AlmClientUpCsfPortn OBJECT-TYPE
	SYNTAX  EkiOnOff
	MAX-ACCESS read-only
	STATUS current
	DESCRIPTION
        "
        Client Signal Fail Inserted :This
        OID indicates a CSF has been inserted
        in the upstream client port.  <Help>
         This status indicates if a Client
        Signal Fail is currently inserted
        on the line signal for this client
        port <Condtype> CLIENT_UP_CSF <Probcause>
        informationalStatus(1000) <Alarmtype>
        other (1) <Polarity> (2)
        "
	::= { pmc1002AlmsynthAlmPortEntry 17 }


pmc1002AlmClientFailPortn OBJECT-TYPE
	SYNTAX  EkiOnOff
	MAX-ACCESS read-only
	STATUS current
	DESCRIPTION
        "
        Client Access Fail :This OID indicates
        a failure on the Client port <Condtype>
        CLIENT_FAIL <Probcause> equipmentMalfunction
        (16) <Alarmtype> synthesisAlarm
        (12)  <Polarity> (2)
        "
	::= { pmc1002AlmsynthAlmPortEntry 13 }


pmc1002AlmClientSfpDdmAlmPortn OBJECT-TYPE
	SYNTAX  EkiOnOff
	MAX-ACCESS read-only
	STATUS current
	DESCRIPTION
        "
        Alarm On Client SFP+ DDM :This
        OID indicates an alarm is being
        received from the Client XFP DDM
         <Help>  This alarm indicates if
        a DDM Alarm has been detected on
        the client transceiver <Condtype>
        CLIENT_SFP_DDM_ALM <Probcause>
         equipmentMalfunction (16) <Alarmtype>
        synthesisAlarm (12)  <Polarity>
        (2)
        "
	::= { pmc1002AlmsynthAlmPortEntry 11 }


pmc1002AlmClientSfpDdmWarningPortn OBJECT-TYPE
	SYNTAX  EkiOnOff
	MAX-ACCESS read-only
	STATUS current
	DESCRIPTION
        "
        Warning On Client SFP+ DDM :This
        OID indicates a warning is being
        received from the Client XFP DDM
         <Help>  This alarm indicates if
        a DDM Warning has been detected
        on the client transceiver <Condtype>
        CLIENT_SFP_DDM_WARNING <Probcause>
        equipmentMalfunction (16) <Alarmtype>
        synthesisAlarm (12)  <Polarity>
        (2)
        "
	::= { pmc1002AlmsynthAlmPortEntry 10 }


pmc1002AlmClientDwCaisPortn OBJECT-TYPE
	SYNTAX  EkiOnOff
	MAX-ACCESS read-only
	STATUS current
	DESCRIPTION
        "
        Client AIS Inserted :This OID
         indicates a CAIS has been inserted
        on the output client port.  <Help>
         This status indicates if a Client
        Alarm Indication Signal is currently
        inserted on the client interface
        <Condtype> CLIENT_DW_CAIS <Probcause>
        informationalStatus(1000) <Alarmtype>
        other (1) <Polarity> (2)
        "
	::= { pmc1002AlmsynthAlmPortEntry 9 }


pmc1002AlmClientLocalOosPortn OBJECT-TYPE
	SYNTAX  EkiOnOff
	MAX-ACCESS read-only
	STATUS current
	DESCRIPTION
        "
        Local Client Port In Service :This
        OID indicates that the local Client
        port is In Service (1) or Out of
        Service (2)  <Help>  This status
        indicates if the local client port
        is in service <Condtype> CLIENT_LOCAL_OOS
        <Probcause> informationalStatus(1000)
        <Alarmtype> other (1) <Polarity>
        (2)
        "
	::= { pmc1002AlmsynthAlmPortEntry 7 }


pmc1002AlmClientDwLsdPortn OBJECT-TYPE
	SYNTAX  EkiOnOff
	MAX-ACCESS read-only
	STATUS current
	DESCRIPTION
        "
        Client Optical Laser Shutdown
         :This OID indicates the Client
        XFP transmitter output is ON.
          <Help>  This status indicates
        if the client transceiver laser
        is ON or OFF <Condtype> CLIENT_DW_LSD
        <Probcause> other (1) <Alarmtype>
        equipmentAlarm (5) <Polarity> (2)
        "
	::= { pmc1002AlmsynthAlmPortEntry 6 }


pmc1002AlmClientHwFailPortn OBJECT-TYPE
	SYNTAX  EkiOnOff
	MAX-ACCESS read-only
	STATUS current
	DESCRIPTION
        "
        Client HW Fail :This OID indicates
        a failure on client port, most
         probably caused by a HW issue.
        <Condtype> CLIENT_HW_FAIL <Probcause>
        equipmentMalfunction (16) <Alarmtype>
        synthesisAlarm (12)  <Polarity>
        (2)
        "
	::= { pmc1002AlmsynthAlmPortEntry 5 }


pmc1002AlmClientDdmAbsentPortn OBJECT-TYPE
	SYNTAX  EkiOnOff
	MAX-ACCESS read-only
	STATUS current
	DESCRIPTION
        "
        DDM Supported On Client SFP+ :This
        OID indicates that the client optical
        interface (XFP or OTX) is not operational.
         <Help>  This status indicates
         if the client transceiver has
         been correctly initialized <Condtype>
        CLIENT_DDM_ABSENT <Probcause> equipmentMalfunction
        (16) <Alarmtype> equipmentAlarm
        (5) <Polarity> (2)
        "
	::= { pmc1002AlmsynthAlmPortEntry 3 }


pmc1002AlmClientSfpAbsentPortn OBJECT-TYPE
	SYNTAX  EkiOnOff
	MAX-ACCESS read-only
	STATUS current
	DESCRIPTION
        "
        Client Optical Module Absent :This
        OID indicates that the XFP module
        is not present in the client port.
         <Help>  This alarm indicates if
        the client transceiver is present.
        <Condtype> CLIENT_SFP_ABSENT <Probcause>
        inputOutputDeviceError (24) <Alarmtype>
        equipmentAlarm (5) <Polarity> (2)
        <Event> ObjectCDINV
        "
	::= { pmc1002AlmsynthAlmPortEntry 2 }


--- *********************************************************
---     TABLE for the pmc1002AlmclientAccessioAlm articles
--- *********************************************************

pmc1002AlmclientAccessioAlmTable OBJECT-TYPE
	SYNTAX  SEQUENCE OF Pmc1002AlmclientAccessioAlmEntry
	MAX-ACCESS not-accessible
	STATUS current
	DESCRIPTION
        "
        List of pmc1002AlmclientAccessioAlm
        Article
        "
	::= { pmc1002AlmClientCrit 16 }


pmc1002AlmclientAccessioAlmEntry OBJECT-TYPE
	SYNTAX Pmc1002AlmclientAccessioAlmEntry
	MAX-ACCESS not-accessible
	STATUS current
	DESCRIPTION
        "
        Row definition for the pmc1002AlmclientAccessioAlm
        table
        "
	INDEX   { pmc1002AlmclientAccessioAlmIndex }
	::= { pmc1002AlmclientAccessioAlmTable 1 }


Pmc1002AlmclientAccessioAlmEntry ::=
	SEQUENCE {
	pmc1002AlmclientAccessioAlmIndex
		INTEGER,
	pmc1002AlmClientUpLosPortn
		EkiOnOff,
	pmc1002AlmClientDwLasFailPortn
		EkiOnOff
	}


pmc1002AlmclientAccessioAlmIndex OBJECT-TYPE
	SYNTAX  INTEGER(0..128)
	MAX-ACCESS  read-only
	STATUS current
	DESCRIPTION
        "
        Index definition for the pmc1002AlmclientAccessioAlm
        table
        "
	::= { pmc1002AlmclientAccessioAlmEntry 1 }


pmc1002AlmClientUpLosPortn OBJECT-TYPE
	SYNTAX  EkiOnOff
	MAX-ACCESS read-only
	STATUS current
	DESCRIPTION
        "
        Client Input Loss Of Signal :This
        OID indicates that no signal is
        present on the XFP of the client
        port  <Help>  This alarm indicates
        if an optical signal is detected
        on the client transceiver input
        <Condtype> CLIENT_UP_LOS <Probcause>
        receiveFailure (41) <Alarmtype>
        physicalViolation (9) <Polarity>
        (2)
        "
	::= { pmc1002AlmclientAccessioAlmEntry 5 }


pmc1002AlmClientDwLasFailPortn OBJECT-TYPE
	SYNTAX  EkiOnOff
	MAX-ACCESS read-only
	STATUS current
	DESCRIPTION
        "
        Client XFP Tx Failed :This OID
        indicates that the transmitter
         fails for the XFP plugged into
        the client port (this alarm reports
        the transmitter failure alarm generated
        by the XFPs) <Condtype> CLIENT_DW_LAS_FAIL
        <Probcause> transmitterFailure
         (56) <Alarmtype> equipmentAlarm
        (5) <Polarity> (2)
        "
	::= { pmc1002AlmclientAccessioAlmEntry 2 }


--- *********************************************************
---     TABLE for the pmc1002AlmclientXfpAlarm1 articles
--- *********************************************************

pmc1002AlmclientXfpAlarm1Table OBJECT-TYPE
	SYNTAX  SEQUENCE OF Pmc1002AlmclientXfpAlarm1Entry
	MAX-ACCESS not-accessible
	STATUS current
	DESCRIPTION
        "
        List of pmc1002AlmclientXfpAlarm1
        Article
        "
	::= { pmc1002AlmClientUrg 32 }


pmc1002AlmclientXfpAlarm1Entry OBJECT-TYPE
	SYNTAX Pmc1002AlmclientXfpAlarm1Entry
	MAX-ACCESS not-accessible
	STATUS current
	DESCRIPTION
        "
        Row definition for the pmc1002AlmclientXfpAlarm1
        table
        "
	INDEX   { pmc1002AlmclientXfpAlarm1Index }
	::= { pmc1002AlmclientXfpAlarm1Table 1 }


Pmc1002AlmclientXfpAlarm1Entry ::=
	SEQUENCE {
	pmc1002AlmclientXfpAlarm1Index
		INTEGER,
	pmc1002AlmClientRxPowerHighAlarmPortn
		EkiOnOff,
	pmc1002AlmClientRxPowerLowAlarmPortn
		EkiOnOff,
	pmc1002AlmClientTempHighAlarmPortn
		EkiOnOff,
	pmc1002AlmClientTempLowAlarmPortn
		EkiOnOff,
	pmc1002AlmClientTxBiasHighAlarmPortn
		EkiOnOff,
	pmc1002AlmClientTxBiasLowAlarmPortn
		EkiOnOff,
	pmc1002AlmClientTxPowerHighAlarmPortn
		EkiOnOff,
	pmc1002AlmClientTxPowerLowAlarmPortn
		EkiOnOff
	}


pmc1002AlmclientXfpAlarm1Index OBJECT-TYPE
	SYNTAX  INTEGER(0..128)
	MAX-ACCESS  read-only
	STATUS current
	DESCRIPTION
        "
        Index definition for the pmc1002AlmclientXfpAlarm1
        table
        "
	::= { pmc1002AlmclientXfpAlarm1Entry 1 }


pmc1002AlmClientRxPowerHighAlarmPortn OBJECT-TYPE
	SYNTAX  EkiOnOff
	MAX-ACCESS read-only
	STATUS current
	DESCRIPTION
        "
        Client Optical Rx Power High :Alarm
        indicating that the XFP received
        optical power is higher than the
        threshold value written in the
         XFP EEPROM <Condtype> CLIENT_RX_POWER_HIGH_ALARM
        <Probcause> receiveFailure (41)
        <Alarmtype> equipmentAlarm (5)
         <Polarity> (2)
        "
	::= { pmc1002AlmclientXfpAlarm1Entry 17 }


pmc1002AlmClientRxPowerLowAlarmPortn OBJECT-TYPE
	SYNTAX  EkiOnOff
	MAX-ACCESS read-only
	STATUS current
	DESCRIPTION
        "
        Client Optical Rx Power Low :Alarm
        indicating that the XFP received
        optical power is lower than the
        threshold value written in the
         XFP EEPROM  <Condtype> CLIENT_RX_POWER_LOW_ALARM
        <Probcause> receiveFailure (41)
        <Alarmtype> equipmentAlarm (5)
         <Polarity> (2)
        "
	::= { pmc1002AlmclientXfpAlarm1Entry 16 }


pmc1002AlmClientTempHighAlarmPortn OBJECT-TYPE
	SYNTAX  EkiOnOff
	MAX-ACCESS read-only
	STATUS current
	DESCRIPTION
        "
        Client Transceiver Temp High :Alarm
        indicating that the XFP/OTX temperature
        is higher than the threshold value
        written in the XFP EEPROM <Condtype>
        CLIENT_TEMP_HIGH_ALARM <Probcause>
        temperatureUnacceptable (51) <Alarmtype>
        equipmentAlarm (5) <Polarity> (2)
        "
	::= { pmc1002AlmclientXfpAlarm1Entry 9 }


pmc1002AlmClientTempLowAlarmPortn OBJECT-TYPE
	SYNTAX  EkiOnOff
	MAX-ACCESS read-only
	STATUS current
	DESCRIPTION
        "
        Client Transceiver Temp Low :Alarm
        indicating that the XFP/OTX temperature
        is lower than the threshold value
        written in the XFP/OTX EEPROM <Condtype>
        CLIENT_TEMP_LOW_ALARM <Probcause>
        temperatureUnacceptable (51) <Alarmtype>
        equipmentAlarm (5) <Polarity> (2)
        "
	::= { pmc1002AlmclientXfpAlarm1Entry 8 }


pmc1002AlmClientTxBiasHighAlarmPortn OBJECT-TYPE
	SYNTAX  EkiOnOff
	MAX-ACCESS read-only
	STATUS current
	DESCRIPTION
        "
        Client Transceiver Bias High :Alarm
        indicating that the XFP/OTX transmitter
        laser bias current is higher than
        the threshold value written in
         the XFP EEPROM <Condtype> CLIENT_TX_BIAS_HIGH_ALARM
        <Probcause> transmitterFailure
         (56) <Alarmtype> equipmentAlarm
        (5) <Polarity> (2)
        "
	::= { pmc1002AlmclientXfpAlarm1Entry 5 }


pmc1002AlmClientTxBiasLowAlarmPortn OBJECT-TYPE
	SYNTAX  EkiOnOff
	MAX-ACCESS read-only
	STATUS current
	DESCRIPTION
        "
        Client Transceiver Bias Low :Alarm
        indicating that the XFP/OTX transmitter
        laser bias current is lower than
        the threshold value written in
         the XFP/OTX EEPROM <Condtype>
         CLIENT_TX_BIAS_LOW_ALARM <Probcause>
        transmitterFailure (56) <Alarmtype>
        equipmentAlarm (5) <Polarity> (2)
        "
	::= { pmc1002AlmclientXfpAlarm1Entry 4 }


pmc1002AlmClientTxPowerHighAlarmPortn OBJECT-TYPE
	SYNTAX  EkiOnOff
	MAX-ACCESS read-only
	STATUS current
	DESCRIPTION
        "
        Client Optical Tx Power High :Alarm
        indicating that the XFP/OTX transmitter
        transmitter output power is higher
        than the threshold value written
        in the XFP EEPROM <Condtype> CLIENT_TX_POWER_HIGH_ALARM
        <Probcause> transmitterFailure
         (56) <Alarmtype> equipmentAlarm
        (5) <Polarity> (2)
        "
	::= { pmc1002AlmclientXfpAlarm1Entry 3 }


pmc1002AlmClientTxPowerLowAlarmPortn OBJECT-TYPE
	SYNTAX  EkiOnOff
	MAX-ACCESS read-only
	STATUS current
	DESCRIPTION
        "
        Client Optical Tx Power Low :Alarm
        indicating that the XFP/OTX transmitter
        transmitter output power is lower
        than the threshold value written
        in the XFP/OTX EEPROM <Condtype>
        CLIENT_TX_POWER_LOW_ALARM <Probcause>
        transmitterFailure (56) <Alarmtype>
        equipmentAlarm (5) <Polarity> (2)
        "
	::= { pmc1002AlmclientXfpAlarm1Entry 2 }


--- *********************************************************
---     TABLE for the pmc1002AlmclientXfpAlarm2 articles
--- *********************************************************

pmc1002AlmclientXfpAlarm2Table OBJECT-TYPE
	SYNTAX  SEQUENCE OF Pmc1002AlmclientXfpAlarm2Entry
	MAX-ACCESS not-accessible
	STATUS current
	DESCRIPTION
        "
        List of pmc1002AlmclientXfpAlarm2
        Article
        "
	::= { pmc1002AlmClientCrit 40 }


pmc1002AlmclientXfpAlarm2Entry OBJECT-TYPE
	SYNTAX Pmc1002AlmclientXfpAlarm2Entry
	MAX-ACCESS not-accessible
	STATUS current
	DESCRIPTION
        "
        Row definition for the pmc1002AlmclientXfpAlarm2
        table
        "
	INDEX   { pmc1002AlmclientXfpAlarm2Index }
	::= { pmc1002AlmclientXfpAlarm2Table 1 }


Pmc1002AlmclientXfpAlarm2Entry ::=
	SEQUENCE {
	pmc1002AlmclientXfpAlarm2Index
		INTEGER,
	pmc1002AlmClientApdSupplyFaultPortn
		EkiOnOff,
	pmc1002AlmClientTecFaultPortn
		EkiOnOff,
	pmc1002AlmClientWavelengthUnlockedPortn
		EkiOnOff,
	pmc1002AlmClientTxNrPortn
		EkiOnOff,
	pmc1002AlmClientTxFaultPortn
		EkiOnOff,
	pmc1002AlmClientTxCdrNotLockedPortn
		EkiOnOff,
	pmc1002AlmClientRxNrPortn
		EkiOnOff,
	pmc1002AlmClientRxCdrNotLockedPortn
		EkiOnOff,
	pmc1002AlmClientModNrPortn
		EkiOnOff
	}


pmc1002AlmclientXfpAlarm2Index OBJECT-TYPE
	SYNTAX  INTEGER(0..128)
	MAX-ACCESS  read-only
	STATUS current
	DESCRIPTION
        "
        Index definition for the pmc1002AlmclientXfpAlarm2
        table
        "
	::= { pmc1002AlmclientXfpAlarm2Entry 1 }


pmc1002AlmClientApdSupplyFaultPortn OBJECT-TYPE
	SYNTAX  EkiOnOff
	MAX-ACCESS read-only
	STATUS current
	DESCRIPTION
        "
        Client Rx Photodiode Power Failed
        :This OID indicates a failure on
        the APD power supply  <Help>  This
        alarm indicates if the APD power
        supply is in fail condition <Condtype>
        CLIENT_APD_SUPPLY_FAULT <Probcause>
        receiverFailure (42) <Alarmtype>
        equipmentAlarm (5) <Polarity> (2)
        "
	::= { pmc1002AlmclientXfpAlarm2Entry 17 }


pmc1002AlmClientTecFaultPortn OBJECT-TYPE
	SYNTAX  EkiOnOff
	MAX-ACCESS read-only
	STATUS current
	DESCRIPTION
        "
        Client Optical Tx Temp Regul.
         Failed :This OID indicates a failure
        on the TEC module  <Help>  This
        alarm indicates if the TEC of the
        Client transceiver is in fail condition
        <Condtype> CLIENT_TEC_FAULT <Probcause>
        transmitterFailure (56) <Alarmtype>
        equipmentAlarm (5) <Polarity> (2)
        "
	::= { pmc1002AlmclientXfpAlarm2Entry 16 }


pmc1002AlmClientWavelengthUnlockedPortn OBJECT-TYPE
	SYNTAX  EkiOnOff
	MAX-ACCESS read-only
	STATUS current
	DESCRIPTION
        "
        Client Optical Tx Wavelength Unlocked
        :This OID indicates that the wavelength
        error is exceeding the manufacturer
        tolerance  <Help>  This alarm indicates
        if the wavelenght of the Client
        transceiver is locked <Condtype>
        CLIENT_WAVELENGTH_UNLOCKED <Probcause>
        transmitterFailure (56) <Alarmtype>
        equipmentAlarm (5) <Polarity> (2)
        "
	::= { pmc1002AlmclientXfpAlarm2Entry 15 }


pmc1002AlmClientTxNrPortn OBJECT-TYPE
	SYNTAX  EkiOnOff
	MAX-ACCESS read-only
	STATUS current
	DESCRIPTION
        "
        Client Optical Tx Not Ready :This
        OID indicates a condition has arisen
        leading to invalid data on the
         transmitting side  <Help>  This
        alarm indicates if the Tx part
         of the Client transceiver is ready
        <Condtype> CLIENT_TX_NR <Probcause>
        transmitterFailure (56) <Alarmtype>
        equipmentAlarm (5) <Polarity> (2)
        "
	::= { pmc1002AlmclientXfpAlarm2Entry 9 }


pmc1002AlmClientTxFaultPortn OBJECT-TYPE
	SYNTAX  EkiOnOff
	MAX-ACCESS read-only
	STATUS current
	DESCRIPTION
        "
        Client Optical Tx Failure :This
        OID indicates a fault condition
        on the laser detected by the safety
        syste  <Help>  This alarm indicates
        if the laser of the Client transceiver
        is in fail condition <Condtype>
        CLIENT_TX_FAULT <Probcause> transmitterFailure
        (56) <Alarmtype> equipmentAlarm
        (5) <Polarity> (2)
        "
	::= { pmc1002AlmclientXfpAlarm2Entry 8 }


pmc1002AlmClientTxCdrNotLockedPortn OBJECT-TYPE
	SYNTAX  EkiOnOff
	MAX-ACCESS read-only
	STATUS current
	DESCRIPTION
        "
        Client Optical Tx CDR Unlocked
        :This OID indicates a loss of lock
        on the transmitting side CDR has
        been detected.  <Help>  This alarm
        indicates if the Tx CDR is locked
        in the Client transceiver <Condtype>
        CLIENT_TX_CDR_NOT_LOCKED1 <Probcause>
        transmitterFailure (56) <Alarmtype>
        equipmentAlarm (5) <Polarity> (2)
        "
	::= { pmc1002AlmclientXfpAlarm2Entry 7 }


pmc1002AlmClientRxNrPortn OBJECT-TYPE
	SYNTAX  EkiOnOff
	MAX-ACCESS read-only
	STATUS current
	DESCRIPTION
        "
        Client Optical Rx Not Ready :This
        OID indicates that a condition
         has arisen leading to invalid
         data on the receiving side.  <Help>
         This alarm indicates if the Rx
        part of the Client transceiver
         is ready <Condtype> CLIENT_RX_NR
        <Probcause> receiveFailure (41)
        <Alarmtype> equipmentAlarm (5)
         <Polarity> (2)
        "
	::= { pmc1002AlmclientXfpAlarm2Entry 6 }


pmc1002AlmClientRxCdrNotLockedPortn OBJECT-TYPE
	SYNTAX  EkiOnOff
	MAX-ACCESS read-only
	STATUS current
	DESCRIPTION
        "
        Client Optical Rx CDR Unlocked
        :This OID indicates that a loss
        of lock on the receiving side CDR
        has been detected  <Help>  This
        alarm indicates if the Rx CDR is
        locked in the Client transceiver
        <Condtype> CLIENT_RX_CDR_NOT_LOCKED1
        <Probcause> receiveFailure (41)
        <Alarmtype> equipmentAlarm (5)
         <Polarity> (2)
        "
	::= { pmc1002AlmclientXfpAlarm2Entry 4 }


pmc1002AlmClientModNrPortn OBJECT-TYPE
	SYNTAX  EkiOnOff
	MAX-ACCESS read-only
	STATUS current
	DESCRIPTION
        "
        Client Optical Module Not Ready
        :This OID indicates that the module
        is unable to determine correct
         data.  <Help>  This alarm indicates
        if the Client transceiver is ready
        <Condtype> CLIENT_MOD_NR <Probcause>
        receiveFailure (41) <Alarmtype>
        equipmentAlarm (5) <Polarity> (2)
        "
	::= { pmc1002AlmclientXfpAlarm2Entry 3 }


--- *********************************************************
---     TABLE for the pmc1002AlmclientXfpWarnings articles
--- *********************************************************

pmc1002AlmclientXfpWarningsTable OBJECT-TYPE
	SYNTAX  SEQUENCE OF Pmc1002AlmclientXfpWarningsEntry
	MAX-ACCESS not-accessible
	STATUS current
	DESCRIPTION
        "
        List of pmc1002AlmclientXfpWarnings
        Article
        "
	::= { pmc1002AlmClientNurg 48 }


pmc1002AlmclientXfpWarningsEntry OBJECT-TYPE
	SYNTAX Pmc1002AlmclientXfpWarningsEntry
	MAX-ACCESS not-accessible
	STATUS current
	DESCRIPTION
        "
        Row definition for the pmc1002AlmclientXfpWarnings
        table
        "
	INDEX   { pmc1002AlmclientXfpWarningsIndex }
	::= { pmc1002AlmclientXfpWarningsTable 1 }


Pmc1002AlmclientXfpWarningsEntry ::=
	SEQUENCE {
	pmc1002AlmclientXfpWarningsIndex
		INTEGER,
	pmc1002AlmClientRxPowerHighWarningPortn
		EkiOnOff,
	pmc1002AlmClientRxPowerLowWarningPortn
		EkiOnOff,
	pmc1002AlmClientTempHighWarningPortn
		EkiOnOff,
	pmc1002AlmClientTempLowWarningPortn
		EkiOnOff,
	pmc1002AlmClientTxBiasHighWarningPortn
		EkiOnOff,
	pmc1002AlmClientTxBiasLowWarningPortn
		EkiOnOff,
	pmc1002AlmClientTxPowerHighWarningPortn
		EkiOnOff,
	pmc1002AlmClientTxPowerLowWarningPortn
		EkiOnOff
	}


pmc1002AlmclientXfpWarningsIndex OBJECT-TYPE
	SYNTAX  INTEGER(0..128)
	MAX-ACCESS  read-only
	STATUS current
	DESCRIPTION
        "
        Index definition for the pmc1002AlmclientXfpWarnings
        table
        "
	::= { pmc1002AlmclientXfpWarningsEntry 1 }


pmc1002AlmClientRxPowerHighWarningPortn OBJECT-TYPE
	SYNTAX  EkiOnOff
	MAX-ACCESS read-only
	STATUS current
	DESCRIPTION
        "
        Client Optical Rx Pwr High Warning
        :Warning indicating that the XFP
        received optical power is higher
        than the threshold value written
        in the XFP EEPROM <Condtype> CLIENT_RX_POWER_HIGH_WARNING
        <Probcause> receiveFailure (41)
        <Alarmtype> equipmentAlarm (5)
         <Polarity> (2)
        "
	::= { pmc1002AlmclientXfpWarningsEntry 17 }


pmc1002AlmClientRxPowerLowWarningPortn OBJECT-TYPE
	SYNTAX  EkiOnOff
	MAX-ACCESS read-only
	STATUS current
	DESCRIPTION
        "
        Client Optical Rx Pwr Low Warning
        :Warning indicating that the XFP
        received optical power is lower
        than the threshold value written
        in the XFP EEPROM  <Condtype> CLIENT_RX_POWER_LOW_WARNING
        <Probcause> receiveFailure (41)
        <Alarmtype> equipmentAlarm (5)
         <Polarity> (2)
        "
	::= { pmc1002AlmclientXfpWarningsEntry 16 }


pmc1002AlmClientTempHighWarningPortn OBJECT-TYPE
	SYNTAX  EkiOnOff
	MAX-ACCESS read-only
	STATUS current
	DESCRIPTION
        "
        Client Transceiver Temp High Warning
        :Warning indicating that the XFP/OTX
        temperature is higher than the
         threshold value written in the
        XFP EEPROM <Condtype> CLIENT_TEMP_HIGH_WARNING
        <Probcause> temperatureUnacceptable
        (51) <Alarmtype> equipmentAlarm
        (5) <Polarity> (2)
        "
	::= { pmc1002AlmclientXfpWarningsEntry 9 }


pmc1002AlmClientTempLowWarningPortn OBJECT-TYPE
	SYNTAX  EkiOnOff
	MAX-ACCESS read-only
	STATUS current
	DESCRIPTION
        "
        Client Transceiver Temp Low Warning
        :Warning indicating that the XFP/OTX
        temperature is lower than the threshold
        value written in the XFP/OTX EEPROM
        <Condtype> CLIENT_TEMP_LOW_WARNING
        <Probcause> temperatureUnacceptable
        (51) <Alarmtype> equipmentAlarm
        (5) <Polarity> (2)
        "
	::= { pmc1002AlmclientXfpWarningsEntry 8 }


pmc1002AlmClientTxBiasHighWarningPortn OBJECT-TYPE
	SYNTAX  EkiOnOff
	MAX-ACCESS read-only
	STATUS current
	DESCRIPTION
        "
        Client Transceiver Bias High Warning
        :Warning indicating that the XFP/OTX
        transmitter laser bias current
         is higher than the threshold value
        written in the XFP EEPROM <Condtype>
        CLIENT_TX_BIAS_HIGH_WARNING <Probcause>
        transmitterFailure (56) <Alarmtype>
        equipmentAlarm (5) <Polarity> (2)
        "
	::= { pmc1002AlmclientXfpWarningsEntry 5 }


pmc1002AlmClientTxBiasLowWarningPortn OBJECT-TYPE
	SYNTAX  EkiOnOff
	MAX-ACCESS read-only
	STATUS current
	DESCRIPTION
        "
        Client Transceiver Bias Low Warning
        :Warning indicating that the XFP/OTX
        transmitter laser bias current
         is lower than the threshold value
        written in the XFP/OTX EEPROM <Condtype>
        CLIENT_TX_BIAS_LOW_WARNING <Probcause>
        transmitterFailure (56) <Alarmtype>
        equipmentAlarm (5) <Polarity> (2)
        "
	::= { pmc1002AlmclientXfpWarningsEntry 4 }


pmc1002AlmClientTxPowerHighWarningPortn OBJECT-TYPE
	SYNTAX  EkiOnOff
	MAX-ACCESS read-only
	STATUS current
	DESCRIPTION
        "
        Client Optical Tx Pwr High Warning
        :Warning indicating that the XFP/OTX
        transmitter transmitter output
         power is higher than the threshold
        value written in the XFP EEPROM
        <Condtype> CLIENT_TX_POWER_HIGH_WARNING
        <Probcause> transmitterFailure
         (56) <Alarmtype> equipmentAlarm
        (5) <Polarity> (2)
        "
	::= { pmc1002AlmclientXfpWarningsEntry 3 }


pmc1002AlmClientTxPowerLowWarningPortn OBJECT-TYPE
	SYNTAX  EkiOnOff
	MAX-ACCESS read-only
	STATUS current
	DESCRIPTION
        "
        Client Optical Tx Pwr Low Warning
        :Warning indicating that the XFP/OTX
        transmitter transmitter output
         power is lower than the threshold
        value written in the XFP/OTX EEPROM
        <Condtype> CLIENT_TX_POWER_LOW_WARNING
        <Probcause> transmitterFailure
         (56) <Alarmtype> equipmentAlarm
        (5) <Polarity> (2)
        "
	::= { pmc1002AlmclientXfpWarningsEntry 2 }


--- *********************************************************
---     TABLE for the pmc1002AlmclientXfpSupplyAlarm articles
--- *********************************************************

pmc1002AlmclientXfpSupplyAlarmTable OBJECT-TYPE
	SYNTAX  SEQUENCE OF Pmc1002AlmclientXfpSupplyAlarmEntry
	MAX-ACCESS not-accessible
	STATUS current
	DESCRIPTION
        "
        List of pmc1002AlmclientXfpSupplyAlarm
        Article
        "
	::= { pmc1002AlmClientUrg 64 }


pmc1002AlmclientXfpSupplyAlarmEntry OBJECT-TYPE
	SYNTAX Pmc1002AlmclientXfpSupplyAlarmEntry
	MAX-ACCESS not-accessible
	STATUS current
	DESCRIPTION
        "
        Row definition for the pmc1002AlmclientXfpSupplyAlarm
        table
        "
	INDEX   { pmc1002AlmclientXfpSupplyAlarmIndex }
	::= { pmc1002AlmclientXfpSupplyAlarmTable 1 }


Pmc1002AlmclientXfpSupplyAlarmEntry ::=
	SEQUENCE {
	pmc1002AlmclientXfpSupplyAlarmIndex
		INTEGER,
	pmc1002AlmClientVcc5HighWarningPortn
		EkiOnOff,
	pmc1002AlmClientVcc5LowWarningPortn
		EkiOnOff,
	pmc1002AlmClientVcc3HighWarningPortn
		EkiOnOff,
	pmc1002AlmClientVcc3LowWarningPortn
		EkiOnOff,
	pmc1002AlmClientVcc2HighWarningPortn
		EkiOnOff,
	pmc1002AlmClientVcc2LowWarningPortn
		EkiOnOff,
	pmc1002AlmClientVee5HighWarningPortn
		EkiOnOff,
	pmc1002AlmClientVee5LowWarningPortn
		EkiOnOff,
	pmc1002AlmClientVcc5HighAlarmPortn
		EkiOnOff,
	pmc1002AlmClientVcc5LowAlarmPortn
		EkiOnOff,
	pmc1002AlmClientVcc3HighAlarmPortn
		EkiOnOff,
	pmc1002AlmClientVcc3LowAlarmPortn
		EkiOnOff,
	pmc1002AlmClientVcc2HighAlarmPortn
		EkiOnOff,
	pmc1002AlmClientVcc2LowAlarmPortn
		EkiOnOff,
	pmc1002AlmClientVee5HighAlarmPortn
		EkiOnOff,
	pmc1002AlmClientVee5LowAlarmPortn
		EkiOnOff
	}


pmc1002AlmclientXfpSupplyAlarmIndex OBJECT-TYPE
	SYNTAX  INTEGER(0..128)
	MAX-ACCESS  read-only
	STATUS current
	DESCRIPTION
        "
        Index definition for the pmc1002AlmclientXfpSupplyAlarm
        table
        "
	::= { pmc1002AlmclientXfpSupplyAlarmEntry 1 }


pmc1002AlmClientVcc5HighWarningPortn OBJECT-TYPE
	SYNTAX  EkiOnOff
	MAX-ACCESS read-only
	STATUS current
	DESCRIPTION
        "
        VCC5 Power Supply High Warning
        :Warning indicating the XFP/OTX
        VCC5 power supply is higher than
        the threshold written in the EEPROM
        <Condtype> CLIENT_VCC5_HIGH_WARNING
        <Probcause> powerProblem (36) <Alarmtype>
        equipmentAlarm (5) <Polarity> (2)
        "
	::= { pmc1002AlmclientXfpSupplyAlarmEntry 17 }


pmc1002AlmClientVcc5LowWarningPortn OBJECT-TYPE
	SYNTAX  EkiOnOff
	MAX-ACCESS read-only
	STATUS current
	DESCRIPTION
        "
        VCC5 Power Supply Low Warning
         :Warning indicating the XFP/OTX
        VCC5 power supply is lower than
        the threshold written in the EEPROM
        <Condtype> CLIENT_VCC5_LOW_WARNING
        <Probcause> powerProblem (36) <Alarmtype>
        equipmentAlarm (5) <Polarity> (2)
        "
	::= { pmc1002AlmclientXfpSupplyAlarmEntry 16 }


pmc1002AlmClientVcc3HighWarningPortn OBJECT-TYPE
	SYNTAX  EkiOnOff
	MAX-ACCESS read-only
	STATUS current
	DESCRIPTION
        "
        VCC3 Power Supply High Warning
        :Warning indicating the XFP/OTX
        VCC3 power supply is higher than
        the threshold written in the EEPROM
        <Condtype> CLIENT_VCC3_HIGH_WARNING
        <Probcause> powerProblem (36) <Alarmtype>
        equipmentAlarm (5) <Polarity> (2)
        "
	::= { pmc1002AlmclientXfpSupplyAlarmEntry 15 }


pmc1002AlmClientVcc3LowWarningPortn OBJECT-TYPE
	SYNTAX  EkiOnOff
	MAX-ACCESS read-only
	STATUS current
	DESCRIPTION
        "
        VCC3 Power Supply Low Warning
         :Warning indicating the XFP/OTX
        VCC3 power supply is lower than
        the threshold written in the EEPROM
        <Condtype> CLIENT_VCC3_LOW_WARNING
        <Probcause> powerProblem (36) <Alarmtype>
        equipmentAlarm (5) <Polarity> (2)
        "
	::= { pmc1002AlmclientXfpSupplyAlarmEntry 14 }


pmc1002AlmClientVcc2HighWarningPortn OBJECT-TYPE
	SYNTAX  EkiOnOff
	MAX-ACCESS read-only
	STATUS current
	DESCRIPTION
        "
        VCC2 Power Supply High Warning
        :Warning indicating the XFP/OTX
        VCC2 power supply is higher than
        the threshold written in the EEPROM
        <Condtype> CLIENT_VCC2_HIGH_WARNING
        <Probcause> powerProblem (36) <Alarmtype>
        equipmentAlarm (5) <Polarity> (2)
        "
	::= { pmc1002AlmclientXfpSupplyAlarmEntry 13 }


pmc1002AlmClientVcc2LowWarningPortn OBJECT-TYPE
	SYNTAX  EkiOnOff
	MAX-ACCESS read-only
	STATUS current
	DESCRIPTION
        "
        VCC2 Power Supply Low Warning
         :Warning indicating the XFP/OTX
        VCC2 power supply is lower than
        the threshold written in the EEPROM
        <Condtype> CLIENT_VCC2_LOW_WARNING
        <Probcause> powerProblem (36) <Alarmtype>
        equipmentAlarm (5) <Polarity> (2)
        "
	::= { pmc1002AlmclientXfpSupplyAlarmEntry 12 }


pmc1002AlmClientVee5HighWarningPortn OBJECT-TYPE
	SYNTAX  EkiOnOff
	MAX-ACCESS read-only
	STATUS current
	DESCRIPTION
        "
        VEE5 Power Supply High Warning
        :Warning indicating the XFP/OTX
        VEE5 power supply is higher than
        the threshold written in the EEPROM
        <Condtype> CLIENT_VEE5_HIGH_WARNING
        <Probcause> powerProblem (36) <Alarmtype>
        equipmentAlarm (5) <Polarity> (2)
        "
	::= { pmc1002AlmclientXfpSupplyAlarmEntry 11 }


pmc1002AlmClientVee5LowWarningPortn OBJECT-TYPE
	SYNTAX  EkiOnOff
	MAX-ACCESS read-only
	STATUS current
	DESCRIPTION
        "
        VEE5 Power Supply Low Warning
         :Warning indicating the XFP/OTX
        VEE5 power supply is lower than
        the threshold written in the EEPROM
        <Condtype> CLIENT_VEE5_LOW_WARNING
        <Probcause> powerProblem (36) <Alarmtype>
        equipmentAlarm (5) <Polarity> (2)
        "
	::= { pmc1002AlmclientXfpSupplyAlarmEntry 10 }


pmc1002AlmClientVcc5HighAlarmPortn OBJECT-TYPE
	SYNTAX  EkiOnOff
	MAX-ACCESS read-only
	STATUS current
	DESCRIPTION
        "
        VCC5 Power Supply High :Alarm
         indicating the XFP/OTX VCC5 power
        supply is higher than the threshold
        written in the EEPROM <Condtype>
        CLIENT_VCC5_HIGH_ALARM <Probcause>
        powerProblem (36) <Alarmtype> equipmentAlarm
        (5) <Polarity> (2)
        "
	::= { pmc1002AlmclientXfpSupplyAlarmEntry 9 }


pmc1002AlmClientVcc5LowAlarmPortn OBJECT-TYPE
	SYNTAX  EkiOnOff
	MAX-ACCESS read-only
	STATUS current
	DESCRIPTION
        "
        VCC5 Power Supply Low :Alarm indicating
        the XFP/OTX VCC5 power supply is
        lower than the threshold written
        in the EEPROM <Condtype> CLIENT_VCC5_LOW_ALARM
        <Probcause> powerProblem (36) <Alarmtype>
        equipmentAlarm (5) <Polarity> (2)
        "
	::= { pmc1002AlmclientXfpSupplyAlarmEntry 8 }


pmc1002AlmClientVcc3HighAlarmPortn OBJECT-TYPE
	SYNTAX  EkiOnOff
	MAX-ACCESS read-only
	STATUS current
	DESCRIPTION
        "
        VCC3 Power Supply High :Alarm
         indicating the XFP/OTX VCC3 power
        supply is higher than the threshold
        written in the EEPROM <Condtype>
        CLIENT_VCC3_HIGH_ALARM <Probcause>
        powerProblem (36) <Alarmtype> equipmentAlarm
        (5) <Polarity> (2)
        "
	::= { pmc1002AlmclientXfpSupplyAlarmEntry 7 }


pmc1002AlmClientVcc3LowAlarmPortn OBJECT-TYPE
	SYNTAX  EkiOnOff
	MAX-ACCESS read-only
	STATUS current
	DESCRIPTION
        "
        VCC3 Power Supply Low :Alarm indicating
        the XFP/OTX VCC3 power supply is
        lower than the threshold written
        in the EEPROM <Condtype> CLIENT_VCC3_LOW_ALARM
        <Probcause> powerProblem (36) <Alarmtype>
        equipmentAlarm (5) <Polarity> (2)
        "
	::= { pmc1002AlmclientXfpSupplyAlarmEntry 6 }


pmc1002AlmClientVcc2HighAlarmPortn OBJECT-TYPE
	SYNTAX  EkiOnOff
	MAX-ACCESS read-only
	STATUS current
	DESCRIPTION
        "
        VCC2 Power Supply High :Alarm
         indicating the XFP/OTX VCC2 power
        supply is higher than the threshold
        written in the EEPROM <Condtype>
        CLIENT_VCC2_HIGH_ALARM <Probcause>
        powerProblem (36) <Alarmtype> equipmentAlarm
        (5) <Polarity> (2)
        "
	::= { pmc1002AlmclientXfpSupplyAlarmEntry 5 }


pmc1002AlmClientVcc2LowAlarmPortn OBJECT-TYPE
	SYNTAX  EkiOnOff
	MAX-ACCESS read-only
	STATUS current
	DESCRIPTION
        "
        VCC2 Power Supply Low :Alarm indicating
        the XFP/OTX VCC2 power supply is
        lower than the threshold written
        in the EEPROM <Condtype> CLIENT_VCC2_LOW_ALARM
        <Probcause> powerProblem (36) <Alarmtype>
        equipmentAlarm (5) <Polarity> (2)
        "
	::= { pmc1002AlmclientXfpSupplyAlarmEntry 4 }


pmc1002AlmClientVee5HighAlarmPortn OBJECT-TYPE
	SYNTAX  EkiOnOff
	MAX-ACCESS read-only
	STATUS current
	DESCRIPTION
        "
        VEE5 Power Supply High :Alarm
         indicating the XFP/OTX VEE5 power
        supply is higher than the threshold
        written in the EEPROM <Condtype>
        CLIENT_VEE5_HIGH_ALARM <Probcause>
        powerProblem (36) <Alarmtype> equipmentAlarm
        (5) <Polarity> (2)
        "
	::= { pmc1002AlmclientXfpSupplyAlarmEntry 3 }


pmc1002AlmClientVee5LowAlarmPortn OBJECT-TYPE
	SYNTAX  EkiOnOff
	MAX-ACCESS read-only
	STATUS current
	DESCRIPTION
        "
        VEE5 Power Supply Low :Alarm indicating
        the XFP/OTX VEE5 power supply is
        lower than the threshold written
        in the EEPROM <Condtype> CLIENT_VEE5_LOW_ALARM
        <Probcause> powerProblem (36) <Alarmtype>
        equipmentAlarm (5) <Polarity> (2)
        "
	::= { pmc1002AlmclientXfpSupplyAlarmEntry 2 }


--- *********************************************************
---     TABLE for the pmc1002AlmclientMapperDeAlm articles
--- *********************************************************

pmc1002AlmclientMapperDeAlmTable OBJECT-TYPE
	SYNTAX  SEQUENCE OF Pmc1002AlmclientMapperDeAlmEntry
	MAX-ACCESS not-accessible
	STATUS current
	DESCRIPTION
        "
        List of pmc1002AlmclientMapperDeAlm
        Article
        "
	::= { pmc1002AlmClientCrit 72 }


pmc1002AlmclientMapperDeAlmEntry OBJECT-TYPE
	SYNTAX Pmc1002AlmclientMapperDeAlmEntry
	MAX-ACCESS not-accessible
	STATUS current
	DESCRIPTION
        "
        Row definition for the pmc1002AlmclientMapperDeAlm
        table
        "
	INDEX   { pmc1002AlmclientMapperDeAlmIndex }
	::= { pmc1002AlmclientMapperDeAlmTable 1 }


Pmc1002AlmclientMapperDeAlmEntry ::=
	SEQUENCE {
	pmc1002AlmclientMapperDeAlmIndex
		INTEGER,
	pmc1002AlmClientDwBufferOvlPortn
		EkiOnOff,
	pmc1002AlmClientDwCsfDetPortn
		EkiOnOff,
	pmc1002AlmClientUpBufferOvlPortn
		EkiOnOff,
	pmc1002AlmClientUpAccOosPortn
		EkiOnOff
	}


pmc1002AlmclientMapperDeAlmIndex OBJECT-TYPE
	SYNTAX  INTEGER(0..128)
	MAX-ACCESS  read-only
	STATUS current
	DESCRIPTION
        "
        Index definition for the pmc1002AlmclientMapperDeAlm
        table
        "
	::= { pmc1002AlmclientMapperDeAlmEntry 1 }


pmc1002AlmClientDwBufferOvlPortn OBJECT-TYPE
	SYNTAX  EkiOnOff
	MAX-ACCESS read-only
	STATUS current
	DESCRIPTION
        "
        Client Downstream Buffer Overload
        :This OID indicates that the de-mapper
        buffer for client port is in overload.
        <Condtype> CLIENT_DW_BUFFER_OVL
        <Probcause> equipmentMalfunction
        (16) <Alarmtype> equipmentAlarm
        (5) <Polarity> (2)
        "
	::= { pmc1002AlmclientMapperDeAlmEntry 15 }


pmc1002AlmClientDwCsfDetPortn OBJECT-TYPE
	SYNTAX  EkiOnOff
	MAX-ACCESS read-only
	STATUS current
	DESCRIPTION
        "
        Client Signal Fail Detected :This
        OID indicates that a CSF has been
        detected on client port in the
         downstream direction   <Help>
          This alarm indicates if a Client
        Signal Fail has been detected in
        the incoming line frame for this
        client port <Condtype> CLIENT_DW_CSF_DET
        <Probcause> receiveFailure (41)
        <Alarmtype> other (1) <Polarity>
        (2)
        "
	::= { pmc1002AlmclientMapperDeAlmEntry 12 }


pmc1002AlmClientUpBufferOvlPortn OBJECT-TYPE
	SYNTAX  EkiOnOff
	MAX-ACCESS read-only
	STATUS current
	DESCRIPTION
        "
        Client Upstream Buffer Overload
        :This OID indicates that the rate
        adaptation buffer for client port
        is in overload. <Condtype> CLIENT_UP_BUFFER_OVL
        <Probcause> receiveFailure (41)
        <Alarmtype> integrityViolation
         (7) <Polarity> (2)
        "
	::= { pmc1002AlmclientMapperDeAlmEntry 11 }


pmc1002AlmClientUpAccOosPortn OBJECT-TYPE
	SYNTAX  EkiOnOff
	MAX-ACCESS read-only
	STATUS current
	DESCRIPTION
        "
        Client Loss Of Synchronisation
        :This OID indicates the upstream
        client input port is in Loss of
        Synchronization  <Help>  This alarms
        indicates if the input client signal
        is correctly synchronized with
         the decoder <Condtype> CLIENT_UP_ACC_OOS
        <Probcause> receiveFailure (41)
        <Alarmtype> integrityViolation
         (7) <Polarity> (2)
        "
	::= { pmc1002AlmclientMapperDeAlmEntry 2 }


--- *********************************************************
---     TABLE for the pmc1002AlmdfrmAlm articles
--- *********************************************************

pmc1002AlmdfrmAlmTable OBJECT-TYPE
	SYNTAX  SEQUENCE OF Pmc1002AlmdfrmAlmEntry
	MAX-ACCESS not-accessible
	STATUS current
	DESCRIPTION
        "
        List of pmc1002AlmdfrmAlm Article
        "
	::= { pmc1002AlmLineCrit 128 }


pmc1002AlmdfrmAlmEntry OBJECT-TYPE
	SYNTAX Pmc1002AlmdfrmAlmEntry
	MAX-ACCESS not-accessible
	STATUS current
	DESCRIPTION
        "
        Row definition for the pmc1002AlmdfrmAlm
        table
        "
	INDEX   { pmc1002AlmdfrmAlmIndex }
	::= { pmc1002AlmdfrmAlmTable 1 }


Pmc1002AlmdfrmAlmEntry ::=
	SEQUENCE {
	pmc1002AlmdfrmAlmIndex
		INTEGER,
	pmc1002AlmLineFecFailPortn
		EkiOnOff,
	pmc1002AlmLineDwLofPortn
		EkiOnOff,
	pmc1002AlmLineDwOofPortn
		EkiOnOff,
	pmc1002AlmLineDwRdiDetPortn
		EkiOnOff,
	pmc1002AlmLineDwAisDetPortn
		EkiOnOff
	}


pmc1002AlmdfrmAlmIndex OBJECT-TYPE
	SYNTAX  INTEGER(0..128)
	MAX-ACCESS  read-only
	STATUS current
	DESCRIPTION
        "
        Index definition for the pmc1002AlmdfrmAlm
        table
        "
	::= { pmc1002AlmdfrmAlmEntry 1 }


pmc1002AlmLineFecFailPortn OBJECT-TYPE
	SYNTAX  EkiOnOff
	MAX-ACCESS read-only
	STATUS current
	DESCRIPTION
        "
        FEC Decoding Fail :This OID indicates
        that the FEC decoder is in an overcapacity
        mode and not able to correct errors
          <Help>  This alarm indicates
         if the FEC decoder is in an over
        capacity mode <Condtype> LINE_FEC_FAIL
        <Probcause> receiveFailure (41)
        <Alarmtype> equipmentAlarm (5)
         <Polarity> (2)
        "
	::= { pmc1002AlmdfrmAlmEntry 6 }


pmc1002AlmLineDwLofPortn OBJECT-TYPE
	SYNTAX  EkiOnOff
	MAX-ACCESS read-only
	STATUS current
	DESCRIPTION
        "
        SONET/SDH Line Loss Of Frame :This
        OID indicates that a Loss Of Frame
        has been detected on line input
        signal  <Help>  This alarm indicates
        if there is a Loss of Frame is
         detected on the line input signal
        <Condtype> LINE_DW_LOF <Probcause>
        receiveFailure (41) <Alarmtype>
        integrityViolation (7) <Polarity>
        (2)
        "
	::= { pmc1002AlmdfrmAlmEntry 5 }


pmc1002AlmLineDwOofPortn OBJECT-TYPE
	SYNTAX  EkiOnOff
	MAX-ACCESS read-only
	STATUS current
	DESCRIPTION
        "
        SONET/SDH Line Out Of Frame :This
        OID indicates that an Out Of Frame
        has been detected on line input
        signal  <Help>  This alarm indicates
        if a Loss Of Frame is detected
         on the line input signal <Condtype>
        LINE_DW_OOF <Probcause> receiveFailure
        (41) <Alarmtype> integrityViolation
        (7) <Polarity> (2)
        "
	::= { pmc1002AlmdfrmAlmEntry 4 }


pmc1002AlmLineDwRdiDetPortn OBJECT-TYPE
	SYNTAX  EkiOnOff
	MAX-ACCESS read-only
	STATUS current
	DESCRIPTION
        "
        MS-RDI/L-RDI Detected On Line
         Input :This OID indicates that
        an MS-RDI has been detected on
         line input signal  <Help>  This
        alarm indicates if there is a MS-RDI/L-RDI
        is detected on the line input signal
        <Condtype> LINE_DW_RDI_DET <Probcause>
        remoteNodeTransmissionError (43)
        <Alarmtype> other (1) <Polarity>
        (2)
        "
	::= { pmc1002AlmdfrmAlmEntry 3 }


pmc1002AlmLineDwAisDetPortn OBJECT-TYPE
	SYNTAX  EkiOnOff
	MAX-ACCESS read-only
	STATUS current
	DESCRIPTION
        "
        MS-AIS/L-AIS Detected On Line
         Input :This OID indicates that
        an MS-AIS has been detected on
         line input signal  <Help>  This
        alarm indicates if there is a MS-AIS/L-AIS
        is detected on the line input signal
        <Condtype> LINE_DW_AIS_DET <Probcause>
        receiveFailure (41) <Alarmtype>
        operationalViolation (8) <Polarity>
        (2)
        "
	::= { pmc1002AlmdfrmAlmEntry 2 }


--- *********************************************************
---     TABLE for the pmc1002AlmdfrmBer articles
--- *********************************************************

pmc1002AlmdfrmBerTable OBJECT-TYPE
	SYNTAX  SEQUENCE OF Pmc1002AlmdfrmBerEntry
	MAX-ACCESS not-accessible
	STATUS current
	DESCRIPTION
        "
        List of pmc1002AlmdfrmBer Article
        "
	::= { pmc1002AlmLineUrg 129 }


pmc1002AlmdfrmBerEntry OBJECT-TYPE
	SYNTAX Pmc1002AlmdfrmBerEntry
	MAX-ACCESS not-accessible
	STATUS current
	DESCRIPTION
        "
        Row definition for the pmc1002AlmdfrmBer
        table
        "
	INDEX   { pmc1002AlmdfrmBerIndex }
	::= { pmc1002AlmdfrmBerTable 1 }


Pmc1002AlmdfrmBerEntry ::=
	SEQUENCE {
	pmc1002AlmdfrmBerIndex
		INTEGER,
	pmc1002AlmLineDegradePortn
		EkiOnOff,
	pmc1002AlmLineSignalFailPortn
		EkiOnOff,
	pmc1002AlmLineSignalDegradePortn
		EkiOnOff
	}


pmc1002AlmdfrmBerIndex OBJECT-TYPE
	SYNTAX  INTEGER(0..128)
	MAX-ACCESS  read-only
	STATUS current
	DESCRIPTION
        "
        Index definition for the pmc1002AlmdfrmBer
        table
        "
	::= { pmc1002AlmdfrmBerEntry 1 }


pmc1002AlmLineDegradePortn OBJECT-TYPE
	SYNTAX  EkiOnOff
	MAX-ACCESS read-only
	STATUS current
	DESCRIPTION
        "
        Fixed Line Signal Degrade :This
        OID indicates that the line input
        signal is DEGRADE. The assetion
        hysteresis is fixed to 10-8 (assertion)
        and 10-9 (de-assertion) <Condtype>
        LINE_DEGRADE <Probcause> degradedSignal
        (13) <Alarmtype> qualityOfServiceAlarm
        (3) <Polarity> (2)
        "
	::= { pmc1002AlmdfrmBerEntry 6 }


pmc1002AlmLineSignalFailPortn OBJECT-TYPE
	SYNTAX  EkiOnOff
	MAX-ACCESS read-only
	STATUS current
	DESCRIPTION
        "
        Custom Line Signal Fail :This
         OID indicates that the line input
        signal is FAIL. The assertion hysteresis
        can be customized by the host <Condtype>
        LINE_SIGNAL_FAIL <Probcause> receiveFailure
        (41) <Alarmtype> integrityViolation
        (7) <Polarity> (2)
        "
	::= { pmc1002AlmdfrmBerEntry 3 }


pmc1002AlmLineSignalDegradePortn OBJECT-TYPE
	SYNTAX  EkiOnOff
	MAX-ACCESS read-only
	STATUS current
	DESCRIPTION
        "
        Custom Line Signal Degrade :This
        OID indicates that the line input
        signal is DEGRADE. The assertion
        hysteresis can customized by the
        host <Condtype> LINE_SIGNAL_DEGRADE
        <Probcause> degradedSignal (13)
        <Alarmtype> qualityOfServiceAlarm
        (3) <Polarity> (2)
        "
	::= { pmc1002AlmdfrmBerEntry 2 }


--- *********************************************************
---     TABLE for the pmc1002AlmlineSyncAlarms articles
--- *********************************************************

pmc1002AlmlineSyncAlarmsTable OBJECT-TYPE
	SYNTAX  SEQUENCE OF Pmc1002AlmlineSyncAlarmsEntry
	MAX-ACCESS not-accessible
	STATUS current
	DESCRIPTION
        "
        List of pmc1002AlmlineSyncAlarms
        Article
        "
	::= { pmc1002AlmLineCrit 133 }


pmc1002AlmlineSyncAlarmsEntry OBJECT-TYPE
	SYNTAX Pmc1002AlmlineSyncAlarmsEntry
	MAX-ACCESS not-accessible
	STATUS current
	DESCRIPTION
        "
        Row definition for the pmc1002AlmlineSyncAlarms
        table
        "
	INDEX   { pmc1002AlmlineSyncAlarmsIndex }
	::= { pmc1002AlmlineSyncAlarmsTable 1 }


Pmc1002AlmlineSyncAlarmsEntry ::=
	SEQUENCE {
	pmc1002AlmlineSyncAlarmsIndex
		INTEGER,
	pmc1002AlmLineDwLosPortn
		EkiOnOff,
	pmc1002AlmLineUpLockerrPortn
		EkiOnOff,
	pmc1002AlmLineDwLockerrPortn
		EkiOnOff
	}


pmc1002AlmlineSyncAlarmsIndex OBJECT-TYPE
	SYNTAX  INTEGER(0..128)
	MAX-ACCESS  read-only
	STATUS current
	DESCRIPTION
        "
        Index definition for the pmc1002AlmlineSyncAlarms
        table
        "
	::= { pmc1002AlmlineSyncAlarmsEntry 1 }


pmc1002AlmLineDwLosPortn OBJECT-TYPE
	SYNTAX  EkiOnOff
	MAX-ACCESS read-only
	STATUS current
	DESCRIPTION
        "
        Line Input Loss Of Signal :This
        OID indicates a loss of signal
         on the 10 Gb/s input.  <Help>
          This alarm indicates if an optical
        signal is detected on the line
         transceiver input <Condtype> LINE_DW_LOS
        <Probcause> receiveFailure (41)
        <Alarmtype> physicalViolation (9)
        <Polarity> (2)
        "
	::= { pmc1002AlmlineSyncAlarmsEntry 17 }


pmc1002AlmLineUpLockerrPortn OBJECT-TYPE
	SYNTAX  EkiOnOff
	MAX-ACCESS read-only
	STATUS current
	DESCRIPTION
        "
        Upstream Clock Lock Error :This
        OID indicates that the serializer
        output 10 Gb/s clock multiplier
        unit is not locked. <Condtype>
         LINE_UP_LOCKERR <Probcause> receiveFailure
        (41) <Alarmtype> equipmentAlarm
        (5) <Polarity> (2)
        "
	::= { pmc1002AlmlineSyncAlarmsEntry 14 }


pmc1002AlmLineDwLockerrPortn OBJECT-TYPE
	SYNTAX  EkiOnOff
	MAX-ACCESS read-only
	STATUS current
	DESCRIPTION
        "
        Downstream Clock Lock Error :This
        OID indicates that the deserializer
        input 10 Gb/s clock recovery is
        not locked. <Condtype> LINE_DW_LOCKERR
        <Probcause> receiveFailure (41)
        <Alarmtype> equipmentAlarm (5)
         <Polarity> (2)
        "
	::= { pmc1002AlmlineSyncAlarmsEntry 13 }


--- *****************************************************
---     LEAF for the modInitFailLevel2 article
--- *****************************************************
pmc1002AlmmodInitFailLevel2 OBJECT IDENTIFIER ::= { pmc1002AlmOtherUrg 194 }




pmc1002AlmSwInitFail OBJECT-TYPE
	  SYNTAX EkiOnOff
	  MAX-ACCESS read-only
	  STATUS current
	  DESCRIPTION
        "
        SW Init Fail :This OID indicates
        that the SW intialization has caused
        unknown intial conditions  <Help>
         This alarm indicates if the SW
        module is correctly initialized
        <Condtype> SW_INIT_FAIL <Probcause>
        softwareError (47) <Alarmtype>
         processingErrorAlarm (4) <Polarity>
        (2)
        "
	  ::= { pmc1002AlmmodInitFailLevel2 5 }



pmc1002AlmResetHwInitFail OBJECT-TYPE
	  SYNTAX EkiOnOff
	  MAX-ACCESS read-only
	  STATUS current
	  DESCRIPTION
        "
        Reset HW Init Fail :This OID indicates
        that the HW intialization has caused
        unknown intial conditions  <Help>
         This alarm indicates if the HW
        has been correctly initialized
         <Condtype> RESET_HW_INIT_FAIL
         <Probcause> softwareError (47)
        <Alarmtype> processingErrorAlarm
        (4) <Polarity> (2)
        "
	  ::= { pmc1002AlmmodInitFailLevel2 4 }



pmc1002AlmBootUndone OBJECT-TYPE
	  SYNTAX EkiOnOff
	  MAX-ACCESS read-only
	  STATUS current
	  DESCRIPTION
        "
        Boot Undone :This OID indicates
        that the boot has not been correctly
        achieved  <Help>  This alarm indicates
        if the module has correctly boot
        <Condtype> BOOT_UNDONE <Probcause>
        softwareError (47) <Alarmtype>
         processingErrorAlarm (4) <Polarity>
        (2)
        "
	  ::= { pmc1002AlmmodInitFailLevel2 3 }



pmc1002AlmNextColdBootForced OBJECT-TYPE
	  SYNTAX EkiOnOff
	  MAX-ACCESS read-only
	  STATUS current
	  DESCRIPTION
        "
        Next Cold Boot Forced :This OID
        indicates that the next Reset will
        be forced Cold  <Help>  This alarm
        indicates that the next reset of
        the module will be forced to cold
        reset <Condtype> NEXT_COLD_BOOT_FORCED
        <Probcause> informationalStatus(1000)
        <Alarmtype> other (1) <Polarity>
        (2)
        "
	  ::= { pmc1002AlmmodInitFailLevel2 2 }



pmc1002AlmLedFail OBJECT-TYPE
	  SYNTAX EkiOnOff
	  MAX-ACCESS read-only
	  STATUS current
	  DESCRIPTION
        "
        Led Fail :This OID indicates that
        Led register has not been correctly
        initalized  <Help>  This alarm
         indicates if the module LEDs are
        correctly initialized <Condtype>
        LED_FAIL <Probcause> softwareError
        (47) <Alarmtype> processingErrorAlarm
        (4) <Polarity> (2)
        "
	  ::= { pmc1002AlmmodInitFailLevel2 1 }



--- *****************************************************
---     LEAF for the modInitFailLevel3 article
--- *****************************************************
pmc1002AlmmodInitFailLevel3 OBJECT IDENTIFIER ::= { pmc1002AlmOtherUrg 195 }




pmc1002AlmClient1InitFail OBJECT-TYPE
	  SYNTAX EkiOnOff
	  MAX-ACCESS read-only
	  STATUS current
	  DESCRIPTION
        "
        Client1 Init Fail :This OID indicates
        that Client 1 registers subset
         has not been correctly initialized
         <Help>  This alarm indicates if
        the client port is correctly initialized
        <Condtype> CLIENT1_INIT_FAIL <Probcause>
        softwareError (47) <Alarmtype>
         processingErrorAlarm (4) <Polarity>
        (2)
        "
	  ::= { pmc1002AlmmodInitFailLevel3 9 }



pmc1002AlmLine1InitFail OBJECT-TYPE
	  SYNTAX EkiOnOff
	  MAX-ACCESS read-only
	  STATUS current
	  DESCRIPTION
        "
        Line1 Init Fail :This OID indicates
        that the Line registersvsubset
         has not been correctly initialized
         <Help>  This alarm indicates if
        the line port is correctly initialized
        <Condtype> LINE1_INIT_FAIL <Probcause>
        softwareError (47) <Alarmtype>
         processingErrorAlarm (4) <Polarity>
        (2)
        "
	  ::= { pmc1002AlmmodInitFailLevel3 7 }



pmc1002AlmXfp2InitFail OBJECT-TYPE
	  SYNTAX EkiOnOff
	  MAX-ACCESS read-only
	  STATUS current
	  DESCRIPTION
        "
        XFP2 Init Fail :This OID indicates
        that the XFP has not been correctly
        initialized  <Help>  This alarm
        indicates if the line transceiver
        2 is correctly initialized <Condtype>
        XFP2_INIT_FAIL <Probcause> softwareError
        (47) <Alarmtype> processingErrorAlarm
        (4) <Polarity> (2)
        "
	  ::= { pmc1002AlmmodInitFailLevel3 6 }



pmc1002AlmXfp1InitFail OBJECT-TYPE
	  SYNTAX EkiOnOff
	  MAX-ACCESS read-only
	  STATUS current
	  DESCRIPTION
        "
        XFP1 Init Fail :This OID indicates
        that the XFP has not been correctly
        initialized  <Help>  This alarm
        indicates if the line transceiver
        1 is correctly initialized <Condtype>
        XFP1_INIT_FAIL <Probcause> softwareError
        (47) <Alarmtype> processingErrorAlarm
        (4) <Polarity> (2)
        "
	  ::= { pmc1002AlmmodInitFailLevel3 5 }



pmc1002AlmInitModuleFail OBJECT-TYPE
	  SYNTAX EkiOnOff
	  MAX-ACCESS read-only
	  STATUS current
	  DESCRIPTION
        "
        Init Module Fail :This OID indicates
        that the Module has not been correctly
        initialized  <Help>  This alarm
        indicates if the SW module is correctly
        initialized <Condtype> INIT_MODULE_FAIL
        <Probcause> softwareError (47)
         <Alarmtype> processingErrorAlarm
        (4) <Polarity> (2)
        "
	  ::= { pmc1002AlmmodInitFailLevel3 3 }



pmc1002AlmObmTypeReadFail OBJECT-TYPE
	  SYNTAX EkiOnOff
	  MAX-ACCESS read-only
	  STATUS current
	  DESCRIPTION
        "
        OBM Type Read Fail :This OID indicates
        that OBM type has not been recognized
         <Help>  This alarm indicates if
        the OBM board has been correctly
        identified <Condtype> OBM_TYPE_READ_FAIL
        <Probcause> softwareError (47)
         <Alarmtype> processingErrorAlarm
        (4) <Polarity> (2)
        "
	  ::= { pmc1002AlmmodInitFailLevel3 2 }



pmc1002AlmGwIdentFail OBJECT-TYPE
	  SYNTAX EkiOnOff
	  MAX-ACCESS read-only
	  STATUS current
	  DESCRIPTION
        "
        GW Ident Fail :This OID indicates
        that GW identification has not
         been read  <Help>  This alarm
         indicates if the GW has been correctly
        identified <Condtype> GW_IDENT_FAIL
        <Probcause> softwareError (47)
         <Alarmtype> processingErrorAlarm
        (4) <Polarity> (2)
        "
	  ::= { pmc1002AlmmodInitFailLevel3 1 }



--- *********************************************************
---     TABLE for the pmc1002AlmlineXfp1Alarm articles
--- *********************************************************

pmc1002AlmlineXfp1AlarmTable OBJECT-TYPE
	SYNTAX  SEQUENCE OF Pmc1002AlmlineXfp1AlarmEntry
	MAX-ACCESS not-accessible
	STATUS current
	DESCRIPTION
        "
        List of pmc1002AlmlineXfp1Alarm
        Article
        "
	::= { pmc1002AlmLineUrg 208 }


pmc1002AlmlineXfp1AlarmEntry OBJECT-TYPE
	SYNTAX Pmc1002AlmlineXfp1AlarmEntry
	MAX-ACCESS not-accessible
	STATUS current
	DESCRIPTION
        "
        Row definition for the pmc1002AlmlineXfp1Alarm
        table
        "
	INDEX   { pmc1002AlmlineXfp1AlarmIndex }
	::= { pmc1002AlmlineXfp1AlarmTable 1 }


Pmc1002AlmlineXfp1AlarmEntry ::=
	SEQUENCE {
	pmc1002AlmlineXfp1AlarmIndex
		INTEGER,
	pmc1002AlmLineRxPowerHighAlarmPortn
		EkiOnOff,
	pmc1002AlmLineRxPowerLowAlarmPortn
		EkiOnOff,
	pmc1002AlmLineTempHighAlarmPortn
		EkiOnOff,
	pmc1002AlmLineTempLowAlarmPortn
		EkiOnOff,
	pmc1002AlmLineTxBiasHighAlarmPortn
		EkiOnOff,
	pmc1002AlmLineTxBiasLowAlarmPortn
		EkiOnOff,
	pmc1002AlmLineTxPowerHighAlarmPortn
		EkiOnOff,
	pmc1002AlmLineTxPowerLowAlarmPortn
		EkiOnOff
	}


pmc1002AlmlineXfp1AlarmIndex OBJECT-TYPE
	SYNTAX  INTEGER(0..128)
	MAX-ACCESS  read-only
	STATUS current
	DESCRIPTION
        "
        Index definition for the pmc1002AlmlineXfp1Alarm
        table
        "
	::= { pmc1002AlmlineXfp1AlarmEntry 1 }


pmc1002AlmLineRxPowerHighAlarmPortn OBJECT-TYPE
	SYNTAX  EkiOnOff
	MAX-ACCESS read-only
	STATUS current
	DESCRIPTION
        "
        Line Optical Rx Power High Alarm
        :Alarm indicating that the XFP
         received optical power is higher
        than the threshold value written
        in the XFP EEPROM <Condtype> LINE_RX_POWER_HIGH_ALARM
        <Probcause> receiveFailure (41)
        <Alarmtype> equipmentAlarm (5)
         <Polarity> (2)
        "
	::= { pmc1002AlmlineXfp1AlarmEntry 17 }


pmc1002AlmLineRxPowerLowAlarmPortn OBJECT-TYPE
	SYNTAX  EkiOnOff
	MAX-ACCESS read-only
	STATUS current
	DESCRIPTION
        "
        Line Optical Rx Power Low Alarm
        :Alarm indicating that the XFP
         received optical power is lower
        than the threshold value written
        in the XFP EEPROM  <Condtype> LINE_RX_POWER_LOW_ALARM
        <Probcause> receiveFailure (41)
        <Alarmtype> equipmentAlarm (5)
         <Polarity> (2)
        "
	::= { pmc1002AlmlineXfp1AlarmEntry 16 }


pmc1002AlmLineTempHighAlarmPortn OBJECT-TYPE
	SYNTAX  EkiOnOff
	MAX-ACCESS read-only
	STATUS current
	DESCRIPTION
        "
        Line Transceiver Temp High Alarm
        :Alarm indicating that the XFP/OTX
        temperature is higher than the
         threshold value written in the
        XFP EEPROM <Condtype> LINE_TEMP_HIGH_ALARM
        <Probcause> temperatureUnacceptable
        (51) <Alarmtype> equipmentAlarm
        (5) <Polarity> (2)
        "
	::= { pmc1002AlmlineXfp1AlarmEntry 9 }


pmc1002AlmLineTempLowAlarmPortn OBJECT-TYPE
	SYNTAX  EkiOnOff
	MAX-ACCESS read-only
	STATUS current
	DESCRIPTION
        "
        Line Transceiver Temp Low Alarm
        :Alarm indicating that the XFP/OTX
        temperature is lower than the threshold
        value written in the XFP/OTX EEPROM
        <Condtype> LINE_TEMP_LOW_ALARM
         <Probcause> temperatureUnacceptable
        (51) <Alarmtype> equipmentAlarm
        (5) <Polarity> (2)
        "
	::= { pmc1002AlmlineXfp1AlarmEntry 8 }


pmc1002AlmLineTxBiasHighAlarmPortn OBJECT-TYPE
	SYNTAX  EkiOnOff
	MAX-ACCESS read-only
	STATUS current
	DESCRIPTION
        "
        Line Transceiver Bias High Alarm
        :Alarm indicating that the XFP/OTX
        transmitter laser bias current
         is higher than the threshold value
        written in the XFP EEPROM <Condtype>
        LINE_TX_BIAS_HIGH_ALARM <Probcause>
        transmitterFailure (56) <Alarmtype>
        equipmentAlarm (5) <Polarity> (2)
        "
	::= { pmc1002AlmlineXfp1AlarmEntry 5 }


pmc1002AlmLineTxBiasLowAlarmPortn OBJECT-TYPE
	SYNTAX  EkiOnOff
	MAX-ACCESS read-only
	STATUS current
	DESCRIPTION
        "
        Line Transceiver Bias Low Alarm
        :Alarm indicating that the XFP/OTX
        transmitter laser bias current
         is lower than the threshold value
        written in the XFP/OTX EEPROM <Condtype>
        LINE_TX_BIAS_LOW_ALARM <Probcause>
        transmitterFailure (56) <Alarmtype>
        equipmentAlarm (5) <Polarity> (2)
        "
	::= { pmc1002AlmlineXfp1AlarmEntry 4 }


pmc1002AlmLineTxPowerHighAlarmPortn OBJECT-TYPE
	SYNTAX  EkiOnOff
	MAX-ACCESS read-only
	STATUS current
	DESCRIPTION
        "
        Line Optical Tx Power High Alarm
        :Alarm indicating that the XFP/OTX
        transmitter transmitter output
         power is higher than the threshold
        value written in the XFP EEPROM
        <Condtype> LINE_TX_POWER_HIGH_ALARM
        <Probcause> transmitterFailure
         (56) <Alarmtype> equipmentAlarm
        (5) <Polarity> (2)
        "
	::= { pmc1002AlmlineXfp1AlarmEntry 3 }


pmc1002AlmLineTxPowerLowAlarmPortn OBJECT-TYPE
	SYNTAX  EkiOnOff
	MAX-ACCESS read-only
	STATUS current
	DESCRIPTION
        "
        Line Optical Tx Power Low Alarm
        :Alarm indicating that the XFP/OTX
        transmitter transmitter output
         power is lower than the threshold
        value written in the XFP/OTX EEPROM
        <Condtype> LINE_TX_POWER_LOW_ALARM
        <Probcause> transmitterFailure
         (56) <Alarmtype> equipmentAlarm
        (5) <Polarity> (2)
        "
	::= { pmc1002AlmlineXfp1AlarmEntry 2 }


--- *********************************************************
---     TABLE for the pmc1002AlmlineXfp1Warnings articles
--- *********************************************************

pmc1002AlmlineXfp1WarningsTable OBJECT-TYPE
	SYNTAX  SEQUENCE OF Pmc1002AlmlineXfp1WarningsEntry
	MAX-ACCESS not-accessible
	STATUS current
	DESCRIPTION
        "
        List of pmc1002AlmlineXfp1Warnings
        Article
        "
	::= { pmc1002AlmLineNurg 209 }


pmc1002AlmlineXfp1WarningsEntry OBJECT-TYPE
	SYNTAX Pmc1002AlmlineXfp1WarningsEntry
	MAX-ACCESS not-accessible
	STATUS current
	DESCRIPTION
        "
        Row definition for the pmc1002AlmlineXfp1Warnings
        table
        "
	INDEX   { pmc1002AlmlineXfp1WarningsIndex }
	::= { pmc1002AlmlineXfp1WarningsTable 1 }


Pmc1002AlmlineXfp1WarningsEntry ::=
	SEQUENCE {
	pmc1002AlmlineXfp1WarningsIndex
		INTEGER,
	pmc1002AlmLineRxPowerHighWarningPortn
		EkiOnOff,
	pmc1002AlmLineRxPowerLowWarningPortn
		EkiOnOff,
	pmc1002AlmLineTempHighWarningPortn
		EkiOnOff,
	pmc1002AlmLineTempLowWarningPortn
		EkiOnOff,
	pmc1002AlmLineTxBiasHighWarningPortn
		EkiOnOff,
	pmc1002AlmLineTxBiasLowWarningPortn
		EkiOnOff,
	pmc1002AlmLineTxPowerHighWarningPortn
		EkiOnOff,
	pmc1002AlmLineTxPowerLowWarningPortn
		EkiOnOff
	}


pmc1002AlmlineXfp1WarningsIndex OBJECT-TYPE
	SYNTAX  INTEGER(0..128)
	MAX-ACCESS  read-only
	STATUS current
	DESCRIPTION
        "
        Index definition for the pmc1002AlmlineXfp1Warnings
        table
        "
	::= { pmc1002AlmlineXfp1WarningsEntry 1 }


pmc1002AlmLineRxPowerHighWarningPortn OBJECT-TYPE
	SYNTAX  EkiOnOff
	MAX-ACCESS read-only
	STATUS current
	DESCRIPTION
        "
        Line Optical Rx Power High Warning
        :Warning indicating that the XFP
        received optical power is higher
        than the threshold value written
        in the XFP EEPROM <Condtype> LINE_RX_POWER_HIGH_WARNING
        <Probcause> receiveFailure (41)
        <Alarmtype> equipmentAlarm (5)
         <Polarity> (2)
        "
	::= { pmc1002AlmlineXfp1WarningsEntry 17 }


pmc1002AlmLineRxPowerLowWarningPortn OBJECT-TYPE
	SYNTAX  EkiOnOff
	MAX-ACCESS read-only
	STATUS current
	DESCRIPTION
        "
        Line Optical Rx Power Low Warning
        :Warning indicating that the XFP
        received optical power is lower
        than the threshold value written
        in the XFP EEPROM  <Condtype> LINE_RX_POWER_LOW_WARNING
        <Probcause> receiveFailure (41)
        <Alarmtype> equipmentAlarm (5)
         <Polarity> (2)
        "
	::= { pmc1002AlmlineXfp1WarningsEntry 16 }


pmc1002AlmLineTempHighWarningPortn OBJECT-TYPE
	SYNTAX  EkiOnOff
	MAX-ACCESS read-only
	STATUS current
	DESCRIPTION
        "
        Line Transceiver Temp High Warning
        :Warning indicating that the XFP/OTX
        temperature is higher than the
         threshold value written in the
        XFP EEPROM <Condtype> LINE_TEMP_HIGH_WARNING
        <Probcause> temperatureUnacceptable
        (51) <Alarmtype> equipmentAlarm
        (5) <Polarity> (2)
        "
	::= { pmc1002AlmlineXfp1WarningsEntry 9 }


pmc1002AlmLineTempLowWarningPortn OBJECT-TYPE
	SYNTAX  EkiOnOff
	MAX-ACCESS read-only
	STATUS current
	DESCRIPTION
        "
        Line Transceiver Temp Low Warning
        :Warning indicating that the XFP/OTX
        temperature is lower than the threshold
        value written in the XFP/OTX EEPROM
        <Condtype> LINE_TEMP_LOW_WARNING
        <Probcause> temperatureUnacceptable
        (51) <Alarmtype> equipmentAlarm
        (5) <Polarity> (2)
        "
	::= { pmc1002AlmlineXfp1WarningsEntry 8 }


pmc1002AlmLineTxBiasHighWarningPortn OBJECT-TYPE
	SYNTAX  EkiOnOff
	MAX-ACCESS read-only
	STATUS current
	DESCRIPTION
        "
        Line Transceiver Bias High Warning
        :Warning indicating that the XFP/OTX
        transmitter laser bias current
         is higher than the threshold value
        written in the XFP EEPROM <Condtype>
        LINE_TX_BIAS_HIGH_WARNING <Probcause>
        transmitterFailure (56) <Alarmtype>
        equipmentAlarm (5) <Polarity> (2)
        "
	::= { pmc1002AlmlineXfp1WarningsEntry 5 }


pmc1002AlmLineTxBiasLowWarningPortn OBJECT-TYPE
	SYNTAX  EkiOnOff
	MAX-ACCESS read-only
	STATUS current
	DESCRIPTION
        "
        Line Transceiver Bias Low Warning
        :Warning indicating that the XFP/OTX
        transmitter laser bias current
         is lower than the threshold value
        written in the XFP/OTX EEPROM <Condtype>
        LINE_TX_BIAS_LOW_WARNING <Probcause>
        transmitterFailure (56) <Alarmtype>
        equipmentAlarm (5) <Polarity> (2)
        "
	::= { pmc1002AlmlineXfp1WarningsEntry 4 }


pmc1002AlmLineTxPowerHighWarningPortn OBJECT-TYPE
	SYNTAX  EkiOnOff
	MAX-ACCESS read-only
	STATUS current
	DESCRIPTION
        "
        Line Optical Tx Power High Warning
        :Warning indicating that the XFP/OTX
        transmitter transmitter output
         power is higher than the threshold
        value written in the XFP EEPROM
        <Condtype> LINE_TX_POWER_HIGH_WARNING
        <Probcause> transmitterFailure
         (56) <Alarmtype> equipmentAlarm
        (5) <Polarity> (2)
        "
	::= { pmc1002AlmlineXfp1WarningsEntry 3 }


pmc1002AlmLineTxPowerLowWarningPortn OBJECT-TYPE
	SYNTAX  EkiOnOff
	MAX-ACCESS read-only
	STATUS current
	DESCRIPTION
        "
        Line Optical Tx Power Low Warning
        :Warning indicating that the XFP/OTX
        transmitter transmitter output
         power is lower than the threshold
        value written in the XFP/OTX EEPROM
        <Condtype> LINE_TX_POWER_LOW_WARNING
        <Probcause> transmitterFailure
         (56) <Alarmtype> equipmentAlarm
        (5) <Polarity> (2)
        "
	::= { pmc1002AlmlineXfp1WarningsEntry 2 }


--- *********************************************************
---     TABLE for the pmc1002AlmlineXfp1Alarms articles
--- *********************************************************

pmc1002AlmlineXfp1AlarmsTable OBJECT-TYPE
	SYNTAX  SEQUENCE OF Pmc1002AlmlineXfp1AlarmsEntry
	MAX-ACCESS not-accessible
	STATUS current
	DESCRIPTION
        "
        List of pmc1002AlmlineXfp1Alarms
        Article
        "
	::= { pmc1002AlmLineCrit 211 }


pmc1002AlmlineXfp1AlarmsEntry OBJECT-TYPE
	SYNTAX Pmc1002AlmlineXfp1AlarmsEntry
	MAX-ACCESS not-accessible
	STATUS current
	DESCRIPTION
        "
        Row definition for the pmc1002AlmlineXfp1Alarms
        table
        "
	INDEX   { pmc1002AlmlineXfp1AlarmsIndex }
	::= { pmc1002AlmlineXfp1AlarmsTable 1 }


Pmc1002AlmlineXfp1AlarmsEntry ::=
	SEQUENCE {
	pmc1002AlmlineXfp1AlarmsIndex
		INTEGER,
	pmc1002AlmLineApdSupplyFaultPortn
		EkiOnOff,
	pmc1002AlmLineTecFaultPortn
		EkiOnOff,
	pmc1002AlmLineWavelengthUnlockedPortn
		EkiOnOff,
	pmc1002AlmLineChannelNotAcquiredPortn
		EkiOnOff,
	pmc1002AlmLineTxNrPortn
		EkiOnOff,
	pmc1002AlmLineTxFaultPortn
		EkiOnOff,
	pmc1002AlmLineTxCdrNotLockedPortn
		EkiOnOff,
	pmc1002AlmLineRxNrPortn
		EkiOnOff,
	pmc1002AlmLineRxCdrNotLockedPortn
		EkiOnOff,
	pmc1002AlmLineModNrPortn
		EkiOnOff
	}


pmc1002AlmlineXfp1AlarmsIndex OBJECT-TYPE
	SYNTAX  INTEGER(0..128)
	MAX-ACCESS  read-only
	STATUS current
	DESCRIPTION
        "
        Index definition for the pmc1002AlmlineXfp1Alarms
        table
        "
	::= { pmc1002AlmlineXfp1AlarmsEntry 1 }


pmc1002AlmLineApdSupplyFaultPortn OBJECT-TYPE
	SYNTAX  EkiOnOff
	MAX-ACCESS read-only
	STATUS current
	DESCRIPTION
        "
        Line Rx Photodiode Power Failed
        :This OID indicates a failure on
        the APD power supply  <Help>  This
        alarm indicates if the APD power
        supply is in fail condition <Condtype>
        LINE_APD_SUPPLY_FAULT <Probcause>
        receiverFailure (42) <Alarmtype>
        equipmentAlarm (5) <Polarity> (2)
        "
	::= { pmc1002AlmlineXfp1AlarmsEntry 17 }


pmc1002AlmLineTecFaultPortn OBJECT-TYPE
	SYNTAX  EkiOnOff
	MAX-ACCESS read-only
	STATUS current
	DESCRIPTION
        "
        Line Optical Tx Temp Regul. Failed
        :This OID indicates a failure on
        the TEC module  <Help>  This alarm
        indicates if the TEC of the line
        transceiver is in fail condition
        <Condtype> LINE_TEC_FAULT <Probcause>
        transmitterFailure (56) <Alarmtype>
        equipmentAlarm (5) <Polarity> (2)
        "
	::= { pmc1002AlmlineXfp1AlarmsEntry 16 }


pmc1002AlmLineWavelengthUnlockedPortn OBJECT-TYPE
	SYNTAX  EkiOnOff
	MAX-ACCESS read-only
	STATUS current
	DESCRIPTION
        "
        Line Optical Tx Wavelength Unlock
        :This OID indicates that the wavelength
        error is exceeding the manufacturer
        tolerance  <Help>  This alarm indicates
        if the wavelenght of the line transceiver
        is locked <Condtype> LINE_WAVELENGTH_UNLOCKED
        <Probcause> transmitterFailure
         (56) <Alarmtype> equipmentAlarm
        (5) <Polarity> (2)
        "
	::= { pmc1002AlmlineXfp1AlarmsEntry 15 }


pmc1002AlmLineChannelNotAcquiredPortn OBJECT-TYPE
	SYNTAX  EkiOnOff
	MAX-ACCESS read-only
	STATUS current
	DESCRIPTION
        "
        DWDM Channel Not Acquired :This
        OID indicates the transceiver didn't
        tune the DWDM Channel succesfully.
         <Help>  This status indicates
         the transceiver has not tuned
         the DWDM Channel succesfully.
         <Condtype> LINE_CHANNEL_NOT_ACQUIRED
        <Probcause> transmitterFailure
         (56) <Alarmtype> equipmentAlarm
        (5) <Polarity> (2)
        "
	::= { pmc1002AlmlineXfp1AlarmsEntry 11 }


pmc1002AlmLineTxNrPortn OBJECT-TYPE
	SYNTAX  EkiOnOff
	MAX-ACCESS read-only
	STATUS current
	DESCRIPTION
        "
        Line Optical Tx Not Ready :This
        OID indicates a condition has arisen
        leading to invalid data on the
         transmitting side  <Help>  This
        alarm indicates if the Tx part
         of the line transceiver is ready
        <Condtype> LINE_TX_NR <Probcause>
        transmitterFailure (56) <Alarmtype>
        equipmentAlarm (5) <Polarity> (2)
        "
	::= { pmc1002AlmlineXfp1AlarmsEntry 9 }


pmc1002AlmLineTxFaultPortn OBJECT-TYPE
	SYNTAX  EkiOnOff
	MAX-ACCESS read-only
	STATUS current
	DESCRIPTION
        "
        Line Optical Tx Failure :This
         OID indicates a fault condition
        on the laser detected by the safety
        syste  <Help>  This alarm indicates
        if the laser of the line transceiver
        is in fail condition <Condtype>
        LINE_TX_FAULT <Probcause> transmitterFailure
        (56) <Alarmtype> equipmentAlarm
        (5) <Polarity> (2)
        "
	::= { pmc1002AlmlineXfp1AlarmsEntry 8 }


pmc1002AlmLineTxCdrNotLockedPortn OBJECT-TYPE
	SYNTAX  EkiOnOff
	MAX-ACCESS read-only
	STATUS current
	DESCRIPTION
        "
        Line Optical Tx CDR Unlocked :This
        OID indicates a loss of lock on
        the transmitting side CDR has been
        detected.  <Help>  This alarm indicates
        if the Tx CDR is locked in the
         line transceiver <Condtype> LINE_TX_CDR_NOT_LOCKED1
        <Probcause> transmitterFailure
         (56) <Alarmtype> equipmentAlarm
        (5) <Polarity> (2)
        "
	::= { pmc1002AlmlineXfp1AlarmsEntry 7 }


pmc1002AlmLineRxNrPortn OBJECT-TYPE
	SYNTAX  EkiOnOff
	MAX-ACCESS read-only
	STATUS current
	DESCRIPTION
        "
        Line Optical Rx Not Ready :This
        OID indicates that a condition
         has arisen leading to invalid
         data on the receiving side.  <Help>
         This alarm indicates if the Rx
        part of the line transceiver is
        ready <Condtype> LINE_RX_NR <Probcause>
        receiveFailure (41) <Alarmtype>
        equipmentAlarm (5) <Polarity> (2)
        "
	::= { pmc1002AlmlineXfp1AlarmsEntry 6 }


pmc1002AlmLineRxCdrNotLockedPortn OBJECT-TYPE
	SYNTAX  EkiOnOff
	MAX-ACCESS read-only
	STATUS current
	DESCRIPTION
        "
        Line Optical Rx CDR Unlocked :This
        OID indicates that a loss of lock
        on the receiving side CDR has been
        detected  <Help>  This alarm indicates
        if the Rx CDR is locked in the
         line transceiver <Condtype> LINE_RX_CDR_NOT_LOCKED1
        <Probcause> receiveFailure (41)
        <Alarmtype> equipmentAlarm (5)
         <Polarity> (2)
        "
	::= { pmc1002AlmlineXfp1AlarmsEntry 4 }


pmc1002AlmLineModNrPortn OBJECT-TYPE
	SYNTAX  EkiOnOff
	MAX-ACCESS read-only
	STATUS current
	DESCRIPTION
        "
        Line Optical Module Not Ready
         :This OID indicates that the module
        is unable to determine correct
         data.  <Help>  This alarm indicates
        if the line transceiver is ready
        <Condtype> LINE_MOD_NR <Probcause>
        receiveFailure (41) <Alarmtype>
        equipmentAlarm (5) <Polarity> (2)
        "
	::= { pmc1002AlmlineXfp1AlarmsEntry 3 }


--- *********************************************************
---     TABLE for the pmc1002AlmlineXfp1SupplyAlarm articles
--- *********************************************************

pmc1002AlmlineXfp1SupplyAlarmTable OBJECT-TYPE
	SYNTAX  SEQUENCE OF Pmc1002AlmlineXfp1SupplyAlarmEntry
	MAX-ACCESS not-accessible
	STATUS current
	DESCRIPTION
        "
        List of pmc1002AlmlineXfp1SupplyAlarm
        Article
        "
	::= { pmc1002AlmLineUrg 212 }


pmc1002AlmlineXfp1SupplyAlarmEntry OBJECT-TYPE
	SYNTAX Pmc1002AlmlineXfp1SupplyAlarmEntry
	MAX-ACCESS not-accessible
	STATUS current
	DESCRIPTION
        "
        Row definition for the pmc1002AlmlineXfp1SupplyAlarm
        table
        "
	INDEX   { pmc1002AlmlineXfp1SupplyAlarmIndex }
	::= { pmc1002AlmlineXfp1SupplyAlarmTable 1 }


Pmc1002AlmlineXfp1SupplyAlarmEntry ::=
	SEQUENCE {
	pmc1002AlmlineXfp1SupplyAlarmIndex
		INTEGER,
	pmc1002AlmLineVcc5HighWarningPortn
		EkiOnOff,
	pmc1002AlmLineVcc5LowWarningPortn
		EkiOnOff,
	pmc1002AlmLineVcc3HighWarningPortn
		EkiOnOff,
	pmc1002AlmLineVcc3LowWarningPortn
		EkiOnOff,
	pmc1002AlmLineVcc2HighWarningPortn
		EkiOnOff,
	pmc1002AlmLineVcc2LowWarningPortn
		EkiOnOff,
	pmc1002AlmLineVee5HighWarningPortn
		EkiOnOff,
	pmc1002AlmLineVee5LowLineWarningPortn
		EkiOnOff,
	pmc1002AlmLineVcc5HighAlarmPortn
		EkiOnOff,
	pmc1002AlmLineVcc5LowAlarmPortn
		EkiOnOff,
	pmc1002AlmLineVcc3HighAlarmPortn
		EkiOnOff,
	pmc1002AlmLineVcc3LowAlarmPortn
		EkiOnOff,
	pmc1002AlmLineVcc2HighAlarmPortn
		EkiOnOff,
	pmc1002AlmLineVcc2LowAlarmPortn
		EkiOnOff,
	pmc1002AlmLineVee5HighAlarmPortn
		EkiOnOff,
	pmc1002AlmLineVee5LowAlarmPortn
		EkiOnOff
	}


pmc1002AlmlineXfp1SupplyAlarmIndex OBJECT-TYPE
	SYNTAX  INTEGER(0..128)
	MAX-ACCESS  read-only
	STATUS current
	DESCRIPTION
        "
        Index definition for the pmc1002AlmlineXfp1SupplyAlarm
        table
        "
	::= { pmc1002AlmlineXfp1SupplyAlarmEntry 1 }


pmc1002AlmLineVcc5HighWarningPortn OBJECT-TYPE
	SYNTAX  EkiOnOff
	MAX-ACCESS read-only
	STATUS current
	DESCRIPTION
        "
        VCC5 Power Supply High Warning
        :Warning indicating the XFP/OTX
        VCC5 power supply is higher than
        the threshold written in the EEPROM
        <Condtype> LINE_VCC5_HIGH_WARNING
        <Probcause> powerProblem (36) <Alarmtype>
        equipmentAlarm (5) <Polarity> (2)
        "
	::= { pmc1002AlmlineXfp1SupplyAlarmEntry 17 }


pmc1002AlmLineVcc5LowWarningPortn OBJECT-TYPE
	SYNTAX  EkiOnOff
	MAX-ACCESS read-only
	STATUS current
	DESCRIPTION
        "
        VCC5 Power Supply Low Warning
         :Warning indicating the XFP/OTX
        VCC5 power supply is lower than
        the threshold written in the EEPROM
        <Condtype> LINE_VCC5_LOW_WARNING
        <Probcause> powerProblem (36) <Alarmtype>
        equipmentAlarm (5) <Polarity> (2)
        "
	::= { pmc1002AlmlineXfp1SupplyAlarmEntry 16 }


pmc1002AlmLineVcc3HighWarningPortn OBJECT-TYPE
	SYNTAX  EkiOnOff
	MAX-ACCESS read-only
	STATUS current
	DESCRIPTION
        "
        VCC3 Power Supply High Warning
        :Warning indicating the XFP/OTX
        VCC3 power supply is higher than
        the threshold written in the EEPROM
        <Condtype> LINE_VCC3_HIGH_WARNING
        <Probcause> powerProblem (36) <Alarmtype>
        equipmentAlarm (5) <Polarity> (2)
        "
	::= { pmc1002AlmlineXfp1SupplyAlarmEntry 15 }


pmc1002AlmLineVcc3LowWarningPortn OBJECT-TYPE
	SYNTAX  EkiOnOff
	MAX-ACCESS read-only
	STATUS current
	DESCRIPTION
        "
        VCC3 Power Supply Low Warning
         :Warning indicating the XFP/OTX
        VCC3 power supply is lower than
        the threshold written in the EEPROM
        <Condtype> LINE_VCC3_LOW_WARNING
        <Probcause> powerProblem (36) <Alarmtype>
        equipmentAlarm (5) <Polarity> (2)
        "
	::= { pmc1002AlmlineXfp1SupplyAlarmEntry 14 }


pmc1002AlmLineVcc2HighWarningPortn OBJECT-TYPE
	SYNTAX  EkiOnOff
	MAX-ACCESS read-only
	STATUS current
	DESCRIPTION
        "
        VCC2 Power Supply High Warning
        :Warning indicating the XFP/OTX
        VCC2 power supply is higher than
        the threshold written in the EEPROM
        <Condtype> LINE_VCC2_HIGH_WARNING
        <Probcause> powerProblem (36) <Alarmtype>
        equipmentAlarm (5) <Polarity> (2)
        "
	::= { pmc1002AlmlineXfp1SupplyAlarmEntry 13 }


pmc1002AlmLineVcc2LowWarningPortn OBJECT-TYPE
	SYNTAX  EkiOnOff
	MAX-ACCESS read-only
	STATUS current
	DESCRIPTION
        "
        VCC2 Power Supply Low Warning
         :Warning indicating the XFP/OTX
        VCC2 power supply is lower than
        the threshold written in the EEPROM
        <Condtype> LINE_VCC2_LOW_WARNING
        <Probcause> powerProblem (36) <Alarmtype>
        equipmentAlarm (5) <Polarity> (2)
        "
	::= { pmc1002AlmlineXfp1SupplyAlarmEntry 12 }


pmc1002AlmLineVee5HighWarningPortn OBJECT-TYPE
	SYNTAX  EkiOnOff
	MAX-ACCESS read-only
	STATUS current
	DESCRIPTION
        "
        VEE5 Power Supply High Warning
        :Warning indicating the XFP/OTX
        VEE5 power supply is higher than
        the threshold written in the EEPROM
        <Condtype> LINE_VEE5_HIGH_WARNING
        <Probcause> powerProblem (36) <Alarmtype>
        equipmentAlarm (5) <Polarity> (2)
        "
	::= { pmc1002AlmlineXfp1SupplyAlarmEntry 11 }


pmc1002AlmLineVee5LowLineWarningPortn OBJECT-TYPE
	SYNTAX  EkiOnOff
	MAX-ACCESS read-only
	STATUS current
	DESCRIPTION
        "
        VEE5 Power Supply Low Warning
         :Warning indicating the XFP/OTX
        VEE5 power supply is lower than
        the threshold written in the EEPROM
        <Condtype> LINE_VEE5_LOW_LINE_WARNING
        <Probcause> powerProblem (36) <Alarmtype>
        equipmentAlarm (5) <Polarity> (2)
        "
	::= { pmc1002AlmlineXfp1SupplyAlarmEntry 10 }


pmc1002AlmLineVcc5HighAlarmPortn OBJECT-TYPE
	SYNTAX  EkiOnOff
	MAX-ACCESS read-only
	STATUS current
	DESCRIPTION
        "
        VCC5 Power Supply High Alarm :Alarm
        indicating the XFP/OTX VCC5 power
        supply is higher than the threshold
        written in the EEPROM <Condtype>
        LINE_VCC5_HIGH_ALARM <Probcause>
        powerProblem (36) <Alarmtype> equipmentAlarm
        (5) <Polarity> (2)
        "
	::= { pmc1002AlmlineXfp1SupplyAlarmEntry 9 }


pmc1002AlmLineVcc5LowAlarmPortn OBJECT-TYPE
	SYNTAX  EkiOnOff
	MAX-ACCESS read-only
	STATUS current
	DESCRIPTION
        "
        VCC5 Power Supply Low Alarm :Alarm
        indicating the XFP/OTX VCC5 power
        supply is lower than the threshold
        written in the EEPROM <Condtype>
        LINE_VCC5_LOW_ALARM <Probcause>
        powerProblem (36) <Alarmtype> equipmentAlarm
        (5) <Polarity> (2)
        "
	::= { pmc1002AlmlineXfp1SupplyAlarmEntry 8 }


pmc1002AlmLineVcc3HighAlarmPortn OBJECT-TYPE
	SYNTAX  EkiOnOff
	MAX-ACCESS read-only
	STATUS current
	DESCRIPTION
        "
        VCC3 Power Supply High Alarm :Alarm
        indicating the XFP/OTX VCC3 power
        supply is higher than the threshold
        written in the EEPROM <Condtype>
        LINE_VCC3_HIGH_ALARM <Probcause>
        powerProblem (36) <Alarmtype> equipmentAlarm
        (5) <Polarity> (2)
        "
	::= { pmc1002AlmlineXfp1SupplyAlarmEntry 7 }


pmc1002AlmLineVcc3LowAlarmPortn OBJECT-TYPE
	SYNTAX  EkiOnOff
	MAX-ACCESS read-only
	STATUS current
	DESCRIPTION
        "
        VCC3 Power Supply Low Alarm :Alarm
        indicating the XFP/OTX VCC3 power
        supply is lower than the threshold
        written in the EEPROM <Condtype>
        LINE_VCC3_LOW_ALARM <Probcause>
        powerProblem (36) <Alarmtype> equipmentAlarm
        (5) <Polarity> (2)
        "
	::= { pmc1002AlmlineXfp1SupplyAlarmEntry 6 }


pmc1002AlmLineVcc2HighAlarmPortn OBJECT-TYPE
	SYNTAX  EkiOnOff
	MAX-ACCESS read-only
	STATUS current
	DESCRIPTION
        "
        VCC2 Power Supply High Alarm :Alarm
        indicating the XFP/OTX VCC2 power
        supply is higher than the threshold
        written in the EEPROM <Condtype>
        LINE_VCC2_HIGH_ALARM <Probcause>
        powerProblem (36) <Alarmtype> equipmentAlarm
        (5) <Polarity> (2)
        "
	::= { pmc1002AlmlineXfp1SupplyAlarmEntry 5 }


pmc1002AlmLineVcc2LowAlarmPortn OBJECT-TYPE
	SYNTAX  EkiOnOff
	MAX-ACCESS read-only
	STATUS current
	DESCRIPTION
        "
        VCC2 Power Supply Low Alarm :Alarm
        indicating the XFP/OTX VCC2 power
        supply is lower than the threshold
        written in the EEPROM <Condtype>
        LINE_VCC2_LOW_ALARM <Probcause>
        powerProblem (36) <Alarmtype> equipmentAlarm
        (5) <Polarity> (2)
        "
	::= { pmc1002AlmlineXfp1SupplyAlarmEntry 4 }


pmc1002AlmLineVee5HighAlarmPortn OBJECT-TYPE
	SYNTAX  EkiOnOff
	MAX-ACCESS read-only
	STATUS current
	DESCRIPTION
        "
        VEE5 Power Supply High Alarm :Alarm
        indicating the XFP/OTX VEE5 power
        supply is higher than the threshold
        written in the EEPROM <Condtype>
        LINE_VEE5_HIGH_ALARM <Probcause>
        powerProblem (36) <Alarmtype> equipmentAlarm
        (5) <Polarity> (2)
        "
	::= { pmc1002AlmlineXfp1SupplyAlarmEntry 3 }


pmc1002AlmLineVee5LowAlarmPortn OBJECT-TYPE
	SYNTAX  EkiOnOff
	MAX-ACCESS read-only
	STATUS current
	DESCRIPTION
        "
        VEE5 Power Supply Low Alarm :Alarm
        indicating the XFP/OTX VEE5 power
        supply is lower than the threshold
        written in the EEPROM <Condtype>
        LINE_VEE5_LOW_ALARM <Probcause>
        powerProblem (36) <Alarmtype> equipmentAlarm
        (5) <Polarity> (2)
        "
	::= { pmc1002AlmlineXfp1SupplyAlarmEntry 2 }


--- *********************************************************
---     TABLE for the pmc1002AlmlineOtx1TlhAlarms articles
--- *********************************************************

pmc1002AlmlineOtx1TlhAlarmsTable OBJECT-TYPE
	SYNTAX  SEQUENCE OF Pmc1002AlmlineOtx1TlhAlarmsEntry
	MAX-ACCESS not-accessible
	STATUS current
	DESCRIPTION
        "
        List of pmc1002AlmlineOtx1TlhAlarms
        Article
        "
	::= { pmc1002AlmLineUrg 224 }


pmc1002AlmlineOtx1TlhAlarmsEntry OBJECT-TYPE
	SYNTAX Pmc1002AlmlineOtx1TlhAlarmsEntry
	MAX-ACCESS not-accessible
	STATUS current
	DESCRIPTION
        "
        Row definition for the pmc1002AlmlineOtx1TlhAlarms
        table
        "
	INDEX   { pmc1002AlmlineOtx1TlhAlarmsIndex }
	::= { pmc1002AlmlineOtx1TlhAlarmsTable 1 }


Pmc1002AlmlineOtx1TlhAlarmsEntry ::=
	SEQUENCE {
	pmc1002AlmlineOtx1TlhAlarmsIndex
		INTEGER,
	pmc1002AlmLineLaserTempHighAlaPortn
		EkiOnOff,
	pmc1002AlmLineFreqDevHighAlaPortn
		EkiOnOff,
	pmc1002AlmLineCdrNotReadyPortn
		EkiOnOff,
	pmc1002AlmLineAgingHighAlaPortn
		EkiOnOff,
	pmc1002AlmLineModulatorAgingHighAlaPortn
		EkiOnOff
	}


pmc1002AlmlineOtx1TlhAlarmsIndex OBJECT-TYPE
	SYNTAX  INTEGER(0..128)
	MAX-ACCESS  read-only
	STATUS current
	DESCRIPTION
        "
        Index definition for the pmc1002AlmlineOtx1TlhAlarms
        table
        "
	::= { pmc1002AlmlineOtx1TlhAlarmsEntry 1 }


pmc1002AlmLineLaserTempHighAlaPortn OBJECT-TYPE
	SYNTAX  EkiOnOff
	MAX-ACCESS read-only
	STATUS current
	DESCRIPTION
        "
        Line Laser Temp. High Alarm :Alarm
        indicating the Line OTX TLH laser
        temperature is higher than the
         threshold written in the EEPROM
        <Condtype> LINE_LASER_TEMP_HIGH_ALA
        <Probcause> temperatureUnacceptable
        (51) <Alarmtype> equipmentAlarm
        (5) <Polarity> (2)
        "
	::= { pmc1002AlmlineOtx1TlhAlarmsEntry 15 }


pmc1002AlmLineFreqDevHighAlaPortn OBJECT-TYPE
	SYNTAX  EkiOnOff
	MAX-ACCESS read-only
	STATUS current
	DESCRIPTION
        "
        Line Freq. Deviation High Alarm
        :Alarm indicating the Line OTX
         TLH frequency deviation is higher
        than the threshold written in the
        EEPROM <Condtype> LINE_FREQ_DEV_HIGH_ALA
        <Probcause> transmitterFailure
         (56) <Alarmtype> equipmentAlarm
        (5) <Polarity> (2)
        "
	::= { pmc1002AlmlineOtx1TlhAlarmsEntry 13 }


pmc1002AlmLineCdrNotReadyPortn OBJECT-TYPE
	SYNTAX  EkiOnOff
	MAX-ACCESS read-only
	STATUS current
	DESCRIPTION
        "
        CDR Not Ready :This OID indicates
        the Clock Data Recovery unit is
        not yet initialized  <Help>  This
        alarm indicates the Clock Data
         Recovery unit is not yet initialized.
        <Condtype> LINE_CDR_NOT_READY <Probcause>
        receiveFailure (41) <Alarmtype>
        equipmentAlarm (5) <Polarity> (2)
        "
	::= { pmc1002AlmlineOtx1TlhAlarmsEntry 10 }


pmc1002AlmLineAgingHighAlaPortn OBJECT-TYPE
	SYNTAX  EkiOnOff
	MAX-ACCESS read-only
	STATUS current
	DESCRIPTION
        "
        Line OTX TLH Aging High Alarm
         :Alarm indicating the Line OTX
        TLH aging is higher than the threshold
        written in the EEPROM <Condtype>
        LINE_AGING_HIGH_ALA <Probcause>
        transmitterFailure (56) <Alarmtype>
        equipmentAlarm (5) <Polarity> (2)
        "
	::= { pmc1002AlmlineOtx1TlhAlarmsEntry 7 }


pmc1002AlmLineModulatorAgingHighAlaPortn OBJECT-TYPE
	SYNTAX  EkiOnOff
	MAX-ACCESS read-only
	STATUS current
	DESCRIPTION
        "
        Line Modulator Aging High Alarm
        :Alarm indicating the Line OTX
         TLH modulator aging is higher
         than the threshold written in
         the EEPROM <Condtype> LINE_MODULATOR_AGING_HIGH_ALA
        <Probcause> transmitterFailure
         (56) <Alarmtype> equipmentAlarm
        (5) <Polarity> (2)
        "
	::= { pmc1002AlmlineOtx1TlhAlarmsEntry 6 }


--- *********************************************************
---     TABLE for the pmc1002AlmlineOtx1TlhWarnings articles
--- *********************************************************

pmc1002AlmlineOtx1TlhWarningsTable OBJECT-TYPE
	SYNTAX  SEQUENCE OF Pmc1002AlmlineOtx1TlhWarningsEntry
	MAX-ACCESS not-accessible
	STATUS current
	DESCRIPTION
        "
        List of pmc1002AlmlineOtx1TlhWarnings
        Article
        "
	::= { pmc1002AlmLineNurg 225 }


pmc1002AlmlineOtx1TlhWarningsEntry OBJECT-TYPE
	SYNTAX Pmc1002AlmlineOtx1TlhWarningsEntry
	MAX-ACCESS not-accessible
	STATUS current
	DESCRIPTION
        "
        Row definition for the pmc1002AlmlineOtx1TlhWarnings
        table
        "
	INDEX   { pmc1002AlmlineOtx1TlhWarningsIndex }
	::= { pmc1002AlmlineOtx1TlhWarningsTable 1 }


Pmc1002AlmlineOtx1TlhWarningsEntry ::=
	SEQUENCE {
	pmc1002AlmlineOtx1TlhWarningsIndex
		INTEGER,
	pmc1002AlmLineLaserTempHighWarningPortn
		EkiOnOff,
	pmc1002AlmLineFreqDevHighWarningPortn
		EkiOnOff,
	pmc1002AlmLineAgingHighWarningPortn
		EkiOnOff,
	pmc1002AlmLineModulatorAgingHighWarningPortn
		EkiOnOff
	}


pmc1002AlmlineOtx1TlhWarningsIndex OBJECT-TYPE
	SYNTAX  INTEGER(0..128)
	MAX-ACCESS  read-only
	STATUS current
	DESCRIPTION
        "
        Index definition for the pmc1002AlmlineOtx1TlhWarnings
        table
        "
	::= { pmc1002AlmlineOtx1TlhWarningsEntry 1 }


pmc1002AlmLineLaserTempHighWarningPortn OBJECT-TYPE
	SYNTAX  EkiOnOff
	MAX-ACCESS read-only
	STATUS current
	DESCRIPTION
        "
        Line Laser Temp. High Warning
         :Warning indicating the Line OTX
        TLH laser temperature is higher
        than the threshold written in the
        EEPROM <Condtype> LINE_LASER_TEMP_HIGH_WARNING
        <Probcause> temperatureUnacceptable
        (51) <Alarmtype> equipmentAlarm
        (5) <Polarity> (2)
        "
	::= { pmc1002AlmlineOtx1TlhWarningsEntry 15 }


pmc1002AlmLineFreqDevHighWarningPortn OBJECT-TYPE
	SYNTAX  EkiOnOff
	MAX-ACCESS read-only
	STATUS current
	DESCRIPTION
        "
        Line Freq. Deviation High Warning
        :Warning indicating the Line OTX
        TLH frequency deviation is higher
        than the threshold written in the
        EEPROM <Condtype> LINE_FREQ_DEV_HIGH_WARNING
        <Probcause> transmitterFailure
         (56) <Alarmtype> equipmentAlarm
        (5) <Polarity> (2)
        "
	::= { pmc1002AlmlineOtx1TlhWarningsEntry 13 }


pmc1002AlmLineAgingHighWarningPortn OBJECT-TYPE
	SYNTAX  EkiOnOff
	MAX-ACCESS read-only
	STATUS current
	DESCRIPTION
        "
        Line OTX TLH Aging High Warning
        :Warning indicating the Line OTX
        TLH aging is higher than the threshold
        written in the EEPROM <Condtype>
        LINE_AGING_HIGH_WARNING <Probcause>
        transmitterFailure (56) <Alarmtype>
        equipmentAlarm (5) <Polarity> (2)
        "
	::= { pmc1002AlmlineOtx1TlhWarningsEntry 7 }


pmc1002AlmLineModulatorAgingHighWarningPortn OBJECT-TYPE
	SYNTAX  EkiOnOff
	MAX-ACCESS read-only
	STATUS current
	DESCRIPTION
        "
        Line Modulator Aging High Warning
        :Warning indicating the Line OTX
        TLH modulator aging is higher than
        the threshold written in the EEPROM
        <Condtype> LINE_MODULATOR_AGING_HIGH_WARNING
        <Probcause> transmitterFailure
         (56) <Alarmtype> equipmentAlarm
        (5) <Polarity> (2)
        "
	::= { pmc1002AlmlineOtx1TlhWarningsEntry 6 }







--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pmc1002CtrlconfMgnt1 OBJECT IDENTIFIER ::= { pmc1002CtrlOther 1 }




pmc1002CtrlConf2Clear1 OBJECT-TYPE
	  SYNTAX EkiOnOff
	  MAX-ACCESS read-write
	  STATUS current
	  DESCRIPTION
        "
        Clear Configuration Tables :This
        OID clears the configuration tables
        from configuration2 in the flash.
         <Help>  This control restores
         the default configuration of the
        module
        "
	  ::= { pmc1002CtrlconfMgnt1 14 }



pmc1002CtrlConf2Flash1 OBJECT-TYPE
	  SYNTAX EkiOnOff
	  MAX-ACCESS read-write
	  STATUS current
	  DESCRIPTION
        "
        Write Configuration Tables :This
        OID saves the current configuration
        of the PM as configuration2 in
         the flash.  <Help>  This control
        saves the customer configuration
        on the module
        "
	  ::= { pmc1002CtrlconfMgnt1 10 }



pmc1002CtrlConf2Load1 OBJECT-TYPE
	  SYNTAX EkiOnOff
	  MAX-ACCESS read-write
	  STATUS current
	  DESCRIPTION
        "
        Load Configuration Tables Set
         Nb 2 :When set this OID enables
        loading from flash configuration2
        into the PM.
        "
	  ::= { pmc1002CtrlconfMgnt1 2 }



pmc1002CtrlConf1Load1 OBJECT-TYPE
	  SYNTAX EkiOnOff
	  MAX-ACCESS read-write
	  STATUS current
	  DESCRIPTION
        "
        Load Configuration Tables Set
         Nb 1 :When set this OID enables
        loading from flash configuration1
        into the PM.
        "
	  ::= { pmc1002CtrlconfMgnt1 1 }



--- *****************************************************
---     LEAF for the synth4 article
--- *****************************************************
pmc1002Ctrlsynth4 OBJECT IDENTIFIER ::= { pmc1002CtrlOther 4 }




pmc1002CtrlCorrelatOff OBJECT-TYPE
	  SYNTAX EkiOnOff
	  MAX-ACCESS read-write
	  STATUS current
	  DESCRIPTION
        "
        Disable Alarm Correlation :This
        OID disables the alarm correlation
        in the PM.
        "
	  ::= { pmc1002Ctrlsynth4 2 }



pmc1002CtrlCorrelatOn OBJECT-TYPE
	  SYNTAX EkiOnOff
	  MAX-ACCESS read-write
	  STATUS current
	  DESCRIPTION
        "
        Enable Alarm Correlation :This
        OID enables the alarm correlation
        in the PM.
        "
	  ::= { pmc1002Ctrlsynth4 1 }



--- *****************************************************
---     LEAF for the swMgnt article
--- *****************************************************
pmc1002CtrlswMgnt OBJECT IDENTIFIER ::= { pmc1002CtrlOther 5 }




pmc1002CtrlLoadSwBank2 OBJECT-TYPE
	  SYNTAX EkiOnOff
	  MAX-ACCESS read-write
	  STATUS current
	  DESCRIPTION
        "
        Set Software Nb 2 As Active :This
        OID, when set, loads the SW from
        bank2 into the PM. It must be followed
        by a reset.  <Help>  This controls
        selects the second SW bank as the
        active bank for the next module
        reset
        "
	  ::= { pmc1002CtrlswMgnt 6 }



pmc1002CtrlLoadSwBank1 OBJECT-TYPE
	  SYNTAX EkiOnOff
	  MAX-ACCESS read-write
	  STATUS current
	  DESCRIPTION
        "
        Set Software Nb 1 As Active :This
        OID, when set, loads the SW from
        bank1 into the PM. It must be followed
        by a reset.  <Help>  This controls
        selects the first SW bank as the
        active bank for the next module
        reset
        "
	  ::= { pmc1002CtrlswMgnt 5 }



pmc1002CtrlWarmReset OBJECT-TYPE
	  SYNTAX EkiOnOff
	  MAX-ACCESS read-write
	  STATUS current
	  DESCRIPTION
        "
        PM Warm Reset :This OID, when
         set, causes a warm reset of the
        PM. This reset is not traffic affecting,
        and the configuration of PM remains
        unchanged.  <Help>  This control
        initiates a warm reset of the module.
        "
	  ::= { pmc1002CtrlswMgnt 3 }



pmc1002CtrlColdReset OBJECT-TYPE
	  SYNTAX EkiOnOff
	  MAX-ACCESS read-write
	  STATUS current
	  DESCRIPTION
        "
        PM Cold Reset :This OID, when
         set, causes a cold reset of the
        PM. This reset is traffic affecting,
        and the configuration of PM is
         reloaded on start-up.  <Help>
          This control initiates a cold
        reset of the module.
        "
	  ::= { pmc1002CtrlswMgnt 2 }



--- *****************************************************
---     LEAF for the gwMgnt article
--- *****************************************************
pmc1002CtrlgwMgnt OBJECT IDENTIFIER ::= { pmc1002CtrlOther 6 }




pmc1002CtrlLoadGwBank4 OBJECT-TYPE
	  SYNTAX EkiOnOff
	  MAX-ACCESS read-write
	  STATUS current
	  DESCRIPTION
        "
        Set Gateware Nb 4 As Active :This
        OID, when set, loads the GW from
        bank4 (Flash) into the PM. It is
        followed by an automatic gateware
        cold reset.
        "
	  ::= { pmc1002CtrlgwMgnt 8 }



pmc1002CtrlLoadGwBank3 OBJECT-TYPE
	  SYNTAX EkiOnOff
	  MAX-ACCESS read-write
	  STATUS current
	  DESCRIPTION
        "
        Set Gateware Nb 3 As Active :This
        OID, when set, loads the GW from
        bank3 (Flash) into the PM. It is
        followed by an automatic gateware
        cold reset.  <Help>  This controls
        initiates a cold reset of the module
        and select the third GW bank as
        the active bank
        "
	  ::= { pmc1002CtrlgwMgnt 7 }



pmc1002CtrlLoadGwBank2 OBJECT-TYPE
	  SYNTAX EkiOnOff
	  MAX-ACCESS read-write
	  STATUS current
	  DESCRIPTION
        "
        Set Gateware Nb 2 As Active :This
        OID, when set, loads the GW from
        bank2 (Flash) into the PM. It is
        followed by an automatic gateware
        cold reset.
        "
	  ::= { pmc1002CtrlgwMgnt 6 }



pmc1002CtrlLoadGwBank1 OBJECT-TYPE
	  SYNTAX EkiOnOff
	  MAX-ACCESS read-write
	  STATUS current
	  DESCRIPTION
        "
        Set Gateware Nb 1 As Active :This
        OID, when set, loads the GW from
        bank1 (Flash) into the PM. It is
        followed by an automatic gateware
        cold reset.  <Help>  This controls
        initiates a cold reset of the module
        and select the first GW bank as
        the active bank
        "
	  ::= { pmc1002CtrlgwMgnt 5 }



pmc1002CtrlCurrentGwReset OBJECT-TYPE
	  SYNTAX EkiOnOff
	  MAX-ACCESS read-write
	  STATUS current
	  DESCRIPTION
        "
        Active Gateware Reset :This OID,
        when set, resets the active gateware.
        It is traffic affecting.
        "
	  ::= { pmc1002CtrlgwMgnt 1 }



--- *********************************************************
---     TABLE for the pmc1002CtrlaccessLoop articles
--- *********************************************************

pmc1002CtrlaccessLoopTable OBJECT-TYPE
	SYNTAX  SEQUENCE OF Pmc1002CtrlaccessLoopEntry
	MAX-ACCESS not-accessible
	STATUS current
	DESCRIPTION
        "
        List of pmc1002CtrlaccessLoop
         Article
        "
	::= { pmc1002CtrlClient 16 }


pmc1002CtrlaccessLoopEntry OBJECT-TYPE
	SYNTAX Pmc1002CtrlaccessLoopEntry
	MAX-ACCESS not-accessible
	STATUS current
	DESCRIPTION
        "
        Row definition for the pmc1002CtrlaccessLoop
        table
        "
	INDEX   { pmc1002CtrlaccessLoopIndex }
	::= { pmc1002CtrlaccessLoopTable 1 }


Pmc1002CtrlaccessLoopEntry ::=
	SEQUENCE {
	pmc1002CtrlaccessLoopIndex
		INTEGER,
	pmc1002CtrlaccessLoopPortn
		EkiState
	}


pmc1002CtrlaccessLoopIndex OBJECT-TYPE
	SYNTAX  INTEGER(0..128)
	MAX-ACCESS  read-only
	STATUS current
	DESCRIPTION
        "
        Index definition for the pmc1002CtrlaccessLoop
        table
        "
	::= { pmc1002CtrlaccessLoopEntry 1 }


pmc1002CtrlaccessLoopPortn OBJECT-TYPE
	SYNTAX  EkiState
	MAX-ACCESS read-write
	STATUS current
	DESCRIPTION
        "
        Client Facility Loopback :This
        OID operates a Client Facility
         Loopback, looping client input
        signal on the client output port.
        The loop is located on the client
        transceiver  <Help> This maintenance
        parameter operates a Client Facility
        Loopback, looping client input
         signal on the client output port.
        The loop is located on the client
        transceiver
        "
	::= { pmc1002CtrlaccessLoopEntry 2 }


--- *********************************************************
---     TABLE for the pmc1002CtrlportOosMode articles
--- *********************************************************

pmc1002CtrlportOosModeTable OBJECT-TYPE
	SYNTAX  SEQUENCE OF Pmc1002CtrlportOosModeEntry
	MAX-ACCESS not-accessible
	STATUS current
	DESCRIPTION
        "
        List of pmc1002CtrlportOosMode
        Article
        "
	::= { pmc1002CtrlClient 18 }


pmc1002CtrlportOosModeEntry OBJECT-TYPE
	SYNTAX Pmc1002CtrlportOosModeEntry
	MAX-ACCESS not-accessible
	STATUS current
	DESCRIPTION
        "
        Row definition for the pmc1002CtrlportOosMode
        table
        "
	INDEX   { pmc1002CtrlportOosModeIndex }
	::= { pmc1002CtrlportOosModeTable 1 }


Pmc1002CtrlportOosModeEntry ::=
	SEQUENCE {
	pmc1002CtrlportOosModeIndex
		INTEGER,
	pmc1002CtrlportOosModePortn
		EkiState
	}


pmc1002CtrlportOosModeIndex OBJECT-TYPE
	SYNTAX  INTEGER(0..128)
	MAX-ACCESS  read-only
	STATUS current
	DESCRIPTION
        "
        Index definition for the pmc1002CtrlportOosMode
        table
        "
	::= { pmc1002CtrlportOosModeEntry 1 }


pmc1002CtrlportOosModePortn OBJECT-TYPE
	SYNTAX  EkiState
	MAX-ACCESS read-write
	STATUS current
	DESCRIPTION
        "
        Client Port Out Of Service :This
        OID sets the client port Out Of
        Service  <Help>  This controls
         defines the service state of the
        client port
        "
	::= { pmc1002CtrlportOosModeEntry 2 }


--- *********************************************************
---     TABLE for the pmc1002CtrlsfpOffCtrl articles
--- *********************************************************

pmc1002CtrlsfpOffCtrlTable OBJECT-TYPE
	SYNTAX  SEQUENCE OF Pmc1002CtrlsfpOffCtrlEntry
	MAX-ACCESS not-accessible
	STATUS current
	DESCRIPTION
        "
        List of pmc1002CtrlsfpOffCtrl
         Article
        "
	::= { pmc1002CtrlClient 20 }


pmc1002CtrlsfpOffCtrlEntry OBJECT-TYPE
	SYNTAX Pmc1002CtrlsfpOffCtrlEntry
	MAX-ACCESS not-accessible
	STATUS current
	DESCRIPTION
        "
        Row definition for the pmc1002CtrlsfpOffCtrl
        table
        "
	INDEX   { pmc1002CtrlsfpOffCtrlIndex }
	::= { pmc1002CtrlsfpOffCtrlTable 1 }


Pmc1002CtrlsfpOffCtrlEntry ::=
	SEQUENCE {
	pmc1002CtrlsfpOffCtrlIndex
		INTEGER,
	pmc1002CtrlsfpOffCtrlPortn
		EkiState
	}


pmc1002CtrlsfpOffCtrlIndex OBJECT-TYPE
	SYNTAX  INTEGER(0..128)
	MAX-ACCESS  read-only
	STATUS current
	DESCRIPTION
        "
        Index definition for the pmc1002CtrlsfpOffCtrl
        table
        "
	::= { pmc1002CtrlsfpOffCtrlEntry 1 }


pmc1002CtrlsfpOffCtrlPortn OBJECT-TYPE
	SYNTAX  EkiState
	MAX-ACCESS read-write
	STATUS current
	DESCRIPTION
        "
        Client SFP+ Optical Laser OFF
         :This OID switches off the SFP.
         <Help>  This control defines the
        laser state of the client transceiver
        "
	::= { pmc1002CtrlsfpOffCtrlEntry 2 }


--- *********************************************************
---     TABLE for the pmc1002CtrlcsfUpIns articles
--- *********************************************************

pmc1002CtrlcsfUpInsTable OBJECT-TYPE
	SYNTAX  SEQUENCE OF Pmc1002CtrlcsfUpInsEntry
	MAX-ACCESS not-accessible
	STATUS current
	DESCRIPTION
        "
        List of pmc1002CtrlcsfUpIns Article
        "
	::= { pmc1002CtrlClient 21 }


pmc1002CtrlcsfUpInsEntry OBJECT-TYPE
	SYNTAX Pmc1002CtrlcsfUpInsEntry
	MAX-ACCESS not-accessible
	STATUS current
	DESCRIPTION
        "
        Row definition for the pmc1002CtrlcsfUpIns
        table
        "
	INDEX   { pmc1002CtrlcsfUpInsIndex }
	::= { pmc1002CtrlcsfUpInsTable 1 }


Pmc1002CtrlcsfUpInsEntry ::=
	SEQUENCE {
	pmc1002CtrlcsfUpInsIndex
		INTEGER,
	pmc1002CtrlcsfUpInsPortn
		EkiState
	}


pmc1002CtrlcsfUpInsIndex OBJECT-TYPE
	SYNTAX  INTEGER(0..128)
	MAX-ACCESS  read-only
	STATUS current
	DESCRIPTION
        "
        Index definition for the pmc1002CtrlcsfUpIns
        table
        "
	::= { pmc1002CtrlcsfUpInsEntry 1 }


pmc1002CtrlcsfUpInsPortn OBJECT-TYPE
	SYNTAX  EkiState
	MAX-ACCESS read-write
	STATUS current
	DESCRIPTION
        "
        Client Signal Fail Insertion :This
        OID, when set, inserts  a client
        signal fail in the upstream client
        Port.  <Help>  This control inserts
        a Client Signal Fail for the client
        port
        "
	::= { pmc1002CtrlcsfUpInsEntry 2 }


--- *********************************************************
---     TABLE for the pmc1002CtrlcaisDwIns articles
--- *********************************************************

pmc1002CtrlcaisDwInsTable OBJECT-TYPE
	SYNTAX  SEQUENCE OF Pmc1002CtrlcaisDwInsEntry
	MAX-ACCESS not-accessible
	STATUS current
	DESCRIPTION
        "
        List of pmc1002CtrlcaisDwIns Article
        "
	::= { pmc1002CtrlClient 22 }


pmc1002CtrlcaisDwInsEntry OBJECT-TYPE
	SYNTAX Pmc1002CtrlcaisDwInsEntry
	MAX-ACCESS not-accessible
	STATUS current
	DESCRIPTION
        "
        Row definition for the pmc1002CtrlcaisDwIns
        table
        "
	INDEX   { pmc1002CtrlcaisDwInsIndex }
	::= { pmc1002CtrlcaisDwInsTable 1 }


Pmc1002CtrlcaisDwInsEntry ::=
	SEQUENCE {
	pmc1002CtrlcaisDwInsIndex
		INTEGER,
	pmc1002CtrlcaisDwInsPortn
		EkiState
	}


pmc1002CtrlcaisDwInsIndex OBJECT-TYPE
	SYNTAX  INTEGER(0..128)
	MAX-ACCESS  read-only
	STATUS current
	DESCRIPTION
        "
        Index definition for the pmc1002CtrlcaisDwIns
        table
        "
	::= { pmc1002CtrlcaisDwInsEntry 1 }


pmc1002CtrlcaisDwInsPortn OBJECT-TYPE
	SYNTAX  EkiState
	MAX-ACCESS read-write
	STATUS current
	DESCRIPTION
        "
        Client AIS Insertion :This OID,
        when set, inserts a client AIS
         on the downstream client Port.
         <Help>  This control inserts a
        Client AIS for the client port
        "
	::= { pmc1002CtrlcaisDwInsEntry 2 }


--- *********************************************************
---     TABLE for the pmc1002CtrlclientAccessTermLoop articles
--- *********************************************************

pmc1002CtrlclientAccessTermLoopTable OBJECT-TYPE
	SYNTAX  SEQUENCE OF Pmc1002CtrlclientAccessTermLoopEntry
	MAX-ACCESS not-accessible
	STATUS current
	DESCRIPTION
        "
        List of pmc1002CtrlclientAccessTermLoop
        Article
        "
	::= { pmc1002CtrlClient 26 }


pmc1002CtrlclientAccessTermLoopEntry OBJECT-TYPE
	SYNTAX Pmc1002CtrlclientAccessTermLoopEntry
	MAX-ACCESS not-accessible
	STATUS current
	DESCRIPTION
        "
        Row definition for the pmc1002CtrlclientAccessTermLoop
        table
        "
	INDEX   { pmc1002CtrlclientAccessTermLoopIndex }
	::= { pmc1002CtrlclientAccessTermLoopTable 1 }


Pmc1002CtrlclientAccessTermLoopEntry ::=
	SEQUENCE {
	pmc1002CtrlclientAccessTermLoopIndex
		INTEGER,
	pmc1002CtrlclientAccessTermLoopPortn
		EkiState
	}


pmc1002CtrlclientAccessTermLoopIndex OBJECT-TYPE
	SYNTAX  INTEGER(0..128)
	MAX-ACCESS  read-only
	STATUS current
	DESCRIPTION
        "
        Index definition for the pmc1002CtrlclientAccessTermLoop
        table
        "
	::= { pmc1002CtrlclientAccessTermLoopEntry 1 }


pmc1002CtrlclientAccessTermLoopPortn OBJECT-TYPE
	SYNTAX  EkiState
	MAX-ACCESS read-write
	STATUS current
	DESCRIPTION
        "
        Client Terminal Loopback :This
        OID operates a Client Terminal
         Loopback, looping client input
        signal on the client output port.
        The loop is located on the line
        transceiver  <Help> This maintenance
        parameter operates a Client Terminal
        Loopback, looping client input
         signal on the client output port.
        The loop is located on the line
        transceiver
        "
	::= { pmc1002CtrlclientAccessTermLoopEntry 2 }


--- *********************************************************
---     TABLE for the pmc1002Ctrlprotocol articles
--- *********************************************************

pmc1002CtrlprotocolTable OBJECT-TYPE
	SYNTAX  SEQUENCE OF Pmc1002CtrlprotocolEntry
	MAX-ACCESS not-accessible
	STATUS current
	DESCRIPTION
        "
        List of pmc1002Ctrlprotocol Article
        "
	::= { pmc1002CtrlClient 52 }


pmc1002CtrlprotocolEntry OBJECT-TYPE
	SYNTAX Pmc1002CtrlprotocolEntry
	MAX-ACCESS not-accessible
	STATUS current
	DESCRIPTION
        "
        Row definition for the pmc1002Ctrlprotocol
        table
        "
	INDEX   { pmc1002CtrlprotocolIndex }
	::= { pmc1002CtrlprotocolTable 1 }


Pmc1002CtrlprotocolEntry ::=
	SEQUENCE {
	pmc1002CtrlprotocolIndex
		INTEGER,
	pmc1002CtrlprotocolPortn
		EkiProtocol
	}


pmc1002CtrlprotocolIndex OBJECT-TYPE
	SYNTAX  INTEGER(0..128)
	MAX-ACCESS  read-only
	STATUS current
	DESCRIPTION
        "
        Index definition for the pmc1002Ctrlprotocol
        table
        "
	::= { pmc1002CtrlprotocolEntry 1 }


pmc1002CtrlprotocolPortn OBJECT-TYPE
	SYNTAX  EkiProtocol
	MAX-ACCESS read-write
	STATUS current
	DESCRIPTION
        "
        Client Protocol: This OID sets
        the protocol of the Client port.
        "
	::= { pmc1002CtrlprotocolEntry 2 }


--- *********************************************************
---     TABLE for the pmc1002CtrlcommAccessLoop articles
--- *********************************************************

pmc1002CtrlcommAccessLoopTable OBJECT-TYPE
	SYNTAX  SEQUENCE OF Pmc1002CtrlcommAccessLoopEntry
	MAX-ACCESS not-accessible
	STATUS deprecated
	DESCRIPTION
        "
        List of pmc1002CtrlcommAccessLoop
        Article
        "
	::= { pmc1002CtrlLine 64 }


pmc1002CtrlcommAccessLoopEntry OBJECT-TYPE
	SYNTAX Pmc1002CtrlcommAccessLoopEntry
	MAX-ACCESS not-accessible
	STATUS deprecated
	DESCRIPTION
        "
        Row definition for the pmc1002CtrlcommAccessLoop
        table
        "
	INDEX   { pmc1002CtrlcommAccessLoopIndex }
	::= { pmc1002CtrlcommAccessLoopTable 1 }


Pmc1002CtrlcommAccessLoopEntry ::=
	SEQUENCE {
	pmc1002CtrlcommAccessLoopIndex
		INTEGER,
	pmc1002CtrlcommAccessLoopPortn
		EkiState
	}


pmc1002CtrlcommAccessLoopIndex OBJECT-TYPE
	SYNTAX  INTEGER(0..128)
	MAX-ACCESS  read-only
	STATUS deprecated
	DESCRIPTION
        "
        Index definition for the pmc1002CtrlcommAccessLoop
        table
        "
	::= { pmc1002CtrlcommAccessLoopEntry 1 }


pmc1002CtrlcommAccessLoopPortn OBJECT-TYPE
	SYNTAX  EkiState
	MAX-ACCESS read-write
	STATUS deprecated
	DESCRIPTION
        "
        PM Full Access Loop Mode :This
        OID, when set, puts the module
         in common access loop back, looping
        the 10 Gb/s output signal on the
        10 Gb/s input.
        "
	::= { pmc1002CtrlcommAccessLoopEntry 2 }


--- *********************************************************
---     TABLE for the pmc1002CtrllineLoop articles
--- *********************************************************

pmc1002CtrllineLoopTable OBJECT-TYPE
	SYNTAX  SEQUENCE OF Pmc1002CtrllineLoopEntry
	MAX-ACCESS not-accessible
	STATUS current
	DESCRIPTION
        "
        List of pmc1002CtrllineLoop Article
        "
	::= { pmc1002CtrlLine 66 }


pmc1002CtrllineLoopEntry OBJECT-TYPE
	SYNTAX Pmc1002CtrllineLoopEntry
	MAX-ACCESS not-accessible
	STATUS current
	DESCRIPTION
        "
        Row definition for the pmc1002CtrllineLoop
        table
        "
	INDEX   { pmc1002CtrllineLoopIndex }
	::= { pmc1002CtrllineLoopTable 1 }


Pmc1002CtrllineLoopEntry ::=
	SEQUENCE {
	pmc1002CtrllineLoopIndex
		INTEGER,
	pmc1002CtrllineLoopPortn
		EkiState
	}


pmc1002CtrllineLoopIndex OBJECT-TYPE
	SYNTAX  INTEGER(0..128)
	MAX-ACCESS  read-only
	STATUS current
	DESCRIPTION
        "
        Index definition for the pmc1002CtrllineLoop
        table
        "
	::= { pmc1002CtrllineLoopEntry 1 }


pmc1002CtrllineLoopPortn OBJECT-TYPE
	SYNTAX  EkiState
	MAX-ACCESS read-write
	STATUS current
	DESCRIPTION
        "
        Line Facility Loopback :This OID
        operates a Line Facility Loopback,
        looping line input signal on the
        line output port. The loop is located
        on the line transceiver. If the
        Line signal carries DCC, the management
        network is impacted  <Help> This
        maintenance parameter operates
         a Line Facility Loopback, looping
        line input signal on the line output
        port. The loop is located on the
        line transceiver. If the Line signal
        carries DCC, the management network
        is impacted
        "
	::= { pmc1002CtrllineLoopEntry 2 }


--- *********************************************************
---     TABLE for the pmc1002CtrlmsAis articles
--- *********************************************************

pmc1002CtrlmsAisTable OBJECT-TYPE
	SYNTAX  SEQUENCE OF Pmc1002CtrlmsAisEntry
	MAX-ACCESS not-accessible
	STATUS current
	DESCRIPTION
        "
        List of pmc1002CtrlmsAis Article
        "
	::= { pmc1002CtrlLine 67 }


pmc1002CtrlmsAisEntry OBJECT-TYPE
	SYNTAX Pmc1002CtrlmsAisEntry
	MAX-ACCESS not-accessible
	STATUS current
	DESCRIPTION
        "
        Row definition for the pmc1002CtrlmsAis
        table
        "
	INDEX   { pmc1002CtrlmsAisIndex }
	::= { pmc1002CtrlmsAisTable 1 }


Pmc1002CtrlmsAisEntry ::=
	SEQUENCE {
	pmc1002CtrlmsAisIndex
		INTEGER,
	pmc1002CtrlmsAisPortn
		EkiState
	}


pmc1002CtrlmsAisIndex OBJECT-TYPE
	SYNTAX  INTEGER(0..128)
	MAX-ACCESS  read-only
	STATUS current
	DESCRIPTION
        "
        Index definition for the pmc1002CtrlmsAis
        table
        "
	::= { pmc1002CtrlmsAisEntry 1 }


pmc1002CtrlmsAisPortn OBJECT-TYPE
	SYNTAX  EkiState
	MAX-ACCESS read-write
	STATUS current
	DESCRIPTION
        "
        Insert MS-AIS/L-AIS On Line Output
        :This OID, when set, inserts an
        MS-AIS/L-AIS in the outgoing STM-64/OC-192
        signal.
        "
	::= { pmc1002CtrlmsAisEntry 2 }


--- *********************************************************
---     TABLE for the pmc1002CtrlfecDisable articles
--- *********************************************************

pmc1002CtrlfecDisableTable OBJECT-TYPE
	SYNTAX  SEQUENCE OF Pmc1002CtrlfecDisableEntry
	MAX-ACCESS not-accessible
	STATUS current
	DESCRIPTION
        "
        List of pmc1002CtrlfecDisable
         Article
        "
	::= { pmc1002CtrlLine 69 }


pmc1002CtrlfecDisableEntry OBJECT-TYPE
	SYNTAX Pmc1002CtrlfecDisableEntry
	MAX-ACCESS not-accessible
	STATUS current
	DESCRIPTION
        "
        Row definition for the pmc1002CtrlfecDisable
        table
        "
	INDEX   { pmc1002CtrlfecDisableIndex }
	::= { pmc1002CtrlfecDisableTable 1 }


Pmc1002CtrlfecDisableEntry ::=
	SEQUENCE {
	pmc1002CtrlfecDisableIndex
		INTEGER,
	pmc1002CtrlfecDisablePortn
		EkiState
	}


pmc1002CtrlfecDisableIndex OBJECT-TYPE
	SYNTAX  INTEGER(0..128)
	MAX-ACCESS  read-only
	STATUS current
	DESCRIPTION
        "
        Index definition for the pmc1002CtrlfecDisable
        table
        "
	::= { pmc1002CtrlfecDisableEntry 1 }


pmc1002CtrlfecDisablePortn OBJECT-TYPE
	SYNTAX  EkiState
	MAX-ACCESS read-write
	STATUS current
	DESCRIPTION
        "
        FEC Disable :This OID disable
         the Forward Error Correction decoder
        on the line receive side  <Help>
         This control disables the Forward
        Error Correction on the line input
        signal.
        "
	::= { pmc1002CtrlfecDisableEntry 2 }


--- *********************************************************
---     TABLE for the pmc1002CtrllineOosMode articles
--- *********************************************************

pmc1002CtrllineOosModeTable OBJECT-TYPE
	SYNTAX  SEQUENCE OF Pmc1002CtrllineOosModeEntry
	MAX-ACCESS not-accessible
	STATUS current
	DESCRIPTION
        "
        List of pmc1002CtrllineOosMode
        Article
        "
	::= { pmc1002CtrlLine 74 }


pmc1002CtrllineOosModeEntry OBJECT-TYPE
	SYNTAX Pmc1002CtrllineOosModeEntry
	MAX-ACCESS not-accessible
	STATUS current
	DESCRIPTION
        "
        Row definition for the pmc1002CtrllineOosMode
        table
        "
	INDEX   { pmc1002CtrllineOosModeIndex }
	::= { pmc1002CtrllineOosModeTable 1 }


Pmc1002CtrllineOosModeEntry ::=
	SEQUENCE {
	pmc1002CtrllineOosModeIndex
		INTEGER,
	pmc1002CtrllineOosModePortn
		EkiState
	}


pmc1002CtrllineOosModeIndex OBJECT-TYPE
	SYNTAX  INTEGER(0..128)
	MAX-ACCESS  read-only
	STATUS current
	DESCRIPTION
        "
        Index definition for the pmc1002CtrllineOosMode
        table
        "
	::= { pmc1002CtrllineOosModeEntry 1 }


pmc1002CtrllineOosModePortn OBJECT-TYPE
	SYNTAX  EkiState
	MAX-ACCESS read-write
	STATUS current
	DESCRIPTION
        "
        Line Port Out Of Service :This
        OID sets the line port Out Of Service
         <Help>  This control defines the
        service state of the line port
        "
	::= { pmc1002CtrllineOosModeEntry 2 }


--- *****************************************************
---     LEAF for the ledTest article
--- *****************************************************
pmc1002CtrlledTest OBJECT IDENTIFIER ::= { pmc1002CtrlOther 192 }




pmc1002CtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { pmc1002CtrlledTest 3 }



pmc1002CtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { pmc1002CtrlledTest 2 }



pmc1002CtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { pmc1002CtrlledTest 1 }



--- *****************************************************
---     LEAF for the moduleOosMode article
--- *****************************************************
pmc1002CtrlmoduleOosMode OBJECT IDENTIFIER ::= { pmc1002CtrlOther 193 }




pmc1002CtrlModuleOosMode OBJECT-TYPE
	  SYNTAX EkiOnOff
	  MAX-ACCESS read-write
	  STATUS current
	  DESCRIPTION
        "
        PM Out Of Service :This OID sets
        the PM1008 Out Of Service  <Help>
         This control defines the service
        state of the complete module
        "
	  ::= { pmc1002CtrlmoduleOosMode 1 }



--- *****************************************************
---     LEAF for the moduleDccMgnt article
--- *****************************************************

pmc1002CtrlmoduleDccMgnt OBJECT-TYPE
	  SYNTAX Pmc1002DccMode
	  MAX-ACCESS read-write
	  STATUS current
	  DESCRIPTION
        "
        DCC Mode :This OID defines the
        DCC mode of the PM (No DCC, Terminal
        Line 1, Terminal Line 2, Terminal
        Line 1&2)   <Help>  This control
        defines the DCC mode of the PM
         (No DCC, Terminal Line 1, Terminal
        Line 2 or Terminal Line 1&2)

        "
	  ::= { pmc1002CtrlOther 196 }



--- *****************************************************
---     LEAF for the maintenanceMode article
--- *****************************************************
pmc1002CtrlmaintenanceMode OBJECT IDENTIFIER ::= { pmc1002CtrlOther 197 }




pmc1002CtrlMaintenanceMode OBJECT-TYPE
	  SYNTAX EkiOnOff
	  MAX-ACCESS read-write
	  STATUS current
	  DESCRIPTION
        "
        Enable Maintenance :This OID enables
        the maintenance mode on the PM.
         <Help>   This control enables
         the maintenance mode on the PM.
        "
	  ::= { pmc1002CtrlmaintenanceMode 1 }



--- *********************************************************
---     TABLE for the pmc1002CtrlxfpOnoff articles
--- *********************************************************

pmc1002CtrlxfpOnoffTable OBJECT-TYPE
	SYNTAX  SEQUENCE OF Pmc1002CtrlxfpOnoffEntry
	MAX-ACCESS not-accessible
	STATUS current
	DESCRIPTION
        "
        List of pmc1002CtrlxfpOnoff Article
        "
	::= { pmc1002CtrlLine 208 }


pmc1002CtrlxfpOnoffEntry OBJECT-TYPE
	SYNTAX Pmc1002CtrlxfpOnoffEntry
	MAX-ACCESS not-accessible
	STATUS current
	DESCRIPTION
        "
        Row definition for the pmc1002CtrlxfpOnoff
        table
        "
	INDEX   { pmc1002CtrlxfpOnoffIndex }
	::= { pmc1002CtrlxfpOnoffTable 1 }


Pmc1002CtrlxfpOnoffEntry ::=
	SEQUENCE {
	pmc1002CtrlxfpOnoffIndex
		INTEGER,
	pmc1002CtrlxfpOnoffPortn
		EkiState
	}


pmc1002CtrlxfpOnoffIndex OBJECT-TYPE
	SYNTAX  INTEGER(0..128)
	MAX-ACCESS  read-only
	STATUS current
	DESCRIPTION
        "
        Index definition for the pmc1002CtrlxfpOnoff
        table
        "
	::= { pmc1002CtrlxfpOnoffEntry 1 }


pmc1002CtrlxfpOnoffPortn OBJECT-TYPE
	SYNTAX  EkiState
	MAX-ACCESS read-write
	STATUS current
	DESCRIPTION
        "
        XFP/OTX Optical Laser OFF :This
        OID switches off the XFP or the
        OTX  <Help>  This control defines
        the laser state of the line transceiver
        "
	::= { pmc1002CtrlxfpOnoffEntry 2 }


--- *********************************************************
---     TABLE for the pmc1002CtrlxfpLineLoop articles
--- *********************************************************

pmc1002CtrlxfpLineLoopTable OBJECT-TYPE
	SYNTAX  SEQUENCE OF Pmc1002CtrlxfpLineLoopEntry
	MAX-ACCESS not-accessible
	STATUS current
	DESCRIPTION
        "
        List of pmc1002CtrlxfpLineLoop
        Article
        "
	::= { pmc1002CtrlLine 209 }


pmc1002CtrlxfpLineLoopEntry OBJECT-TYPE
	SYNTAX Pmc1002CtrlxfpLineLoopEntry
	MAX-ACCESS not-accessible
	STATUS current
	DESCRIPTION
        "
        Row definition for the pmc1002CtrlxfpLineLoop
        table
        "
	INDEX   { pmc1002CtrlxfpLineLoopIndex }
	::= { pmc1002CtrlxfpLineLoopTable 1 }


Pmc1002CtrlxfpLineLoopEntry ::=
	SEQUENCE {
	pmc1002CtrlxfpLineLoopIndex
		INTEGER,
	pmc1002CtrlxfpLineLoopPortn
		EkiState
	}


pmc1002CtrlxfpLineLoopIndex OBJECT-TYPE
	SYNTAX  INTEGER(0..128)
	MAX-ACCESS  read-only
	STATUS current
	DESCRIPTION
        "
        Index definition for the pmc1002CtrlxfpLineLoop
        table
        "
	::= { pmc1002CtrlxfpLineLoopEntry 1 }


pmc1002CtrlxfpLineLoopPortn OBJECT-TYPE
	SYNTAX  EkiState
	MAX-ACCESS read-write
	STATUS current
	DESCRIPTION
        "
        Line XFP/OTX Loop :This OID operates
        a line loopback on the line XFP
        or the OTX  <Help>  This control
        defines the line loop back of the
        line transceiver
        "
	::= { pmc1002CtrlxfpLineLoopEntry 2 }


--- *********************************************************
---     TABLE for the pmc1002CtrlxfpLineXfiLoop articles
--- *********************************************************

pmc1002CtrlxfpLineXfiLoopTable OBJECT-TYPE
	SYNTAX  SEQUENCE OF Pmc1002CtrlxfpLineXfiLoopEntry
	MAX-ACCESS not-accessible
	STATUS current
	DESCRIPTION
        "
        List of pmc1002CtrlxfpLineXfiLoop
        Article
        "
	::= { pmc1002CtrlLine 210 }


pmc1002CtrlxfpLineXfiLoopEntry OBJECT-TYPE
	SYNTAX Pmc1002CtrlxfpLineXfiLoopEntry
	MAX-ACCESS not-accessible
	STATUS current
	DESCRIPTION
        "
        Row definition for the pmc1002CtrlxfpLineXfiLoop
        table
        "
	INDEX   { pmc1002CtrlxfpLineXfiLoopIndex }
	::= { pmc1002CtrlxfpLineXfiLoopTable 1 }


Pmc1002CtrlxfpLineXfiLoopEntry ::=
	SEQUENCE {
	pmc1002CtrlxfpLineXfiLoopIndex
		INTEGER,
	pmc1002CtrlxfpLineXfiLoopPortn
		EkiState
	}


pmc1002CtrlxfpLineXfiLoopIndex OBJECT-TYPE
	SYNTAX  INTEGER(0..128)
	MAX-ACCESS  read-only
	STATUS current
	DESCRIPTION
        "
        Index definition for the pmc1002CtrlxfpLineXfiLoop
        table
        "
	::= { pmc1002CtrlxfpLineXfiLoopEntry 1 }


pmc1002CtrlxfpLineXfiLoopPortn OBJECT-TYPE
	SYNTAX  EkiState
	MAX-ACCESS read-write
	STATUS current
	DESCRIPTION
        "
        Line XFP/OTX XFI Loop :This OID
        operates a XFI loopback on the
         line XFP or the OTX  <Help>  This
        control defines the XFI loop back
        of the line transceiver
        "
	::= { pmc1002CtrlxfpLineXfiLoopEntry 2 }


--- *********************************************************
---     TABLE for the pmc1002CtrllineTunableChannel articles
--- *********************************************************

pmc1002CtrllineTunableChannelTable OBJECT-TYPE
	SYNTAX  SEQUENCE OF Pmc1002CtrllineTunableChannelEntry
	MAX-ACCESS not-accessible
	STATUS current
	DESCRIPTION
        "
        List of pmc1002CtrllineTunableChannel
        Article
        "
	::= { pmc1002CtrlLine 212 }


pmc1002CtrllineTunableChannelEntry OBJECT-TYPE
	SYNTAX Pmc1002CtrllineTunableChannelEntry
	MAX-ACCESS not-accessible
	STATUS current
	DESCRIPTION
        "
        Row definition for the pmc1002CtrllineTunableChannel
        table
        "
	INDEX   { pmc1002CtrllineTunableChannelIndex }
	::= { pmc1002CtrllineTunableChannelTable 1 }


Pmc1002CtrllineTunableChannelEntry ::=
	SEQUENCE {
	pmc1002CtrllineTunableChannelIndex
		INTEGER,
	pmc1002CtrllineTunableChannelPortn
		Pmc1002OtxChannel
	}


pmc1002CtrllineTunableChannelIndex OBJECT-TYPE
	SYNTAX  INTEGER(0..128)
	MAX-ACCESS  read-only
	STATUS current
	DESCRIPTION
        "
        Index definition for the pmc1002CtrllineTunableChannel
        table
        "
	::= { pmc1002CtrllineTunableChannelEntry 1 }


pmc1002CtrllineTunableChannelPortn OBJECT-TYPE
	SYNTAX  Pmc1002OtxChannel
	MAX-ACCESS read-write
	STATUS current
	DESCRIPTION
        "
        ITU Channel :This OID selects
         the ITU channel of the Line OTX
        TLH Laser  <Help>   This control
        defines the ITU channel of the
         Line OTX TLH Laser
        "
	::= { pmc1002CtrllineTunableChannelEntry 2 }


--- *********************************************************
---     TABLE for the pmc1002CtrllinePhotodiodeMode articles
--- *********************************************************

pmc1002CtrllinePhotodiodeModeTable OBJECT-TYPE
	SYNTAX  SEQUENCE OF Pmc1002CtrllinePhotodiodeModeEntry
	MAX-ACCESS not-accessible
	STATUS current
	DESCRIPTION
        "
        List of pmc1002CtrllinePhotodiodeMode
        Article
        "
	::= { pmc1002CtrlLine 213 }


pmc1002CtrllinePhotodiodeModeEntry OBJECT-TYPE
	SYNTAX Pmc1002CtrllinePhotodiodeModeEntry
	MAX-ACCESS not-accessible
	STATUS current
	DESCRIPTION
        "
        Row definition for the pmc1002CtrllinePhotodiodeMode
        table
        "
	INDEX   { pmc1002CtrllinePhotodiodeModeIndex }
	::= { pmc1002CtrllinePhotodiodeModeTable 1 }


Pmc1002CtrllinePhotodiodeModeEntry ::=
	SEQUENCE {
	pmc1002CtrllinePhotodiodeModeIndex
		INTEGER,
	pmc1002CtrllinePhotodiodeModePortn
		Pmc1002OtxMode
	}


pmc1002CtrllinePhotodiodeModeIndex OBJECT-TYPE
	SYNTAX  INTEGER(0..128)
	MAX-ACCESS  read-only
	STATUS current
	DESCRIPTION
        "
        Index definition for the pmc1002CtrllinePhotodiodeMode
        table
        "
	::= { pmc1002CtrllinePhotodiodeModeEntry 1 }


pmc1002CtrllinePhotodiodeModePortn OBJECT-TYPE
	SYNTAX  Pmc1002OtxMode
	MAX-ACCESS read-write
	STATUS current
	DESCRIPTION
        "
        OTX TLH Rx Sens. Mode :This OID
        defines the Rx sensiblity mode
         of the Line OTX TLH  <Help>
         This control defines the receiver
        sensibility mode of the Line OTX
        TLH Laser (OTX60, OTX80 or Custom)
        "
	::= { pmc1002CtrllinePhotodiodeModeEntry 2 }


--- *********************************************************
---     TABLE for the pmc1002CtrllinePhotodiodeValue articles
--- *********************************************************

pmc1002CtrllinePhotodiodeValueTable OBJECT-TYPE
	SYNTAX  SEQUENCE OF Pmc1002CtrllinePhotodiodeValueEntry
	MAX-ACCESS not-accessible
	STATUS current
	DESCRIPTION
        "
        List of pmc1002CtrllinePhotodiodeValue
        Article
        "
	::= { pmc1002CtrlLine 214 }


pmc1002CtrllinePhotodiodeValueEntry OBJECT-TYPE
	SYNTAX Pmc1002CtrllinePhotodiodeValueEntry
	MAX-ACCESS not-accessible
	STATUS current
	DESCRIPTION
        "
        Row definition for the pmc1002CtrllinePhotodiodeValue
        table
        "
	INDEX   { pmc1002CtrllinePhotodiodeValueIndex }
	::= { pmc1002CtrllinePhotodiodeValueTable 1 }


Pmc1002CtrllinePhotodiodeValueEntry ::=
	SEQUENCE {
	pmc1002CtrllinePhotodiodeValueIndex
		INTEGER,
	pmc1002CtrllinePhotodiodeValuePortn
		Pmc1002AdjustValue
	}


pmc1002CtrllinePhotodiodeValueIndex OBJECT-TYPE
	SYNTAX  INTEGER(0..128)
	MAX-ACCESS  read-only
	STATUS current
	DESCRIPTION
        "
        Index definition for the pmc1002CtrllinePhotodiodeValue
        table
        "
	::= { pmc1002CtrllinePhotodiodeValueEntry 1 }


pmc1002CtrllinePhotodiodeValuePortn OBJECT-TYPE
	SYNTAX  Pmc1002AdjustValue
	MAX-ACCESS read-write
	STATUS current
	DESCRIPTION
        "
        OTX TLH Rx Sensibility :This OID
        sets the Rx sensibility of the
         Line OTX TLH (custom mode only)
         <Help>   This control defines
         the receiver sensibility value
        (only in Custom mode) of the Line
        OTX TLH Laser
        "
	::= { pmc1002CtrllinePhotodiodeValueEntry 2 }


--- *********************************************************
---     TABLE for the pmc1002CtrllinePowerLaser articles
--- *********************************************************

pmc1002CtrllinePowerLaserTable OBJECT-TYPE
	SYNTAX  SEQUENCE OF Pmc1002CtrllinePowerLaserEntry
	MAX-ACCESS not-accessible
	STATUS current
	DESCRIPTION
        "
        List of pmc1002CtrllinePowerLaser
        Article
        "
	::= { pmc1002CtrlLine 215 }


pmc1002CtrllinePowerLaserEntry OBJECT-TYPE
	SYNTAX Pmc1002CtrllinePowerLaserEntry
	MAX-ACCESS not-accessible
	STATUS current
	DESCRIPTION
        "
        Row definition for the pmc1002CtrllinePowerLaser
        table
        "
	INDEX   { pmc1002CtrllinePowerLaserIndex }
	::= { pmc1002CtrllinePowerLaserTable 1 }


Pmc1002CtrllinePowerLaserEntry ::=
	SEQUENCE {
	pmc1002CtrllinePowerLaserIndex
		INTEGER,
	pmc1002CtrllinePowerLaserPortn
		INTEGER
	}


pmc1002CtrllinePowerLaserIndex OBJECT-TYPE
	SYNTAX  INTEGER(0..128)
	MAX-ACCESS  read-only
	STATUS current
	DESCRIPTION
        "
        Index definition for the pmc1002CtrllinePowerLaser
        table
        "
	::= { pmc1002CtrllinePowerLaserEntry 1 }


pmc1002CtrllinePowerLaserPortn OBJECT-TYPE
	SYNTAX  INTEGER (0..255)
	MAX-ACCESS read-write
	STATUS current
	DESCRIPTION
        "
        Laser Output Power [3-5] :This
        OID sets the output power value
        on the laser of the Line OTX TLH
        (AV=Power*10+158)  (Unit = dBm)
         <Help>   This control defines
         the start-up output power of the
        Line OTX TLH
        "
	::= { pmc1002CtrllinePowerLaserEntry 2 }


--- *********************************************************
---     TABLE for the pmc1002CtrlotxVlhReset articles
--- *********************************************************

pmc1002CtrlotxVlhResetTable OBJECT-TYPE
	SYNTAX  SEQUENCE OF Pmc1002CtrlotxVlhResetEntry
	MAX-ACCESS not-accessible
	STATUS current
	DESCRIPTION
        "
        List of pmc1002CtrlotxVlhReset
        Article
        "
	::= { pmc1002CtrlLine 216 }


pmc1002CtrlotxVlhResetEntry OBJECT-TYPE
	SYNTAX Pmc1002CtrlotxVlhResetEntry
	MAX-ACCESS not-accessible
	STATUS current
	DESCRIPTION
        "
        Row definition for the pmc1002CtrlotxVlhReset
        table
        "
	INDEX   { pmc1002CtrlotxVlhResetIndex }
	::= { pmc1002CtrlotxVlhResetTable 1 }


Pmc1002CtrlotxVlhResetEntry ::=
	SEQUENCE {
	pmc1002CtrlotxVlhResetIndex
		INTEGER,
	pmc1002CtrlotxVlhResetPortn
		EkiState
	}


pmc1002CtrlotxVlhResetIndex OBJECT-TYPE
	SYNTAX  INTEGER(0..128)
	MAX-ACCESS  read-only
	STATUS current
	DESCRIPTION
        "
        Index definition for the pmc1002CtrlotxVlhReset
        table
        "
	::= { pmc1002CtrlotxVlhResetEntry 1 }


pmc1002CtrlotxVlhResetPortn OBJECT-TYPE
	SYNTAX  EkiState
	MAX-ACCESS read-write
	STATUS current
	DESCRIPTION
        "
        OTX-VLH Reset :This OID resets
        the OTX-VLH module  <Help>  This
        control resets the OTX-VLH and
         its parameters
        "
	::= { pmc1002CtrlotxVlhResetEntry 2 }


--- *********************************************************
---     TABLE for the pmc1002CtrllineLoopTransceiver articles
--- *********************************************************

pmc1002CtrllineLoopTransceiverTable OBJECT-TYPE
	SYNTAX  SEQUENCE OF Pmc1002CtrllineLoopTransceiverEntry
	MAX-ACCESS not-accessible
	STATUS current
	DESCRIPTION
        "
        List of pmc1002CtrllineLoopTransceiver
        Article
        "
	::= { pmc1002CtrlLine 218 }


pmc1002CtrllineLoopTransceiverEntry OBJECT-TYPE
	SYNTAX Pmc1002CtrllineLoopTransceiverEntry
	MAX-ACCESS not-accessible
	STATUS current
	DESCRIPTION
        "
        Row definition for the pmc1002CtrllineLoopTransceiver
        table
        "
	INDEX   { pmc1002CtrllineLoopTransceiverIndex }
	::= { pmc1002CtrllineLoopTransceiverTable 1 }


Pmc1002CtrllineLoopTransceiverEntry ::=
	SEQUENCE {
	pmc1002CtrllineLoopTransceiverIndex
		INTEGER,
	pmc1002CtrllineLoopTransceiverPortn
		EkiState
	}


pmc1002CtrllineLoopTransceiverIndex OBJECT-TYPE
	SYNTAX  INTEGER(0..128)
	MAX-ACCESS  read-only
	STATUS current
	DESCRIPTION
        "
        Index definition for the pmc1002CtrllineLoopTransceiver
        table
        "
	::= { pmc1002CtrllineLoopTransceiverEntry 1 }


pmc1002CtrllineLoopTransceiverPortn OBJECT-TYPE
	SYNTAX  EkiState
	MAX-ACCESS read-write
	STATUS current
	DESCRIPTION
        "
        Line Terminal Loopback :This OID
        operates a Line Terminal Loopback,
        looping line input signal on the
        line output port. The loop is located
        on all client transceivers  <Help>
        This maintenance parameter operates
        a Line Terminal Loopback, looping
        line input signal on the line output
        port. The loop is located on all
        client transceivers.
        "
	::= { pmc1002CtrllineLoopTransceiverEntry 2 }


--- *********************************************************
---     TABLE for the pmc1002CtrlclientResetAllCount articles
--- *********************************************************

pmc1002CtrlclientResetAllCountTable OBJECT-TYPE
	SYNTAX  SEQUENCE OF Pmc1002CtrlclientResetAllCountEntry
	MAX-ACCESS not-accessible
	STATUS current
	DESCRIPTION
        "
        List of pmc1002CtrlclientResetAllCount
        Article
        "
	::= { pmc1002CtrlClient 271 }


pmc1002CtrlclientResetAllCountEntry OBJECT-TYPE
	SYNTAX Pmc1002CtrlclientResetAllCountEntry
	MAX-ACCESS not-accessible
	STATUS current
	DESCRIPTION
        "
        Row definition for the pmc1002CtrlclientResetAllCount
        table
        "
	INDEX   { pmc1002CtrlclientResetAllCountIndex }
	::= { pmc1002CtrlclientResetAllCountTable 1 }


Pmc1002CtrlclientResetAllCountEntry ::=
	SEQUENCE {
	pmc1002CtrlclientResetAllCountIndex
		INTEGER,
	pmc1002CtrlclientResetAllCountsPortn
		EkiState
	}


pmc1002CtrlclientResetAllCountIndex OBJECT-TYPE
	SYNTAX  INTEGER(0..128)
	MAX-ACCESS  read-only
	STATUS current
	DESCRIPTION
        "
        Index definition for the pmc1002CtrlclientResetAllCount
        table
        "
	::= { pmc1002CtrlclientResetAllCountEntry 1 }


pmc1002CtrlclientResetAllCountsPortn OBJECT-TYPE
	SYNTAX  EkiState
	MAX-ACCESS read-write
	STATUS current
	DESCRIPTION
        "
        Client Counters Reset :This OID
        resets every counter on the client
        port  <Help>   This control operates
        a reset on the statistics current
        ,previous and history client port
        counters
        "
	::= { pmc1002CtrlclientResetAllCountEntry 2 }


--- *********************************************************
---     TABLE for the pmc1002CtrllineResetAllCount articles
--- *********************************************************

pmc1002CtrllineResetAllCountTable OBJECT-TYPE
	SYNTAX  SEQUENCE OF Pmc1002CtrllineResetAllCountEntry
	MAX-ACCESS not-accessible
	STATUS current
	DESCRIPTION
        "
        List of pmc1002CtrllineResetAllCount
        Article
        "
	::= { pmc1002CtrlLine 335 }


pmc1002CtrllineResetAllCountEntry OBJECT-TYPE
	SYNTAX Pmc1002CtrllineResetAllCountEntry
	MAX-ACCESS not-accessible
	STATUS current
	DESCRIPTION
        "
        Row definition for the pmc1002CtrllineResetAllCount
        table
        "
	INDEX   { pmc1002CtrllineResetAllCountIndex }
	::= { pmc1002CtrllineResetAllCountTable 1 }


Pmc1002CtrllineResetAllCountEntry ::=
	SEQUENCE {
	pmc1002CtrllineResetAllCountIndex
		INTEGER,
	pmc1002CtrllineResetAllCountsPortn
		EkiState
	}


pmc1002CtrllineResetAllCountIndex OBJECT-TYPE
	SYNTAX  INTEGER(0..128)
	MAX-ACCESS  read-only
	STATUS current
	DESCRIPTION
        "
        Index definition for the pmc1002CtrllineResetAllCount
        table
        "
	::= { pmc1002CtrllineResetAllCountEntry 1 }


pmc1002CtrllineResetAllCountsPortn OBJECT-TYPE
	SYNTAX  EkiState
	MAX-ACCESS read-write
	STATUS current
	DESCRIPTION
        "
        Line Counters Reset :This OID
         resets every counter on the line
        port  <Help>   This control operates
        a reset on the statistics current
        ,previous and history line port
        counters
        "
	::= { pmc1002CtrllineResetAllCountEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pmc1002CntclientUpErrCnt articles
--- *********************************************************

pmc1002CntclientUpErrCntTable OBJECT-TYPE
	SYNTAX  SEQUENCE OF Pmc1002CntclientUpErrCntEntry
	MAX-ACCESS not-accessible
	STATUS current
	DESCRIPTION
        "
        List of pmc1002CntclientUpErrCnt
        Article
        "
	::= { pmc1002CntClient 32 }


pmc1002CntclientUpErrCntEntry OBJECT-TYPE
	SYNTAX Pmc1002CntclientUpErrCntEntry
	MAX-ACCESS not-accessible
	STATUS current
	DESCRIPTION
        "
        Row definition for the pmc1002CntclientUpErrCnt
        table
        "
	INDEX   { pmc1002CntclientUpErrCntIndex }
	::= { pmc1002CntclientUpErrCntTable 1 }


Pmc1002CntclientUpErrCntEntry ::=
	SEQUENCE {
	pmc1002CntclientUpErrCntIndex
		INTEGER,
	pmc1002CntclientUpErrCntValuePortn
		Counter32,
	pmc1002CntclientUpErrCntErrorPortn
		EkiOnOff,
	pmc1002CntclientUpErrCntOverloadPortn
		EkiOnOff
	}


pmc1002CntclientUpErrCntIndex OBJECT-TYPE
	SYNTAX  INTEGER(0..128)
	MAX-ACCESS  read-only
	STATUS current
	DESCRIPTION
        "
        Index definition for the pmc1002CntclientUpErrCnt
        table
        "
	::= { pmc1002CntclientUpErrCntEntry 1 }


pmc1002CntclientUpErrCntValuePortn OBJECT-TYPE
	SYNTAX  Counter32
	MAX-ACCESS read-only
	STATUS current
	DESCRIPTION
        "
        Client Input Errors :This counter
        is increased each time a FCS error
        is detected in 10GbE mode or a
         B1 error is detected in OC-192/STM-64
        mode on the client input stream
         <Help>  This counter gives the
        number of FCS errors or B1 errors
        on the client input port
        "
	::= { pmc1002CntclientUpErrCntEntry 2 }


pmc1002CntclientUpErrCntErrorPortn OBJECT-TYPE
	SYNTAX  EkiOnOff
	MAX-ACCESS read-only
	STATUS current
	DESCRIPTION
        "
        Client Counter Error :This OID
        when set indicates the FCS error
        counter value is invalid on input
        Port
        "
	::= { pmc1002CntclientUpErrCntEntry 3 }


pmc1002CntclientUpErrCntOverloadPortn OBJECT-TYPE
	SYNTAX  EkiOnOff
	MAX-ACCESS read-only
	STATUS current
	DESCRIPTION
        "
        Client Counter Overload :This
         OID when set indicates a FCS error
        counter overload on input Port
        "
	::= { pmc1002CntclientUpErrCntEntry 4 }


--- *********************************************************
---     TABLE for the pmc1002CntclientUpTimCnt articles
--- *********************************************************

pmc1002CntclientUpTimCntTable OBJECT-TYPE
	SYNTAX  SEQUENCE OF Pmc1002CntclientUpTimCntEntry
	MAX-ACCESS not-accessible
	STATUS current
	DESCRIPTION
        "
        List of pmc1002CntclientUpTimCnt
        Article
        "
	::= { pmc1002CntClient 40 }


pmc1002CntclientUpTimCntEntry OBJECT-TYPE
	SYNTAX Pmc1002CntclientUpTimCntEntry
	MAX-ACCESS not-accessible
	STATUS current
	DESCRIPTION
        "
        Row definition for the pmc1002CntclientUpTimCnt
        table
        "
	INDEX   { pmc1002CntclientUpTimCntIndex }
	::= { pmc1002CntclientUpTimCntTable 1 }


Pmc1002CntclientUpTimCntEntry ::=
	SEQUENCE {
	pmc1002CntclientUpTimCntIndex
		INTEGER,
	pmc1002CntclientUpTimCntValuePortn
		Counter32,
	pmc1002CntclientUpTimCntErrorPortn
		EkiOnOff,
	pmc1002CntclientUpTimCntOverloadPortn
		EkiOnOff
	}


pmc1002CntclientUpTimCntIndex OBJECT-TYPE
	SYNTAX  INTEGER(0..128)
	MAX-ACCESS  read-only
	STATUS current
	DESCRIPTION
        "
        Index definition for the pmc1002CntclientUpTimCnt
        table
        "
	::= { pmc1002CntclientUpTimCntEntry 1 }


pmc1002CntclientUpTimCntValuePortn OBJECT-TYPE
	SYNTAX  Counter32
	MAX-ACCESS read-only
	STATUS current
	DESCRIPTION
        "
        Client Upstream Timer Counter
         :This is the timing counter dedicated
        to the upstream access counters.
        It is incremented every 125 us.
        "
	::= { pmc1002CntclientUpTimCntEntry 2 }


pmc1002CntclientUpTimCntErrorPortn OBJECT-TYPE
	SYNTAX  EkiOnOff
	MAX-ACCESS read-only
	STATUS current
	DESCRIPTION
        "
        Client Counter Error :This OID
        when set indicates the upstream
        timing counter value is invalid
        on Port
        "
	::= { pmc1002CntclientUpTimCntEntry 3 }


pmc1002CntclientUpTimCntOverloadPortn OBJECT-TYPE
	SYNTAX  EkiOnOff
	MAX-ACCESS read-only
	STATUS current
	DESCRIPTION
        "
        Client Counter Overload :This
         OID when set indicates a upstream
        timing counter overload on Port
        "
	::= { pmc1002CntclientUpTimCntEntry 4 }


--- *********************************************************
---     TABLE for the pmc1002CntclientDwErrCnt articles
--- *********************************************************

pmc1002CntclientDwErrCntTable OBJECT-TYPE
	SYNTAX  SEQUENCE OF Pmc1002CntclientDwErrCntEntry
	MAX-ACCESS not-accessible
	STATUS current
	DESCRIPTION
        "
        List of pmc1002CntclientDwErrCnt
        Article
        "
	::= { pmc1002CntClient 64 }


pmc1002CntclientDwErrCntEntry OBJECT-TYPE
	SYNTAX Pmc1002CntclientDwErrCntEntry
	MAX-ACCESS not-accessible
	STATUS current
	DESCRIPTION
        "
        Row definition for the pmc1002CntclientDwErrCnt
        table
        "
	INDEX   { pmc1002CntclientDwErrCntIndex }
	::= { pmc1002CntclientDwErrCntTable 1 }


Pmc1002CntclientDwErrCntEntry ::=
	SEQUENCE {
	pmc1002CntclientDwErrCntIndex
		INTEGER,
	pmc1002CntclientDwErrCntValuePortn
		Counter32,
	pmc1002CntclientDwErrCntErrorPortn
		EkiOnOff,
	pmc1002CntclientDwErrCntOverloadPortn
		EkiOnOff
	}


pmc1002CntclientDwErrCntIndex OBJECT-TYPE
	SYNTAX  INTEGER(0..128)
	MAX-ACCESS  read-only
	STATUS current
	DESCRIPTION
        "
        Index definition for the pmc1002CntclientDwErrCnt
        table
        "
	::= { pmc1002CntclientDwErrCntEntry 1 }


pmc1002CntclientDwErrCntValuePortn OBJECT-TYPE
	SYNTAX  Counter32
	MAX-ACCESS read-only
	STATUS current
	DESCRIPTION
        "
        Client Output Errors :This counter
        is increased each time a B1/FCS
        error is detected on the client
        output stream  <Help>  This counter
        gives the number of FCS errors
         or B1 errors on the client output
        port
        "
	::= { pmc1002CntclientDwErrCntEntry 2 }


pmc1002CntclientDwErrCntErrorPortn OBJECT-TYPE
	SYNTAX  EkiOnOff
	MAX-ACCESS read-only
	STATUS current
	DESCRIPTION
        "
        Client Counter Error :This OID
        when set indicates the FCS error
        counter value is invalid on output
        Port
        "
	::= { pmc1002CntclientDwErrCntEntry 3 }


pmc1002CntclientDwErrCntOverloadPortn OBJECT-TYPE
	SYNTAX  EkiOnOff
	MAX-ACCESS read-only
	STATUS current
	DESCRIPTION
        "
        Client Counter Overload :This
         OID when set indicates a FCS error
        counter overload on output Port
        "
	::= { pmc1002CntclientDwErrCntEntry 4 }


--- *********************************************************
---     TABLE for the pmc1002CntclientDwTimCnt articles
--- *********************************************************

pmc1002CntclientDwTimCntTable OBJECT-TYPE
	SYNTAX  SEQUENCE OF Pmc1002CntclientDwTimCntEntry
	MAX-ACCESS not-accessible
	STATUS current
	DESCRIPTION
        "
        List of pmc1002CntclientDwTimCnt
        Article
        "
	::= { pmc1002CntClient 72 }


pmc1002CntclientDwTimCntEntry OBJECT-TYPE
	SYNTAX Pmc1002CntclientDwTimCntEntry
	MAX-ACCESS not-accessible
	STATUS current
	DESCRIPTION
        "
        Row definition for the pmc1002CntclientDwTimCnt
        table
        "
	INDEX   { pmc1002CntclientDwTimCntIndex }
	::= { pmc1002CntclientDwTimCntTable 1 }


Pmc1002CntclientDwTimCntEntry ::=
	SEQUENCE {
	pmc1002CntclientDwTimCntIndex
		INTEGER,
	pmc1002CntclientDwTimCntValuePortn
		Counter32,
	pmc1002CntclientDwTimCntErrorPortn
		EkiOnOff,
	pmc1002CntclientDwTimCntOverloadPortn
		EkiOnOff
	}


pmc1002CntclientDwTimCntIndex OBJECT-TYPE
	SYNTAX  INTEGER(0..128)
	MAX-ACCESS  read-only
	STATUS current
	DESCRIPTION
        "
        Index definition for the pmc1002CntclientDwTimCnt
        table
        "
	::= { pmc1002CntclientDwTimCntEntry 1 }


pmc1002CntclientDwTimCntValuePortn OBJECT-TYPE
	SYNTAX  Counter32
	MAX-ACCESS read-only
	STATUS current
	DESCRIPTION
        "
        Client Downstream Timer Counter
        :This is the timing counter dedicated
        to the downstream access counters.
        It is incremented every 125 us.
        "
	::= { pmc1002CntclientDwTimCntEntry 2 }


pmc1002CntclientDwTimCntErrorPortn OBJECT-TYPE
	SYNTAX  EkiOnOff
	MAX-ACCESS read-only
	STATUS current
	DESCRIPTION
        "
        Client Counter Error :This OID
        when set indicates the downstream
        timer counter value is invalid
         on Port
        "
	::= { pmc1002CntclientDwTimCntEntry 3 }


pmc1002CntclientDwTimCntOverloadPortn OBJECT-TYPE
	SYNTAX  EkiOnOff
	MAX-ACCESS read-only
	STATUS current
	DESCRIPTION
        "
        Client Counter Overload :This
         OID when set indicates a downstream
        timer counter overload on Port
        "
	::= { pmc1002CntclientDwTimCntEntry 4 }


--- *********************************************************
---     TABLE for the pmc1002CntlineDfrmErrCnt articles
--- *********************************************************

pmc1002CntlineDfrmErrCntTable OBJECT-TYPE
	SYNTAX  SEQUENCE OF Pmc1002CntlineDfrmErrCntEntry
	MAX-ACCESS not-accessible
	STATUS current
	DESCRIPTION
        "
        List of pmc1002CntlineDfrmErrCnt
        Article
        "
	::= { pmc1002CntLine 152 }


pmc1002CntlineDfrmErrCntEntry OBJECT-TYPE
	SYNTAX Pmc1002CntlineDfrmErrCntEntry
	MAX-ACCESS not-accessible
	STATUS current
	DESCRIPTION
        "
        Row definition for the pmc1002CntlineDfrmErrCnt
        table
        "
	INDEX   { pmc1002CntlineDfrmErrCntIndex }
	::= { pmc1002CntlineDfrmErrCntTable 1 }


Pmc1002CntlineDfrmErrCntEntry ::=
	SEQUENCE {
	pmc1002CntlineDfrmErrCntIndex
		INTEGER,
	pmc1002CntlineDfrmErrCntValuePortn
		Counter32,
	pmc1002CntlineDfrmErrCntErrorPortn
		EkiOnOff,
	pmc1002CntlineDfrmErrCntOverloadPortn
		EkiOnOff
	}


pmc1002CntlineDfrmErrCntIndex OBJECT-TYPE
	SYNTAX  INTEGER(0..128)
	MAX-ACCESS  read-only
	STATUS current
	DESCRIPTION
        "
        Index definition for the pmc1002CntlineDfrmErrCnt
        table
        "
	::= { pmc1002CntlineDfrmErrCntEntry 1 }


pmc1002CntlineDfrmErrCntValuePortn OBJECT-TYPE
	SYNTAX  Counter32
	MAX-ACCESS read-only
	STATUS current
	DESCRIPTION
        "
        Line Input B1 Errors :This counter
        is incremented each time a B1 error
        is detected on the Deframer input
        stream.  <Help>  This counter gives
        the number of B1 errors on the
         line port
        "
	::= { pmc1002CntlineDfrmErrCntEntry 2 }


pmc1002CntlineDfrmErrCntErrorPortn OBJECT-TYPE
	SYNTAX  EkiOnOff
	MAX-ACCESS read-only
	STATUS current
	DESCRIPTION
        "
        Line Counter Error :This OID when
        set indicates the B1 error counter
        value is invalid on Port
        "
	::= { pmc1002CntlineDfrmErrCntEntry 3 }


pmc1002CntlineDfrmErrCntOverloadPortn OBJECT-TYPE
	SYNTAX  EkiOnOff
	MAX-ACCESS read-only
	STATUS current
	DESCRIPTION
        "
        Line Counter Overload :This OID
        when set indicates a B1 error counter
        overload on Port
        "
	::= { pmc1002CntlineDfrmErrCntEntry 4 }


--- *********************************************************
---     TABLE for the pmc1002CntlineDfrmTimCnt articles
--- *********************************************************

pmc1002CntlineDfrmTimCntTable OBJECT-TYPE
	SYNTAX  SEQUENCE OF Pmc1002CntlineDfrmTimCntEntry
	MAX-ACCESS not-accessible
	STATUS current
	DESCRIPTION
        "
        List of pmc1002CntlineDfrmTimCnt
        Article
        "
	::= { pmc1002CntLine 153 }


pmc1002CntlineDfrmTimCntEntry OBJECT-TYPE
	SYNTAX Pmc1002CntlineDfrmTimCntEntry
	MAX-ACCESS not-accessible
	STATUS current
	DESCRIPTION
        "
        Row definition for the pmc1002CntlineDfrmTimCnt
        table
        "
	INDEX   { pmc1002CntlineDfrmTimCntIndex }
	::= { pmc1002CntlineDfrmTimCntTable 1 }


Pmc1002CntlineDfrmTimCntEntry ::=
	SEQUENCE {
	pmc1002CntlineDfrmTimCntIndex
		INTEGER,
	pmc1002CntlineDfrmTimCntValuePortn
		Counter32,
	pmc1002CntlineDfrmTimCntErrorPortn
		EkiOnOff,
	pmc1002CntlineDfrmTimCntOverloadPortn
		EkiOnOff
	}


pmc1002CntlineDfrmTimCntIndex OBJECT-TYPE
	SYNTAX  INTEGER(0..128)
	MAX-ACCESS  read-only
	STATUS current
	DESCRIPTION
        "
        Index definition for the pmc1002CntlineDfrmTimCnt
        table
        "
	::= { pmc1002CntlineDfrmTimCntEntry 1 }


pmc1002CntlineDfrmTimCntValuePortn OBJECT-TYPE
	SYNTAX  Counter32
	MAX-ACCESS read-only
	STATUS current
	DESCRIPTION
        "
        Line Timer Counter :This is the
        timing counter dedicated to the
        downstream deframer counters. It
        is incremented every 125 us.
        "
	::= { pmc1002CntlineDfrmTimCntEntry 2 }


pmc1002CntlineDfrmTimCntErrorPortn OBJECT-TYPE
	SYNTAX  EkiOnOff
	MAX-ACCESS read-only
	STATUS current
	DESCRIPTION
        "
        Line Counter Error :This OID when
        set indicates the deframer timer
        counter value is invalid on Port
        "
	::= { pmc1002CntlineDfrmTimCntEntry 3 }


pmc1002CntlineDfrmTimCntOverloadPortn OBJECT-TYPE
	SYNTAX  EkiOnOff
	MAX-ACCESS read-only
	STATUS current
	DESCRIPTION
        "
        Line Counter Overload :This OID
        when set indicates a deframer timer
        counter overload on Port
        "
	::= { pmc1002CntlineDfrmTimCntEntry 4 }


--- *********************************************************
---     TABLE for the pmc1002CntlineDfrmPrimErrCnt articles
--- *********************************************************

pmc1002CntlineDfrmPrimErrCntTable OBJECT-TYPE
	SYNTAX  SEQUENCE OF Pmc1002CntlineDfrmPrimErrCntEntry
	MAX-ACCESS not-accessible
	STATUS current
	DESCRIPTION
        "
        List of pmc1002CntlineDfrmPrimErrCnt
        Article
        "
	::= { pmc1002CntLine 154 }


pmc1002CntlineDfrmPrimErrCntEntry OBJECT-TYPE
	SYNTAX Pmc1002CntlineDfrmPrimErrCntEntry
	MAX-ACCESS not-accessible
	STATUS current
	DESCRIPTION
        "
        Row definition for the pmc1002CntlineDfrmPrimErrCnt
        table
        "
	INDEX   { pmc1002CntlineDfrmPrimErrCntIndex }
	::= { pmc1002CntlineDfrmPrimErrCntTable 1 }


Pmc1002CntlineDfrmPrimErrCntEntry ::=
	SEQUENCE {
	pmc1002CntlineDfrmPrimErrCntIndex
		INTEGER,
	pmc1002CntlineDfrmPrimErrCntValuePortn
		Counter32,
	pmc1002CntlineDfrmPrimErrCntErrorPortn
		EkiOnOff,
	pmc1002CntlineDfrmPrimErrCntOverloadPortn
		EkiOnOff
	}


pmc1002CntlineDfrmPrimErrCntIndex OBJECT-TYPE
	SYNTAX  INTEGER(0..128)
	MAX-ACCESS  read-only
	STATUS current
	DESCRIPTION
        "
        Index definition for the pmc1002CntlineDfrmPrimErrCnt
        table
        "
	::= { pmc1002CntlineDfrmPrimErrCntEntry 1 }


pmc1002CntlineDfrmPrimErrCntValuePortn OBJECT-TYPE
	SYNTAX  Counter32
	MAX-ACCESS read-only
	STATUS current
	DESCRIPTION
        "
        Line Input FEC Corrected Errors
        :This counter is incremented each
        time an error is corrected by the
        Forward Error Correction decoder
         <Help>  This counter gives the
        number of errors corrected by the
        FEC on the line port
        "
	::= { pmc1002CntlineDfrmPrimErrCntEntry 2 }


pmc1002CntlineDfrmPrimErrCntErrorPortn OBJECT-TYPE
	SYNTAX  EkiOnOff
	MAX-ACCESS read-only
	STATUS current
	DESCRIPTION
        "
        Line FEC Counter Error :This bit
        when set indicates the FEC counter
        value is invalid on Port
        "
	::= { pmc1002CntlineDfrmPrimErrCntEntry 3 }


pmc1002CntlineDfrmPrimErrCntOverloadPortn OBJECT-TYPE
	SYNTAX  EkiOnOff
	MAX-ACCESS read-only
	STATUS current
	DESCRIPTION
        "
        Line FEC Counter Overload :This
        bit when set indicates a FEC counter
        overload on Port
        "
	::= { pmc1002CntlineDfrmPrimErrCntEntry 4 }


pmc1002CntCountersReset  OBJECT-TYPE
	SYNTAX EkiOnOff
	MAX-ACCESS read-write
	STATUS current
	DESCRIPTION
	"Counters Reset:This OID resets and restarts all the counters"
	::= { pmc1002counters  259 }

pmc1002CntCountersStop  OBJECT-TYPE
	SYNTAX EkiOnOff
	MAX-ACCESS read-write
	STATUS current
	DESCRIPTION
	"Counters stop:This OID stops all the counters"
	::= { pmc1002counters 260 }






--- *****************************************************
--- $$$$$$$$$$$$$$$$$$$$$$$$$$$$$$$$$$$$$$$$$$$$$$$$$$$$$
---     RMON
--- $$$$$$$$$$$$$$$$$$$$$$$$$$$$$$$$$$$$$$$$$$$$$$$$$$$$$
--- *****************************************************



--- *********************************************************
---     TABLE for the pmc1002MonupRmonByteCnt articles
--- *********************************************************

pmc1002MonupRmonByteCntTable OBJECT-TYPE
	SYNTAX  SEQUENCE OF Pmc1002MonupRmonByteCntEntry
	MAX-ACCESS not-accessible
	STATUS current
	DESCRIPTION
        "
        List of pmc1002MonupRmonByteCnt
        Article
        "
	::= { pmc1002RmonClient 16 }


pmc1002MonupRmonByteCntEntry OBJECT-TYPE
	SYNTAX Pmc1002MonupRmonByteCntEntry
	MAX-ACCESS not-accessible
	STATUS current
	DESCRIPTION
        "
        Row definition for the pmc1002MonupRmonByteCnt
        table
        "
	INDEX   { pmc1002MonupRmonByteCntIndex }
	::= { pmc1002MonupRmonByteCntTable 1 }


Pmc1002MonupRmonByteCntEntry ::=
	SEQUENCE {
	pmc1002MonupRmonByteCntIndex
		INTEGER,
	pmc1002MonupRmonByteCntValuePortn
		Counter64,
	pmc1002MonupRmonByteCntErrorPortn
		EkiOnOff,
	pmc1002MonupRmonByteCntOverloadPortn
		EkiOnOff
	}


pmc1002MonupRmonByteCntIndex OBJECT-TYPE
	SYNTAX  INTEGER(0..128)
	MAX-ACCESS  read-only
	STATUS current
	DESCRIPTION
        "
        Index definition for the pmc1002MonupRmonByteCnt
        table
        "
	::= { pmc1002MonupRmonByteCntEntry 1 }


pmc1002MonupRmonByteCntValuePortn OBJECT-TYPE
	SYNTAX  Counter64
	MAX-ACCESS read-only
	STATUS current
	DESCRIPTION
        "
        Client Input Bytes :This counter
        is increased each time a data byte
        is received on the client port
          <Help>  This counter gives the
        number of bytes received on the
        client port
        "
	::= { pmc1002MonupRmonByteCntEntry 2 }


pmc1002MonupRmonByteCntErrorPortn OBJECT-TYPE
	SYNTAX  EkiOnOff
	MAX-ACCESS read-only
	STATUS current
	DESCRIPTION
        "
        Input Bytes Counter Error :This
        OID when set indicates the input
        Bytes counter value is invalid
         on client port
        "
	::= { pmc1002MonupRmonByteCntEntry 3 }


pmc1002MonupRmonByteCntOverloadPortn OBJECT-TYPE
	SYNTAX  EkiOnOff
	MAX-ACCESS read-only
	STATUS current
	DESCRIPTION
        "
        Input Bytes Counter Overload :This
        OID when set indicates an input
        Bytes counter overload on client
        port
        "
	::= { pmc1002MonupRmonByteCntEntry 4 }


--- *********************************************************
---     TABLE for the pmc1002MonupRmonCrcErrorCnt articles
--- *********************************************************

pmc1002MonupRmonCrcErrorCntTable OBJECT-TYPE
	SYNTAX  SEQUENCE OF Pmc1002MonupRmonCrcErrorCntEntry
	MAX-ACCESS not-accessible
	STATUS current
	DESCRIPTION
        "
        List of pmc1002MonupRmonCrcErrorCnt
        Article
        "
	::= { pmc1002RmonClient 24 }


pmc1002MonupRmonCrcErrorCntEntry OBJECT-TYPE
	SYNTAX Pmc1002MonupRmonCrcErrorCntEntry
	MAX-ACCESS not-accessible
	STATUS current
	DESCRIPTION
        "
        Row definition for the pmc1002MonupRmonCrcErrorCnt
        table
        "
	INDEX   { pmc1002MonupRmonCrcErrorCntIndex }
	::= { pmc1002MonupRmonCrcErrorCntTable 1 }


Pmc1002MonupRmonCrcErrorCntEntry ::=
	SEQUENCE {
	pmc1002MonupRmonCrcErrorCntIndex
		INTEGER,
	pmc1002MonupRmonCrcErrorCntValuePortn
		Counter64,
	pmc1002MonupRmonCrcErrorCntErrorPortn
		EkiOnOff,
	pmc1002MonupRmonCrcErrorCntOverloadPortn
		EkiOnOff
	}


pmc1002MonupRmonCrcErrorCntIndex OBJECT-TYPE
	SYNTAX  INTEGER(0..128)
	MAX-ACCESS  read-only
	STATUS current
	DESCRIPTION
        "
        Index definition for the pmc1002MonupRmonCrcErrorCnt
        table
        "
	::= { pmc1002MonupRmonCrcErrorCntEntry 1 }


pmc1002MonupRmonCrcErrorCntValuePortn OBJECT-TYPE
	SYNTAX  Counter64
	MAX-ACCESS read-only
	STATUS current
	DESCRIPTION
        "
        Client Input CRC Errors :This
         counter is increased each time
        a CRC error is detected on the
         client port.   <Help>  This counter
        gives the number of CRC Errors
         received on the client port
        "
	::= { pmc1002MonupRmonCrcErrorCntEntry 2 }


pmc1002MonupRmonCrcErrorCntErrorPortn OBJECT-TYPE
	SYNTAX  EkiOnOff
	MAX-ACCESS read-only
	STATUS current
	DESCRIPTION
        "
        Input CRC Errors Counter Error
        :This OID when set indicates the
        input CRC Errors counter value
         is invalid on client port
        "
	::= { pmc1002MonupRmonCrcErrorCntEntry 3 }


pmc1002MonupRmonCrcErrorCntOverloadPortn OBJECT-TYPE
	SYNTAX  EkiOnOff
	MAX-ACCESS read-only
	STATUS current
	DESCRIPTION
        "
        Input CRC Errors Counter Overload
        :This OID when set indicates an
        input CRC Errors counter overload
        on client port
        "
	::= { pmc1002MonupRmonCrcErrorCntEntry 4 }


--- *********************************************************
---     TABLE for the pmc1002MonupRmonPacketsCnt articles
--- *********************************************************

pmc1002MonupRmonPacketsCntTable OBJECT-TYPE
	SYNTAX  SEQUENCE OF Pmc1002MonupRmonPacketsCntEntry
	MAX-ACCESS not-accessible
	STATUS current
	DESCRIPTION
        "
        List of pmc1002MonupRmonPacketsCnt
        Article
        "
	::= { pmc1002RmonClient 32 }


pmc1002MonupRmonPacketsCntEntry OBJECT-TYPE
	SYNTAX Pmc1002MonupRmonPacketsCntEntry
	MAX-ACCESS not-accessible
	STATUS current
	DESCRIPTION
        "
        Row definition for the pmc1002MonupRmonPacketsCnt
        table
        "
	INDEX   { pmc1002MonupRmonPacketsCntIndex }
	::= { pmc1002MonupRmonPacketsCntTable 1 }


Pmc1002MonupRmonPacketsCntEntry ::=
	SEQUENCE {
	pmc1002MonupRmonPacketsCntIndex
		INTEGER,
	pmc1002MonupRmonPacketsCntValuePortn
		Counter64,
	pmc1002MonupRmonPacketsCntErrorPortn
		EkiOnOff,
	pmc1002MonupRmonPacketsCntOverloadPortn
		EkiOnOff
	}


pmc1002MonupRmonPacketsCntIndex OBJECT-TYPE
	SYNTAX  INTEGER(0..128)
	MAX-ACCESS  read-only
	STATUS current
	DESCRIPTION
        "
        Index definition for the pmc1002MonupRmonPacketsCnt
        table
        "
	::= { pmc1002MonupRmonPacketsCntEntry 1 }


pmc1002MonupRmonPacketsCntValuePortn OBJECT-TYPE
	SYNTAX  Counter64
	MAX-ACCESS read-only
	STATUS current
	DESCRIPTION
        "
        Client Input Packets :This counter
        is increased each time a packet
        is received on the client port
          <Help>  This counter gives the
        number of packets received on the
        client port
        "
	::= { pmc1002MonupRmonPacketsCntEntry 2 }


pmc1002MonupRmonPacketsCntErrorPortn OBJECT-TYPE
	SYNTAX  EkiOnOff
	MAX-ACCESS read-only
	STATUS current
	DESCRIPTION
        "
        Input Packets Counter Error :This
        OID when set indicates the input
        Packets counter value is invalid
        on client port
        "
	::= { pmc1002MonupRmonPacketsCntEntry 3 }


pmc1002MonupRmonPacketsCntOverloadPortn OBJECT-TYPE
	SYNTAX  EkiOnOff
	MAX-ACCESS read-only
	STATUS current
	DESCRIPTION
        "
        Input Packets Counter Overload
        :This OID when set indicates an
        input Packets counter overload
         on client port
        "
	::= { pmc1002MonupRmonPacketsCntEntry 4 }


--- *********************************************************
---     TABLE for the pmc1002MonupRmonBroadcastCnt articles
--- *********************************************************

pmc1002MonupRmonBroadcastCntTable OBJECT-TYPE
	SYNTAX  SEQUENCE OF Pmc1002MonupRmonBroadcastCntEntry
	MAX-ACCESS not-accessible
	STATUS current
	DESCRIPTION
        "
        List of pmc1002MonupRmonBroadcastCnt
        Article
        "
	::= { pmc1002RmonClient 40 }


pmc1002MonupRmonBroadcastCntEntry OBJECT-TYPE
	SYNTAX Pmc1002MonupRmonBroadcastCntEntry
	MAX-ACCESS not-accessible
	STATUS current
	DESCRIPTION
        "
        Row definition for the pmc1002MonupRmonBroadcastCnt
        table
        "
	INDEX   { pmc1002MonupRmonBroadcastCntIndex }
	::= { pmc1002MonupRmonBroadcastCntTable 1 }


Pmc1002MonupRmonBroadcastCntEntry ::=
	SEQUENCE {
	pmc1002MonupRmonBroadcastCntIndex
		INTEGER,
	pmc1002MonupRmonBroadcastCntValuePortn
		Counter64,
	pmc1002MonupRmonBroadcastCntErrorPortn
		EkiOnOff,
	pmc1002MonupRmonBroadcastCntOverloadPortn
		EkiOnOff
	}


pmc1002MonupRmonBroadcastCntIndex OBJECT-TYPE
	SYNTAX  INTEGER(0..128)
	MAX-ACCESS  read-only
	STATUS current
	DESCRIPTION
        "
        Index definition for the pmc1002MonupRmonBroadcastCnt
        table
        "
	::= { pmc1002MonupRmonBroadcastCntEntry 1 }


pmc1002MonupRmonBroadcastCntValuePortn OBJECT-TYPE
	SYNTAX  Counter64
	MAX-ACCESS read-only
	STATUS current
	DESCRIPTION
        "
        Client Input Broadcast Packets
        :This counter is increased each
        time a broadcast packet is received
        on the client port.   <Help>  This
        counter gives the number of Broadcast
        packets received on the client
         port
        "
	::= { pmc1002MonupRmonBroadcastCntEntry 2 }


pmc1002MonupRmonBroadcastCntErrorPortn OBJECT-TYPE
	SYNTAX  EkiOnOff
	MAX-ACCESS read-only
	STATUS current
	DESCRIPTION
        "
        Input Broadcast Counter Error
         :This OID when set indicates the
        input Broadcast counter value is
        invalid on client port
        "
	::= { pmc1002MonupRmonBroadcastCntEntry 3 }


pmc1002MonupRmonBroadcastCntOverloadPortn OBJECT-TYPE
	SYNTAX  EkiOnOff
	MAX-ACCESS read-only
	STATUS current
	DESCRIPTION
        "
        Input Broadcast Counter Overload
        :This OID when set indicates an
        input Broadcast counter overload
        on client port
        "
	::= { pmc1002MonupRmonBroadcastCntEntry 4 }


--- *********************************************************
---     TABLE for the pmc1002MonupRmonMulticastCnt articles
--- *********************************************************

pmc1002MonupRmonMulticastCntTable OBJECT-TYPE
	SYNTAX  SEQUENCE OF Pmc1002MonupRmonMulticastCntEntry
	MAX-ACCESS not-accessible
	STATUS current
	DESCRIPTION
        "
        List of pmc1002MonupRmonMulticastCnt
        Article
        "
	::= { pmc1002RmonClient 48 }


pmc1002MonupRmonMulticastCntEntry OBJECT-TYPE
	SYNTAX Pmc1002MonupRmonMulticastCntEntry
	MAX-ACCESS not-accessible
	STATUS current
	DESCRIPTION
        "
        Row definition for the pmc1002MonupRmonMulticastCnt
        table
        "
	INDEX   { pmc1002MonupRmonMulticastCntIndex }
	::= { pmc1002MonupRmonMulticastCntTable 1 }


Pmc1002MonupRmonMulticastCntEntry ::=
	SEQUENCE {
	pmc1002MonupRmonMulticastCntIndex
		INTEGER,
	pmc1002MonupRmonMulticastCntValuePortn
		Counter64,
	pmc1002MonupRmonMulticastCntErrorPortn
		EkiOnOff,
	pmc1002MonupRmonMulticastCntOverloadPortn
		EkiOnOff
	}


pmc1002MonupRmonMulticastCntIndex OBJECT-TYPE
	SYNTAX  INTEGER(0..128)
	MAX-ACCESS  read-only
	STATUS current
	DESCRIPTION
        "
        Index definition for the pmc1002MonupRmonMulticastCnt
        table
        "
	::= { pmc1002MonupRmonMulticastCntEntry 1 }


pmc1002MonupRmonMulticastCntValuePortn OBJECT-TYPE
	SYNTAX  Counter64
	MAX-ACCESS read-only
	STATUS current
	DESCRIPTION
        "
        Client Input Multicast Packets
        :This counter is increased each
        time a Multicast packet is received
        on the client port.  <Help>  This
        counter gives the number of Multicast
        packets received on the client
         port
        "
	::= { pmc1002MonupRmonMulticastCntEntry 2 }


pmc1002MonupRmonMulticastCntErrorPortn OBJECT-TYPE
	SYNTAX  EkiOnOff
	MAX-ACCESS read-only
	STATUS current
	DESCRIPTION
        "
        Input Multicast Counter Error
         :This OID when set indicates the
        input Multicast counter value is
        invalid on client port
        "
	::= { pmc1002MonupRmonMulticastCntEntry 3 }


pmc1002MonupRmonMulticastCntOverloadPortn OBJECT-TYPE
	SYNTAX  EkiOnOff
	MAX-ACCESS read-only
	STATUS current
	DESCRIPTION
        "
        Input Multicast Counter Overload
        :This OID when set indicates an
        input Multicast counter overload
        on client port
        "
	::= { pmc1002MonupRmonMulticastCntEntry 4 }


--- *********************************************************
---     TABLE for the pmc1002MonupRmonTimerCnt articles
--- *********************************************************

pmc1002MonupRmonTimerCntTable OBJECT-TYPE
	SYNTAX  SEQUENCE OF Pmc1002MonupRmonTimerCntEntry
	MAX-ACCESS not-accessible
	STATUS current
	DESCRIPTION
        "
        List of pmc1002MonupRmonTimerCnt
        Article
        "
	::= { pmc1002RmonClient 56 }


pmc1002MonupRmonTimerCntEntry OBJECT-TYPE
	SYNTAX Pmc1002MonupRmonTimerCntEntry
	MAX-ACCESS not-accessible
	STATUS current
	DESCRIPTION
        "
        Row definition for the pmc1002MonupRmonTimerCnt
        table
        "
	INDEX   { pmc1002MonupRmonTimerCntIndex }
	::= { pmc1002MonupRmonTimerCntTable 1 }


Pmc1002MonupRmonTimerCntEntry ::=
	SEQUENCE {
	pmc1002MonupRmonTimerCntIndex
		INTEGER,
	pmc1002MonupRmonTimerCntValuePortn
		Counter64,
	pmc1002MonupRmonTimerCntErrorPortn
		EkiOnOff,
	pmc1002MonupRmonTimerCntOverloadPortn
		EkiOnOff
	}


pmc1002MonupRmonTimerCntIndex OBJECT-TYPE
	SYNTAX  INTEGER(0..128)
	MAX-ACCESS  read-only
	STATUS current
	DESCRIPTION
        "
        Index definition for the pmc1002MonupRmonTimerCnt
        table
        "
	::= { pmc1002MonupRmonTimerCntEntry 1 }


pmc1002MonupRmonTimerCntValuePortn OBJECT-TYPE
	SYNTAX  Counter64
	MAX-ACCESS read-only
	STATUS current
	DESCRIPTION
        "
        RMON Timer On Client Input :This
        is the timing counter dedicated
        to the upstream RMON counters.
         It is incremented every 125 us.
        "
	::= { pmc1002MonupRmonTimerCntEntry 2 }


pmc1002MonupRmonTimerCntErrorPortn OBJECT-TYPE
	SYNTAX  EkiOnOff
	MAX-ACCESS read-only
	STATUS current
	DESCRIPTION
        "
        Input RMON Timer Error :This OID
        when set indicates the input RMON
        timer is invalid on client port
        "
	::= { pmc1002MonupRmonTimerCntEntry 3 }


pmc1002MonupRmonTimerCntOverloadPortn OBJECT-TYPE
	SYNTAX  EkiOnOff
	MAX-ACCESS read-only
	STATUS current
	DESCRIPTION
        "
        Input RMON Timer Overload :This
        OID when set indicates an input
        RMON timer overload on client port
        "
	::= { pmc1002MonupRmonTimerCntEntry 4 }


--- *********************************************************
---     TABLE for the pmc1002MonupRmonPauseFrameCnt articles
--- *********************************************************

pmc1002MonupRmonPauseFrameCntTable OBJECT-TYPE
	SYNTAX  SEQUENCE OF Pmc1002MonupRmonPauseFrameCntEntry
	MAX-ACCESS not-accessible
	STATUS current
	DESCRIPTION
        "
        List of pmc1002MonupRmonPauseFrameCnt
        Article
        "
	::= { pmc1002RmonClient 64 }


pmc1002MonupRmonPauseFrameCntEntry OBJECT-TYPE
	SYNTAX Pmc1002MonupRmonPauseFrameCntEntry
	MAX-ACCESS not-accessible
	STATUS current
	DESCRIPTION
        "
        Row definition for the pmc1002MonupRmonPauseFrameCnt
        table
        "
	INDEX   { pmc1002MonupRmonPauseFrameCntIndex }
	::= { pmc1002MonupRmonPauseFrameCntTable 1 }


Pmc1002MonupRmonPauseFrameCntEntry ::=
	SEQUENCE {
	pmc1002MonupRmonPauseFrameCntIndex
		INTEGER,
	pmc1002MonupRmonPauseFrameCntValuePortn
		Counter64,
	pmc1002MonupRmonPauseFrameCntErrorPortn
		EkiOnOff,
	pmc1002MonupRmonPauseFrameCntOverloadPortn
		EkiOnOff
	}


pmc1002MonupRmonPauseFrameCntIndex OBJECT-TYPE
	SYNTAX  INTEGER(0..128)
	MAX-ACCESS  read-only
	STATUS current
	DESCRIPTION
        "
        Index definition for the pmc1002MonupRmonPauseFrameCnt
        table
        "
	::= { pmc1002MonupRmonPauseFrameCntEntry 1 }


pmc1002MonupRmonPauseFrameCntValuePortn OBJECT-TYPE
	SYNTAX  Counter64
	MAX-ACCESS read-only
	STATUS current
	DESCRIPTION
        "
        Client Input Pause Frames :This
        counter is increased each time
         a Pause frame is received on the
        client port
        "
	::= { pmc1002MonupRmonPauseFrameCntEntry 2 }


pmc1002MonupRmonPauseFrameCntErrorPortn OBJECT-TYPE
	SYNTAX  EkiOnOff
	MAX-ACCESS read-only
	STATUS current
	DESCRIPTION
        "
        Input Pause Counter Error :This
        OID when set indicates the input
        Pause counter value is invalid
         on client port
        "
	::= { pmc1002MonupRmonPauseFrameCntEntry 3 }


pmc1002MonupRmonPauseFrameCntOverloadPortn OBJECT-TYPE
	SYNTAX  EkiOnOff
	MAX-ACCESS read-only
	STATUS current
	DESCRIPTION
        "
        Input Pause Counter Overload :This
        OID when set indicates an input
        Pause counter overload on client
        port
        "
	::= { pmc1002MonupRmonPauseFrameCntEntry 4 }


--- *********************************************************
---     TABLE for the pmc1002MonupRmonDropFrameCnt articles
--- *********************************************************

pmc1002MonupRmonDropFrameCntTable OBJECT-TYPE
	SYNTAX  SEQUENCE OF Pmc1002MonupRmonDropFrameCntEntry
	MAX-ACCESS not-accessible
	STATUS current
	DESCRIPTION
        "
        List of pmc1002MonupRmonDropFrameCnt
        Article
        "
	::= { pmc1002RmonClient 72 }


pmc1002MonupRmonDropFrameCntEntry OBJECT-TYPE
	SYNTAX Pmc1002MonupRmonDropFrameCntEntry
	MAX-ACCESS not-accessible
	STATUS current
	DESCRIPTION
        "
        Row definition for the pmc1002MonupRmonDropFrameCnt
        table
        "
	INDEX   { pmc1002MonupRmonDropFrameCntIndex }
	::= { pmc1002MonupRmonDropFrameCntTable 1 }


Pmc1002MonupRmonDropFrameCntEntry ::=
	SEQUENCE {
	pmc1002MonupRmonDropFrameCntIndex
		INTEGER,
	pmc1002MonupRmonDropFrameCntValuePortn
		Counter64,
	pmc1002MonupRmonDropFrameCntErrorPortn
		EkiOnOff,
	pmc1002MonupRmonDropFrameCntOverloadPortn
		EkiOnOff
	}


pmc1002MonupRmonDropFrameCntIndex OBJECT-TYPE
	SYNTAX  INTEGER(0..128)
	MAX-ACCESS  read-only
	STATUS current
	DESCRIPTION
        "
        Index definition for the pmc1002MonupRmonDropFrameCnt
        table
        "
	::= { pmc1002MonupRmonDropFrameCntEntry 1 }


pmc1002MonupRmonDropFrameCntValuePortn OBJECT-TYPE
	SYNTAX  Counter64
	MAX-ACCESS read-only
	STATUS current
	DESCRIPTION
        "
        Client Input Drop Packets :This
        counter is increased each time
         a Frame is dropped on the input
        client port
        "
	::= { pmc1002MonupRmonDropFrameCntEntry 2 }


pmc1002MonupRmonDropFrameCntErrorPortn OBJECT-TYPE
	SYNTAX  EkiOnOff
	MAX-ACCESS read-only
	STATUS current
	DESCRIPTION
        "
        Input Drop Counter Error :This
        OID when set indicates the input
        Drop counter value is invalid on
        client port
        "
	::= { pmc1002MonupRmonDropFrameCntEntry 3 }


pmc1002MonupRmonDropFrameCntOverloadPortn OBJECT-TYPE
	SYNTAX  EkiOnOff
	MAX-ACCESS read-only
	STATUS current
	DESCRIPTION
        "
        Input Drop Counter Overload :This
        OID when set indicates an input
        Drop counter overload on client
        port
        "
	::= { pmc1002MonupRmonDropFrameCntEntry 4 }


--- *********************************************************
---     TABLE for the pmc1002MonupRmonBitsCnt articles
--- *********************************************************

pmc1002MonupRmonBitsCntTable OBJECT-TYPE
	SYNTAX  SEQUENCE OF Pmc1002MonupRmonBitsCntEntry
	MAX-ACCESS not-accessible
	STATUS current
	DESCRIPTION
        "
        List of pmc1002MonupRmonBitsCnt
        Article
        "
	::= { pmc1002RmonClient 80 }


pmc1002MonupRmonBitsCntEntry OBJECT-TYPE
	SYNTAX Pmc1002MonupRmonBitsCntEntry
	MAX-ACCESS not-accessible
	STATUS current
	DESCRIPTION
        "
        Row definition for the pmc1002MonupRmonBitsCnt
        table
        "
	INDEX   { pmc1002MonupRmonBitsCntIndex }
	::= { pmc1002MonupRmonBitsCntTable 1 }


Pmc1002MonupRmonBitsCntEntry ::=
	SEQUENCE {
	pmc1002MonupRmonBitsCntIndex
		INTEGER,
	pmc1002MonupRmonBitsCntValuePortn
		Counter64,
	pmc1002MonupRmonBitsCntErrorPortn
		EkiOnOff,
	pmc1002MonupRmonBitsCntOverloadPortn
		EkiOnOff
	}


pmc1002MonupRmonBitsCntIndex OBJECT-TYPE
	SYNTAX  INTEGER(0..128)
	MAX-ACCESS  read-only
	STATUS current
	DESCRIPTION
        "
        Index definition for the pmc1002MonupRmonBitsCnt
        table
        "
	::= { pmc1002MonupRmonBitsCntEntry 1 }


pmc1002MonupRmonBitsCntValuePortn OBJECT-TYPE
	SYNTAX  Counter64
	MAX-ACCESS read-only
	STATUS current
	DESCRIPTION
        "
        Client Input Bits :This counter
        is increased each time a bit is
        received on the input client port
        "
	::= { pmc1002MonupRmonBitsCntEntry 2 }


pmc1002MonupRmonBitsCntErrorPortn OBJECT-TYPE
	SYNTAX  EkiOnOff
	MAX-ACCESS read-only
	STATUS current
	DESCRIPTION
        "
        Input Bits Counter Error :This
        OID when set indicates the input
        Bits counter value is invalid on
        client port
        "
	::= { pmc1002MonupRmonBitsCntEntry 3 }


pmc1002MonupRmonBitsCntOverloadPortn OBJECT-TYPE
	SYNTAX  EkiOnOff
	MAX-ACCESS read-only
	STATUS current
	DESCRIPTION
        "
        Input Bits Counter Overload :This
        OID when set indicates an input
        Bits counter overload on client
        port
        "
	::= { pmc1002MonupRmonBitsCntEntry 4 }


--- *********************************************************
---     TABLE for the pmc1002MonupRmonUnicastCnt articles
--- *********************************************************

pmc1002MonupRmonUnicastCntTable OBJECT-TYPE
	SYNTAX  SEQUENCE OF Pmc1002MonupRmonUnicastCntEntry
	MAX-ACCESS not-accessible
	STATUS current
	DESCRIPTION
        "
        List of pmc1002MonupRmonUnicastCnt
        Article
        "
	::= { pmc1002RmonClient 88 }


pmc1002MonupRmonUnicastCntEntry OBJECT-TYPE
	SYNTAX Pmc1002MonupRmonUnicastCntEntry
	MAX-ACCESS not-accessible
	STATUS current
	DESCRIPTION
        "
        Row definition for the pmc1002MonupRmonUnicastCnt
        table
        "
	INDEX   { pmc1002MonupRmonUnicastCntIndex }
	::= { pmc1002MonupRmonUnicastCntTable 1 }


Pmc1002MonupRmonUnicastCntEntry ::=
	SEQUENCE {
	pmc1002MonupRmonUnicastCntIndex
		INTEGER,
	pmc1002MonupRmonUnicastCntValuePortn
		Counter64,
	pmc1002MonupRmonUnicastCntErrorPortn
		EkiOnOff,
	pmc1002MonupRmonUnicastCntOverloadPortn
		EkiOnOff
	}


pmc1002MonupRmonUnicastCntIndex OBJECT-TYPE
	SYNTAX  INTEGER(0..128)
	MAX-ACCESS  read-only
	STATUS current
	DESCRIPTION
        "
        Index definition for the pmc1002MonupRmonUnicastCnt
        table
        "
	::= { pmc1002MonupRmonUnicastCntEntry 1 }


pmc1002MonupRmonUnicastCntValuePortn OBJECT-TYPE
	SYNTAX  Counter64
	MAX-ACCESS read-only
	STATUS current
	DESCRIPTION
        "
        Client Input Unicast Packets :This
        counter is increased each time
         a Unicast packet is received on
        client input  <Help>  This counter
        gives the number of Unicast packets
        received on the client input port
        "
	::= { pmc1002MonupRmonUnicastCntEntry 2 }


pmc1002MonupRmonUnicastCntErrorPortn OBJECT-TYPE
	SYNTAX  EkiOnOff
	MAX-ACCESS read-only
	STATUS current
	DESCRIPTION
        "
        Input Unicast Counter Error :This
        OID when set indicates the input
        Drop counter value is invalid on
        client port
        "
	::= { pmc1002MonupRmonUnicastCntEntry 3 }


pmc1002MonupRmonUnicastCntOverloadPortn OBJECT-TYPE
	SYNTAX  EkiOnOff
	MAX-ACCESS read-only
	STATUS current
	DESCRIPTION
        "
        Input Unicast Counter Overload
        :This OID when set indicates an
        input Drop counter overload on
         client port
        "
	::= { pmc1002MonupRmonUnicastCntEntry 4 }


--- *********************************************************
---     TABLE for the pmc1002MonupRmonNonUnicastCnt articles
--- *********************************************************

pmc1002MonupRmonNonUnicastCntTable OBJECT-TYPE
	SYNTAX  SEQUENCE OF Pmc1002MonupRmonNonUnicastCntEntry
	MAX-ACCESS not-accessible
	STATUS current
	DESCRIPTION
        "
        List of pmc1002MonupRmonNonUnicastCnt
        Article
        "
	::= { pmc1002RmonClient 96 }


pmc1002MonupRmonNonUnicastCntEntry OBJECT-TYPE
	SYNTAX Pmc1002MonupRmonNonUnicastCntEntry
	MAX-ACCESS not-accessible
	STATUS current
	DESCRIPTION
        "
        Row definition for the pmc1002MonupRmonNonUnicastCnt
        table
        "
	INDEX   { pmc1002MonupRmonNonUnicastCntIndex }
	::= { pmc1002MonupRmonNonUnicastCntTable 1 }


Pmc1002MonupRmonNonUnicastCntEntry ::=
	SEQUENCE {
	pmc1002MonupRmonNonUnicastCntIndex
		INTEGER,
	pmc1002MonupRmonNonUnicastCntValuePortn
		Counter64,
	pmc1002MonupRmonNonUnicastCntErrorPortn
		EkiOnOff,
	pmc1002MonupRmonNonUnicastCntOverloadPortn
		EkiOnOff
	}


pmc1002MonupRmonNonUnicastCntIndex OBJECT-TYPE
	SYNTAX  INTEGER(0..128)
	MAX-ACCESS  read-only
	STATUS current
	DESCRIPTION
        "
        Index definition for the pmc1002MonupRmonNonUnicastCnt
        table
        "
	::= { pmc1002MonupRmonNonUnicastCntEntry 1 }


pmc1002MonupRmonNonUnicastCntValuePortn OBJECT-TYPE
	SYNTAX  Counter64
	MAX-ACCESS read-only
	STATUS current
	DESCRIPTION
        "
        Client Input Non Unicast Packets
        :This counter is increased each
        time a Non Unicast packet is received
        on client input    <Help>  This
        counter gives the number of Non
        Unicast packets received on the
        client input port
        "
	::= { pmc1002MonupRmonNonUnicastCntEntry 2 }


pmc1002MonupRmonNonUnicastCntErrorPortn OBJECT-TYPE
	SYNTAX  EkiOnOff
	MAX-ACCESS read-only
	STATUS current
	DESCRIPTION
        "
        Input Non Unicast Counter Error
        :This OID when set indicates the
        input Bits counter value is invalid
        on client port
        "
	::= { pmc1002MonupRmonNonUnicastCntEntry 3 }


pmc1002MonupRmonNonUnicastCntOverloadPortn OBJECT-TYPE
	SYNTAX  EkiOnOff
	MAX-ACCESS read-only
	STATUS current
	DESCRIPTION
        "
        Input Non Unicast Counter Overload
        :This OID when set indicates an
        input Bits counter overload on
         client port
        "
	::= { pmc1002MonupRmonNonUnicastCntEntry 4 }


--- *********************************************************
---     TABLE for the pmc1002MondwRmonByteCnt articles
--- *********************************************************

pmc1002MondwRmonByteCntTable OBJECT-TYPE
	SYNTAX  SEQUENCE OF Pmc1002MondwRmonByteCntEntry
	MAX-ACCESS not-accessible
	STATUS current
	DESCRIPTION
        "
        List of pmc1002MondwRmonByteCnt
        Article
        "
	::= { pmc1002RmonClient 112 }


pmc1002MondwRmonByteCntEntry OBJECT-TYPE
	SYNTAX Pmc1002MondwRmonByteCntEntry
	MAX-ACCESS not-accessible
	STATUS current
	DESCRIPTION
        "
        Row definition for the pmc1002MondwRmonByteCnt
        table
        "
	INDEX   { pmc1002MondwRmonByteCntIndex }
	::= { pmc1002MondwRmonByteCntTable 1 }


Pmc1002MondwRmonByteCntEntry ::=
	SEQUENCE {
	pmc1002MondwRmonByteCntIndex
		INTEGER,
	pmc1002MondwRmonByteCntValuePortn
		Counter64,
	pmc1002MondwRmonByteCntErrorPortn
		EkiOnOff,
	pmc1002MondwRmonByteCntOverloadPortn
		EkiOnOff
	}


pmc1002MondwRmonByteCntIndex OBJECT-TYPE
	SYNTAX  INTEGER(0..128)
	MAX-ACCESS  read-only
	STATUS current
	DESCRIPTION
        "
        Index definition for the pmc1002MondwRmonByteCnt
        table
        "
	::= { pmc1002MondwRmonByteCntEntry 1 }


pmc1002MondwRmonByteCntValuePortn OBJECT-TYPE
	SYNTAX  Counter64
	MAX-ACCESS read-only
	STATUS current
	DESCRIPTION
        "
        Client Output Bytes :This counter
        is increased each time a data byte
        is transmitted on the client port.
         <Help>  This counter gives the
        number of bytes transmitted on
         the client port
        "
	::= { pmc1002MondwRmonByteCntEntry 2 }


pmc1002MondwRmonByteCntErrorPortn OBJECT-TYPE
	SYNTAX  EkiOnOff
	MAX-ACCESS read-only
	STATUS current
	DESCRIPTION
        "
        Output Bytes Counter Error :This
        OID when set indicates the output
        Bytes counter value is invalid
         on client port
        "
	::= { pmc1002MondwRmonByteCntEntry 3 }


pmc1002MondwRmonByteCntOverloadPortn OBJECT-TYPE
	SYNTAX  EkiOnOff
	MAX-ACCESS read-only
	STATUS current
	DESCRIPTION
        "
        Output Bytes Counter Overload
         :This OID when set indicates an
        output Bytes counter overload on
        client port
        "
	::= { pmc1002MondwRmonByteCntEntry 4 }


--- *********************************************************
---     TABLE for the pmc1002MondwRmonCrcErrorCnt articles
--- *********************************************************

pmc1002MondwRmonCrcErrorCntTable OBJECT-TYPE
	SYNTAX  SEQUENCE OF Pmc1002MondwRmonCrcErrorCntEntry
	MAX-ACCESS not-accessible
	STATUS current
	DESCRIPTION
        "
        List of pmc1002MondwRmonCrcErrorCnt
        Article
        "
	::= { pmc1002RmonClient 120 }


pmc1002MondwRmonCrcErrorCntEntry OBJECT-TYPE
	SYNTAX Pmc1002MondwRmonCrcErrorCntEntry
	MAX-ACCESS not-accessible
	STATUS current
	DESCRIPTION
        "
        Row definition for the pmc1002MondwRmonCrcErrorCnt
        table
        "
	INDEX   { pmc1002MondwRmonCrcErrorCntIndex }
	::= { pmc1002MondwRmonCrcErrorCntTable 1 }


Pmc1002MondwRmonCrcErrorCntEntry ::=
	SEQUENCE {
	pmc1002MondwRmonCrcErrorCntIndex
		INTEGER,
	pmc1002MondwRmonCrcErrorCntValuePortn
		Counter64,
	pmc1002MondwRmonCrcErrorCntErrorPortn
		EkiOnOff,
	pmc1002MondwRmonCrcErrorCntOverloadPortn
		EkiOnOff
	}


pmc1002MondwRmonCrcErrorCntIndex OBJECT-TYPE
	SYNTAX  INTEGER(0..128)
	MAX-ACCESS  read-only
	STATUS current
	DESCRIPTION
        "
        Index definition for the pmc1002MondwRmonCrcErrorCnt
        table
        "
	::= { pmc1002MondwRmonCrcErrorCntEntry 1 }


pmc1002MondwRmonCrcErrorCntValuePortn OBJECT-TYPE
	SYNTAX  Counter64
	MAX-ACCESS read-only
	STATUS current
	DESCRIPTION
        "
        Client Output CRC Errors :This
        counter is increased each time
         a CRC error is detected on the
        output client port  <Help>  This
        counter gives the number of CRC
        Errors transmitted on the client
        port
        "
	::= { pmc1002MondwRmonCrcErrorCntEntry 2 }


pmc1002MondwRmonCrcErrorCntErrorPortn OBJECT-TYPE
	SYNTAX  EkiOnOff
	MAX-ACCESS read-only
	STATUS current
	DESCRIPTION
        "
        Output CRC Errors Counter Error
        :This OID when set indicates the
        output CRC Errors counter value
        is invalid on client port
        "
	::= { pmc1002MondwRmonCrcErrorCntEntry 3 }


pmc1002MondwRmonCrcErrorCntOverloadPortn OBJECT-TYPE
	SYNTAX  EkiOnOff
	MAX-ACCESS read-only
	STATUS current
	DESCRIPTION
        "
        Output CRC Errors Counter Overload
        :This OID when set indicates an
        output CRC Errors counter overload
        on client port
        "
	::= { pmc1002MondwRmonCrcErrorCntEntry 4 }


--- *********************************************************
---     TABLE for the pmc1002MondwRmonPacketsCnt articles
--- *********************************************************

pmc1002MondwRmonPacketsCntTable OBJECT-TYPE
	SYNTAX  SEQUENCE OF Pmc1002MondwRmonPacketsCntEntry
	MAX-ACCESS not-accessible
	STATUS current
	DESCRIPTION
        "
        List of pmc1002MondwRmonPacketsCnt
        Article
        "
	::= { pmc1002RmonClient 128 }


pmc1002MondwRmonPacketsCntEntry OBJECT-TYPE
	SYNTAX Pmc1002MondwRmonPacketsCntEntry
	MAX-ACCESS not-accessible
	STATUS current
	DESCRIPTION
        "
        Row definition for the pmc1002MondwRmonPacketsCnt
        table
        "
	INDEX   { pmc1002MondwRmonPacketsCntIndex }
	::= { pmc1002MondwRmonPacketsCntTable 1 }


Pmc1002MondwRmonPacketsCntEntry ::=
	SEQUENCE {
	pmc1002MondwRmonPacketsCntIndex
		INTEGER,
	pmc1002MondwRmonPacketsCntValuePortn
		Counter64,
	pmc1002MondwRmonPacketsCntErrorPortn
		EkiOnOff,
	pmc1002MondwRmonPacketsCntOverloadPortn
		EkiOnOff
	}


pmc1002MondwRmonPacketsCntIndex OBJECT-TYPE
	SYNTAX  INTEGER(0..128)
	MAX-ACCESS  read-only
	STATUS current
	DESCRIPTION
        "
        Index definition for the pmc1002MondwRmonPacketsCnt
        table
        "
	::= { pmc1002MondwRmonPacketsCntEntry 1 }


pmc1002MondwRmonPacketsCntValuePortn OBJECT-TYPE
	SYNTAX  Counter64
	MAX-ACCESS read-only
	STATUS current
	DESCRIPTION
        "
        Client Output Packets :This counter
        is increased each time a packet
        is transmitted on the client port.
         <Help>  This counter gives the
        number of packets transmitted on
        the client port
        "
	::= { pmc1002MondwRmonPacketsCntEntry 2 }


pmc1002MondwRmonPacketsCntErrorPortn OBJECT-TYPE
	SYNTAX  EkiOnOff
	MAX-ACCESS read-only
	STATUS current
	DESCRIPTION
        "
        Output Packets Counter Error :This
        OID when set indicates the output
        Packets counter value is invalid
        on client port
        "
	::= { pmc1002MondwRmonPacketsCntEntry 3 }


pmc1002MondwRmonPacketsCntOverloadPortn OBJECT-TYPE
	SYNTAX  EkiOnOff
	MAX-ACCESS read-only
	STATUS current
	DESCRIPTION
        "
        Output Packets Counter Overload
        :This OID when set indicates an
        output Packets counter overload
        on client port
        "
	::= { pmc1002MondwRmonPacketsCntEntry 4 }


--- *********************************************************
---     TABLE for the pmc1002MondwRmonBroadcastCnt articles
--- *********************************************************

pmc1002MondwRmonBroadcastCntTable OBJECT-TYPE
	SYNTAX  SEQUENCE OF Pmc1002MondwRmonBroadcastCntEntry
	MAX-ACCESS not-accessible
	STATUS current
	DESCRIPTION
        "
        List of pmc1002MondwRmonBroadcastCnt
        Article
        "
	::= { pmc1002RmonClient 136 }


pmc1002MondwRmonBroadcastCntEntry OBJECT-TYPE
	SYNTAX Pmc1002MondwRmonBroadcastCntEntry
	MAX-ACCESS not-accessible
	STATUS current
	DESCRIPTION
        "
        Row definition for the pmc1002MondwRmonBroadcastCnt
        table
        "
	INDEX   { pmc1002MondwRmonBroadcastCntIndex }
	::= { pmc1002MondwRmonBroadcastCntTable 1 }


Pmc1002MondwRmonBroadcastCntEntry ::=
	SEQUENCE {
	pmc1002MondwRmonBroadcastCntIndex
		INTEGER,
	pmc1002MondwRmonBroadcastCntValuePortn
		Counter64,
	pmc1002MondwRmonBroadcastCntErrorPortn
		EkiOnOff,
	pmc1002MondwRmonBroadcastCntOverloadPortn
		EkiOnOff
	}


pmc1002MondwRmonBroadcastCntIndex OBJECT-TYPE
	SYNTAX  INTEGER(0..128)
	MAX-ACCESS  read-only
	STATUS current
	DESCRIPTION
        "
        Index definition for the pmc1002MondwRmonBroadcastCnt
        table
        "
	::= { pmc1002MondwRmonBroadcastCntEntry 1 }


pmc1002MondwRmonBroadcastCntValuePortn OBJECT-TYPE
	SYNTAX  Counter64
	MAX-ACCESS read-only
	STATUS current
	DESCRIPTION
        "
        Client Output Broadcast Packets
        :This counter is increased each
        time a broadcast packet is transmitted
        on the client port.  <Help>  This
        counter gives the number of Broadcast
        packets transmitted on the client
        port
        "
	::= { pmc1002MondwRmonBroadcastCntEntry 2 }


pmc1002MondwRmonBroadcastCntErrorPortn OBJECT-TYPE
	SYNTAX  EkiOnOff
	MAX-ACCESS read-only
	STATUS current
	DESCRIPTION
        "
        Output Broadcast Counter Error
        :This OID when set indicates the
        output Broadcast counter value
         is invalid on client port
        "
	::= { pmc1002MondwRmonBroadcastCntEntry 3 }


pmc1002MondwRmonBroadcastCntOverloadPortn OBJECT-TYPE
	SYNTAX  EkiOnOff
	MAX-ACCESS read-only
	STATUS current
	DESCRIPTION
        "
        Output Broadcast Counter Overload
        :This OID when set indicates an
        output Broadcast counter overload
        on client port
        "
	::= { pmc1002MondwRmonBroadcastCntEntry 4 }


--- *********************************************************
---     TABLE for the pmc1002MondwRmonMulticastCnt articles
--- *********************************************************

pmc1002MondwRmonMulticastCntTable OBJECT-TYPE
	SYNTAX  SEQUENCE OF Pmc1002MondwRmonMulticastCntEntry
	MAX-ACCESS not-accessible
	STATUS current
	DESCRIPTION
        "
        List of pmc1002MondwRmonMulticastCnt
        Article
        "
	::= { pmc1002RmonClient 144 }


pmc1002MondwRmonMulticastCntEntry OBJECT-TYPE
	SYNTAX Pmc1002MondwRmonMulticastCntEntry
	MAX-ACCESS not-accessible
	STATUS current
	DESCRIPTION
        "
        Row definition for the pmc1002MondwRmonMulticastCnt
        table
        "
	INDEX   { pmc1002MondwRmonMulticastCntIndex }
	::= { pmc1002MondwRmonMulticastCntTable 1 }


Pmc1002MondwRmonMulticastCntEntry ::=
	SEQUENCE {
	pmc1002MondwRmonMulticastCntIndex
		INTEGER,
	pmc1002MondwRmonMulticastCntValuePortn
		Counter64,
	pmc1002MondwRmonMulticastCntErrorPortn
		EkiOnOff,
	pmc1002MondwRmonMulticastCntOverloadPortn
		EkiOnOff
	}


pmc1002MondwRmonMulticastCntIndex OBJECT-TYPE
	SYNTAX  INTEGER(0..128)
	MAX-ACCESS  read-only
	STATUS current
	DESCRIPTION
        "
        Index definition for the pmc1002MondwRmonMulticastCnt
        table
        "
	::= { pmc1002MondwRmonMulticastCntEntry 1 }


pmc1002MondwRmonMulticastCntValuePortn OBJECT-TYPE
	SYNTAX  Counter64
	MAX-ACCESS read-only
	STATUS current
	DESCRIPTION
        "
        Client Output Multicast Packets
        :This counter is increased each
        time a Multicast packet is tra,smitted
        on the client port.  <Help>  This
        counter gives the number of Multicast
        packets transmitted on the client
        port
        "
	::= { pmc1002MondwRmonMulticastCntEntry 2 }


pmc1002MondwRmonMulticastCntErrorPortn OBJECT-TYPE
	SYNTAX  EkiOnOff
	MAX-ACCESS read-only
	STATUS current
	DESCRIPTION
        "
        Output Multicast Counter Error
        :This OID when set indicates the
        output Multicast counter value
         is invalid on client port
        "
	::= { pmc1002MondwRmonMulticastCntEntry 3 }


pmc1002MondwRmonMulticastCntOverloadPortn OBJECT-TYPE
	SYNTAX  EkiOnOff
	MAX-ACCESS read-only
	STATUS current
	DESCRIPTION
        "
        Output Multicast Counter Overload
        :This OID when set indicates an
        output Multicast counter overload
        on client port
        "
	::= { pmc1002MondwRmonMulticastCntEntry 4 }


--- *********************************************************
---     TABLE for the pmc1002MondwRmonPauseFrameCnt articles
--- *********************************************************

pmc1002MondwRmonPauseFrameCntTable OBJECT-TYPE
	SYNTAX  SEQUENCE OF Pmc1002MondwRmonPauseFrameCntEntry
	MAX-ACCESS not-accessible
	STATUS current
	DESCRIPTION
        "
        List of pmc1002MondwRmonPauseFrameCnt
        Article
        "
	::= { pmc1002RmonClient 152 }


pmc1002MondwRmonPauseFrameCntEntry OBJECT-TYPE
	SYNTAX Pmc1002MondwRmonPauseFrameCntEntry
	MAX-ACCESS not-accessible
	STATUS current
	DESCRIPTION
        "
        Row definition for the pmc1002MondwRmonPauseFrameCnt
        table
        "
	INDEX   { pmc1002MondwRmonPauseFrameCntIndex }
	::= { pmc1002MondwRmonPauseFrameCntTable 1 }


Pmc1002MondwRmonPauseFrameCntEntry ::=
	SEQUENCE {
	pmc1002MondwRmonPauseFrameCntIndex
		INTEGER,
	pmc1002MondwRmonPauseFrameCntValuePortn
		Counter64,
	pmc1002MondwRmonPauseFrameCntErrorPortn
		EkiOnOff,
	pmc1002MondwRmonPauseFrameCntOverloadPortn
		EkiOnOff
	}


pmc1002MondwRmonPauseFrameCntIndex OBJECT-TYPE
	SYNTAX  INTEGER(0..128)
	MAX-ACCESS  read-only
	STATUS current
	DESCRIPTION
        "
        Index definition for the pmc1002MondwRmonPauseFrameCnt
        table
        "
	::= { pmc1002MondwRmonPauseFrameCntEntry 1 }


pmc1002MondwRmonPauseFrameCntValuePortn OBJECT-TYPE
	SYNTAX  Counter64
	MAX-ACCESS read-only
	STATUS current
	DESCRIPTION
        "
        Client Output Pause Frames :This
        counter is increased each time
         a Pause frame is generated by
         the PM on the client port
        "
	::= { pmc1002MondwRmonPauseFrameCntEntry 2 }


pmc1002MondwRmonPauseFrameCntErrorPortn OBJECT-TYPE
	SYNTAX  EkiOnOff
	MAX-ACCESS read-only
	STATUS current
	DESCRIPTION
        "
        Output Pause Counter Error :This
        OID when set indicates the output
        Pause counter value is invalid
         on client port
        "
	::= { pmc1002MondwRmonPauseFrameCntEntry 3 }


pmc1002MondwRmonPauseFrameCntOverloadPortn OBJECT-TYPE
	SYNTAX  EkiOnOff
	MAX-ACCESS read-only
	STATUS current
	DESCRIPTION
        "
        Output Pause Counter Overload
         :This OID when set indicates an
        output Pause counter overload on
        client port
        "
	::= { pmc1002MondwRmonPauseFrameCntEntry 4 }


--- *********************************************************
---     TABLE for the pmc1002MondwRmonTimerCnt articles
--- *********************************************************

pmc1002MondwRmonTimerCntTable OBJECT-TYPE
	SYNTAX  SEQUENCE OF Pmc1002MondwRmonTimerCntEntry
	MAX-ACCESS not-accessible
	STATUS current
	DESCRIPTION
        "
        List of pmc1002MondwRmonTimerCnt
        Article
        "
	::= { pmc1002RmonClient 160 }


pmc1002MondwRmonTimerCntEntry OBJECT-TYPE
	SYNTAX Pmc1002MondwRmonTimerCntEntry
	MAX-ACCESS not-accessible
	STATUS current
	DESCRIPTION
        "
        Row definition for the pmc1002MondwRmonTimerCnt
        table
        "
	INDEX   { pmc1002MondwRmonTimerCntIndex }
	::= { pmc1002MondwRmonTimerCntTable 1 }


Pmc1002MondwRmonTimerCntEntry ::=
	SEQUENCE {
	pmc1002MondwRmonTimerCntIndex
		INTEGER,
	pmc1002MondwRmonTimerCntValuePortn
		Counter64,
	pmc1002MondwRmonTimerCntErrorPortn
		EkiOnOff,
	pmc1002MondwRmonTimerCntOverloadPortn
		EkiOnOff
	}


pmc1002MondwRmonTimerCntIndex OBJECT-TYPE
	SYNTAX  INTEGER(0..128)
	MAX-ACCESS  read-only
	STATUS current
	DESCRIPTION
        "
        Index definition for the pmc1002MondwRmonTimerCnt
        table
        "
	::= { pmc1002MondwRmonTimerCntEntry 1 }


pmc1002MondwRmonTimerCntValuePortn OBJECT-TYPE
	SYNTAX  Counter64
	MAX-ACCESS read-only
	STATUS current
	DESCRIPTION
        "
        RMON Timer On Client Output :This
        is the timing counter dedicated
        to the downstream RMON counters.
        It is incremented every 125 us.
        "
	::= { pmc1002MondwRmonTimerCntEntry 2 }


pmc1002MondwRmonTimerCntErrorPortn OBJECT-TYPE
	SYNTAX  EkiOnOff
	MAX-ACCESS read-only
	STATUS current
	DESCRIPTION
        "
        Output RMON Timer Error :This
         OID when set indicates the output
        RMON timer is invalid on client
        port
        "
	::= { pmc1002MondwRmonTimerCntEntry 3 }


pmc1002MondwRmonTimerCntOverloadPortn OBJECT-TYPE
	SYNTAX  EkiOnOff
	MAX-ACCESS read-only
	STATUS current
	DESCRIPTION
        "
        Output RMON Timer Overload :This
        OID when set indicates an output
        RMON timer overload on client port
        "
	::= { pmc1002MondwRmonTimerCntEntry 4 }


--- *********************************************************
---     TABLE for the pmc1002MondwRmonBitsCnt articles
--- *********************************************************

pmc1002MondwRmonBitsCntTable OBJECT-TYPE
	SYNTAX  SEQUENCE OF Pmc1002MondwRmonBitsCntEntry
	MAX-ACCESS not-accessible
	STATUS current
	DESCRIPTION
        "
        List of pmc1002MondwRmonBitsCnt
        Article
        "
	::= { pmc1002RmonClient 168 }


pmc1002MondwRmonBitsCntEntry OBJECT-TYPE
	SYNTAX Pmc1002MondwRmonBitsCntEntry
	MAX-ACCESS not-accessible
	STATUS current
	DESCRIPTION
        "
        Row definition for the pmc1002MondwRmonBitsCnt
        table
        "
	INDEX   { pmc1002MondwRmonBitsCntIndex }
	::= { pmc1002MondwRmonBitsCntTable 1 }


Pmc1002MondwRmonBitsCntEntry ::=
	SEQUENCE {
	pmc1002MondwRmonBitsCntIndex
		INTEGER,
	pmc1002MondwRmonBitsCntValuePortn
		Counter64,
	pmc1002MondwRmonBitsCntErrorPortn
		EkiOnOff,
	pmc1002MondwRmonBitsCntOverloadPortn
		EkiOnOff
	}


pmc1002MondwRmonBitsCntIndex OBJECT-TYPE
	SYNTAX  INTEGER(0..128)
	MAX-ACCESS  read-only
	STATUS current
	DESCRIPTION
        "
        Index definition for the pmc1002MondwRmonBitsCnt
        table
        "
	::= { pmc1002MondwRmonBitsCntEntry 1 }


pmc1002MondwRmonBitsCntValuePortn OBJECT-TYPE
	SYNTAX  Counter64
	MAX-ACCESS read-only
	STATUS current
	DESCRIPTION
        "
        Client Output Bits :This counter
        is increased each time a bit is
        received on the Output client port
        "
	::= { pmc1002MondwRmonBitsCntEntry 2 }


pmc1002MondwRmonBitsCntErrorPortn OBJECT-TYPE
	SYNTAX  EkiOnOff
	MAX-ACCESS read-only
	STATUS current
	DESCRIPTION
        "
        Output Bits Counter Error :This
        OID when set indicates the output
        Bits counter value is invalid on
        client port
        "
	::= { pmc1002MondwRmonBitsCntEntry 3 }


pmc1002MondwRmonBitsCntOverloadPortn OBJECT-TYPE
	SYNTAX  EkiOnOff
	MAX-ACCESS read-only
	STATUS current
	DESCRIPTION
        "
        Output Bits Counter Overload :This
        OID when set indicates an output
        Bits counter overload on client
        port
        "
	::= { pmc1002MondwRmonBitsCntEntry 4 }


--- *********************************************************
---     TABLE for the pmc1002MondwRmonUnicastCnt articles
--- *********************************************************

pmc1002MondwRmonUnicastCntTable OBJECT-TYPE
	SYNTAX  SEQUENCE OF Pmc1002MondwRmonUnicastCntEntry
	MAX-ACCESS not-accessible
	STATUS current
	DESCRIPTION
        "
        List of pmc1002MondwRmonUnicastCnt
        Article
        "
	::= { pmc1002RmonClient 176 }


pmc1002MondwRmonUnicastCntEntry OBJECT-TYPE
	SYNTAX Pmc1002MondwRmonUnicastCntEntry
	MAX-ACCESS not-accessible
	STATUS current
	DESCRIPTION
        "
        Row definition for the pmc1002MondwRmonUnicastCnt
        table
        "
	INDEX   { pmc1002MondwRmonUnicastCntIndex }
	::= { pmc1002MondwRmonUnicastCntTable 1 }


Pmc1002MondwRmonUnicastCntEntry ::=
	SEQUENCE {
	pmc1002MondwRmonUnicastCntIndex
		INTEGER,
	pmc1002MondwRmonUnicastCntValuePortn
		Counter64,
	pmc1002MondwRmonUnicastCntErrorPortn
		EkiOnOff,
	pmc1002MondwRmonUnicastCntOverloadPortn
		EkiOnOff
	}


pmc1002MondwRmonUnicastCntIndex OBJECT-TYPE
	SYNTAX  INTEGER(0..128)
	MAX-ACCESS  read-only
	STATUS current
	DESCRIPTION
        "
        Index definition for the pmc1002MondwRmonUnicastCnt
        table
        "
	::= { pmc1002MondwRmonUnicastCntEntry 1 }


pmc1002MondwRmonUnicastCntValuePortn OBJECT-TYPE
	SYNTAX  Counter64
	MAX-ACCESS read-only
	STATUS current
	DESCRIPTION
        "
        Client Output Unicast Packets
         :This counter is increased each
        time a Unicast packet is transmitted
        on client port   <Help>  This counter
        gives the number of Unicast packets
        transmitted on the client output
        port
        "
	::= { pmc1002MondwRmonUnicastCntEntry 2 }


pmc1002MondwRmonUnicastCntErrorPortn OBJECT-TYPE
	SYNTAX  EkiOnOff
	MAX-ACCESS read-only
	STATUS current
	DESCRIPTION
        "
        Output Unicast Counter Error :This
        OID when set indicates the output
        RMON timer is invalid on client
        port
        "
	::= { pmc1002MondwRmonUnicastCntEntry 3 }


pmc1002MondwRmonUnicastCntOverloadPortn OBJECT-TYPE
	SYNTAX  EkiOnOff
	MAX-ACCESS read-only
	STATUS current
	DESCRIPTION
        "
        Output Unicast Counter Overload
        :This OID when set indicates an
        output RMON timer overload on client
        port
        "
	::= { pmc1002MondwRmonUnicastCntEntry 4 }


--- *********************************************************
---     TABLE for the pmc1002MondwRmonNonUnicastCnt articles
--- *********************************************************

pmc1002MondwRmonNonUnicastCntTable OBJECT-TYPE
	SYNTAX  SEQUENCE OF Pmc1002MondwRmonNonUnicastCntEntry
	MAX-ACCESS not-accessible
	STATUS current
	DESCRIPTION
        "
        List of pmc1002MondwRmonNonUnicastCnt
        Article
        "
	::= { pmc1002RmonClient 184 }


pmc1002MondwRmonNonUnicastCntEntry OBJECT-TYPE
	SYNTAX Pmc1002MondwRmonNonUnicastCntEntry
	MAX-ACCESS not-accessible
	STATUS current
	DESCRIPTION
        "
        Row definition for the pmc1002MondwRmonNonUnicastCnt
        table
        "
	INDEX   { pmc1002MondwRmonNonUnicastCntIndex }
	::= { pmc1002MondwRmonNonUnicastCntTable 1 }


Pmc1002MondwRmonNonUnicastCntEntry ::=
	SEQUENCE {
	pmc1002MondwRmonNonUnicastCntIndex
		INTEGER,
	pmc1002MondwRmonNonUnicastCntValuePortn
		Counter64,
	pmc1002MondwRmonNonUnicastCntErrorPortn
		EkiOnOff,
	pmc1002MondwRmonNonUnicastCntOverloadPortn
		EkiOnOff
	}


pmc1002MondwRmonNonUnicastCntIndex OBJECT-TYPE
	SYNTAX  INTEGER(0..128)
	MAX-ACCESS  read-only
	STATUS current
	DESCRIPTION
        "
        Index definition for the pmc1002MondwRmonNonUnicastCnt
        table
        "
	::= { pmc1002MondwRmonNonUnicastCntEntry 1 }


pmc1002MondwRmonNonUnicastCntValuePortn OBJECT-TYPE
	SYNTAX  Counter64
	MAX-ACCESS read-only
	STATUS current
	DESCRIPTION
        "
        Client Output Non Unicast Packets
        :This counter is increased each
        time a Non Unicast packet is transmitted
        on client port   <Help>  This counter
        gives the number of Non Unicast
        packets transmitted on the client
        output port
        "
	::= { pmc1002MondwRmonNonUnicastCntEntry 2 }


pmc1002MondwRmonNonUnicastCntErrorPortn OBJECT-TYPE
	SYNTAX  EkiOnOff
	MAX-ACCESS read-only
	STATUS current
	DESCRIPTION
        "
        Output Non Unicast Counter Error
        :This OID when set indicates the
        output Bits counter value is invalid
        on client port
        "
	::= { pmc1002MondwRmonNonUnicastCntEntry 3 }


pmc1002MondwRmonNonUnicastCntOverloadPortn OBJECT-TYPE
	SYNTAX  EkiOnOff
	MAX-ACCESS read-only
	STATUS current
	DESCRIPTION
        "
        Output Non Unicast Counter Overload
        :This OID when set indicates an
        output Bits counter overload on
        client port
        "
	::= { pmc1002MondwRmonNonUnicastCntEntry 4 }


pmc1002MonCountersReset  OBJECT-TYPE
	SYNTAX EkiOnOff
	MAX-ACCESS read-write
	STATUS current
	DESCRIPTION
	"RMON Counters Reset:This OID resets and restarts all the RMON counters"
	::= { pmc1002RmonOther  359 }

pmc1002MonCountersStop  OBJECT-TYPE
	SYNTAX EkiOnOff
	MAX-ACCESS read-write
	STATUS current
	DESCRIPTION
	"RMON Counters stop:This OID stops all the RMON counters"
	::= { pmc1002RmonOther  360 }






--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pmc1002Mesrsynth0 OBJECT-TYPE
	  SYNTAX EkiMeasureType
	  MAX-ACCESS read-only
	  STATUS deprecated
	  DESCRIPTION
        "
        Not Used :This OID gives the unit
        used on AUX1 measurement of XFP#1
         (Unit = )
        "
	  ::= { pmc1002MesrOther 0 }



pmc1002Mesrsynth1 OBJECT-TYPE
	  SYNTAX EkiMeasureType
	  MAX-ACCESS read-only
	  STATUS deprecated
	  DESCRIPTION
        "
        Not Used :This OID gives the unit
        used on AUX2 measurement of XFP#1
         (Unit = )
        "
	  ::= { pmc1002MesrOther 1 }



--- *********************************************************
---     TABLE for the pmc1002MesrclientModTempMeas articles
--- *********************************************************

pmc1002MesrclientModTempMeasTable OBJECT-TYPE
	SYNTAX  SEQUENCE OF Pmc1002MesrclientModTempMeasEntry
	MAX-ACCESS not-accessible
	STATUS current
	DESCRIPTION
        "
        List of pmc1002MesrclientModTempMeas
        Article
        "
	::= { pmc1002MesrClient 16 }


pmc1002MesrclientModTempMeasEntry OBJECT-TYPE
	SYNTAX Pmc1002MesrclientModTempMeasEntry
	MAX-ACCESS not-accessible
	STATUS current
	DESCRIPTION
        "
        Row definition for the pmc1002MesrclientModTempMeas
        table
        "
	INDEX   { pmc1002MesrclientModTempMeasIndex }
	::= { pmc1002MesrclientModTempMeasTable 1 }


Pmc1002MesrclientModTempMeasEntry ::=
	SEQUENCE {
	pmc1002MesrclientModTempMeasIndex
		INTEGER,
	pmc1002MesrclientModTempMeasPortn
		INTEGER
	}


pmc1002MesrclientModTempMeasIndex OBJECT-TYPE
	SYNTAX  INTEGER(0..128)
	MAX-ACCESS  read-only
	STATUS current
	DESCRIPTION
        "
        Index definition for the pmc1002MesrclientModTempMeas
        table
        "
	::= { pmc1002MesrclientModTempMeasEntry 1 }


pmc1002MesrclientModTempMeasPortn OBJECT-TYPE
	SYNTAX  INTEGER (0..65535)
	MAX-ACCESS read-only
	STATUS current
	DESCRIPTION
        "
        Client SFP+ Temperature :This
         OID gives the temperature value
        of the XFP plugged in port, read
        from the DDM (Digital Diagnostic
        Monitoring) (Temperature = AV/256)
         (Unit = C)  <Help>  This measure
        gives the temperature of the client
        transceiver
        "
	::= { pmc1002MesrclientModTempMeasEntry 2 }


--- *********************************************************
---     TABLE for the pmc1002MesrclientBiasCurrentMeas articles
--- *********************************************************

pmc1002MesrclientBiasCurrentMeasTable OBJECT-TYPE
	SYNTAX  SEQUENCE OF Pmc1002MesrclientBiasCurrentMeasEntry
	MAX-ACCESS not-accessible
	STATUS current
	DESCRIPTION
        "
        List of pmc1002MesrclientBiasCurrentMeas
        Article
        "
	::= { pmc1002MesrClient 32 }


pmc1002MesrclientBiasCurrentMeasEntry OBJECT-TYPE
	SYNTAX Pmc1002MesrclientBiasCurrentMeasEntry
	MAX-ACCESS not-accessible
	STATUS current
	DESCRIPTION
        "
        Row definition for the pmc1002MesrclientBiasCurrentMeas
        table
        "
	INDEX   { pmc1002MesrclientBiasCurrentMeasIndex }
	::= { pmc1002MesrclientBiasCurrentMeasTable 1 }


Pmc1002MesrclientBiasCurrentMeasEntry ::=
	SEQUENCE {
	pmc1002MesrclientBiasCurrentMeasIndex
		INTEGER,
	pmc1002MesrclientBiasCurrentMeasPortn
		INTEGER
	}


pmc1002MesrclientBiasCurrentMeasIndex OBJECT-TYPE
	SYNTAX  INTEGER(0..128)
	MAX-ACCESS  read-only
	STATUS current
	DESCRIPTION
        "
        Index definition for the pmc1002MesrclientBiasCurrentMeas
        table
        "
	::= { pmc1002MesrclientBiasCurrentMeasEntry 1 }


pmc1002MesrclientBiasCurrentMeasPortn OBJECT-TYPE
	SYNTAX  INTEGER (0..65535)
	MAX-ACCESS read-only
	STATUS current
	DESCRIPTION
        "
        Client SFP+ Laser Bias :This OID
        gives the bias value of the XFP
        plugged into port, read from the
        DDM (Digital Diagnostic Monitoring)
         (Bias = AV/500) (Unit = mA)  <Help>
         This measure gives the bias of
        the client transceiver
        "
	::= { pmc1002MesrclientBiasCurrentMeasEntry 2 }


--- *********************************************************
---     TABLE for the pmc1002MesrclientTxPowerMeas articles
--- *********************************************************

pmc1002MesrclientTxPowerMeasTable OBJECT-TYPE
	SYNTAX  SEQUENCE OF Pmc1002MesrclientTxPowerMeasEntry
	MAX-ACCESS not-accessible
	STATUS current
	DESCRIPTION
        "
        List of pmc1002MesrclientTxPowerMeas
        Article
        "
	::= { pmc1002MesrClient 40 }


pmc1002MesrclientTxPowerMeasEntry OBJECT-TYPE
	SYNTAX Pmc1002MesrclientTxPowerMeasEntry
	MAX-ACCESS not-accessible
	STATUS current
	DESCRIPTION
        "
        Row definition for the pmc1002MesrclientTxPowerMeas
        table
        "
	INDEX   { pmc1002MesrclientTxPowerMeasIndex }
	::= { pmc1002MesrclientTxPowerMeasTable 1 }


Pmc1002MesrclientTxPowerMeasEntry ::=
	SEQUENCE {
	pmc1002MesrclientTxPowerMeasIndex
		INTEGER,
	pmc1002MesrclientTxPowerMeasPortn
		INTEGER
	}


pmc1002MesrclientTxPowerMeasIndex OBJECT-TYPE
	SYNTAX  INTEGER(0..128)
	MAX-ACCESS  read-only
	STATUS current
	DESCRIPTION
        "
        Index definition for the pmc1002MesrclientTxPowerMeas
        table
        "
	::= { pmc1002MesrclientTxPowerMeasEntry 1 }


pmc1002MesrclientTxPowerMeasPortn OBJECT-TYPE
	SYNTAX  INTEGER (0..65535)
	MAX-ACCESS read-only
	STATUS current
	DESCRIPTION
        "
        Client SFP+ Tx Power :This OID
        gives the transmit power value
         of the XFP plugged into port,
         read from the DDM (Digital Diagnostic
        Monitoring) (Power = 10*log(AV)-40)
        (Unit = dBm)  <Help>  This measure
        gives the Tx optical power of the
        client transceiver
        "
	::= { pmc1002MesrclientTxPowerMeasEntry 2 }


--- *********************************************************
---     TABLE for the pmc1002MesrclientRxPowerMeas articles
--- *********************************************************

pmc1002MesrclientRxPowerMeasTable OBJECT-TYPE
	SYNTAX  SEQUENCE OF Pmc1002MesrclientRxPowerMeasEntry
	MAX-ACCESS not-accessible
	STATUS current
	DESCRIPTION
        "
        List of pmc1002MesrclientRxPowerMeas
        Article
        "
	::= { pmc1002MesrClient 48 }


pmc1002MesrclientRxPowerMeasEntry OBJECT-TYPE
	SYNTAX Pmc1002MesrclientRxPowerMeasEntry
	MAX-ACCESS not-accessible
	STATUS current
	DESCRIPTION
        "
        Row definition for the pmc1002MesrclientRxPowerMeas
        table
        "
	INDEX   { pmc1002MesrclientRxPowerMeasIndex }
	::= { pmc1002MesrclientRxPowerMeasTable 1 }


Pmc1002MesrclientRxPowerMeasEntry ::=
	SEQUENCE {
	pmc1002MesrclientRxPowerMeasIndex
		INTEGER,
	pmc1002MesrclientRxPowerMeasPortn
		INTEGER
	}


pmc1002MesrclientRxPowerMeasIndex OBJECT-TYPE
	SYNTAX  INTEGER(0..128)
	MAX-ACCESS  read-only
	STATUS current
	DESCRIPTION
        "
        Index definition for the pmc1002MesrclientRxPowerMeas
        table
        "
	::= { pmc1002MesrclientRxPowerMeasEntry 1 }


pmc1002MesrclientRxPowerMeasPortn OBJECT-TYPE
	SYNTAX  INTEGER (0..65535)
	MAX-ACCESS read-only
	STATUS current
	DESCRIPTION
        "
        Client SFP+ Rx Power :This OID
        gives the receive power value of
        the XFP plugged into port, read
        in the DDM (Digital Diagnostic
         Monitoring) (Power = 10*log(AV)-40)
        (Unit = dBm)  <Help>  This measure
        gives the Rx optical power of the
        client transceiver
        "
	::= { pmc1002MesrclientRxPowerMeasEntry 2 }


--- *********************************************************
---     TABLE for the pmc1002Mesrline1ModTempMeas articles
--- *********************************************************

pmc1002Mesrline1ModTempMeasTable OBJECT-TYPE
	SYNTAX  SEQUENCE OF Pmc1002Mesrline1ModTempMeasEntry
	MAX-ACCESS not-accessible
	STATUS current
	DESCRIPTION
        "
        List of pmc1002Mesrline1ModTempMeas
        Article
        "
	::= { pmc1002MesrLine 208 }


pmc1002Mesrline1ModTempMeasEntry OBJECT-TYPE
	SYNTAX Pmc1002Mesrline1ModTempMeasEntry
	MAX-ACCESS not-accessible
	STATUS current
	DESCRIPTION
        "
        Row definition for the pmc1002Mesrline1ModTempMeas
        table
        "
	INDEX   { pmc1002Mesrline1ModTempMeasIndex }
	::= { pmc1002Mesrline1ModTempMeasTable 1 }


Pmc1002Mesrline1ModTempMeasEntry ::=
	SEQUENCE {
	pmc1002Mesrline1ModTempMeasIndex
		INTEGER,
	pmc1002Mesrline1ModTempMeasPortn
		INTEGER
	}


pmc1002Mesrline1ModTempMeasIndex OBJECT-TYPE
	SYNTAX  INTEGER(0..128)
	MAX-ACCESS  read-only
	STATUS current
	DESCRIPTION
        "
        Index definition for the pmc1002Mesrline1ModTempMeas
        table
        "
	::= { pmc1002Mesrline1ModTempMeasEntry 1 }


pmc1002Mesrline1ModTempMeasPortn OBJECT-TYPE
	SYNTAX  INTEGER (0..65535)
	MAX-ACCESS read-only
	STATUS current
	DESCRIPTION
        "
        Line Optical Module Temperature
        :This OID gives the temperature
        of the XFP or OTX plugged in line#n,
        read from the DDM (Digital Diagnostic
        Monitoring) (Temperature = AV/256)
        (Unit = C)  <Help>  This measure
        gives the temperature of the line
        transceiver
        "
	::= { pmc1002Mesrline1ModTempMeasEntry 2 }


--- *********************************************************
---     TABLE for the pmc1002Mesrline1Reserved articles
--- *********************************************************

pmc1002Mesrline1ReservedTable OBJECT-TYPE
	SYNTAX  SEQUENCE OF Pmc1002Mesrline1ReservedEntry
	MAX-ACCESS not-accessible
	STATUS deprecated
	DESCRIPTION
        "
        List of pmc1002Mesrline1Reserved
        Article
        "
	::= { pmc1002MesrLine 209 }


pmc1002Mesrline1ReservedEntry OBJECT-TYPE
	SYNTAX Pmc1002Mesrline1ReservedEntry
	MAX-ACCESS not-accessible
	STATUS deprecated
	DESCRIPTION
        "
        Row definition for the pmc1002Mesrline1Reserved
        table
        "
	INDEX   { pmc1002Mesrline1ReservedIndex }
	::= { pmc1002Mesrline1ReservedTable 1 }


Pmc1002Mesrline1ReservedEntry ::=
	SEQUENCE {
	pmc1002Mesrline1ReservedIndex
		INTEGER,
	pmc1002Mesrline1ReservedPortn
		INTEGER
	}


pmc1002Mesrline1ReservedIndex OBJECT-TYPE
	SYNTAX  INTEGER(0..128)
	MAX-ACCESS  read-only
	STATUS deprecated
	DESCRIPTION
        "
        Index definition for the pmc1002Mesrline1Reserved
        table
        "
	::= { pmc1002Mesrline1ReservedEntry 1 }


pmc1002Mesrline1ReservedPortn OBJECT-TYPE
	SYNTAX  INTEGER (0..65535)
	MAX-ACCESS read-only
	STATUS deprecated
	DESCRIPTION
        "
        Not Used :Reserved
        "
	::= { pmc1002Mesrline1ReservedEntry 2 }


--- *********************************************************
---     TABLE for the pmc1002Mesrline1BiasCurrentMeas articles
--- *********************************************************

pmc1002Mesrline1BiasCurrentMeasTable OBJECT-TYPE
	SYNTAX  SEQUENCE OF Pmc1002Mesrline1BiasCurrentMeasEntry
	MAX-ACCESS not-accessible
	STATUS current
	DESCRIPTION
        "
        List of pmc1002Mesrline1BiasCurrentMeas
        Article
        "
	::= { pmc1002MesrLine 210 }


pmc1002Mesrline1BiasCurrentMeasEntry OBJECT-TYPE
	SYNTAX Pmc1002Mesrline1BiasCurrentMeasEntry
	MAX-ACCESS not-accessible
	STATUS current
	DESCRIPTION
        "
        Row definition for the pmc1002Mesrline1BiasCurrentMeas
        table
        "
	INDEX   { pmc1002Mesrline1BiasCurrentMeasIndex }
	::= { pmc1002Mesrline1BiasCurrentMeasTable 1 }


Pmc1002Mesrline1BiasCurrentMeasEntry ::=
	SEQUENCE {
	pmc1002Mesrline1BiasCurrentMeasIndex
		INTEGER,
	pmc1002Mesrline1BiasCurrentMeasPortn
		INTEGER
	}


pmc1002Mesrline1BiasCurrentMeasIndex OBJECT-TYPE
	SYNTAX  INTEGER(0..128)
	MAX-ACCESS  read-only
	STATUS current
	DESCRIPTION
        "
        Index definition for the pmc1002Mesrline1BiasCurrentMeas
        table
        "
	::= { pmc1002Mesrline1BiasCurrentMeasEntry 1 }


pmc1002Mesrline1BiasCurrentMeasPortn OBJECT-TYPE
	SYNTAX  INTEGER (0..65535)
	MAX-ACCESS read-only
	STATUS current
	DESCRIPTION
        "
        XFP Or OTX Laser Bias :This OID
        gives the bias value of the XFP
        or OTX plugged in line #n, read
        from the DDM (Digital Diagnostic
        Monitoring) (Bias = AV/500) (Unit
        = mA)  <Help>  This measure gives
        the bias of the line transceiver
        "
	::= { pmc1002Mesrline1BiasCurrentMeasEntry 2 }


--- *********************************************************
---     TABLE for the pmc1002Mesrline1TxPowerMeas articles
--- *********************************************************

pmc1002Mesrline1TxPowerMeasTable OBJECT-TYPE
	SYNTAX  SEQUENCE OF Pmc1002Mesrline1TxPowerMeasEntry
	MAX-ACCESS not-accessible
	STATUS current
	DESCRIPTION
        "
        List of pmc1002Mesrline1TxPowerMeas
        Article
        "
	::= { pmc1002MesrLine 211 }


pmc1002Mesrline1TxPowerMeasEntry OBJECT-TYPE
	SYNTAX Pmc1002Mesrline1TxPowerMeasEntry
	MAX-ACCESS not-accessible
	STATUS current
	DESCRIPTION
        "
        Row definition for the pmc1002Mesrline1TxPowerMeas
        table
        "
	INDEX   { pmc1002Mesrline1TxPowerMeasIndex }
	::= { pmc1002Mesrline1TxPowerMeasTable 1 }


Pmc1002Mesrline1TxPowerMeasEntry ::=
	SEQUENCE {
	pmc1002Mesrline1TxPowerMeasIndex
		INTEGER,
	pmc1002Mesrline1TxPowerMeasPortn
		INTEGER
	}


pmc1002Mesrline1TxPowerMeasIndex OBJECT-TYPE
	SYNTAX  INTEGER(0..128)
	MAX-ACCESS  read-only
	STATUS current
	DESCRIPTION
        "
        Index definition for the pmc1002Mesrline1TxPowerMeas
        table
        "
	::= { pmc1002Mesrline1TxPowerMeasEntry 1 }


pmc1002Mesrline1TxPowerMeasPortn OBJECT-TYPE
	SYNTAX  INTEGER (0..65535)
	MAX-ACCESS read-only
	STATUS current
	DESCRIPTION
        "
        Line Optical Module Tx Power :This
        OID gives the transmit power value
        of the XFP or OTX plugged in line
        #n, read from the DDM (Digital
           Diagnostic Monitoring) (Power
        = 10*log(AV)-40) (Unit = dBm)
         <Help>  This measure gives the
        Tx optical power of the line transceiver
        "
	::= { pmc1002Mesrline1TxPowerMeasEntry 2 }


--- *********************************************************
---     TABLE for the pmc1002Mesrline1RxPowerMeas articles
--- *********************************************************

pmc1002Mesrline1RxPowerMeasTable OBJECT-TYPE
	SYNTAX  SEQUENCE OF Pmc1002Mesrline1RxPowerMeasEntry
	MAX-ACCESS not-accessible
	STATUS current
	DESCRIPTION
        "
        List of pmc1002Mesrline1RxPowerMeas
        Article
        "
	::= { pmc1002MesrLine 212 }


pmc1002Mesrline1RxPowerMeasEntry OBJECT-TYPE
	SYNTAX Pmc1002Mesrline1RxPowerMeasEntry
	MAX-ACCESS not-accessible
	STATUS current
	DESCRIPTION
        "
        Row definition for the pmc1002Mesrline1RxPowerMeas
        table
        "
	INDEX   { pmc1002Mesrline1RxPowerMeasIndex }
	::= { pmc1002Mesrline1RxPowerMeasTable 1 }


Pmc1002Mesrline1RxPowerMeasEntry ::=
	SEQUENCE {
	pmc1002Mesrline1RxPowerMeasIndex
		INTEGER,
	pmc1002Mesrline1RxPowerMeasPortn
		INTEGER
	}


pmc1002Mesrline1RxPowerMeasIndex OBJECT-TYPE
	SYNTAX  INTEGER(0..128)
	MAX-ACCESS  read-only
	STATUS current
	DESCRIPTION
        "
        Index definition for the pmc1002Mesrline1RxPowerMeas
        table
        "
	::= { pmc1002Mesrline1RxPowerMeasEntry 1 }


pmc1002Mesrline1RxPowerMeasPortn OBJECT-TYPE
	SYNTAX  INTEGER (0..65535)
	MAX-ACCESS read-only
	STATUS current
	DESCRIPTION
        "
        Line Optical Module Rx Power :This
        OID gives the receive power value
        of the XFP or OTX plugged in line
        #n, read from the DDM (Digital
         Diagnostic Monitoring) (Power
         = 10*log(AV)-40) (Unit = dBm)
          <Help>  This measure gives the
        Rx optical power of the line transceiver
        "
	::= { pmc1002Mesrline1RxPowerMeasEntry 2 }


--- *********************************************************
---     TABLE for the pmc1002Mesrline1Aux1Meas articles
--- *********************************************************

pmc1002Mesrline1Aux1MeasTable OBJECT-TYPE
	SYNTAX  SEQUENCE OF Pmc1002Mesrline1Aux1MeasEntry
	MAX-ACCESS not-accessible
	STATUS deprecated
	DESCRIPTION
        "
        List of pmc1002Mesrline1Aux1Meas
        Article
        "
	::= { pmc1002MesrLine 213 }


pmc1002Mesrline1Aux1MeasEntry OBJECT-TYPE
	SYNTAX Pmc1002Mesrline1Aux1MeasEntry
	MAX-ACCESS not-accessible
	STATUS deprecated
	DESCRIPTION
        "
        Row definition for the pmc1002Mesrline1Aux1Meas
        table
        "
	INDEX   { pmc1002Mesrline1Aux1MeasIndex }
	::= { pmc1002Mesrline1Aux1MeasTable 1 }


Pmc1002Mesrline1Aux1MeasEntry ::=
	SEQUENCE {
	pmc1002Mesrline1Aux1MeasIndex
		INTEGER,
	pmc1002Mesrline1Aux1MeasPortn
		INTEGER
	}


pmc1002Mesrline1Aux1MeasIndex OBJECT-TYPE
	SYNTAX  INTEGER(0..128)
	MAX-ACCESS  read-only
	STATUS deprecated
	DESCRIPTION
        "
        Index definition for the pmc1002Mesrline1Aux1Meas
        table
        "
	::= { pmc1002Mesrline1Aux1MeasEntry 1 }


pmc1002Mesrline1Aux1MeasPortn OBJECT-TYPE
	SYNTAX  INTEGER (0..65535)
	MAX-ACCESS read-only
	STATUS deprecated
	DESCRIPTION
        "
        Not Used :This OID gives the receive
        power value read in the DDM (Digital
        Diagnostic Monitoring) of the XFP
        or OTX plugged in line #n (Unit
        = ?)
        "
	::= { pmc1002Mesrline1Aux1MeasEntry 2 }


--- *********************************************************
---     TABLE for the pmc1002Mesrline1Aux2Meas articles
--- *********************************************************

pmc1002Mesrline1Aux2MeasTable OBJECT-TYPE
	SYNTAX  SEQUENCE OF Pmc1002Mesrline1Aux2MeasEntry
	MAX-ACCESS not-accessible
	STATUS deprecated
	DESCRIPTION
        "
        List of pmc1002Mesrline1Aux2Meas
        Article
        "
	::= { pmc1002MesrLine 214 }


pmc1002Mesrline1Aux2MeasEntry OBJECT-TYPE
	SYNTAX Pmc1002Mesrline1Aux2MeasEntry
	MAX-ACCESS not-accessible
	STATUS deprecated
	DESCRIPTION
        "
        Row definition for the pmc1002Mesrline1Aux2Meas
        table
        "
	INDEX   { pmc1002Mesrline1Aux2MeasIndex }
	::= { pmc1002Mesrline1Aux2MeasTable 1 }


Pmc1002Mesrline1Aux2MeasEntry ::=
	SEQUENCE {
	pmc1002Mesrline1Aux2MeasIndex
		INTEGER,
	pmc1002Mesrline1Aux2MeasPortn
		INTEGER
	}


pmc1002Mesrline1Aux2MeasIndex OBJECT-TYPE
	SYNTAX  INTEGER(0..128)
	MAX-ACCESS  read-only
	STATUS deprecated
	DESCRIPTION
        "
        Index definition for the pmc1002Mesrline1Aux2Meas
        table
        "
	::= { pmc1002Mesrline1Aux2MeasEntry 1 }


pmc1002Mesrline1Aux2MeasPortn OBJECT-TYPE
	SYNTAX  INTEGER (0..65535)
	MAX-ACCESS read-only
	STATUS deprecated
	DESCRIPTION
        "
        Not Used :This OID gives the receive
        power value read in the DDM (Digital
        Diagnostic Monitoring) of the XFP
        or OTX plugged in line #n (Unit
        = ?)
        "
	::= { pmc1002Mesrline1Aux2MeasEntry 2 }


--- *********************************************************
---     TABLE for the pmc1002Mesrline1Aging articles
--- *********************************************************

pmc1002Mesrline1AgingTable OBJECT-TYPE
	SYNTAX  SEQUENCE OF Pmc1002Mesrline1AgingEntry
	MAX-ACCESS not-accessible
	STATUS current
	DESCRIPTION
        "
        List of pmc1002Mesrline1Aging
         Article
        "
	::= { pmc1002MesrLine 224 }


pmc1002Mesrline1AgingEntry OBJECT-TYPE
	SYNTAX Pmc1002Mesrline1AgingEntry
	MAX-ACCESS not-accessible
	STATUS current
	DESCRIPTION
        "
        Row definition for the pmc1002Mesrline1Aging
        table
        "
	INDEX   { pmc1002Mesrline1AgingIndex }
	::= { pmc1002Mesrline1AgingTable 1 }


Pmc1002Mesrline1AgingEntry ::=
	SEQUENCE {
	pmc1002Mesrline1AgingIndex
		INTEGER,
	pmc1002Mesrline1AgingPortn
		INTEGER
	}


pmc1002Mesrline1AgingIndex OBJECT-TYPE
	SYNTAX  INTEGER(0..128)
	MAX-ACCESS  read-only
	STATUS current
	DESCRIPTION
        "
        Index definition for the pmc1002Mesrline1Aging
        table
        "
	::= { pmc1002Mesrline1AgingEntry 1 }


pmc1002Mesrline1AgingPortn OBJECT-TYPE
	SYNTAX  INTEGER (0..65535)
	MAX-ACCESS read-only
	STATUS current
	DESCRIPTION
        "
        Line OTX TLH Aging :This OID gives
        the aging of the Line OTX TLH,
         read from the DDM (Digital Diagnostic
        Monitoring)  (Aging = AV)  (Unit
        = %)  <Help>  This measure gives
        the aging of the Line OTX TLH
        "
	::= { pmc1002Mesrline1AgingEntry 2 }


--- *********************************************************
---     TABLE for the pmc1002Mesrline1LaserTemperature articles
--- *********************************************************

pmc1002Mesrline1LaserTemperatureTable OBJECT-TYPE
	SYNTAX  SEQUENCE OF Pmc1002Mesrline1LaserTemperatureEntry
	MAX-ACCESS not-accessible
	STATUS deprecated
	DESCRIPTION
        "
        List of pmc1002Mesrline1LaserTemperature
        Article
        "
	::= { pmc1002MesrLine 225 }


pmc1002Mesrline1LaserTemperatureEntry OBJECT-TYPE
	SYNTAX Pmc1002Mesrline1LaserTemperatureEntry
	MAX-ACCESS not-accessible
	STATUS deprecated
	DESCRIPTION
        "
        Row definition for the pmc1002Mesrline1LaserTemperature
        table
        "
	INDEX   { pmc1002Mesrline1LaserTemperatureIndex }
	::= { pmc1002Mesrline1LaserTemperatureTable 1 }


Pmc1002Mesrline1LaserTemperatureEntry ::=
	SEQUENCE {
	pmc1002Mesrline1LaserTemperatureIndex
		INTEGER,
	pmc1002Mesrline1LaserTemperaturePortn
		INTEGER
	}


pmc1002Mesrline1LaserTemperatureIndex OBJECT-TYPE
	SYNTAX  INTEGER(0..128)
	MAX-ACCESS  read-only
	STATUS deprecated
	DESCRIPTION
        "
        Index definition for the pmc1002Mesrline1LaserTemperature
        table
        "
	::= { pmc1002Mesrline1LaserTemperatureEntry 1 }


pmc1002Mesrline1LaserTemperaturePortn OBJECT-TYPE
	SYNTAX  INTEGER (0..65535)
	MAX-ACCESS read-only
	STATUS deprecated
	DESCRIPTION
        "
        Line OTX TLH Laser Temperature
        :This OID gives the laser temperature
        of the Line OTX TLH, read from
         the DDM (Digital Diagnostic Monitoring)
        (Temperature = AV/256) (Unit =
         C)  <Help>  This measure gives
        the laser temperature of the Line
        OTX TLH
        "
	::= { pmc1002Mesrline1LaserTemperatureEntry 2 }


--- *********************************************************
---     TABLE for the pmc1002Mesrline1FreqDeviation articles
--- *********************************************************

pmc1002Mesrline1FreqDeviationTable OBJECT-TYPE
	SYNTAX  SEQUENCE OF Pmc1002Mesrline1FreqDeviationEntry
	MAX-ACCESS not-accessible
	STATUS current
	DESCRIPTION
        "
        List of pmc1002Mesrline1FreqDeviation
        Article
        "
	::= { pmc1002MesrLine 226 }


pmc1002Mesrline1FreqDeviationEntry OBJECT-TYPE
	SYNTAX Pmc1002Mesrline1FreqDeviationEntry
	MAX-ACCESS not-accessible
	STATUS current
	DESCRIPTION
        "
        Row definition for the pmc1002Mesrline1FreqDeviation
        table
        "
	INDEX   { pmc1002Mesrline1FreqDeviationIndex }
	::= { pmc1002Mesrline1FreqDeviationTable 1 }


Pmc1002Mesrline1FreqDeviationEntry ::=
	SEQUENCE {
	pmc1002Mesrline1FreqDeviationIndex
		INTEGER,
	pmc1002Mesrline1FreqDeviationPortn
		INTEGER
	}


pmc1002Mesrline1FreqDeviationIndex OBJECT-TYPE
	SYNTAX  INTEGER(0..128)
	MAX-ACCESS  read-only
	STATUS current
	DESCRIPTION
        "
        Index definition for the pmc1002Mesrline1FreqDeviation
        table
        "
	::= { pmc1002Mesrline1FreqDeviationEntry 1 }


pmc1002Mesrline1FreqDeviationPortn OBJECT-TYPE
	SYNTAX  INTEGER (0..65535)
	MAX-ACCESS read-only
	STATUS current
	DESCRIPTION
        "
        Line OTX TLH Frequency Deviation
        :This OID gives the frequency deviation
        of the Line OTX TLH, read from
         the DDM (Digital Diagnostic Monitoring)
         (Deviation = (AV-32768)*100)
         (Unit = MHz)  <Help>  This measure
        gives the frequency deviation of
        the Line OTX TLH
        "
	::= { pmc1002Mesrline1FreqDeviationEntry 2 }


--- *********************************************************
---     TABLE for the pmc1002Mesrline1LaserWvlength articles
--- *********************************************************

pmc1002Mesrline1LaserWvlengthTable OBJECT-TYPE
	SYNTAX  SEQUENCE OF Pmc1002Mesrline1LaserWvlengthEntry
	MAX-ACCESS not-accessible
	STATUS current
	DESCRIPTION
        "
        List of pmc1002Mesrline1LaserWvlength
        Article
        "
	::= { pmc1002MesrLine 227 }


pmc1002Mesrline1LaserWvlengthEntry OBJECT-TYPE
	SYNTAX Pmc1002Mesrline1LaserWvlengthEntry
	MAX-ACCESS not-accessible
	STATUS current
	DESCRIPTION
        "
        Row definition for the pmc1002Mesrline1LaserWvlength
        table
        "
	INDEX   { pmc1002Mesrline1LaserWvlengthIndex }
	::= { pmc1002Mesrline1LaserWvlengthTable 1 }


Pmc1002Mesrline1LaserWvlengthEntry ::=
	SEQUENCE {
	pmc1002Mesrline1LaserWvlengthIndex
		INTEGER,
	pmc1002Mesrline1LaserWvlengthPortn
		INTEGER
	}


pmc1002Mesrline1LaserWvlengthIndex OBJECT-TYPE
	SYNTAX  INTEGER(0..128)
	MAX-ACCESS  read-only
	STATUS current
	DESCRIPTION
        "
        Index definition for the pmc1002Mesrline1LaserWvlength
        table
        "
	::= { pmc1002Mesrline1LaserWvlengthEntry 1 }


pmc1002Mesrline1LaserWvlengthPortn OBJECT-TYPE
	SYNTAX  INTEGER (0..65535)
	MAX-ACCESS read-only
	STATUS current
	DESCRIPTION
        "
        Line Optical Module Wavelength
        :This OID gives the laser wavelength
        of the Line OTX TLH, read from
         the DDM (Digital Diagnostic Monitoring)
        (Wavelength=299792458/((193,100+(AV-32768
        )*12,5)*10 3))  (Unit = nm)  <Help>
         This measure gives the laser wavelength
        of the Line OTX TLH
        "
	::= { pmc1002Mesrline1LaserWvlengthEntry 2 }







--- *****************************************************
--- $$$$$$$$$$$$$$$$$$$$$$$$$$$$$$$$$$$$$$$$$$$$$$$$$$$$$
---     PERFORMANCE
--- $$$$$$$$$$$$$$$$$$$$$$$$$$$$$$$$$$$$$$$$$$$$$$$$$$$$$
--- *****************************************************



--- *****************************************************
---     Leaf of the telecomClientCurrent15Stat
--- *****************************************************
--- *********************************************************
---     TABLE for the pmc1002PerfTelecomClientCurrent15Stat articles
--- *********************************************************

pmc1002PerfTelecomClientCurrent15StatTable OBJECT-TYPE
	SYNTAX  SEQUENCE OF Pmc1002PerfTelecomClientCurrent15StatEntry
	MAX-ACCESS not-accessible
	STATUS current
	DESCRIPTION
        "
        List of pmc1002PerfTelecomClientCurrent15Stat
        Article
        "
	::= { pmc1002MonClient 16 }


pmc1002PerfTelecomClientCurrent15StatEntry OBJECT-TYPE
	SYNTAX Pmc1002PerfTelecomClientCurrent15StatEntry
	MAX-ACCESS not-accessible
	STATUS current
	DESCRIPTION
        "
        Row definition for the pmc1002PerfTelecomClientCurrent15Stat
        table
        "
	INDEX   { pmc1002PerfTelecomClientCurrent15StatIndex }
	::= { pmc1002PerfTelecomClientCurrent15StatTable 1 }


Pmc1002PerfTelecomClientCurrent15StatEntry ::=
	SEQUENCE {
	pmc1002PerfTelecomClientCurrent15StatIndex
		INTEGER,
	pmc1002PerfTelecomClientCurrent15StatInvCvPortn
		EkiOnOff,
	pmc1002PerfTelecomClientCurrent15StatCvValuePortn
		Unsigned32,
	pmc1002PerfTelecomClientCurrent15StatInvEsPortn
		EkiOnOff,
	pmc1002PerfTelecomClientCurrent15StatEsValuePortn
		Unsigned32,
	pmc1002PerfTelecomClientCurrent15StatInvSesPortn
		EkiOnOff,
	pmc1002PerfTelecomClientCurrent15StatSesValuePortn
		Unsigned32,
	pmc1002PerfTelecomClientCurrent15StatInvSefsPortn
		EkiOnOff,
	pmc1002PerfTelecomClientCurrent15StatSefsValuePortn
		Unsigned32,
	pmc1002PerfTelecomClientCurrent15StatInvUasPortn
		EkiOnOff,
	pmc1002PerfTelecomClientCurrent15StatUasValuePortn
		Unsigned32
	}


pmc1002PerfTelecomClientCurrent15StatIndex OBJECT-TYPE
	SYNTAX  INTEGER(0..128)
	MAX-ACCESS  read-only
	STATUS current
	DESCRIPTION
        "
        Index definition for the pmc1002PerfTelecomClientCurrent15Stat
        table
        "
	::= { pmc1002PerfTelecomClientCurrent15StatEntry 1 }


pmc1002PerfTelecomClientCurrent15StatInvCvPortn OBJECT-TYPE
	SYNTAX  EkiOnOff
	MAX-ACCESS read-only
	STATUS current
	DESCRIPTION
        "
        Current 15-min CV counter inv.
        :This OID indicates that the current
        15-min Coding Violation counter
        is invalid
        "
	::= { pmc1002PerfTelecomClientCurrent15StatEntry 2 }


pmc1002PerfTelecomClientCurrent15StatCvValuePortn OBJECT-TYPE
	SYNTAX  Unsigned32
	MAX-ACCESS read-only
	STATUS current
	DESCRIPTION
        "
        Current 15-min CV counter :This
        OID gives the current 15-min Coding
        Violation counter value
        "
	::= { pmc1002PerfTelecomClientCurrent15StatEntry 3 }


pmc1002PerfTelecomClientCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pmc1002PerfTelecomClientCurrent15StatEntry 4 }


pmc1002PerfTelecomClientCurrent15StatEsValuePortn OBJECT-TYPE
	SYNTAX  Unsigned32
	MAX-ACCESS read-only
	STATUS current
	DESCRIPTION
        "
        Current 15-min ES counter :This
        OID gives the current 15-min Errored
        Second counter value
        "
	::= { pmc1002PerfTelecomClientCurrent15StatEntry 5 }


pmc1002PerfTelecomClientCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pmc1002PerfTelecomClientCurrent15StatEntry 6 }


pmc1002PerfTelecomClientCurrent15StatSesValuePortn OBJECT-TYPE
	SYNTAX  Unsigned32
	MAX-ACCESS read-only
	STATUS current
	DESCRIPTION
        "
        Current 15-min SES counter :This
        OID gives the current 15-min severely
        Errored Second counter value
        "
	::= { pmc1002PerfTelecomClientCurrent15StatEntry 7 }


pmc1002PerfTelecomClientCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pmc1002PerfTelecomClientCurrent15StatEntry 8 }


pmc1002PerfTelecomClientCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pmc1002PerfTelecomClientCurrent15StatEntry 9 }


pmc1002PerfTelecomClientCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pmc1002PerfTelecomClientCurrent15StatEntry 10 }


pmc1002PerfTelecomClientCurrent15StatUasValuePortn OBJECT-TYPE
	SYNTAX  Unsigned32
	MAX-ACCESS read-only
	STATUS current
	DESCRIPTION
        "
        Current 15-min UAS counter :This
        OID gives the current 15-min UnAvailable
        Second counter value
        "
	::= { pmc1002PerfTelecomClientCurrent15StatEntry 11 }


--- *****************************************************
---     Leaf of the telecomClientPast15Stat
--- *****************************************************
--- *********************************************************
---     TABLE for the pmc1002PerfTelecomClientPast15StatHistory articles
--- *********************************************************

pmc1002PerfTelecomClientPast15StatHistoryPort1Table OBJECT-TYPE
	SYNTAX  SEQUENCE OF Pmc1002PerfTelecomClientPast15StatHistoryPort1Entry
	MAX-ACCESS not-accessible
	STATUS current
	DESCRIPTION
        "
        List of pmc1002PerfTelecomClientPast15StatHistory
        Article
        "
	::= { pmc1002MonClient 24 }


pmc1002PerfTelecomClientPast15StatHistoryPort1Entry OBJECT-TYPE
	SYNTAX Pmc1002PerfTelecomClientPast15StatHistoryPort1Entry
	MAX-ACCESS not-accessible
	STATUS current
	DESCRIPTION
        "
        Row definition for the pmc1002PerfTelecomClientPast15StatHistory
        table
        "
	INDEX   { pmc1002PerfTelecomClientPast15StatHistoryPort1Index }
	::= { pmc1002PerfTelecomClientPast15StatHistoryPort1Table 1 }


Pmc1002PerfTelecomClientPast15StatHistoryPort1Entry ::=
	SEQUENCE {
	pmc1002PerfTelecomClientPast15StatHistoryPort1Index
		INTEGER,
	pmc1002PerfTelecomClientPast15StatHistoryInvCvPort1
		EkiOnOff,
	pmc1002PerfTelecomClientPast15StatHistoryCvValuePort1
		Unsigned32,
	pmc1002PerfTelecomClientPast15StatHistoryInvEsPort1
		EkiOnOff,
	pmc1002PerfTelecomClientPast15StatHistoryEsValuePort1
		Unsigned32,
	pmc1002PerfTelecomClientPast15StatHistoryInvSesPort1
		EkiOnOff,
	pmc1002PerfTelecomClientPast15StatHistorySesValuePort1
		Unsigned32,
	pmc1002PerfTelecomClientPast15StatHistoryInvSefsPort1
		EkiOnOff,
	pmc1002PerfTelecomClientPast15StatHistorySefsValuePort1
		Unsigned32,
	pmc1002PerfTelecomClientPast15StatHistoryInvUasPort1
		EkiOnOff,
	pmc1002PerfTelecomClientPast15StatHistoryUasValuePort1
		Unsigned32
	}


pmc1002PerfTelecomClientPast15StatHistoryPort1Index OBJECT-TYPE
	SYNTAX  INTEGER(0..128)
	MAX-ACCESS  read-only
	STATUS current
	DESCRIPTION
        "
        Index definition for the pmc1002PerfTelecomClientPast15StatHistory
        table
        "
	::= { pmc1002PerfTelecomClientPast15StatHistoryPort1Entry 1 }


pmc1002PerfTelecomClientPast15StatHistoryInvCvPort1 OBJECT-TYPE
	SYNTAX  EkiOnOff
	MAX-ACCESS read-only
	STATUS current
	DESCRIPTION
        "
        Previous 15-min CV counter inv.
        :This OID indicates that the previous
        15-min Coding Violation counter
        is invalid
        "
	::= { pmc1002PerfTelecomClientPast15StatHistoryPort1Entry 2 }


pmc1002PerfTelecomClientPast15StatHistoryCvValuePort1 OBJECT-TYPE
	SYNTAX  Unsigned32
	MAX-ACCESS read-only
	STATUS current
	DESCRIPTION
        "
        Previous 15-min CV counter :This
        OID gives the previous 15-min Coding
        Violation counter value
        "
	::= { pmc1002PerfTelecomClientPast15StatHistoryPort1Entry 3 }


pmc1002PerfTelecomClientPast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pmc1002PerfTelecomClientPast15StatHistoryPort1Entry 4 }


pmc1002PerfTelecomClientPast15StatHistoryEsValuePort1 OBJECT-TYPE
	SYNTAX  Unsigned32
	MAX-ACCESS read-only
	STATUS current
	DESCRIPTION
        "
        Previous 15-min ES counter :This
        OID gives the previous 15-min Errored
        Second counter value
        "
	::= { pmc1002PerfTelecomClientPast15StatHistoryPort1Entry 5 }


pmc1002PerfTelecomClientPast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pmc1002PerfTelecomClientPast15StatHistoryPort1Entry 6 }


pmc1002PerfTelecomClientPast15StatHistorySesValuePort1 OBJECT-TYPE
	SYNTAX  Unsigned32
	MAX-ACCESS read-only
	STATUS current
	DESCRIPTION
        "
        Previous 15-min SES counter :This
        OID gives the previous 15-min severely
        Errored Second counter value
        "
	::= { pmc1002PerfTelecomClientPast15StatHistoryPort1Entry 7 }


pmc1002PerfTelecomClientPast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pmc1002PerfTelecomClientPast15StatHistoryPort1Entry 8 }


pmc1002PerfTelecomClientPast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pmc1002PerfTelecomClientPast15StatHistoryPort1Entry 9 }


pmc1002PerfTelecomClientPast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pmc1002PerfTelecomClientPast15StatHistoryPort1Entry 10 }


pmc1002PerfTelecomClientPast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pmc1002PerfTelecomClientPast15StatHistoryPort1Entry 11 }


--- *****************************************************
---     Leaf of the telecomClientCurrent24Stat
--- *****************************************************
--- *********************************************************
---     TABLE for the pmc1002PerfTelecomClientCurrent24Stat articles
--- *********************************************************

pmc1002PerfTelecomClientCurrent24StatTable OBJECT-TYPE
	SYNTAX  SEQUENCE OF Pmc1002PerfTelecomClientCurrent24StatEntry
	MAX-ACCESS not-accessible
	STATUS current
	DESCRIPTION
        "
        List of pmc1002PerfTelecomClientCurrent24Stat
        Article
        "
	::= { pmc1002MonClient 32 }


pmc1002PerfTelecomClientCurrent24StatEntry OBJECT-TYPE
	SYNTAX Pmc1002PerfTelecomClientCurrent24StatEntry
	MAX-ACCESS not-accessible
	STATUS current
	DESCRIPTION
        "
        Row definition for the pmc1002PerfTelecomClientCurrent24Stat
        table
        "
	INDEX   { pmc1002PerfTelecomClientCurrent24StatIndex }
	::= { pmc1002PerfTelecomClientCurrent24StatTable 1 }


Pmc1002PerfTelecomClientCurrent24StatEntry ::=
	SEQUENCE {
	pmc1002PerfTelecomClientCurrent24StatIndex
		INTEGER,
	pmc1002PerfTelecomClientCurrent24StatInvCvPortn
		EkiOnOff,
	pmc1002PerfTelecomClientCurrent24StatCvValuePortn
		Unsigned32,
	pmc1002PerfTelecomClientCurrent24StatInvEsPortn
		EkiOnOff,
	pmc1002PerfTelecomClientCurrent24StatEsValuePortn
		Unsigned32,
	pmc1002PerfTelecomClientCurrent24StatInvSesPortn
		EkiOnOff,
	pmc1002PerfTelecomClientCurrent24StatSesValuePortn
		Unsigned32,
	pmc1002PerfTelecomClientCurrent24StatInvSefsPortn
		EkiOnOff,
	pmc1002PerfTelecomClientCurrent24StatSefsValuePortn
		Unsigned32,
	pmc1002PerfTelecomClientCurrent24StatInvUasPortn
		EkiOnOff,
	pmc1002PerfTelecomClientCurrent24StatUasValuePortn
		Unsigned32
	}


pmc1002PerfTelecomClientCurrent24StatIndex OBJECT-TYPE
	SYNTAX  INTEGER(0..128)
	MAX-ACCESS  read-only
	STATUS current
	DESCRIPTION
        "
        Index definition for the pmc1002PerfTelecomClientCurrent24Stat
        table
        "
	::= { pmc1002PerfTelecomClientCurrent24StatEntry 1 }


pmc1002PerfTelecomClientCurrent24StatInvCvPortn OBJECT-TYPE
	SYNTAX  EkiOnOff
	MAX-ACCESS read-only
	STATUS current
	DESCRIPTION
        "
        Current 24-hours CV counter inv.
        :This OID indicates that the current
        24-hours Coding Violation counter
        is invalid
        "
	::= { pmc1002PerfTelecomClientCurrent24StatEntry 2 }


pmc1002PerfTelecomClientCurrent24StatCvValuePortn OBJECT-TYPE
	SYNTAX  Unsigned32
	MAX-ACCESS read-only
	STATUS current
	DESCRIPTION
        "
        Current 24-hours CV counter :This
        OID gives the current 24-hours
         Coding Violation counter value
        "
	::= { pmc1002PerfTelecomClientCurrent24StatEntry 3 }


pmc1002PerfTelecomClientCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pmc1002PerfTelecomClientCurrent24StatEntry 4 }


pmc1002PerfTelecomClientCurrent24StatEsValuePortn OBJECT-TYPE
	SYNTAX  Unsigned32
	MAX-ACCESS read-only
	STATUS current
	DESCRIPTION
        "
        Current 24-hours ES counter :This
        OID gives the current 24-hours
         Errored Second counter value
        "
	::= { pmc1002PerfTelecomClientCurrent24StatEntry 5 }


pmc1002PerfTelecomClientCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pmc1002PerfTelecomClientCurrent24StatEntry 6 }


pmc1002PerfTelecomClientCurrent24StatSesValuePortn OBJECT-TYPE
	SYNTAX  Unsigned32
	MAX-ACCESS read-only
	STATUS current
	DESCRIPTION
        "
        Current 24-hours SES counter :This
        OID gives the current 24-hours
         severely Errored Second counter
        value
        "
	::= { pmc1002PerfTelecomClientCurrent24StatEntry 7 }


pmc1002PerfTelecomClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pmc1002PerfTelecomClientCurrent24StatEntry 8 }


pmc1002PerfTelecomClientCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pmc1002PerfTelecomClientCurrent24StatEntry 9 }


pmc1002PerfTelecomClientCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pmc1002PerfTelecomClientCurrent24StatEntry 10 }


pmc1002PerfTelecomClientCurrent24StatUasValuePortn OBJECT-TYPE
	SYNTAX  Unsigned32
	MAX-ACCESS read-only
	STATUS current
	DESCRIPTION
        "
        Current 24-hours UAS counter :This
        OID gives the current 24-hours
         UnAvailable Second counter value
        "
	::= { pmc1002PerfTelecomClientCurrent24StatEntry 11 }


--- *****************************************************
---     Leaf of the telecomClientPast24Stat
--- *****************************************************
--- *********************************************************
---     TABLE for the pmc1002PerfTelecomClientPast24StatHistory articles
--- *********************************************************

pmc1002PerfTelecomClientPast24StatHistoryPort1Table OBJECT-TYPE
	SYNTAX  SEQUENCE OF Pmc1002PerfTelecomClientPast24StatHistoryPort1Entry
	MAX-ACCESS not-accessible
	STATUS current
	DESCRIPTION
        "
        List of pmc1002PerfTelecomClientPast24StatHistory
        Article
        "
	::= { pmc1002MonClient 40 }


pmc1002PerfTelecomClientPast24StatHistoryPort1Entry OBJECT-TYPE
	SYNTAX Pmc1002PerfTelecomClientPast24StatHistoryPort1Entry
	MAX-ACCESS not-accessible
	STATUS current
	DESCRIPTION
        "
        Row definition for the pmc1002PerfTelecomClientPast24StatHistory
        table
        "
	INDEX   { pmc1002PerfTelecomClientPast24StatHistoryPort1Index }
	::= { pmc1002PerfTelecomClientPast24StatHistoryPort1Table 1 }


Pmc1002PerfTelecomClientPast24StatHistoryPort1Entry ::=
	SEQUENCE {
	pmc1002PerfTelecomClientPast24StatHistoryPort1Index
		INTEGER,
	pmc1002PerfTelecomClientPast24StatHistoryInvCvPort1
		EkiOnOff,
	pmc1002PerfTelecomClientPast24StatHistoryCvValuePort1
		Unsigned32,
	pmc1002PerfTelecomClientPast24StatHistoryInvEsPort1
		EkiOnOff,
	pmc1002PerfTelecomClientPast24StatHistoryEsValuePort1
		Unsigned32,
	pmc1002PerfTelecomClientPast24StatHistoryInvSesPort1
		EkiOnOff,
	pmc1002PerfTelecomClientPast24StatHistorySesValuePort1
		Unsigned32,
	pmc1002PerfTelecomClientPast24StatHistoryInvSefsPort1
		EkiOnOff,
	pmc1002PerfTelecomClientPast24StatHistorySefsValuePort1
		Unsigned32,
	pmc1002PerfTelecomClientPast24StatHistoryInvUasPort1
		EkiOnOff,
	pmc1002PerfTelecomClientPast24StatHistoryUasValuePort1
		Unsigned32
	}


pmc1002PerfTelecomClientPast24StatHistoryPort1Index OBJECT-TYPE
	SYNTAX  INTEGER(0..128)
	MAX-ACCESS  read-only
	STATUS current
	DESCRIPTION
        "
        Index definition for the pmc1002PerfTelecomClientPast24StatHistory
        table
        "
	::= { pmc1002PerfTelecomClientPast24StatHistoryPort1Entry 1 }


pmc1002PerfTelecomClientPast24StatHistoryInvCvPort1 OBJECT-TYPE
	SYNTAX  EkiOnOff
	MAX-ACCESS read-only
	STATUS current
	DESCRIPTION
        "
        Previous 24-hours CV counter inv.
        :This OID indicates that the previous
        24-hours Coding Violation counter
        is invalid
        "
	::= { pmc1002PerfTelecomClientPast24StatHistoryPort1Entry 2 }


pmc1002PerfTelecomClientPast24StatHistoryCvValuePort1 OBJECT-TYPE
	SYNTAX  Unsigned32
	MAX-ACCESS read-only
	STATUS current
	DESCRIPTION
        "
        Previous 24-hours CV counter :This
        OID gives the previous 24-hours
        Coding Violation counter value
        "
	::= { pmc1002PerfTelecomClientPast24StatHistoryPort1Entry 3 }


pmc1002PerfTelecomClientPast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pmc1002PerfTelecomClientPast24StatHistoryPort1Entry 4 }


pmc1002PerfTelecomClientPast24StatHistoryEsValuePort1 OBJECT-TYPE
	SYNTAX  Unsigned32
	MAX-ACCESS read-only
	STATUS current
	DESCRIPTION
        "
        Previous 24-hours ES counter :This
        OID gives the previous 24-hours
        Errored Second counter value
        "
	::= { pmc1002PerfTelecomClientPast24StatHistoryPort1Entry 5 }


pmc1002PerfTelecomClientPast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pmc1002PerfTelecomClientPast24StatHistoryPort1Entry 6 }


pmc1002PerfTelecomClientPast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pmc1002PerfTelecomClientPast24StatHistoryPort1Entry 7 }


pmc1002PerfTelecomClientPast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pmc1002PerfTelecomClientPast24StatHistoryPort1Entry 8 }


pmc1002PerfTelecomClientPast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pmc1002PerfTelecomClientPast24StatHistoryPort1Entry 9 }


pmc1002PerfTelecomClientPast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pmc1002PerfTelecomClientPast24StatHistoryPort1Entry 10 }


pmc1002PerfTelecomClientPast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pmc1002PerfTelecomClientPast24StatHistoryPort1Entry 11 }


--- *****************************************************
---     Leaf of the telecomLineCurrent15Stat
--- *****************************************************
--- *********************************************************
---     TABLE for the pmc1002PerfTelecomLineCurrent15Stat articles
--- *********************************************************

pmc1002PerfTelecomLineCurrent15StatTable OBJECT-TYPE
	SYNTAX  SEQUENCE OF Pmc1002PerfTelecomLineCurrent15StatEntry
	MAX-ACCESS not-accessible
	STATUS current
	DESCRIPTION
        "
        List of pmc1002PerfTelecomLineCurrent15Stat
        Article
        "
	::= { pmc1002MonLine 128 }


pmc1002PerfTelecomLineCurrent15StatEntry OBJECT-TYPE
	SYNTAX Pmc1002PerfTelecomLineCurrent15StatEntry
	MAX-ACCESS not-accessible
	STATUS current
	DESCRIPTION
        "
        Row definition for the pmc1002PerfTelecomLineCurrent15Stat
        table
        "
	INDEX   { pmc1002PerfTelecomLineCurrent15StatIndex }
	::= { pmc1002PerfTelecomLineCurrent15StatTable 1 }


Pmc1002PerfTelecomLineCurrent15StatEntry ::=
	SEQUENCE {
	pmc1002PerfTelecomLineCurrent15StatIndex
		INTEGER,
	pmc1002PerfTelecomLineCurrent15StatInvCvPortn
		EkiOnOff,
	pmc1002PerfTelecomLineCurrent15StatCvValuePortn
		Unsigned32,
	pmc1002PerfTelecomLineCurrent15StatInvEsPortn
		EkiOnOff,
	pmc1002PerfTelecomLineCurrent15StatEsValuePortn
		Unsigned32,
	pmc1002PerfTelecomLineCurrent15StatInvSesPortn
		EkiOnOff,
	pmc1002PerfTelecomLineCurrent15StatSesValuePortn
		Unsigned32,
	pmc1002PerfTelecomLineCurrent15StatInvSefsPortn
		EkiOnOff,
	pmc1002PerfTelecomLineCurrent15StatSefsValuePortn
		Unsigned32,
	pmc1002PerfTelecomLineCurrent15StatInvUasPortn
		EkiOnOff,
	pmc1002PerfTelecomLineCurrent15StatUasValuePortn
		Unsigned32
	}


pmc1002PerfTelecomLineCurrent15StatIndex OBJECT-TYPE
	SYNTAX  INTEGER(0..128)
	MAX-ACCESS  read-only
	STATUS current
	DESCRIPTION
        "
        Index definition for the pmc1002PerfTelecomLineCurrent15Stat
        table
        "
	::= { pmc1002PerfTelecomLineCurrent15StatEntry 1 }


pmc1002PerfTelecomLineCurrent15StatInvCvPortn OBJECT-TYPE
	SYNTAX  EkiOnOff
	MAX-ACCESS read-only
	STATUS current
	DESCRIPTION
        "
        Current 15-min CV counter inv.
        :This OID indicates that the current
        15-min Coding Violation counter
        is invalid
        "
	::= { pmc1002PerfTelecomLineCurrent15StatEntry 2 }


pmc1002PerfTelecomLineCurrent15StatCvValuePortn OBJECT-TYPE
	SYNTAX  Unsigned32
	MAX-ACCESS read-only
	STATUS current
	DESCRIPTION
        "
        Current 15-min CV counter :This
        OID gives the current 15-min Coding
        Violation counter value
        "
	::= { pmc1002PerfTelecomLineCurrent15StatEntry 3 }


pmc1002PerfTelecomLineCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pmc1002PerfTelecomLineCurrent15StatEntry 4 }


pmc1002PerfTelecomLineCurrent15StatEsValuePortn OBJECT-TYPE
	SYNTAX  Unsigned32
	MAX-ACCESS read-only
	STATUS current
	DESCRIPTION
        "
        Current 15-min ES counter :This
        OID gives the current 15-min Errored
        Second counter value
        "
	::= { pmc1002PerfTelecomLineCurrent15StatEntry 5 }


pmc1002PerfTelecomLineCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pmc1002PerfTelecomLineCurrent15StatEntry 6 }


pmc1002PerfTelecomLineCurrent15StatSesValuePortn OBJECT-TYPE
	SYNTAX  Unsigned32
	MAX-ACCESS read-only
	STATUS current
	DESCRIPTION
        "
        Current 15-min SES counter :This
        OID gives the current 15-min severely
        Errored Second counter value
        "
	::= { pmc1002PerfTelecomLineCurrent15StatEntry 7 }


pmc1002PerfTelecomLineCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pmc1002PerfTelecomLineCurrent15StatEntry 8 }


pmc1002PerfTelecomLineCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pmc1002PerfTelecomLineCurrent15StatEntry 9 }


pmc1002PerfTelecomLineCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pmc1002PerfTelecomLineCurrent15StatEntry 10 }


pmc1002PerfTelecomLineCurrent15StatUasValuePortn OBJECT-TYPE
	SYNTAX  Unsigned32
	MAX-ACCESS read-only
	STATUS current
	DESCRIPTION
        "
        Current 15-min UAS counter :This
        OID gives the current 15-min UnAvailable
        Second counter value
        "
	::= { pmc1002PerfTelecomLineCurrent15StatEntry 11 }


--- *****************************************************
---     Leaf of the telecomLinePast15Stat
--- *****************************************************
--- *********************************************************
---     TABLE for the pmc1002PerfTelecomLinePast15StatHistory articles
--- *********************************************************

pmc1002PerfTelecomLinePast15StatHistoryPort1Table OBJECT-TYPE
	SYNTAX  SEQUENCE OF Pmc1002PerfTelecomLinePast15StatHistoryPort1Entry
	MAX-ACCESS not-accessible
	STATUS current
	DESCRIPTION
        "
        List of pmc1002PerfTelecomLinePast15StatHistory
        Article
        "
	::= { pmc1002MonLine 129 }


pmc1002PerfTelecomLinePast15StatHistoryPort1Entry OBJECT-TYPE
	SYNTAX Pmc1002PerfTelecomLinePast15StatHistoryPort1Entry
	MAX-ACCESS not-accessible
	STATUS current
	DESCRIPTION
        "
        Row definition for the pmc1002PerfTelecomLinePast15StatHistory
        table
        "
	INDEX   { pmc1002PerfTelecomLinePast15StatHistoryPort1Index }
	::= { pmc1002PerfTelecomLinePast15StatHistoryPort1Table 1 }


Pmc1002PerfTelecomLinePast15StatHistoryPort1Entry ::=
	SEQUENCE {
	pmc1002PerfTelecomLinePast15StatHistoryPort1Index
		INTEGER,
	pmc1002PerfTelecomLinePast15StatHistoryInvCvPort1
		EkiOnOff,
	pmc1002PerfTelecomLinePast15StatHistoryCvValuePort1
		Unsigned32,
	pmc1002PerfTelecomLinePast15StatHistoryInvEsPort1
		EkiOnOff,
	pmc1002PerfTelecomLinePast15StatHistoryEsValuePort1
		Unsigned32,
	pmc1002PerfTelecomLinePast15StatHistoryInvSesPort1
		EkiOnOff,
	pmc1002PerfTelecomLinePast15StatHistorySesValuePort1
		Unsigned32,
	pmc1002PerfTelecomLinePast15StatHistoryInvSefsPort1
		EkiOnOff,
	pmc1002PerfTelecomLinePast15StatHistorySefsValuePort1
		Unsigned32,
	pmc1002PerfTelecomLinePast15StatHistoryInvUasPort1
		EkiOnOff,
	pmc1002PerfTelecomLinePast15StatHistoryUasValuePort1
		Unsigned32
	}


pmc1002PerfTelecomLinePast15StatHistoryPort1Index OBJECT-TYPE
	SYNTAX  INTEGER(0..128)
	MAX-ACCESS  read-only
	STATUS current
	DESCRIPTION
        "
        Index definition for the pmc1002PerfTelecomLinePast15StatHistory
        table
        "
	::= { pmc1002PerfTelecomLinePast15StatHistoryPort1Entry 1 }


pmc1002PerfTelecomLinePast15StatHistoryInvCvPort1 OBJECT-TYPE
	SYNTAX  EkiOnOff
	MAX-ACCESS read-only
	STATUS current
	DESCRIPTION
        "
        Previous 15-min CV counter inv.
        :This OID indicates that the previous
        15-min Coding Violation counter
        is invalid
        "
	::= { pmc1002PerfTelecomLinePast15StatHistoryPort1Entry 2 }


pmc1002PerfTelecomLinePast15StatHistoryCvValuePort1 OBJECT-TYPE
	SYNTAX  Unsigned32
	MAX-ACCESS read-only
	STATUS current
	DESCRIPTION
        "
        Previous 15-min CV counter :This
        OID gives the previous 15-min Coding
        Violation counter value
        "
	::= { pmc1002PerfTelecomLinePast15StatHistoryPort1Entry 3 }


pmc1002PerfTelecomLinePast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pmc1002PerfTelecomLinePast15StatHistoryPort1Entry 4 }


pmc1002PerfTelecomLinePast15StatHistoryEsValuePort1 OBJECT-TYPE
	SYNTAX  Unsigned32
	MAX-ACCESS read-only
	STATUS current
	DESCRIPTION
        "
        Previous 15-min ES counter :This
        OID gives the previous 15-min Errored
        Second counter value
        "
	::= { pmc1002PerfTelecomLinePast15StatHistoryPort1Entry 5 }


pmc1002PerfTelecomLinePast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pmc1002PerfTelecomLinePast15StatHistoryPort1Entry 6 }


pmc1002PerfTelecomLinePast15StatHistorySesValuePort1 OBJECT-TYPE
	SYNTAX  Unsigned32
	MAX-ACCESS read-only
	STATUS current
	DESCRIPTION
        "
        Previous 15-min SES counter :This
        OID gives the previous 15-min severely
        Errored Second counter value
        "
	::= { pmc1002PerfTelecomLinePast15StatHistoryPort1Entry 7 }


pmc1002PerfTelecomLinePast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pmc1002PerfTelecomLinePast15StatHistoryPort1Entry 8 }


pmc1002PerfTelecomLinePast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pmc1002PerfTelecomLinePast15StatHistoryPort1Entry 9 }


pmc1002PerfTelecomLinePast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pmc1002PerfTelecomLinePast15StatHistoryPort1Entry 10 }


pmc1002PerfTelecomLinePast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pmc1002PerfTelecomLinePast15StatHistoryPort1Entry 11 }


--- *****************************************************
---     Leaf of the telecomLineCurrent24Stat
--- *****************************************************
--- *********************************************************
---     TABLE for the pmc1002PerfTelecomLineCurrent24Stat articles
--- *********************************************************

pmc1002PerfTelecomLineCurrent24StatTable OBJECT-TYPE
	SYNTAX  SEQUENCE OF Pmc1002PerfTelecomLineCurrent24StatEntry
	MAX-ACCESS not-accessible
	STATUS current
	DESCRIPTION
        "
        List of pmc1002PerfTelecomLineCurrent24Stat
        Article
        "
	::= { pmc1002MonLine 130 }


pmc1002PerfTelecomLineCurrent24StatEntry OBJECT-TYPE
	SYNTAX Pmc1002PerfTelecomLineCurrent24StatEntry
	MAX-ACCESS not-accessible
	STATUS current
	DESCRIPTION
        "
        Row definition for the pmc1002PerfTelecomLineCurrent24Stat
        table
        "
	INDEX   { pmc1002PerfTelecomLineCurrent24StatIndex }
	::= { pmc1002PerfTelecomLineCurrent24StatTable 1 }


Pmc1002PerfTelecomLineCurrent24StatEntry ::=
	SEQUENCE {
	pmc1002PerfTelecomLineCurrent24StatIndex
		INTEGER,
	pmc1002PerfTelecomLineCurrent24StatInvCvPortn
		EkiOnOff,
	pmc1002PerfTelecomLineCurrent24StatCvValuePortn
		Unsigned32,
	pmc1002PerfTelecomLineCurrent24StatInvEsPortn
		EkiOnOff,
	pmc1002PerfTelecomLineCurrent24StatEsValuePortn
		Unsigned32,
	pmc1002PerfTelecomLineCurrent24StatInvSesPortn
		EkiOnOff,
	pmc1002PerfTelecomLineCurrent24StatSesValuePortn
		Unsigned32,
	pmc1002PerfTelecomLineCurrent24StatInvSefsPortn
		EkiOnOff,
	pmc1002PerfTelecomLineCurrent24StatSefsValuePortn
		Unsigned32,
	pmc1002PerfTelecomLineCurrent24StatInvUasPortn
		EkiOnOff,
	pmc1002PerfTelecomLineCurrent24StatUasValuePortn
		Unsigned32
	}


pmc1002PerfTelecomLineCurrent24StatIndex OBJECT-TYPE
	SYNTAX  INTEGER(0..128)
	MAX-ACCESS  read-only
	STATUS current
	DESCRIPTION
        "
        Index definition for the pmc1002PerfTelecomLineCurrent24Stat
        table
        "
	::= { pmc1002PerfTelecomLineCurrent24StatEntry 1 }


pmc1002PerfTelecomLineCurrent24StatInvCvPortn OBJECT-TYPE
	SYNTAX  EkiOnOff
	MAX-ACCESS read-only
	STATUS current
	DESCRIPTION
        "
        Current 24-hours CV counter inv.
        :This OID indicates that the current
        24-hours Coding Violation counter
        is invalid
        "
	::= { pmc1002PerfTelecomLineCurrent24StatEntry 2 }


pmc1002PerfTelecomLineCurrent24StatCvValuePortn OBJECT-TYPE
	SYNTAX  Unsigned32
	MAX-ACCESS read-only
	STATUS current
	DESCRIPTION
        "
        Current 24-hours CV counter :This
        OID gives the current 24-hours
         Coding Violation counter value
        "
	::= { pmc1002PerfTelecomLineCurrent24StatEntry 3 }


pmc1002PerfTelecomLineCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pmc1002PerfTelecomLineCurrent24StatEntry 4 }


pmc1002PerfTelecomLineCurrent24StatEsValuePortn OBJECT-TYPE
	SYNTAX  Unsigned32
	MAX-ACCESS read-only
	STATUS current
	DESCRIPTION
        "
        Current 24-hours ES counter :This
        OID gives the current 24-hours
         Errored Second counter value
        "
	::= { pmc1002PerfTelecomLineCurrent24StatEntry 5 }


pmc1002PerfTelecomLineCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pmc1002PerfTelecomLineCurrent24StatEntry 6 }


pmc1002PerfTelecomLineCurrent24StatSesValuePortn OBJECT-TYPE
	SYNTAX  Unsigned32
	MAX-ACCESS read-only
	STATUS current
	DESCRIPTION
        "
        Current 24-hours SES counter :This
        OID gives the current 24-hours
         severely Errored Second counter
        value
        "
	::= { pmc1002PerfTelecomLineCurrent24StatEntry 7 }


pmc1002PerfTelecomLineCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pmc1002PerfTelecomLineCurrent24StatEntry 8 }


pmc1002PerfTelecomLineCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pmc1002PerfTelecomLineCurrent24StatEntry 9 }


pmc1002PerfTelecomLineCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pmc1002PerfTelecomLineCurrent24StatEntry 10 }


pmc1002PerfTelecomLineCurrent24StatUasValuePortn OBJECT-TYPE
	SYNTAX  Unsigned32
	MAX-ACCESS read-only
	STATUS current
	DESCRIPTION
        "
        Current 24-hours UAS counter :This
        OID gives the current 24-hours
         UnAvailable Second counter value
        "
	::= { pmc1002PerfTelecomLineCurrent24StatEntry 11 }


--- *****************************************************
---     Leaf of the telecomLinePast24Stat
--- *****************************************************
--- *********************************************************
---     TABLE for the pmc1002PerfTelecomLinePast24StatHistory articles
--- *********************************************************

pmc1002PerfTelecomLinePast24StatHistoryPort1Table OBJECT-TYPE
	SYNTAX  SEQUENCE OF Pmc1002PerfTelecomLinePast24StatHistoryPort1Entry
	MAX-ACCESS not-accessible
	STATUS current
	DESCRIPTION
        "
        List of pmc1002PerfTelecomLinePast24StatHistory
        Article
        "
	::= { pmc1002MonLine 131 }


pmc1002PerfTelecomLinePast24StatHistoryPort1Entry OBJECT-TYPE
	SYNTAX Pmc1002PerfTelecomLinePast24StatHistoryPort1Entry
	MAX-ACCESS not-accessible
	STATUS current
	DESCRIPTION
        "
        Row definition for the pmc1002PerfTelecomLinePast24StatHistory
        table
        "
	INDEX   { pmc1002PerfTelecomLinePast24StatHistoryPort1Index }
	::= { pmc1002PerfTelecomLinePast24StatHistoryPort1Table 1 }


Pmc1002PerfTelecomLinePast24StatHistoryPort1Entry ::=
	SEQUENCE {
	pmc1002PerfTelecomLinePast24StatHistoryPort1Index
		INTEGER,
	pmc1002PerfTelecomLinePast24StatHistoryInvCvPort1
		EkiOnOff,
	pmc1002PerfTelecomLinePast24StatHistoryCvValuePort1
		Unsigned32,
	pmc1002PerfTelecomLinePast24StatHistoryInvEsPort1
		EkiOnOff,
	pmc1002PerfTelecomLinePast24StatHistoryEsValuePort1
		Unsigned32,
	pmc1002PerfTelecomLinePast24StatHistoryInvSesPort1
		EkiOnOff,
	pmc1002PerfTelecomLinePast24StatHistorySesValuePort1
		Unsigned32,
	pmc1002PerfTelecomLinePast24StatHistoryInvSefsPort1
		EkiOnOff,
	pmc1002PerfTelecomLinePast24StatHistorySefsValuePort1
		Unsigned32,
	pmc1002PerfTelecomLinePast24StatHistoryInvUasPort1
		EkiOnOff,
	pmc1002PerfTelecomLinePast24StatHistoryUasValuePort1
		Unsigned32
	}


pmc1002PerfTelecomLinePast24StatHistoryPort1Index OBJECT-TYPE
	SYNTAX  INTEGER(0..128)
	MAX-ACCESS  read-only
	STATUS current
	DESCRIPTION
        "
        Index definition for the pmc1002PerfTelecomLinePast24StatHistory
        table
        "
	::= { pmc1002PerfTelecomLinePast24StatHistoryPort1Entry 1 }


pmc1002PerfTelecomLinePast24StatHistoryInvCvPort1 OBJECT-TYPE
	SYNTAX  EkiOnOff
	MAX-ACCESS read-only
	STATUS current
	DESCRIPTION
        "
        Previous 24-hours CV counter inv.
        :This OID indicates that the previous
        24-hours Coding Violation counter
        is invalid
        "
	::= { pmc1002PerfTelecomLinePast24StatHistoryPort1Entry 2 }


pmc1002PerfTelecomLinePast24StatHistoryCvValuePort1 OBJECT-TYPE
	SYNTAX  Unsigned32
	MAX-ACCESS read-only
	STATUS current
	DESCRIPTION
        "
        Previous 24-hours CV counter :This
        OID gives the previous 24-hours
        Coding Violation counter value
        "
	::= { pmc1002PerfTelecomLinePast24StatHistoryPort1Entry 3 }


pmc1002PerfTelecomLinePast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pmc1002PerfTelecomLinePast24StatHistoryPort1Entry 4 }


pmc1002PerfTelecomLinePast24StatHistoryEsValuePort1 OBJECT-TYPE
	SYNTAX  Unsigned32
	MAX-ACCESS read-only
	STATUS current
	DESCRIPTION
        "
        Previous 24-hours ES counter :This
        OID gives the previous 24-hours
        Errored Second counter value
        "
	::= { pmc1002PerfTelecomLinePast24StatHistoryPort1Entry 5 }


pmc1002PerfTelecomLinePast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pmc1002PerfTelecomLinePast24StatHistoryPort1Entry 6 }


pmc1002PerfTelecomLinePast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pmc1002PerfTelecomLinePast24StatHistoryPort1Entry 7 }


pmc1002PerfTelecomLinePast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pmc1002PerfTelecomLinePast24StatHistoryPort1Entry 8 }


pmc1002PerfTelecomLinePast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pmc1002PerfTelecomLinePast24StatHistoryPort1Entry 9 }


pmc1002PerfTelecomLinePast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pmc1002PerfTelecomLinePast24StatHistoryPort1Entry 10 }


pmc1002PerfTelecomLinePast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pmc1002PerfTelecomLinePast24StatHistoryPort1Entry 11 }


--- *****************************************************
---     Leaf of the datacomClientCurrent15Stat
--- *****************************************************
--- *********************************************************
---     TABLE for the pmc1002PerfDatacomClientCurrent15Stat articles
--- *********************************************************

pmc1002PerfDatacomClientCurrent15StatTable OBJECT-TYPE
	SYNTAX  SEQUENCE OF Pmc1002PerfDatacomClientCurrent15StatEntry
	MAX-ACCESS not-accessible
	STATUS current
	DESCRIPTION
        "
        List of pmc1002PerfDatacomClientCurrent15Stat
        Article
        "
	::= { pmc1002MonClient 256 }


pmc1002PerfDatacomClientCurrent15StatEntry OBJECT-TYPE
	SYNTAX Pmc1002PerfDatacomClientCurrent15StatEntry
	MAX-ACCESS not-accessible
	STATUS current
	DESCRIPTION
        "
        Row definition for the pmc1002PerfDatacomClientCurrent15Stat
        table
        "
	INDEX   { pmc1002PerfDatacomClientCurrent15StatIndex }
	::= { pmc1002PerfDatacomClientCurrent15StatTable 1 }


Pmc1002PerfDatacomClientCurrent15StatEntry ::=
	SEQUENCE {
	pmc1002PerfDatacomClientCurrent15StatIndex
		INTEGER,
	pmc1002perfdatacomclientCurrent15StatOutNonunicastCountInvPortn
		EkiOnOff,
	pmc1002perfdatacomclientCurrent15StatOutNonunicastCountPortn
		Counter64,
	pmc1002perfdatacomclientCurrent15StatOutUnicastCountInvPortn
		EkiOnOff,
	pmc1002perfdatacomclientCurrent15StatOutUnicastCountPortn
		Counter64,
	pmc1002perfdatacomclientCurrent15StatOutMulticastCountInvPortn
		EkiOnOff,
	pmc1002perfdatacomclientCurrent15StatOutMulticastCountPortn
		Counter64,
	pmc1002perfdatacomclientCurrent15StatOutBroadcastCountInvPortn
		EkiOnOff,
	pmc1002perfdatacomclientCurrent15StatOutBroadcastCountPortn
		Counter64,
	pmc1002perfdatacomclientCurrent15StatOutBytesCountInvPortn
		EkiOnOff,
	pmc1002perfdatacomclientCurrent15StatOutBytesCountPortn
		Counter64,
	pmc1002perfdatacomclientCurrent15StatInNonunicastCountInvPortn
		EkiOnOff,
	pmc1002perfdatacomclientCurrent15StatInNonunicastCountPortn
		Counter64,
	pmc1002perfdatacomclientCurrent15StatInUnicastCountInvPortn
		EkiOnOff,
	pmc1002perfdatacomclientCurrent15StatInUnicastCountPortn
		Counter64,
	pmc1002perfdatacomclientCurrent15StatInMulticastCountInvPortn
		EkiOnOff,
	pmc1002perfdatacomclientCurrent15StatInMulticastCountPortn
		Counter64,
	pmc1002perfdatacomclientCurrent15StatInBroadcastCountInvPortn
		EkiOnOff,
	pmc1002perfdatacomclientCurrent15StatInBroadcastCountPortn
		Counter64,
	pmc1002perfdatacomclientCurrent15StatInCrcCountInvPortn
		EkiOnOff,
	pmc1002perfdatacomclientCurrent15StatInCrcCountPortn
		Counter64,
	pmc1002perfdatacomclientCurrent15StatInBytesCountInvPortn
		EkiOnOff,
	pmc1002perfdatacomclientCurrent15StatInBytesCountPortn
		Counter64
	}


pmc1002PerfDatacomClientCurrent15StatIndex OBJECT-TYPE
	SYNTAX  INTEGER(0..128)
	MAX-ACCESS  read-only
	STATUS current
	DESCRIPTION
        "
        Index definition for the pmc1002PerfDatacomClientCurrent15Stat
        table
        "
	::= { pmc1002PerfDatacomClientCurrent15StatEntry 1 }


pmc1002perfdatacomclientCurrent15StatOutNonunicastCountInvPortn OBJECT-TYPE
	SYNTAX  EkiOnOff
	MAX-ACCESS read-only
	STATUS current
	DESCRIPTION
        "
        Client Current 15-min Output Non
        Unicast counter inv. :This OID
         indicates that the current 15-min
        Non Unicast counter is invalid
        "
	::= { pmc1002PerfDatacomClientCurrent15StatEntry 44 }


pmc1002perfdatacomclientCurrent15StatOutNonunicastCountPortn OBJECT-TYPE
	SYNTAX  Counter64
	MAX-ACCESS read-only
	STATUS current
	DESCRIPTION
        "
        Client Current 15-min Output Non
        Unicast counter :This OID gives
        the current 15-min Non Unicast
         counter value
        "
	::= { pmc1002PerfDatacomClientCurrent15StatEntry 45 }


pmc1002perfdatacomclientCurrent15StatOutUnicastCountInvPortn OBJECT-TYPE
	SYNTAX  EkiOnOff
	MAX-ACCESS read-only
	STATUS current
	DESCRIPTION
        "
        Client Current 15-min Output Unicast
        counter inv. :This OID indicates
        that the current 15-min Unicast
        counter is invalid
        "
	::= { pmc1002PerfDatacomClientCurrent15StatEntry 42 }


pmc1002perfdatacomclientCurrent15StatOutUnicastCountPortn OBJECT-TYPE
	SYNTAX  Counter64
	MAX-ACCESS read-only
	STATUS current
	DESCRIPTION
        "
        Client Current 15-min Output Unicast
        counter :This OID gives the current
        15-min Unicast counter value
        "
	::= { pmc1002PerfDatacomClientCurrent15StatEntry 43 }


pmc1002perfdatacomclientCurrent15StatOutMulticastCountInvPortn OBJECT-TYPE
	SYNTAX  EkiOnOff
	MAX-ACCESS read-only
	STATUS current
	DESCRIPTION
        "
        Client Current 15-min Output Multicast
        counter inv. :This OID indicates
        that the current 15-min Multicast
        counter is invalid
        "
	::= { pmc1002PerfDatacomClientCurrent15StatEntry 34 }


pmc1002perfdatacomclientCurrent15StatOutMulticastCountPortn OBJECT-TYPE
	SYNTAX  Counter64
	MAX-ACCESS read-only
	STATUS current
	DESCRIPTION
        "
        Client Current 15-min Output Multicast
        counter :This OID gives the current
        15-min Multicast counter value
        "
	::= { pmc1002PerfDatacomClientCurrent15StatEntry 35 }


pmc1002perfdatacomclientCurrent15StatOutBroadcastCountInvPortn OBJECT-TYPE
	SYNTAX  EkiOnOff
	MAX-ACCESS read-only
	STATUS current
	DESCRIPTION
        "
        Client Current 15-min Output Broadcast
        counter inv. :This OID indicates
        that the current 15-min Broadcast
        counter is invalid
        "
	::= { pmc1002PerfDatacomClientCurrent15StatEntry 32 }


pmc1002perfdatacomclientCurrent15StatOutBroadcastCountPortn OBJECT-TYPE
	SYNTAX  Counter64
	MAX-ACCESS read-only
	STATUS current
	DESCRIPTION
        "
        Client Current 15-min Output Broadcast
        counter :This OID gives the current
        15-min Broadcast counter value
        "
	::= { pmc1002PerfDatacomClientCurrent15StatEntry 33 }


pmc1002perfdatacomclientCurrent15StatOutBytesCountInvPortn OBJECT-TYPE
	SYNTAX  EkiOnOff
	MAX-ACCESS read-only
	STATUS current
	DESCRIPTION
        "
        Client Current 15-min Output Bytes
        counter inv. :This OID indicates
        that the current 15-min Bytes counter
        is invalid
        "
	::= { pmc1002PerfDatacomClientCurrent15StatEntry 26 }


pmc1002perfdatacomclientCurrent15StatOutBytesCountPortn OBJECT-TYPE
	SYNTAX  Counter64
	MAX-ACCESS read-only
	STATUS current
	DESCRIPTION
        "
        Client Current 15-min Output Bytes
        counter :This OID gives the current
        15-min Bytes counter value
        "
	::= { pmc1002PerfDatacomClientCurrent15StatEntry 27 }


pmc1002perfdatacomclientCurrent15StatInNonunicastCountInvPortn OBJECT-TYPE
	SYNTAX  EkiOnOff
	MAX-ACCESS read-only
	STATUS current
	DESCRIPTION
        "
        Client Current 15-min Input Non
        Unicast counter inv. :This OID
         indicates that the current 15-min
        Non unicast counter is invalid
        "
	::= { pmc1002PerfDatacomClientCurrent15StatEntry 22 }


pmc1002perfdatacomclientCurrent15StatInNonunicastCountPortn OBJECT-TYPE
	SYNTAX  Counter64
	MAX-ACCESS read-only
	STATUS current
	DESCRIPTION
        "
        Client Current 15-min Input Non
        Unicast counter :This OID gives
        the current 15-min Non Unicast
         counter value
        "
	::= { pmc1002PerfDatacomClientCurrent15StatEntry 23 }


pmc1002perfdatacomclientCurrent15StatInUnicastCountInvPortn OBJECT-TYPE
	SYNTAX  EkiOnOff
	MAX-ACCESS read-only
	STATUS current
	DESCRIPTION
        "
        Client Current 15-min Input Unicast
        counter inv. :This OID indicates
        that the current 15-min Unicast
        counter is invalid
        "
	::= { pmc1002PerfDatacomClientCurrent15StatEntry 20 }


pmc1002perfdatacomclientCurrent15StatInUnicastCountPortn OBJECT-TYPE
	SYNTAX  Counter64
	MAX-ACCESS read-only
	STATUS current
	DESCRIPTION
        "
        Client Current 15-min Input Unicast
        counter :This OID gives the current
        15-min Unicast counter value
        "
	::= { pmc1002PerfDatacomClientCurrent15StatEntry 21 }


pmc1002perfdatacomclientCurrent15StatInMulticastCountInvPortn OBJECT-TYPE
	SYNTAX  EkiOnOff
	MAX-ACCESS read-only
	STATUS current
	DESCRIPTION
        "
        Client Current 15-min Input Multicast
        counter inv. :This OID indicates
        that the current 15-min Multicast
        counter is invalid
        "
	::= { pmc1002PerfDatacomClientCurrent15StatEntry 10 }


pmc1002perfdatacomclientCurrent15StatInMulticastCountPortn OBJECT-TYPE
	SYNTAX  Counter64
	MAX-ACCESS read-only
	STATUS current
	DESCRIPTION
        "
        Client Current 15-min Input Multicast
        counter :This OID gives the current
        15-min Multicast counter value
        "
	::= { pmc1002PerfDatacomClientCurrent15StatEntry 11 }


pmc1002perfdatacomclientCurrent15StatInBroadcastCountInvPortn OBJECT-TYPE
	SYNTAX  EkiOnOff
	MAX-ACCESS read-only
	STATUS current
	DESCRIPTION
        "
        Client Current 15-min Input Broadcast
        counter inv. :This OID indicates
        that the current 15-min Broadcast
        counter is invalid
        "
	::= { pmc1002PerfDatacomClientCurrent15StatEntry 8 }


pmc1002perfdatacomclientCurrent15StatInBroadcastCountPortn OBJECT-TYPE
	SYNTAX  Counter64
	MAX-ACCESS read-only
	STATUS current
	DESCRIPTION
        "
        Client Current 15-min Input Broadcast
        counter :This OID gives the current
        15-min Broadcast counter value
        "
	::= { pmc1002PerfDatacomClientCurrent15StatEntry 9 }


pmc1002perfdatacomclientCurrent15StatInCrcCountInvPortn OBJECT-TYPE
	SYNTAX  EkiOnOff
	MAX-ACCESS read-only
	STATUS current
	DESCRIPTION
        "
        Client Current 15-min Input CRC
        counter inv. :This OID indicates
        that the current 15-min CRC counter
        is invalid
        "
	::= { pmc1002PerfDatacomClientCurrent15StatEntry 4 }


pmc1002perfdatacomclientCurrent15StatInCrcCountPortn OBJECT-TYPE
	SYNTAX  Counter64
	MAX-ACCESS read-only
	STATUS current
	DESCRIPTION
        "
        Client Current 15-min Input CRC
        counter :This OID gives the current
        15-min CRC counter value
        "
	::= { pmc1002PerfDatacomClientCurrent15StatEntry 5 }


pmc1002perfdatacomclientCurrent15StatInBytesCountInvPortn OBJECT-TYPE
	SYNTAX  EkiOnOff
	MAX-ACCESS read-only
	STATUS current
	DESCRIPTION
        "
        Client Current 15-min Input Bytes
        counter inv. :This OID indicates
        that the current 15-min Bytes counter
        is invalid
        "
	::= { pmc1002PerfDatacomClientCurrent15StatEntry 2 }


pmc1002perfdatacomclientCurrent15StatInBytesCountPortn OBJECT-TYPE
	SYNTAX  Counter64
	MAX-ACCESS read-only
	STATUS current
	DESCRIPTION
        "
        Client Current 15-min Input Bytes
        counter :This OID gives the current
        15-min Bytes counter value
        "
	::= { pmc1002PerfDatacomClientCurrent15StatEntry 3 }


--- *****************************************************
---     Leaf of the datacomClientPast15Stat
--- *****************************************************
--- *********************************************************
---     TABLE for the pmc1002PerfDatacomClientPast15StatHistory articles
--- *********************************************************

pmc1002PerfDatacomClientPast15StatHistoryPort1Table OBJECT-TYPE
	SYNTAX  SEQUENCE OF Pmc1002PerfDatacomClientPast15StatHistoryPort1Entry
	MAX-ACCESS not-accessible
	STATUS current
	DESCRIPTION
        "
        List of pmc1002PerfDatacomClientPast15StatHistory
        Article
        "
	::= { pmc1002MonClient 264 }


pmc1002PerfDatacomClientPast15StatHistoryPort1Entry OBJECT-TYPE
	SYNTAX Pmc1002PerfDatacomClientPast15StatHistoryPort1Entry
	MAX-ACCESS not-accessible
	STATUS current
	DESCRIPTION
        "
        Row definition for the pmc1002PerfDatacomClientPast15StatHistory
        table
        "
	INDEX   { pmc1002PerfDatacomClientPast15StatHistoryPort1Index }
	::= { pmc1002PerfDatacomClientPast15StatHistoryPort1Table 1 }


Pmc1002PerfDatacomClientPast15StatHistoryPort1Entry ::=
	SEQUENCE {
	pmc1002PerfDatacomClientPast15StatHistoryPort1Index
		INTEGER,
	pmc1002perfdatacomclientPast15StatOutNonunicastCountInvPort1
		EkiOnOff,
	pmc1002perfdatacomclientPast15StatOutNonunicastCountPort1
		Counter64,
	pmc1002perfdatacomclientPast15StatOutUnicastCountInvPort1
		EkiOnOff,
	pmc1002perfdatacomclientPast15StatOutUnicastCountPort1
		Counter64,
	pmc1002perfdatacomclientPast15StatOutMulticastCountInvPort1
		EkiOnOff,
	pmc1002perfdatacomclientPast15StatOutMulticastCountPort1
		Counter64,
	pmc1002perfdatacomclientPast15StatOutBroadcastCountInvPort1
		EkiOnOff,
	pmc1002perfdatacomclientPast15StatOutBroadcastCountPort1
		Counter64,
	pmc1002perfdatacomclientPast15StatOutBytesCountInvPort1
		EkiOnOff,
	pmc1002perfdatacomclientPast15StatOutBytesCountPort1
		Counter64,
	pmc1002perfdatacomclientPast15StatInNonunicastCountInvPort1
		EkiOnOff,
	pmc1002perfdatacomclientPast15StatInNonunicastCountPort1
		Counter64,
	pmc1002perfdatacomclientPast15StatInUnicastCountInvPort1
		EkiOnOff,
	pmc1002perfdatacomclientPast15StatInUnicastCountPort1
		Counter64,
	pmc1002perfdatacomclientPast15StatInMulticastCountInvPort1
		EkiOnOff,
	pmc1002perfdatacomclientPast15StatInMulticastCountPort1
		Counter64,
	pmc1002perfdatacomclientPast15StatInBroadcastCountInvPort1
		EkiOnOff,
	pmc1002perfdatacomclientPast15StatInBroadcastCountPort1
		Counter64,
	pmc1002perfdatacomclientPast15StatInCrcCountInvPort1
		EkiOnOff,
	pmc1002perfdatacomclientPast15StatInCrcCountPort1
		Counter64,
	pmc1002perfdatacomclientPast15StatInBytesCountInvPort1
		EkiOnOff,
	pmc1002perfdatacomclientPast15StatInBytesCountPort1
		Counter64
	}


pmc1002PerfDatacomClientPast15StatHistoryPort1Index OBJECT-TYPE
	SYNTAX  INTEGER(0..128)
	MAX-ACCESS  read-only
	STATUS current
	DESCRIPTION
        "
        Index definition for the pmc1002PerfDatacomClientPast15StatHistory
        table
        "
	::= { pmc1002PerfDatacomClientPast15StatHistoryPort1Entry 1 }


pmc1002perfdatacomclientPast15StatOutNonunicastCountInvPort1 OBJECT-TYPE
	SYNTAX  EkiOnOff
	MAX-ACCESS read-only
	STATUS current
	DESCRIPTION
        "
        Client Past 15-min Output Non
         Unicast counter inv. :This OID
        indicates that the past 15-min
         Non Unicast counter is invalid
        "
	::= { pmc1002PerfDatacomClientPast15StatHistoryPort1Entry 44 }


pmc1002perfdatacomclientPast15StatOutNonunicastCountPort1 OBJECT-TYPE
	SYNTAX  Counter64
	MAX-ACCESS read-only
	STATUS current
	DESCRIPTION
        "
        Client Past 15-min Output Non
         Unicast counter :This OID gives
        the past 15-min Non Unicast counter
        value
        "
	::= { pmc1002PerfDatacomClientPast15StatHistoryPort1Entry 45 }


pmc1002perfdatacomclientPast15StatOutUnicastCountInvPort1 OBJECT-TYPE
	SYNTAX  EkiOnOff
	MAX-ACCESS read-only
	STATUS current
	DESCRIPTION
        "
        Client Past 15-min Output Unicast
        counter inv. :This OID indicates
        that the past 15-min Unicast counter
        is invalid
        "
	::= { pmc1002PerfDatacomClientPast15StatHistoryPort1Entry 42 }


pmc1002perfdatacomclientPast15StatOutUnicastCountPort1 OBJECT-TYPE
	SYNTAX  Counter64
	MAX-ACCESS read-only
	STATUS current
	DESCRIPTION
        "
        Client Past 15-min Output Unicast
        counter :This OID gives the past
        15-min Unicast counter value
        "
	::= { pmc1002PerfDatacomClientPast15StatHistoryPort1Entry 43 }


pmc1002perfdatacomclientPast15StatOutMulticastCountInvPort1 OBJECT-TYPE
	SYNTAX  EkiOnOff
	MAX-ACCESS read-only
	STATUS current
	DESCRIPTION
        "
        Client Past 15-min Output Multicast
        counter inv. :This OID indicates
        that the past 15-min Multicast
         counter is invalid
        "
	::= { pmc1002PerfDatacomClientPast15StatHistoryPort1Entry 34 }


pmc1002perfdatacomclientPast15StatOutMulticastCountPort1 OBJECT-TYPE
	SYNTAX  Counter64
	MAX-ACCESS read-only
	STATUS current
	DESCRIPTION
        "
        Client Past 15-min Output Multicast
        counter :This OID gives the past
        15-min Multicast counter value
        "
	::= { pmc1002PerfDatacomClientPast15StatHistoryPort1Entry 35 }


pmc1002perfdatacomclientPast15StatOutBroadcastCountInvPort1 OBJECT-TYPE
	SYNTAX  EkiOnOff
	MAX-ACCESS read-only
	STATUS current
	DESCRIPTION
        "
        Client Past 15-min Output Broadcast
        counter inv. :This OID indicates
        that the past 15-min Broadcast
         counter is invalid
        "
	::= { pmc1002PerfDatacomClientPast15StatHistoryPort1Entry 32 }


pmc1002perfdatacomclientPast15StatOutBroadcastCountPort1 OBJECT-TYPE
	SYNTAX  Counter64
	MAX-ACCESS read-only
	STATUS current
	DESCRIPTION
        "
        Client Past 15-min Output Broadcast
        counter :This OID gives the past
        15-min Broadcast counter value
        "
	::= { pmc1002PerfDatacomClientPast15StatHistoryPort1Entry 33 }


pmc1002perfdatacomclientPast15StatOutBytesCountInvPort1 OBJECT-TYPE
	SYNTAX  EkiOnOff
	MAX-ACCESS read-only
	STATUS current
	DESCRIPTION
        "
        Client Past 15-min Output Bytes
        counter inv. :This OID indicates
        that the past 15-min Bytes counter
        is invalid
        "
	::= { pmc1002PerfDatacomClientPast15StatHistoryPort1Entry 26 }


pmc1002perfdatacomclientPast15StatOutBytesCountPort1 OBJECT-TYPE
	SYNTAX  Counter64
	MAX-ACCESS read-only
	STATUS current
	DESCRIPTION
        "
        Client Past 15-min Output Bytes
        counter :This OID gives the past
        15-min Bytes counter value
        "
	::= { pmc1002PerfDatacomClientPast15StatHistoryPort1Entry 27 }


pmc1002perfdatacomclientPast15StatInNonunicastCountInvPort1 OBJECT-TYPE
	SYNTAX  EkiOnOff
	MAX-ACCESS read-only
	STATUS current
	DESCRIPTION
        "
        Client Past 15-min Input Non Unicast
        counter inv. :This OID indicates
        that the past 15-min Non unicast
        counter is invalid
        "
	::= { pmc1002PerfDatacomClientPast15StatHistoryPort1Entry 22 }


pmc1002perfdatacomclientPast15StatInNonunicastCountPort1 OBJECT-TYPE
	SYNTAX  Counter64
	MAX-ACCESS read-only
	STATUS current
	DESCRIPTION
        "
        Client Past 15-min Input Non Unicast
        counter :This OID gives the past
        15-min Non Unicast counter value
        "
	::= { pmc1002PerfDatacomClientPast15StatHistoryPort1Entry 23 }


pmc1002perfdatacomclientPast15StatInUnicastCountInvPort1 OBJECT-TYPE
	SYNTAX  EkiOnOff
	MAX-ACCESS read-only
	STATUS current
	DESCRIPTION
        "
        Client Past 15-min Input Unicast
        counter inv. :This OID indicates
        that the past 15-min Unicast counter
        is invalid
        "
	::= { pmc1002PerfDatacomClientPast15StatHistoryPort1Entry 20 }


pmc1002perfdatacomclientPast15StatInUnicastCountPort1 OBJECT-TYPE
	SYNTAX  Counter64
	MAX-ACCESS read-only
	STATUS current
	DESCRIPTION
        "
        Client Past 15-min Input Unicast
        counter :This OID gives the past
        15-min Unicast counter value
        "
	::= { pmc1002PerfDatacomClientPast15StatHistoryPort1Entry 21 }


pmc1002perfdatacomclientPast15StatInMulticastCountInvPort1 OBJECT-TYPE
	SYNTAX  EkiOnOff
	MAX-ACCESS read-only
	STATUS current
	DESCRIPTION
        "
        Client Past 15-min Input Multicast
        counter inv. :This OID indicates
        that the past 15-min Multicast
         counter is invalid
        "
	::= { pmc1002PerfDatacomClientPast15StatHistoryPort1Entry 10 }


pmc1002perfdatacomclientPast15StatInMulticastCountPort1 OBJECT-TYPE
	SYNTAX  Counter64
	MAX-ACCESS read-only
	STATUS current
	DESCRIPTION
        "
        Client Past 15-min Input Multicast
        counter :This OID gives the past
        15-min Multicast counter value
        "
	::= { pmc1002PerfDatacomClientPast15StatHistoryPort1Entry 11 }


pmc1002perfdatacomclientPast15StatInBroadcastCountInvPort1 OBJECT-TYPE
	SYNTAX  EkiOnOff
	MAX-ACCESS read-only
	STATUS current
	DESCRIPTION
        "
        Client Past 15-min Input Broadcast
        counter inv. :This OID indicates
        that the past 15-min Broadcast
         counter is invalid
        "
	::= { pmc1002PerfDatacomClientPast15StatHistoryPort1Entry 8 }


pmc1002perfdatacomclientPast15StatInBroadcastCountPort1 OBJECT-TYPE
	SYNTAX  Counter64
	MAX-ACCESS read-only
	STATUS current
	DESCRIPTION
        "
        Client Past 15-min Input Broadcast
        counter :This OID gives the past
        15-min Broadcast counter value
        "
	::= { pmc1002PerfDatacomClientPast15StatHistoryPort1Entry 9 }


pmc1002perfdatacomclientPast15StatInCrcCountInvPort1 OBJECT-TYPE
	SYNTAX  EkiOnOff
	MAX-ACCESS read-only
	STATUS current
	DESCRIPTION
        "
        Client Past 15-min Input CRC counter
        inv. :This OID indicates that the
        past 15-min CRC counter is invalid
        "
	::= { pmc1002PerfDatacomClientPast15StatHistoryPort1Entry 4 }


pmc1002perfdatacomclientPast15StatInCrcCountPort1 OBJECT-TYPE
	SYNTAX  Counter64
	MAX-ACCESS read-only
	STATUS current
	DESCRIPTION
        "
        Client Past 15-min Input CRC counter
        :This OID gives the past 15-min
        CRC counter value
        "
	::= { pmc1002PerfDatacomClientPast15StatHistoryPort1Entry 5 }


pmc1002perfdatacomclientPast15StatInBytesCountInvPort1 OBJECT-TYPE
	SYNTAX  EkiOnOff
	MAX-ACCESS read-only
	STATUS current
	DESCRIPTION
        "
        Client Past 15-min Input Bytes
        counter inv. :This OID indicates
        that the past 15-min Bytes counter
        is invalid
        "
	::= { pmc1002PerfDatacomClientPast15StatHistoryPort1Entry 2 }


pmc1002perfdatacomclientPast15StatInBytesCountPort1 OBJECT-TYPE
	SYNTAX  Counter64
	MAX-ACCESS read-only
	STATUS current
	DESCRIPTION
        "
        Client Past 15-min Input Bytes
        counter :This OID gives the past
        15-min Bytes counter value
        "
	::= { pmc1002PerfDatacomClientPast15StatHistoryPort1Entry 3 }


--- *****************************************************
---     Leaf of the datacomClientCurrent24Stat
--- *****************************************************
--- *********************************************************
---     TABLE for the pmc1002PerfDatacomClientCurrent24Stat articles
--- *********************************************************

pmc1002PerfDatacomClientCurrent24StatTable OBJECT-TYPE
	SYNTAX  SEQUENCE OF Pmc1002PerfDatacomClientCurrent24StatEntry
	MAX-ACCESS not-accessible
	STATUS current
	DESCRIPTION
        "
        List of pmc1002PerfDatacomClientCurrent24Stat
        Article
        "
	::= { pmc1002MonClient 272 }


pmc1002PerfDatacomClientCurrent24StatEntry OBJECT-TYPE
	SYNTAX Pmc1002PerfDatacomClientCurrent24StatEntry
	MAX-ACCESS not-accessible
	STATUS current
	DESCRIPTION
        "
        Row definition for the pmc1002PerfDatacomClientCurrent24Stat
        table
        "
	INDEX   { pmc1002PerfDatacomClientCurrent24StatIndex }
	::= { pmc1002PerfDatacomClientCurrent24StatTable 1 }


Pmc1002PerfDatacomClientCurrent24StatEntry ::=
	SEQUENCE {
	pmc1002PerfDatacomClientCurrent24StatIndex
		INTEGER,
	pmc1002perfdatacomclientCurrent24StatOutNonunicastCountInvPortn
		EkiOnOff,
	pmc1002perfdatacomclientCurrent24StatOutNonunicastCountPortn
		Counter64,
	pmc1002perfdatacomclientCurrent24StatOutUnicastCountInvPortn
		EkiOnOff,
	pmc1002perfdatacomclientCurrent24StatOutUnicastCountPortn
		Counter64,
	pmc1002perfdatacomclientCurrent24StatOutMulticastCountInvPortn
		EkiOnOff,
	pmc1002perfdatacomclientCurrent24StatOutMulticastCountPortn
		Counter64,
	pmc1002perfdatacomclientCurrent24StatOutBroadcastCountInvPortn
		EkiOnOff,
	pmc1002perfdatacomclientCurrent24StatOutBroadcastCountPortn
		Counter64,
	pmc1002perfdatacomclientCurrent24StatOutBytesCountInvPortn
		EkiOnOff,
	pmc1002perfdatacomclientCurrent24StatOutBytesCountPortn
		Counter64,
	pmc1002perfdatacomclientCurrent24StatInNonunicastCountInvPortn
		EkiOnOff,
	pmc1002perfdatacomclientCurrent24StatInNonunicastCountPortn
		Counter64,
	pmc1002perfdatacomclientCurrent24StatInUnicastCountInvPortn
		EkiOnOff,
	pmc1002perfdatacomclientCurrent24StatInUnicastCountPortn
		Counter64,
	pmc1002perfdatacomclientCurrent24StatInMulticastCountInvPortn
		EkiOnOff,
	pmc1002perfdatacomclientCurrent24StatInMulticastCountPortn
		Counter64,
	pmc1002perfdatacomclientCurrent24StatInBroadcastCountInvPortn
		EkiOnOff,
	pmc1002perfdatacomclientCurrent24StatInBroadcastCountPortn
		Counter64,
	pmc1002perfdatacomclientCurrent24StatInCrcCountInvPortn
		EkiOnOff,
	pmc1002perfdatacomclientCurrent24StatInCrcCountPortn
		Counter64,
	pmc1002perfdatacomclientCurrent24StatInBytesCountInvPortn
		EkiOnOff,
	pmc1002perfdatacomclientCurrent24StatInBytesCountPortn
		Counter64
	}


pmc1002PerfDatacomClientCurrent24StatIndex OBJECT-TYPE
	SYNTAX  INTEGER(0..128)
	MAX-ACCESS  read-only
	STATUS current
	DESCRIPTION
        "
        Index definition for the pmc1002PerfDatacomClientCurrent24Stat
        table
        "
	::= { pmc1002PerfDatacomClientCurrent24StatEntry 1 }


pmc1002perfdatacomclientCurrent24StatOutNonunicastCountInvPortn OBJECT-TYPE
	SYNTAX  EkiOnOff
	MAX-ACCESS read-only
	STATUS current
	DESCRIPTION
        "
        Client Current 24-hours Output
        Non Unicast counter inv. :This
         OID indicates that the current
        24-hours Non Unicast counter is
        invalid
        "
	::= { pmc1002PerfDatacomClientCurrent24StatEntry 44 }


pmc1002perfdatacomclientCurrent24StatOutNonunicastCountPortn OBJECT-TYPE
	SYNTAX  Counter64
	MAX-ACCESS read-only
	STATUS current
	DESCRIPTION
        "
        Client Current 24-hours Output
        Non Unicast counter :This OID gives
        the current 24-hours Non Unicast
        counter value
        "
	::= { pmc1002PerfDatacomClientCurrent24StatEntry 45 }


pmc1002perfdatacomclientCurrent24StatOutUnicastCountInvPortn OBJECT-TYPE
	SYNTAX  EkiOnOff
	MAX-ACCESS read-only
	STATUS current
	DESCRIPTION
        "
        Client Current 24-hours Output
        Unicast counter inv. :This OID
         indicates that the current 24-hours
        Unicast counter is invalid
        "
	::= { pmc1002PerfDatacomClientCurrent24StatEntry 42 }


pmc1002perfdatacomclientCurrent24StatOutUnicastCountPortn OBJECT-TYPE
	SYNTAX  Counter64
	MAX-ACCESS read-only
	STATUS current
	DESCRIPTION
        "
        Client Current 24-hours Output
        Unicast counter :This OID gives
        the current 24-hours Unicast counter
        value
        "
	::= { pmc1002PerfDatacomClientCurrent24StatEntry 43 }


pmc1002perfdatacomclientCurrent24StatOutMulticastCountInvPortn OBJECT-TYPE
	SYNTAX  EkiOnOff
	MAX-ACCESS read-only
	STATUS current
	DESCRIPTION
        "
        Client Current 24-hours Output
        Multicast counter inv. :This OID
        indicates that the current 24-hours
        Multicast counter is invalid
        "
	::= { pmc1002PerfDatacomClientCurrent24StatEntry 34 }


pmc1002perfdatacomclientCurrent24StatOutMulticastCountPortn OBJECT-TYPE
	SYNTAX  Counter64
	MAX-ACCESS read-only
	STATUS current
	DESCRIPTION
        "
        Client Current 24-hours Output
        Multicast counter :This OID gives
        the current 24-hours Multicast
         counter value
        "
	::= { pmc1002PerfDatacomClientCurrent24StatEntry 35 }


pmc1002perfdatacomclientCurrent24StatOutBroadcastCountInvPortn OBJECT-TYPE
	SYNTAX  EkiOnOff
	MAX-ACCESS read-only
	STATUS current
	DESCRIPTION
        "
        Client Current 24-hours Output
        Broadcast counter inv. :This OID
        indicates that the current 24-hours
        Broadcast counter is invalid
        "
	::= { pmc1002PerfDatacomClientCurrent24StatEntry 32 }


pmc1002perfdatacomclientCurrent24StatOutBroadcastCountPortn OBJECT-TYPE
	SYNTAX  Counter64
	MAX-ACCESS read-only
	STATUS current
	DESCRIPTION
        "
        Client Current 24-hours Output
        Broadcast counter :This OID gives
        the current 24-hours Broadcast
         counter value
        "
	::= { pmc1002PerfDatacomClientCurrent24StatEntry 33 }


pmc1002perfdatacomclientCurrent24StatOutBytesCountInvPortn OBJECT-TYPE
	SYNTAX  EkiOnOff
	MAX-ACCESS read-only
	STATUS current
	DESCRIPTION
        "
        Client Current 24-hours Output
        Bytes counter inv. :This OID indicates
        that the current 24-hours Bytes
        counter is invalid
        "
	::= { pmc1002PerfDatacomClientCurrent24StatEntry 26 }


pmc1002perfdatacomclientCurrent24StatOutBytesCountPortn OBJECT-TYPE
	SYNTAX  Counter64
	MAX-ACCESS read-only
	STATUS current
	DESCRIPTION
        "
        Client Current 24-hours Output
        Bytes counter :This OID gives the
        current 24-hours Bytes counter
         value
        "
	::= { pmc1002PerfDatacomClientCurrent24StatEntry 27 }


pmc1002perfdatacomclientCurrent24StatInNonunicastCountInvPortn OBJECT-TYPE
	SYNTAX  EkiOnOff
	MAX-ACCESS read-only
	STATUS current
	DESCRIPTION
        "
        Client Current 24-hours Input
         Non Unicast counter inv. :This
        OID indicates that the current
         24-hours Non unicast counter is
        invalid
        "
	::= { pmc1002PerfDatacomClientCurrent24StatEntry 22 }


pmc1002perfdatacomclientCurrent24StatInNonunicastCountPortn OBJECT-TYPE
	SYNTAX  Counter64
	MAX-ACCESS read-only
	STATUS current
	DESCRIPTION
        "
        Client Current 24-hours Input
         Non Unicast counter :This OID
         gives the current 24-hours Non
        Unicast counter value
        "
	::= { pmc1002PerfDatacomClientCurrent24StatEntry 23 }


pmc1002perfdatacomclientCurrent24StatInUnicastCountInvPortn OBJECT-TYPE
	SYNTAX  EkiOnOff
	MAX-ACCESS read-only
	STATUS current
	DESCRIPTION
        "
        Client Current 24-hours Input
         Unicast counter inv. :This OID
        indicates that the current 24-hours
        Unicast counter is invalid
        "
	::= { pmc1002PerfDatacomClientCurrent24StatEntry 20 }


pmc1002perfdatacomclientCurrent24StatInUnicastCountPortn OBJECT-TYPE
	SYNTAX  Counter64
	MAX-ACCESS read-only
	STATUS current
	DESCRIPTION
        "
        Client Current 24-hours Input
         Unicast counter :This OID gives
        the current 24-hours Unicast counter
        value
        "
	::= { pmc1002PerfDatacomClientCurrent24StatEntry 21 }


pmc1002perfdatacomclientCurrent24StatInMulticastCountInvPortn OBJECT-TYPE
	SYNTAX  EkiOnOff
	MAX-ACCESS read-only
	STATUS current
	DESCRIPTION
        "
        Client Current 24-hours Input
         Multicast counter inv. :This OID
        indicates that the current 24-hours
        Multicast counter is invalid
        "
	::= { pmc1002PerfDatacomClientCurrent24StatEntry 10 }


pmc1002perfdatacomclientCurrent24StatInMulticastCountPortn OBJECT-TYPE
	SYNTAX  Counter64
	MAX-ACCESS read-only
	STATUS current
	DESCRIPTION
        "
        Client Current 24-hours Input
         Multicast counter :This OID gives
        the current 24-hours Multicast
         counter value
        "
	::= { pmc1002PerfDatacomClientCurrent24StatEntry 11 }


pmc1002perfdatacomclientCurrent24StatInBroadcastCountInvPortn OBJECT-TYPE
	SYNTAX  EkiOnOff
	MAX-ACCESS read-only
	STATUS current
	DESCRIPTION
        "
        Client Current 24-hours Input
         Broadcast counter inv. :This OID
        indicates that the current 24-hours
        Broadcast counter is invalid
        "
	::= { pmc1002PerfDatacomClientCurrent24StatEntry 8 }


pmc1002perfdatacomclientCurrent24StatInBroadcastCountPortn OBJECT-TYPE
	SYNTAX  Counter64
	MAX-ACCESS read-only
	STATUS current
	DESCRIPTION
        "
        Client Current 24-hours Input
         Broadcast counter :This OID gives
        the current 24-hours Broadcast
         counter value
        "
	::= { pmc1002PerfDatacomClientCurrent24StatEntry 9 }


pmc1002perfdatacomclientCurrent24StatInCrcCountInvPortn OBJECT-TYPE
	SYNTAX  EkiOnOff
	MAX-ACCESS read-only
	STATUS current
	DESCRIPTION
        "
        Client Current 24-hours Input
         CRC counter inv. :This OID indicates
        that the current 24-hours CRC counter
        is invalid
        "
	::= { pmc1002PerfDatacomClientCurrent24StatEntry 4 }


pmc1002perfdatacomclientCurrent24StatInCrcCountPortn OBJECT-TYPE
	SYNTAX  Counter64
	MAX-ACCESS read-only
	STATUS current
	DESCRIPTION
        "
        Client Current 24-hours Input
         CRC counter :This OID gives the
        current 24-hours CRC counter value
        "
	::= { pmc1002PerfDatacomClientCurrent24StatEntry 5 }


pmc1002perfdatacomclientCurrent24StatInBytesCountInvPortn OBJECT-TYPE
	SYNTAX  EkiOnOff
	MAX-ACCESS read-only
	STATUS current
	DESCRIPTION
        "
        Client Current 24-hours Input
         Bytes counter inv. :This OID indicates
        that the current 24-hours Bytes
        counter is invalid
        "
	::= { pmc1002PerfDatacomClientCurrent24StatEntry 2 }


pmc1002perfdatacomclientCurrent24StatInBytesCountPortn OBJECT-TYPE
	SYNTAX  Counter64
	MAX-ACCESS read-only
	STATUS current
	DESCRIPTION
        "
        Client Current 24-hours Input
         Bytes counter :This OID gives
         the current 24-hours Bytes counter
        value
        "
	::= { pmc1002PerfDatacomClientCurrent24StatEntry 3 }


--- *****************************************************
---     Leaf of the datacomClientPast24Stat
--- *****************************************************
--- *********************************************************
---     TABLE for the pmc1002PerfDatacomClientPast24StatHistory articles
--- *********************************************************

pmc1002PerfDatacomClientPast24StatHistoryPort1Table OBJECT-TYPE
	SYNTAX  SEQUENCE OF Pmc1002PerfDatacomClientPast24StatHistoryPort1Entry
	MAX-ACCESS not-accessible
	STATUS current
	DESCRIPTION
        "
        List of pmc1002PerfDatacomClientPast24StatHistory
        Article
        "
	::= { pmc1002MonClient 280 }


pmc1002PerfDatacomClientPast24StatHistoryPort1Entry OBJECT-TYPE
	SYNTAX Pmc1002PerfDatacomClientPast24StatHistoryPort1Entry
	MAX-ACCESS not-accessible
	STATUS current
	DESCRIPTION
        "
        Row definition for the pmc1002PerfDatacomClientPast24StatHistory
        table
        "
	INDEX   { pmc1002PerfDatacomClientPast24StatHistoryPort1Index }
	::= { pmc1002PerfDatacomClientPast24StatHistoryPort1Table 1 }


Pmc1002PerfDatacomClientPast24StatHistoryPort1Entry ::=
	SEQUENCE {
	pmc1002PerfDatacomClientPast24StatHistoryPort1Index
		INTEGER,
	pmc1002perfdatacomclientPast24StatOutNonunicastCountInvPort1
		EkiOnOff,
	pmc1002perfdatacomclientPast24StatOutNonunicastCountPort1
		Counter64,
	pmc1002perfdatacomclientPast24StatOutUnicastCountInvPort1
		EkiOnOff,
	pmc1002perfdatacomclientPast24StatOutUnicastCountPort1
		Counter64,
	pmc1002perfdatacomclientPast24StatOutMulticastCountInvPort1
		EkiOnOff,
	pmc1002perfdatacomclientPast24StatOutMulticastCountPort1
		Counter64,
	pmc1002perfdatacomclientPast24StatOutBroadcastCountInvPort1
		EkiOnOff,
	pmc1002perfdatacomclientPast24StatOutBroadcastCountPort1
		Counter64,
	pmc1002perfdatacomclientPast24StatOutBytesCountInvPort1
		EkiOnOff,
	pmc1002perfdatacomclientPast24StatOutBytesCountPort1
		Counter64,
	pmc1002perfdatacomclientPast24StatInNonunicastCountInvPort1
		EkiOnOff,
	pmc1002perfdatacomclientPast24StatInNonunicastCountPort1
		Counter64,
	pmc1002perfdatacomclientPast24StatInUnicastCountInvPort1
		EkiOnOff,
	pmc1002perfdatacomclientPast24StatInUnicastCountPort1
		Counter64,
	pmc1002perfdatacomclientPast24StatInMulticastCountInvPort1
		EkiOnOff,
	pmc1002perfdatacomclientPast24StatInMulticastCountPort1
		Counter64,
	pmc1002perfdatacomclientPast24StatInBroadcastCountInvPort1
		EkiOnOff,
	pmc1002perfdatacomclientPast24StatInBroadcastCountPort1
		Counter64,
	pmc1002perfdatacomclientPast24StatInCrcCountInvPort1
		EkiOnOff,
	pmc1002perfdatacomclientPast24StatInCrcCountPort1
		Counter64,
	pmc1002perfdatacomclientPast24StatInBytesCountInvPort1
		EkiOnOff,
	pmc1002perfdatacomclientPast24StatInBytesCountPort1
		Counter64
	}


pmc1002PerfDatacomClientPast24StatHistoryPort1Index OBJECT-TYPE
	SYNTAX  INTEGER(0..128)
	MAX-ACCESS  read-only
	STATUS current
	DESCRIPTION
        "
        Index definition for the pmc1002PerfDatacomClientPast24StatHistory
        table
        "
	::= { pmc1002PerfDatacomClientPast24StatHistoryPort1Entry 1 }


pmc1002perfdatacomclientPast24StatOutNonunicastCountInvPort1 OBJECT-TYPE
	SYNTAX  EkiOnOff
	MAX-ACCESS read-only
	STATUS current
	DESCRIPTION
        "
        Client Past 24-hours Output Non
        Unicast counter inv. :This OID
         indicates that the past 24-hours
        Non Unicast counter is invalid
        "
	::= { pmc1002PerfDatacomClientPast24StatHistoryPort1Entry 44 }


pmc1002perfdatacomclientPast24StatOutNonunicastCountPort1 OBJECT-TYPE
	SYNTAX  Counter64
	MAX-ACCESS read-only
	STATUS current
	DESCRIPTION
        "
        Client Past 24-hours Output Non
        Unicast counter :This OID gives
        the past 24-hours Non Unicast counter
        value
        "
	::= { pmc1002PerfDatacomClientPast24StatHistoryPort1Entry 45 }


pmc1002perfdatacomclientPast24StatOutUnicastCountInvPort1 OBJECT-TYPE
	SYNTAX  EkiOnOff
	MAX-ACCESS read-only
	STATUS current
	DESCRIPTION
        "
        Client Past 24-hours Output Unicast
        counter inv. :This OID indicates
        that the past 24-hours Unicast
         counter is invalid
        "
	::= { pmc1002PerfDatacomClientPast24StatHistoryPort1Entry 42 }


pmc1002perfdatacomclientPast24StatOutUnicastCountPort1 OBJECT-TYPE
	SYNTAX  Counter64
	MAX-ACCESS read-only
	STATUS current
	DESCRIPTION
        "
        Client Past 24-hours Output Unicast
        counter :This OID gives the past
        24-hours Unicast counter value
        "
	::= { pmc1002PerfDatacomClientPast24StatHistoryPort1Entry 43 }


pmc1002perfdatacomclientPast24StatOutMulticastCountInvPort1 OBJECT-TYPE
	SYNTAX  EkiOnOff
	MAX-ACCESS read-only
	STATUS current
	DESCRIPTION
        "
        Client Past 24-hours Output Multicast
        counter inv. :This OID indicates
        that the past 24-hours Multicast
        counter is invalid
        "
	::= { pmc1002PerfDatacomClientPast24StatHistoryPort1Entry 34 }


pmc1002perfdatacomclientPast24StatOutMulticastCountPort1 OBJECT-TYPE
	SYNTAX  Counter64
	MAX-ACCESS read-only
	STATUS current
	DESCRIPTION
        "
        Client Past 24-hours Output Multicast
        counter :This OID gives the past
        24-hours Multicast counter value
        "
	::= { pmc1002PerfDatacomClientPast24StatHistoryPort1Entry 35 }


pmc1002perfdatacomclientPast24StatOutBroadcastCountInvPort1 OBJECT-TYPE
	SYNTAX  EkiOnOff
	MAX-ACCESS read-only
	STATUS current
	DESCRIPTION
        "
        Client Past 24-hours Output Broadcast
        counter inv. :This OID indicates
        that the past 24-hours Broadcast
        counter is invalid
        "
	::= { pmc1002PerfDatacomClientPast24StatHistoryPort1Entry 32 }


pmc1002perfdatacomclientPast24StatOutBroadcastCountPort1 OBJECT-TYPE
	SYNTAX  Counter64
	MAX-ACCESS read-only
	STATUS current
	DESCRIPTION
        "
        Client Past 24-hours Output Broadcast
        counter :This OID gives the past
        24-hours Broadcast counter value
        "
	::= { pmc1002PerfDatacomClientPast24StatHistoryPort1Entry 33 }


pmc1002perfdatacomclientPast24StatOutBytesCountInvPort1 OBJECT-TYPE
	SYNTAX  EkiOnOff
	MAX-ACCESS read-only
	STATUS current
	DESCRIPTION
        "
        Client Past 24-hours Output Bytes
        counter inv. :This OID indicates
        that the past 24-hours Bytes counter
        is invalid
        "
	::= { pmc1002PerfDatacomClientPast24StatHistoryPort1Entry 26 }


pmc1002perfdatacomclientPast24StatOutBytesCountPort1 OBJECT-TYPE
	SYNTAX  Counter64
	MAX-ACCESS read-only
	STATUS current
	DESCRIPTION
        "
        Client Past 24-hours Output Bytes
        counter :This OID gives the past
        24-hours Bytes counter value
        "
	::= { pmc1002PerfDatacomClientPast24StatHistoryPort1Entry 27 }


pmc1002perfdatacomclientPast24StatInNonunicastCountInvPort1 OBJECT-TYPE
	SYNTAX  EkiOnOff
	MAX-ACCESS read-only
	STATUS current
	DESCRIPTION
        "
        Client Past 24-hours Input Non
        Unicast counter inv. :This OID
         indicates that the past 24-hours
        Non unicast counter is invalid
        "
	::= { pmc1002PerfDatacomClientPast24StatHistoryPort1Entry 22 }


pmc1002perfdatacomclientPast24StatInNonunicastCountPort1 OBJECT-TYPE
	SYNTAX  Counter64
	MAX-ACCESS read-only
	STATUS current
	DESCRIPTION
        "
        Client Past 24-hours Input Non
        Unicast counter :This OID gives
        the past 24-hours Non Unicast counter
        value
        "
	::= { pmc1002PerfDatacomClientPast24StatHistoryPort1Entry 23 }


pmc1002perfdatacomclientPast24StatInUnicastCountInvPort1 OBJECT-TYPE
	SYNTAX  EkiOnOff
	MAX-ACCESS read-only
	STATUS current
	DESCRIPTION
        "
        Client Past 24-hours Input Unicast
        counter inv. :This OID indicates
        that the past 24-hours Unicast
         counter is invalid
        "
	::= { pmc1002PerfDatacomClientPast24StatHistoryPort1Entry 20 }


pmc1002perfdatacomclientPast24StatInUnicastCountPort1 OBJECT-TYPE
	SYNTAX  Counter64
	MAX-ACCESS read-only
	STATUS current
	DESCRIPTION
        "
        Client Past 24-hours Input Unicast
        counter :This OID gives the past
        24-hours Unicast counter value
        "
	::= { pmc1002PerfDatacomClientPast24StatHistoryPort1Entry 21 }


pmc1002perfdatacomclientPast24StatInMulticastCountInvPort1 OBJECT-TYPE
	SYNTAX  EkiOnOff
	MAX-ACCESS read-only
	STATUS current
	DESCRIPTION
        "
        Client Past 24-hours Input Multicast
        counter inv. :This OID indicates
        that the past 24-hours Multicast
        counter is invalid
        "
	::= { pmc1002PerfDatacomClientPast24StatHistoryPort1Entry 10 }


pmc1002perfdatacomclientPast24StatInMulticastCountPort1 OBJECT-TYPE
	SYNTAX  Counter64
	MAX-ACCESS read-only
	STATUS current
	DESCRIPTION
        "
        Client Past 24-hours Input Multicast
        counter :This OID gives the past
        24-hours Multicast counter value
        "
	::= { pmc1002PerfDatacomClientPast24StatHistoryPort1Entry 11 }


pmc1002perfdatacomclientPast24StatInBroadcastCountInvPort1 OBJECT-TYPE
	SYNTAX  EkiOnOff
	MAX-ACCESS read-only
	STATUS current
	DESCRIPTION
        "
        Client Past 24-hours Input Broadcast
        counter inv. :This OID indicates
        that the past 24-hours Broadcast
        counter is invalid
        "
	::= { pmc1002PerfDatacomClientPast24StatHistoryPort1Entry 8 }


pmc1002perfdatacomclientPast24StatInBroadcastCountPort1 OBJECT-TYPE
	SYNTAX  Counter64
	MAX-ACCESS read-only
	STATUS current
	DESCRIPTION
        "
        Client Past 24-hours Input Broadcast
        counter :This OID gives the past
        24-hours Broadcast counter value
        "
	::= { pmc1002PerfDatacomClientPast24StatHistoryPort1Entry 9 }


pmc1002perfdatacomclientPast24StatInCrcCountInvPort1 OBJECT-TYPE
	SYNTAX  EkiOnOff
	MAX-ACCESS read-only
	STATUS current
	DESCRIPTION
        "
        Client Past 24-hours Input CRC
        counter inv. :This OID indicates
        that the past 24-hours CRC counter
        is invalid
        "
	::= { pmc1002PerfDatacomClientPast24StatHistoryPort1Entry 4 }


pmc1002perfdatacomclientPast24StatInCrcCountPort1 OBJECT-TYPE
	SYNTAX  Counter64
	MAX-ACCESS read-only
	STATUS current
	DESCRIPTION
        "
        Client Past 24-hours Input CRC
        counter :This OID gives the past
        24-hours CRC counter value
        "
	::= { pmc1002PerfDatacomClientPast24StatHistoryPort1Entry 5 }


pmc1002perfdatacomclientPast24StatInBytesCountInvPort1 OBJECT-TYPE
	SYNTAX  EkiOnOff
	MAX-ACCESS read-only
	STATUS current
	DESCRIPTION
        "
        Client Past 24-hours Input Bytes
        counter inv. :This OID indicates
        that the past 24-hours Bytes counter
        is invalid
        "
	::= { pmc1002PerfDatacomClientPast24StatHistoryPort1Entry 2 }


pmc1002perfdatacomclientPast24StatInBytesCountPort1 OBJECT-TYPE
	SYNTAX  Counter64
	MAX-ACCESS read-only
	STATUS current
	DESCRIPTION
        "
        Client Past 24-hours Input Bytes
        counter :This OID gives the past
        24-hours Bytes counter value
        "
	::= { pmc1002PerfDatacomClientPast24StatHistoryPort1Entry 3 }



pmc1002PerfEnable OBJECT-TYPE
	SYNTAX EkiOnOff
	MAX-ACCESS read-write
	STATUS current
	DESCRIPTION
        "
        Perf. Mon. Enable :This OID enables
        the Performance Monitoring application
        "
	::= { pmc1002MonSync 257 }


pmc1002Perf15minSync OBJECT-TYPE
	SYNTAX EkiOnOff
	MAX-ACCESS read-write
	STATUS current
	DESCRIPTION
        "
        Perf. Mon. 15-min sync. :This
         OID must be used in external synchronisation
        mode only to send a 15-min synchronisation
        command
        "
	::= { pmc1002MonSync 259 }


pmc1002Perf24hSync OBJECT-TYPE
	SYNTAX EkiOnOff
	MAX-ACCESS read-write
	STATUS current
	DESCRIPTION
        "
        Perf. Mon. 24-hours sync. :This
        OID must be used in external synchronisation
        mode only to send a 24-hours synchronisation
        command
        "
	::= { pmc1002MonSync 260 }


pmc1002Perf15MinShort OBJECT-TYPE
	SYNTAX EkiOnOff
	MAX-ACCESS read-write
	STATUS current
	DESCRIPTION
        "
        15-min period is short :This OID
        indicates that the 15-min period
        lasts less than 890 seconds
        "
	::= { pmc1002MonTimeStamp 1 }


pmc1002Perf15MinLong OBJECT-TYPE
	SYNTAX EkiOnOff
	MAX-ACCESS read-write
	STATUS current
	DESCRIPTION
        "
        15-min period is long :This OID
        indicates that the 15-min period
        lasts more than 910 seconds
        "
	::= { pmc1002MonTimeStamp 2 }


pmc1002Perf24HoursShort OBJECT-TYPE
	SYNTAX Counter32
	MAX-ACCESS read-write
	STATUS current
	DESCRIPTION
        "
        24-hours period is short :This
        OID indicates that 24-hours period
        lasts less than 86390 seconds
        "
	::= { pmc1002MonTimeStamp 5 }


pmc1002Perf24HoursLong OBJECT-TYPE
	SYNTAX Counter32
	MAX-ACCESS read-write
	STATUS current
	DESCRIPTION
        "
        24-hours period is long :This
         OID indicates that 24-hours period
        lasts more than 86410 seconds
        "
	::= { pmc1002MonTimeStamp 6 }


pmc1002PerfCurrent15MinElapsedTime OBJECT-TYPE
	SYNTAX Counter32
	MAX-ACCESS read-write
	STATUS current
	DESCRIPTION
        "
        Current 15min period Elapsed Time
         :This OID gives the number of
         seconds elapsed in the current
        15-minutes period
        "
	::= { pmc1002MonTimeStamp 7 }


pmc1002PerfCurrent24HoursElapsedTime OBJECT-TYPE
	SYNTAX Counter32
	MAX-ACCESS read-write
	STATUS current
	DESCRIPTION
        "
        Current 24hours period Elapsed
        Time :This OID gives the number
        of seconds elapsed in the current
        24-hours period
        "
	::= { pmc1002MonTimeStamp 8 }






--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pmc1002DwlrestartProcess OBJECT IDENTIFIER ::= { pmc1002DwlOther 0 }




pmc1002DwlColdRestartProcessed OBJECT-TYPE
	  SYNTAX EkiOnOff
	  MAX-ACCESS read-only
	  STATUS current
	  DESCRIPTION
        "
        Cold Restart :This OID indicates
        that the module last restart was
        a Cold RESTART
        "
	  ::= { pmc1002DwlrestartProcess 2 }



pmc1002DwlWarmRestartProcessed OBJECT-TYPE
	  SYNTAX EkiOnOff
	  MAX-ACCESS read-only
	  STATUS current
	  DESCRIPTION
        "
        Warm Restart :This OID indicates
        that the module last restart was
        a Warm RESTART
        "
	  ::= { pmc1002DwlrestartProcess 1 }



--- *****************************************************
---     LEAF for the swBanksUsed article
--- *****************************************************
pmc1002DwlswBanksUsed OBJECT IDENTIFIER ::= { pmc1002DwlOther 1 }




pmc1002DwlSwBank2Notempty OBJECT-TYPE
	  SYNTAX EkiOnOff
	  MAX-ACCESS read-only
	  STATUS current
	  DESCRIPTION
        "
        SW bank 2 loaded  :This OID indicates
        a software is loaded in SW bank
        2  <Help>  This status indicates
        if the SW bank 2 contains SW package
        "
	  ::= { pmc1002DwlswBanksUsed 6 }



pmc1002DwlSwBank1Notempty OBJECT-TYPE
	  SYNTAX EkiOnOff
	  MAX-ACCESS read-only
	  STATUS current
	  DESCRIPTION
        "
        SW bank 1 loaded  :This OID indicates
        a software is loaded in SW bank
        1  <Help>  This status indicates
        if the SW bank 1 contains SW package
        "
	  ::= { pmc1002DwlswBanksUsed 5 }



pmc1002DwlSwBank2Used OBJECT-TYPE
	  SYNTAX EkiOnOff
	  MAX-ACCESS read-only
	  STATUS current
	  DESCRIPTION
        "
        SW bank 2 active  :This OID indicates
        the module is working on SW bank
        2  <Help>  This status indicates
        if the SW bank 2 is active or standby
        "
	  ::= { pmc1002DwlswBanksUsed 2 }



pmc1002DwlSwBank1Used OBJECT-TYPE
	  SYNTAX EkiOnOff
	  MAX-ACCESS read-only
	  STATUS current
	  DESCRIPTION
        "
        SW bank 1 active  :This OID indicates
        the module is working on SW bank
        1  <Help>  This status indicates
        if the SW bank 1 is active or standby
        "
	  ::= { pmc1002DwlswBanksUsed 1 }



--- *****************************************************
---     LEAF for the gwBanksUsed article
--- *****************************************************
pmc1002DwlgwBanksUsed OBJECT IDENTIFIER ::= { pmc1002DwlOther 2 }




pmc1002DwlGwBank4Notempty OBJECT-TYPE
	  SYNTAX EkiOnOff
	  MAX-ACCESS read-only
	  STATUS deprecated
	  DESCRIPTION
        "
        GW bank 4 loaded  :This OID indicates
        a gateware is loaded in GW bank
        4
        "
	  ::= { pmc1002DwlgwBanksUsed 8 }



pmc1002DwlGwBank3Notempty OBJECT-TYPE
	  SYNTAX EkiOnOff
	  MAX-ACCESS read-only
	  STATUS current
	  DESCRIPTION
        "
        GW bank 3 loaded  :This OID indicates
        a gateware is loaded in GW bank
        3  <Help>  This status indicates
        if the GW bank 3 contains GW package
        "
	  ::= { pmc1002DwlgwBanksUsed 7 }



pmc1002DwlGwBank2Notempty OBJECT-TYPE
	  SYNTAX EkiOnOff
	  MAX-ACCESS read-only
	  STATUS deprecated
	  DESCRIPTION
        "
        GW bank 2 loaded  :This OID indicates
        a gateware is loaded in GW bank
        2
        "
	  ::= { pmc1002DwlgwBanksUsed 6 }



pmc1002DwlGwBank1Notempty OBJECT-TYPE
	  SYNTAX EkiOnOff
	  MAX-ACCESS read-only
	  STATUS current
	  DESCRIPTION
        "
        GW bank 1 loaded  :This OID indicates
        a gateware is loaded in GW bank
        1  <Help>  This status indicates
        if the GW bank 1 contains GW package
        "
	  ::= { pmc1002DwlgwBanksUsed 5 }



pmc1002DwlGwBank4Used OBJECT-TYPE
	  SYNTAX EkiOnOff
	  MAX-ACCESS read-only
	  STATUS deprecated
	  DESCRIPTION
        "
        GW bank 4 active  :This OID indicates
        the module is working on GW bank
        4
        "
	  ::= { pmc1002DwlgwBanksUsed 4 }



pmc1002DwlGwBank3Used OBJECT-TYPE
	  SYNTAX EkiOnOff
	  MAX-ACCESS read-only
	  STATUS current
	  DESCRIPTION
        "
        GW bank 3 active  :This OID indicates
        the module is working on GW bank
        3  <Help>  This status indicates
        if the GW bank 3 is active or standby
        "
	  ::= { pmc1002DwlgwBanksUsed 3 }



pmc1002DwlGwBank2Used OBJECT-TYPE
	  SYNTAX EkiOnOff
	  MAX-ACCESS read-only
	  STATUS deprecated
	  DESCRIPTION
        "
        GW bank 2 active  :This OID indicates
        the module is working on GW bank
        2
        "
	  ::= { pmc1002DwlgwBanksUsed 2 }



pmc1002DwlGwBank1Used OBJECT-TYPE
	  SYNTAX EkiOnOff
	  MAX-ACCESS read-only
	  STATUS current
	  DESCRIPTION
        "
        GW bank 1 active  :This OID indicates
        the module is working on GW bank
        1  <Help>  This status indicates
        if the GW bank 1 is active or standby
        "
	  ::= { pmc1002DwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pmc1002CfgAccessCAisCsf OBJECT IDENTIFIER ::= { pmc1002Config 1 }



--- *****************************************************
---     LEAF for the table 0012
--- *****************************************************

pmc1002CfgClientcaiscsfTable OBJECT-TYPE
	SYNTAX  SEQUENCE OF Pmc1002CfgClientcaiscsfEntry
	MAX-ACCESS not-accessible
	STATUS current
	DESCRIPTION
        "
        List of  Article
        "
	::= { pmc1002CfgAccessCAisCsf 1 }


pmc1002CfgClientcaiscsfEntry OBJECT-TYPE
	SYNTAX Pmc1002CfgClientcaiscsfEntry
	MAX-ACCESS not-accessible
	STATUS current
	DESCRIPTION
        "
        Row definition for the accessCAisCsf
        table
        "
	INDEX   { pmc1002CfgClientcaiscsfIndex }
	::= { pmc1002CfgClientcaiscsfTable 1 }


Pmc1002CfgClientcaiscsfEntry ::=
	SEQUENCE {
	pmc1002CfgClientcaiscsfIndex
		INTEGER,
	pmc1002CfgCAisModePortn
		Unsigned32,
	pmc1002CfgUpAccessioAlmPortn
		Unsigned32,
	pmc1002CfgUpMapperDeAlmPortn
		Unsigned32,
	pmc1002CfgDownAccessioAlmPortn
		Unsigned32,
	pmc1002CfgDownMapperDeAlmPortn
		Unsigned32,
	pmc1002CfgDownDfrmAlmPortn
		Unsigned32,
	pmc1002CfgDownLineSyncAlarmsPortn
		Unsigned32
	}


pmc1002CfgClientcaiscsfIndex OBJECT-TYPE
	SYNTAX  INTEGER(0..128)
	MAX-ACCESS  read-only
	STATUS current
	DESCRIPTION
        "
        Index definition for the clientcaiscsf
        table
        "
	::= { pmc1002CfgClientcaiscsfEntry 1 }


pmc1002CfgCAisModePortn OBJECT-TYPE
	SYNTAX  Unsigned32 (0..65536)
	MAX-ACCESS read-write
	STATUS current
	DESCRIPTION
        "
        CAIS mode  on Client Port :This
        register enables/disables port
          laser shutdown on CAIS insertion
        condition
        "
	::= { pmc1002CfgClientcaiscsfEntry 3 }


pmc1002CfgUpAccessioAlmPortn OBJECT-TYPE
	SYNTAX  Unsigned32 (0..65536)
	MAX-ACCESS read-write
	STATUS current
	DESCRIPTION
        "
        CSF contributors on Client Port
        :This register configures the contributors
        to upstream CSF insertion on the
        port.
        "
	::= { pmc1002CfgClientcaiscsfEntry 9 }


pmc1002CfgUpMapperDeAlmPortn OBJECT-TYPE
	SYNTAX  Unsigned32 (0..65536)
	MAX-ACCESS read-write
	STATUS current
	DESCRIPTION
        "
        CSF contributors on Client Port
        :This register configures the contributors
        to upstream CSF insertion on the
        port.
        "
	::= { pmc1002CfgClientcaiscsfEntry 10 }


pmc1002CfgDownAccessioAlmPortn OBJECT-TYPE
	SYNTAX  Unsigned32 (0..65536)
	MAX-ACCESS read-write
	STATUS current
	DESCRIPTION
        "
        CAIS contributors on Client Port
        :This register configures the contributors
        to downstream CAIS insertion on
         port.
        "
	::= { pmc1002CfgClientcaiscsfEntry 17 }


pmc1002CfgDownMapperDeAlmPortn OBJECT-TYPE
	SYNTAX  Unsigned32 (0..65536)
	MAX-ACCESS read-write
	STATUS current
	DESCRIPTION
        "
        CAIS contributors on Client Port
        :This register configures the contributors
        to downstream CAIS insertion on
         port.
        "
	::= { pmc1002CfgClientcaiscsfEntry 18 }


pmc1002CfgDownDfrmAlmPortn OBJECT-TYPE
	SYNTAX  Unsigned32 (0..65536)
	MAX-ACCESS read-write
	STATUS current
	DESCRIPTION
        "
        CAIS contributors on Client Port
        :This register configures the contributors
        to downstream CAIS insertion on
         port.
        "
	::= { pmc1002CfgClientcaiscsfEntry 19 }


pmc1002CfgDownLineSyncAlarmsPortn OBJECT-TYPE
	SYNTAX  Unsigned32 (0..65536)
	MAX-ACCESS read-write
	STATUS deprecated
	DESCRIPTION
        "
        CAIS contributors on Client Port
        :This register configures the contributors
        to downstream CAIS insertion on
         port.
        "
	::= { pmc1002CfgClientcaiscsfEntry 20 }


--- *****************************************************
---     LEAF for the table Group startup
--- *****************************************************

pmc1002CfgStartup OBJECT IDENTIFIER ::= { pmc1002Config 2 }



--- *****************************************************
---     LEAF for the table 2111
--- *****************************************************

pmc1002CfgClientStartupTable OBJECT-TYPE
	SYNTAX  SEQUENCE OF Pmc1002CfgClientStartupEntry
	MAX-ACCESS not-accessible
	STATUS current
	DESCRIPTION
        "
        List of  Article
        "
	::= { pmc1002CfgStartup 1 }


pmc1002CfgClientStartupEntry OBJECT-TYPE
	SYNTAX Pmc1002CfgClientStartupEntry
	MAX-ACCESS not-accessible
	STATUS current
	DESCRIPTION
        "
        Row definition for the startup
        table
        "
	INDEX   { pmc1002CfgClientStartupIndex }
	::= { pmc1002CfgClientStartupTable 1 }


Pmc1002CfgClientStartupEntry ::=
	SEQUENCE {
	pmc1002CfgClientStartupIndex
		INTEGER,
	pmc1002CfgSystConfPortPortn
		Unsigned32,
	pmc1002CfgNetConfPortPortn
		Unsigned32,
	pmc1002CfgPortsOptionsPortn
		Unsigned32
	}


pmc1002CfgClientStartupIndex OBJECT-TYPE
	SYNTAX  INTEGER(0..128)
	MAX-ACCESS  read-only
	STATUS current
	DESCRIPTION
        "
        Index definition for the clientStartup
        table
        "
	::= { pmc1002CfgClientStartupEntry 1 }


pmc1002CfgSystConfPortPortn OBJECT-TYPE
	SYNTAX  Unsigned32 (0..65536)
	MAX-ACCESS read-write
	STATUS current
	DESCRIPTION
        "
        Default Settings on Client Port
        :This  register configures the
         default initialisation settings
        on the port.
        "
	::= { pmc1002CfgClientStartupEntry 3 }


pmc1002CfgNetConfPortPortn OBJECT-TYPE
	SYNTAX  Unsigned32 (0..65536)
	MAX-ACCESS read-write
	STATUS current
	DESCRIPTION
        "
        Default Protocol on Client Port
        :This register configures the default
        initialisation protocol on the
         port.
        "
	::= { pmc1002CfgClientStartupEntry 4 }


pmc1002CfgPortsOptionsPortn OBJECT-TYPE
	SYNTAX  Unsigned32 (0..65536)
	MAX-ACCESS read-write
	STATUS current
	DESCRIPTION
        "
        Default Options on Client Port
        :This register configures the default
        options on the client port
        "
	::= { pmc1002CfgClientStartupEntry 6 }


--- *****************************************************
---     LEAF for the table 2191
--- *****************************************************

pmc1002tablelineStartup OBJECT IDENTIFIER ::= { pmc1002CfgStartup 2 }



pmc1002CfgsynthTransLine1 OBJECT-TYPE
	  SYNTAX Unsigned32 (0..65536)
	  MAX-ACCESS read-write
	  STATUS current
	  DESCRIPTION
        "
        Default Settings on Line 1 :This
        register configures the default
        initialisation settings on Line
        port 1.
        "
	  ::= { pmc1002tablelineStartup 2 }



pmc1002CfgnetConfMod OBJECT-TYPE
	  SYNTAX Unsigned32 (0..65536)
	  MAX-ACCESS read-write
	  STATUS current
	  DESCRIPTION
        "
        Default Protocol on Module :This
        register configures the default
        initialisation protocol on the
         module.
        "
	  ::= { pmc1002tablelineStartup 3 }



pmc1002CfglineOptions1 OBJECT-TYPE
	  SYNTAX Unsigned32 (0..65536)
	  MAX-ACCESS read-write
	  STATUS current
	  DESCRIPTION
        "
        Default Options on Active Line
        Port :This register configures
         the default options on the active
        line port
        "
	  ::= { pmc1002tablelineStartup 5 }



pmc1002CfgsystTransLine2 OBJECT-TYPE
	  SYNTAX Unsigned32 (0..65536)
	  MAX-ACCESS read-write
	  STATUS current
	  DESCRIPTION
        "
        Default Settings on Line 2 :This
        register configures the default
        initialisation settings on Line
        port 2.
        "
	  ::= { pmc1002tablelineStartup 6 }



pmc1002CfglineSelection OBJECT-TYPE
	  SYNTAX Unsigned32 (0..65536)
	  MAX-ACCESS read-write
	  STATUS current
	  DESCRIPTION
        "
        Default Settings of active line
        :This  register configures the
         start up active line.
        "
	  ::= { pmc1002tablelineStartup 7 }



--- *****************************************************
---     LEAF for the table 21AB
--- *****************************************************

pmc1002CfgXfpTable OBJECT-TYPE
	SYNTAX  SEQUENCE OF Pmc1002CfgXfpEntry
	MAX-ACCESS not-accessible
	STATUS current
	DESCRIPTION
        "
        List of  Article
        "
	::= { pmc1002CfgStartup 3 }


pmc1002CfgXfpEntry OBJECT-TYPE
	SYNTAX Pmc1002CfgXfpEntry
	MAX-ACCESS not-accessible
	STATUS current
	DESCRIPTION
        "
        Row definition for the startup
        table
        "
	INDEX   { pmc1002CfgXfpIndex }
	::= { pmc1002CfgXfpTable 1 }


Pmc1002CfgXfpEntry ::=
	SEQUENCE {
	pmc1002CfgXfpIndex
		INTEGER,
	pmc1002CfgSystConfXfpPortn
		Unsigned32,
	pmc1002CfgDataRateConfXfpPortn
		Unsigned32
	}


pmc1002CfgXfpIndex OBJECT-TYPE
	SYNTAX  INTEGER(0..128)
	MAX-ACCESS  read-only
	STATUS current
	DESCRIPTION
        "
        Index definition for the xfp table
        "
	::= { pmc1002CfgXfpEntry 1 }


pmc1002CfgSystConfXfpPortn OBJECT-TYPE
	SYNTAX  Unsigned32 (0..65536)
	MAX-ACCESS read-write
	STATUS current
	DESCRIPTION
        "
        Default settings on XFP Port :This
        register configures the default
        initialisation settings on XFP
         port.
        "
	::= { pmc1002CfgXfpEntry 3 }


pmc1002CfgDataRateConfXfpPortn OBJECT-TYPE
	SYNTAX  Unsigned32 (0..65536)
	MAX-ACCESS read-write
	STATUS deprecated
	DESCRIPTION
        "
        :Reserved
        "
	::= { pmc1002CfgXfpEntry 4 }


--- *****************************************************
---     LEAF for the table 25A8
--- *****************************************************

pmc1002CfgOtxtlhTable OBJECT-TYPE
	SYNTAX  SEQUENCE OF Pmc1002CfgOtxtlhEntry
	MAX-ACCESS not-accessible
	STATUS current
	DESCRIPTION
        "
        List of  Article
        "
	::= { pmc1002CfgStartup 4 }


pmc1002CfgOtxtlhEntry OBJECT-TYPE
	SYNTAX Pmc1002CfgOtxtlhEntry
	MAX-ACCESS not-accessible
	STATUS current
	DESCRIPTION
        "
        Row definition for the startup
        table
        "
	INDEX   { pmc1002CfgOtxtlhIndex }
	::= { pmc1002CfgOtxtlhTable 1 }


Pmc1002CfgOtxtlhEntry ::=
	SEQUENCE {
	pmc1002CfgOtxtlhIndex
		INTEGER,
	pmc1002CfgLineOtxMiscPortn
		Unsigned32,
	pmc1002CfgLineDitherRatePortn
		Unsigned32,
	pmc1002CfgLineDitherFhzPortn
		Unsigned32,
	pmc1002CfgLinePwrLaserPortn
		Unsigned32,
	pmc1002CfgLineFCurrentPortn
		Unsigned32,
	pmc1002CfgLineGridCurrentPortn
		Unsigned32,
	pmc1002CfgFPortn
		Unsigned32,
	pmc1002CfgReservedPortn
		Unsigned32,
	pmc1002CfgLinePhotodiodeModePortn
		Unsigned32,
	pmc1002CfgLinePhotodiodeValuePortn
		Unsigned32
	}


pmc1002CfgOtxtlhIndex OBJECT-TYPE
	SYNTAX  INTEGER(0..128)
	MAX-ACCESS  read-only
	STATUS current
	DESCRIPTION
        "
        Index definition for the otxtlh
        table
        "
	::= { pmc1002CfgOtxtlhEntry 1 }


pmc1002CfgLineOtxMiscPortn OBJECT-TYPE
	SYNTAX  Unsigned32 (0..65536)
	MAX-ACCESS read-write
	STATUS current
	DESCRIPTION
        "
        Default Line OTX TLH miscellaneous
        :This register configures the start-up
        miscellaneous mode of the Line
         OTX TLH
        "
	::= { pmc1002CfgOtxtlhEntry 3 }


pmc1002CfgLineDitherRatePortn OBJECT-TYPE
	SYNTAX  Unsigned32 (0..65536)
	MAX-ACCESS read-write
	STATUS current
	DESCRIPTION
        "
        Default Line OTX TLH FM amplitude
        :This register configures the start-up
        width of the frequency modulation
        of the Line OTX TLH
        "
	::= { pmc1002CfgOtxtlhEntry 4 }


pmc1002CfgLineDitherFhzPortn OBJECT-TYPE
	SYNTAX  Unsigned32 (0..65536)
	MAX-ACCESS read-write
	STATUS current
	DESCRIPTION
        "
        Default Line OTX TLH FM frequency
        :This register configures the start-up
        frequency of the frequency modulation
        of the Line OTX TLH
        "
	::= { pmc1002CfgOtxtlhEntry 5 }


pmc1002CfgLinePwrLaserPortn OBJECT-TYPE
	SYNTAX  Unsigned32 (0..65536)
	MAX-ACCESS read-write
	STATUS current
	DESCRIPTION
        "
        Defaut Line OTX TLH output Power
        :This register configures the start-up
        output power of the Line OTX TLH
         (Unit = dBm)
        "
	::= { pmc1002CfgOtxtlhEntry 6 }


pmc1002CfgLineFCurrentPortn OBJECT-TYPE
	SYNTAX  Unsigned32 (0..65536)
	MAX-ACCESS read-write
	STATUS current
	DESCRIPTION
        "
        Default Line OTX TLH Channel :This
        register configures the start-up
        laser channel of the Line OTX TLH
        "
	::= { pmc1002CfgOtxtlhEntry 7 }


pmc1002CfgLineGridCurrentPortn OBJECT-TYPE
	SYNTAX  Unsigned32 (0..65536)
	MAX-ACCESS read-write
	STATUS current
	DESCRIPTION
        "
        Default Line OTX TLH Grid :This
        register configures the start-up
        laser grid of the Line OTX TLH
        "
	::= { pmc1002CfgOtxtlhEntry 8 }


pmc1002CfgFPortn OBJECT-TYPE
	SYNTAX  Unsigned32 (0..65536)
	MAX-ACCESS read-write
	STATUS current
	DESCRIPTION
        "
        Default Line OTX TLH lowest Freq
        :This register configures the start-up
        lowest frequency supported on the
        Line OTX TLH
        "
	::= { pmc1002CfgOtxtlhEntry 9 }


pmc1002CfgReservedPortn OBJECT-TYPE
	SYNTAX  Unsigned32 (0..65536)
	MAX-ACCESS read-write
	STATUS deprecated
	DESCRIPTION
        "
        :
        "
	::= { pmc1002CfgOtxtlhEntry 10 }


pmc1002CfgLinePhotodiodeModePortn OBJECT-TYPE
	SYNTAX  Unsigned32 (0..65536)
	MAX-ACCESS read-write
	STATUS current
	DESCRIPTION
        "
        Default Line OTX TLH APD mode
         :This register configures the
         start-up APD mode of the Line
         OTX TLH
        "
	::= { pmc1002CfgOtxtlhEntry 11 }


pmc1002CfgLinePhotodiodeValuePortn OBJECT-TYPE
	SYNTAX  Unsigned32 (0..65536)
	MAX-ACCESS read-write
	STATUS current
	DESCRIPTION
        "
        Default Line OTX TLH APD atten.
        :This register configures the start-up
        APD attenuation on the Line OTX
        TLH
        "
	::= { pmc1002CfgOtxtlhEntry 12 }


--- *****************************************************
---     LEAF for the table Group labels
--- *****************************************************

pmc1002CfgLabels OBJECT IDENTIFIER ::= { pmc1002Config 3 }



--- *****************************************************
---     LEAF for the table NO_VALUE
--- *****************************************************

pmc1002CfgLabelclientTable OBJECT-TYPE
	SYNTAX  SEQUENCE OF Pmc1002CfgLabelclientEntry
	MAX-ACCESS not-accessible
	STATUS current
	DESCRIPTION
        "
        List of  Article
        "
	::= { pmc1002CfgLabels 1 }


pmc1002CfgLabelclientEntry OBJECT-TYPE
	SYNTAX Pmc1002CfgLabelclientEntry
	MAX-ACCESS not-accessible
	STATUS current
	DESCRIPTION
        "
        Row definition for the labels
         table
        "
	INDEX   { pmc1002CfgLabelclientIndex }
	::= { pmc1002CfgLabelclientTable 1 }


Pmc1002CfgLabelclientEntry ::=
	SEQUENCE {
	pmc1002CfgLabelclientIndex
		INTEGER,
	pmc1002CfgLabelclientPortn
		DisplayString
	}


pmc1002CfgLabelclientIndex OBJECT-TYPE
	SYNTAX  INTEGER(0..128)
	MAX-ACCESS  read-only
	STATUS current
	DESCRIPTION
        "
        Index definition for the labelclient
        table
        "
	::= { pmc1002CfgLabelclientEntry 1 }


pmc1002CfgLabelclientPortn OBJECT-TYPE
	SYNTAX  DisplayString( SIZE(1..16))
	MAX-ACCESS read-write
	STATUS current
	DESCRIPTION
        "
        Default settings on the label
         of the Ports :These registers
         configures the default initialisation
        settings of the labels of the ports.
        "
	::= { pmc1002CfgLabelclientEntry 3 }


--- *****************************************************
---     LEAF for the table NO_VALUE
--- *****************************************************

pmc1002CfgLabellineTable OBJECT-TYPE
	SYNTAX  SEQUENCE OF Pmc1002CfgLabellineEntry
	MAX-ACCESS not-accessible
	STATUS current
	DESCRIPTION
        "
        List of  Article
        "
	::= { pmc1002CfgLabels 2 }


pmc1002CfgLabellineEntry OBJECT-TYPE
	SYNTAX Pmc1002CfgLabellineEntry
	MAX-ACCESS not-accessible
	STATUS current
	DESCRIPTION
        "
        Row definition for the labels
         table
        "
	INDEX   { pmc1002CfgLabellineIndex }
	::= { pmc1002CfgLabellineTable 1 }


Pmc1002CfgLabellineEntry ::=
	SEQUENCE {
	pmc1002CfgLabellineIndex
		INTEGER,
	pmc1002CfgLabellinePortn
		DisplayString
	}


pmc1002CfgLabellineIndex OBJECT-TYPE
	SYNTAX  INTEGER(0..128)
	MAX-ACCESS  read-only
	STATUS current
	DESCRIPTION
        "
        Index definition for the labelline
        table
        "
	::= { pmc1002CfgLabellineEntry 1 }


pmc1002CfgLabellinePortn OBJECT-TYPE
	SYNTAX  DisplayString( SIZE(1..16))
	MAX-ACCESS read-write
	STATUS current
	DESCRIPTION
        "
        Default settings on the label
         of the lines :These registers
         configures the default initialisation
        settings of the labels of the lines.
        "
	::= { pmc1002CfgLabellineEntry 3 }


--- *****************************************************
---     LEAF for the table Group other
--- *****************************************************

pmc1002CfgOther OBJECT IDENTIFIER ::= { pmc1002Config 4 }



--- *****************************************************
---     LEAF for the table 2300
--- *****************************************************

pmc1002tablemoduleOther OBJECT IDENTIFIER ::= { pmc1002CfgOther 1 }



pmc1002Cfgmode OBJECT-TYPE
	  SYNTAX Unsigned32 (0..65536)
	  MAX-ACCESS read-write
	  STATUS current
	  DESCRIPTION
        "
        Default settings on Module :This
        register selects the DCC  configuration
        of the PM
        "
	  ::= { pmc1002tablemoduleOther 2 }



--- *****************************************************
---     LEAF for the table Group startuptablefive
--- *****************************************************

pmc1002CfgStartuptablefive OBJECT IDENTIFIER ::= { pmc1002Config 5 }



--- *****************************************************
---     LEAF for the table 0005
--- *****************************************************

pmc1002CfgOtxtlhcapabilitiesTable OBJECT-TYPE
	SYNTAX  SEQUENCE OF Pmc1002CfgOtxtlhcapabilitiesEntry
	MAX-ACCESS not-accessible
	STATUS current
	DESCRIPTION
        "
        List of  Article
        "
	::= { pmc1002CfgStartuptablefive 1 }


pmc1002CfgOtxtlhcapabilitiesEntry OBJECT-TYPE
	SYNTAX Pmc1002CfgOtxtlhcapabilitiesEntry
	MAX-ACCESS not-accessible
	STATUS current
	DESCRIPTION
        "
        Row definition for the startuptablefive
        table
        "
	INDEX   { pmc1002CfgOtxtlhcapabilitiesIndex }
	::= { pmc1002CfgOtxtlhcapabilitiesTable 1 }


Pmc1002CfgOtxtlhcapabilitiesEntry ::=
	SEQUENCE {
	pmc1002CfgOtxtlhcapabilitiesIndex
		INTEGER,
	pmc1002CfgComponentTypePortn
		Unsigned32,
	pmc1002CfgMiscellaneousPortn
		Unsigned32,
	pmc1002CfgFirstChannelPortn
		Unsigned32,
	pmc1002CfgLastChannelPortn
		Unsigned32,
	pmc1002CfgGridPortn
		Unsigned32
	}


pmc1002CfgOtxtlhcapabilitiesIndex OBJECT-TYPE
	SYNTAX  INTEGER(0..128)
	MAX-ACCESS  read-only
	STATUS current
	DESCRIPTION
        "
        Index definition for the otxtlhcapabilities
        table
        "
	::= { pmc1002CfgOtxtlhcapabilitiesEntry 1 }


pmc1002CfgComponentTypePortn OBJECT-TYPE
	SYNTAX  Unsigned32 (0..65536)
	MAX-ACCESS read-only
	STATUS current
	DESCRIPTION
        "
        Component parameters :This OID
        defines the component parameters
        "
	::= { pmc1002CfgOtxtlhcapabilitiesEntry 3 }


pmc1002CfgMiscellaneousPortn OBJECT-TYPE
	SYNTAX  Unsigned32 (0..65536)
	MAX-ACCESS read-only
	STATUS current
	DESCRIPTION
        "
        Miscellaneous default settings
        :This OID defines the miscellaneous
        parameters
        "
	::= { pmc1002CfgOtxtlhcapabilitiesEntry 4 }


pmc1002CfgFirstChannelPortn OBJECT-TYPE
	SYNTAX  Unsigned32 (0..65536)
	MAX-ACCESS read-only
	STATUS current
	DESCRIPTION
        "
        Number of the first channel of
        the component :This OID defines
        the first channel number of the
        PM
        "
	::= { pmc1002CfgOtxtlhcapabilitiesEntry 5 }


pmc1002CfgLastChannelPortn OBJECT-TYPE
	SYNTAX  Unsigned32 (0..65536)
	MAX-ACCESS read-only
	STATUS current
	DESCRIPTION
        "
        Number of the last channel of
         the component :This OID defines
        the last channel number of the
         PM
        "
	::= { pmc1002CfgOtxtlhcapabilitiesEntry 6 }


pmc1002CfgGridPortn OBJECT-TYPE
	SYNTAX  Unsigned32 (0..65536)
	MAX-ACCESS read-only
	STATUS current
	DESCRIPTION
        "
        Grid value of the component :This
        OID defines the grid of the PM
        "
	::= { pmc1002CfgOtxtlhcapabilitiesEntry 7 }



pmc1002CfgWriteConfiguration  OBJECT-TYPE
	SYNTAX EkiOnOff
	MAX-ACCESS read-write
	STATUS current
	DESCRIPTION
	"Write configuration to module:This OID
	 writes the complete configuration to the module"
	::= { pmc1002Config 257 }






--- *****************************************************
---     TRAP OBJECTS
--- *****************************************************


pmc1002trapBoardNumber OBJECT-TYPE
	SYNTAX INTEGER(1..64)
	MAX-ACCESS read-only
	STATUS current
	DESCRIPTION
	"Last module which generates a trap"
	::= { pmc1002traps 1 }



pmc1002trapClientNumber OBJECT-TYPE
	SYNTAX INTEGER(1..64)
	MAX-ACCESS read-only
	STATUS current
	DESCRIPTION
	"Last module which generates a trap"
	::= { pmc1002traps 2 }



pmc1002trapLineNumber OBJECT-TYPE
	SYNTAX INTEGER(1..64)
	MAX-ACCESS read-only
	STATUS current
	DESCRIPTION
	"Last module which generates a trap"
	::= { pmc1002traps 3 }







--- *****************************************************
---     LINE TRAPS
--- *****************************************************

pmc1002LineTrapNotUrgentGoesOn NOTIFICATION-TYPE
	OBJECTS {pmc1002AlmLineDdmWarningPortn, pmc1002trapLineNumber, pmc1002trapBoardNumber}
	STATUS current
	--&FILTNAME    "PM C1002 Line Not Urgent ON"
	--&ACTIONS     { log, minor }
	--&MATCH       { pmc1002AlmLineDdmWarningPortn "on", pmc1002trapLineNumber "$2", pmc1002trapBoardNumber "$3"}
	--&MESG        "DDM Warning appears on Line Port $2 of PM C1002 in Slot $3 ($A)"
	DESCRIPTION "Not urgent Line default is activated"
	::= { pmc1002traps 30 }

pmc1002LineTrapNotUrgentGoesOff NOTIFICATION-TYPE
	OBJECTS {pmc1002AlmLineDdmWarningPortn, pmc1002trapLineNumber, pmc1002trapBoardNumber}
	STATUS current
	--&FILTNAME    "PM C1002 Line Not Urgent OFF"
	--&ACTIONS     { log, normal }
	--&CLEARS      { "PM C1002 Line Not Urgent ON" }
	--&MATCH       { pmc1002AlmLineDdmWarningPortn "on", pmc1002trapLineNumber "$2", pmc1002trapBoardNumber "$3"}
	--&MESG        "DDM Warning disappears on Line Port $2 of PM C1002 in Slot $3 ($A)"
	DESCRIPTION "Not urgent Line default disappeared"
	::= { pmc1002traps 31 }

pmc1002LineTrapUrgentGoesOn NOTIFICATION-TYPE
	OBJECTS {pmc1002AlmLineDdmAlmPortn, pmc1002trapLineNumber, pmc1002trapBoardNumber}
	STATUS current
	--&FILTNAME    "PM C1002 Line Urgent ON"
	--&ACTIONS     { log, major }
	--&MATCH       { pmc1002AlmLineDdmAlmPortn "on", pmc1002trapLineNumber "$2", pmc1002trapBoardNumber "$3"}
	--&MESG        "DDM Alarm appears on Line Port $2 of PM C1002 in Slot $3 ($A)"
	DESCRIPTION "Urgent Line default is activated"
	::= { pmc1002traps 32 }

pmc1002LineTrapUrgentGoesOff NOTIFICATION-TYPE
	OBJECTS {pmc1002AlmLineDdmAlmPortn, pmc1002trapLineNumber, pmc1002trapBoardNumber}
	STATUS current
	--&FILTNAME    "PM C1002 Line Urgent OFF"
	--&ACTIONS     { log, normal }
	--&CLEARS      { "PM C1002 Line Urgent ON" }
	--&MATCH       { pmc1002AlmLineDdmAlmPortn "on", pmc1002trapLineNumber "$2", pmc1002trapBoardNumber "$3"}
	--&MESG        "DDM Alarm disappears on Line Port $2 of PM C1002 in Slot $3 ($A)"
	DESCRIPTION "Urgent Line default disappeared"
	::= { pmc1002traps 33 }

pmc1002LineTrapCritGoesOn NOTIFICATION-TYPE
	OBJECTS {pmc1002AlmLineFailPortn , pmc1002AlmLineHwFailPortn, pmc1002trapLineNumber, pmc1002trapBoardNumber}
	STATUS current
	--&FILTNAME    "PM C1002 Line Fail ON"
	--&ACTIONS     { log, critical }
	--&MATCH       { pmc1002AlmLineFailPortn "on", pmc1002AlmLineHwFailPortn "*", pmc1002trapLineNumber "$3", pmc1002trapBoardNumber "$4"}
	--&MESG        "Line Port $3 Down on PM C1002 in Slot $4 ($A)"

	--&FILTNAME    "PM C1002 Line HW Fail ON (Hidden)"
	--&ACTIONS     { info }
	--&MATCH       { pmc1002AlmLineFailPortn "*", pmc1002AlmLineHwFailPortn "on", pmc1002trapLineNumber "$3", pmc1002trapBoardNumber "$4"}
	--&MESG        "Line Port $3 Down on PM C1002 in Slot $4 ($A)"
	DESCRIPTION "Critical Line default is activated"
	::= { pmc1002traps 34 }

pmc1002LineTrapCritGoesOff NOTIFICATION-TYPE
	OBJECTS {pmc1002AlmLineFailPortn , pmc1002AlmLineHwFailPortn, pmc1002trapLineNumber, pmc1002trapBoardNumber}
	STATUS current
	--&FILTNAME    "PM C1002 Line Fail OFF"
	--&ACTIONS     { log,  normal }
	--&CLEARS      { "PM C1002 Line Fail ON" }
	--&MATCH       { pmc1002AlmLineFailPortn "on", pmc1002AlmLineHwFailPortn "*", pmc1002trapLineNumber "$3", pmc1002trapBoardNumber "$4"}
	--&MESG        "Line Port $3 Up on PM C1002 in Slot $4 ($A)"

	--&FILTNAME    "PM C1002 Line HW Fail OFF (Hidden)"
	--&ACTIONS     { info }
	--&MATCH       { pmc1002AlmLineFailPortn "*", pmc1002AlmLineHwFailPortn "on", pmc1002trapLineNumber "$3", pmc1002trapBoardNumber "$4"}
	--&MESG        "Line Port $3 Up on PM C1002 in Slot $4 ($A)"
	DESCRIPTION "Critical Line default disappeared"
	::= { pmc1002traps 35 }






--- *****************************************************
---     CLIENT TRAPS
--- *****************************************************

pmc1002ClientTrapNotUrgentGoesOn NOTIFICATION-TYPE
	OBJECTS {pmc1002AlmClientSfpDdmWarningPortn, pmc1002trapClientNumber, pmc1002trapBoardNumber}
	STATUS current
	--&FILTNAME    "PM C1002 Client Not Urgent ON"
	--&ACTIONS     { log, minor }
	--&MATCH       { pmc1002AlmClientSfpDdmWarningPortn "on", pmc1002trapClientNumber "$2", pmc1002trapBoardNumber "$3"}
	--&MESG        "DDM Warning appears on Client Port $2 of PM C1002 in Slot $3 ($A)"
	DESCRIPTION "Not urgent client default is activated"
	::= { pmc1002traps 40 }

pmc1002ClientTrapNotUrgentGoesOff NOTIFICATION-TYPE
	OBJECTS {pmc1002AlmClientSfpDdmWarningPortn, pmc1002trapClientNumber, pmc1002trapBoardNumber}
	STATUS current
	--&FILTNAME    "PM C1002 Client Not Urgent OFF"
	--&ACTIONS     { log, normal }
	--&CLEARS      { "PM C1002 Client Not Urgent ON" }
	--&MATCH       { pmc1002AlmClientSfpDdmWarningPortn "on", pmc1002trapClientNumber "$2", pmc1002trapBoardNumber "$3"}
	--&MESG        "DDM Warning appears on Client Port $2 of PM C1002 in Slot $3 ($A)"
	DESCRIPTION "Not urgent client default disappeared"
	::= { pmc1002traps 41 }

pmc1002ClientTrapUrgentGoesOn NOTIFICATION-TYPE
	OBJECTS {pmc1002AlmClientSfpDdmAlmPortn, pmc1002trapClientNumber, pmc1002trapBoardNumber}
	STATUS current
	--&FILTNAME    "PM C1002 Client Urgent ON"
	--&ACTIONS     { log, major }
	--&MATCH       { pmc1002AlmClientSfpDdmAlmPortn "on", pmc1002trapClientNumber "$2", pmc1002trapBoardNumber "$3"}
	--&MESG        "DDM Alarm appears on Client Port $2 of PM C1002 in Slot $3 ($A)"
	DESCRIPTION "Urgent client default is activated"
	::= { pmc1002traps 42 }

pmc1002ClientTrapUrgentGoesOff NOTIFICATION-TYPE
	OBJECTS {pmc1002AlmClientSfpDdmAlmPortn, pmc1002trapClientNumber, pmc1002trapBoardNumber}
	STATUS current
	--&FILTNAME    "PM C1002 Client Urgent OFF"
	--&ACTIONS     { log, normal }
	--&CLEARS      { "PM C1002 Client Urgent ON" }
	--&MATCH       { pmc1002AlmClientSfpDdmAlmPortn "on", pmc1002trapClientNumber "$2", pmc1002trapBoardNumber "$3"}
	--&MESG        "DDM Alarm disappears on Client Port $2 of PM C1002 in Slot $3 ($A)"
	DESCRIPTION "Urgent client default disappeared"
	::= { pmc1002traps 43 }

pmc1002ClientTrapCritGoesOn NOTIFICATION-TYPE
	OBJECTS {pmc1002AlmClientFailPortn, pmc1002AlmClientHwFailPortn, pmc1002trapClientNumber,pmc1002trapBoardNumber}
	STATUS current
	--&FILTNAME    "PM C1002 Client Fail ON"
	--&ACTIONS     { log, critical }
	--&MATCH       { pmc1002AlmClientFailPortn "on", pmc1002AlmClientHwFailPortn "*", pmc1002trapClientNumber "$3", pmc1002trapBoardNumber "$4"}
	--&MESG        "Client Port $3 Down on PM C1002 in Slot $4 ($A)"

	--&FILTNAME    "PM C1002 Client HW Fail ON (Hidden)"
	--&ACTIONS     { info }
	--&MATCH       { pmc1002AlmClientFailPortn "*", pmc1002AlmClientHwFailPortn "on", pmc1002trapClientNumber "$3", pmc1002trapBoardNumber "$4"}
	--&MESG        "Client Port $3 Down on PM C1002 in Slot $4 ($A)"
	DESCRIPTION "Critical client default is activated"
	::= { pmc1002traps 44 }

pmc1002ClientTrapCritGoesOff NOTIFICATION-TYPE
	OBJECTS {pmc1002AlmClientFailPortn, pmc1002AlmClientHwFailPortn, pmc1002trapClientNumber, pmc1002trapBoardNumber}
	STATUS current
	--&FILTNAME    "PM C1002 Client Fail OFF"
	--&ACTIONS     { log, normal }
	--&CLEARS      { "PM C1002 Client Fail ON" }
	--&MATCH       { pmc1002AlmClientFailPortn "on", pmc1002AlmClientHwFailPortn "*", pmc1002trapClientNumber "$3", pmc1002trapBoardNumber "$4"}
	--&MESG        "Client Port $3 Up on PM C1002 in Slot $4 ($A)"

	--&FILTNAME    "PM C1002 Client HW Fail OFF (Hidden)"
	--&ACTIONS     { info }
	--&MATCH       { pmc1002AlmClientFailPortn "*", pmc1002AlmClientHwFailPortn "on", pmc1002trapClientNumber "$3", pmc1002trapBoardNumber "$4"}
	--&MESG        "Client Port $3 Up on PM C1002 in Slot $4 ($A)"
	DESCRIPTION "Critical client default disappeared"
	::= { pmc1002traps 45 }






--- *****************************************************
---     HW TRAPS
--- *****************************************************

pmc1002PowerTrapUrgentGoesOn NOTIFICATION-TYPE
	OBJECTS {pmc1002AlmDefFuseB, pmc1002AlmDefFuseA , pmc1002trapBoardNumber}
	STATUS current
	--&FILTNAME    "PM C1002 Fuse A Fail ON"
	--&ACTIONS     { log, major }
	--&MATCH       { pmc1002AlmDefFuseB "*", pmc1002AlmDefFuseA "on", pmc1002trapBoardNumber "$3"}
	--&MESG        "Power Input A Fail on PM C1002 in Slot $3 ($A)"

	--&FILTNAME    "PM C1002 Fuse B Fail ON"
	--&ACTIONS     { log, major }
	--&MATCH       { pmc1002AlmDefFuseB "on", pmc1002AlmDefFuseA "*", pmc1002trapBoardNumber "$3"}
	--&MESG        "Power Input B Fail on PM C1002 in Slot $3 ($A)"
	DESCRIPTION "Urgent power supply default is activated"
	::= { pmc1002traps 50 }

pmc1002PowerTrapUrgentGoesOff NOTIFICATION-TYPE
	OBJECTS {pmc1002AlmDefFuseB, pmc1002AlmDefFuseA , pmc1002trapBoardNumber}
	STATUS current
	--&FILTNAME    "PM C1002 Fuse A&B Fail OFF"
	--&ACTIONS     { log, normal}
	--&CLEARS      { "PM C1002 Fuse A Fail ON", "PM C1002 Fuse B Fail ON" }
	--&MATCH       { pmc1002AlmDefFuseB "on", pmc1002AlmDefFuseA "on", pmc1002trapBoardNumber "$3"}
	--&MESG        "Power Inputs A and B Present on PM C1002 in Slot $3 ($A)"

	DESCRIPTION "Urgent power supply default disappeared"
	::= { pmc1002traps 51 }






END
