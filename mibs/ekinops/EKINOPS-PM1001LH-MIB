-- *****************************************************************
-- EKINOPS-pm1001lh.TXT:  MIB
--
--MIB Part Number:3MI00004ANAF
--MIB Version:02
--
-- Copyright (c) 2016 by Ekinops
-- All rights reserved.
--
-- *****************************************************************

EKINOPS-PM1001LH-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

modulepm1001lh MODULE-IDENTITY
        LAST-UPDATED "201606020000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.net"
        DESCRIPTION
          "MIB for managing Ekinops modules with PM1001LH software"
	REVISION "200610170000Z"
	DESCRIPTION
	  "Initial Version."
	REVISION "200702210000Z"
	DESCRIPTION
	  "Adding module init fail alarms"
	REVISION "200705290000Z"
	DESCRIPTION
	  "Replace EkiLineProtocol by EkiProtocol"
	REVISION "200706290000Z"
	DESCRIPTION
	  "Add DCC alarms"
	REVISION "200712030000Z"
	DESCRIPTION
	  "Update Ekinops Address,Helps on objects, Ports Labels"
	REVISION "200804210000Z"
	DESCRIPTION
	  "OTX-TLH feature"
	REVISION "200810270000Z"
	DESCRIPTION
	  "New RMON counters"
	REVISION "200811250000Z"
	DESCRIPTION
	  "DCC Storms suppress"
	REVISION "200812010000Z"
	DESCRIPTION
	  "Add Port Option on Client"
	REVISION "200812040000Z"
	DESCRIPTION
	  "Cosmetics for mib compilers"
	REVISION "200904090000Z"
	DESCRIPTION
	  "Add DCC ans MAINTENANCE control"
	REVISION "200905150000Z"
	DESCRIPTION
	  "CondType parameters insertion"
	REVISION "200912170000Z"
	DESCRIPTION
	  "Add CDR_Not_Ready for OTX-VLH"
	REVISION "201001280000Z"
	DESCRIPTION
	  "XFP-T parameter"
	REVISION "201002230000Z"
	DESCRIPTION
	  "Probcause,AlarmType - NMS"
	REVISION "201002230000Z"
	DESCRIPTION
	  "Probcause,AlarmType - NMS"
	REVISION "201003080000Z"
	DESCRIPTION
	  "FEC Fail insertion"
	REVISION "201003080000Z"
	DESCRIPTION
	  "OTX-VLH Reset"
	REVISION "201006010000Z"
	DESCRIPTION
	  "Perf Enable Insertion"
	REVISION "201007050000Z"
	DESCRIPTION
	  "Loss Of Frame help inserted"
	REVISION "201008310000Z"
	DESCRIPTION
	  "Line OOF current instead of deprecated"
	REVISION "201011080000Z"
	DESCRIPTION
	  "Formulas in comments and Event on XFP init"
	REVISION "201101070000Z"
	DESCRIPTION
	  "Insert object in config for WB mode"
	REVISION "201207030000Z"
	DESCRIPTION
	  "Minor cosmetic updates"
	REVISION "201304030000Z"
	DESCRIPTION
	  "S1,K1,K2 suppress"
	REVISION "201403250000Z"
	DESCRIPTION
	  "Probcause,AlarmType - NMS completion"
	REVISION "201501140000Z"
	DESCRIPTION
	  "Add Loopback objects"
	REVISION "201501140000Z"
	DESCRIPTION
	  "Labels cosmetic updates"
	REVISION "201605200000Z"
	DESCRIPTION
	  "New AlarmType – synthesisAlarm (12)"
	REVISION "201606020000Z"
	DESCRIPTION
	  "Capabilities objects of Table 5"
        ::= { ekinops 10 }



--- *****************************************************
---     LEAF LEVEL 2
--- *****************************************************


pm1001lhalarms OBJECT IDENTIFIER ::= { modulepm1001lh 2 }
pm1001lhAlmOther OBJECT IDENTIFIER ::= { pm1001lhalarms 1 }
pm1001lhAlmOtherNurg OBJECT IDENTIFIER ::= { pm1001lhAlmOther 1 }
pm1001lhAlmOtherUrg OBJECT IDENTIFIER ::= { pm1001lhAlmOther 2 }
pm1001lhAlmOtherCrit OBJECT IDENTIFIER ::= { pm1001lhAlmOther 3 }

pm1001lhAlmClient OBJECT IDENTIFIER ::= { pm1001lhalarms 2 }
pm1001lhAlmClientNurg OBJECT IDENTIFIER ::= { pm1001lhAlmClient 1 }
pm1001lhAlmClientUrg OBJECT IDENTIFIER ::= { pm1001lhAlmClient 2 }
pm1001lhAlmClientCrit OBJECT IDENTIFIER ::= { pm1001lhAlmClient 3 }

pm1001lhAlmLine OBJECT IDENTIFIER ::= { pm1001lhalarms 3 }
pm1001lhAlmLineNurg OBJECT IDENTIFIER ::= { pm1001lhAlmLine 1 }
pm1001lhAlmLineUrg OBJECT IDENTIFIER ::= { pm1001lhAlmLine 2 }
pm1001lhAlmLineCrit OBJECT IDENTIFIER ::= { pm1001lhAlmLine 3 }





pm1001lhmeasures OBJECT IDENTIFIER ::= { modulepm1001lh 3 }
pm1001lhMesrOther OBJECT IDENTIFIER ::= { pm1001lhmeasures 1 }
pm1001lhMesrClient OBJECT IDENTIFIER ::= { pm1001lhmeasures 2 }
pm1001lhMesrLine OBJECT IDENTIFIER ::= { pm1001lhmeasures 3 }




pm1001lhcounters OBJECT IDENTIFIER ::= { modulepm1001lh 4 }
pm1001lhCntOther OBJECT IDENTIFIER ::= { pm1001lhcounters 1 }
pm1001lhCntClient OBJECT IDENTIFIER ::= { pm1001lhcounters 2 }
pm1001lhCntLine OBJECT IDENTIFIER ::= { pm1001lhcounters 3 }


pm1001lhcontrolsWrite OBJECT IDENTIFIER ::= { modulepm1001lh 6 }
pm1001lhCtrlOther OBJECT IDENTIFIER ::= { pm1001lhcontrolsWrite 1 }
pm1001lhCtrlClient OBJECT IDENTIFIER ::= { pm1001lhcontrolsWrite 2 }
pm1001lhCtrlLine OBJECT IDENTIFIER ::= { pm1001lhcontrolsWrite 3 }

pm1001lhri OBJECT IDENTIFIER ::= { modulepm1001lh 7 }
pm1001lhriTable OBJECT IDENTIFIER ::= { pm1001lhri 1 }

pm1001lhdownload OBJECT IDENTIFIER ::= { modulepm1001lh 8 }
pm1001lhDwlOther OBJECT IDENTIFIER ::= { pm1001lhdownload 1 }
pm1001lhDwlClient OBJECT IDENTIFIER ::= { pm1001lhdownload 2 }
pm1001lhDwlLine OBJECT IDENTIFIER ::= { pm1001lhdownload 3 }

pm1001lhConfig OBJECT IDENTIFIER ::= { modulepm1001lh 10 }

pm1001lhtraps OBJECT IDENTIFIER ::= { modulepm1001lh 11 }

pm1001lhMonitoring OBJECT IDENTIFIER ::= { modulepm1001lh 12}

pm1001lhMonOther OBJECT IDENTIFIER ::= { pm1001lhMonitoring 1 }
pm1001lhMonSync OBJECT IDENTIFIER ::= { pm1001lhMonOther 1 }
pm1001lhMonTimeStamp OBJECT IDENTIFIER ::= { pm1001lhMonOther 2 }

pm1001lhMonClient OBJECT IDENTIFIER ::= { pm1001lhMonitoring 2 }

pm1001lhMonLine OBJECT IDENTIFIER ::= { pm1001lhMonitoring 3 }

pm1001lhRmon OBJECT IDENTIFIER ::= { pm1001lhMonitoring 4 }

pm1001lhRmonClient OBJECT IDENTIFIER ::= { pm1001lhRmon 1 }
pm1001lhRmonLine OBJECT IDENTIFIER ::= { pm1001lhRmon 2 }
pm1001lhRmonOther OBJECT IDENTIFIER ::= { pm1001lhRmon 3 }

--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Pm1001lhOtxMode ::= TEXTUAL-CONVENTION
    STATUS      current
    DESCRIPTION "Different modes on OTX-TLH on client and line ports"
    SYNTAX INTEGER {
		otx80mode(1),
		otx60mode(2),
		otxadjustmode(4)
           }

Pm1001lhOtxGrid ::= TEXTUAL-CONVENTION
    STATUS      current
    DESCRIPTION "Different grids on OTX-TLH on client and line ports"
    SYNTAX INTEGER {
		otxgrid200(200),
		otxgrid100(100),
		otxgrid50(50)
           }

Pm1001lhAdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pm1001lhOtxChannel ::= TEXTUAL-CONVENTION
    STATUS      current
    DESCRIPTION "Channel selection on OTX-TLH on client and line ports"
    SYNTAX INTEGER


--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm1001lhRinvReloadInventory OBJECT-TYPE
  SYNTAX EkiOnOff
  MAX-ACCESS read-write
  STATUS current
  DESCRIPTION
        "Reload the inventory: This OID triggers an
         inventory reload."
  ::= { pm1001lhri 2 }

pm1001lhRinvHwPlatform OBJECT-TYPE
  SYNTAX DisplayString
  MAX-ACCESS read-only
  STATUS current
  DESCRIPTION
        "HW platform description: This OID contains the
         description of the Hardware platform."
  ::= { pm1001lhri 3 }

pm1001lhRinvModulePlatform OBJECT-TYPE
  SYNTAX DisplayString
  MAX-ACCESS read-only
  STATUS current
  DESCRIPTION
        "Module platform description: This OID contains the
         description of the Module."
  ::= { pm1001lhri 4 }

pm1001lhRinvSwPlatform OBJECT-TYPE
  SYNTAX DisplayString
  MAX-ACCESS read-only
  STATUS current
  DESCRIPTION
        "SW platform description: This OID contains the
         description of the Software platform."
  ::= { pm1001lhri 5 }

pm1001lhRinvGwPlatform OBJECT-TYPE
  SYNTAX DisplayString
  MAX-ACCESS read-only
  STATUS current
  DESCRIPTION
        "GW platform desciption: This OID contains the
         description of the Gateware platform."
  ::= { pm1001lhri 6 }


pm1001lhRinvClient OBJECT-TYPE
  SYNTAX DisplayString
  MAX-ACCESS read-only
  STATUS current
  DESCRIPTION
        "Inventory for the Client port: This OID contains
         the inventory for the Client port."
  ::= { pm1001lhri 7 }

pm1001lhRinvLine OBJECT-TYPE
  SYNTAX DisplayString
  MAX-ACCESS read-only
  STATUS current
  DESCRIPTION
        "Inventory for the Line: This OID contains
         the inventory for the Line."
  ::= { pm1001lhri 8 }






--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm1001lhAlmsynthAlm0 OBJECT IDENTIFIER ::= { pm1001lhAlmOtherCrit 0 }




pm1001lhAlmDefFuseB OBJECT-TYPE
	  SYNTAX EkiOnOff
	  MAX-ACCESS read-only
	  STATUS current
	  DESCRIPTION
        "
        Fuse B Fail :This OID indicates
        that the fuse of the power input
        B is in fail condition  <Help>
          Status of the Fuse B <Condtype>
        DEF_FUSE_B <Probcause> powerProblem
        (36) <Alarmtype> equipmentAlarm
        (5) <Polarity> (2)
        "
	  ::= { pm1001lhAlmsynthAlm0 16 }



pm1001lhAlmDefFuseA OBJECT-TYPE
	  SYNTAX EkiOnOff
	  MAX-ACCESS read-only
	  STATUS current
	  DESCRIPTION
        "
        Fuse A Fail :This OID indicates
        that the fuse of the power input
        A is in fail condition  <Help>
          Status of the Fuse A <Condtype>
        DEF_FUSE_A <Probcause> powerProblem
        (36) <Alarmtype> equipmentAlarm
        (5) <Polarity> (2)
        "
	  ::= { pm1001lhAlmsynthAlm0 15 }



pm1001lhAlmModGlobFail OBJECT-TYPE
	  SYNTAX EkiOnOff
	  MAX-ACCESS read-only
	  STATUS current
	  DESCRIPTION
        "
        Module Failure :This OID is set
        on detection of a failure originating
        from the PM <Condtype> MOD_GLOB_FAIL
        <Probcause> equipmentMalfunction
        (16) <Alarmtype> synthesisAlarm
        (12)  <Polarity> (2)
        "
	  ::= { pm1001lhAlmsynthAlm0 9 }



--- *****************************************************
---     LEAF for the synthAlm2 article
--- *****************************************************
pm1001lhAlmsynthAlm2 OBJECT IDENTIFIER ::= { pm1001lhAlmOtherNurg 2 }




pm1001lhAlmMaintenanceOn OBJECT-TYPE
	  SYNTAX EkiOnOff
	  MAX-ACCESS read-only
	  STATUS current
	  DESCRIPTION
        "
        Maintenance Mode :This OID indicates
        that the PM is in maintenance mode.
         <Help>  This alarm indicates that
        the maintenance mode is enabled
        on the PM <Condtype> MAINTENANCE_ON
        <Probcause> other (1) <Alarmtype>
        other (1) <Polarity> (2)
        "
	  ::= { pm1001lhAlmsynthAlm2 5 }



pm1001lhAlmCorrelatOff OBJECT-TYPE
	  SYNTAX EkiOnOff
	  MAX-ACCESS read-only
	  STATUS current
	  DESCRIPTION
        "
        Not Used :This OID, when set,
         indicates that alarm correlation
        is not being performed. <Condtype>
        CORRELAT_OFF <Probcause> other
         (1) <Alarmtype> other (1) <Polarity>
        (2)
        "
	  ::= { pm1001lhAlmsynthAlm2 4 }



pm1001lhAlmConfTableLoad OBJECT-TYPE
	  SYNTAX EkiOnOff
	  MAX-ACCESS read-only
	  STATUS current
	  DESCRIPTION
        "
        PM Configuration Load :This OID
         is at 1 during the loading of
         configuration tables in the modules
        RAM. <Condtype> CONF_TABLE_LOAD
        <Probcause> other (1) <Alarmtype>
        other (1) <Polarity> (2)
        "
	  ::= { pm1001lhAlmsynthAlm2 3 }



pm1001lhAlmInvUpload OBJECT-TYPE
	  SYNTAX EkiOnOff
	  MAX-ACCESS read-only
	  STATUS current
	  DESCRIPTION
        "
        Inventory Upload :This OID is
         at 1 during the uploading of PM
        inventory information. <Condtype>
        INV_UPLOAD <Probcause> other (1)
        <Alarmtype> other (1) <Polarity>
        (2)
        "
	  ::= { pm1001lhAlmsynthAlm2 2 }



pm1001lhAlmConfTableSave OBJECT-TYPE
	  SYNTAX EkiOnOff
	  MAX-ACCESS read-only
	  STATUS current
	  DESCRIPTION
        "
        PM Configuration Save :This OID
        is at 1 during the saving of a
         new configuration table in the
        module Flash memory. <Condtype>
        CONF_TABLE_SAVE <Probcause> other
        (1) <Alarmtype> other (1) <Polarity>
        (2)
        "
	  ::= { pm1001lhAlmsynthAlm2 1 }



--- *****************************************************
---     LEAF for the synthAlmLine article
--- *****************************************************
pm1001lhAlmsynthAlmLine OBJECT IDENTIFIER ::= { pm1001lhAlmLineCrit 7 }




pm1001lhAlmLineFail OBJECT-TYPE
	  SYNTAX EkiOnOff
	  MAX-ACCESS read-only
	  STATUS current
	  DESCRIPTION
        "
        Line Port Failure :This OID indicates
        a failure on the line port <Condtype>
        LINE_FAIL <Probcause> equipmentMalfunction
        (16) <Alarmtype> synthesisAlarm
        (12)  <Polarity> (2)
        "
	  ::= { pm1001lhAlmsynthAlmLine 12 }



pm1001lhAlmLineDdmAlm OBJECT-TYPE
	  SYNTAX EkiOnOff
	  MAX-ACCESS read-only
	  STATUS current
	  DESCRIPTION
        "
        Alarm On Line Optical Module DDM
        :This OID indicates an alarm is
        present coming out of Line optical
        interface DDM  <Help>  This alarm
        indicates if a DDM Alarm has been
        detected on the line transceiver
        <Condtype> LINE_DDM_ALM <Probcause>
        equipmentMalfunction (16) <Alarmtype>
        synthesisAlarm (12)  <Polarity>
        (2)
        "
	  ::= { pm1001lhAlmsynthAlmLine 10 }



pm1001lhAlmLineDdmWarning OBJECT-TYPE
	  SYNTAX EkiOnOff
	  MAX-ACCESS read-only
	  STATUS current
	  DESCRIPTION
        "
        Warning On Line Optical Module
        DDM :This OID indicates a warning
        is present coming out of Line optical
        interface DDM  <Help>  This alarm
        indicates if a DDM Warning has
         been detected on the line transceiver
        <Condtype> LINE_DDM_WARNING <Probcause>
        equipmentMalfunction (16) <Alarmtype>
        synthesisAlarm (12)  <Polarity>
        (2)
        "
	  ::= { pm1001lhAlmsynthAlmLine 9 }



pm1001lhAlmLineUpRdiIns OBJECT-TYPE
	  SYNTAX EkiOnOff
	  MAX-ACCESS read-only
	  STATUS current
	  DESCRIPTION
        "
        MS-RDI/L-RDI Inserted On Line
         :This OID indicates an upstream
        RDI has been inserted in the outgoing
        10 Gb/s signal.   <Help>  This
         status indicates if a MS-RDI/L-RDI
        is currently inserted on the line
        interface. <Condtype> LINE_UP_RDI_INS
        <Probcause> informationalStatus(1000)
        <Alarmtype> other (1) <Polarity>
        (2)
        "
	  ::= { pm1001lhAlmsynthAlmLine 8 }



pm1001lhAlmLineLocalOos OBJECT-TYPE
	  SYNTAX EkiOnOff
	  MAX-ACCESS read-only
	  STATUS current
	  DESCRIPTION
        "
        Line Port In Service :This OID
        indicates that the Line port is
        In Service (1) of Out or Service
        (2)  <Help>  This status indicates
        if the line port is in service
         <Condtype> LINE_LOCAL_OOS <Probcause>
        informationalStatus(1000) <Alarmtype>
        other (1) <Polarity> (2)
        "
	  ::= { pm1001lhAlmsynthAlmLine 6 }



pm1001lhAlmLineXfpTxOff OBJECT-TYPE
	  SYNTAX EkiOnOff
	  MAX-ACCESS read-only
	  STATUS current
	  DESCRIPTION
        "
        Line Optical Laser Shutdown :This
        OID indicates the line optical
         output power is on  <Help>  This
        status indicates if the line transceiver
        laser is ON or OFF <Condtype> LINE_XFP_TX_OFF
        <Probcause> other (1) <Alarmtype>
        equipmentAlarm (5) <Polarity> (2)
        "
	  ::= { pm1001lhAlmsynthAlmLine 5 }



pm1001lhAlmLineHwFail OBJECT-TYPE
	  SYNTAX EkiOnOff
	  MAX-ACCESS read-only
	  STATUS current
	  DESCRIPTION
        "
        Line Port HW Failure :This OID
        indicates a failure on line port,
        most probably caused by a HW issue
        <Condtype> LINE_HW_FAIL <Probcause>
        equipmentMalfunction (16) <Alarmtype>
        synthesisAlarm (12) ) <Polarity>
        (2)
        "
	  ::= { pm1001lhAlmsynthAlmLine 4 }



pm1001lhAlmLineXfpInitNotCompl OBJECT-TYPE
	  SYNTAX EkiOnOff
	  MAX-ACCESS read-only
	  STATUS current
	  DESCRIPTION
        "
        Line Optical Module Ready :This
        OID indicates that the line optical
        interface (XFP or OTX) is not operational.
         <Help>  This status indicates
         if the line transceiver has been
        correctly initialized <Condtype>
        LINE_XFP_INIT_NOT_COMPL <Probcause>
        equipmentMalfunction (16) <Alarmtype>
        equipmentAlarm (5) <Polarity> (2)
        <Event> ObjectCDINV
        "
	  ::= { pm1001lhAlmsynthAlmLine 2 }



pm1001lhAlmLineXfpAbsent OBJECT-TYPE
	  SYNTAX EkiOnOff
	  MAX-ACCESS read-only
	  STATUS current
	  DESCRIPTION
        "
        Line Optical Module Absent :This
        OID indicates that the line optical
        interface (XFP or OTX) is not plugged
        in.  <Help>  This alarm indicates
        if the line transceiver is present.
        <Condtype> LINE_XFP_ABSENT <Probcause>
        inputOutputDeviceError (24) <Alarmtype>
        equipmentAlarm (5) <Polarity> (2)
        <Event> ObjectCDINV
        "
	  ::= { pm1001lhAlmsynthAlmLine 1 }



--- *****************************************************
---     LEAF for the synthAlmPort article
--- *****************************************************
pm1001lhAlmsynthAlmPort OBJECT IDENTIFIER ::= { pm1001lhAlmClientCrit 8 }




pm1001lhAlmClientUpCsf OBJECT-TYPE
	  SYNTAX EkiOnOff
	  MAX-ACCESS read-only
	  STATUS current
	  DESCRIPTION
        "
        Client Signal Fail Inserted :This
        OID indicates a CSF has been inserted
        in the upstream client port.  <Help>
         This status indicates if a Client
        Signal Fail is currently inserted
        on the line signal for this client
        port <Condtype> CLIENT_UP_CSF <Probcause>
        other (1) <Alarmtype> other (1)
        <Polarity> (2)
        "
	  ::= { pm1001lhAlmsynthAlmPort 16 }



pm1001lhAlmClientFail OBJECT-TYPE
	  SYNTAX EkiOnOff
	  MAX-ACCESS read-only
	  STATUS current
	  DESCRIPTION
        "
        Client Access Fail :This OID indicates
        a failure on the Client port <Condtype>
        CLIENT_FAIL <Probcause> equipmentMalfunction
        (16) <Alarmtype> synthesisAlarm
        (12)  <Polarity> (2)
        "
	  ::= { pm1001lhAlmsynthAlmPort 12 }



pm1001lhAlmClientXfpDdmAlm OBJECT-TYPE
	  SYNTAX EkiOnOff
	  MAX-ACCESS read-only
	  STATUS current
	  DESCRIPTION
        "
        Alarm On Client XFP DDM :This
         OID indicates an alarm is being
        received from the Client XFP DDM
         <Help>  This alarm indicates if
        a DDM Alarm has been detected on
        the client transceiver <Condtype>
        CLIENT_XFP_DDM_ALM <Probcause>
         equipmentMalfunction (16) <Alarmtype>
        synthesisAlarm (12)  <Polarity>
        (2)
        "
	  ::= { pm1001lhAlmsynthAlmPort 10 }



pm1001lhAlmClientXfpDdmWarning OBJECT-TYPE
	  SYNTAX EkiOnOff
	  MAX-ACCESS read-only
	  STATUS current
	  DESCRIPTION
        "
        Warning On Client XFP DDM :This
        OID indicates a warning is being
        received from the Client XFP DDM
         <Help>  This alarm indicates if
        a DDM Warning has been detected
        on the client transceiver <Condtype>
        CLIENT_XFP_DDM_WARNING <Probcause>
        equipmentMalfunction (16) <Alarmtype>
        synthesisAlarm (12)  <Polarity>
        (2)
        "
	  ::= { pm1001lhAlmsynthAlmPort 9 }



pm1001lhAlmClientDwCais OBJECT-TYPE
	  SYNTAX EkiOnOff
	  MAX-ACCESS read-only
	  STATUS current
	  DESCRIPTION
        "
        Client AIS Inserted :This OID
         indicates a CAIS has been inserted
        on the output client port.  <Help>
         This status indicates if a Client
        Alarm Indication Signal is currently
        inserted on the client interface
        <Condtype> CLIENT_DW_CAIS <Probcause>
        informationalStatus(1000) <Alarmtype>
        other (1) <Polarity> (2)
        "
	  ::= { pm1001lhAlmsynthAlmPort 8 }



pm1001lhAlmClientLocalOos OBJECT-TYPE
	  SYNTAX EkiOnOff
	  MAX-ACCESS read-only
	  STATUS current
	  DESCRIPTION
        "
        Local Client Port In Service :This
        OID indicates that the local Client
        port is In Service (1) or Out of
        Service (2)  <Help>  This status
        indicates if the local client port
        is in service <Condtype> CLIENT_LOCAL_OOS
        <Probcause> informationalStatus(1000)
        <Alarmtype> other (1) <Polarity>
        (2)
        "
	  ::= { pm1001lhAlmsynthAlmPort 6 }



pm1001lhAlmClientDwLsd OBJECT-TYPE
	  SYNTAX EkiOnOff
	  MAX-ACCESS read-only
	  STATUS current
	  DESCRIPTION
        "
        Client Optical Laser Shutdown
         :This OID indicates the Client
        XFP transmitter output is ON.
          <Help>  This status indicates
        if the client transceiver laser
        is ON or OFF <Condtype> CLIENT_DW_LSD
        <Probcause> other (1) <Alarmtype>
        equipmentAlarm (5) <Polarity> (2)
        "
	  ::= { pm1001lhAlmsynthAlmPort 5 }



pm1001lhAlmClientHwFail OBJECT-TYPE
	  SYNTAX EkiOnOff
	  MAX-ACCESS read-only
	  STATUS current
	  DESCRIPTION
        "
        Client HW Fail :This OID indicates
        a failure on client port, most
         probably caused by a HW issue.
        <Condtype> CLIENT_HW_FAIL <Probcause>
        equipmentMalfunction (16) <Alarmtype>
        synthesisAlarm (12) ) <Polarity>
        (2)
        "
	  ::= { pm1001lhAlmsynthAlmPort 4 }



pm1001lhAlmClientDdmAbsent OBJECT-TYPE
	  SYNTAX EkiOnOff
	  MAX-ACCESS read-only
	  STATUS current
	  DESCRIPTION
        "
        Client Optical Module Ready :This
        OID indicates that the client optical
        interface (XFP or OTX) is not operational.
         <Help>  This status indicates
         if the client transceiver has
         been correctly initialized <Condtype>
        CLIENT_DDM_ABSENT <Probcause> equipmentMalfunction
        (16) <Alarmtype> equipmentAlarm
        (5) <Polarity> (2)
        "
	  ::= { pm1001lhAlmsynthAlmPort 2 }



pm1001lhAlmClientXfpAbsent OBJECT-TYPE
	  SYNTAX EkiOnOff
	  MAX-ACCESS read-only
	  STATUS current
	  DESCRIPTION
        "
        Client Optical Module Absent :This
        OID indicates that the XFP module
        is not present in the client port.
         <Help>  This alarm indicates if
        the client transceiver is present.
        <Condtype> CLIENT_XFP_ABSENT <Probcause>
        inputOutputDeviceError (24) <Alarmtype>
        equipmentAlarm (5) <Polarity> (2)
        <Event> ObjectCDINV
        "
	  ::= { pm1001lhAlmsynthAlmPort 1 }



--- *****************************************************
---     LEAF for the clientAccessioAlm article
--- *****************************************************
pm1001lhAlmclientAccessioAlm OBJECT IDENTIFIER ::= { pm1001lhAlmClientCrit 16 }




pm1001lhAlmClientUpLos OBJECT-TYPE
	  SYNTAX EkiOnOff
	  MAX-ACCESS read-only
	  STATUS current
	  DESCRIPTION
        "
        Client Input Loss Of Signal :This
        OID indicates that no signal is
        present on the XFP of the client
        port  <Help>  This alarm indicates
        if an optical signal is detected
        on the client transceiver input
        <Condtype> CLIENT_UP_LOS <Probcause>
        receiveFailure (41) <Alarmtype>
        physicalViolation (9) <Polarity>
        (2)
        "
	  ::= { pm1001lhAlmclientAccessioAlm 4 }



pm1001lhAlmClientDwLasFail OBJECT-TYPE
	  SYNTAX EkiOnOff
	  MAX-ACCESS read-only
	  STATUS current
	  DESCRIPTION
        "
        Client XFP Tx Failed :This OID
        indicates that the transmitter
         fails for the XFP plugged into
        the client port (this alarm reports
        the transmitter failure alarm generated
        by the XFPs) <Condtype> CLIENT_DW_LAS_FAIL
        <Probcause> transmitterFailure
         (56) <Alarmtype> equipmentAlarm
        (5) <Polarity> (2)
        "
	  ::= { pm1001lhAlmclientAccessioAlm 1 }



--- *****************************************************
---     LEAF for the clientXfpAlarm1 article
--- *****************************************************
pm1001lhAlmclientXfpAlarm1 OBJECT IDENTIFIER ::= { pm1001lhAlmClientUrg 32 }




pm1001lhAlmClientRxPowerHighAlarm OBJECT-TYPE
	  SYNTAX EkiOnOff
	  MAX-ACCESS read-only
	  STATUS current
	  DESCRIPTION
        "
        Client Optical Rx Power High :Alarm
        indicating that the XFP received
        optical power is higher than the
        threshold value written in the
         XFP EEPROM <Condtype> CLIENT_RX_POWER_HIGH_ALARM
        <Probcause> receiveFailure (41)
        <Alarmtype> equipmentAlarm (5)
         <Polarity> (2)
        "
	  ::= { pm1001lhAlmclientXfpAlarm1 16 }



pm1001lhAlmClientRxPowerLowAlarm OBJECT-TYPE
	  SYNTAX EkiOnOff
	  MAX-ACCESS read-only
	  STATUS current
	  DESCRIPTION
        "
        Client Optical Rx Power Low :Alarm
        indicating that the XFP received
        optical power is lower than the
        threshold value written in the
         XFP EEPROM  <Condtype> CLIENT_RX_POWER_LOW_ALARM
        <Probcause> receiveFailure (41)
        <Alarmtype> equipmentAlarm (5)
         <Polarity> (2)
        "
	  ::= { pm1001lhAlmclientXfpAlarm1 15 }



pm1001lhAlmClientTempHighAlarm OBJECT-TYPE
	  SYNTAX EkiOnOff
	  MAX-ACCESS read-only
	  STATUS current
	  DESCRIPTION
        "
        Client Transceiver Temp High :Alarm
        indicating that the XFP/OTX temperature
        is higher than the threshold value
        written in the XFP EEPROM <Condtype>
        CLIENT_TEMP_HIGH_ALARM <Probcause>
        temperatureUnacceptable (51) <Alarmtype>
        equipmentAlarm (5) <Polarity> (2)
        "
	  ::= { pm1001lhAlmclientXfpAlarm1 8 }



pm1001lhAlmClientTempLowAlarm OBJECT-TYPE
	  SYNTAX EkiOnOff
	  MAX-ACCESS read-only
	  STATUS current
	  DESCRIPTION
        "
        Client Transceiver Temp Low :Alarm
        indicating that the XFP/OTX temperature
        is lower than the threshold value
        written in the XFP/OTX EEPROM <Condtype>
        CLIENT_TEMP_LOW_ALARM <Probcause>
        temperatureUnacceptable (51) <Alarmtype>
        equipmentAlarm (5) <Polarity> (2)
        "
	  ::= { pm1001lhAlmclientXfpAlarm1 7 }



pm1001lhAlmClientTxBiasHighAlarm OBJECT-TYPE
	  SYNTAX EkiOnOff
	  MAX-ACCESS read-only
	  STATUS current
	  DESCRIPTION
        "
        Client Transceiver Bias High :Alarm
        indicating that the XFP/OTX transmitter
        laser bias current is higher than
        the threshold value written in
         the XFP EEPROM <Condtype> CLIENT_TX_BIAS_HIGH_ALARM
        <Probcause> transmitterFailure
         (56) <Alarmtype> equipmentAlarm
        (5) <Polarity> (2)
        "
	  ::= { pm1001lhAlmclientXfpAlarm1 4 }



pm1001lhAlmClientTxBiasLowAlarm OBJECT-TYPE
	  SYNTAX EkiOnOff
	  MAX-ACCESS read-only
	  STATUS current
	  DESCRIPTION
        "
        Client Transceiver Bias Low :Alarm
        indicating that the XFP/OTX transmitter
        laser bias current is lower than
        the threshold value written in
         the XFP/OTX EEPROM <Condtype>
         CLIENT_TX_BIAS_LOW_ALARM <Probcause>
        transmitterFailure (56) <Alarmtype>
        equipmentAlarm (5) <Polarity> (2)
        "
	  ::= { pm1001lhAlmclientXfpAlarm1 3 }



pm1001lhAlmClientTxPowerHighAlarm OBJECT-TYPE
	  SYNTAX EkiOnOff
	  MAX-ACCESS read-only
	  STATUS current
	  DESCRIPTION
        "
        Client Optical Tx Power High :Alarm
        indicating that the XFP/OTX transmitter
        transmitter output power is higher
        than the threshold value written
        in the XFP EEPROM <Condtype> CLIENT_TX_POWER_HIGH_ALARM
        <Probcause> transmitterFailure
         (56) <Alarmtype> equipmentAlarm
        (5) <Polarity> (2)
        "
	  ::= { pm1001lhAlmclientXfpAlarm1 2 }



pm1001lhAlmClientTxPowerLowAlarm OBJECT-TYPE
	  SYNTAX EkiOnOff
	  MAX-ACCESS read-only
	  STATUS current
	  DESCRIPTION
        "
        Client Optical Tx Power Low :Alarm
        indicating that the XFP/OTX transmitter
        transmitter output power is lower
        than the threshold value written
        in the XFP/OTX EEPROM <Condtype>
        CLIENT_TX_POWER_LOW_ALARM <Probcause>
        transmitterFailure (56) <Alarmtype>
        equipmentAlarm (5) <Polarity> (2)
        "
	  ::= { pm1001lhAlmclientXfpAlarm1 1 }



--- *****************************************************
---     LEAF for the clientXfpAlarm2 article
--- *****************************************************
pm1001lhAlmclientXfpAlarm2 OBJECT IDENTIFIER ::= { pm1001lhAlmClientCrit 40 }




pm1001lhAlmClientApdSupplyFault OBJECT-TYPE
	  SYNTAX EkiOnOff
	  MAX-ACCESS read-only
	  STATUS current
	  DESCRIPTION
        "
        Client Rx Photodiode Power Failed
        :This OID indicates a failure on
        the APD power supply  <Help>  This
        alarm indicates if the APD power
        supply is in fail condition <Condtype>
        CLIENT_APD_SUPPLY_FAULT <Probcause>
        receiverFailure (42) <Alarmtype>
        equipmentAlarm (5) <Polarity> (2)
        "
	  ::= { pm1001lhAlmclientXfpAlarm2 16 }



pm1001lhAlmClientTecFault OBJECT-TYPE
	  SYNTAX EkiOnOff
	  MAX-ACCESS read-only
	  STATUS current
	  DESCRIPTION
        "
        Client Optical Tx Temp Regul.
         Failed :This OID indicates a failure
        on the TEC module  <Help>  This
        alarm indicates if the TEC of the
        Client transceiver is in fail condition
        <Condtype> CLIENT_TEC_FAULT <Probcause>
        transmitterFailure (56) <Alarmtype>
        equipmentAlarm (5) <Polarity> (2)
        "
	  ::= { pm1001lhAlmclientXfpAlarm2 15 }



pm1001lhAlmClientWavelengthUnlocked OBJECT-TYPE
	  SYNTAX EkiOnOff
	  MAX-ACCESS read-only
	  STATUS current
	  DESCRIPTION
        "
        Client Optical Tx Wavelength Unlocked
        :This OID indicates that the wavelength
        error is exceeding the manufacturer
        tolerance  <Help>  This alarm indicates
        if the wavelenght of the Client
        transceiver is locked <Condtype>
        CLIENT_WAVELENGTH_UNLOCKED <Probcause>
        transmitterFailure (56) <Alarmtype>
        equipmentAlarm (5) <Polarity> (2)
        "
	  ::= { pm1001lhAlmclientXfpAlarm2 14 }



pm1001lhAlmClientTxNr OBJECT-TYPE
	  SYNTAX EkiOnOff
	  MAX-ACCESS read-only
	  STATUS current
	  DESCRIPTION
        "
        Client Optical Tx Not Ready :This
        OID indicates a condition has arisen
        leading to invalid data on the
         transmitting side  <Help>  This
        alarm indicates if the Tx part
         of the Client transceiver is ready
        <Condtype> CLIENT_TX_NR <Probcause>
        transmitterFailure (56) <Alarmtype>
        equipmentAlarm (5) <Polarity> (2)
        "
	  ::= { pm1001lhAlmclientXfpAlarm2 8 }



pm1001lhAlmClientTxFault OBJECT-TYPE
	  SYNTAX EkiOnOff
	  MAX-ACCESS read-only
	  STATUS current
	  DESCRIPTION
        "
        Client Optical Tx Failure :This
        OID indicates a fault condition
        on the laser detected by the safety
        syste  <Help>  This alarm indicates
        if the laser of the Client transceiver
        is in fail condition <Condtype>
        CLIENT_TX_FAULT <Probcause> transmitterFailure
        (56) <Alarmtype> equipmentAlarm
        (5) <Polarity> (2)
        "
	  ::= { pm1001lhAlmclientXfpAlarm2 7 }



pm1001lhAlmClientTxCdrNotLocked1 OBJECT-TYPE
	  SYNTAX EkiOnOff
	  MAX-ACCESS read-only
	  STATUS current
	  DESCRIPTION
        "
        Client Optical Tx CDR Unlocked
        :This OID indicates a loss of lock
        on the transmitting side CDR has
        been detected.  <Help>  This alarm
        indicates if the Tx CDR is locked
        in the Client transceiver <Condtype>
        CLIENT_TX_CDR_NOT_LOCKED1 <Probcause>
        transmitterFailure (56) <Alarmtype>
        equipmentAlarm (5) <Polarity> (2)
        "
	  ::= { pm1001lhAlmclientXfpAlarm2 6 }



pm1001lhAlmClientRxNr OBJECT-TYPE
	  SYNTAX EkiOnOff
	  MAX-ACCESS read-only
	  STATUS current
	  DESCRIPTION
        "
        Client Optical Rx Not Ready :This
        OID indicates that a condition
         has arisen leading to invalid
         data on the receiving side.  <Help>
         This alarm indicates if the Rx
        part of the Client transceiver
         is ready <Condtype> CLIENT_RX_NR
        <Probcause> receiveFailure (41)
        <Alarmtype> equipmentAlarm (5)
         <Polarity> (2)
        "
	  ::= { pm1001lhAlmclientXfpAlarm2 5 }



pm1001lhAlmClientRxCdrNotLocked1 OBJECT-TYPE
	  SYNTAX EkiOnOff
	  MAX-ACCESS read-only
	  STATUS current
	  DESCRIPTION
        "
        Client Optical Rx CDR Unlocked
        :This OID indicates that a loss
        of lock on the receiving side CDR
        has been detected  <Help>  This
        alarm indicates if the Rx CDR is
        locked in the Client transceiver
        <Condtype> CLIENT_RX_CDR_NOT_LOCKED1
        <Probcause> receiveFailure (41)
        <Alarmtype> equipmentAlarm (5)
         <Polarity> (2)
        "
	  ::= { pm1001lhAlmclientXfpAlarm2 3 }



pm1001lhAlmClientModNr OBJECT-TYPE
	  SYNTAX EkiOnOff
	  MAX-ACCESS read-only
	  STATUS current
	  DESCRIPTION
        "
        Client Optical Module Not Ready
        :This OID indicates that the module
        is unable to determine correct
         data.  <Help>  This alarm indicates
        if the Client transceiver is ready
        <Condtype> CLIENT_MOD_NR <Probcause>
        receiveFailure (41) <Alarmtype>
        equipmentAlarm (5) <Polarity> (2)
        "
	  ::= { pm1001lhAlmclientXfpAlarm2 2 }



--- *****************************************************
---     LEAF for the clientXfpWarnings article
--- *****************************************************
pm1001lhAlmclientXfpWarnings OBJECT IDENTIFIER ::= { pm1001lhAlmClientNurg 48 }




pm1001lhAlmClientRxPowerHighWarning OBJECT-TYPE
	  SYNTAX EkiOnOff
	  MAX-ACCESS read-only
	  STATUS current
	  DESCRIPTION
        "
        Client Optical Rx Pwr High Warning
        :Warning indicating that the XFP
        received optical power is higher
        than the threshold value written
        in the XFP EEPROM <Condtype> CLIENT_RX_POWER_HIGH_WARNING
        <Probcause> receiveFailure (41)
        <Alarmtype> equipmentAlarm (5)
         <Polarity> (2)
        "
	  ::= { pm1001lhAlmclientXfpWarnings 16 }



pm1001lhAlmClientRxPowerLowWarning OBJECT-TYPE
	  SYNTAX EkiOnOff
	  MAX-ACCESS read-only
	  STATUS current
	  DESCRIPTION
        "
        Client Optical Rx Pwr Low Warning
        :Warning indicating that the XFP
        received optical power is lower
        than the threshold value written
        in the XFP EEPROM  <Condtype> CLIENT_RX_POWER_LOW_WARNING
        <Probcause> receiveFailure (41)
        <Alarmtype> equipmentAlarm (5)
         <Polarity> (2)
        "
	  ::= { pm1001lhAlmclientXfpWarnings 15 }



pm1001lhAlmClientTempHighWarning OBJECT-TYPE
	  SYNTAX EkiOnOff
	  MAX-ACCESS read-only
	  STATUS current
	  DESCRIPTION
        "
        Client Transceiver Temp High Warning
        :Warning indicating that the XFP/OTX
        temperature is higher than the
         threshold value written in the
        XFP EEPROM <Condtype> CLIENT_TEMP_HIGH_WARNING
        <Probcause> temperatureUnacceptable
        (51) <Alarmtype> equipmentAlarm
        (5) <Polarity> (2)
        "
	  ::= { pm1001lhAlmclientXfpWarnings 8 }



pm1001lhAlmClientTempLowWarning OBJECT-TYPE
	  SYNTAX EkiOnOff
	  MAX-ACCESS read-only
	  STATUS current
	  DESCRIPTION
        "
        Client Transceiver Temp Low Warning
        :Warning indicating that the XFP/OTX
        temperature is lower than the threshold
        value written in the XFP/OTX EEPROM
        <Condtype> CLIENT_TEMP_LOW_WARNING
        <Probcause> temperatureUnacceptable
        (51) <Alarmtype> equipmentAlarm
        (5) <Polarity> (2)
        "
	  ::= { pm1001lhAlmclientXfpWarnings 7 }



pm1001lhAlmClientTxBiasHighWarning OBJECT-TYPE
	  SYNTAX EkiOnOff
	  MAX-ACCESS read-only
	  STATUS current
	  DESCRIPTION
        "
        Client Transceiver Bias High Warning
        :Warning indicating that the XFP/OTX
        transmitter laser bias current
         is higher than the threshold value
        written in the XFP EEPROM <Condtype>
        CLIENT_TX_BIAS_HIGH_WARNING <Probcause>
        transmitterFailure (56) <Alarmtype>
        equipmentAlarm (5) <Polarity> (2)
        "
	  ::= { pm1001lhAlmclientXfpWarnings 4 }



pm1001lhAlmClientTxBiasLowWarning OBJECT-TYPE
	  SYNTAX EkiOnOff
	  MAX-ACCESS read-only
	  STATUS current
	  DESCRIPTION
        "
        Client Transceiver Bias Low Warning
        :Warning indicating that the XFP/OTX
        transmitter laser bias current
         is lower than the threshold value
        written in the XFP/OTX EEPROM <Condtype>
        CLIENT_TX_BIAS_LOW_WARNING <Probcause>
        transmitterFailure (56) <Alarmtype>
        equipmentAlarm (5) <Polarity> (2)
        "
	  ::= { pm1001lhAlmclientXfpWarnings 3 }



pm1001lhAlmClientTxPowerHighWarning OBJECT-TYPE
	  SYNTAX EkiOnOff
	  MAX-ACCESS read-only
	  STATUS current
	  DESCRIPTION
        "
        Client Optical Tx Pwr High Warning
        :Warning indicating that the XFP/OTX
        transmitter transmitter output
         power is higher than the threshold
        value written in the XFP EEPROM
        <Condtype> CLIENT_TX_POWER_HIGH_WARNING
        <Probcause> transmitterFailure
         (56) <Alarmtype> equipmentAlarm
        (5) <Polarity> (2)
        "
	  ::= { pm1001lhAlmclientXfpWarnings 2 }



pm1001lhAlmClientTxPowerLowWarning OBJECT-TYPE
	  SYNTAX EkiOnOff
	  MAX-ACCESS read-only
	  STATUS current
	  DESCRIPTION
        "
        Client Optical Tx Pwr Low Warning
        :Warning indicating that the XFP/OTX
        transmitter transmitter output
         power is lower than the threshold
        value written in the XFP/OTX EEPROM
        <Condtype> CLIENT_TX_POWER_LOW_WARNING
        <Probcause> transmitterFailure
         (56) <Alarmtype> equipmentAlarm
        (5) <Polarity> (2)
        "
	  ::= { pm1001lhAlmclientXfpWarnings 1 }



--- *****************************************************
---     LEAF for the clientXfpSupplyAlarm article
--- *****************************************************
pm1001lhAlmclientXfpSupplyAlarm OBJECT IDENTIFIER ::= { pm1001lhAlmClientUrg 64 }




pm1001lhAlmClientVcc5HighWarning OBJECT-TYPE
	  SYNTAX EkiOnOff
	  MAX-ACCESS read-only
	  STATUS current
	  DESCRIPTION
        "
        VCC5 Power Supply High Warning
        :Warning indicating the XFP/OTX
        VCC5 power supply is higher than
        the threshold written in the EEPROM
        <Condtype> CLIENT_VCC5_HIGH_WARNING
        <Probcause> powerProblem (36) <Alarmtype>
        equipmentAlarm (5) <Polarity> (2)
        "
	  ::= { pm1001lhAlmclientXfpSupplyAlarm 16 }



pm1001lhAlmClientVcc5LowWarning OBJECT-TYPE
	  SYNTAX EkiOnOff
	  MAX-ACCESS read-only
	  STATUS current
	  DESCRIPTION
        "
        VCC5 Power Supply Low Warning
         :Warning indicating the XFP/OTX
        VCC5 power supply is lower than
        the threshold written in the EEPROM
        <Condtype> CLIENT_VCC5_LOW_WARNING
        <Probcause> powerProblem (36) <Alarmtype>
        equipmentAlarm (5) <Polarity> (2)
        "
	  ::= { pm1001lhAlmclientXfpSupplyAlarm 15 }



pm1001lhAlmClientVcc3HighWarning OBJECT-TYPE
	  SYNTAX EkiOnOff
	  MAX-ACCESS read-only
	  STATUS current
	  DESCRIPTION
        "
        VCC3 Power Supply High Warning
        :Warning indicating the XFP/OTX
        VCC3 power supply is higher than
        the threshold written in the EEPROM
        <Condtype> CLIENT_VCC3_HIGH_WARNING
        <Probcause> powerProblem (36) <Alarmtype>
        equipmentAlarm (5) <Polarity> (2)
        "
	  ::= { pm1001lhAlmclientXfpSupplyAlarm 14 }



pm1001lhAlmClientVcc3LowWarning OBJECT-TYPE
	  SYNTAX EkiOnOff
	  MAX-ACCESS read-only
	  STATUS current
	  DESCRIPTION
        "
        VCC3 Power Supply Low Warning
         :Warning indicating the XFP/OTX
        VCC3 power supply is lower than
        the threshold written in the EEPROM
        <Condtype> CLIENT_VCC3_LOW_WARNING
        <Probcause> powerProblem (36) <Alarmtype>
        equipmentAlarm (5) <Polarity> (2)
        "
	  ::= { pm1001lhAlmclientXfpSupplyAlarm 13 }



pm1001lhAlmClientVcc2HighWarning OBJECT-TYPE
	  SYNTAX EkiOnOff
	  MAX-ACCESS read-only
	  STATUS current
	  DESCRIPTION
        "
        VCC2 Power Supply High Warning
        :Warning indicating the XFP/OTX
        VCC2 power supply is higher than
        the threshold written in the EEPROM
        <Condtype> CLIENT_VCC2_HIGH_WARNING
        <Probcause> powerProblem (36) <Alarmtype>
        equipmentAlarm (5) <Polarity> (2)
        "
	  ::= { pm1001lhAlmclientXfpSupplyAlarm 12 }



pm1001lhAlmClientVcc2LowWarning OBJECT-TYPE
	  SYNTAX EkiOnOff
	  MAX-ACCESS read-only
	  STATUS current
	  DESCRIPTION
        "
        VCC2 Power Supply Low Warning
         :Warning indicating the XFP/OTX
        VCC2 power supply is lower than
        the threshold written in the EEPROM
        <Condtype> CLIENT_VCC2_LOW_WARNING
        <Probcause> powerProblem (36) <Alarmtype>
        equipmentAlarm (5) <Polarity> (2)
        "
	  ::= { pm1001lhAlmclientXfpSupplyAlarm 11 }



pm1001lhAlmClientVee5HighWarning OBJECT-TYPE
	  SYNTAX EkiOnOff
	  MAX-ACCESS read-only
	  STATUS current
	  DESCRIPTION
        "
        VEE5 Power Supply High Warning
        :Warning indicating the XFP/OTX
        VEE5 power supply is higher than
        the threshold written in the EEPROM
        <Condtype> CLIENT_VEE5_HIGH_WARNING
        <Probcause> powerProblem (36) <Alarmtype>
        equipmentAlarm (5) <Polarity> (2)
        "
	  ::= { pm1001lhAlmclientXfpSupplyAlarm 10 }



pm1001lhAlmClientVee5LowWarning OBJECT-TYPE
	  SYNTAX EkiOnOff
	  MAX-ACCESS read-only
	  STATUS current
	  DESCRIPTION
        "
        VEE5 Power Supply Low Warning
         :Warning indicating the XFP/OTX
        VEE5 power supply is lower than
        the threshold written in the EEPROM
        <Condtype> CLIENT_VEE5_LOW_WARNING
        <Probcause> powerProblem (36) <Alarmtype>
        equipmentAlarm (5) <Polarity> (2)
        "
	  ::= { pm1001lhAlmclientXfpSupplyAlarm 9 }



pm1001lhAlmClientVcc5HighAlarm OBJECT-TYPE
	  SYNTAX EkiOnOff
	  MAX-ACCESS read-only
	  STATUS current
	  DESCRIPTION
        "
        VCC5 Power Supply High :Alarm
         indicating the XFP/OTX VCC5 power
        supply is higher than the threshold
        written in the EEPROM <Condtype>
        CLIENT_VCC5_HIGH_ALARM <Probcause>
        powerProblem (36) <Alarmtype> equipmentAlarm
        (5) <Polarity> (2)
        "
	  ::= { pm1001lhAlmclientXfpSupplyAlarm 8 }



pm1001lhAlmClientVcc5LowAlarm OBJECT-TYPE
	  SYNTAX EkiOnOff
	  MAX-ACCESS read-only
	  STATUS current
	  DESCRIPTION
        "
        VCC5 Power Supply Low :Alarm indicating
        the XFP/OTX VCC5 power supply is
        lower than the threshold written
        in the EEPROM <Condtype> CLIENT_VCC5_LOW_ALARM
        <Probcause> powerProblem (36) <Alarmtype>
        equipmentAlarm (5) <Polarity> (2)
        "
	  ::= { pm1001lhAlmclientXfpSupplyAlarm 7 }



pm1001lhAlmClientVcc3HighAlarm OBJECT-TYPE
	  SYNTAX EkiOnOff
	  MAX-ACCESS read-only
	  STATUS current
	  DESCRIPTION
        "
        VCC3 Power Supply High :Alarm
         indicating the XFP/OTX VCC3 power
        supply is higher than the threshold
        written in the EEPROM <Condtype>
        CLIENT_VCC3_HIGH_ALARM <Probcause>
        powerProblem (36) <Alarmtype> equipmentAlarm
        (5) <Polarity> (2)
        "
	  ::= { pm1001lhAlmclientXfpSupplyAlarm 6 }



pm1001lhAlmClientVcc3LowAlarm OBJECT-TYPE
	  SYNTAX EkiOnOff
	  MAX-ACCESS read-only
	  STATUS current
	  DESCRIPTION
        "
        VCC3 Power Supply Low :Alarm indicating
        the XFP/OTX VCC3 power supply is
        lower than the threshold written
        in the EEPROM <Condtype> CLIENT_VCC3_LOW_ALARM
        <Probcause> powerProblem (36) <Alarmtype>
        equipmentAlarm (5) <Polarity> (2)
        "
	  ::= { pm1001lhAlmclientXfpSupplyAlarm 5 }



pm1001lhAlmClientVcc2HighAlarm OBJECT-TYPE
	  SYNTAX EkiOnOff
	  MAX-ACCESS read-only
	  STATUS current
	  DESCRIPTION
        "
        VCC2 Power Supply High :Alarm
         indicating the XFP/OTX VCC2 power
        supply is higher than the threshold
        written in the EEPROM <Condtype>
        CLIENT_VCC2_HIGH_ALARM <Probcause>
        powerProblem (36) <Alarmtype> equipmentAlarm
        (5) <Polarity> (2)
        "
	  ::= { pm1001lhAlmclientXfpSupplyAlarm 4 }



pm1001lhAlmClientVcc2LowAlarm OBJECT-TYPE
	  SYNTAX EkiOnOff
	  MAX-ACCESS read-only
	  STATUS current
	  DESCRIPTION
        "
        VCC2 Power Supply Low :Alarm indicating
        the XFP/OTX VCC2 power supply is
        lower than the threshold written
        in the EEPROM <Condtype> CLIENT_VCC2_LOW_ALARM
        <Probcause> powerProblem (36) <Alarmtype>
        equipmentAlarm (5) <Polarity> (2)
        "
	  ::= { pm1001lhAlmclientXfpSupplyAlarm 3 }



pm1001lhAlmClientVee5HighAlarm OBJECT-TYPE
	  SYNTAX EkiOnOff
	  MAX-ACCESS read-only
	  STATUS current
	  DESCRIPTION
        "
        VEE5 Power Supply High :Alarm
         indicating the XFP/OTX VEE5 power
        supply is higher than the threshold
        written in the EEPROM <Condtype>
        CLIENT_VEE5_HIGH_ALARM <Probcause>
        powerProblem (36) <Alarmtype> equipmentAlarm
        (5) <Polarity> (2)
        "
	  ::= { pm1001lhAlmclientXfpSupplyAlarm 2 }



pm1001lhAlmClientVee5LowAlarm OBJECT-TYPE
	  SYNTAX EkiOnOff
	  MAX-ACCESS read-only
	  STATUS current
	  DESCRIPTION
        "
        VEE5 Power Supply Low :Alarm indicating
        the XFP/OTX VEE5 power supply is
        lower than the threshold written
        in the EEPROM <Condtype> CLIENT_VEE5_LOW_ALARM
        <Probcause> powerProblem (36) <Alarmtype>
        equipmentAlarm (5) <Polarity> (2)
        "
	  ::= { pm1001lhAlmclientXfpSupplyAlarm 1 }



--- *****************************************************
---     LEAF for the clientMapperDeAlm article
--- *****************************************************
pm1001lhAlmclientMapperDeAlm OBJECT IDENTIFIER ::= { pm1001lhAlmClientCrit 72 }




pm1001lhAlmClientDwBufferOvl OBJECT-TYPE
	  SYNTAX EkiOnOff
	  MAX-ACCESS read-only
	  STATUS current
	  DESCRIPTION
        "
        Client Downstream Buffer Overload
        :This OID indicates that the de-mapper
        buffer for client port is in overload.
        <Condtype> CLIENT_DW_BUFFER_OVL
        <Probcause> equipmentMalfunction
        (16) <Alarmtype> equipmentAlarm
        (5) <Polarity> (2)
        "
	  ::= { pm1001lhAlmclientMapperDeAlm 14 }



pm1001lhAlmClientDwCsfDet OBJECT-TYPE
	  SYNTAX EkiOnOff
	  MAX-ACCESS read-only
	  STATUS current
	  DESCRIPTION
        "
        Client Signal Fail Detected :This
        OID indicates that a CSF has been
        detected on client port in the
         downstream direction   <Help>
          This alarm indicates if a Client
        Signal Fail has been detected in
        the incoming line frame for this
        client port <Condtype> CLIENT_DW_CSF_DET
        <Probcause> receiveFailure (41)
        <Alarmtype> other (1) <Polarity>
        (2)
        "
	  ::= { pm1001lhAlmclientMapperDeAlm 11 }



pm1001lhAlmClientUpBufferOvl OBJECT-TYPE
	  SYNTAX EkiOnOff
	  MAX-ACCESS read-only
	  STATUS current
	  DESCRIPTION
        "
        Client Upstream Buffer Overload
        :This OID indicates that the rate
        adaptation buffer for client port
        is in overload. <Condtype> CLIENT_UP_BUFFER_OVL
        <Probcause> receiveFailure (41)
        <Alarmtype> integrityViolation
         (7) <Polarity> (2)
        "
	  ::= { pm1001lhAlmclientMapperDeAlm 10 }



pm1001lhAlmClientUpAccOos OBJECT-TYPE
	  SYNTAX EkiOnOff
	  MAX-ACCESS read-only
	  STATUS current
	  DESCRIPTION
        "
        Client Loss Of Synchronisation
        :This OID indicates the upstream
        client input port is in Loss of
        Synchronization  <Help>  This alarms
        indicates if the input client signal
        is correctly synchronized with
         the decoder <Condtype> CLIENT_UP_ACC_OOS
        <Probcause> receiveFailure (41)
        <Alarmtype> integrityViolation
         (7) <Polarity> (2)
        "
	  ::= { pm1001lhAlmclientMapperDeAlm 1 }



--- *****************************************************
---     LEAF for the dfrmAlm article
--- *****************************************************
pm1001lhAlmdfrmAlm OBJECT IDENTIFIER ::= { pm1001lhAlmLineCrit 128 }




pm1001lhAlmLineFecFail OBJECT-TYPE
	  SYNTAX EkiOnOff
	  MAX-ACCESS read-only
	  STATUS current
	  DESCRIPTION
        "
        FEC Decoding Fail :This OID indicates
        that the FEC decoder is in an overcapacity
        mode and not able to correct errors
          <Help>  This alarm indicates
         if the FEC decoder is in an over
        capacity mode <Condtype> LINE_FEC_FAIL
        <Probcause> receiveFailure (41)
        <Alarmtype> qualityOfServiceAlarm
        (3) <Polarity> (2)
        "
	  ::= { pm1001lhAlmdfrmAlm 5 }



pm1001lhAlmLineDwLof OBJECT-TYPE
	  SYNTAX EkiOnOff
	  MAX-ACCESS read-only
	  STATUS current
	  DESCRIPTION
        "
        SONET/SDH Line Loss Of Frame :This
        OID indicates that a Loss Of Frame
        has been detected on line input
        signal  <Help>  This alarm indicates
        if there is a Loss of Frame is
         detected on the line input signal
        <Condtype> LINE_DW_LOF <Probcause>
        receiveFailure (41) <Alarmtype>
        integrityViolation (7) <Polarity>
        (2)
        "
	  ::= { pm1001lhAlmdfrmAlm 4 }



pm1001lhAlmLineDwOof OBJECT-TYPE
	  SYNTAX EkiOnOff
	  MAX-ACCESS read-only
	  STATUS current
	  DESCRIPTION
        "
        SONET/SDH Line Out Of Frame :This
        OID indicates that an Out Of Frame
        has been detected on line input
        signal  <Help>  This alarm indicates
        if a Loss Of Frame is detected
         on the line input signal <Condtype>
        LINE_DW_OOF <Probcause> receiveFailure
        (41) <Alarmtype> integrityViolation
        (7) <Polarity> (2)
        "
	  ::= { pm1001lhAlmdfrmAlm 3 }



pm1001lhAlmLineDwRdiDet OBJECT-TYPE
	  SYNTAX EkiOnOff
	  MAX-ACCESS read-only
	  STATUS current
	  DESCRIPTION
        "
        MS-RDI/L-RDI Detected On Line
         Input :This OID indicates that
        an MS-RDI has been detected on
         line input signal  <Help>  This
        alarm indicates if there is a MS-RDI/L-RDI
        is detected on the line input signal
        <Condtype> LINE_DW_RDI_DET <Probcause>
        remoteNodeTransmissionError (43)
        <Alarmtype> other (1) <Polarity>
        (2)
        "
	  ::= { pm1001lhAlmdfrmAlm 2 }



pm1001lhAlmLineDwAisDet OBJECT-TYPE
	  SYNTAX EkiOnOff
	  MAX-ACCESS read-only
	  STATUS current
	  DESCRIPTION
        "
        MS-AIS/L-AIS Detected On Line
         Input :This OID indicates that
        an MS-AIS has been detected on
         line input signal  <Help>  This
        alarm indicates if there is a MS-AIS/L-AIS
        is detected on the line input signal
        <Condtype> LINE_DW_AIS_DET <Probcause>
        receiveFailure (41) <Alarmtype>
        operationalViolation (8) <Polarity>
        (2)
        "
	  ::= { pm1001lhAlmdfrmAlm 1 }



--- *****************************************************
---     LEAF for the dfrmBer article
--- *****************************************************
pm1001lhAlmdfrmBer OBJECT IDENTIFIER ::= { pm1001lhAlmLineUrg 129 }




pm1001lhAlmLineDegrade OBJECT-TYPE
	  SYNTAX EkiOnOff
	  MAX-ACCESS read-only
	  STATUS current
	  DESCRIPTION
        "
        Fixed Line Signal Degrade :This
        OID indicates that the line input
        signal is DEGRADE. The assetion
        hysteresis is fixed to 10-8 (assertion)
        and 10-9 (de-assertion) <Condtype>
        LINE_DEGRADE <Probcause> degradedSignal
        (13) <Alarmtype> qualityOfServiceAlarm
        (3) <Polarity> (2)
        "
	  ::= { pm1001lhAlmdfrmBer 5 }



pm1001lhAlmLineSignalFail OBJECT-TYPE
	  SYNTAX EkiOnOff
	  MAX-ACCESS read-only
	  STATUS current
	  DESCRIPTION
        "
        Custom Line Signal Fail :This
         OID indicates that the line input
        signal is FAIL. The assertion hysteresis
        can be customized by the host <Condtype>
        LINE_SIGNAL_FAIL <Probcause> receiveFailure
        (41) <Alarmtype> integrityViolation
        (7) <Polarity> (2)
        "
	  ::= { pm1001lhAlmdfrmBer 2 }



pm1001lhAlmLineSignalDegrade OBJECT-TYPE
	  SYNTAX EkiOnOff
	  MAX-ACCESS read-only
	  STATUS current
	  DESCRIPTION
        "
        Custom Line Signal Degrade :This
        OID indicates that the line input
        signal is DEGRADE. The assertion
        hysteresis can customized by the
        host <Condtype> LINE_SIGNAL_DEGRADE
        <Probcause> degradedSignal (13)
        <Alarmtype> qualityOfServiceAlarm
        (3) <Polarity> (2)
        "
	  ::= { pm1001lhAlmdfrmBer 1 }



--- *****************************************************
---     LEAF for the lineSyncAlarms article
--- *****************************************************
pm1001lhAlmlineSyncAlarms OBJECT IDENTIFIER ::= { pm1001lhAlmLineCrit 133 }




pm1001lhAlmLineDwLos OBJECT-TYPE
	  SYNTAX EkiOnOff
	  MAX-ACCESS read-only
	  STATUS current
	  DESCRIPTION
        "
        Line Input Loss Of Signal :This
        OID indicates a loss of signal
         on the 10 Gb/s input.  <Help>
          This alarm indicates if an optical
        signal is detected on the line
         transceiver input <Condtype> LINE_DW_LOS
        <Probcause> receiveFailure (41)
        <Alarmtype> physicalViolation (9)
        <Polarity> (2)
        "
	  ::= { pm1001lhAlmlineSyncAlarms 16 }



pm1001lhAlmLineUpLockerr OBJECT-TYPE
	  SYNTAX EkiOnOff
	  MAX-ACCESS read-only
	  STATUS current
	  DESCRIPTION
        "
        Upstream Clock Lock Error :This
        OID indicates that the serializer
        output 10 Gb/s clock multiplier
        unit is not locked. <Condtype>
         LINE_UP_LOCKERR <Probcause> receiveFailure
        (41) <Alarmtype> equipmentAlarm
        (5) <Polarity> (2)
        "
	  ::= { pm1001lhAlmlineSyncAlarms 13 }



pm1001lhAlmLineDwLockerr OBJECT-TYPE
	  SYNTAX EkiOnOff
	  MAX-ACCESS read-only
	  STATUS current
	  DESCRIPTION
        "
        Downstream Clock Lock Error :This
        OID indicates that the deserializer
        input 10 Gb/s clock recovery is
        not locked. <Condtype> LINE_DW_LOCKERR
        <Probcause> receiveFailure (41)
        <Alarmtype> equipmentAlarm (5)
         <Polarity> (2)
        "
	  ::= { pm1001lhAlmlineSyncAlarms 12 }



--- *****************************************************
---     LEAF for the modInitFailLevel2 article
--- *****************************************************
pm1001lhAlmmodInitFailLevel2 OBJECT IDENTIFIER ::= { pm1001lhAlmOtherUrg 194 }




pm1001lhAlmSwInitFail OBJECT-TYPE
	  SYNTAX EkiOnOff
	  MAX-ACCESS read-only
	  STATUS current
	  DESCRIPTION
        "
        SW Init Fail :This OID indicates
        that the SW intialization has caused
        unknown intial conditions  <Help>
         This alarm indicates if the SW
        module is correctly initialized
        <Condtype> SW_INIT_FAIL <Probcause>
        softwareError (47) <Alarmtype>
         processingErrorAlarm (4) <Polarity>
        (2)
        "
	  ::= { pm1001lhAlmmodInitFailLevel2 5 }



pm1001lhAlmResetHwInitFail OBJECT-TYPE
	  SYNTAX EkiOnOff
	  MAX-ACCESS read-only
	  STATUS current
	  DESCRIPTION
        "
        Reset HW Init Fail :This OID indicates
        that the HW intialization has caused
        unknown intial conditions  <Help>
         This alarm indicates if the HW
        has been correctly initialized
         <Condtype> RESET_HW_INIT_FAIL
         <Probcause> softwareError (47)
        <Alarmtype> processingErrorAlarm
        (4) <Polarity> (2)
        "
	  ::= { pm1001lhAlmmodInitFailLevel2 4 }



pm1001lhAlmBootUndone OBJECT-TYPE
	  SYNTAX EkiOnOff
	  MAX-ACCESS read-only
	  STATUS current
	  DESCRIPTION
        "
        Boot Undone :This OID indicates
        that the boot has not been correctly
        achieved  <Help>  This alarm indicates
        if the module has correctly boot
        <Condtype> BOOT_UNDONE <Probcause>
        softwareError (47) <Alarmtype>
         processingErrorAlarm (4) <Polarity>
        (2)
        "
	  ::= { pm1001lhAlmmodInitFailLevel2 3 }



pm1001lhAlmNextColdBootForced OBJECT-TYPE
	  SYNTAX EkiOnOff
	  MAX-ACCESS read-only
	  STATUS current
	  DESCRIPTION
        "
        Next Cold Boot Forced :This OID
        indicates that the next Reset will
        be forced Cold  <Help>  This alarm
        indicates that the next reset of
        the module will be forced to cold
        reset <Condtype> NEXT_COLD_BOOT_FORCED
        <Probcause> informationalStatus(1000)
        <Alarmtype> other (1) <Polarity>
        (2)
        "
	  ::= { pm1001lhAlmmodInitFailLevel2 2 }



pm1001lhAlmLedFail OBJECT-TYPE
	  SYNTAX EkiOnOff
	  MAX-ACCESS read-only
	  STATUS current
	  DESCRIPTION
        "
        Led Fail :This OID indicates that
        Led register has not been correctly
        initalized  <Help>  This alarm
         indicates if the module LEDs are
        correctly initialized <Condtype>
        LED_FAIL <Probcause> softwareError
        (47) <Alarmtype> processingErrorAlarm
        (4) <Polarity> (2)
        "
	  ::= { pm1001lhAlmmodInitFailLevel2 1 }



--- *****************************************************
---     LEAF for the modInitFailLevel3 article
--- *****************************************************
pm1001lhAlmmodInitFailLevel3 OBJECT IDENTIFIER ::= { pm1001lhAlmOtherUrg 195 }




pm1001lhAlmClient1InitFail OBJECT-TYPE
	  SYNTAX EkiOnOff
	  MAX-ACCESS read-only
	  STATUS current
	  DESCRIPTION
        "
        Client1 Init Fail :This OID indicates
        that Client 1 registers subset
         has not been correctly initialized
         <Help>  This alarm indicates if
        the client port is correctly initialized
        <Condtype> CLIENT1_INIT_FAIL <Probcause>
        softwareError (47) <Alarmtype>
         processingErrorAlarm (4) <Polarity>
        (2)
        "
	  ::= { pm1001lhAlmmodInitFailLevel3 9 }



pm1001lhAlmLine1InitFail OBJECT-TYPE
	  SYNTAX EkiOnOff
	  MAX-ACCESS read-only
	  STATUS current
	  DESCRIPTION
        "
        Line1 Init Fail :This OID indicates
        that the Line registersvsubset
         has not been correctly initialized
         <Help>  This alarm indicates if
        the line port is correctly initialized
        <Condtype> LINE1_INIT_FAIL <Probcause>
        softwareError (47) <Alarmtype>
         processingErrorAlarm (4) <Polarity>
        (2)
        "
	  ::= { pm1001lhAlmmodInitFailLevel3 7 }



pm1001lhAlmXfp2InitFail OBJECT-TYPE
	  SYNTAX EkiOnOff
	  MAX-ACCESS read-only
	  STATUS current
	  DESCRIPTION
        "
        XFP2 Init Fail :This OID indicates
        that the XFP has not been correctly
        initialized  <Help>  This alarm
        indicates if the line transceiver
        2 is correctly initialized <Condtype>
        XFP2_INIT_FAIL <Probcause> softwareError
        (47) <Alarmtype> processingErrorAlarm
        (4) <Polarity> (2)
        "
	  ::= { pm1001lhAlmmodInitFailLevel3 6 }



pm1001lhAlmXfp1InitFail OBJECT-TYPE
	  SYNTAX EkiOnOff
	  MAX-ACCESS read-only
	  STATUS current
	  DESCRIPTION
        "
        XFP1 Init Fail :This OID indicates
        that the XFP has not been correctly
        initialized  <Help>  This alarm
        indicates if the line transceiver
        1 is correctly initialized <Condtype>
        XFP1_INIT_FAIL <Probcause> softwareError
        (47) <Alarmtype> processingErrorAlarm
        (4) <Polarity> (2)
        "
	  ::= { pm1001lhAlmmodInitFailLevel3 5 }



pm1001lhAlmInitModuleFail OBJECT-TYPE
	  SYNTAX EkiOnOff
	  MAX-ACCESS read-only
	  STATUS current
	  DESCRIPTION
        "
        Init Module Fail :This OID indicates
        that the Module has not been correctly
        initialized  <Help>  This alarm
        indicates if the SW module is correctly
        initialized <Condtype> INIT_MODULE_FAIL
        <Probcause> softwareError (47)
         <Alarmtype> processingErrorAlarm
        (4) <Polarity> (2)
        "
	  ::= { pm1001lhAlmmodInitFailLevel3 3 }



pm1001lhAlmObmTypeReadFail OBJECT-TYPE
	  SYNTAX EkiOnOff
	  MAX-ACCESS read-only
	  STATUS current
	  DESCRIPTION
        "
        OBM Type Read Fail :This OID indicates
        that OBM type has not been recognized
         <Help>  This alarm indicates if
        the OBM board has been correctly
        identified <Condtype> OBM_TYPE_READ_FAIL
        <Probcause> softwareError (47)
         <Alarmtype> processingErrorAlarm
        (4) <Polarity> (2)
        "
	  ::= { pm1001lhAlmmodInitFailLevel3 2 }



pm1001lhAlmGwIdentFail OBJECT-TYPE
	  SYNTAX EkiOnOff
	  MAX-ACCESS read-only
	  STATUS current
	  DESCRIPTION
        "
        GW Ident Fail :This OID indicates
        that GW identification has not
         been read  <Help>  This alarm
         indicates if the GW has been correctly
        identified <Condtype> GW_IDENT_FAIL
        <Probcause> softwareError (47)
         <Alarmtype> processingErrorAlarm
        (4) <Polarity> (2)
        "
	  ::= { pm1001lhAlmmodInitFailLevel3 1 }



--- *****************************************************
---     LEAF for the lineXfpAlarm1 article
--- *****************************************************
pm1001lhAlmlineXfpAlarm1 OBJECT IDENTIFIER ::= { pm1001lhAlmLineUrg 208 }




pm1001lhAlmLineRxPowerHighAlarm OBJECT-TYPE
	  SYNTAX EkiOnOff
	  MAX-ACCESS read-only
	  STATUS current
	  DESCRIPTION
        "
        Line Optical Rx Power High Alarm
        :Alarm indicating that the XFP
         received optical power is higher
        than the threshold value written
        in the XFP EEPROM <Condtype> LINE_RX_POWER_HIGH_ALARM
        <Probcause> receiveFailure (41)
        <Alarmtype> equipmentAlarm (5)
         <Polarity> (2)
        "
	  ::= { pm1001lhAlmlineXfpAlarm1 16 }



pm1001lhAlmLineRxPowerLowAlarm OBJECT-TYPE
	  SYNTAX EkiOnOff
	  MAX-ACCESS read-only
	  STATUS current
	  DESCRIPTION
        "
        Line Optical Rx Power Low Alarm
        :Alarm indicating that the XFP
         received optical power is lower
        than the threshold value written
        in the XFP EEPROM  <Condtype> LINE_RX_POWER_LOW_ALARM
        <Probcause> receiveFailure (41)
        <Alarmtype> equipmentAlarm (5)
         <Polarity> (2)
        "
	  ::= { pm1001lhAlmlineXfpAlarm1 15 }



pm1001lhAlmLineTempHighAlarm OBJECT-TYPE
	  SYNTAX EkiOnOff
	  MAX-ACCESS read-only
	  STATUS current
	  DESCRIPTION
        "
        Line Transceiver Temp High Alarm
        :Alarm indicating that the XFP/OTX
        temperature is higher than the
         threshold value written in the
        XFP EEPROM <Condtype> LINE_TEMP_HIGH_ALARM
        <Probcause> temperatureUnacceptable
        (51) <Alarmtype> equipmentAlarm
        (5) <Polarity> (2)
        "
	  ::= { pm1001lhAlmlineXfpAlarm1 8 }



pm1001lhAlmLineTempLowAlarm OBJECT-TYPE
	  SYNTAX EkiOnOff
	  MAX-ACCESS read-only
	  STATUS current
	  DESCRIPTION
        "
        Line Transceiver Temp Low Alarm
        :Alarm indicating that the XFP/OTX
        temperature is lower than the threshold
        value written in the XFP/OTX EEPROM
        <Condtype> LINE_TEMP_LOW_ALARM
         <Probcause> temperatureUnacceptable
        (51) <Alarmtype> equipmentAlarm
        (5) <Polarity> (2)
        "
	  ::= { pm1001lhAlmlineXfpAlarm1 7 }



pm1001lhAlmLineTxBiasHighAlarm OBJECT-TYPE
	  SYNTAX EkiOnOff
	  MAX-ACCESS read-only
	  STATUS current
	  DESCRIPTION
        "
        Line Transceiver Bias High Alarm
        :Alarm indicating that the XFP/OTX
        transmitter laser bias current
         is higher than the threshold value
        written in the XFP EEPROM <Condtype>
        LINE_TX_BIAS_HIGH_ALARM <Probcause>
        transmitterFailure (56) <Alarmtype>
        equipmentAlarm (5) <Polarity> (2)
        "
	  ::= { pm1001lhAlmlineXfpAlarm1 4 }



pm1001lhAlmLineTxBiasLowAlarm OBJECT-TYPE
	  SYNTAX EkiOnOff
	  MAX-ACCESS read-only
	  STATUS current
	  DESCRIPTION
        "
        Line Transceiver Bias Low Alarm
        :Alarm indicating that the XFP/OTX
        transmitter laser bias current
         is lower than the threshold value
        written in the XFP/OTX EEPROM <Condtype>
        LINE_TX_BIAS_LOW_ALARM <Probcause>
        transmitterFailure (56) <Alarmtype>
        equipmentAlarm (5) <Polarity> (2)
        "
	  ::= { pm1001lhAlmlineXfpAlarm1 3 }



pm1001lhAlmLineTxPowerHighAlarm OBJECT-TYPE
	  SYNTAX EkiOnOff
	  MAX-ACCESS read-only
	  STATUS current
	  DESCRIPTION
        "
        Line Optical Tx Power High Alarm
        :Alarm indicating that the XFP/OTX
        transmitter transmitter output
         power is higher than the threshold
        value written in the XFP EEPROM
        <Condtype> LINE_TX_POWER_HIGH_ALARM
        <Probcause> transmitterFailure
         (56) <Alarmtype> equipmentAlarm
        (5) <Polarity> (2)
        "
	  ::= { pm1001lhAlmlineXfpAlarm1 2 }



pm1001lhAlmLineTxPowerLowAlarm OBJECT-TYPE
	  SYNTAX EkiOnOff
	  MAX-ACCESS read-only
	  STATUS current
	  DESCRIPTION
        "
        Line Optical Tx Power Low Alarm
        :Alarm indicating that the XFP/OTX
        transmitter transmitter output
         power is lower than the threshold
        value written in the XFP/OTX EEPROM
        <Condtype> LINE_TX_POWER_LOW_ALARM
        <Probcause> transmitterFailure
         (56) <Alarmtype> equipmentAlarm
        (5) <Polarity> (2)
        "
	  ::= { pm1001lhAlmlineXfpAlarm1 1 }



--- *****************************************************
---     LEAF for the lineXfpWarnings article
--- *****************************************************
pm1001lhAlmlineXfpWarnings OBJECT IDENTIFIER ::= { pm1001lhAlmLineNurg 209 }




pm1001lhAlmLineRxPowerHighWarning OBJECT-TYPE
	  SYNTAX EkiOnOff
	  MAX-ACCESS read-only
	  STATUS current
	  DESCRIPTION
        "
        Line Optical Rx Power High Warning
        :Warning indicating that the XFP
        received optical power is higher
        than the threshold value written
        in the XFP EEPROM <Condtype> LINE_RX_POWER_HIGH_WARNING
        <Probcause> receiveFailure (41)
        <Alarmtype> equipmentAlarm (5)
         <Polarity> (2)
        "
	  ::= { pm1001lhAlmlineXfpWarnings 16 }



pm1001lhAlmLineRxPowerLowWarning OBJECT-TYPE
	  SYNTAX EkiOnOff
	  MAX-ACCESS read-only
	  STATUS current
	  DESCRIPTION
        "
        Line Optical Rx Power Low Warning
        :Warning indicating that the XFP
        received optical power is lower
        than the threshold value written
        in the XFP EEPROM  <Condtype> LINE_RX_POWER_LOW_WARNING
        <Probcause> receiveFailure (41)
        <Alarmtype> equipmentAlarm (5)
         <Polarity> (2)
        "
	  ::= { pm1001lhAlmlineXfpWarnings 15 }



pm1001lhAlmLineTempHighWarning OBJECT-TYPE
	  SYNTAX EkiOnOff
	  MAX-ACCESS read-only
	  STATUS current
	  DESCRIPTION
        "
        Line Transceiver Temp High Warning
        :Warning indicating that the XFP/OTX
        temperature is higher than the
         threshold value written in the
        XFP EEPROM <Condtype> LINE_TEMP_HIGH_WARNING
        <Probcause> temperatureUnacceptable
        (51) <Alarmtype> equipmentAlarm
        (5) <Polarity> (2)
        "
	  ::= { pm1001lhAlmlineXfpWarnings 8 }



pm1001lhAlmLineTempLowWarning OBJECT-TYPE
	  SYNTAX EkiOnOff
	  MAX-ACCESS read-only
	  STATUS current
	  DESCRIPTION
        "
        Line Transceiver Temp Low Warning
        :Warning indicating that the XFP/OTX
        temperature is lower than the threshold
        value written in the XFP/OTX EEPROM
        <Condtype> LINE_TEMP_LOW_WARNING
        <Probcause> temperatureUnacceptable
        (51) <Alarmtype> equipmentAlarm
        (5) <Polarity> (2)
        "
	  ::= { pm1001lhAlmlineXfpWarnings 7 }



pm1001lhAlmLineTxBiasHighWarning OBJECT-TYPE
	  SYNTAX EkiOnOff
	  MAX-ACCESS read-only
	  STATUS current
	  DESCRIPTION
        "
        Line Transceiver Bias High Warning
        :Warning indicating that the XFP/OTX
        transmitter laser bias current
         is higher than the threshold value
        written in the XFP EEPROM <Condtype>
        LINE_TX_BIAS_HIGH_WARNING <Probcause>
        transmitterFailure (56) <Alarmtype>
        equipmentAlarm (5) <Polarity> (2)
        "
	  ::= { pm1001lhAlmlineXfpWarnings 4 }



pm1001lhAlmLineTxBiasLowWarning OBJECT-TYPE
	  SYNTAX EkiOnOff
	  MAX-ACCESS read-only
	  STATUS current
	  DESCRIPTION
        "
        Line Transceiver Bias Low Warning
        :Warning indicating that the XFP/OTX
        transmitter laser bias current
         is lower than the threshold value
        written in the XFP/OTX EEPROM <Condtype>
        LINE_TX_BIAS_LOW_WARNING <Probcause>
        transmitterFailure (56) <Alarmtype>
        equipmentAlarm (5) <Polarity> (2)
        "
	  ::= { pm1001lhAlmlineXfpWarnings 3 }



pm1001lhAlmLineTxPowerHighWarning OBJECT-TYPE
	  SYNTAX EkiOnOff
	  MAX-ACCESS read-only
	  STATUS current
	  DESCRIPTION
        "
        Line Optical Tx Power High Warning
        :Warning indicating that the XFP/OTX
        transmitter transmitter output
         power is higher than the threshold
        value written in the XFP EEPROM
        <Condtype> LINE_TX_POWER_HIGH_WARNING
        <Probcause> transmitterFailure
         (56) <Alarmtype> equipmentAlarm
        (5) <Polarity> (2)
        "
	  ::= { pm1001lhAlmlineXfpWarnings 2 }



pm1001lhAlmLineTxPowerLowWarning OBJECT-TYPE
	  SYNTAX EkiOnOff
	  MAX-ACCESS read-only
	  STATUS current
	  DESCRIPTION
        "
        Line Optical Tx Power Low Warning
        :Warning indicating that the XFP/OTX
        transmitter transmitter output
         power is lower than the threshold
        value written in the XFP/OTX EEPROM
        <Condtype> LINE_TX_POWER_LOW_WARNING
        <Probcause> transmitterFailure
         (56) <Alarmtype> equipmentAlarm
        (5) <Polarity> (2)
        "
	  ::= { pm1001lhAlmlineXfpWarnings 1 }



--- *****************************************************
---     LEAF for the lineXfpAlarms2 article
--- *****************************************************
pm1001lhAlmlineXfpAlarms2 OBJECT IDENTIFIER ::= { pm1001lhAlmLineCrit 211 }




pm1001lhAlmLineApdSupplyFault OBJECT-TYPE
	  SYNTAX EkiOnOff
	  MAX-ACCESS read-only
	  STATUS current
	  DESCRIPTION
        "
        Line Rx Photodiode Power Failed
        :This OID indicates a failure on
        the APD power supply  <Help>  This
        alarm indicates if the APD power
        supply is in fail condition <Condtype>
        LINE_APD_SUPPLY_FAULT <Probcause>
        receiverFailure (42) <Alarmtype>
        equipmentAlarm (5) <Polarity> (2)
        "
	  ::= { pm1001lhAlmlineXfpAlarms2 16 }



pm1001lhAlmLineTecFault OBJECT-TYPE
	  SYNTAX EkiOnOff
	  MAX-ACCESS read-only
	  STATUS current
	  DESCRIPTION
        "
        Line Optical Tx Temp Regul. Failed
        :This OID indicates a failure on
        the TEC module  <Help>  This alarm
        indicates if the TEC of the line
        transceiver is in fail condition
        <Condtype> LINE_TEC_FAULT <Probcause>
        transmitterFailure (56) <Alarmtype>
        equipmentAlarm (5) <Polarity> (2)
        "
	  ::= { pm1001lhAlmlineXfpAlarms2 15 }



pm1001lhAlmLineWavelengthUnlocked OBJECT-TYPE
	  SYNTAX EkiOnOff
	  MAX-ACCESS read-only
	  STATUS current
	  DESCRIPTION
        "
        Line Optical Tx Wavelength Unlock
        :This OID indicates that the wavelength
        error is exceeding the manufacturer
        tolerance  <Help>  This alarm indicates
        if the wavelenght of the line transceiver
        is locked <Condtype> LINE_WAVELENGTH_UNLOCKED
        <Probcause> transmitterFailure
         (56) <Alarmtype> equipmentAlarm
        (5) <Polarity> (2)
        "
	  ::= { pm1001lhAlmlineXfpAlarms2 14 }



pm1001lhAlmLineChannelNotAcquired OBJECT-TYPE
	  SYNTAX EkiOnOff
	  MAX-ACCESS read-only
	  STATUS current
	  DESCRIPTION
        "
        DWDM Channel Not Acquired :This
        OID indicates the transceiver didn't
        tune the DWDM Channel succesfully.
         <Help>  This status indicates
         the transceiver has not tuned
         the DWDM Channel succesfully.
         <Condtype> LINE_CHANNEL_NOT_ACQUIRED
        <Probcause> transmitterFailure
         (56) <Alarmtype> equipmentAlarm
        (5) <Polarity> (2)
        "
	  ::= { pm1001lhAlmlineXfpAlarms2 10 }



pm1001lhAlmLineTxNr OBJECT-TYPE
	  SYNTAX EkiOnOff
	  MAX-ACCESS read-only
	  STATUS current
	  DESCRIPTION
        "
        Line Optical Tx Not Ready :This
        OID indicates a condition has arisen
        leading to invalid data on the
         transmitting side  <Help>  This
        alarm indicates if the Tx part
         of the line transceiver is ready
        <Condtype> LINE_TX_NR <Probcause>
        transmitterFailure (56) <Alarmtype>
        equipmentAlarm (5) <Polarity> (2)
        "
	  ::= { pm1001lhAlmlineXfpAlarms2 8 }



pm1001lhAlmLineTxFault OBJECT-TYPE
	  SYNTAX EkiOnOff
	  MAX-ACCESS read-only
	  STATUS current
	  DESCRIPTION
        "
        Line Optical Tx Failure :This
         OID indicates a fault condition
        on the laser detected by the safety
        syste  <Help>  This alarm indicates
        if the laser of the line transceiver
        is in fail condition <Condtype>
        LINE_TX_FAULT <Probcause> transmitterFailure
        (56) <Alarmtype> equipmentAlarm
        (5) <Polarity> (2)
        "
	  ::= { pm1001lhAlmlineXfpAlarms2 7 }



pm1001lhAlmLineTxCdrNotLocked1 OBJECT-TYPE
	  SYNTAX EkiOnOff
	  MAX-ACCESS read-only
	  STATUS current
	  DESCRIPTION
        "
        Line Optical Tx CDR Unlocked :This
        OID indicates a loss of lock on
        the transmitting side CDR has been
        detected.  <Help>  This alarm indicates
        if the Tx CDR is locked in the
         line transceiver <Condtype> LINE_TX_CDR_NOT_LOCKED1
        <Probcause> transmitterFailure
         (56) <Alarmtype> equipmentAlarm
        (5) <Polarity> (2)
        "
	  ::= { pm1001lhAlmlineXfpAlarms2 6 }



pm1001lhAlmLineRxNr OBJECT-TYPE
	  SYNTAX EkiOnOff
	  MAX-ACCESS read-only
	  STATUS current
	  DESCRIPTION
        "
        Line Optical Rx Not Ready :This
        OID indicates that a condition
         has arisen leading to invalid
         data on the receiving side.  <Help>
         This alarm indicates if the Rx
        part of the line transceiver is
        ready <Condtype> LINE_RX_NR <Probcause>
        receiveFailure (41) <Alarmtype>
        equipmentAlarm (5) <Polarity> (2)
        "
	  ::= { pm1001lhAlmlineXfpAlarms2 5 }



pm1001lhAlmLineRxCdrNotLocked1 OBJECT-TYPE
	  SYNTAX EkiOnOff
	  MAX-ACCESS read-only
	  STATUS current
	  DESCRIPTION
        "
        Line Optical Rx CDR Unlocked :This
        OID indicates that a loss of lock
        on the receiving side CDR has been
        detected  <Help>  This alarm indicates
        if the Rx CDR is locked in the
         line transceiver <Condtype> LINE_RX_CDR_NOT_LOCKED1
        <Probcause> receiveFailure (41)
        <Alarmtype> equipmentAlarm (5)
         <Polarity> (2)
        "
	  ::= { pm1001lhAlmlineXfpAlarms2 3 }



pm1001lhAlmLineModNr OBJECT-TYPE
	  SYNTAX EkiOnOff
	  MAX-ACCESS read-only
	  STATUS current
	  DESCRIPTION
        "
        Line Optical Module Not Ready
         :This OID indicates that the module
        is unable to determine correct
         data.  <Help>  This alarm indicates
        if the line transceiver is ready
        <Condtype> LINE_MOD_NR <Probcause>
        receiveFailure (41) <Alarmtype>
        equipmentAlarm (5) <Polarity> (2)
        "
	  ::= { pm1001lhAlmlineXfpAlarms2 2 }



--- *****************************************************
---     LEAF for the lineXfpSupplyAlarm article
--- *****************************************************
pm1001lhAlmlineXfpSupplyAlarm OBJECT IDENTIFIER ::= { pm1001lhAlmLineUrg 212 }




pm1001lhAlmLineVcc5HighWarning OBJECT-TYPE
	  SYNTAX EkiOnOff
	  MAX-ACCESS read-only
	  STATUS current
	  DESCRIPTION
        "
        VCC5 Power Supply High Warning
        :Warning indicating the XFP/OTX
        VCC5 power supply is higher than
        the threshold written in the EEPROM
        <Condtype> LINE_VCC5_HIGH_WARNING
        <Probcause> powerProblem (36) <Alarmtype>
        equipmentAlarm (5) <Polarity> (2)
        "
	  ::= { pm1001lhAlmlineXfpSupplyAlarm 16 }



pm1001lhAlmLineVcc5LowWarning OBJECT-TYPE
	  SYNTAX EkiOnOff
	  MAX-ACCESS read-only
	  STATUS current
	  DESCRIPTION
        "
        VCC5 Power Supply Low Warning
         :Warning indicating the XFP/OTX
        VCC5 power supply is lower than
        the threshold written in the EEPROM
        <Condtype> LINE_VCC5_LOW_WARNING
        <Probcause> powerProblem (36) <Alarmtype>
        equipmentAlarm (5) <Polarity> (2)
        "
	  ::= { pm1001lhAlmlineXfpSupplyAlarm 15 }



pm1001lhAlmLineVcc3HighWarning OBJECT-TYPE
	  SYNTAX EkiOnOff
	  MAX-ACCESS read-only
	  STATUS current
	  DESCRIPTION
        "
        VCC3 Power Supply High Warning
        :Warning indicating the XFP/OTX
        VCC3 power supply is higher than
        the threshold written in the EEPROM
        <Condtype> LINE_VCC3_HIGH_WARNING
        <Probcause> powerProblem (36) <Alarmtype>
        equipmentAlarm (5) <Polarity> (2)
        "
	  ::= { pm1001lhAlmlineXfpSupplyAlarm 14 }



pm1001lhAlmLineVcc3LowWarning OBJECT-TYPE
	  SYNTAX EkiOnOff
	  MAX-ACCESS read-only
	  STATUS current
	  DESCRIPTION
        "
        VCC3 Power Supply Low Warning
         :Warning indicating the XFP/OTX
        VCC3 power supply is lower than
        the threshold written in the EEPROM
        <Condtype> LINE_VCC3_LOW_WARNING
        <Probcause> powerProblem (36) <Alarmtype>
        equipmentAlarm (5) <Polarity> (2)
        "
	  ::= { pm1001lhAlmlineXfpSupplyAlarm 13 }



pm1001lhAlmLineVcc2HighWarning OBJECT-TYPE
	  SYNTAX EkiOnOff
	  MAX-ACCESS read-only
	  STATUS current
	  DESCRIPTION
        "
        VCC2 Power Supply High Warning
        :Warning indicating the XFP/OTX
        VCC2 power supply is higher than
        the threshold written in the EEPROM
        <Condtype> LINE_VCC2_HIGH_WARNING
        <Probcause> powerProblem (36) <Alarmtype>
        equipmentAlarm (5) <Polarity> (2)
        "
	  ::= { pm1001lhAlmlineXfpSupplyAlarm 12 }



pm1001lhAlmLineVcc2LowWarning OBJECT-TYPE
	  SYNTAX EkiOnOff
	  MAX-ACCESS read-only
	  STATUS current
	  DESCRIPTION
        "
        VCC2 Power Supply Low Warning
         :Warning indicating the XFP/OTX
        VCC2 power supply is lower than
        the threshold written in the EEPROM
        <Condtype> LINE_VCC2_LOW_WARNING
        <Probcause> powerProblem (36) <Alarmtype>
        equipmentAlarm (5) <Polarity> (2)
        "
	  ::= { pm1001lhAlmlineXfpSupplyAlarm 11 }



pm1001lhAlmLineVee5HighWarning OBJECT-TYPE
	  SYNTAX EkiOnOff
	  MAX-ACCESS read-only
	  STATUS current
	  DESCRIPTION
        "
        VEE5 Power Supply High Warning
        :Warning indicating the XFP/OTX
        VEE5 power supply is higher than
        the threshold written in the EEPROM
        <Condtype> LINE_VEE5_HIGH_WARNING
        <Probcause> powerProblem (36) <Alarmtype>
        equipmentAlarm (5) <Polarity> (2)
        "
	  ::= { pm1001lhAlmlineXfpSupplyAlarm 10 }



pm1001lhAlmLineVee5LowLineWarning OBJECT-TYPE
	  SYNTAX EkiOnOff
	  MAX-ACCESS read-only
	  STATUS current
	  DESCRIPTION
        "
        VEE5 Power Supply Low Warning
         :Warning indicating the XFP/OTX
        VEE5 power supply is lower than
        the threshold written in the EEPROM
        <Condtype> LINE_VEE5_LOW_LINE_WARNING
        <Probcause> powerProblem (36) <Alarmtype>
        equipmentAlarm (5) <Polarity> (2)
        "
	  ::= { pm1001lhAlmlineXfpSupplyAlarm 9 }



pm1001lhAlmLineVcc5HighAlarm OBJECT-TYPE
	  SYNTAX EkiOnOff
	  MAX-ACCESS read-only
	  STATUS current
	  DESCRIPTION
        "
        VCC5 Power Supply High Alarm :Alarm
        indicating the XFP/OTX VCC5 power
        supply is higher than the threshold
        written in the EEPROM <Condtype>
        LINE_VCC5_HIGH_ALARM <Probcause>
        powerProblem (36) <Alarmtype> equipmentAlarm
        (5) <Polarity> (2)
        "
	  ::= { pm1001lhAlmlineXfpSupplyAlarm 8 }



pm1001lhAlmLineVcc5LowAlarm OBJECT-TYPE
	  SYNTAX EkiOnOff
	  MAX-ACCESS read-only
	  STATUS current
	  DESCRIPTION
        "
        VCC5 Power Supply Low Alarm :Alarm
        indicating the XFP/OTX VCC5 power
        supply is lower than the threshold
        written in the EEPROM <Condtype>
        LINE_VCC5_LOW_ALARM <Probcause>
        powerProblem (36) <Alarmtype> equipmentAlarm
        (5) <Polarity> (2)
        "
	  ::= { pm1001lhAlmlineXfpSupplyAlarm 7 }



pm1001lhAlmLineVcc3HighAlarm OBJECT-TYPE
	  SYNTAX EkiOnOff
	  MAX-ACCESS read-only
	  STATUS current
	  DESCRIPTION
        "
        VCC3 Power Supply High Alarm :Alarm
        indicating the XFP/OTX VCC3 power
        supply is higher than the threshold
        written in the EEPROM <Condtype>
        LINE_VCC3_HIGH_ALARM <Probcause>
        powerProblem (36) <Alarmtype> equipmentAlarm
        (5) <Polarity> (2)
        "
	  ::= { pm1001lhAlmlineXfpSupplyAlarm 6 }



pm1001lhAlmLineVcc3LowAlarm OBJECT-TYPE
	  SYNTAX EkiOnOff
	  MAX-ACCESS read-only
	  STATUS current
	  DESCRIPTION
        "
        VCC3 Power Supply Low Alarm :Alarm
        indicating the XFP/OTX VCC3 power
        supply is lower than the threshold
        written in the EEPROM <Condtype>
        LINE_VCC3_LOW_ALARM <Probcause>
        powerProblem (36) <Alarmtype> equipmentAlarm
        (5) <Polarity> (2)
        "
	  ::= { pm1001lhAlmlineXfpSupplyAlarm 5 }



pm1001lhAlmLineVcc2HighAlarm OBJECT-TYPE
	  SYNTAX EkiOnOff
	  MAX-ACCESS read-only
	  STATUS current
	  DESCRIPTION
        "
        VCC2 Power Supply High Alarm :Alarm
        indicating the XFP/OTX VCC2 power
        supply is higher than the threshold
        written in the EEPROM <Condtype>
        LINE_VCC2_HIGH_ALARM <Probcause>
        powerProblem (36) <Alarmtype> equipmentAlarm
        (5) <Polarity> (2)
        "
	  ::= { pm1001lhAlmlineXfpSupplyAlarm 4 }



pm1001lhAlmLineVcc2LowAlarm OBJECT-TYPE
	  SYNTAX EkiOnOff
	  MAX-ACCESS read-only
	  STATUS current
	  DESCRIPTION
        "
        VCC2 Power Supply Low Alarm :Alarm
        indicating the XFP/OTX VCC2 power
        supply is lower than the threshold
        written in the EEPROM <Condtype>
        LINE_VCC2_LOW_ALARM <Probcause>
        powerProblem (36) <Alarmtype> equipmentAlarm
        (5) <Polarity> (2)
        "
	  ::= { pm1001lhAlmlineXfpSupplyAlarm 3 }



pm1001lhAlmLineVee5HighAlarm OBJECT-TYPE
	  SYNTAX EkiOnOff
	  MAX-ACCESS read-only
	  STATUS current
	  DESCRIPTION
        "
        VEE5 Power Supply High Alarm :Alarm
        indicating the XFP/OTX VEE5 power
        supply is higher than the threshold
        written in the EEPROM <Condtype>
        LINE_VEE5_HIGH_ALARM <Probcause>
        powerProblem (36) <Alarmtype> equipmentAlarm
        (5) <Polarity> (2)
        "
	  ::= { pm1001lhAlmlineXfpSupplyAlarm 2 }



pm1001lhAlmLineVee5LowAlarm OBJECT-TYPE
	  SYNTAX EkiOnOff
	  MAX-ACCESS read-only
	  STATUS current
	  DESCRIPTION
        "
        VEE5 Power Supply Low Alarm :Alarm
        indicating the XFP/OTX VEE5 power
        supply is lower than the threshold
        written in the EEPROM <Condtype>
        LINE_VEE5_LOW_ALARM <Probcause>
        powerProblem (36) <Alarmtype> equipmentAlarm
        (5) <Polarity> (2)
        "
	  ::= { pm1001lhAlmlineXfpSupplyAlarm 1 }



--- *****************************************************
---     LEAF for the lineOtxTlhAlarms3 article
--- *****************************************************
pm1001lhAlmlineOtxTlhAlarms3 OBJECT IDENTIFIER ::= { pm1001lhAlmLineUrg 224 }




pm1001lhAlmLineLaserTempHighAla OBJECT-TYPE
	  SYNTAX EkiOnOff
	  MAX-ACCESS read-only
	  STATUS current
	  DESCRIPTION
        "
        Line Laser Temp. High Alarm :Alarm
        indicating the Line OTX TLH laser
        temperature is higher than the
         threshold written in the EEPROM
        <Condtype> LINE_LASER_TEMP_HIGH_ALA
        <Probcause> temperatureUnacceptable
        (51) <Alarmtype> equipmentAlarm
        (5) <Polarity> (2)
        "
	  ::= { pm1001lhAlmlineOtxTlhAlarms3 14 }



pm1001lhAlmLineFreqDevHighAla OBJECT-TYPE
	  SYNTAX EkiOnOff
	  MAX-ACCESS read-only
	  STATUS current
	  DESCRIPTION
        "
        Line Freq. Deviation High Alarm
        :Alarm indicating the Line OTX
         TLH frequency deviation is higher
        than the threshold written in the
        EEPROM <Condtype> LINE_FREQ_DEV_HIGH_ALA
        <Probcause> transmitterFailure
         (56) <Alarmtype> equipmentAlarm
        (5) <Polarity> (2)
        "
	  ::= { pm1001lhAlmlineOtxTlhAlarms3 12 }



pm1001lhAlmLineCdrNotReady  OBJECT-TYPE
	  SYNTAX EkiOnOff
	  MAX-ACCESS read-only
	  STATUS current
	  DESCRIPTION
        "
        CDR Not Ready :This OID indicates
        the Clock Data Recovery unit is
        not yet initialized  <Help>  This
        alarm indicates the Clock Data
         Recovery unit is not yet initialized.
        <Condtype> LINE_CDR_NOT_READY
         <Probcause> receiveFailure (41)
        <Alarmtype> equipmentAlarm (5)
         <Polarity> (2)
        "
	  ::= { pm1001lhAlmlineOtxTlhAlarms3 9 }



pm1001lhAlmLineAgingHighAla OBJECT-TYPE
	  SYNTAX EkiOnOff
	  MAX-ACCESS read-only
	  STATUS current
	  DESCRIPTION
        "
        Line OTX TLH Aging High Alarm
         :Alarm indicating the Line OTX
        TLH aging is higher than the threshold
        written in the EEPROM <Condtype>
        LINE_AGING_HIGH_ALA <Probcause>
        transmitterFailure (56) <Alarmtype>
        equipmentAlarm (5) <Polarity> (2)
        "
	  ::= { pm1001lhAlmlineOtxTlhAlarms3 6 }



pm1001lhAlmLineModulatorAgingHighAla OBJECT-TYPE
	  SYNTAX EkiOnOff
	  MAX-ACCESS read-only
	  STATUS current
	  DESCRIPTION
        "
        Line Modulator Aging High Alarm
        :Alarm indicating the Line OTX
         TLH modulator aging is higher
         than the threshold written in
         the EEPROM <Condtype> LINE_MODULATOR_AGING_HIGH_ALA
        <Probcause> transmitterFailure
         (56) <Alarmtype> equipmentAlarm
        (5) <Polarity> (2)
        "
	  ::= { pm1001lhAlmlineOtxTlhAlarms3 5 }



--- *****************************************************
---     LEAF for the lineOtxTlhWarnings article
--- *****************************************************
pm1001lhAlmlineOtxTlhWarnings OBJECT IDENTIFIER ::= { pm1001lhAlmLineNurg 225 }




pm1001lhAlmLineLaserTempHighWarning OBJECT-TYPE
	  SYNTAX EkiOnOff
	  MAX-ACCESS read-only
	  STATUS current
	  DESCRIPTION
        "
        Line Laser Temp. High Warning
         :Warning indicating the Line OTX
        TLH laser temperature is higher
        than the threshold written in the
        EEPROM <Condtype> LINE_LASER_TEMP_HIGH_WARNING
        <Probcause> temperatureUnacceptable
        (51) <Alarmtype> equipmentAlarm
        (5) <Polarity> (2)
        "
	  ::= { pm1001lhAlmlineOtxTlhWarnings 14 }



pm1001lhAlmLineFreqDevHighWarning OBJECT-TYPE
	  SYNTAX EkiOnOff
	  MAX-ACCESS read-only
	  STATUS current
	  DESCRIPTION
        "
        Line Freq. Deviation High Warning
        :Warning indicating the Line OTX
        TLH frequency deviation is higher
        than the threshold written in the
        EEPROM <Condtype> LINE_FREQ_DEV_HIGH_WARNING
        <Probcause> transmitterFailure
         (56) <Alarmtype> equipmentAlarm
        (5) <Polarity> (2)
        "
	  ::= { pm1001lhAlmlineOtxTlhWarnings 12 }



pm1001lhAlmLineAgingHighWarning OBJECT-TYPE
	  SYNTAX EkiOnOff
	  MAX-ACCESS read-only
	  STATUS current
	  DESCRIPTION
        "
        Line OTX TLH Aging High Warning
        :Warning indicating the Line OTX
        TLH aging is higher than the threshold
        written in the EEPROM <Condtype>
        LINE_AGING_HIGH_WARNING <Probcause>
        transmitterFailure (56) <Alarmtype>
        equipmentAlarm (5) <Polarity> (2)
        "
	  ::= { pm1001lhAlmlineOtxTlhWarnings 6 }



pm1001lhAlmLineModulatorAgingHighWarning OBJECT-TYPE
	  SYNTAX EkiOnOff
	  MAX-ACCESS read-only
	  STATUS current
	  DESCRIPTION
        "
        Line Modulator Aging High Warning
        :Warning indicating the Line OTX
        TLH modulator aging is higher than
        the threshold written in the EEPROM
        <Condtype> LINE_MODULATOR_AGING_HIGH_WARNING
        <Probcause> transmitterFailure
         (56) <Alarmtype> equipmentAlarm
        (5) <Polarity> (2)
        "
	  ::= { pm1001lhAlmlineOtxTlhWarnings 5 }








--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pm1001lhCtrlconfMgnt1 OBJECT IDENTIFIER ::= { pm1001lhCtrlOther 1 }




pm1001lhCtrlConf2Clear1 OBJECT-TYPE
	  SYNTAX EkiOnOff
	  MAX-ACCESS read-write
	  STATUS current
	  DESCRIPTION
        "
        Clear Configuration Tables :This
        OID clears the configuration tables
        from configuration2 in the flash.
         <Help>  This control restores
         the default configuration of the
        module
        "
	  ::= { pm1001lhCtrlconfMgnt1 14 }



pm1001lhCtrlConf2Flash1 OBJECT-TYPE
	  SYNTAX EkiOnOff
	  MAX-ACCESS read-write
	  STATUS current
	  DESCRIPTION
        "
        Write Configuration Tables :This
        OID saves the current configuration
        of the PM as configuration2 in
         the flash.  <Help>  This control
        saves the customer configuration
        on the module
        "
	  ::= { pm1001lhCtrlconfMgnt1 10 }



pm1001lhCtrlConf2Load1 OBJECT-TYPE
	  SYNTAX EkiOnOff
	  MAX-ACCESS read-write
	  STATUS current
	  DESCRIPTION
        "
        Load Configuration Tables Set
         Nb 2 :When set this OID enables
        loading from flash configuration2
        into the PM.
        "
	  ::= { pm1001lhCtrlconfMgnt1 2 }



pm1001lhCtrlConf1Load1 OBJECT-TYPE
	  SYNTAX EkiOnOff
	  MAX-ACCESS read-write
	  STATUS current
	  DESCRIPTION
        "
        Load Configuration Tables Set
         Nb 1 :When set this OID enables
        loading from flash configuration1
        into the PM.
        "
	  ::= { pm1001lhCtrlconfMgnt1 1 }



--- *****************************************************
---     LEAF for the synth4 article
--- *****************************************************
pm1001lhCtrlsynth4 OBJECT IDENTIFIER ::= { pm1001lhCtrlOther 4 }




pm1001lhCtrlCorrelatOff OBJECT-TYPE
	  SYNTAX EkiOnOff
	  MAX-ACCESS read-write
	  STATUS current
	  DESCRIPTION
        "
        Disable Alarm Correlation :This
        OID disables the alarm correlation
        in the PM.
        "
	  ::= { pm1001lhCtrlsynth4 2 }



pm1001lhCtrlCorrelatOn OBJECT-TYPE
	  SYNTAX EkiOnOff
	  MAX-ACCESS read-write
	  STATUS current
	  DESCRIPTION
        "
        Enable Alarm Correlation :This
        OID enables the alarm correlation
        in the PM.
        "
	  ::= { pm1001lhCtrlsynth4 1 }



--- *****************************************************
---     LEAF for the swMgnt article
--- *****************************************************
pm1001lhCtrlswMgnt OBJECT IDENTIFIER ::= { pm1001lhCtrlOther 5 }




pm1001lhCtrlLoadSwBank2 OBJECT-TYPE
	  SYNTAX EkiOnOff
	  MAX-ACCESS read-write
	  STATUS current
	  DESCRIPTION
        "
        Set Software Nb 2 As Active :This
        OID, when set, loads the SW from
        bank2 into the PM. It must be followed
        by a reset.  <Help>  This controls
        selects the second SW bank as the
        active bank for the next module
        reset
        "
	  ::= { pm1001lhCtrlswMgnt 6 }



pm1001lhCtrlLoadSwBank1 OBJECT-TYPE
	  SYNTAX EkiOnOff
	  MAX-ACCESS read-write
	  STATUS current
	  DESCRIPTION
        "
        Set Software Nb 1 As Active :This
        OID, when set, loads the SW from
        bank1 into the PM. It must be followed
        by a reset.  <Help>  This controls
        selects the first SW bank as the
        active bank for the next module
        reset
        "
	  ::= { pm1001lhCtrlswMgnt 5 }



pm1001lhCtrlWarmReset OBJECT-TYPE
	  SYNTAX EkiOnOff
	  MAX-ACCESS read-write
	  STATUS current
	  DESCRIPTION
        "
        PM Warm Reset :This OID, when
         set, causes a warm reset of the
        PM. This reset is not traffic affecting,
        and the configuration of PM remains
        unchanged.  <Help>  This control
        initiates a warm reset of the module.
        "
	  ::= { pm1001lhCtrlswMgnt 3 }



pm1001lhCtrlColdReset OBJECT-TYPE
	  SYNTAX EkiOnOff
	  MAX-ACCESS read-write
	  STATUS current
	  DESCRIPTION
        "
        PM Cold Reset :This OID, when
         set, causes a cold reset of the
        PM. This reset is traffic affecting,
        and the configuration of PM is
         reloaded on start-up.  <Help>
          This control initiates a cold
        reset of the module.
        "
	  ::= { pm1001lhCtrlswMgnt 2 }



--- *****************************************************
---     LEAF for the gwMgnt article
--- *****************************************************
pm1001lhCtrlgwMgnt OBJECT IDENTIFIER ::= { pm1001lhCtrlOther 6 }




pm1001lhCtrlLoadGwBank4 OBJECT-TYPE
	  SYNTAX EkiOnOff
	  MAX-ACCESS read-write
	  STATUS current
	  DESCRIPTION
        "
        Set Gateware Nb 4 As Active :This
        OID, when set, loads the GW from
        bank4 (Flash) into the PM. It is
        followed by an automatic gateware
        cold reset.
        "
	  ::= { pm1001lhCtrlgwMgnt 8 }



pm1001lhCtrlLoadGwBank3 OBJECT-TYPE
	  SYNTAX EkiOnOff
	  MAX-ACCESS read-write
	  STATUS current
	  DESCRIPTION
        "
        Set Gateware Nb 3 As Active :This
        OID, when set, loads the GW from
        bank3 (Flash) into the PM. It is
        followed by an automatic gateware
        cold reset.  <Help>  This controls
        initiates a cold reset of the module
        and select the third GW bank as
        the active bank
        "
	  ::= { pm1001lhCtrlgwMgnt 7 }



pm1001lhCtrlLoadGwBank2 OBJECT-TYPE
	  SYNTAX EkiOnOff
	  MAX-ACCESS read-write
	  STATUS current
	  DESCRIPTION
        "
        Set Gateware Nb 2 As Active :This
        OID, when set, loads the GW from
        bank2 (Flash) into the PM. It is
        followed by an automatic gateware
        cold reset.
        "
	  ::= { pm1001lhCtrlgwMgnt 6 }



pm1001lhCtrlLoadGwBank1 OBJECT-TYPE
	  SYNTAX EkiOnOff
	  MAX-ACCESS read-write
	  STATUS current
	  DESCRIPTION
        "
        Set Gateware Nb 1 As Active :This
        OID, when set, loads the GW from
        bank1 (Flash) into the PM. It is
        followed by an automatic gateware
        cold reset.  <Help>  This controls
        initiates a cold reset of the module
        and select the first GW bank as
        the active bank
        "
	  ::= { pm1001lhCtrlgwMgnt 5 }



pm1001lhCtrlCurrentGwReset OBJECT-TYPE
	  SYNTAX EkiOnOff
	  MAX-ACCESS read-write
	  STATUS current
	  DESCRIPTION
        "
        Active Gateware Reset :This OID,
        when set, resets the active gateware.
        It is traffic affecting.
        "
	  ::= { pm1001lhCtrlgwMgnt 1 }



--- *********************************************************
---     TABLE for the pm1001lhCtrlaccessLoop articles
--- *********************************************************

pm1001lhCtrlaccessLoopTable OBJECT-TYPE
	SYNTAX  SEQUENCE OF Pm1001lhCtrlaccessLoopEntry
	MAX-ACCESS not-accessible
	STATUS current
	DESCRIPTION
        "
        List of pm1001lhCtrlaccessLoop
        Article
        "
	::= { pm1001lhCtrlClient 16 }


pm1001lhCtrlaccessLoopEntry OBJECT-TYPE
	SYNTAX Pm1001lhCtrlaccessLoopEntry
	MAX-ACCESS not-accessible
	STATUS current
	DESCRIPTION
        "
        Row definition for the pm1001lhCtrlaccessLoop
        table
        "
	INDEX   { pm1001lhCtrlaccessLoopIndex }
	::= { pm1001lhCtrlaccessLoopTable 1 }


Pm1001lhCtrlaccessLoopEntry ::=
	SEQUENCE {
	pm1001lhCtrlaccessLoopIndex
		INTEGER,
	pm1001lhCtrlaccessLoopPortn
		EkiState
	}


pm1001lhCtrlaccessLoopIndex OBJECT-TYPE
	SYNTAX  INTEGER(0..128)
	MAX-ACCESS  read-only
	STATUS current
	DESCRIPTION
        "
        Index definition for the pm1001lhCtrlaccessLoop
        table
        "
	::= { pm1001lhCtrlaccessLoopEntry 1 }


pm1001lhCtrlaccessLoopPortn OBJECT-TYPE
	SYNTAX  EkiState
	MAX-ACCESS read-write
	STATUS current
	DESCRIPTION
        "
        Client Facility Loopback :This
        OID operates a Client Facility
         Loopback, looping client input
        signal on the client output port.
        The loop is located on the client
        transceiver  <Help> This maintenance
        parameter operates a Client Facility
        Loopback, looping client input
         signal on the client output port.
        The loop is located on the client
        transceiver
        "
	::= { pm1001lhCtrlaccessLoopEntry 2 }


--- *********************************************************
---     TABLE for the pm1001lhCtrlportOosMode articles
--- *********************************************************

pm1001lhCtrlportOosModeTable OBJECT-TYPE
	SYNTAX  SEQUENCE OF Pm1001lhCtrlportOosModeEntry
	MAX-ACCESS not-accessible
	STATUS current
	DESCRIPTION
        "
        List of pm1001lhCtrlportOosMode
        Article
        "
	::= { pm1001lhCtrlClient 18 }


pm1001lhCtrlportOosModeEntry OBJECT-TYPE
	SYNTAX Pm1001lhCtrlportOosModeEntry
	MAX-ACCESS not-accessible
	STATUS current
	DESCRIPTION
        "
        Row definition for the pm1001lhCtrlportOosMode
        table
        "
	INDEX   { pm1001lhCtrlportOosModeIndex }
	::= { pm1001lhCtrlportOosModeTable 1 }


Pm1001lhCtrlportOosModeEntry ::=
	SEQUENCE {
	pm1001lhCtrlportOosModeIndex
		INTEGER,
	pm1001lhCtrlportOosModePortn
		EkiState
	}


pm1001lhCtrlportOosModeIndex OBJECT-TYPE
	SYNTAX  INTEGER(0..128)
	MAX-ACCESS  read-only
	STATUS current
	DESCRIPTION
        "
        Index definition for the pm1001lhCtrlportOosMode
        table
        "
	::= { pm1001lhCtrlportOosModeEntry 1 }


pm1001lhCtrlportOosModePortn OBJECT-TYPE
	SYNTAX  EkiState
	MAX-ACCESS read-write
	STATUS current
	DESCRIPTION
        "
        Client Port Out Of Service :This
        OID sets the client port Out Of
        Service  <Help>  This controls
         defines the service state of the
        client port
        "
	::= { pm1001lhCtrlportOosModeEntry 2 }


--- *********************************************************
---     TABLE for the pm1001lhCtrlxfpOffCtrl articles
--- *********************************************************

pm1001lhCtrlxfpOffCtrlTable OBJECT-TYPE
	SYNTAX  SEQUENCE OF Pm1001lhCtrlxfpOffCtrlEntry
	MAX-ACCESS not-accessible
	STATUS current
	DESCRIPTION
        "
        List of pm1001lhCtrlxfpOffCtrl
        Article
        "
	::= { pm1001lhCtrlClient 20 }


pm1001lhCtrlxfpOffCtrlEntry OBJECT-TYPE
	SYNTAX Pm1001lhCtrlxfpOffCtrlEntry
	MAX-ACCESS not-accessible
	STATUS current
	DESCRIPTION
        "
        Row definition for the pm1001lhCtrlxfpOffCtrl
        table
        "
	INDEX   { pm1001lhCtrlxfpOffCtrlIndex }
	::= { pm1001lhCtrlxfpOffCtrlTable 1 }


Pm1001lhCtrlxfpOffCtrlEntry ::=
	SEQUENCE {
	pm1001lhCtrlxfpOffCtrlIndex
		INTEGER,
	pm1001lhCtrlxfpOffCtrlPortn
		EkiState
	}


pm1001lhCtrlxfpOffCtrlIndex OBJECT-TYPE
	SYNTAX  INTEGER(0..128)
	MAX-ACCESS  read-only
	STATUS current
	DESCRIPTION
        "
        Index definition for the pm1001lhCtrlxfpOffCtrl
        table
        "
	::= { pm1001lhCtrlxfpOffCtrlEntry 1 }


pm1001lhCtrlxfpOffCtrlPortn OBJECT-TYPE
	SYNTAX  EkiState
	MAX-ACCESS read-write
	STATUS current
	DESCRIPTION
        "
        Client SFP Laser Shutdown :This
        OID switches off the XFP.  <Help>
         This control defines the laser
        state of the client transceiver
        "
	::= { pm1001lhCtrlxfpOffCtrlEntry 2 }


--- *********************************************************
---     TABLE for the pm1001lhCtrlcsfUpIns articles
--- *********************************************************

pm1001lhCtrlcsfUpInsTable OBJECT-TYPE
	SYNTAX  SEQUENCE OF Pm1001lhCtrlcsfUpInsEntry
	MAX-ACCESS not-accessible
	STATUS current
	DESCRIPTION
        "
        List of pm1001lhCtrlcsfUpIns Article
        "
	::= { pm1001lhCtrlClient 21 }


pm1001lhCtrlcsfUpInsEntry OBJECT-TYPE
	SYNTAX Pm1001lhCtrlcsfUpInsEntry
	MAX-ACCESS not-accessible
	STATUS current
	DESCRIPTION
        "
        Row definition for the pm1001lhCtrlcsfUpIns
        table
        "
	INDEX   { pm1001lhCtrlcsfUpInsIndex }
	::= { pm1001lhCtrlcsfUpInsTable 1 }


Pm1001lhCtrlcsfUpInsEntry ::=
	SEQUENCE {
	pm1001lhCtrlcsfUpInsIndex
		INTEGER,
	pm1001lhCtrlcsfUpInsPortn
		EkiState
	}


pm1001lhCtrlcsfUpInsIndex OBJECT-TYPE
	SYNTAX  INTEGER(0..128)
	MAX-ACCESS  read-only
	STATUS current
	DESCRIPTION
        "
        Index definition for the pm1001lhCtrlcsfUpIns
        table
        "
	::= { pm1001lhCtrlcsfUpInsEntry 1 }


pm1001lhCtrlcsfUpInsPortn OBJECT-TYPE
	SYNTAX  EkiState
	MAX-ACCESS read-write
	STATUS current
	DESCRIPTION
        "
        Client Signal Fail Insertion :This
        OID, when set, inserts  a client
        signal fail in the upstream client
        Port.  <Help>  This control inserts
        a Client Signal Fail for the client
        port
        "
	::= { pm1001lhCtrlcsfUpInsEntry 2 }


--- *********************************************************
---     TABLE for the pm1001lhCtrlcaisDwIns articles
--- *********************************************************

pm1001lhCtrlcaisDwInsTable OBJECT-TYPE
	SYNTAX  SEQUENCE OF Pm1001lhCtrlcaisDwInsEntry
	MAX-ACCESS not-accessible
	STATUS current
	DESCRIPTION
        "
        List of pm1001lhCtrlcaisDwIns
         Article
        "
	::= { pm1001lhCtrlClient 22 }


pm1001lhCtrlcaisDwInsEntry OBJECT-TYPE
	SYNTAX Pm1001lhCtrlcaisDwInsEntry
	MAX-ACCESS not-accessible
	STATUS current
	DESCRIPTION
        "
        Row definition for the pm1001lhCtrlcaisDwIns
        table
        "
	INDEX   { pm1001lhCtrlcaisDwInsIndex }
	::= { pm1001lhCtrlcaisDwInsTable 1 }


Pm1001lhCtrlcaisDwInsEntry ::=
	SEQUENCE {
	pm1001lhCtrlcaisDwInsIndex
		INTEGER,
	pm1001lhCtrlcaisDwInsPortn
		EkiState
	}


pm1001lhCtrlcaisDwInsIndex OBJECT-TYPE
	SYNTAX  INTEGER(0..128)
	MAX-ACCESS  read-only
	STATUS current
	DESCRIPTION
        "
        Index definition for the pm1001lhCtrlcaisDwIns
        table
        "
	::= { pm1001lhCtrlcaisDwInsEntry 1 }


pm1001lhCtrlcaisDwInsPortn OBJECT-TYPE
	SYNTAX  EkiState
	MAX-ACCESS read-write
	STATUS current
	DESCRIPTION
        "
        Client AIS Insertion :This OID,
        when set, inserts a client AIS
         on the downstream client Port.
         <Help>  This control inserts a
        Client AIS for the client port
        "
	::= { pm1001lhCtrlcaisDwInsEntry 2 }


--- *********************************************************
---     TABLE for the pm1001lhCtrlclientAccessTermLoop articles
--- *********************************************************

pm1001lhCtrlclientAccessTermLoopTable OBJECT-TYPE
	SYNTAX  SEQUENCE OF Pm1001lhCtrlclientAccessTermLoopEntry
	MAX-ACCESS not-accessible
	STATUS current
	DESCRIPTION
        "
        List of pm1001lhCtrlclientAccessTermLoop
        Article
        "
	::= { pm1001lhCtrlClient 26 }


pm1001lhCtrlclientAccessTermLoopEntry OBJECT-TYPE
	SYNTAX Pm1001lhCtrlclientAccessTermLoopEntry
	MAX-ACCESS not-accessible
	STATUS current
	DESCRIPTION
        "
        Row definition for the pm1001lhCtrlclientAccessTermLoop
        table
        "
	INDEX   { pm1001lhCtrlclientAccessTermLoopIndex }
	::= { pm1001lhCtrlclientAccessTermLoopTable 1 }


Pm1001lhCtrlclientAccessTermLoopEntry ::=
	SEQUENCE {
	pm1001lhCtrlclientAccessTermLoopIndex
		INTEGER,
	pm1001lhCtrlclientAccessTermLoopPortn
		EkiState
	}


pm1001lhCtrlclientAccessTermLoopIndex OBJECT-TYPE
	SYNTAX  INTEGER(0..128)
	MAX-ACCESS  read-only
	STATUS current
	DESCRIPTION
        "
        Index definition for the pm1001lhCtrlclientAccessTermLoop
        table
        "
	::= { pm1001lhCtrlclientAccessTermLoopEntry 1 }


pm1001lhCtrlclientAccessTermLoopPortn OBJECT-TYPE
	SYNTAX  EkiState
	MAX-ACCESS read-write
	STATUS current
	DESCRIPTION
        "
        Client Terminal Loopback :This
        OID operates a Client Terminal
         Loopback, looping client input
        signal on the client output port.
        The loop is located on the line
        transceiver  <Help> This maintenance
        parameter operates a Client Terminal
        Loopback, looping client input
         signal on the client output port.
        The loop is located on the line
        transceiver
        "
	::= { pm1001lhCtrlclientAccessTermLoopEntry 2 }


pm1001lhCtrlprotocol OBJECT-TYPE
	  SYNTAX EkiProtocol
	  MAX-ACCESS read-write
	  STATUS current
	  DESCRIPTION
        "
        Client Protocol :This OID sets
        the protocol of the Client port
        "
	  ::= { pm1001lhCtrlClient 52 }



--- *****************************************************
---     LEAF for the commAccessLoop article
--- *****************************************************
pm1001lhCtrlcommAccessLoop OBJECT IDENTIFIER ::= { pm1001lhCtrlLine 64 }




pm1001lhCtrlCommAccessloop OBJECT-TYPE
	  SYNTAX EkiOnOff
	  MAX-ACCESS read-write
	  STATUS deprecated
	  DESCRIPTION
        "
        PM Full Access Loop Mode :This
        OID, when set, puts the module
         in common access loop back, looping
        the 10 Gb/s output signal on the
        10 Gb/s input.
        "
	  ::= { pm1001lhCtrlcommAccessLoop 1 }



--- *****************************************************
---     LEAF for the lineLoop article
--- *****************************************************
pm1001lhCtrllineLoop OBJECT IDENTIFIER ::= { pm1001lhCtrlLine 66 }




pm1001lhCtrlLineLoop OBJECT-TYPE
	  SYNTAX EkiOnOff
	  MAX-ACCESS read-write
	  STATUS deprecated
	  DESCRIPTION
        "
        PM Line Loop Mode :This OID, when
        set at '1' puts the module in line
        loopback mode, looping the received
        10 Gb/s signal on the transmit
         10 Gb/s output. The Upstream part
        of the module is timed on the 10
        Gb/s recovered clock in that case.
        "
	  ::= { pm1001lhCtrllineLoop 1 }



--- *****************************************************
---     LEAF for the msAis article
--- *****************************************************
pm1001lhCtrlmsAis OBJECT IDENTIFIER ::= { pm1001lhCtrlLine 67 }




pm1001lhCtrlMsAis OBJECT-TYPE
	  SYNTAX EkiOnOff
	  MAX-ACCESS read-write
	  STATUS current
	  DESCRIPTION
        "
        Insert MS-AIS/L-AIS On Line Output
        :This OID, when set, inserts an
        MS-AIS/L-AIS in the outgoing STM-64/OC-192
        signal.
        "
	  ::= { pm1001lhCtrlmsAis 1 }



--- *****************************************************
---     LEAF for the fecDisable article
--- *****************************************************
pm1001lhCtrlfecDisable OBJECT IDENTIFIER ::= { pm1001lhCtrlLine 69 }




pm1001lhCtrlFecInhibition OBJECT-TYPE
	  SYNTAX EkiOnOff
	  MAX-ACCESS read-write
	  STATUS current
	  DESCRIPTION
        "
        FEC Disable :This OID disable
         the Forward Error Correction decoder
        on the line receive side  <Help>
         This control disables the Forward
        Error Correction on the line input
        signal.
        "
	  ::= { pm1001lhCtrlfecDisable 1 }



--- *****************************************************
---     LEAF for the lineOosMode article
--- *****************************************************
pm1001lhCtrllineOosMode OBJECT IDENTIFIER ::= { pm1001lhCtrlLine 74 }




pm1001lhCtrlLineOosMode OBJECT-TYPE
	  SYNTAX EkiOnOff
	  MAX-ACCESS read-write
	  STATUS current
	  DESCRIPTION
        "
        Line Port Out Of Service :This
        OID sets the line port Out Of Service
         <Help>  This control defines the
        service state of the line port
        "
	  ::= { pm1001lhCtrllineOosMode 1 }



--- *****************************************************
---     LEAF for the ledTest article
--- *****************************************************
pm1001lhCtrlledTest OBJECT IDENTIFIER ::= { pm1001lhCtrlOther 192 }




pm1001lhCtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { pm1001lhCtrlledTest 3 }



pm1001lhCtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { pm1001lhCtrlledTest 2 }



pm1001lhCtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { pm1001lhCtrlledTest 1 }



--- *****************************************************
---     LEAF for the moduleOosMode article
--- *****************************************************
pm1001lhCtrlmoduleOosMode OBJECT IDENTIFIER ::= { pm1001lhCtrlOther 193 }




pm1001lhCtrlModuleOosMode OBJECT-TYPE
	  SYNTAX EkiOnOff
	  MAX-ACCESS read-write
	  STATUS current
	  DESCRIPTION
        "
        PM Out Of Service :This OID sets
        the PM1008 Out Of Service  <Help>
         This control defines the service
        state of the complete module
        "
	  ::= { pm1001lhCtrlmoduleOosMode 1 }



--- *****************************************************
---     LEAF for the maintenanceMode article
--- *****************************************************
pm1001lhCtrlmaintenanceMode OBJECT IDENTIFIER ::= { pm1001lhCtrlOther 197 }




pm1001lhCtrlMaintenanceMode OBJECT-TYPE
	  SYNTAX EkiOnOff
	  MAX-ACCESS read-write
	  STATUS current
	  DESCRIPTION
        "
        Module Maintenance Mode :This
         OID enables the maintenance mode
        on the PM.  <Help>   This control
        enables the maintenance mode on
        the PM.
        "
	  ::= { pm1001lhCtrlmaintenanceMode 1 }



--- *****************************************************
---     LEAF for the dccEnable article
--- *****************************************************
pm1001lhCtrldccEnable OBJECT IDENTIFIER ::= { pm1001lhCtrlOther 198 }




pm1001lhCtrlDccEnable OBJECT-TYPE
	  SYNTAX EkiOnOff
	  MAX-ACCESS read-write
	  STATUS current
	  DESCRIPTION
        "
        DCC Enable :This OID enables the
        DCC mode on the PM   <Help>   This
        control enables the DCC mode on
        the PM
        "
	  ::= { pm1001lhCtrldccEnable 1 }



--- *********************************************************
---     TABLE for the pm1001lhCtrlxfpOnoff articles
--- *********************************************************

pm1001lhCtrlxfpOnoffTable OBJECT-TYPE
	SYNTAX  SEQUENCE OF Pm1001lhCtrlxfpOnoffEntry
	MAX-ACCESS not-accessible
	STATUS current
	DESCRIPTION
        "
        List of pm1001lhCtrlxfpOnoff Article
        "
	::= { pm1001lhCtrlLine 208 }


pm1001lhCtrlxfpOnoffEntry OBJECT-TYPE
	SYNTAX Pm1001lhCtrlxfpOnoffEntry
	MAX-ACCESS not-accessible
	STATUS current
	DESCRIPTION
        "
        Row definition for the pm1001lhCtrlxfpOnoff
        table
        "
	INDEX   { pm1001lhCtrlxfpOnoffIndex }
	::= { pm1001lhCtrlxfpOnoffTable 1 }


Pm1001lhCtrlxfpOnoffEntry ::=
	SEQUENCE {
	pm1001lhCtrlxfpOnoffIndex
		INTEGER,
	pm1001lhCtrlxfpOnoffPortn
		EkiState
	}


pm1001lhCtrlxfpOnoffIndex OBJECT-TYPE
	SYNTAX  INTEGER(0..128)
	MAX-ACCESS  read-only
	STATUS current
	DESCRIPTION
        "
        Index definition for the pm1001lhCtrlxfpOnoff
        table
        "
	::= { pm1001lhCtrlxfpOnoffEntry 1 }


pm1001lhCtrlxfpOnoffPortn OBJECT-TYPE
	SYNTAX  EkiState
	MAX-ACCESS read-write
	STATUS current
	DESCRIPTION
        "
        Line Optical Laser Shutdown :This
        OID switches off the XFP or the
        OTX  <Help>  This control defines
        the laser state of the line transceiver
        "
	::= { pm1001lhCtrlxfpOnoffEntry 2 }


--- *********************************************************
---     TABLE for the pm1001lhCtrlxfpLineLoop articles
--- *********************************************************

pm1001lhCtrlxfpLineLoopTable OBJECT-TYPE
	SYNTAX  SEQUENCE OF Pm1001lhCtrlxfpLineLoopEntry
	MAX-ACCESS not-accessible
	STATUS current
	DESCRIPTION
        "
        List of pm1001lhCtrlxfpLineLoop
        Article
        "
	::= { pm1001lhCtrlLine 209 }


pm1001lhCtrlxfpLineLoopEntry OBJECT-TYPE
	SYNTAX Pm1001lhCtrlxfpLineLoopEntry
	MAX-ACCESS not-accessible
	STATUS current
	DESCRIPTION
        "
        Row definition for the pm1001lhCtrlxfpLineLoop
        table
        "
	INDEX   { pm1001lhCtrlxfpLineLoopIndex }
	::= { pm1001lhCtrlxfpLineLoopTable 1 }


Pm1001lhCtrlxfpLineLoopEntry ::=
	SEQUENCE {
	pm1001lhCtrlxfpLineLoopIndex
		INTEGER,
	pm1001lhCtrlxfpLineLoopPortn
		EkiState
	}


pm1001lhCtrlxfpLineLoopIndex OBJECT-TYPE
	SYNTAX  INTEGER(0..128)
	MAX-ACCESS  read-only
	STATUS current
	DESCRIPTION
        "
        Index definition for the pm1001lhCtrlxfpLineLoop
        table
        "
	::= { pm1001lhCtrlxfpLineLoopEntry 1 }


pm1001lhCtrlxfpLineLoopPortn OBJECT-TYPE
	SYNTAX  EkiState
	MAX-ACCESS read-write
	STATUS current
	DESCRIPTION
        "
        Line XFP/OTX Loop :This OID operates
        a line loopback on the line XFP
        or the OTX  <Help>  This control
        defines the line loop back of the
        line transceiver
        "
	::= { pm1001lhCtrlxfpLineLoopEntry 2 }


--- *********************************************************
---     TABLE for the pm1001lhCtrlxfpLineXfiLoop articles
--- *********************************************************

pm1001lhCtrlxfpLineXfiLoopTable OBJECT-TYPE
	SYNTAX  SEQUENCE OF Pm1001lhCtrlxfpLineXfiLoopEntry
	MAX-ACCESS not-accessible
	STATUS current
	DESCRIPTION
        "
        List of pm1001lhCtrlxfpLineXfiLoop
        Article
        "
	::= { pm1001lhCtrlLine 210 }


pm1001lhCtrlxfpLineXfiLoopEntry OBJECT-TYPE
	SYNTAX Pm1001lhCtrlxfpLineXfiLoopEntry
	MAX-ACCESS not-accessible
	STATUS current
	DESCRIPTION
        "
        Row definition for the pm1001lhCtrlxfpLineXfiLoop
        table
        "
	INDEX   { pm1001lhCtrlxfpLineXfiLoopIndex }
	::= { pm1001lhCtrlxfpLineXfiLoopTable 1 }


Pm1001lhCtrlxfpLineXfiLoopEntry ::=
	SEQUENCE {
	pm1001lhCtrlxfpLineXfiLoopIndex
		INTEGER,
	pm1001lhCtrlxfpLineXfiLoopPortn
		EkiState
	}


pm1001lhCtrlxfpLineXfiLoopIndex OBJECT-TYPE
	SYNTAX  INTEGER(0..128)
	MAX-ACCESS  read-only
	STATUS current
	DESCRIPTION
        "
        Index definition for the pm1001lhCtrlxfpLineXfiLoop
        table
        "
	::= { pm1001lhCtrlxfpLineXfiLoopEntry 1 }


pm1001lhCtrlxfpLineXfiLoopPortn OBJECT-TYPE
	SYNTAX  EkiState
	MAX-ACCESS read-write
	STATUS current
	DESCRIPTION
        "
        Line XFP/OTX XFI Loop :This OID
        operates a XFI loopback on the
         line XFP or the OTX  <Help>  This
        control defines the XFI loop back
        of the line transceiver
        "
	::= { pm1001lhCtrlxfpLineXfiLoopEntry 2 }


--- *****************************************************
---     LEAF for the lineTunableChannel article
--- *****************************************************

pm1001lhCtrllineTunableChannel OBJECT-TYPE
	  SYNTAX Pm1001lhOtxChannel
	  MAX-ACCESS read-write
	  STATUS current
	  DESCRIPTION
        "
        ITU Channel :This OID selects
         the ITU channel of the Line OTX
        TLH Laser  <Help>   This control
        defines the ITU channel of the
         Line OTX TLH Laser
        "
	  ::= { pm1001lhCtrlLine 212 }



--- *****************************************************
---     LEAF for the linePhotodiodeMode article
--- *****************************************************

pm1001lhCtrllinePhotodiodeMode OBJECT-TYPE
	  SYNTAX Pm1001lhOtxMode
	  MAX-ACCESS read-write
	  STATUS current
	  DESCRIPTION
        "
        OTX TLH Rx Sens. Mode :This OID
        defines the Rx sensiblity mode
         of the Line OTX TLH  <Help>
         This control defines the receiver
        sensibility mode of the Line OTX
        TLH Laser (OTX60, OTX80 or Custom)
        "
	  ::= { pm1001lhCtrlLine 213 }



--- *****************************************************
---     LEAF for the linePhotodiodeValue article
--- *****************************************************

pm1001lhCtrllinePhotodiodeValue OBJECT-TYPE
	  SYNTAX Pm1001lhAdjustValue
	  MAX-ACCESS read-write
	  STATUS current
	  DESCRIPTION
        "
        OTX TLH Rx Sensibility :This OID
        sets the Rx sensibility of the
         Line OTX TLH (custom mode only)
         <Help>   This control defines
         the receiver sensibility value
        (only in Custom mode) of the Line
        OTX TLH Laser
        "
	  ::= { pm1001lhCtrlLine 214 }



--- *****************************************************
---     LEAF for the linePowerLaser article
--- *****************************************************

pm1001lhCtrllinePowerLaser OBJECT-TYPE
	  SYNTAX Unsigned32 (0..65535)
	  MAX-ACCESS read-write
	  STATUS current
	  DESCRIPTION
        "
        Line Laser Output Power [3-5]
         :This OID sets the output power
        value on the laser of the Line
         OTX TLH (AV=Power*10+158) (Unit
        = dBm)  <Help>   This control defines
        the start-up output power of the
        Line OTX TLH
        "
	  ::= { pm1001lhCtrlLine 215 }



--- *****************************************************
---     LEAF for the otxVlhReset article
--- *****************************************************
pm1001lhCtrlotxVlhReset OBJECT IDENTIFIER ::= { pm1001lhCtrlLine 216 }




pm1001lhCtrlOtxVlhReset OBJECT-TYPE
	  SYNTAX EkiOnOff
	  MAX-ACCESS read-write
	  STATUS current
	  DESCRIPTION
        "
        OTX-VLH Reset :This OID resets
        the OTX-VLH module  <Help>  This
        control resets the OTX-VLH and
         its parameters
        "
	  ::= { pm1001lhCtrlotxVlhReset 1 }



--- *********************************************************
---     TABLE for the pm1001lhCtrllineAccessLoop articles
--- *********************************************************

pm1001lhCtrllineAccessLoopTable OBJECT-TYPE
	SYNTAX  SEQUENCE OF Pm1001lhCtrllineAccessLoopEntry
	MAX-ACCESS not-accessible
	STATUS current
	DESCRIPTION
        "
        List of pm1001lhCtrllineAccessLoop
        Article
        "
	::= { pm1001lhCtrlLine 217 }


pm1001lhCtrllineAccessLoopEntry OBJECT-TYPE
	SYNTAX Pm1001lhCtrllineAccessLoopEntry
	MAX-ACCESS not-accessible
	STATUS current
	DESCRIPTION
        "
        Row definition for the pm1001lhCtrllineAccessLoop
        table
        "
	INDEX   { pm1001lhCtrllineAccessLoopIndex }
	::= { pm1001lhCtrllineAccessLoopTable 1 }


Pm1001lhCtrllineAccessLoopEntry ::=
	SEQUENCE {
	pm1001lhCtrllineAccessLoopIndex
		INTEGER,
	pm1001lhCtrllineAccessLoopPortn
		EkiState
	}


pm1001lhCtrllineAccessLoopIndex OBJECT-TYPE
	SYNTAX  INTEGER(0..128)
	MAX-ACCESS  read-only
	STATUS current
	DESCRIPTION
        "
        Index definition for the pm1001lhCtrllineAccessLoop
        table
        "
	::= { pm1001lhCtrllineAccessLoopEntry 1 }


pm1001lhCtrllineAccessLoopPortn OBJECT-TYPE
	SYNTAX  EkiState
	MAX-ACCESS read-write
	STATUS current
	DESCRIPTION
        "
        Line Facility Loopback :This OID
        operates a Line Facility Loopback,
        looping line input signal on the
        line output port. The loop is located
        on the line transceiver. If the
        Line signal carries DCC, the management
        network is impacted  <Help> This
        maintenance parameter operates
         a Line Facility Loopback, looping
        line input signal on the line output
        port. The loop is located on the
        line transceiver. If the Line signal
        carries DCC, the management network
        is impacted
        "
	::= { pm1001lhCtrllineAccessLoopEntry 2 }


--- *********************************************************
---     TABLE for the pm1001lhCtrllineLoopTransceiver articles
--- *********************************************************

pm1001lhCtrllineLoopTransceiverTable OBJECT-TYPE
	SYNTAX  SEQUENCE OF Pm1001lhCtrllineLoopTransceiverEntry
	MAX-ACCESS not-accessible
	STATUS current
	DESCRIPTION
        "
        List of pm1001lhCtrllineLoopTransceiver
        Article
        "
	::= { pm1001lhCtrlLine 218 }


pm1001lhCtrllineLoopTransceiverEntry OBJECT-TYPE
	SYNTAX Pm1001lhCtrllineLoopTransceiverEntry
	MAX-ACCESS not-accessible
	STATUS current
	DESCRIPTION
        "
        Row definition for the pm1001lhCtrllineLoopTransceiver
        table
        "
	INDEX   { pm1001lhCtrllineLoopTransceiverIndex }
	::= { pm1001lhCtrllineLoopTransceiverTable 1 }


Pm1001lhCtrllineLoopTransceiverEntry ::=
	SEQUENCE {
	pm1001lhCtrllineLoopTransceiverIndex
		INTEGER,
	pm1001lhCtrllineLoopTransceiverPortn
		EkiState
	}


pm1001lhCtrllineLoopTransceiverIndex OBJECT-TYPE
	SYNTAX  INTEGER(0..128)
	MAX-ACCESS  read-only
	STATUS current
	DESCRIPTION
        "
        Index definition for the pm1001lhCtrllineLoopTransceiver
        table
        "
	::= { pm1001lhCtrllineLoopTransceiverEntry 1 }


pm1001lhCtrllineLoopTransceiverPortn OBJECT-TYPE
	SYNTAX  EkiState
	MAX-ACCESS read-write
	STATUS current
	DESCRIPTION
        "
        Line Terminal Loopback :This OID
        operates a Line Terminal Loopback,
        looping line input signal on the
        line output port. The loop is located
        on all client transceivers  <Help>
        This maintenance parameter operates
        a Line Terminal Loopback, looping
        line input signal on the line output
        port. The loop is located on all
        client transceivers.
        "
	::= { pm1001lhCtrllineLoopTransceiverEntry 2 }


--- *********************************************************
---     TABLE for the pm1001lhCtrlclientResetAllCount articles
--- *********************************************************

pm1001lhCtrlclientResetAllCountTable OBJECT-TYPE
	SYNTAX  SEQUENCE OF Pm1001lhCtrlclientResetAllCountEntry
	MAX-ACCESS not-accessible
	STATUS current
	DESCRIPTION
        "
        List of pm1001lhCtrlclientResetAllCount
        Article
        "
	::= { pm1001lhCtrlClient 271 }


pm1001lhCtrlclientResetAllCountEntry OBJECT-TYPE
	SYNTAX Pm1001lhCtrlclientResetAllCountEntry
	MAX-ACCESS not-accessible
	STATUS current
	DESCRIPTION
        "
        Row definition for the pm1001lhCtrlclientResetAllCount
        table
        "
	INDEX   { pm1001lhCtrlclientResetAllCountIndex }
	::= { pm1001lhCtrlclientResetAllCountTable 1 }


Pm1001lhCtrlclientResetAllCountEntry ::=
	SEQUENCE {
	pm1001lhCtrlclientResetAllCountIndex
		INTEGER,
	pm1001lhCtrlclientResetAllCountsPortn
		EkiState
	}


pm1001lhCtrlclientResetAllCountIndex OBJECT-TYPE
	SYNTAX  INTEGER(0..128)
	MAX-ACCESS  read-only
	STATUS current
	DESCRIPTION
        "
        Index definition for the pm1001lhCtrlclientResetAllCount
        table
        "
	::= { pm1001lhCtrlclientResetAllCountEntry 1 }


pm1001lhCtrlclientResetAllCountsPortn OBJECT-TYPE
	SYNTAX  EkiState
	MAX-ACCESS read-write
	STATUS current
	DESCRIPTION
        "
        Client Counters Reset :This OID
        resets every counter on the client
        port  <Help>   This control operates
        a reset on the statistics current
        ,previous and history client port
        counters
        "
	::= { pm1001lhCtrlclientResetAllCountEntry 2 }


--- *********************************************************
---     TABLE for the pm1001lhCtrllineResetAllCount articles
--- *********************************************************

pm1001lhCtrllineResetAllCountTable OBJECT-TYPE
	SYNTAX  SEQUENCE OF Pm1001lhCtrllineResetAllCountEntry
	MAX-ACCESS not-accessible
	STATUS current
	DESCRIPTION
        "
        List of pm1001lhCtrllineResetAllCount
        Article
        "
	::= { pm1001lhCtrlLine 335 }


pm1001lhCtrllineResetAllCountEntry OBJECT-TYPE
	SYNTAX Pm1001lhCtrllineResetAllCountEntry
	MAX-ACCESS not-accessible
	STATUS current
	DESCRIPTION
        "
        Row definition for the pm1001lhCtrllineResetAllCount
        table
        "
	INDEX   { pm1001lhCtrllineResetAllCountIndex }
	::= { pm1001lhCtrllineResetAllCountTable 1 }


Pm1001lhCtrllineResetAllCountEntry ::=
	SEQUENCE {
	pm1001lhCtrllineResetAllCountIndex
		INTEGER,
	pm1001lhCtrllineResetAllCountsPortn
		EkiState
	}


pm1001lhCtrllineResetAllCountIndex OBJECT-TYPE
	SYNTAX  INTEGER(0..128)
	MAX-ACCESS  read-only
	STATUS current
	DESCRIPTION
        "
        Index definition for the pm1001lhCtrllineResetAllCount
        table
        "
	::= { pm1001lhCtrllineResetAllCountEntry 1 }


pm1001lhCtrllineResetAllCountsPortn OBJECT-TYPE
	SYNTAX  EkiState
	MAX-ACCESS read-write
	STATUS current
	DESCRIPTION
        "
        Line Counters Reset :This OID
         resets every counter on the line
        port  <Help>   This control operates
        a reset on the statistics current
        ,previous and history line port
        counters
        "
	::= { pm1001lhCtrllineResetAllCountEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pm1001lhCntclientUpErrCnt articles
--- *********************************************************

pm1001lhCntclientUpErrCntTable OBJECT-TYPE
	SYNTAX  SEQUENCE OF Pm1001lhCntclientUpErrCntEntry
	MAX-ACCESS not-accessible
	STATUS current
	DESCRIPTION
        "
        List of pm1001lhCntclientUpErrCnt
        Article
        "
	::= { pm1001lhCntClient 32 }


pm1001lhCntclientUpErrCntEntry OBJECT-TYPE
	SYNTAX Pm1001lhCntclientUpErrCntEntry
	MAX-ACCESS not-accessible
	STATUS current
	DESCRIPTION
        "
        Row definition for the pm1001lhCntclientUpErrCnt
        table
        "
	INDEX   { pm1001lhCntclientUpErrCntIndex }
	::= { pm1001lhCntclientUpErrCntTable 1 }


Pm1001lhCntclientUpErrCntEntry ::=
	SEQUENCE {
	pm1001lhCntclientUpErrCntIndex
		INTEGER,
	pm1001lhCntclientUpErrCntValuePortn
		Counter32,
	pm1001lhCntclientUpErrCntErrorPortn
		EkiOnOff,
	pm1001lhCntclientUpErrCntOverloadPortn
		EkiOnOff
	}


pm1001lhCntclientUpErrCntIndex OBJECT-TYPE
	SYNTAX  INTEGER(0..128)
	MAX-ACCESS  read-only
	STATUS current
	DESCRIPTION
        "
        Index definition for the pm1001lhCntclientUpErrCnt
        table
        "
	::= { pm1001lhCntclientUpErrCntEntry 1 }


pm1001lhCntclientUpErrCntValuePortn OBJECT-TYPE
	SYNTAX  Counter32
	MAX-ACCESS read-only
	STATUS current
	DESCRIPTION
        "
        Client Input Errors :This counter
        is increased each time a FCS error
        is detected in 10GbE mode or a
         B1 error is detected in OC-192/STM-64
        mode on the client input stream
         <Help>  This counter gives the
        number of FCS errors or B1 errors
        on the client input port
        "
	::= { pm1001lhCntclientUpErrCntEntry 2 }


pm1001lhCntclientUpErrCntErrorPortn OBJECT-TYPE
	SYNTAX  EkiOnOff
	MAX-ACCESS read-only
	STATUS current
	DESCRIPTION
        "
        Client Counter Error :This OID
        when set indicates the FCS error
        counter value is invalid on input
        Port
        "
	::= { pm1001lhCntclientUpErrCntEntry 3 }


pm1001lhCntclientUpErrCntOverloadPortn OBJECT-TYPE
	SYNTAX  EkiOnOff
	MAX-ACCESS read-only
	STATUS current
	DESCRIPTION
        "
        Client Counter Overload :This
         OID when set indicates a FCS error
        counter overload on input Port
        "
	::= { pm1001lhCntclientUpErrCntEntry 4 }


--- *********************************************************
---     TABLE for the pm1001lhCntclientUpTimCnt articles
--- *********************************************************

pm1001lhCntclientUpTimCntTable OBJECT-TYPE
	SYNTAX  SEQUENCE OF Pm1001lhCntclientUpTimCntEntry
	MAX-ACCESS not-accessible
	STATUS current
	DESCRIPTION
        "
        List of pm1001lhCntclientUpTimCnt
        Article
        "
	::= { pm1001lhCntClient 40 }


pm1001lhCntclientUpTimCntEntry OBJECT-TYPE
	SYNTAX Pm1001lhCntclientUpTimCntEntry
	MAX-ACCESS not-accessible
	STATUS current
	DESCRIPTION
        "
        Row definition for the pm1001lhCntclientUpTimCnt
        table
        "
	INDEX   { pm1001lhCntclientUpTimCntIndex }
	::= { pm1001lhCntclientUpTimCntTable 1 }


Pm1001lhCntclientUpTimCntEntry ::=
	SEQUENCE {
	pm1001lhCntclientUpTimCntIndex
		INTEGER,
	pm1001lhCntclientUpTimCntValuePortn
		Counter32,
	pm1001lhCntclientUpTimCntErrorPortn
		EkiOnOff,
	pm1001lhCntclientUpTimCntOverloadPortn
		EkiOnOff
	}


pm1001lhCntclientUpTimCntIndex OBJECT-TYPE
	SYNTAX  INTEGER(0..128)
	MAX-ACCESS  read-only
	STATUS current
	DESCRIPTION
        "
        Index definition for the pm1001lhCntclientUpTimCnt
        table
        "
	::= { pm1001lhCntclientUpTimCntEntry 1 }


pm1001lhCntclientUpTimCntValuePortn OBJECT-TYPE
	SYNTAX  Counter32
	MAX-ACCESS read-only
	STATUS current
	DESCRIPTION
        "
        Client Upstream Timer Counter
         :This is the timing counter dedicated
        to the upstream access counters.
        It is incremented every 125 us.
        "
	::= { pm1001lhCntclientUpTimCntEntry 2 }


pm1001lhCntclientUpTimCntErrorPortn OBJECT-TYPE
	SYNTAX  EkiOnOff
	MAX-ACCESS read-only
	STATUS current
	DESCRIPTION
        "
        Client Counter Error :This OID
        when set indicates the upstream
        timing counter value is invalid
        on Port
        "
	::= { pm1001lhCntclientUpTimCntEntry 3 }


pm1001lhCntclientUpTimCntOverloadPortn OBJECT-TYPE
	SYNTAX  EkiOnOff
	MAX-ACCESS read-only
	STATUS current
	DESCRIPTION
        "
        Client Counter Overload :This
         OID when set indicates a upstream
        timing counter overload on Port
        "
	::= { pm1001lhCntclientUpTimCntEntry 4 }


--- *********************************************************
---     TABLE for the pm1001lhCntclientDwErrCnt articles
--- *********************************************************

pm1001lhCntclientDwErrCntTable OBJECT-TYPE
	SYNTAX  SEQUENCE OF Pm1001lhCntclientDwErrCntEntry
	MAX-ACCESS not-accessible
	STATUS current
	DESCRIPTION
        "
        List of pm1001lhCntclientDwErrCnt
        Article
        "
	::= { pm1001lhCntClient 64 }


pm1001lhCntclientDwErrCntEntry OBJECT-TYPE
	SYNTAX Pm1001lhCntclientDwErrCntEntry
	MAX-ACCESS not-accessible
	STATUS current
	DESCRIPTION
        "
        Row definition for the pm1001lhCntclientDwErrCnt
        table
        "
	INDEX   { pm1001lhCntclientDwErrCntIndex }
	::= { pm1001lhCntclientDwErrCntTable 1 }


Pm1001lhCntclientDwErrCntEntry ::=
	SEQUENCE {
	pm1001lhCntclientDwErrCntIndex
		INTEGER,
	pm1001lhCntclientDwErrCntValuePortn
		Counter32,
	pm1001lhCntclientDwErrCntErrorPortn
		EkiOnOff,
	pm1001lhCntclientDwErrCntOverloadPortn
		EkiOnOff
	}


pm1001lhCntclientDwErrCntIndex OBJECT-TYPE
	SYNTAX  INTEGER(0..128)
	MAX-ACCESS  read-only
	STATUS current
	DESCRIPTION
        "
        Index definition for the pm1001lhCntclientDwErrCnt
        table
        "
	::= { pm1001lhCntclientDwErrCntEntry 1 }


pm1001lhCntclientDwErrCntValuePortn OBJECT-TYPE
	SYNTAX  Counter32
	MAX-ACCESS read-only
	STATUS current
	DESCRIPTION
        "
        Client Output Errors :This counter
        is increased each time a B1/FCS
        error is detected on the client
        output stream  <Help>  This counter
        gives the number of FCS errors
         or B1 errors on the client output
        port
        "
	::= { pm1001lhCntclientDwErrCntEntry 2 }


pm1001lhCntclientDwErrCntErrorPortn OBJECT-TYPE
	SYNTAX  EkiOnOff
	MAX-ACCESS read-only
	STATUS current
	DESCRIPTION
        "
        Client Counter Error :This OID
        when set indicates the FCS error
        counter value is invalid on output
        Port
        "
	::= { pm1001lhCntclientDwErrCntEntry 3 }


pm1001lhCntclientDwErrCntOverloadPortn OBJECT-TYPE
	SYNTAX  EkiOnOff
	MAX-ACCESS read-only
	STATUS current
	DESCRIPTION
        "
        Client Counter Overload :This
         OID when set indicates a FCS error
        counter overload on output Port
        "
	::= { pm1001lhCntclientDwErrCntEntry 4 }


--- *********************************************************
---     TABLE for the pm1001lhCntclientDwTimCnt articles
--- *********************************************************

pm1001lhCntclientDwTimCntTable OBJECT-TYPE
	SYNTAX  SEQUENCE OF Pm1001lhCntclientDwTimCntEntry
	MAX-ACCESS not-accessible
	STATUS current
	DESCRIPTION
        "
        List of pm1001lhCntclientDwTimCnt
        Article
        "
	::= { pm1001lhCntClient 72 }


pm1001lhCntclientDwTimCntEntry OBJECT-TYPE
	SYNTAX Pm1001lhCntclientDwTimCntEntry
	MAX-ACCESS not-accessible
	STATUS current
	DESCRIPTION
        "
        Row definition for the pm1001lhCntclientDwTimCnt
        table
        "
	INDEX   { pm1001lhCntclientDwTimCntIndex }
	::= { pm1001lhCntclientDwTimCntTable 1 }


Pm1001lhCntclientDwTimCntEntry ::=
	SEQUENCE {
	pm1001lhCntclientDwTimCntIndex
		INTEGER,
	pm1001lhCntclientDwTimCntValuePortn
		Counter32,
	pm1001lhCntclientDwTimCntErrorPortn
		EkiOnOff,
	pm1001lhCntclientDwTimCntOverloadPortn
		EkiOnOff
	}


pm1001lhCntclientDwTimCntIndex OBJECT-TYPE
	SYNTAX  INTEGER(0..128)
	MAX-ACCESS  read-only
	STATUS current
	DESCRIPTION
        "
        Index definition for the pm1001lhCntclientDwTimCnt
        table
        "
	::= { pm1001lhCntclientDwTimCntEntry 1 }


pm1001lhCntclientDwTimCntValuePortn OBJECT-TYPE
	SYNTAX  Counter32
	MAX-ACCESS read-only
	STATUS current
	DESCRIPTION
        "
        Client Downstream Timer Counter
        :This is the timing counter dedicated
        to the downstream access counters.
        It is incremented every 125 us.
        "
	::= { pm1001lhCntclientDwTimCntEntry 2 }


pm1001lhCntclientDwTimCntErrorPortn OBJECT-TYPE
	SYNTAX  EkiOnOff
	MAX-ACCESS read-only
	STATUS current
	DESCRIPTION
        "
        Client Counter Error :This OID
        when set indicates the downstream
        timer counter value is invalid
         on Port
        "
	::= { pm1001lhCntclientDwTimCntEntry 3 }


pm1001lhCntclientDwTimCntOverloadPortn OBJECT-TYPE
	SYNTAX  EkiOnOff
	MAX-ACCESS read-only
	STATUS current
	DESCRIPTION
        "
        Client Counter Overload :This
         OID when set indicates a downstream
        timer counter overload on Port
        "
	::= { pm1001lhCntclientDwTimCntEntry 4 }


--- *********************************************************
---     TABLE for the pm1001lhCntlineDfrmErrCnt articles
--- *********************************************************

pm1001lhCntlineDfrmErrCntTable OBJECT-TYPE
	SYNTAX  SEQUENCE OF Pm1001lhCntlineDfrmErrCntEntry
	MAX-ACCESS not-accessible
	STATUS current
	DESCRIPTION
        "
        List of pm1001lhCntlineDfrmErrCnt
        Article
        "
	::= { pm1001lhCntLine 152 }


pm1001lhCntlineDfrmErrCntEntry OBJECT-TYPE
	SYNTAX Pm1001lhCntlineDfrmErrCntEntry
	MAX-ACCESS not-accessible
	STATUS current
	DESCRIPTION
        "
        Row definition for the pm1001lhCntlineDfrmErrCnt
        table
        "
	INDEX   { pm1001lhCntlineDfrmErrCntIndex }
	::= { pm1001lhCntlineDfrmErrCntTable 1 }


Pm1001lhCntlineDfrmErrCntEntry ::=
	SEQUENCE {
	pm1001lhCntlineDfrmErrCntIndex
		INTEGER,
	pm1001lhCntlineDfrmErrCntValuePortn
		Counter32,
	pm1001lhCntlineDfrmErrCntErrorPortn
		EkiOnOff,
	pm1001lhCntlineDfrmErrCntOverloadPortn
		EkiOnOff
	}


pm1001lhCntlineDfrmErrCntIndex OBJECT-TYPE
	SYNTAX  INTEGER(0..128)
	MAX-ACCESS  read-only
	STATUS current
	DESCRIPTION
        "
        Index definition for the pm1001lhCntlineDfrmErrCnt
        table
        "
	::= { pm1001lhCntlineDfrmErrCntEntry 1 }


pm1001lhCntlineDfrmErrCntValuePortn OBJECT-TYPE
	SYNTAX  Counter32
	MAX-ACCESS read-only
	STATUS current
	DESCRIPTION
        "
        Line Input B1 Errors :This counter
        is incremented each time a B1 error
        is detected on the Deframer input
        stream.  <Help>  This counter gives
        the number of B1 errors on the
         line port
        "
	::= { pm1001lhCntlineDfrmErrCntEntry 2 }


pm1001lhCntlineDfrmErrCntErrorPortn OBJECT-TYPE
	SYNTAX  EkiOnOff
	MAX-ACCESS read-only
	STATUS current
	DESCRIPTION
        "
        Line Counter Error :This OID when
        set indicates the B1 error counter
        value is invalid on Port
        "
	::= { pm1001lhCntlineDfrmErrCntEntry 3 }


pm1001lhCntlineDfrmErrCntOverloadPortn OBJECT-TYPE
	SYNTAX  EkiOnOff
	MAX-ACCESS read-only
	STATUS current
	DESCRIPTION
        "
        Line Counter Overload :This OID
        when set indicates a B1 error counter
        overload on Port
        "
	::= { pm1001lhCntlineDfrmErrCntEntry 4 }


--- *********************************************************
---     TABLE for the pm1001lhCntlineDfrmTimCnt articles
--- *********************************************************

pm1001lhCntlineDfrmTimCntTable OBJECT-TYPE
	SYNTAX  SEQUENCE OF Pm1001lhCntlineDfrmTimCntEntry
	MAX-ACCESS not-accessible
	STATUS current
	DESCRIPTION
        "
        List of pm1001lhCntlineDfrmTimCnt
        Article
        "
	::= { pm1001lhCntLine 153 }


pm1001lhCntlineDfrmTimCntEntry OBJECT-TYPE
	SYNTAX Pm1001lhCntlineDfrmTimCntEntry
	MAX-ACCESS not-accessible
	STATUS current
	DESCRIPTION
        "
        Row definition for the pm1001lhCntlineDfrmTimCnt
        table
        "
	INDEX   { pm1001lhCntlineDfrmTimCntIndex }
	::= { pm1001lhCntlineDfrmTimCntTable 1 }


Pm1001lhCntlineDfrmTimCntEntry ::=
	SEQUENCE {
	pm1001lhCntlineDfrmTimCntIndex
		INTEGER,
	pm1001lhCntlineDfrmTimCntValuePortn
		Counter32,
	pm1001lhCntlineDfrmTimCntErrorPortn
		EkiOnOff,
	pm1001lhCntlineDfrmTimCntOverloadPortn
		EkiOnOff
	}


pm1001lhCntlineDfrmTimCntIndex OBJECT-TYPE
	SYNTAX  INTEGER(0..128)
	MAX-ACCESS  read-only
	STATUS current
	DESCRIPTION
        "
        Index definition for the pm1001lhCntlineDfrmTimCnt
        table
        "
	::= { pm1001lhCntlineDfrmTimCntEntry 1 }


pm1001lhCntlineDfrmTimCntValuePortn OBJECT-TYPE
	SYNTAX  Counter32
	MAX-ACCESS read-only
	STATUS current
	DESCRIPTION
        "
        Line Timer :This is the timing
        counter dedicated to the downstream
        deframer counters. It is incremented
        every 125 us.
        "
	::= { pm1001lhCntlineDfrmTimCntEntry 2 }


pm1001lhCntlineDfrmTimCntErrorPortn OBJECT-TYPE
	SYNTAX  EkiOnOff
	MAX-ACCESS read-only
	STATUS current
	DESCRIPTION
        "
        Line Counter Error :This OID when
        set indicates the deframer timer
        counter value is invalid on Port
        "
	::= { pm1001lhCntlineDfrmTimCntEntry 3 }


pm1001lhCntlineDfrmTimCntOverloadPortn OBJECT-TYPE
	SYNTAX  EkiOnOff
	MAX-ACCESS read-only
	STATUS current
	DESCRIPTION
        "
        Line Counter Overload :This OID
        when set indicates a deframer timer
        counter overload on Port
        "
	::= { pm1001lhCntlineDfrmTimCntEntry 4 }


--- *********************************************************
---     TABLE for the pm1001lhCntlineDfrmPrimErrCnt articles
--- *********************************************************

pm1001lhCntlineDfrmPrimErrCntTable OBJECT-TYPE
	SYNTAX  SEQUENCE OF Pm1001lhCntlineDfrmPrimErrCntEntry
	MAX-ACCESS not-accessible
	STATUS current
	DESCRIPTION
        "
        List of pm1001lhCntlineDfrmPrimErrCnt
        Article
        "
	::= { pm1001lhCntLine 154 }


pm1001lhCntlineDfrmPrimErrCntEntry OBJECT-TYPE
	SYNTAX Pm1001lhCntlineDfrmPrimErrCntEntry
	MAX-ACCESS not-accessible
	STATUS current
	DESCRIPTION
        "
        Row definition for the pm1001lhCntlineDfrmPrimErrCnt
        table
        "
	INDEX   { pm1001lhCntlineDfrmPrimErrCntIndex }
	::= { pm1001lhCntlineDfrmPrimErrCntTable 1 }


Pm1001lhCntlineDfrmPrimErrCntEntry ::=
	SEQUENCE {
	pm1001lhCntlineDfrmPrimErrCntIndex
		INTEGER,
	pm1001lhCntlineDfrmPrimErrCntValuePortn
		Counter32,
	pm1001lhCntlineDfrmPrimErrCntErrorPortn
		EkiOnOff,
	pm1001lhCntlineDfrmPrimErrCntOverloadPortn
		EkiOnOff
	}


pm1001lhCntlineDfrmPrimErrCntIndex OBJECT-TYPE
	SYNTAX  INTEGER(0..128)
	MAX-ACCESS  read-only
	STATUS current
	DESCRIPTION
        "
        Index definition for the pm1001lhCntlineDfrmPrimErrCnt
        table
        "
	::= { pm1001lhCntlineDfrmPrimErrCntEntry 1 }


pm1001lhCntlineDfrmPrimErrCntValuePortn OBJECT-TYPE
	SYNTAX  Counter32
	MAX-ACCESS read-only
	STATUS current
	DESCRIPTION
        "
        Line Input FEC Corrected Errors
        :This counter is incremented each
        time an error is corrected by the
        Forward Error Correction decoder
         <Help>  This counter gives the
        number of errors corrected by the
        FEC on the line port
        "
	::= { pm1001lhCntlineDfrmPrimErrCntEntry 2 }


pm1001lhCntlineDfrmPrimErrCntErrorPortn OBJECT-TYPE
	SYNTAX  EkiOnOff
	MAX-ACCESS read-only
	STATUS current
	DESCRIPTION
        "
        Line FEC Counter Error :This bit
        when set indicates the FEC counter
        value is invalid on Port
        "
	::= { pm1001lhCntlineDfrmPrimErrCntEntry 3 }


pm1001lhCntlineDfrmPrimErrCntOverloadPortn OBJECT-TYPE
	SYNTAX  EkiOnOff
	MAX-ACCESS read-only
	STATUS current
	DESCRIPTION
        "
        Line FEC Counter Overload :This
        bit when set indicates a FEC counter
        overload on Port
        "
	::= { pm1001lhCntlineDfrmPrimErrCntEntry 4 }


--- *********************************************************
---     TABLE for the pm1001lhCntlineDfrmErrCntS articles
--- *********************************************************

pm1001lhCntlineDfrmErrCntSTable OBJECT-TYPE
	SYNTAX  SEQUENCE OF Pm1001lhCntlineDfrmErrCntSEntry
	MAX-ACCESS not-accessible
	STATUS current
	DESCRIPTION
        "
        List of pm1001lhCntlineDfrmErrCntS
        Article
        "
	::= { pm1001lhCntLine 1160 }


pm1001lhCntlineDfrmErrCntSEntry OBJECT-TYPE
	SYNTAX Pm1001lhCntlineDfrmErrCntSEntry
	MAX-ACCESS not-accessible
	STATUS current
	DESCRIPTION
        "
        Row definition for the pm1001lhCntlineDfrmErrCntS
        table
        "
	INDEX   { pm1001lhCntlineDfrmErrCntSIndex }
	::= { pm1001lhCntlineDfrmErrCntSTable 1 }


Pm1001lhCntlineDfrmErrCntSEntry ::=
	SEQUENCE {
	pm1001lhCntlineDfrmErrCntSIndex
		INTEGER,
	pm1001lhCntlineDfrmErrCntSValuePortn
		Counter32,
	pm1001lhCntlineDfrmErrCntSErrorPortn
		EkiOnOff,
	pm1001lhCntlineDfrmErrCntSOverloadPortn
		EkiOnOff
	}


pm1001lhCntlineDfrmErrCntSIndex OBJECT-TYPE
	SYNTAX  INTEGER(0..128)
	MAX-ACCESS  read-only
	STATUS current
	DESCRIPTION
        "
        Index definition for the pm1001lhCntlineDfrmErrCntS
        table
        "
	::= { pm1001lhCntlineDfrmErrCntSEntry 1 }


pm1001lhCntlineDfrmErrCntSValuePortn OBJECT-TYPE
	SYNTAX  Counter32
	MAX-ACCESS read-only
	STATUS current
	DESCRIPTION
        "
        Line B1 error rate (/s) :This
         OID gives the number of B1 errors
        per second that are detected on
        the Deframer input stream.
        "
	::= { pm1001lhCntlineDfrmErrCntSEntry 2 }


pm1001lhCntlineDfrmErrCntSErrorPortn OBJECT-TYPE
	SYNTAX  EkiOnOff
	MAX-ACCESS read-only
	STATUS current
	DESCRIPTION
        "

        "
	::= { pm1001lhCntlineDfrmErrCntSEntry 3 }


pm1001lhCntlineDfrmErrCntSOverloadPortn OBJECT-TYPE
	SYNTAX  EkiOnOff
	MAX-ACCESS read-only
	STATUS current
	DESCRIPTION
        "

        "
	::= { pm1001lhCntlineDfrmErrCntSEntry 4 }


pm1001lhCntCountersReset  OBJECT-TYPE
	SYNTAX EkiOnOff
	MAX-ACCESS read-write
	STATUS current
	DESCRIPTION
	"Counters Reset:This OID resets and restarts all the counters"
	::= { pm1001lhcounters  259 }

pm1001lhCntCountersStop  OBJECT-TYPE
	SYNTAX EkiOnOff
	MAX-ACCESS read-write
	STATUS current
	DESCRIPTION
	"Counters stop:This OID stops all the counters"
	::= { pm1001lhcounters 260 }






--- *****************************************************
--- $$$$$$$$$$$$$$$$$$$$$$$$$$$$$$$$$$$$$$$$$$$$$$$$$$$$$
---     RMON
--- $$$$$$$$$$$$$$$$$$$$$$$$$$$$$$$$$$$$$$$$$$$$$$$$$$$$$
--- *****************************************************



--- *********************************************************
---     TABLE for the pm1001lhMonupRmonByteCnt articles
--- *********************************************************

pm1001lhMonupRmonByteCntTable OBJECT-TYPE
	SYNTAX  SEQUENCE OF Pm1001lhMonupRmonByteCntEntry
	MAX-ACCESS not-accessible
	STATUS current
	DESCRIPTION
        "
        List of pm1001lhMonupRmonByteCnt
        Article
        "
	::= { pm1001lhRmonClient 16 }


pm1001lhMonupRmonByteCntEntry OBJECT-TYPE
	SYNTAX Pm1001lhMonupRmonByteCntEntry
	MAX-ACCESS not-accessible
	STATUS current
	DESCRIPTION
        "
        Row definition for the pm1001lhMonupRmonByteCnt
        table
        "
	INDEX   { pm1001lhMonupRmonByteCntIndex }
	::= { pm1001lhMonupRmonByteCntTable 1 }


Pm1001lhMonupRmonByteCntEntry ::=
	SEQUENCE {
	pm1001lhMonupRmonByteCntIndex
		INTEGER,
	pm1001lhMonupRmonByteCntValuePortn
		Counter64,
	pm1001lhMonupRmonByteCntErrorPortn
		EkiOnOff,
	pm1001lhMonupRmonByteCntOverloadPortn
		EkiOnOff
	}


pm1001lhMonupRmonByteCntIndex OBJECT-TYPE
	SYNTAX  INTEGER(0..128)
	MAX-ACCESS  read-only
	STATUS current
	DESCRIPTION
        "
        Index definition for the pm1001lhMonupRmonByteCnt
        table
        "
	::= { pm1001lhMonupRmonByteCntEntry 1 }


pm1001lhMonupRmonByteCntValuePortn OBJECT-TYPE
	SYNTAX  Counter64
	MAX-ACCESS read-only
	STATUS current
	DESCRIPTION
        "
        Client Input Bytes :This counter
        is increased each time a data byte
        is received on the client port
          <Help>  This counter gives the
        number of bytes received on the
        client port
        "
	::= { pm1001lhMonupRmonByteCntEntry 2 }


pm1001lhMonupRmonByteCntErrorPortn OBJECT-TYPE
	SYNTAX  EkiOnOff
	MAX-ACCESS read-only
	STATUS current
	DESCRIPTION
        "
        Input Bytes Counter Error :This
        OID when set indicates the input
        Bytes counter value is invalid
         on client port
        "
	::= { pm1001lhMonupRmonByteCntEntry 3 }


pm1001lhMonupRmonByteCntOverloadPortn OBJECT-TYPE
	SYNTAX  EkiOnOff
	MAX-ACCESS read-only
	STATUS current
	DESCRIPTION
        "
        Input Bytes Counter Overload :This
        OID when set indicates an input
        Bytes counter overload on client
        port
        "
	::= { pm1001lhMonupRmonByteCntEntry 4 }


--- *********************************************************
---     TABLE for the pm1001lhMonupRmonCrcErrorCnt articles
--- *********************************************************

pm1001lhMonupRmonCrcErrorCntTable OBJECT-TYPE
	SYNTAX  SEQUENCE OF Pm1001lhMonupRmonCrcErrorCntEntry
	MAX-ACCESS not-accessible
	STATUS current
	DESCRIPTION
        "
        List of pm1001lhMonupRmonCrcErrorCnt
        Article
        "
	::= { pm1001lhRmonClient 24 }


pm1001lhMonupRmonCrcErrorCntEntry OBJECT-TYPE
	SYNTAX Pm1001lhMonupRmonCrcErrorCntEntry
	MAX-ACCESS not-accessible
	STATUS current
	DESCRIPTION
        "
        Row definition for the pm1001lhMonupRmonCrcErrorCnt
        table
        "
	INDEX   { pm1001lhMonupRmonCrcErrorCntIndex }
	::= { pm1001lhMonupRmonCrcErrorCntTable 1 }


Pm1001lhMonupRmonCrcErrorCntEntry ::=
	SEQUENCE {
	pm1001lhMonupRmonCrcErrorCntIndex
		INTEGER,
	pm1001lhMonupRmonCrcErrorCntValuePortn
		Counter64,
	pm1001lhMonupRmonCrcErrorCntErrorPortn
		EkiOnOff,
	pm1001lhMonupRmonCrcErrorCntOverloadPortn
		EkiOnOff
	}


pm1001lhMonupRmonCrcErrorCntIndex OBJECT-TYPE
	SYNTAX  INTEGER(0..128)
	MAX-ACCESS  read-only
	STATUS current
	DESCRIPTION
        "
        Index definition for the pm1001lhMonupRmonCrcErrorCnt
        table
        "
	::= { pm1001lhMonupRmonCrcErrorCntEntry 1 }


pm1001lhMonupRmonCrcErrorCntValuePortn OBJECT-TYPE
	SYNTAX  Counter64
	MAX-ACCESS read-only
	STATUS current
	DESCRIPTION
        "
        Client Input CRC Errors :This
         counter is increased each time
        a CRC error is detected on the
         client port.   <Help>  This counter
        gives the number of CRC Errors
         received on the client port
        "
	::= { pm1001lhMonupRmonCrcErrorCntEntry 2 }


pm1001lhMonupRmonCrcErrorCntErrorPortn OBJECT-TYPE
	SYNTAX  EkiOnOff
	MAX-ACCESS read-only
	STATUS current
	DESCRIPTION
        "
        Input CRC Errors Counter Error
        :This OID when set indicates the
        input CRC Errors counter value
         is invalid on client port
        "
	::= { pm1001lhMonupRmonCrcErrorCntEntry 3 }


pm1001lhMonupRmonCrcErrorCntOverloadPortn OBJECT-TYPE
	SYNTAX  EkiOnOff
	MAX-ACCESS read-only
	STATUS current
	DESCRIPTION
        "
        Input CRC Errors Counter Overload
        :This OID when set indicates an
        input CRC Errors counter overload
        on client port
        "
	::= { pm1001lhMonupRmonCrcErrorCntEntry 4 }


--- *********************************************************
---     TABLE for the pm1001lhMonupRmonPacketsCnt articles
--- *********************************************************

pm1001lhMonupRmonPacketsCntTable OBJECT-TYPE
	SYNTAX  SEQUENCE OF Pm1001lhMonupRmonPacketsCntEntry
	MAX-ACCESS not-accessible
	STATUS current
	DESCRIPTION
        "
        List of pm1001lhMonupRmonPacketsCnt
        Article
        "
	::= { pm1001lhRmonClient 32 }


pm1001lhMonupRmonPacketsCntEntry OBJECT-TYPE
	SYNTAX Pm1001lhMonupRmonPacketsCntEntry
	MAX-ACCESS not-accessible
	STATUS current
	DESCRIPTION
        "
        Row definition for the pm1001lhMonupRmonPacketsCnt
        table
        "
	INDEX   { pm1001lhMonupRmonPacketsCntIndex }
	::= { pm1001lhMonupRmonPacketsCntTable 1 }


Pm1001lhMonupRmonPacketsCntEntry ::=
	SEQUENCE {
	pm1001lhMonupRmonPacketsCntIndex
		INTEGER,
	pm1001lhMonupRmonPacketsCntValuePortn
		Counter64,
	pm1001lhMonupRmonPacketsCntErrorPortn
		EkiOnOff,
	pm1001lhMonupRmonPacketsCntOverloadPortn
		EkiOnOff
	}


pm1001lhMonupRmonPacketsCntIndex OBJECT-TYPE
	SYNTAX  INTEGER(0..128)
	MAX-ACCESS  read-only
	STATUS current
	DESCRIPTION
        "
        Index definition for the pm1001lhMonupRmonPacketsCnt
        table
        "
	::= { pm1001lhMonupRmonPacketsCntEntry 1 }


pm1001lhMonupRmonPacketsCntValuePortn OBJECT-TYPE
	SYNTAX  Counter64
	MAX-ACCESS read-only
	STATUS current
	DESCRIPTION
        "
        Packets Counter On Client Input
        :This counter is increased each
        time a packet is received on the
        client port  <Help>  This counter
        gives the number of packets received
        on the client port
        "
	::= { pm1001lhMonupRmonPacketsCntEntry 2 }


pm1001lhMonupRmonPacketsCntErrorPortn OBJECT-TYPE
	SYNTAX  EkiOnOff
	MAX-ACCESS read-only
	STATUS current
	DESCRIPTION
        "
        Input Packets Counter Error :This
        OID when set indicates the input
        Packets counter value is invalid
        on client port
        "
	::= { pm1001lhMonupRmonPacketsCntEntry 3 }


pm1001lhMonupRmonPacketsCntOverloadPortn OBJECT-TYPE
	SYNTAX  EkiOnOff
	MAX-ACCESS read-only
	STATUS current
	DESCRIPTION
        "
        Input Packets Counter Overload
        :This OID when set indicates an
        input Packets counter overload
         on client port
        "
	::= { pm1001lhMonupRmonPacketsCntEntry 4 }


--- *********************************************************
---     TABLE for the pm1001lhMonupRmonBroadcastCnt articles
--- *********************************************************

pm1001lhMonupRmonBroadcastCntTable OBJECT-TYPE
	SYNTAX  SEQUENCE OF Pm1001lhMonupRmonBroadcastCntEntry
	MAX-ACCESS not-accessible
	STATUS current
	DESCRIPTION
        "
        List of pm1001lhMonupRmonBroadcastCnt
        Article
        "
	::= { pm1001lhRmonClient 40 }


pm1001lhMonupRmonBroadcastCntEntry OBJECT-TYPE
	SYNTAX Pm1001lhMonupRmonBroadcastCntEntry
	MAX-ACCESS not-accessible
	STATUS current
	DESCRIPTION
        "
        Row definition for the pm1001lhMonupRmonBroadcastCnt
        table
        "
	INDEX   { pm1001lhMonupRmonBroadcastCntIndex }
	::= { pm1001lhMonupRmonBroadcastCntTable 1 }


Pm1001lhMonupRmonBroadcastCntEntry ::=
	SEQUENCE {
	pm1001lhMonupRmonBroadcastCntIndex
		INTEGER,
	pm1001lhMonupRmonBroadcastCntValuePortn
		Counter64,
	pm1001lhMonupRmonBroadcastCntErrorPortn
		EkiOnOff,
	pm1001lhMonupRmonBroadcastCntOverloadPortn
		EkiOnOff
	}


pm1001lhMonupRmonBroadcastCntIndex OBJECT-TYPE
	SYNTAX  INTEGER(0..128)
	MAX-ACCESS  read-only
	STATUS current
	DESCRIPTION
        "
        Index definition for the pm1001lhMonupRmonBroadcastCnt
        table
        "
	::= { pm1001lhMonupRmonBroadcastCntEntry 1 }


pm1001lhMonupRmonBroadcastCntValuePortn OBJECT-TYPE
	SYNTAX  Counter64
	MAX-ACCESS read-only
	STATUS current
	DESCRIPTION
        "
        Client Input Broadcast Packets
        :This counter is increased each
        time a broadcast packet is received
        on the client port.   <Help>  This
        counter gives the number of Broadcast
        packets received on the client
         port
        "
	::= { pm1001lhMonupRmonBroadcastCntEntry 2 }


pm1001lhMonupRmonBroadcastCntErrorPortn OBJECT-TYPE
	SYNTAX  EkiOnOff
	MAX-ACCESS read-only
	STATUS current
	DESCRIPTION
        "
        Input Broadcast Counter Error
         :This OID when set indicates the
        input Broadcast counter value is
        invalid on client port
        "
	::= { pm1001lhMonupRmonBroadcastCntEntry 3 }


pm1001lhMonupRmonBroadcastCntOverloadPortn OBJECT-TYPE
	SYNTAX  EkiOnOff
	MAX-ACCESS read-only
	STATUS current
	DESCRIPTION
        "
        Input Broadcast Counter Overload
        :This OID when set indicates an
        input Broadcast counter overload
        on client port
        "
	::= { pm1001lhMonupRmonBroadcastCntEntry 4 }


--- *********************************************************
---     TABLE for the pm1001lhMonupRmonMulticastCnt articles
--- *********************************************************

pm1001lhMonupRmonMulticastCntTable OBJECT-TYPE
	SYNTAX  SEQUENCE OF Pm1001lhMonupRmonMulticastCntEntry
	MAX-ACCESS not-accessible
	STATUS current
	DESCRIPTION
        "
        List of pm1001lhMonupRmonMulticastCnt
        Article
        "
	::= { pm1001lhRmonClient 48 }


pm1001lhMonupRmonMulticastCntEntry OBJECT-TYPE
	SYNTAX Pm1001lhMonupRmonMulticastCntEntry
	MAX-ACCESS not-accessible
	STATUS current
	DESCRIPTION
        "
        Row definition for the pm1001lhMonupRmonMulticastCnt
        table
        "
	INDEX   { pm1001lhMonupRmonMulticastCntIndex }
	::= { pm1001lhMonupRmonMulticastCntTable 1 }


Pm1001lhMonupRmonMulticastCntEntry ::=
	SEQUENCE {
	pm1001lhMonupRmonMulticastCntIndex
		INTEGER,
	pm1001lhMonupRmonMulticastCntValuePortn
		Counter64,
	pm1001lhMonupRmonMulticastCntErrorPortn
		EkiOnOff,
	pm1001lhMonupRmonMulticastCntOverloadPortn
		EkiOnOff
	}


pm1001lhMonupRmonMulticastCntIndex OBJECT-TYPE
	SYNTAX  INTEGER(0..128)
	MAX-ACCESS  read-only
	STATUS current
	DESCRIPTION
        "
        Index definition for the pm1001lhMonupRmonMulticastCnt
        table
        "
	::= { pm1001lhMonupRmonMulticastCntEntry 1 }


pm1001lhMonupRmonMulticastCntValuePortn OBJECT-TYPE
	SYNTAX  Counter64
	MAX-ACCESS read-only
	STATUS current
	DESCRIPTION
        "
        Client Input Multicast Packets
        :This counter is increased each
        time a Multicast packet is received
        on the client port.  <Help>  This
        counter gives the number of Multicast
        packets received on the client
         port
        "
	::= { pm1001lhMonupRmonMulticastCntEntry 2 }


pm1001lhMonupRmonMulticastCntErrorPortn OBJECT-TYPE
	SYNTAX  EkiOnOff
	MAX-ACCESS read-only
	STATUS current
	DESCRIPTION
        "
        Input Multicast Counter Error
         :This OID when set indicates the
        input Multicast counter value is
        invalid on client port
        "
	::= { pm1001lhMonupRmonMulticastCntEntry 3 }


pm1001lhMonupRmonMulticastCntOverloadPortn OBJECT-TYPE
	SYNTAX  EkiOnOff
	MAX-ACCESS read-only
	STATUS current
	DESCRIPTION
        "
        Input Multicast Counter Overload
        :This OID when set indicates an
        input Multicast counter overload
        on client port
        "
	::= { pm1001lhMonupRmonMulticastCntEntry 4 }


--- *********************************************************
---     TABLE for the pm1001lhMonupRmonTimerCnt articles
--- *********************************************************

pm1001lhMonupRmonTimerCntTable OBJECT-TYPE
	SYNTAX  SEQUENCE OF Pm1001lhMonupRmonTimerCntEntry
	MAX-ACCESS not-accessible
	STATUS current
	DESCRIPTION
        "
        List of pm1001lhMonupRmonTimerCnt
        Article
        "
	::= { pm1001lhRmonClient 56 }


pm1001lhMonupRmonTimerCntEntry OBJECT-TYPE
	SYNTAX Pm1001lhMonupRmonTimerCntEntry
	MAX-ACCESS not-accessible
	STATUS current
	DESCRIPTION
        "
        Row definition for the pm1001lhMonupRmonTimerCnt
        table
        "
	INDEX   { pm1001lhMonupRmonTimerCntIndex }
	::= { pm1001lhMonupRmonTimerCntTable 1 }


Pm1001lhMonupRmonTimerCntEntry ::=
	SEQUENCE {
	pm1001lhMonupRmonTimerCntIndex
		INTEGER,
	pm1001lhMonupRmonTimerCntValuePortn
		Counter64,
	pm1001lhMonupRmonTimerCntErrorPortn
		EkiOnOff,
	pm1001lhMonupRmonTimerCntOverloadPortn
		EkiOnOff
	}


pm1001lhMonupRmonTimerCntIndex OBJECT-TYPE
	SYNTAX  INTEGER(0..128)
	MAX-ACCESS  read-only
	STATUS current
	DESCRIPTION
        "
        Index definition for the pm1001lhMonupRmonTimerCnt
        table
        "
	::= { pm1001lhMonupRmonTimerCntEntry 1 }


pm1001lhMonupRmonTimerCntValuePortn OBJECT-TYPE
	SYNTAX  Counter64
	MAX-ACCESS read-only
	STATUS current
	DESCRIPTION
        "
        RMON Timer On Client Input :This
        is the timing counter dedicated
        to the upstream RMON counters.
         It is incremented every 125 us.
        "
	::= { pm1001lhMonupRmonTimerCntEntry 2 }


pm1001lhMonupRmonTimerCntErrorPortn OBJECT-TYPE
	SYNTAX  EkiOnOff
	MAX-ACCESS read-only
	STATUS current
	DESCRIPTION
        "
        Input RMON Timer Error :This OID
        when set indicates the input RMON
        timer is invalid on client port
        "
	::= { pm1001lhMonupRmonTimerCntEntry 3 }


pm1001lhMonupRmonTimerCntOverloadPortn OBJECT-TYPE
	SYNTAX  EkiOnOff
	MAX-ACCESS read-only
	STATUS current
	DESCRIPTION
        "
        Input RMON Timer Overload :This
        OID when set indicates an input
        RMON timer overload on client port
        "
	::= { pm1001lhMonupRmonTimerCntEntry 4 }


--- *********************************************************
---     TABLE for the pm1001lhMonupRmonPauseFrameCnt articles
--- *********************************************************

pm1001lhMonupRmonPauseFrameCntTable OBJECT-TYPE
	SYNTAX  SEQUENCE OF Pm1001lhMonupRmonPauseFrameCntEntry
	MAX-ACCESS not-accessible
	STATUS current
	DESCRIPTION
        "
        List of pm1001lhMonupRmonPauseFrameCnt
        Article
        "
	::= { pm1001lhRmonClient 64 }


pm1001lhMonupRmonPauseFrameCntEntry OBJECT-TYPE
	SYNTAX Pm1001lhMonupRmonPauseFrameCntEntry
	MAX-ACCESS not-accessible
	STATUS current
	DESCRIPTION
        "
        Row definition for the pm1001lhMonupRmonPauseFrameCnt
        table
        "
	INDEX   { pm1001lhMonupRmonPauseFrameCntIndex }
	::= { pm1001lhMonupRmonPauseFrameCntTable 1 }


Pm1001lhMonupRmonPauseFrameCntEntry ::=
	SEQUENCE {
	pm1001lhMonupRmonPauseFrameCntIndex
		INTEGER,
	pm1001lhMonupRmonPauseFrameCntValuePortn
		Counter64,
	pm1001lhMonupRmonPauseFrameCntErrorPortn
		EkiOnOff,
	pm1001lhMonupRmonPauseFrameCntOverloadPortn
		EkiOnOff
	}


pm1001lhMonupRmonPauseFrameCntIndex OBJECT-TYPE
	SYNTAX  INTEGER(0..128)
	MAX-ACCESS  read-only
	STATUS current
	DESCRIPTION
        "
        Index definition for the pm1001lhMonupRmonPauseFrameCnt
        table
        "
	::= { pm1001lhMonupRmonPauseFrameCntEntry 1 }


pm1001lhMonupRmonPauseFrameCntValuePortn OBJECT-TYPE
	SYNTAX  Counter64
	MAX-ACCESS read-only
	STATUS current
	DESCRIPTION
        "
        Pause Counter On Client Input
         :This counter is increased each
        time a Pause frame is received
         on the client port
        "
	::= { pm1001lhMonupRmonPauseFrameCntEntry 2 }


pm1001lhMonupRmonPauseFrameCntErrorPortn OBJECT-TYPE
	SYNTAX  EkiOnOff
	MAX-ACCESS read-only
	STATUS current
	DESCRIPTION
        "
        Input Pause Counter Error :This
        OID when set indicates the input
        Pause counter value is invalid
         on client port
        "
	::= { pm1001lhMonupRmonPauseFrameCntEntry 3 }


pm1001lhMonupRmonPauseFrameCntOverloadPortn OBJECT-TYPE
	SYNTAX  EkiOnOff
	MAX-ACCESS read-only
	STATUS current
	DESCRIPTION
        "
        Input Pause Counter Overload :This
        OID when set indicates an input
        Pause counter overload on client
        port
        "
	::= { pm1001lhMonupRmonPauseFrameCntEntry 4 }


--- *********************************************************
---     TABLE for the pm1001lhMonupRmonDropFrameCnt articles
--- *********************************************************

pm1001lhMonupRmonDropFrameCntTable OBJECT-TYPE
	SYNTAX  SEQUENCE OF Pm1001lhMonupRmonDropFrameCntEntry
	MAX-ACCESS not-accessible
	STATUS current
	DESCRIPTION
        "
        List of pm1001lhMonupRmonDropFrameCnt
        Article
        "
	::= { pm1001lhRmonClient 72 }


pm1001lhMonupRmonDropFrameCntEntry OBJECT-TYPE
	SYNTAX Pm1001lhMonupRmonDropFrameCntEntry
	MAX-ACCESS not-accessible
	STATUS current
	DESCRIPTION
        "
        Row definition for the pm1001lhMonupRmonDropFrameCnt
        table
        "
	INDEX   { pm1001lhMonupRmonDropFrameCntIndex }
	::= { pm1001lhMonupRmonDropFrameCntTable 1 }


Pm1001lhMonupRmonDropFrameCntEntry ::=
	SEQUENCE {
	pm1001lhMonupRmonDropFrameCntIndex
		INTEGER,
	pm1001lhMonupRmonDropFrameCntValuePortn
		Counter64,
	pm1001lhMonupRmonDropFrameCntErrorPortn
		EkiOnOff,
	pm1001lhMonupRmonDropFrameCntOverloadPortn
		EkiOnOff
	}


pm1001lhMonupRmonDropFrameCntIndex OBJECT-TYPE
	SYNTAX  INTEGER(0..128)
	MAX-ACCESS  read-only
	STATUS current
	DESCRIPTION
        "
        Index definition for the pm1001lhMonupRmonDropFrameCnt
        table
        "
	::= { pm1001lhMonupRmonDropFrameCntEntry 1 }


pm1001lhMonupRmonDropFrameCntValuePortn OBJECT-TYPE
	SYNTAX  Counter64
	MAX-ACCESS read-only
	STATUS current
	DESCRIPTION
        "
        Drop Counter On Client Input :This
        counter is increased each time
         a Frame is dropped on the input
        client port
        "
	::= { pm1001lhMonupRmonDropFrameCntEntry 2 }


pm1001lhMonupRmonDropFrameCntErrorPortn OBJECT-TYPE
	SYNTAX  EkiOnOff
	MAX-ACCESS read-only
	STATUS current
	DESCRIPTION
        "
        Input Drop Counter Error :This
        OID when set indicates the input
        Drop counter value is invalid on
        client port
        "
	::= { pm1001lhMonupRmonDropFrameCntEntry 3 }


pm1001lhMonupRmonDropFrameCntOverloadPortn OBJECT-TYPE
	SYNTAX  EkiOnOff
	MAX-ACCESS read-only
	STATUS current
	DESCRIPTION
        "
        Input Drop Counter Overload :This
        OID when set indicates an input
        Drop counter overload on client
        port
        "
	::= { pm1001lhMonupRmonDropFrameCntEntry 4 }


--- *********************************************************
---     TABLE for the pm1001lhMonupRmonBitsCnt articles
--- *********************************************************

pm1001lhMonupRmonBitsCntTable OBJECT-TYPE
	SYNTAX  SEQUENCE OF Pm1001lhMonupRmonBitsCntEntry
	MAX-ACCESS not-accessible
	STATUS current
	DESCRIPTION
        "
        List of pm1001lhMonupRmonBitsCnt
        Article
        "
	::= { pm1001lhRmonClient 80 }


pm1001lhMonupRmonBitsCntEntry OBJECT-TYPE
	SYNTAX Pm1001lhMonupRmonBitsCntEntry
	MAX-ACCESS not-accessible
	STATUS current
	DESCRIPTION
        "
        Row definition for the pm1001lhMonupRmonBitsCnt
        table
        "
	INDEX   { pm1001lhMonupRmonBitsCntIndex }
	::= { pm1001lhMonupRmonBitsCntTable 1 }


Pm1001lhMonupRmonBitsCntEntry ::=
	SEQUENCE {
	pm1001lhMonupRmonBitsCntIndex
		INTEGER,
	pm1001lhMonupRmonBitsCntValuePortn
		Counter64,
	pm1001lhMonupRmonBitsCntErrorPortn
		EkiOnOff,
	pm1001lhMonupRmonBitsCntOverloadPortn
		EkiOnOff
	}


pm1001lhMonupRmonBitsCntIndex OBJECT-TYPE
	SYNTAX  INTEGER(0..128)
	MAX-ACCESS  read-only
	STATUS current
	DESCRIPTION
        "
        Index definition for the pm1001lhMonupRmonBitsCnt
        table
        "
	::= { pm1001lhMonupRmonBitsCntEntry 1 }


pm1001lhMonupRmonBitsCntValuePortn OBJECT-TYPE
	SYNTAX  Counter64
	MAX-ACCESS read-only
	STATUS current
	DESCRIPTION
        "
        Bits Counter On Client Input :This
        counter is increased each time
         a bit is received on the input
        client port
        "
	::= { pm1001lhMonupRmonBitsCntEntry 2 }


pm1001lhMonupRmonBitsCntErrorPortn OBJECT-TYPE
	SYNTAX  EkiOnOff
	MAX-ACCESS read-only
	STATUS current
	DESCRIPTION
        "
        Input Bits Counter Error :This
        OID when set indicates the input
        Bits counter value is invalid on
        client port
        "
	::= { pm1001lhMonupRmonBitsCntEntry 3 }


pm1001lhMonupRmonBitsCntOverloadPortn OBJECT-TYPE
	SYNTAX  EkiOnOff
	MAX-ACCESS read-only
	STATUS current
	DESCRIPTION
        "
        Input Bits Counter Overload :This
        OID when set indicates an input
        Bits counter overload on client
        port
        "
	::= { pm1001lhMonupRmonBitsCntEntry 4 }


--- *********************************************************
---     TABLE for the pm1001lhMonupRmonUnicastCnt articles
--- *********************************************************

pm1001lhMonupRmonUnicastCntTable OBJECT-TYPE
	SYNTAX  SEQUENCE OF Pm1001lhMonupRmonUnicastCntEntry
	MAX-ACCESS not-accessible
	STATUS current
	DESCRIPTION
        "
        List of pm1001lhMonupRmonUnicastCnt
        Article
        "
	::= { pm1001lhRmonClient 88 }


pm1001lhMonupRmonUnicastCntEntry OBJECT-TYPE
	SYNTAX Pm1001lhMonupRmonUnicastCntEntry
	MAX-ACCESS not-accessible
	STATUS current
	DESCRIPTION
        "
        Row definition for the pm1001lhMonupRmonUnicastCnt
        table
        "
	INDEX   { pm1001lhMonupRmonUnicastCntIndex }
	::= { pm1001lhMonupRmonUnicastCntTable 1 }


Pm1001lhMonupRmonUnicastCntEntry ::=
	SEQUENCE {
	pm1001lhMonupRmonUnicastCntIndex
		INTEGER,
	pm1001lhMonupRmonUnicastCntValuePortn
		Counter64,
	pm1001lhMonupRmonUnicastCntErrorPortn
		EkiOnOff,
	pm1001lhMonupRmonUnicastCntOverloadPortn
		EkiOnOff
	}


pm1001lhMonupRmonUnicastCntIndex OBJECT-TYPE
	SYNTAX  INTEGER(0..128)
	MAX-ACCESS  read-only
	STATUS current
	DESCRIPTION
        "
        Index definition for the pm1001lhMonupRmonUnicastCnt
        table
        "
	::= { pm1001lhMonupRmonUnicastCntEntry 1 }


pm1001lhMonupRmonUnicastCntValuePortn OBJECT-TYPE
	SYNTAX  Counter64
	MAX-ACCESS read-only
	STATUS current
	DESCRIPTION
        "
        Client Input Unicast Packets :This
        counter is increased each time
         a Unicast packet is received on
        client input  <Help>  This counter
        gives the number of Unicast packets
        received on the client input port
        "
	::= { pm1001lhMonupRmonUnicastCntEntry 2 }


pm1001lhMonupRmonUnicastCntErrorPortn OBJECT-TYPE
	SYNTAX  EkiOnOff
	MAX-ACCESS read-only
	STATUS current
	DESCRIPTION
        "
        Input Unicast Counter Error :This
        OID when set indicates the input
        Drop counter value is invalid on
        client port
        "
	::= { pm1001lhMonupRmonUnicastCntEntry 3 }


pm1001lhMonupRmonUnicastCntOverloadPortn OBJECT-TYPE
	SYNTAX  EkiOnOff
	MAX-ACCESS read-only
	STATUS current
	DESCRIPTION
        "
        Input Unicast Counter Overload
        :This OID when set indicates an
        input Drop counter overload on
         client port
        "
	::= { pm1001lhMonupRmonUnicastCntEntry 4 }


--- *********************************************************
---     TABLE for the pm1001lhMonupRmonNonUnicastCnt articles
--- *********************************************************

pm1001lhMonupRmonNonUnicastCntTable OBJECT-TYPE
	SYNTAX  SEQUENCE OF Pm1001lhMonupRmonNonUnicastCntEntry
	MAX-ACCESS not-accessible
	STATUS current
	DESCRIPTION
        "
        List of pm1001lhMonupRmonNonUnicastCnt
        Article
        "
	::= { pm1001lhRmonClient 96 }


pm1001lhMonupRmonNonUnicastCntEntry OBJECT-TYPE
	SYNTAX Pm1001lhMonupRmonNonUnicastCntEntry
	MAX-ACCESS not-accessible
	STATUS current
	DESCRIPTION
        "
        Row definition for the pm1001lhMonupRmonNonUnicastCnt
        table
        "
	INDEX   { pm1001lhMonupRmonNonUnicastCntIndex }
	::= { pm1001lhMonupRmonNonUnicastCntTable 1 }


Pm1001lhMonupRmonNonUnicastCntEntry ::=
	SEQUENCE {
	pm1001lhMonupRmonNonUnicastCntIndex
		INTEGER,
	pm1001lhMonupRmonNonUnicastCntValuePortn
		Counter64,
	pm1001lhMonupRmonNonUnicastCntErrorPortn
		EkiOnOff,
	pm1001lhMonupRmonNonUnicastCntOverloadPortn
		EkiOnOff
	}


pm1001lhMonupRmonNonUnicastCntIndex OBJECT-TYPE
	SYNTAX  INTEGER(0..128)
	MAX-ACCESS  read-only
	STATUS current
	DESCRIPTION
        "
        Index definition for the pm1001lhMonupRmonNonUnicastCnt
        table
        "
	::= { pm1001lhMonupRmonNonUnicastCntEntry 1 }


pm1001lhMonupRmonNonUnicastCntValuePortn OBJECT-TYPE
	SYNTAX  Counter64
	MAX-ACCESS read-only
	STATUS current
	DESCRIPTION
        "
        Client Input Not Unicast Packets
        :This counter is increased each
        time a Non Unicast packet is received
        on client input    <Help>  This
        counter gives the number of Non
        Unicast packets received on the
        client input port
        "
	::= { pm1001lhMonupRmonNonUnicastCntEntry 2 }


pm1001lhMonupRmonNonUnicastCntErrorPortn OBJECT-TYPE
	SYNTAX  EkiOnOff
	MAX-ACCESS read-only
	STATUS current
	DESCRIPTION
        "
        Input Non Unicast Counter Error
        :This OID when set indicates the
        input Bits counter value is invalid
        on client port
        "
	::= { pm1001lhMonupRmonNonUnicastCntEntry 3 }


pm1001lhMonupRmonNonUnicastCntOverloadPortn OBJECT-TYPE
	SYNTAX  EkiOnOff
	MAX-ACCESS read-only
	STATUS current
	DESCRIPTION
        "
        Input Non Unicast Counter Overload
        :This OID when set indicates an
        input Bits counter overload on
         client port
        "
	::= { pm1001lhMonupRmonNonUnicastCntEntry 4 }


--- *********************************************************
---     TABLE for the pm1001lhMondwRmonByteCnt articles
--- *********************************************************

pm1001lhMondwRmonByteCntTable OBJECT-TYPE
	SYNTAX  SEQUENCE OF Pm1001lhMondwRmonByteCntEntry
	MAX-ACCESS not-accessible
	STATUS current
	DESCRIPTION
        "
        List of pm1001lhMondwRmonByteCnt
        Article
        "
	::= { pm1001lhRmonClient 112 }


pm1001lhMondwRmonByteCntEntry OBJECT-TYPE
	SYNTAX Pm1001lhMondwRmonByteCntEntry
	MAX-ACCESS not-accessible
	STATUS current
	DESCRIPTION
        "
        Row definition for the pm1001lhMondwRmonByteCnt
        table
        "
	INDEX   { pm1001lhMondwRmonByteCntIndex }
	::= { pm1001lhMondwRmonByteCntTable 1 }


Pm1001lhMondwRmonByteCntEntry ::=
	SEQUENCE {
	pm1001lhMondwRmonByteCntIndex
		INTEGER,
	pm1001lhMondwRmonByteCntValuePortn
		Counter64,
	pm1001lhMondwRmonByteCntErrorPortn
		EkiOnOff,
	pm1001lhMondwRmonByteCntOverloadPortn
		EkiOnOff
	}


pm1001lhMondwRmonByteCntIndex OBJECT-TYPE
	SYNTAX  INTEGER(0..128)
	MAX-ACCESS  read-only
	STATUS current
	DESCRIPTION
        "
        Index definition for the pm1001lhMondwRmonByteCnt
        table
        "
	::= { pm1001lhMondwRmonByteCntEntry 1 }


pm1001lhMondwRmonByteCntValuePortn OBJECT-TYPE
	SYNTAX  Counter64
	MAX-ACCESS read-only
	STATUS current
	DESCRIPTION
        "
        Client Output Bytes :This counter
        is increased each time a data byte
        is transmitted on the client port.
         <Help>  This counter gives the
        number of bytes transmitted on
         the client port
        "
	::= { pm1001lhMondwRmonByteCntEntry 2 }


pm1001lhMondwRmonByteCntErrorPortn OBJECT-TYPE
	SYNTAX  EkiOnOff
	MAX-ACCESS read-only
	STATUS current
	DESCRIPTION
        "
        Output Bytes Counter Error :This
        OID when set indicates the output
        Bytes counter value is invalid
         on client port
        "
	::= { pm1001lhMondwRmonByteCntEntry 3 }


pm1001lhMondwRmonByteCntOverloadPortn OBJECT-TYPE
	SYNTAX  EkiOnOff
	MAX-ACCESS read-only
	STATUS current
	DESCRIPTION
        "
        Output Bytes Counter Overload
         :This OID when set indicates an
        output Bytes counter overload on
        client port
        "
	::= { pm1001lhMondwRmonByteCntEntry 4 }


--- *********************************************************
---     TABLE for the pm1001lhMondwRmonCrcErrorCnt articles
--- *********************************************************

pm1001lhMondwRmonCrcErrorCntTable OBJECT-TYPE
	SYNTAX  SEQUENCE OF Pm1001lhMondwRmonCrcErrorCntEntry
	MAX-ACCESS not-accessible
	STATUS current
	DESCRIPTION
        "
        List of pm1001lhMondwRmonCrcErrorCnt
        Article
        "
	::= { pm1001lhRmonClient 120 }


pm1001lhMondwRmonCrcErrorCntEntry OBJECT-TYPE
	SYNTAX Pm1001lhMondwRmonCrcErrorCntEntry
	MAX-ACCESS not-accessible
	STATUS current
	DESCRIPTION
        "
        Row definition for the pm1001lhMondwRmonCrcErrorCnt
        table
        "
	INDEX   { pm1001lhMondwRmonCrcErrorCntIndex }
	::= { pm1001lhMondwRmonCrcErrorCntTable 1 }


Pm1001lhMondwRmonCrcErrorCntEntry ::=
	SEQUENCE {
	pm1001lhMondwRmonCrcErrorCntIndex
		INTEGER,
	pm1001lhMondwRmonCrcErrorCntValuePortn
		Counter64,
	pm1001lhMondwRmonCrcErrorCntErrorPortn
		EkiOnOff,
	pm1001lhMondwRmonCrcErrorCntOverloadPortn
		EkiOnOff
	}


pm1001lhMondwRmonCrcErrorCntIndex OBJECT-TYPE
	SYNTAX  INTEGER(0..128)
	MAX-ACCESS  read-only
	STATUS current
	DESCRIPTION
        "
        Index definition for the pm1001lhMondwRmonCrcErrorCnt
        table
        "
	::= { pm1001lhMondwRmonCrcErrorCntEntry 1 }


pm1001lhMondwRmonCrcErrorCntValuePortn OBJECT-TYPE
	SYNTAX  Counter64
	MAX-ACCESS read-only
	STATUS current
	DESCRIPTION
        "
        CRC Errors Counter On Client Output
        :This counter is increased each
        time a CRC error is detected on
        the output client port  <Help>
          This counter gives the number
        of CRC Errors transmitted on the
        client port
        "
	::= { pm1001lhMondwRmonCrcErrorCntEntry 2 }


pm1001lhMondwRmonCrcErrorCntErrorPortn OBJECT-TYPE
	SYNTAX  EkiOnOff
	MAX-ACCESS read-only
	STATUS current
	DESCRIPTION
        "
        Output CRC Errors Counter Error
        :This OID when set indicates the
        output CRC Errors counter value
        is invalid on client port
        "
	::= { pm1001lhMondwRmonCrcErrorCntEntry 3 }


pm1001lhMondwRmonCrcErrorCntOverloadPortn OBJECT-TYPE
	SYNTAX  EkiOnOff
	MAX-ACCESS read-only
	STATUS current
	DESCRIPTION
        "
        Output CRC Errors Counter Overload
        :This OID when set indicates an
        output CRC Errors counter overload
        on client port
        "
	::= { pm1001lhMondwRmonCrcErrorCntEntry 4 }


--- *********************************************************
---     TABLE for the pm1001lhMondwRmonPacketsCnt articles
--- *********************************************************

pm1001lhMondwRmonPacketsCntTable OBJECT-TYPE
	SYNTAX  SEQUENCE OF Pm1001lhMondwRmonPacketsCntEntry
	MAX-ACCESS not-accessible
	STATUS current
	DESCRIPTION
        "
        List of pm1001lhMondwRmonPacketsCnt
        Article
        "
	::= { pm1001lhRmonClient 128 }


pm1001lhMondwRmonPacketsCntEntry OBJECT-TYPE
	SYNTAX Pm1001lhMondwRmonPacketsCntEntry
	MAX-ACCESS not-accessible
	STATUS current
	DESCRIPTION
        "
        Row definition for the pm1001lhMondwRmonPacketsCnt
        table
        "
	INDEX   { pm1001lhMondwRmonPacketsCntIndex }
	::= { pm1001lhMondwRmonPacketsCntTable 1 }


Pm1001lhMondwRmonPacketsCntEntry ::=
	SEQUENCE {
	pm1001lhMondwRmonPacketsCntIndex
		INTEGER,
	pm1001lhMondwRmonPacketsCntValuePortn
		Counter64,
	pm1001lhMondwRmonPacketsCntErrorPortn
		EkiOnOff,
	pm1001lhMondwRmonPacketsCntOverloadPortn
		EkiOnOff
	}


pm1001lhMondwRmonPacketsCntIndex OBJECT-TYPE
	SYNTAX  INTEGER(0..128)
	MAX-ACCESS  read-only
	STATUS current
	DESCRIPTION
        "
        Index definition for the pm1001lhMondwRmonPacketsCnt
        table
        "
	::= { pm1001lhMondwRmonPacketsCntEntry 1 }


pm1001lhMondwRmonPacketsCntValuePortn OBJECT-TYPE
	SYNTAX  Counter64
	MAX-ACCESS read-only
	STATUS current
	DESCRIPTION
        "
        Packets Counter On Client Output
        :This counter is increased each
        time a packet is transmitted on
        the client port.  <Help>  This
         counter gives the number of packets
        transmitted on the client port
        "
	::= { pm1001lhMondwRmonPacketsCntEntry 2 }


pm1001lhMondwRmonPacketsCntErrorPortn OBJECT-TYPE
	SYNTAX  EkiOnOff
	MAX-ACCESS read-only
	STATUS current
	DESCRIPTION
        "
        Output Packets Counter Error :This
        OID when set indicates the output
        Packets counter value is invalid
        on client port
        "
	::= { pm1001lhMondwRmonPacketsCntEntry 3 }


pm1001lhMondwRmonPacketsCntOverloadPortn OBJECT-TYPE
	SYNTAX  EkiOnOff
	MAX-ACCESS read-only
	STATUS current
	DESCRIPTION
        "
        Output Packets Counter Overload
        :This OID when set indicates an
        output Packets counter overload
        on client port
        "
	::= { pm1001lhMondwRmonPacketsCntEntry 4 }


--- *********************************************************
---     TABLE for the pm1001lhMondwRmonBroadcastCnt articles
--- *********************************************************

pm1001lhMondwRmonBroadcastCntTable OBJECT-TYPE
	SYNTAX  SEQUENCE OF Pm1001lhMondwRmonBroadcastCntEntry
	MAX-ACCESS not-accessible
	STATUS current
	DESCRIPTION
        "
        List of pm1001lhMondwRmonBroadcastCnt
        Article
        "
	::= { pm1001lhRmonClient 136 }


pm1001lhMondwRmonBroadcastCntEntry OBJECT-TYPE
	SYNTAX Pm1001lhMondwRmonBroadcastCntEntry
	MAX-ACCESS not-accessible
	STATUS current
	DESCRIPTION
        "
        Row definition for the pm1001lhMondwRmonBroadcastCnt
        table
        "
	INDEX   { pm1001lhMondwRmonBroadcastCntIndex }
	::= { pm1001lhMondwRmonBroadcastCntTable 1 }


Pm1001lhMondwRmonBroadcastCntEntry ::=
	SEQUENCE {
	pm1001lhMondwRmonBroadcastCntIndex
		INTEGER,
	pm1001lhMondwRmonBroadcastCntValuePortn
		Counter64,
	pm1001lhMondwRmonBroadcastCntErrorPortn
		EkiOnOff,
	pm1001lhMondwRmonBroadcastCntOverloadPortn
		EkiOnOff
	}


pm1001lhMondwRmonBroadcastCntIndex OBJECT-TYPE
	SYNTAX  INTEGER(0..128)
	MAX-ACCESS  read-only
	STATUS current
	DESCRIPTION
        "
        Index definition for the pm1001lhMondwRmonBroadcastCnt
        table
        "
	::= { pm1001lhMondwRmonBroadcastCntEntry 1 }


pm1001lhMondwRmonBroadcastCntValuePortn OBJECT-TYPE
	SYNTAX  Counter64
	MAX-ACCESS read-only
	STATUS current
	DESCRIPTION
        "
        Client Output Broadcast Packets
        :This counter is increased each
        time a broadcast packet is transmitted
        on the client port.  <Help>  This
        counter gives the number of Broadcast
        packets transmitted on the client
        port
        "
	::= { pm1001lhMondwRmonBroadcastCntEntry 2 }


pm1001lhMondwRmonBroadcastCntErrorPortn OBJECT-TYPE
	SYNTAX  EkiOnOff
	MAX-ACCESS read-only
	STATUS current
	DESCRIPTION
        "
        Output Broadcast Counter Error
        :This OID when set indicates the
        output Broadcast counter value
         is invalid on client port
        "
	::= { pm1001lhMondwRmonBroadcastCntEntry 3 }


pm1001lhMondwRmonBroadcastCntOverloadPortn OBJECT-TYPE
	SYNTAX  EkiOnOff
	MAX-ACCESS read-only
	STATUS current
	DESCRIPTION
        "
        Output Broadcast Counter Overload
        :This OID when set indicates an
        output Broadcast counter overload
        on client port
        "
	::= { pm1001lhMondwRmonBroadcastCntEntry 4 }


--- *********************************************************
---     TABLE for the pm1001lhMondwRmonMulticastCnt articles
--- *********************************************************

pm1001lhMondwRmonMulticastCntTable OBJECT-TYPE
	SYNTAX  SEQUENCE OF Pm1001lhMondwRmonMulticastCntEntry
	MAX-ACCESS not-accessible
	STATUS current
	DESCRIPTION
        "
        List of pm1001lhMondwRmonMulticastCnt
        Article
        "
	::= { pm1001lhRmonClient 144 }


pm1001lhMondwRmonMulticastCntEntry OBJECT-TYPE
	SYNTAX Pm1001lhMondwRmonMulticastCntEntry
	MAX-ACCESS not-accessible
	STATUS current
	DESCRIPTION
        "
        Row definition for the pm1001lhMondwRmonMulticastCnt
        table
        "
	INDEX   { pm1001lhMondwRmonMulticastCntIndex }
	::= { pm1001lhMondwRmonMulticastCntTable 1 }


Pm1001lhMondwRmonMulticastCntEntry ::=
	SEQUENCE {
	pm1001lhMondwRmonMulticastCntIndex
		INTEGER,
	pm1001lhMondwRmonMulticastCntValuePortn
		Counter64,
	pm1001lhMondwRmonMulticastCntErrorPortn
		EkiOnOff,
	pm1001lhMondwRmonMulticastCntOverloadPortn
		EkiOnOff
	}


pm1001lhMondwRmonMulticastCntIndex OBJECT-TYPE
	SYNTAX  INTEGER(0..128)
	MAX-ACCESS  read-only
	STATUS current
	DESCRIPTION
        "
        Index definition for the pm1001lhMondwRmonMulticastCnt
        table
        "
	::= { pm1001lhMondwRmonMulticastCntEntry 1 }


pm1001lhMondwRmonMulticastCntValuePortn OBJECT-TYPE
	SYNTAX  Counter64
	MAX-ACCESS read-only
	STATUS current
	DESCRIPTION
        "
        Client Output Multicast Packets
        :This counter is increased each
        time a Multicast packet is tra,smitted
        on the client port.  <Help>  This
        counter gives the number of Multicast
        packets transmitted on the client
        port
        "
	::= { pm1001lhMondwRmonMulticastCntEntry 2 }


pm1001lhMondwRmonMulticastCntErrorPortn OBJECT-TYPE
	SYNTAX  EkiOnOff
	MAX-ACCESS read-only
	STATUS current
	DESCRIPTION
        "
        Output Multicast Counter Error
        :This OID when set indicates the
        output Multicast counter value
         is invalid on client port
        "
	::= { pm1001lhMondwRmonMulticastCntEntry 3 }


pm1001lhMondwRmonMulticastCntOverloadPortn OBJECT-TYPE
	SYNTAX  EkiOnOff
	MAX-ACCESS read-only
	STATUS current
	DESCRIPTION
        "
        Output Multicast Counter Overload
        :This OID when set indicates an
        output Multicast counter overload
        on client port
        "
	::= { pm1001lhMondwRmonMulticastCntEntry 4 }


--- *********************************************************
---     TABLE for the pm1001lhMondwRmonPauseFrameCnt articles
--- *********************************************************

pm1001lhMondwRmonPauseFrameCntTable OBJECT-TYPE
	SYNTAX  SEQUENCE OF Pm1001lhMondwRmonPauseFrameCntEntry
	MAX-ACCESS not-accessible
	STATUS current
	DESCRIPTION
        "
        List of pm1001lhMondwRmonPauseFrameCnt
        Article
        "
	::= { pm1001lhRmonClient 152 }


pm1001lhMondwRmonPauseFrameCntEntry OBJECT-TYPE
	SYNTAX Pm1001lhMondwRmonPauseFrameCntEntry
	MAX-ACCESS not-accessible
	STATUS current
	DESCRIPTION
        "
        Row definition for the pm1001lhMondwRmonPauseFrameCnt
        table
        "
	INDEX   { pm1001lhMondwRmonPauseFrameCntIndex }
	::= { pm1001lhMondwRmonPauseFrameCntTable 1 }


Pm1001lhMondwRmonPauseFrameCntEntry ::=
	SEQUENCE {
	pm1001lhMondwRmonPauseFrameCntIndex
		INTEGER,
	pm1001lhMondwRmonPauseFrameCntValuePortn
		Counter64,
	pm1001lhMondwRmonPauseFrameCntErrorPortn
		EkiOnOff,
	pm1001lhMondwRmonPauseFrameCntOverloadPortn
		EkiOnOff
	}


pm1001lhMondwRmonPauseFrameCntIndex OBJECT-TYPE
	SYNTAX  INTEGER(0..128)
	MAX-ACCESS  read-only
	STATUS current
	DESCRIPTION
        "
        Index definition for the pm1001lhMondwRmonPauseFrameCnt
        table
        "
	::= { pm1001lhMondwRmonPauseFrameCntEntry 1 }


pm1001lhMondwRmonPauseFrameCntValuePortn OBJECT-TYPE
	SYNTAX  Counter64
	MAX-ACCESS read-only
	STATUS current
	DESCRIPTION
        "
        Pause Counter On Client Output
        :This counter is increased each
        time a Pause frame is generated
        by the PM on the client port
        "
	::= { pm1001lhMondwRmonPauseFrameCntEntry 2 }


pm1001lhMondwRmonPauseFrameCntErrorPortn OBJECT-TYPE
	SYNTAX  EkiOnOff
	MAX-ACCESS read-only
	STATUS current
	DESCRIPTION
        "
        Output Pause Counter Error :This
        OID when set indicates the output
        Pause counter value is invalid
         on client port
        "
	::= { pm1001lhMondwRmonPauseFrameCntEntry 3 }


pm1001lhMondwRmonPauseFrameCntOverloadPortn OBJECT-TYPE
	SYNTAX  EkiOnOff
	MAX-ACCESS read-only
	STATUS current
	DESCRIPTION
        "
        Output Pause Counter Overload
         :This OID when set indicates an
        output Pause counter overload on
        client port
        "
	::= { pm1001lhMondwRmonPauseFrameCntEntry 4 }


--- *********************************************************
---     TABLE for the pm1001lhMondwRmonTimerCnt articles
--- *********************************************************

pm1001lhMondwRmonTimerCntTable OBJECT-TYPE
	SYNTAX  SEQUENCE OF Pm1001lhMondwRmonTimerCntEntry
	MAX-ACCESS not-accessible
	STATUS current
	DESCRIPTION
        "
        List of pm1001lhMondwRmonTimerCnt
        Article
        "
	::= { pm1001lhRmonClient 160 }


pm1001lhMondwRmonTimerCntEntry OBJECT-TYPE
	SYNTAX Pm1001lhMondwRmonTimerCntEntry
	MAX-ACCESS not-accessible
	STATUS current
	DESCRIPTION
        "
        Row definition for the pm1001lhMondwRmonTimerCnt
        table
        "
	INDEX   { pm1001lhMondwRmonTimerCntIndex }
	::= { pm1001lhMondwRmonTimerCntTable 1 }


Pm1001lhMondwRmonTimerCntEntry ::=
	SEQUENCE {
	pm1001lhMondwRmonTimerCntIndex
		INTEGER,
	pm1001lhMondwRmonTimerCntValuePortn
		Counter64,
	pm1001lhMondwRmonTimerCntErrorPortn
		EkiOnOff,
	pm1001lhMondwRmonTimerCntOverloadPortn
		EkiOnOff
	}


pm1001lhMondwRmonTimerCntIndex OBJECT-TYPE
	SYNTAX  INTEGER(0..128)
	MAX-ACCESS  read-only
	STATUS current
	DESCRIPTION
        "
        Index definition for the pm1001lhMondwRmonTimerCnt
        table
        "
	::= { pm1001lhMondwRmonTimerCntEntry 1 }


pm1001lhMondwRmonTimerCntValuePortn OBJECT-TYPE
	SYNTAX  Counter64
	MAX-ACCESS read-only
	STATUS current
	DESCRIPTION
        "
        RMON Timer On Client Output :This
        is the timing counter dedicated
        to the downstream RMON counters.
        It is incremented every 125 us.
        "
	::= { pm1001lhMondwRmonTimerCntEntry 2 }


pm1001lhMondwRmonTimerCntErrorPortn OBJECT-TYPE
	SYNTAX  EkiOnOff
	MAX-ACCESS read-only
	STATUS current
	DESCRIPTION
        "
        Output RMON Timer Error :This
         OID when set indicates the output
        RMON timer is invalid on client
        port
        "
	::= { pm1001lhMondwRmonTimerCntEntry 3 }


pm1001lhMondwRmonTimerCntOverloadPortn OBJECT-TYPE
	SYNTAX  EkiOnOff
	MAX-ACCESS read-only
	STATUS current
	DESCRIPTION
        "
        Output RMON Timer Overload :This
        OID when set indicates an output
        RMON timer overload on client port
        "
	::= { pm1001lhMondwRmonTimerCntEntry 4 }


--- *********************************************************
---     TABLE for the pm1001lhMondwRmonBitsCnt articles
--- *********************************************************

pm1001lhMondwRmonBitsCntTable OBJECT-TYPE
	SYNTAX  SEQUENCE OF Pm1001lhMondwRmonBitsCntEntry
	MAX-ACCESS not-accessible
	STATUS current
	DESCRIPTION
        "
        List of pm1001lhMondwRmonBitsCnt
        Article
        "
	::= { pm1001lhRmonClient 168 }


pm1001lhMondwRmonBitsCntEntry OBJECT-TYPE
	SYNTAX Pm1001lhMondwRmonBitsCntEntry
	MAX-ACCESS not-accessible
	STATUS current
	DESCRIPTION
        "
        Row definition for the pm1001lhMondwRmonBitsCnt
        table
        "
	INDEX   { pm1001lhMondwRmonBitsCntIndex }
	::= { pm1001lhMondwRmonBitsCntTable 1 }


Pm1001lhMondwRmonBitsCntEntry ::=
	SEQUENCE {
	pm1001lhMondwRmonBitsCntIndex
		INTEGER,
	pm1001lhMondwRmonBitsCntValuePortn
		Counter64,
	pm1001lhMondwRmonBitsCntErrorPortn
		EkiOnOff,
	pm1001lhMondwRmonBitsCntOverloadPortn
		EkiOnOff
	}


pm1001lhMondwRmonBitsCntIndex OBJECT-TYPE
	SYNTAX  INTEGER(0..128)
	MAX-ACCESS  read-only
	STATUS current
	DESCRIPTION
        "
        Index definition for the pm1001lhMondwRmonBitsCnt
        table
        "
	::= { pm1001lhMondwRmonBitsCntEntry 1 }


pm1001lhMondwRmonBitsCntValuePortn OBJECT-TYPE
	SYNTAX  Counter64
	MAX-ACCESS read-only
	STATUS current
	DESCRIPTION
        "
        Bits Counter On Client Output
         :This counter is increased each
        time a bit is received on the Output
        client port
        "
	::= { pm1001lhMondwRmonBitsCntEntry 2 }


pm1001lhMondwRmonBitsCntErrorPortn OBJECT-TYPE
	SYNTAX  EkiOnOff
	MAX-ACCESS read-only
	STATUS current
	DESCRIPTION
        "
        Output Bits Counter Error :This
        OID when set indicates the output
        Bits counter value is invalid on
        client port
        "
	::= { pm1001lhMondwRmonBitsCntEntry 3 }


pm1001lhMondwRmonBitsCntOverloadPortn OBJECT-TYPE
	SYNTAX  EkiOnOff
	MAX-ACCESS read-only
	STATUS current
	DESCRIPTION
        "
        Output Bits Counter Overload :This
        OID when set indicates an output
        Bits counter overload on client
        port
        "
	::= { pm1001lhMondwRmonBitsCntEntry 4 }


--- *********************************************************
---     TABLE for the pm1001lhMondwRmonUnicastCnt articles
--- *********************************************************

pm1001lhMondwRmonUnicastCntTable OBJECT-TYPE
	SYNTAX  SEQUENCE OF Pm1001lhMondwRmonUnicastCntEntry
	MAX-ACCESS not-accessible
	STATUS current
	DESCRIPTION
        "
        List of pm1001lhMondwRmonUnicastCnt
        Article
        "
	::= { pm1001lhRmonClient 176 }


pm1001lhMondwRmonUnicastCntEntry OBJECT-TYPE
	SYNTAX Pm1001lhMondwRmonUnicastCntEntry
	MAX-ACCESS not-accessible
	STATUS current
	DESCRIPTION
        "
        Row definition for the pm1001lhMondwRmonUnicastCnt
        table
        "
	INDEX   { pm1001lhMondwRmonUnicastCntIndex }
	::= { pm1001lhMondwRmonUnicastCntTable 1 }


Pm1001lhMondwRmonUnicastCntEntry ::=
	SEQUENCE {
	pm1001lhMondwRmonUnicastCntIndex
		INTEGER,
	pm1001lhMondwRmonUnicastCntValuePortn
		Counter64,
	pm1001lhMondwRmonUnicastCntErrorPortn
		EkiOnOff,
	pm1001lhMondwRmonUnicastCntOverloadPortn
		EkiOnOff
	}


pm1001lhMondwRmonUnicastCntIndex OBJECT-TYPE
	SYNTAX  INTEGER(0..128)
	MAX-ACCESS  read-only
	STATUS current
	DESCRIPTION
        "
        Index definition for the pm1001lhMondwRmonUnicastCnt
        table
        "
	::= { pm1001lhMondwRmonUnicastCntEntry 1 }


pm1001lhMondwRmonUnicastCntValuePortn OBJECT-TYPE
	SYNTAX  Counter64
	MAX-ACCESS read-only
	STATUS current
	DESCRIPTION
        "
        Client Output Unicast Packets
         :This counter is increased each
        time a Unicast packet is transmitted
        on client port   <Help>  This counter
        gives the number of Unicast packets
        transmitted on the client output
        port
        "
	::= { pm1001lhMondwRmonUnicastCntEntry 2 }


pm1001lhMondwRmonUnicastCntErrorPortn OBJECT-TYPE
	SYNTAX  EkiOnOff
	MAX-ACCESS read-only
	STATUS current
	DESCRIPTION
        "
        Output Unicast Counter Error :This
        OID when set indicates the output
        RMON timer is invalid on client
        port
        "
	::= { pm1001lhMondwRmonUnicastCntEntry 3 }


pm1001lhMondwRmonUnicastCntOverloadPortn OBJECT-TYPE
	SYNTAX  EkiOnOff
	MAX-ACCESS read-only
	STATUS current
	DESCRIPTION
        "
        Output Unicast Counter Overload
        :This OID when set indicates an
        output RMON timer overload on client
        port
        "
	::= { pm1001lhMondwRmonUnicastCntEntry 4 }


--- *********************************************************
---     TABLE for the pm1001lhMondwRmonNonUnicastCnt articles
--- *********************************************************

pm1001lhMondwRmonNonUnicastCntTable OBJECT-TYPE
	SYNTAX  SEQUENCE OF Pm1001lhMondwRmonNonUnicastCntEntry
	MAX-ACCESS not-accessible
	STATUS current
	DESCRIPTION
        "
        List of pm1001lhMondwRmonNonUnicastCnt
        Article
        "
	::= { pm1001lhRmonClient 184 }


pm1001lhMondwRmonNonUnicastCntEntry OBJECT-TYPE
	SYNTAX Pm1001lhMondwRmonNonUnicastCntEntry
	MAX-ACCESS not-accessible
	STATUS current
	DESCRIPTION
        "
        Row definition for the pm1001lhMondwRmonNonUnicastCnt
        table
        "
	INDEX   { pm1001lhMondwRmonNonUnicastCntIndex }
	::= { pm1001lhMondwRmonNonUnicastCntTable 1 }


Pm1001lhMondwRmonNonUnicastCntEntry ::=
	SEQUENCE {
	pm1001lhMondwRmonNonUnicastCntIndex
		INTEGER,
	pm1001lhMondwRmonNonUnicastCntValuePortn
		Counter64,
	pm1001lhMondwRmonNonUnicastCntErrorPortn
		EkiOnOff,
	pm1001lhMondwRmonNonUnicastCntOverloadPortn
		EkiOnOff
	}


pm1001lhMondwRmonNonUnicastCntIndex OBJECT-TYPE
	SYNTAX  INTEGER(0..128)
	MAX-ACCESS  read-only
	STATUS current
	DESCRIPTION
        "
        Index definition for the pm1001lhMondwRmonNonUnicastCnt
        table
        "
	::= { pm1001lhMondwRmonNonUnicastCntEntry 1 }


pm1001lhMondwRmonNonUnicastCntValuePortn OBJECT-TYPE
	SYNTAX  Counter64
	MAX-ACCESS read-only
	STATUS current
	DESCRIPTION
        "
        Client Output Not Unicast Packets
        :This counter is increased each
        time a Non Unicast packet is transmitted
        on client port   <Help>  This counter
        gives the number of Non Unicast
        packets transmitted on the client
        output port
        "
	::= { pm1001lhMondwRmonNonUnicastCntEntry 2 }


pm1001lhMondwRmonNonUnicastCntErrorPortn OBJECT-TYPE
	SYNTAX  EkiOnOff
	MAX-ACCESS read-only
	STATUS current
	DESCRIPTION
        "
        Output Non Unicast Counter Error
        :This OID when set indicates the
        output Bits counter value is invalid
        on client port
        "
	::= { pm1001lhMondwRmonNonUnicastCntEntry 3 }


pm1001lhMondwRmonNonUnicastCntOverloadPortn OBJECT-TYPE
	SYNTAX  EkiOnOff
	MAX-ACCESS read-only
	STATUS current
	DESCRIPTION
        "
        Output Non Unicast Counter Overload
        :This OID when set indicates an
        output Bits counter overload on
        client port
        "
	::= { pm1001lhMondwRmonNonUnicastCntEntry 4 }


pm1001lhMonCountersReset  OBJECT-TYPE
	SYNTAX EkiOnOff
	MAX-ACCESS read-write
	STATUS current
	DESCRIPTION
	"RMON Counters Reset:This OID resets and restarts all the RMON counters"
	::= { pm1001lhRmonOther  359 }

pm1001lhMonCountersStop  OBJECT-TYPE
	SYNTAX EkiOnOff
	MAX-ACCESS read-write
	STATUS current
	DESCRIPTION
	"RMON Counters stop:This OID stops all the RMON counters"
	::= { pm1001lhRmonOther  360 }






--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pm1001lhMesrsynth0 OBJECT-TYPE
	  SYNTAX EkiMeasureType
	  MAX-ACCESS read-only
	  STATUS deprecated
	  DESCRIPTION
        "
        Not Used :This OID gives the unit
        used on AUX1 measurement of XFP#1
         (Unit = )
        "
	  ::= { pm1001lhMesrOther 0 }



pm1001lhMesrsynth1 OBJECT-TYPE
	  SYNTAX EkiMeasureType
	  MAX-ACCESS read-only
	  STATUS deprecated
	  DESCRIPTION
        "
        Not Used :This OID gives the unit
        used on AUX2 measurement of XFP#1
         (Unit = )
        "
	  ::= { pm1001lhMesrOther 1 }



--- *****************************************************
---     LEAF for the clientModTempMeas article
--- *****************************************************

pm1001lhMesrclientModTempMeas OBJECT-TYPE
	  SYNTAX Unsigned32 (0..65535)
	  MAX-ACCESS read-only
	  STATUS current
	  DESCRIPTION
        "
        Client Optical Module Temperature
        :This OID gives the temperature
        value of the XFP plugged in port,
        read from the DDM (Digital Diagnostic
        Monitoring) (Temperature = AV/256)
          (Unit = C)  <Help>  This measure
        gives the temperature of the client
        transceiver
        "
	  ::= { pm1001lhMesrClient 16 }



--- *****************************************************
---     LEAF for the clientBiasCurrentMeas article
--- *****************************************************

pm1001lhMesrclientBiasCurrentMeas OBJECT-TYPE
	  SYNTAX Unsigned32 (0..65535)
	  MAX-ACCESS read-only
	  STATUS current
	  DESCRIPTION
        "
        Client Optical Module Laser Bias
        :This OID gives the bias value
         of the XFP plugged into port,
         read from the DDM (Digital Diagnostic
        Monitoring)   (Bias = AV/500)
         (Unit = mA)  <Help>  This measure
        gives the bias of the client transceiver
        "
	  ::= { pm1001lhMesrClient 32 }



--- *****************************************************
---     LEAF for the clientTxPowerMeas article
--- *****************************************************

pm1001lhMesrclientTxPowerMeas OBJECT-TYPE
	  SYNTAX Unsigned32 (0..65535)
	  MAX-ACCESS read-only
	  STATUS current
	  DESCRIPTION
        "
        Client Optical Module Tx Power
        :This OID gives the transmit power
        value of the XFP plugged into port,
        read from the DDM (Digital Diagnostic
        Monitoring)   (Power = 10*log(AV)-40)
         (Unit = dBm)  <Help>  This measure
        gives the Tx optical power of the
        client transceiver
        "
	  ::= { pm1001lhMesrClient 40 }



--- *****************************************************
---     LEAF for the clientRxPowerMeas article
--- *****************************************************

pm1001lhMesrclientRxPowerMeas OBJECT-TYPE
	  SYNTAX Unsigned32 (0..65535)
	  MAX-ACCESS read-only
	  STATUS current
	  DESCRIPTION
        "
        Client Optical Module Rx Power
        :This OID gives the receive power
        value of the XFP plugged into port,
        read in the DDM (Digital Diagnostic
        Monitoring)  (Power = 10*log(AV)-40)
          (Unit = dBm)  <Help>  This measure
        gives the Rx optical power of the
        client transceiver
        "
	  ::= { pm1001lhMesrClient 48 }



--- *****************************************************
---     LEAF for the lineModTempMeas article
--- *****************************************************

pm1001lhMesrlineModTempMeas OBJECT-TYPE
	  SYNTAX Unsigned32 (0..65535)
	  MAX-ACCESS read-only
	  STATUS current
	  DESCRIPTION
        "
        Line Optical Module Temperature
        :This OID gives the temperature
        of the XFP or OTX plugged in line#1,
        read from the DDM (Digital Diagnostic
        Monitoring)   (Temperature = AV/256)
         (Unit = C)  <Help>  This measure
        gives the temperature of the line
        transceiver
        "
	  ::= { pm1001lhMesrLine 208 }



--- *****************************************************
---     LEAF for the lineReserved article
--- *****************************************************

pm1001lhMesrlineReserved OBJECT-TYPE
	  SYNTAX Unsigned32 (0..65535)
	  MAX-ACCESS read-only
	  STATUS deprecated
	  DESCRIPTION
        "
        Not Used :Reserved
        "
	  ::= { pm1001lhMesrLine 209 }



--- *****************************************************
---     LEAF for the lineBiasCurrentMeas article
--- *****************************************************

pm1001lhMesrlineBiasCurrentMeas OBJECT-TYPE
	  SYNTAX Unsigned32 (0..65535)
	  MAX-ACCESS read-only
	  STATUS current
	  DESCRIPTION
        "
        Line Optical Module Laser Bias
        :This OID gives the bias value
         of the XFP or OTX plugged in line
        #1, read from the DDM (Digital
         Diagnostic Monitoring)  (Bias
         = AV/500) (Unit = mA)  <Help>
          This measure gives the bias of
        the line transceiver
        "
	  ::= { pm1001lhMesrLine 210 }



--- *****************************************************
---     LEAF for the lineTxPowerMeas article
--- *****************************************************

pm1001lhMesrlineTxPowerMeas OBJECT-TYPE
	  SYNTAX Unsigned32 (0..65535)
	  MAX-ACCESS read-only
	  STATUS current
	  DESCRIPTION
        "
        Line Optical Module Tx Power :This
        OID gives the transmit power value
        of the XFP or OTX plugged in line
        #1, read from the DDM (Digital
           Diagnostic Monitoring)  (Power
        = 10*log(AV)-40)  (Unit = dBm)
          <Help>  This measure gives the
        Tx optical power of the line transceiver
        "
	  ::= { pm1001lhMesrLine 211 }



--- *****************************************************
---     LEAF for the lineRxPowerMeas article
--- *****************************************************

pm1001lhMesrlineRxPowerMeas OBJECT-TYPE
	  SYNTAX Unsigned32 (0..65535)
	  MAX-ACCESS read-only
	  STATUS current
	  DESCRIPTION
        "
        Line Optical Module Rx Power :This
        OID gives the receive power value
        of the XFP or OTX plugged in line
        #1, read from the DDM (Digital
         Diagnostic Monitoring) (Power
         = 10*log(AV)-40)  (Unit = dBm)
         <Help>  This measure gives the
        Rx optical power of the line transceiver
        "
	  ::= { pm1001lhMesrLine 212 }



--- *****************************************************
---     LEAF for the lineAux1Meas article
--- *****************************************************

pm1001lhMesrlineAux1Meas OBJECT-TYPE
	  SYNTAX Unsigned32 (0..65535)
	  MAX-ACCESS read-only
	  STATUS deprecated
	  DESCRIPTION
        "
        Not Used :This OID gives the receive
        power value read in the DDM (Digital
        Diagnostic Monitoring) of the XFP
        or OTX plugged in line #1 (Unit
        = ?)
        "
	  ::= { pm1001lhMesrLine 213 }



--- *****************************************************
---     LEAF for the lineAux2Meas article
--- *****************************************************

pm1001lhMesrlineAux2Meas OBJECT-TYPE
	  SYNTAX Unsigned32 (0..65535)
	  MAX-ACCESS read-only
	  STATUS deprecated
	  DESCRIPTION
        "
        Not Used :This OID gives the receive
        power value read in the DDM (Digital
        Diagnostic Monitoring) of the XFP
        or OTX plugged in line #1 (Unit
        = ?)
        "
	  ::= { pm1001lhMesrLine 214 }



--- *****************************************************
---     LEAF for the lineAging article
--- *****************************************************

pm1001lhMesrlineAging OBJECT-TYPE
	  SYNTAX Unsigned32 (0..65535)
	  MAX-ACCESS read-only
	  STATUS current
	  DESCRIPTION
        "
        Line OTX TLH Aging :This OID gives
        the aging of the Line OTX TLH,
         read from the DDM (Digital Diagnostic
        Monitoring)  (Aging = AV) (Unit
        = %)  <Help>  This measure gives
        the aging of the Line OTX TLH
        "
	  ::= { pm1001lhMesrLine 224 }



--- *****************************************************
---     LEAF for the lineLaserTemperature article
--- *****************************************************

pm1001lhMesrlineLaserTemperature OBJECT-TYPE
	  SYNTAX Unsigned32 (0..65535)
	  MAX-ACCESS read-only
	  STATUS deprecated
	  DESCRIPTION
        "
        Line OTX TLH Laser Temperature
        :This OID gives the laser temperature
        of the Line OTX TLH, read from
         the DDM (Digital Diagnostic Monitoring)
         (Temperature = AV/256) (Unit =
        C)  <Help>  This measure gives
         the laser temperature of the Line
        OTX TLH
        "
	  ::= { pm1001lhMesrLine 225 }



--- *****************************************************
---     LEAF for the lineFreqDeviation article
--- *****************************************************

pm1001lhMesrlineFreqDeviation OBJECT-TYPE
	  SYNTAX Unsigned32 (0..65535)
	  MAX-ACCESS read-only
	  STATUS current
	  DESCRIPTION
        "
        Line OTX TLH Frequency Deviation
        :This OID gives the frequency deviation
        of the Line OTX TLH, read from
         the DDM (Digital Diagnostic Monitoring)
         (Deviation = (AV-32768)*100) (Unit
        = MHz)  <Help>  This measure gives
        the frequency deviation of the
         Line OTX TLH
        "
	  ::= { pm1001lhMesrLine 226 }



--- *****************************************************
---     LEAF for the lineLaserWvlength article
--- *****************************************************

pm1001lhMesrlineLaserWvlength OBJECT-TYPE
	  SYNTAX Unsigned32 (0..65535)
	  MAX-ACCESS read-only
	  STATUS current
	  DESCRIPTION
        "
        Line Optical Module Wavelength
        :This OID gives the laser wavelength
        of the Line OTX TLH, read from
         the DDM (Digital Diagnostic Monitoring)
         (Wavelength=299792458/((193,100+(AV-32768
        )*12,5)*10 3)) (Unit = nm)  <Help>
         This measure gives the laser wavelength
        of the Line OTX TLH
        "
	  ::= { pm1001lhMesrLine 227 }








--- *****************************************************
--- $$$$$$$$$$$$$$$$$$$$$$$$$$$$$$$$$$$$$$$$$$$$$$$$$$$$$
---     PERFORMANCE
--- $$$$$$$$$$$$$$$$$$$$$$$$$$$$$$$$$$$$$$$$$$$$$$$$$$$$$
--- *****************************************************



--- *****************************************************
---     Leaf of the telecomClientCurrent15Stat
--- *****************************************************
--- *********************************************************
---     TABLE for the pm1001lhPerfTelecomClientCurrent15Stat articles
--- *********************************************************

pm1001lhPerfTelecomClientCurrent15StatTable OBJECT-TYPE
	SYNTAX  SEQUENCE OF Pm1001lhPerfTelecomClientCurrent15StatEntry
	MAX-ACCESS not-accessible
	STATUS current
	DESCRIPTION
        "
        List of pm1001lhPerfTelecomClientCurrent15Stat
        Article
        "
	::= { pm1001lhMonClient 16 }


pm1001lhPerfTelecomClientCurrent15StatEntry OBJECT-TYPE
	SYNTAX Pm1001lhPerfTelecomClientCurrent15StatEntry
	MAX-ACCESS not-accessible
	STATUS current
	DESCRIPTION
        "
        Row definition for the pm1001lhPerfTelecomClientCurrent15Stat
        table
        "
	INDEX   { pm1001lhPerfTelecomClientCurrent15StatIndex }
	::= { pm1001lhPerfTelecomClientCurrent15StatTable 1 }


Pm1001lhPerfTelecomClientCurrent15StatEntry ::=
	SEQUENCE {
	pm1001lhPerfTelecomClientCurrent15StatIndex
		INTEGER,
	pm1001lhPerfTelecomClientCurrent15StatInvCvPortn
		EkiOnOff,
	pm1001lhPerfTelecomClientCurrent15StatCvValuePortn
		Unsigned32,
	pm1001lhPerfTelecomClientCurrent15StatInvEsPortn
		EkiOnOff,
	pm1001lhPerfTelecomClientCurrent15StatEsValuePortn
		Unsigned32,
	pm1001lhPerfTelecomClientCurrent15StatInvSesPortn
		EkiOnOff,
	pm1001lhPerfTelecomClientCurrent15StatSesValuePortn
		Unsigned32,
	pm1001lhPerfTelecomClientCurrent15StatInvSefsPortn
		EkiOnOff,
	pm1001lhPerfTelecomClientCurrent15StatSefsValuePortn
		Unsigned32,
	pm1001lhPerfTelecomClientCurrent15StatInvUasPortn
		EkiOnOff,
	pm1001lhPerfTelecomClientCurrent15StatUasValuePortn
		Unsigned32
	}


pm1001lhPerfTelecomClientCurrent15StatIndex OBJECT-TYPE
	SYNTAX  INTEGER(0..128)
	MAX-ACCESS  read-only
	STATUS current
	DESCRIPTION
        "
        Index definition for the pm1001lhPerfTelecomClientCurrent15Stat
        table
        "
	::= { pm1001lhPerfTelecomClientCurrent15StatEntry 1 }


pm1001lhPerfTelecomClientCurrent15StatInvCvPortn OBJECT-TYPE
	SYNTAX  EkiOnOff
	MAX-ACCESS read-only
	STATUS current
	DESCRIPTION
        "
        Current 15-min CV counter inv.
        :This OID indicates that the current
        15-min Coding Violation counter
        is invalid
        "
	::= { pm1001lhPerfTelecomClientCurrent15StatEntry 2 }


pm1001lhPerfTelecomClientCurrent15StatCvValuePortn OBJECT-TYPE
	SYNTAX  Unsigned32
	MAX-ACCESS read-only
	STATUS current
	DESCRIPTION
        "
        Current 15-min CV counter :This
        OID gives the current 15-min Coding
        Violation counter value
        "
	::= { pm1001lhPerfTelecomClientCurrent15StatEntry 3 }


pm1001lhPerfTelecomClientCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pm1001lhPerfTelecomClientCurrent15StatEntry 4 }


pm1001lhPerfTelecomClientCurrent15StatEsValuePortn OBJECT-TYPE
	SYNTAX  Unsigned32
	MAX-ACCESS read-only
	STATUS current
	DESCRIPTION
        "
        Current 15-min ES counter :This
        OID gives the current 15-min Errored
        Second counter value
        "
	::= { pm1001lhPerfTelecomClientCurrent15StatEntry 5 }


pm1001lhPerfTelecomClientCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pm1001lhPerfTelecomClientCurrent15StatEntry 6 }


pm1001lhPerfTelecomClientCurrent15StatSesValuePortn OBJECT-TYPE
	SYNTAX  Unsigned32
	MAX-ACCESS read-only
	STATUS current
	DESCRIPTION
        "
        Current 15-min SES counter :This
        OID gives the current 15-min severely
        Errored Second counter value
        "
	::= { pm1001lhPerfTelecomClientCurrent15StatEntry 7 }


pm1001lhPerfTelecomClientCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pm1001lhPerfTelecomClientCurrent15StatEntry 8 }


pm1001lhPerfTelecomClientCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pm1001lhPerfTelecomClientCurrent15StatEntry 9 }


pm1001lhPerfTelecomClientCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pm1001lhPerfTelecomClientCurrent15StatEntry 10 }


pm1001lhPerfTelecomClientCurrent15StatUasValuePortn OBJECT-TYPE
	SYNTAX  Unsigned32
	MAX-ACCESS read-only
	STATUS current
	DESCRIPTION
        "
        Current 15-min UAS counter :This
        OID gives the current 15-min UnAvailable
        Second counter value
        "
	::= { pm1001lhPerfTelecomClientCurrent15StatEntry 11 }


--- *****************************************************
---     Leaf of the telecomClientPast15Stat
--- *****************************************************
--- *********************************************************
---     TABLE for the pm1001lhPerfTelecomClientPast15StatHistory articles
--- *********************************************************

pm1001lhPerfTelecomClientPast15StatHistoryPort1Table OBJECT-TYPE
	SYNTAX  SEQUENCE OF Pm1001lhPerfTelecomClientPast15StatHistoryPort1Entry
	MAX-ACCESS not-accessible
	STATUS current
	DESCRIPTION
        "
        List of pm1001lhPerfTelecomClientPast15StatHistory
        Article
        "
	::= { pm1001lhMonClient 24 }


pm1001lhPerfTelecomClientPast15StatHistoryPort1Entry OBJECT-TYPE
	SYNTAX Pm1001lhPerfTelecomClientPast15StatHistoryPort1Entry
	MAX-ACCESS not-accessible
	STATUS current
	DESCRIPTION
        "
        Row definition for the pm1001lhPerfTelecomClientPast15StatHistory
        table
        "
	INDEX   { pm1001lhPerfTelecomClientPast15StatHistoryPort1Index }
	::= { pm1001lhPerfTelecomClientPast15StatHistoryPort1Table 1 }


Pm1001lhPerfTelecomClientPast15StatHistoryPort1Entry ::=
	SEQUENCE {
	pm1001lhPerfTelecomClientPast15StatHistoryPort1Index
		INTEGER,
	pm1001lhPerfTelecomClientPast15StatHistoryInvCvPort1
		EkiOnOff,
	pm1001lhPerfTelecomClientPast15StatHistoryCvValuePort1
		Unsigned32,
	pm1001lhPerfTelecomClientPast15StatHistoryInvEsPort1
		EkiOnOff,
	pm1001lhPerfTelecomClientPast15StatHistoryEsValuePort1
		Unsigned32,
	pm1001lhPerfTelecomClientPast15StatHistoryInvSesPort1
		EkiOnOff,
	pm1001lhPerfTelecomClientPast15StatHistorySesValuePort1
		Unsigned32,
	pm1001lhPerfTelecomClientPast15StatHistoryInvSefsPort1
		EkiOnOff,
	pm1001lhPerfTelecomClientPast15StatHistorySefsValuePort1
		Unsigned32,
	pm1001lhPerfTelecomClientPast15StatHistoryInvUasPort1
		EkiOnOff,
	pm1001lhPerfTelecomClientPast15StatHistoryUasValuePort1
		Unsigned32
	}


pm1001lhPerfTelecomClientPast15StatHistoryPort1Index OBJECT-TYPE
	SYNTAX  INTEGER(0..128)
	MAX-ACCESS  read-only
	STATUS current
	DESCRIPTION
        "
        Index definition for the pm1001lhPerfTelecomClientPast15StatHistory
        table
        "
	::= { pm1001lhPerfTelecomClientPast15StatHistoryPort1Entry 1 }


pm1001lhPerfTelecomClientPast15StatHistoryInvCvPort1 OBJECT-TYPE
	SYNTAX  EkiOnOff
	MAX-ACCESS read-only
	STATUS current
	DESCRIPTION
        "
        Previous 15-min CV counter inv.
        :This OID indicates that the previous
        15-min Coding Violation counter
        is invalid
        "
	::= { pm1001lhPerfTelecomClientPast15StatHistoryPort1Entry 2 }


pm1001lhPerfTelecomClientPast15StatHistoryCvValuePort1 OBJECT-TYPE
	SYNTAX  Unsigned32
	MAX-ACCESS read-only
	STATUS current
	DESCRIPTION
        "
        Previous 15-min CV counter :This
        OID gives the previous 15-min Coding
        Violation counter value
        "
	::= { pm1001lhPerfTelecomClientPast15StatHistoryPort1Entry 3 }


pm1001lhPerfTelecomClientPast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pm1001lhPerfTelecomClientPast15StatHistoryPort1Entry 4 }


pm1001lhPerfTelecomClientPast15StatHistoryEsValuePort1 OBJECT-TYPE
	SYNTAX  Unsigned32
	MAX-ACCESS read-only
	STATUS current
	DESCRIPTION
        "
        Previous 15-min ES counter :This
        OID gives the previous 15-min Errored
        Second counter value
        "
	::= { pm1001lhPerfTelecomClientPast15StatHistoryPort1Entry 5 }


pm1001lhPerfTelecomClientPast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pm1001lhPerfTelecomClientPast15StatHistoryPort1Entry 6 }


pm1001lhPerfTelecomClientPast15StatHistorySesValuePort1 OBJECT-TYPE
	SYNTAX  Unsigned32
	MAX-ACCESS read-only
	STATUS current
	DESCRIPTION
        "
        Previous 15-min SES counter :This
        OID gives the previous 15-min severely
        Errored Second counter value
        "
	::= { pm1001lhPerfTelecomClientPast15StatHistoryPort1Entry 7 }


pm1001lhPerfTelecomClientPast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pm1001lhPerfTelecomClientPast15StatHistoryPort1Entry 8 }


pm1001lhPerfTelecomClientPast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pm1001lhPerfTelecomClientPast15StatHistoryPort1Entry 9 }


pm1001lhPerfTelecomClientPast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pm1001lhPerfTelecomClientPast15StatHistoryPort1Entry 10 }


pm1001lhPerfTelecomClientPast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pm1001lhPerfTelecomClientPast15StatHistoryPort1Entry 11 }


--- *****************************************************
---     Leaf of the telecomClientCurrent24Stat
--- *****************************************************
--- *********************************************************
---     TABLE for the pm1001lhPerfTelecomClientCurrent24Stat articles
--- *********************************************************

pm1001lhPerfTelecomClientCurrent24StatTable OBJECT-TYPE
	SYNTAX  SEQUENCE OF Pm1001lhPerfTelecomClientCurrent24StatEntry
	MAX-ACCESS not-accessible
	STATUS current
	DESCRIPTION
        "
        List of pm1001lhPerfTelecomClientCurrent24Stat
        Article
        "
	::= { pm1001lhMonClient 32 }


pm1001lhPerfTelecomClientCurrent24StatEntry OBJECT-TYPE
	SYNTAX Pm1001lhPerfTelecomClientCurrent24StatEntry
	MAX-ACCESS not-accessible
	STATUS current
	DESCRIPTION
        "
        Row definition for the pm1001lhPerfTelecomClientCurrent24Stat
        table
        "
	INDEX   { pm1001lhPerfTelecomClientCurrent24StatIndex }
	::= { pm1001lhPerfTelecomClientCurrent24StatTable 1 }


Pm1001lhPerfTelecomClientCurrent24StatEntry ::=
	SEQUENCE {
	pm1001lhPerfTelecomClientCurrent24StatIndex
		INTEGER,
	pm1001lhPerfTelecomClientCurrent24StatInvCvPortn
		EkiOnOff,
	pm1001lhPerfTelecomClientCurrent24StatCvValuePortn
		Unsigned32,
	pm1001lhPerfTelecomClientCurrent24StatInvEsPortn
		EkiOnOff,
	pm1001lhPerfTelecomClientCurrent24StatEsValuePortn
		Unsigned32,
	pm1001lhPerfTelecomClientCurrent24StatInvSesPortn
		EkiOnOff,
	pm1001lhPerfTelecomClientCurrent24StatSesValuePortn
		Unsigned32,
	pm1001lhPerfTelecomClientCurrent24StatInvSefsPortn
		EkiOnOff,
	pm1001lhPerfTelecomClientCurrent24StatSefsValuePortn
		Unsigned32,
	pm1001lhPerfTelecomClientCurrent24StatInvUasPortn
		EkiOnOff,
	pm1001lhPerfTelecomClientCurrent24StatUasValuePortn
		Unsigned32
	}


pm1001lhPerfTelecomClientCurrent24StatIndex OBJECT-TYPE
	SYNTAX  INTEGER(0..128)
	MAX-ACCESS  read-only
	STATUS current
	DESCRIPTION
        "
        Index definition for the pm1001lhPerfTelecomClientCurrent24Stat
        table
        "
	::= { pm1001lhPerfTelecomClientCurrent24StatEntry 1 }


pm1001lhPerfTelecomClientCurrent24StatInvCvPortn OBJECT-TYPE
	SYNTAX  EkiOnOff
	MAX-ACCESS read-only
	STATUS current
	DESCRIPTION
        "
        Current 24-hours CV counter inv.
        :This OID indicates that the current
        24-hours Coding Violation counter
        is invalid
        "
	::= { pm1001lhPerfTelecomClientCurrent24StatEntry 2 }


pm1001lhPerfTelecomClientCurrent24StatCvValuePortn OBJECT-TYPE
	SYNTAX  Unsigned32
	MAX-ACCESS read-only
	STATUS current
	DESCRIPTION
        "
        Current 24-hours CV counter :This
        OID gives the current 24-hours
         Coding Violation counter value
        "
	::= { pm1001lhPerfTelecomClientCurrent24StatEntry 3 }


pm1001lhPerfTelecomClientCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pm1001lhPerfTelecomClientCurrent24StatEntry 4 }


pm1001lhPerfTelecomClientCurrent24StatEsValuePortn OBJECT-TYPE
	SYNTAX  Unsigned32
	MAX-ACCESS read-only
	STATUS current
	DESCRIPTION
        "
        Current 24-hours ES counter :This
        OID gives the current 24-hours
         Errored Second counter value
        "
	::= { pm1001lhPerfTelecomClientCurrent24StatEntry 5 }


pm1001lhPerfTelecomClientCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pm1001lhPerfTelecomClientCurrent24StatEntry 6 }


pm1001lhPerfTelecomClientCurrent24StatSesValuePortn OBJECT-TYPE
	SYNTAX  Unsigned32
	MAX-ACCESS read-only
	STATUS current
	DESCRIPTION
        "
        Current 24-hours SES counter :This
        OID gives the current 24-hours
         severely Errored Second counter
        value
        "
	::= { pm1001lhPerfTelecomClientCurrent24StatEntry 7 }


pm1001lhPerfTelecomClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pm1001lhPerfTelecomClientCurrent24StatEntry 8 }


pm1001lhPerfTelecomClientCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pm1001lhPerfTelecomClientCurrent24StatEntry 9 }


pm1001lhPerfTelecomClientCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pm1001lhPerfTelecomClientCurrent24StatEntry 10 }


pm1001lhPerfTelecomClientCurrent24StatUasValuePortn OBJECT-TYPE
	SYNTAX  Unsigned32
	MAX-ACCESS read-only
	STATUS current
	DESCRIPTION
        "
        Current 24-hours UAS counter :This
        OID gives the current 24-hours
         UnAvailable Second counter value
        "
	::= { pm1001lhPerfTelecomClientCurrent24StatEntry 11 }


--- *****************************************************
---     Leaf of the telecomClientPast24Stat
--- *****************************************************
--- *********************************************************
---     TABLE for the pm1001lhPerfTelecomClientPast24StatHistory articles
--- *********************************************************

pm1001lhPerfTelecomClientPast24StatHistoryPort1Table OBJECT-TYPE
	SYNTAX  SEQUENCE OF Pm1001lhPerfTelecomClientPast24StatHistoryPort1Entry
	MAX-ACCESS not-accessible
	STATUS current
	DESCRIPTION
        "
        List of pm1001lhPerfTelecomClientPast24StatHistory
        Article
        "
	::= { pm1001lhMonClient 40 }


pm1001lhPerfTelecomClientPast24StatHistoryPort1Entry OBJECT-TYPE
	SYNTAX Pm1001lhPerfTelecomClientPast24StatHistoryPort1Entry
	MAX-ACCESS not-accessible
	STATUS current
	DESCRIPTION
        "
        Row definition for the pm1001lhPerfTelecomClientPast24StatHistory
        table
        "
	INDEX   { pm1001lhPerfTelecomClientPast24StatHistoryPort1Index }
	::= { pm1001lhPerfTelecomClientPast24StatHistoryPort1Table 1 }


Pm1001lhPerfTelecomClientPast24StatHistoryPort1Entry ::=
	SEQUENCE {
	pm1001lhPerfTelecomClientPast24StatHistoryPort1Index
		INTEGER,
	pm1001lhPerfTelecomClientPast24StatHistoryInvCvPort1
		EkiOnOff,
	pm1001lhPerfTelecomClientPast24StatHistoryCvValuePort1
		Unsigned32,
	pm1001lhPerfTelecomClientPast24StatHistoryInvEsPort1
		EkiOnOff,
	pm1001lhPerfTelecomClientPast24StatHistoryEsValuePort1
		Unsigned32,
	pm1001lhPerfTelecomClientPast24StatHistoryInvSesPort1
		EkiOnOff,
	pm1001lhPerfTelecomClientPast24StatHistorySesValuePort1
		Unsigned32,
	pm1001lhPerfTelecomClientPast24StatHistoryInvSefsPort1
		EkiOnOff,
	pm1001lhPerfTelecomClientPast24StatHistorySefsValuePort1
		Unsigned32,
	pm1001lhPerfTelecomClientPast24StatHistoryInvUasPort1
		EkiOnOff,
	pm1001lhPerfTelecomClientPast24StatHistoryUasValuePort1
		Unsigned32
	}


pm1001lhPerfTelecomClientPast24StatHistoryPort1Index OBJECT-TYPE
	SYNTAX  INTEGER(0..128)
	MAX-ACCESS  read-only
	STATUS current
	DESCRIPTION
        "
        Index definition for the pm1001lhPerfTelecomClientPast24StatHistory
        table
        "
	::= { pm1001lhPerfTelecomClientPast24StatHistoryPort1Entry 1 }


pm1001lhPerfTelecomClientPast24StatHistoryInvCvPort1 OBJECT-TYPE
	SYNTAX  EkiOnOff
	MAX-ACCESS read-only
	STATUS current
	DESCRIPTION
        "
        Previous 24-hours CV counter inv.
        :This OID indicates that the previous
        24-hours Coding Violation counter
        is invalid
        "
	::= { pm1001lhPerfTelecomClientPast24StatHistoryPort1Entry 2 }


pm1001lhPerfTelecomClientPast24StatHistoryCvValuePort1 OBJECT-TYPE
	SYNTAX  Unsigned32
	MAX-ACCESS read-only
	STATUS current
	DESCRIPTION
        "
        Previous 24-hours CV counter :This
        OID gives the previous 24-hours
        Coding Violation counter value
        "
	::= { pm1001lhPerfTelecomClientPast24StatHistoryPort1Entry 3 }


pm1001lhPerfTelecomClientPast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pm1001lhPerfTelecomClientPast24StatHistoryPort1Entry 4 }


pm1001lhPerfTelecomClientPast24StatHistoryEsValuePort1 OBJECT-TYPE
	SYNTAX  Unsigned32
	MAX-ACCESS read-only
	STATUS current
	DESCRIPTION
        "
        Previous 24-hours ES counter :This
        OID gives the previous 24-hours
        Errored Second counter value
        "
	::= { pm1001lhPerfTelecomClientPast24StatHistoryPort1Entry 5 }


pm1001lhPerfTelecomClientPast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pm1001lhPerfTelecomClientPast24StatHistoryPort1Entry 6 }


pm1001lhPerfTelecomClientPast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pm1001lhPerfTelecomClientPast24StatHistoryPort1Entry 7 }


pm1001lhPerfTelecomClientPast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm1001lhPerfTelecomClientPast24StatHistoryPort1Entry 8 }


pm1001lhPerfTelecomClientPast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pm1001lhPerfTelecomClientPast24StatHistoryPort1Entry 9 }


pm1001lhPerfTelecomClientPast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pm1001lhPerfTelecomClientPast24StatHistoryPort1Entry 10 }


pm1001lhPerfTelecomClientPast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pm1001lhPerfTelecomClientPast24StatHistoryPort1Entry 11 }


--- *****************************************************
---     Leaf of the telecomLineCurrent15Stat
--- *****************************************************
--- *********************************************************
---     TABLE for the pm1001lhPerfTelecomLineCurrent15Stat articles
--- *********************************************************

pm1001lhPerfTelecomLineCurrent15StatTable OBJECT-TYPE
	SYNTAX  SEQUENCE OF Pm1001lhPerfTelecomLineCurrent15StatEntry
	MAX-ACCESS not-accessible
	STATUS current
	DESCRIPTION
        "
        List of pm1001lhPerfTelecomLineCurrent15Stat
        Article
        "
	::= { pm1001lhMonLine 128 }


pm1001lhPerfTelecomLineCurrent15StatEntry OBJECT-TYPE
	SYNTAX Pm1001lhPerfTelecomLineCurrent15StatEntry
	MAX-ACCESS not-accessible
	STATUS current
	DESCRIPTION
        "
        Row definition for the pm1001lhPerfTelecomLineCurrent15Stat
        table
        "
	INDEX   { pm1001lhPerfTelecomLineCurrent15StatIndex }
	::= { pm1001lhPerfTelecomLineCurrent15StatTable 1 }


Pm1001lhPerfTelecomLineCurrent15StatEntry ::=
	SEQUENCE {
	pm1001lhPerfTelecomLineCurrent15StatIndex
		INTEGER,
	pm1001lhPerfTelecomLineCurrent15StatInvCvPortn
		EkiOnOff,
	pm1001lhPerfTelecomLineCurrent15StatCvValuePortn
		Unsigned32,
	pm1001lhPerfTelecomLineCurrent15StatInvEsPortn
		EkiOnOff,
	pm1001lhPerfTelecomLineCurrent15StatEsValuePortn
		Unsigned32,
	pm1001lhPerfTelecomLineCurrent15StatInvSesPortn
		EkiOnOff,
	pm1001lhPerfTelecomLineCurrent15StatSesValuePortn
		Unsigned32,
	pm1001lhPerfTelecomLineCurrent15StatInvSefsPortn
		EkiOnOff,
	pm1001lhPerfTelecomLineCurrent15StatSefsValuePortn
		Unsigned32,
	pm1001lhPerfTelecomLineCurrent15StatInvUasPortn
		EkiOnOff,
	pm1001lhPerfTelecomLineCurrent15StatUasValuePortn
		Unsigned32
	}


pm1001lhPerfTelecomLineCurrent15StatIndex OBJECT-TYPE
	SYNTAX  INTEGER(0..128)
	MAX-ACCESS  read-only
	STATUS current
	DESCRIPTION
        "
        Index definition for the pm1001lhPerfTelecomLineCurrent15Stat
        table
        "
	::= { pm1001lhPerfTelecomLineCurrent15StatEntry 1 }


pm1001lhPerfTelecomLineCurrent15StatInvCvPortn OBJECT-TYPE
	SYNTAX  EkiOnOff
	MAX-ACCESS read-only
	STATUS current
	DESCRIPTION
        "
        Current 15-min CV counter inv.
        :This OID indicates that the current
        15-min Coding Violation counter
        is invalid
        "
	::= { pm1001lhPerfTelecomLineCurrent15StatEntry 2 }


pm1001lhPerfTelecomLineCurrent15StatCvValuePortn OBJECT-TYPE
	SYNTAX  Unsigned32
	MAX-ACCESS read-only
	STATUS current
	DESCRIPTION
        "
        Current 15-min CV counter :This
        OID gives the current 15-min Coding
        Violation counter value
        "
	::= { pm1001lhPerfTelecomLineCurrent15StatEntry 3 }


pm1001lhPerfTelecomLineCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { pm1001lhPerfTelecomLineCurrent15StatEntry 4 }


pm1001lhPerfTelecomLineCurrent15StatEsValuePortn OBJECT-TYPE
	SYNTAX  Unsigned32
	MAX-ACCESS read-only
	STATUS current
	DESCRIPTION
        "
        Current 15-min ES counter :This
        OID gives the current 15-min Errored
        Second counter value
        "
	::= { pm1001lhPerfTelecomLineCurrent15StatEntry 5 }


pm1001lhPerfTelecomLineCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { pm1001lhPerfTelecomLineCurrent15StatEntry 6 }


pm1001lhPerfTelecomLineCurrent15StatSesValuePortn OBJECT-TYPE
	SYNTAX  Unsigned32
	MAX-ACCESS read-only
	STATUS current
	DESCRIPTION
        "
        Current 15-min SES counter :This
        OID gives the current 15-min severely
        Errored Second counter value
        "
	::= { pm1001lhPerfTelecomLineCurrent15StatEntry 7 }


pm1001lhPerfTelecomLineCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { pm1001lhPerfTelecomLineCurrent15StatEntry 8 }


pm1001lhPerfTelecomLineCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { pm1001lhPerfTelecomLineCurrent15StatEntry 9 }


pm1001lhPerfTelecomLineCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { pm1001lhPerfTelecomLineCurrent15StatEntry 10 }


pm1001lhPerfTelecomLineCurrent15StatUasValuePortn OBJECT-TYPE
	SYNTAX  Unsigned32
	MAX-ACCESS read-only
	STATUS current
	DESCRIPTION
        "
        Current 15-min UAS counter :This
        OID gives the current 15-min UnAvailable
        Second counter value
        "
	::= { pm1001lhPerfTelecomLineCurrent15StatEntry 11 }


--- *****************************************************
---     Leaf of the telecomLinePast15Stat
--- *****************************************************
--- *********************************************************
---     TABLE for the pm1001lhPerfTelecomLinePast15StatHistory articles
--- *********************************************************

pm1001lhPerfTelecomLinePast15StatHistoryPort1Table OBJECT-TYPE
	SYNTAX  SEQUENCE OF Pm1001lhPerfTelecomLinePast15StatHistoryPort1Entry
	MAX-ACCESS not-accessible
	STATUS current
	DESCRIPTION
        "
        List of pm1001lhPerfTelecomLinePast15StatHistory
        Article
        "
	::= { pm1001lhMonLine 129 }


pm1001lhPerfTelecomLinePast15StatHistoryPort1Entry OBJECT-TYPE
	SYNTAX Pm1001lhPerfTelecomLinePast15StatHistoryPort1Entry
	MAX-ACCESS not-accessible
	STATUS current
	DESCRIPTION
        "
        Row definition for the pm1001lhPerfTelecomLinePast15StatHistory
        table
        "
	INDEX   { pm1001lhPerfTelecomLinePast15StatHistoryPort1Index }
	::= { pm1001lhPerfTelecomLinePast15StatHistoryPort1Table 1 }


Pm1001lhPerfTelecomLinePast15StatHistoryPort1Entry ::=
	SEQUENCE {
	pm1001lhPerfTelecomLinePast15StatHistoryPort1Index
		INTEGER,
	pm1001lhPerfTelecomLinePast15StatHistoryInvCvPort1
		EkiOnOff,
	pm1001lhPerfTelecomLinePast15StatHistoryCvValuePort1
		Unsigned32,
	pm1001lhPerfTelecomLinePast15StatHistoryInvEsPort1
		EkiOnOff,
	pm1001lhPerfTelecomLinePast15StatHistoryEsValuePort1
		Unsigned32,
	pm1001lhPerfTelecomLinePast15StatHistoryInvSesPort1
		EkiOnOff,
	pm1001lhPerfTelecomLinePast15StatHistorySesValuePort1
		Unsigned32,
	pm1001lhPerfTelecomLinePast15StatHistoryInvSefsPort1
		EkiOnOff,
	pm1001lhPerfTelecomLinePast15StatHistorySefsValuePort1
		Unsigned32,
	pm1001lhPerfTelecomLinePast15StatHistoryInvUasPort1
		EkiOnOff,
	pm1001lhPerfTelecomLinePast15StatHistoryUasValuePort1
		Unsigned32
	}


pm1001lhPerfTelecomLinePast15StatHistoryPort1Index OBJECT-TYPE
	SYNTAX  INTEGER(0..128)
	MAX-ACCESS  read-only
	STATUS current
	DESCRIPTION
        "
        Index definition for the pm1001lhPerfTelecomLinePast15StatHistory
        table
        "
	::= { pm1001lhPerfTelecomLinePast15StatHistoryPort1Entry 1 }


pm1001lhPerfTelecomLinePast15StatHistoryInvCvPort1 OBJECT-TYPE
	SYNTAX  EkiOnOff
	MAX-ACCESS read-only
	STATUS current
	DESCRIPTION
        "
        Previous 15-min CV counter inv.
        :This OID indicates that the previous
        15-min Coding Violation counter
        is invalid
        "
	::= { pm1001lhPerfTelecomLinePast15StatHistoryPort1Entry 2 }


pm1001lhPerfTelecomLinePast15StatHistoryCvValuePort1 OBJECT-TYPE
	SYNTAX  Unsigned32
	MAX-ACCESS read-only
	STATUS current
	DESCRIPTION
        "
        Previous 15-min CV counter :This
        OID gives the previous 15-min Coding
        Violation counter value
        "
	::= { pm1001lhPerfTelecomLinePast15StatHistoryPort1Entry 3 }


pm1001lhPerfTelecomLinePast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { pm1001lhPerfTelecomLinePast15StatHistoryPort1Entry 4 }


pm1001lhPerfTelecomLinePast15StatHistoryEsValuePort1 OBJECT-TYPE
	SYNTAX  Unsigned32
	MAX-ACCESS read-only
	STATUS current
	DESCRIPTION
        "
        Previous 15-min ES counter :This
        OID gives the previous 15-min Errored
        Second counter value
        "
	::= { pm1001lhPerfTelecomLinePast15StatHistoryPort1Entry 5 }


pm1001lhPerfTelecomLinePast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { pm1001lhPerfTelecomLinePast15StatHistoryPort1Entry 6 }


pm1001lhPerfTelecomLinePast15StatHistorySesValuePort1 OBJECT-TYPE
	SYNTAX  Unsigned32
	MAX-ACCESS read-only
	STATUS current
	DESCRIPTION
        "
        Previous 15-min SES counter :This
        OID gives the previous 15-min severely
        Errored Second counter value
        "
	::= { pm1001lhPerfTelecomLinePast15StatHistoryPort1Entry 7 }


pm1001lhPerfTelecomLinePast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { pm1001lhPerfTelecomLinePast15StatHistoryPort1Entry 8 }


pm1001lhPerfTelecomLinePast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { pm1001lhPerfTelecomLinePast15StatHistoryPort1Entry 9 }


pm1001lhPerfTelecomLinePast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { pm1001lhPerfTelecomLinePast15StatHistoryPort1Entry 10 }


pm1001lhPerfTelecomLinePast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { pm1001lhPerfTelecomLinePast15StatHistoryPort1Entry 11 }


--- *****************************************************
---     Leaf of the telecomLineCurrent24Stat
--- *****************************************************
--- *********************************************************
---     TABLE for the pm1001lhPerfTelecomLineCurrent24Stat articles
--- *********************************************************

pm1001lhPerfTelecomLineCurrent24StatTable OBJECT-TYPE
	SYNTAX  SEQUENCE OF Pm1001lhPerfTelecomLineCurrent24StatEntry
	MAX-ACCESS not-accessible
	STATUS current
	DESCRIPTION
        "
        List of pm1001lhPerfTelecomLineCurrent24Stat
        Article
        "
	::= { pm1001lhMonLine 130 }


pm1001lhPerfTelecomLineCurrent24StatEntry OBJECT-TYPE
	SYNTAX Pm1001lhPerfTelecomLineCurrent24StatEntry
	MAX-ACCESS not-accessible
	STATUS current
	DESCRIPTION
        "
        Row definition for the pm1001lhPerfTelecomLineCurrent24Stat
        table
        "
	INDEX   { pm1001lhPerfTelecomLineCurrent24StatIndex }
	::= { pm1001lhPerfTelecomLineCurrent24StatTable 1 }


Pm1001lhPerfTelecomLineCurrent24StatEntry ::=
	SEQUENCE {
	pm1001lhPerfTelecomLineCurrent24StatIndex
		INTEGER,
	pm1001lhPerfTelecomLineCurrent24StatInvCvPortn
		EkiOnOff,
	pm1001lhPerfTelecomLineCurrent24StatCvValuePortn
		Unsigned32,
	pm1001lhPerfTelecomLineCurrent24StatInvEsPortn
		EkiOnOff,
	pm1001lhPerfTelecomLineCurrent24StatEsValuePortn
		Unsigned32,
	pm1001lhPerfTelecomLineCurrent24StatInvSesPortn
		EkiOnOff,
	pm1001lhPerfTelecomLineCurrent24StatSesValuePortn
		Unsigned32,
	pm1001lhPerfTelecomLineCurrent24StatInvSefsPortn
		EkiOnOff,
	pm1001lhPerfTelecomLineCurrent24StatSefsValuePortn
		Unsigned32,
	pm1001lhPerfTelecomLineCurrent24StatInvUasPortn
		EkiOnOff,
	pm1001lhPerfTelecomLineCurrent24StatUasValuePortn
		Unsigned32
	}


pm1001lhPerfTelecomLineCurrent24StatIndex OBJECT-TYPE
	SYNTAX  INTEGER(0..128)
	MAX-ACCESS  read-only
	STATUS current
	DESCRIPTION
        "
        Index definition for the pm1001lhPerfTelecomLineCurrent24Stat
        table
        "
	::= { pm1001lhPerfTelecomLineCurrent24StatEntry 1 }


pm1001lhPerfTelecomLineCurrent24StatInvCvPortn OBJECT-TYPE
	SYNTAX  EkiOnOff
	MAX-ACCESS read-only
	STATUS current
	DESCRIPTION
        "
        Current 24-hours CV counter inv.
        :This OID indicates that the current
        24-hours Coding Violation counter
        is invalid
        "
	::= { pm1001lhPerfTelecomLineCurrent24StatEntry 2 }


pm1001lhPerfTelecomLineCurrent24StatCvValuePortn OBJECT-TYPE
	SYNTAX  Unsigned32
	MAX-ACCESS read-only
	STATUS current
	DESCRIPTION
        "
        Current 24-hours CV counter :This
        OID gives the current 24-hours
         Coding Violation counter value
        "
	::= { pm1001lhPerfTelecomLineCurrent24StatEntry 3 }


pm1001lhPerfTelecomLineCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { pm1001lhPerfTelecomLineCurrent24StatEntry 4 }


pm1001lhPerfTelecomLineCurrent24StatEsValuePortn OBJECT-TYPE
	SYNTAX  Unsigned32
	MAX-ACCESS read-only
	STATUS current
	DESCRIPTION
        "
        Current 24-hours ES counter :This
        OID gives the current 24-hours
         Errored Second counter value
        "
	::= { pm1001lhPerfTelecomLineCurrent24StatEntry 5 }


pm1001lhPerfTelecomLineCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { pm1001lhPerfTelecomLineCurrent24StatEntry 6 }


pm1001lhPerfTelecomLineCurrent24StatSesValuePortn OBJECT-TYPE
	SYNTAX  Unsigned32
	MAX-ACCESS read-only
	STATUS current
	DESCRIPTION
        "
        Current 24-hours SES counter :This
        OID gives the current 24-hours
         severely Errored Second counter
        value
        "
	::= { pm1001lhPerfTelecomLineCurrent24StatEntry 7 }


pm1001lhPerfTelecomLineCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { pm1001lhPerfTelecomLineCurrent24StatEntry 8 }


pm1001lhPerfTelecomLineCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { pm1001lhPerfTelecomLineCurrent24StatEntry 9 }


pm1001lhPerfTelecomLineCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { pm1001lhPerfTelecomLineCurrent24StatEntry 10 }


pm1001lhPerfTelecomLineCurrent24StatUasValuePortn OBJECT-TYPE
	SYNTAX  Unsigned32
	MAX-ACCESS read-only
	STATUS current
	DESCRIPTION
        "
        Current 24-hours UAS counter :This
        OID gives the current 24-hours
         UnAvailable Second counter value
        "
	::= { pm1001lhPerfTelecomLineCurrent24StatEntry 11 }


--- *****************************************************
---     Leaf of the telecomLinePast24Stat
--- *****************************************************
--- *********************************************************
---     TABLE for the pm1001lhPerfTelecomLinePast24StatHistory articles
--- *********************************************************

pm1001lhPerfTelecomLinePast24StatHistoryPort1Table OBJECT-TYPE
	SYNTAX  SEQUENCE OF Pm1001lhPerfTelecomLinePast24StatHistoryPort1Entry
	MAX-ACCESS not-accessible
	STATUS current
	DESCRIPTION
        "
        List of pm1001lhPerfTelecomLinePast24StatHistory
        Article
        "
	::= { pm1001lhMonLine 131 }


pm1001lhPerfTelecomLinePast24StatHistoryPort1Entry OBJECT-TYPE
	SYNTAX Pm1001lhPerfTelecomLinePast24StatHistoryPort1Entry
	MAX-ACCESS not-accessible
	STATUS current
	DESCRIPTION
        "
        Row definition for the pm1001lhPerfTelecomLinePast24StatHistory
        table
        "
	INDEX   { pm1001lhPerfTelecomLinePast24StatHistoryPort1Index }
	::= { pm1001lhPerfTelecomLinePast24StatHistoryPort1Table 1 }


Pm1001lhPerfTelecomLinePast24StatHistoryPort1Entry ::=
	SEQUENCE {
	pm1001lhPerfTelecomLinePast24StatHistoryPort1Index
		INTEGER,
	pm1001lhPerfTelecomLinePast24StatHistoryInvCvPort1
		EkiOnOff,
	pm1001lhPerfTelecomLinePast24StatHistoryCvValuePort1
		Unsigned32,
	pm1001lhPerfTelecomLinePast24StatHistoryInvEsPort1
		EkiOnOff,
	pm1001lhPerfTelecomLinePast24StatHistoryEsValuePort1
		Unsigned32,
	pm1001lhPerfTelecomLinePast24StatHistoryInvSesPort1
		EkiOnOff,
	pm1001lhPerfTelecomLinePast24StatHistorySesValuePort1
		Unsigned32,
	pm1001lhPerfTelecomLinePast24StatHistoryInvSefsPort1
		EkiOnOff,
	pm1001lhPerfTelecomLinePast24StatHistorySefsValuePort1
		Unsigned32,
	pm1001lhPerfTelecomLinePast24StatHistoryInvUasPort1
		EkiOnOff,
	pm1001lhPerfTelecomLinePast24StatHistoryUasValuePort1
		Unsigned32
	}


pm1001lhPerfTelecomLinePast24StatHistoryPort1Index OBJECT-TYPE
	SYNTAX  INTEGER(0..128)
	MAX-ACCESS  read-only
	STATUS current
	DESCRIPTION
        "
        Index definition for the pm1001lhPerfTelecomLinePast24StatHistory
        table
        "
	::= { pm1001lhPerfTelecomLinePast24StatHistoryPort1Entry 1 }


pm1001lhPerfTelecomLinePast24StatHistoryInvCvPort1 OBJECT-TYPE
	SYNTAX  EkiOnOff
	MAX-ACCESS read-only
	STATUS current
	DESCRIPTION
        "
        Previous 24-hours CV counter inv.
        :This OID indicates that the previous
        24-hours Coding Violation counter
        is invalid
        "
	::= { pm1001lhPerfTelecomLinePast24StatHistoryPort1Entry 2 }


pm1001lhPerfTelecomLinePast24StatHistoryCvValuePort1 OBJECT-TYPE
	SYNTAX  Unsigned32
	MAX-ACCESS read-only
	STATUS current
	DESCRIPTION
        "
        Previous 24-hours CV counter :This
        OID gives the previous 24-hours
        Coding Violation counter value
        "
	::= { pm1001lhPerfTelecomLinePast24StatHistoryPort1Entry 3 }


pm1001lhPerfTelecomLinePast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { pm1001lhPerfTelecomLinePast24StatHistoryPort1Entry 4 }


pm1001lhPerfTelecomLinePast24StatHistoryEsValuePort1 OBJECT-TYPE
	SYNTAX  Unsigned32
	MAX-ACCESS read-only
	STATUS current
	DESCRIPTION
        "
        Previous 24-hours ES counter :This
        OID gives the previous 24-hours
        Errored Second counter value
        "
	::= { pm1001lhPerfTelecomLinePast24StatHistoryPort1Entry 5 }


pm1001lhPerfTelecomLinePast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { pm1001lhPerfTelecomLinePast24StatHistoryPort1Entry 6 }


pm1001lhPerfTelecomLinePast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { pm1001lhPerfTelecomLinePast24StatHistoryPort1Entry 7 }


pm1001lhPerfTelecomLinePast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { pm1001lhPerfTelecomLinePast24StatHistoryPort1Entry 8 }


pm1001lhPerfTelecomLinePast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { pm1001lhPerfTelecomLinePast24StatHistoryPort1Entry 9 }


pm1001lhPerfTelecomLinePast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { pm1001lhPerfTelecomLinePast24StatHistoryPort1Entry 10 }


pm1001lhPerfTelecomLinePast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { pm1001lhPerfTelecomLinePast24StatHistoryPort1Entry 11 }


--- *****************************************************
---     Leaf of the datacomClientCurrent15Stat
--- *****************************************************
--- *********************************************************
---     TABLE for the pm1001lhPerfDatacomClientCurrent15Stat articles
--- *********************************************************

pm1001lhPerfDatacomClientCurrent15StatTable OBJECT-TYPE
	SYNTAX  SEQUENCE OF Pm1001lhPerfDatacomClientCurrent15StatEntry
	MAX-ACCESS not-accessible
	STATUS current
	DESCRIPTION
        "
        List of pm1001lhPerfDatacomClientCurrent15Stat
        Article
        "
	::= { pm1001lhMonClient 256 }


pm1001lhPerfDatacomClientCurrent15StatEntry OBJECT-TYPE
	SYNTAX Pm1001lhPerfDatacomClientCurrent15StatEntry
	MAX-ACCESS not-accessible
	STATUS current
	DESCRIPTION
        "
        Row definition for the pm1001lhPerfDatacomClientCurrent15Stat
        table
        "
	INDEX   { pm1001lhPerfDatacomClientCurrent15StatIndex }
	::= { pm1001lhPerfDatacomClientCurrent15StatTable 1 }


Pm1001lhPerfDatacomClientCurrent15StatEntry ::=
	SEQUENCE {
	pm1001lhPerfDatacomClientCurrent15StatIndex
		INTEGER,
	pm1001lhperfdatacomclientCurrent15StatOutNonunicastCountInvPortn
		EkiOnOff,
	pm1001lhperfdatacomclientCurrent15StatOutNonunicastCountPortn
		Counter64,
	pm1001lhperfdatacomclientCurrent15StatOutUnicastCountInvPortn
		EkiOnOff,
	pm1001lhperfdatacomclientCurrent15StatOutUnicastCountPortn
		Counter64,
	pm1001lhperfdatacomclientCurrent15StatOutMulticastCountInvPortn
		EkiOnOff,
	pm1001lhperfdatacomclientCurrent15StatOutMulticastCountPortn
		Counter64,
	pm1001lhperfdatacomclientCurrent15StatOutBroadcastCountInvPortn
		EkiOnOff,
	pm1001lhperfdatacomclientCurrent15StatOutBroadcastCountPortn
		Counter64,
	pm1001lhperfdatacomclientCurrent15StatOutBytesCountInvPortn
		EkiOnOff,
	pm1001lhperfdatacomclientCurrent15StatOutBytesCountPortn
		Counter64,
	pm1001lhperfdatacomclientCurrent15StatInNonunicastCountInvPortn
		EkiOnOff,
	pm1001lhperfdatacomclientCurrent15StatInNonunicastCountPortn
		Counter64,
	pm1001lhperfdatacomclientCurrent15StatInUnicastCountInvPortn
		EkiOnOff,
	pm1001lhperfdatacomclientCurrent15StatInUnicastCountPortn
		Counter64,
	pm1001lhperfdatacomclientCurrent15StatInMulticastCountInvPortn
		EkiOnOff,
	pm1001lhperfdatacomclientCurrent15StatInMulticastCountPortn
		Counter64,
	pm1001lhperfdatacomclientCurrent15StatInBroadcastCountInvPortn
		EkiOnOff,
	pm1001lhperfdatacomclientCurrent15StatInBroadcastCountPortn
		Counter64,
	pm1001lhperfdatacomclientCurrent15StatInCrcCountInvPortn
		EkiOnOff,
	pm1001lhperfdatacomclientCurrent15StatInCrcCountPortn
		Counter64,
	pm1001lhperfdatacomclientCurrent15StatInBytesCountInvPortn
		EkiOnOff,
	pm1001lhperfdatacomclientCurrent15StatInBytesCountPortn
		Counter64
	}


pm1001lhPerfDatacomClientCurrent15StatIndex OBJECT-TYPE
	SYNTAX  INTEGER(0..128)
	MAX-ACCESS  read-only
	STATUS current
	DESCRIPTION
        "
        Index definition for the pm1001lhPerfDatacomClientCurrent15Stat
        table
        "
	::= { pm1001lhPerfDatacomClientCurrent15StatEntry 1 }


pm1001lhperfdatacomclientCurrent15StatOutNonunicastCountInvPortn OBJECT-TYPE
	SYNTAX  EkiOnOff
	MAX-ACCESS read-only
	STATUS current
	DESCRIPTION
        "
        Client Current 15-min Output Non
        Unicast counter inv. :This OID
         indicates that the current 15-min
        Non Unicast counter is invalid
        "
	::= { pm1001lhPerfDatacomClientCurrent15StatEntry 44 }


pm1001lhperfdatacomclientCurrent15StatOutNonunicastCountPortn OBJECT-TYPE
	SYNTAX  Counter64
	MAX-ACCESS read-only
	STATUS current
	DESCRIPTION
        "
        Client Current 15-min Output Non
        Unicast counter :This OID gives
        the current 15-min Non Unicast
         counter value
        "
	::= { pm1001lhPerfDatacomClientCurrent15StatEntry 45 }


pm1001lhperfdatacomclientCurrent15StatOutUnicastCountInvPortn OBJECT-TYPE
	SYNTAX  EkiOnOff
	MAX-ACCESS read-only
	STATUS current
	DESCRIPTION
        "
        Client Current 15-min Output Unicast
        counter inv. :This OID indicates
        that the current 15-min Unicast
        counter is invalid
        "
	::= { pm1001lhPerfDatacomClientCurrent15StatEntry 42 }


pm1001lhperfdatacomclientCurrent15StatOutUnicastCountPortn OBJECT-TYPE
	SYNTAX  Counter64
	MAX-ACCESS read-only
	STATUS current
	DESCRIPTION
        "
        Client Current 15-min Output Unicast
        counter :This OID gives the current
        15-min Unicast counter value
        "
	::= { pm1001lhPerfDatacomClientCurrent15StatEntry 43 }


pm1001lhperfdatacomclientCurrent15StatOutMulticastCountInvPortn OBJECT-TYPE
	SYNTAX  EkiOnOff
	MAX-ACCESS read-only
	STATUS current
	DESCRIPTION
        "
        Client Current 15-min Output Multicast
        counter inv. :This OID indicates
        that the current 15-min Multicast
        counter is invalid
        "
	::= { pm1001lhPerfDatacomClientCurrent15StatEntry 34 }


pm1001lhperfdatacomclientCurrent15StatOutMulticastCountPortn OBJECT-TYPE
	SYNTAX  Counter64
	MAX-ACCESS read-only
	STATUS current
	DESCRIPTION
        "
        Client Current 15-min Output Multicast
        counter :This OID gives the current
        15-min Multicast counter value
        "
	::= { pm1001lhPerfDatacomClientCurrent15StatEntry 35 }


pm1001lhperfdatacomclientCurrent15StatOutBroadcastCountInvPortn OBJECT-TYPE
	SYNTAX  EkiOnOff
	MAX-ACCESS read-only
	STATUS current
	DESCRIPTION
        "
        Client Current 15-min Output Broadcast
        counter inv. :This OID indicates
        that the current 15-min Broadcast
        counter is invalid
        "
	::= { pm1001lhPerfDatacomClientCurrent15StatEntry 32 }


pm1001lhperfdatacomclientCurrent15StatOutBroadcastCountPortn OBJECT-TYPE
	SYNTAX  Counter64
	MAX-ACCESS read-only
	STATUS current
	DESCRIPTION
        "
        Client Current 15-min Output Broadcast
        counter :This OID gives the current
        15-min Broadcast counter value
        "
	::= { pm1001lhPerfDatacomClientCurrent15StatEntry 33 }


pm1001lhperfdatacomclientCurrent15StatOutBytesCountInvPortn OBJECT-TYPE
	SYNTAX  EkiOnOff
	MAX-ACCESS read-only
	STATUS current
	DESCRIPTION
        "
        Client Current 15-min Output Bytes
        counter inv. :This OID indicates
        that the current 15-min Bytes counter
        is invalid
        "
	::= { pm1001lhPerfDatacomClientCurrent15StatEntry 26 }


pm1001lhperfdatacomclientCurrent15StatOutBytesCountPortn OBJECT-TYPE
	SYNTAX  Counter64
	MAX-ACCESS read-only
	STATUS current
	DESCRIPTION
        "
        Client Current 15-min Output Bytes
        counter :This OID gives the current
        15-min Bytes counter value
        "
	::= { pm1001lhPerfDatacomClientCurrent15StatEntry 27 }


pm1001lhperfdatacomclientCurrent15StatInNonunicastCountInvPortn OBJECT-TYPE
	SYNTAX  EkiOnOff
	MAX-ACCESS read-only
	STATUS current
	DESCRIPTION
        "
        Client Current 15-min Input Non
        Unicast counter inv. :This OID
         indicates that the current 15-min
        Non unicast counter is invalid
        "
	::= { pm1001lhPerfDatacomClientCurrent15StatEntry 22 }


pm1001lhperfdatacomclientCurrent15StatInNonunicastCountPortn OBJECT-TYPE
	SYNTAX  Counter64
	MAX-ACCESS read-only
	STATUS current
	DESCRIPTION
        "
        Client Current 15-min Input Non
        Unicast counter :This OID gives
        the current 15-min Non Unicast
         counter value
        "
	::= { pm1001lhPerfDatacomClientCurrent15StatEntry 23 }


pm1001lhperfdatacomclientCurrent15StatInUnicastCountInvPortn OBJECT-TYPE
	SYNTAX  EkiOnOff
	MAX-ACCESS read-only
	STATUS current
	DESCRIPTION
        "
        Client Current 15-min Input Unicast
        counter inv. :This OID indicates
        that the current 15-min Unicast
        counter is invalid
        "
	::= { pm1001lhPerfDatacomClientCurrent15StatEntry 20 }


pm1001lhperfdatacomclientCurrent15StatInUnicastCountPortn OBJECT-TYPE
	SYNTAX  Counter64
	MAX-ACCESS read-only
	STATUS current
	DESCRIPTION
        "
        Client Current 15-min Input Unicast
        counter :This OID gives the current
        15-min Unicast counter value
        "
	::= { pm1001lhPerfDatacomClientCurrent15StatEntry 21 }


pm1001lhperfdatacomclientCurrent15StatInMulticastCountInvPortn OBJECT-TYPE
	SYNTAX  EkiOnOff
	MAX-ACCESS read-only
	STATUS current
	DESCRIPTION
        "
        Client Current 15-min Input Multicast
        counter inv. :This OID indicates
        that the current 15-min Multicast
        counter is invalid
        "
	::= { pm1001lhPerfDatacomClientCurrent15StatEntry 10 }


pm1001lhperfdatacomclientCurrent15StatInMulticastCountPortn OBJECT-TYPE
	SYNTAX  Counter64
	MAX-ACCESS read-only
	STATUS current
	DESCRIPTION
        "
        Client Current 15-min Input Multicast
        counter :This OID gives the current
        15-min Multicast counter value
        "
	::= { pm1001lhPerfDatacomClientCurrent15StatEntry 11 }


pm1001lhperfdatacomclientCurrent15StatInBroadcastCountInvPortn OBJECT-TYPE
	SYNTAX  EkiOnOff
	MAX-ACCESS read-only
	STATUS current
	DESCRIPTION
        "
        Client Current 15-min Input Broadcast
        counter inv. :This OID indicates
        that the current 15-min Broadcast
        counter is invalid
        "
	::= { pm1001lhPerfDatacomClientCurrent15StatEntry 8 }


pm1001lhperfdatacomclientCurrent15StatInBroadcastCountPortn OBJECT-TYPE
	SYNTAX  Counter64
	MAX-ACCESS read-only
	STATUS current
	DESCRIPTION
        "
        Client Current 15-min Input Broadcast
        counter :This OID gives the current
        15-min Broadcast counter value
        "
	::= { pm1001lhPerfDatacomClientCurrent15StatEntry 9 }


pm1001lhperfdatacomclientCurrent15StatInCrcCountInvPortn OBJECT-TYPE
	SYNTAX  EkiOnOff
	MAX-ACCESS read-only
	STATUS current
	DESCRIPTION
        "
        Client Current 15-min Input CRC
        counter inv. :This OID indicates
        that the current 15-min CRC counter
        is invalid
        "
	::= { pm1001lhPerfDatacomClientCurrent15StatEntry 4 }


pm1001lhperfdatacomclientCurrent15StatInCrcCountPortn OBJECT-TYPE
	SYNTAX  Counter64
	MAX-ACCESS read-only
	STATUS current
	DESCRIPTION
        "
        Client Current 15-min Input CRC
        counter :This OID gives the current
        15-min CRC counter value
        "
	::= { pm1001lhPerfDatacomClientCurrent15StatEntry 5 }


pm1001lhperfdatacomclientCurrent15StatInBytesCountInvPortn OBJECT-TYPE
	SYNTAX  EkiOnOff
	MAX-ACCESS read-only
	STATUS current
	DESCRIPTION
        "
        Client Current 15-min Input Bytes
        counter inv. :This OID indicates
        that the current 15-min Bytes counter
        is invalid
        "
	::= { pm1001lhPerfDatacomClientCurrent15StatEntry 2 }


pm1001lhperfdatacomclientCurrent15StatInBytesCountPortn OBJECT-TYPE
	SYNTAX  Counter64
	MAX-ACCESS read-only
	STATUS current
	DESCRIPTION
        "
        Client Current 15-min Input Bytes
        counter :This OID gives the current
        15-min Bytes counter value
        "
	::= { pm1001lhPerfDatacomClientCurrent15StatEntry 3 }


--- *****************************************************
---     Leaf of the datacomClientPast15Stat
--- *****************************************************
--- *********************************************************
---     TABLE for the pm1001lhPerfDatacomClientPast15StatHistory articles
--- *********************************************************

pm1001lhPerfDatacomClientPast15StatHistoryPort1Table OBJECT-TYPE
	SYNTAX  SEQUENCE OF Pm1001lhPerfDatacomClientPast15StatHistoryPort1Entry
	MAX-ACCESS not-accessible
	STATUS current
	DESCRIPTION
        "
        List of pm1001lhPerfDatacomClientPast15StatHistory
        Article
        "
	::= { pm1001lhMonClient 264 }


pm1001lhPerfDatacomClientPast15StatHistoryPort1Entry OBJECT-TYPE
	SYNTAX Pm1001lhPerfDatacomClientPast15StatHistoryPort1Entry
	MAX-ACCESS not-accessible
	STATUS current
	DESCRIPTION
        "
        Row definition for the pm1001lhPerfDatacomClientPast15StatHistory
        table
        "
	INDEX   { pm1001lhPerfDatacomClientPast15StatHistoryPort1Index }
	::= { pm1001lhPerfDatacomClientPast15StatHistoryPort1Table 1 }


Pm1001lhPerfDatacomClientPast15StatHistoryPort1Entry ::=
	SEQUENCE {
	pm1001lhPerfDatacomClientPast15StatHistoryPort1Index
		INTEGER,
	pm1001lhperfdatacomclientPast15StatOutNonunicastCountInvPort1
		EkiOnOff,
	pm1001lhperfdatacomclientPast15StatOutNonunicastCountPort1
		Counter64,
	pm1001lhperfdatacomclientPast15StatOutUnicastCountInvPort1
		EkiOnOff,
	pm1001lhperfdatacomclientPast15StatOutUnicastCountPort1
		Counter64,
	pm1001lhperfdatacomclientPast15StatOutMulticastCountInvPort1
		EkiOnOff,
	pm1001lhperfdatacomclientPast15StatOutMulticastCountPort1
		Counter64,
	pm1001lhperfdatacomclientPast15StatOutBroadcastCountInvPort1
		EkiOnOff,
	pm1001lhperfdatacomclientPast15StatOutBroadcastCountPort1
		Counter64,
	pm1001lhperfdatacomclientPast15StatOutBytesCountInvPort1
		EkiOnOff,
	pm1001lhperfdatacomclientPast15StatOutBytesCountPort1
		Counter64,
	pm1001lhperfdatacomclientPast15StatInNonunicastCountInvPort1
		EkiOnOff,
	pm1001lhperfdatacomclientPast15StatInNonunicastCountPort1
		Counter64,
	pm1001lhperfdatacomclientPast15StatInUnicastCountInvPort1
		EkiOnOff,
	pm1001lhperfdatacomclientPast15StatInUnicastCountPort1
		Counter64,
	pm1001lhperfdatacomclientPast15StatInMulticastCountInvPort1
		EkiOnOff,
	pm1001lhperfdatacomclientPast15StatInMulticastCountPort1
		Counter64,
	pm1001lhperfdatacomclientPast15StatInBroadcastCountInvPort1
		EkiOnOff,
	pm1001lhperfdatacomclientPast15StatInBroadcastCountPort1
		Counter64,
	pm1001lhperfdatacomclientPast15StatInCrcCountInvPort1
		EkiOnOff,
	pm1001lhperfdatacomclientPast15StatInCrcCountPort1
		Counter64,
	pm1001lhperfdatacomclientPast15StatInBytesCountInvPort1
		EkiOnOff,
	pm1001lhperfdatacomclientPast15StatInBytesCountPort1
		Counter64
	}


pm1001lhPerfDatacomClientPast15StatHistoryPort1Index OBJECT-TYPE
	SYNTAX  INTEGER(0..128)
	MAX-ACCESS  read-only
	STATUS current
	DESCRIPTION
        "
        Index definition for the pm1001lhPerfDatacomClientPast15StatHistory
        table
        "
	::= { pm1001lhPerfDatacomClientPast15StatHistoryPort1Entry 1 }


pm1001lhperfdatacomclientPast15StatOutNonunicastCountInvPort1 OBJECT-TYPE
	SYNTAX  EkiOnOff
	MAX-ACCESS read-only
	STATUS current
	DESCRIPTION
        "
        Client Past 15-min Output Non
         Unicast counter inv. :This OID
        indicates that the past 15-min
         Non Unicast counter is invalid
        "
	::= { pm1001lhPerfDatacomClientPast15StatHistoryPort1Entry 44 }


pm1001lhperfdatacomclientPast15StatOutNonunicastCountPort1 OBJECT-TYPE
	SYNTAX  Counter64
	MAX-ACCESS read-only
	STATUS current
	DESCRIPTION
        "
        Client Past 15-min Output Non
         Unicast counter :This OID gives
        the past 15-min Non Unicast counter
        value
        "
	::= { pm1001lhPerfDatacomClientPast15StatHistoryPort1Entry 45 }


pm1001lhperfdatacomclientPast15StatOutUnicastCountInvPort1 OBJECT-TYPE
	SYNTAX  EkiOnOff
	MAX-ACCESS read-only
	STATUS current
	DESCRIPTION
        "
        Client Past 15-min Output Unicast
        counter inv. :This OID indicates
        that the past 15-min Unicast counter
        is invalid
        "
	::= { pm1001lhPerfDatacomClientPast15StatHistoryPort1Entry 42 }


pm1001lhperfdatacomclientPast15StatOutUnicastCountPort1 OBJECT-TYPE
	SYNTAX  Counter64
	MAX-ACCESS read-only
	STATUS current
	DESCRIPTION
        "
        Client Past 15-min Output Unicast
        counter :This OID gives the past
        15-min Unicast counter value
        "
	::= { pm1001lhPerfDatacomClientPast15StatHistoryPort1Entry 43 }


pm1001lhperfdatacomclientPast15StatOutMulticastCountInvPort1 OBJECT-TYPE
	SYNTAX  EkiOnOff
	MAX-ACCESS read-only
	STATUS current
	DESCRIPTION
        "
        Client Past 15-min Output Multicast
        counter inv. :This OID indicates
        that the past 15-min Multicast
         counter is invalid
        "
	::= { pm1001lhPerfDatacomClientPast15StatHistoryPort1Entry 34 }


pm1001lhperfdatacomclientPast15StatOutMulticastCountPort1 OBJECT-TYPE
	SYNTAX  Counter64
	MAX-ACCESS read-only
	STATUS current
	DESCRIPTION
        "
        Client Past 15-min Output Multicast
        counter :This OID gives the past
        15-min Multicast counter value
        "
	::= { pm1001lhPerfDatacomClientPast15StatHistoryPort1Entry 35 }


pm1001lhperfdatacomclientPast15StatOutBroadcastCountInvPort1 OBJECT-TYPE
	SYNTAX  EkiOnOff
	MAX-ACCESS read-only
	STATUS current
	DESCRIPTION
        "
        Client Past 15-min Output Broadcast
        counter inv. :This OID indicates
        that the past 15-min Broadcast
         counter is invalid
        "
	::= { pm1001lhPerfDatacomClientPast15StatHistoryPort1Entry 32 }


pm1001lhperfdatacomclientPast15StatOutBroadcastCountPort1 OBJECT-TYPE
	SYNTAX  Counter64
	MAX-ACCESS read-only
	STATUS current
	DESCRIPTION
        "
        Client Past 15-min Output Broadcast
        counter :This OID gives the past
        15-min Broadcast counter value
        "
	::= { pm1001lhPerfDatacomClientPast15StatHistoryPort1Entry 33 }


pm1001lhperfdatacomclientPast15StatOutBytesCountInvPort1 OBJECT-TYPE
	SYNTAX  EkiOnOff
	MAX-ACCESS read-only
	STATUS current
	DESCRIPTION
        "
        Client Past 15-min Output Bytes
        counter inv. :This OID indicates
        that the past 15-min Bytes counter
        is invalid
        "
	::= { pm1001lhPerfDatacomClientPast15StatHistoryPort1Entry 26 }


pm1001lhperfdatacomclientPast15StatOutBytesCountPort1 OBJECT-TYPE
	SYNTAX  Counter64
	MAX-ACCESS read-only
	STATUS current
	DESCRIPTION
        "
        Client Past 15-min Output Bytes
        counter :This OID gives the past
        15-min Bytes counter value
        "
	::= { pm1001lhPerfDatacomClientPast15StatHistoryPort1Entry 27 }


pm1001lhperfdatacomclientPast15StatInNonunicastCountInvPort1 OBJECT-TYPE
	SYNTAX  EkiOnOff
	MAX-ACCESS read-only
	STATUS current
	DESCRIPTION
        "
        Client Past 15-min Input Non Unicast
        counter inv. :This OID indicates
        that the past 15-min Non unicast
        counter is invalid
        "
	::= { pm1001lhPerfDatacomClientPast15StatHistoryPort1Entry 22 }


pm1001lhperfdatacomclientPast15StatInNonunicastCountPort1 OBJECT-TYPE
	SYNTAX  Counter64
	MAX-ACCESS read-only
	STATUS current
	DESCRIPTION
        "
        Client Past 15-min Input Non Unicast
        counter :This OID gives the past
        15-min Non Unicast counter value
        "
	::= { pm1001lhPerfDatacomClientPast15StatHistoryPort1Entry 23 }


pm1001lhperfdatacomclientPast15StatInUnicastCountInvPort1 OBJECT-TYPE
	SYNTAX  EkiOnOff
	MAX-ACCESS read-only
	STATUS current
	DESCRIPTION
        "
        Client Past 15-min Input Unicast
        counter inv. :This OID indicates
        that the past 15-min Unicast counter
        is invalid
        "
	::= { pm1001lhPerfDatacomClientPast15StatHistoryPort1Entry 20 }


pm1001lhperfdatacomclientPast15StatInUnicastCountPort1 OBJECT-TYPE
	SYNTAX  Counter64
	MAX-ACCESS read-only
	STATUS current
	DESCRIPTION
        "
        Client Past 15-min Input Unicast
        counter :This OID gives the past
        15-min Unicast counter value
        "
	::= { pm1001lhPerfDatacomClientPast15StatHistoryPort1Entry 21 }


pm1001lhperfdatacomclientPast15StatInMulticastCountInvPort1 OBJECT-TYPE
	SYNTAX  EkiOnOff
	MAX-ACCESS read-only
	STATUS current
	DESCRIPTION
        "
        Client Past 15-min Input Multicast
        counter inv. :This OID indicates
        that the past 15-min Multicast
         counter is invalid
        "
	::= { pm1001lhPerfDatacomClientPast15StatHistoryPort1Entry 10 }


pm1001lhperfdatacomclientPast15StatInMulticastCountPort1 OBJECT-TYPE
	SYNTAX  Counter64
	MAX-ACCESS read-only
	STATUS current
	DESCRIPTION
        "
        Client Past 15-min Input Multicast
        counter :This OID gives the past
        15-min Multicast counter value
        "
	::= { pm1001lhPerfDatacomClientPast15StatHistoryPort1Entry 11 }


pm1001lhperfdatacomclientPast15StatInBroadcastCountInvPort1 OBJECT-TYPE
	SYNTAX  EkiOnOff
	MAX-ACCESS read-only
	STATUS current
	DESCRIPTION
        "
        Client Past 15-min Input Broadcast
        counter inv. :This OID indicates
        that the past 15-min Broadcast
         counter is invalid
        "
	::= { pm1001lhPerfDatacomClientPast15StatHistoryPort1Entry 8 }


pm1001lhperfdatacomclientPast15StatInBroadcastCountPort1 OBJECT-TYPE
	SYNTAX  Counter64
	MAX-ACCESS read-only
	STATUS current
	DESCRIPTION
        "
        Client Past 15-min Input Broadcast
        counter :This OID gives the past
        15-min Broadcast counter value
        "
	::= { pm1001lhPerfDatacomClientPast15StatHistoryPort1Entry 9 }


pm1001lhperfdatacomclientPast15StatInCrcCountInvPort1 OBJECT-TYPE
	SYNTAX  EkiOnOff
	MAX-ACCESS read-only
	STATUS current
	DESCRIPTION
        "
        Client Past 15-min Input CRC counter
        inv. :This OID indicates that the
        past 15-min CRC counter is invalid
        "
	::= { pm1001lhPerfDatacomClientPast15StatHistoryPort1Entry 4 }


pm1001lhperfdatacomclientPast15StatInCrcCountPort1 OBJECT-TYPE
	SYNTAX  Counter64
	MAX-ACCESS read-only
	STATUS current
	DESCRIPTION
        "
        Client Past 15-min Input CRC counter
        :This OID gives the past 15-min
        CRC counter value
        "
	::= { pm1001lhPerfDatacomClientPast15StatHistoryPort1Entry 5 }


pm1001lhperfdatacomclientPast15StatInBytesCountInvPort1 OBJECT-TYPE
	SYNTAX  EkiOnOff
	MAX-ACCESS read-only
	STATUS current
	DESCRIPTION
        "
        Client Past 15-min Input Bytes
        counter inv. :This OID indicates
        that the past 15-min Bytes counter
        is invalid
        "
	::= { pm1001lhPerfDatacomClientPast15StatHistoryPort1Entry 2 }


pm1001lhperfdatacomclientPast15StatInBytesCountPort1 OBJECT-TYPE
	SYNTAX  Counter64
	MAX-ACCESS read-only
	STATUS current
	DESCRIPTION
        "
        Client Past 15-min Input Bytes
        counter :This OID gives the past
        15-min Bytes counter value
        "
	::= { pm1001lhPerfDatacomClientPast15StatHistoryPort1Entry 3 }


--- *****************************************************
---     Leaf of the datacomClientCurrent24Stat
--- *****************************************************
--- *********************************************************
---     TABLE for the pm1001lhPerfDatacomClientCurrent24Stat articles
--- *********************************************************

pm1001lhPerfDatacomClientCurrent24StatTable OBJECT-TYPE
	SYNTAX  SEQUENCE OF Pm1001lhPerfDatacomClientCurrent24StatEntry
	MAX-ACCESS not-accessible
	STATUS current
	DESCRIPTION
        "
        List of pm1001lhPerfDatacomClientCurrent24Stat
        Article
        "
	::= { pm1001lhMonClient 272 }


pm1001lhPerfDatacomClientCurrent24StatEntry OBJECT-TYPE
	SYNTAX Pm1001lhPerfDatacomClientCurrent24StatEntry
	MAX-ACCESS not-accessible
	STATUS current
	DESCRIPTION
        "
        Row definition for the pm1001lhPerfDatacomClientCurrent24Stat
        table
        "
	INDEX   { pm1001lhPerfDatacomClientCurrent24StatIndex }
	::= { pm1001lhPerfDatacomClientCurrent24StatTable 1 }


Pm1001lhPerfDatacomClientCurrent24StatEntry ::=
	SEQUENCE {
	pm1001lhPerfDatacomClientCurrent24StatIndex
		INTEGER,
	pm1001lhperfdatacomclientCurrent24StatOutNonunicastCountInvPortn
		EkiOnOff,
	pm1001lhperfdatacomclientCurrent24StatOutNonunicastCountPortn
		Counter64,
	pm1001lhperfdatacomclientCurrent24StatOutUnicastCountInvPortn
		EkiOnOff,
	pm1001lhperfdatacomclientCurrent24StatOutUnicastCountPortn
		Counter64,
	pm1001lhperfdatacomclientCurrent24StatOutMulticastCountInvPortn
		EkiOnOff,
	pm1001lhperfdatacomclientCurrent24StatOutMulticastCountPortn
		Counter64,
	pm1001lhperfdatacomclientCurrent24StatOutBroadcastCountInvPortn
		EkiOnOff,
	pm1001lhperfdatacomclientCurrent24StatOutBroadcastCountPortn
		Counter64,
	pm1001lhperfdatacomclientCurrent24StatOutBytesCountInvPortn
		EkiOnOff,
	pm1001lhperfdatacomclientCurrent24StatOutBytesCountPortn
		Counter64,
	pm1001lhperfdatacomclientCurrent24StatInNonunicastCountInvPortn
		EkiOnOff,
	pm1001lhperfdatacomclientCurrent24StatInNonunicastCountPortn
		Counter64,
	pm1001lhperfdatacomclientCurrent24StatInUnicastCountInvPortn
		EkiOnOff,
	pm1001lhperfdatacomclientCurrent24StatInUnicastCountPortn
		Counter64,
	pm1001lhperfdatacomclientCurrent24StatInMulticastCountInvPortn
		EkiOnOff,
	pm1001lhperfdatacomclientCurrent24StatInMulticastCountPortn
		Counter64,
	pm1001lhperfdatacomclientCurrent24StatInBroadcastCountInvPortn
		EkiOnOff,
	pm1001lhperfdatacomclientCurrent24StatInBroadcastCountPortn
		Counter64,
	pm1001lhperfdatacomclientCurrent24StatInCrcCountInvPortn
		EkiOnOff,
	pm1001lhperfdatacomclientCurrent24StatInCrcCountPortn
		Counter64,
	pm1001lhperfdatacomclientCurrent24StatInBytesCountInvPortn
		EkiOnOff,
	pm1001lhperfdatacomclientCurrent24StatInBytesCountPortn
		Counter64
	}


pm1001lhPerfDatacomClientCurrent24StatIndex OBJECT-TYPE
	SYNTAX  INTEGER(0..128)
	MAX-ACCESS  read-only
	STATUS current
	DESCRIPTION
        "
        Index definition for the pm1001lhPerfDatacomClientCurrent24Stat
        table
        "
	::= { pm1001lhPerfDatacomClientCurrent24StatEntry 1 }


pm1001lhperfdatacomclientCurrent24StatOutNonunicastCountInvPortn OBJECT-TYPE
	SYNTAX  EkiOnOff
	MAX-ACCESS read-only
	STATUS current
	DESCRIPTION
        "
        Client Current 24-hours Output
        Non Unicast counter inv. :This
         OID indicates that the current
        24-hours Non Unicast counter is
        invalid
        "
	::= { pm1001lhPerfDatacomClientCurrent24StatEntry 44 }


pm1001lhperfdatacomclientCurrent24StatOutNonunicastCountPortn OBJECT-TYPE
	SYNTAX  Counter64
	MAX-ACCESS read-only
	STATUS current
	DESCRIPTION
        "
        Client Current 24-hours Output
        Non Unicast counter :This OID gives
        the current 24-hours Non Unicast
        counter value
        "
	::= { pm1001lhPerfDatacomClientCurrent24StatEntry 45 }


pm1001lhperfdatacomclientCurrent24StatOutUnicastCountInvPortn OBJECT-TYPE
	SYNTAX  EkiOnOff
	MAX-ACCESS read-only
	STATUS current
	DESCRIPTION
        "
        Client Current 24-hours Output
        Unicast counter inv. :This OID
         indicates that the current 24-hours
        Unicast counter is invalid
        "
	::= { pm1001lhPerfDatacomClientCurrent24StatEntry 42 }


pm1001lhperfdatacomclientCurrent24StatOutUnicastCountPortn OBJECT-TYPE
	SYNTAX  Counter64
	MAX-ACCESS read-only
	STATUS current
	DESCRIPTION
        "
        Client Current 24-hours Output
        Unicast counter :This OID gives
        the current 24-hours Unicast counter
        value
        "
	::= { pm1001lhPerfDatacomClientCurrent24StatEntry 43 }


pm1001lhperfdatacomclientCurrent24StatOutMulticastCountInvPortn OBJECT-TYPE
	SYNTAX  EkiOnOff
	MAX-ACCESS read-only
	STATUS current
	DESCRIPTION
        "
        Client Current 24-hours Output
        Multicast counter inv. :This OID
        indicates that the current 24-hours
        Multicast counter is invalid
        "
	::= { pm1001lhPerfDatacomClientCurrent24StatEntry 34 }


pm1001lhperfdatacomclientCurrent24StatOutMulticastCountPortn OBJECT-TYPE
	SYNTAX  Counter64
	MAX-ACCESS read-only
	STATUS current
	DESCRIPTION
        "
        Client Current 24-hours Output
        Multicast counter :This OID gives
        the current 24-hours Multicast
         counter value
        "
	::= { pm1001lhPerfDatacomClientCurrent24StatEntry 35 }


pm1001lhperfdatacomclientCurrent24StatOutBroadcastCountInvPortn OBJECT-TYPE
	SYNTAX  EkiOnOff
	MAX-ACCESS read-only
	STATUS current
	DESCRIPTION
        "
        Client Current 24-hours Output
        Broadcast counter inv. :This OID
        indicates that the current 24-hours
        Broadcast counter is invalid
        "
	::= { pm1001lhPerfDatacomClientCurrent24StatEntry 32 }


pm1001lhperfdatacomclientCurrent24StatOutBroadcastCountPortn OBJECT-TYPE
	SYNTAX  Counter64
	MAX-ACCESS read-only
	STATUS current
	DESCRIPTION
        "
        Client Current 24-hours Output
        Broadcast counter :This OID gives
        the current 24-hours Broadcast
         counter value
        "
	::= { pm1001lhPerfDatacomClientCurrent24StatEntry 33 }


pm1001lhperfdatacomclientCurrent24StatOutBytesCountInvPortn OBJECT-TYPE
	SYNTAX  EkiOnOff
	MAX-ACCESS read-only
	STATUS current
	DESCRIPTION
        "
        Client Current 24-hours Output
        Bytes counter inv. :This OID indicates
        that the current 24-hours Bytes
        counter is invalid
        "
	::= { pm1001lhPerfDatacomClientCurrent24StatEntry 26 }


pm1001lhperfdatacomclientCurrent24StatOutBytesCountPortn OBJECT-TYPE
	SYNTAX  Counter64
	MAX-ACCESS read-only
	STATUS current
	DESCRIPTION
        "
        Client Current 24-hours Output
        Bytes counter :This OID gives the
        current 24-hours Bytes counter
         value
        "
	::= { pm1001lhPerfDatacomClientCurrent24StatEntry 27 }


pm1001lhperfdatacomclientCurrent24StatInNonunicastCountInvPortn OBJECT-TYPE
	SYNTAX  EkiOnOff
	MAX-ACCESS read-only
	STATUS current
	DESCRIPTION
        "
        Client Current 24-hours Input
         Non Unicast counter inv. :This
        OID indicates that the current
         24-hours Non unicast counter is
        invalid
        "
	::= { pm1001lhPerfDatacomClientCurrent24StatEntry 22 }


pm1001lhperfdatacomclientCurrent24StatInNonunicastCountPortn OBJECT-TYPE
	SYNTAX  Counter64
	MAX-ACCESS read-only
	STATUS current
	DESCRIPTION
        "
        Client Current 24-hours Input
         Non Unicast counter :This OID
         gives the current 24-hours Non
        Unicast counter value
        "
	::= { pm1001lhPerfDatacomClientCurrent24StatEntry 23 }


pm1001lhperfdatacomclientCurrent24StatInUnicastCountInvPortn OBJECT-TYPE
	SYNTAX  EkiOnOff
	MAX-ACCESS read-only
	STATUS current
	DESCRIPTION
        "
        Client Current 24-hours Input
         Unicast counter inv. :This OID
        indicates that the current 24-hours
        Unicast counter is invalid
        "
	::= { pm1001lhPerfDatacomClientCurrent24StatEntry 20 }


pm1001lhperfdatacomclientCurrent24StatInUnicastCountPortn OBJECT-TYPE
	SYNTAX  Counter64
	MAX-ACCESS read-only
	STATUS current
	DESCRIPTION
        "
        Client Current 24-hours Input
         Unicast counter :This OID gives
        the current 24-hours Unicast counter
        value
        "
	::= { pm1001lhPerfDatacomClientCurrent24StatEntry 21 }


pm1001lhperfdatacomclientCurrent24StatInMulticastCountInvPortn OBJECT-TYPE
	SYNTAX  EkiOnOff
	MAX-ACCESS read-only
	STATUS current
	DESCRIPTION
        "
        Client Current 24-hours Input
         Multicast counter inv. :This OID
        indicates that the current 24-hours
        Multicast counter is invalid
        "
	::= { pm1001lhPerfDatacomClientCurrent24StatEntry 10 }


pm1001lhperfdatacomclientCurrent24StatInMulticastCountPortn OBJECT-TYPE
	SYNTAX  Counter64
	MAX-ACCESS read-only
	STATUS current
	DESCRIPTION
        "
        Client Current 24-hours Input
         Multicast counter :This OID gives
        the current 24-hours Multicast
         counter value
        "
	::= { pm1001lhPerfDatacomClientCurrent24StatEntry 11 }


pm1001lhperfdatacomclientCurrent24StatInBroadcastCountInvPortn OBJECT-TYPE
	SYNTAX  EkiOnOff
	MAX-ACCESS read-only
	STATUS current
	DESCRIPTION
        "
        Client Current 24-hours Input
         Broadcast counter inv. :This OID
        indicates that the current 24-hours
        Broadcast counter is invalid
        "
	::= { pm1001lhPerfDatacomClientCurrent24StatEntry 8 }


pm1001lhperfdatacomclientCurrent24StatInBroadcastCountPortn OBJECT-TYPE
	SYNTAX  Counter64
	MAX-ACCESS read-only
	STATUS current
	DESCRIPTION
        "
        Client Current 24-hours Input
         Broadcast counter :This OID gives
        the current 24-hours Broadcast
         counter value
        "
	::= { pm1001lhPerfDatacomClientCurrent24StatEntry 9 }


pm1001lhperfdatacomclientCurrent24StatInCrcCountInvPortn OBJECT-TYPE
	SYNTAX  EkiOnOff
	MAX-ACCESS read-only
	STATUS current
	DESCRIPTION
        "
        Client Current 24-hours Input
         CRC counter inv. :This OID indicates
        that the current 24-hours CRC counter
        is invalid
        "
	::= { pm1001lhPerfDatacomClientCurrent24StatEntry 4 }


pm1001lhperfdatacomclientCurrent24StatInCrcCountPortn OBJECT-TYPE
	SYNTAX  Counter64
	MAX-ACCESS read-only
	STATUS current
	DESCRIPTION
        "
        Client Current 24-hours Input
         CRC counter :This OID gives the
        current 24-hours CRC counter value
        "
	::= { pm1001lhPerfDatacomClientCurrent24StatEntry 5 }


pm1001lhperfdatacomclientCurrent24StatInBytesCountInvPortn OBJECT-TYPE
	SYNTAX  EkiOnOff
	MAX-ACCESS read-only
	STATUS current
	DESCRIPTION
        "
        Client Current 24-hours Input
         Bytes counter inv. :This OID indicates
        that the current 24-hours Bytes
        counter is invalid
        "
	::= { pm1001lhPerfDatacomClientCurrent24StatEntry 2 }


pm1001lhperfdatacomclientCurrent24StatInBytesCountPortn OBJECT-TYPE
	SYNTAX  Counter64
	MAX-ACCESS read-only
	STATUS current
	DESCRIPTION
        "
        Client Current 24-hours Input
         Bytes counter :This OID gives
         the current 24-hours Bytes counter
        value
        "
	::= { pm1001lhPerfDatacomClientCurrent24StatEntry 3 }


--- *****************************************************
---     Leaf of the datacomClientPast24Stat
--- *****************************************************
--- *********************************************************
---     TABLE for the pm1001lhPerfDatacomClientPast24StatHistory articles
--- *********************************************************

pm1001lhPerfDatacomClientPast24StatHistoryPort1Table OBJECT-TYPE
	SYNTAX  SEQUENCE OF Pm1001lhPerfDatacomClientPast24StatHistoryPort1Entry
	MAX-ACCESS not-accessible
	STATUS current
	DESCRIPTION
        "
        List of pm1001lhPerfDatacomClientPast24StatHistory
        Article
        "
	::= { pm1001lhMonClient 280 }


pm1001lhPerfDatacomClientPast24StatHistoryPort1Entry OBJECT-TYPE
	SYNTAX Pm1001lhPerfDatacomClientPast24StatHistoryPort1Entry
	MAX-ACCESS not-accessible
	STATUS current
	DESCRIPTION
        "
        Row definition for the pm1001lhPerfDatacomClientPast24StatHistory
        table
        "
	INDEX   { pm1001lhPerfDatacomClientPast24StatHistoryPort1Index }
	::= { pm1001lhPerfDatacomClientPast24StatHistoryPort1Table 1 }


Pm1001lhPerfDatacomClientPast24StatHistoryPort1Entry ::=
	SEQUENCE {
	pm1001lhPerfDatacomClientPast24StatHistoryPort1Index
		INTEGER,
	pm1001lhperfdatacomclientPast24StatOutNonunicastCountInvPort1
		EkiOnOff,
	pm1001lhperfdatacomclientPast24StatOutNonunicastCountPort1
		Counter64,
	pm1001lhperfdatacomclientPast24StatOutUnicastCountInvPort1
		EkiOnOff,
	pm1001lhperfdatacomclientPast24StatOutUnicastCountPort1
		Counter64,
	pm1001lhperfdatacomclientPast24StatOutMulticastCountInvPort1
		EkiOnOff,
	pm1001lhperfdatacomclientPast24StatOutMulticastCountPort1
		Counter64,
	pm1001lhperfdatacomclientPast24StatOutBroadcastCountInvPort1
		EkiOnOff,
	pm1001lhperfdatacomclientPast24StatOutBroadcastCountPort1
		Counter64,
	pm1001lhperfdatacomclientPast24StatOutBytesCountInvPort1
		EkiOnOff,
	pm1001lhperfdatacomclientPast24StatOutBytesCountPort1
		Counter64,
	pm1001lhperfdatacomclientPast24StatInNonunicastCountInvPort1
		EkiOnOff,
	pm1001lhperfdatacomclientPast24StatInNonunicastCountPort1
		Counter64,
	pm1001lhperfdatacomclientPast24StatInUnicastCountInvPort1
		EkiOnOff,
	pm1001lhperfdatacomclientPast24StatInUnicastCountPort1
		Counter64,
	pm1001lhperfdatacomclientPast24StatInMulticastCountInvPort1
		EkiOnOff,
	pm1001lhperfdatacomclientPast24StatInMulticastCountPort1
		Counter64,
	pm1001lhperfdatacomclientPast24StatInBroadcastCountInvPort1
		EkiOnOff,
	pm1001lhperfdatacomclientPast24StatInBroadcastCountPort1
		Counter64,
	pm1001lhperfdatacomclientPast24StatInCrcCountInvPort1
		EkiOnOff,
	pm1001lhperfdatacomclientPast24StatInCrcCountPort1
		Counter64,
	pm1001lhperfdatacomclientPast24StatInBytesCountInvPort1
		EkiOnOff,
	pm1001lhperfdatacomclientPast24StatInBytesCountPort1
		Counter64
	}


pm1001lhPerfDatacomClientPast24StatHistoryPort1Index OBJECT-TYPE
	SYNTAX  INTEGER(0..128)
	MAX-ACCESS  read-only
	STATUS current
	DESCRIPTION
        "
        Index definition for the pm1001lhPerfDatacomClientPast24StatHistory
        table
        "
	::= { pm1001lhPerfDatacomClientPast24StatHistoryPort1Entry 1 }


pm1001lhperfdatacomclientPast24StatOutNonunicastCountInvPort1 OBJECT-TYPE
	SYNTAX  EkiOnOff
	MAX-ACCESS read-only
	STATUS current
	DESCRIPTION
        "
        Client Past 24-hours Output Non
        Unicast counter inv. :This OID
         indicates that the past 24-hours
        Non Unicast counter is invalid
        "
	::= { pm1001lhPerfDatacomClientPast24StatHistoryPort1Entry 44 }


pm1001lhperfdatacomclientPast24StatOutNonunicastCountPort1 OBJECT-TYPE
	SYNTAX  Counter64
	MAX-ACCESS read-only
	STATUS current
	DESCRIPTION
        "
        Client Past 24-hours Output Non
        Unicast counter :This OID gives
        the past 24-hours Non Unicast counter
        value
        "
	::= { pm1001lhPerfDatacomClientPast24StatHistoryPort1Entry 45 }


pm1001lhperfdatacomclientPast24StatOutUnicastCountInvPort1 OBJECT-TYPE
	SYNTAX  EkiOnOff
	MAX-ACCESS read-only
	STATUS current
	DESCRIPTION
        "
        Client Past 24-hours Output Unicast
        counter inv. :This OID indicates
        that the past 24-hours Unicast
         counter is invalid
        "
	::= { pm1001lhPerfDatacomClientPast24StatHistoryPort1Entry 42 }


pm1001lhperfdatacomclientPast24StatOutUnicastCountPort1 OBJECT-TYPE
	SYNTAX  Counter64
	MAX-ACCESS read-only
	STATUS current
	DESCRIPTION
        "
        Client Past 24-hours Output Unicast
        counter :This OID gives the past
        24-hours Unicast counter value
        "
	::= { pm1001lhPerfDatacomClientPast24StatHistoryPort1Entry 43 }


pm1001lhperfdatacomclientPast24StatOutMulticastCountInvPort1 OBJECT-TYPE
	SYNTAX  EkiOnOff
	MAX-ACCESS read-only
	STATUS current
	DESCRIPTION
        "
        Client Past 24-hours Output Multicast
        counter inv. :This OID indicates
        that the past 24-hours Multicast
        counter is invalid
        "
	::= { pm1001lhPerfDatacomClientPast24StatHistoryPort1Entry 34 }


pm1001lhperfdatacomclientPast24StatOutMulticastCountPort1 OBJECT-TYPE
	SYNTAX  Counter64
	MAX-ACCESS read-only
	STATUS current
	DESCRIPTION
        "
        Client Past 24-hours Output Multicast
        counter :This OID gives the past
        24-hours Multicast counter value
        "
	::= { pm1001lhPerfDatacomClientPast24StatHistoryPort1Entry 35 }


pm1001lhperfdatacomclientPast24StatOutBroadcastCountInvPort1 OBJECT-TYPE
	SYNTAX  EkiOnOff
	MAX-ACCESS read-only
	STATUS current
	DESCRIPTION
        "
        Client Past 24-hours Output Broadcast
        counter inv. :This OID indicates
        that the past 24-hours Broadcast
        counter is invalid
        "
	::= { pm1001lhPerfDatacomClientPast24StatHistoryPort1Entry 32 }


pm1001lhperfdatacomclientPast24StatOutBroadcastCountPort1 OBJECT-TYPE
	SYNTAX  Counter64
	MAX-ACCESS read-only
	STATUS current
	DESCRIPTION
        "
        Client Past 24-hours Output Broadcast
        counter :This OID gives the past
        24-hours Broadcast counter value
        "
	::= { pm1001lhPerfDatacomClientPast24StatHistoryPort1Entry 33 }


pm1001lhperfdatacomclientPast24StatOutBytesCountInvPort1 OBJECT-TYPE
	SYNTAX  EkiOnOff
	MAX-ACCESS read-only
	STATUS current
	DESCRIPTION
        "
        Client Past 24-hours Output Bytes
        counter inv. :This OID indicates
        that the past 24-hours Bytes counter
        is invalid
        "
	::= { pm1001lhPerfDatacomClientPast24StatHistoryPort1Entry 26 }


pm1001lhperfdatacomclientPast24StatOutBytesCountPort1 OBJECT-TYPE
	SYNTAX  Counter64
	MAX-ACCESS read-only
	STATUS current
	DESCRIPTION
        "
        Client Past 24-hours Output Bytes
        counter :This OID gives the past
        24-hours Bytes counter value
        "
	::= { pm1001lhPerfDatacomClientPast24StatHistoryPort1Entry 27 }


pm1001lhperfdatacomclientPast24StatInNonunicastCountInvPort1 OBJECT-TYPE
	SYNTAX  EkiOnOff
	MAX-ACCESS read-only
	STATUS current
	DESCRIPTION
        "
        Client Past 24-hours Input Non
        Unicast counter inv. :This OID
         indicates that the past 24-hours
        Non unicast counter is invalid
        "
	::= { pm1001lhPerfDatacomClientPast24StatHistoryPort1Entry 22 }


pm1001lhperfdatacomclientPast24StatInNonunicastCountPort1 OBJECT-TYPE
	SYNTAX  Counter64
	MAX-ACCESS read-only
	STATUS current
	DESCRIPTION
        "
        Client Past 24-hours Input Non
        Unicast counter :This OID gives
        the past 24-hours Non Unicast counter
        value
        "
	::= { pm1001lhPerfDatacomClientPast24StatHistoryPort1Entry 23 }


pm1001lhperfdatacomclientPast24StatInUnicastCountInvPort1 OBJECT-TYPE
	SYNTAX  EkiOnOff
	MAX-ACCESS read-only
	STATUS current
	DESCRIPTION
        "
        Client Past 24-hours Input Unicast
        counter inv. :This OID indicates
        that the past 24-hours Unicast
         counter is invalid
        "
	::= { pm1001lhPerfDatacomClientPast24StatHistoryPort1Entry 20 }


pm1001lhperfdatacomclientPast24StatInUnicastCountPort1 OBJECT-TYPE
	SYNTAX  Counter64
	MAX-ACCESS read-only
	STATUS current
	DESCRIPTION
        "
        Client Past 24-hours Input Unicast
        counter :This OID gives the past
        24-hours Unicast counter value
        "
	::= { pm1001lhPerfDatacomClientPast24StatHistoryPort1Entry 21 }


pm1001lhperfdatacomclientPast24StatInMulticastCountInvPort1 OBJECT-TYPE
	SYNTAX  EkiOnOff
	MAX-ACCESS read-only
	STATUS current
	DESCRIPTION
        "
        Client Past 24-hours Input Multicast
        counter inv. :This OID indicates
        that the past 24-hours Multicast
        counter is invalid
        "
	::= { pm1001lhPerfDatacomClientPast24StatHistoryPort1Entry 10 }


pm1001lhperfdatacomclientPast24StatInMulticastCountPort1 OBJECT-TYPE
	SYNTAX  Counter64
	MAX-ACCESS read-only
	STATUS current
	DESCRIPTION
        "
        Client Past 24-hours Input Multicast
        counter :This OID gives the past
        24-hours Multicast counter value
        "
	::= { pm1001lhPerfDatacomClientPast24StatHistoryPort1Entry 11 }


pm1001lhperfdatacomclientPast24StatInBroadcastCountInvPort1 OBJECT-TYPE
	SYNTAX  EkiOnOff
	MAX-ACCESS read-only
	STATUS current
	DESCRIPTION
        "
        Client Past 24-hours Input Broadcast
        counter inv. :This OID indicates
        that the past 24-hours Broadcast
        counter is invalid
        "
	::= { pm1001lhPerfDatacomClientPast24StatHistoryPort1Entry 8 }


pm1001lhperfdatacomclientPast24StatInBroadcastCountPort1 OBJECT-TYPE
	SYNTAX  Counter64
	MAX-ACCESS read-only
	STATUS current
	DESCRIPTION
        "
        Client Past 24-hours Input Broadcast
        counter :This OID gives the past
        24-hours Broadcast counter value
        "
	::= { pm1001lhPerfDatacomClientPast24StatHistoryPort1Entry 9 }


pm1001lhperfdatacomclientPast24StatInCrcCountInvPort1 OBJECT-TYPE
	SYNTAX  EkiOnOff
	MAX-ACCESS read-only
	STATUS current
	DESCRIPTION
        "
        Client Past 24-hours Input CRC
        counter inv. :This OID indicates
        that the past 24-hours CRC counter
        is invalid
        "
	::= { pm1001lhPerfDatacomClientPast24StatHistoryPort1Entry 4 }


pm1001lhperfdatacomclientPast24StatInCrcCountPort1 OBJECT-TYPE
	SYNTAX  Counter64
	MAX-ACCESS read-only
	STATUS current
	DESCRIPTION
        "
        Client Past 24-hours Input CRC
        counter :This OID gives the past
        24-hours CRC counter value
        "
	::= { pm1001lhPerfDatacomClientPast24StatHistoryPort1Entry 5 }


pm1001lhperfdatacomclientPast24StatInBytesCountInvPort1 OBJECT-TYPE
	SYNTAX  EkiOnOff
	MAX-ACCESS read-only
	STATUS current
	DESCRIPTION
        "
        Client Past 24-hours Input Bytes
        counter inv. :This OID indicates
        that the past 24-hours Bytes counter
        is invalid
        "
	::= { pm1001lhPerfDatacomClientPast24StatHistoryPort1Entry 2 }


pm1001lhperfdatacomclientPast24StatInBytesCountPort1 OBJECT-TYPE
	SYNTAX  Counter64
	MAX-ACCESS read-only
	STATUS current
	DESCRIPTION
        "
        Client Past 24-hours Input Bytes
        counter :This OID gives the past
        24-hours Bytes counter value
        "
	::= { pm1001lhPerfDatacomClientPast24StatHistoryPort1Entry 3 }



pm1001lhPerfEnable OBJECT-TYPE
	SYNTAX EkiOnOff
	MAX-ACCESS read-write
	STATUS current
	DESCRIPTION
        "
        Perf. Mon. Enable :This OID enables
        the Performance Monitoring application
        "
	::= { pm1001lhMonSync 257 }


pm1001lhPerf15minSync OBJECT-TYPE
	SYNTAX EkiOnOff
	MAX-ACCESS read-write
	STATUS current
	DESCRIPTION
        "
        Perf. Mon. 15-min sync. :This
         OID must be used in external synchronisation
        mode only to send a 15-min synchronisation
        command
        "
	::= { pm1001lhMonSync 259 }


pm1001lhPerf24hSync OBJECT-TYPE
	SYNTAX EkiOnOff
	MAX-ACCESS read-write
	STATUS current
	DESCRIPTION
        "
        Perf. Mon. 24-hours sync. :This
        OID must be used in external synchronisation
        mode only to send a 24-hours synchronisation
        command
        "
	::= { pm1001lhMonSync 260 }


pm1001lhPerf15MinShort OBJECT-TYPE
	SYNTAX EkiOnOff
	MAX-ACCESS read-write
	STATUS current
	DESCRIPTION
        "
        15-min period is short :This OID
        indicates that the 15-min period
        lasts less than 890 seconds
        "
	::= { pm1001lhMonTimeStamp 1 }


pm1001lhPerf15MinLong OBJECT-TYPE
	SYNTAX EkiOnOff
	MAX-ACCESS read-write
	STATUS current
	DESCRIPTION
        "
        15-min period is long :This OID
        indicates that the 15-min period
        lasts more than 910 seconds
        "
	::= { pm1001lhMonTimeStamp 2 }


pm1001lhPerf24HoursShort OBJECT-TYPE
	SYNTAX Counter32
	MAX-ACCESS read-write
	STATUS current
	DESCRIPTION
        "
        24-hours period is short :This
        OID indicates that 24-hours period
        lasts less than 86390 seconds
        "
	::= { pm1001lhMonTimeStamp 5 }


pm1001lhPerf24HoursLong OBJECT-TYPE
	SYNTAX Counter32
	MAX-ACCESS read-write
	STATUS current
	DESCRIPTION
        "
        24-hours period is long :This
         OID indicates that 24-hours period
        lasts more than 86410 seconds
        "
	::= { pm1001lhMonTimeStamp 6 }


pm1001lhPerfCurrent15MinElapsedTime OBJECT-TYPE
	SYNTAX Counter32
	MAX-ACCESS read-write
	STATUS current
	DESCRIPTION
        "
        Current 15min period Elapsed Time
         :This OID gives the number of
         seconds elapsed in the current
        15-minutes period
        "
	::= { pm1001lhMonTimeStamp 7 }


pm1001lhPerfCurrent24HoursElapsedTime OBJECT-TYPE
	SYNTAX Counter32
	MAX-ACCESS read-write
	STATUS current
	DESCRIPTION
        "
        Current 24hours period Elapsed
        Time :This OID gives the number
        of seconds elapsed in the current
        24-hours period
        "
	::= { pm1001lhMonTimeStamp 8 }






--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pm1001lhDwlrestartProcess OBJECT IDENTIFIER ::= { pm1001lhDwlOther 0 }




pm1001lhDwlColdRestartProcessed OBJECT-TYPE
	  SYNTAX EkiOnOff
	  MAX-ACCESS read-only
	  STATUS current
	  DESCRIPTION
        "
        Cold Restart :This OID indicates
        that the module last restart was
        a Cold RESTART
        "
	  ::= { pm1001lhDwlrestartProcess 2 }



pm1001lhDwlWarmRestartProcessed OBJECT-TYPE
	  SYNTAX EkiOnOff
	  MAX-ACCESS read-only
	  STATUS current
	  DESCRIPTION
        "
        Warm Restart :This OID indicates
        that the module last restart was
        a Warm RESTART
        "
	  ::= { pm1001lhDwlrestartProcess 1 }



--- *****************************************************
---     LEAF for the swBanksUsed article
--- *****************************************************
pm1001lhDwlswBanksUsed OBJECT IDENTIFIER ::= { pm1001lhDwlOther 1 }




pm1001lhDwlSwBank2Notempty OBJECT-TYPE
	  SYNTAX EkiOnOff
	  MAX-ACCESS read-only
	  STATUS current
	  DESCRIPTION
        "
        SW bank 2 loaded  :This OID indicates
        a software is loaded in SW bank
        2  <Help>  This status indicates
        if the SW bank 2 contains SW package
        "
	  ::= { pm1001lhDwlswBanksUsed 6 }



pm1001lhDwlSwBank1Notempty OBJECT-TYPE
	  SYNTAX EkiOnOff
	  MAX-ACCESS read-only
	  STATUS current
	  DESCRIPTION
        "
        SW bank 1 loaded  :This OID indicates
        a software is loaded in SW bank
        1  <Help>  This status indicates
        if the SW bank 1 contains SW package
        "
	  ::= { pm1001lhDwlswBanksUsed 5 }



pm1001lhDwlSwBank2Used OBJECT-TYPE
	  SYNTAX EkiOnOff
	  MAX-ACCESS read-only
	  STATUS current
	  DESCRIPTION
        "
        SW bank 2 active  :This OID indicates
        the module is working on SW bank
        2  <Help>  This status indicates
        if the SW bank 2 is active or standby
        "
	  ::= { pm1001lhDwlswBanksUsed 2 }



pm1001lhDwlSwBank1Used OBJECT-TYPE
	  SYNTAX EkiOnOff
	  MAX-ACCESS read-only
	  STATUS current
	  DESCRIPTION
        "
        SW bank 1 active  :This OID indicates
        the module is working on SW bank
        1  <Help>  This status indicates
        if the SW bank 1 is active or standby
        "
	  ::= { pm1001lhDwlswBanksUsed 1 }



--- *****************************************************
---     LEAF for the gwBanksUsed article
--- *****************************************************
pm1001lhDwlgwBanksUsed OBJECT IDENTIFIER ::= { pm1001lhDwlOther 2 }




pm1001lhDwlGwBank4Notempty OBJECT-TYPE
	  SYNTAX EkiOnOff
	  MAX-ACCESS read-only
	  STATUS deprecated
	  DESCRIPTION
        "
        GW bank 4 loaded  :This OID indicates
        a gateware is loaded in GW bank
        4
        "
	  ::= { pm1001lhDwlgwBanksUsed 8 }



pm1001lhDwlGwBank3Notempty OBJECT-TYPE
	  SYNTAX EkiOnOff
	  MAX-ACCESS read-only
	  STATUS current
	  DESCRIPTION
        "
        GW bank 3 loaded  :This OID indicates
        a gateware is loaded in GW bank
        3  <Help>  This status indicates
        if the GW bank 3 contains GW package
        "
	  ::= { pm1001lhDwlgwBanksUsed 7 }



pm1001lhDwlGwBank2Notempty OBJECT-TYPE
	  SYNTAX EkiOnOff
	  MAX-ACCESS read-only
	  STATUS deprecated
	  DESCRIPTION
        "
        GW bank 2 loaded  :This OID indicates
        a gateware is loaded in GW bank
        2
        "
	  ::= { pm1001lhDwlgwBanksUsed 6 }



pm1001lhDwlGwBank1Notempty OBJECT-TYPE
	  SYNTAX EkiOnOff
	  MAX-ACCESS read-only
	  STATUS current
	  DESCRIPTION
        "
        GW bank 1 loaded  :This OID indicates
        a gateware is loaded in GW bank
        1  <Help>  This status indicates
        if the GW bank 1 contains GW package
        "
	  ::= { pm1001lhDwlgwBanksUsed 5 }



pm1001lhDwlGwBank4Used OBJECT-TYPE
	  SYNTAX EkiOnOff
	  MAX-ACCESS read-only
	  STATUS deprecated
	  DESCRIPTION
        "
        GW bank 4 active  :This OID indicates
        the module is working on GW bank
        4
        "
	  ::= { pm1001lhDwlgwBanksUsed 4 }



pm1001lhDwlGwBank3Used OBJECT-TYPE
	  SYNTAX EkiOnOff
	  MAX-ACCESS read-only
	  STATUS current
	  DESCRIPTION
        "
        GW bank 3 active  :This OID indicates
        the module is working on GW bank
        3  <Help>  This status indicates
        if the GW bank 3 is active or standby
        "
	  ::= { pm1001lhDwlgwBanksUsed 3 }



pm1001lhDwlGwBank2Used OBJECT-TYPE
	  SYNTAX EkiOnOff
	  MAX-ACCESS read-only
	  STATUS deprecated
	  DESCRIPTION
        "
        GW bank 2 active  :This OID indicates
        the module is working on GW bank
        2
        "
	  ::= { pm1001lhDwlgwBanksUsed 2 }



pm1001lhDwlGwBank1Used OBJECT-TYPE
	  SYNTAX EkiOnOff
	  MAX-ACCESS read-only
	  STATUS current
	  DESCRIPTION
        "
        GW bank 1 active  :This OID indicates
        the module is working on GW bank
        1  <Help>  This status indicates
        if the GW bank 1 is active or standby
        "
	  ::= { pm1001lhDwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pm1001lhCfgAccessCAisCsf OBJECT IDENTIFIER ::= { pm1001lhConfig 1 }



--- *****************************************************
---     LEAF for the table 0012
--- *****************************************************

pm1001lhCfgClientcaiscsfTable OBJECT-TYPE
	SYNTAX  SEQUENCE OF Pm1001lhCfgClientcaiscsfEntry
	MAX-ACCESS not-accessible
	STATUS current
	DESCRIPTION
        "
        List of  Article
        "
	::= { pm1001lhCfgAccessCAisCsf 1 }


pm1001lhCfgClientcaiscsfEntry OBJECT-TYPE
	SYNTAX Pm1001lhCfgClientcaiscsfEntry
	MAX-ACCESS not-accessible
	STATUS current
	DESCRIPTION
        "
        Row definition for the accessCAisCsf
        table
        "
	INDEX   { pm1001lhCfgClientcaiscsfIndex }
	::= { pm1001lhCfgClientcaiscsfTable 1 }


Pm1001lhCfgClientcaiscsfEntry ::=
	SEQUENCE {
	pm1001lhCfgClientcaiscsfIndex
		INTEGER,
	pm1001lhCfgCAisModePortn
		Unsigned32,
	pm1001lhCfgUpAccessioAlmPortn
		Unsigned32,
	pm1001lhCfgUpMapperDeAlmPortn
		Unsigned32,
	pm1001lhCfgDownAccessioAlmPortn
		Unsigned32,
	pm1001lhCfgDownMapperDeAlmPortn
		Unsigned32,
	pm1001lhCfgDownDfrmAlmPortn
		Unsigned32,
	pm1001lhCfgDownLineSyncAlarmsPortn
		Unsigned32
	}


pm1001lhCfgClientcaiscsfIndex OBJECT-TYPE
	SYNTAX  INTEGER(0..128)
	MAX-ACCESS  read-only
	STATUS current
	DESCRIPTION
        "
        Index definition for the clientcaiscsf
        table
        "
	::= { pm1001lhCfgClientcaiscsfEntry 1 }


pm1001lhCfgCAisModePortn OBJECT-TYPE
	SYNTAX  Unsigned32 (0..65536)
	MAX-ACCESS read-write
	STATUS current
	DESCRIPTION
        "
        CAIS mode  on Client Port :This
        register enables/disables port
          laser shutdown on CAIS insertion
        condition
        "
	::= { pm1001lhCfgClientcaiscsfEntry 3 }


pm1001lhCfgUpAccessioAlmPortn OBJECT-TYPE
	SYNTAX  Unsigned32 (0..65536)
	MAX-ACCESS read-write
	STATUS current
	DESCRIPTION
        "
        CSF contributors on Client Port
        :This register configures the contributors
        to upstream CSF insertion on the
        port.
        "
	::= { pm1001lhCfgClientcaiscsfEntry 9 }


pm1001lhCfgUpMapperDeAlmPortn OBJECT-TYPE
	SYNTAX  Unsigned32 (0..65536)
	MAX-ACCESS read-write
	STATUS current
	DESCRIPTION
        "
        CSF contributors on Client Port
        :This register configures the contributors
        to upstream CSF insertion on the
        port.
        "
	::= { pm1001lhCfgClientcaiscsfEntry 10 }


pm1001lhCfgDownAccessioAlmPortn OBJECT-TYPE
	SYNTAX  Unsigned32 (0..65536)
	MAX-ACCESS read-write
	STATUS current
	DESCRIPTION
        "
        CAIS contributors on Client Port
        :This register configures the contributors
        to downstream CAIS insertion on
         port.
        "
	::= { pm1001lhCfgClientcaiscsfEntry 17 }


pm1001lhCfgDownMapperDeAlmPortn OBJECT-TYPE
	SYNTAX  Unsigned32 (0..65536)
	MAX-ACCESS read-write
	STATUS current
	DESCRIPTION
        "
        CAIS contributors on Client Port
        :This register configures the contributors
        to downstream CAIS insertion on
         port.
        "
	::= { pm1001lhCfgClientcaiscsfEntry 18 }


pm1001lhCfgDownDfrmAlmPortn OBJECT-TYPE
	SYNTAX  Unsigned32 (0..65536)
	MAX-ACCESS read-write
	STATUS current
	DESCRIPTION
        "
        CAIS contributors on Client Port
        :This register configures the contributors
        to downstream CAIS insertion on
         port.
        "
	::= { pm1001lhCfgClientcaiscsfEntry 19 }


pm1001lhCfgDownLineSyncAlarmsPortn OBJECT-TYPE
	SYNTAX  Unsigned32 (0..65536)
	MAX-ACCESS read-write
	STATUS deprecated
	DESCRIPTION
        "
        CAIS contributors on Client Port
        :This register configures the contributors
        to downstream CAIS insertion on
         port.
        "
	::= { pm1001lhCfgClientcaiscsfEntry 20 }


--- *****************************************************
---     LEAF for the table Group startup
--- *****************************************************

pm1001lhCfgStartup OBJECT IDENTIFIER ::= { pm1001lhConfig 2 }



--- *****************************************************
---     LEAF for the table 2111
--- *****************************************************

pm1001lhCfgClientStartupTable OBJECT-TYPE
	SYNTAX  SEQUENCE OF Pm1001lhCfgClientStartupEntry
	MAX-ACCESS not-accessible
	STATUS current
	DESCRIPTION
        "
        List of  Article
        "
	::= { pm1001lhCfgStartup 1 }


pm1001lhCfgClientStartupEntry OBJECT-TYPE
	SYNTAX Pm1001lhCfgClientStartupEntry
	MAX-ACCESS not-accessible
	STATUS current
	DESCRIPTION
        "
        Row definition for the startup
        table
        "
	INDEX   { pm1001lhCfgClientStartupIndex }
	::= { pm1001lhCfgClientStartupTable 1 }


Pm1001lhCfgClientStartupEntry ::=
	SEQUENCE {
	pm1001lhCfgClientStartupIndex
		INTEGER,
	pm1001lhCfgSystConfPortPortn
		Unsigned32,
	pm1001lhCfgNetConfPortPortn
		Unsigned32,
	pm1001lhCfgPortsOptionsPortn
		Unsigned32
	}


pm1001lhCfgClientStartupIndex OBJECT-TYPE
	SYNTAX  INTEGER(0..128)
	MAX-ACCESS  read-only
	STATUS current
	DESCRIPTION
        "
        Index definition for the clientStartup
        table
        "
	::= { pm1001lhCfgClientStartupEntry 1 }


pm1001lhCfgSystConfPortPortn OBJECT-TYPE
	SYNTAX  Unsigned32 (0..65536)
	MAX-ACCESS read-write
	STATUS current
	DESCRIPTION
        "
        Default Settings on Client Port
        :This  register configures the
         default initialisation settings
        on the port.
        "
	::= { pm1001lhCfgClientStartupEntry 3 }


pm1001lhCfgNetConfPortPortn OBJECT-TYPE
	SYNTAX  Unsigned32 (0..65536)
	MAX-ACCESS read-write
	STATUS current
	DESCRIPTION
        "
        Default Protocol on Client Port
        :This register configures the default
        initialisation protocol on the
         port.
        "
	::= { pm1001lhCfgClientStartupEntry 4 }


pm1001lhCfgPortsOptionsPortn OBJECT-TYPE
	SYNTAX  Unsigned32 (0..65536)
	MAX-ACCESS read-write
	STATUS current
	DESCRIPTION
        "
        Default Options on Client Port
        :This register configures the default
        options on the client port
        "
	::= { pm1001lhCfgClientStartupEntry 6 }


--- *****************************************************
---     LEAF for the table 2191
--- *****************************************************

pm1001lhtablelineStartup OBJECT IDENTIFIER ::= { pm1001lhCfgStartup 2 }



pm1001lhCfgsynthTransLine OBJECT-TYPE
	  SYNTAX Unsigned32 (0..65536)
	  MAX-ACCESS read-write
	  STATUS current
	  DESCRIPTION
        "
        Default Settings on Line 1 :This
        register configures the default
        initialisation settings on Line
        port 1.
        "
	  ::= { pm1001lhtablelineStartup 2 }



pm1001lhCfglineOptions1 OBJECT-TYPE
	  SYNTAX Unsigned32 (0..65536)
	  MAX-ACCESS read-write
	  STATUS current
	  DESCRIPTION
        "
        Default Options on Active Line
        Port :This register configures
         the default options on the active
        line port
        "
	  ::= { pm1001lhtablelineStartup 5 }



--- *****************************************************
---     LEAF for the table 21AB
--- *****************************************************

pm1001lhCfgXfpTable OBJECT-TYPE
	SYNTAX  SEQUENCE OF Pm1001lhCfgXfpEntry
	MAX-ACCESS not-accessible
	STATUS current
	DESCRIPTION
        "
        List of  Article
        "
	::= { pm1001lhCfgStartup 3 }


pm1001lhCfgXfpEntry OBJECT-TYPE
	SYNTAX Pm1001lhCfgXfpEntry
	MAX-ACCESS not-accessible
	STATUS current
	DESCRIPTION
        "
        Row definition for the startup
        table
        "
	INDEX   { pm1001lhCfgXfpIndex }
	::= { pm1001lhCfgXfpTable 1 }


Pm1001lhCfgXfpEntry ::=
	SEQUENCE {
	pm1001lhCfgXfpIndex
		INTEGER,
	pm1001lhCfgSystConfXfpPortn
		Unsigned32,
	pm1001lhCfgDataRateConfXfpPortn
		Unsigned32
	}


pm1001lhCfgXfpIndex OBJECT-TYPE
	SYNTAX  INTEGER(0..128)
	MAX-ACCESS  read-only
	STATUS current
	DESCRIPTION
        "
        Index definition for the xfp table
        "
	::= { pm1001lhCfgXfpEntry 1 }


pm1001lhCfgSystConfXfpPortn OBJECT-TYPE
	SYNTAX  Unsigned32 (0..65536)
	MAX-ACCESS read-write
	STATUS current
	DESCRIPTION
        "
        Default settings on XFP Port :This
        register configures the default
        initialisation settings on XFP
         port.
        "
	::= { pm1001lhCfgXfpEntry 3 }


pm1001lhCfgDataRateConfXfpPortn OBJECT-TYPE
	SYNTAX  Unsigned32 (0..65536)
	MAX-ACCESS read-write
	STATUS deprecated
	DESCRIPTION
        "
        :Reserved
        "
	::= { pm1001lhCfgXfpEntry 4 }


--- *****************************************************
---     LEAF for the table 25A8
--- *****************************************************

pm1001lhCfgOtxtlhTable OBJECT-TYPE
	SYNTAX  SEQUENCE OF Pm1001lhCfgOtxtlhEntry
	MAX-ACCESS not-accessible
	STATUS current
	DESCRIPTION
        "
        List of  Article
        "
	::= { pm1001lhCfgStartup 4 }


pm1001lhCfgOtxtlhEntry OBJECT-TYPE
	SYNTAX Pm1001lhCfgOtxtlhEntry
	MAX-ACCESS not-accessible
	STATUS current
	DESCRIPTION
        "
        Row definition for the startup
        table
        "
	INDEX   { pm1001lhCfgOtxtlhIndex }
	::= { pm1001lhCfgOtxtlhTable 1 }


Pm1001lhCfgOtxtlhEntry ::=
	SEQUENCE {
	pm1001lhCfgOtxtlhIndex
		INTEGER,
	pm1001lhCfgLineOtxMiscPortn
		Unsigned32,
	pm1001lhCfgLineDitherRatePortn
		Unsigned32,
	pm1001lhCfgLineDitherFhzPortn
		Unsigned32,
	pm1001lhCfgLinePwrLaserPortn
		Unsigned32,
	pm1001lhCfgLineFCurrentPortn
		Unsigned32,
	pm1001lhCfgLineGridCurrentPortn
		Unsigned32,
	pm1001lhCfgFPortn
		Unsigned32,
	pm1001lhCfgReservedPortn
		Unsigned32,
	pm1001lhCfgLinePhotodiodeModePortn
		Unsigned32,
	pm1001lhCfgLinePhotodiodeValuePortn
		Unsigned32
	}


pm1001lhCfgOtxtlhIndex OBJECT-TYPE
	SYNTAX  INTEGER(0..128)
	MAX-ACCESS  read-only
	STATUS current
	DESCRIPTION
        "
        Index definition for the otxtlh
        table
        "
	::= { pm1001lhCfgOtxtlhEntry 1 }


pm1001lhCfgLineOtxMiscPortn OBJECT-TYPE
	SYNTAX  Unsigned32 (0..65536)
	MAX-ACCESS read-write
	STATUS current
	DESCRIPTION
        "
        Default Line OTX TLH miscellaneous
        :This register configures the start-up
        miscellaneous mode of the Line
         OTX TLH
        "
	::= { pm1001lhCfgOtxtlhEntry 3 }


pm1001lhCfgLineDitherRatePortn OBJECT-TYPE
	SYNTAX  Unsigned32 (0..65536)
	MAX-ACCESS read-write
	STATUS current
	DESCRIPTION
        "
        Default Line OTX TLH FM amplitude
        :This register configures the start-up
        width of the frequency modulation
        of the Line OTX TLH
        "
	::= { pm1001lhCfgOtxtlhEntry 4 }


pm1001lhCfgLineDitherFhzPortn OBJECT-TYPE
	SYNTAX  Unsigned32 (0..65536)
	MAX-ACCESS read-write
	STATUS current
	DESCRIPTION
        "
        Default Line OTX TLH FM frequency
        :This register configures the start-up
        frequency of the frequency modulation
        of the Line OTX TLH
        "
	::= { pm1001lhCfgOtxtlhEntry 5 }


pm1001lhCfgLinePwrLaserPortn OBJECT-TYPE
	SYNTAX  Unsigned32 (0..65536)
	MAX-ACCESS read-write
	STATUS current
	DESCRIPTION
        "
        Defaut Line OTX TLH output Power
        :This register configures the start-up
        output power of the Line OTX TLH
         (Unit = dBm)
        "
	::= { pm1001lhCfgOtxtlhEntry 6 }


pm1001lhCfgLineFCurrentPortn OBJECT-TYPE
	SYNTAX  Unsigned32 (0..65536)
	MAX-ACCESS read-write
	STATUS current
	DESCRIPTION
        "
        Default Line OTX TLH Channel :This
        register configures the start-up
        laser channel of the Line OTX TLH
        "
	::= { pm1001lhCfgOtxtlhEntry 7 }


pm1001lhCfgLineGridCurrentPortn OBJECT-TYPE
	SYNTAX  Unsigned32 (0..65536)
	MAX-ACCESS read-write
	STATUS current
	DESCRIPTION
        "
        Default Line OTX TLH Grid :This
        register configures the start-up
        laser grid of the Line OTX TLH
        "
	::= { pm1001lhCfgOtxtlhEntry 8 }


pm1001lhCfgFPortn OBJECT-TYPE
	SYNTAX  Unsigned32 (0..65536)
	MAX-ACCESS read-write
	STATUS current
	DESCRIPTION
        "
        Default Line OTX TLH lowest Freq
        :This register configures the start-up
        lowest frequency supported on the
        Line OTX TLH
        "
	::= { pm1001lhCfgOtxtlhEntry 9 }


pm1001lhCfgReservedPortn OBJECT-TYPE
	SYNTAX  Unsigned32 (0..65536)
	MAX-ACCESS read-write
	STATUS deprecated
	DESCRIPTION
        "
        :
        "
	::= { pm1001lhCfgOtxtlhEntry 10 }


pm1001lhCfgLinePhotodiodeModePortn OBJECT-TYPE
	SYNTAX  Unsigned32 (0..65536)
	MAX-ACCESS read-write
	STATUS current
	DESCRIPTION
        "
        Default Line OTX TLH APD mode
         :This register configures the
         start-up APD mode of the Line
         OTX TLH
        "
	::= { pm1001lhCfgOtxtlhEntry 11 }


pm1001lhCfgLinePhotodiodeValuePortn OBJECT-TYPE
	SYNTAX  Unsigned32 (0..65536)
	MAX-ACCESS read-write
	STATUS current
	DESCRIPTION
        "
        Default Line OTX TLH APD atten.
        :This register configures the start-up
        APD attenuation on the Line OTX
        TLH
        "
	::= { pm1001lhCfgOtxtlhEntry 12 }


--- *****************************************************
---     LEAF for the table Group labels
--- *****************************************************

pm1001lhCfgLabels OBJECT IDENTIFIER ::= { pm1001lhConfig 3 }



--- *****************************************************
---     LEAF for the table NO_VALUE
--- *****************************************************

pm1001lhCfgLabelclientTable OBJECT-TYPE
	SYNTAX  SEQUENCE OF Pm1001lhCfgLabelclientEntry
	MAX-ACCESS not-accessible
	STATUS current
	DESCRIPTION
        "
        List of  Article
        "
	::= { pm1001lhCfgLabels 1 }


pm1001lhCfgLabelclientEntry OBJECT-TYPE
	SYNTAX Pm1001lhCfgLabelclientEntry
	MAX-ACCESS not-accessible
	STATUS current
	DESCRIPTION
        "
        Row definition for the labels
         table
        "
	INDEX   { pm1001lhCfgLabelclientIndex }
	::= { pm1001lhCfgLabelclientTable 1 }


Pm1001lhCfgLabelclientEntry ::=
	SEQUENCE {
	pm1001lhCfgLabelclientIndex
		INTEGER,
	pm1001lhCfgLabelclientPortn
		DisplayString
	}


pm1001lhCfgLabelclientIndex OBJECT-TYPE
	SYNTAX  INTEGER(0..128)
	MAX-ACCESS  read-only
	STATUS current
	DESCRIPTION
        "
        Index definition for the labelclient
        table
        "
	::= { pm1001lhCfgLabelclientEntry 1 }


pm1001lhCfgLabelclientPortn OBJECT-TYPE
	SYNTAX  DisplayString( SIZE(1..16))
	MAX-ACCESS read-write
	STATUS current
	DESCRIPTION
        "
        Default settings on the label
         of the Ports :These registers
         configures the default initialisation
        settings of the labels of the ports.
        "
	::= { pm1001lhCfgLabelclientEntry 3 }


--- *****************************************************
---     LEAF for the table NO_VALUE
--- *****************************************************

pm1001lhCfgLabellineTable OBJECT-TYPE
	SYNTAX  SEQUENCE OF Pm1001lhCfgLabellineEntry
	MAX-ACCESS not-accessible
	STATUS current
	DESCRIPTION
        "
        List of  Article
        "
	::= { pm1001lhCfgLabels 2 }


pm1001lhCfgLabellineEntry OBJECT-TYPE
	SYNTAX Pm1001lhCfgLabellineEntry
	MAX-ACCESS not-accessible
	STATUS current
	DESCRIPTION
        "
        Row definition for the labels
         table
        "
	INDEX   { pm1001lhCfgLabellineIndex }
	::= { pm1001lhCfgLabellineTable 1 }


Pm1001lhCfgLabellineEntry ::=
	SEQUENCE {
	pm1001lhCfgLabellineIndex
		INTEGER,
	pm1001lhCfgLabellinePortn
		DisplayString
	}


pm1001lhCfgLabellineIndex OBJECT-TYPE
	SYNTAX  INTEGER(0..128)
	MAX-ACCESS  read-only
	STATUS current
	DESCRIPTION
        "
        Index definition for the labelline
        table
        "
	::= { pm1001lhCfgLabellineEntry 1 }


pm1001lhCfgLabellinePortn OBJECT-TYPE
	SYNTAX  DisplayString( SIZE(1..16))
	MAX-ACCESS read-write
	STATUS current
	DESCRIPTION
        "
        Default settings on the label
         of the lines :These registers
         configures the default initialisation
        settings of the labels of the lines.
        "
	::= { pm1001lhCfgLabellineEntry 3 }


--- *****************************************************
---     LEAF for the table Group startuptablefive
--- *****************************************************

pm1001lhCfgStartuptablefive OBJECT IDENTIFIER ::= { pm1001lhConfig 4 }



--- *****************************************************
---     LEAF for the table 0005
--- *****************************************************

pm1001lhCfgOtxtlhcapabilitiesTable OBJECT-TYPE
	SYNTAX  SEQUENCE OF Pm1001lhCfgOtxtlhcapabilitiesEntry
	MAX-ACCESS not-accessible
	STATUS current
	DESCRIPTION
        "
        List of  Article
        "
	::= { pm1001lhCfgStartuptablefive 1 }


pm1001lhCfgOtxtlhcapabilitiesEntry OBJECT-TYPE
	SYNTAX Pm1001lhCfgOtxtlhcapabilitiesEntry
	MAX-ACCESS not-accessible
	STATUS current
	DESCRIPTION
        "
        Row definition for the startuptablefive
        table
        "
	INDEX   { pm1001lhCfgOtxtlhcapabilitiesIndex }
	::= { pm1001lhCfgOtxtlhcapabilitiesTable 1 }


Pm1001lhCfgOtxtlhcapabilitiesEntry ::=
	SEQUENCE {
	pm1001lhCfgOtxtlhcapabilitiesIndex
		INTEGER,
	pm1001lhCfgComponentTypePortn
		Unsigned32,
	pm1001lhCfgMiscellaneousPortn
		Unsigned32,
	pm1001lhCfgFirstChannelPortn
		Unsigned32,
	pm1001lhCfgLastChannelPortn
		Unsigned32,
	pm1001lhCfgGridPortn
		Unsigned32
	}


pm1001lhCfgOtxtlhcapabilitiesIndex OBJECT-TYPE
	SYNTAX  INTEGER(0..128)
	MAX-ACCESS  read-only
	STATUS current
	DESCRIPTION
        "
        Index definition for the otxtlhcapabilities
        table
        "
	::= { pm1001lhCfgOtxtlhcapabilitiesEntry 1 }


pm1001lhCfgComponentTypePortn OBJECT-TYPE
	SYNTAX  Unsigned32 (0..65536)
	MAX-ACCESS read-only
	STATUS current
	DESCRIPTION
        "
        Component parameters :This OID
        defines the component parameters
        "
	::= { pm1001lhCfgOtxtlhcapabilitiesEntry 3 }


pm1001lhCfgMiscellaneousPortn OBJECT-TYPE
	SYNTAX  Unsigned32 (0..65536)
	MAX-ACCESS read-only
	STATUS current
	DESCRIPTION
        "
        Miscellaneous default settings
        :This OID defines the miscellaneous
        parameters
        "
	::= { pm1001lhCfgOtxtlhcapabilitiesEntry 4 }


pm1001lhCfgFirstChannelPortn OBJECT-TYPE
	SYNTAX  Unsigned32 (0..65536)
	MAX-ACCESS read-only
	STATUS current
	DESCRIPTION
        "
        Number of the first channel of
        the component :This OID defines
        the first channel number of the
        PM
        "
	::= { pm1001lhCfgOtxtlhcapabilitiesEntry 5 }


pm1001lhCfgLastChannelPortn OBJECT-TYPE
	SYNTAX  Unsigned32 (0..65536)
	MAX-ACCESS read-only
	STATUS current
	DESCRIPTION
        "
        Number of the last channel of
         the component :This OID defines
        the last channel number of the
         PM
        "
	::= { pm1001lhCfgOtxtlhcapabilitiesEntry 6 }


pm1001lhCfgGridPortn OBJECT-TYPE
	SYNTAX  Unsigned32 (0..65536)
	MAX-ACCESS read-only
	STATUS current
	DESCRIPTION
        "
        Grid value of the component :This
        OID defines the grid of the PM
        "
	::= { pm1001lhCfgOtxtlhcapabilitiesEntry 7 }



pm1001lhCfgWriteConfiguration  OBJECT-TYPE
	SYNTAX EkiOnOff
	MAX-ACCESS read-write
	STATUS current
	DESCRIPTION
	"Write configuration to module:This OID
	 writes the complete configuration to the module"
	::= { pm1001lhConfig 257 }






--- *****************************************************
---     TRAP OBJECTS
--- *****************************************************


pm1001lhtrapBoardNumber OBJECT-TYPE
	SYNTAX INTEGER(1..64)
	MAX-ACCESS read-only
	STATUS current
	DESCRIPTION
	"Last module which generates a trap"
	::= { pm1001lhtraps 1 }







--- *****************************************************
---     LINE TRAPS
--- *****************************************************

pm1001lhLineTrapNotUrgentGoesOn NOTIFICATION-TYPE
	OBJECTS {pm1001lhAlmLineDdmWarning, pm1001lhtrapBoardNumber}
	STATUS current
	--&FILTNAME    "PM1001LH Line Not Urgent ON"
	--&ACTIONS     { log, minor }
	--&MATCH       { pm1001lhAlmLineDdmWarning "on", pm1001lhtrapBoardNumber "$2"}
	--&MESG        "DDM Warning appears on Line Port of PM1001LH in Slot $2 ($A)"
	DESCRIPTION "Not urgent Line default is activated"
	::= { pm1001lhtraps 30 }

pm1001lhLineTrapNotUrgentGoesOff NOTIFICATION-TYPE
	OBJECTS {pm1001lhAlmLineDdmWarning, pm1001lhtrapBoardNumber}
	STATUS current
	--&FILTNAME    "PM1001LH Line Not Urgent OFF"
	--&ACTIONS     { log, normal }
	--&CLEARS      { "PM1001LH Line Not Urgent ON" }
	--&MATCH       { pm1001lhAlmLineDdmWarning "on", pm1001lhtrapBoardNumber "$2"}
	--&MESG        "DDM Warning disappears on Line Port of PM1001LH in Slot $2 ($A)"
	DESCRIPTION "Not urgent Line default disappeared"
	::= { pm1001lhtraps 31 }

pm1001lhLineTrapUrgentGoesOn NOTIFICATION-TYPE
	OBJECTS {pm1001lhAlmLineDdmAlm, pm1001lhtrapBoardNumber}
	STATUS current
	--&FILTNAME    "PM1001LH Line Urgent ON"
	--&ACTIONS     { log, major }
	--&MATCH       { pm1001lhAlmLineDdmAlm "on", pm1001lhtrapBoardNumber "$2"}
	--&MESG        "DDM Alarm appears on Line Port of PM1001LH in Slot $2 ($A)"
	DESCRIPTION "Urgent Line default is activated"
	::= { pm1001lhtraps 32 }

pm1001lhLineTrapUrgentGoesOff NOTIFICATION-TYPE
	OBJECTS {pm1001lhAlmLineDdmAlm, pm1001lhtrapBoardNumber}
	STATUS current
	--&FILTNAME    "PM1001LH Line Urgent OFF"
	--&ACTIONS     { log, normal }
	--&CLEARS      { "PM1001LH Line Urgent ON" }
	--&MATCH       { pm1001lhAlmLineDdmAlm "on", pm1001lhtrapBoardNumber "$2"}
	--&MESG        "DDM Alarm disappears on Line Port of PM1001LH in Slot $2 ($A)"
	DESCRIPTION "Urgent Line default disappeared"
	::= { pm1001lhtraps 33 }

pm1001lhLineTrapCritGoesOn NOTIFICATION-TYPE
	OBJECTS {pm1001lhAlmLineFail , pm1001lhAlmLineHwFail, pm1001lhtrapBoardNumber}
	STATUS current
	--&FILTNAME    "PM1001LH Line Fail ON"
	--&ACTIONS     { log, critical }
	--&MATCH       { pm1001lhAlmLineFail "on", pm1001lhAlmLineHwFail "*", pm1001lhtrapBoardNumber "$3"}
	--&MESG        "Line Port Down on PM1001LH in Slot $3 ($A)"

	--&FILTNAME    "PM1001LH Line HW Fail ON (Hidden)"
	--&ACTIONS     { info }
	--&MATCH       { pm1001lhAlmLineFail "*", pm1001lhAlmLineHwFail "on", pm1001lhtrapBoardNumber "$3"}
	--&MESG        "Line Port Down on PM1001LH in Slot $3 ($A)"
	DESCRIPTION "Critical Line default is activated"
	::= { pm1001lhtraps 34 }

pm1001lhLineTrapCritGoesOff NOTIFICATION-TYPE
	OBJECTS {pm1001lhAlmLineFail , pm1001lhAlmLineHwFail, pm1001lhtrapBoardNumber}
	STATUS current
	--&FILTNAME    "PM1001LH Line Fail OFF"
	--&ACTIONS     { log,  normal }
	--&CLEARS      { "PM1001LH Line Fail ON" }
	--&MATCH       { pm1001lhAlmLineFail "on", pm1001lhAlmLineHwFail "*", pm1001lhtrapBoardNumber "$3"}
	--&MESG        "Line Port Up on PM1001LH in Slot $3 ($A)"

	--&FILTNAME    "PM1001LH Line HW Fail OFF (Hidden)"
	--&ACTIONS     { info }
	--&MATCH       { pm1001lhAlmLineFail "*", pm1001lhAlmLineHwFail "on", pm1001lhtrapBoardNumber "$3"}
	--&MESG        "Line Port Up on PM1001LH in Slot $3 ($A)"
	DESCRIPTION "Critical Line default disappeared"
	::= { pm1001lhtraps 35 }






--- *****************************************************
---     CLIENT TRAPS
--- *****************************************************

pm1001lhClientTrapNotUrgentGoesOn NOTIFICATION-TYPE
	OBJECTS {pm1001lhAlmClientXfpDdmWarning, pm1001lhtrapBoardNumber}
	STATUS current
	--&FILTNAME    "PM1001LH Client Not Urgent ON"
	--&ACTIONS     { log, minor }
	--&MATCH       { pm1001lhAlmClientXfpDdmWarning "on", pm1001lhtrapBoardNumber "$2"}
	--&MESG        "DDM Warning appears on Client Port of PM1001LH in Slot $2 ($A)"
	DESCRIPTION "Not urgent client default is activated"
	::= { pm1001lhtraps 40 }

pm1001lhClientTrapNotUrgentGoesOff NOTIFICATION-TYPE
	OBJECTS {pm1001lhAlmClientXfpDdmWarning, pm1001lhtrapBoardNumber}
	STATUS current
	--&FILTNAME    "PM1001LH Client Not Urgent OFF"
	--&ACTIONS     { log, normal }
	--&CLEARS      { "PM1001LH Client Not Urgent ON" }
	--&MATCH       { pm1001lhAlmClientXfpDdmWarning "on", pm1001lhtrapBoardNumber "$2"}
	--&MESG        "DDM Warning appears on Client Port of PM1001LH in Slot $2 ($A)"
	DESCRIPTION "Not urgent client default disappeared"
	::= { pm1001lhtraps 41 }

pm1001lhClientTrapUrgentGoesOn NOTIFICATION-TYPE
	OBJECTS {pm1001lhAlmClientXfpDdmAlm, pm1001lhtrapBoardNumber}
	STATUS current
	--&FILTNAME    "PM1001LH Client Urgent ON"
	--&ACTIONS     { log, major }
	--&MATCH       { pm1001lhAlmClientXfpDdmAlm "on", pm1001lhtrapBoardNumber "$2"}
	--&MESG        "DDM Alarm appears on Client Port of PM1001LH in Slot $2 ($A)"
	DESCRIPTION "Urgent client default is activated"
	::= { pm1001lhtraps 42 }

pm1001lhClientTrapUrgentGoesOff NOTIFICATION-TYPE
	OBJECTS {pm1001lhAlmClientXfpDdmAlm, pm1001lhtrapBoardNumber}
	STATUS current
	--&FILTNAME    "PM1001LH Client Urgent OFF"
	--&ACTIONS     { log, normal }
	--&CLEARS      { "PM1001LH Client Urgent ON" }
	--&MATCH       { pm1001lhAlmClientXfpDdmAlm "on", pm1001lhtrapBoardNumber "$2"}
	--&MESG        "DDM Alarm disappears on Client Port of PM1001LH in Slot $2 ($A)"
	DESCRIPTION "Urgent client default disappeared"
	::= { pm1001lhtraps 43 }

pm1001lhClientTrapCritGoesOn NOTIFICATION-TYPE
	OBJECTS {pm1001lhAlmClientFail, pm1001lhAlmClientHwFail, pm1001lhtrapBoardNumber}
	STATUS current
	--&FILTNAME    "PM1001LH Client Fail ON"
	--&ACTIONS     { log, critical }
	--&MATCH       { pm1001lhAlmClientFail "on", pm1001lhAlmClientHwFail "*", pm1001lhtrapBoardNumber "$3"}
	--&MESG        "Client Port Down on PM1001LH in Slot $3 ($A)"

	--&FILTNAME    "PM1001LH Client HW Fail ON (Hidden)"
	--&ACTIONS     { info }
	--&MATCH       { pm1001lhAlmClientFail "*", pm1001lhAlmClientHwFail "on", pm1001lhtrapBoardNumber "$3"}
	--&MESG        "Client Port Down on PM1001LH in Slot $3 ($A)"
	DESCRIPTION "Critical client default is activated"
	::= { pm1001lhtraps 44 }

pm1001lhClientTrapCritGoesOff NOTIFICATION-TYPE
	OBJECTS {pm1001lhAlmClientFail, pm1001lhAlmClientHwFail, pm1001lhtrapBoardNumber}
	STATUS current
	--&FILTNAME    "PM1001LH Client Fail OFF"
	--&ACTIONS     { log, normal }
	--&CLEARS      { "PM1001LH Client Fail ON" }
	--&MATCH       { pm1001lhAlmClientFail "on", pm1001lhAlmClientHwFail "*", pm1001lhtrapBoardNumber "$3"}
	--&MESG        "Client Port Up on PM1001LH in Slot $3 ($A)"

	--&FILTNAME    "PM1001LH Client HW Fail OFF (Hidden)"
	--&ACTIONS     { info }
	--&MATCH       { pm1001lhAlmClientFail "*", pm1001lhAlmClientHwFail "on", pm1001lhtrapBoardNumber "$3"}
	--&MESG        "Client Port Up on PM1001LH in Slot $3 ($A)"
	DESCRIPTION "Critical client default disappeared"
	::= { pm1001lhtraps 45 }






--- *****************************************************
---     HW TRAPS
--- *****************************************************

pm1001lhPowerTrapUrgentGoesOn NOTIFICATION-TYPE
	OBJECTS {pm1001lhAlmDefFuseB, pm1001lhAlmDefFuseA , pm1001lhtrapBoardNumber}
	STATUS current
	--&FILTNAME    "PM1001LH Fuse A Fail ON"
	--&ACTIONS     { log, major }
	--&MATCH       { pm1001lhAlmDefFuseB "*", pm1001lhAlmDefFuseA "on", pm1001lhtrapBoardNumber "$3"}
	--&MESG        "Power Input A Fail on PM1001LH in Slot $3 ($A)"

	--&FILTNAME    "PM1001LH Fuse B Fail ON"
	--&ACTIONS     { log, major }
	--&MATCH       { pm1001lhAlmDefFuseB "on", pm1001lhAlmDefFuseA "*", pm1001lhtrapBoardNumber "$3"}
	--&MESG        "Power Input B Fail on PM1001LH in Slot $3 ($A)"
	DESCRIPTION "Urgent power supply default is activated"
	::= { pm1001lhtraps 50 }

pm1001lhPowerTrapUrgentGoesOff NOTIFICATION-TYPE
	OBJECTS {pm1001lhAlmDefFuseB, pm1001lhAlmDefFuseA , pm1001lhtrapBoardNumber}
	STATUS current
	--&FILTNAME    "PM1001LH Fuse A&B Fail OFF"
	--&ACTIONS     { log, normal}
	--&CLEARS      { "PM1001LH Fuse A Fail ON", "PM1001LH Fuse B Fail ON" }
	--&MATCH       { pm1001lhAlmDefFuseB "on", pm1001lhAlmDefFuseA "on", pm1001lhtrapBoardNumber "$3"}
	--&MESG        "Power Inputs A and B Present on PM1001LH in Slot $3 ($A)"
	DESCRIPTION "Urgent power supply default disappeared"
	::= { pm1001lhtraps 51 }






END
