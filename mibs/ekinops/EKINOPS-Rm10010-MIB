-- *****************************************************************
-- EKINOPS-Rm10010.TXT:  MIB
--
--MIB Part Number:3MI00027ADCA
--MIB Version:03
--
-- Copyright (c) 2016 by Ekinops
-- All rights reserved.
--
-- *****************************************************************

EKINOPS-Rm10010-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress
        		FROM SNMPv2-SMI
 	TEXTUAL-CONVENTION,
	DisplayString
                FROM SNMPv2-TC;

moduleRm10010 MODULE-IDENTITY
        LAST-UPDATED "201606020000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.fr"
        DESCRIPTION
          "Creation."

	REVISION "201111090000Z"
	DESCRIPTION
	  "Creation"
	REVISION "201111090000Z"
	DESCRIPTION
	  "Creation"
	REVISION "201206180000Z"
	DESCRIPTION
	  "Client In Loop insertion,Multiprotocol insertion"
	REVISION "201206290000Z"
	DESCRIPTION
	  "Client In Loop insertion,Multiprotocol insertion"
	REVISION "201207040000Z"
	DESCRIPTION
	  "New measurements on line"
	REVISION "201207100000Z"
	DESCRIPTION
	  "Fix on traps"
	REVISION "201207240000Z"
	DESCRIPTION
	  "New measurements on line"
	REVISION "201208290000Z"
	DESCRIPTION
	  "Add Oid for Measurements reset"
	REVISION "201211130000Z"
	DESCRIPTION
	  "Fan Speed Control"
	REVISION "201309050000Z"
	DESCRIPTION
	  "Measurement Label modification"
	REVISION "201401160000Z"
	DESCRIPTION
	  "Add ProbCause on CSF detected"
	REVISION "201404010000Z"
	DESCRIPTION
	  "Probcause,AlarmType - NMS completion"
	REVISION "201410140000Z"
	DESCRIPTION
	  "OSNR help completion"
	REVISION "201501210000Z"
	DESCRIPTION
	  "Labels cosmetic updates"
	REVISION "201506260000Z"
	DESCRIPTION
	  "Add Performance Oids"
	REVISION "201510120000Z"
	DESCRIPTION
	  "OVL on SNMP"
	REVISION "201510120000Z"
	DESCRIPTION
	  "OVL on SNMP-Object name on perf datacom"
	REVISION "201510200000Z"
	DESCRIPTION
	  "Add F0 objet"
	REVISION "201604290000Z"
	DESCRIPTION
	  "Datacom Perf SNMP objects corrections"
	REVISION "201605200000Z"
	DESCRIPTION
	  "New AlarmType – synthesisAlarm (12)"
	REVISION "201606020000Z"
	DESCRIPTION
	  "Capabilities objects of Table 5"
        ::= { ekinops 53 }



--- *****************************************************
---     LEAF LEVEL 2
--- *****************************************************


rm10010alarms OBJECT IDENTIFIER ::= { moduleRm10010 2 }
rm10010AlmOther OBJECT IDENTIFIER ::= { rm10010alarms 1 }
rm10010AlmOtherNurg OBJECT IDENTIFIER ::= { rm10010AlmOther 1 }
rm10010AlmOtherUrg OBJECT IDENTIFIER ::= { rm10010AlmOther 2 }
rm10010AlmOtherCrit OBJECT IDENTIFIER ::= { rm10010AlmOther 3 }

rm10010AlmClient OBJECT IDENTIFIER ::= { rm10010alarms 2 }
rm10010AlmClientNurg OBJECT IDENTIFIER ::= { rm10010AlmClient 1 }
rm10010AlmClientUrg OBJECT IDENTIFIER ::= { rm10010AlmClient 2 }
rm10010AlmClientCrit OBJECT IDENTIFIER ::= { rm10010AlmClient 3 }

rm10010AlmLine OBJECT IDENTIFIER ::= { rm10010alarms 3 }
rm10010AlmLineNurg OBJECT IDENTIFIER ::= { rm10010AlmLine 1 }
rm10010AlmLineUrg OBJECT IDENTIFIER ::= { rm10010AlmLine 2 }
rm10010AlmLineCrit OBJECT IDENTIFIER ::= { rm10010AlmLine 3 }





rm10010measures OBJECT IDENTIFIER ::= { moduleRm10010 3 }
rm10010MesrOther OBJECT IDENTIFIER ::= { rm10010measures 1 }
rm10010MesrClient OBJECT IDENTIFIER ::= { rm10010measures 2 }
rm10010MesrLine OBJECT IDENTIFIER ::= { rm10010measures 3 }




rm10010counters OBJECT IDENTIFIER ::= { moduleRm10010 4 }
rm10010CntOther OBJECT IDENTIFIER ::= { rm10010counters 1 }
rm10010CntClient OBJECT IDENTIFIER ::= { rm10010counters 2 }
rm10010CntLine OBJECT IDENTIFIER ::= { rm10010counters 3 }


rm10010controlsWrite OBJECT IDENTIFIER ::= { moduleRm10010 6 }
rm10010CtrlOther OBJECT IDENTIFIER ::= { rm10010controlsWrite 1 }
rm10010CtrlClient OBJECT IDENTIFIER ::= { rm10010controlsWrite 2 }
rm10010CtrlLine OBJECT IDENTIFIER ::= { rm10010controlsWrite 3 }

rm10010ri OBJECT IDENTIFIER ::= { moduleRm10010 7 }
rm10010riTable OBJECT IDENTIFIER ::= { rm10010ri 1 }

rm10010download OBJECT IDENTIFIER ::= { moduleRm10010 8 }
rm10010DwlOther OBJECT IDENTIFIER ::= { rm10010download 1 }
rm10010DwlClient OBJECT IDENTIFIER ::= { rm10010download 2 }
rm10010DwlLine OBJECT IDENTIFIER ::= { rm10010download 3 }


rm10010Config OBJECT IDENTIFIER ::= { moduleRm10010 9 }

rm10010traps OBJECT IDENTIFIER ::= { moduleRm10010 10 }



rm10010Monitoring OBJECT IDENTIFIER ::= { moduleRm10010 11}

rm10010MonOther OBJECT IDENTIFIER ::= { rm10010Monitoring 1 }
rm10010MonRmon OBJECT IDENTIFIER ::= { rm10010MonOther 3 }

rm10010MonClient OBJECT IDENTIFIER ::= { rm10010Monitoring 2 }
rm10010MonClientRmonCounter OBJECT IDENTIFIER ::= { rm10010MonClient 4 }


rm10010MonPerfOther OBJECT IDENTIFIER ::= { rm10010Monitoring 5 }
rm10010MonPerfSync OBJECT IDENTIFIER ::= { rm10010MonPerfOther 1 }
rm10010MonPerfTimeStamp OBJECT IDENTIFIER ::= { rm10010MonPerfOther 2 }


rm10010MonPerfClient OBJECT IDENTIFIER ::= { rm10010Monitoring 6 }

rm10010MonPerfLine OBJECT IDENTIFIER ::= { rm10010Monitoring 7 }



--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Rm10010MultiRate ::= TEXTUAL-CONVENTION
    STATUS      current
    DESCRIPTION "different rate for a client port"
    SYNTAX INTEGER {
		rate100Mhz(0),
		rate250Mhz(1),
		rate500Mhz(2),
		rate1Ghz(3)
           }

Rm10010OtxMode ::= TEXTUAL-CONVENTION
    STATUS      current
    DESCRIPTION "Different modes on OTX-TLH on client and line ports"
    SYNTAX INTEGER {
		otx80mode(1),
		otx60mode(2),
		otxadjustmode(4)
           }

Rm10010OtxGrid ::= TEXTUAL-CONVENTION
    STATUS      current
    DESCRIPTION "Different grids on OTX-TLH on client and line ports"
    SYNTAX INTEGER {
		otxgrid200(200),
		otxgrid100(100),
		otxgrid50(50)
           }

Rm10010AdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Rm10010ClientProtocol ::= TEXTUAL-CONVENTION
    STATUS      current
    DESCRIPTION "Different values on the protocol on the client ports"
    SYNTAX INTEGER {
		protocolclientvalue0(0),
		protocolclientvalue1(1),
		protocolclientvalue2(2),
		protocolclientvalue3(3),
		protocolclientvalue4(4),
		protocolclientvalue5(5),
		protocolclientvalue6(6),
		protocolclientvalue7(7),
		protocolclientvalue8(8)
           }

Rm10010ProtocolMode ::= TEXTUAL-CONVENTION
    STATUS      current
    DESCRIPTION "Different values on the protocol mode"
    SYNTAX INTEGER {
		protocolmodevalue0(0),
		protocolmodevalue1(1),
		protocolmodevalue2(2),
		protocolmodevalue3(3)
           }

Rm10010OtxChannel ::= TEXTUAL-CONVENTION
    STATUS      current
    DESCRIPTION "Channel selection on transceiver Tx line ports"
    SYNTAX INTEGER

Rm10010OrxChannel ::= TEXTUAL-CONVENTION
    STATUS      current
    DESCRIPTION "Channel selection on transceiver Rx line ports"
    SYNTAX INTEGER

--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

rm10010RinvReloadInventory OBJECT-TYPE
  SYNTAX EkiOnOff
  MAX-ACCESS read-write
  STATUS current
  DESCRIPTION
        "Reload the inventory: This OID triggers an
         inventory reload."
  ::= { rm10010ri 2 }

rm10010RinvHwPlatform OBJECT-TYPE
  SYNTAX DisplayString
  MAX-ACCESS read-only
  STATUS current
  DESCRIPTION
        "HW platform description: This OID contains the
         description of the Hardware platform."
  ::= { rm10010ri 3 }

rm10010RinvModulePlatform OBJECT-TYPE
  SYNTAX DisplayString
  MAX-ACCESS read-only
  STATUS current
  DESCRIPTION
        "Module platform description: This OID contains the
         description of the Module."
  ::= { rm10010ri 4 }

rm10010RinvSwPlatform OBJECT-TYPE
  SYNTAX DisplayString
  MAX-ACCESS read-only
  STATUS current
  DESCRIPTION
        "SW platform description: This OID contains the
         description of the Software platform."
  ::= { rm10010ri 5 }

rm10010RinvGwPlatform OBJECT-TYPE
  SYNTAX DisplayString
  MAX-ACCESS read-only
  STATUS current
  DESCRIPTION
        "GW platform desciption: This OID contains the
         description of the Gateware platform."
  ::= { rm10010ri 6 }


rm10010RinvSfpTable OBJECT-TYPE
      SYNTAX  SEQUENCE OF Rm10010RinvSfpEntry
      MAX-ACCESS  not-accessible
      STATUS  current
      DESCRIPTION
              "List of the SFPs on the selected module"
      ::= { rm10010riTable 1 }

rm10010RinvSfpEntry OBJECT-TYPE
        SYNTAX  Rm10010RinvSfpEntry
        MAX-ACCESS  not-accessible
        STATUS  current
        DESCRIPTION
              "Row definition for the SFP table"
        INDEX   { rm10010RinvSfpIndex }
        ::= { rm10010RinvSfpTable 1 }



Rm10010RinvSfpEntry::=
        SEQUENCE {
          rm10010RinvSfpIndex
              Integer32,
          rm10010Rinvsfp
              DisplayString
        }


    rm10010RinvSfpIndex OBJECT-TYPE
        SYNTAX  Integer32(1..16)
        MAX-ACCESS  read-only
        STATUS  current
        DESCRIPTION
              "Index for SFP table"
        ::= { rm10010RinvSfpEntry 1 }


    rm10010Rinvsfp OBJECT-TYPE
        SYNTAX  DisplayString
        MAX-ACCESS  read-only
        STATUS  current
        DESCRIPTION
              "Inventory for the SFP: This OID contains the inventory for the SFP"
        ::= { rm10010RinvSfpEntry 2 }




rm10010RinvLineTable OBJECT-TYPE
      SYNTAX  SEQUENCE OF Rm10010RinvLineEntry
      MAX-ACCESS  not-accessible
      STATUS  current
      DESCRIPTION
              "List of the XFPs on the selected module"
      ::= { rm10010riTable 2 }

rm10010RinvLineEntry OBJECT-TYPE
        SYNTAX  Rm10010RinvLineEntry
        MAX-ACCESS  not-accessible
        STATUS  current
        DESCRIPTION
              "Row definition for the XFP table"
        INDEX   { rm10010RinvLineIndex }
        ::= { rm10010RinvLineTable 1 }



Rm10010RinvLineEntry::=
        SEQUENCE {
          rm10010RinvLineIndex
              Integer32,
          rm10010RinvxfpLine
              DisplayString
        }


    rm10010RinvLineIndex OBJECT-TYPE
        SYNTAX  Integer32(1..16)
        MAX-ACCESS  read-only
        STATUS  current
        DESCRIPTION
              "Index for XFP table"
        ::= { rm10010RinvLineEntry 1 }


    rm10010RinvxfpLine OBJECT-TYPE
        SYNTAX  DisplayString
        MAX-ACCESS  read-only
        STATUS  current
        DESCRIPTION
              "Inventory for the XFP: This OID contains the inventory for the XFP"
        ::= { rm10010RinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
rm10010AlmsynthAlm0 OBJECT IDENTIFIER ::= { rm10010AlmOtherCrit 0 }




rm10010AlmDefFuseB OBJECT-TYPE
	  SYNTAX EkiOnOff
	  MAX-ACCESS read-only
	  STATUS current
	  DESCRIPTION
        "
        Fuse B Fail :This OID indicates
        that the fuse of the power input
        B is in fail condition <Help> Status
        of the Fuse B <Condtype> DEF_FUSE_B
        <Probcause> powerProblem (36) <Alarmtype>
        equipmentAlarm (5) <Polarity> (2)
        "
	  ::= { rm10010AlmsynthAlm0 16 }



rm10010AlmDefFuseA OBJECT-TYPE
	  SYNTAX EkiOnOff
	  MAX-ACCESS read-only
	  STATUS current
	  DESCRIPTION
        "
        Fuse A Fail :This OID indicates
        that the fuse of the power input
        A is in fail condition <Help> Status
        of the Fuse A <Condtype> DEF_FUSE_A
        <Probcause> powerProblem (36) <Alarmtype>
        equipmentAlarm (5) <Polarity> (2)
        "
	  ::= { rm10010AlmsynthAlm0 15 }



rm10010AlmModGlobFail OBJECT-TYPE
	  SYNTAX EkiOnOff
	  MAX-ACCESS read-only
	  STATUS current
	  DESCRIPTION
        "
        Module Failure :This OID is set
        on detection of a failure originating
        from the RM <Help> This alarm is
        set on detection of a failure originating
        from the equipment <Condtype> MOD_GLOB_FAIL
        <Probcause> other (1) <Alarmtype>
        synthesisAlarm (12)  <Polarity>
        (2)
        "
	  ::= { rm10010AlmsynthAlm0 9 }



rm10010AlmFailFan OBJECT-TYPE
	  SYNTAX EkiOnOff
	  MAX-ACCESS read-only
	  STATUS current
	  DESCRIPTION
        "
        Fan Fail :This OID is at 1 when
        any fail occurs on the fan tray
        <Help> This alarm indicates that
        the Fan tray module is in a failure
        condition <Condtype> FAIL_FAN <Probcause>
        equipmentMalfunction (16) <Alarmtype>
        equipmentAlarm (5) <Polarity> (2)
        "
	  ::= { rm10010AlmsynthAlm0 2 }



--- *****************************************************
---     LEAF for the synthAlm2 article
--- *****************************************************
rm10010AlmsynthAlm2 OBJECT IDENTIFIER ::= { rm10010AlmOtherNurg 2 }




rm10010AlmMaintenanceOn OBJECT-TYPE
	  SYNTAX EkiOnOff
	  MAX-ACCESS read-only
	  STATUS current
	  DESCRIPTION
        "
        Maintenance Mode :This OID indicates
        that the RM is in maintenance mode.
        <Help> This alarm indicates that
        the maintenance mode is enabled
        on the PM <Condtype> MAINTENANCE_ON
        <Probcause> informationalStatus(1000)
        <Alarmtype> other (1) <Polarity>
        (2)
        "
	  ::= { rm10010AlmsynthAlm2 5 }



rm10010AlmCorrelatOff OBJECT-TYPE
	  SYNTAX EkiOnOff
	  MAX-ACCESS read-only
	  STATUS current
	  DESCRIPTION
        "
        Not Used :This OID, when set,
         indicates that alarm correlation
        is not being performed. <Condtype>
        CORRELAT_OFF <Probcause> informationalStatus(1000)
        <Alarmtype> other (1) <Polarity>
        (2)
        "
	  ::= { rm10010AlmsynthAlm2 4 }



rm10010AlmConfTableLoad OBJECT-TYPE
	  SYNTAX EkiOnOff
	  MAX-ACCESS read-only
	  STATUS current
	  DESCRIPTION
        "
        PM Configuration Load :This OID
         is at 1 during the loading of
         configuration tables in the modules
        RAM. <Condtype> CONF_TABLE_LOAD
        <Probcause> informationalStatus(1000)
        <Alarmtype> other (1) <Polarity>
        (2)
        "
	  ::= { rm10010AlmsynthAlm2 3 }



rm10010AlmInvUpload OBJECT-TYPE
	  SYNTAX EkiOnOff
	  MAX-ACCESS read-only
	  STATUS current
	  DESCRIPTION
        "
        Inventory Upload :This OID is
         at 1 during the uploading of PM
        inventory information. <Condtype>
        INV_UPLOAD <Probcause> informationalStatus(1000)
        <Alarmtype> other (1) <Polarity>
        (2)
        "
	  ::= { rm10010AlmsynthAlm2 2 }



rm10010AlmConfTableSave OBJECT-TYPE
	  SYNTAX EkiOnOff
	  MAX-ACCESS read-only
	  STATUS current
	  DESCRIPTION
        "
        PM Configuration Save :This OID
        is at 1 during the saving of a
         new configuration table in the
        module Flash memory. <Condtype>
        CONF_TABLE_SAVE <Probcause> informationalStatus(1000)
        <Alarmtype> other (1) <Polarity>
        (2)
        "
	  ::= { rm10010AlmsynthAlm2 1 }



--- *********************************************************
---     TABLE for the rm10010AlmsynthAlmPort articles
--- *********************************************************

rm10010AlmsynthAlmPortTable OBJECT-TYPE
	SYNTAX  SEQUENCE OF Rm10010AlmsynthAlmPortEntry
	MAX-ACCESS not-accessible
	STATUS current
	DESCRIPTION
        "
        List of rm10010AlmsynthAlmPort
        Article
        "
	::= { rm10010AlmClientCrit 8 }


rm10010AlmsynthAlmPortEntry OBJECT-TYPE
	SYNTAX Rm10010AlmsynthAlmPortEntry
	MAX-ACCESS not-accessible
	STATUS current
	DESCRIPTION
        "
        Row definition for the rm10010AlmsynthAlmPort
        table
        "
	INDEX   { rm10010AlmsynthAlmPortIndex }
	::= { rm10010AlmsynthAlmPortTable 1 }


Rm10010AlmsynthAlmPortEntry ::=
	SEQUENCE {
	rm10010AlmsynthAlmPortIndex
		INTEGER,
	rm10010AlmUpCsfPortn
		EkiOnOff,
	rm10010AlmFailAccPortn
		EkiOnOff,
	rm10010AlmSfpDdmAlmPortn
		EkiOnOff,
	rm10010AlmSfpDdmWarningPortn
		EkiOnOff,
	rm10010AlmDwCaisPortn
		EkiOnOff,
	rm10010AlmClientRemoteOosPortn
		EkiOnOff,
	rm10010AlmClientLocalOosPortn
		EkiOnOff,
	rm10010AlmDwLsdPortn
		EkiOnOff,
	rm10010AlmHwFailAccPortn
		EkiOnOff,
	rm10010AlmDdmAbsentPortn
		EkiOnOff,
	rm10010AlmSfpAbsentPortn
		EkiOnOff
	}


rm10010AlmsynthAlmPortIndex OBJECT-TYPE
	SYNTAX  INTEGER(0..128)
	MAX-ACCESS  read-only
	STATUS current
	DESCRIPTION
        "
        Index definition for the rm10010AlmsynthAlmPort
        table
        "
	::= { rm10010AlmsynthAlmPortEntry 1 }


rm10010AlmUpCsfPortn OBJECT-TYPE
	SYNTAX  EkiOnOff
	MAX-ACCESS read-only
	STATUS current
	DESCRIPTION
        "
        Client Signal Fail Inserted :This
        OID indicates a CSF has been inserted
        in the upstream client port. <Help>
        This status indicates if a Client
        Signal Fail is currently inserted
        on the line signal for this client
        port <Condtype> UP_CSF_1 <Probcause>
        informationalStatus(1000) <Alarmtype>
        other (1) <Polarity> (2)
        "
	::= { rm10010AlmsynthAlmPortEntry 17 }


rm10010AlmFailAccPortn OBJECT-TYPE
	SYNTAX  EkiOnOff
	MAX-ACCESS read-only
	STATUS current
	DESCRIPTION
        "
        Client Access Fail :This OID indicates
        a failure on the Client port <Help>
        This alarm indicates a failure
         on the Client port <Condtype>
         FAIL_ACC_1 <Probcause> equipmentMalfunction
        (16) <Alarmtype> synthesisAlarm
        (12)  <Polarity> (2)
        "
	::= { rm10010AlmsynthAlmPortEntry 13 }


rm10010AlmSfpDdmAlmPortn OBJECT-TYPE
	SYNTAX  EkiOnOff
	MAX-ACCESS read-only
	STATUS current
	DESCRIPTION
        "
        Alarm On Client Trscv DDM :This
        OID indicates an alarm is being
        received from the Client Transceiver
        DDM <Help> This alarm indicates
        if a DDM Alarm has been detected
        on the client transceiver <Condtype>
        SFP_DDM_ALM_1 <Probcause> inputOutputDeviceError
        (24) <Alarmtype> synthesisAlarm
        (12)  <Polarity> (2)
        "
	::= { rm10010AlmsynthAlmPortEntry 11 }


rm10010AlmSfpDdmWarningPortn OBJECT-TYPE
	SYNTAX  EkiOnOff
	MAX-ACCESS read-only
	STATUS current
	DESCRIPTION
        "
        Warning On Client Trscv DDM :This
        OID indicates a warning is being
        received from the Client Transceiver
        DDM <Help> This alarm indicates
        if a DDM Warning has been detected
        on the client transceiver <Condtype>
        SFP_DDM_WARNING_1 <Probcause> inputOutputDeviceError
        (24) <Alarmtype> synthesisAlarm
        (12)  <Polarity> (2)
        "
	::= { rm10010AlmsynthAlmPortEntry 10 }


rm10010AlmDwCaisPortn OBJECT-TYPE
	SYNTAX  EkiOnOff
	MAX-ACCESS read-only
	STATUS current
	DESCRIPTION
        "
        Client AIS Inserted :This OID
         indicates a CAIS has been inserted
        on the output client port. <Help>
        This status indicates if a Client
        Alarm Indication Signal is currently
        inserted on the client interface
        <Condtype> DW_CAIS_1 <Probcause>
        informationalStatus(1000) <Alarmtype>
        other (1) <Polarity> (2)
        "
	::= { rm10010AlmsynthAlmPortEntry 9 }


rm10010AlmClientRemoteOosPortn OBJECT-TYPE
	SYNTAX  EkiOnOff
	MAX-ACCESS read-only
	STATUS current
	DESCRIPTION
        "
        Remote Client Port In Service
         :This OID indicates that the remote
        Client port is In Service (1) or
        Out of Service (2) <Help> This
         status indicates if the remote
        client port is in service <Condtype>
        CLIENT_REMOTE_OOS <Probcause> informationalStatus(1000)
        <Alarmtype> other (1) <Polarity>
        (2)
        "
	::= { rm10010AlmsynthAlmPortEntry 8 }


rm10010AlmClientLocalOosPortn OBJECT-TYPE
	SYNTAX  EkiOnOff
	MAX-ACCESS read-only
	STATUS current
	DESCRIPTION
        "
        Local Client Port In Service :This
        OID indicates that the local Client
        port is In Service (1) or Out of
        Service (2) <Help> This status
         indicates if the local client
         port is in service <Condtype>
         CLIENT_LOCAL_OOS <Probcause> informationalStatus(1000)
        <Alarmtype> other (1) <Polarity>
        (2)
        "
	::= { rm10010AlmsynthAlmPortEntry 7 }


rm10010AlmDwLsdPortn OBJECT-TYPE
	SYNTAX  EkiOnOff
	MAX-ACCESS read-only
	STATUS current
	DESCRIPTION
        "
        Client Trscv Laser Shutdown :This
        OID indicates the Client transceiver
        laser is shutdown <Help> This status
        indicates if the client transceiver
        laser is shutdown <Condtype> DW_LSD_1
        <Probcause> other (1) <Alarmtype>
        equipmentAlarm (5) <Polarity> (2)
        "
	::= { rm10010AlmsynthAlmPortEntry 6 }


rm10010AlmHwFailAccPortn OBJECT-TYPE
	SYNTAX  EkiOnOff
	MAX-ACCESS read-only
	STATUS current
	DESCRIPTION
        "
        Client HW Fail :This OID indicates
        a failure on client port, most
         probably caused by a HW issue.
        <Help> This alarm indicates a failure
        on client port, most probably caused
        by a HW issue. <Condtype> HW_FAIL_ACC_1
        <Probcause> equipmentMalfunction
        (16) <Alarmtype> synthesisAlarm
        (12)   <Polarity> (2)
        "
	::= { rm10010AlmsynthAlmPortEntry 5 }


rm10010AlmDdmAbsentPortn OBJECT-TYPE
	SYNTAX  EkiOnOff
	MAX-ACCESS read-only
	STATUS current
	DESCRIPTION
        "
        DDM Supported On Client Trscv
         :This OID indicates that the Client
        transceiver supports the Digital
        Diagnostic Monitoring function
         <Help> This status indicates if
        the client transceiver includes
        the DDM feature <Condtype> DDM_ABSENT_1
        <Probcause> informationalStatus(1000)
        <Alarmtype> other (1) <Polarity>
        (2)
        "
	::= { rm10010AlmsynthAlmPortEntry 3 }


rm10010AlmSfpAbsentPortn OBJECT-TYPE
	SYNTAX  EkiOnOff
	MAX-ACCESS read-only
	STATUS current
	DESCRIPTION
        "
        Client Optical Module Absent :This
        OID indicates that the Transceiver
        is not present in the client port.
        <Help> This alarm indicates if
         the client transceiver is not
         plugged <Condtype> SFP_ABSENT_1
        <Probcause> inputOutputDeviceError
        (24) <Alarmtype> equipmentAlarm
        (5) <Polarity> (2) <Event> ObjectCDINV
        "
	::= { rm10010AlmsynthAlmPortEntry 2 }


--- *********************************************************
---     TABLE for the rm10010AlmsynthAlmLine articles
--- *********************************************************

rm10010AlmsynthAlmLineTable OBJECT-TYPE
	SYNTAX  SEQUENCE OF Rm10010AlmsynthAlmLineEntry
	MAX-ACCESS not-accessible
	STATUS current
	DESCRIPTION
        "
        List of rm10010AlmsynthAlmLine
        Article
        "
	::= { rm10010AlmLineCrit 24 }


rm10010AlmsynthAlmLineEntry OBJECT-TYPE
	SYNTAX Rm10010AlmsynthAlmLineEntry
	MAX-ACCESS not-accessible
	STATUS current
	DESCRIPTION
        "
        Row definition for the rm10010AlmsynthAlmLine
        table
        "
	INDEX   { rm10010AlmsynthAlmLineIndex }
	::= { rm10010AlmsynthAlmLineTable 1 }


Rm10010AlmsynthAlmLineEntry ::=
	SEQUENCE {
	rm10010AlmsynthAlmLineIndex
		INTEGER,
	rm10010AlmLineActivePortn
		EkiOnOff,
	rm10010AlmLineFailPortn
		EkiOnOff,
	rm10010AlmLineDdmAlmPortn
		EkiOnOff,
	rm10010AlmLineDdmWarningPortn
		EkiOnOff,
	rm10010AlmUpRdiInsPortn
		EkiOnOff,
	rm10010AlmLineLocalOosPortn
		EkiOnOff,
	rm10010AlmXfpTxOffPortn
		EkiOnOff,
	rm10010AlmLineHwFailPortn
		EkiOnOff,
	rm10010AlmXfpInitNotComplPortn
		EkiOnOff,
	rm10010AlmXfpAbsentPortn
		EkiOnOff
	}


rm10010AlmsynthAlmLineIndex OBJECT-TYPE
	SYNTAX  INTEGER(0..128)
	MAX-ACCESS  read-only
	STATUS current
	DESCRIPTION
        "
        Index definition for the rm10010AlmsynthAlmLine
        table
        "
	::= { rm10010AlmsynthAlmLineEntry 1 }


rm10010AlmLineActivePortn OBJECT-TYPE
	SYNTAX  EkiOnOff
	MAX-ACCESS read-only
	STATUS current
	DESCRIPTION
        "
        Line Active :This OID indicates
        whether the line is active or standby.
        <Help> This status indicates whether
        the line is active or standby.
         <Condtype> LINE_ACTIVE <Probcause>
        informationalStatus(1000) <Alarmtype>
        other (1) <Polarity> (2)
        "
	::= { rm10010AlmsynthAlmLineEntry 17 }


rm10010AlmLineFailPortn OBJECT-TYPE
	SYNTAX  EkiOnOff
	MAX-ACCESS read-only
	STATUS current
	DESCRIPTION
        "
        Line Port Failure :This OID indicates
        a failure on the line port <Help>
        This alarm indicates a failure
         on the line port <Condtype> LINE_FAIL
        <Probcause> equipmentMalfunction
        (16) <Alarmtype> synthesisAlarm
        (12)  <Polarity> (2)
        "
	::= { rm10010AlmsynthAlmLineEntry 13 }


rm10010AlmLineDdmAlmPortn OBJECT-TYPE
	SYNTAX  EkiOnOff
	MAX-ACCESS read-only
	STATUS current
	DESCRIPTION
        "
        Alarm On Line Optical Module DDM
        :This OID indicates an alarm is
        present coming out of Line transceiver
        DDM <Help> This alarm indicates
        if a DDM Alarm has been detected
        on the line transceiver <Condtype>
        LINE_DDM_ALM <Probcause> inputOutputDeviceError
        (24) <Alarmtype> synthesisAlarm
        (12)  <Polarity> (2)
        "
	::= { rm10010AlmsynthAlmLineEntry 11 }


rm10010AlmLineDdmWarningPortn OBJECT-TYPE
	SYNTAX  EkiOnOff
	MAX-ACCESS read-only
	STATUS current
	DESCRIPTION
        "
        Warning On Line Optical Module
        DDM :This OID indicates a warning
        is present coming out of Line transceiver
        DDM <Help> This alarm indicates
        if a DDM Warning has been detected
        on the line transceiver <Condtype>
        LINE_DDM_WARNING <Probcause> inputOutputDeviceError
        (24) <Alarmtype> synthesisAlarm
        (12)  <Polarity> (2)
        "
	::= { rm10010AlmsynthAlmLineEntry 10 }


rm10010AlmUpRdiInsPortn OBJECT-TYPE
	SYNTAX  EkiOnOff
	MAX-ACCESS read-only
	STATUS current
	DESCRIPTION
        "
        MS-RDI/L-RDI Inserted On Line
         :This OID indicates an upstream
        MS-RDI/L-RDI has been inserted
         in the outgoing 10 Gb/s SDH/SONET
        signal. <Help> This status indicates
        if a MS-RDI/L-RDI is currently
         inserted on the line interface.
        <Condtype> UP_RDI_INS <Probcause>
        informationalStatus(1000) <Alarmtype>
        other (1) <Polarity> (2)
        "
	::= { rm10010AlmsynthAlmLineEntry 9 }


rm10010AlmLineLocalOosPortn OBJECT-TYPE
	SYNTAX  EkiOnOff
	MAX-ACCESS read-only
	STATUS current
	DESCRIPTION
        "
        Line Port In Service :This OID
        indicates that the Line port is
        In Service (1) of Out or Service
        (2) <Help> This status indicates
        if the line port is in service
         <Condtype> LINE_LOCAL_OOS <Probcause>
        informationalStatus(1000) <Alarmtype>
        other (1) <Polarity> (2)
        "
	::= { rm10010AlmsynthAlmLineEntry 7 }


rm10010AlmXfpTxOffPortn OBJECT-TYPE
	SYNTAX  EkiOnOff
	MAX-ACCESS read-only
	STATUS current
	DESCRIPTION
        "
        Line Trscv Laser Shutdown :This
        OID indicates the Line transceiver
        laser is shutdown <Help> This status
        indicates if the Line transceiver
        laser is shutdown <Condtype> XFP_TX_OFF
        <Probcause> other (1) <Alarmtype>
        equipmentAlarm (5) <Polarity> (2)
        "
	::= { rm10010AlmsynthAlmLineEntry 6 }


rm10010AlmLineHwFailPortn OBJECT-TYPE
	SYNTAX  EkiOnOff
	MAX-ACCESS read-only
	STATUS current
	DESCRIPTION
        "
        Line Port HW Failure :This OID
        indicates a failure on line port,
        most probably caused by a HW issue
        <Help> This alarm indicates a failure
        on line port, most probably caused
        by a HW issue <Condtype> LINE_HW_FAIL
        <Probcause> equipmentMalfunction
        (16) <Alarmtype> synthesisAlarm
        (12)  <Polarity> (2)
        "
	::= { rm10010AlmsynthAlmLineEntry 5 }


rm10010AlmXfpInitNotComplPortn OBJECT-TYPE
	SYNTAX  EkiOnOff
	MAX-ACCESS read-only
	STATUS current
	DESCRIPTION
        "
        Line Optical Module Ready :This
        OID indicates that the optical
         interface is not operational.
         <Help> This status indicates if
        the line transceiver has been correctly
        initialized <Condtype> XFP_INIT_NOT_COMPL
        <Probcause> equipmentMalfunction
        (16) <Alarmtype> equipmentAlarm
        (5) <Polarity> (2)
        "
	::= { rm10010AlmsynthAlmLineEntry 3 }


rm10010AlmXfpAbsentPortn OBJECT-TYPE
	SYNTAX  EkiOnOff
	MAX-ACCESS read-only
	STATUS current
	DESCRIPTION
        "
        Line Optical Module Absent :This
        OID indicates that the line optical
        interface is not present. <Help>
        This alarm indicates if the line
        transceiver is not plugged <Condtype>
        XFP_ABSENT <Probcause> inputOutputDeviceError
        (24) <Alarmtype> equipmentAlarm
        (5) <Polarity> (2)
        "
	::= { rm10010AlmsynthAlmLineEntry 2 }


--- *****************************************************
---     LEAF for the clientModuleState article
--- *****************************************************
rm10010AlmclientModuleState OBJECT IDENTIFIER ::= { rm10010AlmOtherCrit 40 }




rm10010AlmCfpHighPowerDown OBJECT-TYPE
	  SYNTAX EkiOnOff
	  MAX-ACCESS read-only
	  STATUS current
	  DESCRIPTION
        "
        Client Trscv High Power Down :This
        OID indicates the Client Trscv
         is entering Low Power state <Help>
        Status indicating the Client Trscv
        is entering Low Power state <Condtype>
        CFP_HIGH_POWER_DOWN <Probcause>
        informationalStatus(1000) <Alarmtype>
        other (1) <Polarity> (2)
        "
	  ::= { rm10010AlmclientModuleState 9 }



rm10010AlmCfpTxTurnOff OBJECT-TYPE
	  SYNTAX EkiOnOff
	  MAX-ACCESS read-only
	  STATUS current
	  DESCRIPTION
        "
        Client Trscv Laser Turn Off :This
        OID indicates the Client Trscv
         is turning off its laser <Help>
        Status indicating the Client Trscv
        is turning off its laser <Condtype>
        CFP_TX_TURN_OFF <Probcause> informationalStatus(1000)
        <Alarmtype> other (1) <Polarity>
        (2)
        "
	  ::= { rm10010AlmclientModuleState 8 }



rm10010AlmCfpFault OBJECT-TYPE
	  SYNTAX EkiOnOff
	  MAX-ACCESS read-only
	  STATUS current
	  DESCRIPTION
        "
        Client Trscv Fault :This OID indicates
        the Client Trscv is in Fault state
        <Help> Status indicating the Client
        Trscv is in Fault state <Condtype>
        CFP_FAULT <Probcause> informationalStatus(1000)
        <Alarmtype> other (1) <Polarity>
        (2)
        "
	  ::= { rm10010AlmclientModuleState 7 }



rm10010AlmCfpReady OBJECT-TYPE
	  SYNTAX EkiOnOff
	  MAX-ACCESS read-only
	  STATUS current
	  DESCRIPTION
        "
        Client Trscv Ready :This OID indicates
        the Client Trscv is ready to operate
        <Help> Status indicating the Client
        Trscv is ready to operate <Condtype>
        CFP_READY <Probcause> informationalStatus(1000)
        <Alarmtype> other (1) <Polarity>
        (2)
        "
	  ::= { rm10010AlmclientModuleState 6 }



rm10010AlmCfpTxTurnOn OBJECT-TYPE
	  SYNTAX EkiOnOff
	  MAX-ACCESS read-only
	  STATUS current
	  DESCRIPTION
        "
        Client Trscv Laser Turn On :This
        OID indicates the Client Trscv
         is turning on its laser <Help>
        Status indicating the Client Trscv
        is turning on its laser <Condtype>
        CFP_TX_TURN_ON <Probcause> informationalStatus(1000)
        <Alarmtype> other (1) <Polarity>
        (2)
        "
	  ::= { rm10010AlmclientModuleState 5 }



rm10010AlmCfpTxOff OBJECT-TYPE
	  SYNTAX EkiOnOff
	  MAX-ACCESS read-only
	  STATUS current
	  DESCRIPTION
        "
        Client Trscv Laser Shutdown :This
        OID indicates the Client Trscv
         Laser is OFF <Help> Status indicating
        the Client Trscv Laser is OFF <Condtype>
        CFP_TX_OFF <Probcause> informationalStatus(1000)
        <Alarmtype> other (1) <Polarity>
        (2)
        "
	  ::= { rm10010AlmclientModuleState 4 }



rm10010AlmCfpHighPowerUp OBJECT-TYPE
	  SYNTAX EkiOnOff
	  MAX-ACCESS read-only
	  STATUS current
	  DESCRIPTION
        "
        Client Trscv High Power Up :This
        OID indicates the Client Trscv
         is leaving Low Power state <Help>
        Status indicating the Client Trscv
        is leaving Low Power state <Condtype>
        CFP_HIGH_POWER_UP <Probcause> informationalStatus(1000)
        <Alarmtype> other (1) <Polarity>
        (2)
        "
	  ::= { rm10010AlmclientModuleState 3 }



rm10010AlmCfpLowPower OBJECT-TYPE
	  SYNTAX EkiOnOff
	  MAX-ACCESS read-only
	  STATUS current
	  DESCRIPTION
        "
        Client Trscv Low Power :This OID
        indicates the Client Trscv is in
        low power state <Help> Status indicating
        the Client Trscv is in low power
        state <Condtype> CFP_LOW_POWER
         <Probcause> informationalStatus(1000)
        <Alarmtype> other (1) <Polarity>
        (2)
        "
	  ::= { rm10010AlmclientModuleState 2 }



rm10010AlmCfpInitialize OBJECT-TYPE
	  SYNTAX EkiOnOff
	  MAX-ACCESS read-only
	  STATUS current
	  DESCRIPTION
        "
        Client Trscv Initialize :This
         OID indicates the Client Trscv
        initialization is in progress <Help>
        Status indicating the Client Trscv
        initialization is in progress <Condtype>
        CFP_INITIALIZE <Probcause> informationalStatus(1000)
        <Alarmtype> other (1) <Polarity>
        (2)
        "
	  ::= { rm10010AlmclientModuleState 1 }



--- *****************************************************
---     LEAF for the clientModuleGeneralStatus article
--- *****************************************************
rm10010AlmclientModuleGeneralStatus OBJECT IDENTIFIER ::= { rm10010AlmOtherCrit 41 }




rm10010AlmCfpHwInterlock OBJECT-TYPE
	  SYNTAX EkiOnOff
	  MAX-ACCESS read-only
	  STATUS current
	  DESCRIPTION
        "
        Client Trscv Hardware Interlock
        :This OID indicates the Client
         Trscv power is higher than the
        cooling capacity <Help> Alarm indicating
        the Client Trscv power is higher
        than the cooling capacity <Condtype>
        CFP_HW_INTERLOCK <Probcause> temperatureUnacceptable
        (51) <Alarmtype> equipmentAlarm
        (5) <Polarity> (2)
        "
	  ::= { rm10010AlmclientModuleGeneralStatus 14 }



rm10010AlmCfpLossOfRefclk OBJECT-TYPE
	  SYNTAX EkiOnOff
	  MAX-ACCESS read-only
	  STATUS current
	  DESCRIPTION
        "
        Client Trscv Loss Of Ref Clock
        :This OID indicates a Loss of Reference
        clock is detected on the Client
        Trscv <Help> Alarm indicating a
        Loss of Reference clock is detected
        on the Client Trscv <Condtype>
         CFP_LOSS_OF_REFCLK <Probcause>
        inputOutputDeviceError (24) <Alarmtype>
        equipmentAlarm (5) <Polarity> (2)
        "
	  ::= { rm10010AlmclientModuleGeneralStatus 11 }



rm10010AlmCfpTxJitterPllLol OBJECT-TYPE
	  SYNTAX EkiOnOff
	  MAX-ACCESS read-only
	  STATUS current
	  DESCRIPTION
        "
        Client Trscv Tx Jitter PLL Loss
        Of Lock :This OID indicates a Tx
        Jitter PLL Loss of Lock is dtected
        on the Client Trscv <Help> Alarm
        indicating a Tx Jitter PLL Loss
        of Lock is dtected on the Client
        Trscv <Condtype> CFP_TX_JITTER_PLL_LOL
        <Probcause> inputOutputDeviceError
        (24) <Alarmtype> equipmentAlarm
        (5) <Polarity> (2)
        "
	  ::= { rm10010AlmclientModuleGeneralStatus 10 }



rm10010AlmCfpTxCmuLol OBJECT-TYPE
	  SYNTAX EkiOnOff
	  MAX-ACCESS read-only
	  STATUS current
	  DESCRIPTION
        "
        Client Trscv CMU Loss Of Lock
         :This OID indicates a Clock Multiplier
        Unit Loss of Lock is detected on
        the Client Trscv <Help> Alarm indicating
        a Clock Multiplier Unit Loss of
        Lock is detected on the Client
         Trscv <Condtype> CFP_TX_CMU_LOL
        <Probcause> inputOutputDeviceError
        (24) <Alarmtype> equipmentAlarm
        (5) <Polarity> (2)
        "
	  ::= { rm10010AlmclientModuleGeneralStatus 9 }



rm10010AlmCfpTxLosf OBJECT-TYPE
	  SYNTAX EkiOnOff
	  MAX-ACCESS read-only
	  STATUS current
	  DESCRIPTION
        "
        Client Trscv Loss Of Signal Functionality
        :This OID indicates a Loss of Signal
        functionality is detected on the
        Client Trscv <Help> Alarm indicating
        a Loss of Signal functionality
         is detected on the Client Trscv
        <Condtype> CFP_TX_LOSF <Probcause>
        lossOfSignal (30) <Alarmtype> equipmentAlarm
        (5) <Polarity> (2)
        "
	  ::= { rm10010AlmclientModuleGeneralStatus 8 }



rm10010AlmCfpTxHostLol OBJECT-TYPE
	  SYNTAX EkiOnOff
	  MAX-ACCESS read-only
	  STATUS current
	  DESCRIPTION
        "
        Client Trscv Tx Host Loss Of Lock
        :This OID indicates of Loss of
         Lock is detected on the Client
        Trscv Tx Host interface <Help>
         Alarm indicating of Loss of Lock
        is detected on the Client Trscv
        Tx Host interface <Condtype> CFP_TX_HOST_LOL
        <Probcause> receiverFailure (42)
        <Alarmtype> equipmentAlarm (5)
         <Polarity> (2)
        "
	  ::= { rm10010AlmclientModuleGeneralStatus 7 }



rm10010AlmCfpRxLos OBJECT-TYPE
	  SYNTAX EkiOnOff
	  MAX-ACCESS read-only
	  STATUS current
	  DESCRIPTION
        "
        Client Trscv Loss Of Signal :This
        OID indicates a Loss of Signal
         is detected on the Client Trscv
        <Help> Alarm indicating a Loss
         of Signal is detected on the Client
        Trscv <Condtype> CFP_RX_LOS <Probcause>
        lossOfSignal (30) <Alarmtype> equipmentAlarm
        (5) <Polarity> (2)
        "
	  ::= { rm10010AlmclientModuleGeneralStatus 6 }



rm10010AlmCfpRxNetworkLol OBJECT-TYPE
	  SYNTAX EkiOnOff
	  MAX-ACCESS read-only
	  STATUS current
	  DESCRIPTION
        "
        Client Trscv Rx Network Loss Of
        Lock :This OID indicates of Loss
        of Lock is dected on the Client
        Trscv Rx Network interface <Help>
        Alarm indicating of Loss of Lock
        is dected on the Client Trscv Rx
        Network interface <Condtype> CFP_RX_NETWORK_LOL
        <Probcause> receiverFailure (42)
        <Alarmtype> equipmentAlarm (5)
         <Polarity> (2)
        "
	  ::= { rm10010AlmclientModuleGeneralStatus 5 }



rm10010AlmCfpOutOfAlignment OBJECT-TYPE
	  SYNTAX EkiOnOff
	  MAX-ACCESS read-only
	  STATUS current
	  DESCRIPTION
        "
        Client Trscv Out Of Alignment
         :This OID indicates an Out of
         alignment on the Client Trscv
         Host Interface <Help> Alarm indicating
        an Out of alignment on the Client
        Trscv Host Interface <Condtype>
        CFP_OUT_OF_ALIGNMENT <Probcause>
        receiverFailure (42) <Alarmtype>
        equipmentAlarm (5) <Polarity> (2)
        "
	  ::= { rm10010AlmclientModuleGeneralStatus 4 }



--- *****************************************************
---     LEAF for the clientGlobalAlarmSummary article
--- *****************************************************
rm10010AlmclientGlobalAlarmSummary OBJECT IDENTIFIER ::= { rm10010AlmOtherCrit 42 }




rm10010AlmCfpGlobAlarmAssertion  OBJECT-TYPE
	  SYNTAX EkiOnOff
	  MAX-ACCESS read-only
	  STATUS current
	  DESCRIPTION
        "
        Client Trscv Global Alarm :This
        OID indicates at least one  Fault
        or Status is detected on the Client
        Trscv module <Help> Synthesis alarm
        indicating at least one Alarm,
         Warning, Fault or Status is detected
        on the Client Trscv module <Condtype>
        CFP_GLOB_ALARM_ASSERTION  <Probcause>
        informationalStatus(1000) <Alarmtype>
        other (1) <Polarity> (2)
        "
	  ::= { rm10010AlmclientGlobalAlarmSummary 16 }



rm10010AlmCfpHostLaneFaultStatus  OBJECT-TYPE
	  SYNTAX EkiOnOff
	  MAX-ACCESS read-only
	  STATUS current
	  DESCRIPTION
        "
        Client Trscv Host Fault And Status
        :This OID indicates at least one
        Fault or Status is detected on
         the Client Trscv Host Interface
        <Help> Synthesis alarm indicating
        at least one Fault or Status is
        detected on the Client Trscv Host
        Interface <Condtype> CFP_HOST_LANE_FAULT_STATUS
         <Probcause> informationalStatus(1000)
        <Alarmtype> other (1) <Polarity>
        (2)
        "
	  ::= { rm10010AlmclientGlobalAlarmSummary 15 }



rm10010AlmCfpNetworkLaneFaultStatus  OBJECT-TYPE
	  SYNTAX EkiOnOff
	  MAX-ACCESS read-only
	  STATUS current
	  DESCRIPTION
        "
        Client Trscv Network Fault And
        Status :This OID indicates at least
        one Fault or Status is detected
        on the Client Trscv Network Interface
        <Help> Synthesis alarm indicating
        at least one Fault or Status is
        detected on the Client Trscv Network
        Interface <Condtype> CFP_NETWORK_LANE_FAULT_STATUS
         <Probcause> informationalStatus(1000)
        <Alarmtype> other (1) <Polarity>
        (2)
        "
	  ::= { rm10010AlmclientGlobalAlarmSummary 14 }



rm10010AlmCfpNetworkLaneAlarmWarning1 OBJECT-TYPE
	  SYNTAX EkiOnOff
	  MAX-ACCESS read-only
	  STATUS current
	  DESCRIPTION
        "
        Client Trscv Network Alarm And
        Warning 1 :This OID indicates at
        least one DDM  is detected on the
        Client Trscv Network Interface
         <Help> Synthesis alarm indicating
        at least one DDM Alarm or DDM Warning
        is detected on the Client Trscv
        Network Interface <Condtype> CFP_NETWORK_LANE_ALARM_WARNING_1
        <Probcause> informationalStatus(1000)
        <Alarmtype> other (1) <Polarity>
        (2)
        "
	  ::= { rm10010AlmclientGlobalAlarmSummary 13 }



rm10010AlmCfpModuleAlarmWarning2 OBJECT-TYPE
	  SYNTAX EkiOnOff
	  MAX-ACCESS read-only
	  STATUS current
	  DESCRIPTION
        "
        Client Trscv Module Alarm And
         Warning 2 :This OID indicates
         at least one DDM is detected on
        the Client Trscv module <Help>
         Synthesis alarm indicating at
         least one DDM Alarm or DDM Warning
        is detected on the Client Trscv
        module <Condtype> CFP_MODULE_ALARM_WARNING_2
        <Probcause> informationalStatus(1000)
        <Alarmtype> other (1) <Polarity>
        (2)
        "
	  ::= { rm10010AlmclientGlobalAlarmSummary 12 }



rm10010AlmCfpModuleAlarmWarning1  OBJECT-TYPE
	  SYNTAX EkiOnOff
	  MAX-ACCESS read-only
	  STATUS current
	  DESCRIPTION
        "
        Client Trscv Module Alarm And
         Warning 1 :This OID indicates
         at least one DDM  This OID is
         detected on the Client Trscv module
        <Help> Synthesis alarm indicating
        at least one DDM Alarm or DDM Warning
        is detected on the Client Trscv
        module <Condtype> CFP_MODULE_ALARM_WARNING_1
         <Probcause> informationalStatus(1000)
        <Alarmtype> other (1) <Polarity>
        (2)
        "
	  ::= { rm10010AlmclientGlobalAlarmSummary 11 }



rm10010AlmCfpModuleFault  OBJECT-TYPE
	  SYNTAX EkiOnOff
	  MAX-ACCESS read-only
	  STATUS current
	  DESCRIPTION
        "
        Client Trscv Module Fault :This
        OID indicates at least one Fault
        is detected on the Client Trscv
        module <Help> Synthesis alarm indicating
        at least one Fault is detected
         on the Client Trscv module <Condtype>
        CFP_MODULE_FAULT  <Probcause> informationalStatus(1000)
        <Alarmtype> other (1) <Polarity>
        (2)
        "
	  ::= { rm10010AlmclientGlobalAlarmSummary 10 }



rm10010AlmCfpModuleGeneralStatus  OBJECT-TYPE
	  SYNTAX EkiOnOff
	  MAX-ACCESS read-only
	  STATUS current
	  DESCRIPTION
        "
        Client Trscv General Status :This
        OID indicates the Client Trscv
         module general status <Help> Synthesis
        alarm indicating the Client Trscv
        module general status <Condtype>
        CFP_MODULE_GENERAL_STATUS  <Probcause>
        informationalStatus(1000) <Alarmtype>
        other (1) <Polarity> (2)
        "
	  ::= { rm10010AlmclientGlobalAlarmSummary 9 }



rm10010AlmCfpModuleState  OBJECT-TYPE
	  SYNTAX EkiOnOff
	  MAX-ACCESS read-only
	  STATUS current
	  DESCRIPTION
        "
        Client Trscv Module State :This
        OID indicates the Client Trscv
         module state <Help> Synthesis
         alarm indicating the Client Trscv
        module state <Condtype> CFP_MODULE_STATE
         <Probcause> informationalStatus(1000)
        <Alarmtype> other (1) <Polarity>
        (2)
        "
	  ::= { rm10010AlmclientGlobalAlarmSummary 8 }



rm10010AlmCfpNetworkLaneAlarmWarning2 OBJECT-TYPE
	  SYNTAX EkiOnOff
	  MAX-ACCESS read-only
	  STATUS current
	  DESCRIPTION
        "
        Client Trscv Network Alarm And
        Warning 2 :This OID indicates at
        least one DDM is detected on the
        Client Trscv Network Interface
         <Help> Synthesis alarm indicating
        at least one DDM Alarm or DDM Warning
        is detected on the Client Trscv
        Network Interface <Condtype> CFP_NETWORK_LANE_ALARM_WARNING_2
        <Probcause> informationalStatus(1000)
        <Alarmtype> other (1) <Polarity>
        (2)
        "
	  ::= { rm10010AlmclientGlobalAlarmSummary 7 }



rm10010AlmCfpSoftGlobAlarmTest  OBJECT-TYPE
	  SYNTAX EkiOnOff
	  MAX-ACCESS read-only
	  STATUS current
	  DESCRIPTION
        "
        Client Trscv Global Alarm SW Test
        :This OID indicates the Client
         Trscv Global Alarm This OID is
        raised by SW request for test purpose
        <Help> Status indicating the Client
        Trscv Global Alarm is raised by
        SW request for test purpose <Condtype>
        CFP_SOFT_GLOB_ALARM_TEST  <Probcause>
        informationalStatus(1000) <Alarmtype>
        other (1) <Polarity> (2)
        "
	  ::= { rm10010AlmclientGlobalAlarmSummary 1 }



--- *****************************************************
---     LEAF for the msaModuleState article
--- *****************************************************
rm10010AlmmsaModuleState OBJECT IDENTIFIER ::= { rm10010AlmOtherCrit 46 }




rm10010AlmMsaHighPowerDown OBJECT-TYPE
	  SYNTAX EkiOnOff
	  MAX-ACCESS read-only
	  STATUS current
	  DESCRIPTION
        "
        Line Trscv High Power Down :This
        OID indicates the Line Trscv is
        entering Low Power state <Help>
        Status indicating the Line Trscv
        is entering Low Power state <Condtype>
        MSA_HIGH_POWER_DOWN <Probcause>
        informationalStatus(1000) <Alarmtype>
        other (1) <Polarity> (2)
        "
	  ::= { rm10010AlmmsaModuleState 9 }



rm10010AlmMsaTxTurnOff OBJECT-TYPE
	  SYNTAX EkiOnOff
	  MAX-ACCESS read-only
	  STATUS current
	  DESCRIPTION
        "
        Line Trscv Laser Turn Off :This
        OID indicates the Line Trscv is
        turning off its laser <Help> Status
        indicating the Line Trscv is turning
        off its laser <Condtype> MSA_TX_TURN_OFF
        <Probcause> informationalStatus(1000)
        <Alarmtype> other (1) <Polarity>
        (2)
        "
	  ::= { rm10010AlmmsaModuleState 8 }



rm10010AlmMsaFault OBJECT-TYPE
	  SYNTAX EkiOnOff
	  MAX-ACCESS read-only
	  STATUS current
	  DESCRIPTION
        "
        Line Trscv Fault :This OID indicates
        the Line Trscv is in Fault state
        <Help> Status indicating the Line
        Trscv is in Fault state <Condtype>
        MSA_FAULT <Probcause> informationalStatus(1000)
        <Alarmtype> other (1) <Polarity>
        (2)
        "
	  ::= { rm10010AlmmsaModuleState 7 }



rm10010AlmMsaReady OBJECT-TYPE
	  SYNTAX EkiOnOff
	  MAX-ACCESS read-only
	  STATUS current
	  DESCRIPTION
        "
        Line Trscv Ready :This OID indicates
        the Line Trscv is ready to operate
        <Help> Status indicating the Line
        Trscv is ready to operate <Condtype>
        MSA_READY <Probcause> informationalStatus(1000)
        <Alarmtype> other (1) <Polarity>
        (2)
        "
	  ::= { rm10010AlmmsaModuleState 6 }



rm10010AlmMsaTxTurnOn OBJECT-TYPE
	  SYNTAX EkiOnOff
	  MAX-ACCESS read-only
	  STATUS current
	  DESCRIPTION
        "
        Line Trscv Laser Turn On :This
        OID indicates the Line Trscv is
        turning on its laser <Help> Status
        indicating the Line Trscv is turning
        on its laser <Condtype> MSA_TX_TURN_ON
        <Probcause> informationalStatus(1000)
        <Alarmtype> other (1) <Polarity>
        (2)
        "
	  ::= { rm10010AlmmsaModuleState 5 }



rm10010AlmMsaTxOff OBJECT-TYPE
	  SYNTAX EkiOnOff
	  MAX-ACCESS read-only
	  STATUS current
	  DESCRIPTION
        "
        Line Trscv Laser Shutdown :This
        OID indicates the Line Trscv Laser
        is OFF <Help> Status indicating
        the Line Trscv Laser is OFF <Condtype>
        MSA_TX_OFF <Probcause> informationalStatus(1000)
        <Alarmtype> other (1) <Polarity>
        (2)
        "
	  ::= { rm10010AlmmsaModuleState 4 }



rm10010AlmMsaHighPowerUp OBJECT-TYPE
	  SYNTAX EkiOnOff
	  MAX-ACCESS read-only
	  STATUS current
	  DESCRIPTION
        "
        Line Trscv High Power Up :This
        OID indicates the Line Trscv is
        leaving Low Power state <Help>
         Status indicating the Line Trscv
        is leaving Low Power state <Condtype>
        MSA_HIGH_POWER_UP <Probcause> informationalStatus(1000)
        <Alarmtype> other (1) <Polarity>
        (2)
        "
	  ::= { rm10010AlmmsaModuleState 3 }



rm10010AlmMsaLowPower OBJECT-TYPE
	  SYNTAX EkiOnOff
	  MAX-ACCESS read-only
	  STATUS current
	  DESCRIPTION
        "
        Line Trscv Low Power :This OID
        indicates the Line Trscv is in
         low power state <Help> Status
         indicating the Line Trscv is in
        low power state <Condtype> MSA_LOW_POWER
        <Probcause> informationalStatus(1000)
        <Alarmtype> other (1) <Polarity>
        (2)
        "
	  ::= { rm10010AlmmsaModuleState 2 }



rm10010AlmMsaInitialize OBJECT-TYPE
	  SYNTAX EkiOnOff
	  MAX-ACCESS read-only
	  STATUS current
	  DESCRIPTION
        "
        Line Trscv Initialize :This OID
        indicates the Line Trscv initialization
        is in progress <Help> Status indicating
        the Line Trscv initialization is
        in progress <Condtype> MSA_INITIALIZE
        <Probcause> informationalStatus(1000)
        <Alarmtype> other (1) <Polarity>
        (2)
        "
	  ::= { rm10010AlmmsaModuleState 1 }



--- *****************************************************
---     LEAF for the msaModuleGeneralStatus article
--- *****************************************************
rm10010AlmmsaModuleGeneralStatus OBJECT IDENTIFIER ::= { rm10010AlmOtherCrit 47 }




rm10010AlmMsaHwInterlock OBJECT-TYPE
	  SYNTAX EkiOnOff
	  MAX-ACCESS read-only
	  STATUS current
	  DESCRIPTION
        "
        Line Trscv Hardware Interlock
         :This OID indicates the Line Trscv
        power is higher than the cooling
        capacity <Help> Alarm indicating
        the Line Trscv power is higher
         than the cooling capacity <Condtype>
        MSA_HW_INTERLOCK <Probcause> temperatureUnacceptable
        (51) <Alarmtype> equipmentAlarm
        (5) <Polarity> (2)
        "
	  ::= { rm10010AlmmsaModuleGeneralStatus 14 }



rm10010AlmMsaLossOfRefclk OBJECT-TYPE
	  SYNTAX EkiOnOff
	  MAX-ACCESS read-only
	  STATUS current
	  DESCRIPTION
        "
        Line Trscv Loss Of Ref Clock :This
        OID indicates a Loss of Reference
        clock is detected on the Line Trscv
        <Help> Alarm indicating a Loss
         of Reference clock is detected
        on the Line Trscv <Condtype> MSA_LOSS_OF_REFCLK
        <Probcause> inputOutputDeviceError
        (24) <Alarmtype> equipmentAlarm
        (5) <Polarity> (2)
        "
	  ::= { rm10010AlmmsaModuleGeneralStatus 11 }



rm10010AlmMsaTxJitterPllLol OBJECT-TYPE
	  SYNTAX EkiOnOff
	  MAX-ACCESS read-only
	  STATUS current
	  DESCRIPTION
        "
        Line Trscv Tx Jitter PLL Loss
         Of Lock :This OID indicates a
         Tx Jitter PLL Loss of Lock is
         detected on the Line Trscv <Help>
        Alarm indicating a Tx Jitter PLL
        Loss of Lock is detected on the
        Line Trscv <Condtype> MSA_TX_JITTER_PLL_LOL
        <Probcause> inputOutputDeviceError
        (24) <Alarmtype> equipmentAlarm
        (5) <Polarity> (2)
        "
	  ::= { rm10010AlmmsaModuleGeneralStatus 10 }



rm10010AlmMsaTxCmuLol OBJECT-TYPE
	  SYNTAX EkiOnOff
	  MAX-ACCESS read-only
	  STATUS current
	  DESCRIPTION
        "
        Line Trscv CMU Loss Of Lock :This
        OID indicates a Clock Multiplier
        Unit Loss of Lock is detected on
        the Line Trscv <Help> Alarm indicating
        a Clock Multiplier Unit Loss of
        Lock is detected on the Line Trscv
        <Condtype> MSA_TX_CMU_LOL <Probcause>
        inputOutputDeviceError (24) <Alarmtype>
        equipmentAlarm (5) <Polarity> (2)
        "
	  ::= { rm10010AlmmsaModuleGeneralStatus 9 }



rm10010AlmMsaTxLosf OBJECT-TYPE
	  SYNTAX EkiOnOff
	  MAX-ACCESS read-only
	  STATUS current
	  DESCRIPTION
        "
        Line Trscv Loss Of Signal Functionality
        :This OID indicates a Loss of Signal
        functionality is detected on the
        Line Trscv <Help> Alarm indicating
        a Loss of Signal functionality
         is detected on the Line Trscv
         <Condtype> MSA_TX_LOSF <Probcause>
        lossOfSignal (30) <Alarmtype> equipmentAlarm
        (5) <Polarity> (2)
        "
	  ::= { rm10010AlmmsaModuleGeneralStatus 8 }



rm10010AlmMsaTxHostLol OBJECT-TYPE
	  SYNTAX EkiOnOff
	  MAX-ACCESS read-only
	  STATUS current
	  DESCRIPTION
        "
        Line Trscv Tx Host Loss Of Lock
        :This OID indicates of Loss of
         Lock is detected on the Line Trscv
        Tx Host interface <Help> Alarm
         indicating of Loss of Lock is
         detected on the Line Trscv Tx
         Host interface <Condtype> MSA_TX_HOST_LOL
        <Probcause> receiverFailure (42)
        <Alarmtype> equipmentAlarm (5)
         <Polarity> (2)
        "
	  ::= { rm10010AlmmsaModuleGeneralStatus 7 }



rm10010AlmMsaRxLos OBJECT-TYPE
	  SYNTAX EkiOnOff
	  MAX-ACCESS read-only
	  STATUS current
	  DESCRIPTION
        "
        Line Trscv Loss Of Signal :This
        OID indicates a Loss of Signal
         is detected on the Line Trscv
         <Help> Alarm indicating a Loss
        of Signal is detected on the Line
        Trscv <Condtype> MSA_RX_LOS <Probcause>
        lossOfSignal (30) <Alarmtype> equipmentAlarm
        (5) <Polarity> (2)
        "
	  ::= { rm10010AlmmsaModuleGeneralStatus 6 }



rm10010AlmMsaRxNetworkLol OBJECT-TYPE
	  SYNTAX EkiOnOff
	  MAX-ACCESS read-only
	  STATUS current
	  DESCRIPTION
        "
        Line Trscv Rx Network Loss Of
         Lock :This OID indicates of Loss
        of Lock is detected on the Line
        Trscv Rx Network interface <Help>
        Alarm indicating of Loss of Lock
        is detected on the Line Trscv Rx
        Network interface <Condtype> MSA_RX_NETWORK_LOL
        <Probcause> receiverFailure (42)
        <Alarmtype> equipmentAlarm (5)
         <Polarity> (2)
        "
	  ::= { rm10010AlmmsaModuleGeneralStatus 5 }



rm10010AlmMsaOutOfAlignment OBJECT-TYPE
	  SYNTAX EkiOnOff
	  MAX-ACCESS read-only
	  STATUS current
	  DESCRIPTION
        "
        Line Trscv Out Of Alignment :This
        OID indicates an Out of alignment
        on the Line Trscv Host Interface
        <Help> Alarm indicating an Out
         of alignment on the Line Trscv
        Host Interface <Condtype> MSA_OUT_OF_ALIGNMENT
        <Probcause> receiverFailure (42)
        <Alarmtype> equipmentAlarm (5)
         <Polarity> (2)
        "
	  ::= { rm10010AlmmsaModuleGeneralStatus 4 }



--- *****************************************************
---     LEAF for the msaGlobalAlarmSummary article
--- *****************************************************
rm10010AlmmsaGlobalAlarmSummary OBJECT IDENTIFIER ::= { rm10010AlmOtherCrit 48 }




rm10010AlmMsaGlobAlarmAssertion  OBJECT-TYPE
	  SYNTAX EkiOnOff
	  MAX-ACCESS read-only
	  STATUS current
	  DESCRIPTION
        "
        Line Trscv Global Alarm :This
         OID indicates at least one Fault
        or Status is detected on the Line
        Trscv module <Help> Synthesis alarm
        indicating at least one Alarm,
         Warning, Fault or Status is detected
        on the Line Trscv module <Condtype>
        MSA_GLOB_ALARM_ASSERTION  <Probcause>
        informationalStatus(1000) <Alarmtype>
        other (1) <Polarity> (2)
        "
	  ::= { rm10010AlmmsaGlobalAlarmSummary 16 }



rm10010AlmMsaHostLaneFaultStatus  OBJECT-TYPE
	  SYNTAX EkiOnOff
	  MAX-ACCESS read-only
	  STATUS current
	  DESCRIPTION
        "
        Line Trscv Host Fault And Status
        :This OID indicates at least one
        Fault or Status is detected on
         the Line Trscv Host Interface
         <Help> Synthesis alarm indicating
        at least one Fault or Status is
        detected on the Line Trscv Host
        Interface <Condtype> MSA_HOST_LANE_FAULT_STATUS
         <Probcause> informationalStatus(1000)
        <Alarmtype> other (1) <Polarity>
        (2)
        "
	  ::= { rm10010AlmmsaGlobalAlarmSummary 15 }



rm10010AlmMsaNetworkLaneFaultStatus  OBJECT-TYPE
	  SYNTAX EkiOnOff
	  MAX-ACCESS read-only
	  STATUS current
	  DESCRIPTION
        "
        Line Trscv Network Fault And Status
        :This OID indicates at least one
        Fault or Status is detected on
         the Line Trscv Network Interface
        <Help> Synthesis alarm indicating
        at least one Fault or Status is
        detected on the Line Trscv Network
        Interface <Condtype> MSA_NETWORK_LANE_FAULT_STATUS
         <Probcause> informationalStatus(1000)
        <Alarmtype> other (1) <Polarity>
        (2)
        "
	  ::= { rm10010AlmmsaGlobalAlarmSummary 14 }



rm10010AlmMsaNetworkLaneAlarmWarning1 OBJECT-TYPE
	  SYNTAX EkiOnOff
	  MAX-ACCESS read-only
	  STATUS current
	  DESCRIPTION
        "
        Line Trscv Network Alarm And Warning
        1 :This OID indicates at least
         one DDM is detected on the Line
        Trscv Network Interface <Help>
         Synthesis alarm indicating at
         least one DDM Alarm or DDM Warning
        is detected on the Line Trscv Network
        Interface <Condtype> MSA_NETWORK_LANE_ALARM_WARNING_1
        <Probcause> informationalStatus(1000)
        <Alarmtype> other (1) <Polarity>
        (2)
        "
	  ::= { rm10010AlmmsaGlobalAlarmSummary 13 }



rm10010AlmMsaModuleAlarmWarning2 OBJECT-TYPE
	  SYNTAX EkiOnOff
	  MAX-ACCESS read-only
	  STATUS current
	  DESCRIPTION
        "
        Line Trscv Module Alarm And Warning
        2 :This OID indicates at least
         one DDM is detected on the Line
        Trscv module <Help> Synthesis alarm
        indicating at least one DDM Alarm
        or DDM Warning is detected on the
        Line Trscv module <Condtype> MSA_MODULE_ALARM_WARNING_2
        <Probcause> informationalStatus(1000)
        <Alarmtype> other (1) <Polarity>
        (2)
        "
	  ::= { rm10010AlmmsaGlobalAlarmSummary 12 }



rm10010AlmMsaModuleAlarmWarning1  OBJECT-TYPE
	  SYNTAX EkiOnOff
	  MAX-ACCESS read-only
	  STATUS current
	  DESCRIPTION
        "
        Line Trscv Module Alarm And Warning
        1 :This OID indicates at least
         one DDM is detected on the Line
        Trscv module <Help> Synthesis alarm
        indicating at least one DDM Alarm
        or DDM Warning is detected on the
        Line Trscv module <Condtype> MSA_MODULE_ALARM_WARNING_1
         <Probcause> informationalStatus(1000)
        <Alarmtype> other (1) <Polarity>
        (2)
        "
	  ::= { rm10010AlmmsaGlobalAlarmSummary 11 }



rm10010AlmModuleFault  OBJECT-TYPE
	  SYNTAX EkiOnOff
	  MAX-ACCESS read-only
	  STATUS current
	  DESCRIPTION
        "
        Line Trscv Module Fault :This
         OID indicates at least one Fault
        is detected on the Line Trscv module
        <Help> Synthesis alarm indicating
        at least one Fault is detected
         on the Line Trscv module <Condtype>
        MODULE_FAULT  <Probcause> informationalStatus(1000)
        <Alarmtype> other (1) <Polarity>
        (2)
        "
	  ::= { rm10010AlmmsaGlobalAlarmSummary 10 }



rm10010AlmMsaModuleGeneralStatus  OBJECT-TYPE
	  SYNTAX EkiOnOff
	  MAX-ACCESS read-only
	  STATUS current
	  DESCRIPTION
        "
        Line Trscv General Status :This
        OID indicates the Line Trscv module
        general <Help> Synthesis alarm
         indicating the Line Trscv module
        general status <Condtype> MSA_MODULE_GENERAL_STATUS
         <Probcause> informationalStatus(1000)
        <Alarmtype> other (1) <Polarity>
        (2)
        "
	  ::= { rm10010AlmmsaGlobalAlarmSummary 9 }



rm10010AlmMsaModuleState  OBJECT-TYPE
	  SYNTAX EkiOnOff
	  MAX-ACCESS read-only
	  STATUS current
	  DESCRIPTION
        "
        Line Trscv Module State :This
         OID indicates the Line Trscv module
        state <Help> Synthesis alarm indicating
        the Line Trscv module state <Condtype>
        MSA_MODULE_STATE  <Probcause> informationalStatus(1000)
        <Alarmtype> other (1) <Polarity>
        (2)
        "
	  ::= { rm10010AlmmsaGlobalAlarmSummary 8 }



rm10010AlmMsaNetworkLaneAlarmWarning2 OBJECT-TYPE
	  SYNTAX EkiOnOff
	  MAX-ACCESS read-only
	  STATUS current
	  DESCRIPTION
        "
        Line Trscv Network Alarm And Warning
        2 :This OID indicates at least
         one DDM This OID is detected on
        the Line Trscv Network Interface
        <Help> Synthesis alarm indicating
        at least one DDM Alarm or DDM Warning
        is detected on the Line Trscv Network
        Interface <Condtype> MSA_NETWORK_LANE_ALARM_WARNING_2
        <Probcause> informationalStatus(1000)
        <Alarmtype> other (1) <Polarity>
        (2)
        "
	  ::= { rm10010AlmmsaGlobalAlarmSummary 7 }



rm10010AlmMsaNetworkHostAlarmStatus OBJECT-TYPE
	  SYNTAX EkiOnOff
	  MAX-ACCESS read-only
	  STATUS current
	  DESCRIPTION
        "
        Line Trscv Network/Host Alarm
         Status :This OID indicates the
        state of the Network and Host interface
        of the Line Trscv <Help> Synthesis
        alarm indicating the alarm state
        of the Network and Host interface
        of the Line Trscv <Condtype> MSA_NETWORK_HOST_ALARM_STATUS
        <Probcause> informationalStatus(1000)
        <Alarmtype> other (1) <Polarity>
        (2)
        "
	  ::= { rm10010AlmmsaGlobalAlarmSummary 6 }



rm10010AlmMsaSoftGlobAlarmTest  OBJECT-TYPE
	  SYNTAX EkiOnOff
	  MAX-ACCESS read-only
	  STATUS current
	  DESCRIPTION
        "
        Line Trscv Global Alarm SW Test
        :This OID indicates the Line Trscv
        Global alarm This OID is raised
        by SW request for test purpose
         <Help> Status indicating the Line
        Trscv Global Alarm is raised by
        SW request for test purpose <Condtype>
        MSA_SOFT_GLOB_ALARM_TEST  <Probcause>
        informationalStatus(1000) <Alarmtype>
        other (1) <Polarity> (2)
        "
	  ::= { rm10010AlmmsaGlobalAlarmSummary 1 }



--- *****************************************************
---     LEAF for the msaNetworkTxAlignment article
--- *****************************************************
rm10010AlmmsaNetworkTxAlignment OBJECT IDENTIFIER ::= { rm10010AlmOtherCrit 49 }




rm10010AlmNetTxLossOfAlignment OBJECT-TYPE
	  SYNTAX EkiOnOff
	  MAX-ACCESS read-only
	  STATUS current
	  DESCRIPTION
        "
        Line Trscv Network Tx Loss Of
         Alignment :This OID indicates
         a Tx Loss of Alignment is detected
        on the Line Trscv Network interface
        <Help> Alarm indicating a Tx Loss
        of Alignment is detected on the
        Line Trscv Network interface <Condtype>
        NET_TX_LOSS_OF_ALIGNMENT <Probcause>
        transmitterFailure (56) <Alarmtype>
        equipmentAlarm (5) <Polarity> (2)
        "
	  ::= { rm10010AlmmsaNetworkTxAlignment 16 }



rm10010AlmNetTxOutOfAlignment OBJECT-TYPE
	  SYNTAX EkiOnOff
	  MAX-ACCESS read-only
	  STATUS current
	  DESCRIPTION
        "
        Line Trscv Network Tx Out Of Alignment
        :This OID indicates a Tx Out of
        Alignment is detected on the Line
        Trscv Network interface <Help>
         Alarm indicating a Tx Out of Alignment
        is detected on the Line Trscv Network
        interface <Condtype> NET_TX_OUT_OF_ALIGNMENT
        <Probcause> transmitterFailure
         (56) <Alarmtype> equipmentAlarm
        (5) <Polarity> (2)
        "
	  ::= { rm10010AlmmsaNetworkTxAlignment 15 }



rm10010AlmNetTxCmuLockFault OBJECT-TYPE
	  SYNTAX EkiOnOff
	  MAX-ACCESS read-only
	  STATUS current
	  DESCRIPTION
        "
        Line Trscv Network Tx CMU Lock
        Fault :This OID indicates a Tx
         Clock Multiplier Unit Lock Fault
        is detected on the Line Trscv Network
        interface <Help> Alarm indicating
        a Tx Clock Multiplier Unit Lock
        Fault is detected on the Line Trscv
        Network interface <Condtype> NET_TX_CMU_LOCK_FAULT
        <Probcause> transmitterFailure
         (56) <Alarmtype> equipmentAlarm
        (5) <Polarity> (2)
        "
	  ::= { rm10010AlmmsaNetworkTxAlignment 14 }



rm10010AlmNetTxReferenceClockFault OBJECT-TYPE
	  SYNTAX EkiOnOff
	  MAX-ACCESS read-only
	  STATUS current
	  DESCRIPTION
        "
        Line Trscv Network Tx Ref Clock
        Fault :This OID indicates a Tx
         Reference Clock Fault is detected
        on the Line Trscv Network interface
        <Help> Alarm indicating a Tx Reference
        Clock Fault is detected on the
         Line Trscv Network interface <Condtype>
        NET_TX_REFERENCE_CLOCK_FAULT <Probcause>
        transmitterFailure (56) <Alarmtype>
        equipmentAlarm (5) <Polarity> (2)
        "
	  ::= { rm10010AlmmsaNetworkTxAlignment 13 }



rm10010AlmNetTxTimingFault OBJECT-TYPE
	  SYNTAX EkiOnOff
	  MAX-ACCESS read-only
	  STATUS current
	  DESCRIPTION
        "
        Line Trscv Network Tx Timing Fault
        :This OID indicates a Tx Timing
        Fault is detected on the Line Trscv
        Network interface <Help> Alarm
         indicating a Tx Timing Fault is
        detected on the Line Trscv Network
        interface <Condtype> NET_TX_TIMING_FAULT
        <Probcause> transmitterFailure
         (56) <Alarmtype> equipmentAlarm
        (5) <Polarity> (2)
        "
	  ::= { rm10010AlmmsaNetworkTxAlignment 12 }



--- *****************************************************
---     LEAF for the msaNetworkRxAlignment article
--- *****************************************************
rm10010AlmmsaNetworkRxAlignment OBJECT IDENTIFIER ::= { rm10010AlmOtherCrit 50 }




rm10010AlmNetRxModemSyncDetectFault OBJECT-TYPE
	  SYNTAX EkiOnOff
	  MAX-ACCESS read-only
	  STATUS current
	  DESCRIPTION
        "
        Line Trscv Network Rx Modem Sync
        Detect Fault :This OID indicates
        a Rx Modem Synchronisation Detection
        Fault is detected on the Line Trscv
        Network interface <Help> Alarm
         indicating a Rx Modem Synchronisation
        Detection Fault is detected on
         the Line Trscv Network interface
        <Condtype> NET_RX_MODEM_SYNC_DETECT_FAULT
        <Probcause> receiverFailure (42)
        <Alarmtype> equipmentAlarm (5)
         <Polarity> (2)
        "
	  ::= { rm10010AlmmsaNetworkRxAlignment 16 }



rm10010AlmNetRxModemLockFault OBJECT-TYPE
	  SYNTAX EkiOnOff
	  MAX-ACCESS read-only
	  STATUS current
	  DESCRIPTION
        "
        Line Trscv Network Rx Modem Lock
        Fault :This OID indicates a Rx
         Modem Lock Fault is detected on
        the Line Trscv Network interface
        <Help> Alarm indicating a Rx Modem
        Lock Fault is detected on the Line
        Trscv Network interface <Condtype>
        NET_RX_MODEM_LOCK_FAULT <Probcause>
        receiverFailure (42) <Alarmtype>
        equipmentAlarm (5) <Polarity> (2)
        "
	  ::= { rm10010AlmmsaNetworkRxAlignment 15 }



rm10010AlmNetRxLossOfAlignment OBJECT-TYPE
	  SYNTAX EkiOnOff
	  MAX-ACCESS read-only
	  STATUS current
	  DESCRIPTION
        "
        Line Trscv Network Rx Loss Of
         Alignment :This OID indicates
         a Rx Loss of Alignment is detected
        on the Line Trscv Network interface
        <Help> Alarm indicating a Rx Loss
        of Alignment is detected on the
        Line Trscv Network interface <Condtype>
        NET_RX_LOSS_OF_ALIGNMENT <Probcause>
        receiverFailure (42) <Alarmtype>
        equipmentAlarm (5) <Polarity> (2)
        "
	  ::= { rm10010AlmmsaNetworkRxAlignment 14 }



rm10010AlmNetRxOutOfAlignment OBJECT-TYPE
	  SYNTAX EkiOnOff
	  MAX-ACCESS read-only
	  STATUS current
	  DESCRIPTION
        "
        Line Trscv Network Rx Out Of Alignment
        :This OID indicates a Rx Out of
        Alignment is detected on the Line
        Trscv Network interface <Help>
         Alarm indicating a Rx Out of Alignment
        is detected on the Line Trscv Network
        interface <Condtype> NET_RX_OUT_OF_ALIGNMENT
        <Probcause> receiverFailure (42)
        <Alarmtype> equipmentAlarm (5)
         <Polarity> (2)
        "
	  ::= { rm10010AlmmsaNetworkRxAlignment 13 }



rm10010AlmNetRxTimingFault OBJECT-TYPE
	  SYNTAX EkiOnOff
	  MAX-ACCESS read-only
	  STATUS current
	  DESCRIPTION
        "
        Line Trscv Network Rx Timing Fault
        :This OID indicates a Rx Timing
        Fault is detected on the Line Trscv
        Network interface <Help> Alarm
         indicating a Rx Timing Fault is
        detected on the Line Trscv Network
        interface <Condtype> NET_RX_TIMING_FAULT
        <Probcause> receiverFailure (42)
        <Alarmtype> equipmentAlarm (5)
         <Polarity> (2)
        "
	  ::= { rm10010AlmmsaNetworkRxAlignment 12 }



--- *****************************************************
---     LEAF for the msaNetworkHostNetworkAlarmSummary article
--- *****************************************************
rm10010AlmmsaNetworkHostNetworkAlarmSummary OBJECT IDENTIFIER ::= { rm10010AlmOtherCrit 51 }




rm10010AlmHostTxOtnStatus OBJECT-TYPE
	  SYNTAX EkiOnOff
	  MAX-ACCESS read-only
	  STATUS current
	  DESCRIPTION
        "
        Line Trscv Host Tx OTN :This OID
        indicates a Tx OTN Fault is detected
        on the Line Trscv Host interface
        <Help> Synthesis Alarm indicating
        a Tx OTN Fault is detected on the
        Line Trscv Host interface <Condtype>
        HOST_TX_OTN_STATUS <Probcause>
         informationalStatus(1000) <Alarmtype>
        other (1) <Polarity> (2)
        "
	  ::= { rm10010AlmmsaNetworkHostNetworkAlarmSummary 16 }



rm10010AlmHostTxAlignment OBJECT-TYPE
	  SYNTAX EkiOnOff
	  MAX-ACCESS read-only
	  STATUS current
	  DESCRIPTION
        "
        Line Trscv Host Tx Alignment :This
        OID indicates a Tx Alignment Fault
        is detected on the Line Trscv Host
        interface <Help> Synthesis Alarm
        indicating a Tx Alignment Fault
        is detected on the Line Trscv Host
        interface <Condtype> HOST_TX_ALIGNMENT
        <Probcause> informationalStatus(1000)
        <Alarmtype> other (1) <Polarity>
        (2)
        "
	  ::= { rm10010AlmmsaNetworkHostNetworkAlarmSummary 15 }



rm10010AlmHostRxAlignment OBJECT-TYPE
	  SYNTAX EkiOnOff
	  MAX-ACCESS read-only
	  STATUS current
	  DESCRIPTION
        "
        Line Trscv Host Rx Alignment :This
        OID indicates a Rx Alignment Fault
        is detected on the Line Trscv Host
        interface <Help> Synthesis Alarm
        indicating a Rx Alignment Fault
        is detected on the Line Trscv Host
        interface <Condtype> HOST_RX_ALIGNMENT
        <Probcause> informationalStatus(1000)
        <Alarmtype> other (1) <Polarity>
        (2)
        "
	  ::= { rm10010AlmmsaNetworkHostNetworkAlarmSummary 14 }



rm10010AlmNetworkRxOtn OBJECT-TYPE
	  SYNTAX EkiOnOff
	  MAX-ACCESS read-only
	  STATUS current
	  DESCRIPTION
        "
        Line Trscv Network Rx OTN :This
        OID indicates a Rx OTN Fault is
        detected on the Line Trscv Network
        interface <Help> Synthesis Alarm
        indicating a Rx OTN Fault is detected
        on the Line Trscv Network interface
        <Condtype> NETWORK_RX_OTN <Probcause>
        informationalStatus(1000) <Alarmtype>
        other (1) <Polarity> (2)
        "
	  ::= { rm10010AlmmsaNetworkHostNetworkAlarmSummary 13 }



rm10010AlmNetworkRxAlignment OBJECT-TYPE
	  SYNTAX EkiOnOff
	  MAX-ACCESS read-only
	  STATUS current
	  DESCRIPTION
        "
        Line Trscv Network Rx Alignment
        :This OID indicates a Rx Alignment
        Fault is detected on the Line Trscv
        Network interface <Help> Synthesis
        Alarm indicating a Rx Alignment
        Fault is detected on the Line Trscv
        Network interface <Condtype> NETWORK_RX_ALIGNMENT
        <Probcause> informationalStatus(1000)
        <Alarmtype> other (1) <Polarity>
        (2)
        "
	  ::= { rm10010AlmmsaNetworkHostNetworkAlarmSummary 12 }



rm10010AlmNetworkTxAlignment OBJECT-TYPE
	  SYNTAX EkiOnOff
	  MAX-ACCESS read-only
	  STATUS current
	  DESCRIPTION
        "
        Line Trscv Network Tx Alignment
        :This OID indicates a Tx Alignment
        Fault is detected on the Line Trscv
        Network interface <Help> Synthesis
        Alarm indicating a Tx Alignment
        Fault is detected on the Line Trscv
        Network interface <Condtype> NETWORK_TX_ALIGNMENT
        <Probcause> informationalStatus(1000)
        <Alarmtype> other (1) <Polarity>
        (2)
        "
	  ::= { rm10010AlmmsaNetworkHostNetworkAlarmSummary 11 }



--- *****************************************************
---     LEAF for the msaHostTxAlignment article
--- *****************************************************
rm10010AlmmsaHostTxAlignment OBJECT IDENTIFIER ::= { rm10010AlmOtherCrit 52 }




rm10010AlmHostTxCdrLockFault OBJECT-TYPE
	  SYNTAX EkiOnOff
	  MAX-ACCESS read-only
	  STATUS current
	  DESCRIPTION
        "
        Line Trscv Host Tx CDR Lock Fault
        :This OID indicates a Tx Clock
         Data Recovery Lock Fault is detected
        on the Line Trscv Host interface
        <Help> Alarm indicating a Tx Clock
        Data Recovery Lock Fault is detected
        on the Line Trscv Host interface
        <Condtype> HOST_TX_CDR_LOCK_FAULT
        <Probcause> receiverFailure (42)
        <Alarmtype> equipmentAlarm (5)
         <Polarity> (2)
        "
	  ::= { rm10010AlmmsaHostTxAlignment 16 }



rm10010AlmHostTxLossOfAlignment OBJECT-TYPE
	  SYNTAX EkiOnOff
	  MAX-ACCESS read-only
	  STATUS current
	  DESCRIPTION
        "
        Line Trscv Host Tx Loss Of Alignment
        :This OID indicates a Tx Loss of
        Alignment is detected on the Line
        Trscv Host interface <Help> Alarm
        indicating a Tx Loss of Alignment
        is detected on the Line Trscv Host
        interface <Condtype> HOST_TX_LOSS_OF_ALIGNMENT
        <Probcause> receiverFailure (42)
        <Alarmtype> equipmentAlarm (5)
         <Polarity> (2)
        "
	  ::= { rm10010AlmmsaHostTxAlignment 15 }



rm10010AlmHostTxOutOfAlignment OBJECT-TYPE
	  SYNTAX EkiOnOff
	  MAX-ACCESS read-only
	  STATUS current
	  DESCRIPTION
        "
        Line Trscv Host Tx Out Of Alignment
        :This OID indicates a Tx Out of
        Alignment is detected on the Line
        Trscv Host interface <Help> Alarm
        indicating a Tx Out of Alignment
        is detected on the Line Trscv Host
        interface <Condtype> HOST_TX_OUT_OF_ALIGNMENT
        <Probcause> receiverFailure (42)
        <Alarmtype> equipmentAlarm (5)
         <Polarity> (2)
        "
	  ::= { rm10010AlmmsaHostTxAlignment 14 }



rm10010AlmHostTxDeskewLockFault OBJECT-TYPE
	  SYNTAX EkiOnOff
	  MAX-ACCESS read-only
	  STATUS current
	  DESCRIPTION
        "
        Line Trscv Host Tx Deskew Lock
        Fault :This OID indicates a Tx
         Deskew Lock Fault is detected
         on  the Line Trscv Host interface
        <Help> Alarm indicating a Tx Deskew
        Lock Fault is detected on  the
         Line Trscv Host interface <Condtype>
        HOST_TX_DESKEW_LOCK_FAULT <Probcause>
        receiverFailure (42) <Alarmtype>
        equipmentAlarm (5) <Polarity> (2)
        "
	  ::= { rm10010AlmmsaHostTxAlignment 13 }



--- *****************************************************
---     LEAF for the msaHostRxAlignment article
--- *****************************************************
rm10010AlmmsaHostRxAlignment OBJECT IDENTIFIER ::= { rm10010AlmOtherCrit 53 }




rm10010AlmHostRxLossOfAlignment OBJECT-TYPE
	  SYNTAX EkiOnOff
	  MAX-ACCESS read-only
	  STATUS current
	  DESCRIPTION
        "
        Line Trscv Host Rx Loss Of Alignment
        :This OID indicates a Rx Loss of
        Alignment is detected on the Line
        Trscv Host interface <Help> Alarm
        indicating a Rx Loss of Alignment
        is detected on the Line Trscv Host
        interface <Condtype> HOST_RX_LOSS_OF_ALIGNMENT
        <Probcause> transmitterFailure
         (56) <Alarmtype> equipmentAlarm
        (5) <Polarity> (2)
        "
	  ::= { rm10010AlmmsaHostRxAlignment 16 }



rm10010AlmHostRxOutOfAlignment OBJECT-TYPE
	  SYNTAX EkiOnOff
	  MAX-ACCESS read-only
	  STATUS current
	  DESCRIPTION
        "
        Line Trscv Host Rx Out Of Alignment
        :This OID indicates a Rx Out of
        Alignment is detected on the Line
        Trscv Host interface <Help> Alarm
        indicating a Rx Out of Alignment
        is detected on the Line Trscv Host
        interface <Condtype> HOST_RX_OUT_OF_ALIGNMENT
        <Probcause> transmitterFailure
         (56) <Alarmtype> equipmentAlarm
        (5) <Polarity> (2)
        "
	  ::= { rm10010AlmmsaHostRxAlignment 15 }



rm10010AlmHostRxCmuLockFault OBJECT-TYPE
	  SYNTAX EkiOnOff
	  MAX-ACCESS read-only
	  STATUS current
	  DESCRIPTION
        "
        Line Trscv Host Rx CMU Lock Fault
        :This OID indicates a Rx Clock
         Multiplier Unit Lock Fault is
         detected on the Line Trscv Host
        interface <Help> Alarm indicating
        a Rx Clock Multiplier Unit Lock
        Fault is detected on the Line Trscv
        Host interface <Condtype> HOST_RX_CMU_LOCK_FAULT
        <Probcause> transmitterFailure
         (56) <Alarmtype> equipmentAlarm
        (5) <Polarity> (2)
        "
	  ::= { rm10010AlmmsaHostRxAlignment 14 }



--- *********************************************************
---     TABLE for the rm10010AlmclientNetworkLaneAlarmWarning articles
--- *********************************************************

rm10010AlmclientNetworkLaneAlarmWarningTable OBJECT-TYPE
	SYNTAX  SEQUENCE OF Rm10010AlmclientNetworkLaneAlarmWarningEntry
	MAX-ACCESS not-accessible
	STATUS current
	DESCRIPTION
        "
        List of rm10010AlmclientNetworkLaneAlarmWarning
        Article
        "
	::= { rm10010AlmClientNurg 56 }


rm10010AlmclientNetworkLaneAlarmWarningEntry OBJECT-TYPE
	SYNTAX Rm10010AlmclientNetworkLaneAlarmWarningEntry
	MAX-ACCESS not-accessible
	STATUS current
	DESCRIPTION
        "
        Row definition for the rm10010AlmclientNetworkLaneAlarmWarning
        table
        "
	INDEX   { rm10010AlmclientNetworkLaneAlarmWarningIndex }
	::= { rm10010AlmclientNetworkLaneAlarmWarningTable 1 }


Rm10010AlmclientNetworkLaneAlarmWarningEntry ::=
	SEQUENCE {
	rm10010AlmclientNetworkLaneAlarmWarningIndex
		INTEGER,
	rm10010AlmClientBiasHighAlarmPortn
		EkiOnOff,
	rm10010AlmClientBiasHighWarningPortn
		EkiOnOff,
	rm10010AlmClientBiasLowWarningPortn
		EkiOnOff,
	rm10010AlmClientBiasLowAlarmPortn
		EkiOnOff,
	rm10010AlmClientTxPowerHighAlarmPortn
		EkiOnOff,
	rm10010AlmClientTxPowerHighWarningPortn
		EkiOnOff,
	rm10010AlmClientTxPowerLowWarningPortn
		EkiOnOff,
	rm10010AlmClientTxPowerLowAlarmPortn
		EkiOnOff,
	rm10010AlmClientLaserTempHighAlarmPortn
		EkiOnOff,
	rm10010AlmClientLaserTempHighWarningPortn
		EkiOnOff,
	rm10010AlmClientLaserTempLowWarningPortn
		EkiOnOff,
	rm10010AlmLaserTempLowAlarmPortn
		EkiOnOff,
	rm10010AlmClientRxPowerHighAlarmPortn
		EkiOnOff,
	rm10010AlmClientRxPowerHighWarningPortn
		EkiOnOff,
	rm10010AlmClientRxPowerLowWarningPortn
		EkiOnOff,
	rm10010AlmClientRxPowerLowAlarmPortn
		EkiOnOff
	}


rm10010AlmclientNetworkLaneAlarmWarningIndex OBJECT-TYPE
	SYNTAX  INTEGER(0..128)
	MAX-ACCESS  read-only
	STATUS current
	DESCRIPTION
        "
        Index definition for the rm10010AlmclientNetworkLaneAlarmWarning
        table
        "
	::= { rm10010AlmclientNetworkLaneAlarmWarningEntry 1 }


rm10010AlmClientBiasHighAlarmPortn OBJECT-TYPE
	SYNTAX  EkiOnOff
	MAX-ACCESS read-only
	STATUS current
	DESCRIPTION
        "
        Client Trscv Bias High Alarm :This
        OID indicates that the Trscv laser
        bias current is higher than the
        threshold value written in the
         Trscv EEPROM <Help> Alarm indicating
        that the Trscv laser bias current
        is higher than the threshold value
        written in the Trscv EEPROM <Condtype>
        CLIENT_BIAS_HIGH_ALARM <Probcause>
        transmitterFailure (56) <Alarmtype>
        equipmentAlarm (5) <Polarity> (2)
        "
	::= { rm10010AlmclientNetworkLaneAlarmWarningEntry 17 }


rm10010AlmClientBiasHighWarningPortn OBJECT-TYPE
	SYNTAX  EkiOnOff
	MAX-ACCESS read-only
	STATUS current
	DESCRIPTION
        "
        Client Trscv Bias High Warning
        :This OID indicates that the Trscv
        laser bias current is higher than
        the threshold value written in
         the Trscv EEPROM <Help> Warning
        indicating that the Trscv laser
        bias current is higher than the
        threshold value written in the
         Trscv EEPROM <Condtype> CLIENT_BIAS_HIGH_WARNING
        <Probcause> transmitterFailure
         (56) <Alarmtype> equipmentAlarm
        (5) <Polarity> (2)
        "
	::= { rm10010AlmclientNetworkLaneAlarmWarningEntry 16 }


rm10010AlmClientBiasLowWarningPortn OBJECT-TYPE
	SYNTAX  EkiOnOff
	MAX-ACCESS read-only
	STATUS current
	DESCRIPTION
        "
        Client Trscv Bias Low Warning
         :This OID indicates that the Trscv
        laser bias current is lower than
        the threshold value written in
         the Trscv EEPROM <Help> Warning
        indicating that the Trscv laser
        bias current is lower than the
         threshold value written in the
        Trscv EEPROM <Condtype> CLIENT_BIAS_LOW_WARNING
        <Probcause> transmitterFailure
         (56) <Alarmtype> equipmentAlarm
        (5) <Polarity> (2)
        "
	::= { rm10010AlmclientNetworkLaneAlarmWarningEntry 15 }


rm10010AlmClientBiasLowAlarmPortn OBJECT-TYPE
	SYNTAX  EkiOnOff
	MAX-ACCESS read-only
	STATUS current
	DESCRIPTION
        "
        Client Trscv Bias Low Alarm :This
        OID indicates that the Trscv laser
        bias current is lower than the
         threshold value written in the
        Trscv EEPROM <Help> Alarm indicating
        that the Trscv laser bias current
        is lower than the threshold value
        written in the Trscv EEPROM <Condtype>
        CLIENT_BIAS_LOW_ALARM <Probcause>
        transmitterFailure (56) <Alarmtype>
        equipmentAlarm (5) <Polarity> (2)
        "
	::= { rm10010AlmclientNetworkLaneAlarmWarningEntry 14 }


rm10010AlmClientTxPowerHighAlarmPortn OBJECT-TYPE
	SYNTAX  EkiOnOff
	MAX-ACCESS read-only
	STATUS current
	DESCRIPTION
        "
        Client Trscv Tx Power High Alarm
        :This OID indicates that the Trscv
        output power is higher than the
        threshold value written in the
         Trscv EEPROM <Help> Alarm indicating
        that the Trscv output power is
         higher than the threshold value
        written in the Trscv EEPROM <Condtype>
        CLIENT_TX_POWER_HIGH_ALARM <Probcause>
        transmitterFailure (56) <Alarmtype>
        equipmentAlarm (5) <Polarity> (2)
        "
	::= { rm10010AlmclientNetworkLaneAlarmWarningEntry 13 }


rm10010AlmClientTxPowerHighWarningPortn OBJECT-TYPE
	SYNTAX  EkiOnOff
	MAX-ACCESS read-only
	STATUS current
	DESCRIPTION
        "
        Client Trscv Tx Power High Warning
        :This OID indicates that the Trscv
        output power is higher than the
        threshold value written in the
         Trscv EEPROM <Help> Warning indicating
        that the Trscv output power is
         higher than the threshold value
        written in the Trscv EEPROM <Condtype>
        CLIENT_TX_POWER_HIGH_WARNING <Probcause>
        transmitterFailure (56) <Alarmtype>
        equipmentAlarm (5) <Polarity> (2)
        "
	::= { rm10010AlmclientNetworkLaneAlarmWarningEntry 12 }


rm10010AlmClientTxPowerLowWarningPortn OBJECT-TYPE
	SYNTAX  EkiOnOff
	MAX-ACCESS read-only
	STATUS current
	DESCRIPTION
        "
        Client Trscv Tx Power Low Warning
        :This OID indicates that the Trscv
        output power is lower than the
         threshold value written in the
        Trscv EEPROM <Help> Warning indicating
        that the Trscv output power is
         lower than the threshold value
        written in the Trscv EEPROM <Condtype>
        CLIENT_TX_POWER_LOW_WARNING <Probcause>
        transmitterFailure (56) <Alarmtype>
        equipmentAlarm (5) <Polarity> (2)
        "
	::= { rm10010AlmclientNetworkLaneAlarmWarningEntry 11 }


rm10010AlmClientTxPowerLowAlarmPortn OBJECT-TYPE
	SYNTAX  EkiOnOff
	MAX-ACCESS read-only
	STATUS current
	DESCRIPTION
        "
        Client Trscv Tx Power Low Alarm
        :This OID indicates that the Trscv
        output power is lower than the
         threshold value written in the
        Trscv EEPROM <Help> Alarm indicating
        that the Trscv output power is
         lower than the threshold value
        written in the Trscv EEPROM <Condtype>
        CLIENT_TX_POWER_LOW_ALARM <Probcause>
        transmitterFailure (56) <Alarmtype>
        equipmentAlarm (5) <Polarity> (2)
        "
	::= { rm10010AlmclientNetworkLaneAlarmWarningEntry 10 }


rm10010AlmClientLaserTempHighAlarmPortn OBJECT-TYPE
	SYNTAX  EkiOnOff
	MAX-ACCESS read-only
	STATUS current
	DESCRIPTION
        "
        Client Trscv Laser Temp High Alarm
        :This OID indicates that the Trscv
        Laser Temperature is higher than
        the threshold value written in
         the Trscv EEPROM <Help> Alarm
         indicating that the Trscv Laser
        Temperature is higher than the
         threshold value written in the
        Trscv EEPROM <Condtype> CLIENT_LASER_TEMP_HIGH_ALARM
        <Probcause> temperatureUnacceptable
        (51) <Alarmtype> equipmentAlarm
        (5) <Polarity> (2)
        "
	::= { rm10010AlmclientNetworkLaneAlarmWarningEntry 9 }


rm10010AlmClientLaserTempHighWarningPortn OBJECT-TYPE
	SYNTAX  EkiOnOff
	MAX-ACCESS read-only
	STATUS current
	DESCRIPTION
        "
        Client Trscv Laser Temp High Warning
        :This OID indicates that the Trscv
        Laser Temperature is higher than
        the threshold value written in
         the Trscv EEPROM <Help> Warning
        indicating that the Trscv Laser
        Temperature is higher than the
         threshold value written in the
        Trscv EEPROM <Condtype> CLIENT_LASER_TEMP_HIGH_WARNING
        <Probcause> temperatureUnacceptable
        (51) <Alarmtype> equipmentAlarm
        (5) <Polarity> (2)
        "
	::= { rm10010AlmclientNetworkLaneAlarmWarningEntry 8 }


rm10010AlmClientLaserTempLowWarningPortn OBJECT-TYPE
	SYNTAX  EkiOnOff
	MAX-ACCESS read-only
	STATUS current
	DESCRIPTION
        "
        Client Trscv Laser Temp Low Warning
        :This OID indicates that the Trscv
        Laser Temperature is lower than
        the threshold value written in
         the Trscv EEPROM <Help> Warning
        indicating that the Trscv Laser
        Temperature is lower than the threshold
        value written in the Trscv EEPROM
        <Condtype> CLIENT_LASER_TEMP_LOW_WARNING
        <Probcause> temperatureUnacceptable
        (51) <Alarmtype> equipmentAlarm
        (5) <Polarity> (2)
        "
	::= { rm10010AlmclientNetworkLaneAlarmWarningEntry 7 }


rm10010AlmLaserTempLowAlarmPortn OBJECT-TYPE
	SYNTAX  EkiOnOff
	MAX-ACCESS read-only
	STATUS current
	DESCRIPTION
        "
        Client Trscv Laser Temp Low Alarm
        :This OID indicates that the Trscv
        Laser Temperature is lower than
        the threshold value written in
         the Trscv EEPROM <Help> Alarm
         indicating that the Trscv Laser
        Temperature is lower than the threshold
        value written in the Trscv EEPROM
        <Condtype> LASER_TEMP_LOW_ALARM
        <Probcause> temperatureUnacceptable
        (51) <Alarmtype> equipmentAlarm
        (5) <Polarity> (2)
        "
	::= { rm10010AlmclientNetworkLaneAlarmWarningEntry 6 }


rm10010AlmClientRxPowerHighAlarmPortn OBJECT-TYPE
	SYNTAX  EkiOnOff
	MAX-ACCESS read-only
	STATUS current
	DESCRIPTION
        "
        Client Trscv Rx Power High Alarm
        :This OID indicates that the Trscv
        input power is higher than the
         threshold value written in the
        Trscv EEPROM <Help> Alarm indicating
        that the Trscv input power is higher
        than the threshold value written
        in the Trscv EEPROM <Condtype>
         CLIENT_RX_POWER_HIGH_ALARM <Probcause>
        receiveFailure (41) <Alarmtype>
        equipmentAlarm (5) <Polarity> (2)
        "
	::= { rm10010AlmclientNetworkLaneAlarmWarningEntry 5 }


rm10010AlmClientRxPowerHighWarningPortn OBJECT-TYPE
	SYNTAX  EkiOnOff
	MAX-ACCESS read-only
	STATUS current
	DESCRIPTION
        "
        Client Trscv Rx Power High Warning
        :This OID indicates that the Trscv
        input power is higher than the
         threshold value written in the
        Trscv EEPROM <Help> Warning indicating
        that the Trscv input power is higher
        than the threshold value written
        in the Trscv EEPROM <Condtype>
         CLIENT_RX_POWER_HIGH_WARNING <Probcause>
        receiveFailure (41) <Alarmtype>
        equipmentAlarm (5) <Polarity> (2)
        "
	::= { rm10010AlmclientNetworkLaneAlarmWarningEntry 4 }


rm10010AlmClientRxPowerLowWarningPortn OBJECT-TYPE
	SYNTAX  EkiOnOff
	MAX-ACCESS read-only
	STATUS current
	DESCRIPTION
        "
        Client Trscv Rx Power Low Warning
        :This OID indicates that the Trscv
        input power is lower than the threshold
        value written in the Trscv EEPROM
        <Help> Warning indicating that
         the Trscv input power is lower
        than the threshold value written
        in the Trscv EEPROM <Condtype>
         CLIENT_RX_POWER_LOW_WARNING <Probcause>
        receiveFailure (41) <Alarmtype>
        equipmentAlarm (5) <Polarity> (2)
        "
	::= { rm10010AlmclientNetworkLaneAlarmWarningEntry 3 }


rm10010AlmClientRxPowerLowAlarmPortn OBJECT-TYPE
	SYNTAX  EkiOnOff
	MAX-ACCESS read-only
	STATUS current
	DESCRIPTION
        "
        Client Trscv Rx Power Low Alarm
        :This OID indicates that the Trscv
        input power is lower than the threshold
        value written in the Trscv EEPROM
        <Help> Alarm indicating that the
        Trscv input power is lower than
        the threshold value written in
         the Trscv EEPROM <Condtype> CLIENT_RX_POWER_LOW_ALARM
        <Probcause> receiveFailure (41)
        <Alarmtype> equipmentAlarm (5)
         <Polarity> (2)
        "
	::= { rm10010AlmclientNetworkLaneAlarmWarningEntry 2 }


--- *********************************************************
---     TABLE for the rm10010AlmclientNetworkLaneFault articles
--- *********************************************************

rm10010AlmclientNetworkLaneFaultTable OBJECT-TYPE
	SYNTAX  SEQUENCE OF Rm10010AlmclientNetworkLaneFaultEntry
	MAX-ACCESS not-accessible
	STATUS current
	DESCRIPTION
        "
        List of rm10010AlmclientNetworkLaneFault
        Article
        "
	::= { rm10010AlmClientUrg 72 }


rm10010AlmclientNetworkLaneFaultEntry OBJECT-TYPE
	SYNTAX Rm10010AlmclientNetworkLaneFaultEntry
	MAX-ACCESS not-accessible
	STATUS current
	DESCRIPTION
        "
        Row definition for the rm10010AlmclientNetworkLaneFault
        table
        "
	INDEX   { rm10010AlmclientNetworkLaneFaultIndex }
	::= { rm10010AlmclientNetworkLaneFaultTable 1 }


Rm10010AlmclientNetworkLaneFaultEntry ::=
	SEQUENCE {
	rm10010AlmclientNetworkLaneFaultIndex
		INTEGER,
	rm10010AlmClientLaneTecFaultPortn
		EkiOnOff,
	rm10010AlmClientLaneWavelengthUnlockedPortn
		EkiOnOff,
	rm10010AlmClientLaneApdPowerSupplyPortn
		EkiOnOff,
	rm10010AlmClientLaneTxLosfPortn
		EkiOnOff,
	rm10010AlmClientLaneTxLolPortn
		EkiOnOff,
	rm10010AlmClientLaneRxLosPortn
		EkiOnOff,
	rm10010AlmClientLaneRxLolPortn
		EkiOnOff,
	rm10010AlmClientLaneRxFifoErrorPortn
		EkiOnOff
	}


rm10010AlmclientNetworkLaneFaultIndex OBJECT-TYPE
	SYNTAX  INTEGER(0..128)
	MAX-ACCESS  read-only
	STATUS current
	DESCRIPTION
        "
        Index definition for the rm10010AlmclientNetworkLaneFault
        table
        "
	::= { rm10010AlmclientNetworkLaneFaultEntry 1 }


rm10010AlmClientLaneTecFaultPortn OBJECT-TYPE
	SYNTAX  EkiOnOff
	MAX-ACCESS read-only
	STATUS current
	DESCRIPTION
        "
        Client Network Lane TEC Fault
         :This OID indicates a TEC Fault
        on the Client Trscv Network Lane
        <Help> Alarm indicating a TEC Fault
        on the Client Trscv Network Lane
        <Condtype> CLIENT_LANE_TEC_FAULT
        <Probcause> transmitterFailure
         (56) <Alarmtype> equipmentAlarm
        (5) <Polarity> (2)
        "
	::= { rm10010AlmclientNetworkLaneFaultEntry 17 }


rm10010AlmClientLaneWavelengthUnlockedPortn OBJECT-TYPE
	SYNTAX  EkiOnOff
	MAX-ACCESS read-only
	STATUS current
	DESCRIPTION
        "
        Client Network Lane Wavelength
        Unlock :This OID indicates a Wavelength
        unlock on the Client Trscv Network
        Lane <Help> Alarm indicating a
         Wavelength unlock on the Client
        Trscv Network Lane <Condtype> CLIENT_LANE_WAVELENGTH_UNLOCKED
        <Probcause> transmitterFailure
         (56) <Alarmtype> equipmentAlarm
        (5) <Polarity> (2)
        "
	::= { rm10010AlmclientNetworkLaneFaultEntry 16 }


rm10010AlmClientLaneApdPowerSupplyPortn OBJECT-TYPE
	SYNTAX  EkiOnOff
	MAX-ACCESS read-only
	STATUS current
	DESCRIPTION
        "
        Client Network Lane APD Power
         Supply :This OID indicates an
         APD Power supply failure on the
        Client Trscv Network Lane <Help>
        Alarm indicating an APD Power supply
        failure on the Client Trscv Network
        Lane <Condtype> CLIENT_LANE_APD_POWER_SUPPLY
        <Probcause> transmitterFailure
         (56) <Alarmtype> equipmentAlarm
        (5) <Polarity> (2)
        "
	::= { rm10010AlmclientNetworkLaneFaultEntry 15 }


rm10010AlmClientLaneTxLosfPortn OBJECT-TYPE
	SYNTAX  EkiOnOff
	MAX-ACCESS read-only
	STATUS current
	DESCRIPTION
        "
        Client Network Lane Tx Loss Of
        Signal Functionality :This OID
         indicates a Tx Loss of Signal
         Functionality on the Client Trscv
        Network Lane <Help> Alarm indicating
        a Tx Loss of Signal Functionality
        on the Client Trscv Network Lane
        <Condtype> CLIENT_LANE_TX_LOSF
         <Probcause> transmitterFailure
        (56) <Alarmtype> equipmentAlarm
        (5) <Polarity> (2)
        "
	::= { rm10010AlmclientNetworkLaneFaultEntry 9 }


rm10010AlmClientLaneTxLolPortn OBJECT-TYPE
	SYNTAX  EkiOnOff
	MAX-ACCESS read-only
	STATUS current
	DESCRIPTION
        "
        Client Network Lane Tx Loss Of
        Lock :This OID indicates a Tx Loss
        of Lock on the Client Trscv Network
        Lane <Help> Alarm indicating a
         Tx Loss of Lock on the Client
         Trscv Network Lane <Condtype>
         CLIENT_LANE_TX_LOL <Probcause>
        transmitterFailure (56) <Alarmtype>
        equipmentAlarm (5) <Polarity> (2)
        "
	::= { rm10010AlmclientNetworkLaneFaultEntry 8 }


rm10010AlmClientLaneRxLosPortn OBJECT-TYPE
	SYNTAX  EkiOnOff
	MAX-ACCESS read-only
	STATUS current
	DESCRIPTION
        "
        Client Network Lane Rx Loss Of
        Signal :This OID indicates a Rx
        Loss of Signal on the Client Trscv
        Network Lane <Help> Alarm indicating
        a Rx Loss of Signal on the Client
        Trscv Network Lane <Condtype> CLIENT_LANE_RX_LOS
        <Probcause> receiveFailure (41)
        <Alarmtype> physicalViolation (9)
        <Polarity> (2)
        "
	::= { rm10010AlmclientNetworkLaneFaultEntry 6 }


rm10010AlmClientLaneRxLolPortn OBJECT-TYPE
	SYNTAX  EkiOnOff
	MAX-ACCESS read-only
	STATUS current
	DESCRIPTION
        "
        Client Network Lane Rx Loss Of
        Lock :This OID indicates a Rx Loss
        of Lock on the Client Trscv Network
        Lane <Help> Alarm indicating a
         Rx Loss of Lock on the Client
         Trscv Network Lane <Condtype>
         CLIENT_LANE_RX_LOL <Probcause>
        receiverFailure (42) <Alarmtype>
        equipmentAlarm (5) <Polarity> (2)
        "
	::= { rm10010AlmclientNetworkLaneFaultEntry 5 }


rm10010AlmClientLaneRxFifoErrorPortn OBJECT-TYPE
	SYNTAX  EkiOnOff
	MAX-ACCESS read-only
	STATUS current
	DESCRIPTION
        "
        Client Network Lane Rx FIFO Error
        :This OID indicates a Rx FIFO Error
        on the Client Trscv Network Lane
        <Help> Alarm indicating a Rx FIFO
        Error on the Client Trscv Network
        Lane <Condtype> CLIENT_LANE_RX_FIFO_ERROR
        <Probcause> receiverFailure (42)
        <Alarmtype> equipmentAlarm (5)
         <Polarity> (2)
        "
	::= { rm10010AlmclientNetworkLaneFaultEntry 4 }


--- *********************************************************
---     TABLE for the rm10010AlmclientHostLaneFault articles
--- *********************************************************

rm10010AlmclientHostLaneFaultTable OBJECT-TYPE
	SYNTAX  SEQUENCE OF Rm10010AlmclientHostLaneFaultEntry
	MAX-ACCESS not-accessible
	STATUS current
	DESCRIPTION
        "
        List of rm10010AlmclientHostLaneFault
        Article
        "
	::= { rm10010AlmClientUrg 88 }


rm10010AlmclientHostLaneFaultEntry OBJECT-TYPE
	SYNTAX Rm10010AlmclientHostLaneFaultEntry
	MAX-ACCESS not-accessible
	STATUS current
	DESCRIPTION
        "
        Row definition for the rm10010AlmclientHostLaneFault
        table
        "
	INDEX   { rm10010AlmclientHostLaneFaultIndex }
	::= { rm10010AlmclientHostLaneFaultTable 1 }


Rm10010AlmclientHostLaneFaultEntry ::=
	SEQUENCE {
	rm10010AlmclientHostLaneFaultIndex
		INTEGER,
	rm10010AlmClientLaneTxFifoErrorPortn
		EkiOnOff,
	rm10010AlmClientTxHostLolPortn
		EkiOnOff,
	rm10010AlmClientCsfDetectedPortn
		EkiOnOff,
	rm10010AlmClientLanesNotAlignedPortn
		EkiOnOff,
	rm10010AlmClientLanes6466UnlockPortn
		EkiOnOff,
	rm10010AlmClientLanesMarkerUnlockPortn
		EkiOnOff,
	rm10010AlmClientInputLossOfSigPortn
		EkiOnOff,
	rm10010AlmClientLossOfSyncPortn
		EkiOnOff
	}


rm10010AlmclientHostLaneFaultIndex OBJECT-TYPE
	SYNTAX  INTEGER(0..128)
	MAX-ACCESS  read-only
	STATUS current
	DESCRIPTION
        "
        Index definition for the rm10010AlmclientHostLaneFault
        table
        "
	::= { rm10010AlmclientHostLaneFaultEntry 1 }


rm10010AlmClientLaneTxFifoErrorPortn OBJECT-TYPE
	SYNTAX  EkiOnOff
	MAX-ACCESS read-only
	STATUS current
	DESCRIPTION
        "
        Client Host Lane Tx FIFO Error
        :This OID indicates a Tx FIFO Error
        on the Client Trscv Host Lane <Help>
        Alarm indicating a Tx FIFO Error
        on the Client Trscv Host Lane <Condtype>
        CLIENT_LANE_TX_FIFO_ERROR <Probcause>
        receiverFailure (42) <Alarmtype>
        equipmentAlarm (5) <Polarity> (2)
        "
	::= { rm10010AlmclientHostLaneFaultEntry 11 }


rm10010AlmClientTxHostLolPortn OBJECT-TYPE
	SYNTAX  EkiOnOff
	MAX-ACCESS read-only
	STATUS current
	DESCRIPTION
        "
        Client Host Lane Tx Loss Of Lock
        :This OID indicates a Tx Loss of
        Lock on the Client Trscv Host Lane
        <Help> Alarm indicating a Tx Loss
        of Lock on the Client Trscv Host
        Lane <Condtype> CLIENT_TX_HOST_LOL
        <Probcause> receiverFailure (42)
        <Alarmtype> equipmentAlarm (5)
         <Polarity> (2)
        "
	::= { rm10010AlmclientHostLaneFaultEntry 10 }


rm10010AlmClientCsfDetectedPortn OBJECT-TYPE
	SYNTAX  EkiOnOff
	MAX-ACCESS read-only
	STATUS current
	DESCRIPTION
        "
        Client Signal Fail Detected :This
        OID indicates that a CSF has been
        detected on client port in the
         downstream direction   <Help>
          This alarm indicates if a Client
        Signal Fail has been detected in
        the incoming line frame for this
        client port <Condtype> CLIENT_CSF_DETECTED
        <Probcause> receiveFailure (41)
        <Alarmtype> other(1) <Polarity>
        (2)
        "
	::= { rm10010AlmclientHostLaneFaultEntry 7 }


rm10010AlmClientLanesNotAlignedPortn OBJECT-TYPE
	SYNTAX  EkiOnOff
	MAX-ACCESS read-only
	STATUS current
	DESCRIPTION
        "
        Client Lanes Not Aligned :This
        OID indicates the Client lanes
         are not aligned <Help> Alarm indicating
        the Client lanes are not aligned
        <Condtype> CLIENT_LANES_NOT_ALIGNED
        <Probcause> receiveFailure (41)
        <Alarmtype> integrityViolation
         (7) <Polarity> (2)
        "
	::= { rm10010AlmclientHostLaneFaultEntry 6 }


rm10010AlmClientLanes6466UnlockPortn OBJECT-TYPE
	SYNTAX  EkiOnOff
	MAX-ACCESS read-only
	STATUS current
	DESCRIPTION
        "
        Client Lanes 64/66b Unlock :This
        OID indicates the Client 64/66b
        decoder is not lock <Help> Alarm
        indicating the Client 64/66b decoder
        is not lock <Condtype> CLIENT_LANES_64_66_UNLOCK
        <Probcause> receiveFailure (41)
        <Alarmtype> integrityViolation
         (7) <Polarity> (2)
        "
	::= { rm10010AlmclientHostLaneFaultEntry 5 }


rm10010AlmClientLanesMarkerUnlockPortn OBJECT-TYPE
	SYNTAX  EkiOnOff
	MAX-ACCESS read-only
	STATUS current
	DESCRIPTION
        "
        Client Lanes Marker Unlock :This
        OID indicates the Client lanes
         marker alignment is not lock <Help>
        Alarm indicating the Client lanes
        marker alignment is not lock <Condtype>
        CLIENT_LANES_MARKER_UNLOCK <Probcause>
        receiveFailure (41) <Alarmtype>
        integrityViolation (7) <Polarity>
        (2)
        "
	::= { rm10010AlmclientHostLaneFaultEntry 4 }


rm10010AlmClientInputLossOfSigPortn OBJECT-TYPE
	SYNTAX  EkiOnOff
	MAX-ACCESS read-only
	STATUS current
	DESCRIPTION
        "
        Client Input Loss Of Signal :This
        OID indicates a Loss of Signal
         is detected on the Client Trscv
        <Help> Alarm indicating a Loss
         of Signal is detected on the Client
        Trscv <Condtype> CLIENT_INPUT_LOSS_OF_SIG
        <Probcause> receiveFailure (41)
        <Alarmtype> physicalViolation (9)
        <Polarity> (2)
        "
	::= { rm10010AlmclientHostLaneFaultEntry 3 }


rm10010AlmClientLossOfSyncPortn OBJECT-TYPE
	SYNTAX  EkiOnOff
	MAX-ACCESS read-only
	STATUS current
	DESCRIPTION
        "
        Client Frame Alignment Loss :This
        OID indicates the module is not
        aligned with the incoming Client
        signal <Help> Alarm indicating
         the module is not aligned with
        the incoming client signal <Condtype>
        CLIENT_LOSS_OF_SYNC <Probcause>
        receiveFailure (41) <Alarmtype>
        integrityViolation (7) <Polarity>
        (2)
        "
	::= { rm10010AlmclientHostLaneFaultEntry 2 }


--- *********************************************************
---     TABLE for the rm10010AlmlineNetworkLaneAlarmWarning1 articles
--- *********************************************************

rm10010AlmlineNetworkLaneAlarmWarning1Table OBJECT-TYPE
	SYNTAX  SEQUENCE OF Rm10010AlmlineNetworkLaneAlarmWarning1Entry
	MAX-ACCESS not-accessible
	STATUS current
	DESCRIPTION
        "
        List of rm10010AlmlineNetworkLaneAlarmWarning1
        Article
        "
	::= { rm10010AlmLineNurg 104 }


rm10010AlmlineNetworkLaneAlarmWarning1Entry OBJECT-TYPE
	SYNTAX Rm10010AlmlineNetworkLaneAlarmWarning1Entry
	MAX-ACCESS not-accessible
	STATUS current
	DESCRIPTION
        "
        Row definition for the rm10010AlmlineNetworkLaneAlarmWarning1
        table
        "
	INDEX   { rm10010AlmlineNetworkLaneAlarmWarning1Index }
	::= { rm10010AlmlineNetworkLaneAlarmWarning1Table 1 }


Rm10010AlmlineNetworkLaneAlarmWarning1Entry ::=
	SEQUENCE {
	rm10010AlmlineNetworkLaneAlarmWarning1Index
		INTEGER,
	rm10010AlmLineBiasHighAlarmPortn
		EkiOnOff,
	rm10010AlmLineBiasHighWarningPortn
		EkiOnOff,
	rm10010AlmLineBiasLowWarningPortn
		EkiOnOff,
	rm10010AlmLineBiasLowAlarmPortn
		EkiOnOff,
	rm10010AlmLineTxPowerHighAlarmPortn
		EkiOnOff,
	rm10010AlmLineTxPowerHighWarningPortn
		EkiOnOff,
	rm10010AlmLineTxPowerLowWarningPortn
		EkiOnOff,
	rm10010AlmLineTxPowerLowAlarmPortn
		EkiOnOff,
	rm10010AlmLineLaserTempHighAlarmPortn
		EkiOnOff,
	rm10010AlmLineLaserTempHighWarningPortn
		EkiOnOff,
	rm10010AlmLineLaserTempLowWarningPortn
		EkiOnOff,
	rm10010AlmLineLaserTempLowAlarmPortn
		EkiOnOff,
	rm10010AlmLineRxPowerHighAlarmPortn
		EkiOnOff,
	rm10010AlmLineRxPowerHighWarningPortn
		EkiOnOff,
	rm10010AlmLineRxPowerLowWarningPortn
		EkiOnOff,
	rm10010AlmLineRxPowerLowAlarmPortn
		EkiOnOff
	}


rm10010AlmlineNetworkLaneAlarmWarning1Index OBJECT-TYPE
	SYNTAX  INTEGER(0..128)
	MAX-ACCESS  read-only
	STATUS current
	DESCRIPTION
        "
        Index definition for the rm10010AlmlineNetworkLaneAlarmWarning1
        table
        "
	::= { rm10010AlmlineNetworkLaneAlarmWarning1Entry 1 }


rm10010AlmLineBiasHighAlarmPortn OBJECT-TYPE
	SYNTAX  EkiOnOff
	MAX-ACCESS read-only
	STATUS current
	DESCRIPTION
        "
        Line Trscv Tx Bias High Alarm
         :This OID indicates that the Trscv
        laser bias current is higher than
        the threshold value written in
         the Trscv EEPROM <Help> Alarm
         indicating that the Trscv laser
        bias current is higher than the
        threshold value written in the
         Trscv EEPROM <Condtype> LINE_BIAS_HIGH_ALARM
        <Probcause> transmitterFailure
         (56) <Alarmtype> equipmentAlarm
        (5) <Polarity> (2)
        "
	::= { rm10010AlmlineNetworkLaneAlarmWarning1Entry 17 }


rm10010AlmLineBiasHighWarningPortn OBJECT-TYPE
	SYNTAX  EkiOnOff
	MAX-ACCESS read-only
	STATUS current
	DESCRIPTION
        "
        Line Trscv Tx Bias High Warning
        :This OID indicates that the Trscv
        laser bias current is higher than
        the threshold value written in
         the Trscv EEPROM <Help> Warning
        indicating that the Trscv laser
        bias current is higher than the
        threshold value written in the
         Trscv EEPROM <Condtype> LINE_BIAS_HIGH_WARNING
        <Probcause> transmitterFailure
         (56) <Alarmtype> equipmentAlarm
        (5) <Polarity> (2)
        "
	::= { rm10010AlmlineNetworkLaneAlarmWarning1Entry 16 }


rm10010AlmLineBiasLowWarningPortn OBJECT-TYPE
	SYNTAX  EkiOnOff
	MAX-ACCESS read-only
	STATUS current
	DESCRIPTION
        "
        Line Trscv Tx Bias Low Warning
        :This OID indicates that the Trscv
        laser bias current is lower than
        the threshold value written in
         the Trscv EEPROM <Help> Warning
        indicating that the Trscv laser
        bias current is lower than the
         threshold value written in the
        Trscv EEPROM <Condtype> LINE_BIAS_LOW_WARNING
        <Probcause> transmitterFailure
         (56) <Alarmtype> equipmentAlarm
        (5) <Polarity> (2)
        "
	::= { rm10010AlmlineNetworkLaneAlarmWarning1Entry 15 }


rm10010AlmLineBiasLowAlarmPortn OBJECT-TYPE
	SYNTAX  EkiOnOff
	MAX-ACCESS read-only
	STATUS current
	DESCRIPTION
        "
        Line Trscv Tx Bias Low Alarm :This
        OID indicates that the Trscv laser
        bias current is lower than the
         threshold value written in the
        Trscv EEPROM <Help> Alarm indicating
        that the Trscv laser bias current
        is lower than the threshold value
        written in the Trscv EEPROM <Condtype>
        LINE_BIAS_LOW_ALARM <Probcause>
        transmitterFailure (56) <Alarmtype>
        equipmentAlarm (5) <Polarity> (2)
        "
	::= { rm10010AlmlineNetworkLaneAlarmWarning1Entry 14 }


rm10010AlmLineTxPowerHighAlarmPortn OBJECT-TYPE
	SYNTAX  EkiOnOff
	MAX-ACCESS read-only
	STATUS current
	DESCRIPTION
        "
        Line Trscv Tx Power High Alarm
        :This OID indicates that the Trscv
        output power is higher than the
        threshold value written in the
         Trscv EEPROM <Help> Alarm indicating
        that the Trscv output power is
         higher than the threshold value
        written in the Trscv EEPROM <Condtype>
        LINE_TX_POWER_HIGH_ALARM <Probcause>
        transmitterFailure (56) <Alarmtype>
        equipmentAlarm (5) <Polarity> (2)
        "
	::= { rm10010AlmlineNetworkLaneAlarmWarning1Entry 13 }


rm10010AlmLineTxPowerHighWarningPortn OBJECT-TYPE
	SYNTAX  EkiOnOff
	MAX-ACCESS read-only
	STATUS current
	DESCRIPTION
        "
        Line Trscv Tx Power High Warning
        :This OID indicates that the Trscv
        output power is higher than the
        threshold value written in the
         Trscv EEPROM <Help> Warning indicating
        that the Trscv output power is
         higher than the threshold value
        written in the Trscv EEPROM <Condtype>
        LINE_TX_POWER_HIGH_WARNING <Probcause>
        transmitterFailure (56) <Alarmtype>
        equipmentAlarm (5) <Polarity> (2)
        "
	::= { rm10010AlmlineNetworkLaneAlarmWarning1Entry 12 }


rm10010AlmLineTxPowerLowWarningPortn OBJECT-TYPE
	SYNTAX  EkiOnOff
	MAX-ACCESS read-only
	STATUS current
	DESCRIPTION
        "
        Line Trscv Tx Power Low Warning
        :This OID indicates that the Trscv
        output power is lower than the
         threshold value written in the
        Trscv EEPROM <Help> Warning indicating
        that the Trscv output power is
         lower than the threshold value
        written in the Trscv EEPROM <Condtype>
        LINE_TX_POWER_LOW_WARNING <Probcause>
        transmitterFailure (56) <Alarmtype>
        equipmentAlarm (5) <Polarity> (2)
        "
	::= { rm10010AlmlineNetworkLaneAlarmWarning1Entry 11 }


rm10010AlmLineTxPowerLowAlarmPortn OBJECT-TYPE
	SYNTAX  EkiOnOff
	MAX-ACCESS read-only
	STATUS current
	DESCRIPTION
        "
        Line Trscv Tx Power Low Alarm
         :This OID indicates that the Trscv
        output power is lower than the
         threshold value written in the
        Trscv EEPROM <Help> Alarm indicating
        that the Trscv output power is
         lower than the threshold value
        written in the Trscv EEPROM <Condtype>
        LINE_TX_POWER_LOW_ALARM <Probcause>
        transmitterFailure (56) <Alarmtype>
        equipmentAlarm (5) <Polarity> (2)
        "
	::= { rm10010AlmlineNetworkLaneAlarmWarning1Entry 10 }


rm10010AlmLineLaserTempHighAlarmPortn OBJECT-TYPE
	SYNTAX  EkiOnOff
	MAX-ACCESS read-only
	STATUS current
	DESCRIPTION
        "
        Line Trscv Tx Laser Temp High
         Alarm :This OID indicates that
        the Trscv Tx Laser Temperature
         is higher than the threshold value
        written in the Trscv EEPROM <Help>
        Alarm indicating that the Trscv
        Tx Laser Temperature is higher
         than the threshold value written
        in the Trscv EEPROM <Condtype>
         LINE_LASER_TEMP_HIGH_ALARM <Probcause>
        temperatureUnacceptable (51) <Alarmtype>
        equipmentAlarm (5) <Polarity> (2)
        "
	::= { rm10010AlmlineNetworkLaneAlarmWarning1Entry 9 }


rm10010AlmLineLaserTempHighWarningPortn OBJECT-TYPE
	SYNTAX  EkiOnOff
	MAX-ACCESS read-only
	STATUS current
	DESCRIPTION
        "
        Line Trscv Tx Laser Temp High
         Warning :This OID indicates that
        the Trscv Tx Laser Temperature
         is higher than the threshold value
        written in the Trscv EEPROM <Help>
        Warning indicating that the Trscv
        Tx Laser Temperature is higher
         than the threshold value written
        in the Trscv EEPROM <Condtype>
         LINE_LASER_TEMP_HIGH_WARNING <Probcause>
        temperatureUnacceptable (51) <Alarmtype>
        equipmentAlarm (5) <Polarity> (2)
        "
	::= { rm10010AlmlineNetworkLaneAlarmWarning1Entry 8 }


rm10010AlmLineLaserTempLowWarningPortn OBJECT-TYPE
	SYNTAX  EkiOnOff
	MAX-ACCESS read-only
	STATUS current
	DESCRIPTION
        "
        Line Trscv Tx Laser Temp Low Warning
        :This OID indicates that the Trscv
        Tx Laser Temperature is lower than
        the threshold value written in
         the Trscv EEPROM <Help> Warning
        indicating that the Trscv Tx Laser
        Temperature is lower than the threshold
        value written in the Trscv EEPROM
        <Condtype> LINE_LASER_TEMP_LOW_WARNING
        <Probcause> temperatureUnacceptable
        (51) <Alarmtype> equipmentAlarm
        (5) <Polarity> (2)
        "
	::= { rm10010AlmlineNetworkLaneAlarmWarning1Entry 7 }


rm10010AlmLineLaserTempLowAlarmPortn OBJECT-TYPE
	SYNTAX  EkiOnOff
	MAX-ACCESS read-only
	STATUS current
	DESCRIPTION
        "
        Line Trscv Tx Laser Temp Low Alarm
        :This OID indicates that the Trscv
        Tx Laser Temperature is lower than
        the threshold value written in
         the Trscv EEPROM <Help> Alarm
         indicating that the Trscv Tx Laser
        Temperature is lower than the threshold
        value written in the Trscv EEPROM
        <Condtype> LINE_LASER_TEMP_LOW_ALARM
        <Probcause> temperatureUnacceptable
        (51) <Alarmtype> equipmentAlarm
        (5) <Polarity> (2)
        "
	::= { rm10010AlmlineNetworkLaneAlarmWarning1Entry 6 }


rm10010AlmLineRxPowerHighAlarmPortn OBJECT-TYPE
	SYNTAX  EkiOnOff
	MAX-ACCESS read-only
	STATUS current
	DESCRIPTION
        "
        Line Trscv Rx Power High Alarm
        :This OID indicates that the Trscv
        input power is higher than the
         threshold value written in the
        Trscv EEPROM <Help> Alarm indicating
        that the Trscv input power is higher
        than the threshold value written
        in the Trscv EEPROM <Condtype>
         LINE_RX_POWER_HIGH_ALARM <Probcause>
        receiveFailure (41) <Alarmtype>
        equipmentAlarm (5) <Polarity> (2)
        "
	::= { rm10010AlmlineNetworkLaneAlarmWarning1Entry 5 }


rm10010AlmLineRxPowerHighWarningPortn OBJECT-TYPE
	SYNTAX  EkiOnOff
	MAX-ACCESS read-only
	STATUS current
	DESCRIPTION
        "
        Line Trscv Rx Power High Warning
        :This OID indicates that the Trscv
        input power is higher than the
         threshold value written in the
        Trscv EEPROM <Help> Warning indicating
        that the Trscv input power is higher
        than the threshold value written
        in the Trscv EEPROM <Condtype>
         LINE_RX_POWER_HIGH_WARNING <Probcause>
        receiveFailure (41) <Alarmtype>
        equipmentAlarm (5) <Polarity> (2)
        "
	::= { rm10010AlmlineNetworkLaneAlarmWarning1Entry 4 }


rm10010AlmLineRxPowerLowWarningPortn OBJECT-TYPE
	SYNTAX  EkiOnOff
	MAX-ACCESS read-only
	STATUS current
	DESCRIPTION
        "
        Line Trscv Rx Power Low Warning
        :This OID indicates that the Trscv
        input power is lower than the threshold
        value written in the Trscv EEPROM
        <Help> Warning indicating that
         the Trscv input power is lower
        than the threshold value written
        in the Trscv EEPROM <Condtype>
         LINE_RX_POWER_LOW_WARNING <Probcause>
        receiveFailure (41) <Alarmtype>
        equipmentAlarm (5) <Polarity> (2)
        "
	::= { rm10010AlmlineNetworkLaneAlarmWarning1Entry 3 }


rm10010AlmLineRxPowerLowAlarmPortn OBJECT-TYPE
	SYNTAX  EkiOnOff
	MAX-ACCESS read-only
	STATUS current
	DESCRIPTION
        "
        Line Trscv Rx Power Low Alarm
         :This OID indicates that the Trscv
        input power is lower than the threshold
        value written in the Trscv EEPROM
        <Help> Alarm indicating that the
        Trscv input power is lower than
        the threshold value written in
         the Trscv EEPROM <Condtype> LINE_RX_POWER_LOW_ALARM
        <Probcause> receiveFailure (41)
        <Alarmtype> equipmentAlarm (5)
         <Polarity> (2)
        "
	::= { rm10010AlmlineNetworkLaneAlarmWarning1Entry 2 }


--- *********************************************************
---     TABLE for the rm10010AlmlineNetworkLaneAlarmWarning2 articles
--- *********************************************************

rm10010AlmlineNetworkLaneAlarmWarning2Table OBJECT-TYPE
	SYNTAX  SEQUENCE OF Rm10010AlmlineNetworkLaneAlarmWarning2Entry
	MAX-ACCESS not-accessible
	STATUS current
	DESCRIPTION
        "
        List of rm10010AlmlineNetworkLaneAlarmWarning2
        Article
        "
	::= { rm10010AlmLineNurg 120 }


rm10010AlmlineNetworkLaneAlarmWarning2Entry OBJECT-TYPE
	SYNTAX Rm10010AlmlineNetworkLaneAlarmWarning2Entry
	MAX-ACCESS not-accessible
	STATUS current
	DESCRIPTION
        "
        Row definition for the rm10010AlmlineNetworkLaneAlarmWarning2
        table
        "
	INDEX   { rm10010AlmlineNetworkLaneAlarmWarning2Index }
	::= { rm10010AlmlineNetworkLaneAlarmWarning2Table 1 }


Rm10010AlmlineNetworkLaneAlarmWarning2Entry ::=
	SEQUENCE {
	rm10010AlmlineNetworkLaneAlarmWarning2Index
		INTEGER,
	rm10010AlmRxLaserBiasHighAlarmPortn
		EkiOnOff,
	rm10010AlmRxLaserBiasHighWarningPortn
		EkiOnOff,
	rm10010AlmRxLaserBiasLowWarningPortn
		EkiOnOff,
	rm10010AlmRxLaserBiasLowAlarmPortn
		EkiOnOff,
	rm10010AlmRxLaserOutputHighAlarmPortn
		EkiOnOff,
	rm10010AlmRxLaserOutputHighWarningPortn
		EkiOnOff,
	rm10010AlmRxLaserOutputLowWarningPortn
		EkiOnOff,
	rm10010AlmRxLaserOutputLowAlarmPortn
		EkiOnOff,
	rm10010AlmRxLaserTempHighAlarmPortn
		EkiOnOff,
	rm10010AlmRxLaserTempHighWarningPortn
		EkiOnOff,
	rm10010AlmRxLaserTempLowWarningPortn
		EkiOnOff,
	rm10010AlmRxLaserTempLowAlarmPortn
		EkiOnOff,
	rm10010AlmTxModulatorBiasHighAlarmPortn
		EkiOnOff,
	rm10010AlmTxModulatorBiasHighWarningPortn
		EkiOnOff,
	rm10010AlmTxModulatorBiasLowWarningPortn
		EkiOnOff,
	rm10010AlmTxModulatorBiasLowAlarmPortn
		EkiOnOff
	}


rm10010AlmlineNetworkLaneAlarmWarning2Index OBJECT-TYPE
	SYNTAX  INTEGER(0..128)
	MAX-ACCESS  read-only
	STATUS current
	DESCRIPTION
        "
        Index definition for the rm10010AlmlineNetworkLaneAlarmWarning2
        table
        "
	::= { rm10010AlmlineNetworkLaneAlarmWarning2Entry 1 }


rm10010AlmRxLaserBiasHighAlarmPortn OBJECT-TYPE
	SYNTAX  EkiOnOff
	MAX-ACCESS read-only
	STATUS current
	DESCRIPTION
        "
        Line Trscv Rx Bias High Alarm
         :This OID indicates that the Trscv
        Rx laser bias current is higher
        than the threshold value written
        in the Trscv EEPROM <Help> Alarm
        indicating that the Trscv Rx laser
        bias current is higher than the
        threshold value written in the
         Trscv EEPROM <Condtype> RX_LASER_BIAS_HIGH_ALARM
        <Probcause> receiveFailure (41)
        <Alarmtype> equipmentAlarm (5)
         <Polarity> (2)
        "
	::= { rm10010AlmlineNetworkLaneAlarmWarning2Entry 17 }


rm10010AlmRxLaserBiasHighWarningPortn OBJECT-TYPE
	SYNTAX  EkiOnOff
	MAX-ACCESS read-only
	STATUS current
	DESCRIPTION
        "
        Line Trscv Rx Bias High Warning
        :This OID indicates that the Trscv
        Rx laser bias current is higher
        than the threshold value written
        in the Trscv EEPROM <Help> Warning
        indicating that the Trscv Rx laser
        bias current is higher than the
        threshold value written in the
         Trscv EEPROM <Condtype> RX_LASER_BIAS_HIGH_WARNING
        <Probcause> receiveFailure (41)
        <Alarmtype> equipmentAlarm (5)
         <Polarity> (2)
        "
	::= { rm10010AlmlineNetworkLaneAlarmWarning2Entry 16 }


rm10010AlmRxLaserBiasLowWarningPortn OBJECT-TYPE
	SYNTAX  EkiOnOff
	MAX-ACCESS read-only
	STATUS current
	DESCRIPTION
        "
        Line Trscv Rx Bias Low Warning
        :This OID indicates that the Trscv
        Rx laser bias current is lower
         than the threshold value written
        in the Trscv EEPROM <Help> Warning
        indicating that the Trscv Rx laser
        bias current is lower than the
         threshold value written in the
        Trscv EEPROM <Condtype> RX_LASER_BIAS_LOW_WARNING
        <Probcause> receiveFailure (41)
        <Alarmtype> equipmentAlarm (5)
         <Polarity> (2)
        "
	::= { rm10010AlmlineNetworkLaneAlarmWarning2Entry 15 }


rm10010AlmRxLaserBiasLowAlarmPortn OBJECT-TYPE
	SYNTAX  EkiOnOff
	MAX-ACCESS read-only
	STATUS current
	DESCRIPTION
        "
        Line Trscv Rx Bias Low Alarm :This
        OID indicates that the Trscv Rx
        laser bias current is lower than
        the threshold value written in
         the Trscv EEPROM <Help> Alarm
         indicating that the Trscv Rx laser
        bias current is lower than the
         threshold value written in the
        Trscv EEPROM <Condtype> RX_LASER_BIAS_LOW_ALARM
        <Probcause> receiveFailure (41)
        <Alarmtype> equipmentAlarm (5)
         <Polarity> (2)
        "
	::= { rm10010AlmlineNetworkLaneAlarmWarning2Entry 14 }


rm10010AlmRxLaserOutputHighAlarmPortn OBJECT-TYPE
	SYNTAX  EkiOnOff
	MAX-ACCESS read-only
	STATUS current
	DESCRIPTION
        "
        Line Trscv Rx Output Power High
        Alarm :This OID indicates that
         the Trscv Rx output power is higher
        than the threshold value written
        in the Trscv EEPROM <Help> Alarm
        indicating that the Trscv Rx output
        power is higher than the threshold
        value written in the Trscv EEPROM
        <Condtype> RX_LASER_OUTPUT_HIGH_ALARM
        <Probcause> receiveFailure (41)
        <Alarmtype> equipmentAlarm (5)
         <Polarity> (2)
        "
	::= { rm10010AlmlineNetworkLaneAlarmWarning2Entry 13 }


rm10010AlmRxLaserOutputHighWarningPortn OBJECT-TYPE
	SYNTAX  EkiOnOff
	MAX-ACCESS read-only
	STATUS current
	DESCRIPTION
        "
        Line Trscv Rx Output Power High
        Warning :This OID indicates that
        the Trscv Rx output power is higher
        than the threshold value written
        in the Trscv EEPROM <Help> Warning
        indicating that the Trscv Rx output
        power is higher than the threshold
        value written in the Trscv EEPROM
        <Condtype> RX_LASER_OUTPUT_HIGH_WARNING
        <Probcause> receiveFailure (41)
        <Alarmtype> equipmentAlarm (5)
         <Polarity> (2)
        "
	::= { rm10010AlmlineNetworkLaneAlarmWarning2Entry 12 }


rm10010AlmRxLaserOutputLowWarningPortn OBJECT-TYPE
	SYNTAX  EkiOnOff
	MAX-ACCESS read-only
	STATUS current
	DESCRIPTION
        "
        Line Trscv Rx Output Power Low
        Warning :This OID indicates that
        the Trscv Rx output power is lower
        than the threshold value written
        in the Trscv EEPROM <Help> Warning
        indicating that the Trscv Rx output
        power is lower than the threshold
        value written in the Trscv EEPROM
        <Condtype> RX_LASER_OUTPUT_LOW_WARNING
        <Probcause> receiveFailure (41)
        <Alarmtype> equipmentAlarm (5)
         <Polarity> (2)
        "
	::= { rm10010AlmlineNetworkLaneAlarmWarning2Entry 11 }


rm10010AlmRxLaserOutputLowAlarmPortn OBJECT-TYPE
	SYNTAX  EkiOnOff
	MAX-ACCESS read-only
	STATUS current
	DESCRIPTION
        "
        Line Trscv Rx Output Power Low
        Alarm :This OID indicates that
         the Trscv Rx output power is lower
        than the threshold value written
        in the Trscv EEPROM <Help> Alarm
        indicating that the Trscv Rx output
        power is lower than the threshold
        value written in the Trscv EEPROM
        <Condtype> RX_LASER_OUTPUT_LOW_ALARM
        <Probcause> receiveFailure (41)
        <Alarmtype> equipmentAlarm (5)
         <Polarity> (2)
        "
	::= { rm10010AlmlineNetworkLaneAlarmWarning2Entry 10 }


rm10010AlmRxLaserTempHighAlarmPortn OBJECT-TYPE
	SYNTAX  EkiOnOff
	MAX-ACCESS read-only
	STATUS current
	DESCRIPTION
        "
        Line Trscv Rx Laser Temp High
         Alarm :This OID indicates that
        the Trscv Rx Laser Temperature
         is higher than the threshold value
        written in the Trscv EEPROM <Help>
        Alarm indicating that the Trscv
        Rx Laser Temperature is higher
         than the threshold value written
        in the Trscv EEPROM <Condtype>
         RX_LASER_TEMP_HIGH_ALARM <Probcause>
        temperatureUnacceptable (51) <Alarmtype>
        equipmentAlarm (5) <Polarity> (2)
        "
	::= { rm10010AlmlineNetworkLaneAlarmWarning2Entry 9 }


rm10010AlmRxLaserTempHighWarningPortn OBJECT-TYPE
	SYNTAX  EkiOnOff
	MAX-ACCESS read-only
	STATUS current
	DESCRIPTION
        "
        Line Trscv Rx Laser Temp High
         Warning :This OID indicates that
        the Trscv Rx Laser Temperature
         is higher than the threshold value
        written in the Trscv EEPROM <Help>
        Warning indicating that the Trscv
        Rx Laser Temperature is higher
         than the threshold value written
        in the Trscv EEPROM <Condtype>
         RX_LASER_TEMP_HIGH_WARNING <Probcause>
        temperatureUnacceptable (51) <Alarmtype>
        equipmentAlarm (5) <Polarity> (2)
        "
	::= { rm10010AlmlineNetworkLaneAlarmWarning2Entry 8 }


rm10010AlmRxLaserTempLowWarningPortn OBJECT-TYPE
	SYNTAX  EkiOnOff
	MAX-ACCESS read-only
	STATUS current
	DESCRIPTION
        "
        Line Trscv Rx Laser Temp Low Warning
        :This OID indicates that the Trscv
        Rx Laser Temperature is lower than
        the threshold value written in
         the Trscv EEPROM <Help> Warning
        indicating that the Trscv Rx Laser
        Temperature is lower than the threshold
        value written in the Trscv EEPROM
        <Condtype> RX_LASER_TEMP_LOW_WARNING
        <Probcause> temperatureUnacceptable
        (51) <Alarmtype> equipmentAlarm
        (5) <Polarity> (2)
        "
	::= { rm10010AlmlineNetworkLaneAlarmWarning2Entry 7 }


rm10010AlmRxLaserTempLowAlarmPortn OBJECT-TYPE
	SYNTAX  EkiOnOff
	MAX-ACCESS read-only
	STATUS current
	DESCRIPTION
        "
        Line Trscv Rx Laser Temp Low Alarm
        :This OID indicates that the Trscv
        Rx Laser Temperature is lower than
        the threshold value written in
         the Trscv EEPROM <Help> Alarm
         indicating that the Trscv Rx Laser
        Temperature is lower than the threshold
        value written in the Trscv EEPROM
        <Condtype> RX_LASER_TEMP_LOW_ALARM
        <Probcause> temperatureUnacceptable
        (51) <Alarmtype> equipmentAlarm
        (5) <Polarity> (2)
        "
	::= { rm10010AlmlineNetworkLaneAlarmWarning2Entry 6 }


rm10010AlmTxModulatorBiasHighAlarmPortn OBJECT-TYPE
	SYNTAX  EkiOnOff
	MAX-ACCESS read-only
	STATUS current
	DESCRIPTION
        "
        Line Trscv Tx Modulator Bias High
        Alarm :This OID indicates that
         the Trscv Tx modulator bias current
        is higher than the threshold value
        written in the Trscv EEPROM <Help>
        Alarm indicating that the Trscv
        Tx modulator bias current is higher
        than the threshold value written
        in the Trscv EEPROM <Condtype>
         TX_MODULATOR_BIAS_HIGH_ALARM <Probcause>
        transmitterFailure (56) <Alarmtype>
        equipmentAlarm (5) <Polarity> (2)
        "
	::= { rm10010AlmlineNetworkLaneAlarmWarning2Entry 5 }


rm10010AlmTxModulatorBiasHighWarningPortn OBJECT-TYPE
	SYNTAX  EkiOnOff
	MAX-ACCESS read-only
	STATUS current
	DESCRIPTION
        "
        Line Trscv Tx Modulator Bias High
        Warning :This OID indicates that
        the Trscv Tx modulator bias current
        is higher than the threshold value
        written in the Trscv EEPROM <Help>
        Warning indicating that the Trscv
        Tx modulator bias current is higher
        than the threshold value written
        in the Trscv EEPROM <Condtype>
         TX_MODULATOR_BIAS_HIGH_WARNING
        <Probcause> transmitterFailure
         (56) <Alarmtype> equipmentAlarm
        (5) <Polarity> (2)
        "
	::= { rm10010AlmlineNetworkLaneAlarmWarning2Entry 4 }


rm10010AlmTxModulatorBiasLowWarningPortn OBJECT-TYPE
	SYNTAX  EkiOnOff
	MAX-ACCESS read-only
	STATUS current
	DESCRIPTION
        "
        Line Trscv Tx Modulator Bias Low
        Warning :This OID indicates that
        the Trscv Tx modulator bias current
        is lower than the threshold value
        written in the Trscv EEPROM <Help>
        Warning indicating that the Trscv
        Tx modulator bias current is lower
        than the threshold value written
        in the Trscv EEPROM <Condtype>
         TX_MODULATOR_BIAS_LOW_WARNING
         <Probcause> transmitterFailure
        (56) <Alarmtype> equipmentAlarm
        (5) <Polarity> (2)
        "
	::= { rm10010AlmlineNetworkLaneAlarmWarning2Entry 3 }


rm10010AlmTxModulatorBiasLowAlarmPortn OBJECT-TYPE
	SYNTAX  EkiOnOff
	MAX-ACCESS read-only
	STATUS current
	DESCRIPTION
        "
        Line Trscv Tx Modulator Bias Low
        Alarm :This OID indicates that
         the Trscv Tx modulator bias current
        is lower than the threshold value
        written in the Trscv EEPROM <Help>
        Alarm indicating that the Trscv
        Tx modulator bias current is lower
        than the threshold value written
        in the Trscv EEPROM <Condtype>
         TX_MODULATOR_BIAS_LOW_ALARM <Probcause>
        transmitterFailure (56) <Alarmtype>
        equipmentAlarm (5) <Polarity> (2)
        "
	::= { rm10010AlmlineNetworkLaneAlarmWarning2Entry 2 }


--- *********************************************************
---     TABLE for the rm10010AlmlineNetworkLaneFault articles
--- *********************************************************

rm10010AlmlineNetworkLaneFaultTable OBJECT-TYPE
	SYNTAX  SEQUENCE OF Rm10010AlmlineNetworkLaneFaultEntry
	MAX-ACCESS not-accessible
	STATUS current
	DESCRIPTION
        "
        List of rm10010AlmlineNetworkLaneFault
        Article
        "
	::= { rm10010AlmLineUrg 136 }


rm10010AlmlineNetworkLaneFaultEntry OBJECT-TYPE
	SYNTAX Rm10010AlmlineNetworkLaneFaultEntry
	MAX-ACCESS not-accessible
	STATUS current
	DESCRIPTION
        "
        Row definition for the rm10010AlmlineNetworkLaneFault
        table
        "
	INDEX   { rm10010AlmlineNetworkLaneFaultIndex }
	::= { rm10010AlmlineNetworkLaneFaultTable 1 }


Rm10010AlmlineNetworkLaneFaultEntry ::=
	SEQUENCE {
	rm10010AlmlineNetworkLaneFaultIndex
		INTEGER,
	rm10010AlmLineLaneTecFaultPortn
		EkiOnOff,
	rm10010AlmLineLaneWavelengthUnlockedPortn
		EkiOnOff,
	rm10010AlmLineLaneApdPowerSupplyPortn
		EkiOnOff,
	rm10010AlmLineLaneTxLosfPortn
		EkiOnOff,
	rm10010AlmLineLaneTxLolPortn
		EkiOnOff,
	rm10010AlmLineLaneRxLosPortn
		EkiOnOff,
	rm10010AlmLineLaneRxLolPortn
		EkiOnOff,
	rm10010AlmLineLaneRxFifoErrorPortn
		EkiOnOff,
	rm10010AlmLineLaneRxTecFaultPortn
		EkiOnOff
	}


rm10010AlmlineNetworkLaneFaultIndex OBJECT-TYPE
	SYNTAX  INTEGER(0..128)
	MAX-ACCESS  read-only
	STATUS current
	DESCRIPTION
        "
        Index definition for the rm10010AlmlineNetworkLaneFault
        table
        "
	::= { rm10010AlmlineNetworkLaneFaultEntry 1 }


rm10010AlmLineLaneTecFaultPortn OBJECT-TYPE
	SYNTAX  EkiOnOff
	MAX-ACCESS read-only
	STATUS current
	DESCRIPTION
        "
        Line Network Lane TEC Fault :This
        OID indicates a Tx TEC Fault on
        the Line Trscv Network Lane <Help>
        Alarm indicating a Tx TEC Fault
        on the Line Trscv Network Lane
         <Condtype> LINE_LANE_TEC_FAULT
        <Probcause> transmitterFailure
         (56) <Alarmtype> equipmentAlarm
        (5) <Polarity> (2)
        "
	::= { rm10010AlmlineNetworkLaneFaultEntry 17 }


rm10010AlmLineLaneWavelengthUnlockedPortn OBJECT-TYPE
	SYNTAX  EkiOnOff
	MAX-ACCESS read-only
	STATUS current
	DESCRIPTION
        "
        Line Network Lane Wavelength Unlock
        :This OID indicates a Wavelength
        unlock on the Line Trscv Network
        Lane <Help> Alarm indicating a
         Wavelength unlock on the Line
         Trscv Network Lane <Condtype>
         LINE_LANE_WAVELENGTH_UNLOCKED
         <Probcause> transmitterFailure
        (56) <Alarmtype> equipmentAlarm
        (5) <Polarity> (2)
        "
	::= { rm10010AlmlineNetworkLaneFaultEntry 16 }


rm10010AlmLineLaneApdPowerSupplyPortn OBJECT-TYPE
	SYNTAX  EkiOnOff
	MAX-ACCESS read-only
	STATUS current
	DESCRIPTION
        "
        Line Network Lane APD Power Supply
        :This OID indicates an APD Power
        supply failure on the Line Trscv
        Network Lane <Help> Alarm indicating
        an APD Power supply failure on
         the Line Trscv Network Lane <Condtype>
        LINE_LANE_APD_POWER_SUPPLY <Probcause>
        transmitterFailure (56) <Alarmtype>
        equipmentAlarm (5) <Polarity> (2)
        "
	::= { rm10010AlmlineNetworkLaneFaultEntry 15 }


rm10010AlmLineLaneTxLosfPortn OBJECT-TYPE
	SYNTAX  EkiOnOff
	MAX-ACCESS read-only
	STATUS current
	DESCRIPTION
        "
        Line Network Lane Tx Loss Of Signal
        Functionality :This OID indicates
        a Tx Loss of Signal Functionality
        on the Line Trscv Network Lane
         <Help> Alarm indicating a Tx Loss
        of Signal Functionality on the
         Line Trscv Network Lane <Condtype>
        LINE_LANE_TX_LOSF <Probcause> transmitterFailure
        (56) <Alarmtype> equipmentAlarm
        (5) <Polarity> (2)
        "
	::= { rm10010AlmlineNetworkLaneFaultEntry 9 }


rm10010AlmLineLaneTxLolPortn OBJECT-TYPE
	SYNTAX  EkiOnOff
	MAX-ACCESS read-only
	STATUS current
	DESCRIPTION
        "
        Line Network Lane Tx Loss Of Lock
        :This OID indicates a Tx Loss of
        Lock on the Line Trscv Network
         Lane <Help> Alarm indicating a
        Tx Loss of Lock on the Line Trscv
        Network Lane <Condtype> LINE_LANE_TX_LOL
        <Probcause> transmitterFailure
         (56) <Alarmtype> equipmentAlarm
        (5) <Polarity> (2)
        "
	::= { rm10010AlmlineNetworkLaneFaultEntry 8 }


rm10010AlmLineLaneRxLosPortn OBJECT-TYPE
	SYNTAX  EkiOnOff
	MAX-ACCESS read-only
	STATUS current
	DESCRIPTION
        "
        Line Network Lane Rx Loss Of Signal
        :This OID indicates a Rx Loss of
        Signal on the Line Trscv Network
        Lane <Help> Alarm indicating a
         Rx Loss of Signal on the Line
         Trscv Network Lane <Condtype>
         LINE_LANE_RX_LOS <Probcause> receiveFailure
        (41) <Alarmtype> physicalViolation
        (9) <Polarity> (2)
        "
	::= { rm10010AlmlineNetworkLaneFaultEntry 6 }


rm10010AlmLineLaneRxLolPortn OBJECT-TYPE
	SYNTAX  EkiOnOff
	MAX-ACCESS read-only
	STATUS current
	DESCRIPTION
        "
        Line Network Lane Rx Loss Of Lock
        :This OID indicates a Rx Loss of
        Lock on the Line Trscv Network
         Lane <Help> Alarm indicating a
        Rx Loss of Lock on the Line Trscv
        Network Lane <Condtype> LINE_LANE_RX_LOL
        <Probcause> receiverFailure (42)
        <Alarmtype> equipmentAlarm (5)
         <Polarity> (2)
        "
	::= { rm10010AlmlineNetworkLaneFaultEntry 5 }


rm10010AlmLineLaneRxFifoErrorPortn OBJECT-TYPE
	SYNTAX  EkiOnOff
	MAX-ACCESS read-only
	STATUS current
	DESCRIPTION
        "
        Line Network Lane Rx FIFO Error
        :This OID indicates a Rx FIFO Error
        on the Line Trscv Network Lane
         <Help> Alarm indicating a Rx FIFO
        Error on the Line Trscv Network
        Lane <Condtype> LINE_LANE_RX_FIFO_ERROR
        <Probcause> receiverFailure (42)
        <Alarmtype> equipmentAlarm (5)
         <Polarity> (2)
        "
	::= { rm10010AlmlineNetworkLaneFaultEntry 4 }


rm10010AlmLineLaneRxTecFaultPortn OBJECT-TYPE
	SYNTAX  EkiOnOff
	MAX-ACCESS read-only
	STATUS current
	DESCRIPTION
        "
        Line Network Lane Rx TEC Fault
        :This OID indicates a Rx TEC Fault
        on the Line Trscv Network Lane
         <Help> Alarm indicating a Rx TEC
        Fault on the Line Trscv Network
        Lane <Condtype> LINE_LANE_RX_TEC_FAULT
        <Probcause> receiverFailure (42)
        <Alarmtype> equipmentAlarm (5)
         <Polarity> (2)
        "
	::= { rm10010AlmlineNetworkLaneFaultEntry 3 }


--- *********************************************************
---     TABLE for the rm10010AlmlineHostLaneFault articles
--- *********************************************************

rm10010AlmlineHostLaneFaultTable OBJECT-TYPE
	SYNTAX  SEQUENCE OF Rm10010AlmlineHostLaneFaultEntry
	MAX-ACCESS not-accessible
	STATUS current
	DESCRIPTION
        "
        List of rm10010AlmlineHostLaneFault
        Article
        "
	::= { rm10010AlmLineUrg 152 }


rm10010AlmlineHostLaneFaultEntry OBJECT-TYPE
	SYNTAX Rm10010AlmlineHostLaneFaultEntry
	MAX-ACCESS not-accessible
	STATUS current
	DESCRIPTION
        "
        Row definition for the rm10010AlmlineHostLaneFault
        table
        "
	INDEX   { rm10010AlmlineHostLaneFaultIndex }
	::= { rm10010AlmlineHostLaneFaultTable 1 }


Rm10010AlmlineHostLaneFaultEntry ::=
	SEQUENCE {
	rm10010AlmlineHostLaneFaultIndex
		INTEGER,
	rm10010AlmLineLaneTxFifoErrorPortn
		EkiOnOff,
	rm10010AlmLineTxHostLolPortn
		EkiOnOff,
	rm10010AlmLineSmIaeDetectedPortn
		EkiOnOff,
	rm10010AlmLineSmIaeInsertedPortn
		EkiOnOff,
	rm10010AlmLineSmBdiDetectedPortn
		EkiOnOff,
	rm10010AlmLineSmBdiInsertedPortn
		EkiOnOff,
	rm10010AlmLineLossOfFramePortn
		EkiOnOff,
	rm10010AlmLineInputLossOfSignalPortn
		EkiOnOff
	}


rm10010AlmlineHostLaneFaultIndex OBJECT-TYPE
	SYNTAX  INTEGER(0..128)
	MAX-ACCESS  read-only
	STATUS current
	DESCRIPTION
        "
        Index definition for the rm10010AlmlineHostLaneFault
        table
        "
	::= { rm10010AlmlineHostLaneFaultEntry 1 }


rm10010AlmLineLaneTxFifoErrorPortn OBJECT-TYPE
	SYNTAX  EkiOnOff
	MAX-ACCESS read-only
	STATUS current
	DESCRIPTION
        "
        Line Host Lane Tx FIFO Error :This
        OID indicates a Tx FIFO Error on
        the Line Trscv Host Lane <Help>
        Alarm indicating a Tx FIFO Error
        on the Line Trscv Host Lane <Condtype>
        LINE_LANE_TX_FIFO_ERROR <Probcause>
        receiverFailure (42) <Alarmtype>
        equipmentAlarm (5) <Polarity> (2)
        "
	::= { rm10010AlmlineHostLaneFaultEntry 11 }


rm10010AlmLineTxHostLolPortn OBJECT-TYPE
	SYNTAX  EkiOnOff
	MAX-ACCESS read-only
	STATUS current
	DESCRIPTION
        "
        Line Host Lane Tx Loss Of Lock
        :This OID indicates a Tx Loss of
        Lock on the Line Trscv Host Lane
        <Help> Alarm indicating a Tx Loss
        of Lock on the Line Trscv Host
         Lane <Condtype> LINE_TX_HOST_LOL
        <Probcause> receiverFailure (42)
        <Alarmtype> equipmentAlarm (5)
         <Polarity> (2)
        "
	::= { rm10010AlmlineHostLaneFaultEntry 10 }


rm10010AlmLineSmIaeDetectedPortn OBJECT-TYPE
	SYNTAX  EkiOnOff
	MAX-ACCESS read-only
	STATUS current
	DESCRIPTION
        "
        Line SM IAE Detected :This OID
        indicates a SM Incoming Alignment
        Error is detected on the incoming
        Line signal <Help> Alarm indicating
        a SM Incoming Alignment Error is
        detected on the incoming Line signal
        <Condtype> LINE_SM_IAE_DETECTED
        <Probcause> receiveFailure (41)
        <Alarmtype> integrityViolation
         (7) <Polarity> (2)
        "
	::= { rm10010AlmlineHostLaneFaultEntry 7 }


rm10010AlmLineSmIaeInsertedPortn OBJECT-TYPE
	SYNTAX  EkiOnOff
	MAX-ACCESS read-only
	STATUS current
	DESCRIPTION
        "
        Line SM IAE Inserted :This OID
        indicates a SM Incoming Alignment
        Error is inserted on the outgoing
        Line signal <Help> Status indicating
        a SM Incoming Alignment Error is
        inserted on the outgoing Line signal
        <Condtype> LINE_SM_IAE_INSERTED
        <Probcause> informationalStatus(1000)
        <Alarmtype> other (1) <Polarity>
        (2)
        "
	::= { rm10010AlmlineHostLaneFaultEntry 6 }


rm10010AlmLineSmBdiDetectedPortn OBJECT-TYPE
	SYNTAX  EkiOnOff
	MAX-ACCESS read-only
	STATUS current
	DESCRIPTION
        "
        Line SM BDI Detected :This OID
        indicates a SM Backward Defect
         Indication is detected on the
         incoming Line signal <Help> Alarm
        indicating a SM Backward Defect
        Indication is detected on the incoming
        Line signal <Condtype> LINE_SM_BDI_DETECTED
        <Probcause> receiveFailure (41)
        <Alarmtype> integrityViolation
         (7) <Polarity> (2)
        "
	::= { rm10010AlmlineHostLaneFaultEntry 5 }


rm10010AlmLineSmBdiInsertedPortn OBJECT-TYPE
	SYNTAX  EkiOnOff
	MAX-ACCESS read-only
	STATUS current
	DESCRIPTION
        "
        Line SM BDI Inserted :This OID
        indicates a SM Backward Defect
         Indication is inserted on the
         outgoing Line signal <Help> Status
        indicating a SM Backward Defect
        Indication is inserted on the outgoing
        Line signal <Condtype> LINE_SM_BDI_INSERTED
        <Probcause> informationalStatus(1000)
        <Alarmtype> other (1) <Polarity>
        (2)
        "
	::= { rm10010AlmlineHostLaneFaultEntry 4 }


rm10010AlmLineLossOfFramePortn OBJECT-TYPE
	SYNTAX  EkiOnOff
	MAX-ACCESS read-only
	STATUS current
	DESCRIPTION
        "
        Line Loss Of Frame :This OID indicates
        the module is not aligned with
         the incoming Line signal <Help>
        Alarm indicating the module is
         not aligned with the incoming
         Line signal <Condtype> LINE_LOSS_OF_FRAME
        <Probcause> receiveFailure (41)
        <Alarmtype> integrityViolation
         (7) <Polarity> (2)
        "
	::= { rm10010AlmlineHostLaneFaultEntry 3 }


rm10010AlmLineInputLossOfSignalPortn OBJECT-TYPE
	SYNTAX  EkiOnOff
	MAX-ACCESS read-only
	STATUS current
	DESCRIPTION
        "
        Line Input Loss Of Signal :This
        OID indicates a Loss of Signal
         is detected on the Line Trscv
         <Help> Alarm indicating a Loss
        of Signal is detected on the Line
        Trscv <Condtype> LINE_INPUT_LOSS_OF_SIGNAL
        <Probcause> receiveFailure (41)
        <Alarmtype> physicalViolation (9)
        <Polarity> (2)
        "
	::= { rm10010AlmlineHostLaneFaultEntry 2 }


--- *********************************************************
---     TABLE for the rm10010AlmlineNetworkLaneRxOtn articles
--- *********************************************************

rm10010AlmlineNetworkLaneRxOtnTable OBJECT-TYPE
	SYNTAX  SEQUENCE OF Rm10010AlmlineNetworkLaneRxOtnEntry
	MAX-ACCESS not-accessible
	STATUS current
	DESCRIPTION
        "
        List of rm10010AlmlineNetworkLaneRxOtn
        Article
        "
	::= { rm10010AlmLineUrg 168 }


rm10010AlmlineNetworkLaneRxOtnEntry OBJECT-TYPE
	SYNTAX Rm10010AlmlineNetworkLaneRxOtnEntry
	MAX-ACCESS not-accessible
	STATUS current
	DESCRIPTION
        "
        Row definition for the rm10010AlmlineNetworkLaneRxOtn
        table
        "
	INDEX   { rm10010AlmlineNetworkLaneRxOtnIndex }
	::= { rm10010AlmlineNetworkLaneRxOtnTable 1 }


Rm10010AlmlineNetworkLaneRxOtnEntry ::=
	SEQUENCE {
	rm10010AlmlineNetworkLaneRxOtnIndex
		INTEGER,
	rm10010AlmLineRxOtnLofPortn
		EkiOnOff,
	rm10010AlmLineRxOtnOofPortn
		EkiOnOff,
	rm10010AlmLineRxOtnLomPortn
		EkiOnOff,
	rm10010AlmLineRxOtnOomPortn
		EkiOnOff,
	rm10010AlmLineRxOtnIaePortn
		EkiOnOff,
	rm10010AlmLineRxSmBdiPortn
		EkiOnOff,
	rm10010AlmLineRxOtnOtuAisPortn
		EkiOnOff,
	rm10010AlmLineRxOtnOduAisPortn
		EkiOnOff
	}


rm10010AlmlineNetworkLaneRxOtnIndex OBJECT-TYPE
	SYNTAX  INTEGER(0..128)
	MAX-ACCESS  read-only
	STATUS current
	DESCRIPTION
        "
        Index definition for the rm10010AlmlineNetworkLaneRxOtn
        table
        "
	::= { rm10010AlmlineNetworkLaneRxOtnEntry 1 }


rm10010AlmLineRxOtnLofPortn OBJECT-TYPE
	SYNTAX  EkiOnOff
	MAX-ACCESS read-only
	STATUS current
	DESCRIPTION
        "
        Line Network Rx LOF :This OID
         indicates a Loss of Frame is detected
        on the Rx Network interface of
         the Line Trscv <Help> Alarm indicating
        a Loss of Frame is detected on
         the Rx Network interface of the
        Line Trscv <Condtype> LINE_RX_OTN_LOF
        <Probcause> receiveFailure (41)
        <Alarmtype> equipmentAlarm (5)
         <Polarity> (2)
        "
	::= { rm10010AlmlineNetworkLaneRxOtnEntry 17 }


rm10010AlmLineRxOtnOofPortn OBJECT-TYPE
	SYNTAX  EkiOnOff
	MAX-ACCESS read-only
	STATUS current
	DESCRIPTION
        "
        Line Network Rx OOF :This OID
         indicates an Out of Frame is detected
        on the Rx Network interface of
         the Line Trscv <Help> Alarm indicating
        an Out of Frame is detected on
         the Rx Network interface of the
        Line Trscv <Condtype> LINE_RX_OTN_OOF
        <Probcause> receiveFailure (41)
        <Alarmtype> equipmentAlarm (5)
         <Polarity> (2)
        "
	::= { rm10010AlmlineNetworkLaneRxOtnEntry 16 }


rm10010AlmLineRxOtnLomPortn OBJECT-TYPE
	SYNTAX  EkiOnOff
	MAX-ACCESS read-only
	STATUS current
	DESCRIPTION
        "
        Line Network Rx LOM :This OID
         indicates a Loss of Multiframe
        is detected on the Rx Network interface
        of the Line Trscv <Help> Alarm
         indicating a Loss of Multiframe
        is detected on the Rx Network interface
        of the Line Trscv <Condtype> LINE_RX_OTN_LOM
        <Probcause> receiveFailure (41)
        <Alarmtype> equipmentAlarm (5)
         <Polarity> (2)
        "
	::= { rm10010AlmlineNetworkLaneRxOtnEntry 15 }


rm10010AlmLineRxOtnOomPortn OBJECT-TYPE
	SYNTAX  EkiOnOff
	MAX-ACCESS read-only
	STATUS current
	DESCRIPTION
        "
        Line Network Rx OOM :This OID
         indicates an Out of Multiframe
        is detected on the Rx Network interface
        of the Line Trscv <Help> Alarm
         indicating an Out of Multiframe
        is detected on the Rx Network interface
        of the Line Trscv <Condtype> LINE_RX_OTN_OOM
        <Probcause> receiveFailure (41)
        <Alarmtype> equipmentAlarm (5)
         <Polarity> (2)
        "
	::= { rm10010AlmlineNetworkLaneRxOtnEntry 14 }


rm10010AlmLineRxOtnIaePortn OBJECT-TYPE
	SYNTAX  EkiOnOff
	MAX-ACCESS read-only
	STATUS current
	DESCRIPTION
        "
        Line Network Rx IAE :This OID
         indicates an Incoming Alignment
        Error is detected on the Rx Network
        interface of the Line Trscv <Help>
        Alarm indicating an Incoming Alignment
        Error is detected on the Rx Network
        interface of the Line Trscv <Condtype>
        LINE_RX_OTN_IAE <Probcause> receiveFailure
        (41) <Alarmtype> equipmentAlarm
        (5) <Polarity> (2)
        "
	::= { rm10010AlmlineNetworkLaneRxOtnEntry 13 }


rm10010AlmLineRxSmBdiPortn OBJECT-TYPE
	SYNTAX  EkiOnOff
	MAX-ACCESS read-only
	STATUS current
	DESCRIPTION
        "
        Line Network Rx SM BDI :This OID
        indicates an SM Backward Defect
        Indication is detected on the Rx
        Network interface of the Line Trscv
        <Help> Alarm indicating an SM Backward
        Defect Indication is detected on
        the Rx Network interface of the
        Line Trscv <Condtype> LINE_RX_SM_BDI
        <Probcause> informationalStatus(1000)
        <Alarmtype> other (1) <Polarity>
        (2)
        "
	::= { rm10010AlmlineNetworkLaneRxOtnEntry 12 }


rm10010AlmLineRxOtnOtuAisPortn OBJECT-TYPE
	SYNTAX  EkiOnOff
	MAX-ACCESS read-only
	STATUS current
	DESCRIPTION
        "
        Line Network Rx OTU AIS :This
         OID indicates an OTU This OID
         Indication Signal is detected
         on the Rx Network interface of
        the Line Trscv <Help> Alarm indicating
        an OTU Alarm Indication Signal
         is detected on the Rx Network
         interface of the Line Trscv <Condtype>
        LINE_RX_OTN_OTU_AIS <Probcause>
        receiveFailure (41) <Alarmtype>
        equipmentAlarm (5) <Polarity> (2)
        "
	::= { rm10010AlmlineNetworkLaneRxOtnEntry 11 }


rm10010AlmLineRxOtnOduAisPortn OBJECT-TYPE
	SYNTAX  EkiOnOff
	MAX-ACCESS read-only
	STATUS current
	DESCRIPTION
        "
        Line Network Rx ODU AIS :This
         OID indicates an ODU This OID
         Indication Signal is detected
         on the Rx Network interface of
        the Line Trscv <Help> Alarm indicating
        an ODU Alarm Indication Signal
         is detected on the Rx Network
         interface of the Line Trscv <Condtype>
        LINE_RX_OTN_ODU_AIS <Probcause>
        receiveFailure (41) <Alarmtype>
        equipmentAlarm (5) <Polarity> (2)
        "
	::= { rm10010AlmlineNetworkLaneRxOtnEntry 10 }


--- *********************************************************
---     TABLE for the rm10010AlmlineHostLaneTxOtn articles
--- *********************************************************

rm10010AlmlineHostLaneTxOtnTable OBJECT-TYPE
	SYNTAX  SEQUENCE OF Rm10010AlmlineHostLaneTxOtnEntry
	MAX-ACCESS not-accessible
	STATUS current
	DESCRIPTION
        "
        List of rm10010AlmlineHostLaneTxOtn
        Article
        "
	::= { rm10010AlmLineUrg 184 }


rm10010AlmlineHostLaneTxOtnEntry OBJECT-TYPE
	SYNTAX Rm10010AlmlineHostLaneTxOtnEntry
	MAX-ACCESS not-accessible
	STATUS current
	DESCRIPTION
        "
        Row definition for the rm10010AlmlineHostLaneTxOtn
        table
        "
	INDEX   { rm10010AlmlineHostLaneTxOtnIndex }
	::= { rm10010AlmlineHostLaneTxOtnTable 1 }


Rm10010AlmlineHostLaneTxOtnEntry ::=
	SEQUENCE {
	rm10010AlmlineHostLaneTxOtnIndex
		INTEGER,
	rm10010AlmLineTxOtnLofPortn
		EkiOnOff,
	rm10010AlmLineTxOtnOofPortn
		EkiOnOff,
	rm10010AlmLineTxOtnLomPortn
		EkiOnOff,
	rm10010AlmLineTxOtnOomPortn
		EkiOnOff,
	rm10010AlmLineTxOtnIaePortn
		EkiOnOff,
	rm10010AlmLineTxSmBdiPortn
		EkiOnOff,
	rm10010AlmLineTxOtnOtuAisPortn
		EkiOnOff,
	rm10010AlmLineTxOtnOduAisPortn
		EkiOnOff
	}


rm10010AlmlineHostLaneTxOtnIndex OBJECT-TYPE
	SYNTAX  INTEGER(0..128)
	MAX-ACCESS  read-only
	STATUS current
	DESCRIPTION
        "
        Index definition for the rm10010AlmlineHostLaneTxOtn
        table
        "
	::= { rm10010AlmlineHostLaneTxOtnEntry 1 }


rm10010AlmLineTxOtnLofPortn OBJECT-TYPE
	SYNTAX  EkiOnOff
	MAX-ACCESS read-only
	STATUS current
	DESCRIPTION
        "
        Line Host Tx LOF :This OID indicates
        a Loss of Frame is detected on
         the Tx Host interface of the Line
        Trscv <Help> Alarm indicating a
        Loss of Frame is detected on the
        Tx Host interface of the Line Trscv
        <Condtype> LINE_TX_OTN_LOF <Probcause>
        receiveFailure (41) <Alarmtype>
        equipmentAlarm (5) <Polarity> (2)
        "
	::= { rm10010AlmlineHostLaneTxOtnEntry 17 }


rm10010AlmLineTxOtnOofPortn OBJECT-TYPE
	SYNTAX  EkiOnOff
	MAX-ACCESS read-only
	STATUS current
	DESCRIPTION
        "
        Line Host Tx OOF :This OID indicates
        an Out of Frame is detected on
         the Tx Host interface of the Line
        Trscv <Help> Alarm indicating an
        Out of Frame is detected on the
        Tx Host interface of the Line Trscv
        <Condtype> LINE_TX_OTN_OOF <Probcause>
        receiveFailure (41) <Alarmtype>
        equipmentAlarm (5) <Polarity> (2)
        "
	::= { rm10010AlmlineHostLaneTxOtnEntry 16 }


rm10010AlmLineTxOtnLomPortn OBJECT-TYPE
	SYNTAX  EkiOnOff
	MAX-ACCESS read-only
	STATUS current
	DESCRIPTION
        "
        Line Host Tx LOM :This OID indicates
        a Loss of Multiframe is detected
        on the Tx Host interface of the
        Line Trscv <Help> Alarm indicating
        a Loss of Multiframe is detected
        on the Tx Host interface of the
        Line Trscv <Condtype> LINE_TX_OTN_LOM
        <Probcause> receiveFailure (41)
        <Alarmtype> equipmentAlarm (5)
         <Polarity> (2)
        "
	::= { rm10010AlmlineHostLaneTxOtnEntry 15 }


rm10010AlmLineTxOtnOomPortn OBJECT-TYPE
	SYNTAX  EkiOnOff
	MAX-ACCESS read-only
	STATUS current
	DESCRIPTION
        "
        Line Host Tx OOM :This OID indicates
        an Out of Multiframe is detected
        on the Tx Host interface of the
        Line Trscv <Help> Alarm indicating
        an Out of Multiframe is detected
        on the Tx Host interface of the
        Line Trscv <Condtype> LINE_TX_OTN_OOM
        <Probcause> receiveFailure (41)
        <Alarmtype> equipmentAlarm (5)
         <Polarity> (2)
        "
	::= { rm10010AlmlineHostLaneTxOtnEntry 14 }


rm10010AlmLineTxOtnIaePortn OBJECT-TYPE
	SYNTAX  EkiOnOff
	MAX-ACCESS read-only
	STATUS current
	DESCRIPTION
        "
        Line Host Tx IAE :This OID indicates
        an Incoming Alignment Error is
         detected on the Tx Host interface
        of the Line Trscv <Help> Alarm
         indicating an Incoming Alignment
        Error is detected on the Tx Host
        interface of the Line Trscv <Condtype>
        LINE_TX_OTN_IAE <Probcause> receiveFailure
        (41) <Alarmtype> equipmentAlarm
        (5) <Polarity> (2)
        "
	::= { rm10010AlmlineHostLaneTxOtnEntry 13 }


rm10010AlmLineTxSmBdiPortn OBJECT-TYPE
	SYNTAX  EkiOnOff
	MAX-ACCESS read-only
	STATUS current
	DESCRIPTION
        "
        Line Host Tx SM BDI :This OID
         indicates an SM Backward Defect
        Indication is detected on the Tx
        Host interface of the Line Trscv
        <Help> Alarm indicating an SM Backward
        Defect Indication is detected on
        the Tx Host interface of the Line
        Trscv <Condtype> LINE_TX_SM_BDI
        <Probcause> informationalStatus(1000)
        <Alarmtype> other (1) <Polarity>
        (2)
        "
	::= { rm10010AlmlineHostLaneTxOtnEntry 12 }


rm10010AlmLineTxOtnOtuAisPortn OBJECT-TYPE
	SYNTAX  EkiOnOff
	MAX-ACCESS read-only
	STATUS current
	DESCRIPTION
        "
        Line Host Tx OTU AIS :This OID
        indicates an OTU This OID Indication
        Signal is detected on the Tx Host
        interface of the Line Trscv <Help>
        Alarm indicating an OTU Alarm Indication
        Signal is detected on the Tx Host
        interface of the Line Trscv <Condtype>
        LINE_TX_OTN_OTU_AIS <Probcause>
        receiveFailure (41) <Alarmtype>
        equipmentAlarm (5) <Polarity> (2)
        "
	::= { rm10010AlmlineHostLaneTxOtnEntry 11 }


rm10010AlmLineTxOtnOduAisPortn OBJECT-TYPE
	SYNTAX  EkiOnOff
	MAX-ACCESS read-only
	STATUS current
	DESCRIPTION
        "
        Line Host Tx ODU AIS :This OID
        indicates an ODU This OID Indication
        Signal is detected on the Tx Host
        interface of the Line Trscv <Help>
        Alarm indicating an ODU Alarm Indication
        Signal is detected on the Tx Host
        interface of the Line Trscv <Condtype>
        LINE_TX_OTN_ODU_AIS <Probcause>
        receiveFailure (41) <Alarmtype>
        equipmentAlarm (5) <Polarity> (2)
        "
	::= { rm10010AlmlineHostLaneTxOtnEntry 10 }


--- *********************************************************
---     TABLE for the rm10010AlmclientSfpAlmDdm articles
--- *********************************************************

rm10010AlmclientSfpAlmDdmTable OBJECT-TYPE
	SYNTAX  SEQUENCE OF Rm10010AlmclientSfpAlmDdmEntry
	MAX-ACCESS not-accessible
	STATUS current
	DESCRIPTION
        "
        List of rm10010AlmclientSfpAlmDdm
        Article
        "
	::= { rm10010AlmClientUrg 216 }


rm10010AlmclientSfpAlmDdmEntry OBJECT-TYPE
	SYNTAX Rm10010AlmclientSfpAlmDdmEntry
	MAX-ACCESS not-accessible
	STATUS current
	DESCRIPTION
        "
        Row definition for the rm10010AlmclientSfpAlmDdm
        table
        "
	INDEX   { rm10010AlmclientSfpAlmDdmIndex }
	::= { rm10010AlmclientSfpAlmDdmTable 1 }


Rm10010AlmclientSfpAlmDdmEntry ::=
	SEQUENCE {
	rm10010AlmclientSfpAlmDdmIndex
		INTEGER,
	rm10010AlmRxPwrHighAlaPortn
		EkiOnOff,
	rm10010AlmRxPwrLowAlaPortn
		EkiOnOff,
	rm10010AlmTempHighAlaPortn
		EkiOnOff,
	rm10010AlmTempLowAlaPortn
		EkiOnOff,
	rm10010AlmVccHighAlaPortn
		EkiOnOff,
	rm10010AlmVccLowAlaPortn
		EkiOnOff,
	rm10010AlmTxBiasHighAlaPortn
		EkiOnOff,
	rm10010AlmTxBiasLowAlaPortn
		EkiOnOff,
	rm10010AlmTxPwrHighAlaPortn
		EkiOnOff,
	rm10010AlmTxPwrLowAlaPortn
		EkiOnOff
	}


rm10010AlmclientSfpAlmDdmIndex OBJECT-TYPE
	SYNTAX  INTEGER(0..128)
	MAX-ACCESS  read-only
	STATUS current
	DESCRIPTION
        "
        Index definition for the rm10010AlmclientSfpAlmDdm
        table
        "
	::= { rm10010AlmclientSfpAlmDdmEntry 1 }


rm10010AlmRxPwrHighAlaPortn OBJECT-TYPE
	SYNTAX  EkiOnOff
	MAX-ACCESS read-only
	STATUS current
	DESCRIPTION
        "
        Client Trscv Rx Power High :This
        OID indicates that the Trscv input
        power of port is higher than the
        threshold value written in the
         Trscv EEPROM <Help> Alarm indicating
        that the Trscv input power of port
        is higher than the threshold value
        written in the Trscv EEPROM <Condtype>
        RX_PWR_HIGH_ALA_1 <Probcause> receiveFailure
        (41) <Alarmtype> equipmentAlarm
        (5) <Polarity> (2)
        "
	::= { rm10010AlmclientSfpAlmDdmEntry 17 }


rm10010AlmRxPwrLowAlaPortn OBJECT-TYPE
	SYNTAX  EkiOnOff
	MAX-ACCESS read-only
	STATUS current
	DESCRIPTION
        "
        Client Trscv Rx Power Low :This
        OID indicates that the Trscv input
        power of port is lower than the
        threshold value written in the
         Trscv EEPROM <Help> Alarm indicating
        that the Trscv input power of port
        is lower than the threshold value
        written in the Trscv EEPROM <Condtype>
        RX_PWR_LOW_ALA_1 <Probcause> receiveFailure
        (41) <Alarmtype> equipmentAlarm
        (5) <Polarity> (2)
        "
	::= { rm10010AlmclientSfpAlmDdmEntry 16 }


rm10010AlmTempHighAlaPortn OBJECT-TYPE
	SYNTAX  EkiOnOff
	MAX-ACCESS read-only
	STATUS current
	DESCRIPTION
        "
        Client Trscv Temp High :This OID
        indicates that the Trscv temperature
        of port is higher than the threshold
        value written in the Trscv EEPROM
        <Help> Alarm indicating that the
        Trscv temperature of port is higher
        than the threshold value written
        in the Trscv EEPROM <Condtype>
         TEMP_HIGH_ALA_1 <Probcause> temperatureUnacceptable
        (51) <Alarmtype> equipmentAlarm
        (5) <Polarity> (2)
        "
	::= { rm10010AlmclientSfpAlmDdmEntry 9 }


rm10010AlmTempLowAlaPortn OBJECT-TYPE
	SYNTAX  EkiOnOff
	MAX-ACCESS read-only
	STATUS current
	DESCRIPTION
        "
        Client Trscv Temp Low :This OID
        indicates that the Trscv temperature
        of port is lower than the threshold
        value written in the Trscv EEPROM
        <Help> Alarm indicating that the
        Trscv temperature of port is lower
        than the threshold value written
        in the Trscv EEPROM <Condtype>
         TEMP_LOW_ALA_1 <Probcause> temperatureUnacceptable
        (51) <Alarmtype> equipmentAlarm
        (5) <Polarity> (2)
        "
	::= { rm10010AlmclientSfpAlmDdmEntry 8 }


rm10010AlmVccHighAlaPortn OBJECT-TYPE
	SYNTAX  EkiOnOff
	MAX-ACCESS read-only
	STATUS current
	DESCRIPTION
        "
        Client Trscv Power Supply High
        :This OID indicates that the Trscv
        power supply of port is higher
         than the threshold value written
        in the Trscv EEPROM <Help> Alarm
        indicating that the Trscv power
        supply of port is higher than the
        threshold value written in the
         Trscv EEPROM <Condtype> VCC_HIGH_ALA_1
        <Probcause> powerProblem (36) <Alarmtype>
        equipmentAlarm (5) <Polarity> (2)
        "
	::= { rm10010AlmclientSfpAlmDdmEntry 7 }


rm10010AlmVccLowAlaPortn OBJECT-TYPE
	SYNTAX  EkiOnOff
	MAX-ACCESS read-only
	STATUS current
	DESCRIPTION
        "
        Client Trscv Power Supply Low
         :This OID indicates that the Trscv
        power supply of port is lower than
        the threshold value written in
         the Trscv EEPROM <Help> Alarm
         indicating that the Trscv power
        supply of port is lower than the
        threshold value written in the
         Trscv EEPROM <Condtype> VCC_LOW_ALA_1
        <Probcause> powerProblem (36) <Alarmtype>
        equipmentAlarm (5) <Polarity> (2)
        "
	::= { rm10010AlmclientSfpAlmDdmEntry 6 }


rm10010AlmTxBiasHighAlaPortn OBJECT-TYPE
	SYNTAX  EkiOnOff
	MAX-ACCESS read-only
	STATUS current
	DESCRIPTION
        "
        Client Trscv Bias High :This OID
        indicates that the Trscv laser
         bias current of port is higher
        than the threshold value written
        in the Trscv EEPROM <Help> Alarm
        indicating that the Trscv laser
        bias current of port is higher
         than the threshold value written
        in the Trscv EEPROM <Condtype>
         TX_BIAS_HIGH_ALA_1 <Probcause>
        transmitterFailure (56) <Alarmtype>
        equipmentAlarm (5) <Polarity> (2)
        "
	::= { rm10010AlmclientSfpAlmDdmEntry 5 }


rm10010AlmTxBiasLowAlaPortn OBJECT-TYPE
	SYNTAX  EkiOnOff
	MAX-ACCESS read-only
	STATUS current
	DESCRIPTION
        "
        Client Trscv Bias Low :This OID
        indicates that the Trscv laser
         bias current of port is lower
         than the threshold value written
        in the Trscv EEPROM <Help> Alarm
        indicating that the Trscv laser
        bias current of port is lower than
        the threshold value written in
         the Trscv EEPROM <Condtype> TX_BIAS_LOW_ALA_1
        <Probcause> transmitterFailure
         (56) <Alarmtype> equipmentAlarm
        (5) <Polarity> (2)
        "
	::= { rm10010AlmclientSfpAlmDdmEntry 4 }


rm10010AlmTxPwrHighAlaPortn OBJECT-TYPE
	SYNTAX  EkiOnOff
	MAX-ACCESS read-only
	STATUS current
	DESCRIPTION
        "
        Client Trscv Tx Power High :This
        OID indicates that the Trscv output
        power of port is higher than the
        threshold value written in the
         Trscv EEPROM <Help> Alarm indicating
        that the Trscv output power of
         port is higher than the threshold
        value written in the Trscv EEPROM
        <Condtype> TX_PWR_HIGH_ALA_1 <Probcause>
        transmitterFailure (56) <Alarmtype>
        equipmentAlarm (5) <Polarity> (2)
        "
	::= { rm10010AlmclientSfpAlmDdmEntry 3 }


rm10010AlmTxPwrLowAlaPortn OBJECT-TYPE
	SYNTAX  EkiOnOff
	MAX-ACCESS read-only
	STATUS current
	DESCRIPTION
        "
        Client Trscv Tx Power Low :This
        OID indicates that the Trscv output
        power of port is lower than the
        threshold value written in the
         Trscv EEPROM <Help> Alarm indicating
        that the Trscv output power of
         port is lower than the threshold
        value written in the Trscv EEPROM
        <Condtype> TX_PWR_LOW_ALA_1 <Probcause>
        transmitterFailure (56) <Alarmtype>
        equipmentAlarm (5) <Polarity> (2)
        "
	::= { rm10010AlmclientSfpAlmDdmEntry 2 }


--- *********************************************************
---     TABLE for the rm10010AlmclientSfpWarnDdm articles
--- *********************************************************

rm10010AlmclientSfpWarnDdmTable OBJECT-TYPE
	SYNTAX  SEQUENCE OF Rm10010AlmclientSfpWarnDdmEntry
	MAX-ACCESS not-accessible
	STATUS current
	DESCRIPTION
        "
        List of rm10010AlmclientSfpWarnDdm
        Article
        "
	::= { rm10010AlmClientNurg 232 }


rm10010AlmclientSfpWarnDdmEntry OBJECT-TYPE
	SYNTAX Rm10010AlmclientSfpWarnDdmEntry
	MAX-ACCESS not-accessible
	STATUS current
	DESCRIPTION
        "
        Row definition for the rm10010AlmclientSfpWarnDdm
        table
        "
	INDEX   { rm10010AlmclientSfpWarnDdmIndex }
	::= { rm10010AlmclientSfpWarnDdmTable 1 }


Rm10010AlmclientSfpWarnDdmEntry ::=
	SEQUENCE {
	rm10010AlmclientSfpWarnDdmIndex
		INTEGER,
	rm10010AlmRxPwrHighWngPortn
		EkiOnOff,
	rm10010AlmRxPwrLowWngPortn
		EkiOnOff,
	rm10010AlmTempHighWngPortn
		EkiOnOff,
	rm10010AlmTempLowWngPortn
		EkiOnOff,
	rm10010AlmVccHighWngPortn
		EkiOnOff,
	rm10010AlmVccLowWngPortn
		EkiOnOff,
	rm10010AlmTxBiasHighWngPortn
		EkiOnOff,
	rm10010AlmTxBiasLowWngPortn
		EkiOnOff,
	rm10010AlmTxPwrHighWngPortn
		EkiOnOff,
	rm10010AlmTxPwLowWngPortn
		EkiOnOff
	}


rm10010AlmclientSfpWarnDdmIndex OBJECT-TYPE
	SYNTAX  INTEGER(0..128)
	MAX-ACCESS  read-only
	STATUS current
	DESCRIPTION
        "
        Index definition for the rm10010AlmclientSfpWarnDdm
        table
        "
	::= { rm10010AlmclientSfpWarnDdmEntry 1 }


rm10010AlmRxPwrHighWngPortn OBJECT-TYPE
	SYNTAX  EkiOnOff
	MAX-ACCESS read-only
	STATUS current
	DESCRIPTION
        "
        Client Trscv Rx Power High Warning
        :This OID indicates that the Trscv
        input power is higher than the
         threshold value written in the
        Trscv EEPROM <Help> Warning indicating
        that the Trscv input power is higher
        than the threshold value written
        in the Trscv EEPROM <Condtype>
         RX_PWR_HIGH_WNG_1 <Probcause>
         receiveFailure (41) <Alarmtype>
        equipmentAlarm (5) <Polarity> (2)
        "
	::= { rm10010AlmclientSfpWarnDdmEntry 17 }


rm10010AlmRxPwrLowWngPortn OBJECT-TYPE
	SYNTAX  EkiOnOff
	MAX-ACCESS read-only
	STATUS current
	DESCRIPTION
        "
        Client Trscv Rx Power Low Warning
        :This OID indicates that the Trscv
        input power is lower than the threshold
        value written in the Trscv EEPROM
        <Help> Warning indicating that
         the Trscv input power is lower
        than the threshold value written
        in the Trscv EEPROM <Condtype>
         RX_PWR_LOW_WNG_1 <Probcause> receiveFailure
        (41) <Alarmtype> equipmentAlarm
        (5) <Polarity> (2)
        "
	::= { rm10010AlmclientSfpWarnDdmEntry 16 }


rm10010AlmTempHighWngPortn OBJECT-TYPE
	SYNTAX  EkiOnOff
	MAX-ACCESS read-only
	STATUS current
	DESCRIPTION
        "
        Client Trscv Temp High Warning
        :This OID indicates that the Trscv
        temperature is higher than the
         threshold value written in the
        Trscv EEPROM <Help> Warning indicating
        that the Trscv temperature is higher
        than the threshold value written
        in the Trscv EEPROM <Condtype>
         TEMP_HIGH_WNG_1 <Probcause> temperatureUnacceptable
        (51) <Alarmtype> equipmentAlarm
        (5) <Polarity> (2)
        "
	::= { rm10010AlmclientSfpWarnDdmEntry 9 }


rm10010AlmTempLowWngPortn OBJECT-TYPE
	SYNTAX  EkiOnOff
	MAX-ACCESS read-only
	STATUS current
	DESCRIPTION
        "
        Client Trscv Temp Low Warning
         :This OID indicates that the Trscv
        temperature is lower than the threshold
        value written in the Trscv EEPROM
        <Help> Warning indicating that
         the Trscv temperature is lower
        than the threshold value written
        in the Trscv EEPROM <Condtype>
         TEMP_LOW_WNG_1 <Probcause> temperatureUnacceptable
        (51) <Alarmtype> equipmentAlarm
        (5) <Polarity> (2)
        "
	::= { rm10010AlmclientSfpWarnDdmEntry 8 }


rm10010AlmVccHighWngPortn OBJECT-TYPE
	SYNTAX  EkiOnOff
	MAX-ACCESS read-only
	STATUS current
	DESCRIPTION
        "
        Client Trscv Power Supply High
        Warning :This OID indicates that
        the Trscv power supply is higher
        than the threshold value written
        in the Trscv EEPROM <Help> Warning
        indicating that the Trscv power
        supply is higher than the threshold
        value written in the Trscv EEPROM
        <Condtype> VCC_HIGH_WNG_1 <Probcause>
        powerProblem (36) <Alarmtype> equipmentAlarm
        (5) <Polarity> (2)
        "
	::= { rm10010AlmclientSfpWarnDdmEntry 7 }


rm10010AlmVccLowWngPortn OBJECT-TYPE
	SYNTAX  EkiOnOff
	MAX-ACCESS read-only
	STATUS current
	DESCRIPTION
        "
        Client Trscv Power Supply Low
         Warning :This OID indicates that
        the Trscv power supply is lower
        than the threshold value written
        in the Trscv EEPROM <Help> Warning
        indicating that the Trscv power
        supply is lower than the threshold
        value written in the Trscv EEPROM
        <Condtype> VCC_LOW_WNG_1 <Probcause>
        powerProblem (36) <Alarmtype> equipmentAlarm
        (5) <Polarity> (2)
        "
	::= { rm10010AlmclientSfpWarnDdmEntry 6 }


rm10010AlmTxBiasHighWngPortn OBJECT-TYPE
	SYNTAX  EkiOnOff
	MAX-ACCESS read-only
	STATUS current
	DESCRIPTION
        "
        Client Trscv Bias High Warning
        :This OID indicates that the Trscv
        laser bias current is higher than
        the threshold value written in
         the Trscv EEPROM <Help> Warning
        indicating that the Trscv laser
        bias current is higher than the
        threshold value written in the
         Trscv EEPROM <Condtype> TX_BIAS_HIGH_WNG_1
        <Probcause> transmitterFailure
         (56) <Alarmtype> equipmentAlarm
        (5) <Polarity> (2)
        "
	::= { rm10010AlmclientSfpWarnDdmEntry 5 }


rm10010AlmTxBiasLowWngPortn OBJECT-TYPE
	SYNTAX  EkiOnOff
	MAX-ACCESS read-only
	STATUS current
	DESCRIPTION
        "
        Client Trscv Bias Low Warning
         :This OID indicates that the Trscv
        laser bias current is lower than
        the threshold value written in
         the Trscv EEPROM <Help> Warning
        indicating that the Trscv laser
        bias current is lower than the
         threshold value written in the
        Trscv EEPROM <Condtype> TX_BIAS_LOW_WNG_1
        <Probcause> transmitterFailure
         (56) <Alarmtype> equipmentAlarm
        (5) <Polarity> (2)
        "
	::= { rm10010AlmclientSfpWarnDdmEntry 4 }


rm10010AlmTxPwrHighWngPortn OBJECT-TYPE
	SYNTAX  EkiOnOff
	MAX-ACCESS read-only
	STATUS current
	DESCRIPTION
        "
        Client Trscv Tx Power High Warning
        :This OID indicates that the Trscv
        output power is higher than the
        threshold value written in the
         Trscv EEPROM <Help> Warning indicating
        that the Trscv output power is
         higher than the threshold value
        written in the Trscv EEPROM <Condtype>
        TX_PWR_HIGH_WNG_1 <Probcause> transmitterFailure
        (56) <Alarmtype> equipmentAlarm
        (5) <Polarity> (2)
        "
	::= { rm10010AlmclientSfpWarnDdmEntry 3 }


rm10010AlmTxPwLowWngPortn OBJECT-TYPE
	SYNTAX  EkiOnOff
	MAX-ACCESS read-only
	STATUS current
	DESCRIPTION
        "
        Client Trscv Tx Power Low Warning
        :This OID indicates that the Trscv
        output power is lower than the
         threshold value written in the
        Trscv EEPROM <Help> Warning indicating
        that the Trscv output power is
         lower than the threshold value
        written in the Trscv EEPROM <Condtype>
        TX_PW_LOW_WNG_1 <Probcause> transmitterFailure
        (56) <Alarmtype> equipmentAlarm
        (5) <Polarity> (2)
        "
	::= { rm10010AlmclientSfpWarnDdmEntry 2 }


--- *****************************************************
---     LEAF for the modFanFail article
--- *****************************************************
rm10010AlmmodFanFail OBJECT IDENTIFIER ::= { rm10010AlmOtherUrg 248 }




rm10010AlmFan4Fail OBJECT-TYPE
	  SYNTAX EkiOnOff
	  MAX-ACCESS read-only
	  STATUS current
	  DESCRIPTION
        "
        Fan Unit N°4 Failed On Fan Module
        :This OID indicates a failure on
        fan 4. Removal of the fan unit
         or no rotation sets the OID.
         <Help>  This alarm indicates if
        the FAN n°4 is in fail condition
        <Condtype> FAN4_FAIL <Probcause>
        heatingVentCoolingSystemProblem
        (22) <Alarmtype> equipmentAlarm
        (5) <Polarity> (2)
        "
	  ::= { rm10010AlmmodFanFail 7 }



rm10010AlmFan3Fail OBJECT-TYPE
	  SYNTAX EkiOnOff
	  MAX-ACCESS read-only
	  STATUS current
	  DESCRIPTION
        "
        Fan Unit N°3 Failed On Fan Module
        :This OID indicates a failure on
        fan 3. Removal of the fan unit
         or no rotation sets the OID.
         <Help>  This alarm indicates if
        the FAN n°3 is in fail condition
        <Condtype> FAN3_FAIL <Probcause>
        heatingVentCoolingSystemProblem
        (22) <Alarmtype> equipmentAlarm
        (5) <Polarity> (2)
        "
	  ::= { rm10010AlmmodFanFail 6 }



rm10010AlmFan2Fail OBJECT-TYPE
	  SYNTAX EkiOnOff
	  MAX-ACCESS read-only
	  STATUS current
	  DESCRIPTION
        "
        Fan Unit N°2 Failed On Fan Module
        :This OID indicates a failure on
        fan 2. Removal of the fan unit
         or no rotation sets the OID.
         <Help>  This alarm indicates if
        the FAN n°2 is in fail condition
        <Condtype> FAN2_FAIL <Probcause>
        heatingVentCoolingSystemProblem
        (22) <Alarmtype> equipmentAlarm
        (5) <Polarity> (2)
        "
	  ::= { rm10010AlmmodFanFail 5 }



rm10010AlmFan1Fail OBJECT-TYPE
	  SYNTAX EkiOnOff
	  MAX-ACCESS read-only
	  STATUS current
	  DESCRIPTION
        "
        Fan Unit N°1 Failed On Fan Module
        :This OID indicates a failure on
        fan 1. Removal of the fan unit
         or no rotation sets the OID.
         <Help>  This alarm indicates if
        the FAN n°1 is in fail condition
        <Condtype> FAN1_FAIL <Probcause>
        heatingVentCoolingSystemProblem
        (22) <Alarmtype> equipmentAlarm
        (5) <Polarity> (2)
        "
	  ::= { rm10010AlmmodFanFail 4 }



rm10010AlmFansFail OBJECT-TYPE
	  SYNTAX EkiOnOff
	  MAX-ACCESS read-only
	  STATUS current
	  DESCRIPTION
        "
        Fan Module Failure :This OID indicates
        that at least one of the 4 FAN
         unit of the FAN module is in fail
        condition  <Help>  This alarm indicates
        if one the FANs is in a fail condition.
        <Condtype> FANS_FAIL <Probcause>
        heatingVentCoolingSystemProblem
        (22) <Alarmtype> equipmentAlarm
        (5) <Polarity> (2)
        "
	  ::= { rm10010AlmmodFanFail 2 }



rm10010AlmFanModuleAbsent OBJECT-TYPE
	  SYNTAX EkiOnOff
	  MAX-ACCESS read-only
	  STATUS current
	  DESCRIPTION
        "
        Fan Module Absent :This OID indicates
        the presence of the FAN module
         in the Chassis.  <Help>  This
         alarm indicates if the FAN module
        is detected in the chassis. <Condtype>
        FAN_MODULE_ABSENT <Probcause> heatingVentCoolingSystemProblem
        (22) <Alarmtype> equipmentAlarm
        (5) <Polarity> (2) <Event> ObjectCDINV
        "
	  ::= { rm10010AlmmodFanFail 1 }








--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
rm10010CtrlconfMgnt1 OBJECT IDENTIFIER ::= { rm10010CtrlOther 1 }




rm10010CtrlConf2Clear1 OBJECT-TYPE
	  SYNTAX EkiOnOff
	  MAX-ACCESS read-write
	  STATUS current
	  DESCRIPTION
        "
        Clear Configuration Tables :This
        OID clears the configuration tables
        from configuration2 in the flash.
         <Help>  This control restores
         the default configuration of the
        module
        "
	  ::= { rm10010CtrlconfMgnt1 14 }



rm10010CtrlConf2Flash1 OBJECT-TYPE
	  SYNTAX EkiOnOff
	  MAX-ACCESS read-write
	  STATUS current
	  DESCRIPTION
        "
        Write Configuration Tables :This
        OID saves the current configuration
        of the PM as configuration2 in
         the flash.  <Help>  This control
        saves the customer configuration
        on the module
        "
	  ::= { rm10010CtrlconfMgnt1 10 }



rm10010CtrlConf2Load1 OBJECT-TYPE
	  SYNTAX EkiOnOff
	  MAX-ACCESS read-write
	  STATUS current
	  DESCRIPTION
        "
        Load Configuration Tables Set
         Nb 2 :When set this OID enables
        loading from flash configuration2
        into the PM.
        "
	  ::= { rm10010CtrlconfMgnt1 2 }



rm10010CtrlConf1Load1 OBJECT-TYPE
	  SYNTAX EkiOnOff
	  MAX-ACCESS read-write
	  STATUS current
	  DESCRIPTION
        "
        Load Configuration Tables Set
         Nb 1 :When set this OID enables
        loading from flash configuration1
        into the PM.
        "
	  ::= { rm10010CtrlconfMgnt1 1 }



--- *****************************************************
---     LEAF for the synth4 article
--- *****************************************************
rm10010Ctrlsynth4 OBJECT IDENTIFIER ::= { rm10010CtrlOther 4 }




rm10010CtrlCorrelatOff OBJECT-TYPE
	  SYNTAX EkiOnOff
	  MAX-ACCESS read-write
	  STATUS current
	  DESCRIPTION
        "
        Disable Alarm Correlation :This
        OID disables the alarm correlation
        in the PM.
        "
	  ::= { rm10010Ctrlsynth4 2 }



rm10010CtrlCorrelatOn OBJECT-TYPE
	  SYNTAX EkiOnOff
	  MAX-ACCESS read-write
	  STATUS current
	  DESCRIPTION
        "
        Enable Alarm Correlation :This
        OID enables the alarm correlation
        in the PM.
        "
	  ::= { rm10010Ctrlsynth4 1 }



--- *****************************************************
---     LEAF for the swMgnt article
--- *****************************************************
rm10010CtrlswMgnt OBJECT IDENTIFIER ::= { rm10010CtrlOther 5 }




rm10010CtrlLoadSwBank2 OBJECT-TYPE
	  SYNTAX EkiOnOff
	  MAX-ACCESS read-write
	  STATUS current
	  DESCRIPTION
        "
        Set Software Nb 2 As Active :This
        OID, when set, loads the SW from
        bank2 into the PM. It must be followed
        by a reset.  <Help>  This controls
        selects the second SW bank as the
        active bank for the next module
        reset
        "
	  ::= { rm10010CtrlswMgnt 6 }



rm10010CtrlLoadSwBank1 OBJECT-TYPE
	  SYNTAX EkiOnOff
	  MAX-ACCESS read-write
	  STATUS current
	  DESCRIPTION
        "
        Set Software Nb 1 As Active :This
        OID, when set, loads the SW from
        bank1 into the PM. It must be followed
        by a reset.  <Help>  This controls
        selects the first SW bank as the
        active bank for the next module
        reset
        "
	  ::= { rm10010CtrlswMgnt 5 }



rm10010CtrlWarmReset OBJECT-TYPE
	  SYNTAX EkiOnOff
	  MAX-ACCESS read-write
	  STATUS current
	  DESCRIPTION
        "
        PM Warm Reset :This OID, when
         set, causes a warm reset of the
        PM. This reset is not traffic affecting,
        and the configuration of PM remains
        unchanged.  <Help>  This control
        initiates a warm reset of the module.
        "
	  ::= { rm10010CtrlswMgnt 3 }



rm10010CtrlColdReset OBJECT-TYPE
	  SYNTAX EkiOnOff
	  MAX-ACCESS read-write
	  STATUS current
	  DESCRIPTION
        "
        PM Cold Reset :This OID, when
         set, causes a cold reset of the
        PM. This reset is traffic affecting,
        and the configuration of PM is
         reloaded on start-up.  <Help>
          This control initiates a cold
        reset of the module.
        "
	  ::= { rm10010CtrlswMgnt 2 }



--- *****************************************************
---     LEAF for the gwMgnt article
--- *****************************************************
rm10010CtrlgwMgnt OBJECT IDENTIFIER ::= { rm10010CtrlOther 6 }




rm10010CtrlLoadGwBank4 OBJECT-TYPE
	  SYNTAX EkiOnOff
	  MAX-ACCESS read-write
	  STATUS current
	  DESCRIPTION
        "
        Set Gateware Nb 4 As Active :This
        OID, when set, loads the GW from
        bank4 (Flash) into the PM. It is
        followed by an automatic gateware
        cold reset.
        "
	  ::= { rm10010CtrlgwMgnt 8 }



rm10010CtrlLoadGwBank3 OBJECT-TYPE
	  SYNTAX EkiOnOff
	  MAX-ACCESS read-write
	  STATUS current
	  DESCRIPTION
        "
        Set Gateware Nb 3 As Active :This
        OID, when set, loads the GW from
        bank3 (Flash) into the PM. It is
        followed by an automatic gateware
        cold reset.  <Help>  This controls
        initiates a cold reset of the module
        and select the third GW bank as
        the active bank
        "
	  ::= { rm10010CtrlgwMgnt 7 }



rm10010CtrlLoadGwBank2 OBJECT-TYPE
	  SYNTAX EkiOnOff
	  MAX-ACCESS read-write
	  STATUS current
	  DESCRIPTION
        "
        Set Gateware Nb 2 As Active :This
        OID, when set, loads the GW from
        bank2 (Flash) into the PM. It is
        followed by an automatic gateware
        cold reset.
        "
	  ::= { rm10010CtrlgwMgnt 6 }



rm10010CtrlLoadGwBank1 OBJECT-TYPE
	  SYNTAX EkiOnOff
	  MAX-ACCESS read-write
	  STATUS current
	  DESCRIPTION
        "
        Set Gateware Nb 1 As Active :This
        OID, when set, loads the GW from
        bank1 (Flash) into the PM. It is
        followed by an automatic gateware
        cold reset.  <Help>  This controls
        initiates a cold reset of the module
        and select the first GW bank as
        the active bank
        "
	  ::= { rm10010CtrlgwMgnt 5 }



rm10010CtrlCurrentGwReset OBJECT-TYPE
	  SYNTAX EkiOnOff
	  MAX-ACCESS read-write
	  STATUS current
	  DESCRIPTION
        "
        Active Gateware Reset :This OID,
        when set, resets the active gateware.
        It is traffic affecting.
        "
	  ::= { rm10010CtrlgwMgnt 1 }



--- *********************************************************
---     TABLE for the rm10010CtrlaccessLoop articles
--- *********************************************************

rm10010CtrlaccessLoopTable OBJECT-TYPE
	SYNTAX  SEQUENCE OF Rm10010CtrlaccessLoopEntry
	MAX-ACCESS not-accessible
	STATUS current
	DESCRIPTION
        "
        List of rm10010CtrlaccessLoop
         Article
        "
	::= { rm10010CtrlClient 16 }


rm10010CtrlaccessLoopEntry OBJECT-TYPE
	SYNTAX Rm10010CtrlaccessLoopEntry
	MAX-ACCESS not-accessible
	STATUS current
	DESCRIPTION
        "
        Row definition for the rm10010CtrlaccessLoop
        table
        "
	INDEX   { rm10010CtrlaccessLoopIndex }
	::= { rm10010CtrlaccessLoopTable 1 }


Rm10010CtrlaccessLoopEntry ::=
	SEQUENCE {
	rm10010CtrlaccessLoopIndex
		INTEGER,
	rm10010CtrlaccessLoopPortn
		EkiState
	}


rm10010CtrlaccessLoopIndex OBJECT-TYPE
	SYNTAX  INTEGER(0..128)
	MAX-ACCESS  read-only
	STATUS current
	DESCRIPTION
        "
        Index definition for the rm10010CtrlaccessLoop
        table
        "
	::= { rm10010CtrlaccessLoopEntry 1 }


rm10010CtrlaccessLoopPortn OBJECT-TYPE
	SYNTAX  EkiState
	MAX-ACCESS read-write
	STATUS current
	DESCRIPTION
        "
        Client Facility Loopback :This
        OID, when set at '1' puts the client
        port in loopback, looping the received
        10 Gb/s signal on the transmit
         10 Gb/s output.  <Help> This control
        enables the Out Loopback on the
        client port, looping the client
        input signal on the client output
        "
	::= { rm10010CtrlaccessLoopEntry 2 }


--- *********************************************************
---     TABLE for the rm10010CtrlclientLoopToLine articles
--- *********************************************************

rm10010CtrlclientLoopToLineTable OBJECT-TYPE
	SYNTAX  SEQUENCE OF Rm10010CtrlclientLoopToLineEntry
	MAX-ACCESS not-accessible
	STATUS current
	DESCRIPTION
        "
        List of rm10010CtrlclientLoopToLine
        Article
        "
	::= { rm10010CtrlClient 17 }


rm10010CtrlclientLoopToLineEntry OBJECT-TYPE
	SYNTAX Rm10010CtrlclientLoopToLineEntry
	MAX-ACCESS not-accessible
	STATUS current
	DESCRIPTION
        "
        Row definition for the rm10010CtrlclientLoopToLine
        table
        "
	INDEX   { rm10010CtrlclientLoopToLineIndex }
	::= { rm10010CtrlclientLoopToLineTable 1 }


Rm10010CtrlclientLoopToLineEntry ::=
	SEQUENCE {
	rm10010CtrlclientLoopToLineIndex
		INTEGER,
	rm10010CtrlclientLoopToLinePortn
		EkiState
	}


rm10010CtrlclientLoopToLineIndex OBJECT-TYPE
	SYNTAX  INTEGER(0..128)
	MAX-ACCESS  read-only
	STATUS current
	DESCRIPTION
        "
        Index definition for the rm10010CtrlclientLoopToLine
        table
        "
	::= { rm10010CtrlclientLoopToLineEntry 1 }


rm10010CtrlclientLoopToLinePortn OBJECT-TYPE
	SYNTAX  EkiState
	MAX-ACCESS read-write
	STATUS current
	DESCRIPTION
        "
        Client Terminal Loopback :This
        OID, when set, puts the client
         port in loop back, looping the
        10 Gb/s output signal on the 10
        Gb/s input.<Help> This control
         enables the In Loopback on the
        client port, looping the client
        output signal on the client input
        "
	::= { rm10010CtrlclientLoopToLineEntry 2 }


--- *********************************************************
---     TABLE for the rm10010CtrlcsfUpIns articles
--- *********************************************************

rm10010CtrlcsfUpInsTable OBJECT-TYPE
	SYNTAX  SEQUENCE OF Rm10010CtrlcsfUpInsEntry
	MAX-ACCESS not-accessible
	STATUS current
	DESCRIPTION
        "
        List of rm10010CtrlcsfUpIns Article
        "
	::= { rm10010CtrlClient 21 }


rm10010CtrlcsfUpInsEntry OBJECT-TYPE
	SYNTAX Rm10010CtrlcsfUpInsEntry
	MAX-ACCESS not-accessible
	STATUS current
	DESCRIPTION
        "
        Row definition for the rm10010CtrlcsfUpIns
        table
        "
	INDEX   { rm10010CtrlcsfUpInsIndex }
	::= { rm10010CtrlcsfUpInsTable 1 }


Rm10010CtrlcsfUpInsEntry ::=
	SEQUENCE {
	rm10010CtrlcsfUpInsIndex
		INTEGER,
	rm10010CtrlcsfUpInsPortn
		EkiState
	}


rm10010CtrlcsfUpInsIndex OBJECT-TYPE
	SYNTAX  INTEGER(0..128)
	MAX-ACCESS  read-only
	STATUS current
	DESCRIPTION
        "
        Index definition for the rm10010CtrlcsfUpIns
        table
        "
	::= { rm10010CtrlcsfUpInsEntry 1 }


rm10010CtrlcsfUpInsPortn OBJECT-TYPE
	SYNTAX  EkiState
	MAX-ACCESS read-write
	STATUS current
	DESCRIPTION
        "
        Client Signal Fail Insertion :This
        OID, when set, inserts  a client
        signal fail in the upstream client
        Port.  <Help>  This control inserts
        a Client Signal Fail for the client
        port
        "
	::= { rm10010CtrlcsfUpInsEntry 2 }


--- *********************************************************
---     TABLE for the rm10010CtrlcaisDwIns articles
--- *********************************************************

rm10010CtrlcaisDwInsTable OBJECT-TYPE
	SYNTAX  SEQUENCE OF Rm10010CtrlcaisDwInsEntry
	MAX-ACCESS not-accessible
	STATUS current
	DESCRIPTION
        "
        List of rm10010CtrlcaisDwIns Article
        "
	::= { rm10010CtrlClient 22 }


rm10010CtrlcaisDwInsEntry OBJECT-TYPE
	SYNTAX Rm10010CtrlcaisDwInsEntry
	MAX-ACCESS not-accessible
	STATUS current
	DESCRIPTION
        "
        Row definition for the rm10010CtrlcaisDwIns
        table
        "
	INDEX   { rm10010CtrlcaisDwInsIndex }
	::= { rm10010CtrlcaisDwInsTable 1 }


Rm10010CtrlcaisDwInsEntry ::=
	SEQUENCE {
	rm10010CtrlcaisDwInsIndex
		INTEGER,
	rm10010CtrlcaisDwInsPortn
		EkiState
	}


rm10010CtrlcaisDwInsIndex OBJECT-TYPE
	SYNTAX  INTEGER(0..128)
	MAX-ACCESS  read-only
	STATUS current
	DESCRIPTION
        "
        Index definition for the rm10010CtrlcaisDwIns
        table
        "
	::= { rm10010CtrlcaisDwInsEntry 1 }


rm10010CtrlcaisDwInsPortn OBJECT-TYPE
	SYNTAX  EkiState
	MAX-ACCESS read-write
	STATUS current
	DESCRIPTION
        "
        Client AIS Insertion :This OID,
        when set, inserts a client AIS
         on the downstream client Port.
         <Help>  This control inserts a
        Client AIS for the client port
        "
	::= { rm10010CtrlcaisDwInsEntry 2 }


--- *********************************************************
---     TABLE for the rm10010CtrlcommAccessLoop articles
--- *********************************************************

rm10010CtrlcommAccessLoopTable OBJECT-TYPE
	SYNTAX  SEQUENCE OF Rm10010CtrlcommAccessLoopEntry
	MAX-ACCESS not-accessible
	STATUS current
	DESCRIPTION
        "
        List of rm10010CtrlcommAccessLoop
        Article
        "
	::= { rm10010CtrlLine 64 }


rm10010CtrlcommAccessLoopEntry OBJECT-TYPE
	SYNTAX Rm10010CtrlcommAccessLoopEntry
	MAX-ACCESS not-accessible
	STATUS current
	DESCRIPTION
        "
        Row definition for the rm10010CtrlcommAccessLoop
        table
        "
	INDEX   { rm10010CtrlcommAccessLoopIndex }
	::= { rm10010CtrlcommAccessLoopTable 1 }


Rm10010CtrlcommAccessLoopEntry ::=
	SEQUENCE {
	rm10010CtrlcommAccessLoopIndex
		INTEGER,
	rm10010CtrlcommAccessLoopPortn
		EkiState
	}


rm10010CtrlcommAccessLoopIndex OBJECT-TYPE
	SYNTAX  INTEGER(0..128)
	MAX-ACCESS  read-only
	STATUS current
	DESCRIPTION
        "
        Index definition for the rm10010CtrlcommAccessLoop
        table
        "
	::= { rm10010CtrlcommAccessLoopEntry 1 }


rm10010CtrlcommAccessLoopPortn OBJECT-TYPE
	SYNTAX  EkiState
	MAX-ACCESS read-write
	STATUS current
	DESCRIPTION
        "
        Line Terminal Loopback :This OID,
        when set, puts the module in common
        access loop back, looping the 100
        Gb/s output signal on the 100 Gb/s
        input.<Help> This control enables
        the In Loopback on the line port,
        looping the 100 Gb/s output signal
        on the 100 Gb/s input
        "
	::= { rm10010CtrlcommAccessLoopEntry 2 }


--- *********************************************************
---     TABLE for the rm10010CtrllineLoop articles
--- *********************************************************

rm10010CtrllineLoopTable OBJECT-TYPE
	SYNTAX  SEQUENCE OF Rm10010CtrllineLoopEntry
	MAX-ACCESS not-accessible
	STATUS current
	DESCRIPTION
        "
        List of rm10010CtrllineLoop Article
        "
	::= { rm10010CtrlLine 66 }


rm10010CtrllineLoopEntry OBJECT-TYPE
	SYNTAX Rm10010CtrllineLoopEntry
	MAX-ACCESS not-accessible
	STATUS current
	DESCRIPTION
        "
        Row definition for the rm10010CtrllineLoop
        table
        "
	INDEX   { rm10010CtrllineLoopIndex }
	::= { rm10010CtrllineLoopTable 1 }


Rm10010CtrllineLoopEntry ::=
	SEQUENCE {
	rm10010CtrllineLoopIndex
		INTEGER,
	rm10010CtrllineLoopPortn
		EkiState
	}


rm10010CtrllineLoopIndex OBJECT-TYPE
	SYNTAX  INTEGER(0..128)
	MAX-ACCESS  read-only
	STATUS current
	DESCRIPTION
        "
        Index definition for the rm10010CtrllineLoop
        table
        "
	::= { rm10010CtrllineLoopEntry 1 }


rm10010CtrllineLoopPortn OBJECT-TYPE
	SYNTAX  EkiState
	MAX-ACCESS read-write
	STATUS current
	DESCRIPTION
        "
        Line Facility Loopback :This OID,
        when set at '1' puts the module
        in line loopback mode, looping
         the received 100 Gb/s signal on
        the transmit 100 Gb/s output. The
        Upstream part of the module is
         timed on the 100 Gb/s recovered
        clock in that case.<Help> This
         control enables the Out Loopback
        on the line port, looping the 100
        Gb/s input signal on the 100 Gb/s
        output
        "
	::= { rm10010CtrllineLoopEntry 2 }


--- *********************************************************
---     TABLE for the rm10010CtrlfecDisable articles
--- *********************************************************

rm10010CtrlfecDisableTable OBJECT-TYPE
	SYNTAX  SEQUENCE OF Rm10010CtrlfecDisableEntry
	MAX-ACCESS not-accessible
	STATUS current
	DESCRIPTION
        "
        List of rm10010CtrlfecDisable
         Article
        "
	::= { rm10010CtrlLine 69 }


rm10010CtrlfecDisableEntry OBJECT-TYPE
	SYNTAX Rm10010CtrlfecDisableEntry
	MAX-ACCESS not-accessible
	STATUS current
	DESCRIPTION
        "
        Row definition for the rm10010CtrlfecDisable
        table
        "
	INDEX   { rm10010CtrlfecDisableIndex }
	::= { rm10010CtrlfecDisableTable 1 }


Rm10010CtrlfecDisableEntry ::=
	SEQUENCE {
	rm10010CtrlfecDisableIndex
		INTEGER,
	rm10010CtrlfecDisablePortn
		EkiState
	}


rm10010CtrlfecDisableIndex OBJECT-TYPE
	SYNTAX  INTEGER(0..128)
	MAX-ACCESS  read-only
	STATUS current
	DESCRIPTION
        "
        Index definition for the rm10010CtrlfecDisable
        table
        "
	::= { rm10010CtrlfecDisableEntry 1 }


rm10010CtrlfecDisablePortn OBJECT-TYPE
	SYNTAX  EkiState
	MAX-ACCESS read-write
	STATUS current
	DESCRIPTION
        "
        Forward Error Correction Inhibition
        :This OID, when set, inhibits the
        Forward Error Correction feature
        on the line input  <Help>  This
        control enables/disables the Forward
        Error Correction on the line interface
        "
	::= { rm10010CtrlfecDisableEntry 2 }


--- *****************************************************
---     LEAF for the ledTest article
--- *****************************************************
rm10010CtrlledTest OBJECT IDENTIFIER ::= { rm10010CtrlOther 192 }




rm10010CtrlLedOff OBJECT-TYPE
	  SYNTAX EkiOnOff
	  MAX-ACCESS read-write
	  STATUS current
	  DESCRIPTION
        "
        Leds Off :This OID switches off
        all the Leds as a test feature.
         <Help>  This control initiates
        a test leds turning all the LEDs
        to OFF
        "
	  ::= { rm10010CtrlledTest 3 }



rm10010CtrlRedLed OBJECT-TYPE
	  SYNTAX EkiOnOff
	  MAX-ACCESS read-write
	  STATUS current
	  DESCRIPTION
        "
        Red Leds Test :This OID switches
        on all the red Leds as a test feature.
         <Help>  This control initiates
        a test leds turning all the LEDs
        to red
        "
	  ::= { rm10010CtrlledTest 2 }



rm10010CtrlGreenLed OBJECT-TYPE
	  SYNTAX EkiOnOff
	  MAX-ACCESS read-write
	  STATUS current
	  DESCRIPTION
        "
        Green Leds Test :This OID switches
        on all the green Leds as a test
        feature.  <Help>  This control
         initiates a test leds turning
         all the LEDs to green
        "
	  ::= { rm10010CtrlledTest 1 }



--- *****************************************************
---     LEAF for the initSwitchMarvell article
--- *****************************************************
rm10010CtrlinitSwitchMarvell OBJECT IDENTIFIER ::= { rm10010CtrlOther 201 }




rm10010CtrlInitSwitchMarvell OBJECT-TYPE
	  SYNTAX EkiOnOff
	  MAX-ACCESS read-write
	  STATUS current
	  DESCRIPTION
        "
        Switch Initialization :This OID
        operates an initialization of the
        switch managed through the module
         <Help>  This control activates
        an initialization of the switch
        managed through the module
        "
	  ::= { rm10010CtrlinitSwitchMarvell 1 }



--- *********************************************************
---     TABLE for the rm10010CtrlmsaLineLoop articles
--- *********************************************************

rm10010CtrlmsaLineLoopTable OBJECT-TYPE
	SYNTAX  SEQUENCE OF Rm10010CtrlmsaLineLoopEntry
	MAX-ACCESS not-accessible
	STATUS current
	DESCRIPTION
        "
        List of rm10010CtrlmsaLineLoop
        Article
        "
	::= { rm10010CtrlLine 209 }


rm10010CtrlmsaLineLoopEntry OBJECT-TYPE
	SYNTAX Rm10010CtrlmsaLineLoopEntry
	MAX-ACCESS not-accessible
	STATUS current
	DESCRIPTION
        "
        Row definition for the rm10010CtrlmsaLineLoop
        table
        "
	INDEX   { rm10010CtrlmsaLineLoopIndex }
	::= { rm10010CtrlmsaLineLoopTable 1 }


Rm10010CtrlmsaLineLoopEntry ::=
	SEQUENCE {
	rm10010CtrlmsaLineLoopIndex
		INTEGER,
	rm10010CtrlmsaLineLoopPortn
		EkiState
	}


rm10010CtrlmsaLineLoopIndex OBJECT-TYPE
	SYNTAX  INTEGER(0..128)
	MAX-ACCESS  read-only
	STATUS current
	DESCRIPTION
        "
        Index definition for the rm10010CtrlmsaLineLoop
        table
        "
	::= { rm10010CtrlmsaLineLoopEntry 1 }


rm10010CtrlmsaLineLoopPortn OBJECT-TYPE
	SYNTAX  EkiState
	MAX-ACCESS read-write
	STATUS current
	DESCRIPTION
        "
        MSA Line Loop :This OID operates
        a line loopback on the MSA Line
         <Help>  This control defines the
        line loop back of the line transceiver
        "
	::= { rm10010CtrlmsaLineLoopEntry 2 }


--- *********************************************************
---     TABLE for the rm10010CtrlmsaTxReset articles
--- *********************************************************

rm10010CtrlmsaTxResetTable OBJECT-TYPE
	SYNTAX  SEQUENCE OF Rm10010CtrlmsaTxResetEntry
	MAX-ACCESS not-accessible
	STATUS current
	DESCRIPTION
        "
        List of rm10010CtrlmsaTxReset
         Article
        "
	::= { rm10010CtrlLine 210 }


rm10010CtrlmsaTxResetEntry OBJECT-TYPE
	SYNTAX Rm10010CtrlmsaTxResetEntry
	MAX-ACCESS not-accessible
	STATUS current
	DESCRIPTION
        "
        Row definition for the rm10010CtrlmsaTxReset
        table
        "
	INDEX   { rm10010CtrlmsaTxResetIndex }
	::= { rm10010CtrlmsaTxResetTable 1 }


Rm10010CtrlmsaTxResetEntry ::=
	SEQUENCE {
	rm10010CtrlmsaTxResetIndex
		INTEGER,
	rm10010CtrlmsaTxResetPortn
		EkiState
	}


rm10010CtrlmsaTxResetIndex OBJECT-TYPE
	SYNTAX  INTEGER(0..128)
	MAX-ACCESS  read-only
	STATUS current
	DESCRIPTION
        "
        Index definition for the rm10010CtrlmsaTxReset
        table
        "
	::= { rm10010CtrlmsaTxResetEntry 1 }


rm10010CtrlmsaTxResetPortn OBJECT-TYPE
	SYNTAX  EkiState
	MAX-ACCESS read-write
	STATUS current
	DESCRIPTION
        "
        Line MSA TX Reset :This OID resets
        the TX portion of the MSA line
         module  <Help > This control
         initiates a reset of the transmitting
        side
        "
	::= { rm10010CtrlmsaTxResetEntry 2 }


--- *********************************************************
---     TABLE for the rm10010CtrlmsaRxReset articles
--- *********************************************************

rm10010CtrlmsaRxResetTable OBJECT-TYPE
	SYNTAX  SEQUENCE OF Rm10010CtrlmsaRxResetEntry
	MAX-ACCESS not-accessible
	STATUS current
	DESCRIPTION
        "
        List of rm10010CtrlmsaRxReset
         Article
        "
	::= { rm10010CtrlLine 211 }


rm10010CtrlmsaRxResetEntry OBJECT-TYPE
	SYNTAX Rm10010CtrlmsaRxResetEntry
	MAX-ACCESS not-accessible
	STATUS current
	DESCRIPTION
        "
        Row definition for the rm10010CtrlmsaRxReset
        table
        "
	INDEX   { rm10010CtrlmsaRxResetIndex }
	::= { rm10010CtrlmsaRxResetTable 1 }


Rm10010CtrlmsaRxResetEntry ::=
	SEQUENCE {
	rm10010CtrlmsaRxResetIndex
		INTEGER,
	rm10010CtrlmsaRxResetPortn
		EkiState
	}


rm10010CtrlmsaRxResetIndex OBJECT-TYPE
	SYNTAX  INTEGER(0..128)
	MAX-ACCESS  read-only
	STATUS current
	DESCRIPTION
        "
        Index definition for the rm10010CtrlmsaRxReset
        table
        "
	::= { rm10010CtrlmsaRxResetEntry 1 }


rm10010CtrlmsaRxResetPortn OBJECT-TYPE
	SYNTAX  EkiState
	MAX-ACCESS read-write
	STATUS current
	DESCRIPTION
        "
        Line MSA RX Reset :This OID resets
        the RX portion of the MSA line
         module  <Help > This control
         initiates a reset of the receiving
        side
        "
	::= { rm10010CtrlmsaRxResetEntry 2 }


--- *********************************************************
---     TABLE for the rm10010CtrlmsaShutdown articles
--- *********************************************************

rm10010CtrlmsaShutdownTable OBJECT-TYPE
	SYNTAX  SEQUENCE OF Rm10010CtrlmsaShutdownEntry
	MAX-ACCESS not-accessible
	STATUS current
	DESCRIPTION
        "
        List of rm10010CtrlmsaShutdown
        Article
        "
	::= { rm10010CtrlLine 212 }


rm10010CtrlmsaShutdownEntry OBJECT-TYPE
	SYNTAX Rm10010CtrlmsaShutdownEntry
	MAX-ACCESS not-accessible
	STATUS current
	DESCRIPTION
        "
        Row definition for the rm10010CtrlmsaShutdown
        table
        "
	INDEX   { rm10010CtrlmsaShutdownIndex }
	::= { rm10010CtrlmsaShutdownTable 1 }


Rm10010CtrlmsaShutdownEntry ::=
	SEQUENCE {
	rm10010CtrlmsaShutdownIndex
		INTEGER,
	rm10010CtrlmsaShutdownPortn
		EkiState
	}


rm10010CtrlmsaShutdownIndex OBJECT-TYPE
	SYNTAX  INTEGER(0..128)
	MAX-ACCESS  read-only
	STATUS current
	DESCRIPTION
        "
        Index definition for the rm10010CtrlmsaShutdown
        table
        "
	::= { rm10010CtrlmsaShutdownEntry 1 }


rm10010CtrlmsaShutdownPortn OBJECT-TYPE
	SYNTAX  EkiState
	MAX-ACCESS read-write
	STATUS current
	DESCRIPTION
        "
        Line MSA Shutdown :This OID enters
        a process to shutdown the MSA line
        module  <Help > This control  initiates
        a shutdown of the module
        "
	::= { rm10010CtrlmsaShutdownEntry 2 }


--- *****************************************************
---     LEAF for the resetCount article
--- *****************************************************
rm10010CtrlresetCount OBJECT IDENTIFIER ::= { rm10010CtrlOther 259 }




rm10010CtrlResetcount OBJECT-TYPE
	  SYNTAX EkiOnOff
	  MAX-ACCESS read-write
	  STATUS current
	  DESCRIPTION
        "
        Module Count Global Reset :This
        OID resets all the errors counters
        on the module  <Help > This control
         initiates a reset of the errors
        counters on the module
        "
	  ::= { rm10010CtrlresetCount 1 }



--- *****************************************************
---     LEAF for the resetRmon article
--- *****************************************************
rm10010CtrlresetRmon OBJECT IDENTIFIER ::= { rm10010CtrlOther 260 }




rm10010CtrlResetrmon OBJECT-TYPE
	  SYNTAX EkiOnOff
	  MAX-ACCESS read-write
	  STATUS current
	  DESCRIPTION
        "
        Module Rmon Global Reset :This
        OID resets all the Rmon counters
        on the module  <Help > This control
         initiates a reset of the Rmon
         counters on the module
        "
	  ::= { rm10010CtrlresetRmon 1 }



--- *****************************************************
---     LEAF for the resetMeasurements article
--- *****************************************************
rm10010CtrlresetMeasurements OBJECT IDENTIFIER ::= { rm10010CtrlOther 261 }




rm10010CtrlResetmeasurements OBJECT-TYPE
	  SYNTAX EkiOnOff
	  MAX-ACCESS read-write
	  STATUS current
	  DESCRIPTION
        "
        Management Meas Global Reset :This
        OID resets some measurements on
        the management  <Help > This control
         initiates a reset of some measurements
        on the management
        "
	  ::= { rm10010CtrlresetMeasurements 1 }



--- *********************************************************
---     TABLE for the rm10010CtrlclientResetAllCount articles
--- *********************************************************

rm10010CtrlclientResetAllCountTable OBJECT-TYPE
	SYNTAX  SEQUENCE OF Rm10010CtrlclientResetAllCountEntry
	MAX-ACCESS not-accessible
	STATUS current
	DESCRIPTION
        "
        List of rm10010CtrlclientResetAllCount
        Article
        "
	::= { rm10010CtrlClient 262 }


rm10010CtrlclientResetAllCountEntry OBJECT-TYPE
	SYNTAX Rm10010CtrlclientResetAllCountEntry
	MAX-ACCESS not-accessible
	STATUS current
	DESCRIPTION
        "
        Row definition for the rm10010CtrlclientResetAllCount
        table
        "
	INDEX   { rm10010CtrlclientResetAllCountIndex }
	::= { rm10010CtrlclientResetAllCountTable 1 }


Rm10010CtrlclientResetAllCountEntry ::=
	SEQUENCE {
	rm10010CtrlclientResetAllCountIndex
		INTEGER,
	rm10010CtrlclientResetAllCountsPortn
		EkiState
	}


rm10010CtrlclientResetAllCountIndex OBJECT-TYPE
	SYNTAX  INTEGER(0..128)
	MAX-ACCESS  read-only
	STATUS current
	DESCRIPTION
        "
        Index definition for the rm10010CtrlclientResetAllCount
        table
        "
	::= { rm10010CtrlclientResetAllCountEntry 1 }


rm10010CtrlclientResetAllCountsPortn OBJECT-TYPE
	SYNTAX  EkiState
	MAX-ACCESS read-write
	STATUS current
	DESCRIPTION
        "
        Client Counters Reset :This OID
        resets every counter on the client
        port  <Help>   This control operates
        a reset on the statistics current
        ,previous and history client port
        counters
        "
	::= { rm10010CtrlclientResetAllCountEntry 2 }


--- *********************************************************
---     TABLE for the rm10010CtrllineResetAllCount articles
--- *********************************************************

rm10010CtrllineResetAllCountTable OBJECT-TYPE
	SYNTAX  SEQUENCE OF Rm10010CtrllineResetAllCountEntry
	MAX-ACCESS not-accessible
	STATUS current
	DESCRIPTION
        "
        List of rm10010CtrllineResetAllCount
        Article
        "
	::= { rm10010CtrlLine 263 }


rm10010CtrllineResetAllCountEntry OBJECT-TYPE
	SYNTAX Rm10010CtrllineResetAllCountEntry
	MAX-ACCESS not-accessible
	STATUS current
	DESCRIPTION
        "
        Row definition for the rm10010CtrllineResetAllCount
        table
        "
	INDEX   { rm10010CtrllineResetAllCountIndex }
	::= { rm10010CtrllineResetAllCountTable 1 }


Rm10010CtrllineResetAllCountEntry ::=
	SEQUENCE {
	rm10010CtrllineResetAllCountIndex
		INTEGER,
	rm10010CtrllineResetAllCountsPortn
		EkiState
	}


rm10010CtrllineResetAllCountIndex OBJECT-TYPE
	SYNTAX  INTEGER(0..128)
	MAX-ACCESS  read-only
	STATUS current
	DESCRIPTION
        "
        Index definition for the rm10010CtrllineResetAllCount
        table
        "
	::= { rm10010CtrllineResetAllCountEntry 1 }


rm10010CtrllineResetAllCountsPortn OBJECT-TYPE
	SYNTAX  EkiState
	MAX-ACCESS read-write
	STATUS current
	DESCRIPTION
        "
        Line Counters Reset :This OID
         resets every counter on the line
        port  <Help>   This control operates
        a reset on the statistics current
        ,previous and history line port
        counters
        "
	::= { rm10010CtrllineResetAllCountEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the rm10010CntclientInputErrorCounterLaneOne articles
--- *********************************************************

rm10010CntclientInputErrorCounterLaneOneTable OBJECT-TYPE
	SYNTAX  SEQUENCE OF Rm10010CntclientInputErrorCounterLaneOneEntry
	MAX-ACCESS not-accessible
	STATUS current
	DESCRIPTION
        "
        List of rm10010CntclientInputErrorCounterLaneOne
        Article
        "
	::= { rm10010CntClient 16 }


rm10010CntclientInputErrorCounterLaneOneEntry OBJECT-TYPE
	SYNTAX Rm10010CntclientInputErrorCounterLaneOneEntry
	MAX-ACCESS not-accessible
	STATUS current
	DESCRIPTION
        "
        Row definition for the rm10010CntclientInputErrorCounterLaneOne
        table
        "
	INDEX   { rm10010CntclientInputErrorCounterLaneOneIndex }
	::= { rm10010CntclientInputErrorCounterLaneOneTable 1 }


Rm10010CntclientInputErrorCounterLaneOneEntry ::=
	SEQUENCE {
	rm10010CntclientInputErrorCounterLaneOneIndex
		INTEGER,
	rm10010CntclientInputErrorCounterLaneOneValuePortn
		Counter32,
	rm10010CntclientInputErrorCounterLaneOneErrorPortn
		EkiOnOff,
	rm10010CntclientInputErrorCounterLaneOneOverloadPortn
		EkiOnOff
	}


rm10010CntclientInputErrorCounterLaneOneIndex OBJECT-TYPE
	SYNTAX  INTEGER(0..128)
	MAX-ACCESS  read-only
	STATUS current
	DESCRIPTION
        "
        Index definition for the rm10010CntclientInputErrorCounterLaneOne
        table
        "
	::= { rm10010CntclientInputErrorCounterLaneOneEntry 1 }


rm10010CntclientInputErrorCounterLaneOneValuePortn OBJECT-TYPE
	SYNTAX  Counter32
	MAX-ACCESS read-only
	STATUS current
	DESCRIPTION
        "
        Client_Input_Error_Counter_Lane1
        :This counter is incremented each
        time a coding violation is detected
        on the host lane of the client
         transceiver <Help> This counter
        is incremented each time a coding
        violation is detected on the host
        lane of the client transceiver
        "
	::= { rm10010CntclientInputErrorCounterLaneOneEntry 2 }


rm10010CntclientInputErrorCounterLaneOneErrorPortn OBJECT-TYPE
	SYNTAX  EkiOnOff
	MAX-ACCESS read-only
	STATUS current
	DESCRIPTION
        "
        Client Input Counter Error :This
        OID when set indicates the rate
        adaptation removal counter value
        is invalid on Port
        "
	::= { rm10010CntclientInputErrorCounterLaneOneEntry 3 }


rm10010CntclientInputErrorCounterLaneOneOverloadPortn OBJECT-TYPE
	SYNTAX  EkiOnOff
	MAX-ACCESS read-only
	STATUS current
	DESCRIPTION
        "
        Client Input Counter Overload
         :This OID when set indicates a
        rate adaptation removal counter
        overload on Port
        "
	::= { rm10010CntclientInputErrorCounterLaneOneEntry 4 }


--- *********************************************************
---     TABLE for the rm10010CntclientInputErrorCounterLaneTwo articles
--- *********************************************************

rm10010CntclientInputErrorCounterLaneTwoTable OBJECT-TYPE
	SYNTAX  SEQUENCE OF Rm10010CntclientInputErrorCounterLaneTwoEntry
	MAX-ACCESS not-accessible
	STATUS current
	DESCRIPTION
        "
        List of rm10010CntclientInputErrorCounterLaneTwo
        Article
        "
	::= { rm10010CntClient 32 }


rm10010CntclientInputErrorCounterLaneTwoEntry OBJECT-TYPE
	SYNTAX Rm10010CntclientInputErrorCounterLaneTwoEntry
	MAX-ACCESS not-accessible
	STATUS current
	DESCRIPTION
        "
        Row definition for the rm10010CntclientInputErrorCounterLaneTwo
        table
        "
	INDEX   { rm10010CntclientInputErrorCounterLaneTwoIndex }
	::= { rm10010CntclientInputErrorCounterLaneTwoTable 1 }


Rm10010CntclientInputErrorCounterLaneTwoEntry ::=
	SEQUENCE {
	rm10010CntclientInputErrorCounterLaneTwoIndex
		INTEGER,
	rm10010CntclientInputErrorCounterLaneTwoValuePortn
		Counter32,
	rm10010CntclientInputErrorCounterLaneTwoErrorPortn
		EkiOnOff,
	rm10010CntclientInputErrorCounterLaneTwoOverloadPortn
		EkiOnOff
	}


rm10010CntclientInputErrorCounterLaneTwoIndex OBJECT-TYPE
	SYNTAX  INTEGER(0..128)
	MAX-ACCESS  read-only
	STATUS current
	DESCRIPTION
        "
        Index definition for the rm10010CntclientInputErrorCounterLaneTwo
        table
        "
	::= { rm10010CntclientInputErrorCounterLaneTwoEntry 1 }


rm10010CntclientInputErrorCounterLaneTwoValuePortn OBJECT-TYPE
	SYNTAX  Counter32
	MAX-ACCESS read-only
	STATUS current
	DESCRIPTION
        "
        Client_Input_Error_Counter_Lane2
        :This counter is incremented each
        time a coding violation is detected
        on the host lane of the client
         transceiver <Help> This counter
        is incremented each time a coding
        violation is detected on the host
        lane of the client transceiver
        "
	::= { rm10010CntclientInputErrorCounterLaneTwoEntry 2 }


rm10010CntclientInputErrorCounterLaneTwoErrorPortn OBJECT-TYPE
	SYNTAX  EkiOnOff
	MAX-ACCESS read-only
	STATUS current
	DESCRIPTION
        "
        Client Input Counter Error :This
        OID when set indicates the client
        error counter value is invalid
         on Port
        "
	::= { rm10010CntclientInputErrorCounterLaneTwoEntry 3 }


rm10010CntclientInputErrorCounterLaneTwoOverloadPortn OBJECT-TYPE
	SYNTAX  EkiOnOff
	MAX-ACCESS read-only
	STATUS current
	DESCRIPTION
        "
        Client Input Counter Overload
         :This OID when set indicates a
        client input error counter overload
        on Port
        "
	::= { rm10010CntclientInputErrorCounterLaneTwoEntry 4 }


--- *********************************************************
---     TABLE for the rm10010CntclientInputErrorCounter articles
--- *********************************************************

rm10010CntclientInputErrorCounterTable OBJECT-TYPE
	SYNTAX  SEQUENCE OF Rm10010CntclientInputErrorCounterEntry
	MAX-ACCESS not-accessible
	STATUS current
	DESCRIPTION
        "
        List of rm10010CntclientInputErrorCounter
        Article
        "
	::= { rm10010CntClient 80 }


rm10010CntclientInputErrorCounterEntry OBJECT-TYPE
	SYNTAX Rm10010CntclientInputErrorCounterEntry
	MAX-ACCESS not-accessible
	STATUS current
	DESCRIPTION
        "
        Row definition for the rm10010CntclientInputErrorCounter
        table
        "
	INDEX   { rm10010CntclientInputErrorCounterIndex }
	::= { rm10010CntclientInputErrorCounterTable 1 }


Rm10010CntclientInputErrorCounterEntry ::=
	SEQUENCE {
	rm10010CntclientInputErrorCounterIndex
		INTEGER,
	rm10010CntclientInputErrorCounterValuePortn
		Counter32,
	rm10010CntclientInputErrorCounterErrorPortn
		EkiOnOff,
	rm10010CntclientInputErrorCounterOverloadPortn
		EkiOnOff
	}


rm10010CntclientInputErrorCounterIndex OBJECT-TYPE
	SYNTAX  INTEGER(0..128)
	MAX-ACCESS  read-only
	STATUS current
	DESCRIPTION
        "
        Index definition for the rm10010CntclientInputErrorCounter
        table
        "
	::= { rm10010CntclientInputErrorCounterEntry 1 }


rm10010CntclientInputErrorCounterValuePortn OBJECT-TYPE
	SYNTAX  Counter32
	MAX-ACCESS read-only
	STATUS current
	DESCRIPTION
        "
        Client Input Errors :This counter
        is increased each time a 10b/8b
        running disparity error is detected
        on the Client input stream  <Help>
         This counter gives the number
         of 10b/8b running disparity errors
        on the client port
        "
	::= { rm10010CntclientInputErrorCounterEntry 2 }


rm10010CntclientInputErrorCounterErrorPortn OBJECT-TYPE
	SYNTAX  EkiOnOff
	MAX-ACCESS read-only
	STATUS current
	DESCRIPTION
        "
        Client Counter Error :This OID
        when set indicates the client error
        counter value is invalid on Port
        "
	::= { rm10010CntclientInputErrorCounterEntry 3 }


rm10010CntclientInputErrorCounterOverloadPortn OBJECT-TYPE
	SYNTAX  EkiOnOff
	MAX-ACCESS read-only
	STATUS current
	DESCRIPTION
        "
        Client Counter Overload :This
         OID when set indicates a client
        input error counter overload on
        Port
        "
	::= { rm10010CntclientInputErrorCounterEntry 4 }


--- *********************************************************
---     TABLE for the rm10010CntclientCbipCounter articles
--- *********************************************************

rm10010CntclientCbipCounterTable OBJECT-TYPE
	SYNTAX  SEQUENCE OF Rm10010CntclientCbipCounterEntry
	MAX-ACCESS not-accessible
	STATUS current
	DESCRIPTION
        "
        List of rm10010CntclientCbipCounter
        Article
        "
	::= { rm10010CntClient 96 }


rm10010CntclientCbipCounterEntry OBJECT-TYPE
	SYNTAX Rm10010CntclientCbipCounterEntry
	MAX-ACCESS not-accessible
	STATUS current
	DESCRIPTION
        "
        Row definition for the rm10010CntclientCbipCounter
        table
        "
	INDEX   { rm10010CntclientCbipCounterIndex }
	::= { rm10010CntclientCbipCounterTable 1 }


Rm10010CntclientCbipCounterEntry ::=
	SEQUENCE {
	rm10010CntclientCbipCounterIndex
		INTEGER,
	rm10010CntclientCbipCounterValuePortn
		Counter32,
	rm10010CntclientCbipCounterErrorPortn
		EkiOnOff,
	rm10010CntclientCbipCounterOverloadPortn
		EkiOnOff
	}


rm10010CntclientCbipCounterIndex OBJECT-TYPE
	SYNTAX  INTEGER(0..128)
	MAX-ACCESS  read-only
	STATUS current
	DESCRIPTION
        "
        Index definition for the rm10010CntclientCbipCounter
        table
        "
	::= { rm10010CntclientCbipCounterEntry 1 }


rm10010CntclientCbipCounterValuePortn OBJECT-TYPE
	SYNTAX  Counter32
	MAX-ACCESS read-only
	STATUS current
	DESCRIPTION
        "
        Client Output Errors :This counter
        is incremented each time a CBIP
        parity error is detected on the
        Client output stream  <Help>  This
        counter gives the number of CBIP
        errors on the client port
        "
	::= { rm10010CntclientCbipCounterEntry 2 }


rm10010CntclientCbipCounterErrorPortn OBJECT-TYPE
	SYNTAX  EkiOnOff
	MAX-ACCESS read-only
	STATUS current
	DESCRIPTION
        "
        Client Counter Error :This OID
        when set indicates the CBIP error
        counter value is invalid on Port
        "
	::= { rm10010CntclientCbipCounterEntry 3 }


rm10010CntclientCbipCounterOverloadPortn OBJECT-TYPE
	SYNTAX  EkiOnOff
	MAX-ACCESS read-only
	STATUS current
	DESCRIPTION
        "
        Client CBIP Counter Overload :This
        OID when set indicates a CBIP error
        counter overload on Port
        "
	::= { rm10010CntclientCbipCounterEntry 4 }


--- *********************************************************
---     TABLE for the rm10010CntlocalLineSmBip8ErrorCounter articles
--- *********************************************************

rm10010CntlocalLineSmBip8ErrorCounterTable OBJECT-TYPE
	SYNTAX  SEQUENCE OF Rm10010CntlocalLineSmBip8ErrorCounterEntry
	MAX-ACCESS not-accessible
	STATUS current
	DESCRIPTION
        "
        List of rm10010CntlocalLineSmBip8ErrorCounter
        Article
        "
	::= { rm10010CntLine 192 }


rm10010CntlocalLineSmBip8ErrorCounterEntry OBJECT-TYPE
	SYNTAX Rm10010CntlocalLineSmBip8ErrorCounterEntry
	MAX-ACCESS not-accessible
	STATUS current
	DESCRIPTION
        "
        Row definition for the rm10010CntlocalLineSmBip8ErrorCounter
        table
        "
	INDEX   { rm10010CntlocalLineSmBip8ErrorCounterIndex }
	::= { rm10010CntlocalLineSmBip8ErrorCounterTable 1 }


Rm10010CntlocalLineSmBip8ErrorCounterEntry ::=
	SEQUENCE {
	rm10010CntlocalLineSmBip8ErrorCounterIndex
		INTEGER,
	rm10010CntlocalLineSmBip8ErrorCounterValuePortn
		Counter64,
	rm10010CntlocalLineSmBip8ErrorCounterErrorPortn
		EkiOnOff,
	rm10010CntlocalLineSmBip8ErrorCounterOverloadPortn
		EkiOnOff
	}


rm10010CntlocalLineSmBip8ErrorCounterIndex OBJECT-TYPE
	SYNTAX  INTEGER(0..128)
	MAX-ACCESS  read-only
	STATUS current
	DESCRIPTION
        "
        Index definition for the rm10010CntlocalLineSmBip8ErrorCounter
        table
        "
	::= { rm10010CntlocalLineSmBip8ErrorCounterEntry 1 }


rm10010CntlocalLineSmBip8ErrorCounterValuePortn OBJECT-TYPE
	SYNTAX  Counter64
	MAX-ACCESS read-only
	STATUS current
	DESCRIPTION
        "
        Line Input SM-BIP8 Errors :This
        OID gives the current Bit Error
        Rate (residual SM-BIP8 error) after
        FEC   <Help> This counter gives
        the current Bit Error Rate (residual
        SM-BIP8 error) after FEC
        "
	::= { rm10010CntlocalLineSmBip8ErrorCounterEntry 2 }


rm10010CntlocalLineSmBip8ErrorCounterErrorPortn OBJECT-TYPE
	SYNTAX  EkiOnOff
	MAX-ACCESS read-only
	STATUS current
	DESCRIPTION
        "
        Line Counter Error :This OID when
        set indicates the B1 error counter
        value is invalid on Port
        "
	::= { rm10010CntlocalLineSmBip8ErrorCounterEntry 3 }


rm10010CntlocalLineSmBip8ErrorCounterOverloadPortn OBJECT-TYPE
	SYNTAX  EkiOnOff
	MAX-ACCESS read-only
	STATUS current
	DESCRIPTION
        "
        Line Counter Overload :This OID
        when set indicates a B1 error counter
        overload on Port
        "
	::= { rm10010CntlocalLineSmBip8ErrorCounterEntry 4 }


--- *********************************************************
---     TABLE for the rm10010CntlocalLineFecCorrectedErrorsCounter articles
--- *********************************************************

rm10010CntlocalLineFecCorrectedErrorsCounterTable OBJECT-TYPE
	SYNTAX  SEQUENCE OF Rm10010CntlocalLineFecCorrectedErrorsCounterEntry
	MAX-ACCESS not-accessible
	STATUS current
	DESCRIPTION
        "
        List of rm10010CntlocalLineFecCorrectedErrorsCounter
        Article
        "
	::= { rm10010CntLine 193 }


rm10010CntlocalLineFecCorrectedErrorsCounterEntry OBJECT-TYPE
	SYNTAX Rm10010CntlocalLineFecCorrectedErrorsCounterEntry
	MAX-ACCESS not-accessible
	STATUS current
	DESCRIPTION
        "
        Row definition for the rm10010CntlocalLineFecCorrectedErrorsCounter
        table
        "
	INDEX   { rm10010CntlocalLineFecCorrectedErrorsCounterIndex }
	::= { rm10010CntlocalLineFecCorrectedErrorsCounterTable 1 }


Rm10010CntlocalLineFecCorrectedErrorsCounterEntry ::=
	SEQUENCE {
	rm10010CntlocalLineFecCorrectedErrorsCounterIndex
		INTEGER,
	rm10010CntlocalLineFecCorrectedErrorsCounterValuePortn
		Counter64,
	rm10010CntlocalLineFecCorrectedErrorsCounterErrorPortn
		EkiOnOff,
	rm10010CntlocalLineFecCorrectedErrorsCounterOverloadPortn
		EkiOnOff
	}


rm10010CntlocalLineFecCorrectedErrorsCounterIndex OBJECT-TYPE
	SYNTAX  INTEGER(0..128)
	MAX-ACCESS  read-only
	STATUS current
	DESCRIPTION
        "
        Index definition for the rm10010CntlocalLineFecCorrectedErrorsCounter
        table
        "
	::= { rm10010CntlocalLineFecCorrectedErrorsCounterEntry 1 }


rm10010CntlocalLineFecCorrectedErrorsCounterValuePortn OBJECT-TYPE
	SYNTAX  Counter64
	MAX-ACCESS read-only
	STATUS current
	DESCRIPTION
        "
        Line Input HD FEC Corrected Errors
        :This OID gives the current Bit
        Error Rate before the Hard Decision
        FEC  <Help> This counter gives
         the current Bit Error Rate before
        the Hard Decision FEC
        "
	::= { rm10010CntlocalLineFecCorrectedErrorsCounterEntry 2 }


rm10010CntlocalLineFecCorrectedErrorsCounterErrorPortn OBJECT-TYPE
	SYNTAX  EkiOnOff
	MAX-ACCESS read-only
	STATUS current
	DESCRIPTION
        "
        FEC Counter Error :This bit when
        set indicates the FEC corrected
        errors counter value is invalid
        on Line
        "
	::= { rm10010CntlocalLineFecCorrectedErrorsCounterEntry 3 }


rm10010CntlocalLineFecCorrectedErrorsCounterOverloadPortn OBJECT-TYPE
	SYNTAX  EkiOnOff
	MAX-ACCESS read-only
	STATUS current
	DESCRIPTION
        "
        FEC Counter Overload :This bit
        when set indicates a FEC corrected
        errors counter overload on Line
        "
	::= { rm10010CntlocalLineFecCorrectedErrorsCounterEntry 4 }


--- *********************************************************
---     TABLE for the rm10010CntremoteLineSmBip8ErrorCounter articles
--- *********************************************************

rm10010CntremoteLineSmBip8ErrorCounterTable OBJECT-TYPE
	SYNTAX  SEQUENCE OF Rm10010CntremoteLineSmBip8ErrorCounterEntry
	MAX-ACCESS not-accessible
	STATUS current
	DESCRIPTION
        "
        List of rm10010CntremoteLineSmBip8ErrorCounter
        Article
        "
	::= { rm10010CntLine 194 }


rm10010CntremoteLineSmBip8ErrorCounterEntry OBJECT-TYPE
	SYNTAX Rm10010CntremoteLineSmBip8ErrorCounterEntry
	MAX-ACCESS not-accessible
	STATUS current
	DESCRIPTION
        "
        Row definition for the rm10010CntremoteLineSmBip8ErrorCounter
        table
        "
	INDEX   { rm10010CntremoteLineSmBip8ErrorCounterIndex }
	::= { rm10010CntremoteLineSmBip8ErrorCounterTable 1 }


Rm10010CntremoteLineSmBip8ErrorCounterEntry ::=
	SEQUENCE {
	rm10010CntremoteLineSmBip8ErrorCounterIndex
		INTEGER,
	rm10010CntremoteLineSmBip8ErrorCounterValuePortn
		Counter64,
	rm10010CntremoteLineSmBip8ErrorCounterErrorPortn
		EkiOnOff,
	rm10010CntremoteLineSmBip8ErrorCounterOverloadPortn
		EkiOnOff
	}


rm10010CntremoteLineSmBip8ErrorCounterIndex OBJECT-TYPE
	SYNTAX  INTEGER(0..128)
	MAX-ACCESS  read-only
	STATUS current
	DESCRIPTION
        "
        Index definition for the rm10010CntremoteLineSmBip8ErrorCounter
        table
        "
	::= { rm10010CntremoteLineSmBip8ErrorCounterEntry 1 }


rm10010CntremoteLineSmBip8ErrorCounterValuePortn OBJECT-TYPE
	SYNTAX  Counter64
	MAX-ACCESS read-only
	STATUS current
	DESCRIPTION
        "
        Remote SM BIP8 :This OID gives
        the current Bit Error Rate (residual
        SM-BIP8 error) after FEC on the
        remote side  <Help> This counter
        gives the current Bit Error Rate
        (residual SM-BIP8 error) after
         FEC on the remote side
        "
	::= { rm10010CntremoteLineSmBip8ErrorCounterEntry 2 }


rm10010CntremoteLineSmBip8ErrorCounterErrorPortn OBJECT-TYPE
	SYNTAX  EkiOnOff
	MAX-ACCESS read-only
	STATUS current
	DESCRIPTION
        "
        Remote Counter Error :
        "
	::= { rm10010CntremoteLineSmBip8ErrorCounterEntry 3 }


rm10010CntremoteLineSmBip8ErrorCounterOverloadPortn OBJECT-TYPE
	SYNTAX  EkiOnOff
	MAX-ACCESS read-only
	STATUS current
	DESCRIPTION
        "
        Remote Counter Overload :
        "
	::= { rm10010CntremoteLineSmBip8ErrorCounterEntry 4 }


--- *********************************************************
---     TABLE for the rm10010CntlineDfrmTimCnt articles
--- *********************************************************

rm10010CntlineDfrmTimCntTable OBJECT-TYPE
	SYNTAX  SEQUENCE OF Rm10010CntlineDfrmTimCntEntry
	MAX-ACCESS not-accessible
	STATUS current
	DESCRIPTION
        "
        List of rm10010CntlineDfrmTimCnt
        Article
        "
	::= { rm10010CntLine 195 }


rm10010CntlineDfrmTimCntEntry OBJECT-TYPE
	SYNTAX Rm10010CntlineDfrmTimCntEntry
	MAX-ACCESS not-accessible
	STATUS current
	DESCRIPTION
        "
        Row definition for the rm10010CntlineDfrmTimCnt
        table
        "
	INDEX   { rm10010CntlineDfrmTimCntIndex }
	::= { rm10010CntlineDfrmTimCntTable 1 }


Rm10010CntlineDfrmTimCntEntry ::=
	SEQUENCE {
	rm10010CntlineDfrmTimCntIndex
		INTEGER,
	rm10010CntlineDfrmTimCntValuePortn
		Counter64,
	rm10010CntlineDfrmTimCntErrorPortn
		EkiOnOff,
	rm10010CntlineDfrmTimCntOverloadPortn
		EkiOnOff
	}


rm10010CntlineDfrmTimCntIndex OBJECT-TYPE
	SYNTAX  INTEGER(0..128)
	MAX-ACCESS  read-only
	STATUS current
	DESCRIPTION
        "
        Index definition for the rm10010CntlineDfrmTimCnt
        table
        "
	::= { rm10010CntlineDfrmTimCntEntry 1 }


rm10010CntlineDfrmTimCntValuePortn OBJECT-TYPE
	SYNTAX  Counter64
	MAX-ACCESS read-only
	STATUS current
	DESCRIPTION
        "
        Line Timer Counter :
        "
	::= { rm10010CntlineDfrmTimCntEntry 2 }


rm10010CntlineDfrmTimCntErrorPortn OBJECT-TYPE
	SYNTAX  EkiOnOff
	MAX-ACCESS read-only
	STATUS current
	DESCRIPTION
        "
        Line Counter Error :This OID when
        set indicates the deframer timer
        counter value is invalid on Port
        "
	::= { rm10010CntlineDfrmTimCntEntry 3 }


rm10010CntlineDfrmTimCntOverloadPortn OBJECT-TYPE
	SYNTAX  EkiOnOff
	MAX-ACCESS read-only
	STATUS current
	DESCRIPTION
        "
        Line Counter Overload :This OID
        when set indicates a deframer timer
        counter overload on Port
        "
	::= { rm10010CntlineDfrmTimCntEntry 4 }


--- *********************************************************
---     TABLE for the rm10010CntlocalLineTrscvFecCorrectedErrorCounter articles
--- *********************************************************

rm10010CntlocalLineTrscvFecCorrectedErrorCounterTable OBJECT-TYPE
	SYNTAX  SEQUENCE OF Rm10010CntlocalLineTrscvFecCorrectedErrorCounterEntry
	MAX-ACCESS not-accessible
	STATUS current
	DESCRIPTION
        "
        List of rm10010CntlocalLineTrscvFecCorrectedErrorCounter
        Article
        "
	::= { rm10010CntLine 196 }


rm10010CntlocalLineTrscvFecCorrectedErrorCounterEntry OBJECT-TYPE
	SYNTAX Rm10010CntlocalLineTrscvFecCorrectedErrorCounterEntry
	MAX-ACCESS not-accessible
	STATUS current
	DESCRIPTION
        "
        Row definition for the rm10010CntlocalLineTrscvFecCorrectedErrorCounter
        table
        "
	INDEX   { rm10010CntlocalLineTrscvFecCorrectedErrorCounterIndex }
	::= { rm10010CntlocalLineTrscvFecCorrectedErrorCounterTable 1 }


Rm10010CntlocalLineTrscvFecCorrectedErrorCounterEntry ::=
	SEQUENCE {
	rm10010CntlocalLineTrscvFecCorrectedErrorCounterIndex
		INTEGER,
	rm10010CntlocalLineTrscvFecCorrectedErrorCounterValuePortn
		Counter64,
	rm10010CntlocalLineTrscvFecCorrectedErrorCounterErrorPortn
		EkiOnOff,
	rm10010CntlocalLineTrscvFecCorrectedErrorCounterOverloadPortn
		EkiOnOff
	}


rm10010CntlocalLineTrscvFecCorrectedErrorCounterIndex OBJECT-TYPE
	SYNTAX  INTEGER(0..128)
	MAX-ACCESS  read-only
	STATUS current
	DESCRIPTION
        "
        Index definition for the rm10010CntlocalLineTrscvFecCorrectedErrorCounter
        table
        "
	::= { rm10010CntlocalLineTrscvFecCorrectedErrorCounterEntry 1 }


rm10010CntlocalLineTrscvFecCorrectedErrorCounterValuePortn OBJECT-TYPE
	SYNTAX  Counter64
	MAX-ACCESS read-only
	STATUS current
	DESCRIPTION
        "
        Line Input SD FEC Corrected Errors
        :This OID gives the current Bit
        Error Rate before the Soft Decision
        FEC  <Help> This counter gives
         the current Bit Error Rate before
        the Soft Decision FEC
        "
	::= { rm10010CntlocalLineTrscvFecCorrectedErrorCounterEntry 2 }


rm10010CntlocalLineTrscvFecCorrectedErrorCounterErrorPortn OBJECT-TYPE
	SYNTAX  EkiOnOff
	MAX-ACCESS read-only
	STATUS current
	DESCRIPTION
        "
        Line Counter Error :This OID when
        set indicates the deframer timer
        counter value is invalid on Port
        "
	::= { rm10010CntlocalLineTrscvFecCorrectedErrorCounterEntry 3 }


rm10010CntlocalLineTrscvFecCorrectedErrorCounterOverloadPortn OBJECT-TYPE
	SYNTAX  EkiOnOff
	MAX-ACCESS read-only
	STATUS current
	DESCRIPTION
        "
        Line Counter Overload :This OID
        when set indicates a deframer timer
        counter overload on Port
        "
	::= { rm10010CntlocalLineTrscvFecCorrectedErrorCounterEntry 4 }


--- *********************************************************
---     TABLE for the rm10010CntlocalLineTrscvFecUncorrectedErrorCounter articles
--- *********************************************************

rm10010CntlocalLineTrscvFecUncorrectedErrorCounterTable OBJECT-TYPE
	SYNTAX  SEQUENCE OF Rm10010CntlocalLineTrscvFecUncorrectedErrorCounterEntry
	MAX-ACCESS not-accessible
	STATUS current
	DESCRIPTION
        "
        List of rm10010CntlocalLineTrscvFecUncorrectedErrorCounter
        Article
        "
	::= { rm10010CntLine 197 }


rm10010CntlocalLineTrscvFecUncorrectedErrorCounterEntry OBJECT-TYPE
	SYNTAX Rm10010CntlocalLineTrscvFecUncorrectedErrorCounterEntry
	MAX-ACCESS not-accessible
	STATUS current
	DESCRIPTION
        "
        Row definition for the rm10010CntlocalLineTrscvFecUncorrectedErrorCounter
        table
        "
	INDEX   { rm10010CntlocalLineTrscvFecUncorrectedErrorCounterIndex }
	::= { rm10010CntlocalLineTrscvFecUncorrectedErrorCounterTable 1 }


Rm10010CntlocalLineTrscvFecUncorrectedErrorCounterEntry ::=
	SEQUENCE {
	rm10010CntlocalLineTrscvFecUncorrectedErrorCounterIndex
		INTEGER,
	rm10010CntlocalLineTrscvFecUncorrectedErrorCounterValuePortn
		Counter64,
	rm10010CntlocalLineTrscvFecUncorrectedErrorCounterErrorPortn
		EkiOnOff,
	rm10010CntlocalLineTrscvFecUncorrectedErrorCounterOverloadPortn
		EkiOnOff
	}


rm10010CntlocalLineTrscvFecUncorrectedErrorCounterIndex OBJECT-TYPE
	SYNTAX  INTEGER(0..128)
	MAX-ACCESS  read-only
	STATUS current
	DESCRIPTION
        "
        Index definition for the rm10010CntlocalLineTrscvFecUncorrectedErrorCounter
        table
        "
	::= { rm10010CntlocalLineTrscvFecUncorrectedErrorCounterEntry 1 }


rm10010CntlocalLineTrscvFecUncorrectedErrorCounterValuePortn OBJECT-TYPE
	SYNTAX  Counter64
	MAX-ACCESS read-only
	STATUS current
	DESCRIPTION
        "
        SD Uncorrected :This OID gives
        the current Bit Error Rate after
        the Soft Decision FEC (residual)
         <Help> This counter gives the
         current Bit Error Rate after the
        Soft Decision FEC (residual)
        "
	::= { rm10010CntlocalLineTrscvFecUncorrectedErrorCounterEntry 2 }


rm10010CntlocalLineTrscvFecUncorrectedErrorCounterErrorPortn OBJECT-TYPE
	SYNTAX  EkiOnOff
	MAX-ACCESS read-only
	STATUS current
	DESCRIPTION
        "
        Line Counter Error :This OID when
        set indicates the deframer timer
        counter value is invalid on Port
        "
	::= { rm10010CntlocalLineTrscvFecUncorrectedErrorCounterEntry 3 }


rm10010CntlocalLineTrscvFecUncorrectedErrorCounterOverloadPortn OBJECT-TYPE
	SYNTAX  EkiOnOff
	MAX-ACCESS read-only
	STATUS current
	DESCRIPTION
        "
        Line Counter Overload :This OID
        when set indicates a deframer timer
        counter overload on Port
        "
	::= { rm10010CntlocalLineTrscvFecUncorrectedErrorCounterEntry 4 }







--- *****************************************************
--- $$$$$$$$$$$$$$$$$$$$$$$$$$$$$$$$$$$$$$$$$$$$$$$$$$$$$
---     RMON - 64 bits COUNTERS
--- $$$$$$$$$$$$$$$$$$$$$$$$$$$$$$$$$$$$$$$$$$$$$$$$$$$$$
--- *****************************************************



--- *********************************************************
---     TABLE for the rm10010MonupRmonBytesCounterClientInput articles
--- *********************************************************

rm10010MonupRmonBytesCounterClientInputTable OBJECT-TYPE
	SYNTAX  SEQUENCE OF Rm10010MonupRmonBytesCounterClientInputEntry
	MAX-ACCESS not-accessible
	STATUS current
	DESCRIPTION
        "
        List of rm10010MonupRmonBytesCounterClientInput
        Article
        "
	::= { rm10010MonClientRmonCounter 16 }


rm10010MonupRmonBytesCounterClientInputEntry OBJECT-TYPE
	SYNTAX Rm10010MonupRmonBytesCounterClientInputEntry
	MAX-ACCESS not-accessible
	STATUS current
	DESCRIPTION
        "
        Row definition for the rm10010MonupRmonBytesCounterClientInput
        table
        "
	INDEX   { rm10010MonupRmonBytesCounterClientInputIndex }
	::= { rm10010MonupRmonBytesCounterClientInputTable 1 }


Rm10010MonupRmonBytesCounterClientInputEntry ::=
	SEQUENCE {
	rm10010MonupRmonBytesCounterClientInputIndex
		INTEGER,
	rm10010MonupRmonBytesCounterClientInputValuePortn
		Counter64,
	rm10010MonupRmonBytesCounterClientInputErrorPortn
		EkiOnOff,
	rm10010MonupRmonBytesCounterClientInputOverloadPortn
		EkiOnOff
	}


rm10010MonupRmonBytesCounterClientInputIndex OBJECT-TYPE
	SYNTAX  INTEGER(0..128)
	MAX-ACCESS  read-only
	STATUS current
	DESCRIPTION
        "
        Index definition for the rm10010MonupRmonBytesCounterClientInput
        table
        "
	::= { rm10010MonupRmonBytesCounterClientInputEntry 1 }


rm10010MonupRmonBytesCounterClientInputValuePortn OBJECT-TYPE
	SYNTAX  Counter64
	MAX-ACCESS read-only
	STATUS current
	DESCRIPTION
        "
        Client Input Bytes :This counter
        is increased each time a data byte
        is received on the client port
          <Help>  This counter gives the
        number of bytes received on the
        client port
        "
	::= { rm10010MonupRmonBytesCounterClientInputEntry 2 }


rm10010MonupRmonBytesCounterClientInputErrorPortn OBJECT-TYPE
	SYNTAX  EkiOnOff
	MAX-ACCESS read-only
	STATUS current
	DESCRIPTION
        "
        Bytes Counter Error :This OID
         when set indicates the Bytes counter
        value is invalid on client port
        "
	::= { rm10010MonupRmonBytesCounterClientInputEntry 3 }


rm10010MonupRmonBytesCounterClientInputOverloadPortn OBJECT-TYPE
	SYNTAX  EkiOnOff
	MAX-ACCESS read-only
	STATUS current
	DESCRIPTION
        "
        Bytes Counter Overload :This OID
        when set indicates a Bytes counter
        overload on client port
        "
	::= { rm10010MonupRmonBytesCounterClientInputEntry 4 }


--- *********************************************************
---     TABLE for the rm10010MonupRmonCrcErrorsCounterClientInput articles
--- *********************************************************

rm10010MonupRmonCrcErrorsCounterClientInputTable OBJECT-TYPE
	SYNTAX  SEQUENCE OF Rm10010MonupRmonCrcErrorsCounterClientInputEntry
	MAX-ACCESS not-accessible
	STATUS current
	DESCRIPTION
        "
        List of rm10010MonupRmonCrcErrorsCounterClientInput
        Article
        "
	::= { rm10010MonClientRmonCounter 32 }


rm10010MonupRmonCrcErrorsCounterClientInputEntry OBJECT-TYPE
	SYNTAX Rm10010MonupRmonCrcErrorsCounterClientInputEntry
	MAX-ACCESS not-accessible
	STATUS current
	DESCRIPTION
        "
        Row definition for the rm10010MonupRmonCrcErrorsCounterClientInput
        table
        "
	INDEX   { rm10010MonupRmonCrcErrorsCounterClientInputIndex }
	::= { rm10010MonupRmonCrcErrorsCounterClientInputTable 1 }


Rm10010MonupRmonCrcErrorsCounterClientInputEntry ::=
	SEQUENCE {
	rm10010MonupRmonCrcErrorsCounterClientInputIndex
		INTEGER,
	rm10010MonupRmonCrcErrorsCounterClientInputValuePortn
		Counter64,
	rm10010MonupRmonCrcErrorsCounterClientInputErrorPortn
		EkiOnOff,
	rm10010MonupRmonCrcErrorsCounterClientInputOverloadPortn
		EkiOnOff
	}


rm10010MonupRmonCrcErrorsCounterClientInputIndex OBJECT-TYPE
	SYNTAX  INTEGER(0..128)
	MAX-ACCESS  read-only
	STATUS current
	DESCRIPTION
        "
        Index definition for the rm10010MonupRmonCrcErrorsCounterClientInput
        table
        "
	::= { rm10010MonupRmonCrcErrorsCounterClientInputEntry 1 }


rm10010MonupRmonCrcErrorsCounterClientInputValuePortn OBJECT-TYPE
	SYNTAX  Counter64
	MAX-ACCESS read-only
	STATUS current
	DESCRIPTION
        "
        Client Input CRC Errors :This
         counter is increased each time
        a CRC error is detected on the
         client port  <Help>  This counter
        gives the number of CRC Errors
         received on the client port
        "
	::= { rm10010MonupRmonCrcErrorsCounterClientInputEntry 2 }


rm10010MonupRmonCrcErrorsCounterClientInputErrorPortn OBJECT-TYPE
	SYNTAX  EkiOnOff
	MAX-ACCESS read-only
	STATUS current
	DESCRIPTION
        "
        CRC Errors Counter Error :This
        OID when set indicates the CRC
         Errors counter value is invalid
        on client port
        "
	::= { rm10010MonupRmonCrcErrorsCounterClientInputEntry 3 }


rm10010MonupRmonCrcErrorsCounterClientInputOverloadPortn OBJECT-TYPE
	SYNTAX  EkiOnOff
	MAX-ACCESS read-only
	STATUS current
	DESCRIPTION
        "
        CRC Errors Counter Overload :This
        OID when set indicates a CRC Errors
        counter overload on client port
        "
	::= { rm10010MonupRmonCrcErrorsCounterClientInputEntry 4 }


--- *********************************************************
---     TABLE for the rm10010MonupRmonPacketsCounterClientInput articles
--- *********************************************************

rm10010MonupRmonPacketsCounterClientInputTable OBJECT-TYPE
	SYNTAX  SEQUENCE OF Rm10010MonupRmonPacketsCounterClientInputEntry
	MAX-ACCESS not-accessible
	STATUS current
	DESCRIPTION
        "
        List of rm10010MonupRmonPacketsCounterClientInput
        Article
        "
	::= { rm10010MonClientRmonCounter 48 }


rm10010MonupRmonPacketsCounterClientInputEntry OBJECT-TYPE
	SYNTAX Rm10010MonupRmonPacketsCounterClientInputEntry
	MAX-ACCESS not-accessible
	STATUS current
	DESCRIPTION
        "
        Row definition for the rm10010MonupRmonPacketsCounterClientInput
        table
        "
	INDEX   { rm10010MonupRmonPacketsCounterClientInputIndex }
	::= { rm10010MonupRmonPacketsCounterClientInputTable 1 }


Rm10010MonupRmonPacketsCounterClientInputEntry ::=
	SEQUENCE {
	rm10010MonupRmonPacketsCounterClientInputIndex
		INTEGER,
	rm10010MonupRmonPacketsCounterClientInputValuePortn
		Counter64,
	rm10010MonupRmonPacketsCounterClientInputErrorPortn
		EkiOnOff,
	rm10010MonupRmonPacketsCounterClientInputOverloadPortn
		EkiOnOff
	}


rm10010MonupRmonPacketsCounterClientInputIndex OBJECT-TYPE
	SYNTAX  INTEGER(0..128)
	MAX-ACCESS  read-only
	STATUS current
	DESCRIPTION
        "
        Index definition for the rm10010MonupRmonPacketsCounterClientInput
        table
        "
	::= { rm10010MonupRmonPacketsCounterClientInputEntry 1 }


rm10010MonupRmonPacketsCounterClientInputValuePortn OBJECT-TYPE
	SYNTAX  Counter64
	MAX-ACCESS read-only
	STATUS current
	DESCRIPTION
        "
        Client Input Packets :This counter
        is increased each time a packet
        is received on the client port
          <Help>  This counter gives the
        number of packets received on the
        client port
        "
	::= { rm10010MonupRmonPacketsCounterClientInputEntry 2 }


rm10010MonupRmonPacketsCounterClientInputErrorPortn OBJECT-TYPE
	SYNTAX  EkiOnOff
	MAX-ACCESS read-only
	STATUS current
	DESCRIPTION
        "
        Packets Counter Error :This OID
        when set indicates the Packets
         counter value is invalid on client
        port
        "
	::= { rm10010MonupRmonPacketsCounterClientInputEntry 3 }


rm10010MonupRmonPacketsCounterClientInputOverloadPortn OBJECT-TYPE
	SYNTAX  EkiOnOff
	MAX-ACCESS read-only
	STATUS current
	DESCRIPTION
        "
        Packets Counter Overload :This
        OID when set indicates a Packets
        counter overload on client port
        "
	::= { rm10010MonupRmonPacketsCounterClientInputEntry 4 }


--- *********************************************************
---     TABLE for the rm10010MonupRmonBroadcastCounterClientInput articles
--- *********************************************************

rm10010MonupRmonBroadcastCounterClientInputTable OBJECT-TYPE
	SYNTAX  SEQUENCE OF Rm10010MonupRmonBroadcastCounterClientInputEntry
	MAX-ACCESS not-accessible
	STATUS current
	DESCRIPTION
        "
        List of rm10010MonupRmonBroadcastCounterClientInput
        Article
        "
	::= { rm10010MonClientRmonCounter 64 }


rm10010MonupRmonBroadcastCounterClientInputEntry OBJECT-TYPE
	SYNTAX Rm10010MonupRmonBroadcastCounterClientInputEntry
	MAX-ACCESS not-accessible
	STATUS current
	DESCRIPTION
        "
        Row definition for the rm10010MonupRmonBroadcastCounterClientInput
        table
        "
	INDEX   { rm10010MonupRmonBroadcastCounterClientInputIndex }
	::= { rm10010MonupRmonBroadcastCounterClientInputTable 1 }


Rm10010MonupRmonBroadcastCounterClientInputEntry ::=
	SEQUENCE {
	rm10010MonupRmonBroadcastCounterClientInputIndex
		INTEGER,
	rm10010MonupRmonBroadcastCounterClientInputValuePortn
		Counter64,
	rm10010MonupRmonBroadcastCounterClientInputErrorPortn
		EkiOnOff,
	rm10010MonupRmonBroadcastCounterClientInputOverloadPortn
		EkiOnOff
	}


rm10010MonupRmonBroadcastCounterClientInputIndex OBJECT-TYPE
	SYNTAX  INTEGER(0..128)
	MAX-ACCESS  read-only
	STATUS current
	DESCRIPTION
        "
        Index definition for the rm10010MonupRmonBroadcastCounterClientInput
        table
        "
	::= { rm10010MonupRmonBroadcastCounterClientInputEntry 1 }


rm10010MonupRmonBroadcastCounterClientInputValuePortn OBJECT-TYPE
	SYNTAX  Counter64
	MAX-ACCESS read-only
	STATUS current
	DESCRIPTION
        "
        Client Input Broadcast Packets
        :This counter is increased each
        time a broadcast packet is received
        on the client port  <Help>  This
        counter gives the number of Broadcast
        packets received on the client
         port
        "
	::= { rm10010MonupRmonBroadcastCounterClientInputEntry 2 }


rm10010MonupRmonBroadcastCounterClientInputErrorPortn OBJECT-TYPE
	SYNTAX  EkiOnOff
	MAX-ACCESS read-only
	STATUS current
	DESCRIPTION
        "
        Broadcast Counter Error :This
         OID when set indicates the Broadcast
        counter value is invalid on client
        port
        "
	::= { rm10010MonupRmonBroadcastCounterClientInputEntry 3 }


rm10010MonupRmonBroadcastCounterClientInputOverloadPortn OBJECT-TYPE
	SYNTAX  EkiOnOff
	MAX-ACCESS read-only
	STATUS current
	DESCRIPTION
        "
        Broadcast Counter Overload :This
        OID when set indicates a Broadcast
        counter overload on client port
        "
	::= { rm10010MonupRmonBroadcastCounterClientInputEntry 4 }


--- *********************************************************
---     TABLE for the rm10010MonupRmonMulticastCounterClientInput articles
--- *********************************************************

rm10010MonupRmonMulticastCounterClientInputTable OBJECT-TYPE
	SYNTAX  SEQUENCE OF Rm10010MonupRmonMulticastCounterClientInputEntry
	MAX-ACCESS not-accessible
	STATUS current
	DESCRIPTION
        "
        List of rm10010MonupRmonMulticastCounterClientInput
        Article
        "
	::= { rm10010MonClientRmonCounter 80 }


rm10010MonupRmonMulticastCounterClientInputEntry OBJECT-TYPE
	SYNTAX Rm10010MonupRmonMulticastCounterClientInputEntry
	MAX-ACCESS not-accessible
	STATUS current
	DESCRIPTION
        "
        Row definition for the rm10010MonupRmonMulticastCounterClientInput
        table
        "
	INDEX   { rm10010MonupRmonMulticastCounterClientInputIndex }
	::= { rm10010MonupRmonMulticastCounterClientInputTable 1 }


Rm10010MonupRmonMulticastCounterClientInputEntry ::=
	SEQUENCE {
	rm10010MonupRmonMulticastCounterClientInputIndex
		INTEGER,
	rm10010MonupRmonMulticastCounterClientInputValuePortn
		Counter64,
	rm10010MonupRmonMulticastCounterClientInputErrorPortn
		EkiOnOff,
	rm10010MonupRmonMulticastCounterClientInputOverloadPortn
		EkiOnOff
	}


rm10010MonupRmonMulticastCounterClientInputIndex OBJECT-TYPE
	SYNTAX  INTEGER(0..128)
	MAX-ACCESS  read-only
	STATUS current
	DESCRIPTION
        "
        Index definition for the rm10010MonupRmonMulticastCounterClientInput
        table
        "
	::= { rm10010MonupRmonMulticastCounterClientInputEntry 1 }


rm10010MonupRmonMulticastCounterClientInputValuePortn OBJECT-TYPE
	SYNTAX  Counter64
	MAX-ACCESS read-only
	STATUS current
	DESCRIPTION
        "
        Client Input Multicast Packets
        :This counter is increased each
        time a Multicast packet is received
        on the client port  <Help>  This
        counter gives the number of Multicast
        packets received on the client
         port
        "
	::= { rm10010MonupRmonMulticastCounterClientInputEntry 2 }


rm10010MonupRmonMulticastCounterClientInputErrorPortn OBJECT-TYPE
	SYNTAX  EkiOnOff
	MAX-ACCESS read-only
	STATUS current
	DESCRIPTION
        "
        Multicast Counter Error :This
         OID when set indicates the Multicast
        counter value is invalid on client
        port
        "
	::= { rm10010MonupRmonMulticastCounterClientInputEntry 3 }


rm10010MonupRmonMulticastCounterClientInputOverloadPortn OBJECT-TYPE
	SYNTAX  EkiOnOff
	MAX-ACCESS read-only
	STATUS current
	DESCRIPTION
        "
        Multicast Counter Overload :This
        OID when set indicates a Multicast
        counter overload on client port
        "
	::= { rm10010MonupRmonMulticastCounterClientInputEntry 4 }


--- *********************************************************
---     TABLE for the rm10010MonupRmonPauseFrameCounterClientInput articles
--- *********************************************************

rm10010MonupRmonPauseFrameCounterClientInputTable OBJECT-TYPE
	SYNTAX  SEQUENCE OF Rm10010MonupRmonPauseFrameCounterClientInputEntry
	MAX-ACCESS not-accessible
	STATUS current
	DESCRIPTION
        "
        List of rm10010MonupRmonPauseFrameCounterClientInput
        Article
        "
	::= { rm10010MonClientRmonCounter 96 }


rm10010MonupRmonPauseFrameCounterClientInputEntry OBJECT-TYPE
	SYNTAX Rm10010MonupRmonPauseFrameCounterClientInputEntry
	MAX-ACCESS not-accessible
	STATUS current
	DESCRIPTION
        "
        Row definition for the rm10010MonupRmonPauseFrameCounterClientInput
        table
        "
	INDEX   { rm10010MonupRmonPauseFrameCounterClientInputIndex }
	::= { rm10010MonupRmonPauseFrameCounterClientInputTable 1 }


Rm10010MonupRmonPauseFrameCounterClientInputEntry ::=
	SEQUENCE {
	rm10010MonupRmonPauseFrameCounterClientInputIndex
		INTEGER,
	rm10010MonupRmonPauseFrameCounterClientInputValuePortn
		Counter64,
	rm10010MonupRmonPauseFrameCounterClientInputErrorPortn
		EkiOnOff,
	rm10010MonupRmonPauseFrameCounterClientInputOverloadPortn
		EkiOnOff
	}


rm10010MonupRmonPauseFrameCounterClientInputIndex OBJECT-TYPE
	SYNTAX  INTEGER(0..128)
	MAX-ACCESS  read-only
	STATUS current
	DESCRIPTION
        "
        Index definition for the rm10010MonupRmonPauseFrameCounterClientInput
        table
        "
	::= { rm10010MonupRmonPauseFrameCounterClientInputEntry 1 }


rm10010MonupRmonPauseFrameCounterClientInputValuePortn OBJECT-TYPE
	SYNTAX  Counter64
	MAX-ACCESS read-only
	STATUS current
	DESCRIPTION
        "
        Client Input Pause Frames :This
        counter is increased each time
         a Pause frame is received on the
        client port  <Help>  This counter
        gives the number of Pause frames
        received on the client port
        "
	::= { rm10010MonupRmonPauseFrameCounterClientInputEntry 2 }


rm10010MonupRmonPauseFrameCounterClientInputErrorPortn OBJECT-TYPE
	SYNTAX  EkiOnOff
	MAX-ACCESS read-only
	STATUS current
	DESCRIPTION
        "
        Pause Counter Error :This OID
         when set indicates the Pause counter
        value is invalid on client port
        "
	::= { rm10010MonupRmonPauseFrameCounterClientInputEntry 3 }


rm10010MonupRmonPauseFrameCounterClientInputOverloadPortn OBJECT-TYPE
	SYNTAX  EkiOnOff
	MAX-ACCESS read-only
	STATUS current
	DESCRIPTION
        "
        Pause Counter Overload :This OID
        when set indicates a Pause counter
        overload on client port
        "
	::= { rm10010MonupRmonPauseFrameCounterClientInputEntry 4 }


--- *********************************************************
---     TABLE for the rm10010MonupRmonUnicastCounterClientInput articles
--- *********************************************************

rm10010MonupRmonUnicastCounterClientInputTable OBJECT-TYPE
	SYNTAX  SEQUENCE OF Rm10010MonupRmonUnicastCounterClientInputEntry
	MAX-ACCESS not-accessible
	STATUS current
	DESCRIPTION
        "
        List of rm10010MonupRmonUnicastCounterClientInput
        Article
        "
	::= { rm10010MonClientRmonCounter 160 }


rm10010MonupRmonUnicastCounterClientInputEntry OBJECT-TYPE
	SYNTAX Rm10010MonupRmonUnicastCounterClientInputEntry
	MAX-ACCESS not-accessible
	STATUS current
	DESCRIPTION
        "
        Row definition for the rm10010MonupRmonUnicastCounterClientInput
        table
        "
	INDEX   { rm10010MonupRmonUnicastCounterClientInputIndex }
	::= { rm10010MonupRmonUnicastCounterClientInputTable 1 }


Rm10010MonupRmonUnicastCounterClientInputEntry ::=
	SEQUENCE {
	rm10010MonupRmonUnicastCounterClientInputIndex
		INTEGER,
	rm10010MonupRmonUnicastCounterClientInputValuePortn
		Counter64,
	rm10010MonupRmonUnicastCounterClientInputErrorPortn
		EkiOnOff,
	rm10010MonupRmonUnicastCounterClientInputOverloadPortn
		EkiOnOff
	}


rm10010MonupRmonUnicastCounterClientInputIndex OBJECT-TYPE
	SYNTAX  INTEGER(0..128)
	MAX-ACCESS  read-only
	STATUS current
	DESCRIPTION
        "
        Index definition for the rm10010MonupRmonUnicastCounterClientInput
        table
        "
	::= { rm10010MonupRmonUnicastCounterClientInputEntry 1 }


rm10010MonupRmonUnicastCounterClientInputValuePortn OBJECT-TYPE
	SYNTAX  Counter64
	MAX-ACCESS read-only
	STATUS current
	DESCRIPTION
        "
        Client Input Unicast Packets :This
        counter is increased each time
         a Unicast packet is received on
        the client port  <Help>  This counter
        gives the number of Unicast packets
        received on the client port
        "
	::= { rm10010MonupRmonUnicastCounterClientInputEntry 2 }


rm10010MonupRmonUnicastCounterClientInputErrorPortn OBJECT-TYPE
	SYNTAX  EkiOnOff
	MAX-ACCESS read-only
	STATUS current
	DESCRIPTION
        "
        Unicast Counter Error :This OID
        when set indicates the Unicast
         counter value is invalid on client
        port
        "
	::= { rm10010MonupRmonUnicastCounterClientInputEntry 3 }


rm10010MonupRmonUnicastCounterClientInputOverloadPortn OBJECT-TYPE
	SYNTAX  EkiOnOff
	MAX-ACCESS read-only
	STATUS current
	DESCRIPTION
        "
        Unicast Counter Overload :This
        OID when set indicates a Unicast
        counter overload on client port
        "
	::= { rm10010MonupRmonUnicastCounterClientInputEntry 4 }


--- *********************************************************
---     TABLE for the rm10010MonupRmonNonunicastCounterClientInput articles
--- *********************************************************

rm10010MonupRmonNonunicastCounterClientInputTable OBJECT-TYPE
	SYNTAX  SEQUENCE OF Rm10010MonupRmonNonunicastCounterClientInputEntry
	MAX-ACCESS not-accessible
	STATUS current
	DESCRIPTION
        "
        List of rm10010MonupRmonNonunicastCounterClientInput
        Article
        "
	::= { rm10010MonClientRmonCounter 176 }


rm10010MonupRmonNonunicastCounterClientInputEntry OBJECT-TYPE
	SYNTAX Rm10010MonupRmonNonunicastCounterClientInputEntry
	MAX-ACCESS not-accessible
	STATUS current
	DESCRIPTION
        "
        Row definition for the rm10010MonupRmonNonunicastCounterClientInput
        table
        "
	INDEX   { rm10010MonupRmonNonunicastCounterClientInputIndex }
	::= { rm10010MonupRmonNonunicastCounterClientInputTable 1 }


Rm10010MonupRmonNonunicastCounterClientInputEntry ::=
	SEQUENCE {
	rm10010MonupRmonNonunicastCounterClientInputIndex
		INTEGER,
	rm10010MonupRmonNonunicastCounterClientInputValuePortn
		Counter64,
	rm10010MonupRmonNonunicastCounterClientInputErrorPortn
		EkiOnOff,
	rm10010MonupRmonNonunicastCounterClientInputOverloadPortn
		EkiOnOff
	}


rm10010MonupRmonNonunicastCounterClientInputIndex OBJECT-TYPE
	SYNTAX  INTEGER(0..128)
	MAX-ACCESS  read-only
	STATUS current
	DESCRIPTION
        "
        Index definition for the rm10010MonupRmonNonunicastCounterClientInput
        table
        "
	::= { rm10010MonupRmonNonunicastCounterClientInputEntry 1 }


rm10010MonupRmonNonunicastCounterClientInputValuePortn OBJECT-TYPE
	SYNTAX  Counter64
	MAX-ACCESS read-only
	STATUS current
	DESCRIPTION
        "
        Client Input Non Unicast Packets
        :This counter is increased each
        time a Non-Unicast packet is received
        on the client port  <Help>  This
        counter gives the number of Non-Unicast
        packets received on the client
         port
        "
	::= { rm10010MonupRmonNonunicastCounterClientInputEntry 2 }


rm10010MonupRmonNonunicastCounterClientInputErrorPortn OBJECT-TYPE
	SYNTAX  EkiOnOff
	MAX-ACCESS read-only
	STATUS current
	DESCRIPTION
        "
        Non Unicast Counter Error :This
        OID when set indicates the Non-Unicast
        counter value is invalid on client
        port
        "
	::= { rm10010MonupRmonNonunicastCounterClientInputEntry 3 }


rm10010MonupRmonNonunicastCounterClientInputOverloadPortn OBJECT-TYPE
	SYNTAX  EkiOnOff
	MAX-ACCESS read-only
	STATUS current
	DESCRIPTION
        "
        Non Unicast Counter Overload :This
        OID when set indicates a Non-Unicast
        counter overload on client port
        "
	::= { rm10010MonupRmonNonunicastCounterClientInputEntry 4 }


--- *********************************************************
---     TABLE for the rm10010MondownRmonBytesCounterClientOutput articles
--- *********************************************************

rm10010MondownRmonBytesCounterClientOutputTable OBJECT-TYPE
	SYNTAX  SEQUENCE OF Rm10010MondownRmonBytesCounterClientOutputEntry
	MAX-ACCESS not-accessible
	STATUS current
	DESCRIPTION
        "
        List of rm10010MondownRmonBytesCounterClientOutput
        Article
        "
	::= { rm10010MonClientRmonCounter 208 }


rm10010MondownRmonBytesCounterClientOutputEntry OBJECT-TYPE
	SYNTAX Rm10010MondownRmonBytesCounterClientOutputEntry
	MAX-ACCESS not-accessible
	STATUS current
	DESCRIPTION
        "
        Row definition for the rm10010MondownRmonBytesCounterClientOutput
        table
        "
	INDEX   { rm10010MondownRmonBytesCounterClientOutputIndex }
	::= { rm10010MondownRmonBytesCounterClientOutputTable 1 }


Rm10010MondownRmonBytesCounterClientOutputEntry ::=
	SEQUENCE {
	rm10010MondownRmonBytesCounterClientOutputIndex
		INTEGER,
	rm10010MondownRmonBytesCounterClientOutputValuePortn
		Counter64,
	rm10010MondownRmonBytesCounterClientOutputErrorPortn
		EkiOnOff,
	rm10010MondownRmonBytesCounterClientOutputOverloadPortn
		EkiOnOff
	}


rm10010MondownRmonBytesCounterClientOutputIndex OBJECT-TYPE
	SYNTAX  INTEGER(0..128)
	MAX-ACCESS  read-only
	STATUS current
	DESCRIPTION
        "
        Index definition for the rm10010MondownRmonBytesCounterClientOutput
        table
        "
	::= { rm10010MondownRmonBytesCounterClientOutputEntry 1 }


rm10010MondownRmonBytesCounterClientOutputValuePortn OBJECT-TYPE
	SYNTAX  Counter64
	MAX-ACCESS read-only
	STATUS current
	DESCRIPTION
        "
        Client Output Bytes :This counter
        is increased each time a data byte
        is transmitted on the client port
         <Help>  This counter gives the
        number of bytes transmitted on
         the client port
        "
	::= { rm10010MondownRmonBytesCounterClientOutputEntry 2 }


rm10010MondownRmonBytesCounterClientOutputErrorPortn OBJECT-TYPE
	SYNTAX  EkiOnOff
	MAX-ACCESS read-only
	STATUS current
	DESCRIPTION
        "
        Bytes Counter Error :This OID
         when set indicates the Bytes counter
        value is invalid on client port
        "
	::= { rm10010MondownRmonBytesCounterClientOutputEntry 3 }


rm10010MondownRmonBytesCounterClientOutputOverloadPortn OBJECT-TYPE
	SYNTAX  EkiOnOff
	MAX-ACCESS read-only
	STATUS current
	DESCRIPTION
        "
        Bytes Counter Overload :This OID
        when set indicates a Bytes counter
        overload on client port
        "
	::= { rm10010MondownRmonBytesCounterClientOutputEntry 4 }


--- *********************************************************
---     TABLE for the rm10010MondownRmonCrcErrorsCounterClientOutput articles
--- *********************************************************

rm10010MondownRmonCrcErrorsCounterClientOutputTable OBJECT-TYPE
	SYNTAX  SEQUENCE OF Rm10010MondownRmonCrcErrorsCounterClientOutputEntry
	MAX-ACCESS not-accessible
	STATUS current
	DESCRIPTION
        "
        List of rm10010MondownRmonCrcErrorsCounterClientOutput
        Article
        "
	::= { rm10010MonClientRmonCounter 224 }


rm10010MondownRmonCrcErrorsCounterClientOutputEntry OBJECT-TYPE
	SYNTAX Rm10010MondownRmonCrcErrorsCounterClientOutputEntry
	MAX-ACCESS not-accessible
	STATUS current
	DESCRIPTION
        "
        Row definition for the rm10010MondownRmonCrcErrorsCounterClientOutput
        table
        "
	INDEX   { rm10010MondownRmonCrcErrorsCounterClientOutputIndex }
	::= { rm10010MondownRmonCrcErrorsCounterClientOutputTable 1 }


Rm10010MondownRmonCrcErrorsCounterClientOutputEntry ::=
	SEQUENCE {
	rm10010MondownRmonCrcErrorsCounterClientOutputIndex
		INTEGER,
	rm10010MondownRmonCrcErrorsCounterClientOutputValuePortn
		Counter64,
	rm10010MondownRmonCrcErrorsCounterClientOutputErrorPortn
		EkiOnOff,
	rm10010MondownRmonCrcErrorsCounterClientOutputOverloadPortn
		EkiOnOff
	}


rm10010MondownRmonCrcErrorsCounterClientOutputIndex OBJECT-TYPE
	SYNTAX  INTEGER(0..128)
	MAX-ACCESS  read-only
	STATUS current
	DESCRIPTION
        "
        Index definition for the rm10010MondownRmonCrcErrorsCounterClientOutput
        table
        "
	::= { rm10010MondownRmonCrcErrorsCounterClientOutputEntry 1 }


rm10010MondownRmonCrcErrorsCounterClientOutputValuePortn OBJECT-TYPE
	SYNTAX  Counter64
	MAX-ACCESS read-only
	STATUS current
	DESCRIPTION
        "
        Client Output CRC Errors :This
        counter is increased each time
         a CRC error is detected on the
        transmit client port  <Help>  This
        counter gives the number of CRC
        Errors transmitted on the client
        port
        "
	::= { rm10010MondownRmonCrcErrorsCounterClientOutputEntry 2 }


rm10010MondownRmonCrcErrorsCounterClientOutputErrorPortn OBJECT-TYPE
	SYNTAX  EkiOnOff
	MAX-ACCESS read-only
	STATUS current
	DESCRIPTION
        "
        CRC Errors Counter Error :This
        OID when set indicates the CRC
         Errors counter value is invalid
        on client port
        "
	::= { rm10010MondownRmonCrcErrorsCounterClientOutputEntry 3 }


rm10010MondownRmonCrcErrorsCounterClientOutputOverloadPortn OBJECT-TYPE
	SYNTAX  EkiOnOff
	MAX-ACCESS read-only
	STATUS current
	DESCRIPTION
        "
        CRC Errors Counter Overload :This
        OID when set indicates a CRC Errors
        counter overload on client port
        "
	::= { rm10010MondownRmonCrcErrorsCounterClientOutputEntry 4 }


--- *********************************************************
---     TABLE for the rm10010MondownRmonPacketsCounterClientOutput articles
--- *********************************************************

rm10010MondownRmonPacketsCounterClientOutputTable OBJECT-TYPE
	SYNTAX  SEQUENCE OF Rm10010MondownRmonPacketsCounterClientOutputEntry
	MAX-ACCESS not-accessible
	STATUS current
	DESCRIPTION
        "
        List of rm10010MondownRmonPacketsCounterClientOutput
        Article
        "
	::= { rm10010MonClientRmonCounter 240 }


rm10010MondownRmonPacketsCounterClientOutputEntry OBJECT-TYPE
	SYNTAX Rm10010MondownRmonPacketsCounterClientOutputEntry
	MAX-ACCESS not-accessible
	STATUS current
	DESCRIPTION
        "
        Row definition for the rm10010MondownRmonPacketsCounterClientOutput
        table
        "
	INDEX   { rm10010MondownRmonPacketsCounterClientOutputIndex }
	::= { rm10010MondownRmonPacketsCounterClientOutputTable 1 }


Rm10010MondownRmonPacketsCounterClientOutputEntry ::=
	SEQUENCE {
	rm10010MondownRmonPacketsCounterClientOutputIndex
		INTEGER,
	rm10010MondownRmonPacketsCounterClientOutputValuePortn
		Counter64,
	rm10010MondownRmonPacketsCounterClientOutputErrorPortn
		EkiOnOff,
	rm10010MondownRmonPacketsCounterClientOutputOverloadPortn
		EkiOnOff
	}


rm10010MondownRmonPacketsCounterClientOutputIndex OBJECT-TYPE
	SYNTAX  INTEGER(0..128)
	MAX-ACCESS  read-only
	STATUS current
	DESCRIPTION
        "
        Index definition for the rm10010MondownRmonPacketsCounterClientOutput
        table
        "
	::= { rm10010MondownRmonPacketsCounterClientOutputEntry 1 }


rm10010MondownRmonPacketsCounterClientOutputValuePortn OBJECT-TYPE
	SYNTAX  Counter64
	MAX-ACCESS read-only
	STATUS current
	DESCRIPTION
        "
        Client Output Packets :This counter
        is increased each time a packet
        is transmitted on the client port
         <Help>  This counter gives the
        number of packets transmitted on
        the client port
        "
	::= { rm10010MondownRmonPacketsCounterClientOutputEntry 2 }


rm10010MondownRmonPacketsCounterClientOutputErrorPortn OBJECT-TYPE
	SYNTAX  EkiOnOff
	MAX-ACCESS read-only
	STATUS current
	DESCRIPTION
        "
        Packets Counter Error :This OID
        when set indicates the Packets
         counter value is invalid on client
        port
        "
	::= { rm10010MondownRmonPacketsCounterClientOutputEntry 3 }


rm10010MondownRmonPacketsCounterClientOutputOverloadPortn OBJECT-TYPE
	SYNTAX  EkiOnOff
	MAX-ACCESS read-only
	STATUS current
	DESCRIPTION
        "
        Packets Counter Overload :This
        OID when set indicates a Packets
        counter overload on client port
        "
	::= { rm10010MondownRmonPacketsCounterClientOutputEntry 4 }


--- *********************************************************
---     TABLE for the rm10010MondownRmonBroadcastCounterClientOutput articles
--- *********************************************************

rm10010MondownRmonBroadcastCounterClientOutputTable OBJECT-TYPE
	SYNTAX  SEQUENCE OF Rm10010MondownRmonBroadcastCounterClientOutputEntry
	MAX-ACCESS not-accessible
	STATUS current
	DESCRIPTION
        "
        List of rm10010MondownRmonBroadcastCounterClientOutput
        Article
        "
	::= { rm10010MonClientRmonCounter 256 }


rm10010MondownRmonBroadcastCounterClientOutputEntry OBJECT-TYPE
	SYNTAX Rm10010MondownRmonBroadcastCounterClientOutputEntry
	MAX-ACCESS not-accessible
	STATUS current
	DESCRIPTION
        "
        Row definition for the rm10010MondownRmonBroadcastCounterClientOutput
        table
        "
	INDEX   { rm10010MondownRmonBroadcastCounterClientOutputIndex }
	::= { rm10010MondownRmonBroadcastCounterClientOutputTable 1 }


Rm10010MondownRmonBroadcastCounterClientOutputEntry ::=
	SEQUENCE {
	rm10010MondownRmonBroadcastCounterClientOutputIndex
		INTEGER,
	rm10010MondownRmonBroadcastCounterClientOutputValuePortn
		Counter64,
	rm10010MondownRmonBroadcastCounterClientOutputErrorPortn
		EkiOnOff,
	rm10010MondownRmonBroadcastCounterClientOutputOverloadPortn
		EkiOnOff
	}


rm10010MondownRmonBroadcastCounterClientOutputIndex OBJECT-TYPE
	SYNTAX  INTEGER(0..128)
	MAX-ACCESS  read-only
	STATUS current
	DESCRIPTION
        "
        Index definition for the rm10010MondownRmonBroadcastCounterClientOutput
        table
        "
	::= { rm10010MondownRmonBroadcastCounterClientOutputEntry 1 }


rm10010MondownRmonBroadcastCounterClientOutputValuePortn OBJECT-TYPE
	SYNTAX  Counter64
	MAX-ACCESS read-only
	STATUS current
	DESCRIPTION
        "
        Client Output Broadcast Packets
        :This counter is increased each
        time a broadcast packet is transmitted
        on the client port  <Help>  This
        counter gives the number of Broadcast
        packets transmitted on the client
        port
        "
	::= { rm10010MondownRmonBroadcastCounterClientOutputEntry 2 }


rm10010MondownRmonBroadcastCounterClientOutputErrorPortn OBJECT-TYPE
	SYNTAX  EkiOnOff
	MAX-ACCESS read-only
	STATUS current
	DESCRIPTION
        "
        Broadcast Counter Error :This
         OID when set indicates the Broadcast
        counter value is invalid on client
        port
        "
	::= { rm10010MondownRmonBroadcastCounterClientOutputEntry 3 }


rm10010MondownRmonBroadcastCounterClientOutputOverloadPortn OBJECT-TYPE
	SYNTAX  EkiOnOff
	MAX-ACCESS read-only
	STATUS current
	DESCRIPTION
        "
        Broadcast Counter Overload :This
        OID when set indicates a Broadcast
        counter overload on client port
        "
	::= { rm10010MondownRmonBroadcastCounterClientOutputEntry 4 }


--- *********************************************************
---     TABLE for the rm10010MondownRmonMulticastCounterClientOutput articles
--- *********************************************************

rm10010MondownRmonMulticastCounterClientOutputTable OBJECT-TYPE
	SYNTAX  SEQUENCE OF Rm10010MondownRmonMulticastCounterClientOutputEntry
	MAX-ACCESS not-accessible
	STATUS current
	DESCRIPTION
        "
        List of rm10010MondownRmonMulticastCounterClientOutput
        Article
        "
	::= { rm10010MonClientRmonCounter 272 }


rm10010MondownRmonMulticastCounterClientOutputEntry OBJECT-TYPE
	SYNTAX Rm10010MondownRmonMulticastCounterClientOutputEntry
	MAX-ACCESS not-accessible
	STATUS current
	DESCRIPTION
        "
        Row definition for the rm10010MondownRmonMulticastCounterClientOutput
        table
        "
	INDEX   { rm10010MondownRmonMulticastCounterClientOutputIndex }
	::= { rm10010MondownRmonMulticastCounterClientOutputTable 1 }


Rm10010MondownRmonMulticastCounterClientOutputEntry ::=
	SEQUENCE {
	rm10010MondownRmonMulticastCounterClientOutputIndex
		INTEGER,
	rm10010MondownRmonMulticastCounterClientOutputValuePortn
		Counter64,
	rm10010MondownRmonMulticastCounterClientOutputErrorPortn
		EkiOnOff,
	rm10010MondownRmonMulticastCounterClientOutputOverloadPortn
		EkiOnOff
	}


rm10010MondownRmonMulticastCounterClientOutputIndex OBJECT-TYPE
	SYNTAX  INTEGER(0..128)
	MAX-ACCESS  read-only
	STATUS current
	DESCRIPTION
        "
        Index definition for the rm10010MondownRmonMulticastCounterClientOutput
        table
        "
	::= { rm10010MondownRmonMulticastCounterClientOutputEntry 1 }


rm10010MondownRmonMulticastCounterClientOutputValuePortn OBJECT-TYPE
	SYNTAX  Counter64
	MAX-ACCESS read-only
	STATUS current
	DESCRIPTION
        "
        Client Output Multicast Packets
        :This counter is increased each
        time a Multicast packet is transmitted
        on the client port  <Help>  This
        counter gives the number of Multicast
        packets transmitted on the client
        port
        "
	::= { rm10010MondownRmonMulticastCounterClientOutputEntry 2 }


rm10010MondownRmonMulticastCounterClientOutputErrorPortn OBJECT-TYPE
	SYNTAX  EkiOnOff
	MAX-ACCESS read-only
	STATUS current
	DESCRIPTION
        "
        Multicast Counter Error :This
         OID when set indicates the Multicast
        counter value is invalid on client
        port
        "
	::= { rm10010MondownRmonMulticastCounterClientOutputEntry 3 }


rm10010MondownRmonMulticastCounterClientOutputOverloadPortn OBJECT-TYPE
	SYNTAX  EkiOnOff
	MAX-ACCESS read-only
	STATUS current
	DESCRIPTION
        "
        Multicast Counter Overload :This
        OID when set indicates a Multicast
        counter overload on client port
        "
	::= { rm10010MondownRmonMulticastCounterClientOutputEntry 4 }


--- *********************************************************
---     TABLE for the rm10010MondownRmonPauseFrameCounterClientOutput articles
--- *********************************************************

rm10010MondownRmonPauseFrameCounterClientOutputTable OBJECT-TYPE
	SYNTAX  SEQUENCE OF Rm10010MondownRmonPauseFrameCounterClientOutputEntry
	MAX-ACCESS not-accessible
	STATUS current
	DESCRIPTION
        "
        List of rm10010MondownRmonPauseFrameCounterClientOutput
        Article
        "
	::= { rm10010MonClientRmonCounter 288 }


rm10010MondownRmonPauseFrameCounterClientOutputEntry OBJECT-TYPE
	SYNTAX Rm10010MondownRmonPauseFrameCounterClientOutputEntry
	MAX-ACCESS not-accessible
	STATUS current
	DESCRIPTION
        "
        Row definition for the rm10010MondownRmonPauseFrameCounterClientOutput
        table
        "
	INDEX   { rm10010MondownRmonPauseFrameCounterClientOutputIndex }
	::= { rm10010MondownRmonPauseFrameCounterClientOutputTable 1 }


Rm10010MondownRmonPauseFrameCounterClientOutputEntry ::=
	SEQUENCE {
	rm10010MondownRmonPauseFrameCounterClientOutputIndex
		INTEGER,
	rm10010MondownRmonPauseFrameCounterClientOutputValuePortn
		Counter64,
	rm10010MondownRmonPauseFrameCounterClientOutputErrorPortn
		EkiOnOff,
	rm10010MondownRmonPauseFrameCounterClientOutputOverloadPortn
		EkiOnOff
	}


rm10010MondownRmonPauseFrameCounterClientOutputIndex OBJECT-TYPE
	SYNTAX  INTEGER(0..128)
	MAX-ACCESS  read-only
	STATUS current
	DESCRIPTION
        "
        Index definition for the rm10010MondownRmonPauseFrameCounterClientOutput
        table
        "
	::= { rm10010MondownRmonPauseFrameCounterClientOutputEntry 1 }


rm10010MondownRmonPauseFrameCounterClientOutputValuePortn OBJECT-TYPE
	SYNTAX  Counter64
	MAX-ACCESS read-only
	STATUS current
	DESCRIPTION
        "
        Client Output Pause Frames :This
        counter is increased each time
         a Pause frame is transmitted on
        the client port  <Help>  This counter
        gives the number of Pause frames
        transmitted on the client port
        "
	::= { rm10010MondownRmonPauseFrameCounterClientOutputEntry 2 }


rm10010MondownRmonPauseFrameCounterClientOutputErrorPortn OBJECT-TYPE
	SYNTAX  EkiOnOff
	MAX-ACCESS read-only
	STATUS current
	DESCRIPTION
        "
        Pause Counter Error :This OID
         when set indicates the Pause counter
        value is invalid on client port
        "
	::= { rm10010MondownRmonPauseFrameCounterClientOutputEntry 3 }


rm10010MondownRmonPauseFrameCounterClientOutputOverloadPortn OBJECT-TYPE
	SYNTAX  EkiOnOff
	MAX-ACCESS read-only
	STATUS current
	DESCRIPTION
        "
        Pause Counter Overload :This OID
        when set indicates a Pause counter
        overload on client port
        "
	::= { rm10010MondownRmonPauseFrameCounterClientOutputEntry 4 }


--- *********************************************************
---     TABLE for the rm10010MondownRmonUnicastCounterClientOutput articles
--- *********************************************************

rm10010MondownRmonUnicastCounterClientOutputTable OBJECT-TYPE
	SYNTAX  SEQUENCE OF Rm10010MondownRmonUnicastCounterClientOutputEntry
	MAX-ACCESS not-accessible
	STATUS current
	DESCRIPTION
        "
        List of rm10010MondownRmonUnicastCounterClientOutput
        Article
        "
	::= { rm10010MonClientRmonCounter 352 }


rm10010MondownRmonUnicastCounterClientOutputEntry OBJECT-TYPE
	SYNTAX Rm10010MondownRmonUnicastCounterClientOutputEntry
	MAX-ACCESS not-accessible
	STATUS current
	DESCRIPTION
        "
        Row definition for the rm10010MondownRmonUnicastCounterClientOutput
        table
        "
	INDEX   { rm10010MondownRmonUnicastCounterClientOutputIndex }
	::= { rm10010MondownRmonUnicastCounterClientOutputTable 1 }


Rm10010MondownRmonUnicastCounterClientOutputEntry ::=
	SEQUENCE {
	rm10010MondownRmonUnicastCounterClientOutputIndex
		INTEGER,
	rm10010MondownRmonUnicastCounterClientOutputValuePortn
		Counter64,
	rm10010MondownRmonUnicastCounterClientOutputErrorPortn
		EkiOnOff,
	rm10010MondownRmonUnicastCounterClientOutputOverloadPortn
		EkiOnOff
	}


rm10010MondownRmonUnicastCounterClientOutputIndex OBJECT-TYPE
	SYNTAX  INTEGER(0..128)
	MAX-ACCESS  read-only
	STATUS current
	DESCRIPTION
        "
        Index definition for the rm10010MondownRmonUnicastCounterClientOutput
        table
        "
	::= { rm10010MondownRmonUnicastCounterClientOutputEntry 1 }


rm10010MondownRmonUnicastCounterClientOutputValuePortn OBJECT-TYPE
	SYNTAX  Counter64
	MAX-ACCESS read-only
	STATUS current
	DESCRIPTION
        "
        Client Output Unicast Packets
         :This counter is increased each
        time a Unicast packet is transmitted
        on the client port  <Help>  This
        counter gives the number of Unicast
        packets transmitted on the client
        port
        "
	::= { rm10010MondownRmonUnicastCounterClientOutputEntry 2 }


rm10010MondownRmonUnicastCounterClientOutputErrorPortn OBJECT-TYPE
	SYNTAX  EkiOnOff
	MAX-ACCESS read-only
	STATUS current
	DESCRIPTION
        "
        Unicast Counter Error :This OID
        when set indicates the Unicast
         counter value is invalid on client
        port
        "
	::= { rm10010MondownRmonUnicastCounterClientOutputEntry 3 }


rm10010MondownRmonUnicastCounterClientOutputOverloadPortn OBJECT-TYPE
	SYNTAX  EkiOnOff
	MAX-ACCESS read-only
	STATUS current
	DESCRIPTION
        "
        Unicast Counter Overload :This
        OID when set indicates a Unicast
        counter overload on client port
        "
	::= { rm10010MondownRmonUnicastCounterClientOutputEntry 4 }


--- *********************************************************
---     TABLE for the rm10010MondownRmonNonunicastCounterClientOutput articles
--- *********************************************************

rm10010MondownRmonNonunicastCounterClientOutputTable OBJECT-TYPE
	SYNTAX  SEQUENCE OF Rm10010MondownRmonNonunicastCounterClientOutputEntry
	MAX-ACCESS not-accessible
	STATUS current
	DESCRIPTION
        "
        List of rm10010MondownRmonNonunicastCounterClientOutput
        Article
        "
	::= { rm10010MonClientRmonCounter 368 }


rm10010MondownRmonNonunicastCounterClientOutputEntry OBJECT-TYPE
	SYNTAX Rm10010MondownRmonNonunicastCounterClientOutputEntry
	MAX-ACCESS not-accessible
	STATUS current
	DESCRIPTION
        "
        Row definition for the rm10010MondownRmonNonunicastCounterClientOutput
        table
        "
	INDEX   { rm10010MondownRmonNonunicastCounterClientOutputIndex }
	::= { rm10010MondownRmonNonunicastCounterClientOutputTable 1 }


Rm10010MondownRmonNonunicastCounterClientOutputEntry ::=
	SEQUENCE {
	rm10010MondownRmonNonunicastCounterClientOutputIndex
		INTEGER,
	rm10010MondownRmonNonunicastCounterClientOutputValuePortn
		Counter64,
	rm10010MondownRmonNonunicastCounterClientOutputErrorPortn
		EkiOnOff,
	rm10010MondownRmonNonunicastCounterClientOutputOverloadPortn
		EkiOnOff
	}


rm10010MondownRmonNonunicastCounterClientOutputIndex OBJECT-TYPE
	SYNTAX  INTEGER(0..128)
	MAX-ACCESS  read-only
	STATUS current
	DESCRIPTION
        "
        Index definition for the rm10010MondownRmonNonunicastCounterClientOutput
        table
        "
	::= { rm10010MondownRmonNonunicastCounterClientOutputEntry 1 }


rm10010MondownRmonNonunicastCounterClientOutputValuePortn OBJECT-TYPE
	SYNTAX  Counter64
	MAX-ACCESS read-only
	STATUS current
	DESCRIPTION
        "
        Client Output Non Unicast Packets
        :This counter is increased each
        time a Non-Unicast packet is transmitted
        on the client port  <Help>  This
        counter gives the number of Non-Unicast
        packets transmitted on the client
        port
        "
	::= { rm10010MondownRmonNonunicastCounterClientOutputEntry 2 }


rm10010MondownRmonNonunicastCounterClientOutputErrorPortn OBJECT-TYPE
	SYNTAX  EkiOnOff
	MAX-ACCESS read-only
	STATUS current
	DESCRIPTION
        "
        Non Unicast Counter Error :This
        OID when set indicates the Non-Unicast
        counter value is invalid on client
        port
        "
	::= { rm10010MondownRmonNonunicastCounterClientOutputEntry 3 }


rm10010MondownRmonNonunicastCounterClientOutputOverloadPortn OBJECT-TYPE
	SYNTAX  EkiOnOff
	MAX-ACCESS read-only
	STATUS current
	DESCRIPTION
        "
        Non Unicast Counter Overload :This
        OID when set indicates a Non-Unicast
        counter overload on client port
        "
	::= { rm10010MondownRmonNonunicastCounterClientOutputEntry 4 }







--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



rm10010Mesrsynth0 OBJECT-TYPE
	  SYNTAX EkiMeasureType
	  MAX-ACCESS read-only
	  STATUS deprecated
	  DESCRIPTION
        "
        Not Used :
        "
	  ::= { rm10010MesrOther 0 }



rm10010Mesrsynth1 OBJECT-TYPE
	  SYNTAX EkiMeasureType
	  MAX-ACCESS read-only
	  STATUS deprecated
	  DESCRIPTION
        "
        Not Used :
        "
	  ::= { rm10010MesrOther 1 }



--- *****************************************************
---     LEAF for the pmIntervalNumber article
--- *****************************************************

rm10010MesrpmIntervalNumber OBJECT-TYPE
	  SYNTAX Unsigned32 (0..65535)
	  MAX-ACCESS read-only
	  STATUS current
	  DESCRIPTION
        "
        PM Interval Counter :
        "
	  ::= { rm10010MesrOther 7 }



--- *****************************************************
---     LEAF for the clientCfpTemp article
--- *****************************************************

rm10010MesrclientCfpTemp OBJECT-TYPE
	  SYNTAX Unsigned32 (0..65535)
	  MAX-ACCESS read-only
	  STATUS current
	  DESCRIPTION
        "
        Client Trscv Temperature :This
        OID gives the temperature value
        of the Client Transceiver, read
        from the DDM (Digital Diagnostic
        Monitoring) (Temperature = AV/256)
        (Unit = C) <Help> This Measure
         gives the temperature value of
        the Client Transceiver
        "
	  ::= { rm10010MesrClient 8 }



--- *****************************************************
---     LEAF for the clientCfp3v3Voltage article
--- *****************************************************

rm10010MesrclientCfp3v3Voltage OBJECT-TYPE
	  SYNTAX Unsigned32 (0..65535)
	  MAX-ACCESS read-only
	  STATUS current
	  DESCRIPTION
        "
        Client Trscv Voltage :This OID
        gives the 3V3 voltage value of
         the Client Transceiver, read from
        the DDM (Digital Diagnostic Monitoring)
         (Voltage = AV/1000) (Unit = V)
        <Help> This Measure gives the 3V3
        voltage value of the Client Transceiver
        "
	  ::= { rm10010MesrClient 9 }



--- *****************************************************
---     LEAF for the clientSoaBiasCurrent article
--- *****************************************************

rm10010MesrclientSoaBiasCurrent OBJECT-TYPE
	  SYNTAX Unsigned32 (0..65535)
	  MAX-ACCESS read-only
	  STATUS current
	  DESCRIPTION
        "
        Client Trscv SOA Bias :This OID
        gives the SOA bias value of the
        Client Transceiver, read from the
        DDM (Digital Diagnostic Monitoring)
         (Bias = AV/500) (Unit = mA) <Help>
        This Measure gives the SOA bias
        value of the Client Transceiver
        "
	  ::= { rm10010MesrClient 10 }



--- *****************************************************
---     LEAF for the lineMsaTemp article
--- *****************************************************

rm10010MesrlineMsaTemp OBJECT-TYPE
	  SYNTAX Unsigned32 (0..65535)
	  MAX-ACCESS read-only
	  STATUS current
	  DESCRIPTION
        "
        Line Trscv Temperature :This OID
        gives the temperature value of
         the Line Transceiver, read from
        the DDM (Digital Diagnostic Monitoring)
         (Temperature = AV/256) (Unit =
        C) <Help> This Measure gives the
        temperature value of the Line Transceiver
        "
	  ::= { rm10010MesrLine 12 }



--- *****************************************************
---     LEAF for the lineMsa3v3Voltage article
--- *****************************************************

rm10010MesrlineMsa3v3Voltage OBJECT-TYPE
	  SYNTAX Unsigned32 (0..65535)
	  MAX-ACCESS read-only
	  STATUS current
	  DESCRIPTION
        "
        Line Trscv Voltage :This OID gives
        the 3V3 voltage value of the Line
        Transceiver, read from the DDM
         (Digital Diagnostic Monitoring)
        (Voltage = AV/1000) (Unit = V)
         <Help> This Measure gives the
         3V3 voltage value of the Line
         Transceiver
        "
	  ::= { rm10010MesrLine 13 }



--- *****************************************************
---     LEAF for the lineSoaBiasCurrent article
--- *****************************************************

rm10010MesrlineSoaBiasCurrent OBJECT-TYPE
	  SYNTAX Unsigned32 (0..65535)
	  MAX-ACCESS read-only
	  STATUS current
	  DESCRIPTION
        "
        Line Trscv SOA Bias :This OID
         gives the SOA bias value of the
        Line Transceiver,read from the
         DDM (Digital Diagnostic Monitoring)
         (Bias = AV/500) (Unit = mA) <Help>
        This Measure gives the SOA bias
        value of the Line Transceiver
        "
	  ::= { rm10010MesrLine 14 }



--- *********************************************************
---     TABLE for the rm10010MesrclientNetTxTemp articles
--- *********************************************************

rm10010MesrclientNetTxTempTable OBJECT-TYPE
	SYNTAX  SEQUENCE OF Rm10010MesrclientNetTxTempEntry
	MAX-ACCESS not-accessible
	STATUS current
	DESCRIPTION
        "
        List of rm10010MesrclientNetTxTemp
        Article
        "
	::= { rm10010MesrClient 16 }


rm10010MesrclientNetTxTempEntry OBJECT-TYPE
	SYNTAX Rm10010MesrclientNetTxTempEntry
	MAX-ACCESS not-accessible
	STATUS current
	DESCRIPTION
        "
        Row definition for the rm10010MesrclientNetTxTemp
        table
        "
	INDEX   { rm10010MesrclientNetTxTempIndex }
	::= { rm10010MesrclientNetTxTempTable 1 }


Rm10010MesrclientNetTxTempEntry ::=
	SEQUENCE {
	rm10010MesrclientNetTxTempIndex
		INTEGER,
	rm10010MesrclientNetTxTempPortn
		INTEGER
	}


rm10010MesrclientNetTxTempIndex OBJECT-TYPE
	SYNTAX  INTEGER(0..128)
	MAX-ACCESS  read-only
	STATUS current
	DESCRIPTION
        "
        Index definition for the rm10010MesrclientNetTxTemp
        table
        "
	::= { rm10010MesrclientNetTxTempEntry 1 }


rm10010MesrclientNetTxTempPortn OBJECT-TYPE
	SYNTAX  INTEGER (0..65535)
	MAX-ACCESS read-only
	STATUS current
	DESCRIPTION
        "
        Client Trscv Temperature :This
        OID gives the Laser temperature
        value of the Client Transceiver,
        read from the DDM (Digital Diagnostic
        Monitoring) (Temperature = AV/256)
        (Unit = C) <Help> This Measure
         gives the Laser temperature value
        of the Client Transceiver
        "
	::= { rm10010MesrclientNetTxTempEntry 2 }


--- *********************************************************
---     TABLE for the rm10010MesrclientNetTxBias articles
--- *********************************************************

rm10010MesrclientNetTxBiasTable OBJECT-TYPE
	SYNTAX  SEQUENCE OF Rm10010MesrclientNetTxBiasEntry
	MAX-ACCESS not-accessible
	STATUS current
	DESCRIPTION
        "
        List of rm10010MesrclientNetTxBias
        Article
        "
	::= { rm10010MesrClient 32 }


rm10010MesrclientNetTxBiasEntry OBJECT-TYPE
	SYNTAX Rm10010MesrclientNetTxBiasEntry
	MAX-ACCESS not-accessible
	STATUS current
	DESCRIPTION
        "
        Row definition for the rm10010MesrclientNetTxBias
        table
        "
	INDEX   { rm10010MesrclientNetTxBiasIndex }
	::= { rm10010MesrclientNetTxBiasTable 1 }


Rm10010MesrclientNetTxBiasEntry ::=
	SEQUENCE {
	rm10010MesrclientNetTxBiasIndex
		INTEGER,
	rm10010MesrclientNetTxBiasPortn
		INTEGER
	}


rm10010MesrclientNetTxBiasIndex OBJECT-TYPE
	SYNTAX  INTEGER(0..128)
	MAX-ACCESS  read-only
	STATUS current
	DESCRIPTION
        "
        Index definition for the rm10010MesrclientNetTxBias
        table
        "
	::= { rm10010MesrclientNetTxBiasEntry 1 }


rm10010MesrclientNetTxBiasPortn OBJECT-TYPE
	SYNTAX  INTEGER (0..65535)
	MAX-ACCESS read-only
	STATUS current
	DESCRIPTION
        "
        Client Trscv Laser Bias :This
         OID gives the Laser bias value
        of the Client Transceiver, read
        from the DDM (Digital Diagnostic
        Monitoring) (Bias = AV/500) (Unit
        = mA) <Help> This Measure gives
        the Laser bias value of the Client
        Transceiver
        "
	::= { rm10010MesrclientNetTxBiasEntry 2 }


--- *********************************************************
---     TABLE for the rm10010MesrclientNetTxPwr articles
--- *********************************************************

rm10010MesrclientNetTxPwrTable OBJECT-TYPE
	SYNTAX  SEQUENCE OF Rm10010MesrclientNetTxPwrEntry
	MAX-ACCESS not-accessible
	STATUS current
	DESCRIPTION
        "
        List of rm10010MesrclientNetTxPwr
        Article
        "
	::= { rm10010MesrClient 48 }


rm10010MesrclientNetTxPwrEntry OBJECT-TYPE
	SYNTAX Rm10010MesrclientNetTxPwrEntry
	MAX-ACCESS not-accessible
	STATUS current
	DESCRIPTION
        "
        Row definition for the rm10010MesrclientNetTxPwr
        table
        "
	INDEX   { rm10010MesrclientNetTxPwrIndex }
	::= { rm10010MesrclientNetTxPwrTable 1 }


Rm10010MesrclientNetTxPwrEntry ::=
	SEQUENCE {
	rm10010MesrclientNetTxPwrIndex
		INTEGER,
	rm10010MesrclientNetTxPwrPortn
		INTEGER
	}


rm10010MesrclientNetTxPwrIndex OBJECT-TYPE
	SYNTAX  INTEGER(0..128)
	MAX-ACCESS  read-only
	STATUS current
	DESCRIPTION
        "
        Index definition for the rm10010MesrclientNetTxPwr
        table
        "
	::= { rm10010MesrclientNetTxPwrEntry 1 }


rm10010MesrclientNetTxPwrPortn OBJECT-TYPE
	SYNTAX  INTEGER (0..65535)
	MAX-ACCESS read-only
	STATUS current
	DESCRIPTION
        "
        Client Trscv Tx Power :This OID
        gives the transmit power value
         of the Client Transceiver, read
        from the DDM (Digital Diagnostic
        Monitoring) (Power = 10*log(AV)-40)
        (Unit = dBm) <Help> This Measure
        gives the transmit power value
         of the Client Transceiver
        "
	::= { rm10010MesrclientNetTxPwrEntry 2 }


--- *********************************************************
---     TABLE for the rm10010MesrclientNetRxPwr articles
--- *********************************************************

rm10010MesrclientNetRxPwrTable OBJECT-TYPE
	SYNTAX  SEQUENCE OF Rm10010MesrclientNetRxPwrEntry
	MAX-ACCESS not-accessible
	STATUS current
	DESCRIPTION
        "
        List of rm10010MesrclientNetRxPwr
        Article
        "
	::= { rm10010MesrClient 64 }


rm10010MesrclientNetRxPwrEntry OBJECT-TYPE
	SYNTAX Rm10010MesrclientNetRxPwrEntry
	MAX-ACCESS not-accessible
	STATUS current
	DESCRIPTION
        "
        Row definition for the rm10010MesrclientNetRxPwr
        table
        "
	INDEX   { rm10010MesrclientNetRxPwrIndex }
	::= { rm10010MesrclientNetRxPwrTable 1 }


Rm10010MesrclientNetRxPwrEntry ::=
	SEQUENCE {
	rm10010MesrclientNetRxPwrIndex
		INTEGER,
	rm10010MesrclientNetRxPwrPortn
		INTEGER
	}


rm10010MesrclientNetRxPwrIndex OBJECT-TYPE
	SYNTAX  INTEGER(0..128)
	MAX-ACCESS  read-only
	STATUS current
	DESCRIPTION
        "
        Index definition for the rm10010MesrclientNetRxPwr
        table
        "
	::= { rm10010MesrclientNetRxPwrEntry 1 }


rm10010MesrclientNetRxPwrPortn OBJECT-TYPE
	SYNTAX  INTEGER (0..65535)
	MAX-ACCESS read-only
	STATUS current
	DESCRIPTION
        "
        Client Trscv Rx Power :This OID
        gives the receive power value of
        the Client Transceiver, read in
        the DDM (Digital Diagnostic Monitoring)
        (Power = 10*log(AV)-40) (Unit =
        dBm) <Help> This Measure gives
         the receive power value of the
        Client Transceiver
        "
	::= { rm10010MesrclientNetRxPwrEntry 2 }


--- *********************************************************
---     TABLE for the rm10010MesrlineNetTxLaserOutputPwr articles
--- *********************************************************

rm10010MesrlineNetTxLaserOutputPwrTable OBJECT-TYPE
	SYNTAX  SEQUENCE OF Rm10010MesrlineNetTxLaserOutputPwrEntry
	MAX-ACCESS not-accessible
	STATUS current
	DESCRIPTION
        "
        List of rm10010MesrlineNetTxLaserOutputPwr
        Article
        "
	::= { rm10010MesrLine 80 }


rm10010MesrlineNetTxLaserOutputPwrEntry OBJECT-TYPE
	SYNTAX Rm10010MesrlineNetTxLaserOutputPwrEntry
	MAX-ACCESS not-accessible
	STATUS current
	DESCRIPTION
        "
        Row definition for the rm10010MesrlineNetTxLaserOutputPwr
        table
        "
	INDEX   { rm10010MesrlineNetTxLaserOutputPwrIndex }
	::= { rm10010MesrlineNetTxLaserOutputPwrTable 1 }


Rm10010MesrlineNetTxLaserOutputPwrEntry ::=
	SEQUENCE {
	rm10010MesrlineNetTxLaserOutputPwrIndex
		INTEGER,
	rm10010MesrlineNetTxLaserOutputPwrPortn
		INTEGER
	}


rm10010MesrlineNetTxLaserOutputPwrIndex OBJECT-TYPE
	SYNTAX  INTEGER(0..128)
	MAX-ACCESS  read-only
	STATUS current
	DESCRIPTION
        "
        Index definition for the rm10010MesrlineNetTxLaserOutputPwr
        table
        "
	::= { rm10010MesrlineNetTxLaserOutputPwrEntry 1 }


rm10010MesrlineNetTxLaserOutputPwrPortn OBJECT-TYPE
	SYNTAX  INTEGER (0..65535)
	MAX-ACCESS read-only
	STATUS current
	DESCRIPTION
        "
        Current Line Trscv Tx Power :This
        OID gives the Tx Laser transmit
        power value of the Line Transceiver,
        read in the DDM (Digital Diagnostic
        Monitoring) (Power = AV/100) (Unit
        = dBm) <Help> This Measure gives
        the Tx Laser transmit power value
        of the Line Transceiver
        "
	::= { rm10010MesrlineNetTxLaserOutputPwrEntry 2 }


--- *********************************************************
---     TABLE for the rm10010MesrlineNetTxLaserTemp articles
--- *********************************************************

rm10010MesrlineNetTxLaserTempTable OBJECT-TYPE
	SYNTAX  SEQUENCE OF Rm10010MesrlineNetTxLaserTempEntry
	MAX-ACCESS not-accessible
	STATUS current
	DESCRIPTION
        "
        List of rm10010MesrlineNetTxLaserTemp
        Article
        "
	::= { rm10010MesrLine 96 }


rm10010MesrlineNetTxLaserTempEntry OBJECT-TYPE
	SYNTAX Rm10010MesrlineNetTxLaserTempEntry
	MAX-ACCESS not-accessible
	STATUS current
	DESCRIPTION
        "
        Row definition for the rm10010MesrlineNetTxLaserTemp
        table
        "
	INDEX   { rm10010MesrlineNetTxLaserTempIndex }
	::= { rm10010MesrlineNetTxLaserTempTable 1 }


Rm10010MesrlineNetTxLaserTempEntry ::=
	SEQUENCE {
	rm10010MesrlineNetTxLaserTempIndex
		INTEGER,
	rm10010MesrlineNetTxLaserTempPortn
		INTEGER
	}


rm10010MesrlineNetTxLaserTempIndex OBJECT-TYPE
	SYNTAX  INTEGER(0..128)
	MAX-ACCESS  read-only
	STATUS current
	DESCRIPTION
        "
        Index definition for the rm10010MesrlineNetTxLaserTemp
        table
        "
	::= { rm10010MesrlineNetTxLaserTempEntry 1 }


rm10010MesrlineNetTxLaserTempPortn OBJECT-TYPE
	SYNTAX  INTEGER (0..65535)
	MAX-ACCESS read-only
	STATUS current
	DESCRIPTION
        "
        Current Line Trscv Tx Laser Temperature
        :This OID gives the Tx Laser Temperature
        value of the Line Transceiver,
         read from the DDM (Digital Diagnostic
        Monitoring) (Temperature = AV/256)
        (Unit = C) <Help> This Measure
         gives the Tx Laser Temperature
        value of the Line Transceiver
        "
	::= { rm10010MesrlineNetTxLaserTempEntry 2 }


--- *********************************************************
---     TABLE for the rm10010MesrlineNetTxBiasCurrent articles
--- *********************************************************

rm10010MesrlineNetTxBiasCurrentTable OBJECT-TYPE
	SYNTAX  SEQUENCE OF Rm10010MesrlineNetTxBiasCurrentEntry
	MAX-ACCESS not-accessible
	STATUS current
	DESCRIPTION
        "
        List of rm10010MesrlineNetTxBiasCurrent
        Article
        "
	::= { rm10010MesrLine 112 }


rm10010MesrlineNetTxBiasCurrentEntry OBJECT-TYPE
	SYNTAX Rm10010MesrlineNetTxBiasCurrentEntry
	MAX-ACCESS not-accessible
	STATUS current
	DESCRIPTION
        "
        Row definition for the rm10010MesrlineNetTxBiasCurrent
        table
        "
	INDEX   { rm10010MesrlineNetTxBiasCurrentIndex }
	::= { rm10010MesrlineNetTxBiasCurrentTable 1 }


Rm10010MesrlineNetTxBiasCurrentEntry ::=
	SEQUENCE {
	rm10010MesrlineNetTxBiasCurrentIndex
		INTEGER,
	rm10010MesrlineNetTxBiasCurrentPortn
		INTEGER
	}


rm10010MesrlineNetTxBiasCurrentIndex OBJECT-TYPE
	SYNTAX  INTEGER(0..128)
	MAX-ACCESS  read-only
	STATUS current
	DESCRIPTION
        "
        Index definition for the rm10010MesrlineNetTxBiasCurrent
        table
        "
	::= { rm10010MesrlineNetTxBiasCurrentEntry 1 }


rm10010MesrlineNetTxBiasCurrentPortn OBJECT-TYPE
	SYNTAX  INTEGER (0..65535)
	MAX-ACCESS read-only
	STATUS current
	DESCRIPTION
        "
        Current Line Trscv Tx Laser Bias
        :This OID gives the Tx Laser Bias
        value of the Line Transceiver,
         read from the DDM (Digital Diagnostic
        Monitoring) (Bias = AV/10) (Unit
        = mA) <Help> This Measure gives
        the Tx Laser Bias value of the
         Line Transceiver
        "
	::= { rm10010MesrlineNetTxBiasCurrentEntry 2 }


--- *********************************************************
---     TABLE for the rm10010MesrlineNetRxInputPwr articles
--- *********************************************************

rm10010MesrlineNetRxInputPwrTable OBJECT-TYPE
	SYNTAX  SEQUENCE OF Rm10010MesrlineNetRxInputPwrEntry
	MAX-ACCESS not-accessible
	STATUS current
	DESCRIPTION
        "
        List of rm10010MesrlineNetRxInputPwr
        Article
        "
	::= { rm10010MesrLine 128 }


rm10010MesrlineNetRxInputPwrEntry OBJECT-TYPE
	SYNTAX Rm10010MesrlineNetRxInputPwrEntry
	MAX-ACCESS not-accessible
	STATUS current
	DESCRIPTION
        "
        Row definition for the rm10010MesrlineNetRxInputPwr
        table
        "
	INDEX   { rm10010MesrlineNetRxInputPwrIndex }
	::= { rm10010MesrlineNetRxInputPwrTable 1 }


Rm10010MesrlineNetRxInputPwrEntry ::=
	SEQUENCE {
	rm10010MesrlineNetRxInputPwrIndex
		INTEGER,
	rm10010MesrlineNetRxInputPwrPortn
		INTEGER
	}


rm10010MesrlineNetRxInputPwrIndex OBJECT-TYPE
	SYNTAX  INTEGER(0..128)
	MAX-ACCESS  read-only
	STATUS current
	DESCRIPTION
        "
        Index definition for the rm10010MesrlineNetRxInputPwr
        table
        "
	::= { rm10010MesrlineNetRxInputPwrEntry 1 }


rm10010MesrlineNetRxInputPwrPortn OBJECT-TYPE
	SYNTAX  INTEGER (0..65535)
	MAX-ACCESS read-only
	STATUS current
	DESCRIPTION
        "
        Current Line Trscv Rx Power :This
        OID gives the Receive power value
        of the Line Transceiver, read in
        the DDM (Digital Diagnostic Monitoring)
        (Power = AV/100) (Unit = dBm) <Help>
        This Measure gives the Receive
         power value of the Line Transceiver
        "
	::= { rm10010MesrlineNetRxInputPwrEntry 2 }


--- *********************************************************
---     TABLE for the rm10010MesrlineResidualChromaticDisp articles
--- *********************************************************

rm10010MesrlineResidualChromaticDispTable OBJECT-TYPE
	SYNTAX  SEQUENCE OF Rm10010MesrlineResidualChromaticDispEntry
	MAX-ACCESS not-accessible
	STATUS current
	DESCRIPTION
        "
        List of rm10010MesrlineResidualChromaticDisp
        Article
        "
	::= { rm10010MesrLine 144 }


rm10010MesrlineResidualChromaticDispEntry OBJECT-TYPE
	SYNTAX Rm10010MesrlineResidualChromaticDispEntry
	MAX-ACCESS not-accessible
	STATUS current
	DESCRIPTION
        "
        Row definition for the rm10010MesrlineResidualChromaticDisp
        table
        "
	INDEX   { rm10010MesrlineResidualChromaticDispIndex }
	::= { rm10010MesrlineResidualChromaticDispTable 1 }


Rm10010MesrlineResidualChromaticDispEntry ::=
	SEQUENCE {
	rm10010MesrlineResidualChromaticDispIndex
		INTEGER,
	rm10010MesrlineResidualChromaticDispPortn
		INTEGER
	}


rm10010MesrlineResidualChromaticDispIndex OBJECT-TYPE
	SYNTAX  INTEGER(0..128)
	MAX-ACCESS  read-only
	STATUS current
	DESCRIPTION
        "
        Index definition for the rm10010MesrlineResidualChromaticDisp
        table
        "
	::= { rm10010MesrlineResidualChromaticDispEntry 1 }


rm10010MesrlineResidualChromaticDispPortn OBJECT-TYPE
	SYNTAX  INTEGER (0..65535)
	MAX-ACCESS read-only
	STATUS current
	DESCRIPTION
        "
        Current Residual Chromatic Dispersion
        :This OID gives the current Residual
        Chromatic Dispersion on the Line
        interface  (Unit = ps/nm)<Help>
        This measure gives the current
         Residual Chromatic Dispersion
         on the Line interface.
        "
	::= { rm10010MesrlineResidualChromaticDispEntry 2 }


--- *********************************************************
---     TABLE for the rm10010MesrlineDiffGroupDelay articles
--- *********************************************************

rm10010MesrlineDiffGroupDelayTable OBJECT-TYPE
	SYNTAX  SEQUENCE OF Rm10010MesrlineDiffGroupDelayEntry
	MAX-ACCESS not-accessible
	STATUS current
	DESCRIPTION
        "
        List of rm10010MesrlineDiffGroupDelay
        Article
        "
	::= { rm10010MesrLine 148 }


rm10010MesrlineDiffGroupDelayEntry OBJECT-TYPE
	SYNTAX Rm10010MesrlineDiffGroupDelayEntry
	MAX-ACCESS not-accessible
	STATUS current
	DESCRIPTION
        "
        Row definition for the rm10010MesrlineDiffGroupDelay
        table
        "
	INDEX   { rm10010MesrlineDiffGroupDelayIndex }
	::= { rm10010MesrlineDiffGroupDelayTable 1 }


Rm10010MesrlineDiffGroupDelayEntry ::=
	SEQUENCE {
	rm10010MesrlineDiffGroupDelayIndex
		INTEGER,
	rm10010MesrlineDiffGroupDelayPortn
		INTEGER
	}


rm10010MesrlineDiffGroupDelayIndex OBJECT-TYPE
	SYNTAX  INTEGER(0..128)
	MAX-ACCESS  read-only
	STATUS current
	DESCRIPTION
        "
        Index definition for the rm10010MesrlineDiffGroupDelay
        table
        "
	::= { rm10010MesrlineDiffGroupDelayEntry 1 }


rm10010MesrlineDiffGroupDelayPortn OBJECT-TYPE
	SYNTAX  INTEGER (0..65535)
	MAX-ACCESS read-only
	STATUS current
	DESCRIPTION
        "
        Current Differential Group Delay
        :This OID gives the current Differential
        Group Delay on the Line interface
          (Unit = ps)<Help> This measure
        gives the current Differential
         Group Delay on the Line interface.
        "
	::= { rm10010MesrlineDiffGroupDelayEntry 2 }


--- *********************************************************
---     TABLE for the rm10010MesrlineQFactor articles
--- *********************************************************

rm10010MesrlineQFactorTable OBJECT-TYPE
	SYNTAX  SEQUENCE OF Rm10010MesrlineQFactorEntry
	MAX-ACCESS not-accessible
	STATUS current
	DESCRIPTION
        "
        List of rm10010MesrlineQFactor
        Article
        "
	::= { rm10010MesrLine 152 }


rm10010MesrlineQFactorEntry OBJECT-TYPE
	SYNTAX Rm10010MesrlineQFactorEntry
	MAX-ACCESS not-accessible
	STATUS current
	DESCRIPTION
        "
        Row definition for the rm10010MesrlineQFactor
        table
        "
	INDEX   { rm10010MesrlineQFactorIndex }
	::= { rm10010MesrlineQFactorTable 1 }


Rm10010MesrlineQFactorEntry ::=
	SEQUENCE {
	rm10010MesrlineQFactorIndex
		INTEGER,
	rm10010MesrlineQFactorPortn
		INTEGER
	}


rm10010MesrlineQFactorIndex OBJECT-TYPE
	SYNTAX  INTEGER(0..128)
	MAX-ACCESS  read-only
	STATUS current
	DESCRIPTION
        "
        Index definition for the rm10010MesrlineQFactor
        table
        "
	::= { rm10010MesrlineQFactorEntry 1 }


rm10010MesrlineQFactorPortn OBJECT-TYPE
	SYNTAX  INTEGER (0..65535)
	MAX-ACCESS read-only
	STATUS current
	DESCRIPTION
        "
        Current Q Factor :This OID gives
        the current Q Factor on the Line
        interface   (Unit = dB) <Help>
         This measure gives the current
        Q Factor on the Line interface.
        "
	::= { rm10010MesrlineQFactorEntry 2 }


--- *********************************************************
---     TABLE for the rm10010MesrlineCarrierFreqOffset articles
--- *********************************************************

rm10010MesrlineCarrierFreqOffsetTable OBJECT-TYPE
	SYNTAX  SEQUENCE OF Rm10010MesrlineCarrierFreqOffsetEntry
	MAX-ACCESS not-accessible
	STATUS current
	DESCRIPTION
        "
        List of rm10010MesrlineCarrierFreqOffset
        Article
        "
	::= { rm10010MesrLine 156 }


rm10010MesrlineCarrierFreqOffsetEntry OBJECT-TYPE
	SYNTAX Rm10010MesrlineCarrierFreqOffsetEntry
	MAX-ACCESS not-accessible
	STATUS current
	DESCRIPTION
        "
        Row definition for the rm10010MesrlineCarrierFreqOffset
        table
        "
	INDEX   { rm10010MesrlineCarrierFreqOffsetIndex }
	::= { rm10010MesrlineCarrierFreqOffsetTable 1 }


Rm10010MesrlineCarrierFreqOffsetEntry ::=
	SEQUENCE {
	rm10010MesrlineCarrierFreqOffsetIndex
		INTEGER,
	rm10010MesrlineCarrierFreqOffsetPortn
		INTEGER
	}


rm10010MesrlineCarrierFreqOffsetIndex OBJECT-TYPE
	SYNTAX  INTEGER(0..128)
	MAX-ACCESS  read-only
	STATUS current
	DESCRIPTION
        "
        Index definition for the rm10010MesrlineCarrierFreqOffset
        table
        "
	::= { rm10010MesrlineCarrierFreqOffsetEntry 1 }


rm10010MesrlineCarrierFreqOffsetPortn OBJECT-TYPE
	SYNTAX  INTEGER (0..65535)
	MAX-ACCESS read-only
	STATUS current
	DESCRIPTION
        "
        Current Carrier Frequency Offset
        :This OID gives the current Carrier
        Frequency Offset on the Line interface
          (Unit = Mhz)<Help> This measure
        gives the current Carrier Frequency
        Offset on the Line interface.
        "
	::= { rm10010MesrlineCarrierFreqOffsetEntry 2 }


--- *********************************************************
---     TABLE for the rm10010MesrlineOsnr articles
--- *********************************************************

rm10010MesrlineOsnrTable OBJECT-TYPE
	SYNTAX  SEQUENCE OF Rm10010MesrlineOsnrEntry
	MAX-ACCESS not-accessible
	STATUS current
	DESCRIPTION
        "
        List of rm10010MesrlineOsnr Article
        "
	::= { rm10010MesrLine 160 }


rm10010MesrlineOsnrEntry OBJECT-TYPE
	SYNTAX Rm10010MesrlineOsnrEntry
	MAX-ACCESS not-accessible
	STATUS current
	DESCRIPTION
        "
        Row definition for the rm10010MesrlineOsnr
        table
        "
	INDEX   { rm10010MesrlineOsnrIndex }
	::= { rm10010MesrlineOsnrTable 1 }


Rm10010MesrlineOsnrEntry ::=
	SEQUENCE {
	rm10010MesrlineOsnrIndex
		INTEGER,
	rm10010MesrlineOsnrPortn
		INTEGER
	}


rm10010MesrlineOsnrIndex OBJECT-TYPE
	SYNTAX  INTEGER(0..128)
	MAX-ACCESS  read-only
	STATUS current
	DESCRIPTION
        "
        Index definition for the rm10010MesrlineOsnr
        table
        "
	::= { rm10010MesrlineOsnrEntry 1 }


rm10010MesrlineOsnrPortn OBJECT-TYPE
	SYNTAX  INTEGER (0..65535)
	MAX-ACCESS read-only
	STATUS current
	DESCRIPTION
        "
        Current OSNR :This OID gives the
        current OSNR on the Line interface
          (OSNR = AV/10) (Unit = dB)<Help>
        This measure gives the current
         OSNR on the Line interface.
        "
	::= { rm10010MesrlineOsnrEntry 2 }


--- *****************************************************
---     LEAF for the lineNetTxLaserOutputPwrAverage article
--- *****************************************************

rm10010MesrlineNetTxLaserOutputPwrAverage OBJECT-TYPE
	  SYNTAX Unsigned32 (0..65535)
	  MAX-ACCESS read-only
	  STATUS current
	  DESCRIPTION
        "
        Average Line Trscv Tx Power :This
        OID gives the average Tx Laser
         transmit power value among the
        network lanes of the Line Transceiver,
        read in the DDM (Digital Diagnostic
        Monitoring)  (Power = AV/100) (Unit
        = dBm) (Unit = dBm) <Help> This
        Measure gives the average Tx Laser
        transmit power value among the
         network lanes of the Line Transceiver
        "
	  ::= { rm10010MesrOther 180 }



--- *****************************************************
---     LEAF for the lineNetTxLaserTempAverage article
--- *****************************************************

rm10010MesrlineNetTxLaserTempAverage OBJECT-TYPE
	  SYNTAX Unsigned32 (0..65535)
	  MAX-ACCESS read-only
	  STATUS current
	  DESCRIPTION
        "
        Average Line Trscv Tx Laser Temperature
        :This OID gives the average Tx
         Laser Temperature value among
         the network lanes of the Line
         Transceiver, read from the DDM
        (Digital Diagnostic Monitoring)
        (Temperature = AV/256) (Unit =
         C) <Help> This Measure gives the
        average Tx Laser Temperature value
        among the network lanes of the
         Line Transceiver
        "
	  ::= { rm10010MesrOther 181 }



--- *****************************************************
---     LEAF for the lineNetTxBiasCurrentAverage article
--- *****************************************************

rm10010MesrlineNetTxBiasCurrentAverage OBJECT-TYPE
	  SYNTAX Unsigned32 (0..65535)
	  MAX-ACCESS read-only
	  STATUS current
	  DESCRIPTION
        "
        Average Line Trscv Tx Laser Bias
        :This OID gives the average Tx
         Laser Bias value among the network
        lanes of the Line Transceiver,
         read from the DDM (Digital Diagnostic
        Monitoring) (Bias = AV/10) (Unit
        = mA) <Help> This Measure gives
        the average Tx Laser Bias value
        among the network lanes of the
         Line Transceiver
        "
	  ::= { rm10010MesrOther 182 }



--- *****************************************************
---     LEAF for the lineNetRxInputPwrAverage article
--- *****************************************************

rm10010MesrlineNetRxInputPwrAverage OBJECT-TYPE
	  SYNTAX Unsigned32 (0..65535)
	  MAX-ACCESS read-only
	  STATUS current
	  DESCRIPTION
        "
        Average Line Trscv Rx Power :This
        OID gives the average Receive power
        value among the network lanes of
        the Line Transceiver, read in the
        DDM (Digital Diagnostic Monitoring)
        (Power = AV/100) (Unit = dBm) <Help>
        This Measure gives the average
         Receive power value among the
         network lanes of the Line Transceiver
        "
	  ::= { rm10010MesrOther 183 }



--- *****************************************************
---     LEAF for the lineResidualChromaticDispAverage article
--- *****************************************************

rm10010MesrlineResidualChromaticDispAverage OBJECT-TYPE
	  SYNTAX Unsigned32 (0..65535)
	  MAX-ACCESS read-only
	  STATUS current
	  DESCRIPTION
        "
        Average Residual Chromatic Dispersion
        :This OID gives the average Residual
        Chromatic Dispersion on the Line
        interface since the last measure
        reset <Help> This measure gives
        the average Residual Chromatic
         Dispersion on the Line interface
        since the last measure reset.
        "
	  ::= { rm10010MesrOther 184 }



--- *****************************************************
---     LEAF for the lineDiffGroupDelayAverage article
--- *****************************************************

rm10010MesrlineDiffGroupDelayAverage OBJECT-TYPE
	  SYNTAX Unsigned32 (0..65535)
	  MAX-ACCESS read-only
	  STATUS current
	  DESCRIPTION
        "
        Average Differential Group Delay
        :This OID gives the average Group
        Delay on the Line interface since
        the last measure reset <Help> This
        measure gives the average Differential
        Group Delay on the Line interface
        since the last measure reset.
        "
	  ::= { rm10010MesrOther 185 }



--- *****************************************************
---     LEAF for the lineQFactorAverage article
--- *****************************************************

rm10010MesrlineQFactorAverage OBJECT-TYPE
	  SYNTAX Unsigned32 (0..65535)
	  MAX-ACCESS read-only
	  STATUS current
	  DESCRIPTION
        "
        Average Q Factor :This OID gives
        the average Q Factor on the Line
        interface since the last measure
        reset <Help> This measure gives
        the average Q Factor on the Line
        interface since the last measure
        reset.
        "
	  ::= { rm10010MesrOther 186 }



--- *****************************************************
---     LEAF for the lineCarrierFreqOffsetAverage article
--- *****************************************************

rm10010MesrlineCarrierFreqOffsetAverage OBJECT-TYPE
	  SYNTAX Unsigned32 (0..65535)
	  MAX-ACCESS read-only
	  STATUS current
	  DESCRIPTION
        "
        Average Carrier Frequency Offset
        :This OID gives the average Carrier
        Frequency Offset on the Line interface
        since the last measure reset <Help>
        This measure gives the average
         Carrier Frequency Offset on the
        Line interface since the last measure
        reset
        "
	  ::= { rm10010MesrOther 187 }



--- *****************************************************
---     LEAF for the lineOsnrAverage article
--- *****************************************************

rm10010MesrlineOsnrAverage OBJECT-TYPE
	  SYNTAX Unsigned32 (0..65535)
	  MAX-ACCESS read-only
	  STATUS current
	  DESCRIPTION
        "
        Average OSNR :This OID gives the
        average OSNR on the Line interface
        since the last measure reset <Help>
        This measure gives the average
         OSNR on the Line interface since
        the last measure reset.
        "
	  ::= { rm10010MesrOther 188 }



--- *****************************************************
---     LEAF for the clientNetTxTempMin article
--- *****************************************************

rm10010MesrclientNetTxTempMin OBJECT-TYPE
	  SYNTAX Unsigned32 (0..65535)
	  MAX-ACCESS read-only
	  STATUS current
	  DESCRIPTION
        "
        Min Client Trscv Laser Temperature
        :This OID gives the minimum Laser
        temperature value among the network
        lanes of the Client Transceiver,
        read from the DDM (Digital Diagnostic
        Monitoring) (Temperature = AV/256)
        (Unit = C) <Help> This Measure
         gives the minimum Laser temperature
        value among the network lanes of
        the Client Transceiver
        "
	  ::= { rm10010MesrOther 192 }



--- *****************************************************
---     LEAF for the clientNetTxBiasMin article
--- *****************************************************

rm10010MesrclientNetTxBiasMin OBJECT-TYPE
	  SYNTAX Unsigned32 (0..65535)
	  MAX-ACCESS read-only
	  STATUS current
	  DESCRIPTION
        "
        Min Client Trscv Laser Bias :This
        OID gives the minimum Laser bias
        value among the network lanes of
        the Client Transceiver, read from
        the DDM (Digital Diagnostic Monitoring)
        (Bias = AV/500) (Unit = mA) <Help>
        This Measure gives the minimum
         Laser bias value among the network
        lanes of the Client Transceiver
        "
	  ::= { rm10010MesrOther 193 }



--- *****************************************************
---     LEAF for the clientNetTxPwrMin article
--- *****************************************************

rm10010MesrclientNetTxPwrMin OBJECT-TYPE
	  SYNTAX Unsigned32 (0..65535)
	  MAX-ACCESS read-only
	  STATUS current
	  DESCRIPTION
        "
        Min Client Trscv Tx Power :This
        OID gives the minimum transmit
         power value among the network
         lanes of the Client Transceiver,
        read from the DDM (Digital Diagnostic
        Monitoring) (Power = 10*log(AV)-40)
        (Unit = dBm) <Help> This Measure
        gives the minimum transmit power
        value among the network lanes of
        the Client Transceiver
        "
	  ::= { rm10010MesrOther 194 }



--- *****************************************************
---     LEAF for the clientNetRxPwrMin article
--- *****************************************************

rm10010MesrclientNetRxPwrMin OBJECT-TYPE
	  SYNTAX Unsigned32 (0..65535)
	  MAX-ACCESS read-only
	  STATUS current
	  DESCRIPTION
        "
        Min Client Trscv Rx Power :This
        OID gives the minimum receive power
        value among the network lanes of
        the Client Transceiver, read in
        the DDM (Digital Diagnostic Monitoring)
        (Power = 10*log(AV)-40) (Unit =
        dBm) <Help> This Measure gives
         the minimum receive power value
        among the network lanes of the
         Client Transceiver
        "
	  ::= { rm10010MesrOther 195 }



--- *****************************************************
---     LEAF for the lineNetTxLaserOutputPwrMin article
--- *****************************************************

rm10010MesrlineNetTxLaserOutputPwrMin OBJECT-TYPE
	  SYNTAX Unsigned32 (0..65535)
	  MAX-ACCESS read-only
	  STATUS current
	  DESCRIPTION
        "
        Min Line Trscv Tx Power :This
         OID gives the minimum Tx Laser
        transmit power value among the
         network lanes of the Line Transceiver,
        read in the DDM (Digital Diagnostic
        Monitoring)  (Power = AV/100) (Unit
        = dBm) (Unit = dBm) <Help> This
        Measure gives the minimum Tx Laser
        transmit power value among the
         network lanes of the Line Transceiver
        "
	  ::= { rm10010MesrOther 196 }



--- *****************************************************
---     LEAF for the lineNetTxLaserTempMin article
--- *****************************************************

rm10010MesrlineNetTxLaserTempMin OBJECT-TYPE
	  SYNTAX Unsigned32 (0..65535)
	  MAX-ACCESS read-only
	  STATUS current
	  DESCRIPTION
        "
        Min Line Trscv Tx Laser Temperature
        :This OID gives the minimum Tx
         Laser Temperature value among
         the network lanes of the Line
         Transceiver, read from the DDM
        (Digital Diagnostic Monitoring)
        (Temperature = AV/256) (Unit =
         C) <Help> This Measure gives the
        minimum Tx Laser Temperature value
        among the network lanes of the
         Line Transceiver
        "
	  ::= { rm10010MesrOther 197 }



--- *****************************************************
---     LEAF for the lineNetTxBiasCurrentMin article
--- *****************************************************

rm10010MesrlineNetTxBiasCurrentMin OBJECT-TYPE
	  SYNTAX Unsigned32 (0..65535)
	  MAX-ACCESS read-only
	  STATUS current
	  DESCRIPTION
        "
        Min Line Trscv Tx Laser Bias :This
        OID gives the minimum Tx Laser
         Bias value among the network lanes
        of the Line Transceiver, read from
        the DDM (Digital Diagnostic Monitoring)
        (Bias = AV/10) (Unit = mA) <Help>
        This Measure gives the minimum
         Tx Laser Bias value among the
         network lanes of the Line Transceiver
        "
	  ::= { rm10010MesrOther 198 }



--- *****************************************************
---     LEAF for the lineNetRxInputPwrMin article
--- *****************************************************

rm10010MesrlineNetRxInputPwrMin OBJECT-TYPE
	  SYNTAX Unsigned32 (0..65535)
	  MAX-ACCESS read-only
	  STATUS current
	  DESCRIPTION
        "
        Min Line Trscv Rx Power :This
         OID gives the minimum Receive
         power value among the network
         lanes of the Line Transceiver,
        read in the DDM (Digital Diagnostic
        Monitoring) (Power = AV/100) (Unit
        = dBm) <Help> This Measure gives
        the minimum Receive power value
        among the network lanes of the
         Line Transceiver
        "
	  ::= { rm10010MesrOther 199 }



--- *****************************************************
---     LEAF for the lineResidualChromaticDispMin article
--- *****************************************************

rm10010MesrlineResidualChromaticDispMin OBJECT-TYPE
	  SYNTAX Unsigned32 (0..65535)
	  MAX-ACCESS read-only
	  STATUS current
	  DESCRIPTION
        "
        Min Residual Chromatic Dispersion
        :This OID gives the minimum Residual
        Chromatic Dispersion on the Line
        interface since the last measure
        reset  (Unit = ps/nm)<Help> This
        measure gives the minimum Residual
        Chromatic Dispersion on the Line
        interface since the last measure
        reset.
        "
	  ::= { rm10010MesrOther 200 }



--- *****************************************************
---     LEAF for the lineDiffGroupDelayMin article
--- *****************************************************

rm10010MesrlineDiffGroupDelayMin OBJECT-TYPE
	  SYNTAX Unsigned32 (0..65535)
	  MAX-ACCESS read-only
	  STATUS current
	  DESCRIPTION
        "
        Min Differential Group Delay :This
        OID gives the minimum Differential
        Group Delay  on the Line interface
        since the last measure reset  (Unit
        = ps)<Help> This measure gives
         the minimum Differential Group
        Delay on the Line interface since
        the last measure reset.
        "
	  ::= { rm10010MesrOther 201 }



--- *****************************************************
---     LEAF for the lineQFactorMin article
--- *****************************************************

rm10010MesrlineQFactorMin OBJECT-TYPE
	  SYNTAX Unsigned32 (0..65535)
	  MAX-ACCESS read-only
	  STATUS current
	  DESCRIPTION
        "
        Min Q Factor :This OID gives the
        minimum Q Factor on the Line interface
        since the last measure reset  (Unit
        = dB)<Help> This measure gives
         the minimum Q Factor on the Line
        interface since the last measure
        reset.
        "
	  ::= { rm10010MesrOther 202 }



--- *****************************************************
---     LEAF for the lineCarrierFreqOffsetMin article
--- *****************************************************

rm10010MesrlineCarrierFreqOffsetMin OBJECT-TYPE
	  SYNTAX Unsigned32 (0..65535)
	  MAX-ACCESS read-only
	  STATUS current
	  DESCRIPTION
        "
        Min Carrier Frequency Offset :This
        OID gives the minimum Carrier Frequency
        Offset on the Line interface since
        the last measure reset  (Unit =
        Mhz)<Help> This measure gives the
        minimum Carrier Frequency Offset
        on the Line interface since the
        last measure reset
        "
	  ::= { rm10010MesrOther 203 }



--- *****************************************************
---     LEAF for the lineOsnrMin article
--- *****************************************************

rm10010MesrlineOsnrMin OBJECT-TYPE
	  SYNTAX Unsigned32 (0..65535)
	  MAX-ACCESS read-only
	  STATUS current
	  DESCRIPTION
        "
        Min OSNR :This OID gives the minimum
        OSNR on the Line interface since
        the last measure reset  (OSNR =
        AV/10) (Unit = dB)<Help> This measure
        gives the minimum OSNR on the Line
        interface since the last measure
        reset.
        "
	  ::= { rm10010MesrOther 204 }



--- *****************************************************
---     LEAF for the clientNetTxTempMax article
--- *****************************************************

rm10010MesrclientNetTxTempMax OBJECT-TYPE
	  SYNTAX Unsigned32 (0..65535)
	  MAX-ACCESS read-only
	  STATUS current
	  DESCRIPTION
        "
        Max Client Trscv Laser Temperature
        :This OID gives the maximum Laser
        temperature value among the network
        lanes of the Client Transceiver,
        read from the DDM (Digital Diagnostic
        Monitoring) (Temperature = AV/256)
        (Unit = C) <Help> This Measure
         gives the maximum Laser temperature
        value among the network lanes of
        the Client Transceiver
        "
	  ::= { rm10010MesrOther 208 }



--- *****************************************************
---     LEAF for the clientNetTxBiasMax article
--- *****************************************************

rm10010MesrclientNetTxBiasMax OBJECT-TYPE
	  SYNTAX Unsigned32 (0..65535)
	  MAX-ACCESS read-only
	  STATUS current
	  DESCRIPTION
        "
        Max Client Trscv Laser Bias :This
        OID gives the maximum Laser bias
        value among the network lanes of
        the Client Transceiver, read from
        the DDM (Digital Diagnostic Monitoring)
        (Bias = AV/500) (Unit = mA) <Help>
        This Measure gives the maximum
         Laser bias value among the network
        lanes of the Client Transceiver
        "
	  ::= { rm10010MesrOther 209 }



--- *****************************************************
---     LEAF for the clientNetTxPwrMax article
--- *****************************************************

rm10010MesrclientNetTxPwrMax OBJECT-TYPE
	  SYNTAX Unsigned32 (0..65535)
	  MAX-ACCESS read-only
	  STATUS current
	  DESCRIPTION
        "
        Max Client Trscv Tx Power :This
        OID gives the maximum transmit
         power value among the network
         lanes of the Client Transceiver,
        read from the DDM (Digital Diagnostic
        Monitoring) (Power = 10*log(AV)-40)
        (Unit = dBm) <Help> This Measure
        gives the maximum transmit power
        value among the network lanes of
        the Client Transceiver
        "
	  ::= { rm10010MesrOther 210 }



--- *****************************************************
---     LEAF for the clientNetRxPwrMax article
--- *****************************************************

rm10010MesrclientNetRxPwrMax OBJECT-TYPE
	  SYNTAX Unsigned32 (0..65535)
	  MAX-ACCESS read-only
	  STATUS current
	  DESCRIPTION
        "
        Max Client Trscv Rx Power :This
        OID gives the maximum receive power
        value among the network lanes of
        the Client Transceiver, read in
        the DDM (Digital Diagnostic Monitoring)
        (Power = 10*log(AV)-40) (Unit =
        dBm) <Help> This Measure gives
         the maximum receive power value
        among the network lanes of the
         Client Transceiver
        "
	  ::= { rm10010MesrOther 211 }



--- *****************************************************
---     LEAF for the lineNetTxLaserOutputPwrMax article
--- *****************************************************

rm10010MesrlineNetTxLaserOutputPwrMax OBJECT-TYPE
	  SYNTAX Unsigned32 (0..65535)
	  MAX-ACCESS read-only
	  STATUS current
	  DESCRIPTION
        "
        Max Line Trscv Tx Power :This
         OID gives the maximum Tx Laser
        transmit power value among the
         network lanes of the Line Transceiver,
        read in the DDM (Digital Diagnostic
        Monitoring) (Power = 10*log(AV)-40)
        (Unit = dBm) <Help> This Measure
        gives the maximum Tx Laser transmit
        power value among the network lanes
        of the Line Transceiver
        "
	  ::= { rm10010MesrOther 212 }



--- *****************************************************
---     LEAF for the lineNetTxLaserTempMax article
--- *****************************************************

rm10010MesrlineNetTxLaserTempMax OBJECT-TYPE
	  SYNTAX Unsigned32 (0..65535)
	  MAX-ACCESS read-only
	  STATUS current
	  DESCRIPTION
        "
        Max Line Trscv Tx Laser Temperature
        :This OID gives the maximum Tx
         Laser Temperature value among
         the network lanes of the Line
         Transceiver, read from the DDM
        (Digital Diagnostic Monitoring)
        (Temperature = AV/256) (Unit =
         C) <Help> This Measure gives the
        maximum Tx Laser Temperature value
        among the network lanes of the
         Line Transceiver
        "
	  ::= { rm10010MesrOther 213 }



--- *****************************************************
---     LEAF for the lineNetTxBiasCurrentMax article
--- *****************************************************

rm10010MesrlineNetTxBiasCurrentMax OBJECT-TYPE
	  SYNTAX Unsigned32 (0..65535)
	  MAX-ACCESS read-only
	  STATUS current
	  DESCRIPTION
        "
        Max Line Trscv Tx Laser Bias :This
        OID gives the maximum Tx Laser
         Bias value among the network lanes
        of the Line Transceiver, read from
        the DDM (Digital Diagnostic Monitoring)
        (Bias = AV/10) (Unit = mA) <Help>
        This Measure gives the maximum
         Tx Laser Bias value among the
         network lanes of the Line Transceiver
        "
	  ::= { rm10010MesrOther 214 }



--- *****************************************************
---     LEAF for the lineNetRxInputPwrMax article
--- *****************************************************

rm10010MesrlineNetRxInputPwrMax OBJECT-TYPE
	  SYNTAX Unsigned32 (0..65535)
	  MAX-ACCESS read-only
	  STATUS current
	  DESCRIPTION
        "
        Max Line Trscv Rx Power :This
         OID gives the maximum Receive
         power value among the network
         lanes of the Line Transceiver,
        read in the DDM (Digital Diagnostic
        Monitoring) (Power = 10*log(AV)-40)
        (Unit = dBm) <Help> This Measure
        gives the maximum Receive power
        value among the network lanes of
        the Line Transceiver
        "
	  ::= { rm10010MesrOther 215 }



--- *****************************************************
---     LEAF for the lineResidualChromaticDispMax article
--- *****************************************************

rm10010MesrlineResidualChromaticDispMax OBJECT-TYPE
	  SYNTAX Unsigned32 (0..65535)
	  MAX-ACCESS read-only
	  STATUS current
	  DESCRIPTION
        "
        Max Residual Chromatic Dispersion
        :This OID gives the maximum Residual
        Chromatic Dispersion on the Line
        interface since the last measure
        reset  (Unit = ps/nm)<Help> This
        measure gives the maximum Residual
        Chromatic Dispersion on the Line
        interface since the last measure
        reset.
        "
	  ::= { rm10010MesrOther 216 }



--- *****************************************************
---     LEAF for the lineDiffGroupDelayMax article
--- *****************************************************

rm10010MesrlineDiffGroupDelayMax OBJECT-TYPE
	  SYNTAX Unsigned32 (0..65535)
	  MAX-ACCESS read-only
	  STATUS current
	  DESCRIPTION
        "
        Max Differential Group Delay :This
        OID gives the maximum Differential
        Group Delay  on the Line interface
        since the last measure reset
         (Unit = ps)<Help> This measure
        gives the maximum Differential
         Group Delay on the Line interface
        since the last measure reset.
        "
	  ::= { rm10010MesrOther 217 }



--- *****************************************************
---     LEAF for the lineQFactorMax article
--- *****************************************************

rm10010MesrlineQFactorMax OBJECT-TYPE
	  SYNTAX Unsigned32 (0..65535)
	  MAX-ACCESS read-only
	  STATUS current
	  DESCRIPTION
        "
        Max Q Factor :This OID gives the
        maximum Q Factor on the Line interface
        since the last measure reset  (Unit
        = dB)<Help> This measure gives
         the maximum Q Factor on the Line
        interface since the last measure
        reset.
        "
	  ::= { rm10010MesrOther 218 }



--- *****************************************************
---     LEAF for the lineCarrierFreqOffsetMax article
--- *****************************************************

rm10010MesrlineCarrierFreqOffsetMax OBJECT-TYPE
	  SYNTAX Unsigned32 (0..65535)
	  MAX-ACCESS read-only
	  STATUS current
	  DESCRIPTION
        "
        Max Carrier Frequency Offset :This
        OID gives the maximum Carrier Frequency
        Offset on the Line interface since
        the last measure reset   (Unit
         = Mhz)<Help> This measure gives
        the maximum Carrier Frequency Offset
        on the Line interface since the
        last measure reset.
        "
	  ::= { rm10010MesrOther 219 }



--- *****************************************************
---     LEAF for the lineOsnrMax article
--- *****************************************************

rm10010MesrlineOsnrMax OBJECT-TYPE
	  SYNTAX Unsigned32 (0..65535)
	  MAX-ACCESS read-only
	  STATUS current
	  DESCRIPTION
        "
        Max OSNR :This OID gives the maximum
        OSNR on the Line interface since
        the last measure reset   (OSNR
         = AV/10) (Unit = dB)<Help> This
        measure gives the maximum OSNR
         on the Line interface since the
        last measure reset
        "
	  ::= { rm10010MesrOther 220 }








--- *****************************************************
--- $$$$$$$$$$$$$$$$$$$$$$$$$$$$$$$$$$$$$$$$$$$$$$$$$$$$$
---     PERFORMANCE
--- $$$$$$$$$$$$$$$$$$$$$$$$$$$$$$$$$$$$$$$$$$$$$$$$$$$$$
--- *****************************************************



--- *****************************************************
---     Leaf of the telecomInputClientCurrent15Stat
--- *****************************************************
--- *********************************************************
---     TABLE for the rm10010PerfTelecomInputClientCurrent15Stat articles
--- *********************************************************

rm10010PerfTelecomInputClientCurrent15StatTable OBJECT-TYPE
	SYNTAX  SEQUENCE OF Rm10010PerfTelecomInputClientCurrent15StatEntry
	MAX-ACCESS not-accessible
	STATUS current
	DESCRIPTION
        "
        List of rm10010PerfTelecomInputClientCurrent15Stat
        Article
        "
	::= { rm10010MonPerfClient 16 }


rm10010PerfTelecomInputClientCurrent15StatEntry OBJECT-TYPE
	SYNTAX Rm10010PerfTelecomInputClientCurrent15StatEntry
	MAX-ACCESS not-accessible
	STATUS current
	DESCRIPTION
        "
        Row definition for the rm10010PerfTelecomInputClientCurrent15Stat
        table
        "
	INDEX   { rm10010PerfTelecomInputClientCurrent15StatIndex }
	::= { rm10010PerfTelecomInputClientCurrent15StatTable 1 }


Rm10010PerfTelecomInputClientCurrent15StatEntry ::=
	SEQUENCE {
	rm10010PerfTelecomInputClientCurrent15StatIndex
		INTEGER,
	rm10010PerfTelecomInputClientCurrent15StatInvCvPortn
		EkiOnOff,
	rm10010PerfTelecomInputClientCurrent15StatCvValuePortn
		Unsigned32,
	rm10010PerfTelecomInputClientCurrent15StatInvEsPortn
		EkiOnOff,
	rm10010PerfTelecomInputClientCurrent15StatEsValuePortn
		Unsigned32,
	rm10010PerfTelecomInputClientCurrent15StatInvSesPortn
		EkiOnOff,
	rm10010PerfTelecomInputClientCurrent15StatSesValuePortn
		Unsigned32,
	rm10010PerfTelecomInputClientCurrent15StatInvSefsPortn
		EkiOnOff,
	rm10010PerfTelecomInputClientCurrent15StatSefsValuePortn
		Unsigned32,
	rm10010PerfTelecomInputClientCurrent15StatInvUasPortn
		EkiOnOff,
	rm10010PerfTelecomInputClientCurrent15StatUasValuePortn
		Unsigned32
	}


rm10010PerfTelecomInputClientCurrent15StatIndex OBJECT-TYPE
	SYNTAX  INTEGER(0..128)
	MAX-ACCESS  read-only
	STATUS current
	DESCRIPTION
        "
        Index definition for the rm10010PerfTelecomInputClientCurrent15Stat
        table
        "
	::= { rm10010PerfTelecomInputClientCurrent15StatEntry 1 }


rm10010PerfTelecomInputClientCurrent15StatInvCvPortn OBJECT-TYPE
	SYNTAX  EkiOnOff
	MAX-ACCESS read-only
	STATUS current
	DESCRIPTION
        "
        Current 15-min EBC counter inv.
        :This OID indicates that the current
        15-min Coding Violation counter
        is invalid
        "
	::= { rm10010PerfTelecomInputClientCurrent15StatEntry 2 }


rm10010PerfTelecomInputClientCurrent15StatCvValuePortn OBJECT-TYPE
	SYNTAX  Unsigned32
	MAX-ACCESS read-only
	STATUS current
	DESCRIPTION
        "
        Current 15-min EBC counter :This
        OID gives the current 15-min Coding
        Violation counter value
        "
	::= { rm10010PerfTelecomInputClientCurrent15StatEntry 3 }


rm10010PerfTelecomInputClientCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { rm10010PerfTelecomInputClientCurrent15StatEntry 4 }


rm10010PerfTelecomInputClientCurrent15StatEsValuePortn OBJECT-TYPE
	SYNTAX  Unsigned32
	MAX-ACCESS read-only
	STATUS current
	DESCRIPTION
        "
        Current 15-min ES counter :This
        OID gives the current 15-min Errored
        Second counter value
        "
	::= { rm10010PerfTelecomInputClientCurrent15StatEntry 5 }


rm10010PerfTelecomInputClientCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { rm10010PerfTelecomInputClientCurrent15StatEntry 6 }


rm10010PerfTelecomInputClientCurrent15StatSesValuePortn OBJECT-TYPE
	SYNTAX  Unsigned32
	MAX-ACCESS read-only
	STATUS current
	DESCRIPTION
        "
        Current 15-min SES counter :This
        OID gives the current 15-min severely
        Errored Second counter value
        "
	::= { rm10010PerfTelecomInputClientCurrent15StatEntry 7 }


rm10010PerfTelecomInputClientCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { rm10010PerfTelecomInputClientCurrent15StatEntry 8 }


rm10010PerfTelecomInputClientCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { rm10010PerfTelecomInputClientCurrent15StatEntry 9 }


rm10010PerfTelecomInputClientCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { rm10010PerfTelecomInputClientCurrent15StatEntry 10 }


rm10010PerfTelecomInputClientCurrent15StatUasValuePortn OBJECT-TYPE
	SYNTAX  Unsigned32
	MAX-ACCESS read-only
	STATUS current
	DESCRIPTION
        "
        Current 15-min UAS counter :This
        OID gives the current 15-min UnAvailable
        Second counter value
        "
	::= { rm10010PerfTelecomInputClientCurrent15StatEntry 11 }


--- *****************************************************
---     Leaf of the telecomInputClientPast15Stat
--- *****************************************************
--- *********************************************************
---     TABLE for the rm10010PerfTelecomInputClientPast15StatHistory articles
--- *********************************************************

rm10010PerfTelecomInputClientPast15StatHistoryPort1Table OBJECT-TYPE
	SYNTAX  SEQUENCE OF Rm10010PerfTelecomInputClientPast15StatHistoryPort1Entry
	MAX-ACCESS not-accessible
	STATUS current
	DESCRIPTION
        "
        List of rm10010PerfTelecomInputClientPast15StatHistory
        Article
        "
	::= { rm10010MonPerfClient 32 }


rm10010PerfTelecomInputClientPast15StatHistoryPort1Entry OBJECT-TYPE
	SYNTAX Rm10010PerfTelecomInputClientPast15StatHistoryPort1Entry
	MAX-ACCESS not-accessible
	STATUS current
	DESCRIPTION
        "
        Row definition for the rm10010PerfTelecomInputClientPast15StatHistory
        table
        "
	INDEX   { rm10010PerfTelecomInputClientPast15StatHistoryPort1Index }
	::= { rm10010PerfTelecomInputClientPast15StatHistoryPort1Table 1 }


Rm10010PerfTelecomInputClientPast15StatHistoryPort1Entry ::=
	SEQUENCE {
	rm10010PerfTelecomInputClientPast15StatHistoryPort1Index
		INTEGER,
	rm10010PerfTelecomInputClientPast15StatHistoryInvCvPort1
		EkiOnOff,
	rm10010PerfTelecomInputClientPast15StatHistoryCvValuePort1
		Unsigned32,
	rm10010PerfTelecomInputClientPast15StatHistoryInvEsPort1
		EkiOnOff,
	rm10010PerfTelecomInputClientPast15StatHistoryEsValuePort1
		Unsigned32,
	rm10010PerfTelecomInputClientPast15StatHistoryInvSesPort1
		EkiOnOff,
	rm10010PerfTelecomInputClientPast15StatHistorySesValuePort1
		Unsigned32,
	rm10010PerfTelecomInputClientPast15StatHistoryInvSefsPort1
		EkiOnOff,
	rm10010PerfTelecomInputClientPast15StatHistorySefsValuePort1
		Unsigned32,
	rm10010PerfTelecomInputClientPast15StatHistoryInvUasPort1
		EkiOnOff,
	rm10010PerfTelecomInputClientPast15StatHistoryUasValuePort1
		Unsigned32
	}


rm10010PerfTelecomInputClientPast15StatHistoryPort1Index OBJECT-TYPE
	SYNTAX  INTEGER(0..128)
	MAX-ACCESS  read-only
	STATUS current
	DESCRIPTION
        "
        Index definition for the rm10010PerfTelecomInputClientPast15StatHistory
        table
        "
	::= { rm10010PerfTelecomInputClientPast15StatHistoryPort1Entry 1 }


rm10010PerfTelecomInputClientPast15StatHistoryInvCvPort1 OBJECT-TYPE
	SYNTAX  EkiOnOff
	MAX-ACCESS read-only
	STATUS current
	DESCRIPTION
        "
        Previous 15-min EBC counter inv.
        :This OID indicates that the previous
        15-min Coding Violation counter
        is invalid
        "
	::= { rm10010PerfTelecomInputClientPast15StatHistoryPort1Entry 2 }


rm10010PerfTelecomInputClientPast15StatHistoryCvValuePort1 OBJECT-TYPE
	SYNTAX  Unsigned32
	MAX-ACCESS read-only
	STATUS current
	DESCRIPTION
        "
        Previous 15-min EBC counter :This
        OID gives the previous 15-min Coding
        Violation counter value
        "
	::= { rm10010PerfTelecomInputClientPast15StatHistoryPort1Entry 3 }


rm10010PerfTelecomInputClientPast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { rm10010PerfTelecomInputClientPast15StatHistoryPort1Entry 4 }


rm10010PerfTelecomInputClientPast15StatHistoryEsValuePort1 OBJECT-TYPE
	SYNTAX  Unsigned32
	MAX-ACCESS read-only
	STATUS current
	DESCRIPTION
        "
        Previous 15-min ES counter :This
        OID gives the previous 15-min Errored
        Second counter value
        "
	::= { rm10010PerfTelecomInputClientPast15StatHistoryPort1Entry 5 }


rm10010PerfTelecomInputClientPast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { rm10010PerfTelecomInputClientPast15StatHistoryPort1Entry 6 }


rm10010PerfTelecomInputClientPast15StatHistorySesValuePort1 OBJECT-TYPE
	SYNTAX  Unsigned32
	MAX-ACCESS read-only
	STATUS current
	DESCRIPTION
        "
        Previous 15-min SES counter :This
        OID gives the previous 15-min severely
        Errored Second counter value
        "
	::= { rm10010PerfTelecomInputClientPast15StatHistoryPort1Entry 7 }


rm10010PerfTelecomInputClientPast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { rm10010PerfTelecomInputClientPast15StatHistoryPort1Entry 8 }


rm10010PerfTelecomInputClientPast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { rm10010PerfTelecomInputClientPast15StatHistoryPort1Entry 9 }


rm10010PerfTelecomInputClientPast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { rm10010PerfTelecomInputClientPast15StatHistoryPort1Entry 10 }


rm10010PerfTelecomInputClientPast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { rm10010PerfTelecomInputClientPast15StatHistoryPort1Entry 11 }


--- *****************************************************
---     Leaf of the telecomInputClientCurrent24Stat
--- *****************************************************
--- *********************************************************
---     TABLE for the rm10010PerfTelecomInputClientCurrent24Stat articles
--- *********************************************************

rm10010PerfTelecomInputClientCurrent24StatTable OBJECT-TYPE
	SYNTAX  SEQUENCE OF Rm10010PerfTelecomInputClientCurrent24StatEntry
	MAX-ACCESS not-accessible
	STATUS current
	DESCRIPTION
        "
        List of rm10010PerfTelecomInputClientCurrent24Stat
        Article
        "
	::= { rm10010MonPerfClient 48 }


rm10010PerfTelecomInputClientCurrent24StatEntry OBJECT-TYPE
	SYNTAX Rm10010PerfTelecomInputClientCurrent24StatEntry
	MAX-ACCESS not-accessible
	STATUS current
	DESCRIPTION
        "
        Row definition for the rm10010PerfTelecomInputClientCurrent24Stat
        table
        "
	INDEX   { rm10010PerfTelecomInputClientCurrent24StatIndex }
	::= { rm10010PerfTelecomInputClientCurrent24StatTable 1 }


Rm10010PerfTelecomInputClientCurrent24StatEntry ::=
	SEQUENCE {
	rm10010PerfTelecomInputClientCurrent24StatIndex
		INTEGER,
	rm10010PerfTelecomInputClientCurrent24StatInvCvPortn
		EkiOnOff,
	rm10010PerfTelecomInputClientCurrent24StatCvValuePortn
		Unsigned32,
	rm10010PerfTelecomInputClientCurrent24StatInvEsPortn
		EkiOnOff,
	rm10010PerfTelecomInputClientCurrent24StatEsValuePortn
		Unsigned32,
	rm10010PerfTelecomInputClientCurrent24StatInvSesPortn
		EkiOnOff,
	rm10010PerfTelecomInputClientCurrent24StatSesValuePortn
		Unsigned32,
	rm10010PerfTelecomInputClientCurrent24StatInvSefsPortn
		EkiOnOff,
	rm10010PerfTelecomInputClientCurrent24StatSefsValuePortn
		Unsigned32,
	rm10010PerfTelecomInputClientCurrent24StatInvUasPortn
		EkiOnOff,
	rm10010PerfTelecomInputClientCurrent24StatUasValuePortn
		Unsigned32
	}


rm10010PerfTelecomInputClientCurrent24StatIndex OBJECT-TYPE
	SYNTAX  INTEGER(0..128)
	MAX-ACCESS  read-only
	STATUS current
	DESCRIPTION
        "
        Index definition for the rm10010PerfTelecomInputClientCurrent24Stat
        table
        "
	::= { rm10010PerfTelecomInputClientCurrent24StatEntry 1 }


rm10010PerfTelecomInputClientCurrent24StatInvCvPortn OBJECT-TYPE
	SYNTAX  EkiOnOff
	MAX-ACCESS read-only
	STATUS current
	DESCRIPTION
        "
        Current 24-hours EBC counter inv.
        :This OID indicates that the current
        24-hours Coding Violation counter
        is invalid
        "
	::= { rm10010PerfTelecomInputClientCurrent24StatEntry 2 }


rm10010PerfTelecomInputClientCurrent24StatCvValuePortn OBJECT-TYPE
	SYNTAX  Unsigned32
	MAX-ACCESS read-only
	STATUS current
	DESCRIPTION
        "
        Current 24-hours EBC counter :This
        OID gives the current 24-hours
         Coding Violation counter value
        "
	::= { rm10010PerfTelecomInputClientCurrent24StatEntry 3 }


rm10010PerfTelecomInputClientCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { rm10010PerfTelecomInputClientCurrent24StatEntry 4 }


rm10010PerfTelecomInputClientCurrent24StatEsValuePortn OBJECT-TYPE
	SYNTAX  Unsigned32
	MAX-ACCESS read-only
	STATUS current
	DESCRIPTION
        "
        Current 24-hours ES counter :This
        OID gives the current 24-hours
         Errored Second counter value
        "
	::= { rm10010PerfTelecomInputClientCurrent24StatEntry 5 }


rm10010PerfTelecomInputClientCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { rm10010PerfTelecomInputClientCurrent24StatEntry 6 }


rm10010PerfTelecomInputClientCurrent24StatSesValuePortn OBJECT-TYPE
	SYNTAX  Unsigned32
	MAX-ACCESS read-only
	STATUS current
	DESCRIPTION
        "
        Current 24-hours SES counter :This
        OID gives the current 24-hours
         severely Errored Second counter
        value
        "
	::= { rm10010PerfTelecomInputClientCurrent24StatEntry 7 }


rm10010PerfTelecomInputClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { rm10010PerfTelecomInputClientCurrent24StatEntry 8 }


rm10010PerfTelecomInputClientCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { rm10010PerfTelecomInputClientCurrent24StatEntry 9 }


rm10010PerfTelecomInputClientCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { rm10010PerfTelecomInputClientCurrent24StatEntry 10 }


rm10010PerfTelecomInputClientCurrent24StatUasValuePortn OBJECT-TYPE
	SYNTAX  Unsigned32
	MAX-ACCESS read-only
	STATUS current
	DESCRIPTION
        "
        Current 24-hours UAS counter :This
        OID gives the current 24-hours
         UnAvailable Second counter value
        "
	::= { rm10010PerfTelecomInputClientCurrent24StatEntry 11 }


--- *****************************************************
---     Leaf of the telecomInputClientPast24Stat
--- *****************************************************
--- *********************************************************
---     TABLE for the rm10010PerfTelecomInputClientPast24StatHistory articles
--- *********************************************************

rm10010PerfTelecomInputClientPast24StatHistoryPort1Table OBJECT-TYPE
	SYNTAX  SEQUENCE OF Rm10010PerfTelecomInputClientPast24StatHistoryPort1Entry
	MAX-ACCESS not-accessible
	STATUS current
	DESCRIPTION
        "
        List of rm10010PerfTelecomInputClientPast24StatHistory
        Article
        "
	::= { rm10010MonPerfClient 64 }


rm10010PerfTelecomInputClientPast24StatHistoryPort1Entry OBJECT-TYPE
	SYNTAX Rm10010PerfTelecomInputClientPast24StatHistoryPort1Entry
	MAX-ACCESS not-accessible
	STATUS current
	DESCRIPTION
        "
        Row definition for the rm10010PerfTelecomInputClientPast24StatHistory
        table
        "
	INDEX   { rm10010PerfTelecomInputClientPast24StatHistoryPort1Index }
	::= { rm10010PerfTelecomInputClientPast24StatHistoryPort1Table 1 }


Rm10010PerfTelecomInputClientPast24StatHistoryPort1Entry ::=
	SEQUENCE {
	rm10010PerfTelecomInputClientPast24StatHistoryPort1Index
		INTEGER,
	rm10010PerfTelecomInputClientPast24StatHistoryInvCvPort1
		EkiOnOff,
	rm10010PerfTelecomInputClientPast24StatHistoryCvValuePort1
		Unsigned32,
	rm10010PerfTelecomInputClientPast24StatHistoryInvEsPort1
		EkiOnOff,
	rm10010PerfTelecomInputClientPast24StatHistoryEsValuePort1
		Unsigned32,
	rm10010PerfTelecomInputClientPast24StatHistoryInvSesPort1
		EkiOnOff,
	rm10010PerfTelecomInputClientPast24StatHistorySesValuePort1
		Unsigned32,
	rm10010PerfTelecomInputClientPast24StatHistoryInvSefsPort1
		EkiOnOff,
	rm10010PerfTelecomInputClientPast24StatHistorySefsValuePort1
		Unsigned32,
	rm10010PerfTelecomInputClientPast24StatHistoryInvUasPort1
		EkiOnOff,
	rm10010PerfTelecomInputClientPast24StatHistoryUasValuePort1
		Unsigned32
	}


rm10010PerfTelecomInputClientPast24StatHistoryPort1Index OBJECT-TYPE
	SYNTAX  INTEGER(0..128)
	MAX-ACCESS  read-only
	STATUS current
	DESCRIPTION
        "
        Index definition for the rm10010PerfTelecomInputClientPast24StatHistory
        table
        "
	::= { rm10010PerfTelecomInputClientPast24StatHistoryPort1Entry 1 }


rm10010PerfTelecomInputClientPast24StatHistoryInvCvPort1 OBJECT-TYPE
	SYNTAX  EkiOnOff
	MAX-ACCESS read-only
	STATUS current
	DESCRIPTION
        "
        Previous 24-hours EBC counter
         inv. :This OID indicates that
         the previous 24-hours Coding Violation
        counter is invalid
        "
	::= { rm10010PerfTelecomInputClientPast24StatHistoryPort1Entry 2 }


rm10010PerfTelecomInputClientPast24StatHistoryCvValuePort1 OBJECT-TYPE
	SYNTAX  Unsigned32
	MAX-ACCESS read-only
	STATUS current
	DESCRIPTION
        "
        Previous 24-hours EBC counter
         :This OID gives the previous 24-hours
        Coding Violation counter value
        "
	::= { rm10010PerfTelecomInputClientPast24StatHistoryPort1Entry 3 }


rm10010PerfTelecomInputClientPast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { rm10010PerfTelecomInputClientPast24StatHistoryPort1Entry 4 }


rm10010PerfTelecomInputClientPast24StatHistoryEsValuePort1 OBJECT-TYPE
	SYNTAX  Unsigned32
	MAX-ACCESS read-only
	STATUS current
	DESCRIPTION
        "
        Previous 24-hours ES counter :This
        OID gives the previous 24-hours
        Errored Second counter value
        "
	::= { rm10010PerfTelecomInputClientPast24StatHistoryPort1Entry 5 }


rm10010PerfTelecomInputClientPast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { rm10010PerfTelecomInputClientPast24StatHistoryPort1Entry 6 }


rm10010PerfTelecomInputClientPast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { rm10010PerfTelecomInputClientPast24StatHistoryPort1Entry 7 }


rm10010PerfTelecomInputClientPast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { rm10010PerfTelecomInputClientPast24StatHistoryPort1Entry 8 }


rm10010PerfTelecomInputClientPast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { rm10010PerfTelecomInputClientPast24StatHistoryPort1Entry 9 }


rm10010PerfTelecomInputClientPast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { rm10010PerfTelecomInputClientPast24StatHistoryPort1Entry 10 }


rm10010PerfTelecomInputClientPast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { rm10010PerfTelecomInputClientPast24StatHistoryPort1Entry 11 }


--- *****************************************************
---     Leaf of the telecomOutputClientCurrent15Stat
--- *****************************************************
--- *********************************************************
---     TABLE for the rm10010PerfTelecomOutputClientCurrent15Stat articles
--- *********************************************************

rm10010PerfTelecomOutputClientCurrent15StatTable OBJECT-TYPE
	SYNTAX  SEQUENCE OF Rm10010PerfTelecomOutputClientCurrent15StatEntry
	MAX-ACCESS not-accessible
	STATUS current
	DESCRIPTION
        "
        List of rm10010PerfTelecomOutputClientCurrent15Stat
        Article
        "
	::= { rm10010MonPerfClient 80 }


rm10010PerfTelecomOutputClientCurrent15StatEntry OBJECT-TYPE
	SYNTAX Rm10010PerfTelecomOutputClientCurrent15StatEntry
	MAX-ACCESS not-accessible
	STATUS current
	DESCRIPTION
        "
        Row definition for the rm10010PerfTelecomOutputClientCurrent15Stat
        table
        "
	INDEX   { rm10010PerfTelecomOutputClientCurrent15StatIndex }
	::= { rm10010PerfTelecomOutputClientCurrent15StatTable 1 }


Rm10010PerfTelecomOutputClientCurrent15StatEntry ::=
	SEQUENCE {
	rm10010PerfTelecomOutputClientCurrent15StatIndex
		INTEGER,
	rm10010PerfTelecomOutputClientCurrent15StatInvCvPortn
		EkiOnOff,
	rm10010PerfTelecomOutputClientCurrent15StatCvValuePortn
		Unsigned32,
	rm10010PerfTelecomOutputClientCurrent15StatInvEsPortn
		EkiOnOff,
	rm10010PerfTelecomOutputClientCurrent15StatEsValuePortn
		Unsigned32,
	rm10010PerfTelecomOutputClientCurrent15StatInvSesPortn
		EkiOnOff,
	rm10010PerfTelecomOutputClientCurrent15StatSesValuePortn
		Unsigned32,
	rm10010PerfTelecomOutputClientCurrent15StatInvSefsPortn
		EkiOnOff,
	rm10010PerfTelecomOutputClientCurrent15StatSefsValuePortn
		Unsigned32,
	rm10010PerfTelecomOutputClientCurrent15StatInvUasPortn
		EkiOnOff,
	rm10010PerfTelecomOutputClientCurrent15StatUasValuePortn
		Unsigned32
	}


rm10010PerfTelecomOutputClientCurrent15StatIndex OBJECT-TYPE
	SYNTAX  INTEGER(0..128)
	MAX-ACCESS  read-only
	STATUS current
	DESCRIPTION
        "
        Index definition for the rm10010PerfTelecomOutputClientCurrent15Stat
        table
        "
	::= { rm10010PerfTelecomOutputClientCurrent15StatEntry 1 }


rm10010PerfTelecomOutputClientCurrent15StatInvCvPortn OBJECT-TYPE
	SYNTAX  EkiOnOff
	MAX-ACCESS read-only
	STATUS current
	DESCRIPTION
        "
        Current 15-min EBC counter inv.
        :This OID indicates that the current
        15-min Coding Violation counter
        is invalid
        "
	::= { rm10010PerfTelecomOutputClientCurrent15StatEntry 2 }


rm10010PerfTelecomOutputClientCurrent15StatCvValuePortn OBJECT-TYPE
	SYNTAX  Unsigned32
	MAX-ACCESS read-only
	STATUS current
	DESCRIPTION
        "
        Current 15-min EBC counter :This
        OID gives the current 15-min Coding
        Violation counter value
        "
	::= { rm10010PerfTelecomOutputClientCurrent15StatEntry 3 }


rm10010PerfTelecomOutputClientCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { rm10010PerfTelecomOutputClientCurrent15StatEntry 4 }


rm10010PerfTelecomOutputClientCurrent15StatEsValuePortn OBJECT-TYPE
	SYNTAX  Unsigned32
	MAX-ACCESS read-only
	STATUS current
	DESCRIPTION
        "
        Current 15-min ES counter :This
        OID gives the current 15-min Errored
        Second counter value
        "
	::= { rm10010PerfTelecomOutputClientCurrent15StatEntry 5 }


rm10010PerfTelecomOutputClientCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { rm10010PerfTelecomOutputClientCurrent15StatEntry 6 }


rm10010PerfTelecomOutputClientCurrent15StatSesValuePortn OBJECT-TYPE
	SYNTAX  Unsigned32
	MAX-ACCESS read-only
	STATUS current
	DESCRIPTION
        "
        Current 15-min SES counter :This
        OID gives the current 15-min severely
        Errored Second counter value
        "
	::= { rm10010PerfTelecomOutputClientCurrent15StatEntry 7 }


rm10010PerfTelecomOutputClientCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { rm10010PerfTelecomOutputClientCurrent15StatEntry 8 }


rm10010PerfTelecomOutputClientCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { rm10010PerfTelecomOutputClientCurrent15StatEntry 9 }


rm10010PerfTelecomOutputClientCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { rm10010PerfTelecomOutputClientCurrent15StatEntry 10 }


rm10010PerfTelecomOutputClientCurrent15StatUasValuePortn OBJECT-TYPE
	SYNTAX  Unsigned32
	MAX-ACCESS read-only
	STATUS current
	DESCRIPTION
        "
        Current 15-min UAS counter :This
        OID gives the current 15-min UnAvailable
        Second counter value
        "
	::= { rm10010PerfTelecomOutputClientCurrent15StatEntry 11 }


--- *****************************************************
---     Leaf of the telecomOutputClientPast15Stat
--- *****************************************************
--- *********************************************************
---     TABLE for the rm10010PerfTelecomOutputClientPast15StatHistory articles
--- *********************************************************

rm10010PerfTelecomOutputClientPast15StatHistoryPort1Table OBJECT-TYPE
	SYNTAX  SEQUENCE OF Rm10010PerfTelecomOutputClientPast15StatHistoryPort1Entry
	MAX-ACCESS not-accessible
	STATUS current
	DESCRIPTION
        "
        List of rm10010PerfTelecomOutputClientPast15StatHistory
        Article
        "
	::= { rm10010MonPerfClient 96 }


rm10010PerfTelecomOutputClientPast15StatHistoryPort1Entry OBJECT-TYPE
	SYNTAX Rm10010PerfTelecomOutputClientPast15StatHistoryPort1Entry
	MAX-ACCESS not-accessible
	STATUS current
	DESCRIPTION
        "
        Row definition for the rm10010PerfTelecomOutputClientPast15StatHistory
        table
        "
	INDEX   { rm10010PerfTelecomOutputClientPast15StatHistoryPort1Index }
	::= { rm10010PerfTelecomOutputClientPast15StatHistoryPort1Table 1 }


Rm10010PerfTelecomOutputClientPast15StatHistoryPort1Entry ::=
	SEQUENCE {
	rm10010PerfTelecomOutputClientPast15StatHistoryPort1Index
		INTEGER,
	rm10010PerfTelecomOutputClientPast15StatHistoryInvCvPort1
		EkiOnOff,
	rm10010PerfTelecomOutputClientPast15StatHistoryCvValuePort1
		Unsigned32,
	rm10010PerfTelecomOutputClientPast15StatHistoryInvEsPort1
		EkiOnOff,
	rm10010PerfTelecomOutputClientPast15StatHistoryEsValuePort1
		Unsigned32,
	rm10010PerfTelecomOutputClientPast15StatHistoryInvSesPort1
		EkiOnOff,
	rm10010PerfTelecomOutputClientPast15StatHistorySesValuePort1
		Unsigned32,
	rm10010PerfTelecomOutputClientPast15StatHistoryInvSefsPort1
		EkiOnOff,
	rm10010PerfTelecomOutputClientPast15StatHistorySefsValuePort1
		Unsigned32,
	rm10010PerfTelecomOutputClientPast15StatHistoryInvUasPort1
		EkiOnOff,
	rm10010PerfTelecomOutputClientPast15StatHistoryUasValuePort1
		Unsigned32
	}


rm10010PerfTelecomOutputClientPast15StatHistoryPort1Index OBJECT-TYPE
	SYNTAX  INTEGER(0..128)
	MAX-ACCESS  read-only
	STATUS current
	DESCRIPTION
        "
        Index definition for the rm10010PerfTelecomOutputClientPast15StatHistory
        table
        "
	::= { rm10010PerfTelecomOutputClientPast15StatHistoryPort1Entry 1 }


rm10010PerfTelecomOutputClientPast15StatHistoryInvCvPort1 OBJECT-TYPE
	SYNTAX  EkiOnOff
	MAX-ACCESS read-only
	STATUS current
	DESCRIPTION
        "
        Previous 15-min EBC counter inv.
        :This OID indicates that the previous
        15-min Coding Violation counter
        is invalid
        "
	::= { rm10010PerfTelecomOutputClientPast15StatHistoryPort1Entry 2 }


rm10010PerfTelecomOutputClientPast15StatHistoryCvValuePort1 OBJECT-TYPE
	SYNTAX  Unsigned32
	MAX-ACCESS read-only
	STATUS current
	DESCRIPTION
        "
        Previous 15-min EBC counter :This
        OID gives the previous 15-min Coding
        Violation counter value
        "
	::= { rm10010PerfTelecomOutputClientPast15StatHistoryPort1Entry 3 }


rm10010PerfTelecomOutputClientPast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { rm10010PerfTelecomOutputClientPast15StatHistoryPort1Entry 4 }


rm10010PerfTelecomOutputClientPast15StatHistoryEsValuePort1 OBJECT-TYPE
	SYNTAX  Unsigned32
	MAX-ACCESS read-only
	STATUS current
	DESCRIPTION
        "
        Previous 15-min ES counter :This
        OID gives the previous 15-min Errored
        Second counter value
        "
	::= { rm10010PerfTelecomOutputClientPast15StatHistoryPort1Entry 5 }


rm10010PerfTelecomOutputClientPast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { rm10010PerfTelecomOutputClientPast15StatHistoryPort1Entry 6 }


rm10010PerfTelecomOutputClientPast15StatHistorySesValuePort1 OBJECT-TYPE
	SYNTAX  Unsigned32
	MAX-ACCESS read-only
	STATUS current
	DESCRIPTION
        "
        Previous 15-min SES counter :This
        OID gives the previous 15-min severely
        Errored Second counter value
        "
	::= { rm10010PerfTelecomOutputClientPast15StatHistoryPort1Entry 7 }


rm10010PerfTelecomOutputClientPast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { rm10010PerfTelecomOutputClientPast15StatHistoryPort1Entry 8 }


rm10010PerfTelecomOutputClientPast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { rm10010PerfTelecomOutputClientPast15StatHistoryPort1Entry 9 }


rm10010PerfTelecomOutputClientPast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { rm10010PerfTelecomOutputClientPast15StatHistoryPort1Entry 10 }


rm10010PerfTelecomOutputClientPast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { rm10010PerfTelecomOutputClientPast15StatHistoryPort1Entry 11 }


--- *****************************************************
---     Leaf of the telecomOutputClientCurrent24Stat
--- *****************************************************
--- *********************************************************
---     TABLE for the rm10010PerfTelecomOutputClientCurrent24Stat articles
--- *********************************************************

rm10010PerfTelecomOutputClientCurrent24StatTable OBJECT-TYPE
	SYNTAX  SEQUENCE OF Rm10010PerfTelecomOutputClientCurrent24StatEntry
	MAX-ACCESS not-accessible
	STATUS current
	DESCRIPTION
        "
        List of rm10010PerfTelecomOutputClientCurrent24Stat
        Article
        "
	::= { rm10010MonPerfClient 112 }


rm10010PerfTelecomOutputClientCurrent24StatEntry OBJECT-TYPE
	SYNTAX Rm10010PerfTelecomOutputClientCurrent24StatEntry
	MAX-ACCESS not-accessible
	STATUS current
	DESCRIPTION
        "
        Row definition for the rm10010PerfTelecomOutputClientCurrent24Stat
        table
        "
	INDEX   { rm10010PerfTelecomOutputClientCurrent24StatIndex }
	::= { rm10010PerfTelecomOutputClientCurrent24StatTable 1 }


Rm10010PerfTelecomOutputClientCurrent24StatEntry ::=
	SEQUENCE {
	rm10010PerfTelecomOutputClientCurrent24StatIndex
		INTEGER,
	rm10010PerfTelecomOutputClientCurrent24StatInvCvPortn
		EkiOnOff,
	rm10010PerfTelecomOutputClientCurrent24StatCvValuePortn
		Unsigned32,
	rm10010PerfTelecomOutputClientCurrent24StatInvEsPortn
		EkiOnOff,
	rm10010PerfTelecomOutputClientCurrent24StatEsValuePortn
		Unsigned32,
	rm10010PerfTelecomOutputClientCurrent24StatInvSesPortn
		EkiOnOff,
	rm10010PerfTelecomOutputClientCurrent24StatSesValuePortn
		Unsigned32,
	rm10010PerfTelecomOutputClientCurrent24StatInvSefsPortn
		EkiOnOff,
	rm10010PerfTelecomOutputClientCurrent24StatSefsValuePortn
		Unsigned32,
	rm10010PerfTelecomOutputClientCurrent24StatInvUasPortn
		EkiOnOff,
	rm10010PerfTelecomOutputClientCurrent24StatUasValuePortn
		Unsigned32
	}


rm10010PerfTelecomOutputClientCurrent24StatIndex OBJECT-TYPE
	SYNTAX  INTEGER(0..128)
	MAX-ACCESS  read-only
	STATUS current
	DESCRIPTION
        "
        Index definition for the rm10010PerfTelecomOutputClientCurrent24Stat
        table
        "
	::= { rm10010PerfTelecomOutputClientCurrent24StatEntry 1 }


rm10010PerfTelecomOutputClientCurrent24StatInvCvPortn OBJECT-TYPE
	SYNTAX  EkiOnOff
	MAX-ACCESS read-only
	STATUS current
	DESCRIPTION
        "
        Current 24-hours EBC counter inv.
        :This OID indicates that the current
        24-hours Coding Violation counter
        is invalid
        "
	::= { rm10010PerfTelecomOutputClientCurrent24StatEntry 2 }


rm10010PerfTelecomOutputClientCurrent24StatCvValuePortn OBJECT-TYPE
	SYNTAX  Unsigned32
	MAX-ACCESS read-only
	STATUS current
	DESCRIPTION
        "
        Current 24-hours EBC counter :This
        OID gives the current 24-hours
         Coding Violation counter value
        "
	::= { rm10010PerfTelecomOutputClientCurrent24StatEntry 3 }


rm10010PerfTelecomOutputClientCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { rm10010PerfTelecomOutputClientCurrent24StatEntry 4 }


rm10010PerfTelecomOutputClientCurrent24StatEsValuePortn OBJECT-TYPE
	SYNTAX  Unsigned32
	MAX-ACCESS read-only
	STATUS current
	DESCRIPTION
        "
        Current 24-hours ES counter :This
        OID gives the current 24-hours
         Errored Second counter value
        "
	::= { rm10010PerfTelecomOutputClientCurrent24StatEntry 5 }


rm10010PerfTelecomOutputClientCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { rm10010PerfTelecomOutputClientCurrent24StatEntry 6 }


rm10010PerfTelecomOutputClientCurrent24StatSesValuePortn OBJECT-TYPE
	SYNTAX  Unsigned32
	MAX-ACCESS read-only
	STATUS current
	DESCRIPTION
        "
        Current 24-hours SES counter :This
        OID gives the current 24-hours
         severely Errored Second counter
        value
        "
	::= { rm10010PerfTelecomOutputClientCurrent24StatEntry 7 }


rm10010PerfTelecomOutputClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { rm10010PerfTelecomOutputClientCurrent24StatEntry 8 }


rm10010PerfTelecomOutputClientCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { rm10010PerfTelecomOutputClientCurrent24StatEntry 9 }


rm10010PerfTelecomOutputClientCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { rm10010PerfTelecomOutputClientCurrent24StatEntry 10 }


rm10010PerfTelecomOutputClientCurrent24StatUasValuePortn OBJECT-TYPE
	SYNTAX  Unsigned32
	MAX-ACCESS read-only
	STATUS current
	DESCRIPTION
        "
        Current 24-hours UAS counter :This
        OID gives the current 24-hours
         UnAvailable Second counter value
        "
	::= { rm10010PerfTelecomOutputClientCurrent24StatEntry 11 }


--- *****************************************************
---     Leaf of the telecomOutputClientPast24Stat
--- *****************************************************
--- *********************************************************
---     TABLE for the rm10010PerfTelecomOutputClientPast24StatHistory articles
--- *********************************************************

rm10010PerfTelecomOutputClientPast24StatHistoryPort1Table OBJECT-TYPE
	SYNTAX  SEQUENCE OF Rm10010PerfTelecomOutputClientPast24StatHistoryPort1Entry
	MAX-ACCESS not-accessible
	STATUS current
	DESCRIPTION
        "
        List of rm10010PerfTelecomOutputClientPast24StatHistory
        Article
        "
	::= { rm10010MonPerfClient 128 }


rm10010PerfTelecomOutputClientPast24StatHistoryPort1Entry OBJECT-TYPE
	SYNTAX Rm10010PerfTelecomOutputClientPast24StatHistoryPort1Entry
	MAX-ACCESS not-accessible
	STATUS current
	DESCRIPTION
        "
        Row definition for the rm10010PerfTelecomOutputClientPast24StatHistory
        table
        "
	INDEX   { rm10010PerfTelecomOutputClientPast24StatHistoryPort1Index }
	::= { rm10010PerfTelecomOutputClientPast24StatHistoryPort1Table 1 }


Rm10010PerfTelecomOutputClientPast24StatHistoryPort1Entry ::=
	SEQUENCE {
	rm10010PerfTelecomOutputClientPast24StatHistoryPort1Index
		INTEGER,
	rm10010PerfTelecomOutputClientPast24StatHistoryInvCvPort1
		EkiOnOff,
	rm10010PerfTelecomOutputClientPast24StatHistoryCvValuePort1
		Unsigned32,
	rm10010PerfTelecomOutputClientPast24StatHistoryInvEsPort1
		EkiOnOff,
	rm10010PerfTelecomOutputClientPast24StatHistoryEsValuePort1
		Unsigned32,
	rm10010PerfTelecomOutputClientPast24StatHistoryInvSesPort1
		EkiOnOff,
	rm10010PerfTelecomOutputClientPast24StatHistorySesValuePort1
		Unsigned32,
	rm10010PerfTelecomOutputClientPast24StatHistoryInvSefsPort1
		EkiOnOff,
	rm10010PerfTelecomOutputClientPast24StatHistorySefsValuePort1
		Unsigned32,
	rm10010PerfTelecomOutputClientPast24StatHistoryInvUasPort1
		EkiOnOff,
	rm10010PerfTelecomOutputClientPast24StatHistoryUasValuePort1
		Unsigned32
	}


rm10010PerfTelecomOutputClientPast24StatHistoryPort1Index OBJECT-TYPE
	SYNTAX  INTEGER(0..128)
	MAX-ACCESS  read-only
	STATUS current
	DESCRIPTION
        "
        Index definition for the rm10010PerfTelecomOutputClientPast24StatHistory
        table
        "
	::= { rm10010PerfTelecomOutputClientPast24StatHistoryPort1Entry 1 }


rm10010PerfTelecomOutputClientPast24StatHistoryInvCvPort1 OBJECT-TYPE
	SYNTAX  EkiOnOff
	MAX-ACCESS read-only
	STATUS current
	DESCRIPTION
        "
        Previous 24-hours EBC counter
         inv. :This OID indicates that
         the previous 24-hours Coding Violation
        counter is invalid
        "
	::= { rm10010PerfTelecomOutputClientPast24StatHistoryPort1Entry 2 }


rm10010PerfTelecomOutputClientPast24StatHistoryCvValuePort1 OBJECT-TYPE
	SYNTAX  Unsigned32
	MAX-ACCESS read-only
	STATUS current
	DESCRIPTION
        "
        Previous 24-hours EBC counter
         :This OID gives the previous 24-hours
        Coding Violation counter value
        "
	::= { rm10010PerfTelecomOutputClientPast24StatHistoryPort1Entry 3 }


rm10010PerfTelecomOutputClientPast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { rm10010PerfTelecomOutputClientPast24StatHistoryPort1Entry 4 }


rm10010PerfTelecomOutputClientPast24StatHistoryEsValuePort1 OBJECT-TYPE
	SYNTAX  Unsigned32
	MAX-ACCESS read-only
	STATUS current
	DESCRIPTION
        "
        Previous 24-hours ES counter :This
        OID gives the previous 24-hours
        Errored Second counter value
        "
	::= { rm10010PerfTelecomOutputClientPast24StatHistoryPort1Entry 5 }


rm10010PerfTelecomOutputClientPast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { rm10010PerfTelecomOutputClientPast24StatHistoryPort1Entry 6 }


rm10010PerfTelecomOutputClientPast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { rm10010PerfTelecomOutputClientPast24StatHistoryPort1Entry 7 }


rm10010PerfTelecomOutputClientPast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { rm10010PerfTelecomOutputClientPast24StatHistoryPort1Entry 8 }


rm10010PerfTelecomOutputClientPast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { rm10010PerfTelecomOutputClientPast24StatHistoryPort1Entry 9 }


rm10010PerfTelecomOutputClientPast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { rm10010PerfTelecomOutputClientPast24StatHistoryPort1Entry 10 }


rm10010PerfTelecomOutputClientPast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { rm10010PerfTelecomOutputClientPast24StatHistoryPort1Entry 11 }


--- *****************************************************
---     Leaf of the telecomLinePostFecCurrent15Stat
--- *****************************************************
--- *********************************************************
---     TABLE for the rm10010PerfTelecomLinePostFecCurrent15Stat articles
--- *********************************************************

rm10010PerfTelecomLinePostFecCurrent15StatTable OBJECT-TYPE
	SYNTAX  SEQUENCE OF Rm10010PerfTelecomLinePostFecCurrent15StatEntry
	MAX-ACCESS not-accessible
	STATUS current
	DESCRIPTION
        "
        List of rm10010PerfTelecomLinePostFecCurrent15Stat
        Article
        "
	::= { rm10010MonPerfLine 192 }


rm10010PerfTelecomLinePostFecCurrent15StatEntry OBJECT-TYPE
	SYNTAX Rm10010PerfTelecomLinePostFecCurrent15StatEntry
	MAX-ACCESS not-accessible
	STATUS current
	DESCRIPTION
        "
        Row definition for the rm10010PerfTelecomLinePostFecCurrent15Stat
        table
        "
	INDEX   { rm10010PerfTelecomLinePostFecCurrent15StatIndex }
	::= { rm10010PerfTelecomLinePostFecCurrent15StatTable 1 }


Rm10010PerfTelecomLinePostFecCurrent15StatEntry ::=
	SEQUENCE {
	rm10010PerfTelecomLinePostFecCurrent15StatIndex
		INTEGER,
	rm10010PerfTelecomLinePostFecCurrent15StatInvCvPortn
		EkiOnOff,
	rm10010PerfTelecomLinePostFecCurrent15StatCvValuePortn
		Unsigned32,
	rm10010PerfTelecomLinePostFecCurrent15StatInvEsPortn
		EkiOnOff,
	rm10010PerfTelecomLinePostFecCurrent15StatEsValuePortn
		Unsigned32,
	rm10010PerfTelecomLinePostFecCurrent15StatInvSesPortn
		EkiOnOff,
	rm10010PerfTelecomLinePostFecCurrent15StatSesValuePortn
		Unsigned32,
	rm10010PerfTelecomLinePostFecCurrent15StatInvSefsPortn
		EkiOnOff,
	rm10010PerfTelecomLinePostFecCurrent15StatSefsValuePortn
		Unsigned32,
	rm10010PerfTelecomLinePostFecCurrent15StatInvUasPortn
		EkiOnOff,
	rm10010PerfTelecomLinePostFecCurrent15StatUasValuePortn
		Unsigned32
	}


rm10010PerfTelecomLinePostFecCurrent15StatIndex OBJECT-TYPE
	SYNTAX  INTEGER(0..128)
	MAX-ACCESS  read-only
	STATUS current
	DESCRIPTION
        "
        Index definition for the rm10010PerfTelecomLinePostFecCurrent15Stat
        table
        "
	::= { rm10010PerfTelecomLinePostFecCurrent15StatEntry 1 }


rm10010PerfTelecomLinePostFecCurrent15StatInvCvPortn OBJECT-TYPE
	SYNTAX  EkiOnOff
	MAX-ACCESS read-only
	STATUS current
	DESCRIPTION
        "
        Current 15-min EBC counter inv.
        :This OID indicates that the current
        15-min Coding Violation counter
        is invalid
        "
	::= { rm10010PerfTelecomLinePostFecCurrent15StatEntry 2 }


rm10010PerfTelecomLinePostFecCurrent15StatCvValuePortn OBJECT-TYPE
	SYNTAX  Unsigned32
	MAX-ACCESS read-only
	STATUS current
	DESCRIPTION
        "
        Current 15-min EBC counter :This
        OID gives the current 15-min Coding
        Violation counter value
        "
	::= { rm10010PerfTelecomLinePostFecCurrent15StatEntry 3 }


rm10010PerfTelecomLinePostFecCurrent15StatInvEsPortn OBJECT-TYPE
	SYNTAX  EkiOnOff
	MAX-ACCESS read-only
	STATUS current
	DESCRIPTION
        "
        Current 15-min ES counter inv.
        :This OID indicates that the current
        15-min Errored Second counter is
        invalid
        "
	::= { rm10010PerfTelecomLinePostFecCurrent15StatEntry 4 }


rm10010PerfTelecomLinePostFecCurrent15StatEsValuePortn OBJECT-TYPE
	SYNTAX  Unsigned32
	MAX-ACCESS read-only
	STATUS current
	DESCRIPTION
        "
        Current 15-min ES counter :This
        OID gives the current 15-min Errored
        Second counter value
        "
	::= { rm10010PerfTelecomLinePostFecCurrent15StatEntry 5 }


rm10010PerfTelecomLinePostFecCurrent15StatInvSesPortn OBJECT-TYPE
	SYNTAX  EkiOnOff
	MAX-ACCESS read-only
	STATUS current
	DESCRIPTION
        "
        Current 15-min SES counter inv.
        :This OID indicates that the current
        15-min severely Errored Second
         counter is invalid
        "
	::= { rm10010PerfTelecomLinePostFecCurrent15StatEntry 6 }


rm10010PerfTelecomLinePostFecCurrent15StatSesValuePortn OBJECT-TYPE
	SYNTAX  Unsigned32
	MAX-ACCESS read-only
	STATUS current
	DESCRIPTION
        "
        Current 15-min SES counter :This
        OID gives the current 15-min severely
        Errored Second counter value
        "
	::= { rm10010PerfTelecomLinePostFecCurrent15StatEntry 7 }


rm10010PerfTelecomLinePostFecCurrent15StatInvSefsPortn OBJECT-TYPE
	SYNTAX  EkiOnOff
	MAX-ACCESS read-only
	STATUS current
	DESCRIPTION
        "
        Current 15-min SEFS counter inv.
        :This OID indicates that the current
        15-min severely Errored Framing
        Second counter is invalid
        "
	::= { rm10010PerfTelecomLinePostFecCurrent15StatEntry 8 }


rm10010PerfTelecomLinePostFecCurrent15StatSefsValuePortn OBJECT-TYPE
	SYNTAX  Unsigned32
	MAX-ACCESS read-only
	STATUS current
	DESCRIPTION
        "
        Current 15-min SEFS counter :This
        OID gives the current 15-min severely
        Errored Framing Second counter
         value
        "
	::= { rm10010PerfTelecomLinePostFecCurrent15StatEntry 9 }


rm10010PerfTelecomLinePostFecCurrent15StatInvUasPortn OBJECT-TYPE
	SYNTAX  EkiOnOff
	MAX-ACCESS read-only
	STATUS current
	DESCRIPTION
        "
        Current 15-min UAS counter inv.
        :This OID indicates that the current
        15-min UnAvailable Second counter
        is invalid
        "
	::= { rm10010PerfTelecomLinePostFecCurrent15StatEntry 10 }


rm10010PerfTelecomLinePostFecCurrent15StatUasValuePortn OBJECT-TYPE
	SYNTAX  Unsigned32
	MAX-ACCESS read-only
	STATUS current
	DESCRIPTION
        "
        Current 15-min UAS counter :This
        OID gives the current 15-min UnAvailable
        Second counter value
        "
	::= { rm10010PerfTelecomLinePostFecCurrent15StatEntry 11 }


--- *****************************************************
---     Leaf of the telecomLinePostFecPast15Stat
--- *****************************************************
--- *********************************************************
---     TABLE for the rm10010PerfTelecomLinePostFecPast15StatHistory articles
--- *********************************************************

rm10010PerfTelecomLinePostFecPast15StatHistoryPort1Table OBJECT-TYPE
	SYNTAX  SEQUENCE OF Rm10010PerfTelecomLinePostFecPast15StatHistoryPort1Entry
	MAX-ACCESS not-accessible
	STATUS current
	DESCRIPTION
        "
        List of rm10010PerfTelecomLinePostFecPast15StatHistory
        Article
        "
	::= { rm10010MonPerfLine 193 }


rm10010PerfTelecomLinePostFecPast15StatHistoryPort1Entry OBJECT-TYPE
	SYNTAX Rm10010PerfTelecomLinePostFecPast15StatHistoryPort1Entry
	MAX-ACCESS not-accessible
	STATUS current
	DESCRIPTION
        "
        Row definition for the rm10010PerfTelecomLinePostFecPast15StatHistory
        table
        "
	INDEX   { rm10010PerfTelecomLinePostFecPast15StatHistoryPort1Index }
	::= { rm10010PerfTelecomLinePostFecPast15StatHistoryPort1Table 1 }


Rm10010PerfTelecomLinePostFecPast15StatHistoryPort1Entry ::=
	SEQUENCE {
	rm10010PerfTelecomLinePostFecPast15StatHistoryPort1Index
		INTEGER,
	rm10010PerfTelecomLinePostFecPast15StatHistoryInvCvPort1
		EkiOnOff,
	rm10010PerfTelecomLinePostFecPast15StatHistoryCvValuePort1
		Unsigned32,
	rm10010PerfTelecomLinePostFecPast15StatHistoryInvEsPort1
		EkiOnOff,
	rm10010PerfTelecomLinePostFecPast15StatHistoryEsValuePort1
		Unsigned32,
	rm10010PerfTelecomLinePostFecPast15StatHistoryInvSesPort1
		EkiOnOff,
	rm10010PerfTelecomLinePostFecPast15StatHistorySesValuePort1
		Unsigned32,
	rm10010PerfTelecomLinePostFecPast15StatHistoryInvSefsPort1
		EkiOnOff,
	rm10010PerfTelecomLinePostFecPast15StatHistorySefsValuePort1
		Unsigned32,
	rm10010PerfTelecomLinePostFecPast15StatHistoryInvUasPort1
		EkiOnOff,
	rm10010PerfTelecomLinePostFecPast15StatHistoryUasValuePort1
		Unsigned32
	}


rm10010PerfTelecomLinePostFecPast15StatHistoryPort1Index OBJECT-TYPE
	SYNTAX  INTEGER(0..128)
	MAX-ACCESS  read-only
	STATUS current
	DESCRIPTION
        "
        Index definition for the rm10010PerfTelecomLinePostFecPast15StatHistory
        table
        "
	::= { rm10010PerfTelecomLinePostFecPast15StatHistoryPort1Entry 1 }


rm10010PerfTelecomLinePostFecPast15StatHistoryInvCvPort1 OBJECT-TYPE
	SYNTAX  EkiOnOff
	MAX-ACCESS read-only
	STATUS current
	DESCRIPTION
        "
        Previous 15-min EBC counter inv.
        :This OID indicates that the previous
        15-min Coding Violation counter
        is invalid
        "
	::= { rm10010PerfTelecomLinePostFecPast15StatHistoryPort1Entry 2 }


rm10010PerfTelecomLinePostFecPast15StatHistoryCvValuePort1 OBJECT-TYPE
	SYNTAX  Unsigned32
	MAX-ACCESS read-only
	STATUS current
	DESCRIPTION
        "
        Previous 15-min EBC counter :This
        OID gives the previous 15-min Coding
        Violation counter value
        "
	::= { rm10010PerfTelecomLinePostFecPast15StatHistoryPort1Entry 3 }


rm10010PerfTelecomLinePostFecPast15StatHistoryInvEsPort1 OBJECT-TYPE
	SYNTAX  EkiOnOff
	MAX-ACCESS read-only
	STATUS current
	DESCRIPTION
        "
        Previous 15-min ES counter inv.
        :This OID indicates that the previous
        15-min Errored Second counter is
        invalid
        "
	::= { rm10010PerfTelecomLinePostFecPast15StatHistoryPort1Entry 4 }


rm10010PerfTelecomLinePostFecPast15StatHistoryEsValuePort1 OBJECT-TYPE
	SYNTAX  Unsigned32
	MAX-ACCESS read-only
	STATUS current
	DESCRIPTION
        "
        Previous 15-min ES counter :This
        OID gives the previous 15-min Errored
        Second counter value
        "
	::= { rm10010PerfTelecomLinePostFecPast15StatHistoryPort1Entry 5 }


rm10010PerfTelecomLinePostFecPast15StatHistoryInvSesPort1 OBJECT-TYPE
	SYNTAX  EkiOnOff
	MAX-ACCESS read-only
	STATUS current
	DESCRIPTION
        "
        Previous 15-min SES counter inv.
        :This OID indicates that the previous
        15-min severely Errored Second
         counter is invalid
        "
	::= { rm10010PerfTelecomLinePostFecPast15StatHistoryPort1Entry 6 }


rm10010PerfTelecomLinePostFecPast15StatHistorySesValuePort1 OBJECT-TYPE
	SYNTAX  Unsigned32
	MAX-ACCESS read-only
	STATUS current
	DESCRIPTION
        "
        Previous 15-min SES counter :This
        OID gives the previous 15-min severely
        Errored Second counter value
        "
	::= { rm10010PerfTelecomLinePostFecPast15StatHistoryPort1Entry 7 }


rm10010PerfTelecomLinePostFecPast15StatHistoryInvSefsPort1 OBJECT-TYPE
	SYNTAX  EkiOnOff
	MAX-ACCESS read-only
	STATUS current
	DESCRIPTION
        "
        Previous 15-min SEFS counter inv.
        :This OID indicates that the previous
        15-min severely Errored Framing
        Second counter is invalid
        "
	::= { rm10010PerfTelecomLinePostFecPast15StatHistoryPort1Entry 8 }


rm10010PerfTelecomLinePostFecPast15StatHistorySefsValuePort1 OBJECT-TYPE
	SYNTAX  Unsigned32
	MAX-ACCESS read-only
	STATUS current
	DESCRIPTION
        "
        Previous 15-min SEFS counter :This
        OID gives the previous 15-min severely
        Errored Framing Second counter
         value
        "
	::= { rm10010PerfTelecomLinePostFecPast15StatHistoryPort1Entry 9 }


rm10010PerfTelecomLinePostFecPast15StatHistoryInvUasPort1 OBJECT-TYPE
	SYNTAX  EkiOnOff
	MAX-ACCESS read-only
	STATUS current
	DESCRIPTION
        "
        Previous 15-min UAS counter inv.
        :This OID indicates that the previous
        15-min UnAvailable Second counter
        is invalid
        "
	::= { rm10010PerfTelecomLinePostFecPast15StatHistoryPort1Entry 10 }


rm10010PerfTelecomLinePostFecPast15StatHistoryUasValuePort1 OBJECT-TYPE
	SYNTAX  Unsigned32
	MAX-ACCESS read-only
	STATUS current
	DESCRIPTION
        "
        Previous 15-min UAS counter :This
        OID gives the previous 15-min UnAvailable
        Second counter value
        "
	::= { rm10010PerfTelecomLinePostFecPast15StatHistoryPort1Entry 11 }


--- *****************************************************
---     Leaf of the telecomLinePostFecCurrent24Stat
--- *****************************************************
--- *********************************************************
---     TABLE for the rm10010PerfTelecomLinePostFecCurrent24Stat articles
--- *********************************************************

rm10010PerfTelecomLinePostFecCurrent24StatTable OBJECT-TYPE
	SYNTAX  SEQUENCE OF Rm10010PerfTelecomLinePostFecCurrent24StatEntry
	MAX-ACCESS not-accessible
	STATUS current
	DESCRIPTION
        "
        List of rm10010PerfTelecomLinePostFecCurrent24Stat
        Article
        "
	::= { rm10010MonPerfLine 194 }


rm10010PerfTelecomLinePostFecCurrent24StatEntry OBJECT-TYPE
	SYNTAX Rm10010PerfTelecomLinePostFecCurrent24StatEntry
	MAX-ACCESS not-accessible
	STATUS current
	DESCRIPTION
        "
        Row definition for the rm10010PerfTelecomLinePostFecCurrent24Stat
        table
        "
	INDEX   { rm10010PerfTelecomLinePostFecCurrent24StatIndex }
	::= { rm10010PerfTelecomLinePostFecCurrent24StatTable 1 }


Rm10010PerfTelecomLinePostFecCurrent24StatEntry ::=
	SEQUENCE {
	rm10010PerfTelecomLinePostFecCurrent24StatIndex
		INTEGER,
	rm10010PerfTelecomLinePostFecCurrent24StatInvCvPortn
		EkiOnOff,
	rm10010PerfTelecomLinePostFecCurrent24StatCvValuePortn
		Unsigned32,
	rm10010PerfTelecomLinePostFecCurrent24StatInvEsPortn
		EkiOnOff,
	rm10010PerfTelecomLinePostFecCurrent24StatEsValuePortn
		Unsigned32,
	rm10010PerfTelecomLinePostFecCurrent24StatInvSesPortn
		EkiOnOff,
	rm10010PerfTelecomLinePostFecCurrent24StatSesValuePortn
		Unsigned32,
	rm10010PerfTelecomLinePostFecCurrent24StatInvSefsPortn
		EkiOnOff,
	rm10010PerfTelecomLinePostFecCurrent24StatSefsValuePortn
		Unsigned32,
	rm10010PerfTelecomLinePostFecCurrent24StatInvUasPortn
		EkiOnOff,
	rm10010PerfTelecomLinePostFecCurrent24StatUasValuePortn
		Unsigned32
	}


rm10010PerfTelecomLinePostFecCurrent24StatIndex OBJECT-TYPE
	SYNTAX  INTEGER(0..128)
	MAX-ACCESS  read-only
	STATUS current
	DESCRIPTION
        "
        Index definition for the rm10010PerfTelecomLinePostFecCurrent24Stat
        table
        "
	::= { rm10010PerfTelecomLinePostFecCurrent24StatEntry 1 }


rm10010PerfTelecomLinePostFecCurrent24StatInvCvPortn OBJECT-TYPE
	SYNTAX  EkiOnOff
	MAX-ACCESS read-only
	STATUS current
	DESCRIPTION
        "
        Current 24-hours EBC counter inv.
        :This OID indicates that the current
        24-hours Coding Violation counter
        is invalid
        "
	::= { rm10010PerfTelecomLinePostFecCurrent24StatEntry 2 }


rm10010PerfTelecomLinePostFecCurrent24StatCvValuePortn OBJECT-TYPE
	SYNTAX  Unsigned32
	MAX-ACCESS read-only
	STATUS current
	DESCRIPTION
        "
        Current 24-hours EBC counter :This
        OID gives the current 24-hours
         Coding Violation counter value
        "
	::= { rm10010PerfTelecomLinePostFecCurrent24StatEntry 3 }


rm10010PerfTelecomLinePostFecCurrent24StatInvEsPortn OBJECT-TYPE
	SYNTAX  EkiOnOff
	MAX-ACCESS read-only
	STATUS current
	DESCRIPTION
        "
        Current 24-hours ES counter inv.
        :This OID indicates that the current
        24-hours Errored Second counter
        is invalid
        "
	::= { rm10010PerfTelecomLinePostFecCurrent24StatEntry 4 }


rm10010PerfTelecomLinePostFecCurrent24StatEsValuePortn OBJECT-TYPE
	SYNTAX  Unsigned32
	MAX-ACCESS read-only
	STATUS current
	DESCRIPTION
        "
        Current 24-hours ES counter :This
        OID gives the current 24-hours
         Errored Second counter value
        "
	::= { rm10010PerfTelecomLinePostFecCurrent24StatEntry 5 }


rm10010PerfTelecomLinePostFecCurrent24StatInvSesPortn OBJECT-TYPE
	SYNTAX  EkiOnOff
	MAX-ACCESS read-only
	STATUS current
	DESCRIPTION
        "
        Current 24-hours SES counter inv.
        :This OID indicates that the current
        24-hours severely Errored Second
        counter is invalid
        "
	::= { rm10010PerfTelecomLinePostFecCurrent24StatEntry 6 }


rm10010PerfTelecomLinePostFecCurrent24StatSesValuePortn OBJECT-TYPE
	SYNTAX  Unsigned32
	MAX-ACCESS read-only
	STATUS current
	DESCRIPTION
        "
        Current 24-hours SES counter :This
        OID gives the current 24-hours
         severely Errored Second counter
        value
        "
	::= { rm10010PerfTelecomLinePostFecCurrent24StatEntry 7 }


rm10010PerfTelecomLinePostFecCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter
        is invalid
        "
	::= { rm10010PerfTelecomLinePostFecCurrent24StatEntry 8 }


rm10010PerfTelecomLinePostFecCurrent24StatSefsValuePortn OBJECT-TYPE
	SYNTAX  Unsigned32
	MAX-ACCESS read-only
	STATUS current
	DESCRIPTION
        "
        Current 24-hours SEFS counter
         :This OID gives the current 24-hours
        severely Errored Framing Second
        counter value
        "
	::= { rm10010PerfTelecomLinePostFecCurrent24StatEntry 9 }


rm10010PerfTelecomLinePostFecCurrent24StatInvUasPortn OBJECT-TYPE
	SYNTAX  EkiOnOff
	MAX-ACCESS read-only
	STATUS current
	DESCRIPTION
        "
        Current 24-hours UAS counter inv.
        :This OID indicates that the current
        24-hours UnAvailable Second counter
        is invalid
        "
	::= { rm10010PerfTelecomLinePostFecCurrent24StatEntry 10 }


rm10010PerfTelecomLinePostFecCurrent24StatUasValuePortn OBJECT-TYPE
	SYNTAX  Unsigned32
	MAX-ACCESS read-only
	STATUS current
	DESCRIPTION
        "
        Current 24-hours UAS counter :This
        OID gives the current 24-hours
         UnAvailable Second counter value
        "
	::= { rm10010PerfTelecomLinePostFecCurrent24StatEntry 11 }


--- *****************************************************
---     Leaf of the telecomLinePostFecPast24Stat
--- *****************************************************
--- *********************************************************
---     TABLE for the rm10010PerfTelecomLinePostFecPast24StatHistory articles
--- *********************************************************

rm10010PerfTelecomLinePostFecPast24StatHistoryPort1Table OBJECT-TYPE
	SYNTAX  SEQUENCE OF Rm10010PerfTelecomLinePostFecPast24StatHistoryPort1Entry
	MAX-ACCESS not-accessible
	STATUS current
	DESCRIPTION
        "
        List of rm10010PerfTelecomLinePostFecPast24StatHistory
        Article
        "
	::= { rm10010MonPerfLine 195 }


rm10010PerfTelecomLinePostFecPast24StatHistoryPort1Entry OBJECT-TYPE
	SYNTAX Rm10010PerfTelecomLinePostFecPast24StatHistoryPort1Entry
	MAX-ACCESS not-accessible
	STATUS current
	DESCRIPTION
        "
        Row definition for the rm10010PerfTelecomLinePostFecPast24StatHistory
        table
        "
	INDEX   { rm10010PerfTelecomLinePostFecPast24StatHistoryPort1Index }
	::= { rm10010PerfTelecomLinePostFecPast24StatHistoryPort1Table 1 }


Rm10010PerfTelecomLinePostFecPast24StatHistoryPort1Entry ::=
	SEQUENCE {
	rm10010PerfTelecomLinePostFecPast24StatHistoryPort1Index
		INTEGER,
	rm10010PerfTelecomLinePostFecPast24StatHistoryInvCvPort1
		EkiOnOff,
	rm10010PerfTelecomLinePostFecPast24StatHistoryCvValuePort1
		Unsigned32,
	rm10010PerfTelecomLinePostFecPast24StatHistoryInvEsPort1
		EkiOnOff,
	rm10010PerfTelecomLinePostFecPast24StatHistoryEsValuePort1
		Unsigned32,
	rm10010PerfTelecomLinePostFecPast24StatHistoryInvSesPort1
		EkiOnOff,
	rm10010PerfTelecomLinePostFecPast24StatHistorySesValuePort1
		Unsigned32,
	rm10010PerfTelecomLinePostFecPast24StatHistoryInvSefsPort1
		EkiOnOff,
	rm10010PerfTelecomLinePostFecPast24StatHistorySefsValuePort1
		Unsigned32,
	rm10010PerfTelecomLinePostFecPast24StatHistoryInvUasPort1
		EkiOnOff,
	rm10010PerfTelecomLinePostFecPast24StatHistoryUasValuePort1
		Unsigned32
	}


rm10010PerfTelecomLinePostFecPast24StatHistoryPort1Index OBJECT-TYPE
	SYNTAX  INTEGER(0..128)
	MAX-ACCESS  read-only
	STATUS current
	DESCRIPTION
        "
        Index definition for the rm10010PerfTelecomLinePostFecPast24StatHistory
        table
        "
	::= { rm10010PerfTelecomLinePostFecPast24StatHistoryPort1Entry 1 }


rm10010PerfTelecomLinePostFecPast24StatHistoryInvCvPort1 OBJECT-TYPE
	SYNTAX  EkiOnOff
	MAX-ACCESS read-only
	STATUS current
	DESCRIPTION
        "
        Previous 24-hours EBC counter
         inv. :This OID indicates that
         the previous 24-hours Coding Violation
        counter is invalid
        "
	::= { rm10010PerfTelecomLinePostFecPast24StatHistoryPort1Entry 2 }


rm10010PerfTelecomLinePostFecPast24StatHistoryCvValuePort1 OBJECT-TYPE
	SYNTAX  Unsigned32
	MAX-ACCESS read-only
	STATUS current
	DESCRIPTION
        "
        Previous 24-hours EBC counter
         :This OID gives the previous 24-hours
        Coding Violation counter value
        "
	::= { rm10010PerfTelecomLinePostFecPast24StatHistoryPort1Entry 3 }


rm10010PerfTelecomLinePostFecPast24StatHistoryInvEsPort1 OBJECT-TYPE
	SYNTAX  EkiOnOff
	MAX-ACCESS read-only
	STATUS current
	DESCRIPTION
        "
        Previous 24-hours ES counter inv.
        :This OID indicates that the previous
        24-hours Errored Second counter
        is invalid
        "
	::= { rm10010PerfTelecomLinePostFecPast24StatHistoryPort1Entry 4 }


rm10010PerfTelecomLinePostFecPast24StatHistoryEsValuePort1 OBJECT-TYPE
	SYNTAX  Unsigned32
	MAX-ACCESS read-only
	STATUS current
	DESCRIPTION
        "
        Previous 24-hours ES counter :This
        OID gives the previous 24-hours
        Errored Second counter value
        "
	::= { rm10010PerfTelecomLinePostFecPast24StatHistoryPort1Entry 5 }


rm10010PerfTelecomLinePostFecPast24StatHistoryInvSesPort1 OBJECT-TYPE
	SYNTAX  EkiOnOff
	MAX-ACCESS read-only
	STATUS current
	DESCRIPTION
        "
        Previous 24-hours SES counter
         inv. :This OID indicates that
         the previous 24-hours severely
        Errored Second counter is invalid
        "
	::= { rm10010PerfTelecomLinePostFecPast24StatHistoryPort1Entry 6 }


rm10010PerfTelecomLinePostFecPast24StatHistorySesValuePort1 OBJECT-TYPE
	SYNTAX  Unsigned32
	MAX-ACCESS read-only
	STATUS current
	DESCRIPTION
        "
        Previous 24-hours SES counter
         :This OID gives the previous 24-hours
        severely Errored Second counter
        value
        "
	::= { rm10010PerfTelecomLinePostFecPast24StatHistoryPort1Entry 7 }


rm10010PerfTelecomLinePostFecPast24StatHistoryInvSefsPort1 OBJECT-TYPE
	SYNTAX  EkiOnOff
	MAX-ACCESS read-only
	STATUS current
	DESCRIPTION
        "
        Previous 24-hours SEFS counter
        inv. :This OID indicates that the
        previous 24-hours severely Errored
        Framing Second counter is invalid
        "
	::= { rm10010PerfTelecomLinePostFecPast24StatHistoryPort1Entry 8 }


rm10010PerfTelecomLinePostFecPast24StatHistorySefsValuePort1 OBJECT-TYPE
	SYNTAX  Unsigned32
	MAX-ACCESS read-only
	STATUS current
	DESCRIPTION
        "
        Previous 24-hours SEFS counter
        :This OID gives the previous 24-hours
        severely Errored Framing Second
        counter value
        "
	::= { rm10010PerfTelecomLinePostFecPast24StatHistoryPort1Entry 9 }


rm10010PerfTelecomLinePostFecPast24StatHistoryInvUasPort1 OBJECT-TYPE
	SYNTAX  EkiOnOff
	MAX-ACCESS read-only
	STATUS current
	DESCRIPTION
        "
        Previous 24-hours UAS counter
         inv. :This OID indicates that
         the previous 24-hours UnAvailable
        Second counter is invalid
        "
	::= { rm10010PerfTelecomLinePostFecPast24StatHistoryPort1Entry 10 }


rm10010PerfTelecomLinePostFecPast24StatHistoryUasValuePort1 OBJECT-TYPE
	SYNTAX  Unsigned32
	MAX-ACCESS read-only
	STATUS current
	DESCRIPTION
        "
        Previous 24-hours UAS counter
         :This OID gives the previous 24-hours
        UnAvailable Second counter value
        "
	::= { rm10010PerfTelecomLinePostFecPast24StatHistoryPort1Entry 11 }


--- *****************************************************
---     Leaf of the telecomBerLinePreFecCurrent15Stat
--- *****************************************************
--- *********************************************************
---     TABLE for the rm10010PerfTelecomBerLinePreFecCurrent15Stat articles
--- *********************************************************

rm10010PerfTelecomBerLinePreFecCurrent15StatTable OBJECT-TYPE
	SYNTAX  SEQUENCE OF Rm10010PerfTelecomBerLinePreFecCurrent15StatEntry
	MAX-ACCESS not-accessible
	STATUS current
	DESCRIPTION
        "
        List of rm10010PerfTelecomBerLinePreFecCurrent15Stat
        Article
        "
	::= { rm10010MonPerfLine 208 }


rm10010PerfTelecomBerLinePreFecCurrent15StatEntry OBJECT-TYPE
	SYNTAX Rm10010PerfTelecomBerLinePreFecCurrent15StatEntry
	MAX-ACCESS not-accessible
	STATUS current
	DESCRIPTION
        "
        Row definition for the rm10010PerfTelecomBerLinePreFecCurrent15Stat
        table
        "
	INDEX   { rm10010PerfTelecomBerLinePreFecCurrent15StatIndex }
	::= { rm10010PerfTelecomBerLinePreFecCurrent15StatTable 1 }


Rm10010PerfTelecomBerLinePreFecCurrent15StatEntry ::=
	SEQUENCE {
	rm10010PerfTelecomBerLinePreFecCurrent15StatIndex
		INTEGER,
	rm10010PerfTelecomBerLinePreFecCurrent15StatInvBerPortn
		EkiOnOff,
	rm10010PerfTelecomBerLinePreFecCurrent15StatBerValuePortn
		Unsigned32,
	rm10010PerfTelecomBerLinePreFecCurrent15StatInvMinBerPortn
		EkiOnOff,
	rm10010PerfTelecomBerLinePreFecCurrent15StatMinBerValuePortn
		Unsigned32,
	rm10010PerfTelecomBerLinePreFecCurrent15StatInvMaxBerPortn
		EkiOnOff,
	rm10010PerfTelecomBerLinePreFecCurrent15StatMaxBerValuePortn
		Unsigned32
	}


rm10010PerfTelecomBerLinePreFecCurrent15StatIndex OBJECT-TYPE
	SYNTAX  INTEGER(0..128)
	MAX-ACCESS  read-only
	STATUS current
	DESCRIPTION
        "
        Index definition for the rm10010PerfTelecomBerLinePreFecCurrent15Stat
        table
        "
	::= { rm10010PerfTelecomBerLinePreFecCurrent15StatEntry 1 }


rm10010PerfTelecomBerLinePreFecCurrent15StatInvBerPortn OBJECT-TYPE
	SYNTAX  EkiOnOff
	MAX-ACCESS read-only
	STATUS current
	DESCRIPTION
        "
        Current 15-min BER counter inv.
        :This OID indicates that the current
        15-min Coding Violation counter
        is invalid
        "
	::= { rm10010PerfTelecomBerLinePreFecCurrent15StatEntry 2 }


rm10010PerfTelecomBerLinePreFecCurrent15StatBerValuePortn OBJECT-TYPE
	SYNTAX  Unsigned32
	MAX-ACCESS read-only
	STATUS current
	DESCRIPTION
        "
        Current 15-min BER counter :This
        OID gives the current 15-min Coding
        Violation counter value
        "
	::= { rm10010PerfTelecomBerLinePreFecCurrent15StatEntry 3 }


rm10010PerfTelecomBerLinePreFecCurrent15StatInvMinBerPortn OBJECT-TYPE
	SYNTAX  EkiOnOff
	MAX-ACCESS read-only
	STATUS current
	DESCRIPTION
        "
        Current 15-min MinBER counter
         inv. :This OID indicates that
         the current 15-min Errored Second
        counter is invalid
        "
	::= { rm10010PerfTelecomBerLinePreFecCurrent15StatEntry 4 }


rm10010PerfTelecomBerLinePreFecCurrent15StatMinBerValuePortn OBJECT-TYPE
	SYNTAX  Unsigned32
	MAX-ACCESS read-only
	STATUS current
	DESCRIPTION
        "
        Current 15-min MinBER counter
         :This OID gives the current 15-min
        Errored Second counter value
        "
	::= { rm10010PerfTelecomBerLinePreFecCurrent15StatEntry 5 }


rm10010PerfTelecomBerLinePreFecCurrent15StatInvMaxBerPortn OBJECT-TYPE
	SYNTAX  EkiOnOff
	MAX-ACCESS read-only
	STATUS current
	DESCRIPTION
        "
        Current 15-min MaxBER counter
         inv. :This OID indicates that
         the current 15-min severely Errored
        Second counter is invalid
        "
	::= { rm10010PerfTelecomBerLinePreFecCurrent15StatEntry 6 }


rm10010PerfTelecomBerLinePreFecCurrent15StatMaxBerValuePortn OBJECT-TYPE
	SYNTAX  Unsigned32
	MAX-ACCESS read-only
	STATUS current
	DESCRIPTION
        "
        Current 15-min MaxBER counter
         :This OID gives the current 15-min
        severely Errored Second counter
        value
        "
	::= { rm10010PerfTelecomBerLinePreFecCurrent15StatEntry 7 }


--- *****************************************************
---     Leaf of the telecomBerLinePreFecPast15Stat
--- *****************************************************
--- *********************************************************
---     TABLE for the rm10010PerfTelecomBerLinePreFecPast15StatHistory articles
--- *********************************************************

rm10010PerfTelecomBerLinePreFecPast15StatHistoryPort1Table OBJECT-TYPE
	SYNTAX  SEQUENCE OF Rm10010PerfTelecomBerLinePreFecPast15StatHistoryPort1Entry
	MAX-ACCESS not-accessible
	STATUS current
	DESCRIPTION
        "
        List of rm10010PerfTelecomBerLinePreFecPast15StatHistory
        Article
        "
	::= { rm10010MonPerfLine 209 }


rm10010PerfTelecomBerLinePreFecPast15StatHistoryPort1Entry OBJECT-TYPE
	SYNTAX Rm10010PerfTelecomBerLinePreFecPast15StatHistoryPort1Entry
	MAX-ACCESS not-accessible
	STATUS current
	DESCRIPTION
        "
        Row definition for the rm10010PerfTelecomBerLinePreFecPast15StatHistory
        table
        "
	INDEX   { rm10010PerfTelecomBerLinePreFecPast15StatHistoryPort1Index }
	::= { rm10010PerfTelecomBerLinePreFecPast15StatHistoryPort1Table 1 }


Rm10010PerfTelecomBerLinePreFecPast15StatHistoryPort1Entry ::=
	SEQUENCE {
	rm10010PerfTelecomBerLinePreFecPast15StatHistoryPort1Index
		INTEGER,
	rm10010PerfTelecomBerLinePreFecPast15StatHistoryInvBerPort1
		EkiOnOff,
	rm10010PerfTelecomBerLinePreFecPast15StatHistoryBerValuePort1
		Unsigned32,
	rm10010PerfTelecomBerLinePreFecPast15StatHistoryInvMinBerPort1
		EkiOnOff,
	rm10010PerfTelecomBerLinePreFecPast15StatHistoryMinBerValuePort1
		Unsigned32,
	rm10010PerfTelecomBerLinePreFecPast15StatHistoryInvMaxBerPort1
		EkiOnOff,
	rm10010PerfTelecomBerLinePreFecPast15StatHistoryMaxBerValuePort1
		Unsigned32
	}


rm10010PerfTelecomBerLinePreFecPast15StatHistoryPort1Index OBJECT-TYPE
	SYNTAX  INTEGER(0..128)
	MAX-ACCESS  read-only
	STATUS current
	DESCRIPTION
        "
        Index definition for the rm10010PerfTelecomBerLinePreFecPast15StatHistory
        table
        "
	::= { rm10010PerfTelecomBerLinePreFecPast15StatHistoryPort1Entry 1 }


rm10010PerfTelecomBerLinePreFecPast15StatHistoryInvBerPort1 OBJECT-TYPE
	SYNTAX  EkiOnOff
	MAX-ACCESS read-only
	STATUS current
	DESCRIPTION
        "
        Previous 15-min BER counter inv.
        :This OID indicates that the previous
        15-min Coding Violation counter
        is invalid
        "
	::= { rm10010PerfTelecomBerLinePreFecPast15StatHistoryPort1Entry 2 }


rm10010PerfTelecomBerLinePreFecPast15StatHistoryBerValuePort1 OBJECT-TYPE
	SYNTAX  Unsigned32
	MAX-ACCESS read-only
	STATUS current
	DESCRIPTION
        "
        Previous 15-min BER counter :This
        OID gives the previous 15-min Coding
        Violation counter value
        "
	::= { rm10010PerfTelecomBerLinePreFecPast15StatHistoryPort1Entry 3 }


rm10010PerfTelecomBerLinePreFecPast15StatHistoryInvMinBerPort1 OBJECT-TYPE
	SYNTAX  EkiOnOff
	MAX-ACCESS read-only
	STATUS current
	DESCRIPTION
        "
        Previous 15-min MinBER counter
        inv. :This OID indicates that the
        previous 15-min Errored Second
         counter is invalid
        "
	::= { rm10010PerfTelecomBerLinePreFecPast15StatHistoryPort1Entry 4 }


rm10010PerfTelecomBerLinePreFecPast15StatHistoryMinBerValuePort1 OBJECT-TYPE
	SYNTAX  Unsigned32
	MAX-ACCESS read-only
	STATUS current
	DESCRIPTION
        "
        Previous 15-min MinBER counter
        :This OID gives the previous 15-min
        Errored Second counter value
        "
	::= { rm10010PerfTelecomBerLinePreFecPast15StatHistoryPort1Entry 5 }


rm10010PerfTelecomBerLinePreFecPast15StatHistoryInvMaxBerPort1 OBJECT-TYPE
	SYNTAX  EkiOnOff
	MAX-ACCESS read-only
	STATUS current
	DESCRIPTION
        "
        Previous 15-min MaxBER counter
        inv. :This OID indicates that the
        previous 15-min severely Errored
        Second counter is invalid
        "
	::= { rm10010PerfTelecomBerLinePreFecPast15StatHistoryPort1Entry 6 }


rm10010PerfTelecomBerLinePreFecPast15StatHistoryMaxBerValuePort1 OBJECT-TYPE
	SYNTAX  Unsigned32
	MAX-ACCESS read-only
	STATUS current
	DESCRIPTION
        "
        Previous 15-min MaxBER counter
        :This OID gives the previous 15-min
        severely Errored Second counter
        value
        "
	::= { rm10010PerfTelecomBerLinePreFecPast15StatHistoryPort1Entry 7 }


--- *****************************************************
---     Leaf of the telecomBerLinePreFecCurrent24Stat
--- *****************************************************
--- *********************************************************
---     TABLE for the rm10010PerfTelecomBerLinePreFecCurrent24Stat articles
--- *********************************************************

rm10010PerfTelecomBerLinePreFecCurrent24StatTable OBJECT-TYPE
	SYNTAX  SEQUENCE OF Rm10010PerfTelecomBerLinePreFecCurrent24StatEntry
	MAX-ACCESS not-accessible
	STATUS current
	DESCRIPTION
        "
        List of rm10010PerfTelecomBerLinePreFecCurrent24Stat
        Article
        "
	::= { rm10010MonPerfLine 210 }


rm10010PerfTelecomBerLinePreFecCurrent24StatEntry OBJECT-TYPE
	SYNTAX Rm10010PerfTelecomBerLinePreFecCurrent24StatEntry
	MAX-ACCESS not-accessible
	STATUS current
	DESCRIPTION
        "
        Row definition for the rm10010PerfTelecomBerLinePreFecCurrent24Stat
        table
        "
	INDEX   { rm10010PerfTelecomBerLinePreFecCurrent24StatIndex }
	::= { rm10010PerfTelecomBerLinePreFecCurrent24StatTable 1 }


Rm10010PerfTelecomBerLinePreFecCurrent24StatEntry ::=
	SEQUENCE {
	rm10010PerfTelecomBerLinePreFecCurrent24StatIndex
		INTEGER,
	rm10010PerfTelecomBerLinePreFecCurrent24StatInvBerPortn
		EkiOnOff,
	rm10010PerfTelecomBerLinePreFecCurrent24StatBerValuePortn
		Unsigned32,
	rm10010PerfTelecomBerLinePreFecCurrent24StatInvMinBerPortn
		EkiOnOff,
	rm10010PerfTelecomBerLinePreFecCurrent24StatMinBerValuePortn
		Unsigned32,
	rm10010PerfTelecomBerLinePreFecCurrent24StatInvMaxBerPortn
		EkiOnOff,
	rm10010PerfTelecomBerLinePreFecCurrent24StatMaxBerValuePortn
		Unsigned32
	}


rm10010PerfTelecomBerLinePreFecCurrent24StatIndex OBJECT-TYPE
	SYNTAX  INTEGER(0..128)
	MAX-ACCESS  read-only
	STATUS current
	DESCRIPTION
        "
        Index definition for the rm10010PerfTelecomBerLinePreFecCurrent24Stat
        table
        "
	::= { rm10010PerfTelecomBerLinePreFecCurrent24StatEntry 1 }


rm10010PerfTelecomBerLinePreFecCurrent24StatInvBerPortn OBJECT-TYPE
	SYNTAX  EkiOnOff
	MAX-ACCESS read-only
	STATUS current
	DESCRIPTION
        "
        Current 24-hours BER counter inv.
        :This OID indicates that the current
        24-hours Coding Violation counter
        is invalid
        "
	::= { rm10010PerfTelecomBerLinePreFecCurrent24StatEntry 2 }


rm10010PerfTelecomBerLinePreFecCurrent24StatBerValuePortn OBJECT-TYPE
	SYNTAX  Unsigned32
	MAX-ACCESS read-only
	STATUS current
	DESCRIPTION
        "
        Current 24-hours BER counter :This
        OID gives the current 24-hours
         Coding Violation counter value
        "
	::= { rm10010PerfTelecomBerLinePreFecCurrent24StatEntry 3 }


rm10010PerfTelecomBerLinePreFecCurrent24StatInvMinBerPortn OBJECT-TYPE
	SYNTAX  EkiOnOff
	MAX-ACCESS read-only
	STATUS current
	DESCRIPTION
        "
        Current 24-hoursMinBER counter
        inv. :This OID indicates that the
        current 24-hours Errored Second
        counter is invalid
        "
	::= { rm10010PerfTelecomBerLinePreFecCurrent24StatEntry 4 }


rm10010PerfTelecomBerLinePreFecCurrent24StatMinBerValuePortn OBJECT-TYPE
	SYNTAX  Unsigned32
	MAX-ACCESS read-only
	STATUS current
	DESCRIPTION
        "
        Current 24-hours MinBER counter
        :This OID gives the current 24-hours
        Errored Second counter value
        "
	::= { rm10010PerfTelecomBerLinePreFecCurrent24StatEntry 5 }


rm10010PerfTelecomBerLinePreFecCurrent24StatInvMaxBerPortn OBJECT-TYPE
	SYNTAX  EkiOnOff
	MAX-ACCESS read-only
	STATUS current
	DESCRIPTION
        "
        Current 24-hours MaxBER counter
        inv. :This OID indicates that the
        current 24-hours severely Errored
        Second counter is invalid
        "
	::= { rm10010PerfTelecomBerLinePreFecCurrent24StatEntry 6 }


rm10010PerfTelecomBerLinePreFecCurrent24StatMaxBerValuePortn OBJECT-TYPE
	SYNTAX  Unsigned32
	MAX-ACCESS read-only
	STATUS current
	DESCRIPTION
        "
        Current 24-hours MaxBER counter
        :This OID gives the current 24-hours
        severely Errored Second counter
        value
        "
	::= { rm10010PerfTelecomBerLinePreFecCurrent24StatEntry 7 }


--- *****************************************************
---     Leaf of the telecomBerLinePreFecPast24Stat
--- *****************************************************
--- *********************************************************
---     TABLE for the rm10010PerfTelecomBerLinePreFecPast24StatHistory articles
--- *********************************************************

rm10010PerfTelecomBerLinePreFecPast24StatHistoryPort1Table OBJECT-TYPE
	SYNTAX  SEQUENCE OF Rm10010PerfTelecomBerLinePreFecPast24StatHistoryPort1Entry
	MAX-ACCESS not-accessible
	STATUS current
	DESCRIPTION
        "
        List of rm10010PerfTelecomBerLinePreFecPast24StatHistory
        Article
        "
	::= { rm10010MonPerfLine 211 }


rm10010PerfTelecomBerLinePreFecPast24StatHistoryPort1Entry OBJECT-TYPE
	SYNTAX Rm10010PerfTelecomBerLinePreFecPast24StatHistoryPort1Entry
	MAX-ACCESS not-accessible
	STATUS current
	DESCRIPTION
        "
        Row definition for the rm10010PerfTelecomBerLinePreFecPast24StatHistory
        table
        "
	INDEX   { rm10010PerfTelecomBerLinePreFecPast24StatHistoryPort1Index }
	::= { rm10010PerfTelecomBerLinePreFecPast24StatHistoryPort1Table 1 }


Rm10010PerfTelecomBerLinePreFecPast24StatHistoryPort1Entry ::=
	SEQUENCE {
	rm10010PerfTelecomBerLinePreFecPast24StatHistoryPort1Index
		INTEGER,
	rm10010PerfTelecomBerLinePreFecPast24StatHistoryInvBerPort1
		EkiOnOff,
	rm10010PerfTelecomBerLinePreFecPast24StatHistoryBerValuePort1
		Unsigned32,
	rm10010PerfTelecomBerLinePreFecPast24StatHistoryInvMinBerPort1
		EkiOnOff,
	rm10010PerfTelecomBerLinePreFecPast24StatHistoryMinBerValuePort1
		Unsigned32,
	rm10010PerfTelecomBerLinePreFecPast24StatHistoryInvMaxBerPort1
		EkiOnOff,
	rm10010PerfTelecomBerLinePreFecPast24StatHistoryMaxBerValuePort1
		Unsigned32
	}


rm10010PerfTelecomBerLinePreFecPast24StatHistoryPort1Index OBJECT-TYPE
	SYNTAX  INTEGER(0..128)
	MAX-ACCESS  read-only
	STATUS current
	DESCRIPTION
        "
        Index definition for the rm10010PerfTelecomBerLinePreFecPast24StatHistory
        table
        "
	::= { rm10010PerfTelecomBerLinePreFecPast24StatHistoryPort1Entry 1 }


rm10010PerfTelecomBerLinePreFecPast24StatHistoryInvBerPort1 OBJECT-TYPE
	SYNTAX  EkiOnOff
	MAX-ACCESS read-only
	STATUS current
	DESCRIPTION
        "
        Previous 24-hours BER counter
         inv. :This OID indicates that
         the previous 24-hours Coding Violation
        counter is invalid
        "
	::= { rm10010PerfTelecomBerLinePreFecPast24StatHistoryPort1Entry 2 }


rm10010PerfTelecomBerLinePreFecPast24StatHistoryBerValuePort1 OBJECT-TYPE
	SYNTAX  Unsigned32
	MAX-ACCESS read-only
	STATUS current
	DESCRIPTION
        "
        Previous 24-hours BER counter
         :This OID gives the previous 24-hours
        Coding Violation counter value
        "
	::= { rm10010PerfTelecomBerLinePreFecPast24StatHistoryPort1Entry 3 }


rm10010PerfTelecomBerLinePreFecPast24StatHistoryInvMinBerPort1 OBJECT-TYPE
	SYNTAX  EkiOnOff
	MAX-ACCESS read-only
	STATUS current
	DESCRIPTION
        "
        Previous 24-hours MinBER counter
        inv. :This OID indicates that the
        previous 24-hours Errored Second
        counter is invalid
        "
	::= { rm10010PerfTelecomBerLinePreFecPast24StatHistoryPort1Entry 4 }


rm10010PerfTelecomBerLinePreFecPast24StatHistoryMinBerValuePort1 OBJECT-TYPE
	SYNTAX  Unsigned32
	MAX-ACCESS read-only
	STATUS current
	DESCRIPTION
        "
        Previous 24-hours MinBER counter
        :This OID gives the previous 24-hours
        Errored Second counter value
        "
	::= { rm10010PerfTelecomBerLinePreFecPast24StatHistoryPort1Entry 5 }


rm10010PerfTelecomBerLinePreFecPast24StatHistoryInvMaxBerPort1 OBJECT-TYPE
	SYNTAX  EkiOnOff
	MAX-ACCESS read-only
	STATUS current
	DESCRIPTION
        "
        Previous 24-hours MaxBER counter
        inv. :This OID indicates that the
        previous 24-hours severely Errored
        Second counter is invalid
        "
	::= { rm10010PerfTelecomBerLinePreFecPast24StatHistoryPort1Entry 6 }


rm10010PerfTelecomBerLinePreFecPast24StatHistoryMaxBerValuePort1 OBJECT-TYPE
	SYNTAX  Unsigned32
	MAX-ACCESS read-only
	STATUS current
	DESCRIPTION
        "
        Previous 24-hours MaxBER counter
        :This OID gives the previous 24-hours
        severely Errored Second counter
        value
        "
	::= { rm10010PerfTelecomBerLinePreFecPast24StatHistoryPort1Entry 7 }


--- *****************************************************
---     Leaf of the datacomClientCurrent15Stat
--- *****************************************************
--- *********************************************************
---     TABLE for the rm10010PerfDatacomClientCurrent15Stat articles
--- *********************************************************

rm10010PerfDatacomClientCurrent15StatTable OBJECT-TYPE
	SYNTAX  SEQUENCE OF Rm10010PerfDatacomClientCurrent15StatEntry
	MAX-ACCESS not-accessible
	STATUS current
	DESCRIPTION
        "
        List of rm10010PerfDatacomClientCurrent15Stat
        Article
        "
	::= { rm10010MonPerfClient 432 }


rm10010PerfDatacomClientCurrent15StatEntry OBJECT-TYPE
	SYNTAX Rm10010PerfDatacomClientCurrent15StatEntry
	MAX-ACCESS not-accessible
	STATUS current
	DESCRIPTION
        "
        Row definition for the rm10010PerfDatacomClientCurrent15Stat
        table
        "
	INDEX   { rm10010PerfDatacomClientCurrent15StatIndex }
	::= { rm10010PerfDatacomClientCurrent15StatTable 1 }


Rm10010PerfDatacomClientCurrent15StatEntry ::=
	SEQUENCE {
	rm10010PerfDatacomClientCurrent15StatIndex
		INTEGER,
	rm10010perfdatacomclientCurrent15StatOutPacketCountInvPortn
		EkiOnOff,
	rm10010perfdatacomclientCurrent15StatOutPacketCountPortn
		Counter64,
	rm10010perfdatacomclientCurrent15StatOutCrcCountInvPortn
		EkiOnOff,
	rm10010perfdatacomclientCurrent15StatOutCrcCountPortn
		Counter64,
	rm10010perfdatacomclientCurrent15StatInPacketCountInvPortn
		EkiOnOff,
	rm10010perfdatacomclientCurrent15StatInPacketCountPortn
		Counter64,
	rm10010perfdatacomclientCurrent15StatInCrcCountInvPortn
		EkiOnOff,
	rm10010perfdatacomclientCurrent15StatInCrcCountPortn
		Counter64
	}


rm10010PerfDatacomClientCurrent15StatIndex OBJECT-TYPE
	SYNTAX  INTEGER(0..128)
	MAX-ACCESS  read-only
	STATUS current
	DESCRIPTION
        "
        Index definition for the rm10010PerfDatacomClientCurrent15Stat
        table
        "
	::= { rm10010PerfDatacomClientCurrent15StatEntry 1 }


rm10010perfdatacomclientCurrent15StatOutPacketCountInvPortn OBJECT-TYPE
	SYNTAX  EkiOnOff
	MAX-ACCESS read-only
	STATUS current
	DESCRIPTION
        "
        Client Current 15-min Output Packet
        counter inv. :This OID indicates
        that the current 15-min Output
         Packets counter is invalid
        "
	::= { rm10010PerfDatacomClientCurrent15StatEntry 30 }


rm10010perfdatacomclientCurrent15StatOutPacketCountPortn OBJECT-TYPE
	SYNTAX  Counter64
	MAX-ACCESS read-only
	STATUS current
	DESCRIPTION
        "
        Client Current 15-min Output Packet
        counter :This OID gives the current
        15-min Output Packets counter value
        "
	::= { rm10010PerfDatacomClientCurrent15StatEntry 31 }


rm10010perfdatacomclientCurrent15StatOutCrcCountInvPortn OBJECT-TYPE
	SYNTAX  EkiOnOff
	MAX-ACCESS read-only
	STATUS current
	DESCRIPTION
        "
        Client Current 15-min Output CRC
        counter inv. :This OID indicates
        that the current 15-min Output
         CRC counter is invalid
        "
	::= { rm10010PerfDatacomClientCurrent15StatEntry 28 }


rm10010perfdatacomclientCurrent15StatOutCrcCountPortn OBJECT-TYPE
	SYNTAX  Counter64
	MAX-ACCESS read-only
	STATUS current
	DESCRIPTION
        "
        Client Current 15-min Output CRC
        counter :This OID gives the current
        15-min Output CRC counter value
        "
	::= { rm10010PerfDatacomClientCurrent15StatEntry 29 }


rm10010perfdatacomclientCurrent15StatInPacketCountInvPortn OBJECT-TYPE
	SYNTAX  EkiOnOff
	MAX-ACCESS read-only
	STATUS current
	DESCRIPTION
        "
        Client Current 15-min Input Packet
        counter inv. :This OID indicates
        that the current 15-min Input Packet
        counter is invalid
        "
	::= { rm10010PerfDatacomClientCurrent15StatEntry 6 }


rm10010perfdatacomclientCurrent15StatInPacketCountPortn OBJECT-TYPE
	SYNTAX  Counter64
	MAX-ACCESS read-only
	STATUS current
	DESCRIPTION
        "
        Client Current 15-min Input Packet
        counter :This OID gives the current
        15-min Input Packet counter value
        "
	::= { rm10010PerfDatacomClientCurrent15StatEntry 7 }


rm10010perfdatacomclientCurrent15StatInCrcCountInvPortn OBJECT-TYPE
	SYNTAX  EkiOnOff
	MAX-ACCESS read-only
	STATUS current
	DESCRIPTION
        "
        Client Current 15-min Input CRC
        counter inv. :This OID indicates
        that the current 15-min Input CRC
        counter is invalid
        "
	::= { rm10010PerfDatacomClientCurrent15StatEntry 4 }


rm10010perfdatacomclientCurrent15StatInCrcCountPortn OBJECT-TYPE
	SYNTAX  Counter64
	MAX-ACCESS read-only
	STATUS current
	DESCRIPTION
        "
        Client Current 15-min Input CRC
        counter :This OID gives the current
        15-min Input CRC counter value
        "
	::= { rm10010PerfDatacomClientCurrent15StatEntry 5 }


--- *****************************************************
---     Leaf of the datacomClientPast15Stat
--- *****************************************************
--- *********************************************************
---     TABLE for the rm10010PerfDatacomClientPast15StatHistory articles
--- *********************************************************

rm10010PerfDatacomClientPast15StatHistoryPort1Table OBJECT-TYPE
	SYNTAX  SEQUENCE OF Rm10010PerfDatacomClientPast15StatHistoryPort1Entry
	MAX-ACCESS not-accessible
	STATUS current
	DESCRIPTION
        "
        List of rm10010PerfDatacomClientPast15StatHistory
        Article
        "
	::= { rm10010MonPerfClient 448 }


rm10010PerfDatacomClientPast15StatHistoryPort1Entry OBJECT-TYPE
	SYNTAX Rm10010PerfDatacomClientPast15StatHistoryPort1Entry
	MAX-ACCESS not-accessible
	STATUS current
	DESCRIPTION
        "
        Row definition for the rm10010PerfDatacomClientPast15StatHistory
        table
        "
	INDEX   { rm10010PerfDatacomClientPast15StatHistoryPort1Index }
	::= { rm10010PerfDatacomClientPast15StatHistoryPort1Table 1 }


Rm10010PerfDatacomClientPast15StatHistoryPort1Entry ::=
	SEQUENCE {
	rm10010PerfDatacomClientPast15StatHistoryPort1Index
		INTEGER,
	rm10010perfdatacomclientPast15StatOutPacketCountInvPort1
		EkiOnOff,
	rm10010perfdatacomclientPast15StatOutPacketCountPort1
		Counter64,
	rm10010perfdatacomclientPast15StatOutCrcCountInvPort1
		EkiOnOff,
	rm10010perfdatacomclientPast15StatOutCrcCountPort1
		Counter64,
	rm10010perfdatacomclientPast15StatInPacketCountInvPort1
		EkiOnOff,
	rm10010perfdatacomclientPast15StatInPacketCountPort1
		Counter64,
	rm10010perfdatacomclientPast15StatInCrcCountInvPort1
		EkiOnOff,
	rm10010perfdatacomclientPast15StatInCrcCountPort1
		Counter64
	}


rm10010PerfDatacomClientPast15StatHistoryPort1Index OBJECT-TYPE
	SYNTAX  INTEGER(0..128)
	MAX-ACCESS  read-only
	STATUS current
	DESCRIPTION
        "
        Index definition for the rm10010PerfDatacomClientPast15StatHistory
        table
        "
	::= { rm10010PerfDatacomClientPast15StatHistoryPort1Entry 1 }


rm10010perfdatacomclientPast15StatOutPacketCountInvPort1 OBJECT-TYPE
	SYNTAX  EkiOnOff
	MAX-ACCESS read-only
	STATUS current
	DESCRIPTION
        "
        Client Past 15-min Output Packet
        counter inv. :This OID indicates
        that the past 15-min Output Packets
        counter is invalid
        "
	::= { rm10010PerfDatacomClientPast15StatHistoryPort1Entry 30 }


rm10010perfdatacomclientPast15StatOutPacketCountPort1 OBJECT-TYPE
	SYNTAX  Counter64
	MAX-ACCESS read-only
	STATUS current
	DESCRIPTION
        "
        Client Past 15-min Output Packet
        counter :This OID gives the past
        15-min Output Packets counter value
        "
	::= { rm10010PerfDatacomClientPast15StatHistoryPort1Entry 31 }


rm10010perfdatacomclientPast15StatOutCrcCountInvPort1 OBJECT-TYPE
	SYNTAX  EkiOnOff
	MAX-ACCESS read-only
	STATUS current
	DESCRIPTION
        "
        Client Past 15-min Output CRC
         counter inv. :This OID indicates
        that the past 15-min Output CRC
        counter is invalid
        "
	::= { rm10010PerfDatacomClientPast15StatHistoryPort1Entry 28 }


rm10010perfdatacomclientPast15StatOutCrcCountPort1 OBJECT-TYPE
	SYNTAX  Counter64
	MAX-ACCESS read-only
	STATUS current
	DESCRIPTION
        "
        Client Past 15-min Output CRC
         counter :This OID gives the past
        15-min Output CRC counter value
        "
	::= { rm10010PerfDatacomClientPast15StatHistoryPort1Entry 29 }


rm10010perfdatacomclientPast15StatInPacketCountInvPort1 OBJECT-TYPE
	SYNTAX  EkiOnOff
	MAX-ACCESS read-only
	STATUS current
	DESCRIPTION
        "
        Client Past 15-min Input Packet
        counter inv. :This OID indicates
        that the past 15-min Input Packet
        counter is invalid
        "
	::= { rm10010PerfDatacomClientPast15StatHistoryPort1Entry 6 }


rm10010perfdatacomclientPast15StatInPacketCountPort1 OBJECT-TYPE
	SYNTAX  Counter64
	MAX-ACCESS read-only
	STATUS current
	DESCRIPTION
        "
        Client Past 15-min Input Packet
        counter :This OID gives the past
        15-min Input Packet counter value
        "
	::= { rm10010PerfDatacomClientPast15StatHistoryPort1Entry 7 }


rm10010perfdatacomclientPast15StatInCrcCountInvPort1 OBJECT-TYPE
	SYNTAX  EkiOnOff
	MAX-ACCESS read-only
	STATUS current
	DESCRIPTION
        "
        Client Past 15-min Input CRC counter
        inv. :This OID indicates that the
        past 15-min Input CRC counter is
        invalid
        "
	::= { rm10010PerfDatacomClientPast15StatHistoryPort1Entry 4 }


rm10010perfdatacomclientPast15StatInCrcCountPort1 OBJECT-TYPE
	SYNTAX  Counter64
	MAX-ACCESS read-only
	STATUS current
	DESCRIPTION
        "
        Client Past 15-min Input CRC counter
        :This OID gives the past 15-min
        Input CRC counter value
        "
	::= { rm10010PerfDatacomClientPast15StatHistoryPort1Entry 5 }


--- *****************************************************
---     Leaf of the datacomClientCurrent24Stat
--- *****************************************************
--- *********************************************************
---     TABLE for the rm10010PerfDatacomClientCurrent24Stat articles
--- *********************************************************

rm10010PerfDatacomClientCurrent24StatTable OBJECT-TYPE
	SYNTAX  SEQUENCE OF Rm10010PerfDatacomClientCurrent24StatEntry
	MAX-ACCESS not-accessible
	STATUS current
	DESCRIPTION
        "
        List of rm10010PerfDatacomClientCurrent24Stat
        Article
        "
	::= { rm10010MonPerfClient 464 }


rm10010PerfDatacomClientCurrent24StatEntry OBJECT-TYPE
	SYNTAX Rm10010PerfDatacomClientCurrent24StatEntry
	MAX-ACCESS not-accessible
	STATUS current
	DESCRIPTION
        "
        Row definition for the rm10010PerfDatacomClientCurrent24Stat
        table
        "
	INDEX   { rm10010PerfDatacomClientCurrent24StatIndex }
	::= { rm10010PerfDatacomClientCurrent24StatTable 1 }


Rm10010PerfDatacomClientCurrent24StatEntry ::=
	SEQUENCE {
	rm10010PerfDatacomClientCurrent24StatIndex
		INTEGER,
	rm10010perfdatacomclientCurrent24StatOutPacketCountInvPortn
		EkiOnOff,
	rm10010perfdatacomclientCurrent24StatOutPacketCountPortn
		Counter64,
	rm10010perfdatacomclientCurrent24StatOutCrcCountInvPortn
		EkiOnOff,
	rm10010perfdatacomclientCurrent24StatOutCrcCountPortn
		Counter64,
	rm10010perfdatacomclientCurrent24StatInPacketCountInvPortn
		EkiOnOff,
	rm10010perfdatacomclientCurrent24StatInPacketCountPortn
		Counter64,
	rm10010perfdatacomclientCurrent24StatInCrcCountInvPortn
		EkiOnOff,
	rm10010perfdatacomclientCurrent24StatInCrcCountPortn
		Counter64
	}


rm10010PerfDatacomClientCurrent24StatIndex OBJECT-TYPE
	SYNTAX  INTEGER(0..128)
	MAX-ACCESS  read-only
	STATUS current
	DESCRIPTION
        "
        Index definition for the rm10010PerfDatacomClientCurrent24Stat
        table
        "
	::= { rm10010PerfDatacomClientCurrent24StatEntry 1 }


rm10010perfdatacomclientCurrent24StatOutPacketCountInvPortn OBJECT-TYPE
	SYNTAX  EkiOnOff
	MAX-ACCESS read-only
	STATUS current
	DESCRIPTION
        "
        Client Current 24-hours Output
        Packet counter inv. :This OID indicates
        that the current 24-hours Output
        Packets counter is invalid
        "
	::= { rm10010PerfDatacomClientCurrent24StatEntry 30 }


rm10010perfdatacomclientCurrent24StatOutPacketCountPortn OBJECT-TYPE
	SYNTAX  Counter64
	MAX-ACCESS read-only
	STATUS current
	DESCRIPTION
        "
        Client Current 24-hours Output
        Packet counter :This OID gives
         the current 24-hours Output Packets
        counter value
        "
	::= { rm10010PerfDatacomClientCurrent24StatEntry 31 }


rm10010perfdatacomclientCurrent24StatOutCrcCountInvPortn OBJECT-TYPE
	SYNTAX  EkiOnOff
	MAX-ACCESS read-only
	STATUS current
	DESCRIPTION
        "
        Client Current 24-hours Output
        CRC counter inv. :This OID indicates
        that the current 24-hours Output
        CRC counter is invalid
        "
	::= { rm10010PerfDatacomClientCurrent24StatEntry 28 }


rm10010perfdatacomclientCurrent24StatOutCrcCountPortn OBJECT-TYPE
	SYNTAX  Counter64
	MAX-ACCESS read-only
	STATUS current
	DESCRIPTION
        "
        Client Current 24-hours Output
        CRC counter :This OID gives the
        current 24-hours Output CRC counter
        value
        "
	::= { rm10010PerfDatacomClientCurrent24StatEntry 29 }


rm10010perfdatacomclientCurrent24StatInPacketCountInvPortn OBJECT-TYPE
	SYNTAX  EkiOnOff
	MAX-ACCESS read-only
	STATUS current
	DESCRIPTION
        "
        Client Current 24-hours Input
         Packet counter inv. :This OID
         indicates that the current 24-hours
        Input Packet counter is invalid
        "
	::= { rm10010PerfDatacomClientCurrent24StatEntry 6 }


rm10010perfdatacomclientCurrent24StatInPacketCountPortn OBJECT-TYPE
	SYNTAX  Counter64
	MAX-ACCESS read-only
	STATUS current
	DESCRIPTION
        "
        Client Current 24-hours Input
         Packet counter :This OID gives
        the current 24-hours Input Packet
        counter value
        "
	::= { rm10010PerfDatacomClientCurrent24StatEntry 7 }


rm10010perfdatacomclientCurrent24StatInCrcCountInvPortn OBJECT-TYPE
	SYNTAX  EkiOnOff
	MAX-ACCESS read-only
	STATUS current
	DESCRIPTION
        "
        Client Current 24-hours Input
         CRC counter inv. :This OID indicates
        that the current 24-hours Input
        CRC counter is invalid
        "
	::= { rm10010PerfDatacomClientCurrent24StatEntry 4 }


rm10010perfdatacomclientCurrent24StatInCrcCountPortn OBJECT-TYPE
	SYNTAX  Counter64
	MAX-ACCESS read-only
	STATUS current
	DESCRIPTION
        "
        Client Current 24-hours Input
         CRC counter :This OID gives the
        current 24-hours Input CRC counter
        value
        "
	::= { rm10010PerfDatacomClientCurrent24StatEntry 5 }


--- *****************************************************
---     Leaf of the datacomClientPast24Stat
--- *****************************************************
--- *********************************************************
---     TABLE for the rm10010PerfDatacomClientPast24StatHistory articles
--- *********************************************************

rm10010PerfDatacomClientPast24StatHistoryPort1Table OBJECT-TYPE
	SYNTAX  SEQUENCE OF Rm10010PerfDatacomClientPast24StatHistoryPort1Entry
	MAX-ACCESS not-accessible
	STATUS current
	DESCRIPTION
        "
        List of rm10010PerfDatacomClientPast24StatHistory
        Article
        "
	::= { rm10010MonPerfClient 480 }


rm10010PerfDatacomClientPast24StatHistoryPort1Entry OBJECT-TYPE
	SYNTAX Rm10010PerfDatacomClientPast24StatHistoryPort1Entry
	MAX-ACCESS not-accessible
	STATUS current
	DESCRIPTION
        "
        Row definition for the rm10010PerfDatacomClientPast24StatHistory
        table
        "
	INDEX   { rm10010PerfDatacomClientPast24StatHistoryPort1Index }
	::= { rm10010PerfDatacomClientPast24StatHistoryPort1Table 1 }


Rm10010PerfDatacomClientPast24StatHistoryPort1Entry ::=
	SEQUENCE {
	rm10010PerfDatacomClientPast24StatHistoryPort1Index
		INTEGER,
	rm10010perfdatacomclientPast24StatOutPacketCountInvPort1
		EkiOnOff,
	rm10010perfdatacomclientPast24StatOutPacketCountPort1
		Counter64,
	rm10010perfdatacomclientPast24StatOutCrcCountInvPort1
		EkiOnOff,
	rm10010perfdatacomclientPast24StatOutCrcCountPort1
		Counter64,
	rm10010perfdatacomclientPast24StatInPacketCountInvPort1
		EkiOnOff,
	rm10010perfdatacomclientPast24StatInPacketCountPort1
		Counter64,
	rm10010perfdatacomclientPast24StatInCrcCountInvPort1
		EkiOnOff,
	rm10010perfdatacomclientPast24StatInCrcCountPort1
		Counter64
	}


rm10010PerfDatacomClientPast24StatHistoryPort1Index OBJECT-TYPE
	SYNTAX  INTEGER(0..128)
	MAX-ACCESS  read-only
	STATUS current
	DESCRIPTION
        "
        Index definition for the rm10010PerfDatacomClientPast24StatHistory
        table
        "
	::= { rm10010PerfDatacomClientPast24StatHistoryPort1Entry 1 }


rm10010perfdatacomclientPast24StatOutPacketCountInvPort1 OBJECT-TYPE
	SYNTAX  EkiOnOff
	MAX-ACCESS read-only
	STATUS current
	DESCRIPTION
        "
        Client Past 24-hours Output Packet
        counter inv. :This OID indicates
        that the past 24-hours Output Packets
        counter is invalid
        "
	::= { rm10010PerfDatacomClientPast24StatHistoryPort1Entry 30 }


rm10010perfdatacomclientPast24StatOutPacketCountPort1 OBJECT-TYPE
	SYNTAX  Counter64
	MAX-ACCESS read-only
	STATUS current
	DESCRIPTION
        "
        Client Past 24-hours Output Packet
        counter :This OID gives the past
        24-hours Output Packets counter
        value
        "
	::= { rm10010PerfDatacomClientPast24StatHistoryPort1Entry 31 }


rm10010perfdatacomclientPast24StatOutCrcCountInvPort1 OBJECT-TYPE
	SYNTAX  EkiOnOff
	MAX-ACCESS read-only
	STATUS current
	DESCRIPTION
        "
        Client Past 24-hours Output CRC
        counter inv. :This OID indicates
        that the past 24-hours Output CRC
        counter is invalid
        "
	::= { rm10010PerfDatacomClientPast24StatHistoryPort1Entry 28 }


rm10010perfdatacomclientPast24StatOutCrcCountPort1 OBJECT-TYPE
	SYNTAX  Counter64
	MAX-ACCESS read-only
	STATUS current
	DESCRIPTION
        "
        Client Past 24-hours Output CRC
        counter :This OID gives the past
        24-hours Output CRC counter value
        "
	::= { rm10010PerfDatacomClientPast24StatHistoryPort1Entry 29 }


rm10010perfdatacomclientPast24StatInPacketCountInvPort1 OBJECT-TYPE
	SYNTAX  EkiOnOff
	MAX-ACCESS read-only
	STATUS current
	DESCRIPTION
        "
        Client Past 24-hours Input Packet
        counter inv. :This OID indicates
        that the past 24-hours Input Packet
        counter is invalid
        "
	::= { rm10010PerfDatacomClientPast24StatHistoryPort1Entry 6 }


rm10010perfdatacomclientPast24StatInPacketCountPort1 OBJECT-TYPE
	SYNTAX  Counter64
	MAX-ACCESS read-only
	STATUS current
	DESCRIPTION
        "
        Client Past 24-hours Input Packet
        counter :This OID gives the past
        24-hours Input Packet counter value
        "
	::= { rm10010PerfDatacomClientPast24StatHistoryPort1Entry 7 }


rm10010perfdatacomclientPast24StatInCrcCountInvPort1 OBJECT-TYPE
	SYNTAX  EkiOnOff
	MAX-ACCESS read-only
	STATUS current
	DESCRIPTION
        "
        Client Past 24-hours Input CRC
        counter inv. :This OID indicates
        that the past 24-hours Input CRC
        counter is invalid
        "
	::= { rm10010PerfDatacomClientPast24StatHistoryPort1Entry 4 }


rm10010perfdatacomclientPast24StatInCrcCountPort1 OBJECT-TYPE
	SYNTAX  Counter64
	MAX-ACCESS read-only
	STATUS current
	DESCRIPTION
        "
        Client Past 24-hours Input CRC
        counter :This OID gives the past
        24-hours Input CRC counter value
        "
	::= { rm10010PerfDatacomClientPast24StatHistoryPort1Entry 5 }



rm10010PerfEnable OBJECT-TYPE
	SYNTAX EkiOnOff
	MAX-ACCESS read-write
	STATUS current
	DESCRIPTION
        "
        Perf. Mon. Enable :This OID enables
        the Performance Monitoring application
        "
	::= { rm10010MonPerfSync 257 }


rm10010Perf15minSync OBJECT-TYPE
	SYNTAX EkiOnOff
	MAX-ACCESS read-write
	STATUS current
	DESCRIPTION
        "
        Perf. Mon. 15-min sync. :This
         OID must be used in external synchronisation
        mode only to send a 15-min synchronisation
        command
        "
	::= { rm10010MonPerfSync 259 }


rm10010Perf24hSync OBJECT-TYPE
	SYNTAX EkiOnOff
	MAX-ACCESS read-write
	STATUS current
	DESCRIPTION
        "
        Perf. Mon. 24-hours sync. :This
        OID must be used in external synchronisation
        mode only to send a 24-hours synchronisation
        command
        "
	::= { rm10010MonPerfSync 260 }


rm10010Perf15MinShort OBJECT-TYPE
	SYNTAX EkiOnOff
	MAX-ACCESS read-write
	STATUS current
	DESCRIPTION
        "
        15-min period is short :This OID
        indicates that the 15-min period
        lasts less than 890 seconds
        "
	::= { rm10010MonPerfTimeStamp 1 }


rm10010Perf15MinLong OBJECT-TYPE
	SYNTAX EkiOnOff
	MAX-ACCESS read-write
	STATUS current
	DESCRIPTION
        "
        15-min period is long :This OID
        indicates that the 15-min period
        lasts more than 910 seconds
        "
	::= { rm10010MonPerfTimeStamp 2 }


rm10010Perf24HoursShort OBJECT-TYPE
	SYNTAX Counter32
	MAX-ACCESS read-write
	STATUS current
	DESCRIPTION
        "
        24-hours period is short :This
        OID indicates that 24-hours period
        lasts less than 86390 seconds
        "
	::= { rm10010MonPerfTimeStamp 5 }


rm10010Perf24HoursLong OBJECT-TYPE
	SYNTAX Counter32
	MAX-ACCESS read-write
	STATUS current
	DESCRIPTION
        "
        24-hours period is long :This
         OID indicates that 24-hours period
        lasts more than 86410 seconds
        "
	::= { rm10010MonPerfTimeStamp 6 }


rm10010PerfCurrent15MinElapsedTime OBJECT-TYPE
	SYNTAX Counter32
	MAX-ACCESS read-write
	STATUS current
	DESCRIPTION
        "
        Current 15min period Elapsed Time
         :This OID gives the number of
         seconds elapsed in the current
        15-minutes period
        "
	::= { rm10010MonPerfTimeStamp 7 }


rm10010PerfCurrent24HoursElapsedTime OBJECT-TYPE
	SYNTAX Counter32
	MAX-ACCESS read-write
	STATUS current
	DESCRIPTION
        "
        Current 24hours period Elapsed
        Time :This OID gives the number
        of seconds elapsed in the current
        24-hours period
        "
	::= { rm10010MonPerfTimeStamp 8 }






--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
rm10010DwlrestartProcess OBJECT IDENTIFIER ::= { rm10010DwlOther 0 }




rm10010DwlColdRestartProcessed OBJECT-TYPE
	  SYNTAX EkiOnOff
	  MAX-ACCESS read-only
	  STATUS current
	  DESCRIPTION
        "
        Cold Restart :This OID indicates
        that the module last restart was
        a Cold RESTART
        "
	  ::= { rm10010DwlrestartProcess 2 }



rm10010DwlWarmRestartProcessed OBJECT-TYPE
	  SYNTAX EkiOnOff
	  MAX-ACCESS read-only
	  STATUS current
	  DESCRIPTION
        "
        Warm Restart :This OID indicates
        that the module last restart was
        a Warm RESTART
        "
	  ::= { rm10010DwlrestartProcess 1 }



--- *****************************************************
---     LEAF for the swBanksUsed article
--- *****************************************************
rm10010DwlswBanksUsed OBJECT IDENTIFIER ::= { rm10010DwlOther 1 }




rm10010DwlSwBank2Notempty OBJECT-TYPE
	  SYNTAX EkiOnOff
	  MAX-ACCESS read-only
	  STATUS current
	  DESCRIPTION
        "
        SW bank 2 loaded :This OID indicates
        a software is loaded in SW bank
        2  <Help>  This status indicates
        if the SW bank 2 contains SW package
        "
	  ::= { rm10010DwlswBanksUsed 6 }



rm10010DwlSwBank1Notempty OBJECT-TYPE
	  SYNTAX EkiOnOff
	  MAX-ACCESS read-only
	  STATUS current
	  DESCRIPTION
        "
        SW bank 1 loaded :This OID indicates
        a software is loaded in SW bank
        1  <Help>  This status indicates
        if the SW bank 1 contains SW package
        "
	  ::= { rm10010DwlswBanksUsed 5 }



rm10010DwlSwBank2Used OBJECT-TYPE
	  SYNTAX EkiOnOff
	  MAX-ACCESS read-only
	  STATUS current
	  DESCRIPTION
        "
        SW bank 2 active :This OID indicates
        the module is working on SW bank
        2  <Help>  This status indicates
        if the SW bank 2 is active or standby
        "
	  ::= { rm10010DwlswBanksUsed 2 }



rm10010DwlSwBank1Used OBJECT-TYPE
	  SYNTAX EkiOnOff
	  MAX-ACCESS read-only
	  STATUS current
	  DESCRIPTION
        "
        SW bank 1 active :This OID indicates
        the module is working on SW bank
        1  <Help>  This status indicates
        if the SW bank 1 is active or standby
        "
	  ::= { rm10010DwlswBanksUsed 1 }



--- *****************************************************
---     LEAF for the gwBanksUsed article
--- *****************************************************
rm10010DwlgwBanksUsed OBJECT IDENTIFIER ::= { rm10010DwlOther 2 }




rm10010DwlGwBank4Notempty OBJECT-TYPE
	  SYNTAX EkiOnOff
	  MAX-ACCESS read-only
	  STATUS current
	  DESCRIPTION
        "
        GW bank 4 loaded :This OID indicates
        a gateware is loaded in GW bank
        4
        "
	  ::= { rm10010DwlgwBanksUsed 8 }



rm10010DwlGwBank3Notempty OBJECT-TYPE
	  SYNTAX EkiOnOff
	  MAX-ACCESS read-only
	  STATUS current
	  DESCRIPTION
        "
        GW bank 3 loaded :This OID indicates
        a gateware is loaded in GW bank
        3  <Help>  This status indicates
        if the GW bank 3 contains GW package
        "
	  ::= { rm10010DwlgwBanksUsed 7 }



rm10010DwlGwBank2Notempty OBJECT-TYPE
	  SYNTAX EkiOnOff
	  MAX-ACCESS read-only
	  STATUS current
	  DESCRIPTION
        "
        GW bank 2 loaded :This OID indicates
        a gateware is loaded in GW bank
        2
        "
	  ::= { rm10010DwlgwBanksUsed 6 }



rm10010DwlGwBank1Notempty OBJECT-TYPE
	  SYNTAX EkiOnOff
	  MAX-ACCESS read-only
	  STATUS current
	  DESCRIPTION
        "
        GW bank 1 loaded :This OID indicates
        a gateware is loaded in GW bank
        1  <Help>  This status indicates
        if the GW bank 1 contains GW package
        "
	  ::= { rm10010DwlgwBanksUsed 5 }



rm10010DwlGwBank4Used OBJECT-TYPE
	  SYNTAX EkiOnOff
	  MAX-ACCESS read-only
	  STATUS current
	  DESCRIPTION
        "
        GW bank 4 active :This OID indicates
        the module is working on GW bank
        4
        "
	  ::= { rm10010DwlgwBanksUsed 4 }



rm10010DwlGwBank3Used OBJECT-TYPE
	  SYNTAX EkiOnOff
	  MAX-ACCESS read-only
	  STATUS current
	  DESCRIPTION
        "
        GW bank 3 active :This OID indicates
        the module is working on GW bank
        3  <Help>  This status indicates
        if the GW bank 3 is active or standby
        "
	  ::= { rm10010DwlgwBanksUsed 3 }



rm10010DwlGwBank2Used OBJECT-TYPE
	  SYNTAX EkiOnOff
	  MAX-ACCESS read-only
	  STATUS current
	  DESCRIPTION
        "
        GW bank 2 active :This OID indicates
        the module is working on GW bank
        2
        "
	  ::= { rm10010DwlgwBanksUsed 2 }



rm10010DwlGwBank1Used OBJECT-TYPE
	  SYNTAX EkiOnOff
	  MAX-ACCESS read-only
	  STATUS current
	  DESCRIPTION
        "
        GW bank 1 active :This OID indicates
        the module is working on GW bank
        1  <Help>  This status indicates
        if the GW bank 1 is active or standby
        "
	  ::= { rm10010DwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

rm10010CfgAccessCAisCsf OBJECT IDENTIFIER ::= { rm10010Config 1 }



--- *****************************************************
---     LEAF for the table 0012
--- *****************************************************

rm10010CfgClientcaiscsfTable OBJECT-TYPE
	SYNTAX  SEQUENCE OF Rm10010CfgClientcaiscsfEntry
	MAX-ACCESS not-accessible
	STATUS current
	DESCRIPTION
        "
        List of  Article
        "
	::= { rm10010CfgAccessCAisCsf 1 }


rm10010CfgClientcaiscsfEntry OBJECT-TYPE
	SYNTAX Rm10010CfgClientcaiscsfEntry
	MAX-ACCESS not-accessible
	STATUS current
	DESCRIPTION
        "
        Row definition for the accessCAisCsf
        table
        "
	INDEX   { rm10010CfgClientcaiscsfIndex }
	::= { rm10010CfgClientcaiscsfTable 1 }


Rm10010CfgClientcaiscsfEntry ::=
	SEQUENCE {
	rm10010CfgClientcaiscsfIndex
		INTEGER,
	rm10010CfgReservePortn
		Unsigned32
	}


rm10010CfgClientcaiscsfIndex OBJECT-TYPE
	SYNTAX  INTEGER(0..128)
	MAX-ACCESS  read-only
	STATUS current
	DESCRIPTION
        "
        Index definition for the clientcaiscsf
        table
        "
	::= { rm10010CfgClientcaiscsfEntry 1 }


rm10010CfgReservePortn OBJECT-TYPE
	SYNTAX  Unsigned32 (0..65536)
	MAX-ACCESS read-write
	STATUS current
	DESCRIPTION
        "
        CAIS mode  on Client Port :This
        register enables/disables port
          laser shutdown on CAIS insertion
        condition
        "
	::= { rm10010CfgClientcaiscsfEntry 3 }


--- *****************************************************
---     LEAF for the table Group startup
--- *****************************************************

rm10010CfgStartup OBJECT IDENTIFIER ::= { rm10010Config 2 }



--- *****************************************************
---     LEAF for the table 2110
--- *****************************************************

rm10010CfgClientStartupTable OBJECT-TYPE
	SYNTAX  SEQUENCE OF Rm10010CfgClientStartupEntry
	MAX-ACCESS not-accessible
	STATUS current
	DESCRIPTION
        "
        List of  Article
        "
	::= { rm10010CfgStartup 1 }


rm10010CfgClientStartupEntry OBJECT-TYPE
	SYNTAX Rm10010CfgClientStartupEntry
	MAX-ACCESS not-accessible
	STATUS current
	DESCRIPTION
        "
        Row definition for the startup
        table
        "
	INDEX   { rm10010CfgClientStartupIndex }
	::= { rm10010CfgClientStartupTable 1 }


Rm10010CfgClientStartupEntry ::=
	SEQUENCE {
	rm10010CfgClientStartupIndex
		INTEGER,
	rm10010CfgSystConfPortPortn
		Unsigned32,
	rm10010CfgNetConfPortPortn
		Unsigned32,
	rm10010CfgOptionsPortPortn
		Unsigned32
	}


rm10010CfgClientStartupIndex OBJECT-TYPE
	SYNTAX  INTEGER(0..128)
	MAX-ACCESS  read-only
	STATUS current
	DESCRIPTION
        "
        Index definition for the clientStartup
        table
        "
	::= { rm10010CfgClientStartupEntry 1 }


rm10010CfgSystConfPortPortn OBJECT-TYPE
	SYNTAX  Unsigned32 (0..65536)
	MAX-ACCESS read-write
	STATUS current
	DESCRIPTION
        "
        Default Settings on Client Port
        :This  register configures the
         default initialisation settings
        on the port.
        "
	::= { rm10010CfgClientStartupEntry 3 }


rm10010CfgNetConfPortPortn OBJECT-TYPE
	SYNTAX  Unsigned32 (0..65536)
	MAX-ACCESS read-write
	STATUS current
	DESCRIPTION
        "
        Default Settings on Client Port
        :This  register configures the
         default initialisation settings
        on the port.
        "
	::= { rm10010CfgClientStartupEntry 4 }


rm10010CfgOptionsPortPortn OBJECT-TYPE
	SYNTAX  Unsigned32 (0..65536)
	MAX-ACCESS read-write
	STATUS current
	DESCRIPTION
        "
        Default Options on Client Port
        :This register configures the default
        options on the port.
        "
	::= { rm10010CfgClientStartupEntry 14 }


--- *****************************************************
---     LEAF for the table 2190
--- *****************************************************

rm10010CfgLineStartupTable OBJECT-TYPE
	SYNTAX  SEQUENCE OF Rm10010CfgLineStartupEntry
	MAX-ACCESS not-accessible
	STATUS current
	DESCRIPTION
        "
        List of  Article
        "
	::= { rm10010CfgStartup 2 }


rm10010CfgLineStartupEntry OBJECT-TYPE
	SYNTAX Rm10010CfgLineStartupEntry
	MAX-ACCESS not-accessible
	STATUS current
	DESCRIPTION
        "
        Row definition for the startup
        table
        "
	INDEX   { rm10010CfgLineStartupIndex }
	::= { rm10010CfgLineStartupTable 1 }


Rm10010CfgLineStartupEntry ::=
	SEQUENCE {
	rm10010CfgLineStartupIndex
		INTEGER,
	rm10010CfgSystConfLinePortn
		Unsigned32,
	rm10010CfgOptionsLinePortn
		Unsigned32
	}


rm10010CfgLineStartupIndex OBJECT-TYPE
	SYNTAX  INTEGER(0..128)
	MAX-ACCESS  read-only
	STATUS current
	DESCRIPTION
        "
        Index definition for the lineStartup
        table
        "
	::= { rm10010CfgLineStartupEntry 1 }


rm10010CfgSystConfLinePortn OBJECT-TYPE
	SYNTAX  Unsigned32 (0..65536)
	MAX-ACCESS read-write
	STATUS current
	DESCRIPTION
        "
        Default Settings on Line :This
        register configures the default
        initialisation settings on Line
        "
	::= { rm10010CfgLineStartupEntry 3 }


rm10010CfgOptionsLinePortn OBJECT-TYPE
	SYNTAX  Unsigned32 (0..65536)
	MAX-ACCESS read-write
	STATUS current
	DESCRIPTION
        "
        Default Options on Line :This
         register configures the default
        options on the line
        "
	::= { rm10010CfgLineStartupEntry 14 }


--- *****************************************************
---     LEAF for the table 21AB
--- *****************************************************

rm10010CfgXfpTable OBJECT-TYPE
	SYNTAX  SEQUENCE OF Rm10010CfgXfpEntry
	MAX-ACCESS not-accessible
	STATUS current
	DESCRIPTION
        "
        List of  Article
        "
	::= { rm10010CfgStartup 3 }


rm10010CfgXfpEntry OBJECT-TYPE
	SYNTAX Rm10010CfgXfpEntry
	MAX-ACCESS not-accessible
	STATUS current
	DESCRIPTION
        "
        Row definition for the startup
        table
        "
	INDEX   { rm10010CfgXfpIndex }
	::= { rm10010CfgXfpTable 1 }


Rm10010CfgXfpEntry ::=
	SEQUENCE {
	rm10010CfgXfpIndex
		INTEGER,
	rm10010CfgSystConfMsaLinePortn
		Unsigned32
	}


rm10010CfgXfpIndex OBJECT-TYPE
	SYNTAX  INTEGER(0..128)
	MAX-ACCESS  read-only
	STATUS current
	DESCRIPTION
        "
        Index definition for the xfp table
        "
	::= { rm10010CfgXfpEntry 1 }


rm10010CfgSystConfMsaLinePortn OBJECT-TYPE
	SYNTAX  Unsigned32 (0..65536)
	MAX-ACCESS read-write
	STATUS current
	DESCRIPTION
        "
        Default settings on MSA :This
         register configures the default
        initialisation settings on MSA
        "
	::= { rm10010CfgXfpEntry 3 }


--- *****************************************************
---     LEAF for the table Group labels
--- *****************************************************

rm10010CfgLabels OBJECT IDENTIFIER ::= { rm10010Config 3 }



--- *****************************************************
---     LEAF for the table 0003
--- *****************************************************

rm10010CfgLabelclientTable OBJECT-TYPE
	SYNTAX  SEQUENCE OF Rm10010CfgLabelclientEntry
	MAX-ACCESS not-accessible
	STATUS current
	DESCRIPTION
        "
        List of  Article
        "
	::= { rm10010CfgLabels 1 }


rm10010CfgLabelclientEntry OBJECT-TYPE
	SYNTAX Rm10010CfgLabelclientEntry
	MAX-ACCESS not-accessible
	STATUS current
	DESCRIPTION
        "
        Row definition for the labels
         table
        "
	INDEX   { rm10010CfgLabelclientIndex }
	::= { rm10010CfgLabelclientTable 1 }


Rm10010CfgLabelclientEntry ::=
	SEQUENCE {
	rm10010CfgLabelclientIndex
		INTEGER,
	rm10010CfgLabelclientPortn
		DisplayString
	}


rm10010CfgLabelclientIndex OBJECT-TYPE
	SYNTAX  INTEGER(0..128)
	MAX-ACCESS  read-only
	STATUS current
	DESCRIPTION
        "
        Index definition for the labelclient
        table
        "
	::= { rm10010CfgLabelclientEntry 1 }


rm10010CfgLabelclientPortn OBJECT-TYPE
	SYNTAX  DisplayString( SIZE(1..16))
	MAX-ACCESS read-write
	STATUS current
	DESCRIPTION
        "
        Default settings on the label
         of the Ports :These registers
         configures the default initialisation
        settings of the labels of the ports.
        "
	::= { rm10010CfgLabelclientEntry 3 }


--- *****************************************************
---     LEAF for the table 0004
--- *****************************************************

rm10010CfgLabellineTable OBJECT-TYPE
	SYNTAX  SEQUENCE OF Rm10010CfgLabellineEntry
	MAX-ACCESS not-accessible
	STATUS current
	DESCRIPTION
        "
        List of  Article
        "
	::= { rm10010CfgLabels 2 }


rm10010CfgLabellineEntry OBJECT-TYPE
	SYNTAX Rm10010CfgLabellineEntry
	MAX-ACCESS not-accessible
	STATUS current
	DESCRIPTION
        "
        Row definition for the labels
         table
        "
	INDEX   { rm10010CfgLabellineIndex }
	::= { rm10010CfgLabellineTable 1 }


Rm10010CfgLabellineEntry ::=
	SEQUENCE {
	rm10010CfgLabellineIndex
		INTEGER,
	rm10010CfgLabellinePortn
		DisplayString
	}


rm10010CfgLabellineIndex OBJECT-TYPE
	SYNTAX  INTEGER(0..128)
	MAX-ACCESS  read-only
	STATUS current
	DESCRIPTION
        "
        Index definition for the labelline
        table
        "
	::= { rm10010CfgLabellineEntry 1 }


rm10010CfgLabellinePortn OBJECT-TYPE
	SYNTAX  DisplayString( SIZE(1..16))
	MAX-ACCESS read-write
	STATUS current
	DESCRIPTION
        "
        Default settings on the label
         of the lines :These registers
         configures the default initialisation
        settings of the labels of the lines.
        "
	::= { rm10010CfgLabellineEntry 3 }


--- *****************************************************
---     LEAF for the table Group startuptlh
--- *****************************************************

rm10010CfgStartuptlh OBJECT IDENTIFIER ::= { rm10010Config 4 }



--- *****************************************************
---     LEAF for the table 25AB
--- *****************************************************

rm10010CfgOtxtlhTable OBJECT-TYPE
	SYNTAX  SEQUENCE OF Rm10010CfgOtxtlhEntry
	MAX-ACCESS not-accessible
	STATUS current
	DESCRIPTION
        "
        List of  Article
        "
	::= { rm10010CfgStartuptlh 1 }


rm10010CfgOtxtlhEntry OBJECT-TYPE
	SYNTAX Rm10010CfgOtxtlhEntry
	MAX-ACCESS not-accessible
	STATUS current
	DESCRIPTION
        "
        Row definition for the startuptlh
        table
        "
	INDEX   { rm10010CfgOtxtlhIndex }
	::= { rm10010CfgOtxtlhTable 1 }


Rm10010CfgOtxtlhEntry ::=
	SEQUENCE {
	rm10010CfgOtxtlhIndex
		INTEGER,
	rm10010CfgLinePwrLaserPortn
		Unsigned32,
	rm10010CfgLineFCurrentPortn
		Unsigned32,
	rm10010CfgLineGridCurrentPortn
		Unsigned32,
	rm10010CfgFPortn
		Unsigned32,
	rm10010CfgRxLineFCurrentPortn
		Unsigned32
	}


rm10010CfgOtxtlhIndex OBJECT-TYPE
	SYNTAX  INTEGER(0..128)
	MAX-ACCESS  read-only
	STATUS current
	DESCRIPTION
        "
        Index definition for the otxtlh
        table
        "
	::= { rm10010CfgOtxtlhEntry 1 }


rm10010CfgLinePwrLaserPortn OBJECT-TYPE
	SYNTAX  Unsigned32 (0..65536)
	MAX-ACCESS read-write
	STATUS current
	DESCRIPTION
        "
        Defaut Line output Power :This
        register configures the start-up
        output power of the Line tranceiver
         (Unit = dBm)
        "
	::= { rm10010CfgOtxtlhEntry 6 }


rm10010CfgLineFCurrentPortn OBJECT-TYPE
	SYNTAX  Unsigned32 (0..65536)
	MAX-ACCESS read-write
	STATUS current
	DESCRIPTION
        "
        Default Line transceiver Tx Channel
        :This register configures the start-up
        laser channel of the Line Tx transceiver
        "
	::= { rm10010CfgOtxtlhEntry 7 }


rm10010CfgLineGridCurrentPortn OBJECT-TYPE
	SYNTAX  Unsigned32 (0..65536)
	MAX-ACCESS read-write
	STATUS current
	DESCRIPTION
        "
        Default Line transceiver Grid
         :This register configures the
         start-up laser grid of the Line
        transceiver
        "
	::= { rm10010CfgOtxtlhEntry 8 }


rm10010CfgFPortn OBJECT-TYPE
	SYNTAX  Unsigned32 (0..65536)
	MAX-ACCESS read-write
	STATUS current
	DESCRIPTION
        "
        Default Line TRX lowest Freq :This
        register configures the start-up
        lowest frequency of the Line transceiver
        "
	::= { rm10010CfgOtxtlhEntry 9 }


rm10010CfgRxLineFCurrentPortn OBJECT-TYPE
	SYNTAX  Unsigned32 (0..65536)
	MAX-ACCESS read-write
	STATUS current
	DESCRIPTION
        "
        Default Line transceiver Rx Channel
        :This register configures the start-up
        laser channel of the Line Rx transceiver
        "
	::= { rm10010CfgOtxtlhEntry 10 }


--- *****************************************************
---     LEAF for the table Group other
--- *****************************************************

rm10010CfgOther OBJECT IDENTIFIER ::= { rm10010Config 5 }



--- *****************************************************
---     LEAF for the table 2300
--- *****************************************************

rm10010tablemoduleOther OBJECT IDENTIFIER ::= { rm10010CfgOther 1 }



rm10010Cfgmode OBJECT-TYPE
	  SYNTAX Unsigned32 (0..65536)
	  MAX-ACCESS read-write
	  STATUS current
	  DESCRIPTION
        "
        Default settings on Module :This
        register selects the configuration
        mode of the module
        "
	  ::= { rm10010tablemoduleOther 2 }



rm10010CfgfanLowSpeedThreshold OBJECT-TYPE
	  SYNTAX Unsigned32 (0..65536)
	  MAX-ACCESS read-write
	  STATUS current
	  DESCRIPTION
        "
        Default settings on Module :This
        register selects the speed threshold
        of the fan's
        "
	  ::= { rm10010tablemoduleOther 3 }



rm10010CfgfanHighSpeedThreshold OBJECT-TYPE
	  SYNTAX Unsigned32 (0..65536)
	  MAX-ACCESS read-write
	  STATUS current
	  DESCRIPTION
        "
        Default settings on Module :This
        register selects the speed threshold
        of the fan's
        "
	  ::= { rm10010tablemoduleOther 4 }



--- *****************************************************
---     LEAF for the table Group startuptablefive
--- *****************************************************

rm10010CfgStartuptablefive OBJECT IDENTIFIER ::= { rm10010Config 6 }



--- *****************************************************
---     LEAF for the table 0005
--- *****************************************************

rm10010CfgOtxtlhcapabilitiesTable OBJECT-TYPE
	SYNTAX  SEQUENCE OF Rm10010CfgOtxtlhcapabilitiesEntry
	MAX-ACCESS not-accessible
	STATUS current
	DESCRIPTION
        "
        List of  Article
        "
	::= { rm10010CfgStartuptablefive 1 }


rm10010CfgOtxtlhcapabilitiesEntry OBJECT-TYPE
	SYNTAX Rm10010CfgOtxtlhcapabilitiesEntry
	MAX-ACCESS not-accessible
	STATUS current
	DESCRIPTION
        "
        Row definition for the startuptablefive
        table
        "
	INDEX   { rm10010CfgOtxtlhcapabilitiesIndex }
	::= { rm10010CfgOtxtlhcapabilitiesTable 1 }


Rm10010CfgOtxtlhcapabilitiesEntry ::=
	SEQUENCE {
	rm10010CfgOtxtlhcapabilitiesIndex
		INTEGER,
	rm10010CfgComponentTypePortn
		Unsigned32,
	rm10010CfgMiscellaneousPortn
		Unsigned32,
	rm10010CfgFirstChannelPortn
		Unsigned32,
	rm10010CfgLastChannelPortn
		Unsigned32,
	rm10010CfgGridPortn
		Unsigned32
	}


rm10010CfgOtxtlhcapabilitiesIndex OBJECT-TYPE
	SYNTAX  INTEGER(0..128)
	MAX-ACCESS  read-only
	STATUS current
	DESCRIPTION
        "
        Index definition for the otxtlhcapabilities
        table
        "
	::= { rm10010CfgOtxtlhcapabilitiesEntry 1 }


rm10010CfgComponentTypePortn OBJECT-TYPE
	SYNTAX  Unsigned32 (0..65536)
	MAX-ACCESS read-only
	STATUS current
	DESCRIPTION
        "
        Component parameters :This OID
        defines the component parameters
        "
	::= { rm10010CfgOtxtlhcapabilitiesEntry 3 }


rm10010CfgMiscellaneousPortn OBJECT-TYPE
	SYNTAX  Unsigned32 (0..65536)
	MAX-ACCESS read-only
	STATUS current
	DESCRIPTION
        "
        Miscellaneous default settings
        :This OID defines the miscellaneous
        parameters
        "
	::= { rm10010CfgOtxtlhcapabilitiesEntry 4 }


rm10010CfgFirstChannelPortn OBJECT-TYPE
	SYNTAX  Unsigned32 (0..65536)
	MAX-ACCESS read-only
	STATUS current
	DESCRIPTION
        "
        Number of the first channel of
        the component :This OID defines
        the first channel number of the
        PM
        "
	::= { rm10010CfgOtxtlhcapabilitiesEntry 5 }


rm10010CfgLastChannelPortn OBJECT-TYPE
	SYNTAX  Unsigned32 (0..65536)
	MAX-ACCESS read-only
	STATUS current
	DESCRIPTION
        "
        Number of the last channel of
         the component :This OID defines
        the last channel number of the
         PM
        "
	::= { rm10010CfgOtxtlhcapabilitiesEntry 6 }


rm10010CfgGridPortn OBJECT-TYPE
	SYNTAX  Unsigned32 (0..65536)
	MAX-ACCESS read-only
	STATUS current
	DESCRIPTION
        "
        Grid value of the component :This
        OID defines the grid of the PM
        "
	::= { rm10010CfgOtxtlhcapabilitiesEntry 7 }



rm10010CfgWriteConfiguration  OBJECT-TYPE
	SYNTAX EkiOnOff
	MAX-ACCESS read-write
	STATUS current
	DESCRIPTION
	"Write configuration to module:This OID
	 writes the complete configuration to the module"
	::= { rm10010Config 257 }






--- *****************************************************
---     TRAP OBJECTS
--- *****************************************************

rm10010trapPortNumber OBJECT-TYPE
	SYNTAX INTEGER(1..64)
	MAX-ACCESS read-only
	STATUS current
	DESCRIPTION
	"Last port which generates a trap"
	::= { rm10010traps 2 }

rm10010trapLineNumber OBJECT-TYPE
	SYNTAX INTEGER(1..64)
	MAX-ACCESS read-only
	STATUS current
	DESCRIPTION
	"Last Line which generates a trap"
	::= { rm10010traps 3 }

rm10010trapBoardNumber OBJECT-TYPE
	SYNTAX INTEGER(1..64)
	MAX-ACCESS read-only
	STATUS current
	DESCRIPTION
	"Last module which generates a trap"
	::= { rm10010traps 4 }







--- *****************************************************
---     LINE TRAPS
--- *****************************************************

rm10010LineTrapNotUrgentGoesOn NOTIFICATION-TYPE
	OBJECTS {rm10010AlmLineDdmWarningPortn, rm10010trapLineNumber, rm10010trapBoardNumber}
	STATUS current
	--&FILTNAME    "RM10010 Line Not Urgent ON"
	--&ACTIONS     { log, minor }
	--&MATCH       { rm10010AlmLineDdmWarningPortn "on", rm10010trapLineNumber "$2", rm10010trapBoardNumber "$3"}
	--&MESG        "DDM Warning appears on Line Port $2 of RM10010 in Slot $3 ($A)"
	DESCRIPTION "Not urgent Line default is activated"
	::= { rm10010traps 30 }

rm10010LineTrapNotUrgentGoesOff NOTIFICATION-TYPE
	OBJECTS {rm10010AlmLineDdmWarningPortn, rm10010trapLineNumber, rm10010trapBoardNumber}
	STATUS current
	--&FILTNAME    "RM10010 Line Not Urgent OFF"
	--&ACTIONS     { log, normal }
	--&CLEARS      { "RM10010 Line Not Urgent ON" }
	--&MATCH       { rm10010AlmLineDdmWarningPortn "on", rm10010trapLineNumber "$2", rm10010trapBoardNumber "$3"}
	--&MESG        "DDM Warning disappears on Line Port $2 of RM10010 in Slot $3 ($A)"
	DESCRIPTION "Not urgent Line default disappeared"
	::= { rm10010traps 31 }

rm10010LineTrapUrgentGoesOn NOTIFICATION-TYPE
	OBJECTS {rm10010AlmLineDdmAlmPortn, rm10010trapLineNumber, rm10010trapBoardNumber}
	STATUS current
	--&FILTNAME    "RM10010 Line Urgent ON"
	--&ACTIONS     { log, major }
	--&MATCH       { rm10010AlmLineDdmAlmPortn "on", rm10010trapLineNumber "$2", rm10010trapBoardNumber "$3"}
	--&MESG        "DDM Alarm appears on Line Port $2 of RM10010 in Slot $3 ($A)"
	DESCRIPTION "Urgent Line default is activated"
	::= { rm10010traps 32 }

rm10010LineTrapUrgentGoesOff NOTIFICATION-TYPE
	OBJECTS {rm10010AlmLineDdmAlmPortn, rm10010trapLineNumber, rm10010trapBoardNumber}
	STATUS current
	--&FILTNAME    "RM10010 Line Urgent OFF"
	--&ACTIONS     { log, normal }
	--&CLEARS      { "RM10010 Line Urgent ON" }
	--&MATCH       { rm10010AlmLineDdmAlmPortn "on", rm10010trapLineNumber "$2", rm10010trapBoardNumber "$3"}
	--&MESG        "DDM Alarm disappears on Line Port $2 of RM10010 in Slot $3 ($A)"
	DESCRIPTION "Urgent Line default disappeared"
	::= { rm10010traps 33 }

rm10010LineTrapCritGoesOn NOTIFICATION-TYPE
	OBJECTS {rm10010AlmLineFailPortn , rm10010AlmLineHwFailPortn , rm10010trapLineNumber, rm10010trapBoardNumber}
	STATUS current
	--&FILTNAME    "RM10010 Line Fail ON"
	--&ACTIONS     { log, critical }
	--&MATCH       { rm10010AlmLineFailPortn "on", rm10010AlmLineHwFailPortn "*", rm10010trapLineNumber "$3", rm10010trapBoardNumber "$4"}
	--&MESG        "Line Port $3 Down on RM10010 in Slot $4 ($A)"

	--&FILTNAME    "RM10010 Line HW Fail ON (Hidden)"
	--&ACTIONS     { info }
	--&MATCH       { rm10010AlmLineFailPortn "*", rm10010AlmLineHwFailPortn "on", rm10010trapLineNumber "$3", rm10010trapBoardNumber "$4"}
	--&MESG        "Line Port $3 Down on RM10010 in Slot $4 ($A)"
	DESCRIPTION "Critical Line default is activated"
	::= { rm10010traps 34 }

rm10010LineTrapCritGoesOff NOTIFICATION-TYPE
	OBJECTS {rm10010AlmLineFailPortn , rm10010AlmLineHwFailPortn , rm10010trapLineNumber, rm10010trapBoardNumber}
	STATUS current
	--&FILTNAME    "RM10010 Line Fail OFF"
	--&ACTIONS     { log,  normal }
	--&CLEARS      { "RM10010 Line Fail ON" }
	--&MATCH       { rm10010AlmLineFailPortn "on", rm10010AlmLineHwFailPortn "*", rm10010trapLineNumber "$3", rm10010trapBoardNumber "$4"}
	--&MESG        "Line Port $3 Up on RM10010 in Slot $4 ($A)"

	--&FILTNAME    "RM10010 Line HW Fail OFF (Hidden)"
	--&ACTIONS     { info }
	--&MATCH       { rm10010AlmLineFailPortn "*", rm10010AlmLineHwFailPortn "on", rm10010trapLineNumber "$3", rm10010trapBoardNumber "$4"}
	--&MESG        "Line Port $3 Up on RM10010 in Slot $4 ($A)"
	DESCRIPTION "Critical Line default disappeared"
	::= { rm10010traps 35 }






--- *****************************************************
---     CLIENT TRAPS
--- *****************************************************

rm10010ClientTrapNotUrgentGoesOn NOTIFICATION-TYPE
	OBJECTS {rm10010AlmSfpDdmWarningPortn, rm10010trapPortNumber, rm10010trapBoardNumber}
	STATUS current
		--&FILTNAME    "RM10010 Client Not Urgent ON"
		--&ACTIONS     { log, minor }
		--&MATCH       { rm10010AlmSfpDdmWarningPortn "on", rm10010trapPortNumber "$2", rm10010trapBoardNumber "$3"}
		--&MESG        "DDM Warning appears on Client Port $2 of RM10010 in Slot $3 ($A)"
	DESCRIPTION "Not urgent client default is activated"
	::= { rm10010traps 40 }

rm10010ClientTrapNotUrgentGoesOff NOTIFICATION-TYPE
	OBJECTS {rm10010AlmSfpDdmWarningPortn, rm10010trapPortNumber, rm10010trapBoardNumber}
	STATUS current
		--&FILTNAME    "RM10010 Client Not Urgent OFF"
		--&ACTIONS     { log, normal }
		--&CLEARS      { "RM10010 Client Not Urgent ON" }
		--&MATCH       { rm10010AlmSfpDdmWarningPortn "on", rm10010trapPortNumber "$2", rm10010trapBoardNumber "$3"}
		--&MESG        "DDM Warning appears on Client Port $2 of RM10010 in Slot $3 ($A)"
	DESCRIPTION "Not urgent client default disappeared"
	::= { rm10010traps 41 }

rm10010ClientTrapUrgentGoesOn NOTIFICATION-TYPE
	OBJECTS {rm10010AlmSfpDdmAlmPortn, rm10010trapPortNumber, rm10010trapBoardNumber}
	STATUS current
		--&FILTNAME    "RM10010 Client Urgent ON"
		--&ACTIONS     { log, major }
		--&MATCH       { rm10010AlmSfpDdmAlmPortn "on", rm10010trapPortNumber "$2", rm10010trapBoardNumber "$3"}
		--&MESG        "DDM Alarm appears on Client Port $2 of RM10010 in Slot $3 ($A)"
	DESCRIPTION "Urgent client default is activated"
	::= { rm10010traps 42 }

rm10010ClientTrapUrgentGoesOff NOTIFICATION-TYPE
	OBJECTS {rm10010AlmSfpDdmAlmPortn, rm10010trapPortNumber, rm10010trapBoardNumber}
	STATUS current
		--&FILTNAME    "RM10010 Client Urgent OFF"
		--&ACTIONS     { log, normal }
		--&CLEARS      { "RM10010 Client Urgent ON" }
		--&MATCH       { rm10010AlmSfpDdmAlmPortn "on", rm10010trapPortNumber "$2", rm10010trapBoardNumber "$3"}
		--&MESG        "DDM Alarm disappears on Client Port $2 of RM10010 in Slot $3 ($A)"
	DESCRIPTION "Urgent client default disappeared"
	::= { rm10010traps 43 }

rm10010ClientTrapCritGoesOn NOTIFICATION-TYPE
	OBJECTS {rm10010AlmFailAccPortn, rm10010AlmHwFailAccPortn, rm10010trapPortNumber, rm10010trapBoardNumber}
	STATUS current
		--&FILTNAME    "RM10010 Client Fail ON"
		--&ACTIONS     { log, critical }
		--&MATCH       { rm10010AlmFailAccPortn "on", rm10010AlmHwFailAccPortn "*", rm10010trapPortNumber "$3", rm10010trapBoardNumber "$4"}
		--&MESG        "Client Port $3 Down on RM10010 in Slot $4 ($A)"

		--&FILTNAME    "RM10010 Client HW Fail ON (Hidden)"
		--&ACTIONS     { info }
		--&MATCH       { rm10010AlmFailAccPortn "*", rm10010AlmHwFailAccPortn "on", rm10010trapPortNumber "$3", rm10010trapBoardNumber "$4"}
		--&MESG        "Client Port $3 Down on RM10010 in Slot $4 ($A)"
	DESCRIPTION "Critical client default is activated"
	::= { rm10010traps 44 }

rm10010ClientTrapCritGoesOff NOTIFICATION-TYPE
	OBJECTS {rm10010AlmFailAccPortn, rm10010AlmHwFailAccPortn, rm10010trapPortNumber, rm10010trapBoardNumber}
	STATUS current
		--&FILTNAME    "RM10010 Client Fail OFF"
		--&ACTIONS     { log, normal }
		--&CLEARS      { "RM10010 Client Fail ON" }
		--&MATCH       { rm10010AlmFailAccPortn "on", rm10010AlmHwFailAccPortn "*", rm10010trapPortNumber "$3", rm10010trapBoardNumber "$4"}
		--&MESG        "Client Port $3 Up on RM10010 in Slot $4 ($A)"

		--&FILTNAME    "RM10010 Client HW Fail OFF (Hidden)"
		--&ACTIONS     { info }
		--&MATCH       { rm10010AlmFailAccPortn "*", rm10010AlmHwFailAccPortn "on", rm10010trapPortNumber "$3", rm10010trapBoardNumber "$4"}
		--&MESG        "Client Port $3 Up on RM10010 in Slot $4 ($A)"
	DESCRIPTION "Critical client default disappeared"
	::= { rm10010traps 45 }






--- *****************************************************
---     HW TRAPS
--- *****************************************************

rm10010PowerTrapUrgentGoesOn NOTIFICATION-TYPE
	OBJECTS {rm10010AlmDefFuseB, rm10010AlmDefFuseA , rm10010trapBoardNumber}
	STATUS current
		--&FILTNAME    "RM10010 Fuse A Fail ON"
		--&ACTIONS     { log, major }
		--&MATCH       { rm10010AlmDefFuseB "*", rm10010AlmDefFuseA "on", rm10010trapBoardNumber "$3"}
		--&MESG        "Power Input A Fail on RM10010 in Slot $3 ($A)"

		--&FILTNAME    "RM10010 Fuse B Fail ON"
		--&ACTIONS     { log, major }
		--&MATCH       { rm10010AlmDefFuseB "on", rm10010AlmDefFuseA "*", rm10010trapBoardNumber "$3"}
		--&MESG        "Power Input B Fail on RM10010 in Slot $3 ($A)"
	DESCRIPTION "Urgent power supply default is activated"
	::= { rm10010traps 50 }

rm10010PowerTrapUrgentGoesOff NOTIFICATION-TYPE
	OBJECTS {rm10010AlmDefFuseB, rm10010AlmDefFuseA , rm10010trapBoardNumber}
	STATUS current
		--&FILTNAME    "RM10010 Fuse A&B Fail OFF"
		--&ACTIONS     { log, normal}
		--&CLEARS      { "RM10010 Fuse A Fail ON", "RM10010 Fuse B Fail ON" }
		--&MATCH       { rm10010AlmDefFuseB "on", rm10010AlmDefFuseA "on", rm10010trapBoardNumber "$3"}
		--&MESG        "Power Inputs A and B Present on RM10010 in Slot $3 ($A)"
	DESCRIPTION "Urgent power supply default disappeared"
	::= { rm10010traps 51 }






END
